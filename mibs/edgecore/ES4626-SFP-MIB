ES4626-SFP-MIB DEFINITIONS ::= BEGIN

--1.5.22
IMPORTS
    OBJECT-TYPE 		  FROM SNMPv2-SMI 
    TEXTUAL-CONVENTION,RowStatus,TimeStamp, TruthValue  FROM SNMPv2-TC   	
        MODULE-IDENTITY, OBJECT-TYPE, mib-2,
    Integer32, Counter32, Gauge32,Unsigned32, NOTIFICATION-TYPE,
    IpAddress, TimeTicks,experimental             FROM SNMPv2-SMI
        MODULE-COMPLIANCE, OBJECT-GROUP,
    NOTIFICATION-GROUP               FROM SNMPv2-CONF

    TRAP-TYPE FROM RFC-1215
    
    enterprises         FROM RFC1155-SMI;
    
    DisplayString                ::= OCTET STRING    
    MacAddress    	         ::= OCTET STRING (SIZE (17))    
    						    -- a 17 octet address
                                                    -- in the
                                                    -- "canonical"
                                                    -- order 
 
InetAddressType ::= TEXTUAL-CONVENTION
    STATUS      current
    DESCRIPTION
        "A value that represents a type of Internet address.

         unknown(0)  An unknown address type.  This value MUST
                     be used if the value of the corresponding
                     InetAddress object is a zero-length string.
                     It may also be used to indicate an IP address
                     that is not in one of the formats defined
                     below.

         ipv4(1)     An IPv4 address as defined by the
                     InetAddressIPv4 textual convention.

         ipv6(2)     An IPv6 address as defined by the
                     InetAddressIPv6 textual convention.

         ipv4z(3)    A non-global IPv4 address including a zone
                     index as defined by the InetAddressIPv4z
                     textual convention.

         ipv6z(4)    A non-global IPv6 address including a zone
                     index as defined by the InetAddressIPv6z
                     textual convention.

         dns(16)     A DNS domain name as defined by the
                     InetAddressDNS textual convention.

         Each definition of a concrete InetAddressType value must be
         accompanied by a definition of a textual convention for use
         with that InetAddressType.

         To support future extensions, the InetAddressType textual
         convention SHOULD NOT be sub-typed in object type definitions.
         It MAY be sub-typed in compliance statements in order to
         require only a subset of these address types for a compliant
         implementation.

         Implementations must ensure that InetAddressType objects
         and any dependent objects (e.g., InetAddress objects) are
         consistent.  An inconsistentValue error must be generated
         if an attempt to change an InetAddressType object would,
         for example, lead to an undefined InetAddress value.  In

         particular, InetAddressType/InetAddress pairs must be
         changed together if the address type changes (e.g., from
         ipv6(2) to ipv4(1))."
    SYNTAX       INTEGER {
                     unknown(0),
                     ipv4(1),
                     ipv6(2),
                     ipv4z(3),
                     ipv6z(4),
                     dns(16)
                 }

InetAddress ::= TEXTUAL-CONVENTION
    STATUS      current
    DESCRIPTION
        "Denotes a generic Internet address.

         An InetAddress value is always interpreted within the context
         of an InetAddressType value.  Every usage of the InetAddress
         textual convention is required to specify the InetAddressType
         object that provides the context.  It is suggested that the
         InetAddressType object be logically registered before the
         object(s) that use the InetAddress textual convention, if
         they appear in the same logical row.

         The value of an InetAddress object must always be
         consistent with the value of the associated InetAddressType
         object.  Attempts to set an InetAddress object to a value
         inconsistent with the associated InetAddressType
         must fail with an inconsistentValue error.

         When this textual convention is used as the syntax of an
         index object, there may be issues with the limit of 128
         sub-identifiers specified in SMIv2, STD 58.  In this case,
         the object definition MUST include a 'SIZE' clause to
         limit the number of potential instance sub-identifiers;
         otherwise the applicable constraints MUST be stated in
         the appropriate conceptual row DESCRIPTION clauses, or
         in the surrounding documentation if there is no single
         DESCRIPTION clause that is appropriate."
    SYNTAX       OCTET STRING (SIZE (0..255))                                                    
                                                    
    VlanList ::= TEXTUAL-CONVENTION
    STATUS      current
    DESCRIPTION
         "Vlan ID range is (1..4094), 
         Each octet within this value specifies a set of eight
         vlans, with the first octet specifying vlans 1 through
         8, the second octet specifying vlans 9 through 16, etc.
         Within each octet, the most significant bit represents
         the lowest numbered vlan, and the least significant bit
         represents the highest numbered vlan.  If that bit has 
         a value of '1' then that vlan is allowed to pass ; 
         the vlan is not allowed if its bit has a value of '0'.
         the value is a changing cells:if the maximum of vlans is 8,you
         sends one octet to me;the remnant octet's value is defaulted '0',
         the remnant octet needn't to send to me."
    SYNTAX      OCTET STRING

    PortList ::= TEXTUAL-CONVENTION
    STATUS      current
    DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING
    
    EnabledStatusPrivate ::= TEXTUAL-CONVENTION
    STATUS      current
    DESCRIPTION
        "A simple status value for the object."
    SYNTAX      INTEGER { enabled(1), disabled(0) }
    
    ValidStatus ::= TEXTUAL-CONVENTION
    STATUS      current
    DESCRIPTION
        "A simple status value for the object to create and destroy
         a table entry. This is a simplified variant of RowStatus as it
         supports only two values. Setting it to valid(1) creates an entry.
         Setting it to invalid(2) destroys an entry."
    SYNTAX      INTEGER { valid(1), invalid(0) }
    
    OspfBigMetric ::= TEXTUAL-CONVENTION
    STATUS      current
    DESCRIPTION
       "The OSPF External Metric."
    SYNTAX      Integer32 (0..'FFFFFE'h)
    
    OspfAreaID ::= TEXTUAL-CONVENTION
    STATUS      current
    DESCRIPTION
       "An OSPF Area Identifier."
    SYNTAX      IpAddress
    
    SnmpAdminString ::= TEXTUAL-CONVENTION
    DISPLAY-HINT "255t"
    STATUS       current
    DESCRIPTION "An octet string containing administrative
                 information, preferably in human-readable form.

                 To facilitate internationalization, this
                 information is represented using the ISO/IEC
                 IS 10646-1 character set, encoded as an octet
                 string using the UTF-8 transformation format
                 described in [RFC2279].

                 Since additional code points are added by
                 amendments to the 10646 standard from time
                 to time, implementations must be prepared to
                 encounter any code point from 0x00000000 to
                 0x7fffffff.  Byte sequences that do not
                 correspond to the valid UTF-8 encoding of a
                 code point or are outside this range are
                 prohibited.

                 The use of control codes should be avoided.

                 When it is necessary to represent a newline,
                 the control code sequence CR LF should be used.

                 The use of leading or trailing white space should
                 be avoided.

                 For code points not directly supported by user
                 interface hardware or software, an alternative
                 means of entry and display, such as hexadecimal,
                 may be provided.

                 For information encoded in 7-bit US-ASCII,
                 the UTF-8 encoding is identical to the
                 US-ASCII encoding.

                 UTF-8 may require multiple bytes to represent a
                 single character / code point; thus the length
                 of this object in octets may be different from
                 the number of characters encoded.  Similarly,
                 size constraints refer to the number of encoded
                 octets, not the number of characters represented
                 by an encoding.

                 Note that when this TC is used for an object that
                 is used or envisioned to be used as an index, then
                 a SIZE restriction MUST be specified so that the
                 number of sub-identifiers for any object instance
                 does not exceed the limit of 128, as defined by
                 [RFC3416].

                 Note that the size of an SnmpAdminString object is
                 measured in octets, not characters.
                "
    SYNTAX       OCTET STRING (SIZE (0..255))
    
    -- InterfaceIndex contains the semantics of ifIndex and should be used
-- for any objects defined in other MIB modules that need these semantics.

InterfaceIndex ::= TEXTUAL-CONVENTION
    DISPLAY-HINT "d"
    STATUS       current
    DESCRIPTION
            "A unique value, greater than zero, for each interface or
            interface sub-layer in the managed system.  It is
            recommended that values are assigned contiguously starting
            from 1.  The value for each interface sub-layer must remain
            constant at least from one re-initialization of the entity's
            network management system to the next re-initialization."
    SYNTAX       Integer32 (1..2147483647)

InterfaceIndexOrZero ::= TEXTUAL-CONVENTION
    DISPLAY-HINT "d"
    STATUS       current
    DESCRIPTION
            "This textual convention is an extension of the
            InterfaceIndex convention.  The latter defines a greater
            than zero value used to identify an interface or interface
            sub-layer in the managed system.  This extension permits the
            additional value of zero.  the value zero is object-specific
            and must therefore be defined as part of the description of
            any object which uses this syntax.  Examples of the usage of
            zero might include situations where interface was unknown,
            or when none or all interfaces need to be referenced."
    SYNTAX       Integer32 (0..2147483647)
    
-- textual conventions

LldpChassisIdSubtype ::= TEXTUAL-CONVENTION
    STATUS      current
    DESCRIPTION
            "This TC describes the source of a chassis identifier.

            The enumeration 'chassisComponent(1)' represents a chassis
            identifier based on the value of entPhysicalAlias object
            (defined in IETF RFC 2737) for a chassis component (i.e.,
            an entPhysicalClass value of 'chassis(3)').

            The enumeration 'interfaceAlias(2)' represents a chassis
            identifier based on the value of ifAlias object (defined in
            IETF RFC 2863) for an interface on the containing chassis.

            The enumeration 'portComponent(3)' represents a chassis
            identifier based on the value of entPhysicalAlias object
            (defined in IETF RFC 2737) for a port or backplane
            component (i.e., entPhysicalClass value of 'port(10)' or
            'backplane(4)'), within the containing chassis.

            The enumeration 'macAddress(4)' represents a chassis
            identifier based on the value of a unicast source MAC address
            (encoded in network byte order and IEEE 802.3 canonical bit
            order), of a port on the containing chassis as defined in
            IEEE Std. 802-2001.

            The enumeration 'networkAddress(5)' represents a chassis
            identifier based on a network address, associated with
            a particular chassis.  The encoded address is actually
            composed of two fields.  The first field is a single octet,
            representing the IANA AddressFamilyNumbers value for the
            specific address type, and the second field is the network
            address value.

            The enumeration 'interfaceName(6)' represents a chassis
            identifier based on the value of ifName object (defined in
            IETF RFC 2863) for an interface on the containing chassis.

            The enumeration 'local(7)' represents a chassis identifier
            based on a locally defined value."
    SYNTAX  INTEGER {
            chassisComponent(1),
            interfaceAlias(2),
            portComponent(3),
            macAddress(4),
            networkAddress(5),
            interfaceName(6),
            local(7)
    }

LldpChassisId ::= TEXTUAL-CONVENTION
    STATUS      current
    DESCRIPTION
            "This TC describes the format of a chassis identifier string.
            Objects of this type are always used with an associated
            LldpChassisIdSubtype object, which identifies the format of
            the particular LldpChassisId object instance.

            If the associated LldpChassisIdSubtype object has a value of
            'chassisComponent(1)', then the octet string identifies
            a particular instance of the entPhysicalAlias object
            (defined in IETF RFC 2737) for a chassis component (i.e.,
            an entPhysicalClass value of 'chassis(3)').

            If the associated LldpChassisIdSubtype object has a value
            of 'interfaceAlias(2)', then the octet string identifies
            a particular instance of the ifAlias object (defined in
            IETF RFC 2863) for an interface on the containing chassis.
            If the particular ifAlias object does not contain any values,
            another chassis identifier type should be used.

            If the associated LldpChassisIdSubtype object has a value
            of 'portComponent(3)', then the octet string identifies a
            particular instance of the entPhysicalAlias object (defined
            in IETF RFC 2737) for a port or backplane component within
            the containing chassis.

            If the associated LldpChassisIdSubtype object has a value of
            'macAddress(4)', then this string identifies a particular
            unicast source MAC address (encoded in network byte order and
            IEEE 802.3 canonical bit order), of a port on the containing
            chassis as defined in IEEE Std. 802-2001.

            If the associated LldpChassisIdSubtype object has a value of
            'networkAddress(5)', then this string identifies a particular
            network address, encoded in network byte order, associated
            with one or more ports on the containing chassis.  The first
            octet contains the IANA Address Family Numbers enumeration
            value for the specific address type, and octets 2 through
            N contain the network address value in network byte order.

            If the associated LldpChassisIdSubtype object has a value
            of 'interfaceName(6)', then the octet string identifies
            a particular instance of the ifName object (defined in
            IETF RFC 2863) for an interface on the containing chassis.
            If the particular ifName object does not contain any values,
            another chassis identifier type should be used.

            If the associated LldpChassisIdSubtype object has a value of
            'local(7)', then this string identifies a locally assigned
            Chassis ID."
    SYNTAX      OCTET STRING (SIZE (1..255))

LldpPortIdSubtype ::= TEXTUAL-CONVENTION
    STATUS      current
    DESCRIPTION
            "This TC describes the source of a particular type of port
            identifier used in the LLDP MIB.

            The enumeration 'interfaceAlias(1)' represents a port
            identifier based on the ifAlias MIB object, defined in IETF
            RFC 2863.

            The enumeration 'portComponent(2)' represents a port
            identifier based on the value of entPhysicalAlias (defined in
            IETF RFC 2737) for a port component (i.e., entPhysicalClass
            value of 'port(10)'), within the containing chassis.

            The enumeration 'macAddress(3)' represents a port identifier
            based on a unicast source MAC address (encoded in network
            byte order and IEEE 802.3 canonical bit order), which has
            been detected by the agent and associated with a particular
            port (IEEE Std. 802-2001).

            The enumeration 'networkAddress(4)' represents a port
            identifier based on a network address, detected by the agent
            and associated with a particular port.

            The enumeration 'interfaceName(5)' represents a port
            identifier based on the ifName MIB object, defined in IETF
            RFC 2863.

            The enumeration 'agentCircuitId(6)' represents a port
            identifier based on the agent-local identifier of the circuit
            (defined in RFC 3046), detected by the agent and associated
            with a particular port.

            The enumeration 'local(7)' represents a port identifier
            based on a value locally assigned."

    SYNTAX  INTEGER {
            interfaceAlias(1),
            portComponent(2),
            macAddress(3),
            networkAddress(4),
            interfaceName(5),
            agentCircuitId(6),
            local(7)
    }

LldpPortId ::= TEXTUAL-CONVENTION
    STATUS      current
    DESCRIPTION
            "This TC describes the format of a port identifier string.
            Objects of this type are always used with an associated
            LldpPortIdSubtype object, which identifies the format of the
            particular LldpPortId object instance.

            If the associated LldpPortIdSubtype object has a value of
            'interfaceAlias(1)', then the octet string identifies a
            particular instance of the ifAlias object (defined in IETF
            RFC 2863).  If the particular ifAlias object does not contain
            any values, another port identifier type should be used.

            If the associated LldpPortIdSubtype object has a value of
            'portComponent(2)', then the octet string identifies a
            particular instance of the entPhysicalAlias object (defined
            in IETF RFC 2737) for a port or backplane component.

            If the associated LldpPortIdSubtype object has a value of
            'macAddress(3)', then this string identifies a particular
            unicast source MAC address (encoded in network byte order
            and IEEE 802.3 canonical bit order) associated with the port
            (IEEE Std. 802-2001).

            If the associated LldpPortIdSubtype object has a value of
            'networkAddress(4)', then this string identifies a network
            address associated with the port.  The first octet contains
            the IANA AddressFamilyNumbers enumeration value for the
            specific address type, and octets 2 through N contain the
            networkAddress address value in network byte order.

            If the associated LldpPortIdSubtype object has a value of
            'interfaceName(5)', then the octet string identifies a
            particular instance of the ifName object (defined in IETF
            RFC 2863).  If the particular ifName object does not contain
            any values, another port identifier type should be used.

            If the associated LldpPortIdSubtype object has a value of
            'agentCircuitId(6)', then this string identifies a agent-local
            identifier of the circuit (defined in RFC 3046).

            If the associated LldpPortIdSubtype object has a value of
            'local(7)', then this string identifies a locally
            assigned port ID."
    SYNTAX      OCTET STRING (SIZE (1..255))

LldpManAddrIfSubtype ::= TEXTUAL-CONVENTION
    STATUS      current
    DESCRIPTION
            "This TC describes the basis of a particular type of
            interface associated with the management address.

            The enumeration 'unknown(1)' represents the case where the
            interface is not known.

            The enumeration 'ifIndex(2)' represents interface identifier
            based on the ifIndex MIB object.

            The enumeration 'systemPortNumber(3)' represents interface
            identifier based on the system port numbering convention."
    REFERENCE 
            "IEEE 802.1AB-2004 section 9.4.9.5"
            
    SYNTAX  INTEGER {
            unknown(1),
            ifIndex(2),
            systemPortNumber(3)
    }

LldpManAddress ::= TEXTUAL-CONVENTION
    STATUS      current
    DESCRIPTION
            "The value of a management address associated with the LLDP
            agent that may be used to reach higher layer entities to
            assist discovery by network management.

            It should be noted that appropriate security credentials,
            such as SNMP engineId, may be required to access the LLDP
            agent using a management address.  These necessary credentials
            should be known by the network management and the objects
            associated with the credentials are not included in the
            LLDP agent."
    SYNTAX      OCTET STRING (SIZE (1..31))

LldpSystemCapabilitiesMap ::= TEXTUAL-CONVENTION
    STATUS      current
    DESCRIPTION
            "This TC describes the system capabilities.

            The bit 'other(0)' indicates that the system has capabilities
            other than those listed below.

            The bit 'repeater(1)' indicates that the system has repeater
            capability.

            The bit 'bridge(2)' indicates that the system has bridge
            capability.

            The bit 'accessPoint(3)' indicates that the system has access
            point capability.

            The bit 'router(4)' indicates that the system has router
            capability.

            The bit 'telephone(5)' indicates that the system has telephone
            capability.

            The bit 'wirelessStation(6)' indicates that the system has
            wireless Station capability.

            The bit 'stationOnly(7)' indicates that the system has only
            station capability and nothing else."
    SYNTAX  BITS {
            other(0),
            repeater(1),
            bridge(2),
            accessPoint(3),
            router(4),
            telephone(5),
            wirelessStation(6),
            stationOnly(7)
    }

LldpPortNumber ::= TEXTUAL-CONVENTION
    DISPLAY-HINT "d"
    STATUS     current 
    DESCRIPTION
            "Each port contained in the chassis (that is known to the
            LLDP agent) is uniquely identified by a port number.

            A port number has no mandatory relationship to an
            InterfaceIndex object (of the interfaces MIB, IETF RFC 2683).
            If the LLDP agent is a IEEE 802.1D, IEEE 802.1Q bridge,
            the LldpPortNumber will have the same value as the
            dot1dBasePort object (defined in IETF RFC 1493) associated
            corresponding bridge port.  If the LLDP agent is not a 
            IEEE 802.1D, IEEE 802.1Q bridge, the LldpPortNumber will
            have the same value as the the corresponding interface's
            InterfaceIndex object.

            Port numbers should be in the range of 1 and 4096 since a
            particular port is also represented by the corresponding
            port number bit in LldpPortList."
    SYNTAX 	Integer32(1..4096)

LldpPortList ::= TEXTUAL-CONVENTION
    STATUS      current
    DESCRIPTION
            "Each octet within this value specifies a set of eight ports,
            with the first octet specifying ports 1 through 8, the second
            octet specifying ports 9 through 16, etc.  Within each octet,
            the most significant bit represents the lowest numbered port,
            and the least significant bit represents the highest numbered
            port.  Thus, each port of the system is represented by a
            single bit within the value of this object.  If that bit has
            a value of '1' then that port is included in the set of ports;
            the port is not included if its bit has a value of '0'."
    REFERENCE 
            "RFC 2674, Section 5"
    SYNTAX  OCTET STRING(SIZE(0..512))  
    
TimeFilter ::= TEXTUAL-CONVENTION
    STATUS        current
    DESCRIPTION





        "To be used for the index to a table.  Allows an application
        to download only those rows changed since a particular time.
        A row is considered changed if the value of any object in the
        row changes or if the row is created or deleted.

        When sysUpTime is equal to zero, this table shall be empty.

        One entry exists for each past value of sysUpTime, except that
        the whole table is purged should sysUpTime wrap.

        As this basic row is updated new conceptual rows are created
        (which still share the now updated object values with all
        other instances).  The number of instances which are created
        is determined by the value of sysUpTime at which the basic row
        was last updated.  One instance will exist for each value of
        sysUpTime at the last update time for the row.  A new
        timeMark instance is created for each new sysUpTime value.
        Each new conceptual row will be associated with the timeMark
        instance which was created at the value of sysUpTime with
        which the conceptual row is to be associated.

        By definition all conceptual rows were updated at or after
        time zero and so at least one conceptual row (associated with
        timeMark.0) must exist for each underlying (basic) row.

        See the appendix for further discussion of this variable.

        Consider the following fooTable:

        fooTable ...
        INDEX { fooTimeMark, fooIndex }

        FooEntry {
           fooTimeMark  TimeFilter
           fooIndex     INTEGER,
           fooCounts    Counter
        }

        Should there be two basic rows in this table (fooIndex == 1,
        fooIndex == 2) and row 1 was updated most recently at time 6,
        while row 2 was updated most recently at time 8, and both rows
        had been updated on several earlier occasions such that the
        current values were 5 and 9 respectively then the following
        fooCounts instances would exist.

        fooCounts.0.1  5
        fooCounts.0.2  9
        fooCounts.1.1  5





        fooCounts.1.2  9
        fooCounts.2.1  5
        fooCounts.2.2  9
        fooCounts.3.1  5
        fooCounts.3.2  9
        fooCounts.4.1  5
        fooCounts.4.2  9
        fooCounts.5.1  5
        fooCounts.5.2  9
        fooCounts.6.1  5
        fooCounts.6.2  9
        fooCounts.7.2  9    -- note that row 1 doesn't exist for
        fooCounts.8.2  9    -- times 7 and 8"
    SYNTAX    TimeTicks    
    
Ipv6Address ::= TEXTUAL-CONVENTION
     DISPLAY-HINT "2x:"
     STATUS       current
     DESCRIPTION
       "This data type is used to model IPv6 addresses.
        This is a binary string of 16 octets in network
        byte-order."
     SYNTAX       OCTET STRING (SIZE (16))      
--********************************************************************************************************
--******************************************************************************************************** 
    accton                          OBJECT IDENTIFIER ::= { enterprises 259 }
    snmpMgt		            OBJECT IDENTIFIER ::= { accton 8 }
    cheetahSwitchMgt		    OBJECT IDENTIFIER ::= { snmpMgt 1 }
    
    ES4626-SFP	            	    OBJECT IDENTIFIER ::= { cheetahSwitchMgt 3 }
    os                     	    OBJECT IDENTIFIER ::= { ES4626-SFP 100 }     
    notifications     		  OBJECT IDENTIFIER ::= { ES4626-SFP 101 }
    conformance          	  OBJECT IDENTIFIER ::= { ES4626-SFP 102 }


--xxx.100.1 
    priSystem                     OBJECT IDENTIFIER ::= { os 1 }
--xxx.100.2
    priSpanningTree               OBJECT IDENTIFIER ::= { os 2 }
--xxx.100.3
    priPorts                 	  OBJECT IDENTIFIER ::= { os 3 }
--xxx.100.4
    priIpConfig			  OBJECT IDENTIFIER ::= { os 4 } 
--xxx.100.5  
    priVlanConfig                 OBJECT IDENTIFIER ::= { os 5 }    
--xxx.100.6
    priJumblyStacking             OBJECT IDENTIFIER ::= { os 6 }
--xxx.100.7
    priUamSecurityPortMib         OBJECT IDENTIFIER ::= { os 7 }
--xxx.100.8
    priIgmpSnoopingMib            OBJECT IDENTIFIER ::= { os 8 }
--xxx.100.9
    priQinQmib         	   	  OBJECT IDENTIFIER ::= { os 9 } 
--xxx.100.10
    prisecurity			  OBJECT IDENTIFIER ::= { os 10 } 
--xxx.100.11
    priQos    			  OBJECT IDENTIFIER ::= { os 11 } 
--xxx.100.12
    primirror    		  OBJECT IDENTIFIER ::= { os 12 } 
--xxx.100.13
    pridhcp    		  	  OBJECT IDENTIFIER ::= { os 13 } 
--xxx.100.14
    priportGroup    		  OBJECT IDENTIFIER ::= { os 14 }     
--xxx.100.15    
    prisnmpMgt         	  	  OBJECT IDENTIFIER ::= { os 15 }  
--xxx.100.16
    l3               		  OBJECT IDENTIFIER ::= { os 16 }         
--xxx.100.17
    sntpMgt               	  OBJECT IDENTIFIER ::= { os 17 }
--xxx.100.18   
    urpf                          OBJECT IDENTIFIER ::= { os 18 }
--xxx.100.20   
    
    dcscm                         OBJECT IDENTIFIER ::= { os 20 }
--xxx.100.21   
    dcscm6                        OBJECT IDENTIFIER ::= { os 21 }      
--xxx.100.22      
    prClusterv2                   OBJECT IDENTIFIER ::= { os 22 }
--xxx.100.23   
    dns                           OBJECT IDENTIFIER ::= { os 23 } 
--xxx.100.24   
    lldpMIB                       OBJECT IDENTIFIER ::= { os 24 } 
--xxx.100.25   
    ntpSnmpMIB                    OBJECT IDENTIFIER ::= { os 25 }
--xxx.100.26
    priPoeConfig    		  OBJECT IDENTIFIER ::= { os 26 }  
--xxx.100.27
    priQos2    		          OBJECT IDENTIFIER ::= { os 27 }                  
    
--xxx.100.28
    mabMgt    		          OBJECT IDENTIFIER ::= { os 28 }    
          
lldpNotifications            OBJECT IDENTIFIER ::= { lldpMIB 0 }
lldpObjects                  OBJECT IDENTIFIER ::= { lldpMIB 1 }
lldpConformance              OBJECT IDENTIFIER ::= { lldpMIB 2 } 

--
-- LLDP MIB Objects
--

lldpConfiguration            OBJECT IDENTIFIER ::= { lldpObjects 1 }
lldpStatistics               OBJECT IDENTIFIER ::= { lldpObjects 2 }
lldpLocalSystemData          OBJECT IDENTIFIER ::= { lldpObjects 3 }
lldpRemoteSystemsData        OBJECT IDENTIFIER ::= { lldpObjects 4 }
lldpExtensions               OBJECT IDENTIFIER ::= { lldpObjects 5 }

--
ntpSnmpMIBObjects  OBJECT IDENTIFIER ::= { ntpSnmpMIB 1 }

-- MIB contains 6 groups

ntpEntInfo         OBJECT IDENTIFIER ::= { ntpSnmpMIBObjects 1 }
ntpEntStatus       OBJECT IDENTIFIER ::= { ntpSnmpMIBObjects 2 }  
            
                     
--********************************************************************************************************
--******************************************************************************************************** 

-- (xxx.100.1)   System group

--xxx.100.1.1
sysResetUnit OBJECT-TYPE
    SYNTAX  INTEGER {
                noReset(1),
                setfactory (2),
                coldReset (3)
            }
    MAX-ACCESS  read-write
    STATUS  current
    DESCRIPTION
        " setfactory(2)
	  coldReset(3)
	  noReset(1)
	  default the status is 1 "
    ::= { priSystem  1}
    
--xxx.100.1.2
sysHardwareVersion OBJECT-TYPE
    SYNTAX  DisplayString (SIZE(1..32))
    MAX-ACCESS  read-only
    STATUS  current
    DESCRIPTION
        "The version information of switch hardware "
    ::= { priSystem  2 }
    
--xxx.100.1.3
sysSoftwareVersion OBJECT-TYPE
    SYNTAX  DisplayString (SIZE(1..32))
    MAX-ACCESS  read-only
    STATUS  current
    DESCRIPTION
        "The version information of switch software "
    ::= { priSystem  3 }
    
--xxx.100.1.4
sysStackFlag OBJECT-TYPE
     SYNTAX  INTEGER {
             stack(1),
             noStack (2)
            }
    MAX-ACCESS  read-only
    STATUS  current
    DESCRIPTION
        "If it is the status of stacking"
    ::= { priSystem  4 }
    
--xxx.100.1.5
sysCPUMac OBJECT-TYPE
    SYNTAX  MacAddress (SIZE(17))
    MAX-ACCESS  read-only
    STATUS  current
    DESCRIPTION
       "The MAC Address is used for switch data transfers"
    ::= { priSystem  5 }

--xxx.100.1.6
sysWriteConfig OBJECT-TYPE
    SYNTAX  INTEGER {
                write(1)
            }
    MAX-ACCESS  read-write
    STATUS  current
    DESCRIPTION
        "write(1)save the current configuration"
    ::= { priSystem  6 }  

--xxx.100.1.7
sysPowerStateTable OBJECT-TYPE 
    SYNTAX  SEQUENCE OF SysPowerStateEntry
    MAX-ACCESS  not-accessible
    STATUS  current
    DESCRIPTION
        "the power supply status is only used for chassis switch"
    ::= { priSystem   7}

--xxx.100.1.7.1
sysPowerStateEntry OBJECT-TYPE
        SYNTAX  SysPowerStateEntry
        MAX-ACCESS  not-accessible
        STATUS  current
        DESCRIPTION
            "power supply status"
        INDEX   { sysPowerSlotIndex }
        ::= { sysPowerStateTable 1 }

SysPowerStateEntry
        ::= SEQUENCE
            {
                sysPowerSlotIndex         INTEGER,
                sysPowerState		  INTEGER,
                sysPowerValue		  INTEGER,
                sysPowerType	  	  INTEGER,
                sysPowerStatus		  INTEGER
            }
            
--xxx.100.1.7.1.1
sysPowerSlotIndex OBJECT-TYPE
        SYNTAX  INTEGER 
        MAX-ACCESS  not-accessible
        STATUS  current
        DESCRIPTION
            "Module model No."
        ::= { sysPowerStateEntry 1 }
            
--xxx.100.1.7.1.2         
sysPowerState  OBJECT-TYPE
       	SYNTAX      INTEGER
        {
            sysPowerInstalled(1),
            sysPowerNotInstalled(0)
        }
        MAX-ACCESS  read-only
        STATUS      current
        DESCRIPTION "if the power supply insert"
        ::= { sysPowerStateEntry 2 }

--xxx.100.1.7.1.3
sysPowerValue OBJECT-TYPE
         SYNTAX  INTEGER
         MAX-ACCESS  read-only
         STATUS  current
         DESCRIPTION "Power Value"
            ::= { sysPowerStateEntry 3 }
                        
--xxx.100.1.7.1.4
sysPowerType OBJECT-TYPE
         SYNTAX  INTEGER
         {
            systemPower(0),
            poePower(1)
         }
         MAX-ACCESS  read-only
         STATUS  current
         DESCRIPTION "Power Type"
            ::= { sysPowerStateEntry 4 }       
            
--xxx.100.1.7.1.5
sysPowerStatus OBJECT-TYPE
         SYNTAX  INTEGER
         {
            normal(0),
            abnormal(1),
            na(2)
         }
         MAX-ACCESS  read-only
         STATUS  current
         DESCRIPTION "Power Status"
            ::= { sysPowerStateEntry 5 }  
                         
--xxx.100.1.8
sysSlotTable OBJECT-TYPE 
    SYNTAX  SEQUENCE OF SysSlotEntry
    MAX-ACCESS  not-accessible
    STATUS  current
    DESCRIPTION
        "machine information,it is only used by chassis."
    ::= { priSystem   8}

--xxx.100.1.8.1
sysSlotEntry OBJECT-TYPE
        SYNTAX  SysSlotEntry
        MAX-ACCESS  not-accessible
        STATUS  current
        DESCRIPTION
            "Switch information"
        INDEX   { sysSlotIndex }
        ::= { sysSlotTable 1 }
        
SysSlotEntry
        ::= SEQUENCE
            {
            	sysSlotIndex			INTEGER,
                sysCPUType			DisplayString,            	
                sysCPUFiveSecondIdle		INTEGER,
                sysCPUThirtySecondIdle		INTEGER,
                sysCPUFiveMinuteIdle		INTEGER,
                sysCPUIdle			INTEGER,
                sysMemorySize			INTEGER,
                sysMemoryBusy			INTEGER,
                sysFlashSize			INTEGER,
                sysTemperature			INTEGER,
                sysCpuUsage			INTEGER	
            }
            
--xxx.100.1.8.1.1
sysSlotIndex OBJECT-TYPE
            SYNTAX  INTEGER 
            MAX-ACCESS  not-accessible
            STATUS  current
            DESCRIPTION
                "Module Model No."
            ::= { sysSlotEntry 1 }

--xxx.100.1.8.1.2
sysCPUType OBJECT-TYPE
    SYNTAX  DisplayString
    MAX-ACCESS  read-only
    STATUS  current
    DESCRIPTION
        "CPU type"
    ::= { sysSlotEntry  2}

--xxx.100.1.8.1.3
sysCPUFiveSecondIdle OBJECT-TYPE
    SYNTAX  INTEGER
    MAX-ACCESS  read-only
    STATUS  current
    DESCRIPTION
        "Last  5 second CPU IDLE"
    ::= { sysSlotEntry  3 }  
    
--xxx.100.1.8.1.4
sysCPUThirtySecondIdle OBJECT-TYPE
    SYNTAX  INTEGER
    MAX-ACCESS  read-only
    STATUS  current
    DESCRIPTION
        "Last 30 second CPU IDLE"
    ::= { sysSlotEntry  4 } 
    
--xxx.100.1.8.1.5
sysCPUFiveMinuteIdle OBJECT-TYPE
    SYNTAX  INTEGER
    MAX-ACCESS  read-only
    STATUS  current
    DESCRIPTION
        "Last  5 minute CPU IDLE"
    ::= { sysSlotEntry  5 } 
    
--xxx.100.1.8.1.6
sysCPUIdle OBJECT-TYPE
    SYNTAX  INTEGER
    MAX-ACCESS  read-only
    STATUS  current
    DESCRIPTION
        "From  running  CPU IDLE"
    ::= { sysSlotEntry  6 }  
    
 --xxx.100.1.8.1.7
sysMemorySize OBJECT-TYPE
    SYNTAX  INTEGER
    MAX-ACCESS  read-only
    STATUS  current
    DESCRIPTION
        "memory size"
    ::= { sysSlotEntry  7 }  
    
 --xxx.100.1.8.1.8
sysMemoryBusy OBJECT-TYPE
    SYNTAX  INTEGER
    MAX-ACCESS  read-only
    STATUS  current
    DESCRIPTION
        "memory usage rent"
    ::= { sysSlotEntry  8 } 

 --xxx.100.1.8.1.9
sysFlashSize OBJECT-TYPE
    SYNTAX  INTEGER
    MAX-ACCESS  read-only
    STATUS  current
    DESCRIPTION
        "The flash capacity of this slot."
    ::= { sysSlotEntry  9 }   

 --xxx.100.1.8.1.10
sysTemperature OBJECT-TYPE
    SYNTAX  INTEGER
    MAX-ACCESS  read-only
    STATUS  current
    DESCRIPTION
        "The Temperature of this slot.80 is 80centigrade"
    ::= { sysSlotEntry  10 }  

--xxx.100.1.8.1.11
sysCpuUsage OBJECT-TYPE
    SYNTAX  INTEGER
    MAX-ACCESS  read-only
    STATUS  current
    DESCRIPTION
        "The CPU usage of this slot."
    ::= { sysSlotEntry  11 }     
    
--********************************************************************************************************

--xxx.100.1.9
switchInfoTable OBJECT-TYPE
        SYNTAX      SEQUENCE OF SwitchInfoEntry
        MAX-ACCESS  not-accessible
        STATUS      current
        DESCRIPTION "Table of descriptive and status information about
                     switches in this system."
        ::= { priSystem 9 }
        
--xxx.100.1.9.1
switchInfoEntry OBJECT-TYPE
        SYNTAX      SwitchInfoEntry
        MAX-ACCESS  not-accessible
        STATUS      current
        DESCRIPTION "An entry in the table, containing information
                     about a single switch in this system."
        INDEX       { swSlotIndex , swUnitIndex }
        ::= { switchInfoTable 1 }

SwitchInfoEntry ::= SEQUENCE
{
    swSlotIndex             INTEGER,
    swUnitIndex             INTEGER,
    swModuleType            INTEGER
}

--xxx.100.1.9.1.1
swSlotIndex OBJECT-TYPE
        SYNTAX      INTEGER
        MAX-ACCESS  read-only
        STATUS      current
        DESCRIPTION "This object identifies the slot within the switch
                     for which this entry contains information.                    
                     While for the chassis device, the value is real switch slot number."
        ::= { switchInfoEntry 1 }
        
--xxx.100.1.9.1.2
swUnitIndex OBJECT-TYPE
        SYNTAX      INTEGER
        MAX-ACCESS  read-only
        STATUS      current
        DESCRIPTION "This object identifies the switch within the system
                     for which this entry contains information. This
                     value can never be greater than switchNumber."
        ::= { switchInfoEntry 2 }

--xxx.100.1.9.1.3
swModuleType OBJECT-TYPE
  SYNTAX      INTEGER
  {
		typeMFC(0),
		typeSFC(1),
		type1GS(2),
		type1GL(3),
		type100M1GT(4),
		type10M100MT(8),		   
		type1-M12GB(101),
		type1-12GT(102),        
		type1-210Gx(103),       
		type1-110Gx(104),       
		type1-CPU8245(105),      
		type1-BACKPLANE(106),    
		type1-24GB(107),         
		type1-24GT(108),         
		type1-36TX(109),         
		type1-4GX32TX(110),      
		type1-16FX(111),         
		type1-ES2GB(112),        
		type1-M4GX24TX(113),     
		type1-ES(114),           
		type1-MI(115),           
		type1-MII(116),          
		type1-12GB(117),         
		type1-M8GB(118),  
		type1-2XFP8GX16GB(119), 
		type1-8GX16GB(120), 
		type1-4GX24TX(121), 
		type1-L-M4GX24TX(122), 
		type1-1XFP8GX16GB(123), 
		type1-2XFP12GX12GT(124), 
		type1-12GX12GT(125), 
		type1-1XFP12GX12GT(126), 
		type1-48GT(127), 
		type1-M1XFP12GX12GT(128), 
		type1-4XFP(129), 
		type1-48GB(130), 
		type1-M44GT(131), 
		type1-M1XFP12GX12GB(132), 
		type1-12GX12GB(133), 
		type1-2XFP12GX12GB(134),
		type1-2XFP24GB12GT(136),
		type1-24GB12GT(137),
		type1-NEWMI(138),
		type1-M1XFP12GX12GTR4(139),
		type1-12GX12GTR4(140),
		type1-2XFP12GX12GTR4(141),
		type2-M12GB(165),        
		type2-12GT(166),         
		type2-210Gx(167),        
		type2-110Gx(168),        
		type2-CPU8245(169),      
		type2-BACKPLANE(170),    
		type2-24GB(171),         
		type2-24GT(172),         
		type2-36TX(173),         
		type2-4GX32TX(174),      
		type2-16FX(175),         
		type2-ES2GB(176),        
		type2-M4GX24TX(177),     
		type2-ES(178),           
		type2-MI(179),           
		type2-MII(180),          
		type2-12GB(181),         
		type2-M8GB(182),        
		type2-2XFP8GX16GB(183),        
		type2-8GX16GB(184),     
		type2-4GX24TX(185),         
		type2-L-M4GX24TX(186),          
		type2-1XFP8GX16GB(187),      
		type2-2XFP12GX12GT(188),      
		type2-12GX12GT(189),          
		type2-1XFP12GX12GT(190),          
		type2-48GT(191),        
		type2-M1XFP12GX12GT(192), 
		type2-4XFP(193), 
		type2-48GB(194), 
		type2-M44GT(195), 
		type2-M1XFP12GX12GB(196), 
		type2-12GX12GB(197), 
		type2-2XFP12GX12GB(198),
		type2-2XFP24GB12GT(200),
		type2-24GB12GT(201),
		type2-NEWMI(202),    
		type2-M1XFP12GX12GTR4(203), 
		type2-12GX12GTR4(204), 
		type2-2XFP12GX12GTR4(205), 
		type3-M (228),
		type3-MI(229),
		type3-24GT(231),
		type3-24GB(232),
		type3-4XFP(234)
  } 
        MAX-ACCESS  read-only
        STATUS      current
        DESCRIPTION "Type of expansion module in this switch slot."
        ::= { switchInfoEntry 3 }   

--xxx.100.1.10
switchFileCopy  OBJECT 	IDENTIFIER ::= { priSystem 10 }

--xxx.100.1.10.1
fileUserName OBJECT-TYPE
	    SYNTAX      DisplayString (SIZE(1..100))
	    MAX-ACCESS  read-write
	    STATUS      current
	    DESCRIPTION
	        "ftp user name"
	    ::= { switchFileCopy  1 }
	    
--xxx.100.1.10.2
fileUserPassword OBJECT-TYPE
	    SYNTAX      DisplayString (SIZE(1..100))
	    MAX-ACCESS  read-write
	    STATUS      current
	    DESCRIPTION
	        "ftp user password"
	    ::= { switchFileCopy  2 }
	    
--xxx.100.1.10.3
fileIPaddress OBJECT-TYPE
	    SYNTAX      DisplayString (SIZE(1..100))
	    MAX-ACCESS  read-write
	    STATUS      current
	    DESCRIPTION
	        "ftp or tftp server ip address"
	    ::= { switchFileCopy  3 }

--xxx.100.1.10.4
sourceFileCopy OBJECT-TYPE
	    SYNTAX      DisplayString (SIZE(1..100))
	    MAX-ACCESS  read-write
	    STATUS      current
	    DESCRIPTION
	        "Source file name or Copy from current system configuration
	                   ."
	    ::= { switchFileCopy  4 }

--xxx.100.1.10.5
destinationFileCopy OBJECT-TYPE
	    SYNTAX      DisplayString  (SIZE(1..100))
	    MAX-ACCESS  read-write
	    STATUS      current
	    DESCRIPTION
	        "Destination file name or Copy to startup configuration."
	    ::= { switchFileCopy  5 }

--xxx.100.1.10.6
fileCopyMode OBJECT-TYPE
            SYNTAX  INTEGER
            	    {
            	    	ascii(0),
               		binary(1)
            	    }
            MAX-ACCESS  read-write
            STATUS  current
            DESCRIPTION
                "ascii(0): ASCII file mode;
                 binary(1): Binary file mode."
            ::= { switchFileCopy  6 } 
            
--xxx.100.1.10.7
fileCopyUseMode OBJECT-TYPE
            SYNTAX  INTEGER
            	    {
            	    	ftp(1),
               		tftp(2)
            	    }
            MAX-ACCESS  read-write
            STATUS  current
            DESCRIPTION
                "ftp(1): ftp server or client;
                 tftp(2): tftp server or client."
            ::= { switchFileCopy  7 } 

--xxx.100.1.10.8
fileCopy OBJECT-TYPE
            SYNTAX  INTEGER
            	    {
               		upload(1),
               		download(2)
            	    }
	    MAX-ACCESS  read-write
	    STATUS      current
	    DESCRIPTION
            "File copy configurate."
    	    ::= { switchFileCopy  8 }
    	    
--xxx.100.1.10.9
fileCopyResult OBJECT-TYPE
            SYNTAX  INTEGER
            	    {
            	        error(0),
               		ok(1),
               		uploading(2),
               		downloading(3),
               		idle(4)
            	    }
	    MAX-ACCESS  read-only
	    STATUS      current
	    DESCRIPTION
            "The result of file copy:error(0):copy file failure;ok(1):copy file success;
            uploading(2):in process of upload file;downloading(3):in process of download file;
            idle(4):be out of copy file."
    	    ::= { switchFileCopy  9 }
--xxx.100.1.11
    switchInfo            	  OBJECT IDENTIFIER ::= { priSystem 11 } 

--xxx.100.1.11.1
switchCPUType OBJECT-TYPE
    SYNTAX  DisplayString
    MAX-ACCESS  read-only
    STATUS  current
    DESCRIPTION
        "The CPU type of switch"
    ::= { switchInfo  1}

--xxx.100.1.11.2
switchCPUFiveSecondIdle OBJECT-TYPE
    SYNTAX  INTEGER
    MAX-ACCESS  read-only
    STATUS  current
    DESCRIPTION
        "Last  5 second CPU IDLE"
    ::= { switchInfo  2 }  
    
--xxx.100.1.11.3
switchCPUThirtySecondIdle OBJECT-TYPE
    SYNTAX  INTEGER
    MAX-ACCESS  read-only
    STATUS  current
    DESCRIPTION
        "Last 30 second CPU IDLE"
    ::= { switchInfo  3 } 
    
--xxx.100.1.11.4
switchCPUFiveMinuteIdle OBJECT-TYPE
    SYNTAX  INTEGER
    MAX-ACCESS  read-only
    STATUS  current
    DESCRIPTION
        "Last  5 minute CPU IDLE"
    ::= { switchInfo  4 } 
    
--xxx.100.1.11.5
switchCPUIdle OBJECT-TYPE
    SYNTAX  INTEGER
    MAX-ACCESS  read-only
    STATUS  current
    DESCRIPTION
        "From  running  CPU IDLE"
    ::= { switchInfo  5 }  
    
 --xxx.100.1.11.6
switchMemorySize OBJECT-TYPE
    SYNTAX  INTEGER
    MAX-ACCESS  read-only
    STATUS  current
    DESCRIPTION
        "memory size"
    ::= { switchInfo  6 }  
    
 --xxx.100.1.11.7
switchMemoryBusy OBJECT-TYPE
    SYNTAX  INTEGER
    MAX-ACCESS  read-only
    STATUS  current
    DESCRIPTION
        "memory usage rent"
    ::= { switchInfo  7 } 

 --xxx.100.1.11.8
switchFlashSize OBJECT-TYPE
    SYNTAX  INTEGER
    MAX-ACCESS  read-only
    STATUS  current
    DESCRIPTION
        "The flash capacity of switch."
    ::= { switchInfo  8 }   

 --xxx.100.1.11.9
switchTemperature OBJECT-TYPE
    SYNTAX  INTEGER
    MAX-ACCESS  read-only
    STATUS  current
    DESCRIPTION
        "The Temperature of switch.80 is 80centigrade"
    ::= { switchInfo  9 }  

--xxx.100.1.11.10
switchCpuUsage OBJECT-TYPE
    SYNTAX  INTEGER
    MAX-ACCESS  read-only
    STATUS  current
    DESCRIPTION
        "The CPU usage of switch."
    ::= { switchInfo  10 }  
    
--xxx.100.1.12
sysFanTable OBJECT-TYPE 
    SYNTAX  SEQUENCE OF SysFanEntry
    MAX-ACCESS  not-accessible
    STATUS  current
    DESCRIPTION
        " the state of fan."
    ::= { priSystem   12}

--xxx.100.1.12.1
sysFanEntry OBJECT-TYPE
        SYNTAX  SysFanEntry
        MAX-ACCESS  not-accessible
        STATUS  current
        DESCRIPTION "fan supply status"
        INDEX   { sysFanIndex }
        ::= { sysFanTable 1 }
        
SysFanEntry
        ::= SEQUENCE
            {
            	sysFanIndex	      INTEGER,
                sysFanInserted        INTEGER,
                sysFanStatus	      INTEGER,
                sysFanSpeed	      INTEGER
            }
            
--xxx.100.1.12.1.1.1
sysFanIndex OBJECT-TYPE
        SYNTAX  INTEGER
        MAX-ACCESS  not-accessible
        STATUS  current
        DESCRIPTION "system fan entry index"
        ::= { sysFanEntry 1 }

--xxx.100.1.12.1.1.2
sysFanInserted  OBJECT-TYPE
    SYNTAX      INTEGER
        {
            sysFanNotInstalled(0),
            sysFanInstalled(1)            
        }
        MAX-ACCESS  read-only
        STATUS      current
        DESCRIPTION "Whether the slot fan is installed or not."
        ::= { sysFanEntry 2 } 
        
--xxx.100.1.12.1.1.3
sysFanStatus  OBJECT-TYPE
    SYNTAX      INTEGER
        {
            abnormal(1),
            normal(0)            
        }
        MAX-ACCESS  read-only
        STATUS      current
        DESCRIPTION "Whether the slot fan is normal or abnormal."
        ::= { sysFanEntry 3 } 
                
--xxx.100.1.12.1.1.4
sysFanSpeed OBJECT-TYPE
	SYNTAX  INTEGER
		{
		    none(0),
		    low(1),
		    medium(2),
		    high(3)
		}
    MAX-ACCESS  read-write
	STATUS	current
	DESCRIPTION
	"Status of Fan. Status: Low(1), Medium(2), High(3), none(0) is readonly"
    ::= { sysFanEntry  4 }    
                             
--********************************************************************************************************
--********************************************************************************************************  
        
-- (xxx.100.2)   Spanning tree group

--xxx.100.2.1 
spanGlobalEnable OBJECT-TYPE
    SYNTAX  INTEGER {
                enable (1),
                disable (2)
            }
    MAX-ACCESS  read-write
    STATUS  current
    DESCRIPTION
        " Enable or disable the Spanning Tree algorithm in the switch."
    ::= { priSpanningTree  1 }
    
--******************************************************************************************************** 
--xxx.100.2.2
    mstpMgt               	  	  OBJECT IDENTIFIER ::= { priSpanningTree 2 }
--xxx.100.2.2.1
    mstpSystemGroup               	  OBJECT IDENTIFIER ::= { mstpMgt 1 }  
--xxx.100.2.2.1.1
        mstpEnable OBJECT-TYPE
            SYNTAX  INTEGER  
            	   {
			enable(1),
			disable(0)
                    }         	
            MAX-ACCESS  read-create
            STATUS  current
            DESCRIPTION
                "Enable or disable the Spanning Tree algorithm in the switch."
            ::= { mstpSystemGroup  1 }

--xxx.100.2.2.1.2
        mstpTCFlush OBJECT-TYPE
            SYNTAX  INTEGER
            	   {
			enable(1),
			disable(2),
			protect(3)
                    }             
            MAX-ACCESS  read-create
            STATUS  current
            DESCRIPTION
                "configure global style of TC FLUSH"
             ::= { mstpSystemGroup  2 }     
--xxx.100.2.2.1.3
        mstpForwardTime OBJECT-TYPE
            SYNTAX  INTEGER           	
            MAX-ACCESS  read-only
            STATUS  current
            DESCRIPTION
                "This time value, measured in units of hundredths of a second, 
                controls how fast a port changes its spanning state when moving 
                towards the Forwarding state.  The value determines how long the 
                port stays in each of the Listening and Learning states, which 
                precede the Forwarding state.  This value is also used, when a 
                topology change has been detected and is underway, to age all 
                dynamic entries in the Forwarding Database."
            ::= { mstpSystemGroup  3 }

--xxx.100.2.2.1.4
        mstpHelloTime OBJECT-TYPE
            SYNTAX  INTEGER    
            MAX-ACCESS  read-only
            STATUS  current
            DESCRIPTION
                "The amount of time between the transmission of Configuration 
                bridge PDUs by this node on any port when it is the root of 
                the spanning tree or trying to become so, in units of hundredths 
                of a second. This is the actual value that this bridge is currently using."
            ::= { mstpSystemGroup  4 }
              
--xxx.100.2.2.1.5
        mstpMaxage OBJECT-TYPE
            SYNTAX  INTEGER          	
            MAX-ACCESS  read-only
            STATUS  current
            DESCRIPTION
                "The maximum age of Spanning Tree Protocol information learned 
                from the network on any port before it is discarded, in units 
                of hundredths of a second.  This is the actual value that this 
                bridge is currently using."
            ::= { mstpSystemGroup  5 }

--xxx.100.2.2.1.6
        mstpMaxhop OBJECT-TYPE
            SYNTAX  INTEGER (1..40)
            MAX-ACCESS  read-create
            STATUS  current
            DESCRIPTION
                "setting global Maxhop of mstp"
            ::= { mstpSystemGroup  6 }  
--xxx.100.2.2.1.7
        mstpMode OBJECT-TYPE
            SYNTAX  INTEGER         
            	   {
			stp(0),
			rstp(2),			
			mstp(3)
                    }                 	
            MAX-ACCESS  read-create
            STATUS  current
            DESCRIPTION
               "setting global mode of mstp,stp or rstp"
            ::= { mstpSystemGroup  7 }

--xxx.100.2.2.1.8
        mstpName OBJECT-TYPE
            SYNTAX  DisplayString (SIZE(1..32))
            MAX-ACCESS  read-create
            STATUS  current
            DESCRIPTION
                "setting the name of mst"
            ::= { mstpSystemGroup  8 }  
--xxx.100.2.2.1.9
        mstpRevisionLevel OBJECT-TYPE
            SYNTAX  INTEGER  (0..65535)          	
            MAX-ACCESS  read-create
            STATUS  current
            DESCRIPTION
                "setting the global revision level of mstp"
            ::= { mstpSystemGroup  9 }

--xxx.100.2.2.1.10
        mstpBridgeForwardDelay OBJECT-TYPE
            SYNTAX  INTEGER (4..30)           	
            MAX-ACCESS  read-create
            STATUS  current
            DESCRIPTION
                "setting global Forwardtime of mstp"
            ::= { mstpSystemGroup  10 }
            
--xxx.100.2.2.1.11
        mstpBridgeHelloTime OBJECT-TYPE
            SYNTAX  INTEGER (1..10)    
            MAX-ACCESS  read-create
            STATUS  current
            DESCRIPTION
                "setting global HelloTime of mstp"
            ::= { mstpSystemGroup  11 }
         
--xxx.100.2.2.1.12
        mstpBridgeMaxage OBJECT-TYPE
            SYNTAX  INTEGER   (6..40)         	
            MAX-ACCESS  read-create
            STATUS  current
            DESCRIPTION
                "setting global Maxage of mstp"
            ::= { mstpSystemGroup  12 } 

--xxx.100.2.2.3
mstpInstancePortTable OBJECT-TYPE 
    SYNTAX  SEQUENCE OF MstpInstancePortEntry
    MAX-ACCESS  not-accessible
    STATUS  current
    DESCRIPTION
        " interrelated parameter list of instance and port "
    ::= { mstpMgt   3}
            
--xxx.100.2.2.3.1
mstpInstancePortEntry OBJECT-TYPE
        SYNTAX  MstpInstancePortEntry
        MAX-ACCESS  not-accessible
        STATUS  current
        DESCRIPTION
            " The index of this table is instance ID and port index" 
        INDEX   { mstpInstancePortInstanceID,mstpInstancePortPortIndex }
        ::= { mstpInstancePortTable 1 }

MstpInstancePortEntry
        ::= SEQUENCE
            {
                mstpInstancePortInstanceID               		INTEGER,
                mstpInstancePortPortIndex				INTEGER,
                mstpInstancePortCost					INTEGER,
                mstpInstancePortPriority				INTEGER,
                mstpInstancePortRootGuard				INTEGER
            }
            
--xxx.100.2.2.3.1.1
mstpInstancePortInstanceID  OBJECT-TYPE
            SYNTAX  INTEGER 
            MAX-ACCESS  not-accessible
            STATUS  current
            DESCRIPTION
                " instance ID"
            ::= { mstpInstancePortEntry 1 }
            
--xxx.100.2.2.3.1.2         
mstpInstancePortPortIndex  OBJECT-TYPE
	SYNTAX      INTEGER
        MAX-ACCESS  not-accessible
        STATUS      current
        DESCRIPTION "port index"
        ::= { mstpInstancePortEntry 2 }
--xxx.100.2.2.3.1.3         
mstpInstancePortCost  OBJECT-TYPE 
        SYNTAX      INTEGER (1..200000000)
        MAX-ACCESS  read-create
        STATUS      current
        DESCRIPTION "port cost of port under the special instance"
        ::= { mstpInstancePortEntry 3 }  
--xxx.100.2.2.3.1.4         
mstpInstancePortPriority  OBJECT-TYPE
        SYNTAX      INTEGER (0..240)
        MAX-ACCESS  read-create
        STATUS      current
        DESCRIPTION "port priority of port under the special instance"
        ::= { mstpInstancePortEntry 4 } 
         
--xxx.100.2.2.3.1.5        
mstpInstancePortRootGuard  OBJECT-TYPE
        SYNTAX      INTEGER
            	   {
			enable(1),
			disable(0)
                    }          
        MAX-ACCESS  read-create
        STATUS      current
        DESCRIPTION "rootguard enable/disable on the current instance"
        ::= { mstpInstancePortEntry 5 }                               

--xxx.100.2.2.2
mstpInstanceTable OBJECT-TYPE 
    SYNTAX  SEQUENCE OF MstpInstanceEntry
    MAX-ACCESS  not-accessible
    STATUS  current
    DESCRIPTION
        " correlative information list with instance"
    ::= { mstpMgt   2}
            
--xxx.100.2.2.2.1
mstpInstanceEntry OBJECT-TYPE
        SYNTAX  MstpInstanceEntry
        MAX-ACCESS  not-accessible
        STATUS  current
        DESCRIPTION
            " The index of this table is instance ID"
        INDEX   { mstpInstanceID}
        ::= { mstpInstanceTable 1 }

MstpInstanceEntry
        ::= SEQUENCE
            {
                mstpInstanceID               			INTEGER,
                mstpInstanceVlans				DisplayString,
                mstpInstanceSwitchPriority			INTEGER
            }
            
--xxx.100.2.2.2.1.1
mstpInstanceID  OBJECT-TYPE
            SYNTAX  INTEGER 
            MAX-ACCESS  not-accessible
            STATUS  current
            DESCRIPTION
                " instance ID"
            ::= { mstpInstanceEntry 1 }
            
--xxx.100.2.2.2.1.2         
mstpInstanceVlans  OBJECT-TYPE
	SYNTAX      DisplayString (SIZE(0..512))
        MAX-ACCESS  read-create
        STATUS      current
        DESCRIPTION " the map of vlans to instance.The input format is  consonant with cli."
        ::= { mstpInstanceEntry 2 }
--xxx.100.2.2.2.1.3         
mstpInstanceSwitchPriority  OBJECT-TYPE 
        SYNTAX      INTEGER (0..61440)
        MAX-ACCESS  read-create
        STATUS      current
        DESCRIPTION " The priority of the router in the special instance."
        ::= { mstpInstanceEntry 3 }  
                                                   
--********************************************************************************************************                                                   
--xxx.100.2.2.4
mstpPortInfoTable OBJECT-TYPE 
    SYNTAX  SEQUENCE OF MstpPortInfoEntry
    MAX-ACCESS  not-accessible
    STATUS  current
    DESCRIPTION
        " mstp information list of port"
    ::= { mstpMgt   4}
            
--xxx.100.2.2.4.1
mstpPortInfoEntry OBJECT-TYPE
        SYNTAX  MstpPortInfoEntry
        MAX-ACCESS  not-accessible
        STATUS  current
        DESCRIPTION
            " The index of this table is port index"
        INDEX   { mstpPortInfoPortIndex}
        ::= { mstpPortInfoTable 1 }

MstpPortInfoEntry
        ::= SEQUENCE
            {
                mstpPortInfoPortIndex               		INTEGER,
                mstpPortInfoEnable				INTEGER,
                mstpPortLinkType				INTEGER,
                mstpPortMcheck					INTEGER,
                mstpPortPortFast				INTEGER,
                mstpPortFormat					INTEGER,
                mstpPortDigestSnp				INTEGER,
                mstpPortTCFlush					INTEGER                                
            }
            
--xxx.100.2.2.4.1.1
mstpPortInfoPortIndex  OBJECT-TYPE
            SYNTAX  INTEGER 
            MAX-ACCESS  not-accessible
            STATUS  current
            DESCRIPTION
                " port index"
            ::= { mstpPortInfoEntry 1 }

--xxx.100.2.2.4.1.2         
mstpPortInfoEnable  OBJECT-TYPE
	SYNTAX      INTEGER
			{
				disable(0),
				enable(1)
			}
        MAX-ACCESS  read-create
        STATUS      current
        DESCRIPTION "enable/disable mstp on the port."
        ::= { mstpPortInfoEntry 2 }
                    
--xxx.100.2.2.4.1.2         
mstpPortLinkType  OBJECT-TYPE
	SYNTAX      INTEGER
			{
				auto(2),
				force-true(1),
				force-false(0)
			}
        MAX-ACCESS  read-create
        STATUS      current
        DESCRIPTION " the p2p link type of the port"
        ::= { mstpPortInfoEntry 3 }
--xxx.100.2.2.4.1.3         
mstpPortMcheck  OBJECT-TYPE 
        SYNTAX      INTEGER 
        		{
        			untrigger(0),
        			trigger(1)
        		}
        MAX-ACCESS  read-create
        STATUS      current
        DESCRIPTION "trigger/untrigger"
        ::= { mstpPortInfoEntry 4 }  
--xxx.100.2.2.4.1.4         
mstpPortPortFast  OBJECT-TYPE
        SYNTAX      INTEGER 
        		{
        			default(0),
        			bpdufilter(1),
        			bpduguard(2),
        			noportfast(3)-- no spanningtree portfast		
        		}
        MAX-ACCESS  read-create
        STATUS      current
                DESCRIPTION "
                default:the port mode is portfast mode
                bpdufilter:the port mode is portfast mode with bpdufilter
                bpduguard:the port mode is portfast mode with bpduguard
                noportfast:the port mode is not portfast mode"
        ::= { mstpPortInfoEntry 5 }  
--xxx.100.2.2.4.1.5        
mstpPortFormat  OBJECT-TYPE
        SYNTAX      INTEGER
            	   {
			standard(0),
			privacy(1),
			auto(2)
                    }          
        MAX-ACCESS  read-create
        STATUS      current
        DESCRIPTION "which mode can be setted up port of message format function"
        ::= { mstpPortInfoEntry 6 }            
--xxx.100.2.2.4.1.6         
mstpPortDigestSnp  OBJECT-TYPE 
        SYNTAX      INTEGER 
            	   {
			enable(1),
			disable(0)
                    }           		
        MAX-ACCESS  read-create
        STATUS      current
        DESCRIPTION "Whether the port use peer's authentication key"
        ::= { mstpPortInfoEntry 7 }  
--xxx.100.2.2.4.1.7         
mstpPortTCFlush  OBJECT-TYPE
        SYNTAX      INTEGER 
            	   {
			enable(1),
			disable(2),
			protect(3),
			useglobal(0)
                    }         	
        MAX-ACCESS  read-create
        STATUS      current
        DESCRIPTION "when topology is changed,  how to flush the mac"  
        ::= { mstpPortInfoEntry 8 }                                                       
--********************************************************************************************************
--******************************************************************************************************** 
    
-- (xxx.100.3)   Ports group

--xxx.100.3.1
portCount OBJECT-TYPE
    SYNTAX  INTEGER (1..256)
    MAX-ACCESS  read-only
    STATUS  current
    DESCRIPTION
        " The total number of ports in the system."
    ::= { priPorts  1 }

--xxx.100.3.2
portTable OBJECT-TYPE
    SYNTAX  SEQUENCE OF PriPortEntry
    MAX-ACCESS  not-accessible
    STATUS  current
    DESCRIPTION
        " A list of port entries."
    ::= { priPorts   2 }

--xxx.100.3.2.1
    priPortEntry OBJECT-TYPE
        SYNTAX  PriPortEntry
        MAX-ACCESS  not-accessible
        STATUS  current
        DESCRIPTION
            " A port entry containing port information, 
            status, and control."
        INDEX   { portIndex }
        ::= { portTable 1 }

    PriPortEntry
        ::= SEQUENCE
            {
                portIndex               INTEGER,
                portName                DisplayString,
                switchNum		INTEGER,
                slotNum 		INTEGER,
                portType                INTEGER,
                flowControlStatus	INTEGER,
                bandwidthControlStatus	INTEGER,  
                maxBandwidth		INTEGER,  
                receiveBandwidth	INTEGER,
                transmitBandwidth	INTEGER,   
--                mdi			INTEGER,
                shutdown		INTEGER,
                loopback    		INTEGER,
                speedDuplex		INTEGER,
                portMode		INTEGER,
                pvid			INTEGER,
                indicatesType		INTEGER,
                vctAction           INTEGER,
                vctLastStatus       DisplayString,
                portTrunkAllowedvlan  OCTET STRING,
                portHybridTaggedAllowedvlan  OCTET STRING,                
                portHybridUntaggedAllowedvlan  OCTET STRING                              
            }

--xxx.100.3.2.1.1
        portIndex OBJECT-TYPE
            SYNTAX  INTEGER (1..1024)
            MAX-ACCESS  read-only
            STATUS  current
            DESCRIPTION
                "port No."
            ::= { priPortEntry 1 }
   

--xxx.100.3.2.1.2
        portName  OBJECT-TYPE
            SYNTAX  DisplayString (SIZE(0..32))
            MAX-ACCESS  read-only
            STATUS  current
            DESCRIPTION
                   " Name of the port. exp:financial."
            ::= { priPortEntry 2 }

            
--xxx.100.3.2.1.3
       switchNum  OBJECT-TYPE
          SYNTAX  INTEGER(0..16)
            MAX-ACCESS  read-only
            STATUS  current
            DESCRIPTION
                   " This value is denoting the number of swith in which this port resides.
                   For the non-stackable device,the value is always 1.
                   While for the stackable device, the value is real switch stack number."
            ::= { priPortEntry 3 }


--xxx.100.3.2.1.4
       slotNum  OBJECT-TYPE
          SYNTAX  INTEGER(0..16)
            MAX-ACCESS  read-only
            STATUS  current
            DESCRIPTION
                   " This value is denoting the number of slot.
                   For the static slot,the value is 1,while for 
                   the extended slot the value is real extended slot number."
            ::= { priPortEntry 4 }


--xxx.100.3.2.1.5
            portType  OBJECT-TYPE
                   SYNTAX      INTEGER
                    {
                        typeSFP(0),
                    	typeCombo(1),
                    	typeFiber(2),
                    	typeSingleOptFE(3),   --modify 04/9/9
                    	typeMultiOptFE(4),
                    	typeElecFE(5),
                    	typeSingleOptGE(6),
                    	typeMultiOptGE(7), 
                    	typeElecGE(8),
                    	typePortAGG(9),
                    	typePortUsbGE(10),
                    	typeOptXge(11),
                        other(255)--modify 03/1/21
                    }
        MAX-ACCESS  read-only
        STATUS      current
        DESCRIPTION "Type of expansion module in this port."
        ::= { priPortEntry 5 }
        
--------------------------------------------------------------------------
-- New requirement begins
--------------------------------------------------------------------------
--xxx.100.3.2.1.6
            flowControlStatus  OBJECT-TYPE
                SYNTAX      INTEGER
                    {
                        disable(0),
                    	enable(1)
                    }
	        MAX-ACCESS  read-write
	        STATUS      current
	        DESCRIPTION 
	        	"The flow-control status of the port. 
	        	Its functionality is exactly same as 'flow control' or 'no flow control' commands
	        	in console mode."
	        ::= { priPortEntry 6 }

--xxx.100.3.2.1.7
            bandwidthControlStatus  OBJECT-TYPE
                SYNTAX      INTEGER
                    {
                         ingress(0),
                    	 egress(1),
                    	 both(2),
                    	 none(3)
                    }
	        MAX-ACCESS  read-only
	        STATUS      current
	        DESCRIPTION 
	        	"The bandwidth-control status of the port. 
	        	Its functionality is to stop the bandwidth control.
	        	The only way to enable bandwidth control is to set receiveBandwidth or transmitBandwith."
	        ::= { priPortEntry 7 }
        
--xxx.100.3.2.1.8
            maxBandwidth  OBJECT-TYPE
                SYNTAX      INTEGER
                	    {
													default(0),
													bw100M(1),
													bw1000M(2),
													bw10000M(3) 
                	    }
	        MAX-ACCESS  read-only
 	        STATUS      current
	        DESCRIPTION 
	        	"The max bandwidth of the port."
	        ::= { priPortEntry 8 }

--xxx.100.3.2.1.9
            receiveBandwidth  OBJECT-TYPE
                SYNTAX      INTEGER
	        MAX-ACCESS  read-write
 	        STATUS      current
	        DESCRIPTION 
	        	"The recevice bandwidth of the port. Its unit is kbs.
	        	The command 'bandwidth control 50 both' in console mode equals
	        	setting both receiveBandwidth and transmitBandwidth to 50 kbs.
	        	Set 0 is no bandwidth."
	        ::= { priPortEntry 9 }

--xxx.100.3.2.1.10
            transmitBandwidth  OBJECT-TYPE
                SYNTAX      INTEGER
	        MAX-ACCESS  read-write
 	        STATUS      current
	        DESCRIPTION 
	        	"The transmit bandwidth of the port. Its unit is kbs.
	        	Set 0 is no bandwidth."
	        ::= { priPortEntry 10 }
	        
--xxx.100.3.2.1.11
--            mdi  OBJECT-TYPE
--                SYNTAX      INTEGER
--                {
--                        auto(0),
--                    	across(1),
--                    	normal(2)
--                }
--	        MAX-ACCESS  read-write
-- 	        STATUS      current
--	        DESCRIPTION 
--	        	"Establish to specify the on-line type of the port;
--	        	 Exchange the every kind of plank card of machine
--			 of thousand trillion this order of above port nonsupport."
--	        ::= { priPortEntry 11 }

--xxx.100.3.2.1.12
            shutdown  OBJECT-TYPE
                SYNTAX      INTEGER
                {
                        shutDown(0),
                    	noshutdown(1)
                }               
	        MAX-ACCESS  read-write
 	        STATUS      current
	        DESCRIPTION 
	        	"Close or open to specify the port."
	        ::= { priPortEntry 12 }
	        
--xxx.100.3.2.1.13
            loopback  OBJECT-TYPE
                SYNTAX      INTEGER
                {
                        noloopback(0),
                    	loopback(1)
                }                 
	        MAX-ACCESS  read-write
 	        STATUS      current
	        DESCRIPTION 
	        	"Open or close to specify the wreath of 
	        	the port back to test the function."
	        ::= { priPortEntry 13 }	
	        
--xxx.100.3.2.1.14
            speedDuplex  OBJECT-TYPE
                SYNTAX      INTEGER
                {
                        auto(0),
                    	half10(1),
                    	full10(2),
                    	half100(3),
                    	full100(4),
                    	half1000(5),
                    	full1000(6),
                    	fx-100(13)
                    	
                }                                   
	        MAX-ACCESS  read-write
 	        STATUS      current
	        DESCRIPTION 
	        	"The speed and duplex status of the port."
	        ::= { priPortEntry 14 }	
	        
--xxx.100.3.2.1.15
            portMode  OBJECT-TYPE
                SYNTAX      INTEGER
                {
                        access(1),
                    	trunk(2),
                    	hybrid(3)                   	
                }                                   
	        MAX-ACCESS  read-write
 	        STATUS      current
	        DESCRIPTION 
	        	"port mode: 1 is access,2 is trunk,3 is hybrid"
	        ::= { priPortEntry 15 }	
	        
--xxx.100.3.2.1.16
            pvid  OBJECT-TYPE
                SYNTAX      INTEGER                                   
	        MAX-ACCESS  read-write
 	        STATUS      current
	        DESCRIPTION 
	        	"port of native vlan No."
	        ::= { priPortEntry 16 }	
	        
--xxx.100.3.2.1.17
	indicatesType OBJECT-TYPE 
        SYNTAX      INTEGER
                    {
                        other(1),
                        hundredBaseTX(2),
                        hundredBaseFX(3),
                        thousandBaseSX(4),
                        thousandBaseLX(5),
                        thousandBaseT(6),
                        thousandBaseGBIC(7),
                        thousandBaseSfp(8),
                        hundredBaseFxScSingleMode(9),
                        hundredBaseFxScMultiMode(10),
                        thousandBaseCX(11),
                        tenG(12)
                    }
        MAX-ACCESS  read-only
        STATUS      current
        DESCRIPTION "Indicates the port type of the configuration of the switch."
	        ::= { priPortEntry 17 }	
--xxx.100.3.2.1.18
	vctAction OBJECT-TYPE 
        SYNTAX      INTEGER
        MAX-ACCESS  read-write
        STATUS      current
        DESCRIPTION "This object indicates the VCT action of the port,only the value 1 is permitted 
                    when SET this entry though you can GET 1(processing) and 0(succeed);
                    The specified port will be shutdown when one sets 1 to this entry,and then it will return 
                    to no shutdown after operate the virtual-cable-test. You can get the status of VCT from
                    the entry vctLastStatus."
	        ::= { priPortEntry 18 }	  
--xxx.100.3.2.1.19
	vctLastStatus OBJECT-TYPE 
        SYNTAX      DisplayString (SIZE(0..1000))
        MAX-ACCESS  read-only
        STATUS      current
        DESCRIPTION "Indicates the last VCT status of the port."
	        ::= { priPortEntry 19 }	
	        
--xxx.100.3.2.1.20
            portTrunkAllowedvlan  OBJECT-TYPE
            SYNTAX      OCTET STRING (SIZE (1..100))                                 
	          MAX-ACCESS  read-write
 	          STATUS      current
	          DESCRIPTION 
	        	"trunk port allowed vlan list string"
	          ::= { priPortEntry 20 }	
	        	               
--xxx.100.3.2.1.21
            portHybridTaggedAllowedvlan  OBJECT-TYPE
            SYNTAX      OCTET STRING (SIZE (1..100))                                 
	          MAX-ACCESS  read-write
 	          STATUS      current
	          DESCRIPTION 
	        	"hybrid port tagged allowed vlan list string"
	          ::= { priPortEntry 21 }	
	          
--xxx.100.3.2.1.22
            portHybridUntaggedAllowedvlan  OBJECT-TYPE
            SYNTAX      OCTET STRING (SIZE (1..100))                                 
	          MAX-ACCESS  read-write
 	          STATUS      current
	          DESCRIPTION 
	        	"hybrid port untagged allowed vlan list string"
	          ::= { priPortEntry 22 }
	        
 	
	                    
--********************************************************************************************************
--******************************************************************************************************** 

--xxx.100.4  priIpConfig

--***************************************

--xxx.100.4.1
            netDefaultGateway  OBJECT-TYPE
                SYNTAX      IpAddress            
	        MAX-ACCESS  read-write
 	        STATUS      current
	        DESCRIPTION 
	        	"The IP Address of the default gateway.  If this value is
        		undefined or unknown, it shall have the value 0.0.0.0."
	        ::= { priIpConfig 1 }

--xxx.100.4.2
            ipHttpState  OBJECT-TYPE
                SYNTAX      INTEGER
                {
                        disable(0),
                    	enable(1)
                }                         
	        MAX-ACCESS  read-write
 	        STATUS      current
	        DESCRIPTION 
	        	"Web server on-off."
	        ::= { priIpConfig 2 }
	        
--xxx.100.4.3
iPAddrTable OBJECT-TYPE
        SYNTAX      SEQUENCE OF IPAddrEntry
        MAX-ACCESS  not-accessible
        STATUS      current
        DESCRIPTION "A table of iPAddrEntry."
        ::= { priIpConfig 3 }

--xxx.100.4.3.1
iPAddrEntry OBJECT-TYPE
        SYNTAX      IPAddrEntry
        MAX-ACCESS  not-accessible
        STATUS      current
        DESCRIPTION "A set of configuration parameters for a particular
        network interface on this device. If the device has no network
        interface, this table is empty.

        The index is composed of the ifIndex assigned to the
        corresponding interface."
        INDEX   { iPAddrVid , iPAddrIPAddress }
        ::= { iPAddrTable 1 }

IPAddrEntry ::= SEQUENCE
{
    iPAddrVid               	INTEGER,
    iPAddrIPAddress             IpAddress,
    iPAddrSubnetMask     	IpAddress,
    iPAddrPrimaryInterface      INTEGER,
    iPAddrStatus		INTEGER
}
--xxx.100.4.3.1.1
iPAddrVid  OBJECT-TYPE
    SYNTAX     INTEGER
    MAX-ACCESS not-accessible
    STATUS     current
    DESCRIPTION "The VLAN interface being used by this table entry. Only the 
                 VLAN interfaces which have an IP configured will appear in
                 the table."
    ::= { iPAddrEntry 1 }
    
--xxx.100.4.3.1.2   
iPAddrIPAddress  OBJECT-TYPE
    SYNTAX     IpAddress
    MAX-ACCESS not-accessible
    STATUS     current
    DESCRIPTION
        "The IP address of this Net interface.  The default value
        for this object is 0.0.0.0.  If either the IPAddrIPAddress
        or IPAddrSubnetMask is 0.0.0.0, then when the device
        boots, it may use BOOTP to try to figure out what these
        values should be. If BOOTP fails, before the device
        can talk on the network, this value must be configured
        (e.g., through a terminal attached to the device)."
    ::= { iPAddrEntry 2 }

--xxx.100.4.3.1.3
iPAddrSubnetMask  OBJECT-TYPE
    SYNTAX     IpAddress
    MAX-ACCESS read-create
    STATUS     current
    DESCRIPTION
        "The subnet mask of this Net interface.  The default value
        for this object is 0.0.0.0.  If either the IPAddrIPAddress
        or IPAddrSubnetMask are 0.0.0.0, then when the device
        boots, it may use BOOTP to try to figure out what these
        values should be. If BOOTP fails, before the device
        can talk on the network, this value must be configured
        (e.g., through a terminal attached to the device)."
    ::= { iPAddrEntry 3 }

--xxx.100.4.3.1.4
iPAddrPrimaryInterface OBJECT-TYPE
    SYNTAX     INTEGER
               {
                   primary(0),
                   secondary(1)
               }
    MAX-ACCESS read-create
    STATUS     current
    DESCRIPTION
        "Whether this is a primary interface."
    ::= { iPAddrEntry 4 }
 
--xxx.100.4.3.1.5
iPAddrStatus OBJECT-TYPE
    SYNTAX     INTEGER
               {
            	   createAndGo(0),
               	   active(1),
               	   destroy(2)
               }
    MAX-ACCESS read-create
    STATUS     current
    DESCRIPTION
        "Now state."
    ::= { iPAddrEntry 5 }        

--********************************************************************************************************

--xxx.100.4.4
interfaceTable OBJECT-TYPE
        SYNTAX      SEQUENCE OF InterfaceEntry
        MAX-ACCESS  not-accessible
        STATUS      current
        DESCRIPTION "A table of interfaceEntry."
        ::= { priIpConfig 4 }

--xxx.100.5.1.1
interfaceEntry OBJECT-TYPE
        SYNTAX      InterfaceEntry
        MAX-ACCESS  not-accessible
        STATUS      current
        DESCRIPTION "A set of configuration parameters for a particular
        network interface on this device. If the device has no network
        interface, this table is empty.

        The index is composed of the ifIndex assigned to the
        corresponding interface."
        INDEX   { intfacetype , intfaceID }
        ::= { interfaceTable 1 }

InterfaceEntry ::= SEQUENCE
{
    intfacetype               	INTEGER,
    intfaceID    		INTEGER,
    intfaceIndex     		INTEGER,
--  intfaceAddressMethod      	INTEGER,
    intfaceStatus		INTEGER
}

intfacetype  OBJECT-TYPE
    SYNTAX     INTEGER
               {
                    vintf(1),
                    loopback(2),
                    tunnel(3)
               }
    MAX-ACCESS not-accessible
    STATUS     current
    DESCRIPTION "The Type of interface.
                 Now support(1)vintf and (2)loopback."
    ::= { interfaceEntry 1 }
    
intfaceID  OBJECT-TYPE
    SYNTAX     INTEGER
    MAX-ACCESS not-accessible
    STATUS     current
    DESCRIPTION
        "The Number of interface.
        exp:intfacetype(1),interfaceID(2) means interface vlan 2.
            if intfacetype(2) interfaceID(4) means interface loopback4.
            if intfacetype(3) interfaceID(5) means interface Tunnel5."
    ::= { interfaceEntry 2 }

intfaceIndex  OBJECT-TYPE
    SYNTAX     INTEGER
    MAX-ACCESS read-only
    STATUS     current
    DESCRIPTION
        "The Index of interface."
    ::= { interfaceEntry 3 }

--intfaceAddressMethod OBJECT-TYPE
--    SYNTAX     INTEGER
--               {
--                    user(0),
--                    dhcp(1),
--                    bootp(2)
--               }
--    MAX-ACCESS read-create
--    STATUS     current
--    DESCRIPTION
--        "Method to get the IP address. 
--        When intfacetype(2/3) intfaceAddressMethod must be user()."
--    ::= { interfaceEntry 4 }

intfaceStatus OBJECT-TYPE
    SYNTAX     INTEGER
               {
            	   createAndGo(0),
               	   active(1),
               	   destroy(2)
               }
    MAX-ACCESS read-create
    STATUS     current
    DESCRIPTION
        "Now state."
    ::= { interfaceEntry 5 }  


	        	                                    
--********************************************************************************************************
--******************************************************************************************************** 

--xxx.100.5  vlanConfig

--***************************************
--vlaninfotable
--***************************************

--xxx.100.5.1
vlanInfoTable OBJECT-TYPE
        SYNTAX      SEQUENCE OF VlanInfoEntry
        MAX-ACCESS  not-accessible
        STATUS      current
        DESCRIPTION "A table containing current configuration information
        for each VLAN currently configured into the device by
        (local or network) management."
        ::= { priVlanConfig 1 }

--xxx.100.5.1.1
vlanInfoEntry OBJECT-TYPE
        SYNTAX      VlanInfoEntry
        MAX-ACCESS  not-accessible
        STATUS      current
        DESCRIPTION "Static information for a VLAN configured into the
        device by (local or network) management."
        INDEX   { vlanID }
        ::= { vlanInfoTable 1 }

VlanInfoEntry ::= SEQUENCE
{
    vlanID             INTEGER,
    vlanName           DisplayString,
    vlanPortNumber     INTEGER,
    vlanRowStatus      INTEGER
}

        
--xxx.100.5.1.1.1
vlanID OBJECT-TYPE
        SYNTAX      INTEGER (1..4094)
        MAX-ACCESS  not-accessible
        STATUS      current
        DESCRIPTION "This value is vlan's ID."
        ::= { vlanInfoEntry 1 }

--xxx.100.5.1.1.2
vlanName OBJECT-TYPE
        SYNTAX      DisplayString (SIZE (1..64))
        MAX-ACCESS  read-create
        STATUS      current
        DESCRIPTION "which may be used to identify the VLAN."
        ::= { vlanInfoEntry 2 }

--xxx.100.5.1.1.3
vlanPortNumber OBJECT-TYPE
        SYNTAX      INTEGER (0..65535)
        MAX-ACCESS  read-only
        STATUS      current
        DESCRIPTION "The sum of vlan's ports."
        ::= { vlanInfoEntry 3 }

--xxx.100.5.1.1.4
vlanRowStatus OBJECT-TYPE
    SYNTAX      INTEGER
    		{
               	   active(1),
               	   destroy(2)    		
    		}
    MAX-ACCESS  read-create
    STATUS      current
    DESCRIPTION
        "This object indicates the status of this entry."
    ::= { vlanInfoEntry 4 }        
    
--********************************************************************************************************
--********************************************************************************************************
          
--xxx.100.6 jumblyStacking

--xxx.100.6.1
sysStackUnitNumber OBJECT-TYPE
    SYNTAX  INTEGER
    MAX-ACCESS  read-only
    STATUS  current
    DESCRIPTION
        " the number of the stacked units."
    ::= { priJumblyStacking  1 } 
               
--xxx.100.6.2
jumblyStackingInfoTable OBJECT-TYPE
        SYNTAX      SEQUENCE OF JumblyStackingInfoEntry
        MAX-ACCESS  not-accessible
        STATUS      current
        DESCRIPTION "Table of descriptive and status information about
                     jumbly stacking in this system."
        ::= { priJumblyStacking 2 }
          
--xxx.100.6.1.1
jumblyStackingInfoEntry OBJECT-TYPE
        SYNTAX      JumblyStackingInfoEntry
        MAX-ACCESS  not-accessible
        STATUS      current
        DESCRIPTION "An entry in the table, containing information
                     about stacking switch in this system."
        INDEX       { swUnitIndex }
        ::= { jumblyStackingInfoTable 1 }

JumblyStackingInfoEntry ::= SEQUENCE
{
    stackingUnitIndex        INTEGER,
    swHardwareVersion       DisplayString,
    swSoftwareVersion       DisplayString,
    swCPUMac                MacAddress,
    swType                  DisplayString
}

--xxx.100.6.1.1.1
stackingUnitIndex OBJECT-TYPE
        SYNTAX      INTEGER
        MAX-ACCESS  read-only
        STATUS      current
        DESCRIPTION "This object identifies the switch within the system
                     for which this entry contains information. This
                     value can never be greater than switchNumber."
        ::= { jumblyStackingInfoEntry 1 }

--xxx.100.6.1.1.2
swHardwareVersion OBJECT-TYPE
    SYNTAX  DisplayString (SIZE(1..32))
    MAX-ACCESS  read-only
    STATUS  current
    DESCRIPTION
        " The text string denoting the version of the hardware."
    ::= { jumblyStackingInfoEntry  2 }

--xxx.100.6.1.1.3
swSoftwareVersion OBJECT-TYPE
    SYNTAX  DisplayString (SIZE(1..32))
    MAX-ACCESS  read-only
    STATUS  current
    DESCRIPTION
        " The text string denoting the version of the software."
    ::= { jumblyStackingInfoEntry  3 }

--xxx.100.6.1.1.4
swCPUMac OBJECT-TYPE
    SYNTAX  MacAddress (SIZE(17))
    MAX-ACCESS  read-only
    STATUS  current
    DESCRIPTION
        " the Mac address of the machine."
    ::= { jumblyStackingInfoEntry  4 } 
    
--xxx.100.6.1.1.5
swType OBJECT-TYPE
    SYNTAX  DisplayString (SIZE(1..32))
    MAX-ACCESS  read-only
    STATUS  current
    DESCRIPTION "Type of this switch."
    ::= { jumblyStackingInfoEntry 5 }

--********************************************************************************************************
--******************************************************************************************************** 
    
--xxx.100.7 uamSecurityPortMib

--xxx.100.7.1
portSecurityTable OBJECT-TYPE
        SYNTAX      SEQUENCE OF PortSecurityEntry
        MAX-ACCESS  not-accessible
        STATUS      current
        DESCRIPTION "The table of port security "
        ::= { priUamSecurityPortMib 1 }

--xxx.100.7.1.1
portSecurityEntry OBJECT-TYPE
        SYNTAX      PortSecurityEntry
        MAX-ACCESS  not-accessible
        STATUS      current
        DESCRIPTION "An entry in the port security table."
        INDEX       { psPortIndex }
        ::= { portSecurityTable 1 }

PortSecurityEntry ::= SEQUENCE
{
    psPortIndex                 INTEGER,
    psPortSecurity              INTEGER,
    psSecuritytSaticMacAdd      MacAddress,
    psSecurityStaticMacDel      MacAddress,
    psSecurityPortLock          INTEGER,
    psSecurityPortMax           INTEGER,
    psSecurityPortConvertmac    INTEGER,
    psSecurityPortLocktimer     INTEGER
}

--xxx.100.7.1.1.1
psPortIndex OBJECT-TYPE
        SYNTAX      INTEGER
        MAX-ACCESS  not-accessible
        STATUS      current
        DESCRIPTION "A unique value for each port"
        ::= { portSecurityEntry 1 }
        
--xxx.100.7.1.1.2
psPortSecurity OBJECT-TYPE
        SYNTAX      INTEGER {
                            disable(0),
                            enable(1)
                           }
        MAX-ACCESS  read-write
        STATUS      current
        DESCRIPTION "enable or disable mac bind on this port"
        ::= { portSecurityEntry 2 } 
        
--xxx.100.7.1.1.3
psSecuritytSaticMacAdd OBJECT-TYPE
        SYNTAX      MacAddress (SIZE(17))
        MAX-ACCESS  read-write
        STATUS      current
        DESCRIPTION "bind Security mac address on this port"
        ::= { portSecurityEntry 3 } 
        
--xxx.100.7.1.1.4
psSecurityStaticMacDel OBJECT-TYPE
        SYNTAX      MacAddress (SIZE(17))
        MAX-ACCESS  read-write
        STATUS      current
        DESCRIPTION "delete Security mac address on this port"
        ::= { portSecurityEntry 4 }  
                  
--xxx.100.7.1.1.5
psSecurityPortLock OBJECT-TYPE
        SYNTAX      INTEGER{
                            unlock(0),
                            lock(1)
                           }
        MAX-ACCESS  read-write
        STATUS      current
        DESCRIPTION "lock or unlock this port"
        ::= { portSecurityEntry 5 }
        
--xxx.100.7.1.1.6
psSecurityPortMax OBJECT-TYPE
        SYNTAX      INTEGER (1..128)
        MAX-ACCESS  read-write
        STATUS      current
        DESCRIPTION "Maximum secure addrs on this port"
        ::= { portSecurityEntry 6 }
 
--xxx.100.7.1.1.7
psSecurityPortConvertmac OBJECT-TYPE
        SYNTAX      INTEGER (1..1)
        MAX-ACCESS  read-write
        STATUS      current
        DESCRIPTION "convert dynamic mac to security mac"
        ::= { portSecurityEntry 7 }                                      

--xxx.100.7.1.1.8
psSecurityPortLocktimer OBJECT-TYPE
        SYNTAX      INTEGER (0..300)
        MAX-ACCESS  read-write
        STATUS      current
        DESCRIPTION "lock timer on this port"
        ::= { portSecurityEntry 8 }
        
--xxx.100.7.2
securityMacPortTable OBJECT-TYPE
        SYNTAX      SEQUENCE OF SecurityMacPortEntry
        MAX-ACCESS  not-accessible
        STATUS      current
        DESCRIPTION "Table of descriptive and status information about security port"
        ::= { priUamSecurityPortMib 2 }
        
--xxx.100.7.2.1
securityMacPortEntry OBJECT-TYPE
        SYNTAX      SecurityMacPortEntry
        MAX-ACCESS  not-accessible
        STATUS      current
        DESCRIPTION "An entry in the security mac port table."
        INDEX       { secPortIndex , secMacAdress }
        ::= { securityMacPortTable 1 }

SecurityMacPortEntry ::= SEQUENCE
{
    secPortIndex                 INTEGER,
    secMacAdress                 MacAddress,
    secVid                       INTEGER
}

--xxx.100.7.2.1.1
secPortIndex OBJECT-TYPE
        SYNTAX      INTEGER
        MAX-ACCESS  read-only
        STATUS      current
        DESCRIPTION "A unique value for each port"
        ::= { securityMacPortEntry 1 }   

--xxx.100.7.2.1.2
secMacAdress OBJECT-TYPE
        SYNTAX      MacAddress (SIZE(17))
        MAX-ACCESS  read-only
        STATUS      current
        DESCRIPTION "Mac adress bind on this port"
        ::= { securityMacPortEntry 2 }  
        
--xxx.100.7.2.1.3
secVid OBJECT-TYPE
        SYNTAX      INTEGER
        MAX-ACCESS  read-only
        STATUS      current
        DESCRIPTION "vlan id of this port(pvid)"
        ::= { securityMacPortEntry 3 } 
        
--********************************************************************************************************
--******************************************************************************************************** 
         
-- (xxx.100.8)   priIgmpSnoopingMib
    
--xxx.100.8.1
priIgmpSnoopingGlobalEnable OBJECT-TYPE
    SYNTAX  INTEGER
    {
         disable(0),
         enable(1)
    }   
    MAX-ACCESS  read-write
    STATUS  current
    DESCRIPTION
        " Enable or disable the IgmpSnooping algorithm in the switch."
    ::= { priIgmpSnoopingMib  1 }

--xxx.100.8.2
priIgmpSnoopingVlanTable OBJECT-TYPE
    SYNTAX  SEQUENCE OF PriIgmpSnoopingEntry
    MAX-ACCESS  not-accessible
    STATUS  current
    DESCRIPTION
        " IopgmpSnoing configuration in vlan."
    ::= { priIgmpSnoopingMib   2 }

--xxx.100.8.2.1
    priIgmpSnoopingEntry OBJECT-TYPE
        SYNTAX  PriIgmpSnoopingEntry
        MAX-ACCESS  not-accessible
        STATUS  current
        DESCRIPTION
            " IgmpSnooping confition in vlan."
        INDEX   { priIgmpSnoopingvlanID }
        ::= { priIgmpSnoopingVlanTable 1 }

    PriIgmpSnoopingEntry
        ::= SEQUENCE
            {
    		priIgmpSnoopingvlanID                  INTEGER,            
                priIgmpSnoopingvlanEnable              INTEGER,
                priIgmpSnoopingleave                   INTEGER,
                priIgmpSnoopingL2gen                   INTEGER,
                priIgmpSnoopingGroupNum                INTEGER,
                priIgmpSnoopingSourceNum               INTEGER,  
                priIgmpSnoopingPort		       DisplayString,
                priIgmpSnoopingPortTime		       INTEGER,
                priIgmpSnoopingQueryInterval	       INTEGER,
                priIgmpSnoopingQueryMrsp	       INTEGER,
                priIgmpSnoopingQueryRobustness         INTEGER,
                priIgmpSnoopingSuppression             INTEGER                                              
            }
            
--xxx.100.8.2.1.1
priIgmpSnoopingvlanID OBJECT-TYPE
        SYNTAX      INTEGER
        MAX-ACCESS  not-accessible
        STATUS      current
        DESCRIPTION "This value is vlan's ID."
        ::= { priIgmpSnoopingEntry 1 }
                    
--xxx.100.8.2.1.2
        priIgmpSnoopingvlanEnable OBJECT-TYPE
            SYNTAX      INTEGER
    	    {
         	disable(0),
         	enable(1)
    	    }             
            MAX-ACCESS  read-write
            STATUS      current
            DESCRIPTION " Enable or disable the IgmpSnooping in the switch.Default:0"
            ::= { priIgmpSnoopingEntry 2 } 
            
--xxx.100.8.2.1.3
        priIgmpSnoopingleave OBJECT-TYPE
            SYNTAX      INTEGER
    	    {
         	no-immediate-leave(0),
         	immediate-leave(1)
    	    }             
            MAX-ACCESS  read-write
            STATUS      current
            DESCRIPTION " Enable or disable the immediate leave config.Default:0"
            ::= { priIgmpSnoopingEntry 3 } 
            
--xxx.100.8.2.1.4
        priIgmpSnoopingL2gen OBJECT-TYPE
            SYNTAX      INTEGER
    	    {
         	no-l2-general-querier(0),
         	l2-general-querier(1)
    	    }             
            MAX-ACCESS  read-write
            STATUS      current
            DESCRIPTION " Enable or disable the l2-general-querier config.Default:0"
            ::= { priIgmpSnoopingEntry 4 } 
            
--xxx.100.8.2.1.5
        priIgmpSnoopingGroupNum OBJECT-TYPE
            SYNTAX      INTEGER (1..65535)            
            MAX-ACCESS  read-write
            STATUS      current
            DESCRIPTION "set the maximum IGMP group the port can join"
            ::= { priIgmpSnoopingEntry 5 } 
            
--xxx.100.8.2.1.6
        priIgmpSnoopingSourceNum OBJECT-TYPE
            SYNTAX      INTEGER (1..65535)         
            MAX-ACCESS  read-write
            STATUS      current
            DESCRIPTION "set the maximum source number"
            ::= { priIgmpSnoopingEntry 6 } 

--xxx.100.8.2.1.7
        priIgmpSnoopingPort OBJECT-TYPE
            SYNTAX      DisplayString         
            MAX-ACCESS  read-only
            STATUS      current
            DESCRIPTION " Get static mrouter port of vlan.
      		ethernet:  Name of Ethernet port
      		ifname:  Name of interface
      		port-channel: Port aggregation."
            ::= { priIgmpSnoopingEntry 7 } 

--xxx.100.8.2.1.8
        priIgmpSnoopingPortTime OBJECT-TYPE
            SYNTAX      INTEGER (1..65535)       
            MAX-ACCESS  read-write
            STATUS      current
            DESCRIPTION " Configure this survive time of mrouter port.Default: 255s"
            ::= { priIgmpSnoopingEntry 8 } 

--xxx.100.8.2.1.9
        priIgmpSnoopingQueryInterval OBJECT-TYPE
            SYNTAX      INTEGER(1..65535)      
            MAX-ACCESS  read-write
            STATUS      current
            DESCRIPTION " Configure this query interval. Default: 125s"
            ::= { priIgmpSnoopingEntry 9 } 
            
--xxx.100.8.2.1.10
        priIgmpSnoopingQueryMrsp OBJECT-TYPE
            SYNTAX      INTEGER(1..25)     
            MAX-ACCESS  read-write
            STATUS      current
            DESCRIPTION " Configure the maximum query response period. Default: 10s"
            ::= { priIgmpSnoopingEntry 10 } 
            
--xxx.100.8.2.1.11
        priIgmpSnoopingQueryRobustness OBJECT-TYPE
            SYNTAX      INTEGER(2..10)        
            MAX-ACCESS  read-write
            STATUS      current
            DESCRIPTION " Configure the query robustness.Default: 2"
            ::= { priIgmpSnoopingEntry 11 }             

--xxx.100.8.2.1.12
        priIgmpSnoopingSuppression OBJECT-TYPE
            SYNTAX      INTEGER(1..65535)        
            MAX-ACCESS  read-write
            STATUS      current
            DESCRIPTION " Configure the suppression query time.Default: 255s"
            ::= { priIgmpSnoopingEntry 12 } 
                                                                                                   
--********************************************************************************************************
--******************************************************************************************************** 
        
-- (xxx.100.9)   QinQ group

--xxx.100.9.1
dot1qTunnelTable OBJECT-TYPE
    SYNTAX  SEQUENCE OF Dot1qTunnelEntry
    MAX-ACCESS  not-accessible
    STATUS  current
    DESCRIPTION
    	" port of qinq tunnel function list"
    ::= { priQinQmib  1}   

--xxx.100.9.1
dot1qTunnelEntry OBJECT-TYPE
        SYNTAX  Dot1qTunnelEntry
        MAX-ACCESS  not-accessible
        STATUS  current
        DESCRIPTION
            " configure of dot1qTunnel"
        INDEX   { qinqPortIndex }
        ::= { dot1qTunnelTable 1 }
        
Dot1qTunnelEntry
        ::= SEQUENCE
            {
            	qinqPortIndex			INTEGER,
            	tunnelPortEnable		INTEGER,
                tunnelPortType			INTEGER
            }

--xxx.100.9.1.1
qinqPortIndex OBJECT-TYPE
    SYNTAX  INTEGER
            MAX-ACCESS  not-accessible
            STATUS  current
            DESCRIPTION
                "port index"
            ::= { dot1qTunnelEntry 1 } 
            
--xxx.100.9.1.2
tunnelPortEnable OBJECT-TYPE
    SYNTAX  INTEGER {
                disable(0),
                enable(1)
            }
            MAX-ACCESS  read-write
            STATUS  current
            DESCRIPTION
                "Enable or disable the dot1q-tunnel in this port."
            ::= { dot1qTunnelEntry 2 }  
            
--xxx.100.9.1.3
tunnelPortType OBJECT-TYPE
    SYNTAX  INTEGER 
            MAX-ACCESS  read-write
            STATUS  current
            DESCRIPTION
                "Protocol type of trunk port(TPID)(exp:8100/9100/9200)."
            ::= { dot1qTunnelEntry 3 }   


            
--xxx.100.9.2
vlanTranslationTable OBJECT-TYPE
    SYNTAX  SEQUENCE OF VlanTranslationEntry
    MAX-ACCESS  not-accessible
    STATUS  current
    DESCRIPTION
    	" VLAN translation basic config."
    ::= { priQinQmib  2}   

--xxx.100.9.2.1
vlanTranslationEntry OBJECT-TYPE
        SYNTAX  VlanTranslationEntry
        MAX-ACCESS  not-accessible
        STATUS  current
        DESCRIPTION
            "VLAN translation"
        INDEX   { translatPortIndex }
        ::= { vlanTranslationTable 1 }
        
VlanTranslationEntry
        ::= SEQUENCE
            {
            	translatPortIndex	      INTEGER,
    		translationEnable             INTEGER,
    		translationDropType           INTEGER		
            }
 
--xxx.100.9.2.1.1
translatPortIndex OBJECT-TYPE
    SYNTAX  INTEGER 
            MAX-ACCESS  not-accessible
            STATUS  current
            DESCRIPTION
                "Index of Port."
            ::= { vlanTranslationEntry 1 }
            
--xxx.100.9.2.1.2
translationEnable OBJECT-TYPE
    SYNTAX  INTEGER {
                disable(0),
                enable(1)
            }
            MAX-ACCESS  read-write
            STATUS  current
            DESCRIPTION
                "if the port can be done translation function"
            ::= { vlanTranslationEntry 2 }  
            
--xxx.100.9.2.1.3
translationDropType OBJECT-TYPE
    SYNTAX  INTEGER {
		in(1),
		out(2),
		both(3),
		noIn(4),
		noOut(5),
		noBoth(6)
            }
            MAX-ACCESS  read-write
            STATUS  current
            DESCRIPTION
                "when VLAN-translation missed, drop packet mode"
            ::= { vlanTranslationEntry 3 } 


--xxx.100.9.3
vlanTranslationTypeTable OBJECT-TYPE
    SYNTAX  SEQUENCE OF VlanTranslationTypeEntry
    MAX-ACCESS  not-accessible
    STATUS  current
    DESCRIPTION
    	" port VLAN-translation of translation relation list"
    ::= { priQinQmib  3}   

--xxx.100.9.3.1
vlanTranslationTypeEntry OBJECT-TYPE
        SYNTAX  VlanTranslationTypeEntry
        MAX-ACCESS  not-accessible
        STATUS  current
        DESCRIPTION
            " port VLAN translation of translation relation,index is port index and translation sort"
        INDEX   { translatPortTypeIndex , translationType ,translationOldVlanid ,translationNewVlanid}
        ::= { vlanTranslationTypeTable 1 }
        
VlanTranslationTypeEntry
        ::= SEQUENCE
            {
            	translatPortTypeIndex	      INTEGER,
    		translationType               INTEGER, 
    		translationOldVlanid   	      INTEGER,
    		translationNewVlanid   	      INTEGER,
    		translationTypeStatus	      INTEGER			
            }
 
--xxx.100.9.3.1.1
translatPortTypeIndex OBJECT-TYPE
    SYNTAX  INTEGER 
            MAX-ACCESS  read-only
            STATUS  current
            DESCRIPTION
                "port index"
            ::= { vlanTranslationTypeEntry 1 }

        
--xxx.100.9.3.1.2
translationType OBJECT-TYPE
    SYNTAX  INTEGER{
		in(1),
		out(2)    
    		}
            MAX-ACCESS  read-only
            STATUS  current
            DESCRIPTION
                "translation type. in:input translation; out:output translation."
            ::= { vlanTranslationTypeEntry 2 } 

--xxx.100.9.3.1.3
translationOldVlanid OBJECT-TYPE
    SYNTAX  INTEGER (1..4094)
            MAX-ACCESS  read-only
            STATUS  current
            DESCRIPTION
                "vlantranslation pre-vid"
            ::= { vlanTranslationTypeEntry 3 } 
            
--xxx.100.9.3.1.4
translationNewVlanid OBJECT-TYPE
    SYNTAX  INTEGER (1..4094)
            MAX-ACCESS  read-only
            STATUS  current
            DESCRIPTION
                "the new vid"
            ::= { vlanTranslationTypeEntry 4 } 

--xxx.100.9.3.1.5
        translationTypeStatus OBJECT-TYPE
            SYNTAX  INTEGER
            	    {            	    	
               		active(1),
               		destroy(2)
            	    }
            MAX-ACCESS  read-create
            STATUS  current
            DESCRIPTION
                " accession/delete VLAN-translation relation"
            ::= { vlanTranslationTypeEntry  5 }    

                                       
--********************************************************************************************************
--********************************************************************************************************              

-- (xxx.100.10)   prisecurity group

--xxx.100.10.1
    acl         	    OBJECT IDENTIFIER ::= { prisecurity 1 } 
--xxx.100.10.1.1
    fireWall         	    OBJECT IDENTIFIER ::= { acl 1 } 
--xxx.100.10.1.2
    timeRange         	    OBJECT IDENTIFIER ::= { acl 2 }     
--xxx.100.10.1.3
    numAcl         	    OBJECT IDENTIFIER ::= { acl 3 }    
--xxx.100.10.1.4
    nameAcl         	    OBJECT IDENTIFIER ::= { acl 4 }

       
    
--xxx.100.10.1.1.1
fireWallEnable OBJECT-TYPE
    SYNTAX  INTEGER{
                disable(0),
                enable(1)
            }
            MAX-ACCESS  read-write
            STATUS  current
            DESCRIPTION
                "firewall on-off"
            ::= { fireWall 1 } 
            
--xxx.100.10.1.1.2
--fireWallOperation OBJECT-TYPE
--    SYNTAX  INTEGER {
--                permit(0),
--                denyipv4(1),
--                denyipv6(2),
--                denyip(3),
--                deny(8)
--            }
--            MAX-ACCESS  read-write
--            STATUS  current
--            DESCRIPTION
--                "fireWall of default rule"
--            ::= { fireWall 2 }    
             
--******************************************************************************************************** 
           
--xxx.100.10.1.2.1
timeRangeTable OBJECT-TYPE
    SYNTAX  SEQUENCE OF TimeRangeEntry
    MAX-ACCESS  not-accessible
    STATUS  current
            DESCRIPTION
                "timeRange Table"
            ::= { timeRange 1 } 
                
--xxx.100.10.1.2.1.1
    timeRangeEntry OBJECT-TYPE
        SYNTAX  TimeRangeEntry
        MAX-ACCESS  not-accessible
        STATUS  current
        DESCRIPTION
            "timeRange Entry"
        INDEX   { timeRangeName }
        ::= { timeRangeTable 1 }

    TimeRangeEntry
        ::= SEQUENCE
            {
                timeRangeName               DisplayString,
                timeRangeType		    INTEGER,
                timeRangeStWeek		    INTEGER,
                timeRangeStTime		    DisplayString,
                timeRangeStDate		    DisplayString,
                timeRangeEndWeek	    INTEGER,
                timeRangeEndTime	    DisplayString,
                timeRangeEndDate	    DisplayString,
                timeRangeStatus             INTEGER
            }

--xxx.100.10.1.2.1.1.1
        timeRangeName OBJECT-TYPE
            SYNTAX  DisplayString(SIZE (1..64))
            MAX-ACCESS  not-accessible
            STATUS  current
            DESCRIPTION
                "TimeRange name"
            ::= { timeRangeEntry 1 }
                      
--xxx.100.10.1.2.1.1.2
        timeRangeType OBJECT-TYPE
            SYNTAX  INTEGER 
            {
                absolute(0),
                absolutePeriodic(1),
                periodic(2)
            }
            MAX-ACCESS  read-create
            STATUS  current
            DESCRIPTION
                "TimeRange type"
            ::= { timeRangeEntry 2 }

--xxx.100.10.1.2.1.1.3
        timeRangeStWeek OBJECT-TYPE
            SYNTAX  INTEGER 
                    {
            	    	monday(1),
               		tuesday(2),
               		wednesday(4),
            	    	thursday(8),
               		friday(16),
               		saturday(32),
               		sunday(64)               		            	
            	    }
            MAX-ACCESS  read-create
            STATUS  current
            DESCRIPTION
                "configurate the start week"
            ::= { timeRangeEntry 3 }
            
--xxx.100.10.1.2.1.1.4
        timeRangeStTime OBJECT-TYPE
            SYNTAX  DisplayString 
            MAX-ACCESS  read-create
            STATUS  current
            DESCRIPTION
                "configurate the start clock"
            ::= { timeRangeEntry 4 }
            
--xxx.100.10.1.2.1.1.5
        timeRangeStDate OBJECT-TYPE
            SYNTAX  DisplayString 
            MAX-ACCESS  read-create
            STATUS  current
            DESCRIPTION
                "configurate the start Date"
            ::= { timeRangeEntry 5 }            
            
--xxx.100.10.1.2.1.1.6
        timeRangeEndWeek OBJECT-TYPE
            SYNTAX  INTEGER 
            	{
            	    	monday(1),
               		tuesday(2),
               		wednesday(4),
            	    	thursday(8),
               		friday(16),
               		saturday(32),
               		sunday(64)               		            	
            	}
            MAX-ACCESS  read-create
            STATUS  current
            DESCRIPTION
                "configurate the end week"
            ::= { timeRangeEntry 6 }
            
--xxx.100.10.1.2.1.1.7
        timeRangeEndTime OBJECT-TYPE
            SYNTAX  DisplayString 
            MAX-ACCESS  read-create
            STATUS  current
            DESCRIPTION
                "configurate the end clock"
            ::= { timeRangeEntry 7 }
            
--xxx.100.10.1.2.1.1.8
        timeRangeEndDate OBJECT-TYPE
            SYNTAX  DisplayString 
            MAX-ACCESS  read-create
            STATUS  current
            DESCRIPTION
                "configurate the end date"
            ::= { timeRangeEntry 8 }  
            
--xxx.100.10.1.2.1.1.9
        timeRangeStatus OBJECT-TYPE
            SYNTAX  INTEGER
            	    {
            	    	createAndGo(0),
               		active(1),
               		destroy(2)
            	    }
            MAX-ACCESS  read-create
            STATUS  current
            DESCRIPTION
                "TimeRange configurate status machine"
            ::= { timeRangeEntry  9 }    
               
--xxx.100.10.1.2.2
timeRangeShowTable OBJECT-TYPE
    SYNTAX  SEQUENCE OF TimeRangeShowEntry
    MAX-ACCESS  not-accessible
    STATUS  current
            DESCRIPTION
                "TimeRange show Table"
            ::= { timeRange 2 } 
                
--xxx.100.10.1.2.2.1
    timeRangeShowEntry OBJECT-TYPE
        SYNTAX  TimeRangeShowEntry
        MAX-ACCESS  not-accessible
        STATUS  current
        DESCRIPTION
            "TimeRange show Entry"
        INDEX   { timeRangeShowName , timeRangeElemNum }
        ::= { timeRangeShowTable 1 }

    TimeRangeShowEntry
        ::= SEQUENCE
            {
                timeRangeShowName           DisplayString,
                timeRangeElemNum	    INTEGER,
                timeRangeShow		    DisplayString
            }    
            
--xxx.100.10.1.2.2.1.1
        timeRangeShowName OBJECT-TYPE
            SYNTAX  DisplayString
            MAX-ACCESS  not-accessible
            STATUS  current
            DESCRIPTION
                "TimeRange name"
            ::= { timeRangeShowEntry 1 }
                      
--xxx.100.10.1.2.2.1.2
        timeRangeElemNum OBJECT-TYPE
            SYNTAX  INTEGER 
            MAX-ACCESS  not-accessible
            STATUS  current
            DESCRIPTION
                "TimeRange group index"
            ::= { timeRangeShowEntry 2 }  
                      
--xxx.100.10.1.2.2.1.3
        timeRangeShow OBJECT-TYPE
            SYNTAX  DisplayString
            MAX-ACCESS  read-only
            STATUS  current
            DESCRIPTION
                "TimeRange configure status"
            ::= { timeRangeShowEntry 3 }     
                                              
--********************************************************************************************************

--xxx.100.10.1.3.2
    numIpStandardAcl            	  OBJECT IDENTIFIER ::= { numAcl 2 } 

--xxx.100.10.1.3.2.1.1
        numIpStandardNum OBJECT-TYPE
            SYNTAX  INTEGER (1..99)
            MAX-ACCESS read-create
            STATUS  current
            DESCRIPTION
                "The name of number-ip-standard-acl group Interface."
            ::= { numIpStandardAcl 1 }

--xxx.100.10.1.3.2.1.2
        numIpStandardAct OBJECT-TYPE
            SYNTAX  INTEGER 
             	    {
            	    	deny(0),
               		permit(1)
            	    }            
            MAX-ACCESS  read-create
            STATUS  current
            DESCRIPTION
                " The action of acl rule."
            ::= { numIpStandardAcl 2 }

--xxx.100.10.1.3.2.1.3
        numIpStandardSrcIpType OBJECT-TYPE
            SYNTAX  INTEGER
            	{
        		specified(0),
        		any(1),
        		host(2)   
        	}            
            MAX-ACCESS  read-create
            STATUS  current
            DESCRIPTION
                "The type of Source Ip address used by this ACE."
            ::= { numIpStandardAcl 3 }
            
--xxx.100.10.1.3.2.1.4
        numIpStandardSrcIp OBJECT-TYPE
            SYNTAX  IpAddress            
            MAX-ACCESS  read-create
            STATUS  current
            DESCRIPTION
                " Source IP-address of basic acl rule."
            ::= { numIpStandardAcl 4 }
            
--xxx.100.10.1.3.2.1.5
        numIpStandardSrcIpWild OBJECT-TYPE
            SYNTAX  IpAddress           
            MAX-ACCESS  read-create
            STATUS  current
            DESCRIPTION
                " Source IP-address wild  of basic acl rule."
            ::= { numIpStandardAcl 5 }

--xxx.100.10.1.3.2.1.6
        numIpStandardStatus OBJECT-TYPE
            SYNTAX  INTEGER
            	    {
            	    	createAndGo(0),
               		active(1),
               		destroy(2)
            	    }
            MAX-ACCESS  read-create
            STATUS  current
            DESCRIPTION
                " now state of the access-list."
            ::= { numIpStandardAcl 6 } 

--********************************************************************************************************

--xxx.100.10.1.3.3
    numMacStandardAcl           	  OBJECT IDENTIFIER ::= { numAcl 3 } 


--xxx.100.10.1.3.3.1
        numMacStandardNum OBJECT-TYPE
            SYNTAX  INTEGER (700..799)
            MAX-ACCESS  read-create
            STATUS  current
            DESCRIPTION
                "The name of number-ip-standard-acl group Interface."
            ::= { numMacStandardAcl 1 }
            
--xxx.100.10.1.3.4.2
        numMacStandardAct OBJECT-TYPE
            SYNTAX  INTEGER
              	    {
            	    	deny(0),
               		permit(1)
            	    }            
            MAX-ACCESS  read-create
            STATUS  current
            DESCRIPTION
                " The action of acl rule."
            ::= { numMacStandardAcl 2 }

--xxx.100.10.1.3.4.3
        numMacStandardSrcMacType OBJECT-TYPE
            SYNTAX  INTEGER
            	{
        		specified(0),
        		any(1),
        		host(2)   
        	}            
            MAX-ACCESS  read-create
            STATUS  current
            DESCRIPTION
                "The type of Source Mac address used by this ACE."
            ::= { numMacStandardAcl 3 }
            
--xxx.100.10.1.3.3.4
        numMacStandardSrcMac OBJECT-TYPE
            SYNTAX  MacAddress (SIZE(17))            
            MAX-ACCESS  read-create
            STATUS  current
            DESCRIPTION
                " Source Mac-address of basic acl rule."
            ::= { numMacStandardAcl 4 }
            
--xxx.100.10.1.3.3.5
        numMacStandardSrcMacWild OBJECT-TYPE
            SYNTAX  MacAddress (SIZE(17))           
            MAX-ACCESS  read-create
            STATUS  current
            DESCRIPTION
                " Source Mac-address wild of basic acl rule."
            ::= { numMacStandardAcl 5 }

--xxx.100.10.1.3.3.6
        numMacStandardStatus OBJECT-TYPE
            SYNTAX  INTEGER
            	    {
            	    	createAndGo(0),
               		active(1),
               		destroy(2)
            	    }
            MAX-ACCESS  read-create
            STATUS  current
            DESCRIPTION
                " now state of the access-list."
            ::= { numMacStandardAcl 6 } 
            
--********************************************************************************************************

--xxx.100.10.1.3.4
    numIpExternAcl           	  OBJECT IDENTIFIER ::= { numAcl 4 }

--xxx.100.10.1.3.4.1
        numIpExternNum OBJECT-TYPE
            SYNTAX  INTEGER (100..199)
            MAX-ACCESS read-create
            STATUS  current
            DESCRIPTION
                "The name of number-ip-Extern-acl group Interface."
            ::= { numIpExternAcl 1 }

--xxx.100.10.1.3.4.3
        numIpExternAct OBJECT-TYPE
            SYNTAX  INTEGER 
             	    {
            	    	deny(0),
               		permit(1)
            	    }            
            MAX-ACCESS  read-create
            STATUS  current
            DESCRIPTION
                " The action of acl rule."
            ::= { numIpExternAcl 3 }

--xxx.100.10.1.3.4.4
        numIpExternSrcIpType OBJECT-TYPE
            SYNTAX  INTEGER
            	{
        		specified(0),
        		any(1),
        		host(2)   
        	}            
            MAX-ACCESS  read-create
            STATUS  current
            DESCRIPTION
                "The type of Source IP address used by this ACE entry."
            ::= { numIpExternAcl 4 }
            
--xxx.100.10.1.3.4.5
        numIpExternSrcIp OBJECT-TYPE
            SYNTAX  IpAddress            
            MAX-ACCESS  read-create
            STATUS  current
            DESCRIPTION
                " Source IP-address of basic acl rule."
            ::= { numIpExternAcl 5 }
            
--xxx.100.10.1.3.4.6
        numIpExternSrcIpWild OBJECT-TYPE
            SYNTAX  IpAddress           
            MAX-ACCESS  read-create
            STATUS  current
            DESCRIPTION
                " Source IP-address wild  of basic acl rule."
            ::= { numIpExternAcl 6 }

--xxx.100.10.1.3.4.7
        numIpExternDestIpType OBJECT-TYPE
            SYNTAX  INTEGER
            	{
        		specified(0),
        		any(1),
        		host(2)   
        	}            
            MAX-ACCESS  read-create
            STATUS  current
            DESCRIPTION
                "The type of Destination IP address used by this ACE entry."
            ::= { numIpExternAcl 7 }
            
--xxx.100.10.1.3.4.8
        numIpExternDestIp OBJECT-TYPE
            SYNTAX  IpAddress            
            MAX-ACCESS  read-create
            STATUS  current
            DESCRIPTION
                " Destination IP-address of basic acl rule."
            ::= { numIpExternAcl 8 }
            
--xxx.100.10.1.3.4.9
        numIpExternDestIpWild OBJECT-TYPE
            SYNTAX  IpAddress           
            MAX-ACCESS  read-create
            STATUS  current
            DESCRIPTION
                " Destination IP-address wild  of basic acl rule."
            ::= { numIpExternAcl 9 }

--xxx.100.10.1.3.4.10
        numIpExternPre OBJECT-TYPE
            SYNTAX  INTEGER(0..7)         
            MAX-ACCESS  read-create
            STATUS  current
            DESCRIPTION
                "Specifies the IP precedence value to be matched against.
        This object could not be configured when the status of the
        entry, caqIpAceStatus, is active(1).  
        
        The value of this object is ignored whenever the value of 
        caqIpAceTosMatchCritial object is not matchIpPrec(3)."
            ::= { numIpExternAcl 10 }

--xxx.100.10.1.3.4.11
        numIpExternTos OBJECT-TYPE
            SYNTAX  INTEGER(0..15)           
            MAX-ACCESS  read-create
            STATUS  current
            DESCRIPTION
                "The value of IP-packet's TOS. <0-15>            
                 Value of TOS(type of service) max-reliability    
                 Match packets with max reliable TOS(2) max-throughput     
                 Match packets with max throughput TOS(4) min-delay          
                 Match packets with min delay TOS(8) min-monetary-cost  
                 Match packets with min monetary cost TOS(1) normal             
                 Match packets with normal TOS(0)"
            ::= { numIpExternAcl 11 }

--xxx.100.10.1.3.4.12
        numIpExternTimeRange OBJECT-TYPE
            SYNTAX DisplayString(SIZE (1..64))           
            MAX-ACCESS  read-create
            STATUS  current
            DESCRIPTION
                "The Time-range of advanced acl rule."
            ::= { numIpExternAcl 12 }

--xxx.100.10.1.3.4.13
        numIpExternProtocol OBJECT-TYPE
            SYNTAX INTEGER(0..255)           
            MAX-ACCESS  read-create
            STATUS  current
            DESCRIPTION
                "The protocol number field in the IP header used to indicate
        the higher layer protocol as specified in RFC 1700. A value 
        value of 0 matches every IP packet. 
        
        For example :
        0 is IP, 1 is ICMP, 2 is IGMP, 4 is IP in IP encapsulation,
        6 is TCP, 9 is IGRP, 17 is UDP, 47 is GRE, 50 is ESP, 51 is AH,
        88 is EIGRP, 89 is OSPF, 94 is KA9Q/NOS compatible IP over IP,
        103 is PIMv2, 108 is PCP."
            ::= { numIpExternAcl 13 }

--xxx.100.10.1.3.4.14
        numIpExternSrcOP OBJECT-TYPE
            SYNTAX INTEGER{
                noOperator(0),
        	lt(1),
        	gt(2),
        	eq(3),
        	neq(4),
        	range(5)
        	}           
            MAX-ACCESS  read-create
            STATUS  current
            DESCRIPTION
                "Indicates how a packet's source TCP/UDP port number is
        to be compared.
        
        If the numIpExternProtocol object in the same row does not
        indicate TCP or UDP, this object has to be 'noOperator(0)' and
        cannot be changed while this row is active, i.e., the value of
        numIpExternStatus in the same row has the value 'active(1)'.
        
        'noOperator(0)', which is the default value, means that no
        comparison is to be made with the source TCP/UDP port number.
        
        lt(1) means less than, gt(2) means greater than, eq(3)
        means equal, neq(4) means not equal. Those 4 operators
        are using the numIpExternSrcPort object as an operand which
        is the only one needed. 
        
        range(5) means that it compares the port value between two 
        numbers, so this operator needs 2 operands. One operand is 
        the starting port number of the range which is numIpExternSrcPort 
        object, and the other operand is the ending port number of the 
        range which the numIpExternSrcPortRange object is in.
        
        Now support(3)eq,(5)range."
            ::= { numIpExternAcl 14 }

--xxx.100.10.1.3.4.15
        numIpExternSrcPort OBJECT-TYPE
            SYNTAX INTEGER(0..65535)          
            MAX-ACCESS  read-create
            STATUS  current
            DESCRIPTION
                "The source port number of the TCP or UDP protocol. If the
        numIpExternSrcOP object in the same row is range(5), this
        object will be the starting port number of the port range.
        This object cannot be configured if numIpExternStatus in the 
        same row is active(1) or numIpExternSrcOP in the same row
        is noOperator(0)."
            ::= { numIpExternAcl 15 }

--xxx.100.10.1.3.4.16          
	numIpExternSrcPortRange OBJECT-TYPE
    	   SYNTAX INTEGER(0..65535)
    	   MAX-ACCESS read-create
    	   STATUS current
    	   DESCRIPTION
        	"The source port number of the TCP or UDP protocol. If the
        numIpExternSrcOP object in the same row is range(5), this
        object will be the ending port number of the port range.
        This object cannot be configured if numIpExternStatus in the 
        same row is active(1) or numIpExternSrcOP in the same row
        is not range(5)."
    ::= { numIpExternAcl 16 }            

--xxx.100.10.1.3.4.17
        numIpExternDestOP OBJECT-TYPE
            SYNTAX INTEGER{
                noOperator(0),
        	lt(1),
        	gt(2),
        	eq(3),
        	neq(4),
        	range(5)
        	}           
            MAX-ACCESS  read-create
            STATUS  current
            DESCRIPTION
                "Indicates how a packet's Destination TCP/UDP port number is
        to be compared.
        
        If the numIpExternProtocol object in the same row does not
        indicate TCP or UDP, this object has to be 'noOperator(0)' and
        cannot be changed while this row is active, i.e., the value of
        numIpExternStatus in the same row has the value 'active(1)'.
        
        'noOperator(0)', which is the default value, means that no
        comparison is to be made with the source TCP/UDP port number.
        
        lt(1) means less than, gt(2) means greater than, eq(3)
        means equal, neq(4) means not equal. Those 4 operators
        are using the numIpExternDestPort object as an operand which
        is the only one needed. 
        
        range(5) means that it compares the port value between two 
        numbers, so this operator needs 2 operands. One operand is 
        the starting port number of the range which is numIpExternSrcPort 
        object, and the other operand is the ending port number of the 
        range which the numIpExternDestPortRange object is in.
        
        Now support(3)eq,(5)range."
            ::= { numIpExternAcl 17 }

--xxx.100.10.1.3.4.18
        numIpExternDestPort OBJECT-TYPE
            SYNTAX INTEGER(0..65535)          
            MAX-ACCESS  read-create
            STATUS  current
            DESCRIPTION
                "The source port number of the TCP or UDP protocol. If the
        numIpExternDestOP object in the same row is range(5), this
        object will be the starting port number of the port range.
        This object cannot be configured if numIpExternStatus in the 
        same row is active(1) or numIpExternDestOP in the same row
        is noOperator(0)."
            ::= { numIpExternAcl 18 }

--xxx.100.10.1.3.4.19          
	numIpExternDestPortRange OBJECT-TYPE
    	   SYNTAX INTEGER(0..65535)
    	   MAX-ACCESS read-create
    	   STATUS current
    	   DESCRIPTION
        	"The source port number of the TCP or UDP protocol. If the
        numIpExternDestOP object in the same row is range(5), this
        object will be the ending port number of the port range.
        This object cannot be configured if numIpExternStatus in the 
        same row is active(1) or numIpExternDestOP in the same row
        is not range(5)."
    		::= { numIpExternAcl 19 }
     
--xxx.100.10.1.3.4.20 
numIpExternIcmpType OBJECT-TYPE
    SYNTAX INTEGER(0..255)
    MAX-ACCESS read-create
    STATUS current
    DESCRIPTION
        "Indicates the message type of ICMP packets. The type is
        a number from 0 to 255."
    DEFVAL { 0 }
    ::= { numIpExternAcl 20 }
    
--xxx.100.10.1.3.4.21 
numIpExternIcmpCode OBJECT-TYPE
    SYNTAX INTEGER(0..255)
    MAX-ACCESS read-create
    STATUS current
    DESCRIPTION
        "Indicates the message code of ICMP packets. The code is
        a number from 0 to 255."
    DEFVAL { 0 }
    ::= { numIpExternAcl 21 }
    
--xxx.100.10.1.3.4.22 
numIpExternIgmpType OBJECT-TYPE
    SYNTAX INTEGER(0..15)
    MAX-ACCESS read-create
    STATUS current
    DESCRIPTION
        "Indicates the message type of IGMP packets. The code is
        a number from 0 to 15."
    DEFVAL { 0 }
    ::= { numIpExternAcl 22 }

--xxx.100.10.1.3.4.23
        numIpExternTcpType OBJECT-TYPE
            SYNTAX  INTEGER
            	    {
            	    	mo(0),
               		fin(1),
            	    	syn(2),
               		rst(4),
            	    	psh(8),
               		ack(16),
               		urg(32)               		               		               		
            	    }
            MAX-ACCESS  read-create
            STATUS  current
            DESCRIPTION
                " Tcp type."
            ::= { numIpExternAcl 23 } 
                        
--xxx.100.10.1.3.4.24
        numIpExternStatus OBJECT-TYPE
            SYNTAX  INTEGER
            	    {
            	    	createAndGo(0),
               		active(1),
               		destroy(2)
            	    }
            MAX-ACCESS  read-create
            STATUS  current
            DESCRIPTION
                " now state of the access-list."
            ::= { numIpExternAcl 24 } 

--********************************************************************************************************           
--xxx.100.10.1.3.5
    numMacExternAcl           	  OBJECT IDENTIFIER ::= { numAcl 5 }
                  
--xxx.100.10.1.3.5.1
        numMacExternNum OBJECT-TYPE
            SYNTAX  INTEGER (1100..1199)
            MAX-ACCESS read-create
            STATUS  current
            DESCRIPTION
                "The name of number-Mac-Extern-acl group Interface."
            ::= { numMacExternAcl 1 }
            
--xxx.100.10.1.3.5.2
--        numMacExternSubitemNum OBJECT-TYPE
--            SYNTAX  INTEGER
--            MAX-ACCESS  not-accessible
--            STATUS  current
--            DESCRIPTION
--                " The number of number-Mac-Extern-acl group's node."
--            ::= { numMacExternAcl 2 }

--xxx.100.10.1.3.5.3
        numMacExternAct OBJECT-TYPE
            SYNTAX  INTEGER 
             	    {
            	    	deny(0),
               		permit(1)
            	    }            
            MAX-ACCESS  read-create
            STATUS  current
            DESCRIPTION
                " The action of acl rule."
            ::= { numMacExternAcl 3 }

--xxx.100.10.1.3.5.4
        numMacExternSrcMacType OBJECT-TYPE
            SYNTAX  INTEGER
            	{
        		specified(0),
        		any(1),
        		host(2)   
        	}            
            MAX-ACCESS  read-create
            STATUS  current
            DESCRIPTION
                "The type of Source Mac address used by this ACE entry."
            ::= { numMacExternAcl 4 }
            
--xxx.100.10.1.3.5.5
        numMacExternSrcMac OBJECT-TYPE
            SYNTAX  MacAddress (SIZE(17))            
            MAX-ACCESS  read-create
            STATUS  current
            DESCRIPTION
                " Source Mac-address of basic acl rule."
            ::= { numMacExternAcl 5 }
            
--xxx.100.10.1.3.5.6
        numMacExternSrcMacWild OBJECT-TYPE
            SYNTAX  MacAddress (SIZE(17))           
            MAX-ACCESS  read-create
            STATUS  current
            DESCRIPTION
                " Source Mac-address wild  of basic acl rule."
            ::= { numMacExternAcl 6 }

--xxx.100.10.1.3.5.7
        numMacExternDestMacType OBJECT-TYPE
            SYNTAX  INTEGER
            	{
        		specified(0),
        		any(1),
        		host(2)   
        	}            
            MAX-ACCESS  read-create
            STATUS  current
            DESCRIPTION
                "The type of Destination Mac address used by this ACE entry."
            ::= { numMacExternAcl 7 }
            
--xxx.100.10.1.3.5.8
        numMacExternDestMac OBJECT-TYPE
            SYNTAX  MacAddress (SIZE(17))            
            MAX-ACCESS  read-create
            STATUS  current
            DESCRIPTION
                " Destination Mac-address of basic acl rule."
            ::= { numMacExternAcl 8 }
            
--xxx.100.10.1.3.5.9
        numMacExternDestMacWild OBJECT-TYPE
            SYNTAX  MacAddress (SIZE(17))           
            MAX-ACCESS  read-create
            STATUS  current
            DESCRIPTION
                " Destination Mac-address wild  of basic acl rule."
            ::= { numMacExternAcl 9 }    
            
--xxx.100.10.1.3.5.10
	numMacExternPacketType OBJECT-TYPE
    	    SYNTAX INTEGER
    	    MAX-ACCESS read-create
    	    STATUS current
    	    DESCRIPTION
                "Indicates the message type of packets.none(0),untagged-eth2(1),
                untagged-802.3(2),tagged-eth2(3),tagged-802.3(4)"
    	    ::= { numMacExternAcl 10 }
            
--xxx.100.10.1.3.5.11
        numMacExternStatus OBJECT-TYPE
            SYNTAX  INTEGER
            	    {
            	    	createAndGo(0),
               		active(1),
               		destroy(2)
            	    }
            MAX-ACCESS  read-create
            STATUS  current
            DESCRIPTION
                " now state of the access-list."
            ::= { numMacExternAcl 11 }            
--********************************************************************************************************

--xxx.100.10.1.3.6
    numMacIpExternAcl           	  OBJECT IDENTIFIER ::= { numAcl 6 }

--xxx.100.10.1.3.6.1
        numMacIpExternNum OBJECT-TYPE
            SYNTAX  INTEGER (3100..3199)
            MAX-ACCESS read-create
            STATUS  current
            DESCRIPTION
                "The name of number-ip-Extern-acl group Interface."
            ::= { numMacIpExternAcl 1 }
            
--xxx.100.10.1.3.6.2
--        numMacIpExternSubitemNum OBJECT-TYPE
--            SYNTAX  INTEGER
--            MAX-ACCESS  not-accessible
--            STATUS  current
--            DESCRIPTION
--                " The number of number-ip-Extern-acl group's node."
--            ::= { numMacIpExternAcl 2 }

--xxx.100.10.1.3.6.3
        numMacIpExternAct OBJECT-TYPE
            SYNTAX  INTEGER 
             	    {
            	    	deny(0),
               		permit(1)
            	    }            
            MAX-ACCESS  read-create
            STATUS  current
            DESCRIPTION
                " The action of acl rule."
            ::= { numMacIpExternAcl 3 }

--xxx.100.10.1.3.6.4
        numMacIpExternSrcMacType OBJECT-TYPE
            SYNTAX  INTEGER
            	{
        		specified(0),
        		any(1),
        		host(2)   
        	}            
            MAX-ACCESS  read-create
            STATUS  current
            DESCRIPTION
                "The type of Source Mac address used by this ACE entry."
            ::= { numMacIpExternAcl 4 }
            
--xxx.100.10.1.3.6.5
        numMacIpExternSrcMac OBJECT-TYPE
            SYNTAX  MacAddress (SIZE(17))            
            MAX-ACCESS  read-create
            STATUS  current
            DESCRIPTION
                " Source Mac-address of basic acl rule."
            ::= { numMacIpExternAcl 5 }
            
--xxx.100.10.1.3.6.6
        numMacIpExternSrcMacWild OBJECT-TYPE
            SYNTAX  MacAddress (SIZE(17))           
            MAX-ACCESS  read-create
            STATUS  current
            DESCRIPTION
                " Source Mac-address wild  of basic acl rule."
            ::= { numMacIpExternAcl 6 }

--xxx.100.10.1.3.6.7
        numMacIpExternDestMacType OBJECT-TYPE
            SYNTAX  INTEGER
            	{
        		specified(0),
        		any(1),
        		host(2)   
        	}            
            MAX-ACCESS  read-create
            STATUS  current
            DESCRIPTION
                "The type of Destination Mac address used by this ACE entry."
            ::= { numMacIpExternAcl 7 }
            
--xxx.100.10.1.3.6.8
        numMacIpExternDestMac OBJECT-TYPE
            SYNTAX  MacAddress (SIZE(17))            
            MAX-ACCESS  read-create
            STATUS  current
            DESCRIPTION
                " Destination Mac-address of basic acl rule."
            ::= { numMacIpExternAcl 8 }
            
--xxx.100.10.1.3.6.9
        numMacIpExternDestMacWild OBJECT-TYPE
            SYNTAX  MacAddress (SIZE(17))           
            MAX-ACCESS  read-create
            STATUS  current
            DESCRIPTION
                " Destination Mac-address wild  of basic acl rule."
            ::= { numMacIpExternAcl 9 }

--xxx.100.10.1.3.6.10
        numMacIpExternSrcIpType OBJECT-TYPE
            SYNTAX  INTEGER
            	{
        		specified(0),
        		any(1),
        		host(2)   
        	}            
            MAX-ACCESS  read-create
            STATUS  current
            DESCRIPTION
                "The type of Source IP address used by this ACE entry."
            ::= { numMacIpExternAcl 10 }
            
--xxx.100.10.1.3.6.11
        numMacIpExternSrcIp OBJECT-TYPE
            SYNTAX  IpAddress            
            MAX-ACCESS  read-create
            STATUS  current
            DESCRIPTION
                " Source IP-address of basic acl rule."
            ::= { numMacIpExternAcl 11 }
            
--xxx.100.10.1.3.6.12
        numMacIpExternSrcIpWild OBJECT-TYPE
            SYNTAX  IpAddress           
            MAX-ACCESS  read-create
            STATUS  current
            DESCRIPTION
                " Source IP-address wild  of basic acl rule."
            ::= { numMacIpExternAcl 12 }

--xxx.100.10.1.3.6.13
        numMacIpExternDestIpType OBJECT-TYPE
            SYNTAX  INTEGER
            	{
        		specified(0),
        		any(1),
        		host(2)   
        	}            
            MAX-ACCESS  read-create
            STATUS  current
            DESCRIPTION
                "The type of Destination IP address used by this ACE entry."
            ::= { numMacIpExternAcl 13 }
            
--xxx.100.10.1.3.6.14
        numMacIpExternDestIp OBJECT-TYPE
            SYNTAX  IpAddress            
            MAX-ACCESS  read-create
            STATUS  current
            DESCRIPTION
                " Destination IP-address of basic acl rule."
            ::= { numMacIpExternAcl 14 }
            
--xxx.100.10.1.3.6.15
        numMacIpExternDestIpWild OBJECT-TYPE
            SYNTAX  IpAddress           
            MAX-ACCESS  read-create
            STATUS  current
            DESCRIPTION
                " Destination IP-address wild  of basic acl rule."
            ::= { numMacIpExternAcl 15 }

--xxx.100.10.1.3.6.16
        numMacIpExternPre OBJECT-TYPE
            SYNTAX  INTEGER(0..7)         
            MAX-ACCESS  read-create
            STATUS  current
            DESCRIPTION
                "Specifies the IP precedence value to be matched against.
        This object could not be configured when the status of the
        entry, caqIpAceStatus, is active(1)"
            ::= { numMacIpExternAcl 16 }

--xxx.100.10.1.3.6.17
        numMacIpExternTos OBJECT-TYPE
            SYNTAX  INTEGER(0..15)           
            MAX-ACCESS  read-create
            STATUS  current
            DESCRIPTION
                "The value of IP-packet's TOS. <0-15>            
                 Value of TOS(type of service) max-reliability    
                 Match packets with max reliable TOS(2) max-throughput     
                 Match packets with max throughput TOS(4) min-delay          
                 Match packets with min delay TOS(8) min-monetary-cost  
                 Match packets with min monetary cost TOS(1) normal             
                 Match packets with normal TOS(0)"
            ::= { numMacIpExternAcl 17 }

--xxx.100.10.1.3.6.18
        numMacIpExternTimeRange OBJECT-TYPE
            SYNTAX DisplayString(SIZE (1..64))           
            MAX-ACCESS  read-create
            STATUS  current
            DESCRIPTION
                "The Time-range of advanced acl rule."
            ::= { numMacIpExternAcl 18 }

--xxx.100.10.1.3.6.19
        numMacIpExternProtocol OBJECT-TYPE
            SYNTAX INTEGER(0..255)           
            MAX-ACCESS  read-create
            STATUS  current
            DESCRIPTION
                "The protocol number field in the IP header used to indicate
        the higher layer protocol as specified in RFC 1700. A value 
        value of 0 matches every IP packet. 
        
        For example :
        0 is IP, 1 is ICMP, 2 is IGMP, 4 is IP in IP encapsulation,
        6 is TCP, 9 is IGRP, 17 is UDP, 47 is GRE, 50 is ESP, 51 is AH,
        88 is EIGRP, 89 is OSPF, 94 is KA9Q/NOS compatible IP over IP,
        103 is PIMv2, 108 is PCP."
            ::= { numMacIpExternAcl 19 }

--xxx.100.10.1.3.6.20
        numMacIpExternSrcOP OBJECT-TYPE
            SYNTAX INTEGER{
        	noOperator(0),
        	lt(1),
        	gt(2),
        	eq(3),
        	neq(4),
        	range(5)
        	}           
            MAX-ACCESS  read-create
            STATUS  current
            DESCRIPTION
                "Indicates how a packet's source TCP/UDP port number is
        to be compared.
        
        If the numMacIpExternProtocol object in the same row does not
        indicate TCP or UDP, this object has to be 'noOperator(0)' and
        cannot be changed while this row is active, i.e., the value of
        numMacIpExternStatus in the same row has the value 'active(1)'.
        
        'noOperator(0)', which is the default value, means that no
        comparison is to be made with the source TCP/UDP port number.
        
        lt(1) means less than, gt(2) means greater than, eq(3)
        means equal, neq(4) means not equal. Those 4 operators
        are using the numMacIpExternSrcPort object as an operand which
        is the only one needed. 
        
        range(5) means that it compares the port value between two 
        numbers, so this operator needs 2 operands. One operand is 
        the starting port number of the range which is numMacIpExternSrcPort 
        object, and the other operand is the ending port number of the 
        range which the numMacIpExternSrcPortRange object is in.
        
        Now support(3)eq,(5)range."
            ::= { numMacIpExternAcl 20 }

--xxx.100.10.1.3.6.21
        numMacIpExternSrcPort OBJECT-TYPE
            SYNTAX INTEGER(0..65535)          
            MAX-ACCESS  read-create
            STATUS  current
            DESCRIPTION
                "The source port number of the TCP or UDP protocol. If the
        numMacIpExternSrcOP object in the same row is range(5), this
        object will be the starting port number of the port range.
        This object cannot be configured if numMacIpExternStatus in the 
        same row is active(1) or numMacIpExternSrcOP in the same row
        is noOperator(0)."
            ::= { numMacIpExternAcl 21 }

--xxx.100.10.1.3.6.22         
	numMacIpExternSrcPortRange OBJECT-TYPE
    	   SYNTAX INTEGER(0..65535)
    	   MAX-ACCESS read-create
    	   STATUS current
    	   DESCRIPTION
        	"The source port number of the TCP or UDP protocol. If the
        numMacIpExternSrcOP object in the same row is range(5), this
        object will be the ending port number of the port range.
        This object cannot be configured if numMacIpExternStatus in the 
        same row is active(1) or numMacIpExternSrcOP in the same row
        is not range(5)."
    ::= { numMacIpExternAcl 22 }            

--xxx.100.10.1.3.6.23
        numMacIpExternDestOP OBJECT-TYPE
            SYNTAX INTEGER{
        	noOperator(0),
        	lt(1),
        	gt(2),
        	eq(3),
        	neq(4),
        	range(5)
        	}           
            MAX-ACCESS  read-create
            STATUS  current
            DESCRIPTION
                "Indicates how a packet's Destination TCP/UDP port number is
        to be compared.
        
        If the numMacIpExternProtocol object in the same row does not
        indicate TCP or UDP, this object has to be 'noOperator(0)' and
        cannot be changed while this row is active, i.e., the value of
        numMacIpExternStatus in the same row has the value 'active(1)'.
        
        'noOperator(0)', which is the default value, means that no
        comparison is to be made with the source TCP/UDP port number.
        
        lt(1) means less than, gt(2) means greater than, eq(3)
        means equal, neq(4) means not equal. Those 4 operators
        are using the numMacIpExternDestPort object as an operand which
        is the only one needed. 
        
        range(5) means that it compares the port value between two 
        numbers, so this operator needs 2 operands. One operand is 
        the starting port number of the range which is numIpExternSrcPort 
        object, and the other operand is the ending port number of the 
        range which the numMacIpExternDestPortRange object is in.
        
        Now support(3)eq,(5)range."
            ::= { numMacIpExternAcl 23 }

--xxx.100.10.1.3.6.24
        numMacIpExternDestPort OBJECT-TYPE
            SYNTAX INTEGER(0..65535)          
            MAX-ACCESS  read-create
            STATUS  current
            DESCRIPTION
                "The source port number of the TCP or UDP protocol. If the
        numMacIpExternDestOP object in the same row is range(5), this
        object will be the starting port number of the port range.
        This object cannot be configured if numMacIpExternStatus in the 
        same row is active(1) or numMacIpExternDestOP in the same row
        is noOperator(0)."
            ::= { numMacIpExternAcl 24 }

--xxx.100.10.1.3.6.25          
	numMacIpExternDestPortRange OBJECT-TYPE
    	   SYNTAX INTEGER(0..65535)
    	   MAX-ACCESS read-create
    	   STATUS current
    	   DESCRIPTION
        	"The source port number of the TCP or UDP protocol. If the
        numMacIpExternDestOP object in the same row is range(5), this
        object will be the ending port number of the port range.
        This object cannot be configured if numMacIpExternStatus in the 
        same row is active(1) or numMacIpExternDestOP in the same row
        is not range(5)."
    ::= { numMacIpExternAcl 25 }
     
--xxx.100.10.1.3.6.26 
numMacIpExternIcmpType OBJECT-TYPE
    SYNTAX INTEGER(0..255)
    MAX-ACCESS read-create
    STATUS current
    DESCRIPTION
        "Indicates the message type of ICMP packets. The type is
        a number from 0 to 255."
    DEFVAL { 0 }
    ::= { numMacIpExternAcl 26 }
    
--xxx.100.10.1.3.6.27 
numMacIpExternIcmpCode OBJECT-TYPE
    SYNTAX INTEGER(0..255)
    MAX-ACCESS read-create
    STATUS current
    DESCRIPTION
        "Indicates the message code of ICMP packets. The code is
        a number from 0 to 255."
    DEFVAL { 0 }
    ::= { numMacIpExternAcl 27 }
    
--xxx.100.10.1.3.6.28
numMacIpExternIgmpType OBJECT-TYPE
    SYNTAX INTEGER(0..15)
    MAX-ACCESS read-create
    STATUS current
    DESCRIPTION
        "Indicates the message type of IGMP packets. The code is
        a number from 0 to 15."
    DEFVAL { 0 }
    ::= { numMacIpExternAcl 28 }

--xxx.100.10.1.3.6.29
        numMacIpExternTcpType OBJECT-TYPE
            SYNTAX  INTEGER
            	    {
            	    	mo(0),
               		fin(1),
            	    	syn(2),
               		rst(4),
            	    	psh(8),
               		ack(16),
               		urg(32)   
            	    }
            MAX-ACCESS  read-create
            STATUS  current
            DESCRIPTION
                " Tcp type."
            ::= { numMacIpExternAcl 29 } 
            
--xxx.100.10.1.3.6.30
        numMacIpExternStatus OBJECT-TYPE
            SYNTAX  INTEGER
            	    {
            	    	createAndGo(0),
               		active(1),
               		destroy(2)
            	    }
            MAX-ACCESS  read-create
            STATUS  current
            DESCRIPTION
                " now state of the access-list."
            ::= { numMacIpExternAcl 30 } 

--********************************************************************************************************    

--xxx.100.10.1.4.2
    nameIpStandardAcl           	  OBJECT IDENTIFIER ::= { nameAcl 2 }

--xxx.100.10.1.4.2.1
        nameIpStandardName OBJECT-TYPE
            SYNTAX  DisplayString(SIZE (1..64))
            MAX-ACCESS read-create
            STATUS  current
            DESCRIPTION
                "The name of name-ip-standard-acl group Interface."
            ::= { nameIpStandardAcl 1 }
            
--xxx.100.10.1.4.2.2
        nameIpStandardAct OBJECT-TYPE
            SYNTAX  INTEGER 
             	    {
            	    	deny(0),
               		permit(1)
            	    }            
            MAX-ACCESS  read-create
            STATUS  current
            DESCRIPTION
                " The action of acl rule."
            ::= { nameIpStandardAcl 2 }

--xxx.100.10.1.4.2.3
        nameIpStandardSrcIpType OBJECT-TYPE
            SYNTAX  INTEGER
            	{
        		specified(0),
        		any(1),
        		host(2)         		
        	}            
            MAX-ACCESS  read-create
            STATUS  current
            DESCRIPTION
                "The type of Source IP address used by this ACE entry."
            ::= { nameIpStandardAcl 3 }
            
--xxx.100.10.1.4.2.4
        nameIpStandardSrcIp OBJECT-TYPE
            SYNTAX  IpAddress            
            MAX-ACCESS  read-create
            STATUS  current
            DESCRIPTION
                " Source IP-address of basic acl rule."
            ::= { nameIpStandardAcl 4 }
            
--xxx.100.10.1.4.2.5
        nameIpStandardSrcIpWild OBJECT-TYPE
            SYNTAX  IpAddress           
            MAX-ACCESS  read-create
            STATUS  current
            DESCRIPTION
                " Source IP-address wild  of basic acl rule."
            ::= { nameIpStandardAcl 5 }

--xxx.100.10.1.4.2.6
        nameIpStandardStatus OBJECT-TYPE
            SYNTAX  INTEGER
            	    {
            	    	createAndGo(0),
               		active(1),
               		destroy(2)
            	    }
            MAX-ACCESS  read-create
            STATUS  current
            DESCRIPTION
                " now state of the access-list."
            ::= { nameIpStandardAcl 6 } 

--********************************************************************************************************

--xxx.100.10.1.4.3
    nameIpExternAcl           	  OBJECT IDENTIFIER ::= { nameAcl 3 }
    
--xxx.100.10.1.4.3.1
        nameIpExternName OBJECT-TYPE
            SYNTAX  DisplayString(SIZE (1..64))
            MAX-ACCESS read-create
            STATUS  current
            DESCRIPTION
                "The name of name-ip-Extern-acl group Interface."
            ::= { nameIpExternAcl 1 }
            
--xxx.100.10.1.4.3.2
--        nameIpExternSubitemNum OBJECT-TYPE
--            SYNTAX  INTEGER
--            MAX-ACCESS  not-accessible
--            STATUS  current
--            DESCRIPTION
--                " The number of name-ip-Extern-acl group's node."
--            ::= { nameIpExternAcl 2 }

--xxx.100.10.1.4.3.3
        nameIpExternAct OBJECT-TYPE
            SYNTAX  INTEGER 
             	    {
            	    	deny(0),
               		permit(1)
            	    }            
            MAX-ACCESS  read-create
            STATUS  current
            DESCRIPTION
                " The action of acl rule."
            ::= { nameIpExternAcl 3 }

--xxx.100.10.1.4.3.4
        nameIpExternSrcIpType OBJECT-TYPE
            SYNTAX  INTEGER
            	{
        		specified(0),
        		any(1),
        		host(2)    
        	}            
            MAX-ACCESS  read-create
            STATUS  current
            DESCRIPTION
                "The type of Source IP address used by this ACE entry."
            ::= { nameIpExternAcl 4 }
            
--xxx.100.10.1.4.3.5
        nameIpExternSrcIp OBJECT-TYPE
            SYNTAX  IpAddress            
            MAX-ACCESS  read-create
            STATUS  current
            DESCRIPTION
                " Source IP-address of basic acl rule."
            ::= { nameIpExternAcl 5 }
            
--xxx.100.10.1.4.3.6
        nameIpExternSrcIpWild OBJECT-TYPE
            SYNTAX  IpAddress           
            MAX-ACCESS  read-create
            STATUS  current
            DESCRIPTION
                " Source IP-address wild  of basic acl rule."
            ::= { nameIpExternAcl 6 }

--xxx.100.10.1.4.3.7
        nameIpExternDestIpType OBJECT-TYPE
            SYNTAX  INTEGER
            	{
        		specified(0),
        		any(1),
        		host(2)   
        	}            
            MAX-ACCESS  read-create
            STATUS  current
            DESCRIPTION
                "The type of Destination IP address used by this ACE entry."
            ::= { nameIpExternAcl 7 }
            
--xxx.100.10.1.4.3.8
        nameIpExternDestIp OBJECT-TYPE
            SYNTAX  IpAddress            
            MAX-ACCESS  read-create
            STATUS  current
            DESCRIPTION
                " Destination IP-address of basic acl rule."
            ::= { nameIpExternAcl 8 }
            
--xxx.100.10.1.4.3.9
        nameIpExternDestIpWild OBJECT-TYPE
            SYNTAX  IpAddress           
            MAX-ACCESS  read-create
            STATUS  current
            DESCRIPTION
                " Destination IP-address wild  of basic acl rule."
            ::= { nameIpExternAcl 9 }

--xxx.100.10.1.4.3.10
        nameIpExternPre OBJECT-TYPE
            SYNTAX  INTEGER(0..7)         
            MAX-ACCESS  read-create
            STATUS  current
            DESCRIPTION
                "Specifies the IP precedence value to be matched against.
        This object could not be configured when the status of the
        entry, caqIpAceStatus, is active(1).  
        
        The value of this object is ignored whenever the value of 
        caqIpAceTosMatchCritial object is not matchIpPrec(3)."
            ::= { nameIpExternAcl 10 }

--xxx.100.10.1.4.3.11
        nameIpExternTos OBJECT-TYPE
            SYNTAX  INTEGER(0..15)           
            MAX-ACCESS  read-create
            STATUS  current
            DESCRIPTION
                "The value of IP-packet's TOS.             
                 Value of TOS(type of service) max-reliability    
                 match packets with max reliable TOS(2), max-throughput     
                 match packets with max throughput TOS(4), min-delay          
                 match packets with min delay TOS(8), min-monetary-cost  
                 match packets with min monetary cost TOS(1), normal             
                 match packets with normal TOS(0)"
            ::= { nameIpExternAcl 11 }

--xxx.100.10.1.4.3.12
        nameIpExternTimeRange OBJECT-TYPE
            SYNTAX DisplayString(SIZE (1..64))           
            MAX-ACCESS  read-create
            STATUS  current
            DESCRIPTION
                "The Time-range of advanced acl rule."
            ::= { nameIpExternAcl 12 }

--xxx.100.10.1.4.3.13
        nameIpExternProtocol OBJECT-TYPE
            SYNTAX INTEGER(0..255)           
            MAX-ACCESS  read-create
            STATUS  current
            DESCRIPTION
                "The protocol number field in the IP header used to indicate
        the higher layer protocol as specified in RFC 1700. A value 
        value of 0 matches every IP packet. 
        
        For example :
        0 is IP, 1 is ICMP, 2 is IGMP, 4 is IP in IP encapsulation,
        6 is TCP, 9 is IGRP, 17 is UDP, 47 is GRE, 50 is ESP, 51 is AH,
        88 is EIGRP, 89 is OSPF, 94 is KA9Q/NOS compatible IP over IP,
        103 is PIMv2, 108 is PCP."
            ::= { nameIpExternAcl 13 }

--xxx.100.10.1.4.3.14
        nameIpExternSrcOP OBJECT-TYPE
            SYNTAX INTEGER{
        	noOperator(0),
        	lt(1),
        	gt(2),
        	eq(3),
        	neq(4),
        	range(5)
        	}           
            MAX-ACCESS  read-create
            STATUS  current
            DESCRIPTION
                "Indicates how a packet's source TCP/UDP port number is
        to be compared.
        
        If the numIpExternProtocol object in the same row does not
        indicate TCP or UDP, this object has to be 'noOperator(0)' and
        cannot be changed while this row is active, i.e., the value of
        numIpExternStatus in the same row has the value 'active(1)'.
        
        'noOperator(0)', which is the default value, means that no
        comparison is to be made with the source TCP/UDP port number.
        
        lt(1) means less than, gt(2) means greater than, eq(3)
        means equal, neq(4) means not equal. Those 4 operators
        are using the numIpExternSrcPort object as an operand which
        is the only one needed. 
        
        range(5) means that it compares the port value between two 
        numbers, so this operator needs 2 operands. One operand is 
        the starting port number of the range which is nameIpExternSrcPort 
        object, and the other operand is the ending port number of the 
        range which the nameIpExternSrcPortRange object is in.
        
        Now support(3)eq,(5)range."
            ::= { nameIpExternAcl 14 }

--xxx.100.10.1.4.3.15
        nameIpExternSrcPort OBJECT-TYPE
            SYNTAX INTEGER(0..65535)          
            MAX-ACCESS  read-create
            STATUS  current
            DESCRIPTION
                "The source port number of the TCP or UDP protocol. If the
        nameIpExternSrcOP object in the same row is range(5), this
        object will be the starting port number of the port range.
        This object cannot be configured if nameIpExternStatus in the 
        same row is active(1) or nameIpExternSrcOP in the same row
        is noOperator(0)."
            ::= { nameIpExternAcl 15 }

--xxx.100.10.1.4.3.16           
	nameIpExternSrcPortRange OBJECT-TYPE
    	   SYNTAX INTEGER(0..65535)
    	   MAX-ACCESS read-create
    	   STATUS current
    	   DESCRIPTION
        	"The source port number of the TCP or UDP protocol. If the
        nameIpExternSrcOP object in the same row is range(5), this
        object will be the ending port number of the port range.
        This object cannot be configured if nameIpExternStatus in the 
        same row is active(1) or nameIpExternSrcOP in the same row
        is not range(5)."
    ::= { nameIpExternAcl 16 }            

--xxx.100.10.1.4.3.17
        nameIpExternDestOP OBJECT-TYPE
            SYNTAX INTEGER{
        	noOperator(0),
        	lt(1),
        	gt(2),
        	eq(3),
        	neq(4),
        	range(5)
        	}           
            MAX-ACCESS  read-create
            STATUS  current
            DESCRIPTION
                "Indicates how a packet's Destination TCP/UDP port number is
        to be compared.
        
        If the nameIpExternProtocol object in the same row does not
        indicate TCP or UDP, this object has to be 'noOperator(0)' and
        cannot be changed while this row is active, i.e., the value of
        nameIpExternStatus in the same row has the value 'active(1)'.
        
        'noOperator(0)', which is the default value, means that no
        comparison is to be made with the source TCP/UDP port number.
        
        lt(1) means less than, gt(2) means greater than, eq(3)
        means equal, neq(4) means not equal. Those 4 operators
        are using the nameIpExternDestPort object as an operand which
        is the only one needed. 
        
        range(5) means that it compares the port value between two 
        numbers, so this operator needs 2 operands. One operand is 
        the starting port number of the range which is nameIpExternSrcPort 
        object, and the other operand is the ending port number of the 
        range which the nameIpExternDestPortRange object is in.
        
        Now support(3)eq,(5)range."
            ::= { nameIpExternAcl 17 }

--xxx.100.10.1.4.3.18
        nameIpExternDestPort OBJECT-TYPE
            SYNTAX INTEGER(0..65535)          
            MAX-ACCESS  read-create
            STATUS  current
            DESCRIPTION
                "The source port number of the TCP or UDP protocol. If the
        nameIpExternDestOP object in the same row is range(5), this
        object will be the starting port number of the port range.
        This object cannot be configured if nameIpExternStatus in the 
        same row is active(1) or nameIpExternDestOP in the same row
        is noOperator(0)."
            ::= { nameIpExternAcl 18 }

--xxx.100.10.1.4.3.19           
	nameIpExternDestPortRange OBJECT-TYPE
    	   SYNTAX INTEGER(0..65535)
    	   MAX-ACCESS read-create
    	   STATUS current
    	   DESCRIPTION
        	"The source port number of the TCP or UDP protocol. If the
        nameIpExternDestOP object in the same row is range(5), this
        object will be the ending port number of the port range.
        This object cannot be configured if nameIpExternStatus in the 
        same row is active(1) or nameIpExternDestOP in the same row
        is not range(5)."
    ::= { nameIpExternAcl 19 }
     
--xxx.100.10.1.4.3.20  
nameIpExternIcmpType OBJECT-TYPE
    SYNTAX INTEGER(0..255)
    MAX-ACCESS read-create
    STATUS current
    DESCRIPTION
        "Indicates the message type of ICMP packets. The type is
        a number from 0 to 255."
    DEFVAL { 0 }
    ::= { nameIpExternAcl 20 }
    
--xxx.100.10.1.4.3.21  
nameIpExternIcmpCode OBJECT-TYPE
    SYNTAX INTEGER(0..255)
    MAX-ACCESS read-create
    STATUS current
    DESCRIPTION
        "Indicates the message code of ICMP packets. The code is
        a number from 0 to 255."
    DEFVAL { 0 }
    ::= { nameIpExternAcl 21 }
    
--xxx.100.10.1.4.3.22 
nameIpExternIgmpType OBJECT-TYPE
    SYNTAX INTEGER(0..15)
    MAX-ACCESS read-create
    STATUS current
    DESCRIPTION
        "Indicates the message type of IGMP packets. The code is
        a number from 0 to 15."
    DEFVAL { 0 }
    ::= { nameIpExternAcl 22 }

--xxx.100.10.1.4.3.23
        nameIpExternTcpType OBJECT-TYPE
            SYNTAX  INTEGER
            	    {
            	    	mo(0),
               		fin(1),
            	    	syn(2),
               		rst(4),
            	    	psh(8),
               		ack(16),
               		urg(32)   
            	    }
            MAX-ACCESS  read-create
            STATUS  current
            DESCRIPTION
                " Tcp type."
            ::= { nameIpExternAcl 23 } 
            
--xxx.100.10.1.4.3.24
        nameIpExternStatus OBJECT-TYPE
            SYNTAX  INTEGER
            	    {
            	    	createAndGo(0),
               		active(1),
               		destroy(2)
            	    }
            MAX-ACCESS  read-create
            STATUS  current
            DESCRIPTION
                " now state of the access-list."
            ::= { nameIpExternAcl 24 } 

--********************************************************************************************************   

--xxx.100.10.1.4.4
    nameMacExternAcl           	  OBJECT IDENTIFIER ::= { nameAcl 4 }
                  
--xxx.100.10.1.4.4.1
        nameMacExternName OBJECT-TYPE
            SYNTAX  DisplayString(SIZE (1..64))
            MAX-ACCESS read-create
            STATUS  current
            DESCRIPTION
                "The name of name-Mac-Extern-acl group Interface."
            ::= { nameMacExternAcl 1 }
            
--xxx.100.10.1.4.4.3
        nameMacExternAct OBJECT-TYPE
            SYNTAX  INTEGER 
             	    {
            	    	deny(0),
               		permit(1)
            	    }            
            MAX-ACCESS  read-create
            STATUS  current
            DESCRIPTION
                " The action of acl rule."
            ::= { nameMacExternAcl 3 }

--xxx.100.10.1.4.4.4
        nameMacExternSrcMacType OBJECT-TYPE
            SYNTAX  INTEGER
            	{
        		specified(0),
        		any(1),
        		host(2)   
        	}            
            MAX-ACCESS  read-create
            STATUS  current
            DESCRIPTION
                "The type of Source Mac address used by this ACE entry."
            ::= { nameMacExternAcl 4 }
            
--xxx.100.10.1.4.4.5
        nameMacExternSrcMac OBJECT-TYPE
            SYNTAX  MacAddress  (SIZE(17))           
            MAX-ACCESS  read-create
            STATUS  current
            DESCRIPTION
                " Source Mac-address of basic acl rule."
            ::= { nameMacExternAcl 5 }
            
--xxx.100.10.1.4.4.6
        nameMacExternSrcMacWild OBJECT-TYPE
            SYNTAX  MacAddress  (SIZE(17))          
            MAX-ACCESS  read-create
            STATUS  current
            DESCRIPTION
                " Source Mac-address wild  of basic acl rule."
            ::= { nameMacExternAcl 6 }

--xxx.100.10.1.4.4.7
        nameMacExternDestMacType OBJECT-TYPE
            SYNTAX  INTEGER
            	{
        		specified(0),
        		any(1),
        		host(2)   
        	}            
            MAX-ACCESS  read-create
            STATUS  current
            DESCRIPTION
                "The type of Destination Mac address used by this ACE entry."
            ::= { nameMacExternAcl 7 }
            
--xxx.100.10.1.4.4.8
        nameMacExternDestMac OBJECT-TYPE
            SYNTAX  MacAddress (SIZE(17))            
            MAX-ACCESS  read-create
            STATUS  current
            DESCRIPTION
                " Destination Mac-address of basic acl rule."
            ::= { nameMacExternAcl 8 }
            
--xxx.100.10.1.4.4.9
        nameMacExternDestMacWild OBJECT-TYPE
            SYNTAX  MacAddress  (SIZE(17))          
            MAX-ACCESS  read-create
            STATUS  current
            DESCRIPTION
                " Destination Mac-address wild  of basic acl rule."
            ::= { nameMacExternAcl 9 }    
            
--xxx.100.10.1.4.4.10
	nameMacExternPacketType OBJECT-TYPE
    	    SYNTAX INTEGER
    	    MAX-ACCESS read-create
    	    STATUS current
    	    DESCRIPTION
                "Indicates the message type of packets.none(0),untagged-eth2(1),
                untagged-802.3(2),tagged-eth2(3),tagged-802.3(4)"
    	    ::= { nameMacExternAcl 10 }
            
--xxx.100.10.1.4.4.11
        nameMacExternStatus OBJECT-TYPE
            SYNTAX  INTEGER
            	    {
            	    	createAndGo(0),
               		active(1),
               		destroy(2)
            	    }
            MAX-ACCESS  read-create
            STATUS  current
            DESCRIPTION
                " now state of the access-list."
            ::= { nameMacExternAcl 11 }        
                
--********************************************************************************************************

--xxx.100.10.1.4.5
    nameMacIpExternAcl           	  OBJECT IDENTIFIER ::= { nameAcl 5 }

--xxx.100.10.1.4.5.1
        nameMacIpExternName OBJECT-TYPE
            SYNTAX  DisplayString(SIZE (1..64))
            MAX-ACCESS read-create
            STATUS  current
            DESCRIPTION
                "The name of name-ip-Extern-acl group Interface."
            ::= { nameMacIpExternAcl 1 }
            
--xxx.100.10.1.4.5.2
--        nameMacIpExternSubitemNum OBJECT-TYPE
--            SYNTAX  INTEGER
--            MAX-ACCESS  not-accessible
--            STATUS  current
--            DESCRIPTION
--                " The number of name-ip-Extern-acl group's node."
--            ::= { nameMacIpExternAcl 2 }

--xxx.100.10.1.4.5.3
        nameMacIpExternAct OBJECT-TYPE
            SYNTAX  INTEGER 
             	    {
            	    	deny(0),
               		permit(1)
            	    }            
            MAX-ACCESS  read-create
            STATUS  current
            DESCRIPTION
                " The action of acl rule."
            ::= { nameMacIpExternAcl 3 }

--xxx.100.10.1.4.5.4
        nameMacIpExternSrcMacType OBJECT-TYPE
            SYNTAX  INTEGER
            	{
        		specified(0),
        		any(1),
        		host(2)   
        	}            
            MAX-ACCESS  read-create
            STATUS  current
            DESCRIPTION
                "The type of Source Mac address used by this ACE entry."
            ::= { nameMacIpExternAcl 4 }
            
--xxx.100.10.1.4.5.5
        nameMacIpExternSrcMac OBJECT-TYPE
            SYNTAX  MacAddress   (SIZE(17))          
            MAX-ACCESS  read-create
            STATUS  current
            DESCRIPTION
                " Source Mac-address of basic acl rule."
            ::= { nameMacIpExternAcl 5 }
            
--xxx.100.10.1.4.5.6
        nameMacIpExternSrcMacWild OBJECT-TYPE
            SYNTAX  MacAddress  (SIZE(17))          
            MAX-ACCESS  read-create
            STATUS  current
            DESCRIPTION
                " Source Mac-address wild  of basic acl rule."
            ::= { nameMacIpExternAcl 6 }

--xxx.100.10.1.4.5.7
        nameMacIpExternDestMacType OBJECT-TYPE
            SYNTAX  INTEGER
            	{
        		specified(0),
        		any(1),
        		host(2)   
        	}            
            MAX-ACCESS  read-create
            STATUS  current
            DESCRIPTION
                "The type of Destination Mac address used by this ACE entry."
            ::= { nameMacIpExternAcl 7 }
            
--xxx.100.10.1.4.5.8
        nameMacIpExternDestMac OBJECT-TYPE
            SYNTAX  MacAddress   (SIZE(17))          
            MAX-ACCESS  read-create
            STATUS  current
            DESCRIPTION
                " Destination Mac-address of basic acl rule."
            ::= { nameMacIpExternAcl 8 }
            
--xxx.100.10.1.4.5.9
        nameMacIpExternDestMacWild OBJECT-TYPE
            SYNTAX  MacAddress  (SIZE(17))          
            MAX-ACCESS  read-create
            STATUS  current
            DESCRIPTION
                " Destination Mac-address wild  of basic acl rule."
            ::= { nameMacIpExternAcl 9 }

--xxx.100.10.1.4.5.10
        nameMacIpExternSrcIpType OBJECT-TYPE
            SYNTAX  INTEGER
            	{
        		specified(0),
        		any(1),
        		host(2)   
        	}            
            MAX-ACCESS  read-create
            STATUS  current
            DESCRIPTION
                "The type of Source IP address used by this ACE entry."
            ::= { nameMacIpExternAcl 10 }
            
--xxx.100.10.1.4.5.11
        nameMacIpExternSrcIp OBJECT-TYPE
            SYNTAX  IpAddress            
            MAX-ACCESS  read-create
            STATUS  current
            DESCRIPTION
                " Source IP-address of basic acl rule."
            ::= { nameMacIpExternAcl 11 }
            
--xxx.100.10.1.4.5.12
        nameMacIpExternSrcIpWild OBJECT-TYPE
            SYNTAX  IpAddress           
            MAX-ACCESS  read-create
            STATUS  current
            DESCRIPTION
                " Source IP-address wild  of basic acl rule."
            ::= { nameMacIpExternAcl 12 }

--xxx.100.10.1.4.5.13
        nameMacIpExternDestIpType OBJECT-TYPE
            SYNTAX  INTEGER
            	{
            	        specified(0),
        		any(1),
        		host(2)
        	}            
            MAX-ACCESS  read-create
            STATUS  current
            DESCRIPTION
                "The type of Destination IP address used by this ACE entry."
            ::= { nameMacIpExternAcl 13 }
            
--xxx.100.10.1.4.5.14
        nameMacIpExternDestIp OBJECT-TYPE
            SYNTAX  IpAddress            
            MAX-ACCESS  read-create
            STATUS  current
            DESCRIPTION
                " Destination IP-address of basic acl rule."
            ::= { nameMacIpExternAcl 14 }
            
--xxx.100.10.1.4.5.15
        nameMacIpExternDestIpWild OBJECT-TYPE
            SYNTAX  IpAddress           
            MAX-ACCESS  read-create
            STATUS  current
            DESCRIPTION
                " Destination IP-address wild  of basic acl rule."
            ::= { nameMacIpExternAcl 15 }

--xxx.100.10.1.4.5.16
        nameMacIpExternPre OBJECT-TYPE
            SYNTAX  INTEGER(0..7)         
            MAX-ACCESS  read-create
            STATUS  current
            DESCRIPTION
                "Specifies the IP precedence value to be matched against.
        This object could not be configured when the status of the
        entry, caqIpAceStatus, is active(1)"
            ::= { nameMacIpExternAcl 16 }

--xxx.100.10.1.4.5.17
        nameMacIpExternTos OBJECT-TYPE
            SYNTAX  INTEGER(0..15)           
            MAX-ACCESS  read-create
            STATUS  current
            DESCRIPTION
                "The value of IP-packet's TOS. <0-15>            
                 Value of TOS(type of service) max-reliability    
                 Match packets with max reliable TOS(2) max-throughput     
                 Match packets with max throughput TOS(4) min-delay          
                 Match packets with min delay TOS(8) min-monetary-cost  
                 Match packets with min monetary cost TOS(1) normal             
                 Match packets with normal TOS(0)"
            ::= { nameMacIpExternAcl 17 }

--xxx.100.10.1.4.5.18
        nameMacIpExternTimeRange OBJECT-TYPE
            SYNTAX DisplayString(SIZE (1..64))           
            MAX-ACCESS  read-create
            STATUS  current
            DESCRIPTION
                "The Time-range of advanced acl rule."
            ::= { nameMacIpExternAcl 18 }

--xxx.100.10.1.4.5.19
        nameMacIpExternProtocol OBJECT-TYPE
            SYNTAX INTEGER(0..255)           
            MAX-ACCESS  read-create
            STATUS  current
            DESCRIPTION
                "The protocol number field in the IP header used to indicate
        the higher layer protocol as specified in RFC 1700. A value 
        value of 0 matches every IP packet. 
        
        For example :
        0 is IP, 1 is ICMP, 2 is IGMP, 4 is IP in IP encapsulation,
        6 is TCP, 9 is IGRP, 17 is UDP, 47 is GRE, 50 is ESP, 51 is AH,
        88 is EIGRP, 89 is OSPF, 94 is KA9Q/NOS compatible IP over IP,
        103 is PIMv2, 108 is PCP."
            ::= { nameMacIpExternAcl 19 }

--xxx.100.10.1.4.5.20
        nameMacIpExternSrcOP OBJECT-TYPE
            SYNTAX INTEGER{
        	noOperator(0),
        	lt(1),
        	gt(2),
        	eq(3),
        	neq(4),
        	range(5)
        	}           
            MAX-ACCESS  read-create
            STATUS  current
            DESCRIPTION
                "Indicates how a packet's source TCP/UDP port number is
        to be compared.
        
        If the nameMacIpExternProtocol object in the same row does not
        indicate TCP or UDP, this object has to be 'noOperator(0)' and
        cannot be changed while this row is active, i.e., the value of
        nameMacIpExternStatus in the same row has the value 'active(1)'.
        
        'noOperator(0)', which is the default value, means that no
        comparison is to be made with the source TCP/UDP port number.
        
        lt(1) means less than, gt(2) means greater than, eq(3)
        means equal, neq(4) means not equal. Those 4 operators
        are using the nameMacIpExternSrcPort object as an operand which
        is the only one needed. 
        
        range(5) means that it compares the port value between two 
        numbers, so this operator needs 2 operands. One operand is 
        the starting port number of the range which is nameMacIpExternSrcPort 
        object, and the other operand is the ending port number of the 
        range which the nameMacIpExternSrcPortRange object is in.
        
        Now support(3)eq,(5)range."
            ::= { nameMacIpExternAcl 20 }

--xxx.100.10.1.4.5.21
        nameMacIpExternSrcPort OBJECT-TYPE
            SYNTAX INTEGER(0..65535)          
            MAX-ACCESS  read-create
            STATUS  current
            DESCRIPTION
                "The source port number of the TCP or UDP protocol. If the
        nameMacIpExternSrcOP object in the same row is range(5), this
        object will be the starting port number of the port range.
        This object cannot be configured if nameMacIpExternStatus in the 
        same row is active(1) or nameMacIpExternSrcOP in the same row
        is noOperator(0)."
            ::= { nameMacIpExternAcl 21 }

--xxx.100.10.1.4.5.22         
	nameMacIpExternSrcPortRange OBJECT-TYPE
    	   SYNTAX INTEGER(0..65535)
    	   MAX-ACCESS read-create
    	   STATUS current
    	   DESCRIPTION
        	"The source port number of the TCP or UDP protocol. If the
        nameMacIpExternSrcOP object in the same row is range(5), this
        object will be the ending port number of the port range.
        This object cannot be configured if nameMacIpExternStatus in the 
        same row is active(1) or nameMacIpExternSrcOP in the same row
        is not range(5)."
    ::= { nameMacIpExternAcl 22 }            

--xxx.100.10.1.4.5.23
        nameMacIpExternDestOP OBJECT-TYPE
            SYNTAX INTEGER{
        	noOperator(0),
        	lt(1),
        	gt(2),
        	eq(3),
        	neq(4),
        	range(5)
        	}           
            MAX-ACCESS  read-create
            STATUS  current
            DESCRIPTION
                "Indicates how a packet's Destination TCP/UDP port number is
        to be compared.
        
        If the nameMacIpExternProtocol object in the same row does not
        indicate TCP or UDP, this object has to be 'noOperator(0)' and
        cannot be changed while this row is active, i.e., the value of
        nameMacIpExternStatus in the same row has the value 'active(1)'.
        
        'noOperator(0)', which is the default value, means that no
        comparison is to be made with the source TCP/UDP port number.
        
        lt(1) means less than, gt(2) means greater than, eq(3)
        means equal, neq(4) means not equal. Those 4 operators
        are using the nameMacIpExternDestPort object as an operand which
        is the only one needed. 
        
        range(5) means that it compares the port value between two 
        numbers, so this operator needs 2 operands. One operand is 
        the starting port number of the range which is nameIpExternSrcPort 
        object, and the other operand is the ending port number of the 
        range which the nameMacIpExternDestPortRange object is in.
        
        Now support(3)eq,(5)range."
            ::= { nameMacIpExternAcl 23 }

--xxx.100.10.1.4.5.24
        nameMacIpExternDestPort OBJECT-TYPE
            SYNTAX INTEGER(0..65535)          
            MAX-ACCESS  read-create
            STATUS  current
            DESCRIPTION
                "The source port number of the TCP or UDP protocol. If the
        nameMacIpExternDestOP object in the same row is range(5), this
        object will be the starting port number of the port range.
        This object cannot be configured if nameMacIpExternStatus in the 
        same row is active(1) or nameMacIpExternDestOP in the same row
        is noOperator(0)."
            ::= { nameMacIpExternAcl 24 }

--xxx.100.10.1.4.5.25          
	nameMacIpExternDestPortRange OBJECT-TYPE
    	   SYNTAX INTEGER(0..65535)
    	   MAX-ACCESS read-create
    	   STATUS current
    	   DESCRIPTION
        	"The source port number of the TCP or UDP protocol. If the
        nameMacIpExternDestOP object in the same row is range(5), this
        object will be the ending port number of the port range.
        This object cannot be configured if nameMacIpExternStatus in the 
        same row is active(1) or nameMacIpExternDestOP in the same row
        is not range(5)."
    ::= { nameMacIpExternAcl 25 }
     
--xxx.100.10.1.4.5.26 
nameMacIpExternIcmpType OBJECT-TYPE
    SYNTAX INTEGER(0..255)
    MAX-ACCESS read-create
    STATUS current
    DESCRIPTION
        "Indicates the message type of ICMP packets. The type is
        a nameber from 0 to 255."
    DEFVAL { 0 }
    ::= { nameMacIpExternAcl 26 }
    
--xxx.100.10.1.4.5.27 
nameMacIpExternIcmpCode OBJECT-TYPE
    SYNTAX INTEGER(0..255)
    MAX-ACCESS read-create
    STATUS current
    DESCRIPTION
        "Indicates the message code of ICMP packets. The code is
        a number from 0 to 255."
    DEFVAL { 0 }
    ::= { nameMacIpExternAcl 27 }
    
--xxx.100.10.1.4.5.28
nameMacIpExternIgmpType OBJECT-TYPE
    SYNTAX INTEGER(0..15)
    MAX-ACCESS read-create
    STATUS current
    DESCRIPTION
        "Indicates the message type of IGMP packets. The code is
        a number from 0 to 15."
    DEFVAL { 0 }
    ::= { nameMacIpExternAcl 28 }

--xxx.100.10.1.4.5.29
        nameMacIpExternTcpType OBJECT-TYPE
            SYNTAX  INTEGER
            	    {
            	    	mo(0),
               		fin(1),
            	    	syn(2),
               		rst(4),
            	    	psh(8),
               		ack(16),
               		urg(32)   
            	    }
            MAX-ACCESS  read-create
            STATUS  current
            DESCRIPTION
                " Tcp type."
            ::= { nameMacIpExternAcl 29 } 
            
--xxx.100.10.1.4.5.30
        nameMacIpExternStatus OBJECT-TYPE
            SYNTAX  INTEGER
            	    {
            	    	createAndGo(0),
               		active(1),
               		destroy(2)
            	    }
            MAX-ACCESS  read-create
            STATUS  current
            DESCRIPTION
                " now state of the access-list."
            ::= { nameMacIpExternAcl 30 } 

--******************************************************************************************************** 

--xxx.100.10.1.2.2
showAclTable OBJECT-TYPE
    SYNTAX  SEQUENCE OF ShowAclEntry
    MAX-ACCESS  not-accessible
    STATUS  current
            DESCRIPTION
                "ACL show list"
            ::= { acl 5 } 

--xxx.100.10.1.51
    showAclEntry OBJECT-TYPE
        SYNTAX  ShowAclEntry
        MAX-ACCESS  not-accessible
        STATUS  current
        DESCRIPTION
            "ACL show"
        INDEX   { aclName , aclRuleNum }
        ::= { showAclTable 1 }

    ShowAclEntry
        ::= SEQUENCE
            {
                aclName                 DisplayString,
                aclRuleNum		INTEGER,
                aclConfig               DisplayString
            }

--xxx.100.10.1.5.1.1
        aclName OBJECT-TYPE
            SYNTAX  DisplayString  (SIZE (1..64))
            MAX-ACCESS  not-accessible
            STATUS  current
            DESCRIPTION
                "ACL group name"
            ::= { showAclEntry 1 }
            
--xxx.100.10.1.5.1.2
        aclRuleNum OBJECT-TYPE
            SYNTAX  INTEGER
            MAX-ACCESS  not-accessible
            STATUS  current
            DESCRIPTION
                "the index of rule in the special access group"
            ::= { showAclEntry 2 }
            
--xxx.100.10.1.5.1.3
        aclConfig OBJECT-TYPE
            SYNTAX  DisplayString
            MAX-ACCESS  read-only
            STATUS  current
            DESCRIPTION
                "ACL configure status"
            ::= { showAclEntry 3 }    
                
--********************************************************************************************************
--******************************************************************************************************** 
--xxx.100.10.2
    sshMgt         	    OBJECT IDENTIFIER ::= { prisecurity 2 } 
    
--******************************************************************************************************** 

sshServerStatus OBJECT-TYPE
        SYNTAX      INTEGER
                    {
               		enable(1),
               		disable(0)
            	    }
        MAX-ACCESS  read-write
        STATUS      current
        DESCRIPTION "The status of Secure Shell Server, set this value
                     to 1 to enable SSH server, set this value to 0 to 
                     disable the SSH server."
        ::= { sshMgt 1 }

sshServerVersion  OBJECT-TYPE
        SYNTAX      INTEGER
        MAX-ACCESS  read-only
        STATUS      current
        DESCRIPTION "The version of the SSH Server."
        ::= { sshMgt 2 }
 
sshTimeout OBJECT-TYPE
        SYNTAX      INTEGER(10..600)
        MAX-ACCESS  read-write
        STATUS      current
        DESCRIPTION "The time interval that the router waits for the SSH 
                     client to respond. The range is 10-600."
        ::= { sshMgt 3 }

sshAuthRetries OBJECT-TYPE
        SYNTAX      INTEGER(1..10)
        MAX-ACCESS  read-write
        STATUS      current
        DESCRIPTION "The number of attempts after which the interface is reset.
                     The range is 1-10."
        ::= { sshMgt 4 }
        
--********************************************************************************************************
 
sshUseTable OBJECT-TYPE
        SYNTAX      SEQUENCE OF SshUseEntry
        MAX-ACCESS  not-accessible
        STATUS      current
        DESCRIPTION "The table for Secure Shell Connection."
        ::= { sshMgt 5 }

sshUseEntry OBJECT-TYPE
        SYNTAX      SshUseEntry
        MAX-ACCESS  not-accessible
        STATUS      current
        DESCRIPTION "The conceptual row for sshConnInfoTable."
        INDEX       { sshUserIndex }
        ::= { sshUseTable 1 }

SshUseEntry ::= SEQUENCE
{
   sshUserIndex		   INTEGER,
   sshUserName             DisplayString,   
   sshUserType   	   INTEGER,
   sshUserPassword         DisplayString,  
   sshUserStatus   	   INTEGER 
}

sshUserIndex OBJECT-TYPE
        SYNTAX      INTEGER
        MAX-ACCESS  not-accessible
        STATUS      current
        DESCRIPTION ""
        ::= { sshUseEntry 1 }
        
sshUserName OBJECT-TYPE
        SYNTAX      DisplayString(SIZE(1..16))
        MAX-ACCESS  read-write
        STATUS      current
        DESCRIPTION ""
        ::= { sshUseEntry 2 }
        
sshUserType OBJECT-TYPE
        SYNTAX      INTEGER
        	{
            	    	noCryptograph(0),
               		cryptograph(7)      	
        	}
        MAX-ACCESS  read-write
        STATUS      current
        DESCRIPTION ""
        ::= { sshUseEntry 3 }        
        
sshUserPassword OBJECT-TYPE
        SYNTAX      DisplayString(SIZE(1..32))
        MAX-ACCESS  read-write
        STATUS      current
        DESCRIPTION ""
        ::= { sshUseEntry 4 }
        
sshUserStatus OBJECT-TYPE
        SYNTAX      INTEGER
        	{
            	    	createAndGo(0),
               		active(1),
               		destroy(2)    	
        	}
        MAX-ACCESS  read-write
        STATUS      current
        DESCRIPTION ""
        ::= { sshUseEntry 5 }          
          
--******************************************************************************************************** 

sshConnInfoTable OBJECT-TYPE
        SYNTAX      SEQUENCE OF SshConnInfoEntry
        MAX-ACCESS  not-accessible
        STATUS      current
        DESCRIPTION "The table for Secure Shell Connection."
        ::= { sshMgt 6 }

sshConnInfoEntry OBJECT-TYPE
        SYNTAX      SshConnInfoEntry
        MAX-ACCESS  not-accessible
        STATUS      current
        DESCRIPTION "The conceptual row for sshConnInfoTable."
        INDEX       { sshConnID }
        ::= { sshConnInfoTable 1 }

SshConnInfoEntry ::= SEQUENCE
{
   sshConnID             INTEGER,
   sshConnVersion   	 INTEGER,
   sshConnStatus         INTEGER,   
   sshConnUserName       DisplayString 
}

sshConnID OBJECT-TYPE
        SYNTAX      INTEGER
        MAX-ACCESS  read-only
        STATUS      current
        DESCRIPTION "The connection ID of the Secure Shell Connection."
        ::= { sshConnInfoEntry 1 }

sshConnVersion OBJECT-TYPE
        SYNTAX      INTEGER
        MAX-ACCESS  read-only
        STATUS      current
        DESCRIPTION "The SSH version."
        ::= { sshConnInfoEntry 2 }

sshConnStatus OBJECT-TYPE
        SYNTAX      INTEGER
                    {
                      negotiationStart(1),
                      authenticationStart(2),
                      sessionStart(3)
                    } 
        MAX-ACCESS  read-only
        STATUS      current
        DESCRIPTION "The SSH connection State. negotiationStart(1) mean the
                     SSH is in its negotiation start state, authenticationStart(2)
                     mean the SSH is in authentication start state, sessionStart(3)
                     mean the SSH is in session start State."
        ::= { sshConnInfoEntry 3 }
        
sshConnUserName OBJECT-TYPE
        SYNTAX      DisplayString
        MAX-ACCESS  read-only
        STATUS      current
        DESCRIPTION "User Name."
        ::= { sshConnInfoEntry 4 }        
        
        
        
--********************************************************************************************************
--********************************************************************************************************  
-- Management for Terminal Access Controller Access Control System plus (TACACS+).

--xxx.100.10.3
    tacacsMgt         	    OBJECT IDENTIFIER ::= { prisecurity 3 } 
    
--********************************************************************************************************         

tacacsServerHostTable OBJECT-TYPE
        SYNTAX      SEQUENCE OF TacacsServerHostEntry
        MAX-ACCESS  not-accessible
        STATUS      current
        DESCRIPTION "IP address of TACACS server."
        ::= { tacacsMgt 1 }

tacacsServerHostEntry OBJECT-TYPE
        SYNTAX  TacacsServerHostEntry
        MAX-ACCESS  not-accessible
        STATUS  current
        DESCRIPTION
            ""
        INDEX   { tacacsServerHostIndex }
        ::= { tacacsServerHostTable 1 } 

    TacacsServerHostEntry
        ::= SEQUENCE
            {
            	tacacsServerHostIndex		INTEGER,
                tacacsServerHostIP		IpAddress,
                tacacsServerHostPort		INTEGER,	                
                tacacsServerHostPrimary		INTEGER,
                tacacsServerHostStatus		INTEGER,  
                tacacsServerHostKey		DisplayString,
                tacacsServerHostTimeout		INTEGER                    
            }
            
tacacsServerHostIndex OBJECT-TYPE
        SYNTAX      INTEGER
        MAX-ACCESS  not-accessible
        STATUS      current
        DESCRIPTION "IP address of TACACS server."
        ::= { tacacsServerHostEntry 1 }

tacacsServerHostIP OBJECT-TYPE
        SYNTAX      IpAddress
        MAX-ACCESS  read-write
        STATUS      current
        DESCRIPTION "IP address of TACACS server."
        ::= { tacacsServerHostEntry 2 }
        
tacacsServerHostPort OBJECT-TYPE
        SYNTAX      INTEGER(0..65535)
        MAX-ACCESS  read-write
        STATUS      current
        DESCRIPTION "Port of TACACS server."
        ::= { tacacsServerHostEntry 3 }        
        
tacacsServerHostPrimary OBJECT-TYPE
        SYNTAX      INTEGER
                    {
            	    	noPrimary(0),
               		primary(1)
                    }          
        MAX-ACCESS  read-write
        STATUS      current
        DESCRIPTION ""
        ::= { tacacsServerHostEntry 4 }          

tacacsServerHostStatus OBJECT-TYPE
        SYNTAX      INTEGER
                    {
            	    	createAndGo(0),
               		active(1),
               		destroy(2)
                    }  
        MAX-ACCESS  read-write
        STATUS      current
        DESCRIPTION ""
        ::= { tacacsServerHostEntry 5 }
        
tacacsServerHostKey OBJECT-TYPE
        SYNTAX      DisplayString (SIZE(1..16))
        MAX-ACCESS  read-write
        STATUS      current
        DESCRIPTION "Key for TACACS."
        ::= { tacacsServerHostEntry 6 }          
        
tacacsServerHostTimeout OBJECT-TYPE
        SYNTAX      INTEGER (1..60)
        MAX-ACCESS  read-write
        STATUS      current
        DESCRIPTION "The time before retransmit of the TACACS server."
        ::= { tacacsServerHostEntry 7 }          
         
--********************************************************************************************************

tacacsServerTimeout OBJECT-TYPE
        SYNTAX      INTEGER (1..60)
        MAX-ACCESS  read-write
        STATUS      current
        DESCRIPTION "The time before retransmit of the TACACS server."
        ::= { tacacsMgt 2 }

tacacsServerKey OBJECT-TYPE
        SYNTAX      DisplayString (SIZE(1..16))
        MAX-ACCESS  read-write
        STATUS      current
        DESCRIPTION "Key for TACACS."
        ::= { tacacsMgt 3 }
        
--********************************************************************************************************
--********************************************************************************************************  

--xxx.100.10.4
    am         	    OBJECT IDENTIFIER ::= { prisecurity 4 } 
    
--********************************************************************************************************         

amGlobalEnable OBJECT-TYPE
        SYNTAX  INTEGER {
                enable (1),
                disable (2)
            }
        MAX-ACCESS  read-write
        STATUS      current
        DESCRIPTION " Global Enable or disable the Access Management."
        ::= { am 1 }

--********************************************************************************************************
      
amPortInfoTable OBJECT-TYPE
        SYNTAX      SEQUENCE OF AmPortInfoEntry
        MAX-ACCESS  not-accessible
        STATUS      current
        DESCRIPTION "Access Management information list of port."
        ::= { am 2 }

amPortInfoEntry OBJECT-TYPE
        SYNTAX  AmPortInfoEntry
        MAX-ACCESS  not-accessible
        STATUS  current
        DESCRIPTION
            ""
        INDEX   { amPortIndex,amPortIp }
        ::= { amPortInfoTable 1 } 

    AmPortInfoEntry
        ::= SEQUENCE
            {
                amPortIndex               		        INTEGER,
                amPortEnable				        INTEGER,
                amPortForwardingType				INTEGER,
                amPortIp					IpAddress,
                amPortMac				        MacAddress,
                amPortCount					INTEGER,
                amPortStatus				        INTEGER        
            }
            
amPortIndex OBJECT-TYPE
        SYNTAX      INTEGER
        MAX-ACCESS  not-accessible
        STATUS      current
        DESCRIPTION "port index"
        ::= { amPortInfoEntry 1 }       
        
amPortEnable OBJECT-TYPE
        SYNTAX  INTEGER {
                enable (1),
                disable (2)
            }
        MAX-ACCESS  read-write
        STATUS      current
        DESCRIPTION "Enable or disable the Access Management on the port."
        ::= { amPortInfoEntry 2 }
                
amPortForwardingType OBJECT-TYPE
        SYNTAX  INTEGER{
			ip-pool(1),
			mac-ip-pool(2)
            }   
        MAX-ACCESS  read-write
        STATUS      current
        DESCRIPTION "Access Management forwarding type."
        ::= { amPortInfoEntry 3 }
 
amPortIp OBJECT-TYPE
        SYNTAX      IpAddress
        MAX-ACCESS  read-only
        STATUS      current
        DESCRIPTION "IP address of Access Management."
        ::= { amPortInfoEntry 4 } 
        
amPortMac OBJECT-TYPE
        SYNTAX      MacAddress  (SIZE(17))       
        MAX-ACCESS  read-write
        STATUS      current
        DESCRIPTION "Mac address of Access Management."
        ::= { amPortInfoEntry 5 }          

amPortCount OBJECT-TYPE
        SYNTAX      INTEGER(1..32)
        MAX-ACCESS  read-write
        STATUS      current
        DESCRIPTION "Seriate IP address number."
        ::= { amPortInfoEntry 6 }  

amPortStatus OBJECT-TYPE
        SYNTAX      INTEGER
                    {
            	    	createAndGo(0),
               		active(1),
               		destroy(2)
                    }  
        MAX-ACCESS  read-write
        STATUS      current
        DESCRIPTION ""
        ::= { amPortInfoEntry 7 }  
         
--********************************************************************************************************
--********************************************************************************************************

--xxx.100.10.5
    radiusMgt         	    OBJECT IDENTIFIER ::= { prisecurity 5 } 
    
--********************************************************************************************************         

aaaEnabled          OBJECT-TYPE
        SYNTAX      INTEGER 
                     {
            	    	enable(1),
               		  disable(0)
                    }        
        MAX-ACCESS  read-write
        STATUS      current
        DESCRIPTION "Enable or disable Aaa function."
        ::= { radiusMgt  1 }
        
aaaAccount          OBJECT-TYPE
        SYNTAX      INTEGER 
                     {
            	    	enable(1),
               		  disable(0)
                    }        
        MAX-ACCESS  read-write
        STATUS      current
        DESCRIPTION "Enable or disable Aaa Accounting function."
        ::= { radiusMgt  2 }        
        
aaaAccountUpdate    OBJECT-TYPE
        SYNTAX      INTEGER 
                     {
            	    	enable(1),
               		  disable(0)
                    }        
        MAX-ACCESS  read-write
        STATUS      current
        DESCRIPTION "Enable or disable Aaa Accounting update function."
        ::= { radiusMgt  3 }  
        
aaaAccountBindingDHCP    OBJECT-TYPE
        SYNTAX      INTEGER 
                     {
            	    	enable(1),
               		  disable(0)
                    }        
        MAX-ACCESS  read-write
        STATUS      current
        DESCRIPTION "Enable or disable Aaa Accounting DHCP-Binding function."
        ::= { radiusMgt  4 }   
          
--********************************************************************************************************   
       
radiusAuthenServerHostTable OBJECT-TYPE
        SYNTAX      SEQUENCE OF RadiusAuthenServerHostEntry
        MAX-ACCESS  not-accessible
        STATUS      current
        DESCRIPTION "Configuration items and information list of RADIUS authentication server host."
        ::= { radiusMgt  5 }

radiusAuthenServerHostEntry OBJECT-TYPE
        SYNTAX  RadiusAuthenServerHostEntry
        MAX-ACCESS  not-accessible
        STATUS  current
        DESCRIPTION  ""
        INDEX   { radiusAuthenServerHostIndex }
        ::= { radiusAuthenServerHostTable 1 } 

       RadiusAuthenServerHostEntry
        ::= SEQUENCE
            {
            	  radiusAuthenServerHostIndex		INTEGER,
                radiusAuthenServerHostIP		IpAddress,
                radiusAuthenServerHostPort		INTEGER,	                
                radiusAuthenServerHostPrimary	INTEGER,
                radiusAuthenServerHostStatus		INTEGER          
            }
            
radiusAuthenServerHostIndex OBJECT-TYPE
        SYNTAX      INTEGER
        MAX-ACCESS  not-accessible
        STATUS      current
        DESCRIPTION "Index of RADIUS authentication server."
        ::= { radiusAuthenServerHostEntry 1 }      
        
radiusAuthenServerHostIP OBJECT-TYPE
        SYNTAX      IpAddress
        MAX-ACCESS  read-write
        STATUS      current
        DESCRIPTION "IP address of RADIUS authentication server."
        ::= { radiusAuthenServerHostEntry 2 }
        
radiusAuthenServerHostPort OBJECT-TYPE
        SYNTAX      INTEGER(0..65535)
        MAX-ACCESS  read-write
        STATUS      current
        DESCRIPTION "Port of RADIUS authentication server."
        ::= { radiusAuthenServerHostEntry 3 }        
        
radiusAuthenServerHostPrimary OBJECT-TYPE
        SYNTAX      INTEGER
                    {
            	    	noPrimary(0),
               		  primary(1)
                    }          
        MAX-ACCESS  read-write
        STATUS      current
        DESCRIPTION "Configuration of primary or not primary "
        ::= { radiusAuthenServerHostEntry 4 }          

radiusAuthenServerHostStatus OBJECT-TYPE
        SYNTAX      INTEGER
                    {            	    
               		active(1),
               		destroy(2)
                    }  
        MAX-ACCESS  read-write
        STATUS      current
        DESCRIPTION "Setting it to  active(1) to creates an entry,setting it to destroy(2) to destroy an entry."
        ::= { radiusAuthenServerHostEntry 5 }   
        
--********************************************************************************************************  
        
radiusAcctServerHostTable OBJECT-TYPE
        SYNTAX      SEQUENCE OF RadiusAcctServerHostEntry
        MAX-ACCESS  not-accessible
        STATUS      current
        DESCRIPTION "Configuration items and information list of RADIUS accounting server host."
        ::= { radiusMgt  6 }

radiusAcctServerHostEntry OBJECT-TYPE
        SYNTAX RadiusAcctServerHostEntry
        MAX-ACCESS  not-accessible
        STATUS  current
        DESCRIPTION  ""
        INDEX   { radiusAcctServerHostIndex }
        ::= { radiusAcctServerHostTable 1 } 

      RadiusAcctServerHostEntry
        ::= SEQUENCE
            {
            	  radiusAcctServerHostIndex		INTEGER,
                radiusAcctServerHostIP		IpAddress,
                radiusAcctServerHostPort		INTEGER,	                
                radiusAcctServerHostPrimary	INTEGER,
                radiusAcctServerHostStatus		INTEGER          
            }
            
radiusAcctServerHostIndex  OBJECT-TYPE
        SYNTAX      INTEGER
        MAX-ACCESS  not-accessible
        STATUS      current
        DESCRIPTION "Index of RADIUS accounting server."
        ::= { radiusAcctServerHostEntry 1 }      
        
radiusAcctServerHostIP OBJECT-TYPE
        SYNTAX      IpAddress
        MAX-ACCESS  read-write
        STATUS      current
        DESCRIPTION "IP address of RADIUS accounting server."
        ::= { radiusAcctServerHostEntry 2 }
        
radiusAcctServerHostPort OBJECT-TYPE
        SYNTAX      INTEGER(0..65535)
        MAX-ACCESS  read-write
        STATUS      current
        DESCRIPTION "Port of RADIUS accounting server."
        ::= { radiusAcctServerHostEntry 3 }        
        
radiusAcctServerHostPrimary	 OBJECT-TYPE
        SYNTAX      INTEGER
                    {
            	    	noPrimary(0),
               		  primary(1)
                    }          
        MAX-ACCESS  read-write
        STATUS      current
        DESCRIPTION "Configuration of primary or not primary "
        ::= { radiusAcctServerHostEntry 4 }          

radiusAcctServerHostStatus OBJECT-TYPE
        SYNTAX      INTEGER
                    {            	    
               		active(1),
               		destroy(2)
                    }  
        MAX-ACCESS  read-write
        STATUS      current
        DESCRIPTION "Setting it to  active(1) to creates an entry,setting it to destroy(2) to destroy an entry."
        ::= { radiusAcctServerHostEntry 5 }       
                                  
--********************************************************************************************************  
radiusServerTimeout OBJECT-TYPE
        SYNTAX      INTEGER (1..1000)
        MAX-ACCESS  read-write
        STATUS      current
        DESCRIPTION "The time before retransmit of the RADIUS server."
        ::= { radiusMgt  7 }
        
radiusServerRetransmit OBJECT-TYPE
        SYNTAX      INTEGER (0..100)
        MAX-ACCESS  read-write
        STATUS      current
        DESCRIPTION "Retransmit time before giving up the current RADIUS server."
        ::= { radiusMgt  8 }
        
radiusServerDeadTime    OBJECT-TYPE
        SYNTAX      INTEGER (1..255)
        MAX-ACCESS  read-write
        STATUS      current
        DESCRIPTION "The time before retry of the down-server."
        ::= { radiusMgt  9 }
         
radiusServerKey OBJECT-TYPE
        SYNTAX      DisplayString (SIZE(1..16))
        MAX-ACCESS  read-write
        STATUS      current
        DESCRIPTION "Key for RADIUS."
        ::= { radiusMgt  10 }
    
radiusServerAccountTimeOut   OBJECT-TYPE
        SYNTAX      INTEGER (60..3600)
        MAX-ACCESS  read-write
        STATUS      current
        DESCRIPTION "Accounting update interval."
        ::= { radiusMgt  11 } 
--********************************************************************************************************
-- (xxx.100.11)   priQos group               

--xxx.100.11.1
    qos         	    OBJECT IDENTIFIER ::= { priQos 1 } 

--******************************************************************************************************** 
    
--xxx.100.11.1.1
qosEnable OBJECT-TYPE
    SYNTAX  INTEGER{
                disable(0),
                enable(1)
            }
            MAX-ACCESS  read-write
            STATUS  current
            DESCRIPTION
                "qos golbal switch.disable express close,enable is open."
            ::= { qos 1 } 
            
--********************************************************************************************************

--xxx.100.11.1.2
qosPortTable OBJECT-TYPE
    SYNTAX  SEQUENCE OF QosPortEntry
    MAX-ACCESS  not-accessible
    STATUS  current
            DESCRIPTION
                "qos port configration."
            ::= { qos 2 } 

--xxx.100.11.1.2.1
    qosPortEntry OBJECT-TYPE
        SYNTAX  QosPortEntry
        MAX-ACCESS  not-accessible
        STATUS  current
        DESCRIPTION
            " qos port list of concrete definition.index is port index"
        INDEX   { qosPortIndex }
        ::= { qosPortTable 1 } 

    QosPortEntry
        ::= SEQUENCE
            {
                qosPortIndex			INTEGER,
                qosPortType			INTEGER,	                
                qosPortCos			INTEGER,
		qosPortTrust			INTEGER,
		qosPortPriority			INTEGER,
		qosPortMutation			DisplayString,
		qosPortQueue			INTEGER,
                qosPortStatus		       	INTEGER          
            }

--xxx.100.11.1.2.1.1
qosPortIndex OBJECT-TYPE
    SYNTAX  INTEGER
            MAX-ACCESS  not-accessible
            STATUS  current
            DESCRIPTION
                "port Index"
            ::= { qosPortEntry 1 } 

--xxx.100.11.1.2.1.2
qosPortType OBJECT-TYPE
    SYNTAX  INTEGER
                {
            		  cos(1),
            	    trust(0),
               		dscpMutation(2),
               		priorityQueueOut(3)	
            	}
            MAX-ACCESS  read-create
            STATUS  current
            DESCRIPTION
                "the relation between qosPortType and CLI:
                1 mls qos cos {<default-cos> };     
		0 mls qos trust {cos [pass-through-cos] [pass-through-dscp]|dscp [pass-through-cos] [pass-through-dscp]| ip-precedence [pass-through-cos] [pass-through-dscp] |port priority <cos> [pass-through-cos] [pass-through-dscp]} ;
		2 mls qos dscp-mutation <dscp-mutation-name>;
		3 priority-queue out.
		According to the relation,when configurate qos with snmp,first set the qosPortType to the correct value to select CLI,
		then set next CLI parameter.Fox example,set qos default cos is 5, first set qosPortType=1 ,then set qosPortCos to 5,
		finally setting qosPortStatus to 1, trigger snmp-cache works."
            ::= { qosPortEntry 2 } 
                               
--xxx.100.11.1.2.1.3
qosPortCos OBJECT-TYPE
    SYNTAX  INTEGER(0..7)
            MAX-ACCESS  read-create
            STATUS  current
            DESCRIPTION
                "port default cos value"
            ::= { qosPortEntry 3 } 

--xxx.100.11.1.2.1.4
qosPortTrust OBJECT-TYPE
    SYNTAX  INTEGER
            	{
            		  priority(0),
            	    priAndPassThroughDscp(1),
            	    priAndPassThroughCos(2),
               		priAndPassThroughCosAndPassThroughDscp(3),
               		cos(4),
               		cosAndPassThroughDscp(5),
               		cosAndPassThroughCos(6),
               		cosAndPassThroughCosAndPassThroughDscp(7),
               		dscp(8),
               		dscpAndPassThroughCos(9),
               		dscpAndPassThroughDscp(10),
               		dscpAndPassThroughDscpAndPassThroughCos(11),
               		ipPrecedence(12),
               		ipPreAndPassThroughCos(13),
               		ipPreAndPassThroughDSCP(14),
               		ipPreAndPassThroughDSCPAndPassThroughCos(15),
               		mplsEXP(16)
            	}
            MAX-ACCESS  read-create
            STATUS  current
            DESCRIPTION
                "Configure port trust.
                  priority(0),mls qos trust port priority <cos>;
                  priAndPassThroughDscp(1),opposite cli is mls qos trust port priority <cos> pass-through-dscp;
                  priAndPassThroughCos(2),opposite cli is mls qos trust port priority <cos> pass-through-cos;
                  priAndPassThroughCosAndPassThroughDscp(3),opposite cli is mls qos trust port priority <cos> pass-through-cos pass-through-dscp;
            	    cos(4),mls qos trust cos;
               	  cosAndPassThroughDscp(5),opposite cli is mls qos trust cos pass-through-dscp;
               	  cosAndPassThroughCos(6),opposite cli is mls qos trust cos pass-through-cos;
               	  cosAndPassThroughCosAndPassThroughDscp(7),opposite cli is mls qos trust cos pass-through-cos pass-through-dscp;
               	  dscp(8),mls qos trust dscp;
               	  dscpAndPassThroughCos(9),opposite cli is mls qos trust dscp pass-through-cos;
               	  dscpAndPassThroughDscp(10),opposite cli is mls qos trust dscp pass-through-dscp;
               	  dscpAndPassThroughDscpAndPassThroughCos(11),opposite cli is mls qos trust dscp pass-through-dscp pass-through-cos;
               	  ipPrecedence(12), mls qos trust ip-precedence;
               	  ipPreAndPassThroughCos(13),opposite cli is mls qos trust ip-precedence pass-through-cos;
               	  ipPreAndPassThroughDSCP(14),opposite cli is mls qos trust ip-precedence pass-through-dscp;
               	  ipPreAndPassThroughDSCPAndPassThroughCos(15),opposite cli is mls qos trust ip-precedence pass-through-dscp pass-through-cos;
               	  mplsEXP(16),mls qos mpls trust exp."
            ::= { qosPortEntry 4 } 
            
--xxx.100.11.1.2.1.5
qosPortPriority OBJECT-TYPE
    SYNTAX  INTEGER (0..7)
            MAX-ACCESS  read-create
            STATUS  current
            DESCRIPTION
                "The corresponding CLI:mls qos trust port priority <cos>."
            ::= { qosPortEntry 5 }             

--xxx.100.11.1.2.1.6
qosPortMutation OBJECT-TYPE
    SYNTAX  DisplayString
            MAX-ACCESS  read-create
            STATUS  current
            DESCRIPTION
                "configure port of dscp-mutation,opposite cli 'mls qos dscp-mutation <dscp-mutation-name>'"
            ::= { qosPortEntry 6 }  

--xxx.100.11.1.2.1.7
        qosPortQueue OBJECT-TYPE
            SYNTAX  INTEGER
            	    {
            	    	priorityQueue(0),
               		wrrQueue(1)
            	    }
            MAX-ACCESS  read-create
            STATUS  current
            DESCRIPTION
                "priorityQueue configure queue out method to strict priority-queue method;
                 wrrQueue restores the default wrr queue out method."
            ::= { qosPortEntry 7 } 

--xxx.100.11.1.2.1.8
        qosPortStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qosPortEntry 8 } 

--******************************************************************************************************** 

--xxx.100.11.1.3
qosClassMapTable OBJECT-TYPE
    SYNTAX  SEQUENCE OF QosClassMapEntry
    MAX-ACCESS  not-accessible
    STATUS  current
            DESCRIPTION
                "classmap configure list"
            ::= { qos 3 } 

--xxx.100.11.1.3.1
    qosclassmapEntry OBJECT-TYPE
        SYNTAX  QosClassMapEntry
        MAX-ACCESS  not-accessible
        STATUS  current
        DESCRIPTION
            " about classmap list of concrete definition,index is classmapname."
        INDEX   { qosClassMapName }
        ::= { qosClassMapTable 1 }
        
    QosClassMapEntry
        ::= SEQUENCE
            {
                qosClassMapName			DisplayString,                
                qosClassMapType			INTEGER,
                qosClassMapAccessGroup       		DisplayString,
                qosClassMapDscp			DisplayString,
                qosClassMapV6Dscp			DisplayString,
                qosClassMapIpPre			DisplayString,
                qosClassMapV6AccGroup		DisplayString,
                qosClassMapV6Flow			DisplayString,
                qosClassMapVlan   			DisplayString,
                qosClassCos   			DisplayString,
                qosClassMapEXPtopmost      DisplayString,
                qosClassMapStatus		       	INTEGER          
            }

--xxx.100.11.1.3.1.1
        qosClassMapName OBJECT-TYPE
            SYNTAX  DisplayString (SIZE(1..32))
            MAX-ACCESS  not-accessible
            STATUS  current
            DESCRIPTION
                "classmap name"
            ::= { qosclassmapEntry 1}

--xxx.100.11.1.3.1.2
        qosClassMapType OBJECT-TYPE
            SYNTAX  INTEGER
            	{
            	    configurClassMap(0),
            	    accessGroup(1),
               		dscp(2),
               		v6dscp(5),
               		ippre(3),
               		v6AccessGroup(8),
               		v6Flow(7),
               		vlan(4), 
               		cos(9),
               		exptopmost(10)
            	}
            MAX-ACCESS  read-create
            STATUS  current
            DESCRIPTION
                "0 class-map <class-map-name>,index is classmapname;
		1 match access-group <acl-index-or-name>,need qosClassMapAccessGroup cooperation;
		2 match ip dscp <dscp-list>    qosClassMapDscp ;
		3 match ip precedence <ip-precedence-list>  qosClassMapIpPre;
		4 match vlan <vlan-list>     qosClassMapVlan;
		5 match ipv6 dscp <dscp-list>    qosClassMapV6Dscp;
		7 match ipv6 flowlabel      qosClassMapV6Flow;
		8 match ipv6 access-group     qosClassMapV6AccGroup
		9 match cos     qosClassCos
	  10 match mpls-experimental topmost    qosClassMapEXPtopmost"
            ::= { qosclassmapEntry  2 }

--xxx.100.11.1.3.1.3
        qosClassMapAccessGroup OBJECT-TYPE
            SYNTAX  DisplayString
            MAX-ACCESS  read-create
            STATUS  current
            DESCRIPTION
                "Match specify access-group (name or number). 
                This object be configured only if qosClassMapType  
                in the same row is accessGroup(1)."
            ::= { qosclassmapEntry  3 }
            
--xxx.100.11.1.3.1.4
        qosClassMapDscp OBJECT-TYPE
            SYNTAX  DisplayString
            MAX-ACCESS  read-create
            STATUS  current
            DESCRIPTION
                "Match specify Dscp.
                This object be configured only if qosClassMapType 
                in the same row is dscp(2)."
            ::= { qosclassmapEntry  4 }  
                      
--xxx.100.11.1.3.1.5
        qosClassMapV6Dscp OBJECT-TYPE
            SYNTAX  DisplayString
            MAX-ACCESS  read-create
            STATUS  current
            DESCRIPTION
                "Match specify ipv6 Dscp.
                This object be configured only if qosClassMapType 
                in the same row is v6dscp(5)."
            ::= { qosclassmapEntry  5 } 
            
--xxx.100.11.1.3.1.6
        qosClassMapIpPre OBJECT-TYPE
            SYNTAX  DisplayString
            MAX-ACCESS  read-create
            STATUS  current
            DESCRIPTION
                "Match specify Ip Precedence.
                This object be configured only if qosClassMapType 
                in the same row is ippre(3)."
            ::= { qosclassmapEntry  6 } 
            
--xxx.100.11.1.3.1.7
        qosClassMapV6AccGroup OBJECT-TYPE
            SYNTAX  DisplayString
            MAX-ACCESS  read-create
            STATUS  current
            DESCRIPTION
                "Match specify Ipv6 Access-Group.
                This object be configured only if qosClassMapType  
                in the same row is v6AccessGroup(8)."
            ::= { qosclassmapEntry  7 } 
            
--xxx.100.11.1.3.1.8
        qosClassMapV6Flow OBJECT-TYPE
            SYNTAX  DisplayString
            MAX-ACCESS  read-create
            STATUS  current
            DESCRIPTION
                "Match specify Ipv6 Flowlabel.
                This object be configured only if qosClassMapType  
                in the same row is v6Flow(6)."
            ::= { qosclassmapEntry  8 } 
            
--xxx.100.11.1.3.1.9
        qosClassMapVlan OBJECT-TYPE
            SYNTAX  DisplayString
            MAX-ACCESS  read-create
            STATUS  current
            DESCRIPTION
                "Match specify Vlan list . At most 8 vlan id.
                This object be configured only if qosClassMapType  
                in the same row is vlan(4)."
            ::= { qosclassmapEntry  9 } 
     
--xxx.100.11.1.3.1.10
        qosClassCos OBJECT-TYPE
            SYNTAX  DisplayString
            MAX-ACCESS  read-create
            STATUS  current
            DESCRIPTION
                "Match specify Cos .
                This object be configured only if qosClassMapType  
                in the same row is cos(9)."
            ::= { qosclassmapEntry 10 }

--xxx.100.11.1.3.1.11
	        qosClassMapEXPtopmost  OBJECT-TYPE
	            SYNTAX  DisplayString
	            MAX-ACCESS  read-create
	            STATUS  current
	            DESCRIPTION
	                "Match specify MPLS EXP.
	                This object be configured only if qosClassMapType  
	                in the same row is EXPtopmost(10)."
	            ::= { qosclassmapEntry 11 }  	        
               
--xxx.100.11.1.3.1.12
        qosClassMapStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qosclassmapEntry 12 }             
                                            
--********************************************************************************************************

--xxx.100.11.1.4
qosPolicyTable OBJECT-TYPE
    SYNTAX  SEQUENCE OF QosPolicyEntry
    MAX-ACCESS  not-accessible
    STATUS  current
            DESCRIPTION
                "qos policy list"
            ::= { qos 4 } 

--xxx.100.11.1.4.1
    qosPolicyEntry OBJECT-TYPE
        SYNTAX  QosPolicyEntry
        MAX-ACCESS  not-accessible
        STATUS  current
        DESCRIPTION
            " qos policy list of definition,index is qos policy and classmap of name"
        INDEX   { qosPolicyName}
        ::= { qosPolicyTable 1 }
        
    QosPolicyEntry
        ::= SEQUENCE
            {
                qosPolicyName				DisplayString,
                qosPolicyClassMap			DisplayString,
                qosPolicyType				INTEGER,
                qosPolicyRateKbps			INTEGER,
                qosPolicyNormalBurstKbps		INTEGER,
                qosPolicyMaximumBurstKbps 		INTEGER,
                qosPolicyPeakKbps			INTEGER, 
                qosPolicyConformAction		INTEGER,
                qosPolicyConformActionChangeValue	INTEGER,
                qosPolicyExceedAction 		INTEGER,
                qosPolicyViolateAction 		INTEGER, 
                qosPolicyAggregatePolicer		DisplayString,
                qosPolicyStatus				INTEGER                               
            }

--xxx.100.11.1.4.1.1
        qosPolicyName OBJECT-TYPE
            SYNTAX  DisplayString (SIZE(1..32))
            MAX-ACCESS  not-accessible
            STATUS  current
            DESCRIPTION
                "QoS Policy name"
            ::= { qosPolicyEntry 1 }

--xxx.100.11.1.4.1.2
        qosPolicyClassMap OBJECT-TYPE
            SYNTAX  DisplayString (SIZE(1..32))
            MAX-ACCESS  read-create
            STATUS  current
            DESCRIPTION
                "Specify the classmap name.After a policy map is created, it can be associated to a class.
                So, if you want the class map to match the policy map,please setting the qosPolicyType to 1,and then
                setting the qosPolicyStatus to 1 ."
            ::= { qosPolicyEntry 2 }

--xxx.100.11.1.4.1.3
        qosPolicyType OBJECT-TYPE
            SYNTAX  INTEGER            	
            	{
            	    	policymap(0),
            	    	matchclassmap(1),
            	    	sp(2),
               		aggregatePolicer(3)         	
            	}
            MAX-ACCESS  read-create
            STATUS  current
            DESCRIPTION
                "the relation between qosPolicyType and CLI:
		0  policy-map <policy-map-name>;
		1  class <class-map-name>;
		2  police <rate-kbps> <burst-kbyte> [exceed-action {drop | policed-dscp-transmit}];
		3  police aggregate <aggregate-policer-name>; "
            ::= { qosPolicyEntry 3 }
            
--xxx.100.11.1.4.1.4
        qosPolicyRateKbps OBJECT-TYPE
            SYNTAX  INTEGER(1..10000000)
            MAX-ACCESS  read-create
            STATUS  current
            DESCRIPTION
                "Rate Bandwidth of one policymap.
                This object be configured only if qosPolicyType 
                in the same row is sp(2). "
            ::= { qosPolicyEntry 4 }            

--xxx.100.11.1.4.1.5
        qosPolicyNormalBurstKbps OBJECT-TYPE
            SYNTAX  INTEGER(1..1000000)
            MAX-ACCESS  read-create
            STATUS  current
            DESCRIPTION
                "Normal burst kbytes."
            ::= { qosPolicyEntry 5 }
            
--xxx.100.11.1.4.1.6
        qosPolicyMaximumBurstKbps OBJECT-TYPE
            SYNTAX  INTEGER(1..1000000)
            MAX-ACCESS  read-create
            STATUS  current
            DESCRIPTION
                "Maximum burst kbytes."
            ::= { qosPolicyEntry 6 }
            
--xxx.100.11.1.4.1.7
        qosPolicyPeakKbps OBJECT-TYPE
            SYNTAX  INTEGER(1..1000000)
            MAX-ACCESS  read-create
            STATUS  current
            DESCRIPTION
                "Peak information rate."
            ::= { qosPolicyEntry 7 } 
            
--xxx.100.11.1.4.1.8
        qosPolicyConformAction OBJECT-TYPE
            SYNTAX  INTEGER
            	{
            	        transmit(0),
            	    	drop(1),
               		set-dscp-transmit(2), 
               		set-prec-transmit(3)        	
            	}
            MAX-ACCESS  read-create
            STATUS  current
            DESCRIPTION
                "conform-action transmit means send packets without any change when specified speed is not exceeded;
                 conform-action drop means drop packets when specified speed is not exceeded;
                 conform-action set-dscp-transmit specifies to mark down packet DSCP value 
                 according to policed-dscp mapping when specified speed is not exceeded;
                 conform-action set-prec-transmit specifies to mark down packet TOS value 
                 according to policed-dscp mapping when specified speed is not exceeded."
            ::= { qosPolicyEntry 8 } 
            
--xxx.100.11.1.4.1.9
        qosPolicyConformActionChangeValue OBJECT-TYPE
            SYNTAX  INTEGER (0..63)
            MAX-ACCESS  read-create
            STATUS  current
            DESCRIPTION
                "If conform-action is set-dscp-transmit(2),the value is between 0-63;
                 else if conform-action is set-prec-transmit(2),the value is between 0-7."
            ::= { qosPolicyEntry 9 }                                                  

--xxx.100.11.1.4.1.10
        qosPolicyExceedAction OBJECT-TYPE
            SYNTAX  INTEGER
            	{
            	        transmit(0),
            	    	drop(1),
               		policeDscpTransmit(2)         	
            	}
            MAX-ACCESS  read-create
            STATUS  current
            DESCRIPTION
                "exceed-action transmit means send packets without any change when specified speed is exceeded;
                 exceed-action drop means drop packets when specified speed is exceeded;
                 exceed-action policed-dscp-transmit specifies to mark down packet DSCP value 
                 according to policed-dscp mapping when specified speed is exceeded."
            ::= { qosPolicyEntry 10 }
            
--xxx.100.11.1.4.1.11
        qosPolicyViolateAction OBJECT-TYPE
            SYNTAX  INTEGER
            	{
            	        transmit(0),
            	    	drop(1),
               		policeDscpTransmit(2)         	
            	}
            MAX-ACCESS  read-create
            STATUS  current
            DESCRIPTION
                "violate-action transmit means send packets without any change when specified speed is violate;
                 violate-action drop means drop packets when specified speed is violate;
                 violate-action policed-dscp-transmit specifies to mark down packet DSCP value 
                 according to policed-dscp mapping when specified speed is violate."
            ::= { qosPolicyEntry 11 }                  

--xxx.100.11.1.4.1.12
        qosPolicyAggregatePolicer OBJECT-TYPE
            SYNTAX  DisplayString
            MAX-ACCESS  read-create
            STATUS  current
            DESCRIPTION
                "aggregate-policer-name.
                This object be configured only if qosPolicyType 
                in the same row is aggregatePolicer(3)."
            ::= { qosPolicyEntry 12 }   

--xxx.100.11.1.4.1.13
        qosPolicyStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qosPolicyEntry 13 } 

--********************************************************************************************************

--xxx.100.11.1.5
qosAggPolicerTable OBJECT-TYPE
    SYNTAX  SEQUENCE OF QosAggPolicerEntry
    MAX-ACCESS  not-accessible
    STATUS  current
            DESCRIPTION
                "qos of AggPolicer list,use it can configure one item AggPolicer,Attention : the get/get next operation can only get snmp cache content,
                please refer to qosshow node for the running configuraton"
            ::= { qos 5 } 

--xxx.100.11.1.5.1
    qosAggPolicerEntry OBJECT-TYPE
        SYNTAX  QosAggPolicerEntry
        MAX-ACCESS  not-accessible
        STATUS  current
        DESCRIPTION
            " index is AggPolicer name."
        INDEX   { qosAggPolicerName }
        ::= { qosAggPolicerTable 1 }
        
    QosAggPolicerEntry
        ::= SEQUENCE
            {
                qosAggPolicerName			DisplayString,
                qosAggPolicerRateKbps			INTEGER,
                qosAggPolicerNormalBurstKbps		INTEGER,
                qosAggPolicerMaximumBurstKbps 		INTEGER,
                qosAggPolicerPeakKbps			INTEGER, 
                qosAggPolicerConformAction		INTEGER,
                qosAggPolicerConformActionChangeValue	INTEGER,
                qosAggPolicerExceedAction 		INTEGER,
                qosAggPolicerViolateAction 		INTEGER,                
                qosAggPolicerStatus			INTEGER                                              
            }

--xxx.100.11.1.5.1.1
        qosAggPolicerName OBJECT-TYPE
            SYNTAX  DisplayString (SIZE(1..32))
            MAX-ACCESS  not-accessible
            STATUS  current
            DESCRIPTION
                "QoS qosAggPolicer name"
            ::= { qosAggPolicerEntry 1 }

--xxx.100.11.1.5.1.2
        qosAggPolicerRateKbps OBJECT-TYPE
            SYNTAX  INTEGER(1..10000000)
            MAX-ACCESS  read-create
            STATUS  current
            DESCRIPTION
                "Rate Bandwidth of After the classification."
            ::= { qosAggPolicerEntry 2 }            

--xxx.100.11.1.5.1.3
        qosAggPolicerNormalBurstKbps OBJECT-TYPE
            SYNTAX  INTEGER(1..1000000)
            MAX-ACCESS  read-create
            STATUS  current
            DESCRIPTION
                "Normal burst kbytes."
            ::= { qosAggPolicerEntry 3 }
            
--xxx.100.11.1.5.1.4
        qosAggPolicerMaximumBurstKbps OBJECT-TYPE
            SYNTAX  INTEGER(1..1000000)
            MAX-ACCESS  read-create
            STATUS  current
            DESCRIPTION
                "Maximum burst kbytes."
            ::= { qosAggPolicerEntry 4 }
            
--xxx.100.11.1.5.1.5
        qosAggPolicerPeakKbps OBJECT-TYPE
            SYNTAX  INTEGER(1..1000000)
            MAX-ACCESS  read-create
            STATUS  current
            DESCRIPTION
                "Peak information rate."
            ::= { qosAggPolicerEntry 5 } 
            
--xxx.100.11.1.5.1.6
        qosAggPolicerConformAction OBJECT-TYPE
            SYNTAX  INTEGER
            	{
            	        transmit(0),
            	    	drop(1),
               		set-dscp-transmit(2), 
               		set-prec-transmit(3)        	
            	}
            MAX-ACCESS  read-create
            STATUS  current
            DESCRIPTION
                "conform-action transmit means send packets without any change when specified speed is not exceeded;
                 conform-action drop means drop packets when specified speed is not exceeded;
                 conform-action set-dscp-transmit specifies to mark down packet DSCP value 
                 according to policed-dscp mapping when specified speed is not exceeded;
                 conform-action set-prec-transmit specifies to mark down packet TOS value 
                 according to policed-dscp mapping when specified speed is not exceeded."
            ::= { qosAggPolicerEntry 6 } 
            
--xxx.100.11.1.5.1.7
        qosAggPolicerConformActionChangeValue OBJECT-TYPE
            SYNTAX  INTEGER (0..63)
            MAX-ACCESS  read-create
            STATUS  current
            DESCRIPTION
                "If conform-action is set-dscp-transmit(2),the value is between 0-63;
                 else if conform-action is set-prec-transmit(2),the value is between 0-7."
            ::= { qosAggPolicerEntry 7 }                                                  

--xxx.100.11.1.5.1.8
        qosAggPolicerExceedAction OBJECT-TYPE
            SYNTAX  INTEGER
            	{
            	        transmit(0),
            	    	drop(1),
               		policeDscpTransmit(2)         	
            	}
            MAX-ACCESS  read-create
            STATUS  current
            DESCRIPTION
                "exceed-action transmit means send packets without any change when specified speed is exceeded;
                 exceed-action drop means drop packets when specified speed is exceeded;
                 exceed-action policed-dscp-transmit specifies to mark down packet DSCP value 
                 according to policed-dscp mapping when specified speed is exceeded."
            ::= { qosAggPolicerEntry 8 }
            
--xxx.100.11.1.5.1.9
        qosAggPolicerViolateAction OBJECT-TYPE
            SYNTAX  INTEGER
            	{
            	        transmit(0),
            	    	drop(1),
               		policeDscpTransmit(2)         	
            	}
            MAX-ACCESS  read-create
            STATUS  current
            DESCRIPTION
                "violate-action transmit means send packets without any change when specified speed is violate;
                 violate-action drop means drop packets when specified speed is violate;
                 violate-action policed-dscp-transmit specifies to mark down packet DSCP value 
                 according to policed-dscp mapping when specified speed is violate."
            ::= { qosAggPolicerEntry 9 }               

--xxx.100.11.1.5.1.10
        qosAggPolicerStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qosAggPolicerEntry 10 } 

--********************************************************************************************************

--xxx.100.11.1.6
qosSetTable OBJECT-TYPE
    SYNTAX  SEQUENCE OF QosSetEntry
    MAX-ACCESS  not-accessible
    STATUS  current
            DESCRIPTION
                "remark new dscp or ip precedence for classified flow"
            ::= { qos 6 } 

--xxx.100.11.1.6.1
    qosSetEntry OBJECT-TYPE
        SYNTAX  QosSetEntry
        MAX-ACCESS  not-accessible
        STATUS  current
        DESCRIPTION
            " qosSetTable list of acce index policyname and classmap name."
        INDEX   { qosSetPolicyMapName }
        ::= { qosSetTable 1 }
        
    QosSetEntry
        ::= SEQUENCE
            {
                qosSetPolicyMapName		DisplayString,
                qosSetClassMapName		DisplayString,
		qosSetType		INTEGER,
		qosSetdscp		INTEGER,
		qosSetprecedence	INTEGER,	
		qosSetnextHop		IpAddress,
		qosSetv6Dscp		INTEGER,
		qosSetv6FlowLabel	INTEGER,
		qosSetv6nextHop		DisplayString,
		qosSetCos		       INTEGER,
		qosSetEXPimposition  INTEGER,
    qosSetStatus		       INTEGER                               
            }

--xxx.100.11.1.6.1.1
        qosSetPolicyMapName OBJECT-TYPE
            SYNTAX  DisplayString (SIZE(1..32))
            MAX-ACCESS  not-accessible
            STATUS  current
            DESCRIPTION
                "QoS Policy name"
            ::= { qosSetEntry 1 }

--xxx.100.11.1.6.1.2
        qosSetClassMapName OBJECT-TYPE
            SYNTAX  DisplayString (SIZE(1..32))
            MAX-ACCESS  read-create
            STATUS  current
            DESCRIPTION
                "QoS class map name"
            ::= { qosSetEntry 2 }
            
--xxx.100.11.1.6.1.3
        qosSetType OBJECT-TYPE
            SYNTAX  INTEGER
            	{
            	    	dscp(1),
               		precedence(2),
               		nextHop(3),
               		v6Dscp(4),            		
               		v6FlowLabel(6),
               		v6nextHop(7),
               		cos(8),
               		expimposition(9)           	
            	}
            MAX-ACCESS  read-create
            STATUS  current
            DESCRIPTION
                "qosSetType range:1,2,3,4,5,6,7,8,9
                1   dscp         Set IP DSCP (DiffServ CodePoints);
                2   precedence   Set IP precedence;
                3   nexthop      Set IP nexthop;
                4   dscp         Set IPv6 DSCP (DiffServ CodePoints);
                6   flowlabel    Set IPv6 flowlabel;
		            7   v6nextHop    Set IPv6 nexthop;
                8   cos          Set CoS ;
                9   expimposition Set mpls-experimental-imposition "		
            ::= { qosSetEntry 3 } 
            
--xxx.100.11.1.6.1.4
        qosSetdscp OBJECT-TYPE
            SYNTAX  INTEGER(0..63)
            MAX-ACCESS  read-create
            STATUS  current
            DESCRIPTION
                "remark dscp for the classified flow"
            ::= { qosSetEntry 4 } 

--xxx.100.11.1.6.1.5
        qosSetprecedence OBJECT-TYPE
            SYNTAX  INTEGER(0..7)
            MAX-ACCESS  read-create
            STATUS  current
            DESCRIPTION
                "remark ip precedence for classified flow"
            ::= { qosSetEntry 5 }
             
--xxx.100.11.1.6.1.6
        qosSetnextHop OBJECT-TYPE
            SYNTAX  IpAddress
            MAX-ACCESS  read-create
            STATUS  current
            DESCRIPTION
                "set nexthop for classified flow"
            ::= { qosSetEntry 6 } 
            
--xxx.100.11.1.6.1.7
        qosSetv6Dscp OBJECT-TYPE
            SYNTAX  INTEGER(0..63)
            MAX-ACCESS  read-create
            STATUS  current
            DESCRIPTION
                "remark ipv6 dscp for classified flow"
            ::= { qosSetEntry 7 }
             
--xxx.100.11.1.6.1.8
        qosSetv6FlowLabel OBJECT-TYPE
            SYNTAX  INTEGER(0..1048575)
            MAX-ACCESS  read-create
            STATUS  current
            DESCRIPTION
                "remark ipv6 flow lable for classified flow"
            ::= { qosSetEntry 8 } 
            
--xxx.100.11.1.6.1.9
        qosSetv6nextHop OBJECT-TYPE
            SYNTAX  DisplayString
            MAX-ACCESS  read-create
            STATUS  current
            DESCRIPTION
                "set IPv6 nexthop for classified flow"
            ::= { qosSetEntry 9 }

--xxx.100.11.1.6.1.10
        qosSetCos OBJECT-TYPE
            SYNTAX  INTEGER(0..7)
            MAX-ACCESS  read-create
            STATUS  current
            DESCRIPTION
                "remark cos for classified flow"
            ::= { qosSetEntry 10 } 
            
--xxx.100.11.1.6.1.11
        qosSetEXPimposition OBJECT-TYPE
            SYNTAX  INTEGER(0..7)
            MAX-ACCESS  read-create
            STATUS  current
            DESCRIPTION
                "remark MPLS EXP value for classified flow"
            ::= { qosSetEntry 11 }             

--xxx.100.11.1.6.1.12
        qosSetStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qosSetEntry 12 } 

--********************************************************************************************************

--xxx.100.11.1.7
qosPortBindTable OBJECT-TYPE
    SYNTAX  SEQUENCE OF QosPortBindEntry
    MAX-ACCESS  not-accessible
    STATUS  current
            DESCRIPTION
                "Apply a policy map to the specified port."
            ::= { qos 7 } 

--xxx.100.11.1.7.1
    qosPortBindEntry OBJECT-TYPE
        SYNTAX  QosPortBindEntry
        MAX-ACCESS  not-accessible
        STATUS  current
        DESCRIPTION
            "the index of this  entry is port-index and policy-map"
        INDEX   { qosPortBindIndex , qosPortBindPolicy }
        ::= { qosPortBindTable 1 }

    QosPortBindEntry
        ::= SEQUENCE
            {
                qosPortBindIndex		INTEGER,
                qosPortBindPolicy		DisplayString,
		qosPortBindType			INTEGER
	    }  
	    
--xxx.100.11.1.7.1.1
        qosPortBindIndex OBJECT-TYPE
            SYNTAX  INTEGER
            MAX-ACCESS  not-accessible
            STATUS  current
            DESCRIPTION
                "QoS Port Index"
            ::= { qosPortBindEntry 1 }

--xxx.100.11.1.7.1.2
        qosPortBindPolicy OBJECT-TYPE
            SYNTAX  DisplayString (SIZE(1..16))
            MAX-ACCESS  not-accessible
            STATUS  current
            DESCRIPTION
                "QoS Policy name"
            ::= { qosPortBindEntry 2 }
            
--xxx.100.11.1.7.1.3
        qosPortBindType OBJECT-TYPE
            SYNTAX  INTEGER
            	{
            	    input(1),
               		output(2),  
               		noinput(3),
               		nooutput(4)            	
            	}
            MAX-ACCESS  read-create
            STATUS  current
            DESCRIPTION
                " input(1),bind the policy-map to ingress port;
               		output(2),bind the policy-map to egress port;
               		noinput(3),unbind the policy-map to ingress port;
               		nooutput(4), unbind the policy-map to egress port"
            ::= { qosPortBindEntry 3 } 

--********************************************************************************************************

--xxx.100.11.1.8
qosPortQueueTable OBJECT-TYPE
    SYNTAX  SEQUENCE OF QosPortQueueEntry
    MAX-ACCESS  not-accessible
    STATUS  current
            DESCRIPTION
                "set golbal qos WRR weight"
            ::= { qos 8 } 

--xxx.100.11.1.8.1
    qosPortQueueEntry OBJECT-TYPE
        SYNTAX  QosPortQueueEntry
        MAX-ACCESS  not-accessible
        STATUS  current
        DESCRIPTION
            " set port qos WRR weight,index is port index."
        INDEX   { qosPortQueueIndex }
        ::= { qosPortQueueTable 1 }

    QosPortQueueEntry
        ::= SEQUENCE
            {
                qosPortQueueIndex		INTEGER,
                qosPortQueueWeight1		INTEGER,
                qosPortQueueWeight2		INTEGER,
                qosPortQueueWeight3		INTEGER,
                qosPortQueueWeight4		INTEGER,
                qosPortQueueWeight5		INTEGER,
                qosPortQueueWeight6		INTEGER,
                qosPortQueueWeight7		INTEGER,
                qosPortQueueWeight8		INTEGER,
		qosPortQueueStatus		INTEGER
	    }  
	    
--xxx.100.11.1.8.1.1
        qosPortQueueIndex OBJECT-TYPE
            SYNTAX  INTEGER
            MAX-ACCESS  not-accessible
            STATUS  current
            DESCRIPTION
                "QoS Port Index"
            ::= { qosPortQueueEntry 1 }

--xxx.100.11.1.8.1.2
        qosPortQueueWeight1 OBJECT-TYPE
            SYNTAX  INTEGER
            MAX-ACCESS  read-create
            STATUS  current
            DESCRIPTION
                "WRR weight,range is 0~15."
            ::= { qosPortQueueEntry 2 }

--xxx.100.11.1.8.1.3
        qosPortQueueWeight2 OBJECT-TYPE
            SYNTAX  INTEGER
            MAX-ACCESS  read-create
            STATUS  current
            DESCRIPTION
                "WRR weight,range is 0~15."
            ::= { qosPortQueueEntry 3 }

--xxx.100.11.1.8.1.4
        qosPortQueueWeight3 OBJECT-TYPE
            SYNTAX  INTEGER
            MAX-ACCESS  read-create
            STATUS  current
            DESCRIPTION
                "WRR weight,range is 0~15."
            ::= { qosPortQueueEntry 4 }
 
 --xxx.100.11.1.8.1.5
        qosPortQueueWeight4 OBJECT-TYPE
            SYNTAX  INTEGER
            MAX-ACCESS  read-create
            STATUS  current
            DESCRIPTION
                "WRR weight,range is 0~15."
            ::= { qosPortQueueEntry 5 }
 
 --xxx.100.11.1.8.1.6
        qosPortQueueWeight5 OBJECT-TYPE
            SYNTAX  INTEGER
            MAX-ACCESS  read-create
            STATUS  current
            DESCRIPTION
                "WRR weight,range is 0~15."
            ::= { qosPortQueueEntry 6 }
 
 --xxx.100.11.1.8.1.7
        qosPortQueueWeight6 OBJECT-TYPE
            SYNTAX  INTEGER
            MAX-ACCESS  read-create
            STATUS  current
            DESCRIPTION
                "WRR weight,range is 0~15."
            ::= { qosPortQueueEntry 7 }
 
 --xxx.100.11.1.8.1.8
        qosPortQueueWeight7 OBJECT-TYPE
            SYNTAX  INTEGER
            MAX-ACCESS  read-create
            STATUS  current
            DESCRIPTION
                "WRR weight,range is 0~15."
            ::= { qosPortQueueEntry 8 }

 --xxx.100.11.1.8.1.9
        qosPortQueueWeight8 OBJECT-TYPE
            SYNTAX  INTEGER
            MAX-ACCESS  read-create
            STATUS  current
            DESCRIPTION
                "WRR weight,range is 0~15."
            ::= { qosPortQueueEntry 9 }

 --xxx.100.11.1.8.1.10
        qosPortQueueStatus OBJECT-TYPE
            SYNTAX  INTEGER
            	    {
               		active(1),
               		destroy(2)
            	    }
            MAX-ACCESS  read-create
            STATUS  current
            DESCRIPTION
                "Setting it to active(1) creates an entry.Setting it to destroy(2) destroys an entry."
            ::= { qosPortQueueEntry 10 } 

--********************************************************************************************************

--xxx.100.11.1.9
qosPortCosMapTable OBJECT-TYPE
    SYNTAX  SEQUENCE OF QosPortCosMapEntry
    MAX-ACCESS  not-accessible
    STATUS  current
            DESCRIPTION
                "COS-Queue map"
            ::= { qos 9 } 

--xxx.100.11.1.9.1
    qosPortCosMapEntry OBJECT-TYPE
        SYNTAX  QosPortCosMapEntry
        MAX-ACCESS  not-accessible
        STATUS  current
        DESCRIPTION
            " COS-Queue map,index is cos-Queue map ID."
        INDEX   { qosPortCosMapQueueId }
        ::= { qosPortCosMapTable 1 }

    QosPortCosMapEntry
        ::= SEQUENCE
            {
                qosPortCosMapQueueId		INTEGER,
                qosPortCosMapCos1		INTEGER,
                qosPortCosMapCos2		INTEGER,
                qosPortCosMapCos3		INTEGER,
                qosPortCosMapCos4		INTEGER,
                qosPortCosMapCos5		INTEGER,
                qosPortCosMapCos6		INTEGER,
                qosPortCosMapCos7		INTEGER,
                qosPortCosMapCos8		INTEGER,
		qosPortCosMapStatus		INTEGER
	    }  
	    
--xxx.100.11.1.9.1.1
        qosPortCosMapQueueId OBJECT-TYPE
            SYNTAX  INTEGER
            MAX-ACCESS  not-accessible
            STATUS  current
            DESCRIPTION
                "queue ID"
            ::= { qosPortCosMapEntry 1 }

--xxx.100.11.1.9.1.2
        qosPortCosMapCos1 OBJECT-TYPE
            SYNTAX  INTEGER
            MAX-ACCESS  read-create
            STATUS  current
            DESCRIPTION
                "COS range is 0~7"
            ::= { qosPortCosMapEntry 2 }

--xxx.100.11.1.9.1.3
        qosPortCosMapCos2 OBJECT-TYPE
            SYNTAX  INTEGER
            MAX-ACCESS  read-create
            STATUS  current
            DESCRIPTION
                 "COS range is 0~7"
            ::= { qosPortCosMapEntry 3 }

--xxx.100.11.1.9.1.4
        qosPortCosMapCos3 OBJECT-TYPE
            SYNTAX  INTEGER
            MAX-ACCESS  read-create
            STATUS  current
            DESCRIPTION
                 "COS range is 0~7"
            ::= { qosPortCosMapEntry 4 }
 
 --xxx.100.11.1.9.1.5
        qosPortCosMapCos4 OBJECT-TYPE
            SYNTAX  INTEGER
            MAX-ACCESS  read-create
            STATUS  current
            DESCRIPTION
                 "COS range is 0~7"
            ::= { qosPortCosMapEntry 5 }
 
 --xxx.100.11.1.9.1.6
        qosPortCosMapCos5 OBJECT-TYPE
            SYNTAX  INTEGER
            MAX-ACCESS  read-create
            STATUS  current
            DESCRIPTION
                 "COS range is 0~7"
            ::= { qosPortCosMapEntry 6 }
 
 --xxx.100.11.1.9.1.7
        qosPortCosMapCos6 OBJECT-TYPE
            SYNTAX  INTEGER
            MAX-ACCESS  read-create
            STATUS  current
            DESCRIPTION
                 "COS range is 0~7"
            ::= { qosPortCosMapEntry 7 }
 
 --xxx.100.11.1.9.1.8
        qosPortCosMapCos7 OBJECT-TYPE
            SYNTAX  INTEGER
            MAX-ACCESS  read-create
            STATUS  current
            DESCRIPTION
                 "COS range is 0~7"
            ::= { qosPortCosMapEntry 8 }

--xxx.100.11.1.9.1.9
        qosPortCosMapCos8 OBJECT-TYPE
            SYNTAX  INTEGER
            MAX-ACCESS  read-create
            STATUS  current
            DESCRIPTION
                 "COS range is 0~7"
            ::= { qosPortCosMapEntry 9 }

--xxx.100.11.1.9.1.10
        qosPortCosMapStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qosPortCosMapEntry 10 } 
                    	                                     
--********************************************************************************************************
--xxx.100.11.1.10
    qosMap         	    OBJECT IDENTIFIER ::= { qos 10 } 

--set class of service(CoS)-to-Differentiated Services Code Point (DSCP) map,DSCP-to-CoS map,DSCP-to-DSCP-mutation map,IP-precedence-to-DSCP map and policed-DSCP map
--xxx.100.11.1.10.1
        qosMapType OBJECT-TYPE
            SYNTAX  INTEGER
            	{
            	    	cosDscp(1),
               		dscpCos(2),
               		dscpMutation(3),
               		ipPrecDscp(4),
               		policedDscp(5),
               		expdscp(6),
               		dscpexp(7)      	
            	}
            MAX-ACCESS  read-create
            STATUS  current
            DESCRIPTION
                "qosMapType range is 1~5.1 mls qos map cos-dscp <dscp1...dscp8>;
                 2 mls qos map  dscp-cos <dscp-list> to <cos>;
                 3 mls qos map  dscp-mutation <dscp-mutation-name> <in-dscp> to <out-dscp>;
		 4  mls qos map ip-prec-dscp <dscp1...dscp8>; 
		 5  mls qos map policed-dscp <dscp-list> to <mark-down-dscp>;
		 6  mls qos map exp-dscp <dscp-value-list>;
		 7  mls qos map dscp-exp <dscp-value-list> to <exp>
		 When you want to configure the Map of DSCP to COS,please configure the qosMapType==2 firstly,
		  input the dscp(1~8) optionally, then  configure the qosMapCos , valid/invalid the qosMapStatus finally."
								
            ::= { qosMap  1 }

--xxx.100.11.1.10.2
        qosMapDscp1 OBJECT-TYPE
            SYNTAX  INTEGER
            MAX-ACCESS  read-create
            STATUS  current
            DESCRIPTION
                "DSCP-CoS map,DSCP range is 0~63"
            ::= { qosMap  2 }

--xxx.100.11.1.10.3
        qosMapDscp2 OBJECT-TYPE
            SYNTAX  INTEGER
            MAX-ACCESS  read-create
            STATUS  current
            DESCRIPTION
                "DSCP-CoS map,DSCP range is 0~63"
            ::= { qosMap  3 }

--xxx.100.11.1.10.4
        qosMapDscp3 OBJECT-TYPE
            SYNTAX  INTEGER
            MAX-ACCESS  read-create
            STATUS  current
            DESCRIPTION
                "DSCP-CoS map,DSCP range is 0~63"
            ::= { qosMap  4 }            
            
--xxx.100.11.1.10.5
        qosMapDscp4 OBJECT-TYPE
            SYNTAX  INTEGER
            MAX-ACCESS  read-create
            STATUS  current
            DESCRIPTION
                "DSCP-CoS map,DSCP range is 0~63"
            ::= { qosMap  5 }
            
--xxx.100.11.1.10.6
        qosMapDscp5 OBJECT-TYPE
            SYNTAX  INTEGER
            MAX-ACCESS  read-create
            STATUS  current
            DESCRIPTION
                "DSCP-CoS map,DSCP range is 0~63"
            ::= { qosMap  6 }
            
--xxx.100.11.1.10.7
        qosMapDscp6 OBJECT-TYPE
            SYNTAX  INTEGER
            MAX-ACCESS  read-create
            STATUS  current
            DESCRIPTION
                "DSCP-CoS map,DSCP range is 0~63"
            ::= { qosMap  7 }

--xxx.100.11.1.10.8
        qosMapDscp7 OBJECT-TYPE
            SYNTAX  INTEGER
            MAX-ACCESS  read-create
            STATUS  current
            DESCRIPTION
                "DSCP-CoS map,DSCP range is 0~63"
            ::= { qosMap  8 }

--xxx.100.11.1.10.9
        qosMapDscp8 OBJECT-TYPE
            SYNTAX  INTEGER
            MAX-ACCESS  read-create
            STATUS  current
            DESCRIPTION
                "DSCP-CoS map,DSCP range is 0~63"
            ::= { qosMap  9 }

--xxx.100.11.1.10.10
        qosMapCos OBJECT-TYPE
            SYNTAX  INTEGER
            MAX-ACCESS  read-create
            STATUS  current
            DESCRIPTION
                "the cos which DSCP map to "
            ::= { qosMap  10 }
            
--xxx.100.11.1.10.11
        qosMapEXP OBJECT-TYPE
            SYNTAX  INTEGER(0..7)
            MAX-ACCESS  read-create
            STATUS  current
            DESCRIPTION
                "the EXP value which DSCP map to "
            ::= { qosMap  11 }         
--xxx.100.11.1.10.12
        qosMapMarkDownDscp OBJECT-TYPE
            SYNTAX  INTEGER
            MAX-ACCESS  read-create
            STATUS  current
            DESCRIPTION
                "the dscp after mark down"
            ::= { qosMap  12 }
            
--xxx.100.11.1.10.13
        qosMapMarkDownType OBJECT-TYPE
            SYNTAX  INTEGER
                    {
               		normal-burst(0),
               		max-burst(1)
            	    }
            MAX-ACCESS  read-create
            STATUS  current
            DESCRIPTION
                "normal-burst:markdown map used by the exceed-action;max-burst:markdown map used by the violate-action."
            ::= { qosMap  13 }                         

--xxx.100.11.1.10.14
        qosMapMutationName OBJECT-TYPE
            SYNTAX  DisplayString (SIZE(1..16))
            MAX-ACCESS  read-create
            STATUS  current
            DESCRIPTION
                "map name"
            ::= { qosMap  14 }   
            
--xxx.100.11.1.10.15
        qosMapMutationOut OBJECT-TYPE
            SYNTAX  INTEGER
            MAX-ACCESS  read-create
            STATUS  current
            DESCRIPTION
                "egress DSCP,only one,eight ingress DSCP value map to one egress value"
            ::= { qosMap  15 }                       
--xxx.100.11.1.10.16
        qosMapStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qosMap 16 } 


--xxx.100.11
    showqos        	   	  OBJECT IDENTIFIER ::= { qos 11 }    
    
--xxx.100.16.2.1
showclassmapTable OBJECT-TYPE 
    SYNTAX  SEQUENCE OF ShowclassmapEntry
    MAX-ACCESS  not-accessible
    STATUS  current
    DESCRIPTION
        " show class map table"
    ::= { showqos   1}
            
--xxx.100.16.2.1.1
showclassmapEntry OBJECT-TYPE
        SYNTAX  ShowclassmapEntry
        MAX-ACCESS  not-accessible
        STATUS  current
        DESCRIPTION
            " show class map entry"
        INDEX   { showclassmapname}
        ::= { showclassmapTable 1 }

ShowclassmapEntry
        ::= SEQUENCE
            {
                showclassmapname               			DisplayString,
                showclassmapmatch				DisplayString
            }
            
--xxx.100.16.2.1.1.1
showclassmapname  OBJECT-TYPE
            SYNTAX  DisplayString (SIZE(1..128))
            MAX-ACCESS  not-accessible
            STATUS  current
            DESCRIPTION
                " classmap name"
            ::= { showclassmapEntry 1 }
            
--xxx.100.16.2.1.1.2         
showclassmapmatch  OBJECT-TYPE
	SYNTAX      DisplayString (SIZE(1..512))	
        MAX-ACCESS  read-only
        STATUS      current
        DESCRIPTION "one item classmap match rule"
        ::= { showclassmapEntry 2 }  


--xxx.100.16.2.1
showpolicymapTable OBJECT-TYPE 
    SYNTAX  SEQUENCE OF ShowpolicymapEntry
    MAX-ACCESS  not-accessible
    STATUS  current
    DESCRIPTION
        " show policy list"
    ::= { showqos   2}
            
--xxx.100.16.2.1.1
showpolicymapEntry OBJECT-TYPE
        SYNTAX  ShowpolicymapEntry
        MAX-ACCESS  not-accessible
        STATUS  current
        DESCRIPTION
            " policy map entry"
        INDEX   { showpolicymapname}
        ::= { showpolicymapTable 1 }

ShowpolicymapEntry
        ::= SEQUENCE
            {
                showpolicymapname               		DisplayString,
                showpolicymapcontent				DisplayString
            }
            
--xxx.100.16.2.1.1.1
showpolicymapname  OBJECT-TYPE
            SYNTAX  DisplayString (SIZE(1..128))
            MAX-ACCESS  not-accessible
            STATUS  current
            DESCRIPTION
                " policy name"
            ::= { showpolicymapEntry 1 }
            
--xxx.100.16.2.1.1.2         
showpolicymapcontent  OBJECT-TYPE
	SYNTAX      DisplayString (SIZE(1..512))	
        MAX-ACCESS  read-only
        STATUS      current
        DESCRIPTION "the match classmap and all defined other rules"
        ::= { showpolicymapEntry 2 }        
        
        
--xxx.100.16.2.1
showqosaggregatepolicerTable OBJECT-TYPE 
    SYNTAX  SEQUENCE OF ShowqosaggregatepolicerEntry
    MAX-ACCESS  not-accessible
    STATUS  current
    DESCRIPTION
        " display aggregatepolicer list"
    ::= { showqos   3}
            
--xxx.100.16.2.1.1
showqosaggregatepolicerEntry OBJECT-TYPE
        SYNTAX  ShowqosaggregatepolicerEntry
        MAX-ACCESS  not-accessible
        STATUS  current
        DESCRIPTION
            " aggregatepolicer entry,index is showqosaggregatepolicername"
        INDEX   { showqosaggregatepolicername}
        ::= { showqosaggregatepolicerTable 1 }

ShowqosaggregatepolicerEntry
        ::= SEQUENCE
            {
                showqosaggregatepolicername               		DisplayString,
                showqosaggregatepolicercontent				DisplayString
            }
            
--xxx.100.16.2.1.1.1
showqosaggregatepolicername  OBJECT-TYPE
            SYNTAX  DisplayString (SIZE(1..128))
            MAX-ACCESS  not-accessible
            STATUS  current
            DESCRIPTION
                " aggregatepolicer name"
            ::= { showqosaggregatepolicerEntry 1 }
            
--xxx.100.16.2.1.1.2         
showqosaggregatepolicercontent  OBJECT-TYPE
	SYNTAX      DisplayString (SIZE(1..512))	
        MAX-ACCESS  read-only
        STATUS      current
        DESCRIPTION "aggregatepolicer parameter"
        ::= { showqosaggregatepolicerEntry 2 }        


--xxx.100.16.2.1
showmlsqosinterfaceTable OBJECT-TYPE 
    SYNTAX  SEQUENCE OF ShowmlsqosinterfaceEntry
    MAX-ACCESS  not-accessible
    STATUS  current
    DESCRIPTION
        " show port qos configuration"
    ::= { showqos   4}
            
--xxx.100.16.2.1.1
showmlsqosinterfaceEntry OBJECT-TYPE
        SYNTAX  ShowmlsqosinterfaceEntry
        MAX-ACCESS  not-accessible
        STATUS  current
        DESCRIPTION
            " showmlsqosinterfaceTable,index is port-index"
        INDEX   { showmlsqosinterfaceIndex}
        ::= { showmlsqosinterfaceTable 1 }

ShowmlsqosinterfaceEntry
        ::= SEQUENCE
            {
                showmlsqosinterfaceIndex               			INTEGER,
                showmlsqosinterfaceqoscontent				DisplayString
            }
            
--xxx.100.16.2.1.1.1
showmlsqosinterfaceIndex  OBJECT-TYPE
            SYNTAX  INTEGER 
            MAX-ACCESS  not-accessible
            STATUS  current
            DESCRIPTION
                " port index"
            ::= { showmlsqosinterfaceEntry 1 }
            
--xxx.100.16.2.1.1.2         
showmlsqosinterfaceqoscontent  OBJECT-TYPE
	SYNTAX      DisplayString (SIZE(1..512))	
        MAX-ACCESS  read-only
        STATUS      current
        DESCRIPTION "qos port configuration"
        ::= { showmlsqosinterfaceEntry 2 }    
        
--xxx.100.9
    showmlsqosmaps        	   	  OBJECT IDENTIFIER ::= { showqos 5 }   

--xxx.100.16.1.1
        showmlsqosmapscosdscp OBJECT-TYPE
            SYNTAX      DisplayString (SIZE(1..512))     	
            MAX-ACCESS  read-only
            STATUS  current
            DESCRIPTION
                "cos-dscp map "
            ::= { showmlsqosmaps 1 }

--xxx.100.16.1.2
        showmlsqosmapscosqueue OBJECT-TYPE
            SYNTAX      DisplayString (SIZE(1..512))                  
            MAX-ACCESS  read-only
            STATUS  current
            DESCRIPTION
                "COS-wrr-queue map"
            ::= { showmlsqosmaps 2 }     
--xxx.100.16.1.3
        showmlsqosmapsdscpcos OBJECT-TYPE
            SYNTAX      DisplayString (SIZE(1..512))                     	
            MAX-ACCESS  read-only
            STATUS  current
            DESCRIPTION
                "DSCP-COS map"
            ::= { showmlsqosmaps  3 }

--xxx.100.16.1.4
        showmlsqosmapsipprecdscp OBJECT-TYPE
            SYNTAX      DisplayString (SIZE(1..512))              
            MAX-ACCESS  read-only
            STATUS  current
            DESCRIPTION
                "IP precedence to DSCP map"
            ::= { showmlsqosmaps  4 }  
--xxx.100.16.1.5
        showmlsqosmapspoliceddscp OBJECT-TYPE
            SYNTAX      DisplayString (SIZE(1..512))                   	
            MAX-ACCESS  read-only
            STATUS  current
            DESCRIPTION
                " DSCP mark down map"
            ::= { showmlsqosmaps  5 }   
            
--xxx.100.16.1.6
        showmlsqosmapspoliceddscpnormalburst OBJECT-TYPE
            SYNTAX      DisplayString (SIZE(1..512))                   	
            MAX-ACCESS  read-only
            STATUS  current
            DESCRIPTION
                " Normal Burst Policed-dscp map"
            ::= { showmlsqosmaps  6 }                
              
--xxx.100.16.1.7
        showmlsqosmapsexpdscp OBJECT-TYPE
            SYNTAX      DisplayString (SIZE(1..512))                    	
            MAX-ACCESS  read-only
            STATUS  current
            DESCRIPTION
                " EXP to DSCP map"
            ::= { showmlsqosmaps  7 } 
            
--xxx.100.16.1.8
        showmlsqosmapsdscpexp OBJECT-TYPE
            SYNTAX      DisplayString (SIZE(1..512))                    	
            MAX-ACCESS  read-only
            STATUS  current
            DESCRIPTION
                " DSCP to EXP map"
            ::= { showmlsqosmaps  8 } 
            
--xxx.100.16.2.1
showmlsqosmapsdscpmutationTable OBJECT-TYPE 
    SYNTAX  SEQUENCE OF ShowmlsqosmapsdscpmutationEntry
    MAX-ACCESS  not-accessible
    STATUS  current
    DESCRIPTION
        " ingress DSCP to egress DSCP map"
    ::= { showqos   6}
            
--xxx.100.16.2.1.1
showmlsqosmapsdscpmutationEntry OBJECT-TYPE
        SYNTAX  ShowmlsqosmapsdscpmutationEntry
        MAX-ACCESS  not-accessible
        STATUS  current
        DESCRIPTION
            "index is dscpmutationname"
        INDEX   { showmlsqosmapsdscpmutationname}
        ::= { showmlsqosmapsdscpmutationTable 1 }

ShowmlsqosmapsdscpmutationEntry
        ::= SEQUENCE
            {
                showmlsqosmapsdscpmutationname               			DisplayString,
                showmlsqosmapsdscpmutationcontent				DisplayString
            }
            
--xxx.100.16.2.1.1.1
showmlsqosmapsdscpmutationname  OBJECT-TYPE
            SYNTAX  DisplayString  (SIZE(1..128))
            MAX-ACCESS  not-accessible
            STATUS  current
            DESCRIPTION
                " dscpmutationname."
            ::= { showmlsqosmapsdscpmutationEntry 1 }
            
--xxx.100.16.2.1.1.2         
showmlsqosmapsdscpmutationcontent  OBJECT-TYPE
	SYNTAX      DisplayString (SIZE(1..512))	
        MAX-ACCESS  read-only
        STATUS      current
        DESCRIPTION "DSCP-DSCP map"
        ::= { showmlsqosmapsdscpmutationEntry 2 }                                 
--********************************************************************************************************
--********************************************************************************************************

--xxx.100.12.1
mirrorDestTable OBJECT-TYPE 
    SYNTAX  SEQUENCE OF MirrorDestEntry
    MAX-ACCESS  not-accessible
    STATUS  current
    DESCRIPTION
        "Destination port for mirrored packets."
    ::= { primirror   1}
            
--xxx.100.12.1.1
mirrorDestEntry OBJECT-TYPE
        SYNTAX  MirrorDestEntry
        MAX-ACCESS  not-accessible
        STATUS  current
        DESCRIPTION
            "Destination port for mirrored packets."
        INDEX   { mirrorDestSession }
        ::= { mirrorDestTable 1 }

MirrorDestEntry
        ::= SEQUENCE
            {
                mirrorDestSession          INTEGER,
                mirrorDestPort		   DisplayString,
                mirrorDestStatus	   INTEGER
            }
            
--xxx.100.12.1.1.1       
mirrorDestSession   OBJECT-TYPE
	SYNTAX      INTEGER (1..4)	
        MAX-ACCESS  read-only
        STATUS      current
        DESCRIPTION "Session ID."
        ::= { mirrorDestEntry 1 } 
          
--xxx.100.12.1.1.2       
mirrorDestPort   OBJECT-TYPE
	SYNTAX      DisplayString(SIZE(1..20))		
        MAX-ACCESS  read-create
        STATUS      current
        DESCRIPTION "mirror destination port  eg:Ethernet1/1."
        ::= { mirrorDestEntry 2 }   

--xxx.100.12.1.1.3       
mirrorDestStatus   OBJECT-TYPE
	SYNTAX      INTEGER
		    {
            	    
               		active(1),
               		destroy(2)		    	
		    }		
        MAX-ACCESS  read-create
        STATUS      current
        DESCRIPTION "Status."
        ::= { mirrorDestEntry 3 } 
        
--********************************************************************************************************

--xxx.100.12.2
mirrorSrcPortTable OBJECT-TYPE 
    SYNTAX  SEQUENCE OF MirrorSrcPortEntry
    MAX-ACCESS  not-accessible
    STATUS  current
    DESCRIPTION
        "Src port for mirrored packets."
    ::= { primirror   2}
            
--xxx.100.12.2.1
mirrorSrcPortEntry OBJECT-TYPE
        SYNTAX  MirrorSrcPortEntry
        MAX-ACCESS  not-accessible
        STATUS  current
        DESCRIPTION
            "Src port for mirrored packets."
        INDEX   { mirrorSrcPortSession , mirrorSrcPortDirect }
        ::= { mirrorSrcPortTable 1 }

MirrorSrcPortEntry
        ::= SEQUENCE
            {
                mirrorSrcPortSession           INTEGER,
                mirrorSrcPortDirect	       INTEGER,
                mirrorSrcPort		       DisplayString,
                mirrorSrcPortStatus            INTEGER
            }
            
--xxx.100.12.2.1.1       
mirrorSrcPortSession   OBJECT-TYPE
	SYNTAX      INTEGER (1..4)	
        MAX-ACCESS  read-only
        STATUS      current
        DESCRIPTION "Session ID."
        ::= { mirrorSrcPortEntry 1 } 
          
--xxx.100.12.2.1.2       
mirrorSrcPortDirect   OBJECT-TYPE
	SYNTAX      INTEGER
		{
               		rx(1),
               		tx(2)		
		}	
        MAX-ACCESS  read-only
        STATUS      current
        DESCRIPTION "Direction of  mirror."
        ::= { mirrorSrcPortEntry 2 }   
        
--xxx.100.12.2.1.3       
mirrorSrcPort   OBJECT-TYPE
	SYNTAX      DisplayString(SIZE(1..512))	
        MAX-ACCESS  read-create
        STATUS      current
        DESCRIPTION "mirror source port. eg:Ethernet1/1."
        ::= { mirrorSrcPortEntry 3 } 
        
--xxx.100.12.2.1.4       
mirrorSrcPortStatus   OBJECT-TYPE
	SYNTAX      INTEGER
		    {
            	    	
               		active(1),
               		destroy(2)		    	
		    }		
        MAX-ACCESS  read-create
        STATUS      current
        DESCRIPTION "Status."
        ::= { mirrorSrcPortEntry 4 }         
        
--********************************************************************************************************

--xxx.100.12.3
mirrorSrcCpuTable OBJECT-TYPE 
    SYNTAX  SEQUENCE OF MirrorSrcCpuEntry
    MAX-ACCESS  not-accessible
    STATUS  current
    DESCRIPTION
        "Src Cpu for mirrored packets."
    ::= { primirror   3}
            
--xxx.100.12.3.1
mirrorSrcCpuEntry OBJECT-TYPE
        SYNTAX  MirrorSrcCpuEntry
        MAX-ACCESS  not-accessible
        STATUS  current
        DESCRIPTION
            "Src Cpu for mirrored packets."
        INDEX   { mirrorSrcCpuSession , mirrorSrcCpuDirect , mirrorSrcCpuSlot }
        ::= { mirrorSrcCpuTable 1 }

MirrorSrcCpuEntry
        ::= SEQUENCE
            {
                mirrorSrcCpuSession    INTEGER,
                mirrorSrcCpuDirect     INTEGER,
                mirrorSrcCpuSlot       INTEGER,
                mirrorSrcCpuStatus     INTEGER     
            }
            
--xxx.100.12.3.1.1       
mirrorSrcCpuSession   OBJECT-TYPE
	SYNTAX      INTEGER(4)	
        MAX-ACCESS  read-only
        STATUS      current
        DESCRIPTION "Session ID."
        ::= { mirrorSrcCpuEntry 1 } 
          
--xxx.100.12.3.1.2       
mirrorSrcCpuDirect   OBJECT-TYPE
	SYNTAX      INTEGER 
		{
               		rx(1),
               		tx(2)		
		}	
        MAX-ACCESS  read-only
        STATUS      current
        DESCRIPTION "Direction of  mirror."
        ::= { mirrorSrcCpuEntry 2 }   
        
--xxx.100.12.3.1.3       
mirrorSrcCpuSlot   OBJECT-TYPE
	SYNTAX      INTEGER	
        MAX-ACCESS  read-only
        STATUS      current
        DESCRIPTION "Src cpu slot index."
        ::= { mirrorSrcCpuEntry 3 } 
        
--xxx.100.12.3.1.4       
mirrorSrcCpuStatus   OBJECT-TYPE
	SYNTAX      INTEGER
		    {
            	    
               		active(1),
               		destroy(2)		    	
		    }	
        MAX-ACCESS  read-create
        STATUS      current
        DESCRIPTION "Status."
        ::= { mirrorSrcCpuEntry 4 }         
 
--******************************************************************************************************** 
 
--xxx.100.12.4
mirrorReflectorPortTable OBJECT-TYPE 
    SYNTAX  SEQUENCE OF MirrorReflectorPortEntry
    MAX-ACCESS  not-accessible
    STATUS  current
    DESCRIPTION
        "mirror reflector destination port configuration Table of Rspan.
        The information about the reflector destination port and 
        its associated session will be specified by this table,which 
        will not present itself in the mirrorDestTable. Which means 
        the mirrorReflectorPortTable and the mirrorDestTable is 
        independent from each other."
    ::= { primirror   4}
 
--xxx.100.12.4.1
mirrorReflectorPortEntry OBJECT-TYPE
        SYNTAX  MirrorReflectorPortEntry
        MAX-ACCESS  not-accessible
        STATUS  current
        DESCRIPTION
            "mirror destination port configuration of Rspan."
        INDEX   { mirrorReflectorPortSession , mirrorReflectorPort }
        ::= { mirrorReflectorPortTable 1 }

MirrorReflectorPortEntry
        ::= SEQUENCE
            {
                mirrorReflectorPortSession           INTEGER,
                mirrorReflectorPort                  INTEGER,          
                mirrorReflectorPortStatus            INTEGER
            }                
        
        
--xxx.100.12.4.1.1       
mirrorReflectorPortSession   OBJECT-TYPE
	SYNTAX      INTEGER (1..4)	
        MAX-ACCESS  read-only
        STATUS      current
        DESCRIPTION "Session ID."
        ::= { mirrorReflectorPortEntry 1 }         

--xxx.100.12.4.1.2       
mirrorReflectorPort   OBJECT-TYPE
	SYNTAX      INTEGER		
        MAX-ACCESS  read-only
        STATUS      current
        DESCRIPTION "mirror reflector destination port number."
        ::= { mirrorReflectorPortEntry 2 }  
 
         
--xxx.100.12.4.1.3       
mirrorReflectorPortStatus   OBJECT-TYPE
	SYNTAX      INTEGER
		    {
            	    
               		active(1),
               		destroy(2)		    	
		    }	
        MAX-ACCESS  read-create
        STATUS      current
        DESCRIPTION "The configuration status of the reflector destination port and its associated session."
        ::= { mirrorReflectorPortEntry 3 }  
                   
--********************************************************************************************************

--xxx.100.12.5
mirrorRspanVlanTable OBJECT-TYPE 
    SYNTAX  SEQUENCE OF MirrorRspanVlanEntry
    MAX-ACCESS  not-accessible
    STATUS  current
    DESCRIPTION
        "Vlan configuration Table of Rspan."
    ::= { primirror   5}
 
--xxx.100.12.5.1
mirrorRspanVlanEntry OBJECT-TYPE
        SYNTAX  MirrorRspanVlanEntry
        MAX-ACCESS  not-accessible
        STATUS  current
        DESCRIPTION
            "Vlan configuration of Rspan."
        INDEX   { mirrorRspanVlan }
        ::= { mirrorRspanVlanTable 1 }

MirrorRspanVlanEntry
        ::= SEQUENCE
            {
                mirrorRspanVlan                INTEGER,
                mirrorRspanVlanStatus          INTEGER
            }
            
--xxx.100.12.5.1.1       
mirrorRspanVlan   OBJECT-TYPE
	SYNTAX      INTEGER 
        MAX-ACCESS  read-only
        STATUS      current
        DESCRIPTION "Vlan ID."
        ::= { mirrorRspanVlanEntry 1 } 

--xxx.100.12.5.1.2       
mirrorRspanVlanStatus   OBJECT-TYPE
	SYNTAX      INTEGER
		    {
            	    
               		active(1),
               		destroy(2)		    	
		    }	
        MAX-ACCESS  read-create
        STATUS      current
        DESCRIPTION "Vlan status."
        ::= { mirrorRspanVlanEntry 2 }     


--********************************************************************************************************
 
--xxx.100.12.6
mirrorRspanSessionTable OBJECT-TYPE 
    SYNTAX  SEQUENCE OF MirrorRspanSessionEntry
    MAX-ACCESS  not-accessible
    STATUS  current
    DESCRIPTION
        "Session configuration Table of Rspan.When creating an entry, 
        the correctness of both the Vlan ID an the Session ID should be ensured.
        When destroying an entry, only the correctness of the Session ID is required."
    ::= { primirror   6}
 
--xxx.100.12.6.1
mirrorRspanSessionEntry OBJECT-TYPE
        SYNTAX  MirrorRspanSessionEntry
        MAX-ACCESS  not-accessible
        STATUS  current
        DESCRIPTION
            "Session configuration of Rspan."
        INDEX   { mirrorRspanSession, mirrorRspanSessionVlan }
        ::= { mirrorRspanSessionTable 1 }

MirrorRspanSessionEntry
        ::= SEQUENCE
            { 
                mirrorRspanSession                  INTEGER,          
                mirrorRspanSessionVlan              INTEGER,               
                mirrorRspanSessionStatus            INTEGER
            }                

--xxx.100.12.6.1.1  
mirrorRspanSession   OBJECT-TYPE
	SYNTAX      INTEGER (1..4)	
        MAX-ACCESS  read-only
        STATUS      current
        DESCRIPTION "Session ID."
        ::= { mirrorRspanSessionEntry 1 }        
              
--xxx.100.12.6.1.2       
mirrorRspanSessionVlan   OBJECT-TYPE
	SYNTAX      INTEGER 
        MAX-ACCESS  read-only
        STATUS      current
        DESCRIPTION "Vlan ID."
        ::= { mirrorRspanSessionEntry 2 } 
        
--xxx.100.12.6.1.3       
mirrorRspanSessionStatus  OBJECT-TYPE
	SYNTAX      INTEGER
		    {
            	    
               		active(1),
               		destroy(2)		    	
		    }	
        MAX-ACCESS  read-create
        STATUS      current
        DESCRIPTION "The configuration status of the mirror session and its associated Rspan Vlan."
        ::= { mirrorRspanSessionEntry 3 }             
                                     
                                               	                                     
--********************************************************************************************************
--********************************************************************************************************
--xxx.100.13.1 
    dhcpRelay                     OBJECT IDENTIFIER ::= { pridhcp 1 }

--xxx.100.13.1.1
        dhcpRelayForwardUdpBootps OBJECT-TYPE
            SYNTAX  INTEGER
            	{
               		bootps(1),
               		noBootps(0)              		           	
            	}
            MAX-ACCESS  read-create
            STATUS  current
            DESCRIPTION "if dhcp rely forward bootps udp broadcast packet,broadcast message bootps."
            ::= { dhcpRelay 1 } 


--xxx.100.13.1.2
dhcpRelayServerAddrTable OBJECT-TYPE
          SYNTAX      SEQUENCE OF DhcpRelayServerAddrEntry
          MAX-ACCESS  not-accessible
          STATUS      current
          DESCRIPTION "The role of DHCP Relay Agent is to forward requests 
                        and replies between server and client when they are not
                        in the same subnet. To enable DHCP Relay service user needs to 
                        specify Relay Server ip address and then restart DHCP Relay.
                        This Table is to specify Relay Server ip address, 
                        the maximum numbers of server ip address user can specify is 5.
                        To Restart DHCP Relay, please use the dhcpRelayRestart variable."
          ::= { dhcpRelay 2 }
          
--xxx.100.13.1.3.1
dhcpRelayServerAddrEntry OBJECT-TYPE
          SYNTAX      DhcpRelayServerAddrEntry
          MAX-ACCESS  not-accessible
          STATUS      current
          DESCRIPTION "A conceptual row of dhcpRelayServerAddrTable."
          INDEX { dhcpRelayServerAddrVlanId , dhcpRelayServerAddrIndex } 
          ::= { dhcpRelayServerAddrTable 1 }
          
DhcpRelayServerAddrEntry ::= SEQUENCE
{
     dhcpRelayServerAddrVlanId  INTEGER,
     dhcpRelayServerAddrIndex    INTEGER,
     dhcpRelayServerAddrServerIp IpAddress,
     dhcpRelayServerAddrStatus   INTEGER    
}

--xxx.100.13.1.3.1.1
dhcpRelayServerAddrVlanId OBJECT-TYPE
          SYNTAX      INTEGER
          MAX-ACCESS  not-accessible
          STATUS      current
          DESCRIPTION "The ID of VLAN interface used by this table entry."
          ::= { dhcpRelayServerAddrEntry 1 }       

--xxx.100.13.1.3.1.2
dhcpRelayServerAddrIndex OBJECT-TYPE
          SYNTAX      INTEGER
          MAX-ACCESS  not-accessible
          STATUS      current
          DESCRIPTION "The index of relay address set in the VLAN interface."
          ::= { dhcpRelayServerAddrEntry 2 }  

--xxx.100.13.1.3.1.3
dhcpRelayServerAddrServerIp OBJECT-TYPE
          SYNTAX      IpAddress
          MAX-ACCESS  read-write
          STATUS      current
          DESCRIPTION "Appoint the destination address used for DHCP relay."
          ::= { dhcpRelayServerAddrEntry 3 }  

--xxx.100.13.1.3.1.4
dhcpRelayServerAddrStatus OBJECT-TYPE
          SYNTAX      INTEGER
          	    {
               		active(1),
               		destroy(2)		    	
		    }
          MAX-ACCESS  read-write
          STATUS      current
          DESCRIPTION "Configuration status."
          ::= { dhcpRelayServerAddrEntry 4 }  

                     
--********************************************************************************************************

--xxx.100.13.2 
    dhcpServer                     OBJECT IDENTIFIER ::= { pridhcp 2 }

--xxx.100.13.2.1
        dhcpServerServiceStatus OBJECT-TYPE
            SYNTAX  INTEGER
            	    {
                        enable(1),
                        disable(0)
                    }
            MAX-ACCESS  read-create
            STATUS  current
            DESCRIPTION
                "Setting this to 1 to enable the dhcp server service.
                 Setting this to 2 to disable the dhcp server service."
            ::= { dhcpServer 1 } 
            
--xxx.100.13.2.2
        dhcploggingStatus OBJECT-TYPE
            SYNTAX  INTEGER
            	    {
                        enable(1),
                        disable(0)
                    }
            MAX-ACCESS  read-create
            STATUS  current
            DESCRIPTION
                "Setting this to 1 to enable the dhcp conflict logging. 
                 Setting this to 0 to disable the dhcp conflict logging."
            ::= { dhcpServer 2 } 
--********************************************************************************************************]

--xxx.100.13.2.3
    dhcpPool               		  OBJECT IDENTIFIER ::= { dhcpServer 3 }         
    
                     
--********************************************************************************************************

--xxx.100.13.2.3.1
dhcpPoolTable OBJECT-TYPE
          SYNTAX      SEQUENCE OF DhcpPoolEntry
          MAX-ACCESS  not-accessible
          STATUS      current
          DESCRIPTION "A dhcp pool is a collection of
                       user configuration such as option config-lease time                         
                        or dns-server IPs, a network address for network pool,
                        or a host IP plus a hardware address pair for host pool. 
                        However, a dhcp pool only can either be a network pool 
                        or a host pool, or none of them (such as that pool only 
                        containing option config no network address config 
                        or a host ip config as well)"
          ::= { dhcpPool 1 }
          
--xxx.100.13.2.3.1.1
dhcpPoolEntry OBJECT-TYPE
          SYNTAX      DhcpPoolEntry
          MAX-ACCESS  not-accessible
          STATUS      current
          DESCRIPTION "A conceptual row of dhcpPoolTable."
          INDEX { dhcpPoolPoolName }
          ::= { dhcpPoolTable 1 }

DhcpPoolEntry ::= SEQUENCE
{
     dhcpPoolPoolName  			DisplayString,
     dhcpPoolStatus 			INTEGER,
     dhcpPoolAddressType		INTEGER,
     dhcpPoolAddress  			IpAddress,
     dhcpPoolAddressPrefix 		IpAddress,
     dhcpPoolAddressStatus		INTEGER,
     dhcpPoolMacAddress 		DisplayString,
     dhcpPoolProType 			INTEGER,
     dhcpPoolMacStatus			INTEGER
}

--xxx.100.13.2.3.1.1.1
dhcpPoolPoolName OBJECT-TYPE
          SYNTAX      DisplayString(SIZE(1..32))
          MAX-ACCESS  not-accessible
          STATUS      current
          DESCRIPTION "PoolName, simply specify a string."
          ::= { dhcpPoolEntry 1 }  
          
--xxx.100.13.2.3.1.1.2          
dhcpPoolStatus OBJECT-TYPE
          SYNTAX      INTEGER
            	    {
               		active(1),
               		destroy(0)
            	    }  
          MAX-ACCESS  read-create
          STATUS      current
          DESCRIPTION "accession delete the pool,according to dhcpPoolName"
          ::= { dhcpPoolEntry 2 }  

--xxx.100.13.2.3.1.1.3          
dhcpPoolAddressType OBJECT-TYPE
          SYNTAX      INTEGER
            	    {
               		network(1),
               		host(2)
            	    }  
          MAX-ACCESS  read-create
          STATUS      current
          DESCRIPTION "configure dhcppool of address style"
          ::= { dhcpPoolEntry 3 }  
                                 
--xxx.100.13.2.3.1.1.4  
dhcpPoolAddress OBJECT-TYPE
          SYNTAX      IpAddress
          MAX-ACCESS  read-create
          STATUS      current
          DESCRIPTION "configurate dhcp pool.
           if dhcpPoolAddressType=1 configurate address range,
		       if dhcpPoolAddressType=2 configurate single address"
          ::= { dhcpPoolEntry 4 }  

--xxx.100.13.2.3.1.1.5
dhcpPoolAddressPrefix OBJECT-TYPE
          SYNTAX      IpAddress
          MAX-ACCESS  read-create
          STATUS      current
          DESCRIPTION "dhcp pool ip address prefix"
          ::= { dhcpPoolEntry 5 }  

--xxx.100.13.2.3.1.1.6          
dhcpPoolAddressStatus OBJECT-TYPE
          SYNTAX    INTEGER
            	    {
               		active(1),
               		destroy(0)
            	    }           
          MAX-ACCESS  read-create
          STATUS      current
          DESCRIPTION "address of configuration satus"
          ::= { dhcpPoolEntry 6 }    

--xxx.100.13.2.3.1.1.7
dhcpPoolMacAddress OBJECT-TYPE
          SYNTAX      DisplayString
          MAX-ACCESS  read-create
          STATUS      current
          DESCRIPTION "appoint user of hardware address.Condition: dhcpPoolAddressType(2)."
          ::= { dhcpPoolEntry 7 }  
          
--xxx.100.13.2.3.1.1.8          
dhcpPoolProType OBJECT-TYPE
          SYNTAX      INTEGER(1..255)
          MAX-ACCESS  read-create
          STATUS      current
          DESCRIPTION "RFC define protocol style of number express,Condition:dhcpPoolAddressType(2)."
          ::= { dhcpPoolEntry 8 } 
 
--xxx.100.13.2.3.1.1.9          
dhcpPoolMacStatus OBJECT-TYPE
          SYNTAX    INTEGER
            	    {
               		active(1),
               		destroy(0)
            	    }           
          MAX-ACCESS  read-create
          STATUS      current
          DESCRIPTION "hardware address configure status.Condition: dhcpPoolAddressType(2)."
          ::= { dhcpPoolEntry 9 }         
          
                                      
--********************************************************************************************************                                     
  
--xxx.100.13.2.3.2
dhcpPoolExpandTable OBJECT-TYPE
          SYNTAX      SEQUENCE OF DhcpPoolExpandEntry
          MAX-ACCESS  not-accessible
          STATUS      current
          DESCRIPTION "A dhcp pool is a collection of
                       user configuration such as option config-lease time                         
                        or dns-server IPs, a network address for network pool,
                        or a host IP plus a hardware address pair for host pool. 
                        However, a dhcp pool only can either be a network pool 
                        or a host pool, or none of them (such as that pool only 
                        containing option config no network address config 
                        or a host ip config as well)"
          ::= { dhcpPool 2 }
          
--xxx.100.13.2.3.2.1
dhcpPoolExpandEntry OBJECT-TYPE
          SYNTAX      DhcpPoolExpandEntry
          MAX-ACCESS  not-accessible
          STATUS      current
          DESCRIPTION "A conceptual row of dhcpPoolExpandTable."
          INDEX { dhcpPoolExpandName }
          ::= { dhcpPoolExpandTable 1 }

DhcpPoolExpandEntry ::= SEQUENCE
{
     dhcpPoolExpandName  		DisplayString,
     dhcpPoolNetbiosNodeType		INTEGER,
     dhcpPoolDomainName			DisplayString,
     dhcpPoolBootFile			DisplayString,
     dhcpPoolCLid			DisplayString,
     dhcpPoolCLname			DisplayString,
     dhcpPoolExpandstatus		INTEGER
}                                 
 
--xxx.100.13.2.3.2.1.1
dhcpPoolExpandName OBJECT-TYPE
          SYNTAX      DisplayString(SIZE(1..32))
          MAX-ACCESS  not-accessible
          STATUS      current
          DESCRIPTION "PoolName, simply specify a string which 
                      string size NO MORE THAN 8"
          ::= { dhcpPoolExpandEntry 1 } 
      
                    
--xxx.100.13.2.3.2.1.2         
dhcpPoolNetbiosNodeType OBJECT-TYPE
          SYNTAX      INTEGER(0..255)
          MAX-ACCESS  read-create
          STATUS      current
          DESCRIPTION "Configure DHCP client of node style. 
                      For example, Broadcast node 1, Peer-to-peer node 2, Mixed node 4, Hybrid node 8"
          ::= { dhcpPoolExpandEntry 2 }                     

--xxx.100.13.2.3.2.1.3         
dhcpPoolDomainName OBJECT-TYPE
          SYNTAX      DisplayString(SIZE(1..255))
          MAX-ACCESS  read-create
          STATUS      current
          DESCRIPTION "DHCP client configure domain name"
          ::= { dhcpPoolExpandEntry 3 }  

--xxx.100.13.2.3.2.1.4         
dhcpPoolBootFile OBJECT-TYPE
          SYNTAX      DisplayString(SIZE(1..255))
          MAX-ACCESS  read-create
          STATUS      current
          DESCRIPTION "configure DHCP client boot-file name"
          ::= { dhcpPoolExpandEntry 4 }
          
--xxx.100.13.2.3.2.1.5        
dhcpPoolCLid OBJECT-TYPE
          SYNTAX      DisplayString
          MAX-ACCESS  read-create
          STATUS      current
          DESCRIPTION "set dhcp pool client id.
		       Condition: the pool of address is handcraft bind"
          ::= { dhcpPoolExpandEntry 5 }
          
--xxx.100.13.2.3.2.1.6          
dhcpPoolCLname OBJECT-TYPE
          SYNTAX      DisplayString(SIZE(1..255))
          MAX-ACCESS  read-create
          STATUS      current
          DESCRIPTION "configure user name.
		       Condition: the pool address is handcraft bind."
          ::= { dhcpPoolExpandEntry 6 }  
                
--xxx.100.13.2.3.2.1.7        
dhcpPoolExpandstatus OBJECT-TYPE
          SYNTAX    INTEGER
            	    {
               		valid(0),
               		destroy(1)
            	    }           
          MAX-ACCESS  read-create
          STATUS      current
          DESCRIPTION "if configure is valid(0),and the list of all configuration operatation accession 
		       if configure is destroy(1),and the list of all configuration operation delet"
          ::= { dhcpPoolExpandEntry 7 }               
                                                         
--********************************************************************************************************       
      
--xxx.100.13.2.3.2.1.2
dhcpLeaseTimeTable OBJECT-TYPE
          SYNTAX      SEQUENCE OF DhcpLeaseTimeEntry
          MAX-ACCESS  not-accessible
          STATUS      current
          DESCRIPTION "configure rent term in address pool"
          ::= { dhcpServer 4 }
          
--xxx.100.13.2.4.1
dhcpLeaseTimeEntry OBJECT-TYPE
          SYNTAX      DhcpLeaseTimeEntry
          MAX-ACCESS  not-accessible
          STATUS      current
          DESCRIPTION "configure rent term in address pool"
          INDEX { dhcpLeaseTimePoolName }
          ::= { dhcpLeaseTimeTable 1 }

DhcpLeaseTimeEntry ::= SEQUENCE
{
     dhcpLeaseTimePoolName  		DisplayString,
     dhcpLeaseTimeType 			INTEGER,
     dhcpLeaseTimeDay  			INTEGER,
     dhcpLeaseTimeHours 		INTEGER,
     dhcpLeaseTimeMinutes 		INTEGER,
     dhcpLeaseTimeStatus 		INTEGER
}

--xxx.100.13.2.4.1.1
dhcpLeaseTimePoolName OBJECT-TYPE
          SYNTAX      DisplayString(SIZE(1..32))
          MAX-ACCESS  not-accessible
          STATUS      current
          DESCRIPTION "PoolName, simply specify a string which 
                      string size NO MORE THAN 8"
          ::= { dhcpLeaseTimeEntry 1 }            
          
--xxx.100.13.2.4.1.2
dhcpLeaseTimeType  OBJECT-TYPE
          SYNTAX      INTEGER
          	      {
          	      	temp(0),
          	      	infinite(1)
          	      }
          MAX-ACCESS  read-create
          STATUS      current
          DESCRIPTION "rent time style,0 is temporarily rent,1 is forever rent"
          ::= { dhcpLeaseTimeEntry 2 }     

--xxx.100.13.2.4.1.3
dhcpLeaseTimeDay  OBJECT-TYPE
          SYNTAX      INTEGER(0..365)
          MAX-ACCESS  read-create
          STATUS      current
          DESCRIPTION "day,condition:dhcpLeaseTimeType=temp(0)."
          ::= { dhcpLeaseTimeEntry 3 }  
          
--xxx.100.13.2.4.1.4
dhcpLeaseTimeHours  OBJECT-TYPE
          SYNTAX      INTEGER(0..23)
          MAX-ACCESS  read-create
          STATUS      current
          DESCRIPTION "hour,condition:dhcpLeaseTimeType=temp(0)."
          ::= { dhcpLeaseTimeEntry 4 }           
          
--xxx.100.13.2.4.1.5
dhcpLeaseTimeMinutes  OBJECT-TYPE
          SYNTAX      INTEGER(0..59)
          MAX-ACCESS  read-create
          STATUS      current
          DESCRIPTION "hour,condition:dhcpLeaseTimeType=temp(0)."
          ::= { dhcpLeaseTimeEntry 5 }  
          
--xxx.100.13.2.4.1.6A
dhcpLeaseTimeStatus  OBJECT-TYPE
          SYNTAX    INTEGER
            	    {
            	    	createAndGo(0),
               		active(1),
               		destroy(2)
            	    }          
          MAX-ACCESS  read-create
          STATUS      current
          DESCRIPTION "Setting this to active(1) creates an entry.
                       Setting this to destroy(2) destroys an entry.
		       default status is 0,no opperation"
          ::= { dhcpLeaseTimeEntry 6 }   
                                                                  
--********************************************************************************************************          

--xxx.100.13.2.5
dhcpPoolOptionTable OBJECT-TYPE
          SYNTAX      SEQUENCE OF DhcpPoolOptionEntry
          MAX-ACCESS  not-accessible
          STATUS      current
          DESCRIPTION "configure pool of optional parameters"
          ::= { dhcpServer 5 }
          
--xxx.100.13.2.5.1
dhcpPoolOptionEntry OBJECT-TYPE
          SYNTAX      DhcpPoolOptionEntry
          MAX-ACCESS  not-accessible
          STATUS      current
          DESCRIPTION "configure pool of optional parameters"
          INDEX { dhcpPoolOptionName, dhcpPoolOptionIndex }
          ::= { dhcpPoolOptionTable 1 }

DhcpPoolOptionEntry ::= SEQUENCE
{
     dhcpPoolOptionName  	DisplayString,
     dhcpPoolOptionIndex	INTEGER,
     dhcpPoolOptionId 		INTEGER,
     dhcpPoolOptionType  	INTEGER,
     dhcpPoolOption 		DisplayString,
     dhcpPoolOptionStatus 	INTEGER
}

--xxx.100.13.2.5.1.1
dhcpPoolOptionName OBJECT-TYPE
          SYNTAX      DisplayString(SIZE(1..32))
          MAX-ACCESS  not-accessible
          STATUS      current
          DESCRIPTION "PoolName, simply specify a string which 
                      string size NO MORE THAN 8"
          ::= { dhcpPoolOptionEntry 1 }     

--xxx.100.13.2.5.1.2
dhcpPoolOptionIndex OBJECT-TYPE
          SYNTAX      INTEGER
          MAX-ACCESS  not-accessible
          STATUS      current
          DESCRIPTION "The index of option which has been set in this pool"
          ::= { dhcpPoolOptionEntry 2 } 

--xxx.100.13.2.5.1.3
dhcpPoolOptionId OBJECT-TYPE
          SYNTAX      INTEGER(0..254)
          MAX-ACCESS  read-create
          STATUS      current
          DESCRIPTION "dhcpPoolOptionId (0..254)"
          ::= { dhcpPoolOptionEntry 3 }   

--xxx.100.13.2.5.1.4
dhcpPoolOptionType OBJECT-TYPE
          SYNTAX      INTEGER
            	    {
            	    	ascii(1),
               		hex(2),
               		ipaddress(3)
            	    }
          MAX-ACCESS  read-create
          STATUS      current
          DESCRIPTION "dhcpPoolOptionType"
          ::= { dhcpPoolOptionEntry 4 }   

--xxx.100.13.2.5.1.5
dhcpPoolOption OBJECT-TYPE
          SYNTAX      DisplayString
          MAX-ACCESS  read-create
          STATUS      current
          DESCRIPTION "
           if dhcpPoolOptionType=1, ASCII string
		       if dhcpPoolOptionType=2, HEX string
		       if dhcpPoolOptionType=3,IP address"
          ::= { dhcpPoolOptionEntry 5 }             

--xxx.100.13.2.5.1.6
dhcpPoolOptionStatus OBJECT-TYPE
          SYNTAX    INTEGER
            	    {
            	    	createAndGo(0),
               		active(1),
               		destroy(2)
            	    } 
          MAX-ACCESS  read-create
          STATUS      current
          DESCRIPTION "optional parameters configure status"
          ::= { dhcpPoolOptionEntry 6 }            
                                                                            
--********************************************************************************************************

--xxx.100.13.2.6
dhcpServerExcludedIpAddrTable OBJECT-TYPE
          SYNTAX      SEQUENCE OF DhcpServerExcludedIpAddrEntry
          MAX-ACCESS  not-accessible
          STATUS      current
          DESCRIPTION "dhcpServer Excluded IpAddr Table"
          ::= { dhcpServer 6 }
          
--xxx.100.13.2.6.1
dhcpServerExcludedIpAddrEntry OBJECT-TYPE
          SYNTAX      DhcpServerExcludedIpAddrEntry
          MAX-ACCESS  not-accessible
          STATUS      current
          DESCRIPTION "dhcpServer Excluded IpAddrEntry"
          INDEX { dhcpServerExcludedIpAddrLowIp , dhcpServerExcludedIpAddrHiIp }
          ::= { dhcpServerExcludedIpAddrTable 1 }

DhcpServerExcludedIpAddrEntry ::= SEQUENCE
{
     dhcpServerExcludedIpAddrLowIp  	IpAddress,
     dhcpServerExcludedIpAddrHiIp 	IpAddress,
     dhcpServerExcludedIpAddrStatus  	INTEGER
}

--xxx.100.13.2.6.2
dhcpServerExcludedIpAddrLowIp OBJECT-TYPE
          SYNTAX      IpAddress
          MAX-ACCESS  not-accessible
          STATUS      current
          DESCRIPTION "The excluded IP address, 
                        or first IP address in an excluded address range."
          ::= { dhcpServerExcludedIpAddrEntry 1 }  
                
--xxx.100.13.2.6.3
dhcpServerExcludedIpAddrHiIp OBJECT-TYPE
          SYNTAX      IpAddress
          MAX-ACCESS  not-accessible
          STATUS      current
          DESCRIPTION "The last IP address in the excluded address range."
          ::= { dhcpServerExcludedIpAddrEntry 2 }   

--xxx.100.13.2.6.4
dhcpServerExcludedIpAddrStatus OBJECT-TYPE
          SYNTAX    INTEGER
            	    {
            	    	createAndGo(0),
               		active(1),
               		destroy(2)
            	    } 
          MAX-ACCESS  read-create
          STATUS      current
          DESCRIPTION "Setting this to active(1) creates an entry.
                       Setting this to destroy(2) destroys an entry."
          ::= { dhcpServerExcludedIpAddrEntry 3 } 

--********************************************************************************************************

--xxx.100.13.2.8
dhcpPoolDnsSerTable OBJECT-TYPE
          SYNTAX      SEQUENCE OF DhcpPoolDnsSerEntry
          MAX-ACCESS  not-accessible
          STATUS      current
          DESCRIPTION " dhcpPool Dns Server Table:the maximum 8 dns is allowed
			the first dns server has the highest priority.so address1 is highest priority,next is address2,address3..."
          ::= { dhcpServer 8 }
          
--xxx.100.13.2.8.1
dhcpPoolDnsSerEntry OBJECT-TYPE
          SYNTAX      DhcpPoolDnsSerEntry
          MAX-ACCESS  not-accessible
          STATUS      current
          DESCRIPTION "is DHCP client configure DNS server"
          INDEX { dhcpPoolDnsSerPoolName }
          ::= { dhcpPoolDnsSerTable 1 }

DhcpPoolDnsSerEntry ::= SEQUENCE
{
     dhcpPoolDnsSerPoolName  	DisplayString,
     dhcpPoolDnsSerIpAddress1 	IpAddress,
     dhcpPoolDnsSerIpAddress2  	IpAddress,
     dhcpPoolDnsSerIpAddress3	IpAddress,
     dhcpPoolDnsSerIpAddress4	IpAddress,
     dhcpPoolDnsSerIpAddress5	IpAddress,
     dhcpPoolDnsSerIpAddress6	IpAddress,
     dhcpPoolDnsSerIpAddress7	IpAddress,
     dhcpPoolDnsSerIpAddress8	IpAddress,
     dhcpPoolDnsSerStatus	INTEGER
}

--xxx.100.13.2.8.1
dhcpPoolDnsSerPoolName OBJECT-TYPE
          SYNTAX      DisplayString
          MAX-ACCESS  not-accessible
          STATUS      current
          DESCRIPTION "PoolName, simply specify a string which 
                      string size NO MORE THAN 8"
          ::= { dhcpPoolDnsSerEntry 1 } 
          
--xxx.100.13.2.8.2
dhcpPoolDnsSerIpAddress1 OBJECT-TYPE
          SYNTAX      IpAddress
          MAX-ACCESS  read-create
          STATUS      current
          DESCRIPTION "IP address,MUST."
          ::= { dhcpPoolDnsSerEntry 2 }          
          
--xxx.100.13.2.8.3
dhcpPoolDnsSerIpAddress2 OBJECT-TYPE
          SYNTAX      IpAddress
          MAX-ACCESS  read-create
          STATUS      current
          DESCRIPTION "IP address,option"
          ::= { dhcpPoolDnsSerEntry 3 }          
          
--xxx.100.13.2.8.4
dhcpPoolDnsSerIpAddress3 OBJECT-TYPE
          SYNTAX      IpAddress
          MAX-ACCESS  read-create
          STATUS      current
          DESCRIPTION "IP address,option"
          ::= { dhcpPoolDnsSerEntry 4 }          
          
--xxx.100.13.2.8.5
dhcpPoolDnsSerIpAddress4 OBJECT-TYPE
          SYNTAX      IpAddress
          MAX-ACCESS  read-create
          STATUS      current
          DESCRIPTION "IP address,option"
          ::= { dhcpPoolDnsSerEntry 5 }          
          
--xxx.100.13.2.8.6
dhcpPoolDnsSerIpAddress5 OBJECT-TYPE
          SYNTAX      IpAddress
          MAX-ACCESS  read-create
          STATUS      current
          DESCRIPTION "IP address,option"
          ::= { dhcpPoolDnsSerEntry 6 }          
          
--xxx.100.13.2.8.7
dhcpPoolDnsSerIpAddress6 OBJECT-TYPE
          SYNTAX      IpAddress
          MAX-ACCESS  read-create
          STATUS      current
          DESCRIPTION "IP address,option"
          ::= { dhcpPoolDnsSerEntry 7 }          
          
--xxx.100.13.2.8.8
dhcpPoolDnsSerIpAddress7 OBJECT-TYPE
          SYNTAX      IpAddress
          MAX-ACCESS  read-create
          STATUS      current
          DESCRIPTION "IP address,option"
          ::= { dhcpPoolDnsSerEntry 8 }          

--xxx.100.13.2.8.9
dhcpPoolDnsSerIpAddress8 OBJECT-TYPE
          SYNTAX      IpAddress
          MAX-ACCESS  read-create
          STATUS      current
          DESCRIPTION "IP address,option"
          ::= { dhcpPoolDnsSerEntry 9 }  

--xxx.100.13.2.8.10
dhcpPoolDnsSerStatus OBJECT-TYPE
          SYNTAX    INTEGER
            	    {
            	    	createAndGo(0),
               		active(1),
               		destroy(2)
            	    } 
          MAX-ACCESS  read-create
          STATUS      current
          DESCRIPTION "configure DNS server status"
          ::= { dhcpPoolDnsSerEntry 10 }            
          
--********************************************************************************************************


--xxx.100.13.2.9
dhcpPoolDefaultRouterTable OBJECT-TYPE
          SYNTAX      SEQUENCE OF DhcpPoolDefaultRouterEntry
          MAX-ACCESS  not-accessible
          STATUS      current
          DESCRIPTION "dhcpPoolDefaultRouterTable:
          the maximum 8 default gateway address can be set,the first gateway has the highest priority,
          So address1 has the highest priority,next is address2,address3..."
          ::= { dhcpServer 9 }
          
--xxx.100.13.2.9.1
dhcpPoolDefaultRouterEntry OBJECT-TYPE
          SYNTAX      DhcpPoolDefaultRouterEntry
          MAX-ACCESS  not-accessible
          STATUS      current
          DESCRIPTION "DHCP client machine configure default gateway"
          INDEX { dhcpPoolDnsSerPoolName }
          ::= { dhcpPoolDefaultRouterTable 1 }

DhcpPoolDefaultRouterEntry ::= SEQUENCE
{
     dhcpPoolDefaultRouterPoolName  	DisplayString,
     dhcpPoolDefaultRouterIpAddress1 	IpAddress,
     dhcpPoolDefaultRouterIpAddress2  	IpAddress,
     dhcpPoolDefaultRouterIpAddress3	IpAddress,
     dhcpPoolDefaultRouterIpAddress4	IpAddress,
     dhcpPoolDefaultRouterIpAddress5	IpAddress,
     dhcpPoolDefaultRouterIpAddress6	IpAddress,
     dhcpPoolDefaultRouterIpAddress7	IpAddress,
     dhcpPoolDefaultRouterIpAddress8	IpAddress,
     dhcpPoolDefaultRouterStatus	INTEGER
}

--xxx.100.13.2.9.1
dhcpPoolDefaultRouterPoolName OBJECT-TYPE
          SYNTAX      DisplayString
          MAX-ACCESS  not-accessible
          STATUS      current
          DESCRIPTION "PoolName, simply specify a string which 
                      string size NO MORE THAN 8"
          ::= { dhcpPoolDefaultRouterEntry 1 } 
          
--xxx.100.13.2.9.2
dhcpPoolDefaultRouterIpAddress1 OBJECT-TYPE
          SYNTAX      IpAddress
          MAX-ACCESS  read-create
          STATUS      current
          DESCRIPTION "IP address,must"
          ::= { dhcpPoolDefaultRouterEntry 2 }          
          
--xxx.100.13.2.9.3
dhcpPoolDefaultRouterIpAddress2 OBJECT-TYPE
          SYNTAX      IpAddress
          MAX-ACCESS  read-create
          STATUS      current
          DESCRIPTION "IP address,option"
          ::= { dhcpPoolDefaultRouterEntry 3 }          
          
--xxx.100.13.2.9.4
dhcpPoolDefaultRouterIpAddress3 OBJECT-TYPE
          SYNTAX      IpAddress
          MAX-ACCESS  read-create
          STATUS      current
          DESCRIPTION "IP address,option"
          ::= { dhcpPoolDefaultRouterEntry 4 }          
          
--xxx.100.13.2.9.5
dhcpPoolDefaultRouterIpAddress4 OBJECT-TYPE
          SYNTAX      IpAddress
          MAX-ACCESS  read-create
          STATUS      current
          DESCRIPTION "IP address,option"
          ::= { dhcpPoolDefaultRouterEntry 5 }          
          
--xxx.100.13.2.9.6
dhcpPoolDefaultRouterIpAddress5 OBJECT-TYPE
          SYNTAX      IpAddress
          MAX-ACCESS  read-create
          STATUS      current
          DESCRIPTION "IP address,option"
          ::= { dhcpPoolDefaultRouterEntry 6 }          
          
--xxx.100.13.2.9.7
dhcpPoolDefaultRouterIpAddress6 OBJECT-TYPE
          SYNTAX      IpAddress
          MAX-ACCESS  read-create
          STATUS      current
          DESCRIPTION "IP address,option"
          ::= { dhcpPoolDefaultRouterEntry 7 }          
          
--xxx.100.13.2.8.8
dhcpPoolDefaultRouterIpAddress7 OBJECT-TYPE
          SYNTAX      IpAddress
          MAX-ACCESS  read-create
          STATUS      current
          DESCRIPTION "IP address,option"
          ::= { dhcpPoolDefaultRouterEntry 8 }          

--xxx.100.13.2.9.9
dhcpPoolDefaultRouterIpAddress8 OBJECT-TYPE
          SYNTAX      IpAddress
          MAX-ACCESS  read-create
          STATUS      current
          DESCRIPTION "IP address,option"
          ::= { dhcpPoolDefaultRouterEntry 9 }  

--xxx.100.13.2.9.10
dhcpPoolDefaultRouterStatus OBJECT-TYPE
          SYNTAX    INTEGER
            	    {
            	    	createAndGo(0),
               		active(1),
               		destroy(2)
            	    } 
          MAX-ACCESS  read-create
          STATUS      current
          DESCRIPTION "configure default gateway state machine"
          ::= { dhcpPoolDefaultRouterEntry 10 }  
--********************************************************************************************************


--xxx.100.13.2.10
dhcpPoolNextServerTable OBJECT-TYPE
          SYNTAX      SEQUENCE OF DhcpPoolNextServerEntry
          MAX-ACCESS  not-accessible
          STATUS      current
          DESCRIPTION "dhcpPoolNextServerTable"
          ::= { dhcpServer 10 }
          
--xxx.100.13.2.10.1
dhcpPoolNextServerEntry OBJECT-TYPE
          SYNTAX      DhcpPoolNextServerEntry
          MAX-ACCESS  not-accessible
          STATUS      current
          DESCRIPTION "dhcpPoolNextServerEntry"
          INDEX { dhcpPoolNextServerPoolName }
          ::= { dhcpPoolNextServerTable  1 }

DhcpPoolNextServerEntry ::= SEQUENCE
{
     dhcpPoolNextServerPoolName  	DisplayString,
     dhcpPoolNextServerIpAddress1 	IpAddress,
     dhcpPoolNextServerIpAddress2  	IpAddress,
     dhcpPoolNextServerIpAddress3	IpAddress,
     dhcpPoolNextServerIpAddress4	IpAddress,
     dhcpPoolNextServerIpAddress5	IpAddress,
     dhcpPoolNextServerIpAddress6	IpAddress,
     dhcpPoolNextServerIpAddress7	IpAddress,
     dhcpPoolNextServerIpAddress8	IpAddress,
     dhcpPoolNextServerStatus	INTEGER
}

--xxx.100.13.2.10.1
dhcpPoolNextServerPoolName OBJECT-TYPE
          SYNTAX      DisplayString
          MAX-ACCESS  not-accessible
          STATUS      current
          DESCRIPTION "PoolName, simply specify a string which 
                      string size NO MORE THAN 8"
          ::= { dhcpPoolNextServerEntry 1 } 
          
--xxx.100.13.2.10.2
dhcpPoolNextServerIpAddress1 OBJECT-TYPE
          SYNTAX      IpAddress
          MAX-ACCESS  read-create
          STATUS      current
          DESCRIPTION "IP address,must"
          ::= { dhcpPoolNextServerEntry 2 }          
          
--xxx.100.13.2.10.3
dhcpPoolNextServerIpAddress2 OBJECT-TYPE
          SYNTAX      IpAddress
          MAX-ACCESS  read-create
          STATUS      current
          DESCRIPTION "IP address,option"
          ::= { dhcpPoolNextServerEntry 3 }          
          
--xxx.100.13.2.10.4
dhcpPoolNextServerIpAddress3 OBJECT-TYPE
          SYNTAX      IpAddress
          MAX-ACCESS  read-create
          STATUS      current
          DESCRIPTION "IP address,option"
          ::= { dhcpPoolNextServerEntry 4 }          
          
--xxx.100.13.2.10.5
dhcpPoolNextServerIpAddress4 OBJECT-TYPE
          SYNTAX      IpAddress
          MAX-ACCESS  read-create
          STATUS      current
          DESCRIPTION "IP address,option"
          ::= { dhcpPoolNextServerEntry 5 }          
          
--xxx.100.13.2.10.6
dhcpPoolNextServerIpAddress5 OBJECT-TYPE
          SYNTAX      IpAddress
          MAX-ACCESS  read-create
          STATUS      current
          DESCRIPTION "IP address,option"
          ::= { dhcpPoolNextServerEntry 6 }          
          
--xxx.100.13.2.10.7
dhcpPoolNextServerIpAddress6 OBJECT-TYPE
          SYNTAX      IpAddress
          MAX-ACCESS  read-create
          STATUS      current
          DESCRIPTION "IP address,option"
          ::= { dhcpPoolNextServerEntry 7 }          
          
--xxx.100.13.2.10.8
dhcpPoolNextServerIpAddress7 OBJECT-TYPE
          SYNTAX      IpAddress
          MAX-ACCESS  read-create
          STATUS      current
          DESCRIPTION "IP address,option"
          ::= { dhcpPoolNextServerEntry 8 }          

--xxx.100.13.2.10.9
dhcpPoolNextServerIpAddress8 OBJECT-TYPE
          SYNTAX      IpAddress
          MAX-ACCESS  read-create
          STATUS      current
          DESCRIPTION "IP address,option"
          ::= { dhcpPoolNextServerEntry 9 }  

--xxx.100.13.2.10.10
dhcpPoolNextServerStatus OBJECT-TYPE
          SYNTAX    INTEGER
            	    {
            	    	createAndGo(0),
               		active(1),
               		destroy(2)
            	    } 
          MAX-ACCESS  read-create
          STATUS      current
          DESCRIPTION "status machine"
          ::= { dhcpPoolNextServerEntry 10 }            
          
--********************************************************************************************************

--xxx.100.13.2.11
dhcpPoolWinsTable OBJECT-TYPE
          SYNTAX      SEQUENCE OF DhcpPoolWinsEntry
          MAX-ACCESS  not-accessible
          STATUS      current
          DESCRIPTION "dhcpPoolWinsTable"
          ::= { dhcpServer 11 }
          
--xxx.100.13.2.11.1
dhcpPoolWinsEntry OBJECT-TYPE
          SYNTAX      DhcpPoolWinsEntry
          MAX-ACCESS  not-accessible
          STATUS      current
          DESCRIPTION "configure Wins sever address"
          INDEX { dhcpPoolDnsSerPoolName }
          ::= { dhcpPoolWinsTable 1 }

DhcpPoolWinsEntry ::= SEQUENCE
{
     dhcpPoolWinsPoolName  	DisplayString,
     dhcpPoolWinsIpAddress1 	IpAddress,
     dhcpPoolWinsIpAddress2  	IpAddress,
     dhcpPoolWinsIpAddress3	IpAddress,
     dhcpPoolWinsIpAddress4	IpAddress,
     dhcpPoolWinsIpAddress5	IpAddress,
     dhcpPoolWinsIpAddress6	IpAddress,
     dhcpPoolWinsIpAddress7	IpAddress,
     dhcpPoolWinsIpAddress8	IpAddress,
     dhcpPoolWinsStatus		INTEGER
}

--xxx.100.13.2.11.1
dhcpPoolWinsPoolName OBJECT-TYPE
          SYNTAX      DisplayString
          MAX-ACCESS  not-accessible
          STATUS      current
          DESCRIPTION "PoolName, simply specify a string which 
                      string size NO MORE THAN 8"
          ::= { dhcpPoolWinsEntry 1 } 
          
--xxx.100.13.2.11.2
dhcpPoolWinsIpAddress1 OBJECT-TYPE
          SYNTAX      IpAddress
          MAX-ACCESS  read-create
          STATUS      current
          DESCRIPTION "IP address,must"
          ::= { dhcpPoolWinsEntry 2 }          
          
--xxx.100.13.2.11.3
dhcpPoolWinsIpAddress2 OBJECT-TYPE
          SYNTAX      IpAddress
          MAX-ACCESS  read-create
          STATUS      current
          DESCRIPTION "IP address,option"
          ::= { dhcpPoolWinsEntry 3 }          
          
--xxx.100.13.2.11.4
dhcpPoolWinsIpAddress3 OBJECT-TYPE
          SYNTAX      IpAddress
          MAX-ACCESS  read-create
          STATUS      current
          DESCRIPTION "IPaddress,option"
          ::= { dhcpPoolWinsEntry 4 }          
          
--xxx.100.13.2.11.5
dhcpPoolWinsIpAddress4 OBJECT-TYPE
          SYNTAX      IpAddress
          MAX-ACCESS  read-create
          STATUS      current
          DESCRIPTION "IP address,option"
          ::= { dhcpPoolWinsEntry 5 }          
          
--xxx.100.13.2.11.6
dhcpPoolWinsIpAddress5 OBJECT-TYPE
          SYNTAX      IpAddress
          MAX-ACCESS  read-create
          STATUS      current
          DESCRIPTION "IP address,option"
          ::= { dhcpPoolWinsEntry 6 }          
          
--xxx.100.13.2.11.7
dhcpPoolWinsIpAddress6 OBJECT-TYPE
          SYNTAX      IpAddress
          MAX-ACCESS  read-create
          STATUS      current
          DESCRIPTION "IP address,option"
          ::= { dhcpPoolWinsEntry 7 }          
          
--xxx.100.13.2.11.8
dhcpPoolWinsIpAddress7 OBJECT-TYPE
          SYNTAX      IpAddress
          MAX-ACCESS  read-create
          STATUS      current
          DESCRIPTION "IP address,option"
          ::= { dhcpPoolWinsEntry 8 }          

--xxx.100.13.2.11.9
dhcpPoolWinsIpAddress8 OBJECT-TYPE
          SYNTAX      IpAddress
          MAX-ACCESS  read-create
          STATUS      current
          DESCRIPTION "IP address,option"
          ::= { dhcpPoolWinsEntry 9 }  

--xxx.100.13.2.11.10
dhcpPoolWinsStatus OBJECT-TYPE
          SYNTAX    INTEGER
            	    {
            	    	createAndGo(0),
               		active(1),
               		destroy(2)
            	    } 
          MAX-ACCESS  read-create
          STATUS      current
          DESCRIPTION "configure wins server status machine"
          ::= { dhcpPoolWinsEntry 10 }  
--********************************************************************************************************

--xxx.100.13.2.12
dhcpServerLeaseBindingTable OBJECT-TYPE
          SYNTAX      SEQUENCE OF DhcpServerLeaseBindingEntry
          MAX-ACCESS  not-accessible
          STATUS      current
          DESCRIPTION "express IP address and MAC address bind status"
          ::= { dhcpServer 12 }
          
--xxx.100.13.2.12.1
dhcpServerLeaseBindingEntry OBJECT-TYPE
          SYNTAX      DhcpServerLeaseBindingEntry
          MAX-ACCESS  not-accessible
          STATUS      current
          DESCRIPTION "express IP address and MAC address bind status"
          INDEX { dhcpServerLeaseBindingIp, dhcpServerLeaseBindingType }
          ::= { dhcpServerLeaseBindingTable 1 }

DhcpServerLeaseBindingEntry ::= SEQUENCE
{
     dhcpServerLeaseBindingIp  		IpAddress,
     dhcpServerLeaseBindingType		INTEGER,     
     dhcpServerLeaseBindingMac 		DisplayString,
     dhcpServerLeaseBindingLeaseTime  	INTEGER
}

--xxx.100.13.2.12.1.1
dhcpServerLeaseBindingIp  OBJECT-TYPE
          SYNTAX      IpAddress
          MAX-ACCESS  read-only
          STATUS      current
          DESCRIPTION "certain address appointed, format is x.x.x.x"
          ::= { dhcpServerLeaseBindingEntry 1 }  

 
--xxx.100.13.2.12.1.2
dhcpServerLeaseBindingType  OBJECT-TYPE
          SYNTAX      INTEGER
          	      {
          	      	manual(1),
          	      	dynamic(2)
          	      }
          MAX-ACCESS  read-only
          STATUS      current
          DESCRIPTION "manual express handcraft bind style;dynamic express dynamic distribution style"
          ::= { dhcpServerLeaseBindingEntry 2 }  
  
--xxx.100.13.2.12.1.3
dhcpServerLeaseBindingMac  OBJECT-TYPE
          SYNTAX      DisplayString
          MAX-ACCESS  read-only
          STATUS      current
          DESCRIPTION "MAC address"
          ::= { dhcpServerLeaseBindingEntry 3 }    
  
--xxx.100.13.2.12.1.4
dhcpServerLeaseBindingLeaseTime  OBJECT-TYPE
          SYNTAX      INTEGER
          MAX-ACCESS  read-only
          STATUS      current
          DESCRIPTION "rent term"
          ::= { dhcpServerLeaseBindingEntry 4 }     
--******************************************************************************************************** 
--portGroupMgt
--xxx.100.14.1
	systemPriority OBJECT-TYPE
	    SYNTAX  INTEGER  (0..65535)        	
	    MAX-ACCESS  read-create
	    STATUS  current
	    DESCRIPTION
	        "Modify the system priority which is used by port group."
	    ::= { priportGroup  1 }
	    
--xxx.100.14.2
	portGroupTable  OBJECT-TYPE
    	    SYNTAX     SEQUENCE OF PortGroupEntry
            MAX-ACCESS not-accessible
    	    STATUS  current
            DESCRIPTION
        	"This table contains port group information associated 
        	with the local system known to this agent."
    	    ::= { priportGroup 2 }
    
--xxx.100.14.2.1
	portGroupEntry  OBJECT-TYPE
    	    SYNTAX     PortGroupEntry
    	    MAX-ACCESS not-accessible
    	    STATUS     current
    	    DESCRIPTION
        	"Configure the port group information."
    	   INDEX { portGroupIndex }
    	   ::= { portGroupTable 1 }
    
	PortGroupEntry ::= SEQUENCE {
	    portGroupIndex		INTEGER,
	    portGroupMemberCount        INTEGER,  
	    loadBalance                 INTEGER,
	    portGroupInfo    		DisplayString
	}

--xxx.100.14.2.1.1
	portGroupIndex  OBJECT-TYPE
	    SYNTAX     INTEGER
	    MAX-ACCESS not-accessible
	    STATUS     current
	    DESCRIPTION
	        "Port group number."
	    ::= { portGroupEntry 1 }

--xxx.100.14.2.1.2
	portGroupMemberCount  OBJECT-TYPE
	    SYNTAX     INTEGER
	    MAX-ACCESS read-only
	    STATUS     current
	    DESCRIPTION
	        "The number of port group member."
	    ::= { portGroupEntry 2 }

--xxx.100.14.2.1.3    
	loadBalance  OBJECT-TYPE
	    SYNTAX     INTEGER
	               {
	               	    dst-src-mac(1),
	               	    dst-src-ip(2),
	               	    src-mac(3),
	               	    dst-mac(4),
	               	    src-ip(5),
	               	    dst-ip(6),
	               	    dst-src-mac-ip(7)
	               }
	    MAX-ACCESS read-create
	    STATUS     current
	    DESCRIPTION
	        "Load balancing method:
	        dst-src-mac(1):destination and source mac address;
	        dst-src-ip(2):destination and source ip address;
	        src-mac(3):source mac address;
	        dst-mac(4):destination mac address;
	        src-ip(5):source ip address;
	        dst-ip(6):destination ip address;
	        dst-src-mac-ip(7):destination and source mac address, ip address.
	        If there is no member in the port group, the value is -1.
	        If you set value to the load balance method that your switch is not unsupported, it will return error. 
	        Please see the handbook and make sure that the load balance method is supported by your switch."
	    ::= { portGroupEntry 3 } 
	    
--xxx.100.14.2.1.4    
	portGroupInfo  OBJECT-TYPE
	    SYNTAX     DisplayString
	    MAX-ACCESS read-only
	    STATUS     current
	    DESCRIPTION
	        "Port group brief information. Format is ID, Mode, Partner ID, Ports and Load-balance.
	        If there is no member in the port group, the value is empty."
	    ::= { portGroupEntry 4 } 
	    
--xxx.100.14.3
	portGroupPortListTable  OBJECT-TYPE
    	    SYNTAX     SEQUENCE OF PortGroupPortListEntry
            MAX-ACCESS not-accessible
    	    STATUS  current
            DESCRIPTION
        	"This table contains port group member information associated 
        	with the local system known to this agent."
    	    ::= { priportGroup 3 }
    
--xxx.100.14.3.1
	portGroupPortListEntry  OBJECT-TYPE
    	    SYNTAX     PortGroupPortListEntry
    	    MAX-ACCESS not-accessible
    	    STATUS     current
    	    DESCRIPTION
        	"Configure the port group member information."
    	   INDEX { portGroupIndex, portGroupMemberIndex}
    	   ::= { portGroupPortListTable 1 }
    
	PortGroupPortListEntry ::= SEQUENCE {
	    portGroupMemberIndex        INTEGER,  
	    portGroupMemberName         DisplayString,
	    portGroupMemberMode    	INTEGER,
	    portGroupMemberPriority     INTEGER,
	    portGroupMemberTimeout      INTEGER,	    
	    portGroupMemberStatus       INTEGER
	}

--xxx.100.14.3.1.1
	portGroupMemberIndex  OBJECT-TYPE
	    SYNTAX     INTEGER
	    MAX-ACCESS not-accessible
	    STATUS     current
	    DESCRIPTION
	        "Port group member index. Format is group number and port index of member."
	    ::= { portGroupPortListEntry 1 }

--xxx.100.14.3.1.2    
	portGroupMemberName  OBJECT-TYPE
	    SYNTAX     DisplayString
	    MAX-ACCESS read-only
	    STATUS     current
	    DESCRIPTION
	        "The name of port group member."
	    ::= { portGroupPortListEntry 2 } 
	    
--xxx.100.14.3.1.3    
	portGroupMemberMode  OBJECT-TYPE
	    SYNTAX     INTEGER
	    {
	    			on(1),
	    			active(2),
	    			passive(3)
	    }
	    MAX-ACCESS read-only
	    STATUS     current
	    DESCRIPTION
	        "The mode of port group member."
	    ::= { portGroupPortListEntry 3 } 
	    
--xxx.100.14.3.1.4    
	portGroupMemberPriority  OBJECT-TYPE
	    SYNTAX     INTEGER (0..65535)
	    MAX-ACCESS read-write
	    STATUS     current
	    DESCRIPTION
	        "The port priority of port group member. If the port group mode is on, the value is -1."
	    ::= { portGroupPortListEntry 4 }
	    
--xxx.100.14.3.1.5    
	portGroupMemberTimeout  OBJECT-TYPE
	    SYNTAX     INTEGER 
	               {
	               	    long(0),
	               	    short(1)	               	    
	               }	    
	    MAX-ACCESS read-only
	    STATUS     current
	    DESCRIPTION
	        "The timeout mode of port group member. If the port group mode is on, the value is -1."
	    ::= { portGroupPortListEntry 5 }	     
	    
--xxx.100.14.3.1.6    
	portGroupMemberStatus  OBJECT-TYPE
	    SYNTAX     INTEGER 
	               {
	               	    unselected(1),
	               	    standby(2),
	               	    selected(3)
	               }	    
	    MAX-ACCESS read-only
	    STATUS     current
	    DESCRIPTION
	        "The status of port group member. If the port group mode is on, the value is -1."
	    ::= { portGroupPortListEntry 6 }	    	    	    	    

--******************************************************************************************************** 
--snmpMgt
--xxx.100.15.1
	snmpSecurityIpStatus OBJECT-TYPE
	    SYNTAX  INTEGER  
	    	   {
			enable(1),
			disable(0)
	            }         	
	    MAX-ACCESS  read-create
	    STATUS  current
	    DESCRIPTION
	        "Enable or disable secure IP address check function on the NMS."
	    ::= { prisnmpMgt  1 }
	    
--xxx.100.15.2            
	snmpTrapHostStatus OBJECT-TYPE
	    SYNTAX  INTEGER  
	    	   {
			enable(1),
			disable(0)
	            }         	
	    MAX-ACCESS  read-create
	    STATUS  current
	    DESCRIPTION
	        "Enable the switch to send Trap message.
	         This command is used for SNMP v1/v2."
	    ::= { prisnmpMgt  2 }  
	    
--xxx.100.15.3            
	snmpRmonStatus OBJECT-TYPE
	    SYNTAX  INTEGER  
	    	   {
			enable(1),
			disable(0)
	            }         	
	    MAX-ACCESS  read-create
	    STATUS  current
	    DESCRIPTION
	        "Enable/disable RMON."
	    ::= { prisnmpMgt  3 } 
	    
--******************************************************************************************************** 
   	    
--xxx.100.15.4
securityIpTable  OBJECT-TYPE
    SYNTAX     SEQUENCE OF SecurityIpEntry
    MAX-ACCESS not-accessible
    STATUS     current
    DESCRIPTION
        "A list of snmp securityIp entries."
    ::= { prisnmpMgt 4 }
    
--xxx.100.15.4.1
securityIpEntry  OBJECT-TYPE
    SYNTAX     SecurityIpEntry
    MAX-ACCESS not-accessible
    STATUS     current
    DESCRIPTION
        "Configure the secure IP address which is 
          allowed to access the switch on the NMS;"
    INDEX { securityIpIndex }
    ::= { securityIpTable 1 }
    
--xxx.100.15.4.1.1
SecurityIpEntry ::= SEQUENCE {
    securityIpIndex		INTEGER,
    securityIpAddress           IpAddress,  
    securityIpStatus            INTEGER
}

--xxx.100.15.4.1.1.2
securityIpIndex  OBJECT-TYPE
    SYNTAX     INTEGER
    MAX-ACCESS not-accessible
    STATUS     current
    DESCRIPTION
        "Index."
    ::= { securityIpEntry 1 }

--xxx.100.15.4.1.1.2
securityIpAddress  OBJECT-TYPE
    SYNTAX     IpAddress
    MAX-ACCESS read-create
    STATUS     current
    DESCRIPTION
        "The address of security."
    ::= { securityIpEntry 2 }

--xxx.100.15.4.1.1.3    
securityIpStatus  OBJECT-TYPE
    SYNTAX     INTEGER
               {
               	    active(1),
               	    destroy(2)
               }
    MAX-ACCESS read-create
    STATUS     current
    DESCRIPTION
        "Writing this to active(1) creates an entry.
         Writing this to destroy(2) destroys an entry."
    ::= { securityIpEntry 3 } 
  
--******************************************************************************************************** 
  
    	    
--xxx.100.15.5
trapDestTable  OBJECT-TYPE
    SYNTAX     SEQUENCE OF TrapDestEntry
    MAX-ACCESS not-accessible
    STATUS     current
    DESCRIPTION
        "A list of trap destination entries."
    ::= { prisnmpMgt 5 }
    
--xxx.100.15.5.1
trapDestEntry  OBJECT-TYPE
    SYNTAX     TrapDestEntry
    MAX-ACCESS not-accessible
    STATUS     current
    DESCRIPTION
        "This entry includes a destination IP address to which to send
        traps for this community."
    INDEX { trapDestIndex }
    ::= { trapDestTable 1 }
    
--xxx.100.15.5.1.1
TrapDestEntry ::= SEQUENCE {
    trapDestIndex		INTEGER,
    trapDestAddress             IpAddress,
    trapDestVersion             INTEGER,     
    trapDestCommunity           DisplayString,  
    trapDestStatus              INTEGER
}

--xxx.100.15.5.1.1.2
trapDestIndex  OBJECT-TYPE
    SYNTAX     INTEGER
    MAX-ACCESS not-accessible
    STATUS     current
    DESCRIPTION
        "Index"
    ::= { trapDestEntry 1 }

--xxx.100.15.5.1.1.2
trapDestAddress  OBJECT-TYPE
    SYNTAX     IpAddress
    MAX-ACCESS read-create
    STATUS     current
    DESCRIPTION
        "The address to send traps."
    ::= { trapDestEntry 2 }
    
--xxx.100.15.5.1.1.3
trapDestVersion OBJECT-TYPE
    SYNTAX     INTEGER
               {
                   version1(0),
                   version2(1)
               }
    MAX-ACCESS read-create
    STATUS     current
    DESCRIPTION
        "This variables represent the version of the Trap we wish to send to trap Receiver.
         If the value is 0, mean we wish to send Version 1 trap. If the value is 1,
         mean we wish to send version 2 trap. "
    ::= { trapDestEntry 3}
    
--xxx.100.15.5.1.1.4
trapDestCommunity  OBJECT-TYPE
    SYNTAX     DisplayString(SIZE(1..255))
    MAX-ACCESS read-create
    STATUS     current
    DESCRIPTION
        "A community to which this destination address belongs."
    ::= { trapDestEntry 4 }

--xxx.100.15.5.1.1.5    
trapDestStatus  OBJECT-TYPE
    SYNTAX     INTEGER
               {
               	    active(1),
               	    destroy(2)
               }
    MAX-ACCESS read-create
    STATUS     current
    DESCRIPTION
        "Writing this to active(1) creates an entry.
         Writing this to destroy(2) destroys an entry."
    ::= { trapDestEntry 5 }
--********************************************************************************************************
--******************************************************************************************************** 

--xxx.100.16.1
    arpMgt               		  OBJECT IDENTIFIER ::= { l3 1 }
--xxx.100.16.2
    routeMgt               		  OBJECT IDENTIFIER ::= { l3 2 }    
--xxx.100.16.1.1
        arpCacheDeleteAll OBJECT-TYPE
            SYNTAX  INTEGER  
            	   {
			delete(1), -- trigger clear all arp cache
			noDelete(0)-- when then snmp agent read this node, the value is meaningless
                    }         	
            MAX-ACCESS  read-create
            STATUS  current
            DESCRIPTION
                "when set , triger flush arp-cache, when get ,nosense"
            ::= { arpMgt  1 }

--xxx.100.16.1.2
        arpCacheTimeout OBJECT-TYPE
            SYNTAX  INTEGER                      
            MAX-ACCESS  read-only
            STATUS  current
            DESCRIPTION
                "arp cache timeout time"
            ::= { arpMgt  2 }     
--xxx.100.16.1.3
        arpSecurityUpdateProtectALL OBJECT-TYPE
            SYNTAX  INTEGER 
            	   {
			enable(1),
			disable(0)
                    }                       	
            MAX-ACCESS  read-create
            STATUS  current
            DESCRIPTION
                "global enable or disable arp security update protect"
            ::= { arpMgt  3 }

--xxx.100.16.1.4
        arpSecurityLearnProtectALL OBJECT-TYPE
            SYNTAX  INTEGER 
            	   {
			enable(1),
			disable(0)
                    }               
            MAX-ACCESS  read-create
            STATUS  current
            DESCRIPTION
                "global enable or disable arp security learn protect"
            ::= { arpMgt  4 }  
--xxx.100.16.1.5
        arpSecurityConvertALL OBJECT-TYPE
            SYNTAX  INTEGER   
            	   {
			enable(1),
			disable(0)
                    }                     	
            MAX-ACCESS  read-create
            STATUS  current
            DESCRIPTION
                "global convert dynamic arp-cache to static arp item .enable mean convert"
            ::= { arpMgt  5 }    


--xxx.100.16.1.6
arpSecurityTable OBJECT-TYPE 
    SYNTAX  SEQUENCE OF ArpsecurityEntry
    MAX-ACCESS  not-accessible
    STATUS  current
    DESCRIPTION
        "arp security table"
    ::= { arpMgt   6}
            
--xxx.100.16.1.6.1
arpsecurityEntry OBJECT-TYPE
        SYNTAX  ArpsecurityEntry
        MAX-ACCESS  not-accessible
        STATUS  current
        DESCRIPTION
            " index is L3 interface index"
        INDEX   { arpSecurityIfindex}
        ::= { arpSecurityTable 1 }

ArpsecurityEntry
        ::= SEQUENCE
            {
                arpSecurityIfindex               		INTEGER,
                arpSecurityUpdateProtect			INTEGER,
                arpSecurityLearnProtect				INTEGER,
                arpSecurityConvert				INTEGER
            }
            
--xxx.100.16.1.6.1.1
arpSecurityIfindex  OBJECT-TYPE
            SYNTAX  INTEGER 
            MAX-ACCESS  not-accessible
            STATUS  current
            DESCRIPTION
                "L3 interface index"
            ::= { arpsecurityEntry 1 }
            
--xxx.100.16.1.6.1.2         
arpSecurityUpdateProtect  OBJECT-TYPE
	SYNTAX      INTEGER
            	   {
			enable(1),
			disable(0)
                    }   	
        MAX-ACCESS  read-create
        STATUS      current
        DESCRIPTION 
                "enable or disable arp security update protect on the current port"
        ::= { arpsecurityEntry 2 }
        
--xxx.100.16.1.6.1.3         
arpSecurityLearnProtect  OBJECT-TYPE 
        SYNTAX      INTEGER 
            	   {
			enable(1),
			disable(0)
                    }           
        MAX-ACCESS  read-create
        STATUS      current
        DESCRIPTION 
                "enable or disable arp security learn protect on the current port"
        ::= { arpsecurityEntry 3 }  
--xxx.100.16.1.6.1.4         
arpSecurityConvert  OBJECT-TYPE
        SYNTAX      INTEGER 
            	   {
			enable(1),
			disable(0)
                    }           
        MAX-ACCESS  read-create
        STATUS      current
        DESCRIPTION "convert dynamic arp-cache to static arp item on the port.enable mean convert,get OPS is nosense"
        ::= { arpsecurityEntry 4 }     
        
        

--xxx.100.16.1.7
arpProxyArpTable OBJECT-TYPE 
    SYNTAX  SEQUENCE OF ArpProxyArpEntry
    MAX-ACCESS  not-accessible
    STATUS  current
    DESCRIPTION
        " configure arp proxy list"
    ::= { arpMgt   7}
            
--xxx.100.16.1.7.1
arpProxyArpEntry OBJECT-TYPE
        SYNTAX  ArpProxyArpEntry
        MAX-ACCESS  not-accessible
        STATUS  current
        DESCRIPTION
            " index is L3 interface index"
        INDEX   { arpProxyArpIfIndex}
        ::= { arpProxyArpTable 1 }

ArpProxyArpEntry
        ::= SEQUENCE
            {
                arpProxyArpIfIndex               		INTEGER,
                arpProxyArpStatus				INTEGER
            }
            
--xxx.100.16.1.7.1.1
arpProxyArpIfIndex  OBJECT-TYPE
            SYNTAX  INTEGER 
            MAX-ACCESS  not-accessible
            STATUS  current
            DESCRIPTION
                " L3 interface index"
            ::= { arpProxyArpEntry 1 }
            
--xxx.100.16.1.7.1.2         
arpProxyArpStatus  OBJECT-TYPE
	SYNTAX      INTEGER
            	   {
			enable(1),
			disable(0)
                    }   	
        MAX-ACCESS  read-create
        STATUS      current
        DESCRIPTION "arp proxy enable"
        ::= { arpProxyArpEntry 2 }                 
        
        
--xxx.100.16.1.7
arpStacticTable OBJECT-TYPE 
    SYNTAX  SEQUENCE OF ArpStaticEntry
    MAX-ACCESS  not-accessible
    STATUS  current
    DESCRIPTION
        " static state arp configuration list"
    ::= { arpMgt   8}
            
--xxx.100.16.1.8.1
arpStaticEntry OBJECT-TYPE
        SYNTAX  ArpStaticEntry
        MAX-ACCESS  not-accessible
        STATUS  current
        DESCRIPTION
            " index is 'arpProxyArpIfIndex.arpStaticIpaddress'."
        INDEX   { arpProxyArpIfIndex,arpStaticIpaddress}
        ::= { arpStacticTable 1 }

ArpStaticEntry
        ::= SEQUENCE
            {
                arpStaticIfindex               		INTEGER,
                arpStaticIpaddress			IpAddress,
                arpStaticMac				MacAddress,
                arpStaticPortIndex			INTEGER,
                arpStaticStatus				INTEGER
            }
            
--xxx.100.16.1.8.1.1
arpStaticIfindex  OBJECT-TYPE
            SYNTAX  INTEGER 
            MAX-ACCESS  not-accessible
            STATUS  current
            DESCRIPTION
                " L3 interface index"
            ::= { arpStaticEntry 1 }
            
--xxx.100.16.1.8.1.2         
arpStaticIpaddress  OBJECT-TYPE
	SYNTAX      IpAddress	
        MAX-ACCESS  not-accessible
        STATUS      current
        DESCRIPTION "ip address"
        ::= { arpStaticEntry 2 }  
--xxx.100.16.1.8.1.3
arpStaticMac  OBJECT-TYPE
            SYNTAX  MacAddress (SIZE(17))
            MAX-ACCESS  read-create
            STATUS  current
            DESCRIPTION
                " the Mac address of the arp item"
            ::= { arpStaticEntry 3 }
            
--xxx.100.16.1.8.1.4         
arpStaticPortIndex  OBJECT-TYPE
	SYNTAX      INTEGER	
        MAX-ACCESS  read-create
        STATUS      current
        DESCRIPTION "the port index of the arp item"
        ::= { arpStaticEntry 4 }              
--xxx.100.16.1.8.1.5
arpStaticStatus  OBJECT-TYPE
            SYNTAX  INTEGER 
            	{
            		valid(1),--create one arp entry , stand for this arp entry is valid
            		invalid(2), --destory one arp entry , stand for this arp entry is invalid
            		waitingforset(3) -- this is the default status
            	}
            MAX-ACCESS  read-create
            STATUS  current
            DESCRIPTION
                "valid(1),this is a active arp when get/getnext; when set,mean create the static arp item
            		invalid(2); when set, mean destory the current arp item
            		waitingforset(3); reserved"
            ::= { arpStaticEntry 5 }
       
       
       
--xxx.100.16.2.1
ipStaticRouteExtTable OBJECT-TYPE 
    SYNTAX  SEQUENCE OF IpStaticRouteExtEntry
    MAX-ACCESS  not-accessible
    STATUS  current
    DESCRIPTION
        " static route configuration list"
    ::= { routeMgt   1}
            
--xxx.100.16.2.1.1
ipStaticRouteExtEntry OBJECT-TYPE
        SYNTAX  IpStaticRouteExtEntry
        MAX-ACCESS  not-accessible
        STATUS  current
        DESCRIPTION
            "The index of this table is ip.mask"
        INDEX   { ipStaticRouteExtDest,ipStaticRouteExtMask }
        ::= { ipStaticRouteExtTable 1 }

IpStaticRouteExtEntry
        ::= SEQUENCE
            {
                ipStaticRouteExtDest               		IpAddress,
                ipStaticRouteExtMask				IpAddress,
                ipStaticRouteExtNextHop				IpAddress,
                ipStaticRouteExtMetric				INTEGER,
                ipStaticRouteExtStatus				INTEGER
            }
            
--xxx.100.16.2.1.1.1
ipStaticRouteExtDest  OBJECT-TYPE
            SYNTAX  IpAddress 
            MAX-ACCESS  not-accessible
            STATUS  current
            DESCRIPTION
                "static route of intention net segment"
            ::= { ipStaticRouteExtEntry 1 }
            
--xxx.100.16.2.1.1.2         
ipStaticRouteExtMask  OBJECT-TYPE
	SYNTAX      IpAddress	
        MAX-ACCESS  not-accessible
        STATUS      current
        DESCRIPTION "mask"
        ::= { ipStaticRouteExtEntry 2 }  
--xxx.100.16.2.1.1.3
ipStaticRouteExtNextHop  OBJECT-TYPE
            SYNTAX  IpAddress
            MAX-ACCESS  read-create
            STATUS  current
            DESCRIPTION
                " next step ip"
            ::= { ipStaticRouteExtEntry 3 }
            
--xxx.100.16.2.1.1.4         
ipStaticRouteExtMetric  OBJECT-TYPE
	SYNTAX      INTEGER(1..255)	
        MAX-ACCESS  read-create
        STATUS      current
        DESCRIPTION " Manage distance/PRI"
        ::= { ipStaticRouteExtEntry 4 }              
--xxx.100.16.2.1.1.5
ipStaticRouteExtStatus  OBJECT-TYPE
            SYNTAX  INTEGER 
            	{
            		valid(1),
            		invalid(2),
            		waitingforset(3)
            	}
            MAX-ACCESS  read-create
            STATUS  current
            DESCRIPTION
                " When you get/getnext one entry, the meaning of 'valid' is that the static route which you get is 
                valid (or active); when you want to configure one static route, 'valid/creating' stand for setting one 
                entry, and 'invalid/destory' stands for delete the static route."
            ::= { ipStaticRouteExtEntry 5 }            
       
--********************************************************************************************************
--********************************************************************************************************        


dvmrpMgt           OBJECT IDENTIFIER ::= { l3 5 }

dvmrpScalar     OBJECT IDENTIFIER ::= { dvmrpMgt 1 }

dvmrpVersionString OBJECT-TYPE
    SYNTAX     DisplayString
    MAX-ACCESS read-only
    STATUS     current
    DESCRIPTION
            "The router's DVMRP version information.  Similar to
            sysDescr in MIB-II, this is a free-form field which can be
            used to display vendor-specific information."
    ::= { dvmrpScalar 1 }

-- dvmrpScalar 2 was previously used for a global
-- Generation ID.  However, the DVMRP spec changed it to
-- a per-interface parameter.
dvmrpNumRoutes OBJECT-TYPE
    SYNTAX     Gauge32
    MAX-ACCESS read-only
    STATUS     current
    DESCRIPTION
            "The number of entries in the routing table.  This can be
            used to monitor the routing table size."


    ::= { dvmrpScalar 3 }

dvmrpReachableRoutes OBJECT-TYPE
    SYNTAX     Gauge32
    MAX-ACCESS read-only
    STATUS     current
    DESCRIPTION
            "The number of entries in the routing table with non
            infinite metrics.  This can be used to detect network
            partitions by observing the ratio of reachable routes to
            total routes."
    ::= { dvmrpScalar 4 }


-- The DVMRP Interface Table

dvmrpInterfaceTable OBJECT-TYPE
    SYNTAX     SEQUENCE OF DvmrpInterfaceEntry
    MAX-ACCESS not-accessible
    STATUS     current
    DESCRIPTION
            "The (conceptual) table listing the router's multicast-
            capable interfaces."
    ::= { dvmrpMgt 2 }

dvmrpInterfaceEntry OBJECT-TYPE
    SYNTAX     DvmrpInterfaceEntry
    MAX-ACCESS not-accessible
    STATUS     current
    DESCRIPTION
            "An entry (conceptual row) in the dvmrpInterfaceTable.  This
            row augments ipMRouteInterfaceEntry in the IP Multicast MIB,
            where the threshold object resides."
    INDEX      { dvmrpInterfaceIndex }
    ::= { dvmrpInterfaceTable 1 }

DvmrpInterfaceEntry ::= SEQUENCE {
    dvmrpInterfaceIndex                 InterfaceIndex,
    dvmrpInterfaceLocalAddress          IpAddress,
    dvmrpInterfaceMetric                Integer32,
    dvmrpInterfaceStatus                RowStatus,
    dvmrpInterfaceRcvBadPkts            Counter32,
    dvmrpInterfaceRcvBadRoutes          Counter32,
    dvmrpInterfaceSentRoutes            Counter32,
    dvmrpInterfaceKey                   SnmpAdminString,
    dvmrpInterfaceKeyVersion            Integer32,
    dvmrpInterfaceGenerationId          Integer32
}

dvmrpInterfaceIndex OBJECT-TYPE
    SYNTAX     InterfaceIndex
    MAX-ACCESS read-only
    STATUS     current
    DESCRIPTION
            "The ifIndex value of the interface for which DVMRP is
            enabled."
    ::= { dvmrpInterfaceEntry 1 }

dvmrpInterfaceLocalAddress OBJECT-TYPE
    SYNTAX     IpAddress
    MAX-ACCESS read-only
    STATUS     current
    DESCRIPTION
            "The IP address this system will use as a source address on
            this interface.  On unnumbered interfaces, it must be the
            same value as dvmrpInterfaceLocalAddress for some interface
            on the system."
    ::= { dvmrpInterfaceEntry 2 }

dvmrpInterfaceMetric OBJECT-TYPE
    SYNTAX     Integer32 (1..31)
    MAX-ACCESS read-create
    STATUS     current
    DESCRIPTION
            "The distance metric for this interface which is used to
            calculate distance vectors."
    DEFVAL     { 1 }
    ::= { dvmrpInterfaceEntry 3 }

dvmrpInterfaceStatus OBJECT-TYPE
    SYNTAX     RowStatus
    MAX-ACCESS read-create
    STATUS     current
    DESCRIPTION
            "The status of this entry.  Creating the entry enables DVMRP
            on the virtual interface; destroying the entry or setting it
            to notInService disables DVMRP on the virtual interface."
    ::= { dvmrpInterfaceEntry 4 }

dvmrpInterfaceRcvBadPkts OBJECT-TYPE
    SYNTAX     Counter32
    MAX-ACCESS read-only
    STATUS     current
    DESCRIPTION
            "The number of DVMRP messages received on the interface by
            the DVMRP process which were subsequently discarded as
            invalid (e.g. invalid packet format, or a route report from
            an unknown neighbor)."
    ::= { dvmrpInterfaceEntry 5 }

dvmrpInterfaceRcvBadRoutes OBJECT-TYPE
    SYNTAX     Counter32
    MAX-ACCESS read-only
    STATUS     current
    DESCRIPTION
            "The number of routes, in valid DVMRP packets, which were
            ignored because the entry was invalid."
    ::= { dvmrpInterfaceEntry 6 }

dvmrpInterfaceSentRoutes OBJECT-TYPE
    SYNTAX     Counter32
    MAX-ACCESS read-only
    STATUS     current
    DESCRIPTION
            "The number of routes, in DVMRP Report packets, which have
            been sent on this interface.  Together with
            dvmrpNeighborRcvRoutes at a peer, this object is useful for
            detecting routes being lost."
    ::= { dvmrpInterfaceEntry 7 }

dvmrpInterfaceKey OBJECT-TYPE
    SYNTAX     SnmpAdminString
    MAX-ACCESS read-only
    STATUS     current
    DESCRIPTION
            "The (shared) key for authenticating neighbors on this
            interface.  This object is intended solely for the purpose
            of setting the interface key, and MUST be accessible only
            via requests using both authentication and privacy.  The
            agent MAY report an empty string in response to get, get-
            next, get-bulk requests."
    ::= { dvmrpInterfaceEntry 8 }

dvmrpInterfaceKeyVersion OBJECT-TYPE
    SYNTAX     Integer32
    MAX-ACCESS read-only
    STATUS     current
    DESCRIPTION
            "The highest version number of all known interface keys for
            this interface used for authenticating neighbors."
    ::= { dvmrpInterfaceEntry 9 }

dvmrpInterfaceGenerationId OBJECT-TYPE
    SYNTAX     Integer32
    MAX-ACCESS read-only
    STATUS     current
    DESCRIPTION
            "The generation identifier for the interface.  This is used
            by neighboring routers to detect whether the DVMRP routing
            table should be resent."
    ::= { dvmrpInterfaceEntry 10 }

-- The DVMRP Neighbor Table

dvmrpNeighborTable OBJECT-TYPE
    SYNTAX     SEQUENCE OF DvmrpNeighborEntry
    MAX-ACCESS not-accessible
    STATUS     current
    DESCRIPTION
            "The (conceptual) table listing the router's DVMRP
            neighbors, as discovered by receiving DVMRP messages."
    ::= { dvmrpMgt 3 }

dvmrpNeighborEntry OBJECT-TYPE
    SYNTAX     DvmrpNeighborEntry
    MAX-ACCESS not-accessible
    STATUS     current
    DESCRIPTION
            "An entry (conceptual row) in the dvmrpNeighborTable."
    INDEX      { dvmrpNeighborIfIndex, dvmrpNeighborAddress }
    ::= { dvmrpNeighborTable 1 }

DvmrpNeighborEntry ::= SEQUENCE {
    dvmrpNeighborIfIndex         InterfaceIndex,
    dvmrpNeighborAddress         IpAddress,
    dvmrpNeighborUpTime          TimeTicks,
    dvmrpNeighborExpiryTime      TimeTicks,
    dvmrpNeighborGenerationId    Integer32,
    dvmrpNeighborMajorVersion    Integer32,
    dvmrpNeighborMinorVersion    Integer32,
    dvmrpNeighborCapabilities    BITS,
    dvmrpNeighborRcvRoutes       Counter32,
    dvmrpNeighborRcvBadPkts      Counter32,
    dvmrpNeighborRcvBadRoutes    Counter32,
    dvmrpNeighborState           INTEGER
}

dvmrpNeighborIfIndex OBJECT-TYPE
    SYNTAX     InterfaceIndex
    MAX-ACCESS read-only
    STATUS     current
    DESCRIPTION
            "The value of ifIndex for the virtual interface used to
            reach this DVMRP neighbor."
    ::= { dvmrpNeighborEntry 1 }

dvmrpNeighborAddress OBJECT-TYPE
    SYNTAX     IpAddress
    MAX-ACCESS read-only
    STATUS     current
    DESCRIPTION
            "The IP address of the DVMRP neighbor for which this entry
            contains information."
    ::= { dvmrpNeighborEntry 2 }

dvmrpNeighborUpTime OBJECT-TYPE
    SYNTAX     TimeTicks
    MAX-ACCESS read-only
    STATUS     current
    DESCRIPTION
            "The time since this DVMRP neighbor (last) became a neighbor
            of the local router."
    ::= { dvmrpNeighborEntry 3 }

dvmrpNeighborExpiryTime OBJECT-TYPE
    SYNTAX     TimeTicks
    MAX-ACCESS read-only
    STATUS     current
    DESCRIPTION
            "The minimum time remaining before this DVMRP neighbor will
            be aged out."
    ::= { dvmrpNeighborEntry 4 }

dvmrpNeighborGenerationId OBJECT-TYPE
    SYNTAX     Integer32
    MAX-ACCESS read-only
    STATUS     current
    DESCRIPTION
            "The neighboring router's generation identifier."
    ::= { dvmrpNeighborEntry 5 }

dvmrpNeighborMajorVersion OBJECT-TYPE
    SYNTAX     Integer32 (0..255)
    MAX-ACCESS read-only
    STATUS     current
    DESCRIPTION
            "The neighboring router's major DVMRP version number."
    ::= { dvmrpNeighborEntry 6 }

dvmrpNeighborMinorVersion OBJECT-TYPE
    SYNTAX     Integer32 (0..255)
    MAX-ACCESS read-only
    STATUS     current
    DESCRIPTION
            "The neighboring router's minor DVMRP version number."
    ::= { dvmrpNeighborEntry 7 }

dvmrpNeighborCapabilities OBJECT-TYPE
    SYNTAX     BITS {
                   leaf(0),
                   prune(1),
                   generationID(2),
                   mtrace(3),
                   snmp(4),
                   netmask(5)
                   
               }
    MAX-ACCESS read-only
    STATUS     current
    DESCRIPTION
            "This object describes the neighboring router's
            capabilities.  The leaf bit indicates that the neighbor has
            only one interface with neighbors.  The prune bit indicates
            that the neighbor supports pruning.  The generationID bit
            indicates that the neighbor sends its generationID in Probe
            messages.  The mtrace bit indicates that the neighbor can
            handle mtrace requests. The snmp bit indicates that the 
            neighbor support snmp. The netmask bit indicates that the 
            neighbor support netmask."
    ::= { dvmrpNeighborEntry 8 }

dvmrpNeighborRcvRoutes OBJECT-TYPE
    SYNTAX     Counter32
    MAX-ACCESS read-only
    STATUS     current
    DESCRIPTION
            "The total number of routes received in valid DVMRP packets
            received from this neighbor.  This can be used to diagnose
            problems such as unicast route injection, as well as giving
            an indication of the level of DVMRP route exchange
            activity."
    ::= { dvmrpNeighborEntry 9 }

dvmrpNeighborRcvBadPkts OBJECT-TYPE
    SYNTAX     Counter32
    MAX-ACCESS read-only
    STATUS     current
    DESCRIPTION
            "The number of packet received from this neighbor which were
            discarded as invalid."
    ::= { dvmrpNeighborEntry 10 }

dvmrpNeighborRcvBadRoutes OBJECT-TYPE
    SYNTAX     Counter32
    MAX-ACCESS read-only
    STATUS     current
    DESCRIPTION
            "The number of routes, in valid DVMRP packets received from
            this neighbor, which were ignored because the entry was
            invalid."
    ::= { dvmrpNeighborEntry 11 }

dvmrpNeighborState OBJECT-TYPE
    SYNTAX     INTEGER { oneway(1), active(2), ignoring(3), down(4) }
    MAX-ACCESS read-only
    STATUS     current
    DESCRIPTION
            "State of the neighbor adjacency."
    ::= { dvmrpNeighborEntry 12 }


-- The DVMRP Route Table

dvmrpRouteTable OBJECT-TYPE
    SYNTAX     SEQUENCE OF DvmrpRouteEntry
    MAX-ACCESS not-accessible
    STATUS     current
    DESCRIPTION
            "The table of routes learned through DVMRP route exchange."
    ::= { dvmrpMgt 4 }

dvmrpRouteEntry OBJECT-TYPE
    SYNTAX     DvmrpRouteEntry
    MAX-ACCESS not-accessible
    STATUS     current
    DESCRIPTION
            "An entry (conceptual row) containing the multicast routing
            information used by DVMRP in place of the unicast routing
            information."
    INDEX      { dvmrpRouteSource, dvmrpRouteSourceMask }
    ::= { dvmrpRouteTable 1 }

DvmrpRouteEntry ::= SEQUENCE {
    dvmrpRouteSource             IpAddress,
    dvmrpRouteSourceMask         IpAddress,
    dvmrpRouteUpstreamNeighbor   IpAddress,
    dvmrpRouteIfIndex            InterfaceIndexOrZero,
    dvmrpRouteMetric             Integer32,
    dvmrpRouteExpiryTime         TimeTicks,
    dvmrpRouteUpTime             TimeTicks
}

dvmrpRouteSource OBJECT-TYPE
    SYNTAX     IpAddress
    MAX-ACCESS read-only
    STATUS     current
    DESCRIPTION
            "The network address which when combined with the
            corresponding value of dvmrpRouteSourceMask identifies the
            sources for which this entry contains multicast routing
            information."
    ::= { dvmrpRouteEntry 1 }

dvmrpRouteSourceMask OBJECT-TYPE
    SYNTAX     IpAddress
    MAX-ACCESS read-only
    STATUS     current
    DESCRIPTION
            "The network mask which when combined with the corresponding
            value of dvmrpRouteSource identifies the sources for which
            this entry contains multicast routing information."
    ::= { dvmrpRouteEntry 2 }

dvmrpRouteUpstreamNeighbor OBJECT-TYPE
    SYNTAX     IpAddress
    MAX-ACCESS read-only
    STATUS     current
    DESCRIPTION
            "The address of the upstream neighbor (e.g., RPF neighbor)
            from which IP datagrams from these sources are received."
    ::= { dvmrpRouteEntry 3 }

dvmrpRouteIfIndex OBJECT-TYPE
    SYNTAX     InterfaceIndexOrZero
    MAX-ACCESS read-only
    STATUS     current
    DESCRIPTION
            "The value of ifIndex for the interface on which IP
            datagrams sent by these sources are received.  A value of 0
            typically means the route is an aggregate for which no next-
            hop interface exists."
    ::= { dvmrpRouteEntry 4 }

dvmrpRouteMetric OBJECT-TYPE
    SYNTAX     Integer32 (1..32)
    MAX-ACCESS read-only
    STATUS     current
    DESCRIPTION
            "The distance in hops to the source subnet."
    ::= { dvmrpRouteEntry 5 }

dvmrpRouteExpiryTime OBJECT-TYPE
    SYNTAX     TimeTicks
    MAX-ACCESS read-only
    STATUS     current
    DESCRIPTION
            "The minimum amount of time remaining before this entry will
            be aged out."
    ::= { dvmrpRouteEntry 6 }

dvmrpRouteUpTime OBJECT-TYPE
    SYNTAX     TimeTicks
    MAX-ACCESS read-only
    STATUS     current
    DESCRIPTION
            "The time since the route represented by this entry was
            learned by the router."
    ::= { dvmrpRouteEntry 7 }

-- The DVMRP Routing Next Hop Table


dvmrpRouteNextHopTable OBJECT-TYPE
    SYNTAX     SEQUENCE OF DvmrpRouteNextHopEntry
    MAX-ACCESS not-accessible
    STATUS     current
    DESCRIPTION
            "The (conceptual) table containing information on the next
            hops on outgoing interfaces for routing IP multicast
            datagrams."
    ::= { dvmrpMgt 5 }

dvmrpRouteNextHopEntry OBJECT-TYPE
    SYNTAX     DvmrpRouteNextHopEntry
    MAX-ACCESS not-accessible
    STATUS     current
    DESCRIPTION
            "An entry (conceptual row) in the list of next hops on
            outgoing interfaces to which IP multicast datagrams from
            particular sources are routed."
    INDEX      { dvmrpRouteNextHopSource, dvmrpRouteNextHopSourceMask,
                 dvmrpRouteNextHopIfIndex }
    ::= { dvmrpRouteNextHopTable 1 }

DvmrpRouteNextHopEntry ::= SEQUENCE {
    dvmrpRouteNextHopSource             IpAddress,
    dvmrpRouteNextHopSourceMask         IpAddress,
    dvmrpRouteNextHopIfIndex            InterfaceIndex,
    dvmrpRouteNextHopType               INTEGER
}

dvmrpRouteNextHopSource OBJECT-TYPE
    SYNTAX     IpAddress
    MAX-ACCESS read-only
    STATUS     current
    DESCRIPTION
            "The network address which when combined with the
            corresponding value of dvmrpRouteNextHopSourceMask
            identifies the sources for which this entry specifies a next
            hop on an outgoing interface."
    ::= { dvmrpRouteNextHopEntry 1 }

dvmrpRouteNextHopSourceMask OBJECT-TYPE
    SYNTAX     IpAddress
    MAX-ACCESS read-only
    STATUS     current
    DESCRIPTION
            "The network mask which when combined with the corresponding
            value of dvmrpRouteNextHopSource identifies the sources for
            which this entry specifies a next hop on an outgoing
            interface."
    ::= { dvmrpRouteNextHopEntry 2 }

dvmrpRouteNextHopIfIndex OBJECT-TYPE
    SYNTAX     InterfaceIndex
    MAX-ACCESS read-only
    STATUS     current
    DESCRIPTION
            "The ifIndex value of the interface for the outgoing
            interface for this next hop."
    ::= { dvmrpRouteNextHopEntry 3 }

dvmrpRouteNextHopType OBJECT-TYPE
    SYNTAX     INTEGER { leaf(1), branch(2) }
    MAX-ACCESS read-only
    STATUS     current
    DESCRIPTION
            "Type is leaf if no downstream dependent neighbors exist on
            the outgoing virtual interface.  Otherwise, type is branch."
    ::= { dvmrpRouteNextHopEntry 4 }

-- The DVMRP Prune Table

dvmrpPruneTable OBJECT-TYPE
    SYNTAX     SEQUENCE OF DvmrpPruneEntry
    MAX-ACCESS not-accessible
    STATUS     current
    DESCRIPTION
            "The (conceptual) table listing the router's upstream prune
            state."
    ::= { dvmrpMgt 6 }

dvmrpPruneEntry OBJECT-TYPE
    SYNTAX     DvmrpPruneEntry
    MAX-ACCESS not-accessible
    STATUS     current
    DESCRIPTION
            "An entry (conceptual row) in the dvmrpPruneTable."
    INDEX      { dvmrpPruneGroup, dvmrpPruneSource,
                 dvmrpPruneSourceMask }
    ::= { dvmrpPruneTable 1 }

DvmrpPruneEntry ::= SEQUENCE {
    dvmrpPruneGroup              IpAddress,
    dvmrpPruneSource             IpAddress,
    dvmrpPruneSourceMask         IpAddress,
    dvmrpPruneExpiryTime         TimeTicks
}

dvmrpPruneGroup OBJECT-TYPE
    SYNTAX     IpAddress
    MAX-ACCESS read-only
    STATUS     current
    DESCRIPTION
            "The group address which has been pruned."
    ::= { dvmrpPruneEntry 1 }

dvmrpPruneSource OBJECT-TYPE
    SYNTAX     IpAddress
    MAX-ACCESS read-only
    STATUS     current
    DESCRIPTION
            "The address of the source or source network which has been
            pruned."
    ::= { dvmrpPruneEntry 2 }

dvmrpPruneSourceMask OBJECT-TYPE
    SYNTAX     IpAddress
    MAX-ACCESS read-only
    STATUS     current
    DESCRIPTION
            "The address of the source or source network which has been
            pruned.  The mask must either be all 1's, or else
            dvmrpPruneSource and dvmrpPruneSourceMask must match
            dvmrpRouteSource and dvmrpRouteSourceMask for some entry in
            the dvmrpRouteTable."
    ::= { dvmrpPruneEntry 3 }

dvmrpPruneExpiryTime OBJECT-TYPE
    SYNTAX     TimeTicks
    MAX-ACCESS read-only
    STATUS     current
    DESCRIPTION
            "The amount of time remaining before this prune should
            expire at the upstream neighbor.  This value should be the
            minimum of the default prune lifetime and the remaining
            prune lifetimes of the local router's downstream neighbors,
            if any."
    ::= { dvmrpPruneEntry 4 }




ripMgt              OBJECT IDENTIFIER ::= { l3 3 }
ospfMgt             OBJECT IDENTIFIER ::= { l3 4 }
-- ripMgt


ripTimers OBJECT IDENTIFIER ::= { ripMgt 1 }

ripUpdateTime OBJECT-TYPE
        SYNTAX      Integer32 (5..2147483647)
        MAX-ACCESS  read-write
        STATUS      current
        DESCRIPTION "The update time in seconds controls the advertising of regular
                     update messages. The real working model, while using this
                     timer, the time should be offset by a small random time
                     (+/- 0 to 5 seconds each time it is set."
        DEFVAL      { 30 }
        ::= { ripTimers 1 }

ripTimeoutTime OBJECT-TYPE
        SYNTAX      Integer32 (5..2147483647)
        MAX-ACCESS  read-write
        STATUS      current
        DESCRIPTION "The timeout timer in seconds governs the validity of a route.
                     It is initialized when a route is established, and any time
                     an update message is received for the route. If the setting time
                     elapses from the last time the timrout was initialized, the route
                     is considered to have expired, and the hop count of the route is
                     set to infinite. It should be at least three times the value of 
                     update timer."
        DEFVAL      { 180 }
        ::= { ripTimers 2 }

ripGarbageCollectionTime OBJECT-TYPE
        SYNTAX      Integer32 (5..2147483647)
        MAX-ACCESS  read-write
        STATUS      current
        DESCRIPTION "When the information about a route becomes invalid, the system
                     should not immediately purge that route from its table. Instead,
                     it continues to advertise the route with a metric of infinite.
                     At the same time, the garbage-collection timer is set for that 
                     route. When the count reaches zero, the route is purged from the
                     the table. This timer allows neighbors to become aware of 
                     the invalidity of a route prior to purging."
        DEFVAL      { 120 }
        ::= { ripTimers 3 }

ripRoutingProcessStatus OBJECT-TYPE
        SYNTAX      EnabledStatusPrivate
        MAX-ACCESS  read-write
        STATUS      current
        DESCRIPTION "Enable or Disable RIP routing process on a system."
        DEFVAL      { disabled }
        ::= { ripMgt 2 }
        
ripRouterVersion OBJECT-TYPE
        SYNTAX      INTEGER
                    {   
                        rip1(1),
                        rip2(2)
                    }
        MAX-ACCESS  read-write
        STATUS      current
        DESCRIPTION "To specify a RIP version used globally by the rourter."
        DEFVAL      { rip2 }
        ::= { ripMgt 3 }
        


ripInstabilityPreventingTable OBJECT-TYPE
        SYNTAX      SEQUENCE OF RipInstabilityPreventingEntry
        MAX-ACCESS  not-accessible
        STATUS      current
        DESCRIPTION "A list of RIP instability preventing status"
        ::= { ripMgt 4 }

ripInstabilityPreventingEntry OBJECT-TYPE
        SYNTAX      RipInstabilityPreventingEntry
        MAX-ACCESS  not-accessible
        STATUS      current
        DESCRIPTION "An entry in the table, containing information
                     about RIP instability preventing configuration.
                     The ifIndex index is a VLAN's ifIndex"
        INDEX       { ripVlanIndex }
        ::= { ripInstabilityPreventingTable 1 }

RipInstabilityPreventingEntry ::= SEQUENCE
{
    ripVlanIndex             Integer32,
    ripSplitHorizonStatus   INTEGER
}


ripVlanIndex OBJECT-TYPE
        SYNTAX      Integer32
        MAX-ACCESS  read-only
        STATUS      current
        DESCRIPTION "This is defined as a VLAN interface.
                     A routing interface is a VLAN binds a IP
                     subnet."
        ::= { ripInstabilityPreventingEntry 1 }
        
ripSplitHorizonStatus OBJECT-TYPE
        SYNTAX      INTEGER
                    {
                        splitHorizon(2),
                        poisonReverse(0),
                        none(1)
                    }
        MAX-ACCESS  read-write
        STATUS      current
        DESCRIPTION "Enable or Disable RIP instability preventing status on an interface" 
        ::= { ripInstabilityPreventingEntry 2 }


ripStatisticsReset OBJECT-TYPE
        SYNTAX      INTEGER
                    {
                        reset(1),
                        noReset(2)
                    }
        MAX-ACCESS  read-write
        STATUS      current
        DESCRIPTION "Write it to reset(1), the following objects in RFC 1724 
                     should be reset: 
                     1. Global Counters:
                        'rip2GlobalRouteChanges',
                        'rip2GlobalQueries'.
                     2. Interface Status Table, for each 'rip2IfStatAddress':
                        'rip2IfStatRcvBadPackets',
                        'rip2IfStatRcvBadRoutes',
                        'rip2IfStatSendUpdates'
                     3. Peer Table, for each 'rip2PeerAddress' and 'rip2PeerDomain',
                        'rip2PeerRcvBadPackets',
                        'rip2PeerRcvBadRoutes'
                     When read it, this value always is noReset(2)."
        ::= { ripMgt 5 }

ripNetworkInterfaceTable OBJECT-TYPE
        SYNTAX      SEQUENCE OF RipNetworkInterfaceEntry
        MAX-ACCESS  not-accessible
        STATUS      current
        DESCRIPTION ""
        ::= { ripMgt 6 }

ripNetworkInterfaceEntry OBJECT-TYPE
        SYNTAX      RipNetworkInterfaceEntry
        MAX-ACCESS  not-accessible
        STATUS      current
        DESCRIPTION ""
        INDEX       { ripNetworkInterfaceAddress }
        ::= { ripNetworkInterfaceTable 1 }

RipNetworkInterfaceEntry ::= SEQUENCE
{
    ripNetworkInterfaceAddress  IpAddress,
    ripNetworkInterfaceStatus   ValidStatus
}


ripNetworkInterfaceAddress OBJECT-TYPE
        SYNTAX      IpAddress
        MAX-ACCESS  read-only
        STATUS      current
        DESCRIPTION "The RIP Network address(the ip address of the interface)."
        ::= { ripNetworkInterfaceEntry 1 }

             
ripNetworkInterfaceStatus OBJECT-TYPE
        SYNTAX      ValidStatus
        MAX-ACCESS  read-create
        STATUS      current
        DESCRIPTION "Set this variable to create or destroy a RIP network address.
         ValidStatus:
         A simple status value for the object to create and destroy
         a table entry. This is a simplified variant of RowStatus as it
         supports only two values. Setting it to valid(1) creates an entry.
         Setting it to invalid(0) destroys an entry." 
        ::= { ripNetworkInterfaceEntry 2 }
        
ripNetworkAddrTable OBJECT-TYPE
        SYNTAX      SEQUENCE OF RipNetworkAddrEntry
        MAX-ACCESS  not-accessible
        STATUS      current
        DESCRIPTION ""
        ::= { ripMgt 7 }

ripNetworkAddrEntry OBJECT-TYPE
        SYNTAX      RipNetworkAddrEntry
        MAX-ACCESS  not-accessible
        STATUS      current
        DESCRIPTION ""
        INDEX       { ripNetworkAddrAddress,ripNetworkAddrPrefixLen }
        ::= { ripNetworkAddrTable 1 }

RipNetworkAddrEntry ::= SEQUENCE
{
    ripNetworkAddrAddress  IpAddress,
    ripNetworkAddrPrefixLen  INTEGER,
    ripNetworkAddrStatus   INTEGER
}


ripNetworkAddrAddress OBJECT-TYPE
        SYNTAX      IpAddress
        MAX-ACCESS  read-only
        STATUS      current
        DESCRIPTION "The RIP Network address."
        ::= { ripNetworkAddrEntry 1 }
        
ripNetworkAddrPrefixLen OBJECT-TYPE
        SYNTAX      INTEGER (0..32)
        MAX-ACCESS  read-only
        STATUS      current
        DESCRIPTION "The RIP Network prefix length of address."
        ::= { ripNetworkAddrEntry 2 }        

             
ripNetworkAddrStatus OBJECT-TYPE
        SYNTAX INTEGER {     
                valid(1),
                invalid (0)
        }
        MAX-ACCESS  read-create
        STATUS      current
        DESCRIPTION "Set this variable to create or destroy a RIP network address.
         ValidStatus:
         A simple status value for the object to create and destroy
         a table entry. This is a simplified variant of RowStatus as it
         supports only two values. Setting it to valid(1) creates an entry.
         Setting it to invalid(0) destroys an entry." 
        ::= { ripNetworkAddrEntry 3 }        
       
        
-- ospfMgt
       
ospfSystemGroup OBJECT IDENTIFIER ::= { ospfMgt 1 } 
    
ospfRouterIdType OBJECT-TYPE
        SYNTAX      INTEGER
                    {
                        auto(1),
                        manual(2)
                    }
        MAX-ACCESS  read-only
        STATUS      current
        DESCRIPTION "Set router ID automatically or  manually."
        DEFVAL { auto }
        ::= { ospfSystemGroup 1 }
 
ospfRfc1583CompatibleState OBJECT-TYPE
        SYNTAX      EnabledStatusPrivate
        MAX-ACCESS  read-write
        STATUS      current
        DESCRIPTION 	"Enable or disable rfc1583 compatibility."
        DEFVAL { disabled }
        ::= { ospfSystemGroup 2 }
 
ospfAutoCost OBJECT-TYPE
        SYNTAX   Integer32 (1..4294967)
        MAX-ACCESS  read-write
        STATUS      current
        DESCRIPTION "Set the reference bandwith of auto cost, the unit is Mbps."
        DEFVAL { 100 }
        ::= { ospfSystemGroup 3 }
       
ospfAdvertiseDefaultRoute OBJECT-TYPE
        SYNTAX   INTEGER
            {
                   disable(0),
                   always(1),
                   notAlways(2)
                }
        MAX-ACCESS  read-write
        STATUS      current
        DESCRIPTION 	"If always is set, always advertises the default route regardless 
                     	of whether the default route exists;If notalways is set ,advertises 
                     	the default route when the router have the default route."
        DEFVAL { disable }
        ::= { ospfSystemGroup 4 }    
     
 
ospfDefaultExternalMetric OBJECT-TYPE
        SYNTAX      OspfBigMetric
        MAX-ACCESS  read-write
        STATUS      current
        DESCRIPTION "Metric used for generating the default route."
        ::= { ospfSystemGroup 5 }    
 
ospfSpfHoldTime OBJECT-TYPE
        SYNTAX   Unsigned32 (0..4294967295)
        MAX-ACCESS  read-write
        STATUS      current
        DESCRIPTION 	"Sets the hold time between two consecutive SPF calculations."
        DEFVAL { 10 }
        ::= { ospfSystemGroup 6 }  

ospfSpfDelayTime OBJECT-TYPE
        SYNTAX   Unsigned32 (0..4294967295)
        MAX-ACCESS  read-write
        STATUS      current
        DESCRIPTION	"Sets the delay time to calculate SPF Delay time, in seconds, between 
                         when OSPF receives a topology change and when it starts an SPF calculation." 
        DEFVAL { 5 }
        ::= { ospfSystemGroup 7 }  
        
ospfAreaNumber OBJECT-TYPE
        SYNTAX   Integer32
        MAX-ACCESS  read-only
        STATUS      current
        DESCRIPTION	"Records the OSPF area numbers." 
              
        DEFVAL { 0 }
        ::= { ospfSystemGroup 8 }       

ospfNssaTable OBJECT-TYPE
        SYNTAX   SEQUENCE OF OspfNssaEntry
        MAX-ACCESS   not-accessible
        STATUS   current
        DESCRIPTION
           "A conceptually table for ospfNssaEntry."       
        ::= {ospfMgt 2 }

ospfNssaEntry OBJECT-TYPE
        SYNTAX   OspfNssaEntry
        MAX-ACCESS   not-accessible
        STATUS   current
        DESCRIPTION
           "A conceptually row for ospfNssaTable."      
      INDEX { ospfNssaAreaId }
      ::= { ospfNssaTable 1 }

OspfNssaEntry ::= SEQUENCE 
      {
        ospfNssaAreaId                     OspfAreaID,
        ospfNssaStatus                     EnabledStatusPrivate,
        ospfNssaRedistributeStatus         EnabledStatusPrivate,
        ospfNssaOriginateDefaultInfoStatus EnabledStatusPrivate

      }

ospfNssaAreaId OBJECT-TYPE
        SYNTAX       OspfAreaID
        MAX-ACCESS   read-only
        STATUS       current
        DESCRIPTION	"The 32-bit identifier for the NSSA. On creation, 
            this can be derived from the instance."
       ::= { ospfNssaEntry 1 }

ospfNssaStatus OBJECT-TYPE
        SYNTAX       EnabledStatusPrivate
        MAX-ACCESS   read-create
        STATUS       current
        DESCRIPTION
			"The status of this conceptual row entry. This object isused to manage the
			creation and deletion of conceptual rows."
			      
       ::= { ospfNssaEntry 2 }       

ospfNssaRedistributeStatus OBJECT-TYPE
        SYNTAX       EnabledStatusPrivate
        MAX-ACCESS   read-create
        STATUS       current
        DESCRIPTION
           "Enabled or disabled to import routes only into the normal areas,
            but not into the NSSA area."
        DEFVAL { enabled }
       ::= { ospfNssaEntry 3 }

ospfNssaOriginateDefaultInfoStatus OBJECT-TYPE
        SYNTAX       EnabledStatusPrivate
        MAX-ACCESS   read-create        
        STATUS       current
        DESCRIPTION	"Enable or disable to generate a Type 7 default into the NSSA area."
           
         DEFVAL { disabled }   
       ::= { ospfNssaEntry 4 }


       
ospfRedistributeTable OBJECT-TYPE
        SYNTAX   SEQUENCE OF OspfRedistributeEntry
        MAX-ACCESS   not-accessible
        STATUS   current
        DESCRIPTION
           "The conceptual table of all of ospfRedistributeEntry."        
        ::= {ospfMgt 3 }


ospfRedistributeEntry OBJECT-TYPE
        SYNTAX       OspfRedistributeEntry
        MAX-ACCESS   not-accessible
        STATUS       current
        DESCRIPTION
           "The conceptual row for ospfRedistributeTable."      
      INDEX { ospfRedistributeProtocol }
      ::= { ospfRedistributeTable 1 }

OspfRedistributeEntry ::= SEQUENCE 
{
         ospfRedistributeProtocol   INTEGER,
         ospfRedistributeStatus     EnabledStatusPrivate,         
         ospfRedistributeMetricType INTEGER,
         ospfRedistributeMetric     OspfBigMetric

}
 
ospfRedistributeProtocol OBJECT-TYPE
        SYNTAX      INTEGER
                {
                  kernel(1),
                  connect(2),
                  static(3),
                  rip(4),
                  ospf(6),
                  bgp(8),
                  isis(9)
                }
        MAX-ACCESS   read-only
        STATUS       current
        DESCRIPTION	"Protocol ID."
           
       ::= { ospfRedistributeEntry 1 }

ospfRedistributeStatus OBJECT-TYPE
        SYNTAX       EnabledStatusPrivate
        MAX-ACCESS   read-create
        STATUS       current
        DESCRIPTION
			" enable-- redistribute the specific route,disable--- does not redistribute the specific route.For example
			 when the ospfRedistributeProtocol is equal to rip, 'enable' stands for redistribute the route from rip."          
       ::= { ospfRedistributeEntry 2 }  

ospfRedistributeMetricType OBJECT-TYPE
        SYNTAX      INTEGER
                {
                      type1(1),
              				type2(2)
                    }
        MAX-ACCESS   read-create
        STATUS       current
        DESCRIPTION
           "Metric type."
        DEFVAL {type2}
       ::= { ospfRedistributeEntry 3 }

ospfRedistributeMetric OBJECT-TYPE
        SYNTAX       OspfBigMetric
        MAX-ACCESS   read-create
        STATUS       current
        DESCRIPTION
           "Metric value."  
       ::= { ospfRedistributeEntry 4 }


       
ospfSummaryAddressTable OBJECT-TYPE
        SYNTAX   SEQUENCE OF OspfSummaryAddressEntry
        MAX-ACCESS   not-accessible
        STATUS   current
        DESCRIPTION
           "The conceptual table of all of ospfSummaryAddressEntry."     
      ::= {ospfMgt 4}

ospfSummaryAddressEntry OBJECT-TYPE
       SYNTAX       OspfSummaryAddressEntry
       MAX-ACCESS   not-accessible
       STATUS       current
       DESCRIPTION
           "The conceptual row for ospfSummaryAddressTable."      
       INDEX { ospfSummaryAddress,ospfSummaryMask }
       ::= { ospfSummaryAddressTable 1 }

OspfSummaryAddressEntry ::= SEQUENCE 
{
       ospfSummaryAddress   IpAddress,
       ospfSummaryMask      IpAddress,
       ospfSummaryStatus    EnabledStatusPrivate
}
 
ospfSummaryAddress OBJECT-TYPE
        SYNTAX       IpAddress
        MAX-ACCESS   read-only
        STATUS       current
        DESCRIPTION
           "Summary address."
        ::= { ospfSummaryAddressEntry 1 }

ospfSummaryMask OBJECT-TYPE
        SYNTAX       IpAddress
        MAX-ACCESS   read-only
        STATUS       current
        DESCRIPTION
           "Summary mask."
       ::= { ospfSummaryAddressEntry 2 }


ospfSummaryStatus OBJECT-TYPE
        SYNTAX       EnabledStatusPrivate
        MAX-ACCESS   read-create
        STATUS       current
        DESCRIPTION
			" valid/enable--- define a summary, invalid/disable destory the summary from the router"        
       ::= { ospfSummaryAddressEntry 3 }   

ospfNetworkAreaAddressTable OBJECT-TYPE
        SYNTAX   SEQUENCE OF OspfNetworkAreaAddressEntry
        MAX-ACCESS   not-accessible
        STATUS   current
        DESCRIPTION
           "The conceptual table of all of ospfNetworkAreaAddressEntry."     
        ::= {ospfMgt 5 }

ospfNetworkAreaAddressEntry OBJECT-TYPE
        SYNTAX       OspfNetworkAreaAddressEntry
        MAX-ACCESS   not-accessible
        STATUS       current
        DESCRIPTION
           "The conceptual row for ospfNetworkAreaAddressTable."       
        INDEX { ospfNetworkAareaAddress,ospfNetworkAreaMask,ospfNetworkAreaAreaId }
        ::= { ospfNetworkAreaAddressTable 1 }

OspfNetworkAreaAddressEntry ::= SEQUENCE
{
       ospfNetworkAareaAddress  IpAddress,
       ospfNetworkAreaMask      IpAddress,
       ospfNetworkAreaAreaId    IpAddress,     
       ospfNetworkAreaStatus    EnabledStatusPrivate
}
 
ospfNetworkAareaAddress OBJECT-TYPE
        SYNTAX       IpAddress
        MAX-ACCESS   read-only
        STATUS       current
        DESCRIPTION
           "NetworkArea address."
       ::= { ospfNetworkAreaAddressEntry 1 }

ospfNetworkAreaMask OBJECT-TYPE
        SYNTAX   IpAddress
        MAX-ACCESS   read-only
        STATUS   current
        DESCRIPTION
           "NetworkArea mask."
       ::= { ospfNetworkAreaAddressEntry 2 }
    
ospfNetworkAreaAreaId OBJECT-TYPE
        SYNTAX       IpAddress
        MAX-ACCESS   read-only
        STATUS       current
        DESCRIPTION
           "NetworkArea area ID."
       ::= { ospfNetworkAreaAddressEntry 3 }

ospfNetworkAreaStatus OBJECT-TYPE
        SYNTAX       EnabledStatusPrivate
        MAX-ACCESS   read-create
        STATUS       current
        DESCRIPTION
			"enabled(1), disabled(0).
			valid/enable--- run the ospf on the interfaces,which match the ipaddr/mask;
			invalid/disable--disable the ospf.
			 ValidStatus:
         A simple status value for the object to create and destroy
         a table entry. This is a simplified variant of RowStatus as it
         supports only two values. Setting it to valid(1) creates an entry.
         Setting it to invalid(0) destroys an entry." 
       ::= { ospfNetworkAreaAddressEntry 4 }   
       
                          
--********************************************************************************************************
--********************************************************************************************************  

sntpPollTime OBJECT-TYPE
        SYNTAX      INTEGER(16..16284)
        MAX-ACCESS  read-write
        STATUS      current
        DESCRIPTION "The interval for SNTP clients to send requests to NTP/SNTP."
        ::= { sntpMgt 1 }
        
--********************************************************************************************************

sntpServerTable OBJECT-TYPE
    SYNTAX     SEQUENCE OF SntpServerEntry
    MAX-ACCESS not-accessible
    STATUS     current
    DESCRIPTION
           "The ipv4 sntp server configration table."
    ::= { sntpMgt 2 }
    
sntpServerEntry OBJECT-TYPE
    SYNTAX     SntpServerEntry
    MAX-ACCESS not-accessible
    STATUS     current
    DESCRIPTION
            "A set of configuration parameters for a ipv4 sntp server."
    INDEX      {sntpServerVersion,sntpServerAddress}
    ::= { sntpServerTable 1 }

SntpServerEntry
        ::= SEQUENCE
            {
                sntpServerVersion         INTEGER,          
                sntpServerAddress         IpAddress,
                sntpServerStatus	  INTEGER
            }

sntpServerVersion  OBJECT-TYPE
            SYNTAX      INTEGER   (1..4)    
            MAX-ACCESS  read-only
            STATUS      current
            DESCRIPTION
                "The version of ipv4 sntp server."
            ::= { sntpServerEntry 1}        

sntpServerAddress   OBJECT-TYPE
            SYNTAX      IpAddress     
            MAX-ACCESS  read-only
            STATUS      current
            DESCRIPTION
                "The ipv4 address of the sntp server."
            ::= { sntpServerEntry 2}            
                      

sntpServerStatus OBJECT-TYPE
             SYNTAX      INTEGER 
                 {
            	    active(1),
            	    destroy (2)              	
            	}     
            MAX-ACCESS  read-create
            STATUS      current
            DESCRIPTION
                "Now state."
            ::= { sntpServerEntry 3 } 
            
sntpServer6Table OBJECT-TYPE
    SYNTAX     SEQUENCE OF SntpServer6Entry
    MAX-ACCESS not-accessible
    STATUS     current
    DESCRIPTION
           "The ipv6 sntp server configration table."
    ::= { sntpMgt 3 }
    
sntpServer6Entry OBJECT-TYPE
    SYNTAX     SntpServer6Entry
    MAX-ACCESS not-accessible
    STATUS     current
    DESCRIPTION
            "A set of configuration parameters for a ipv6 sntp server."
    INDEX      {sntpServer6Version,sntpServer6Address}
    ::= { sntpServer6Table 1 }

SntpServer6Entry
        ::= SEQUENCE
            {
                sntpServer6Version         INTEGER,           
                sntpServer6Address         Ipv6Address,
                sntpServer6Status	  INTEGER
            } 
                 
sntpServer6Version  OBJECT-TYPE
            SYNTAX      INTEGER   (1..4)    
            MAX-ACCESS  read-only
            STATUS      current
            DESCRIPTION
                "The version of ipv6 sntp server."
            ::= { sntpServer6Entry 1}  

sntpServer6Address   OBJECT-TYPE
            SYNTAX      Ipv6Address     
            MAX-ACCESS  read-only
            STATUS      current
            DESCRIPTION
                "The IP address of the ipv6 sntp server."
            ::= { sntpServer6Entry 2}                              

sntpServer6Status OBJECT-TYPE
             SYNTAX      INTEGER 
                 {
            	    active(1),
            	    destroy (2)              	
            	}     
            MAX-ACCESS  read-create
            STATUS      current
            DESCRIPTION
                "Now state."
            ::= { sntpServer6Entry 3 }             

sntpTimeZone  OBJECT 	IDENTIFIER ::= { sntpMgt 4 }

sntpTimeZoneName OBJECT-TYPE
    SYNTAX      DisplayString
    MAX-ACCESS  read-write
    STATUS      current
    DESCRIPTION "The name of sntp time zone."
    ::= { sntpTimeZone 1 }

sntpTimeZoneType OBJECT-TYPE
    SYNTAX      INTEGER
    		{
    			add(1),
    			subtract(0)
    		}
    MAX-ACCESS  read-write
    STATUS      current
    DESCRIPTION "The type of sntp time zone."
    ::= { sntpTimeZone 2 }

sntpTimeZoneTime OBJECT-TYPE
    SYNTAX      INTEGER(0..12)
    MAX-ACCESS  read-write
    STATUS      current
    DESCRIPTION "The interval time of sntp time zone."
    ::= { sntpTimeZone 3 }
     
sntpTimeZoneStatus OBJECT-TYPE
    SYNTAX      INTEGER
    		{
            	    	createAndGo(0),
               		active(1),
               		destroy(2)
               	}	    
    MAX-ACCESS  read-write
    STATUS      current
    DESCRIPTION "now state of sntp time zone."
    ::= { sntpTimeZone 4 }    

--********************************************************************************************************
--******************************************************************************************************** 
--xxx.100.18.1 Urpf 

urpfEnable OBJECT-TYPE
        SYNTAX  INTEGER {
                enable (1),
                disable (0)
            }
        MAX-ACCESS  read-write
        STATUS      current
        DESCRIPTION " Global Enable or disable the Unicast reverse path forwarding."
        ::= { urpf 1 }
        
-- The Urpf Interface Configration Table

urpfPortTable OBJECT-TYPE
    SYNTAX     SEQUENCE OF UrpfPortEntry
    MAX-ACCESS not-accessible
    STATUS     current
    DESCRIPTION
           "The URPF port configration table."
    ::= { urpf 2 }
    
--xxx.100.18.1.1
urpfPortEntry OBJECT-TYPE
    SYNTAX     UrpfPortEntry
    MAX-ACCESS not-accessible
    STATUS     current
    DESCRIPTION
            "The index of this table is port index."
    INDEX      { urpfPortIndex }
    ::= { urpfPortTable 1 }

UrpfPortEntry
        ::= SEQUENCE
            {
                urpfPortIndex              INTEGER,
                urpfPortMode                 INTEGER,
                urpfPortAllowDefault         INTEGER,
                urpfPortStatus		           INTEGER
            }
       
--xxx.100.18.1.1.1
urpfPortIndex  OBJECT-TYPE
            SYNTAX      INTEGER 
            MAX-ACCESS  read-only
            STATUS      current
            DESCRIPTION
                "Port Index."
            ::= { urpfPortEntry 1 }

--xxx.100.18.1.1.2
urpfPortMode   OBJECT-TYPE
            SYNTAX      INTEGER 
             {
            		  loose(1),
            	   strict(0)               	
            	}     
            MAX-ACCESS  read-create
            STATUS      current
            DESCRIPTION
                "Configration of the URPF mode on the port."
            ::= { urpfPortEntry 2}            
                    
--xxx.100.18.1.1.3
urpfPortAllowDefault  OBJECT-TYPE
            SYNTAX      INTEGER 
            {
            		     allowdefaultroute(1),
            	       noallowdefaultroute(0)               	
            	}     
            MAX-ACCESS  read-create
            STATUS      current
            DESCRIPTION
                "Allow or not allow default route of URPF."
            ::= { urpfPortEntry 3}   

--xxx.100.18.1.1.4
urpfPortStatus OBJECT-TYPE
             SYNTAX      INTEGER 
              {
            		  active(1),
            	    destroy (2)              	
            	}     
            MAX-ACCESS  read-create
            STATUS      current
            DESCRIPTION
                "Setting it to  active(1) to creates an entry,setting it to destroy(2) to destroy an entry."
            ::= { urpfPortEntry 4 }            
--********************************************************************************************************
--******************************************************************************************************** 



--xxx.100.20.1 Dcscm dc

-- The Dcscm dc Enable Table

dcscmdcEnable OBJECT-TYPE
    SYNTAX     INTEGER
    {
        disable(0),
        enable(1)
    }
    MAX-ACCESS read-write
    STATUS     current
    DESCRIPTION
           "Dcscm destination control multicast is disable or enable"
    ::= { dcscm 1 }

--xxx.100.20.2

-- The Dcscm dc Acl Table

dcscmdcAcl  OBJECT IDENTIFIER    ::= { dcscm 2 }

            
--xxx.100.20.2.1
dcscmdcAclNumber  OBJECT-TYPE
            SYNTAX      INTEGER  (6000..7999)
            MAX-ACCESS  read-create
            STATUS      current
            DESCRIPTION
                "Acl number of Dcscm destination control multicast,the range is 6000--7999."
            ::= { dcscmdcAcl 1 }
            
--xxx.100.20.2.2
dcscmdcAclSourceIp  OBJECT-TYPE
            SYNTAX      IpAddress 
            MAX-ACCESS  read-create
            STATUS      current
            DESCRIPTION
                "Source ip address of acl entry "
            ::= { dcscmdcAcl 2}  
      
--xxx.100.20.2.3
dcscmdcAclSourceMask  OBJECT-TYPE
            SYNTAX      IpAddress 
            MAX-ACCESS  read-create
            STATUS      current
            DESCRIPTION
                "Source Mask of acl entry "
            ::= { dcscmdcAcl 3}        

--xxx.100.20.2.4
dcscmdcAclDestinationIp  OBJECT-TYPE
            SYNTAX      IpAddress 
            MAX-ACCESS  read-create
            STATUS      current
            DESCRIPTION
                "Destination ip address of acl entry.the destination ip must be a valid multicast group address. "
            ::= { dcscmdcAcl 4}              
            
--xxx.100.20.2.5
dcscmdcAclDestinationMask  OBJECT-TYPE
            SYNTAX      IpAddress 
            MAX-ACCESS  read-create
            STATUS      current
            DESCRIPTION
                "Destination Mask of acl entry. the destination mask should meet the request of muticast group address. "
            ::= { dcscmdcAcl 5} 

--xxx.100.20.2.6
dcscmdcAclPermitOrDeny  OBJECT-TYPE
            SYNTAX      INTEGER  
            {
            permit(1),
            deny(0),
            deltheAcl(2)
            }
            MAX-ACCESS  read-write
            STATUS      current
            DESCRIPTION
                " acl entry permit or deny ; 0:deny; 1:permit; 2:del this acl entry"
            ::= { dcscmdcAcl 6}    
 
--xxx.100.20.3

-- The DCSCM VMac Destination binding Table

dcscmVMacbindingTable OBJECT-TYPE
    SYNTAX     SEQUENCE OF DcscmVMacbindingEntry
    MAX-ACCESS not-accessible
    STATUS     current
    DESCRIPTION
           "dcscm destination control multicast, Acl is binded to VMac"
    ::= { dcscm 3 }
--xxx.100.20.3.1
dcscmVMacbindingEntry OBJECT-TYPE
    SYNTAX     DcscmVMacbindingEntry
    MAX-ACCESS not-accessible
    STATUS     current
    DESCRIPTION
            "The index of this table is Vlanid,MacAddress"
    INDEX      { dcscmVMacbindingVlanid,dcscmVMacbindingMacAddr }
    ::= { dcscmVMacbindingTable 1 }

DcscmVMacbindingEntry
        ::= SEQUENCE
            {
                dcscmVMacbindingVlanid            INTEGER,
                dcscmVMacbindingMacAddr           MacAddress,
                dcscmVMacbindingAclNumber         INTEGER
            }
            
--xxx.100.20.3.1.1
dcscmVMacbindingVlanid  OBJECT-TYPE
            SYNTAX      INTEGER  (1..4094) 
            MAX-ACCESS  read-only
            STATUS      current
            DESCRIPTION
                " Dcscm destination control multicast,The vlanid of rule"
            ::= { dcscmVMacbindingEntry 1 }  
 
--xxx.100.20.3.1.2
dcscmVMacbindingMacAddr  OBJECT-TYPE
            SYNTAX      MacAddress (SIZE(17)) 
            MAX-ACCESS  read-only
            STATUS      current
            DESCRIPTION
                " Dcscm destination control multicast,The Mac Address of rule"
            ::= { dcscmVMacbindingEntry 2 }    
            
--xxx.100.20.3.1.3
dcscmVMacbindingAclNumber  OBJECT-TYPE
            SYNTAX      INTEGER  (0|6000..7999)
            MAX-ACCESS  read-write
            STATUS      current
            DESCRIPTION
                " Dcscm destination control multicast,The Acl number of rule ; 0 means del the rule binded to vmac"
            ::= { dcscmVMacbindingEntry 3 }                                

--xxx.100.20.4

-- The DCSCM Sip Destination binding Table

dcscmSipbindingTable OBJECT-TYPE
    SYNTAX     SEQUENCE OF DcscmSipbindingEntry
    MAX-ACCESS not-accessible
    STATUS     current
    DESCRIPTION
           "dcscm destination control multicast, Acl is binded to Sip"
    ::= { dcscm 4 }    
--xxx.100.20.4.1
dcscmSipbindingEntry OBJECT-TYPE
    SYNTAX     DcscmSipbindingEntry
    MAX-ACCESS not-accessible
    STATUS     current
    DESCRIPTION
            "The index of this table is Sourceip,SourceMask "
    INDEX      { dcscmSipbindingSipAddress,dcscmSipbindingSipMask }
    ::= { dcscmSipbindingTable 1 }

DcscmSipbindingEntry
        ::= SEQUENCE
            {
                dcscmSipbindingSipAddress           IpAddress,
                dcscmSipbindingSipMask              INTEGER,
                dcscmSipbindingAclNumber         INTEGER
            }
            
--xxx.100.20.4.1.1
dcscmSipbindingSipAddress  OBJECT-TYPE
            SYNTAX      IpAddress 
            MAX-ACCESS  read-only
            STATUS      current
            DESCRIPTION
                " Dcscm destination control multicast,The Source ip of rule"
            ::= { dcscmSipbindingEntry 1 }  
 
--xxx.100.20.4.1.2
dcscmSipbindingSipMask  OBJECT-TYPE
            SYNTAX      INTEGER 
            MAX-ACCESS  read-only
            STATUS      current
            DESCRIPTION
                " Dcscm destination control multicast,The Source ip mask len of rule"
            ::= { dcscmSipbindingEntry 2 }    
            
--xxx.100.20.4.1.3
dcscmSipbindingAclNumber  OBJECT-TYPE
            SYNTAX      INTEGER   (0|6000..7999)
            MAX-ACCESS  read-write
            STATUS      current
            DESCRIPTION
                " Dcscm destination control multicast,The Acl number of rule;0 means del the rule binded to sip"
            ::= { dcscmSipbindingEntry 3 }
            
--xxx.100.20.5

-- The DCSCM Port Destination binding Table

dcscmdcPortbindingTable OBJECT-TYPE
    SYNTAX     SEQUENCE OF DcscmdcPortbindingEntry
    MAX-ACCESS not-accessible
    STATUS     current
    DESCRIPTION
           "dcscm destination control multicast, Acl is binded to Port"
    ::= { dcscm 5 }
--xxx.100.20.5.1
dcscmdcPortbindingEntry OBJECT-TYPE
    SYNTAX     DcscmdcPortbindingEntry
    MAX-ACCESS not-accessible
    STATUS     current
    DESCRIPTION
            "The index of this table is PortName"
    INDEX      { dcscmdcPortbindingPortName }
    ::= { dcscmdcPortbindingTable 1 }

DcscmdcPortbindingEntry
        ::= SEQUENCE
            {
                dcscmdcPortbindingPortName           INTEGER,
                dcscmdcPortbindingAclNumber         INTEGER
            }
            
--xxx.100.20.5.1.1
dcscmdcPortbindingPortName  OBJECT-TYPE
            SYNTAX      INTEGER
            MAX-ACCESS  read-only
            STATUS      current
            DESCRIPTION
                " Dcscm destination control multicast,The Port index of rule"
            ::= { dcscmdcPortbindingEntry 1 }  
 
--xxx.100.20.5.1.2
dcscmdcPortbindingAclNumber  OBJECT-TYPE
            SYNTAX      INTEGER  (0|6000..7999)
            MAX-ACCESS  read-write
            STATUS      current
            DESCRIPTION
                " Dcscm destination control multicast,The Acl number of rule;0 means del the rule binded to port"
            ::= { dcscmdcPortbindingEntry 2 }  
            
--xxx.100.20.6 Dcscm sc

-- The Dcscm sc Enable Table

dcscmscEnable OBJECT-TYPE
    SYNTAX     INTEGER
    {
        disable(0),
        enable(1)
    }
    MAX-ACCESS read-write
    STATUS     current
    DESCRIPTION
           "dcscm source control multicast is disable or enable"
    ::= { dcscm 6 }

--xxx.100.20.7

-- The DCSCM Sc Acl Table

dcscmscAcl  OBJECT IDENTIFIER  ::= { dcscm 7 }

            
--xxx.100.20.7.1
dcscmscAclNumber  OBJECT-TYPE
            SYNTAX      INTEGER (5000..5099)
            MAX-ACCESS  read-write
            STATUS      current
            DESCRIPTION
                "Acl number of Dcscm source control multicast,the range is 5000--5099."
            ::= { dcscmscAcl 1 }
            
--xxx.100.20.7.2
dcscmscAclSourceIp  OBJECT-TYPE
            SYNTAX      IpAddress 
            MAX-ACCESS  read-write
            STATUS      current
            DESCRIPTION
                "Source ip address of acl entry "
            ::= { dcscmscAcl 2}  
      
--xxx.100.20.7.3
dcscmscAclSourceMask  OBJECT-TYPE
            SYNTAX      IpAddress 
            MAX-ACCESS  read-write
            STATUS      current
            DESCRIPTION
                "Source Mask of acl entry "
            ::= { dcscmscAcl 3}        

--xxx.100.20.7.4
dcscmscAclDestinationIp  OBJECT-TYPE
            SYNTAX      IpAddress 
            MAX-ACCESS  read-write
            STATUS      current
            DESCRIPTION
                "Destination ip address of acl entry, the destination ip must be a valid multicast group address."
            ::= { dcscmscAcl 4}              
            
--xxx.100.20.7.5
dcscmscAclDestinationMask  OBJECT-TYPE
            SYNTAX      IpAddress 
            MAX-ACCESS  read-write
            STATUS      current
            DESCRIPTION
                "Destination Mask of acl entry, the destination mask should meet the request of muticast group address."
            ::= { dcscmscAcl 5} 

--xxx.100.20.7.6
dcscmscAclPermitOrDeny  OBJECT-TYPE
            SYNTAX      INTEGER 
            {
            permit(1),
            deny(0),
            deltheAcl(2)
            }
            MAX-ACCESS  read-write
            STATUS      current
            DESCRIPTION
                " acl entry permit or deny;0:deny; 1:permit; 2:del this acl"
            ::= { dcscmscAcl 6} 
            
--xxx.100.20.8

-- The DCSCM Sc Port binding Table

dcscmscPortbindingTable OBJECT-TYPE
    SYNTAX     SEQUENCE OF DcscmscPortbindingEntry
    MAX-ACCESS not-accessible
    STATUS     current
    DESCRIPTION
           "dcscm destination control multicast, Acl is binded to Port"
    ::= { dcscm 8 }
--xxx.100.20.8.1
dcscmscPortbindingEntry OBJECT-TYPE
    SYNTAX     DcscmscPortbindingEntry
    MAX-ACCESS not-accessible
    STATUS     current
    DESCRIPTION
            "The index of this table is PortName"
    INDEX      { dcscmscPortbindingPortName }
    ::= { dcscmscPortbindingTable 1 }

DcscmscPortbindingEntry
        ::= SEQUENCE
            {
                dcscmscPortbindingPortName           INTEGER,
                dcscmscPortbindingAclNumber          INTEGER
            }
            
--xxx.100.20.8.1.1
dcscmscPortbindingPortName  OBJECT-TYPE
            SYNTAX      INTEGER
            MAX-ACCESS  read-only
            STATUS      current
            DESCRIPTION
                " Dcscm source control multicast,The Port Number of rule"
            ::= { dcscmscPortbindingEntry 1 }  
 
--xxx.100.20.8.1.2
dcscmscPortbindingAclNumber  OBJECT-TYPE
            SYNTAX      INTEGER  (0|5000..5099)
            MAX-ACCESS  read-write
            STATUS      current
            DESCRIPTION
                " Dcscm source control multicast,The Acl number of rule ; 0 means to del the rule binded to port"
            ::= { dcscmscPortbindingEntry 2 } 
                         
--xxx.100.20.9

-- The DCSCM Policy multicast Table

dcscmpcTable OBJECT-TYPE
    SYNTAX     SEQUENCE OF DcscmpcEntry
    MAX-ACCESS not-accessible
    STATUS     current
    DESCRIPTION
           "dcscm policy multicast table"
    ::= { dcscm 9 }
--xxx.100.20.9.1
dcscmpcEntry OBJECT-TYPE
    SYNTAX     DcscmpcEntry
    MAX-ACCESS not-accessible
    STATUS     current
    DESCRIPTION
            "The index of this table is dcscmpcSourceIp,dcscmpcSourceMasklen,dcscmpcDestinationIp,dcscmpcDestinationMasklen"
    INDEX      {dcscmpcSourceIp,dcscmpcSourceMasklen,dcscmpcDestinationIp,dcscmpcDestinationMasklen}
    ::= { dcscmpcTable 1 }

DcscmpcEntry
        ::= SEQUENCE
            {
                dcscmpcSourceIp		          IpAddress,
                dcscmpcSourceMasklen   		   INTEGER,
                dcscmpcDestinationIp        IpAddress,
                dcscmpcDestinationMasklen      INTEGER,
                dcscmpccos                  INTEGER
            }
            
--xxx.100.20.9.1.1
dcscmpcSourceIp  OBJECT-TYPE
            SYNTAX      IpAddress 
            MAX-ACCESS  read-only
            STATUS      current
            DESCRIPTION
                "source ip address of policy multicast "
            ::= { dcscmpcEntry 1}  
      
--xxx.100.20.9.1.2
dcscmpcSourceMasklen  OBJECT-TYPE
            SYNTAX      INTEGER 
            MAX-ACCESS  read-only
            STATUS      current
            DESCRIPTION
                "Mask length of source Ip"
            ::= { dcscmpcEntry 2}        

--xxx.100.20.9.1.3
dcscmpcDestinationIp  OBJECT-TYPE
            SYNTAX      IpAddress 
            MAX-ACCESS  read-only
            STATUS      current
            DESCRIPTION
                "Destination ip address of policy multicast,the destination ip must be a valid multicast group address. "
            ::= { dcscmpcEntry 3}              
            
--xxx.100.20.9.1.4
dcscmpcDestinationMasklen  OBJECT-TYPE
            SYNTAX      INTEGER 
            MAX-ACCESS  read-only
            STATUS      current
            DESCRIPTION
                "Mask length of destination Ip"
            ::= { dcscmpcEntry 4} 

--xxx.100.20.9.1.5
dcscmpccos  OBJECT-TYPE
            SYNTAX      INTEGER (0..8)
            MAX-ACCESS  read-write
            STATUS      current
            DESCRIPTION
                " cos value of policy multicast; between 0 and 7 ;8 means to del the policy"
            ::= { dcscmpcEntry 5} 
            

--xxx.100.21.1 Dcscm6 dc

-- The Dcscm6 dc Enable Table

dcscm6dcEnable OBJECT-TYPE
    SYNTAX     INTEGER
    {
        disable(0),
        enable(1)
    }
    MAX-ACCESS read-write
    STATUS     current
    DESCRIPTION
           "dcscm6 destination control multicast is disable or enable"
    ::= { dcscm6 1 }

--xxx.100.21.2

-- The DCSCM6 dc Acl Table

dcscm6dcAcl OBJECT IDENTIFIER  ::= { dcscm6 2 }

            
--xxx.100.21.2.1
dcscm6dcAclNumber  OBJECT-TYPE
            SYNTAX      INTEGER (9000..10999)
            MAX-ACCESS  read-write
            STATUS      current
            DESCRIPTION
                "Acl number of Dcscm6 destination control multicast,the range is 9000--10999."
            ::= { dcscm6dcAcl 1 }
            
--xxx.100.21.2.2
dcscm6dcAclSourceIp  OBJECT-TYPE
            SYNTAX      Ipv6Address 
            MAX-ACCESS  read-write
            STATUS      current
            DESCRIPTION
                "Source ip address of acl entry "
            ::= { dcscm6dcAcl 2}  
      
--xxx.100.21.2.3
dcscm6dcAclSourceMask  OBJECT-TYPE
            SYNTAX      INTEGER (1..128) 
            MAX-ACCESS  read-write
            STATUS      current
            DESCRIPTION
                "Source MaskLen of acl entry "
            ::= { dcscm6dcAcl 3}        

--xxx.100.21.2.4
dcscm6dcAclDestinationIp  OBJECT-TYPE
            SYNTAX      Ipv6Address 
            MAX-ACCESS  read-write
            STATUS      current
            DESCRIPTION
                "Destination ip address of acl entry,the destination ip must be a valid multicast group address. "
            ::= { dcscm6dcAcl 4}              
            
--xxx.100.21.2.5
dcscm6dcAclDestinationMask  OBJECT-TYPE
            SYNTAX      INTEGER (8..128)
            MAX-ACCESS  read-write
            STATUS      current
            DESCRIPTION
                "Destination MaskLen of acl entry ,the mask length should meet the request of multicast group address."
            ::= { dcscm6dcAcl 5} 

--xxx.100.21.2.6
dcscm6dcAclPermitOrDeny  OBJECT-TYPE
            SYNTAX      INTEGER 
            {
            permit(1),
            deny(0),
            deltheAcl(2)
            }
            MAX-ACCESS  read-write
            STATUS      current
            DESCRIPTION
                " acl entry permit or deny; 0:deny; 1:permit; 2:del this acl"
            ::= { dcscm6dcAcl 6}    
 
--xxx.100.21.3

-- The DCSCM6 VMac Destination binding Table

dcscm6VMacbindingTable OBJECT-TYPE
    SYNTAX     SEQUENCE OF Dcscm6VMacbindingEntry
    MAX-ACCESS not-accessible
    STATUS     current
    DESCRIPTION
           "dcscm6 destination control multicast, Acl is binded to VMac"
    ::= { dcscm6 3 }
--xxx.100.21.3.1
dcscm6VMacbindingEntry OBJECT-TYPE
    SYNTAX     Dcscm6VMacbindingEntry
    MAX-ACCESS not-accessible
    STATUS     current
    DESCRIPTION
            "The index of this table is Vlanid,MacAddress"
    INDEX      { dcscm6VMacbindingVlanid,dcscm6VMacbindingMacAddr }
    ::= { dcscm6VMacbindingTable 1 }

Dcscm6VMacbindingEntry
        ::= SEQUENCE
            {
                dcscm6VMacbindingVlanid            INTEGER,
                dcscm6VMacbindingMacAddr           MacAddress,
                dcscm6VMacbindingAclNumber         INTEGER
            }
            
--xxx.100.21.3.1.1
dcscm6VMacbindingVlanid  OBJECT-TYPE
            SYNTAX      INTEGER (1..4094)
            MAX-ACCESS  read-only
            STATUS      current
            DESCRIPTION
                " Dcscm6 destination control multicast,The vlanid of rule"
            ::= { dcscm6VMacbindingEntry 1 }  
 
--xxx.100.21.3.1.2
dcscm6VMacbindingMacAddr  OBJECT-TYPE
            SYNTAX      MacAddress  (SIZE(17))
            MAX-ACCESS  read-only
            STATUS      current
            DESCRIPTION
                " Dcscm6 destination control multicast,The Mac Address of rule"
            ::= { dcscm6VMacbindingEntry 2 }    
            
--xxx.100.21.3.1.3
dcscm6VMacbindingAclNumber  OBJECT-TYPE
            SYNTAX      INTEGER (0|9000..10999)
            MAX-ACCESS  read-write
            STATUS      current
            DESCRIPTION
                " Dcscm6 destination control multicast,The Acl number of rule;0 means del the rule binded to vmac"
            ::= { dcscm6VMacbindingEntry 3 }                                

--xxx.100.21.4

-- The DCSCM6 Sip Destination binding Table

dcscm6SipbindingTable OBJECT-TYPE
    SYNTAX     SEQUENCE OF Dcscm6SipbindingEntry
    MAX-ACCESS not-accessible
    STATUS     current
    DESCRIPTION
           "dcscm6 destination control multicast, Acl is binded to Sip"
    ::= { dcscm6 4 }    
--xxx.100.21.4.1
dcscm6SipbindingEntry OBJECT-TYPE
    SYNTAX     Dcscm6SipbindingEntry
    MAX-ACCESS not-accessible
    STATUS     current
    DESCRIPTION
            "The index of this table is Sourceip,SourceMaskLen "
    INDEX      { dcscm6SipbindingSipAddress,dcscm6SipbindingSipMaskLen }
    ::= { dcscm6SipbindingTable 1 }

Dcscm6SipbindingEntry
        ::= SEQUENCE
            {
                dcscm6SipbindingSipAddress           Ipv6Address,
                dcscm6SipbindingSipMaskLen           INTEGER,
                dcscm6SipbindingAclNumber         INTEGER
            }
            
--xxx.100.21.4.1.1
dcscm6SipbindingSipAddress  OBJECT-TYPE
            SYNTAX      Ipv6Address 
            MAX-ACCESS  read-only
            STATUS      current
            DESCRIPTION
                " Dcscm6 destination control multicast,The Source ip of rule"
            ::= { dcscm6SipbindingEntry 1 }  
 
--xxx.100.21.4.1.2
dcscm6SipbindingSipMaskLen  OBJECT-TYPE
            SYNTAX      INTEGER (1..128)
            MAX-ACCESS  read-only
            STATUS      current
            DESCRIPTION
                " Dcscm6 destination control multicast,The Source ip mask len of rule"
            ::= { dcscm6SipbindingEntry 2 }    
            
--xxx.100.21.4.1.3
dcscm6SipbindingAclNumber  OBJECT-TYPE
            SYNTAX      INTEGER (0|9000..10999)
            MAX-ACCESS  read-write
            STATUS      current
            DESCRIPTION
                " Dcscm6 destination control multicast,The Acl number of rule;0 means del the rule binded to sip"
            ::= { dcscm6SipbindingEntry 3 }
            
--xxx.100.21.5

-- The DCSCM6 Port Destination binding Table

dcscm6dcPortbindingTable OBJECT-TYPE
    SYNTAX     SEQUENCE OF Dcscm6dcPortbindingEntry
    MAX-ACCESS not-accessible
    STATUS     current
    DESCRIPTION
           "dcscm6 destination control multicast, Acl is binded to Port"
    ::= { dcscm6 5 }
--xxx.100.21.5.1
dcscm6dcPortbindingEntry OBJECT-TYPE
    SYNTAX     Dcscm6dcPortbindingEntry
    MAX-ACCESS not-accessible
    STATUS     current
    DESCRIPTION
            "The index of this table is PortName"
    INDEX      { dcscm6dcPortbindingPortName }
    ::= { dcscm6dcPortbindingTable 1 }

Dcscm6dcPortbindingEntry
        ::= SEQUENCE
            {
                dcscm6dcPortbindingPortName           INTEGER,
                dcscm6dcPortbindingAclNumber         INTEGER
            }
            
--xxx.100.21.5.1.1
dcscm6dcPortbindingPortName  OBJECT-TYPE
            SYNTAX      INTEGER
            MAX-ACCESS  read-only
            STATUS      current
            DESCRIPTION
                " Dcscm6 destination control multicast,The Port Number of rule"
            ::= { dcscm6dcPortbindingEntry 1 }  
 
--xxx.100.21.5.1.2
dcscm6dcPortbindingAclNumber  OBJECT-TYPE
            SYNTAX      INTEGER (0|9000..10999)
            MAX-ACCESS  read-write
            STATUS      current
            DESCRIPTION
                " Dcscm6 destination control multicast,The Acl number of rule;0 means del the rule binded to port"
            ::= { dcscm6dcPortbindingEntry 2 }  
            
--xxx.100.21.6 Dcscm6 sc

-- The Dcscm6 sc Enable Table

dcscm6scEnable OBJECT-TYPE
    SYNTAX     INTEGER
    {
        disable(0),
        enable(1)
    }
    MAX-ACCESS read-write
    STATUS     current
    DESCRIPTION
           "dcscm6 source control multicast is disable or enable"
    ::= { dcscm6 6 }

--xxx.100.21.7

-- The DCSCM6 Sc Acl Table

dcscm6scAcl OBJECT IDENTIFIER   ::= { dcscm6 7 }
            
--xxx.100.21.7.1
dcscm6scAclNumber  OBJECT-TYPE
            SYNTAX      INTEGER (8000..8099)
            MAX-ACCESS  read-write
            STATUS      current
            DESCRIPTION
                "Acl number of Dcscm6 source control multicast.the range is 8000--8099"
            ::= { dcscm6scAcl 1 }
            
--xxx.100.21.7.2
dcscm6scAclSourceIp  OBJECT-TYPE
            SYNTAX      Ipv6Address
            MAX-ACCESS  read-write
            STATUS      current
            DESCRIPTION
                "Source ip address of acl entry "
            ::= { dcscm6scAcl 2}  
      
--xxx.100.21.7.3
dcscm6scAclSourceMask  OBJECT-TYPE
            SYNTAX      INTEGER (1..128)
            MAX-ACCESS  read-write
            STATUS      current
            DESCRIPTION
                "Source MaskLen of acl entry "
            ::= { dcscm6scAcl 3}        

--xxx.100.21.7.4
dcscm6scAclDestinationIp  OBJECT-TYPE
            SYNTAX      Ipv6Address 
            MAX-ACCESS  read-write
            STATUS      current
            DESCRIPTION
                "Destination ip address of acl entry,the destination ip must be a valid multicast group address. "
            ::= { dcscm6scAcl 4}              
            
--xxx.100.21.7.5
dcscm6scAclDestinationMask  OBJECT-TYPE
            SYNTAX      INTEGER (8..128)
            MAX-ACCESS  read-write
            STATUS      current
            DESCRIPTION
                "Destination MaskLen of acl entry ,the mask length should meet the request of multicast group address."
            ::= { dcscm6scAcl 5} 

--xxx.100.21.7.6
dcscm6scAclPermitOrDeny  OBJECT-TYPE
            SYNTAX      INTEGER 
            {
            permit(1),
            deny(0),
            deltheAcl(2)
            }
            MAX-ACCESS  read-write
            STATUS      current
            DESCRIPTION
                " acl entry permit or deny; 0:deny; 1:permit; 2:del this acl"
            ::= { dcscm6scAcl 6} 
            
--xxx.100.21.8

-- The DCSCM6 Sc Port Destination binding Table

dcscm6scPortbindingTable OBJECT-TYPE
    SYNTAX     SEQUENCE OF Dcscm6scPortbindingEntry
    MAX-ACCESS not-accessible
    STATUS     current
    DESCRIPTION
           "dcscm6 destination control multicast, Acl is binded to Port"
    ::= { dcscm6 8 }
--xxx.100.21.8.1
dcscm6scPortbindingEntry OBJECT-TYPE
    SYNTAX     Dcscm6scPortbindingEntry
    MAX-ACCESS not-accessible
    STATUS     current
    DESCRIPTION
            "The index of this table is PortName"
    INDEX      { dcscm6scPortbindingPortName }
    ::= { dcscm6scPortbindingTable 1 }

Dcscm6scPortbindingEntry
        ::= SEQUENCE
            {
                dcscm6scPortbindingPortName           INTEGER,
                dcscm6scPortbindingAclNumber          INTEGER
            }
            
--xxx.100.21.8.1.1
dcscm6scPortbindingPortName  OBJECT-TYPE
            SYNTAX      INTEGER
            MAX-ACCESS  read-only
            STATUS      current
            DESCRIPTION
                " Dcscm6 source control multicast,The Port Number of rule"
            ::= { dcscm6scPortbindingEntry 1 }  
 
--xxx.100.21.8.1.2
dcscm6scPortbindingAclNumber  OBJECT-TYPE
            SYNTAX      INTEGER (0|8000..8099)
            MAX-ACCESS  read-write
            STATUS      current
            DESCRIPTION
                " Dcscm6 source control multicast,The Acl number of rule,0 means to del the rule binded to port"
            ::= { dcscm6scPortbindingEntry 2 } 
                         
--xxx.100.21.9

-- The DCSCM6 Policy multicast Table

dcscm6pcTable OBJECT-TYPE
    SYNTAX     SEQUENCE OF Dcscm6pcEntry
    MAX-ACCESS not-accessible
    STATUS     current
    DESCRIPTION
           "dcscm6 policy multicast table"
    ::= { dcscm6 9 }
--xxx.100.21.9.1
dcscm6pcEntry OBJECT-TYPE
    SYNTAX     Dcscm6pcEntry
    MAX-ACCESS not-accessible
    STATUS     current
    DESCRIPTION
            "The index of this table is dcscm6pcSourceIp,dcscm6pcSourceMask,dcscm6pcDestinationIp,dcscm6pcDestinationMask"
    INDEX      {dcscm6pcSourceIp,dcscm6pcSourceMask,dcscm6pcDestinationIp,dcscm6pcDestinationMask}
    ::= { dcscm6pcTable 1 }

Dcscm6pcEntry
        ::= SEQUENCE
            {
                dcscm6pcSourceIp		         Ipv6Address,
                dcscm6pcSourceMask   		     INTEGER,
                dcscm6pcDestinationIp        Ipv6Address,
                dcscm6pcDestinationMask      INTEGER,
                dcscm6pccos                  INTEGER
            }
            
--xxx.100.21.9.1.1
dcscm6pcSourceIp  OBJECT-TYPE
            SYNTAX      Ipv6Address 
            MAX-ACCESS  read-only
            STATUS      current
            DESCRIPTION
                "source ip address of policy multicast "
            ::= { dcscm6pcEntry 1}  
      
--xxx.100.21.9.1.2
dcscm6pcSourceMask  OBJECT-TYPE
            SYNTAX      INTEGER (1..128)
            MAX-ACCESS  read-only
            STATUS      current
            DESCRIPTION
                "Source MaskLen  of policy multicast "
            ::= { dcscm6pcEntry 2}        

--xxx.100.21.9.1.3
dcscm6pcDestinationIp  OBJECT-TYPE
            SYNTAX      Ipv6Address 
            MAX-ACCESS  read-only
            STATUS      current
            DESCRIPTION
                "Destination ip address of policy multicast "
            ::= { dcscm6pcEntry 3}              
            
--xxx.100.21.9.1.4
dcscm6pcDestinationMask  OBJECT-TYPE
            SYNTAX      INTEGER (8..128)
            MAX-ACCESS  read-only
            STATUS      current
            DESCRIPTION
                "Destination MaskLen of policy multicast "
            ::= { dcscm6pcEntry 4} 

--xxx.100.21.9.1.5
dcscm6pccos  OBJECT-TYPE
            SYNTAX      INTEGER  (0..8)
            MAX-ACCESS  read-write
            STATUS      current
            DESCRIPTION
                " cos value of policy multicast; between 0 and 7 ;8 means to del the policy"
            ::= { dcscm6pcEntry 5}  
            
--********************************************************************************************************
--********************************************************************************************************  

--xxx.100.22.1
clusterv2Base            OBJECT IDENTIFIER ::= { prClusterv2 1 }

--xxx.100.22.1.1
clusterv2BaseKey OBJECT-TYPE
    SYNTAX        OCTET STRING (SIZE (1..16))
    MAX-ACCESS    read-write
    STATUS        current
    DESCRIPTION
            "cluster run switch,set the key word only while the cluster is not running
            and you should set it with set clusterv2BaseRun."
    ::= { clusterv2Base 1 }

--xxx.100.22.1.2
clusterv2BaseVlan OBJECT-TYPE
    SYNTAX        INTEGER (1..4094)
    MAX-ACCESS    read-write
    STATUS        current
    DESCRIPTION
            "cluster run switch,set the Vlan only when the cluster is not running
            and you should set it with set clusterv2BaseRun.
            if get result is 0 that the cluser is not running!"
    ::= { clusterv2Base 2 }

--xxx.100.22.1.3
clusterv2BaseRun OBJECT-TYPE
    SYNTAX       INTEGER {
                           enable(1),
                           disable(0)
                          }
    MAX-ACCESS    read-write
    STATUS        current
    DESCRIPTION
            "cluster run switch,set the key word and vlan id or stop the cluster."
    ::= { clusterv2Base 3 }

--xxx.100.22.1.4
clusterv2BaseRole OBJECT-TYPE
    SYNTAX       INTEGER {
                           candidateDevice(1),
                           memberDevice(2),
                           commanderDevice(3),                                          
                           none(255)
                          }
    MAX-ACCESS    read-only
    STATUS        current
    DESCRIPTION
            "The role of the device. 
            none means cluster device isn't running."
    ::= { clusterv2Base 4 }

--xxx.100.22.1.5
clusterv2BaseVersion OBJECT-TYPE
    SYNTAX      OCTET STRING (SIZE (1..10))
    MAX-ACCESS  read-only
    STATUS      current
    DESCRIPTION
            "version of cluster."
    ::= { clusterv2Base 5 }

--xxx.100.22.1.6
clusterv2BaseMaxNumberOfMembers OBJECT-TYPE
    SYNTAX        INTEGER
    MAX-ACCESS    read-only
    STATUS        current
    DESCRIPTION
            "The maximum number of cluster members allowed in the
             cluster.  The command switch is considered as a cluster
             member also."
    ::= { clusterv2Base 6 }
    
--xxx.100.22.1.7    
clusterv2BaseMaxNumberOfSwitches OBJECT-TYPE
    SYNTAX        INTEGER
    MAX-ACCESS    read-only
    STATUS        current
    DESCRIPTION
            "The maximum number of cluster switches allowed in the
             cluster. The Candidates include commander,candidate and member."
    ::= { clusterv2Base 7 }

--xxx.100.22.2
clusterv2Create          OBJECT IDENTIFIER ::= { prClusterv2 2 }

--xxx.100.22.2.1
clusterv2CreateIPPool OBJECT-TYPE
    SYNTAX    IpAddress
    MAX-ACCESS    read-write
    STATUS    current
    DESCRIPTION
        "ip pool.Valid cluster ip-pool format like as 10.x.x.x,default is 10.254.254.1 .
        if get result is 0 that the cluser is not running!
        set it only on the device is not commander and should set it with set clusterv2CreateCmdrOperate." 
    ::= { clusterv2Create 1}

--xxx.100.22.2.2
clusterv2CreateName OBJECT-TYPE
    SYNTAX      OCTET STRING (SIZE (1..32))
   	MAX-ACCESS    read-write
   	STATUS    current
   	DESCRIPTION
       "create the clustername while create the cluster commander,
        set it only on the device is not commander and should set it with set clusterv2CreateCmdrOperate."
   	::= { clusterv2Create 2}

--xxx.100.22.2.3
clusterv2CreateCmdrOperate OBJECT-TYPE
   	SYNTAX    INTEGER {   			   								
                         	create(1),
                         	destroy(0)
                       }
   	MAX-ACCESS    read-write
   	STATUS    current
   	DESCRIPTION
       "if set create ,operation is to build cluster according to clusterv2CreateClusterIPPool/clusterv2StatusClusterName.
        if set destroy , operation is try to clear the IPPool and the ClusterName.
        set create only on the device is not commander.
        set destroy only on the device is commander."
   	::= { clusterv2Create 3}

--xxx.100.22.3
clusterv2Status          OBJECT IDENTIFIER ::= { prClusterv2 3 }

--xxx.100.22.3.1
clusterv2StatusClusterName OBJECT-TYPE
    SYNTAX        OCTET STRING (SIZE (1..32))
    MAX-ACCESS    read-write
    STATUS        current
    DESCRIPTION
            "The name of the cluster.Set only on the device is not commander.The default is NULL."
    ::= { clusterv2Status 1 }

--xxx.100.22.3.2
clusterv2StatusKeepalive OBJECT-TYPE
    SYNTAX    INTEGER (3..30)
    MAX-ACCESS    read-write
    STATUS    current
    DESCRIPTION
        "cluster keepalive interval(3-30 second).
        if get result is 0 that the cluser is not running!"
    ::= { clusterv2Status 2 }

--xxx.100.22.3.3
clusterv2StatusLoss-count OBJECT-TYPE
    SYNTAX    INTEGER (1..10)
    MAX-ACCESS    read-write
    STATUS    current
    DESCRIPTION
        "cluster the max(1-10) loss-count packet during the keeplive interval.
        if get result is 0 that the cluser is not running!"
    ::= { clusterv2Status 3}

--xxx.100.22.4
clusterv2Commander       OBJECT IDENTIFIER ::= { prClusterv2 4 }

--xxx.100.22.4.1
clusterv2CommanderAutoAddMem OBJECT-TYPE
    SYNTAX       INTEGER {
                           enable(1),
                           disable(0)
                          }
    MAX-ACCESS    read-write
    STATUS        current
    DESCRIPTION
            "auto add mem switch"
    ::= { clusterv2Commander 1 }

--xxx.100.22.4.2
clusterv2MemberCounter OBJECT-TYPE
    SYNTAX        Counter32
    MAX-ACCESS    read-only
    STATUS        current
    DESCRIPTION
            "member number on commander,read only on commander or will return 65535."
    ::= { clusterv2Commander 2 }

--xxx.100.22.4.3
clusterv2MemberTable OBJECT-TYPE
    SYNTAX      SEQUENCE OF Clusterv2MemberEntry
    MAX-ACCESS  not-accessible
    STATUS      current
    DESCRIPTION
            "This table contains one row per cluster member,
            including the command switch,read only on commander."
    ::= { clusterv2Commander 3 }
--xxx.100.22.4.3.1
clusterv2MemberEntry OBJECT-TYPE
    SYNTAX      Clusterv2MemberEntry
    MAX-ACCESS  not-accessible
    STATUS      current
    DESCRIPTION
            "An entry containing cluster management information
            applicable to a particular cluster member."
    INDEX { clusterv2MemberNumber }
    ::= { clusterv2MemberTable 1 }

Clusterv2MemberEntry ::= 
      SEQUENCE {
      				 clusterv2MemberNumber                  INTEGER,
               clusterv2MemberIpAddress               IpAddress,               
               clusterv2MemberMacAddress              MacAddress,
               clusterv2MemberOperStatus              INTEGER,
               clusterv2MemberHostName		    				OCTET STRING,
               clusterv2MemberDeviceType		    			OCTET STRING
      }

--xxx.100.22.4.3.1.1
clusterv2MemberNumber OBJECT-TYPE
    SYNTAX      INTEGER
    MAX-ACCESS  read-only
    STATUS      current
    DESCRIPTION
            "An arbitrary value which uniquely identifies the 
             cluster member switch number. It ranges from 1 to
             clusterv2StatusMaxNumberOfMembers,read only on commander."
    ::= { clusterv2MemberEntry 1 }
    
--xxx.100.22.4.3.1.2
clusterv2MemberIpAddress OBJECT-TYPE
    SYNTAX      IpAddress
    MAX-ACCESS  read-only
    STATUS      current
    DESCRIPTION
            "The management ip address of the member device."
    ::= { clusterv2MemberEntry 2 }

--xxx.100.22.4.3.1.3
clusterv2MemberOperStatus OBJECT-TYPE
    SYNTAX      INTEGER {
                           notMember(1),
    											 inactiveMember(2),
    											 memberTobe(3),
    											 activeMember(4)
                        }
    MAX-ACCESS  read-only
    STATUS      current
    DESCRIPTION
            "The status of cluster management connectivity between
             the command switch and a cluster member. Cluster management
             connectivity is determined by the exchange of cluster
             management messages between the command switch and a
             cluster member."
    ::= { clusterv2MemberEntry 3 }

--xxx.100.22.4.3.1.4
clusterv2MemberMacAddress OBJECT-TYPE
    SYNTAX      MacAddress (SIZE(17))
    MAX-ACCESS  read-only
    STATUS      current
    DESCRIPTION
            "The management MAC address of the member device."
    ::= { clusterv2MemberEntry 4 }

--xxx.100.22.4.3.1.5 
clusterv2MemberHostName OBJECT-TYPE
    SYNTAX        OCTET STRING (SIZE (1..32))
    MAX-ACCESS    read-only
    STATUS        current
    DESCRIPTION
            ""
    ::= { clusterv2MemberEntry 5 }

--xxx.100.22.4.3.1.6
clusterv2MemberDeviceType OBJECT-TYPE
    SYNTAX        OCTET STRING (SIZE (1..32))
    MAX-ACCESS    read-only
    STATUS        current
    DESCRIPTION
            "deviceType such as 5526S, 2008A etc"
    ::= { clusterv2MemberEntry 6 }   
    
--The Cluster Candidate Table
--xxx.100.22.4.4
clusterv2CandidateCounter OBJECT-TYPE
    SYNTAX        Counter32
    MAX-ACCESS    read-only
    STATUS        current
    DESCRIPTION
            "candidate number on commander,read only on commander or will return 65535."
    ::= { clusterv2Commander 4 }
--xxx.100.22.4.5
clusterv2CandidateTable OBJECT-TYPE
    SYNTAX      SEQUENCE OF Clusterv2CandidateEntry
    MAX-ACCESS  not-accessible
    STATUS      current
    DESCRIPTION
            "This table contains one row per cluster candidate,
             A cluster candidate is a device that is currently
             eligible to be added to the cluster of a command
             switch.  A device is eligible if it satisfies the
             following conditions:
             1. It start the cluster func.
             2. It is in a same L2 LAN with commander switch
       
             The entries in this table and the entries in 
             clusterMemberTable are mutually exclusive at all
             times.  That is, any device that is a cluster
             member never shows up in the clusterCandidateTable
             or is never a candidate at the same time .  Also, any 
             candidate that shows up in clusterCandidateTable should not
             appear in clusterMemberTable."
    ::= { clusterv2Commander 5 }

--xxx.100.22.4.5.1
clusterv2CandidateEntry       OBJECT-TYPE
    SYNTAX      Clusterv2CandidateEntry
    MAX-ACCESS  not-accessible
    STATUS      current
    DESCRIPTION
            "An entry pertaining to a single candidate device."
    INDEX { clusterv2CandidateId }
    ::= { clusterv2CandidateTable 1 }

Clusterv2CandidateEntry ::= SEQUENCE {
      clusterv2CandidateId    INTEGER,
      clusterv2CandidateMacAddress    MacAddress,
      clusterv2CandidateHostName			OCTET STRING,
      clusterv2CandidateDeviceType		OCTET STRING
}

--xxx.100.22.4.5.1.1
clusterv2CandidateId OBJECT-TYPE
    SYNTAX      INTEGER
    MAX-ACCESS  read-only
    STATUS      current
    DESCRIPTION
            "The candidate id."
    ::= { clusterv2CandidateEntry 1 }


--xxx.100.22.4.5.1.2
clusterv2CandidateMacAddress OBJECT-TYPE
    SYNTAX      MacAddress (SIZE(17))
    MAX-ACCESS  read-only
    STATUS      current
    DESCRIPTION
            "The MAC address of a device qualified to
             to be a cluster member of the command switch 
             cluster."
    ::= { clusterv2CandidateEntry 2 }    

--xxx.100.22.4.5.1.3
clusterv2CandidateHostName OBJECT-TYPE
    SYNTAX        OCTET STRING (SIZE (1..32))
    MAX-ACCESS    read-only
    STATUS        current
    DESCRIPTION
            ""
    ::= { clusterv2CandidateEntry 3 }

--xxx.100.22.4.5.1.4
clusterv2CandidateDeviceType OBJECT-TYPE
    SYNTAX        OCTET STRING (SIZE (1..32))
    MAX-ACCESS    read-only
    STATUS        current
    DESCRIPTION
            ""
    ::= { clusterv2CandidateEntry 4 }
    
    
--xxx.100.22.4.6
clusterv2RebootMem OBJECT-TYPE
    SYNTAX        OCTET STRING (SIZE (1..30))
   	MAX-ACCESS    read-write
   	STATUS    current
   	DESCRIPTION
       "Operation is to reboot the specified member.you can select more member one time,
       the value connected with '-' or ';',the string len is 1-30 .set only on commander."
   	::= { clusterv2Commander 6}
   	
--********************************************************************************************************
--******************************************************************************************************** 
--xxx.100.23 Dns group

--xxx.100.23.1
dnsEnable OBJECT-TYPE
    SYNTAX  INTEGER{
                disable(0),
                enable(1)
            }
            MAX-ACCESS  read-write
            STATUS  current
            DESCRIPTION
                "Enable or disable dns dynamic domain resolving."
            ::= {dns 1 }           
    
--xxx.100.23.2

-- The DNS Server List Table

dnsServerTable OBJECT-TYPE
    SYNTAX     SEQUENCE OF DnsServerEntry
    MAX-ACCESS not-accessible
    STATUS     current
    DESCRIPTION
           "The dns server list table which consists of a sequence of 'dnsServerEntry' items which describe
           the configured dns server IP information."
    ::= { dns 2 }
    
--xxx.100.23.2.1
dnsServerEntry OBJECT-TYPE
    SYNTAX     DnsServerEntry
    MAX-ACCESS not-accessible
    STATUS     current
    DESCRIPTION
            "An entry in the dnsServerTable containing the dns server IP."
    INDEX      { dnsServerInetAddrType,dnsServerIpAddr }
    ::= {dnsServerTable 1 }

DnsServerEntry
        ::= SEQUENCE
            {
                dnsServerInetAddrType       InetAddressType,
                dnsServerIpAddr		          InetAddress,
                dnsServerPriority	          INTEGER,
                dnsServerStatus	            INTEGER
            }
            
--xxx.100.23.2.1.1
dnsServerInetAddrType   OBJECT-TYPE
            SYNTAX      InetAddressType 
            MAX-ACCESS  not-accessible
            STATUS      current
            DESCRIPTION
                "The IP address type of dnsServerEntry. This value applies to dnsServerIpAddr."
            ::= { dnsServerEntry 1 }
      
--xxx.100.23.2.1.2
dnsServerIpAddr  OBJECT-TYPE
            SYNTAX      InetAddress 
            MAX-ACCESS  read-only
            STATUS      current
            DESCRIPTION
                "The dns server IP address with 'dnsServerInetAddrType' to indicate the IP address type(IPv4 or IPv6)."
            ::= { dnsServerEntry 2}    
            
--xxx.100.23.2.1.3           
dnsServerPriority OBJECT-TYPE
            SYNTAX  INTEGER(0..255)
            MAX-ACCESS  read-create
            STATUS  current
            DESCRIPTION
                "Current Priority of the dns server."
            ::= { dnsServerEntry  3 }            

--xxx.100.23.2.1.4           
dnsServerStatus OBJECT-TYPE
            SYNTAX  INTEGER
            	    {
            	    	createAndGo(0),
               		  active(1),
               		  destroy(2)
            	    }
            MAX-ACCESS  read-create
            STATUS  current
            DESCRIPTION
                "Current state of the dns server."
            ::= { dnsServerEntry  4 }                                                      
            
--xxx.100.23.3

-- The DNS Domain Suffix Table

dnsDomainSuffixTable OBJECT-TYPE
    SYNTAX     SEQUENCE OF DnsDomainSuffixEntry
    MAX-ACCESS not-accessible
    STATUS     current
    DESCRIPTION
           "The dns domain suffix table which consists of a sequence of 'dnsDomainSuffixEntry' items which describe
           the configured dns domain suffix information."
    ::= { dns 3 }
    
--xxx.100.23.3.1
dnsDomainSuffixEntry OBJECT-TYPE
    SYNTAX     DnsDomainSuffixEntry
    MAX-ACCESS not-accessible
    STATUS     current
    DESCRIPTION
            "An entry in the dnsDomainSuffixTable containing the dns domain suffix."
    INDEX      { dnsDomainSuffix }
    ::= { dnsDomainSuffixTable 1 }

DnsDomainSuffixEntry
        ::= SEQUENCE
            {
                dnsDomainSuffix               	DisplayString,
                dnsDomainSuffixStatus	          INTEGER
            }
            
--xxx.100.23.3.1.1
dnsDomainSuffix  OBJECT-TYPE
            SYNTAX      DisplayString 
            MAX-ACCESS  read-only
            STATUS      current
            DESCRIPTION
                "The dns domain suffix(e.g. commpany.com)."
            ::= { dnsDomainSuffixEntry 1 }

--xxx.100.23.3.1.2          
dnsDomainSuffixStatus OBJECT-TYPE
            SYNTAX  INTEGER
            	    {
            	    	createAndGo(0),
               		  active(1),
               		  destroy(2)
            	    }
            MAX-ACCESS  read-create
            STATUS  current
            DESCRIPTION
                "Current state of the dns domain suffix."
            ::= { dnsDomainSuffixEntry  2 }            
      
--xxx.100.23.4

-- The DNS Dynamic Host Table

dnsDynHostTable OBJECT-TYPE
    SYNTAX     SEQUENCE OF DnsDynHostEntry
    MAX-ACCESS not-accessible
    STATUS     current
    DESCRIPTION
           "The dns dynamic host table which consists of a sequence of 'dnsDynHostEntry' items which describe
           the resolved dns dynamic host information."
    ::= { dns 4 }
    
--xxx.100.23.4.1
dnsDynHostEntry OBJECT-TYPE
    SYNTAX     DnsDynHostEntry
    MAX-ACCESS not-accessible
    STATUS     current
    DESCRIPTION
            "An entry in the dnsDynHostTable containing the dns dynamic host information."
    INDEX      { dnsDynHostIndex }
    ::= { dnsDynHostTable 1 }
   
DnsDynHostEntry
        ::= SEQUENCE
            {   
                dnsDynHostIndex                  INTEGER,
                dnsDynHostName	                 DisplayString,
                dnsDynHostIpAddr					       InetAddress,   
                dnsDynHostTtl                    INTEGER 	
            }
            
--xxx.100.23.4.1.1
dnsDynHostIndex  OBJECT-TYPE
    SYNTAX     INTEGER
    MAX-ACCESS not-accessible
    STATUS     current
    DESCRIPTION
        "Index of position in the cache "
    ::= { dnsDynHostEntry 1 }
      

--xxx.100.23.4.1.2
dnsDynHostName  OBJECT-TYPE
            SYNTAX      DisplayString 
            MAX-ACCESS  read-only
            STATUS      current
            DESCRIPTION
                "The dns dynamic host name(e.g. www.sina.com.cn)."
            ::= { dnsDynHostEntry 2 }

--xxx.100.23.4.1.3
dnsDynHostIpAddr  OBJECT-TYPE
            SYNTAX      InetAddress 
            MAX-ACCESS  read-only
            STATUS      current
            DESCRIPTION
                "The dns dynamic host's IP address with 'dnsDynHostInetAddrType' to indicate the IP address type(IPv4 or IPv6)."
            ::= { dnsDynHostEntry 3} 
            
--xxx.100.23.4.1.4
dnsDynHostTtl  OBJECT-TYPE
            SYNTAX      INTEGER 
            MAX-ACCESS  read-only
            STATUS      current
            DESCRIPTION
                "The dns dynamic host's living time(seconds)."
            ::= { dnsDynHostEntry 4}    	

-- 
-- ***********************************************************
-- 
--                  L L D P    C O N F I G 
-- 
-- *********************************************************** 
--

lldpMessageTxInterval OBJECT-TYPE
    SYNTAX      Integer32(5..32768)
    UNITS       "seconds"
    MAX-ACCESS  read-write
    STATUS      current
    DESCRIPTION
            "The interval at which LLDP frames are transmitted on
            behalf of this LLDP agent.

            The default value for lldpMessageTxInterval object is
            30 seconds.

            The value of this object must be restored from non-volatile
            storage after a re-initialization of the management system."
    REFERENCE 
            "IEEE 802.1AB-2004 section 10.5.3.3"
    DEFVAL     { 30 }
    ::= { lldpConfiguration 1 }

lldpMessageTxHoldMultiplier OBJECT-TYPE
    SYNTAX      Integer32(2..10)
    MAX-ACCESS  read-write
    STATUS      current
    DESCRIPTION
            "The time-to-live value expressed as a multiple of the
            lldpMessageTxInterval object.  The actual time-to-live value
            used in LLDP frames, transmitted on behalf of this LLDP agent,
            can be expressed by the following formula: TTL = min(65535,
            (lldpMessageTxInterval * lldpMessageTxHoldMultiplier)) For
            example, if the value of lldpMessageTxInterval is '30', and
            the value of lldpMessageTxHoldMultiplier is '4', then the
            value '120' is encoded in the TTL field in the LLDP header.

            The default value for lldpMessageTxHoldMultiplier object is 4.

            The value of this object must be restored from non-volatile
            storage after a re-initialization of the management system."
    REFERENCE 
            "IEEE 802.1AB-2004 section 10.5.3.3"
    DEFVAL      { 4 }    
    ::= { lldpConfiguration 2 }


lldpTxDelay OBJECT-TYPE
    SYNTAX      Integer32(1..8192)
    UNITS       "seconds"
    MAX-ACCESS  read-write
    STATUS      current
    DESCRIPTION
            "The lldpTxDelay indicates the delay (in units
            of seconds) between successive LLDP frame transmissions 
            initiated by value/status changes in the LLDP local systems
            MIB.  The recommended value for the lldpTxDelay is set by the
            following  formula:

               1 <= lldpTxDelay <= (0.25 * lldpMessageTxInterval)

            The default value for lldpTxDelay object is 2 seconds.

            The value of this object must be restored from non-volatile
            storage after a re-initialization of the management system."
    REFERENCE 
            "IEEE 802.1AB-2004 section 10.5.3.3"
    DEFVAL      { 2 }    
    ::= { lldpConfiguration 4 }

lldpNotificationInterval OBJECT-TYPE
    SYNTAX      Integer32(5..3600)
    UNITS       "seconds"
    MAX-ACCESS  read-write
    STATUS      current
    DESCRIPTION
            "This object controls the transmission of LLDP notifications.

            the agent must not generate more than one lldpRemTablesChange
            notification-event in the indicated period, where a
            'notification-event' is the transmission of a single
            notification PDU type to a list of notification destinations.
            If additional changes in lldpRemoteSystemsData object
            groups occur within the indicated throttling period,
            then these trap- events must be suppressed by the
            agent. An NMS should periodically check the value of
            lldpStatsRemTableLastChangeTime to detect any missed
            lldpRemTablesChange notification-events, e.g. due to
            throttling or transmission loss.

            If notification transmission is enabled for particular ports,
            the suggested default throttling period is 5 seconds.

            The value of this object must be restored from non-volatile
            storage after a re-initialization of the management system."
    DEFVAL { 5 }
    ::= { lldpConfiguration 5 }

--
-- lldpPortConfigTable: LLDP configuration on a per port basis
--

lldpPortConfigTable   OBJECT-TYPE
    SYNTAX      SEQUENCE OF LldpPortConfigEntry
    MAX-ACCESS  not-accessible
    STATUS      current
    DESCRIPTION
            "The table that controls LLDP frame transmission on individual
            ports."
    ::= { lldpConfiguration 6 }

lldpPortConfigEntry   OBJECT-TYPE
    SYNTAX      LldpPortConfigEntry
    MAX-ACCESS  not-accessible
    STATUS      current
    DESCRIPTION
            "LLDP configuration information for a particular port.
            This configuration parameter controls the transmission and
            the reception of LLDP frames on those ports whose rows are
            created in this table."
     INDEX  { lldpPortConfigPortNum }
    ::= { lldpPortConfigTable 1 }

LldpPortConfigEntry ::= SEQUENCE {
      lldpPortConfigPortNum            LldpPortNumber,
      lldpPortConfigAdminStatus        INTEGER,
      lldpPortConfigNotificationEnable INTEGER,
      lldpPortConfigTLVsTxEnable       INTEGER }

lldpPortConfigPortNum   OBJECT-TYPE
    SYNTAX      LldpPortNumber 
    MAX-ACCESS  not-accessible
    STATUS      current
    DESCRIPTION
            "The index value used to identify the port component
            (contained in the local chassis with the LLDP agent)
            associated with this entry.

            The value of this object is used as a port index to the
            lldpPortConfigTable."
    ::= { lldpPortConfigEntry 1 }

lldpPortConfigAdminStatus  OBJECT-TYPE 
    SYNTAX INTEGER { 
       txOnly(1), 
       rxOnly(2),
       txAndRx(3),
       disabled(0)
    }
    MAX-ACCESS read-write 
    STATUS     current 
    DESCRIPTION 
            "The administratively desired status of the local LLDP agent.

            If the associated lldpPortConfigAdminStatus object has a
            value of 'txOnly(1)', then LLDP agent will transmit LLDP
            frames on this port and it will not store any information
            about the remote systems connected.
         
            If the associated lldpPortConfigAdminStatus object has a
            value of 'rxOnly(2)', then the LLDP agent will receive,
            but it will not transmit LLDP frames on this port.

            If the associated lldpPortConfigAdminStatus object has a
            value of 'txAndRx(3)', then the LLDP agent will transmit
            and receive LLDP frames on this port.

            If the associated lldpPortConfigAdminStatus object has a
            value of 'disabled(0)', then LLDP agent will not transmit or
            receive LLDP frames on this port.  If there is remote systems
            information which is received on this port and stored in
            other tables, before the port's lldpPortConfigAdminStatus
            becomes disabled, then the information will naturally age out."
    REFERENCE 
            "IEEE 802.1AB-2004 section 10.5.1"
    DEFVAL  { txAndRx }    
   ::= { lldpPortConfigEntry 2 } 

lldpPortConfigNotificationEnable OBJECT-TYPE 
    SYNTAX  INTEGER { 
       true(1), 
       false(0)
    }
    MAX-ACCESS read-write 
    STATUS     current 
    DESCRIPTION 
            "The lldpPortConfigNotificationEnable controls, on a per
            port basis,  whether or not notifications from the agent
            are enabled. The value true(1) means that notifications are
            enabled; the value false(0) means that they are not."
    DEFVAL  { false }    
   ::= { lldpPortConfigEntry 3 } 

lldpPortConfigTLVsTxEnable OBJECT-TYPE
    SYNTAX      INTEGER (1..15)
    MAX-ACCESS  read-write
    STATUS      current
    DESCRIPTION
--            "The lldpPortConfigTLVsTxEnable, defined as a bitmap,
--           includes the basic set of LLDP TLVs whose transmission is
--            allowed on the local LLDP agent by the network management.
--            Each bit in the bitmap corresponds to a TLV type associated
--            with a specific optional TLV.
--
--            It should be noted that the organizationally defined TLVs
--            are excluded from the lldpTLVsTxEnable bitmap.
--            
--            LLDP Organization Specific Information Extension MIBs should
--            have similar configuration object to control transmission
--            of their organizationally defined TLVs.
--
--            The bit 'portDesc(0)' indicates that LLDP agent should
--            transmit 'Port Description TLV'.
--
--            The bit 'sysName(1)' indicates that LLDP agent should transmit
--            'System Name TLV'.
--
--            The bit 'sysDesc(2)' indicates that LLDP agent should transmit
--            'System Description TLV'.
--
--            The bit 'sysCap(3)' indicates that LLDP agent should transmit
--            'System Capabilities TLV'.
--
--            There is no bit reserved for the management address TLV type
--           since transmission of management address TLVs are controlled
--            by another object, lldpConfigManAddrTable.
--
--            The default value for lldpPortConfigTLVsTxEnable object is
--            empty set, which means no enumerated values are set.
--
--            The value of this object must be restored from non-volatile
--            storage after a re-initialization of the management system."
            "
            The value '1' indicates that LLDP agent should transmit 'Port Description TLV'.

            The value '2' indicates that LLDP agent should transmit 'System Name TLV'.
            
            The value '3' indicates that LLDP agent should transmit 'Port Description and System Name TLV'.
            
            The value '4' indicates that LLDP agent should transmit 'System Description TLV'.   
                    
            The value '5' indicates that LLDP agent should transmit 'Port Description and System Description TLV'.  
            
            The value '6' indicates that LLDP agent should transmit 'System Name and System Description TLV'.   
            
            The value '7' indicates that LLDP agent should transmit 'Port Description,System Name and System Description TLV'. 
            
            The value '8' indicates that LLDP agent should transmit 'System Capabilities TLV'.   
            
            The value '9' indicates that LLDP agent should transmit 'Port Description and System Capabilities TLV'. 
            
            The value '10' indicates that LLDP agent should transmit 'System Name and System Capabilities TLV'. 
            
            The value '11' indicates that LLDP agent should transmit 'Port Description,System Name and System Capabilities TLV'.   
            
            The value '12' indicates that LLDP agent should transmit 'System Description and System Capabilities TLV'.   
            
            The value '13' indicates that LLDP agent should transmit 'Port Description,System Description and System Capabilities TLV'.  
            
            The value '14' indicates that LLDP agent should transmit 'System Name,System Description and System Capabilities TLV'.  
            
            The value '15' indicates that LLDP agent should transmit 'Port Description,System Name,System Description and System Capabilities TLV'."
--    DEFVAL  { { } }
    ::= { lldpPortConfigEntry 4 } 

--
--  *********************************************************** 
--
--                   L L D P    S T A T S 
--
--  *********************************************************** 
--
-- LLDP Stats Group

lldpStatsRemTablesLastChangeTime OBJECT-TYPE
    SYNTAX      TimeStamp
    MAX-ACCESS  read-only
    STATUS      current
    DESCRIPTION
            "The value of sysUpTime object (defined in IETF RFC 3418)
            at the time an entry is created, modified, or deleted in the
            in tables associated with the lldpRemoteSystemsData objects
            and all LLDP extension objects associated with remote systems.

            An NMS can use this object to reduce polling of the
            lldpRemoteSystemsData objects."
    ::= { lldpStatistics 1 }

lldpStatsRemTablesInserts OBJECT-TYPE
    SYNTAX      Counter32
    UNITS       "table entries"
    MAX-ACCESS  read-only
    STATUS      current
    DESCRIPTION
            "The number of times an entry has been inserted into tables
            associated with the lldpRemoteSystemsData objects and all
            LLDP extension objects associated with remote systems."
    ::= { lldpStatistics 2 }

lldpStatsRemTablesDeletes   OBJECT-TYPE
    SYNTAX      Counter32
    UNITS       "table entries"
    MAX-ACCESS  read-only
    STATUS      current

    DESCRIPTION
            "The number of times an entry has been deleted from tables
            associated with the lldpRemoteSystemsData objects and all
            LLDP extension objects associated with remote systems."
    ::= { lldpStatistics 3 }

lldpStatsRemTablesDrops  OBJECT-TYPE
    SYNTAX      Counter32
    UNITS       "table entries"
    MAX-ACCESS  read-only

    STATUS      current
    DESCRIPTION
            "The number of times a new entry could not be created in the
            tables associated with the lldpRemoteSystemsData objects
            and all LLDP extension objects associated with the remote
            systems because of insufficient resources."
    ::= { lldpStatistics 4 }

lldpStatsRemTablesAgeouts   OBJECT-TYPE
    SYNTAX      Counter32
    MAX-ACCESS  read-only
    STATUS      current
    DESCRIPTION
            "The number of times an entry has been deleted from tables
            associated with the lldpRemoteSystemsData objects and all
            LLDP extension objects associated with remote systems because
            the information timeliness interval for those entries have
            expired."
    ::= { lldpStatistics 5 }

lldpStatsPortTable  OBJECT-TYPE
    SYNTAX      SEQUENCE OF LldpStatsPortEntry
    MAX-ACCESS  not-accessible
    STATUS      current
    DESCRIPTION 
            "A table containing LLDP statistics for individual ports.
            Entries are not required to exist in this table while the
            lldpPortConfigEntry object is equal to 'disabled(0)'."
    ::= { lldpStatistics 6 } 

lldpStatsPortEntry   OBJECT-TYPE
     SYNTAX      LldpStatsPortEntry
     MAX-ACCESS  not-accessible
     STATUS      current
     DESCRIPTION
             "LLDP frame statistics for a particular port.  The port
             must be contained in the same chassis as the LLDP agent.
            
             All counter values in a particular entry shall be
             maintained on a continuing basis and shall not be deleted
             upon expiration of rxInfoTTL timing counters in the LLDP
             remote systems MIB of the receipt of a shutdown frame from
             a remote LLDP agent.

             All statistical counters associated with a particular
             port on the local LLDP agent become frozen whenever the
             adminStatus is disabled for the same port."
     INDEX  { lldpStatsPortNum }
     ::= { lldpStatsPortTable 1 } 

LldpStatsPortEntry ::= SEQUENCE {      
      lldpStatsPortNum                   LldpPortNumber,
      lldpStatsPortFramesDiscardedTotal  Counter32,
      lldpStatsPortFramesInErrors        Counter32,
      lldpStatsPortFramesInTotal         Counter32,
      lldpStatsPortFramesOutTotal        Counter32,
      lldpStatsPortTLVsDiscardedTotal    Counter32,
      lldpStatsPortTLVsUnrecognizedTotal Counter32,
      lldpStatsPortAgeouts               Counter32
}

lldpStatsPortNum   OBJECT-TYPE
    SYNTAX      LldpPortNumber 
    MAX-ACCESS  not-accessible
    STATUS      current
    DESCRIPTION
            "The index value used to identify the port component
            (contained in the local chassis with the LLDP agent)
            associated with this entry.

            The value of this object is used as a port index to the
            lldpStatsTable."
    ::= { lldpStatsPortEntry 1 } 

lldpStatsPortFramesDiscardedTotal OBJECT-TYPE 
    SYNTAX        Counter32
    MAX-ACCESS read-only
    STATUS     current 
    DESCRIPTION 
            "The number of LLDP frames received by this LLDP agent on
            the indicated port, and then discarded for any reason.
            This counter can provide an indication that LLDP header
            formating problems may exist with the local LLDP agent in
            the sending system or that LLDPDU validation problems may
            exist with the local LLDP agent in the receiving system."
   REFERENCE 
            "IEEE 802.1AB-2004 section 10.5.2"
   ::= { lldpStatsPortEntry 2 } 

lldpStatsPortFramesInErrors  OBJECT-TYPE
    SYNTAX        Counter32
    MAX-ACCESS    read-only
    STATUS        current
    DESCRIPTION
            "The number of invalid LLDP frames received by this LLDP
            agent on the indicated port, while this LLDP agent is enabled."
    REFERENCE 
            "IEEE 802.1AB-2004 section 10.5.2"
    ::= { lldpStatsPortEntry 3 }

lldpStatsPortFramesInTotal OBJECT-TYPE
    SYNTAX        Counter32
    MAX-ACCESS    read-only
    STATUS        current
    DESCRIPTION
            "The number of valid LLDP frames received by this LLDP agent
            on the indicated port, while this LLDP agent is enabled."
    REFERENCE 
            "IEEE 802.1AB-2004 section 10.5.2"
    ::= { lldpStatsPortEntry 4 }

lldpStatsPortFramesOutTotal  OBJECT-TYPE
    SYNTAX        Counter32
    MAX-ACCESS    read-only
    STATUS        current
    DESCRIPTION
            "The number of LLDP frames transmitted by this LLDP agent
            on the indicated port."
    REFERENCE 
            "IEEE 802.1AB-2004 section 10.5.2"
    ::= { lldpStatsPortEntry 5 }

lldpStatsPortTLVsDiscardedTotal OBJECT-TYPE
    SYNTAX        Counter32
    MAX-ACCESS    read-only
    STATUS        current
    DESCRIPTION
            "The number of LLDP TLVs discarded for any reason by this LLDP
            agent on the indicated port."
    REFERENCE 
            "IEEE 802.1AB-2004 section 10.5.2"
    ::= { lldpStatsPortEntry 6 }

lldpStatsPortTLVsUnrecognizedTotal  OBJECT-TYPE
    SYNTAX        Counter32
    MAX-ACCESS    read-only
    STATUS        current
    DESCRIPTION
            "The number of LLDP TLVs received on the given port that
            are not recognized by this LLDP agent on the indicated port.
            
            An unrecognized TLV is referred to as the TLV whose type value
            is in the range of reserved TLV types (000 1001 - 111 1110)
            in Table 9.1 of the IEEE Std. 802.1AB-2004.  An unrecognized
            TLV may be a basic management TLV from a later LLDP version."
    REFERENCE 
            "IEEE 802.1AB-2004 section 10.5.2"
    ::= { lldpStatsPortEntry 7 }

lldpStatsPortAgeouts   OBJECT-TYPE
    SYNTAX      Counter32
    MAX-ACCESS  read-only
    STATUS      current
    DESCRIPTION
            "The counter that represents the number of age-outs occurred
            on a given port.  An age-out is referred to as the number
            of times an entry has been deleted from tables associated
            with the lldpRemoteSystemsData objects and all LLDP extension
            objects associated with remote systems because the information
            timeliness interval for those entries have expired.

            This counter is similar to lldpStatsRemTablesNumAgeouts,
            except that the counter is on a per port basis.  This enables
            NMS to poll tables associated with the lldpRemoteSystemsData
            objects and all LLDP extension objects associated with remote
            systems on the indicated port only."
    REFERENCE 
            "IEEE 802.1AB-2004 section 10.5.2"
    ::= { lldpStatsPortEntry 9 }


--  ***********************************************************
--
--          L O C A L    S Y S T E M    D A T A
--
--  ***********************************************************

lldpLocChassisType  OBJECT-TYPE
    SYNTAX      LldpChassisIdSubtype
    MAX-ACCESS  read-only
    STATUS      current
    DESCRIPTION
            "The type of encoding used to identify the chassis
            associated with the local system."
    REFERENCE 
            "IEEE 802.1AB-2004 section 9.4.2.2"
    ::= { lldpLocalSystemData 1 }

lldpLocChassisId  OBJECT-TYPE
    SYNTAX      LldpChassisId
    MAX-ACCESS  read-only
    STATUS      current
    DESCRIPTION
            "The string value used to identify the chassis component
            associated with the local system."
    REFERENCE 
            "IEEE 802.1AB-2004 section 9.4.2.3"
    ::= { lldpLocalSystemData 2 }

lldpLocSysName  OBJECT-TYPE
    SYNTAX      SnmpAdminString (SIZE(0..255))
    MAX-ACCESS  read-only
    STATUS      current
    DESCRIPTION
            "The string value used to identify the system name of the
            local system.  If the local agent supports IETF RFC 3418,
            lldpLocSysName object should have the same value of sysName
            object."
    REFERENCE 
            "IEEE 802.1AB-2004 section 9.4.6.2"
    ::= { lldpLocalSystemData 3 }

lldpLocSysDesc  OBJECT-TYPE
    SYNTAX      SnmpAdminString (SIZE(0..255))
    MAX-ACCESS  read-only
    STATUS      current
    DESCRIPTION
            "The string value used to identify the system description
            of the local system.  If the local agent supports IETF RFC 3418,
            lldpLocSysDesc object should have the same value of sysDesc
            object."
    REFERENCE 
            "IEEE 802.1AB-2004 section 9.4.7.2"
    ::= { lldpLocalSystemData 4 }

lldpLocSysCapSupported OBJECT-TYPE
    SYNTAX      LldpSystemCapabilitiesMap
    MAX-ACCESS  read-only
    STATUS      current
    DESCRIPTION
            "The bitmap value used to identify which system capabilities
            are supported on the local system."
    REFERENCE 
            "IEEE 802.1AB-2004 section 9.4.8.1"
    ::= { lldpLocalSystemData 5 }

lldpLocSysCapEnabled  OBJECT-TYPE
    SYNTAX      LldpSystemCapabilitiesMap
    MAX-ACCESS  read-only
    STATUS      current
    DESCRIPTION
            "The bitmap value used to identify which system capabilities
            are enabled on the local system."
    REFERENCE 
            "IEEE 802.1AB-2004 section 9.4.8.2"
    ::= { lldpLocalSystemData 6 }


--
-- lldpLocPortTable : Port specific Local system data
--

lldpLocPortTable OBJECT-TYPE
    SYNTAX      SEQUENCE OF LldpLocPortEntry
    MAX-ACCESS  not-accessible
    STATUS      current
    DESCRIPTION
            "This table contains one or more rows per port information
            associated with the local system known to this agent."
    ::= { lldpLocalSystemData 7 }

lldpLocPortEntry OBJECT-TYPE
    SYNTAX      LldpLocPortEntry 
    MAX-ACCESS  not-accessible
    STATUS      current
    DESCRIPTION
            "Information about a particular port component.

            Entries may be created and deleted in this table by the
            agent."
    INDEX   { lldpLocPortNum }
    ::= { lldpLocPortTable 1 }

LldpLocPortEntry ::= SEQUENCE {
      lldpLocPortNum                LldpPortNumber,
      lldpLocPortSubtype            LldpPortIdSubtype,
      lldpLocPortId                 LldpPortId,
      lldpLocPortDesc               SnmpAdminString
}

lldpLocPortNum  OBJECT-TYPE
    SYNTAX      LldpPortNumber
    MAX-ACCESS  not-accessible
    STATUS      current
    DESCRIPTION
            "The index value used to identify the port component
            (contained in the local chassis with the LLDP agent)
            associated with this entry.
            
            The value of this object is used as a port index to the
            lldpLocPortTable."
    ::= { lldpLocPortEntry 1 }

lldpLocPortSubtype  OBJECT-TYPE
    SYNTAX      LldpPortIdSubtype
    MAX-ACCESS  read-only
    STATUS      current
    DESCRIPTION
            "The type of port identifier encoding used in the associated
            'lldpLocPortId' object."
    REFERENCE 
            "IEEE 802.1AB-2004 section 9.4.3.2"
    ::= { lldpLocPortEntry 2 }

lldpLocPortId  OBJECT-TYPE
    SYNTAX      LldpPortId
    MAX-ACCESS  read-only
    STATUS      current
    DESCRIPTION
            "The string value used to identify the port component
            associated with a given port in the local system."
    REFERENCE 
            "IEEE 802.1AB-2004 section 9.4.3.3"
    ::= { lldpLocPortEntry 3 }

lldpLocPortDesc  OBJECT-TYPE
    SYNTAX      SnmpAdminString (SIZE(0..255))
    MAX-ACCESS  read-only
    STATUS      current
    DESCRIPTION
            "The string value used to identify the 802 LAN station's port
            description associated with the local system.  If the local
            agent supports IETF RFC 2863, lldpLocPortDesc object should
            have the same value of ifDescr object."
    REFERENCE 
            "IEEE 802.1AB-2004 section 9.4.5.2"
    ::= { lldpLocPortEntry 4 }

--  ***********************************************************
--
--          R E M O T E    S Y S T E M S    D A T A
--
--  ***********************************************************

lldpRemTable OBJECT-TYPE
    SYNTAX      SEQUENCE OF LldpRemEntry
    MAX-ACCESS  not-accessible
    STATUS      current
    DESCRIPTION
            "This table contains one or more rows per physical network
            connection known to this agent.  The agent may wish to ensure
            that only one lldpRemEntry is present for each local port,
            or it may choose to maintain multiple lldpRemEntries for
            the same local port."
    ::= { lldpRemoteSystemsData 1 }

lldpRemEntry OBJECT-TYPE
    SYNTAX      LldpRemEntry
    MAX-ACCESS  not-accessible
    STATUS      current
    DESCRIPTION
            "Information about a particular physical network connection.
            Entries may be created and deleted in this table by the agent,
            if a physical topology discovery process is active."
    INDEX   {lldpRemLocalPortNum,lldpRemIndex }
    ::= { lldpRemTable 1 }

LldpRemEntry ::= SEQUENCE {
      lldpRemLocalPortNum       LldpPortNumber,
      lldpRemIndex              Integer32,
      lldpRemChassisIdSubtype   LldpChassisIdSubtype,
      lldpRemChassisId          LldpChassisId,
      lldpRemPortIdSubtype      LldpPortIdSubtype,
      lldpRemPortId             LldpPortId,
      lldpRemPortDesc           SnmpAdminString,
      lldpRemSysName            SnmpAdminString,
      lldpRemSysDesc            SnmpAdminString,
      lldpRemSysCapSupported    LldpSystemCapabilitiesMap,
      lldpRemSysCapEnabled      LldpSystemCapabilitiesMap,
      lldpRemTimeMark		TimeFilter
}

lldpRemLocalPortNum  OBJECT-TYPE
    SYNTAX      LldpPortNumber
    MAX-ACCESS  not-accessible
    STATUS      current
    DESCRIPTION
            "The index value used to identify the port component
            (contained in the local chassis with the LLDP agent)
            associated with this entry.  The lldpRemLocalPortNum
            identifies the port on which the remote system information
            is received.

            The value of this object is used as a port index to the
            lldpRemTable."
    ::= { lldpRemEntry 1 }

lldpRemIndex  OBJECT-TYPE
    SYNTAX      Integer32(1..2147483647)
    MAX-ACCESS  not-accessible
    STATUS      current
    DESCRIPTION
            "This object represents an arbitrary local integer value used
            by this agent to identify a particular connection instance,
            unique only for the indicated remote system.

            An agent is encouraged to assign monotonically increasing
            index values to new entries, starting with one, after each
            reboot.  It is considered unlikely that the lldpRemIndex
            will wrap between reboots."
    ::= { lldpRemEntry 2 }

lldpRemChassisIdSubtype  OBJECT-TYPE
    SYNTAX      LldpChassisIdSubtype
    MAX-ACCESS  read-only
    STATUS      current
    DESCRIPTION
            "The type of encoding used to identify the chassis associated
            with the remote system."
    REFERENCE 
            "IEEE 802.1AB-2004 section 9.4.2.2"
    ::= { lldpRemEntry 3 }

lldpRemChassisId  OBJECT-TYPE
    SYNTAX      LldpChassisId
    MAX-ACCESS  read-only
    STATUS      current
    DESCRIPTION
            "The string value used to identify the chassis component
            associated with the remote system."
    REFERENCE 
            "IEEE 802.1AB-2004 section 9.4.2.3"
    ::= { lldpRemEntry 4 }

lldpRemPortIdSubtype  OBJECT-TYPE
    SYNTAX      LldpPortIdSubtype
    MAX-ACCESS  read-only
    STATUS      current
    DESCRIPTION
            "The type of port identifier encoding used in the associated
            'lldpRemPortId' object."
    REFERENCE 
            "IEEE 802.1AB-2004 section 9.4.3.2"
    ::= { lldpRemEntry 5 }

lldpRemPortId  OBJECT-TYPE
    SYNTAX      LldpPortId
    MAX-ACCESS  read-only
    STATUS      current
    DESCRIPTION
            "The string value used to identify the port component
            associated with the remote system."
    REFERENCE 
            "IEEE 802.1AB-2004 section 9.4.3.3"
    ::= { lldpRemEntry 6 }

lldpRemPortDesc  OBJECT-TYPE
    SYNTAX      SnmpAdminString (SIZE(0..255))
    MAX-ACCESS  read-only
    STATUS      current
    DESCRIPTION
            "The string value used to identify the description of
            the given port associated with the remote system."
    REFERENCE 
            "IEEE 802.1AB-2004 section 9.4.5.2"
    ::= { lldpRemEntry 7 }

lldpRemSysName  OBJECT-TYPE
    SYNTAX      SnmpAdminString (SIZE(0..255))
    MAX-ACCESS  read-only
    STATUS      current
    DESCRIPTION
            "The string value used to identify the system name of the
            remote system."
    REFERENCE 
            "IEEE 802.1AB-2004 section 9.4.6.2"
    ::= { lldpRemEntry 8 }

lldpRemSysDesc  OBJECT-TYPE
    SYNTAX      SnmpAdminString (SIZE(0..255))
    MAX-ACCESS  read-only
    STATUS      current
    DESCRIPTION
            "The string value used to identify the system description
            of the remote system."
    REFERENCE 
            "IEEE 802.1AB-2004 section 9.4.7.2"
    ::= { lldpRemEntry 9 }

lldpRemSysCapSupported OBJECT-TYPE
    SYNTAX      LldpSystemCapabilitiesMap
    MAX-ACCESS  read-only
    STATUS      current
    DESCRIPTION
            "The bitmap value used to identify which system capabilities
            are supported on the remote system."
    REFERENCE 
            "IEEE 802.1AB-2004 section 9.4.8.1"
    ::= { lldpRemEntry 10 }

lldpRemSysCapEnabled  OBJECT-TYPE
    SYNTAX      LldpSystemCapabilitiesMap
    MAX-ACCESS  read-only
    STATUS      current
    DESCRIPTION
            "The bitmap value used to identify which system capabilities
            are enabled on the remote system."
    REFERENCE 
            "IEEE 802.1AB-2004 section 9.4.8.2"
    ::= { lldpRemEntry 11 }
    
lldpRemTimeMark  OBJECT-TYPE
    SYNTAX      TimeFilter
    MAX-ACCESS  read-only
    STATUS      current
    DESCRIPTION
            "A TimeFilter for this entry.  See the TimeFilter textual
            convention in IETF RFC 2021 and 
            http://www.ietf.org/IESG/Implementations/RFC2021-Implementation.txt
            to see how TimeFilter works."
    REFERENCE 
            "IETF RFC 2021 section 6"
    ::= { lldpRemEntry 12 }

--
-- lldpRemUnknownTLVTable : Unrecognized TLV information 
--
lldpRemUnknownTLVTable  OBJECT-TYPE
    SYNTAX      SEQUENCE OF LldpRemUnknownTLVEntry
    MAX-ACCESS  not-accessible
    STATUS      current
    DESCRIPTION
            "This table contains information about an incoming TLV which
            is not recognized by the receiving LLDP agent.  The TLV may
            be from a later version of the basic management set.

            This table should only contain TLVs that are found in a
            single LLDP frame.  Entries of this this table, associated
            with an MAC service access point (MSAP, the access point for
            MAC services provided to the LCC sublayer, defined in IEEE
            100, which is also identified with a particular
            lldpRemLocalPortNum, lldpRemIndex pair) are overwritten with
            most recently received unrecognized TLV from the same MSAP,
            or they will naturally age out when the rxInfoTTL timer
            (associated with the MSAP) expires."
    REFERENCE 
            "IEEE 802.1AB-2004 section 10.3.2"
    ::= { lldpRemoteSystemsData 3 }

lldpRemUnknownTLVEntry OBJECT-TYPE
    SYNTAX      LldpRemUnknownTLVEntry
    MAX-ACCESS  not-accessible
    STATUS      current
    DESCRIPTION
            "Information about an unrecognized TLV received from a
            physical network connection.  Entries may be created and
            deleted in this table by the agent, if a physical topology
            discovery process is active."
    INDEX   {
           lldpRemUnknownTLVType 
    }
    ::= { lldpRemUnknownTLVTable 1 }

LldpRemUnknownTLVEntry ::= SEQUENCE {
      lldpRemUnknownTLVType     Integer32,
      lldpRemUnknownTLVInfo     OCTET STRING
}

lldpRemUnknownTLVType OBJECT-TYPE
    SYNTAX      Integer32(9..126)
    MAX-ACCESS  not-accessible
    STATUS      current
    DESCRIPTION
            "This object represents the value extracted from the type
            field of the TLV."
    REFERENCE 
            "IEEE 802.1AB-2004 section 10.3.5"
    ::= { lldpRemUnknownTLVEntry 1 }

lldpRemUnknownTLVInfo OBJECT-TYPE
    SYNTAX      OCTET STRING (SIZE(0..511))
    MAX-ACCESS  read-only
    STATUS      current
    DESCRIPTION
            "This object represents the value extracted from the value
            field of the TLV."
    REFERENCE 
            "IEEE 802.1AB-2004 section 10.3.5"
    ::= { lldpRemUnknownTLVEntry 2 }

--
-- ***********************************************************
-- 
--        L L D P   M I B   N O T I F I C A T I O N S
-- 
-- *********************************************************** 
--

lldpNotificationPrefix OBJECT IDENTIFIER ::= { lldpNotifications 0 }

lldpRemTablesChange NOTIFICATION-TYPE
    OBJECTS {
        lldpStatsRemTablesInserts,
        lldpStatsRemTablesDeletes,
        lldpStatsRemTablesDrops,
        lldpStatsRemTablesAgeouts
    }
    STATUS        current
    DESCRIPTION
            "A lldpRemTablesChange notification is sent when the value
            of lldpStatsRemTableLastChangeTime changes.  It can be
            utilized by an NMS to trigger LLDP remote systems table
            maintenance polls.

            Note that transmission of lldpRemTablesChange
            notifications are throttled by the agent, as specified by the
            'lldpNotificationInterval' object."
   ::= { lldpNotificationPrefix 1 }


--
-- ***********************************************************
-- 
--           L L D P   M I B   C O N F O R M A N C E 
-- 
-- *********************************************************** 
--

lldpCompliances OBJECT IDENTIFIER ::= { lldpConformance 1 }
lldpGroups      OBJECT IDENTIFIER ::= { lldpConformance 2 }

-- compliance statements

lldpCompliance MODULE-COMPLIANCE
    STATUS  current
    DESCRIPTION
            "The compliance statement for SNMP entities which implement
            the LLDP MIB."
    MODULE  -- this module
        MANDATORY-GROUPS { 
                           lldpConfigGroup, 
                           lldpStatsGroup, 
                           lldpLocSysGroup,
                           lldpRemSysGroup,
                           lldpNotificationsGroup
        }
        GROUP lldpOptLocSysGroup 
            DESCRIPTION
                "This object represent the information associated with
                the optional TLVs, therefore the agent may not implement
                them."
    ::= { lldpCompliances 1 }

-- MIB groupings

lldpConfigGroup    OBJECT-GROUP
    OBJECTS {
        lldpMessageTxInterval,
        lldpMessageTxHoldMultiplier,
--        lldpReinitDelay,
        lldpTxDelay,
        lldpNotificationInterval,
        lldpPortConfigAdminStatus,
        lldpPortConfigNotificationEnable,
        lldpPortConfigTLVsTxEnable
--        lldpConfigManAddrPortsTxEnable
    }
    STATUS  current
    DESCRIPTION
            "The collection of objects which are used to configure the
            LLDP implementation behavior.

            This group is mandatory for agents which implement the LLDP."
    ::= { lldpGroups 1 }

lldpStatsGroup    OBJECT-GROUP
    OBJECTS {
        lldpStatsRemTablesLastChangeTime,
        lldpStatsRemTablesInserts,
        lldpStatsRemTablesDeletes,
        lldpStatsRemTablesDrops,
        lldpStatsRemTablesAgeouts,
        lldpStatsPortFramesDiscardedTotal,
        lldpStatsPortFramesInErrors,
        lldpStatsPortFramesInTotal,
        lldpStatsPortFramesOutTotal,
        lldpStatsPortTLVsDiscardedTotal,
        lldpStatsPortTLVsUnrecognizedTotal,
        lldpStatsPortAgeouts
    }
    STATUS  current
    DESCRIPTION
            "The collection of objects which are used to represent LLDP
            statistics.

            This group is mandatory for agents which implement the LLDP."
    ::= { lldpGroups 2 }

lldpLocSysGroup  OBJECT-GROUP
    OBJECTS {
        lldpLocChassisType,
        lldpLocChassisId,
        lldpLocPortSubtype,
        lldpLocPortId
    }
    STATUS  current
    DESCRIPTION
            "The collection of objects which are used to represent LLDP
            Local System Information.  The objects represent the 
            information associated with the mandatory TLVs.
            
            This group is mandatory for agents which implement the LLDP."
    ::= { lldpGroups 3 }

lldpOptLocSysGroup  OBJECT-GROUP
    OBJECTS {
        lldpLocPortDesc,
        lldpLocSysDesc,
        lldpLocSysName,
        lldpLocSysCapSupported,
        lldpLocSysCapEnabled
--        lldpLocManAddrLen,
--        lldpLocManAddrIfSubtype,
--        lldpLocManAddrIfId,
--        lldpLocManAddrOID
    }
    STATUS  current
    DESCRIPTION
            "The collection of objects which are used to represent optional
            LLDP Local System Information.  The objects represent the 
            information associated with the optional TLVs.
            
            This group is optional for agents which implement the LLDP."
    ::= { lldpGroups 4 }

lldpRemSysGroup  OBJECT-GROUP
    OBJECTS {
        lldpRemChassisIdSubtype,
        lldpRemChassisId,
        lldpRemPortIdSubtype,
        lldpRemPortId,
        lldpRemPortDesc,
        lldpRemSysName,
        lldpRemSysDesc,
        lldpRemSysCapSupported,
        lldpRemSysCapEnabled,
--        lldpRemManAddrIfSubtype,
--        lldpRemManAddrIfId,
--        lldpRemManAddrOID,
        lldpRemUnknownTLVInfo
--        lldpRemOrgDefInfo 
    }
    STATUS  current
    DESCRIPTION
            "The collection of objects which are used to represent
            LLDP Remote Systems Information.  The objects represent the
            information associated with the basic TLV set.  Please note
            that even the agent doesn't implement some of the optional
            TLVs, it shall recognize all the optional TLV information
            that the remote system may advertise.
            
            This group is mandatory for agents which implement the LLDP."
    ::= { lldpGroups 5 }

lldpNotificationsGroup  NOTIFICATION-GROUP
    NOTIFICATIONS {
        lldpRemTablesChange 
    }
    STATUS  current
    DESCRIPTION
            "The collection of notifications used to indicate LLDP MIB
            data consistency and general status information.

            This group is mandatory for agents which implement the LLDP."
    ::= { lldpGroups 6 }

--********************************************************************************************************
--********************************************************************************************************  
--
-- Textual Conventions
--

NtpStratum ::= TEXTUAL-CONVENTION
    DISPLAY-HINT "d"
    STATUS      current
    DESCRIPTION
        "The NTP stratum, with 16 representing no stratum."
    SYNTAX      Unsigned32 (1..16)

NtpDateTime ::= TEXTUAL-CONVENTION
    DISPLAY-HINT "4d:4d:4d.4d"
    STATUS      current
    DESCRIPTION
        "NTP date/time on the device, in 128-bit
         NTP date format. Ref: draft-ietf-ntp-ntpv4-proto-06,
         section 6:
          It includes a 64-bit signed seconds field
          spanning 584 billion years and a 64-bit fraction
          field resolving .05 attosecond (i.e. 0.5e-18).
          For convenience in mapping between formats, the
          seconds field is divided into a 32-bit era field
          and a 32-bit timestamp field.

         If time is not syncronized this field shall be a
         zero-length string.

         This TC is not to be used for objects that are used
         to set the time of the node querying this object.
         NTP should be used for this--or at least SNTP."
    SYNTAX      OCTET STRING (SIZE (0 | 16))

--
-- Section 1: General NTP Entity information objects
--            (relatively static information)
--

ntpEntSoftwareName OBJECT-TYPE
    SYNTAX      DisplayString
    MAX-ACCESS  read-only
    STATUS      current
    DESCRIPTION
        "The product name of the installed NTP version."
    ::= { ntpEntInfo  1 }

ntpEntSoftwareVersion OBJECT-TYPE
    SYNTAX      DisplayString
    MAX-ACCESS  read-only
    STATUS      current
    DESCRIPTION
        "The software version of the installed NTP implementation."
    ::= { ntpEntInfo  2 }

ntpEntSoftwareVendor OBJECT-TYPE
    SYNTAX      DisplayString
    MAX-ACCESS  read-only
    STATUS      current
    DESCRIPTION
        "The vendor/author of the installed NTP version."
    ::= { ntpEntInfo  4 }

ntpEntSystemType OBJECT-TYPE
    SYNTAX      DisplayString
    MAX-ACCESS  read-only
    STATUS      current
    DESCRIPTION
        "General hardware/os platform information."
    ::= { ntpEntInfo  5 }

ntpEntTimeResolution OBJECT-TYPE
    SYNTAX      DisplayString
    MAX-ACCESS  read-only
    STATUS      current
    DESCRIPTION
        "A string describing the time resolution of the running NTP
         implementation."
    ::= { ntpEntInfo  6 }

ntpEntTimePrecision OBJECT-TYPE
    SYNTAX      Integer32
    MAX-ACCESS  read-only
    STATUS      current
    DESCRIPTION
        "The entity's precision in integer format."
    ::= { ntpEntInfo  9 }

--
-- Section 2: Current NTP status (dynamic information)
--

ntpEntStatusCurrentMode OBJECT-TYPE
    SYNTAX      DisplayString
    MAX-ACCESS  read-only
    STATUS      current
    DESCRIPTION
        "The actual mode of NTP as a string"
    ::= { ntpEntStatus 1 }

ntpEntStatusCurrentModeVal OBJECT-TYPE
    SYNTAX      INTEGER {
                            notRunning(1),
                            notSynchronized(2),
                            noneConfigured(3),
                            syncToLocal(4),
                            syncToRefclock(5),
                            syncToRemoteServer(6),
                            unknown(99)
                        }
    MAX-ACCESS  read-only
    STATUS      current
    DESCRIPTION
        "The current mode of the NTP as integer value."
    DEFVAL { 99 }
    ::= { ntpEntStatus 2 }

ntpEntStatusStratum OBJECT-TYPE
    SYNTAX      NtpStratum
    MAX-ACCESS  read-only
    STATUS      current
    DESCRIPTION
        "The NTP entity's own stratum value."
    DEFVAL { 16 }
    ::= { ntpEntStatus 3 }

ntpEntStatusActiveRefSourceId OBJECT-TYPE
    SYNTAX      Unsigned32 (0..4294967295)
    MAX-ACCESS  read-only
    STATUS      current
    DESCRIPTION
        "The association ID of the current syspeer."
    DEFVAL { 0 }
    ::= { ntpEntStatus 4 }

ntpEntStatusActiveRefSourceName OBJECT-TYPE
    SYNTAX      DisplayString
    MAX-ACCESS  read-only
    STATUS      current
    DESCRIPTION
        "The hostname/descriptive name of the current reference source
         selected as syspeer."
    ::= { ntpEntStatus 5 }

ntpEntStatusNumberOfRefSources OBJECT-TYPE
    SYNTAX      Unsigned32 (0..99)
    MAX-ACCESS  read-only
    STATUS      current
    DESCRIPTION
        "The number of reference sources configured for NTP."
    DEFVAL { 0 }
    ::= { ntpEntStatus 7 }

ntpEntStatusDateTime OBJECT-TYPE
    SYNTAX      NtpDateTime
    MAX-ACCESS  read-only
    STATUS      current
    DESCRIPTION
        "The current NTP date/time on the device, in 128-bit
         NTP date format. Ref: draft-ietf-ntp-ntpv4-proto-06,
         section 6:
          It includes a 64-bit signed seconds field
          spanning 584 billion years and a 64-bit fraction
          field resolving .05 attosecond (i.e. 0.5e-18).
          For convenience in mapping between formats, the
          seconds field is divided into a 32-bit era field
          and a 32-bit timestamp field.

         If time is not syncronized this field shall be a
         zero-length string.

         This object can be used to timestamp events on this
         node and allow a management station to coorelate
         different time objects. For example, a management
         station could query this object and sysUpTime in
         the same operation to be able to relate sysUpTime
         to NTP time.

         This object is not to be used to set the time of
         the node querying this object. NTP should be used
         for this--or at least SNTP."
    ::= { ntpEntStatus 10 }

ntpEntStatusInPkts OBJECT-TYPE
    SYNTAX      Counter32
    MAX-ACCESS  read-only
    STATUS      current
    DESCRIPTION
        "The total number of NTP messages delivered to the
         NTP entity from the transport service."
    ::= { ntpEntStatus 13 }

ntpEntStatusOutPkts OBJECT-TYPE
    SYNTAX      Counter32
    MAX-ACCESS  read-only
    STATUS      current
    DESCRIPTION
        "The total number of NTP messages delivered to the
         transport service by this NTP entity."
    ::= { ntpEntStatus 14 }

ntpEntStatusBadVersion OBJECT-TYPE
    SYNTAX      Counter32
    MAX-ACCESS  read-only
    STATUS      current
    DESCRIPTION
        "The total number of NTP messages which were delivered
         to this NTP entity and were for an unsupported NTP
         version."
    ::= { ntpEntStatus 15 }

ntpEntStatusProtocolError OBJECT-TYPE
    SYNTAX      Counter32
    MAX-ACCESS  read-only
    STATUS      current
    DESCRIPTION
        "The total number of NTP messages which were delivered
         to this NTP entity and this entity was not able to
         process due to an NTP protocol error."
    ::= { ntpEntStatus 16 }



--
-- Conformance/Compliance statements
--

ntpEntConformance OBJECT IDENTIFIER ::= { ntpSnmpMIB 6 }

ntpEntCompliances OBJECT IDENTIFIER ::= { ntpEntConformance 1 }
ntpEntGroups      OBJECT IDENTIFIER ::= { ntpEntConformance 2 }

ntpEntNTPCompliance MODULE-COMPLIANCE
    STATUS      current
    DESCRIPTION
        "The compliance statement for SNMP entities which use NTP and
         implement the NTP MIB"
    MODULE  -- this module
        MANDATORY-GROUPS {
                           ntpEntObjectsGroup1,
                           ntpEntObjectsGroup2,
                           ntpEntNotifPrefixGroup
        }
        ::= { ntpEntCompliances 1 }

ntpEntSNTPCompliance MODULE-COMPLIANCE
    STATUS      current
    DESCRIPTION
        "The compliance statement for SNMP entities which use SNTP and
         implement the NTP MIB"
    MODULE  -- this module
        MANDATORY-GROUPS {
                           ntpEntObjectsGroup1
        }
        ::= { ntpEntCompliances 2 }

ntpEntObjectsGroup1 OBJECT-GROUP
    OBJECTS {
              ntpEntSoftwareName,
              ntpEntSoftwareVersion,
--              ntpEntSoftwareVersionVal,
              ntpEntSoftwareVendor,
              ntpEntSystemType,
--              ntpEntStatusEntityUptime,
              ntpEntStatusDateTime
--              ntpAssocName,
--              ntpAssocRefId,
--              ntpAssocAddressType,
--              ntpAssocAddress
    }
    STATUS      current
    DESCRIPTION
        "A collection of objects for the NTP MIB that all NTP
         or SNTP entities should implement."
    ::= { ntpEntGroups 1 }

ntpEntObjectsGroup2 OBJECT-GROUP
    OBJECTS {
              ntpEntTimeResolution,
--              ntpEntTimeResolutionVal,
              ntpEntTimePrecision,
--              ntpEntTimePrecisionVal,
--              ntpEntTimeDistance,
              ntpEntStatusCurrentMode,
              ntpEntStatusCurrentModeVal,
              ntpEntStatusStratum,
              ntpEntStatusActiveRefSourceId,
              ntpEntStatusActiveRefSourceName,
--              ntpEntStatusActiveOffset,
              ntpEntStatusNumberOfRefSources,
--              ntpEntStatusDispersion,
--              ntpEntStatusLeapSecond,
--              ntpEntStatusLeapSecDirection,
              ntpEntStatusInPkts,
              ntpEntStatusOutPkts,
              ntpEntStatusBadVersion,
              ntpEntStatusProtocolError
--              ntpEntStatusNotifications,
--              ntpAssocOffset,
--              ntpAssocStratum,
--              ntpAssocStatusJitter,
--              ntpAssocStatusDelay,
--              ntpAssocStatusDispersion,
--              ntpAssocStatInPkts,
--              ntpAssocStatOutPkts,
--              ntpAssocStatProtocolError,
--              ntpEntHeartbeatInterval,
--              ntpEntNotifBits,
--              ntpEntNotifMessage
    }
    STATUS      current
    DESCRIPTION
        "A collection of objects for the NTP MIB that are optional
         for NTP or SNTP entities to implement."
    ::= { ntpEntGroups 2 }

--ntpEntNotifPrefixGroup NOTIFICATION-GROUP
--    NOTIFICATIONS {
--                    ntpEntNotifModeChange,
--                    ntpEntNotifStratumChange,
--                    ntpEntNotifSyspeerChanged,
--                    ntpEntNotifAddAssociation,
--                    ntpEntNotifRemoveAssociation,
--                    ntpEntNotifConfigChanged,
--                    ntpEntNotifLeapSecondAnnounced,
--                    ntpEntNotifHeartbeat
--    }
--    STATUS      current
--    DESCRIPTION
--        "A collection of notifications for the NTP MIB"
--    ::= { ntpEntGroups 3 }
 
--********************************************************************************************************
--********************************************************************************************************              

-- (xxx.100.26)   priPoeConfig group
  		    
--xxx.100.26.1
poeSystemEnable OBJECT-TYPE
    SYNTAX  INTEGER
	    {
		         	enable (1), 
		         	disable (0)
	    }  
    MAX-ACCESS  read-write
    STATUS  current
    DESCRIPTION
        " The power inline global switch. Enable expresses it is turned on, while disable indicates that off."
    ::= { priPoeConfig   1 }
    
--xxx.100.26.2
poeMaxPower OBJECT-TYPE
    SYNTAX  INTEGER (37..180) 
    MAX-ACCESS  read-write
    STATUS  current
    DESCRIPTION
        " The power inline global available power whitch cannot be exceeded by the total power of all PDs."
    ::= { priPoeConfig   2 } 
    
--xxx.100.26.3
poePoliceEnable OBJECT-TYPE
    SYNTAX  INTEGER
	    {
		         	enable (1), 
		         	disable (0)
	    }  
    MAX-ACCESS  read-write
    STATUS  current
    DESCRIPTION
        " The power inline power mamagement switch. Enable expresses it is in priority-policy mode, while disable indicates that in first-in-first-get mode."
    ::= { priPoeConfig   3 }  
    
--xxx.100.26.4
poeLegacyEnable OBJECT-TYPE
    SYNTAX  INTEGER
	    {
		         	enable (1), 
		         	disable (0)
	    }  
    MAX-ACCESS  read-write
    STATUS  current
    DESCRIPTION
        " The power inline nonstandard PD detect switch. Enable expresses nonstandard PD can be detected, while disable indicates that cannot be detected."
    ::= { priPoeConfig   4 } 
    
--xxx.100.26.5
poeDisconnect OBJECT-TYPE
    SYNTAX  INTEGER
	    {
		         	ac  (0),
		         	dc  (1)		         	
	    }  
    MAX-ACCESS  read-only
    STATUS  current
    DESCRIPTION
        " The power inline disconnection mode."
    ::= { priPoeConfig  5 }   
    
--xxx.100.26.6
poeCurrentPower OBJECT-TYPE
    SYNTAX  INTEGER
    MAX-ACCESS  read-only
    STATUS  current
    DESCRIPTION
        " The power inline current export power. It is a real time value."
    ::= { priPoeConfig   6 } 
    
--xxx.100.26.7
poePortMode OBJECT-TYPE
        SYNTAX      INTEGER
 	    {
                               spare (1), 
                               signal (0)
	    }        
        MAX-ACCESS  read-only
        STATUS      current
        DESCRIPTION 
        " The power inline power supply mode."
        ::= { priPoeConfig 7 }        
    
--xxx.100.26.8
poeSoftwareVersion OBJECT-TYPE
    SYNTAX  DisplayString (SIZE(1..32))
    MAX-ACCESS  read-only
    STATUS  current
    DESCRIPTION
        " The power inline software version."
    ::= { priPoeConfig   8 }  
    
--xxx.100.26.9
poeHardwareVersion OBJECT-TYPE
    SYNTAX  DisplayString (SIZE(1..32))
    MAX-ACCESS  read-only
    STATUS  current
    DESCRIPTION
        " The power inline hardware version."
    ::= { priPoeConfig   9 }
                                  
--xxx.100.26.10
    poePortConfigTable OBJECT-TYPE
        SYNTAX  SEQUENCE OF PoePortConfigEntry
        MAX-ACCESS  not-accessible
        STATUS  current
        DESCRIPTION
            " The power inline port configuration table"
        ::= { priPoeConfig 10 }
        
--xxx.100.26.10.1
    poePortConfigEntry OBJECT-TYPE
        SYNTAX  PoePortConfigEntry
        MAX-ACCESS  not-accessible
        STATUS  current
        DESCRIPTION
            " The power inline configuration in port."
        INDEX   { portIndex }
        ::= { poePortConfigTable 1 }        

    PoePortConfigEntry
        ::= SEQUENCE
            {
                poePortIndex               INTEGER,
                poePortStatus              INTEGER,
                poePortPriority	           INTEGER,
                poePortMaxPower	           INTEGER,  
                poePortCurrentPower        INTEGER,
                poePortCurrentCurrent	   INTEGER,
                poePortCurrentVoltage      INTEGER,
                poePortPdStatus		   INTEGER,
                poePortPdClass		   INTEGER
            }
            
--xxx.100.26.10.1.1
poePortIndex OBJECT-TYPE
        SYNTAX      INTEGER
        MAX-ACCESS  not-accessible
        STATUS      current
        DESCRIPTION 
            "The power inline port index."
        ::= { poePortConfigEntry 1 }	
        
--xxx.100.26.10.1.2
poePortStatus OBJECT-TYPE
        SYNTAX      INTEGER
 	    {
		         	enable (1), 
		         	disable (0)
	    }        
        MAX-ACCESS  read-write
        STATUS      current
        DESCRIPTION 
        " The power inline port switch. Enable expresses it is turned on, while disable indicates that off."
        ::= { poePortConfigEntry 2 } 
        
--xxx.100.26.10.1.3
poePortPriority OBJECT-TYPE
        SYNTAX      INTEGER
 	    {
                               critical (0), 
                               high (1), 
                               low (2)
	    }        
        MAX-ACCESS  read-write
        STATUS      current
        DESCRIPTION 
        " The power inline port priority."
        ::= { poePortConfigEntry 3 }  
        
--xxx.100.26.10.1.4
poePortMaxPower OBJECT-TYPE
        SYNTAX      INTEGER (1..15400)       
        MAX-ACCESS  read-write
        STATUS      current
        DESCRIPTION 
        " The power inline port available power whitch cannot be exceeded by the connected PD."
        ::= { poePortConfigEntry 4 } 
        
--xxx.100.26.10.1.5
poePortCurrentPower OBJECT-TYPE
        SYNTAX      INTEGER        
        MAX-ACCESS  read-only
        STATUS      current
        DESCRIPTION 
        " The power inline port used power. It is a real time value."
        ::= { poePortConfigEntry 5 }    
        
--xxx.100.26.10.1.6
poePortCurrentCurrent OBJECT-TYPE
        SYNTAX      INTEGER        
        MAX-ACCESS  read-only
        STATUS      current
        DESCRIPTION 
        " The power inline port export current. It is a real time value."
        ::= { poePortConfigEntry 6 }  
        
--xxx.100.26.10.1.7
poePortCurrentVoltage OBJECT-TYPE
        SYNTAX      INTEGER        
        MAX-ACCESS  read-only
        STATUS      current
        DESCRIPTION 
        " The power inline port export voltage. It is a real time value."
        ::= { poePortConfigEntry 7 }
        
--xxx.100.26.10.1.8
poePortPdStatus OBJECT-TYPE
        SYNTAX      INTEGER
        {
               on(1), 
               off(2),
               faulty(3),
               deny(4)
        }        
        MAX-ACCESS  read-only
        STATUS      current
        DESCRIPTION 
        " The power inline detect status. on(1):PD is connected and natural powered, off(2):PD is not connected,
        faulty(3):error, deny(4):power is low or high."
        ::= { poePortConfigEntry 8 } 
        
--xxx.100.26.10.1.9
poePortPdClass OBJECT-TYPE
        SYNTAX      INTEGER        
        MAX-ACCESS  read-only
        STATUS      current
        DESCRIPTION 
        " The connected PD class of power inline"
        ::= { poePortConfigEntry 9 }                                                           	             

--********************************************************************************************************
--********************************************************************************************************              

-- (xxx.100.27)   priQos2 group

--xxx.100.27.1
    qos2         	    OBJECT IDENTIFIER ::= { priQos2 1 } 
--********************************************************************************************************
--xxx.100.27.1.1
    qos2MapCostoIntp         	    OBJECT IDENTIFIER ::= { qos2 1 } 
    
--xxx.100.27.1.1.1
        qos2MapCostoIntp1 OBJECT-TYPE
            SYNTAX  INTEGER
            MAX-ACCESS  read-create
            STATUS  current
            DESCRIPTION
                "COS to IntPrio map,IntPrio1<0-7>."
            ::= { qos2MapCostoIntp  1 }

--xxx.100.27.1.1.2
	    qos2MapCostoIntp2 OBJECT-TYPE
	        SYNTAX  INTEGER
	        MAX-ACCESS  read-create
	        STATUS  current
	        DESCRIPTION
	            "COS to IntPrio map,IntPrio2<0-7>."
	        ::= { qos2MapCostoIntp  2 }

--xxx.100.27.1.1.3
	    qos2MapCostoIntp3 OBJECT-TYPE
	        SYNTAX  INTEGER
	        MAX-ACCESS  read-create
	        STATUS  current
	        DESCRIPTION
	            "COS to IntPrio map,IntPrio1<0-7>."
	        ::= { qos2MapCostoIntp  3 }

--xxx.100.27.1.1.4
	    qos2MapCostoIntp4 OBJECT-TYPE
	        SYNTAX  INTEGER
	        MAX-ACCESS  read-create
	        STATUS  current
	        DESCRIPTION
	            "COS to IntPrio map,IntPrio1<0-7>."
	        ::= { qos2MapCostoIntp  4 }

--xxx.100.27.1.1.5
	    qos2MapCostoIntp5 OBJECT-TYPE
	        SYNTAX  INTEGER
	        MAX-ACCESS  read-create
	        STATUS  current
	        DESCRIPTION
	            "COS to IntPrio map,IntPrio1<0-7>."
	        ::= { qos2MapCostoIntp  5 }

--xxx.100.27.1.1.6      
	    qos2MapCostoIntp6 OBJECT-TYPE
	        SYNTAX  INTEGER
	        MAX-ACCESS  read-create
	        STATUS  current
	        DESCRIPTION
	            "COS to IntPrio map,IntPrio1<0-7>."
	        ::= { qos2MapCostoIntp  6 }

--xxx.100.27.1.1.7        
	    qos2MapCostoIntp7 OBJECT-TYPE
	        SYNTAX  INTEGER
	        MAX-ACCESS  read-create
	        STATUS  current
	        DESCRIPTION
	            "COS to IntPrio map,IntPrio1<0-7>."
	        ::= { qos2MapCostoIntp  7 }

--xxx.100.27.1.1.8     
	    qos2MapCostoIntp8 OBJECT-TYPE
	        SYNTAX  INTEGER
	        MAX-ACCESS  read-create
	        STATUS  current
	        DESCRIPTION
	            "COS to IntPrio map,IntPrio1<0-7>."
	        ::= { qos2MapCostoIntp  8 }
                              
--xxx.100.27.1.1.9
        qos2MapCostoIntpStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapCostoIntp 9 } 
            
--xxx.100.27.1.2
    qos2MapCostoDP         	    OBJECT IDENTIFIER ::= { qos2 2 } 
    
--xxx.100.27.1.2.1
        qos2MapCostoDP1 OBJECT-TYPE
            SYNTAX  INTEGER
            MAX-ACCESS  read-create
            STATUS  current
            DESCRIPTION
                "COS to drop precedence map,Drop Precedence1<0-2>."
            ::= { qos2MapCostoDP  1 }

--xxx.100.27.1.2.2
	    qos2MapCostoDP2 OBJECT-TYPE
	        SYNTAX  INTEGER
	        MAX-ACCESS  read-create
	        STATUS  current
	        DESCRIPTION
	            "COS to drop precedence map,Drop Precedence2<0-2>."
	        ::= { qos2MapCostoDP  2 }

--xxx.100.27.1.2.3
	    qos2MapCostoDP3 OBJECT-TYPE
	        SYNTAX  INTEGER
	        MAX-ACCESS  read-create
	        STATUS  current
	        DESCRIPTION
	            "COS to drop precedence map,Drop Precedence3<0-2>."
	        ::= { qos2MapCostoDP  3 }

--xxx.100.27.1.2.4
	    qos2MapCostoDP4 OBJECT-TYPE
	        SYNTAX  INTEGER
	        MAX-ACCESS  read-create
	        STATUS  current
	        DESCRIPTION
	            "COS to drop precedence map,Drop Precedence4<0-2>."
	        ::= { qos2MapCostoDP  4 }

--xxx.100.27.1.2.5
	    qos2MapCostoDP5 OBJECT-TYPE
	        SYNTAX  INTEGER
	        MAX-ACCESS  read-create
	        STATUS  current
	        DESCRIPTION
	            "COS to drop precedence map,Drop Precedence5<0-2>."
	        ::= { qos2MapCostoDP  5 }

--xxx.100.27.1.2.6      
	    qos2MapCostoDP6 OBJECT-TYPE
	        SYNTAX  INTEGER
	        MAX-ACCESS  read-create
	        STATUS  current
	        DESCRIPTION
	            "COS to drop precedence map,Drop Precedence6<0-2>."
	        ::= { qos2MapCostoDP  6 }

--xxx.100.27.1.2.7        
	    qos2MapCostoDP7 OBJECT-TYPE
	        SYNTAX  INTEGER
	        MAX-ACCESS  read-create
	        STATUS  current
	        DESCRIPTION
	            "COS to drop precedence map,Drop Precedence7<0-2>."
	        ::= { qos2MapCostoDP  7 }

--xxx.100.27.1.2.8     
	    qos2MapCostoDP8 OBJECT-TYPE
	        SYNTAX  INTEGER
	        MAX-ACCESS  read-create
	        STATUS  current
	        DESCRIPTION
	            "COS to drop precedence map,Drop Precedence8<0-2>."
	        ::= { qos2MapCostoDP  8 }
                              
--xxx.100.27.1.2.9
        qos2MapCostoDPStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapCostoDP 9 }             

--xxx.100.27.1.3
    qos2MapDSCPtoDSCP         	    OBJECT IDENTIFIER ::= { qos2 3 } 
    
--xxx.100.27.1.3.1
        qos2MapDSCPtoDSCP1 OBJECT-TYPE
            SYNTAX  INTEGER
            MAX-ACCESS  read-create
            STATUS  current
            DESCRIPTION
                "DSCP to DSCP map, DSCP1<0-63>."
            ::= { qos2MapDSCPtoDSCP  1 }

--xxx.100.27.1.3.2
	    qos2MapDSCPtoDSCP2 OBJECT-TYPE
	        SYNTAX  INTEGER
	        MAX-ACCESS  read-create
	        STATUS  current
	        DESCRIPTION
	            "DSCP to DSCP map, DSCP2<0-63>."
	        ::= { qos2MapDSCPtoDSCP  2 }

--xxx.100.27.1.3.3
	    qos2MapDSCPtoDSCP3 OBJECT-TYPE
	        SYNTAX  INTEGER
	        MAX-ACCESS  read-create
	        STATUS  current
	        DESCRIPTION
	            "DSCP to DSCP map, DSCP3<0-63>."
	        ::= { qos2MapDSCPtoDSCP  3 }

--xxx.100.27.1.3.4
	    qos2MapDSCPtoDSCP4 OBJECT-TYPE
	        SYNTAX  INTEGER
	        MAX-ACCESS  read-create
	        STATUS  current
	        DESCRIPTION
	            "DSCP to DSCP map, DSCP4<0-63>."
	        ::= { qos2MapDSCPtoDSCP  4 }

--xxx.100.27.1.3.5
	    qos2MapDSCPtoDSCP5 OBJECT-TYPE
	        SYNTAX  INTEGER
	        MAX-ACCESS  read-create
	        STATUS  current
	        DESCRIPTION
	            "DSCP to DSCP map, DSCP5<0-63>."
	        ::= { qos2MapDSCPtoDSCP  5 }

--xxx.100.27.1.3.6      
	    qos2MapDSCPtoDSCP6 OBJECT-TYPE
	        SYNTAX  INTEGER
	        MAX-ACCESS  read-create
	        STATUS  current
	        DESCRIPTION
	            "DSCP to DSCP map, DSCP6<0-63>."
	        ::= { qos2MapDSCPtoDSCP  6 }

--xxx.100.27.1.3.7        
	    qos2MapDSCPtoDSCP7 OBJECT-TYPE
	        SYNTAX  INTEGER
	        MAX-ACCESS  read-create
	        STATUS  current
	        DESCRIPTION
	            "DSCP to DSCP map, DSCP7<0-63>."
	        ::= { qos2MapDSCPtoDSCP  7 }

--xxx.100.27.1.3.8     
	    qos2MapDSCPtoDSCP8 OBJECT-TYPE
	        SYNTAX  INTEGER
	        MAX-ACCESS  read-create
	        STATUS  current
	        DESCRIPTION
	            "DSCP to DSCP map, DSCP8<0-63>."
	        ::= { qos2MapDSCPtoDSCP 8 }

--xxx.100.27.1.3.9     
	    qos2MapDSCPtoDSCPoutDSCP OBJECT-TYPE
	        SYNTAX  INTEGER
	        MAX-ACCESS  read-create
	        STATUS  current
	        DESCRIPTION
	            "DSCP to DSCP map, outDSCP<0-63>."
	        ::= { qos2MapDSCPtoDSCP 9 }
	                                   
--xxx.100.27.1.3.10
        qos2MapDSCPtoDSCPStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapDSCPtoDSCP 10 }    
                     
--xxx.100.27.1.4
    qos2MapDSCPtoIntp        	    OBJECT IDENTIFIER ::= { qos2 4 } 
    
--xxx.100.27.1.4.1
        qos2MapDSCPtoIntp1 OBJECT-TYPE
            SYNTAX  INTEGER
            MAX-ACCESS  read-create
            STATUS  current
            DESCRIPTION
                "DSCP to Intp map, DSCP1<0-63>."
            ::= { qos2MapDSCPtoIntp  1 }

--xxx.100.27.1.4.2
	    qos2MapDSCPtoIntp2 OBJECT-TYPE
	        SYNTAX  INTEGER
	        MAX-ACCESS  read-create
	        STATUS  current
	        DESCRIPTION
	            "DSCP to Intp map, DSCP2<0-63>."
	        ::= { qos2MapDSCPtoIntp  2 }

--xxx.100.27.1.4.3
	    qos2MapDSCPtoIntp3 OBJECT-TYPE
	        SYNTAX  INTEGER
	        MAX-ACCESS  read-create
	        STATUS  current
	        DESCRIPTION
	            "DSCP to Intp map, DSCP3<0-63>."
	        ::= { qos2MapDSCPtoIntp  3 }

--xxx.100.27.1.4.4
	    qos2MapDSCPtoIntp4 OBJECT-TYPE
	        SYNTAX  INTEGER
	        MAX-ACCESS  read-create
	        STATUS  current
	        DESCRIPTION
	            "DSCP to Intp map, DSCP4<0-63>."
	        ::= { qos2MapDSCPtoIntp  4 }

--xxx.100.27.1.4.5
	    qos2MapDSCPtoIntp5 OBJECT-TYPE
	        SYNTAX  INTEGER
	        MAX-ACCESS  read-create
	        STATUS  current
	        DESCRIPTION
	            "DSCP to Intp map, DSCP5<0-63>."
	        ::= { qos2MapDSCPtoIntp  5 }

--xxx.100.27.1.4.6      
	    qos2MapDSCPtoIntp6 OBJECT-TYPE
	        SYNTAX  INTEGER
	        MAX-ACCESS  read-create
	        STATUS  current
	        DESCRIPTION
	            "DSCP to Intp map, DSCP6<0-63>."
	        ::= { qos2MapDSCPtoIntp  6 }

--xxx.100.27.1.4.7        
	    qos2MapDSCPtoIntp7 OBJECT-TYPE
	        SYNTAX  INTEGER
	        MAX-ACCESS  read-create
	        STATUS  current
	        DESCRIPTION
	            "DSCP to Intp map, DSCP7<0-63>."
	        ::= { qos2MapDSCPtoIntp  7 }

--xxx.100.27.1.4.8     
	    qos2MapDSCPtoIntp8 OBJECT-TYPE
	        SYNTAX  INTEGER
	        MAX-ACCESS  read-create
	        STATUS  current
	        DESCRIPTION
	            "DSCP to Intp map, DSCP8<0-63>."
	        ::= { qos2MapDSCPtoIntp 8 }

--xxx.100.27.1.4.9     
	    qos2MapDSCPtoIntpIntPriovalue OBJECT-TYPE
	        SYNTAX  INTEGER
	        MAX-ACCESS  read-create
	        STATUS  current
	        DESCRIPTION
	            "DSCP to Intp map, IntPrio value<0-7>."
	        ::= { qos2MapDSCPtoIntp 9 }
	                                   
--xxx.100.27.1.4.10
        qos2MapDSCPtoIntpStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapDSCPtoIntp 10 }            

--xxx.100.27.1.5
    qos2MapDSCPtoDP       	    OBJECT IDENTIFIER ::= { qos2 5 } 
    
--xxx.100.27.1.5.1
        qos2MapDSCPtoDP1 OBJECT-TYPE
            SYNTAX  INTEGER
            MAX-ACCESS  read-create
            STATUS  current
            DESCRIPTION
                "DSCP to DP map, DSCP1<0-63>."
            ::= { qos2MapDSCPtoDP  1 }

--xxx.100.27.1.5.2
	    qos2MapDSCPtoDP2 OBJECT-TYPE
	        SYNTAX  INTEGER
	        MAX-ACCESS  read-create
	        STATUS  current
	        DESCRIPTION
	            "DSCP to DP map, DSCP2<0-63>."
	        ::= { qos2MapDSCPtoDP  2 }

--xxx.100.27.1.5.3
	    qos2MapDSCPtoDP3 OBJECT-TYPE
	        SYNTAX  INTEGER
	        MAX-ACCESS  read-create
	        STATUS  current
	        DESCRIPTION
	            "DSCP to DP map, DSCP3<0-63>."
	        ::= { qos2MapDSCPtoDP  3 }

--xxx.100.27.1.5.4
	    qos2MapDSCPtoDP4 OBJECT-TYPE
	        SYNTAX  INTEGER
	        MAX-ACCESS  read-create
	        STATUS  current
	        DESCRIPTION
	            "DSCP to DP map, DSCP4<0-63>."
	        ::= { qos2MapDSCPtoDP  4 }

--xxx.100.27.1.5.5
	    qos2MapDSCPtoDP5 OBJECT-TYPE
	        SYNTAX  INTEGER
	        MAX-ACCESS  read-create
	        STATUS  current
	        DESCRIPTION
	            "DSCP to DP map, DSCP5<0-63>."
	        ::= { qos2MapDSCPtoDP  5 }

--xxx.100.27.1.5.6      
	    qos2MapDSCPtoDP6 OBJECT-TYPE
	        SYNTAX  INTEGER
	        MAX-ACCESS  read-create
	        STATUS  current
	        DESCRIPTION
	            "DSCP to DP map, DSCP6<0-63>."
	        ::= { qos2MapDSCPtoDP  6 }

--xxx.100.27.1.5.7        
	    qos2MapDSCPtoDP7 OBJECT-TYPE
	        SYNTAX  INTEGER
	        MAX-ACCESS  read-create
	        STATUS  current
	        DESCRIPTION
	            "DSCP to DP map, DSCP7<0-63>."
	        ::= { qos2MapDSCPtoDP  7 }

--xxx.100.27.1.5.8     
	    qos2MapDSCPtoDP8 OBJECT-TYPE
	        SYNTAX  INTEGER
	        MAX-ACCESS  read-create
	        STATUS  current
	        DESCRIPTION
	            "DSCP to DP map, DSCP8<0-63>."
	        ::= { qos2MapDSCPtoDP 8 }

--xxx.100.27.1.5.9     
	    qos2MapDSCPtoDPvalue OBJECT-TYPE
	        SYNTAX  INTEGER
	        MAX-ACCESS  read-create
	        STATUS  current
	        DESCRIPTION
	            "DSCP to DP map, Drop Precedence value<0-2>."
	        ::= { qos2MapDSCPtoDP 9 }
	                                   
--xxx.100.27.1.5.10
        qos2MapDSCPtoDPStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapDSCPtoDP 10 }            

--xxx.100.27.1.6
    qos2MapExptoIntp       	    OBJECT IDENTIFIER ::= { qos2 6 } 
    
--xxx.100.27.1.6.1
        qos2MapExptoIntp1 OBJECT-TYPE
            SYNTAX  INTEGER
            MAX-ACCESS  read-create
            STATUS  current
            DESCRIPTION
                "EXP to Intp map,  IntPrio1 value<0-7>."
            ::= { qos2MapExptoIntp  1 }

--xxx.100.27.1.6.2
	    qos2MapExptoIntp2 OBJECT-TYPE
	        SYNTAX  INTEGER
	        MAX-ACCESS  read-create
	        STATUS  current
	        DESCRIPTION
	            "EXP to Intp map,  IntPrio2 value<0-7>."
	        ::= { qos2MapExptoIntp  2 }

--xxx.100.27.1.6.3
	    qos2MapExptoIntp3 OBJECT-TYPE
	        SYNTAX  INTEGER
	        MAX-ACCESS  read-create
	        STATUS  current
	        DESCRIPTION
	            "EXP to Intp map,  IntPrio3 value<0-7>."
	        ::= { qos2MapExptoIntp  3 }

--xxx.100.27.1.6.4
	    qos2MapExptoIntp4 OBJECT-TYPE
	        SYNTAX  INTEGER
	        MAX-ACCESS  read-create
	        STATUS  current
	        DESCRIPTION
	            "EXP to Intp map,  IntPrio4 value<0-7>."
	        ::= { qos2MapExptoIntp  4 }

--xxx.100.27.1.6.5
	    qos2MapExptoIntp5 OBJECT-TYPE
	        SYNTAX  INTEGER
	        MAX-ACCESS  read-create
	        STATUS  current
	        DESCRIPTION
	            "EXP to Intp map,  IntPrio5 value<0-7>."
	        ::= { qos2MapExptoIntp  5 }

--xxx.100.27.1.6.6      
	    qos2MapExptoIntp6 OBJECT-TYPE
	        SYNTAX  INTEGER
	        MAX-ACCESS  read-create
	        STATUS  current
	        DESCRIPTION
	            "EXP to Intp map,  IntPrio6 value<0-7>."
	        ::= { qos2MapExptoIntp  6 }

--xxx.100.27.1.6.7        
	    qos2MapExptoIntp7 OBJECT-TYPE
	        SYNTAX  INTEGER
	        MAX-ACCESS  read-create
	        STATUS  current
	        DESCRIPTION
	            "EXP to Intp map,  IntPrio7 value<0-7>."
	        ::= { qos2MapExptoIntp  7 }

--xxx.100.27.1.6.8     
	    qos2MapExptoIntp8 OBJECT-TYPE
	        SYNTAX  INTEGER
	        MAX-ACCESS  read-create
	        STATUS  current
	        DESCRIPTION
	            "EXP to Intp map,  IntPrio8 value<0-7>."
	        ::= { qos2MapExptoIntp 8 }
	                                   
--xxx.100.27.1.6.9
        qos2MapExptoIntpStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapExptoIntp 9 }            

--xxx.100.27.1.7
    qos2MapExptoDP       	    OBJECT IDENTIFIER ::= { qos2 7 } 
    
--xxx.100.27.1.7.1
        qos2MapExptoDP1 OBJECT-TYPE
            SYNTAX  INTEGER
            MAX-ACCESS  read-create
            STATUS  current
            DESCRIPTION
                "EXP to DP map, Drop Precedence value<0-2>."
            ::= { qos2MapExptoDP  1 }

--xxx.100.27.1.7.2
	    qos2MapExptoDP2 OBJECT-TYPE
	        SYNTAX  INTEGER
	        MAX-ACCESS  read-create
	        STATUS  current
	        DESCRIPTION
	            "EXP to DP map, Drop Precedence value<0-2>."
	        ::= { qos2MapExptoDP  2 }

--xxx.100.27.1.7.3
	    qos2MapExptoDP3 OBJECT-TYPE
	        SYNTAX  INTEGER
	        MAX-ACCESS  read-create
	        STATUS  current
	        DESCRIPTION
	            "EXP to DP map, Drop Precedence value<0-2>."
	        ::= { qos2MapExptoDP  3 }

--xxx.100.27.1.7.4
	    qos2MapExptoDP4 OBJECT-TYPE
	        SYNTAX  INTEGER
	        MAX-ACCESS  read-create
	        STATUS  current
	        DESCRIPTION
	            "EXP to DP map, Drop Precedence value<0-2>."
	        ::= { qos2MapExptoDP  4 }

--xxx.100.27.1.7.5
	    qos2MapExptoDP5 OBJECT-TYPE
	        SYNTAX  INTEGER
	        MAX-ACCESS  read-create
	        STATUS  current
	        DESCRIPTION
	            "EXP to DP map, Drop Precedence value<0-2>."
	        ::= { qos2MapExptoDP  5 }

--xxx.100.27.1.7.6      
	    qos2MapExptoDP6 OBJECT-TYPE
	        SYNTAX  INTEGER
	        MAX-ACCESS  read-create
	        STATUS  current
	        DESCRIPTION
	            "EXP to DP map, Drop Precedence value<0-2>."
	        ::= { qos2MapExptoDP  6 }

--xxx.100.27.1.7.7        
	    qos2MapExptoDP7 OBJECT-TYPE
	        SYNTAX  INTEGER
	        MAX-ACCESS  read-create
	        STATUS  current
	        DESCRIPTION
	            "EXP to DP map, Drop Precedence value<0-2>."
	        ::= { qos2MapExptoDP  7 }

--xxx.100.27.1.7.8     
	    qos2MapExptoDP8 OBJECT-TYPE
	        SYNTAX  INTEGER
	        MAX-ACCESS  read-create
	        STATUS  current
	        DESCRIPTION
	            "EXP to DP map, Drop Precedence value<0-2>."
	        ::= { qos2MapExptoDP 8 }
	                                   
--xxx.100.27.1.7.9
        qos2MapExptoDPStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapExptoDP 9 }            

--xxx.100.27.1.8
    qos2MapIntptoDSCP       	    OBJECT IDENTIFIER ::= { qos2 8 } 
    
--xxx.100.27.1.8.1
        qos2MapIntptoDSCP1 OBJECT-TYPE
            SYNTAX  INTEGER
            MAX-ACCESS  read-create
            STATUS  current
            DESCRIPTION
                "Intp to DSCP map, IntPrio value<0-7>."
            ::= { qos2MapIntptoDSCP  1 }

--xxx.100.27.1.8.2
	    qos2MapIntptoDSCP2 OBJECT-TYPE
	        SYNTAX  INTEGER
	        MAX-ACCESS  read-create
	        STATUS  current
	        DESCRIPTION
	            "Intp to DSCP map, IntPrio value<0-7>."
	        ::= { qos2MapIntptoDSCP  2 }

--xxx.100.27.1.8.3
	    qos2MapIntptoDSCP3 OBJECT-TYPE
	        SYNTAX  INTEGER
	        MAX-ACCESS  read-create
	        STATUS  current
	        DESCRIPTION
	            "Intp to DSCP map, IntPrio value<0-7>."
	        ::= { qos2MapIntptoDSCP  3 }

--xxx.100.27.1.8.4
	    qos2MapIntptoDSCP4 OBJECT-TYPE
	        SYNTAX  INTEGER
	        MAX-ACCESS  read-create
	        STATUS  current
	        DESCRIPTION
	            "Intp to DSCP map, IntPrio value<0-7>."
	        ::= { qos2MapIntptoDSCP  4 }

--xxx.100.27.1.8.5
	    qos2MapIntptoDSCP5 OBJECT-TYPE
	        SYNTAX  INTEGER
	        MAX-ACCESS  read-create
	        STATUS  current
	        DESCRIPTION
	            "Intp to DSCP map, IntPrio value<0-7>."
	        ::= { qos2MapIntptoDSCP  5 }

--xxx.100.27.1.8.6      
	    qos2MapIntptoDSCP6 OBJECT-TYPE
	        SYNTAX  INTEGER
	        MAX-ACCESS  read-create
	        STATUS  current
	        DESCRIPTION
	            "Intp to DSCP map, IntPrio value<0-7>."
	        ::= { qos2MapIntptoDSCP  6 }

--xxx.100.27.1.8.7        
	    qos2MapIntptoDSCP7 OBJECT-TYPE
	        SYNTAX  INTEGER
	        MAX-ACCESS  read-create
	        STATUS  current
	        DESCRIPTION
	            "Intp to DSCP map, IntPrio value<0-7>."
	        ::= { qos2MapIntptoDSCP  7 }

--xxx.100.27.1.8.8     
	    qos2MapIntptoDSCP8 OBJECT-TYPE
	        SYNTAX  INTEGER
	        MAX-ACCESS  read-create
	        STATUS  current
	        DESCRIPTION
	            "Intp to DSCP map, IntPrio value<0-7>."
	        ::= { qos2MapIntptoDSCP 8 }
	                                   
--xxx.100.27.1.8.9
        qos2MapIntptoDSCPStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapIntptoDSCP 9 }            

--xxx.100.27.1.10
    qos2MapIntptoEXP       	    OBJECT IDENTIFIER ::= { qos2 10 } 
    
--xxx.100.27.1.10.1
        qos2MapIntptoEXP1 OBJECT-TYPE
            SYNTAX  INTEGER
            MAX-ACCESS  read-create
            STATUS  current
            DESCRIPTION
                "Intp to EXP map, EXP value<0-7>."
            ::= { qos2MapIntptoEXP  1 }

--xxx.100.27.1.10.2
	    qos2MapIntptoEXP2 OBJECT-TYPE
	        SYNTAX  INTEGER
	        MAX-ACCESS  read-create
	        STATUS  current
	        DESCRIPTION
	            "Intp to EXP map, EXP value<0-7>."
	        ::= { qos2MapIntptoEXP  2 }

--xxx.100.27.1.10.3
	    qos2MapIntptoEXP3 OBJECT-TYPE
	        SYNTAX  INTEGER
	        MAX-ACCESS  read-create
	        STATUS  current
	        DESCRIPTION
	            "Intp to EXP map, EXP value<0-7>."
	        ::= { qos2MapIntptoEXP  3 }

--xxx.100.27.1.10.4
	    qos2MapIntptoEXP4 OBJECT-TYPE
	        SYNTAX  INTEGER
	        MAX-ACCESS  read-create
	        STATUS  current
	        DESCRIPTION
	            "Intp to EXP map, EXP value<0-7>."
	        ::= { qos2MapIntptoEXP  4 }

--xxx.100.27.1.10.5
	    qos2MapIntptoEXP5 OBJECT-TYPE
	        SYNTAX  INTEGER
	        MAX-ACCESS  read-create
	        STATUS  current
	        DESCRIPTION
	            "Intp to EXP map, EXP value<0-7>."
	        ::= { qos2MapIntptoEXP  5 }

--xxx.100.27.1.10.6      
	    qos2MapIntptoEXP6 OBJECT-TYPE
	        SYNTAX  INTEGER
	        MAX-ACCESS  read-create
	        STATUS  current
	        DESCRIPTION
	            "Intp to EXP map, EXP value<0-7>."
	        ::= { qos2MapIntptoEXP  6 }

--xxx.100.27.1.10.7        
	    qos2MapIntptoEXP7 OBJECT-TYPE
	        SYNTAX  INTEGER
	        MAX-ACCESS  read-create
	        STATUS  current
	        DESCRIPTION
	            "Intp to EXP map, EXP value<0-7>."
	        ::= { qos2MapIntptoEXP  7 }

--xxx.100.27.1.10.8     
	    qos2MapIntptoEXP8 OBJECT-TYPE
	        SYNTAX  INTEGER
	        MAX-ACCESS  read-create
	        STATUS  current
	        DESCRIPTION
	            "Intp to EXP map, EXP value<0-7>."
	        ::= { qos2MapIntptoEXP 8 }
	                                   
--xxx.100.27.1.10.9
        qos2MapIntptoEXPStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2MapIntptoEXP 9 }                  

--xxx.100.27.1.11
    qos2AggregatePolicy       	    OBJECT IDENTIFIER ::= { qos2 11 } 
    
--xxx.100.27.1.11.1
        qos2AggPolicyName OBJECT-TYPE
            SYNTAX  DisplayString (SIZE(1..64))
            MAX-ACCESS  read-create
            STATUS  current
            DESCRIPTION
                "Aggregate policy name<1-64>."
            ::= { qos2AggregatePolicy  1 }

--xxx.100.27.1.11.2
	    qos2AggPolicyCIRKbps OBJECT-TYPE
	        SYNTAX  INTEGER
	        MAX-ACCESS  read-create
	        STATUS  current
	        DESCRIPTION
	            "CIR(Committed Information Rate) Kbits per second <1-10000000>."
	        ::= { qos2AggregatePolicy  2 }

--xxx.100.27.1.11.3
	    qos2AggPolicyCBSKbps OBJECT-TYPE
	        SYNTAX  INTEGER
	        MAX-ACCESS  read-create
	        STATUS  current
	        DESCRIPTION
	            "CBS(Committed Burst Size) Kbits per second <1-1000000>."
	        ::= { qos2AggregatePolicy  3 }

--xxx.100.27.1.11.4
	    qos2AggPolicyPBSKbps OBJECT-TYPE
	        SYNTAX  INTEGER
	        MAX-ACCESS  read-create
	        STATUS  current
	        DESCRIPTION
	            "PBS(Peak Burst Size) Kbits per second <1-1000000>."
	        ::= { qos2AggregatePolicy  4 }

--xxx.100.27.1.11.5
	    qos2AggPolicyPIRKbps OBJECT-TYPE
	        SYNTAX  INTEGER
	        MAX-ACCESS  read-create
	        STATUS  current
	        DESCRIPTION
	            "PIR(Peak Information Rate) Kbits per second <1-10000000>."
	        ::= { qos2AggregatePolicy  5 }

--xxx.100.27.1.11.6      
	    qos2AggPolicyConformAction OBJECT-TYPE
	        SYNTAX  INTEGER
            	{
            	    transmit(0),
            	    drop(1),
               		set-dscp-transmit(2), 
               		set-prec-transmit(3),
               		set-cos-transmit(4), 
               		set-drop-precedence(5),
               		set-internal-priority(6)           		      	
            	}
	        MAX-ACCESS  read-create
	        STATUS  current
	        DESCRIPTION
	            "conform-action transmit means send packets without any change when specified speed is not exceeded; 
	             conform-action drop means drop packets when specified speed is not exceeded; 
	             conform-action set-dscp-transmit specifies to mark down packet DSCP value according to policed-dscp mapping when specified speed is not exceeded; 
	             conform-action set-prec-transmit specifies to mark down packet TOS value according to policed-dscp mapping when specified speed is not exceeded.
                ."
	        ::= { qos2AggregatePolicy  6 }

--xxx.100.27.1.11.7        
	    qos2AggPolicyConformActionChangeValue OBJECT-TYPE
	        SYNTAX  INTEGER
	        MAX-ACCESS  read-create
	        STATUS  current
	        DESCRIPTION
	            "If conform-action is set-dscp-transmit(2),the value is between 0-63; 
	             If conform-action is set-prec-transmit(3),the value is between 0-7;
	             If conform-action is set-cos-transmit(4),the value is between 0-7;
	             If conform-action is set-drop-precedence(5),the value is between 0-2;
	             If conform-action is set-internal-priority(6),the value is between 0-7;"
	        ::= { qos2AggregatePolicy  7 }

--xxx.100.27.1.11.8      
	    qos2AggPolicyExceedAction OBJECT-TYPE
	        SYNTAX  INTEGER
            	{
            	    transmit(0),
            	    drop(1),
               		set-dscp-transmit(2), 
               		set-prec-transmit(3),
               		set-cos-transmit(4), 
               		set-drop-precedence(5),
               		set-internal-priority(6)           		      	
            	}
	        MAX-ACCESS  read-create
	        STATUS  current
	        DESCRIPTION
	            "conform-action transmit means send packets without any change when specified speed is not exceeded; 
	             conform-action drop means drop packets when specified speed is not exceeded; 
	             conform-action set-dscp-transmit specifies to mark down packet DSCP value according to policed-dscp mapping when specified speed is not exceeded; 
	             conform-action set-prec-transmit specifies to mark down packet TOS value according to policed-dscp mapping when specified speed is not exceeded.
                ."
	        ::= { qos2AggregatePolicy  8 }

--xxx.100.27.1.11.9        
	    qos2AggPolicyExceedActionChangeValue OBJECT-TYPE
	        SYNTAX  INTEGER
	        MAX-ACCESS  read-create
	        STATUS  current
	        DESCRIPTION
	            "If conform-action is set-dscp-transmit(2),the value is between 0-63; 
	             If conform-action is set-prec-transmit(3),the value is between 0-7;
	             If conform-action is set-cos-transmit(4),the value is between 0-7;
	             If conform-action is set-drop-precedence(5),the value is between 0-2;
	             If conform-action is set-internal-priority(6),the value is between 0-7;"
	        ::= { qos2AggregatePolicy  9 }
	        
--xxx.100.27.1.11.10      
	    qos2AggPolicyViolateAction OBJECT-TYPE
	        SYNTAX  INTEGER
            	{
            	    transmit(0),
            	    drop(1),
               		set-dscp-transmit(2), 
               		set-prec-transmit(3),
               		set-cos-transmit(4), 
               		set-drop-precedence(5),
               		set-internal-priority(6)           		      	
            	}
	        MAX-ACCESS  read-create
	        STATUS  current
	        DESCRIPTION
	            "conform-action transmit means send packets without any change when specified speed is not exceeded; 
	             conform-action drop means drop packets when specified speed is not exceeded; 
	             conform-action set-dscp-transmit specifies to mark down packet DSCP value according to policed-dscp mapping when specified speed is not exceeded; 
	             conform-action set-prec-transmit specifies to mark down packet TOS value according to policed-dscp mapping when specified speed is not exceeded.
                ."
	        ::= { qos2AggregatePolicy  10 }

--xxx.100.27.1.11.11        
	    qos2AggPolicyViolateActionChangeValue OBJECT-TYPE
	        SYNTAX  INTEGER
	        MAX-ACCESS  read-create
	        STATUS  current
	        DESCRIPTION
	            "If conform-action is set-dscp-transmit(2),the value is between 0-63; 
	             If conform-action is set-prec-transmit(3),the value is between 0-7;
	             If conform-action is set-cos-transmit(4),the value is between 0-7;
	             If conform-action is set-drop-precedence(5),the value is between 0-2;
	             If conform-action is set-internal-priority(6),the value is between 0-7;"
	        ::= { qos2AggregatePolicy  11 }	        

--xxx.100.27.1.11.12
        qos2AggPolicyStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2AggregatePolicy 12 }          


--xxx.100.27.1.12
qos2ServicePolicyTable OBJECT-TYPE
    SYNTAX  SEQUENCE OF Qos2ServicePolicyEntry
    MAX-ACCESS  not-accessible
    STATUS  current
    DESCRIPTION
    	" QoS service policy table."
    ::= { qos2  12}   

--xxx.100.27.1.12.1
qos2ServicePolicyEntry OBJECT-TYPE
        SYNTAX  Qos2ServicePolicyEntry
        MAX-ACCESS  not-accessible
        STATUS  current
        DESCRIPTION
            " QoS service policy table."
        INDEX   { qos2PolicyMapName }
        ::= { qos2ServicePolicyTable 1 }
        
Qos2ServicePolicyEntry
        ::= SEQUENCE
            {
            qos2PolicyMapName	             DisplayString ,
    		qos2ServicePolicyVlanList         DisplayString , 
    		qos2ServicePolicyStatus	         INTEGER			
            }
 
--xxx.100.27.1.12.1.1
qos2PolicyMapName OBJECT-TYPE
    SYNTAX  DisplayString (SIZE(1..64)) 
            MAX-ACCESS  read-only
            STATUS  current
            DESCRIPTION
                "Policy map name<1-64>."
            ::= { qos2ServicePolicyEntry 1 }

        
--xxx.100.27.1.12.1.2
qos2ServicePolicyVlanList OBJECT-TYPE
    SYNTAX  DisplayString 
            MAX-ACCESS  read-only
            STATUS  current
            DESCRIPTION
                "Vlan list."
            ::= { qos2ServicePolicyEntry 2 } 

--xxx.100.27.1.12.1.3
qos2ServicePolicyStatus OBJECT-TYPE
    SYNTAX  INTEGER 
        	    {
           		active(1),
           		destroy(2)
        	    }
            MAX-ACCESS  read-create
            STATUS  current
            DESCRIPTION
                " Setting it to  active(1) to creates an entry,setting it to destroy(2) to destroy an entry."
            ::= { qos2ServicePolicyEntry 3 } 
	                                               
--xxx.100.27.1.13
qos2PortTable         	    OBJECT IDENTIFIER ::= { qos2 13 } 

--xxx.100.27.1.13.1
qos2PortIndex OBJECT-TYPE
    SYNTAX  INTEGER (1..10000)
            MAX-ACCESS  read-create
            STATUS  current
            DESCRIPTION
                "port Index"
            ::= { qos2PortTable 1 } 

--xxx.100.27.1.13.2
qos2PortType OBJECT-TYPE
    SYNTAX  INTEGER
                {
            	          trust(0),                
            		  cos(1),
            		  policy(2),            		  
 			  queueAndBandwidth(3),
               		  queueAndAlgorithm(4), 			  
               		  queueAndWdrr(5),
               		  queueAndWrr(6)
            	}
            MAX-ACCESS  read-create
            STATUS  current
            DESCRIPTION
                "the relation between qosPortType and CLI:
 		0 mls qos trust {cos |dscp };               
                1 mls qos cos {<default-cos>};     
		2 service-policy input WORD;
		3 mls qos queue {<queue id>} bandwidth {<MinBandwidth> <MaxBandwidth>};
		4 mls qos queue algorithm {sp |wdrr |wrr };
		5 mls qos queue wdrr weight {<Queue1 bandwidth> <Queue2 bandwidth> <Queue3 bandwidth> <Queue4 bandwidth> <Queue5 bandwidth> <Queue6 bandwidth> <Queue7 bandwidth> <Queue8 bandwidth>};
		6 mls qos queue wrr weight {<Queue1 weight> <Queue2 weight> <Queue3 weight> <Queue4 weight> <Queue5 weight> <Queue6 weight> <Queue7 weight> <Queue8 weight>}.						
		According to the relation,when configurate qos with snmp,first set the qosPortType to the correct value to select CLI,
		then set next CLI parameter.Fox example,set qos default cos is 5, first set qosPortType=1 ,then set qosPortCos to 5,
		finally setting qosPortStatus to 1, trigger snmp-cache works."
            ::= { qos2PortTable 2 }  
                               
--xxx.100.27.1.13.3
qos2PortCos OBJECT-TYPE
    SYNTAX  INTEGER(0..7)
            MAX-ACCESS  read-create
            STATUS  current
            DESCRIPTION
                "port default cos value"
            ::= { qos2PortTable 3 } 

--xxx.100.27.1.13.4
qos2PortTrust OBJECT-TYPE
    SYNTAX  INTEGER
            	{
               		cos(0),
               		dscp(1)
            	}
            MAX-ACCESS  read-create
            STATUS  current
            DESCRIPTION
                "Configure port trust.
            	  cos(0),mls qos trust cos;
               	  dscp(1),mls qos trust dscp."
            ::= { qos2PortTable 4 } 
            
--xxx.100.27.1.13.5
qos2PortPolicy OBJECT-TYPE
    SYNTAX  DisplayString
            MAX-ACCESS  read-create
            STATUS  current
            DESCRIPTION
                "The corresponding CLI:service-policy input WORD."
            ::= { qos2PortTable 5 }             

--xxx.100.27.1.13.6
qos2PortQueueBandwidth OBJECT-TYPE
    SYNTAX  DisplayString
            MAX-ACCESS  read-create
            STATUS  current
            DESCRIPTION
                "The corresponding CLI:mls qos queue {<queue id>} bandwidth {<MinBandwidth> <MaxBandwidth>}."  
            ::= { qos2PortTable 6 } 

--xxx.100.27.1.13.7
qos2PortQueueAlgorithm OBJECT-TYPE
    SYNTAX  INTEGER
            	{
               		sp(0),
               		wdrr(1),
               		wrr(2)               		
            	}
    	    MAX-ACCESS  read-create
    	    STATUS  current
            DESCRIPTION
                "The corresponding CLI:mls qos queue algorithm {sp |wdrr |wrr }."
            ::= { qos2PortTable 7 } 
            
--xxx.100.27.1.13.8
qos2PortQueueWdrr OBJECT-TYPE
    SYNTAX  DisplayString
            MAX-ACCESS  read-create
            STATUS  current
            DESCRIPTION
                "The corresponding CLI:mls qos queue wdrr weight {<Queue1 bandwidth> <Queue2 bandwidth> <Queue3 bandwidth> <Queue4 bandwidth> <Queue5 bandwidth> <Queue6 bandwidth> <Queue7 bandwidth> <Queue8 bandwidth>}."
            ::= { qos2PortTable 8 }   
            
--xxx.100.27.1.13.9
qos2PortQueueWrr OBJECT-TYPE
    SYNTAX  DisplayString
            MAX-ACCESS  read-create
            STATUS  current
            DESCRIPTION
                "The corresponding CLI:mls qos queue wrr weight {<Queue1 weight> <Queue2 weight> <Queue3 weight> <Queue4 weight> <Queue5 weight> <Queue6 weight> <Queue7 weight> <Queue8 weight>}." 
            ::= { qos2PortTable 9 }                        

--xxx.100.27.1.13.10
qos2PortStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2PortTable 10 }   

                                            
--********************************************************************************************************    
--xxx.100.27.1.14
qos2ClassMapTable         	    OBJECT IDENTIFIER ::= { qos2 14 } 

--xxx.100.27.1.14.1
        qos2ClassMapName OBJECT-TYPE
            SYNTAX  DisplayString (SIZE(1..64))
            MAX-ACCESS  read-create
            STATUS  current
            DESCRIPTION
                "classmap name"
            ::= { qos2ClassMapTable 1}

--xxx.100.27.1.14.2
        qos2ClassMapType OBJECT-TYPE
            SYNTAX  INTEGER
            	{
            	    configurClassMap(0),
            	    accessGroup(1),
               	    dscp(2),
               	    v6dscp(5),
               	    ippre(3),
               	    v6AccessGroup(8),
               	    v6Flow(7),
               	    vlan(4), 
               	    cos(9),
               	    exp(10)
            	}
            MAX-ACCESS  read-create
            STATUS  current
            DESCRIPTION
                "0 class-map <class-map-name>,index is classmapname;
		1 match access-group <acl-index-or-name>,need qos2ClassMapAccessGroup cooperation;
		2 match ip dscp <dscp-list>,need qos2ClassMapDscp cooperation;
		3 match ip precedence <ip-precedence-list>,need qos2ClassMapIpPre cooperation;
		4 match vlan <vlan-list>,need qos2ClassMapVlan cooperation;
		5 match ipv6 dscp <dscp-list>,need qos2ClassMapV6Dscp cooperation;
		7 match ipv6 flowlabel,need qos2ClassMapV6Flow cooperation;
		8 match ipv6 access-group,need qos2ClassMapV6AccGroup cooperation;
		9 match cos,need qos2ClassCos cooperation;
	        10 match exp <exp-list>,need qos2ClassMapExp cooperation."
            ::= { qos2ClassMapTable  2 }

--xxx.100.27.1.14.3
        qos2ClassMapAccessGroup OBJECT-TYPE
            SYNTAX  DisplayString
            MAX-ACCESS  read-create
            STATUS  current
            DESCRIPTION
                "Match specify access-group (name or number). 
                This object be configured only if qosClassMapType  
                in the same row is accessGroup(1)."
            ::= { qos2ClassMapTable 3 }
            
--xxx.100.27.1.14.4
        qos2ClassMapDscp OBJECT-TYPE
            SYNTAX  DisplayString
            MAX-ACCESS  read-create
            STATUS  current
            DESCRIPTION
                "Match specify Dscp.
                This object be configured only if qosClassMapType 
                in the same row is dscp(2)."
            ::= { qos2ClassMapTable  4 }  
                      
--xxx.100.27.1.14.5
        qos2ClassMapV6Dscp OBJECT-TYPE
            SYNTAX  DisplayString
            MAX-ACCESS  read-create
            STATUS  current
            DESCRIPTION
                "Match specify ipv6 Dscp.
                This object be configured only if qosClassMapType 
                in the same row is v6dscp(5)."
            ::= { qos2ClassMapTable  5 } 
            
--xxx.100.27.1.14.6
        qos2ClassMapIpPre OBJECT-TYPE
            SYNTAX  DisplayString
            MAX-ACCESS  read-create
            STATUS  current
            DESCRIPTION
                "Match specify Ip Precedence.
                This object be configured only if qosClassMapType 
                in the same row is ippre(3)."
            ::= { qos2ClassMapTable  6 } 
            
--xxx.100.27.1.14.7
        qos2ClassMapV6AccGroup OBJECT-TYPE
            SYNTAX  DisplayString
            MAX-ACCESS  read-create
            STATUS  current
            DESCRIPTION
                "Match specify Ipv6 Access-Group.
                This object be configured only if qosClassMapType  
                in the same row is v6AccessGroup(8)."
            ::= { qos2ClassMapTable  7 } 
            
--xxx.100.27.1.14.8
        qos2ClassMapV6Flow OBJECT-TYPE
            SYNTAX  DisplayString
            MAX-ACCESS  read-create
            STATUS  current
            DESCRIPTION
                "Match specify Ipv6 Flowlabel.
                This object be configured only if qosClassMapType  
                in the same row is v6Flow(6)."
            ::= { qos2ClassMapTable  8 } 
            
--xxx.100.27.1.14.9
        qos2ClassMapVlan OBJECT-TYPE
            SYNTAX  DisplayString
            MAX-ACCESS  read-create
            STATUS  current
            DESCRIPTION
                "Match specify Vlan list . At most 8 vlan id.
                This object be configured only if qosClassMapType  
                in the same row is vlan(4)."
            ::= { qos2ClassMapTable  9 } 
     
--xxx.100.27.1.1410
        qos2ClassMapCos OBJECT-TYPE
            SYNTAX  DisplayString
            MAX-ACCESS  read-create
            STATUS  current
            DESCRIPTION
                "Match specify Cos .
                This object be configured only if qosClassMapType  
                in the same row is cos(9)."
            ::= { qos2ClassMapTable 10 }

--xxx.100.27.1.14.11
        qos2ClassMapExp  OBJECT-TYPE
            SYNTAX  DisplayString
            MAX-ACCESS  read-create
            STATUS  current
            DESCRIPTION
                "Match specify MPLS EXP.
                This object be configured only if qosClassMapType  
                in the same row is Exp(10)."
            ::= { qos2ClassMapTable 11 }  	        
               
--xxx.100.27.1.14.12
        qos2ClassMapStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2ClassMapTable 12 } 
            
--********************************************************************************************************

--xxx.100.27.1.15
qos2PolicyTable         	    OBJECT IDENTIFIER ::= { qos2 15 } 

--xxx.100.27.1.15.1
        qos2PolicyName OBJECT-TYPE
            SYNTAX  DisplayString (SIZE(1..64))
            MAX-ACCESS  read-create
            STATUS  current
            DESCRIPTION
                "QoS Policy name"
            ::= { qos2PolicyTable 1 }

--xxx.100.27.1.15.2
        qos2PolicyClassMap OBJECT-TYPE
            SYNTAX  DisplayString (SIZE(1..64))
            MAX-ACCESS  read-create
            STATUS  current
            DESCRIPTION
                "Specify the classmap name.After a policy map is created, it can be associated to a class.
                So, if you want the class map to match the policy map,please setting the qosPolicyType to 1,and then
                setting the qosPolicyStatus to 1 ."
            ::= { qos2PolicyTable 2 }
            
--xxx.100.27.1.15.3
        qos2PolicyInsertClassMap OBJECT-TYPE
            SYNTAX  DisplayString (SIZE(1..64))
            MAX-ACCESS  read-create
            STATUS  current
            DESCRIPTION
                "Specify the position of classmap name."
            ::= { qos2PolicyTable 3 }            

--xxx.100.27.1.15.4
        qos2PolicyType OBJECT-TYPE
            SYNTAX  INTEGER            	
            	{
            	    	policymap(0),
            	    	matchclassmap(1),
            	    	threeColor(2),
               		aggregatePolicer(3), 
               		accounting(4)               		        	
            	}
            MAX-ACCESS  read-create
            STATUS  current
            DESCRIPTION
                "the relation between qosPolicyType and CLI:
		0  policy-map <policy-map-name>;
		1  class <class-map-name>;
		2  policy <bits_per_second> <normal_burst_bytes> [pir <peak_rate_bps>] |  <maximum_burst_bytes> [{conform-action ACTION | exceed-action ACTION | violate-action ACTION }];
		3  policy aggregate <aggregate-policer-name>; 
		4  accounting. " 
            ::= { qos2PolicyTable 4 }
            
--xxx.100.27.1.15.5
        qos2PolicyCIRKbps OBJECT-TYPE
            SYNTAX  INTEGER(1..10000000)
            MAX-ACCESS  read-create
            STATUS  current
            DESCRIPTION
                "CIR(Committed Information Rate) Kbits per second <1-10000000>."
            ::= { qos2PolicyTable 5 }            

--xxx.100.27.1.15.6
        qos2PolicyCBSKbps OBJECT-TYPE
            SYNTAX  INTEGER(1..1000000)
            MAX-ACCESS  read-create
            STATUS  current
            DESCRIPTION
                "CBS(Committed Burst Size) Kbits per second <1-1000000>."
            ::= { qos2PolicyTable 6 }
            
--xxx.100.27.1.15.7
        qos2PolicyPBSKbps OBJECT-TYPE
            SYNTAX  INTEGER(1..1000000)
            MAX-ACCESS  read-create
            STATUS  current
            DESCRIPTION
                "PBS(Peak Burst Size) Kbits per second <1-1000000>."
            ::= { qos2PolicyTable 7 }
            
--xxx.100.27.1.15.8
        qos2PolicyPIRKbps OBJECT-TYPE
            SYNTAX  INTEGER(1..10000000)
            MAX-ACCESS  read-create
            STATUS  current
            DESCRIPTION
                "PIR(Peak Information Rate) Kbits per second <1-10000000>."
            ::= { qos2PolicyTable 8 }                                                                         

--xxx.100.27.1.15.9
        qos2PolicyConformActionChange OBJECT-TYPE
            SYNTAX  INTEGER
            	{
            	        transmit(0),
            	    	drop(1),
               		set-dscp-transmit(2), 
               		set-prec-transmit(3),
  			set-cos-transmit(4),
			set-internal-priority(5), 
			set-drop-Precedence(6)        	
            	}
            MAX-ACCESS  read-create
            STATUS  current
            DESCRIPTION
                "transmit(0): means send packets without any change;
		drop(1): means drop packets;
		set-dscp-transmit(2): send packets and remark dscp value;
		set-prec-transmit(3): send packets and remark ip-precedence value;
		set-cos-transmit(4): send packets and remark cos value;
		set-internal-priority(5):send packets and remark internal-priority value ;
		set-drop-Precedence(6): send packets and remark drop-precedence value."               
            ::= { qos2PolicyTable 9 }            
            
--xxx.100.27.1.15.10
        qos2PolicyConformActionChangeValue OBJECT-TYPE
            SYNTAX  INTEGER (0..63) 
            MAX-ACCESS  read-create
            STATUS  current
            DESCRIPTION
                "If action is set-dscp-transmit(2),the value is between 0-63;
                 else if action is set-prec-transmit(3),the value is between 0-7;
                 else if action is set-cos-transmit(4),the value is between 0-7;
                 else if action is set-internal-priority(5),the value is between 0-7;
                 else if action is set-drop-Precedence(6),the value is between 0-2."
            ::= { qos2PolicyTable 10 }   
            
--xxx.100.27.1.15.11
        qos2PolicyExceedActionChange OBJECT-TYPE
            SYNTAX  INTEGER
            	{
            	        transmit(0),
            	    	drop(1),
               		set-dscp-transmit(2), 
               		set-prec-transmit(3),
  			set-cos-transmit(4),
			set-internal-priority(5), 
			set-drop-Precedence(6)        	
            	}
            MAX-ACCESS  read-create
            STATUS  current
            DESCRIPTION
                "transmit(0): means send packets without any change;
		drop(1): means drop packets;
		set-dscp-transmit(2): send packets and remark dscp value;
		set-prec-transmit(3): send packets and remark ip-precedence value;
		set-cos-transmit(4): send packets and remark cos value;
		set-internal-priority(5):send packets and remark internal-priority value ;
		set-drop-Precedence(6): send packets and remark drop-precedence value."               
            ::= { qos2PolicyTable 11 }            
            
--xxx.100.27.1.15.12
        qos2PolicyExceedActionChangeValue OBJECT-TYPE
            SYNTAX  INTEGER (0..63) 
            MAX-ACCESS  read-create
            STATUS  current
            DESCRIPTION
                "If action is set-dscp-transmit(2),the value is between 0-63;
                 else if action is set-prec-transmit(3),the value is between 0-7;
                 else if action is set-cos-transmit(4),the value is between 0-7;
                 else if action is set-internal-priority(5),the value is between 0-7;
                 else if action is set-drop-Precedence(6),the value is between 0-2."
            ::= { qos2PolicyTable 12 }  
            
--xxx.100.27.1.15.13
        qos2PolicyViolateActionChange OBJECT-TYPE
            SYNTAX  INTEGER
            	{
            	        transmit(0),
            	    	drop(1),
               		set-dscp-transmit(2), 
               		set-prec-transmit(3),
  			set-cos-transmit(4),
			set-internal-priority(5), 
			set-drop-Precedence(6)        	
            	}
            MAX-ACCESS  read-create
            STATUS  current
            DESCRIPTION
                "transmit(0): means send packets without any change;
		drop(1): means drop packets;
		set-dscp-transmit(2): send packets and remark dscp value;
		set-prec-transmit(3): send packets and remark ip-precedence value;
		set-cos-transmit(4): send packets and remark cos value;
		set-internal-priority(5):send packets and remark internal-priority value ;
		set-drop-Precedence(6): send packets and remark drop-precedence value."               
            ::= { qos2PolicyTable 13 }            
            
--xxx.100.27.1.15.14
        qos2PolicyViolateActionChangeValue OBJECT-TYPE
            SYNTAX  INTEGER (0..63) 
            MAX-ACCESS  read-create
            STATUS  current
            DESCRIPTION
                "If action is set-dscp-transmit(2),the value is between 0-63;
                 else if action is set-prec-transmit(3),the value is between 0-7;
                 else if action is set-cos-transmit(4),the value is between 0-7;
                 else if action is set-internal-priority(5),the value is between 0-7;
                 else if action is set-drop-Precedence(6),the value is between 0-2."
            ::= { qos2PolicyTable 14 }                                                    

--xxx.100.27.1.15.15
        qos2PolicyAggregatePolicer OBJECT-TYPE
            SYNTAX  DisplayString
            MAX-ACCESS  read-create
            STATUS  current
            DESCRIPTION
                "aggregate-policer-name.
                This object be configured only if qosPolicyType 
                in the same row is aggregatePolicer(3)."
            ::= { qos2PolicyTable 15 }   

--xxx.100.27.1.15.16
        qos2PolicyStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2PolicyTable 16 } 

--******************************************************************************************************** 


--********************************************************************************************************                        
--xxx.100.27.1.16
qos2SetTable         	    OBJECT IDENTIFIER ::= { qos2 16 } 

--xxx.100.27.1.16.1
        qos2SetPolicyMapName OBJECT-TYPE
            SYNTAX  DisplayString (SIZE(1..32))
            MAX-ACCESS  read-create
            STATUS  current
            DESCRIPTION
                "QoS Policy name."
            ::= { qos2SetTable 1 }

--xxx.100.27.1.16.2
        qos2SetClassMapName OBJECT-TYPE
            SYNTAX  DisplayString (SIZE(1..32))
            MAX-ACCESS  read-create
            STATUS  current
            DESCRIPTION
                "QoS class map name."
            ::= { qos2SetTable 2 }
            
--xxx.100.27.1.16.3
        qos2SetType OBJECT-TYPE
            SYNTAX  INTEGER
            	{
            	    	dscp(1),
               		precedence(2),
                	internal-priority(3),  
                	drop-precedence(4),                	            		
               		nextHop(5),          		
               		v6nextHop(6),
               		cos(7)          	
            	}
            MAX-ACCESS  read-create
            STATUS  current
            DESCRIPTION
                "qos2SetType range:1,2,3,4,5,6
                1   dscp         	Set IP DSCP (DiffServ CodePoints);
                2   precedence   	Set IP precedence;
                3   internal-priority   Set internal-priority;
                4   drop-precedence   	Set drop-precedence;
                5   nexthop      	Set IP nexthop;
		6   v6nextHop    	Set IPv6 nexthop;
                7   cos          	Set CoS ."		
            ::= { qos2SetTable 3 } 
            
--xxx.100.27.1.16.4
        qos2SetDscp OBJECT-TYPE
            SYNTAX  INTEGER(0..63)
            MAX-ACCESS  read-create
            STATUS  current
            DESCRIPTION
                "remark dscp for the classified flow."
            ::= { qos2SetTable 4 } 

--xxx.100.27.1.16.5
        qos2SetPrecedence OBJECT-TYPE
            SYNTAX  INTEGER(0..7)
            MAX-ACCESS  read-create
            STATUS  current
            DESCRIPTION
                "remark ip precedence for classified flow."
            ::= { qos2SetTable 5 }
            
--xxx.100.27.1.16.6
        qos2SetInternalPriority OBJECT-TYPE
            SYNTAX  INTEGER(0..7)
            MAX-ACCESS  read-create
            STATUS  current
            DESCRIPTION
                "remark internal priority for classified flow."
            ::= { qos2SetTable 6 }  
            
--xxx.100.27.1.16.7
        qos2SetDropPrecedence OBJECT-TYPE
            SYNTAX  INTEGER(0..2)
            MAX-ACCESS  read-create
            STATUS  current
            DESCRIPTION
                "remark drop precedence for classified flow."
            ::= { qos2SetTable 7 }                       

--xxx.100.27.1.16.8
        qos2SetDefaultPBR OBJECT-TYPE
            SYNTAX  INTEGER(0..1)
            MAX-ACCESS  read-create
            STATUS  current
            DESCRIPTION
                "0:no set default PBR for classified flow;
                 1:set default PBR for classified flow."
            ::= { qos2SetTable 8 } 
            
--xxx.100.27.1.16.9
        qos2SetVrf OBJECT-TYPE
            SYNTAX  INTEGER(0..252)
            MAX-ACCESS  read-create
            STATUS  current
            DESCRIPTION
                "set vrf value for classified flow."
            ::= { qos2SetTable 9 }              
                         
--xxx.100.27.1.16.10
        qos2SetnextHop OBJECT-TYPE
            SYNTAX  IpAddress
            MAX-ACCESS  read-create
            STATUS  current
            DESCRIPTION
                "set nexthop for classified flow."
            ::= { qos2SetTable 10 }                        
            
--xxx.100.11.1.16.11
        qos2Setv6nextHop OBJECT-TYPE
            SYNTAX  DisplayString
            MAX-ACCESS  read-create
            STATUS  current
            DESCRIPTION
                "set IPv6 nexthop for classified flow"
            ::= { qos2SetTable 11 }

--xxx.100.27.1.16.12
        qos2SetCos OBJECT-TYPE
            SYNTAX  INTEGER(0..7)
            MAX-ACCESS  read-create
            STATUS  current
            DESCRIPTION
                "remark cos for classified flow"
            ::= { qos2SetTable 12 } 
                      

--xxx.100.27.1.16.13
        qos2SetStatus OBJECT-TYPE
            SYNTAX  INTEGER
            	    {
               		active(1),
               		destroy(2)
            	    }
            MAX-ACCESS  read-create
            STATUS  current
            DESCRIPTION
                " Setting it to  active(1) to creates an entry,setting it to destroy(2) to destroy an entry."
            ::= { qos2SetTable 13 } 
	                                                                     
--********************************************************************************************************
--******************************************************************************************************** 
-- (xxx.100.28)   mabMgt group

--********************************************************************************************************      

mabOnlineUserTable OBJECT-TYPE
        SYNTAX      SEQUENCE OF mabOnlineUserEntry
        MAX-ACCESS  not-accessible
        STATUS      current
        DESCRIPTION "Show the information of MAB users."
        ::= { mabMgt  1 }

mabOnlineUserEntry OBJECT-TYPE
        SYNTAX  mabOnlineUserEntry
        MAX-ACCESS  not-accessible
        STATUS  current
        DESCRIPTION  ""
        INDEX   { mabOnlineUserIndex }
        ::= { mabOnlineUserTable 1 } 

       mabOnlineUserEntry
        ::= SEQUENCE
            {
            	  mabOnlineUserIndex		INTEGER,
                mabOnlineUserMac		  DisplayString,          
                mabOnlineUserName		DisplayString,	
                mabOnlineUserPort		DisplayString,                                     
                mabOnlineUserState	  DisplayString       
            }
            
mabOnlineUserIndex OBJECT-TYPE
        SYNTAX      INTEGER
        MAX-ACCESS  not-accessible
        STATUS      current
        DESCRIPTION "The index of MAB user."
        ::= { mabOnlineUserEntry 1 }
        
mabOnlineUserMac OBJECT-TYPE
        SYNTAX      DisplayString (SIZE(17))
        MAX-ACCESS  read-only
        STATUS      current
        DESCRIPTION "The mac of MAB user."
        ::= { mabOnlineUserEntry 2 }  
        
mabOnlineUserName OBJECT-TYPE
        SYNTAX      DisplayString (SIZE(1..32))
        MAX-ACCESS  read-only
        STATUS      current
        DESCRIPTION "The username of MAB user."
        ::= { mabOnlineUserEntry 3 }  
        
mabOnlineUserState OBJECT-TYPE
        SYNTAX      DisplayString (SIZE(1..18))
        MAX-ACCESS  read-only
        STATUS      current
        DESCRIPTION "The state of MAB user."
        ::= { mabOnlineUserEntry 5 }
        
mabOnlineUserPort OBJECT-TYPE
        SYNTAX      DisplayString (SIZE(1..14))
        MAX-ACCESS  read-only
        STATUS      current
        DESCRIPTION "The port for MAB user."
        ::= { mabOnlineUserEntry 4 }  
        
mabSetUserOffline          OBJECT-TYPE
        SYNTAX      DisplayString (SIZE(17))      
        MAX-ACCESS  read-write
        STATUS      current
        DESCRIPTION "The mac of user offline."
        ::= { mabMgt  2 }          
                                       
                 
--trap  
--xxx.101.100 
    antiArpscan  OBJECT 	IDENTIFIER ::= { notifications 100 }
    
--********************************************************************************************************      
       
--xxx.101.100.1   
    prohibitPortOID 			OBJECT IDENTIFIER ::= { antiArpscan 1 }
--xxx.101.100.2   
    recoverPortOID 		OBJECT IDENTIFIER ::= { antiArpscan 2 }
--xxx.101.100.3      
    prohibitIPOID			OBJECT IDENTIFIER ::= { antiArpscan 3 }
--xxx.101.100.4   
    prohibitIPExceedSlimitOID 	OBJECT IDENTIFIER ::= { antiArpscan 4 }
--xxx.101.100.5   
    prohibitIPExceedHlimitOID 	OBJECT IDENTIFIER ::= { antiArpscan 5 }
--xxx.101.100.6   
    recoverIPOID 		OBJECT IDENTIFIER ::= { antiArpscan 6 }
--xxx.101.100.7   
    ipAddress 			OBJECT IDENTIFIER ::= { antiArpscan 7 }        
                          
--********************************************************************************************************  
--********************************************************************************************************  
--trap  
--xxx.101.101 
    fan  OBJECT 	IDENTIFIER ::= { notifications 101 }
    
--******************************************************************************************************** 
--xxx.101.101.1
fanAbnormalOID			OBJECT IDENTIFIER ::= { fan 1 }
--xxx.101.101.2  
fanNormalOID			 	OBJECT IDENTIFIER ::= { fan 2 } 
--xxx.101.101.3
fanInsertOID 				OBJECT IDENTIFIER ::= { fan 3 }
--xxx.101.101.4
fanPullOutOID 			OBJECT IDENTIFIER ::= { fan 4 }

--********************************************************************************************************  
--trap  
--xxx.101.102 
    power  OBJECT 	IDENTIFIER ::= { notifications 102 }
    
--******************************************************************************************************** 
--xxx.101.102.1
powerAbnormalOID 		OBJECT IDENTIFIER ::= { power 1 }
--xxx.101.102.2    
powerNormalOID 			OBJECT IDENTIFIER ::= { power 2 }
--xxx.101.102.3
powerInsertOID 			OBJECT IDENTIFIER ::= { power 3 }
--xxx.101.102.4			
powerPullOutOID			OBJECT IDENTIFIER ::= { power 4 }  

--********************************************************************************************************  
--trap  
--xxx.101.103 
    slotTemperature  OBJECT 	IDENTIFIER ::= { notifications 103 }
    
--******************************************************************************************************** 
--xxx.101.103.1
slotTemperatureHigherOID 	OBJECT IDENTIFIER ::= { slotTemperature 1 } 
--xxx.101.103.2  
slotTemperatureLowerOID		OBJECT IDENTIFIER ::= { slotTemperature 2 } 

--********************************************************************************************************  
--trap  
--xxx.101.103 
--    slotTemperature  OBJECT 	IDENTIFIER ::= { notifications 103 }
    
--******************************************************************************************************** 

--********************************************************************************************************  
--trap  
--xxx.101.104 
    dhcpsnooping  OBJECT 	IDENTIFIER ::= { notifications 104 }
    
--******************************************************************************************************** 
--xxx.101.104.1   
    shutdownPort 					OBJECT IDENTIFIER ::= { dhcpsnooping 1 }
--xxx.101.104.2   
    noShutdownPort 				OBJECT IDENTIFIER ::= { dhcpsnooping 2 }
--xxx.101.104.3      
    addBlackhole					OBJECT IDENTIFIER ::= { dhcpsnooping 3 }
--xxx.101.104.4   
    delBlackhole 					OBJECT IDENTIFIER ::= { dhcpsnooping 4 }
--********************************************************************************************************     

--trap  
--xxx.101.105 
    rateViolation  OBJECT 	IDENTIFIER ::= { notifications 105 }
    
--******************************************************************************************************** 
--xxx.101.105.1
rateViolationShutdownPort			OBJECT IDENTIFIER ::= { rateViolation 1 }
--xxx.101.105.2  
rateViolationNoShutdownPort		OBJECT IDENTIFIER ::= { rateViolation 2 } 
--******************************************************************************************************** 

--trap  
--xxx.101.106 
    portGroup  OBJECT 	IDENTIFIER ::= { notifications 106 }    
--******************************************************************************************************** 
--xxx.101.106.1
    portGroupCreate		OBJECT IDENTIFIER ::= { portGroup 1 }
--xxx.101.106.2  
    portGroupDelete		OBJECT IDENTIFIER ::= { portGroup 2 } 
--xxx.101.106.3  
    portGroupUpdate		OBJECT IDENTIFIER ::= { portGroup 2 } 
--******************************************************************************************************** 
                                                  
END

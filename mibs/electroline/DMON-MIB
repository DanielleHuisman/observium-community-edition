DMON-MIB DEFINITIONS ::= BEGIN

IMPORTS
        enterprises
                FROM SNMPv2-SMI
        MODULE-COMPLIANCE
                FROM SNMPv2-CONF
        electrolineCoRoot
                FROM ELECTROLINE-GLOBAL-REG;


ModulationType ::= TEXTUAL-CONVENTION
       STATUS          current
       DESCRIPTION
            ""
       SYNTAX          INTEGER {
         unknown(-1),
         qam16(0),
         qam64(1),
         qam256(2),
         qam1024(3),
         qam32(4),
         qam128(5),
         qpsk(6)
       }
                
                


dmonMib                   OBJECT IDENTIFIER ::= { electrolineCoRoot 999999 }
dmonPhyGroup              OBJECT IDENTIFIER ::= { dmonMib 1 }
dmonCommonGroup           OBJECT IDENTIFIER ::= { dmonMib 2 }
dmonDsgMcastRedirectGroup OBJECT IDENTIFIER ::= { dmonMib 3 } 

END

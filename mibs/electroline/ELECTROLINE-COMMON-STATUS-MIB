--**************************************************************************
--                                                                          
--    Copyright 2014 Electroline Equipment Inc.                                   
--    All Rights Reserved                                                                          
--                                                                          
--                                                                          
--                                                                          
--**************************************************************************
--    Filename: ELECTROLINE-COMMON-CONFIG.mib
--    Author:   AlainLeclerc
--    Creation Date: 2014-01-14
--**************************************************************************
--    Description:
--
--	This file contains the MIB definition of the Status branch 
--  for the electroline products.
--		
--**************************************************************************
--    Revision History:
--    2014.01.14    Alain Leclerc      First Release
--**************************************************************************

ELECTROLINE-COMMON-STATUS-MIB DEFINITIONS ::= BEGIN

IMPORTS
    MODULE-IDENTITY,OBJECT-TYPE,Integer32 FROM SNMPv2-SMI
    RowStatus  FROM SNMPv2-TC        
    commonStatus, electrolineCommon FROM ELECTROLINE-COMMON-ROOT-MIB
    commonPhysAddress, commonLogicalID	FROM SCTE-HMS-COMMON-MIB
    NetworkAddress FROM RFC1155-SMI
    DisplayString  FROM RFC1213-MIB
    InetAddress,
    InetAddressType
    	FROM INET-ADDRESS-MIB;     -- RFC 4001
    

-- **************************************************************************
-- * ELECTROLINE MISC. Statuses
-- * 
-- **************************************************************************
internalTemperature  OBJECT-TYPE
     SYNTAX INTEGER (-60..130)
     ACCESS read-only
     STATUS current
     DESCRIPTION 
          "Measured temperature inside the NE's case/housing.
          Units degrees Celsius."
     ::= { commonStatus 1 }

inetNetworkAddressType OBJECT-TYPE
        SYNTAX      InetAddressType
        MAX-ACCESS  read-only
        STATUS      current
        DESCRIPTION
            "The address type of DHT's RF interface IP address assigned by the DHCP server.
             Values: unknown(0), ipv4(1), ipv6(2), ipv4z(3), ipv6z(4), dns(16)
	     The update of this object is coherent to cfgHmsEmsAddressIP object."
	::= { commonStatus 2 }
		     
inetNetworkAddress OBJECT-TYPE
	SYNTAX InetAddress
	MAX-ACCESS read-only
	STATUS current
	DESCRIPTION
		"This is the device RF interface IP address assigned by the DHCP Server."
	::= { commonStatus 3 }


inetMonitoringNetworkAddressType OBJECT-TYPE
        SYNTAX      InetAddressType
        MAX-ACCESS  read-only
        STATUS      current
        DESCRIPTION
            "The address type of DHT's RF interface IP address assigned by the DHCP server
	    as monitoring interface in DualIp mode.
             Values: unknown(0), ipv4(1), ipv6(2), ipv4z(3), ipv6z(4), dns(16)
	     The update of this object is coherent to cfgHmsEmsAddressIP object."
	::= { commonStatus 4 }
		     
inetMonitoringNetworkAddress OBJECT-TYPE
	SYNTAX InetAddress
	MAX-ACCESS read-only
	STATUS current
	DESCRIPTION
		"This is the DHT's RF interface IP address assigned by the DHCP Server
		as monitoring interface in DualIp mode."
	::= { commonStatus 5 }

END

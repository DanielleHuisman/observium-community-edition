--**************************************************************************
--                                                                          
--    Copyright 2004 Electroline Equipment Inc                                   
--    All Rights Reserved                                                                          
--                                                                          
--                                                                          
--                                                                          
--**************************************************************************
--    Filename: ELECTROLINE-DHT-REMOTE-SWITCH.mib
--    Author:   Nathaniel Mercure
--    Creation Date: 2004.12.09
--
--**************************************************************************
--    Description:
--
--		This MIB contains all controls for a remote switch
--		
--**************************************************************************
--    Revision History:
--	  2004.12.09	Nathaniel Mercure   	First Draft						 
--	  2004.12.15	Carlene Gardner 	   	Linguistic revision						
--**************************************************************************

ELECTROLINE-DHT-REMOTE-SWITCH-MIB DEFINITIONS ::= BEGIN

IMPORTS
    MODULE-IDENTITY,
    OBJECT-TYPE,
    Integer32, Counter32
        FROM SNMPv2-SMI
    TruthValue
        FROM SNMPv2-TC          
    dhtExtensionsMibObjects       
        FROM ELECTROLINE-DHT-EXTENSIONS-MIB;
                    
dhtRemoteSwitchMib MODULE-IDENTITY
    LAST-UPDATED "200412100000Z"
    ORGANIZATION "Electroline Equipment Inc"
    CONTACT-INFO
        "Electroline Equipment Inc.
         E-mail: support@electroline.com
         Telephone:
         	(514) 374-6335 
         	(800)-461-3344 (Toll-free - North America)
        "
    DESCRIPTION
        "This set of objects controls a remote switch that may be present and connected to the DHT.
        This file includes a control object, and status objecy and a failsafe timer.
        "
    REVISION      "200412100000Z"
    DESCRIPTION
            "Initial version of this MIB module."
    ::= { dhtExtensionsMibObjects 11 }
                
--dhtRemoteSwitch MIb Objs
dhtRemoteSwitchObjects 		OBJECT IDENTIFIER ::= { dhtRemoteSwitchMib 1 } 

--Remote Switch Objs
dhtRemoteSwitchPresence OBJECT-TYPE
     SYNTAX TruthValue
     MAX-ACCESS read-only
     STATUS current    
     DESCRIPTION
		"Defines if a switch is connected to the DHT. 
	
			True(1) = Remote switch present.
			False(2) = Remote switch not present.
		"
 		   
     ::= { dhtRemoteSwitchObjects 1 }
     
dhtRemoteSwitchManagement OBJECT IDENTIFIER ::= { dhtRemoteSwitchObjects 11 }

--RemoteSwitchManagement Objs
	dhtRemoteSwitchControl OBJECT-TYPE
		SYNTAX INTEGER { off(1), on(2) }
		MAX-ACCESS read-write
		STATUS current    
		DESCRIPTION
			"Equipment control
		 	1 = Turns the switch to the OFF position
		 	2 = Turns the switch to the ON position
		
			Default: Off(1)
			"
	::= { dhtRemoteSwitchManagement 1 }    
     
     dhtRemoteSwitchAutoStopTimer OBJECT-TYPE
	     SYNTAX INTEGER  (20..120)
	     MAX-ACCESS read-write
	     STATUS current    
	     DESCRIPTION
		   "Defines the maximum ON time in minutes for the remote switch. 
			Reset internal timer every time the switch is turned to the ON position
			with dhtRemoteSwitchControl object. This object returns only the defined 
			length of the period, not the current number of minutes remaining in the 
			counter value. The value of this object is stored in non-volatile memory
		
			Default=30 min
			"

     ::= { dhtRemoteSwitchManagement 2 } 
     
     dhtRemoteSwitchStatus OBJECT-TYPE
	     SYNTAX INTEGER { on(1),off(2), mismatch(3),timeout(4) }		
	     MAX-ACCESS read-only
	     STATUS current    
	     DESCRIPTION
		   "Returns values related to the switch's status signal.

		 	1 = Switch is ON (as per switch status signal)
		 	2 = Switch is OFF (as per switch status signal)
			3 = A status mismatch occurred between the switch's control pin and 
			    the status pin  (reference: dhtRemoteSwitchControl). 
			    If a mismatch occurs, the DHT turns the switch OFF but the 
			    dhtRemoteSwitchControl  object reports its user-defined value. The 
			    value of the dhtRemoteSwitchStatus object is latched.
			    The dhtRemoteSwitchStatus object reverts to its normal operation (On/Off) 
			    when a value is written to the dhtRemoteSwitchControl object.
			    Also, if a mismatch occurs, the failsafe timer stops.  
			      
			4 = The failsafe timer timed out. The switch turns OFF.
			    dhtRemoteSwitchControl is set to Off(1) position.
			    This object reverts to its normal operation (On/Off)
		     	when a value is written to the dhtRemoteSwitchControl object."		

     ::= { dhtRemoteSwitchManagement 3 }   
     
	dhtRemoteSwitchOnTime OBJECT-TYPE
		SYNTAX Counter32 
		MAX-ACCESS read-write
		STATUS current    
		DESCRIPTION
			"Counts the amount of time in minutes the switch is ON. Writing 0 resets
			the counter. This object is set to 0 every time the DHT reboots (power cycle, 
			sleep mode, reset).
		
			The value of this item *is not* stored in non-volatile memory."  
			
	::= { dhtRemoteSwitchManagement 4 }     
     
END

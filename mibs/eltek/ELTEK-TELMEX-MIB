-- ----------------------------------------------------------
-- Eltek Power System
-- Telmex MIB
-- ----------------------------------------------------------
-- $Revision:1$
-- $Author: knskno$
-- $Archive: Documents/EltekTelmex_branch13.mib$
-- $Date: 22. august 2019 09:34:01$

ELTEK-TELMEX-MIB DEFINITIONS ::= BEGIN

IMPORTS
	NOTIFICATION-TYPE, MODULE-IDENTITY, enterprises
		FROM SNMPv2-SMI
	eltek
		FROM ELTEK-COMMON-MIB;


telmex               OBJECT IDENTIFIER ::= { eltek 13 }
eltekTraps           OBJECT IDENTIFIER ::= { telmex 1 }

mainsFailAlarmOn  NOTIFICATION-TYPE
	STATUS     current
	DESCRIPTION 
		"Falla de CA (alarma)"
	--#SUMMARY "Falla de CA (alarma)"
	--#ARGUMENTS { }
	--#SEVERITY MAJOR
	--#STATE OPERATIONAL
	::= { eltekTraps 1 }

mainsFailAlarmOff  NOTIFICATION-TYPE
	STATUS     current
	DESCRIPTION 
		"Falla de CA (normal)"
	--#SUMMARY "Falla de CA (normal)"
	--#ARGUMENTS { }
	--#SEVERITY CLEARED
	--#STATE OPERATIONAL
	::= { eltekTraps 2 }

batteryVoltageLowAlarmOn  NOTIFICATION-TYPE
	STATUS     current
	DESCRIPTION 
		"BAJO VOLTAJE CD (alarma)"
	--#SUMMARY "BAJO VOLTAJE CD (alarma)"
	--#ARGUMENTS { }
	--#SEVERITY MAJOR
	--#STATE OPERATIONAL
	::= { eltekTraps 3 }

batteryVoltageLowAlarmOff  NOTIFICATION-TYPE
	STATUS     current
	DESCRIPTION 
		"BAJO VOLTAJE CD (normal)"
	--#SUMMARY "BAJO VOLTAJE CD (normal)"
	--#ARGUMENTS { }
	--#SEVERITY CLEARED
	--#STATE OPERATIONAL
	::= { eltekTraps 4 }

batteryVoltageHighAlarmOn  NOTIFICATION-TYPE
	STATUS     current
	DESCRIPTION 
		"ALTO VOLTAJE CD (alarma)"
	--#SUMMARY "ALTO VOLTAJE CD (alarma)"
	--#ARGUMENTS { }
	--#SEVERITY MAJOR
	--#STATE OPERATIONAL
	::= { eltekTraps 5 }

batteryVoltageHighAlarmOff  NOTIFICATION-TYPE
	STATUS     current
	DESCRIPTION 
		"ALTO VOLTAJE CD (normal)"
	--#SUMMARY "ALTO VOLTAJE CD (normal)"
	--#ARGUMENTS { }
	--#SEVERITY CLEARED
	--#STATE OPERATIONAL
	::= { eltekTraps 6 }

rectifierErrorAlarmOn  NOTIFICATION-TYPE
	STATUS     current
	DESCRIPTION 
		"Falla de Rectificador Urgente (alarma)"
	--#SUMMARY "Falla de Rectificador Urgente (alarma)"
	--#ARGUMENTS { }
	--#SEVERITY MAJOR
	--#STATE OPERATIONAL
	::= { eltekTraps 7 }

rectifierErrorAlarmOff  NOTIFICATION-TYPE
	STATUS     current
	DESCRIPTION 
		"Falla de Rectificador Urgente (normal)"
	--#SUMMARY "Falla de Rectificador Urgente (normal)"
	--#ARGUMENTS { }
	--#SEVERITY CLEARED
	--#STATE OPERATIONAL
	::= { eltekTraps 8 }

userAlarm1On  NOTIFICATION-TYPE
	STATUS     current
	DESCRIPTION 
		"Falla de SUPRESOR (alarma)"
	--#SUMMARY "Falla de SUPRESOR (alarma)"
	--#ARGUMENTS { }
	--#SEVERITY MAJOR
	--#STATE OPERATIONAL
	::= { eltekTraps 9 }

userAlarm1Off  NOTIFICATION-TYPE
	STATUS     current
	DESCRIPTION 
		"Falla de SUPRESOR (normal)"
	--#SUMMARY "Falla de SUPRESOR (normal)"
	--#ARGUMENTS { }
	--#SEVERITY CLEARED
	--#STATE OPERATIONAL
	::= { eltekTraps 10 }

userAlarm2On  NOTIFICATION-TYPE
	STATUS     current
	DESCRIPTION 
		"PUERTA ABIERTA (alarma)"
	--#SUMMARY "PUERTA ABIERTA (alarma)"
	--#ARGUMENTS { }
	--#SEVERITY MAJOR
	--#STATE OPERATIONAL
	::= { eltekTraps 11 }

userAlarm2Off  NOTIFICATION-TYPE
	STATUS     current
	DESCRIPTION 
		"PUERTA ABIERTA (normal)"
	--#SUMMARY "PUERTA ABIERTA (normal)"
	--#ARGUMENTS { }
	--#SEVERITY CLEARED
	--#STATE OPERATIONAL
	::= { eltekTraps 12 }

userAlarm3On  NOTIFICATION-TYPE
	STATUS     current
	DESCRIPTION 
		"ALTA TEMPERATURA (alarma)"
	--#SUMMARY "ALTA TEMPERATURA (alarma)"
	--#ARGUMENTS { }
	--#SEVERITY MAJOR
	--#STATE OPERATIONAL
	::= { eltekTraps 13 }

userAlarm3Off  NOTIFICATION-TYPE
	STATUS     current
	DESCRIPTION 
		"ALTA TEMPERATURA (normal)"
	--#SUMMARY "ALTA TEMPERATURA (normal)"
	--#ARGUMENTS { }
	--#SEVERITY CLEARED
	--#STATE OPERATIONAL
	::= { eltekTraps 14 }

userAlarm4On  NOTIFICATION-TYPE
	STATUS     current
	DESCRIPTION 
		"Falla de Ventilador (alarma)"
	--#SUMMARY "Falla de Ventilador (alarma)"
	--#ARGUMENTS { }
	--#SEVERITY MAJOR
	--#STATE OPERATIONAL
	::= { eltekTraps 15 }

userAlarm4Off  NOTIFICATION-TYPE
	STATUS     current
	DESCRIPTION 
		"Falla de Ventilador (normal)"
	--#SUMMARY "Falla de Ventilador (normal)"
	--#ARGUMENTS { }
	--#SEVERITY CLEARED
	--#STATE OPERATIONAL
	::= { eltekTraps 16 }

userAlarm5On  NOTIFICATION-TYPE
	STATUS     current
	DESCRIPTION 
		"Falla de Inversor (alarma)"
	--#SUMMARY "Falla de Inversor (alarma)"
	--#ARGUMENTS { }
	--#SEVERITY MAJOR
	--#STATE OPERATIONAL
	::= { eltekTraps 17 }

userAlarm5Off  NOTIFICATION-TYPE
	STATUS     current
	DESCRIPTION 
		"Falla de Inversor (normal)"
	--#SUMMARY "Falla de Inversor (normal)"
	--#ARGUMENTS { }
	--#SEVERITY CLEARED
	--#STATE OPERATIONAL
	::= { eltekTraps 18 }

userAlarm6On  NOTIFICATION-TYPE
	STATUS     current
	DESCRIPTION 
		"GEPE OFF (alarma)"
	--#SUMMARY "GEPE OFF (alarma)"
	--#ARGUMENTS { }
	--#SEVERITY MAJOR
	--#STATE OPERATIONAL
	::= { eltekTraps 19 }

userAlarm6Off  NOTIFICATION-TYPE
	STATUS     current
	DESCRIPTION 
		"GEPE ON (normal)"
	--#SUMMARY "GEPE ON (normal)"
	--#ARGUMENTS { }
	--#SEVERITY CLEARED
	--#STATE OPERATIONAL
	::= { eltekTraps 20 }

loadFuseAlarmOn  NOTIFICATION-TYPE
	STATUS     current
	DESCRIPTION 
		"Interruptor de Distribución (alarma)"
	--#SUMMARY "Interruptor de Distribución (alarma)"
	--#ARGUMENTS { }
	--#SEVERITY MAJOR
	--#STATE OPERATIONAL
	::= { eltekTraps 21 }

loadFuseAlarmOff  NOTIFICATION-TYPE
	STATUS     current
	DESCRIPTION 
		"Interruptor de Distribución (normal)"
	--#SUMMARY "Interruptor de Distribución (normal)"
	--#ARGUMENTS { }
	--#SEVERITY CLEARED
	--#STATE OPERATIONAL
	::= { eltekTraps 22 }

batteryFuseAlarmOn  NOTIFICATION-TYPE
	STATUS     current
	DESCRIPTION 
		"Interruptor de Batería (alarma)"
	--#SUMMARY "Interruptor de Batería (alarma)"
	--#ARGUMENTS { }
	--#SEVERITY MAJOR
	--#STATE OPERATIONAL
	::= { eltekTraps 23 }

batteryFuseAlarmOff  NOTIFICATION-TYPE
	STATUS     current
	DESCRIPTION 
		"Interruptor de Batería (normal)"
	--#SUMMARY "Interruptor de Batería (normal)"
	--#ARGUMENTS { }
	--#SEVERITY CLEARED
	--#STATE OPERATIONAL
	::= { eltekTraps 24 }


END


-- This MIB was created using NuDesign Team's Visual MIBuilder (Ver 4.4).

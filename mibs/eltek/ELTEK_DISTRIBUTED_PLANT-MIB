-- Eltek MIB for ELTEK Distributed Control System Power plant designs
-- $Revision:   1.5  $
-- $Author:   hajo  $
-- $Archive:   V:/PVCS_DB1/archives/WebPower Distributed (2.1)/mibs/Eltek_DistPowerPlant_branch8.mib-arc  $    
-- $Date:   Aug 08 2006 10:18:04  $  

ELTEK_DISTRIBUTED_PLANT-MIB DEFINITIONS ::= BEGIN

IMPORTS
   NOTIFICATION-TYPE, OBJECT-TYPE, MODULE-IDENTITY, 
   mib-2, enterprises, Integer32
      FROM SNMPv2-SMI
   NOTIFICATION-GROUP
      FROM SNMPv2-CONF
   DisplayString
      FROM SNMPv2-TC
   eltek
      FROM ELTEK-COMMON-MIB;


-- Aeongold branch will be 1
-- AL175    branch will be 2
-- AL6000      branch will be 3
-- Webpower proto branch will be 4
-- Smartpack      branch will be 5
-- Nextel Smartpack  branch will be 6
-- ELTEK Common     branch will be 7
-- ELTEK Distributed  branch will be 8

eltekDistributedPlant  OBJECT IDENTIFIER ::= { eltek 8 }


-- This branch contains OIDs for configuration of the Smartpack Control System's
-- basic data and settings

controlSystem        OBJECT IDENTIFIER ::= { eltekDistributedPlant 1 }

systemTime           OBJECT IDENTIFIER ::= { controlSystem 1 }

systemTimeTime  OBJECT-TYPE
   SYNTAX     DisplayString (SIZE(0..255))
   MAX-ACCESS read-only
   STATUS     current
   DESCRIPTION 
      "The system date and time. Used for event timestamps and logging"
   ::= { systemTime 1 }

systemInfoRefresh  OBJECT-TYPE
   SYNTAX     INTEGER {
      pushbutton (0),
      refreshdata (1)
   }
   MAX-ACCESS read-write
   STATUS     current
   DESCRIPTION 
      "This object will re-initialize the agent, updating MIB data values."
   ::= { controlSystem 2 }

systemTrapRepeatRate  OBJECT-TYPE
   SYNTAX     Integer32 (0..10)
   MAX-ACCESS read-write
   STATUS     current
   DESCRIPTION 
      "This object sets the repeat rate of any active traps, in seconds.
      Entering 0 (zero) will prevent repeating traps - one trap only will be sent per alarm event."
   ::= { controlSystem 3 }

systemSendOffTrap  OBJECT-TYPE
   SYNTAX     INTEGER {
      off (0),
      on (1)
   }
   MAX-ACCESS read-write
   STATUS     current
   DESCRIPTION 
      "A separate off-trap will be issued when an alarm condition goes off, if this flag is set to 1.
      Entering 0 (zero) will prevent OFF traps from being transmitted."
   ::= { controlSystem 4 }

systemNumOfControlUnits  OBJECT-TYPE
   SYNTAX     Integer32 (0..8)
   MAX-ACCESS read-only
   STATUS     current
   DESCRIPTION 
      "The number of expected system controllers (smartpacks, smartnodes stc.) in a distributed system"
   ::= { controlSystem 5 }

systemControlUnitIndex  OBJECT-TYPE
   SYNTAX     Integer32 (0..7)
   MAX-ACCESS accessible-for-notify
   STATUS     current
   DESCRIPTION 
      "Index used for navigating int the table of 1 to 8 system controller input groups"
   ::= { controlSystem 6 }

systemControlUnitTable  OBJECT-TYPE
   SYNTAX SEQUENCE OF SystemControlUnitEntry
   MAX-ACCESS not-accessible
   STATUS     current
   DESCRIPTION 
      ""
   ::= { controlSystem 7 }

systemControlUnitEntry  OBJECT-TYPE
   SYNTAX   SystemControlUnitEntry
   MAX-ACCESS not-accessible
   STATUS     current
   DESCRIPTION 
      ""
   INDEX { systemControlUnitIndex }
   ::= { systemControlUnitTable 1 }

SystemControlUnitEntry ::= SEQUENCE {
   inputControlUnitID
      Integer32,
   inputUserConfigurable1
      INTEGER,
   inputUserConfigurable2
      INTEGER,
   inputUserConfigurable3
      INTEGER,
   inputUserConfigurable4
      INTEGER,
   inputUserConfigurable5
      INTEGER,
   inputUserConfigurable6
      INTEGER,
   inputUserConfigurable7
      INTEGER,
   inputUserConfigurable8
      INTEGER,
   inputUserConfigurable9
      INTEGER,
   inputUserConfigurable10
      INTEGER
}

inputControlUnitID  OBJECT-TYPE
   SYNTAX     Integer32 (1..8)
   MAX-ACCESS read-only
   STATUS     current
   DESCRIPTION 
      " "
   ::= { systemControlUnitEntry 1 }

inputUserConfigurable1  OBJECT-TYPE
   SYNTAX     INTEGER {
      normal (0),
      alarm (1)
   }
   MAX-ACCESS read-only
   STATUS     current
   DESCRIPTION 
      "Generic alarm linked to user specified alarms. These have no specific name in the MIB. 
      User configurable alarms will on some systems have text attached to the traps that explains the purpose of the alarm. "
   ::= { systemControlUnitEntry 2 }

inputUserConfigurable2  OBJECT-TYPE
   SYNTAX     INTEGER {
      normal (0),
      alarm (1)
   }
   MAX-ACCESS read-only
   STATUS     current
   DESCRIPTION 
      "Generic alarm linked to user specified alarms. These have no specific name in the MIB. 
      User configurable alarms will on some systems have text attached to the traps that explains the purpose of the alarm. "
   ::= { systemControlUnitEntry 3 }

inputUserConfigurable3  OBJECT-TYPE
   SYNTAX     INTEGER {
      normal (0),
      alarm (1)
   }
   MAX-ACCESS read-only
   STATUS     current
   DESCRIPTION 
      "Generic alarm linked to user specified alarms. These have no specific name in the MIB. 
      User configurable alarms will on some systems have text attached to the traps that explains the purpose of the alarm. "
   ::= { systemControlUnitEntry 4 }

inputUserConfigurable4  OBJECT-TYPE
   SYNTAX     INTEGER {
      normal (0),
      alarm (1)
   }
   MAX-ACCESS read-only
   STATUS     current
   DESCRIPTION 
      "Generic alarm linked to user specified alarms. These have no specific name in the MIB. 
      User configurable alarms will on some systems have text attached to the traps that explains the purpose of the alarm. "
   ::= { systemControlUnitEntry 5 }

inputUserConfigurable5  OBJECT-TYPE
   SYNTAX     INTEGER {
      normal (0),
      alarm (1)
   }
   MAX-ACCESS read-only
   STATUS     current
   DESCRIPTION 
      "Generic alarm linked to user specified alarms. These have no specific name in the MIB. 
      User configurable alarms will on some systems have text attached to the traps that explains the purpose of the alarm. "
   ::= { systemControlUnitEntry 6 }

inputUserConfigurable6  OBJECT-TYPE
   SYNTAX     INTEGER {
      normal (0),
      alarm (1)
   }
   MAX-ACCESS read-only
   STATUS     current
   DESCRIPTION 
      "Generic alarm linked to user specified alarms. These have no specific name in the MIB. 
      User configurable alarms will on some systems have text attached to the traps that explains the purpose of the alarm. "
   ::= { systemControlUnitEntry 7 }

inputUserConfigurable7  OBJECT-TYPE
   SYNTAX     INTEGER {
      normal (0),
      alarm (1)
   }
   MAX-ACCESS read-only
   STATUS     current
   DESCRIPTION 
      "Generic alarm linked to user specified alarms. These have no specific name in the MIB. 
      User configurable alarms will on some systems have text attached to the traps that explains the purpose of the alarm. "
   ::= { systemControlUnitEntry 8 }

inputUserConfigurable8  OBJECT-TYPE
   SYNTAX     INTEGER {
      normal (0),
      alarm (1)
   }
   MAX-ACCESS read-only
   STATUS     current
   DESCRIPTION 
      "Generic alarm linked to user specified alarms. These have no specific name in the MIB. 
      User configurable alarms will on some systems have text attached to the traps that explains the purpose of the alarm. "
   ::= { systemControlUnitEntry 9 }

inputUserConfigurable9  OBJECT-TYPE
   SYNTAX     INTEGER {
      normal (0),
      alarm (1)
   }
   MAX-ACCESS read-only
   STATUS     current
   DESCRIPTION 
      "Generic alarm linked to user specified alarms. These have no specific name in the MIB. 
      User configurable alarms will on some systems have text attached to the traps that explains the purpose of the alarm. "
   ::= { systemControlUnitEntry 10 }

inputUserConfigurable10  OBJECT-TYPE
   SYNTAX     INTEGER {
      normal (0),
      alarm (1)
   }
   MAX-ACCESS read-only
   STATUS     current
   DESCRIPTION 
      "Generic alarm linked to user specified alarms. These have no specific name in the MIB. 
      User configurable alarms will on some systems have text attached to the traps that explains the purpose of the alarm. "
   ::= { systemControlUnitEntry 11 }

systemLinkStatus  OBJECT-TYPE
   SYNTAX     INTEGER {
      linkdown (0),
      linkup (1)
   }
   MAX-ACCESS read-only
   STATUS     current
   DESCRIPTION 
      "A flag showing the status of the serial port used between the Webpower adapter 
      and the Control system.  If this flag shows status linkdown, the propable cause is
      that the wrong baudrate is set, which again is likely to happen when booting a 
      brand new board.  Execute a 'systemInitiateEEPROM' command to fix."
   ::= { controlSystem 8 }

systemInitiateEEPROM  OBJECT-TYPE
   SYNTAX     INTEGER {
      pushbutton (0),
      start (1)
   }
   MAX-ACCESS read-write
   STATUS     deprecated
   DESCRIPTION 
      "pushbutton function that initiates a forced write of baudrate of 38400bps
      for the serial port. It also writes default data to the eeprom. This function is used for 
      productiontest only. The 3rd party OS used in this application are not able to write  
      default data to EEPROM at boot time. A minimum set of configuration is thus created 
      in RAM. A production test facility must therefore run this command as a part of the 
      production test for the unit to function properly.
      "
   ::= { controlSystem 9 }

-- This branch contains OIDs for configuration of the DC Power System's
-- basic factory data and user's installation settings

dcSystem             OBJECT IDENTIFIER ::= { eltekDistributedPlant 2 }

dcPlant              OBJECT IDENTIFIER ::= { dcSystem 1 }

-- This branch contains OIDs for configuration of the DC Power System's
-- installation and location settings

systemSiteInfo       OBJECT IDENTIFIER ::= { dcPlant 3 }

systemSiteInfoCustomer  OBJECT-TYPE
   SYNTAX     DisplayString (SIZE(0..32))
   MAX-ACCESS read-only
   STATUS     current
   DESCRIPTION 
      "The Customer name (as stored in the Smartpack Control Unit)"
   ::= { systemSiteInfo 1 }

systemSiteInfoLocation  OBJECT-TYPE
   SYNTAX     DisplayString (SIZE(0..32))
   MAX-ACCESS read-only
   STATUS     current
   DESCRIPTION 
      "The system/site Location details (as stored in the Smartpack Control Unit)."
   ::= { systemSiteInfo 2 }

systemSiteInfoMessage1  OBJECT-TYPE
   SYNTAX     DisplayString (SIZE(0..32))
   MAX-ACCESS read-only
   STATUS     current
   DESCRIPTION 
      "The system/site Info Message record #1 (as stored in the Smartpack Control Unit). 31 Bytes."
   ::= { systemSiteInfo 3 }

systemSiteInfoMessage2  OBJECT-TYPE
   SYNTAX     DisplayString (SIZE(0..32))
   MAX-ACCESS read-only
   STATUS     current
   DESCRIPTION 
      "The system/site Info Message record #2 (as stored in the Smartpack Control Unit). 31 Bytes."
   ::= { systemSiteInfo 4 }

systemSiteInfoInstalledDate  OBJECT-TYPE
   SYNTAX     DisplayString (SIZE(0..16))
   MAX-ACCESS read-only
   STATUS     current
   DESCRIPTION 
      "The system's Installed Date text string (as stored in the Smartpack Control Unit) 16bytes."
   ::= { systemSiteInfo 5 }

systemSiteInfoControllerType  OBJECT-TYPE
   SYNTAX     INTEGER {
      al175 (0),
      al4000 (1),
      al6000 (2),
      smartpack (3)
   }
   MAX-ACCESS read-only
   STATUS     current
   DESCRIPTION 
      "The system Controller Module currently connected.
       AL175/MCU=0; AEON Gold=1; AL6000=2; Smartpack=3"
   ::= { systemSiteInfo 6 }

systemSiteInfoSystemSeriaNum  OBJECT-TYPE
   SYNTAX     DisplayString (SIZE(0..16))
   MAX-ACCESS read-only
   STATUS     current
   DESCRIPTION 
      "The serial number for the complete system"
   ::= { systemSiteInfo 7 }

systemSiteInfoControllerSeriaNum  OBJECT-TYPE
   SYNTAX     DisplayString (SIZE(0..16))
   MAX-ACCESS read-only
   STATUS     current
   DESCRIPTION 
      "The serial number for the system controller"
   ::= { systemSiteInfo 8 }

systemNominalVoltage  OBJECT-TYPE
   SYNTAX     INTEGER {
      prs48v (0),
      prs24v (1),
      prs12v (2),
      prs26v (3),
      prs60v (4)
   }
   MAX-ACCESS read-only
   STATUS     current
   DESCRIPTION 
      "The nominal voltage rating. 12V/24V/48V/60V systems
       0=48V
       1=24V
       2=12V
       3=26V
       4=60V"
   ::= { dcPlant 4 }

systemOperationalStatus  OBJECT-TYPE
   SYNTAX     INTEGER {
      floatvoltreg (0),
      floattempcomp (1),
      batteryboost (2),
      batterytest (3)
   }
   MAX-ACCESS read-only
   STATUS     current
   DESCRIPTION 
      "A summary status showing if the system is testing, boosting, floating etc.
       0=Float, voltage regulated
       1=Float, temperature comp. regulated;
       2=equalize
       3=battery test"
   ::= { dcSystem 2 }

-- This branch contains OIDs for configuration of the DC Power System's
-- Battery charging and protection related settings

battery              OBJECT IDENTIFIER ::= { eltekDistributedPlant 3 }

batteryName  OBJECT-TYPE
   SYNTAX     DisplayString (SIZE(0..16))
   MAX-ACCESS read-only
   STATUS     current
   DESCRIPTION 
      "A descriptive name of the battery installed in the system"
   ::= { battery 1 }

batteryVoltage  OBJECT-TYPE
   SYNTAX     Integer32 (0..7500)
   UNITS    "1/100 Volt; i.e. 5400 = 54.00V"
   MAX-ACCESS read-only
   STATUS     current
   DESCRIPTION 
      "The measured battery voltage."
   ::= { battery 2 }

batteryCurrent  OBJECT-TYPE
   SYNTAX     Integer32
   UNITS    "Amperes; i.e. 20 = 20 Amperes"
   MAX-ACCESS read-only
   STATUS     current
   DESCRIPTION 
      "The measured battery current."
   ::= { battery 3 }

batteryTemp  OBJECT-TYPE
   SYNTAX     Integer32 (0..9999)
   UNITS    "1/10 Deg. C; i.e. 250 = 25.0 Deg. C."
   MAX-ACCESS read-only
   STATUS     current
   DESCRIPTION 
      "The battery temperature "
   ::= { battery 4 }

batteryBreakerStatus  OBJECT-TYPE
   SYNTAX     INTEGER {
      closed (0),
      open (1)
   }
   MAX-ACCESS read-only
   STATUS     current
   DESCRIPTION 
      "The state of the battery fuse/breaker can be either closed(0) or open(1) "
   ::= { battery 5 }

batteryChargeCurrentLimitCtrl  OBJECT-TYPE
   SYNTAX     INTEGER {
      deactivate (0),
      activate (1)
   }
   MAX-ACCESS read-write
   STATUS     current
   DESCRIPTION 
      "Control field for the battery charge limitation feature; 0=inactive, 1=active."
   ::= { battery 6 }

batteryChargeCurrentLimitValue  OBJECT-TYPE
   SYNTAX     Integer32 (0..2100)
   UNITS    "Amperes; i.e. 20 = 20 Amperes"
   MAX-ACCESS read-write
   STATUS     current
   DESCRIPTION 
      "Battery charging current limit value"
   ::= { battery 7 }

batteryTempCompEnable  OBJECT-TYPE
   SYNTAX     INTEGER {
      disable (0),
      enable (1)
   }
   MAX-ACCESS read-write
   STATUS     current
   DESCRIPTION 
      "Enable (0) or Disable (1) Battery Temperature Compensated output regulation mode"
   ::= { battery 8 }

batteryFloatVoltConfig  OBJECT-TYPE
   SYNTAX     Integer32 (4300..6000)
   UNITS    "1/100 Volt; i.e. 5400 = 54.00V"
   MAX-ACCESS read-write
   STATUS     current
   DESCRIPTION 
      "The Voltage at which the DC System float charges."
   ::= { battery 9 }

batteryEqualizeVoltConfig  OBJECT-TYPE
   SYNTAX     Integer32 (4300..6000)
   UNITS    "1/100 Volt; i.e. 5400 = 54.00V"
   MAX-ACCESS read-write
   STATUS     current
   DESCRIPTION 
      "The Voltage at which the DC System boost charges the batteries."
   ::= { battery 10 }

batteryHighMajorAlarmVoltageConfig  OBJECT-TYPE
   SYNTAX     Integer32
   MAX-ACCESS read-write
   STATUS     current
   DESCRIPTION 
      "The High Battery Voltage alarm limit set voltage"
   ::= { battery 11 }

batteryHighMinorAlarmVoltageConfig  OBJECT-TYPE
   SYNTAX     Integer32
   UNITS    "1/100 Volt; i.e. 5400 = 54.00V"
   MAX-ACCESS read-write
   STATUS     current
   DESCRIPTION 
      "The High Battery Voltage alarm limit set voltage"
   ::= { battery 12 }

batteryLowMajorAlarmVoltageConfig  OBJECT-TYPE
   SYNTAX     Integer32
   UNITS    "1/100 Volt; i.e. 5400 = 54.00V"
   MAX-ACCESS read-write
   STATUS     current
   DESCRIPTION 
      "The Low Battery Voltage Alarm limit set voltage"
   ::= { battery 13 }

-- This alarm may be used to warn of impending Low Voltage Battery Disconnect operation

batteryLowMinorAlarmVoltageConfig  OBJECT-TYPE
   SYNTAX     Integer32
   UNITS    "1/100 Volt; i.e. 5400 = 54.00V"
   MAX-ACCESS read-write
   STATUS     current
   DESCRIPTION 
      "The Very Low Battery Voltage Alarm limit set voltage"
   ::= { battery 14 }

batteryStartManualTest  OBJECT-TYPE
   SYNTAX     INTEGER {
      pushbutton (0),
      starttest (1),
      stoptest (2)
   }
   MAX-ACCESS read-write
   STATUS     current
   DESCRIPTION 
      "This pushbutton will start a manual battery test if otherwise the system allows it."
   ::= { battery 15 }

batteryStartManualBoost  OBJECT-TYPE
   SYNTAX     INTEGER {
      pushbutton (0),
      startboost (1),
      stopboost (2)
   }
   MAX-ACCESS read-write
   STATUS     current
   DESCRIPTION 
      "This pushbutton will start a manual battery boost if otherwise the system allows it."
   ::= { battery 16 }

-- This branch contains OIDs for configuration of the DC Power System's
-- Battery Disconnect Contactor  / Emergency Disconnect related settings

batteryLVD           OBJECT IDENTIFIER ::= { battery 17 }

batteryLVDStatus  OBJECT-TYPE
   SYNTAX     INTEGER {
      connect (0),
      disconnect (1),
      disable (2)
   }
   MAX-ACCESS read-only
   STATUS     current
   DESCRIPTION 
      "Contactor is closed(0) or open(1) "
   ::= { batteryLVD 1 }

batteryLVDDisconnectVoltage  OBJECT-TYPE
   SYNTAX     Integer32 (0..7200)
   UNITS    "1/100 Volt; i.e. 5400 = 54.00V"
   MAX-ACCESS read-write
   STATUS     current
   DESCRIPTION 
      "The Contactor Disconnect Voltage"
   ::= { batteryLVD 2 }

batteryLVDConnectVoltage  OBJECT-TYPE
   SYNTAX     Integer32 (0..7200)
   UNITS    "1/100 Volt; i.e. 5400 = 54.00V"
   MAX-ACCESS read-write
   STATUS     current
   DESCRIPTION 
      "The Contactor Reconnect Voltage"
   ::= { batteryLVD 3 }

batteryBanksNumofBanks  OBJECT-TYPE
   SYNTAX     Integer32
   MAX-ACCESS read-only
   STATUS     current
   DESCRIPTION 
      ""
   ::= { battery 18 }

batteryBanks         OBJECT IDENTIFIER ::= { battery 19 }

-- This setpoint / value is common for all battery strings monitored

batterySymmetryDeltaLimitVoltage  OBJECT-TYPE
   SYNTAX     Integer32
   MAX-ACCESS read-write
   STATUS     current
   DESCRIPTION 
      "The allowable deviation of the midpoint battery voltage from the theoretical.
       Exceeding this value in either direction (+/-) causes an alarm state"
   ::= { batteryBanks 1 }

batteryBanksIndex  OBJECT-TYPE
   SYNTAX     Integer32 (0..7)
   MAX-ACCESS accessible-for-notify
   STATUS     current
   DESCRIPTION 
      "Index used for navigating int the table of 1 to 8 batterybank symmetry groups"
   ::= { batteryBanks 2 }

batteryBanksTable  OBJECT-TYPE
   SYNTAX SEQUENCE OF BatteryBanksEntry
   MAX-ACCESS not-accessible
   STATUS     current
   DESCRIPTION 
      "A table of up to 8 battery banks. Each bank may have up to 8 symmetry or midpoint measuments"
   ::= { batteryBanks 3 }

batteryBanksEntry  OBJECT-TYPE
   SYNTAX   BatteryBanksEntry
   MAX-ACCESS not-accessible
   STATUS     current
   DESCRIPTION 
      "a distributed control system may contain up to 8 battery banks."
   INDEX { batteryBanksIndex }
   ::= { batteryBanksTable 1 }

BatteryBanksEntry ::= SEQUENCE {
	batteryBankID
		Integer32,
	batteryBanksSymmetry1enable
		INTEGER,
	batteryBanksSymmetry1status
		INTEGER,
	batteryBanksSymmetry1deltaVoltage
		Integer32,
	batteryBanksSymmetry2enable
		INTEGER,
	batteryBanksSymmetry2status
		INTEGER,
	batteryBanksSymmetry2deltaVoltage
		Integer32,
	batteryBanksSymmetry3enable
		INTEGER,
	batteryBanksSymmetry3status
		INTEGER,
	batteryBanksSymmetry3deltaVoltage
		Integer32,
	batteryBanksSymmetry4enable
		INTEGER,
	batteryBanksSymmetry4status
		INTEGER,
	batteryBanksSymmetry4deltaVoltage
		Integer32,
	batteryBanksSymmetry5enable
		INTEGER,
	batteryBanksSymmetry5status
		INTEGER,
	batteryBanksSymmetry5deltaVoltage
		Integer32,
	batteryBanksSymmetry6enable
		INTEGER,
	batteryBanksSymmetry6status
		INTEGER,
	batteryBanksSymmetry6deltaVoltage
		Integer32,
	batteryBanksSymmetry7enable
		INTEGER,
	batteryBanksSymmetry7status
		INTEGER,
	batteryBanksSymmetry7deltaVoltage
		Integer32,
	batteryBanksSymmetry8enable
		INTEGER,
	batteryBanksSymmetry8status
		INTEGER,
	batteryBanksSymmetry8deltaVoltage
		Integer32
}


batteryBankID  OBJECT-TYPE
   SYNTAX     Integer32 (1..8)
   MAX-ACCESS read-only
   STATUS     current
   DESCRIPTION 
      ""
   ::= { batteryBanksEntry 1 }

batteryBanksSymmetry1enable  OBJECT-TYPE
	SYNTAX     INTEGER {
		disable (0),
		enable (1)
	}
	MAX-ACCESS read-write
	STATUS     current
	DESCRIPTION 
		"When set to 'on' the the symmetry input is activated. when turned off, measuments
		      for this input is turned off and the correcponding value will read 0 volts and 
		      the alarm flag will be turned off"
	::= { batteryBanksEntry 2 }

batteryBanksSymmetry1status  OBJECT-TYPE
	SYNTAX     INTEGER {
		ok (0),
		minorAlarm (1),
		majorAlarm (2),
		disabled (3),
		error (4)
	}
	MAX-ACCESS read-only
	STATUS     current
	DESCRIPTION 
		"Status (0=Normal; 1=Alarm) of the Battery Monitor channel which corresponds 
		       to the batteryMidpointIndex value"
	::= { batteryBanksEntry 3 }

batteryBanksSymmetry1deltaVoltage  OBJECT-TYPE
	SYNTAX     Integer32
	MAX-ACCESS read-only
	STATUS     current
	DESCRIPTION 
		"The measured battery voltage deviation from midpoint of the Battery Monitor channel
		       which corresponds to the batteryMidpointIndex value."
	::= { batteryBanksEntry 4 }

batteryBanksSymmetry2enable  OBJECT-TYPE
	SYNTAX     INTEGER {
		disable (0),
		enable (1)
	}
	MAX-ACCESS read-write
	STATUS     current
	DESCRIPTION 
		"When set to 'on' the the symmetry input is activated. when turned off, measuments
		      for this input is turned off and the correcponding value will read 0 volts and 
		      the alarm flag will be turned off"
	::= { batteryBanksEntry 5 }

batteryBanksSymmetry2status  OBJECT-TYPE
	SYNTAX     INTEGER {
		ok (0),
		minorAlarm (1),
		majorAlarm (2),
		disabled (3),
		error (4)
	}
	MAX-ACCESS read-only
	STATUS     current
	DESCRIPTION 
		"Status (0=Normal; 1=Alarm) of the Battery Monitor channel which corresponds 
		       to the batteryMidpointIndex value"
	::= { batteryBanksEntry 6 }

batteryBanksSymmetry2deltaVoltage  OBJECT-TYPE
	SYNTAX     Integer32
	MAX-ACCESS read-only
	STATUS     current
	DESCRIPTION 
		"The measured battery voltage deviation from midpoint of the Battery Monitor channel
		       which corresponds to the batteryMidpointIndex value."
	::= { batteryBanksEntry 7 }

batteryBanksSymmetry3enable  OBJECT-TYPE
	SYNTAX     INTEGER {
		disable (0),
		enable (1)
	}
	MAX-ACCESS read-write
	STATUS     current
	DESCRIPTION 
		"When set to 'on' the the symmetry input is activated. when turned off, measuments
		      for this input is turned off and the correcponding value will read 0 volts and 
		      the alarm flag will be turned off"
	::= { batteryBanksEntry 8 }

batteryBanksSymmetry3status  OBJECT-TYPE
	SYNTAX     INTEGER {
		ok (0),
		minorAlarm (1),
		majorAlarm (2),
		disabled (3),
		error (4)
	}
	MAX-ACCESS read-only
	STATUS     current
	DESCRIPTION 
		"Status (0=Normal; 1=Alarm) of the Battery Monitor channel which corresponds 
		       to the batteryMidpointIndex value"
	::= { batteryBanksEntry 9 }

batteryBanksSymmetry3deltaVoltage  OBJECT-TYPE
	SYNTAX     Integer32
	MAX-ACCESS read-only
	STATUS     current
	DESCRIPTION 
		"The measured battery voltage deviation from midpoint of the Battery Monitor channel
		       which corresponds to the batteryMidpointIndex value."
	::= { batteryBanksEntry 10 }

batteryBanksSymmetry4enable  OBJECT-TYPE
	SYNTAX     INTEGER {
		disable (0),
		enable (1)
	}
	MAX-ACCESS read-write
	STATUS     current
	DESCRIPTION 
		"When set to 'on' the the symmetry input is activated. when turned off, measuments
		      for this input is turned off and the correcponding value will read 0 volts and 
		      the alarm flag will be turned off"
	::= { batteryBanksEntry 11 }

batteryBanksSymmetry4status  OBJECT-TYPE
	SYNTAX     INTEGER {
		ok (0),
		minorAlarm (1),
		majorAlarm (2),
		disabled (3),
		error (4)
	}
	MAX-ACCESS read-only
	STATUS     current
	DESCRIPTION 
		"Status (0=Normal; 1=Alarm) of the Battery Monitor channel which corresponds 
		       to the batteryMidpointIndex value"
	::= { batteryBanksEntry 12 }

batteryBanksSymmetry4deltaVoltage  OBJECT-TYPE
	SYNTAX     Integer32
	MAX-ACCESS read-only
	STATUS     current
	DESCRIPTION 
		"The measured battery voltage deviation from midpoint of the Battery Monitor channel
		       which corresponds to the batteryMidpointIndex value."
	::= { batteryBanksEntry 13 }

batteryBanksSymmetry5enable  OBJECT-TYPE
	SYNTAX     INTEGER {
		disable (0),
		enable (1)
	}
	MAX-ACCESS read-write
	STATUS     current
	DESCRIPTION 
		"When set to 'on' the the symmetry input is activated. when turned off, measuments
		      for this input is turned off and the correcponding value will read 0 volts and 
		      the alarm flag will be turned off"
	::= { batteryBanksEntry 14 }

batteryBanksSymmetry5status  OBJECT-TYPE
	SYNTAX     INTEGER {
		ok (0),
		minorAlarm (1),
		majorAlarm (2),
		disabled (3),
		error (4)
	}
	MAX-ACCESS read-only
	STATUS     current
	DESCRIPTION 
		"Status (0=Normal; 1=Alarm) of the Battery Monitor channel which corresponds 
		       to the batteryMidpointIndex value"
	::= { batteryBanksEntry 15 }

batteryBanksSymmetry5deltaVoltage  OBJECT-TYPE
	SYNTAX     Integer32
	MAX-ACCESS read-only
	STATUS     current
	DESCRIPTION 
		"The measured battery voltage deviation from midpoint of the Battery Monitor channel
		       which corresponds to the batteryMidpointIndex value."
	::= { batteryBanksEntry 16 }

batteryBanksSymmetry6enable  OBJECT-TYPE
	SYNTAX     INTEGER {
		disable (0),
		enable (1)
	}
	MAX-ACCESS read-write
	STATUS     current
	DESCRIPTION 
		"When set to 'on' the the symmetry input is activated. when turned off, measuments
		      for this input is turned off and the correcponding value will read 0 volts and 
		      the alarm flag will be turned off"
	::= { batteryBanksEntry 17 }

batteryBanksSymmetry6status  OBJECT-TYPE
	SYNTAX     INTEGER {
		ok (0),
		minorAlarm (1),
		majorAlarm (2),
		disabled (3),
		error (4)
	}
	MAX-ACCESS read-only
	STATUS     current
	DESCRIPTION 
		"Status (0=Normal; 1=Alarm) of the Battery Monitor channel which corresponds 
		       to the batteryMidpointIndex value"
	::= { batteryBanksEntry 18 }

batteryBanksSymmetry6deltaVoltage  OBJECT-TYPE
	SYNTAX     Integer32
	MAX-ACCESS read-only
	STATUS     current
	DESCRIPTION 
		"The measured battery voltage deviation from midpoint of the Battery Monitor channel
		       which corresponds to the batteryMidpointIndex value."
	::= { batteryBanksEntry 19 }

batteryBanksSymmetry7enable  OBJECT-TYPE
	SYNTAX     INTEGER {
		disable (0),
		enable (1)
	}
	MAX-ACCESS read-write
	STATUS     current
	DESCRIPTION 
		"When set to 'on' the the symmetry input is activated. when turned off, measuments
		      for this input is turned off and the correcponding value will read 0 volts and 
		      the alarm flag will be turned off"
	::= { batteryBanksEntry 20 }

batteryBanksSymmetry7status  OBJECT-TYPE
	SYNTAX     INTEGER {
		ok (0),
		minorAlarm (1),
		majorAlarm (2),
		disabled (3),
		error (4)
	}
	MAX-ACCESS read-only
	STATUS     current
	DESCRIPTION 
		"Status (0=Normal; 1=Alarm) of the Battery Monitor channel which corresponds 
		       to the batteryMidpointIndex value"
	::= { batteryBanksEntry 21 }

batteryBanksSymmetry7deltaVoltage  OBJECT-TYPE
	SYNTAX     Integer32
	MAX-ACCESS read-only
	STATUS     current
	DESCRIPTION 
		"The measured battery voltage deviation from midpoint of the Battery Monitor channel
		       which corresponds to the batteryMidpointIndex value."
	::= { batteryBanksEntry 22 }

batteryBanksSymmetry8enable  OBJECT-TYPE
	SYNTAX     INTEGER {
		disable (0),
		enable (1)
	}
	MAX-ACCESS read-write
	STATUS     current
	DESCRIPTION 
		"When set to 'on' the the symmetry input is activated. when turned off, measuments
		      for this input is turned off and the correcponding value will read 0 volts and 
		      the alarm flag will be turned off"
	::= { batteryBanksEntry 23 }

batteryBanksSymmetry8status  OBJECT-TYPE
	SYNTAX     INTEGER {
		ok (0),
		minorAlarm (1),
		majorAlarm (2),
		disabled (3),
		error (4)
	}
	MAX-ACCESS read-only
	STATUS     current
	DESCRIPTION 
		"Status (0=Normal; 1=Alarm) of the Battery Monitor channel which corresponds 
		       to the batteryMidpointIndex value"
	::= { batteryBanksEntry 24 }

batteryBanksSymmetry8deltaVoltage  OBJECT-TYPE
	SYNTAX     Integer32
	MAX-ACCESS read-only
	STATUS     current
	DESCRIPTION 
		"The measured battery voltage deviation from midpoint of the Battery Monitor channel
		       which corresponds to the batteryMidpointIndex value."
	::= { batteryBanksEntry 25 }

-- This branch contains OIDs related to the DC Load Distribution equipment

loadDistribution     OBJECT IDENTIFIER ::= { eltekDistributedPlant 4 }

loadDistributionCurrent  OBJECT-TYPE
   SYNTAX     Integer32
   UNITS    "Amperes; i.e. 20 = 20 Amperes"
   MAX-ACCESS read-only
   STATUS     current
   DESCRIPTION 
      "The total load current"
   ::= { loadDistribution 1 }

loadDistributionBreakerStatus  OBJECT-TYPE
   SYNTAX     INTEGER {
      closed (0),
      open (1)
   }
   MAX-ACCESS read-only
   STATUS     current
   DESCRIPTION 
      "The state of the load fuse/breaker can be either closed(0) or open(1) "
   ::= { loadDistribution 2 }

-- This branch contains OIDs related to the Load Disconnect / Load Shedding equipment

loadDistributionLVDStatus  OBJECT IDENTIFIER ::= { loadDistribution 3 }

loadLVD1EnableStatus  OBJECT-TYPE
   SYNTAX     INTEGER {
      disabled (0),
      enabled (1)
   }
   MAX-ACCESS read-only
   STATUS     current
   DESCRIPTION 
      "The status of contactors configuration. 'enabled' means that the contactor is i n use. 'disabled' means that the contactor is disconfigured and not in use."
   ::= { loadDistributionLVDStatus 1 }

loadLVD1Status  OBJECT-TYPE
   SYNTAX     INTEGER {
      connect (0),
      disconnect (1),
      disable (2)
   }
   MAX-ACCESS read-only
   STATUS     current
   DESCRIPTION 
      "The primary load Contactor is closed(0) or open(1) "
   ::= { loadDistributionLVDStatus 2 }

loadLVD1ConnectVoltage  OBJECT-TYPE
   SYNTAX     Integer32 (0..7200)
   UNITS    "1/100 Volt; i.e. 5400 = 54.00V"
   MAX-ACCESS read-write
   STATUS     current
   DESCRIPTION 
      "The primary loads Contactor Connect Voltage"
   ::= { loadDistributionLVDStatus 3 }

loadLVD1DisconnectVoltage  OBJECT-TYPE
   SYNTAX     Integer32 (0..7200)
   UNITS    "1/100 Volt; i.e. 5400 = 54.00V"
   MAX-ACCESS read-write
   STATUS     current
   DESCRIPTION 
      "The primary load Contactor Disconnect Voltage"
   ::= { loadDistributionLVDStatus 4 }

loadLVD2EnableStatus  OBJECT-TYPE
   SYNTAX     INTEGER {
      disabled (0),
      enabled (1)
   }
   MAX-ACCESS read-only
   STATUS     current
   DESCRIPTION 
      "The status of contactors configuration. 'enabled' means that the contactor is i n use. 
      'disabled' means that the contactor is disconfigured and not in use."
   ::= { loadDistributionLVDStatus 5 }

loadLVD2Status  OBJECT-TYPE
   SYNTAX     INTEGER {
      connect (0),
      disconnect (1),
      disable (2)
   }
   MAX-ACCESS read-only
   STATUS     current
   DESCRIPTION 
      "The secondary load Contactor is closed(0) or open(1) "
   ::= { loadDistributionLVDStatus 6 }

loadLVD2ConnectVoltage  OBJECT-TYPE
   SYNTAX     Integer32 (0..7200)
   MAX-ACCESS read-write
   STATUS     current
   DESCRIPTION 
      "The secondary load Contactor Connect Voltage"
   ::= { loadDistributionLVDStatus 7 }

loadLVD2DisconnectVoltage  OBJECT-TYPE
   SYNTAX     Integer32 (0..7200)
   UNITS    "1/100 Volt; i.e. 5400 = 54.00V"
   MAX-ACCESS read-write
   STATUS     current
   DESCRIPTION 
      "The secondary loads Contactor Disconnect Voltage"
   ::= { loadDistributionLVDStatus 8 }

loadLVD3EnableStatus  OBJECT-TYPE
   SYNTAX     INTEGER {
      disabled (0),
      enabled (1)
   }
   MAX-ACCESS read-only
   STATUS     current
   DESCRIPTION 
      "The status of contactors configuration. 'enabled' means that the contactor is i n use. 
      'disabled' means that the contactor is disconfigured and not in use."
   ::= { loadDistributionLVDStatus 9 }

loadLVD3Status  OBJECT-TYPE
   SYNTAX     INTEGER {
      connect (0),
      disconnect (1),
      disable (2)
   }
   MAX-ACCESS read-only
   STATUS     current
   DESCRIPTION 
      "The third critical loads Contactor is closed(0) or open(1) "
   ::= { loadDistributionLVDStatus 10 }

loadLVD3ConnectVoltage  OBJECT-TYPE
   SYNTAX     Integer32 (0..7200)
   MAX-ACCESS read-write
   STATUS     current
   DESCRIPTION 
      "The third critical load Contactor Connect Voltage"
   ::= { loadDistributionLVDStatus 11 }

loadLVD3DisconnectVoltage  OBJECT-TYPE
   SYNTAX     Integer32 (0..7200)
   UNITS    "1/100 Volt; i.e. 5400 = 54.00V"
   MAX-ACCESS read-write
   STATUS     current
   DESCRIPTION 
      "The third critical loads Contactor Disconnect Voltage"
   ::= { loadDistributionLVDStatus 12 }

-- This branch contains OIDs related to the Flatpack 2 rectifier parameters

rectifier            OBJECT IDENTIFIER ::= { eltekDistributedPlant 5 }

rectifierInstalledRectifiers  OBJECT-TYPE
   SYNTAX     Integer32 (1..101)
   MAX-ACCESS read-only
   STATUS     current
   DESCRIPTION 
      "The installed number of rectifiers for this DC Power System."
   ::= { rectifier 1 }

rectifierRectifiersActive  OBJECT-TYPE
   SYNTAX     Integer32 (1..101)
   MAX-ACCESS read-only
   STATUS     current
   DESCRIPTION 
      "The actual number of active rectifiers in this DC Power System."
   ::= { rectifier 2 }

rectifierTotalCurrent  OBJECT-TYPE
   SYNTAX     Integer32
   UNITS    "Amperes; i.e. 20 = 20 Amperes"
   MAX-ACCESS read-only
   STATUS     current
   DESCRIPTION 
      "The DC system's total available current"
   ::= { rectifier 3 }

rectifierUtilization  OBJECT-TYPE
   SYNTAX     Integer32 (0..100)
   MAX-ACCESS read-only
   STATUS     current
   DESCRIPTION 
      "Utilization in % of available rectifier capacity"
   ::= { rectifier 4 }

-- This branch contains OIDs for polling of the Flatpack 2 Rectifier status settings

rectifierStatus      OBJECT IDENTIFIER ::= { rectifier 5 }

rectifierStatusNoIndex  OBJECT-TYPE
   SYNTAX     Integer32 (1..20)
   MAX-ACCESS read-write
   STATUS     current
   DESCRIPTION 
      "A starting index for the rectifierStatusTable array"
   DEFVAL  { 1 }
   ::= { rectifierStatus 1 }

rectifierStatusTable  OBJECT-TYPE
   SYNTAX SEQUENCE OF RectifierStatusEntry
   MAX-ACCESS not-accessible
   STATUS     current
   DESCRIPTION 
      "A table listing up to sixteen sequential recifiers, starting
      from the rectifier number specified by rectifierStatusNoIndex"
   ::= { rectifierStatus 2 }

rectifierStatusEntry  OBJECT-TYPE
   SYNTAX   RectifierStatusEntry
   MAX-ACCESS not-accessible
   STATUS     current
   DESCRIPTION 
      "A row of rectifier status data corresponding to the rectifierStatusNoIndex value"
   INDEX { rectifierStatusID }
   ::= { rectifierStatusTable 1 }

RectifierStatusEntry ::= SEQUENCE {
   rectifierStatusID
      Integer32,
   rectifierStatusStatus
      INTEGER,
   rectifierStatusOutputCurrent
      Integer32,
   rectifierStatusOutputVoltage
      Integer32,
   rectifierStatusTemp
      Integer32,
   rectifierStatusType
      DisplayString,
   rectifierStatusSKU
      DisplayString,
   rectifierStatusSerialNo
      DisplayString,
   rectifierStatusRevisionLevel
      DisplayString
}

rectifierStatusID  OBJECT-TYPE
   SYNTAX     Integer32 (1..100)
   MAX-ACCESS read-only
   STATUS     current
   DESCRIPTION 
      "The rectifier ID number of the rectifier record."
   ::= { rectifierStatusEntry 1 }

rectifierStatusStatus  OBJECT-TYPE
   SYNTAX     INTEGER {
      absent (0),
      active (1),
      failed (2),
      walkin (3),
      disabledbycommand (4)
   }
   MAX-ACCESS read-only
   STATUS     current
   DESCRIPTION 
      "The operational status of the rectifier record.
      absent (0),
      active (1),
      failed (2),
      walkin (3),
      disabledbycommand (4)
      
      "
   ::= { rectifierStatusEntry 2 }

rectifierStatusOutputCurrent  OBJECT-TYPE
   SYNTAX     Integer32 (0..65535)
   UNITS    "1/10 Amperes; i.e. 200 = 20 Amperes"
   MAX-ACCESS read-only
   STATUS     current
   DESCRIPTION 
      "The rectifier current of the rectifier record."
   ::= { rectifierStatusEntry 3 }

rectifierStatusOutputVoltage  OBJECT-TYPE
   SYNTAX     Integer32 (0..65535)
   UNITS    "1/100 Volt; i.e. 5400 = 54.00V"
   MAX-ACCESS read-only
   STATUS     current
   DESCRIPTION 
      "The rectifier voltage of the rectifier record."
   ::= { rectifierStatusEntry 4 }

rectifierStatusTemp  OBJECT-TYPE
   SYNTAX     Integer32 (0..65535)
   UNITS    "Deg. C/10; i.e. 350 = 35.0 Deg. C"
   MAX-ACCESS read-only
   STATUS     current
   DESCRIPTION 
      "The heatsink temperature of the rectifier record."
   ::= { rectifierStatusEntry 5 }

rectifierStatusType  OBJECT-TYPE
   SYNTAX     DisplayString (SIZE(0..16))
   MAX-ACCESS read-only
   STATUS     current
   DESCRIPTION 
      "The rectifier article number string of the rectifier record."
   ::= { rectifierStatusEntry 6 }

rectifierStatusSKU  OBJECT-TYPE
   SYNTAX     DisplayString (SIZE(0..16))
   MAX-ACCESS read-only
   STATUS     current
   DESCRIPTION 
      "The rectifier Stock Keeping Unit number or other user-defined ID of the rectifier record."
   ::= { rectifierStatusEntry 7 }

rectifierStatusSerialNo  OBJECT-TYPE
   SYNTAX     DisplayString (SIZE(0..16))
   MAX-ACCESS read-only
   STATUS     current
   DESCRIPTION 
      "The rectifier serial number string of the rectifier record."
   ::= { rectifierStatusEntry 8 }

rectifierStatusRevisionLevel  OBJECT-TYPE
   SYNTAX     DisplayString (SIZE(0..16))
   MAX-ACCESS read-only
   STATUS     current
   DESCRIPTION 
      "The rectifier version number string of the rectifier record."
   ::= { rectifierStatusEntry 9 }

acDistribution       OBJECT IDENTIFIER ::= { eltekDistributedPlant 6 }

acVoltage1  OBJECT-TYPE
   SYNTAX     Integer32
   UNITS    "Volts AC"
   MAX-ACCESS read-only
   STATUS     current
   DESCRIPTION 
      "The AC Voltage of phase 1"
   ::= { acDistribution 1 }

acVoltage2  OBJECT-TYPE
   SYNTAX     Integer32
   UNITS    "Volts AC"
   MAX-ACCESS read-only
   STATUS     current
   DESCRIPTION 
      "The AC Voltage of phase 2"
   ::= { acDistribution 2 }

acVoltage3  OBJECT-TYPE
   SYNTAX     Integer32
   UNITS    "Volts AC"
   MAX-ACCESS read-only
   STATUS     current
   DESCRIPTION 
      "The AC Voltage of phase 3"
   ::= { acDistribution 3 }

-- This branch contains Alarms and Events that are mappable to alarm relay positions.
-- Also duplicated as Traps

alarmGroup           OBJECT IDENTIFIER ::= { eltekDistributedPlant 7 }

-- Common alarm types: (12) as specified by Nextel as relay outputs,
-- others available for inclusion to Plant summation alarms

alarmWellknownAlarms  OBJECT IDENTIFIER ::= { alarmGroup 1 }

alarmMajorHighBattVolt  OBJECT-TYPE
   SYNTAX     INTEGER {
      normal (0),
      alarm (1)
   }
   MAX-ACCESS read-only
   STATUS     current
   DESCRIPTION 
      "The Very High Battery Voltage Alarm"
   ::= { alarmWellknownAlarms 1 }

alarmMinorHighBattVolt  OBJECT-TYPE
   SYNTAX     INTEGER {
      normal (0),
      alarm (1)
   }
   MAX-ACCESS read-only
   STATUS     current
   DESCRIPTION 
      "The High Battery Voltage alarm"
   ::= { alarmWellknownAlarms 2 }

alarmMajorLowBattVolt  OBJECT-TYPE
   SYNTAX     INTEGER {
      normal (0),
      alarm (1)
   }
   MAX-ACCESS read-only
   STATUS     current
   DESCRIPTION 
      "The Very Low Battery Voltage Alarm"
   ::= { alarmWellknownAlarms 3 }

alarmMinorLowBattVolt  OBJECT-TYPE
   SYNTAX     INTEGER {
      normal (0),
      alarm (1)
   }
   MAX-ACCESS read-only
   STATUS     current
   DESCRIPTION 
      "The Low Battery Voltage Alarm"
   ::= { alarmWellknownAlarms 4 }

alarmMajorBatteryHighTemp  OBJECT-TYPE
   SYNTAX     INTEGER {
      normal (0),
      alarm (1)
   }
   MAX-ACCESS read-only
   STATUS     current
   DESCRIPTION 
      "Temperature much too high alarm, or  temperature compensation circuit / probe failure alarm"
   ::= { alarmWellknownAlarms 5 }

alarmMinorBatteryHighTemp  OBJECT-TYPE
   SYNTAX     INTEGER {
      normal (0),
      alarm (1)
   }
   MAX-ACCESS read-only
   STATUS     current
   DESCRIPTION 
      "Temperature much too high alarm"
   ::= { alarmWellknownAlarms 6 }

alarmBatteryDisconnectOpen  OBJECT-TYPE
   SYNTAX     INTEGER {
      normal (0),
      alarm (1)
   }
   MAX-ACCESS read-only
   STATUS     current
   DESCRIPTION 
      "The Battery Disconnect Contactor alarm"
   ::= { alarmWellknownAlarms 7 }

alarmLVD1open  OBJECT-TYPE
   SYNTAX     INTEGER {
      normal (0),
      alarm (1)
   }
   MAX-ACCESS read-only
   STATUS     current
   DESCRIPTION 
      "The A Bus (primary loads) Contactor alarm. The contactor dropout voltage has been
       reached and the contactor will release."
   ::= { alarmWellknownAlarms 8 }

alarmLVD2open  OBJECT-TYPE
   SYNTAX     INTEGER {
      normal (0),
      alarm (1)
   }
   MAX-ACCESS read-only
   STATUS     current
   DESCRIPTION 
      "The B Bus (secondary loads) Contactor alarm. The contactor dropout voltage has been
       reached and the contactor will release."
   ::= { alarmWellknownAlarms 9 }

alarmLVD3open  OBJECT-TYPE
   SYNTAX     INTEGER {
      normal (0),
      alarm (1)
   }
   MAX-ACCESS read-only
   STATUS     current
   DESCRIPTION 
      "The C Bus (critical loads) Contactor alarm. The contactor dropout voltage has been
       reached and the contactor will release.
      "
   ::= { alarmWellknownAlarms 10 }

alarmACmains  OBJECT-TYPE
   SYNTAX     INTEGER {
      normal (0),
      alarm (1)
   }
   MAX-ACCESS read-only
   STATUS     current
   DESCRIPTION 
      "The AC voltage has dropped below critical level, 
      or one or more AC input phases was lost."
   ::= { alarmWellknownAlarms 11 }

alarmBatteryBreakerOpen  OBJECT-TYPE
   SYNTAX     INTEGER {
      normal (0),
      alarm (1)
   }
   MAX-ACCESS read-only
   STATUS     current
   DESCRIPTION 
      "Battery string disconnect breaker/fuse alarm"
   ::= { alarmWellknownAlarms 12 }

alarmDistributionBreakerOpen  OBJECT-TYPE
   SYNTAX     INTEGER {
      normal (0),
      alarm (1)
   }
   MAX-ACCESS read-only
   STATUS     current
   DESCRIPTION 
      "The Load Distribution breaker/fuse alarm "
   ::= { alarmWellknownAlarms 13 }

alarmMajorRectifier  OBJECT-TYPE
   SYNTAX     INTEGER {
      normal (0),
      alarm (1)
   }
   MAX-ACCESS read-only
   STATUS     current
   DESCRIPTION 
      "This is a 'multiple rectifiers have failed' alarm"
   ::= { alarmWellknownAlarms 14 }

alarmMinorRectifier  OBJECT-TYPE
   SYNTAX     INTEGER {
      normal (0),
      alarm (1)
   }
   MAX-ACCESS read-only
   STATUS     current
   DESCRIPTION 
      "This is a 'one rectifier has failed' alarm"
   ::= { alarmWellknownAlarms 15 }

alarmMajorBatteryMidpoint  OBJECT-TYPE
   SYNTAX     INTEGER {
      normal (0),
      alarm (1)
   }
   MAX-ACCESS read-only
   STATUS     current
   DESCRIPTION 
      "Battery Symmetry (midpoint) Delta Voltage is badly out of limits alarm"
   ::= { alarmWellknownAlarms 16 }

alarmMinorBatteryMidpoint  OBJECT-TYPE
   SYNTAX     INTEGER {
      normal (0),
      alarm (1)
   }
   MAX-ACCESS read-only
   STATUS     current
   DESCRIPTION 
      "Battery Symmetry (midpoint) Delta Voltage out of limits alarm"
   ::= { alarmWellknownAlarms 17 }

alarmBatteryLifeEnded  OBJECT-TYPE
   SYNTAX     INTEGER {
      normal (0),
      alarm (1)
   }
   MAX-ACCESS read-only
   STATUS     current
   DESCRIPTION 
      "The battery capacity has dropped below critical level. 
      A battery test has measured the fully charged capacity to be too low, 
      and thus probably the battery lifecycle to be near expired."
   ::= { alarmWellknownAlarms 18 }

alarmBatteryTestmodeEntered  OBJECT-TYPE
   SYNTAX     INTEGER {
      normal (0),
      alarm (1)
   }
   MAX-ACCESS read-only
   STATUS     current
   DESCRIPTION 
      "The system has lowered the battery charge voltage in order to discharge the batteries 
      to a predefinend level. When the criteria for stopping the battery testing is reached, the 
      charge voltage is increased to commence normal charging."
   ::= { alarmWellknownAlarms 19 }

alarmBatteryBoostmodeEntered  OBJECT-TYPE
   SYNTAX     INTEGER {
      normal (0),
      alarm (1)
   }
   MAX-ACCESS read-only
   STATUS     current
   DESCRIPTION 
      "The system has increased the battery charge voltage in order to equalize the 
      battery cells charging. When the criteria for stopping the battery equalizing is reached, 
      the charge voltage is lowered to commence normal charging."
   ::= { alarmWellknownAlarms 20 }

dcSystemTraps  NOTIFICATION-GROUP
   NOTIFICATIONS { alarmMajorHighBattVoltTrap, 
      alarmMinorHighBattVoltTrap, 
      alarmMajorLowBattVoltTrap, 
      alarmMinorLowBattVoltTrap, 
      alarmMajorBatteryHighTempTrap, 
      alarmMinorBatteryHighTempTrap, 
      alarmBatteryDisconnectOpenTrap, 
      alarmLVD1openTrap, 
      alarmLVD2openTrap, 
      alarmLVD3openTrap, 
      alarmACmainsTrap, 
      alarmBatteryBreakerOpenTrap, 
      alarmDistributionBreakerOpenTrap, 
      alarmMajorRectifierTrap, 
      alarmMinorRectifierTrap, 
      alarmMajorBatteryMidpointTrap, 
      alarmMinorBatteryMidpointTrap, 
      alarmBatteryLifeEndedTrap, 
      alarmBatteryTestmodeEnteredTrap, 
      alarmBatteryBoostmodeEnteredTrap, 
      alarmController1proginputTrap, 
      alarmController2proginputTrap, 
      alarmController3proginputTrap, 
      alarmController4proginputTrap, 
      alarmController5proginputTrap, 
      alarmController6proginputTrap, 
      alarmController7proginputTrap, 
      alarmController8proginputTrap }
   STATUS     current
   DESCRIPTION 
      " This branch contains the Alarm Notification Traps, which duplicate the alarmGroup OIDs.
       Each alarm condition is represented by a Alarm Condition Trap and an associated OFF
       Trap, which is optionally transmitted according to the state of  OID systemSendOffTrap"
   ::= { eltekDistributedPlant 8 }



alarmMajorHighBattVoltTrap  NOTIFICATION-TYPE
   OBJECTS { alarmMajorHighBattVolt }
   STATUS     current
   DESCRIPTION 
      "The Very High Battery Voltage alarm"
   ::= { dcSystemTraps 1 }

alarmMinorHighBattVoltTrap  NOTIFICATION-TYPE
   OBJECTS { alarmMinorHighBattVolt }
   STATUS     current
   DESCRIPTION 
      "The High Battery Voltage alarm"
   ::= { dcSystemTraps 2 }

alarmMajorLowBattVoltTrap  NOTIFICATION-TYPE
   OBJECTS { alarmMajorLowBattVolt }
   STATUS     current
   DESCRIPTION 
      "The Very Low Battery Voltage Alarm"
   ::= { dcSystemTraps 3 }

alarmMinorLowBattVoltTrap  NOTIFICATION-TYPE
   OBJECTS { alarmMinorLowBattVolt }
   STATUS     current
   DESCRIPTION 
      "The Low Battery Voltage Alarm"
   ::= { dcSystemTraps 4 }

alarmMajorBatteryHighTempTrap  NOTIFICATION-TYPE
   OBJECTS { alarmMajorBatteryHighTemp }
   STATUS     current
   DESCRIPTION 
      "High Battery temperature alarm or 
      Temperature Compensation circuit / probe failure alarm"
   ::= { dcSystemTraps 5 }

alarmMinorBatteryHighTempTrap  NOTIFICATION-TYPE
   OBJECTS { alarmMinorBatteryHighTemp }
   STATUS     current
   DESCRIPTION 
      "High Battery temperature alarm"
   ::= { dcSystemTraps 6 }

alarmBatteryDisconnectOpenTrap  NOTIFICATION-TYPE
   OBJECTS { alarmBatteryDisconnectOpen }
   STATUS     current
   DESCRIPTION 
      "The Battery Disconnect Contactor alarm"
   ::= { dcSystemTraps 7 }

alarmLVD1openTrap  NOTIFICATION-TYPE
   OBJECTS { alarmLVD1open }
   STATUS     current
   DESCRIPTION 
      "The A Bus (primary loads) Contactor is open alarm"
   ::= { dcSystemTraps 8 }

alarmLVD2openTrap  NOTIFICATION-TYPE
   OBJECTS { alarmLVD2open }
   STATUS     current
   DESCRIPTION 
      "The B Bus (secondary loads) Contactor is open alarm"
   ::= { dcSystemTraps 9 }

alarmLVD3openTrap  NOTIFICATION-TYPE
   OBJECTS { alarmLVD3open }
   STATUS     current
   DESCRIPTION 
      "The C Bus (critical loads) Contactor alarm. The contactor dropout voltage has been
       reached and the contactor is released.
      "
   ::= { dcSystemTraps 10 }

alarmACmainsTrap  NOTIFICATION-TYPE
   OBJECTS { alarmACmains }
   STATUS     current
   DESCRIPTION 
      "The AC voltage has dropped below critical level, 
      or one or more AC input phases was lost."
   ::= { dcSystemTraps 11 }

alarmBatteryBreakerOpenTrap  NOTIFICATION-TYPE
   OBJECTS { alarmBatteryBreakerOpen }
   STATUS     current
   DESCRIPTION 
      "Battery string disconnect breaker/fuse alarm"
   ::= { dcSystemTraps 12 }

alarmDistributionBreakerOpenTrap  NOTIFICATION-TYPE
   OBJECTS { alarmDistributionBreakerOpen }
   STATUS     current
   DESCRIPTION 
      "The Load Distribution breaker/fuse alarm"
   ::= { dcSystemTraps 13 }

alarmMajorRectifierTrap  NOTIFICATION-TYPE
   OBJECTS { alarmMajorRectifier }
   STATUS     current
   DESCRIPTION 
      "This is a 'multiple rectifiers have failed' alarm"
   ::= { dcSystemTraps 14 }

alarmMinorRectifierTrap  NOTIFICATION-TYPE
   OBJECTS { alarmMinorRectifier }
   STATUS     current
   DESCRIPTION 
      "This is a 'one rectifier has failed' alarm"
   ::= { dcSystemTraps 15 }

alarmMajorBatteryMidpointTrap  NOTIFICATION-TYPE
   OBJECTS { alarmMajorBatteryMidpoint }
   STATUS     current
   DESCRIPTION 
      "Battery Symmetry (midpoint) Delta Voltage out of 'major fault' limits alarm"
   ::= { dcSystemTraps 16 }

alarmMinorBatteryMidpointTrap  NOTIFICATION-TYPE
   OBJECTS { alarmMinorBatteryMidpoint }
   STATUS     current
   DESCRIPTION 
      "Battery Symmetry (midpoint) Delta Voltage out of limits alarm"
   ::= { dcSystemTraps 17 }

alarmBatteryLifeEndedTrap  NOTIFICATION-TYPE
   OBJECTS { alarmBatteryLifeEnded }
   STATUS     current
   DESCRIPTION 
      "The battery capacity has dropped below critical level. 
      A battery test has measured the fully charged capacity to be too low, 
      and thus probably the battery lifecycle to be near expired."
   ::= { dcSystemTraps 18 }

alarmBatteryTestmodeEnteredTrap  NOTIFICATION-TYPE
   OBJECTS { alarmBatteryTestmodeEntered }
   STATUS     current
   DESCRIPTION 
      "The system has lowered the battery charge voltage in order to discharge the batteries 
      to a predefinend level. When the criteria for stopping the battery testing is reached, the 
      charge voltage is increased to commence normal charging."
   ::= { dcSystemTraps 19 }

alarmBatteryBoostmodeEnteredTrap  NOTIFICATION-TYPE
   OBJECTS { alarmBatteryBoostmodeEntered }
   STATUS     current
   DESCRIPTION 
      "The system has increased the battery charge voltage in order to equalize the 
      battery cells charging. When the criteria for stopping the battery equalizing is reached, 
      the charge voltage is lowered to commence normal charging."
   ::= { dcSystemTraps 20 }

alarmController1proginputTrap  NOTIFICATION-TYPE
   OBJECTS { inputUserConfigurable1 }
   STATUS     current
   DESCRIPTION 
      "Generic alarm linked to user specified alarms. These have no specific name in the MIB. 
      User configurable alarms will on some systems have text attached to the traps 
      that explains the purpose of the alarm. "
   ::= { dcSystemTraps 21 }

alarmController2proginputTrap  NOTIFICATION-TYPE
   OBJECTS { inputUserConfigurable2 }
   STATUS     current
   DESCRIPTION 
      "Generic alarm linked to user specified alarms. These have no specific name in the MIB. 
      User configurable alarms will on some systems have text attached to the traps 
      that explains the purpose of the alarm. "
   ::= { dcSystemTraps 22 }

alarmController3proginputTrap  NOTIFICATION-TYPE
   OBJECTS { inputUserConfigurable3 }
   STATUS     current
   DESCRIPTION 
      "Generic alarm linked to user specified alarms. These have no specific name in the MIB. 
      User configurable alarms will on some systems have text attached to the traps 
      that explains the purpose of the alarm. "
   ::= { dcSystemTraps 23 }

alarmController4proginputTrap  NOTIFICATION-TYPE
   OBJECTS { inputUserConfigurable4 }
   STATUS     current
   DESCRIPTION 
      "Generic alarm linked to user specified alarms. These have no specific name in the MIB. 
      User configurable alarms will on some systems have text attached to the traps 
      that explains the purpose of the alarm. "
   ::= { dcSystemTraps 24 }

alarmController5proginputTrap  NOTIFICATION-TYPE
   OBJECTS { inputUserConfigurable5 }
   STATUS     current
   DESCRIPTION 
      "Generic alarm linked to user specified alarms. These have no specific name in the MIB. 
      User configurable alarms will on some systems have text attached to the traps 
      that explains the purpose of the alarm. "
   ::= { dcSystemTraps 25 }

alarmController6proginputTrap  NOTIFICATION-TYPE
   OBJECTS { inputUserConfigurable6 }
   STATUS     current
   DESCRIPTION 
      "Generic alarm linked to user specified alarms. These have no specific name in the MIB. 
      User configurable alarms will on some systems have text attached to the traps 
      that explains the purpose of the alarm. "
   ::= { dcSystemTraps 26 }

alarmController7proginputTrap  NOTIFICATION-TYPE
   OBJECTS { inputUserConfigurable7 }
   STATUS     current
   DESCRIPTION 
      "Generic alarm linked to user specified alarms. These have no specific name in the MIB. 
      User configurable alarms will on some systems have text attached to the traps 
      that explains the purpose of the alarm. "
   ::= { dcSystemTraps 27 }

alarmController8proginputTrap  NOTIFICATION-TYPE
   OBJECTS { inputUserConfigurable8 }
   STATUS     current
   DESCRIPTION 
      "Generic alarm linked to user specified alarms. These have no specific name in the MIB. 
      User configurable alarms will on some systems have text attached to the traps 
      that explains the purpose of the alarm. "
   ::= { dcSystemTraps 28 }

END


-- This MIB was created using NuDesign Team's Visual MIBuilder (Ver 4.4).

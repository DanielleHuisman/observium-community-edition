-- Mon Aug 8 2016: Added support for inverter, grid inverter and rectiverter.
-- 
-- $Revision:88$
-- $Author: jujino$
-- $Archive: Documents/EltekEnexusPowersystem.mib$
-- $Date: 4. mars 2021 13:56:51$
-- 

SP2-MIB DEFINITIONS ::= BEGIN

IMPORTS
	NOTIFICATION-TYPE, OBJECT-TYPE, MODULE-IDENTITY, 
	enterprises, Unsigned32, Counter32, Integer32
		FROM SNMPv2-SMI
	NOTIFICATION-GROUP
		FROM SNMPv2-CONF
	DateAndTime, DisplayString
		FROM SNMPv2-TC;

eltek MODULE-IDENTITY
	LAST-UPDATED "201306271334Z"
	ORGANIZATION 
		"ELTEK power System MIB Working Group"
	CONTACT-INFO 
		"Eltek R&D.
		         Postal: Eltek AS
		         P.O. Box 3043
		         N-3003 Drammen
		         Norway
		         Tel: +47-32 20 32 00
		         Fax: +47-32 20 31 20
		         web:  www.eltek.com
		         "
	DESCRIPTION 
		"An ongoing effort toward a generic MIB for all ELTEK products.
		         Branch overview:
		         Aeongold branch will be 1
		         AL175 branch will be 2
		         AL6000 branch will be 3
		         Internal used branch will be 4
		         Internal used branch will be 5
		         OEM Smartpack branch will be 6
		         ELTEK Common branch will be 7 (SmartPack, MCU, AEON w/WebPower sw V2.x)
		         ELTEK Distributed branch will be 8 (SmartPack w/WebPower sw V3.x)
		         ELTEK Distributed V2 branch will be 9 (SmartPack w/WebPower sw V4.0)
		         ELTEK Distributed V3 branch will be 9 (SmartPack w/WebPower sw V4.1)
		         ELTEK Distributed V4 branch will be 9 (SmartPack w/WebPower sw V4.1, V4.2, V4.3, V4.5 and compack V1.0, V1.01, V1.02, V1.03)
		         ELTEK Distributed V5 branch will be 9 (SmartPack w/WebPower sw V4.1, V4.2, V4.3, V4.5, V4.6)
		         ELTEK Distributed V6 branch will be 9 (SmartPack2 sw V1.1, V1.2, V1.3)
		         ELTEK Distributed V7 branch will be 9 (SmartPack w/WebPower sw V4.1, V4.2, V4.3, V4.5, V4.6, V4.7 and compack V1.04, V1.05)
		         ELTEK eNexus MIB branch will be 10 (SmartPack2 Touch V2.x, Smartpack R V2.x, SmartPack2 V2.x, SmartPack S V2.x and Compack V2.x)
		         ELTEK Brasil office will have branch 11 
		         ELTEK BMS-EM MIB will have branch 12
		         ELTEK TELMEX MIB will have branch 13
		         ELTEK MSM MIB will have branch 14
		                        "

	REVISION "201306271033Z"
	DESCRIPTION 
		"added support for rectifier group, mains group, battery group and flexi monitor"

	REVISION "201111250958Z"
	DESCRIPTION 
		"additional values to all alarm status enums"

	REVISION "201110171334Z"
	DESCRIPTION 
		"Major changes in OID order and names; added mains monitor energy log and generator fail status"

	REVISION "201108190916Z"
	DESCRIPTION 
		"hopefully final version. Stared implementation of eltek api"

	REVISION "201108190947Z"
	DESCRIPTION 
		"adjustment"

	REVISION "201109051128Z"
	DESCRIPTION 
		"fixed up mains group"
::= { enterprises 12148 }


-- Supported by SmartPack2 Touch, Smartpack R, SmartPack2, Smartpack S and Compack products
-- SNMP V1,V2c and V3.
-- 

eNexus               OBJECT IDENTIFIER ::= { eltek 10 }

-- This branch contains all tables and oid's needed for Eltek's trap system

eltekTraps           OBJECT IDENTIFIER ::= { eNexus 1 }

-- These are variable bindings used by the traps defined in  powerSystemTraps branch. 

powerAlarmVars       OBJECT IDENTIFIER ::= { eltekTraps 1 }

-- The generic Subsystem Traps, a generic trap for each sub system.
-- There are many alarm sources for each subsystem.
-- 
--  A list of the power plant subsystems:
-- 
--  1. Battery
--  2. Load
--  3. Mains
--  4. Rectifiers
--  5. ControlSystem
--  6. DcDc
--  7. Inputs
--  8. Generator
--  9. solarCharger
--  10. windcharger
--  11. inverter
-- 
-- Each trap contains subsystem status, text description of the alarm source, 
-- alarm status var, subsystem Status OID, subsystem Status Value, 
-- OID of the variable indicated the Measured value and the Measured value itself.

powerSystemTraps     OBJECT IDENTIFIER ::= { eltekTraps 2 }

-- This branch contains OID's for configuration of the power system's
-- basic factory data and the power system's installation settings.
-- 
-- 

powerSystem          OBJECT IDENTIFIER ::= { eNexus 2 }

-- This branch contains OIDs related to the Mains/AC feed subsystem. 
-- Here you will find info about mains status, voltages, currents, fuses, and mains monitor units

mains                OBJECT IDENTIFIER ::= { eNexus 3 }

-- This is the monitor of number of failed phase(s), which is(are) in major or minor low alarm.

mainsMainsFailure    OBJECT IDENTIFIER ::= { mains 2 }

-- This branch contains information about AC Mains Monitor control unit.

mainsMonitors        OBJECT IDENTIFIER ::= { mains 5 }

-- This branch contains mains outage/running time log depending on the log mode.

mainsOutageLog       OBJECT IDENTIFIER ::= { mains 6 }

-- This branch contains OIDs related to the systems (Diesel)Generator subsystem. 
-- Here you will find info about the generator running status, start/stop criteria, fuel tank monitoring, 
-- and energy delivery history. 
-- 

generator            OBJECT IDENTIFIER ::= { eNexus 4 }

-- This branch contains information about generator energy logs.

generatorEnergyLog   OBJECT IDENTIFIER ::= { generator 23 }

-- This branch contains information about generator running hours.

generatorRunHoursLog  OBJECT IDENTIFIER ::= { generator 24 }

-- This branch contains information about generator fuel consumption.

generatorFuelConsumptionLog  OBJECT IDENTIFIER ::= { generator 25 }

-- DSE Generator

gseGenerator         OBJECT IDENTIFIER ::= { generator 26 }

-- This is the monitor of generator failure

generatorFailure     OBJECT IDENTIFIER ::= { generator 27 }

-- This branch contains OIDs related to the Rectifiers subsystem. 
-- Here you will find info about the rectifiers status, capacity and health, currents and 
-- energy consumption history
-- 

rectifiers           OBJECT IDENTIFIER ::= { eNexus 5 }

-- This branch contains information about the total rectifier current, which is calculated 
-- by summing up current from each rectifier.

rectifiersCurrent    OBJECT IDENTIFIER ::= { rectifiers 2 }

-- This branch contains information about the used rectifier capacity.

rectifiersCapacity   OBJECT IDENTIFIER ::= { rectifiers 3 }

-- This branch contains information about the rectifier error monitor.

rectifiersError      OBJECT IDENTIFIER ::= { rectifiers 4 }

-- This branch contains information about rectifiers' energy logs.

rectifiersEnergyLog  OBJECT IDENTIFIER ::= { rectifiers 7 }

-- Show The highest value of the rectifier temperature measurements

rectifiersTemperature  OBJECT IDENTIFIER ::= { rectifiers 18 }

-- This branch contains OIDs related to the DCDC converter subsystem. 
-- Here you will find info about the dcdc status, capacity and health, currents and 
-- converted-energy history

dcdc                 OBJECT IDENTIFIER ::= { eNexus 6 }

-- This branch is obsolete.

dcdcObsolete         OBJECT IDENTIFIER ::= { dcdc 7 }

-- This branch contains OIDs related to the Solar charger subsystem. 
-- Here you will find info about the Solar charger status, capacity and health, currents and 
-- energy delivery history
-- 

solarChargers        OBJECT IDENTIFIER ::= { eNexus 7 }

-- This branch contains information about the total solar current.

solarChargersCurrent  OBJECT IDENTIFIER ::= { solarChargers 2 }

-- This branch is obsolete.

solarChargersObsolete  OBJECT IDENTIFIER ::= { solarChargers 3 }

-- This branch contains information about the solar error monitor.

solarChargersError   OBJECT IDENTIFIER ::= { solarChargers 4 }

-- This branch contains information about solar chargers' energy logs.

solarChargersEnergyLog  OBJECT IDENTIFIER ::= { solarChargers 7 }

-- This branch contains OIDs related to the Wind charger subsystem. 
-- Here you will find info about the Wind charger status, capacity and health, currents and 
-- energy delivery history

windChargers         OBJECT IDENTIFIER ::= { eNexus 8 }

-- This branch contains information about the total wind current.

windChargersCurrent  OBJECT IDENTIFIER ::= { windChargers 2 }

-- This branch is obsolete.

windChargersObsolete  OBJECT IDENTIFIER ::= { windChargers 3 }

-- This branch contains information about the wind error monitor.

windChargersError    OBJECT IDENTIFIER ::= { windChargers 4 }

-- This branch contains information about wind chargers' energy logs.

windChargersEnergyLog  OBJECT IDENTIFIER ::= { windChargers 7 }

-- This branch contains OIDs related to the Load subsystem. 
-- Here you will find info about load status, currents, fuses,  contactors
-- and load monitor units
-- 

load                 OBJECT IDENTIFIER ::= { eNexus 9 }

-- This is the monitor of total load current

loadCurrent          OBJECT IDENTIFIER ::= { load 2 }

-- This branch contains information about load energy logs.

loadEnergyLog        OBJECT IDENTIFIER ::= { load 8 }

-- This branch contains all avalable information about the power systems battery subsystem.
-- Here is data about battery health, condition, test results, monitoring equipment battery banks/strings, 
-- battery breakers and disconnection systems. 
-- Note that this branch represents battery group 1 in a system with battery groups.

battery              OBJECT IDENTIFIER ::= { eNexus 10 }

-- This is one of many 'data monitors' found throughout the power system.  
-- The 'data monitors' is found on several levels on all subsystems and they all act as 
-- trap sources. Whenever a status changes in a 'data monitor', a trap in its parent
-- subsystem may be sendt.  The data monitor branches can easily be recognised by the 
-- presence of a xxxxTrapRepeatCounter node.

batteryVoltage       OBJECT IDENTIFIER ::= { battery 5 }

-- This is the total battery current.

batteryCurrents      OBJECT IDENTIFIER ::= { battery 6 }

-- Show The highest value of the enabled battery temperature measurements

batteryTemperatures  OBJECT IDENTIFIER ::= { battery 7 }

-- This is the estimated battery remaining discharge time until battery disconnection.

batteryTimeLeft      OBJECT IDENTIFIER ::= { battery 8 }

-- This is the remaining capacity before battery disconnection.

batteryRemainingCapacity  OBJECT IDENTIFIER ::= { battery 9 }

-- This is the used battery capacity

batteryUsedCapacity  OBJECT IDENTIFIER ::= { battery 10 }

-- This is the total battery capacity estimated from the latest battery test result.

batteryTotalCapacity  OBJECT IDENTIFIER ::= { battery 11 }

-- The battery quality is calculated from the latest battery test.

batteryQuality       OBJECT IDENTIFIER ::= { battery 12 }

-- This branch contains OIDs related to the Battery Disconnect. 

batteryLVBD          OBJECT IDENTIFIER ::= { battery 13 }

-- This branch contains information about battery charge current limit.

batteryChargeCurrentLimit  OBJECT IDENTIFIER ::= { battery 14 }

-- This branch contains information about battery boost

batteryBoost         OBJECT IDENTIFIER ::= { battery 15 }

-- This branch contains information about battery test

batteryTest          OBJECT IDENTIFIER ::= { battery 16 }
batteryTempComp      OBJECT IDENTIFIER ::= { battery 17 }

-- This brance contains information about battery banks

batteryBank          OBJECT IDENTIFIER ::= { battery 18 }

-- This branch contains information about battery monitor control unit.

batteryMonitors      OBJECT IDENTIFIER ::= { battery 19 }

-- This branch contains information about battery energy logs.

batteryEnergyLog     OBJECT IDENTIFIER ::= { battery 20 }

-- This branch contains information about battery discharge cycle logs.

batteryCycleLog      OBJECT IDENTIFIER ::= { battery 21 }

-- This branch contains information about battery Equalize

batteryEqualize      OBJECT IDENTIFIER ::= { battery 22 }

-- The ah (x100) battery has been charged.

batteryAhCharged     OBJECT IDENTIFIER ::= { battery 23 }

-- The ah (x100) battery has been discharged.

batteryAhDischarged  OBJECT IDENTIFIER ::= { battery 24 }

-- This branch contains information about battery run time logs.

batteryRunTimeLog    OBJECT IDENTIFIER ::= { battery 25 }

-- information of battery modules

batteryModule        OBJECT IDENTIFIER ::= { battery 26 }

-- This branch contains information about the battery error monitor.

batteryModuleError   OBJECT IDENTIFIER ::= { batteryModule 2 }

-- This branch contains information about the battery comm error monitor.

batteryModuleCommError  OBJECT IDENTIFIER ::= { batteryModule 3 }

-- This branch is a container for the status of programmable inputs for
-- control units and I/O units.  The two dimensional tables are double indexed.
-- Input number index and control unit index. Note that the inputs should not be
-- configurated in this table if the physical inputs are already used as other system
-- inputs, for example battery temperature.

inputs               OBJECT IDENTIFIER ::= { eNexus 11 }

-- This branch contains OIDs related to the systems Alarm output relays status. 
-- 

outputs              OBJECT IDENTIFIER ::= { eNexus 12 }

-- This branch contains OIDs related to the Controlsystem subsystem. 
-- Here you will find info about controller status and inventory. I/O units 
-- with outdoor related functionality is placed here. Current/Flexi Monitors with 
-- programmable system types and functionalities.There is also some pushbuttons for 
-- resetting alarms and reread system inventory. 

controlSystem        OBJECT IDENTIFIER ::= { eNexus 13 }

-- SNMP trap configurations

snmp                 OBJECT IDENTIFIER ::= { controlSystem 4 }

-- This branch contains information about IO unit.

controlSystemIoUnits  OBJECT IDENTIFIER ::= { controlSystem 7 }

-- This branch contains control system inventory, including control unit description, status, serial 
-- number, hardware part number, hardware version, software part number and software version.

controlSystemInventory  OBJECT IDENTIFIER ::= { controlSystem 8 }

-- This branch contains information about current monitor.

currentMonitors      OBJECT IDENTIFIER ::= { controlSystem 9 }

-- This branch contains information about flexi monitor.

flexiMonitors        OBJECT IDENTIFIER ::= { controlSystem 10 }

-- main controller (SP2 Basic Ind, SP2 Basic, Compack, Smartpack S and Smartpack R. Note: There is no earth fault detection on Smartpack R)

mainControlUnits     OBJECT IDENTIFIER ::= { controlSystem 11 }

-- control units error monitors

controlSystemSummary  OBJECT IDENTIFIER ::= { controlSystem 12 }

-- This is the monitor of number of failed main controllers(SP2 Basic Ind, SP2 Basic, Compack, Smartpack S), which is(are) lost communication.

mainControlUnitsError  OBJECT IDENTIFIER ::= { controlSystemSummary 1 }

-- This is the monitor of number of failed smartnodes, which is(are) lost communication.

smartNodeError       OBJECT IDENTIFIER ::= { controlSystemSummary 2 }

-- This is the monitor of number of failed battery monitors,which is(are) lost communication.

batteryMonitorError  OBJECT IDENTIFIER ::= { controlSystemSummary 3 }

-- This is the monitor of number of failed load monitors,which is(are) lost communication.

loadMonitorError     OBJECT IDENTIFIER ::= { controlSystemSummary 4 }

-- This is the monitor of number of failed IO units,which is(are) lost communication.

ioUnitError          OBJECT IDENTIFIER ::= { controlSystemSummary 5 }

-- This is the monitor of number of failed mains monitors,which is(are) lost communication.

mainsMonitorError    OBJECT IDENTIFIER ::= { controlSystemSummary 6 }

-- This is the monitor of number of failed flexi monitors,which is(are) lost communication.

flexiMonitorError    OBJECT IDENTIFIER ::= { controlSystemSummary 7 }

-- Show The highest value of the enabled ambient temperature measurements

ambientTemperature   OBJECT IDENTIFIER ::= { controlSystem 13 }

-- Show the difference value of the battery temperature and ambient temperature

deltaTemperature     OBJECT IDENTIFIER ::= { controlSystem 14 }

-- This is the monitor of number of failed attempt of user log-in.

userSuspended        OBJECT IDENTIFIER ::= { controlSystem 15 }

-- Information regarding demand response

demandResponse       OBJECT IDENTIFIER ::= { controlSystem 25 }

-- Information regarding tariff control

tariffControl        OBJECT IDENTIFIER ::= { controlSystem 31 }

-- This branch contains OIDs related to the systems alarm groups. The alarm groups are internal entities 
-- that serves as input sources for the Alarm outputs

alarmGroups          OBJECT IDENTIFIER ::= { eNexus 14 }

-- This branch contains all avalable information about the battery group 2 in a system with battery groups.
-- Here is data about battery health, condition, test results, monitoring equipment battery banks/strings, 
-- battery breakers and disconnection systems.

batteryGroup2        OBJECT IDENTIFIER ::= { eNexus 15 }

-- This is one of many 'data monitors' found throughout the power system.  
-- The 'data monitors' is found on several levels on all subsystems and they all act as 
-- trap sources. Whenever a status changes in a 'data monitor', a trap in its parent
-- subsystem may be sendt.  The data monitor branches can easily be recognised by the 
-- presence of a xxxxTrapRepeatCounter node.

batteryGroup2Voltage  OBJECT IDENTIFIER ::= { batteryGroup2 5 }

-- This is the total battery current of battery group 2

batteryGroup2Currents  OBJECT IDENTIFIER ::= { batteryGroup2 6 }

-- Show The highest value of the enabled battery temperature measurements of battery group 2.

batteryGroup2Temperatures  OBJECT IDENTIFIER ::= { batteryGroup2 7 }

-- This is the estimated battery remaining discharge time of battery group 2 until battery disconnection.

batteryGroup2TimeLeft  OBJECT IDENTIFIER ::= { batteryGroup2 8 }

-- This is the remaining capacity of battery group 2 before battery disconnection.

batteryGroup2RemainingCapacity  OBJECT IDENTIFIER ::= { batteryGroup2 9 }

-- This is the used battery capacity of battery group 2

batteryGroup2UsedCapacity  OBJECT IDENTIFIER ::= { batteryGroup2 10 }

-- This is the total battery capacity of battery group 2, estimated from the latest battery test result.

batteryGroup2TotalCapacity  OBJECT IDENTIFIER ::= { batteryGroup2 11 }

-- The battery quality is calculated from the latest battery test.

batteryGroup2Quality  OBJECT IDENTIFIER ::= { batteryGroup2 12 }

-- This branch contains OIDs related to the Battery Disconnect of battery group 2. 

batteryGroup2LVBD    OBJECT IDENTIFIER ::= { batteryGroup2 13 }

-- This branch contains information about battery charge current limit.

batteryGroup2ChargeCurrentLimit  OBJECT IDENTIFIER ::= { batteryGroup2 14 }

-- This branch contains information about battery boost of battery group 2

batteryGroup2Boost   OBJECT IDENTIFIER ::= { batteryGroup2 15 }

-- This branch contains information about battery test of battery group 2

batteryGroup2Test    OBJECT IDENTIFIER ::= { batteryGroup2 16 }
batteryGroup2TempComp  OBJECT IDENTIFIER ::= { batteryGroup2 17 }

-- This brance contains information about battery banks of battery group 2

batteryGroup2Bank    OBJECT IDENTIFIER ::= { batteryGroup2 18 }

-- This branch contains information about battery energy logs of battery group 2.

batteryGroup2EnergyLog  OBJECT IDENTIFIER ::= { batteryGroup2 19 }

-- This branch contains information about battery discharge cycle logs of battery group 2.

batteryGroup2CycleLog  OBJECT IDENTIFIER ::= { batteryGroup2 20 }

-- This branch contains information about battery Equalize of battery group 2.

batteryGroup2Equalize  OBJECT IDENTIFIER ::= { batteryGroup2 21 }

-- The ah (x100) battery has been charged for battery group 2.

batteryGroup2AhCharged  OBJECT IDENTIFIER ::= { batteryGroup2 22 }

-- The ah (x100) battery has been discharged for battery group 2.

batteryGroup2AhDischarged  OBJECT IDENTIFIER ::= { batteryGroup2 23 }

-- This branch contains OIDs related to the Inverters subsystem. 
-- Here you will find info about the inverters status, capacity and health, currents and 
-- energy consumption history
-- 

inverters            OBJECT IDENTIFIER ::= { eNexus 16 }

-- This branch contains information about the inverter error monitor.

invertersError       OBJECT IDENTIFIER ::= { inverters 2 }

-- Show The highest value of the rectifier temperature measurements

invertersTemperature  OBJECT IDENTIFIER ::= { inverters 3 }

-- This branch contains information about the ac current from phase 1.

invertersAcCurrent1  OBJECT IDENTIFIER ::= { inverters 4 }

-- This branch contains information about the ac current from phase 2.

invertersAcCurrent2  OBJECT IDENTIFIER ::= { inverters 5 }

-- This branch contains information about the ac current from phase 3.

invertersAcCurrent3  OBJECT IDENTIFIER ::= { inverters 6 }

-- This branch contains information about the ac voltage of phase 1.

invertersAcVoltage1  OBJECT IDENTIFIER ::= { inverters 7 }

-- This branch contains information about theac voltage of phase 2.

invertersAcVoltage2  OBJECT IDENTIFIER ::= { inverters 8 }

-- This branch contains information about theac voltage of phase 3.

invertersAcVoltage3  OBJECT IDENTIFIER ::= { inverters 9 }

-- This branch contains information about the ac frequency.

invertersAcFrequencyDeviation  OBJECT IDENTIFIER ::= { inverters 10 }

-- This branch contains OIDs related to the grid inverters subsystem. 
-- Here you will find info about the inverters status, capacity and health, currents and 
-- energy consumption history
-- 

gridInvertersObsolete  OBJECT IDENTIFIER ::= { eNexus 17 }

-- This branch contains OIDs related to the Rectiverters subsystem. 
-- Here you will find info about the rectifiers status, capacity and health, currents and 
-- energy consumption history
-- 

rectiverters         OBJECT IDENTIFIER ::= { eNexus 18 }

-- This branch contains information about the total rectifier current, which is calculated 
-- by summing up current from each rectifier.

rectivertersDcCurrent  OBJECT IDENTIFIER ::= { rectiverters 2 }

-- This branch contains information about the rectifier error monitor.

rectivertersError    OBJECT IDENTIFIER ::= { rectiverters 3 }

-- Show The highest value of the rectifier temperature measurements

rectivertersTemperature  OBJECT IDENTIFIER ::= { rectiverters 4 }

-- This branch contains information about the total rectifier current, which is calculated 
-- by summing up current from each rectifier.

rectivertersAcOutCurrent1  OBJECT IDENTIFIER ::= { rectiverters 5 }

-- This branch contains information about the total rectifier current, which is calculated 
-- by summing up current from each rectifier.

rectivertersAcOutCurrent2  OBJECT IDENTIFIER ::= { rectiverters 6 }

-- This branch contains information about the total rectifier current, which is calculated 
-- by summing up current from each rectifier.

rectivertersAcOutCurrent3  OBJECT IDENTIFIER ::= { rectiverters 7 }

-- This branch contains information about the total rectifier current, which is calculated 
-- by summing up current from each rectifier.

rectivertersAcOutVoltage1  OBJECT IDENTIFIER ::= { rectiverters 8 }

-- This branch contains information about the total rectifier current, which is calculated 
-- by summing up current from each rectifier.

rectivertersAcOutVoltage2  OBJECT IDENTIFIER ::= { rectiverters 9 }

-- This branch contains information about the total rectifier current, which is calculated 
-- by summing up current from each rectifier.

rectivertersAcOutVoltage3  OBJECT IDENTIFIER ::= { rectiverters 10 }

-- This branch contains information about the total rectifier current, which is calculated 
-- by summing up current from each rectiverter.

rectivertersAcFrequencyDeviation  OBJECT IDENTIFIER ::= { rectiverters 11 }
fuelCells            OBJECT IDENTIFIER ::= { eNexus 19 }

-- This branch contains information about the total fuel cell current.

fuelCellsCurrent     OBJECT IDENTIFIER ::= { fuelCells 2 }

-- This branch is obsolete.

fuelCellsPower       OBJECT IDENTIFIER ::= { fuelCells 3 }

-- This branch contains information about the fuel cell error monitor.

fuelCellsError       OBJECT IDENTIFIER ::= { fuelCells 4 }

-- This branch contains information about fuel cell chargers' energy logs.

fuelCellsEnergyLog   OBJECT IDENTIFIER ::= { fuelCells 7 }

alarmSubsysSourceDescr  OBJECT-TYPE
	SYNTAX     DisplayString (SIZE(0..32))
	MAX-ACCESS accessible-for-notify
	STATUS     current
	DESCRIPTION 
		"A description of the source generating the trap for the Alarm Condition. 
		Used in alarmSubSystemTrap to describe the alarm source. 
		Example: 'batteryVoltageDescription'"
	::= { powerAlarmVars 1 }

-- status var and value of trap variables
-- 

alarmSubsysStatusOid  OBJECT-TYPE
	SYNTAX     OBJECT IDENTIFIER
	MAX-ACCESS accessible-for-notify
	STATUS     current
	DESCRIPTION 
		"The OID (name) of the object indicating the alarm-status for which the alarm is 
		generated.  The Status must be an INTEGER  type.
		
		Example: SP2-MIB::batteryVoltage.batteryVoltageStatus
		1.3.6.1.4.1.12148.10.3.5.2:
		
		This object maybe polled by the SNMP management application,
		to monitor the current Status object."
	::= { powerAlarmVars 2 }

alarmSubsysStatusValue  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS accessible-for-notify
	STATUS     current
	DESCRIPTION 
		"The value of the Status object of the subsystem for which the
		alarm-status is generated. The OID (name) of this object is
		indicated by alarmSubsysStatusOid above.
		
		
		Example: the value of SP2-MIB::batteryVoltage.batteryVoltageStatus
		one of: error (0), normal (1), minorAlarm (2), etc."
	::= { powerAlarmVars 3 }

alarmSubsysStatusOnOff  OBJECT-TYPE
	SYNTAX     INTEGER {
		off (0),
		on (1)
	}
	MAX-ACCESS accessible-for-notify
	STATUS     current
	DESCRIPTION 
		"This indicates if the abnormal condition is on or goes off."
	::= { powerAlarmVars 4 }

-- measured var and value of trap variables
-- 

alarmMeasuredVarOid  OBJECT-TYPE
	SYNTAX     OBJECT IDENTIFIER
	MAX-ACCESS accessible-for-notify
	STATUS     current
	DESCRIPTION 
		"The OID (name) of the measured-object indicating some
		measurement (e.g voltage) for which the alarm is generated.
		
		Example: SP2-MIB::batteryVoltage.batteryVoltageValue
		1.3.6.1.4.1.12148.10.3.5.1
		
		This object maybe polled by the SNMP management application,
		to monitor the current measurement."
	::= { powerAlarmVars 5 }

alarmMeasuredVarValue  OBJECT-TYPE
	SYNTAX     Integer32
	MAX-ACCESS accessible-for-notify
	STATUS     current
	DESCRIPTION 
		"The value of the measured-object for which the alarm-status
		is generated, for example 13 volt. The actual value is in
		units defined by the actual variable (e.g volts). The units
		must use INTEGER type.
		
		The OID (name) of this object is indicated by
		alarmMeasuredVarOid above.
		
		Example: Value of SP2-MIB::batteryVoltage.batteryVoltageValue
		'The measured battery voltage'"
	::= { powerAlarmVars 6 }

alarmTrapCounterVarValue  OBJECT-TYPE
	SYNTAX     Integer32
	MAX-ACCESS accessible-for-notify
	STATUS     current
	DESCRIPTION 
		""
	::= { powerAlarmVars 7 }

alarmTrapTime  OBJECT-TYPE
	SYNTAX     DateAndTime (SIZE(8..11))
	MAX-ACCESS accessible-for-notify
	STATUS     current
	DESCRIPTION 
		"Time stemp of trap"
	::= { powerAlarmVars 8 }

-- 

alarmPowerSystemTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue, 
		alarmTrapTime }
	STATUS     current
	DESCRIPTION 
		"This Trap is sent when an alarm condition occurs in the power system."
	::= { powerSystemTraps 1 }

-- alarm subsystem-name (Battery, Load, etc.)
-- text description of the alarm source
-- alarm status var
-- subsystem Status OID
-- subsystem Status Value
-- measured var
-- OID of the variable indicated the Measured value
-- Measured value

alarmBatteryTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue, 
		alarmTrapTime }
	STATUS     current
	DESCRIPTION 
		"This Trap is sent when an alarm condition occurs in the battery subsystem."
	::= { powerSystemTraps 2 }

-- alarm subsystem-name (Battery, Load, etc.)
-- text description of the alarm source
-- alarm status var
-- subsystem Status OID
-- subsystem Status Value
-- measured var
-- OID of the variable indicated the Measured value
-- Measured value

alarmLoadGroupTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue, 
		alarmTrapTime }
	STATUS     current
	DESCRIPTION 
		"This Trap is sent when an alarm condition occurs in the Load subsystem."
	::= { powerSystemTraps 3 }

-- alarm subsystem-name (Battery, Load, etc.)
-- text description of the alarm source
-- alarm status var
-- subsystem Status OID
-- subsystem Status Value
-- measured var
-- OID of the variable indicated the Measured value
-- Measured value

alarmMainsTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue, 
		alarmTrapTime }
	STATUS     current
	DESCRIPTION 
		"This Trap is sent when an alarm condition occurs in the Mains subsystem."
	::= { powerSystemTraps 4 }

-- alarm subsystem-name (Battery, Load, etc.)
-- text description of the alarm source
-- alarm status var
-- subsystem Status OID
-- subsystem Status Value
-- measured var
-- OID of the variable indicated the Measured value
-- Measured value

alarmRectifierTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue, 
		alarmTrapTime }
	STATUS     current
	DESCRIPTION 
		"This Trap is sent when an alarm condition occurs in the Rectifier subsystem."
	::= { powerSystemTraps 5 }

-- alarm subsystem-name (Battery, Load, etc.)
-- text description of the alarm source
-- alarm status var
-- subsystem Status OID
-- subsystem Status Value
-- measured var
-- OID of the variable indicated the Measured value
-- Measured value

alarmControlSystemTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue, 
		alarmTrapTime }
	STATUS     current
	DESCRIPTION 
		"This Trap is sent when an alarm condition occurs in the Control-system subsystem."
	::= { powerSystemTraps 6 }

-- alarm subsystem-name (Battery, Load, etc.)
-- text description of the alarm source
-- alarm status var
-- subsystem Status OID
-- subsystem Status Value
-- measured var
-- OID of the variable indicated the Measured value
-- Measured value

alarmDcDcTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue, 
		alarmTrapTime }
	STATUS     current
	DESCRIPTION 
		"This Trap is sent when an alarm condition occurs in the DCDC converter subsystem."
	::= { powerSystemTraps 7 }

-- alarm subsystem-name (Battery, Load, etc.)
-- text description of the alarm source
-- alarm status var
-- subsystem Status OID
-- subsystem Status Value
-- measured var
-- OID of the variable indicated the Measured value
-- Measured value

alarmInputsTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue, 
		alarmTrapTime }
	STATUS     current
	DESCRIPTION 
		"This Trap is sent when an alarm condition occurs in the Inputs subsystem."
	::= { powerSystemTraps 8 }

-- alarm subsystem-name (Battery, Load, etc.)
-- text description of the alarm source
-- alarm status var
-- subsystem Status OID
-- subsystem Status Value
-- measured var
-- OID of the variable indicated the Measured value
-- Measured value

alarmOutputsTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue, 
		alarmTrapTime }
	STATUS     current
	DESCRIPTION 
		"This Trap is sent when an alarm condition occurs in the Outputs subsystem."
	::= { powerSystemTraps 9 }

-- alarm subsystem-name (Battery, Load, etc.)
-- text description of the alarm source
-- alarm status var
-- subsystem Status OID
-- subsystem Status Value
-- measured var
-- OID of the variable indicated the Measured value
-- Measured value

alarmGeneratorTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue, 
		alarmTrapTime }
	STATUS     current
	DESCRIPTION 
		"This Trap is sent when an alarm condition occurs in the Generator subsystem."
	::= { powerSystemTraps 10 }

-- alarm subsystem-name (Battery, Load, etc.)
-- text description of the alarm source
-- alarm status var
-- subsystem Status OID
-- subsystem Status Value
-- measured var
-- OID of the variable indicated the Measured value
-- Measured value

alarmSolarChargerTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue, 
		alarmTrapTime }
	STATUS     current
	DESCRIPTION 
		"This Trap is sent when an alarm condition occurs in the SolarCharger subsystem."
	::= { powerSystemTraps 11 }

alarmWindChargerTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue, 
		alarmTrapTime }
	STATUS     current
	DESCRIPTION 
		"This Trap is sent when an alarm condition occurs in the WindCharger subsystem."
	::= { powerSystemTraps 12 }

infoHeartBeatTrap  NOTIFICATION-TYPE
	OBJECTS { alarmSubsysSourceDescr }
	STATUS     current
	DESCRIPTION 
		"When enabled, this trap will be transmitted at regular inervals. This trap is not
		intended to be an alarm but more like some information that the system is alive and
		the link is up."
	::= { powerSystemTraps 13 }

-- alarm subsystem-name (Battery, Load, etc.)
-- text description of the alarm source
-- alarm status var
-- subsystem Status OID
-- subsystem Status Value
-- measured var
-- OID of the variable indicated the Measured value
-- Measured value

alarmInverterTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue, 
		alarmTrapTime }
	STATUS     current
	DESCRIPTION 
		"This Trap is sent when an alarm condition occurs in the Inverter subsystem."
	::= { powerSystemTraps 14 }

-- alarm subsystem-name (Battery, Load, etc.)
-- text description of the alarm source
-- alarm status var
-- subsystem Status OID
-- subsystem Status Value
-- measured var
-- OID of the variable indicated the Measured value
-- Measured value

alarmGridInverterTrapObsolete  NOTIFICATION-TYPE
	STATUS     current
	DESCRIPTION 
		"This Trap is sent when an alarm condition occurs in the Grid Inverter subsystem."
	::= { powerSystemTraps 15 }

-- alarm subsystem-name (Battery, Load, etc.)
-- text description of the alarm source
-- alarm status var
-- subsystem Status OID
-- subsystem Status Value
-- measured var
-- OID of the variable indicated the Measured value
-- Measured value

alarmRectiverterTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue, 
		alarmTrapTime }
	STATUS     current
	DESCRIPTION 
		"This Trap is sent when an alarm condition occurs in the Rectiverter subsystem."
	::= { powerSystemTraps 16 }

infoBatteryTestTrap  NOTIFICATION-TYPE
	OBJECTS { alarmSubsysSourceDescr, 
		alarmSubsysStatusOnOff, 
		alarmTrapCounterVarValue, 
		alarmTrapTime }
	STATUS     current
	DESCRIPTION 
		"This Trap is sent when battery test is performed in the power system: 
		"
	::= { powerSystemTraps 17 }

alarmFuelCellTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue, 
		alarmTrapTime }
	STATUS     current
	DESCRIPTION 
		"This Trap is sent when an alarm condition occurs in the fuel cell subsystem."
	::= { powerSystemTraps 18 }

powerSystemStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"A status value showing the overall condition of the power system."
	::= { powerSystem 1 }

powerSystemType  OBJECT-TYPE
	SYNTAX     INTEGER {
		smartpack2 (1),
		smartpackS (2),
		compack (3),
		smartpack2Touch (4),
		smartpackR (5)
	}
	MAX-ACCESS read-only
	STATUS     current
	DESCRIPTION 
		"A value showing the type of the power system, which is named after the main controller."
	::= { powerSystem 2 }

powerSystemMode  OBJECT-TYPE
	SYNTAX     INTEGER {
		off (0),
		test (1),
		boost (2),
		float (3),
		emergency (4),
		startupdelay (5),
		equalize (6)
	}
	MAX-ACCESS read-only
	STATUS     current
	DESCRIPTION 
		"A summary status showing if the system is in test, boost, float, equalize, emergency or start-up delay mode
		"
	::= { powerSystem 3 }

powerSystemCompany  OBJECT-TYPE
	SYNTAX     DisplayString (SIZE(0..32))
	MAX-ACCESS read-write
	STATUS     current
	DESCRIPTION 
		"The Copmany name (as stored in the Control Unit)."
	::= { powerSystem 4 }

powerSystemSite  OBJECT-TYPE
	SYNTAX     DisplayString (SIZE(0..32))
	MAX-ACCESS read-write
	STATUS     current
	DESCRIPTION 
		"The system/site Location details (as stored in the Control Unit)."
	::= { powerSystem 5 }

powerSystemModel  OBJECT-TYPE
	SYNTAX     DisplayString (SIZE(0..32))
	MAX-ACCESS read-only
	STATUS     current
	DESCRIPTION 
		"The model/part number of the power system (as stored in the Control Unit)."
	::= { powerSystem 6 }

powerSystemSerialNumber  OBJECT-TYPE
	SYNTAX     DisplayString (SIZE(0..16))
	MAX-ACCESS read-write
	STATUS     current
	DESCRIPTION 
		"The serial number for the complete system."
	::= { powerSystem 7 }

powerSystemInstallDate  OBJECT-TYPE
	SYNTAX     DateAndTime
	MAX-ACCESS read-write
	STATUS     current
	DESCRIPTION 
		"The system's Installation date (as stored in the Control Unit)."
	::= { powerSystem 8 }

powerSystemNominalVoltage  OBJECT-TYPE
	SYNTAX     Integer32
	MAX-ACCESS read-only
	STATUS     current
	DESCRIPTION 
		"The nominal voltage rating. 12V/24V/48V/60V/110V/220V/380V etc. systems."
	::= { powerSystem 9 }

powerSystemLongitude  OBJECT-TYPE
	SYNTAX     Integer32 (-180..180)
	MAX-ACCESS read-write
	STATUS     current
	DESCRIPTION 
		"A part of the systems global positioning data. The range +-180degrees
		Longitude lines are imaginary lines running from the north pole to the south pole. 
		Longitudes are usually (WGS84) referenced from Greenwich, England where it has 
		been established as Zero Degrees longitude. Latitude and Longitude together with
		the Elevation can be used for automagically placing system icons on 
		NMS/Sitemonitors system that support this.  "
	::= { powerSystem 10 }

powerSystemLongitudeDecimal  OBJECT-TYPE
	SYNTAX     Integer32
	MAX-ACCESS read-write
	STATUS     current
	DESCRIPTION 
		"The decimal part of dcSystemLatitude contains up to 7digits. This number is 
		in 1/1000000 degree fractions or 0,0000001 degree. A part of the systems global 
		positioning data. Longitude lines are imaginary lines running from the north pole to
		the south pole.  Longitudes are usually (WGS84) referenced from Greenwich, England where it has 
		been established as Zero Degrees longitude. Latitude and Longitude together with
		the Elevation can be used for automagically placing system icons on 
		NMS/Sitemonitors system that support this.  "
	::= { powerSystem 11 }

powerSystemLatitude  OBJECT-TYPE
	SYNTAX     Integer32 (-90..90)
	MAX-ACCESS read-write
	STATUS     current
	DESCRIPTION 
		"A part of the systems global positioning data. The latitude gives the location of a place 
		on Earth (or other planetary body) north or south of the equator. Lines of Latitude has 
		a range of  +-90 degrees and are the imaginary horizontal lines shown running 
		east-to-west (or west to east).  Latitude and Longitude together with
		the Elevation can be used for automagically placing system icons on 
		NMS/Sitemonitors system that support this. "
	::= { powerSystem 12 }

powerSystemLatitudeDecimal  OBJECT-TYPE
	SYNTAX     Integer32
	MAX-ACCESS read-write
	STATUS     current
	DESCRIPTION 
		"The decimal part of dcSystemLatitude contains up to 7digits. This number is 
		in 1/1000000 degree fractions or 0,0000001 degree. A part of the systems global 
		positioning data.
		Lines of Latitude has a range of  +-90 degrees and are the imaginary horizontal 
		lines shown running east-to-west (or west to east).  Latitude and Longitude together with
		the Elevation can be used for automagically placing system icons on 
		NMS/Sitemonitors system that support this. 
		
		
		Longitude lines are imaginary lines running from the north pole to
		the south pole.
		 
		Longitudes are usually (WGS84) referenced from Greenwich, England where it has 
		been established as Zero Degrees longitude. Latitude and Longitude together with
		the Elevation can be used for automagically placing system icons on 
		NMS/Sitemonitors system that support this.  "
	::= { powerSystem 13 }

powerSystemElevation  OBJECT-TYPE
	SYNTAX     Integer32
	MAX-ACCESS read-write
	STATUS     current
	DESCRIPTION 
		"A part of the systems global positioning data. This is the sites height above sealevel in Meters.
		The  Elevation together with Latituse and Longitude is used for automagically placing
		system icons on NMS/Sitemonitors system that support this."
	::= { powerSystem 14 }

powerSystemCurrentDecimalSetting  OBJECT-TYPE
	SYNTAX     INTEGER {
		ampere (0),
		deciAmpere (1)
	}
	MAX-ACCESS read-write
	STATUS     current
	DESCRIPTION 
		"A global flag telling if the current values in the system is Amperes or DeciAmpres"
	::= { powerSystem 15 }

powerSystemTemperatureScale  OBJECT-TYPE
	SYNTAX     INTEGER {
		celcius (0),
		fahrenheit (1)
	}
	MAX-ACCESS read-write
	STATUS     current
	DESCRIPTION 
		"A flag telling if the temperatures values in the system is of Celcius or Fahrenheit type"
	::= { powerSystem 16 }

powerSystemCapacityScale  OBJECT-TYPE
	SYNTAX     INTEGER {
		ah (0),
		percent (1)
	}
	MAX-ACCESS read-write
	STATUS     current
	DESCRIPTION 
		"A flag telling if the system's battery capacity value is a percentage
		of a fully charged battery, or in AmpereHours"
	::= { powerSystem 17 }

powerSystemEnergySource  OBJECT-TYPE
	SYNTAX     INTEGER {
		off (0),
		grid (1),
		generator (2),
		battery (3),
		solar (4),
		wind (5),
		fuelcell (6)
	}
	MAX-ACCESS read-only
	STATUS     current
	DESCRIPTION 
		"Show the energy source that currently powering the system."
	::= { powerSystem 18 }

mainsStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of mains/AC feed subsystem."
	::= { mains 1 }

mainsMainsFailureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed phases is higher than the defined alarm level."
	::= { mainsMainsFailure 1 }

mainsMainsFailureDescription  OBJECT-TYPE
	SYNTAX     DisplayString (SIZE(0..16))
	MAX-ACCESS read-write
	STATUS     current
	DESCRIPTION 
		"A textual description of the mains phase failure monitor. This is stored in the system controller
		and can be changed by the user."
	::= { mainsMainsFailure 2 }

mainsMainsFailureTrapRepeatCounter  OBJECT-TYPE
	SYNTAX     Integer32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { mainsMainsFailure 3 }

mainsMainsFailureAlarmEnable  OBJECT-TYPE
	SYNTAX     INTEGER {
		disabled (0),
		enabled (1)
	}
	MAX-ACCESS read-write
	STATUS     current
	DESCRIPTION 
		"This value once enabled, the alarm condition of the monitor will be reported."
	::= { mainsMainsFailure 4 }

mainsMainsFailureValue  OBJECT-TYPE
	SYNTAX     Integer32
	MAX-ACCESS read-only
	STATUS     current
	DESCRIPTION 
		"The detected number of failed phases."
	::= { mainsMainsFailure 5 }

mainsMainsFailureMajorAlarmLevel  OBJECT-TYPE
	SYNTAX     Integer32
	MAX-ACCESS read-write
	STATUS     current
	DESCRIPTION 
		"The major alarm limit"
	::= { mainsMainsFailure 6 }

mainsMainsFailureMinorAlarmLevel  OBJECT-TYPE
	SYNTAX     Integer32
	MAX-ACCESS read-write
	STATUS     current
	DESCRIPTION 
		"The minor alarm limit"
	::= { mainsMainsFailure 7 }

mainsNumberOfPhases  OBJECT-TYPE
	SYNTAX     Integer32
	MAX-ACCESS read-write
	STATUS     current
	DESCRIPTION 
		"This value showing the number of phases of the mains subsystem."
	::= { mains 3 }

mainsVoltageTable  OBJECT-TYPE
	SYNTAX SEQUENCE OF MainsVoltageEntry
	MAX-ACCESS not-accessible
	STATUS     current
	DESCRIPTION 
		"This table contains information about mains voltage monitor"
	::= { mains 4 }

mainsVoltageEntry  OBJECT-TYPE
	SYNTAX 	MainsVoltageEntry
	MAX-ACCESS not-accessible
	STATUS     current
	DESCRIPTION 
		""
	INDEX { mainsVoltageIndex }
	::= { mainsVoltageTable 1 }

MainsVoltageEntry ::= SEQUENCE {
	mainsVoltageIndex
		Integer32,
	mainsVoltageStatus
		INTEGER,
	mainsVoltageDescription
		DisplayString,
	mainsVoltageTrapRepeatCounter
		Counter32,
	mainsVoltageAlarmEnable
		INTEGER,
	mainsVoltageValue
		Integer32,
	mainsVoltageMajorHighLevel
		Integer32,
	mainsVoltageMinorHighLevel
		Integer32,
	mainsVoltageMinorLowLevel
		Integer32,
	mainsVoltageMajorLowLevel
		Integer32
}

mainsVoltageIndex  OBJECT-TYPE
	SYNTAX     Integer32 (1..12)
	MAX-ACCESS not-accessible
	STATUS     current
	DESCRIPTION 
		"Index used for navigating the rows 1..12  of mainsVoltageTable"
	::= { mainsVoltageEntry 1 }

mainsVoltageStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured mains voltage."
	::= { mainsVoltageEntry 2 }

mainsVoltageDescription  OBJECT-TYPE
	SYNTAX     DisplayString (SIZE(0..16))
	MAX-ACCESS read-write
	STATUS     current
	DESCRIPTION 
		"A textual description of the mains voltage monitor. This is stored in the system controller
		and can be changed by the user.  "
	::= { mainsVoltageEntry 3 }

mainsVoltageTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { mainsVoltageEntry 4 }

mainsVoltageAlarmEnable  OBJECT-TYPE
	SYNTAX     INTEGER {
		disabled (0),
		enabled (1)
	}
	MAX-ACCESS read-write
	STATUS     current
	DESCRIPTION 
		"This value once enabled, the alarm condition of the monitor will be reported."
	::= { mainsVoltageEntry 5 }

mainsVoltageValue  OBJECT-TYPE
	SYNTAX     Integer32
	MAX-ACCESS read-only
	STATUS     current
	DESCRIPTION 
		"The value of the measured mains voltage."
	::= { mainsVoltageEntry 6 }

mainsVoltageMajorHighLevel  OBJECT-TYPE
	SYNTAX     Integer32
	MAX-ACCESS read-write
	STATUS     current
	DESCRIPTION 
		"The major high alarm limit"
	::= { mainsVoltageEntry 7 }

mainsVoltageMinorHighLevel  OBJECT-TYPE
	SYNTAX     Integer32
	MAX-ACCESS read-write
	STATUS     current
	DESCRIPTION 
		"The minor high alarm limit"
	::= { mainsVoltageEntry 8 }

mainsVoltageMinorLowLevel  OBJECT-TYPE
	SYNTAX     Integer32
	MAX-ACCESS read-write
	STATUS     current
	DESCRIPTION 
		"The minor low alarm limit"
	::= { mainsVoltageEntry 9 }

mainsVoltageMajorLowLevel  OBJECT-TYPE
	SYNTAX     Integer32
	MAX-ACCESS read-write
	STATUS     current
	DESCRIPTION 
		"The major low alarm limit"
	::= { mainsVoltageEntry 10 }

mainsMonitorsNumberOfUnits  OBJECT-TYPE
	SYNTAX     Integer32 (0..14)
	MAX-ACCESS read-write
	STATUS     current
	DESCRIPTION 
		"This is the number of AC Mains Monitor CAN Nodes installed in the system."
	::= { mainsMonitors 1 }

mainsMonitorsTable  OBJECT-TYPE
	SYNTAX SEQUENCE OF MainsMonitorsEntry
	MAX-ACCESS not-accessible
	STATUS     current
	DESCRIPTION 
		"This table contains the number of voltage, current and frequency measurements in each AC Mains Monitor"
	::= { mainsMonitors 2 }

mainsMonitorsEntry  OBJECT-TYPE
	SYNTAX 	MainsMonitorsEntry
	MAX-ACCESS not-accessible
	STATUS     current
	DESCRIPTION 
		""
	INDEX { mainsMonitorIndex }
	::= { mainsMonitorsTable 1 }

MainsMonitorsEntry ::= SEQUENCE {
	mainsMonitorIndex
		Integer32,
	mainsMonitorNumberOfVoltages
		Integer32,
	mainsMonitorNumberOfCurrents
		Integer32,
	mainsMonitorNumberOfFrequencies
		Integer32
}

mainsMonitorIndex  OBJECT-TYPE
	SYNTAX     Integer32 (1..14)
	MAX-ACCESS not-accessible
	STATUS     current
	DESCRIPTION 
		"Index used for navigating the rows of mainsMonitorsTable
		The size of the table is defined by the system  "
	::= { mainsMonitorsEntry 1 }

mainsMonitorNumberOfVoltages  OBJECT-TYPE
	SYNTAX     Integer32 (0..3)
	MAX-ACCESS read-only
	STATUS     current
	DESCRIPTION 
		"The number of voltage measurements in the AC Mains Monitor"
	::= { mainsMonitorsEntry 2 }

mainsMonitorNumberOfCurrents  OBJECT-TYPE
	SYNTAX     Integer32 (0..3)
	MAX-ACCESS read-only
	STATUS     current
	DESCRIPTION 
		"The number of current measurements in the AC Mains Monitor"
	::= { mainsMonitorsEntry 3 }

mainsMonitorNumberOfFrequencies  OBJECT-TYPE
	SYNTAX     Integer32 (0..3)
	MAX-ACCESS read-only
	STATUS     current
	DESCRIPTION 
		"The number of frequency measurements in the AC Mains Monitor"
	::= { mainsMonitorsEntry 4 }

mainsMonitorVoltageTable  OBJECT-TYPE
	SYNTAX SEQUENCE OF MainsMonitorVoltageEntry
	MAX-ACCESS not-accessible
	STATUS     current
	DESCRIPTION 
		"This table contains information about mains voltage in AC Mains Monitor"
	::= { mainsMonitors 3 }

mainsMonitorVoltageEntry  OBJECT-TYPE
	SYNTAX 	MainsMonitorVoltageEntry
	MAX-ACCESS not-accessible
	STATUS     current
	DESCRIPTION 
		""
	INDEX { mainsMonitorIndex, 
		mainsMonitorPhaseIndex }
	::= { mainsMonitorVoltageTable 1 }

MainsMonitorVoltageEntry ::= SEQUENCE {
	mainsMonitorPhaseIndex
		Integer32,
	mainsMonitorVoltageStatus
		INTEGER,
	mainsMonitorVoltageDescription
		DisplayString,
	mainsMonitorVoltageTrapRepeatCounter
		Counter32,
	mainsMonitorVoltageAlarmEnable
		INTEGER,
	mainsMonitorVoltageValue
		Integer32,
	mainsMonitorVoltageMajorHighLevel
		Integer32,
	mainsMonitorVoltageMinorHighLevel
		Integer32,
	mainsMonitorVoltageMinorLowLevel
		Integer32,
	mainsMonitorVoltageMajorLowLevel
		Integer32
}

mainsMonitorPhaseIndex  OBJECT-TYPE
	SYNTAX     Integer32 (1..3)
	MAX-ACCESS not-accessible
	STATUS     current
	DESCRIPTION 
		"Index used for navigating the rows 1..3  of mainsMonitorVolatgeTable"
	::= { mainsMonitorVoltageEntry 1 }

mainsMonitorVoltageStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured mains voltage in AC Mains Monitor."
	::= { mainsMonitorVoltageEntry 2 }

mainsMonitorVoltageDescription  OBJECT-TYPE
	SYNTAX     DisplayString (SIZE(1..16))
	MAX-ACCESS read-write
	STATUS     current
	DESCRIPTION 
		"A textual description of the mains voltage in AC Mains Monitor. This is stored in the system controller
		and can be changed by the user."
	::= { mainsMonitorVoltageEntry 3 }

mainsMonitorVoltageTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { mainsMonitorVoltageEntry 4 }

mainsMonitorVoltageAlarmEnable  OBJECT-TYPE
	SYNTAX     INTEGER {
		disabled (0),
		enabled (1)
	}
	MAX-ACCESS read-write
	STATUS     current
	DESCRIPTION 
		"This value once enabled, the alarm condition of the monitor will be reported."
	::= { mainsMonitorVoltageEntry 5 }

mainsMonitorVoltageValue  OBJECT-TYPE
	SYNTAX     Integer32
	MAX-ACCESS read-only
	STATUS     current
	DESCRIPTION 
		"The value of the measured mains voltage in AC Mains Monitor."
	::= { mainsMonitorVoltageEntry 6 }

mainsMonitorVoltageMajorHighLevel  OBJECT-TYPE
	SYNTAX     Integer32
	MAX-ACCESS read-write
	STATUS     current
	DESCRIPTION 
		"The major high alarm limit"
	::= { mainsMonitorVoltageEntry 7 }

mainsMonitorVoltageMinorHighLevel  OBJECT-TYPE
	SYNTAX     Integer32
	MAX-ACCESS read-write
	STATUS     current
	DESCRIPTION 
		"The minor high alarm limit"
	::= { mainsMonitorVoltageEntry 8 }

mainsMonitorVoltageMinorLowLevel  OBJECT-TYPE
	SYNTAX     Integer32
	MAX-ACCESS read-write
	STATUS     current
	DESCRIPTION 
		"The minor low alarm limit"
	::= { mainsMonitorVoltageEntry 9 }

mainsMonitorVoltageMajorLowLevel  OBJECT-TYPE
	SYNTAX     Integer32
	MAX-ACCESS read-write
	STATUS     current
	DESCRIPTION 
		"The major low alarm limit"
	::= { mainsMonitorVoltageEntry 10 }

mainsMonitorCurrentTable  OBJECT-TYPE
	SYNTAX SEQUENCE OF MainsMonitorCurrentEntry
	MAX-ACCESS not-accessible
	STATUS     current
	DESCRIPTION 
		"This table contains information about mains current in AC Mains Monitor"
	::= { mainsMonitors 4 }

mainsMonitorCurrentEntry  OBJECT-TYPE
	SYNTAX 	MainsMonitorCurrentEntry
	MAX-ACCESS not-accessible
	STATUS     current
	DESCRIPTION 
		""
	INDEX { mainsMonitorIndex, 
		mainsMonitorPhaseIndex }
	::= { mainsMonitorCurrentTable 1 }

MainsMonitorCurrentEntry ::= SEQUENCE {
	mainsMonitorCurrentStatus
		INTEGER,
	mainsMonitorCurrentDescription
		DisplayString,
	mainsMonitorCurrentTrapRepeatCounter
		Counter32,
	mainsMonitorCurrentAlarmEnable
		INTEGER,
	mainsMonitorCurrentValue
		Integer32,
	mainsMonitorCurrentMajorHighLevel
		Integer32,
	mainsMonitorCurrentMinorHighLevel
		Integer32
}

mainsMonitorCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured mains current in AC Mains Monitor."
	::= { mainsMonitorCurrentEntry 1 }

mainsMonitorCurrentDescription  OBJECT-TYPE
	SYNTAX     DisplayString (SIZE(1..16))
	MAX-ACCESS read-write
	STATUS     current
	DESCRIPTION 
		"A textual description of the mains current in AC Mains Monitor. This is stored in the system controller
		and can be changed by the user."
	::= { mainsMonitorCurrentEntry 2 }

mainsMonitorCurrentTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { mainsMonitorCurrentEntry 3 }

mainsMonitorCurrentAlarmEnable  OBJECT-TYPE
	SYNTAX     INTEGER {
		disabled (0),
		enabled (1)
	}
	MAX-ACCESS read-write
	STATUS     current
	DESCRIPTION 
		"This value once enabled, the alarm condition of the monitor will be reported."
	::= { mainsMonitorCurrentEntry 4 }

mainsMonitorCurrentValue  OBJECT-TYPE
	SYNTAX     Integer32
	MAX-ACCESS read-only
	STATUS     current
	DESCRIPTION 
		"The value of the measured mains current in AC Mains Monitor."
	::= { mainsMonitorCurrentEntry 5 }

mainsMonitorCurrentMajorHighLevel  OBJECT-TYPE
	SYNTAX     Integer32
	MAX-ACCESS read-write
	STATUS     current
	DESCRIPTION 
		"The major high alarm limit"
	::= { mainsMonitorCurrentEntry 6 }

mainsMonitorCurrentMinorHighLevel  OBJECT-TYPE
	SYNTAX     Integer32
	MAX-ACCESS read-write
	STATUS     current
	DESCRIPTION 
		"The minor high alarm limit"
	::= { mainsMonitorCurrentEntry 7 }

mainsMonitorFrequencyTable  OBJECT-TYPE
	SYNTAX SEQUENCE OF MainsMonitorFrequencyEntry
	MAX-ACCESS not-accessible
	STATUS     current
	DESCRIPTION 
		"This table contains information about mains frequency in AC Mains Monitor"
	::= { mainsMonitors 5 }

mainsMonitorFrequencyEntry  OBJECT-TYPE
	SYNTAX 	MainsMonitorFrequencyEntry
	MAX-ACCESS not-accessible
	STATUS     current
	DESCRIPTION 
		""
	INDEX { mainsMonitorIndex }
	::= { mainsMonitorFrequencyTable 1 }

MainsMonitorFrequencyEntry ::= SEQUENCE {
	mainsMonitorFrequencyStatus
		INTEGER,
	mainsMonitorFrequencyDescription
		DisplayString,
	mainsMonitorFrequencyTrapRepeatCounter
		Counter32,
	mainsMonitorFrequencyAlarmEnable
		INTEGER,
	mainsMonitorFrequencyValue
		Integer32,
	mainsMonitorFrequencyMajorHighLevel
		Integer32,
	mainsMonitorFrequencyMinorHighLevel
		Integer32,
	mainsMonitorFrequencyMinorLowLevel
		Integer32,
	mainsMonitorFrequencyMajorLowLevel
		Integer32
}

mainsMonitorFrequencyStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured mains frequency in AC Mains Monitor."
	::= { mainsMonitorFrequencyEntry 1 }

mainsMonitorFrequencyDescription  OBJECT-TYPE
	SYNTAX     DisplayString (SIZE(0..16))
	MAX-ACCESS read-write
	STATUS     current
	DESCRIPTION 
		"A textual description of the mains frequency in AC Mains Monitor. This is stored in the system
		 controller 
		and can be changed by the user.  "
	::= { mainsMonitorFrequencyEntry 2 }

mainsMonitorFrequencyTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { mainsMonitorFrequencyEntry 3 }

mainsMonitorFrequencyAlarmEnable  OBJECT-TYPE
	SYNTAX     INTEGER {
		disabled (0),
		enabled (1)
	}
	MAX-ACCESS read-write
	STATUS     current
	DESCRIPTION 
		"This value once enabled, the alarm condition of the monitor will be reported."
	::= { mainsMonitorFrequencyEntry 4 }

mainsMonitorFrequencyValue  OBJECT-TYPE
	SYNTAX     Integer32
	MAX-ACCESS read-only
	STATUS     current
	DESCRIPTION 
		"The value of the measured mains frequency in AC Mains Monitor."
	::= { mainsMonitorFrequencyEntry 5 }

mainsMonitorFrequencyMajorHighLevel  OBJECT-TYPE
	SYNTAX     Integer32
	MAX-ACCESS read-write
	STATUS     current
	DESCRIPTION 
		"The major high alarm limit"
	::= { mainsMonitorFrequencyEntry 6 }

mainsMonitorFrequencyMinorHighLevel  OBJECT-TYPE
	SYNTAX     Integer32
	MAX-ACCESS read-write
	STATUS     current
	DESCRIPTION 
		"The minor high alarm limit"
	::= { mainsMonitorFrequencyEntry 7 }

mainsMonitorFrequencyMinorLowLevel  OBJECT-TYPE
	SYNTAX     Integer32
	MAX-ACCESS read-write
	STATUS     current
	DESCRIPTION 
		"The minor low alarm limit"
	::= { mainsMonitorFrequencyEntry 8 }

mainsMonitorFrequencyMajorLowLevel  OBJECT-TYPE
	SYNTAX     Integer32
	MAX-ACCESS read-write
	STATUS     current
	DESCRIPTION 
		"The major low alarm limit"
	::= { mainsMonitorFrequencyEntry 9 }

mainsMonitorEnergyLogAccumulatedTable  OBJECT-TYPE
	SYNTAX SEQUENCE OF MainsMonitorEnergyLogAccumulatedEntry
	MAX-ACCESS not-accessible
	STATUS     current
	DESCRIPTION 
		"This table contains the accumulated energy consumption measured in AC Mains Monitor"
	::= { mainsMonitors 6 }

mainsMonitorEnergyLogAccumulatedEntry  OBJECT-TYPE
	SYNTAX 	MainsMonitorEnergyLogAccumulatedEntry
	MAX-ACCESS not-accessible
	STATUS     current
	DESCRIPTION 
		""
	INDEX { mainsMonitorIndex }
	::= { mainsMonitorEnergyLogAccumulatedTable 1 }

MainsMonitorEnergyLogAccumulatedEntry ::= SEQUENCE {
	mainsMonitorEnergyLogAccumulated
		Integer32
}

mainsMonitorEnergyLogAccumulated  OBJECT-TYPE
	SYNTAX     Integer32
	MAX-ACCESS read-only
	STATUS     current
	DESCRIPTION 
		"The accumulated energy consumption value"
	::= { mainsMonitorEnergyLogAccumulatedEntry 1 }

mainsMonitorEnergyLogLastHoursNumberOfEntries  OBJECT-TYPE
	SYNTAX     Integer32 (0..52)
	MAX-ACCESS read-only
	STATUS     current
	DESCRIPTION 
		"This is the maximal number of entries stored in hourly energy log"
	::= { mainsMonitors 7 }

mainsMonitorEnergyLogLastHoursTable  OBJECT-TYPE
	SYNTAX SEQUENCE OF MainsMonitorEnergyLogLastHoursEntry
	MAX-ACCESS not-accessible
	STATUS     current
	DESCRIPTION 
		"This table contains energy consumption values logged every hour in AC Mains Monitor."
	::= { mainsMonitors 8 }

mainsMonitorEnergyLogLastHoursEntry  OBJECT-TYPE
	SYNTAX 	MainsMonitorEnergyLogLastHoursEntry
	MAX-ACCESS not-accessible
	STATUS     current
	DESCRIPTION 
		""
	INDEX { mainsMonitorIndex, 
		mainsMonitorEnergyLogLastHoursIndex }
	::= { mainsMonitorEnergyLogLastHoursTable 1 }

MainsMonitorEnergyLogLastHoursEntry ::= SEQUENCE {
	mainsMonitorEnergyLogLastHoursIndex
		Integer32,
	mainsMonitorEnergyLogLastHoursValue
		Integer32
}

mainsMonitorEnergyLogLastHoursIndex  OBJECT-TYPE
	SYNTAX     Integer32 (1..52)
	MAX-ACCESS not-accessible
	STATUS     current
	DESCRIPTION 
		"Index used for navigating the rows 1..52  of mainsMonitorEnergyLogLastHoursTable"
	::= { mainsMonitorEnergyLogLastHoursEntry 1 }

mainsMonitorEnergyLogLastHoursValue  OBJECT-TYPE
	SYNTAX     Integer32
	MAX-ACCESS read-only
	STATUS     current
	DESCRIPTION 
		"Energy consumption value logged every hour in AC Mains Monitor."
	::= { mainsMonitorEnergyLogLastHoursEntry 2 }

mainsMonitorEnergyLogLastDaysNumberOfEntries  OBJECT-TYPE
	SYNTAX     Integer32 (0..52)
	MAX-ACCESS read-only
	STATUS     current
	DESCRIPTION 
		"This is the maximal number of entries stored in daily energy log"
	::= { mainsMonitors 9 }

mainsMonitorEnergyLogLastDaysTable  OBJECT-TYPE
	SYNTAX SEQUENCE OF MainsMonitorEnergyLogLastDaysEntry
	MAX-ACCESS not-accessible
	STATUS     current
	DESCRIPTION 
		"This table contains energy consumption values logged every day in AC Mains Monitor."
	::= { mainsMonitors 10 }

mainsMonitorEnergyLogLastDaysEntry  OBJECT-TYPE
	SYNTAX 	MainsMonitorEnergyLogLastDaysEntry
	MAX-ACCESS not-accessible
	STATUS     current
	DESCRIPTION 
		""
	INDEX { mainsMonitorIndex, 
		mainsMonitorEnergyLogLastDaysIndex }
	::= { mainsMonitorEnergyLogLastDaysTable 1 }

MainsMonitorEnergyLogLastDaysEntry ::= SEQUENCE {
	mainsMonitorEnergyLogLastDaysIndex
		Integer32,
	mainsMonitorEnergyLogLastDaysValue
		Integer32
}

mainsMonitorEnergyLogLastDaysIndex  OBJECT-TYPE
	SYNTAX     Integer32 (1..52)
	MAX-ACCESS not-accessible
	STATUS     current
	DESCRIPTION 
		"Index used for navigating the rows 1..52  of mainsMonitorEnergyLogLastDaysTable"
	::= { mainsMonitorEnergyLogLastDaysEntry 1 }

mainsMonitorEnergyLogLastDaysValue  OBJECT-TYPE
	SYNTAX     Integer32
	MAX-ACCESS read-only
	STATUS     current
	DESCRIPTION 
		"Energy consumption value logged every day in AC Mains Monitor."
	::= { mainsMonitorEnergyLogLastDaysEntry 2 }

mainsMonitorEnergyLogLastWeeksNumberOfEntries  OBJECT-TYPE
	SYNTAX     Integer32 (0..52)
	MAX-ACCESS read-only
	STATUS     current
	DESCRIPTION 
		"This is the maximal number of entries stored in weekly energy log"
	::= { mainsMonitors 11 }

mainsMonitorEnergyLogLastWeeksTable  OBJECT-TYPE
	SYNTAX SEQUENCE OF MainsMonitorEnergyLogLastWeeksEntry
	MAX-ACCESS not-accessible
	STATUS     current
	DESCRIPTION 
		"This table contains energy consumption values logged every week in AC Mains Monitor."
	::= { mainsMonitors 12 }

mainsMonitorEnergyLogLastWeeksEntry  OBJECT-TYPE
	SYNTAX 	MainsMonitorEnergyLogLastWeeksEntry
	MAX-ACCESS not-accessible
	STATUS     current
	DESCRIPTION 
		""
	INDEX { mainsMonitorIndex, 
		mainsMonitorEnergyLogLastWeeksIndex }
	::= { mainsMonitorEnergyLogLastWeeksTable 1 }

MainsMonitorEnergyLogLastWeeksEntry ::= SEQUENCE {
	mainsMonitorEnergyLogLastWeeksIndex
		Integer32,
	mainsMonitorEnergyLogLastWeeksValue
		Integer32
}

mainsMonitorEnergyLogLastWeeksIndex  OBJECT-TYPE
	SYNTAX     Integer32 (1..52)
	MAX-ACCESS not-accessible
	STATUS     current
	DESCRIPTION 
		"Index used for navigating the rows 1..52  of mainsMonitorEnergyLogLastWeeksTable"
	::= { mainsMonitorEnergyLogLastWeeksEntry 1 }

mainsMonitorEnergyLogLastWeeksValue  OBJECT-TYPE
	SYNTAX     Integer32
	MAX-ACCESS read-only
	STATUS     current
	DESCRIPTION 
		"Energy consumption value logged every week in AC Mains Monitor."
	::= { mainsMonitorEnergyLogLastWeeksEntry 2 }

mainsMonitorActivePowerTable  OBJECT-TYPE
	SYNTAX SEQUENCE OF MainsMonitorActivePowerEntry
	MAX-ACCESS not-accessible
	STATUS     current
	DESCRIPTION 
		"This table contains information about mains active power in AC Mains Monitor"
	::= { mainsMonitors 13 }

mainsMonitorActivePowerEntry  OBJECT-TYPE
	SYNTAX 	MainsMonitorActivePowerEntry
	MAX-ACCESS not-accessible
	STATUS     current
	DESCRIPTION 
		""
	INDEX { mainsMonitorIndex, 
		mainsMonitorPhaseIndex }
	::= { mainsMonitorActivePowerTable 1 }

MainsMonitorActivePowerEntry ::= SEQUENCE {
	mainsMonitorActivePowerStatus
		INTEGER,
	mainsMonitorActivePowerDescription
		DisplayString,
	mainsMonitorActivePowerTrapRepeatCounter
		Counter32,
	mainsMonitorActivePowerAlarmEnable
		INTEGER,
	mainsMonitorActivePowerValue
		Integer32,
	mainsMonitorActivePowerMajorHighLevel
		Integer32,
	mainsMonitorActivePowerMinorHighLevel
		Integer32
}

mainsMonitorActivePowerStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured mains active power in AC Mains Monitor."
	::= { mainsMonitorActivePowerEntry 1 }

mainsMonitorActivePowerDescription  OBJECT-TYPE
	SYNTAX     DisplayString (SIZE(1..16))
	MAX-ACCESS read-write
	STATUS     current
	DESCRIPTION 
		"A textual description of the mains active power in AC Mains Monitor. This is stored in the system controller
		and can be changed by the user."
	::= { mainsMonitorActivePowerEntry 2 }

mainsMonitorActivePowerTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { mainsMonitorActivePowerEntry 3 }

mainsMonitorActivePowerAlarmEnable  OBJECT-TYPE
	SYNTAX     INTEGER {
		disabled (0),
		enabled (1)
	}
	MAX-ACCESS read-write
	STATUS     current
	DESCRIPTION 
		"This value once enabled, the alarm condition of the monitor will be reported."
	::= { mainsMonitorActivePowerEntry 4 }

mainsMonitorActivePowerValue  OBJECT-TYPE
	SYNTAX     Integer32
	MAX-ACCESS read-only
	STATUS     current
	DESCRIPTION 
		"The value of the measured mains active power in AC Mains Monitor."
	::= { mainsMonitorActivePowerEntry 5 }

mainsMonitorActivePowerMajorHighLevel  OBJECT-TYPE
	SYNTAX     Integer32
	MAX-ACCESS read-write
	STATUS     current
	DESCRIPTION 
		"The major high alarm limit"
	::= { mainsMonitorActivePowerEntry 6 }

mainsMonitorActivePowerMinorHighLevel  OBJECT-TYPE
	SYNTAX     Integer32
	MAX-ACCESS read-write
	STATUS     current
	DESCRIPTION 
		"The minor high alarm limit"
	::= { mainsMonitorActivePowerEntry 7 }

mainsMonitorReactivePowerTable  OBJECT-TYPE
	SYNTAX SEQUENCE OF MainsMonitorReactivePowerEntry
	MAX-ACCESS not-accessible
	STATUS     current
	DESCRIPTION 
		"This table contains information about mains reactive power in AC Mains Monitor"
	::= { mainsMonitors 14 }

mainsMonitorReactivePowerEntry  OBJECT-TYPE
	SYNTAX 	MainsMonitorReactivePowerEntry
	MAX-ACCESS not-accessible
	STATUS     current
	DESCRIPTION 
		""
	INDEX { mainsMonitorIndex, 
		mainsMonitorPhaseIndex }
	::= { mainsMonitorReactivePowerTable 1 }

MainsMonitorReactivePowerEntry ::= SEQUENCE {
	mainsMonitorReactivePowerStatus
		INTEGER,
	mainsMonitorReactivePowerDescription
		DisplayString,
	mainsMonitorReactivePowerTrapRepeatCounter
		Counter32,
	mainsMonitorReactivePowerAlarmEnable
		INTEGER,
	mainsMonitorReactivePowerValue
		Integer32,
	mainsMonitorReactivePowerMajorHighLevel
		Integer32,
	mainsMonitorReactivePowerMinorHighLevel
		Integer32
}

mainsMonitorReactivePowerStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured mains reactive power in AC Mains Monitor."
	::= { mainsMonitorReactivePowerEntry 1 }

mainsMonitorReactivePowerDescription  OBJECT-TYPE
	SYNTAX     DisplayString (SIZE(1..16))
	MAX-ACCESS read-write
	STATUS     current
	DESCRIPTION 
		"A textual description of the mains reactive power in AC Mains Monitor. This is stored in the system controller
		and can be changed by the user."
	::= { mainsMonitorReactivePowerEntry 2 }

mainsMonitorReactivePowerTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { mainsMonitorReactivePowerEntry 3 }

mainsMonitorReactivePowerAlarmEnable  OBJECT-TYPE
	SYNTAX     INTEGER {
		disabled (0),
		enabled (1)
	}
	MAX-ACCESS read-write
	STATUS     current
	DESCRIPTION 
		"This value once enabled, the alarm condition of the monitor will be reported."
	::= { mainsMonitorReactivePowerEntry 4 }

mainsMonitorReactivePowerValue  OBJECT-TYPE
	SYNTAX     Integer32
	MAX-ACCESS read-only
	STATUS     current
	DESCRIPTION 
		"The value of the measured mains reactive power in AC Mains Monitor."
	::= { mainsMonitorReactivePowerEntry 5 }

mainsMonitorReactivePowerMajorHighLevel  OBJECT-TYPE
	SYNTAX     Integer32
	MAX-ACCESS read-write
	STATUS     current
	DESCRIPTION 
		"The major high alarm limit"
	::= { mainsMonitorReactivePowerEntry 6 }

mainsMonitorReactivePowerMinorHighLevel  OBJECT-TYPE
	SYNTAX     Integer32
	MAX-ACCESS read-write
	STATUS     current
	DESCRIPTION 
		"The minor high alarm limit"
	::= { mainsMonitorReactivePowerEntry 7 }

mainsMonitorApparentPowerTable  OBJECT-TYPE
	SYNTAX SEQUENCE OF MainsMonitorApparentPowerEntry
	MAX-ACCESS not-accessible
	STATUS     current
	DESCRIPTION 
		"This table contains information about mains apparent power in AC Mains Monitor"
	::= { mainsMonitors 15 }

mainsMonitorApparentPowerEntry  OBJECT-TYPE
	SYNTAX 	MainsMonitorApparentPowerEntry
	MAX-ACCESS not-accessible
	STATUS     current
	DESCRIPTION 
		""
	INDEX { mainsMonitorIndex, 
		mainsMonitorPhaseIndex }
	::= { mainsMonitorApparentPowerTable 1 }

MainsMonitorApparentPowerEntry ::= SEQUENCE {
	mainsMonitorApparentPowerStatus
		INTEGER,
	mainsMonitorApparentPowerDescription
		DisplayString,
	mainsMonitorApparentPowerTrapRepeatCounter
		Counter32,
	mainsMonitorApparentPowerAlarmEnable
		INTEGER,
	mainsMonitorApparentPowerValue
		Integer32,
	mainsMonitorApparentPowerMajorHighLevel
		Integer32,
	mainsMonitorApparentPowerMinorHighLevel
		Integer32
}

mainsMonitorApparentPowerStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured mains apparent power in AC Mains Monitor."
	::= { mainsMonitorApparentPowerEntry 1 }

mainsMonitorApparentPowerDescription  OBJECT-TYPE
	SYNTAX     DisplayString (SIZE(1..16))
	MAX-ACCESS read-write
	STATUS     current
	DESCRIPTION 
		"A textual description of the mains apparent power in AC Mains Monitor. This is stored in the system controller
		and can be changed by the user."
	::= { mainsMonitorApparentPowerEntry 2 }

mainsMonitorApparentPowerTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { mainsMonitorApparentPowerEntry 3 }

mainsMonitorApparentPowerAlarmEnable  OBJECT-TYPE
	SYNTAX     INTEGER {
		disabled (0),
		enabled (1)
	}
	MAX-ACCESS read-write
	STATUS     current
	DESCRIPTION 
		"This value once enabled, the alarm condition of the monitor will be reported."
	::= { mainsMonitorApparentPowerEntry 4 }

mainsMonitorApparentPowerValue  OBJECT-TYPE
	SYNTAX     Integer32
	MAX-ACCESS read-only
	STATUS     current
	DESCRIPTION 
		"The value of the measured mains apparent power in AC Mains Monitor."
	::= { mainsMonitorApparentPowerEntry 5 }

mainsMonitorApparentPowerMajorHighLevel  OBJECT-TYPE
	SYNTAX     Integer32
	MAX-ACCESS read-write
	STATUS     current
	DESCRIPTION 
		"The major high alarm limit"
	::= { mainsMonitorApparentPowerEntry 6 }

mainsMonitorApparentPowerMinorHighLevel  OBJECT-TYPE
	SYNTAX     Integer32
	MAX-ACCESS read-write
	STATUS     current
	DESCRIPTION 
		"The minor high alarm limit"
	::= { mainsMonitorApparentPowerEntry 7 }

mainsOutageTotal  OBJECT-TYPE
	SYNTAX     Integer32
	MAX-ACCESS read-only
	STATUS     current
	DESCRIPTION 
		"This is the total mains outage time measured in hours. Note that the value of this OID
		does not changed when the 'mainsLogMode' OID is set to 'runningTime'. The total running
		time is available at OID 1.3.6.1.4.1.12148.10.3.15."
	::= { mainsOutageLog 1 }

mainsOutageLogDaysNumberOfEntries  OBJECT-TYPE
	SYNTAX     Integer32 (0..52)
	MAX-ACCESS read-only
	STATUS     current
	DESCRIPTION 
		"This is the maximal number of entries stored in daily mains outage/running time log."
	::= { mainsOutageLog 2 }

mainsOutageLogDaysTable  OBJECT-TYPE
	SYNTAX SEQUENCE OF MainsOutageLogDaysEntry
	MAX-ACCESS not-accessible
	STATUS     current
	DESCRIPTION 
		"This table contains daily mains outage or running time log depending on the log mode."
	::= { mainsOutageLog 3 }

mainsOutageLogDaysEntry  OBJECT-TYPE
	SYNTAX 	MainsOutageLogDaysEntry
	MAX-ACCESS not-accessible
	STATUS     current
	DESCRIPTION 
		""
	INDEX { mainsOutageLogDaysIndex }
	::= { mainsOutageLogDaysTable 1 }

MainsOutageLogDaysEntry ::= SEQUENCE {
	mainsOutageLogDaysIndex
		Integer32,
	mainsOutageLogDaysValue
		Integer32
}

mainsOutageLogDaysIndex  OBJECT-TYPE
	SYNTAX     Integer32 (1..52)
	MAX-ACCESS not-accessible
	STATUS     current
	DESCRIPTION 
		"Index used for navigating the rows 1..52  of mainsOutageLogDaysTable"
	::= { mainsOutageLogDaysEntry 1 }

mainsOutageLogDaysValue  OBJECT-TYPE
	SYNTAX     Integer32
	MAX-ACCESS read-only
	STATUS     current
	DESCRIPTION 
		"Mains outage or running time value in minutes, logged every day."
	::= { mainsOutageLogDaysEntry 2 }

mainsOutageLogWeeksNumberOfEntries  OBJECT-TYPE
	SYNTAX     Integer32 (0..52)
	MAX-ACCESS read-only
	STATUS     current
	DESCRIPTION 
		"This is the maximal number of entries stored in weekly mains outage/running time log."
	::= { mainsOutageLog 4 }

mainsOutageLogWeeksTable  OBJECT-TYPE
	SYNTAX SEQUENCE OF MainsOutageLogWeeksEntry
	MAX-ACCESS not-accessible
	STATUS     current
	DESCRIPTION 
		"This table contains weekly mains outage or running time log depending on the log mode."
	::= { mainsOutageLog 5 }

mainsOutageLogWeeksEntry  OBJECT-TYPE
	SYNTAX 	MainsOutageLogWeeksEntry
	MAX-ACCESS not-accessible
	STATUS     current
	DESCRIPTION 
		""
	INDEX { mainsOutageLogWeeksIndex }
	::= { mainsOutageLogWeeksTable 1 }

MainsOutageLogWeeksEntry ::= SEQUENCE {
	mainsOutageLogWeeksIndex
		Integer32,
	mainsOutageLogWeeksValue
		Integer32
}

mainsOutageLogWeeksIndex  OBJECT-TYPE
	SYNTAX     Integer32 (1..52)
	MAX-ACCESS not-accessible
	STATUS     current
	DESCRIPTION 
		"Index used for navigating the rows 1..52  of mainsOutageLogWeeksTable"
	::= { mainsOutageLogWeeksEntry 1 }

mainsOutageLogWeeksValue  OBJECT-TYPE
	SYNTAX     Integer32
	MAX-ACCESS read-only
	STATUS     current
	DESCRIPTION 
		"Mains outage or running time value in hours, logged every week."
	::= { mainsOutageLogWeeksEntry 2 }

mainsOutageLogMonthsNumberOfEntries  OBJECT-TYPE
	SYNTAX     Integer32 (0..52)
	MAX-ACCESS read-only
	STATUS     current
	DESCRIPTION 
		"This is the maximal number of entries stored in monthly mains outage/running time log."
	::= { mainsOutageLog 6 }

mainsOutageLogMonthsTable  OBJECT-TYPE
	SYNTAX SEQUENCE OF MainsOutageLogMonthsEntry
	MAX-ACCESS not-accessible
	STATUS     current
	DESCRIPTION 
		"This table contains monthly mains outage or running time log depending on the log mode."
	::= { mainsOutageLog 7 }

mainsOutageLogMonthsEntry  OBJECT-TYPE
	SYNTAX 	MainsOutageLogMonthsEntry
	MAX-ACCESS not-accessible
	STATUS     current
	DESCRIPTION 
		""
	INDEX { mainsOutageLogMonthsIndex }
	::= { mainsOutageLogMonthsTable 1 }

MainsOutageLogMonthsEntry ::= SEQUENCE {
	mainsOutageLogMonthsIndex
		Integer32,
	mainsOutageLogMonthsValue
		Integer32
}

mainsOutageLogMonthsIndex  OBJECT-TYPE
	SYNTAX     Integer32 (1..52)
	MAX-ACCESS not-accessible
	STATUS     current
	DESCRIPTION 
		"Index used for navigating the rows 1..52  of mainsOutageLogMonthsTable"
	::= { mainsOutageLogMonthsEntry 1 }

mainsOutageLogMonthsValue  OBJECT-TYPE
	SYNTAX     Integer32
	MAX-ACCESS read-only
	STATUS     current
	DESCRIPTION 
		"Mains outage or running time value in hours, logged every month."
	::= { mainsOutageLogMonthsEntry 2 }

mainsLogMode  OBJECT-TYPE
	SYNTAX     INTEGER {
		outageTime (0),
		runningTime (1)
	}
	MAX-ACCESS read-write
	STATUS     current
	DESCRIPTION 
		"This value determines if the mains outage time or running time should be logged."
	::= { mainsOutageLog 8 }

mainsNumberOfGroups  OBJECT-TYPE
	SYNTAX     Integer32
	MAX-ACCESS read-only
	STATUS     current
	DESCRIPTION 
		"This value showing the number of groups of the mains subsystem."
	::= { mains 7 }

mainsGroupsTable  OBJECT-TYPE
	SYNTAX SEQUENCE OF MainsGroupsEntry
	MAX-ACCESS not-accessible
	STATUS     current
	DESCRIPTION 
		"This table contains the status of mains group and number of phases in each group."
	::= { mains 8 }

mainsGroupsEntry  OBJECT-TYPE
	SYNTAX 	MainsGroupsEntry
	MAX-ACCESS not-accessible
	STATUS     current
	DESCRIPTION 
		""
	INDEX { mainsGroupIndex }
	::= { mainsGroupsTable 1 }

MainsGroupsEntry ::= SEQUENCE {
	mainsGroupIndex
		Integer32,
	mainsGroupStatus
		INTEGER,
	mainsGroupNumberOfPhases
		Integer32
}

mainsGroupIndex  OBJECT-TYPE
	SYNTAX     Integer32 (1..10)
	MAX-ACCESS not-accessible
	STATUS     current
	DESCRIPTION 
		"Index used for navigating the rows 1..10  of mainsGroupTable"
	::= { mainsGroupsEntry 1 }

mainsGroupStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of mains group."
	::= { mainsGroupsEntry 2 }

mainsGroupNumberOfPhases  OBJECT-TYPE
	SYNTAX     Integer32
	MAX-ACCESS read-write
	STATUS     current
	DESCRIPTION 
		"This value showing the number of phases of the mains group subsystem."
	::= { mainsGroupsEntry 3 }

mainsGroupMainsFailureTable  OBJECT-TYPE
	SYNTAX SEQUENCE OF MainsGroupMainsFailureEntry
	MAX-ACCESS not-accessible
	STATUS     current
	DESCRIPTION 
		"This table contains information about mains failure monitor of mains group"
	::= { mains 9 }

mainsGroupMainsFailureEntry  OBJECT-TYPE
	SYNTAX 	MainsGroupMainsFailureEntry
	MAX-ACCESS not-accessible
	STATUS     current
	DESCRIPTION 
		""
	INDEX { mainsGroupIndex }
	::= { mainsGroupMainsFailureTable 1 }

MainsGroupMainsFailureEntry ::= SEQUENCE {
	mainsGroupMainsFailureStatus
		INTEGER,
	mainsGroupMainsFailureDescription
		DisplayString,
	mainsGroupMainsFailureTrapRepeatCounter
		Integer32,
	mainsGroupMainsFailureAlarmEnable
		INTEGER,
	mainsGroupMainsFailureValue
		Integer32,
	mainsGroupMainsFailureMajorAlarmLevel
		Integer32,
	mainsGroupMainsFailureMinorAlarmLevel
		Integer32
}

mainsGroupMainsFailureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed phases is higher than the defined alarm level for the mains group"
	::= { mainsGroupMainsFailureEntry 1 }

mainsGroupMainsFailureDescription  OBJECT-TYPE
	SYNTAX     DisplayString (SIZE(0..16))
	MAX-ACCESS read-write
	STATUS     current
	DESCRIPTION 
		"A textual description of the mains group phase failure monitor. This is stored in the system controller
		and can be changed by the user."
	::= { mainsGroupMainsFailureEntry 2 }

mainsGroupMainsFailureTrapRepeatCounter  OBJECT-TYPE
	SYNTAX     Integer32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { mainsGroupMainsFailureEntry 3 }

mainsGroupMainsFailureAlarmEnable  OBJECT-TYPE
	SYNTAX     INTEGER {
		disabled (0),
		enabled (1)
	}
	MAX-ACCESS read-write
	STATUS     current
	DESCRIPTION 
		"This value once enabled, the alarm condition of the monitor will be reported."
	::= { mainsGroupMainsFailureEntry 4 }

mainsGroupMainsFailureValue  OBJECT-TYPE
	SYNTAX     Integer32
	MAX-ACCESS read-only
	STATUS     current
	DESCRIPTION 
		"The detected number of failed phases in the mains group."
	::= { mainsGroupMainsFailureEntry 5 }

mainsGroupMainsFailureMajorAlarmLevel  OBJECT-TYPE
	SYNTAX     Integer32
	MAX-ACCESS read-write
	STATUS     current
	DESCRIPTION 
		"The major alarm limit"
	::= { mainsGroupMainsFailureEntry 6 }

mainsGroupMainsFailureMinorAlarmLevel  OBJECT-TYPE
	SYNTAX     Integer32
	MAX-ACCESS read-write
	STATUS     current
	DESCRIPTION 
		"The minor alarm limit"
	::= { mainsGroupMainsFailureEntry 7 }

mainsGroupVoltageTable  OBJECT-TYPE
	SYNTAX SEQUENCE OF MainsGroupVoltageEntry
	MAX-ACCESS not-accessible
	STATUS     current
	DESCRIPTION 
		"This table contains information about mains voltage monitors for mains group"
	::= { mains 10 }

mainsGroupVoltageEntry  OBJECT-TYPE
	SYNTAX 	MainsGroupVoltageEntry
	MAX-ACCESS not-accessible
	STATUS     current
	DESCRIPTION 
		""
	INDEX { mainsGroupIndex, 
		mainsGroupVoltageIndex }
	::= { mainsGroupVoltageTable 1 }

MainsGroupVoltageEntry ::= SEQUENCE {
	mainsGroupVoltageIndex
		Integer32,
	mainsGroupVoltageStatus
		INTEGER,
	mainsGroupVoltageDescription
		DisplayString,
	mainsGroupVoltageTrapRepeatCounter
		Integer32,
	mainsGroupVoltageAlarmEnable
		INTEGER,
	mainsGroupVoltageValue
		Integer32,
	mainsGroupVoltageMajorHighLevel
		Integer32,
	mainsGroupVoltageMinorHighLevel
		Integer32,
	mainsGroupVoltageMinorLowLevel
		Integer32,
	mainsGroupVoltageMajorLowLevel
		Integer32
}

mainsGroupVoltageIndex  OBJECT-TYPE
	SYNTAX     Integer32 (1..12)
	MAX-ACCESS not-accessible
	STATUS     current
	DESCRIPTION 
		"Index used for navigating the rows 1..12  of mainsGroupVoltageTable"
	::= { mainsGroupVoltageEntry 1 }

mainsGroupVoltageStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured mains voltage of the mains group."
	::= { mainsGroupVoltageEntry 2 }

mainsGroupVoltageDescription  OBJECT-TYPE
	SYNTAX     DisplayString (SIZE(0..16))
	MAX-ACCESS read-write
	STATUS     current
	DESCRIPTION 
		"A textual description of the mains voltage monitor of the mains group. This is stored in the system controller
		and can be changed by the user.  "
	::= { mainsGroupVoltageEntry 3 }

mainsGroupVoltageTrapRepeatCounter  OBJECT-TYPE
	SYNTAX     Integer32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { mainsGroupVoltageEntry 4 }

mainsGroupVoltageAlarmEnable  OBJECT-TYPE
	SYNTAX     INTEGER {
		disabled (0),
		enabled (1)
	}
	MAX-ACCESS read-write
	STATUS     current
	DESCRIPTION 
		"This value once enabled, the alarm condition of the monitor will be reported."
	::= { mainsGroupVoltageEntry 5 }

mainsGroupVoltageValue  OBJECT-TYPE
	SYNTAX     Integer32
	MAX-ACCESS read-only
	STATUS     current
	DESCRIPTION 
		"The value of the measured mains voltage in the mains group."
	::= { mainsGroupVoltageEntry 6 }

mainsGroupVoltageMajorHighLevel  OBJECT-TYPE
	SYNTAX     Integer32
	MAX-ACCESS read-write
	STATUS     current
	DESCRIPTION 
		"The major high alarm limit"
	::= { mainsGroupVoltageEntry 7 }

mainsGroupVoltageMinorHighLevel  OBJECT-TYPE
	SYNTAX     Integer32
	MAX-ACCESS read-write
	STATUS     current
	DESCRIPTION 
		"The minor high alarm limit"
	::= { mainsGroupVoltageEntry 8 }

mainsGroupVoltageMinorLowLevel  OBJECT-TYPE
	SYNTAX     Integer32
	MAX-ACCESS read-write
	STATUS     current
	DESCRIPTION 
		"The minor low alarm limit"
	::= { mainsGroupVoltageEntry 9 }

mainsGroupVoltageMajorLowLevel  OBJECT-TYPE
	SYNTAX     Integer32
	MAX-ACCESS read-write
	STATUS     current
	DESCRIPTION 
		"The major low alarm limit"
	::= { mainsGroupVoltageEntry 10 }

mainsGroupOutageLogTable  OBJECT-TYPE
	SYNTAX SEQUENCE OF MainsGroupOutageLogEntry
	MAX-ACCESS not-accessible
	STATUS     current
	DESCRIPTION 
		" This table contains total mains outage of the mains group and number of entries in each log table."
	::= { mains 11 }

mainsGroupOutageLogEntry  OBJECT-TYPE
	SYNTAX 	MainsGroupOutageLogEntry
	MAX-ACCESS not-accessible
	STATUS     current
	DESCRIPTION 
		""
	INDEX { mainsGroupIndex }
	::= { mainsGroupOutageLogTable 1 }

MainsGroupOutageLogEntry ::= SEQUENCE {
	mainsGroupOutageTotal
		Integer32,
	mainsGroupOutageLogDaysNumberOfEntries
		Integer32,
	mainsGroupOutageLogWeeksNumberOfEntries
		Integer32,
	mainsGroupOutageLogMonthsNumberOfEntries
		Integer32
}

mainsGroupOutageTotal  OBJECT-TYPE
	SYNTAX     Integer32
	MAX-ACCESS read-only
	STATUS     current
	DESCRIPTION 
		"This is the total mains outage time measured in hours in the mains group."
	::= { mainsGroupOutageLogEntry 1 }

mainsGroupOutageLogDaysNumberOfEntries  OBJECT-TYPE
	SYNTAX     Integer32
	MAX-ACCESS read-only
	STATUS     current
	DESCRIPTION 
		"This is the maximal number of entries stored in daily mains outage log."
	::= { mainsGroupOutageLogEntry 2 }

mainsGroupOutageLogWeeksNumberOfEntries  OBJECT-TYPE
	SYNTAX     Integer32
	MAX-ACCESS read-only
	STATUS     current
	DESCRIPTION 
		"This is the maximal number of entries stored in weekly mains outage time log."
	::= { mainsGroupOutageLogEntry 3 }

mainsGroupOutageLogMonthsNumberOfEntries  OBJECT-TYPE
	SYNTAX     Integer32
	MAX-ACCESS read-only
	STATUS     current
	DESCRIPTION 
		"This is the maximal number of entries stored in monthly mains outage time log."
	::= { mainsGroupOutageLogEntry 4 }

mainsGroupOutageLogDaysTable  OBJECT-TYPE
	SYNTAX SEQUENCE OF MainsGroupOutageLogDaysEntry
	MAX-ACCESS not-accessible
	STATUS     current
	DESCRIPTION 
		"This table contains daily mains outage time log of mains group."
	::= { mains 12 }

mainsGroupOutageLogDaysEntry  OBJECT-TYPE
	SYNTAX 	MainsGroupOutageLogDaysEntry
	MAX-ACCESS not-accessible
	STATUS     current
	DESCRIPTION 
		""
	INDEX { mainsGroupIndex, 
		mainsGroupOutageLogDaysIndex }
	::= { mainsGroupOutageLogDaysTable 1 }

MainsGroupOutageLogDaysEntry ::= SEQUENCE {
	mainsGroupOutageLogDaysIndex
		Integer32,
	mainsGroupOutageLogDaysValue
		Integer32
}

mainsGroupOutageLogDaysIndex  OBJECT-TYPE
	SYNTAX     Integer32 (1..52)
	MAX-ACCESS not-accessible
	STATUS     current
	DESCRIPTION 
		"Index used for navigating the rows 1..52  of mainsGroupOutageLogDaysTable"
	::= { mainsGroupOutageLogDaysEntry 1 }

mainsGroupOutageLogDaysValue  OBJECT-TYPE
	SYNTAX     Integer32
	MAX-ACCESS read-only
	STATUS     current
	DESCRIPTION 
		"Mains outage time value in minutes of each mains group, logged every day."
	::= { mainsGroupOutageLogDaysEntry 2 }

mainsGroupOutageLogWeeksTable  OBJECT-TYPE
	SYNTAX SEQUENCE OF MainsGroupOutageLogWeeksEntry
	MAX-ACCESS not-accessible
	STATUS     current
	DESCRIPTION 
		"This table contains weekly mains outage time log of mains group."
	::= { mains 13 }

mainsGroupOutageLogWeeksEntry  OBJECT-TYPE
	SYNTAX 	MainsGroupOutageLogWeeksEntry
	MAX-ACCESS not-accessible
	STATUS     current
	DESCRIPTION 
		""
	INDEX { mainsGroupIndex, 
		mainsGroupOutageLogWeeksIndex }
	::= { mainsGroupOutageLogWeeksTable 1 }

MainsGroupOutageLogWeeksEntry ::= SEQUENCE {
	mainsGroupOutageLogWeeksIndex
		Integer32,
	mainsGroupOutageLogWeeksValue
		Integer32
}

mainsGroupOutageLogWeeksIndex  OBJECT-TYPE
	SYNTAX     Integer32 (1..52)
	MAX-ACCESS not-accessible
	STATUS     current
	DESCRIPTION 
		"Index used for navigating the rows 1..52  of mainsGroupOutageLogWeeksTable"
	::= { mainsGroupOutageLogWeeksEntry 1 }

mainsGroupOutageLogWeeksValue  OBJECT-TYPE
	SYNTAX     Integer32
	MAX-ACCESS read-only
	STATUS     current
	DESCRIPTION 
		"Mains outage time value in hours of each mains group, logged every week."
	::= { mainsGroupOutageLogWeeksEntry 2 }

mainsGroupOutageLogMonthsTable  OBJECT-TYPE
	SYNTAX SEQUENCE OF MainsGroupOutageLogMonthsEntry
	MAX-ACCESS not-accessible
	STATUS     current
	DESCRIPTION 
		"This table contains monthly mains outage time log of mains group."
	::= { mains 14 }

mainsGroupOutageLogMonthsEntry  OBJECT-TYPE
	SYNTAX 	MainsGroupOutageLogMonthsEntry
	MAX-ACCESS not-accessible
	STATUS     current
	DESCRIPTION 
		""
	INDEX { mainsGroupIndex, 
		mainsGroupOutageLogMonthsIndex }
	::= { mainsGroupOutageLogMonthsTable 1 }

MainsGroupOutageLogMonthsEntry ::= SEQUENCE {
	mainsGroupOutageLogMonthsIndex
		Integer32,
	mainsGroupOutageLogMonthsValue
		Integer32
}

mainsGroupOutageLogMonthsIndex  OBJECT-TYPE
	SYNTAX     Integer32 (1..52)
	MAX-ACCESS not-accessible
	STATUS     current
	DESCRIPTION 
		"Index used for navigating the rows 1..52  of mainsGroupOutageLogMonthsTable"
	::= { mainsGroupOutageLogMonthsEntry 1 }

mainsGroupOutageLogMonthsValue  OBJECT-TYPE
	SYNTAX     Integer32
	MAX-ACCESS read-only
	STATUS     current
	DESCRIPTION 
		"Mains outage time value in hours of each mains group, logged every month."
	::= { mainsGroupOutageLogMonthsEntry 2 }

mainsRunningHours  OBJECT-TYPE
	SYNTAX     Unsigned32
	MAX-ACCESS read-only
	STATUS     current
	DESCRIPTION 
		"This is the total mains running time measured in hours. The total outage
		time is available at OID 1.3.6.1.4.1.12148.10.3.6.1"
	::= { mains 15 }

generatorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of generator subsystem."
	::= { generator 1 }

generatorFailStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of generator failure monitor."
	::= { generator 2 }

generatorActivation  OBJECT-TYPE
	SYNTAX     Integer32
	MAX-ACCESS read-only
	STATUS     current
	DESCRIPTION 
		"Indicate if the generator run output signal is activated."
	::= { generator 3 }

generatorDischargeValue  OBJECT-TYPE
	SYNTAX     Integer32
	MAX-ACCESS read-only
	STATUS     current
	DESCRIPTION 
		"This is the present discharge value in percentage of total capacity."
	::= { generator 4 }

generatorMainsDelay  OBJECT-TYPE
	SYNTAX     Integer32
	MAX-ACCESS read-only
	STATUS     current
	DESCRIPTION 
		"Elapsing time of mains failure."
	::= { generator 5 }

generatorChargeTime  OBJECT-TYPE
	SYNTAX     Integer32
	MAX-ACCESS read-only
	STATUS     current
	DESCRIPTION 
		"Elapsing time of charging with generator running."
	::= { generator 6 }

generatorCapacityControlledStartStopEnable  OBJECT-TYPE
	SYNTAX     INTEGER {
		disabled (0),
		enabled (1)
	}
	MAX-ACCESS read-write
	STATUS     current
	DESCRIPTION 
		"Battery charge/discharge level control of starting and stopping of generator "
	::= { generator 7 }

generatorCapacityStartOnDischargeLimit  OBJECT-TYPE
	SYNTAX     Integer32 (0..100)
	MAX-ACCESS read-write
	STATUS     current
	DESCRIPTION 
		"When the generatorCapacityControlled is enabled, the generator is started 
		when the remaining battery capacity drops below this limit in percentage of the total capacity."
	::= { generator 8 }

generatorCapacityStopOnChargeLimit  OBJECT-TYPE
	SYNTAX     Integer32 (0..100)
	MAX-ACCESS read-write
	STATUS     current
	DESCRIPTION 
		"When the generatorCapacityControlled is enabled, the generator is stopped 
		when the remaining battery capacity is greater than this limit in percentage of the total capacity."
	::= { generator 9 }

generatorCurrentLimitControlledStopEnable  OBJECT-TYPE
	SYNTAX     INTEGER {
		disabled (0),
		enabled (1)
	}
	MAX-ACCESS read-write
	STATUS     current
	DESCRIPTION 
		"Enables the generator to stop when the charge current drops below generatorCurrentLimitControlledStopValue. "
	::= { generator 10 }

generatorCurrentLimitControlledStopValue  OBJECT-TYPE
	SYNTAX     Integer32 (0..100)
	MAX-ACCESS read-write
	STATUS     current
	DESCRIPTION 
		"Generator stops when the charge current drop drops below this level. "
	::= { generator 11 }

generatorVoltageControlledStartEnable  OBJECT-TYPE
	SYNTAX     INTEGER {
		disabled (0),
		enabled (1)
	}
	MAX-ACCESS read-write
	STATUS     current
	DESCRIPTION 
		"Enable/disable voltage controlled generator activation."
	::= { generator 12 }

generatorVoltageControlStartVoltage  OBJECT-TYPE
	SYNTAX     Integer32
	MAX-ACCESS read-write
	STATUS     current
	DESCRIPTION 
		"The voltage limit to start generator."
	::= { generator 13 }

generatorVoltageControlStopAfter  OBJECT-TYPE
	SYNTAX     Integer32
	MAX-ACCESS read-write
	STATUS     current
	DESCRIPTION 
		"A time delay for stopping generator when generator is activated by voltage."
	::= { generator 14 }

generatorDailyRunEnable  OBJECT-TYPE
	SYNTAX     INTEGER {
		disabled (0),
		enabled (1)
	}
	MAX-ACCESS read-write
	STATUS     current
	DESCRIPTION 
		"Enable/disable generator daily run function."
	::= { generator 15 }

generatorDailyRunSetupTable  OBJECT-TYPE
	SYNTAX SEQUENCE OF GeneratorDailyRunSetupEntry
	MAX-ACCESS not-accessible
	STATUS     current
	DESCRIPTION 
		"This table contains configurations of generator daily run."
	::= { generator 16 }

generatorDailyRunSetupEntry  OBJECT-TYPE
	SYNTAX 	GeneratorDailyRunSetupEntry
	MAX-ACCESS not-accessible
	STATUS     current
	DESCRIPTION 
		""
	INDEX { generatorDailyRunDayIndex }
	::= { generatorDailyRunSetupTable 1 }

GeneratorDailyRunSetupEntry ::= SEQUENCE {
	generatorDailyRunDayIndex
		INTEGER,
	generatorDailyRunStartHour
		Integer32,
	generatorDailyRunStopHour
		Integer32
}

generatorDailyRunDayIndex  OBJECT-TYPE
	SYNTAX     INTEGER {
		sunday (1),
		monday (2),
		tuesday (3),
		wednesday (4),
		thursday (5),
		friday (6),
		saturday (7)
	}
	MAX-ACCESS not-accessible
	STATUS     current
	DESCRIPTION 
		"Index used for navigating the rows 1..7  of generatorDailyRunSetupTable"
	::= { generatorDailyRunSetupEntry 1 }

generatorDailyRunStartHour  OBJECT-TYPE
	SYNTAX     Integer32 (0..23)
	MAX-ACCESS read-write
	STATUS     current
	DESCRIPTION 
		"Generator daily starting time."
	::= { generatorDailyRunSetupEntry 2 }

generatorDailyRunStopHour  OBJECT-TYPE
	SYNTAX     Integer32 (0..23)
	MAX-ACCESS read-write
	STATUS     current
	DESCRIPTION 
		"Generator daily stopping time."
	::= { generatorDailyRunSetupEntry 3 }

generatorMonthlyRunEnable  OBJECT-TYPE
	SYNTAX     INTEGER {
		disabled (0),
		enabled (1)
	}
	MAX-ACCESS read-write
	STATUS     current
	DESCRIPTION 
		"Enable/disable generator monthly run function."
	::= { generator 17 }

generatorMonthlyRunStartTime  OBJECT-TYPE
	SYNTAX     Integer32 (0..23)
	MAX-ACCESS read-write
	STATUS     current
	DESCRIPTION 
		"Generator monthly run starting time."
	::= { generator 18 }

generatorMonthlyRunStartDayinMonth1  OBJECT-TYPE
	SYNTAX     Integer32 (1..32)
	MAX-ACCESS read-write
	STATUS     current
	DESCRIPTION 
		"Generator monthly run starting day #1."
	::= { generator 19 }

generatorMonthlyRunStartDayinMonth2  OBJECT-TYPE
	SYNTAX     Integer32 (1..32)
	MAX-ACCESS read-write
	STATUS     current
	DESCRIPTION 
		"Generator monthly run starting day #2."
	::= { generator 20 }

generatorTankNumberOfTanks  OBJECT-TYPE
	SYNTAX     Integer32 (0..2)
	MAX-ACCESS read-only
	STATUS     current
	DESCRIPTION 
		"Number of fuel tanks."
	::= { generator 21 }

generatorTankTable  OBJECT-TYPE
	SYNTAX SEQUENCE OF GeneratorTankEntry
	MAX-ACCESS not-accessible
	STATUS     current
	DESCRIPTION 
		"This table contains information about generator fuel tanks."
	::= { generator 22 }

generatorTankEntry  OBJECT-TYPE
	SYNTAX 	GeneratorTankEntry
	MAX-ACCESS not-accessible
	STATUS     current
	DESCRIPTION 
		""
	INDEX { generatorTankIndex }
	::= { generatorTankTable 1 }

GeneratorTankEntry ::= SEQUENCE {
	generatorTankIndex
		Integer32,
	generatorTankStatus
		INTEGER,
	generatorTankDescription
		DisplayString,
	generatorTankTrapRepeatCounter
		Counter32,
	generatorTankEnable
		INTEGER,
	generatorTankValue
		Integer32,
	generatorTankMajorHighLevel
		Integer32,
	generatorTankMinorHighLevel
		Integer32,
	generatorTankMinorLowLevel
		Integer32,
	generatorTankMajorLowLevel
		Integer32
}

generatorTankIndex  OBJECT-TYPE
	SYNTAX     Integer32 (1..2)
	MAX-ACCESS not-accessible
	STATUS     current
	DESCRIPTION 
		"Index used for navigating the rows 1..2  of generatorTankTable"
	::= { generatorTankEntry 1 }

generatorTankStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured fuel level in tank."
	::= { generatorTankEntry 2 }

generatorTankDescription  OBJECT-TYPE
	SYNTAX     DisplayString (SIZE(0..16))
	MAX-ACCESS read-write
	STATUS     current
	DESCRIPTION 
		"A textual description of the fuel level monitor. This is stored in the system controller
		and can be changed by the user.  "
	::= { generatorTankEntry 3 }

generatorTankTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { generatorTankEntry 4 }

generatorTankEnable  OBJECT-TYPE
	SYNTAX     INTEGER {
		disabled (0),
		enabled (1)
	}
	MAX-ACCESS read-write
	STATUS     current
	DESCRIPTION 
		"This value once enabled, the alarm condition of the monitor will be reported."
	::= { generatorTankEntry 5 }

generatorTankValue  OBJECT-TYPE
	SYNTAX     Integer32
	MAX-ACCESS read-only
	STATUS     current
	DESCRIPTION 
		"The value of the measured fuel level."
	::= { generatorTankEntry 6 }

generatorTankMajorHighLevel  OBJECT-TYPE
	SYNTAX     Integer32
	MAX-ACCESS read-write
	STATUS     current
	DESCRIPTION 
		"The major high alarm limit"
	::= { generatorTankEntry 7 }

generatorTankMinorHighLevel  OBJECT-TYPE
	SYNTAX     Integer32
	MAX-ACCESS read-write
	STATUS     current
	DESCRIPTION 
		"The minor high alarm limit"
	::= { generatorTankEntry 8 }

generatorTankMinorLowLevel  OBJECT-TYPE
	SYNTAX     Integer32
	MAX-ACCESS read-write
	STATUS     current
	DESCRIPTION 
		"The minor low alarm limit"
	::= { generatorTankEntry 9 }

generatorTankMajorLowLevel  OBJECT-TYPE
	SYNTAX     Integer32
	MAX-ACCESS read-write
	STATUS     current
	DESCRIPTION 
		"The major low alarm limit"
	::= { generatorTankEntry 10 }

generatorEnergyLogAccumulated  OBJECT-TYPE
	SYNTAX     Integer32
	MAX-ACCESS read-only
	STATUS     current
	DESCRIPTION 
		"This is the accumulated energy delivered through rectifiers from generator."
	::= { generatorEnergyLog 1 }

generatorEnergyLogLastHoursNumberOfEntries  OBJECT-TYPE
	SYNTAX     Integer32 (0..52)
	MAX-ACCESS read-only
	STATUS     current
	DESCRIPTION 
		"This is the maximal number of entries stored in generator hourly energy log."
	::= { generatorEnergyLog 2 }

generatorEnergyLogLastHoursTable  OBJECT-TYPE
	SYNTAX SEQUENCE OF GeneratorEnergyLogLastHoursEntry
	MAX-ACCESS not-accessible
	STATUS     current
	DESCRIPTION 
		"This table contains hourly energy log of generator."
	::= { generatorEnergyLog 3 }

generatorEnergyLogLastHoursEntry  OBJECT-TYPE
	SYNTAX 	GeneratorEnergyLogLastHoursEntry
	MAX-ACCESS not-accessible
	STATUS     current
	DESCRIPTION 
		""
	INDEX { generatorEnergyLogLastHoursIndex }
	::= { generatorEnergyLogLastHoursTable 1 }

GeneratorEnergyLogLastHoursEntry ::= SEQUENCE {
	generatorEnergyLogLastHoursIndex
		Integer32,
	generatorEnergyLogLastHoursValue
		Integer32
}

generatorEnergyLogLastHoursIndex  OBJECT-TYPE
	SYNTAX     Integer32 (1..52)
	MAX-ACCESS not-accessible
	STATUS     current
	DESCRIPTION 
		"Index used for navigating the rows 1..52  of generatorEnergyLogLastHoursTable"
	::= { generatorEnergyLogLastHoursEntry 1 }

generatorEnergyLogLastHoursValue  OBJECT-TYPE
	SYNTAX     Integer32
	MAX-ACCESS read-only
	STATUS     current
	DESCRIPTION 
		"Energy value logged every hour."
	::= { generatorEnergyLogLastHoursEntry 2 }

generatorEnergyLogLastDaysNumberOfEntries  OBJECT-TYPE
	SYNTAX     Integer32 (0..52)
	MAX-ACCESS read-only
	STATUS     current
	DESCRIPTION 
		"This is the maximal number of entries stored in generator daily energy log."
	::= { generatorEnergyLog 4 }

generatorEnergyLogLastDaysTable  OBJECT-TYPE
	SYNTAX SEQUENCE OF GeneratorEnergyLogLastDaysEntry
	MAX-ACCESS not-accessible
	STATUS     current
	DESCRIPTION 
		"This table contains daily energy log of generator."
	::= { generatorEnergyLog 5 }

generatorEnergyLogLastDaysEntry  OBJECT-TYPE
	SYNTAX 	GeneratorEnergyLogLastDaysEntry
	MAX-ACCESS not-accessible
	STATUS     current
	DESCRIPTION 
		""
	INDEX { generatorEnergyLogLastDaysIndex }
	::= { generatorEnergyLogLastDaysTable 1 }

GeneratorEnergyLogLastDaysEntry ::= SEQUENCE {
	generatorEnergyLogLastDaysIndex
		Integer32,
	generatorEnergyLogLastDaysValue
		Integer32
}

generatorEnergyLogLastDaysIndex  OBJECT-TYPE
	SYNTAX     Integer32 (1..52)
	MAX-ACCESS not-accessible
	STATUS     current
	DESCRIPTION 
		"Index used for navigating the rows 1..52  of generatorEnergyLogLastDaysTable"
	::= { generatorEnergyLogLastDaysEntry 1 }

generatorEnergyLogLastDaysValue  OBJECT-TYPE
	SYNTAX     Integer32
	MAX-ACCESS read-only
	STATUS     current
	DESCRIPTION 
		"Energy value logged every day"
	::= { generatorEnergyLogLastDaysEntry 2 }

generatorEnergyLogLastWeeksNumberOfEntries  OBJECT-TYPE
	SYNTAX     Integer32 (0..52)
	MAX-ACCESS read-only
	STATUS     current
	DESCRIPTION 
		"This is the maximal number of entries stored in generator weekly energy log."
	::= { generatorEnergyLog 6 }

generatorEnergyLogLastWeeksTable  OBJECT-TYPE
	SYNTAX SEQUENCE OF GeneratorEnergyLogLastWeeksEntry
	MAX-ACCESS not-accessible
	STATUS     current
	DESCRIPTION 
		"This table contains weekly energy log of generator."
	::= { generatorEnergyLog 7 }

generatorEnergyLogLastWeeksEntry  OBJECT-TYPE
	SYNTAX 	GeneratorEnergyLogLastWeeksEntry
	MAX-ACCESS not-accessible
	STATUS     current
	DESCRIPTION 
		""
	INDEX { generatorEnergyLogLastWeeksIndex }
	::= { generatorEnergyLogLastWeeksTable 1 }

GeneratorEnergyLogLastWeeksEntry ::= SEQUENCE {
	generatorEnergyLogLastWeeksIndex
		Integer32,
	generatorEnergyLogLastWeeksValue
		Integer32
}

generatorEnergyLogLastWeeksIndex  OBJECT-TYPE
	SYNTAX     Integer32 (1..52)
	MAX-ACCESS not-accessible
	STATUS     current
	DESCRIPTION 
		"Index used for navigating the rows 1..52  of generatorEnergyLogLastWeeksTable"
	::= { generatorEnergyLogLastWeeksEntry 1 }

generatorEnergyLogLastWeeksValue  OBJECT-TYPE
	SYNTAX     Integer32
	MAX-ACCESS read-only
	STATUS     current
	DESCRIPTION 
		"Energy value logged every week."
	::= { generatorEnergyLogLastWeeksEntry 2 }

generatorRunHoursTotalHours  OBJECT-TYPE
	SYNTAX     Integer32
	MAX-ACCESS read-only
	STATUS     current
	DESCRIPTION 
		"This is the total generator running hours."
	::= { generatorRunHoursLog 1 }

generatorRunHoursLogLastDaysNumberOfEntries  OBJECT-TYPE
	SYNTAX     Integer32 (0..52)
	MAX-ACCESS read-only
	STATUS     current
	DESCRIPTION 
		"This is the maximal number of entries stored in generator daily running hours log."
	::= { generatorRunHoursLog 2 }

generatorRunHoursLogLastDaysTable  OBJECT-TYPE
	SYNTAX SEQUENCE OF GeneratorRunHoursLogLastDaysEntry
	MAX-ACCESS not-accessible
	STATUS     current
	DESCRIPTION 
		"generator running time in minutes"
	::= { generatorRunHoursLog 3 }

generatorRunHoursLogLastDaysEntry  OBJECT-TYPE
	SYNTAX 	GeneratorRunHoursLogLastDaysEntry
	MAX-ACCESS not-accessible
	STATUS     current
	DESCRIPTION 
		""
	INDEX { generatorRunHoursLogLastDaysIndex }
	::= { generatorRunHoursLogLastDaysTable 1 }

GeneratorRunHoursLogLastDaysEntry ::= SEQUENCE {
	generatorRunHoursLogLastDaysIndex
		Integer32,
	generatorRunHoursLogLastDaysValue
		Integer32
}

generatorRunHoursLogLastDaysIndex  OBJECT-TYPE
	SYNTAX     Integer32 (1..52)
	MAX-ACCESS not-accessible
	STATUS     current
	DESCRIPTION 
		"Index used for navigating the rows 1..52  of generatorRunHoursLogLastDaysTable"
	::= { generatorRunHoursLogLastDaysEntry 1 }

generatorRunHoursLogLastDaysValue  OBJECT-TYPE
	SYNTAX     Integer32
	MAX-ACCESS read-only
	STATUS     current
	DESCRIPTION 
		"Generator running time in minutes, logged every day."
	::= { generatorRunHoursLogLastDaysEntry 2 }

generatorRunHoursLogLastWeeksNumberOfEntries  OBJECT-TYPE
	SYNTAX     Integer32 (0..52)
	MAX-ACCESS read-only
	STATUS     current
	DESCRIPTION 
		"This is the maximal number of entries stored in generator weekly running hours log."
	::= { generatorRunHoursLog 4 }

generatorRunHoursLogLastWeeksTable  OBJECT-TYPE
	SYNTAX SEQUENCE OF GeneratorRunHoursLogLastWeeksEntry
	MAX-ACCESS not-accessible
	STATUS     current
	DESCRIPTION 
		"generator running time in hours"
	::= { generatorRunHoursLog 5 }

generatorRunHoursLogLastWeeksEntry  OBJECT-TYPE
	SYNTAX 	GeneratorRunHoursLogLastWeeksEntry
	MAX-ACCESS not-accessible
	STATUS     current
	DESCRIPTION 
		""
	INDEX { generatorRunHoursLogLastWeeksIndex }
	::= { generatorRunHoursLogLastWeeksTable 1 }

GeneratorRunHoursLogLastWeeksEntry ::= SEQUENCE {
	generatorRunHoursLogLastWeeksIndex
		Integer32,
	generatorRunHoursLogLastWeeksValue
		Integer32
}

generatorRunHoursLogLastWeeksIndex  OBJECT-TYPE
	SYNTAX     Integer32 (1..52)
	MAX-ACCESS not-accessible
	STATUS     current
	DESCRIPTION 
		"Index used for navigating the rows 1..52  of generatorRunHoursLogLastWeeksTable"
	::= { generatorRunHoursLogLastWeeksEntry 1 }

generatorRunHoursLogLastWeeksValue  OBJECT-TYPE
	SYNTAX     Integer32
	MAX-ACCESS read-only
	STATUS     current
	DESCRIPTION 
		"Generator running time in hours, logged every week."
	::= { generatorRunHoursLogLastWeeksEntry 2 }

generatorRunHoursLogLastMonthsNumberOfEntries  OBJECT-TYPE
	SYNTAX     Integer32 (0..52)
	MAX-ACCESS read-only
	STATUS     current
	DESCRIPTION 
		"This is the maximal number of entries stored in generator monthly running hours log."
	::= { generatorRunHoursLog 6 }

generatorRunHoursLogLastMonthsTable  OBJECT-TYPE
	SYNTAX SEQUENCE OF GeneratorRunHoursLogLastMonthsEntry
	MAX-ACCESS not-accessible
	STATUS     current
	DESCRIPTION 
		"generator running time in hours"
	::= { generatorRunHoursLog 7 }

generatorRunHoursLogLastMonthsEntry  OBJECT-TYPE
	SYNTAX 	GeneratorRunHoursLogLastMonthsEntry
	MAX-ACCESS not-accessible
	STATUS     current
	DESCRIPTION 
		""
	INDEX { generatorRunHoursLogLastMonthsIndex }
	::= { generatorRunHoursLogLastMonthsTable 1 }

GeneratorRunHoursLogLastMonthsEntry ::= SEQUENCE {
	generatorRunHoursLogLastMonthsIndex
		Integer32,
	generatorRunHoursLogLastMonthsValue
		Integer32
}

generatorRunHoursLogLastMonthsIndex  OBJECT-TYPE
	SYNTAX     Integer32 (1..52)
	MAX-ACCESS not-accessible
	STATUS     current
	DESCRIPTION 
		"Index used for navigating the rows 1..52  of generatorRunHoursLogLastMonthsTable"
	::= { generatorRunHoursLogLastMonthsEntry 1 }

generatorRunHoursLogLastMonthsValue  OBJECT-TYPE
	SYNTAX     Integer32
	MAX-ACCESS read-only
	STATUS     current
	DESCRIPTION 
		"Generator running time in hours, logged every month."
	::= { generatorRunHoursLogLastMonthsEntry 2 }

generatorFuelConsumptionTotalUsedTable  OBJECT-TYPE
	SYNTAX SEQUENCE OF GeneratorFuelConsumptionTotalUsedEntry
	MAX-ACCESS not-accessible
	STATUS     current
	DESCRIPTION 
		"This table contains total fuel consumption for each tank."
	::= { generatorFuelConsumptionLog 1 }

generatorFuelConsumptionTotalUsedEntry  OBJECT-TYPE
	SYNTAX 	GeneratorFuelConsumptionTotalUsedEntry
	MAX-ACCESS not-accessible
	STATUS     current
	DESCRIPTION 
		""
	INDEX { generatorTankIndex }
	::= { generatorFuelConsumptionTotalUsedTable 1 }

GeneratorFuelConsumptionTotalUsedEntry ::= SEQUENCE {
	generatorFuelConsumptionTotalUsed
		Integer32
}

generatorFuelConsumptionTotalUsed  OBJECT-TYPE
	SYNTAX     Integer32
	MAX-ACCESS read-only
	STATUS     current
	DESCRIPTION 
		"Total fuel consumption value."
	::= { generatorFuelConsumptionTotalUsedEntry 1 }

generatorFuelConsumptionLogLastDaysNoOfEntries  OBJECT-TYPE
	SYNTAX     Integer32 (0..52)
	MAX-ACCESS read-only
	STATUS     current
	DESCRIPTION 
		"This is the maximal number of entries stored in generator daily fuel consumption log."
	::= { generatorFuelConsumptionLog 2 }

generatorFuelConsumptionLogLastDaysTable  OBJECT-TYPE
	SYNTAX SEQUENCE OF GeneratorFuelConsumptionLogLastDaysEntry
	MAX-ACCESS not-accessible
	STATUS     current
	DESCRIPTION 
		"This table contains generator daily fuel consumption log."
	::= { generatorFuelConsumptionLog 3 }

generatorFuelConsumptionLogLastDaysEntry  OBJECT-TYPE
	SYNTAX 	GeneratorFuelConsumptionLogLastDaysEntry
	MAX-ACCESS not-accessible
	STATUS     current
	DESCRIPTION 
		""
	INDEX { generatorTankIndex, 
		generatorFuelConsumptionLogLastDaysIndex }
	::= { generatorFuelConsumptionLogLastDaysTable 1 }

GeneratorFuelConsumptionLogLastDaysEntry ::= SEQUENCE {
	generatorFuelConsumptionLogLastDaysIndex
		Integer32,
	generatorFuelConsumptionLogLastDaysValue
		Integer32
}

generatorFuelConsumptionLogLastDaysIndex  OBJECT-TYPE
	SYNTAX     Integer32 (1..52)
	MAX-ACCESS not-accessible
	STATUS     current
	DESCRIPTION 
		"Index used for navigating the rows 1..52  of generatorFuelConsumptionLogLastDaysTable"
	::= { generatorFuelConsumptionLogLastDaysEntry 1 }

generatorFuelConsumptionLogLastDaysValue  OBJECT-TYPE
	SYNTAX     Integer32
	MAX-ACCESS read-only
	STATUS     current
	DESCRIPTION 
		"Generator fuel consumption value, logged every day."
	::= { generatorFuelConsumptionLogLastDaysEntry 2 }

generatorFuelConsumptionLogLastWeeksNoOfEntries  OBJECT-TYPE
	SYNTAX     Integer32 (0..52)
	MAX-ACCESS read-only
	STATUS     current
	DESCRIPTION 
		"This is the maximal number of entries stored in generator weekly fuel consumption log."
	::= { generatorFuelConsumptionLog 4 }

generatorFuelConsumptionLogLastWeeksTable  OBJECT-TYPE
	SYNTAX SEQUENCE OF GeneratorFuelConsumptionLogLastWeeksEntry
	MAX-ACCESS not-accessible
	STATUS     current
	DESCRIPTION 
		"This table contains generator weekly fuel consumption log."
	::= { generatorFuelConsumptionLog 5 }

generatorFuelConsumptionLogLastWeeksEntry  OBJECT-TYPE
	SYNTAX 	GeneratorFuelConsumptionLogLastWeeksEntry
	MAX-ACCESS not-accessible
	STATUS     current
	DESCRIPTION 
		""
	INDEX { generatorTankIndex, 
		generatorFuelConsumptionLogLastWeeksIndex }
	::= { generatorFuelConsumptionLogLastWeeksTable 1 }

GeneratorFuelConsumptionLogLastWeeksEntry ::= SEQUENCE {
	generatorFuelConsumptionLogLastWeeksIndex
		Integer32,
	generatorFuelConsumptionLogLastWeeksValue
		Integer32
}

generatorFuelConsumptionLogLastWeeksIndex  OBJECT-TYPE
	SYNTAX     Integer32 (1..52)
	MAX-ACCESS not-accessible
	STATUS     current
	DESCRIPTION 
		"Index used for navigating the rows 1..52  of generatorFuelConsumptionLogLastWeeksTable"
	::= { generatorFuelConsumptionLogLastWeeksEntry 1 }

generatorFuelConsumptionLogLastWeeksValue  OBJECT-TYPE
	SYNTAX     Integer32
	MAX-ACCESS read-only
	STATUS     current
	DESCRIPTION 
		"Generator fuel consumption value, logged every week."
	::= { generatorFuelConsumptionLogLastWeeksEntry 2 }

generatorFuelConsumptionLogLastMonthsNoOfEntries  OBJECT-TYPE
	SYNTAX     Integer32 (0..52)
	MAX-ACCESS read-only
	STATUS     current
	DESCRIPTION 
		"This is the maximal number of entries stored in generator hourly fuel consumption log."
	::= { generatorFuelConsumptionLog 6 }

generatorFuelConsumptionLogLastMonthsTable  OBJECT-TYPE
	SYNTAX SEQUENCE OF GeneratorFuelConsumptionLogLastMonthsEntry
	MAX-ACCESS not-accessible
	STATUS     current
	DESCRIPTION 
		"This table contains generator hourly fuel consumption log."
	::= { generatorFuelConsumptionLog 7 }

generatorFuelConsumptionLogLastMonthsEntry  OBJECT-TYPE
	SYNTAX 	GeneratorFuelConsumptionLogLastMonthsEntry
	MAX-ACCESS not-accessible
	STATUS     current
	DESCRIPTION 
		""
	INDEX { generatorTankIndex, 
		generatorFuelConsumptionLogLastMonthsIndex }
	::= { generatorFuelConsumptionLogLastMonthsTable 1 }

GeneratorFuelConsumptionLogLastMonthsEntry ::= SEQUENCE {
	generatorFuelConsumptionLogLastMonthsIndex
		Integer32,
	generatorFuelConsumptionLogLastMonthsValue
		Integer32
}

generatorFuelConsumptionLogLastMonthsIndex  OBJECT-TYPE
	SYNTAX     Integer32 (1..52)
	MAX-ACCESS not-accessible
	STATUS     current
	DESCRIPTION 
		"Index used for navigating the rows 1..52  of generatorFuelConsumptionLogLastHoursTable"
	::= { generatorFuelConsumptionLogLastMonthsEntry 1 }

generatorFuelConsumptionLogLastMonthsValue  OBJECT-TYPE
	SYNTAX     Integer32
	MAX-ACCESS read-only
	STATUS     current
	DESCRIPTION 
		"Generator fuel consumption value, logged every hour."
	::= { generatorFuelConsumptionLogLastMonthsEntry 2 }

gseGeneratorOilPressure  OBJECT-TYPE
	SYNTAX     Integer32
	MAX-ACCESS read-only
	STATUS     current
	DESCRIPTION 
		"Oil pressure in kpa"
	::= { gseGenerator 1 }

gseGeneratorCoolantTemperature  OBJECT-TYPE
	SYNTAX     Integer32
	MAX-ACCESS read-only
	STATUS     current
	DESCRIPTION 
		"Coolant temperature"
	::= { gseGenerator 2 }

gseGeneratorFuelLevel  OBJECT-TYPE
	SYNTAX     Integer32
	MAX-ACCESS read-only
	STATUS     current
	DESCRIPTION 
		"Fuel level in percentage"
	::= { gseGenerator 3 }

gseGeneratorEngineBatteryVoltage  OBJECT-TYPE
	SYNTAX     Integer32
	MAX-ACCESS read-only
	STATUS     current
	DESCRIPTION 
		"Engine Battery voltage"
	::= { gseGenerator 4 }

gseGeneratorEngineSpeed  OBJECT-TYPE
	SYNTAX     Integer32
	MAX-ACCESS read-only
	STATUS     current
	DESCRIPTION 
		"Engine speed in RPM"
	::= { gseGenerator 5 }

gseGeneratorFrequency  OBJECT-TYPE
	SYNTAX     Integer32
	MAX-ACCESS read-only
	STATUS     current
	DESCRIPTION 
		"Generator frequency in Hz"
	::= { gseGenerator 6 }

gseGeneratorEngineRunTime  OBJECT-TYPE
	SYNTAX     Integer32
	MAX-ACCESS read-only
	STATUS     current
	DESCRIPTION 
		"Engine run time in seconds"
	::= { gseGenerator 7 }

gseGeneratorMode  OBJECT-TYPE
	SYNTAX     INTEGER {
		stop (0),
		auto (1),
		manual (2),
		testOnLoad (3),
		autoWithManualRestore (4),
		userConfigutation (5),
		off (6)
	}
	MAX-ACCESS read-only
	STATUS     current
	DESCRIPTION 
		"Generator Auto/manual mode"
	::= { gseGenerator 8 }

gseGeneratorRunning  OBJECT-TYPE
	SYNTAX     INTEGER {
		engineStopped (0),
		prestart (1),
		warmingUp (2),
		running (3),
		coolingDown (4),
		engineStoped (5),
		postRun (6),
		notDefined (7),
		sae1 (8),
		sae2 (9),
		sae3 (10),
		sae4 (11),
		sae5 (12),
		sae6 (13),
		reserved (14),
		notAvailable (15)
	}
	MAX-ACCESS read-only
	STATUS     current
	DESCRIPTION 
		"generator operating state"
	::= { gseGenerator 9 }

gseGeneratorHighTemperature  OBJECT-TYPE
	SYNTAX     INTEGER {
		disabledInput (0),
		notActiveAlarm (1),
		warningAlarm (2),
		shutdownAlarm (3),
		electricalTripAlarm (4),
		controlledShutdownAlarm (5),
		reserved1 (6),
		reserved2 (7),
		inactiveIndication1 (8),
		inactiveIndication2 (9),
		activeIndication (10),
		reserved3 (11),
		unimplementedAlarm (12)
	}
	MAX-ACCESS read-only
	STATUS     current
	DESCRIPTION 
		""
	::= { gseGenerator 10 }

gseGeneratorLowOilPressure  OBJECT-TYPE
	SYNTAX     INTEGER {
		disabledInput (0),
		notActiveAlarm (1),
		warningAlarm (2),
		shutdownAlarm (3),
		electricalTripAlarm (4),
		controlledShutdownAlarm (5),
		reserved1 (6),
		reserved2 (7),
		inactiveIndication1 (8),
		inactiveIndication2 (9),
		activeIndication (10),
		reserved3 (11),
		unimplementedAlarm (12)
	}
	MAX-ACCESS read-only
	STATUS     current
	DESCRIPTION 
		""
	::= { gseGenerator 11 }

gseGeneratorFuelProbeFail  OBJECT-TYPE
	SYNTAX     INTEGER {
		disabledInput (0),
		notActiveAlarm (1),
		warningAlarm (2),
		shutdownAlarm (3),
		electricalTripAlarm (4),
		controlledShutdownAlarm (5),
		reserved1 (6),
		reserved2 (7),
		inactiveIndication1 (8),
		inactiveIndication2 (9),
		activeIndication (10),
		reserved3 (11),
		unimplementedAlarm (12)
	}
	MAX-ACCESS read-only
	STATUS     current
	DESCRIPTION 
		""
	::= { gseGenerator 12 }

gseGeneratorFuelTankLevelLow  OBJECT-TYPE
	SYNTAX     INTEGER {
		disabledInput (0),
		notActiveAlarm (1),
		warningAlarm (2),
		shutdownAlarm (3),
		electricalTripAlarm (4),
		controlledShutdownAlarm (5),
		reserved1 (6),
		reserved2 (7),
		inactiveIndication1 (8),
		inactiveIndication2 (9),
		activeIndication (10),
		reserved3 (11),
		unimplementedAlarm (12)
	}
	MAX-ACCESS read-only
	STATUS     current
	DESCRIPTION 
		""
	::= { gseGenerator 13 }

gseGeneratorFuelTankLoss  OBJECT-TYPE
	SYNTAX     INTEGER {
		disabledInput (0),
		notActiveAlarm (1),
		warningAlarm (2),
		shutdownAlarm (3),
		electricalTripAlarm (4),
		controlledShutdownAlarm (5),
		reserved1 (6),
		reserved2 (7),
		inactiveIndication1 (8),
		inactiveIndication2 (9),
		activeIndication (10),
		reserved3 (11),
		unimplementedAlarm (12)
	}
	MAX-ACCESS read-only
	STATUS     current
	DESCRIPTION 
		""
	::= { gseGenerator 14 }

gseGeneratorRMSCommunicationFailure  OBJECT-TYPE
	SYNTAX     INTEGER {
		disabledInput (0),
		notActiveAlarm (1),
		warningAlarm (2),
		shutdownAlarm (3),
		electricalTripAlarm (4),
		controlledShutdownAlarm (5),
		reserved1 (6),
		reserved2 (7),
		inactiveIndication1 (8),
		inactiveIndication2 (9),
		activeIndication (10),
		reserved3 (11),
		unimplementedAlarm (12)
	}
	MAX-ACCESS read-only
	STATUS     current
	DESCRIPTION 
		""
	::= { gseGenerator 15 }

gseGeneratorOtherAlarms  OBJECT-TYPE
	SYNTAX     INTEGER {
		disabledInput (0),
		notActiveAlarm (1),
		warningAlarm (2),
		shutdownAlarm (3),
		electricalTripAlarm (4),
		controlledShutdownAlarm (5),
		reserved1 (6),
		reserved2 (7),
		inactiveIndication1 (8),
		inactiveIndication2 (9),
		activeIndication (10),
		reserved3 (11),
		unimplementedAlarm (12)
	}
	MAX-ACCESS read-only
	STATUS     current
	DESCRIPTION 
		""
	::= { gseGenerator 16 }

generatorFailureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed phases is higher than the defined alarm level."
	::= { generatorFailure 1 }

generatorFailureDescription  OBJECT-TYPE
	SYNTAX     DisplayString (SIZE(0..16))
	MAX-ACCESS read-write
	STATUS     current
	DESCRIPTION 
		"A textual description of the generator failure monitor. This is stored in the system controller
		and can be changed by the user."
	::= { generatorFailure 2 }

generatorFailureTrapRepeatCounter  OBJECT-TYPE
	SYNTAX     Integer32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { generatorFailure 3 }

generatorFailureAlarmEnable  OBJECT-TYPE
	SYNTAX     INTEGER {
		disabled (0),
		enabled (1)
	}
	MAX-ACCESS read-write
	STATUS     current
	DESCRIPTION 
		"This value once enabled, the alarm condition of the monitor will be reported."
	::= { generatorFailure 4 }

generatorFailureValue  OBJECT-TYPE
	SYNTAX     Integer32
	MAX-ACCESS read-only
	STATUS     current
	DESCRIPTION 
		"The value of the monitor."
	::= { generatorFailure 5 }

rectifiersStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of rectifier subsystem."
	::= { rectifiers 1 }

rectifiersCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { rectifiersCurrent 1 }

rectifiersCurrentDescription  OBJECT-TYPE
	SYNTAX     DisplayString (SIZE(0..16))
	MAX-ACCESS read-write
	STATUS     current
	DESCRIPTION 
		"A textual description of the total rectifier current monitor. This is stored in the system controller
		and can be changed by the user"
	::= { rectifiersCurrent 2 }

rectifiersCurrentTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectifiersCurrent 3 }

rectifiersCurrentAlarmEnable  OBJECT-TYPE
	SYNTAX     INTEGER {
		disabled (0),
		enabled (1)
	}
	MAX-ACCESS read-write
	STATUS     current
	DESCRIPTION 
		"This value once enabled, the alarm condition of the monitor will be reported."
	::= { rectifiersCurrent 4 }

rectifiersCurrentValue  OBJECT-TYPE
	SYNTAX     Integer32
	MAX-ACCESS read-only
	STATUS     current
	DESCRIPTION 
		"The value of the measured total rectifier current."
	::= { rectifiersCurrent 5 }

rectifiersCurrentMajorAlarmLevel  OBJECT-TYPE
	SYNTAX     Integer32
	MAX-ACCESS read-write
	STATUS     current
	DESCRIPTION 
		"The major alarm limit"
	::= { rectifiersCurrent 6 }

rectifiersCurrentMinorAlarmLevel  OBJECT-TYPE
	SYNTAX     Integer32
	MAX-ACCESS read-write
	STATUS     current
	DESCRIPTION 
		"The minor alarm limit"
	::= { rectifiersCurrent 7 }

rectifiersCapacityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured used rectifier capacity."
	::= { rectifiersCapacity 1 }

rectifiersCapacityDescription  OBJECT-TYPE
	SYNTAX     DisplayString (SIZE(0..16))
	MAX-ACCESS read-write
	STATUS     current
	DESCRIPTION 
		"A textual description of the used rectifier capacity monitor. This is stored in the system controller
		and can be changed by the user"
	::= { rectifiersCapacity 2 }

rectifiersCapacityTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectifiersCapacity 3 }

rectifiersCapacityAlarmEnable  OBJECT-TYPE
	SYNTAX     INTEGER {
		disabled (0),
		enabled (1)
	}
	MAX-ACCESS read-write
	STATUS     current
	DESCRIPTION 
		"This value once enabled, the alarm condition of the monitor will be reported."
	::= { rectifiersCapacity 4 }

rectifiersCapacityValue  OBJECT-TYPE
	SYNTAX     Integer32
	MAX-ACCESS read-only
	STATUS     current
	DESCRIPTION 
		"The used rectifier capacity value presented in percentage of the total installed rectifier capacity."
	::= { rectifiersCapacity 5 }

rectifiersCapacityMajorAlarmLevel  OBJECT-TYPE
	SYNTAX     Integer32
	MAX-ACCESS read-write
	STATUS     current
	DESCRIPTION 
		"The major alarm limit"
	::= { rectifiersCapacity 6 }

rectifiersCapacityMinorAlarmLevel  OBJECT-TYPE
	SYNTAX     Integer32
	MAX-ACCESS read-write
	STATUS     current
	DESCRIPTION 
		"The minor alarm limit"
	::= { rectifiersCapacity 7 }

rectifiersErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed units is higher than the defined alarm level."
	::= { rectifiersError 1 }

rectifiersErrorDescription  OBJECT-TYPE
	SYNTAX     DisplayString (SIZE(0..16))
	MAX-ACCESS read-write
	STATUS     current
	DESCRIPTION 
		"A textual description of the rectifier error monitor. This is stored in the system controller
		and can be changed by the user"
	::= { rectifiersError 2 }

rectifiersErrorTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectifiersError 3 }

rectifiersErrorEnable  OBJECT-TYPE
	SYNTAX     INTEGER {
		disabled (0),
		enabled (1)
	}
	MAX-ACCESS read-write
	STATUS     current
	DESCRIPTION 
		"This value once enabled, the alarm condition of the monitor will be reported."
	::= { rectifiersError 4 }

rectifiersErrorValue  OBJECT-TYPE
	SYNTAX     Integer32
	MAX-ACCESS read-only
	STATUS     current
	DESCRIPTION 
		"The number of failed rectifiers."
	::= { rectifiersError 5 }

rectifiersErrorMajorAlarmLevel  OBJECT-TYPE
	SYNTAX     Integer32
	MAX-ACCESS read-write
	STATUS     current
	DESCRIPTION 
		"The major alarm limit"
	::= { rectifiersError 6 }

rectifiersErrorMinorAlarmLevel  OBJECT-TYPE
	SYNTAX     Integer32
	MAX-ACCESS read-write
	STATUS     current
	DESCRIPTION 
		"The minor alarm limit"
	::= { rectifiersError 7 }

rectifiersNumberOfRectifiers  OBJECT-TYPE
	SYNTAX     Integer32 (0..100)
	MAX-ACCESS read-write
	STATUS     current
	DESCRIPTION 
		"Number of installed rectifiers."
	::= { rectifiers 5 }

rectifierTable  OBJECT-TYPE
	SYNTAX SEQUENCE OF RectifierEntry
	MAX-ACCESS not-accessible
	STATUS     current
	DESCRIPTION 
		"This table shows the information of each rectifier installed in the system."
	::= { rectifiers 6 }

rectifierEntry  OBJECT-TYPE
	SYNTAX 	RectifierEntry
	MAX-ACCESS not-accessible
	STATUS     current
	DESCRIPTION 
		""
	INDEX { rectifierIndex }
	::= { rectifierTable 1 }

RectifierEntry ::= SEQUENCE {
	rectifierIndex
		Integer32,
	rectifierStatus
		INTEGER,
	rectifierOutputCurrentValue
		Integer32,
	rectifierInputVoltageValue
		Integer32,
	rectifierType
		DisplayString,
	rectifierHwPartNumber
		DisplayString,
	rectifierHwVersion
		DisplayString,
	rectifierSwPartNumber
		DisplayString,
	rectifierSwVersion
		DisplayString,
	rectifierSerialNumber
		DisplayString
}

rectifierIndex  OBJECT-TYPE
	SYNTAX     Integer32 (1..100)
	MAX-ACCESS not-accessible
	STATUS     current
	DESCRIPTION 
		"Index used for navigating the rows 1..100  of rectifierTable"
	::= { rectifierEntry 1 }

rectifierStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of rectifier."
	::= { rectifierEntry 2 }

rectifierOutputCurrentValue  OBJECT-TYPE
	SYNTAX     Integer32
	MAX-ACCESS read-only
	STATUS     current
	DESCRIPTION 
		"The output current value of rectifier."
	::= { rectifierEntry 3 }

rectifierInputVoltageValue  OBJECT-TYPE
	SYNTAX     Integer32
	MAX-ACCESS read-only
	STATUS     current
	DESCRIPTION 
		"The input voltage value of rectifier."
	::= { rectifierEntry 4 }

rectifierType  OBJECT-TYPE
	SYNTAX     DisplayString (SIZE(0..27))
	MAX-ACCESS read-only
	STATUS     current
	DESCRIPTION 
		"Type of rectifier"
	::= { rectifierEntry 5 }

rectifierHwPartNumber  OBJECT-TYPE
	SYNTAX     DisplayString (SIZE(0..12))
	MAX-ACCESS read-only
	STATUS     current
	DESCRIPTION 
		"Hardware part number of rectifier"
	::= { rectifierEntry 6 }

rectifierHwVersion  OBJECT-TYPE
	SYNTAX     DisplayString (SIZE(0..6))
	MAX-ACCESS read-only
	STATUS     current
	DESCRIPTION 
		"Hardware version number of rectifier"
	::= { rectifierEntry 7 }

rectifierSwPartNumber  OBJECT-TYPE
	SYNTAX     DisplayString (SIZE(0..12))
	MAX-ACCESS read-only
	STATUS     current
	DESCRIPTION 
		"Part number of secondary software in rectifier"
	::= { rectifierEntry 8 }

rectifierSwVersion  OBJECT-TYPE
	SYNTAX     DisplayString (SIZE(0..6))
	MAX-ACCESS read-only
	STATUS     current
	DESCRIPTION 
		"Version number of secondary software in rectifier"
	::= { rectifierEntry 9 }

rectifierSerialNumber  OBJECT-TYPE
	SYNTAX     DisplayString (SIZE(1..12))
	MAX-ACCESS read-only
	STATUS     current
	DESCRIPTION 
		"Serial number of rectifier"
	::= { rectifierEntry 10 }

rectifiersEnergyLogAccumulated  OBJECT-TYPE
	SYNTAX     Integer32
	MAX-ACCESS read-only
	STATUS     current
	DESCRIPTION 
		"This is the accumulated energy delivered from rectifiers."
	::= { rectifiersEnergyLog 1 }

rectifiersEnergyLogLastHoursNumberOfEntries  OBJECT-TYPE
	SYNTAX     Integer32 (0..52)
	MAX-ACCESS read-only
	STATUS     current
	DESCRIPTION 
		"This is the maximal number of entries stored in rectifier hourly energy log."
	::= { rectifiersEnergyLog 2 }

rectifiersEnergyLogLastHoursTable  OBJECT-TYPE
	SYNTAX SEQUENCE OF RectifiersEnergyLogLastHoursEntry
	MAX-ACCESS not-accessible
	STATUS     current
	DESCRIPTION 
		"This table contains hourly energy log of rectifiers."
	::= { rectifiersEnergyLog 3 }

rectifiersEnergyLogLastHoursEntry  OBJECT-TYPE
	SYNTAX 	RectifiersEnergyLogLastHoursEntry
	MAX-ACCESS not-accessible
	STATUS     current
	DESCRIPTION 
		""
	INDEX { rectifiersEnergyLogLastHoursIndex }
	::= { rectifiersEnergyLogLastHoursTable 1 }

RectifiersEnergyLogLastHoursEntry ::= SEQUENCE {
	rectifiersEnergyLogLastHoursIndex
		Integer32,
	rectifiersEnergyLogLastHoursValue
		Integer32
}

rectifiersEnergyLogLastHoursIndex  OBJECT-TYPE
	SYNTAX     Integer32 (1..52)
	MAX-ACCESS not-accessible
	STATUS     current
	DESCRIPTION 
		"Index used for navigating the rows 1..52  of rectifiersEnergyLogLastHoursTable"
	::= { rectifiersEnergyLogLastHoursEntry 1 }

rectifiersEnergyLogLastHoursValue  OBJECT-TYPE
	SYNTAX     Integer32
	MAX-ACCESS read-only
	STATUS     current
	DESCRIPTION 
		"Energy value logged every hour."
	::= { rectifiersEnergyLogLastHoursEntry 2 }

rectifiersEnergyLogLastDaysNumberOfEntries  OBJECT-TYPE
	SYNTAX     Integer32 (0..52)
	MAX-ACCESS read-only
	STATUS     current
	DESCRIPTION 
		"This is the maximal number of entries stored in rectifier daily energy log."
	::= { rectifiersEnergyLog 4 }

rectifiersEnergyLogLastDaysTable  OBJECT-TYPE
	SYNTAX SEQUENCE OF RectifiersEnergyLogLastDaysEntry
	MAX-ACCESS not-accessible
	STATUS     current
	DESCRIPTION 
		"This table contains daily energy log of rectifiers."
	::= { rectifiersEnergyLog 5 }

rectifiersEnergyLogLastDaysEntry  OBJECT-TYPE
	SYNTAX 	RectifiersEnergyLogLastDaysEntry
	MAX-ACCESS not-accessible
	STATUS     current
	DESCRIPTION 
		""
	INDEX { rectifiersEnergyLogLastDaysIndex }
	::= { rectifiersEnergyLogLastDaysTable 1 }

RectifiersEnergyLogLastDaysEntry ::= SEQUENCE {
	rectifiersEnergyLogLastDaysIndex
		Integer32,
	rectifiersEnergyLogLastDaysValue
		Integer32
}

rectifiersEnergyLogLastDaysIndex  OBJECT-TYPE
	SYNTAX     Integer32 (1..52)
	MAX-ACCESS not-accessible
	STATUS     current
	DESCRIPTION 
		"Index used for navigating the rows 1..52  of rectifiersEnergyLogLastDaysTable"
	::= { rectifiersEnergyLogLastDaysEntry 1 }

rectifiersEnergyLogLastDaysValue  OBJECT-TYPE
	SYNTAX     Integer32
	MAX-ACCESS read-only
	STATUS     current
	DESCRIPTION 
		"Energy value logged every day."
	::= { rectifiersEnergyLogLastDaysEntry 2 }

rectifiersEnergyLogLastWeeksNumberOfEntries  OBJECT-TYPE
	SYNTAX     Integer32 (0..52)
	MAX-ACCESS read-only
	STATUS     current
	DESCRIPTION 
		"This is the maximal number of entries stored in rectifier weekly energy log."
	::= { rectifiersEnergyLog 6 }

rectifiersEnergyLogLastWeeksTable  OBJECT-TYPE
	SYNTAX SEQUENCE OF RectifiersEnergyLogLastWeeksEntry
	MAX-ACCESS not-accessible
	STATUS     current
	DESCRIPTION 
		"This table contains weekly energy log of rectifiers."
	::= { rectifiersEnergyLog 7 }

rectifiersEnergyLogLastWeeksEntry  OBJECT-TYPE
	SYNTAX 	RectifiersEnergyLogLastWeeksEntry
	MAX-ACCESS not-accessible
	STATUS     current
	DESCRIPTION 
		""
	INDEX { rectifiersEnergyLogLastWeeksIndex }
	::= { rectifiersEnergyLogLastWeeksTable 1 }

RectifiersEnergyLogLastWeeksEntry ::= SEQUENCE {
	rectifiersEnergyLogLastWeeksIndex
		Integer32,
	rectifiersEnergyLogLastWeeksValue
		Integer32
}

rectifiersEnergyLogLastWeeksIndex  OBJECT-TYPE
	SYNTAX     Integer32 (1..52)
	MAX-ACCESS not-accessible
	STATUS     current
	DESCRIPTION 
		"Index used for navigating the rows 1..52  of rectifiersEnergyLogLastWeekTable"
	::= { rectifiersEnergyLogLastWeeksEntry 1 }

rectifiersEnergyLogLastWeeksValue  OBJECT-TYPE
	SYNTAX     Integer32
	MAX-ACCESS read-only
	STATUS     current
	DESCRIPTION 
		"Energy value logged every week."
	::= { rectifiersEnergyLogLastWeeksEntry 2 }

rectifiersNumberOfGroups  OBJECT-TYPE
	SYNTAX     Integer32
	MAX-ACCESS read-only
	STATUS     current
	DESCRIPTION 
		"Number of rectifier groups"
	::= { rectifiers 8 }

rectifierGroupsTable  OBJECT-TYPE
	SYNTAX SEQUENCE OF RectifierGroupsEntry
	MAX-ACCESS not-accessible
	STATUS     current
	DESCRIPTION 
		"This table contains status and the number of installed rectifiers of each rectifier groups."
	::= { rectifiers 9 }

rectifierGroupsEntry  OBJECT-TYPE
	SYNTAX 	RectifierGroupsEntry
	MAX-ACCESS not-accessible
	STATUS     current
	DESCRIPTION 
		""
	INDEX { rectifierGroupIndex }
	::= { rectifierGroupsTable 1 }

RectifierGroupsEntry ::= SEQUENCE {
	rectifierGroupIndex
		Integer32,
	rectifierGroupStatus
		INTEGER,
	rectifierGroupNumberOfRectifiers
		Integer32
}

rectifierGroupIndex  OBJECT-TYPE
	SYNTAX     Integer32 (1..10)
	MAX-ACCESS not-accessible
	STATUS     current
	DESCRIPTION 
		"Index used for navigating the rows 1..10  of rectifierGroupsTable"
	::= { rectifierGroupsEntry 1 }

rectifierGroupStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of each rectifier group."
	::= { rectifierGroupsEntry 2 }

rectifierGroupNumberOfRectifiers  OBJECT-TYPE
	SYNTAX     Integer32 (0..100)
	MAX-ACCESS read-write
	STATUS     current
	DESCRIPTION 
		"Number of installed rectifiers in each rectifier groups"
	::= { rectifierGroupsEntry 3 }

rectifierGroupCurrentTable  OBJECT-TYPE
	SYNTAX SEQUENCE OF RectifierGroupCurrentEntry
	MAX-ACCESS not-accessible
	STATUS     current
	DESCRIPTION 
		"This table contains information about the total rectifier current of each rectifier groups, which is calculated 
		 by summing up current from each rectifier in a rectifier group."
	::= { rectifiers 10 }

rectifierGroupCurrentEntry  OBJECT-TYPE
	SYNTAX 	RectifierGroupCurrentEntry
	MAX-ACCESS not-accessible
	STATUS     current
	DESCRIPTION 
		""
	INDEX { rectifierGroupIndex }
	::= { rectifierGroupCurrentTable 1 }

RectifierGroupCurrentEntry ::= SEQUENCE {
	rectifierGroupCurrentStatus
		INTEGER,
	rectifierGroupCurrentDescription
		DisplayString,
	rectifierGroupCurrentTrapRepeatCounter
		Integer32,
	rectifierGroupCurrentAlarmEnable
		INTEGER,
	rectifierGroupCurrentValue
		Integer32,
	rectifierGroupCurrentMajorAlarmLevel
		Integer32,
	rectifierGroupCurrentMinorAlarmLevel
		Integer32
}

rectifierGroupCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current of the rectifier group"
	::= { rectifierGroupCurrentEntry 1 }

rectifierGroupCurrentDescription  OBJECT-TYPE
	SYNTAX     DisplayString (SIZE(0..16))
	MAX-ACCESS read-write
	STATUS     current
	DESCRIPTION 
		"A textual description of the total rectifier current monitor of a rectifier group. This is stored in the system controller
		and can be changed by the user"
	::= { rectifierGroupCurrentEntry 2 }

rectifierGroupCurrentTrapRepeatCounter  OBJECT-TYPE
	SYNTAX     Integer32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectifierGroupCurrentEntry 3 }

rectifierGroupCurrentAlarmEnable  OBJECT-TYPE
	SYNTAX     INTEGER {
		disabled (0),
		enabled (1)
	}
	MAX-ACCESS read-write
	STATUS     current
	DESCRIPTION 
		"This value once enabled, the alarm condition of the monitor will be reported."
	::= { rectifierGroupCurrentEntry 4 }

rectifierGroupCurrentValue  OBJECT-TYPE
	SYNTAX     Integer32
	MAX-ACCESS read-only
	STATUS     current
	DESCRIPTION 
		"The value of the measured total rectifier current of each rectifier group."
	::= { rectifierGroupCurrentEntry 5 }

rectifierGroupCurrentMajorAlarmLevel  OBJECT-TYPE
	SYNTAX     Integer32
	MAX-ACCESS read-write
	STATUS     current
	DESCRIPTION 
		"The major alarm limit"
	::= { rectifierGroupCurrentEntry 6 }

rectifierGroupCurrentMinorAlarmLevel  OBJECT-TYPE
	SYNTAX     Integer32
	MAX-ACCESS read-write
	STATUS     current
	DESCRIPTION 
		"The minor alarm limit"
	::= { rectifierGroupCurrentEntry 7 }

rectifierGroupCapacityTable  OBJECT-TYPE
	SYNTAX SEQUENCE OF RectifierGroupCapacityEntry
	MAX-ACCESS not-accessible
	STATUS     current
	DESCRIPTION 
		" This table contains information about the used rectifier capacity of each rectifier group."
	::= { rectifiers 11 }

rectifierGroupCapacityEntry  OBJECT-TYPE
	SYNTAX 	RectifierGroupCapacityEntry
	MAX-ACCESS not-accessible
	STATUS     current
	DESCRIPTION 
		""
	INDEX { rectifierGroupIndex }
	::= { rectifierGroupCapacityTable 1 }

RectifierGroupCapacityEntry ::= SEQUENCE {
	rectifierGroupCapacityStatus
		INTEGER,
	rectifierGroupCapacityDescription
		DisplayString,
	rectifierGroupCapacityTrapRepeatCounter
		Integer32,
	rectifierGroupCapacityAlarmEnable
		INTEGER,
	rectifierGroupCapacityValue
		Integer32,
	rectifierGroupCapacityMajorAlarmLevel
		Integer32,
	rectifierGroupCapacityMinorAlarmLevel
		Integer32
}

rectifierGroupCapacityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured used rectifier capacity of each rectifier group"
	::= { rectifierGroupCapacityEntry 1 }

rectifierGroupCapacityDescription  OBJECT-TYPE
	SYNTAX     DisplayString (SIZE(0..16))
	MAX-ACCESS read-write
	STATUS     current
	DESCRIPTION 
		"A textual description of the used rectifier capacity monitor of each rectifier group. This is stored in the system controller
		and can be changed by the user"
	::= { rectifierGroupCapacityEntry 2 }

rectifierGroupCapacityTrapRepeatCounter  OBJECT-TYPE
	SYNTAX     Integer32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectifierGroupCapacityEntry 3 }

rectifierGroupCapacityAlarmEnable  OBJECT-TYPE
	SYNTAX     INTEGER {
		disabled (0),
		enabled (1)
	}
	MAX-ACCESS read-write
	STATUS     current
	DESCRIPTION 
		"This value once enabled, the alarm condition of the monitor will be reported."
	::= { rectifierGroupCapacityEntry 4 }

rectifierGroupCapacityValue  OBJECT-TYPE
	SYNTAX     Integer32
	MAX-ACCESS read-only
	STATUS     current
	DESCRIPTION 
		"The used rectifier capacity value presented in percentage of the total installed rectifier capacity of each rectifier group."
	::= { rectifierGroupCapacityEntry 5 }

rectifierGroupCapacityMajorAlarmLevel  OBJECT-TYPE
	SYNTAX     Integer32
	MAX-ACCESS read-write
	STATUS     current
	DESCRIPTION 
		"The major alarm limit"
	::= { rectifierGroupCapacityEntry 6 }

rectifierGroupCapacityMinorAlarmLevel  OBJECT-TYPE
	SYNTAX     Integer32
	MAX-ACCESS read-write
	STATUS     current
	DESCRIPTION 
		"The minor alarm limit"
	::= { rectifierGroupCapacityEntry 7 }

rectifierGroupErrorTable  OBJECT-TYPE
	SYNTAX SEQUENCE OF RectifierGroupErrorEntry
	MAX-ACCESS not-accessible
	STATUS     current
	DESCRIPTION 
		" This table contains information about the rectifier error monitor of each rectifier group."
	::= { rectifiers 12 }

rectifierGroupErrorEntry  OBJECT-TYPE
	SYNTAX 	RectifierGroupErrorEntry
	MAX-ACCESS not-accessible
	STATUS     current
	DESCRIPTION 
		""
	INDEX { rectifierGroupIndex }
	::= { rectifierGroupErrorTable 1 }

RectifierGroupErrorEntry ::= SEQUENCE {
	rectifierGroupErrorStatus
		INTEGER,
	rectifierGroupErrorDescription
		DisplayString,
	rectifierGroupErrorTrapRepeatCounter
		Integer32,
	rectifierGroupErrorAlarmEnable
		INTEGER,
	rectifierGroupErrorValue
		Integer32,
	rectifierGroupErrorMajorAlarmLevel
		Integer32,
	rectifierGroupErrorMinorAlarmLevel
		Integer32
}

rectifierGroupErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed units is higher than the defined alarm level."
	::= { rectifierGroupErrorEntry 1 }

rectifierGroupErrorDescription  OBJECT-TYPE
	SYNTAX     DisplayString (SIZE(0..16))
	MAX-ACCESS read-write
	STATUS     current
	DESCRIPTION 
		"A textual description of the rectifier error monitor of each rectifier group. This is stored in the system controller
		and can be changed by the user"
	::= { rectifierGroupErrorEntry 2 }

rectifierGroupErrorTrapRepeatCounter  OBJECT-TYPE
	SYNTAX     Integer32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectifierGroupErrorEntry 3 }

rectifierGroupErrorAlarmEnable  OBJECT-TYPE
	SYNTAX     INTEGER {
		disabled (0),
		enabled (1)
	}
	MAX-ACCESS read-write
	STATUS     current
	DESCRIPTION 
		"This value once enabled, the alarm condition of the monitor will be reported."
	::= { rectifierGroupErrorEntry 4 }

rectifierGroupErrorValue  OBJECT-TYPE
	SYNTAX     Integer32
	MAX-ACCESS read-only
	STATUS     current
	DESCRIPTION 
		"The number of failed rectifiers of each rectifier group."
	::= { rectifierGroupErrorEntry 5 }

rectifierGroupErrorMajorAlarmLevel  OBJECT-TYPE
	SYNTAX     Integer32
	MAX-ACCESS read-write
	STATUS     current
	DESCRIPTION 
		"The major alarm limit"
	::= { rectifierGroupErrorEntry 6 }

rectifierGroupErrorMinorAlarmLevel  OBJECT-TYPE
	SYNTAX     Integer32
	MAX-ACCESS read-write
	STATUS     current
	DESCRIPTION 
		"The minor alarm limit"
	::= { rectifierGroupErrorEntry 7 }

rectifierGroupRectifierTable  OBJECT-TYPE
	SYNTAX SEQUENCE OF RectifierGroupRectifierEntry
	MAX-ACCESS not-accessible
	STATUS     current
	DESCRIPTION 
		"This table shows the information of each rectifier installed in each of the rectifier group in the system."
	::= { rectifiers 13 }

rectifierGroupRectifierEntry  OBJECT-TYPE
	SYNTAX 	RectifierGroupRectifierEntry
	MAX-ACCESS not-accessible
	STATUS     current
	DESCRIPTION 
		""
	INDEX { rectifierGroupIndex, 
		rectifierGroupRectifierIndex }
	::= { rectifierGroupRectifierTable 1 }

RectifierGroupRectifierEntry ::= SEQUENCE {
	rectifierGroupRectifierIndex
		Integer32,
	rectifierGroupRectifierStatus
		INTEGER,
	rectifierGroupRectifierOutputCurrentValue
		Integer32,
	rectifierGroupRectifierInputVoltageValue
		Integer32,
	rectifierGroupRectifierType
		DisplayString,
	rectifierGroupRectifierHwPartNumber
		DisplayString,
	rectifierGroupRectifierHwVersion
		DisplayString,
	rectifierGroupRectifierSwPartNumber
		DisplayString,
	rectifierGroupRectifierSwVersion
		DisplayString
}

rectifierGroupRectifierIndex  OBJECT-TYPE
	SYNTAX     Integer32 (1..100)
	MAX-ACCESS not-accessible
	STATUS     current
	DESCRIPTION 
		"Index used for navigating the rows 1..100  of rectifierGroupRectifierTable"
	::= { rectifierGroupRectifierEntry 1 }

rectifierGroupRectifierStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of rectifier."
	::= { rectifierGroupRectifierEntry 2 }

rectifierGroupRectifierOutputCurrentValue  OBJECT-TYPE
	SYNTAX     Integer32
	MAX-ACCESS read-only
	STATUS     current
	DESCRIPTION 
		"The output current value of rectifier."
	::= { rectifierGroupRectifierEntry 3 }

rectifierGroupRectifierInputVoltageValue  OBJECT-TYPE
	SYNTAX     Integer32
	MAX-ACCESS read-only
	STATUS     current
	DESCRIPTION 
		"The input voltage value of rectifier."
	::= { rectifierGroupRectifierEntry 4 }

rectifierGroupRectifierType  OBJECT-TYPE
	SYNTAX     DisplayString (SIZE(0..27))
	MAX-ACCESS read-only
	STATUS     current
	DESCRIPTION 
		"Type of rectifier"
	::= { rectifierGroupRectifierEntry 5 }

rectifierGroupRectifierHwPartNumber  OBJECT-TYPE
	SYNTAX     DisplayString (SIZE(0..12))
	MAX-ACCESS read-only
	STATUS     current
	DESCRIPTION 
		"Hardware part number of rectifier"
	::= { rectifierGroupRectifierEntry 6 }

rectifierGroupRectifierHwVersion  OBJECT-TYPE
	SYNTAX     DisplayString (SIZE(0..6))
	MAX-ACCESS read-only
	STATUS     current
	DESCRIPTION 
		"Hardware version number of rectifier"
	::= { rectifierGroupRectifierEntry 7 }

rectifierGroupRectifierSwPartNumber  OBJECT-TYPE
	SYNTAX     DisplayString (SIZE(0..12))
	MAX-ACCESS read-only
	STATUS     current
	DESCRIPTION 
		"Part number of secondary software in rectifier"
	::= { rectifierGroupRectifierEntry 8 }

rectifierGroupRectifierSwVersion  OBJECT-TYPE
	SYNTAX     DisplayString (SIZE(0..6))
	MAX-ACCESS read-only
	STATUS     current
	DESCRIPTION 
		"Version number of secondary software in rectifier"
	::= { rectifierGroupRectifierEntry 9 }

rectifierGroupEnergyLogTable  OBJECT-TYPE
	SYNTAX SEQUENCE OF RectifierGroupEnergyLogEntry
	MAX-ACCESS not-accessible
	STATUS     current
	DESCRIPTION 
		" This branch contains information about rectifiers' energy logs of each rectifier group."
	::= { rectifiers 14 }

rectifierGroupEnergyLogEntry  OBJECT-TYPE
	SYNTAX 	RectifierGroupEnergyLogEntry
	MAX-ACCESS not-accessible
	STATUS     current
	DESCRIPTION 
		""
	INDEX { rectifierGroupIndex }
	::= { rectifierGroupEnergyLogTable 1 }

RectifierGroupEnergyLogEntry ::= SEQUENCE {
	rectifierGroupEnergyLogAccumulated
		Integer32,
	rectifierGroupEnergyLogLastHoursNumberOfEntries
		Integer32,
	rectifierGroupEnergyLogLastDaysNumberOfEntries
		Integer32,
	rectifierGroupEnergyLogLastWeeksNumberOfEntries
		Integer32
}

rectifierGroupEnergyLogAccumulated  OBJECT-TYPE
	SYNTAX     Integer32
	MAX-ACCESS read-only
	STATUS     current
	DESCRIPTION 
		"This is the accumulated energy delivered from rectifiers of each rectifier group."
	::= { rectifierGroupEnergyLogEntry 1 }

rectifierGroupEnergyLogLastHoursNumberOfEntries  OBJECT-TYPE
	SYNTAX     Integer32
	MAX-ACCESS read-only
	STATUS     current
	DESCRIPTION 
		"This is the maximal number of entries stored in rectifier group hourly energy log."
	::= { rectifierGroupEnergyLogEntry 2 }

rectifierGroupEnergyLogLastDaysNumberOfEntries  OBJECT-TYPE
	SYNTAX     Integer32
	MAX-ACCESS read-only
	STATUS     current
	DESCRIPTION 
		"This is the maximal number of entries stored in rectifier group daily energy log."
	::= { rectifierGroupEnergyLogEntry 3 }

rectifierGroupEnergyLogLastWeeksNumberOfEntries  OBJECT-TYPE
	SYNTAX     Integer32
	MAX-ACCESS read-only
	STATUS     current
	DESCRIPTION 
		"This is the maximal number of entries stored in rectifier group weekly energy log."
	::= { rectifierGroupEnergyLogEntry 4 }

rectifierGroupEnergyLogLastHoursTable  OBJECT-TYPE
	SYNTAX SEQUENCE OF RectifierGroupEnergyLogLastHoursEntry
	MAX-ACCESS not-accessible
	STATUS     current
	DESCRIPTION 
		"This table contains hourly energy log of each rectifier group"
	::= { rectifiers 15 }

rectifierGroupEnergyLogLastHoursEntry  OBJECT-TYPE
	SYNTAX 	RectifierGroupEnergyLogLastHoursEntry
	MAX-ACCESS not-accessible
	STATUS     current
	DESCRIPTION 
		""
	INDEX { rectifierGroupIndex, 
		rectifierGroupEnergyLogLastHoursIndex }
	::= { rectifierGroupEnergyLogLastHoursTable 1 }

RectifierGroupEnergyLogLastHoursEntry ::= SEQUENCE {
	rectifierGroupEnergyLogLastHoursIndex
		Integer32,
	rectifierGroupEnergyLogLastHoursValue
		Integer32
}

rectifierGroupEnergyLogLastHoursIndex  OBJECT-TYPE
	SYNTAX     Integer32 (1..52)
	MAX-ACCESS not-accessible
	STATUS     current
	DESCRIPTION 
		"Index used for navigating the rows 1..52  of rectifierGroupEnergyLogLastHoursTable"
	::= { rectifierGroupEnergyLogLastHoursEntry 1 }

rectifierGroupEnergyLogLastHoursValue  OBJECT-TYPE
	SYNTAX     Integer32
	MAX-ACCESS read-only
	STATUS     current
	DESCRIPTION 
		"Energy value logged every hour."
	::= { rectifierGroupEnergyLogLastHoursEntry 2 }

rectifierGroupEnergyLogLastDaysTable  OBJECT-TYPE
	SYNTAX SEQUENCE OF RectifierGroupEnergyLogLastDaysEntry
	MAX-ACCESS not-accessible
	STATUS     current
	DESCRIPTION 
		"This table contains daily energy log of each rectifier group"
	::= { rectifiers 16 }

rectifierGroupEnergyLogLastDaysEntry  OBJECT-TYPE
	SYNTAX 	RectifierGroupEnergyLogLastDaysEntry
	MAX-ACCESS not-accessible
	STATUS     current
	DESCRIPTION 
		""
	INDEX { rectifierGroupIndex, 
		rectifierGroupEnergyLogLastDaysIndex }
	::= { rectifierGroupEnergyLogLastDaysTable 1 }

RectifierGroupEnergyLogLastDaysEntry ::= SEQUENCE {
	rectifierGroupEnergyLogLastDaysIndex
		Integer32,
	rectifierGroupEnergyLogLastDaysValue
		Integer32
}

rectifierGroupEnergyLogLastDaysIndex  OBJECT-TYPE
	SYNTAX     Integer32 (1..52)
	MAX-ACCESS not-accessible
	STATUS     current
	DESCRIPTION 
		"Index used for navigating the rows 1..52  of rectifierGroupEnergyLogLasDaysTable"
	::= { rectifierGroupEnergyLogLastDaysEntry 1 }

rectifierGroupEnergyLogLastDaysValue  OBJECT-TYPE
	SYNTAX     Integer32
	MAX-ACCESS read-only
	STATUS     current
	DESCRIPTION 
		"Energy value logged every day."
	::= { rectifierGroupEnergyLogLastDaysEntry 2 }

rectifierGroupEnergyLogLastWeeksTable  OBJECT-TYPE
	SYNTAX SEQUENCE OF RectifierGroupEnergyLogLastWeeksEntry
	MAX-ACCESS not-accessible
	STATUS     current
	DESCRIPTION 
		"This table contains weekly energy log of each rectifier group"
	::= { rectifiers 17 }

rectifierGroupEnergyLogLastWeeksEntry  OBJECT-TYPE
	SYNTAX 	RectifierGroupEnergyLogLastWeeksEntry
	MAX-ACCESS not-accessible
	STATUS     current
	DESCRIPTION 
		""
	INDEX { rectifierGroupIndex, 
		rectifierGroupEnergyLogLastWeeksIndex }
	::= { rectifierGroupEnergyLogLastWeeksTable 1 }

RectifierGroupEnergyLogLastWeeksEntry ::= SEQUENCE {
	rectifierGroupEnergyLogLastWeeksIndex
		Integer32,
	rectifierGroupEnergyLogLastWeeksValue
		Integer32
}

rectifierGroupEnergyLogLastWeeksIndex  OBJECT-TYPE
	SYNTAX     Integer32 (1..52)
	MAX-ACCESS not-accessible
	STATUS     current
	DESCRIPTION 
		"Index used for navigating the rows 1..52  of rectifierGroupEnergyLogLastWeeksTable"
	::= { rectifierGroupEnergyLogLastWeeksEntry 1 }

rectifierGroupEnergyLogLastWeeksValue  OBJECT-TYPE
	SYNTAX     Integer32
	MAX-ACCESS read-only
	STATUS     current
	DESCRIPTION 
		"Energy value logged every week."
	::= { rectifierGroupEnergyLogLastWeeksEntry 2 }

rectifiersTemperatureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The state of the rectifier temperature can be either one of the defined enumerated values"
	::= { rectifiersTemperature 1 }

rectifiersTemperatureDescription  OBJECT-TYPE
	SYNTAX     DisplayString (SIZE(0..16))
	MAX-ACCESS read-write
	STATUS     current
	DESCRIPTION 
		"A textual description of the rectifier temperature monitor. This is stored in the system controller
		and can be changed by the user. "
	::= { rectifiersTemperature 2 }

rectifiersTemperatureTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectifiersTemperature 3 }

rectifiersTemperatureAlarmEnable  OBJECT-TYPE
	SYNTAX     INTEGER {
		disabled (0),
		enabled (1)
	}
	MAX-ACCESS read-write
	STATUS     current
	DESCRIPTION 
		"This value once enabled, the alarm condition of the monitor will be reported."
	::= { rectifiersTemperature 4 }

rectifiersTemperatureValue  OBJECT-TYPE
	SYNTAX     Integer32 (0..9999)
	MAX-ACCESS read-only
	STATUS     current
	DESCRIPTION 
		"The highest value of the rectifier temperature measurements.
		Depending on the global setting in the Control unit, this value will be presented in Celsius
		or Fahrenheit."
	::= { rectifiersTemperature 5 }

rectifiersTemperatureMajorHighLevel  OBJECT-TYPE
	SYNTAX     Integer32
	MAX-ACCESS read-write
	STATUS     current
	DESCRIPTION 
		"The major high alarm limit"
	::= { rectifiersTemperature 6 }

rectifiersTemperatureMinorHighLevel  OBJECT-TYPE
	SYNTAX     Integer32
	MAX-ACCESS read-write
	STATUS     current
	DESCRIPTION 
		"The minor high alarm limit"
	::= { rectifiersTemperature 7 }

rectifiersTemperatureMinorLowLevel  OBJECT-TYPE
	SYNTAX     Integer32
	MAX-ACCESS read-write
	STATUS     current
	DESCRIPTION 
		"The minor low alarm limit"
	::= { rectifiersTemperature 8 }

rectifiersTemperatureMajorLowLevel  OBJECT-TYPE
	SYNTAX     Integer32
	MAX-ACCESS read-write
	STATUS     current
	DESCRIPTION 
		"The major low alarm limit"
	::= { rectifiersTemperature 9 }

rectifierGroupTemperatureTable  OBJECT-TYPE
	SYNTAX SEQUENCE OF RectifierGroupTemperatureEntry
	MAX-ACCESS not-accessible
	STATUS     current
	DESCRIPTION 
		"This table contains information about the highest rectifier temperature of each rectifier groups, which is calculated 
		 by summing up current from each rectifier in a rectifier group."
	::= { rectifiers 19 }

rectifierGroupTemperatureEntry  OBJECT-TYPE
	SYNTAX 	RectifierGroupTemperatureEntry
	MAX-ACCESS not-accessible
	STATUS     current
	DESCRIPTION 
		""
	INDEX { rectifierGroupIndex }
	::= { rectifierGroupTemperatureTable 1 }

RectifierGroupTemperatureEntry ::= SEQUENCE {
	rectifierGroupTemperatureStatus
		INTEGER,
	rectifierGroupTemperatureDescription
		DisplayString,
	rectifierGroupTemperatureTrapRepeatCounter
		Integer32,
	rectifierGroupTemperatureAlarmEnable
		INTEGER,
	rectifierGroupTemperatureValue
		Integer32,
	rectifierGroupTemperatureMajorHighLevel
		Integer32,
	rectifierGroupTemperatureMinorHighLevel
		Integer32,
	rectifierGroupTemperatureMinorLowLevel
		Integer32,
	rectifierGroupTemperatureMajorLowLevel
		Integer32
}

rectifierGroupTemperatureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured highest rectifier temperature of the rectifier group"
	::= { rectifierGroupTemperatureEntry 1 }

rectifierGroupTemperatureDescription  OBJECT-TYPE
	SYNTAX     DisplayString (SIZE(0..16))
	MAX-ACCESS read-write
	STATUS     current
	DESCRIPTION 
		"A textual description of the highest rectifier temperature monitor of a rectifier group. This is stored in the system controller
		and can be changed by the user"
	::= { rectifierGroupTemperatureEntry 2 }

rectifierGroupTemperatureTrapRepeatCounter  OBJECT-TYPE
	SYNTAX     Integer32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectifierGroupTemperatureEntry 3 }

rectifierGroupTemperatureAlarmEnable  OBJECT-TYPE
	SYNTAX     INTEGER {
		disabled (0),
		enabled (1)
	}
	MAX-ACCESS read-write
	STATUS     current
	DESCRIPTION 
		"This value once enabled, the alarm condition of the monitor will be reported."
	::= { rectifierGroupTemperatureEntry 4 }

rectifierGroupTemperatureValue  OBJECT-TYPE
	SYNTAX     Integer32
	MAX-ACCESS read-only
	STATUS     current
	DESCRIPTION 
		"The value of the measured highest rectifier temperature of each rectifier group."
	::= { rectifierGroupTemperatureEntry 5 }

rectifierGroupTemperatureMajorHighLevel  OBJECT-TYPE
	SYNTAX     Integer32
	MAX-ACCESS read-write
	STATUS     current
	DESCRIPTION 
		"The major high alarm limit"
	::= { rectifierGroupTemperatureEntry 6 }

rectifierGroupTemperatureMinorHighLevel  OBJECT-TYPE
	SYNTAX     Integer32
	MAX-ACCESS read-write
	STATUS     current
	DESCRIPTION 
		"The minor high alarm limit"
	::= { rectifierGroupTemperatureEntry 7 }

rectifierGroupTemperatureMinorLowLevel  OBJECT-TYPE
	SYNTAX     Integer32
	MAX-ACCESS read-write
	STATUS     current
	DESCRIPTION 
		"The minor low alarm limit"
	::= { rectifierGroupTemperatureEntry 8 }

rectifierGroupTemperatureMajorLowLevel  OBJECT-TYPE
	SYNTAX     Integer32
	MAX-ACCESS read-write
	STATUS     current
	DESCRIPTION 
		"The major low alarm limit"
	::= { rectifierGroupTemperatureEntry 9 }

rectifiersCurrentLimitEnable  OBJECT-TYPE
	SYNTAX     INTEGER {
		disabled (0),
		enabled (1)
	}
	MAX-ACCESS read-write
	STATUS     current
	DESCRIPTION 
		"Enable/disable current limit"
	::= { rectifiers 20 }

rectifiersCurrentLimitValue  OBJECT-TYPE
	SYNTAX     Integer32
	MAX-ACCESS read-write
	STATUS     current
	DESCRIPTION 
		"Current limit value"
	::= { rectifiers 21 }

dcdcNumberOfGroups  OBJECT-TYPE
	SYNTAX     Integer32 (0..5)
	MAX-ACCESS read-only
	STATUS     current
	DESCRIPTION 
		"Number of dcdc groups"
	::= { dcdc 1 }

dcdcGroupsTable  OBJECT-TYPE
	SYNTAX SEQUENCE OF DcdcGroupsEntry
	MAX-ACCESS not-accessible
	STATUS     current
	DESCRIPTION 
		"This table contains information about dcdc groups."
	::= { dcdc 2 }

dcdcGroupsEntry  OBJECT-TYPE
	SYNTAX 	DcdcGroupsEntry
	MAX-ACCESS not-accessible
	STATUS     current
	DESCRIPTION 
		""
	INDEX { dcdcGroupIndex }
	::= { dcdcGroupsTable 1 }

DcdcGroupsEntry ::= SEQUENCE {
	dcdcGroupIndex
		Integer32,
	dcdcGroupStatus
		INTEGER,
	dcdcGroupNumberOfDcdcConverters
		Integer32,
	dcdcGroupOutputVoltage
		Integer32,
	dcdcNumberOfCurrents
		Integer32,
	dcdcNumberOfCapacities
		Integer32,
	dcdcNumberOfAlarms
		Integer32
}

dcdcGroupIndex  OBJECT-TYPE
	SYNTAX     Integer32 (1..10)
	MAX-ACCESS not-accessible
	STATUS     current
	DESCRIPTION 
		""
	::= { dcdcGroupsEntry 1 }

dcdcGroupStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of dcdc group."
	::= { dcdcGroupsEntry 2 }

dcdcGroupNumberOfDcdcConverters  OBJECT-TYPE
	SYNTAX     Integer32
	MAX-ACCESS read-write
	STATUS     current
	DESCRIPTION 
		"Number of installed dcdc converters."
	::= { dcdcGroupsEntry 3 }

dcdcGroupOutputVoltage  OBJECT-TYPE
	SYNTAX     Integer32
	MAX-ACCESS read-write
	STATUS     current
	DESCRIPTION 
		"Output voltage of dcdc converters"
	::= { dcdcGroupsEntry 4 }

dcdcNumberOfCurrents  OBJECT-TYPE
	SYNTAX     Integer32 (0..5)
	MAX-ACCESS read-only
	STATUS     current
	DESCRIPTION 
		"Number of dcdc currents"
	::= { dcdcGroupsEntry 5 }

dcdcNumberOfCapacities  OBJECT-TYPE
	SYNTAX     Integer32 (0..5)
	MAX-ACCESS read-only
	STATUS     current
	DESCRIPTION 
		"Number of dcdc capacities"
	::= { dcdcGroupsEntry 6 }

dcdcNumberOfAlarms  OBJECT-TYPE
	SYNTAX     Integer32 (0..5)
	MAX-ACCESS read-only
	STATUS     current
	DESCRIPTION 
		"Number of dcdc alarms"
	::= { dcdcGroupsEntry 7 }

dcdcCurrentTable  OBJECT-TYPE
	SYNTAX SEQUENCE OF DcdcCurrentEntry
	MAX-ACCESS not-accessible
	STATUS     current
	DESCRIPTION 
		"This table contains information about the total dcdc current."
	::= { dcdc 3 }

dcdcCurrentEntry  OBJECT-TYPE
	SYNTAX 	DcdcCurrentEntry
	MAX-ACCESS not-accessible
	STATUS     current
	DESCRIPTION 
		""
	INDEX { dcdcGroupIndex }
	::= { dcdcCurrentTable 1 }

DcdcCurrentEntry ::= SEQUENCE {
	dcdcCurrentStatus
		INTEGER,
	dcdcCurrentDescription
		DisplayString,
	dcdcCurrentTrapRepeatCounter
		Counter32,
	dcdcCurrentAlarmEnable
		INTEGER,
	dcdcCurrentValue
		Integer32,
	dcdcCurrentMajorAlarmLevel
		Integer32,
	dcdcCurrentMinorAlarmLevel
		Integer32
}

dcdcCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total dcdc current."
	::= { dcdcCurrentEntry 1 }

dcdcCurrentDescription  OBJECT-TYPE
	SYNTAX     DisplayString (SIZE(0..16))
	MAX-ACCESS read-write
	STATUS     current
	DESCRIPTION 
		"A textual description of the total dcdc current monitor. This is stored in the system controller
		and can be changed by the user"
	::= { dcdcCurrentEntry 2 }

dcdcCurrentTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { dcdcCurrentEntry 3 }

dcdcCurrentAlarmEnable  OBJECT-TYPE
	SYNTAX     INTEGER {
		disabled (0),
		enabled (1)
	}
	MAX-ACCESS read-write
	STATUS     current
	DESCRIPTION 
		"This value once enabled, the alarm condition of the monitor will be reported."
	::= { dcdcCurrentEntry 4 }

dcdcCurrentValue  OBJECT-TYPE
	SYNTAX     Integer32
	MAX-ACCESS read-only
	STATUS     current
	DESCRIPTION 
		"The value of the measured total dcdc current."
	::= { dcdcCurrentEntry 5 }

dcdcCurrentMajorAlarmLevel  OBJECT-TYPE
	SYNTAX     Integer32
	MAX-ACCESS read-write
	STATUS     current
	DESCRIPTION 
		"The major alarm limit"
	::= { dcdcCurrentEntry 6 }

dcdcCurrentMinorAlarmLevel  OBJECT-TYPE
	SYNTAX     Integer32
	MAX-ACCESS read-write
	STATUS     current
	DESCRIPTION 
		"The minor alarm limit"
	::= { dcdcCurrentEntry 7 }

dcdcCapacityTable  OBJECT-TYPE
	SYNTAX SEQUENCE OF DcdcCapacityEntry
	MAX-ACCESS not-accessible
	STATUS     current
	DESCRIPTION 
		"This table contains information about the used dcdc capacity."
	::= { dcdc 4 }

dcdcCapacityEntry  OBJECT-TYPE
	SYNTAX 	DcdcCapacityEntry
	MAX-ACCESS not-accessible
	STATUS     current
	DESCRIPTION 
		""
	INDEX { dcdcGroupIndex }
	::= { dcdcCapacityTable 1 }

DcdcCapacityEntry ::= SEQUENCE {
	dcdcCapacityStatus
		INTEGER,
	dcdcCapacityDescription
		DisplayString,
	dcdcCapacityTrapRepeatCounter
		Counter32,
	dcdcCapacityAlarmEnable
		INTEGER,
	dcdcCapacityValue
		Integer32,
	dcdcCapacityMajorAlarmLevel
		Integer32,
	dcdcCapacityMinorAlarmLevel
		Integer32
}

dcdcCapacityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured used dcdc capacity."
	::= { dcdcCapacityEntry 1 }

dcdcCapacityDescription  OBJECT-TYPE
	SYNTAX     DisplayString (SIZE(0..16))
	MAX-ACCESS read-write
	STATUS     current
	DESCRIPTION 
		"A textual description of the used dcdc capacity monitor. This is stored in the system controller
		and can be changed by the user"
	::= { dcdcCapacityEntry 2 }

dcdcCapacityTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes of"
	::= { dcdcCapacityEntry 3 }

dcdcCapacityAlarmEnable  OBJECT-TYPE
	SYNTAX     INTEGER {
		disabled (0),
		enabled (1)
	}
	MAX-ACCESS read-write
	STATUS     current
	DESCRIPTION 
		"This value once enabled, the alarm condition of the monitor will be reported."
	::= { dcdcCapacityEntry 4 }

dcdcCapacityValue  OBJECT-TYPE
	SYNTAX     Integer32
	MAX-ACCESS read-only
	STATUS     current
	DESCRIPTION 
		"The used dcdc capacity value presented in percentage of the total installed dcdc capacity."
	::= { dcdcCapacityEntry 5 }

dcdcCapacityMajorAlarmLevel  OBJECT-TYPE
	SYNTAX     Integer32
	MAX-ACCESS read-write
	STATUS     current
	DESCRIPTION 
		"The major alarm limit"
	::= { dcdcCapacityEntry 6 }

dcdcCapacityMinorAlarmLevel  OBJECT-TYPE
	SYNTAX     Integer32
	MAX-ACCESS read-write
	STATUS     current
	DESCRIPTION 
		"The minor alarm limit"
	::= { dcdcCapacityEntry 7 }

dcdcTable  OBJECT-TYPE
	SYNTAX SEQUENCE OF DcdcEntry
	MAX-ACCESS not-accessible
	STATUS     current
	DESCRIPTION 
		"This table shows the information of each dcdc converter installed in the system."
	::= { dcdc 5 }

dcdcEntry  OBJECT-TYPE
	SYNTAX 	DcdcEntry
	MAX-ACCESS not-accessible
	STATUS     current
	DESCRIPTION 
		""
	INDEX { dcdcGroupIndex, 
		dcdcIndex }
	::= { dcdcTable 1 }

DcdcEntry ::= SEQUENCE {
	dcdcIndex
		Integer32,
	dcdcStatus
		INTEGER,
	dcdcOutputCurrentValue
		Integer32,
	dcdcInputVoltageValue
		Integer32,
	dcdcType
		DisplayString,
	dcdcHwPartNumber
		DisplayString,
	dcdcHwVersion
		DisplayString,
	dcdcSwPartNumber
		DisplayString,
	dcdcSwVersion
		DisplayString
}

-- Index used for navigating the rows 1..100 of dcdcTable

dcdcIndex  OBJECT-TYPE
	SYNTAX     Integer32 (1..100)
	MAX-ACCESS not-accessible
	STATUS     current
	DESCRIPTION 
		"Index used for navigating the rows 1..100  of dcdcTable"
	::= { dcdcEntry 1 }

dcdcStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of dcdc converter"
	::= { dcdcEntry 2 }

dcdcOutputCurrentValue  OBJECT-TYPE
	SYNTAX     Integer32
	MAX-ACCESS read-only
	STATUS     current
	DESCRIPTION 
		"The output current value of dcdc."
	::= { dcdcEntry 3 }

dcdcInputVoltageValue  OBJECT-TYPE
	SYNTAX     Integer32
	MAX-ACCESS read-only
	STATUS     current
	DESCRIPTION 
		"The input voltage value of dcdc."
	::= { dcdcEntry 4 }

dcdcType  OBJECT-TYPE
	SYNTAX     DisplayString (SIZE(0..27))
	MAX-ACCESS read-only
	STATUS     current
	DESCRIPTION 
		"Type of dcdc converter"
	::= { dcdcEntry 5 }

dcdcHwPartNumber  OBJECT-TYPE
	SYNTAX     DisplayString (SIZE(0..12))
	MAX-ACCESS read-only
	STATUS     current
	DESCRIPTION 
		"Hardware part number of dcdc converter"
	::= { dcdcEntry 6 }

dcdcHwVersion  OBJECT-TYPE
	SYNTAX     DisplayString (SIZE(0..6))
	MAX-ACCESS read-only
	STATUS     current
	DESCRIPTION 
		"Hardware version number of dcdc converter"
	::= { dcdcEntry 7 }

dcdcSwPartNumber  OBJECT-TYPE
	SYNTAX     DisplayString (SIZE(0..12))
	MAX-ACCESS read-only
	STATUS     current
	DESCRIPTION 
		"Part number of secondary software in dcdc converter"
	::= { dcdcEntry 8 }

dcdcSwVersion  OBJECT-TYPE
	SYNTAX     DisplayString (SIZE(0..6))
	MAX-ACCESS read-only
	STATUS     current
	DESCRIPTION 
		"Version number of secondary software in dcdc converter"
	::= { dcdcEntry 9 }

dcdcErrorTable  OBJECT-TYPE
	SYNTAX SEQUENCE OF DcdcErrorEntry
	MAX-ACCESS not-accessible
	STATUS     current
	DESCRIPTION 
		"This table contains information about the dcdc error monitor."
	::= { dcdc 6 }

dcdcErrorEntry  OBJECT-TYPE
	SYNTAX 	DcdcErrorEntry
	MAX-ACCESS not-accessible
	STATUS     current
	DESCRIPTION 
		""
	INDEX { dcdcGroupIndex }
	::= { dcdcErrorTable 1 }

DcdcErrorEntry ::= SEQUENCE {
	dcdcErrorStatus
		INTEGER,
	dcdcErrorDescription
		DisplayString,
	dcdcErrorTrapRepeatCounter
		Counter32,
	dcdcErrorEnable
		INTEGER,
	dcdcErrorValue
		Integer32,
	dcdcErrorMajorAlarmLevel
		Integer32,
	dcdcErrorMinorAlarmLevel
		Integer32
}

dcdcErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed units is higher than the defined alarm level."
	::= { dcdcErrorEntry 1 }

dcdcErrorDescription  OBJECT-TYPE
	SYNTAX     DisplayString (SIZE(0..16))
	MAX-ACCESS read-write
	STATUS     current
	DESCRIPTION 
		"A textual description of the dcdc error monitor. This is stored in the system controller
		and can be changed by the user"
	::= { dcdcErrorEntry 2 }

dcdcErrorTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { dcdcErrorEntry 3 }

dcdcErrorEnable  OBJECT-TYPE
	SYNTAX     INTEGER {
		disabled (0),
		enabled (1)
	}
	MAX-ACCESS read-write
	STATUS     current
	DESCRIPTION 
		"This value once enabled, the alarm condition of the monitor will be reported."
	::= { dcdcErrorEntry 4 }

dcdcErrorValue  OBJECT-TYPE
	SYNTAX     Integer32
	MAX-ACCESS read-only
	STATUS     current
	DESCRIPTION 
		"The number of failed dcdc converters."
	::= { dcdcErrorEntry 5 }

dcdcErrorMajorAlarmLevel  OBJECT-TYPE
	SYNTAX     Integer32
	MAX-ACCESS read-write
	STATUS     current
	DESCRIPTION 
		"The major alarm limit"
	::= { dcdcErrorEntry 6 }

dcdcErrorMinorAlarmLevel  OBJECT-TYPE
	SYNTAX     Integer32
	MAX-ACCESS read-write
	STATUS     current
	DESCRIPTION 
		"The minor alarm limit"
	::= { dcdcErrorEntry 7 }

solarChargersStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of solar charger subsystem."
	::= { solarChargers 1 }

solarChargersCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total solar current."
	::= { solarChargersCurrent 1 }

solarChargersCurrentDescription  OBJECT-TYPE
	SYNTAX     DisplayString (SIZE(0..16))
	MAX-ACCESS read-write
	STATUS     current
	DESCRIPTION 
		"A textual description of the total solar current monitor. This is stored in the system controller
		and can be changed by the user"
	::= { solarChargersCurrent 2 }

solarChargersCurrentTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { solarChargersCurrent 3 }

solarChargersCurrentAlarmEnable  OBJECT-TYPE
	SYNTAX     INTEGER {
		disabled (0),
		enabled (1)
	}
	MAX-ACCESS read-write
	STATUS     current
	DESCRIPTION 
		"This value once enabled, the alarm condition of the monitor will be reported."
	::= { solarChargersCurrent 4 }

solarChargersCurrentValue  OBJECT-TYPE
	SYNTAX     Integer32
	MAX-ACCESS read-only
	STATUS     current
	DESCRIPTION 
		"The value of the measured total solar current."
	::= { solarChargersCurrent 5 }

solarChargersCurrentMajorAlarmLevel  OBJECT-TYPE
	SYNTAX     Integer32
	MAX-ACCESS read-write
	STATUS     current
	DESCRIPTION 
		"The major alarm limit"
	::= { solarChargersCurrent 6 }

solarChargersCurrentMinorAlarmLevel  OBJECT-TYPE
	SYNTAX     Integer32
	MAX-ACCESS read-write
	STATUS     current
	DESCRIPTION 
		"The minor alarm limit"
	::= { solarChargersCurrent 7 }

solarChargersErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed units is higher than the defined alarm level."
	::= { solarChargersError 1 }

solarChargersErrorDescription  OBJECT-TYPE
	SYNTAX     DisplayString (SIZE(0..16))
	MAX-ACCESS read-write
	STATUS     current
	DESCRIPTION 
		"A textual description of the solar error monitor. This is stored in the system controller
		and can be changed by the user"
	::= { solarChargersError 2 }

solarChargersErrorTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { solarChargersError 3 }

solarChargersErrorEnable  OBJECT-TYPE
	SYNTAX     INTEGER {
		disabled (0),
		enabled (1)
	}
	MAX-ACCESS read-write
	STATUS     current
	DESCRIPTION 
		"This value once enabled, the alarm condition of the monitor will be reported."
	::= { solarChargersError 4 }

solarChargersErrorValue  OBJECT-TYPE
	SYNTAX     Integer32
	MAX-ACCESS read-only
	STATUS     current
	DESCRIPTION 
		"The number of failed solar chargers."
	::= { solarChargersError 5 }

solarChargersErrorMajorAlarmLevel  OBJECT-TYPE
	SYNTAX     Integer32
	MAX-ACCESS read-write
	STATUS     current
	DESCRIPTION 
		"The major alarm limit"
	::= { solarChargersError 6 }

solarChargersErrorMinorAlarmLevel  OBJECT-TYPE
	SYNTAX     Integer32
	MAX-ACCESS read-write
	STATUS     current
	DESCRIPTION 
		"The minor alarm limit"
	::= { solarChargersError 7 }

solarChargersNumberOfSolarChargers  OBJECT-TYPE
	SYNTAX     Integer32 (0..100)
	MAX-ACCESS read-write
	STATUS     current
	DESCRIPTION 
		"Number of installed solar chargers."
	::= { solarChargers 5 }

solarChargerTable  OBJECT-TYPE
	SYNTAX SEQUENCE OF SolarChargerEntry
	MAX-ACCESS not-accessible
	STATUS     current
	DESCRIPTION 
		"This table shows the information of each solar charger installed in the system."
	::= { solarChargers 6 }

solarChargerEntry  OBJECT-TYPE
	SYNTAX 	SolarChargerEntry
	MAX-ACCESS not-accessible
	STATUS     current
	DESCRIPTION 
		""
	INDEX { solarChargerIndex }
	::= { solarChargerTable 1 }

SolarChargerEntry ::= SEQUENCE {
	solarChargerIndex
		Integer32,
	solarChargerStatus
		INTEGER,
	solarChargerOutputCurrentValue
		Integer32,
	solarChargerInputVoltageValue
		Integer32,
	solarChargerType
		DisplayString,
	solarChargerHwPartNumber
		DisplayString,
	solarChargerHwVersion
		DisplayString,
	solarChargerSwPartNumber
		DisplayString,
	solarChargerSwVersion
		DisplayString
}

solarChargerIndex  OBJECT-TYPE
	SYNTAX     Integer32 (1..100)
	MAX-ACCESS not-accessible
	STATUS     current
	DESCRIPTION 
		"Index used for navigating the rows 1..100 of solarChargerTable"
	::= { solarChargerEntry 1 }

solarChargerStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of solar charger."
	::= { solarChargerEntry 2 }

solarChargerOutputCurrentValue  OBJECT-TYPE
	SYNTAX     Integer32
	MAX-ACCESS read-only
	STATUS     current
	DESCRIPTION 
		"The output current value of solar charger."
	::= { solarChargerEntry 3 }

solarChargerInputVoltageValue  OBJECT-TYPE
	SYNTAX     Integer32
	MAX-ACCESS read-only
	STATUS     current
	DESCRIPTION 
		"The input voltage value of solar charger."
	::= { solarChargerEntry 4 }

solarChargerType  OBJECT-TYPE
	SYNTAX     DisplayString (SIZE(0..27))
	MAX-ACCESS read-only
	STATUS     current
	DESCRIPTION 
		"Type of solar charger"
	::= { solarChargerEntry 5 }

solarChargerHwPartNumber  OBJECT-TYPE
	SYNTAX     DisplayString (SIZE(0..12))
	MAX-ACCESS read-only
	STATUS     current
	DESCRIPTION 
		"Hardware part number of solar charger"
	::= { solarChargerEntry 6 }

solarChargerHwVersion  OBJECT-TYPE
	SYNTAX     DisplayString (SIZE(0..6))
	MAX-ACCESS read-only
	STATUS     current
	DESCRIPTION 
		"Hardware version number of solar charger"
	::= { solarChargerEntry 7 }

solarChargerSwPartNumber  OBJECT-TYPE
	SYNTAX     DisplayString (SIZE(0..12))
	MAX-ACCESS read-only
	STATUS     current
	DESCRIPTION 
		"Part number of secondary software in solar charger"
	::= { solarChargerEntry 8 }

solarChargerSwVersion  OBJECT-TYPE
	SYNTAX     DisplayString (SIZE(0..6))
	MAX-ACCESS read-only
	STATUS     current
	DESCRIPTION 
		"Version number of secondary software in solar charger"
	::= { solarChargerEntry 9 }

solarChargersEnergyLogAccumulated  OBJECT-TYPE
	SYNTAX     Integer32
	MAX-ACCESS read-only
	STATUS     current
	DESCRIPTION 
		"This is the accumulated energy delivered from solar chargers."
	::= { solarChargersEnergyLog 1 }

solarChargersEnergyLogLastHoursNumberOfEntries  OBJECT-TYPE
	SYNTAX     Integer32
	MAX-ACCESS read-only
	STATUS     current
	DESCRIPTION 
		"This is the maximal number of entries stored in solar charger hourly energy log."
	::= { solarChargersEnergyLog 2 }

solarChargersEnergyLogLastHoursTable  OBJECT-TYPE
	SYNTAX SEQUENCE OF SolarChargersEnergyLogLastHoursEntry
	MAX-ACCESS not-accessible
	STATUS     current
	DESCRIPTION 
		"This table contains hourly energy log of solar chargers."
	::= { solarChargersEnergyLog 3 }

solarChargersEnergyLogLastHoursEntry  OBJECT-TYPE
	SYNTAX 	SolarChargersEnergyLogLastHoursEntry
	MAX-ACCESS not-accessible
	STATUS     current
	DESCRIPTION 
		""
	INDEX { solarChargersEnergyLogLastHoursIndex }
	::= { solarChargersEnergyLogLastHoursTable 1 }

SolarChargersEnergyLogLastHoursEntry ::= SEQUENCE {
	solarChargersEnergyLogLastHoursIndex
		Integer32,
	solarChargersEnergyLogLastHoursValue
		Integer32
}

solarChargersEnergyLogLastHoursIndex  OBJECT-TYPE
	SYNTAX     Integer32 (1..52)
	MAX-ACCESS not-accessible
	STATUS     current
	DESCRIPTION 
		"Index used for navigating the rows 1..52 of solarChargersEnergyLogLastHoursTable"
	::= { solarChargersEnergyLogLastHoursEntry 1 }

solarChargersEnergyLogLastHoursValue  OBJECT-TYPE
	SYNTAX     Integer32
	MAX-ACCESS read-only
	STATUS     current
	DESCRIPTION 
		"Energy value logged every hour."
	::= { solarChargersEnergyLogLastHoursEntry 2 }

solarChargersEnergyLogLastDaysNumberOfEntries  OBJECT-TYPE
	SYNTAX     Integer32
	MAX-ACCESS read-only
	STATUS     current
	DESCRIPTION 
		"This is the maximal number of entries stored in solar charger daily energy log."
	::= { solarChargersEnergyLog 4 }

solarChargersEnergyLogLastDaysTable  OBJECT-TYPE
	SYNTAX SEQUENCE OF SolarChargersEnergyLogLastDaysEntry
	MAX-ACCESS not-accessible
	STATUS     current
	DESCRIPTION 
		"This table contains daily energy log of solar chargers."
	::= { solarChargersEnergyLog 5 }

solarChargersEnergyLogLastDaysEntry  OBJECT-TYPE
	SYNTAX 	SolarChargersEnergyLogLastDaysEntry
	MAX-ACCESS not-accessible
	STATUS     current
	DESCRIPTION 
		""
	INDEX { solarChargersEnergyLogLastDaysIndex }
	::= { solarChargersEnergyLogLastDaysTable 1 }

SolarChargersEnergyLogLastDaysEntry ::= SEQUENCE {
	solarChargersEnergyLogLastDaysIndex
		Integer32,
	solarChargersEnergyLogLastDaysValue
		Integer32
}

solarChargersEnergyLogLastDaysIndex  OBJECT-TYPE
	SYNTAX     Integer32 (1..52)
	MAX-ACCESS not-accessible
	STATUS     current
	DESCRIPTION 
		"Index used for navigating the rows 1..52 of solarChargersEnergyLogLastDaysTable"
	::= { solarChargersEnergyLogLastDaysEntry 1 }

solarChargersEnergyLogLastDaysValue  OBJECT-TYPE
	SYNTAX     Integer32
	MAX-ACCESS read-only
	STATUS     current
	DESCRIPTION 
		"Energy value logged every day."
	::= { solarChargersEnergyLogLastDaysEntry 2 }

solarChargersEnergyLogLastWeeksNumberOfEntries  OBJECT-TYPE
	SYNTAX     Integer32
	MAX-ACCESS read-only
	STATUS     current
	DESCRIPTION 
		"This is the maximal number of entries stored in solar charger weekly energy log."
	::= { solarChargersEnergyLog 6 }

solarChargersEnergyLogLastWeeksTable  OBJECT-TYPE
	SYNTAX SEQUENCE OF SolarChargersEnergyLogLastWeeksEntry
	MAX-ACCESS not-accessible
	STATUS     current
	DESCRIPTION 
		"This table contains weekly energy log of solar chargers."
	::= { solarChargersEnergyLog 7 }

solarChargersEnergyLogLastWeeksEntry  OBJECT-TYPE
	SYNTAX 	SolarChargersEnergyLogLastWeeksEntry
	MAX-ACCESS not-accessible
	STATUS     current
	DESCRIPTION 
		""
	INDEX { solarChargersEnergyLogLastWeeksIndex }
	::= { solarChargersEnergyLogLastWeeksTable 1 }

SolarChargersEnergyLogLastWeeksEntry ::= SEQUENCE {
	solarChargersEnergyLogLastWeeksIndex
		Integer32,
	solarChargersEnergyLogLastWeeksValue
		Integer32
}

solarChargersEnergyLogLastWeeksIndex  OBJECT-TYPE
	SYNTAX     Integer32 (1..52)
	MAX-ACCESS not-accessible
	STATUS     current
	DESCRIPTION 
		"Index used for navigating the rows 1..52 of solarChargersEnergyLogLastWeekTable"
	::= { solarChargersEnergyLogLastWeeksEntry 1 }

solarChargersEnergyLogLastWeeksValue  OBJECT-TYPE
	SYNTAX     Integer32
	MAX-ACCESS read-only
	STATUS     current
	DESCRIPTION 
		"Energy value logged every week."
	::= { solarChargersEnergyLogLastWeeksEntry 2 }

solarChargersEarthFaultStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of solar charger's Earth Fault monitor"
	::= { solarChargers 8 }

windChargersStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of wind charger subsystem."
	::= { windChargers 1 }

windChargersCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total wind current."
	::= { windChargersCurrent 1 }

windChargersCurrentDescription  OBJECT-TYPE
	SYNTAX     DisplayString (SIZE(0..16))
	MAX-ACCESS read-write
	STATUS     current
	DESCRIPTION 
		"A textual description of the total wind current monitor. This is stored in the system controller
		and can be changed by the user"
	::= { windChargersCurrent 2 }

windChargersCurrentTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { windChargersCurrent 3 }

windChargersCurrentAlarmEnable  OBJECT-TYPE
	SYNTAX     INTEGER {
		disabled (0),
		enabled (1)
	}
	MAX-ACCESS read-write
	STATUS     current
	DESCRIPTION 
		"This value once enabled, the alarm condition of the monitor will be reported."
	::= { windChargersCurrent 4 }

windChargersCurrentValue  OBJECT-TYPE
	SYNTAX     Integer32
	MAX-ACCESS read-only
	STATUS     current
	DESCRIPTION 
		"The value of the measured total wind current."
	::= { windChargersCurrent 5 }

windChargersCurrentMajorAlarmLevel  OBJECT-TYPE
	SYNTAX     Integer32
	MAX-ACCESS read-write
	STATUS     current
	DESCRIPTION 
		"The major alarm limit"
	::= { windChargersCurrent 6 }

windChargersCurrentMinorAlarmLevel  OBJECT-TYPE
	SYNTAX     Integer32
	MAX-ACCESS read-write
	STATUS     current
	DESCRIPTION 
		"The minor alarm limit"
	::= { windChargersCurrent 7 }

windChargersErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed units is higher than the defined alarm level."
	::= { windChargersError 1 }

windChargersErrorDescription  OBJECT-TYPE
	SYNTAX     DisplayString (SIZE(0..16))
	MAX-ACCESS read-write
	STATUS     current
	DESCRIPTION 
		"A textual description of the wind error monitor. This is stored in the system controller
		and can be changed by the user"
	::= { windChargersError 2 }

windChargersErrorTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { windChargersError 3 }

windChargersErrorEnable  OBJECT-TYPE
	SYNTAX     INTEGER {
		disabled (0),
		enabled (1)
	}
	MAX-ACCESS read-write
	STATUS     current
	DESCRIPTION 
		"This value once enabled, the alarm condition of the monitor will be reported."
	::= { windChargersError 4 }

windChargersErrorValue  OBJECT-TYPE
	SYNTAX     Integer32
	MAX-ACCESS read-only
	STATUS     current
	DESCRIPTION 
		"The number of failed wind chargers."
	::= { windChargersError 5 }

windChargersErrorMajorAlarmLevel  OBJECT-TYPE
	SYNTAX     Integer32
	MAX-ACCESS read-write
	STATUS     current
	DESCRIPTION 
		"The major alarm limit"
	::= { windChargersError 6 }

windChargersErrorMinorAlarmLevel  OBJECT-TYPE
	SYNTAX     Integer32
	MAX-ACCESS read-write
	STATUS     current
	DESCRIPTION 
		"The minor alarm limit"
	::= { windChargersError 7 }

windChargersNumberOfWindChargers  OBJECT-TYPE
	SYNTAX     Integer32 (0..254)
	MAX-ACCESS read-write
	STATUS     current
	DESCRIPTION 
		"Number of installed wind chargers."
	::= { windChargers 5 }

windChargerTable  OBJECT-TYPE
	SYNTAX SEQUENCE OF WindChargerEntry
	MAX-ACCESS not-accessible
	STATUS     current
	DESCRIPTION 
		"This table shows the information of each wind charger installed in the system."
	::= { windChargers 6 }

windChargerEntry  OBJECT-TYPE
	SYNTAX 	WindChargerEntry
	MAX-ACCESS not-accessible
	STATUS     current
	DESCRIPTION 
		""
	INDEX { windChargerIndex }
	::= { windChargerTable 1 }

WindChargerEntry ::= SEQUENCE {
	windChargerIndex
		Integer32,
	windChargerStatus
		INTEGER,
	windChargerOutputCurrentValue
		Integer32,
	windChargerInputVoltageValue
		Integer32,
	windChargerType
		DisplayString,
	windChargerHwPartNumber
		DisplayString,
	windChargerHwVersion
		DisplayString,
	windChargerSwPartNumber
		DisplayString,
	windChargerSwVersion
		DisplayString
}

windChargerIndex  OBJECT-TYPE
	SYNTAX     Integer32 (1..100)
	MAX-ACCESS not-accessible
	STATUS     current
	DESCRIPTION 
		"Index used for navigating the rows 1..100 of windChargerTable"
	::= { windChargerEntry 1 }

windChargerStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of wind charger."
	::= { windChargerEntry 2 }

windChargerOutputCurrentValue  OBJECT-TYPE
	SYNTAX     Integer32
	MAX-ACCESS read-only
	STATUS     current
	DESCRIPTION 
		"The output current value of wind charger."
	::= { windChargerEntry 3 }

windChargerInputVoltageValue  OBJECT-TYPE
	SYNTAX     Integer32
	MAX-ACCESS read-only
	STATUS     current
	DESCRIPTION 
		"The input voltage value of wind charger."
	::= { windChargerEntry 4 }

windChargerType  OBJECT-TYPE
	SYNTAX     DisplayString (SIZE(0..27))
	MAX-ACCESS read-only
	STATUS     current
	DESCRIPTION 
		"Type of wind charger"
	::= { windChargerEntry 5 }

windChargerHwPartNumber  OBJECT-TYPE
	SYNTAX     DisplayString (SIZE(0..12))
	MAX-ACCESS read-only
	STATUS     current
	DESCRIPTION 
		"Hardware part number of wind charger"
	::= { windChargerEntry 6 }

windChargerHwVersion  OBJECT-TYPE
	SYNTAX     DisplayString (SIZE(0..6))
	MAX-ACCESS read-only
	STATUS     current
	DESCRIPTION 
		"Hardware version number of wind charger"
	::= { windChargerEntry 7 }

windChargerSwPartNumber  OBJECT-TYPE
	SYNTAX     DisplayString (SIZE(0..12))
	MAX-ACCESS read-only
	STATUS     current
	DESCRIPTION 
		"Part number of secondary software in wind charger"
	::= { windChargerEntry 8 }

windChargerSwVersion  OBJECT-TYPE
	SYNTAX     DisplayString (SIZE(0..6))
	MAX-ACCESS read-only
	STATUS     current
	DESCRIPTION 
		"Version number of secondary software in wind charger"
	::= { windChargerEntry 9 }

windChargersEnergyLogAccumulated  OBJECT-TYPE
	SYNTAX     Integer32
	MAX-ACCESS read-only
	STATUS     current
	DESCRIPTION 
		"This is the accumulated energy delivered to/from wind chargers."
	::= { windChargersEnergyLog 1 }

windChargersEnergyLogLastHoursNumberOfEntries  OBJECT-TYPE
	SYNTAX     Integer32 (0..52)
	MAX-ACCESS read-only
	STATUS     current
	DESCRIPTION 
		"This is the maximal number of entries stored in wind charger hourly energy log."
	::= { windChargersEnergyLog 2 }

windChargersEnergyLogLastHoursTable  OBJECT-TYPE
	SYNTAX SEQUENCE OF WindChargersEnergyLogLastHoursEntry
	MAX-ACCESS not-accessible
	STATUS     current
	DESCRIPTION 
		"This table contains hourly energy log of wind chargers."
	::= { windChargersEnergyLog 3 }

windChargersEnergyLogLastHoursEntry  OBJECT-TYPE
	SYNTAX 	WindChargersEnergyLogLastHoursEntry
	MAX-ACCESS not-accessible
	STATUS     current
	DESCRIPTION 
		""
	INDEX { windChargersEnergyLogLastHoursIndex }
	::= { windChargersEnergyLogLastHoursTable 1 }

WindChargersEnergyLogLastHoursEntry ::= SEQUENCE {
	windChargersEnergyLogLastHoursIndex
		Integer32,
	windChargersEnergyLogLastHoursValue
		Integer32
}

windChargersEnergyLogLastHoursIndex  OBJECT-TYPE
	SYNTAX     Integer32 (1..52)
	MAX-ACCESS not-accessible
	STATUS     current
	DESCRIPTION 
		"Index used for navigating the rows 1..52 of windChargersEnergyLogLastHoursTable"
	::= { windChargersEnergyLogLastHoursEntry 1 }

windChargersEnergyLogLastHoursValue  OBJECT-TYPE
	SYNTAX     Integer32
	MAX-ACCESS read-only
	STATUS     current
	DESCRIPTION 
		"Energy value logged every hour."
	::= { windChargersEnergyLogLastHoursEntry 2 }

windChargersEnergyLogLastDaysNumberOfEntries  OBJECT-TYPE
	SYNTAX     Integer32 (0..52)
	MAX-ACCESS read-only
	STATUS     current
	DESCRIPTION 
		"This is the maximal number of entries stored in wind charger daily energy log."
	::= { windChargersEnergyLog 4 }

windChargersEnergyLogLastDaysTable  OBJECT-TYPE
	SYNTAX SEQUENCE OF WindChargersEnergyLogLastDaysEntry
	MAX-ACCESS not-accessible
	STATUS     current
	DESCRIPTION 
		"This table contains daily energy log of wind chargers."
	::= { windChargersEnergyLog 5 }

windChargersEnergyLogLastDaysEntry  OBJECT-TYPE
	SYNTAX 	WindChargersEnergyLogLastDaysEntry
	MAX-ACCESS not-accessible
	STATUS     current
	DESCRIPTION 
		""
	INDEX { windChargersEnergyLogLastDaysIndex }
	::= { windChargersEnergyLogLastDaysTable 1 }

WindChargersEnergyLogLastDaysEntry ::= SEQUENCE {
	windChargersEnergyLogLastDaysIndex
		Integer32,
	windChargersEnergyLogLastDaysValue
		Integer32
}

windChargersEnergyLogLastDaysIndex  OBJECT-TYPE
	SYNTAX     Integer32 (1..52)
	MAX-ACCESS not-accessible
	STATUS     current
	DESCRIPTION 
		"Index used for navigating the rows 1..52 of windChargersEnergyLogLastDaysTable"
	::= { windChargersEnergyLogLastDaysEntry 1 }

windChargersEnergyLogLastDaysValue  OBJECT-TYPE
	SYNTAX     Integer32
	MAX-ACCESS read-only
	STATUS     current
	DESCRIPTION 
		"Energy value logged every day."
	::= { windChargersEnergyLogLastDaysEntry 2 }

windChargersEnergyLogLastWeeksNumberOfEntries  OBJECT-TYPE
	SYNTAX     Integer32 (0..52)
	MAX-ACCESS read-only
	STATUS     current
	DESCRIPTION 
		"This is the maximal number of entries stored in wind charger weekly energy log."
	::= { windChargersEnergyLog 6 }

windChargersEnergyLogLastWeeksTable  OBJECT-TYPE
	SYNTAX SEQUENCE OF WindChargersEnergyLogLastWeeksEntry
	MAX-ACCESS not-accessible
	STATUS     current
	DESCRIPTION 
		"This table contains weekly energy log of wind chargers."
	::= { windChargersEnergyLog 7 }

windChargersEnergyLogLastWeeksEntry  OBJECT-TYPE
	SYNTAX 	WindChargersEnergyLogLastWeeksEntry
	MAX-ACCESS not-accessible
	STATUS     current
	DESCRIPTION 
		""
	INDEX { windChargersEnergyLogLastWeeksIndex }
	::= { windChargersEnergyLogLastWeeksTable 1 }

WindChargersEnergyLogLastWeeksEntry ::= SEQUENCE {
	windChargersEnergyLogLastWeeksIndex
		Integer32,
	windChargersEnergyLogLastWeeksValue
		Integer32
}

windChargersEnergyLogLastWeeksIndex  OBJECT-TYPE
	SYNTAX     Integer32 (1..52)
	MAX-ACCESS not-accessible
	STATUS     current
	DESCRIPTION 
		"Index used for navigating the rows 1..52 of windChargersEnergyLogLastWeekTable"
	::= { windChargersEnergyLogLastWeeksEntry 1 }

windChargersEnergyLogLastWeeksValue  OBJECT-TYPE
	SYNTAX     Integer32
	MAX-ACCESS read-only
	STATUS     current
	DESCRIPTION 
		"Energy value logged every week."
	::= { windChargersEnergyLogLastWeeksEntry 2 }

loadStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of load subsystem."
	::= { load 1 }

loadCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured load current."
	::= { loadCurrent 1 }

loadCurrentDescription  OBJECT-TYPE
	SYNTAX     DisplayString (SIZE(0..16))
	MAX-ACCESS read-write
	STATUS     current
	DESCRIPTION 
		"A textual description of the load current monitor. This is stored in the system controller
		and can be changed by the user. "
	::= { loadCurrent 2 }

loadCurrentTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { loadCurrent 3 }

loadCurrentAlarmEnable  OBJECT-TYPE
	SYNTAX     INTEGER {
		disabled (0),
		enabled (1)
	}
	MAX-ACCESS read-write
	STATUS     current
	DESCRIPTION 
		"This value once enabled, the alarm condition of the monitor will be reported."
	::= { loadCurrent 4 }

loadCurrentValue  OBJECT-TYPE
	SYNTAX     Integer32
	MAX-ACCESS read-only
	STATUS     current
	DESCRIPTION 
		"The value of the measured load current."
	::= { loadCurrent 5 }

loadCurrentMajorHighLevel  OBJECT-TYPE
	SYNTAX     Integer32
	MAX-ACCESS read-write
	STATUS     current
	DESCRIPTION 
		"The major high alarm limit"
	::= { loadCurrent 6 }

loadCurrentMinorHighLevel  OBJECT-TYPE
	SYNTAX     Integer32
	MAX-ACCESS read-write
	STATUS     current
	DESCRIPTION 
		"The minor high alarm limit"
	::= { loadCurrent 7 }

loadFusesStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of the load fuses."
	::= { load 3 }

loadNumberOfGroups  OBJECT-TYPE
	SYNTAX     Integer32 (1..8)
	MAX-ACCESS read-write
	STATUS     current
	DESCRIPTION 
		"Number of load groups"
	::= { load 4 }

loadGroupTable  OBJECT-TYPE
	SYNTAX SEQUENCE OF LoadGroupEntry
	MAX-ACCESS not-accessible
	STATUS     current
	DESCRIPTION 
		"This table contains information about load groups."
	::= { load 5 }

loadGroupEntry  OBJECT-TYPE
	SYNTAX 	LoadGroupEntry
	MAX-ACCESS not-accessible
	STATUS     current
	DESCRIPTION 
		""
	INDEX { loadGroupIndex }
	::= { loadGroupTable 1 }

LoadGroupEntry ::= SEQUENCE {
	loadGroupIndex
		Integer32,
	loadGroupStatus
		INTEGER,
	loadNumberOfLVLDs
		Integer32,
	loadNumberOfVoltages
		Integer32
}

loadGroupIndex  OBJECT-TYPE
	SYNTAX     Integer32 (1..8)
	MAX-ACCESS not-accessible
	STATUS     current
	DESCRIPTION 
		"Index used for navigating the rows 1..8  of loadGroupTable"
	::= { loadGroupEntry 1 }

loadGroupStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of load group"
	::= { loadGroupEntry 2 }

loadNumberOfLVLDs  OBJECT-TYPE
	SYNTAX     Integer32 (0..4)
	MAX-ACCESS read-only
	STATUS     current
	DESCRIPTION 
		"Number of LVLDs installed in load group"
	::= { loadGroupEntry 3 }

loadNumberOfVoltages  OBJECT-TYPE
	SYNTAX     Integer32 (0..4)
	MAX-ACCESS read-only
	STATUS     current
	DESCRIPTION 
		"Number of voltages in load group"
	::= { loadGroupEntry 4 }

loadLVLDTable  OBJECT-TYPE
	SYNTAX SEQUENCE OF LoadLVLDEntry
	MAX-ACCESS not-accessible
	STATUS     current
	DESCRIPTION 
		"This table contains information about LVLDs"
	::= { load 6 }

loadLVLDEntry  OBJECT-TYPE
	SYNTAX 	LoadLVLDEntry
	MAX-ACCESS not-accessible
	STATUS     current
	DESCRIPTION 
		""
	INDEX { loadGroupIndex, 
		loadLVLDIndex }
	::= { loadLVLDTable 1 }

LoadLVLDEntry ::= SEQUENCE {
	loadLVLDIndex
		Integer32,
	loadLVLDStatus
		INTEGER,
	loadLVLDDescription
		DisplayString,
	loadLVLDTrapRepeatCounter
		Counter32,
	loadLVLDEnable
		INTEGER,
	loadLVLDValue
		Integer32,
	loadLVLDConnectVoltage
		Integer32,
	loadLVLDDisconnectVoltage
		Integer32,
	loadLVLDDisconnectDelayEnable
		INTEGER,
	loadLVLDDisconnectDelayTime
		Integer32
}

loadLVLDIndex  OBJECT-TYPE
	SYNTAX     Integer32 (1..8)
	MAX-ACCESS not-accessible
	STATUS     current
	DESCRIPTION 
		"Index used for navigating the rows 1..8  of loadLVLDTable"
	::= { loadLVLDEntry 1 }

loadLVLDStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of LVLD"
	::= { loadLVLDEntry 2 }

loadLVLDDescription  OBJECT-TYPE
	SYNTAX     DisplayString (SIZE(0..16))
	MAX-ACCESS read-write
	STATUS     current
	DESCRIPTION 
		"A textual description of the LVLD. This is stored in the system controller
		and can be changed by the user.  "
	::= { loadLVLDEntry 3 }

loadLVLDTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { loadLVLDEntry 4 }

loadLVLDEnable  OBJECT-TYPE
	SYNTAX     INTEGER {
		disabled (0),
		enabled (1)
	}
	MAX-ACCESS read-write
	STATUS     current
	DESCRIPTION 
		"This value once enabled, the alarm condition of the LVLD will be reported."
	::= { loadLVLDEntry 5 }

loadLVLDValue  OBJECT-TYPE
	SYNTAX     Integer32
	MAX-ACCESS read-only
	STATUS     current
	DESCRIPTION 
		"The measured value of the LVLD."
	::= { loadLVLDEntry 6 }

loadLVLDConnectVoltage  OBJECT-TYPE
	SYNTAX     Integer32
	MAX-ACCESS read-write
	STATUS     current
	DESCRIPTION 
		"The load Contactor's Reconnect Voltage"
	::= { loadLVLDEntry 7 }

loadLVLDDisconnectVoltage  OBJECT-TYPE
	SYNTAX     Integer32
	MAX-ACCESS read-write
	STATUS     current
	DESCRIPTION 
		"The load Contactor's Disconnect Voltage"
	::= { loadLVLDEntry 8 }

loadLVLDDisconnectDelayEnable  OBJECT-TYPE
	SYNTAX     INTEGER {
		disabled (0),
		enabled (1)
	}
	MAX-ACCESS read-write
	STATUS     current
	DESCRIPTION 
		"Enable/disable LVLD disconnect delay."
	::= { loadLVLDEntry 9 }

loadLVLDDisconnectDelayTime  OBJECT-TYPE
	SYNTAX     Integer32
	MAX-ACCESS read-write
	STATUS     current
	DESCRIPTION 
		"LVLD disconnect delay time in minutes."
	::= { loadLVLDEntry 10 }

loadFuseTable  OBJECT-TYPE
	SYNTAX SEQUENCE OF LoadFuseEntry
	MAX-ACCESS not-accessible
	STATUS     current
	DESCRIPTION 
		"This table contains information about load fuse "
	::= { load 7 }

loadFuseEntry  OBJECT-TYPE
	SYNTAX 	LoadFuseEntry
	MAX-ACCESS not-accessible
	STATUS     current
	DESCRIPTION 
		""
	INDEX { loadGroupIndex }
	::= { loadFuseTable 1 }

LoadFuseEntry ::= SEQUENCE {
	loadFuseStatus
		INTEGER,
	loadFuseDescription
		DisplayString,
	loadFuseTrapRepeatCounter
		Counter32,
	loadFuseAlarmEnable
		INTEGER,
	loadFuseValue
		Integer32
}

loadFuseStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11)
	}
	MAX-ACCESS read-only
	STATUS     current
	DESCRIPTION 
		"The status of load fuse"
	::= { loadFuseEntry 1 }

loadFuseDescription  OBJECT-TYPE
	SYNTAX     DisplayString (SIZE(0..16))
	MAX-ACCESS read-write
	STATUS     current
	DESCRIPTION 
		"A textual description of the load fuse monitor. This is stored in the system controller
		and can be changed by the user. "
	::= { loadFuseEntry 2 }

loadFuseTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { loadFuseEntry 3 }

loadFuseAlarmEnable  OBJECT-TYPE
	SYNTAX     INTEGER {
		disabled (0),
		enabled (1)
	}
	MAX-ACCESS read-write
	STATUS     current
	DESCRIPTION 
		"This value once enabled, the alarm condition of the monitor will be reported."
	::= { loadFuseEntry 4 }

loadFuseValue  OBJECT-TYPE
	SYNTAX     Integer32
	MAX-ACCESS read-write
	STATUS     current
	DESCRIPTION 
		"The measured value of the load fuse."
	::= { loadFuseEntry 5 }

loadEnergyLogAccumulated  OBJECT-TYPE
	SYNTAX     Integer32
	MAX-ACCESS read-only
	STATUS     current
	DESCRIPTION 
		"This is the accumulated energy delivered to load."
	::= { loadEnergyLog 1 }

loadEnergyLogLastHoursNumberOfEntries  OBJECT-TYPE
	SYNTAX     Integer32 (0..52)
	MAX-ACCESS read-only
	STATUS     current
	DESCRIPTION 
		"This is the maximal number of entries stored in load hourly energy log."
	::= { loadEnergyLog 2 }

loadEnergyLogLastHoursTable  OBJECT-TYPE
	SYNTAX SEQUENCE OF LoadEnergyLogLastHoursEntry
	MAX-ACCESS not-accessible
	STATUS     current
	DESCRIPTION 
		""
	::= { loadEnergyLog 3 }

loadEnergyLogLastHoursEntry  OBJECT-TYPE
	SYNTAX 	LoadEnergyLogLastHoursEntry
	MAX-ACCESS not-accessible
	STATUS     current
	DESCRIPTION 
		""
	INDEX { loadEnergyLogLastHoursIndex }
	::= { loadEnergyLogLastHoursTable 1 }

LoadEnergyLogLastHoursEntry ::= SEQUENCE {
	loadEnergyLogLastHoursIndex
		Integer32,
	loadEnergyLogLastHoursValue
		Integer32
}

loadEnergyLogLastHoursIndex  OBJECT-TYPE
	SYNTAX     Integer32 (1..52)
	MAX-ACCESS not-accessible
	STATUS     current
	DESCRIPTION 
		"Index used for navigating the rows 1..52  of loadEnergyLogLastHoursTable"
	::= { loadEnergyLogLastHoursEntry 1 }

loadEnergyLogLastHoursValue  OBJECT-TYPE
	SYNTAX     Integer32
	MAX-ACCESS read-only
	STATUS     current
	DESCRIPTION 
		"Energy value logged every hour."
	::= { loadEnergyLogLastHoursEntry 2 }

loadEnergyLogLastDaysNumberOfEntries  OBJECT-TYPE
	SYNTAX     Integer32 (0..52)
	MAX-ACCESS read-only
	STATUS     current
	DESCRIPTION 
		"This is the maximal number of entries stored in load daily energy log."
	::= { loadEnergyLog 4 }

loadEnergyLogLastDaysTable  OBJECT-TYPE
	SYNTAX SEQUENCE OF LoadEnergyLogLastDaysEntry
	MAX-ACCESS not-accessible
	STATUS     current
	DESCRIPTION 
		""
	::= { loadEnergyLog 5 }

loadEnergyLogLastDaysEntry  OBJECT-TYPE
	SYNTAX 	LoadEnergyLogLastDaysEntry
	MAX-ACCESS not-accessible
	STATUS     current
	DESCRIPTION 
		""
	INDEX { loadEnergyLogLastDaysIndex }
	::= { loadEnergyLogLastDaysTable 1 }

LoadEnergyLogLastDaysEntry ::= SEQUENCE {
	loadEnergyLogLastDaysIndex
		Integer32,
	loadEnergyLogLastDaysValue
		Integer32
}

loadEnergyLogLastDaysIndex  OBJECT-TYPE
	SYNTAX     Integer32 (1..52)
	MAX-ACCESS not-accessible
	STATUS     current
	DESCRIPTION 
		"Index used for navigating the rows 1..52  of loadEnergyLogLastDaysTable"
	::= { loadEnergyLogLastDaysEntry 1 }

loadEnergyLogLastDaysValue  OBJECT-TYPE
	SYNTAX     Integer32
	MAX-ACCESS read-only
	STATUS     current
	DESCRIPTION 
		"Energy value logged every day."
	::= { loadEnergyLogLastDaysEntry 2 }

loadEnergyLogLastWeeksNumberOfEntries  OBJECT-TYPE
	SYNTAX     Integer32 (0..52)
	MAX-ACCESS read-only
	STATUS     current
	DESCRIPTION 
		"This is the maximal number of entries stored in load weekly energy log."
	::= { loadEnergyLog 6 }

loadEnergyLogLastWeeksTable  OBJECT-TYPE
	SYNTAX SEQUENCE OF LoadEnergyLogLastWeeksEntry
	MAX-ACCESS not-accessible
	STATUS     current
	DESCRIPTION 
		""
	::= { loadEnergyLog 7 }

loadEnergyLogLastWeeksEntry  OBJECT-TYPE
	SYNTAX 	LoadEnergyLogLastWeeksEntry
	MAX-ACCESS not-accessible
	STATUS     current
	DESCRIPTION 
		""
	INDEX { loadEnergyLogLastWeeksIndex }
	::= { loadEnergyLogLastWeeksTable 1 }

LoadEnergyLogLastWeeksEntry ::= SEQUENCE {
	loadEnergyLogLastWeeksIndex
		Integer32,
	loadEnergyLogLastWeeksValue
		Integer32
}

loadEnergyLogLastWeeksIndex  OBJECT-TYPE
	SYNTAX     Integer32 (1..52)
	MAX-ACCESS not-accessible
	STATUS     current
	DESCRIPTION 
		"Index used for navigating the rows 1..52  of loadEnergyLogLastWeekTable"
	::= { loadEnergyLogLastWeeksEntry 1 }

loadEnergyLogLastWeeksValue  OBJECT-TYPE
	SYNTAX     Integer32
	MAX-ACCESS read-only
	STATUS     current
	DESCRIPTION 
		"Energy value logged every week."
	::= { loadEnergyLogLastWeeksEntry 2 }

loadVoltageTable  OBJECT-TYPE
	SYNTAX SEQUENCE OF LoadVoltageEntry
	MAX-ACCESS not-accessible
	STATUS     current
	DESCRIPTION 
		"This table contains information about voltages"
	::= { load 9 }

loadVoltageEntry  OBJECT-TYPE
	SYNTAX 	LoadVoltageEntry
	MAX-ACCESS not-accessible
	STATUS     current
	DESCRIPTION 
		""
	INDEX { loadGroupIndex, 
		loadVoltageIndex }
	::= { loadVoltageTable 1 }

LoadVoltageEntry ::= SEQUENCE {
	loadVoltageIndex
		Integer32,
	loadVoltageStatus
		INTEGER,
	loadVoltageDescription
		DisplayString,
	loadVoltageTrapRepeatCounter
		Counter32,
	loadVoltageEnable
		INTEGER,
	loadVoltageValue
		Integer32
}

loadVoltageIndex  OBJECT-TYPE
	SYNTAX     Integer32 (1..3)
	MAX-ACCESS not-accessible
	STATUS     current
	DESCRIPTION 
		"Index used for navigating the rows 1..3  of loadVoltageTable"
	::= { loadVoltageEntry 1 }

loadVoltageStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of voltage"
	::= { loadVoltageEntry 2 }

loadVoltageDescription  OBJECT-TYPE
	SYNTAX     DisplayString (SIZE(0..16))
	MAX-ACCESS read-write
	STATUS     current
	DESCRIPTION 
		"A textual description of the voltage. This is stored in the system controller
		and can be changed by the user.  "
	::= { loadVoltageEntry 3 }

loadVoltageTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { loadVoltageEntry 4 }

loadVoltageEnable  OBJECT-TYPE
	SYNTAX     INTEGER {
		disabled (0),
		enabled (1)
	}
	MAX-ACCESS read-write
	STATUS     current
	DESCRIPTION 
		"This value once enabled, the alarm condition of the LVLD will be reported."
	::= { loadVoltageEntry 5 }

loadVoltageValue  OBJECT-TYPE
	SYNTAX     Integer32
	MAX-ACCESS read-only
	STATUS     current
	DESCRIPTION 
		"The measured value of the voltage."
	::= { loadVoltageEntry 6 }

-- The reported status of the battery subsystem. The status reflects the condition 
-- of all underlying alarm monitors in the battery subsystem

batteryStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"A toplevel status for the battery subsystem.  The state of this reflects the status of all 
		underlying statuses for the battery. Any change in one of the 'data monitors' in 
		the battery subsystem will propagate up to this status indicator."
	::= { battery 1 }

batteryDescription  OBJECT-TYPE
	SYNTAX     DisplayString (SIZE(0..32))
	MAX-ACCESS read-write
	STATUS     current
	DESCRIPTION 
		"A descriptive name of the battery installed in the system."
	::= { battery 2 }

batteryReferenceVoltage  OBJECT-TYPE
	SYNTAX     Integer32 (840..60417)
	MAX-ACCESS read-write
	STATUS     current
	DESCRIPTION 
		"The Voltage at which the DC System float charges.
		Acts as reference voltage when running temperature compensated charging."
	::= { battery 3 }

batteryFusesStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The state of the battery fuses/breakers can mainly be normal(1) or majorAlarm(3) and  
		some other rarely used values ."
	::= { battery 4 }

-- The status value for the measured battery voltage. If the battery voltage reach outside 
-- the limits set by the major/minor low/high level settings this status will change accordingly.

batteryVoltageStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured battery voltage."
	::= { batteryVoltage 1 }

batteryVoltageDescription  OBJECT-TYPE
	SYNTAX     DisplayString (SIZE(0..16))
	MAX-ACCESS read-write
	STATUS     current
	DESCRIPTION 
		"A textual description of the battery voltage monitor. This is stored in the system controller
		and can be changed by the user.  "
	::= { batteryVoltage 2 }

batteryVoltageTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { batteryVoltage 3 }

batteryVoltageAlarmEnable  OBJECT-TYPE
	SYNTAX     INTEGER {
		disabled (0),
		enabled (1)
	}
	MAX-ACCESS read-write
	STATUS     current
	DESCRIPTION 
		"The measured battery voltage alarm enable/disable control"
	::= { batteryVoltage 4 }

batteryVoltageValue  OBJECT-TYPE
	SYNTAX     Integer32
	MAX-ACCESS read-only
	STATUS     current
	DESCRIPTION 
		"The value of the measured battery voltage. Scale is 0.01v."
	::= { batteryVoltage 5 }

batteryVoltageMajorHighLevel  OBJECT-TYPE
	SYNTAX     Integer32
	MAX-ACCESS read-write
	STATUS     current
	DESCRIPTION 
		"The Major High Battery Voltage alarm limit set voltage.Scale is 0.01v."
	::= { batteryVoltage 6 }

batteryVoltageMinorHighLevel  OBJECT-TYPE
	SYNTAX     Integer32
	MAX-ACCESS read-write
	STATUS     current
	DESCRIPTION 
		"The Minor High Battery Voltage alarm limit set voltage.Scale is 0.01v."
	::= { batteryVoltage 7 }

batteryVoltageMinorLowLevel  OBJECT-TYPE
	SYNTAX     Integer32
	MAX-ACCESS read-write
	STATUS     current
	DESCRIPTION 
		"The Minor Low Battery Voltage alarm limit set voltage.Scale is 0.01v."
	::= { batteryVoltage 8 }

batteryVoltageMajorLowLevel  OBJECT-TYPE
	SYNTAX     Integer32
	MAX-ACCESS read-write
	STATUS     current
	DESCRIPTION 
		"The Major Low Battery Voltage alarm limit set voltage.Scale is 0.01v."
	::= { batteryVoltage 9 }

batteryCurrentsStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured battery current"
	::= { batteryCurrents 1 }

batteryCurrentsDescription  OBJECT-TYPE
	SYNTAX     DisplayString (SIZE(0..16))
	MAX-ACCESS read-write
	STATUS     current
	DESCRIPTION 
		"A textual description of the battery current monitor. This is stored in the system controller
		and can be changed by the user.  "
	::= { batteryCurrents 2 }

batteryCurrentsTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryCurrents 3 }

batteryCurrentsAlarmEnable  OBJECT-TYPE
	SYNTAX     INTEGER {
		disabled (0),
		enabled (1)
	}
	MAX-ACCESS read-write
	STATUS     current
	DESCRIPTION 
		"This value once enabled, the alarm condition of the monitor will be reported."
	::= { batteryCurrents 4 }

batteryCurrentsValue  OBJECT-TYPE
	SYNTAX     Integer32
	MAX-ACCESS read-only
	STATUS     current
	DESCRIPTION 
		"The measured total battery current.
		This is the sum of all the enabled shunt measurements in the system.
		Negative battery current indicates discharging of the batteries.
		Positive battery current indicates charging of the batteries.
		Note that the units measured may be i Amperes or in Deciamperes depending on global system settings"
	::= { batteryCurrents 5 }

batteryCurrentsMajorHighLevel  OBJECT-TYPE
	SYNTAX     Integer32
	MAX-ACCESS read-write
	STATUS     current
	DESCRIPTION 
		"The major high alarm limit"
	::= { batteryCurrents 6 }

batteryCurrentsMinorHighLevel  OBJECT-TYPE
	SYNTAX     Integer32
	MAX-ACCESS read-write
	STATUS     current
	DESCRIPTION 
		"The minor high alarm limit"
	::= { batteryCurrents 7 }

batteryCurrentsMinorLowLevel  OBJECT-TYPE
	SYNTAX     Integer32
	MAX-ACCESS read-write
	STATUS     current
	DESCRIPTION 
		"The minor low alarm limit"
	::= { batteryCurrents 8 }

batteryCurrentsMajorLowLevel  OBJECT-TYPE
	SYNTAX     Integer32
	MAX-ACCESS read-write
	STATUS     current
	DESCRIPTION 
		"The major low alarm limit"
	::= { batteryCurrents 9 }

batteryTemperaturesStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The state of the battery fuses/breakers can be either one of the defined enumerated values"
	::= { batteryTemperatures 1 }

batteryTemperaturesDescription  OBJECT-TYPE
	SYNTAX     DisplayString (SIZE(0..16))
	MAX-ACCESS read-write
	STATUS     current
	DESCRIPTION 
		"A textual description of the battery temperature monitor. This is stored in the system controller
		and can be changed by the user. "
	::= { batteryTemperatures 2 }

batteryTemperaturesTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { batteryTemperatures 3 }

batteryTemperaturesAlarmEnable  OBJECT-TYPE
	SYNTAX     INTEGER {
		disabled (0),
		enabled (1)
	}
	MAX-ACCESS read-write
	STATUS     current
	DESCRIPTION 
		"This value once enabled, the alarm condition of the monitor will be reported."
	::= { batteryTemperatures 4 }

batteryTemperaturesValue  OBJECT-TYPE
	SYNTAX     Integer32 (0..9999)
	MAX-ACCESS read-only
	STATUS     current
	DESCRIPTION 
		"The highest value of the enabled battery temperature measurements.
		Depending on the global setting in the Control unit, this value will be presented in Celsius
		or Fahrenheit."
	::= { batteryTemperatures 5 }

batteryTemperaturesMajorHighLevel  OBJECT-TYPE
	SYNTAX     Integer32
	MAX-ACCESS read-write
	STATUS     current
	DESCRIPTION 
		"The major high alarm limit"
	::= { batteryTemperatures 6 }

batteryTemperaturesMinorHighLevel  OBJECT-TYPE
	SYNTAX     Integer32
	MAX-ACCESS read-write
	STATUS     current
	DESCRIPTION 
		"The minor high alarm limit"
	::= { batteryTemperatures 7 }

batteryTemperaturesMinorLowLevel  OBJECT-TYPE
	SYNTAX     Integer32
	MAX-ACCESS read-write
	STATUS     current
	DESCRIPTION 
		"The minor low alarm limit"
	::= { batteryTemperatures 8 }

batteryTemperaturesMajorLowLevel  OBJECT-TYPE
	SYNTAX     Integer32
	MAX-ACCESS read-write
	STATUS     current
	DESCRIPTION 
		"The major low alarm limit"
	::= { batteryTemperatures 9 }

batteryTimeLeftStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the estimated battery remaining backup time."
	::= { batteryTimeLeft 1 }

batteryTimeLeftDescription  OBJECT-TYPE
	SYNTAX     DisplayString (SIZE(0..16))
	MAX-ACCESS read-write
	STATUS     current
	DESCRIPTION 
		"A textual description of the battery discharge time monitor. This is stored in the system controller
		and can be changed by the user.  "
	::= { batteryTimeLeft 2 }

batteryTimeLeftTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryTimeLeft 3 }

batteryTimeLeftAlarmEnable  OBJECT-TYPE
	SYNTAX     INTEGER {
		disabled (0),
		enabled (1)
	}
	MAX-ACCESS read-write
	STATUS     current
	DESCRIPTION 
		"This value once enabled, the alarm condition of the monitor will be reported."
	::= { batteryTimeLeft 4 }

batteryTimeLeftValue  OBJECT-TYPE
	SYNTAX     Integer32
	MAX-ACCESS read-only
	STATUS     current
	DESCRIPTION 
		"The estimated value of battery remaining backup time."
	::= { batteryTimeLeft 5 }

batteryTimeLeftMinorAlarmLevel  OBJECT-TYPE
	SYNTAX     Integer32
	MAX-ACCESS read-write
	STATUS     current
	DESCRIPTION 
		"The minor alarm limit"
	::= { batteryTimeLeft 6 }

batteryTimeLeftMajorAlarmLevel  OBJECT-TYPE
	SYNTAX     Integer32
	MAX-ACCESS read-write
	STATUS     current
	DESCRIPTION 
		"The major alarm limit"
	::= { batteryTimeLeft 7 }

batteryRemainingCapacityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the battery remaining capacity monitor."
	::= { batteryRemainingCapacity 1 }

batteryRemainingCapacityDescription  OBJECT-TYPE
	SYNTAX     DisplayString (SIZE(0..16))
	MAX-ACCESS read-write
	STATUS     current
	DESCRIPTION 
		"A textual description of the battery remaining capacity monitor. This is stored in the system controller
		and can be changed by the user."
	::= { batteryRemainingCapacity 2 }

batteryRemainingCapacityTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryRemainingCapacity 3 }

batteryRemainingCapacityAlarmEnable  OBJECT-TYPE
	SYNTAX     INTEGER {
		disabled (0),
		enabled (1)
	}
	MAX-ACCESS read-write
	STATUS     current
	DESCRIPTION 
		"This value once enabled, the alarm condition of the monitor will be reported."
	::= { batteryRemainingCapacity 4 }

batteryRemainingCapacityValue  OBJECT-TYPE
	SYNTAX     Integer32
	MAX-ACCESS read-only
	STATUS     current
	DESCRIPTION 
		"Battery remaining capacity (SOC) value estimated from the latest battery test result."
	::= { batteryRemainingCapacity 5 }

batteryRemainingCapacityMinorLowLevel  OBJECT-TYPE
	SYNTAX     Integer32
	MAX-ACCESS read-write
	STATUS     current
	DESCRIPTION 
		"The minor low alarm limit"
	::= { batteryRemainingCapacity 6 }

batteryRemainingCapacityMajorLowLevel  OBJECT-TYPE
	SYNTAX     Integer32
	MAX-ACCESS read-write
	STATUS     current
	DESCRIPTION 
		"The major low alarm limit"
	::= { batteryRemainingCapacity 7 }

batteryUsedCapacityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the battery used capacity (DoD) monitor"
	::= { batteryUsedCapacity 1 }

batteryUsedCapacityDescription  OBJECT-TYPE
	SYNTAX     DisplayString (SIZE(0..16))
	MAX-ACCESS read-write
	STATUS     current
	DESCRIPTION 
		"A textual description of the battery used capacity (DoD) monitor. This is stored in the system controller
		and can be changed by the user.  "
	::= { batteryUsedCapacity 2 }

batteryUsedCapacityTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryUsedCapacity 3 }

batteryUsedCapacityAlarmEnable  OBJECT-TYPE
	SYNTAX     INTEGER {
		disabled (0),
		enabled (1)
	}
	MAX-ACCESS read-write
	STATUS     current
	DESCRIPTION 
		"This value once enabled, the alarm condition of the monitor will be reported."
	::= { batteryUsedCapacity 4 }

batteryUsedCapacityValue  OBJECT-TYPE
	SYNTAX     Integer32
	MAX-ACCESS read-only
	STATUS     current
	DESCRIPTION 
		"This is the estimated battery used capacity (DoD)."
	::= { batteryUsedCapacity 5 }

batteryUsedCapacityMajorAlarmLevel  OBJECT-TYPE
	SYNTAX     Integer32
	MAX-ACCESS read-write
	STATUS     current
	DESCRIPTION 
		"The major alarm limit"
	::= { batteryUsedCapacity 6 }

batteryUsedCapacityMinorAlarmLevel  OBJECT-TYPE
	SYNTAX     Integer32
	MAX-ACCESS read-write
	STATUS     current
	DESCRIPTION 
		"The minor alarm limit"
	::= { batteryUsedCapacity 7 }

batteryTotalCapacityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the total capacity monitor."
	::= { batteryTotalCapacity 1 }

batteryTotalCapacityDescription  OBJECT-TYPE
	SYNTAX     DisplayString (SIZE(0..16))
	MAX-ACCESS read-write
	STATUS     current
	DESCRIPTION 
		"A textual description of the battery total capacity monitor. This is stored in the system controller
		and can be changed by the user"
	::= { batteryTotalCapacity 2 }

batteryTotalCapacityTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryTotalCapacity 3 }

batteryTotalCapacityAlarmEnable  OBJECT-TYPE
	SYNTAX     INTEGER {
		disabled (0),
		enabled (1)
	}
	MAX-ACCESS read-write
	STATUS     current
	DESCRIPTION 
		"This value once enabled, the alarm condition of the monitor will be reported."
	::= { batteryTotalCapacity 4 }

batteryTotalCapacityValue  OBJECT-TYPE
	SYNTAX     Integer32
	MAX-ACCESS read-only
	STATUS     current
	DESCRIPTION 
		"This is the estimated total battery capacity (installed Ah - SoH) value."
	::= { batteryTotalCapacity 5 }

batteryTotalCapacityMinorLowLevel  OBJECT-TYPE
	SYNTAX     Integer32
	MAX-ACCESS read-write
	STATUS     current
	DESCRIPTION 
		"The minor low alarm limit"
	::= { batteryTotalCapacity 6 }

batteryTotalCapacityMajorLowLevel  OBJECT-TYPE
	SYNTAX     Integer32
	MAX-ACCESS read-write
	STATUS     current
	DESCRIPTION 
		"The major low alarm limit"
	::= { batteryTotalCapacity 7 }

batteryQualityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the battery quality (SoH) monitor."
	::= { batteryQuality 1 }

batteryQualityDescription  OBJECT-TYPE
	SYNTAX     DisplayString (SIZE(0..16))
	MAX-ACCESS read-write
	STATUS     current
	DESCRIPTION 
		"A textual description of the battery quality (SoH) monitor. This is stored in the system controller
		and can be changed by the user"
	::= { batteryQuality 2 }

batteryQualityTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { batteryQuality 3 }

batteryQualityAlarmEnable  OBJECT-TYPE
	SYNTAX     INTEGER {
		disabled (0),
		enabled (1)
	}
	MAX-ACCESS read-write
	STATUS     current
	DESCRIPTION 
		"This value once enabled, the alarm condition of the monitor will be reported."
	::= { batteryQuality 4 }

batteryQualityValue  OBJECT-TYPE
	SYNTAX     Integer32
	MAX-ACCESS read-only
	STATUS     current
	DESCRIPTION 
		"The calculated battery quality (SoH) based on the latest battery test"
	::= { batteryQuality 5 }

batteryQualityMinorAlarmLevel  OBJECT-TYPE
	SYNTAX     Integer32
	MAX-ACCESS read-write
	STATUS     current
	DESCRIPTION 
		"The minor alarm limit"
	::= { batteryQuality 6 }

batteryQualityMajorAlarmLevel  OBJECT-TYPE
	SYNTAX     Integer32
	MAX-ACCESS read-write
	STATUS     current
	DESCRIPTION 
		"The major alarm limit"
	::= { batteryQuality 7 }

batteryLVBDStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The Battery Contactor is connected, disconnected, disabled or in any other alarm condition"
	::= { batteryLVBD 1 }

batteryLVBDDescription  OBJECT-TYPE
	SYNTAX     DisplayString (SIZE(0..16))
	MAX-ACCESS read-write
	STATUS     current
	DESCRIPTION 
		"A textual description of the battery LVBD monitor. This is stored in the system controller
		and can be changed by the user.  "
	::= { batteryLVBD 2 }

batteryLVBDTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryLVBD 3 }

batteryLVBDEnable  OBJECT-TYPE
	SYNTAX     INTEGER {
		disabled (0),
		enabled (1)
	}
	MAX-ACCESS read-write
	STATUS     current
	DESCRIPTION 
		"This value once enabled, the alarm condition of the LVBD will be reported."
	::= { batteryLVBD 4 }

batteryLVBDValue  OBJECT-TYPE
	SYNTAX     Integer32
	MAX-ACCESS read-only
	STATUS     current
	DESCRIPTION 
		"The measured value of the LVBD."
	::= { batteryLVBD 5 }

batteryLVBDConnectVoltage  OBJECT-TYPE
	SYNTAX     Integer32
	MAX-ACCESS read-write
	STATUS     current
	DESCRIPTION 
		"The Battery Contactor's Reconnect Voltage"
	::= { batteryLVBD 6 }

batteryLVBDDisconnectVoltage  OBJECT-TYPE
	SYNTAX     Integer32
	MAX-ACCESS read-write
	STATUS     current
	DESCRIPTION 
		"The Battery Contactor's Disconnect Voltage"
	::= { batteryLVBD 7 }

batteryChargeCurrentLimitEnable  OBJECT-TYPE
	SYNTAX     INTEGER {
		disabled (0),
		enabled (1)
	}
	MAX-ACCESS read-write
	STATUS     current
	DESCRIPTION 
		"Enable/disable of the battery charge current limitation feature; 0=disable, 1=enable."
	::= { batteryChargeCurrentLimit 1 }

batteryChargeCurrentLimitValue  OBJECT-TYPE
	SYNTAX     Integer32 (0..32767)
	MAX-ACCESS read-write
	STATUS     current
	DESCRIPTION 
		"Battery charging current limit value. Used only when AC source is mains feed.
		Note that the units measured may be i Amperes or in Deciamperes depending on global system settings"
	::= { batteryChargeCurrentLimit 2 }

batteryBoostVoltage  OBJECT-TYPE
	SYNTAX     Integer32 (870..60418)
	MAX-ACCESS read-write
	STATUS     current
	DESCRIPTION 
		"The Voltage at which the DC System boost charges the batteries."
	::= { batteryBoost 1 }

batteryBoostCommand  OBJECT-TYPE
	SYNTAX     INTEGER {
		pushbutton (0),
		startboost (1),
		stopboost (2)
	}
	MAX-ACCESS read-write
	STATUS     current
	DESCRIPTION 
		"This pushbutton will start or stop a manual battery boost if the system allows it."
	::= { batteryBoost 2 }

batteryBoostCurrentThreshold  OBJECT-TYPE
	SYNTAX     Integer32
	MAX-ACCESS read-write
	STATUS     current
	DESCRIPTION 
		"The boosting will terminate when the charge current drops below the BoostCurrentThreshold limit."
	::= { batteryBoost 3 }

batteryBoostManualMaxDuration  OBJECT-TYPE
	SYNTAX     Integer32 (0..1440)
	MAX-ACCESS read-write
	STATUS     current
	DESCRIPTION 
		"A protection against overcharging.  
		When running manual boost, the boosting will always terminate at this point.  "
	::= { batteryBoost 4 }

batteryTestVoltage  OBJECT-TYPE
	SYNTAX     Integer32
	MAX-ACCESS read-write
	STATUS     current
	DESCRIPTION 
		"This is the simplified battery test end voltage. The battery test will be terminated when the voltage
		drops below the end voltage."
	::= { batteryTest 1 }

batteryTestCommand  OBJECT-TYPE
	SYNTAX     INTEGER {
		pushbutton (0),
		starttest (1),
		stoptest (2)
	}
	MAX-ACCESS read-write
	STATUS     current
	DESCRIPTION 
		"This pushbutton will start or stop a manual battery test if the system allows it."
	::= { batteryTest 2 }

batteryTestNumberOfResults  OBJECT-TYPE
	SYNTAX     Integer32 (0..10)
	MAX-ACCESS read-only
	STATUS     current
	DESCRIPTION 
		"This is the number of valid battery test results stored in controller."
	::= { batteryTest 3 }

batteryTestResultTable  OBJECT-TYPE
	SYNTAX SEQUENCE OF BatteryTestResultEntry
	MAX-ACCESS not-accessible
	STATUS     current
	DESCRIPTION 
		"This table contains the battery test results stored in controller."
	::= { batteryTest 4 }

batteryTestResultEntry  OBJECT-TYPE
	SYNTAX 	BatteryTestResultEntry
	MAX-ACCESS not-accessible
	STATUS     current
	DESCRIPTION 
		""
	INDEX { batteryTestResultIndex }
	::= { batteryTestResultTable 1 }

BatteryTestResultEntry ::= SEQUENCE {
	batteryTestResultIndex
		Integer32,
	batteryTestResultStartDateTime
		DateAndTime,
	batteryTestResultDuration
		Integer32,
	batteryTestResultDischarged
		Integer32,
	batteryTestResultQuality
		Integer32,
	batteryTestResultEndVoltage
		Integer32,
	batteryTestResultTestResult
		INTEGER,
	batteryTestResultTerminationCriteria
		INTEGER,
	batteryTestResultBatteryTemperature
		Integer32
}

batteryTestResultIndex  OBJECT-TYPE
	SYNTAX     Integer32 (1..10)
	MAX-ACCESS not-accessible
	STATUS     current
	DESCRIPTION 
		"A index pointing to one of ten possible battery test results"
	::= { batteryTestResultEntry 1 }

batteryTestResultStartDateTime  OBJECT-TYPE
	SYNTAX     DateAndTime
	MAX-ACCESS read-only
	STATUS     current
	DESCRIPTION 
		"This is the time and date when the test started."
	::= { batteryTestResultEntry 2 }

batteryTestResultDuration  OBJECT-TYPE
	SYNTAX     Integer32
	MAX-ACCESS read-only
	STATUS     current
	DESCRIPTION 
		"This is the test duration in minutes."
	::= { batteryTestResultEntry 3 }

batteryTestResultDischarged  OBJECT-TYPE
	SYNTAX     Integer32
	MAX-ACCESS read-only
	STATUS     current
	DESCRIPTION 
		"This is the discharged Ah during test."
	::= { batteryTestResultEntry 4 }

batteryTestResultQuality  OBJECT-TYPE
	SYNTAX     Integer32
	MAX-ACCESS read-only
	STATUS     current
	DESCRIPTION 
		"This is the calculated battery quality (SoH)in percentage."
	::= { batteryTestResultEntry 5 }

batteryTestResultEndVoltage  OBJECT-TYPE
	SYNTAX     Integer32
	MAX-ACCESS read-only
	STATUS     current
	DESCRIPTION 
		"This is the test end voltage in volt."
	::= { batteryTestResultEntry 6 }

batteryTestResultTestResult  OBJECT-TYPE
	SYNTAX     INTEGER {
		error (0),
		normal (1),
		minorHigh (2),
		majorHigh (3),
		disable (4),
		disconnect (5),
		reconnect (6),
		critical (7),
		majorLow (8),
		minorLow (9)
	}
	MAX-ACCESS read-only
	STATUS     current
	DESCRIPTION 
		"This is the test result."
	::= { batteryTestResultEntry 7 }

batteryTestResultTerminationCriteria  OBJECT-TYPE
	SYNTAX     INTEGER {
		na (0),
		endVoltage (1),
		endTime (2),
		userCancel (3),
		mainsCancel (4),
		endAh (5)
	}
	MAX-ACCESS read-only
	STATUS     current
	DESCRIPTION 
		"This is the test Termination Criteria."
	::= { batteryTestResultEntry 8 }

batteryTestResultBatteryTemperature  OBJECT-TYPE
	SYNTAX     Integer32
	MAX-ACCESS read-only
	STATUS     current
	DESCRIPTION 
		"This is the battery temperature"
	::= { batteryTestResultEntry 9 }

batteryTestDuration  OBJECT-TYPE
	SYNTAX     Unsigned32
	MAX-ACCESS read-write
	STATUS     current
	DESCRIPTION 
		"This is the battery test max duration. "
	::= { batteryTest 5 }

batteryTestCfgTestType  OBJECT-TYPE
	SYNTAX     INTEGER {
		normalTest (0),
		simplifiedTest (1)
	}
	MAX-ACCESS read-write
	STATUS     current
	DESCRIPTION 
		"This is to configurate normal or simplified battery test."
	::= { batteryTest 6 }

batteryTestEnableMaxDuration  OBJECT-TYPE
	SYNTAX     INTEGER {
		disabled (0),
		enabled (1)
	}
	MAX-ACCESS read-write
	STATUS     current
	DESCRIPTION 
		"This is to enable/disable battery test max duration."
	::= { batteryTest 7 }

batteryTempCompEnable  OBJECT-TYPE
	SYNTAX     INTEGER {
		disabled (0),
		enabled (1)
	}
	MAX-ACCESS read-write
	STATUS     current
	DESCRIPTION 
		"Enable (1) or Disable (0)  of Battery Temperature Compensated output regulation mode"
	::= { batteryTempComp 1 }

batteryBankNumberOfBanks  OBJECT-TYPE
	SYNTAX     Integer32 (0..8)
	MAX-ACCESS read-write
	STATUS     current
	DESCRIPTION 
		"Number of battery banks installed in system."
	::= { batteryBank 1 }

batteryBankTable  OBJECT-TYPE
	SYNTAX SEQUENCE OF BatteryBankEntry
	MAX-ACCESS not-accessible
	STATUS     current
	DESCRIPTION 
		""
	::= { batteryBank 2 }

batteryBankEntry  OBJECT-TYPE
	SYNTAX 	BatteryBankEntry
	MAX-ACCESS not-accessible
	STATUS     current
	DESCRIPTION 
		""
	INDEX { batteryBankIndex }
	::= { batteryBankTable 1 }

BatteryBankEntry ::= SEQUENCE {
	batteryBankIndex
		Integer32,
	batteryBankStatus
		INTEGER,
	batteryBankNumberOfTemperatures
		Integer32,
	batteryBankNumberOfCurrents
		Integer32,
	batteryBankNumberOfFuses
		Integer32,
	batteryBankNumberOfSymmetries
		Integer32
}

batteryBankIndex  OBJECT-TYPE
	SYNTAX     Integer32 (1..8)
	MAX-ACCESS not-accessible
	STATUS     current
	DESCRIPTION 
		"Index used for navigating the rows 1..8  of batteryBankTable "
	::= { batteryBankEntry 1 }

batteryBankStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of battery bank"
	::= { batteryBankEntry 2 }

batteryBankNumberOfTemperatures  OBJECT-TYPE
	SYNTAX     Integer32 (0..4)
	MAX-ACCESS read-only
	STATUS     current
	DESCRIPTION 
		"Number of temperature measurements in battery bank."
	::= { batteryBankEntry 3 }

batteryBankNumberOfCurrents  OBJECT-TYPE
	SYNTAX     Integer32 (0..4)
	MAX-ACCESS read-only
	STATUS     current
	DESCRIPTION 
		"Number of current measurements in battery bank."
	::= { batteryBankEntry 4 }

batteryBankNumberOfFuses  OBJECT-TYPE
	SYNTAX     Integer32 (0..4)
	MAX-ACCESS read-only
	STATUS     current
	DESCRIPTION 
		"Number of fuses installed in battery bank."
	::= { batteryBankEntry 5 }

batteryBankNumberOfSymmetries  OBJECT-TYPE
	SYNTAX     Integer32 (0..4)
	MAX-ACCESS read-only
	STATUS     current
	DESCRIPTION 
		"Number of symmetry measurements available in battery bank."
	::= { batteryBankEntry 6 }

batteryBankTemperatureTable  OBJECT-TYPE
	SYNTAX SEQUENCE OF BatteryBankTemperatureEntry
	MAX-ACCESS not-accessible
	STATUS     current
	DESCRIPTION 
		""
	::= { batteryBank 3 }

batteryBankTemperatureEntry  OBJECT-TYPE
	SYNTAX 	BatteryBankTemperatureEntry
	MAX-ACCESS not-accessible
	STATUS     current
	DESCRIPTION 
		""
	INDEX { batteryBankIndex, 
		batteryTemperatureIndex }
	::= { batteryBankTemperatureTable 1 }

BatteryBankTemperatureEntry ::= SEQUENCE {
	batteryTemperatureIndex
		Integer32,
	batteryTemperatureStatus
		INTEGER,
	batteryTemperatureDescription
		DisplayString,
	batteryTemperatureTrapRepeatCounter
		Counter32,
	batteryTemperatureAlarmEnable
		INTEGER,
	batteryTemperatureValue
		Integer32,
	batteryTemperatureMajorHighLevel
		Integer32,
	batteryTemperatureMinorHighLevel
		Integer32,
	batteryTemperatureMinorLowLevel
		Integer32,
	batteryTemperatureMajorLowLevel
		Integer32
}

batteryTemperatureIndex  OBJECT-TYPE
	SYNTAX     Integer32 (1..4)
	MAX-ACCESS not-accessible
	STATUS     current
	DESCRIPTION 
		"This index denotes which row in the temperature input table.
		The size of the table is defined by the batteryBankNumberOfTemp   "
	::= { batteryBankTemperatureEntry 1 }

batteryTemperatureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery temperature monitor"
	::= { batteryBankTemperatureEntry 2 }

batteryTemperatureDescription  OBJECT-TYPE
	SYNTAX     DisplayString (SIZE(0..16))
	MAX-ACCESS read-write
	STATUS     current
	DESCRIPTION 
		"A textual description of the battery temperature monitor. This is stored in the system controller
		and can be changed by the user. "
	::= { batteryBankTemperatureEntry 3 }

batteryTemperatureTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryBankTemperatureEntry 4 }

batteryTemperatureAlarmEnable  OBJECT-TYPE
	SYNTAX     INTEGER {
		disabled (0),
		enabled (1)
	}
	MAX-ACCESS read-write
	STATUS     current
	DESCRIPTION 
		"This value once enabled, the alarm condition of the monitor will be reported."
	::= { batteryBankTemperatureEntry 5 }

batteryTemperatureValue  OBJECT-TYPE
	SYNTAX     Integer32
	MAX-ACCESS read-only
	STATUS     current
	DESCRIPTION 
		"The measured battery temperature."
	::= { batteryBankTemperatureEntry 6 }

batteryTemperatureMajorHighLevel  OBJECT-TYPE
	SYNTAX     Integer32
	MAX-ACCESS read-write
	STATUS     current
	DESCRIPTION 
		"The major high alarm limit"
	::= { batteryBankTemperatureEntry 7 }

batteryTemperatureMinorHighLevel  OBJECT-TYPE
	SYNTAX     Integer32
	MAX-ACCESS read-write
	STATUS     current
	DESCRIPTION 
		"The minor high alarm limit"
	::= { batteryBankTemperatureEntry 8 }

batteryTemperatureMinorLowLevel  OBJECT-TYPE
	SYNTAX     Integer32
	MAX-ACCESS read-write
	STATUS     current
	DESCRIPTION 
		"The minor low alarm limit"
	::= { batteryBankTemperatureEntry 9 }

batteryTemperatureMajorLowLevel  OBJECT-TYPE
	SYNTAX     Integer32
	MAX-ACCESS read-write
	STATUS     current
	DESCRIPTION 
		"The major low alarm limit"
	::= { batteryBankTemperatureEntry 10 }

batteryBankCurrentTable  OBJECT-TYPE
	SYNTAX SEQUENCE OF BatteryBankCurrentEntry
	MAX-ACCESS not-accessible
	STATUS     current
	DESCRIPTION 
		""
	::= { batteryBank 4 }

batteryBankCurrentEntry  OBJECT-TYPE
	SYNTAX 	BatteryBankCurrentEntry
	MAX-ACCESS not-accessible
	STATUS     current
	DESCRIPTION 
		""
	INDEX { batteryBankIndex, 
		batteryCurrentIndex }
	::= { batteryBankCurrentTable 1 }

BatteryBankCurrentEntry ::= SEQUENCE {
	batteryCurrentIndex
		Integer32,
	batteryCurrentStatus
		INTEGER,
	batteryCurrentDescription
		DisplayString,
	batteryCurrentTrapRepeatCounter
		Counter32,
	batteryCurrentAlarmEnable
		INTEGER,
	batteryCurrentValue
		Integer32,
	batteryCurrentMajorHighLevel
		Integer32,
	batteryCurrentMinorHighLevel
		Integer32,
	batteryCurrentMinorLowLevel
		Integer32,
	batteryCurrentMajorLowLevel
		Integer32
}

batteryCurrentIndex  OBJECT-TYPE
	SYNTAX     Integer32 (1..4)
	MAX-ACCESS not-accessible
	STATUS     current
	DESCRIPTION 
		"This index denotes which row in the current input table.
		        The size of the table is defined by the system"
	::= { batteryBankCurrentEntry 1 }

batteryCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery current monitor"
	::= { batteryBankCurrentEntry 2 }

batteryCurrentDescription  OBJECT-TYPE
	SYNTAX     DisplayString (SIZE(0..16))
	MAX-ACCESS read-write
	STATUS     current
	DESCRIPTION 
		"A textual description of the battery current monitor. This is stored in the system controller
		and can be changed by the user. "
	::= { batteryBankCurrentEntry 3 }

batteryCurrentTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryBankCurrentEntry 4 }

batteryCurrentAlarmEnable  OBJECT-TYPE
	SYNTAX     INTEGER {
		disabled (0),
		enabled (1)
	}
	MAX-ACCESS read-write
	STATUS     current
	DESCRIPTION 
		"This value once enabled, the alarm condition of the monitor will be reported."
	::= { batteryBankCurrentEntry 5 }

batteryCurrentValue  OBJECT-TYPE
	SYNTAX     Integer32
	MAX-ACCESS read-only
	STATUS     current
	DESCRIPTION 
		"The measured battery current"
	::= { batteryBankCurrentEntry 6 }

batteryCurrentMajorHighLevel  OBJECT-TYPE
	SYNTAX     Integer32
	MAX-ACCESS read-write
	STATUS     current
	DESCRIPTION 
		"The major high alarm limit"
	::= { batteryBankCurrentEntry 7 }

batteryCurrentMinorHighLevel  OBJECT-TYPE
	SYNTAX     Integer32
	MAX-ACCESS read-write
	STATUS     current
	DESCRIPTION 
		"The minor high alarm limit"
	::= { batteryBankCurrentEntry 8 }

batteryCurrentMinorLowLevel  OBJECT-TYPE
	SYNTAX     Integer32
	MAX-ACCESS read-write
	STATUS     current
	DESCRIPTION 
		"The minor low alarm limit"
	::= { batteryBankCurrentEntry 9 }

batteryCurrentMajorLowLevel  OBJECT-TYPE
	SYNTAX     Integer32
	MAX-ACCESS read-write
	STATUS     current
	DESCRIPTION 
		"The major low alarm limit"
	::= { batteryBankCurrentEntry 10 }

batteryBankFuseTable  OBJECT-TYPE
	SYNTAX SEQUENCE OF BatteryBankFuseEntry
	MAX-ACCESS not-accessible
	STATUS     current
	DESCRIPTION 
		""
	::= { batteryBank 5 }

batteryBankFuseEntry  OBJECT-TYPE
	SYNTAX 	BatteryBankFuseEntry
	MAX-ACCESS not-accessible
	STATUS     current
	DESCRIPTION 
		""
	INDEX { batteryBankIndex, 
		batteryFuseIndex }
	::= { batteryBankFuseTable 1 }

BatteryBankFuseEntry ::= SEQUENCE {
	batteryFuseIndex
		Integer32,
	batteryFuseStatus
		INTEGER,
	batteryFuseDescription
		DisplayString,
	batteryFuseTrapRepeatCounter
		Counter32,
	batteryFuseAlarmEnable
		INTEGER,
	batteryFuseValue
		Integer32
}

batteryFuseIndex  OBJECT-TYPE
	SYNTAX     Integer32 (1..4)
	MAX-ACCESS not-accessible
	STATUS     current
	DESCRIPTION 
		"This index denotes which row in the fuse table.
		        The size of the table is defined by the system"
	::= { batteryBankFuseEntry 1 }

batteryFuseStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery fuse monitor"
	::= { batteryBankFuseEntry 2 }

batteryFuseDescription  OBJECT-TYPE
	SYNTAX     DisplayString (SIZE(0..16))
	MAX-ACCESS read-write
	STATUS     current
	DESCRIPTION 
		"A textual description of the battery fuse monitor. This is stored in the system controller
		and can be changed by the user."
	::= { batteryBankFuseEntry 3 }

batteryFuseTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryBankFuseEntry 4 }

batteryFuseAlarmEnable  OBJECT-TYPE
	SYNTAX     INTEGER {
		disabled (0),
		enabled (1)
	}
	MAX-ACCESS read-write
	STATUS     current
	DESCRIPTION 
		"This value once enabled, the alarm condition of the monitor will be reported."
	::= { batteryBankFuseEntry 5 }

batteryFuseValue  OBJECT-TYPE
	SYNTAX     Integer32
	MAX-ACCESS read-only
	STATUS     current
	DESCRIPTION 
		"The measured value of battery fuse input."
	::= { batteryBankFuseEntry 6 }

batteryBankSymmetryTable  OBJECT-TYPE
	SYNTAX SEQUENCE OF BatteryBankSymmetryEntry
	MAX-ACCESS not-accessible
	STATUS     current
	DESCRIPTION 
		""
	::= { batteryBank 6 }

batteryBankSymmetryEntry  OBJECT-TYPE
	SYNTAX 	BatteryBankSymmetryEntry
	MAX-ACCESS not-accessible
	STATUS     current
	DESCRIPTION 
		""
	INDEX { batteryBankIndex, 
		batteryBankSymmetryIndex }
	::= { batteryBankSymmetryTable 1 }

BatteryBankSymmetryEntry ::= SEQUENCE {
	batteryBankSymmetryIndex
		Integer32,
	batteryBankSymmetryStatus
		INTEGER,
	batteryBankSymmetryDescription
		DisplayString,
	batteryBankSymmetryTrapRepeatCounter
		Counter32,
	batteryBankSymmetryAlarmEnable
		INTEGER,
	batteryBankSymmetryMeasureValue
		Integer32,
	batteryBankSymmetryDeltaValue
		Integer32,
	batteryBankSymmetryMajorAlarmLevel
		Integer32,
	batteryBankSymmetryMinorAlarmLevel
		Integer32
}

batteryBankSymmetryIndex  OBJECT-TYPE
	SYNTAX     Integer32 (1..8)
	MAX-ACCESS not-accessible
	STATUS     current
	DESCRIPTION 
		"This index denotes which row in the symmetry input table.
		The size of the table is defined by the batteryMonitorNumberOfSymmetries"
	::= { batteryBankSymmetryEntry 1 }

batteryBankSymmetryStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery symmetry monitor"
	::= { batteryBankSymmetryEntry 2 }

batteryBankSymmetryDescription  OBJECT-TYPE
	SYNTAX     DisplayString (SIZE(0..16))
	MAX-ACCESS read-write
	STATUS     current
	DESCRIPTION 
		"A textual description of the battery monitor symmetry. This is stored in the system controller
		and can be changed by the user. "
	::= { batteryBankSymmetryEntry 3 }

batteryBankSymmetryTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off"
	::= { batteryBankSymmetryEntry 4 }

batteryBankSymmetryAlarmEnable  OBJECT-TYPE
	SYNTAX     INTEGER {
		disabled (0),
		enabled (1)
	}
	MAX-ACCESS read-write
	STATUS     current
	DESCRIPTION 
		"This value once enabled, the alarm condition of the monitor will be reported."
	::= { batteryBankSymmetryEntry 5 }

batteryBankSymmetryMeasureValue  OBJECT-TYPE
	SYNTAX     Integer32
	MAX-ACCESS read-only
	STATUS     current
	DESCRIPTION 
		"The measured battery symmetry voltage in battery monitor."
	::= { batteryBankSymmetryEntry 6 }

batteryBankSymmetryDeltaValue  OBJECT-TYPE
	SYNTAX     Integer32
	MAX-ACCESS read-only
	STATUS     current
	DESCRIPTION 
		"The measured battery symmetry delta voltage in battery monitor."
	::= { batteryBankSymmetryEntry 7 }

batteryBankSymmetryMajorAlarmLevel  OBJECT-TYPE
	SYNTAX     Integer32
	MAX-ACCESS read-write
	STATUS     current
	DESCRIPTION 
		"The major alarm limit"
	::= { batteryBankSymmetryEntry 8 }

batteryBankSymmetryMinorAlarmLevel  OBJECT-TYPE
	SYNTAX     Integer32
	MAX-ACCESS read-write
	STATUS     current
	DESCRIPTION 
		"The minor alarm limit"
	::= { batteryBankSymmetryEntry 9 }

batteryMonitorsNumberOfUnits  OBJECT-TYPE
	SYNTAX     Integer32
	MAX-ACCESS read-write
	STATUS     current
	DESCRIPTION 
		"The number of battery monitor installed in system."
	::= { batteryMonitors 1 }

batteryMonitorsTable  OBJECT-TYPE
	SYNTAX SEQUENCE OF BatteryMonitorsEntry
	MAX-ACCESS not-accessible
	STATUS     current
	DESCRIPTION 
		""
	::= { batteryMonitors 2 }

batteryMonitorsEntry  OBJECT-TYPE
	SYNTAX 	BatteryMonitorsEntry
	MAX-ACCESS not-accessible
	STATUS     current
	DESCRIPTION 
		""
	INDEX { batteryMonitorIndex }
	::= { batteryMonitorsTable 1 }

BatteryMonitorsEntry ::= SEQUENCE {
	batteryMonitorIndex
		Integer32,
	batteryMonitorNumberOfTemperatures
		Integer32,
	batteryMonitorNumberOfCurrents
		Integer32,
	batteryMonitorNumberOfFuses
		Integer32,
	batteryMonitorNumberOfSymmetries
		Integer32
}

batteryMonitorIndex  OBJECT-TYPE
	SYNTAX     Integer32 (1..8)
	MAX-ACCESS not-accessible
	STATUS     current
	DESCRIPTION 
		"Index used for navigating the rows 1..8  of batteryMonitorsTable"
	::= { batteryMonitorsEntry 1 }

batteryMonitorNumberOfTemperatures  OBJECT-TYPE
	SYNTAX     Integer32 (0..4)
	MAX-ACCESS read-only
	STATUS     current
	DESCRIPTION 
		"The number of temperature measurements in battery monitor."
	::= { batteryMonitorsEntry 2 }

batteryMonitorNumberOfCurrents  OBJECT-TYPE
	SYNTAX     Integer32 (0..4)
	MAX-ACCESS read-only
	STATUS     current
	DESCRIPTION 
		"The number of current measurements in battery monitor."
	::= { batteryMonitorsEntry 3 }

batteryMonitorNumberOfFuses  OBJECT-TYPE
	SYNTAX     Integer32 (0..4)
	MAX-ACCESS read-only
	STATUS     current
	DESCRIPTION 
		"The number of fuse measurements in battery monitor."
	::= { batteryMonitorsEntry 4 }

batteryMonitorNumberOfSymmetries  OBJECT-TYPE
	SYNTAX     Integer32 (0..4)
	MAX-ACCESS read-only
	STATUS     current
	DESCRIPTION 
		"The number of symmetry measurements in battery monitor."
	::= { batteryMonitorsEntry 5 }

batteryMonitorTemperatureTable  OBJECT-TYPE
	SYNTAX SEQUENCE OF BatteryMonitorTemperatureEntry
	MAX-ACCESS not-accessible
	STATUS     current
	DESCRIPTION 
		""
	::= { batteryMonitors 3 }

batteryMonitorTemperatureEntry  OBJECT-TYPE
	SYNTAX 	BatteryMonitorTemperatureEntry
	MAX-ACCESS not-accessible
	STATUS     current
	DESCRIPTION 
		""
	INDEX { batteryMonitorIndex, 
		batteryMonitorTemperatureIndex }
	::= { batteryMonitorTemperatureTable 1 }

BatteryMonitorTemperatureEntry ::= SEQUENCE {
	batteryMonitorTemperatureIndex
		Integer32,
	batteryMonitorTemperatureStatus
		INTEGER,
	batteryMonitorTemperatureDescription
		DisplayString,
	batteryMonitorTemperatureTrapRepeatCounter
		Counter32,
	batteryMonitorTemperatureAlarmEnable
		INTEGER,
	batteryMonitorTemperatureValue
		Integer32,
	batteryMonitorTemperatureMajorHighLevel
		Integer32,
	batteryMonitorTemperatureMinorHighLevel
		Integer32,
	batteryMonitorTemperatureMinorLowLevel
		Integer32,
	batteryMonitorTemperatureMajorLowLevel
		Integer32
}

batteryMonitorTemperatureIndex  OBJECT-TYPE
	SYNTAX     Integer32 (1..4)
	MAX-ACCESS not-accessible
	STATUS     current
	DESCRIPTION 
		"This index denotes which row in the temperature input table.
		The size of the table is defined by the batteryMonitorNumberOfTemperatures"
	::= { batteryMonitorTemperatureEntry 1 }

batteryMonitorTemperatureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery temperature monitor"
	::= { batteryMonitorTemperatureEntry 2 }

batteryMonitorTemperatureDescription  OBJECT-TYPE
	SYNTAX     DisplayString (SIZE(0..16))
	MAX-ACCESS read-write
	STATUS     current
	DESCRIPTION 
		"A textual description of the battery monitor temperature. This is stored in the system controller
		and can be changed by the user. "
	::= { batteryMonitorTemperatureEntry 3 }

batteryMonitorTemperatureTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off"
	::= { batteryMonitorTemperatureEntry 4 }

batteryMonitorTemperatureAlarmEnable  OBJECT-TYPE
	SYNTAX     INTEGER {
		disabled (0),
		enabled (1)
	}
	MAX-ACCESS read-write
	STATUS     current
	DESCRIPTION 
		"This value once enabled, the alarm condition of the monitor will be reported."
	::= { batteryMonitorTemperatureEntry 5 }

batteryMonitorTemperatureValue  OBJECT-TYPE
	SYNTAX     Integer32
	MAX-ACCESS read-only
	STATUS     current
	DESCRIPTION 
		"The measured battery temperature in battery monitor."
	::= { batteryMonitorTemperatureEntry 6 }

batteryMonitorTemperatureMajorHighLevel  OBJECT-TYPE
	SYNTAX     Integer32
	MAX-ACCESS read-write
	STATUS     current
	DESCRIPTION 
		"The major high alarm limit"
	::= { batteryMonitorTemperatureEntry 7 }

batteryMonitorTemperatureMinorHighLevel  OBJECT-TYPE
	SYNTAX     Integer32
	MAX-ACCESS read-write
	STATUS     current
	DESCRIPTION 
		"The minor high alarm limit"
	::= { batteryMonitorTemperatureEntry 8 }

batteryMonitorTemperatureMinorLowLevel  OBJECT-TYPE
	SYNTAX     Integer32
	MAX-ACCESS read-write
	STATUS     current
	DESCRIPTION 
		"The minor low alarm limit"
	::= { batteryMonitorTemperatureEntry 9 }

batteryMonitorTemperatureMajorLowLevel  OBJECT-TYPE
	SYNTAX     Integer32
	MAX-ACCESS read-write
	STATUS     current
	DESCRIPTION 
		"The major low alarm limit"
	::= { batteryMonitorTemperatureEntry 10 }

batteryMonitorCurrentTable  OBJECT-TYPE
	SYNTAX SEQUENCE OF BatteryMonitorCurrentEntry
	MAX-ACCESS not-accessible
	STATUS     current
	DESCRIPTION 
		""
	::= { batteryMonitors 4 }

batteryMonitorCurrentEntry  OBJECT-TYPE
	SYNTAX 	BatteryMonitorCurrentEntry
	MAX-ACCESS not-accessible
	STATUS     current
	DESCRIPTION 
		""
	INDEX { batteryMonitorIndex, 
		batteryMonitorCurrentIndex }
	::= { batteryMonitorCurrentTable 1 }

BatteryMonitorCurrentEntry ::= SEQUENCE {
	batteryMonitorCurrentIndex
		Integer32,
	batteryMonitorCurrentStatus
		INTEGER,
	batteryMonitorCurrentDescription
		DisplayString,
	batteryMonitorCurrentTrapRepeatCounter
		Counter32,
	batteryMonitorCurrentAlarmEnable
		INTEGER,
	batteryMonitorCurrentValue
		Integer32,
	batteryMonitorCurrentMajorHighLevel
		Integer32,
	batteryMonitorCurrentMinorHighLevel
		Integer32,
	batteryMonitorCurrentMinorLowLevel
		Integer32,
	batteryMonitorCurrentMajorLowLevel
		Integer32
}

batteryMonitorCurrentIndex  OBJECT-TYPE
	SYNTAX     Integer32 (1..4)
	MAX-ACCESS not-accessible
	STATUS     current
	DESCRIPTION 
		"This index denotes which row in the current input table.
		The size of the table is defined by the batteryMonitorNumberOfCurrents"
	::= { batteryMonitorCurrentEntry 1 }

batteryMonitorCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery current monitor"
	::= { batteryMonitorCurrentEntry 2 }

batteryMonitorCurrentDescription  OBJECT-TYPE
	SYNTAX     DisplayString (SIZE(0..16))
	MAX-ACCESS read-write
	STATUS     current
	DESCRIPTION 
		"A textual description of the battery monitor current. This is stored in the system controller
		and can be changed by the user. "
	::= { batteryMonitorCurrentEntry 3 }

batteryMonitorCurrentTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off"
	::= { batteryMonitorCurrentEntry 4 }

batteryMonitorCurrentAlarmEnable  OBJECT-TYPE
	SYNTAX     INTEGER {
		disabled (0),
		enabled (1)
	}
	MAX-ACCESS read-write
	STATUS     current
	DESCRIPTION 
		"This value once enabled, the alarm condition of the monitor will be reported."
	::= { batteryMonitorCurrentEntry 5 }

batteryMonitorCurrentValue  OBJECT-TYPE
	SYNTAX     Integer32
	MAX-ACCESS read-only
	STATUS     current
	DESCRIPTION 
		"The measured battery current in battery monitor."
	::= { batteryMonitorCurrentEntry 6 }

batteryMonitorCurrentMajorHighLevel  OBJECT-TYPE
	SYNTAX     Integer32
	MAX-ACCESS read-write
	STATUS     current
	DESCRIPTION 
		"The major high alarm limit"
	::= { batteryMonitorCurrentEntry 7 }

batteryMonitorCurrentMinorHighLevel  OBJECT-TYPE
	SYNTAX     Integer32
	MAX-ACCESS read-write
	STATUS     current
	DESCRIPTION 
		"The minor high alarm limit"
	::= { batteryMonitorCurrentEntry 8 }

batteryMonitorCurrentMinorLowLevel  OBJECT-TYPE
	SYNTAX     Integer32
	MAX-ACCESS read-write
	STATUS     current
	DESCRIPTION 
		"The minor low alarm limit"
	::= { batteryMonitorCurrentEntry 9 }

batteryMonitorCurrentMajorLowLevel  OBJECT-TYPE
	SYNTAX     Integer32
	MAX-ACCESS read-write
	STATUS     current
	DESCRIPTION 
		"The major low alarm limit"
	::= { batteryMonitorCurrentEntry 10 }

batteryMonitorFuseTable  OBJECT-TYPE
	SYNTAX SEQUENCE OF BatteryMonitorFuseEntry
	MAX-ACCESS not-accessible
	STATUS     current
	DESCRIPTION 
		""
	::= { batteryMonitors 5 }

batteryMonitorFuseEntry  OBJECT-TYPE
	SYNTAX 	BatteryMonitorFuseEntry
	MAX-ACCESS not-accessible
	STATUS     current
	DESCRIPTION 
		""
	INDEX { batteryMonitorIndex, 
		batteryMonitorFuseIndex }
	::= { batteryMonitorFuseTable 1 }

BatteryMonitorFuseEntry ::= SEQUENCE {
	batteryMonitorFuseIndex
		Integer32,
	batteryMonitorFuseStatus
		INTEGER,
	batteryMonitorFuseDescription
		DisplayString,
	batteryMonitorFuseTrapRepeatCounter
		Counter32,
	batteryMonitorFuseAlarmEnable
		INTEGER,
	batteryMonitorFuseValue
		Integer32
}

batteryMonitorFuseIndex  OBJECT-TYPE
	SYNTAX     Integer32 (1..4)
	MAX-ACCESS not-accessible
	STATUS     current
	DESCRIPTION 
		"This index denotes which row in the fuse table.
		The size of the table is defined by the batteryMonitorNumberOfFuses"
	::= { batteryMonitorFuseEntry 1 }

batteryMonitorFuseStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery fuse monitor"
	::= { batteryMonitorFuseEntry 2 }

batteryMonitorFuseDescription  OBJECT-TYPE
	SYNTAX     DisplayString (SIZE(0..16))
	MAX-ACCESS read-write
	STATUS     current
	DESCRIPTION 
		"A textual description of the battery monitor fuse. This is stored in the system controller
		and can be changed by the user. "
	::= { batteryMonitorFuseEntry 3 }

batteryMonitorFuseTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off"
	::= { batteryMonitorFuseEntry 4 }

batteryMonitorFuseAlarmEnable  OBJECT-TYPE
	SYNTAX     INTEGER {
		disabled (0),
		enabled (1)
	}
	MAX-ACCESS read-write
	STATUS     current
	DESCRIPTION 
		"This value once enabled, the alarm condition of the monitor will be reported."
	::= { batteryMonitorFuseEntry 5 }

batteryMonitorFuseValue  OBJECT-TYPE
	SYNTAX     Integer32
	MAX-ACCESS read-only
	STATUS     current
	DESCRIPTION 
		"The measured value of battery fuse in battery monitor."
	::= { batteryMonitorFuseEntry 6 }

batteryMonitorSymmetryTable  OBJECT-TYPE
	SYNTAX SEQUENCE OF BatteryMonitorSymmetryEntry
	MAX-ACCESS not-accessible
	STATUS     current
	DESCRIPTION 
		""
	::= { batteryMonitors 6 }

batteryMonitorSymmetryEntry  OBJECT-TYPE
	SYNTAX 	BatteryMonitorSymmetryEntry
	MAX-ACCESS not-accessible
	STATUS     current
	DESCRIPTION 
		""
	INDEX { batteryMonitorIndex, 
		batteryMonitorSymmetryIndex }
	::= { batteryMonitorSymmetryTable 1 }

BatteryMonitorSymmetryEntry ::= SEQUENCE {
	batteryMonitorSymmetryIndex
		Integer32,
	batteryMonitorSymmetryStatus
		INTEGER,
	batteryMonitorSymmetryDescription
		DisplayString,
	batteryMonitorSymmetryTrapRepeatCounter
		Counter32,
	batteryMonitorSymmetryAlarmEnable
		INTEGER,
	batteryMonitorSymmetryMeasureValue
		Integer32,
	batteryMonitorSymmetryDeltaValue
		Integer32,
	batteryMonitorSymmetryMajorAlarmLevel
		Integer32,
	batteryMonitorSymmetryMinorAlarmLevel
		Integer32
}

batteryMonitorSymmetryIndex  OBJECT-TYPE
	SYNTAX     Integer32 (1..8)
	MAX-ACCESS not-accessible
	STATUS     current
	DESCRIPTION 
		"This index denotes which row in the symmetry input table.
		The size of the table is defined by the batteryMonitorNumberOfSymmetries"
	::= { batteryMonitorSymmetryEntry 1 }

batteryMonitorSymmetryStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery symmetry monitor"
	::= { batteryMonitorSymmetryEntry 2 }

batteryMonitorSymmetryDescription  OBJECT-TYPE
	SYNTAX     DisplayString (SIZE(0..16))
	MAX-ACCESS read-write
	STATUS     current
	DESCRIPTION 
		"A textual description of the battery monitor symmetry. This is stored in the system controller
		and can be changed by the user. "
	::= { batteryMonitorSymmetryEntry 3 }

batteryMonitorSymmetryTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off"
	::= { batteryMonitorSymmetryEntry 4 }

batteryMonitorSymmetryAlarmEnable  OBJECT-TYPE
	SYNTAX     INTEGER {
		disabled (0),
		enabled (1)
	}
	MAX-ACCESS read-write
	STATUS     current
	DESCRIPTION 
		"This value once enabled, the alarm condition of the monitor will be reported."
	::= { batteryMonitorSymmetryEntry 5 }

batteryMonitorSymmetryMeasureValue  OBJECT-TYPE
	SYNTAX     Integer32
	MAX-ACCESS read-only
	STATUS     current
	DESCRIPTION 
		"The measured battery symmetry voltage in battery monitor."
	::= { batteryMonitorSymmetryEntry 6 }

batteryMonitorSymmetryDeltaValue  OBJECT-TYPE
	SYNTAX     Integer32
	MAX-ACCESS read-only
	STATUS     current
	DESCRIPTION 
		"The measured battery symmetry delta voltage in battery monitor."
	::= { batteryMonitorSymmetryEntry 7 }

batteryMonitorSymmetryMajorAlarmLevel  OBJECT-TYPE
	SYNTAX     Integer32
	MAX-ACCESS read-write
	STATUS     current
	DESCRIPTION 
		"The major alarm limit"
	::= { batteryMonitorSymmetryEntry 8 }

batteryMonitorSymmetryMinorAlarmLevel  OBJECT-TYPE
	SYNTAX     Integer32
	MAX-ACCESS read-write
	STATUS     current
	DESCRIPTION 
		"The minor alarm limit"
	::= { batteryMonitorSymmetryEntry 9 }

batteryEnergyLogAccumulated  OBJECT-TYPE
	SYNTAX     Integer32
	MAX-ACCESS read-only
	STATUS     current
	DESCRIPTION 
		"This is the accumulated energy delivered to/from battery."
	::= { batteryEnergyLog 1 }

batteryEnergyLogLastHoursNumberOfEntries  OBJECT-TYPE
	SYNTAX     Integer32 (0..52)
	MAX-ACCESS read-only
	STATUS     current
	DESCRIPTION 
		"This is the maximal number of entries stored in battery hourly energy log."
	::= { batteryEnergyLog 2 }

batteryEnergyLogLastHoursTable  OBJECT-TYPE
	SYNTAX SEQUENCE OF BatteryEnergyLogLastHoursEntry
	MAX-ACCESS not-accessible
	STATUS     current
	DESCRIPTION 
		"This table contains hourly energy log of battery."
	::= { batteryEnergyLog 3 }

batteryEnergyLogLastHoursEntry  OBJECT-TYPE
	SYNTAX 	BatteryEnergyLogLastHoursEntry
	MAX-ACCESS not-accessible
	STATUS     current
	DESCRIPTION 
		""
	INDEX { batteryEnergyLogLastHoursIndex }
	::= { batteryEnergyLogLastHoursTable 1 }

BatteryEnergyLogLastHoursEntry ::= SEQUENCE {
	batteryEnergyLogLastHoursIndex
		Integer32,
	batteryEnergyLogLastHoursValue
		Integer32
}

batteryEnergyLogLastHoursIndex  OBJECT-TYPE
	SYNTAX     Integer32 (1..52)
	MAX-ACCESS not-accessible
	STATUS     current
	DESCRIPTION 
		"Index used for navigating the rows 1..52  of batteryEnergyLogLastHoursTable"
	::= { batteryEnergyLogLastHoursEntry 1 }

batteryEnergyLogLastHoursValue  OBJECT-TYPE
	SYNTAX     Integer32
	MAX-ACCESS read-only
	STATUS     current
	DESCRIPTION 
		"Energy value logged every hour."
	::= { batteryEnergyLogLastHoursEntry 2 }

batteryEnergyLogLastDaysNumberOfEntries  OBJECT-TYPE
	SYNTAX     Integer32 (0..52)
	MAX-ACCESS read-only
	STATUS     current
	DESCRIPTION 
		"This is the maximal number of entries stored in battery daily energy log."
	::= { batteryEnergyLog 4 }

batteryEnergyLogLastDaysTable  OBJECT-TYPE
	SYNTAX SEQUENCE OF BatteryEnergyLogLastDaysEntry
	MAX-ACCESS not-accessible
	STATUS     current
	DESCRIPTION 
		"This table contains daily energy log of battery."
	::= { batteryEnergyLog 5 }

batteryEnergyLogLastDaysEntry  OBJECT-TYPE
	SYNTAX 	BatteryEnergyLogLastDaysEntry
	MAX-ACCESS not-accessible
	STATUS     current
	DESCRIPTION 
		""
	INDEX { batteryEnergyLogLastDaysIndex }
	::= { batteryEnergyLogLastDaysTable 1 }

BatteryEnergyLogLastDaysEntry ::= SEQUENCE {
	batteryEnergyLogLastDaysIndex
		Integer32,
	batteryEnergyLogLastDaysValue
		Integer32
}

batteryEnergyLogLastDaysIndex  OBJECT-TYPE
	SYNTAX     Integer32 (1..52)
	MAX-ACCESS not-accessible
	STATUS     current
	DESCRIPTION 
		"Index used for navigating the rows 1..52  of batteryEnergyLogLastDaysTable"
	::= { batteryEnergyLogLastDaysEntry 1 }

batteryEnergyLogLastDaysValue  OBJECT-TYPE
	SYNTAX     Integer32
	MAX-ACCESS read-only
	STATUS     current
	DESCRIPTION 
		"Energy value logged every day."
	::= { batteryEnergyLogLastDaysEntry 2 }

batteryEnergyLogLastWeeksNumberOfEntries  OBJECT-TYPE
	SYNTAX     Integer32 (0..52)
	MAX-ACCESS read-only
	STATUS     current
	DESCRIPTION 
		"This is the maximal number of entries stored in battery weekly energy log."
	::= { batteryEnergyLog 6 }

batteryEnergyLogLastWeeksTable  OBJECT-TYPE
	SYNTAX SEQUENCE OF BatteryEnergyLogLastWeeksEntry
	MAX-ACCESS not-accessible
	STATUS     current
	DESCRIPTION 
		"This table contains weekly energy log of battery."
	::= { batteryEnergyLog 7 }

batteryEnergyLogLastWeeksEntry  OBJECT-TYPE
	SYNTAX 	BatteryEnergyLogLastWeeksEntry
	MAX-ACCESS not-accessible
	STATUS     current
	DESCRIPTION 
		""
	INDEX { batteryEnergyLogLastWeeksIndex }
	::= { batteryEnergyLogLastWeeksTable 1 }

BatteryEnergyLogLastWeeksEntry ::= SEQUENCE {
	batteryEnergyLogLastWeeksIndex
		Integer32,
	batteryEnergyLogLastWeeksValue
		Integer32
}

batteryEnergyLogLastWeeksIndex  OBJECT-TYPE
	SYNTAX     Integer32 (1..52)
	MAX-ACCESS not-accessible
	STATUS     current
	DESCRIPTION 
		"Index used for navigating the rows 1..52  of batteryEnergyLogLastWeekTable"
	::= { batteryEnergyLogLastWeeksEntry 1 }

batteryEnergyLogLastWeeksValue  OBJECT-TYPE
	SYNTAX     Integer32
	MAX-ACCESS read-only
	STATUS     current
	DESCRIPTION 
		"Energy value logged every week."
	::= { batteryEnergyLogLastWeeksEntry 2 }

batteryCycleLogTotalCycles  OBJECT-TYPE
	SYNTAX     Integer32
	MAX-ACCESS read-only
	STATUS     current
	DESCRIPTION 
		"This is the total number of battery discharge cycles."
	::= { batteryCycleLog 1 }

batteryCycleLogDaysNumberOfEntries  OBJECT-TYPE
	SYNTAX     Integer32 (0..52)
	MAX-ACCESS read-only
	STATUS     current
	DESCRIPTION 
		"This is the maximal number of entries stored in daily battery discharge cycle log."
	::= { batteryCycleLog 2 }

batteryCycleLogDaysTable  OBJECT-TYPE
	SYNTAX SEQUENCE OF BatteryCycleLogDaysEntry
	MAX-ACCESS not-accessible
	STATUS     current
	DESCRIPTION 
		"This table contains daily battery discharge cycle log."
	::= { batteryCycleLog 3 }

batteryCycleLogDaysEntry  OBJECT-TYPE
	SYNTAX 	BatteryCycleLogDaysEntry
	MAX-ACCESS not-accessible
	STATUS     current
	DESCRIPTION 
		""
	INDEX { batteryCycleLogDaysIndex }
	::= { batteryCycleLogDaysTable 1 }

BatteryCycleLogDaysEntry ::= SEQUENCE {
	batteryCycleLogDaysIndex
		Integer32,
	batteryCycleLogDaysValue
		Integer32
}

batteryCycleLogDaysIndex  OBJECT-TYPE
	SYNTAX     Integer32 (1..52)
	MAX-ACCESS not-accessible
	STATUS     current
	DESCRIPTION 
		"Index used for navigating the rows 1..52  of batteryCycleLogLastDaysTable"
	::= { batteryCycleLogDaysEntry 1 }

batteryCycleLogDaysValue  OBJECT-TYPE
	SYNTAX     Integer32
	MAX-ACCESS read-only
	STATUS     current
	DESCRIPTION 
		"Number of discharge cycles logged every day."
	::= { batteryCycleLogDaysEntry 2 }

batteryCycleLogWeeksNumberOfEntries  OBJECT-TYPE
	SYNTAX     Integer32 (0..52)
	MAX-ACCESS read-only
	STATUS     current
	DESCRIPTION 
		"This is the maximal number of entries stored in weeky battery discharge cycle log."
	::= { batteryCycleLog 4 }

batteryCycleLogWeeksTable  OBJECT-TYPE
	SYNTAX SEQUENCE OF BatteryCycleLogWeeksEntry
	MAX-ACCESS not-accessible
	STATUS     current
	DESCRIPTION 
		"This table contains weekly battery discharge cycle log."
	::= { batteryCycleLog 5 }

batteryCycleLogWeeksEntry  OBJECT-TYPE
	SYNTAX 	BatteryCycleLogWeeksEntry
	MAX-ACCESS not-accessible
	STATUS     current
	DESCRIPTION 
		""
	INDEX { batteryCycleLogWeeksIndex }
	::= { batteryCycleLogWeeksTable 1 }

BatteryCycleLogWeeksEntry ::= SEQUENCE {
	batteryCycleLogWeeksIndex
		Integer32,
	batteryCycleLogWeeksValue
		Integer32
}

batteryCycleLogWeeksIndex  OBJECT-TYPE
	SYNTAX     Integer32 (1..52)
	MAX-ACCESS not-accessible
	STATUS     current
	DESCRIPTION 
		"Index used for navigating the rows 1..52  of batteryCycleLogLastWeeksTable"
	::= { batteryCycleLogWeeksEntry 1 }

batteryCycleLogWeeksValue  OBJECT-TYPE
	SYNTAX     Integer32
	MAX-ACCESS read-only
	STATUS     current
	DESCRIPTION 
		"Number of discharge cycles logged every week."
	::= { batteryCycleLogWeeksEntry 2 }

batteryCycleLogMonthsNumberOfEntries  OBJECT-TYPE
	SYNTAX     Integer32 (0..52)
	MAX-ACCESS read-only
	STATUS     current
	DESCRIPTION 
		"This is the maximal number of entries stored in monthly battery discharge cycle log."
	::= { batteryCycleLog 6 }

batteryCycleLogMonthsTable  OBJECT-TYPE
	SYNTAX SEQUENCE OF BatteryCycleLogMonthsEntry
	MAX-ACCESS not-accessible
	STATUS     current
	DESCRIPTION 
		"This table contains monthly battery discharge cycle log."
	::= { batteryCycleLog 7 }

batteryCycleLogMonthsEntry  OBJECT-TYPE
	SYNTAX 	BatteryCycleLogMonthsEntry
	MAX-ACCESS not-accessible
	STATUS     current
	DESCRIPTION 
		""
	INDEX { batteryCycleLogMonthsIndex }
	::= { batteryCycleLogMonthsTable 1 }

BatteryCycleLogMonthsEntry ::= SEQUENCE {
	batteryCycleLogMonthsIndex
		Integer32,
	batteryCycleLogMonthsValue
		Integer32
}

batteryCycleLogMonthsIndex  OBJECT-TYPE
	SYNTAX     Integer32 (1..52)
	MAX-ACCESS not-accessible
	STATUS     current
	DESCRIPTION 
		"Index used for navigating the rows 1..52  of batteryCycleLogLastMonthTable"
	::= { batteryCycleLogMonthsEntry 1 }

batteryCycleLogMonthsValue  OBJECT-TYPE
	SYNTAX     Integer32
	MAX-ACCESS read-only
	STATUS     current
	DESCRIPTION 
		"Number of discharge cycles logged every month."
	::= { batteryCycleLogMonthsEntry 2 }

batteryEqualizeVoltage  OBJECT-TYPE
	SYNTAX     Integer32 (870..60418)
	MAX-ACCESS read-write
	STATUS     current
	DESCRIPTION 
		"The Voltage at which the DC System equalize charges the batteries."
	::= { batteryEqualize 1 }

batteryEqualizeCommand  OBJECT-TYPE
	SYNTAX     INTEGER {
		pushbutton (0),
		startequalize (1),
		stopequalize (2)
	}
	MAX-ACCESS read-write
	STATUS     current
	DESCRIPTION 
		"This pushbutton will start or stop a manual battery equalize if the system allows it."
	::= { batteryEqualize 2 }

batteryEqualizeCurrentThreshold  OBJECT-TYPE
	SYNTAX     Integer32
	MAX-ACCESS read-write
	STATUS     current
	DESCRIPTION 
		"The equalizing will terminate when the charge current drops below the EqualizeCurrentThreshold limit."
	::= { batteryEqualize 3 }

batteryEqualizeManualMaxDuration  OBJECT-TYPE
	SYNTAX     Integer32 (0..1440)
	MAX-ACCESS read-write
	STATUS     current
	DESCRIPTION 
		"A protection against overcharging.  
		When running manual equalize, the boosting will always terminate at this point.  "
	::= { batteryEqualize 4 }

batteryAhChargedStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the battery ah charged monitor."
	::= { batteryAhCharged 1 }

batteryAhChargedDescription  OBJECT-TYPE
	SYNTAX     DisplayString (SIZE(0..16))
	MAX-ACCESS read-write
	STATUS     current
	DESCRIPTION 
		"A textual description of the battery ah charged monitor. This is stored in the system controller
		and can be changed by the user"
	::= { batteryAhCharged 2 }

batteryAhChargedTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { batteryAhCharged 3 }

batteryAhChargedAlarmEnable  OBJECT-TYPE
	SYNTAX     INTEGER {
		disabled (0),
		enabled (1)
	}
	MAX-ACCESS read-write
	STATUS     current
	DESCRIPTION 
		"This value once enabled, the alarm condition of the monitor will be reported."
	::= { batteryAhCharged 4 }

batteryAhChargedValue  OBJECT-TYPE
	SYNTAX     Integer32
	MAX-ACCESS read-only
	STATUS     current
	DESCRIPTION 
		"The calculated battery ah (x100) charged value."
	::= { batteryAhCharged 5 }

batteryAhChargedMinorHighLevel  OBJECT-TYPE
	SYNTAX     Integer32
	MAX-ACCESS read-write
	STATUS     current
	DESCRIPTION 
		"The minor high alarm limit"
	::= { batteryAhCharged 6 }

batteryAhChargedMajorHighLevel  OBJECT-TYPE
	SYNTAX     Integer32
	MAX-ACCESS read-write
	STATUS     current
	DESCRIPTION 
		"The major high alarm limit"
	::= { batteryAhCharged 7 }

batteryAhDischargedStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the battery ah discharged monitor."
	::= { batteryAhDischarged 1 }

batteryAhDischargedDescription  OBJECT-TYPE
	SYNTAX     DisplayString (SIZE(0..16))
	MAX-ACCESS read-write
	STATUS     current
	DESCRIPTION 
		"A textual description of the battery ah discharged monitor. This is stored in the system controller
		and can be changed by the user"
	::= { batteryAhDischarged 2 }

batteryAhDischargedTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { batteryAhDischarged 3 }

batteryAhDischargedAlarmEnable  OBJECT-TYPE
	SYNTAX     INTEGER {
		disabled (0),
		enabled (1)
	}
	MAX-ACCESS read-write
	STATUS     current
	DESCRIPTION 
		"This value once enabled, the alarm condition of the monitor will be reported."
	::= { batteryAhDischarged 4 }

batteryAhDischargedValue  OBJECT-TYPE
	SYNTAX     Integer32
	MAX-ACCESS read-only
	STATUS     current
	DESCRIPTION 
		"The calculated battery ah (x100) discharged value."
	::= { batteryAhDischarged 5 }

batteryAhDischargedMinorHighLevel  OBJECT-TYPE
	SYNTAX     Integer32
	MAX-ACCESS read-write
	STATUS     current
	DESCRIPTION 
		"The minor high alarm limit"
	::= { batteryAhDischarged 6 }

batteryAhDischargedMajorHighLevel  OBJECT-TYPE
	SYNTAX     Integer32
	MAX-ACCESS read-write
	STATUS     current
	DESCRIPTION 
		"The major high alarm limit"
	::= { batteryAhDischarged 7 }

batteryRunTimeAccumulated  OBJECT-TYPE
	SYNTAX     Unsigned32
	MAX-ACCESS read-only
	STATUS     current
	DESCRIPTION 
		"This is the accumulated running time of battery in hours."
	::= { batteryRunTimeLog 1 }

batteryRunTimeLogDaysNumberOfEntries  OBJECT-TYPE
	SYNTAX     Integer32 (0..52)
	MAX-ACCESS read-only
	STATUS     current
	DESCRIPTION 
		"This is the maximal number of entries stored in daily battery run time log."
	::= { batteryRunTimeLog 2 }

batteryRunTimeLogDaysTable  OBJECT-TYPE
	SYNTAX SEQUENCE OF BatteryRunTimeLogDaysEntry
	MAX-ACCESS not-accessible
	STATUS     current
	DESCRIPTION 
		"This table contains daily battery run time log."
	::= { batteryRunTimeLog 3 }

batteryRunTimeLogDaysEntry  OBJECT-TYPE
	SYNTAX 	BatteryRunTimeLogDaysEntry
	MAX-ACCESS not-accessible
	STATUS     current
	DESCRIPTION 
		""
	INDEX { batteryRunTimeLogDaysIndex }
	::= { batteryRunTimeLogDaysTable 1 }

BatteryRunTimeLogDaysEntry ::= SEQUENCE {
	batteryRunTimeLogDaysIndex
		Integer32,
	batteryRunTimeLogDaysValue
		Integer32
}

batteryRunTimeLogDaysIndex  OBJECT-TYPE
	SYNTAX     Integer32 (1..52)
	MAX-ACCESS not-accessible
	STATUS     current
	DESCRIPTION 
		"Index used for navigating the rows 1..52  of batteryRunTimeLogDaysTable"
	::= { batteryRunTimeLogDaysEntry 1 }

batteryRunTimeLogDaysValue  OBJECT-TYPE
	SYNTAX     Integer32
	MAX-ACCESS read-only
	STATUS     current
	DESCRIPTION 
		"Battery running minutes logged every day."
	::= { batteryRunTimeLogDaysEntry 2 }

batteryRunTimeLogWeeksNumberOfEntries  OBJECT-TYPE
	SYNTAX     Integer32 (0..52)
	MAX-ACCESS read-only
	STATUS     current
	DESCRIPTION 
		"This is the maximal number of entries stored in weeky battery run time log."
	::= { batteryRunTimeLog 4 }

batteryRunTimeLogWeeksTable  OBJECT-TYPE
	SYNTAX SEQUENCE OF BatteryRunTimeLogWeeksEntry
	MAX-ACCESS not-accessible
	STATUS     current
	DESCRIPTION 
		"This table contains weekly battery run time log."
	::= { batteryRunTimeLog 5 }

batteryRunTimeLogWeeksEntry  OBJECT-TYPE
	SYNTAX 	BatteryRunTimeLogWeeksEntry
	MAX-ACCESS not-accessible
	STATUS     current
	DESCRIPTION 
		""
	INDEX { batteryRunTimeLogWeeksIndex }
	::= { batteryRunTimeLogWeeksTable 1 }

BatteryRunTimeLogWeeksEntry ::= SEQUENCE {
	batteryRunTimeLogWeeksIndex
		Integer32,
	batteryRunTimeLogWeeksValue
		Integer32
}

batteryRunTimeLogWeeksIndex  OBJECT-TYPE
	SYNTAX     Integer32 (1..52)
	MAX-ACCESS not-accessible
	STATUS     current
	DESCRIPTION 
		"Index used for navigating the rows 1..52  of batteryRunTimeLogWeeksTable"
	::= { batteryRunTimeLogWeeksEntry 1 }

batteryRunTimeLogWeeksValue  OBJECT-TYPE
	SYNTAX     Integer32
	MAX-ACCESS read-only
	STATUS     current
	DESCRIPTION 
		"Battery running hours logged every week."
	::= { batteryRunTimeLogWeeksEntry 2 }

batteryRunTimeLogMonthsNumberOfEntries  OBJECT-TYPE
	SYNTAX     Integer32 (0..52)
	MAX-ACCESS read-only
	STATUS     current
	DESCRIPTION 
		"This is the maximal number of entries stored in monthly battery run time log."
	::= { batteryRunTimeLog 6 }

batteryRunTimeLogMonthsTable  OBJECT-TYPE
	SYNTAX SEQUENCE OF BatteryRunTimeLogMonthsEntry
	MAX-ACCESS not-accessible
	STATUS     current
	DESCRIPTION 
		"This table contains monthly battery run time log."
	::= { batteryRunTimeLog 7 }

batteryRunTimeLogMonthsEntry  OBJECT-TYPE
	SYNTAX 	BatteryRunTimeLogMonthsEntry
	MAX-ACCESS not-accessible
	STATUS     current
	DESCRIPTION 
		""
	INDEX { batteryRunTimeLogMonthsIndex }
	::= { batteryRunTimeLogMonthsTable 1 }

BatteryRunTimeLogMonthsEntry ::= SEQUENCE {
	batteryRunTimeLogMonthsIndex
		Integer32,
	batteryRunTimeLogMonthsValue
		Integer32
}

batteryRunTimeLogMonthsIndex  OBJECT-TYPE
	SYNTAX     Integer32 (1..52)
	MAX-ACCESS not-accessible
	STATUS     current
	DESCRIPTION 
		"Index used for navigating the rows 1..52  of batteryRunTimeLogMonthsTable"
	::= { batteryRunTimeLogMonthsEntry 1 }

batteryRunTimeLogMonthsValue  OBJECT-TYPE
	SYNTAX     Integer32
	MAX-ACCESS read-only
	STATUS     current
	DESCRIPTION 
		"Battery running hours logged every month."
	::= { batteryRunTimeLogMonthsEntry 2 }

batteryModuleNoOfBatteryModules  OBJECT-TYPE
	SYNTAX     Integer32 (0..100)
	MAX-ACCESS read-only
	STATUS     current
	DESCRIPTION 
		"The number of battery modules installed"
	::= { batteryModule 1 }

batteryModuleErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed units is higher than the defined alarm level."
	::= { batteryModuleError 1 }

batteryModuleErrorDescription  OBJECT-TYPE
	SYNTAX     DisplayString (SIZE(0..16))
	MAX-ACCESS read-write
	STATUS     current
	DESCRIPTION 
		"A textual description of the battery error monitor. This is stored in the system controller
		and can be changed by the user"
	::= { batteryModuleError 2 }

batteryModuleErrorTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { batteryModuleError 3 }

batteryModuleErrorEnable  OBJECT-TYPE
	SYNTAX     INTEGER {
		disabled (0),
		enabled (1)
	}
	MAX-ACCESS read-write
	STATUS     current
	DESCRIPTION 
		"This value once enabled, the alarm condition of the monitor will be reported."
	::= { batteryModuleError 4 }

batteryModuleErrorValue  OBJECT-TYPE
	SYNTAX     Integer32
	MAX-ACCESS read-only
	STATUS     current
	DESCRIPTION 
		"The number of failed batteries."
	::= { batteryModuleError 5 }

batteryModuleErrorMajorAlarmLevel  OBJECT-TYPE
	SYNTAX     Integer32
	MAX-ACCESS read-write
	STATUS     current
	DESCRIPTION 
		"The major alarm limit"
	::= { batteryModuleError 6 }

batteryModuleErrorMinorAlarmLevel  OBJECT-TYPE
	SYNTAX     Integer32
	MAX-ACCESS read-write
	STATUS     current
	DESCRIPTION 
		"The minor alarm limit"
	::= { batteryModuleError 7 }

batteryModuleCommErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed units is higher than the defined alarm level."
	::= { batteryModuleCommError 1 }

batteryModuleCommErrorDescription  OBJECT-TYPE
	SYNTAX     DisplayString (SIZE(0..16))
	MAX-ACCESS read-write
	STATUS     current
	DESCRIPTION 
		"A textual description of the battery comm error monitor. This is stored in the system controller
		and can be changed by the user"
	::= { batteryModuleCommError 2 }

batteryModuleCommErrorTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { batteryModuleCommError 3 }

batteryModuleCommErrorEnable  OBJECT-TYPE
	SYNTAX     INTEGER {
		disabled (0),
		enabled (1)
	}
	MAX-ACCESS read-write
	STATUS     current
	DESCRIPTION 
		"This value once enabled, the alarm condition of the monitor will be reported."
	::= { batteryModuleCommError 4 }

batteryModuleCommErrorValue  OBJECT-TYPE
	SYNTAX     Integer32
	MAX-ACCESS read-only
	STATUS     current
	DESCRIPTION 
		"The number of batteries in comm error."
	::= { batteryModuleCommError 5 }

batteryModuleCommErrorMajorAlarmLevel  OBJECT-TYPE
	SYNTAX     Integer32
	MAX-ACCESS read-write
	STATUS     current
	DESCRIPTION 
		"The major alarm limit"
	::= { batteryModuleCommError 6 }

batteryModuleCommErrorMinorAlarmLevel  OBJECT-TYPE
	SYNTAX     Integer32
	MAX-ACCESS read-write
	STATUS     current
	DESCRIPTION 
		"The minor alarm limit"
	::= { batteryModuleCommError 7 }

batteryModuleTable  OBJECT-TYPE
	SYNTAX SEQUENCE OF BatteryModuleEntry
	MAX-ACCESS not-accessible
	STATUS     current
	DESCRIPTION 
		"Information of individule battery module"
	::= { batteryModule 4 }

batteryModuleEntry  OBJECT-TYPE
	SYNTAX 	BatteryModuleEntry
	MAX-ACCESS not-accessible
	STATUS     current
	DESCRIPTION 
		""
	INDEX { batteryModuleIndex }
	::= { batteryModuleTable 1 }

BatteryModuleEntry ::= SEQUENCE {
	batteryModuleIndex
		Integer32,
	batteryModuleStatus
		INTEGER,
	batteryModuleBatteryVoltage
		Integer32,
	batteryModuleBatteryCurrent
		Integer32,
	batteryModuleBatteryRemCap
		Integer32,
	batteryModuleBatteryTemperature
		Integer32,
	batteryModuleBatteryQuality
		Integer32,
	batteryModuleMaxChargeCurrent
		Integer32,
	batteryModuleMaxDischargeCurrent
		Integer32,
	batteryModuleBatteryMode
		DisplayString,
	batteryModuleChargeMode
		DisplayString,
	batteryModuleManufacturer
		DisplayString,
	batteryModulePartNumber
		DisplayString,
	batteryModuleSerialNumber
		DisplayString,
	batteryModuleSoftwareVersion
		DisplayString,
	batteryModuleProductionDate
		DateAndTime,
	batteryModuleAccumulatedAhCharged
		Integer32,
	batteryModuleAccumulatedAhDischarged
		Integer32,
	batteryModuleNoOfChargeCycles
		Integer32,
	batteryModuleNoOfDischargeCycles
		Integer32
}

batteryModuleIndex  OBJECT-TYPE
	SYNTAX     Integer32 (1..100)
	MAX-ACCESS not-accessible
	STATUS     current
	DESCRIPTION 
		"Index used for navigating the rows 1..100  of batteryModuleTable "
	::= { batteryModuleEntry 1 }

batteryModuleStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		" The status value for the battery module"
	::= { batteryModuleEntry 2 }

batteryModuleBatteryVoltage  OBJECT-TYPE
	SYNTAX     Integer32
	MAX-ACCESS read-only
	STATUS     current
	DESCRIPTION 
		"Battery voltage value"
	::= { batteryModuleEntry 3 }

batteryModuleBatteryCurrent  OBJECT-TYPE
	SYNTAX     Integer32
	MAX-ACCESS read-only
	STATUS     current
	DESCRIPTION 
		"Battery current value"
	::= { batteryModuleEntry 4 }

batteryModuleBatteryRemCap  OBJECT-TYPE
	SYNTAX     Integer32
	MAX-ACCESS read-only
	STATUS     current
	DESCRIPTION 
		"Battery remaining capacity value"
	::= { batteryModuleEntry 5 }

batteryModuleBatteryTemperature  OBJECT-TYPE
	SYNTAX     Integer32
	MAX-ACCESS read-only
	STATUS     current
	DESCRIPTION 
		"Battery temperature value"
	::= { batteryModuleEntry 6 }

batteryModuleBatteryQuality  OBJECT-TYPE
	SYNTAX     Integer32
	MAX-ACCESS read-only
	STATUS     current
	DESCRIPTION 
		"Battery quality value "
	::= { batteryModuleEntry 7 }

batteryModuleMaxChargeCurrent  OBJECT-TYPE
	SYNTAX     Integer32
	MAX-ACCESS read-only
	STATUS     current
	DESCRIPTION 
		"Maximal charging current in Amp"
	::= { batteryModuleEntry 8 }

batteryModuleMaxDischargeCurrent  OBJECT-TYPE
	SYNTAX     Integer32
	MAX-ACCESS read-only
	STATUS     current
	DESCRIPTION 
		"Maximal discharge current in Amp"
	::= { batteryModuleEntry 9 }

batteryModuleBatteryMode  OBJECT-TYPE
	SYNTAX     DisplayString
	MAX-ACCESS read-only
	STATUS     current
	DESCRIPTION 
		"Battery mode"
	::= { batteryModuleEntry 10 }

batteryModuleChargeMode  OBJECT-TYPE
	SYNTAX     DisplayString
	MAX-ACCESS read-only
	STATUS     current
	DESCRIPTION 
		"Charge mode"
	::= { batteryModuleEntry 11 }

batteryModuleManufacturer  OBJECT-TYPE
	SYNTAX     DisplayString (SIZE(0..27))
	MAX-ACCESS read-only
	STATUS     current
	DESCRIPTION 
		"Battery manufaturer"
	::= { batteryModuleEntry 12 }

batteryModulePartNumber  OBJECT-TYPE
	SYNTAX     DisplayString (SIZE(0..16))
	MAX-ACCESS read-only
	STATUS     current
	DESCRIPTION 
		"Part number"
	::= { batteryModuleEntry 13 }

batteryModuleSerialNumber  OBJECT-TYPE
	SYNTAX     DisplayString (SIZE(0..16))
	MAX-ACCESS read-only
	STATUS     current
	DESCRIPTION 
		"Serial number"
	::= { batteryModuleEntry 14 }

batteryModuleSoftwareVersion  OBJECT-TYPE
	SYNTAX     DisplayString (SIZE(0..16))
	MAX-ACCESS read-only
	STATUS     current
	DESCRIPTION 
		"Software version"
	::= { batteryModuleEntry 15 }

batteryModuleProductionDate  OBJECT-TYPE
	SYNTAX     DateAndTime (SIZE(8..11))
	MAX-ACCESS read-only
	STATUS     current
	DESCRIPTION 
		"Date of production"
	::= { batteryModuleEntry 16 }

batteryModuleAccumulatedAhCharged  OBJECT-TYPE
	SYNTAX     Integer32
	MAX-ACCESS read-only
	STATUS     current
	DESCRIPTION 
		"Accumulated Ah charged"
	::= { batteryModuleEntry 17 }

batteryModuleAccumulatedAhDischarged  OBJECT-TYPE
	SYNTAX     Integer32
	MAX-ACCESS read-only
	STATUS     current
	DESCRIPTION 
		"Accumulated Ah discharged"
	::= { batteryModuleEntry 18 }

batteryModuleNoOfChargeCycles  OBJECT-TYPE
	SYNTAX     Integer32
	MAX-ACCESS read-only
	STATUS     current
	DESCRIPTION 
		"Number of charge cycles"
	::= { batteryModuleEntry 19 }

batteryModuleNoOfDischargeCycles  OBJECT-TYPE
	SYNTAX     Integer32
	MAX-ACCESS read-only
	STATUS     current
	DESCRIPTION 
		"Number of discharge cycles"
	::= { batteryModuleEntry 20 }

-- In smartpack2 system, highest inputControlUnitIndex corresponds to smartpack2 master controller

inputControlUnitsTable  OBJECT-TYPE
	SYNTAX SEQUENCE OF InputControlUnitsEntry
	MAX-ACCESS not-accessible
	STATUS     current
	DESCRIPTION 
		""
	::= { inputs 1 }

inputControlUnitsEntry  OBJECT-TYPE
	SYNTAX 	InputControlUnitsEntry
	MAX-ACCESS not-accessible
	STATUS     current
	DESCRIPTION 
		""
	INDEX { inputControlUnitIndex }
	::= { inputControlUnitsTable 1 }

InputControlUnitsEntry ::= SEQUENCE {
	inputControlUnitIndex
		Integer32,
	inputControlUnitNumberOfInputs
		Integer32
}

inputControlUnitIndex  OBJECT-TYPE
	SYNTAX     Integer32 (1..14)
	MAX-ACCESS not-accessible
	STATUS     current
	DESCRIPTION 
		"Index used for navigating the rows of inputControlUnitTable
		The size of the table is defined by the system  "
	::= { inputControlUnitsEntry 1 }

inputControlUnitNumberOfInputs  OBJECT-TYPE
	SYNTAX     Integer32 (0..8)
	MAX-ACCESS read-only
	STATUS     current
	DESCRIPTION 
		"Number of programmable inputs available in controller."
	::= { inputControlUnitsEntry 2 }

-- In smartpack2 system, highest inputControlUnitIndex corresponds to smartpack2 master controller

inputControlUnitInputTable  OBJECT-TYPE
	SYNTAX SEQUENCE OF InputControlUnitInputEntry
	MAX-ACCESS not-accessible
	STATUS     current
	DESCRIPTION 
		"This table contains the status of the programmable inputs for Control Units.
		"
	::= { inputs 2 }

inputControlUnitInputEntry  OBJECT-TYPE
	SYNTAX 	InputControlUnitInputEntry
	MAX-ACCESS not-accessible
	STATUS     current
	DESCRIPTION 
		""
	INDEX { inputControlUnitIndex, 
		inputControlUnitInputIndex }
	::= { inputControlUnitInputTable 1 }

InputControlUnitInputEntry ::= SEQUENCE {
	inputControlUnitInputIndex
		Integer32,
	inputControlUnitInputStatus
		INTEGER,
	inputControlUnitInputDescription
		DisplayString,
	inputControlUnitInputTrapRepeatCounter
		Counter32,
	inputControlUnitInputAlarmEnable
		INTEGER,
	inputControlUnitInputValue
		Integer32,
	inputControlUnitInputConfiguration
		INTEGER
}

inputControlUnitInputIndex  OBJECT-TYPE
	SYNTAX     Integer32 (1..10)
	MAX-ACCESS not-accessible
	STATUS     current
	DESCRIPTION 
		"Index used for navigating the rows  of inputControlUnitInputTable
		The size of the table is defined by the inputControlUnitNumberOfInputs   "
	::= { inputControlUnitInputEntry 1 }

inputControlUnitInputStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"Programmable input status.
		"
	::= { inputControlUnitInputEntry 2 }

inputControlUnitInputDescription  OBJECT-TYPE
	SYNTAX     DisplayString (SIZE(0..16))
	MAX-ACCESS read-write
	STATUS     current
	DESCRIPTION 
		"A textual description of the programmable input. This is stored in the system controller
		and can be changed by the user.  "
	::= { inputControlUnitInputEntry 3 }

inputControlUnitInputTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { inputControlUnitInputEntry 4 }

inputControlUnitInputAlarmEnable  OBJECT-TYPE
	SYNTAX     INTEGER {
		disabled (0),
		enabled (1)
	}
	MAX-ACCESS read-write
	STATUS     current
	DESCRIPTION 
		"This will enable or disable this inputs Alarm functionality.
		Setting 'disabled' here will turn off lock the status to 'disabled' state"
	::= { inputControlUnitInputEntry 5 }

inputControlUnitInputValue  OBJECT-TYPE
	SYNTAX     Integer32
	MAX-ACCESS read-write
	STATUS     current
	DESCRIPTION 
		"The inputs measured Value. Depending on the type of input, this may
		 represent a Voltage, a Temperature, a Current or a Boolean value.
		Note: This value can only be set for virtual input on SP2 master or Smartpack S. 
		When this value is set to '0', the input is deactivated; When this value is set to '1', 
		the input is activated; 
		if set to any other value, an Inconsistent Value error
		will be generated. "
	::= { inputControlUnitInputEntry 6 }

inputControlUnitInputConfiguration  OBJECT-TYPE
	SYNTAX     INTEGER {
		normallyOpen (1),
		normallyClosed (2),
		diodeMatrix (3),
		voltage (4),
		clock (5),
		virtual (6),
		temperature (7),
		temp4-20mA (8)
	}
	MAX-ACCESS read-write
	STATUS     current
	DESCRIPTION 
		"Configuration of the input type. Configurations available for different controllers are as follows:
		SP2 Basic(normally open, normally closed);
		SP2 BasicInd(normally open,normally closed, temperature, temp 4-20mA, voltage);
		Compack inputs 1-4(clock, virtual),inputs 5-7(normally open,normally closed, temperature, temp 4-20mA, voltage, clock); 
		SmartpackS inputs 1-4(clock, virtual), inputs 5-8(normally open,normally closed,voltage,temperature,temp 4-20mA), 
		inputs 9-10(normally open,normally closed,voltage); 
		Smartpack R inputs 1-6(normally open,normally closed,diode matrix,clock, voltage),inputs 7-10(clock, virtual). "
	::= { inputControlUnitInputEntry 7 }

inputIoUnitsTable  OBJECT-TYPE
	SYNTAX SEQUENCE OF InputIoUnitsEntry
	MAX-ACCESS not-accessible
	STATUS     current
	DESCRIPTION 
		""
	::= { inputs 3 }

inputIoUnitsEntry  OBJECT-TYPE
	SYNTAX 	InputIoUnitsEntry
	MAX-ACCESS not-accessible
	STATUS     current
	DESCRIPTION 
		""
	INDEX { inputIoUnitIndex }
	::= { inputIoUnitsTable 1 }

InputIoUnitsEntry ::= SEQUENCE {
	inputIoUnitIndex
		Integer32,
	inputIoUnitNumberOfInputs
		Integer32
}

inputIoUnitIndex  OBJECT-TYPE
	SYNTAX     Integer32 (1..14)
	MAX-ACCESS not-accessible
	STATUS     current
	DESCRIPTION 
		"Index used for navigating the rows of inputIoUnitsTable
		The size of the table is defined by the system  "
	::= { inputIoUnitsEntry 1 }

inputIoUnitNumberOfInputs  OBJECT-TYPE
	SYNTAX     Integer32 (0..8)
	MAX-ACCESS read-only
	STATUS     current
	DESCRIPTION 
		"Number of programmable inputs available in IO unit."
	::= { inputIoUnitsEntry 2 }

inputIoUnitProgInputTable  OBJECT-TYPE
	SYNTAX SEQUENCE OF InputIoUnitProgInputEntry
	MAX-ACCESS not-accessible
	STATUS     current
	DESCRIPTION 
		"This table contains the status of the programmable inputs for I/O monitor units.
		. "
	::= { inputs 4 }

-- This branch contains OIDs related to the systems generic input subsystem. 
-- Here you will find info about the programmable inputs found in system controllers, 
-- I/O monitors and AC Mains Monitor units.
-- 

inputIoUnitProgInputEntry  OBJECT-TYPE
	SYNTAX 	InputIoUnitProgInputEntry
	MAX-ACCESS not-accessible
	STATUS     current
	DESCRIPTION 
		""
	INDEX { inputIoUnitIndex, 
		inputIoUnitProgInputIndex }
	::= { inputIoUnitProgInputTable 1 }

InputIoUnitProgInputEntry ::= SEQUENCE {
	inputIoUnitProgInputIndex
		Integer32,
	inputIoUnitProgInputStatus
		INTEGER,
	inputIoUnitProgInputDescription
		DisplayString,
	inputIoUnitProgInputTrapRepeatCounter
		Counter32,
	inputIoUnitProgInputAlarmEnable
		INTEGER,
	inputIoUnitProgInputValue
		Integer32,
	inputIoUnitProgInputConfiguration
		INTEGER
}

inputIoUnitProgInputIndex  OBJECT-TYPE
	SYNTAX     Integer32 (1..6)
	MAX-ACCESS not-accessible
	STATUS     current
	DESCRIPTION 
		"The Index to the Input of the selected I/O monitor unit.
		Or the input number if you like."
	::= { inputIoUnitProgInputEntry 1 }

inputIoUnitProgInputStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"Programmable input status.
		"
	::= { inputIoUnitProgInputEntry 2 }

inputIoUnitProgInputDescription  OBJECT-TYPE
	SYNTAX     DisplayString (SIZE(0..16))
	MAX-ACCESS read-write
	STATUS     current
	DESCRIPTION 
		"A textual description of the programmable input in IO unit. This is stored in the system controller
		and can be changed by the user."
	::= { inputIoUnitProgInputEntry 3 }

inputIoUnitProgInputTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { inputIoUnitProgInputEntry 4 }

inputIoUnitProgInputAlarmEnable  OBJECT-TYPE
	SYNTAX     INTEGER {
		disabled (0),
		enabled (1)
	}
	MAX-ACCESS read-write
	STATUS     current
	DESCRIPTION 
		"This will enable or disable this inputs Alarm functionality.
		Setting 'disabled' here will turn off lock the status to 'disabled' state"
	::= { inputIoUnitProgInputEntry 5 }

inputIoUnitProgInputValue  OBJECT-TYPE
	SYNTAX     Integer32
	MAX-ACCESS read-only
	STATUS     current
	DESCRIPTION 
		"The inputs measured Value. Depending on the type of input, this may
		represent a Voltage, a Temperature, a Current or a Boolean value."
	::= { inputIoUnitProgInputEntry 6 }

inputIoUnitProgInputConfiguration  OBJECT-TYPE
	SYNTAX     INTEGER {
		normallyOpen (1),
		normallyClosed (2),
		diodeMatrix (3),
		voltage (4),
		clock (5)
	}
	MAX-ACCESS read-write
	STATUS     current
	DESCRIPTION 
		"Configuration of the input type. Configurations available for IO unit are normally open,
		normally closed, diode matrix, voltage and clock. Note: If an input is set to 'clock', it can 
		not be configurated to 'normally open', 'normally closed' and 'diode matrix' directly, it has
		to be configurated to 'voltage' first. 
		"
	::= { inputIoUnitProgInputEntry 7 }

outputControlUnitTable  OBJECT-TYPE
	SYNTAX SEQUENCE OF OutputControlUnitEntry
	MAX-ACCESS not-accessible
	STATUS     current
	DESCRIPTION 
		""
	::= { outputs 1 }

outputControlUnitEntry  OBJECT-TYPE
	SYNTAX 	OutputControlUnitEntry
	MAX-ACCESS not-accessible
	STATUS     current
	DESCRIPTION 
		""
	INDEX { outputControlUnitIndex }
	::= { outputControlUnitTable 1 }

OutputControlUnitEntry ::= SEQUENCE {
	outputControlUnitIndex
		Integer32,
	outputControlUnitNumberOfOutputs
		Integer32
}

outputControlUnitIndex  OBJECT-TYPE
	SYNTAX     Integer32 (1..14)
	MAX-ACCESS not-accessible
	STATUS     current
	DESCRIPTION 
		"Index used for navigating the rows of outputControlUnitTable
		The size of the table is defined by the system  "
	::= { outputControlUnitEntry 1 }

outputControlUnitNumberOfOutputs  OBJECT-TYPE
	SYNTAX     Integer32 (0..8)
	MAX-ACCESS read-only
	STATUS     current
	DESCRIPTION 
		"Number of outputs available in controller."
	::= { outputControlUnitEntry 2 }

outputControlUnitOutputTable  OBJECT-TYPE
	SYNTAX SEQUENCE OF OutputControlUnitOutputEntry
	MAX-ACCESS not-accessible
	STATUS     current
	DESCRIPTION 
		"This table contains the status of the outputs for Control Units."
	::= { outputs 2 }

outputControlUnitOutputEntry  OBJECT-TYPE
	SYNTAX 	OutputControlUnitOutputEntry
	MAX-ACCESS not-accessible
	STATUS     current
	DESCRIPTION 
		""
	INDEX { outputControlUnitIndex, 
		outputControlUnitOutputIndex }
	::= { outputControlUnitOutputTable 1 }

OutputControlUnitOutputEntry ::= SEQUENCE {
	outputControlUnitOutputIndex
		Integer32,
	outputControlUnitOutputStatus
		INTEGER,
	outputControlUnitOutputDescription
		DisplayString
}

outputControlUnitOutputIndex  OBJECT-TYPE
	SYNTAX     Integer32 (1..16)
	MAX-ACCESS not-accessible
	STATUS     current
	DESCRIPTION 
		"Index used for navigating the rows  of outputControlUnitoutputTable
		The size of the table is defined by the outputControlUnitNumberOfOutputs   "
	::= { outputControlUnitOutputEntry 1 }

outputControlUnitOutputStatus  OBJECT-TYPE
	SYNTAX     INTEGER {
		notenergized (0),
		energized (1),
		disconnected (2),
		connected (3)
	}
	MAX-ACCESS read-only
	STATUS     current
	DESCRIPTION 
		"General output relays may be 'energized' or 'not energized'. 'energized' and 
		'not energized' correspond 
		to normal and alarm condition respectively for normally
		activated configuration. 
		Latched contactors may have values 'disconnected' or 'connected' "
	::= { outputControlUnitOutputEntry 2 }

outputControlUnitOutputDescription  OBJECT-TYPE
	SYNTAX     DisplayString (SIZE(0..16))
	MAX-ACCESS read-write
	STATUS     current
	DESCRIPTION 
		"A textual description of the output. This is stored in the system controller
		and can be changed by the user. "
	::= { outputControlUnitOutputEntry 3 }

outputIoUnitTable  OBJECT-TYPE
	SYNTAX SEQUENCE OF OutputIoUnitEntry
	MAX-ACCESS not-accessible
	STATUS     current
	DESCRIPTION 
		""
	::= { outputs 3 }

outputIoUnitEntry  OBJECT-TYPE
	SYNTAX 	OutputIoUnitEntry
	MAX-ACCESS not-accessible
	STATUS     current
	DESCRIPTION 
		""
	INDEX { outputIoUnitIndex }
	::= { outputIoUnitTable 1 }

OutputIoUnitEntry ::= SEQUENCE {
	outputIoUnitIndex
		Integer32,
	outputIoUnitNumberOfOutputs
		Integer32
}

outputIoUnitIndex  OBJECT-TYPE
	SYNTAX     Integer32 (1..14)
	MAX-ACCESS not-accessible
	STATUS     current
	DESCRIPTION 
		"Index used for navigating the rows of outputIoUnitTable
		The size of the table is defined by the system  "
	::= { outputIoUnitEntry 1 }

outputIoUnitNumberOfOutputs  OBJECT-TYPE
	SYNTAX     Integer32 (0..8)
	MAX-ACCESS read-only
	STATUS     current
	DESCRIPTION 
		"Number of outputs available in IO unit."
	::= { outputIoUnitEntry 2 }

outputIoUnitOutputTable  OBJECT-TYPE
	SYNTAX SEQUENCE OF OutputIoUnitOutputEntry
	MAX-ACCESS not-accessible
	STATUS     current
	DESCRIPTION 
		"This table contains the status of the outputs for IO Units."
	::= { outputs 4 }

outputIoUnitOutputEntry  OBJECT-TYPE
	SYNTAX 	OutputIoUnitOutputEntry
	MAX-ACCESS not-accessible
	STATUS     current
	DESCRIPTION 
		""
	INDEX { outputIoUnitIndex, 
		outputIoUnitOutputIndex }
	::= { outputIoUnitOutputTable 1 }

OutputIoUnitOutputEntry ::= SEQUENCE {
	outputIoUnitOutputIndex
		Integer32,
	outputIoUnitOutputStatus
		INTEGER,
	outputIoUnitOutputDescription
		DisplayString
}

outputIoUnitOutputIndex  OBJECT-TYPE
	SYNTAX     Integer32 (1..14)
	MAX-ACCESS not-accessible
	STATUS     current
	DESCRIPTION 
		"Index used for navigating the rows  of outputIOUnitOutputTable
		The size of the table is defined by the outputIOUnitNumberOfOutputs "
	::= { outputIoUnitOutputEntry 1 }

outputIoUnitOutputStatus  OBJECT-TYPE
	SYNTAX     INTEGER {
		notenergized (0),
		energized (1),
		disconnected (2),
		connected (3)
	}
	MAX-ACCESS read-only
	STATUS     current
	DESCRIPTION 
		"General output relays may be 'energized' or 'not energized'. 
		Latched contactors may have values 'disconnected' or 'connected' "
	::= { outputIoUnitOutputEntry 2 }

outputIoUnitOutputDescription  OBJECT-TYPE
	SYNTAX     DisplayString (SIZE(0..16))
	MAX-ACCESS read-write
	STATUS     current
	DESCRIPTION 
		"A textual description of the output in IO unit. This is stored in the system controller
		and can be changed by the user. "
	::= { outputIoUnitOutputEntry 3 }

controlSystemStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of control system subsystem"
	::= { controlSystem 1 }

controlSystemClock  OBJECT-TYPE
	SYNTAX     DateAndTime (SIZE(8..11))
	MAX-ACCESS read-write
	STATUS     current
	DESCRIPTION 
		"This is the system time."
	::= { controlSystem 2 }

controlSystemNumberOfControlUnits  OBJECT-TYPE
	SYNTAX     Integer32 (1..14)
	MAX-ACCESS read-write
	STATUS     current
	DESCRIPTION 
		"Total number of main controllers (SP2 Master, SP2 Basic Ind, SP2 Basic, Compack, Smartpack S, Smartpack)"
	::= { controlSystem 3 }

snmpSendOffTraps  OBJECT-TYPE
	SYNTAX     INTEGER {
		disabled (0),
		enabled (1)
	}
	MAX-ACCESS read-write
	STATUS     current
	DESCRIPTION 
		"When this is enabled, a trap is sent when a alarm condition goes off ."
	::= { snmp 1 }

snmpTrapRepeatRate  OBJECT-TYPE
	SYNTAX     Integer32 (0..1440)
	MAX-ACCESS read-write
	STATUS     current
	DESCRIPTION 
		"The time between every repeated trap when an alarm condition is on. 
		To turn repetetive traps off, set to zero.  Can be 0 to 1440 minutes i.e 24 hours."
	::= { snmp 2 }

snmpHeartBeatTrapRepeatRate  OBJECT-TYPE
	SYNTAX     Integer32 (0..1440)
	MAX-ACCESS read-write
	STATUS     current
	DESCRIPTION 
		"The time between every heartbeat trap when an alarm condition is on. 
		To turn heartbeat traps off, set to zero.  Can be 0 to 1440 minutes i.e 24 hours."
	::= { snmp 3 }

snmpInhibitTraps  OBJECT-TYPE
	SYNTAX     INTEGER {
		disabled (0),
		enabled (1)
	}
	MAX-ACCESS read-write
	STATUS     current
	DESCRIPTION 
		"When this is enabled, no trap is sent regardless of alarm conditions.
		"
	::= { snmp 4 }

snmpResendTraps  OBJECT-TYPE
	SYNTAX     INTEGER {
		pushbutton (0),
		resendtraps (1)
	}
	MAX-ACCESS read-write
	STATUS     current
	DESCRIPTION 
		"Resend traps once for all active alarms"
	::= { snmp 5 }

snmpTrapsTargetAddressTable  OBJECT-TYPE
	SYNTAX SEQUENCE OF SnmpTrapsTargetAddressEntry
	MAX-ACCESS not-accessible
	STATUS     current
	DESCRIPTION 
		"This table shows the trap target address. Note that it is NOT allowed 
		to change or create SNMP v3 trap target address IPs."
	::= { snmp 6 }

snmpTrapsTargetAddressEntry  OBJECT-TYPE
	SYNTAX 	SnmpTrapsTargetAddressEntry
	MAX-ACCESS not-accessible
	STATUS     current
	DESCRIPTION 
		""
	INDEX { snmpTrapsTargetAddressIndex }
	::= { snmpTrapsTargetAddressTable 1 }

SnmpTrapsTargetAddressEntry ::= SEQUENCE {
	snmpTrapsTargetAddressIndex
		Integer32,
	snmpTrapsTargetAddressIP
		DisplayString,
	snmpTrapsTargetAddressPort
		Integer32,
	snmpTrapsTargetAddressVersion
		INTEGER
}

snmpTrapsTargetAddressIndex  OBJECT-TYPE
	SYNTAX     Integer32 (1..10)
	MAX-ACCESS not-accessible
	STATUS     current
	DESCRIPTION 
		""
	::= { snmpTrapsTargetAddressEntry 1 }

snmpTrapsTargetAddressIP  OBJECT-TYPE
	SYNTAX     DisplayString (SIZE(1..80))
	MAX-ACCESS read-write
	STATUS     current
	DESCRIPTION 
		"Note that it is only allowed 
		to change or create SNMP v2c trap target address IPs."
	::= { snmpTrapsTargetAddressEntry 2 }

snmpTrapsTargetAddressPort  OBJECT-TYPE
	SYNTAX     Integer32
	MAX-ACCESS read-only
	STATUS     current
	DESCRIPTION 
		""
	::= { snmpTrapsTargetAddressEntry 3 }

snmpTrapsTargetAddressVersion  OBJECT-TYPE
	SYNTAX     INTEGER {
		undefined (0),
		v1 (1),
		v2c (2),
		v3 (3)
	}
	MAX-ACCESS read-only
	STATUS     current
	DESCRIPTION 
		""
	::= { snmpTrapsTargetAddressEntry 4 }

controlSystemResetManualAlarms  OBJECT-TYPE
	SYNTAX     INTEGER {
		pushbutton (0),
		resetalarm (1)
	}
	MAX-ACCESS read-write
	STATUS     current
	DESCRIPTION 
		"Reset manual alarms and put buzzer into silence."
	::= { controlSystem 5 }

controlSystemResetNumberOfModules  OBJECT-TYPE
	SYNTAX     INTEGER {
		pushbutton (0),
		resetnumber (1)
	}
	MAX-ACCESS read-write
	STATUS     current
	DESCRIPTION 
		"If set to '1', the number of modules (rectifier, solar charger, wind charger, control units, etc.)
		will be reset, and only those modules communicating are counted."
	::= { controlSystem 6 }

controlSystemIoUnitsNumberOfUnits  OBJECT-TYPE
	SYNTAX     Integer32 (0..14)
	MAX-ACCESS read-write
	STATUS     current
	DESCRIPTION 
		"This is the number of IO units installed in the system."
	::= { controlSystemIoUnits 1 }

controlSystemIoUnitsTable  OBJECT-TYPE
	SYNTAX SEQUENCE OF ControlSystemIoUnitsEntry
	MAX-ACCESS not-accessible
	STATUS     current
	DESCRIPTION 
		""
	::= { controlSystemIoUnits 2 }

controlSystemIoUnitsEntry  OBJECT-TYPE
	SYNTAX 	ControlSystemIoUnitsEntry
	MAX-ACCESS not-accessible
	STATUS     current
	DESCRIPTION 
		""
	INDEX { controlSystemIoUnitIndex }
	::= { controlSystemIoUnitsTable 1 }

ControlSystemIoUnitsEntry ::= SEQUENCE {
	controlSystemIoUnitIndex
		Integer32,
	controlSystemIoUnitNumberOfTemperatures
		Integer32,
	controlSystemIoUnitNumberOfFans
		Integer32
}

controlSystemIoUnitIndex  OBJECT-TYPE
	SYNTAX     Integer32 (1..14)
	MAX-ACCESS not-accessible
	STATUS     current
	DESCRIPTION 
		"Index used for navigating the rows of controlSystemIoUnitTable
		The size of the table is defined by the system"
	::= { controlSystemIoUnitsEntry 1 }

controlSystemIoUnitNumberOfTemperatures  OBJECT-TYPE
	SYNTAX     Integer32 (0..4)
	MAX-ACCESS read-only
	STATUS     current
	DESCRIPTION 
		"Number of temperature measurements available in IO unit"
	::= { controlSystemIoUnitsEntry 2 }

controlSystemIoUnitNumberOfFans  OBJECT-TYPE
	SYNTAX     Integer32 (0..4)
	MAX-ACCESS read-only
	STATUS     current
	DESCRIPTION 
		"Number of fan measurements available in IO unit"
	::= { controlSystemIoUnitsEntry 3 }

controlSystemIoUnitTemperatureTable  OBJECT-TYPE
	SYNTAX SEQUENCE OF ControlSystemIoUnitTemperatureEntry
	MAX-ACCESS not-accessible
	STATUS     current
	DESCRIPTION 
		""
	::= { controlSystemIoUnits 3 }

controlSystemIoUnitTemperatureEntry  OBJECT-TYPE
	SYNTAX 	ControlSystemIoUnitTemperatureEntry
	MAX-ACCESS not-accessible
	STATUS     current
	DESCRIPTION 
		""
	INDEX { controlSystemIoUnitIndex, 
		controlSystemIoUnitTemperatureIndex }
	::= { controlSystemIoUnitTemperatureTable 1 }

ControlSystemIoUnitTemperatureEntry ::= SEQUENCE {
	controlSystemIoUnitTemperatureIndex
		Integer32,
	controlSystemIoUnitTemperatureStatus
		INTEGER,
	controlSystemIoUnitTemperatureDescription
		DisplayString,
	controlSystemIoUnitTemperatureTrapRepeatCounter
		Counter32,
	controlSystemIoUnitTemperatureAlarmEnable
		INTEGER,
	controlSystemIoUnitTemperatureValue
		Integer32,
	controlSystemIoUnitTemperatureMajorHighLevel
		Integer32,
	controlSystemIoUnitTemperatureMinorHighLevel
		Integer32,
	controlSystemIoUnitTemperatureMinorLowLevel
		Integer32,
	controlSystemIoUnitTemperatureMajorLowLevel
		Integer32
}

controlSystemIoUnitTemperatureIndex  OBJECT-TYPE
	SYNTAX     Integer32 (1..2)
	MAX-ACCESS not-accessible
	STATUS     current
	DESCRIPTION 
		"Index used for navigating the rows  of controlSystemIoUnitTemperatureTable
		The size of the table is defined by the controlSystemIoUnitNumberOfTemperatures"
	::= { controlSystemIoUnitTemperatureEntry 1 }

controlSystemIoUnitTemperatureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of temperature monitor"
	::= { controlSystemIoUnitTemperatureEntry 2 }

controlSystemIoUnitTemperatureDescription  OBJECT-TYPE
	SYNTAX     DisplayString (SIZE(0..16))
	MAX-ACCESS read-write
	STATUS     current
	DESCRIPTION 
		"A textual description of the temperature monitor in control system. This is stored in the system controller
		and can be changed by the user."
	::= { controlSystemIoUnitTemperatureEntry 3 }

controlSystemIoUnitTemperatureTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { controlSystemIoUnitTemperatureEntry 4 }

controlSystemIoUnitTemperatureAlarmEnable  OBJECT-TYPE
	SYNTAX     INTEGER {
		disabled (0),
		enabled (1)
	}
	MAX-ACCESS read-write
	STATUS     current
	DESCRIPTION 
		"This value once enabled, the alarm condition of the monitor will be reported."
	::= { controlSystemIoUnitTemperatureEntry 5 }

controlSystemIoUnitTemperatureValue  OBJECT-TYPE
	SYNTAX     Integer32
	MAX-ACCESS read-only
	STATUS     current
	DESCRIPTION 
		"The measured temperature value."
	::= { controlSystemIoUnitTemperatureEntry 6 }

controlSystemIoUnitTemperatureMajorHighLevel  OBJECT-TYPE
	SYNTAX     Integer32
	MAX-ACCESS read-write
	STATUS     current
	DESCRIPTION 
		"The major high alarm limit"
	::= { controlSystemIoUnitTemperatureEntry 7 }

controlSystemIoUnitTemperatureMinorHighLevel  OBJECT-TYPE
	SYNTAX     Integer32
	MAX-ACCESS read-write
	STATUS     current
	DESCRIPTION 
		"The minor high alarm limit"
	::= { controlSystemIoUnitTemperatureEntry 8 }

controlSystemIoUnitTemperatureMinorLowLevel  OBJECT-TYPE
	SYNTAX     Integer32
	MAX-ACCESS read-write
	STATUS     current
	DESCRIPTION 
		"The minor low alarm limit"
	::= { controlSystemIoUnitTemperatureEntry 9 }

controlSystemIoUnitTemperatureMajorLowLevel  OBJECT-TYPE
	SYNTAX     Integer32
	MAX-ACCESS read-write
	STATUS     current
	DESCRIPTION 
		"The major low alarm limit"
	::= { controlSystemIoUnitTemperatureEntry 10 }

controlSystemIoUnitFanTable  OBJECT-TYPE
	SYNTAX SEQUENCE OF ControlSystemIoUnitFanEntry
	MAX-ACCESS not-accessible
	STATUS     current
	DESCRIPTION 
		""
	::= { controlSystemIoUnits 4 }

controlSystemIoUnitFanEntry  OBJECT-TYPE
	SYNTAX 	ControlSystemIoUnitFanEntry
	MAX-ACCESS not-accessible
	STATUS     current
	DESCRIPTION 
		""
	INDEX { controlSystemIoUnitIndex, 
		controlSystemIoUnitFanIndex }
	::= { controlSystemIoUnitFanTable 1 }

ControlSystemIoUnitFanEntry ::= SEQUENCE {
	controlSystemIoUnitFanIndex
		Integer32,
	controlSystemIoUnitFanSpeedValue
		Integer32,
	controlSystemIoUnitFanSpeedDeviation
		Integer32,
	controlSystemIoUnitFanControl
		Integer32
}

controlSystemIoUnitFanIndex  OBJECT-TYPE
	SYNTAX     Integer32 (1..2)
	MAX-ACCESS not-accessible
	STATUS     current
	DESCRIPTION 
		"Index used for navigating the rows 1..2 of ioUnitFan Table"
	::= { controlSystemIoUnitFanEntry 1 }

controlSystemIoUnitFanSpeedValue  OBJECT-TYPE
	SYNTAX     Integer32
	MAX-ACCESS read-only
	STATUS     current
	DESCRIPTION 
		"The measured fan speed"
	::= { controlSystemIoUnitFanEntry 2 }

controlSystemIoUnitFanSpeedDeviation  OBJECT-TYPE
	SYNTAX     Integer32
	MAX-ACCESS read-only
	STATUS     current
	DESCRIPTION 
		"The measured fan speed deviation"
	::= { controlSystemIoUnitFanEntry 3 }

controlSystemIoUnitFanControl  OBJECT-TYPE
	SYNTAX     Integer32
	MAX-ACCESS read-only
	STATUS     current
	DESCRIPTION 
		"Fan speed control value in percentage"
	::= { controlSystemIoUnitFanEntry 4 }

controlUnitNumberOfUnits  OBJECT-TYPE
	SYNTAX     Integer32 (1..254)
	MAX-ACCESS read-only
	STATUS     current
	DESCRIPTION 
		"Total number of control units installed in system."
	::= { controlSystemInventory 1 }

controlUnitTable  OBJECT-TYPE
	SYNTAX SEQUENCE OF ControlUnitEntry
	MAX-ACCESS not-accessible
	STATUS     current
	DESCRIPTION 
		"A table containing an inventory listing. Each row represent one of the system hardware 
		unit that is connected to the can bus. These units are system controllers, 
		battery monitors, I/O units, AC Mains Monitor boxes and load monitors.  Due to the system 
		architechture the tables index are not contiguous. Each unit type har its own address 
		range on the can bus.  All unit types except the system controller may contain 
		from 0 to 14 units.  The system controlller can never be zero.  Then there is no powersystem.
		
		"
	::= { controlSystemInventory 2 }

controlUnitEntry  OBJECT-TYPE
	SYNTAX 	ControlUnitEntry
	MAX-ACCESS not-accessible
	STATUS     current
	DESCRIPTION 
		"One row  in the table containing all hardware units connected to the canbus.   "
	INDEX { controlUnitIndex }
	::= { controlUnitTable 1 }

ControlUnitEntry ::= SEQUENCE {
	controlUnitIndex
		Integer32,
	controlUnitDescription
		DisplayString,
	controlUnitStatus
		INTEGER,
	controlUnitSerialNumber
		DisplayString,
	controlUnitHwPartNumber
		DisplayString,
	controlUnitHwVersion
		DisplayString,
	controlUnitSwPartNumber
		DisplayString,
	controlUnitSwVersion
		DisplayString
}

controlUnitIndex  OBJECT-TYPE
	SYNTAX     Integer32 (1..254)
	MAX-ACCESS not-accessible
	STATUS     current
	DESCRIPTION 
		"Index used for navigating the rows  of controlUnitTable
		The size of the table is defined by the controlUnitNumberOfUnits   "
	::= { controlUnitEntry 1 }

controlUnitDescription  OBJECT-TYPE
	SYNTAX     DisplayString (SIZE(0..32))
	MAX-ACCESS read-only
	STATUS     current
	DESCRIPTION 
		"A textual description of the control unit"
	::= { controlUnitEntry 2 }

controlUnitStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of the control unit."
	::= { controlUnitEntry 3 }

controlUnitSerialNumber  OBJECT-TYPE
	SYNTAX     DisplayString (SIZE(0..12))
	MAX-ACCESS read-only
	STATUS     current
	DESCRIPTION 
		"Serial number of the control unit."
	::= { controlUnitEntry 4 }

controlUnitHwPartNumber  OBJECT-TYPE
	SYNTAX     DisplayString (SIZE(0..12))
	MAX-ACCESS read-only
	STATUS     current
	DESCRIPTION 
		"Hardware part number of the control unit."
	::= { controlUnitEntry 5 }

controlUnitHwVersion  OBJECT-TYPE
	SYNTAX     DisplayString (SIZE(0..20))
	MAX-ACCESS read-only
	STATUS     current
	DESCRIPTION 
		"Hardware version of the control unit."
	::= { controlUnitEntry 6 }

controlUnitSwPartNumber  OBJECT-TYPE
	SYNTAX     DisplayString (SIZE(0..12))
	MAX-ACCESS read-only
	STATUS     current
	DESCRIPTION 
		"Software part number of the control unit."
	::= { controlUnitEntry 7 }

controlUnitSwVersion  OBJECT-TYPE
	SYNTAX     DisplayString (SIZE(0..20))
	MAX-ACCESS read-only
	STATUS     current
	DESCRIPTION 
		"Software version of the control unit."
	::= { controlUnitEntry 8 }

currentMonitorsNumberOfUnits  OBJECT-TYPE
	SYNTAX     Integer32 (0..14)
	MAX-ACCESS read-write
	STATUS     current
	DESCRIPTION 
		"This is the number of current monitors installed in the system."
	::= { currentMonitors 1 }

currentMonitorsTable  OBJECT-TYPE
	SYNTAX SEQUENCE OF CurrentMonitorsEntry
	MAX-ACCESS not-accessible
	STATUS     current
	DESCRIPTION 
		""
	::= { currentMonitors 2 }

currentMonitorsEntry  OBJECT-TYPE
	SYNTAX 	CurrentMonitorsEntry
	MAX-ACCESS not-accessible
	STATUS     current
	DESCRIPTION 
		""
	INDEX { currentMonitorIndex }
	::= { currentMonitorsTable 1 }

CurrentMonitorsEntry ::= SEQUENCE {
	currentMonitorIndex
		Integer32,
	currentMonitorType
		INTEGER,
	currentMonitorId
		Integer32,
	currentMonitorNumberOfFuses
		Integer32,
	currentMonitorNumberOfCurrents
		Integer32
}

currentMonitorIndex  OBJECT-TYPE
	SYNTAX     Integer32 (1..14)
	MAX-ACCESS not-accessible
	STATUS     current
	DESCRIPTION 
		"Index used for navigating the rows of currentMonitorsTable
		The size of the table is defined by the system"
	::= { currentMonitorsEntry 1 }

currentMonitorType  OBJECT-TYPE
	SYNTAX     INTEGER {
		stdLoadMonitor (1),
		loadCurrMonitor (2),
		rectCurrMonitor (3),
		dcdcCurrMonitor (4),
		solarCurrMonitor (5),
		windCurrMonitor (6),
		fuelcellCurrMonitor (7)
	}
	MAX-ACCESS read-only
	STATUS     current
	DESCRIPTION 
		"This shows if the current monitor is configured as standard load monitor (1), load current 
		monitor (2), rectifier current monitor (3), dcdc current monitor (4), solar current monitor (5),
		wind current monitor (6) or fuel cell current monitor (7)."
	::= { currentMonitorsEntry 2 }

currentMonitorId  OBJECT-TYPE
	SYNTAX     Integer32
	MAX-ACCESS read-only
	STATUS     current
	DESCRIPTION 
		"This is the unit index for each current monitor type."
	::= { currentMonitorsEntry 3 }

currentMonitorNumberOfFuses  OBJECT-TYPE
	SYNTAX     Integer32 (0..8)
	MAX-ACCESS read-only
	STATUS     current
	DESCRIPTION 
		"Number of fuse measurements in current monitor."
	::= { currentMonitorsEntry 4 }

currentMonitorNumberOfCurrents  OBJECT-TYPE
	SYNTAX     Integer32 (0..8)
	MAX-ACCESS read-only
	STATUS     current
	DESCRIPTION 
		"Number of current measurements in current monitor."
	::= { currentMonitorsEntry 5 }

currentMonitorFuseTable  OBJECT-TYPE
	SYNTAX SEQUENCE OF CurrentMonitorFuseEntry
	MAX-ACCESS not-accessible
	STATUS     current
	DESCRIPTION 
		""
	::= { currentMonitors 3 }

currentMonitorFuseEntry  OBJECT-TYPE
	SYNTAX 	CurrentMonitorFuseEntry
	MAX-ACCESS not-accessible
	STATUS     current
	DESCRIPTION 
		""
	INDEX { currentMonitorIndex, 
		currentMonitorFuseIndex }
	::= { currentMonitorFuseTable 1 }

CurrentMonitorFuseEntry ::= SEQUENCE {
	currentMonitorFuseIndex
		Integer32,
	currentMonitorFuseStatus
		INTEGER,
	currentMonitorFuseDescription
		DisplayString,
	currentMonitorFuseTrapRepeatCounter
		Counter32,
	currentMonitorFuseAlarmEnable
		INTEGER,
	currentMonitorFuseValue
		Integer32
}

currentMonitorFuseIndex  OBJECT-TYPE
	SYNTAX     Integer32 (1..8)
	MAX-ACCESS not-accessible
	STATUS     current
	DESCRIPTION 
		"Index used for navigating the rows  of currentMonitorFuseTable
		The size of the table is defined by the currentMonitorNumberOfFuses"
	::= { currentMonitorFuseEntry 1 }

currentMonitorFuseStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of fuse in current monitor"
	::= { currentMonitorFuseEntry 2 }

currentMonitorFuseDescription  OBJECT-TYPE
	SYNTAX     DisplayString (SIZE(1..16))
	MAX-ACCESS read-write
	STATUS     current
	DESCRIPTION 
		"A textual description of the fuse monitor. This is stored in the system controller
		and can be changed by the user."
	::= { currentMonitorFuseEntry 3 }

currentMonitorFuseTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { currentMonitorFuseEntry 4 }

currentMonitorFuseAlarmEnable  OBJECT-TYPE
	SYNTAX     INTEGER {
		disabled (0),
		enabled (1)
	}
	MAX-ACCESS read-write
	STATUS     current
	DESCRIPTION 
		"This value once enabled, the alarm condition of the monitor will be reported."
	::= { currentMonitorFuseEntry 5 }

currentMonitorFuseValue  OBJECT-TYPE
	SYNTAX     Integer32
	MAX-ACCESS read-only
	STATUS     current
	DESCRIPTION 
		"The measured fuse value."
	::= { currentMonitorFuseEntry 6 }

currentMonitorCurrentTable  OBJECT-TYPE
	SYNTAX SEQUENCE OF CurrentMonitorCurrentEntry
	MAX-ACCESS not-accessible
	STATUS     current
	DESCRIPTION 
		""
	::= { currentMonitors 4 }

currentMonitorCurrentEntry  OBJECT-TYPE
	SYNTAX 	CurrentMonitorCurrentEntry
	MAX-ACCESS not-accessible
	STATUS     current
	DESCRIPTION 
		""
	INDEX { currentMonitorIndex, 
		currentMonitorCurrentIndex }
	::= { currentMonitorCurrentTable 1 }

CurrentMonitorCurrentEntry ::= SEQUENCE {
	currentMonitorCurrentIndex
		Integer32,
	currentMonitorCurrentStatus
		INTEGER,
	currentMonitorCurrentDescription
		DisplayString,
	currentMonitorCurrentTrapRepeatCounter
		Counter32,
	currentMonitorCurrentAlarmEnable
		INTEGER,
	currentMonitorCurrentValue
		Integer32,
	currentMonitorCurrentMajorAlarmLevel
		Integer32,
	currentMonitorCurrentMinorAlarmLevel
		Integer32
}

currentMonitorCurrentIndex  OBJECT-TYPE
	SYNTAX     Integer32 (1..8)
	MAX-ACCESS not-accessible
	STATUS     current
	DESCRIPTION 
		"Index used for navigating the rows  of currentMonitorCurrentTable
		The size of the table is defined by the currentMonitorNumberOfCurrents"
	::= { currentMonitorCurrentEntry 1 }

currentMonitorCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of current in current monitor"
	::= { currentMonitorCurrentEntry 2 }

currentMonitorCurrentDescription  OBJECT-TYPE
	SYNTAX     DisplayString (SIZE(0..16))
	MAX-ACCESS read-write
	STATUS     current
	DESCRIPTION 
		"A textual description of the current monitor. This is stored in the system controller
		and can be changed by the user."
	::= { currentMonitorCurrentEntry 3 }

currentMonitorCurrentTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { currentMonitorCurrentEntry 4 }

currentMonitorCurrentAlarmEnable  OBJECT-TYPE
	SYNTAX     INTEGER {
		disabled (0),
		enabled (1)
	}
	MAX-ACCESS read-write
	STATUS     current
	DESCRIPTION 
		"This value once enabled, the alarm condition of the monitor will be reported."
	::= { currentMonitorCurrentEntry 5 }

currentMonitorCurrentValue  OBJECT-TYPE
	SYNTAX     Integer32
	MAX-ACCESS read-only
	STATUS     current
	DESCRIPTION 
		"The measured current value."
	::= { currentMonitorCurrentEntry 6 }

currentMonitorCurrentMajorAlarmLevel  OBJECT-TYPE
	SYNTAX     Integer32
	MAX-ACCESS read-write
	STATUS     current
	DESCRIPTION 
		"The major alarm limit"
	::= { currentMonitorCurrentEntry 7 }

currentMonitorCurrentMinorAlarmLevel  OBJECT-TYPE
	SYNTAX     Integer32
	MAX-ACCESS read-write
	STATUS     current
	DESCRIPTION 
		"The minor alarm limit"
	::= { currentMonitorCurrentEntry 8 }

currentMonitorEnergyLogAccumulatedTable  OBJECT-TYPE
	SYNTAX SEQUENCE OF CurrentMonitorEnergyLogAccumulatedEntry
	MAX-ACCESS not-accessible
	STATUS     current
	DESCRIPTION 
		"This table contains the accumulated energy consumption measured in current monitor"
	::= { currentMonitors 5 }

currentMonitorEnergyLogAccumulatedEntry  OBJECT-TYPE
	SYNTAX 	CurrentMonitorEnergyLogAccumulatedEntry
	MAX-ACCESS not-accessible
	STATUS     current
	DESCRIPTION 
		""
	INDEX { currentMonitorIndex, 
		currentMonitorCurrentIndex }
	::= { currentMonitorEnergyLogAccumulatedTable 1 }

CurrentMonitorEnergyLogAccumulatedEntry ::= SEQUENCE {
	currentMonitorEnergyLogAccumulated
		Integer32
}

currentMonitorEnergyLogAccumulated  OBJECT-TYPE
	SYNTAX     Integer32
	MAX-ACCESS read-only
	STATUS     current
	DESCRIPTION 
		"The accumulated energy consumption value"
	::= { currentMonitorEnergyLogAccumulatedEntry 1 }

currentMonitorEnergyLogLastHoursNumberOfEntries  OBJECT-TYPE
	SYNTAX     Integer32 (0..52)
	MAX-ACCESS read-only
	STATUS     current
	DESCRIPTION 
		"This is the maximal number of entries stored in hourly energy log"
	::= { currentMonitors 6 }

currentMonitorEnergyLogLastHoursTable  OBJECT-TYPE
	SYNTAX SEQUENCE OF CurrentMonitorEnergyLogLastHoursEntry
	MAX-ACCESS not-accessible
	STATUS     current
	DESCRIPTION 
		"This table contains energy consumption values logged every hour in current monitor."
	::= { currentMonitors 7 }

currentMonitorEnergyLogLastHoursEntry  OBJECT-TYPE
	SYNTAX 	CurrentMonitorEnergyLogLastHoursEntry
	MAX-ACCESS not-accessible
	STATUS     current
	DESCRIPTION 
		""
	INDEX { currentMonitorIndex, 
		currentMonitorCurrentIndex, 
		currentMonitorEnergyLogLastHoursIndex }
	::= { currentMonitorEnergyLogLastHoursTable 1 }

CurrentMonitorEnergyLogLastHoursEntry ::= SEQUENCE {
	currentMonitorEnergyLogLastHoursIndex
		Integer32,
	currentMonitorEnergyLogLastHoursValue
		Integer32
}

currentMonitorEnergyLogLastHoursIndex  OBJECT-TYPE
	SYNTAX     Integer32 (1..52)
	MAX-ACCESS not-accessible
	STATUS     current
	DESCRIPTION 
		"Index used for navigating the rows 1..52  of currentMonitorEnergyLogLastHoursTable"
	::= { currentMonitorEnergyLogLastHoursEntry 1 }

currentMonitorEnergyLogLastHoursValue  OBJECT-TYPE
	SYNTAX     Integer32
	MAX-ACCESS read-only
	STATUS     current
	DESCRIPTION 
		"Energy consumption value logged every hour in current monitor."
	::= { currentMonitorEnergyLogLastHoursEntry 2 }

currentMonitorEnergyLogLastDaysNumberOfEntries  OBJECT-TYPE
	SYNTAX     Integer32 (0..52)
	MAX-ACCESS read-only
	STATUS     current
	DESCRIPTION 
		"This is the maximal number of entries stored in daily energy log"
	::= { currentMonitors 8 }

currentMonitorEnergyLogLastDaysTable  OBJECT-TYPE
	SYNTAX SEQUENCE OF CurrentMonitorEnergyLogLastDaysEntry
	MAX-ACCESS not-accessible
	STATUS     current
	DESCRIPTION 
		"This table contains energy consumption values logged every day in current monitor."
	::= { currentMonitors 9 }

currentMonitorEnergyLogLastDaysEntry  OBJECT-TYPE
	SYNTAX 	CurrentMonitorEnergyLogLastDaysEntry
	MAX-ACCESS not-accessible
	STATUS     current
	DESCRIPTION 
		""
	INDEX { currentMonitorIndex, 
		currentMonitorCurrentIndex, 
		currentMonitorEnergyLogLastDaysIndex }
	::= { currentMonitorEnergyLogLastDaysTable 1 }

CurrentMonitorEnergyLogLastDaysEntry ::= SEQUENCE {
	currentMonitorEnergyLogLastDaysIndex
		Integer32,
	currentMonitorEnergyLogLastDaysValue
		Integer32
}

currentMonitorEnergyLogLastDaysIndex  OBJECT-TYPE
	SYNTAX     Integer32 (1..52)
	MAX-ACCESS not-accessible
	STATUS     current
	DESCRIPTION 
		"Index used for navigating the rows 1..52  of currentMonitorEnergyLogLastDaysTable"
	::= { currentMonitorEnergyLogLastDaysEntry 1 }

currentMonitorEnergyLogLastDaysValue  OBJECT-TYPE
	SYNTAX     Integer32
	MAX-ACCESS read-only
	STATUS     current
	DESCRIPTION 
		"Energy consumption value logged every day in current monitor."
	::= { currentMonitorEnergyLogLastDaysEntry 2 }

currentMonitorEnergyLogLastWeeksNumberOfEntries  OBJECT-TYPE
	SYNTAX     Integer32 (0..52)
	MAX-ACCESS read-only
	STATUS     current
	DESCRIPTION 
		"This is the maximal number of entries stored in weekly energy log"
	::= { currentMonitors 10 }

currentMonitorEnergyLogLastWeeksTable  OBJECT-TYPE
	SYNTAX SEQUENCE OF CurrentMonitorEnergyLogLastWeeksEntry
	MAX-ACCESS not-accessible
	STATUS     current
	DESCRIPTION 
		"This table contains energy consumption values logged every week in current monitor."
	::= { currentMonitors 11 }

currentMonitorEnergyLogLastWeeksEntry  OBJECT-TYPE
	SYNTAX 	CurrentMonitorEnergyLogLastWeeksEntry
	MAX-ACCESS not-accessible
	STATUS     current
	DESCRIPTION 
		""
	INDEX { currentMonitorIndex, 
		currentMonitorCurrentIndex, 
		currentMonitorEnergyLogLastWeeksIndex }
	::= { currentMonitorEnergyLogLastWeeksTable 1 }

CurrentMonitorEnergyLogLastWeeksEntry ::= SEQUENCE {
	currentMonitorEnergyLogLastWeeksIndex
		Integer32,
	currentMonitorEnergyLogLastWeeksValue
		Integer32
}

currentMonitorEnergyLogLastWeeksIndex  OBJECT-TYPE
	SYNTAX     Integer32 (1..52)
	MAX-ACCESS not-accessible
	STATUS     current
	DESCRIPTION 
		"Index used for navigating the rows 1..52  of currentMonitorEnergyLogLastWeekTable"
	::= { currentMonitorEnergyLogLastWeeksEntry 1 }

currentMonitorEnergyLogLastWeeksValue  OBJECT-TYPE
	SYNTAX     Integer32
	MAX-ACCESS read-only
	STATUS     current
	DESCRIPTION 
		"Energy consumption value logged every week in current monitor."
	::= { currentMonitorEnergyLogLastWeeksEntry 2 }

flexiMonitorsNumberOfUnits  OBJECT-TYPE
	SYNTAX     Integer32 (0..14)
	MAX-ACCESS read-write
	STATUS     current
	DESCRIPTION 
		"This is the number of fleximonitors installed in the system."
	::= { flexiMonitors 1 }

flexiMonitorsTable  OBJECT-TYPE
	SYNTAX SEQUENCE OF FlexiMonitorsEntry
	MAX-ACCESS not-accessible
	STATUS     current
	DESCRIPTION 
		""
	::= { flexiMonitors 2 }

flexiMonitorsEntry  OBJECT-TYPE
	SYNTAX 	FlexiMonitorsEntry
	MAX-ACCESS not-accessible
	STATUS     current
	DESCRIPTION 
		""
	INDEX { flexiMonitorIndex }
	::= { flexiMonitorsTable 1 }

FlexiMonitorsEntry ::= SEQUENCE {
	flexiMonitorIndex
		Integer32,
	flexiMonitorType
		INTEGER,
	flexiMonitorId
		Integer32,
	flexiMonitorNumberOfInputs
		Integer32,
	flexiMonitorNumberOfOutputs
		Integer32,
	flexiMonitorNumberOfCurrentInputs
		Integer32
}

flexiMonitorIndex  OBJECT-TYPE
	SYNTAX     Integer32 (1..14)
	MAX-ACCESS not-accessible
	STATUS     current
	DESCRIPTION 
		"Index used for navigating the rows of flexiMonitorsTable
		The size of the table is defined by the system"
	::= { flexiMonitorsEntry 1 }

flexiMonitorType  OBJECT-TYPE
	SYNTAX     INTEGER {
		battFlexiMonitor (1),
		loadFlexiMonitor (2),
		rectFlexiMonitor (3),
		contrFlexiMonitor (4),
		dcdcFlexiMonitor (5),
		solarFlexiMonitor (6),
		windFlexiMonitor (7),
		fuelcFlexiMonitor (8)
	}
	MAX-ACCESS read-only
	STATUS     current
	DESCRIPTION 
		"This shows if the fleximonitor is configured as battery monitor (1), load 
		monitor (2), rectifier monitor (3), controller monitor(4), dcdc monitor (5), solar monitor (6),
		wind monitor (7) or fuel cell monitor 8)."
	::= { flexiMonitorsEntry 2 }

flexiMonitorId  OBJECT-TYPE
	SYNTAX     Integer32
	MAX-ACCESS read-only
	STATUS     current
	DESCRIPTION 
		"This is the unit index for each fleximonitor type."
	::= { flexiMonitorsEntry 3 }

flexiMonitorNumberOfInputs  OBJECT-TYPE
	SYNTAX     Integer32 (0..8)
	MAX-ACCESS read-only
	STATUS     current
	DESCRIPTION 
		"Number of inputs in fleximonitor."
	::= { flexiMonitorsEntry 4 }

flexiMonitorNumberOfOutputs  OBJECT-TYPE
	SYNTAX     Integer32
	MAX-ACCESS read-only
	STATUS     current
	DESCRIPTION 
		"Number of outputs in fleximonitor."
	::= { flexiMonitorsEntry 5 }

flexiMonitorNumberOfCurrentInputs  OBJECT-TYPE
	SYNTAX     Integer32 (0..8)
	MAX-ACCESS read-only
	STATUS     current
	DESCRIPTION 
		"Number of current inputs in fleximonitor."
	::= { flexiMonitorsEntry 6 }

flexiMonitorInputTable  OBJECT-TYPE
	SYNTAX SEQUENCE OF FlexiMonitorInputEntry
	MAX-ACCESS not-accessible
	STATUS     current
	DESCRIPTION 
		""
	::= { flexiMonitors 3 }

flexiMonitorInputEntry  OBJECT-TYPE
	SYNTAX 	FlexiMonitorInputEntry
	MAX-ACCESS not-accessible
	STATUS     current
	DESCRIPTION 
		""
	INDEX { flexiMonitorIndex, 
		flexiMonitorInputIndex }
	::= { flexiMonitorInputTable 1 }

FlexiMonitorInputEntry ::= SEQUENCE {
	flexiMonitorInputIndex
		Integer32,
	flexiMonitorInputStatus
		INTEGER,
	flexiMonitorInputDescription
		DisplayString,
	flexiMonitorInputTrapRepeatCounter
		Counter32,
	flexiMonitorInputAlarmEnable
		INTEGER,
	flexiMonitorInputValue
		Integer32,
	flexiMonitorInputConfiguration
		INTEGER
}

flexiMonitorInputIndex  OBJECT-TYPE
	SYNTAX     Integer32 (1..16)
	MAX-ACCESS not-accessible
	STATUS     current
	DESCRIPTION 
		"Index used for navigating the rows  of flexiMonitorInputTable
		The size of the table is defined by the flexiMonitorNumberOfInputs"
	::= { flexiMonitorInputEntry 1 }

flexiMonitorInputStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"Programmable input status.
		"
	::= { flexiMonitorInputEntry 2 }

flexiMonitorInputDescription  OBJECT-TYPE
	SYNTAX     DisplayString (SIZE(0..16))
	MAX-ACCESS read-write
	STATUS     current
	DESCRIPTION 
		"A textual description of the programmable input. This is stored in the system controller
		and can be changed by the user.  ."
	::= { flexiMonitorInputEntry 3 }

flexiMonitorInputTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { flexiMonitorInputEntry 4 }

flexiMonitorInputAlarmEnable  OBJECT-TYPE
	SYNTAX     INTEGER {
		disabled (0),
		enabled (1)
	}
	MAX-ACCESS read-write
	STATUS     current
	DESCRIPTION 
		"This will enable or disable this inputs Alarm functionality.
		Setting 'disabled' here will turn off lock the status to 'disabled' state"
	::= { flexiMonitorInputEntry 5 }

flexiMonitorInputValue  OBJECT-TYPE
	SYNTAX     Integer32
	MAX-ACCESS read-only
	STATUS     current
	DESCRIPTION 
		"The inputs measured Value. Depending on the type of input, this may
		 represent a Voltage, a Temperature, a Current, a Speed or a Boolean value."
	::= { flexiMonitorInputEntry 6 }

flexiMonitorInputConfiguration  OBJECT-TYPE
	SYNTAX     INTEGER {
		progIn-NormallyOpen (1),
		progIn-NormallyClosed (2),
		voltage (3),
		temperature (4),
		current (5),
		speed (6),
		fuse-NormallyOpen (7),
		fuse-NormallyClosed (8),
		fuse-DiodeMatrix (9),
		current4-20mA (10),
		temp4-20mA (11),
		percent4-20mA (12)
	}
	MAX-ACCESS read-write
	STATUS     current
	DESCRIPTION 
		"Configuration of the input type. Available configurations are: ProgIn-Normally Open(1), ProgIn-Normally Closed(2),
		Voltage(3), Temperature(4),Current(5),Speed(6),Fuse-Normally Open(7),Fuse-Normally Closed(8), Fuse-Diode Matrix(9)
		current4-20mA(10),temp4-20mA(11),percent4-20mA(12)."
	::= { flexiMonitorInputEntry 7 }

flexiMonitorOutputTable  OBJECT-TYPE
	SYNTAX SEQUENCE OF FlexiMonitorOutputEntry
	MAX-ACCESS not-accessible
	STATUS     current
	DESCRIPTION 
		""
	::= { flexiMonitors 4 }

flexiMonitorOutputEntry  OBJECT-TYPE
	SYNTAX 	FlexiMonitorOutputEntry
	MAX-ACCESS not-accessible
	STATUS     current
	DESCRIPTION 
		""
	INDEX { flexiMonitorIndex, 
		flexiMonitorOutputIndex }
	::= { flexiMonitorOutputTable 1 }

FlexiMonitorOutputEntry ::= SEQUENCE {
	flexiMonitorOutputIndex
		Integer32,
	flexiMonitorOutputStatus
		INTEGER,
	flexiMonitorOutputDescription
		DisplayString
}

flexiMonitorOutputIndex  OBJECT-TYPE
	SYNTAX     Integer32 (1..16)
	MAX-ACCESS not-accessible
	STATUS     current
	DESCRIPTION 
		"Index used for navigating the rows  of flexiMonitorOutputTable
		The size of the table is defined by the flexiMonitorNumberOfOutputs"
	::= { flexiMonitorOutputEntry 1 }

flexiMonitorOutputStatus  OBJECT-TYPE
	SYNTAX     INTEGER {
		notenergized (0),
		energized (1),
		disconnected (2),
		connected (3)
	}
	MAX-ACCESS read-only
	STATUS     current
	DESCRIPTION 
		"General output relays may be 'energized' or 'not energized'. 'energized' and 
		'not energized' correspond 
		to normal and alarm condition respectively for normally
		activated configuration. 
		Latched contactors may have values 'disconnected' or 'connected'"
	::= { flexiMonitorOutputEntry 2 }

flexiMonitorOutputDescription  OBJECT-TYPE
	SYNTAX     DisplayString
	MAX-ACCESS read-write
	STATUS     current
	DESCRIPTION 
		"A textual description of the output. This is stored in the system controller
		and can be changed by the user. "
	::= { flexiMonitorOutputEntry 3 }

flexiMonitorCurrentInputTable  OBJECT-TYPE
	SYNTAX SEQUENCE OF FlexiMonitorCurrentInputEntry
	MAX-ACCESS not-accessible
	STATUS     current
	DESCRIPTION 
		""
	::= { flexiMonitors 5 }

flexiMonitorCurrentInputEntry  OBJECT-TYPE
	SYNTAX 	FlexiMonitorCurrentInputEntry
	MAX-ACCESS not-accessible
	STATUS     current
	DESCRIPTION 
		""
	INDEX { flexiMonitorIndex, 
		flexiMonitorCurrentInputIndex }
	::= { flexiMonitorCurrentInputTable 1 }

FlexiMonitorCurrentInputEntry ::= SEQUENCE {
	flexiMonitorCurrentInputIndex
		Integer32,
	flexiMonitorCurrentInputDescription
		DisplayString,
	flexiMonitorCurrentInputPricePerKW
		DisplayString,
	flexiMonitorCurrentInputCurrency
		DisplayString
}

flexiMonitorCurrentInputIndex  OBJECT-TYPE
	SYNTAX     Integer32 (1..16)
	MAX-ACCESS not-accessible
	STATUS     current
	DESCRIPTION 
		"Index used for navigating the rows  of flexiMonitorInputTable
		The size of the table is defined by the flexiMonitorNumberOfInputs"
	::= { flexiMonitorCurrentInputEntry 1 }

flexiMonitorCurrentInputDescription  OBJECT-TYPE
	SYNTAX     DisplayString (SIZE(0..16))
	MAX-ACCESS read-only
	STATUS     current
	DESCRIPTION 
		"A textual description of the programmable input. This is stored in the system controller
		and can be changed by the user.  ."
	::= { flexiMonitorCurrentInputEntry 2 }

flexiMonitorCurrentInputPricePerKW  OBJECT-TYPE
	SYNTAX     DisplayString
	MAX-ACCESS read-write
	STATUS     current
	DESCRIPTION 
		"Price per kW. To be used together with energy cost logs."
	::= { flexiMonitorCurrentInputEntry 3 }

flexiMonitorCurrentInputCurrency  OBJECT-TYPE
	SYNTAX     DisplayString (SIZE(1..6))
	MAX-ACCESS read-write
	STATUS     current
	DESCRIPTION 
		"The currency used in energy cost logs."
	::= { flexiMonitorCurrentInputEntry 4 }

flexiMonitorEnergyCostLogLastMonthsNumberOfEntries  OBJECT-TYPE
	SYNTAX     Integer32
	MAX-ACCESS read-only
	STATUS     current
	DESCRIPTION 
		""
	::= { flexiMonitors 6 }

flexiMonitorEnergyCostLogLastMonthsTable  OBJECT-TYPE
	SYNTAX SEQUENCE OF FlexiMonitorEnergyCostLogLastMonthsEntry
	MAX-ACCESS not-accessible
	STATUS     current
	DESCRIPTION 
		""
	::= { flexiMonitors 7 }

flexiMonitorEnergyCostLogLastMonthsEntry  OBJECT-TYPE
	SYNTAX 	FlexiMonitorEnergyCostLogLastMonthsEntry
	MAX-ACCESS not-accessible
	STATUS     current
	DESCRIPTION 
		""
	INDEX { flexiMonitorIndex, 
		flexiMonitorCurrentInputIndex, 
		flexiMonitorEnergyCostLogLastMonthsIndex }
	::= { flexiMonitorEnergyCostLogLastMonthsTable 1 }

FlexiMonitorEnergyCostLogLastMonthsEntry ::= SEQUENCE {
	flexiMonitorEnergyCostLogLastMonthsIndex
		Integer32,
	flexiMonitorEnergyCostLogLastMonthsMonth
		INTEGER,
	flexiMonitorEnergyCostLogLastMonthsEnergy
		Integer32,
	flexiMonitorEnergyCostLogLastMonthsCost
		DisplayString
}

flexiMonitorEnergyCostLogLastMonthsIndex  OBJECT-TYPE
	SYNTAX     Integer32
	MAX-ACCESS not-accessible
	STATUS     current
	DESCRIPTION 
		"Index used for navigating the rows 1..12"
	::= { flexiMonitorEnergyCostLogLastMonthsEntry 1 }

flexiMonitorEnergyCostLogLastMonthsMonth  OBJECT-TYPE
	SYNTAX     INTEGER {
		january (1),
		february (2),
		march (3),
		april (4),
		may (5),
		june (6),
		july (7),
		august (8),
		september (9),
		october (10),
		november (11),
		december (12)
	}
	MAX-ACCESS read-only
	STATUS     current
	DESCRIPTION 
		"Index by month"
	::= { flexiMonitorEnergyCostLogLastMonthsEntry 2 }

flexiMonitorEnergyCostLogLastMonthsEnergy  OBJECT-TYPE
	SYNTAX     Integer32
	MAX-ACCESS read-only
	STATUS     current
	DESCRIPTION 
		"Energy in kWh"
	::= { flexiMonitorEnergyCostLogLastMonthsEntry 3 }

flexiMonitorEnergyCostLogLastMonthsCost  OBJECT-TYPE
	SYNTAX     DisplayString
	MAX-ACCESS read-only
	STATUS     current
	DESCRIPTION 
		"Energy cost"
	::= { flexiMonitorEnergyCostLogLastMonthsEntry 4 }

flexiMonitorEnergyCostLogLastYearsNumberOfEntries  OBJECT-TYPE
	SYNTAX     Integer32
	MAX-ACCESS read-only
	STATUS     current
	DESCRIPTION 
		""
	::= { flexiMonitors 8 }

flexiMonitorEnergyCostLogLastYearsTable  OBJECT-TYPE
	SYNTAX SEQUENCE OF FlexiMonitorEnergyCostLogLastYearsEntry
	MAX-ACCESS not-accessible
	STATUS     current
	DESCRIPTION 
		""
	::= { flexiMonitors 9 }

flexiMonitorEnergyCostLogLastYearsEntry  OBJECT-TYPE
	SYNTAX 	FlexiMonitorEnergyCostLogLastYearsEntry
	MAX-ACCESS not-accessible
	STATUS     current
	DESCRIPTION 
		""
	INDEX { flexiMonitorIndex, 
		flexiMonitorCurrentInputIndex, 
		flexiMonitorEnergyCostLogLastYearsIndex }
	::= { flexiMonitorEnergyCostLogLastYearsTable 1 }

FlexiMonitorEnergyCostLogLastYearsEntry ::= SEQUENCE {
	flexiMonitorEnergyCostLogLastYearsIndex
		Integer32,
	flexiMonitorEnergyCostLogLastYearsYear
		DisplayString,
	flexiMonitorEnergyCostLogLastYearsEnergy
		Integer32,
	flexiMonitorEnergyCostLogLastYearsCost
		DisplayString
}

flexiMonitorEnergyCostLogLastYearsIndex  OBJECT-TYPE
	SYNTAX     Integer32
	MAX-ACCESS not-accessible
	STATUS     current
	DESCRIPTION 
		"Index used for navigating the rows 1..12"
	::= { flexiMonitorEnergyCostLogLastYearsEntry 1 }

flexiMonitorEnergyCostLogLastYearsYear  OBJECT-TYPE
	SYNTAX     DisplayString (SIZE(4))
	MAX-ACCESS read-only
	STATUS     current
	DESCRIPTION 
		"Index by year"
	::= { flexiMonitorEnergyCostLogLastYearsEntry 2 }

flexiMonitorEnergyCostLogLastYearsEnergy  OBJECT-TYPE
	SYNTAX     Integer32
	MAX-ACCESS read-only
	STATUS     current
	DESCRIPTION 
		"Energy in kWh"
	::= { flexiMonitorEnergyCostLogLastYearsEntry 3 }

flexiMonitorEnergyCostLogLastYearsCost  OBJECT-TYPE
	SYNTAX     DisplayString
	MAX-ACCESS read-only
	STATUS     current
	DESCRIPTION 
		"Energy cost"
	::= { flexiMonitorEnergyCostLogLastYearsEntry 4 }

flexiMonitorEnergyLogAccumulatedTable  OBJECT-TYPE
	SYNTAX SEQUENCE OF FlexiMonitorEnergyLogAccumulatedEntry
	MAX-ACCESS not-accessible
	STATUS     current
	DESCRIPTION 
		"This table contains the accumulated energy consumption measured in fleximonitor"
	::= { flexiMonitors 10 }

flexiMonitorEnergyLogAccumulatedEntry  OBJECT-TYPE
	SYNTAX 	FlexiMonitorEnergyLogAccumulatedEntry
	MAX-ACCESS not-accessible
	STATUS     current
	DESCRIPTION 
		""
	INDEX { flexiMonitorIndex, 
		flexiMonitorCurrentInputIndex }
	::= { flexiMonitorEnergyLogAccumulatedTable 1 }

FlexiMonitorEnergyLogAccumulatedEntry ::= SEQUENCE {
	flexiMonitorEnergyLogAccumulated
		Integer32
}

flexiMonitorEnergyLogAccumulated  OBJECT-TYPE
	SYNTAX     Integer32
	MAX-ACCESS read-only
	STATUS     current
	DESCRIPTION 
		"The accumulated energy consumption value"
	::= { flexiMonitorEnergyLogAccumulatedEntry 1 }

flexiMonitorEnergyLogLastHoursNumberOfEntries  OBJECT-TYPE
	SYNTAX     Integer32 (0..52)
	MAX-ACCESS read-only
	STATUS     current
	DESCRIPTION 
		"This is the maximal number of entries stored in hourly energy log"
	::= { flexiMonitors 11 }

flexiMonitorEnergyLogLastHoursTable  OBJECT-TYPE
	SYNTAX SEQUENCE OF FlexiMonitorEnergyLogLastHoursEntry
	MAX-ACCESS not-accessible
	STATUS     current
	DESCRIPTION 
		"This table contains energy consumption values logged every hour in fleximonitor."
	::= { flexiMonitors 12 }

flexiMonitorEnergyLogLastHoursEntry  OBJECT-TYPE
	SYNTAX 	FlexiMonitorEnergyLogLastHoursEntry
	MAX-ACCESS not-accessible
	STATUS     current
	DESCRIPTION 
		""
	INDEX { flexiMonitorIndex, 
		flexiMonitorCurrentInputIndex, 
		flexiMonitorEnergyLogLastHoursIndex }
	::= { flexiMonitorEnergyLogLastHoursTable 1 }

FlexiMonitorEnergyLogLastHoursEntry ::= SEQUENCE {
	flexiMonitorEnergyLogLastHoursIndex
		Integer32,
	flexiMonitorEnergyLogLastHoursValue
		Integer32
}

flexiMonitorEnergyLogLastHoursIndex  OBJECT-TYPE
	SYNTAX     Integer32 (1..52)
	MAX-ACCESS not-accessible
	STATUS     current
	DESCRIPTION 
		"Index used for navigating the rows 1..52  of flexiMonitorEnergyLogLastHoursTable"
	::= { flexiMonitorEnergyLogLastHoursEntry 1 }

flexiMonitorEnergyLogLastHoursValue  OBJECT-TYPE
	SYNTAX     Integer32
	MAX-ACCESS read-only
	STATUS     current
	DESCRIPTION 
		"Energy consumption value logged every hour in fleximonitor."
	::= { flexiMonitorEnergyLogLastHoursEntry 2 }

flexiMonitorEnergyLogLastDaysNumberOfEntries  OBJECT-TYPE
	SYNTAX     Integer32 (0..52)
	MAX-ACCESS read-only
	STATUS     current
	DESCRIPTION 
		"This is the maximal number of entries stored in daily energy log"
	::= { flexiMonitors 13 }

flexiMonitorEnergyLogLastDaysTable  OBJECT-TYPE
	SYNTAX SEQUENCE OF FlexiMonitorEnergyLogLastDaysEntry
	MAX-ACCESS not-accessible
	STATUS     current
	DESCRIPTION 
		"This table contains energy consumption values logged every day in fleximonitor."
	::= { flexiMonitors 14 }

flexiMonitorEnergyLogLastDaysEntry  OBJECT-TYPE
	SYNTAX 	FlexiMonitorEnergyLogLastDaysEntry
	MAX-ACCESS not-accessible
	STATUS     current
	DESCRIPTION 
		""
	INDEX { flexiMonitorIndex, 
		flexiMonitorCurrentInputIndex, 
		flexiMonitorEnergyLogLastDaysIndex }
	::= { flexiMonitorEnergyLogLastDaysTable 1 }

FlexiMonitorEnergyLogLastDaysEntry ::= SEQUENCE {
	flexiMonitorEnergyLogLastDaysIndex
		Integer32,
	flexiMonitorEnergyLogLastDaysValue
		Integer32
}

flexiMonitorEnergyLogLastDaysIndex  OBJECT-TYPE
	SYNTAX     Integer32 (1..52)
	MAX-ACCESS not-accessible
	STATUS     current
	DESCRIPTION 
		"Index used for navigating the rows 1..52  of flexiMonitorEnergyLogLastDaysTable"
	::= { flexiMonitorEnergyLogLastDaysEntry 1 }

flexiMonitorEnergyLogLastDaysValue  OBJECT-TYPE
	SYNTAX     Integer32
	MAX-ACCESS read-only
	STATUS     current
	DESCRIPTION 
		"Energy consumption value logged every day in fleximonitor."
	::= { flexiMonitorEnergyLogLastDaysEntry 2 }

flexiMonitorEnergyLogLastWeeksNumberOfEntries  OBJECT-TYPE
	SYNTAX     Integer32 (0..52)
	MAX-ACCESS read-only
	STATUS     current
	DESCRIPTION 
		"This is the maximal number of entries stored in weekly energy log"
	::= { flexiMonitors 15 }

flexiMonitorEnergyLogLastWeeksTable  OBJECT-TYPE
	SYNTAX SEQUENCE OF FlexiMonitorEnergyLogLastWeeksEntry
	MAX-ACCESS not-accessible
	STATUS     current
	DESCRIPTION 
		"This table contains energy consumption values logged every week in fleximonitor."
	::= { flexiMonitors 16 }

flexiMonitorEnergyLogLastWeeksEntry  OBJECT-TYPE
	SYNTAX 	FlexiMonitorEnergyLogLastWeeksEntry
	MAX-ACCESS not-accessible
	STATUS     current
	DESCRIPTION 
		""
	INDEX { flexiMonitorIndex, 
		flexiMonitorCurrentInputIndex, 
		flexiMonitorEnergyLogLastWeeksIndex }
	::= { flexiMonitorEnergyLogLastWeeksTable 1 }

FlexiMonitorEnergyLogLastWeeksEntry ::= SEQUENCE {
	flexiMonitorEnergyLogLastWeeksIndex
		Integer32,
	flexiMonitorEnergyLogLastWeeksValue
		Integer32
}

flexiMonitorEnergyLogLastWeeksIndex  OBJECT-TYPE
	SYNTAX     Integer32 (1..52)
	MAX-ACCESS not-accessible
	STATUS     current
	DESCRIPTION 
		"Index used for navigating the rows 1..52  of flexiMonitorEnergyLogLastWeeksTable"
	::= { flexiMonitorEnergyLogLastWeeksEntry 1 }

flexiMonitorEnergyLogLastWeeksValue  OBJECT-TYPE
	SYNTAX     Integer32
	MAX-ACCESS read-only
	STATUS     current
	DESCRIPTION 
		"Energy consumption value logged every week in fleximonitor."
	::= { flexiMonitorEnergyLogLastWeeksEntry 2 }

mainControlUnitsTable  OBJECT-TYPE
	SYNTAX SEQUENCE OF MainControlUnitsEntry
	MAX-ACCESS not-accessible
	STATUS     current
	DESCRIPTION 
		""
	::= { mainControlUnits 1 }

mainControlUnitsEntry  OBJECT-TYPE
	SYNTAX 	MainControlUnitsEntry
	MAX-ACCESS not-accessible
	STATUS     current
	DESCRIPTION 
		""
	INDEX { mainControlUnitIndex }
	::= { mainControlUnitsTable 1 }

MainControlUnitsEntry ::= SEQUENCE {
	mainControlUnitIndex
		Integer32,
	mainControlUnitNumberOfTemperatures
		Integer32
}

mainControlUnitIndex  OBJECT-TYPE
	SYNTAX     Integer32 (1..14)
	MAX-ACCESS not-accessible
	STATUS     current
	DESCRIPTION 
		"Index used for navigating the rows of controlUnitTable
		The size of the table is defined by the system"
	::= { mainControlUnitsEntry 1 }

mainControlUnitNumberOfTemperatures  OBJECT-TYPE
	SYNTAX     Integer32 (1..14)
	MAX-ACCESS read-only
	STATUS     current
	DESCRIPTION 
		"Total number of temperature measurements in main controller"
	::= { mainControlUnitsEntry 2 }

mainControlUnitTemperatureTable  OBJECT-TYPE
	SYNTAX SEQUENCE OF MainControlUnitTemperatureEntry
	MAX-ACCESS not-accessible
	STATUS     current
	DESCRIPTION 
		""
	::= { mainControlUnits 2 }

mainControlUnitTemperatureEntry  OBJECT-TYPE
	SYNTAX 	MainControlUnitTemperatureEntry
	MAX-ACCESS not-accessible
	STATUS     current
	DESCRIPTION 
		""
	INDEX { mainControlUnitIndex, 
		mainControlUnitTemperatureIndex }
	::= { mainControlUnitTemperatureTable 1 }

MainControlUnitTemperatureEntry ::= SEQUENCE {
	mainControlUnitTemperatureIndex
		Integer32,
	mainControlUnitTemperatureStatus
		INTEGER,
	mainControlUnitTemperatureDescription
		DisplayString,
	mainControlUnitTemperatureTrapRepeatCounter
		Counter32,
	mainControlUnitTemperatureAlarmEnable
		INTEGER,
	mainControlUnitTemperatureValue
		Integer32,
	mainControlUnitTemperatureMajorHighLevel
		Integer32,
	mainControlUnitTemperatureMinorHighLevel
		Integer32,
	mainControlUnitTemperatureMinorLowLevel
		Integer32,
	mainControlUnitTemperatureMajorLowLevel
		Integer32
}

mainControlUnitTemperatureIndex  OBJECT-TYPE
	SYNTAX     Integer32 (1..4)
	MAX-ACCESS not-accessible
	STATUS     current
	DESCRIPTION 
		"This index denotes which row in the temperature input table.
		The size of the table is defined by the batteryBankNumberOfTemp   "
	::= { mainControlUnitTemperatureEntry 1 }

mainControlUnitTemperatureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery temperature monitor"
	::= { mainControlUnitTemperatureEntry 2 }

mainControlUnitTemperatureDescription  OBJECT-TYPE
	SYNTAX     DisplayString (SIZE(0..16))
	MAX-ACCESS read-write
	STATUS     current
	DESCRIPTION 
		"A textual description of the battery temperature monitor. This is stored in the system controller
		and can be changed by the user. "
	::= { mainControlUnitTemperatureEntry 3 }

mainControlUnitTemperatureTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { mainControlUnitTemperatureEntry 4 }

mainControlUnitTemperatureAlarmEnable  OBJECT-TYPE
	SYNTAX     INTEGER {
		disabled (0),
		enabled (1)
	}
	MAX-ACCESS read-write
	STATUS     current
	DESCRIPTION 
		"This value once enabled, the alarm condition of the monitor will be reported."
	::= { mainControlUnitTemperatureEntry 5 }

mainControlUnitTemperatureValue  OBJECT-TYPE
	SYNTAX     Integer32
	MAX-ACCESS read-only
	STATUS     current
	DESCRIPTION 
		"The measured battery temperature."
	::= { mainControlUnitTemperatureEntry 6 }

mainControlUnitTemperatureMajorHighLevel  OBJECT-TYPE
	SYNTAX     Integer32
	MAX-ACCESS read-write
	STATUS     current
	DESCRIPTION 
		"The major high alarm limit"
	::= { mainControlUnitTemperatureEntry 7 }

mainControlUnitTemperatureMinorHighLevel  OBJECT-TYPE
	SYNTAX     Integer32
	MAX-ACCESS read-write
	STATUS     current
	DESCRIPTION 
		"The minor high alarm limit"
	::= { mainControlUnitTemperatureEntry 8 }

mainControlUnitTemperatureMinorLowLevel  OBJECT-TYPE
	SYNTAX     Integer32
	MAX-ACCESS read-write
	STATUS     current
	DESCRIPTION 
		"The minor low alarm limit"
	::= { mainControlUnitTemperatureEntry 9 }

mainControlUnitTemperatureMajorLowLevel  OBJECT-TYPE
	SYNTAX     Integer32
	MAX-ACCESS read-write
	STATUS     current
	DESCRIPTION 
		"The major low alarm limit"
	::= { mainControlUnitTemperatureEntry 10 }

mainControlUnitEarthFaultTable  OBJECT-TYPE
	SYNTAX SEQUENCE OF MainControlUnitEarthFaultEntry
	MAX-ACCESS not-accessible
	STATUS     current
	DESCRIPTION 
		""
	::= { mainControlUnits 3 }

mainControlUnitEarthFaultEntry  OBJECT-TYPE
	SYNTAX 	MainControlUnitEarthFaultEntry
	MAX-ACCESS not-accessible
	STATUS     current
	DESCRIPTION 
		""
	INDEX { mainControlUnitIndex }
	::= { mainControlUnitEarthFaultTable 1 }

MainControlUnitEarthFaultEntry ::= SEQUENCE {
	mainControlUnitEarthFaultStatus
		INTEGER,
	mainControlUnitEarthFaultDescription
		DisplayString,
	mainControlUnitEarthFaultTrapRepeatCounter
		Integer32,
	mainControlUnitEarthFaultAlarmEnable
		INTEGER,
	mainControlUnitEarthFaultValue
		Integer32,
	mainControlUnitEarthFaultMajorAlarmLevel
		Integer32
}

mainControlUnitEarthFaultStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the earth resistance is lower than the defined alarm level."
	::= { mainControlUnitEarthFaultEntry 1 }

mainControlUnitEarthFaultDescription  OBJECT-TYPE
	SYNTAX     DisplayString (SIZE(0..16))
	MAX-ACCESS read-write
	STATUS     current
	DESCRIPTION 
		"A textual description of the earth fault monitor. This is stored in the system controller
		and can be changed by the user."
	::= { mainControlUnitEarthFaultEntry 2 }

mainControlUnitEarthFaultTrapRepeatCounter  OBJECT-TYPE
	SYNTAX     Integer32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { mainControlUnitEarthFaultEntry 3 }

mainControlUnitEarthFaultAlarmEnable  OBJECT-TYPE
	SYNTAX     INTEGER {
		disabled (0),
		enabled (1)
	}
	MAX-ACCESS read-write
	STATUS     current
	DESCRIPTION 
		"This value once enabled, the alarm condition of the monitor will be reported."
	::= { mainControlUnitEarthFaultEntry 4 }

mainControlUnitEarthFaultValue  OBJECT-TYPE
	SYNTAX     Integer32
	MAX-ACCESS read-only
	STATUS     current
	DESCRIPTION 
		"The measured value of the earth resistance in kOhm."
	::= { mainControlUnitEarthFaultEntry 5 }

mainControlUnitEarthFaultMajorAlarmLevel  OBJECT-TYPE
	SYNTAX     Integer32
	MAX-ACCESS read-write
	STATUS     current
	DESCRIPTION 
		"The major alarm limit"
	::= { mainControlUnitEarthFaultEntry 6 }

mainControlUnitsErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed main controllers is higher than the defined alarm level."
	::= { mainControlUnitsError 1 }

mainControlUnitsErrorDescription  OBJECT-TYPE
	SYNTAX     DisplayString (SIZE(0..16))
	MAX-ACCESS read-write
	STATUS     current
	DESCRIPTION 
		"A textual description of the main control units error monitor. This is stored in the system controller
		and can be changed by the user."
	::= { mainControlUnitsError 2 }

mainControlUnitsErrorTrapRepeatCounter  OBJECT-TYPE
	SYNTAX     Integer32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { mainControlUnitsError 3 }

mainControlUnitsErrorAlarmEnable  OBJECT-TYPE
	SYNTAX     INTEGER {
		disabled (0),
		enabled (1)
	}
	MAX-ACCESS read-write
	STATUS     current
	DESCRIPTION 
		"This value once enabled, the alarm condition of the monitor will be reported."
	::= { mainControlUnitsError 4 }

mainControlUnitsErrorValue  OBJECT-TYPE
	SYNTAX     Integer32
	MAX-ACCESS read-only
	STATUS     current
	DESCRIPTION 
		"The detected number of failed main controllers."
	::= { mainControlUnitsError 5 }

mainControlUnitsErrorMajorAlarmLevel  OBJECT-TYPE
	SYNTAX     Integer32
	MAX-ACCESS read-write
	STATUS     current
	DESCRIPTION 
		"The major alarm limit"
	::= { mainControlUnitsError 6 }

mainControlUnitsErrorMinorAlarmLevel  OBJECT-TYPE
	SYNTAX     Integer32
	MAX-ACCESS read-write
	STATUS     current
	DESCRIPTION 
		"The minor alarm limit"
	::= { mainControlUnitsError 7 }

smartNodeErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed smartnodes is higher than the defined alarm level."
	::= { smartNodeError 1 }

smartNodeErrorDescription  OBJECT-TYPE
	SYNTAX     DisplayString (SIZE(0..16))
	MAX-ACCESS read-write
	STATUS     current
	DESCRIPTION 
		"A textual description of the smartnode error monitor. This is stored in the system controller
		and can be changed by the user."
	::= { smartNodeError 2 }

smartNodeErrorTrapRepeatCounter  OBJECT-TYPE
	SYNTAX     Integer32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { smartNodeError 3 }

smartNodeErrorAlarmEnable  OBJECT-TYPE
	SYNTAX     INTEGER {
		disabled (0),
		enabled (1)
	}
	MAX-ACCESS read-write
	STATUS     current
	DESCRIPTION 
		"This value once enabled, the alarm condition of the monitor will be reported."
	::= { smartNodeError 4 }

smartNodeErrorValue  OBJECT-TYPE
	SYNTAX     Integer32
	MAX-ACCESS read-only
	STATUS     current
	DESCRIPTION 
		"The detected number of failed smartnodes."
	::= { smartNodeError 5 }

smartNodeErrorMajorAlarmLevel  OBJECT-TYPE
	SYNTAX     Integer32
	MAX-ACCESS read-write
	STATUS     current
	DESCRIPTION 
		"The major alarm limit"
	::= { smartNodeError 6 }

smartNodeErrorMinorAlarmLevel  OBJECT-TYPE
	SYNTAX     Integer32
	MAX-ACCESS read-write
	STATUS     current
	DESCRIPTION 
		"The minor alarm limit"
	::= { smartNodeError 7 }

batteryMonitorErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed battery monitors is higher than the defined alarm level."
	::= { batteryMonitorError 1 }

batteryMonitorErrorDescription  OBJECT-TYPE
	SYNTAX     DisplayString (SIZE(0..16))
	MAX-ACCESS read-write
	STATUS     current
	DESCRIPTION 
		"A textual description of the battery monitor error monitor. This is stored in the system controller
		and can be changed by the user."
	::= { batteryMonitorError 2 }

batteryMonitorErrorTrapRepeatCounter  OBJECT-TYPE
	SYNTAX     Integer32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryMonitorError 3 }

batteryMonitorErrorAlarmEnable  OBJECT-TYPE
	SYNTAX     INTEGER {
		disabled (0),
		enabled (1)
	}
	MAX-ACCESS read-write
	STATUS     current
	DESCRIPTION 
		"This value once enabled, the alarm condition of the monitor will be reported."
	::= { batteryMonitorError 4 }

batteryMonitorErrorValue  OBJECT-TYPE
	SYNTAX     Integer32
	MAX-ACCESS read-only
	STATUS     current
	DESCRIPTION 
		"The detected number of failed battery monitors."
	::= { batteryMonitorError 5 }

batteryMonitorErrorMajorAlarmLevel  OBJECT-TYPE
	SYNTAX     Integer32
	MAX-ACCESS read-write
	STATUS     current
	DESCRIPTION 
		"The major alarm limit"
	::= { batteryMonitorError 6 }

batteryMonitorErrorMinorAlarmLevel  OBJECT-TYPE
	SYNTAX     Integer32
	MAX-ACCESS read-write
	STATUS     current
	DESCRIPTION 
		"The minor alarm limit"
	::= { batteryMonitorError 7 }

loadMonitorErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed load monitors is higher than the defined alarm level."
	::= { loadMonitorError 1 }

loadMonitorErrorDescription  OBJECT-TYPE
	SYNTAX     DisplayString (SIZE(0..16))
	MAX-ACCESS read-write
	STATUS     current
	DESCRIPTION 
		"A textual description of the load monitor error monitor. This is stored in the system controller
		and can be changed by the user."
	::= { loadMonitorError 2 }

loadMonitorErrorTrapRepeatCounter  OBJECT-TYPE
	SYNTAX     Integer32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { loadMonitorError 3 }

loadMonitorErrorAlarmEnable  OBJECT-TYPE
	SYNTAX     INTEGER {
		disabled (0),
		enabled (1)
	}
	MAX-ACCESS read-write
	STATUS     current
	DESCRIPTION 
		"This value once enabled, the alarm condition of the monitor will be reported."
	::= { loadMonitorError 4 }

loadMonitorErrorValue  OBJECT-TYPE
	SYNTAX     Integer32
	MAX-ACCESS read-only
	STATUS     current
	DESCRIPTION 
		"The detected number of failed load monitors."
	::= { loadMonitorError 5 }

loadMonitorErrorMajorAlarmLevel  OBJECT-TYPE
	SYNTAX     Integer32
	MAX-ACCESS read-write
	STATUS     current
	DESCRIPTION 
		"The major alarm limit"
	::= { loadMonitorError 6 }

loadMonitorErrorMinorAlarmLevel  OBJECT-TYPE
	SYNTAX     Integer32
	MAX-ACCESS read-write
	STATUS     current
	DESCRIPTION 
		"The minor alarm limit"
	::= { loadMonitorError 7 }

ioUnitErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed IO units is higher than the defined alarm level."
	::= { ioUnitError 1 }

ioUnitErrorDescription  OBJECT-TYPE
	SYNTAX     DisplayString (SIZE(0..16))
	MAX-ACCESS read-write
	STATUS     current
	DESCRIPTION 
		"A textual description of the IO unit error monitor. This is stored in the system controller
		and can be changed by the user."
	::= { ioUnitError 2 }

ioUnitErrorTrapRepeatCounter  OBJECT-TYPE
	SYNTAX     Integer32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { ioUnitError 3 }

ioUnitErrorAlarmEnable  OBJECT-TYPE
	SYNTAX     INTEGER {
		disabled (0),
		enabled (1)
	}
	MAX-ACCESS read-write
	STATUS     current
	DESCRIPTION 
		"This value once enabled, the alarm condition of the monitor will be reported."
	::= { ioUnitError 4 }

ioUnitErrorValue  OBJECT-TYPE
	SYNTAX     Integer32
	MAX-ACCESS read-only
	STATUS     current
	DESCRIPTION 
		"The detected number of failed IO units."
	::= { ioUnitError 5 }

ioUnitErrorMajorAlarmLevel  OBJECT-TYPE
	SYNTAX     Integer32
	MAX-ACCESS read-write
	STATUS     current
	DESCRIPTION 
		"The major alarm limit"
	::= { ioUnitError 6 }

ioUnitErrorMinorAlarmLevel  OBJECT-TYPE
	SYNTAX     Integer32
	MAX-ACCESS read-write
	STATUS     current
	DESCRIPTION 
		"The minor alarm limit"
	::= { ioUnitError 7 }

mainsMonitorErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed mains monitors is higher than the defined alarm level."
	::= { mainsMonitorError 1 }

mainsMonitorErrorDescription  OBJECT-TYPE
	SYNTAX     DisplayString (SIZE(0..16))
	MAX-ACCESS read-write
	STATUS     current
	DESCRIPTION 
		"A textual description of the mains monitor error monitor. This is stored in the system controller
		and can be changed by the user."
	::= { mainsMonitorError 2 }

mainsMonitorErrorTrapRepeatCounter  OBJECT-TYPE
	SYNTAX     Integer32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { mainsMonitorError 3 }

mainsMonitorErrorAlarmEnable  OBJECT-TYPE
	SYNTAX     INTEGER {
		disabled (0),
		enabled (1)
	}
	MAX-ACCESS read-write
	STATUS     current
	DESCRIPTION 
		"This value once enabled, the alarm condition of the monitor will be reported."
	::= { mainsMonitorError 4 }

mainsMonitorErrorValue  OBJECT-TYPE
	SYNTAX     Integer32
	MAX-ACCESS read-only
	STATUS     current
	DESCRIPTION 
		"The detected number of failed mains monitors."
	::= { mainsMonitorError 5 }

mainsMonitorErrorMajorAlarmLevel  OBJECT-TYPE
	SYNTAX     Integer32
	MAX-ACCESS read-write
	STATUS     current
	DESCRIPTION 
		"The major alarm limit"
	::= { mainsMonitorError 6 }

mainsMonitorErrorMinorAlarmLevel  OBJECT-TYPE
	SYNTAX     Integer32
	MAX-ACCESS read-write
	STATUS     current
	DESCRIPTION 
		"The minor alarm limit"
	::= { mainsMonitorError 7 }

flexiMonitorErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed flexi monitors is higher than the defined alarm level."
	::= { flexiMonitorError 1 }

flexiMonitorErrorDescription  OBJECT-TYPE
	SYNTAX     DisplayString (SIZE(0..16))
	MAX-ACCESS read-write
	STATUS     current
	DESCRIPTION 
		"A textual description of the flexi monitor error monitor. This is stored in the system controller
		and can be changed by the user."
	::= { flexiMonitorError 2 }

flexiMonitorErrorTrapRepeatCounter  OBJECT-TYPE
	SYNTAX     Integer32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { flexiMonitorError 3 }

flexiMonitorErrorAlarmEnable  OBJECT-TYPE
	SYNTAX     INTEGER {
		disabled (0),
		enabled (1)
	}
	MAX-ACCESS read-write
	STATUS     current
	DESCRIPTION 
		"This value once enabled, the alarm condition of the monitor will be reported."
	::= { flexiMonitorError 4 }

flexiMonitorErrorValue  OBJECT-TYPE
	SYNTAX     Integer32
	MAX-ACCESS read-only
	STATUS     current
	DESCRIPTION 
		"The detected number of failed flexi monitors."
	::= { flexiMonitorError 5 }

flexiMonitorErrorMajorAlarmLevel  OBJECT-TYPE
	SYNTAX     Integer32
	MAX-ACCESS read-write
	STATUS     current
	DESCRIPTION 
		"The major alarm limit"
	::= { flexiMonitorError 6 }

flexiMonitorErrorMinorAlarmLevel  OBJECT-TYPE
	SYNTAX     Integer32
	MAX-ACCESS read-write
	STATUS     current
	DESCRIPTION 
		"The minor alarm limit"
	::= { flexiMonitorError 7 }

ambientTemperatureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The state of the ambient temperature can be either one of the defined enumerated values"
	::= { ambientTemperature 1 }

ambientTemperatureDescription  OBJECT-TYPE
	SYNTAX     DisplayString (SIZE(0..16))
	MAX-ACCESS read-write
	STATUS     current
	DESCRIPTION 
		"A textual description of the ambient temperature monitor. This is stored in the system controller
		and can be changed by the user. "
	::= { ambientTemperature 2 }

ambientTemperatureTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { ambientTemperature 3 }

ambientTemperatureAlarmEnable  OBJECT-TYPE
	SYNTAX     INTEGER {
		disabled (0),
		enabled (1)
	}
	MAX-ACCESS read-write
	STATUS     current
	DESCRIPTION 
		"This value once enabled, the alarm condition of the monitor will be reported."
	::= { ambientTemperature 4 }

ambientTemperatureValue  OBJECT-TYPE
	SYNTAX     Integer32 (0..9999)
	MAX-ACCESS read-only
	STATUS     current
	DESCRIPTION 
		"The highest value of the enabled ambient temperature measurements.
		Depending on the global setting in the Control unit, this value will be presented in Celsius
		or Fahrenheit."
	::= { ambientTemperature 5 }

ambientTemperatureMajorHighLevel  OBJECT-TYPE
	SYNTAX     Integer32
	MAX-ACCESS read-write
	STATUS     current
	DESCRIPTION 
		"The major high alarm limit"
	::= { ambientTemperature 6 }

ambientTemperatureMinorHighLevel  OBJECT-TYPE
	SYNTAX     Integer32
	MAX-ACCESS read-write
	STATUS     current
	DESCRIPTION 
		"The minor high alarm limit"
	::= { ambientTemperature 7 }

ambientTemperatureMinorLowLevel  OBJECT-TYPE
	SYNTAX     Integer32
	MAX-ACCESS read-write
	STATUS     current
	DESCRIPTION 
		"The minor low alarm limit"
	::= { ambientTemperature 8 }

ambientTemperatureMajorLowLevel  OBJECT-TYPE
	SYNTAX     Integer32
	MAX-ACCESS read-write
	STATUS     current
	DESCRIPTION 
		"The major low alarm limit"
	::= { ambientTemperature 9 }

deltaTemperatureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The state of the delta temperature can be either one of the defined enumerated values"
	::= { deltaTemperature 1 }

deltaTemperatureDescription  OBJECT-TYPE
	SYNTAX     DisplayString (SIZE(0..16))
	MAX-ACCESS read-write
	STATUS     current
	DESCRIPTION 
		"A textual description of the delta temperature monitor. This is stored in the system controller
		and can be changed by the user. "
	::= { deltaTemperature 2 }

deltaTemperatureTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { deltaTemperature 3 }

deltaTemperatureAlarmEnable  OBJECT-TYPE
	SYNTAX     INTEGER {
		disabled (0),
		enabled (1)
	}
	MAX-ACCESS read-write
	STATUS     current
	DESCRIPTION 
		"This value once enabled, the alarm condition of the monitor will be reported."
	::= { deltaTemperature 4 }

deltaTemperatureValue  OBJECT-TYPE
	SYNTAX     Integer32 (0..9999)
	MAX-ACCESS read-only
	STATUS     current
	DESCRIPTION 
		"The delta temperature value.
		Depending on the global setting in the Control unit, this value will be presented in Celsius
		or Fahrenheit."
	::= { deltaTemperature 5 }

deltaTemperatureMajorHighLevel  OBJECT-TYPE
	SYNTAX     Integer32
	MAX-ACCESS read-write
	STATUS     current
	DESCRIPTION 
		"The major high alarm limit"
	::= { deltaTemperature 6 }

deltaTemperatureMinorHighLevel  OBJECT-TYPE
	SYNTAX     Integer32
	MAX-ACCESS read-write
	STATUS     current
	DESCRIPTION 
		"The minor high alarm limit"
	::= { deltaTemperature 7 }

deltaTemperatureMinorLowLevel  OBJECT-TYPE
	SYNTAX     Integer32
	MAX-ACCESS read-write
	STATUS     current
	DESCRIPTION 
		"The minor low alarm limit"
	::= { deltaTemperature 8 }

deltaTemperatureMajorLowLevel  OBJECT-TYPE
	SYNTAX     Integer32
	MAX-ACCESS read-write
	STATUS     current
	DESCRIPTION 
		"The major low alarm limit"
	::= { deltaTemperature 9 }

userSuspendedStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed attempts is higher than the defined alarm level."
	::= { userSuspended 1 }

userSuspendedDescription  OBJECT-TYPE
	SYNTAX     DisplayString (SIZE(0..16))
	MAX-ACCESS read-write
	STATUS     current
	DESCRIPTION 
		"A textual description of the login failure monitor. This is stored in the system controller
		and can be changed by the user."
	::= { userSuspended 2 }

userSuspendedTrapRepeatCounter  OBJECT-TYPE
	SYNTAX     Integer32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { userSuspended 3 }

userSuspendedAlarmEnable  OBJECT-TYPE
	SYNTAX     INTEGER {
		disabled (0),
		enabled (1)
	}
	MAX-ACCESS read-write
	STATUS     current
	DESCRIPTION 
		"This value once enabled, the alarm condition of the monitor will be reported."
	::= { userSuspended 4 }

userSuspendedValue  OBJECT-TYPE
	SYNTAX     Integer32
	MAX-ACCESS read-only
	STATUS     current
	DESCRIPTION 
		"The detected number of failed attempts."
	::= { userSuspended 5 }

userSuspendedMajorAlarmLevel  OBJECT-TYPE
	SYNTAX     Integer32
	MAX-ACCESS read-write
	STATUS     current
	DESCRIPTION 
		"The major alarm limit"
	::= { userSuspended 6 }

controlSystemSaveEnergyLog  OBJECT-TYPE
	SYNTAX     INTEGER {
		pushbutton (0),
		savelog (1)
	}
	MAX-ACCESS read-write
	STATUS     current
	DESCRIPTION 
		"Save energy logs to FTP server."
	::= { controlSystem 16 }

controlSystemSaveDataLog  OBJECT-TYPE
	SYNTAX     INTEGER {
		pushbutton (0),
		savelog (1)
	}
	MAX-ACCESS read-write
	STATUS     current
	DESCRIPTION 
		"Save data logs to FTP server."
	::= { controlSystem 17 }

controlSystemNTPServerIP  OBJECT-TYPE
	SYNTAX     DisplayString (SIZE(1..80))
	MAX-ACCESS read-write
	STATUS     current
	DESCRIPTION 
		""
	::= { controlSystem 18 }

controlSystemReboot  OBJECT-TYPE
	SYNTAX     INTEGER {
		pushbutton (0),
		reboot (1)
	}
	MAX-ACCESS read-write
	STATUS     current
	DESCRIPTION 
		"Reboot main controller (Smartpack 2, Smartpack S, Compack, Smartpack 2 TOUCH)"
	::= { controlSystem 19 }

controlSystemSaveEventLog  OBJECT-TYPE
	SYNTAX     INTEGER {
		pushbutton (0),
		savelog (1)
	}
	MAX-ACCESS read-write
	STATUS     current
	DESCRIPTION 
		"Save event logs to FTP server."
	::= { controlSystem 20 }

controlSystemSaveAccountLog  OBJECT-TYPE
	SYNTAX     INTEGER {
		pushbutton (0),
		savelog (1)
	}
	MAX-ACCESS read-write
	STATUS     current
	DESCRIPTION 
		"Save account logs to FTP server."
	::= { controlSystem 21 }

controlSystemSetCfgFromXmlFiles  OBJECT-TYPE
	SYNTAX     INTEGER {
		pushbutton (0),
		setCfg (1)
	}
	MAX-ACCESS read-write
	STATUS     current
	DESCRIPTION 
		"Set configurations from default1.XML, default2.XML and default3.XML in Default folder"
	::= { controlSystem 22 }

controlSystemNumberOfGenericModbusData  OBJECT-TYPE
	SYNTAX     Integer32 (0..50)
	MAX-ACCESS read-only
	STATUS     current
	DESCRIPTION 
		"Number of genaric Modbus data configured in system"
	::= { controlSystem 23 }

controlSystemGenericModbusDataTable  OBJECT-TYPE
	SYNTAX SEQUENCE OF ControlSystemGenericModbusDataEntry
	MAX-ACCESS not-accessible
	STATUS     current
	DESCRIPTION 
		""
	::= { controlSystem 24 }

controlSystemGenericModbusDataEntry  OBJECT-TYPE
	SYNTAX 	ControlSystemGenericModbusDataEntry
	MAX-ACCESS not-accessible
	STATUS     current
	DESCRIPTION 
		""
	INDEX { controlSystemGenericModbusDataIndex }
	::= { controlSystemGenericModbusDataTable 1 }

ControlSystemGenericModbusDataEntry ::= SEQUENCE {
	controlSystemGenericModbusDataIndex
		Integer32,
	controlSystemGenericModbusDataDescription
		DisplayString,
	controlSystemGenericModbusDataValue
		DisplayString,
	controlSystemGenericModbusDataUnit
		DisplayString
}

controlSystemGenericModbusDataIndex  OBJECT-TYPE
	SYNTAX     Integer32 (1..50)
	MAX-ACCESS not-accessible
	STATUS     current
	DESCRIPTION 
		"Index used for navigating the rows of table
		The size of the table is defined by the system"
	::= { controlSystemGenericModbusDataEntry 1 }

controlSystemGenericModbusDataDescription  OBJECT-TYPE
	SYNTAX     DisplayString (SIZE(0..32))
	MAX-ACCESS read-only
	STATUS     current
	DESCRIPTION 
		"description of generic Modbus data"
	::= { controlSystemGenericModbusDataEntry 2 }

controlSystemGenericModbusDataValue  OBJECT-TYPE
	SYNTAX     DisplayString (SIZE(0..32))
	MAX-ACCESS read-only
	STATUS     current
	DESCRIPTION 
		"Value of generic Modbus data"
	::= { controlSystemGenericModbusDataEntry 3 }

controlSystemGenericModbusDataUnit  OBJECT-TYPE
	SYNTAX     DisplayString (SIZE(0..12))
	MAX-ACCESS read-only
	STATUS     current
	DESCRIPTION 
		"Unit of generic Modbus data"
	::= { controlSystemGenericModbusDataEntry 4 }

demandResponseStatus  OBJECT-TYPE
	SYNTAX     INTEGER {
		notInitialized (0),
		notEnabled (1),
		initializedAndReady (2),
		active (3),
		active-phaseDependant (4),
		reachedDoDStopLevelOrVoltStopLevel (5),
		reachedDoDStopLevel (6),
		reachedVoltStopLevel (7),
		feed-inFromBatteryNotReady (8),
		terminatedOnMAXTime (9),
		notEnoughBackupCapacity (10),
		notReady-NotInFLOAT (11),
		notReady-AlarmsInSystem (12)
	}
	MAX-ACCESS read-only
	STATUS     current
	DESCRIPTION 
		"Status of demand response"
	::= { demandResponse 1 }

demandResponseMinBatteryBackupTime  OBJECT-TYPE
	SYNTAX     Integer32
	MAX-ACCESS read-write
	STATUS     current
	DESCRIPTION 
		"This parameter set the required minimum battery backup time in minutes for this system. 
		The controller must ensure that there always are at least the required battery backup time left 
		during and after an DSR event. "
	::= { demandResponse 2 }

demandResponsePowerForecast  OBJECT-TYPE
	SYNTAX     Integer32
	MAX-ACCESS read-only
	STATUS     current
	DESCRIPTION 
		"This is an average load power in watt during last 52 hours "
	::= { demandResponse 3 }

demandResponseAvailableEnergy  OBJECT-TYPE
	SYNTAX     Integer32
	MAX-ACCESS read-only
	STATUS     current
	DESCRIPTION 
		"Estimated available energy based on the battery capacity, the load power and the expected backup time of the load groups"
	::= { demandResponse 4 }

demandResponseBatteryDischargePower  OBJECT-TYPE
	SYNTAX     Integer32
	MAX-ACCESS read-write
	STATUS     current
	DESCRIPTION 
		"This parameter controls the discharge power of the battery during an DSR event.
		Scale is 0.01kw"
	::= { demandResponse 5 }

demandResponseMaxTime  OBJECT-TYPE
	SYNTAX     Integer32
	MAX-ACCESS read-write
	STATUS     current
	DESCRIPTION 
		"The maximum discharge duration in minutes"
	::= { demandResponse 6 }

demandResponseControl  OBJECT-TYPE
	SYNTAX     INTEGER {
		pushButton (0),
		activate (1),
		deactivate (2)
	}
	MAX-ACCESS read-write
	STATUS     current
	DESCRIPTION 
		"Activate/deactivate demand response"
	::= { demandResponse 7 }

genericAlarmMonitorTable  OBJECT-TYPE
	SYNTAX SEQUENCE OF GenericAlarmMonitorEntry
	MAX-ACCESS not-accessible
	STATUS     current
	DESCRIPTION 
		"generic alarm monitors to be used with 3rd-party modbus devices"
	::= { controlSystem 26 }

genericAlarmMonitorEntry  OBJECT-TYPE
	SYNTAX 	GenericAlarmMonitorEntry
	MAX-ACCESS not-accessible
	STATUS     current
	DESCRIPTION 
		""
	INDEX { genericAlarmMonitorIndex }
	::= { genericAlarmMonitorTable 1 }

GenericAlarmMonitorEntry ::= SEQUENCE {
	genericAlarmMonitorIndex
		Integer32,
	genericAlarmMonitorStatus
		INTEGER,
	genericAlarmMonitorDescription
		DisplayString,
	genericAlarmMonitorTrapRepeatCounter
		Counter32,
	genericAlarmMonitorAlarmEnable
		INTEGER,
	genericAlarmMonitorValue
		Integer32,
	genericAlarmMonitorUnit
		DisplayString
}

genericAlarmMonitorIndex  OBJECT-TYPE
	SYNTAX     Integer32 (1..100)
	MAX-ACCESS not-accessible
	STATUS     current
	DESCRIPTION 
		""
	::= { genericAlarmMonitorEntry 1 }

genericAlarmMonitorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The state of the alarm monitor can be either one of the defined enumerated values"
	::= { genericAlarmMonitorEntry 2 }

genericAlarmMonitorDescription  OBJECT-TYPE
	SYNTAX     DisplayString (SIZE(0..16))
	MAX-ACCESS read-write
	STATUS     current
	DESCRIPTION 
		"A textual description of the generic alarm monitor. This is stored in the system controller
		and can be changed by the user. "
	::= { genericAlarmMonitorEntry 3 }

genericAlarmMonitorTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { genericAlarmMonitorEntry 4 }

genericAlarmMonitorAlarmEnable  OBJECT-TYPE
	SYNTAX     INTEGER {
		disabled (0),
		enabled (1)
	}
	MAX-ACCESS read-write
	STATUS     current
	DESCRIPTION 
		"This value once enabled, the alarm condition of the monitor will be reported."
	::= { genericAlarmMonitorEntry 5 }

genericAlarmMonitorValue  OBJECT-TYPE
	SYNTAX     Integer32 (0..9999)
	MAX-ACCESS read-only
	STATUS     current
	DESCRIPTION 
		"The generic alarm monitor value. Scale is dependent on the scale setting of the corresponding generic modbus value."
	::= { genericAlarmMonitorEntry 6 }

genericAlarmMonitorUnit  OBJECT-TYPE
	SYNTAX     DisplayString (SIZE(0..16))
	MAX-ACCESS read-only
	STATUS     current
	DESCRIPTION 
		"A textual description of the unit of generic alarm monitor. "
	::= { genericAlarmMonitorEntry 7 }

genericLogsTable  OBJECT-TYPE
	SYNTAX SEQUENCE OF GenericLogsEntry
	MAX-ACCESS not-accessible
	STATUS     current
	DESCRIPTION 
		"Generic logs connected to the last ten generic alarm monitors (#91-#100)"
	::= { controlSystem 27 }

genericLogsEntry  OBJECT-TYPE
	SYNTAX 	GenericLogsEntry
	MAX-ACCESS not-accessible
	STATUS     current
	DESCRIPTION 
		""
	INDEX { genericLogsIndex }
	::= { genericLogsTable 1 }

GenericLogsEntry ::= SEQUENCE {
	genericLogsIndex
		Integer32,
	genericLogsAccumulated
		Unsigned32,
	genericLogsDaysNumberOfEntries
		Integer32,
	genericLogsWeeksNumberOfEntries
		Integer32,
	genericLogsMonthsNumberOfEntries
		Integer32
}

genericLogsIndex  OBJECT-TYPE
	SYNTAX     Integer32 (1..10)
	MAX-ACCESS not-accessible
	STATUS     current
	DESCRIPTION 
		"generic log index 1...10"
	::= { genericLogsEntry 1 }

genericLogsAccumulated  OBJECT-TYPE
	SYNTAX     Unsigned32
	MAX-ACCESS read-only
	STATUS     current
	DESCRIPTION 
		"This is the accumulated trip log value in hours."
	::= { genericLogsEntry 2 }

genericLogsDaysNumberOfEntries  OBJECT-TYPE
	SYNTAX     Integer32
	MAX-ACCESS read-only
	STATUS     current
	DESCRIPTION 
		"This is the maximal number of entries stored in daily log"
	::= { genericLogsEntry 3 }

genericLogsWeeksNumberOfEntries  OBJECT-TYPE
	SYNTAX     Integer32
	MAX-ACCESS read-only
	STATUS     current
	DESCRIPTION 
		"This is the maximal number of entries stored in weekly log"
	::= { genericLogsEntry 4 }

genericLogsMonthsNumberOfEntries  OBJECT-TYPE
	SYNTAX     Integer32
	MAX-ACCESS read-only
	STATUS     current
	DESCRIPTION 
		"This is the maximal number of entries stored in monthly log"
	::= { genericLogsEntry 5 }

genericLogDaysTable  OBJECT-TYPE
	SYNTAX SEQUENCE OF GenericLogDaysEntry
	MAX-ACCESS not-accessible
	STATUS     current
	DESCRIPTION 
		"This table contains daily generic log."
	::= { controlSystem 28 }

genericLogDaysEntry  OBJECT-TYPE
	SYNTAX 	GenericLogDaysEntry
	MAX-ACCESS not-accessible
	STATUS     current
	DESCRIPTION 
		""
	INDEX { genericLogsIndex, 
		genericLogDaysIndex }
	::= { genericLogDaysTable 1 }

GenericLogDaysEntry ::= SEQUENCE {
	genericLogDaysIndex
		Unsigned32,
	genericLogDaysValue
		Integer32
}

genericLogDaysIndex  OBJECT-TYPE
	SYNTAX     Unsigned32 (1..52)
	MAX-ACCESS not-accessible
	STATUS     current
	DESCRIPTION 
		"Index used for navigating the rows 1..52  of genericLogDaysTable"
	::= { genericLogDaysEntry 1 }

genericLogDaysValue  OBJECT-TYPE
	SYNTAX     Integer32
	MAX-ACCESS read-only
	STATUS     current
	DESCRIPTION 
		"generic monitor value in minutes logged every day."
	::= { genericLogDaysEntry 2 }

genericLogWeeksTable  OBJECT-TYPE
	SYNTAX SEQUENCE OF GenericLogWeeksEntry
	MAX-ACCESS not-accessible
	STATUS     current
	DESCRIPTION 
		"This table contains weekly generic log."
	::= { controlSystem 29 }

genericLogWeeksEntry  OBJECT-TYPE
	SYNTAX 	GenericLogWeeksEntry
	MAX-ACCESS not-accessible
	STATUS     current
	DESCRIPTION 
		""
	INDEX { genericLogsIndex, 
		genericLogWeeksIndex }
	::= { genericLogWeeksTable 1 }

GenericLogWeeksEntry ::= SEQUENCE {
	genericLogWeeksIndex
		Unsigned32,
	genericLogWeeksValue
		Integer32
}

genericLogWeeksIndex  OBJECT-TYPE
	SYNTAX     Unsigned32 (1..52)
	MAX-ACCESS not-accessible
	STATUS     current
	DESCRIPTION 
		"Index used for navigating the rows 1..52  of genericLogWeeksTable"
	::= { genericLogWeeksEntry 1 }

genericLogWeeksValue  OBJECT-TYPE
	SYNTAX     Integer32
	MAX-ACCESS read-only
	STATUS     current
	DESCRIPTION 
		"generic monitor value in hours logged every week."
	::= { genericLogWeeksEntry 2 }

genericLogMonthsTable  OBJECT-TYPE
	SYNTAX SEQUENCE OF GenericLogMonthsEntry
	MAX-ACCESS not-accessible
	STATUS     current
	DESCRIPTION 
		"This table contains monthly generic log."
	::= { controlSystem 30 }

genericLogMonthsEntry  OBJECT-TYPE
	SYNTAX 	GenericLogMonthsEntry
	MAX-ACCESS not-accessible
	STATUS     current
	DESCRIPTION 
		""
	INDEX { genericLogsIndex, 
		genericLogMonthsIndex }
	::= { genericLogMonthsTable 1 }

GenericLogMonthsEntry ::= SEQUENCE {
	genericLogMonthsIndex
		Unsigned32,
	genericLogMonthsValue
		Integer32
}

genericLogMonthsIndex  OBJECT-TYPE
	SYNTAX     Unsigned32 (1..52)
	MAX-ACCESS not-accessible
	STATUS     current
	DESCRIPTION 
		"Index used for navigating the rows 1..52  of genericLogMonthsTable"
	::= { genericLogMonthsEntry 1 }

genericLogMonthsValue  OBJECT-TYPE
	SYNTAX     Integer32
	MAX-ACCESS read-only
	STATUS     current
	DESCRIPTION 
		"generic monitor value in hours logged every month."
	::= { genericLogMonthsEntry 2 }

tariffControlEnable  OBJECT-TYPE
	SYNTAX     INTEGER {
		diasable (0),
		enable (1)
	}
	MAX-ACCESS read-write
	STATUS     current
	DESCRIPTION 
		"Enable/disable tariff control function"
	::= { tariffControl 1 }

tariffControlChargeInhibit  OBJECT-TYPE
	SYNTAX     INTEGER {
		disable (0),
		enable (1)
	}
	MAX-ACCESS read-write
	STATUS     current
	DESCRIPTION 
		"Enable/disable battery charge inhibit"
	::= { tariffControl 2 }

tariffControlMaxTime  OBJECT-TYPE
	SYNTAX     Integer32
	MAX-ACCESS read-write
	STATUS     current
	DESCRIPTION 
		"The maximum discharge duration in minutes"
	::= { tariffControl 3 }

tariffControlBatteryVoltageStopControl  OBJECT-TYPE
	SYNTAX     INTEGER {
		disable (0),
		enable (1)
	}
	MAX-ACCESS read-write
	STATUS     current
	DESCRIPTION 
		"Enable/disable battery voltage stop control"
	::= { tariffControl 4 }

tariffControlBatteryVoltageStopLimit  OBJECT-TYPE
	SYNTAX     Integer32
	MAX-ACCESS read-write
	STATUS     current
	DESCRIPTION 
		""
	::= { tariffControl 5 }

tariffControlBatteryVoltageHysteresis  OBJECT-TYPE
	SYNTAX     Integer32
	MAX-ACCESS read-write
	STATUS     current
	DESCRIPTION 
		""
	::= { tariffControl 6 }

tariffControlActivate  OBJECT-TYPE
	SYNTAX     INTEGER {
		pushButton (0),
		activate (1),
		deactivate (2)
	}
	MAX-ACCESS read-write
	STATUS     current
	DESCRIPTION 
		"Activate/deactivate demand response"
	::= { tariffControl 7 }

alarmGroupTable  OBJECT-TYPE
	SYNTAX SEQUENCE OF AlarmGroupEntry
	MAX-ACCESS not-accessible
	STATUS     current
	DESCRIPTION 
		""
	::= { alarmGroups 1 }

alarmGroupEntry  OBJECT-TYPE
	SYNTAX 	AlarmGroupEntry
	MAX-ACCESS not-accessible
	STATUS     current
	DESCRIPTION 
		""
	INDEX { alarmGroupIndex }
	::= { alarmGroupTable 1 }

AlarmGroupEntry ::= SEQUENCE {
	alarmGroupIndex
		Integer32,
	alarmGroupStatus
		INTEGER,
	alarmGroupDescription
		DisplayString
}

alarmGroupIndex  OBJECT-TYPE
	SYNTAX     Integer32 (1..49)
	MAX-ACCESS not-accessible
	STATUS     current
	DESCRIPTION 
		"Index used for navigating the rows 1..49 of alarmGroupTable"
	::= { alarmGroupEntry 1 }

alarmGroupStatus  OBJECT-TYPE
	SYNTAX     INTEGER {
		normal (0),
		alarm (1)
	}
	MAX-ACCESS read-only
	STATUS     current
	DESCRIPTION 
		"The status of alarm group"
	::= { alarmGroupEntry 2 }

alarmGroupDescription  OBJECT-TYPE
	SYNTAX     DisplayString (SIZE(0..16))
	MAX-ACCESS read-write
	STATUS     current
	DESCRIPTION 
		"A textual description of the alarm group. This is stored in the system controller
		and can be changed by the user."
	::= { alarmGroupEntry 3 }

-- The reported status of the battery group 2 subsystem. The status reflects the condition 
-- of all underlying alarm monitors in the battery group 2 subsystem

batteryGroup2Status  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"A toplevel status for the battery group 2.The state of this reflects the status of all 
		underlying statuses for the battery. Any change in one of the 'data monitors' in 
		the battery subsystem will propagate up to this status indicator."
	::= { batteryGroup2 1 }

batteryGroup2Description  OBJECT-TYPE
	SYNTAX     DisplayString (SIZE(0..32))
	MAX-ACCESS read-write
	STATUS     current
	DESCRIPTION 
		"A descriptive name of the battery installed in the battery group 2."
	::= { batteryGroup2 2 }

batteryGroup2ReferenceVoltage  OBJECT-TYPE
	SYNTAX     Integer32 (840..60417)
	MAX-ACCESS read-write
	STATUS     current
	DESCRIPTION 
		"The reference voltage of battery group 2."
	::= { batteryGroup2 3 }

batteryGroup2FusesStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The state of the battery fuses/breakers can mainly be normal(1) or majorAlarm(3) and  
		some other rarely used values ."
	::= { batteryGroup2 4 }

-- The status value for the measured battery voltage. If the battery voltage reach outside 
-- the limits set by the major/minor low/high level settings this status will change accordingly.

batteryGroup2VoltageStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured battery voltage."
	::= { batteryGroup2Voltage 1 }

batteryGroup2VoltageDescription  OBJECT-TYPE
	SYNTAX     DisplayString (SIZE(0..16))
	MAX-ACCESS read-write
	STATUS     current
	DESCRIPTION 
		"A textual description of the battery voltage monitor. This is stored in the system controller
		and can be changed by the user.  "
	::= { batteryGroup2Voltage 2 }

batteryGroup2VoltageTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { batteryGroup2Voltage 3 }

batteryGroup2VoltageAlarmEnable  OBJECT-TYPE
	SYNTAX     INTEGER {
		disabled (0),
		enabled (1)
	}
	MAX-ACCESS read-write
	STATUS     current
	DESCRIPTION 
		"The measured battery voltage alarm enable/disable control"
	::= { batteryGroup2Voltage 4 }

batteryGroup2VoltageValue  OBJECT-TYPE
	SYNTAX     Integer32
	MAX-ACCESS read-only
	STATUS     current
	DESCRIPTION 
		"The value of the measured battery voltage.Scale is 0.01v."
	::= { batteryGroup2Voltage 5 }

batteryGroup2VoltageMajorHighLevel  OBJECT-TYPE
	SYNTAX     Integer32
	MAX-ACCESS read-write
	STATUS     current
	DESCRIPTION 
		"The Major High Battery Voltage alarm limit set voltage.Scale is 0.01v."
	::= { batteryGroup2Voltage 6 }

batteryGroup2VoltageMinorHighLevel  OBJECT-TYPE
	SYNTAX     Integer32
	MAX-ACCESS read-write
	STATUS     current
	DESCRIPTION 
		"The Minor High Battery Voltage alarm limit set voltage.Scale is 0.01v."
	::= { batteryGroup2Voltage 7 }

batteryGroup2VoltageMinorLowLevel  OBJECT-TYPE
	SYNTAX     Integer32
	MAX-ACCESS read-write
	STATUS     current
	DESCRIPTION 
		"The Minor Low Battery Voltage alarm limit set voltage.Scale is 0.01v."
	::= { batteryGroup2Voltage 8 }

batteryGroup2VoltageMajorLowLevel  OBJECT-TYPE
	SYNTAX     Integer32
	MAX-ACCESS read-write
	STATUS     current
	DESCRIPTION 
		"The Major Low Battery Voltage alarm limit set voltage.Scale is 0.01v."
	::= { batteryGroup2Voltage 9 }

batteryGroup2CurrentsStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured battery current"
	::= { batteryGroup2Currents 1 }

batteryGroup2CurrentsDescription  OBJECT-TYPE
	SYNTAX     DisplayString (SIZE(0..16))
	MAX-ACCESS read-write
	STATUS     current
	DESCRIPTION 
		"A textual description of the battery current monitor. This is stored in the system controller
		and can be changed by the user.  "
	::= { batteryGroup2Currents 2 }

batteryGroup2CurrentsTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryGroup2Currents 3 }

batteryGroup2CurrentsAlarmEnable  OBJECT-TYPE
	SYNTAX     INTEGER {
		disabled (0),
		enabled (1)
	}
	MAX-ACCESS read-write
	STATUS     current
	DESCRIPTION 
		"This value once enabled, the alarm condition of the monitor will be reported."
	::= { batteryGroup2Currents 4 }

batteryGroup2CurrentsValue  OBJECT-TYPE
	SYNTAX     Integer32
	MAX-ACCESS read-only
	STATUS     current
	DESCRIPTION 
		"The measured total battery current.
		This is the sum of all the enabled shunt measurements in the system.
		Negative battery current indicates discharging of the batteries.
		Positive battery current indicates charging of the batteries.
		Note that the units measured may be i Amperes or in Deciamperes depending on global system settings"
	::= { batteryGroup2Currents 5 }

batteryGroup2CurrentsMajorHighLevel  OBJECT-TYPE
	SYNTAX     Integer32
	MAX-ACCESS read-write
	STATUS     current
	DESCRIPTION 
		"The major high alarm limit"
	::= { batteryGroup2Currents 6 }

batteryGroup2CurrentsMinorHighLevel  OBJECT-TYPE
	SYNTAX     Integer32
	MAX-ACCESS read-write
	STATUS     current
	DESCRIPTION 
		"The minor high alarm limit"
	::= { batteryGroup2Currents 7 }

batteryGroup2CurrentsMinorLowLevel  OBJECT-TYPE
	SYNTAX     Integer32
	MAX-ACCESS read-write
	STATUS     current
	DESCRIPTION 
		"The minor low alarm limit"
	::= { batteryGroup2Currents 8 }

batteryGroup2CurrentsMajorLowLevel  OBJECT-TYPE
	SYNTAX     Integer32
	MAX-ACCESS read-write
	STATUS     current
	DESCRIPTION 
		"The major low alarm limit"
	::= { batteryGroup2Currents 9 }

batteryGroup2TemperaturesStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The state of the battery fuses/breakers can be either one of the defined enumerated values"
	::= { batteryGroup2Temperatures 1 }

batteryGroup2TemperaturesDescription  OBJECT-TYPE
	SYNTAX     DisplayString (SIZE(0..16))
	MAX-ACCESS read-write
	STATUS     current
	DESCRIPTION 
		"A textual description of the battery temperature monitor. This is stored in the system controller
		and can be changed by the user. "
	::= { batteryGroup2Temperatures 2 }

batteryGroup2TemperaturesTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { batteryGroup2Temperatures 3 }

batteryGroup2TemperaturesAlarmEnable  OBJECT-TYPE
	SYNTAX     INTEGER {
		disabled (0),
		enabled (1)
	}
	MAX-ACCESS read-write
	STATUS     current
	DESCRIPTION 
		"This value once enabled, the alarm condition of the monitor will be reported."
	::= { batteryGroup2Temperatures 4 }

batteryGroup2TemperaturesValue  OBJECT-TYPE
	SYNTAX     Integer32 (0..9999)
	MAX-ACCESS read-only
	STATUS     current
	DESCRIPTION 
		"The highest value of the enabled battery temperature measurements.
		Depending on the global setting in the Control unit, this value will be presented in Celsius
		or Fahrenheit."
	::= { batteryGroup2Temperatures 5 }

batteryGroup2TemperaturesMajorHighLevel  OBJECT-TYPE
	SYNTAX     Integer32
	MAX-ACCESS read-write
	STATUS     current
	DESCRIPTION 
		"The major high alarm limit"
	::= { batteryGroup2Temperatures 6 }

batteryGroup2TemperaturesMinorHighLevel  OBJECT-TYPE
	SYNTAX     Integer32
	MAX-ACCESS read-write
	STATUS     current
	DESCRIPTION 
		"The minor high alarm limit"
	::= { batteryGroup2Temperatures 7 }

batteryGroup2TemperaturesMinorLowLevel  OBJECT-TYPE
	SYNTAX     Integer32
	MAX-ACCESS read-write
	STATUS     current
	DESCRIPTION 
		"The minor low alarm limit"
	::= { batteryGroup2Temperatures 8 }

batteryGroup2TemperaturesMajorLowLevel  OBJECT-TYPE
	SYNTAX     Integer32
	MAX-ACCESS read-write
	STATUS     current
	DESCRIPTION 
		"The major low alarm limit"
	::= { batteryGroup2Temperatures 9 }

batteryGroup2TimeLeftStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the estimated battery remaining backup time."
	::= { batteryGroup2TimeLeft 1 }

batteryGroup2TimeLeftDescription  OBJECT-TYPE
	SYNTAX     DisplayString (SIZE(0..16))
	MAX-ACCESS read-write
	STATUS     current
	DESCRIPTION 
		"A textual description of the battery discharge time monitor. This is stored in the system controller
		and can be changed by the user.  "
	::= { batteryGroup2TimeLeft 2 }

batteryGroup2TimeLeftTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryGroup2TimeLeft 3 }

batteryGroup2TimeLeftAlarmEnable  OBJECT-TYPE
	SYNTAX     INTEGER {
		disabled (0),
		enabled (1)
	}
	MAX-ACCESS read-write
	STATUS     current
	DESCRIPTION 
		"This value once enabled, the alarm condition of the monitor will be reported."
	::= { batteryGroup2TimeLeft 4 }

batteryGroup2TimeLeftValue  OBJECT-TYPE
	SYNTAX     Integer32
	MAX-ACCESS read-only
	STATUS     current
	DESCRIPTION 
		"The estimated value of battery remaining backup time."
	::= { batteryGroup2TimeLeft 5 }

batteryGroup2TimeLeftMinorAlarmLevel  OBJECT-TYPE
	SYNTAX     Integer32
	MAX-ACCESS read-write
	STATUS     current
	DESCRIPTION 
		"The minor alarm limit"
	::= { batteryGroup2TimeLeft 6 }

batteryGroup2TimeLeftMajorAlarmLevel  OBJECT-TYPE
	SYNTAX     Integer32
	MAX-ACCESS read-write
	STATUS     current
	DESCRIPTION 
		"The major alarm limit"
	::= { batteryGroup2TimeLeft 7 }

batteryGroup2RemainingCapacityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the battery remaining capacity monitor."
	::= { batteryGroup2RemainingCapacity 1 }

batteryGroup2RemainingCapacityDescription  OBJECT-TYPE
	SYNTAX     DisplayString (SIZE(0..16))
	MAX-ACCESS read-write
	STATUS     current
	DESCRIPTION 
		"A textual description of the battery remaining capacity monitor. This is stored in the system controller
		and can be changed by the user."
	::= { batteryGroup2RemainingCapacity 2 }

batteryGroup2RemainingCapacityTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryGroup2RemainingCapacity 3 }

batteryGroup2RemainingCapacityAlarmEnable  OBJECT-TYPE
	SYNTAX     INTEGER {
		disabled (0),
		enabled (1)
	}
	MAX-ACCESS read-write
	STATUS     current
	DESCRIPTION 
		"This value once enabled, the alarm condition of the monitor will be reported."
	::= { batteryGroup2RemainingCapacity 4 }

batteryGroup2RemainingCapacityValue  OBJECT-TYPE
	SYNTAX     Integer32
	MAX-ACCESS read-only
	STATUS     current
	DESCRIPTION 
		"Battery remaining capacity (SOC) value estimated from the latest battery test result."
	::= { batteryGroup2RemainingCapacity 5 }

batteryGroup2RemainingCapacityMinorLowLevel  OBJECT-TYPE
	SYNTAX     Integer32
	MAX-ACCESS read-write
	STATUS     current
	DESCRIPTION 
		"The minor low alarm limit"
	::= { batteryGroup2RemainingCapacity 6 }

batteryGroup2RemainingCapacityMajorLowLevel  OBJECT-TYPE
	SYNTAX     Integer32
	MAX-ACCESS read-write
	STATUS     current
	DESCRIPTION 
		"The major low alarm limit"
	::= { batteryGroup2RemainingCapacity 7 }

batteryGroup2UsedCapacityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the battery used capacity (DoD) monitor"
	::= { batteryGroup2UsedCapacity 1 }

batteryGroup2UsedCapacityDescription  OBJECT-TYPE
	SYNTAX     DisplayString (SIZE(0..16))
	MAX-ACCESS read-write
	STATUS     current
	DESCRIPTION 
		"A textual description of the battery used capacity (DoD) monitor. This is stored in the system controller
		and can be changed by the user.  "
	::= { batteryGroup2UsedCapacity 2 }

batteryGroup2UsedCapacityTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryGroup2UsedCapacity 3 }

batteryGroup2UsedCapacityAlarmEnable  OBJECT-TYPE
	SYNTAX     INTEGER {
		disabled (0),
		enabled (1)
	}
	MAX-ACCESS read-write
	STATUS     current
	DESCRIPTION 
		"This value once enabled, the alarm condition of the monitor will be reported."
	::= { batteryGroup2UsedCapacity 4 }

batteryGroup2UsedCapacityValue  OBJECT-TYPE
	SYNTAX     Integer32
	MAX-ACCESS read-only
	STATUS     current
	DESCRIPTION 
		"This is the estimated battery used capacity (DoD)."
	::= { batteryGroup2UsedCapacity 5 }

batteryGroup2UsedCapacityMajorAlarmLevel  OBJECT-TYPE
	SYNTAX     Integer32
	MAX-ACCESS read-write
	STATUS     current
	DESCRIPTION 
		"The major alarm limit"
	::= { batteryGroup2UsedCapacity 6 }

batteryGroup2UsedCapacityMinorAlarmLevel  OBJECT-TYPE
	SYNTAX     Integer32
	MAX-ACCESS read-write
	STATUS     current
	DESCRIPTION 
		"The minor alarm limit"
	::= { batteryGroup2UsedCapacity 7 }

batteryGroup2TotalCapacityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the total capacity monitor."
	::= { batteryGroup2TotalCapacity 1 }

batteryGroup2TotalCapacityDescription  OBJECT-TYPE
	SYNTAX     DisplayString (SIZE(0..16))
	MAX-ACCESS read-write
	STATUS     current
	DESCRIPTION 
		"A textual description of the battery total capacity monitor. This is stored in the system controller
		and can be changed by the user"
	::= { batteryGroup2TotalCapacity 2 }

batteryGroup2TotalCapacityTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryGroup2TotalCapacity 3 }

batteryGroup2TotalCapacityAlarmEnable  OBJECT-TYPE
	SYNTAX     INTEGER {
		disabled (0),
		enabled (1)
	}
	MAX-ACCESS read-write
	STATUS     current
	DESCRIPTION 
		"This value once enabled, the alarm condition of the monitor will be reported."
	::= { batteryGroup2TotalCapacity 4 }

batteryGroup2TotalCapacityValue  OBJECT-TYPE
	SYNTAX     Integer32
	MAX-ACCESS read-only
	STATUS     current
	DESCRIPTION 
		"This is the estimated total battery capacity (installed Ah - SoH) value."
	::= { batteryGroup2TotalCapacity 5 }

batteryGroup2TotalCapacityMinorLowLevel  OBJECT-TYPE
	SYNTAX     Integer32
	MAX-ACCESS read-write
	STATUS     current
	DESCRIPTION 
		"The minor low alarm limit"
	::= { batteryGroup2TotalCapacity 6 }

batteryGroup2TotalCapacityMajorLowLevel  OBJECT-TYPE
	SYNTAX     Integer32
	MAX-ACCESS read-write
	STATUS     current
	DESCRIPTION 
		"The major low alarm limit"
	::= { batteryGroup2TotalCapacity 7 }

batteryGroup2QualityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the battery quality (SoH) monitor."
	::= { batteryGroup2Quality 1 }

batteryGroup2QualityDescription  OBJECT-TYPE
	SYNTAX     DisplayString (SIZE(0..16))
	MAX-ACCESS read-write
	STATUS     current
	DESCRIPTION 
		"A textual description of the battery quality (SoH) monitor. This is stored in the system controller
		and can be changed by the user"
	::= { batteryGroup2Quality 2 }

batteryGroup2QualityTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { batteryGroup2Quality 3 }

batteryGroup2QualityAlarmEnable  OBJECT-TYPE
	SYNTAX     INTEGER {
		disabled (0),
		enabled (1)
	}
	MAX-ACCESS read-write
	STATUS     current
	DESCRIPTION 
		"This value once enabled, the alarm condition of the monitor will be reported."
	::= { batteryGroup2Quality 4 }

batteryGroup2QualityValue  OBJECT-TYPE
	SYNTAX     Integer32
	MAX-ACCESS read-only
	STATUS     current
	DESCRIPTION 
		"The calculated battery quality (SoH) based on the latest battery test"
	::= { batteryGroup2Quality 5 }

batteryGroup2QualityMinorAlarmLevel  OBJECT-TYPE
	SYNTAX     Integer32
	MAX-ACCESS read-write
	STATUS     current
	DESCRIPTION 
		"The minor alarm limit"
	::= { batteryGroup2Quality 6 }

batteryGroup2QualityMajorAlarmLevel  OBJECT-TYPE
	SYNTAX     Integer32
	MAX-ACCESS read-write
	STATUS     current
	DESCRIPTION 
		"The major alarm limit"
	::= { batteryGroup2Quality 7 }

batteryGroup2LVBDStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The Battery Contactor is connected, disconnected, disabled or in any other alarm condition"
	::= { batteryGroup2LVBD 1 }

batteryGroup2LVBDDescription  OBJECT-TYPE
	SYNTAX     DisplayString (SIZE(0..16))
	MAX-ACCESS read-write
	STATUS     current
	DESCRIPTION 
		"A textual description of the battery LVBD monitor. This is stored in the system controller
		and can be changed by the user.  "
	::= { batteryGroup2LVBD 2 }

batteryGroup2LVBDTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryGroup2LVBD 3 }

batteryGroup2LVBDEnable  OBJECT-TYPE
	SYNTAX     INTEGER {
		disabled (0),
		enabled (1)
	}
	MAX-ACCESS read-write
	STATUS     current
	DESCRIPTION 
		"This value once enabled, the alarm condition of the LVBD will be reported."
	::= { batteryGroup2LVBD 4 }

batteryGroup2LVBDValue  OBJECT-TYPE
	SYNTAX     Integer32
	MAX-ACCESS read-only
	STATUS     current
	DESCRIPTION 
		"The measured value of the LVBD."
	::= { batteryGroup2LVBD 5 }

batteryGroup2LVBDConnectVoltage  OBJECT-TYPE
	SYNTAX     Integer32
	MAX-ACCESS read-write
	STATUS     current
	DESCRIPTION 
		"The Battery Contactor's Reconnect Voltage"
	::= { batteryGroup2LVBD 6 }

batteryGroup2LVBDDisconnectVoltage  OBJECT-TYPE
	SYNTAX     Integer32
	MAX-ACCESS read-write
	STATUS     current
	DESCRIPTION 
		"The Battery Contactor's Disconnect Voltage"
	::= { batteryGroup2LVBD 7 }

batteryGroup2ChargeCurrentLimitEnable  OBJECT-TYPE
	SYNTAX     INTEGER {
		disabled (0),
		enabled (1)
	}
	MAX-ACCESS read-write
	STATUS     current
	DESCRIPTION 
		"Enable/disable of the battery charge current limitation feature; 0=disable, 1=enable."
	::= { batteryGroup2ChargeCurrentLimit 1 }

batteryGroup2ChargeCurrentLimitValue  OBJECT-TYPE
	SYNTAX     Integer32 (0..32767)
	MAX-ACCESS read-write
	STATUS     current
	DESCRIPTION 
		"Battery charging current limit value. Used only when AC source is mains feed.
		Note that the units measured may be i Amperes or in Deciamperes depending on global system settings"
	::= { batteryGroup2ChargeCurrentLimit 2 }

batteryGroup2BoostVoltage  OBJECT-TYPE
	SYNTAX     Integer32 (870..60418)
	MAX-ACCESS read-write
	STATUS     current
	DESCRIPTION 
		"The Voltage at which the DC System boost charges the batteries."
	::= { batteryGroup2Boost 1 }

batteryGroup2BoostCommand  OBJECT-TYPE
	SYNTAX     INTEGER {
		pushbutton (0),
		startboost (1),
		stopboost (2)
	}
	MAX-ACCESS read-write
	STATUS     current
	DESCRIPTION 
		"This pushbutton will start or stop a manual battery boost if the system allows it."
	::= { batteryGroup2Boost 2 }

batteryGroup2BoostCurrentThreshold  OBJECT-TYPE
	SYNTAX     Integer32
	MAX-ACCESS read-write
	STATUS     current
	DESCRIPTION 
		"The boosting will terminate when the charge current drops below the BoostCurrentThreshold limit."
	::= { batteryGroup2Boost 3 }

batteryGroup2BoostManualMaxDuration  OBJECT-TYPE
	SYNTAX     Integer32 (0..1440)
	MAX-ACCESS read-write
	STATUS     current
	DESCRIPTION 
		"A protection against overcharging.  
		When running manual boost, the boosting will always terminate at this point.  "
	::= { batteryGroup2Boost 4 }

batteryGroup2TestVoltage  OBJECT-TYPE
	SYNTAX     Integer32
	MAX-ACCESS read-write
	STATUS     current
	DESCRIPTION 
		"This is the battery test end voltage. The battery test will be terminated when the voltage
		drops below the end voltage."
	::= { batteryGroup2Test 1 }

batteryGroup2TestCommand  OBJECT-TYPE
	SYNTAX     INTEGER {
		pushbutton (0),
		starttest (1),
		stoptest (2)
	}
	MAX-ACCESS read-write
	STATUS     current
	DESCRIPTION 
		"This pushbutton will start or stop a manual battery test if the system allows it."
	::= { batteryGroup2Test 2 }

batteryGroup2TestNumberOfResults  OBJECT-TYPE
	SYNTAX     Integer32 (0..10)
	MAX-ACCESS read-only
	STATUS     current
	DESCRIPTION 
		"This is the number of valid battery test results stored in controller."
	::= { batteryGroup2Test 3 }

batteryGroup2TestResultTable  OBJECT-TYPE
	SYNTAX SEQUENCE OF BatteryGroup2TestResultEntry
	MAX-ACCESS not-accessible
	STATUS     current
	DESCRIPTION 
		"This table contains the battery test results stored in controller."
	::= { batteryGroup2Test 4 }

batteryGroup2TestResultEntry  OBJECT-TYPE
	SYNTAX 	BatteryGroup2TestResultEntry
	MAX-ACCESS not-accessible
	STATUS     current
	DESCRIPTION 
		""
	INDEX { batteryGroup2TestResultIndex }
	::= { batteryGroup2TestResultTable 1 }

BatteryGroup2TestResultEntry ::= SEQUENCE {
	batteryGroup2TestResultIndex
		Integer32,
	batteryGroup2TestResultStartDateTime
		DateAndTime,
	batteryGroup2TestResultDuration
		Integer32,
	batteryGroup2TestResultDischarged
		Integer32,
	batteryGroup2TestResultQuality
		Integer32,
	batteryGroup2TestResultEndVoltage
		Integer32,
	batteryGroup2TestResultTestResult
		INTEGER,
	batteryGroup2TestResultTerminationCriteria
		INTEGER,
	batteryGroup2TestResultBatteryTemperature
		Integer32
}

batteryGroup2TestResultIndex  OBJECT-TYPE
	SYNTAX     Integer32 (1..10)
	MAX-ACCESS not-accessible
	STATUS     current
	DESCRIPTION 
		"A index pointing to one of ten possible battery test results"
	::= { batteryGroup2TestResultEntry 1 }

batteryGroup2TestResultStartDateTime  OBJECT-TYPE
	SYNTAX     DateAndTime
	MAX-ACCESS read-only
	STATUS     current
	DESCRIPTION 
		"This is the time and date when the test started."
	::= { batteryGroup2TestResultEntry 2 }

batteryGroup2TestResultDuration  OBJECT-TYPE
	SYNTAX     Integer32
	MAX-ACCESS read-only
	STATUS     current
	DESCRIPTION 
		"This is the test duration in minutes."
	::= { batteryGroup2TestResultEntry 3 }

batteryGroup2TestResultDischarged  OBJECT-TYPE
	SYNTAX     Integer32
	MAX-ACCESS read-only
	STATUS     current
	DESCRIPTION 
		"This is the discharged Ah during test."
	::= { batteryGroup2TestResultEntry 4 }

batteryGroup2TestResultQuality  OBJECT-TYPE
	SYNTAX     Integer32
	MAX-ACCESS read-only
	STATUS     current
	DESCRIPTION 
		"This is the calculated battery quality (SoH)in percentage."
	::= { batteryGroup2TestResultEntry 5 }

batteryGroup2TestResultEndVoltage  OBJECT-TYPE
	SYNTAX     Integer32
	MAX-ACCESS read-only
	STATUS     current
	DESCRIPTION 
		"This is the test end voltage in volt."
	::= { batteryGroup2TestResultEntry 6 }

batteryGroup2TestResultTestResult  OBJECT-TYPE
	SYNTAX     INTEGER {
		error (0),
		normal (1),
		minorHigh (2),
		majorHigh (3),
		disable (4),
		disconnect (5),
		reconnect (6),
		critical (7),
		majorLow (8),
		minorLow (9)
	}
	MAX-ACCESS read-only
	STATUS     current
	DESCRIPTION 
		"This is the test result."
	::= { batteryGroup2TestResultEntry 7 }

batteryGroup2TestResultTerminationCriteria  OBJECT-TYPE
	SYNTAX     INTEGER {
		na (0),
		endVoltage (1),
		endTime (2),
		userCancel (3),
		mainsCancel (4),
		endAh (5)
	}
	MAX-ACCESS read-only
	STATUS     current
	DESCRIPTION 
		"This is the test Termination Criteria."
	::= { batteryGroup2TestResultEntry 8 }

batteryGroup2TestResultBatteryTemperature  OBJECT-TYPE
	SYNTAX     Integer32
	MAX-ACCESS read-only
	STATUS     current
	DESCRIPTION 
		"This is the battery temperature"
	::= { batteryGroup2TestResultEntry 9 }

batteryGroup2TestDuration  OBJECT-TYPE
	SYNTAX     Unsigned32
	MAX-ACCESS read-write
	STATUS     current
	DESCRIPTION 
		"This is the battery test max duration. "
	::= { batteryGroup2Test 5 }

batteryGroup2TestCfgTestType  OBJECT-TYPE
	SYNTAX     INTEGER {
		normalTest (0),
		simplifiedTest (1)
	}
	MAX-ACCESS read-write
	STATUS     current
	DESCRIPTION 
		"This is to configurate normal or simplified battery test."
	::= { batteryGroup2Test 6 }

batteryGroup2TestEnableMaxDuration  OBJECT-TYPE
	SYNTAX     INTEGER {
		disabled (0),
		enabled (1)
	}
	MAX-ACCESS read-write
	STATUS     current
	DESCRIPTION 
		"This is to enable/disable battery test max duration."
	::= { batteryGroup2Test 7 }

batteryGroup2TempCompEnable  OBJECT-TYPE
	SYNTAX     INTEGER {
		disabled (0),
		enabled (1)
	}
	MAX-ACCESS read-write
	STATUS     current
	DESCRIPTION 
		"Enable (1) or Disable (0)  of Battery Temperature Compensated output regulation mode"
	::= { batteryGroup2TempComp 1 }

batteryGroup2BankStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of battery bank"
	::= { batteryGroup2Bank 1 }

batteryGroup2BankNumberOfTemperatures  OBJECT-TYPE
	SYNTAX     Integer32
	MAX-ACCESS read-only
	STATUS     current
	DESCRIPTION 
		"Number of temperature measurements in battery bank."
	::= { batteryGroup2Bank 2 }

batteryGroup2BankNumberOfCurrents  OBJECT-TYPE
	SYNTAX     Integer32
	MAX-ACCESS read-only
	STATUS     current
	DESCRIPTION 
		"Number of current measurements in battery bank."
	::= { batteryGroup2Bank 3 }

batteryGroup2BankNumberOfFuses  OBJECT-TYPE
	SYNTAX     Integer32
	MAX-ACCESS read-only
	STATUS     current
	DESCRIPTION 
		"Number of fuses installed in battery bank."
	::= { batteryGroup2Bank 4 }

batteryGroup2BankNumberOfSymmetries  OBJECT-TYPE
	SYNTAX     Integer32
	MAX-ACCESS read-only
	STATUS     current
	DESCRIPTION 
		"Number of fuses installed in battery bank."
	::= { batteryGroup2Bank 5 }

batteryGroup2BankTemperatureTable  OBJECT-TYPE
	SYNTAX SEQUENCE OF BatteryGroup2BankTemperatureEntry
	MAX-ACCESS not-accessible
	STATUS     current
	DESCRIPTION 
		""
	::= { batteryGroup2Bank 6 }

batteryGroup2BankTemperatureEntry  OBJECT-TYPE
	SYNTAX 	BatteryGroup2BankTemperatureEntry
	MAX-ACCESS not-accessible
	STATUS     current
	DESCRIPTION 
		""
	INDEX { batteryGroup2TemperatureIndex }
	::= { batteryGroup2BankTemperatureTable 1 }

BatteryGroup2BankTemperatureEntry ::= SEQUENCE {
	batteryGroup2TemperatureIndex
		Integer32,
	batteryGroup2TemperatureStatus
		INTEGER,
	batteryGroup2TemperatureDescription
		DisplayString,
	batteryGroup2TemperatureTrapRepeatCounter
		Counter32,
	batteryGroup2TemperatureAlarmEnable
		INTEGER,
	batteryGroup2TemperatureValue
		Integer32,
	batteryGroup2TemperatureMajorHighLevel
		Integer32,
	batteryGroup2TemperatureMinorHighLevel
		Integer32,
	batteryGroup2TemperatureMinorLowLevel
		Integer32,
	batteryGroup2TemperatureMajorLowLevel
		Integer32
}

batteryGroup2TemperatureIndex  OBJECT-TYPE
	SYNTAX     Integer32 (1..4)
	MAX-ACCESS not-accessible
	STATUS     current
	DESCRIPTION 
		"This index denotes which row in the temperature input table.
		The size of the table is defined by the batteryGroup2BankNumberOfTemperatures   "
	::= { batteryGroup2BankTemperatureEntry 1 }

batteryGroup2TemperatureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery temperature monitor"
	::= { batteryGroup2BankTemperatureEntry 2 }

batteryGroup2TemperatureDescription  OBJECT-TYPE
	SYNTAX     DisplayString (SIZE(0..16))
	MAX-ACCESS read-write
	STATUS     current
	DESCRIPTION 
		"A textual description of the battery temperature monitor. This is stored in the system controller
		and can be changed by the user. "
	::= { batteryGroup2BankTemperatureEntry 3 }

batteryGroup2TemperatureTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryGroup2BankTemperatureEntry 4 }

batteryGroup2TemperatureAlarmEnable  OBJECT-TYPE
	SYNTAX     INTEGER {
		disabled (0),
		enabled (1)
	}
	MAX-ACCESS read-write
	STATUS     current
	DESCRIPTION 
		"This value once enabled, the alarm condition of the monitor will be reported."
	::= { batteryGroup2BankTemperatureEntry 5 }

batteryGroup2TemperatureValue  OBJECT-TYPE
	SYNTAX     Integer32
	MAX-ACCESS read-only
	STATUS     current
	DESCRIPTION 
		"The measured battery temperature."
	::= { batteryGroup2BankTemperatureEntry 6 }

batteryGroup2TemperatureMajorHighLevel  OBJECT-TYPE
	SYNTAX     Integer32
	MAX-ACCESS read-write
	STATUS     current
	DESCRIPTION 
		"The major high alarm limit"
	::= { batteryGroup2BankTemperatureEntry 7 }

batteryGroup2TemperatureMinorHighLevel  OBJECT-TYPE
	SYNTAX     Integer32
	MAX-ACCESS read-write
	STATUS     current
	DESCRIPTION 
		"The minor high alarm limit"
	::= { batteryGroup2BankTemperatureEntry 8 }

batteryGroup2TemperatureMinorLowLevel  OBJECT-TYPE
	SYNTAX     Integer32
	MAX-ACCESS read-write
	STATUS     current
	DESCRIPTION 
		"The minor low alarm limit"
	::= { batteryGroup2BankTemperatureEntry 9 }

batteryGroup2TemperatureMajorLowLevel  OBJECT-TYPE
	SYNTAX     Integer32
	MAX-ACCESS read-write
	STATUS     current
	DESCRIPTION 
		"The major low alarm limit"
	::= { batteryGroup2BankTemperatureEntry 10 }

batteryGroup2BankCurrentTable  OBJECT-TYPE
	SYNTAX SEQUENCE OF BatteryGroup2BankCurrentEntry
	MAX-ACCESS not-accessible
	STATUS     current
	DESCRIPTION 
		""
	::= { batteryGroup2Bank 7 }

batteryGroup2BankCurrentEntry  OBJECT-TYPE
	SYNTAX 	BatteryGroup2BankCurrentEntry
	MAX-ACCESS not-accessible
	STATUS     current
	DESCRIPTION 
		""
	INDEX { batteryGroup2CurrentIndex }
	::= { batteryGroup2BankCurrentTable 1 }

BatteryGroup2BankCurrentEntry ::= SEQUENCE {
	batteryGroup2CurrentIndex
		Integer32,
	batteryGroup2CurrentStatus
		INTEGER,
	batteryGroup2CurrentDescription
		DisplayString,
	batteryGroup2CurrentTrapRepeatCounter
		Counter32,
	batteryGroup2CurrentAlarmEnable
		INTEGER,
	batteryGroup2CurrentValue
		Integer32,
	batteryGroup2CurrentMajorHighLevel
		Integer32,
	batteryGroup2CurrentMinorHighLevel
		Integer32,
	batteryGroup2CurrentMinorLowLevel
		Integer32,
	batteryGroup2CurrentMajorLowLevel
		Integer32
}

batteryGroup2CurrentIndex  OBJECT-TYPE
	SYNTAX     Integer32 (1..4)
	MAX-ACCESS not-accessible
	STATUS     current
	DESCRIPTION 
		"This index denotes which row in the current input table.
		        The size of the table is defined by the system"
	::= { batteryGroup2BankCurrentEntry 1 }

batteryGroup2CurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery current monitor"
	::= { batteryGroup2BankCurrentEntry 2 }

batteryGroup2CurrentDescription  OBJECT-TYPE
	SYNTAX     DisplayString (SIZE(0..16))
	MAX-ACCESS read-write
	STATUS     current
	DESCRIPTION 
		"A textual description of the battery current monitor. This is stored in the system controller
		and can be changed by the user. "
	::= { batteryGroup2BankCurrentEntry 3 }

batteryGroup2CurrentTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryGroup2BankCurrentEntry 4 }

batteryGroup2CurrentAlarmEnable  OBJECT-TYPE
	SYNTAX     INTEGER {
		disabled (0),
		enabled (1)
	}
	MAX-ACCESS read-write
	STATUS     current
	DESCRIPTION 
		"This value once enabled, the alarm condition of the monitor will be reported."
	::= { batteryGroup2BankCurrentEntry 5 }

batteryGroup2CurrentValue  OBJECT-TYPE
	SYNTAX     Integer32
	MAX-ACCESS read-only
	STATUS     current
	DESCRIPTION 
		"The measured battery current"
	::= { batteryGroup2BankCurrentEntry 6 }

batteryGroup2CurrentMajorHighLevel  OBJECT-TYPE
	SYNTAX     Integer32
	MAX-ACCESS read-write
	STATUS     current
	DESCRIPTION 
		"The major high alarm limit"
	::= { batteryGroup2BankCurrentEntry 7 }

batteryGroup2CurrentMinorHighLevel  OBJECT-TYPE
	SYNTAX     Integer32
	MAX-ACCESS read-write
	STATUS     current
	DESCRIPTION 
		"The minor high alarm limit"
	::= { batteryGroup2BankCurrentEntry 8 }

batteryGroup2CurrentMinorLowLevel  OBJECT-TYPE
	SYNTAX     Integer32
	MAX-ACCESS read-write
	STATUS     current
	DESCRIPTION 
		"The minor low alarm limit"
	::= { batteryGroup2BankCurrentEntry 9 }

batteryGroup2CurrentMajorLowLevel  OBJECT-TYPE
	SYNTAX     Integer32
	MAX-ACCESS read-write
	STATUS     current
	DESCRIPTION 
		"The major low alarm limit"
	::= { batteryGroup2BankCurrentEntry 10 }

batteryGroup2BankFuseTable  OBJECT-TYPE
	SYNTAX SEQUENCE OF BatteryGroup2BankFuseEntry
	MAX-ACCESS not-accessible
	STATUS     current
	DESCRIPTION 
		""
	::= { batteryGroup2Bank 8 }

batteryGroup2BankFuseEntry  OBJECT-TYPE
	SYNTAX 	BatteryGroup2BankFuseEntry
	MAX-ACCESS not-accessible
	STATUS     current
	DESCRIPTION 
		""
	INDEX { batteryGroup2FuseIndex }
	::= { batteryGroup2BankFuseTable 1 }

BatteryGroup2BankFuseEntry ::= SEQUENCE {
	batteryGroup2FuseIndex
		Integer32,
	batteryGroup2FuseStatus
		INTEGER,
	batteryGroup2FuseDescription
		DisplayString,
	batteryGroup2FuseTrapRepeatCounter
		Counter32,
	batteryGroup2FuseAlarmEnable
		INTEGER,
	batteryGroup2FuseValue
		Integer32
}

batteryGroup2FuseIndex  OBJECT-TYPE
	SYNTAX     Integer32 (1..4)
	MAX-ACCESS not-accessible
	STATUS     current
	DESCRIPTION 
		"This index denotes which row in the fuse table.
		        The size of the table is defined by the system"
	::= { batteryGroup2BankFuseEntry 1 }

batteryGroup2FuseStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery fuse monitor"
	::= { batteryGroup2BankFuseEntry 2 }

batteryGroup2FuseDescription  OBJECT-TYPE
	SYNTAX     DisplayString (SIZE(0..16))
	MAX-ACCESS read-write
	STATUS     current
	DESCRIPTION 
		"A textual description of the battery fuse monitor. This is stored in the system controller
		and can be changed by the user."
	::= { batteryGroup2BankFuseEntry 3 }

batteryGroup2FuseTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryGroup2BankFuseEntry 4 }

batteryGroup2FuseAlarmEnable  OBJECT-TYPE
	SYNTAX     INTEGER {
		disabled (0),
		enabled (1)
	}
	MAX-ACCESS read-write
	STATUS     current
	DESCRIPTION 
		"This value once enabled, the alarm condition of the monitor will be reported."
	::= { batteryGroup2BankFuseEntry 5 }

batteryGroup2FuseValue  OBJECT-TYPE
	SYNTAX     Integer32
	MAX-ACCESS read-only
	STATUS     current
	DESCRIPTION 
		"The measured value of battery fuse input."
	::= { batteryGroup2BankFuseEntry 6 }

batteryGroup2BankSymmetryTable  OBJECT-TYPE
	SYNTAX SEQUENCE OF BatteryGroup2BankSymmetryEntry
	MAX-ACCESS not-accessible
	STATUS     current
	DESCRIPTION 
		""
	::= { batteryGroup2Bank 9 }

batteryGroup2BankSymmetryEntry  OBJECT-TYPE
	SYNTAX 	BatteryGroup2BankSymmetryEntry
	MAX-ACCESS not-accessible
	STATUS     current
	DESCRIPTION 
		""
	INDEX { batteryGroup2BankSymmetryIndex }
	::= { batteryGroup2BankSymmetryTable 1 }

BatteryGroup2BankSymmetryEntry ::= SEQUENCE {
	batteryGroup2BankSymmetryIndex
		Integer32,
	batteryGroup2BankSymmetryStatus
		INTEGER,
	batteryGroup2BankSymmetryDescription
		DisplayString,
	batteryGroup2BankSymmetryTrapRepeatCounter
		Counter32,
	batteryGroup2BankSymmetryAlarmEnable
		INTEGER,
	batteryGroup2BankSymmetryMeasureValue
		Integer32,
	batteryGroup2BankSymmetryDeltaValue
		Integer32,
	batteryGroup2BankSymmetryMajorAlarmLevel
		Integer32,
	batteryGroup2BankSymmetryMinorAlarmLevel
		Integer32
}

batteryGroup2BankSymmetryIndex  OBJECT-TYPE
	SYNTAX     Integer32 (1..8)
	MAX-ACCESS not-accessible
	STATUS     current
	DESCRIPTION 
		"This index denotes which row in the symmetry input table.
		The size of the table is defined by the batteryMonitorNumberOfSymmetries"
	::= { batteryGroup2BankSymmetryEntry 1 }

batteryGroup2BankSymmetryStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery symmetry monitor"
	::= { batteryGroup2BankSymmetryEntry 2 }

batteryGroup2BankSymmetryDescription  OBJECT-TYPE
	SYNTAX     DisplayString (SIZE(0..16))
	MAX-ACCESS read-write
	STATUS     current
	DESCRIPTION 
		"A textual description of the battery monitor symmetry. This is stored in the system controller
		and can be changed by the user. "
	::= { batteryGroup2BankSymmetryEntry 3 }

batteryGroup2BankSymmetryTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off"
	::= { batteryGroup2BankSymmetryEntry 4 }

batteryGroup2BankSymmetryAlarmEnable  OBJECT-TYPE
	SYNTAX     INTEGER {
		disabled (0),
		enabled (1)
	}
	MAX-ACCESS read-write
	STATUS     current
	DESCRIPTION 
		"This value once enabled, the alarm condition of the monitor will be reported."
	::= { batteryGroup2BankSymmetryEntry 5 }

batteryGroup2BankSymmetryMeasureValue  OBJECT-TYPE
	SYNTAX     Integer32
	MAX-ACCESS read-only
	STATUS     current
	DESCRIPTION 
		"The measured battery symmetry voltage in battery monitor."
	::= { batteryGroup2BankSymmetryEntry 6 }

batteryGroup2BankSymmetryDeltaValue  OBJECT-TYPE
	SYNTAX     Integer32
	MAX-ACCESS read-only
	STATUS     current
	DESCRIPTION 
		"The measured battery symmetry delta voltage in battery monitor."
	::= { batteryGroup2BankSymmetryEntry 7 }

batteryGroup2BankSymmetryMajorAlarmLevel  OBJECT-TYPE
	SYNTAX     Integer32
	MAX-ACCESS read-write
	STATUS     current
	DESCRIPTION 
		"The major alarm limit"
	::= { batteryGroup2BankSymmetryEntry 8 }

batteryGroup2BankSymmetryMinorAlarmLevel  OBJECT-TYPE
	SYNTAX     Integer32
	MAX-ACCESS read-write
	STATUS     current
	DESCRIPTION 
		"The minor alarm limit"
	::= { batteryGroup2BankSymmetryEntry 9 }

batteryGroup2EnergyLogAccumulated  OBJECT-TYPE
	SYNTAX     Integer32
	MAX-ACCESS read-only
	STATUS     current
	DESCRIPTION 
		"This is the accumulated energy delivered to/from battery."
	::= { batteryGroup2EnergyLog 1 }

batteryGroup2EnergyLogLastHoursNumberOfEntries  OBJECT-TYPE
	SYNTAX     Integer32 (0..52)
	MAX-ACCESS read-only
	STATUS     current
	DESCRIPTION 
		"This is the maximal number of entries stored in battery hourly energy log."
	::= { batteryGroup2EnergyLog 2 }

batteryGroup2EnergyLogLastHoursTable  OBJECT-TYPE
	SYNTAX SEQUENCE OF BatteryGroup2EnergyLogLastHoursEntry
	MAX-ACCESS not-accessible
	STATUS     current
	DESCRIPTION 
		"This table contains hourly energy log of battery."
	::= { batteryGroup2EnergyLog 3 }

batteryGroup2EnergyLogLastHoursEntry  OBJECT-TYPE
	SYNTAX 	BatteryGroup2EnergyLogLastHoursEntry
	MAX-ACCESS not-accessible
	STATUS     current
	DESCRIPTION 
		""
	INDEX { batteryGroup2EnergyLogLastHoursIndex }
	::= { batteryGroup2EnergyLogLastHoursTable 1 }

BatteryGroup2EnergyLogLastHoursEntry ::= SEQUENCE {
	batteryGroup2EnergyLogLastHoursIndex
		Integer32,
	batteryGroup2EnergyLogLastHoursValue
		Integer32
}

batteryGroup2EnergyLogLastHoursIndex  OBJECT-TYPE
	SYNTAX     Integer32 (1..52)
	MAX-ACCESS not-accessible
	STATUS     current
	DESCRIPTION 
		"Index used for navigating the rows 1..52  of batteryEnergyLogLastHoursTable"
	::= { batteryGroup2EnergyLogLastHoursEntry 1 }

batteryGroup2EnergyLogLastHoursValue  OBJECT-TYPE
	SYNTAX     Integer32
	MAX-ACCESS read-only
	STATUS     current
	DESCRIPTION 
		"Energy value logged every hour."
	::= { batteryGroup2EnergyLogLastHoursEntry 2 }

batteryGroup2EnergyLogLastDaysNumberOfEntries  OBJECT-TYPE
	SYNTAX     Integer32 (0..52)
	MAX-ACCESS read-only
	STATUS     current
	DESCRIPTION 
		"This is the maximal number of entries stored in battery daily energy log."
	::= { batteryGroup2EnergyLog 4 }

batteryGroup2EnergyLogLastDaysTable  OBJECT-TYPE
	SYNTAX SEQUENCE OF BatteryGroup2EnergyLogLastDaysEntry
	MAX-ACCESS not-accessible
	STATUS     current
	DESCRIPTION 
		"This table contains daily energy log of battery."
	::= { batteryGroup2EnergyLog 5 }

batteryGroup2EnergyLogLastDaysEntry  OBJECT-TYPE
	SYNTAX 	BatteryGroup2EnergyLogLastDaysEntry
	MAX-ACCESS not-accessible
	STATUS     current
	DESCRIPTION 
		""
	INDEX { batteryGroup2EnergyLogLastDaysIndex }
	::= { batteryGroup2EnergyLogLastDaysTable 1 }

BatteryGroup2EnergyLogLastDaysEntry ::= SEQUENCE {
	batteryGroup2EnergyLogLastDaysIndex
		Integer32,
	batteryGroup2EnergyLogLastDaysValue
		Integer32
}

batteryGroup2EnergyLogLastDaysIndex  OBJECT-TYPE
	SYNTAX     Integer32 (1..52)
	MAX-ACCESS not-accessible
	STATUS     current
	DESCRIPTION 
		"Index used for navigating the rows 1..52  of batteryEnergyLogLastDaysTable"
	::= { batteryGroup2EnergyLogLastDaysEntry 1 }

batteryGroup2EnergyLogLastDaysValue  OBJECT-TYPE
	SYNTAX     Integer32
	MAX-ACCESS read-only
	STATUS     current
	DESCRIPTION 
		"Energy value logged every day."
	::= { batteryGroup2EnergyLogLastDaysEntry 2 }

batteryGroup2EnergyLogLastWeeksNumberOfEntries  OBJECT-TYPE
	SYNTAX     Integer32 (0..52)
	MAX-ACCESS read-only
	STATUS     current
	DESCRIPTION 
		"This is the maximal number of entries stored in battery weekly energy log."
	::= { batteryGroup2EnergyLog 6 }

batteryGroup2EnergyLogLastWeeksTable  OBJECT-TYPE
	SYNTAX SEQUENCE OF BatteryGroup2EnergyLogLastWeeksEntry
	MAX-ACCESS not-accessible
	STATUS     current
	DESCRIPTION 
		"This table contains weekly energy log of battery."
	::= { batteryGroup2EnergyLog 7 }

batteryGroup2EnergyLogLastWeeksEntry  OBJECT-TYPE
	SYNTAX 	BatteryGroup2EnergyLogLastWeeksEntry
	MAX-ACCESS not-accessible
	STATUS     current
	DESCRIPTION 
		""
	INDEX { batteryGroup2EnergyLogLastWeeksIndex }
	::= { batteryGroup2EnergyLogLastWeeksTable 1 }

BatteryGroup2EnergyLogLastWeeksEntry ::= SEQUENCE {
	batteryGroup2EnergyLogLastWeeksIndex
		Integer32,
	batteryGroup2EnergyLogLastWeeksValue
		Integer32
}

batteryGroup2EnergyLogLastWeeksIndex  OBJECT-TYPE
	SYNTAX     Integer32 (1..52)
	MAX-ACCESS not-accessible
	STATUS     current
	DESCRIPTION 
		"Index used for navigating the rows 1..52  of batteryEnergyLogLastWeekTable"
	::= { batteryGroup2EnergyLogLastWeeksEntry 1 }

batteryGroup2EnergyLogLastWeeksValue  OBJECT-TYPE
	SYNTAX     Integer32
	MAX-ACCESS read-only
	STATUS     current
	DESCRIPTION 
		"Energy value logged every week."
	::= { batteryGroup2EnergyLogLastWeeksEntry 2 }

batteryGroup2CycleLogTotalCycles  OBJECT-TYPE
	SYNTAX     Integer32
	MAX-ACCESS read-only
	STATUS     current
	DESCRIPTION 
		"This is the total number of battery discharge cycles."
	::= { batteryGroup2CycleLog 1 }

batteryGroup2CycleLogDaysNumberOfEntries  OBJECT-TYPE
	SYNTAX     Integer32 (0..52)
	MAX-ACCESS read-only
	STATUS     current
	DESCRIPTION 
		"This is the maximal number of entries stored in daily battery discharge cycle log."
	::= { batteryGroup2CycleLog 2 }

batteryGroup2CycleLogDaysTable  OBJECT-TYPE
	SYNTAX SEQUENCE OF BatteryGroup2CycleLogDaysEntry
	MAX-ACCESS not-accessible
	STATUS     current
	DESCRIPTION 
		"This table contains daily battery discharge cycle log."
	::= { batteryGroup2CycleLog 3 }

batteryGroup2CycleLogDaysEntry  OBJECT-TYPE
	SYNTAX 	BatteryGroup2CycleLogDaysEntry
	MAX-ACCESS not-accessible
	STATUS     current
	DESCRIPTION 
		""
	INDEX { batteryGroup2CycleLogDaysIndex }
	::= { batteryGroup2CycleLogDaysTable 1 }

BatteryGroup2CycleLogDaysEntry ::= SEQUENCE {
	batteryGroup2CycleLogDaysIndex
		Integer32,
	batteryGroup2CycleLogDaysValue
		Integer32
}

batteryGroup2CycleLogDaysIndex  OBJECT-TYPE
	SYNTAX     Integer32 (1..52)
	MAX-ACCESS not-accessible
	STATUS     current
	DESCRIPTION 
		"Index used for navigating the rows 1..52  of batteryCycleLogLastDaysTable"
	::= { batteryGroup2CycleLogDaysEntry 1 }

batteryGroup2CycleLogDaysValue  OBJECT-TYPE
	SYNTAX     Integer32
	MAX-ACCESS read-only
	STATUS     current
	DESCRIPTION 
		"Number of discharge cycles logged every day."
	::= { batteryGroup2CycleLogDaysEntry 2 }

batteryGroup2CycleLogWeeksNumberOfEntries  OBJECT-TYPE
	SYNTAX     Integer32 (0..52)
	MAX-ACCESS read-only
	STATUS     current
	DESCRIPTION 
		"This is the maximal number of entries stored in weeky battery discharge cycle log."
	::= { batteryGroup2CycleLog 4 }

batteryGroup2CycleLogWeeksTable  OBJECT-TYPE
	SYNTAX SEQUENCE OF BatteryGroup2CycleLogWeeksEntry
	MAX-ACCESS not-accessible
	STATUS     current
	DESCRIPTION 
		"This table contains weekly battery discharge cycle log."
	::= { batteryGroup2CycleLog 5 }

batteryGroup2CycleLogWeeksEntry  OBJECT-TYPE
	SYNTAX 	BatteryGroup2CycleLogWeeksEntry
	MAX-ACCESS not-accessible
	STATUS     current
	DESCRIPTION 
		""
	INDEX { batteryGroup2CycleLogWeeksIndex }
	::= { batteryGroup2CycleLogWeeksTable 1 }

BatteryGroup2CycleLogWeeksEntry ::= SEQUENCE {
	batteryGroup2CycleLogWeeksIndex
		Integer32,
	batteryGroup2CycleLogWeeksValue
		Integer32
}

batteryGroup2CycleLogWeeksIndex  OBJECT-TYPE
	SYNTAX     Integer32 (1..52)
	MAX-ACCESS not-accessible
	STATUS     current
	DESCRIPTION 
		"Index used for navigating the rows 1..52  of batteryCycleLogLastWeeksTable"
	::= { batteryGroup2CycleLogWeeksEntry 1 }

batteryGroup2CycleLogWeeksValue  OBJECT-TYPE
	SYNTAX     Integer32
	MAX-ACCESS read-only
	STATUS     current
	DESCRIPTION 
		"Number of discharge cycles logged every week."
	::= { batteryGroup2CycleLogWeeksEntry 2 }

batteryGroup2CycleLogMonthsNumberOfEntries  OBJECT-TYPE
	SYNTAX     Integer32 (0..52)
	MAX-ACCESS read-only
	STATUS     current
	DESCRIPTION 
		"This is the maximal number of entries stored in monthly battery discharge cycle log."
	::= { batteryGroup2CycleLog 6 }

batteryGroup2CycleLogMonthsTable  OBJECT-TYPE
	SYNTAX SEQUENCE OF BatteryGroup2CycleLogMonthsEntry
	MAX-ACCESS not-accessible
	STATUS     current
	DESCRIPTION 
		"This table contains monthly battery discharge cycle log."
	::= { batteryGroup2CycleLog 7 }

batteryGroup2CycleLogMonthsEntry  OBJECT-TYPE
	SYNTAX 	BatteryGroup2CycleLogMonthsEntry
	MAX-ACCESS not-accessible
	STATUS     current
	DESCRIPTION 
		""
	INDEX { batteryGroup2CycleLogMonthsIndex }
	::= { batteryGroup2CycleLogMonthsTable 1 }

BatteryGroup2CycleLogMonthsEntry ::= SEQUENCE {
	batteryGroup2CycleLogMonthsIndex
		Integer32,
	batteryGroup2CycleLogMonthsValue
		Integer32
}

batteryGroup2CycleLogMonthsIndex  OBJECT-TYPE
	SYNTAX     Integer32 (1..52)
	MAX-ACCESS not-accessible
	STATUS     current
	DESCRIPTION 
		"Index used for navigating the rows 1..52  of batteryCycleLogLastMonthTable"
	::= { batteryGroup2CycleLogMonthsEntry 1 }

batteryGroup2CycleLogMonthsValue  OBJECT-TYPE
	SYNTAX     Integer32
	MAX-ACCESS read-only
	STATUS     current
	DESCRIPTION 
		"Number of discharge cycles logged every month."
	::= { batteryGroup2CycleLogMonthsEntry 2 }

batteryGroup2EqualizeVoltage  OBJECT-TYPE
	SYNTAX     Integer32 (870..60418)
	MAX-ACCESS read-write
	STATUS     current
	DESCRIPTION 
		"The Voltage at which the DC System equalize charges the batteries."
	::= { batteryGroup2Equalize 1 }

batteryGroup2EqualizeCommand  OBJECT-TYPE
	SYNTAX     INTEGER {
		pushbutton (0),
		startequalize (1),
		stopequalize (2)
	}
	MAX-ACCESS read-write
	STATUS     current
	DESCRIPTION 
		"This pushbutton will start or stop a manual battery equalize if the system allows it."
	::= { batteryGroup2Equalize 2 }

batteryGroup2EqualizeCurrentThreshold  OBJECT-TYPE
	SYNTAX     Integer32
	MAX-ACCESS read-write
	STATUS     current
	DESCRIPTION 
		"The equalizing will terminate when the charge current drops below the EqualizeCurrentThreshold limit."
	::= { batteryGroup2Equalize 3 }

batteryGroup2EqualizeManualMaxDuration  OBJECT-TYPE
	SYNTAX     Integer32 (0..1440)
	MAX-ACCESS read-write
	STATUS     current
	DESCRIPTION 
		"A protection against overcharging.  
		When running manual equalize, the boosting will always terminate at this point.  "
	::= { batteryGroup2Equalize 4 }

batteryGroup2AhChargedStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the battery ah charged monitor."
	::= { batteryGroup2AhCharged 1 }

batteryGroup2AhChargedDescription  OBJECT-TYPE
	SYNTAX     DisplayString (SIZE(0..16))
	MAX-ACCESS read-write
	STATUS     current
	DESCRIPTION 
		"A textual description of the battery ah charged monitor. This is stored in the system controller
		and can be changed by the user"
	::= { batteryGroup2AhCharged 2 }

batteryGroup2AhChargedTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { batteryGroup2AhCharged 3 }

batteryGroup2AhChargedAlarmEnable  OBJECT-TYPE
	SYNTAX     INTEGER {
		disabled (0),
		enabled (1)
	}
	MAX-ACCESS read-write
	STATUS     current
	DESCRIPTION 
		"This value once enabled, the alarm condition of the monitor will be reported."
	::= { batteryGroup2AhCharged 4 }

batteryGroup2AhChargedValue  OBJECT-TYPE
	SYNTAX     Integer32
	MAX-ACCESS read-only
	STATUS     current
	DESCRIPTION 
		"The calculated battery ah (x100) charged value."
	::= { batteryGroup2AhCharged 5 }

batteryGroup2AhChargedMinorHighLevel  OBJECT-TYPE
	SYNTAX     Integer32
	MAX-ACCESS read-write
	STATUS     current
	DESCRIPTION 
		"The minor high alarm limit"
	::= { batteryGroup2AhCharged 6 }

batteryGroup2AhChargedMajorHighLevel  OBJECT-TYPE
	SYNTAX     Integer32
	MAX-ACCESS read-write
	STATUS     current
	DESCRIPTION 
		"The major high alarm limit"
	::= { batteryGroup2AhCharged 7 }

batteryGroup2AhDischargedStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the battery ah discharged monitor."
	::= { batteryGroup2AhDischarged 1 }

batteryGroup2AhDischargedDescription  OBJECT-TYPE
	SYNTAX     DisplayString (SIZE(0..16))
	MAX-ACCESS read-write
	STATUS     current
	DESCRIPTION 
		"A textual description of the battery ah discharged monitor. This is stored in the system controller
		and can be changed by the user"
	::= { batteryGroup2AhDischarged 2 }

batteryGroup2AhDischargedTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { batteryGroup2AhDischarged 3 }

batteryGroup2AhDischargedAlarmEnable  OBJECT-TYPE
	SYNTAX     INTEGER {
		disabled (0),
		enabled (1)
	}
	MAX-ACCESS read-write
	STATUS     current
	DESCRIPTION 
		"This value once enabled, the alarm condition of the monitor will be reported."
	::= { batteryGroup2AhDischarged 4 }

batteryGroup2AhDischargedValue  OBJECT-TYPE
	SYNTAX     Integer32
	MAX-ACCESS read-only
	STATUS     current
	DESCRIPTION 
		"The calculated battery ah (x100) discharged value."
	::= { batteryGroup2AhDischarged 5 }

batteryGroup2AhDischargedMinorHighLevel  OBJECT-TYPE
	SYNTAX     Integer32
	MAX-ACCESS read-write
	STATUS     current
	DESCRIPTION 
		"The minor high alarm limit"
	::= { batteryGroup2AhDischarged 6 }

batteryGroup2AhDischargedMajorHighLevel  OBJECT-TYPE
	SYNTAX     Integer32
	MAX-ACCESS read-write
	STATUS     current
	DESCRIPTION 
		"The major high alarm limit"
	::= { batteryGroup2AhDischarged 7 }

invertersStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of inverter subsystem."
	::= { inverters 1 }

invertersErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed units is higher than the defined alarm level."
	::= { invertersError 1 }

invertersErrorDescription  OBJECT-TYPE
	SYNTAX     DisplayString (SIZE(0..16))
	MAX-ACCESS read-write
	STATUS     current
	DESCRIPTION 
		"A textual description of the inverter error monitor. This is stored in the system controller
		and can be changed by the user"
	::= { invertersError 2 }

invertersErrorTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { invertersError 3 }

invertersErrorEnable  OBJECT-TYPE
	SYNTAX     INTEGER {
		disabled (0),
		enabled (1)
	}
	MAX-ACCESS read-write
	STATUS     current
	DESCRIPTION 
		"This value once enabled, the alarm condition of the monitor will be reported."
	::= { invertersError 4 }

invertersErrorValue  OBJECT-TYPE
	SYNTAX     Integer32
	MAX-ACCESS read-only
	STATUS     current
	DESCRIPTION 
		"The number of failed inverters."
	::= { invertersError 5 }

invertersErrorMajorAlarmLevel  OBJECT-TYPE
	SYNTAX     Integer32
	MAX-ACCESS read-write
	STATUS     current
	DESCRIPTION 
		"The major alarm limit"
	::= { invertersError 6 }

invertersErrorMinorAlarmLevel  OBJECT-TYPE
	SYNTAX     Integer32
	MAX-ACCESS read-write
	STATUS     current
	DESCRIPTION 
		"The minor alarm limit"
	::= { invertersError 7 }

invertersTemperatureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The state of the rectifier temperature can be either one of the defined enumerated values"
	::= { invertersTemperature 1 }

invertersTemperatureDescription  OBJECT-TYPE
	SYNTAX     DisplayString (SIZE(0..16))
	MAX-ACCESS read-write
	STATUS     current
	DESCRIPTION 
		"A textual description of the rectifier temperature monitor. This is stored in the system controller
		and can be changed by the user. "
	::= { invertersTemperature 2 }

invertersTemperatureTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { invertersTemperature 3 }

invertersTemperatureAlarmEnable  OBJECT-TYPE
	SYNTAX     INTEGER {
		disabled (0),
		enabled (1)
	}
	MAX-ACCESS read-write
	STATUS     current
	DESCRIPTION 
		"This value once enabled, the alarm condition of the monitor will be reported."
	::= { invertersTemperature 4 }

invertersTemperatureValue  OBJECT-TYPE
	SYNTAX     Integer32 (0..9999)
	MAX-ACCESS read-only
	STATUS     current
	DESCRIPTION 
		"The highest value of the rectifier temperature measurements.
		Depending on the global setting in the Control unit, this value will be presented in Celsius
		or Fahrenheit."
	::= { invertersTemperature 5 }

invertersTemperatureMajorHighLevel  OBJECT-TYPE
	SYNTAX     Integer32
	MAX-ACCESS read-write
	STATUS     current
	DESCRIPTION 
		"The major high alarm limit"
	::= { invertersTemperature 6 }

invertersTemperatureMinorHighLevel  OBJECT-TYPE
	SYNTAX     Integer32
	MAX-ACCESS read-write
	STATUS     current
	DESCRIPTION 
		"The minor high alarm limit"
	::= { invertersTemperature 7 }

invertersTemperatureMinorLowLevel  OBJECT-TYPE
	SYNTAX     Integer32
	MAX-ACCESS read-write
	STATUS     current
	DESCRIPTION 
		"The minor low alarm limit"
	::= { invertersTemperature 8 }

invertersTemperatureMajorLowLevel  OBJECT-TYPE
	SYNTAX     Integer32
	MAX-ACCESS read-write
	STATUS     current
	DESCRIPTION 
		"The major low alarm limit"
	::= { invertersTemperature 9 }

invertersAcCurrent1Status  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { invertersAcCurrent1 1 }

invertersAcCurrent1Description  OBJECT-TYPE
	SYNTAX     DisplayString (SIZE(0..16))
	MAX-ACCESS read-write
	STATUS     current
	DESCRIPTION 
		"A textual description of the total rectifier current monitor. This is stored in the system controller
		and can be changed by the user"
	::= { invertersAcCurrent1 2 }

invertersAcCurrent1TrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { invertersAcCurrent1 3 }

invertersAcCurrent1AlarmEnable  OBJECT-TYPE
	SYNTAX     INTEGER {
		disabled (0),
		enabled (1)
	}
	MAX-ACCESS read-write
	STATUS     current
	DESCRIPTION 
		"This value once enabled, the alarm condition of the monitor will be reported."
	::= { invertersAcCurrent1 4 }

invertersAcCurrent1Value  OBJECT-TYPE
	SYNTAX     Integer32
	MAX-ACCESS read-only
	STATUS     current
	DESCRIPTION 
		"The value of the measured total rectifier current."
	::= { invertersAcCurrent1 5 }

invertersAcCurrent1MajorAlarmLevel  OBJECT-TYPE
	SYNTAX     Integer32
	MAX-ACCESS read-write
	STATUS     current
	DESCRIPTION 
		"The major alarm limit"
	::= { invertersAcCurrent1 6 }

invertersAcCurrent1MinorAlarmLevel  OBJECT-TYPE
	SYNTAX     Integer32
	MAX-ACCESS read-write
	STATUS     current
	DESCRIPTION 
		"The minor alarm limit"
	::= { invertersAcCurrent1 7 }

invertersAcCurrent2Status  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { invertersAcCurrent2 1 }

invertersAcCurrent2Description  OBJECT-TYPE
	SYNTAX     DisplayString (SIZE(0..16))
	MAX-ACCESS read-write
	STATUS     current
	DESCRIPTION 
		"A textual description of the total rectifier current monitor. This is stored in the system controller
		and can be changed by the user"
	::= { invertersAcCurrent2 2 }

invertersAcCurrent2TrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { invertersAcCurrent2 3 }

invertersAcCurrent2AlarmEnable  OBJECT-TYPE
	SYNTAX     INTEGER {
		disabled (0),
		enabled (1)
	}
	MAX-ACCESS read-write
	STATUS     current
	DESCRIPTION 
		"This value once enabled, the alarm condition of the monitor will be reported."
	::= { invertersAcCurrent2 4 }

invertersAcCurrent2Value  OBJECT-TYPE
	SYNTAX     Integer32
	MAX-ACCESS read-only
	STATUS     current
	DESCRIPTION 
		"The value of the measured total rectifier current."
	::= { invertersAcCurrent2 5 }

invertersAcCurrent2MajorAlarmLevel  OBJECT-TYPE
	SYNTAX     Integer32
	MAX-ACCESS read-write
	STATUS     current
	DESCRIPTION 
		"The major alarm limit"
	::= { invertersAcCurrent2 6 }

invertersAcCurrent2MinorAlarmLevel  OBJECT-TYPE
	SYNTAX     Integer32
	MAX-ACCESS read-write
	STATUS     current
	DESCRIPTION 
		"The minor alarm limit"
	::= { invertersAcCurrent2 7 }

invertersAcCurrent3Status  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { invertersAcCurrent3 1 }

invertersAcCurrent3Description  OBJECT-TYPE
	SYNTAX     DisplayString (SIZE(0..16))
	MAX-ACCESS read-write
	STATUS     current
	DESCRIPTION 
		"A textual description of the total rectifier current monitor. This is stored in the system controller
		and can be changed by the user"
	::= { invertersAcCurrent3 2 }

invertersAcCurrent3TrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { invertersAcCurrent3 3 }

invertersAcCurrent3AlarmEnable  OBJECT-TYPE
	SYNTAX     INTEGER {
		disabled (0),
		enabled (1)
	}
	MAX-ACCESS read-write
	STATUS     current
	DESCRIPTION 
		"This value once enabled, the alarm condition of the monitor will be reported."
	::= { invertersAcCurrent3 4 }

invertersAcCurrent3Value  OBJECT-TYPE
	SYNTAX     Integer32
	MAX-ACCESS read-only
	STATUS     current
	DESCRIPTION 
		"The value of the measured total rectifier current."
	::= { invertersAcCurrent3 5 }

invertersAcCurrent3MajorAlarmLevel  OBJECT-TYPE
	SYNTAX     Integer32
	MAX-ACCESS read-write
	STATUS     current
	DESCRIPTION 
		"The major alarm limit"
	::= { invertersAcCurrent3 6 }

invertersAcCurrent3MinorAlarmLevel  OBJECT-TYPE
	SYNTAX     Integer32
	MAX-ACCESS read-write
	STATUS     current
	DESCRIPTION 
		"The minor alarm limit"
	::= { invertersAcCurrent3 7 }

invertersAcVoltage1Status  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { invertersAcVoltage1 1 }

invertersAcVoltage1Description  OBJECT-TYPE
	SYNTAX     DisplayString (SIZE(0..16))
	MAX-ACCESS read-write
	STATUS     current
	DESCRIPTION 
		"A textual description of the total rectifier current monitor. This is stored in the system controller
		and can be changed by the user"
	::= { invertersAcVoltage1 2 }

invertersAcVoltage1TrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { invertersAcVoltage1 3 }

invertersAcVoltage1AlarmEnable  OBJECT-TYPE
	SYNTAX     INTEGER {
		disabled (0),
		enabled (1)
	}
	MAX-ACCESS read-write
	STATUS     current
	DESCRIPTION 
		"This value once enabled, the alarm condition of the monitor will be reported."
	::= { invertersAcVoltage1 4 }

invertersAcVoltage1Value  OBJECT-TYPE
	SYNTAX     Integer32
	MAX-ACCESS read-only
	STATUS     current
	DESCRIPTION 
		"The value of the measured total rectifier current."
	::= { invertersAcVoltage1 5 }

invertersAcVoltage1MajorHighLevel  OBJECT-TYPE
	SYNTAX     Integer32
	MAX-ACCESS read-write
	STATUS     current
	DESCRIPTION 
		"The major alarm limit"
	::= { invertersAcVoltage1 6 }

invertersAcVoltage1MinorHighLevel  OBJECT-TYPE
	SYNTAX     Integer32
	MAX-ACCESS read-write
	STATUS     current
	DESCRIPTION 
		"The minor alarm limit"
	::= { invertersAcVoltage1 7 }

invertersAcVoltage1MinorLowLevel  OBJECT-TYPE
	SYNTAX     Integer32
	MAX-ACCESS read-write
	STATUS     current
	DESCRIPTION 
		"The minor alarm limit"
	::= { invertersAcVoltage1 8 }

invertersAcVoltage1MajorLowLevel  OBJECT-TYPE
	SYNTAX     Integer32
	MAX-ACCESS read-write
	STATUS     current
	DESCRIPTION 
		"The minor alarm limit"
	::= { invertersAcVoltage1 9 }

invertersAcVoltage2Status  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { invertersAcVoltage2 1 }

invertersAcVoltage2Description  OBJECT-TYPE
	SYNTAX     DisplayString (SIZE(0..16))
	MAX-ACCESS read-write
	STATUS     current
	DESCRIPTION 
		"A textual description of the total rectifier current monitor. This is stored in the system controller
		and can be changed by the user"
	::= { invertersAcVoltage2 2 }

invertersAcVoltage2TrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { invertersAcVoltage2 3 }

invertersAcVoltage2AlarmEnable  OBJECT-TYPE
	SYNTAX     INTEGER {
		disabled (0),
		enabled (1)
	}
	MAX-ACCESS read-write
	STATUS     current
	DESCRIPTION 
		"This value once enabled, the alarm condition of the monitor will be reported."
	::= { invertersAcVoltage2 4 }

invertersAcVoltage2Value  OBJECT-TYPE
	SYNTAX     Integer32
	MAX-ACCESS read-only
	STATUS     current
	DESCRIPTION 
		"The value of the measured total rectifier current."
	::= { invertersAcVoltage2 5 }

invertersAcVoltage2MajorHighLevel  OBJECT-TYPE
	SYNTAX     Integer32
	MAX-ACCESS read-write
	STATUS     current
	DESCRIPTION 
		"The major alarm limit"
	::= { invertersAcVoltage2 6 }

invertersAcVoltage2MinorHighLevel  OBJECT-TYPE
	SYNTAX     Integer32
	MAX-ACCESS read-write
	STATUS     current
	DESCRIPTION 
		"The minor alarm limit"
	::= { invertersAcVoltage2 7 }

invertersAcVoltage2MinorLowLevel  OBJECT-TYPE
	SYNTAX     Integer32
	MAX-ACCESS read-write
	STATUS     current
	DESCRIPTION 
		"The minor alarm limit"
	::= { invertersAcVoltage2 8 }

invertersAcVoltage2MajorLowLevel  OBJECT-TYPE
	SYNTAX     Integer32
	MAX-ACCESS read-write
	STATUS     current
	DESCRIPTION 
		"The minor alarm limit"
	::= { invertersAcVoltage2 9 }

invertersAcVoltage3Status  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { invertersAcVoltage3 1 }

invertersAcVoltage3Description  OBJECT-TYPE
	SYNTAX     DisplayString (SIZE(0..16))
	MAX-ACCESS read-write
	STATUS     current
	DESCRIPTION 
		"A textual description of the total rectifier current monitor. This is stored in the system controller
		and can be changed by the user"
	::= { invertersAcVoltage3 2 }

invertersAcVoltage3TrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { invertersAcVoltage3 3 }

invertersAcVoltage3AlarmEnable  OBJECT-TYPE
	SYNTAX     INTEGER {
		disabled (0),
		enabled (1)
	}
	MAX-ACCESS read-write
	STATUS     current
	DESCRIPTION 
		"This value once enabled, the alarm condition of the monitor will be reported."
	::= { invertersAcVoltage3 4 }

invertersAcVoltage3Value  OBJECT-TYPE
	SYNTAX     Integer32
	MAX-ACCESS read-only
	STATUS     current
	DESCRIPTION 
		"The value of the measured total rectifier current."
	::= { invertersAcVoltage3 5 }

invertersAcVoltage3MajorHighLevel  OBJECT-TYPE
	SYNTAX     Integer32
	MAX-ACCESS read-write
	STATUS     current
	DESCRIPTION 
		"The major alarm limit"
	::= { invertersAcVoltage3 6 }

invertersAcVoltage3MinorHighLevel  OBJECT-TYPE
	SYNTAX     Integer32
	MAX-ACCESS read-write
	STATUS     current
	DESCRIPTION 
		"The minor alarm limit"
	::= { invertersAcVoltage3 7 }

invertersAcVoltage3MinorLowLevel  OBJECT-TYPE
	SYNTAX     Integer32
	MAX-ACCESS read-write
	STATUS     current
	DESCRIPTION 
		"The minor alarm limit"
	::= { invertersAcVoltage3 8 }

invertersAcVoltage3MajorLowLevel  OBJECT-TYPE
	SYNTAX     Integer32
	MAX-ACCESS read-write
	STATUS     current
	DESCRIPTION 
		"The minor alarm limit"
	::= { invertersAcVoltage3 9 }

invertersAcFrequencyDeviationStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { invertersAcFrequencyDeviation 1 }

invertersAcFrequencyDeviationDescription  OBJECT-TYPE
	SYNTAX     DisplayString (SIZE(0..16))
	MAX-ACCESS read-write
	STATUS     current
	DESCRIPTION 
		"A textual description of the total rectifier current monitor. This is stored in the system controller
		and can be changed by the user"
	::= { invertersAcFrequencyDeviation 2 }

invertersAcFrequencyDeviationTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { invertersAcFrequencyDeviation 3 }

invertersAcFrequencyDeviationAlarmEnable  OBJECT-TYPE
	SYNTAX     INTEGER {
		disabled (0),
		enabled (1)
	}
	MAX-ACCESS read-write
	STATUS     current
	DESCRIPTION 
		"This value once enabled, the alarm condition of the monitor will be reported."
	::= { invertersAcFrequencyDeviation 4 }

invertersAcFrequencyDeviationValue  OBJECT-TYPE
	SYNTAX     Integer32
	MAX-ACCESS read-only
	STATUS     current
	DESCRIPTION 
		"The value of the measured total rectifier current."
	::= { invertersAcFrequencyDeviation 5 }

invertersAcFrequencyDeviationMajorHighLevel  OBJECT-TYPE
	SYNTAX     Integer32
	MAX-ACCESS read-write
	STATUS     current
	DESCRIPTION 
		"The major alarm limit"
	::= { invertersAcFrequencyDeviation 6 }

invertersAcFrequencyDeviationMinorHighLevel  OBJECT-TYPE
	SYNTAX     Integer32
	MAX-ACCESS read-write
	STATUS     current
	DESCRIPTION 
		"The minor alarm limit"
	::= { invertersAcFrequencyDeviation 7 }

invertersAcFrequencyDeviationMinorLowLevel  OBJECT-TYPE
	SYNTAX     Integer32
	MAX-ACCESS read-write
	STATUS     current
	DESCRIPTION 
		"The minor alarm limit"
	::= { invertersAcFrequencyDeviation 8 }

invertersAcFrequencyDeviationMajorLowLevel  OBJECT-TYPE
	SYNTAX     Integer32
	MAX-ACCESS read-write
	STATUS     current
	DESCRIPTION 
		"The major alarm limit"
	::= { invertersAcFrequencyDeviation 9 }

invertersAcFrequency  OBJECT-TYPE
	SYNTAX     Integer32
	MAX-ACCESS read-only
	STATUS     current
	DESCRIPTION 
		""
	::= { inverters 11 }

rectivertersStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of rectifier subsystem."
	::= { rectiverters 1 }

rectivertersDcCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { rectivertersDcCurrent 1 }

rectivertersDcCurrentDescription  OBJECT-TYPE
	SYNTAX     DisplayString (SIZE(0..16))
	MAX-ACCESS read-write
	STATUS     current
	DESCRIPTION 
		"A textual description of the total rectifier current monitor. This is stored in the system controller
		and can be changed by the user"
	::= { rectivertersDcCurrent 2 }

rectivertersDcCurrentTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectivertersDcCurrent 3 }

rectivertersDcCurrentAlarmEnable  OBJECT-TYPE
	SYNTAX     INTEGER {
		disabled (0),
		enabled (1)
	}
	MAX-ACCESS read-write
	STATUS     current
	DESCRIPTION 
		"This value once enabled, the alarm condition of the monitor will be reported."
	::= { rectivertersDcCurrent 4 }

rectivertersDcCurrentValue  OBJECT-TYPE
	SYNTAX     Integer32
	MAX-ACCESS read-only
	STATUS     current
	DESCRIPTION 
		"The value of the measured total rectifier current."
	::= { rectivertersDcCurrent 5 }

rectivertersDcCurrentMajorAlarmLevel  OBJECT-TYPE
	SYNTAX     Integer32
	MAX-ACCESS read-write
	STATUS     current
	DESCRIPTION 
		"The major alarm limit"
	::= { rectivertersDcCurrent 6 }

rectivertersDcCurrentMinorAlarmLevel  OBJECT-TYPE
	SYNTAX     Integer32
	MAX-ACCESS read-write
	STATUS     current
	DESCRIPTION 
		"The minor alarm limit"
	::= { rectivertersDcCurrent 7 }

rectivertersErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed units is higher than the defined alarm level."
	::= { rectivertersError 1 }

rectivertersErrorDescription  OBJECT-TYPE
	SYNTAX     DisplayString (SIZE(0..16))
	MAX-ACCESS read-write
	STATUS     current
	DESCRIPTION 
		"A textual description of the rectifier error monitor. This is stored in the system controller
		and can be changed by the user"
	::= { rectivertersError 2 }

rectivertersErrorTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectivertersError 3 }

rectivertersErrorEnable  OBJECT-TYPE
	SYNTAX     INTEGER {
		disabled (0),
		enabled (1)
	}
	MAX-ACCESS read-write
	STATUS     current
	DESCRIPTION 
		"This value once enabled, the alarm condition of the monitor will be reported."
	::= { rectivertersError 4 }

rectivertersErrorValue  OBJECT-TYPE
	SYNTAX     Integer32
	MAX-ACCESS read-only
	STATUS     current
	DESCRIPTION 
		"The number of failed rectifiers."
	::= { rectivertersError 5 }

rectivertersErrorMajorAlarmLevel  OBJECT-TYPE
	SYNTAX     Integer32
	MAX-ACCESS read-write
	STATUS     current
	DESCRIPTION 
		"The major alarm limit"
	::= { rectivertersError 6 }

rectivertersErrorMinorAlarmLevel  OBJECT-TYPE
	SYNTAX     Integer32
	MAX-ACCESS read-write
	STATUS     current
	DESCRIPTION 
		"The minor alarm limit"
	::= { rectivertersError 7 }

rectivertersTemperatureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The state of the rectifier temperature can be either one of the defined enumerated values"
	::= { rectivertersTemperature 1 }

rectivertersTemperatureDescription  OBJECT-TYPE
	SYNTAX     DisplayString (SIZE(0..16))
	MAX-ACCESS read-write
	STATUS     current
	DESCRIPTION 
		"A textual description of the rectifier temperature monitor. This is stored in the system controller
		and can be changed by the user. "
	::= { rectivertersTemperature 2 }

rectivertersTemperatureTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectivertersTemperature 3 }

rectivertersTemperatureAlarmEnable  OBJECT-TYPE
	SYNTAX     INTEGER {
		disabled (0),
		enabled (1)
	}
	MAX-ACCESS read-write
	STATUS     current
	DESCRIPTION 
		"This value once enabled, the alarm condition of the monitor will be reported."
	::= { rectivertersTemperature 4 }

rectivertersTemperatureValue  OBJECT-TYPE
	SYNTAX     Integer32 (0..9999)
	MAX-ACCESS read-only
	STATUS     current
	DESCRIPTION 
		"The highest value of the rectifier temperature measurements.
		Depending on the global setting in the Control unit, this value will be presented in Celsius
		or Fahrenheit."
	::= { rectivertersTemperature 5 }

rectivertersTemperatureMajorHighLevel  OBJECT-TYPE
	SYNTAX     Integer32
	MAX-ACCESS read-write
	STATUS     current
	DESCRIPTION 
		"The major high alarm limit"
	::= { rectivertersTemperature 6 }

rectivertersTemperatureMinorHighLevel  OBJECT-TYPE
	SYNTAX     Integer32
	MAX-ACCESS read-write
	STATUS     current
	DESCRIPTION 
		"The minor high alarm limit"
	::= { rectivertersTemperature 7 }

rectivertersTemperatureMinorLowLevel  OBJECT-TYPE
	SYNTAX     Integer32
	MAX-ACCESS read-write
	STATUS     current
	DESCRIPTION 
		"The minor low alarm limit"
	::= { rectivertersTemperature 8 }

rectivertersTemperatureMajorLowLevel  OBJECT-TYPE
	SYNTAX     Integer32
	MAX-ACCESS read-write
	STATUS     current
	DESCRIPTION 
		"The major low alarm limit"
	::= { rectivertersTemperature 9 }

rectivertersAcOutCurrent1Status  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { rectivertersAcOutCurrent1 1 }

rectivertersAcOutCurrent1Description  OBJECT-TYPE
	SYNTAX     DisplayString (SIZE(0..16))
	MAX-ACCESS read-write
	STATUS     current
	DESCRIPTION 
		"A textual description of the total rectifier current monitor. This is stored in the system controller
		and can be changed by the user"
	::= { rectivertersAcOutCurrent1 2 }

rectivertersAcOutCurrent1TrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectivertersAcOutCurrent1 3 }

rectivertersAcOutCurrent1AlarmEnable  OBJECT-TYPE
	SYNTAX     INTEGER {
		disabled (0),
		enabled (1)
	}
	MAX-ACCESS read-write
	STATUS     current
	DESCRIPTION 
		"This value once enabled, the alarm condition of the monitor will be reported."
	::= { rectivertersAcOutCurrent1 4 }

rectivertersAcOutCurrent1Value  OBJECT-TYPE
	SYNTAX     Integer32
	MAX-ACCESS read-only
	STATUS     current
	DESCRIPTION 
		"The value of the measured total rectifier current."
	::= { rectivertersAcOutCurrent1 5 }

rectivertersAcOutCurrent1MajorAlarmLevel  OBJECT-TYPE
	SYNTAX     Integer32
	MAX-ACCESS read-write
	STATUS     current
	DESCRIPTION 
		"The major alarm limit"
	::= { rectivertersAcOutCurrent1 6 }

rectivertersAcOutCurrent1MinorAlarmLevel  OBJECT-TYPE
	SYNTAX     Integer32
	MAX-ACCESS read-write
	STATUS     current
	DESCRIPTION 
		"The minor alarm limit"
	::= { rectivertersAcOutCurrent1 7 }

rectivertersAcOutCurrent2Status  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { rectivertersAcOutCurrent2 1 }

rectivertersAcOutCurrent2Description  OBJECT-TYPE
	SYNTAX     DisplayString (SIZE(0..16))
	MAX-ACCESS read-write
	STATUS     current
	DESCRIPTION 
		"A textual description of the total rectifier current monitor. This is stored in the system controller
		and can be changed by the user"
	::= { rectivertersAcOutCurrent2 2 }

rectivertersAcOutCurrent2TrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectivertersAcOutCurrent2 3 }

rectivertersAcOutCurrent2AlarmEnable  OBJECT-TYPE
	SYNTAX     INTEGER {
		disabled (0),
		enabled (1)
	}
	MAX-ACCESS read-write
	STATUS     current
	DESCRIPTION 
		"This value once enabled, the alarm condition of the monitor will be reported."
	::= { rectivertersAcOutCurrent2 4 }

rectivertersAcOutCurrent2Value  OBJECT-TYPE
	SYNTAX     Integer32
	MAX-ACCESS read-only
	STATUS     current
	DESCRIPTION 
		"The value of the measured total rectifier current."
	::= { rectivertersAcOutCurrent2 5 }

rectivertersAcOutCurrent2MajorAlarmLevel  OBJECT-TYPE
	SYNTAX     Integer32
	MAX-ACCESS read-write
	STATUS     current
	DESCRIPTION 
		"The major alarm limit"
	::= { rectivertersAcOutCurrent2 6 }

rectivertersAcOutCurrent2MinorAlarmLevel  OBJECT-TYPE
	SYNTAX     Integer32
	MAX-ACCESS read-write
	STATUS     current
	DESCRIPTION 
		"The minor alarm limit"
	::= { rectivertersAcOutCurrent2 7 }

rectivertersAcOutCurrent3Status  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { rectivertersAcOutCurrent3 1 }

rectivertersAcOutCurrent3Description  OBJECT-TYPE
	SYNTAX     DisplayString (SIZE(0..16))
	MAX-ACCESS read-write
	STATUS     current
	DESCRIPTION 
		"A textual description of the total rectifier current monitor. This is stored in the system controller
		and can be changed by the user"
	::= { rectivertersAcOutCurrent3 2 }

rectivertersAcOutCurrent3TrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectivertersAcOutCurrent3 3 }

rectivertersAcOutCurrent3AlarmEnable  OBJECT-TYPE
	SYNTAX     INTEGER {
		disabled (0),
		enabled (1)
	}
	MAX-ACCESS read-write
	STATUS     current
	DESCRIPTION 
		"This value once enabled, the alarm condition of the monitor will be reported."
	::= { rectivertersAcOutCurrent3 4 }

rectivertersAcOutCurrent3Value  OBJECT-TYPE
	SYNTAX     Integer32
	MAX-ACCESS read-only
	STATUS     current
	DESCRIPTION 
		"The value of the measured total rectifier current."
	::= { rectivertersAcOutCurrent3 5 }

rectivertersAcOutCurrent3MajorAlarmLevel  OBJECT-TYPE
	SYNTAX     Integer32
	MAX-ACCESS read-write
	STATUS     current
	DESCRIPTION 
		"The major alarm limit"
	::= { rectivertersAcOutCurrent3 6 }

rectivertersAcOutCurrent3MinorAlarmLevel  OBJECT-TYPE
	SYNTAX     Integer32
	MAX-ACCESS read-write
	STATUS     current
	DESCRIPTION 
		"The minor alarm limit"
	::= { rectivertersAcOutCurrent3 7 }

rectivertersAcOutVoltage1Status  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { rectivertersAcOutVoltage1 1 }

rectivertersAcOutVoltage1Description  OBJECT-TYPE
	SYNTAX     DisplayString (SIZE(0..16))
	MAX-ACCESS read-write
	STATUS     current
	DESCRIPTION 
		"A textual description of the total rectifier current monitor. This is stored in the system controller
		and can be changed by the user"
	::= { rectivertersAcOutVoltage1 2 }

rectivertersAcOutVoltage1TrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectivertersAcOutVoltage1 3 }

rectivertersAcOutVoltage1AlarmEnable  OBJECT-TYPE
	SYNTAX     INTEGER {
		disabled (0),
		enabled (1)
	}
	MAX-ACCESS read-write
	STATUS     current
	DESCRIPTION 
		"This value once enabled, the alarm condition of the monitor will be reported."
	::= { rectivertersAcOutVoltage1 4 }

rectivertersAcOutVoltage1Value  OBJECT-TYPE
	SYNTAX     Integer32
	MAX-ACCESS read-only
	STATUS     current
	DESCRIPTION 
		"The value of the measured total rectifier current."
	::= { rectivertersAcOutVoltage1 5 }

rectivertersAcOutVoltage1MajorHighLevel  OBJECT-TYPE
	SYNTAX     Integer32
	MAX-ACCESS read-write
	STATUS     current
	DESCRIPTION 
		"The major alarm limit"
	::= { rectivertersAcOutVoltage1 6 }

rectivertersAcOutVoltage1MinorHighLevel  OBJECT-TYPE
	SYNTAX     Integer32
	MAX-ACCESS read-write
	STATUS     current
	DESCRIPTION 
		"The minor alarm limit"
	::= { rectivertersAcOutVoltage1 7 }

rectivertersAcOutVoltage1MinorLowLevel  OBJECT-TYPE
	SYNTAX     Integer32
	MAX-ACCESS read-write
	STATUS     current
	DESCRIPTION 
		"The minor alarm limit"
	::= { rectivertersAcOutVoltage1 8 }

rectivertersAcOutVoltage1MajorLowLevel  OBJECT-TYPE
	SYNTAX     Integer32
	MAX-ACCESS read-write
	STATUS     current
	DESCRIPTION 
		"The major alarm limit"
	::= { rectivertersAcOutVoltage1 9 }

rectivertersAcOutVoltage2Status  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { rectivertersAcOutVoltage2 1 }

rectivertersAcOutVoltage2Description  OBJECT-TYPE
	SYNTAX     DisplayString (SIZE(0..16))
	MAX-ACCESS read-write
	STATUS     current
	DESCRIPTION 
		"A textual description of the total rectifier current monitor. This is stored in the system controller
		and can be changed by the user"
	::= { rectivertersAcOutVoltage2 2 }

rectivertersAcOutVoltage2TrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectivertersAcOutVoltage2 3 }

rectivertersAcOutVoltage2AlarmEnable  OBJECT-TYPE
	SYNTAX     INTEGER {
		disabled (0),
		enabled (1)
	}
	MAX-ACCESS read-write
	STATUS     current
	DESCRIPTION 
		"This value once enabled, the alarm condition of the monitor will be reported."
	::= { rectivertersAcOutVoltage2 4 }

rectivertersAcOutVoltage2Value  OBJECT-TYPE
	SYNTAX     Integer32
	MAX-ACCESS read-only
	STATUS     current
	DESCRIPTION 
		"The value of the measured total rectifier current."
	::= { rectivertersAcOutVoltage2 5 }

rectivertersAcOutVoltage2MajorHighLevel  OBJECT-TYPE
	SYNTAX     Integer32
	MAX-ACCESS read-write
	STATUS     current
	DESCRIPTION 
		"The major alarm limit"
	::= { rectivertersAcOutVoltage2 6 }

rectivertersAcOutVoltage2MinorHighLevel  OBJECT-TYPE
	SYNTAX     Integer32
	MAX-ACCESS read-write
	STATUS     current
	DESCRIPTION 
		"The minor alarm limit"
	::= { rectivertersAcOutVoltage2 7 }

rectivertersAcOutVoltage2MinorLowLevel  OBJECT-TYPE
	SYNTAX     Integer32
	MAX-ACCESS read-write
	STATUS     current
	DESCRIPTION 
		"The minor alarm limit"
	::= { rectivertersAcOutVoltage2 8 }

rectivertersAcOutVoltage2MajorLowLevel  OBJECT-TYPE
	SYNTAX     Integer32
	MAX-ACCESS read-write
	STATUS     current
	DESCRIPTION 
		"The major alarm limit"
	::= { rectivertersAcOutVoltage2 9 }

rectivertersAcOutVoltage3Status  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { rectivertersAcOutVoltage3 1 }

rectivertersAcOutVoltage3Description  OBJECT-TYPE
	SYNTAX     DisplayString (SIZE(0..16))
	MAX-ACCESS read-write
	STATUS     current
	DESCRIPTION 
		"A textual description of the total rectifier current monitor. This is stored in the system controller
		and can be changed by the user"
	::= { rectivertersAcOutVoltage3 2 }

rectivertersAcOutVoltage3TrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectivertersAcOutVoltage3 3 }

rectivertersAcOutVoltage3AlarmEnable  OBJECT-TYPE
	SYNTAX     INTEGER {
		disabled (0),
		enabled (1)
	}
	MAX-ACCESS read-write
	STATUS     current
	DESCRIPTION 
		"This value once enabled, the alarm condition of the monitor will be reported."
	::= { rectivertersAcOutVoltage3 4 }

rectivertersAcOutVoltage3Value  OBJECT-TYPE
	SYNTAX     Integer32
	MAX-ACCESS read-only
	STATUS     current
	DESCRIPTION 
		"The value of the measured total rectifier current."
	::= { rectivertersAcOutVoltage3 5 }

rectivertersAcOutVoltage3MajorHighLevel  OBJECT-TYPE
	SYNTAX     Integer32
	MAX-ACCESS read-write
	STATUS     current
	DESCRIPTION 
		"The major alarm limit"
	::= { rectivertersAcOutVoltage3 6 }

rectivertersAcOutVoltage3MinorHighLevel  OBJECT-TYPE
	SYNTAX     Integer32
	MAX-ACCESS read-write
	STATUS     current
	DESCRIPTION 
		"The minor alarm limit"
	::= { rectivertersAcOutVoltage3 7 }

rectivertersAcOutVoltage3MinorLowLevel  OBJECT-TYPE
	SYNTAX     Integer32
	MAX-ACCESS read-write
	STATUS     current
	DESCRIPTION 
		"The minor alarm limit"
	::= { rectivertersAcOutVoltage3 8 }

rectivertersAcOutVoltage3MajorLowLevel  OBJECT-TYPE
	SYNTAX     Integer32
	MAX-ACCESS read-write
	STATUS     current
	DESCRIPTION 
		"The major alarm limit"
	::= { rectivertersAcOutVoltage3 9 }

rectivertersAcFrequencyDeviationStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { rectivertersAcFrequencyDeviation 1 }

rectivertersAcFrequencyDeviationDescription  OBJECT-TYPE
	SYNTAX     DisplayString (SIZE(0..16))
	MAX-ACCESS read-write
	STATUS     current
	DESCRIPTION 
		"A textual description of the total rectifier current monitor. This is stored in the system controller
		and can be changed by the user"
	::= { rectivertersAcFrequencyDeviation 2 }

rectivertersAcFrequencyDeviationTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectivertersAcFrequencyDeviation 3 }

rectivertersAcFrequencyDeviationAlarmEnable  OBJECT-TYPE
	SYNTAX     INTEGER {
		disabled (0),
		enabled (1)
	}
	MAX-ACCESS read-write
	STATUS     current
	DESCRIPTION 
		"This value once enabled, the alarm condition of the monitor will be reported."
	::= { rectivertersAcFrequencyDeviation 4 }

rectivertersAcFrequencyDeviationValue  OBJECT-TYPE
	SYNTAX     Integer32
	MAX-ACCESS read-only
	STATUS     current
	DESCRIPTION 
		"The value of the measured total rectifier current."
	::= { rectivertersAcFrequencyDeviation 5 }

rectivertersAcFrequencyDeviationMajorHighLevel  OBJECT-TYPE
	SYNTAX     Integer32
	MAX-ACCESS read-write
	STATUS     current
	DESCRIPTION 
		"The major alarm limit"
	::= { rectivertersAcFrequencyDeviation 6 }

rectivertersAcFrequencyDeviationMinorHighLevel  OBJECT-TYPE
	SYNTAX     Integer32
	MAX-ACCESS read-write
	STATUS     current
	DESCRIPTION 
		"The minor alarm limit"
	::= { rectivertersAcFrequencyDeviation 7 }

rectivertersAcFrequencyDeviationMinorLowLevel  OBJECT-TYPE
	SYNTAX     Integer32
	MAX-ACCESS read-write
	STATUS     current
	DESCRIPTION 
		"The minor alarm limit"
	::= { rectivertersAcFrequencyDeviation 8 }

rectivertersAcFrequencyDeviationMajorLowLevel  OBJECT-TYPE
	SYNTAX     Integer32
	MAX-ACCESS read-write
	STATUS     current
	DESCRIPTION 
		"The minor alarm limit"
	::= { rectivertersAcFrequencyDeviation 9 }

rectivertersAcFrequency  OBJECT-TYPE
	SYNTAX     Integer32
	MAX-ACCESS read-only
	STATUS     current
	DESCRIPTION 
		""
	::= { rectiverters 12 }

rectivertersAcOutVoltageConfig  OBJECT-TYPE
	SYNTAX     Integer32 (190..250)
	MAX-ACCESS read-write
	STATUS     current
	DESCRIPTION 
		"Set ac output voltage"
	::= { rectiverters 13 }

rectivertersAcOutFrequencyConfig  OBJECT-TYPE
	SYNTAX     Integer32 (4500..10600)
	MAX-ACCESS read-write
	STATUS     current
	DESCRIPTION 
		"Set ac output frequency. Scale is 0.01 Hz."
	::= { rectiverters 14 }

fuelCellsStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of fuel cell charger subsystem."
	::= { fuelCells 1 }

fuelCellsCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total fuel cell current."
	::= { fuelCellsCurrent 1 }

fuelCellsCurrentDescription  OBJECT-TYPE
	SYNTAX     DisplayString (SIZE(0..16))
	MAX-ACCESS read-write
	STATUS     current
	DESCRIPTION 
		"A textual description of the total fuel cell current monitor. This is stored in the system controller
		and can be changed by the user"
	::= { fuelCellsCurrent 2 }

fuelCellsCurrentTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { fuelCellsCurrent 3 }

fuelCellsCurrentAlarmEnable  OBJECT-TYPE
	SYNTAX     INTEGER {
		disabled (0),
		enabled (1)
	}
	MAX-ACCESS read-write
	STATUS     current
	DESCRIPTION 
		"This value once enabled, the alarm condition of the monitor will be reported."
	::= { fuelCellsCurrent 4 }

fuelCellsCurrentValue  OBJECT-TYPE
	SYNTAX     Integer32
	MAX-ACCESS read-only
	STATUS     current
	DESCRIPTION 
		"The value of the measured total fuel cell current."
	::= { fuelCellsCurrent 5 }

fuelCellsCurrentMajorAlarmLevel  OBJECT-TYPE
	SYNTAX     Integer32
	MAX-ACCESS read-write
	STATUS     current
	DESCRIPTION 
		"The major alarm limit"
	::= { fuelCellsCurrent 6 }

fuelCellsCurrentMinorAlarmLevel  OBJECT-TYPE
	SYNTAX     Integer32
	MAX-ACCESS read-write
	STATUS     current
	DESCRIPTION 
		"The minor alarm limit"
	::= { fuelCellsCurrent 7 }

fuelCellsPowerStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total fuel cell power."
	::= { fuelCellsPower 1 }

fuelCellsPowerDescription  OBJECT-TYPE
	SYNTAX     DisplayString (SIZE(0..16))
	MAX-ACCESS read-write
	STATUS     current
	DESCRIPTION 
		"A textual description of the total fuel cell current monitor. This is stored in the system controller
		and can be changed by the user"
	::= { fuelCellsPower 2 }

fuelCellsPowerTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { fuelCellsPower 3 }

fuelCellsPowerAlarmEnable  OBJECT-TYPE
	SYNTAX     INTEGER {
		disabled (0),
		enabled (1)
	}
	MAX-ACCESS read-write
	STATUS     current
	DESCRIPTION 
		"This value once enabled, the alarm condition of the monitor will be reported."
	::= { fuelCellsPower 4 }

fuelCellsPowerValue  OBJECT-TYPE
	SYNTAX     Integer32
	MAX-ACCESS read-only
	STATUS     current
	DESCRIPTION 
		"The value of the measured total fuel cell power."
	::= { fuelCellsPower 5 }

fuelCellsPowerMajorAlarmLevel  OBJECT-TYPE
	SYNTAX     Integer32
	MAX-ACCESS read-write
	STATUS     current
	DESCRIPTION 
		"The major alarm limit"
	::= { fuelCellsPower 6 }

fuelCellsPowerMinorAlarmLevel  OBJECT-TYPE
	SYNTAX     Integer32
	MAX-ACCESS read-write
	STATUS     current
	DESCRIPTION 
		"The minor alarm limit"
	::= { fuelCellsPower 7 }

fuelCellsErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed units is higher than the defined alarm level."
	::= { fuelCellsError 1 }

fuelCellsErrorDescription  OBJECT-TYPE
	SYNTAX     DisplayString (SIZE(0..16))
	MAX-ACCESS read-write
	STATUS     current
	DESCRIPTION 
		"A textual description of the fuel cell error monitor. This is stored in the system controller
		and can be changed by the user"
	::= { fuelCellsError 2 }

fuelCellsErrorTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { fuelCellsError 3 }

fuelCellsErrorEnable  OBJECT-TYPE
	SYNTAX     INTEGER {
		disabled (0),
		enabled (1)
	}
	MAX-ACCESS read-write
	STATUS     current
	DESCRIPTION 
		"This value once enabled, the alarm condition of the monitor will be reported."
	::= { fuelCellsError 4 }

fuelCellsErrorValue  OBJECT-TYPE
	SYNTAX     Integer32
	MAX-ACCESS read-only
	STATUS     current
	DESCRIPTION 
		"The number of failed fuel cell chargers."
	::= { fuelCellsError 5 }

fuelCellsErrorMajorAlarmLevel  OBJECT-TYPE
	SYNTAX     Integer32
	MAX-ACCESS read-write
	STATUS     current
	DESCRIPTION 
		"The major alarm limit"
	::= { fuelCellsError 6 }

fuelCellsErrorMinorAlarmLevel  OBJECT-TYPE
	SYNTAX     Integer32
	MAX-ACCESS read-write
	STATUS     current
	DESCRIPTION 
		"The minor alarm limit"
	::= { fuelCellsError 7 }

fuelCellsNumberOfFuelCells  OBJECT-TYPE
	SYNTAX     Integer32 (0..100)
	MAX-ACCESS read-write
	STATUS     current
	DESCRIPTION 
		"Number of installed fuel cell chargers."
	::= { fuelCells 5 }

fuelCellTable  OBJECT-TYPE
	SYNTAX SEQUENCE OF FuelCellEntry
	MAX-ACCESS not-accessible
	STATUS     current
	DESCRIPTION 
		"This table shows the information of each fuel cell installed in the system."
	::= { fuelCells 6 }

fuelCellEntry  OBJECT-TYPE
	SYNTAX 	FuelCellEntry
	MAX-ACCESS not-accessible
	STATUS     current
	DESCRIPTION 
		""
	INDEX { fuelCellIndex }
	::= { fuelCellTable 1 }

FuelCellEntry ::= SEQUENCE {
	fuelCellIndex
		Integer32,
	fuelCellStatus
		INTEGER,
	fuelCellMode
		INTEGER,
	fuelCellCurrentValue
		Integer32,
	fuelCellVoltageValue
		Integer32,
	fuelCellPowerValue
		Integer32,
	fuelCellType
		DisplayString,
	fuelCellInletTemperature
		Integer32,
	fuelCellOutletTemperature
		Integer32,
	fuelCellRoomTemperature
		Integer32,
	fuelCellFan
		Integer32,
	fuelCellH2Storage1
		INTEGER,
	fuelCellH2Storage2
		INTEGER,
	fuelCellH2Storage3
		INTEGER,
	fuelCellDO22
		Integer32,
	fuelCellDO23
		Integer32,
	fuelCellDO24
		Integer32,
	fuelCellDO25
		Integer32,
	fuelCellDO26
		Integer32,
	fuelCellDO27
		Integer32,
	fuelCellDC1current
		Integer32,
	fuelCellDC2current
		Integer32,
	fuelCellDC3current
		Integer32,
	fuelCellDC4current
		Integer32,
	fuelCellDC5current
		Integer32,
	fuelCellDC6current
		Integer32
}

fuelCellIndex  OBJECT-TYPE
	SYNTAX     Integer32 (1..100)
	MAX-ACCESS not-accessible
	STATUS     current
	DESCRIPTION 
		"Index used for navigating the rows 1..100 of fuelCellTable"
	::= { fuelCellEntry 1 }

fuelCellStatus  OBJECT-TYPE
	SYNTAX     INTEGER {
		normal (0),
		fileSystemInitError (1),
		rTDBInitError (2),
		rTDBMemAllocError (3),
		datalogMemAllocError (4),
		versionConfigFailed (5),
		loggerConfigError (6),
		diagnostMemoryAllocationError (7),
		diagnostParametersNotFound (8),
		reserved0 (9),
		h2StorageEmpty (10),
		h2Sup1ValveError (11),
		h2Sup2ValveError (12),
		h2Sup3ValveError (13),
		pS1ValveError (14),
		pS2ValveError (15),
		sT1OrPS1ValveError (16),
		sT2OrPS2ValveError (17),
		stack1InputValveError (18),
		stack2InputValveError (19),
		pWMValveError (20),
		h2SupplyValvesError (21),
		menuInitMemoryAllocationError (22),
		reserved1 (23),
		reserved2 (24),
		uiRTDBParamNotFound (25),
		reserved3 (26),
		reserved4 (27),
		pbRTDBParamNotFound (28),
		reserved5 (29),
		validatorMemoryAllocError (30),
		validatorInitTooMuchItems (31),
		validatorNotInitedCorrectly (32),
		xMLParserInitError (33),
		xMLParserError (34),
		dcdcRTDBParamNotFound (35),
		reserved6 (36),
		funcTaskInitFails (37),
		pbConfigurationFailed (38),
		regulatorsConfigFailed (39),
		pbCommunicationError (40),
		pbFLASHError (41),
		pbRAMError (42),
		reserved7 (43),
		pbValvesError (44),
		pbSup1-2ValveError (45),
		pbSup3-InletValveError (46),
		pbSt1_In-PS1ValveError (47),
		pbAux1ValveError (48),
		pbSt2In-PS2ValveError (49),
		pbPWM-Aux2ValveError (50),
		pb5BarSensorError (51),
		pb0dot5BarSensorError (52),
		pbSafetyAlarm (53),
		pbSafetyChainLocked (54),
		reserved8 (55),
		reserved9 (56),
		uiVersionNotSupported (57),
		pbVersionNotSupported (58),
		dcdcVersionNotSupported (59),
		dcdcCommunicationError (60),
		reserved10 (61),
		dcdc-1CommunicationError (62),
		dcdc-2CommunicationError (63),
		dcdc-3CommunicationError (64),
		dcdc-4CommunicationError (65),
		dcdc-5CommunicationError (66),
		dcdc-6CommunicationError (67),
		dcdcConfigError (68),
		dcdcErrorCodeReturned (69),
		systemLockedCallSupport (70),
		bothStacksInBadConditions (71),
		powerNetBootloaderError (72),
		systemTypeNotDefined (73),
		powerNetSettingsError (74),
		noWorkingDCDCLeft (75),
		reserved11 (76),
		selfTestDCDC1-2-3TestLoadError (77),
		reserved12 (78),
		reserved13 (79),
		selfTestDCDC4-5-6TestLoadError (80),
		aUXIOMemoryAllocError (81),
		aUXRTDBParamNotFound (82),
		highExhaustTemperature (83),
		reserved14 (84),
		reserved15 (85),
		reserved16 (86),
		reserved17 (87),
		timeZoneConfigError (88),
		canNotCopyRTDBToFlash (89),
		wrongHWorSWVersionInRTDB (90),
		wrongRTDBInFlash (91),
		noValidRTDBonFlashAndSDcard (92),
		errorLoadingRTDBfromFlash (93)
	}
	MAX-ACCESS read-only
	STATUS     current
	DESCRIPTION 
		"The overall status of fuel cell."
	::= { fuelCellEntry 2 }

fuelCellMode  OBJECT-TYPE
	SYNTAX     INTEGER {
		init (0),
		diagnost (1),
		standBy (2),
		powerUp (3),
		backUp (4),
		powerDown (5),
		selfTest (6),
		override (7),
		shutDown (8),
		safeMode (9),
		safeLock (10)
	}
	MAX-ACCESS read-only
	STATUS     current
	DESCRIPTION 
		"The mode value of fuel cell."
	::= { fuelCellEntry 3 }

fuelCellCurrentValue  OBJECT-TYPE
	SYNTAX     Integer32
	MAX-ACCESS read-only
	STATUS     current
	DESCRIPTION 
		"The output current value of fuel cell."
	::= { fuelCellEntry 4 }

fuelCellVoltageValue  OBJECT-TYPE
	SYNTAX     Integer32
	MAX-ACCESS read-only
	STATUS     current
	DESCRIPTION 
		"The input voltage value of fuel cell."
	::= { fuelCellEntry 5 }

fuelCellPowerValue  OBJECT-TYPE
	SYNTAX     Integer32
	MAX-ACCESS read-only
	STATUS     current
	DESCRIPTION 
		"The input voltage value of fuel cell."
	::= { fuelCellEntry 6 }

fuelCellType  OBJECT-TYPE
	SYNTAX     DisplayString (SIZE(0..27))
	MAX-ACCESS read-only
	STATUS     current
	DESCRIPTION 
		"Type of fuel cell"
	::= { fuelCellEntry 7 }

fuelCellInletTemperature  OBJECT-TYPE
	SYNTAX     Integer32
	MAX-ACCESS read-only
	STATUS     current
	DESCRIPTION 
		"The inlet temp value of fuel cell."
	::= { fuelCellEntry 8 }

fuelCellOutletTemperature  OBJECT-TYPE
	SYNTAX     Integer32
	MAX-ACCESS read-only
	STATUS     current
	DESCRIPTION 
		"The outlet temp value of fuel cell."
	::= { fuelCellEntry 9 }

fuelCellRoomTemperature  OBJECT-TYPE
	SYNTAX     Integer32
	MAX-ACCESS read-only
	STATUS     current
	DESCRIPTION 
		"The room temp value of fuel cell."
	::= { fuelCellEntry 10 }

fuelCellFan  OBJECT-TYPE
	SYNTAX     Integer32
	MAX-ACCESS read-only
	STATUS     current
	DESCRIPTION 
		"The fan value of fuel cell."
	::= { fuelCellEntry 11 }

fuelCellH2Storage1  OBJECT-TYPE
	SYNTAX     INTEGER {
		empty (0),
		full (1)
	}
	MAX-ACCESS read-only
	STATUS     current
	DESCRIPTION 
		"The H2 storage 1 value of fuel cell."
	::= { fuelCellEntry 12 }

fuelCellH2Storage2  OBJECT-TYPE
	SYNTAX     INTEGER {
		empty (0),
		full (1)
	}
	MAX-ACCESS read-only
	STATUS     current
	DESCRIPTION 
		"The H2 storage 2 value of fuel cell."
	::= { fuelCellEntry 13 }

fuelCellH2Storage3  OBJECT-TYPE
	SYNTAX     INTEGER {
		empty (0),
		full (1)
	}
	MAX-ACCESS read-only
	STATUS     current
	DESCRIPTION 
		"The H2 storage 3 value of fuel cell."
	::= { fuelCellEntry 14 }

fuelCellDO22  OBJECT-TYPE
	SYNTAX     Integer32
	MAX-ACCESS read-only
	STATUS     current
	DESCRIPTION 
		"The DO22 value of fuel cell."
	::= { fuelCellEntry 15 }

fuelCellDO23  OBJECT-TYPE
	SYNTAX     Integer32
	MAX-ACCESS read-only
	STATUS     current
	DESCRIPTION 
		"The DO23 value of fuel cell."
	::= { fuelCellEntry 16 }

fuelCellDO24  OBJECT-TYPE
	SYNTAX     Integer32
	MAX-ACCESS read-only
	STATUS     current
	DESCRIPTION 
		"The DO24 value of fuel cell."
	::= { fuelCellEntry 17 }

fuelCellDO25  OBJECT-TYPE
	SYNTAX     Integer32
	MAX-ACCESS read-only
	STATUS     current
	DESCRIPTION 
		"The DO25 value of fuel cell."
	::= { fuelCellEntry 18 }

fuelCellDO26  OBJECT-TYPE
	SYNTAX     Integer32
	MAX-ACCESS read-only
	STATUS     current
	DESCRIPTION 
		"The DO26 value of fuel cell."
	::= { fuelCellEntry 19 }

fuelCellDO27  OBJECT-TYPE
	SYNTAX     Integer32
	MAX-ACCESS read-only
	STATUS     current
	DESCRIPTION 
		"The DO27 value of fuel cell."
	::= { fuelCellEntry 20 }

fuelCellDC1current  OBJECT-TYPE
	SYNTAX     Integer32
	MAX-ACCESS read-only
	STATUS     current
	DESCRIPTION 
		"The DC1 current value of fuel cell."
	::= { fuelCellEntry 21 }

fuelCellDC2current  OBJECT-TYPE
	SYNTAX     Integer32
	MAX-ACCESS read-only
	STATUS     current
	DESCRIPTION 
		"The DC2 current value of fuel cell."
	::= { fuelCellEntry 22 }

fuelCellDC3current  OBJECT-TYPE
	SYNTAX     Integer32
	MAX-ACCESS read-only
	STATUS     current
	DESCRIPTION 
		"The DC3 current value of fuel cell."
	::= { fuelCellEntry 23 }

fuelCellDC4current  OBJECT-TYPE
	SYNTAX     Integer32
	MAX-ACCESS read-only
	STATUS     current
	DESCRIPTION 
		"The DC4 current value of fuel cell."
	::= { fuelCellEntry 24 }

fuelCellDC5current  OBJECT-TYPE
	SYNTAX     Integer32
	MAX-ACCESS read-only
	STATUS     current
	DESCRIPTION 
		"The DC5 current value of fuel cell."
	::= { fuelCellEntry 25 }

fuelCellDC6current  OBJECT-TYPE
	SYNTAX     Integer32
	MAX-ACCESS read-only
	STATUS     current
	DESCRIPTION 
		"The DC6 current value of fuel cell."
	::= { fuelCellEntry 26 }

fuelCellsEnergyLogAccumulated  OBJECT-TYPE
	SYNTAX     Integer32
	MAX-ACCESS read-only
	STATUS     current
	DESCRIPTION 
		"This is the accumulated energy delivered from fuel cell."
	::= { fuelCellsEnergyLog 1 }

fuelCellsEnergyLogLastHoursNumberOfEntries  OBJECT-TYPE
	SYNTAX     Integer32
	MAX-ACCESS read-only
	STATUS     current
	DESCRIPTION 
		"This is the maximal number of entries stored in fuel cell hourly energy log."
	::= { fuelCellsEnergyLog 2 }

fuelCellsEnergyLogLastHoursTable  OBJECT-TYPE
	SYNTAX SEQUENCE OF FuelCellsEnergyLogLastHoursEntry
	MAX-ACCESS not-accessible
	STATUS     current
	DESCRIPTION 
		"This table contains hourly energy log of fuel cell."
	::= { fuelCellsEnergyLog 3 }

fuelCellsEnergyLogLastHoursEntry  OBJECT-TYPE
	SYNTAX 	FuelCellsEnergyLogLastHoursEntry
	MAX-ACCESS not-accessible
	STATUS     current
	DESCRIPTION 
		""
	INDEX { fuelCellsEnergyLogLastHoursIndex }
	::= { fuelCellsEnergyLogLastHoursTable 1 }

FuelCellsEnergyLogLastHoursEntry ::= SEQUENCE {
	fuelCellsEnergyLogLastHoursIndex
		Integer32,
	fuelCellsEnergyLogLastHoursValue
		Integer32
}

fuelCellsEnergyLogLastHoursIndex  OBJECT-TYPE
	SYNTAX     Integer32 (1..52)
	MAX-ACCESS not-accessible
	STATUS     current
	DESCRIPTION 
		"Index used for navigating the rows 1..52 of fuelCellsEnergyLogLastHoursTable"
	::= { fuelCellsEnergyLogLastHoursEntry 1 }

fuelCellsEnergyLogLastHoursValue  OBJECT-TYPE
	SYNTAX     Integer32
	MAX-ACCESS read-only
	STATUS     current
	DESCRIPTION 
		"Energy value logged every hour."
	::= { fuelCellsEnergyLogLastHoursEntry 2 }

fuelCellsEnergyLogLastDaysNumberOfEntries  OBJECT-TYPE
	SYNTAX     Integer32
	MAX-ACCESS read-only
	STATUS     current
	DESCRIPTION 
		"This is the maximal number of entries stored in fuel cell daily energy log."
	::= { fuelCellsEnergyLog 4 }

fuelCellsEnergyLogLastDaysTable  OBJECT-TYPE
	SYNTAX SEQUENCE OF FuelCellsEnergyLogLastDaysEntry
	MAX-ACCESS not-accessible
	STATUS     current
	DESCRIPTION 
		"This table contains daily energy log of fuel cell."
	::= { fuelCellsEnergyLog 5 }

fuelCellsEnergyLogLastDaysEntry  OBJECT-TYPE
	SYNTAX 	FuelCellsEnergyLogLastDaysEntry
	MAX-ACCESS not-accessible
	STATUS     current
	DESCRIPTION 
		""
	INDEX { fuelCellsEnergyLogLastDaysIndex }
	::= { fuelCellsEnergyLogLastDaysTable 1 }

FuelCellsEnergyLogLastDaysEntry ::= SEQUENCE {
	fuelCellsEnergyLogLastDaysIndex
		Integer32,
	fuelCellsEnergyLogLastDaysValue
		Integer32
}

fuelCellsEnergyLogLastDaysIndex  OBJECT-TYPE
	SYNTAX     Integer32 (1..52)
	MAX-ACCESS not-accessible
	STATUS     current
	DESCRIPTION 
		"Index used for navigating the rows 1..52 of fuelCellsEnergyLogLastDaysTable"
	::= { fuelCellsEnergyLogLastDaysEntry 1 }

fuelCellsEnergyLogLastDaysValue  OBJECT-TYPE
	SYNTAX     Integer32
	MAX-ACCESS read-only
	STATUS     current
	DESCRIPTION 
		"Energy value logged every day."
	::= { fuelCellsEnergyLogLastDaysEntry 2 }

fuelCellsEnergyLogLastWeeksNumberOfEntries  OBJECT-TYPE
	SYNTAX     Integer32
	MAX-ACCESS read-only
	STATUS     current
	DESCRIPTION 
		"This is the maximal number of entries stored in fuel cell weekly energy log."
	::= { fuelCellsEnergyLog 6 }

fuelCellsEnergyLogLastWeeksTable  OBJECT-TYPE
	SYNTAX SEQUENCE OF FuelCellsEnergyLogLastWeeksEntry
	MAX-ACCESS not-accessible
	STATUS     current
	DESCRIPTION 
		"This table contains weekly energy log of fuel cell."
	::= { fuelCellsEnergyLog 7 }

fuelCellsEnergyLogLastWeeksEntry  OBJECT-TYPE
	SYNTAX 	FuelCellsEnergyLogLastWeeksEntry
	MAX-ACCESS not-accessible
	STATUS     current
	DESCRIPTION 
		""
	INDEX { fuelCellsEnergyLogLastWeeksIndex }
	::= { fuelCellsEnergyLogLastWeeksTable 1 }

FuelCellsEnergyLogLastWeeksEntry ::= SEQUENCE {
	fuelCellsEnergyLogLastWeeksIndex
		Integer32,
	fuelCellsEnergyLogLastWeeksValue
		Integer32
}

fuelCellsEnergyLogLastWeeksIndex  OBJECT-TYPE
	SYNTAX     Integer32 (1..52)
	MAX-ACCESS not-accessible
	STATUS     current
	DESCRIPTION 
		"Index used for navigating the rows 1..52 of fuelCellsEnergyLogLastWeekTable"
	::= { fuelCellsEnergyLogLastWeeksEntry 1 }

fuelCellsEnergyLogLastWeeksValue  OBJECT-TYPE
	SYNTAX     Integer32
	MAX-ACCESS read-only
	STATUS     current
	DESCRIPTION 
		"Energy value logged every week."
	::= { fuelCellsEnergyLogLastWeeksEntry 2 }

fuelCellsReset  OBJECT-TYPE
	SYNTAX     INTEGER {
		pushbutton (0),
		reset (1)
	}
	MAX-ACCESS read-write
	STATUS     current
	DESCRIPTION 
		""
	::= { fuelCells 8 }

fuelCellsUnlock  OBJECT-TYPE
	SYNTAX     INTEGER {
		pushbutton (0),
		unlock (1)
	}
	MAX-ACCESS read-write
	STATUS     current
	DESCRIPTION 
		""
	::= { fuelCells 9 }

fuelCellsSelfTest  OBJECT-TYPE
	SYNTAX     INTEGER {
		pushbutton (0),
		selfTest (1)
	}
	MAX-ACCESS read-write
	STATUS     current
	DESCRIPTION 
		""
	::= { fuelCells 10 }

powerSystemTrapsGroup  NOTIFICATION-GROUP
	NOTIFICATIONS { alarmBatteryTrap, 
		alarmControlSystemTrap, 
		alarmDcDcTrap, 
		alarmGeneratorTrap, 
		alarmInputsTrap, 
		alarmInverterTrap, 
		alarmLoadGroupTrap, 
		alarmMainsTrap, 
		alarmOutputsTrap, 
		alarmPowerSystemTrap, 
		alarmRectifierTrap, 
		alarmRectiverterTrap, 
		alarmSolarChargerTrap, 
		alarmWindChargerTrap, 
		infoBatteryTestTrap, 
		alarmFuelCellTrap }
	STATUS     current
	DESCRIPTION 
		"The powerSystem Trap goup. Entry point for the trap list."
	::= { eltekTraps 3 }
END


-- This MIB was created using NuDesign Team's Visual MIBuilder (Ver 4.4).
-- EOF EltekSmartPack2-1.1.mib

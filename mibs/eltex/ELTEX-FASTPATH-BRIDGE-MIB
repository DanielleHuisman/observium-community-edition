ELTEX-FASTPATH-BRIDGE-MIB DEFINITIONS ::= BEGIN

IMPORTS
    MODULE-IDENTITY, OBJECT-TYPE         FROM SNMPv2-SMI
    TEXTUAL-CONVENTION                   FROM SNMPv2-TC
    dot1dBasePort                        FROM BRIDGE-MIB
    eltMesFastpath                       FROM ELTEX-MES-FASTPATH-MIB;

eltFastpathBridgeMIB MODULE-IDENTITY
    LAST-UPDATED "201709050000Z"
    ORGANIZATION "Eltex Enterprise Co, Ltd."
    CONTACT-INFO "www.eltex-co.ru"
    DESCRIPTION
        "This private MIB module contains Eltex's port mac address definition."
    -- Revision history.
    REVISION
        "201709050000Z"
    DESCRIPTION
        "Initial revision."
    ::= { eltMesFastpath 3 }

efpBridgeObjects              OBJECT IDENTIFIER ::= { eltFastpathBridgeMIB 1 }

efpBridgeConfigs              OBJECT IDENTIFIER ::= { efpBridgeObjects 2 }

EfpBridgeStpGroupMacAddressType ::= TEXTUAL-CONVENTION
    STATUS          current
    DESCRIPTION         "Type of STP BPDU destination MAC address"
    SYNTAX          INTEGER  {
                                dot1d   (1),  -- Bridge Group Address (01-80-C2-00-00-00)
                                dot1ad  (2),  -- Provider Bridge Group Address (01-80-C2-00-00-08),
                                auto    (3)   -- use Provider Bridge Group Address if port dot1ad mode set to NNI, otherwise Bridge Group Address is used
                             }

efpBridgeConfigsStp           OBJECT IDENTIFIER ::= { efpBridgeConfigs 1 }

efpBridgeStpConfigPortTable OBJECT-TYPE
    SYNTAX          SEQUENCE OF EfpBridgeStpConfigPortEntry
    MAX-ACCESS      not-accessible
    STATUS          current
    DESCRIPTION        "Port configuration table for Spanning Tree Protocol."
    ::= { efpBridgeConfigsStp 1 }

efpBridgeStpConfigPortEntry OBJECT-TYPE
    SYNTAX          EfpBridgeStpConfigPortEntry
    MAX-ACCESS      not-accessible
    STATUS          current
    DESCRIPTION        "Port configuration entry for Spanning Tree Protocol."
    INDEX           { dot1dBasePort }
    ::= { efpBridgeStpConfigPortTable 1 }

EfpBridgeStpConfigPortEntry ::= SEQUENCE {
    efpBridgeStpConfigPortGroupMacAddress  EfpBridgeStpGroupMacAddressType
}

efpBridgeStpConfigPortGroupMacAddress OBJECT-TYPE
    SYNTAX          EfpBridgeStpGroupMacAddressType
    MAX-ACCESS      read-write
    STATUS          current
    DESCRIPTION         "Sets destination MAC address for Bridge PDUs. A port sends
                        and receives BPDUs only with specified group MAC address."
    DEFVAL          { dot1d }
    ::= { efpBridgeStpConfigPortEntry 1 }

efpBridgeNotifications        OBJECT IDENTIFIER ::= { eltFastpathBridgeMIB 2 }

efpBridgeNotificationsPrefix  OBJECT IDENTIFIER ::= { efpBridgeNotifications 0 }

efpBridgeConformance          OBJECT IDENTIFIER ::= { eltFastpathBridgeMIB 3 }

END

ELTEX-FASTPATH-INVENTORY-MIB DEFINITIONS ::= BEGIN

IMPORTS
    MODULE-IDENTITY, OBJECT-TYPE        FROM SNMPv2-SMI
    DisplayString                       FROM SNMPv2-TC
    MODULE-COMPLIANCE, OBJECT-GROUP     FROM SNMPv2-CONF
    agentInventoryUnitEntry             FROM FASTPATH-INVENTORY-MIB
    eltMesFastpath                      FROM ELTEX-MES-FASTPATH-MIB;

eltFastpathInventoryMIB MODULE-IDENTITY
    LAST-UPDATED "201702070000Z"
    ORGANIZATION "Eltex Enterprise Co, Ltd."
    CONTACT-INFO "www.eltex-co.ru"
    DESCRIPTION
        "This MIB defines the objects used for FastPath to
        configure and report information and status of units,
        slots and supported cards (Eltex extensions)."
    REVISION "201702070000Z"
    DESCRIPTION
          "Initial revision."
    ::= { eltMesFastpath 1 }

--**************************************************************************************
-- efpInventoryGlobals
--
--**************************************************************************************

efpInventoryObjects              OBJECT IDENTIFIER ::= { eltFastpathInventoryMIB 1 }

efpInventoryGlobals              OBJECT IDENTIFIER ::= { efpInventoryObjects 1 }

--**************************************************************************************
-- efpAgentInventoryUnitTable
--
--**************************************************************************************

efpAgentInventoryUnitTable OBJECT-TYPE
    SYNTAX         SEQUENCE OF EfpAgentInventoryUnitEntry
    MAX-ACCESS     not-accessible
    STATUS         current
    DESCRIPTION
        "This table augments existing FASTPATH table agentInventoryUnitTable."
    ::= { efpInventoryGlobals 1 }

efpAgentInventoryUnitEntry OBJECT-TYPE
    SYNTAX         EfpAgentInventoryUnitEntry
    MAX-ACCESS     not-accessible
    STATUS         current
    DESCRIPTION
        "Each Instance corresponds with a different unit managed by this agent."
    AUGMENTS       { agentInventoryUnitEntry }
    ::= { efpAgentInventoryUnitTable 1 }

EfpAgentInventoryUnitEntry ::=
    SEQUENCE {
     efpAgentInventoryUnitImage1CommitHash
             DisplayString,
     efpAgentInventoryUnitImage2CommitHash
             DisplayString,
     efpAgentInventoryUnitImage1Timestamp
             DisplayString,
     efpAgentInventoryUnitImage2Timestamp
             DisplayString,
     efpAgentInventoryUnitImage1Md5Digest
             DisplayString,
     efpAgentInventoryUnitImage2Md5Digest
             DisplayString,
     efpAgentInventoryActiveImage
             INTEGER,
     efpAgentInventoryNextActiveImage
             INTEGER
    }

efpAgentInventoryUnitImage1CommitHash OBJECT-TYPE
    SYNTAX      DisplayString (SIZE(0..80))
    MAX-ACCESS  read-only
    STATUS      current
    DESCRIPTION
        "Commit hash for Image1."
    ::= { efpAgentInventoryUnitEntry 1 }

efpAgentInventoryUnitImage2CommitHash OBJECT-TYPE
    SYNTAX      DisplayString (SIZE(0..80))
    MAX-ACCESS  read-only
    STATUS      current
    DESCRIPTION
        "Commit hash for Image2."
    ::= { efpAgentInventoryUnitEntry 2 }

efpAgentInventoryUnitImage1Timestamp OBJECT-TYPE
    SYNTAX      DisplayString (SIZE(0..80))
    MAX-ACCESS  read-only
    STATUS      current
    DESCRIPTION
        "Timestamp for Image1."
    ::= { efpAgentInventoryUnitEntry 3 }

efpAgentInventoryUnitImage2Timestamp OBJECT-TYPE
    SYNTAX      DisplayString (SIZE(0..80))
    MAX-ACCESS  read-only
    STATUS      current
    DESCRIPTION
        "Timestamp for Image2."
    ::= { efpAgentInventoryUnitEntry 4 }

efpAgentInventoryUnitImage1Md5Digest OBJECT-TYPE
    SYNTAX      DisplayString (SIZE(0..80))
    MAX-ACCESS  read-only
    STATUS      current
    DESCRIPTION
        "MD5 digest for Image1."
    ::= { efpAgentInventoryUnitEntry 5 }

efpAgentInventoryUnitImage2Md5Digest OBJECT-TYPE
    SYNTAX      DisplayString (SIZE(0..80))
    MAX-ACCESS  read-only
    STATUS      current
    DESCRIPTION
        "MD5 digest for Image2."
    ::= { efpAgentInventoryUnitEntry 6 }

efpAgentInventoryActiveImage OBJECT-TYPE
    SYNTAX      INTEGER {
                unknown(1),
                image1(2),
                image2(3)
                }
    MAX-ACCESS  read-only
    STATUS      current
    DESCRIPTION
        "The active image name. image1 or image2."
     ::= { efpAgentInventoryUnitEntry 7 }

efpAgentInventoryNextActiveImage OBJECT-TYPE
    SYNTAX      INTEGER {
                unknown(1),
                image1(2),
                image2(3)
                }
    MAX-ACCESS  read-only
    STATUS      current
    DESCRIPTION
        "The image selected for loading on next boot."
     ::= { efpAgentInventoryUnitEntry 8 }

efpInventoryNotifications        OBJECT IDENTIFIER ::= { eltFastpathInventoryMIB 2 }

efpInventoryNotificationsPrefix  OBJECT IDENTIFIER ::= { efpInventoryNotifications 0 }

-- conformance information
efpInventoryConformance          OBJECT IDENTIFIER ::= { eltFastpathInventoryMIB 3 }

efpInventoryCompliances          OBJECT IDENTIFIER ::= { efpInventoryConformance 1 }

-- compliance statements
efpInventoryCompliance MODULE-COMPLIANCE
    STATUS  obsolete
    DESCRIPTION
            "The compliance statement for SNMP entities which implement
            version 1 of the eltFastpathInventoryMIB MIB."
    MODULE  -- this module
        GROUP efpInventoryUnitGroup
        DESCRIPTION
            "Implementation of the agentInventoryUnitTable is only mandatory
            on systems which support the capability of managing multiple units
            in a stack."
    ::= { efpInventoryCompliances 1 }

efpFastPathInventoryMIBCompliance2 MODULE-COMPLIANCE
    STATUS  current
    DESCRIPTION
            "The compliance statement for SNMP entities which implement
            version 2 of the eltFastpathInventoryMIB MIB."
    MODULE  -- this module
        GROUP efpInventoryUnitGroup
        DESCRIPTION
            "Implementation of the agentInventoryUnitTable is only mandatory
            on systems which support the capability of managing multiple units
            in a stack."
    ::= { efpInventoryCompliances 2 }

efpInventoryGroups               OBJECT IDENTIFIER ::= { efpInventoryConformance 2 }

efpInventoryUnitGroup    OBJECT-GROUP
    OBJECTS {
                 efpAgentInventoryUnitImage1CommitHash,
                 efpAgentInventoryUnitImage2CommitHash,
                 efpAgentInventoryUnitImage1Timestamp,
                 efpAgentInventoryUnitImage2Timestamp,
                 efpAgentInventoryUnitImage1Md5Digest,
                 efpAgentInventoryUnitImage2Md5Digest,
                 efpAgentInventoryActiveImage,
                 efpAgentInventoryNextActiveImage
            }
    STATUS  current
    DESCRIPTION
            "The collection of objects which are used to represent
            multiple units in the stack."
    ::= { efpInventoryGroups 2 }


END

ELTEX-FASTPATH-QOS-MIB DEFINITIONS ::= BEGIN

IMPORTS
    MODULE-IDENTITY     FROM SNMPv2-SMI
    eltMesFastpath      FROM ELTEX-MES-FASTPATH-MIB;

eltFastpathQosMIB MODULE-IDENTITY
    LAST-UPDATED "201703090000Z" -- 09 Mar 2017 12:00:00 GMT
    ORGANIZATION "Eltex Enterprise Co, Ltd."
    CONTACT-INFO "www.eltex-co.ru"
    DESCRIPTION
        "The MIB definitaions for Quality of Service Flex package."

    -- Revision history.
    REVISION
        "201703090000Z"
    DESCRIPTION
        "Initial revision."

    ::= { eltMesFastpath 2 }

END

ELTEX-FASTPATH-SWITCHING-MIB DEFINITIONS ::= BEGIN

IMPORTS
    MODULE-IDENTITY, OBJECT-TYPE  FROM SNMPv2-SMI
    eltMesFastpath                FROM ELTEX-MES-FASTPATH-MIB;

eltFastpathSwitchingMIB MODULE-IDENTITY
    LAST-UPDATED "201802260000Z"
    ORGANIZATION "Eltex Enterprise Co, Ltd."
    CONTACT-INFO "www.eltex-co.ru"
    DESCRIPTION
        "Eltex extensions for FastPath Switching"
    -- Revision history.
    REVISION
        "201802260000Z"
    DESCRIPTION
        "Initial revision."
    ::= { eltMesFastpath 5 }


efpSwitchingObjects               OBJECT IDENTIFIER ::= { eltFastpathSwitchingMIB 1 }

efpSwitchingCpuTrafficGlobals     OBJECT IDENTIFIER ::= { efpSwitchingObjects 1 }

--
-- efpSwitchingCpuTrafficConfigs
--

efpSwitchingCpuTrafficConfigs     OBJECT IDENTIFIER ::= { efpSwitchingObjects 2 }

efpAgentCpuTrafficRateLimitQueueTable OBJECT-TYPE
    SYNTAX          SEQUENCE OF EfpAgentCpuTrafficRateLimitQueueEntry
    MAX-ACCESS      not-accessible
    STATUS          current
    DESCRIPTION     "A list of CPU rate limiters."
    ::= { efpSwitchingCpuTrafficConfigs 1 }

efpAgentCpuTrafficRateLimitQueueEntry OBJECT-TYPE
    SYNTAX          EfpAgentCpuTrafficRateLimitQueueEntry
    MAX-ACCESS      not-accessible
    STATUS          current
    DESCRIPTION     "An entry containing the custom CPU
                    rate limiter configuration for specific
                    CPU queue."
    INDEX           { efpAgentCpuTrafficRateLimitQueueNumber }
    ::= { efpAgentCpuTrafficRateLimitQueueTable 1 }

EfpAgentCpuTrafficRateLimitQueueEntry ::= SEQUENCE {
    efpAgentCpuTrafficRateLimitQueueNumber  Integer32,
    efpAgentCpuTrafficRateLimitQueueLimit   Integer32
}

efpAgentCpuTrafficRateLimitQueueNumber OBJECT-TYPE
    SYNTAX          Integer32
    MAX-ACCESS      read-only
    STATUS          current
    DESCRIPTION     "CPU queue number"
    ::= { efpAgentCpuTrafficRateLimitQueueEntry 1 }

efpAgentCpuTrafficRateLimitQueueLimit OBJECT-TYPE
    SYNTAX          Integer32 (8..2048)
    MAX-ACCESS      read-write
    STATUS          current
    DESCRIPTION     "Value of rate-limiter for respective CPU queue, packets per second."
    ::= { efpAgentCpuTrafficRateLimitQueueEntry 2 }

--
-- efpSwitchingCpuTrafficStatistics
--

efpSwitchingCpuTrafficStatistics  OBJECT IDENTIFIER ::= { efpSwitchingObjects 3 }

efpAgentCpuTrafficRateLimitQueueStatTable OBJECT-TYPE
    SYNTAX          SEQUENCE OF EfpAgentCpuTrafficRateLimitQueueStatEntry
    MAX-ACCESS      not-accessible
    STATUS          current
    DESCRIPTION     "A list of CPU stats."
    ::= { efpSwitchingCpuTrafficStatistics 1 }

efpAgentCpuTrafficRateLimitQueueStatEntry OBJECT-TYPE
    SYNTAX          EfpAgentCpuTrafficRateLimitQueueStatEntry
    MAX-ACCESS      not-accessible
    STATUS          current
    DESCRIPTION     "An entry containing the custom CPU
                    rate statistics for specific cos."
    INDEX           { efpAgentCpuTrafficRateLimitQueueNumber }
    ::= { efpAgentCpuTrafficRateLimitQueueStatTable 1 }

EfpAgentCpuTrafficRateLimitQueueStatEntry ::= SEQUENCE {
    efpAgentCpuTrafficRateLimitQueueRate     Integer32,
    efpAgentCpuTrafficRateLimitQueuePackets  Integer32
}

efpAgentCpuTrafficRateLimitQueueRate OBJECT-TYPE
    SYNTAX          Integer32
    MAX-ACCESS      read-only
    STATUS          current
    DESCRIPTION     "Current rate of respective CPU queue, packets per second"
    ::= { efpAgentCpuTrafficRateLimitQueueStatEntry 1 }

efpAgentCpuTrafficRateLimitQueuePackets OBJECT-TYPE
    SYNTAX          Integer32
    MAX-ACCESS      read-only
    STATUS          current
    DESCRIPTION     "Total received packets count on respective CPU queue"
    ::= { efpAgentCpuTrafficRateLimitQueueStatEntry 2 }

efpSwitchingNotifications         OBJECT IDENTIFIER ::= { eltFastpathSwitchingMIB 2 }

efpSwitchingNotificationsPrefix   OBJECT IDENTIFIER ::= { efpSwitchingNotifications 0 }

efpSwitchingConformance           OBJECT IDENTIFIER ::= { eltFastpathSwitchingMIB 3 }

efpSwitchingCompliances           OBJECT IDENTIFIER ::= { efpSwitchingConformance 1 }

END

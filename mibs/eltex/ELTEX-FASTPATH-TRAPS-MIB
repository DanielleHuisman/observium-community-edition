ELTEX-FASTPATH-TRAPS-MIB DEFINITIONS ::= BEGIN

IMPORTS
    MODULE-IDENTITY, OBJECT-TYPE, NOTIFICATION-TYPE  FROM SNMPv2-SMI
    TEXTUAL-CONVENTION                               FROM SNMPv2-TC
    eltMesFastpath                                   FROM ELTEX-MES-FASTPATH-MIB;


eltFastpathTrapsMIB MODULE-IDENTITY
    LAST-UPDATED "201710060000Z"
    ORGANIZATION "Eltex Enterprise Co, Ltd."
    CONTACT-INFO "www.eltex-co.ru"
    DESCRIPTION
        "This private MIB module contains Eltex's specific traps"
    -- Revision history.
    REVISION
        "201710060000Z"
    DESCRIPTION
        "Initial revision."
    ::= { eltMesFastpath 4 }

efpTrapsObjects             OBJECT IDENTIFIER ::= { eltFastpathTrapsMIB 1 }

efpGeneralTestTrapStatus  OBJECT-TYPE
    SYNTAX      INTEGER {
                active(1),
                success(2),
                failure(3),
                uninitialized(4)
            }
    MAX-ACCESS  read-write
    STATUS      current
    DESCRIPTION
                "Status of General trap capability test
                active(1)        - trap testing is in progress. Set to
                                   this value to start the test.
                success(2)       - A successful test was performed. Cannot
                                   be set.
                failure(3)       - A failure was encountered during the
                                   test. Cannot be set.
                uninitialized(4) - No test has been performed yet. Cannot
                                   be set."
    DEFVAL { uninitialized }
    ::= { efpTrapsObjects 1 }

efpTrapsNotifications       OBJECT IDENTIFIER ::= { eltFastpathTrapsMIB 2 }

efpTrapsNotificationsPrefix OBJECT IDENTIFIER ::= { efpTrapsNotifications 0 }

efpWriteMemoryTrap NOTIFICATION-TYPE
    STATUS      current
    DESCRIPTION
                "Trap is sent when write memory operation is performed"
    ::= { efpTrapsNotificationsPrefix 1 }

efpCopyFinishedTrap NOTIFICATION-TYPE
    STATUS      current
    DESCRIPTION
                "Trap is sent when copy operation is successfully performed"
    ::= { efpTrapsNotificationsPrefix 2 }

efpCopyFailedTrap NOTIFICATION-TYPE
    STATUS      current
    DESCRIPTION
                "Trap is sent when copy operation is failed"
    ::= { efpTrapsNotificationsPrefix 3 }

efpGeneralTestTrap NOTIFICATION-TYPE
    STATUS      current
    DESCRIPTION
                "Trap is intended for management systems. It makes sure that
                the device is properly configured & generally capable to
                send traps. Trap is sent when SNMPSET operation for
                efpGeneralTestTrapStatus is performed"
    ::= { efpTrapsNotificationsPrefix 4 }

efpConfigurationReloadedTrap NOTIFICATION-TYPE
    STATUS      current
    DESCRIPTION
                "Trap is sent when running configuration is reloaded"
    ::= { efpTrapsNotificationsPrefix 5 }

efpConfigurationReloadFailedTrap NOTIFICATION-TYPE
    STATUS      current
    DESCRIPTION
                "Trap is sent when running configuration reload is failed"
    ::= { efpTrapsNotificationsPrefix 6 }

efpTrapsConformance         OBJECT IDENTIFIER ::= { eltFastpathTrapsMIB 3 }

END

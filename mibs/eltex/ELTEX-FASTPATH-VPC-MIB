ELTEX-FASTPATH-VPC-MIB DEFINITIONS ::= BEGIN

IMPORTS
    MODULE-IDENTITY, OBJECT-TYPE  FROM SNMPv2-SMI
    TruthValue                    FROM SNMPv2-TC
    eltMesFastpath                FROM ELTEX-MES-FASTPATH-MIB;

eltFastpathVpcMIB MODULE-IDENTITY
    LAST-UPDATED "201808310000Z"
    ORGANIZATION "Eltex Enterprise Co, Ltd."
    CONTACT-INFO "www.eltex-co.ru"
    DESCRIPTION
        "Eltex extensions for FastPath VPC"
    -- Revision history.
    REVISION
        "201808310000Z"
    DESCRIPTION
        "Initial revision."
    ::= { eltMesFastpath 6 }

efpVpcObjects               OBJECT IDENTIFIER ::= { eltFastpathVpcMIB 1 }

efpVpcGlobals               OBJECT IDENTIFIER ::= { efpVpcObjects 1 }

efpVpcOrphanIsolationMode OBJECT-TYPE
    SYNTAX  TruthValue
    MAX-ACCESS  read-write
    STATUS  current
    DESCRIPTION
        "This field enables orphan ports isolation globally on the device.
        If this object value is 'true', packets from peer could not be egressed
        on ports not involved in VPC.
        If this object value is 'false', packets from peer could be egressed
        on ports not involved in VPC."
    DEFVAL { true }
    ::= { efpVpcGlobals 1 }

efpVpcNotifications         OBJECT IDENTIFIER ::= { eltFastpathVpcMIB 2 }

efpVpcNotificationsPrefix   OBJECT IDENTIFIER ::= { efpVpcNotifications 0 }

efpVpcConformance           OBJECT IDENTIFIER ::= { eltFastpathVpcMIB 3 }

END

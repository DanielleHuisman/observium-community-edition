ELTEX-MAC-NOTIFICATION-MIB DEFINITIONS ::= BEGIN

IMPORTS
        MODULE-IDENTITY, OBJECT-TYPE, NOTIFICATION-TYPE, Integer32
                FROM SNMPv2-SMI
        TruthValue, TimeStamp, MacAddress, TEXTUAL-CONVENTION
                FROM SNMPv2-TC
        ifIndex
                FROM IF-MIB
        VlanIndex
                FROM CISCO-VTP-MIB
        eltexLtd
                FROM ELTEX-SMI-ACTUAL;

eltexMacNotificationMIB MODULE-IDENTITY
    LAST-UPDATED    "201511050000Z"
    ORGANIZATION    "Eltex Enterprise Co, Ltd."
    CONTACT-INFO
        "www.eltex.nsk.ru"
    DESCRIPTION
        "Configuration of MAC notification feature."
    REVISION   "201511050000Z"
    DESCRIPTION
        "Initial version of this MIB module."
    ::= { eltexLtd 33 }


eltexMacNotificationObjects OBJECT IDENTIFIER ::= { eltexMacNotificationMIB 1 }

-- -------------------- --
-- eltexMnFlappingObjects --
-- -------------------- --
eltexMnFlappingObjects OBJECT IDENTIFIER ::= { eltexMacNotificationObjects 1 }

eltexMnFlappingFeatureEnabled  OBJECT-TYPE
    SYNTAX        TruthValue
    MAX-ACCESS    read-write
    STATUS        current
    DESCRIPTION
        "Specifies whether the MAC Flapping notification feature is
         currently running in the device.

         Setting this object to false(2) disables the MAC Flapping
         notification feature globally.

         Setting this object to true(1) will start the MAC Flapping
         notification feature running in the device."
    DEFVAL { true }
    ::= { eltexMnFlappingObjects 1 }

eltexMnFlappingNotificationsEnabled OBJECT-TYPE
     SYNTAX          TruthValue
     MAX-ACCESS      read-write
     STATUS          current
     DESCRIPTION
         "Specifies whether eltexMnFlappingNotification notifications
          will or will not be sent when a MAC flapping is detected by
          the MAC flapping notification feature.

          Setting this object to false(2) will not send the
          eltexMnFlappingNotification notifications.

          Setting this object to true(1) will send the
          eltexMnFlappingNotification notifications."
    DEFVAL { true }
    ::= { eltexMnFlappingObjects 2 }

eltexMnFlappingAddress OBJECT-TYPE
     SYNTAX          MacAddress
     MAX-ACCESS      read-only
     STATUS          current
     DESCRIPTION
         "Indicates the MAC address that is flapping between
          eltexMnFlappingFirstPortId and eltexMnFlappingSecondPortId on
          eltexMnFlappingVlanNumber.

          This object is instantiated only when eltexMnFlappingFeatureEnabled
          value is set to true(1) and a MAC flapping is detected by the MAC
          flapping notification feature."
    ::= { eltexMnFlappingObjects 3 }

eltexMnFlappingVlanNumber OBJECT-TYPE
     SYNTAX          VlanIndex
     MAX-ACCESS      read-only
     STATUS          current
     DESCRIPTION
         "Indicates the VLAN on which the eltexMnFlappingAddress is flapping
          between eltexMnFlappingFirstPortId to eltexMnFlappingSecondPortId.

          This object is instantiated only when eltexMnFlappingFeatureEnabled
          value is set to true(1) and a MAC flapping is detected by the MAC
          flapping notification feature."
    ::= { eltexMnFlappingObjects 4 }

eltexMnFlappingFirstPortId OBJECT-TYPE
     SYNTAX          Integer32 (1..65535)
     MAX-ACCESS      read-only
     STATUS          current
     DESCRIPTION
         "The first value of dot1dBasePort for the bridge port on which
          the eltexMnFlappingAddress is flapping on eltexMnFlappingVlanNumber.

          This object is instantiated only when eltexMnFlappingFeatureEnabled
          value is set to true(1) and a MAC flapping is detected by the MAC
          flapping notification feature."
     REFERENCE
               "dot1dBasePort is defined in RFC1493."
    ::= { eltexMnFlappingObjects 5 }

eltexMnFlappingSecondPortId OBJECT-TYPE
     SYNTAX          Integer32 (1..65535)
     MAX-ACCESS      read-only
     STATUS          current
     DESCRIPTION
         "The second value of dot1dBasePort for the bridge port on which
          the eltexMnFlappingAddress is flapping on eltexMnFlappingVlanNumber.

          This object is instantiated only when eltexMnFlappingFeatureEnabled
          value is set to true(1) and a MAC flapping is detected by the MAC
          flapping notification feature."
     REFERENCE
               "dot1dBasePort is defined in RFC1493."
    ::= { eltexMnFlappingObjects 6 }

eltexMnFlappingTime OBJECT-TYPE
     SYNTAX          TimeStamp
     MAX-ACCESS      read-only
     STATUS          current
     DESCRIPTION
         "The value of sysUpTime when a eltexMnFlappingAddress is flapping
          between eltexMnFlappingFirstPortId and eltexMnFlappingSecondPortId.

          This object is instantiated only when eltexMnFlappingFeatureEnabled
          value is set to true(1) and a MAC flapping is detected by the MAC
          flapping notification feature."
    ::= { eltexMnFlappingObjects 7 }

-- -------------- --
-- Notifications  --
-- -------------- --
eltexMnNotificationPrefix OBJECT IDENTIFIER ::= { eltexMacNotificationMIB 2 }

eltexMnNotifications OBJECT IDENTIFIER ::= { eltexMnNotificationPrefix 0 }

eltexMnFlappingNotification NOTIFICATION-TYPE
    OBJECTS {
              eltexMnFlappingAddress,
              eltexMnFlappingVlanNumber,
              eltexMnFlappingFirstPortId,
              eltexMnFlappingSecondPortId,
              eltexMnFlappingTime
            }
    STATUS  current
    DESCRIPTION
        "This notification is generated when a MAC address is
         flapping between two or more interfaces."
    ::= { eltexMnNotifications 1 }

END

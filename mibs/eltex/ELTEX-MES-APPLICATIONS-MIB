ELTEX-MES-APPLICATIONS-MIB DEFINITIONS ::= BEGIN

-- Title:                ELTEX-MES-APPLICATIONS-MIB
-- Version:              1.0
-- Date:                 26-Jun-2018

IMPORTS
    MODULE-IDENTITY, OBJECT-TYPE    FROM SNMPv2-SMI
    TruthValue                      FROM SNMPv2-TC
    eltMes                          FROM ELTEX-MES
    rsPingInetEntry                 FROM RADLAN-rndApplications;

eltMesApplicationsMIB MODULE-IDENTITY
    LAST-UPDATED    "201806260000Z"
    ORGANIZATION    "Eltex Enterprise, Ltd."
    CONTACT-INFO    
        "www.eltex-co.ru"
    DESCRIPTION
        "Applications MIB."
    REVISION        "201806260000Z"
    DESCRIPTION "Initial version."
    ::= { eltMes 96 }


eltMesApplicationsObjects OBJECT IDENTIFIER
    ::= { eltMesApplicationsMIB 1 }

eltMesApplicationsGlobals OBJECT IDENTIFIER
    ::= { eltMesApplicationsObjects 1 }


eltPingInetTable OBJECT-TYPE
    SYNTAX SEQUENCE OF EltPingInetEntry
    MAX-ACCESS  not-accessible
    STATUS      current
    DESCRIPTION
        "This table augments rsPingInetTable."
    ::= { eltMesApplicationsGlobals 1 }

eltPingInetEntry OBJECT-TYPE
    SYNTAX      EltPingInetEntry
    MAX-ACCESS  not-accessible
    STATUS      current
    DESCRIPTION
        "An entry of eltPingInetTable."
    AUGMENTS { rsPingInetEntry }
    ::= { eltPingInetTable 1 }

EltPingInetEntry ::= SEQUENCE {

    eltPingInetDontFragment     TruthValue

    }

eltPingInetDontFragment OBJECT-TYPE
    SYNTAX      TruthValue
    MAX-ACCESS  read-write
    STATUS      current
    DESCRIPTION 
        "Explicitly prohibit packets fragmentation. When set to true
         ping datagrams exceeding MTU size are not allowed to be fragmented."
    DEFVAL      { false }
    ::= { eltPingInetEntry 1 }

END

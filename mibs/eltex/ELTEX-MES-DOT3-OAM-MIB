ELTEX-MES-DOT3-OAM-MIB DEFINITIONS ::= BEGIN

IMPORTS
	MODULE-IDENTITY, OBJECT-TYPE, Counter32, Unsigned32,
	 Integer32, Counter64, NOTIFICATION-TYPE
	 FROM SNMPv2-SMI
	 -- from [RFC2578]
	TEXTUAL-CONVENTION, MacAddress, TimeStamp, TruthValue

	 FROM SNMPv2-TC
	 -- from [RFC2579]
	ifIndex
	 FROM IF-MIB
	 -- from [RFC2863]
	MODULE-COMPLIANCE, OBJECT-GROUP
	 FROM SNMPv2-CONF

	PortList   FROM Q-BRIDGE-MIB

	elt-mes-mib-2  FROM ELTEX-MES-MNG-MIB;

eltMesDot3OamMIB MODULE-IDENTITY
			LAST-UPDATED "201511190000Z" -- November 19,2015
			ORGANIZATION "Eltex Ent"
			CONTACT-INFO
					"www.eltex.nsk.ru"
   			DESCRIPTION "Initial version."
   			REVISION    "201302220000Z"  -- Februrary 22,2013
            DESCRIPTION
					"Initial revision."

			REVISION	 "201511190000Z" -- November 19,2015
			DESCRIPTION
  				"Deprecate all objects in this module."
	::= { elt-mes-mib-2 158 }

eltMesDot3OamObjects    OBJECT IDENTIFIER ::= { eltMesDot3OamMIB 1 }

eltDot3OamClearStatistic OBJECT-TYPE
    SYNTAX      PortList
    MAX-ACCESS  read-write
    STATUS      deprecated
    DESCRIPTION
        "Each bit that is set in this portList represent a port that
         its OAM statistic should be reset."
    ::= { eltMesDot3OamObjects 7 }

END

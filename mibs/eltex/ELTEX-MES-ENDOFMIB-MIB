ELTEX-MES-ENDOFMIB-MIB DEFINITIONS ::= BEGIN

-- Title:                ELTEX MES-Series Switches
--                       Private TRAPS MIB
-- Version:              1.0
-- Date:                 1-Jan-2012

IMPORTS
    eltMes                                                  FROM ELTEX-MES
    OBJECT-TYPE, MODULE-IDENTITY                            FROM SNMPv2-SMI;

eltMesEndOfMibGroup MODULE-IDENTITY
                LAST-UPDATED "201207130000Z"
                ORGANIZATION "Eltex Enterprise Co, Ltd."
                CONTACT-INFO
                      "www.eltex.nsk.ru"
                DESCRIPTION
                      "This private MIB module defines End of Eltex private MIBs."
                REVISION "201207130000Z"
                DESCRIPTION
                      "Initial revision."
        ::= { eltMes 1000 }

eltEndOfMib OBJECT-TYPE
      SYNTAX  INTEGER
      MAX-ACCESS   read-only
      STATUS   current
      DESCRIPTION
        " This variable indicates this is the end of Eltex MIB."
      ::= {  eltMesEndOfMibGroup 1  }

END

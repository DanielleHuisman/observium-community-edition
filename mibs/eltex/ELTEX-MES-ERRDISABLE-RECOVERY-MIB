-- -----------------------------------------------------------------------------
-- MIB NAME : Eltex MES ERRDISABLE Recovery Configuration
-- FILE NAME: eltInterfacesRecovery.mib
-- DATE     : 2015/10/2
-- VERSION  : 2.00
-- PURPOSE  : MIB extention of ERRDISABLE Recovery feature
-- -----------------------------------------------------------------------------

ELTEX-MES-ERRDISABLE-RECOVERY-MIB DEFINITIONS ::= BEGIN

IMPORTS
	TruthValue,TEXTUAL-CONVENTION,
	RowStatus                      FROM SNMPv2-TC
	MODULE-IDENTITY, OBJECT-TYPE   FROM SNMPv2-SMI
	ifIndex                        FROM IF-MIB
	eltMes                         FROM ELTEX-MES
	rlErrdisableRecoveryIfReason   FROM MARVELL-ERRDISABLE-RECOVERY-MIB
	;

eltMesErrdisableRecovery      OBJECT IDENTIFIER ::= { eltMes 128 }
eltMesErrdisableRecoveryTraps OBJECT IDENTIFIER ::= { eltMesErrdisableRecovery 0 }

-- -----------------------------------------------------------------------------
-- SCALARS
-- -----------------------------------------------------------------------------

eltErrdisableRecoveryTrapEnable OBJECT-TYPE
	SYNTAX       TruthValue
	MAX-ACCESS   read-write
	STATUS       current
	DEFVAL       {false}
	DESCRIPTION
		"Enable/Disable sending of trap for errdisable."
	::= { eltMesErrdisableRecovery 1 }

-- -----------------------------------------------------------------------------
-- Notifications
-- -----------------------------------------------------------------------------

eltErrdisableRecoveryTrap NOTIFICATION-TYPE
		OBJECTS {
  			ifIndex,
			rlErrdisableRecoveryIfReason
		}
		STATUS  current
		DESCRIPTION
				"A eltErrdisableRecoveryNotif is generated when moved
				 to errdisable state."
	::= { eltMesErrdisableRecoveryTraps 1 }

END

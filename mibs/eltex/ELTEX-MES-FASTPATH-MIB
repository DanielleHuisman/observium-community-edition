ELTEX-MES-FASTPATH-MIB DEFINITIONS ::= BEGIN

IMPORTS
    OBJECT-GROUP
        FROM SNMPv2-CONF
    elHardware
        FROM ELTEX-SMI-ACTUAL;

eltMesFastpath OBJECT IDENTIFIER ::= { elHardware 103 }

-- eltFastpathInventoryMIB OBJECT IDENTIFIER  ::= { eltMesFastpath 1 }
-- see ELTEX-FASTPATH-INVENTORY-MIB.mx

-- eltFastpathQosMIB OBJECT IDENTIFIER        ::= { eltMesFastpath 2 }
-- see ELTEX-FASTPATH-QOS-MIB.mx

-- eltFastpathBridgeMIB MODULE-IDENTITY       ::= { eltMesFastpath 3 }
-- see ELTEX-FASTPATH-BRIDGE-MIB.mx

-- eltFastpathTrapsMIB MODULE-IDENTITY        ::= { eltMesFastpath 4 }
-- see ELTEX-FASTPATH-TRAPS-MIB.mx

-- eltFastpathSwitchingMIB MODULE-IDENTITY    ::= { eltMesFastpath 5 }
-- see ELTEX-FASTPATH-SWITCHING-MIB.mx

-- eltFastpathVpcMIB MODULE-IDENTITY          ::= { eltMesFastpath 6 }
-- see ELTEX-FASTPATH-VPC-MIB.mx

END

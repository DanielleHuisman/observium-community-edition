-- -----------------------------------------------------------------------------
-- MIB NAME : Eltex MES GVRP Configuration
-- FILE NAME: eltGvrp.mib
-- DATE     : 2018/1/15
-- VERSION  : 1.00
-- PURPOSE  : MIB extention of GVRP feature
-- -----------------------------------------------------------------------------

ELTEX-MES-GVRP-MIB DEFINITIONS ::= BEGIN

IMPORTS
	TruthValue,TEXTUAL-CONVENTION,
	RowStatus, TruthValue          FROM SNMPv2-TC
	MODULE-IDENTITY, OBJECT-TYPE   FROM SNMPv2-SMI
	ifIndex                        FROM IF-MIB
	eltMes                         FROM ELTEX-MES;

eltMesGvrpMIB MODULE-IDENTITY
           LAST-UPDATED "201801150000Z"
           ORGANIZATION "Eltex Enterprise Co, Ltd."
           CONTACT-INFO "www.eltex.nsk.ru"
           DESCRIPTION " "

           REVISION "201801150000Z"
           DESCRIPTION "Initial revision."
		::= { eltMes 256 }

eltMesGvrpObjects OBJECT IDENTIFIER ::= { eltMesGvrpMIB 1 }
eltMesGvrpConfigs OBJECT IDENTIFIER ::= { eltMesGvrpObjects 1 }

--------------------------------------------------------------
-- GVRP Vlan Advertisement Forbid Table
--------------------------------------------------------------

eltGvrpAdvertisementForbidVlanTable OBJECT-TYPE
   SYNTAX      SEQUENCE OF EltGvrpAdvertisementForbidVlanEntry
   MAX-ACCESS  not-accessible
   STATUS      current
   DESCRIPTION
       "A table contains only one entry of a static vlan list."
   ::= { eltMesGvrpConfigs 1 }

	eltGvrpAdvertisementForbidVlanEntry OBJECT-TYPE
	   SYNTAX      EltGvrpAdvertisementForbidVlanEntry
	   MAX-ACCESS  not-accessible
	   STATUS      current
	   DESCRIPTION
		   "Statically created by local or network management vlan list"
	   INDEX   { eltGvrpAdvertisementForbidVlanIndex }
	   ::= { eltGvrpAdvertisementForbidVlanTable 1 }

	EltGvrpAdvertisementForbidVlanEntry ::= SEQUENCE {
		eltGvrpAdvertisementForbidVlanIndex           INTEGER,
		eltGvrpAdvertisementForbidVlanId1To1024       OCTET STRING,
		eltGvrpAdvertisementForbidVlanId1025To2048    OCTET STRING,
		eltGvrpAdvertisementForbidVlanId2049To3072    OCTET STRING,
		eltGvrpAdvertisementForbidVlanId3073To4094    OCTET STRING
	}

   eltGvrpAdvertisementForbidVlanIndex  OBJECT-TYPE
      SYNTAX      INTEGER {
           static(1)
      }
      MAX-ACCESS  not-accessible
      STATUS      current
      DESCRIPTION
        "The table contains only one static entry."
      ::= { eltGvrpAdvertisementForbidVlanEntry 1 }

   eltGvrpAdvertisementForbidVlanId1To1024 OBJECT-TYPE
      SYNTAX      OCTET STRING(SIZE(0..128))
      MAX-ACCESS  read-write
      STATUS      current
      DESCRIPTION
        "A list of vlans from 1 to 1024."
      DEFVAL {'00'H}
      ::= { eltGvrpAdvertisementForbidVlanEntry 2 }

   eltGvrpAdvertisementForbidVlanId1025To2048 OBJECT-TYPE
      SYNTAX      OCTET STRING(SIZE(0..128))
      MAX-ACCESS  read-write
      STATUS      current
      DESCRIPTION
        "A list of vlans from 1025 to 2048."
      DEFVAL {'00'H}
      ::= { eltGvrpAdvertisementForbidVlanEntry 3 }

   eltGvrpAdvertisementForbidVlanId2049To3072 OBJECT-TYPE
      SYNTAX      OCTET STRING(SIZE(0..128))
      MAX-ACCESS  read-write
      STATUS      current
      DESCRIPTION
        "A list of vlans from 2049 to 3072."
      DEFVAL {'00'H}
      ::= { eltGvrpAdvertisementForbidVlanEntry 4 }

   eltGvrpAdvertisementForbidVlanId3073To4094 OBJECT-TYPE
      SYNTAX      OCTET STRING(SIZE(0..128))
      MAX-ACCESS  read-write
      STATUS      current
      DESCRIPTION
        "A list of vlans from 3073 to 4094."
      DEFVAL {'00'H}
      ::= { eltGvrpAdvertisementForbidVlanEntry 5 }

--------------------------------------------------------------
-- GVRP dynamic-to-static vlan conversion enable
--------------------------------------------------------------

eltGvrpStaticVlanEnable OBJECT-TYPE
    SYNTAX      TruthValue
    MAX-ACCESS  read-write
    STATUS      current
    DESCRIPTION
        "Enable dynamic-to-static vlan conversion."
    DEFVAL { false }
    ::= { eltMesGvrpConfigs 2 }

 END

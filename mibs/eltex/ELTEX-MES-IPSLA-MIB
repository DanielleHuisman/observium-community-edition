ELTEX-MES-IPSLA-MIB DEFINITIONS ::= BEGIN

-- Title:      ELTEX MES IP Service Level Agreements Extension Private
-- Version:    1.0
-- Date:       21 Apr 2015

IMPORTS
    MODULE-IDENTITY, OBJECT-TYPE, IpAddress,
    Counter32                                       FROM SNMPv2-SMI
    TEXTUAL-CONVENTION, TruthValue, RowStatus,
    DisplayString, TimeStamp                        FROM SNMPv2-TC
    InterfaceIndexOrZero                            FROM IF-MIB
    eltMesMng                                       FROM ELTEX-MES;

eltMesIpSlaMIB MODULE-IDENTITY
    LAST-UPDATED "201511190000Z"	-- November 19, 2015
    ORGANIZATION "Eltex Ltd."
    CONTACT-INFO
        "http://www.eltex.nsk.ru"
    DESCRIPTION
        "This module defines a MIB for IP Service Level
        Agreements Application. IP SLA operations allows
        to analyze IP service levels by using active
        traffic monitoring.

        Each of IP SLA operation is described by protocol
        it uses and type of performance metric.

        IP SLA Objects
        |--- Application Group
        |    |--- Responder Administration
        |         |--- UDP Jitter Responder Defenitions
        |
        |--- Administration Group
        |    |--- Overall Control Administration
        |    |--- ICMP Echo Administration Definitions
        |    |--- UDP Jitter Administration Definitions
        |
        |--- Statistics Collection Group
        |    |--- Overall Control Statistics
        |    |--- ICMP Echo Statistics Definitions
        |    |--- UDP Jitter Statistics Definitions
        |
        |--- Schedule Configuration
        |
        |--- History Collection Group

        IP SLA Notifications
        |
        "

    REVISION	 "201511190000Z"  	-- November 19, 2015
    DESCRIPTION
        "Deprecate all objects in this module."
    ::= { eltMesMng 6 }

--
-- IP Service Level Agreements MIB Objects
--

eltMesIpSlaObjects  OBJECT IDENTIFIER
    ::= { eltMesIpSlaMIB 1 }

-- IP Service Level Agreements Object Groups


eltMesIpSlaAppl  OBJECT IDENTIFIER
    ::= { eltMesIpSlaObjects 1 }

eltMesIpSlaAdmin  OBJECT IDENTIFIER
    ::= { eltMesIpSlaObjects 2 }

eltMesIpSlaStats  OBJECT IDENTIFIER
    ::= { eltMesIpSlaObjects 3 }

eltMesIpSlaSchedule  OBJECT IDENTIFIER
    ::= { eltMesIpSlaObjects 4 }

--eltMesIpSlaHistory  OBJECT IDENTIFIER
--    ::= { eltMesIpSlaObjects 5 }

-- Operation type textual convention

EltIpSlaOperationType ::= TEXTUAL-CONVENTION
    STATUS          deprecated
    DESCRIPTION
        "Specifies the type of IP SLA operation."
    SYNTAX          INTEGER  {
                        icmp-echo       (1),
                        udp-jitter      (2)
-- Reserved types
--                      udp-echo        (3),
--                      path-jitter     (4),
--                      path-echo       (5),
--                      ethernet-jitter (6),
--                      ethernet-echo   (7),
--                      tcp-connect     (8),
--                      dhcp            (9),
--                      dns             (10),
--                      ftp             (11),
--                      http            (12)
                    }

-- Operation status textual convention

EltIpSlaOperationStatus ::= TEXTUAL-CONVENTION
    STATUS          deprecated
    DESCRIPTION
        "Specifies the status of IP SLA operation."
    SYNTAX          INTEGER  {
                        active          (1),
                        inactive        (2)
                    }

-- Responder control

eltIpSlaApplResponder OBJECT-TYPE
    ::= { eltMesIpSlaAppl 13 }

eltIpSlaApplResponderUdpJitterPort OBJECT-TYPE
    SYNTAX          INTEGER (0..65535)
    MAX-ACCESS      read-write
    STATUS          deprecated
    DESCRIPTION
        "Defines UDP port number which is listened by IP SLA responder
        for UDP Jitter operations"
    DEFVAL          { 0 }
    ::= { eltIpSlaApplResponder 1 }

-- Overall Control Administration Table

eltIpSlaAdminCtrlTable OBJECT-TYPE
    SYNTAX          SEQUENCE OF EltIpSlaAdminCtrlEntry
    MAX-ACCESS      read-write
    STATUS          deprecated
    DESCRIPTION
        "A table of IP SLA overall control administration definitions.

        The IP SLA control is located in multiple tables. This
        first table defines the most common SLA configuration. The
        following tables contain objects which configure scheduling,
        information gathering, and notification generation. All of
        these tables using this table's index as their own."
    ::= { eltMesIpSlaAdmin 1 }

eltIpSlaAdminCtrlEntry OBJECT-TYPE
    SYNTAX          EltIpSlaAdminCtrlEntry
    MAX-ACCESS      read-write
    STATUS          deprecated
    DESCRIPTION
        "A row entry representing a single IP SLA operation."
    INDEX           { eltIpSlaAdminCtrlIndex }
    ::= { eltIpSlaAdminCtrlTable 1 }

EltIpSlaAdminCtrlEntry ::= SEQUENCE {
        eltIpSlaAdminCtrlIndex              INTEGER,
        eltIpSlaAdminCtrlType               EltIpSlaOperationType,
        eltIpSlaAdminCtrlStatus             EltIpSlaOperationStatus,
        eltIpSlaAdminCtrlFrequency          INTEGER,
        eltIpSlaAdminCtrlTag                DisplayString,
        eltIpSlaAdminCtrlOwner              DisplayString,
        eltIpSlaAdminCtrlRowStatus          RowStatus
}

eltIpSlaAdminCtrlIndex OBJECT-TYPE
    SYNTAX          INTEGER
    MAX-ACCESS      read-write
    STATUS          deprecated
    DESCRIPTION
        "This field specifies index for all IP SLA tables.
        Rows with identic index in each of following tables
        describes the same IP SLA operation as this table does."
    ::= { eltIpSlaAdminCtrlEntry 1 }

eltIpSlaAdminCtrlType OBJECT-TYPE
    SYNTAX          EltIpSlaOperationType
    MAX-ACCESS      read-write
    STATUS          deprecated
    DESCRIPTION
        "This field specifies type of IP SLA operation."
    ::= { eltIpSlaAdminCtrlEntry 2 }

eltIpSlaAdminCtrlStatus OBJECT-TYPE
    SYNTAX          EltIpSlaOperationStatus
    MAX-ACCESS      read-only
    STATUS          deprecated
    DESCRIPTION
        "This field specifies status of IP SLA operation."
    ::= { eltIpSlaAdminCtrlEntry 3 }

eltIpSlaAdminCtrlFrequency OBJECT-TYPE
    SYNTAX          INTEGER (0..604800)
    UNITS           "seconds"
    MAX-ACCESS      read-write
    STATUS          deprecated
    DESCRIPTION
        "Specifies the duration between initiating each IP SLA
        operation.

        This object cannot be set to a value which would be a
        shorter duration than operation timeout."
    DEFVAL          { 60 }
    ::= { eltIpSlaAdminCtrlEntry 4 }

eltIpSlaAdminCtrlTag OBJECT-TYPE
    SYNTAX          DisplayString (SIZE  (0..128))
    MAX-ACCESS      read-write
    STATUS          deprecated
    DESCRIPTION
        "The field provides description tag for IP SLA operation."
    DEFVAL          { "" }
    ::= { eltIpSlaAdminCtrlEntry 5 }

eltIpSlaAdminCtrlOwner OBJECT-TYPE
    SYNTAX          DisplayString (SIZE  (0..32))
    MAX-ACCESS      read-write
    STATUS          deprecated
    DESCRIPTION
        "The field describes owner of the IP SLA operation."
    DEFVAL          { "" }
    ::= { eltIpSlaAdminCtrlEntry 6 }

eltIpSlaAdminCtrlRowStatus OBJECT-TYPE
    SYNTAX          RowStatus
    MAX-ACCESS      read-write
    STATUS          deprecated
    DESCRIPTION
        "The status of the MIB entry."
    ::= { eltIpSlaAdminCtrlEntry 7 }

-- ICMP Echo Administration Table

eltIpSlaAdminIcmpEchoTable OBJECT-TYPE
    SYNTAX          SEQUENCE OF EltIpSlaAdminIcmpEchoEntry
    MAX-ACCESS      read-write
    STATUS          deprecated
    DESCRIPTION
        "A table of ICMP Echo operation definitions."
    ::= { eltMesIpSlaAdmin 2 }

eltIpSlaAdminIcmpEchoEntry OBJECT-TYPE
    SYNTAX          EltIpSlaAdminIcmpEchoEntry
    MAX-ACCESS      read-write
    STATUS          deprecated
    DESCRIPTION
        "A row entry representing a single ICMP Echo operation."
    INDEX           { eltIpSlaAdminIcmpEchoIndex }
    ::= { eltIpSlaAdminIcmpEchoTable 1 }

EltIpSlaAdminIcmpEchoEntry ::= SEQUENCE {
        eltIpSlaAdminIcmpEchoIndex              INTEGER,
        eltIpSlaAdminIcmpEchoTargetAddress      IpAddress,
        eltIpSlaAdminIcmpEchoSourceAddress      IpAddress,
        eltIpSlaAdminIcmpEchoSourceInterface    InterfaceIndexOrZero,
        eltIpSlaAdminIcmpEchoTimeOut            INTEGER,
        eltIpSlaAdminIcmpEchoReqDataSize        INTEGER,
        eltIpSlaAdminIcmpEchoTOS                INTEGER,
        eltIpSlaAdminIcmpEchoRowStatus          RowStatus
}

eltIpSlaAdminIcmpEchoIndex OBJECT-TYPE
    SYNTAX          INTEGER
    MAX-ACCESS      read-write
    STATUS          deprecated
    DESCRIPTION
        "This field specifies index for ICMP Echo operation.
        Index of each row must match the index in eltIpSlaAdminCtrl table."
    ::= { eltIpSlaAdminIcmpEchoEntry 1 }

eltIpSlaAdminIcmpEchoTargetAddress OBJECT-TYPE
    SYNTAX          IpAddress
    MAX-ACCESS      read-write
    STATUS          deprecated
    DESCRIPTION
        "A string which specifies IP address of the destination."
    ::= { eltIpSlaAdminIcmpEchoEntry 2 }

eltIpSlaAdminIcmpEchoSourceAddress OBJECT-TYPE
    SYNTAX          IpAddress
    MAX-ACCESS      read-write
    STATUS          deprecated
    DESCRIPTION
        "A string which specifies the source IP address."
    ::= { eltIpSlaAdminIcmpEchoEntry 3 }

eltIpSlaAdminIcmpEchoSourceInterface OBJECT-TYPE
    SYNTAX          InterfaceIndexOrZero
    MAX-ACCESS      read-write
    STATUS          deprecated
    DESCRIPTION
        "A string which specifies the source interface."
    ::= { eltIpSlaAdminIcmpEchoEntry 4 }

eltIpSlaAdminIcmpEchoTimeOut OBJECT-TYPE
    SYNTAX          INTEGER (0..3600000)
    UNITS           "milliseconds"
    MAX-ACCESS      read-write
    STATUS          deprecated
    DESCRIPTION
        "Specifies the duration to wait for a IP SLA operation
        completion.

        For connection oriented protocols, this may cause the
        connection to be closed by the operation.  Once closed, it
        will be assumed that the connection reestablishment
        will be performed.  To prevent unwanted closure of
        connections, be sure to set this value to a realistic
        connection timeout."
    DEFVAL          { 1000 }
    ::= { eltIpSlaAdminIcmpEchoEntry 5 }

eltIpSlaAdminIcmpEchoReqDataSize OBJECT-TYPE
    SYNTAX          INTEGER (0..1432)
    MAX-ACCESS      read-write
    STATUS          deprecated
    DESCRIPTION
        "This object represents the number of octets to be
        placed into packages send during IP SLA operation"
    DEFVAL          { 56 }
    ::= { eltIpSlaAdminIcmpEchoEntry 6 }

eltIpSlaAdminIcmpEchoTOS OBJECT-TYPE
    SYNTAX          INTEGER (0..255)
    MAX-ACCESS      read-write
    STATUS          deprecated
    DESCRIPTION
        "This object represents the type of service octet in an
        IP header."
    REFERENCE
        "Refer to the following documents for TOS definition.
               RFC791/1349  for IPv4, IPv6, draft-ietf-diffserv-header-02.txt"
    DEFVAL          { 0 }
    ::= { eltIpSlaAdminIcmpEchoEntry 7 }

eltIpSlaAdminIcmpEchoRowStatus OBJECT-TYPE
    SYNTAX          RowStatus
    MAX-ACCESS      read-write
    STATUS          deprecated
    DESCRIPTION
        "The status of the MIB entry."
    ::= { eltIpSlaAdminIcmpEchoEntry 8 }

-- Operation status textual convention

EltIpSlaStatsOperStatus ::= TEXTUAL-CONVENTION
    STATUS          deprecated
    DESCRIPTION
        "Specifies the status of IP SLA operation."
    SYNTAX          INTEGER  {
                        unknown     (0),
                        ok          (1),
                        failed      (2)
                    }

-- UDP Jitter Administration Table

eltIpSlaAdminUdpJitterTable OBJECT-TYPE
    SYNTAX          SEQUENCE OF EltIpSlaAdminUdpJitterEntry
    MAX-ACCESS      read-write
    STATUS          deprecated
    DESCRIPTION
        "A table of UDP Jitter operation definitions."
    ::= { eltMesIpSlaAdmin 3 }

eltIpSlaAdminUdpJitterEntry OBJECT-TYPE
    SYNTAX          EltIpSlaAdminUdpJitterEntry
    MAX-ACCESS      read-write
    STATUS          deprecated
    DESCRIPTION
        "A row entry representing a single UDP Jitter operation."
    INDEX           { eltIpSlaAdminUdpJitterIndex }
    ::= { eltIpSlaAdminUdpJitterTable 1 }

EltIpSlaAdminUdpJitterEntry ::= SEQUENCE {
        eltIpSlaAdminUdpJitterIndex             INTEGER,
        eltIpSlaAdminUdpJitterTargetAddress     IpAddress,
        eltIpSlaAdminUdpJitterTargetPort        INTEGER,
        eltIpSlaAdminUdpJitterSourceAddress     IpAddress,
        eltIpSlaAdminUdpJitterSourcePort        INTEGER,
        eltIpSlaAdminUdpJitterSourceInterface   InterfaceIndexOrZero,
        eltIpSlaAdminUdpJitterInterval          INTEGER,
        eltIpSlaAdminUdpJitterNumPackets        INTEGER,
        eltIpSlaAdminUdpJitterTimeOut           INTEGER,
        eltIpSlaAdminUdpJitterReqDataSize       INTEGER,
        eltIpSlaAdminUdpJitterTOS               INTEGER,
        eltIpSlaAdminUdpJitterRowStatus         RowStatus
}

eltIpSlaAdminUdpJitterIndex OBJECT-TYPE
    SYNTAX          INTEGER
    MAX-ACCESS      read-write
    STATUS          deprecated
    DESCRIPTION
        "This field specifies index for UdpJitter operation.
        Index of each row must match the index in eltIpSlaAdminCtrl table."
    ::= { eltIpSlaAdminUdpJitterEntry 1 }

eltIpSlaAdminUdpJitterTargetAddress OBJECT-TYPE
    SYNTAX          IpAddress
    MAX-ACCESS      read-write
    STATUS          deprecated
    DESCRIPTION
        "A string which specifies IP address of the destination."
    ::= { eltIpSlaAdminUdpJitterEntry 2 }

eltIpSlaAdminUdpJitterTargetPort OBJECT-TYPE
    SYNTAX          INTEGER (0..65535)
    MAX-ACCESS      read-write
    STATUS          deprecated
    DESCRIPTION
        "A number of destination UDP port."
    ::= { eltIpSlaAdminUdpJitterEntry 3 }

eltIpSlaAdminUdpJitterSourceAddress OBJECT-TYPE
    SYNTAX          IpAddress
    MAX-ACCESS      read-write
    STATUS          deprecated
    DESCRIPTION
        "A string which specifies the source IP address."
    ::= { eltIpSlaAdminUdpJitterEntry 4 }

eltIpSlaAdminUdpJitterSourcePort OBJECT-TYPE
    SYNTAX          INTEGER (0..65535)
    MAX-ACCESS      read-write
    STATUS          deprecated
    DESCRIPTION
        "A number of source UDP port."
    ::= { eltIpSlaAdminUdpJitterEntry 5 }

eltIpSlaAdminUdpJitterSourceInterface OBJECT-TYPE
    SYNTAX          InterfaceIndexOrZero
    MAX-ACCESS      read-write
    STATUS          deprecated
    DESCRIPTION
        "A string which specifies the source interface."
    DEFVAL          { 0 }
    ::= { eltIpSlaAdminUdpJitterEntry 6 }

eltIpSlaAdminUdpJitterInterval OBJECT-TYPE
    SYNTAX          INTEGER (0..60000)
    UNITS           "milliseconds"
    MAX-ACCESS      read-write
    STATUS          deprecated
    DESCRIPTION
        "This value represents the inter-packet delay between packets
        and is in milliseconds. This value is currently used for
        Jitter probe. This object is applicable to jitter probe only."
    DEFVAL          { 20 }
    ::= { eltIpSlaAdminUdpJitterEntry 7 }

eltIpSlaAdminUdpJitterNumPackets OBJECT-TYPE
    SYNTAX          INTEGER (0..1000)
    MAX-ACCESS      read-write
    STATUS          deprecated
    DESCRIPTION
        "This value represents the number of packets that need to be
        transmitted. This value is currently used for Jitter probe.
        This object is applicable to jitter probe only."
    DEFVAL          { 10 }
    ::= { eltIpSlaAdminUdpJitterEntry 8 }

eltIpSlaAdminUdpJitterTimeOut OBJECT-TYPE
    SYNTAX          INTEGER (0..3600000)
    UNITS           "milliseconds"
    MAX-ACCESS      read-write
    STATUS          deprecated
    DESCRIPTION
        "Specifies the duration to wait for a IP SLA operation
        completion.

        For connection oriented protocols, this may cause the
        connection to be closed by the operation.  Once closed, it
        will be assumed that the connection reestablishment
        will be performed.  To prevent unwanted closure of
        connections, be sure to set this value to a realistic
        connection timeout."
    DEFVAL          { 1000 }
    ::= { eltIpSlaAdminUdpJitterEntry 9 }

eltIpSlaAdminUdpJitterReqDataSize OBJECT-TYPE
    SYNTAX          INTEGER (0..1432)
    MAX-ACCESS      read-write
    STATUS          deprecated
    DESCRIPTION
        "This object represents the number of octets to be
        placed into packages send during IP SLA operation"
    DEFVAL          { 30 }
    ::= { eltIpSlaAdminUdpJitterEntry 10 }

eltIpSlaAdminUdpJitterTOS OBJECT-TYPE
    SYNTAX          INTEGER (0..255)
    MAX-ACCESS      read-write
    STATUS          deprecated
    DESCRIPTION
        "This object represents the type of service octet in an
        IP header."
    REFERENCE
        "Refer to the following documents for TOS definition.
               RFC791/1349  for IPv4, IPv6, draft-ietf-diffserv-header-02.txt"
    DEFVAL          { 0 }
    ::= { eltIpSlaAdminUdpJitterEntry 11 }

eltIpSlaAdminUdpJitterRowStatus OBJECT-TYPE
    SYNTAX          RowStatus
    MAX-ACCESS      read-write
    STATUS          deprecated
    DESCRIPTION
        "The status of the MIB entry."
    ::= { eltIpSlaAdminUdpJitterEntry 12 }

-- ICMP Echo Operation Statictics Table

eltIpSlaStatsIcmpEchoTable OBJECT-TYPE
    SYNTAX          SEQUENCE OF EltIpSlaStatsIcmpEchoEntry
    MAX-ACCESS      read-write
    STATUS          deprecated
    DESCRIPTION
        "The database of ICMP Echo operation statistics."
    ::= { eltMesIpSlaStats 2 }

eltIpSlaStatsIcmpEchoEntry OBJECT-TYPE
    SYNTAX          EltIpSlaStatsIcmpEchoEntry
    MAX-ACCESS      read-write
    STATUS          deprecated
    DESCRIPTION
        "A row entry representing an IP SLA operation."
    INDEX           { eltIpSlaStatsIcmpEchoIndex }
    ::= { eltIpSlaStatsIcmpEchoTable 1 }

EltIpSlaStatsIcmpEchoEntry ::= SEQUENCE {
        eltIpSlaStatsIcmpEchoIndex          INTEGER,
        eltIpSlaStatsIcmpEchoLastStatus     EltIpSlaStatsOperStatus,
        eltIpSlaStatsIcmpEchoLastLatency    INTEGER,
        eltIpSlaStatsIcmpEchoMinLatency     INTEGER,
        eltIpSlaStatsIcmpEchoAvgLatency     INTEGER,
        eltIpSlaStatsIcmpEchoMaxLatency     INTEGER,
        eltIpSlaStatsIcmpEchoOperationsCtr  Counter32,
        eltIpSlaStatsIcmpEchoSuccessesCtr   Counter32,
        eltIpSlaStatsIcmpEchoFailuresCtr    Counter32,
        eltIpSlaStatsIcmpEchoTimeoutCtr     Counter32,
        eltIpSlaStatsIcmpEchoUnreachNetCtr  Counter32,
        eltIpSlaStatsIcmpEchoUnreachHostCtr Counter32,
        eltIpSlaStatsIcmpEchoUnreachProtCtr Counter32,
        eltIpSlaStatsIcmpEchoExTimeTransCtr Counter32,
        eltIpSlaStatsIcmpEchoExTimeReassCtr Counter32,
        eltIpSlaStatsIcmpEchoUnableSendCtr  Counter32,
        eltIpSlaStatsIcmpEchoBadReplyCtr    Counter32
}

eltIpSlaStatsIcmpEchoIndex OBJECT-TYPE
    SYNTAX          INTEGER
    MAX-ACCESS      read-write
    STATUS          deprecated
    DESCRIPTION
        "The index of ICMP Echo statistics row. It matches the indexes
        of operations in the Overall Control Group tables."
    ::= { eltIpSlaStatsIcmpEchoEntry 1 }

eltIpSlaStatsIcmpEchoLastStatus OBJECT-TYPE
    SYNTAX          EltIpSlaStatsOperStatus
    MAX-ACCESS      read-only
    STATUS          deprecated
    DESCRIPTION
        "The string contains a status of the last completed operation."
    ::= { eltIpSlaStatsIcmpEchoEntry 2 }

eltIpSlaStatsIcmpEchoLastLatency OBJECT-TYPE
    SYNTAX          INTEGER
    UNITS           "milliseconds"
    MAX-ACCESS      read-only
    STATUS          deprecated
    DESCRIPTION
        "A latency measured during the last completed operation."
    ::= { eltIpSlaStatsIcmpEchoEntry 3 }

eltIpSlaStatsIcmpEchoMinLatency OBJECT-TYPE
    SYNTAX          INTEGER
    UNITS           "milliseconds"
    MAX-ACCESS      read-only
    STATUS          deprecated
    DESCRIPTION
        "The lowest latency measured during all successfully
        completed operations."
    ::= { eltIpSlaStatsIcmpEchoEntry 4 }

eltIpSlaStatsIcmpEchoAvgLatency OBJECT-TYPE
    SYNTAX          INTEGER
    UNITS           "milliseconds"
    MAX-ACCESS      read-only
    STATUS          deprecated
    DESCRIPTION
        "The average of latencies measured during all successfully
        completed operations."
    ::= { eltIpSlaStatsIcmpEchoEntry 5 }

eltIpSlaStatsIcmpEchoMaxLatency OBJECT-TYPE
    SYNTAX          INTEGER
    UNITS           "milliseconds"
    MAX-ACCESS      read-only
    STATUS          deprecated
    DESCRIPTION
        "The highest of latencies measured during all successfully
        completed operations."
    ::= { eltIpSlaStatsIcmpEchoEntry 6 }

eltIpSlaStatsIcmpEchoOperationsCtr OBJECT-TYPE
    SYNTAX          Counter32
    MAX-ACCESS      read-only
    STATUS          deprecated
    DESCRIPTION
        "Indicates the number of all operations which were tried
        to perform."
    ::= { eltIpSlaStatsIcmpEchoEntry 7 }

eltIpSlaStatsIcmpEchoSuccessesCtr OBJECT-TYPE
    SYNTAX          Counter32
    MAX-ACCESS      read-only
    STATUS          deprecated
    DESCRIPTION
        "Indicates the number of successfully completed operations."
    ::= { eltIpSlaStatsIcmpEchoEntry 8 }

eltIpSlaStatsIcmpEchoFailuresCtr OBJECT-TYPE
    SYNTAX          Counter32
    MAX-ACCESS      read-only
    STATUS          deprecated
    DESCRIPTION
        "Indicates the number of unsuccessfully completed operations."
    ::= { eltIpSlaStatsIcmpEchoEntry 9 }

eltIpSlaStatsIcmpEchoTimeoutCtr OBJECT-TYPE
    SYNTAX          Counter32
    MAX-ACCESS      read-only
    STATUS          deprecated
    DESCRIPTION
        "Indicates the number of operations which were failed
        by timeout."
    ::= { eltIpSlaStatsIcmpEchoEntry 10 }

eltIpSlaStatsIcmpEchoUnreachNetCtr OBJECT-TYPE
    SYNTAX          Counter32
    MAX-ACCESS      read-only
    STATUS          deprecated
    DESCRIPTION
        "Indicates the number of operations which were failed
        due to unreachable net."
    ::= { eltIpSlaStatsIcmpEchoEntry 11 }

eltIpSlaStatsIcmpEchoUnreachHostCtr OBJECT-TYPE
    SYNTAX          Counter32
    MAX-ACCESS      read-only
    STATUS          deprecated
    DESCRIPTION
        "Indicates the number of operations which were failed
        due to unreachable host."
    ::= { eltIpSlaStatsIcmpEchoEntry 12 }

eltIpSlaStatsIcmpEchoUnreachProtCtr OBJECT-TYPE
    SYNTAX          Counter32
    MAX-ACCESS      read-only
    STATUS          deprecated
    DESCRIPTION
        "Indicates the number of operations which were failed
        due to unreachable protocol."
    ::= { eltIpSlaStatsIcmpEchoEntry 13 }

eltIpSlaStatsIcmpEchoExTimeTransCtr OBJECT-TYPE
    SYNTAX          Counter32
    MAX-ACCESS      read-only
    STATUS          deprecated
    DESCRIPTION
        "Indicates the number of operations which were failed
        due to exceeded TTL in transit."
    ::= { eltIpSlaStatsIcmpEchoEntry 14 }

eltIpSlaStatsIcmpEchoExTimeReassCtr OBJECT-TYPE
    SYNTAX          Counter32
    MAX-ACCESS      read-only
    STATUS          deprecated
    DESCRIPTION
        "Indicates the number of operations which were failed
        due to exceeded time of fragment reassembly."
    ::= { eltIpSlaStatsIcmpEchoEntry 15 }

eltIpSlaStatsIcmpEchoUnableSendCtr OBJECT-TYPE
    SYNTAX          Counter32
    MAX-ACCESS      read-only
    STATUS          deprecated
    DESCRIPTION
        "Indicates the number of operations which were failed
        while sending a request packet."
    ::= { eltIpSlaStatsIcmpEchoEntry 16 }

eltIpSlaStatsIcmpEchoBadReplyCtr OBJECT-TYPE
    SYNTAX          Counter32
    MAX-ACCESS      read-only
    STATUS          deprecated
    DESCRIPTION
        "Indicates the number of operations which were failed
        due to bad reply data."
    ::= { eltIpSlaStatsIcmpEchoEntry 17 }

-- UDP Jitter Operation Statictics Table

eltIpSlaStatsUdpJitterTable OBJECT-TYPE
    SYNTAX          SEQUENCE OF EltIpSlaStatsUdpJitterEntry
    MAX-ACCESS      read-write
    STATUS          deprecated
    DESCRIPTION
        "The database of UDP Jitter operation statistics."
    ::= { eltMesIpSlaStats 3 }

eltIpSlaStatsUdpJitterEntry OBJECT-TYPE
    SYNTAX          EltIpSlaStatsUdpJitterEntry
    MAX-ACCESS      read-write
    STATUS          deprecated
    DESCRIPTION
        "A row entry representing an IP SLA operation."
    INDEX           { eltIpSlaStatsUdpJitterIndex }
    ::= { eltIpSlaStatsUdpJitterTable 1 }

EltIpSlaStatsUdpJitterEntry ::= SEQUENCE {
        eltIpSlaStatsUdpJitterIndex             INTEGER,
        eltIpSlaStatsUdpJitterLastStatus        EltIpSlaStatsOperStatus,
        eltIpSlaStatsUdpJitterLastLatency       INTEGER,
        eltIpSlaStatsUdpJitterNumLatency        INTEGER,
        eltIpSlaStatsUdpJitterSumLatency        INTEGER,
        eltIpSlaStatsUdpJitterMinLatency        INTEGER,
        eltIpSlaStatsUdpJitterAvgLatency        INTEGER,
        eltIpSlaStatsUdpJitterMaxLatency        INTEGER,
        eltIpSlaStatsUdpJitterNumSDLatency      INTEGER,
        eltIpSlaStatsUdpJitterSumSDLatency      INTEGER,
        eltIpSlaStatsUdpJitterMinSDLatency      INTEGER,
        eltIpSlaStatsUdpJitterAvgSDLatency      INTEGER,
        eltIpSlaStatsUdpJitterMaxSDLatency      INTEGER,
        eltIpSlaStatsUdpJitterNumDSLatency      INTEGER,
        eltIpSlaStatsUdpJitterSumDSLatency      INTEGER,
        eltIpSlaStatsUdpJitterMinDSLatency      INTEGER,
        eltIpSlaStatsUdpJitterAvgDSLatency      INTEGER,
        eltIpSlaStatsUdpJitterMaxDSLatency      INTEGER,
        eltIpSlaStatsUdpJitterNumSDPosJitter    INTEGER,
        eltIpSlaStatsUdpJitterSumSDPosJitter    INTEGER,
        eltIpSlaStatsUdpJitterMinSDPosJitter    INTEGER,
        eltIpSlaStatsUdpJitterAvgSDPosJitter    INTEGER,
        eltIpSlaStatsUdpJitterMaxSDPosJitter    INTEGER,
        eltIpSlaStatsUdpJitterNumDSPosJitter    INTEGER,
        eltIpSlaStatsUdpJitterSumDSPosJitter    INTEGER,
        eltIpSlaStatsUdpJitterMinDSPosJitter    INTEGER,
        eltIpSlaStatsUdpJitterAvgDSPosJitter    INTEGER,
        eltIpSlaStatsUdpJitterMaxDSPosJitter    INTEGER,
        eltIpSlaStatsUdpJitterNumSDNegJitter    INTEGER,
        eltIpSlaStatsUdpJitterSumSDNegJitter    INTEGER,
        eltIpSlaStatsUdpJitterMinSDNegJitter    INTEGER,
        eltIpSlaStatsUdpJitterAvgSDNegJitter    INTEGER,
        eltIpSlaStatsUdpJitterMaxSDNegJitter    INTEGER,
        eltIpSlaStatsUdpJitterNumDSNegJitter    INTEGER,
        eltIpSlaStatsUdpJitterSumDSNegJitter    INTEGER,
        eltIpSlaStatsUdpJitterMinDSNegJitter    INTEGER,
        eltIpSlaStatsUdpJitterAvgDSNegJitter    INTEGER,
        eltIpSlaStatsUdpJitterMaxDSNegJitter    INTEGER,
        eltIpSlaStatsUdpJitterOperationsCtr     Counter32,
        eltIpSlaStatsUdpJitterSuccessesCtr      Counter32,
        eltIpSlaStatsUdpJitterFailuresCtr       Counter32,
        eltIpSlaStatsUdpJitterTimeoutCtr        Counter32,
        eltIpSlaStatsUdpJitterUnreachNetCtr     Counter32,
        eltIpSlaStatsUdpJitterUnreachHostCtr    Counter32,
        eltIpSlaStatsUdpJitterUnreachPortCtr    Counter32,
        eltIpSlaStatsUdpJitterUnreachProtCtr    Counter32,
        eltIpSlaStatsUdpJitterExTimeTransCtr    Counter32,
        eltIpSlaStatsUdpJitterExTimeReassCtr    Counter32,
        eltIpSlaStatsUdpJitterUnableSendCtr     Counter32,
        eltIpSlaStatsUdpJitterBadReplyCtr       Counter32,
        eltIpSlaStatsUdpJitterPacketsOOSCtr     Counter32
}

eltIpSlaStatsUdpJitterIndex OBJECT-TYPE
    SYNTAX          INTEGER
    MAX-ACCESS      read-write
    STATUS          deprecated
    DESCRIPTION
        "The index of UDP Jitter statistics row. It matches the indexes
        of operations in the Overall Control Group tables."
    ::= { eltIpSlaStatsUdpJitterEntry 1 }

eltIpSlaStatsUdpJitterLastStatus OBJECT-TYPE
    SYNTAX          EltIpSlaStatsOperStatus
    MAX-ACCESS      read-only
    STATUS          deprecated
    DESCRIPTION
        "The string contains a status of the last completed operation."
    ::= { eltIpSlaStatsUdpJitterEntry 2 }

eltIpSlaStatsUdpJitterLastLatency OBJECT-TYPE
    SYNTAX          INTEGER
    UNITS           "milliseconds"
    MAX-ACCESS      read-only
    STATUS          deprecated
    DESCRIPTION
        "A two-way latency measured during the last completed operation."
    ::= { eltIpSlaStatsUdpJitterEntry 3 }

eltIpSlaStatsUdpJitterNumLatency OBJECT-TYPE
    SYNTAX          INTEGER
    UNITS           "milliseconds"
    MAX-ACCESS      read-only
    STATUS          deprecated
    DESCRIPTION
        "The number of two-way latencies measured during  all successfully
        completed operations."
    ::= { eltIpSlaStatsUdpJitterEntry 4 }

eltIpSlaStatsUdpJitterSumLatency OBJECT-TYPE
    SYNTAX          INTEGER
    UNITS           "milliseconds"
    MAX-ACCESS      read-only
    STATUS          deprecated
    DESCRIPTION
        "The sum of two-way latencies measured during  all successfully
        completed operations."
    ::= { eltIpSlaStatsUdpJitterEntry 5 }

eltIpSlaStatsUdpJitterMinLatency OBJECT-TYPE
    SYNTAX          INTEGER
    UNITS           "milliseconds"
    MAX-ACCESS      read-only
    STATUS          deprecated
    DESCRIPTION
        "The lowest two-way latency measured during all successfully
        completed operations."
    ::= { eltIpSlaStatsUdpJitterEntry 6 }

eltIpSlaStatsUdpJitterAvgLatency OBJECT-TYPE
    SYNTAX          INTEGER
    UNITS           "milliseconds"
    MAX-ACCESS      read-only
    STATUS          deprecated
    DESCRIPTION
        "The average of two-way latencies measured during all successfully
        completed operations."
    ::= { eltIpSlaStatsUdpJitterEntry 7 }

eltIpSlaStatsUdpJitterMaxLatency OBJECT-TYPE
    SYNTAX          INTEGER
    UNITS           "milliseconds"
    MAX-ACCESS      read-only
    STATUS          deprecated
    DESCRIPTION
        "The highest of two-way latencies measured during all successfully
        completed operations."
    ::= { eltIpSlaStatsUdpJitterEntry 8 }

eltIpSlaStatsUdpJitterNumSDLatency OBJECT-TYPE
    SYNTAX          INTEGER
    MAX-ACCESS      read-only
    STATUS          deprecated
    DESCRIPTION
        "The number of one-way source-to-destination latencies measured
        during all successfully completed operations."
    ::= { eltIpSlaStatsUdpJitterEntry 9 }

eltIpSlaStatsUdpJitterSumSDLatency OBJECT-TYPE
    SYNTAX          INTEGER
    UNITS           "milliseconds"
    MAX-ACCESS      read-only
    STATUS          deprecated
    DESCRIPTION
        "The sum of one-way source-to-destination latencies measured
        during all successfully completed operations."
    ::= { eltIpSlaStatsUdpJitterEntry 10 }

eltIpSlaStatsUdpJitterMinSDLatency OBJECT-TYPE
    SYNTAX          INTEGER
    UNITS           "milliseconds"
    MAX-ACCESS      read-only
    STATUS          deprecated
    DESCRIPTION
        "The lowest one-way source-to-destination latency measured
        during all successfully completed operations."
    ::= { eltIpSlaStatsUdpJitterEntry 11 }

eltIpSlaStatsUdpJitterAvgSDLatency OBJECT-TYPE
    SYNTAX          INTEGER
    UNITS           "milliseconds"
    MAX-ACCESS      read-only
    STATUS          deprecated
    DESCRIPTION
        "The average one-way source-to-destination latency measured
        during all successfully completed operations."
    ::= { eltIpSlaStatsUdpJitterEntry 12 }

eltIpSlaStatsUdpJitterMaxSDLatency OBJECT-TYPE
    SYNTAX          INTEGER
    UNITS           "milliseconds"
    MAX-ACCESS      read-only
    STATUS          deprecated
    DESCRIPTION
        "The maximum one-way source-to-destination latency measured
        during all successfully completed operations."
    ::= { eltIpSlaStatsUdpJitterEntry 13 }

eltIpSlaStatsUdpJitterNumDSLatency OBJECT-TYPE
    SYNTAX          INTEGER
    MAX-ACCESS      read-only
    STATUS          deprecated
    DESCRIPTION
        "The number of one-way destination-to-source latencies measured
        during all successfully completed operations."
    ::= { eltIpSlaStatsUdpJitterEntry 14 }

eltIpSlaStatsUdpJitterSumDSLatency OBJECT-TYPE
    SYNTAX          INTEGER
    UNITS           "milliseconds"
    MAX-ACCESS      read-only
    STATUS          deprecated
    DESCRIPTION
        "The sum of one-way destination-to-source latencies measured
        during all successfully completed operations."
    ::= { eltIpSlaStatsUdpJitterEntry 15 }

eltIpSlaStatsUdpJitterMinDSLatency OBJECT-TYPE
    SYNTAX          INTEGER
    UNITS           "milliseconds"
    MAX-ACCESS      read-only
    STATUS          deprecated
    DESCRIPTION
        "The lowest one-way destination-to-source latency measured
        during all successfully completed operations."
    ::= { eltIpSlaStatsUdpJitterEntry 16 }

eltIpSlaStatsUdpJitterAvgDSLatency OBJECT-TYPE
    SYNTAX          INTEGER
    UNITS           "milliseconds"
    MAX-ACCESS      read-only
    STATUS          deprecated
    DESCRIPTION
        "The average one-way destination-to-source latency measured
        during all successfully completed operations."
    ::= { eltIpSlaStatsUdpJitterEntry 17 }

eltIpSlaStatsUdpJitterMaxDSLatency OBJECT-TYPE
    SYNTAX          INTEGER
    UNITS           "milliseconds"
    MAX-ACCESS      read-only
    STATUS          deprecated
    DESCRIPTION
        "The maximum one-way destination-to-source latency measured
        during all successfully completed operations."
    ::= { eltIpSlaStatsUdpJitterEntry 18 }

eltIpSlaStatsUdpJitterNumSDPosJitter OBJECT-TYPE
    SYNTAX          INTEGER
    MAX-ACCESS      read-only
    STATUS          deprecated
    DESCRIPTION
        "The number of one-way source-to-destination positive jitters
        measured during all successfully completed operations."
    ::= { eltIpSlaStatsUdpJitterEntry 19 }

eltIpSlaStatsUdpJitterSumSDPosJitter OBJECT-TYPE
    SYNTAX          INTEGER
    MAX-ACCESS      read-only
    STATUS          deprecated
    DESCRIPTION
        "The sum of one-way source-to-destination positive jitters
        measured during all successfully completed operations."
    ::= { eltIpSlaStatsUdpJitterEntry 20 }

eltIpSlaStatsUdpJitterMinSDPosJitter OBJECT-TYPE
    SYNTAX          INTEGER
    UNITS           "milliseconds"
    MAX-ACCESS      read-only
    STATUS          deprecated
    DESCRIPTION
        "The lowest one-way source-to-destination positive jitter
        measured during all successfully completed operations."
    ::= { eltIpSlaStatsUdpJitterEntry 21 }

eltIpSlaStatsUdpJitterAvgSDPosJitter OBJECT-TYPE
    SYNTAX          INTEGER
    UNITS           "milliseconds"
    MAX-ACCESS      read-only
    STATUS          deprecated
    DESCRIPTION
        "The average one-way source-to-destination positive jitter
        measured during all successfully completed operations."
    ::= { eltIpSlaStatsUdpJitterEntry 22 }

eltIpSlaStatsUdpJitterMaxSDPosJitter OBJECT-TYPE
    SYNTAX          INTEGER
    UNITS           "milliseconds"
    MAX-ACCESS      read-only
    STATUS          deprecated
    DESCRIPTION
        "The maximum one-way source-to-destination positive jitter
        measured during all successfully completed operations."
    ::= { eltIpSlaStatsUdpJitterEntry 23 }

eltIpSlaStatsUdpJitterNumDSPosJitter OBJECT-TYPE
    SYNTAX          INTEGER
    MAX-ACCESS      read-only
    STATUS          deprecated
    DESCRIPTION
        "The number of one-way destination-to-source positive jitters
        measured during all successfully completed operations."
    ::= { eltIpSlaStatsUdpJitterEntry 24 }

eltIpSlaStatsUdpJitterSumDSPosJitter OBJECT-TYPE
    SYNTAX          INTEGER
    UNITS           "milliseconds"
    MAX-ACCESS      read-only
    STATUS          deprecated
    DESCRIPTION
        "The sum of one-way destination-to-source positive jitters
        measured during all successfully completed operations."
    ::= { eltIpSlaStatsUdpJitterEntry 25 }

eltIpSlaStatsUdpJitterMinDSPosJitter OBJECT-TYPE
    SYNTAX          INTEGER
    UNITS           "milliseconds"
    MAX-ACCESS      read-only
    STATUS          deprecated
    DESCRIPTION
        "The lowest one-way destination-to-source positive jitter
        measured during all successfully completed operations."
    ::= { eltIpSlaStatsUdpJitterEntry 26 }

eltIpSlaStatsUdpJitterAvgDSPosJitter OBJECT-TYPE
    SYNTAX          INTEGER
    UNITS           "milliseconds"
    MAX-ACCESS      read-only
    STATUS          deprecated
    DESCRIPTION
        "The average one-way destination-to-source positive jitter
        measured  during all successfully completed operations."
    ::= { eltIpSlaStatsUdpJitterEntry 27 }

eltIpSlaStatsUdpJitterMaxDSPosJitter OBJECT-TYPE
    SYNTAX          INTEGER
    UNITS           "milliseconds"
    MAX-ACCESS      read-only
    STATUS          deprecated
    DESCRIPTION
        "The maximum one-way destination-to-source positive jitter
        measured during all successfully completed operations."
    ::= { eltIpSlaStatsUdpJitterEntry 28 }

eltIpSlaStatsUdpJitterNumSDNegJitter OBJECT-TYPE
    SYNTAX          INTEGER
    MAX-ACCESS      read-only
    STATUS          deprecated
    DESCRIPTION
        "The number of one-way source-to-destination negative jitters
        measured during all successfully completed operations."
    ::= { eltIpSlaStatsUdpJitterEntry 29 }

eltIpSlaStatsUdpJitterSumSDNegJitter OBJECT-TYPE
    SYNTAX          INTEGER
    MAX-ACCESS      read-only
    STATUS          deprecated
    DESCRIPTION
        "The sum of one-way source-to-destination negative jitters
        measured during all successfully completed operations."
    ::= { eltIpSlaStatsUdpJitterEntry 30 }

eltIpSlaStatsUdpJitterMinSDNegJitter OBJECT-TYPE
    SYNTAX          INTEGER
    UNITS           "milliseconds"
    MAX-ACCESS      read-only
    STATUS          deprecated
    DESCRIPTION
        "The lowest one-way source-to-destination negative jitter
        measured during all successfully completed operations."
    ::= { eltIpSlaStatsUdpJitterEntry 31 }

eltIpSlaStatsUdpJitterAvgSDNegJitter OBJECT-TYPE
    SYNTAX          INTEGER
    UNITS           "milliseconds"
    MAX-ACCESS      read-only
    STATUS          deprecated
    DESCRIPTION
        "The average one-way source-to-destination negative jitter
        measured during all successfully completed operations."
    ::= { eltIpSlaStatsUdpJitterEntry 32 }

eltIpSlaStatsUdpJitterMaxSDNegJitter OBJECT-TYPE
    SYNTAX          INTEGER
    UNITS           "milliseconds"
    MAX-ACCESS      read-only
    STATUS          deprecated
    DESCRIPTION
        "The maximum one-way source-to-destination negative jitter
        measured during all successfully completed operations."
    ::= { eltIpSlaStatsUdpJitterEntry 33 }

eltIpSlaStatsUdpJitterNumDSNegJitter OBJECT-TYPE
    SYNTAX          INTEGER
    MAX-ACCESS      read-only
    STATUS          deprecated
    DESCRIPTION
        "The number of one-way destination-to-source negative jitters
        measured during all successfully completed operations."
    ::= { eltIpSlaStatsUdpJitterEntry 34 }

eltIpSlaStatsUdpJitterSumDSNegJitter OBJECT-TYPE
    SYNTAX          INTEGER
    UNITS           "milliseconds"
    MAX-ACCESS      read-only
    STATUS          deprecated
    DESCRIPTION
        "The sum oflowest one-way destination-to-source negative jitters
        measured during all successfully completed operations."
    ::= { eltIpSlaStatsUdpJitterEntry 35 }

eltIpSlaStatsUdpJitterMinDSNegJitter OBJECT-TYPE
    SYNTAX          INTEGER
    UNITS           "milliseconds"
    MAX-ACCESS      read-only
    STATUS          deprecated
    DESCRIPTION
        "The lowest one-way destination-to-source negative jitter
        measured during all successfully completed operations."
    ::= { eltIpSlaStatsUdpJitterEntry 36 }

eltIpSlaStatsUdpJitterAvgDSNegJitter OBJECT-TYPE
    SYNTAX          INTEGER
    UNITS           "milliseconds"
    MAX-ACCESS      read-only
    STATUS          deprecated
    DESCRIPTION
        "The average one-way destination-to-source negative jitter
        measured  during all successfully completed operations."
    ::= { eltIpSlaStatsUdpJitterEntry 37 }

eltIpSlaStatsUdpJitterMaxDSNegJitter OBJECT-TYPE
    SYNTAX          INTEGER
    UNITS           "milliseconds"
    MAX-ACCESS      read-only
    STATUS          deprecated
    DESCRIPTION
        "The maximum one-way destination-to-source negative jitter
        measured during all successfully completed operations."
    ::= { eltIpSlaStatsUdpJitterEntry 38 }

eltIpSlaStatsUdpJitterOperationsCtr OBJECT-TYPE
    SYNTAX          Counter32
    MAX-ACCESS      read-only
    STATUS          deprecated
    DESCRIPTION
        "Indicates the number of all operations which were tried
        to perform."
    ::= { eltIpSlaStatsUdpJitterEntry 39 }

eltIpSlaStatsUdpJitterSuccessesCtr OBJECT-TYPE
    SYNTAX          Counter32
    MAX-ACCESS      read-only
    STATUS          deprecated
    DESCRIPTION
        "Indicates the number of successfully completed operations."
    ::= { eltIpSlaStatsUdpJitterEntry 40 }

eltIpSlaStatsUdpJitterFailuresCtr OBJECT-TYPE
    SYNTAX          Counter32
    MAX-ACCESS      read-only
    STATUS          deprecated
    DESCRIPTION
        "Indicates the number of unsuccessfully completed operations."
    ::= { eltIpSlaStatsUdpJitterEntry 41 }

eltIpSlaStatsUdpJitterTimeoutCtr OBJECT-TYPE
    SYNTAX          Counter32
    MAX-ACCESS      read-only
    STATUS          deprecated
    DESCRIPTION
        "Indicates the number of operations which were failed
        by timeout."
    ::= { eltIpSlaStatsUdpJitterEntry 42 }

eltIpSlaStatsUdpJitterUnreachNetCtr OBJECT-TYPE
    SYNTAX          Counter32
    MAX-ACCESS      read-only
    STATUS          deprecated
    DESCRIPTION
        "Indicates the number of operations which were failed
        due to unreachable net."
    ::= { eltIpSlaStatsUdpJitterEntry 43 }

eltIpSlaStatsUdpJitterUnreachHostCtr OBJECT-TYPE
    SYNTAX          Counter32
    MAX-ACCESS      read-only
    STATUS          deprecated
    DESCRIPTION
        "Indicates the number of operations which were failed
        due to unreachable host."
    ::= { eltIpSlaStatsUdpJitterEntry 44 }

eltIpSlaStatsUdpJitterUnreachPortCtr OBJECT-TYPE
    SYNTAX          Counter32
    MAX-ACCESS      read-only
    STATUS          deprecated
    DESCRIPTION
        "Indicates the number of operations which were failed
        due to unreachable UDP port."
    ::= { eltIpSlaStatsUdpJitterEntry 45 }

eltIpSlaStatsUdpJitterUnreachProtCtr OBJECT-TYPE
    SYNTAX          Counter32
    MAX-ACCESS      read-only
    STATUS          deprecated
    DESCRIPTION
        "Indicates the number of operations which were failed
        due to unreachable protocol."
    ::= { eltIpSlaStatsUdpJitterEntry 46 }

eltIpSlaStatsUdpJitterExTimeTransCtr OBJECT-TYPE
    SYNTAX          Counter32
    MAX-ACCESS      read-only
    STATUS          deprecated
    DESCRIPTION
        "Indicates the number of operations which were failed
        due to exceeded TTL in transit."
    ::= { eltIpSlaStatsUdpJitterEntry 47 }

eltIpSlaStatsUdpJitterExTimeReassCtr OBJECT-TYPE
    SYNTAX          Counter32
    MAX-ACCESS      read-only
    STATUS          deprecated
    DESCRIPTION
        "Indicates the number of operations which were failed
        due to exceeded time of fragment reassembly."
    ::= { eltIpSlaStatsUdpJitterEntry 48 }

eltIpSlaStatsUdpJitterUnableSendCtr OBJECT-TYPE
    SYNTAX          Counter32
    MAX-ACCESS      read-only
    STATUS          deprecated
    DESCRIPTION
        "Indicates the number of operations which were failed
        while sending a request packet."
    ::= { eltIpSlaStatsUdpJitterEntry 49 }

eltIpSlaStatsUdpJitterBadReplyCtr OBJECT-TYPE
    SYNTAX          Counter32
    MAX-ACCESS      read-only
    STATUS          deprecated
    DESCRIPTION
        "Indicates the number of operations which were failed
        due to bad reply data."
    ::= { eltIpSlaStatsUdpJitterEntry 50 }

eltIpSlaStatsUdpJitterPacketsOOSCtr OBJECT-TYPE
    SYNTAX          Counter32
    MAX-ACCESS      read-only
    STATUS          deprecated
    DESCRIPTION
        "Indicates the number of packets recievied out of sequence."
    ::= { eltIpSlaStatsUdpJitterEntry 51 }

-- Schedule start/stop triggers
eltIpSlaScheduleStartTrigger OBJECT-TYPE
    SYNTAX          INTEGER
    MAX-ACCESS      read-write
    STATUS          deprecated
    DESCRIPTION
        "Writing operation's index in this scalar triggers
        starting of the operation."
    ::= { eltMesIpSlaSchedule 1 }

eltIpSlaScheduleStopTrigger OBJECT-TYPE
    SYNTAX          INTEGER
    MAX-ACCESS      read-write
    STATUS          deprecated
    DESCRIPTION
        "Writing operation's index in this scalar triggers
        stopping of the operation."
    ::= { eltMesIpSlaSchedule 2 }

-- NOTIFICATION DEFINITIONS
--
-- This section defines the traps that
-- can be generated by the agent.

--eltMesIpSlaNotifications OBJECT IDENTIFIER
--    ::= { eltMesIpSlaMIB 2 }

END

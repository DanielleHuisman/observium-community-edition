ELTEX-MES-ISS-BRIDGE-MIB DEFINITIONS ::= BEGIN

IMPORTS
    MODULE-IDENTITY
            FROM SNMPv2-SMI
    eltMesIss
            FROM ELTEX-MES-ISS-MIB;


eltMesIssBridgeMIB MODULE-IDENTITY
    LAST-UPDATED "201906030000Z"
    ORGANIZATION "Eltex Enterprise, Ltd."
    CONTACT-INFO
            "eltex-co.ru"
    DESCRIPTION
            "MIB extensions for IEEE 802.1Q Bridge.
             This is an aggregation MIB for all Spanning Tree protocols."
    REVISION "201905210000Z"
    DESCRIPTION "Initial revision."
    ::= { eltMesIss 14 }

eltMesIssBridgeMIBObjects   OBJECT IDENTIFIER ::= { eltMesIssBridgeMIB 1 }

eltMesIssMstMIB             OBJECT IDENTIFIER ::= { eltMesIssBridgeMIBObjects 1 }
 -- see ELTEX-MES-ISS-MST-MIB.mib

END

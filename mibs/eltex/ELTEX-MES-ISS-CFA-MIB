ELTEX-MES-ISS-CFA-MIB DEFINITIONS ::= BEGIN

IMPORTS
    OBJECT-TYPE, MODULE-IDENTITY
            FROM SNMPv2-SMI
    eltMesIss
            FROM ELTEX-MES-ISS-MIB;


eltMesIssCfaMIB MODULE-IDENTITY
    LAST-UPDATED "202005250000Z"
    ORGANIZATION "Eltex Enterprise, Ltd."
    CONTACT-INFO
            "eltex-co.ru"
    DESCRIPTION
            "Eltex MIB extensions for CFA module."
    REVISION "202005250000Z"
    DESCRIPTION "Initial revision."
    ::= { eltMesIss 20 }

-- Top level MIB structure

eltMesIssCfaObjects        OBJECT IDENTIFIER ::= { eltMesIssCfaMIB 1 }
eltMesIssCfaNotifications  OBJECT IDENTIFIER ::= { eltMesIssCfaMIB 2 }

-- MIB Groups

eltMesIssCfaGlobals        OBJECT IDENTIFIER ::= { eltMesIssCfaObjects 1 }

-- Low level Mib structure

-- -----------------------------------------------------------------------------
-- CFA global variables
-- -----------------------------------------------------------------------------

eltMesIssCfaGlobalMtu OBJECT-TYPE
    SYNTAX      INTEGER (128..12288)
    MAX-ACCESS  read-write
    STATUS      current
    DESCRIPTION
        "This variable allows to change MTU globally on all interfaces.
         The maximum MTU value may differ between devices."
    ::= { eltMesIssCfaGlobals 1 }

END

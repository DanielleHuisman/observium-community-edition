ELTEX-MES-ISS-ERPS-MIB DEFINITIONS ::= BEGIN

IMPORTS
    OBJECT-TYPE, MODULE-IDENTITY, Unsigned32
            FROM SNMPv2-SMI
    RowStatus
            FROM SNMPv2-TC
    fsErpsContextId, fsErpsRingId
            FROM ARICENT-ERPS-MIB
    eltMesIss
            FROM ELTEX-MES-ISS-MIB;

eltMesIssErpsMIB MODULE-IDENTITY
    LAST-UPDATED "202112060000Z"
    ORGANIZATION "Eltex Enterprise, Ltd."
    CONTACT-INFO
            "eltex-co.ru"
    DESCRIPTION
            "Eltex MIB extensions for ERPS module."
    REVISION "202112060000Z"
    DESCRIPTION "Initial revision."

    ::= { eltMesIss 29 }


-- Top level MIB structure

eltMesIssErpsObjects       OBJECT IDENTIFIER ::= { eltMesIssErpsMIB 1 }

-- MIB Groups

eltMesIssErpsRingConfig        OBJECT IDENTIFIER ::= { eltMesIssErpsObjects 1 }

-- --------------------------------------------------------------------------
-- Ring's IFM Table
-- --------------------------------------------------------------------------

eltMesIssErpsRingIfmTable OBJECT-TYPE
    SYNTAX      SEQUENCE OF EltMesIssErpsRingIfmEntry
    MAX-ACCESS  not-accessible
    STATUS      current
    DESCRIPTION
        "This table contains the configurations related to the monitoring
         entities of the ring entry in the fsErpsRingTable.

         Entry can be created for a {ContextId , RingId} in this table, only
         when the corresponding entry exists in the fsErpsRingTable."
    ::= { eltMesIssErpsRingConfig 2 }

eltMesIssErpsRingIfmEntry OBJECT-TYPE
    SYNTAX      EltMesIssErpsRingIfmEntry
    MAX-ACCESS  not-accessible
    STATUS      current
    DESCRIPTION
        "The entry indicates the monitoring entities for each ring entry."
    INDEX { fsErpsContextId, fsErpsRingId }
    ::= { eltMesIssErpsRingIfmTable 1 }

EltMesIssErpsRingIfmEntry ::=
    SEQUENCE {
        eltMesIssErpsRingIfmMdLevel
            Unsigned32,
        eltMesIssErpsRingIfmRowStatus
            RowStatus
    }

eltMesIssErpsRingIfmMdLevel OBJECT-TYPE
    SYNTAX      Unsigned32(0..7)
    MAX-ACCESS  read-write
    STATUS      current
    DESCRIPTION
        "This refers to the Maintenance Domain Level.
         Every incoming ERPS packet will be forwarded to a ring with
         confiured monitoring type IFM on the same MD level."
   ::= { eltMesIssErpsRingIfmEntry 1 }

eltMesIssErpsRingIfmRowStatus OBJECT-TYPE
    SYNTAX      RowStatus
    MAX-ACCESS  read-write
    STATUS      current
    DESCRIPTION
        "Denotes the Row Status of the Ring IFM Entry.  Creation or
         modification of any entry in this table is allowed, only when the
         corresponding ring entry is created and not active in the
         fsErpsRingTable.

         Similarly RowStatus of fsErpsRingTable can't be made active,
         when this RowStaus is not active.
         This object cannot be set to 'destroy', if corresponding ring
         entry's RowStatus in fsErpsRingTable is active."
    ::= { eltMesIssErpsRingIfmEntry 2 }

END

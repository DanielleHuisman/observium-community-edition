ELTEX-MES-ISS-FIREWALL-MIB DEFINITIONS ::= BEGIN

IMPORTS
    OBJECT-TYPE, MODULE-IDENTITY
            FROM SNMPv2-SMI
    TruthValue
            FROM SNMPv2-TC
    ifIndex
            FROM IF-MIB
    eltMesIss
            FROM ELTEX-MES-ISS-MIB;

eltMesIssFwlMIB MODULE-IDENTITY
    LAST-UPDATED "202104210000Z"
    ORGANIZATION "Eltex Enterprise, Ltd."
    CONTACT-INFO
        "eltex-co.ru"
    DESCRIPTION
        "This MIB module contains security features."
    REVISION "202104210000Z"
    DESCRIPTION "Initial revision."
    ::= { eltMesIss 27 }

-- Top level MIB structure

eltMesIssFwlObjects        OBJECT IDENTIFIER ::= { eltMesIssFwlMIB 1 }
eltMesIssFwlNotifications  OBJECT IDENTIFIER ::= { eltMesIssFwlMIB 2 }

-- MIB Groups

eltMesIssFwlGlobals        OBJECT IDENTIFIER ::= { eltMesIssFwlObjects 1 }
eltMesIssFwlTcpSynLimit    OBJECT IDENTIFIER ::= { eltMesIssFwlObjects 2 }

-- -----------------------------------------------------------------------------
-- Firewall Warning global configuration
-- -----------------------------------------------------------------------------

eltMesIssFwlNotificationInterval OBJECT-TYPE
    SYNTAX      INTEGER
    MAX-ACCESS  read-write
    STATUS      current
    DESCRIPTION
        "Defines the interval between notifications
         about Firewall security violations in seconds."
    ::= { eltMesIssFwlGlobals 1 }

-- -----------------------------------------------------------------------------
-- TCP SYN Limit global configuration
-- -----------------------------------------------------------------------------

eltMesIssFwlTcpSynLimitEnable OBJECT-TYPE
    SYNTAX      TruthValue
    MAX-ACCESS  read-write
    STATUS      current
    DESCRIPTION
        "Defines the state of TCP SYN packets limit.
         It is used to prevent TCP Flood Attack."
    DEFVAL { false }
    ::= { eltMesIssFwlTcpSynLimit 1 }

-- -----------------------------------------------------------------------------
-- TCP SYN Limit Interface table
-- -----------------------------------------------------------------------------

eltMesIssFwlTcpSynLimitInterfaceTable OBJECT-TYPE
    SYNTAX      SEQUENCE OF EltMesIssFwlTcpSynLimitInterfaceEntry
    MAX-ACCESS  not-accessible
    STATUS      current
    DESCRIPTION
        "The table contains interface security settings."
    ::= { eltMesIssFwlTcpSynLimit 2 }

eltMesIssFwlTcpSynLimitInterfaceEntry OBJECT-TYPE
    SYNTAX      EltMesIssFwlTcpSynLimitInterfaceEntry
    MAX-ACCESS  not-accessible
    STATUS      current
    DESCRIPTION
        "The row definition for this table."
    INDEX { ifIndex }
    ::= { eltMesIssFwlTcpSynLimitInterfaceTable 1 }

EltMesIssFwlTcpSynLimitInterfaceEntry ::=
    SEQUENCE {
        eltMesIssFwlTcpSynLimitValue  INTEGER
    }

eltMesIssFwlTcpSynLimitValue OBJECT-TYPE
    SYNTAX      INTEGER
    MAX-ACCESS  read-write
    STATUS      current
    DESCRIPTION
        "Limit of TCP SYN packets per second.
         0 means that limit is disabled."
    ::= { eltMesIssFwlTcpSynLimitInterfaceEntry 1 }

END

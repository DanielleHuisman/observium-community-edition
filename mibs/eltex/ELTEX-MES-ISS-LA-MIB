ELTEX-MES-ISS-LA-MIB DEFINITIONS ::= BEGIN

IMPORTS
    OBJECT-TYPE, MODULE-IDENTITY, Integer32
            FROM SNMPv2-SMI
    eltMesIss
            FROM ELTEX-MES-ISS-MIB;


eltMesIssLaMIB MODULE-IDENTITY
    LAST-UPDATED "202012280000Z"
    ORGANIZATION "Eltex Enterprise, Ltd."
    CONTACT-INFO
            "eltex-co.ru"
    DESCRIPTION
            "Eltex MIB extensions for LA module."
    REVISION "202012280000Z"
    DESCRIPTION "Initial revision."
    ::= { eltMesIss 23 }

-- Top level MIB structure
eltMesIssLaObjects         OBJECT IDENTIFIER ::= { eltMesIssLaMIB 1 }

-- MIB Groups
eltMesIssLaGlobals         OBJECT IDENTIFIER ::= { eltMesIssLaObjects 1 }

-- -----------------------------------------------------------------------------
-- LA global variables
-- -----------------------------------------------------------------------------
eltMesIssLaSelectionPolicyTable  OBJECT-TYPE
    SYNTAX     SEQUENCE OF EltMesIssLaSelectionPolicyEntry
    MAX-ACCESS not-accessible
    STATUS     current
    DESCRIPTION
       "This table contains sets of policy configurations to be used by port-channels."
    ::= { eltMesIssLaGlobals 1 }

eltMesIssLaSelectionPolicyEntry OBJECT-TYPE
    SYNTAX     EltMesIssLaSelectionPolicyEntry
    MAX-ACCESS not-accessible
    STATUS     current
    DESCRIPTION
          "An entry for each policy set."
    INDEX { eltMesIssLaAlgorithmIdx }
    ::= { eltMesIssLaSelectionPolicyTable 1 }

EltMesIssLaSelectionPolicyEntry ::=
    SEQUENCE {
        eltMesIssLaAlgorithmIdx
            Integer32,
        eltMesIssLaPortChannelSelectionPolicy
            INTEGER
    }

eltMesIssLaAlgorithmIdx OBJECT-TYPE
        SYNTAX      Integer32
        MAX-ACCESS  not-accessible
        STATUS      current
        DESCRIPTION
              "Distribution algorithm index."
        ::= { eltMesIssLaSelectionPolicyEntry 1 }

eltMesIssLaPortChannelSelectionPolicy OBJECT-TYPE
    SYNTAX  INTEGER {
        macSrc(1),
        macDst(2),
        macSrcDst(3),
        ipSrc(4),
        ipDst(5),
        ipSrcDst(6),
        macIpSrcDst(7),
        macIpPortSrcDst(8)
    }
    MAX-ACCESS  read-write
    STATUS      current
    DESCRIPTION
        "Link selection policy to be used by the port-channels."
    DEFVAL {macSrcDst}
    ::= { eltMesIssLaSelectionPolicyEntry 2 }

END

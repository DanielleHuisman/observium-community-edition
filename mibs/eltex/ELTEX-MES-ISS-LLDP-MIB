ELTEX-MES-ISS-LLDP-MIB DEFINITIONS ::= BEGIN

-- Title:      ELTEX LLDP Private MIB
-- Version:    1.0
-- Date:       12 Feb 2019

IMPORTS
        MODULE-IDENTITY, OBJECT-TYPE
            FROM SNMPv2-SMI
        OBJECT-GROUP
            FROM SNMPv2-CONF
        TruthValue, DisplayString
            FROM SNMPv2-TC
        eltMesIss
            FROM ELTEX-MES-ISS-MIB;

eltMesIssLldpMIB MODULE-IDENTITY
        LAST-UPDATED "201902120000Z"
        ORGANIZATION "Eltex Enterprise, Ltd."
        CONTACT-INFO
                "eltex-co.ru"
        DESCRIPTION
                "LLDP MIB definitions."
        REVISION "201902120000Z"
        DESCRIPTION "Initial revision."
    ::= { eltMesIss 10 }

eltMesIssLldpObjects        OBJECT IDENTIFIER ::= { eltMesIssLldpMIB 1 }

eltMesIssLldpGlobalConfig   OBJECT IDENTIFIER ::= { eltMesIssLldpObjects 1 }

-- ---------------------
-- LLDP Global Config --
-- ---------------------

eltMesIssLldpduMode OBJECT-TYPE
    SYNTAX  INTEGER {
        filtering(1),
        flooding(2)
    }
    MAX-ACCESS  read-write
    STATUS      current
    DESCRIPTION
        "Action with LLDPDU upon globally disabled LLDP.

        If the associated eltMesIssLldpduMode object has a value of
        'filtering(1)', then received frames are containing LLDPDU
        will be dropped.

        If the associated eltMesIssLldpduMode object has a value of
        'flooding(2)', then received frames containing LLDPDU
        will flood all active ports."
    DEFVAL  { filtering }
    ::= { eltMesIssLldpGlobalConfig 1 }

END

ELTEX-MES-ISS-PPPOE-MIB DEFINITIONS ::= BEGIN

IMPORTS
        MODULE-IDENTITY, OBJECT-TYPE, NOTIFICATION-TYPE
                FROM SNMPv2-SMI
        OBJECT-GROUP
                FROM SNMPv2-CONF
        RowStatus, TEXTUAL-CONVENTION, MacAddress, TruthValue
                FROM SNMPv2-TC
        eltMesIss
                FROM ELTEX-MES-ISS-MIB;

eltMesIssPppoeMIB MODULE-IDENTITY
        LAST-UPDATED "201811220000Z" 
        ORGANIZATION "Eltex Enterprise, Ltd." 
        CONTACT-INFO
                "eltex-co.ru" 
        DESCRIPTION
                "PPP over Ethernet MIB definitions." 
        REVISION "201811220000Z" 
        DESCRIPTION "Initial revision." 
    ::= { eltMesIss 2 }

-- Top level MIB structure

   eltMesIssPppoeObjects       OBJECT IDENTIFIER ::= { eltMesIssPppoeMIB 1 }

-- MIB Groups

   eltMesIssPppoeGlobals       OBJECT IDENTIFIER ::= { eltMesIssPppoeObjects 1 }
   
eltMesIssPppoePassthroughEnabled OBJECT-TYPE 
    SYNTAX      TruthValue
    MAX-ACCESS  read-write 
    STATUS      current 
    DESCRIPTION 
        "Specifies the admin status of the PPPoE Passthrough feature. If PPPoE
        Passthrough is enabled the packet processor treats PPPoE packets as unknown
        L2 traffic and do not parse encapsulated L3 packets, so these packets
        transparently pass through the switch. If PPPoE Passthrough is disabled,
        transported L3 data become a subject for packet processor's engines
        (e.g ACL) and encapsulated packets are treated much as like as regular
        IP packets."
    DEFVAL  { false }
    ::= { eltMesIssPppoeGlobals 1 }

END

ELTEX-MES-ISS-SSH-MIB DEFINITIONS ::= BEGIN

IMPORTS
    MODULE-IDENTITY, OBJECT-TYPE, NOTIFICATION-TYPE
        FROM SNMPv2-SMI
    eltMesIss
        FROM ELTEX-MES-ISS-MIB;

eltMesIssSshMIB MODULE-IDENTITY
    LAST-UPDATED "202204190000Z"
    ORGANIZATION "Eltex Enterprise, Ltd."
    CONTACT-INFO
        "eltex-co.ru"
    DESCRIPTION
        "This private MIB module contains Eltex SSH definitions."
    REVISION "202204190000Z"
    DESCRIPTION "Initial revision."
    ::= { eltMesIss 30 }

-- Top level MIB structure

eltMesIssSshObjects        OBJECT IDENTIFIER ::= { eltMesIssSshMIB 1 }

-- MIB Groups

eltMesIssSshGlobals        OBJECT IDENTIFIER ::= { eltMesIssSshObjects 1 }

-- Low level Mib structure

-- -----------------------------------------------------------------------------
-- SSH global variables
-- -----------------------------------------------------------------------------

eltMesIssSshAuthTypes OBJECT-TYPE
    SYNTAX BITS {
        password(0),
        publickey(1)
    }
    MAX-ACCESS read-write
    STATUS current
    DESCRIPTION
          "This object is to configure the SSH authentication types list.
          This object takes values as bit mask.

          The value of each bit position is as given below with bit 0 being the 
          least significant bit:
               BIT 1 - public key authentication
               BIT 0 - password authentication
          "
    DEFVAL  { '80'H }
    ::= { eltMesIssSshGlobals 1}

END

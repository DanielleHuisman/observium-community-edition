ELTEX-MES-ISS-SYSLOG-MIB DEFINITIONS ::= BEGIN

IMPORTS
    OBJECT-TYPE, MODULE-IDENTITY
            FROM SNMPv2-SMI
    TruthValue, DisplayString
            FROM SNMPv2-TC
    eltMesIss
            FROM ELTEX-MES-ISS-MIB;


eltMesIssSyslogMIB MODULE-IDENTITY
    LAST-UPDATED "202007290000Z"
    ORGANIZATION "Eltex Enterprise, Ltd."
    CONTACT-INFO
            "eltex-co.ru"
    DESCRIPTION
            "SYSLOG MIB definitions for ISS system."
    REVISION "202007290000Z"
    DESCRIPTION "Initial revision."
    ::= { eltMesIss 22 }

-- Top level MIB structure

eltMesIssSyslogObjects        OBJECT IDENTIFIER ::= { eltMesIssSyslogMIB 1 }
eltMesIssSyslogNotifications  OBJECT IDENTIFIER ::= { eltMesIssSyslogMIB 2 }

-- MIB Groups

eltMesIssSyslogGlobals        OBJECT IDENTIFIER ::= { eltMesIssSyslogObjects 1 }

-- Low level Mib structure

-- -----------------------------------------------------------------------------
-- Syslog configuration
-- -----------------------------------------------------------------------------

eltMesIssSyslogVersionMode OBJECT-TYPE
    SYNTAX INTEGER {
        empty (1),
        present (2)
    }
    MAX-ACCESS  read-write
    STATUS      current
    DESCRIPTION
        "Defines the mode of the VERSION field
        of the SYSLOG message packets sent to the SYSLOG server"
    DEFVAL { empty }
    ::= { eltMesIssSyslogGlobals 1 }

eltMesIssSyslogVersionString OBJECT-TYPE
    SYNTAX  DisplayString (SIZE(0..4))
    MAX-ACCESS read-only
    STATUS current
    DESCRIPTION
        "Defines the string value of the VERSION field
        of the SYSLOG message packets sent to the SYSLOG server"
    ::= { eltMesIssSyslogGlobals 2 }

eltMesIssSyslogTimestampMode OBJECT-TYPE
    SYNTAX INTEGER {
        legacy (1),
        rfc5424 (2)
    }
    MAX-ACCESS  read-write
    STATUS      current
    DESCRIPTION
        "Defines the mode of the TIMESTAMP field
        of the SYSLOG message packets sent to the SYSLOG server"
    DEFVAL { legacy }
    ::= { eltMesIssSyslogGlobals 3 }

eltMesIssSyslogHostnameMode OBJECT-TYPE
    SYNTAX INTEGER {
        empty (1),
        string (2),
        hostname (3),
        ip (4),
        ipv6 (5)
    }
    MAX-ACCESS  read-write
    STATUS      current
    DESCRIPTION
        "Defines the mode of the HOSTNAME field
        of the SYSLOG message packets sent to the SYSLOG server"
    DEFVAL { empty }
    ::= { eltMesIssSyslogGlobals 4 }

eltMesIssSyslogHostnameString OBJECT-TYPE
    SYNTAX  DisplayString (SIZE(0..128))
    MAX-ACCESS read-write
    STATUS current
    DESCRIPTION
        "Defines the string value of the HOSTNAME field
        of the SYSLOG message packets sent to the SYSLOG server"
    ::= { eltMesIssSyslogGlobals 5 }

END

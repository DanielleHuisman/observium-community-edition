ELTEX-MES-ISS-VLAN-TUNNEL-MIB DEFINITIONS ::= BEGIN

IMPORTS
        OBJECT-TYPE, MODULE-IDENTITY, Integer32, Counter32
                FROM SNMPv2-SMI
        eltMesIss
                FROM ELTEX-MES-ISS-MIB
        TEXTUAL-CONVENTION, MacAddress
                FROM SNMPv2-TC
        TunnelStatus, fsVlanTunnelProtocolEntry,
        fsVlanTunnelProtocolStatsEntry, fsVlanDiscardStatsEntry
                FROM ARICENT-VLAN-EXT-MIB;

eltMesIssVlanTunnelMIB MODULE-IDENTITY
        LAST-UPDATED "202106290000Z"
        ORGANIZATION "Eltex Enterprise, Ltd."
        CONTACT-INFO
                "eltex-co.ru"
        DESCRIPTION
                "MIB extensions for configuring tunnel protocol."
        REVISION "202106290000Z"
        DESCRIPTION "Added objects for VRRP tunneling."
        REVISION "202007060000Z"
        DESCRIPTION "Initial revision."
    ::= { eltMesIss 21 }

-- --------------------------
-- Top level MIB structure --
-- --------------------------

eltMesIssVlanTunnelObjects  OBJECT IDENTIFIER  ::= { eltMesIssVlanTunnelMIB 1 }
eltMesIssVlanDiscardObjects OBJECT IDENTIFIER  ::= { eltMesIssVlanTunnelMIB 2 }

-- ----------------------
-- Vlan tunnel objects --
-- ----------------------

eltMesIssVlanTunnelPvstAddress OBJECT-TYPE
    SYNTAX      MacAddress
    MAX-ACCESS  read-write
    STATUS      current
    DESCRIPTION
        "This object specifies the MAC address to be used for PVST packets
         tunneling . When PVST tunneling is enabled on the port, this MAC address
         will be used as destination MAC address of the PVST packets
         received over the port.

         PVST packets received with this MAC address will be treated as
         data packets and are not processed.

         When the tunneled PVST packets are sent out of the given network,
         this MAC address will be replaced with the reserved address defined
         for the PVST packets. This is done only when PVST protocol
         tunnel status is set to Tunnel on the outgoing port, else the
         packets are dropped."
    ::= { eltMesIssVlanTunnelObjects 1 }

eltMesIssVlanTunnelVtpAddress OBJECT-TYPE
    SYNTAX      MacAddress
    MAX-ACCESS  read-write
    STATUS      current
    DESCRIPTION
        "This object specifies the MAC address to be used for VTP packets
         tunneling . When VTP tunneling is enabled on the port, this MAC address
         will be used as destination MAC address of the VTP packets
         received over the port.

         VTP packets received with this MAC address will be treated as
         data packets and are not processed.

         When the tunneled VTP packets are sent out of the given network,
         this MAC address will be replaced with the reserved address defined
         for the VTP packets. This is done only when VTP protocol
         tunnel status is set to Tunnel on the outgoing port, else the
         packets are dropped."
    ::= { eltMesIssVlanTunnelObjects 2 }

eltMesIssVlanTunnelOspfAddress OBJECT-TYPE
    SYNTAX      MacAddress
    MAX-ACCESS  read-write
    STATUS      current
    DESCRIPTION
        "This object specifies the MAC address to be used for OSPF packets
         tunneling . When OSPF tunneling is enabled on the port, this MAC address
         will be used as destination MAC address of the OSPF packets
         received over the port.

         OSPF packets received with this MAC address will be treated as
         data packets and are not processed.

         When the tunneled OSPF packets are sent out of the given network,
         this MAC address will be replaced with the reserved address defined
         for the OSPF packets. This is done only when OSPF protocol
         tunnel status is set to Tunnel on the outgoing port, else the
         packets are dropped."
    ::= { eltMesIssVlanTunnelObjects 3 }

eltMesIssVlanTunnelRipAddress OBJECT-TYPE
    SYNTAX      MacAddress
    MAX-ACCESS  read-write
    STATUS      current
    DESCRIPTION
        "This object specifies the MAC address to be used for RIP packets
         tunneling . When RIP tunneling is enabled on the port, this MAC address
         will be used as destination MAC address of the RIP packets
         received over the port.

         RIP packets received with this MAC address will be treated as
         data packets and are not processed.

         When the tunneled RIP packets are sent out of the given network,
         this MAC address will be replaced with the reserved address defined
         for the RIP packets. This is done only when RIP protocol
         tunnel status is set to Tunnel on the outgoing port, else the
         packets are dropped."
    ::= { eltMesIssVlanTunnelObjects 4 }

eltMesIssVlanTunnelVrrpAddress OBJECT-TYPE
    SYNTAX      MacAddress
    MAX-ACCESS  read-write
    STATUS      current
    DESCRIPTION
        "This object specifies the MAC address to be used for VRRP packets
         tunneling . When VRRP tunneling is enabled on the port, this MAC address
         will be used as destination MAC address of the VRRP packets
         received over the port.

         VRRP packets received with this MAC address will be treated as
         data packets and are not processed.

         When the tunneled VRRP packets are sent out of the given network,
         this MAC address will be replaced with the reserved address defined
         for the VRRP packets. This is done only when VRRP protocol
         tunnel status is set to Tunnel on the outgoing port, else the
         packets are dropped."
    ::= { eltMesIssVlanTunnelObjects 5 }

-- ----------------------------------------------------------------
-- Tunnel protocol configuration table
-- ----------------------------------------------------------------

eltMesIssVlanTunnelProtocolTable OBJECT-TYPE
    SYNTAX      SEQUENCE OF EltMesIssVlanTunnelProtocolEntry
    MAX-ACCESS  not-accessible
    STATUS      current
    DESCRIPTION
        "This table contains information about the handling (Tunnel/Peer/Discard)
         of customer protocols (PVST/VTP/OSPF/RIP/VRRP) inside a given network."
    ::= { eltMesIssVlanTunnelObjects 6 }

eltMesIssVlanTunnelProtocolEntry OBJECT-TYPE
    SYNTAX      EltMesIssVlanTunnelProtocolEntry
    MAX-ACCESS  not-accessible
    STATUS      current
    DESCRIPTION
        "Entry indicating the handling (Tunnel/Peer/Discard) of
         customer protocols (PVST/VTP/OSPF/RIP/VRRP) on this port.
         Tunnel Status cannot be set to 'tunnel/discard', if the protocol
         is enabled on the port."
    AUGMENTS { fsVlanTunnelProtocolEntry }
    ::= { eltMesIssVlanTunnelProtocolTable 1 }

EltMesIssVlanTunnelProtocolEntry ::=
    SEQUENCE {
        eltMesIssVlanTunnelProtocolPvst  TunnelStatus,
        eltMesIssVlanTunnelProtocolVtp   TunnelStatus,
        eltMesIssVlanTunnelProtocolOspf  TunnelStatus,
        eltMesIssVlanTunnelProtocolRip   TunnelStatus,
        eltMesIssVlanTunnelProtocolVrrp  TunnelStatus
    }

eltMesIssVlanTunnelProtocolPvst OBJECT-TYPE
    SYNTAX      TunnelStatus
    MAX-ACCESS  read-write
    STATUS      current
    DESCRIPTION
        "The object specifies whether to peer/tunnel/discard the PVST packets
         received on the port."
    ::= { eltMesIssVlanTunnelProtocolEntry 1 }

eltMesIssVlanTunnelProtocolVtp OBJECT-TYPE
    SYNTAX      TunnelStatus
    MAX-ACCESS  read-write
    STATUS      current
    DESCRIPTION
        "The object specifies whether to peer/tunnel/discard the VTP packets
         received on the port."
    ::= { eltMesIssVlanTunnelProtocolEntry 2 }

eltMesIssVlanTunnelProtocolOspf OBJECT-TYPE
    SYNTAX      TunnelStatus
    MAX-ACCESS  read-write
    STATUS      current
    DESCRIPTION
        "The object specifies whether to peer/tunnel/discard the OSPF packets
         received on the port."
    ::= { eltMesIssVlanTunnelProtocolEntry 3 }

eltMesIssVlanTunnelProtocolRip OBJECT-TYPE
    SYNTAX      TunnelStatus
    MAX-ACCESS  read-write
    STATUS      current
    DESCRIPTION
        "The object specifies whether to peer/tunnel/discard the RIP packets
         received on the port."
    ::= { eltMesIssVlanTunnelProtocolEntry 4 }

eltMesIssVlanTunnelProtocolVrrp OBJECT-TYPE
    SYNTAX      TunnelStatus
    MAX-ACCESS  read-write
    STATUS      current
    DESCRIPTION
        "The object specifies whether to peer/tunnel/discard the VRRP packets
         received on the port."
    ::= { eltMesIssVlanTunnelProtocolEntry 5 }

-- ----------------------------------------------------------------
-- Tunnel protocol statistics table
-- ----------------------------------------------------------------
eltMesIssVlanTunnelProtocolStatsTable OBJECT-TYPE
    SYNTAX      SEQUENCE OF EltMesIssVlanTunnelProtocolStatsEntry
    MAX-ACCESS  not-accessible
    STATUS      current
    DESCRIPTION
        "This table contains statistics information about the tunneled
         protocols (PVST/VTP/OSPF/RIP/VRRP)
         received and transmitted over a port."
    ::= { eltMesIssVlanTunnelObjects 7 }

eltMesIssVlanTunnelProtocolStatsEntry OBJECT-TYPE
    SYNTAX      EltMesIssVlanTunnelProtocolStatsEntry
    MAX-ACCESS  not-accessible
    STATUS      current
    DESCRIPTION
        "Entry indicating the handling (Tunnel/Peer/Discard) of
         protocols (PVST/VTP/OSPF/RIP/VRRP) on this port."
    AUGMENTS { fsVlanTunnelProtocolStatsEntry }
    ::= { eltMesIssVlanTunnelProtocolStatsTable 1 }

EltMesIssVlanTunnelProtocolStatsEntry ::=
    SEQUENCE {
        eltMesIssVlanTunnelProtocolPvstPktsRecvd  Counter32,
        eltMesIssVlanTunnelProtocolPvstPktsSent   Counter32,
        eltMesIssVlanTunnelProtocolVtpPktsRecvd   Counter32,
        eltMesIssVlanTunnelProtocolVtpPktsSent    Counter32,
        eltMesIssVlanTunnelProtocolOspfPktsRecvd  Counter32,
        eltMesIssVlanTunnelProtocolOspfPktsSent   Counter32,
        eltMesIssVlanTunnelProtocolRipPktsRecvd   Counter32,
        eltMesIssVlanTunnelProtocolRipPktsSent    Counter32,
        eltMesIssVlanTunnelProtocolVrrpPktsRecvd  Counter32,
        eltMesIssVlanTunnelProtocolVrrpPktsSent   Counter32
    }

eltMesIssVlanTunnelProtocolPvstPktsRecvd OBJECT-TYPE
    SYNTAX      Counter32
    MAX-ACCESS  read-only
    STATUS      current
    DESCRIPTION
        "This object displays the number of PVST packets received on a port
         on which the PVST tunneling status is enabled."
    ::= { eltMesIssVlanTunnelProtocolStatsEntry 1 }

eltMesIssVlanTunnelProtocolPvstPktsSent OBJECT-TYPE
    SYNTAX      Counter32
    MAX-ACCESS  read-only
    STATUS      current
    DESCRIPTION
        "This object displays the number of PVST packets transmitted on a port
         for which the PVST tunneling status is enabled."
    ::= { eltMesIssVlanTunnelProtocolStatsEntry 2 }

eltMesIssVlanTunnelProtocolVtpPktsRecvd OBJECT-TYPE
    SYNTAX      Counter32
    MAX-ACCESS  read-only
    STATUS      current
    DESCRIPTION
        "This object displays the number of VTP packets received on a port
         on which the VTP tunneling status is enabled."
    ::= { eltMesIssVlanTunnelProtocolStatsEntry 3 }

eltMesIssVlanTunnelProtocolVtpPktsSent OBJECT-TYPE
    SYNTAX      Counter32
    MAX-ACCESS  read-only
    STATUS      current
    DESCRIPTION
        "This object displays the number of VTP packets transmitted on a port
        for which the VTP tunneling status is enabled."
    ::= { eltMesIssVlanTunnelProtocolStatsEntry 4 }

eltMesIssVlanTunnelProtocolOspfPktsRecvd OBJECT-TYPE
    SYNTAX      Counter32
    MAX-ACCESS  read-only
    STATUS      current
    DESCRIPTION
        "This object displays the number of OSPF packets received on a port
         on which the OSPF tunneling status is enabled."
    ::= { eltMesIssVlanTunnelProtocolStatsEntry 5 }

eltMesIssVlanTunnelProtocolOspfPktsSent OBJECT-TYPE
    SYNTAX      Counter32
    MAX-ACCESS  read-only
    STATUS      current
    DESCRIPTION
        "This object displays the number of OSPF packets transmitted on a port
        for which the OSPF tunneling status is enabled."
    ::= { eltMesIssVlanTunnelProtocolStatsEntry 6 }

eltMesIssVlanTunnelProtocolRipPktsRecvd OBJECT-TYPE
    SYNTAX      Counter32
    MAX-ACCESS  read-only
    STATUS      current
    DESCRIPTION
        "This object displays the number of RIP packets received on a port
         on which the RIP tunneling status is enabled."
    ::= { eltMesIssVlanTunnelProtocolStatsEntry 7 }

eltMesIssVlanTunnelProtocolRipPktsSent OBJECT-TYPE
    SYNTAX      Counter32
    MAX-ACCESS  read-only
    STATUS      current
    DESCRIPTION
        "This object displays the number of RIP packets transmitted on a port
         for which the RIP tunneling status is enabled."
    ::= { eltMesIssVlanTunnelProtocolStatsEntry 8 }

eltMesIssVlanTunnelProtocolVrrpPktsRecvd OBJECT-TYPE
    SYNTAX      Counter32
    MAX-ACCESS  read-only
    STATUS      current
    DESCRIPTION
        "This object displays the number of VRRP packets received on a port
         on which the VRRP tunneling status is enabled."
    ::= { eltMesIssVlanTunnelProtocolStatsEntry 9 }

eltMesIssVlanTunnelProtocolVrrpPktsSent OBJECT-TYPE
    SYNTAX      Counter32
    MAX-ACCESS  read-only
    STATUS      current
    DESCRIPTION
        "This object displays the number of VRRP packets transmitted on a port
         for which the VRRP tunneling status is enabled."
    ::= { eltMesIssVlanTunnelProtocolStatsEntry 10 }

-- ----------------------------------------------------------------
-- VLAN Discard statistics table
-- ----------------------------------------------------------------
eltMesIssVlanDiscardStatsTable OBJECT-TYPE
    SYNTAX      SEQUENCE OF EltMesIssVlanDiscardStatsEntry
    MAX-ACCESS  not-accessible
    STATUS      current
    DESCRIPTION
        "This table contains statistics information about the protocol
         packets (PVST/VTP/OSPF/RIP/VRRP) discarded on
         reception and transmission side due to 'Discard' tunnel protocol
         status."
    ::= { eltMesIssVlanDiscardObjects 1 }

eltMesIssVlanDiscardStatsEntry OBJECT-TYPE
    SYNTAX      EltMesIssVlanDiscardStatsEntry
    MAX-ACCESS  not-accessible
    STATUS      current
    DESCRIPTION
        "Entry indicating the Discard statistics for L2 protocol packets."
    AUGMENTS { fsVlanDiscardStatsEntry }
    ::= { eltMesIssVlanDiscardStatsTable 1 }

EltMesIssVlanDiscardStatsEntry ::=
    SEQUENCE {
        eltMesIssVlanDiscardPvstPktsRx  Counter32,
        eltMesIssVlanDiscardPvstPktsTx  Counter32,
        eltMesIssVlanDiscardVtpPktsRx   Counter32,
        eltMesIssVlanDiscardVtpPktsTx   Counter32,
        eltMesIssVlanDiscardOspfPktsRx  Counter32,
        eltMesIssVlanDiscardOspfPktsTx  Counter32,
        eltMesIssVlanDiscardRipPktsRx   Counter32,
        eltMesIssVlanDiscardRipPktsTx   Counter32,
        eltMesIssVlanDiscardVrrpPktsRx   Counter32,
        eltMesIssVlanDiscardVrrpPktsTx   Counter32
    }

eltMesIssVlanDiscardPvstPktsRx OBJECT-TYPE
    SYNTAX      Counter32
    MAX-ACCESS  read-only
    STATUS      current
    DESCRIPTION
        "This object displays the number of PVST packets discarded on
         the reception side when the tunnel protocol status is
         set as Discard."
    ::= { eltMesIssVlanDiscardStatsEntry 1 }

eltMesIssVlanDiscardPvstPktsTx OBJECT-TYPE
    SYNTAX      Counter32
    MAX-ACCESS  read-only
    STATUS      current
    DESCRIPTION
        "This object displays the number of PVST packets discarded on
         the transmission side when the tunnel protocol status is
         set as Discard."
    ::= { eltMesIssVlanDiscardStatsEntry 2 }

eltMesIssVlanDiscardVtpPktsRx OBJECT-TYPE
    SYNTAX      Counter32
    MAX-ACCESS  read-only
    STATUS      current
    DESCRIPTION
        "This object displays the number of VTP packets discarded on
         the reception side when the tunnel protocol status is
         set as Discard."
    ::= { eltMesIssVlanDiscardStatsEntry 3 }

eltMesIssVlanDiscardVtpPktsTx OBJECT-TYPE
    SYNTAX      Counter32
    MAX-ACCESS  read-only
    STATUS      current
    DESCRIPTION
        "This object displays the number of VTP packets discarded on
         the transmission side when the tunnel protocol status is
         set as Discard."
    ::= { eltMesIssVlanDiscardStatsEntry 4 }

eltMesIssVlanDiscardOspfPktsRx OBJECT-TYPE
    SYNTAX      Counter32
    MAX-ACCESS  read-only
    STATUS      current
    DESCRIPTION
        "This object displays the number of OSPF packets discarded on
         the reception side when the tunnel protocol status is
         set as Discard."
    ::= { eltMesIssVlanDiscardStatsEntry 5 }

eltMesIssVlanDiscardOspfPktsTx OBJECT-TYPE
    SYNTAX      Counter32
    MAX-ACCESS  read-only
    STATUS      current
    DESCRIPTION
        "This object displays the number of OSPF packets discarded on
         the transmission side when the tunnel protocol status is
         set as Discard."
    ::= { eltMesIssVlanDiscardStatsEntry 6 }

eltMesIssVlanDiscardRipPktsRx OBJECT-TYPE
    SYNTAX      Counter32
    MAX-ACCESS  read-only
    STATUS      current
    DESCRIPTION
        "This object displays the number of RIP packets discarded on
         the reception side when the tunnel protocol status is
         set as Discard."
    ::= { eltMesIssVlanDiscardStatsEntry 7 }

eltMesIssVlanDiscardRipPktsTx OBJECT-TYPE
    SYNTAX      Counter32
    MAX-ACCESS  read-only
    STATUS      current
    DESCRIPTION
        "This object displays the number of RIP packets discarded on
         the transmission side when the tunnel protocol status is
         set as Discard."
    ::= { eltMesIssVlanDiscardStatsEntry 8 }

eltMesIssVlanDiscardVrrpPktsRx OBJECT-TYPE
    SYNTAX      Counter32
    MAX-ACCESS  read-only
    STATUS      current
    DESCRIPTION
        "This object displays the number of VRRP packets discarded on
         the reception side when the tunnel protocol status is
         set as Discard."
    ::= { eltMesIssVlanDiscardStatsEntry 9 }

eltMesIssVlanDiscardVrrpPktsTx OBJECT-TYPE
    SYNTAX      Counter32
    MAX-ACCESS  read-only
    STATUS      current
    DESCRIPTION
        "This object displays the number of VRRP packets discarded on
         the transmission side when the tunnel protocol status is
         set as Discard."
    ::= { eltMesIssVlanDiscardStatsEntry 10 }

END

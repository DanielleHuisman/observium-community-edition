ELTEX-MES-L2-TUNNEL-CONFIG-MIB DEFINITIONS ::= BEGIN

IMPORTS
    eltMes
        FROM ELTEX-MES
    MODULE-IDENTITY,
    OBJECT-TYPE,
    NOTIFICATION-TYPE,
    Unsigned32,
    Counter32
        FROM SNMPv2-SMI
    MODULE-COMPLIANCE,
    OBJECT-GROUP,
    NOTIFICATION-GROUP
        FROM SNMPv2-CONF
    TruthValue,
    MacAddress
        FROM SNMPv2-TC
    ifIndex
        FROM IF-MIB
    QosLayer2Cos
        FROM CISCO-QOS-PIB-MIB;

eltMesL2TunnelConfig MODULE-IDENTITY
    LAST-UPDATED "201511190000Z"	-- November 19, 2015
    ORGANIZATION "Eltex Enterprise Co, Ltd."
    CONTACT-INFO "www.eltex.nsk.ru"
    DESCRIPTION
        "This MIB module is for layer 2 tunneling related configurations
        on a device.

        Tunneling allows separate local networks to be considered as
        a single VLAN. These separate networks are connected via an
        ISP, which will tunnel the packets from one network to another,
        making it appear as if the two networks are actually just one."

    REVISION	 "201511190000Z"  	-- November 19, 2015
    DESCRIPTION
        "Deprecate all objects in this module."
          ::= { eltMes 13 }

eltMesLtcMIBObjects     OBJECT IDENTIFIER ::= { eltMesL2TunnelConfig 1 }

eltMesLtcGlobal            OBJECT IDENTIFIER ::= { eltMesLtcMIBObjects 1 }
eltMesLtcTunneledProtocol  OBJECT IDENTIFIER ::= { eltMesLtcMIBObjects 2 }
eltMesLtcTunnelThreshold   OBJECT IDENTIFIER ::= { eltMesLtcMIBObjects 3 }
eltMesLtcTunnelStatistics  OBJECT IDENTIFIER ::= { eltMesLtcMIBObjects 4 }

-- -------------------- --
-- Textual Conventions  --
-- -------------------- --

EltLtcTunneledProtocolIndex ::= TEXTUAL-CONVENTION
    STATUS          deprecated
    DESCRIPTION     "A tunneled protocol of an interface.
                    Supported value is stp(1)."
    SYNTAX          INTEGER {
                        stp(1)
                    }

-- ------------------------ --
-- eltLtcNotificationEnable --
-- ------------------------ --

eltLtcNotificationEnable OBJECT-TYPE
    SYNTAX          TruthValue
    MAX-ACCESS      read-write
    STATUS          deprecated
    DESCRIPTION
        "This object indicates whether the system will
        generate the eltLtcTunnelDropThresholdExceeded and
        eltLtcTunnelShutdownThresholdExceeded notifications."
    ::= { eltMesLtcGlobal 1 }

-- ---------------- --
-- eltLtcMacAddress --
-- ---------------- --

eltLtcTunnelMacAddress OBJECT-TYPE
    SYNTAX          MacAddress
    MAX-ACCESS      read-write
    STATUS          deprecated
    DESCRIPTION
        "The destination MAC address that replaces the original destination
	MAC address of tunneled frames."
    DEFVAL { '0100EEEE0000'H }
    ::= { eltMesLtcGlobal 2 }

-- ---------------------------- --
-- eltLtcTunneledProtocolTable  --
-- ---------------------------- --

eltLtcTunneledProtocolTable OBJECT-TYPE
    SYNTAX          SEQUENCE OF EltLtcTunneledProtocolEntry
    MAX-ACCESS      not-accessible
    STATUS          deprecated
    DESCRIPTION
        "This table contains information about the protocols being
        tunneled. Only tunneled protocol filtering capable interfaces
        are shown."
    ::= { eltMesLtcTunneledProtocol 1 }

eltLtcTunneledProtocolEntry OBJECT-TYPE
    SYNTAX          EltLtcTunneledProtocolEntry
    MAX-ACCESS      not-accessible
    STATUS          deprecated
    DESCRIPTION
        "Information about the protocols being tunneled. Only tunneled
        protocol filtering capable interfaces are shown."
    INDEX           { ifIndex }
    ::= { eltLtcTunneledProtocolTable 1 }

EltLtcTunneledProtocolEntry ::= SEQUENCE {
        eltLtcTunneledProtocolType BITS,
        eltLtcTunnelCos            QosLayer2Cos
}

eltLtcTunneledProtocolType OBJECT-TYPE
    SYNTAX          BITS {
                        stp(0)
                        ,workaround(1) -- workaround to Bug #50007
                    }
    MAX-ACCESS      read-write
    STATUS          deprecated
    DESCRIPTION
        "Indicates tunneled protocol of the interface.

        If a BIT is set, then the value of the corresponding
        protocol is tunneled. Specifically, if the 'stp(0)' BIT
        is set, then the Spanning Tree Protocol PDU is tunneled.
        At this moment, there are no other supported protocols.

        If the bit for a given protocol is set for an interface, then
        the statistics for that interface and protocol will start to be
        monitored."
    ::= { eltLtcTunneledProtocolEntry 1 }

eltLtcTunnelCos OBJECT-TYPE
    SYNTAX          QosLayer2Cos
    MAX-ACCESS      read-write
    STATUS          deprecated
    DESCRIPTION
        "Specifies the user priority of the tunneled PDUs for the
        interface."
    ::= { eltLtcTunneledProtocolEntry 2 }

-- -------------------------- --
-- eltLtcTunnelThresholdTable --
-- -------------------------- --

eltLtcTunnelThresholdTable OBJECT-TYPE
    SYNTAX          SEQUENCE OF EltLtcTunnelThresholdEntry
    MAX-ACCESS      not-accessible
    STATUS          deprecated
    DESCRIPTION
        "This table contains information about the thresholds for
        protocol tunneling. Only tunneled protocol filtering capable
        interfaces are shown. The objects will be on a per interface,
        per protocol basis."
    ::= { eltMesLtcTunnelThreshold 1 }

eltLtcTunnelThresholdEntry OBJECT-TYPE
    SYNTAX          EltLtcTunnelThresholdEntry
    MAX-ACCESS      not-accessible
    STATUS          deprecated
    DESCRIPTION
        "Information about the thresholds for protocol tunneling. Only
        tunneled protocol filtering capable interfaces are shown. The
        entries will be on a per interface, per protocol basis"
    INDEX           {
                        ifIndex,
                        eltLtcTunnelThresholdProtocolIndex
                    }
    ::= { eltLtcTunnelThresholdTable 1 }

EltLtcTunnelThresholdEntry ::= SEQUENCE {
        eltLtcTunnelThresholdProtocolIndex EltLtcTunneledProtocolIndex,
        eltLtcTunnelDropThreshold          Unsigned32,
        eltLtcTunnelShutdownThreshold      Unsigned32
}

eltLtcTunnelThresholdProtocolIndex OBJECT-TYPE
    SYNTAX          EltLtcTunneledProtocolIndex
    MAX-ACCESS      not-accessible
    STATUS          deprecated
    DESCRIPTION     "A tunneled protocol of an interface."
    ::= { eltLtcTunnelThresholdEntry 1 }

eltLtcTunnelDropThreshold OBJECT-TYPE
    SYNTAX          Unsigned32
    UNITS           "PDUs/sec"
    MAX-ACCESS      read-write
    STATUS          deprecated
    DESCRIPTION
        "The drop threshold on an interface for a given protocol. After
        reaching this drop threshold, the interface will start dropping
        PDUs for the given protocol. This value cannot be greater than
        the value of eltLtcTunnelShutdownThreshold.  A value of 0
        indicates that no limit is set."
    DEFVAL          { 0 }
    ::= { eltLtcTunnelThresholdEntry 2 }

eltLtcTunnelShutdownThreshold OBJECT-TYPE
    SYNTAX          Unsigned32
    UNITS           "PDUs/sec"
    MAX-ACCESS      read-write
    STATUS          deprecated
    DESCRIPTION
        "The shutdown threshold on an interface for a given protocol.
        After reaching the shutdown threshold, the interface will
        shutdown for the given protocol.  This value cannot be less
        than the value of eltLtcTunnelDropThreshold. A value of 0
        indicates that no limit is set."
    DEFVAL          { 0 }
    ::= { eltLtcTunnelThresholdEntry 3 }


-- ---------------------------- --
-- eltLtcTunnelStatisticsTable  --
-- ---------------------------- --

eltLtcTunnelStatisticsTable OBJECT-TYPE
    SYNTAX          SEQUENCE OF EltLtcTunnelStatisticsEntry
    MAX-ACCESS      not-accessible
    STATUS          deprecated
    DESCRIPTION
        "This table contains protocol tunneling statistics on the
        interface."
    ::= { eltMesLtcTunnelStatistics 1 }

eltLtcTunnelStatisticsEntry OBJECT-TYPE
    SYNTAX          EltLtcTunnelStatisticsEntry
    MAX-ACCESS      not-accessible
    STATUS          deprecated
    DESCRIPTION     "Protocol tunneling statistics on the interface."
    INDEX           {
                        ifIndex,
                        eltLtcTunneledProtocolIndex
                    }
    ::= { eltLtcTunnelStatisticsTable 1 }

EltLtcTunnelStatisticsEntry ::= SEQUENCE {
        eltLtcTunneledProtocolIndex EltLtcTunneledProtocolIndex,
        eltLtcTunnelEncapStats      Counter32,
        eltLtcTunnelDecapStats      Counter32,
        eltLtcTunnelDropStats       Counter32
}

eltLtcTunneledProtocolIndex OBJECT-TYPE
    SYNTAX          EltLtcTunneledProtocolIndex
    MAX-ACCESS      not-accessible
    STATUS          deprecated
    DESCRIPTION     "A tunneled protocol of an interface."
    ::= { eltLtcTunnelStatisticsEntry 1 }

eltLtcTunnelEncapStats OBJECT-TYPE
    SYNTAX          Counter32
    UNITS           "encapsulated PDUs"
    MAX-ACCESS      read-only
    STATUS          deprecated
    DESCRIPTION
        "The tunneled PDU encapsulation statistics of an interface.
        These statistics cover the number of tunneled ingress
        PDUs."
    ::= { eltLtcTunnelStatisticsEntry 2 }

eltLtcTunnelDecapStats OBJECT-TYPE
    SYNTAX          Counter32
    UNITS           "de-encapsulated PDUs"
    MAX-ACCESS      read-only
    STATUS          deprecated
    DESCRIPTION
        "The tunneled PDU de-encapsulation statistics of an interface.
        These statistics cover the number of tunneled egress PDUs."
    ::= { eltLtcTunnelStatisticsEntry 3 }

eltLtcTunnelDropStats OBJECT-TYPE
    SYNTAX          Counter32
    UNITS           "PDUs"
    MAX-ACCESS      read-only
    STATUS          deprecated
    DESCRIPTION
        "The number of PDUs dropped on an interface for a given
        protocol. The PDUs will be dropped when the
        eltLtcTunnelDropThreshold is reached."
    ::= { eltLtcTunnelStatisticsEntry 4 }

-- ------------- --
-- Notifications --
-- ------------- --

eltMesLtcMIBNotifications  OBJECT IDENTIFIER
    ::= { eltMesL2TunnelConfig 2 }

eltMesLtcMIBNotificationsPrefix  OBJECT IDENTIFIER
    ::= { eltMesLtcMIBNotifications 0 }



eltLtcTunnelDropThresholdExceeded NOTIFICATION-TYPE
    OBJECTS         { eltLtcTunnelDropThreshold }
    STATUS          deprecated
    DESCRIPTION
        "This notification is generated when the
        eltLtcTunnelDropThreshold has been exceeded."
   ::= { eltMesLtcMIBNotificationsPrefix 1 }


eltLtcTunnelShutdownThresholdExceeded NOTIFICATION-TYPE
    OBJECTS         { eltLtcTunnelShutdownThreshold }
    STATUS          deprecated
    DESCRIPTION
        "This notification is generated when the
        eltLtcTunnelShutdownThreshold has been exceeded."
   ::= { eltMesLtcMIBNotificationsPrefix 2 }

END

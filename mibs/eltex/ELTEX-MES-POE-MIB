ELTEX-MES-POE-MIB DEFINITIONS ::= BEGIN

IMPORTS
    MODULE-IDENTITY, OBJECT-TYPE        FROM SNMPv2-SMI
    eltMes                              FROM ELTEX-MES
    TruthValue                          FROM SNMPv2-TC;

eltMesPoe  MODULE-IDENTITY 
    LAST-UPDATED "201904020000Z"
    ORGANIZATION "Eltex Enterprise Co, Ltd."
    CONTACT-INFO
          "http://eltex-co.ru/"
    DESCRIPTION
        "This MIB defines the objects to control PoE subsystem."

    REVISION "201904020000Z"
    DESCRIPTION
        "Add object eltPoeAutoRestart."

    REVISION "201711070000Z"
    DESCRIPTION
        "Initial revision."
    ::= { eltMes 16 }

eltMesPoeNotifications OBJECT IDENTIFIER ::= { eltMesPoe 0 }
eltMesPoeObjects       OBJECT IDENTIFIER ::= { eltMesPoe 1 }

eltPoeRestartAction OBJECT-TYPE
    SYNTAX       INTEGER(0|1..8|255)
    MAX-ACCESS   read-write
    STATUS       current
    DESCRIPTION  "Restart PoE subsystem.
                  1..8 - unit's number in stack; 0 - all stack; 255 - no action" 
    DEFVAL       { 255 }
  ::= { eltMesPoeObjects 1 }
  
eltPoeDisabled OBJECT-TYPE
    SYNTAX       TruthValue
    MAX-ACCESS   read-write
    STATUS       current
    DESCRIPTION  "Indicates whether PoE is enabled or disabled in the system." 
    DEFVAL       { true }
  ::= { eltMesPoeObjects 2 }

eltPoeAutoRestart OBJECT-TYPE
    SYNTAX       TruthValue
    MAX-ACCESS   read-write
    STATUS       current
    DESCRIPTION  "Enables automatic restart of POE after failure." 
    DEFVAL       { true }
  ::= { eltMesPoeObjects 3 }

END

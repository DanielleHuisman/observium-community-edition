ELTEX-MES-SMARTPORTS-MIB DEFINITIONS ::= BEGIN

-- Title:      ELTEX MES SMARTPORTS Private MIB
-- Version:    1.0
-- Date:       26 Sep 2019

IMPORTS
    OBJECT-TYPE, MODULE-IDENTITY, IpAddress, Unsigned32,Counter32       FROM SNMPv2-SMI
    DisplayString, TEXTUAL-CONVENTION, TruthValue, RowStatus            FROM SNMPv2-TC
    rlSmartPortsMacroManageEntry                                        FROM RADLAN-SMARTPORTS-MIB
    eltMes                                                              FROM ELTEX-MES;

eltMesSmartPorts MODULE-IDENTITY
    LAST-UPDATED "201909260000Z"
    ORGANIZATION "Eltex Ltd."
    CONTACT-INFO "eltex-co.ru"
    DESCRIPTION
        "The private MIB module definition for SmartPorts services in Eltex devices."
    ::= { eltMes 17 }

---


eltMesSmartPortsObjects OBJECT IDENTIFIER ::= { eltMesSmartPorts 1 }

eltMesSmartPortsGlobals OBJECT IDENTIFIER ::= { eltMesSmartPortsObjects 1 } 

eltMesSmartPortsConfigs OBJECT IDENTIFIER ::= { eltMesSmartPortsObjects 2 }      

---

eltSmartPortsMacroManageTable OBJECT-TYPE
    SYNTAX      SEQUENCE OF EltSmartPortsMacroManageEntry
    MAX-ACCESS  not-accessible
    STATUS      current
    DESCRIPTION
        "A table containing Syslog collector information."
    ::= { eltMesSmartPortsConfigs 1 }

eltSmartPortsMacroManageEntry OBJECT-TYPE
    SYNTAX      EltSmartPortsMacroManageEntry
    MAX-ACCESS  not-accessible
    STATUS      current
    DESCRIPTION
        "An entry in the eltSmartPortsMacroManageTable."
    AUGMENTS   { rlSmartPortsMacroManageEntry }
    ::= { eltSmartPortsMacroManageTable 1 }

EltSmartPortsMacroManageEntry ::=
    SEQUENCE {
        eltSmartPortsMacroTrackObject Unsigned32,
        eltSmartPortsMacroTrackActivationState INTEGER
    }

eltSmartPortsMacroTrackObject OBJECT-TYPE
    SYNTAX       Unsigned32
    MAX-ACCESS   read-write
    STATUS       current
    DESCRIPTION
        "Number of associates a track object.
         0 - no association"
    DEFVAL { 0 }
    ::= { eltSmartPortsMacroManageEntry 1 }

eltSmartPortsMacroTrackActivationState OBJECT-TYPE
    SYNTAX      INTEGER {
                    any(0),
                    up(1),
                    down(2)
                }
    MAX-ACCESS  read-write
    STATUS      current
    DESCRIPTION 
        "Track state at which the macro is activated."
    DEFVAL { any }
    ::= { eltSmartPortsMacroManageEntry 2 }

END

ELTEX-QOS-MIB DEFINITIONS ::= BEGIN

-- Title:      ELTEX Quality of Service
-- Version:    1.0
-- Date:       23 Apr 2015

IMPORTS
    eltexLtd                                                FROM ELTEX-SMI-ACTUAL
    MODULE-IDENTITY, OBJECT-TYPE, Counter64, Integer32      FROM SNMPv2-SMI
    DisplayString                                           FROM SNMPv2-TC;

--
-- QoS Policy Statistics
--

eltQos MODULE-IDENTITY
    LAST-UPDATED "201504230000Z"
    ORGANIZATION "ELTEX"
    CONTACT-INFO
            "eltex@eltex.nsk.ru"
    DESCRIPTION
            "ELTEX Quality of Service"
    REVISION     "201504230000Z"
    DESCRIPTION
            ""
    ::= { eltexLtd 20 }

eltQosPolicyStats OBJECT IDENTIFIER ::= { eltQos 1 }

--
-- QoS Policy Statistics Table
--

eltQosPolicyStatsTable OBJECT-TYPE
    SYNTAX      SEQUENCE OF EltQosPolicyStatsEntry
    MAX-ACCESS  not-accessible
    STATUS      current
    DESCRIPTION
        "This table specifies Police Action related Statistical information."
    ::= { eltQosPolicyStats 1 }

eltQosPolicyStatsEntry OBJECT-TYPE
    SYNTAX      EltQosPolicyStatsEntry
    MAX-ACCESS  not-accessible
    STATUS      current
    DESCRIPTION
           "An entry containing management information applicable to a
            particular interface."
    INDEX   { eltQosPolicyStatsPolicyIndex }
    ::= { eltQosPolicyStatsTable 1 }

EltQosPolicyStatsEntry ::=
    SEQUENCE {
        eltQosPolicyStatsPolicyIndex   Integer32,
        eltQosPolicyStatsPolicy        DisplayString,
        eltQosPolicyStatsifDescr       DisplayString,
        eltQosPolicyStatsBytes         Counter64,
        eltQosPolicyStatsPkts          Counter64,
        eltQosPolicyStatsDrops         Counter64
    }

eltQosPolicyStatsPolicyIndex OBJECT-TYPE
    SYNTAX      Integer32 (1..2147483647)
    MAX-ACCESS  read-only
    STATUS      current
    DESCRIPTION
            "A unique value, greater than zero, for each policy."
    ::= { eltQosPolicyStatsEntry 1 }

eltQosPolicyStatsifDescr OBJECT-TYPE
    SYNTAX      DisplayString (SIZE (0..255))
    MAX-ACCESS  read-only
    STATUS      current
    DESCRIPTION
            "A textual string containing information about the
            interface. This string should include the name of the
            manufacturer, the product name and the version of the
            interface hardware/software."
    ::= { eltQosPolicyStatsEntry 2 }

eltQosPolicyStatsPolicy OBJECT-TYPE
    SYNTAX      DisplayString (SIZE (0..255))
    MAX-ACCESS  read-only
    STATUS      current
    DESCRIPTION
            "Name of the policy map."
    ::= { eltQosPolicyStatsEntry 3 }

eltQosPolicyStatsBytes OBJECT-TYPE
    SYNTAX      Counter64
    MAX-ACCESS  read-only
    STATUS      current
    DESCRIPTION
            "The count of octets treated as conforming by the policing feature."
    ::= { eltQosPolicyStatsEntry 4 }

eltQosPolicyStatsPkts OBJECT-TYPE
    SYNTAX      Counter64
    MAX-ACCESS  read-only
    STATUS      current
    DESCRIPTION
            "The count of packets treated as conforming by the policing feature."
    ::= { eltQosPolicyStatsEntry 5 }

eltQosPolicyStatsDrops OBJECT-TYPE
    SYNTAX      Counter64
    MAX-ACCESS  read-only
    STATUS      current
    DESCRIPTION
            "The count of packets dropped as conforming by the policing feature."
    ::= { eltQosPolicyStatsEntry 6 }

--
-- QoS Class Statistics
--

eltQosClassStats OBJECT IDENTIFIER ::= { eltQos 2}

--
-- QoS Class Statistics Table
--

eltQosClassStatsTable OBJECT-TYPE
    SYNTAX SEQUENCE OF EltQosClassStatsEntry
    MAX-ACCESS not-accessible
    STATUS current
    DESCRIPTION
        "This table specifies Class Action related Statistical information."
    ::= { eltQosClassStats 1 }

eltQosClassStatsEntry OBJECT-TYPE
    SYNTAX      EltQosClassStatsEntry
    MAX-ACCESS  not-accessible
    STATUS      current
    DESCRIPTION
           "An entry containing management information applicable to a
            particular interface."
    INDEX   { eltQosClassStatsClassIndex }
    ::= { eltQosClassStatsTable 1 }


EltQosClassStatsEntry ::=
    SEQUENCE {
        eltQosClassStatsClassIndex   Integer32,
        eltQosClassStatsPolicy       DisplayString,
        eltQosClassStatsClass        DisplayString,
        eltQosClassStatsifDescr      DisplayString,
        eltQosClassStatsBytes        Counter64,
        eltQosClassStatsPkts         Counter64,
        eltQosClassStatsDrops        Counter64
    }

eltQosClassStatsClassIndex OBJECT-TYPE
    SYNTAX      Integer32 (1..2147483647)
    MAX-ACCESS  read-only
    STATUS      current
    DESCRIPTION
            "A unique value, greater than zero, for each class."
    ::= { eltQosClassStatsEntry 1 }

eltQosClassStatsifDescr OBJECT-TYPE
    SYNTAX      DisplayString (SIZE (0..255))
    MAX-ACCESS  read-only
    STATUS      current
    DESCRIPTION
            "A textual string containing information about the
            interface. This string should include the name of the
            manufacturer, the product name and the version of the
            interface hardware/software."
    ::= { eltQosClassStatsEntry 2 }

eltQosClassStatsClass OBJECT-TYPE
    SYNTAX      DisplayString (SIZE (0..255))
    MAX-ACCESS  read-only
    STATUS      current
    DESCRIPTION
            "Name of the class map."
    ::= { eltQosClassStatsEntry 3 }

eltQosClassStatsPolicy OBJECT-TYPE
    SYNTAX      DisplayString (SIZE (0..255))
    MAX-ACCESS  read-only
    STATUS      current
    DESCRIPTION
            "Name of the policy map."
    ::= { eltQosClassStatsEntry 4 }

eltQosClassStatsBytes OBJECT-TYPE
    SYNTAX      Counter64
    MAX-ACCESS  read-only
    STATUS      current
    DESCRIPTION
            "The count of octets treated as conforming by the class feature."
    ::= { eltQosClassStatsEntry 5 }

eltQosClassStatsPkts OBJECT-TYPE
    SYNTAX      Counter64
    MAX-ACCESS  read-only
    STATUS      current
    DESCRIPTION
            "The count of packets treated as conforming by the class feature."
    ::= { eltQosClassStatsEntry 6 }

eltQosClassStatsDrops OBJECT-TYPE
    SYNTAX      Counter64
    MAX-ACCESS  read-only
    STATUS      current
    DESCRIPTION
            "The count of packets dropped as conforming by the class feature."
    ::= { eltQosClassStatsEntry 7 }

END

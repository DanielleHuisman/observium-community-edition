ELTEX-VLAN-TRANSLATION-MIB DEFINITIONS ::= BEGIN

  IMPORTS
    OBJECT-TYPE
      FROM SNMPv2-SMI

    ifIndex
      FROM IF-MIB

    TEXTUAL-CONVENTION,
    RowStatus
      FROM SNMPv2-TC

    VlanId
      FROM Q-BRIDGE-MIB

    eltexLtd
      FROM ELTEX-SMI-ACTUAL;

  eltexVlanTranslationMIB MODULE-IDENTITY
    LAST-UPDATED "201911070000Z" -- Thu Nov 07 00:00:00 GMT 2019
    ORGANIZATION "Eltex Enterprise Co, Ltd."
    CONTACT-INFO 
        "www.eltex-co.ru"
    DESCRIPTION  
            "The MIB module for vlan translation management."
    REVISION "201911070000Z"
    DESCRIPTION
            "Added addVlan action."
    REVISION "201902040000Z"
    DESCRIPTION "Initial revision."
  ::= { eltexLtd 54 }

-------------------------------------------------------------------------------
-- Textual Conversions.

EltexSqinqDirection ::= TEXTUAL-CONVENTION
    STATUS      current
    DESCRIPTION
        "Selective QinQ ingress/egress rule."
    SYNTAX  INTEGER {
        ingress(1),
        egress(2)
    }

EltexSqinqAction ::= TEXTUAL-CONVENTION
    STATUS      current
    DESCRIPTION
        "Selective QinQ action."
    SYNTAX  INTEGER {
        overrideVlan(1),
        addVlan(2),
        permit(3),
        deny(4)
    }

-------------------------------------------------------------------------------

eltexVlanTranslationObjects  OBJECT IDENTIFIER ::= { eltexVlanTranslationMIB 1 }

eltexSqinqObjects            OBJECT IDENTIFIER ::= { eltexVlanTranslationObjects 1 }

eltexSqinqGlobals            OBJECT IDENTIFIER ::= { eltexSqinqObjects 1 }
eltexSqinqConfigs            OBJECT IDENTIFIER ::= { eltexSqinqObjects 2 }
eltexSqinqStatistics         OBJECT IDENTIFIER ::= { eltexSqinqObjects 3 }

-------------------------------------------------------------------------------

--
-- Selective QinQ ports configuration
--

eltexSqinqPortTable OBJECT-TYPE
    SYNTAX      SEQUENCE OF EltexSqinqPortEntry
    MAX-ACCESS  not-accessible
    STATUS      current
    DESCRIPTION
       "The table specifies all Selective QinQ rules configured by user."
    ::=  { eltexSqinqConfigs 1 }

eltexSqinqPortEntry OBJECT-TYPE
    SYNTAX      EltexSqinqPortEntry
    MAX-ACCESS  not-accessible
    STATUS      current
    DESCRIPTION
        "An entry in the eltexSqinqPortTable."
    INDEX  { ifIndex, 
             eltexSqinqDirection, 
             eltexSqinqClassifierVlan }
    ::= { eltexSqinqPortTable 1 }

EltexSqinqPortEntry ::=
    SEQUENCE {
        eltexSqinqDirection        EltexSqinqDirection,
        eltexSqinqClassifierVlan   VlanId,
        eltexSqinqAction           EltexSqinqAction,
        eltexSqinqActionVlan       VlanId,
        eltexSqinqRowStatus        RowStatus
    }

eltexSqinqDirection OBJECT-TYPE
    SYNTAX      EltexSqinqDirection
    MAX-ACCESS  not-accessible
    STATUS      current
    DESCRIPTION
        "Selective QinQ rule direction."
    ::= { eltexSqinqPortEntry 1 }

eltexSqinqClassifierVlan OBJECT-TYPE
    SYNTAX      VlanId
    MAX-ACCESS  not-accessible
    STATUS      current
    DESCRIPTION
        "Selective QinQ rule classifier's VLAN id."
    ::= { eltexSqinqPortEntry 2 }

eltexSqinqAction OBJECT-TYPE
    SYNTAX      EltexSqinqAction
    MAX-ACCESS  read-write
    STATUS      current
    DESCRIPTION
        "Selective QinQ rule action."
    ::= { eltexSqinqPortEntry 3 }

eltexSqinqActionVlan OBJECT-TYPE
    SYNTAX      VlanId
    MAX-ACCESS  read-write
    STATUS      current
    DESCRIPTION
        "Selective QinQ rule action's VLAN id."
    ::= { eltexSqinqPortEntry 4 }

eltexSqinqRowStatus OBJECT-TYPE
    SYNTAX      RowStatus
    MAX-ACCESS  read-write
    STATUS      current
    DESCRIPTION
        "RowStatus for Selective QinQ table. Allowed values are 
         CreateAndWait, Active and Destroy."
    ::= { eltexSqinqPortEntry 5 }

END

-- *****************************************************************
-- Engenius Private MIB
--
-- March 2009, Greg Lin
--
-- Copyright (c) 2000-2003 by Sendfar Technology Co., Ltd.
-- All rights reserved.
-- *****************************************************************

--module definition

ENGENIUS-STATUS-MIB DEFINITIONS ::= BEGIN

       IMPORTS
       MODULE-IDENTITY, OBJECT-TYPE, 
       Counter32, IpAddress, enterprises, dod        
       FROM SNMPv2-SMI
       DisplayString , MacAddress, RowStatus, TruthValue
       FROM SNMPv2-TC;

-- module OID definition
   engeniusstatus MODULE-IDENTITY
   LAST-UPDATED "0511250000Z"
   ORGANIZATION "Senao R&D Dept., S/W Division"
   CONTACT-INFO
       "
       Info
       SENAO INTERNATIONAL CO., LTD.
       No.500, Fusing 3 Rd., Hwa-Ya Technical Park,
       Kuei-Shan Hsiang, TAOYUAN County 333, TAIWAN, R.O.C.
       Tel: 886-3-328-9289
       Fax: 886-3-328-9666
       E-mail: info@senao.com.tw
       "
   DESCRIPTION
       "The MIB module defines Senao implementation-specific metrics useful in managing IEEE 802.11 on Senao devices.
This is used as a supplement to the standard 802.11 MIB proposed by IEEE."
   REVISION "0511250000Z"    
   DESCRIPTION	    "first draft"

      

    ::= { engenius 3 }

engenius				OBJECT IDENTIFIER ::= { enterprises 14125 }



-- Group OID definition

   wirelessCBStatus OBJECT IDENTIFIER ::= { engeniusstatus 1 }
   wirelessAPStatus OBJECT IDENTIFIER ::= { engeniusstatus 2 } 
   ifCBStatus       OBJECT IDENTIFIER ::= { engeniusstatus 3 }
   ifAPStatus       OBJECT IDENTIFIER ::= { engeniusstatus 4 }

   
-- objects definition CB

  cbConnectionStatus OBJECT-TYPE
	    SYNTAX OCTET STRING 
	    MAX-ACCESS  read-only
	    STATUS  mandatory
	    DESCRIPTION
		    " This attribute reflects the Service Set ID used in the SSID parameter of the most recent MLME_Scan.request"
	::= { wirelessCBStatus 1 }

  cbSignalStrength OBJECT-TYPE
	    SYNTAX OCTET STRING 
	    MAX-ACCESS  read-only
	    STATUS  mandatory
	    DESCRIPTION
		    " signal strength refers to the magnitude of the electric field at a reference point that is a significant distance from the transmitting antenna"
	::= { wirelessCBStatus 2 }
	

	cbCurrentTxRate OBJECT-TYPE
	    SYNTAX OCTET STRING 
	    MAX-ACCESS  read-only
	    STATUS  mandatory
	    DESCRIPTION
		    " The transmit bit rates operated, corresponding to data rates from 1 Mb/s to 54 Mb/s."
	::= { wirelessCBStatus 3 }


	cbCurrentChannel OBJECT-TYPE
	    SYNTAX OCTET STRING 
	    MAX-ACCESS  read-only
	    STATUS  mandatory
	    DESCRIPTION
		    " The operating frequency channel. Valid numbers are as defind in ISO/IEC 8802-11:1999, 15.4.6.2."
	::= { wirelessCBStatus 4 }


	cbEssid OBJECT-TYPE
		SYNTAX OCTET STRING 
    	MAX-ACCESS read-only
    	STATUS mandatory
		DESCRIPTION
			" This attribute reflects the Service Set ID. This value may be modified by an external management entity and used by the local SME to make decisions about the Scanning process. The connectedToSSID length is limit between 1~ 32 characters."			
	::= { wirelessCBStatus 5 }
	
	cbTxPower OBJECT-TYPE
		SYNTAX OCTET STRING 
    	MAX-ACCESS read-only
    	STATUS mandatory
		DESCRIPTION
			" The Tx Power is transmit power setting value."			
	::= { wirelessCBStatus 6 }	
	        
	cbIpAddress OBJECT-TYPE
		SYNTAX OCTET STRING 
    	MAX-ACCESS read-only
    	STATUS mandatory
		DESCRIPTION
			" The IP address of this device used over its interface."		
	::= { wirelessCBStatus 7 }		        

	        
	        
	        
-- objects definition AP

	apSsidProfile_1 OBJECT-TYPE
		SYNTAX OCTET STRING 
    	MAX-ACCESS read-only
    	STATUS mandatory
		DESCRIPTION
			" This attribute reflects the Service Set ID. This value may be modified by an external management entity and used by the local SME to make decisions about the Scanning process. The connectedToSSID length is limit between 1~ 32 characters."			
	::= { wirelessAPStatus 1 }   
	
	apSsidProfile_2 OBJECT-TYPE
		SYNTAX OCTET STRING 
    	MAX-ACCESS read-only
    	STATUS mandatory
		DESCRIPTION
			" This attribute reflects the Service Set ID. This value may be modified by an external management entity and used by the local SME to make decisions about the Scanning process. The connectedToSSID length is limit between 1~ 32 characters."			
	::= { wirelessAPStatus 2 }   
	
	
	apSsidProfile_3 OBJECT-TYPE
		SYNTAX OCTET STRING 
    	MAX-ACCESS read-only
    	STATUS mandatory
		DESCRIPTION
			" This attribute reflects the Service Set ID. This value may be modified by an external management entity and used by the local SME to make decisions about the Scanning process. The connectedToSSID length is limit between 1~ 32 characters."			
	::= { wirelessAPStatus 3 }   
	
	
	apSsidProfile_4 OBJECT-TYPE
		SYNTAX OCTET STRING 
    	MAX-ACCESS read-only
    	STATUS mandatory
		DESCRIPTION
			" This attribute reflects the Service Set ID. This value may be modified by an external management entity and used by the local SME to make decisions about the Scanning process. The connectedToSSID length is limit between 1~ 32 characters."			
	::= { wirelessAPStatus 4 }   

  apWlanMode OBJECT-TYPE
	    SYNTAX OCTET STRING 
	    MAX-ACCESS  read-only
	    STATUS  mandatory
	    DESCRIPTION
		    " The operating mode of the WLAN interface"
	::= { wirelessAPStatus 5 }


	apCurrentChannel OBJECT-TYPE
	    SYNTAX OCTET STRING 
	    MAX-ACCESS  read-only
	    STATUS  mandatory
	    DESCRIPTION
		    " The operating frequency channel. Valid numbers are as defind in ISO/IEC 8802-11:1999, 15.4.6.2."
	::= { wirelessAPStatus 6 }

	apTxPower OBJECT-TYPE
	    SYNTAX OCTET STRING 
	    MAX-ACCESS  read-only
	    STATUS  mandatory
	    DESCRIPTION
		    " The operating transmission power. Valid numbers are as defind in ISO/IEC 8802-11:1999, 15.4.6.2."
	::= { wirelessAPStatus 7 }

	apIpAddress OBJECT-TYPE
	    SYNTAX OCTET STRING 
	    MAX-ACCESS  read-only
	    STATUS  mandatory
	    DESCRIPTION
		    " The IP address of this device used over its interface."
	::= { wirelessAPStatus 8 }
	

-- CB Ath0 
	        
	cbAth0_RxPackets OBJECT-TYPE
		SYNTAX OCTET STRING 
    	MAX-ACCESS read-only
    	STATUS mandatory
		DESCRIPTION
			" The number of packets received on the radio interface Ath0."			
	::= { ifCBStatus 1 }
	        

	cbAth0_RxBytes OBJECT-TYPE
		SYNTAX OCTET STRING 
    	MAX-ACCESS read-only
    	STATUS mandatory
		DESCRIPTION
			" The number of bytes received on the radio interface Ath0."			
	::= { ifCBStatus 2 }
	        
	cbAth0_RxErrors OBJECT-TYPE
		SYNTAX OCTET STRING 
    	MAX-ACCESS read-only
    	STATUS mandatory
		DESCRIPTION
			" The number of errors packets received on the radio interface Ath0."			
	::= { ifCBStatus 3 }
	        

	cbAth0_TxPackets OBJECT-TYPE
		SYNTAX OCTET STRING 
    	MAX-ACCESS read-only
    	STATUS mandatory
		DESCRIPTION
			" The number of packets transmited on the radio interface Ath0."			
	::= { ifCBStatus 4 }
	        

	cbAth0_TxBytes OBJECT-TYPE
		SYNTAX OCTET STRING 
    	MAX-ACCESS read-only
    	STATUS mandatory
		DESCRIPTION
			" The number of bytes transmited on the radio interface Ath0."			
	::= { ifCBStatus 5 }
	        
	cbAth0_TxErrors OBJECT-TYPE
		SYNTAX OCTET STRING 
    	MAX-ACCESS read-only
    	STATUS mandatory
		DESCRIPTION
			" The number of error packets transmited on the radio interface Ath0."			
	::= { ifCBStatus 6 }


-- CB br0 
	        
	cbBr0_RxPackets OBJECT-TYPE
		SYNTAX OCTET STRING 
    	MAX-ACCESS read-only
    	STATUS mandatory
		DESCRIPTION
			" The number of packets received on the Bridge interface br0."			
	::= { ifCBStatus 7 }
	        

	cbBr0_RxBytes OBJECT-TYPE
		SYNTAX OCTET STRING 
    	MAX-ACCESS read-only
    	STATUS mandatory
		DESCRIPTION
			" The number of bytes received on the Bridge interface br0."			
	::= { ifCBStatus 8 }
	        
	cbBr0_RxErrors OBJECT-TYPE
		SYNTAX OCTET STRING 
    	MAX-ACCESS read-only
    	STATUS mandatory
		DESCRIPTION
			" The number of errors packets received on the Bridge interface br0."			
	::= { ifCBStatus 9 }
	        

	cbBr0_TxPackets OBJECT-TYPE
		SYNTAX OCTET STRING 
    	MAX-ACCESS read-only
    	STATUS mandatory
		DESCRIPTION
			" The number of packets transmited on the Bridge interface br0."			
	::= { ifCBStatus 10 }
	        

	cbBr0_TxBytes OBJECT-TYPE
		SYNTAX OCTET STRING 
    	MAX-ACCESS read-only
    	STATUS mandatory
		DESCRIPTION
			" The number of bytes transmited on the Bridge interface br0."			
	::= { ifCBStatus 11 }
	        
	cbBr0_TxErrors OBJECT-TYPE
		SYNTAX OCTET STRING 
    	MAX-ACCESS read-only
    	STATUS mandatory
		DESCRIPTION
			" The number of error packets transmited on the Bridge interface br0."			
	::= { ifCBStatus 12 }



-- CB eth0 
	        
	cbEth0_RxPackets OBJECT-TYPE
		SYNTAX OCTET STRING 
    	MAX-ACCESS read-only
    	STATUS mandatory
		DESCRIPTION
			" The number of packets received on the ethernet interface eth0."			
	::= { ifCBStatus 13 }
	        

	cbEth0_RxBytes OBJECT-TYPE
		SYNTAX OCTET STRING 
    	MAX-ACCESS read-only
    	STATUS mandatory
		DESCRIPTION
			" The number of bytes received on the ethernet interface eth0."			
	::= { ifCBStatus 14 }
	        
	cbEth0_RxErrors OBJECT-TYPE
		SYNTAX OCTET STRING 
    	MAX-ACCESS read-only
    	STATUS mandatory
		DESCRIPTION
			" The number of errors packets received on the ethernet interface eth0."			
	::= { ifCBStatus 15 }
	        

	cbEth0_TxPackets OBJECT-TYPE
		SYNTAX OCTET STRING 
    	MAX-ACCESS read-only
    	STATUS mandatory
		DESCRIPTION
			" The number of packets transmited on the ethernet interface eth0."			
	::= { ifCBStatus 16 }
	        

	cbEth0_TxBytes OBJECT-TYPE
		SYNTAX OCTET STRING 
    	MAX-ACCESS read-only
    	STATUS mandatory
		DESCRIPTION
			" The number of bytes transmited on the ethernet interface eth0."			
	::= { ifCBStatus 17 }
	        
	cbEth0_TxErrors OBJECT-TYPE
		SYNTAX OCTET STRING 
    	MAX-ACCESS read-only
    	STATUS mandatory
		DESCRIPTION
			" The number of error packets transmited on the ethernet interface eth0."			
	::= { ifCBStatus 18 }



-- AP Ath1 ~4
	        
	apAth1_RxPackets OBJECT-TYPE
		SYNTAX OCTET STRING 
    	MAX-ACCESS read-only
    	STATUS mandatory
		DESCRIPTION
			" The number of packets received on the radio interface ath1."			
	::= { ifAPStatus 1 }
	        

	apAth1_RxBytes OBJECT-TYPE
		SYNTAX OCTET STRING 
    	MAX-ACCESS read-only
    	STATUS mandatory
		DESCRIPTION
			" The number of bytes received on the radio interface ath1."			
	::= { ifAPStatus 2 }
	        
	apAth1_RxErrors OBJECT-TYPE
		SYNTAX OCTET STRING 
    	MAX-ACCESS read-only
    	STATUS mandatory
		DESCRIPTION
			" The number of errors packets received on the radio interface ath1."			
	::= { ifAPStatus 3 }
	        

	apAth1_TxPackets OBJECT-TYPE
		SYNTAX OCTET STRING 
    	MAX-ACCESS read-only
    	STATUS mandatory
		DESCRIPTION
			" The number of packets transmited on the radio interface ath1."			
	::= { ifAPStatus 4 }
	        

	apAth1_TxBytes OBJECT-TYPE
		SYNTAX OCTET STRING 
    	MAX-ACCESS read-only
    	STATUS mandatory
		DESCRIPTION
			" The number of bytes transmited on the radio interface ath1."			
	::= { ifAPStatus 5 }
	        
	apAth1_TxErrors OBJECT-TYPE
		SYNTAX OCTET STRING 
    	MAX-ACCESS read-only
    	STATUS mandatory
		DESCRIPTION
			" The number of error packets transmited on the radio interface ath1."			
	::= { ifAPStatus 6 }

  ------- end of Ath1
  
 apAth2_RxPackets OBJECT-TYPE
		SYNTAX OCTET STRING 
    	MAX-ACCESS read-only
    	STATUS mandatory
		DESCRIPTION
			" The number of packets received on the radio interface ath2."			
	::= { ifAPStatus 7 }
	        

	apAth2_RxBytes OBJECT-TYPE
		SYNTAX OCTET STRING 
    	MAX-ACCESS read-only
    	STATUS mandatory
		DESCRIPTION
			" The number of bytes received on the radio interface ath2."			
	::= { ifAPStatus 8 }
	        
	apAth2_RxErrors OBJECT-TYPE
		SYNTAX OCTET STRING 
    	MAX-ACCESS read-only
    	STATUS mandatory
		DESCRIPTION
			" The number of errors packets received on the radio interface ath2."			
	::= { ifAPStatus 9 }
	        

	apAth2_TxPackets OBJECT-TYPE
		SYNTAX OCTET STRING 
    	MAX-ACCESS read-only
    	STATUS mandatory
		DESCRIPTION
			" The number of packets transmited on the radio interface ath2."			
	::= { ifAPStatus 10 }
	        

	apAth2_TxBytes OBJECT-TYPE
		SYNTAX OCTET STRING 
    	MAX-ACCESS read-only
    	STATUS mandatory
		DESCRIPTION
			" The number of bytes transmited on the radio interface ath2."			
	::= { ifAPStatus 11 }
	        
	apAth2_TxErrors OBJECT-TYPE
		SYNTAX OCTET STRING 
    	MAX-ACCESS read-only
    	STATUS mandatory
		DESCRIPTION
			" The number of error packets transmited on the radio interface ath2."			
	::= { ifAPStatus 12 }
	
-- End of Ath2

 apAth3_RxPackets OBJECT-TYPE
		SYNTAX OCTET STRING 
    	MAX-ACCESS read-only
    	STATUS mandatory
		DESCRIPTION
			" The number of packets received on the radio interface ath3."			
	::= { ifAPStatus 13 }
	        

	apAth3_RxBytes OBJECT-TYPE
		SYNTAX OCTET STRING 
    	MAX-ACCESS read-only
    	STATUS mandatory
		DESCRIPTION
			" The number of bytes received on the radio interface ath3."			
	::= { ifAPStatus 14 }
	        
	apAth3_RxErrors OBJECT-TYPE
		SYNTAX OCTET STRING 
    	MAX-ACCESS read-only
    	STATUS mandatory
		DESCRIPTION
			" The number of errors packets received on the radio interface ath3."			
	::= { ifAPStatus 15 }
	        

	apAth3_TxPackets OBJECT-TYPE
		SYNTAX OCTET STRING 
    	MAX-ACCESS read-only
    	STATUS mandatory
		DESCRIPTION
			" The number of packets transmited on the radio interface ath3."			
	::= { ifAPStatus 16 }
	        

	apAth3_TxBytes OBJECT-TYPE
		SYNTAX OCTET STRING 
    	MAX-ACCESS read-only
    	STATUS mandatory
		DESCRIPTION
			" The number of bytes transmited on the radio interface ath3."			
	::= { ifAPStatus 17 }
	        
	apAth3_TxErrors OBJECT-TYPE
		SYNTAX OCTET STRING 
    	MAX-ACCESS read-only
    	STATUS mandatory
		DESCRIPTION
			" The number of error packets transmited on the radio interface ath3."			
	::= { ifAPStatus 18 }
	
-- End of Ath3

 
 apAth4_RxPackets OBJECT-TYPE
		SYNTAX OCTET STRING 
    	MAX-ACCESS read-only
    	STATUS mandatory
		DESCRIPTION
			" The number of packets received on the radio interface ath4."			
	::= { ifAPStatus 19 }
	        

	apAth4_RxBytes OBJECT-TYPE
		SYNTAX OCTET STRING 
    	MAX-ACCESS read-only
    	STATUS mandatory
		DESCRIPTION
			" The number of bytes received on the radio interface ath4."			
	::= { ifAPStatus 20 }
	        
	apAth4_RxErrors OBJECT-TYPE
		SYNTAX OCTET STRING 
    	MAX-ACCESS read-only
    	STATUS mandatory
		DESCRIPTION
			" The number of errors packets received on the radio interface ath4."			
	::= { ifAPStatus 21 }
	        

	apAth4_TxPackets OBJECT-TYPE
		SYNTAX OCTET STRING 
    	MAX-ACCESS read-only
    	STATUS mandatory
		DESCRIPTION
			" The number of packets transmited on the radio interface ath4."			
	::= { ifAPStatus 22 }
	        

	apAth4_TxBytes OBJECT-TYPE
		SYNTAX OCTET STRING 
    	MAX-ACCESS read-only
    	STATUS mandatory
		DESCRIPTION
			" The number of bytes transmited on the radio interface ath4."			
	::= { ifAPStatus 23 }
	        
	apAth4_TxErrors OBJECT-TYPE
		SYNTAX OCTET STRING 
    	MAX-ACCESS read-only
    	STATUS mandatory
		DESCRIPTION
			" The number of error packets transmited on the radio interface ath4."			
	::= { ifAPStatus 24 }
	
-- End of Ath4


--==================================================
-- AP Ath1 ~4 vid 1~4
	        
	apAth1V_RxPackets OBJECT-TYPE
		SYNTAX OCTET STRING 
    	MAX-ACCESS read-only
    	STATUS mandatory
		DESCRIPTION
			" The number of packets received on the radio vlan interface ath1."			
	::= { ifAPStatus 25 }
	        

	apAth1V_RxBytes OBJECT-TYPE
		SYNTAX OCTET STRING 
    	MAX-ACCESS read-only
    	STATUS mandatory
		DESCRIPTION
			" The number of bytes received on the radio vlan interface ath1."			
	::= { ifAPStatus 26 }
	        
	apAth1V_RxErrors OBJECT-TYPE
		SYNTAX OCTET STRING 
    	MAX-ACCESS read-only
    	STATUS mandatory
		DESCRIPTION
			" The number of errors packets received on the radio vlan interface ath1."			
	::= { ifAPStatus 27 }
	        

	apAth1V_TxPackets OBJECT-TYPE
		SYNTAX OCTET STRING 
    	MAX-ACCESS read-only
    	STATUS mandatory
		DESCRIPTION
			" The number of packets transmited on the radio vlan interface ath1."			
	::= { ifAPStatus 28 }
	        

	apAth1V_TxBytes OBJECT-TYPE
		SYNTAX OCTET STRING 
    	MAX-ACCESS read-only
    	STATUS mandatory
		DESCRIPTION
			" The number of bytes transmited on the radio vlan interface ath1."			
	::= { ifAPStatus 29 }
	        
	apAth1V_TxErrors OBJECT-TYPE
		SYNTAX OCTET STRING 
    	MAX-ACCESS read-only
    	STATUS mandatory
		DESCRIPTION
			" The number of error packets transmited on the radio vlan interface ath1"			
	::= { ifAPStatus 30 }

 -- end of Ath1 vid 1
  
 apAth2V_RxPackets OBJECT-TYPE
		SYNTAX OCTET STRING 
    	MAX-ACCESS read-only
    	STATUS mandatory
		DESCRIPTION
			" The number of packets received on the radio vlan interface ath2."			
	::= { ifAPStatus 31 }
	        

	apAth2V_RxBytes OBJECT-TYPE
		SYNTAX OCTET STRING 
    	MAX-ACCESS read-only
    	STATUS mandatory
		DESCRIPTION
			" The number of bytes received on the radio vlan interface ath2."			
	::= { ifAPStatus 32 }
	        
	apAth2V_RxErrors OBJECT-TYPE
		SYNTAX OCTET STRING 
    	MAX-ACCESS read-only
    	STATUS mandatory
		DESCRIPTION
			" The number of errors packets received on the radio vlan interface ath2."			
	::= { ifAPStatus 33 }
	        

	apAth2V_TxPackets OBJECT-TYPE
		SYNTAX OCTET STRING 
    	MAX-ACCESS read-only
    	STATUS mandatory
		DESCRIPTION
			" The number of packets transmited on the radio vlan interface ath2."			
	::= { ifAPStatus 34 }
	        

	apAth2V_TxBytes OBJECT-TYPE
		SYNTAX OCTET STRING 
    	MAX-ACCESS read-only
    	STATUS mandatory
		DESCRIPTION
			" The number of bytes transmited on the radio vlan interface ath2."			
	::= { ifAPStatus 35 }
	        
	apAth2V_TxErrors OBJECT-TYPE
		SYNTAX OCTET STRING 
    	MAX-ACCESS read-only
    	STATUS mandatory
		DESCRIPTION
			" The number of error packets transmited on the radio vlan interface ath2."			
	::= { ifAPStatus 36 }
	
-- End of Ath2 vid 2

 apAth3V_RxPackets OBJECT-TYPE
		SYNTAX OCTET STRING 
    	MAX-ACCESS read-only
    	STATUS mandatory
		DESCRIPTION
			" The number of packets received on the radio vlan interface ath3."			
	::= { ifAPStatus 37 }
	        

	apAth3V_RxBytes OBJECT-TYPE
		SYNTAX OCTET STRING 
    	MAX-ACCESS read-only
    	STATUS mandatory
		DESCRIPTION
			" The number of bytes received on the radio vlan interface ath3."			
	::= { ifAPStatus 38 }
	        
	apAth3V_RxErrors OBJECT-TYPE
		SYNTAX OCTET STRING 
    	MAX-ACCESS read-only
    	STATUS mandatory
		DESCRIPTION
			" The number of errors packets received on the radio vlan interface ath3."			
	::= { ifAPStatus 39 }
	        

	apAth3V_TxPackets OBJECT-TYPE
		SYNTAX OCTET STRING 
    	MAX-ACCESS read-only
    	STATUS mandatory
		DESCRIPTION
			" The number of packets transmited on the radio vlan interface ath3."			
	::= { ifAPStatus 40 }
	        

	apAth3V_TxBytes OBJECT-TYPE
		SYNTAX OCTET STRING 
    	MAX-ACCESS read-only
    	STATUS mandatory
		DESCRIPTION
			" The number of bytes transmited on the radio vlan interface ath3."			
	::= { ifAPStatus 41 }
	        
	apAth3V_TxErrors OBJECT-TYPE
		SYNTAX OCTET STRING 
    	MAX-ACCESS read-only
    	STATUS mandatory
		DESCRIPTION
			" The number of error packets transmited on the radio vlan interface ath3."			
	::= { ifAPStatus 42 }
	
-- End of Ath3 vid 3

 
 apAth4V_RxPackets OBJECT-TYPE
		SYNTAX OCTET STRING 
    	MAX-ACCESS read-only
    	STATUS mandatory
		DESCRIPTION
			" The number of packets received on the radio vlan interface ath4."			
	::= { ifAPStatus 43 }
	        

	apAth4V_RxBytes OBJECT-TYPE
		SYNTAX OCTET STRING 
    	MAX-ACCESS read-only
    	STATUS mandatory
		DESCRIPTION
			" The number of bytes received on the radio vlan interface ath4."			
	::= { ifAPStatus 44 }
	        
	apAth4V_RxErrors OBJECT-TYPE
		SYNTAX OCTET STRING 
    	MAX-ACCESS read-only
    	STATUS mandatory
		DESCRIPTION
			" The number of errors packets received on the radio vlan interface ath4."			
	::= { ifAPStatus 45 }
	        

	apAth4V_TxPackets OBJECT-TYPE
		SYNTAX OCTET STRING 
    	MAX-ACCESS read-only
    	STATUS mandatory
		DESCRIPTION
			" The number of packets transmited on the radio vlan interface ath4."			
	::= { ifAPStatus 46 }
	        

	apAth4V_TxBytes OBJECT-TYPE
		SYNTAX OCTET STRING 
    	MAX-ACCESS read-only
    	STATUS mandatory
		DESCRIPTION
			" The number of bytes transmited on the radio vlan interface ath4."			
	::= { ifAPStatus 47 }
	        
	apAth4V_TxErrors OBJECT-TYPE
		SYNTAX OCTET STRING 
    	MAX-ACCESS read-only
    	STATUS mandatory
		DESCRIPTION
			" The number of error packets transmited on the radio vlan interface ath4."			
	::= { ifAPStatus 48 }
	
-- End of Ath4 vid 4




-- AP br0~ 4 
	       
	apBr0_RxPackets OBJECT-TYPE
		SYNTAX OCTET STRING 
    	MAX-ACCESS read-only
    	STATUS mandatory
		DESCRIPTION
			" The number of packets received on the Bridge interface br0."			
	::= { ifAPStatus 49 }
	        

	apBr0_RxBytes OBJECT-TYPE
		SYNTAX OCTET STRING 
    	MAX-ACCESS read-only
    	STATUS mandatory
		DESCRIPTION
			" The number of bytes received on the Bridge interface br0."			
	::= { ifAPStatus 50 }
	        
	apBr0_RxErrors OBJECT-TYPE
		SYNTAX OCTET STRING 
    	MAX-ACCESS read-only
    	STATUS mandatory
		DESCRIPTION
			" The number of errors packets received on the Bridge interface br0."			
	::= { ifAPStatus 51 }
	        

	apBr0_TxPackets OBJECT-TYPE
		SYNTAX OCTET STRING 
    	MAX-ACCESS read-only
    	STATUS mandatory
		DESCRIPTION
			" The number of packets transmited on the Bridge interface br0."			
	::= { ifAPStatus 52 }
	        

	apBr0_TxBytes OBJECT-TYPE
		SYNTAX OCTET STRING 
    	MAX-ACCESS read-only
    	STATUS mandatory
		DESCRIPTION
			" The number of bytes transmited on the Bridge interface br0."			
	::= { ifAPStatus 53 }
	        
	apBr0_TxErrors OBJECT-TYPE
		SYNTAX OCTET STRING 
    	MAX-ACCESS read-only
    	STATUS mandatory
		DESCRIPTION
			" The number of error packets transmited on the Bridge interface br0."			
	::= { ifAPStatus 54 }

  ------ End of Br0	       
	        
	apBr1_RxPackets OBJECT-TYPE
		SYNTAX OCTET STRING 
    	MAX-ACCESS read-only
    	STATUS mandatory
		DESCRIPTION
			" The number of packets received on the Bridge interface br1."			
	::= { ifAPStatus 55 }
	        

	apBr1_RxBytes OBJECT-TYPE
		SYNTAX OCTET STRING 
    	MAX-ACCESS read-only
    	STATUS mandatory
		DESCRIPTION
			" The number of bytes received on the Bridge interface br1."			
	::= { ifAPStatus 56 }
	        
	apBr1_RxErrors OBJECT-TYPE
		SYNTAX OCTET STRING 
    	MAX-ACCESS read-only
    	STATUS mandatory
		DESCRIPTION
			" The number of errors packets received on the Bridge interface br1."			
	::= { ifAPStatus 57 }
	        

	apBr1_TxPackets OBJECT-TYPE
		SYNTAX OCTET STRING 
    	MAX-ACCESS read-only
    	STATUS mandatory
		DESCRIPTION
			" The number of packets transmited on the Bridge interface br1."			
	::= { ifAPStatus 58 }
	        

	apBr1_TxBytes OBJECT-TYPE
		SYNTAX OCTET STRING 
    	MAX-ACCESS read-only
    	STATUS mandatory
		DESCRIPTION
			" The number of bytes transmited on the Bridge interface br1."			
	::= { ifAPStatus 59 }
	        
	apBr1_TxErrors OBJECT-TYPE
		SYNTAX OCTET STRING 
    	MAX-ACCESS read-only
    	STATUS mandatory
		DESCRIPTION
			" The number of error packets transmited on the Bridge interface br1."			
	::= { ifAPStatus 60 }

  ------ End of Br1

	apBr2_RxPackets OBJECT-TYPE
		SYNTAX OCTET STRING 
    	MAX-ACCESS read-only
    	STATUS mandatory
		DESCRIPTION
			" The number of packets received on the Bridge interface br2."			
	::= { ifAPStatus 61 }
	        

	apBr2_RxBytes OBJECT-TYPE
		SYNTAX OCTET STRING 
    	MAX-ACCESS read-only
    	STATUS mandatory
		DESCRIPTION
			" The number of bytes received on the Bridge interface br2."			
	::= { ifAPStatus 62 }
	        
	apBr2_RxErrors OBJECT-TYPE
		SYNTAX OCTET STRING 
    	MAX-ACCESS read-only
    	STATUS mandatory
		DESCRIPTION
			" The number of errors packets received on the Bridge interface br2."			
	::= { ifAPStatus 63 }
	        

	apBr2_TxPackets OBJECT-TYPE
		SYNTAX OCTET STRING 
    	MAX-ACCESS read-only
    	STATUS mandatory
		DESCRIPTION
			" The number of packets transmited on the Bridge interface br2."			
	::= { ifAPStatus 64 }
	        

	apBr2_TxBytes OBJECT-TYPE
		SYNTAX OCTET STRING 
    	MAX-ACCESS read-only
    	STATUS mandatory
		DESCRIPTION
			" The number of bytes transmited on the Bridge interface br2."			
	::= { ifAPStatus 65 }
	        
	apBr2_TxErrors OBJECT-TYPE
		SYNTAX OCTET STRING 
    	MAX-ACCESS read-only
    	STATUS mandatory
		DESCRIPTION
			" The number of error packets transmited on the Bridge interface br2."			
	::= { ifAPStatus 66 }

  ------ End of Br2
  
	apBr3_RxPackets OBJECT-TYPE
		SYNTAX OCTET STRING 
    	MAX-ACCESS read-only
    	STATUS mandatory
		DESCRIPTION
			" The number of packets received on the Bridge interface br3."			
	::= { ifAPStatus 67 }
	        

	apBr3_RxBytes OBJECT-TYPE
		SYNTAX OCTET STRING 
    	MAX-ACCESS read-only
    	STATUS mandatory
		DESCRIPTION
			" The number of bytes received on the Bridge interface br3."			
	::= { ifAPStatus 68 }
	        
	apBr3_RxErrors OBJECT-TYPE
		SYNTAX OCTET STRING 
    	MAX-ACCESS read-only
    	STATUS mandatory
		DESCRIPTION
			" The number of errors packets received on the Bridge interface br3."			
	::= { ifAPStatus 69 }
	        

	apBr3_TxPackets OBJECT-TYPE
		SYNTAX OCTET STRING 
    	MAX-ACCESS read-only
    	STATUS mandatory
		DESCRIPTION
			" The number of packets transmited on the Bridge interface br3."			
	::= { ifAPStatus 70 }
	        

	apBr3_TxBytes OBJECT-TYPE
		SYNTAX OCTET STRING 
    	MAX-ACCESS read-only
    	STATUS mandatory
		DESCRIPTION
			" The number of bytes transmited on the Bridge interface br3."			
	::= { ifAPStatus 71 }
	        
	apBr3_TxErrors OBJECT-TYPE
		SYNTAX OCTET STRING 
    	MAX-ACCESS read-only
    	STATUS mandatory
		DESCRIPTION
			" The number of error packets transmited on the Bridge interface br3."			
	::= { ifAPStatus 72 }

  ------ End of Br3
  
	apBr4_RxPackets OBJECT-TYPE
		SYNTAX OCTET STRING 
    	MAX-ACCESS read-only
    	STATUS mandatory
		DESCRIPTION
			" The number of packets received on the Bridge interface br4."			
	::= { ifAPStatus 73 }
	        

	apBr4_RxBytes OBJECT-TYPE
		SYNTAX OCTET STRING 
    	MAX-ACCESS read-only
    	STATUS mandatory
		DESCRIPTION
			" The number of bytes received on the Bridge interface br4."			
	::= { ifAPStatus 74 }
	        
	apBr4_RxErrors OBJECT-TYPE
		SYNTAX OCTET STRING 
    	MAX-ACCESS read-only
    	STATUS mandatory
		DESCRIPTION
			" The number of errors packets received on the Bridge interface br4."			
	::= { ifAPStatus 75 }
	        

	apBr4_TxPackets OBJECT-TYPE
		SYNTAX OCTET STRING 
    	MAX-ACCESS read-only
    	STATUS mandatory
		DESCRIPTION
			" The number of packets transmited on the Bridge interface br4."			
	::= { ifAPStatus 76 }
	        

	apBr4_TxBytes OBJECT-TYPE
		SYNTAX OCTET STRING 
    	MAX-ACCESS read-only
    	STATUS mandatory
		DESCRIPTION
			" The number of bytes transmited on the Bridge interface br4."			
	::= { ifAPStatus 77 }
	        
	apBr4_TxErrors OBJECT-TYPE
		SYNTAX OCTET STRING 
    	MAX-ACCESS read-only
    	STATUS mandatory
		DESCRIPTION
			" The number of error packets transmited on the Bridge interface br4."			
	::= { ifAPStatus 78 }

  ------ End of Br4    


-- AP eth0 
	        
	apEth0_RxPackets OBJECT-TYPE
		SYNTAX OCTET STRING 
    	MAX-ACCESS read-only
    	STATUS mandatory
		DESCRIPTION
			" The number of packets received on the Ethernet interface eth0."			
	::= { ifAPStatus 79 }
	        

	apEth0_RxBytes OBJECT-TYPE
		SYNTAX OCTET STRING 
    	MAX-ACCESS read-only
    	STATUS mandatory
		DESCRIPTION
			" The number of bytes received on the Ethernet interface eth0."			
	::= { ifAPStatus 80 }
	        
	apEth0_RxErrors OBJECT-TYPE
		SYNTAX OCTET STRING 
    	MAX-ACCESS read-only
    	STATUS mandatory
		DESCRIPTION
			" The number of errors packets received on the Ethernet interface eth0."			
	::= { ifAPStatus 81 }
	        

	apEth0_TxPackets OBJECT-TYPE
		SYNTAX OCTET STRING 
    	MAX-ACCESS read-only
    	STATUS mandatory
		DESCRIPTION
			" The number of packets transmited on the Ethernet interface eth0."			
	::= { ifAPStatus 82 }
	        

	apEth0_TxBytes OBJECT-TYPE
		SYNTAX OCTET STRING 
    	MAX-ACCESS read-only
    	STATUS mandatory
		DESCRIPTION
			" The number of bytes transmited on the Ethernet interface eth0."			
	::= { ifAPStatus 83 }
	        
	apEth0_TxErrors OBJECT-TYPE
		SYNTAX OCTET STRING 
    	MAX-ACCESS read-only
    	STATUS mandatory
		DESCRIPTION
			" The number of error packets transmited on the Ethernet interface eth0."			
	::= { ifAPStatus 84 }


-- AP eth0 vid 1 ~ 4
	        
	apEth0V1_RxPackets OBJECT-TYPE
		SYNTAX OCTET STRING 
    	MAX-ACCESS read-only
    	STATUS mandatory
		DESCRIPTION
			" The number of packets received on the Ethernet vlan interface eth0 at profile 1."			
	::= { ifAPStatus 85 }
	        

	apEth0V1_RxBytes OBJECT-TYPE
		SYNTAX OCTET STRING 
    	MAX-ACCESS read-only
    	STATUS mandatory
		DESCRIPTION
			" The number of bytes received on the Ethernet vlan interface eth0 at profile 1."			
	::= { ifAPStatus 86 }
	        
	apEth0V1_RxErrors OBJECT-TYPE
		SYNTAX OCTET STRING 
    	MAX-ACCESS read-only
    	STATUS mandatory
		DESCRIPTION
			" The number of errors packets received on the Ethernet vlan interface eth0 at profile 1."			
	::= { ifAPStatus 87 }
	        

	apEth0V1_TxPackets OBJECT-TYPE
		SYNTAX OCTET STRING 
    	MAX-ACCESS read-only
    	STATUS mandatory
		DESCRIPTION
			" The number of packets transmited on the Ethernet vlan interface eth0 at profile 1."			
	::= { ifAPStatus 88 }
	        

	apEth0V1_TxBytes OBJECT-TYPE
		SYNTAX OCTET STRING 
    	MAX-ACCESS read-only
    	STATUS mandatory
		DESCRIPTION
			" The number of bytes transmited on the Ethernet vlan interface eth0 at profile 1."			
	::= { ifAPStatus 89 }
	        
	apEth0V1_TxErrors OBJECT-TYPE
		SYNTAX OCTET STRING 
    	MAX-ACCESS read-only
    	STATUS mandatory
		DESCRIPTION
			" The number of error packets transmited on the Ethernet vlan interface eth0 at profile 1."			
	::= { ifAPStatus 90 }
	
	------- end of Eth0 vid 1

	apEth0V2_RxPackets OBJECT-TYPE
		SYNTAX OCTET STRING 
    	MAX-ACCESS read-only
    	STATUS mandatory
		DESCRIPTION
			" The number of packets received on the Ethernet vlan interface eth0 at profile 2."			
	::= { ifAPStatus 91 }
	        

	apEth0V2_RxBytes OBJECT-TYPE
		SYNTAX OCTET STRING 
    	MAX-ACCESS read-only
    	STATUS mandatory
		DESCRIPTION
			" The number of bytes received on the Ethernet vlan interface eth0 at profile 2."			
	::= { ifAPStatus 92 }
	        
	apEth0V2_RxErrors OBJECT-TYPE
		SYNTAX OCTET STRING 
    	MAX-ACCESS read-only
    	STATUS mandatory
		DESCRIPTION
			" The number of errors packets received on the Ethernet vlan interface eth0 at profile 2."			
	::= { ifAPStatus 93 }
	        

	apEth0V2_TxPackets OBJECT-TYPE
		SYNTAX OCTET STRING 
    	MAX-ACCESS read-only
    	STATUS mandatory
		DESCRIPTION
			" The number of packets transmited on the Ethernet vlan interface eth0 at profile 2."			
	::= { ifAPStatus 94 }
	        

	apEth0V2_TxBytes OBJECT-TYPE
		SYNTAX OCTET STRING 
    	MAX-ACCESS read-only
    	STATUS mandatory
		DESCRIPTION
			" The number of bytes transmited on the Ethernet vlan interface eth0 at profile 2."			
	::= { ifAPStatus 95 }
	        
	apEth0V2_TxErrors OBJECT-TYPE
		SYNTAX OCTET STRING 
    	MAX-ACCESS read-only
    	STATUS mandatory
		DESCRIPTION
			" The number of error packets transmited on the Ethernet vlan interface eth0 at profile 2."			
	::= { ifAPStatus 96 }
	
	------- end of Eth0 vid 2
	
	apEth0V3_RxPackets OBJECT-TYPE
		SYNTAX OCTET STRING 
    	MAX-ACCESS read-only
    	STATUS mandatory
		DESCRIPTION
			" The number of packets received on the Ethernet vlan interface eth0 at profile 3."			
	::= { ifAPStatus 97 }
	        

	apEth0V3_RxBytes OBJECT-TYPE
		SYNTAX OCTET STRING 
    	MAX-ACCESS read-only
    	STATUS mandatory
		DESCRIPTION
			" The number of bytes received on the Ethernet vlan interface eth0 at profile 3."			
	::= { ifAPStatus 98 }
	        
	apEth0V3_RxErrors OBJECT-TYPE
		SYNTAX OCTET STRING 
    	MAX-ACCESS read-only
    	STATUS mandatory
		DESCRIPTION
			" The number of errors packets received on the Ethernet vlan interface eth0 at profile 3."			
	::= { ifAPStatus 99 }
	        

	apEth0V3_TxPackets OBJECT-TYPE
		SYNTAX OCTET STRING 
    	MAX-ACCESS read-only
    	STATUS mandatory
		DESCRIPTION
			" The number of packets transmited on the Ethernet vlan interface eth0 at profile 3."			
	::= { ifAPStatus 100 }
	        

	apEth0V3_TxBytes OBJECT-TYPE
		SYNTAX OCTET STRING 
    	MAX-ACCESS read-only
    	STATUS mandatory
		DESCRIPTION
			" The number of bytes transmited on the Ethernet vlan interface eth0 at profile 3."			
	::= { ifAPStatus 101 }
	        
	apEth0V3_TxErrors OBJECT-TYPE
		SYNTAX OCTET STRING 
    	MAX-ACCESS read-only
    	STATUS mandatory
		DESCRIPTION
			" The number of error packets transmited on the Ethernet vlan interface eth0 at profile 3."			
	::= { ifAPStatus 102 }
	
	------- end of Eth0 vid 3
	
	apEth0V4_RxPackets OBJECT-TYPE
		SYNTAX OCTET STRING 
    	MAX-ACCESS read-only
    	STATUS mandatory
		DESCRIPTION
			" The number of packets received on the Ethernet vlan interface eth0 at profile 4."			
	::= { ifAPStatus 103 }
	        

	apEth0V4_RxBytes OBJECT-TYPE
		SYNTAX OCTET STRING 
    	MAX-ACCESS read-only
    	STATUS mandatory
		DESCRIPTION
			" The number of bytes received on the Ethernet vlan interface eth0 at profile 4."			
	::= { ifAPStatus 104 }
	        
	apEth0V4_RxErrors OBJECT-TYPE
		SYNTAX OCTET STRING 
    	MAX-ACCESS read-only
    	STATUS mandatory
		DESCRIPTION
			" The number of errors packets received on the Ethernet vlan interface eth0 at profile 4."			
	::= { ifAPStatus 105 }
	        

	apEth0V4_TxPackets OBJECT-TYPE
		SYNTAX OCTET STRING 
    	MAX-ACCESS read-only
    	STATUS mandatory
		DESCRIPTION
			" The number of packets transmited on the Ethernet vlan interface eth0 at profile 4."			
	::= { ifAPStatus 106 }
	        

	apEth0V4_TxBytes OBJECT-TYPE
		SYNTAX OCTET STRING 
    	MAX-ACCESS read-only
    	STATUS mandatory
		DESCRIPTION
			" The number of bytes transmited on the Ethernet vlan interface eth0 at profile 4."			
	::= { ifAPStatus 107 }
	        
	apEth0V4_TxErrors OBJECT-TYPE
		SYNTAX OCTET STRING 
    	MAX-ACCESS read-only
    	STATUS mandatory
		DESCRIPTION
			" The number of error packets transmited on the Ethernet vlan interface eth0 at profile 4."			
	::= { ifAPStatus 108 }
	
	------- end of Eth0 vid 4		


   
END

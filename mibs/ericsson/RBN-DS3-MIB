-- *****************************************************************
-- RBN-DS3-MIB
--
-- Copyright (c) 2005 RedBack Networks, Inc.
-- All rights reserved.
--
-- *****************************************************************

RBN-DS3-MIB DEFINITIONS ::= BEGIN

IMPORTS
        MODULE-IDENTITY,
        OBJECT-TYPE
                FROM SNMPv2-SMI
        MODULE-COMPLIANCE,
        OBJECT-GROUP
                FROM SNMPv2-CONF
        RbnAlarmPerceivedSeverity,
        RbnAlarmServiceAffecting
                FROM RBN-ALARM-TC
        dsx3ConfigEntry
                FROM DS3-MIB
        rbnMgmt
                FROM RBN-SMI;

rbnDS3MIB MODULE-IDENTITY
        LAST-UPDATED    "200505090000Z" -- May 9, 2005
        ORGANIZATION    "RedBack Networks, Inc."
        CONTACT-INFO
                "       RedBack Networks, Inc.

                Postal: 300 Holger Way
                        San Jose, CA  95134
                        USA

                 Phone: +1 408 750 5000
                   Fax: +1 408 750 5599

                E-mail: mib-info@redback.com"
        DESCRIPTION
                "The MIB that describes DS3 and E3 interfaces objects
                beyond those instrumented by standards-track MIBs."
        REVISION        "200505090000Z" -- May 9, 2005
        DESCRIPTION
                "Initial version"
        ::= { rbnMgmt 38 }


rbnDs3MIBObjects OBJECT IDENTIFIER ::= { rbnDS3MIB 1 }

rbnDsx3ConfigTable   OBJECT-TYPE
        SYNTAX       SEQUENCE OF RbnDsx3ConfigEntry
        MAX-ACCESS   not-accessible
        STATUS       current
        DESCRIPTION
                "The DS3/E3 Configuration table."
        ::= { rbnDs3MIBObjects 1 }

rbnDsx3ConfigEntry    OBJECT-TYPE
        SYNTAX       RbnDsx3ConfigEntry
        MAX-ACCESS   not-accessible
        STATUS       current
        DESCRIPTION
                "An entry in the DS3/E3 Configuration table."
        AUGMENTS { dsx3ConfigEntry }
        ::= { rbnDsx3ConfigTable 1 }

RbnDsx3ConfigEntry ::=
        SEQUENCE {
                rbnDsx3AlarmSeverity           RbnAlarmPerceivedSeverity,
                rbnDsx3AlarmServiceAffecting   RbnAlarmServiceAffecting
        }

rbnDsx3AlarmSeverity OBJECT-TYPE
        SYNTAX      RbnAlarmPerceivedSeverity
        MAX-ACCESS  read-only
        STATUS      current
        DESCRIPTION
                "The perceived severity of the interface alarm."
        ::= { rbnDsx3ConfigEntry 1 }


rbnDsx3AlarmServiceAffecting OBJECT-TYPE
        SYNTAX      RbnAlarmServiceAffecting
        MAX-ACCESS  read-only
        STATUS      current
        DESCRIPTION
                "Indicates whether the interface alarm is
                service affecting."
        ::= { rbnDsx3ConfigEntry 2 }


-- Conformance Information

rbnDs3MIBConformance OBJECT IDENTIFIER ::=
        { rbnDS3MIB 2 }

rbnDs3MIBGroups OBJECT IDENTIFIER ::=
        { rbnDs3MIBConformance 1 }

rbnDs3MIBCompliances OBJECT IDENTIFIER ::=
        { rbnDs3MIBConformance 2 }


-- Compliance Statements

rbnDs3MIBCompliance MODULE-COMPLIANCE
        STATUS      current
        DESCRIPTION
                "The compliance statement for using this MIB for
                all DS3/E3 interfaces."
        MODULE      -- this module
        MANDATORY-GROUPS {
                rbnDs3Group
                }
        ::= { rbnDs3MIBCompliances 1 }

-- Units of Conformance

rbnDs3Group OBJECT-GROUP
        OBJECTS {
                rbnDsx3AlarmSeverity,
                rbnDsx3AlarmServiceAffecting
        }
        STATUS      current
        DESCRIPTION
                "A collection of objects providing supplemental
                configuration information applicable to all DS3/E3
                interfaces."
        ::= { rbnDs3MIBGroups 1 }

END

-- *****************************************************************
-- *****************************************************************
-- RBN-EPSC-MIB Evolved Packet System Control (EPSC) MIB
--
-- Copyright (c) 2008 RedBack Networks, Inc.
-- All rights reserved.
-- 
-- *****************************************************************

RBN-EPSC-MIB DEFINITIONS ::= BEGIN

IMPORTS
    OBJECT-TYPE, MODULE-IDENTITY, Counter64, Gauge32
        FROM SNMPv2-SMI
    MODULE-COMPLIANCE, OBJECT-GROUP
        FROM SNMPv2-CONF
    rbnMgmt
        FROM RBN-SMI;

rbnEpscMIB MODULE-IDENTITY
    LAST-UPDATED   "201105111456Z"
        ORGANIZATION    "RedBack Networks, Inc."
    CONTACT-INFO
                "       RedBack Networks, Inc.
       
                Postal: 300 Holger Way
                    San Jose, CA  95134
                    USA

             Phone: +1 408 750 5000
               Fax: +1 408 750 5599

                E-mail: mib-info@redback.com"
    DESCRIPTION 
            "The RBN-EPSC-MIB is mainly used to monitor 
            the Evolved Packet System Control."

    REVISION       "201105111456Z"
    DESCRIPTION 
            "Added counters for ICR"

    REVISION       "201105021409Z"
    DESCRIPTION 
            "Added counters for S2a"

    REVISION       "201103111203Z"
    DESCRIPTION 
            "Added a counter for S2a"

     REVISION       "201102011204Z"
    DESCRIPTION 
            "Corrected a s2a counter name"
 
    REVISION       "201101261500Z"
    DESCRIPTION 
            "Added S2a."
    REVISION       "201101261322Z"
    DESCRIPTION 
	    "Added S6b."

    REVISION       "201012161100Z"
    DESCRIPTION 
            "Added Gy."
    REVISION       "201003111535Z"
    DESCRIPTION 
            "Initial version."

    ::= { rbnMgmt 44 }


-- Textual Conventions
-- In case Notification objects are specified, it should have the 0 
-- OID within rbnEpscMIB (i.e. "::= { rbnEpscMIB 0 }") in order to
-- conform with RFC4181.

rbnEpscMIBObjects OBJECT IDENTIFIER
    ::= { rbnEpscMIB 1 }
rbnEpscMIBConformance OBJECT IDENTIFIER
    ::= { rbnEpscMIB 2 }

rbnEpscMIBGroups OBJECT IDENTIFIER
    ::= { rbnEpscMIBConformance 1 }

rbnEpscMIBCompliances OBJECT IDENTIFIER
    ::= { rbnEpscMIBConformance 2 }

--
-- Common statistics object grouping
--
rbnEpscCommonStats OBJECT IDENTIFIER
    ::= { rbnEpscMIBObjects 1 }
rbnEpscCommonGeneral OBJECT IDENTIFIER
    ::= { rbnEpscCommonStats 1 }
rbnEpscCommonCharging OBJECT IDENTIFIER
    ::= { rbnEpscCommonStats 2 } 
rbnEpscCommonDiameter OBJECT IDENTIFIER
    ::= { rbnEpscCommonStats 3 }
rbnEpscCommonIcr OBJECT IDENTIFIER
    ::= { rbnEpscCommonStats 4 }

--
-- SGW statistics object grouping
--
rbnEpscSgwStats OBJECT IDENTIFIER
    ::= { rbnEpscMIBObjects 2 }
rbnEpscSgwGeneral OBJECT IDENTIFIER
    ::= { rbnEpscSgwStats 1 }
--
-- OBJECT IDENTIFIER ::= { rbnEpscSgwStats 2 } is reserved for future use
--
rbnEpscSgwS5S8Gtp OBJECT IDENTIFIER
    ::= { rbnEpscSgwStats 3 }
rbnEpscSgwS11S4 OBJECT IDENTIFIER
    ::= { rbnEpscSgwStats 4 }
rbnEpscSgwCharging OBJECT IDENTIFIER
    ::= { rbnEpscSgwStats 5 }

--
-- PGW statistics object grouping
--
rbnEpscPgwStats OBJECT IDENTIFIER
    ::= { rbnEpscMIBObjects 3 }
rbnEpscPgwGeneral OBJECT IDENTIFIER
    ::= { rbnEpscPgwStats 1 }
rbnEpscPgwGx OBJECT IDENTIFIER
    ::= { rbnEpscPgwStats 2 }
rbnEpscPgwCharging OBJECT IDENTIFIER
    ::= { rbnEpscPgwStats 3 }
rbnEpscPgwGnGp OBJECT IDENTIFIER
    ::= { rbnEpscPgwStats 4 }
rbnEpscPgwS5S8Gtp OBJECT IDENTIFIER
    ::= { rbnEpscPgwStats 5 }
rbnEpscPgwGy OBJECT IDENTIFIER
    ::= { rbnEpscPgwStats 6 }
rbnEpscPgwS2aPmip OBJECT IDENTIFIER
    ::= { rbnEpscPgwStats 7 }
rbnEpscPgwS6b OBJECT IDENTIFIER
    ::= { rbnEpscPgwStats 8 }

--
-- rbnEpscCommonGeneral counters/gauges
--
rbnEpscConnectionsEstablished OBJECT-TYPE
    SYNTAX     Gauge32
    MAX-ACCESS read-only
    STATUS     current
    DESCRIPTION 
        "Current number of established Connections on this Gateway."
    ::= { rbnEpscCommonGeneral 1 }

rbnEpscPdnConnectionTimeout OBJECT-TYPE
    SYNTAX     Counter64
    MAX-ACCESS read-only
    STATUS     current
    DESCRIPTION 
        "This counter is updated when no valid Modify Bearer Request 
        message is received before the activation timeout has expired."
    ::= { rbnEpscCommonGeneral 2 }

rbnEpscBearersEstablished OBJECT-TYPE
    SYNTAX     Gauge32
    MAX-ACCESS read-only
    STATUS     current
    DESCRIPTION 
        "Current number of established EPS Bearers and PDP Contexts 
        on this Gateway."
    ::= { rbnEpscCommonGeneral 3 }

rbnEpscUeAttached  OBJECT-TYPE
    SYNTAX     Gauge32
    MAX-ACCESS read-only
    STATUS     current
    DESCRIPTION 
        "Current number of User Equipment (UE) attached to the gateway."
    ::= { rbnEpscCommonGeneral 4 }

--
-- rbnEpscCommonCharging counters/gauges
--
rbnEpscClosedCdrFiles OBJECT-TYPE
    SYNTAX     Counter64
    MAX-ACCESS read-only
    STATUS     current
    DESCRIPTION 
        "Total number of closed CDR files."
    ::= { rbnEpscCommonCharging 1 }

rbnEpscRfAcrSent OBJECT-TYPE
    SYNTAX     Counter64
    MAX-ACCESS read-only
    STATUS     current
    DESCRIPTION 
        "Total number of Accounting-Request messages sent over 
        the Rf interface."
    ::= { rbnEpscCommonCharging 2 }

rbnEpscRfAcaSuccRcvd OBJECT-TYPE
    SYNTAX     Counter64
    MAX-ACCESS read-only
    STATUS     current
    DESCRIPTION 
        "Total number of Accounting-Answer messages received over 
        the Rf interface with result code diameter success."
    ::= { rbnEpscCommonCharging 3 }

rbnEpscRfAcaFailRcvd OBJECT-TYPE
    SYNTAX     Counter64
    MAX-ACCESS read-only
    STATUS     current
    DESCRIPTION 
        "Total number of Accounting-Answer messages recieved over 
        the Rf interface with result code different from diameter 
        success or if syntax errors in message."
    ::= { rbnEpscCommonCharging 4 }

rbnEpscRfAcrWrittenToDisk OBJECT-TYPE
    SYNTAX     Counter64
    MAX-ACCESS read-only
    STATUS     current
    DESCRIPTION 
        "Total number of Accounting-Request messages written to
        file on disk."
    ::= { rbnEpscCommonCharging 5 }

--
-- rbnEpscCommonDiameter counters/gauges
--

rbnEpscDiameterMsgInvalidRcvd OBJECT-TYPE
    SYNTAX     Counter64
    MAX-ACCESS read-only
    STATUS     current
    DESCRIPTION 
        "Total number of Diameter messages received from a Diameter 
	peer that either cannot be correctly interpreted or the 
	messages do not include all Mandatory AVPs."
    ::= { rbnEpscCommonDiameter 1 }

--
-- rbnEpscCommonIcr counters/gauges
--

rbnEpscIcrCreateSessionSyncRcvd OBJECT-TYPE
    SYNTAX     Counter64
    MAX-ACCESS read-only
    STATUS     current
    DESCRIPTION
	"Total number of <eps-c create session sync> messages received 
	from the active ICR peer.  The <eps-c create session sync> messages 
	are sent to the standby ICR peer when a UE session is created or 
	modified on the active ICR peer."
    ::= { rbnEpscCommonIcr 1 }

rbnEpscIcrCreateSessionSyncSent OBJECT-TYPE
    SYNTAX     Counter64
    MAX-ACCESS read-only
    STATUS     current
    DESCRIPTION 
        "Total number of <eps-c create session sync> messages sent to 
	the standby ICR peer.  The <eps-c create session sync> messages 
	are sent to the standby ICR peer when a UE session is created or 
	modified on the active ICR peer."
    ::= { rbnEpscCommonIcr 2 }

rbnEpscIcrDeleteSessionSyncRcvd OBJECT-TYPE
    SYNTAX     Counter64
    MAX-ACCESS read-only
    STATUS     current
    DESCRIPTION 
	"Total number of <eps-c delete session sync> messages received 
	from the active ICR peer. The <eps-c delete session sync> messages 
	are sent to the standby ICR peer when a UE session is deleted on 
	the active ICR peer."
    ::= { rbnEpscCommonIcr 3 }

rbnEpscIcrDeleteSessionSyncSent OBJECT-TYPE
    SYNTAX     Counter64
    MAX-ACCESS read-only
    STATUS     current
    DESCRIPTION 
	"Total number of <eps-c delete session sync> messages sent to the 
	standby ICR peer. The <eps-c delete session sync> messages are sent 
	to the standby ICR peer when a UE session is deleted on the active 
	ICR peer."
    ::= { rbnEpscCommonIcr 4 }

--
-- rbnEpscSgwGeneral counters/gauges
--
rbnEpscSgwUeEcmConnected  OBJECT-TYPE
    SYNTAX     Gauge32
    MAX-ACCESS read-only
    STATUS     current
    DESCRIPTION 
        "Current number of User Equipment (UE) in EPS Connection Management 
        state ECM-CONNECTED in the gateway."
    ::= { rbnEpscSgwGeneral 2 }

--
-- rbnEpscSgwS5S8 counters/gauges
--
rbnEpscS5S8CreateSessionReqSent  OBJECT-TYPE
    SYNTAX     Counter64
    MAX-ACCESS read-only
    STATUS     current
    DESCRIPTION 
        "Total number of GTPv2-C Create Session Request messages sent by
        the SGW over the S5/S8 SGW GTP-C interface."
    ::= { rbnEpscSgwS5S8Gtp 1 }

rbnEpscS5S8CreateSessionRespAccRcvd  OBJECT-TYPE
    SYNTAX     Counter64
    MAX-ACCESS read-only
    STATUS     current
    DESCRIPTION 
        "Total number of GTPv2-C Create Session Response messages with 
        acceptance response cause values received by the SGW over the 
        S5/S8 SGW GTP-C interface."
    ::= { rbnEpscSgwS5S8Gtp 2 }

rbnEpscS5S8CreateSessionRespRejRcvd  OBJECT-TYPE
    SYNTAX     Counter64
    MAX-ACCESS read-only
    STATUS     current
    DESCRIPTION 
        "Total number of GTPv2-C Create Session Response messages with
        rejection response cause values received by the SGW over the 
        S5/S8 SGW GTP-C interface."
    ::= { rbnEpscSgwS5S8Gtp 3 }

rbnEpscS5S8DeleteSessionReqSent  OBJECT-TYPE
    SYNTAX     Counter64
    MAX-ACCESS read-only
    STATUS     current
    DESCRIPTION 
        "Total number of GTPv2-C Delete Session Request messages sent 
        by the SGW over the S5/S8 SGW GTP-C interface."
    ::= { rbnEpscSgwS5S8Gtp 4 }

rbnEpscS5S8DeleteSessionRespAccRcvd  OBJECT-TYPE
    SYNTAX     Counter64
    MAX-ACCESS read-only
    STATUS     current
    DESCRIPTION 
        "Total number of GTPv2-C Delete Session Response messages with 
        acceptance cause values received by the SGW over the 
        S5/S8 SGW GTP-C interface."
    ::= { rbnEpscSgwS5S8Gtp 5 }

rbnEpscS5S8DeleteSessionRespRejRcvd  OBJECT-TYPE
    SYNTAX     Counter64
    MAX-ACCESS read-only
    STATUS     current
    DESCRIPTION 
        "Total number of GTPv2-C Delete Session Response messages with 
        rejection response cause values received by the SGW over the 
        S5/S8 SGW GTP-C interface."
    ::= { rbnEpscSgwS5S8Gtp 6 }

rbnEpscS5S8DeleteBearerReqRcvd  OBJECT-TYPE
    SYNTAX     Counter64
    MAX-ACCESS read-only
    STATUS     current
    DESCRIPTION 
        "Total number of GTPv2-C Delete Bearer Request messages received
        by the SGW over the S5/S8 SGW GTP-C interface."
    ::= { rbnEpscSgwS5S8Gtp 7 }

rbnEpscS5S8DeleteBearerRespAccSent  OBJECT-TYPE
    SYNTAX     Counter64
    MAX-ACCESS read-only
    STATUS     current
    DESCRIPTION 
        "Total number of GTPv2-C Delete Bearer Response messages with 
        acceptance response cause values sent by the SGW over the 
        S5/S8 SGW GTP-C interface."
    ::= { rbnEpscSgwS5S8Gtp 8 }

rbnEpscS5S8DeleteBearerRespRejSent  OBJECT-TYPE
    SYNTAX     Counter64
    MAX-ACCESS read-only
    STATUS     current
    DESCRIPTION 
        "Total number of GTPv2-C Delete Bearer Response messages with 
        rejection response cause values sent by the SGW over the 
        S5/S8 SGW GTP-C interface."
    ::= { rbnEpscSgwS5S8Gtp 9 }

rbnEpscS5S8CreateBearerReqRcvd  OBJECT-TYPE
    SYNTAX     Counter64
    MAX-ACCESS read-only
    STATUS     current
    DESCRIPTION 
        "Total number of GTPv2-C Create Bearer Request messages received 
        by the SGW over the S5/S8 SGW GTP-C interface."
    ::= { rbnEpscSgwS5S8Gtp 10 }

rbnEpscS5S8CreateBearerRespAccSent  OBJECT-TYPE
    SYNTAX     Counter64
    MAX-ACCESS read-only
    STATUS     current
    DESCRIPTION 
        "Total number of GTPv2-C Create Bearer Response messages with 
        acceptance response cause values sent by the SGW over the 
        S5/S8 SGW GTP-C interface."
    ::= { rbnEpscSgwS5S8Gtp 11 }

rbnEpscS5S8CreateBearerRespRejSent  OBJECT-TYPE
    SYNTAX     Counter64
    MAX-ACCESS read-only
    STATUS     current
    DESCRIPTION 
        "Total number of GTPv2-C Create Bearer Response messages with 
        rejection response cause values sent by the SGW over the 
        S5/S8 SGW GTP-C interface."
    ::= { rbnEpscSgwS5S8Gtp 12 }

rbnEpscS5S8DeleteBearerCmdSent  OBJECT-TYPE
    SYNTAX     Counter64
    MAX-ACCESS read-only
    STATUS     current
    DESCRIPTION 
        "Total number of GTPv2-C Delete Bearer Command messages sent
        by the SGW over the S5/S8 SGW GTP-C interface."
    ::= { rbnEpscSgwS5S8Gtp 13 }

rbnEpscS5S8DeleteBearerFailureIndRcvd  OBJECT-TYPE
    SYNTAX     Counter64
    MAX-ACCESS read-only
    STATUS     current
    DESCRIPTION 
        "Total number of GTPv2-C Delete Bearer Failure Indication messages
        received by the SGW over the S5/S8 SGW GTP-C interface."
    ::= { rbnEpscSgwS5S8Gtp 14 }

rbnEpscS5S8UpdateBearerReqRcvd  OBJECT-TYPE
    SYNTAX     Counter64
    MAX-ACCESS read-only
    STATUS     current
    DESCRIPTION 
        "Total number of GTPv2-C Update Bearer Request messages received
        by the SGW over the S5/S8 SGW GTP-C interface."
    ::= { rbnEpscSgwS5S8Gtp 15 }

rbnEpscS5S8UpdateBearerRespAccSent  OBJECT-TYPE
    SYNTAX     Counter64
    MAX-ACCESS read-only
    STATUS     current
    DESCRIPTION 
        "Total number of GTPv2-C Update Bearer Response messages with 
        acceptance response cause values sent by the SGW over the 
        S5/S8 SGW GTP-C interface."
    ::= { rbnEpscSgwS5S8Gtp 16 }

rbnEpscS5S8UpdateBearerRespRejSent  OBJECT-TYPE
    SYNTAX     Counter64
    MAX-ACCESS read-only
    STATUS     current
    DESCRIPTION 
        "Total number of GTPv2-C Update Bearer Response messages with 
        rejection response cause values sent by the SGW over the 
        S5/S8 SGW GTP-C interface."
    ::= { rbnEpscSgwS5S8Gtp 17 }

rbnEpscS5S8ModifyBearerReqSent  OBJECT-TYPE
    SYNTAX     Counter64
    MAX-ACCESS read-only
    STATUS     current
    DESCRIPTION 
        "Total number of GTPv2-C Modify Bearer Request messages sent by
        the SGW over the S5/S8 SGW GTP-C interface."
    ::= { rbnEpscSgwS5S8Gtp 18 }

rbnEpscS5S8ModifyBearerRespAccRcvd  OBJECT-TYPE
    SYNTAX     Counter64
    MAX-ACCESS read-only
    STATUS     current
    DESCRIPTION 
        "Total number of GTPv2-C Modify Bearer Response messages with
        acceptance response cause values received by the SGW over the
        S5/S8 SGW GTP-C interface."
    ::= { rbnEpscSgwS5S8Gtp 19 }

rbnEpscS5S8ModifyBearerRespRejRcvd  OBJECT-TYPE
    SYNTAX     Counter64
    MAX-ACCESS read-only
    STATUS     current
    DESCRIPTION 
        "Total number of GTPv2-C Modify Bearer Response messages with
        rejection response cause values received by the SGW over the
        S5/S8 SGW GTP-C interface."
    ::= { rbnEpscSgwS5S8Gtp 20 }


--
-- rbnEpscSgwS11S4 counters/gauges
--
rbnEpscS11S4CreateSessionReqRcvd OBJECT-TYPE
    SYNTAX     Counter64
    MAX-ACCESS read-only
    STATUS     current
    DESCRIPTION 
        "Total number of GTPv2-C Create Session Request messages received 
        over the S11/S4 interface."
    ::= { rbnEpscSgwS11S4 1 }

rbnEpscS11S4CreateSessionRespAccSent OBJECT-TYPE
    SYNTAX     Counter64
    MAX-ACCESS read-only
    STATUS     current
    DESCRIPTION 
        "Total number of GTPv2-C Create Session Response messages with 
        acceptance response cause values sent over the S11/S4 interface."
    ::= { rbnEpscSgwS11S4 2 }

rbnEpscS11S4CreateSessionRespRejSent OBJECT-TYPE
    SYNTAX     Counter64
    MAX-ACCESS read-only
    STATUS     current
    DESCRIPTION 
        "Total number of GTPv2-C Create Session Response messages with 
        rejection response cause values sent over the S11/S4 interface."
    ::= { rbnEpscSgwS11S4 3 }

rbnEpscS11S4ModifyBearerReqRcvd OBJECT-TYPE
    SYNTAX     Counter64
    MAX-ACCESS read-only
    STATUS     current
    DESCRIPTION 
        "Total number of GTPv2-C Modify Bearer Request messages received 
        over the S11/S4 interface."
    ::= { rbnEpscSgwS11S4 4 }

rbnEpscS11S4ModifyBearerRespAccSent OBJECT-TYPE
    SYNTAX     Counter64
    MAX-ACCESS read-only
    STATUS     current
    DESCRIPTION 
        "Total number of GTPv2-C Modify Bearer Request messages with 
        acceptance response cause values sent over the S11/S4 interface."
    ::= { rbnEpscSgwS11S4 5 }

rbnEpscS11S4ModifyBearerRespRejSent OBJECT-TYPE
    SYNTAX     Counter64
    MAX-ACCESS read-only
    STATUS     current
    DESCRIPTION 
        "Total number of GTPv2-C Modify Bearer Request messages with 
        rejection response cause values sent over the S11/S4 interface."
    ::= { rbnEpscSgwS11S4 6 }

rbnEpscS11S4DeleteSessionReqRcvd OBJECT-TYPE
    SYNTAX     Counter64
    MAX-ACCESS read-only
    STATUS     current
    DESCRIPTION 
        "Total number of GTPv2-C Delete Session Request messages 
        received over the S11/S4 interface."
    ::= { rbnEpscSgwS11S4 7 }

rbnEpscS11S4DeleteSessionRespAccSent OBJECT-TYPE
    SYNTAX     Counter64
    MAX-ACCESS read-only
    STATUS     current
    DESCRIPTION 
        "Total number of GTPv2-C Delete Session Response messages with 
        acceptance response cause values sent over the S11/S4 interface."
    ::= { rbnEpscSgwS11S4 8 }

rbnEpscS11S4DeleteSessionRespRejSent OBJECT-TYPE
    SYNTAX     Counter64
    MAX-ACCESS read-only
    STATUS     current
    DESCRIPTION 
        "Total number of GTPv2-C Delete Session Response messages with
        rejection response cause values sent over the S11/S4 interface."
    ::= { rbnEpscSgwS11S4 9 }

rbnEpscS11S4DlDataNotificationSent OBJECT-TYPE
    SYNTAX     Counter64
    MAX-ACCESS read-only
    STATUS     current
    DESCRIPTION 
        "Total number of GTPv2-C Downlink Data Notification messages 
        sent over the S11/S4 interface."
    ::= { rbnEpscSgwS11S4 10 }

rbnEpscS11S4DlDataNotificationAckRcvd OBJECT-TYPE
    SYNTAX     Counter64
    MAX-ACCESS read-only
    STATUS     current
    DESCRIPTION 
        "Total number of GTPv2-C Downlink Data Notification Acknowledgement
        messages received over the S11/S4 interface."
    ::= { rbnEpscSgwS11S4 11 }

rbnEpscS11S4DlDataNotifFailureIndRcvd OBJECT-TYPE
    SYNTAX     Counter64
    MAX-ACCESS read-only
    STATUS     current
    DESCRIPTION 
        "Total number of GTPv2-C Downlink Data Notification Failure Indication
        messages received over the S11/S4 interface. "
    ::= { rbnEpscSgwS11S4 12 }

rbnEpscS11S4DeleteBearerReqSent  OBJECT-TYPE
    SYNTAX     Counter64
    MAX-ACCESS read-only
    STATUS     current
    DESCRIPTION 
        "Total number of GTPv2-C Delete Bearer Request messages 
        sent over the S11/S4 interface."
    ::= { rbnEpscSgwS11S4 13 }

rbnEpscS11S4DeleteBearerRespAccRcvd  OBJECT-TYPE
    SYNTAX     Counter64
    MAX-ACCESS read-only
    STATUS     current
    DESCRIPTION 
        "Total number of GTPv2-C Delete Bearer Response messages with 
        acceptance response cause values received over the S11/S4 interface."
    ::= { rbnEpscSgwS11S4 14 }

rbnEpscS11S4DeleteBearerRespRejRcvd  OBJECT-TYPE
    SYNTAX     Counter64
    MAX-ACCESS read-only
    STATUS     current
    DESCRIPTION 
        "Total number of GTPv2-C Delete Bearer Response messages with
        rejection response cause values received over the S11/S4 interface."
    ::= { rbnEpscSgwS11S4 15 }

rbnEpscS11S4RelAccessBearersReqRcvd OBJECT-TYPE
    SYNTAX     Counter64
    MAX-ACCESS read-only
    STATUS     current
    DESCRIPTION 
        "Total number of GTPv2-C Release Access Bearers Request messages 
        received over the S11/S4 interface."
    ::= { rbnEpscSgwS11S4 16 }

rbnEpscS11S4RelAccessBearersRespAccSent OBJECT-TYPE
    SYNTAX     Counter64
    MAX-ACCESS read-only
    STATUS     current
    DESCRIPTION 
        "Total number of GTPv2-C Release Access Bearers Response messages
        with acceptance response cause values sent over the S11/S4 interface."
    ::= { rbnEpscSgwS11S4 17 }

rbnEpscS11S4RelAccessBearersRespRejSent OBJECT-TYPE
    SYNTAX     Counter64
    MAX-ACCESS read-only
    STATUS     current
    DESCRIPTION 
        "Total number of GTPv2-C Release Access Bearers Response messages
        with rejection response cause values sent over the S11S4 interface."
    ::= { rbnEpscSgwS11S4 18 }

rbnEpscS11S4CreateBearerReqSent  OBJECT-TYPE
    SYNTAX     Counter64
    MAX-ACCESS read-only
    STATUS     current
    DESCRIPTION 
        "Total number of GTPv2-C Create Bearer Request messages 
        sent over the S11/S4 interface."
    ::= { rbnEpscSgwS11S4 19 }

rbnEpscS11S4CreateBearerRespAccRcvd  OBJECT-TYPE
    SYNTAX     Counter64
    MAX-ACCESS read-only
    STATUS     current
    DESCRIPTION 
        "Total number of GTPv2-C Create Bearer Response messages with 
        acceptance response cause values received over the S11/S4 interface."
    ::= { rbnEpscSgwS11S4 20 }

rbnEpscS11S4CreateBearerRespRejRcvd  OBJECT-TYPE
    SYNTAX     Counter64
    MAX-ACCESS read-only
    STATUS     current
    DESCRIPTION 
        "Total number of GTPv2-C Create Bearer Response messages with
        rejection response cause values received over the S11/S4 interface."
    ::= { rbnEpscSgwS11S4 21 }

rbnEpscS11S4DeleteBearerCmdRcvd OBJECT-TYPE
    SYNTAX     Counter64
    MAX-ACCESS read-only
    STATUS     current
    DESCRIPTION 
        "Total number of GTPv2-C Delete Bearer Command messages received
        over the S11/S4 interface."
    ::= { rbnEpscSgwS11S4 22 }

rbnEpscS11S4DeleteBearerFailureIndSent OBJECT-TYPE
    SYNTAX     Counter64
    MAX-ACCESS read-only
    STATUS     current
    DESCRIPTION 
        "Total number of GTPv2-C Delete Bearer Failure Indication messages
        sent over the S11/S4 interface. "
    ::= { rbnEpscSgwS11S4 23 }

rbnEpscS11S4UpdateBearerReqSent  OBJECT-TYPE
    SYNTAX     Counter64
    MAX-ACCESS read-only
    STATUS     current
    DESCRIPTION 
        "Total number of GTPv2-C Update Bearer Request messages 
        sent over the S11/S4 interface."
    ::= { rbnEpscSgwS11S4 24 }

rbnEpscS11S4UpdateBearerRespAccRcvd  OBJECT-TYPE
    SYNTAX     Counter64
    MAX-ACCESS read-only
    STATUS     current
    DESCRIPTION 
        "Total number of GTPv2-C Update Bearer Response messages with 
        acceptance response cause values received over the S11/S4 interface."
    ::= { rbnEpscSgwS11S4 25 }

rbnEpscS11S4UpdateBearerRespRejRcvd  OBJECT-TYPE
    SYNTAX     Counter64
    MAX-ACCESS read-only
    STATUS     current
    DESCRIPTION 
        "Total number of GTPv2-C Update Bearer Response messages with
        rejection response cause values received over the S11/S4 interface."
    ::= { rbnEpscSgwS11S4 26 }

--
-- rbnEpscSgwCharging counters/gauges
--
rbnEpscSgwCdrsEncoded OBJECT-TYPE
    SYNTAX     Counter64
    MAX-ACCESS read-only
    STATUS     current
    DESCRIPTION 
        "Total number of ASN.1/BER encoded SGW-CDRs."
    ::= { rbnEpscSgwCharging 1 }

--
-- rbnEpscPgwCharging counters/gauges
--
rbnEpscPgwCdrsEncoded OBJECT-TYPE
    SYNTAX     Counter64
    MAX-ACCESS read-only
    STATUS     current
    DESCRIPTION 
        "Total number of ASN.1/BER encoded PGW-CDRs."
    ::= { rbnEpscPgwCharging 1 }

--
-- rbnEpscPgwGy counters/gauges
--
rbnEpscGyCcrInitialSent OBJECT-TYPE
    SYNTAX     Counter64
    MAX-ACCESS read-only
    STATUS     current
    DESCRIPTION 
        "Total number of Credit-Control Request initial messages sent
        over the Gy interface."
    ::= { rbnEpscPgwGy 1 }

rbnEpscGyCcaInitialSuccRcvd OBJECT-TYPE
    SYNTAX     Counter64
    MAX-ACCESS read-only
    STATUS     current
    DESCRIPTION 
        "Total number of Credit-Control Answer initial messages with 
        result code diameter success received over the Gy interface."
    ::= { rbnEpscPgwGy 2 }

rbnEpscGyCcrTerminateSent OBJECT-TYPE
    SYNTAX     Counter64
    MAX-ACCESS read-only
    STATUS     current
    DESCRIPTION 
        "Total number of Credit-Control Request terminate messages sent
        over the Gy interface."
    ::= { rbnEpscPgwGy 3 }

rbnEpscGyCcaTerminateSuccRcvd OBJECT-TYPE
    SYNTAX     Counter64
    MAX-ACCESS read-only
    STATUS     current
    DESCRIPTION 
        "Total number of Credit-Control Answer terminate messages with 
        result code diameter success received over the Gy interface."
    ::= { rbnEpscPgwGy 4 }

rbnEpscGyCcaInitialFailRcvd OBJECT-TYPE
    SYNTAX     Counter64
    MAX-ACCESS read-only
    STATUS     current
    DESCRIPTION 
        "Total number of Credit-Control Answer initial messages with
        result code diameter failure received over the Gy interface."
    ::= { rbnEpscPgwGy 5 }

rbnEpscGyCcaTerminateFailRcvd OBJECT-TYPE
    SYNTAX     Counter64
    MAX-ACCESS read-only
    STATUS     current
    DESCRIPTION 
        "Total number of Credit-Control Answer terminate messages with 
        result code diameter failure received over the Gy interface."
    ::= { rbnEpscPgwGy 6 }

--
-- rbnEpscPgwGx counters/gauges
--
rbnEpscGxCcrInitialSent OBJECT-TYPE
    SYNTAX     Counter64
    MAX-ACCESS read-only
    STATUS     current
    DESCRIPTION 
        "Total number of Credit-Control Request initial messages sent
        over the Gx interface."
    ::= { rbnEpscPgwGx 1 }

rbnEpscGxCcaInitialSuccRcvd OBJECT-TYPE
    SYNTAX     Counter64
    MAX-ACCESS read-only
    STATUS     current
    DESCRIPTION 
        "Total number of Credit-Control Answer initial messages with 
        result code diameter success received over the Gx interface."
    ::= { rbnEpscPgwGx 2 }

rbnEpscGxCcaInitialFailRcvd OBJECT-TYPE
    SYNTAX     Counter64
    MAX-ACCESS read-only
    STATUS     current
    DESCRIPTION 
        "Total number of Credit-Control Answer initial messages with
        result code diameter failure received over the Gx interface."
    ::= { rbnEpscPgwGx 3 }

rbnEpscGxCcrUpdateSent OBJECT-TYPE
    SYNTAX     Counter64
    MAX-ACCESS read-only
    STATUS     current
    DESCRIPTION 
        "Total number of Credit-Control Request update messages sent over
        the Gx interface."
    ::= { rbnEpscPgwGx 4 }

rbnEpscGxCcaUpdateSuccRcvd OBJECT-TYPE
    SYNTAX     Counter64
    MAX-ACCESS read-only
    STATUS     current
    DESCRIPTION 
        "Total number of Credit-Control Answer update messages with 
        result code diameter success received over the Gx interface."
    ::= { rbnEpscPgwGx 5 }

rbnEpscGxCcaUpdateFailRcvd OBJECT-TYPE
    SYNTAX     Counter64
    MAX-ACCESS read-only
    STATUS     current
    DESCRIPTION 
        "Total number of Credit-Control Answer update messages with 
        result code diameter failure received over the Gx interface."
    ::= { rbnEpscPgwGx 6 }

rbnEpscGxCcrTerminateSent OBJECT-TYPE
    SYNTAX     Counter64
    MAX-ACCESS read-only
    STATUS     current
    DESCRIPTION 
        "Total number of Credit-Control Request terminate messages sent
        over the Gx interface."
    ::= { rbnEpscPgwGx 7 }

rbnEpscGxCcaTerminateSuccRcvd OBJECT-TYPE
    SYNTAX     Counter64
    MAX-ACCESS read-only
    STATUS     current
    DESCRIPTION 
        "Total number of Credit-Control Answer terminate messages with 
        result code diameter success received over the Gx interface."
    ::= { rbnEpscPgwGx 8 }

rbnEpscGxCcaTerminateFailRcvd OBJECT-TYPE
    SYNTAX     Counter64
    MAX-ACCESS read-only
    STATUS     current
    DESCRIPTION 
        "Total number of Credit-Control Answer terminate messages with 
        result code diameter failure received over the Gx interface."
    ::= { rbnEpscPgwGx 9 }

rbnEpscGxRarRcvd OBJECT-TYPE
    SYNTAX     Counter64
    MAX-ACCESS read-only
    STATUS     current
    DESCRIPTION 
        "Total number of Re-Auth Request messages received over
        the Gx interface."
    ::= { rbnEpscPgwGx 10 }

rbnEpscGxRaaSuccSent OBJECT-TYPE
    SYNTAX     Counter64
    MAX-ACCESS read-only
    STATUS     current
    DESCRIPTION 
        "Total number of Re-Auth Answer messages with result code 
        diameter success sent over the Gx interface."
    ::= { rbnEpscPgwGx 11 }

rbnEpscGxRaaFailSent OBJECT-TYPE
    SYNTAX     Counter64
    MAX-ACCESS read-only
    STATUS     current
    DESCRIPTION 
        "Total number of Re-Auth Answer messages with result code
        diameter failure sent over the Gx interface."
    ::= { rbnEpscPgwGx 12 }

--
-- rbnEpscPgwGnGp counters/gauges
--
rbnEpscGnGpDeletePdpCtxReqRcvd OBJECT-TYPE
    SYNTAX     Counter64
    MAX-ACCESS read-only
    STATUS     current
    DESCRIPTION 
        "Total number of GTPv1-C Delete PDP Context Request messages received
        over the Gn/Gp interface from a Pre-Rel-8 SGSN."
    ::= { rbnEpscPgwGnGp 1 }

rbnEpscGnGpDeletePdpCtxRespAccSent OBJECT-TYPE
    SYNTAX     Counter64
    MAX-ACCESS read-only
    STATUS     current
    DESCRIPTION 
        "Total number of GTPv1-C Delete PDP Context Response messages with
        cause value Accepted sent over the Gn/Gp interface to a Pre-Rel-8 SGSN."
    ::= { rbnEpscPgwGnGp 2 }

rbnEpscGnGpUpdatePdpCtxReqRcvd OBJECT-TYPE
    SYNTAX     Counter64
    MAX-ACCESS read-only
    STATUS     current
    DESCRIPTION 
        "Total number of GTPv1-C Update PDP Context Request messages received
        over the Gn/Gp interface from a Pre-Rel-8 SGSN."
    ::= { rbnEpscPgwGnGp 3 }

rbnEpscGnGpUpdatePdpCtxRespAccSent OBJECT-TYPE
    SYNTAX     Counter64
    MAX-ACCESS read-only
    STATUS     current
    DESCRIPTION 
        "Total number of GTPv1-C Update PDP Context Response messages with
        cause value Accepted sent over the Gn/Gp interface to a Pre-Rel-8 SGSN."
    ::= { rbnEpscPgwGnGp 4 }

rbnEpscGnGpCreatePdpCtxReqRcvd OBJECT-TYPE
    SYNTAX     Counter64
    MAX-ACCESS read-only
    STATUS     current
    DESCRIPTION 
        "Total number of GTPv1-C Create PDP Context Request messages received 
        over the Gn/Gp interface from a Pre-Rel-8 SGSN."
    ::= { rbnEpscPgwGnGp 5 }

rbnEpscGnGpCreatePdpCtxRespAccSent OBJECT-TYPE
    SYNTAX     Counter64
    MAX-ACCESS read-only
    STATUS     current
    DESCRIPTION 
        "Total number of GTPv1-C Create PDP Context Response messages with 
        cause value Accepted sent over the Gn/Gp interface to a Pre-Rel-8 SGSN."
    ::= { rbnEpscPgwGnGp 6 }

rbnEpscGnGpUpdatePdpCtxRespRejSent OBJECT-TYPE
    SYNTAX     Counter64
    MAX-ACCESS read-only
    STATUS     current
    DESCRIPTION 
        "Total number of GTPv1-C Update PDP Context Response messages with
        cause value Rejected sent over the Gn/Gp interface to a Pre-Rel-8 SGSN."
    ::= { rbnEpscPgwGnGp 7 }

rbnEpscGnGpDeletePdpCtxRespRejSent OBJECT-TYPE
    SYNTAX     Counter64
    MAX-ACCESS read-only
    STATUS     current
    DESCRIPTION 
        "Total number of GTPv1-C Delete PDP Context Response messages with
        cause value Rejected sent over the Gn/Gp interface to a Pre-Rel-8 SGSN."
    ::= { rbnEpscPgwGnGp 8 }

rbnEpscGnGpCreatePdpCtxRespRejSent OBJECT-TYPE
    SYNTAX     Counter64
    MAX-ACCESS read-only
    STATUS     current
    DESCRIPTION 
        "Total number of GTPv1-C Create PDP Context Response messages with 
        cause value Rejected sent over the Gn/Gp interface to a Pre-Rel-8 SGSN."
    ::= { rbnEpscPgwGnGp 9 }

rbnEpscGnGpUpdatePdpCtxReqSent OBJECT-TYPE
    SYNTAX     Counter64
    MAX-ACCESS read-only
    STATUS     current
    DESCRIPTION 
        "Total number of GTPv1-C Update PDP Context Request messages sent
        over the Gn/Gp interface to a Gn/Gp-SGSN"
    ::= { rbnEpscPgwGnGp 10 }

rbnEpscGnGpUpdatePdpCtxRespAccRcvd OBJECT-TYPE
    SYNTAX     Counter64
    MAX-ACCESS read-only
    STATUS     current
    DESCRIPTION 
        "Total number of GTPv1-C Update PDP Context Response messages with
        acceptance response received over the Gn/Gp interface from a Gn/Gp-SGSN"
    ::= { rbnEpscPgwGnGp 11 }

rbnEpscGnGpUpdatePdpCtxRespRejRcvd OBJECT-TYPE
    SYNTAX     Counter64
    MAX-ACCESS read-only
    STATUS     current
    DESCRIPTION 
        "Total number of GTPv1-C Update PDP Context Response messages with
        rejection response received over the Gn/Gp interface from a Gn/Gp-SGSN"
    ::= { rbnEpscPgwGnGp 12 }

rbnEpscGnGpDeletePdpCtxReqSent OBJECT-TYPE
    SYNTAX     Counter64
    MAX-ACCESS read-only
    STATUS     current
    DESCRIPTION 
        "Total number of GTPv1-C Delete PDP Context Request messages sent over
        the Gn/Gp interface to a Gn/Gp-SGSN."
    ::= { rbnEpscPgwGnGp 13 }

rbnEpscGnGpDeletePdpCtxRespAccRcvd OBJECT-TYPE
    SYNTAX     Counter64
    MAX-ACCESS read-only
    STATUS     current
    DESCRIPTION 
        "Total number of GTPv1-C Delete PDP Context Response messages with
        acceptance cause values received over the Gn/Gp interface from a
        Gn/Gp-SGSN."
    ::= { rbnEpscPgwGnGp 14 }

rbnEpscGnGpDeletePdpCtxRespRejRcvd OBJECT-TYPE
    SYNTAX     Counter64
    MAX-ACCESS read-only
    STATUS     current
    DESCRIPTION 
        "Total number of GTPv1-C Delete PDP Context Response messages with
        rejection response received over the Gn/Gp interface from a Gn/Gp-SGSN."
    ::= { rbnEpscPgwGnGp 15 }

--
-- rbnEpscPgwS2a counters/gauges
--

rbnEpscS2aPmipMsgInvalidRcvd  OBJECT-TYPE
    SYNTAX     Counter64
    MAX-ACCESS read-only
    STATUS     current
    DESCRIPTION 
        "Total number of invalid messages received by the PGW 
	over the S2a interface."
    ::= { rbnEpscPgwS2aPmip 1 }

rbnEpscS2aPbuPdnConnCreateRcvd     OBJECT-TYPE
    SYNTAX     Counter64
    MAX-ACCESS read-only
    STATUS     current
    DESCRIPTION 
        "Total number of PMIP <PDN Connection Creation> PBU messages 
	received by the PGW over the S2a interface."
    ::= { rbnEpscPgwS2aPmip 2 }

rbnEpscS2aPbaPdnConnCreateAccSent             OBJECT-TYPE
    SYNTAX     Counter64
    MAX-ACCESS read-only
    STATUS     current
    DESCRIPTION 
        "Total number of PMIP <PDN Connection Creation> PBA messages with acceptance
	response cause values sent by the PGW over the S2a interface."
    ::= { rbnEpscPgwS2aPmip 3 }

rbnEpscS2aPbaPdnConnCreateRejSent            OBJECT-TYPE
    SYNTAX     Counter64
    MAX-ACCESS read-only
    STATUS     current
    DESCRIPTION 
        "Total number of PMIP <PDN Connection Creation> PBA messages with 
	rejection response cause values sent by the PGW over the S2a interface."
    ::= { rbnEpscPgwS2aPmip 4 }

rbnEpscS2aPbuPdnConnLifeExtRcvd  OBJECT-TYPE
    SYNTAX     Counter64
    MAX-ACCESS read-only
    STATUS     current
    DESCRIPTION 
        "Total number of PMIP <PDN Connection Lifetime Extension> PBU messages 
	received by the PGW over the S2a interface"
    ::= { rbnEpscPgwS2aPmip 5 }

rbnEpscS2aPbaPdnConnLifeExtAccSent       OBJECT-TYPE
    SYNTAX     Counter64
    MAX-ACCESS read-only
    STATUS     current
    DESCRIPTION 
        "Total number of PMIP <PDN Connection Lifetime Extension> PBA messages with 
	acceptance response cause values sent by the PGW over the S2a interface."
    ::= { rbnEpscPgwS2aPmip 6 }

rbnEpscS2aPbaPdnConnLifeExtRejSent      OBJECT-TYPE
    SYNTAX     Counter64
    MAX-ACCESS read-only
    STATUS     current
    DESCRIPTION 
        "Total number of PMIP <PDN Connection Lifetime Extension> PBA messages with 
	rejection response cause values sent by the PGW over the S2a interface."
    ::= { rbnEpscPgwS2aPmip 7 }

rbnEpscS2aPbuPdnConnDeletionRcvd    OBJECT-TYPE
    SYNTAX     Counter64
    MAX-ACCESS read-only
    STATUS     current
    DESCRIPTION 
        "Total number of PMIP <PDN Connection Deletion> PBU messages 
	received by the PGW over the S2a interface"
    ::= { rbnEpscPgwS2aPmip 8 }

rbnEpscS2aPbaPdnConnDeletionAccSent           OBJECT-TYPE
    SYNTAX     Counter64
    MAX-ACCESS read-only
    STATUS     current
    DESCRIPTION 
        "Total number of PMIP <PDN Connection Deletion> PBA messages with acceptance
	response cause values sent by the PGW over the S2a interface."
    ::= { rbnEpscPgwS2aPmip 9 }

rbnEpscS2aPbaPdnConnDeletionRejSent          OBJECT-TYPE
    SYNTAX     Counter64
    MAX-ACCESS read-only
    STATUS     current
    DESCRIPTION 
        "Total number of PMIP <PDN Connection Deletion> PBA messages with rejection
	 response cause values sent by the PGW over the S2a interface."
    ::= { rbnEpscPgwS2aPmip 10 }

rbnEpscS2aBriPdnConnDeletionSent              OBJECT-TYPE
    SYNTAX     Counter64
    MAX-ACCESS read-only
    STATUS     current
    DESCRIPTION 
        "Total number of PMIP <LMA Initiated PDN Connection Deletion> 
	BRI messages sent by the PGW over the S2a interface."
    ::= { rbnEpscPgwS2aPmip 11 }

rbnEpscS2aBraPdnConnDeletionAccRcvd                OBJECT-TYPE
    SYNTAX     Counter64
    MAX-ACCESS read-only
    STATUS     current
    DESCRIPTION 
        "Total number of PMIP <LMA Initiated PDN Connection Deletion> BRA messages 
	with acceptance response cause values received by the PGW over the S2a interface."
    ::= { rbnEpscPgwS2aPmip 12 }

rbnEpscS2aBraPdnConnDeletionRejRcvd               OBJECT-TYPE
    SYNTAX     Counter64
    MAX-ACCESS read-only
    STATUS     current
    DESCRIPTION 
        "Total number of PMIP <LMA Initiated PDN Connection Deletion> BRA messages 
	with rejection response cause values received by the PGW over the S2a interface."
    ::= { rbnEpscPgwS2aPmip 13 }

rbnEpscS2aPbuPdnConnHoIntraRcvd   OBJECT-TYPE
    SYNTAX     Counter64
    MAX-ACCESS read-only
    STATUS     current
    DESCRIPTION 
        "Total number of PMIP <intra non-3GPP PDN Connection Handover> PBU messages 
	received by the PGW over the S2a interface."
    ::= { rbnEpscPgwS2aPmip 14 }

rbnEpscS2aPbaPdnConnHoIntraAccSent        OBJECT-TYPE
    SYNTAX     Counter64
    MAX-ACCESS read-only
    STATUS     current
    DESCRIPTION 
        "Total number of PMIP <intra non-3GPP PDN Connection Handover> PBA messages
	 with acceptance response cause values sent by the PGW over the S2a interface."
    ::= { rbnEpscPgwS2aPmip 15 }

rbnEpscS2aPbaPdnConnHoIntraRejSent       OBJECT-TYPE
    SYNTAX     Counter64
    MAX-ACCESS read-only
    STATUS     current
    DESCRIPTION 
        "Total number of PMIP <intra non-3GPP PDN Connection Handover> PBA messages
	 with rejection response cause values sent by the PGW over the S2a interface."
    ::= { rbnEpscPgwS2aPmip 16 }

rbnEpscS2aBraPdnConnDeletionInvalidRcvd        OBJECT-TYPE
    SYNTAX     Counter64
    MAX-ACCESS read-only
    STATUS     current
    DESCRIPTION 
        "Total number of PMIP <LMA Initiated PDN Connection Deletion> BRA messages
	 with invalid content received by the PGW over the S2a interface."
    ::= { rbnEpscPgwS2aPmip 17 }

--
-- rbnEpscPgwS5S8 counters/gauges
--
rbnEpscS5S8CreateSessionReqRcvd  OBJECT-TYPE
    SYNTAX     Counter64
    MAX-ACCESS read-only
    STATUS     current
    DESCRIPTION 
        "Total number of GTPv2-C Create Session Request messages
        received by the PGW over the S5/S8 interface."
    ::= { rbnEpscPgwS5S8Gtp 1 }

rbnEpscS5S8CreateSessionRespAccSent  OBJECT-TYPE
    SYNTAX     Counter64
    MAX-ACCESS read-only
    STATUS     current
    DESCRIPTION 
        "Total number of GTPv2-C Create Session Response messages with
        acceptance response cause values sent by the PGW over the
        S5/S8 interface."
    ::= { rbnEpscPgwS5S8Gtp 2 }

rbnEpscS5S8CreateSessionRespRejSent  OBJECT-TYPE
    SYNTAX     Counter64
    MAX-ACCESS read-only
    STATUS     current
    DESCRIPTION 
        "Total number of GTPv2-C Create Session Response messages with
        rejection response cause values sent by the PGW over the
        S5/S8 interface."
    ::= { rbnEpscPgwS5S8Gtp 3 }

rbnEpscS5S8ModifyBearerReqRcvd  OBJECT-TYPE
    SYNTAX     Counter64
    MAX-ACCESS read-only
    STATUS     current
    DESCRIPTION 
        "Total number of GTPv2-C Modify Bearer Request messages
        received by the PGW over the S5/S8 interface."
    ::= { rbnEpscPgwS5S8Gtp 4 }

rbnEpscS5S8ModifyBearerRespAccSent  OBJECT-TYPE
    SYNTAX     Counter64
    MAX-ACCESS read-only
    STATUS     current
    DESCRIPTION 
        "Total number of GTPv2-C Modify Bearer Response messages with
        acceptance response values sent by the PGW over the
        S5/S8 interface."
    ::= { rbnEpscPgwS5S8Gtp 5 }

rbnEpscS5S8ModifyBearerRespRejSent  OBJECT-TYPE
    SYNTAX     Counter64
    MAX-ACCESS read-only
    STATUS     current
    DESCRIPTION 
        "Total number of GTPv2-C Modify Bearer Response messages with
        rejection response cause values sent by the PGW over the
        S5/S8 interface."
    ::= { rbnEpscPgwS5S8Gtp 6 }

rbnEpscS5S8DeleteSessionReqRcvd  OBJECT-TYPE
    SYNTAX     Counter64
    MAX-ACCESS read-only
    STATUS     current
    DESCRIPTION 
        "Total number of GTPv2-C Delete Session Request messages
        received by the PGW over the S5/S8 interface."
    ::= { rbnEpscPgwS5S8Gtp 7 }

rbnEpscS5S8DeleteSessionRespAccSent  OBJECT-TYPE
    SYNTAX     Counter64
    MAX-ACCESS read-only
    STATUS     current
    DESCRIPTION 
        "Total number of GTPv2-C Delete Session Response messages with
        acceptance response cause values sent by the PGW over the 
        S5/S8 interface."
    ::= { rbnEpscPgwS5S8Gtp 8 }

rbnEpscS5S8DeleteSessionRespRejSent  OBJECT-TYPE
    SYNTAX     Counter64
    MAX-ACCESS read-only
    STATUS     current
    DESCRIPTION 
        "Total number of GTPv2-C Delete Session Response messages 
        with rejection response cause values sent by the PGW over 
        the S5/S8 interface."
    ::= { rbnEpscPgwS5S8Gtp 9 }

rbnEpscS5S8CreateBearerReqSent  OBJECT-TYPE
    SYNTAX     Counter64
    MAX-ACCESS read-only
    STATUS     current
    DESCRIPTION 
        "Create Bearer Request messages sent by the PGW over the 
        S5/S8 PGW GTP-C interface."
    ::= { rbnEpscPgwS5S8Gtp 10 }

rbnEpscS5S8CreateBearerRespAccRcvd  OBJECT-TYPE
    SYNTAX     Counter64
    MAX-ACCESS read-only
    STATUS     current
    DESCRIPTION 
        "Create Bearer Response messages with acceptance response 
        cause values received by the PGW over the S5/S8 PGW GTP-C 
        interface."
    ::= { rbnEpscPgwS5S8Gtp 11 }

rbnEpscS5S8CreateBearerRespRejRcvd  OBJECT-TYPE
    SYNTAX     Counter64
    MAX-ACCESS read-only
    STATUS     current
    DESCRIPTION 
        "Create Bearer Response messages with rejection response 
        cause values received by the PGW over the S5/S8 PGW GTP-C 
        interface."
    ::= { rbnEpscPgwS5S8Gtp 12 }

rbnEpscS5S8DeleteBearerCmdRcvd  OBJECT-TYPE
    SYNTAX     Counter64
    MAX-ACCESS read-only
    STATUS     current
    DESCRIPTION
        "Delete Bearer Command messages received by the PGW over 
        the S5/S8 PGW GTP-C interface." 
    ::= { rbnEpscPgwS5S8Gtp 13 }

rbnEpscS5S8DeleteBearerFailureIndSent  OBJECT-TYPE
    SYNTAX     Counter64
    MAX-ACCESS read-only
    STATUS     current
    DESCRIPTION 
        "Delete Bearer Failure Indication messages sent by the PGW 
        over the S5/S8 PGW GTP-C interface."
    ::= { rbnEpscPgwS5S8Gtp 14 }

rbnEpscS5S8DeleteBearerReqSent  OBJECT-TYPE
    SYNTAX     Counter64
    MAX-ACCESS read-only
    STATUS     current
    DESCRIPTION 
        "Delete Bearer Request messages sent by the PGW over the 
        S5/S8 PGW GTP-C interface."
    ::= { rbnEpscPgwS5S8Gtp 15 }

rbnEpscS5S8DeleteBearerRespAccRcvd  OBJECT-TYPE
    SYNTAX     Counter64
    MAX-ACCESS read-only
    STATUS     current
    DESCRIPTION 
        "Delete Bearer Response messages with acceptance response 
        cause values received by the PGW over the S5/S8 PGW GTP-C 
        interface."
    ::= { rbnEpscPgwS5S8Gtp 16 }

rbnEpscS5S8DeleteBearerRespRejRcvd  OBJECT-TYPE
    SYNTAX     Counter64
    MAX-ACCESS read-only
    STATUS     current
    DESCRIPTION 
        "Delete Bearer Response messages with rejection response 
        cause values received by the PGW over the S5/S8 PGW GTP-C 
        interface."
    ::= { rbnEpscPgwS5S8Gtp 17 }

rbnEpscS5S8UpdateBearerReqSent  OBJECT-TYPE
    SYNTAX     Counter64
    MAX-ACCESS read-only
    STATUS     current
    DESCRIPTION 
        "Update Bearer Request messages sent by the PGW over the 
        S5/S8 PGW GTP-C interface."
    ::= { rbnEpscPgwS5S8Gtp 18 }

rbnEpscS5S8UpdateBearerRespAccRcvd  OBJECT-TYPE
    SYNTAX     Counter64
    MAX-ACCESS read-only
    STATUS     current
    DESCRIPTION 
        "Update Bearer Response messages with acceptance response 
        cause values received by the PGW over the S5/S8 PGW GTP-C 
        interface."
    ::= { rbnEpscPgwS5S8Gtp 19 }

rbnEpscS5S8UpdateBearerRespRejRcvd  OBJECT-TYPE
    SYNTAX     Counter64
    MAX-ACCESS read-only
    STATUS     current
    DESCRIPTION 
        "Update Bearer Response messages with rejection response 
        cause values received by the PGW over the S5/S8 PGW GTP-C 
        interface."
    ::= { rbnEpscPgwS5S8Gtp 20 }

--
-- rbnEpscPgwS6b counters/gauges
--

rbnEpscS6bAarSent  OBJECT-TYPE
    SYNTAX     Counter64
    MAX-ACCESS read-only
    STATUS     current
    DESCRIPTION 
        "Total number of <Authorization Request> AAR messages sent by
	 the PGW over the S6b interface."
    ::= { rbnEpscPgwS6b 1 }

rbnEpscS6bAaaSuccRcvd  OBJECT-TYPE
    SYNTAX     Counter64
    MAX-ACCESS read-only
    STATUS     current
    DESCRIPTION 
        "Total number of <Authorization Answer> AAA messages with 
	acceptance response cause values received by the PGW over the
	 S6b interface."
    ::= { rbnEpscPgwS6b 2 }

rbnEpscS6bAaaFailRcvd  OBJECT-TYPE
    SYNTAX     Counter64
    MAX-ACCESS read-only
    STATUS     current
    DESCRIPTION 
        "Total number of <Authorization Answer> AAA messages with 
	rejection response cause values received by the PGW over 
	the S6b interface."
    ::= { rbnEpscPgwS6b 3 }

rbnEpscS6bAaaInvalidRcvd  OBJECT-TYPE
    SYNTAX     Counter64
    MAX-ACCESS read-only
    STATUS     current
    DESCRIPTION 
        "Total number of <Authorization Answer> AAA messages with invalid
	 content received by the PGW over the S6b interface."
    ::= { rbnEpscPgwS6b 4 }

rbnEpscS6bStrSent  OBJECT-TYPE
    SYNTAX     Counter64
    MAX-ACCESS read-only
    STATUS     current
    DESCRIPTION 
        "Total number of <Session Termination Request> STR messages 
	sent by the PGW over the S6b interface."
    ::= { rbnEpscPgwS6b 5 }

rbnEpscS6bStaSuccRcvd  OBJECT-TYPE
    SYNTAX     Counter64
    MAX-ACCESS read-only
    STATUS     current
    DESCRIPTION 
        "Total number of <Session Termination Answer> STA messages with
	acceptance response cause values received by the PGW over the 
	S6b interface."
    ::= { rbnEpscPgwS6b 6 }

rbnEpscS6bStaFailRcvd  OBJECT-TYPE
    SYNTAX     Counter64
    MAX-ACCESS read-only
    STATUS     current
    DESCRIPTION 
        "Total number of <Session Termination Answer> STA messages with 
	rejection response cause values received by the PGW over the 
	S6b interface."
    ::= { rbnEpscPgwS6b 7 }

--
-- Compliance Statements
--
rbnEpscMIBCompliance MODULE-COMPLIANCE
    STATUS        current
    DESCRIPTION
        "The compliance statement for Ericsson
        SNMP entities which represent EPSC statistics"
    MODULE        -- this module
    MANDATORY-GROUPS {
        rbnEpscCommonGeneralGroup,
        rbnEpscCommonChargingGroup,
        rbnEpscSgwGeneralGroup,
        rbnEpscSgwS5S8GtpGroup,
        rbnEpscSgwS11S4Group,
        rbnEpscSgwChargingGroup,
        rbnEpscPgwChargingGroup,
-- rbnEpscPgwGeneralGroup group is reserved for future use.
--         rbnEpscPgwGeneralGroup,
        rbnEpscPgwGxGroup,
        rbnEpscPgwGnGpGroup,
        rbnEpscPgwS5S8GtpGroup,
        rbnEpscPgwGyGroup,
	rbnEpscPgwS2aPmipGroup,
	rbnEpscPgwS6bGroup,
	rbnEpscCommonDiameterGroup,
	rbnEpscCommonIcrGroup
    }
    ::= { rbnEpscMIBCompliances 1 }

--
-- Units of Conformance
--
rbnEpscCommonGeneralGroup  OBJECT-GROUP
    OBJECTS { 
        rbnEpscConnectionsEstablished, 
        rbnEpscPdnConnectionTimeout,
        rbnEpscBearersEstablished, 
        rbnEpscUeAttached } 
    STATUS     current
    DESCRIPTION 
        "A collection of objects providing EPSC statistical
         information common for SGW and PGW."
    ::= { rbnEpscMIBGroups 1 }

rbnEpscCommonChargingGroup  OBJECT-GROUP
    OBJECTS { 
        rbnEpscClosedCdrFiles,
        rbnEpscRfAcrSent,
        rbnEpscRfAcaSuccRcvd,
        rbnEpscRfAcaFailRcvd,
        rbnEpscRfAcrWrittenToDisk } 
    STATUS     current
    DESCRIPTION 
        "A collection of objects providing EPSC statistical
         charging information common for SGW and PGW."
    ::= { rbnEpscMIBGroups 2 }

rbnEpscSgwGeneralGroup  OBJECT-GROUP
    OBJECTS { 
        rbnEpscSgwUeEcmConnected }
    STATUS     current
    DESCRIPTION 
        "A collection of objects providing EPSC statistical
         information for SGW."
    ::= { rbnEpscMIBGroups 3 }

rbnEpscSgwS5S8GtpGroup  OBJECT-GROUP 
     OBJECTS { 
        rbnEpscS5S8CreateSessionReqSent, 
        rbnEpscS5S8CreateSessionRespAccRcvd, 
        rbnEpscS5S8CreateSessionRespRejRcvd, 
        rbnEpscS5S8DeleteBearerReqRcvd, 
        rbnEpscS5S8DeleteBearerRespAccSent, 
        rbnEpscS5S8DeleteBearerRespRejSent, 
        rbnEpscS5S8DeleteSessionReqSent, 
        rbnEpscS5S8DeleteSessionRespAccRcvd, 
        rbnEpscS5S8DeleteSessionRespRejRcvd,
        rbnEpscS5S8ModifyBearerReqSent, 
        rbnEpscS5S8ModifyBearerRespAccRcvd, 
        rbnEpscS5S8ModifyBearerRespRejRcvd,
        rbnEpscS5S8CreateBearerReqRcvd,
        rbnEpscS5S8CreateBearerRespAccSent,
        rbnEpscS5S8CreateBearerRespRejSent,
        rbnEpscS5S8DeleteBearerCmdSent,
        rbnEpscS5S8DeleteBearerFailureIndRcvd,
        rbnEpscS5S8UpdateBearerReqRcvd,
        rbnEpscS5S8UpdateBearerRespAccSent,
        rbnEpscS5S8UpdateBearerRespRejSent }
     STATUS     current
     DESCRIPTION 
         "A collection of objects providing EPSC statistical
          information for SGW S5 and S8 interfaces over GTP."
     ::= { rbnEpscMIBGroups 4 }

rbnEpscSgwS11S4Group  OBJECT-GROUP
    OBJECTS { 
        rbnEpscS11S4CreateSessionReqRcvd, 
        rbnEpscS11S4CreateSessionRespAccSent, 
        rbnEpscS11S4CreateSessionRespRejSent, 
        rbnEpscS11S4ModifyBearerReqRcvd, 
        rbnEpscS11S4ModifyBearerRespAccSent, 
        rbnEpscS11S4ModifyBearerRespRejSent, 
        rbnEpscS11S4DeleteSessionReqRcvd, 
        rbnEpscS11S4DeleteSessionRespAccSent, 
        rbnEpscS11S4DeleteSessionRespRejSent, 
        rbnEpscS11S4DlDataNotificationSent, 
        rbnEpscS11S4DlDataNotificationAckRcvd, 
        rbnEpscS11S4DlDataNotifFailureIndRcvd, 
        rbnEpscS11S4DeleteBearerReqSent, 
        rbnEpscS11S4DeleteBearerRespAccRcvd, 
        rbnEpscS11S4DeleteBearerRespRejRcvd, 
        rbnEpscS11S4RelAccessBearersReqRcvd, 
        rbnEpscS11S4RelAccessBearersRespAccSent, 
        rbnEpscS11S4RelAccessBearersRespRejSent,
        rbnEpscS11S4CreateBearerReqSent,
        rbnEpscS11S4CreateBearerRespAccRcvd,
        rbnEpscS11S4CreateBearerRespRejRcvd,
        rbnEpscS11S4DeleteBearerCmdRcvd,
        rbnEpscS11S4DeleteBearerFailureIndSent,
        rbnEpscS11S4UpdateBearerReqSent,
        rbnEpscS11S4UpdateBearerRespAccRcvd,
        rbnEpscS11S4UpdateBearerRespRejRcvd } 
    STATUS     current
    DESCRIPTION 
        "A collection of objects providing EPSC statistical
         information for S11 and S4 interfaces."
    ::= { rbnEpscMIBGroups 5 }

rbnEpscSgwChargingGroup  OBJECT-GROUP
    OBJECTS {
        rbnEpscSgwCdrsEncoded }
    STATUS     current
    DESCRIPTION 
        "A collection of objects providing EPSC statistical
        information for SGW charging."
    ::= { rbnEpscMIBGroups 6 }

-- rbnEpscPgwGeneralGroup group is reserved for future use.
-- It will be defined as soon as the group contain a counter object. 
-- rbnEpscPgwGeneralGroup  OBJECT-GROUP
--    OBJECTS { 
--    }
--    STATUS     current
--    DESCRIPTION 
--        "A collection of objects providing EPSC statistical
--         information for PGW."
--    ::= { rbnEpscMIBGroups 7 }

rbnEpscPgwGxGroup  OBJECT-GROUP
   OBJECTS { 
       rbnEpscGxCcaInitialFailRcvd,
       rbnEpscGxCcaInitialSuccRcvd,
       rbnEpscGxCcaTerminateFailRcvd,
       rbnEpscGxCcaTerminateSuccRcvd,
       rbnEpscGxCcaUpdateFailRcvd,
       rbnEpscGxCcaUpdateSuccRcvd,
       rbnEpscGxCcrInitialSent,
       rbnEpscGxCcrTerminateSent,
       rbnEpscGxCcrUpdateSent,
       rbnEpscGxRaaFailSent,
       rbnEpscGxRaaSuccSent,
       rbnEpscGxRarRcvd }
   STATUS     current
   DESCRIPTION 
       "A collection of objects providing EPSC statistical
        information for PGW Gx interface."
   ::= { rbnEpscMIBGroups 8 }

rbnEpscPgwChargingGroup  OBJECT-GROUP
    OBJECTS {
        rbnEpscPgwCdrsEncoded }
    STATUS     current
    DESCRIPTION 
        "A collection of objects providing EPSC statistical
        information for PGW charging."
    ::= { rbnEpscMIBGroups 9 }

rbnEpscPgwGnGpGroup  OBJECT-GROUP
    OBJECTS {
        rbnEpscGnGpDeletePdpCtxReqRcvd,
        rbnEpscGnGpDeletePdpCtxRespAccSent,
        rbnEpscGnGpUpdatePdpCtxReqRcvd,
        rbnEpscGnGpUpdatePdpCtxRespAccSent, 
        rbnEpscGnGpCreatePdpCtxReqRcvd,
        rbnEpscGnGpCreatePdpCtxRespAccSent,
        rbnEpscGnGpUpdatePdpCtxRespRejSent, 
        rbnEpscGnGpDeletePdpCtxRespRejSent,
        rbnEpscGnGpCreatePdpCtxRespRejSent,
        rbnEpscGnGpUpdatePdpCtxReqSent,
        rbnEpscGnGpUpdatePdpCtxRespAccRcvd,
        rbnEpscGnGpUpdatePdpCtxRespRejRcvd,
        rbnEpscGnGpDeletePdpCtxReqSent,
        rbnEpscGnGpDeletePdpCtxRespAccRcvd,
        rbnEpscGnGpDeletePdpCtxRespRejRcvd }
    STATUS     current
    DESCRIPTION 
        "A collection of objects providing EPSC statistical
         information for Gn and Gp interfaces."
    ::= { rbnEpscMIBGroups 13 }

rbnEpscPgwS5S8GtpGroup  OBJECT-GROUP 
     OBJECTS { 
        rbnEpscS5S8CreateSessionReqRcvd, 
        rbnEpscS5S8CreateSessionRespAccSent, 
        rbnEpscS5S8CreateSessionRespRejSent, 
        rbnEpscS5S8ModifyBearerReqRcvd, 
        rbnEpscS5S8ModifyBearerRespAccSent, 
        rbnEpscS5S8ModifyBearerRespRejSent, 
        rbnEpscS5S8DeleteSessionReqRcvd, 
        rbnEpscS5S8DeleteSessionRespAccSent, 
        rbnEpscS5S8DeleteSessionRespRejSent,
        rbnEpscS5S8CreateBearerReqSent,
        rbnEpscS5S8CreateBearerRespAccRcvd,
        rbnEpscS5S8CreateBearerRespRejRcvd,
        rbnEpscS5S8DeleteBearerCmdRcvd,
        rbnEpscS5S8DeleteBearerFailureIndSent,
        rbnEpscS5S8DeleteBearerReqSent,
        rbnEpscS5S8DeleteBearerRespAccRcvd,
        rbnEpscS5S8DeleteBearerRespRejRcvd,
        rbnEpscS5S8UpdateBearerReqSent,
        rbnEpscS5S8UpdateBearerRespAccRcvd,
        rbnEpscS5S8UpdateBearerRespRejRcvd }
     STATUS     current
     DESCRIPTION 
         "A collection of objects providing EPSC statistical
          information for PGW S5 and S8 interfaces over GTP."
     ::= { rbnEpscMIBGroups 11 }

rbnEpscPgwGyGroup  OBJECT-GROUP
   OBJECTS { 
       rbnEpscGyCcaInitialFailRcvd,
       rbnEpscGyCcaInitialSuccRcvd,
       rbnEpscGyCcaTerminateFailRcvd,
       rbnEpscGyCcaTerminateSuccRcvd,
       rbnEpscGyCcrInitialSent,
       rbnEpscGyCcrTerminateSent}
   STATUS     current
   DESCRIPTION 
       "A collection of counters providing EPSC statistical
        information for the Gy interface."
   ::= { rbnEpscMIBGroups 14 }

rbnEpscPgwS2aPmipGroup  OBJECT-GROUP 
     OBJECTS { 
	rbnEpscS2aPmipMsgInvalidRcvd,
	rbnEpscS2aPbuPdnConnCreateRcvd,
	rbnEpscS2aPbaPdnConnCreateAccSent,
	rbnEpscS2aPbaPdnConnCreateRejSent,
	rbnEpscS2aPbuPdnConnLifeExtRcvd,
	rbnEpscS2aPbaPdnConnLifeExtAccSent,
	rbnEpscS2aPbaPdnConnLifeExtRejSent,
	rbnEpscS2aPbuPdnConnDeletionRcvd,
	rbnEpscS2aPbaPdnConnDeletionAccSent,
	rbnEpscS2aPbaPdnConnDeletionRejSent,
	rbnEpscS2aBriPdnConnDeletionSent,
	rbnEpscS2aBraPdnConnDeletionAccRcvd, 
	rbnEpscS2aBraPdnConnDeletionRejRcvd,
	rbnEpscS2aPbuPdnConnHoIntraRcvd,
	rbnEpscS2aPbaPdnConnHoIntraAccSent,
	rbnEpscS2aPbaPdnConnHoIntraRejSent,
        rbnEpscS2aBraPdnConnDeletionInvalidRcvd }
     STATUS     current
     DESCRIPTION 
         "A collection of counters providing EPSC statistical information for PGW S2a interface"
     ::= { rbnEpscMIBGroups 15 }

rbnEpscPgwS6bGroup  OBJECT-GROUP
   OBJECTS { 
       rbnEpscS6bAarSent,
       rbnEpscS6bAaaSuccRcvd,	
       rbnEpscS6bAaaFailRcvd,
       rbnEpscS6bAaaInvalidRcvd,
       rbnEpscS6bStrSent,
       rbnEpscS6bStaSuccRcvd,
       rbnEpscS6bStaFailRcvd}
   STATUS     current
   DESCRIPTION 
       "A collection of counters providing EPSC statistical 
	information for PGW S6b interface."
   ::= { rbnEpscMIBGroups 16 }

rbnEpscCommonDiameterGroup  OBJECT-GROUP
   OBJECTS { 
       rbnEpscDiameterMsgInvalidRcvd}
   STATUS     current
   DESCRIPTION 
       "A collection of counters providing EPSC statistical 
	information for both SGW and PGW protocols."
   ::= { rbnEpscMIBGroups 17 }

rbnEpscCommonIcrGroup  OBJECT-GROUP
   OBJECTS { 
       rbnEpscIcrCreateSessionSyncRcvd,
       rbnEpscIcrCreateSessionSyncSent,
       rbnEpscIcrDeleteSessionSyncRcvd,
       rbnEpscIcrDeleteSessionSyncSent}
   STATUS     current
   DESCRIPTION 
       "A collection of counters providing EPSC statistical information 
	regarding ICR for both SGW and PGW."
   ::= { rbnEpscMIBGroups 18 }

END

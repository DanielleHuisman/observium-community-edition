ETA-RCI10-MIB DEFINITIONS ::= BEGIN

IMPORTS
    OBJECT-TYPE, IpAddress, MODULE-IDENTITY, NOTIFICATION-TYPE, enterprises, Integer32   FROM SNMPv2-SMI;

-- 1.3.6.1.4.1.44086.4.1
rci10 MODULE-IDENTITY 
	LAST-UPDATED "201810081546Z"		-- October 08, 2018 at 15:46 GMT
	ORGANIZATION 
		"E-T-A Elektrotechnische Apparate GmbH"
	CONTACT-INFO 
		"www.e-t-a.de"
	DESCRIPTION 
		"Copyright notice
		(c) E-T-A Elektrotechnische Apparate GmbH
		2014-2015 Florian Pfanner, Michael Haerteis
		
		This MIB file was created for a RCI10. Via
		SNMP the slave states can be retrieved and device actions can initiated."
	REVISION "201810081546Z"		-- October 08, 2018 at 15:46 GMT
	DESCRIPTION 
		"Version 1.020 (added fuse objects for device type 0x70)"
	REVISION "201703031052Z"		-- March 03, 2017 at 10:52 GMT
	DESCRIPTION 
		"Version 1.010 (added exernal alarms)"
	REVISION "201502021303Z"		-- February 02, 2015 at 13:03 GMT
	DESCRIPTION 
		"Initial version"
	::= { etaProp 1 }
    
    eta   			        OBJECT IDENTIFIER ::= { enterprises 44086 }
    etaProp			        OBJECT IDENTIFIER ::= { eta 4 }
    
    system 			        OBJECT IDENTIFIER ::= { rci10 1 }
    snmp                    OBJECT IDENTIFIER ::= { system 1  }
    ethernet                OBJECT IDENTIFIER ::= { system 2  }
    ipv4                    OBJECT IDENTIFIER ::= { ethernet 1 }
    ipv6                    OBJECT IDENTIFIER ::= { ethernet 2 }
    dateTime                OBJECT IDENTIFIER ::= { system 3 }
	fuses			        OBJECT IDENTIFIER ::= { rci10 10 }
    feedA			        OBJECT IDENTIFIER ::= { fuses 1 }
	feedB			        OBJECT IDENTIFIER ::= { fuses 2 }
	externalAlarms	        OBJECT IDENTIFIER ::= { rci10 20 }
    eaFeedA			        OBJECT IDENTIFIER ::= { externalAlarms 1 }
	eaFeedB			        OBJECT IDENTIFIER ::= { externalAlarms 2 }
    notifications           OBJECT IDENTIFIER ::= { rci10 100 }
    prefix                  OBJECT IDENTIFIER ::= { notifications 1 }
    systemNotifications     OBJECT IDENTIFIER ::= { prefix 1 }
    fusesNotifications      OBJECT IDENTIFIER ::= { prefix 10 }
	externalAlarmNotifications OBJECT IDENTIFIER ::= { prefix 20 }
    objects                 OBJECT IDENTIFIER ::= { notifications 2 }
    systemObjects           OBJECT IDENTIFIER ::= { objects 1 }
    fusesObjects            OBJECT IDENTIFIER ::= { objects 10 }
	externalAlarmObjects    OBJECT IDENTIFIER ::= { objects 20 }



snmpTrapsEnable OBJECT-TYPE
    SYNTAX Integer32 (0..1)
    MAX-ACCESS read-write
    STATUS current
    DESCRIPTION
        "If 1 sending of SNMP traps is enabled. Else no traps will be sent"
    ::= { snmp 1 }


snmpTrapTarget OBJECT-TYPE
    SYNTAX OCTET STRING (SIZE (1..100))
    MAX-ACCESS read-write
    STATUS current
    DESCRIPTION
        "Traps are sent to the destination given here. This could be an IP address or a host name."
    ::= { snmp 2 }
    
snmpProtocol OBJECT-TYPE
    SYNTAX OCTET STRING
    MAX-ACCESS read-only
    STATUS current
    DESCRIPTION
        "SNMP protocol version currently used. The value can only be changed using the SSH configuration."
    ::= { snmp 3 }
    
snmpCommunityString OBJECT-TYPE
    SYNTAX OCTET STRING (SIZE (1..20))
    MAX-ACCESS read-write
    STATUS current
    DESCRIPTION
        "SNMP community string used to access the values. Also the SNMP traps are sent using this community string. Only valid if SNMPv2c is used."
    ::= { snmp 10 }

snmpLogin OBJECT-TYPE
    SYNTAX OCTET STRING (SIZE (1..20))
    MAX-ACCESS read-write
    STATUS current
    DESCRIPTION
        "Login name used to access the SNMP data values. Only valid if SNMPv3 is used."
    ::= { snmp 20 }

snmpPassword OBJECT-TYPE
    SYNTAX OCTET STRING (SIZE (1..20))
    MAX-ACCESS read-write
    STATUS current
    DESCRIPTION
        "Password used to access the SNMP data values. The password have to be at least eight characters long. Only valid if SNMPv3 is used."
    ::= { snmp 21 }
    
snmpAuthentication OBJECT-TYPE
    SYNTAX OCTET STRING (SIZE (3))
    MAX-ACCESS read-write
    STATUS current
    DESCRIPTION
        "Authentication method used to encrypt the SNMP data transmission. Valid entries are 'MD5' and 'SHA'. Only valid if SNMPv3 is used."
    ::= { snmp 22 }
    
snmpEncryption OBJECT-TYPE
    SYNTAX OCTET STRING (SIZE (3))
    MAX-ACCESS read-write
    STATUS current
    DESCRIPTION
        "Encryption method used for the SNMP data transmission. Valid entries are 'AES', 'DES' and 'off'. Only valid if SNMPv3 is used."
    ::= { snmp 23 }
    
snmpEncryptionKey OBJECT-TYPE
    SYNTAX OCTET STRING (SIZE (1..500))
    MAX-ACCESS read-write
    STATUS current
    DESCRIPTION
        "Encryption key used for the SNMP data transmission. Only valid if SNMPv3 is used."
    ::= { snmp 24 }
    


dnsServer OBJECT-TYPE
    SYNTAX IpAddress
    MAX-ACCESS read-write
    STATUS current
    DESCRIPTION
        "Address of DNS server, for example 192.168.0.1. The address given here can be either an IPv4 or an IPv6 address."
    ::= { ethernet 10 }

   


dhcpv4Enable OBJECT-TYPE
    SYNTAX Integer32 (0..1)
    MAX-ACCESS read-write
    STATUS current
    DESCRIPTION
        "If 1 the IPv4 settings are automatically obtained using DHCP."
    ::= { ipv4 1 }

ip4Address OBJECT-TYPE
    SYNTAX IpAddress
    MAX-ACCESS read-write
    STATUS current
    DESCRIPTION
        "IPv4 adress of the RCI10, for example 192.168.1.25."
    ::= { ipv4 10 }
    
ip4NetMask OBJECT-TYPE
    SYNTAX IpAddress
    MAX-ACCESS read-write
    STATUS current
    DESCRIPTION
        "IPv4 network mask, for example 255.255.255.0."
    ::= { ipv4 11 }

ip4Gateway OBJECT-TYPE
    SYNTAX IpAddress
    MAX-ACCESS read-write
    STATUS current
    DESCRIPTION
        "IPv4 gateway address, for example 192.168.1.1."
    ::= { ipv4 12 }



dhcpv6Enable OBJECT-TYPE
    SYNTAX Integer32 (0..1)
    MAX-ACCESS read-write
    STATUS current
    DESCRIPTION
        "If 1 the IPv6 settings are automatically obtained using DHCP."
    ::= { ipv6 1 }

ip6Address OBJECT-TYPE
    SYNTAX IpAddress
    MAX-ACCESS read-write
    STATUS current
    DESCRIPTION
        "IPv6 adress of the RCI10, for example 2001:0db8:85a3::1000."
    ::= { ipv6 10 }
    
ip6PrefixLength OBJECT-TYPE
    SYNTAX Integer32 (1..128)
    MAX-ACCESS read-write
    STATUS current
    DESCRIPTION
        "IPv6 network prefix length. Valid range is from 1 to 128."
    ::= { ipv6 11 }


time OBJECT-TYPE
    SYNTAX OCTET STRING (SIZE (8))
    MAX-ACCESS read-write
    STATUS current
    DESCRIPTION
        "Current system time. Write to this object to update the system time, use the format HH:MM:SS."
    ::= { dateTime 1 }
    
date OBJECT-TYPE
    SYNTAX OCTET STRING (SIZE (10))
    MAX-ACCESS read-write
    STATUS current
    DESCRIPTION
        "Current date of the RCI10. Write to this object to update the system date, use the format dd.mm.yyyy."
    ::= { dateTime 2 }

timezone OBJECT-TYPE
    SYNTAX Integer32 (-12..12)
    MAX-ACCESS read-write
    STATUS current
    DESCRIPTION
        "Timezone of the RCI10. The timezone gives the difference between UTC and local time in hours."
    ::= { dateTime 3 }

dstEn OBJECT-TYPE
    SYNTAX Integer32 (0..1)
    MAX-ACCESS read-write
    STATUS current
    DESCRIPTION
        "If 1 the daylight saving time is enabled."
    ::= { dateTime 4 }



hwVersion OBJECT-TYPE
	SYNTAX OCTET STRING
	MAX-ACCESS read-only
	STATUS current
	DESCRIPTION
		"RCI10 hardware version"
	::= { system 11 }

hwSerial OBJECT-TYPE
	SYNTAX OCTET STRING
	MAX-ACCESS read-only
	STATUS current
	DESCRIPTION
		"RCI10 hardware serial number"
	::= { system 12 }

swVersion OBJECT-TYPE
    SYNTAX OCTET STRING
    MAX-ACCESS read-only
    STATUS current
    DESCRIPTION
        "RCI10 software version"
    ::= { system 13 }

systemName OBJECT-TYPE
    SYNTAX OCTET STRING (SIZE (1..100))
    MAX-ACCESS read-write
    STATUS current
    DESCRIPTION
        "RCI10 System Name"
    ::= { system 14 }

systemContact OBJECT-TYPE
    SYNTAX OCTET STRING (SIZE (1..100))
    MAX-ACCESS read-write
    STATUS current
    DESCRIPTION
        "Name of the person which is responsible for the system"
    ::= { system 15 }

systemLocation OBJECT-TYPE
    SYNTAX OCTET STRING (SIZE (1..100))
    MAX-ACCESS read-write
    STATUS current
    DESCRIPTION
        "Location of this RCI10"
    ::= { system 16 }

reboot OBJECT-TYPE
    SYNTAX Integer32 (0..1)
    MAX-ACCESS read-write
    STATUS current
    DESCRIPTION
        "Write 1 to this value will cause a reboot of the RCI10."
    ::= { system 50 }





sumCurrentA OBJECT-TYPE
	SYNTAX Integer32
	MAX-ACCESS read-only
	STATUS current
	DESCRIPTION
		"Current of the whole feed in milliampere"
	::= { feedA 1 }
	



sumCurrentB OBJECT-TYPE
	SYNTAX Integer32
	MAX-ACCESS read-only
	STATUS current
	DESCRIPTION
		"Current of the whole feed in milliampere"
	::= { feedB 1 }



switchAllFuses OBJECT-TYPE
    SYNTAX Integer32 (0..1)
    MAX-ACCESS read-write
    STATUS current
    DESCRIPTION
        "Sets the output state of all fuses: 0=output off, 1=output on"
    ::= { fuses 20 }


monitorEnabled OBJECT-TYPE
    SYNTAX Integer32 (0..1)
    MAX-ACCESS read-only
    STATUS current
    DESCRIPTION
        "If 1 is returned any automatic feed or fuse monitor is enabled."
    ::= { fuses 40 }






fusesATable OBJECT-TYPE
    SYNTAX SEQUENCE OF FusesAEntry
    MAX-ACCESS not-accessible
    STATUS current
    DESCRIPTION
        " "
    ::= { feedA 10 }

fusesAEntry OBJECT-TYPE
    SYNTAX FusesAEntry
    MAX-ACCESS not-accessible
    STATUS current
    DESCRIPTION
        " "
    INDEX {indexA}    
    ::= { fusesATable 1 }
    
FusesAEntry ::= SEQUENCE {
		indexA			Integer32,
		availableA      Integer32,
		deviceTypeA     Integer32,
		serialA			Integer32,
		hwVersionA		Integer32,
		swVersionA		Integer32,
		nominalCurrentA	Integer32,
		errNoSysParA	Integer32,
		errCrcParamA	Integer32,
		errCrcProgA		Integer32,
		errIntMemA		Integer32,
		errControllerA	Integer32,
		errWatchdogA	Integer32,
		voltageA		Integer32,
		temperatureA	Integer32,
		loadOutputA		Integer32,
		statusShortA	Integer32,
		statusOverloadA	Integer32,
		statusUvltA		Integer32,
		statusOvltA		Integer32,
		statusOtmpA		Integer32,
		statusNoVccA	Integer32,
		loadA   		Integer32,
        	labelA          OCTET STRING,
		nominalVoltageA		OCTET STRING,
		multiEsxA		Integer32		
    }

indexA OBJECT-TYPE
    SYNTAX Integer32 (1..20)
    MAX-ACCESS not-accessible
    STATUS current
    DESCRIPTION
        "Fuse index"
    ::= { fusesAEntry 1 }

availableA OBJECT-TYPE
    SYNTAX Integer32
    MAX-ACCESS read-only
    STATUS current
    DESCRIPTION
        "Status of fuse: 0=no fuse, 1=fuse available"
    ::= { fusesAEntry 2 }

deviceTypeA OBJECT-TYPE
    SYNTAX Integer32
    MAX-ACCESS read-only
    STATUS current
    DESCRIPTION
        "Type number of the fuse"
    ::= { fusesAEntry 3 }

serialA OBJECT-TYPE
    SYNTAX Integer32
    MAX-ACCESS read-only
    STATUS current
    DESCRIPTION
        "Serial number of the fuse"
    ::= { fusesAEntry 4 }
	
hwVersionA OBJECT-TYPE
    SYNTAX Integer32
    MAX-ACCESS read-only
    STATUS current
    DESCRIPTION
        "Hardware version number of the fuse"
    ::= { fusesAEntry 5 }
	
swVersionA OBJECT-TYPE
    SYNTAX Integer32
    MAX-ACCESS read-only
    STATUS current
    DESCRIPTION
        "Software version number of the fuse"
    ::= { fusesAEntry 6 }
	
nominalCurrentA OBJECT-TYPE
    SYNTAX Integer32
    MAX-ACCESS read-only
    STATUS current
    DESCRIPTION
        "Nominal current of the fuse in milliampere"
    ::= { fusesAEntry 7 }
	
errNoSysParA OBJECT-TYPE
    SYNTAX Integer32
    MAX-ACCESS read-only
    STATUS current
    DESCRIPTION
        "No systemparameter available fault: 0=no fault, 1=fault"
    ::= { fusesAEntry 8 }
	
errCrcParamA OBJECT-TYPE
    SYNTAX Integer32
    MAX-ACCESS read-only
    STATUS current
    DESCRIPTION
        "Parameter CRC fault: 0=no fault, 1=fault"
    ::= { fusesAEntry 9 }
	
errCrcProgA OBJECT-TYPE
    SYNTAX Integer32
    MAX-ACCESS read-only
    STATUS current
    DESCRIPTION
        "Program memory CRC fault: 0=no fault, 1=fault"
    ::= { fusesAEntry 10 }
	
errIntMemA OBJECT-TYPE
    SYNTAX Integer32
    MAX-ACCESS read-only
    STATUS current
    DESCRIPTION
        "Internal memory fault: 0=no fault, 1=fault"
    ::= { fusesAEntry 11 }
	
errControllerA OBJECT-TYPE
    SYNTAX Integer32
    MAX-ACCESS read-only
    STATUS current
    DESCRIPTION
        "Controller fault: 0=no fault, 1=fault"
    ::= { fusesAEntry 12 }
	
errWatchdogA OBJECT-TYPE
    SYNTAX Integer32
    MAX-ACCESS read-only
    STATUS current
    DESCRIPTION
        "Watchdog reset fault: 0=no fault, 1=fault"
    ::= { fusesAEntry 13 }
	
voltageA OBJECT-TYPE
    SYNTAX Integer32
    MAX-ACCESS read-only
    STATUS current
    DESCRIPTION
        "Power supply voltage in millivolt"
    ::= { fusesAEntry 14 }
	
temperatureA OBJECT-TYPE
    SYNTAX Integer32
    MAX-ACCESS read-only
    STATUS current
    DESCRIPTION
        "Current temperature of the fuse in millivolt"
    ::= { fusesAEntry 15 }
	
loadOutputA OBJECT-TYPE
    SYNTAX Integer32 (0..1)
    MAX-ACCESS read-write
    STATUS current
    DESCRIPTION
        "Output status of the fuse: 0=output off, 1=output on"
    ::= { fusesAEntry 16 }
	
statusShortA OBJECT-TYPE
    SYNTAX Integer32
    MAX-ACCESS read-only
    STATUS current
    DESCRIPTION
        "Short is detected by this fuse: 0=no fault, 1=fault"
    ::= { fusesAEntry 17 }
	
statusOverloadA OBJECT-TYPE
    SYNTAX Integer32
    MAX-ACCESS read-only
    STATUS current
    DESCRIPTION
        "Overload status: 0=no overload, 1=overload"
    ::= { fusesAEntry 18 }
	
statusUvltA OBJECT-TYPE
    SYNTAX Integer32
    MAX-ACCESS read-only
    STATUS current
    DESCRIPTION
        "Undervoltage status: 0=no undervoltage, 1=undervoltage"
    ::= { fusesAEntry 19 }
	
statusOvltA OBJECT-TYPE
    SYNTAX Integer32
    MAX-ACCESS read-only
    STATUS current
    DESCRIPTION
        "Overvoltage status: 0=no overvoltage, 1=overvoltage"
    ::= { fusesAEntry 20 }
	
statusOtmpA OBJECT-TYPE
    SYNTAX Integer32
    MAX-ACCESS read-only
    STATUS current
    DESCRIPTION
        "Overtemperature status: 0=no overtemperature, 1=overtemperature"
    ::= { fusesAEntry 21 }
	
statusNoVccA OBJECT-TYPE
    SYNTAX Integer32
    MAX-ACCESS read-only
    STATUS current
    DESCRIPTION
        "No VCC status: 0=no VCC, 1=VCC ok"
    ::= { fusesAEntry 22 }
	
loadA OBJECT-TYPE
    SYNTAX Integer32
    MAX-ACCESS read-only
    STATUS current
    DESCRIPTION
        "Current in milliampere which flows throuth the fuse"
    ::= { fusesAEntry 23 }
	
labelA OBJECT-TYPE
    SYNTAX  OCTET STRING (SIZE (0..20))
    MAX-ACCESS read-write
    STATUS current
    DESCRIPTION
        "Label given for this fuse"
    ::= { fusesAEntry 24 }

nominalVoltageA OBJECT-TYPE
    SYNTAX  OCTET STRING (SIZE (0..9))
    MAX-ACCESS read-only
    STATUS current
    DESCRIPTION
        "Polarity and nominal voltage of the fuse in volt. E.g.: -48"
    ::= { fusesAEntry 25 }

multiEsxA OBJECT-TYPE
    SYNTAX Integer32
    MAX-ACCESS read-only
    STATUS current
    DESCRIPTION
        "MultiEsx: Fuses are connected in parallel to protect higher nominal loads: 0=not connected, 1=connected to a lower slot index, 2=connected as first"
    ::= { fusesAEntry 26 }


fusesBTable OBJECT-TYPE
    SYNTAX SEQUENCE OF FusesBEntry
    MAX-ACCESS not-accessible
    STATUS current
    DESCRIPTION
        " "
    ::= { feedB 10 }

fusesBEntry OBJECT-TYPE
    SYNTAX FusesBEntry
    MAX-ACCESS not-accessible
    STATUS current
    DESCRIPTION
        " "
    INDEX {indexB}
    
    ::= { fusesBTable 1 }
    
FusesBEntry ::= SEQUENCE {
		indexB			    Integer32,
        availableB          Integer32,
		deviceTypeB			Integer32,
		serialB			    Integer32,
		hwVersionB			Integer32,
		swVersionB			Integer32,
		nominalCurrentB		Integer32,
		errNoSysParB		Integer32,
		errCrcParamB		Integer32,
		errCrcProgB			Integer32,
		errIntMemB			Integer32,
		errControllerB		Integer32,
		errWatchdogB		Integer32,
		voltageB			Integer32,
		temperatureB		Integer32,
		loadOutputB			Integer32,
		statusShortB		Integer32,
		statusOverloadB		Integer32,
		statusUvltB			Integer32,
		statusOvltB			Integer32,
		statusOtmpB			Integer32,
		statusNoVccB		Integer32,
		loadB			    Integer32,
        	labelB              OCTET STRING
		nominalVoltageB		OCTET STRING,
		multiEsxB		Integer32
    }

indexB OBJECT-TYPE
    SYNTAX Integer32 (11..20)
    MAX-ACCESS not-accessible
    STATUS current
    DESCRIPTION
        "Fuse index"
    ::= { fusesBEntry 1 }

availableB OBJECT-TYPE
    SYNTAX Integer32
    MAX-ACCESS read-only
    STATUS current
    DESCRIPTION
        "Status of fuse: 0=no fuse, 1=fuse available"
    ::= { fusesBEntry 2 }

deviceTypeB OBJECT-TYPE
    SYNTAX Integer32
    MAX-ACCESS read-only
    STATUS current
    DESCRIPTION
        "Type number of the fuse"
    ::= { fusesBEntry 3 }

serialB OBJECT-TYPE
    SYNTAX Integer32
    MAX-ACCESS read-only
    STATUS current
    DESCRIPTION
        "Serial number of the fuse"
    ::= { fusesBEntry 4 }
	
hwVersionB OBJECT-TYPE
    SYNTAX Integer32
    MAX-ACCESS read-only
    STATUS current
    DESCRIPTION
        "Hardware version number of the fuse"
    ::= { fusesBEntry 5 }
	
swVersionB OBJECT-TYPE
    SYNTAX Integer32
    MAX-ACCESS read-only
    STATUS current
    DESCRIPTION
        "Software version number of the fuse"
    ::= { fusesBEntry 6 }
	
nominalCurrentB OBJECT-TYPE
    SYNTAX Integer32
    MAX-ACCESS read-only
    STATUS current
    DESCRIPTION
        "Nominal current of the fuse in milliampere"
    ::= { fusesBEntry 7 }
	
errNoSysParB OBJECT-TYPE
    SYNTAX Integer32
    MAX-ACCESS read-only
    STATUS current
    DESCRIPTION
        "No systemparameter available fault: 0=no fault, 1=fault"
    ::= { fusesBEntry 8 }
	
errCrcParamB OBJECT-TYPE
    SYNTAX Integer32
    MAX-ACCESS read-only
    STATUS current
    DESCRIPTION
        "Parameter CRC fault: 0=no fault, 1=fault"
    ::= { fusesBEntry 9 }
	
errCrcProgB OBJECT-TYPE
    SYNTAX Integer32
    MAX-ACCESS read-only
    STATUS current
    DESCRIPTION
        "Program memory CRC fault: 0=no fault, 1=fault"
    ::= { fusesBEntry 10 }
	
errIntMemB OBJECT-TYPE
    SYNTAX Integer32
    MAX-ACCESS read-only
    STATUS current
    DESCRIPTION
        "Internal memory fault: 0=no fault, 1=fault"
    ::= { fusesBEntry 11 }
	
errControllerB OBJECT-TYPE
    SYNTAX Integer32
    MAX-ACCESS read-only
    STATUS current
    DESCRIPTION
        "Controller fault: 0=no fault, 1=fault"
    ::= { fusesBEntry 12 }
	
errWatchdogB OBJECT-TYPE
    SYNTAX Integer32
    MAX-ACCESS read-only
    STATUS current
    DESCRIPTION
        "Watchdog reset fault: 0=no fault, 1=fault"
    ::= { fusesBEntry 13 }
	
voltageB OBJECT-TYPE
    SYNTAX Integer32
    MAX-ACCESS read-only
    STATUS current
    DESCRIPTION
        "Power supply voltage in millivolt"
    ::= { fusesBEntry 14 }
	
temperatureB OBJECT-TYPE
    SYNTAX Integer32
    MAX-ACCESS read-only
    STATUS current
    DESCRIPTION
        "Current temperature of the fuse in millivolt"
    ::= { fusesBEntry 15 }
	
loadOutputB OBJECT-TYPE
    SYNTAX Integer32 (0..1)
    MAX-ACCESS read-write
    STATUS current
    DESCRIPTION
        "Output status of the fuse: 0=output off, 1=output on"
    ::= { fusesBEntry 16 }
	
statusShortB OBJECT-TYPE
    SYNTAX Integer32
    MAX-ACCESS read-only
    STATUS current
    DESCRIPTION
        "Short is detected by this fuse: 0=no fault, 1=fault"
    ::= { fusesBEntry 17 }
	
statusOverloadB OBJECT-TYPE
    SYNTAX Integer32
    MAX-ACCESS read-only
    STATUS current
    DESCRIPTION
        "Overload status: 0=no overload, 1=overload"
    ::= { fusesBEntry 18 }
	
statusUvltB OBJECT-TYPE
    SYNTAX Integer32
    MAX-ACCESS read-only
    STATUS current
    DESCRIPTION
        "Undervoltage status: 0=no undervoltage, 1=undervoltage"
    ::= { fusesBEntry 19 }
	
statusOvltB OBJECT-TYPE
    SYNTAX Integer32
    MAX-ACCESS read-only
    STATUS current
    DESCRIPTION
        "Overvoltage status: 0=no overvoltage, 1=overvoltage"
    ::= { fusesBEntry 20 }
	
statusOtmpB OBJECT-TYPE
    SYNTAX Integer32
    MAX-ACCESS read-only
    STATUS current
    DESCRIPTION
        "Overtemperature status: 0=no overtemperature, 1=overtemperature"
    ::= { fusesBEntry 21 }
	
statusNoVccB OBJECT-TYPE
    SYNTAX Integer32
    MAX-ACCESS read-only
    STATUS current
    DESCRIPTION
        "No VCC status: 0=no VCC, 1=VCC ok"
    ::= { fusesBEntry 22 }
	
loadB OBJECT-TYPE
    SYNTAX Integer32
    MAX-ACCESS read-only
    STATUS current
    DESCRIPTION
        "Load current in milliampere which flows throuth the fuse"
    ::= { fusesBEntry 23 }

labelB OBJECT-TYPE
    SYNTAX OCTET STRING (SIZE (0..20))
    MAX-ACCESS read-write
    STATUS current
    DESCRIPTION
        "Label given for this fuse"
    ::= { fusesBEntry 24 }

nominalVoltageB OBJECT-TYPE
    SYNTAX  OCTET STRING (SIZE (0..9))
    MAX-ACCESS read-only
    STATUS current
    DESCRIPTION
        "Polarity and nominal voltage of the fuse in volt. E.g.: -48"
    ::= { fusesBEntry 25 }

multiEsxB OBJECT-TYPE
    SYNTAX Integer32
    MAX-ACCESS read-only
    STATUS current
    DESCRIPTION
        "MultiEsx: Fuses are connected in parallel to protect higher nominal loads: 0=not connected, 1=connected to a lower slot index, 2=connected as first"
    ::= { fusesBEntry 26 }


-- externalAlarms:
-- 1.3.6.1.4.1.44086.4.1.20.1.1
eaATable OBJECT-TYPE
    SYNTAX SEQUENCE OF EaAEntry
    MAX-ACCESS not-accessible
    STATUS current
    DESCRIPTION
        " "
    ::= { eaFeedA 1 }

eaAEntry OBJECT-TYPE
    SYNTAX EaAEntry
    MAX-ACCESS not-accessible
    STATUS current
    DESCRIPTION
        " "
    INDEX {eaIndexA}    
    ::= { eaATable 1 }
    
EaAEntry ::= SEQUENCE {
		eaIndexA		Integer32,
		eaAvailableA    Integer32,
		eaDeviceTypeA   Integer32,
		eaSerialA		Integer32,
		eaHwVersionA	Integer32,
		eaSwVersionA	Integer32,
		eaOutput1A		Integer32,
		eaOutput2A		Integer32,
		eaInput1A		Integer32,
		eaInput2A		Integer32,
		eaInput3A		Integer32,
		eaInput4A		Integer32,
		eaInput5A		Integer32,
		eaInput6A		Integer32,
		eaInput7A		Integer32,
		eaInput8A		Integer32,
		eaAnalogInputA	Integer32,
        eaLabelOutput1A OCTET STRING,
		eaLabelOutput2A OCTET STRING,
		eaLabelInput1A	OCTET STRING,
		eaLabelInput2A  OCTET STRING,
		eaLabelInput3A  OCTET STRING,
		eaLabelInput4A  OCTET STRING,
		eaLabelInput5A  OCTET STRING,
		eaLabelInput6A  OCTET STRING,
		eaLabelInput7A  OCTET STRING,
		eaLabelInput8A  OCTET STRING,
		eaLabelAnalogInputA		OCTET STRING,
		eaSignallingGroupOutput1A	OCTET STRING,
		eaSignallingActiveOutput1A	Integer32,
		eaSignallingGroupOutput2A	OCTET STRING,
		eaSignallingActiveOutput2A	Integer32,
		eaLogicFunctionOutput1A		OCTET STRING,
		eaLogicFunctionActiveOutput1A Integer32,
		eaLogicFunctionOutput2A		OCTET STRING,
		eaLogicFunctionActiveOutput2A Integer32
    }

eaIndexA OBJECT-TYPE
    SYNTAX Integer32 (1..20)
    MAX-ACCESS not-accessible
    STATUS current
    DESCRIPTION
        "Device index (slot number)"
    ::= { eaAEntry 1 }

eaAvailableA OBJECT-TYPE
    SYNTAX Integer32
    MAX-ACCESS read-only
    STATUS current
    DESCRIPTION
        "Status of the device: 0=no EAI device, 1=EEAI device available"
    ::= { eaAEntry 2 }

eaDeviceTypeA OBJECT-TYPE
    SYNTAX Integer32
    MAX-ACCESS read-only
    STATUS current
    DESCRIPTION
        "Type number of the device"
    ::= { eaAEntry 3 }

eaSerialA OBJECT-TYPE
    SYNTAX Integer32
    MAX-ACCESS read-only
    STATUS current
    DESCRIPTION
        "Serial number of the device"
    ::= { eaAEntry 4 }
	
eaHwVersionA OBJECT-TYPE
    SYNTAX Integer32
    MAX-ACCESS read-only
    STATUS current
    DESCRIPTION
        "Hardware version number of the device"
    ::= { eaAEntry 5 }
	
eaSwVersionA OBJECT-TYPE
    SYNTAX Integer32
    MAX-ACCESS read-only
    STATUS current
    DESCRIPTION
        "Software version number of the device"
    ::= { eaAEntry 6 }

eaOutput1A OBJECT-TYPE
    SYNTAX Integer32 (0..1)
    MAX-ACCESS read-write
    STATUS current
    DESCRIPTION
        "Status of the relay output1: 0=output off, 1=output on (contact to normaly close is closed)"
    ::= { eaAEntry 7 }
	
eaOutput2A OBJECT-TYPE
    SYNTAX Integer32 (0..1)
    MAX-ACCESS read-write
    STATUS current
    DESCRIPTION
        "Status of the relay output2: 0=output off, 1=output on (contact to normaly close is closed)"
    ::= { eaAEntry 8 }
	
eaInput1A OBJECT-TYPE
    SYNTAX Integer32
    MAX-ACCESS read-only
    STATUS current
    DESCRIPTION
        "Status digital input1: 0=low, 1=high"
    ::= { eaAEntry 9 }
	
eaInput2A OBJECT-TYPE
    SYNTAX Integer32
    MAX-ACCESS read-only
    STATUS current
    DESCRIPTION
        "Status digital input2: 0=low, 1=high"
    ::= { eaAEntry 10 }
	
eaInput3A OBJECT-TYPE
    SYNTAX Integer32
    MAX-ACCESS read-only
    STATUS current
    DESCRIPTION
        "Status digital input3: 0=low, 1=high"
    ::= { eaAEntry 11 }
	
eaInput4A OBJECT-TYPE
    SYNTAX Integer32
    MAX-ACCESS read-only
    STATUS current
    DESCRIPTION
        "Status digital input4: 0=low, 1=high"
    ::= { eaAEntry 12 }
	
eaInput5A OBJECT-TYPE
    SYNTAX Integer32
    MAX-ACCESS read-only
    STATUS current
    DESCRIPTION
        "Status digital input5: 0=low, 1=high"
    ::= { eaAEntry 13 }
	
eaInput6A OBJECT-TYPE
    SYNTAX Integer32
    MAX-ACCESS read-only
    STATUS current
    DESCRIPTION
        "Status digital input6: 0=low, 1=high"
    ::= { eaAEntry 14 }
	
eaInput7A OBJECT-TYPE
    SYNTAX Integer32
    MAX-ACCESS read-only
    STATUS current
    DESCRIPTION
        "Status digital input7: 0=low, 1=high"
    ::= { eaAEntry 15 }
	
eaInput8A OBJECT-TYPE
    SYNTAX Integer32
    MAX-ACCESS read-only
    STATUS current
    DESCRIPTION
        "Status digital input8: 0=low, 1=high"
    ::= { eaAEntry 16 }
	
eaAnalogInputA OBJECT-TYPE
    SYNTAX Integer32
    MAX-ACCESS read-only
    STATUS current
    DESCRIPTION
        "Analog current input in mA"
    ::= { eaAEntry 17 }

eaLabelOutput1A OBJECT-TYPE
    SYNTAX OCTET STRING (SIZE (0..20))
    MAX-ACCESS read-write
    STATUS current
    DESCRIPTION
        "Label for output1 of this EAI device"
    ::= { eaAEntry 18 }

eaLabelOutput2A OBJECT-TYPE
    SYNTAX OCTET STRING (SIZE (0..20))
    MAX-ACCESS read-write
    STATUS current
    DESCRIPTION
        "Label for output2 of this EAI device"
    ::= { eaAEntry 19 }
	
eaLabelInput1A OBJECT-TYPE
    SYNTAX OCTET STRING (SIZE (0..20))
    MAX-ACCESS read-write
    STATUS current
    DESCRIPTION
        "Label for input1 of this EAI device"
    ::= { eaAEntry 20 }

eaLabelInput2A OBJECT-TYPE
    SYNTAX OCTET STRING (SIZE (0..20))
    MAX-ACCESS read-write
    STATUS current
    DESCRIPTION
        "Label for input2 of this EAI device"
    ::= { eaAEntry 21 }
	
eaLabelInput3A OBJECT-TYPE
    SYNTAX OCTET STRING (SIZE (0..20))
    MAX-ACCESS read-write
    STATUS current
    DESCRIPTION
        "Label for input3 of this EAI device"
    ::= { eaAEntry 22 }
	
eaLabelInput4A OBJECT-TYPE
    SYNTAX OCTET STRING (SIZE (0..20))
    MAX-ACCESS read-write
    STATUS current
    DESCRIPTION
        "Label for input4 of this EAI device"
    ::= { eaAEntry 23 }
	
eaLabelInput5A OBJECT-TYPE
    SYNTAX OCTET STRING (SIZE (0..20))
    MAX-ACCESS read-write
    STATUS current
    DESCRIPTION
        "Label for input5 of this EAI device"
    ::= { eaAEntry 24 }
	
eaLabelInput6A OBJECT-TYPE
    SYNTAX OCTET STRING (SIZE (0..20))
    MAX-ACCESS read-write
    STATUS current
    DESCRIPTION
        "Label for input6 of this EAI device"
    ::= { eaAEntry 25 }
	
eaLabelInput7A OBJECT-TYPE
    SYNTAX OCTET STRING (SIZE (0..20))
    MAX-ACCESS read-write
    STATUS current
    DESCRIPTION
        "Label for input7 of this EAI device"
    ::= { eaAEntry 26 }
	
eaLabelInput8A OBJECT-TYPE
    SYNTAX OCTET STRING (SIZE (0..20))
    MAX-ACCESS read-write
    STATUS current
    DESCRIPTION
        "Label for input8 of this EAI device"
    ::= { eaAEntry 27 }
	
eaLabelAnalogInputA OBJECT-TYPE
    SYNTAX OCTET STRING (SIZE (0..20))
    MAX-ACCESS read-write
    STATUS current
    DESCRIPTION
        "Label for the analog input of this EAI device"
    ::= { eaAEntry 28 }
	
eaSignallingGroupOutput1A OBJECT-TYPE
    SYNTAX OCTET STRING (SIZE (20))
    MAX-ACCESS read-write
    STATUS current
    DESCRIPTION
        "Signalling function for output1. 
		 Syntax: 20 (for 20 slots) characters '0' or '1'.
		 '0'= signalling not active for this slot; '0'= signalling is active for this slot"
    ::= { eaAEntry 29 }
	
eaSignallingActiveOutput1A OBJECT-TYPE
    SYNTAX Integer32
    MAX-ACCESS read-only
    STATUS current
    DESCRIPTION
        "Status of signalling function for output1: 0=not active, 1=active"
    ::= { eaAEntry 30 }
	
eaSignallingGroupOutput2A OBJECT-TYPE
    SYNTAX OCTET STRING (SIZE (20))
    MAX-ACCESS read-write
    STATUS current
    DESCRIPTION
        "Signalling function for output2. 
		 Syntax: 20 (for 20 slots) characters '0' or '1'.
		 '0'= signalling not active for this slot; '0'= signalling is active for this slot"
    ::= { eaAEntry 31 }
	
eaSignallingActiveOutput2A OBJECT-TYPE
    SYNTAX Integer32
    MAX-ACCESS read-only
    STATUS current
    DESCRIPTION
        "Status of signalling function for output2: 0=not active, 1=active"
    ::= { eaAEntry 32 }

eaLogicFunctionOutput1A OBJECT-TYPE
    SYNTAX OCTET STRING (SIZE (0..40))
    MAX-ACCESS read-write
    STATUS current
    DESCRIPTION
        "Logic function for output1.
		 Length: 40 characters. Syntax: Logic connections '*'=AND, '+'=OR, '!'=Negation;
		 Signals: EAI digital input 'eai<slot address>in<input number>', ESX state 'esx<slot address><state>'"
    ::= { eaAEntry 33 }	
	
eaLogicFunctionActiveOutput1A OBJECT-TYPE
    SYNTAX Integer32
    MAX-ACCESS read-only
    STATUS current
    DESCRIPTION
        "Status of logic function for output1: 0=not active, 1=active"
    ::= { eaAEntry 34 }
	
eaLogicFunctionOutput2A OBJECT-TYPE
    SYNTAX OCTET STRING (SIZE (0..40))
    MAX-ACCESS read-write
    STATUS current
    DESCRIPTION
        "Logic function for output2.
		 Length: 40 characters. Syntax: Logic connections '*'=AND, '+'=OR, '!'=Negation;
		 Signals: EAI digital input 'eai<slot address>in<input number>', ESX state 'esx<slot address><state>'"
    ::= { eaAEntry 35 }	

eaLogicFunctionActiveOutput2A OBJECT-TYPE
    SYNTAX Integer32
    MAX-ACCESS read-only
    STATUS current
    DESCRIPTION
        "Status of logic function for output2: 0=not active, 1=active"
    ::= { eaAEntry 36 }




-- 1.3.6.1.4.1.44086.4.1.20.2.1
eaBTable OBJECT-TYPE
    SYNTAX SEQUENCE OF EaBEntry
    MAX-ACCESS not-accessible
    STATUS current
    DESCRIPTION
        " "
    ::= { eaFeedB 1 }

eaBEntry OBJECT-TYPE
    SYNTAX EaBEntry
    MAX-ACCESS not-accessible
    STATUS current
    DESCRIPTION
        " "
    INDEX {eaIndexB}    
    ::= { eaBTable 1 }
    
EaBEntry ::= SEQUENCE {
		eaIndexB		Integer32,
		eaAvailableB    Integer32,
		eaDeviceTypeB   Integer32,
		eaSerialB		Integer32,
		eaHwVersionB	Integer32,
		eaSwVersionB	Integer32,
		eaOutput1B		Integer32,
		eaOutput2B		Integer32,
		eaInput1B		Integer32,
		eaInput2B		Integer32,
		eaInput3B		Integer32,
		eaInput4B		Integer32,
		eaInput5B		Integer32,
		eaInput6B		Integer32,
		eaInput7B		Integer32,
		eaInput8B		Integer32,
		eaAnalogInputB	Integer32,
        eaLabelOutput1B OCTET STRING,
		eaLabelOutput2B OCTET STRING,
		eaLabelInput1B	OCTET STRING,
		eaLabelInput2B  OCTET STRING,
		eaLabelInput3B  OCTET STRING,
		eaLabelInput4B  OCTET STRING,
		eaLabelInput5B  OCTET STRING,
		eaLabelInput6B  OCTET STRING,
		eaLabelInput7B  OCTET STRING,
		eaLabelInput8B  OCTET STRING,
		eaLabelAnalogInputB		OCTET STRING,
		eaSignallingGroupOutput1B	OCTET STRING,
		eaSignallingActiveOutput1B	Integer32,
		eaSignallingGroupOutput2B	OCTET STRING,
		eaSignallingActiveOutput2B	Integer32,
		eaLogicFunctionOutput1B		OCTET STRING,
		eaLogicFunctionActiveOutput1B Integer32,
		eaLogicFunctionOutput2B		OCTET STRING,
		eaLogicFunctionActiveOutput2B Integer32
    }

eaIndexB OBJECT-TYPE
    SYNTAX Integer32 (1..20)
    MAX-ACCESS not-accessible
    STATUS current
    DESCRIPTION
        "Device index (slot number)"
    ::= { eaBEntry 1 }

eaAvailableB OBJECT-TYPE
    SYNTAX Integer32
    MAX-ACCESS read-only
    STATUS current
    DESCRIPTION
        "Status of the device: 0=no EAI device, 1=EEAI device available"
    ::= { eaBEntry 2 }

eaDeviceTypeB OBJECT-TYPE
    SYNTAX Integer32
    MAX-ACCESS read-only
    STATUS current
    DESCRIPTION
        "Type number of the device"
    ::= { eaBEntry 3 }

eaSerialB OBJECT-TYPE
    SYNTAX Integer32
    MAX-ACCESS read-only
    STATUS current
    DESCRIPTION
        "Serial number of the device"
    ::= { eaBEntry 4 }
	
eaHwVersionB OBJECT-TYPE
    SYNTAX Integer32
    MAX-ACCESS read-only
    STATUS current
    DESCRIPTION
        "Hardware version number of the device"
    ::= { eaBEntry 5 }
	
eaSwVersionB OBJECT-TYPE
    SYNTAX Integer32
    MAX-ACCESS read-only
    STATUS current
    DESCRIPTION
        "Software version number of the device"
    ::= { eaBEntry 6 }

eaOutput1B OBJECT-TYPE
    SYNTAX Integer32 (0..1)
    MAX-ACCESS read-write
    STATUS current
    DESCRIPTION
        "Status of the relay output1: 0=output off, 1=output on (contact to normaly close is closed)"
    ::= { eaBEntry 7 }
	
eaOutput2B OBJECT-TYPE
    SYNTAX Integer32 (0..1)
    MAX-ACCESS read-write
    STATUS current
    DESCRIPTION
        "Status of the relay output2: 0=output off, 1=output on (contact to normaly close is closed)"
    ::= { eaBEntry 8 }
	
eaInput1B OBJECT-TYPE
    SYNTAX Integer32
    MAX-ACCESS read-only
    STATUS current
    DESCRIPTION
        "Status digital input1: 0=low, 1=high"
    ::= { eaBEntry 9 }
	
eaInput2B OBJECT-TYPE
    SYNTAX Integer32
    MAX-ACCESS read-only
    STATUS current
    DESCRIPTION
        "Status digital input2: 0=low, 1=high"
    ::= { eaBEntry 10 }
	
eaInput3B OBJECT-TYPE
    SYNTAX Integer32
    MAX-ACCESS read-only
    STATUS current
    DESCRIPTION
        "Status digital input3: 0=low, 1=high"
    ::= { eaBEntry 11 }
	
eaInput4B OBJECT-TYPE
    SYNTAX Integer32
    MAX-ACCESS read-only
    STATUS current
    DESCRIPTION
        "Status digital input4: 0=low, 1=high"
    ::= { eaBEntry 12 }
	
eaInput5B OBJECT-TYPE
    SYNTAX Integer32
    MAX-ACCESS read-only
    STATUS current
    DESCRIPTION
        "Status digital input5: 0=low, 1=high"
    ::= { eaBEntry 13 }
	
eaInput6B OBJECT-TYPE
    SYNTAX Integer32
    MAX-ACCESS read-only
    STATUS current
    DESCRIPTION
        "Status digital input6: 0=low, 1=high"
    ::= { eaBEntry 14 }
	
eaInput7B OBJECT-TYPE
    SYNTAX Integer32
    MAX-ACCESS read-only
    STATUS current
    DESCRIPTION
        "Status digital input7: 0=low, 1=high"
    ::= { eaBEntry 15 }
	
eaInput8B OBJECT-TYPE
    SYNTAX Integer32
    MAX-ACCESS read-only
    STATUS current
    DESCRIPTION
        "Status digital input8: 0=low, 1=high"
    ::= { eaBEntry 16 }
	
eaAnalogInputB OBJECT-TYPE
    SYNTAX Integer32
    MAX-ACCESS read-only
    STATUS current
    DESCRIPTION
        "Analog current input in mA"
    ::= { eaBEntry 17 }

eaLabelOutput1B OBJECT-TYPE
    SYNTAX OCTET STRING (SIZE (0..20))
    MAX-ACCESS read-write
    STATUS current
    DESCRIPTION
        "Label for output1 of this EAI device"
    ::= { eaBEntry 18 }

eaLabelOutput2B OBJECT-TYPE
    SYNTAX OCTET STRING (SIZE (0..20))
    MAX-ACCESS read-write
    STATUS current
    DESCRIPTION
        "Label for output2 of this EAI device"
    ::= { eaBEntry 19 }
	
eaLabelInput1B OBJECT-TYPE
    SYNTAX OCTET STRING (SIZE (0..20))
    MAX-ACCESS read-write
    STATUS current
    DESCRIPTION
        "Label for input1 of this EAI device"
    ::= { eaBEntry 20 }

eaLabelInput2B OBJECT-TYPE
    SYNTAX OCTET STRING (SIZE (0..20))
    MAX-ACCESS read-write
    STATUS current
    DESCRIPTION
        "Label for input2 of this EAI device"
    ::= { eaBEntry 21 }
	
eaLabelInput3B OBJECT-TYPE
    SYNTAX OCTET STRING (SIZE (0..20))
    MAX-ACCESS read-write
    STATUS current
    DESCRIPTION
        "Label for input3 of this EAI device"
    ::= { eaBEntry 22 }
	
eaLabelInput4B OBJECT-TYPE
    SYNTAX OCTET STRING (SIZE (0..20))
    MAX-ACCESS read-write
    STATUS current
    DESCRIPTION
        "Label for input4 of this EAI device"
    ::= { eaBEntry 23 }
	
eaLabelInput5B OBJECT-TYPE
    SYNTAX OCTET STRING (SIZE (0..20))
    MAX-ACCESS read-write
    STATUS current
    DESCRIPTION
        "Label for input5 of this EAI device"
    ::= { eaBEntry 24 }
	
eaLabelInput6B OBJECT-TYPE
    SYNTAX OCTET STRING (SIZE (0..20))
    MAX-ACCESS read-write
    STATUS current
    DESCRIPTION
        "Label for input6 of this EAI device"
    ::= { eaBEntry 25 }
	
eaLabelInput7B OBJECT-TYPE
    SYNTAX OCTET STRING (SIZE (0..20))
    MAX-ACCESS read-write
    STATUS current
    DESCRIPTION
        "Label for input7 of this EAI device"
    ::= { eaBEntry 26 }
	
eaLabelInput8B OBJECT-TYPE
    SYNTAX OCTET STRING (SIZE (0..20))
    MAX-ACCESS read-write
    STATUS current
    DESCRIPTION
        "Label for input8 of this EAI device"
    ::= { eaBEntry 27 }
	
eaLabelAnalogInputB OBJECT-TYPE
    SYNTAX OCTET STRING (SIZE (0..20))
    MAX-ACCESS read-write
    STATUS current
    DESCRIPTION
        "Label for the analog input of this EAI device"
    ::= { eaBEntry 28 }
	
eaSignallingGroupOutput1B OBJECT-TYPE
    SYNTAX OCTET STRING (SIZE (20))
    MAX-ACCESS read-write
    STATUS current
    DESCRIPTION
        "Signalling function for output1. 
		 Syntax: 20 (for 20 slots) characters '0' or '1'.
		 '0'= signalling not active for this slot; '0'= signalling is active for this slot"
    ::= { eaBEntry 29 }
	
eaSignallingActiveOutput1B OBJECT-TYPE
    SYNTAX Integer32
    MAX-ACCESS read-only
    STATUS current
    DESCRIPTION
        "Status of signalling function for output1: 0=not active, 1=active"
    ::= { eaBEntry 30 }
	
eaSignallingGroupOutput2B OBJECT-TYPE
    SYNTAX OCTET STRING (SIZE (20))
    MAX-ACCESS read-write
    STATUS current
    DESCRIPTION
        "Signalling function for output2. 
		 Syntax: 20 (for 20 slots) characters '0' or '1'.
		 '0'= signalling not active for this slot; '0'= signalling is active for this slot"
    ::= { eaBEntry 31 }
	
eaSignallingActiveOutput2B OBJECT-TYPE
    SYNTAX Integer32
    MAX-ACCESS read-only
    STATUS current
    DESCRIPTION
        "Status of signalling function for output2: 0=not active, 1=active"
    ::= { eaBEntry 32 }

eaLogicFunctionOutput1B OBJECT-TYPE
    SYNTAX OCTET STRING (SIZE (0..40))
    MAX-ACCESS read-write
    STATUS current
    DESCRIPTION
        "Logic function for output1.
		 Length: 40 characters. Syntax: Logic connections '*'=AND, '+'=OR, '!'=Negation;
		 Signals: EAI digital input 'eai<slot address>in<input number>', ESX state 'esx<slot address><state>'"
    ::= { eaBEntry 33 }	
	
eaLogicFunctionActiveOutput1B OBJECT-TYPE
    SYNTAX Integer32
    MAX-ACCESS read-only
    STATUS current
    DESCRIPTION
        "Status of logic function for output1: 0=not active, 1=active"
    ::= { eaBEntry 34 }
	
eaLogicFunctionOutput2B OBJECT-TYPE
    SYNTAX OCTET STRING (SIZE (0..40))
    MAX-ACCESS read-write
    STATUS current
    DESCRIPTION
        "Logic function for output2.
		 Length: 40 characters. Syntax: Logic connections '*'=AND, '+'=OR, '!'=Negation;
		 Signals: EAI digital input 'eai<slot address>in<input number>', ESX state 'esx<slot address><state>'"
    ::= { eaBEntry 35 }	

eaLogicFunctionActiveOutput2B OBJECT-TYPE
    SYNTAX Integer32
    MAX-ACCESS read-only
    STATUS current
    DESCRIPTION
        "Status of logic function for output2: 0=not active, 1=active"
    ::= { eaBEntry 36 }



	
-- Traps object types
resetReason OBJECT-TYPE
    SYNTAX          OCTET STRING
    MAX-ACCESS      accessible-for-notify
    STATUS          current
    DESCRIPTION
        "Holds a human readable text which gives the reason for reset. Possible
         values are coldstart, warmstart or watchdog"
    ::= { systemObjects 1 }

failureReason OBJECT-TYPE
    SYNTAX          OCTET STRING
    MAX-ACCESS      accessible-for-notify
    STATUS          current
    DESCRIPTION
        "Holds a human readable text which gives the reason for system failure."
    ::= { systemObjects 2 }


fuseNr OBJECT-TYPE
    SYNTAX          OCTET STRING
    MAX-ACCESS      accessible-for-notify
    STATUS          current
    DESCRIPTION
        "Gives the number of a fuse"
    ::= { fusesObjects 1}
    
    
fuseLabel OBJECT-TYPE
    SYNTAX          OCTET STRING
    MAX-ACCESS      accessible-for-notify
    STATUS          current
    DESCRIPTION
        "Gives the label of a fuse"
    ::= { fusesObjects 2}
    

fuseOutputState OBJECT-TYPE
    SYNTAX          Integer32
    MAX-ACCESS      accessible-for-notify
    STATUS          current
    DESCRIPTION
        "Defines the output state of a fuse. 0 = Output off, 1 = Output on"
    ::= { fusesObjects 5}
    
    
fuseErrorRegister OBJECT-TYPE
    SYNTAX          Integer32
    MAX-ACCESS      accessible-for-notify
    STATUS          current
    DESCRIPTION
        "Defines the error register data type."
    ::= { fusesObjects 10}

fuseStatusShortCircuit OBJECT-TYPE
    SYNTAX          Integer32
    MAX-ACCESS      accessible-for-notify
    STATUS          current
    DESCRIPTION
        "Status register flag for short circuit"
    ::= { fusesObjects 20}

fuseStatusOverload OBJECT-TYPE
    SYNTAX          Integer32
    MAX-ACCESS      accessible-for-notify
    STATUS          current
    DESCRIPTION
        "Status register flag for overload"
    ::= { fusesObjects 21}

fuseStatusUndervoltage OBJECT-TYPE
    SYNTAX          Integer32
    MAX-ACCESS      accessible-for-notify
    STATUS          current
    DESCRIPTION
        "Status register flag for undervoltage"
    ::= { fusesObjects 22}

fuseStatusOvervoltage OBJECT-TYPE
    SYNTAX          Integer32
    MAX-ACCESS      accessible-for-notify
    STATUS          current
    DESCRIPTION
        "Status register flag for overvoltage"
    ::= { fusesObjects 23}

fuseStatusOvertemperature OBJECT-TYPE
    SYNTAX          Integer32
    MAX-ACCESS      accessible-for-notify
    STATUS          current
    DESCRIPTION
        "Status register flag for overtemperature"
    ::= { fusesObjects 24}

fuseStatusNoPowerSupply  OBJECT-TYPE
    SYNTAX          Integer32
    MAX-ACCESS      accessible-for-notify
    STATUS          current
    DESCRIPTION
        "Status register flag for no power supply"
    ::= { fusesObjects 25}
        
    
fuseOldNominalCurrent   OBJECT-TYPE
    SYNTAX          Integer32
    MAX-ACCESS      accessible-for-notify
    STATUS          current
    DESCRIPTION
        "The nominal current of the fuse which was located in this slot before."
    ::= { fusesObjects 30}
    
fuseNewNominalCurrent   OBJECT-TYPE
    SYNTAX          Integer32
    MAX-ACCESS      accessible-for-notify
    STATUS          current
    DESCRIPTION
        "The nominal current of the new fuse"
    ::= { fusesObjects 31}

-- Trap object types for external alarm interface

eaSlotNr OBJECT-TYPE
    SYNTAX          OCTET STRING
    MAX-ACCESS      accessible-for-notify
    STATUS          current
    DESCRIPTION
        "Gives the slot number of a external alarm device"
    ::= { externalAlarmObjects 1}
	
eaInputStates OBJECT-TYPE
    SYNTAX          OCTET STRING
    MAX-ACCESS      accessible-for-notify
    STATUS          current
    DESCRIPTION
        "Gives the input states of the external alarm device. [Left -> right: output 1 .. output n]"
    ::= { externalAlarmObjects 2}
	
eaOutputStates OBJECT-TYPE
    SYNTAX          OCTET STRING
    MAX-ACCESS      accessible-for-notify
    STATUS          current
    DESCRIPTION
        "Gives the output states of the external alarm device. [Left -> right: output 1 .. output n]"
    ::= { externalAlarmObjects 3}
		
eaFailureMsg OBJECT-TYPE
    SYNTAX          OCTET STRING
    MAX-ACCESS      accessible-for-notify
    STATUS          current
    DESCRIPTION
        "Gives a human readable text for a external alarm device failure."
    ::= { externalAlarmObjects 4}
	
eaMsg OBJECT-TYPE
    SYNTAX          OCTET STRING
    MAX-ACCESS      accessible-for-notify
    STATUS          current
    DESCRIPTION
        "Gives a human readable text for a external alarm device notification."
    ::= { externalAlarmObjects 5}

eaInputNr OBJECT-TYPE
    SYNTAX          Integer32
    MAX-ACCESS      accessible-for-notify
    STATUS          current
    DESCRIPTION
        "Gives the input Nr. of a external alarm device input. [1-8]"
    ::= { externalAlarmObjects 6}

eaInputLabel OBJECT-TYPE
    SYNTAX          OCTET STRING
    MAX-ACCESS      accessible-for-notify
    STATUS          current
    DESCRIPTION
        "Gives the label of a external alarm device input."
    ::= { externalAlarmObjects 7}

eaInputState OBJECT-TYPE
    SYNTAX          OCTET STRING
    MAX-ACCESS      accessible-for-notify
    STATUS          current
    DESCRIPTION
        "Gives the state of an external alarm device input. [raise/clear]"
    ::= { externalAlarmObjects 8}
	
eaOutputNr OBJECT-TYPE
    SYNTAX          Integer32
    MAX-ACCESS      accessible-for-notify
    STATUS          current
    DESCRIPTION
        "Gives the output Nr. of a external alarm device output. [1-2]"
    ::= { externalAlarmObjects 9}

eaOutputLabel OBJECT-TYPE
    SYNTAX          OCTET STRING
    MAX-ACCESS      accessible-for-notify
    STATUS          current
    DESCRIPTION
        "Gives the label of a external alarm device output."
    ::= { externalAlarmObjects 10}

eaOutputState OBJECT-TYPE
    SYNTAX          OCTET STRING
    MAX-ACCESS      accessible-for-notify
    STATUS          current
    DESCRIPTION
        "Gives the state of an external alarm device output. [raise/clear]"
    ::= { externalAlarmObjects 11}
	
-- Traps
powerUp NOTIFICATION-TYPE
	OBJECTS { resetReason }
	STATUS current
	DESCRIPTION
		"This notification is sent after a successful power up"
	::= { systemNotifications 1 }


systemFailure NOTIFICATION-TYPE
	OBJECTS { failureReason }
	STATUS current
	DESCRIPTION
		"If the system enters failure mode this Trap is sent"
	::= { systemNotifications 2 }



fuseNew NOTIFICATION-TYPE
	OBJECTS { fuseNr, fuseLabel }
	STATUS current
	DESCRIPTION
		"This Trap is sent if a new fuse was found"
	::= { fusesNotifications 1 }
	
fuseGone NOTIFICATION-TYPE
	OBJECTS { fuseNr, fuseLabel }
	STATUS current
	DESCRIPTION
		"Informs that a fuse which responds onto requests in the past does no longer 
		 respond."
	::= { fusesNotifications 2 }

fuseWrong NOTIFICATION-TYPE
	OBJECTS { fuseNr, fuseLabel, fuseNewNominalCurrent, fuseOldNominalCurrent }
	STATUS current
	DESCRIPTION
		"A recently added fuse has a different nominal current as the fuse in the same
		 slot had before."
	::= { fusesNotifications 3 }

fuseOutputStateChanged NOTIFICATION-TYPE
	OBJECTS { fuseNr, fuseLabel, fuseOutputState }
	STATUS current
	DESCRIPTION
		"Informs that the output state of a fuse had changed his status."
	::= { fusesNotifications 4 }

fuseFailure NOTIFICATION-TYPE
	OBJECTS { fuseNr, fuseLabel, fuseStatusShortCircuit, fuseStatusOverload, fuseStatusUndervoltage, fuseStatusOvervoltage, fuseStatusOvertemperature, fuseStatusNoPowerSupply, fuseErrorRegister }
	STATUS current
	DESCRIPTION
		"If any status or error flag changes, this trap is sent."
	::= { fusesNotifications 5 }
	
-- Traps for external alarm interface

eaNew NOTIFICATION-TYPE
	OBJECTS { eaSlotNr }
	STATUS current
	DESCRIPTION
		"This Trap is sent if a new external alarm device was found"
	::= { externalAlarmNotifications 1 }
	
eaGone NOTIFICATION-TYPE
	OBJECTS { eaSlotNr }
	STATUS current
	DESCRIPTION
		"Informs that a external alarm device, which responded onto requests in the past, does no longer 
		 respond."
	::= { externalAlarmNotifications 2 }
	
eaActiveFunctionWarning NOTIFICATION-TYPE
	OBJECTS { eaSlotNr, eaMsg }
	STATUS current
	DESCRIPTION
		"Informs that a logic- or signalling function is configured for a new plugged or pulled external alarm device."
	::= { externalAlarmNotifications 3 }

eaInternalError NOTIFICATION-TYPE
	OBJECTS { eaSlotNr, eaFailureMsg }
	STATUS current
	DESCRIPTION
		"Informs that a internal error of external alarm device occured"
	::= { externalAlarmNotifications 4 }
	
eaMasterWasNotAvailable NOTIFICATION-TYPE
	OBJECTS { eaMsg }
	STATUS current
	DESCRIPTION
		"Informs (one time) that a external alarm device detected, that the master device was not available for some time."
	::= { externalAlarmNotifications 5 }
	
eaInputChanged NOTIFICATION-TYPE
	OBJECTS { eaSlotNr, eaInputStates }
	STATUS current
	DESCRIPTION
		"Informs that a external alarm device input has changed its state; Summary for all inputs of one external alarm device."
	::= { externalAlarmNotifications 6 }
	
eaOutputChanged NOTIFICATION-TYPE
	OBJECTS { eaSlotNr, eaOutputStates }
	STATUS current
	DESCRIPTION
		"Informs that a external alarm device output has changed its state; Summary for all outputs of one external alarm device."
	::= { externalAlarmNotifications 7 }

eaSingleInputChanged NOTIFICATION-TYPE
	OBJECTS { eaSlotNr, eaInputNr, eaInputLabel, eaInputState }
	STATUS current
	DESCRIPTION
		"Informs that a external alarm device input has changed its state; Is sent for every changed input.
        If input changed high: 'raise'; If input changed low: 'clear'"
	::= { externalAlarmNotifications 8 }

eaSingleOutputChanged NOTIFICATION-TYPE
	OBJECTS { eaSlotNr, eaOutputNr, eaOutputLabel, eaOutputState }
	STATUS current
	DESCRIPTION
		"Informs that a external alarm device output has changed its state; Is sent for every changed output.
        If output changed high: 'raise'; If output changed low: 'clear'"
	::= { externalAlarmNotifications 9 }
	
END

-- MIB File: extreme-bgp4v2-tc.mib
EXTREME-BGP4V2-TC-MIB DEFINITIONS ::= BEGIN
     IMPORTS
         extremeAgent FROM EXTREME-BASE-MIB
         mib-2, MODULE-IDENTITY FROM SNMPv2-SMI
         TEXTUAL-CONVENTION FROM SNMPv2-TC;

     extremeBgp4V2TC MODULE-IDENTITY
             LAST-UPDATED "201811020000Z"
             ORGANIZATION "Extreme Networks, Inc."
             CONTACT-INFO
              "Postal: Extreme Networks, Inc.
                      6480 Via Del Oro
                      San Jose, CA 95119 USA
             Phone:   +1 408 579-2800
             E-mail:  support@extremenetworks.com
             WWW:     http://www.extremenetworks.com"

             DESCRIPTION
                     "Textual conventions for BGP-4.
                      This version is taken from
                      draft-ietf-idr-bgp4-mibv2-tc-mib-05 and
                      modified with 'extreme' prefix to
                      home it inside the Extreme enterprise space.
                      There are no modifications in the MIB objects as such.

                      Copyright (C) The IETF Trust (2014).  This
                      version of this MIB module is part of RFC XXX;
                      see the RFC itself for full legal notices."
 -- RFC Editor - replace XXX with RFC number

             REVISION "201811020000Z"
             DESCRIPTION
                    "Added the MIB in Extreme enterprise space since,
                     the RFC number is not allocated yet for this MIB."

             REVISION "201401230000Z"
             DESCRIPTION
                    "Initial version."
             ::= { extremeAgent 52 }

     --
     -- Textual Conventions
     --

     ExtremeBgp4V2IdentifierTC ::= TEXTUAL-CONVENTION
         DISPLAY-HINT "1d."
         STATUS       current
         DESCRIPTION
             "The representation of a BGP Identifier.  BGP Identifiers
              are presented in the received network byte order.

              The BGP Identifier is displayed as if it is an IP address,
              even if it would be an illegal one."
         REFERENCE
             "RFC 4273, Section 4.2"
         SYNTAX OCTET STRING(SIZE (4))

     ExtremeBgp4V2AddressFamilyIdentifierTC ::= TEXTUAL-CONVENTION
         STATUS       current
         DESCRIPTION
             "The representation of a BGP AFI.  The value of this object
              should be restricted to be between the values of 0 and
              65535."
         REFERENCE
             "RFC 4760, Section 3"
         SYNTAX INTEGER {
                 ipv4(1),
                 ipv6(2)
             }

     ExtremeBgp4V2SubsequentAddressFamilyIdentifierTC ::= TEXTUAL-CONVENTION
         STATUS       current
         DESCRIPTION
             "The representation of a BGP SAFI"
         REFERENCE
             "RFC 4760, Section 3.  The value of this object should be
              restricted to be between the values of 0 and 255."
         SYNTAX INTEGER {
                 unicast(1),
                 multicast(2),
                 mpls(4)
             }

 END

-- ################################################################################

EXTREMEdot11f-MIB DEFINITIONS ::= BEGIN 
	IMPORTS 

	MODULE-IDENTITY FROM SNMPv2-SMI
	extremeAP FROM EXTREME-BASE-MIB;


-- ********************************************************************** 
-- * MODULE IDENTITY 
-- ********************************************************************** 

	extremeDot11f MODULE-IDENTITY 
	LAST-UPDATED "0107020000Z" 
	ORGANIZATION "Extreme Networks"
	CONTACT-INFO 
		" "

	DESCRIPTION 
	"This MIB module provides management of IAPP on a set of APs.
	 It is functionally identical to the IAPP MIB from the IEEE
	 with the addition of a new index."
    ::= { extremeAP 22 }

END

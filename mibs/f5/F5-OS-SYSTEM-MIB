F5-OS-SYSTEM-MIB DEFINITIONS ::= BEGIN

IMPORTS
    MODULE-IDENTITY
        FROM SNMPv2-SMI
    platform
        FROM F5-COMMON-SMI-MIB
    ;

--================================================================
f5OsSystem MODULE-IDENTITY
    LAST-UPDATED "202204070000Z"
    ORGANIZATION "F5 Networks, Inc."
    CONTACT-INFO
         "postal: F5 Networks, Inc.
                  801 Fifth Avenue
                  Seattle, WA 98104
          phone:  (206) 272-6500
          email:  support@f5.com"
    DESCRIPTION
        "Top-level infrastructure of the F5OS System MIB tree."

    REVISION      "202204070000Z"
    DESCRIPTION
            "Initial revision."

    ::= { platform 3 }

--================================================================

f5OsSystemModelOIDs              OBJECT IDENTIFIER ::= { f5OsSystem 1 }

f5OsAppR5x00                     OBJECT IDENTIFIER ::= { f5OsSystemModelOIDs  1 }
f5OsAppR10x00                    OBJECT IDENTIFIER ::= { f5OsSystemModelOIDs  2 }
f5OsAppR2x00                     OBJECT IDENTIFIER ::= { f5OsSystemModelOIDs  3 }
f5OsAppR4x00                     OBJECT IDENTIFIER ::= { f5OsSystemModelOIDs  4 }
f5OsVelosCx410                   OBJECT IDENTIFIER ::= { f5OsSystemModelOIDs  5 }
f5OsVelosCx410Partition          OBJECT IDENTIFIER ::= { f5OsSystemModelOIDs  6 }

END

--
-- GEPON-OLT-COMMON-MIB.my
-- MIB generated by MG-SOFT Visual MIB Builder Version 5.0  Build 250
-- Monday, November 21, 2016 at 16:35:03
--

--  File Name : GEPONOLTCOMMONMIB.mib
-- Date      : Fri Sep 17 15:29:45 CST 2010
-- Author    : AdventNet Agent Toolkit C Edition  MibEditor 6
-- V2.001	replace stream by traffic,add some nodes to dslPerformance and so on CWT 20100118 
-- V2.002	add available number OID and available list OID for adsl pvc vlan    CWT 20100122
-- V2.003	imports dsl performance from rfc2662   								 CWT 20100126
-- v2.004        dslam performance selfdefinition,yangdan,20100210   
-- v2.005	add ftthLogicWhiteListTable and divide portEnable to two table       CWT 20100308

	GEPON-OLT-COMMON-MIB DEFINITIONS ::= BEGIN
 
		IMPORTS
			ifIndex			
				FROM IF-MIB			
			snmp			
				FROM RFC1213-MIB			
			OBJECT-GROUP, MODULE-COMPLIANCE			
				FROM SNMPv2-CONF			
			enterprises, TimeTicks, IpAddress, Integer32, Unsigned32, 
			Gauge32, Counter32, Counter64, OBJECT-TYPE, MODULE-IDENTITY			
				FROM SNMPv2-SMI			
			MacAddress, RowStatus, TruthValue, TimeStamp, DateAndTime, 
			TEXTUAL-CONVENTION			
				FROM SNMPv2-TC;
	
	
		-- 1.3.6.1.4.1.5875.800.1002.3
		fhOltDataObjModule MODULE-IDENTITY 
			LAST-UPDATED "201507071613Z"		-- July 07, 2015 at 16:13 GMT
			ORGANIZATION 
				"Organization:fiberhome."
			CONTACT-INFO 
				"Contact-info:contact fiberhome technical support"
			DESCRIPTION 
				"Description:Support fiberhome mib"
			REVISION "201507071614Z"		-- July 07, 2015 at 16:14 GMT
			DESCRIPTION 
				" "
			::= { fhOltDataGroup 3 }

		
	
--
-- Type definitions
--
	
--  textual conventions
		DisplayString ::= OCTET STRING

--                          This data type is used to model textual information taken
-- from the NVT ASCII character set.  By convention, objects
-- with this syntax are declared as having
-- 
--      SIZE (0..255)
		PhysAddress ::= OCTET STRING

	

-- Textual conventions
-- 
-- TEXTUALCONVENTIONS 
		MyTC ::= TEXTUAL-CONVENTION
			STATUS current
			DESCRIPTION 
				"TC Description"
			SYNTAX Integer32

	
--
-- Node definitions
--
		-- 1.3.6.1.4.1.5875
		fiberhome OBJECT IDENTIFIER ::= { enterprises 5875 }

				-- 1.3.6.1.4.1.5875.800
		standard OBJECT IDENTIFIER ::= { fiberhome 800 }

				-- 1.3.6.1.4.1.5875.800.3
		oltData OBJECT IDENTIFIER ::= { standard 3 }

				-- 1.3.6.1.4.1.5875.800.3.1
		onuWhiteList OBJECT IDENTIFIER ::= { oltData 1 }

				-- 1.3.6.1.4.1.5875.800.3.1.1
		onuPhysicalwhiteListTable OBJECT-TYPE
			SYNTAX SEQUENCE OF OnuPhysicalwhiteListEntry
			MAX-ACCESS not-accessible
			STATUS current
			DESCRIPTION
				"Description"
			::= { onuWhiteList 1 }

				-- 1.3.6.1.4.1.5875.800.3.1.1.1
		onuPhysicalwhiteListEntry OBJECT-TYPE
			SYNTAX OnuPhysicalwhiteListEntry
			MAX-ACCESS not-accessible
			STATUS current
			DESCRIPTION
				"Row Description"
			INDEX { onuAuthNo1 }
			::= { onuPhysicalwhiteListTable 1 }

		
		OnuPhysicalwhiteListEntry ::=
			SEQUENCE { 
				onuAuthNo1
					Unsigned32,
				onuSlotForPhysical
					Integer32,
				onuPonForPhysical
					Integer32,
				onuMacForPhysical
					OCTET STRING,
				actionForPhysical
					INTEGER
			 }

		-- 1.3.6.1.4.1.5875.800.3.1.1.1.1
		onuAuthNo1 OBJECT-TYPE
			SYNTAX Unsigned32 (1..1024)
			MAX-ACCESS read-only
			STATUS current
			DESCRIPTION
				"Column Description"
			::= { onuPhysicalwhiteListEntry 1 }

				-- 1.3.6.1.4.1.5875.800.3.1.1.1.2
		onuSlotForPhysical OBJECT-TYPE
			SYNTAX Integer32 (0..1024)
			MAX-ACCESS read-create
			STATUS current
			DESCRIPTION
				"SLOT Number"
			::= { onuPhysicalwhiteListEntry 2 }

				-- 1.3.6.1.4.1.5875.800.3.1.1.1.3
		onuPonForPhysical OBJECT-TYPE
			SYNTAX Integer32 (0..1024)
			MAX-ACCESS read-create
			STATUS current
			DESCRIPTION
				"PON Number"
			::= { onuPhysicalwhiteListEntry 3 }

				-- 1.3.6.1.4.1.5875.800.3.1.1.1.4
		onuMacForPhysical OBJECT-TYPE
			SYNTAX OCTET STRING
			MAX-ACCESS read-create
			STATUS current
			DESCRIPTION
				"Physical Authentication Identifier (MAC) "
			::= { onuPhysicalwhiteListEntry 4 }

				-- 1.3.6.1.4.1.5875.800.3.1.1.1.5
		actionForPhysical OBJECT-TYPE
			SYNTAX INTEGER
				{
				active(1),
				create(4),
				destroy(6)
				}
			MAX-ACCESS read-create
			STATUS current
			DESCRIPTION
				"4: Create
				6: Delete
				"
			::= { onuPhysicalwhiteListEntry 5 }

				-- 1.3.6.1.4.1.5875.800.3.1.2
		onuLogicWhiteListTable OBJECT-TYPE
			SYNTAX SEQUENCE OF OnuLogicWhiteListEntry
			MAX-ACCESS not-accessible
			STATUS current
			DESCRIPTION
				"Description"
			::= { onuWhiteList 2 }

				-- 1.3.6.1.4.1.5875.800.3.1.2.1
		onuLogicWhiteListEntry OBJECT-TYPE
			SYNTAX OnuLogicWhiteListEntry
			MAX-ACCESS not-accessible
			STATUS current
			DESCRIPTION
				"Row Description"
			INDEX { onuAuthNo2 }
			::= { onuLogicWhiteListTable 1 }

		
		OnuLogicWhiteListEntry ::=
			SEQUENCE { 
				onuAuthNo2
					Unsigned32,
				onuSlotForLogic
					Integer32,
				onuPonForLogic
					Integer32,
				onuSnForLogic
					OCTET STRING,
				onuSnPasswordForLogic
					OCTET STRING,
				actionForLogic
					INTEGER
			 }

		-- 1.3.6.1.4.1.5875.800.3.1.2.1.1
		onuAuthNo2 OBJECT-TYPE
			SYNTAX Unsigned32 (1..1024)
			MAX-ACCESS read-only
			STATUS current
			DESCRIPTION
				"Add the logical authentication whitelist "
			::= { onuLogicWhiteListEntry 1 }

				-- 1.3.6.1.4.1.5875.800.3.1.2.1.2
		onuSlotForLogic OBJECT-TYPE
			SYNTAX Integer32
			MAX-ACCESS read-create
			STATUS current
			DESCRIPTION
				"SLOT Number"
			::= { onuLogicWhiteListEntry 2 }

				-- 1.3.6.1.4.1.5875.800.3.1.2.1.3
		onuPonForLogic OBJECT-TYPE
			SYNTAX Integer32
			MAX-ACCESS read-create
			STATUS current
			DESCRIPTION
				"PON Number"
			::= { onuLogicWhiteListEntry 3 }

				-- 1.3.6.1.4.1.5875.800.3.1.2.1.4
		onuSnForLogic OBJECT-TYPE
			SYNTAX OCTET STRING
			MAX-ACCESS read-create
			STATUS current
			DESCRIPTION
				"Logical Authentication Identifier (SN)"
			::= { onuLogicWhiteListEntry 4 }

				-- 1.3.6.1.4.1.5875.800.3.1.2.1.5
		onuSnPasswordForLogic OBJECT-TYPE
			SYNTAX OCTET STRING
			MAX-ACCESS read-create
			STATUS current
			DESCRIPTION
				"Logical Authentication Password"
			::= { onuLogicWhiteListEntry 5 }

				-- 1.3.6.1.4.1.5875.800.3.1.2.1.6
		actionForLogic OBJECT-TYPE
			SYNTAX INTEGER
				{
				active(1),
				create(4),
				destroy(6)
				}
			MAX-ACCESS read-create
			STATUS current
			DESCRIPTION
				"4: Create
				6: Delete
				"
			::= { onuLogicWhiteListEntry 6 }

				-- 1.3.6.1.4.1.5875.800.3.1.3
		applyCommand OBJECT-TYPE
			SYNTAX Integer32 (0..1024)
			MAX-ACCESS read-write
			STATUS current
			DESCRIPTION
				"0x1093: logical whitelist application"
			::= { onuWhiteList 3 }

				-- 1.3.6.1.4.1.5875.800.3.1.4
		onuMacListFor5516Table OBJECT-TYPE
			SYNTAX SEQUENCE OF OnuMacListFor5516Entry
			MAX-ACCESS not-accessible
			STATUS current
			DESCRIPTION
				"Description"
			::= { onuWhiteList 4 }

				-- 1.3.6.1.4.1.5875.800.3.1.4.1
		onuMacListFor5516Entry OBJECT-TYPE
			SYNTAX OnuMacListFor5516Entry
			MAX-ACCESS not-accessible
			STATUS current
			DESCRIPTION
				"Row Description"
			INDEX { macListId }
			::= { onuMacListFor5516Table 1 }

		
		OnuMacListFor5516Entry ::=
			SEQUENCE { 
				macListId
					Integer32,
				slotNoForMacList
					Integer32,
				ponNoForMacList
					Integer32,
				onuNoForMacList
					Integer32,
				onuTypeForMacList
					Integer32,
				macForMacList
					MacAddress,
				passwordForMacList
					OCTET STRING,
				actionForMacList
					INTEGER
			 }

		-- 1.3.6.1.4.1.5875.800.3.1.4.1.1
		macListId OBJECT-TYPE
			SYNTAX Integer32 (1..1024)
			MAX-ACCESS read-only
			STATUS current
			DESCRIPTION
				"Physical Identifier Whitelist ID"
			::= { onuMacListFor5516Entry 1 }

		
--                   Physical Identifier Whitelist ID
		-- 1.3.6.1.4.1.5875.800.3.1.4.1.2
		slotNoForMacList OBJECT-TYPE
			SYNTAX Integer32 (0..1024)
			MAX-ACCESS read-create
			STATUS current
			DESCRIPTION
				"SLOT Number"
			::= { onuMacListFor5516Entry 2 }

				-- 1.3.6.1.4.1.5875.800.3.1.4.1.3
		ponNoForMacList OBJECT-TYPE
			SYNTAX Integer32 (0..1024)
			MAX-ACCESS read-create
			STATUS current
			DESCRIPTION
				"PON Number"
			::= { onuMacListFor5516Entry 3 }

				-- 1.3.6.1.4.1.5875.800.3.1.4.1.4
		onuNoForMacList OBJECT-TYPE
			SYNTAX Integer32 (0..1024)
			MAX-ACCESS read-create
			STATUS current
			DESCRIPTION
				"ONU Type"
			::= { onuMacListFor5516Entry 4 }

				-- 1.3.6.1.4.1.5875.800.3.1.4.1.5
		onuTypeForMacList OBJECT-TYPE
			SYNTAX Integer32 (0..1024)
			MAX-ACCESS read-create
			STATUS current
			DESCRIPTION
				"See ONU type correspondence table"
			::= { onuMacListFor5516Entry 5 }

				-- 1.3.6.1.4.1.5875.800.3.1.4.1.6
		macForMacList OBJECT-TYPE
			SYNTAX MacAddress (SIZE (6))
			MAX-ACCESS read-create
			STATUS current
			DESCRIPTION
				"MAC Address"
			::= { onuMacListFor5516Entry 6 }

				-- 1.3.6.1.4.1.5875.800.3.1.4.1.7
		passwordForMacList OBJECT-TYPE
			SYNTAX OCTET STRING
			MAX-ACCESS read-create
			STATUS current
			DESCRIPTION
				"If there is no password, leave it unfilled"
			::= { onuMacListFor5516Entry 7 }

				-- 1.3.6.1.4.1.5875.800.3.1.4.1.8
		actionForMacList OBJECT-TYPE
			SYNTAX INTEGER (1..10)
			MAX-ACCESS read-create
			STATUS current
			DESCRIPTION
				"4: create
				6: delete
				7: modify
				"
			::= { onuMacListFor5516Entry 8 }

				-- 1.3.6.1.4.1.5875.800.3.1.5
		onuSnListFor5516Table OBJECT-TYPE
			SYNTAX SEQUENCE OF OnuSnListFor5516Entry
			MAX-ACCESS not-accessible
			STATUS current
			DESCRIPTION
				"Description"
			::= { onuWhiteList 5 }

				-- 1.3.6.1.4.1.5875.800.3.1.5.1
		onuSnListFor5516Entry OBJECT-TYPE
			SYNTAX OnuSnListFor5516Entry
			MAX-ACCESS not-accessible
			STATUS current
			DESCRIPTION
				"Row Description"
			INDEX { snListId }
			::= { onuSnListFor5516Table 1 }

		
		OnuSnListFor5516Entry ::=
			SEQUENCE { 
				snListId
					Integer32,
				slotNoForSnList
					Integer32,
				ponNoForSnList
					Integer32,
				onuNoForSnList
					Integer32,
				onuTypeForSnList
					Integer32,
				snForSnList
					OCTET STRING,
				passwordForSnList
					OCTET STRING,
				actionForSnList
					RowStatus
			 }

		-- 1.3.6.1.4.1.5875.800.3.1.5.1.1
		snListId OBJECT-TYPE
			SYNTAX Integer32 (0..1024)
			MAX-ACCESS read-only
			STATUS current
			DESCRIPTION
				"SN Whitelist ID"
			::= { onuSnListFor5516Entry 1 }

				-- 1.3.6.1.4.1.5875.800.3.1.5.1.2
		slotNoForSnList OBJECT-TYPE
			SYNTAX Integer32
			MAX-ACCESS read-create
			STATUS current
			DESCRIPTION
				"SLOT Number"
			::= { onuSnListFor5516Entry 2 }

				-- 1.3.6.1.4.1.5875.800.3.1.5.1.3
		ponNoForSnList OBJECT-TYPE
			SYNTAX Integer32
			MAX-ACCESS read-create
			STATUS current
			DESCRIPTION
				"PON Number"
			::= { onuSnListFor5516Entry 3 }

				-- 1.3.6.1.4.1.5875.800.3.1.5.1.4
		onuNoForSnList OBJECT-TYPE
			SYNTAX Integer32
			MAX-ACCESS read-create
			STATUS current
			DESCRIPTION
				"ONU Number"
			::= { onuSnListFor5516Entry 4 }

				-- 1.3.6.1.4.1.5875.800.3.1.5.1.5
		onuTypeForSnList OBJECT-TYPE
			SYNTAX Integer32
			MAX-ACCESS read-create
			STATUS current
			DESCRIPTION
				"See ONU type correspondence table"
			::= { onuSnListFor5516Entry 5 }

				-- 1.3.6.1.4.1.5875.800.3.1.5.1.6
		snForSnList OBJECT-TYPE
			SYNTAX OCTET STRING
			MAX-ACCESS read-create
			STATUS current
			DESCRIPTION
				"SN"
			::= { onuSnListFor5516Entry 6 }

				-- 1.3.6.1.4.1.5875.800.3.1.5.1.7
		passwordForSnList OBJECT-TYPE
			SYNTAX OCTET STRING
			MAX-ACCESS read-create
			STATUS current
			DESCRIPTION
				"If there is no password, leave it unfilled."
			::= { onuSnListFor5516Entry 7 }

				-- 1.3.6.1.4.1.5875.800.3.1.5.1.8
		actionForSnList OBJECT-TYPE
			SYNTAX RowStatus
				{
				active(1),
				notInService(2),
				notReady(3),
				createAndGo(4),
				createAndWait(5),
				destroy(6)
				}
			MAX-ACCESS read-create
			STATUS current
			DESCRIPTION
				"4: create
				6:delete
				7:modify
				"
			::= { onuSnListFor5516Entry 8 }

				-- 1.3.6.1.4.1.5875.800.3.1.6
		onuPhyPasswordWhiteListTable OBJECT-TYPE
			SYNTAX SEQUENCE OF OnuPhyPasswordWhiteListEntry
			MAX-ACCESS not-accessible
			STATUS current
			DESCRIPTION
				"Description."
			::= { onuWhiteList 6 }

				-- 1.3.6.1.4.1.5875.800.3.1.6.1
		onuPhyPasswordWhiteListEntry OBJECT-TYPE
			SYNTAX OnuPhyPasswordWhiteListEntry
			MAX-ACCESS not-accessible
			STATUS current
			DESCRIPTION
				"Description."
			INDEX { phyPasswordWhiteListID }
			::= { onuPhyPasswordWhiteListTable 1 }

		
		OnuPhyPasswordWhiteListEntry ::=
			SEQUENCE { 
				phyPasswordWhiteListID
					Integer32,
				slotPhyPasswordWhiteList
					Integer32,
				ponPhyPasswordWhiteList
					Integer32,
				onuPhyPasswordWhiteList
					Integer32,
				onuPhyPasswordWhiteListType
					Integer32,
				phyPasswordWhiteList
					OCTET STRING,
				actionPhyPasswordWhiteList
					INTEGER
			 }
		-- 1.3.6.1.4.1.5875.800.3.1.6.1.1
		phyPasswordWhiteListID OBJECT-TYPE
			SYNTAX Integer32 (0..20000)
			MAX-ACCESS read-only
			STATUS current
			DESCRIPTION
				"Description."
			::= { onuPhyPasswordWhiteListEntry 1 }

				-- 1.3.6.1.4.1.5875.800.3.1.6.1.2
		slotPhyPasswordWhiteList OBJECT-TYPE
			SYNTAX Integer32
			MAX-ACCESS read-create
			STATUS current
			DESCRIPTION
				"Description."
			::= { onuPhyPasswordWhiteListEntry 2 }

				-- 1.3.6.1.4.1.5875.800.3.1.6.1.3
		ponPhyPasswordWhiteList OBJECT-TYPE
			SYNTAX Integer32
			MAX-ACCESS read-create
			STATUS current
			DESCRIPTION
				"Description."
			::= { onuPhyPasswordWhiteListEntry 3 }

				-- 1.3.6.1.4.1.5875.800.3.1.6.1.4
		onuPhyPasswordWhiteList OBJECT-TYPE
			SYNTAX Integer32
			MAX-ACCESS read-create
			STATUS current
			DESCRIPTION
				"Description."
			::= { onuPhyPasswordWhiteListEntry 4 }

				-- 1.3.6.1.4.1.5875.800.3.1.6.1.5
		onuPhyPasswordWhiteListType OBJECT-TYPE
			SYNTAX Integer32
			MAX-ACCESS read-create
			STATUS current
			DESCRIPTION
				"Description."
			::= { onuPhyPasswordWhiteListEntry 5 }

				-- 1.3.6.1.4.1.5875.800.3.1.6.1.7
		phyPasswordWhiteList OBJECT-TYPE
			SYNTAX OCTET STRING
			MAX-ACCESS read-create
			STATUS current
			DESCRIPTION
				"Description."
			::= { onuPhyPasswordWhiteListEntry 7 }

				-- 1.3.6.1.4.1.5875.800.3.1.6.1.8
		actionPhyPasswordWhiteList OBJECT-TYPE
			SYNTAX INTEGER (1..10)
			MAX-ACCESS read-create
			STATUS current
			DESCRIPTION
				"4: create
				6: delete
				7: modify
				"
			::= { onuPhyPasswordWhiteListEntry 8 }

				-- 1.3.6.1.4.1.5875.800.3.2
		interfaceEnable OBJECT IDENTIFIER ::= { oltData 2 }

				-- 1.3.6.1.4.1.5875.800.3.2.1
		voicePortEnableTable OBJECT-TYPE
			SYNTAX SEQUENCE OF VoicePortEnableEntry
			MAX-ACCESS not-accessible
			STATUS current
			DESCRIPTION
				"Description"
			::= { interfaceEnable 1 }

				-- 1.3.6.1.4.1.5875.800.3.2.1.1
		voicePortEnableEntry OBJECT-TYPE
			SYNTAX VoicePortEnableEntry
			MAX-ACCESS not-accessible
			STATUS current
			DESCRIPTION
				"Row Description"
			INDEX { potsIndex }
			::= { voicePortEnableTable 1 }

		
		VoicePortEnableEntry ::=
			SEQUENCE { 
				potsPortEnable
					INTEGER
			 }

		-- 1.3.6.1.4.1.5875.800.3.2.1.1.2
		potsPortEnable OBJECT-TYPE
			SYNTAX INTEGER
				{
				enable(1),
				disable(0)
				}
			MAX-ACCESS read-create
			STATUS current
			DESCRIPTION
				"0-disable
				1-enable"
			::= { voicePortEnableEntry 2 }

				-- 1.3.6.1.4.1.5875.800.3.2.2
		dataPortEnableTable OBJECT-TYPE
			SYNTAX SEQUENCE OF DataPortEnableEntry
			MAX-ACCESS not-accessible
			STATUS current
			DESCRIPTION
				"Description"
			::= { interfaceEnable 2 }

				-- 1.3.6.1.4.1.5875.800.3.2.2.1
		dataPortEnableEntry OBJECT-TYPE
			SYNTAX DataPortEnableEntry
			MAX-ACCESS not-accessible
			STATUS current
			DESCRIPTION
				"Row Description"
			INDEX { portIndex }
			::= { dataPortEnableTable 1 }

		
		DataPortEnableEntry ::=
			SEQUENCE { 
				dataPortEnable
					INTEGER
			 }

		-- 1.3.6.1.4.1.5875.800.3.2.2.1.2
		dataPortEnable OBJECT-TYPE
			SYNTAX INTEGER
				{
				enable(1),
				disable(0)
				}
			MAX-ACCESS read-create
			STATUS current
			DESCRIPTION
				"0-disable
				1-enable"
			::= { dataPortEnableEntry 2 }

				-- 1.3.6.1.4.1.5875.800.3.2.3
		oltPonEnableTable OBJECT-TYPE
			SYNTAX SEQUENCE OF OltPonEnableEntry
			MAX-ACCESS not-accessible
			STATUS current
			DESCRIPTION
				"Description"
			::= { interfaceEnable 3 }

				-- 1.3.6.1.4.1.5875.800.3.2.3.1
		oltPonEnableEntry OBJECT-TYPE
			SYNTAX OltPonEnableEntry
			MAX-ACCESS not-accessible
			STATUS current
			DESCRIPTION
				"Row Description"
			INDEX { ponIndex }
			::= { oltPonEnableTable 1 }

		
		OltPonEnableEntry ::=
			SEQUENCE { 
				oltPonEnable
					INTEGER
			 }

		-- 1.3.6.1.4.1.5875.800.3.2.3.1.1
		oltPonEnable OBJECT-TYPE
			SYNTAX INTEGER
				{
				enable(1),
				disable(0)
				}
			MAX-ACCESS read-create
			STATUS current
			DESCRIPTION
				"Column Description:
				1:enable
				0:disable"
			::= { oltPonEnableEntry 1 }

				-- 1.3.6.1.4.1.5875.800.3.3
		onuPortConfig OBJECT IDENTIFIER ::= { oltData 3 }

				-- 1.3.6.1.4.1.5875.800.3.3.1
		bandwidthProfileTable OBJECT-TYPE
			SYNTAX SEQUENCE OF BandwidthProfileEntry
			MAX-ACCESS not-accessible
			STATUS current
			DESCRIPTION
				"Description"
			::= { onuPortConfig 1 }

				-- 1.3.6.1.4.1.5875.800.3.3.1.1
		bandwidthProfileEntry OBJECT-TYPE
			SYNTAX BandwidthProfileEntry
			MAX-ACCESS not-accessible
			STATUS current
			DESCRIPTION
				"Row Description"
			INDEX { bandwidthProfileId }
			::= { bandwidthProfileTable 1 }

		
		BandwidthProfileEntry ::=
			SEQUENCE { 
				bandwidthProfileId
					Integer32,
				bandwidthProfileName
					OCTET STRING,
				upMinRate
					Integer32,
				upMaxRate
					Integer32,
				downMinRate
					Integer32,
				downMaxRate
					Integer32,
				fixedRate
					Integer32,
				bandwidthProfileAction
					INTEGER
			 }

		-- 1.3.6.1.4.1.5875.800.3.3.1.1.1
		bandwidthProfileId OBJECT-TYPE
			SYNTAX Integer32 (1..1024)
			MAX-ACCESS read-only
			STATUS current
			DESCRIPTION
				"Profile ID (Index) "
			::= { bandwidthProfileEntry 1 }

				-- 1.3.6.1.4.1.5875.800.3.3.1.1.2
		bandwidthProfileName OBJECT-TYPE
			SYNTAX OCTET STRING
			MAX-ACCESS read-create
			STATUS current
			DESCRIPTION
				"Profile Name
				The max length of name is 20"
			::= { bandwidthProfileEntry 2 }

				-- 1.3.6.1.4.1.5875.800.3.3.1.1.3
		upMinRate OBJECT-TYPE
			SYNTAX Integer32 (0..1024)
			MAX-ACCESS read-create
			STATUS current
			DESCRIPTION
				"Major parameter
				0??1000000"
			::= { bandwidthProfileEntry 3 }

				-- 1.3.6.1.4.1.5875.800.3.3.1.1.4
		upMaxRate OBJECT-TYPE
			SYNTAX Integer32 (0..1024)
			MAX-ACCESS read-create
			STATUS current
			DESCRIPTION
				"Service Uplink Maximum Allowed Bandwidth
				256??10000000"
			::= { bandwidthProfileEntry 4 }

				-- 1.3.6.1.4.1.5875.800.3.3.1.1.5
		downMinRate OBJECT-TYPE
			SYNTAX Integer32 (0..1024)
			MAX-ACCESS read-create
			STATUS current
			DESCRIPTION
				"Major parameter
				0-1000000"
			::= { bandwidthProfileEntry 5 }

				-- 1.3.6.1.4.1.5875.800.3.3.1.1.6
		downMaxRate OBJECT-TYPE
			SYNTAX Integer32 (0..1024)
			MAX-ACCESS read-create
			STATUS current
			DESCRIPTION
				"Service Downlink Maximum Allowed Bandwidth
				256??10000000"
			::= { bandwidthProfileEntry 6 }

				-- 1.3.6.1.4.1.5875.800.3.3.1.1.7
		fixedRate OBJECT-TYPE
			SYNTAX Integer32 (0..1024)
			MAX-ACCESS read-create
			STATUS current
			DESCRIPTION
				"Service Uplink Fixed Allocated Bandwidth
				0??1000000"
			::= { bandwidthProfileEntry 7 }

				-- 1.3.6.1.4.1.5875.800.3.3.1.1.12
		bandwidthProfileAction OBJECT-TYPE
			SYNTAX INTEGER
				{
				active(1),
				create(4),
				destroy(6),
				modify(7)
				}
			MAX-ACCESS read-create
			STATUS current
			DESCRIPTION
				"4:create
				6:delete
				7:modify
				"
			::= { bandwidthProfileEntry 12 }

				-- 1.3.6.1.4.1.5875.800.3.3.2
		attachPortBandwidthProfileTable OBJECT-TYPE
			SYNTAX SEQUENCE OF AttachPortBandwidthProfileEntry
			MAX-ACCESS not-accessible
			STATUS current
			DESCRIPTION
				"Description"
			::= { onuPortConfig 2 }

				-- 1.3.6.1.4.1.5875.800.3.3.2.1
		attachPortBandwidthProfileEntry OBJECT-TYPE
			SYNTAX AttachPortBandwidthProfileEntry
			MAX-ACCESS not-accessible
			STATUS current
			DESCRIPTION
				"Row Description"
			INDEX { fttbIfIndex }
			::= { attachPortBandwidthProfileTable 1 }

		
		AttachPortBandwidthProfileEntry ::=
			SEQUENCE { 
				fttbIfIndex
					Unsigned32,
				attachBandwidthProfileId
					Integer32,
				attachBandwidthProfileName
					OCTET STRING,
				unAttatchPortAttributeProfileAction
					Integer32
			 }

		-- 1.3.6.1.4.1.5875.800.3.3.2.1.1
		fttbIfIndex OBJECT-TYPE
			SYNTAX Unsigned32 (1..1024)
			MAX-ACCESS read-only
			STATUS current
			DESCRIPTION
				"Port Index"
			::= { attachPortBandwidthProfileEntry 1 }

				-- 1.3.6.1.4.1.5875.800.3.3.2.1.2
		attachBandwidthProfileId OBJECT-TYPE
			SYNTAX Integer32 (0..1024)
			MAX-ACCESS read-create
			STATUS current
			DESCRIPTION
				"Profile ID Binding"
			::= { attachPortBandwidthProfileEntry 2 }

				-- 1.3.6.1.4.1.5875.800.3.3.2.1.4
		attachBandwidthProfileName OBJECT-TYPE
			SYNTAX OCTET STRING
			MAX-ACCESS read-create
			STATUS current
			DESCRIPTION
				"Profile Name Binding
				The max length of name is 20"
			::= { attachPortBandwidthProfileEntry 4 }

				-- 1.3.6.1.4.1.5875.800.3.3.2.1.5
		unAttatchPortAttributeProfileAction OBJECT-TYPE
			SYNTAX Integer32 (0..1)
			MAX-ACCESS read-create
			STATUS current
			DESCRIPTION
				"0: unbind"
			::= { attachPortBandwidthProfileEntry 5 }

				-- 1.3.6.1.4.1.5875.800.3.3.3
		portAttributeProfileTable OBJECT-TYPE
			SYNTAX SEQUENCE OF PortAttributeProfileEntry
			MAX-ACCESS not-accessible
			STATUS current
			DESCRIPTION
				"Description"
			::= { onuPortConfig 3 }

				-- 1.3.6.1.4.1.5875.800.3.3.3.1
		portAttributeProfileEntry OBJECT-TYPE
			SYNTAX PortAttributeProfileEntry
			MAX-ACCESS not-accessible
			STATUS current
			DESCRIPTION
				"Row Description"
			INDEX { portAttributeProfileId }
			::= { portAttributeProfileTable 1 }

		
		PortAttributeProfileEntry ::=
			SEQUENCE { 
				portAttributeProfileId
					Integer32,
				portAttributeProfileName
					OCTET STRING,
				autoNegotiation
					INTEGER,
				speed
					Integer32,
				duplex
					INTEGER,
				flowControl
					INTEGER,
				portAttributeProfileAction
					INTEGER
			 }

		-- 1.3.6.1.4.1.5875.800.3.3.3.1.1
		portAttributeProfileId OBJECT-TYPE
			SYNTAX Integer32 (1..1024)
			MAX-ACCESS read-only
			STATUS current
			DESCRIPTION
				"Profile ID (Index)"
			::= { portAttributeProfileEntry 1 }

				-- 1.3.6.1.4.1.5875.800.3.3.3.1.2
		portAttributeProfileName OBJECT-TYPE
			SYNTAX OCTET STRING
			MAX-ACCESS read-create
			STATUS current
			DESCRIPTION
				"Profile Name
				The max length of name is 20"
			::= { portAttributeProfileEntry 2 }

				-- 1.3.6.1.4.1.5875.800.3.3.3.1.3
		autoNegotiation OBJECT-TYPE
			SYNTAX INTEGER
				{
				enable(1),
				disable(0),
				disableFor5116(2)
				}
			MAX-ACCESS read-create
			STATUS current
			DESCRIPTION
				"5516:
				1: Enable
				0: Disable
				5116: 
				1: Enable
				2: Disable
				"
			::= { portAttributeProfileEntry 3 }

				-- 1.3.6.1.4.1.5875.800.3.3.3.1.4
		speed OBJECT-TYPE
			SYNTAX Integer32 (0..2)
			MAX-ACCESS read-create
			STATUS current
			DESCRIPTION
				"0: 10M
				1: 100M
				2: 1000M
				"
			::= { portAttributeProfileEntry 4 }

				-- 1.3.6.1.4.1.5875.800.3.3.3.1.5
		duplex OBJECT-TYPE
			SYNTAX INTEGER
				{
				enable(1),
				disable(0)
				}
			MAX-ACCESS read-create
			STATUS current
			DESCRIPTION
				"1: Enable
				0: Disable
				"
			::= { portAttributeProfileEntry 5 }

				-- 1.3.6.1.4.1.5875.800.3.3.3.1.6
		flowControl OBJECT-TYPE
			SYNTAX INTEGER
				{
				enable(1),
				disable(0)
				}
			MAX-ACCESS read-create
			STATUS current
			DESCRIPTION
				"Column Description:
				1:enable
				0:disable"
			::= { portAttributeProfileEntry 6 }

				-- 1.3.6.1.4.1.5875.800.3.3.3.1.10
		portAttributeProfileAction OBJECT-TYPE
			SYNTAX INTEGER
				{
				active(1),
				create(4),
				destroy(6),
				modify(7)
				}
			MAX-ACCESS read-create
			STATUS current
			DESCRIPTION
				"Column Description
				4:create
				6:destroy
				7:modify"
			::= { portAttributeProfileEntry 10 }

				-- 1.3.6.1.4.1.5875.800.3.3.4
		attachPortAttributeProfileTable OBJECT-TYPE
			SYNTAX SEQUENCE OF AttachPortAttributeProfileEntry
			MAX-ACCESS not-accessible
			STATUS current
			DESCRIPTION
				"Description"
			::= { onuPortConfig 4 }

				-- 1.3.6.1.4.1.5875.800.3.3.4.1
		attachPortAttributeProfileEntry OBJECT-TYPE
			SYNTAX AttachPortAttributeProfileEntry
			MAX-ACCESS not-accessible
			STATUS current
			DESCRIPTION
				"Row Description"
			INDEX { portIndex }
			::= { attachPortAttributeProfileTable 1 }

		
		AttachPortAttributeProfileEntry ::=
			SEQUENCE { 
				attachPortAttributeProfileName
					OCTET STRING,
				setDefaultPortAttributeProfileAction
					Integer32
			 }
		-- 1.3.6.1.4.1.5875.800.3.3.4.1.1
		attachPortAttributeProfileName OBJECT-TYPE
			SYNTAX OCTET STRING
			MAX-ACCESS read-create
			STATUS current
			DESCRIPTION
				"Profile Name Binding
				The max length of name is 20"
			::= { attachPortAttributeProfileEntry 1 }

				-- 1.3.6.1.4.1.5875.800.3.3.4.1.2
		setDefaultPortAttributeProfileAction OBJECT-TYPE
			SYNTAX Integer32 (0..1)
			MAX-ACCESS read-create
			STATUS current
			DESCRIPTION
				"0: unbind"
			::= { attachPortAttributeProfileEntry 2 }

				-- 1.3.6.1.4.1.5875.800.3.3.5
		ponBandwidthProfileTable OBJECT-TYPE
			SYNTAX SEQUENCE OF PonBandwidthProfileEntry
			MAX-ACCESS not-accessible
			STATUS current
			DESCRIPTION
				"Description"
			::= { onuPortConfig 5 }

				-- 1.3.6.1.4.1.5875.800.3.3.5.1
		ponBandwidthProfileEntry OBJECT-TYPE
			SYNTAX PonBandwidthProfileEntry
			MAX-ACCESS not-accessible
			STATUS current
			DESCRIPTION
				"Row Description"
			INDEX { ponBandwidthProfileId }
			::= { ponBandwidthProfileTable 1 }

		
		PonBandwidthProfileEntry ::=
			SEQUENCE { 
				ponBandwidthProfileId
					Integer32,
				ponBandwidthProfileName
					OCTET STRING,
				ponUpMinRate
					Integer32,
				ponUpMaxRate
					Integer32,
				ponDownMinRate
					Integer32,
				ponDownMaxRate
					Integer32,
				ponFixedRate
					Integer32,
				ponBandwidthProfileAction
					INTEGER
			 }
		-- 1.3.6.1.4.1.5875.800.3.3.5.1.1
		ponBandwidthProfileId OBJECT-TYPE
			SYNTAX Integer32 (1..1024)
			MAX-ACCESS read-only
			STATUS current
			DESCRIPTION
				"Profile ID (Index) "
			::= { ponBandwidthProfileEntry 1 }

				-- 1.3.6.1.4.1.5875.800.3.3.5.1.2
		ponBandwidthProfileName OBJECT-TYPE
			SYNTAX OCTET STRING
			MAX-ACCESS read-create
			STATUS current
			DESCRIPTION
				"Profile Name
				The max length of name is 20"
			::= { ponBandwidthProfileEntry 2 }

				-- 1.3.6.1.4.1.5875.800.3.3.5.1.3
		ponUpMinRate OBJECT-TYPE
			SYNTAX Integer32 (0..1024)
			MAX-ACCESS read-create
			STATUS current
			DESCRIPTION
				"Unit??kbps
				0-1000000
				"
			::= { ponBandwidthProfileEntry 3 }

				-- 1.3.6.1.4.1.5875.800.3.3.5.1.4
		ponUpMaxRate OBJECT-TYPE
			SYNTAX Integer32 (0..1024)
			MAX-ACCESS read-create
			STATUS current
			DESCRIPTION
				"Unit??kbps
				256-1000000
				"
			::= { ponBandwidthProfileEntry 4 }

				-- 1.3.6.1.4.1.5875.800.3.3.5.1.5
		ponDownMinRate OBJECT-TYPE
			SYNTAX Integer32 (0..1024)
			MAX-ACCESS read-create
			STATUS current
			DESCRIPTION
				"Unit??kbps
				0-1000000
				"
			::= { ponBandwidthProfileEntry 5 }

				-- 1.3.6.1.4.1.5875.800.3.3.5.1.6
		ponDownMaxRate OBJECT-TYPE
			SYNTAX Integer32 (0..1024)
			MAX-ACCESS read-create
			STATUS current
			DESCRIPTION
				"Unit??kbps
				256-1000000
				"
			::= { ponBandwidthProfileEntry 6 }

				-- 1.3.6.1.4.1.5875.800.3.3.5.1.7
		ponFixedRate OBJECT-TYPE
			SYNTAX Integer32 (0..1024)
			MAX-ACCESS read-create
			STATUS current
			DESCRIPTION
				"5516??
				Unit??kbps
				0-1000000
				"
			::= { ponBandwidthProfileEntry 7 }

				-- 1.3.6.1.4.1.5875.800.3.3.5.1.12
		ponBandwidthProfileAction OBJECT-TYPE
			SYNTAX INTEGER
				{
				active(1),
				create(4),
				destroy(6),
				modify(7)
				}
			MAX-ACCESS read-create
			STATUS current
			DESCRIPTION
				"4:create
				6:delete"
			::= { ponBandwidthProfileEntry 12 }

				-- 1.3.6.1.4.1.5875.800.3.3.6
		attachPonBandwidthProfileTable OBJECT-TYPE
			SYNTAX SEQUENCE OF AttachPonBandwidthProfileEntry
			MAX-ACCESS not-accessible
			STATUS current
			DESCRIPTION
				"Description"
			::= { onuPortConfig 6 }

				-- 1.3.6.1.4.1.5875.800.3.3.6.1
		attachPonBandwidthProfileEntry OBJECT-TYPE
			SYNTAX AttachPonBandwidthProfileEntry
			MAX-ACCESS not-accessible
			STATUS current
			DESCRIPTION
				"Row Description"
			INDEX { fttbIfIndex }
			::= { attachPonBandwidthProfileTable 1 }

		
		AttachPonBandwidthProfileEntry ::=
			SEQUENCE { 
				onuPonIfIndex
					Unsigned32,
				attachPonBandwidthProfileId
					Integer32,
				attachPonBandwidthProfileName
					OCTET STRING,
				unAttatchPonBandwidthProfileAction
					Integer32
			 }
		-- 1.3.6.1.4.1.5875.800.3.3.6.1.1
		onuPonIfIndex OBJECT-TYPE
			SYNTAX Unsigned32
			MAX-ACCESS read-only
			STATUS current
			DESCRIPTION
				"Port Index"
			::= { attachPonBandwidthProfileEntry 1 }

				-- 1.3.6.1.4.1.5875.800.3.3.6.1.2
		attachPonBandwidthProfileId OBJECT-TYPE
			SYNTAX Integer32 (0..1024)
			MAX-ACCESS read-create
			STATUS current
			DESCRIPTION
				"Profile ID"
			::= { attachPonBandwidthProfileEntry 2 }

				-- 1.3.6.1.4.1.5875.800.3.3.6.1.3
		attachPonBandwidthProfileName OBJECT-TYPE
			SYNTAX OCTET STRING
			MAX-ACCESS read-create
			STATUS current
			DESCRIPTION
				"Profile Name Binding
				The max length of name is 20"
			::= { attachPonBandwidthProfileEntry 3 }

				-- 1.3.6.1.4.1.5875.800.3.3.6.1.4
		unAttatchPonBandwidthProfileAction OBJECT-TYPE
			SYNTAX Integer32 (0..1)
			MAX-ACCESS read-create
			STATUS current
			DESCRIPTION
				"0: unbind"
			::= { attachPonBandwidthProfileEntry 4 }

				-- 1.3.6.1.4.1.5875.800.3.3.10
		getNextPortProfileId OBJECT IDENTIFIER ::= { onuPortConfig 10 }

				-- 1.3.6.1.4.1.5875.800.3.3.10.1
		getNextBandwidthProfileId OBJECT-TYPE
			SYNTAX Integer32
			MAX-ACCESS read-only
			STATUS current
			DESCRIPTION
				"Leaf node"
			::= { getNextPortProfileId 1 }

				-- 1.3.6.1.4.1.5875.800.3.3.10.2
		getNextPortAttributeProfileId OBJECT-TYPE
			SYNTAX Integer32
			MAX-ACCESS read-only
			STATUS current
			DESCRIPTION
				"Leaf node"
			::= { getNextPortProfileId 2 }

				-- 1.3.6.1.4.1.5875.800.3.3.10.3
		getNextPonBandwidthProfileId OBJECT-TYPE
			SYNTAX Integer32
			MAX-ACCESS read-only
			STATUS current
			DESCRIPTION
				"Leaf node"
			::= { getNextPortProfileId 3 }

				-- 1.3.6.1.4.1.5875.800.3.5
		feServiceConfigure OBJECT IDENTIFIER ::= { oltData 5 }

				-- 1.3.6.1.4.1.5875.800.3.5.1
		feServiceCfgTable OBJECT-TYPE
			SYNTAX SEQUENCE OF FeServiceCfgEntry
			MAX-ACCESS not-accessible
			STATUS current
			DESCRIPTION
				"Description"
			::= { feServiceConfigure 1 }

				-- 1.3.6.1.4.1.5875.800.3.5.1.1
		feServiceCfgEntry OBJECT-TYPE
			SYNTAX FeServiceCfgEntry
			MAX-ACCESS not-accessible
			STATUS current
			DESCRIPTION
				"Row Description"
			INDEX { portIndex, serviceId }
			::= { feServiceCfgTable 1 }

		
		FeServiceCfgEntry ::=
			SEQUENCE { 
				serviceId
					Integer32,
				serviceType
					Integer32,
				cvlanMode
					INTEGER,
				cvlan
					Integer32,
				cvlanCos
					Integer32,
				tvlan
					Integer32,
				tvlanCos
					Integer32,
				svlan
					Integer32,
				svlanCos
					Integer32,
				upMinBandWidth
					Integer32,
				upManBandWidth
					Integer32,
				dnBandWidth
					Integer32,
				serviceVlanName
					OCTET STRING,
				qinqProfileName
					OCTET STRING,
				feServiceCfgAction
					INTEGER
			 }
		-- 1.3.6.1.4.1.5875.800.3.5.1.1.1
		serviceId OBJECT-TYPE
			SYNTAX Integer32 (1..1024)
			MAX-ACCESS read-only
			STATUS current
			DESCRIPTION
				"1 -16"
			::= { feServiceCfgEntry 1 }

				-- 1.3.6.1.4.1.5875.800.3.5.1.1.2
		serviceType OBJECT-TYPE
			SYNTAX Integer32 (0..1)
			MAX-ACCESS read-create
			STATUS current
			DESCRIPTION
				"Data service configuration"
			::= { feServiceCfgEntry 2 }

				-- 1.3.6.1.4.1.5875.800.3.5.1.1.3
		cvlanMode OBJECT-TYPE
			SYNTAX INTEGER
				{
				tag(1),
				transparent(3)
				}
			MAX-ACCESS read-create
			STATUS current
			DESCRIPTION
				"1:TAG
				3: Transparent
				"
			::= { feServiceCfgEntry 3 }

				-- 1.3.6.1.4.1.5875.800.3.5.1.1.4
		cvlan OBJECT-TYPE
			SYNTAX Integer32 (1..4085)
			MAX-ACCESS read-create
			STATUS current
			DESCRIPTION
				"1-4085??
				65535
				"
			::= { feServiceCfgEntry 4 }

				-- 1.3.6.1.4.1.5875.800.3.5.1.1.5
		cvlanCos OBJECT-TYPE
			SYNTAX Integer32 (0..7)
			MAX-ACCESS read-create
			STATUS current
			DESCRIPTION
				"0-7
				255
				"
			::= { feServiceCfgEntry 5 }

				-- 1.3.6.1.4.1.5875.800.3.5.1.1.6
		tvlan OBJECT-TYPE
			SYNTAX Integer32 (1..4085 | 65535)
			MAX-ACCESS read-create
			STATUS current
			DESCRIPTION
				"1 - 4085??
				65535: translation disabled
				"
			::= { feServiceCfgEntry 6 }

				-- 1.3.6.1.4.1.5875.800.3.5.1.1.7
		tvlanCos OBJECT-TYPE
			SYNTAX Integer32 (0..7 | 255)
			MAX-ACCESS read-create
			STATUS current
			DESCRIPTION
				"
				0-7
				255
				"
			::= { feServiceCfgEntry 7 }

				-- 1.3.6.1.4.1.5875.800.3.5.1.1.8
		svlan OBJECT-TYPE
			SYNTAX Integer32 (1..4085 | 65535)
			MAX-ACCESS read-create
			STATUS current
			DESCRIPTION
				"1 - 4085??
				65535:QINQ disabled
				"
			::= { feServiceCfgEntry 8 }

				-- 1.3.6.1.4.1.5875.800.3.5.1.1.9
		svlanCos OBJECT-TYPE
			SYNTAX Integer32 (0..7 | 255)
			MAX-ACCESS read-create
			STATUS current
			DESCRIPTION
				"0-7,255
				"
			::= { feServiceCfgEntry 9 }

				-- 1.3.6.1.4.1.5875.800.3.5.1.1.10
		upMinBandWidth OBJECT-TYPE
			SYNTAX Integer32 (0..1000000)
			MAX-ACCESS read-create
			STATUS current
			DESCRIPTION
				"0-1000000
				This value is invalid for GPON ONU
				"
			::= { feServiceCfgEntry 10 }

				-- 1.3.6.1.4.1.5875.800.3.5.1.1.11
		upManBandWidth OBJECT-TYPE
			SYNTAX Integer32 (256..1000000)
			MAX-ACCESS read-create
			STATUS current
			DESCRIPTION
				"256-1000000"
			::= { feServiceCfgEntry 11 }

				-- 1.3.6.1.4.1.5875.800.3.5.1.1.12
		dnBandWidth OBJECT-TYPE
			SYNTAX Integer32 (0..1000000)
			MAX-ACCESS read-create
			STATUS current
			DESCRIPTION
				"0-1000000"
			::= { feServiceCfgEntry 12 }

				-- 1.3.6.1.4.1.5875.800.3.5.1.1.15
		serviceVlanName OBJECT-TYPE
			SYNTAX OCTET STRING
			MAX-ACCESS read-create
			STATUS current
			DESCRIPTION
				"Length <=30"
			::= { feServiceCfgEntry 15 }

				-- 1.3.6.1.4.1.5875.800.3.5.1.1.16
		qinqProfileName OBJECT-TYPE
			SYNTAX OCTET STRING
			MAX-ACCESS read-create
			STATUS current
			DESCRIPTION
				"Length <=16, If the QINQ is disabled, this value is invalid."
			::= { feServiceCfgEntry 16 }

				-- 1.3.6.1.4.1.5875.800.3.5.1.1.20
		feServiceCfgAction OBJECT-TYPE
			SYNTAX INTEGER
				{
				active(1),
				create(4),
				destroy(6),
				modify(7)
				}
			MAX-ACCESS read-create
			STATUS current
			DESCRIPTION
				"4:create
				6:delete
				7:modify
				"
			::= { feServiceCfgEntry 20 }

				-- 1.3.6.1.4.1.5875.800.3.5.2
		feServiceCfgIdTable OBJECT-TYPE
			SYNTAX SEQUENCE OF FeServiceCfgIdEntry
			MAX-ACCESS not-accessible
			STATUS current
			DESCRIPTION
				"Description"
			::= { feServiceConfigure 2 }

				-- 1.3.6.1.4.1.5875.800.3.5.2.1
		feServiceCfgIdEntry OBJECT-TYPE
			SYNTAX FeServiceCfgIdEntry
			MAX-ACCESS not-accessible
			STATUS current
			DESCRIPTION
				"Row Description"
			INDEX { portIndex }
			::= { feServiceCfgIdTable 1 }

		
		FeServiceCfgIdEntry ::=
			SEQUENCE { 
				nextServiceId
					Integer32
			 }
		-- 1.3.6.1.4.1.5875.800.3.5.2.1.1
		nextServiceId OBJECT-TYPE
			SYNTAX Integer32
			MAX-ACCESS read-only
			STATUS current
			DESCRIPTION
				"The index indicates the port"
			::= { feServiceCfgIdEntry 1 }

				-- 1.3.6.1.4.1.5875.800.3.5.3
		feServiceCfgApplyTable OBJECT-TYPE
			SYNTAX SEQUENCE OF FeServiceCfgApplyEntry
			MAX-ACCESS not-accessible
			STATUS current
			DESCRIPTION
				"Description"
			::= { feServiceConfigure 3 }

				-- 1.3.6.1.4.1.5875.800.3.5.3.1
		feServiceCfgApplyEntry OBJECT-TYPE
			SYNTAX FeServiceCfgApplyEntry
			MAX-ACCESS not-accessible
			STATUS current
			DESCRIPTION
				"Row Description"
			INDEX { portIndex }
			::= { feServiceCfgApplyTable 1 }

		
		FeServiceCfgApplyEntry ::=
			SEQUENCE { 
				feServiceCfgApplyCommand
					TruthValue
			 }
		-- 1.3.6.1.4.1.5875.800.3.5.3.1.1
		feServiceCfgApplyCommand OBJECT-TYPE
			SYNTAX TruthValue
			MAX-ACCESS read-create
			STATUS current
			DESCRIPTION
				"1: apply"
			::= { feServiceCfgApplyEntry 1 }

				-- 1.3.6.1.4.1.5875.800.3.7
		qinq OBJECT IDENTIFIER ::= { oltData 7 }

				-- 1.3.6.1.4.1.5875.800.3.7.2
		attachQINQProfileTable OBJECT-TYPE
			SYNTAX SEQUENCE OF AttachQINQProfileEntry
			MAX-ACCESS not-accessible
			STATUS current
			DESCRIPTION
				"Description"
			::= { qinq 2 }

				-- 1.3.6.1.4.1.5875.800.3.7.2.1
		attachQINQProfileEntry OBJECT-TYPE
			SYNTAX AttachQINQProfileEntry
			MAX-ACCESS not-accessible
			STATUS current
			DESCRIPTION
				"Row Description"
			INDEX { attachQINQProfileName }
			::= { attachQINQProfileTable 1 }

		
		AttachQINQProfileEntry ::=
			SEQUENCE { 
				attachQINQProfileId
					Integer32,
				attachQINQProfileName
					OCTET STRING,
				attachQINQSvlan
					Integer32,
				attachQINQTpid
					Integer32,
				attachQINQCos
					Integer32,
				attachQINQProfileAction
					INTEGER
			 }
		-- 1.3.6.1.4.1.5875.800.3.7.2.1.1
		attachQINQProfileId OBJECT-TYPE
			SYNTAX Integer32 (0..1024)
			MAX-ACCESS read-only
			STATUS current
			DESCRIPTION
				"Column Description"
			::= { attachQINQProfileEntry 1 }

				-- 1.3.6.1.4.1.5875.800.3.7.2.1.2
		attachQINQProfileName OBJECT-TYPE
			SYNTAX OCTET STRING
			MAX-ACCESS read-create
			STATUS current
			DESCRIPTION
				"Column Description"
			::= { attachQINQProfileEntry 2 }

				-- 1.3.6.1.4.1.5875.800.3.7.2.1.3
		attachQINQSvlan OBJECT-TYPE
			SYNTAX Integer32 (0..1024)
			MAX-ACCESS read-create
			STATUS current
			DESCRIPTION
				"Column Description"
			::= { attachQINQProfileEntry 3 }

				-- 1.3.6.1.4.1.5875.800.3.7.2.1.4
		attachQINQTpid OBJECT-TYPE
			SYNTAX Integer32 (0..1024)
			MAX-ACCESS read-create
			STATUS current
			DESCRIPTION
				"Column Description"
			::= { attachQINQProfileEntry 4 }

				-- 1.3.6.1.4.1.5875.800.3.7.2.1.5
		attachQINQCos OBJECT-TYPE
			SYNTAX Integer32 (0..1024)
			MAX-ACCESS read-create
			STATUS current
			DESCRIPTION
				"Column Description"
			::= { attachQINQProfileEntry 5 }

				-- 1.3.6.1.4.1.5875.800.3.7.2.1.6
		attachQINQProfileAction OBJECT-TYPE
			SYNTAX INTEGER
				{
				create(4),
				destroy(6)
				}
			MAX-ACCESS read-create
			STATUS current
			DESCRIPTION
				"4-create
				6-delete
				7-modify"
			::= { attachQINQProfileEntry 6 }

				-- 1.3.6.1.4.1.5875.800.3.7.3
		attchQinqProfileToOnuTable OBJECT-TYPE
			SYNTAX SEQUENCE OF AttchQinqProfileToOnuEntry
			MAX-ACCESS not-accessible
			STATUS current
			DESCRIPTION
				"Description"
			::= { qinq 3 }

				-- 1.3.6.1.4.1.5875.800.3.7.3.1
		attchQinqProfileToOnuEntry OBJECT-TYPE
			SYNTAX AttchQinqProfileToOnuEntry
			MAX-ACCESS not-accessible
			STATUS current
			DESCRIPTION
				"Row Description"
			INDEX { onuIndex }
			::= { attchQinqProfileToOnuTable 1 }

		
		AttchQinqProfileToOnuEntry ::=
			SEQUENCE { 
				attchQinqProfileName
					OCTET STRING,
				qinqAttchAction
					Integer32,
				getOnuQinqProfileName
					OCTET STRING
			 }
		-- 1.3.6.1.4.1.5875.800.3.7.3.1.1
		attchQinqProfileName OBJECT-TYPE
			SYNTAX OCTET STRING
			MAX-ACCESS read-create
			STATUS current
			DESCRIPTION
				"QINQ Domain Profile Name
				The max length of name is 16"
			::= { attchQinqProfileToOnuEntry 1 }

				-- 1.3.6.1.4.1.5875.800.3.7.3.1.2
		qinqAttchAction OBJECT-TYPE
			SYNTAX Integer32 (0..1)
			MAX-ACCESS read-create
			STATUS current
			DESCRIPTION
				"Description:
				
				1: bind
				0: unbind
				"
			::= { attchQinqProfileToOnuEntry 2 }

				-- 1.3.6.1.4.1.5875.800.3.7.3.1.3
		getOnuQinqProfileName OBJECT-TYPE
			SYNTAX OCTET STRING
			MAX-ACCESS read-only
			STATUS current
			DESCRIPTION
				"Get The Bound Profile Name On The ONU"
			::= { attchQinqProfileToOnuEntry 3 }

				-- 1.3.6.1.4.1.5875.800.3.7.4
		qinqBandWidthCfgTable OBJECT-TYPE
			SYNTAX SEQUENCE OF QinqBandWidthCfgEntry
			MAX-ACCESS not-accessible
			STATUS current
			DESCRIPTION
				"Description"
			::= { qinq 4 }

				-- 1.3.6.1.4.1.5875.800.3.7.4.1
		qinqBandWidthCfgEntry OBJECT-TYPE
			SYNTAX QinqBandWidthCfgEntry
			MAX-ACCESS not-accessible
			STATUS current
			DESCRIPTION
				"Row Description"
			INDEX { onuIndex, onuQinqProfileName, qinqServiceId }
			::= { qinqBandWidthCfgTable 1 }

		
		QinqBandWidthCfgEntry ::=
			SEQUENCE { 
				onuQinqProfileName
					OCTET STRING,
				qinqServiceId
					Integer32,
				usMinBandwidth
					Integer32,
				usMaxBandwidth
					Integer32,
				usBurstBandwidth
					Integer32,
				dsMinBandwidth
					Integer32,
				dsMaxBandwidth
					Integer32,
				dsBurstBandwidth
					Integer32,
				qinqBandwidthCfgAction
					Integer32
			 }
		-- 1.3.6.1.4.1.5875.800.3.7.4.1.1
		onuQinqProfileName OBJECT-TYPE
			SYNTAX OCTET STRING
			MAX-ACCESS read-only
			STATUS current
			DESCRIPTION
				"Index
				The name acts as the index, which is composed of length and ASCII.
				e.g. if the profile name is abc, the index is 3.97.98.99.
				"
			::= { qinqBandWidthCfgEntry 1 }

				-- 1.3.6.1.4.1.5875.800.3.7.4.1.2
		qinqServiceId OBJECT-TYPE
			SYNTAX Integer32 (1..1024)
			MAX-ACCESS read-only
			STATUS current
			DESCRIPTION
				"Index"
			::= { qinqBandWidthCfgEntry 2 }

				-- 1.3.6.1.4.1.5875.800.3.7.4.1.3
		usMinBandwidth OBJECT-TYPE
			SYNTAX Integer32
			MAX-ACCESS read-create
			STATUS current
			DESCRIPTION
				"Unit: kps"
			::= { qinqBandWidthCfgEntry 3 }

				-- 1.3.6.1.4.1.5875.800.3.7.4.1.4
		usMaxBandwidth OBJECT-TYPE
			SYNTAX Integer32
			MAX-ACCESS read-create
			STATUS current
			DESCRIPTION
				"Unit: kps"
			::= { qinqBandWidthCfgEntry 4 }

				-- 1.3.6.1.4.1.5875.800.3.7.4.1.5
		usBurstBandwidth OBJECT-TYPE
			SYNTAX Integer32
			MAX-ACCESS read-create
			STATUS current
			DESCRIPTION
				"Unit: kps"
			::= { qinqBandWidthCfgEntry 5 }

				-- 1.3.6.1.4.1.5875.800.3.7.4.1.6
		dsMinBandwidth OBJECT-TYPE
			SYNTAX Integer32
			MAX-ACCESS read-create
			STATUS current
			DESCRIPTION
				"Unit: kps"
			::= { qinqBandWidthCfgEntry 6 }

				-- 1.3.6.1.4.1.5875.800.3.7.4.1.7
		dsMaxBandwidth OBJECT-TYPE
			SYNTAX Integer32
			MAX-ACCESS read-create
			STATUS current
			DESCRIPTION
				"Unit: kps"
			::= { qinqBandWidthCfgEntry 7 }

				-- 1.3.6.1.4.1.5875.800.3.7.4.1.8
		dsBurstBandwidth OBJECT-TYPE
			SYNTAX Integer32 (0..1024)
			MAX-ACCESS read-create
			STATUS current
			DESCRIPTION
				"Unit: kps"
			::= { qinqBandWidthCfgEntry 8 }

				-- 1.3.6.1.4.1.5875.800.3.7.4.1.20
		qinqBandwidthCfgAction OBJECT-TYPE
			SYNTAX Integer32 (0..1024)
			MAX-ACCESS read-create
			STATUS current
			DESCRIPTION
				"7: configure"
			::= { qinqBandWidthCfgEntry 20 }

				-- 1.3.6.1.4.1.5875.800.3.7.5
		qinqBandwidthCfgApplyTable OBJECT-TYPE
			SYNTAX SEQUENCE OF QinqBandwidthCfgApplyEntry
			MAX-ACCESS not-accessible
			STATUS current
			DESCRIPTION
				"Description"
			::= { qinq 5 }

				-- 1.3.6.1.4.1.5875.800.3.7.5.1
		qinqBandwidthCfgApplyEntry OBJECT-TYPE
			SYNTAX QinqBandwidthCfgApplyEntry
			MAX-ACCESS not-accessible
			STATUS current
			DESCRIPTION
				"Row Description"
			INDEX { onuIndex }
			::= { qinqBandwidthCfgApplyTable 1 }

		
		QinqBandwidthCfgApplyEntry ::=
			SEQUENCE { 
				qinqBandwidthCfgApply
					Integer32
			 }
		-- 1.3.6.1.4.1.5875.800.3.7.5.1.1
		qinqBandwidthCfgApply OBJECT-TYPE
			SYNTAX Integer32
			MAX-ACCESS read-create
			STATUS current
			DESCRIPTION
				"1: apply"
			::= { qinqBandwidthCfgApplyEntry 1 }

				-- 1.3.6.1.4.1.5875.800.3.7.7
		qinqDomainTable OBJECT-TYPE
			SYNTAX SEQUENCE OF QinqDomainEntry
			MAX-ACCESS not-accessible
			STATUS current
			DESCRIPTION
				"Description"
			::= { qinq 7 }

				-- 1.3.6.1.4.1.5875.800.3.7.7.1
		qinqDomainEntry OBJECT-TYPE
			SYNTAX QinqDomainEntry
			MAX-ACCESS not-accessible
			STATUS current
			DESCRIPTION
				"Row Description"
			INDEX { qinqDomainName }
			::= { qinqDomainTable 1 }

		
		QinqDomainEntry ::=
			SEQUENCE { 
				qinqDomainName
					OCTET STRING,
				qinqDomainAction
					RowStatus,
				qinqDomainServiceNum
					Integer32,
				nextQinqDomainServiceId
					Integer32
			 }
		-- 1.3.6.1.4.1.5875.800.3.7.7.1.1
		qinqDomainName OBJECT-TYPE
			SYNTAX OCTET STRING
			MAX-ACCESS read-only
			STATUS current
			DESCRIPTION
				"The name acts as the index, which is composed of length and ASCII.
				e.g. if the profile name is abc, the index is 3.97.98.99.
				"
			::= { qinqDomainEntry 1 }

				-- 1.3.6.1.4.1.5875.800.3.7.7.1.4
		qinqDomainAction OBJECT-TYPE
			SYNTAX RowStatus
			MAX-ACCESS read-create
			STATUS current
			DESCRIPTION
				"4. create
				6: delete
				"
			::= { qinqDomainEntry 4 }

				-- 1.3.6.1.4.1.5875.800.3.7.7.1.5
		qinqDomainServiceNum OBJECT-TYPE
			SYNTAX Integer32
			MAX-ACCESS read-only
			STATUS current
			DESCRIPTION
				"The service quantity contained in this domain."
			::= { qinqDomainEntry 5 }

				-- 1.3.6.1.4.1.5875.800.3.7.7.1.6
		nextQinqDomainServiceId OBJECT-TYPE
			SYNTAX Integer32
			MAX-ACCESS read-only
			STATUS current
			DESCRIPTION
				"Create the service of this domain after the ID is obtained."
			::= { qinqDomainEntry 6 }

				-- 1.3.6.1.4.1.5875.800.3.7.8
		qinqDomainServiceTable OBJECT-TYPE
			SYNTAX SEQUENCE OF QinqDomainServiceEntry
			MAX-ACCESS not-accessible
			STATUS current
			DESCRIPTION
				"Description"
			::= { qinq 8 }

				-- 1.3.6.1.4.1.5875.800.3.7.8.1
		qinqDomainServiceEntry OBJECT-TYPE
			SYNTAX QinqDomainServiceEntry
			MAX-ACCESS not-accessible
			STATUS current
			DESCRIPTION
				"Row Description"
			INDEX { qinqDomainName, qinqDomainServiceId }
			::= { qinqDomainServiceTable 1 }

		
		QinqDomainServiceEntry ::=
			SEQUENCE { 
				qinqDomainServiceId
					Integer32,
				qinqDomainServiceType
					INTEGER,
				qinqDomainLayer1OldVlan
					Integer32,
				qinqDomainLayer1OldVlanCos
					Integer32,
				qinqDomainLayer1VlanAction
					Integer32,
				qinqDomainLayer1VlanCos
					Integer32,
				qinqDomainLayer1Tpid
					Integer32,
				qinqDomainLayer1NewVlan
					Integer32,
				qinqDomainLayer2OldVlan
					Integer32,
				qinqDomainLayer2OldVlanCos
					Integer32,
				qinqDomainLayer2VlanAction
					Integer32,
				qinqDomainLayer2VlanCos
					Integer32,
				qinqDomainLayer2Tpid
					Integer32,
				qinqDomainLayer2NewVlan
					Integer32,
				qinqDomainUpRuleType
					Integer32,
				qinqDomainUpRuleValue
					OCTET STRING,
				qinqDomainUpRuleOperation
					Integer32,
				qinqDomainDnRuleType
					Integer32,
				qinqDomainDnRuleValue
					OCTET STRING,
				qinqDomainDnRuleOperation
					Integer32,
				getNextQinqDomainServiceRuleID
					Integer32,
				qinqDomainServiceAction
					INTEGER
			 }
		-- 1.3.6.1.4.1.5875.800.3.7.8.1.1
		qinqDomainServiceId OBJECT-TYPE
			SYNTAX Integer32 (1..1024)
			MAX-ACCESS read-only
			STATUS current
			DESCRIPTION
				"The service ID is unique in the QINQ domain and identifies a unique service."
			::= { qinqDomainServiceEntry 1 }

				-- 1.3.6.1.4.1.5875.800.3.7.8.1.2
		qinqDomainServiceType OBJECT-TYPE
			SYNTAX INTEGER
				{
				single(0),
				shared(1)
				}
			MAX-ACCESS read-create
			STATUS current
			DESCRIPTION
				"0: unique
				1: shared
				"
			::= { qinqDomainServiceEntry 2 }

				-- 1.3.6.1.4.1.5875.800.3.7.8.1.4
		qinqDomainLayer1OldVlan OBJECT-TYPE
			SYNTAX Integer32 (0..4085 | 65535)
			MAX-ACCESS read-create
			STATUS current
			DESCRIPTION
				"0 to 4085, 0xffff"
			::= { qinqDomainServiceEntry 4 }

				-- 1.3.6.1.4.1.5875.800.3.7.8.1.5
		qinqDomainLayer1OldVlanCos OBJECT-TYPE
			SYNTAX Integer32 (0..7)
			MAX-ACCESS read-create
			STATUS current
			DESCRIPTION
				"Description:
				value:0~7"
			::= { qinqDomainServiceEntry 5 }

				-- 1.3.6.1.4.1.5875.800.3.7.8.1.6
		qinqDomainLayer1VlanAction OBJECT-TYPE
			SYNTAX Integer32 (0..3)
			MAX-ACCESS read-create
			STATUS current
			DESCRIPTION
				"Description:
				1:add
				2:interpret
				3:transparent"
			::= { qinqDomainServiceEntry 6 }

				-- 1.3.6.1.4.1.5875.800.3.7.8.1.7
		qinqDomainLayer1VlanCos OBJECT-TYPE
			SYNTAX Integer32 (0..7 | 255)
			MAX-ACCESS read-create
			STATUS current
			DESCRIPTION
				"Description:
				1:value:0~7;
				2:255(null)"
			::= { qinqDomainServiceEntry 7 }

				-- 1.3.6.1.4.1.5875.800.3.7.8.1.8
		qinqDomainLayer1Tpid OBJECT-TYPE
			SYNTAX Integer32 (0..1024)
			MAX-ACCESS read-create
			STATUS current
			DESCRIPTION
				"Default value: 0x8100"
			::= { qinqDomainServiceEntry 8 }

				-- 1.3.6.1.4.1.5875.800.3.7.8.1.9
		qinqDomainLayer1NewVlan OBJECT-TYPE
			SYNTAX Integer32 (1..4085 | 65535)
			MAX-ACCESS read-create
			STATUS current
			DESCRIPTION
				"Description:
				1:value 1~4085
				2: 0xffff(null)"
			::= { qinqDomainServiceEntry 9 }

				-- 1.3.6.1.4.1.5875.800.3.7.8.1.10
		qinqDomainLayer2OldVlan OBJECT-TYPE
			SYNTAX Integer32 (0..65535)
			MAX-ACCESS read-create
			STATUS current
			DESCRIPTION
				"Description:
				1:value 0~4085
				2:0xffff"
			::= { qinqDomainServiceEntry 10 }

				-- 1.3.6.1.4.1.5875.800.3.7.8.1.11
		qinqDomainLayer2OldVlanCos OBJECT-TYPE
			SYNTAX Integer32 (0..7)
			MAX-ACCESS read-create
			STATUS current
			DESCRIPTION
				"Description:
				value:0~7"
			::= { qinqDomainServiceEntry 11 }

				-- 1.3.6.1.4.1.5875.800.3.7.8.1.12
		qinqDomainLayer2VlanAction OBJECT-TYPE
			SYNTAX Integer32 (1..3)
			MAX-ACCESS read-create
			STATUS current
			DESCRIPTION
				"Description:
				1:add
				2:interpret
				3:transparent"
			::= { qinqDomainServiceEntry 12 }

				-- 1.3.6.1.4.1.5875.800.3.7.8.1.13
		qinqDomainLayer2VlanCos OBJECT-TYPE
			SYNTAX Integer32 (0..7 | 255)
			MAX-ACCESS read-create
			STATUS current
			DESCRIPTION
				"Description:
				1:value 0~7
				2:oxff(null)"
			::= { qinqDomainServiceEntry 13 }

				-- 1.3.6.1.4.1.5875.800.3.7.8.1.14
		qinqDomainLayer2Tpid OBJECT-TYPE
			SYNTAX Integer32
			MAX-ACCESS read-create
			STATUS current
			DESCRIPTION
				"Default value: 0x8100"
			::= { qinqDomainServiceEntry 14 }

				-- 1.3.6.1.4.1.5875.800.3.7.8.1.15
		qinqDomainLayer2NewVlan OBJECT-TYPE
			SYNTAX Integer32 (1..4085 | 65535)
			MAX-ACCESS read-create
			STATUS current
			DESCRIPTION
				"Description:
				1:value0~4085	
				2:65535(null)"
			::= { qinqDomainServiceEntry 15 }

				-- 1.3.6.1.4.1.5875.800.3.7.8.1.30
		qinqDomainUpRuleType OBJECT-TYPE
			SYNTAX Integer32 (0..1024)
			MAX-ACCESS read-create
			STATUS current
			DESCRIPTION
				"Default value: 1
				See the note for the parameter value.
				"
			::= { qinqDomainServiceEntry 30 }

				-- 1.3.6.1.4.1.5875.800.3.7.8.1.31
		qinqDomainUpRuleValue OBJECT-TYPE
			SYNTAX OCTET STRING
			MAX-ACCESS read-create
			STATUS current
			DESCRIPTION
				"Default value: 00 00 00 00 00 02 00 00
				See the note for the parameter value.
				"
			::= { qinqDomainServiceEntry 31 }

				-- 1.3.6.1.4.1.5875.800.3.7.8.1.32
		qinqDomainUpRuleOperation OBJECT-TYPE
			SYNTAX Integer32 (0..1024)
			MAX-ACCESS read-create
			STATUS current
			DESCRIPTION
				"Default value: 5
				See the note for the parameter value.
				"
			::= { qinqDomainServiceEntry 32 }

				-- 1.3.6.1.4.1.5875.800.3.7.8.1.33
		qinqDomainDnRuleType OBJECT-TYPE
			SYNTAX Integer32 (0..1024)
			MAX-ACCESS read-create
			STATUS current
			DESCRIPTION
				"Default value: 2
				See the note for the parameter value.
				"
			::= { qinqDomainServiceEntry 33 }

				-- 1.3.6.1.4.1.5875.800.3.7.8.1.34
		qinqDomainDnRuleValue OBJECT-TYPE
			SYNTAX OCTET STRING
			MAX-ACCESS read-create
			STATUS current
			DESCRIPTION
				"Default value: 00 00 00 00 00 01 00 00
				See the note for the parameter value.
				"
			::= { qinqDomainServiceEntry 34 }

				-- 1.3.6.1.4.1.5875.800.3.7.8.1.35
		qinqDomainDnRuleOperation OBJECT-TYPE
			SYNTAX Integer32 (0..1024)
			MAX-ACCESS read-create
			STATUS current
			DESCRIPTION
				"Default value: 5
				See the note for the parameter value.
				"
			::= { qinqDomainServiceEntry 35 }

				-- 1.3.6.1.4.1.5875.800.3.7.8.1.36
		getNextQinqDomainServiceRuleID OBJECT-TYPE
			SYNTAX Integer32 (0..1024)
			MAX-ACCESS read-only
			STATUS current
			DESCRIPTION
				"Get the rule domain index of the service domian"
			::= { qinqDomainServiceEntry 36 }

				-- 1.3.6.1.4.1.5875.800.3.7.8.1.100
		qinqDomainServiceAction OBJECT-TYPE
			SYNTAX INTEGER (1..1024)
			MAX-ACCESS read-create
			STATUS current
			DESCRIPTION
				"4:create
				6:delete
				"
			::= { qinqDomainServiceEntry 100 }

				-- 1.3.6.1.4.1.5875.800.3.7.9
		qinqDomainServiceRuleTable OBJECT-TYPE
			SYNTAX SEQUENCE OF QinqDomainServiceRuleEntry
			MAX-ACCESS not-accessible
			STATUS current
			DESCRIPTION
				"Description"
			::= { qinq 9 }

				-- 1.3.6.1.4.1.5875.800.3.7.9.1
		qinqDomainServiceRuleEntry OBJECT-TYPE
			SYNTAX QinqDomainServiceRuleEntry
			MAX-ACCESS not-accessible
			STATUS current
			DESCRIPTION
				"Row Description"
			INDEX { qinqDomainName, qinqDomainServiceId, qinqDomainServiceRuleIndex }
			::= { qinqDomainServiceRuleTable 1 }

		
		QinqDomainServiceRuleEntry ::=
			SEQUENCE { 
				qinqDomainServiceRuleIndex
					Integer32,
				qinqDomainServiceUpRuleType
					Integer32,
				qinqDomainServiceUpRuleValue
					OCTET STRING,
				qinqDomainServiceUpRuleOperation
					Integer32,
				qinqDomainServiceDnRuleType
					Integer32,
				qinqDomainServiceDnRuleValue
					OCTET STRING,
				qinqDomainServiceDnRuleOperation
					Integer32,
				qinqDomainServiceRuleAction
					INTEGER
			 }
		-- 1.3.6.1.4.1.5875.800.3.7.9.1.3
		qinqDomainServiceRuleIndex OBJECT-TYPE
			SYNTAX Integer32 (1..1024)
			MAX-ACCESS not-accessible
			STATUS current
			DESCRIPTION
				"Rule Domain Term Index"
			::= { qinqDomainServiceRuleEntry 3 }

				-- 1.3.6.1.4.1.5875.800.3.7.9.1.4
		qinqDomainServiceUpRuleType OBJECT-TYPE
			SYNTAX Integer32
			MAX-ACCESS read-create
			STATUS current
			DESCRIPTION
				"Uplink Rule Domain"
			::= { qinqDomainServiceRuleEntry 4 }

				-- 1.3.6.1.4.1.5875.800.3.7.9.1.5
		qinqDomainServiceUpRuleValue OBJECT-TYPE
			SYNTAX OCTET STRING
			MAX-ACCESS read-create
			STATUS current
			DESCRIPTION
				"Uplink Domain Value"
			::= { qinqDomainServiceRuleEntry 5 }

				-- 1.3.6.1.4.1.5875.800.3.7.9.1.6
		qinqDomainServiceUpRuleOperation OBJECT-TYPE
			SYNTAX Integer32
			MAX-ACCESS read-create
			STATUS current
			DESCRIPTION
				"Uplink Operator"
			::= { qinqDomainServiceRuleEntry 6 }

				-- 1.3.6.1.4.1.5875.800.3.7.9.1.7
		qinqDomainServiceDnRuleType OBJECT-TYPE
			SYNTAX Integer32
			MAX-ACCESS read-create
			STATUS current
			DESCRIPTION
				"Downlink Rule Domain"
			::= { qinqDomainServiceRuleEntry 7 }

				-- 1.3.6.1.4.1.5875.800.3.7.9.1.8
		qinqDomainServiceDnRuleValue OBJECT-TYPE
			SYNTAX OCTET STRING
			MAX-ACCESS read-create
			STATUS current
			DESCRIPTION
				"Downlink Domain Value"
			::= { qinqDomainServiceRuleEntry 8 }

				-- 1.3.6.1.4.1.5875.800.3.7.9.1.9
		qinqDomainServiceDnRuleOperation OBJECT-TYPE
			SYNTAX Integer32
			MAX-ACCESS read-create
			STATUS current
			DESCRIPTION
				"Downlink Operator"
			::= { qinqDomainServiceRuleEntry 9 }

				-- 1.3.6.1.4.1.5875.800.3.7.9.1.20
		qinqDomainServiceRuleAction OBJECT-TYPE
			SYNTAX INTEGER (1..1024)
			MAX-ACCESS read-create
			STATUS current
			DESCRIPTION
				"4:create
				6:delete
				7:modify
				"
			::= { qinqDomainServiceRuleEntry 20 }

				-- 1.3.6.1.4.1.5875.800.3.7.10
		attachQinqProfileToPonTable OBJECT-TYPE
			SYNTAX SEQUENCE OF AttachQinqProfileToPonEntry
			MAX-ACCESS not-accessible
			STATUS current
			DESCRIPTION
				"Description."
			::= { qinq 10 }

				-- 1.3.6.1.4.1.5875.800.3.7.10.1
		attachQinqProfileToPonEntry OBJECT-TYPE
			SYNTAX AttachQinqProfileToPonEntry
			MAX-ACCESS not-accessible
			STATUS current
			DESCRIPTION
				"Description."
			INDEX { ponIndex }
			::= { attachQinqProfileToPonTable 1 }

		
		AttachQinqProfileToPonEntry ::=
			SEQUENCE { 
				attchQinqToPonProfileName
					OCTET STRING,
				qinqAttchToPonAction
					Integer32,
				getPonQinqProfileName
					OCTET STRING
			 }
		-- 1.3.6.1.4.1.5875.800.3.7.10.1.1
		attchQinqToPonProfileName OBJECT-TYPE
			SYNTAX OCTET STRING
			MAX-ACCESS read-create
			STATUS current
			DESCRIPTION
				"Column Description"
			::= { attachQinqProfileToPonEntry 1 }

				-- 1.3.6.1.4.1.5875.800.3.7.10.1.2
		qinqAttchToPonAction OBJECT-TYPE
			SYNTAX Integer32 (0..1)
			MAX-ACCESS read-create
			STATUS current
			DESCRIPTION
				"Description:
				1:bind(1)
				2:unbind(0)"
			::= { attachQinqProfileToPonEntry 2 }

				-- 1.3.6.1.4.1.5875.800.3.7.10.1.3
		getPonQinqProfileName OBJECT-TYPE
			SYNTAX OCTET STRING
			MAX-ACCESS read-only
			STATUS current
			DESCRIPTION
				"Description"
			::= { attachQinqProfileToPonEntry 3 }

				-- 1.3.6.1.4.1.5875.800.3.8
		ftthPerformance OBJECT IDENTIFIER ::= { oltData 8 }

				-- 1.3.6.1.4.1.5875.800.3.8.1
		ftthPerformanceCardEnableTable OBJECT-TYPE
			SYNTAX SEQUENCE OF FtthPerformanceCardEnableEntry
			MAX-ACCESS not-accessible
			STATUS current
			DESCRIPTION
				"Description"
			::= { ftthPerformance 1 }

				-- 1.3.6.1.4.1.5875.800.3.8.1.1
		ftthPerformanceCardEnableEntry OBJECT-TYPE
			SYNTAX FtthPerformanceCardEnableEntry
			MAX-ACCESS not-accessible
			STATUS current
			DESCRIPTION
				"Row Description"
			INDEX { slotIndex }
			::= { ftthPerformanceCardEnableTable 1 }

		
		FtthPerformanceCardEnableEntry ::=
			SEQUENCE { 
				ftthPerformanceCardEnable
					Integer32
			 }
		-- 1.3.6.1.4.1.5875.800.3.8.1.1.2
		ftthPerformanceCardEnable OBJECT-TYPE
			SYNTAX Integer32
			MAX-ACCESS read-create
			STATUS current
			DESCRIPTION
				"  0-disable      1-enable"
			::= { ftthPerformanceCardEnableEntry 2 }

				-- 1.3.6.1.4.1.5875.800.3.8.2
		ftthIsPerformanceSupport OBJECT-TYPE
			SYNTAX INTEGER
				{
				unsupport(0),
				support(1)
				}
			MAX-ACCESS read-only
			STATUS current
			DESCRIPTION
				"Description :
				0:support
				1:unsupport"
			::= { ftthPerformance 2 }

				-- 1.3.6.1.4.1.5875.800.3.8.3
		ftthPerformanceEnableFor5516 OBJECT-TYPE
			SYNTAX INTEGER
				{
				disable(0),
				enable(1)
				}
			MAX-ACCESS read-write
			STATUS current
			DESCRIPTION
				"Description :
				0:disable
				1:enable"
			::= { ftthPerformance 3 }

				-- 1.3.6.1.4.1.5875.800.3.8.6
		ftthSystemPerformance OBJECT IDENTIFIER ::= { ftthPerformance 6 }

				-- 1.3.6.1.4.1.5875.800.3.8.6.1
		utilization OBJECT IDENTIFIER ::= { ftthSystemPerformance 1 }

				-- 1.3.6.1.4.1.5875.800.3.8.6.1.1
		cpuUtilization OBJECT-TYPE
			SYNTAX Integer32
			MAX-ACCESS read-only
			STATUS current
			DESCRIPTION
				"cpu utilization"
			::= { utilization 1 }

				-- 1.3.6.1.4.1.5875.800.3.8.6.1.2
		memUtilization OBJECT-TYPE
			SYNTAX Integer32
			MAX-ACCESS read-only
			STATUS current
			DESCRIPTION
				"mem utilization"
			::= { utilization 2 }

				-- 1.3.6.1.4.1.5875.800.3.8.6.1.3
		currentTemperature OBJECT-TYPE
			SYNTAX Integer32
			MAX-ACCESS read-only
			STATUS current
			DESCRIPTION
				"current Temperature"
			::= { utilization 3 }

				-- 1.3.6.1.4.1.5875.800.3.8.7
		ftthVlanTransmitPerformanceTable OBJECT-TYPE
			SYNTAX SEQUENCE OF FtthVlanTransmitPerformanceEntry
			MAX-ACCESS not-accessible
			STATUS current
			DESCRIPTION
				"Description"
			::= { ftthPerformance 7 }

				-- 1.3.6.1.4.1.5875.800.3.8.7.1
		ftthVlanTransmitPerformanceEntry OBJECT-TYPE
			SYNTAX FtthVlanTransmitPerformanceEntry
			MAX-ACCESS not-accessible
			STATUS current
			DESCRIPTION
				"Row Description"
			INDEX { vlanID, uplinkIndex }
			::= { ftthVlanTransmitPerformanceTable 1 }

		
		FtthVlanTransmitPerformanceEntry ::=
			SEQUENCE { 
				vlanID
					Integer32,
				framesUs
					Counter32,
				framesDs
					Counter32,
				octetsUs
					Counter32,
				octetsDs
					Counter32,
				discardsUs
					Counter64,
				discardsDs
					Counter64
			 }
		-- 1.3.6.1.4.1.5875.800.3.8.7.1.1
		vlanID OBJECT-TYPE
			SYNTAX Integer32 (1..4096)
			MAX-ACCESS read-only
			STATUS current
			DESCRIPTION
				"Index"
			::= { ftthVlanTransmitPerformanceEntry 1 }

				-- 1.3.6.1.4.1.5875.800.3.8.7.1.2
		framesUs OBJECT-TYPE
			SYNTAX Counter32
			MAX-ACCESS read-only
			STATUS current
			DESCRIPTION
				"0 to 2147483647"
			::= { ftthVlanTransmitPerformanceEntry 2 }

				-- 1.3.6.1.4.1.5875.800.3.8.7.1.3
		framesDs OBJECT-TYPE
			SYNTAX Counter32
			MAX-ACCESS read-only
			STATUS current
			DESCRIPTION
				"0 to 2147483647"
			::= { ftthVlanTransmitPerformanceEntry 3 }

				-- 1.3.6.1.4.1.5875.800.3.8.7.1.4
		octetsUs OBJECT-TYPE
			SYNTAX Counter32
			MAX-ACCESS read-only
			STATUS current
			DESCRIPTION
				"0 to 2147483647"
			::= { ftthVlanTransmitPerformanceEntry 4 }

				-- 1.3.6.1.4.1.5875.800.3.8.7.1.5
		octetsDs OBJECT-TYPE
			SYNTAX Counter32
			MAX-ACCESS read-only
			STATUS current
			DESCRIPTION
				"0 to 2147483647"
			::= { ftthVlanTransmitPerformanceEntry 5 }

				-- 1.3.6.1.4.1.5875.800.3.8.7.1.6
		discardsUs OBJECT-TYPE
			SYNTAX Counter64
			MAX-ACCESS read-only
			STATUS current
			DESCRIPTION
				"0 to 1.85E19"
			::= { ftthVlanTransmitPerformanceEntry 6 }

				-- 1.3.6.1.4.1.5875.800.3.8.7.1.7
		discardsDs OBJECT-TYPE
			SYNTAX Counter64
			MAX-ACCESS read-only
			STATUS current
			DESCRIPTION
				"0 to 1.85E19"
			::= { ftthVlanTransmitPerformanceEntry 7 }

				-- 1.3.6.1.4.1.5875.800.3.9
		systemInfo OBJECT IDENTIFIER ::= { oltData 9 }

				-- 1.3.6.1.4.1.5875.800.3.9.1
		frameInfo OBJECT IDENTIFIER ::= { systemInfo 1 }

				-- 1.3.6.1.4.1.5875.800.3.9.1.1
		frameInfoTable OBJECT-TYPE
			SYNTAX SEQUENCE OF FrameInfoEntry
			MAX-ACCESS not-accessible
			STATUS current
			DESCRIPTION
				"Description"
			::= { frameInfo 1 }

				-- 1.3.6.1.4.1.5875.800.3.9.1.1.1
		frameInfoEntry OBJECT-TYPE
			SYNTAX FrameInfoEntry
			MAX-ACCESS not-accessible
			STATUS current
			DESCRIPTION
				"Row Description"
			INDEX { frameIndex }
			::= { frameInfoTable 1 }

		
		FrameInfoEntry ::=
			SEQUENCE { 
				frameIndex
					Integer32,
				frameType
					Integer32,
				frameName
					OCTET STRING,
				slotNumOfFrame
					Integer32
			 }
		-- 1.3.6.1.4.1.5875.800.3.9.1.1.1.1
		frameIndex OBJECT-TYPE
			SYNTAX Integer32 (1..1024)
			MAX-ACCESS read-only
			STATUS current
			DESCRIPTION
				"Subrack Index"
			::= { frameInfoEntry 1 }

				-- 1.3.6.1.4.1.5875.800.3.9.1.1.1.2
		frameType OBJECT-TYPE
			SYNTAX Integer32 (0..1024)
			MAX-ACCESS read-only
			STATUS current
			DESCRIPTION
				"1: An5116-02
				2: An5116-06
				11: An5516-01
				6: An5516-06
				12: An5516-04
				"
			::= { frameInfoEntry 2 }

				-- 1.3.6.1.4.1.5875.800.3.9.1.1.1.3
		frameName OBJECT-TYPE
			SYNTAX OCTET STRING
			MAX-ACCESS read-only
			STATUS current
			DESCRIPTION
				"Subrack Name"
			::= { frameInfoEntry 3 }

				-- 1.3.6.1.4.1.5875.800.3.9.1.1.1.4
		slotNumOfFrame OBJECT-TYPE
			SYNTAX Integer32 (0..1024)
			MAX-ACCESS read-only
			STATUS current
			DESCRIPTION
				"25"
			::= { frameInfoEntry 4 }

				-- 1.3.6.1.4.1.5875.800.3.9.2
		cardInfo OBJECT IDENTIFIER ::= { systemInfo 2 }

				-- 1.3.6.1.4.1.5875.800.3.9.2.1
		cardInfoTable OBJECT-TYPE
			SYNTAX SEQUENCE OF CardInfoEntry
			MAX-ACCESS not-accessible
			STATUS current
			DESCRIPTION
				"Description"
			::= { cardInfo 1 }

				-- 1.3.6.1.4.1.5875.800.3.9.2.1.1
		cardInfoEntry OBJECT-TYPE
			SYNTAX CardInfoEntry
			MAX-ACCESS not-accessible
			STATUS current
			DESCRIPTION
				"Row Description"
			INDEX { slotIndex }
			::= { cardInfoTable 1 }

		
		CardInfoEntry ::=
			SEQUENCE { 
				cardType
					Integer32,
				cardHardwareVersion
					OCTET STRING,
				cardSoftwateVersion
					OCTET STRING,
				cardStatus
					Integer32,
				cardNumOfPorts
					Integer32,
				cardAvailablePorts
					Integer32,
				cardCpuUtil
					Integer32,
				cardMemUtil
					Integer32
			 }
		-- 1.3.6.1.4.1.5875.800.3.9.2.1.1.2
		cardType OBJECT-TYPE
			SYNTAX Integer32 (0..1024)
			MAX-ACCESS read-only
			STATUS current
			DESCRIPTION
				"5116 Series:
				260: EC2
				259: GUP7
				401: GFUP
				249: GUPE7 
				286??AC16
				
				5516 Series??
				508: EC4B
				514: EC8B
				552: ECOB
				502: GC4B
				527: GC8B
				550: GCOB
				545: XP4A
				575: XP8A
				605: CE1B
				602: C155A
				413: GU6F
				420: GS8F
				414: HU2A
				415: HU1A
				526: XG2B
				555: XG4B
				553: XG8A
				549: GSOF
				"
			::= { cardInfoEntry 2 }

				-- 1.3.6.1.4.1.5875.800.3.9.2.1.1.3
		cardHardwareVersion OBJECT-TYPE
			SYNTAX OCTET STRING
			MAX-ACCESS read-only
			STATUS current
			DESCRIPTION
				"Hardware Version"
			::= { cardInfoEntry 3 }

				-- 1.3.6.1.4.1.5875.800.3.9.2.1.1.4
		cardSoftwateVersion OBJECT-TYPE
			SYNTAX OCTET STRING
			MAX-ACCESS read-only
			STATUS current
			DESCRIPTION
				"Software Version
				
				"
			::= { cardInfoEntry 4 }

				-- 1.3.6.1.4.1.5875.800.3.9.2.1.1.5
		cardStatus OBJECT-TYPE
			SYNTAX Integer32 (0..1024)
			MAX-ACCESS read-only
			STATUS current
			DESCRIPTION
				"1: Normal,
				0: Interrupted
				"
			::= { cardInfoEntry 5 }

				-- 1.3.6.1.4.1.5875.800.3.9.2.1.1.6
		cardNumOfPorts OBJECT-TYPE
			SYNTAX Integer32 (0..1024)
			MAX-ACCESS read-only
			STATUS current
			DESCRIPTION
				"Service Card Port Number"
			::= { cardInfoEntry 6 }

				-- 1.3.6.1.4.1.5875.800.3.9.2.1.1.7
		cardAvailablePorts OBJECT-TYPE
			SYNTAX Integer32 (0..1024)
			MAX-ACCESS read-only
			STATUS current
			DESCRIPTION
				"Service Card Actived Port Number"
			::= { cardInfoEntry 7 }

				-- 1.3.6.1.4.1.5875.800.3.9.2.1.1.8
		cardCpuUtil OBJECT-TYPE
			SYNTAX Integer32
			MAX-ACCESS read-only
			STATUS current
			DESCRIPTION
				"The parameter value divided by 100 equals the actual value.
				Not available for AN5116 Series
				"
			::= { cardInfoEntry 8 }

				-- 1.3.6.1.4.1.5875.800.3.9.2.1.1.9
		cardMemUtil OBJECT-TYPE
			SYNTAX Integer32
			MAX-ACCESS read-only
			STATUS current
			DESCRIPTION
				"The parameter value divided by 100 equals the actual value.
				Not available for AN5116 Series
				"
			::= { cardInfoEntry 9 }

				-- 1.3.6.1.4.1.5875.800.3.9.3
		interfaceInfo OBJECT IDENTIFIER ::= { systemInfo 3 }

				-- 1.3.6.1.4.1.5875.800.3.9.3.1
		portInfoTable OBJECT-TYPE
			SYNTAX SEQUENCE OF PortInfoEntry
			MAX-ACCESS not-accessible
			STATUS current
			DESCRIPTION
				"Description"
			::= { interfaceInfo 1 }

				-- 1.3.6.1.4.1.5875.800.3.9.3.1.1
		portInfoEntry OBJECT-TYPE
			SYNTAX PortInfoEntry
			MAX-ACCESS not-accessible
			STATUS current
			DESCRIPTION
				"Row Description"
			INDEX { portIndex }
			::= { portInfoTable 1 }

		
		PortInfoEntry ::=
			SEQUENCE { 
				portType
					Integer32,
				portEnableStatus
					Integer32,
				portOnlineStatus
					Integer32,
				portSpeed
					Integer32,
				portName
					OCTET STRING,
				portDesc
					OCTET STRING,
				portMode
					Integer32,
				portVlan
					OCTET STRING,
				portMac
					OCTET STRING,
				portDefaultVlan
					Integer32,
				portAutoneg
					Integer32,
				portMacNumberLimit
					Integer32
			 }
		-- 1.3.6.1.4.1.5875.800.3.9.3.1.1.2
		portType OBJECT-TYPE
			SYNTAX Integer32 (0..1024)
			MAX-ACCESS read-only
			STATUS current
			DESCRIPTION
				"The 5516??
				2: FE port
				"
			::= { portInfoEntry 2 }

				-- 1.3.6.1.4.1.5875.800.3.9.3.1.1.3
		portEnableStatus OBJECT-TYPE
			SYNTAX Integer32 (0..1024)
			MAX-ACCESS read-only
			STATUS current
			DESCRIPTION
				"The 5516??
				1??enable
				0??disable
				"
			::= { portInfoEntry 3 }

				-- 1.3.6.1.4.1.5875.800.3.9.3.1.1.4
		portOnlineStatus OBJECT-TYPE
			SYNTAX Integer32 (0..1024)
			MAX-ACCESS read-only
			STATUS current
			DESCRIPTION
				"1??online
				0??offline
				"
			::= { portInfoEntry 4 }

				-- 1.3.6.1.4.1.5875.800.3.9.3.1.1.5
		portSpeed OBJECT-TYPE
			SYNTAX Integer32 (0..1024)
			MAX-ACCESS read-only
			STATUS current
			DESCRIPTION
				"NGPON??GPON 
				0:10M
				1:100M
				2:1000M
				The unit is Mbit/s
				"
			::= { portInfoEntry 5 }

				-- 1.3.6.1.4.1.5875.800.3.9.3.1.1.6
		portName OBJECT-TYPE
			SYNTAX OCTET STRING
			MAX-ACCESS read-only
			STATUS current
			DESCRIPTION
				"Port Name"
			::= { portInfoEntry 6 }

				-- 1.3.6.1.4.1.5875.800.3.9.3.1.1.7
		portDesc OBJECT-TYPE
			SYNTAX OCTET STRING
			MAX-ACCESS read-create
			STATUS current
			DESCRIPTION
				"Not available"
			::= { portInfoEntry 7 }

				-- 1.3.6.1.4.1.5875.800.3.9.3.1.1.8
		portMode OBJECT-TYPE
			SYNTAX Integer32
			MAX-ACCESS read-only
			STATUS current
			DESCRIPTION
				"Description:
				1:full duplex(1)
				2:half duplex(0)"
			::= { portInfoEntry 8 }

				-- 1.3.6.1.4.1.5875.800.3.9.3.1.1.9
		portVlan OBJECT-TYPE
			SYNTAX OCTET STRING
			MAX-ACCESS read-only
			STATUS current
			DESCRIPTION
				"String	All the VLANs under the port is devided by ??:??
				Unavailable
				"
			::= { portInfoEntry 9 }

				-- 1.3.6.1.4.1.5875.800.3.9.3.1.1.10
		portMac OBJECT-TYPE
			SYNTAX OCTET STRING
			MAX-ACCESS read-only
			STATUS current
			DESCRIPTION
				"All the MACs under the port is devided by ??:??
				Unavailable
				"
			::= { portInfoEntry 10 }

				-- 1.3.6.1.4.1.5875.800.3.9.3.1.1.11
		portDefaultVlan OBJECT-TYPE
			SYNTAX Integer32
			MAX-ACCESS read-only
			STATUS current
			DESCRIPTION
				"Port default VLAN
				(default value for the 5516: 4088)
				"
			::= { portInfoEntry 11 }

				-- 1.3.6.1.4.1.5875.800.3.9.3.1.1.12
		portAutoneg OBJECT-TYPE
			SYNTAX Integer32 (0..1)
			MAX-ACCESS read-only
			STATUS current
			DESCRIPTION
				"The 5516??
				1??enable
				0??disable
				"
			::= { portInfoEntry 12 }

				-- 1.3.6.1.4.1.5875.800.3.9.3.1.1.13
		portMacNumberLimit OBJECT-TYPE
			SYNTAX Integer32
			MAX-ACCESS read-create
			STATUS current
			DESCRIPTION
				"0-16 000??
				0:No Limit
				˵????
				After configuration is complete without the use of the 1.3.6.1.4.1.5875.800.3.10.1.1.29
				The application is not effective
				"
			::= { portInfoEntry 13 }

				-- 1.3.6.1.4.1.5875.800.3.9.3.2
		potsInfoTable OBJECT-TYPE
			SYNTAX SEQUENCE OF PotsInfoEntry
			MAX-ACCESS not-accessible
			STATUS current
			DESCRIPTION
				"Description"
			::= { interfaceInfo 2 }

				-- 1.3.6.1.4.1.5875.800.3.9.3.2.1
		potsInfoEntry OBJECT-TYPE
			SYNTAX PotsInfoEntry
			MAX-ACCESS not-accessible
			STATUS current
			DESCRIPTION
				"Row Description"
			INDEX { potsIndex }
			::= { potsInfoTable 1 }

		
		PotsInfoEntry ::=
			SEQUENCE { 
				potsType
					Integer32,
				potsName
					OCTET STRING,
				potsDesc
					OCTET STRING,
				potsEnableStatus
					Integer32,
				potsIdleStatus
					Integer32
			 }
		-- 1.3.6.1.4.1.5875.800.3.9.3.2.1.1
		potsType OBJECT-TYPE
			SYNTAX Integer32 (0..1024)
			MAX-ACCESS read-only
			STATUS current
			DESCRIPTION
				"The 5516:
				600
				"
			::= { potsInfoEntry 1 }

				-- 1.3.6.1.4.1.5875.800.3.9.3.2.1.2
		potsName OBJECT-TYPE
			SYNTAX OCTET STRING
			MAX-ACCESS read-only
			STATUS current
			DESCRIPTION
				"Port Name"
			::= { potsInfoEntry 2 }

				-- 1.3.6.1.4.1.5875.800.3.9.3.2.1.3
		potsDesc OBJECT-TYPE
			SYNTAX OCTET STRING
			MAX-ACCESS read-create
			STATUS current
			DESCRIPTION
				"W is not available"
			::= { potsInfoEntry 3 }

				-- 1.3.6.1.4.1.5875.800.3.9.3.2.1.4
		potsEnableStatus OBJECT-TYPE
			SYNTAX Integer32
			MAX-ACCESS read-only
			STATUS current
			DESCRIPTION
				"The 5516??
				1??enable
				0??disable
				The 5116:
				1: enable
				2: disable
				"
			::= { potsInfoEntry 4 }

				-- 1.3.6.1.4.1.5875.800.3.9.3.2.1.5
		potsIdleStatus OBJECT-TYPE
			SYNTAX Integer32
			MAX-ACCESS read-only
			STATUS current
			DESCRIPTION
				"0. the port is not activated
				1. the port is registrating
				2. the port is in idle status
				3. the port is off-hook
				4. the port is dialing
				5. the port is ringing
				6. the port is ringing back tone
				7. the port is connecting
				8. the port is connected
				9. the port is hung up
				10. the port is not connected
				11. the port is busy
				12. the port is failed to register
				"
			::= { potsInfoEntry 5 }

				-- 1.3.6.1.4.1.5875.800.3.9.3.3
		onuPonInfoTable OBJECT-TYPE
			SYNTAX SEQUENCE OF OnuPonInfoEntry
			MAX-ACCESS not-accessible
			STATUS current
			DESCRIPTION
				"Description"
			::= { interfaceInfo 3 }

				-- 1.3.6.1.4.1.5875.800.3.9.3.3.1
		onuPonInfoEntry OBJECT-TYPE
			SYNTAX OnuPonInfoEntry
			MAX-ACCESS not-accessible
			STATUS current
			DESCRIPTION
				"Row Description"
			INDEX { onuIndex }
			::= { onuPonInfoTable 1 }

		
		OnuPonInfoEntry ::=
			SEQUENCE { 
				onuPonType
					Integer32,
				onuPonName
					OCTET STRING,
				onuPonDesc
					OCTET STRING,
				onuPonEnableStatus
					Integer32,
				onuPonSpeed
					Integer32,
				onuPonRxOpticalPower
					Integer32,
				onuPonTxOpticalPower
					Integer32,
				onuPonOpticalVltage
					Integer32,
				onuPonOpticalCurrent
					Integer32,
				onuPonOpticalTemperature
					Integer32,
				onuPonIsOpticalPowerValid
					INTEGER,
				onuPonUpstreamSpeed
					Integer32
			 }
		-- 1.3.6.1.4.1.5875.800.3.9.3.3.1.1
		onuPonType OBJECT-TYPE
			SYNTAX Integer32
			MAX-ACCESS read-only
			STATUS current
			DESCRIPTION
				"Port Type"
			::= { onuPonInfoEntry 1 }

				-- 1.3.6.1.4.1.5875.800.3.9.3.3.1.2
		onuPonName OBJECT-TYPE
			SYNTAX OCTET STRING
			MAX-ACCESS read-only
			STATUS current
			DESCRIPTION
				"Port Name"
			::= { onuPonInfoEntry 2 }

				-- 1.3.6.1.4.1.5875.800.3.9.3.3.1.3
		onuPonDesc OBJECT-TYPE
			SYNTAX OCTET STRING
			MAX-ACCESS read-create
			STATUS current
			DESCRIPTION
				"W is not available"
			::= { onuPonInfoEntry 3 }

				-- 1.3.6.1.4.1.5875.800.3.9.3.3.1.4
		onuPonEnableStatus OBJECT-TYPE
			SYNTAX Integer32
			MAX-ACCESS read-only
			STATUS current
			DESCRIPTION
				"1: Enable
				0: Disable
				"
			::= { onuPonInfoEntry 4 }

				-- 1.3.6.1.4.1.5875.800.3.9.3.3.1.5
		onuPonSpeed OBJECT-TYPE
			SYNTAX Integer32
			MAX-ACCESS read-only
			STATUS current
			DESCRIPTION
				"Unit: Mbit/S"
			::= { onuPonInfoEntry 5 }

				-- 1.3.6.1.4.1.5875.800.3.9.3.3.1.6
		onuPonRxOpticalPower OBJECT-TYPE
			SYNTAX Integer32
			MAX-ACCESS read-only
			STATUS current
			DESCRIPTION
				"The parameter value divided by 100 equals the actual value (Unit: Dbm)"
			::= { onuPonInfoEntry 6 }

				-- 1.3.6.1.4.1.5875.800.3.9.3.3.1.7
		onuPonTxOpticalPower OBJECT-TYPE
			SYNTAX Integer32
			MAX-ACCESS read-only
			STATUS current
			DESCRIPTION
				"The parameter value divided by 100 equals the actual value (Unit: Dbm)"
			::= { onuPonInfoEntry 7 }

				-- 1.3.6.1.4.1.5875.800.3.9.3.3.1.8
		onuPonOpticalVltage OBJECT-TYPE
			SYNTAX Integer32
			MAX-ACCESS read-only
			STATUS current
			DESCRIPTION
				"The parameter value divided by 100 equals the actual value (Unit: V)"
			::= { onuPonInfoEntry 8 }

				-- 1.3.6.1.4.1.5875.800.3.9.3.3.1.9
		onuPonOpticalCurrent OBJECT-TYPE
			SYNTAX Integer32
			MAX-ACCESS read-only
			STATUS current
			DESCRIPTION
				"The parameter value divided by 100 equals the actual value (Unit: mA)"
			::= { onuPonInfoEntry 9 }

				-- 1.3.6.1.4.1.5875.800.3.9.3.3.1.10
		onuPonOpticalTemperature OBJECT-TYPE
			SYNTAX Integer32
			MAX-ACCESS read-only
			STATUS current
			DESCRIPTION
				"The parameter value divided by 100 equals the actual value (Unit: ??)"
			::= { onuPonInfoEntry 10 }

				-- 1.3.6.1.4.1.5875.800.3.9.3.3.1.11
		onuPonIsOpticalPowerValid OBJECT-TYPE
			SYNTAX INTEGER
				{
				support(1),
				nonsupport(2)
				}
			MAX-ACCESS read-create
			STATUS current
			DESCRIPTION
				"Only available for the 5116
				1: available
				2: not available
				"
			::= { onuPonInfoEntry 11 }

				-- 1.3.6.1.4.1.5875.800.3.9.3.3.1.12
		onuPonUpstreamSpeed OBJECT-TYPE
			SYNTAX Integer32
			MAX-ACCESS read-only
			STATUS current
			DESCRIPTION
				"Unit:Mbit/S
				(Only available for Jiangsu test)
				"
			::= { onuPonInfoEntry 12 }

				-- 1.3.6.1.4.1.5875.800.3.9.3.4
		oltPonInfoTable OBJECT-TYPE
			SYNTAX SEQUENCE OF OltPonInfoEntry
			MAX-ACCESS not-accessible
			STATUS current
			DESCRIPTION
				"Description"
			::= { interfaceInfo 4 }

				-- 1.3.6.1.4.1.5875.800.3.9.3.4.1
		oltPonInfoEntry OBJECT-TYPE
			SYNTAX OltPonInfoEntry
			MAX-ACCESS not-accessible
			STATUS current
			DESCRIPTION
				"Row Description"
			INDEX { ponIndex }
			::= { oltPonInfoTable 1 }

		
		OltPonInfoEntry ::=
			SEQUENCE { 
				oltPonType
					Integer32,
				oltPonName
					OCTET STRING,
				oltPonDesc
					OCTET STRING,
				oltPonEnableStatus
					Integer32,
				oltPonOnlineStatus
					Integer32,
				oltPonSpeed
					Integer32,
				oltPonTxOpticalPower
					Integer32,
				oltPonOpticalVltage
					Integer32,
				oltPonOpticalCurrent
					Integer32,
				oltPonOpticalTemperature
					Integer32,
				oltPonAuthOnuNum
					Integer32,
				oltPonUpStreamSpeed
					Integer32,
				oltPonOpticalModuleType
					Integer32,
				oltPonVendorName
					OCTET STRING,
				oltPonVendorPn
					OCTET STRING,
				oltPonVendorSn
					OCTET STRING,
				oltPonDownwardAssociationSn
					OCTET STRING,
				oltPonXgOpticalCurrent
					Integer32,
				oltPonXgTxOpticalPower
					Integer32
			 }
		-- 1.3.6.1.4.1.5875.800.3.9.3.4.1.1
		oltPonType OBJECT-TYPE
			SYNTAX Integer32
			MAX-ACCESS read-only
			STATUS current
			DESCRIPTION
				"See the type code table in the Appendix for card type"
			::= { oltPonInfoEntry 1 }

				-- 1.3.6.1.4.1.5875.800.3.9.3.4.1.2
		oltPonName OBJECT-TYPE
			SYNTAX OCTET STRING
			MAX-ACCESS read-only
			STATUS current
			DESCRIPTION
				"Port Name"
			::= { oltPonInfoEntry 2 }

				-- 1.3.6.1.4.1.5875.800.3.9.3.4.1.3
		oltPonDesc OBJECT-TYPE
			SYNTAX OCTET STRING
			MAX-ACCESS read-create
			STATUS current
			DESCRIPTION
				"Port Description"
			::= { oltPonInfoEntry 3 }

				-- 1.3.6.1.4.1.5875.800.3.9.3.4.1.4
		oltPonEnableStatus OBJECT-TYPE
			SYNTAX Integer32
			MAX-ACCESS read-only
			STATUS current
			DESCRIPTION
				"1: Enable
				0: Disable
				"
			::= { oltPonInfoEntry 4 }

				-- 1.3.6.1.4.1.5875.800.3.9.3.4.1.5
		oltPonOnlineStatus OBJECT-TYPE
			SYNTAX Integer32
			MAX-ACCESS read-only
			STATUS current
			DESCRIPTION
				"1: Online
				0: Offline
				(Online: the authorized ONU is connected with this port and the ONU is online)
				"
			::= { oltPonInfoEntry 5 }

				-- 1.3.6.1.4.1.5875.800.3.9.3.4.1.6
		oltPonSpeed OBJECT-TYPE
			SYNTAX Integer32
			MAX-ACCESS read-only
			STATUS current
			DESCRIPTION
				"Unit: Mbit/S"
			::= { oltPonInfoEntry 6 }

				-- 1.3.6.1.4.1.5875.800.3.9.3.4.1.8
		oltPonTxOpticalPower OBJECT-TYPE
			SYNTAX Integer32
			MAX-ACCESS read-only
			STATUS current
			DESCRIPTION
				"The parameter value divided by 100 equals the actual value (Unit: Dbm)"
			::= { oltPonInfoEntry 8 }

				-- 1.3.6.1.4.1.5875.800.3.9.3.4.1.9
		oltPonOpticalVltage OBJECT-TYPE
			SYNTAX Integer32
			MAX-ACCESS read-only
			STATUS current
			DESCRIPTION
				"The parameter value divided by 100 equals the actual value (Unit: V)"
			::= { oltPonInfoEntry 9 }

				-- 1.3.6.1.4.1.5875.800.3.9.3.4.1.10
		oltPonOpticalCurrent OBJECT-TYPE
			SYNTAX Integer32
			MAX-ACCESS read-only
			STATUS current
			DESCRIPTION
				"The parameter value divided by 100 equals the actual value  (Unit: mA)"
			::= { oltPonInfoEntry 10 }

				-- 1.3.6.1.4.1.5875.800.3.9.3.4.1.11
		oltPonOpticalTemperature OBJECT-TYPE
			SYNTAX Integer32
			MAX-ACCESS read-only
			STATUS current
			DESCRIPTION
				"The parameter value divided by 100 equals the actual value (Unit: ??)"
			::= { oltPonInfoEntry 11 }

				-- 1.3.6.1.4.1.5875.800.3.9.3.4.1.12
		oltPonAuthOnuNum OBJECT-TYPE
			SYNTAX Integer32 (0..1024)
			MAX-ACCESS read-only
			STATUS current
			DESCRIPTION
				"Authorized ONU Amount of PON Port"
			::= { oltPonInfoEntry 12 }

				-- 1.3.6.1.4.1.5875.800.3.9.3.4.1.13
		oltPonUpStreamSpeed OBJECT-TYPE
			SYNTAX Integer32
			MAX-ACCESS read-only
			STATUS current
			DESCRIPTION
				"Unit: Mbit/S
				(Only available for Jiangsu test)
				"
			::= { oltPonInfoEntry 13 }

				-- 1.3.6.1.4.1.5875.800.3.9.3.4.1.15
		oltPonOpticalModuleType OBJECT-TYPE
			SYNTAX Integer32
			MAX-ACCESS read-only
			STATUS current
			DESCRIPTION
				"Optical module type list: 
				1: unknown
				2: classbplus
				3: classcplus
				4: classb
				5: px20
				6: px20plus 
				7: pr30 
				8: pr20 
				9: prx30 
				10: prx20
				11: invalid
				12: absent (the optical module is not present)
				"
			::= { oltPonInfoEntry 15 }

				-- 1.3.6.1.4.1.5875.800.3.9.3.4.1.16
		oltPonVendorName OBJECT-TYPE
			SYNTAX OCTET STRING
			MAX-ACCESS read-only
			STATUS current
			DESCRIPTION
				"Description."
			::= { oltPonInfoEntry 16 }

				-- 1.3.6.1.4.1.5875.800.3.9.3.4.1.17
		oltPonVendorPn OBJECT-TYPE
			SYNTAX OCTET STRING
			MAX-ACCESS read-only
			STATUS current
			DESCRIPTION
				"Description."
			::= { oltPonInfoEntry 17 }

				-- 1.3.6.1.4.1.5875.800.3.9.3.4.1.18
		oltPonVendorSn OBJECT-TYPE
			SYNTAX OCTET STRING
			MAX-ACCESS read-only
			STATUS current
			DESCRIPTION
				"Description."
			::= { oltPonInfoEntry 18 }

				-- 1.3.6.1.4.1.5875.800.3.9.3.4.1.19
		oltPonDownwardAssociationSn OBJECT-TYPE
			SYNTAX OCTET STRING
			MAX-ACCESS read-only
			STATUS current
			DESCRIPTION
				"Description."
			::= { oltPonInfoEntry 19 }

				-- 1.3.6.1.4.1.5875.800.3.9.3.4.1.20
		oltPonXgOpticalCurrent OBJECT-TYPE
			SYNTAX Integer32
			MAX-ACCESS read-only
			STATUS current
			DESCRIPTION
				"Description."
			::= { oltPonInfoEntry 20 }

				-- 1.3.6.1.4.1.5875.800.3.9.3.4.1.21
		oltPonXgTxOpticalPower OBJECT-TYPE
			SYNTAX Integer32
			MAX-ACCESS read-only
			STATUS current
			DESCRIPTION
				"Description."
			::= { oltPonInfoEntry 21 }

				-- 1.3.6.1.4.1.5875.800.3.9.3.5
		oltUplinkInfoTable OBJECT-TYPE
			SYNTAX SEQUENCE OF OltUplinkInfoEntry
			MAX-ACCESS not-accessible
			STATUS current
			DESCRIPTION
				"Description"
			::= { interfaceInfo 5 }

				-- 1.3.6.1.4.1.5875.800.3.9.3.5.1
		oltUplinkInfoEntry OBJECT-TYPE
			SYNTAX OltUplinkInfoEntry
			MAX-ACCESS not-accessible
			STATUS current
			DESCRIPTION
				"Row Description"
			INDEX { uplinkIndex }
			::= { oltUplinkInfoTable 1 }

		
		OltUplinkInfoEntry ::=
			SEQUENCE { 
				uplinkType
					Integer32,
				uplinkName
					OCTET STRING,
				uplinkDesc
					OCTET STRING,
				uplinkEnableStatus
					Integer32,
				uplinkSpeed
					Integer32,
				uplinkMacStr
					OCTET STRING,
				oltUplinkTxOpticalPower
					Integer32,
				oltUplinkRxOpticalPower
					Integer32,
				oltUplinkOpticalTemperature
					Integer32,
				oltUplinkOpticalVltage
					Integer32,
				oltUplinkOpticalCurrent
					Integer32,
				oltUplinkOpticalModuleType
					Integer32,
				oltUplinkVendorName
					Integer32,
				oltUplinkVendorPn
					Integer32,
				oltUplinkVendorSn
					Integer32,
				oltUplinkDownwardAssociationSn
					Integer32
			 }
		-- 1.3.6.1.4.1.5875.800.3.9.3.5.1.1
		uplinkType OBJECT-TYPE
			SYNTAX Integer32 (0..1024)
			MAX-ACCESS read-only
			STATUS current
			DESCRIPTION
				"NGPON Series??
				4: 10GM Replace Port
				5: 1000M Replace Port
				5516 Series??
				1:PON
				2:FE
				3:Gigabit
				4:Gigabit optical port 
				5:pots port
				6:10GE optical port 
				7: Gigabit electrical port
				"
			::= { oltUplinkInfoEntry 1 }

				-- 1.3.6.1.4.1.5875.800.3.9.3.5.1.2
		uplinkName OBJECT-TYPE
			SYNTAX OCTET STRING
			MAX-ACCESS read-only
			STATUS current
			DESCRIPTION
				"Port Name"
			::= { oltUplinkInfoEntry 2 }

				-- 1.3.6.1.4.1.5875.800.3.9.3.5.1.3
		uplinkDesc OBJECT-TYPE
			SYNTAX OCTET STRING
			MAX-ACCESS read-create
			STATUS current
			DESCRIPTION
				"Port Description"
			::= { oltUplinkInfoEntry 3 }

				-- 1.3.6.1.4.1.5875.800.3.9.3.5.1.4
		uplinkEnableStatus OBJECT-TYPE
			SYNTAX Integer32
			MAX-ACCESS read-only
			STATUS current
			DESCRIPTION
				"5116 Series
				1: Enable
				2: Disable
				
				5516 Series??
				1??Enable
				0??Disable
				"
			::= { oltUplinkInfoEntry 4 }

				-- 1.3.6.1.4.1.5875.800.3.9.3.5.1.5
		uplinkSpeed OBJECT-TYPE
			SYNTAX Integer32
			MAX-ACCESS read-only
			STATUS current
			DESCRIPTION
				"NGPON Series
				0:??10??
				1:??100??
				2:??1000??
				3: ??10000??
				Other:
				Mbps
				"
			::= { oltUplinkInfoEntry 5 }

				-- 1.3.6.1.4.1.5875.800.3.9.3.5.1.6
		uplinkMacStr OBJECT-TYPE
			SYNTAX OCTET STRING
			MAX-ACCESS read-only
			STATUS current
			DESCRIPTION
				"MAC+VID format??The MAC occupies 6 digits and the VID occupies 2 digits. Every 8 digits is a MAC mapping."
			::= { oltUplinkInfoEntry 6 }

				-- 1.3.6.1.4.1.5875.800.3.9.3.5.1.7
		oltUplinkTxOpticalPower OBJECT-TYPE
			SYNTAX Integer32
			MAX-ACCESS read-only
			STATUS current
			DESCRIPTION
				"Description."
			::= { oltUplinkInfoEntry 7 }

				-- 1.3.6.1.4.1.5875.800.3.9.3.5.1.8
		oltUplinkRxOpticalPower OBJECT-TYPE
			SYNTAX Integer32
			MAX-ACCESS read-only
			STATUS current
			DESCRIPTION
				"Description."
			::= { oltUplinkInfoEntry 8 }

				-- 1.3.6.1.4.1.5875.800.3.9.3.5.1.9
		oltUplinkOpticalTemperature OBJECT-TYPE
			SYNTAX Integer32
			MAX-ACCESS read-only
			STATUS current
			DESCRIPTION
				"Description."
			::= { oltUplinkInfoEntry 9 }

				-- 1.3.6.1.4.1.5875.800.3.9.3.5.1.10
		oltUplinkOpticalVltage OBJECT-TYPE
			SYNTAX Integer32
			MAX-ACCESS read-only
			STATUS current
			DESCRIPTION
				"Description."
			::= { oltUplinkInfoEntry 10 }

				-- 1.3.6.1.4.1.5875.800.3.9.3.5.1.11
		oltUplinkOpticalCurrent OBJECT-TYPE
			SYNTAX Integer32
			MAX-ACCESS read-only
			STATUS current
			DESCRIPTION
				"Description."
			::= { oltUplinkInfoEntry 11 }

				-- 1.3.6.1.4.1.5875.800.3.9.3.5.1.12
		oltUplinkOpticalModuleType OBJECT-TYPE
			SYNTAX Integer32
			MAX-ACCESS read-only
			STATUS current
			DESCRIPTION
				"Description."
			::= { oltUplinkInfoEntry 12 }

				-- 1.3.6.1.4.1.5875.800.3.9.3.5.1.13
		oltUplinkVendorName OBJECT-TYPE
			SYNTAX Integer32
			MAX-ACCESS read-only
			STATUS current
			DESCRIPTION
				"Description."
			::= { oltUplinkInfoEntry 13 }

				-- 1.3.6.1.4.1.5875.800.3.9.3.5.1.14
		oltUplinkVendorPn OBJECT-TYPE
			SYNTAX Integer32
			MAX-ACCESS read-only
			STATUS current
			DESCRIPTION
				"Description."
			::= { oltUplinkInfoEntry 14 }

				-- 1.3.6.1.4.1.5875.800.3.9.3.5.1.15
		oltUplinkVendorSn OBJECT-TYPE
			SYNTAX Integer32
			MAX-ACCESS read-only
			STATUS current
			DESCRIPTION
				"Description."
			::= { oltUplinkInfoEntry 15 }

				-- 1.3.6.1.4.1.5875.800.3.9.3.5.1.16
		oltUplinkDownwardAssociationSn OBJECT-TYPE
			SYNTAX Integer32
			MAX-ACCESS read-only
			STATUS current
			DESCRIPTION
				"Description."
			::= { oltUplinkInfoEntry 16 }

				-- 1.3.6.1.4.1.5875.800.3.9.3.6
		oltPonOpticalStatisticsTable OBJECT-TYPE
			SYNTAX SEQUENCE OF OltPonOpticalStatisticsEntry
			MAX-ACCESS not-accessible
			STATUS current
			DESCRIPTION
				"Description"
			::= { interfaceInfo 6 }

				-- 1.3.6.1.4.1.5875.800.3.9.3.6.1
		oltPonopticalStatisticsEntry OBJECT-TYPE
			SYNTAX OltPonOpticalStatisticsEntry
			MAX-ACCESS not-accessible
			STATUS current
			DESCRIPTION
				"Row Description"
			INDEX { ponIndex }
			::= { oltPonOpticalStatisticsTable 1 }

		
		OltPonOpticalStatisticsEntry ::=
			SEQUENCE { 
				oltPonOpticalStatisticsSwitch
					Integer32
			 }
		-- 1.3.6.1.4.1.5875.800.3.9.3.6.1.1
		oltPonOpticalStatisticsSwitch OBJECT-TYPE
			SYNTAX Integer32
			MAX-ACCESS read-create
			STATUS current
			DESCRIPTION
				"1: Enable
				0: Disable
				It is Enable by default for GPON and Disable is not supported.
				"
			::= { oltPonopticalStatisticsEntry 1 }

				-- 1.3.6.1.4.1.5875.800.3.9.3.7
		oltPonRxOpticalPowerTable OBJECT-TYPE
			SYNTAX SEQUENCE OF OltPonRxOpticalPowerEntry
			MAX-ACCESS not-accessible
			STATUS current
			DESCRIPTION
				"Description"
			::= { interfaceInfo 7 }

				-- 1.3.6.1.4.1.5875.800.3.9.3.7.1
		oltPonRxOpticalPowerEntry OBJECT-TYPE
			SYNTAX OltPonRxOpticalPowerEntry
			MAX-ACCESS not-accessible
			STATUS current
			DESCRIPTION
				"Row Description"
			INDEX { ponIndex, onuNoRxOpticalPower }
			::= { oltPonRxOpticalPowerTable 1 }

		
		OltPonRxOpticalPowerEntry ::=
			SEQUENCE { 
				onuNoRxOpticalPower
					Integer32,
				oltPonRxOpticalPower
					Integer32
			 }
		-- 1.3.6.1.4.1.5875.800.3.9.3.7.1.1
		onuNoRxOpticalPower OBJECT-TYPE
			SYNTAX Integer32 (1..10000)
			MAX-ACCESS read-only
			STATUS current
			DESCRIPTION
				"ONU Number (index)"
			::= { oltPonRxOpticalPowerEntry 1 }

				-- 1.3.6.1.4.1.5875.800.3.9.3.7.1.2
		oltPonRxOpticalPower OBJECT-TYPE
			SYNTAX Integer32
			MAX-ACCESS read-only
			STATUS current
			DESCRIPTION
				"The parameter value divided by 100 equals the actual value (Unit: Dbm)"
			::= { oltPonRxOpticalPowerEntry 2 }

				-- 1.3.6.1.4.1.5875.800.3.9.3.8
		oltPonInfoRealtimeTable OBJECT-TYPE
			SYNTAX SEQUENCE OF OltPonInfoRealtimeEntry
			MAX-ACCESS not-accessible
			STATUS current
			DESCRIPTION
				"Description"
			::= { interfaceInfo 8 }

				-- 1.3.6.1.4.1.5875.800.3.9.3.8.1
		oltPonInfoRealtimeEntry OBJECT-TYPE
			SYNTAX OltPonInfoRealtimeEntry
			MAX-ACCESS not-accessible
			STATUS current
			DESCRIPTION
				"Row Description"
			INDEX { ponIndex }
			::= { oltPonInfoRealtimeTable 1 }

		
		OltPonInfoRealtimeEntry ::=
			SEQUENCE { 
				oltPonTxOpticalPowerRealtime
					Integer32,
				oltPonOpticalTemperatureRealtime
					Integer32,
				oltPonOpticalVltageRealtime
					Integer32,
				oltPonOpticalCurrentRealtime
					Integer32,
				oltPonXgOpticalCurrentRealtime
					Integer32,
				oltPonXgTxOpticalPowerRealtime
					Integer32
			 }
		-- 1.3.6.1.4.1.5875.800.3.9.3.8.1.2
		oltPonTxOpticalPowerRealtime OBJECT-TYPE
			SYNTAX Integer32
			MAX-ACCESS read-only
			STATUS current
			DESCRIPTION
				"Column Description"
			::= { oltPonInfoRealtimeEntry 2 }

				-- 1.3.6.1.4.1.5875.800.3.9.3.8.1.3
		oltPonOpticalTemperatureRealtime OBJECT-TYPE
			SYNTAX Integer32
			MAX-ACCESS read-only
			STATUS current
			DESCRIPTION
				"Column Description"
			::= { oltPonInfoRealtimeEntry 3 }

				-- 1.3.6.1.4.1.5875.800.3.9.3.8.1.4
		oltPonOpticalVltageRealtime OBJECT-TYPE
			SYNTAX Integer32
			MAX-ACCESS read-only
			STATUS current
			DESCRIPTION
				"Column Description"
			::= { oltPonInfoRealtimeEntry 4 }

				-- 1.3.6.1.4.1.5875.800.3.9.3.8.1.5
		oltPonOpticalCurrentRealtime OBJECT-TYPE
			SYNTAX Integer32
			MAX-ACCESS read-only
			STATUS current
			DESCRIPTION
				"Column Description"
			::= { oltPonInfoRealtimeEntry 5 }

				-- 1.3.6.1.4.1.5875.800.3.9.3.8.1.6
		oltPonXgOpticalCurrentRealtime OBJECT-TYPE
			SYNTAX Integer32
			MAX-ACCESS read-only
			STATUS current
			DESCRIPTION
				"Description."
			::= { oltPonInfoRealtimeEntry 6 }

				-- 1.3.6.1.4.1.5875.800.3.9.3.8.1.7
		oltPonXgTxOpticalPowerRealtime OBJECT-TYPE
			SYNTAX Integer32
			MAX-ACCESS read-only
			STATUS current
			DESCRIPTION
				"Description."
			::= { oltPonInfoRealtimeEntry 7 }

				-- 1.3.6.1.4.1.5875.800.3.9.3.9
		oltPonRxOpticalPowerRealtimeTable OBJECT-TYPE
			SYNTAX SEQUENCE OF OltPonRxOpticalPowerRealtimeEntry
			MAX-ACCESS not-accessible
			STATUS current
			DESCRIPTION
				"Description"
			::= { interfaceInfo 9 }

				-- 1.3.6.1.4.1.5875.800.3.9.3.9.1
		oltPonRxOpticalPowerRealtimeEntry OBJECT-TYPE
			SYNTAX OltPonRxOpticalPowerRealtimeEntry
			MAX-ACCESS not-accessible
			STATUS current
			DESCRIPTION
				"Row Description"
			INDEX { ponIndex, onuNoRxOpticalPower }
			::= { oltPonRxOpticalPowerRealtimeTable 1 }

		
		OltPonRxOpticalPowerRealtimeEntry ::=
			SEQUENCE { 
				onuNoRxOpticalPowerRealtime
					Integer32,
				oltPonRxOpticalPowerRealtime
					Integer32
			 }
		-- 1.3.6.1.4.1.5875.800.3.9.3.9.1.1
		onuNoRxOpticalPowerRealtime OBJECT-TYPE
			SYNTAX Integer32 (1..10000)
			MAX-ACCESS read-only
			STATUS current
			DESCRIPTION
				"Column Description"
			::= { oltPonRxOpticalPowerRealtimeEntry 1 }

				-- 1.3.6.1.4.1.5875.800.3.9.3.9.1.2
		oltPonRxOpticalPowerRealtime OBJECT-TYPE
			SYNTAX Integer32
			MAX-ACCESS read-only
			STATUS current
			DESCRIPTION
				"Description"
			::= { oltPonRxOpticalPowerRealtimeEntry 2 }

				-- 1.3.6.1.4.1.5875.800.3.9.3.10
		onuPonInfoRealtimeTable OBJECT-TYPE
			SYNTAX SEQUENCE OF OnuPonInfoRealtimeEntry
			MAX-ACCESS not-accessible
			STATUS current
			DESCRIPTION
				"Description"
			::= { interfaceInfo 10 }

				-- 1.3.6.1.4.1.5875.800.3.9.3.10.1
		onuPonInfoRealtimeEntry OBJECT-TYPE
			SYNTAX OnuPonInfoRealtimeEntry
			MAX-ACCESS not-accessible
			STATUS current
			DESCRIPTION
				"Row Description"
			INDEX { onuIndex }
			::= { onuPonInfoRealtimeTable 1 }

		
		OnuPonInfoRealtimeEntry ::=
			SEQUENCE { 
				onuPonTxOpticalPowerRealtime
					Integer32,
				onuPonRxOpticalPowerRealtime
					Integer32,
				onuPonOpticalTemperatureRealtime
					Integer32,
				onuPonOpticalVltageRealtime
					Integer32,
				onuPonOpticalCurrentRealtime
					Integer32
			 }
		-- 1.3.6.1.4.1.5875.800.3.9.3.10.1.2
		onuPonTxOpticalPowerRealtime OBJECT-TYPE
			SYNTAX Integer32
			MAX-ACCESS read-only
			STATUS current
			DESCRIPTION
				"Column Description"
			::= { onuPonInfoRealtimeEntry 2 }

				-- 1.3.6.1.4.1.5875.800.3.9.3.10.1.3
		onuPonRxOpticalPowerRealtime OBJECT-TYPE
			SYNTAX Integer32
			MAX-ACCESS read-only
			STATUS current
			DESCRIPTION
				"Column Description"
			::= { onuPonInfoRealtimeEntry 3 }

				-- 1.3.6.1.4.1.5875.800.3.9.3.10.1.4
		onuPonOpticalTemperatureRealtime OBJECT-TYPE
			SYNTAX Integer32
			MAX-ACCESS read-only
			STATUS current
			DESCRIPTION
				"Column Description"
			::= { onuPonInfoRealtimeEntry 4 }

				-- 1.3.6.1.4.1.5875.800.3.9.3.10.1.5
		onuPonOpticalVltageRealtime OBJECT-TYPE
			SYNTAX Integer32
			MAX-ACCESS read-only
			STATUS current
			DESCRIPTION
				"Column Description"
			::= { onuPonInfoRealtimeEntry 5 }

				-- 1.3.6.1.4.1.5875.800.3.9.3.10.1.6
		onuPonOpticalCurrentRealtime OBJECT-TYPE
			SYNTAX Integer32
			MAX-ACCESS read-only
			STATUS current
			DESCRIPTION
				"Column Description"
			::= { onuPonInfoRealtimeEntry 6 }

				-- 1.3.6.1.4.1.5875.800.3.9.4
		sysInfo OBJECT IDENTIFIER ::= { systemInfo 4 }

				-- 1.3.6.1.4.1.5875.800.3.9.4.1
		sysIp OBJECT-TYPE
			SYNTAX IpAddress
			MAX-ACCESS read-only
			STATUS current
			DESCRIPTION
				"System IP"
			::= { sysInfo 1 }

				-- 1.3.6.1.4.1.5875.800.3.9.4.2
		sysMac OBJECT-TYPE
			SYNTAX MacAddress
			MAX-ACCESS read-only
			STATUS current
			DESCRIPTION
				"MAC Address"
			::= { sysInfo 2 }

				-- 1.3.6.1.4.1.5875.800.3.9.4.3
		sysSoftVersion OBJECT-TYPE
			SYNTAX OCTET STRING
			MAX-ACCESS read-only
			STATUS current
			DESCRIPTION
				"Software Version"
			::= { sysInfo 3 }

				-- 1.3.6.1.4.1.5875.800.3.9.4.4
		sysHardVersion OBJECT-TYPE
			SYNTAX OCTET STRING
			MAX-ACCESS read-only
			STATUS current
			DESCRIPTION
				"Hardware Version"
			::= { sysInfo 4 }

				-- 1.3.6.1.4.1.5875.800.3.9.4.5
		sysTemperature OBJECT-TYPE
			SYNTAX Integer32
			MAX-ACCESS read-only
			STATUS current
			DESCRIPTION
				"Device Temperature"
			::= { sysInfo 5 }

				-- 1.3.6.1.4.1.5875.800.3.9.4.6
		sysAuthOnuNum OBJECT-TYPE
			SYNTAX Integer32
			MAX-ACCESS read-only
			STATUS current
			DESCRIPTION
				"Description"
			::= { sysInfo 6 }

				-- 1.3.6.1.4.1.5875.800.3.9.4.7
		sysFtpServerIp OBJECT-TYPE
			SYNTAX IpAddress
			MAX-ACCESS read-write
			STATUS current
			DESCRIPTION
				"Description"
			::= { sysInfo 7 }

				-- 1.3.6.1.4.1.5875.800.3.9.4.8
		sysFtpServerName OBJECT-TYPE
			SYNTAX OCTET STRING
			MAX-ACCESS read-write
			STATUS current
			DESCRIPTION
				"Description"
			::= { sysInfo 8 }

				-- 1.3.6.1.4.1.5875.800.3.9.4.9
		sysFtpServerPwd OBJECT-TYPE
			SYNTAX OCTET STRING
			MAX-ACCESS read-write
			STATUS current
			DESCRIPTION
				"Description"
			::= { sysInfo 9 }

				-- 1.3.6.1.4.1.5875.800.3.9.4.10
		sysFtpFilename OBJECT-TYPE
			SYNTAX OCTET STRING
			MAX-ACCESS read-write
			STATUS current
			DESCRIPTION
				"Description"
			::= { sysInfo 10 }

				-- 1.3.6.1.4.1.5875.800.3.9.4.12
		sysFtpAction OBJECT-TYPE
			SYNTAX Integer32 (0..1024)
			MAX-ACCESS read-write
			STATUS current
			DESCRIPTION
				"Description"
			::= { sysInfo 12 }

				-- 1.3.6.1.4.1.5875.800.3.9.4.13
		sysCmdExecRetCode OBJECT-TYPE
			SYNTAX Integer32
			MAX-ACCESS read-only
			STATUS current
			DESCRIPTION
				"Command execution return code:
				
				Referenct command execution return code table."
			::= { sysInfo 13 }

				-- 1.3.6.1.4.1.5875.800.3.9.4.20
		sysGateway OBJECT-TYPE
			SYNTAX IpAddress
			MAX-ACCESS read-only
			STATUS current
			DESCRIPTION
				"Description"
			::= { sysInfo 20 }

				-- 1.3.6.1.4.1.5875.800.3.9.5
		slotInfoFor5516 OBJECT IDENTIFIER ::= { systemInfo 5 }

				-- 1.3.6.1.4.1.5875.800.3.9.5.1
		slotInfoTable OBJECT-TYPE
			SYNTAX SEQUENCE OF SlotInfoEntry
			MAX-ACCESS not-accessible
			STATUS current
			DESCRIPTION
				"Description"
			::= { slotInfoFor5516 1 }

				-- 1.3.6.1.4.1.5875.800.3.9.5.1.1
		slotInfoEntry OBJECT-TYPE
			SYNTAX SlotInfoEntry
			MAX-ACCESS not-accessible
			STATUS current
			DESCRIPTION
				"Row Description"
			INDEX { slotIndex }
			::= { slotInfoTable 1 }

		
		SlotInfoEntry ::=
			SEQUENCE { 
				occupiedStatus
					INTEGER,
				authCardType
					Integer32,
				occupiedCardType
					Integer32
			 }
		-- 1.3.6.1.4.1.5875.800.3.9.5.1.1.2
		occupiedStatus OBJECT-TYPE
			SYNTAX INTEGER
				{
				occupied(1),
				empty(0)
				}
			MAX-ACCESS read-only
			STATUS current
			DESCRIPTION
				"1: present
				0: not present
				"
			::= { slotInfoEntry 2 }

				-- 1.3.6.1.4.1.5875.800.3.9.5.1.1.3
		authCardType OBJECT-TYPE
			SYNTAX Integer32
			MAX-ACCESS read-only
			STATUS current
			DESCRIPTION
				"5516 Series??
				355: HSWA
				379: HSWB
				365: HSWD
				360: HSUA
				374: HSUB
				378: HSUC
				508: EC4B
				514: EC8B
				552: ECOB
				502: GC4B
				527: GC8B
				550: GCOB
				545: XP4A
				575: XP8A
				605: CE1B
				602: C155A
				413: GU6F
				420: GS8F
				414: HU2A
				415: HU1A
				526 :XG2B
				555: XG4B
				553: XG8A
				549: GSOF
				610: CIO
				611: PWR
				741: FAN
				"
			::= { slotInfoEntry 3 }

				-- 1.3.6.1.4.1.5875.800.3.9.5.1.1.4
		occupiedCardType OBJECT-TYPE
			SYNTAX Integer32
			MAX-ACCESS read-only
			STATUS current
			DESCRIPTION
				"5516 Series??
				355: HSWA
				379: HSWB
				365: HSWD
				360: HSUA
				374: HSUB
				378: HSUC
				508: EC4B
				514: EC8B
				552: ECOB
				502: GC4B
				527: GC8B
				550: GCOB
				545: XP4A
				575: XP8A
				605: CE1B
				602: C155A
				413: GU6F
				420: GS8F
				414: HU2A
				415: HU1A
				526: XG2B
				555: XG4B
				553: XG8A
				549: GSOF
				610: CIO
				611: PWR
				741: FAN
				0: no line card is detected
				
				"
			::= { slotInfoEntry 4 }

				-- 1.3.6.1.4.1.5875.800.3.9.6
		onu2PonLength OBJECT IDENTIFIER ::= { systemInfo 6 }

				-- 1.3.6.1.4.1.5875.800.3.9.6.1
		onu2PonLengthTable OBJECT-TYPE
			SYNTAX SEQUENCE OF Onu2PonLengthEntry
			MAX-ACCESS not-accessible
			STATUS current
			DESCRIPTION
				"Description"
			::= { onu2PonLength 1 }

				-- 1.3.6.1.4.1.5875.800.3.9.6.1.1
		onu2PonLengthEntry OBJECT-TYPE
			SYNTAX Onu2PonLengthEntry
			MAX-ACCESS not-accessible
			STATUS current
			DESCRIPTION
				"Row Description"
			INDEX { onuIndex }
			::= { onu2PonLengthTable 1 }

		
		Onu2PonLengthEntry ::=
			SEQUENCE { 
				length
					Integer32
			 }
		-- 1.3.6.1.4.1.5875.800.3.9.6.1.1.1
		length OBJECT-TYPE
			SYNTAX Integer32
			MAX-ACCESS read-only
			STATUS current
			DESCRIPTION
				"The ONU status should be online; otherwise the returned value is 0."
			::= { onu2PonLengthEntry 1 }

				-- 1.3.6.1.4.1.5875.800.3.9.8
		mgrCardInfo OBJECT IDENTIFIER ::= { systemInfo 8 }

				-- 1.3.6.1.4.1.5875.800.3.9.8.1
		mgrCardInfoTable OBJECT-TYPE
			SYNTAX SEQUENCE OF MgrCardInfoEntry
			MAX-ACCESS not-accessible
			STATUS current
			DESCRIPTION
				"Description"
			::= { mgrCardInfo 1 }

				-- 1.3.6.1.4.1.5875.800.3.9.8.1.1
		mgrCardInfoEntry OBJECT-TYPE
			SYNTAX MgrCardInfoEntry
			MAX-ACCESS not-accessible
			STATUS current
			DESCRIPTION
				"Row Description"
			INDEX { slotIndex }
			::= { mgrCardInfoTable 1 }

		
		MgrCardInfoEntry ::=
			SEQUENCE { 
				mgrCardType
					Integer32,
				mgrCardHandwareVersion
					OCTET STRING,
				mgrCardSoftwareVession
					OCTET STRING,
				mgrCardWorkStatus
					Integer32,
				mgrCardCpuUtil
					Integer32,
				mgrCardMemUtil
					Integer32
			 }
		-- 1.3.6.1.4.1.5875.800.3.9.8.1.1.1
		mgrCardType OBJECT-TYPE
			SYNTAX Integer32
			MAX-ACCESS read-only
			STATUS current
			DESCRIPTION
				"AN 5116 Series: 350: GSWC
				
				5516 Series??
				355??HSWA
				
				"
			::= { mgrCardInfoEntry 1 }

				-- 1.3.6.1.4.1.5875.800.3.9.8.1.1.2
		mgrCardHandwareVersion OBJECT-TYPE
			SYNTAX OCTET STRING
			MAX-ACCESS read-only
			STATUS current
			DESCRIPTION
				"Hardware Version"
			::= { mgrCardInfoEntry 2 }

				-- 1.3.6.1.4.1.5875.800.3.9.8.1.1.3
		mgrCardSoftwareVession OBJECT-TYPE
			SYNTAX OCTET STRING
			MAX-ACCESS read-only
			STATUS current
			DESCRIPTION
				"Software Version"
			::= { mgrCardInfoEntry 3 }

				-- 1.3.6.1.4.1.5875.800.3.9.8.1.1.4
		mgrCardWorkStatus OBJECT-TYPE
			SYNTAX Integer32
			MAX-ACCESS read-only
			STATUS current
			DESCRIPTION
				"1: Normal,
				0: Interrupted
				"
			::= { mgrCardInfoEntry 4 }

				-- 1.3.6.1.4.1.5875.800.3.9.8.1.1.5
		mgrCardCpuUtil OBJECT-TYPE
			SYNTAX Integer32
			MAX-ACCESS read-only
			STATUS current
			DESCRIPTION
				"The parameter value divided by 100 equals the actual value"
			::= { mgrCardInfoEntry 5 }

				-- 1.3.6.1.4.1.5875.800.3.9.8.1.1.6
		mgrCardMemUtil OBJECT-TYPE
			SYNTAX Integer32
			MAX-ACCESS read-only
			STATUS current
			DESCRIPTION
				"The parameter value divided by 100 equals the actual value"
			::= { mgrCardInfoEntry 6 }

				-- 1.3.6.1.4.1.5875.800.3.9.9
		onuAddressInfo OBJECT IDENTIFIER ::= { systemInfo 9 }

				-- 1.3.6.1.4.1.5875.800.3.9.9.1
		onuAddressInfoTable OBJECT-TYPE
			SYNTAX SEQUENCE OF OnuAddressInfoEntry
			MAX-ACCESS not-accessible
			STATUS current
			DESCRIPTION
				"Description"
			::= { onuAddressInfo 1 }

				-- 1.3.6.1.4.1.5875.800.3.9.9.1.1
		onuAddressInfoEntry OBJECT-TYPE
			SYNTAX OnuAddressInfoEntry
			MAX-ACCESS not-accessible
			STATUS current
			DESCRIPTION
				"Row Description"
			INDEX { onuAddressManageIp }
			::= { onuAddressInfoTable 1 }

		
		OnuAddressInfoEntry ::=
			SEQUENCE { 
				onuAddressManageIp
					IpAddress,
				onuAddressSlot
					Integer32,
				onuAddressPon
					Integer32,
				onuAddressOnuId
					Integer32,
				onuAddressOnuIfIndex
					Integer32
			 }
		-- 1.3.6.1.4.1.5875.800.3.9.9.1.1.1
		onuAddressManageIp OBJECT-TYPE
			SYNTAX IpAddress
			MAX-ACCESS not-accessible
			STATUS current
			DESCRIPTION
				"Index (decimal notation)"
			::= { onuAddressInfoEntry 1 }

				-- 1.3.6.1.4.1.5875.800.3.9.9.1.1.2
		onuAddressSlot OBJECT-TYPE
			SYNTAX Integer32
			MAX-ACCESS read-only
			STATUS current
			DESCRIPTION
				"ONU slot"
			::= { onuAddressInfoEntry 2 }

				-- 1.3.6.1.4.1.5875.800.3.9.9.1.1.3
		onuAddressPon OBJECT-TYPE
			SYNTAX Integer32
			MAX-ACCESS read-only
			STATUS current
			DESCRIPTION
				"ONU PON port"
			::= { onuAddressInfoEntry 3 }

				-- 1.3.6.1.4.1.5875.800.3.9.9.1.1.4
		onuAddressOnuId OBJECT-TYPE
			SYNTAX Integer32
			MAX-ACCESS read-only
			STATUS current
			DESCRIPTION
				"ONU number"
			::= { onuAddressInfoEntry 4 }

				-- 1.3.6.1.4.1.5875.800.3.9.9.1.1.5
		onuAddressOnuIfIndex OBJECT-TYPE
			SYNTAX Integer32
			MAX-ACCESS read-only
			STATUS current
			DESCRIPTION
				"Column Description"
			::= { onuAddressInfoEntry 5 }

				-- 1.3.6.1.4.1.5875.800.3.10
		authOnuInf OBJECT IDENTIFIER ::= { oltData 10 }

				-- 1.3.6.1.4.1.5875.800.3.10.1
		authOnuListTable OBJECT-TYPE
			SYNTAX SEQUENCE OF AuthOnuListEntry
			MAX-ACCESS not-accessible
			STATUS current
			DESCRIPTION
				"Description"
			::= { authOnuInf 1 }

				-- 1.3.6.1.4.1.5875.800.3.10.1.1
		authOnuListEntry OBJECT-TYPE
			SYNTAX AuthOnuListEntry
			MAX-ACCESS not-accessible
			STATUS current
			DESCRIPTION
				"Row Description"
			INDEX { onuIndex }
			::= { authOnuListTable 1 }

		
		AuthOnuListEntry ::=
			SEQUENCE { 
				authOnuListSlot
					Integer32,
				authOnuListPon
					Integer32,
				authOnuListOnuid
					Integer32,
				authOnuListOnuType
					Integer32,
				authOnuListIp
					OCTET STRING,
				authOnuListName
					OCTET STRING,
				authOnuListSnLoid
					OCTET STRING,
				authOnuListSnPwd
					OCTET STRING,
				authOnuListMac
					OCTET STRING,
				onuStatus
					Integer32,
				authOnuSoftwareVersion
					OCTET STRING,
				authOnuHardwareVersion
					OCTET STRING,
				authOnuFirmwareVersion
					OCTET STRING,
				authOnuListOnuReboot
					INTEGER,
				authOnuCpuUsage
					Integer32,
				authOnuMemoryUsage
					Integer32,
				authOnuWebSwitch
					Integer32,
				authOnuWebPort
					Integer32,
				authOnuWebAdmin
					OCTET STRING,
				authOnuWebAdminPassword
					OCTET STRING,
				authOnuOpticalSwitch
					Integer32,
				authOnuWebServerSwitch
					Integer32,
				authOnuTelnetServerSwitch
					Integer32,
				authOnuWebUNIswitch
					Integer32,
				authOnuTelnetUNIswitch
					Integer32,
				authOnuConsoleSwitch
					Integer32,
				authOnuMacNumberLimit
					Integer32,
				authOnuMacNumberLimitApply
					Integer32,
				authOnuLastUp
					OCTET STRING,
				authOnuLastDown
					OCTET STRING,
				authOnuRegKey
					OCTET STRING,
				authOnuRegType
					Integer32
			 }
		-- 1.3.6.1.4.1.5875.800.3.10.1.1.2
		authOnuListSlot OBJECT-TYPE
			SYNTAX Integer32
			MAX-ACCESS read-only
			STATUS current
			DESCRIPTION
				"Slot Number"
			::= { authOnuListEntry 2 }

				-- 1.3.6.1.4.1.5875.800.3.10.1.1.3
		authOnuListPon OBJECT-TYPE
			SYNTAX Integer32
			MAX-ACCESS read-only
			STATUS current
			DESCRIPTION
				"PON Number"
			::= { authOnuListEntry 3 }

				-- 1.3.6.1.4.1.5875.800.3.10.1.1.4
		authOnuListOnuid OBJECT-TYPE
			SYNTAX Integer32
			MAX-ACCESS read-only
			STATUS current
			DESCRIPTION
				"ONU Number"
			::= { authOnuListEntry 4 }

				-- 1.3.6.1.4.1.5875.800.3.10.1.1.5
		authOnuListOnuType OBJECT-TYPE
			SYNTAX Integer32
			MAX-ACCESS read-only
			STATUS current
			DESCRIPTION
				"The 5116:
				0: offline or fiber cut
				1: online
				2: power cut
				The 5516:
				0: fiber cut
				1: online
				2: power cut
				3: offline
				The NGPON:
				0: offline or fiber cut / power cut 
				1: online
				"
			::= { authOnuListEntry 5 }

				-- 1.3.6.1.4.1.5875.800.3.10.1.1.6
		authOnuListIp OBJECT-TYPE
			SYNTAX OCTET STRING
			MAX-ACCESS read-only
			STATUS current
			DESCRIPTION
				"See ONU correspondence table below"
			::= { authOnuListEntry 6 }

				-- 1.3.6.1.4.1.5875.800.3.10.1.1.7
		authOnuListName OBJECT-TYPE
			SYNTAX OCTET STRING
			MAX-ACCESS read-only
			STATUS current
			DESCRIPTION
				"Device name (not available)"
			::= { authOnuListEntry 7 }

				-- 1.3.6.1.4.1.5875.800.3.10.1.1.8
		authOnuListSnLoid OBJECT-TYPE
			SYNTAX OCTET STRING
			MAX-ACCESS read-only
			STATUS current
			DESCRIPTION
				"ONU Logic Authentication Identifier"
			::= { authOnuListEntry 8 }

				-- 1.3.6.1.4.1.5875.800.3.10.1.1.9
		authOnuListSnPwd OBJECT-TYPE
			SYNTAX OCTET STRING
			MAX-ACCESS read-only
			STATUS current
			DESCRIPTION
				"ONU Logic Authentication "
			::= { authOnuListEntry 9 }

				-- 1.3.6.1.4.1.5875.800.3.10.1.1.10
		authOnuListMac OBJECT-TYPE
			SYNTAX OCTET STRING
			MAX-ACCESS read-only
			STATUS current
			DESCRIPTION
				"ONU MAC Address"
			::= { authOnuListEntry 10 }

				-- 1.3.6.1.4.1.5875.800.3.10.1.1.11
		onuStatus OBJECT-TYPE
			SYNTAX Integer32 (0..1)
			MAX-ACCESS read-only
			STATUS current
			DESCRIPTION
				"Description:
				1:offonline/fiber cut/power failure(0)
				2:online(1)"
			::= { authOnuListEntry 11 }

				-- 1.3.6.1.4.1.5875.800.3.10.1.1.12
		authOnuSoftwareVersion OBJECT-TYPE
			SYNTAX OCTET STRING
			MAX-ACCESS read-only
			STATUS current
			DESCRIPTION
				"CPU software version. It is not available for the ONU without CPU and the HG device."
			::= { authOnuListEntry 12 }

				-- 1.3.6.1.4.1.5875.800.3.10.1.1.13
		authOnuHardwareVersion OBJECT-TYPE
			SYNTAX OCTET STRING
			MAX-ACCESS read-only
			STATUS current
			DESCRIPTION
				"ONU Hardware Version"
			::= { authOnuListEntry 13 }

				-- 1.3.6.1.4.1.5875.800.3.10.1.1.14
		authOnuFirmwareVersion OBJECT-TYPE
			SYNTAX OCTET STRING
			MAX-ACCESS read-only
			STATUS current
			DESCRIPTION
				"ONU Firmware Version"
			::= { authOnuListEntry 14 }

				-- 1.3.6.1.4.1.5875.800.3.10.1.1.15
		authOnuListOnuReboot OBJECT-TYPE
			SYNTAX INTEGER
				{
				normal(0),
				reboot(1)
				}
			MAX-ACCESS read-create
			STATUS current
			DESCRIPTION
				"Control command
				1??Restart 
				0??Normal (only for query)
				"
			::= { authOnuListEntry 15 }

				-- 1.3.6.1.4.1.5875.800.3.10.1.1.16
		authOnuCpuUsage OBJECT-TYPE
			SYNTAX Integer32
			MAX-ACCESS read-only
			STATUS current
			DESCRIPTION
				"Description"
			::= { authOnuListEntry 16 }

				-- 1.3.6.1.4.1.5875.800.3.10.1.1.17
		authOnuMemoryUsage OBJECT-TYPE
			SYNTAX Integer32
			MAX-ACCESS read-only
			STATUS current
			DESCRIPTION
				"Description"
			::= { authOnuListEntry 17 }

				-- 1.3.6.1.4.1.5875.800.3.10.1.1.18
		authOnuWebSwitch OBJECT-TYPE
			SYNTAX Integer32
			MAX-ACCESS read-create
			STATUS current
			DESCRIPTION
				"Description"
			::= { authOnuListEntry 18 }

				-- 1.3.6.1.4.1.5875.800.3.10.1.1.19
		authOnuWebPort OBJECT-TYPE
			SYNTAX Integer32
			MAX-ACCESS read-create
			STATUS current
			DESCRIPTION
				"Description"
			::= { authOnuListEntry 19 }

				-- 1.3.6.1.4.1.5875.800.3.10.1.1.20
		authOnuWebAdmin OBJECT-TYPE
			SYNTAX OCTET STRING
			MAX-ACCESS read-create
			STATUS current
			DESCRIPTION
				"Description"
			::= { authOnuListEntry 20 }

				-- 1.3.6.1.4.1.5875.800.3.10.1.1.21
		authOnuWebAdminPassword OBJECT-TYPE
			SYNTAX OCTET STRING
			MAX-ACCESS read-create
			STATUS current
			DESCRIPTION
				"Description"
			::= { authOnuListEntry 21 }

				-- 1.3.6.1.4.1.5875.800.3.10.1.1.22
		authOnuOpticalSwitch OBJECT-TYPE
			SYNTAX Integer32
			MAX-ACCESS read-create
			STATUS current
			DESCRIPTION
				"Description"
			::= { authOnuListEntry 22 }

				-- 1.3.6.1.4.1.5875.800.3.10.1.1.23
		authOnuWebServerSwitch OBJECT-TYPE
			SYNTAX Integer32
			MAX-ACCESS read-create
			STATUS current
			DESCRIPTION
				"Description"
			::= { authOnuListEntry 23 }

				-- 1.3.6.1.4.1.5875.800.3.10.1.1.24
		authOnuTelnetServerSwitch OBJECT-TYPE
			SYNTAX Integer32
			MAX-ACCESS read-create
			STATUS current
			DESCRIPTION
				"Description"
			::= { authOnuListEntry 24 }

				-- 1.3.6.1.4.1.5875.800.3.10.1.1.25
		authOnuWebUNIswitch OBJECT-TYPE
			SYNTAX Integer32
			MAX-ACCESS read-create
			STATUS current
			DESCRIPTION
				"Description"
			::= { authOnuListEntry 25 }

				-- 1.3.6.1.4.1.5875.800.3.10.1.1.26
		authOnuTelnetUNIswitch OBJECT-TYPE
			SYNTAX Integer32
			MAX-ACCESS read-create
			STATUS current
			DESCRIPTION
				"Description"
			::= { authOnuListEntry 26 }

				-- 1.3.6.1.4.1.5875.800.3.10.1.1.27
		authOnuConsoleSwitch OBJECT-TYPE
			SYNTAX Integer32
			MAX-ACCESS read-create
			STATUS current
			DESCRIPTION
				"Description"
			::= { authOnuListEntry 27 }

				-- 1.3.6.1.4.1.5875.800.3.10.1.1.28
		authOnuMacNumberLimit OBJECT-TYPE
			SYNTAX Integer32
			MAX-ACCESS read-create
			STATUS current
			DESCRIPTION
				"That is ONU PON port limit.
				0-16 000??
				0:No Limit
				˵????
				After configuration is complete without the use of the 1.3.6.1.4.1.5875.800.3.10.1.1.29
				The application is not effective
				"
			::= { authOnuListEntry 28 }

				-- 1.3.6.1.4.1.5875.800.3.10.1.1.29
		authOnuMacNumberLimitApply OBJECT-TYPE
			SYNTAX Integer32
			MAX-ACCESS read-create
			STATUS current
			DESCRIPTION
				"Application of the ONU representation 
				1??Apply
				"
			::= { authOnuListEntry 29 }

				-- 1.3.6.1.4.1.5875.800.3.10.1.1.30
		authOnuLastUp OBJECT-TYPE
			SYNTAX OCTET STRING
			MAX-ACCESS read-only
			STATUS current
			DESCRIPTION
				"Description."
			::= { authOnuListEntry 30 }

				-- 1.3.6.1.4.1.5875.800.3.10.1.1.31
		authOnuLastDown OBJECT-TYPE
			SYNTAX OCTET STRING
			MAX-ACCESS read-only
			STATUS current
			DESCRIPTION
				"Description."
			::= { authOnuListEntry 31 }

				-- 1.3.6.1.4.1.5875.800.3.10.1.1.32
		authOnuRegKey OBJECT-TYPE
			SYNTAX OCTET STRING
			MAX-ACCESS read-only
			STATUS current
			DESCRIPTION
				"Description."
			::= { authOnuListEntry 32 }

				-- 1.3.6.1.4.1.5875.800.3.10.1.1.33
		authOnuRegType OBJECT-TYPE
			SYNTAX Integer32
			MAX-ACCESS read-only
			STATUS current
			DESCRIPTION
				"Description."
			::= { authOnuListEntry 33 }

				-- 1.3.6.1.4.1.5875.800.3.11
		unauthOnuList OBJECT IDENTIFIER ::= { oltData 11 }

				-- 1.3.6.1.4.1.5875.800.3.11.1
		unauthOnuListTable OBJECT-TYPE
			SYNTAX SEQUENCE OF UnauthOnuListEntry
			MAX-ACCESS not-accessible
			STATUS current
			DESCRIPTION
				"Description"
			::= { unauthOnuList 1 }

				-- 1.3.6.1.4.1.5875.800.3.11.1.1
		unauthOnuListEntry OBJECT-TYPE
			SYNTAX UnauthOnuListEntry
			MAX-ACCESS not-accessible
			STATUS current
			DESCRIPTION
				"Row Description"
			INDEX { unauthOnuListOnuIndex }
			::= { unauthOnuListTable 1 }

		
		UnauthOnuListEntry ::=
			SEQUENCE { 
				unauthOnuListOnuIndex
					Integer32,
				unauthOnuListSlot
					Integer32,
				unauthOnuListPon
					Integer32,
				unauthOnuListOnuType
					Integer32,
				unauthOnuListSnLoid
					OCTET STRING,
				unauthOnuListPwd
					OCTET STRING,
				unauthOnuListMac
					OCTET STRING
			 }
		-- 1.3.6.1.4.1.5875.800.3.11.1.1.1
		unauthOnuListOnuIndex OBJECT-TYPE
			SYNTAX Integer32 (1..10000)
			MAX-ACCESS read-only
			STATUS current
			DESCRIPTION
				"Column Description"
			::= { unauthOnuListEntry 1 }

				-- 1.3.6.1.4.1.5875.800.3.11.1.1.2
		unauthOnuListSlot OBJECT-TYPE
			SYNTAX Integer32
			MAX-ACCESS read-only
			STATUS current
			DESCRIPTION
				"SLOT Number"
			::= { unauthOnuListEntry 2 }

				-- 1.3.6.1.4.1.5875.800.3.11.1.1.3
		unauthOnuListPon OBJECT-TYPE
			SYNTAX Integer32
			MAX-ACCESS read-only
			STATUS current
			DESCRIPTION
				"PON Number"
			::= { unauthOnuListEntry 3 }

				-- 1.3.6.1.4.1.5875.800.3.11.1.1.4
		unauthOnuListOnuType OBJECT-TYPE
			SYNTAX Integer32
			MAX-ACCESS read-only
			STATUS current
			DESCRIPTION
				"See ONU type correspondence table"
			::= { unauthOnuListEntry 4 }

				-- 1.3.6.1.4.1.5875.800.3.11.1.1.5
		unauthOnuListSnLoid OBJECT-TYPE
			SYNTAX OCTET STRING
			MAX-ACCESS read-only
			STATUS current
			DESCRIPTION
				"SN Logical Serial Number"
			::= { unauthOnuListEntry 5 }

				-- 1.3.6.1.4.1.5875.800.3.11.1.1.6
		unauthOnuListPwd OBJECT-TYPE
			SYNTAX OCTET STRING
			MAX-ACCESS read-only
			STATUS current
			DESCRIPTION
				"SN Password"
			::= { unauthOnuListEntry 6 }

				-- 1.3.6.1.4.1.5875.800.3.11.1.1.7
		unauthOnuListMac OBJECT-TYPE
			SYNTAX OCTET STRING
			MAX-ACCESS read-only
			STATUS current
			DESCRIPTION
				"MAC Address"
			::= { unauthOnuListEntry 7 }

				-- 1.3.6.1.4.1.5875.800.3.12
		onuAuthModeFor5116 OBJECT IDENTIFIER ::= { oltData 12 }

				-- 1.3.6.1.4.1.5875.800.3.12.1
		onuAuthModeTable OBJECT-TYPE
			SYNTAX SEQUENCE OF OnuAuthModeEntry
			MAX-ACCESS not-accessible
			STATUS current
			DESCRIPTION
				"Description"
			::= { onuAuthModeFor5116 1 }

				-- 1.3.6.1.4.1.5875.800.3.12.1.1
		onuAuthModeEntry OBJECT-TYPE
			SYNTAX OnuAuthModeEntry
			MAX-ACCESS not-accessible
			STATUS current
			DESCRIPTION
				"Row Description"
			INDEX { slotIndex }
			::= { onuAuthModeTable 1 }

		
		OnuAuthModeEntry ::=
			SEQUENCE { 
				macAuthEnable
					TruthValue,
				snAuthEnable
					TruthValue
			 }
		-- 1.3.6.1.4.1.5875.800.3.12.1.1.2
		macAuthEnable OBJECT-TYPE
			SYNTAX TruthValue
			MAX-ACCESS read-create
			STATUS current
			DESCRIPTION
				"1: enable
				0: disable
				"
			::= { onuAuthModeEntry 2 }

				-- 1.3.6.1.4.1.5875.800.3.12.1.1.3
		snAuthEnable OBJECT-TYPE
			SYNTAX TruthValue
			MAX-ACCESS read-create
			STATUS current
			DESCRIPTION
				"1: enable
				0: disable
				"
			::= { onuAuthModeEntry 3 }

				-- 1.3.6.1.4.1.5875.800.3.13
		onuWarrantTypeFor5116 OBJECT IDENTIFIER ::= { oltData 13 }

				-- 1.3.6.1.4.1.5875.800.3.13.1
		onuWarrentTypeTable OBJECT-TYPE
			SYNTAX SEQUENCE OF OnuWarrentTypeEntry
			MAX-ACCESS not-accessible
			STATUS current
			DESCRIPTION
				"Description"
			::= { onuWarrantTypeFor5116 1 }

				-- 1.3.6.1.4.1.5875.800.3.13.1.1
		onuWarrentTypeEntry OBJECT-TYPE
			SYNTAX OnuWarrentTypeEntry
			MAX-ACCESS not-accessible
			STATUS current
			DESCRIPTION
				"Row Description"
			INDEX { slotIndex }
			::= { onuWarrentTypeTable 1 }

		
		OnuWarrentTypeEntry ::=
			SEQUENCE { 
				warrantType
					Integer32
			 }
		-- 1.3.6.1.4.1.5875.800.3.13.1.1.2
		warrantType OBJECT-TYPE
			SYNTAX Integer32
			MAX-ACCESS read-create
			STATUS current
			DESCRIPTION
				"1: manual mode
				2: auto mode
				3: mixed mode
				"
			::= { onuWarrentTypeEntry 2 }

				-- 1.3.6.1.4.1.5875.800.3.14
		ponAuthModeFor5516 OBJECT IDENTIFIER ::= { oltData 14 }

				-- 1.3.6.1.4.1.5875.800.3.14.1
		ponAuthModeTable OBJECT-TYPE
			SYNTAX SEQUENCE OF PonAuthModeEntry
			MAX-ACCESS not-accessible
			STATUS current
			DESCRIPTION
				"Description"
			::= { ponAuthModeFor5516 1 }

				-- 1.3.6.1.4.1.5875.800.3.14.1.1
		ponAuthModeEntry OBJECT-TYPE
			SYNTAX PonAuthModeEntry
			MAX-ACCESS not-accessible
			STATUS current
			DESCRIPTION
				"Row Description"
			INDEX { ponIndex }
			::= { ponAuthModeTable 1 }

		
		PonAuthModeEntry ::=
			SEQUENCE { 
				authMode
					Integer32
			 }
		-- 1.3.6.1.4.1.5875.800.3.14.1.1.2
		authMode OBJECT-TYPE
			SYNTAX Integer32 (0..8)
			MAX-ACCESS read-create
			STATUS current
			DESCRIPTION
				"NGPON: 
				0- Physical identifier authentication;.
				1- Physical identifier + physical password authentication.
				2- Physical password authentication.
				3- Logical identifier + logical password authentication.
				4- Physical identifier / logical identifier (containing password) authentication.
				5- Unauthentication.
				6- Logical identifier authentication (not containing password).
				7- Physical identifier / logical identifier (not containing password) authentication.
				8- Logical password authentication
				"
			::= { ponAuthModeEntry 2 }

				-- 1.3.6.1.4.1.5875.800.3.15
		cardWarrentFor5516 OBJECT IDENTIFIER ::= { oltData 15 }

				-- 1.3.6.1.4.1.5875.800.3.15.1
		cardWarrentTable OBJECT-TYPE
			SYNTAX SEQUENCE OF CardWarrentEntry
			MAX-ACCESS not-accessible
			STATUS current
			DESCRIPTION
				"Description"
			::= { cardWarrentFor5516 1 }

				-- 1.3.6.1.4.1.5875.800.3.15.1.1
		cardWarrentEntry OBJECT-TYPE
			SYNTAX CardWarrentEntry
			MAX-ACCESS not-accessible
			STATUS current
			DESCRIPTION
				"Row Description"
			INDEX { slotIndex }
			::= { cardWarrentTable 1 }

		
		CardWarrentEntry ::=
			SEQUENCE { 
				warrentCardType
					Integer32
			 }
		-- 1.3.6.1.4.1.5875.800.3.15.1.1.2
		warrentCardType OBJECT-TYPE
			SYNTAX Integer32
			MAX-ACCESS read-create
			STATUS current
			DESCRIPTION
				"See correspondence table"
			::= { cardWarrentEntry 2 }

				-- 1.3.6.1.4.1.5875.800.3.16
		globalVlan OBJECT IDENTIFIER ::= { oltData 16 }

				-- 1.3.6.1.4.1.5875.800.3.16.1
		globalVlanTable OBJECT-TYPE
			SYNTAX SEQUENCE OF GlobalVlanEntry
			MAX-ACCESS not-accessible
			STATUS current
			DESCRIPTION
				"Description"
			::= { globalVlan 1 }

				-- 1.3.6.1.4.1.5875.800.3.16.1.1
		globalVlanEntry OBJECT-TYPE
			SYNTAX GlobalVlanEntry
			MAX-ACCESS not-accessible
			STATUS current
			DESCRIPTION
				"Row Description"
			INDEX { vlanConfigId }
			::= { globalVlanTable 1 }

		
		GlobalVlanEntry ::=
			SEQUENCE { 
				vlanConfigId
					Integer32,
				serviceName
					OCTET STRING,
				beginVlanId
					Integer32,
				endVlanId
					Integer32,
				upLinkPort
					Integer32,
				tagStatus
					INTEGER,
				globalVlanAction
					INTEGER
			 }
		-- 1.3.6.1.4.1.5875.800.3.16.1.1.1
		vlanConfigId OBJECT-TYPE
			SYNTAX Integer32 (1..10000)
			MAX-ACCESS read-only
			STATUS current
			DESCRIPTION
				"Local VLAN configuration
				101-4195"
			::= { globalVlanEntry 1 }

				-- 1.3.6.1.4.1.5875.800.3.16.1.1.2
		serviceName OBJECT-TYPE
			SYNTAX OCTET STRING
			MAX-ACCESS read-create
			STATUS current
			DESCRIPTION
				"Service Name
				The max
				length of service name is:23"
			::= { globalVlanEntry 2 }

				-- 1.3.6.1.4.1.5875.800.3.16.1.1.3
		beginVlanId OBJECT-TYPE
			SYNTAX Integer32 (0..1024)
			MAX-ACCESS read-create
			STATUS current
			DESCRIPTION
				"Outer Starting VLAN ID
				1-4085"
			::= { globalVlanEntry 3 }

				-- 1.3.6.1.4.1.5875.800.3.16.1.1.4
		endVlanId OBJECT-TYPE
			SYNTAX Integer32
			MAX-ACCESS read-create
			STATUS current
			DESCRIPTION
				"Outer Ending VLAN ID
				1-4085"
			::= { globalVlanEntry 4 }

				-- 1.3.6.1.4.1.5875.800.3.16.1.1.5
		upLinkPort OBJECT-TYPE
			SYNTAX Integer32
			MAX-ACCESS read-create
			STATUS current
			DESCRIPTION
				"1-7
				51-TRUNK group 1 (TRUNK group 1) 
				52- TRUNK group 2 (TRUNK group 2) 
				53- TRUNK group 3 (TRUNK group 3) 
				"
			::= { globalVlanEntry 5 }

				-- 1.3.6.1.4.1.5875.800.3.16.1.1.6
		tagStatus OBJECT-TYPE
			SYNTAX INTEGER
				{
				tag(1),
				untag(0)
				}
			MAX-ACCESS read-create
			STATUS current
			DESCRIPTION
				"NGPON: 
				0 untag
				1 tag
				"
			::= { globalVlanEntry 6 }

				-- 1.3.6.1.4.1.5875.800.3.16.1.1.7
		globalVlanAction OBJECT-TYPE
			SYNTAX INTEGER
				{
				active(1),
				create(4),
				destroy(6),
				modify(7)
				}
			MAX-ACCESS read-create
			STATUS current
			DESCRIPTION
				"4:create
				6:delete
				7:modify
				"
			::= { globalVlanEntry 7 }

				-- 1.3.6.1.4.1.5875.800.3.16.2
		nextGlobalVlanId OBJECT-TYPE
			SYNTAX Integer32 (0..1024)
			MAX-ACCESS read-only
			STATUS current
			DESCRIPTION
				"Leaf node"
			::= { globalVlan 2 }

				-- 1.3.6.1.4.1.5875.800.3.16.3
		globalVlanAttachPortTable OBJECT-TYPE
			SYNTAX SEQUENCE OF GlobalVlanAttachPortEntry
			MAX-ACCESS not-accessible
			STATUS current
			DESCRIPTION
				"Description"
			::= { globalVlan 3 }

				-- 1.3.6.1.4.1.5875.800.3.16.3.1
		globalVlanAttachPortEntry OBJECT-TYPE
			SYNTAX GlobalVlanAttachPortEntry
			MAX-ACCESS not-accessible
			STATUS current
			DESCRIPTION
				"Row Description"
			INDEX { vlanId, upLinkPortNo }
			::= { globalVlanAttachPortTable 1 }

		
		GlobalVlanAttachPortEntry ::=
			SEQUENCE { 
				vlanId
					Integer32,
				upLinkPortNo
					Integer32,
				vlanType
					Integer32,
				vlanTag
					Integer32,
				globalVlanAttachAction
					INTEGER
			 }
		-- 1.3.6.1.4.1.5875.800.3.16.3.1.1
		vlanId OBJECT-TYPE
			SYNTAX Integer32 (1..10000)
			MAX-ACCESS read-only
			STATUS current
			DESCRIPTION
				"vlan ID
				1-4085"
			::= { globalVlanAttachPortEntry 1 }

				-- 1.3.6.1.4.1.5875.800.3.16.3.1.2
		upLinkPortNo OBJECT-TYPE
			SYNTAX Integer32 (0..1000)
			MAX-ACCESS read-only
			STATUS current
			DESCRIPTION
				"Column Description"
			::= { globalVlanAttachPortEntry 2 }

				-- 1.3.6.1.4.1.5875.800.3.16.3.1.3
		vlanType OBJECT-TYPE
			SYNTAX Integer32
			MAX-ACCESS read-only
			STATUS current
			DESCRIPTION
				"Column Description"
			::= { globalVlanAttachPortEntry 3 }

				-- 1.3.6.1.4.1.5875.800.3.16.3.1.4
		vlanTag OBJECT-TYPE
			SYNTAX Integer32
			MAX-ACCESS read-create
			STATUS current
			DESCRIPTION
				"Column Description:
				1:tag(1)
				2:untag(0)"
			::= { globalVlanAttachPortEntry 4 }

				-- 1.3.6.1.4.1.5875.800.3.16.3.1.5
		globalVlanAttachAction OBJECT-TYPE
			SYNTAX INTEGER
				{
				active(1),
				create(4),
				destroy(6),
				modify(7)
				}
			MAX-ACCESS read-create
			STATUS current
			DESCRIPTION
				"Column Description"
			::= { globalVlanAttachPortEntry 5 }

				-- 1.3.6.1.4.1.5875.800.3.16.4
		nextGlobalVlanAttachPortIndex OBJECT-TYPE
			SYNTAX Integer32 (0..1024)
			MAX-ACCESS read-only
			STATUS current
			DESCRIPTION
				"Description"
			::= { globalVlan 4 }

				-- 1.3.6.1.4.1.5875.800.3.17
		onuManageVlan OBJECT IDENTIFIER ::= { oltData 17 }

				-- 1.3.6.1.4.1.5875.800.3.17.1
		onuManageVlanTable OBJECT-TYPE
			SYNTAX SEQUENCE OF OnuManageVlanEntry
			MAX-ACCESS not-accessible
			STATUS current
			DESCRIPTION
				"Description"
			::= { onuManageVlan 1 }

				-- 1.3.6.1.4.1.5875.800.3.17.1.1
		onuManageVlanEntry OBJECT-TYPE
			SYNTAX OnuManageVlanEntry
			MAX-ACCESS not-accessible
			STATUS current
			DESCRIPTION
				"Row Description"
			INDEX { onuIndex, manageVlanIndex }
			::= { onuManageVlanTable 1 }

		
		OnuManageVlanEntry ::=
			SEQUENCE { 
				manageVlanIndex
					Integer32,
				onuMac
					MacAddress,
				manageVlanName
					OCTET STRING,
				portNo
					Integer32,
				tagStatus1
					Integer32,
				manageSvlan
					Integer32,
				manageSvlanCos
					Integer32,
				mamageCvlan
					Integer32,
				mamageCvlanCos
					Integer32,
				onuIp
					IpAddress,
				onuMask
					IpAddress,
				onuGateway
					IpAddress,
				onuManageVlanAction
					INTEGER
			 }
		-- 1.3.6.1.4.1.5875.800.3.17.1.1.1
		manageVlanIndex OBJECT-TYPE
			SYNTAX Integer32 (1..10000)
			MAX-ACCESS not-accessible
			STATUS current
			DESCRIPTION
				"Index"
			::= { onuManageVlanEntry 1 }

				-- 1.3.6.1.4.1.5875.800.3.17.1.1.2
		onuMac OBJECT-TYPE
			SYNTAX MacAddress
			MAX-ACCESS read-create
			STATUS current
			DESCRIPTION
				"Physical Authentication Identifier (MAC) 
				The length of mac address is 12"
			::= { onuManageVlanEntry 2 }

				-- 1.3.6.1.4.1.5875.800.3.17.1.1.4
		manageVlanName OBJECT-TYPE
			SYNTAX OCTET STRING
			MAX-ACCESS read-create
			STATUS current
			DESCRIPTION
				"Management VLAN Name
				The max length of name is 16"
			::= { onuManageVlanEntry 4 }

				-- 1.3.6.1.4.1.5875.800.3.17.1.1.5
		portNo OBJECT-TYPE
			SYNTAX Integer32
			MAX-ACCESS read-create
			STATUS current
			DESCRIPTION
				"Port Number"
			::= { onuManageVlanEntry 5 }

				-- 1.3.6.1.4.1.5875.800.3.17.1.1.6
		tagStatus1 OBJECT-TYPE
			SYNTAX Integer32
			MAX-ACCESS read-create
			STATUS current
			DESCRIPTION
				"Tag
				0??untag??untag??
				1??tag??tag??"
			::= { onuManageVlanEntry 6 }

				-- 1.3.6.1.4.1.5875.800.3.17.1.1.7
		manageSvlan OBJECT-TYPE
			SYNTAX Integer32
			MAX-ACCESS read-create
			STATUS current
			DESCRIPTION
				"Management Svlan
				1??4085"
			::= { onuManageVlanEntry 7 }

				-- 1.3.6.1.4.1.5875.800.3.17.1.1.8
		manageSvlanCos OBJECT-TYPE
			SYNTAX Integer32
			MAX-ACCESS read-create
			STATUS current
			DESCRIPTION
				"Management Svlan Priority
				0-7"
			::= { onuManageVlanEntry 8 }

				-- 1.3.6.1.4.1.5875.800.3.17.1.1.9
		mamageCvlan OBJECT-TYPE
			SYNTAX Integer32
			MAX-ACCESS read-create
			STATUS current
			DESCRIPTION
				"Management Cvlan
				1-4085,0xffff"
			::= { onuManageVlanEntry 9 }

				-- 1.3.6.1.4.1.5875.800.3.17.1.1.10
		mamageCvlanCos OBJECT-TYPE
			SYNTAX Integer32
			MAX-ACCESS read-create
			STATUS current
			DESCRIPTION
				"Management Cvlan Priority
				0-7??0xffff"
			::= { onuManageVlanEntry 10 }

				-- 1.3.6.1.4.1.5875.800.3.17.1.1.11
		onuIp OBJECT-TYPE
			SYNTAX IpAddress
			MAX-ACCESS read-create
			STATUS current
			DESCRIPTION
				"IP Address
				0x0-0xFFFFFFFF"
			::= { onuManageVlanEntry 11 }

				-- 1.3.6.1.4.1.5875.800.3.17.1.1.12
		onuMask OBJECT-TYPE
			SYNTAX IpAddress
			MAX-ACCESS read-create
			STATUS current
			DESCRIPTION
				"Mask
				0x0-0xFFFFFFFF"
			::= { onuManageVlanEntry 12 }

				-- 1.3.6.1.4.1.5875.800.3.17.1.1.13
		onuGateway OBJECT-TYPE
			SYNTAX IpAddress
			MAX-ACCESS read-create
			STATUS current
			DESCRIPTION
				"Gateway
				0x0-0xFFFFFFFF"
			::= { onuManageVlanEntry 13 }

				-- 1.3.6.1.4.1.5875.800.3.17.1.1.14
		onuManageVlanAction OBJECT-TYPE
			SYNTAX INTEGER { modify(7) }
			MAX-ACCESS read-create
			STATUS current
			DESCRIPTION
				"7:modify"
			::= { onuManageVlanEntry 14 }

				-- 1.3.6.1.4.1.5875.800.3.18
		trunkConfig OBJECT IDENTIFIER ::= { oltData 18 }

				-- 1.3.6.1.4.1.5875.800.3.18.1
		trunkConfigTable OBJECT-TYPE
			SYNTAX SEQUENCE OF TrunkConfigEntry
			MAX-ACCESS not-accessible
			STATUS current
			DESCRIPTION
				"Description"
			::= { trunkConfig 1 }

				-- 1.3.6.1.4.1.5875.800.3.18.1.1
		trunkConfigEntry OBJECT-TYPE
			SYNTAX TrunkConfigEntry
			MAX-ACCESS not-accessible
			STATUS current
			DESCRIPTION
				"Row Description"
			INDEX { trunkGroupId }
			::= { trunkConfigTable 1 }

		
		TrunkConfigEntry ::=
			SEQUENCE { 
				trunkGroupId
					Integer32,
				masterPort
					Integer32,
				memberPort
					Integer32,
				trunkConfigAction
					INTEGER
			 }
		-- 1.3.6.1.4.1.5875.800.3.18.1.1.1
		trunkGroupId OBJECT-TYPE
			SYNTAX Integer32 (1..10000)
			MAX-ACCESS read-only
			STATUS current
			DESCRIPTION
				"TRUNK port 
				link aggregation
				1-6"
			::= { trunkConfigEntry 1 }

				-- 1.3.6.1.4.1.5875.800.3.18.1.1.2
		masterPort OBJECT-TYPE
			SYNTAX Integer32
			MAX-ACCESS read-create
			STATUS current
			DESCRIPTION
				"The 5116:
				Direct port number
				5516:
				Logical port number, composed of the SLOT number and PON number.
				"
			::= { trunkConfigEntry 2 }

				-- 1.3.6.1.4.1.5875.800.3.18.1.1.3
		memberPort OBJECT-TYPE
			SYNTAX Integer32
			MAX-ACCESS read-create
			STATUS current
			DESCRIPTION
				"The 5116:
				The bit of a byte indicates whether the port is the TRUNK group member. For example: if bit0 is 1, the port 1 is the TRUNK group member; if bit1 is 0, the port 2 is not the TRUNK group member. There are totally 7 ports, indicated by bit0 to bit6.
				The 5516:
				32 bit integer: 0 to 31bit from right to left. Among which, 0 to 5 bits indicate the first group ports (1 to 6) and 16 to 21 bits indicate the second group ports (1 to 6).
				"
			::= { trunkConfigEntry 3 }

				-- 1.3.6.1.4.1.5875.800.3.18.1.1.4
		trunkConfigAction OBJECT-TYPE
			SYNTAX INTEGER
				{
				active(1),
				create(4),
				destroy(6),
				modify(7)
				}
			MAX-ACCESS read-create
			STATUS current
			DESCRIPTION
				"4:create
				6:delete
				7:modify
				"
			::= { trunkConfigEntry 4 }

				-- 1.3.6.1.4.1.5875.800.3.18.2
		nextTrunkConfigId OBJECT-TYPE
			SYNTAX Integer32 (0..1024)
			MAX-ACCESS read-only
			STATUS current
			DESCRIPTION
				"Leaf node"
			::= { trunkConfig 2 }

				-- 1.3.6.1.4.1.5875.800.3.19
		onuPonConfig OBJECT IDENTIFIER ::= { oltData 19 }

				-- 1.3.6.1.4.1.5875.800.3.19.1
		onuPonCfgTable OBJECT-TYPE
			SYNTAX SEQUENCE OF OnuPonCfgEntry
			MAX-ACCESS not-accessible
			STATUS current
			DESCRIPTION
				"Description"
			::= { onuPonConfig 1 }

				-- 1.3.6.1.4.1.5875.800.3.19.1.1
		onuPonCfgEntry OBJECT-TYPE
			SYNTAX OnuPonCfgEntry
			MAX-ACCESS not-accessible
			STATUS current
			DESCRIPTION
				"Row Description"
			INDEX { onuIndex }
			::= { onuPonCfgTable 1 }

		
		OnuPonCfgEntry ::=
			SEQUENCE { 
				upBandwidth
					Integer32,
				dnBandwidth
					Integer32,
				upAssureBandwidth
					Integer32,
				upFixedBandwidth
					Integer32,
				onuPonCfgActon
					Integer32
			 }
		-- 1.3.6.1.4.1.5875.800.3.19.1.1.1
		upBandwidth OBJECT-TYPE
			SYNTAX Integer32
			MAX-ACCESS read-create
			STATUS current
			DESCRIPTION
				"Uplink Bandwidth
				Unit: kps"
			::= { onuPonCfgEntry 1 }

				-- 1.3.6.1.4.1.5875.800.3.19.1.1.2
		dnBandwidth OBJECT-TYPE
			SYNTAX Integer32
			MAX-ACCESS read-create
			STATUS current
			DESCRIPTION
				"Downlink Bandwidth
				Unit: kps"
			::= { onuPonCfgEntry 2 }

				-- 1.3.6.1.4.1.5875.800.3.19.1.1.3
		upAssureBandwidth OBJECT-TYPE
			SYNTAX Integer32
			MAX-ACCESS read-create
			STATUS current
			DESCRIPTION
				"The fixed value is 0 for the 5516"
			::= { onuPonCfgEntry 3 }

				-- 1.3.6.1.4.1.5875.800.3.19.1.1.4
		upFixedBandwidth OBJECT-TYPE
			SYNTAX Integer32
			MAX-ACCESS read-create
			STATUS current
			DESCRIPTION
				"The fixed value is 0 for the 5516"
			::= { onuPonCfgEntry 4 }

				-- 1.3.6.1.4.1.5875.800.3.19.1.1.5
		onuPonCfgActon OBJECT-TYPE
			SYNTAX Integer32
			MAX-ACCESS read-create
			STATUS current
			DESCRIPTION
				"7:modify"
			::= { onuPonCfgEntry 5 }

				-- 1.3.6.1.4.1.5875.800.3.20
		saveCfg2Flash OBJECT IDENTIFIER ::= { oltData 20 }

				-- 1.3.6.1.4.1.5875.800.3.20.1
		save2Flash OBJECT-TYPE
			SYNTAX Integer32
			MAX-ACCESS read-write
			STATUS current
			DESCRIPTION
				"1: Write the configuration into the FLASH"
			::= { saveCfg2Flash 1 }

				-- 1.3.6.1.4.1.5875.800.3.21
		mac2OnuInfo OBJECT IDENTIFIER ::= { oltData 21 }

				-- 1.3.6.1.4.1.5875.800.3.21.1
		mac2OnuInfoTable OBJECT-TYPE
			SYNTAX SEQUENCE OF Mac2OnuInfoEntry
			MAX-ACCESS not-accessible
			STATUS current
			DESCRIPTION
				"Description"
			::= { mac2OnuInfo 1 }

				-- 1.3.6.1.4.1.5875.800.3.21.1.1
		mac2OnuInfoEntry OBJECT-TYPE
			SYNTAX Mac2OnuInfoEntry
			MAX-ACCESS not-accessible
			STATUS current
			DESCRIPTION
				"Row Description"
			INDEX { onuMacString }
			::= { mac2OnuInfoTable 1 }

		
		Mac2OnuInfoEntry ::=
			SEQUENCE { 
				onuMacString
					OCTET STRING,
				onuAuthID
					Integer32,
				onuWhileListID
					Integer32,
				onuMacSlot
					Integer32,
				onuMacPon
					Integer32
			 }
		-- 1.3.6.1.4.1.5875.800.3.21.1.1.1
		onuMacString OBJECT-TYPE
			SYNTAX OCTET STRING (SIZE (12))
			MAX-ACCESS not-accessible
			STATUS current
			DESCRIPTION
				"MAC Address (Index)"
			::= { mac2OnuInfoEntry 1 }

				-- 1.3.6.1.4.1.5875.800.3.21.1.1.2
		onuAuthID OBJECT-TYPE
			SYNTAX Integer32
			MAX-ACCESS read-only
			STATUS current
			DESCRIPTION
				"ONU Number"
			::= { mac2OnuInfoEntry 2 }

				-- 1.3.6.1.4.1.5875.800.3.21.1.1.3
		onuWhileListID OBJECT-TYPE
			SYNTAX Integer32
			MAX-ACCESS read-only
			STATUS current
			DESCRIPTION
				"Physical Whitelist ID"
			::= { mac2OnuInfoEntry 3 }

				-- 1.3.6.1.4.1.5875.800.3.21.1.1.4
		onuMacSlot OBJECT-TYPE
			SYNTAX Integer32
			MAX-ACCESS read-only
			STATUS current
			DESCRIPTION
				"Description"
			::= { mac2OnuInfoEntry 4 }

				-- 1.3.6.1.4.1.5875.800.3.21.1.1.5
		onuMacPon OBJECT-TYPE
			SYNTAX Integer32
			MAX-ACCESS read-only
			STATUS current
			DESCRIPTION
				"Description"
			::= { mac2OnuInfoEntry 5 }

				-- 1.3.6.1.4.1.5875.800.3.22
		sn2OnuInfo OBJECT IDENTIFIER ::= { oltData 22 }

				-- 1.3.6.1.4.1.5875.800.3.22.1
		sn2OnuInfoTable OBJECT-TYPE
			SYNTAX SEQUENCE OF Sn2OnuInfoEntry
			MAX-ACCESS not-accessible
			STATUS current
			DESCRIPTION
				"Description"
			::= { sn2OnuInfo 1 }

				-- 1.3.6.1.4.1.5875.800.3.22.1.1
		sn2OnuInfoEntry OBJECT-TYPE
			SYNTAX Sn2OnuInfoEntry
			MAX-ACCESS not-accessible
			STATUS current
			DESCRIPTION
				"Row Description"
			INDEX { onuSNString }
			::= { sn2OnuInfoTable 1 }

		
		Sn2OnuInfoEntry ::=
			SEQUENCE { 
				onuSNString
					OCTET STRING,
				onuSNAuthID
					Integer32,
				onuSNWhilteListID
					Integer32
			 }
		-- 1.3.6.1.4.1.5875.800.3.22.1.1.1
		onuSNString OBJECT-TYPE
			SYNTAX OCTET STRING (SIZE (1..24))
			MAX-ACCESS not-accessible
			STATUS current
			DESCRIPTION
				"Column Description"
			::= { sn2OnuInfoEntry 1 }

		
--                   SN (Index)
		-- 1.3.6.1.4.1.5875.800.3.22.1.1.2
		onuSNAuthID OBJECT-TYPE
			SYNTAX Integer32
			MAX-ACCESS read-only
			STATUS current
			DESCRIPTION
				"Column Description"
			::= { sn2OnuInfoEntry 2 }

		
--                   ONU Number
		-- 1.3.6.1.4.1.5875.800.3.22.1.1.3
		onuSNWhilteListID OBJECT-TYPE
			SYNTAX Integer32
			MAX-ACCESS read-only
			STATUS current
			DESCRIPTION
				"Column Description"
			::= { sn2OnuInfoEntry 3 }

		
--                   Logical Whitelist ID
		-- 1.3.6.1.4.1.5875.800.3.23
		snmpConfig OBJECT IDENTIFIER ::= { oltData 23 }

				-- 1.3.6.1.4.1.5875.800.3.23.1
		trapReceiveIp OBJECT-TYPE
			SYNTAX IpAddress
			MAX-ACCESS read-write
			STATUS current
			DESCRIPTION
				"Description"
			::= { snmpConfig 1 }

		-- 1.3.6.1.4.1.5875.800.3.23.2
		community OBJECT-TYPE
			SYNTAX OCTET STRING
			MAX-ACCESS read-write
			STATUS current
			DESCRIPTION
				"Description"
			::= { snmpConfig 2 }

		-- 1.3.6.1.4.1.5875.800.3.23.3
		snmpTrapTable OBJECT-TYPE
			SYNTAX SEQUENCE OF SnmpTrapEntry
			MAX-ACCESS not-accessible
			STATUS current
			DESCRIPTION
				"Description"
			::= { snmpConfig 3 }

		-- 1.3.6.1.4.1.5875.800.3.23.3.1
		snmpTrapEntry OBJECT-TYPE
			SYNTAX SnmpTrapEntry
			MAX-ACCESS not-accessible
			STATUS current
			DESCRIPTION
				"Row Description"
			INDEX { snmpTrapv4Index }
			::= { snmpTrapTable 1 }

		
		SnmpTrapEntry ::=
			SEQUENCE { 
				snmpTrapv4Index
					Integer32,
				snmpTrapIpv4
					IpAddress,
				snmpTrapPort
					Integer32,
				snmpTrapVersion
					INTEGER,
				snmpTrapReportVersion
					INTEGER,
				snmpTrapCommunity
					OCTET STRING,
				snmpTrapAction
					INTEGER
			 }
		-- 1.3.6.1.4.1.5875.800.3.23.3.1.1
		snmpTrapv4Index OBJECT-TYPE
			SYNTAX Integer32 (1..65535)
			MAX-ACCESS not-accessible
			STATUS current
			DESCRIPTION
				"Trap Index
				0-10"
			::= { snmpTrapEntry 1 }

				-- 1.3.6.1.4.1.5875.800.3.23.3.1.2
		snmpTrapIpv4 OBJECT-TYPE
			SYNTAX IpAddress
			MAX-ACCESS read-create
			STATUS current
			DESCRIPTION
				"Trap IP Address
				IP address cannot be repeated"
			::= { snmpTrapEntry 2 }

				-- 1.3.6.1.4.1.5875.800.3.23.3.1.3
		snmpTrapPort OBJECT-TYPE
			SYNTAX Integer32
			MAX-ACCESS read-create
			STATUS current
			DESCRIPTION
				"Trap IP Port
				0-65535"
			::= { snmpTrapEntry 3 }

				-- 1.3.6.1.4.1.5875.800.3.23.3.1.4
		snmpTrapVersion OBJECT-TYPE
			SYNTAX INTEGER
				{
				v1(1),
				v2c(2)
				}
			MAX-ACCESS read-create
			STATUS current
			DESCRIPTION
				"Trap IP Version
				1: v1
				2: v2c
				"
			::= { snmpTrapEntry 4 }

				-- 1.3.6.1.4.1.5875.800.3.23.3.1.5
		snmpTrapReportVersion OBJECT-TYPE
			SYNTAX INTEGER
				{
				privFormat(0),
				stdFormat(1)
				}
			MAX-ACCESS read-create
			STATUS current
			DESCRIPTION
				"0:privFormat
				1:stdFormat
				"
			::= { snmpTrapEntry 5 }

				-- 1.3.6.1.4.1.5875.800.3.23.3.1.6
		snmpTrapCommunity OBJECT-TYPE
			SYNTAX OCTET STRING
			MAX-ACCESS read-create
			STATUS current
			DESCRIPTION
				"Trap Community
				The max length of name is 32"
			::= { snmpTrapEntry 6 }

				-- 1.3.6.1.4.1.5875.800.3.23.3.1.20
		snmpTrapAction OBJECT-TYPE
			SYNTAX INTEGER
				{
				create(4),
				destroy(6),
				modify(7),
				active(1)
				}
			MAX-ACCESS read-create
			STATUS current
			DESCRIPTION
				"4:create
				6:delete
				7:modify
				"
			::= { snmpTrapEntry 20 }

				-- 1.3.6.1.4.1.5875.800.3.23.4
		snmpCommunityTable OBJECT-TYPE
			SYNTAX SEQUENCE OF SnmpCommunityEntry
			MAX-ACCESS not-accessible
			STATUS current
			DESCRIPTION
				"Description"
			::= { snmpConfig 4 }

				-- 1.3.6.1.4.1.5875.800.3.23.4.1
		snmpCommunityEntry OBJECT-TYPE
			SYNTAX SnmpCommunityEntry
			MAX-ACCESS not-accessible
			STATUS current
			DESCRIPTION
				"Row Description"
			INDEX { snmpCommunityIndex }
			::= { snmpCommunityTable 1 }

		
		SnmpCommunityEntry ::=
			SEQUENCE { 
				snmpCommunityIndex
					Integer32,
				snmpCommunity
					OCTET STRING,
				snmpCommunityPermission
					INTEGER
			 }
		-- 1.3.6.1.4.1.5875.800.3.23.4.1.1
		snmpCommunityIndex OBJECT-TYPE
			SYNTAX Integer32 (1..1024)
			MAX-ACCESS not-accessible
			STATUS current
			DESCRIPTION
				"Community Index
				Fixed to two"
			::= { snmpCommunityEntry 1 }

				-- 1.3.6.1.4.1.5875.800.3.23.4.1.2
		snmpCommunity OBJECT-TYPE
			SYNTAX OCTET STRING
			MAX-ACCESS read-create
			STATUS current
			DESCRIPTION
				"SNMP Community
				The max length of name is 255"
			::= { snmpCommunityEntry 2 }

				-- 1.3.6.1.4.1.5875.800.3.23.4.1.3
		snmpCommunityPermission OBJECT-TYPE
			SYNTAX INTEGER
				{
				ro(1),
				rw(2)
				}
			MAX-ACCESS read-create
			STATUS current
			DESCRIPTION
				"1: ro (1)
				2: rw (2)
				"
			::= { snmpCommunityEntry 3 }

				-- 1.3.6.1.4.1.5875.800.3.23.5
		snmpTrapv6Table OBJECT-TYPE
			SYNTAX SEQUENCE OF SnmpTrapv6Entry
			MAX-ACCESS not-accessible
			STATUS current
			DESCRIPTION
				"Description"
			::= { snmpConfig 5 }

				-- 1.3.6.1.4.1.5875.800.3.23.5.1
		snmpTrapv6Entry OBJECT-TYPE
			SYNTAX SnmpTrapv6Entry
			MAX-ACCESS not-accessible
			STATUS current
			DESCRIPTION
				"Row Description"
			INDEX { snmpTrapv6Index }
			::= { snmpTrapv6Table 1 }

		
		SnmpTrapv6Entry ::=
			SEQUENCE { 
				snmpTrapv6Index
					Integer32,
				snmpTrapIpv6
					OCTET STRING,
				snmpTrapv6Port
					Integer32,
				snmpTrapv6Version
					INTEGER,
				snmpTrapReportv6Version
					INTEGER,
				snmpTrapv6Community
					OCTET STRING,
				snmpTrapv6Action
					INTEGER
			 }
		-- 1.3.6.1.4.1.5875.800.3.23.5.1.1
		snmpTrapv6Index OBJECT-TYPE
			SYNTAX Integer32 (1..65535)
			MAX-ACCESS not-accessible
			STATUS current
			DESCRIPTION
				"Column Description"
			::= { snmpTrapv6Entry 1 }

				-- 1.3.6.1.4.1.5875.800.3.23.5.1.2
		snmpTrapIpv6 OBJECT-TYPE
			SYNTAX OCTET STRING (SIZE (16))
			MAX-ACCESS read-create
			STATUS current
			DESCRIPTION
				"This data type is used to model IPv6 addresses.
				This is a binary string of 16 octets in network byte-order."
			::= { snmpTrapv6Entry 2 }

				-- 1.3.6.1.4.1.5875.800.3.23.5.1.3
		snmpTrapv6Port OBJECT-TYPE
			SYNTAX Integer32
			MAX-ACCESS read-create
			STATUS current
			DESCRIPTION
				"Column Description"
			::= { snmpTrapv6Entry 3 }

				-- 1.3.6.1.4.1.5875.800.3.23.5.1.4
		snmpTrapv6Version OBJECT-TYPE
			SYNTAX INTEGER
				{
				v1(1),
				v2c(2)
				}
			MAX-ACCESS read-create
			STATUS current
			DESCRIPTION
				"Column Description"
			::= { snmpTrapv6Entry 4 }

				-- 1.3.6.1.4.1.5875.800.3.23.5.1.5
		snmpTrapReportv6Version OBJECT-TYPE
			SYNTAX INTEGER
				{
				privFormat(0),
				stdFormat(1)
				}
			MAX-ACCESS read-create
			STATUS current
			DESCRIPTION
				"Column Description"
			::= { snmpTrapv6Entry 5 }

				-- 1.3.6.1.4.1.5875.800.3.23.5.1.6
		snmpTrapv6Community OBJECT-TYPE
			SYNTAX OCTET STRING
			MAX-ACCESS read-create
			STATUS current
			DESCRIPTION
				"Column Description"
			::= { snmpTrapv6Entry 6 }

				-- 1.3.6.1.4.1.5875.800.3.23.5.1.20
		snmpTrapv6Action OBJECT-TYPE
			SYNTAX INTEGER
				{
				create(4),
				destroy(6),
				modify(7),
				active(1)
				}
			MAX-ACCESS read-create
			STATUS current
			DESCRIPTION
				"Column Description"
			::= { snmpTrapv6Entry 20 }

				-- 1.3.6.1.4.1.5875.800.3.23.6
		snmpExCommunityTable OBJECT-TYPE
			SYNTAX SEQUENCE OF SnmpExCommunityEntry
			MAX-ACCESS not-accessible
			STATUS current
			DESCRIPTION
				"Description."
			::= { snmpConfig 6 }

				-- 1.3.6.1.4.1.5875.800.3.23.6.1
		snmpExCommunityEntry OBJECT-TYPE
			SYNTAX SnmpExCommunityEntry
			MAX-ACCESS not-accessible
			STATUS current
			DESCRIPTION
				"Description."
			INDEX { snmpExCommunityIndex }
			::= { snmpExCommunityTable 1 }

		
		SnmpExCommunityEntry ::=
			SEQUENCE { 
				snmpExCommunityIndex
					Integer32,
				snmpExCommunity
					OCTET STRING,
				snmpExCommunityPermission
					INTEGER
			 }
		-- 1.3.6.1.4.1.5875.800.3.23.6.1.1
		snmpExCommunityIndex OBJECT-TYPE
			SYNTAX Integer32 (1..1024)
			MAX-ACCESS not-accessible
			STATUS current
			DESCRIPTION
				"Community Index
				value:1-10"
			::= { snmpExCommunityEntry 1 }

				-- 1.3.6.1.4.1.5875.800.3.23.6.1.2
		snmpExCommunity OBJECT-TYPE
			SYNTAX OCTET STRING
			MAX-ACCESS read-create
			STATUS current
			DESCRIPTION
				"SNMP Community"
			::= { snmpExCommunityEntry 2 }

				-- 1.3.6.1.4.1.5875.800.3.23.6.1.3
		snmpExCommunityPermission OBJECT-TYPE
			SYNTAX INTEGER
				{
				ro(1),
				rw(2)
				}
			MAX-ACCESS read-create
			STATUS current
			DESCRIPTION
				"1: ro (1)
				2: rw (2)
				"
			::= { snmpExCommunityEntry 3 }

				-- 1.3.6.1.4.1.5875.800.3.23.7
		manageIpTable OBJECT-TYPE
			SYNTAX SEQUENCE OF ManageIpEntry
			MAX-ACCESS not-accessible
			STATUS current
			DESCRIPTION
				"Description"
			::= { snmpConfig 7 }

				-- 1.3.6.1.4.1.5875.800.3.23.7.1
		manageIpEntry OBJECT-TYPE
			SYNTAX ManageIpEntry
			MAX-ACCESS not-accessible
			STATUS current
			DESCRIPTION
				"Row Description"
			INDEX { manageIpv4Index }
			::= { manageIpTable 1 }

		
		ManageIpEntry ::=
			SEQUENCE { 
				manageIpv4Index
					Integer32,
				manageIpVlanName
					OCTET STRING,
				manageIpvlanID
					INTEGER,
				manageIpv4
					IpAddress,
				manageIpv4Mask
					INTEGER,
				manageIpv4GateWay
					IpAddress,
				manageMacAddr
					OCTET STRING,
				manageVlanType
					INTEGER,
				iNnerVlanID
					INTEGER
			 }
		-- 1.3.6.1.4.1.5875.800.3.23.7.1.1
		manageIpv4Index OBJECT-TYPE
			SYNTAX Integer32 (1..1024)
			MAX-ACCESS not-accessible
			STATUS current
			DESCRIPTION
				"Column Description"
			::= { manageIpEntry 1 }

				-- 1.3.6.1.4.1.5875.800.3.23.7.1.2
		manageIpVlanName OBJECT-TYPE
			SYNTAX OCTET STRING
			MAX-ACCESS read-create
			STATUS current
			DESCRIPTION
				"Column Description"
			::= { manageIpEntry 2 }

				-- 1.3.6.1.4.1.5875.800.3.23.7.1.3
		manageIpvlanID OBJECT-TYPE
			SYNTAX INTEGER
			MAX-ACCESS read-create
			STATUS current
			DESCRIPTION
				"Column Description"
			::= { manageIpEntry 3 }

				-- 1.3.6.1.4.1.5875.800.3.23.7.1.4
		manageIpv4 OBJECT-TYPE
			SYNTAX IpAddress
			MAX-ACCESS read-create
			STATUS current
			DESCRIPTION
				"Column Description"
			::= { manageIpEntry 4 }

				-- 1.3.6.1.4.1.5875.800.3.23.7.1.5
		manageIpv4Mask OBJECT-TYPE
			SYNTAX INTEGER
			MAX-ACCESS read-create
			STATUS current
			DESCRIPTION
				"Column Description"
			::= { manageIpEntry 5 }

				-- 1.3.6.1.4.1.5875.800.3.23.7.1.6
		manageIpv4GateWay OBJECT-TYPE
			SYNTAX IpAddress
			MAX-ACCESS read-create
			STATUS current
			DESCRIPTION
				"Column Description"
			::= { manageIpEntry 6 }

				-- 1.3.6.1.4.1.5875.800.3.23.7.1.8
		manageMacAddr OBJECT-TYPE
			SYNTAX OCTET STRING
			MAX-ACCESS read-create
			STATUS current
			DESCRIPTION
				"Column Description"
			::= { manageIpEntry 8 }

				-- 1.3.6.1.4.1.5875.800.3.23.7.1.9
		manageVlanType OBJECT-TYPE
			SYNTAX INTEGER
			MAX-ACCESS read-create
			STATUS current
			DESCRIPTION
				"Column Description"
			::= { manageIpEntry 9 }

				-- 1.3.6.1.4.1.5875.800.3.23.7.1.10
		iNnerVlanID OBJECT-TYPE
			SYNTAX INTEGER
			MAX-ACCESS read-create
			STATUS current
			DESCRIPTION
				"Column Description"
			::= { manageIpEntry 10 }

				-- 1.3.6.1.4.1.5875.800.3.24
		igmpConfig OBJECT IDENTIFIER ::= { oltData 24 }

				-- 1.3.6.1.4.1.5875.800.3.24.1
		igmpBaseCfg OBJECT IDENTIFIER ::= { igmpConfig 1 }

				-- 1.3.6.1.4.1.5875.800.3.24.1.1
		igmpMode OBJECT-TYPE
			SYNTAX INTEGER
				{
				controlled(1),
				proxy-proxy(2),
				snooping(3),
				proxy-snooping(4),
				disable(5),
				active(6)
				}
			MAX-ACCESS read-only
			STATUS current
			DESCRIPTION
				"1.	Controllable
				2.	Proxy
				3.	Snooping
				4.	Proxy-Snooping
				5.	Disable
				6.	Active snooping
				"
			::= { igmpBaseCfg 1 }

				-- 1.3.6.1.4.1.5875.800.3.24.1.2
		igmpVlan OBJECT-TYPE
			SYNTAX Integer32
			MAX-ACCESS read-write
			STATUS current
			DESCRIPTION
				"Multicast vlan"
			::= { igmpBaseCfg 2 }

				-- 1.3.6.1.4.1.5875.800.3.24.1.3
		igmpProxyIp OBJECT-TYPE
			SYNTAX IpAddress
			MAX-ACCESS read-write
			STATUS current
			DESCRIPTION
				"Multicast Proxy IP"
			::= { igmpBaseCfg 3 }

				-- 1.3.6.1.4.1.5875.800.3.24.1.4
		igmpProtocolVersion OBJECT-TYPE
			SYNTAX INTEGER
				{
				igmpv1v2(1),
				igmpv3(2)
				}
			MAX-ACCESS read-only
			STATUS current
			DESCRIPTION
				"1: igmp version 1/2
				2: igmp version 3
				"
			::= { igmpBaseCfg 4 }

				-- 1.3.6.1.4.1.5875.800.3.24.2
		igmpProtocolPara OBJECT IDENTIFIER ::= { igmpConfig 2 }

				-- 1.3.6.1.4.1.5875.800.3.24.2.1
		robustnessVariable OBJECT-TYPE
			SYNTAX Integer32
			MAX-ACCESS read-write
			STATUS current
			DESCRIPTION
				"Robustness Index
				2-16"
			::= { igmpProtocolPara 1 }

				-- 1.3.6.1.4.1.5875.800.3.24.2.2
		queryRespInterval OBJECT-TYPE
			SYNTAX Integer32
			MAX-ACCESS read-write
			STATUS current
			DESCRIPTION
				"General Query Response Interval
				1-255 sencond"
			::= { igmpProtocolPara 2 }

				-- 1.3.6.1.4.1.5875.800.3.24.2.3
		lastQueryInterval OBJECT-TYPE
			SYNTAX Integer32
			MAX-ACCESS read-write
			STATUS current
			DESCRIPTION
				"Last Group Member Query Interval
				1-255 sencond"
			::= { igmpProtocolPara 3 }

				-- 1.3.6.1.4.1.5875.800.3.24.2.4
		lastQueryCount OBJECT-TYPE
			SYNTAX Integer32
			MAX-ACCESS read-write
			STATUS current
			DESCRIPTION
				"Last Group Member Query frequency
				1-16 "
			::= { igmpProtocolPara 4 }

				-- 1.3.6.1.4.1.5875.800.3.24.2.5
		queryInterval OBJECT-TYPE
			SYNTAX Integer32
			MAX-ACCESS read-write
			STATUS current
			DESCRIPTION
				"General Query Time Interval
				11-255 sencond"
			::= { igmpProtocolPara 5 }

				-- 1.3.6.1.4.1.5875.800.3.24.2.6
		groupMembInterval OBJECT-TYPE
			SYNTAX Integer32 (0..1024)
			MAX-ACCESS read-write
			STATUS current
			DESCRIPTION
				"Group Member Aging Time
				23-765 sencond"
			::= { igmpProtocolPara 6 }

				-- 1.3.6.1.4.1.5875.800.3.24.4
		igmpProfileTable OBJECT-TYPE
			SYNTAX SEQUENCE OF IgmpProfileEntry
			MAX-ACCESS not-accessible
			STATUS current
			DESCRIPTION
				"Description"
			::= { igmpConfig 4 }

				-- 1.3.6.1.4.1.5875.800.3.24.4.1
		igmpProfileEntry OBJECT-TYPE
			SYNTAX IgmpProfileEntry
			MAX-ACCESS not-accessible
			STATUS current
			DESCRIPTION
				"Row Description"
			INDEX { igmpProfileIndex }
			::= { igmpProfileTable 1 }

		
		IgmpProfileEntry ::=
			SEQUENCE { 
				igmpProfileIndex
					Integer32,
				igmpProfileName
					OCTET STRING,
				igmpProfileAction
					INTEGER
			 }
		-- 1.3.6.1.4.1.5875.800.3.24.4.1.1
		igmpProfileIndex OBJECT-TYPE
			SYNTAX Integer32 (0..65535)
			MAX-ACCESS not-accessible
			STATUS current
			DESCRIPTION
				"Index"
			::= { igmpProfileEntry 1 }

				-- 1.3.6.1.4.1.5875.800.3.24.4.1.2
		igmpProfileName OBJECT-TYPE
			SYNTAX OCTET STRING
			MAX-ACCESS read-create
			STATUS current
			DESCRIPTION
				"profile Name
				Length 1-20"
			::= { igmpProfileEntry 2 }

				-- 1.3.6.1.4.1.5875.800.3.24.4.1.20
		igmpProfileAction OBJECT-TYPE
			SYNTAX INTEGER
				{
				active(1),
				create(4),
				destroy(6),
				modify(7)
				}
			MAX-ACCESS read-create
			STATUS current
			DESCRIPTION
				"4:create
				6:delete
				7:modify
				"
			::= { igmpProfileEntry 20 }

				-- 1.3.6.1.4.1.5875.800.3.24.5
		igmpProfileGroupTable OBJECT-TYPE
			SYNTAX SEQUENCE OF IgmpProfileGroupEntry
			MAX-ACCESS not-accessible
			STATUS current
			DESCRIPTION
				"Description"
			::= { igmpConfig 5 }

				-- 1.3.6.1.4.1.5875.800.3.24.5.1
		igmpProfileGroupEntry OBJECT-TYPE
			SYNTAX IgmpProfileGroupEntry
			MAX-ACCESS not-accessible
			STATUS current
			DESCRIPTION
				"Row Description"
			INDEX { igmpProfileIndex, igmpProfileGroupIndex }
			::= { igmpProfileGroupTable 1 }

		
		IgmpProfileGroupEntry ::=
			SEQUENCE { 
				igmpProfileGroupIndex
					Integer32,
				groupAddressBegin
					IpAddress,
				groupAddressEnd
					IpAddress,
				igmpProfileGroupAuthority
					INTEGER,
				igmpProfileGroupAction
					INTEGER
			 }
		-- 1.3.6.1.4.1.5875.800.3.24.5.1.1
		igmpProfileGroupIndex OBJECT-TYPE
			SYNTAX Integer32 (1..65535)
			MAX-ACCESS not-accessible
			STATUS current
			DESCRIPTION
				"Index"
			::= { igmpProfileGroupEntry 1 }

				-- 1.3.6.1.4.1.5875.800.3.24.5.1.2
		groupAddressBegin OBJECT-TYPE
			SYNTAX IpAddress
			MAX-ACCESS read-create
			STATUS current
			DESCRIPTION
				"Start IP
				ipv4??
				0xe0000100-0xefffffff
				ipv6??
				ff00????0001-
				ff1f:ffff:ffff:ffff:ffff:ffff:ffff:ffff"
			::= { igmpProfileGroupEntry 2 }

				-- 1.3.6.1.4.1.5875.800.3.24.5.1.3
		groupAddressEnd OBJECT-TYPE
			SYNTAX IpAddress
			MAX-ACCESS read-create
			STATUS current
			DESCRIPTION
				"End IP
				ipv4??
				0xe0000100-0xefffffff
				ipv6??
				ff00????0001-
				ff1f:ffff:ffff:ffff:ffff:ffff:ffff:ffff"
			::= { igmpProfileGroupEntry 3 }

				-- 1.3.6.1.4.1.5875.800.3.24.5.1.4
		igmpProfileGroupAuthority OBJECT-TYPE
			SYNTAX INTEGER
				{
				normal(1),
				preview(2),
				forbid(3)
				}
			MAX-ACCESS read-create
			STATUS current
			DESCRIPTION
				"1: normal
				2: preview
				3. forbid
				"
			::= { igmpProfileGroupEntry 4 }

				-- 1.3.6.1.4.1.5875.800.3.24.5.1.20
		igmpProfileGroupAction OBJECT-TYPE
			SYNTAX INTEGER
				{
				active(1),
				create(4),
				destroy(6),
				modify(7)
				}
			MAX-ACCESS read-create
			STATUS current
			DESCRIPTION
				"4:create
				6:delete
				7:modify
				"
			::= { igmpProfileGroupEntry 20 }

				-- 1.3.6.1.4.1.5875.800.3.24.6
		igmpActiveMultiGroupNumberTable OBJECT-TYPE
			SYNTAX SEQUENCE OF IgmpActiveMultiGroupNumberEntry
			MAX-ACCESS not-accessible
			STATUS current
			DESCRIPTION
				"Description"
			::= { igmpConfig 6 }

				-- 1.3.6.1.4.1.5875.800.3.24.6.1
		igmpActiveMultiGroupNumberEntry OBJECT-TYPE
			SYNTAX IgmpActiveMultiGroupNumberEntry
			MAX-ACCESS not-accessible
			STATUS current
			DESCRIPTION
				"Row Description"
			INDEX { portIndex, igmpvlan }
			::= { igmpActiveMultiGroupNumberTable 1 }

		
		IgmpActiveMultiGroupNumberEntry ::=
			SEQUENCE { 
				igmpvlan
					Integer32,
				igmpActiveMultiGroup
					Integer32
			 }
		-- 1.3.6.1.4.1.5875.800.3.24.6.1.1
		igmpvlan OBJECT-TYPE
			SYNTAX Integer32 (0..65535)
			MAX-ACCESS not-accessible
			STATUS current
			DESCRIPTION
				"Index"
			::= { igmpActiveMultiGroupNumberEntry 1 }

				-- 1.3.6.1.4.1.5875.800.3.24.6.1.2
		igmpActiveMultiGroup OBJECT-TYPE
			SYNTAX Integer32 (0..65535)
			MAX-ACCESS read-only
			STATUS current
			DESCRIPTION
				"Multicast Group Number
				0-1024"
			::= { igmpActiveMultiGroupNumberEntry 2 }

				-- 1.3.6.1.4.1.5875.800.3.24.7
		igmpactiveJoinPortsNumberTable OBJECT-TYPE
			SYNTAX SEQUENCE OF IgmpactiveJoinPortsNumberEntry
			MAX-ACCESS not-accessible
			STATUS current
			DESCRIPTION
				"Description"
			::= { igmpConfig 7 }

				-- 1.3.6.1.4.1.5875.800.3.24.7.1
		igmpactiveJoinPortsNumberEntry OBJECT-TYPE
			SYNTAX IgmpactiveJoinPortsNumberEntry
			MAX-ACCESS not-accessible
			STATUS current
			DESCRIPTION
				"Row Description"
			INDEX { fttbIfIndex, igmpMultiGroupAddress }
			::= { igmpactiveJoinPortsNumberTable 1 }

		
		IgmpactiveJoinPortsNumberEntry ::=
			SEQUENCE { 
				igmpMultiGroupAddress
					IpAddress,
				activeJoinPorts
					Integer32
			 }
		-- 1.3.6.1.4.1.5875.800.3.24.7.1.1
		igmpMultiGroupAddress OBJECT-TYPE
			SYNTAX IpAddress
			MAX-ACCESS not-accessible
			STATUS current
			DESCRIPTION
				"Index"
			::= { igmpactiveJoinPortsNumberEntry 1 }

				-- 1.3.6.1.4.1.5875.800.3.24.7.1.2
		activeJoinPorts OBJECT-TYPE
			SYNTAX Integer32
			MAX-ACCESS read-only
			STATUS current
			DESCRIPTION
				"Activated Port Number
				AN5516-01??1-8??11-18"
			::= { igmpactiveJoinPortsNumberEntry 2 }

				-- 1.3.6.1.4.1.5875.800.3.24.8
		portIgmpCfgTable OBJECT-TYPE
			SYNTAX SEQUENCE OF PortIgmpCfgEntry
			MAX-ACCESS not-accessible
			STATUS current
			DESCRIPTION
				"Description"
			::= { igmpConfig 8 }

				-- 1.3.6.1.4.1.5875.800.3.24.8.1
		portIgmpCfgEntry OBJECT-TYPE
			SYNTAX PortIgmpCfgEntry
			MAX-ACCESS not-accessible
			STATUS current
			DESCRIPTION
				"Row Description"
			INDEX { portIndex, profileIndex }
			::= { portIgmpCfgTable 1 }

		
		PortIgmpCfgEntry ::=
			SEQUENCE { 
				profileIndex
					Integer32,
				portCtrlEnable
					INTEGER,
				igmpProfile
					OCTET STRING,
				leaveMode
					INTEGER,
				maxOnlineNum
					Integer32,
				portBandwidth
					Integer32,
				portSignalVlan
					Integer32,
				portIgmpCfgAction
					RowStatus
			 }
		-- 1.3.6.1.4.1.5875.800.3.24.8.1.1
		profileIndex OBJECT-TYPE
			SYNTAX Integer32 (0..1024)
			MAX-ACCESS not-accessible
			STATUS current
			DESCRIPTION
				"Index"
			::= { portIgmpCfgEntry 1 }

				-- 1.3.6.1.4.1.5875.800.3.24.8.1.2
		portCtrlEnable OBJECT-TYPE
			SYNTAX INTEGER
				{
				controlled(1),
				uncontrolled(0)
				}
			MAX-ACCESS read-create
			STATUS current
			DESCRIPTION
				"0:non-controllable
				1:controllable
				"
			::= { portIgmpCfgEntry 2 }

				-- 1.3.6.1.4.1.5875.800.3.24.8.1.3
		igmpProfile OBJECT-TYPE
			SYNTAX OCTET STRING
			MAX-ACCESS read-create
			STATUS current
			DESCRIPTION
				"Multicast Profile Name
				Length 1-20"
			::= { portIgmpCfgEntry 3 }

				-- 1.3.6.1.4.1.5875.800.3.24.8.1.4
		leaveMode OBJECT-TYPE
			SYNTAX INTEGER
				{
				nonFastLeave(0),
				fastLeave(1)
				}
			MAX-ACCESS read-create
			STATUS current
			DESCRIPTION
				"0: Normal
				1: Fast
				"
			::= { portIgmpCfgEntry 4 }

				-- 1.3.6.1.4.1.5875.800.3.24.8.1.5
		maxOnlineNum OBJECT-TYPE
			SYNTAX Integer32 (0..1024)
			MAX-ACCESS read-create
			STATUS current
			DESCRIPTION
				"Maximum Online Group Number
				0-32"
			::= { portIgmpCfgEntry 5 }

				-- 1.3.6.1.4.1.5875.800.3.24.8.1.6
		portBandwidth OBJECT-TYPE
			SYNTAX Integer32 (0..1024)
			MAX-ACCESS read-create
			STATUS current
			DESCRIPTION
				"Port Bandwidth
				0-100000 Kbit/s"
			::= { portIgmpCfgEntry 6 }

				-- 1.3.6.1.4.1.5875.800.3.24.8.1.7
		portSignalVlan OBJECT-TYPE
			SYNTAX Integer32 (0..1024)
			MAX-ACCESS read-create
			STATUS current
			DESCRIPTION
				"Port Signal vlan
				0-4085"
			::= { portIgmpCfgEntry 7 }

				-- 1.3.6.1.4.1.5875.800.3.24.8.1.20
		portIgmpCfgAction OBJECT-TYPE
			SYNTAX RowStatus
				{
				active(1),
				notInService(2),
				notReady(3),
				createAndGo(4),
				createAndWait(5),
				destroy(6)
				}
			MAX-ACCESS read-create
			STATUS current
			DESCRIPTION
				"4:create
				6:delete
				7:modify
				"
			::= { portIgmpCfgEntry 20 }

				-- 1.3.6.1.4.1.5875.800.3.25
		onuAuth OBJECT IDENTIFIER ::= { oltData 25 }

				-- 1.3.6.1.4.1.5875.800.3.25.1
		onuPhysicsAuthTable OBJECT-TYPE
			SYNTAX SEQUENCE OF OnuPhysicsAuthEntry
			MAX-ACCESS not-accessible
			STATUS current
			DESCRIPTION
				"Description"
			::= { onuAuth 1 }

				-- 1.3.6.1.4.1.5875.800.3.25.1.1
		onuPhysicsAuthEntry OBJECT-TYPE
			SYNTAX OnuPhysicsAuthEntry
			MAX-ACCESS not-accessible
			STATUS current
			DESCRIPTION
				"Row Description"
			INDEX { onuIndex }
			::= { onuPhysicsAuthTable 1 }

		
		OnuPhysicsAuthEntry ::=
			SEQUENCE { 
				onuSlotForMacAuth
					Integer32,
				onuPonForMacAuth
					Integer32,
				onuNoForMacAuth
					Integer32,
				onuTypeForMacAuth
					Integer32,
				macForMacAuth
					OCTET STRING,
				passwordForMacAuth
					OCTET STRING,
				actionForMacAuth
					INTEGER
			 }
		-- 1.3.6.1.4.1.5875.800.3.25.1.1.1
		onuSlotForMacAuth OBJECT-TYPE
			SYNTAX Integer32
			MAX-ACCESS read-create
			STATUS current
			DESCRIPTION
				"SLOT Number"
			::= { onuPhysicsAuthEntry 1 }

				-- 1.3.6.1.4.1.5875.800.3.25.1.1.2
		onuPonForMacAuth OBJECT-TYPE
			SYNTAX Integer32
			MAX-ACCESS read-create
			STATUS current
			DESCRIPTION
				"PON Number"
			::= { onuPhysicsAuthEntry 2 }

				-- 1.3.6.1.4.1.5875.800.3.25.1.1.3
		onuNoForMacAuth OBJECT-TYPE
			SYNTAX Integer32
			MAX-ACCESS read-create
			STATUS current
			DESCRIPTION
				"The ONU number is the pre-allocated ONU authorization number"
			::= { onuPhysicsAuthEntry 3 }

				-- 1.3.6.1.4.1.5875.800.3.25.1.1.4
		onuTypeForMacAuth OBJECT-TYPE
			SYNTAX Integer32
			MAX-ACCESS read-create
			STATUS current
			DESCRIPTION
				"See ONU type correspondence table"
			::= { onuPhysicsAuthEntry 4 }

				-- 1.3.6.1.4.1.5875.800.3.25.1.1.5
		macForMacAuth OBJECT-TYPE
			SYNTAX OCTET STRING
			MAX-ACCESS read-create
			STATUS current
			DESCRIPTION
				"MAC Address"
			::= { onuPhysicsAuthEntry 5 }

				-- 1.3.6.1.4.1.5875.800.3.25.1.1.6
		passwordForMacAuth OBJECT-TYPE
			SYNTAX OCTET STRING (SIZE (1..6))
			MAX-ACCESS read-create
			STATUS current
			DESCRIPTION
				"If there is no password, leave it unfilled."
			::= { onuPhysicsAuthEntry 6 }

				-- 1.3.6.1.4.1.5875.800.3.25.1.1.17
		actionForMacAuth OBJECT-TYPE
			SYNTAX INTEGER
				{
				active(1),
				create(4),
				destroy(6)
				}
			MAX-ACCESS read-create
			STATUS current
			DESCRIPTION
				"4:create
				6:delete
				"
			::= { onuPhysicsAuthEntry 17 }

				-- 1.3.6.1.4.1.5875.800.3.25.2
		onuSnAuthFor5116Table OBJECT-TYPE
			SYNTAX SEQUENCE OF OnuSnAuthFor5116Entry
			MAX-ACCESS not-accessible
			STATUS current
			DESCRIPTION
				"Description"
			::= { onuAuth 2 }

				-- 1.3.6.1.4.1.5875.800.3.25.2.1
		onuSnAuthFor5116Entry OBJECT-TYPE
			SYNTAX OnuSnAuthFor5116Entry
			MAX-ACCESS not-accessible
			STATUS current
			DESCRIPTION
				"Row Description"
			INDEX { onuIndex }
			::= { onuSnAuthFor5116Table 1 }

		
		OnuSnAuthFor5116Entry ::=
			SEQUENCE { 
				slotNoForSnAuth
					Integer32,
				ponNoForSnMacAuth
					Integer32,
				onuNoForSnAuth
					Integer32,
				onuTypeForSnAuth
					Integer32,
				snForsnAuth
					OCTET STRING,
				passwordForSnAuth
					OCTET STRING,
				actionForSnAuth
					INTEGER
			 }
		-- 1.3.6.1.4.1.5875.800.3.25.2.1.1
		slotNoForSnAuth OBJECT-TYPE
			SYNTAX Integer32
			MAX-ACCESS read-create
			STATUS current
			DESCRIPTION
				"SLOT Number"
			::= { onuSnAuthFor5116Entry 1 }

				-- 1.3.6.1.4.1.5875.800.3.25.2.1.2
		ponNoForSnMacAuth OBJECT-TYPE
			SYNTAX Integer32
			MAX-ACCESS read-create
			STATUS current
			DESCRIPTION
				"PON Number"
			::= { onuSnAuthFor5116Entry 2 }

				-- 1.3.6.1.4.1.5875.800.3.25.2.1.3
		onuNoForSnAuth OBJECT-TYPE
			SYNTAX Integer32
			MAX-ACCESS read-create
			STATUS current
			DESCRIPTION
				"The ONU number is the pre-allocated ONU authorization number"
			::= { onuSnAuthFor5116Entry 3 }

				-- 1.3.6.1.4.1.5875.800.3.25.2.1.4
		onuTypeForSnAuth OBJECT-TYPE
			SYNTAX Integer32
			MAX-ACCESS read-create
			STATUS current
			DESCRIPTION
				"See ONU type correspondence table"
			::= { onuSnAuthFor5116Entry 4 }

				-- 1.3.6.1.4.1.5875.800.3.25.2.1.5
		snForsnAuth OBJECT-TYPE
			SYNTAX OCTET STRING
			MAX-ACCESS read-create
			STATUS current
			DESCRIPTION
				"SN"
			::= { onuSnAuthFor5116Entry 5 }

				-- 1.3.6.1.4.1.5875.800.3.25.2.1.6
		passwordForSnAuth OBJECT-TYPE
			SYNTAX OCTET STRING
			MAX-ACCESS read-create
			STATUS current
			DESCRIPTION
				"If there is no password, leave it unfilled."
			::= { onuSnAuthFor5116Entry 6 }

				-- 1.3.6.1.4.1.5875.800.3.25.2.1.17
		actionForSnAuth OBJECT-TYPE
			SYNTAX INTEGER
				{
				active(1),
				create(4),
				destroy(6)
				}
			MAX-ACCESS read-create
			STATUS current
			DESCRIPTION
				"4:create
				6:delete
				"
			::= { onuSnAuthFor5116Entry 17 }

				-- 1.3.6.1.4.1.5875.800.3.26
		cvlan2Svlan OBJECT IDENTIFIER ::= { oltData 26 }

				-- 1.3.6.1.4.1.5875.800.3.26.1
		cvlan2SvlanTable OBJECT-TYPE
			SYNTAX SEQUENCE OF Cvlan2SvlanEntry
			MAX-ACCESS not-accessible
			STATUS current
			DESCRIPTION
				"Description"
			::= { cvlan2Svlan 1 }

				-- 1.3.6.1.4.1.5875.800.3.26.1.1
		cvlan2SvlanEntry OBJECT-TYPE
			SYNTAX Cvlan2SvlanEntry
			MAX-ACCESS not-accessible
			STATUS current
			DESCRIPTION
				"Row Description"
			INDEX { onuIndex, onuCvlanVid }
			::= { cvlan2SvlanTable 1 }

		
		Cvlan2SvlanEntry ::=
			SEQUENCE { 
				onuCvlanVid
					Integer32,
				onuSvlanVid
					Integer32
			 }
		-- 1.3.6.1.4.1.5875.800.3.26.1.1.1
		onuCvlanVid OBJECT-TYPE
			SYNTAX Integer32 (1..65535)
			MAX-ACCESS not-accessible
			STATUS current
			DESCRIPTION
				"Index"
			::= { cvlan2SvlanEntry 1 }

				-- 1.3.6.1.4.1.5875.800.3.26.1.1.2
		onuSvlanVid OBJECT-TYPE
			SYNTAX Integer32
			MAX-ACCESS read-only
			STATUS current
			DESCRIPTION
				"Svlan Value"
			::= { cvlan2SvlanEntry 2 }

				-- 1.3.6.1.4.1.5875.800.3.27
		onuCatvInfo OBJECT IDENTIFIER ::= { oltData 27 }

				-- 1.3.6.1.4.1.5875.800.3.27.1
		onuCatvEnableTable OBJECT-TYPE
			SYNTAX SEQUENCE OF OnuCatvEnableEntry
			MAX-ACCESS not-accessible
			STATUS current
			DESCRIPTION
				"Description"
			::= { onuCatvInfo 1 }

				-- 1.3.6.1.4.1.5875.800.3.27.1.1
		onuCatvEnableEntry OBJECT-TYPE
			SYNTAX OnuCatvEnableEntry
			MAX-ACCESS not-accessible
			STATUS current
			DESCRIPTION
				"Row Description"
			INDEX { onuIndex }
			::= { onuCatvEnableTable 1 }

		
		OnuCatvEnableEntry ::=
			SEQUENCE { 
				onuCatvEnable
					INTEGER,
				onuCatvRfOutputOffset
					Integer32
			 }
		-- 1.3.6.1.4.1.5875.800.3.27.1.1.1
		onuCatvEnable OBJECT-TYPE
			SYNTAX INTEGER
				{
				disable(0),
				enable(1)
				}
			MAX-ACCESS read-create
			STATUS current
			DESCRIPTION
				"0:disable
				1:enable
				"
			::= { onuCatvEnableEntry 1 }

				-- 1.3.6.1.4.1.5875.800.3.27.1.1.2
		onuCatvRfOutputOffset OBJECT-TYPE
			SYNTAX Integer32 (-128..128)
			MAX-ACCESS read-create
			STATUS current
			DESCRIPTION
				"Description."
			::= { onuCatvEnableEntry 2 }

				-- 1.3.6.1.4.1.5875.800.3.28
		onuSNReplace OBJECT IDENTIFIER ::= { oltData 28 }

				-- 1.3.6.1.4.1.5875.800.3.28.1
		onuSNReplaceTable OBJECT-TYPE
			SYNTAX SEQUENCE OF OnuSNReplaceEntry
			MAX-ACCESS not-accessible
			STATUS current
			DESCRIPTION
				"Description"
			::= { onuSNReplace 1 }

				-- 1.3.6.1.4.1.5875.800.3.28.1.1
		onuSNReplaceEntry OBJECT-TYPE
			SYNTAX OnuSNReplaceEntry
			MAX-ACCESS not-accessible
			STATUS current
			DESCRIPTION
				"Row Description"
			INDEX { onuIndex }
			::= { onuSNReplaceTable 1 }

		
		OnuSNReplaceEntry ::=
			SEQUENCE { 
				onuSNReplaceSlot
					Integer32,
				onuSNReplacePon
					Integer32,
				onuSNReplaceOnuId
					Integer32,
				onuSNReplaceSnLoid
					OCTET STRING,
				onuSNReplaceSnPwd
					OCTET STRING,
				onuSNReplaceNewSnLoid
					OCTET STRING,
				onuSNReplaceNewSnPwd
					OCTET STRING,
				onuSNReplaceStatus
					Integer32
			 }
		-- 1.3.6.1.4.1.5875.800.3.28.1.1.1
		onuSNReplaceSlot OBJECT-TYPE
			SYNTAX Integer32
			MAX-ACCESS read-only
			STATUS current
			DESCRIPTION
				"Column Description"
			::= { onuSNReplaceEntry 1 }

				-- 1.3.6.1.4.1.5875.800.3.28.1.1.2
		onuSNReplacePon OBJECT-TYPE
			SYNTAX Integer32
			MAX-ACCESS read-only
			STATUS current
			DESCRIPTION
				"Column Description"
			::= { onuSNReplaceEntry 2 }

				-- 1.3.6.1.4.1.5875.800.3.28.1.1.3
		onuSNReplaceOnuId OBJECT-TYPE
			SYNTAX Integer32
			MAX-ACCESS read-only
			STATUS current
			DESCRIPTION
				"Column Description"
			::= { onuSNReplaceEntry 3 }

				-- 1.3.6.1.4.1.5875.800.3.28.1.1.4
		onuSNReplaceSnLoid OBJECT-TYPE
			SYNTAX OCTET STRING
			MAX-ACCESS read-create
			STATUS current
			DESCRIPTION
				"Column Description"
			::= { onuSNReplaceEntry 4 }

				-- 1.3.6.1.4.1.5875.800.3.28.1.1.5
		onuSNReplaceSnPwd OBJECT-TYPE
			SYNTAX OCTET STRING
			MAX-ACCESS read-create
			STATUS current
			DESCRIPTION
				"Column Description"
			::= { onuSNReplaceEntry 5 }

				-- 1.3.6.1.4.1.5875.800.3.28.1.1.6
		onuSNReplaceNewSnLoid OBJECT-TYPE
			SYNTAX OCTET STRING
			MAX-ACCESS read-create
			STATUS current
			DESCRIPTION
				"Column Description"
			::= { onuSNReplaceEntry 6 }

				-- 1.3.6.1.4.1.5875.800.3.28.1.1.7
		onuSNReplaceNewSnPwd OBJECT-TYPE
			SYNTAX OCTET STRING
			MAX-ACCESS read-only
			STATUS current
			DESCRIPTION
				"Column Description"
			::= { onuSNReplaceEntry 7 }

				-- 1.3.6.1.4.1.5875.800.3.28.1.1.8
		onuSNReplaceStatus OBJECT-TYPE
			SYNTAX Integer32 (0..1)
			MAX-ACCESS read-create
			STATUS current
			DESCRIPTION
				"Description:
				1:offonline/fiber cut/power failure(0)
				2:online(1)"
			::= { onuSNReplaceEntry 8 }

				-- 1.3.6.1.4.1.5875.800.3.30
		gponOnuServiceConfig OBJECT IDENTIFIER ::= { oltData 30 }

				-- 1.3.6.1.4.1.5875.800.3.30.1
		gponRmtManageCfgTable OBJECT-TYPE
			SYNTAX SEQUENCE OF GponRmtManageCfgEntry
			MAX-ACCESS not-accessible
			STATUS current
			DESCRIPTION
				"Description"
			::= { gponOnuServiceConfig 1 }

				-- 1.3.6.1.4.1.5875.800.3.30.1.1
		gponRmtManageCfgEntry OBJECT-TYPE
			SYNTAX GponRmtManageCfgEntry
			MAX-ACCESS not-accessible
			STATUS current
			DESCRIPTION
				"Row Description"
			INDEX { onuIndex }
			::= { gponRmtManageCfgTable 1 }

		
		GponRmtManageCfgEntry ::=
			SEQUENCE { 
				gponRmtManageUrl
					OCTET STRING,
				gponRmtManageUser
					OCTET STRING,
				gponRmtManagePwd
					OCTET STRING,
				gponRmtManageAction
					INTEGER
			 }
		-- 1.3.6.1.4.1.5875.800.3.30.1.1.1
		gponRmtManageUrl OBJECT-TYPE
			SYNTAX OCTET STRING
			MAX-ACCESS read-create
			STATUS current
			DESCRIPTION
				"ACS Server URL
				The max length of URL is 128"
			::= { gponRmtManageCfgEntry 1 }

				-- 1.3.6.1.4.1.5875.800.3.30.1.1.2
		gponRmtManageUser OBJECT-TYPE
			SYNTAX OCTET STRING
			MAX-ACCESS read-create
			STATUS current
			DESCRIPTION
				"Username For Connecting ACS Server
				The max length of username is 64"
			::= { gponRmtManageCfgEntry 2 }

				-- 1.3.6.1.4.1.5875.800.3.30.1.1.3
		gponRmtManagePwd OBJECT-TYPE
			SYNTAX OCTET STRING
			MAX-ACCESS read-create
			STATUS current
			DESCRIPTION
				"Password For Connecting ACS Server
				The max length of password is 64"
			::= { gponRmtManageCfgEntry 3 }

				-- 1.3.6.1.4.1.5875.800.3.30.1.1.4
		gponRmtManageAction OBJECT-TYPE
			SYNTAX INTEGER
				{
				active(1),
				create(4),
				modify(7)
				}
			MAX-ACCESS read-create
			STATUS current
			DESCRIPTION
				"7:modify"
			::= { gponRmtManageCfgEntry 4 }

				-- 1.3.6.1.4.1.5875.800.3.30.2
		gponVEIPManagePathCfgTable OBJECT-TYPE
			SYNTAX SEQUENCE OF GponVEIPManagePathCfgEntry
			MAX-ACCESS not-accessible
			STATUS current
			DESCRIPTION
				"Description"
			::= { gponOnuServiceConfig 2 }

				-- 1.3.6.1.4.1.5875.800.3.30.2.1
		gponVEIPManagePathCfgEntry OBJECT-TYPE
			SYNTAX GponVEIPManagePathCfgEntry
			MAX-ACCESS not-accessible
			STATUS current
			DESCRIPTION
				"Row Description"
			INDEX { portIndex }
			::= { gponVEIPManagePathCfgTable 1 }

		
		GponVEIPManagePathCfgEntry ::=
			SEQUENCE { 
				gponVEIPManagePathDsp
					Integer32,
				gponVEIPManagePathIPAddress
					OCTET STRING,
				gponVEIPManagePathGateWay
					OCTET STRING,
				gponVEIPManagePathPrimaryDns
					OCTET STRING,
				gponVEIPManagePathSecondaryDns
					OCTET STRING,
				gponVEIPManagePathNetworkPort
					Integer32,
				gponVEIPManagePathCVlan
					Integer32,
				gponVEIPManagePathCVlanCos
					Integer32,
				gponVEIPManagePathIpMask
					Integer32,
				gponVEIPManagePathCfgPortType
					Integer32,
				gponVEIPManagePathCfgChannelEnable
					Integer32,
				gponVEIPManagePathCfgmode
					Integer32,
				gponVEIPManagePathCfgManageVlanName
					OCTET STRING,
				gponVEIPManagePathCfgIPProtocol
					Integer32,
				gponVEIPManagePathCfgToSDSCP
					Integer32,
				gponVEIPManagePathCfgTag
					Integer32,
				gponVEIPManagePathCfgSvlanTpid
					Integer32,
				gponVEIPManagePathCfgSVlanId
					Integer32,
				gponVEIPManagePathCfgSvlanCos
					Integer32,
				gponVEIPManagePathCfgCVlanTpid
					Integer32,
				gponVEIPManagePathAction
					INTEGER
			 }
		-- 1.3.6.1.4.1.5875.800.3.30.2.1.1
		gponVEIPManagePathDsp OBJECT-TYPE
			SYNTAX Integer32 (0..1)
			MAX-ACCESS read-create
			STATUS current
			DESCRIPTION
				"0: DHCP
				1: Static
				If the value is 0, keep null for the following 4 items.
				"
			::= { gponVEIPManagePathCfgEntry 1 }

				-- 1.3.6.1.4.1.5875.800.3.30.2.1.2
		gponVEIPManagePathIPAddress OBJECT-TYPE
			SYNTAX OCTET STRING
			MAX-ACCESS read-create
			STATUS current
			DESCRIPTION
				"Static IP Address
				The max length of the string is 128"
			::= { gponVEIPManagePathCfgEntry 2 }

				-- 1.3.6.1.4.1.5875.800.3.30.2.1.3
		gponVEIPManagePathGateWay OBJECT-TYPE
			SYNTAX OCTET STRING
			MAX-ACCESS read-create
			STATUS current
			DESCRIPTION
				"Gateway
				The max length of the string is 128"
			::= { gponVEIPManagePathCfgEntry 3 }

				-- 1.3.6.1.4.1.5875.800.3.30.2.1.4
		gponVEIPManagePathPrimaryDns OBJECT-TYPE
			SYNTAX OCTET STRING
			MAX-ACCESS read-create
			STATUS current
			DESCRIPTION
				"First-Choice DNS
				The max length of the string is 128"
			::= { gponVEIPManagePathCfgEntry 4 }

				-- 1.3.6.1.4.1.5875.800.3.30.2.1.5
		gponVEIPManagePathSecondaryDns OBJECT-TYPE
			SYNTAX OCTET STRING
			MAX-ACCESS read-create
			STATUS current
			DESCRIPTION
				"Standby DNS
				The max length of the string is 128"
			::= { gponVEIPManagePathCfgEntry 5 }

				-- 1.3.6.1.4.1.5875.800.3.30.2.1.6
		gponVEIPManagePathNetworkPort OBJECT-TYPE
			SYNTAX Integer32 (0..65535)
			MAX-ACCESS read-create
			STATUS current
			DESCRIPTION
				"Network Port Number
				0 to 65535"
			::= { gponVEIPManagePathCfgEntry 6 }

				-- 1.3.6.1.4.1.5875.800.3.30.2.1.7
		gponVEIPManagePathCVlan OBJECT-TYPE
			SYNTAX Integer32 (1..4085 | 65535)
			MAX-ACCESS read-create
			STATUS current
			DESCRIPTION
				"1 to 4085
				0xffff (null)
				"
			::= { gponVEIPManagePathCfgEntry 7 }

				-- 1.3.6.1.4.1.5875.800.3.30.2.1.8
		gponVEIPManagePathCVlanCos OBJECT-TYPE
			SYNTAX Integer32 (0..7 | 65535)
			MAX-ACCESS read-create
			STATUS current
			DESCRIPTION
				"0 to 7,
				0xffff (null)
				"
			::= { gponVEIPManagePathCfgEntry 8 }

				-- 1.3.6.1.4.1.5875.800.3.30.2.1.9
		gponVEIPManagePathIpMask OBJECT-TYPE
			SYNTAX Integer32
			MAX-ACCESS read-create
			STATUS current
			DESCRIPTION
				"Mask
				0-32"
			::= { gponVEIPManagePathCfgEntry 9 }

				-- 1.3.6.1.4.1.5875.800.3.30.2.1.10
		gponVEIPManagePathCfgPortType OBJECT-TYPE
			SYNTAX Integer32
			MAX-ACCESS read-create
			STATUS current
			DESCRIPTION
				"4:VEIP"
			::= { gponVEIPManagePathCfgEntry 10 }

				-- 1.3.6.1.4.1.5875.800.3.30.2.1.11
		gponVEIPManagePathCfgChannelEnable OBJECT-TYPE
			SYNTAX Integer32
			MAX-ACCESS read-create
			STATUS current
			DESCRIPTION
				"0-disable
				1-enable"
			::= { gponVEIPManagePathCfgEntry 11 }

				-- 1.3.6.1.4.1.5875.800.3.30.2.1.12
		gponVEIPManagePathCfgmode OBJECT-TYPE
			SYNTAX Integer32
			MAX-ACCESS read-create
			STATUS current
			DESCRIPTION
				"0:TR-069
				1:SNMP
				2:TR-069_VOIP
				
				"
			::= { gponVEIPManagePathCfgEntry 12 }

				-- 1.3.6.1.4.1.5875.800.3.30.2.1.13
		gponVEIPManagePathCfgManageVlanName OBJECT-TYPE
			SYNTAX OCTET STRING
			MAX-ACCESS read-create
			STATUS current
			DESCRIPTION
				"Default value:manage"
			::= { gponVEIPManagePathCfgEntry 13 }

				-- 1.3.6.1.4.1.5875.800.3.30.2.1.14
		gponVEIPManagePathCfgIPProtocol OBJECT-TYPE
			SYNTAX Integer32
			MAX-ACCESS read-create
			STATUS current
			DESCRIPTION
				"1:TCP
				2:UDP"
			::= { gponVEIPManagePathCfgEntry 14 }

				-- 1.3.6.1.4.1.5875.800.3.30.2.1.15
		gponVEIPManagePathCfgToSDSCP OBJECT-TYPE
			SYNTAX Integer32
			MAX-ACCESS read-create
			STATUS current
			DESCRIPTION
				"0-63"
			::= { gponVEIPManagePathCfgEntry 15 }

				-- 1.3.6.1.4.1.5875.800.3.30.2.1.16
		gponVEIPManagePathCfgTag OBJECT-TYPE
			SYNTAX Integer32
			MAX-ACCESS read-create
			STATUS current
			DESCRIPTION
				"0:untag
				1:tag
				"
			::= { gponVEIPManagePathCfgEntry 16 }

				-- 1.3.6.1.4.1.5875.800.3.30.2.1.17
		gponVEIPManagePathCfgSvlanTpid OBJECT-TYPE
			SYNTAX Integer32
			MAX-ACCESS read-create
			STATUS current
			DESCRIPTION
				"1-65534,0xffff;
				Default value:0x8100
				"
			::= { gponVEIPManagePathCfgEntry 17 }

				-- 1.3.6.1.4.1.5875.800.3.30.2.1.18
		gponVEIPManagePathCfgSVlanId OBJECT-TYPE
			SYNTAX Integer32
			MAX-ACCESS read-create
			STATUS current
			DESCRIPTION
				"1-4085,0xffff
				Default value:0xffff
				"
			::= { gponVEIPManagePathCfgEntry 18 }

				-- 1.3.6.1.4.1.5875.800.3.30.2.1.19
		gponVEIPManagePathCfgSvlanCos OBJECT-TYPE
			SYNTAX Integer32
			MAX-ACCESS read-create
			STATUS current
			DESCRIPTION
				"0-7,0xffff
				Default value:0xffff
				"
			::= { gponVEIPManagePathCfgEntry 19 }

				-- 1.3.6.1.4.1.5875.800.3.30.2.1.20
		gponVEIPManagePathCfgCVlanTpid OBJECT-TYPE
			SYNTAX Integer32
			MAX-ACCESS read-create
			STATUS current
			DESCRIPTION
				"1-65534,0xffff"
			::= { gponVEIPManagePathCfgEntry 20 }

				-- 1.3.6.1.4.1.5875.800.3.30.2.1.30
		gponVEIPManagePathAction OBJECT-TYPE
			SYNTAX INTEGER
				{
				active(1),
				create(4),
				destroy(6),
				modify(7)
				}
			MAX-ACCESS read-create
			STATUS current
			DESCRIPTION
				"4:create
				6:delete
				7:modify
				"
			::= { gponVEIPManagePathCfgEntry 30 }

				-- 1.3.6.1.4.1.5875.800.3.30.3
		gponVEIPServiceCfgTable OBJECT-TYPE
			SYNTAX SEQUENCE OF GponVEIPServiceCfgEntry
			MAX-ACCESS not-accessible
			STATUS current
			DESCRIPTION
				"Description"
			::= { gponOnuServiceConfig 3 }

				-- 1.3.6.1.4.1.5875.800.3.30.3.1
		gponVEIPServiceCfgEntry OBJECT-TYPE
			SYNTAX GponVEIPServiceCfgEntry
			MAX-ACCESS not-accessible
			STATUS current
			DESCRIPTION
				"Row Description"
			INDEX { portIndex, gponVEIPServiceID }
			::= { gponVEIPServiceCfgTable 1 }

		
		GponVEIPServiceCfgEntry ::=
			SEQUENCE { 
				gponVEIPServiceID
					Integer32,
				gponVEIPServiceTls
					Integer32,
				gponVEIPServiceCVlan
					Integer32,
				gponVEIPServiceCVlanCos
					Integer32,
				gponVEIPServiceTVlan
					Integer32,
				gponVEIPServiceTVlanCos
					Integer32,
				gponVEIPServiceSVlan
					Integer32,
				gponVEIPServiceSVlanCos
					Integer32,
				gponVEIPServiceUsBandWidth
					Integer32,
				gponVEIPServiceDsBandWidth
					Integer32,
				gponVEIPServiceProfileName
					OCTET STRING,
				gponVEIPServiceAction
					INTEGER
			 }
		-- 1.3.6.1.4.1.5875.800.3.30.3.1.1
		gponVEIPServiceID OBJECT-TYPE
			SYNTAX Integer32 (1..65535)
			MAX-ACCESS not-accessible
			STATUS current
			DESCRIPTION
				"Index 1 to 16"
			::= { gponVEIPServiceCfgEntry 1 }

				-- 1.3.6.1.4.1.5875.800.3.30.3.1.2
		gponVEIPServiceTls OBJECT-TYPE
			SYNTAX Integer32 (0..1)
			MAX-ACCESS read-create
			STATUS current
			DESCRIPTION
				"0: non-TLS
				1: TLS
				One VEIP port can only have one TLS.
				"
			::= { gponVEIPServiceCfgEntry 2 }

				-- 1.3.6.1.4.1.5875.800.3.30.3.1.3
		gponVEIPServiceCVlan OBJECT-TYPE
			SYNTAX Integer32 (1..4085 | 65535)
			MAX-ACCESS read-create
			STATUS current
			DESCRIPTION
				"1 to 4085
				0xffff (null)
				"
			::= { gponVEIPServiceCfgEntry 3 }

				-- 1.3.6.1.4.1.5875.800.3.30.3.1.4
		gponVEIPServiceCVlanCos OBJECT-TYPE
			SYNTAX Integer32 (0..7 | 65535)
			MAX-ACCESS read-create
			STATUS current
			DESCRIPTION
				"0 to 7
				0xffff (null)
				"
			::= { gponVEIPServiceCfgEntry 4 }

				-- 1.3.6.1.4.1.5875.800.3.30.3.1.5
		gponVEIPServiceTVlan OBJECT-TYPE
			SYNTAX Integer32 (1..4085 | 65535)
			MAX-ACCESS read-create
			STATUS current
			DESCRIPTION
				"1 to 4085
				0xffff (null)
				"
			::= { gponVEIPServiceCfgEntry 5 }

				-- 1.3.6.1.4.1.5875.800.3.30.3.1.6
		gponVEIPServiceTVlanCos OBJECT-TYPE
			SYNTAX Integer32 (0..7 | 65535)
			MAX-ACCESS read-create
			STATUS current
			DESCRIPTION
				"0 to 7
				0xffff (null)
				"
			::= { gponVEIPServiceCfgEntry 6 }

				-- 1.3.6.1.4.1.5875.800.3.30.3.1.7
		gponVEIPServiceSVlan OBJECT-TYPE
			SYNTAX Integer32 (1..4085 | 65535)
			MAX-ACCESS read-create
			STATUS current
			DESCRIPTION
				"1 to 4085
				0xffff (null)
				"
			::= { gponVEIPServiceCfgEntry 7 }

				-- 1.3.6.1.4.1.5875.800.3.30.3.1.8
		gponVEIPServiceSVlanCos OBJECT-TYPE
			SYNTAX Integer32 (0..7 | 65535)
			MAX-ACCESS read-create
			STATUS current
			DESCRIPTION
				"0 to 7
				0xffff (null)
				"
			::= { gponVEIPServiceCfgEntry 8 }

				-- 1.3.6.1.4.1.5875.800.3.30.3.1.9
		gponVEIPServiceUsBandWidth OBJECT-TYPE
			SYNTAX Integer32
			MAX-ACCESS read-create
			STATUS current
			DESCRIPTION
				"Uplink Maximum Bandwidth
				0-0xffffffff"
			::= { gponVEIPServiceCfgEntry 9 }

				-- 1.3.6.1.4.1.5875.800.3.30.3.1.10
		gponVEIPServiceDsBandWidth OBJECT-TYPE
			SYNTAX Integer32 (0..1024)
			MAX-ACCESS read-create
			STATUS current
			DESCRIPTION
				"Downlink Maximum Bandwidth
				0-0xffffffff"
			::= { gponVEIPServiceCfgEntry 10 }

				-- 1.3.6.1.4.1.5875.800.3.30.3.1.11
		gponVEIPServiceProfileName OBJECT-TYPE
			SYNTAX OCTET STRING
			MAX-ACCESS read-create
			STATUS current
			DESCRIPTION
				"Service model profile name"
			::= { gponVEIPServiceCfgEntry 11 }

				-- 1.3.6.1.4.1.5875.800.3.30.3.1.12
		gponVEIPServiceAction OBJECT-TYPE
			SYNTAX INTEGER
				{
				active(1),
				create(4),
				destroy(6),
				modify(7)
				}
			MAX-ACCESS read-create
			STATUS current
			DESCRIPTION
				"4:create
				6:delete
				7:modify
				"
			::= { gponVEIPServiceCfgEntry 12 }

				-- 1.3.6.1.4.1.5875.800.3.30.4
		gponVEIPServiceIDCfgTable OBJECT-TYPE
			SYNTAX SEQUENCE OF GponVEIPServiceIDCfgEntry
			MAX-ACCESS not-accessible
			STATUS current
			DESCRIPTION
				"Obtain the available service ID (the node of the EPON3.1 is abandoned) "
			::= { gponOnuServiceConfig 4 }

				-- 1.3.6.1.4.1.5875.800.3.30.4.1
		gponVEIPServiceIDCfgEntry OBJECT-TYPE
			SYNTAX GponVEIPServiceIDCfgEntry
			MAX-ACCESS not-accessible
			STATUS current
			DESCRIPTION
				"Row Description"
			INDEX { portIndex }
			::= { gponVEIPServiceIDCfgTable 1 }

		
		GponVEIPServiceIDCfgEntry ::=
			SEQUENCE { 
				nextGponVEIPServiceID
					Integer32
			 }
		-- 1.3.6.1.4.1.5875.800.3.30.4.1.1
		nextGponVEIPServiceID OBJECT-TYPE
			SYNTAX Integer32
			MAX-ACCESS read-only
			STATUS current
			DESCRIPTION
				"Obtain the available service ID (available for the EPON3.1) "
			::= { gponVEIPServiceIDCfgEntry 1 }

				-- 1.3.6.1.4.1.5875.800.3.30.5
		gponOnuDefaultQinQConfTable OBJECT-TYPE
			SYNTAX SEQUENCE OF GponOnuDefaultQinQConfEntry
			MAX-ACCESS not-accessible
			STATUS current
			DESCRIPTION
				"Description."
			::= { gponOnuServiceConfig 5 }

				-- 1.3.6.1.4.1.5875.800.3.30.5.1
		gponOnuDefaultQinQConfEntry OBJECT-TYPE
			SYNTAX GponOnuDefaultQinQConfEntry
			MAX-ACCESS not-accessible
			STATUS current
			DESCRIPTION
				"Description."
			INDEX { onuIndex, gponOnuQinQServiceSN }
			::= { gponOnuDefaultQinQConfTable 1 }

		
		GponOnuDefaultQinQConfEntry ::=
			SEQUENCE { 
				gponOnuQinQServiceSN
					Integer32,
				gponOnuQinQCvlanID
					Integer32,
				gponOnuQinQCvlanPriority
					Integer32,
				gponOnuQinQTransVlanID
					Integer32,
				gponOnuQinQTransVLANPriority
					Integer32,
				gponOnuQinQSvlanID
					Integer32,
				gponOnuQinQSvlanPriority
					Integer32,
				gponOnuQinQOperation
					Integer32
			 }
		-- 1.3.6.1.4.1.5875.800.3.30.5.1.1
		gponOnuQinQServiceSN OBJECT-TYPE
			SYNTAX Integer32 (0..20000)
			MAX-ACCESS read-only
			STATUS current
			DESCRIPTION
				"Service SN (Index)
				Index 1 to 16"
			::= { gponOnuDefaultQinQConfEntry 1 }

				-- 1.3.6.1.4.1.5875.800.3.30.5.1.3
		gponOnuQinQCvlanID OBJECT-TYPE
			SYNTAX Integer32
			MAX-ACCESS read-write
			STATUS current
			DESCRIPTION
				"CVLAN ID
				1??4085
				0xffff(null)
				"
			::= { gponOnuDefaultQinQConfEntry 3 }

				-- 1.3.6.1.4.1.5875.800.3.30.5.1.4
		gponOnuQinQCvlanPriority OBJECT-TYPE
			SYNTAX Integer32
			MAX-ACCESS read-write
			STATUS current
			DESCRIPTION
				"CVLAN Priority
				0??7
				0xff(null)
				"
			::= { gponOnuDefaultQinQConfEntry 4 }

				-- 1.3.6.1.4.1.5875.800.3.30.5.1.5
		gponOnuQinQTransVlanID OBJECT-TYPE
			SYNTAX Integer32
			MAX-ACCESS read-write
			STATUS current
			DESCRIPTION
				"Translation VLAN ID:
				1??4085
				0xffff(null)
				"
			::= { gponOnuDefaultQinQConfEntry 5 }

				-- 1.3.6.1.4.1.5875.800.3.30.5.1.6
		gponOnuQinQTransVLANPriority OBJECT-TYPE
			SYNTAX Integer32
			MAX-ACCESS read-write
			STATUS current
			DESCRIPTION
				"Translation VLAN Priority or COS
				0??7
				0xff(null)
				"
			::= { gponOnuDefaultQinQConfEntry 6 }

				-- 1.3.6.1.4.1.5875.800.3.30.5.1.7
		gponOnuQinQSvlanID OBJECT-TYPE
			SYNTAX Integer32
			MAX-ACCESS read-write
			STATUS current
			DESCRIPTION
				"SVLAN ID
				1??4085
				0xffff(null)
				"
			::= { gponOnuDefaultQinQConfEntry 7 }

				-- 1.3.6.1.4.1.5875.800.3.30.5.1.8
		gponOnuQinQSvlanPriority OBJECT-TYPE
			SYNTAX Integer32
			MAX-ACCESS read-write
			STATUS current
			DESCRIPTION
				"SVLAN Priority or COS:
				0??7
				0xff(null)
				"
			::= { gponOnuDefaultQinQConfEntry 8 }

				-- 1.3.6.1.4.1.5875.800.3.30.5.1.12
		gponOnuQinQOperation OBJECT-TYPE
			SYNTAX Integer32
			MAX-ACCESS read-write
			STATUS current
			DESCRIPTION
				"Operation:
				4:create
				6:delete
				7:modify
				"
			::= { gponOnuDefaultQinQConfEntry 12 }

				-- 1.3.6.1.4.1.5875.800.3.30.6
		gponGetNextServiceIDTable OBJECT-TYPE
			SYNTAX SEQUENCE OF GponGetNextServiceIDEntry
			MAX-ACCESS not-accessible
			STATUS current
			DESCRIPTION
				"Description."
			::= { gponOnuServiceConfig 6 }

				-- 1.3.6.1.4.1.5875.800.3.30.6.1
		gponGetNextServiceIDEntry OBJECT-TYPE
			SYNTAX GponGetNextServiceIDEntry
			MAX-ACCESS not-accessible
			STATUS current
			DESCRIPTION
				"Description."
			INDEX { onuIndex, gponGetNextServiceID }
			::= { gponGetNextServiceIDTable 1 }

		
		GponGetNextServiceIDEntry ::=
			SEQUENCE { 
				gponGetNextServiceID
					Integer32
			 }
		-- 1.3.6.1.4.1.5875.800.3.30.6.1.1
		gponGetNextServiceID OBJECT-TYPE
			SYNTAX Integer32 (0..20000)
			MAX-ACCESS read-only
			STATUS current
			DESCRIPTION
				"Index
				1~16"
			::= { gponGetNextServiceIDEntry 1 }

				-- 1.3.6.1.4.1.5875.800.3.50
		gponConfig OBJECT IDENTIFIER ::= { oltData 50 }

				-- 1.3.6.1.4.1.5875.800.3.50.1
		gponServiceBandwidthCfg OBJECT IDENTIFIER ::= { gponConfig 1 }

				-- 1.3.6.1.4.1.5875.800.3.50.1.1
		gponServiceBandwidthCfgTable OBJECT-TYPE
			SYNTAX SEQUENCE OF GponServiceBandwidthCfgEntry
			MAX-ACCESS not-accessible
			STATUS current
			DESCRIPTION
				"Description"
			::= { gponServiceBandwidthCfg 1 }

				-- 1.3.6.1.4.1.5875.800.3.50.1.1.1
		gponServiceBandwidthCfgEntry OBJECT-TYPE
			SYNTAX GponServiceBandwidthCfgEntry
			MAX-ACCESS not-accessible
			STATUS current
			DESCRIPTION
				"Row Description"
			INDEX { onuIndex, gponServiceType }
			::= { gponServiceBandwidthCfgTable 1 }

		
		GponServiceBandwidthCfgEntry ::=
			SEQUENCE { 
				gponServiceType
					Integer32,
				gponFixedBandwidth
					Integer32,
				gponAssureBandwidth
					Integer32,
				gponMaxBandwidth
					Integer32,
				gponBandwidthCfgAction
					RowStatus
			 }
		-- 1.3.6.1.4.1.5875.800.3.50.1.1.1.1
		gponServiceType OBJECT-TYPE
			SYNTAX Integer32 (1..65535)
			MAX-ACCESS not-accessible
			STATUS current
			DESCRIPTION
				"Column Description:
				1:IGMP 
				2:broadband Internet access
				3:Voice
				4:TDM
				5:integrated service"
			::= { gponServiceBandwidthCfgEntry 1 }

				-- 1.3.6.1.4.1.5875.800.3.50.1.1.1.2
		gponFixedBandwidth OBJECT-TYPE
			SYNTAX Integer32 (0..1024)
			MAX-ACCESS read-create
			STATUS current
			DESCRIPTION
				"Fixed Bandwidth
				16-128000 Kbyte/s"
			::= { gponServiceBandwidthCfgEntry 2 }

				-- 1.3.6.1.4.1.5875.800.3.50.1.1.1.3
		gponAssureBandwidth OBJECT-TYPE
			SYNTAX Integer32
			MAX-ACCESS read-create
			STATUS current
			DESCRIPTION
				"Assured Bandwidth
				0??32??256000 Kbyte/s"
			::= { gponServiceBandwidthCfgEntry 3 }

				-- 1.3.6.1.4.1.5875.800.3.50.1.1.1.4
		gponMaxBandwidth OBJECT-TYPE
			SYNTAX Integer32
			MAX-ACCESS read-create
			STATUS current
			DESCRIPTION
				"Maximum Bandwidth
				16??256000Kbyte/s"
			::= { gponServiceBandwidthCfgEntry 4 }

				-- 1.3.6.1.4.1.5875.800.3.50.1.1.1.10
		gponBandwidthCfgAction OBJECT-TYPE
			SYNTAX RowStatus
			MAX-ACCESS read-create
			STATUS current
			DESCRIPTION
				"4:create
				6:delete
				7:modify
				"
			::= { gponServiceBandwidthCfgEntry 10 }

				-- 1.3.6.1.4.1.5875.800.3.51
		ponOpticalThresh OBJECT IDENTIFIER ::= { oltData 51 }

				-- 1.3.6.1.4.1.5875.800.3.51.1
		onuPonOpticalThreshTable OBJECT-TYPE
			SYNTAX SEQUENCE OF OnuPonOpticalThreshEntry
			MAX-ACCESS not-accessible
			STATUS current
			DESCRIPTION
				"Description"
			::= { ponOpticalThresh 1 }

				-- 1.3.6.1.4.1.5875.800.3.51.1.1
		onuPonOpticalThreshEntry OBJECT-TYPE
			SYNTAX OnuPonOpticalThreshEntry
			MAX-ACCESS not-accessible
			STATUS current
			DESCRIPTION
				"Row Description"
			INDEX { onuOpticalProfileId }
			::= { onuPonOpticalThreshTable 1 }

		
		OnuPonOpticalThreshEntry ::=
			SEQUENCE { 
				onuOpticalProfileId
					Integer32,
				onuOpticalProfilename
					OCTET STRING,
				recOptOverReport
					Integer32,
				recOptOverClear
					Integer32,
				recOptLowReport
					Integer32,
				recOptLowClear
					Integer32,
				sendOptOverReport
					Integer32,
				sendOptiOverClear
					Integer32,
				sendOptLowReport
					Integer32,
				sendOptLowClear
					Integer32
			 }
		-- 1.3.6.1.4.1.5875.800.3.51.1.1.1
		onuOpticalProfileId OBJECT-TYPE
			SYNTAX Integer32 (1..65535)
			MAX-ACCESS not-accessible
			STATUS current
			DESCRIPTION
				"Column Description
				0~64"
			::= { onuPonOpticalThreshEntry 1 }

				-- 1.3.6.1.4.1.5875.800.3.51.1.1.2
		onuOpticalProfilename OBJECT-TYPE
			SYNTAX OCTET STRING
			MAX-ACCESS read-only
			STATUS current
			DESCRIPTION
				"Column Description"
			::= { onuPonOpticalThreshEntry 2 }

				-- 1.3.6.1.4.1.5875.800.3.51.1.1.3
		recOptOverReport OBJECT-TYPE
			SYNTAX Integer32
			MAX-ACCESS read-only
			STATUS current
			DESCRIPTION
				"Receive optical  over alarm report when the receive optical over the threshold
				
				-4000~820"
			::= { onuPonOpticalThreshEntry 3 }

				-- 1.3.6.1.4.1.5875.800.3.51.1.1.4
		recOptOverClear OBJECT-TYPE
			SYNTAX Integer32
			MAX-ACCESS read-only
			STATUS current
			DESCRIPTION
				"Receive optical Over alarm disappear when the receive optical lower  the threshold
				-4000~820"
			::= { onuPonOpticalThreshEntry 4 }

				-- 1.3.6.1.4.1.5875.800.3.51.1.1.5
		recOptLowReport OBJECT-TYPE
			SYNTAX Integer32
			MAX-ACCESS read-only
			STATUS current
			DESCRIPTION
				"Receive optical low alarm report when the receive optical lower  the threshold
				-4000~820"
			::= { onuPonOpticalThreshEntry 5 }

				-- 1.3.6.1.4.1.5875.800.3.51.1.1.6
		recOptLowClear OBJECT-TYPE
			SYNTAX Integer32
			MAX-ACCESS read-only
			STATUS current
			DESCRIPTION
				"Receive optical low alarm clear when the receive optical over the threshold
				-4000~820"
			::= { onuPonOpticalThreshEntry 6 }

				-- 1.3.6.1.4.1.5875.800.3.51.1.1.7
		sendOptOverReport OBJECT-TYPE
			SYNTAX Integer32
			MAX-ACCESS read-only
			STATUS current
			DESCRIPTION
				"Send optical over alarm report when the send optical over the threshold
				
				-4000~820"
			::= { onuPonOpticalThreshEntry 7 }

				-- 1.3.6.1.4.1.5875.800.3.51.1.1.8
		sendOptiOverClear OBJECT-TYPE
			SYNTAX Integer32
			MAX-ACCESS read-only
			STATUS current
			DESCRIPTION
				"Send optical over alarm disappear when the send optical low the threshold
				
				-4000~820"
			::= { onuPonOpticalThreshEntry 8 }

				-- 1.3.6.1.4.1.5875.800.3.51.1.1.9
		sendOptLowReport OBJECT-TYPE
			SYNTAX Integer32
			MAX-ACCESS read-only
			STATUS current
			DESCRIPTION
				"Send optical low alarm report when the send optical lower the threshold
				
				-4000~820"
			::= { onuPonOpticalThreshEntry 9 }

				-- 1.3.6.1.4.1.5875.800.3.51.1.1.10
		sendOptLowClear OBJECT-TYPE
			SYNTAX Integer32
			MAX-ACCESS read-only
			STATUS current
			DESCRIPTION
				"Send optical low alarm disappear when the send optical over the threshold
				
				-4000~820"
			::= { onuPonOpticalThreshEntry 10 }

				-- 1.3.6.1.4.1.5875.800.3.51.2
		attachOptTable OBJECT-TYPE
			SYNTAX SEQUENCE OF AttachOptEntry
			MAX-ACCESS not-accessible
			STATUS current
			DESCRIPTION
				"Description"
			::= { ponOpticalThresh 2 }

				-- 1.3.6.1.4.1.5875.800.3.51.2.1
		attachOptEntry OBJECT-TYPE
			SYNTAX AttachOptEntry
			MAX-ACCESS not-accessible
			STATUS current
			DESCRIPTION
				"Row Description"
			INDEX { onuIndex }
			::= { attachOptTable 1 }

		
		AttachOptEntry ::=
			SEQUENCE { 
				attachOptProfileId
					Integer32,
				attachOptProfileName
					OCTET STRING,
				unattachOptiProfile
					INTEGER
			 }
		-- 1.3.6.1.4.1.5875.800.3.51.2.1.2
		attachOptProfileId OBJECT-TYPE
			SYNTAX Integer32 (0..1024)
			MAX-ACCESS read-create
			STATUS current
			DESCRIPTION
				"ONU attach the optical profile througth the ID
				0xffff means have not bind"
			::= { attachOptEntry 2 }

				-- 1.3.6.1.4.1.5875.800.3.51.2.1.3
		attachOptProfileName OBJECT-TYPE
			SYNTAX OCTET STRING
			MAX-ACCESS read-create
			STATUS current
			DESCRIPTION
				"ONU attach the optical profile througth the name
				
				0:bind OK, 
				< 0 :error"
			::= { attachOptEntry 3 }

				-- 1.3.6.1.4.1.5875.800.3.51.2.1.4
		unattachOptiProfile OBJECT-TYPE
			SYNTAX INTEGER { unattach(0) }
			MAX-ACCESS read-create
			STATUS current
			DESCRIPTION
				"unattach the optical profile
				0:unbind"
			::= { attachOptEntry 4 }

				-- 1.3.6.1.4.1.5875.800.3.51.3
		oltOpticalThresh OBJECT IDENTIFIER ::= { ponOpticalThresh 3 }

				-- 1.3.6.1.4.1.5875.800.3.51.3.1
		oltOptRecMaxthresh OBJECT-TYPE
			SYNTAX Integer32 (0..1024)
			MAX-ACCESS read-write
			STATUS current
			DESCRIPTION
				"olt optical receive max thresh
				-3200~-100"
			::= { oltOpticalThresh 1 }

				-- 1.3.6.1.4.1.5875.800.3.51.3.2
		oltOptRecMinthresh OBJECT-TYPE
			SYNTAX Integer32 (0..1024)
			MAX-ACCESS read-write
			STATUS current
			DESCRIPTION
				"olt optical receive mix thresh
				-3200~-100"
			::= { oltOpticalThresh 2 }

				-- 1.3.6.1.4.1.5875.800.3.51.3.3
		oltOptSendMaxthresh OBJECT-TYPE
			SYNTAX Integer32 (0..1024)
			MAX-ACCESS read-write
			STATUS current
			DESCRIPTION
				"olt optical send max thresh
				-400 ~1000"
			::= { oltOpticalThresh 3 }

				-- 1.3.6.1.4.1.5875.800.3.51.3.4
		oltOptSendMixthresh OBJECT-TYPE
			SYNTAX Integer32 (0..1024)
			MAX-ACCESS read-write
			STATUS current
			DESCRIPTION
				"olt optical send min thresh
				-400 ~1000"
			::= { oltOpticalThresh 4 }

				-- 1.3.6.1.4.1.5875.800.3.52
		wanService OBJECT IDENTIFIER ::= { oltData 52 }

				-- 1.3.6.1.4.1.5875.800.3.52.1
		wanServiceTable OBJECT-TYPE
			SYNTAX SEQUENCE OF WanServiceEntry
			MAX-ACCESS not-accessible
			STATUS current
			DESCRIPTION
				"Description"
			::= { wanService 1 }

				-- 1.3.6.1.4.1.5875.800.3.52.1.1
		wanServiceEntry OBJECT-TYPE
			SYNTAX WanServiceEntry
			MAX-ACCESS not-accessible
			STATUS current
			DESCRIPTION
				"Row Description"
			INDEX { onuIndex, wanIndex }
			::= { wanServiceTable 1 }

		
		WanServiceEntry ::=
			SEQUENCE { 
				wanIndex
					Integer32,
				wanMode
					Integer32,
				wanConnType
					Integer32,
				wanVlanId
					Integer32,
				wanVlanCos
					Integer32,
				wanNatEnable
					Integer32,
				wanDsp
					Integer32,
				wanIpAddress
					IpAddress,
				wanIPSubnet
					IpAddress,
				wanIpMask
					IpAddress,
				wanMasterDns
					IpAddress,
				wanSlaveDns
					IpAddress,
				wanPPPoeProxy
					Integer32,
				wanPPPoeUsername
					OCTET STRING,
				wanPPPoePassword
					OCTET STRING,
				wanPPPoeServer
					OCTET STRING,
				wanPPPoeMode
					Integer32,
				wanQosEnable
					Integer32,
				wanVlanMode
					Integer32,
				wantranslationstate
					Integer32,
				wanTranVlanID
					Integer32,
				wanTranCos
					Integer32,
				wanQinqState
					Integer32,
				wanTPID
					Integer32,
				wanSvlanID
					Integer32,
				wanSvlanCos
					Integer32,
				wanDhcpRemoteID
					OCTET STRING,
				wanbindport
					Integer32,
				wanServiceActiveFlag
					Integer32,
				wanServiceAction
					Integer32
			 }
		-- 1.3.6.1.4.1.5875.800.3.52.1.1.1
		wanIndex OBJECT-TYPE
			SYNTAX Integer32 (1..1024)
			MAX-ACCESS not-accessible
			STATUS current
			DESCRIPTION
				"Column Description"
			::= { wanServiceEntry 1 }

				-- 1.3.6.1.4.1.5875.800.3.52.1.1.2
		wanMode OBJECT-TYPE
			SYNTAX Integer32
			MAX-ACCESS read-create
			STATUS current
			DESCRIPTION
				"WAN LINK MODE
				0: TR069
				1: INTERNET
				2: TR069_INTERNET
				3: multicast
				4: VOIP
				5: VOIP_INTERNET
				
				100??Other"
			::= { wanServiceEntry 2 }

				-- 1.3.6.1.4.1.5875.800.3.52.1.1.3
		wanConnType OBJECT-TYPE
			SYNTAX Integer32
			MAX-ACCESS read-create
			STATUS current
			DESCRIPTION
				"WAN LINK TYPE
				0:bridge
				1:route"
			::= { wanServiceEntry 3 }

				-- 1.3.6.1.4.1.5875.800.3.52.1.1.4
		wanVlanId OBJECT-TYPE
			SYNTAX Integer32 (0..1024)
			MAX-ACCESS read-create
			STATUS current
			DESCRIPTION
				"VLAN ID
				1-4085,0xffff(null)"
			::= { wanServiceEntry 4 }

				-- 1.3.6.1.4.1.5875.800.3.52.1.1.5
		wanVlanCos OBJECT-TYPE
			SYNTAX Integer32
			MAX-ACCESS read-create
			STATUS current
			DESCRIPTION
				"Description
				0??7,0xffff(null)"
			::= { wanServiceEntry 5 }

				-- 1.3.6.1.4.1.5875.800.3.52.1.1.6
		wanNatEnable OBJECT-TYPE
			SYNTAX Integer32
			MAX-ACCESS read-create
			STATUS current
			DESCRIPTION
				"NAT
				0:disable
				1:enable"
			::= { wanServiceEntry 6 }

				-- 1.3.6.1.4.1.5875.800.3.52.1.1.7
		wanDsp OBJECT-TYPE
			SYNTAX Integer32
			MAX-ACCESS read-create
			STATUS current
			DESCRIPTION
				"DSP
				0:DHCP
				1:Static
				2:PPPOE
				0xffff:null"
			::= { wanServiceEntry 7 }

				-- 1.3.6.1.4.1.5875.800.3.52.1.1.8
		wanIpAddress OBJECT-TYPE
			SYNTAX IpAddress
			MAX-ACCESS read-create
			STATUS current
			DESCRIPTION
				"STATIC IP
				0x0-0xFFFFFFFF"
			::= { wanServiceEntry 8 }

				-- 1.3.6.1.4.1.5875.800.3.52.1.1.9
		wanIPSubnet OBJECT-TYPE
			SYNTAX IpAddress
			MAX-ACCESS read-create
			STATUS current
			DESCRIPTION
				"IP SUBNET
				0x0-0xFFFFFFFF"
			::= { wanServiceEntry 9 }

				-- 1.3.6.1.4.1.5875.800.3.52.1.1.10
		wanIpMask OBJECT-TYPE
			SYNTAX IpAddress
			MAX-ACCESS read-create
			STATUS current
			DESCRIPTION
				"IP MASK
				0x0-0xFFFFFFFF"
			::= { wanServiceEntry 10 }

				-- 1.3.6.1.4.1.5875.800.3.52.1.1.11
		wanMasterDns OBJECT-TYPE
			SYNTAX IpAddress
			MAX-ACCESS read-create
			STATUS current
			DESCRIPTION
				"MASTER DNS
				0x0-0xFFFFFFFF"
			::= { wanServiceEntry 11 }

				-- 1.3.6.1.4.1.5875.800.3.52.1.1.12
		wanSlaveDns OBJECT-TYPE
			SYNTAX IpAddress
			MAX-ACCESS read-create
			STATUS current
			DESCRIPTION
				"SLAVE DNS
				0x0-0xFFFFFFFF"
			::= { wanServiceEntry 12 }

				-- 1.3.6.1.4.1.5875.800.3.52.1.1.13
		wanPPPoeProxy OBJECT-TYPE
			SYNTAX Integer32
			MAX-ACCESS read-create
			STATUS current
			DESCRIPTION
				"PPPoe Proxy
				0:disable
				1:enable"
			::= { wanServiceEntry 13 }

				-- 1.3.6.1.4.1.5875.800.3.52.1.1.14
		wanPPPoeUsername OBJECT-TYPE
			SYNTAX OCTET STRING
			MAX-ACCESS read-create
			STATUS current
			DESCRIPTION
				"PPPoe UserName
				0-32 byte"
			::= { wanServiceEntry 14 }

				-- 1.3.6.1.4.1.5875.800.3.52.1.1.15
		wanPPPoePassword OBJECT-TYPE
			SYNTAX OCTET STRING
			MAX-ACCESS read-create
			STATUS current
			DESCRIPTION
				"PPPoe Password
				0-32 byte"
			::= { wanServiceEntry 15 }

				-- 1.3.6.1.4.1.5875.800.3.52.1.1.16
		wanPPPoeServer OBJECT-TYPE
			SYNTAX OCTET STRING
			MAX-ACCESS read-create
			STATUS current
			DESCRIPTION
				"PPPoe Server
				0-32 byte"
			::= { wanServiceEntry 16 }

				-- 1.3.6.1.4.1.5875.800.3.52.1.1.17
		wanPPPoeMode OBJECT-TYPE
			SYNTAX Integer32
			MAX-ACCESS read-create
			STATUS current
			DESCRIPTION
				"PPPoe Mode
				0:Auto connect
				1:connect when have payload"
			::= { wanServiceEntry 17 }

				-- 1.3.6.1.4.1.5875.800.3.52.1.1.18
		wanQosEnable OBJECT-TYPE
			SYNTAX Integer32 (0..1024)
			MAX-ACCESS read-create
			STATUS current
			DESCRIPTION
				"Qos Enable
				0:disable
				1:enable"
			::= { wanServiceEntry 18 }

				-- 1.3.6.1.4.1.5875.800.3.52.1.1.19
		wanVlanMode OBJECT-TYPE
			SYNTAX Integer32
			MAX-ACCESS read-create
			STATUS current
			DESCRIPTION
				"Vlan Mode
				1:tag
				3:transparent"
			::= { wanServiceEntry 19 }

				-- 1.3.6.1.4.1.5875.800.3.52.1.1.20
		wantranslationstate OBJECT-TYPE
			SYNTAX Integer32
			MAX-ACCESS read-create
			STATUS current
			DESCRIPTION
				"Translation State
				0:disable
				1:enable"
			::= { wanServiceEntry 20 }

				-- 1.3.6.1.4.1.5875.800.3.52.1.1.21
		wanTranVlanID OBJECT-TYPE
			SYNTAX Integer32
			MAX-ACCESS read-create
			STATUS current
			DESCRIPTION
				"Tran VlanID
				1-4085,0xffff(null)"
			::= { wanServiceEntry 21 }

				-- 1.3.6.1.4.1.5875.800.3.52.1.1.22
		wanTranCos OBJECT-TYPE
			SYNTAX Integer32
			MAX-ACCESS read-create
			STATUS current
			DESCRIPTION
				"Tran Cos
				0??7,0xffff(null)"
			::= { wanServiceEntry 22 }

				-- 1.3.6.1.4.1.5875.800.3.52.1.1.23
		wanQinqState OBJECT-TYPE
			SYNTAX Integer32
			MAX-ACCESS read-create
			STATUS current
			DESCRIPTION
				"Qinq State
				0:disable
				1:enable"
			::= { wanServiceEntry 23 }

				-- 1.3.6.1.4.1.5875.800.3.52.1.1.24
		wanTPID OBJECT-TYPE
			SYNTAX Integer32
			MAX-ACCESS read-create
			STATUS current
			DESCRIPTION
				"TP ID
				
				suggest: 0x81000-0xfffe"
			::= { wanServiceEntry 24 }

				-- 1.3.6.1.4.1.5875.800.3.52.1.1.25
		wanSvlanID OBJECT-TYPE
			SYNTAX Integer32
			MAX-ACCESS read-create
			STATUS current
			DESCRIPTION
				"Svlan ID
				1-4085,0xffff(null)"
			::= { wanServiceEntry 25 }

				-- 1.3.6.1.4.1.5875.800.3.52.1.1.26
		wanSvlanCos OBJECT-TYPE
			SYNTAX Integer32
			MAX-ACCESS read-create
			STATUS current
			DESCRIPTION
				"Svlan Cos
				0??7,0xffff(null)"
			::= { wanServiceEntry 26 }

				-- 1.3.6.1.4.1.5875.800.3.52.1.1.27
		wanDhcpRemoteID OBJECT-TYPE
			SYNTAX OCTET STRING
			MAX-ACCESS read-create
			STATUS current
			DESCRIPTION
				"DHCP Remote ID
				The max length of the string is 10"
			::= { wanServiceEntry 27 }

				-- 1.3.6.1.4.1.5875.800.3.52.1.1.28
		wanbindport OBJECT-TYPE
			SYNTAX Integer32
			MAX-ACCESS read-create
			STATUS current
			DESCRIPTION
				"Bind port
				Bit0~bit3:lan1~lan4
				Bit4~bit7:SD1~SD4"
			::= { wanServiceEntry 28 }

				-- 1.3.6.1.4.1.5875.800.3.52.1.1.29
		wanServiceActiveFlag OBJECT-TYPE
			SYNTAX Integer32 (0..1)
			MAX-ACCESS read-create
			STATUS current
			DESCRIPTION
				"Active Flag
				0-activation
				1-deactivation"
			::= { wanServiceEntry 29 }

				-- 1.3.6.1.4.1.5875.800.3.52.1.1.40
		wanServiceAction OBJECT-TYPE
			SYNTAX Integer32 (0..1024)
			MAX-ACCESS read-create
			STATUS current
			DESCRIPTION
				"Action
				4-create
				6-delete
				7-modify"
			::= { wanServiceEntry 40 }

				-- 1.3.6.1.4.1.5875.800.3.52.2
		applywanserviceTable OBJECT-TYPE
			SYNTAX SEQUENCE OF ApplywanserviceEntry
			MAX-ACCESS not-accessible
			STATUS current
			DESCRIPTION
				"Description"
			::= { wanService 2 }

				-- 1.3.6.1.4.1.5875.800.3.52.2.1
		applywanserviceEntry OBJECT-TYPE
			SYNTAX ApplywanserviceEntry
			MAX-ACCESS not-accessible
			STATUS current
			DESCRIPTION
				"Row Description"
			INDEX { onuIndex }
			::= { applywanserviceTable 1 }

		
		ApplywanserviceEntry ::=
			SEQUENCE { 
				getNextwanIndex
					Integer32,
				applyWanAction
					Integer32
			 }
		-- 1.3.6.1.4.1.5875.800.3.52.2.1.1
		getNextwanIndex OBJECT-TYPE
			SYNTAX Integer32 (0..1024)
			MAX-ACCESS read-only
			STATUS current
			DESCRIPTION
				"Description"
			::= { applywanserviceEntry 1 }

				-- 1.3.6.1.4.1.5875.800.3.52.2.1.2
		applyWanAction OBJECT-TYPE
			SYNTAX Integer32 (0..1024)
			MAX-ACCESS read-create
			STATUS current
			DESCRIPTION
				"Column Description"
			::= { applywanserviceEntry 2 }

				-- 1.3.6.1.4.1.5875.800.3.53
		gponServiceBandwith OBJECT IDENTIFIER ::= { oltData 53 }

				-- 1.3.6.1.4.1.5875.800.3.53.1
		gponServiceBandwithTable OBJECT-TYPE
			SYNTAX SEQUENCE OF gponServiceBandwithEntry
			MAX-ACCESS not-accessible
			STATUS current
			DESCRIPTION
				"gpon service bandwith"
			::= { gponServiceBandwith 1 }

				-- 1.3.6.1.4.1.5875.800.3.53.1.1
		gponServiceBandwithEntry OBJECT-TYPE
			SYNTAX gponServiceBandwithEntry
			MAX-ACCESS not-accessible
			STATUS current
			DESCRIPTION
				"Row Description"
			INDEX { gponSerBwProIndex }
			::= { gponServiceBandwithTable 1 }

		
		gponServiceBandwithEntry ::=
			SEQUENCE { 
				gponSerBwProIndex
					Integer32,
				gponSerBwProName
					OCTET STRING,
				gponSerBwProAction
					Integer32
			 }
		-- 1.3.6.1.4.1.5875.800.3.53.1.1.1
		gponSerBwProIndex OBJECT-TYPE
			SYNTAX Integer32 (0..1024)
			MAX-ACCESS not-accessible
			STATUS current
			DESCRIPTION
				"Profile ID (Index) "
			::= { gponServiceBandwithEntry 1 }

				-- 1.3.6.1.4.1.5875.800.3.53.1.1.2
		gponSerBwProName OBJECT-TYPE
			SYNTAX OCTET STRING
			MAX-ACCESS read-create
			STATUS current
			DESCRIPTION
				"32 bytes"
			::= { gponServiceBandwithEntry 2 }

				-- 1.3.6.1.4.1.5875.800.3.53.1.1.8
		gponSerBwProAction OBJECT-TYPE
			SYNTAX Integer32
			MAX-ACCESS read-create
			STATUS current
			DESCRIPTION
				"4. Set
				6: delete
				"
			::= { gponServiceBandwithEntry 8 }

				-- 1.3.6.1.4.1.5875.800.3.53.2
		getNextGponSerBwId OBJECT-TYPE
			SYNTAX Integer32 (0..1024)
			MAX-ACCESS read-only
			STATUS current
			DESCRIPTION
				" Leaf node"
			::= { gponServiceBandwith 2 }

				-- 1.3.6.1.4.1.5875.800.3.53.3
		gponServiceBwProfileTable OBJECT-TYPE
			SYNTAX SEQUENCE OF gponServiceBwProfileEntry
			MAX-ACCESS not-accessible
			STATUS current
			DESCRIPTION
				"gpon service bandwith"
			::= { gponServiceBandwith 3 }

				-- 1.3.6.1.4.1.5875.800.3.53.3.1
		gponServiceBwProfileEntry OBJECT-TYPE
			SYNTAX gponServiceBwProfileEntry
			MAX-ACCESS not-accessible
			STATUS current
			DESCRIPTION
				"Row Description"
			INDEX { gponSerBwProIndex, gponSerBwTypeIndex }
			::= { gponServiceBwProfileTable 1 }

		
		gponServiceBwProfileEntry ::=
			SEQUENCE { 
				gponSerBwTypeIndex
					Integer32,
				fixBw
					Integer32,
				assureBw
					Integer32,
				maxBw
					Integer32,
				gponSerBwTypeAction
					Integer32
			 }
		-- 1.3.6.1.4.1.5875.800.3.53.3.1.2
		gponSerBwTypeIndex OBJECT-TYPE
			SYNTAX Integer32 (1..65535)
			MAX-ACCESS not-accessible
			STATUS current
			DESCRIPTION
				"1:IPTV 
				2: data
				3: Voice
				4:TDM
				5??Integrated Service
				6?? data2
				7?? data3
				8?? data4
				9?? COM service
				14:Manage service
				Description??
				unique??non-repeatable 
				"
			::= { gponServiceBwProfileEntry 2 }

				-- 1.3.6.1.4.1.5875.800.3.53.3.1.3
		fixBw OBJECT-TYPE
			SYNTAX Integer32
			MAX-ACCESS read-create
			STATUS current
			DESCRIPTION
				"Unit??Kbit/s
				Range??
				128~ 1024000Kbit/s
				Parameter must be the integral multiples of 8, not divided rounding
				"
			::= { gponServiceBwProfileEntry 3 }

				-- 1.3.6.1.4.1.5875.800.3.53.3.1.4
		assureBw OBJECT-TYPE
			SYNTAX Integer32
			MAX-ACCESS read-create
			STATUS current
			DESCRIPTION
				"Unit??Kbit/s
				Range??
				0??256??1024000 Kbit/s
				Parameter must be the integral multiples of 8, not divided rounding
				"
			::= { gponServiceBwProfileEntry 4 }

				-- 1.3.6.1.4.1.5875.800.3.53.3.1.5
		maxBw OBJECT-TYPE
			SYNTAX Integer32
			MAX-ACCESS read-create
			STATUS current
			DESCRIPTION
				"Unit??Kbit/s
				Range??
				
				128~ 1024000Kbit/s
				Parameter must be the integral multiples of 8, not divided rounding
				"
			::= { gponServiceBwProfileEntry 5 }

				-- 1.3.6.1.4.1.5875.800.3.53.3.1.20
		gponSerBwTypeAction OBJECT-TYPE
			SYNTAX Integer32
			MAX-ACCESS read-create
			STATUS current
			DESCRIPTION
				"4??Set 
				6: Delete
				"
			::= { gponServiceBwProfileEntry 20 }

				-- 1.3.6.1.4.1.5875.800.3.53.4
		attachgponSerBwTable OBJECT-TYPE
			SYNTAX SEQUENCE OF attachgponSerBwEntry
			MAX-ACCESS not-accessible
			STATUS current
			DESCRIPTION
				"Description"
			::= { gponServiceBandwith 4 }

				-- 1.3.6.1.4.1.5875.800.3.53.4.1
		attachgponSerBwEntry OBJECT-TYPE
			SYNTAX attachgponSerBwEntry
			MAX-ACCESS not-accessible
			STATUS current
			DESCRIPTION
				"Row Description"
			INDEX { onuIndex }
			::= { attachgponSerBwTable 1 }

		
		attachgponSerBwEntry ::=
			SEQUENCE { 
				attachgponBwProfileId
					Integer32,
				attachgponBwProfileName
					OCTET STRING,
				unattachgponBwProfile
					INTEGER
			 }
		-- 1.3.6.1.4.1.5875.800.3.53.4.1.2
		attachgponBwProfileId OBJECT-TYPE
			SYNTAX Integer32 (0..1024)
			MAX-ACCESS read-create
			STATUS current
			DESCRIPTION
				"Index"
			::= { attachgponSerBwEntry 2 }

				-- 1.3.6.1.4.1.5875.800.3.53.4.1.3
		attachgponBwProfileName OBJECT-TYPE
			SYNTAX OCTET STRING
			MAX-ACCESS read-create
			STATUS current
			DESCRIPTION
				"Profile Name Binding"
			::= { attachgponSerBwEntry 3 }

				-- 1.3.6.1.4.1.5875.800.3.53.4.1.4
		unattachgponBwProfile OBJECT-TYPE
			SYNTAX INTEGER { unattach(0) }
			MAX-ACCESS read-create
			STATUS current
			DESCRIPTION
				"0: unbind"
			::= { attachgponSerBwEntry 4 }

				-- 1.3.6.1.4.1.5875.800.3.54
		mibPerformExtern OBJECT IDENTIFIER ::= { oltData 54 }

				-- 1.3.6.1.4.1.5875.800.3.54.1
		mibPerformExternTable OBJECT-TYPE
			SYNTAX SEQUENCE OF mibPerformExternEntry
			MAX-ACCESS not-accessible
			STATUS current
			DESCRIPTION
				"Description"
			::= { mibPerformExtern 1 }

				-- 1.3.6.1.4.1.5875.800.3.54.1.1
		mibPerformExternEntry OBJECT-TYPE
			SYNTAX mibPerformExternEntry
			MAX-ACCESS not-accessible
			STATUS current
			DESCRIPTION
				"Row Description"
			INDEX { onuIndex }
			::= { mibPerformExternTable 1 }

		
		mibPerformExternEntry ::=
			SEQUENCE { 
				mibInflowsBIP
					Integer32,
				mibOutflowsBIP
					Integer32
			 }
		-- 1.3.6.1.4.1.5875.800.3.54.1.1.2
		mibInflowsBIP OBJECT-TYPE
			SYNTAX Integer32 (0..1024)
			MAX-ACCESS read-only
			STATUS current
			DESCRIPTION
				"Port Traffic Collection Extending Part
				Inflows BIP8"
			::= { mibPerformExternEntry 2 }

				-- 1.3.6.1.4.1.5875.800.3.54.1.1.3
		mibOutflowsBIP OBJECT-TYPE
			SYNTAX Integer32 (0..1024)
			MAX-ACCESS read-only
			STATUS current
			DESCRIPTION
				"Port Traffic Collection Extending Part
				Outflows BIP8"
			::= { mibPerformExternEntry 3 }

				-- 1.3.6.1.4.1.5875.800.3.54.2
		mibPerformExternTableNextScalar OBJECT-TYPE
			SYNTAX Integer32 (0..1024)
			MAX-ACCESS read-only
			STATUS current
			DESCRIPTION
				"Description"
			::= { mibPerformExtern 2 }

		
--                          the Interfaces table
-- The Interfaces table contains information on the entity's
-- interfaces.  Each interface is thought of as being
-- attached to a `subnetwork'.  Note that this term should
-- not be confused with `subnet' which refers to an
-- addressing partitioning scheme used in the Internet suite
-- of protocols.
		-- 1.3.6.1.4.1.5875.800.3.54.3
		onuPonMibPerformTable OBJECT-TYPE
			SYNTAX SEQUENCE OF OnuPonMibPerformEntry
			MAX-ACCESS not-accessible
			STATUS current
			DESCRIPTION
				"A list of interface entries.  The number of
				entries is given by the value of ifNumber."
			::= { mibPerformExtern 3 }

				-- 1.3.6.1.4.1.5875.800.3.54.3.1
		onuPonMibPerformEntry OBJECT-TYPE
			SYNTAX OnuPonMibPerformEntry
			MAX-ACCESS not-accessible
			STATUS current
			DESCRIPTION
				"An interface entry containing objects at the
				subnetwork layer and below for a particular
				interface."
			INDEX { onuIndex }
			::= { onuPonMibPerformTable 1 }

		
		OnuPonMibPerformEntry ::=
			SEQUENCE { 
				ifDescr
					DisplayString,
				ifType
					INTEGER,
				ifMtu
					INTEGER,
				ifSpeed
					INTEGER,
				ifPhysAddress
					PhysAddress,
				ifAdminStatus
					INTEGER,
				ifOperStatus
					INTEGER,
				ifLastChange
					TimeTicks,
				ifInOctets
					INTEGER,
				ifInUcastPkts
					INTEGER,
				ifInNUcastPkts
					INTEGER,
				ifInDiscards
					INTEGER,
				ifInErrors
					INTEGER,
				ifInUnknownProtos
					INTEGER,
				ifOutOctets
					INTEGER,
				ifOutUcastPkts
					INTEGER,
				ifOutNUcastPkts
					INTEGER,
				ifOutDiscards
					INTEGER,
				ifOutErrors
					INTEGER,
				inflowsBIP
					Integer32,
				outflowsBIP
					Integer32,
				ifOutMulticastPkts
					Counter32,
				ifInBroadcastPkts
					Counter32,
				ifInMulticastPkts
					Counter32,
				ifOutBroadcastPkts
					Counter32,
				ifHCInOctets
					Counter64,
				ifHCInUcastPkts
					Counter64,
				ifHCInMulticastPkts
					Counter64,
				ifHCInBroadcastPkts
					Counter64,
				ifHCOutOctets
					Counter64,
				ifHCOutUcastPkts
					Counter64,
				ifHCOutMulticastPkts
					Counter64,
				ifHCOutBroadcastPkts
					Counter64,
				ifLinkUpDownTrapEnable
					INTEGER,
				ifHighSpeed
					Gauge32,
				ifPromiscuousMode
					TruthValue,
				ifConnectorPresent
					TruthValue,
				ifAlias
					DisplayString,
				ifCounterDiscontinuityTime
					TimeStamp,
				ferfRecvGoodPackageOctets
					Counter64,
				ferfRecvDiscardedPackageOctets
					Counter64,
				ferfRecvErrorPackageOctets
					Counter64,
				ferfSendGoodPackageOctets
					Counter64,
				ferfSendDiscardedPackageOctets
					Counter64,
				ferfSendErrorPackageOctets
					Counter64,
				ferfRecv64OctetsLenPkts
					Counter64,
				ferfRecv65to127OctetsLenPkts
					Counter64,
				ferfRecv128to255OctetsLenPkts
					Counter64,
				ferfRecv256to511OctetsLenPkts
					Counter64,
				ferfRecv512to1023OctetsLenPkts
					Counter64,
				ferfRecv1024to1518OctetsLenPkts
					Counter64,
				ferfLossSignalSeconds
					Counter64,
				ferfErroredSeconds
					Counter64,
				ferfSeverelyErroredSeconds
					Counter64,
				ferfUnavailableSeconds
					Counter64,
				ferfDetectMonitorDiscardPacketNumber
					Counter64,
				ferfRecvPauseFlowControlFrames
					Counter64,
				ferfSendPauseFlowControlFrames
					Counter64,
				ferfChecksumErrors
					Counter64,
				ferfFcsFrameCheckErrors
					INTEGER,
				ferfExcessiveCollisionStatistics
					Counter64,
				ferfSingleCollisionSendOkFrames
					Counter64,
				ferfMultipleCollisionsSendOkFrames
					Counter64,
				ferfPortInFlow
					Counter64,
				ferfPortOnuFlow
					Counter64,
				lineCodeError
					Counter64
			 }
		-- 1.3.6.1.4.1.5875.800.3.54.3.1.2
		ifDescr OBJECT-TYPE
			SYNTAX DisplayString (SIZE (0..255))
			MAX-ACCESS read-only
			STATUS current
			DESCRIPTION
				"A textual string containing information about the
				interface.  This string should include the name of
				the manufacturer, the product name and the version
				of the hardware interface."
			::= { onuPonMibPerformEntry 2 }

		
--                          none of the following
-- T1
-- european equiv. of T1
-- proprietary serial
-- CLNP over IP [11]
-- XNS over IP
-- generic SLIP
-- ULTRA technologies
-- T3
-- SMDS
		-- 1.3.6.1.4.1.5875.800.3.54.3.1.3
		ifType OBJECT-TYPE
			SYNTAX INTEGER
				{
				other(1),
				regular1822(2),
				hdh1822(3),
				ddn-x25(4),
				rfc877-x25(5),
				ethernet-csmacd(6),
				iso88023-csmacd(7),
				iso88024-tokenBus(8),
				iso88025-tokenRing(9),
				iso88026-man(10),
				starLan(11),
				proteon-10Mbit(12),
				proteon-80Mbit(13),
				hyperchannel(14),
				fddi(15),
				lapb(16),
				sdlc(17),
				ds1(18),
				e1(19),
				basicISDN(20),
				primaryISDN(21),
				propPointToPointSerial(22),
				ppp(23),
				softwareLoopback(24),
				eon(25),
				ethernet-3Mbit(26),
				nsip(27),
				slip(28),
				ultra(29),
				ds3(30),
				sip(31),
				frame-relay(32)
				}
			MAX-ACCESS read-only
			STATUS current
			DESCRIPTION
				"The type of interface, distinguished according to
				the physical/link protocol(s) immediately `below'
				the network layer in the protocol stack."
			::= { onuPonMibPerformEntry 3 }

				-- 1.3.6.1.4.1.5875.800.3.54.3.1.4
		ifMtu OBJECT-TYPE
			SYNTAX INTEGER
			MAX-ACCESS read-only
			STATUS current
			DESCRIPTION
				"The size of the largest datagram which can be
				sent/received on the interface, specified in
				octets.  For interfaces that are used for
				transmitting network datagrams, this is the size
				of the largest network datagram that can be sent
				on the interface."
			::= { onuPonMibPerformEntry 4 }

				-- 1.3.6.1.4.1.5875.800.3.54.3.1.5
		ifSpeed OBJECT-TYPE
			SYNTAX INTEGER
			MAX-ACCESS read-only
			STATUS current
			DESCRIPTION
				"An estimate of the interface's current bandwidth
				in bits per second.  For interfaces which do not
				vary in bandwidth or for those where no accurate
				estimation can be made, this object should contain
				the nominal bandwidth."
			::= { onuPonMibPerformEntry 5 }

				-- 1.3.6.1.4.1.5875.800.3.54.3.1.6
		ifPhysAddress OBJECT-TYPE
			SYNTAX PhysAddress
			MAX-ACCESS read-only
			STATUS current
			DESCRIPTION
				"The interface's address at the protocol layer
				immediately `below' the network layer in the
				protocol stack.  For interfaces which do not have
				such an address (e.g., a serial line), this object
				should contain an octet string of zero length."
			::= { onuPonMibPerformEntry 6 }

		
--                          ready to pass packets
-- in some test mode
		-- 1.3.6.1.4.1.5875.800.3.54.3.1.7
		ifAdminStatus OBJECT-TYPE
			SYNTAX INTEGER
				{
				up(1),
				down(2),
				testing(3)
				}
			MAX-ACCESS read-write
			STATUS current
			DESCRIPTION
				"The desired state of the interface.  The
				testing(3) state indicates that no operational
				packets can be passed."
			::= { onuPonMibPerformEntry 7 }

		
--                          ready to pass packets
-- in some test mode
		-- 1.3.6.1.4.1.5875.800.3.54.3.1.8
		ifOperStatus OBJECT-TYPE
			SYNTAX INTEGER
				{
				up(1),
				down(2),
				testing(3)
				}
			MAX-ACCESS read-only
			STATUS current
			DESCRIPTION
				"The current operational state of the interface.
				The testing(3) state indicates that no operational
				packets can be passed."
			::= { onuPonMibPerformEntry 8 }

				-- 1.3.6.1.4.1.5875.800.3.54.3.1.9
		ifLastChange OBJECT-TYPE
			SYNTAX TimeTicks
			MAX-ACCESS read-only
			STATUS current
			DESCRIPTION
				"The value of sysUpTime at the time the interface
				entered its current operational state.  If the
				current state was entered prior to the last re-
				initialization of the local network management
				subsystem, then this object contains a zero
				value."
			::= { onuPonMibPerformEntry 9 }

				-- 1.3.6.1.4.1.5875.800.3.54.3.1.10
		ifInOctets OBJECT-TYPE
			SYNTAX INTEGER
			MAX-ACCESS read-only
			STATUS current
			DESCRIPTION
				"The total number of octets received on the
				interface, including framing characters."
			::= { onuPonMibPerformEntry 10 }

				-- 1.3.6.1.4.1.5875.800.3.54.3.1.11
		ifInUcastPkts OBJECT-TYPE
			SYNTAX INTEGER
			MAX-ACCESS read-only
			STATUS current
			DESCRIPTION
				"The number of subnetwork-unicast packets
				delivered to a higher-layer protocol."
			::= { onuPonMibPerformEntry 11 }

				-- 1.3.6.1.4.1.5875.800.3.54.3.1.12
		ifInNUcastPkts OBJECT-TYPE
			SYNTAX INTEGER
			MAX-ACCESS read-only
			STATUS current
			DESCRIPTION
				"The number of non-unicast (i.e., subnetwork-
				broadcast or subnetwork-multicast) packets
				delivered to a higher-layer protocol."
			::= { onuPonMibPerformEntry 12 }

				-- 1.3.6.1.4.1.5875.800.3.54.3.1.13
		ifInDiscards OBJECT-TYPE
			SYNTAX INTEGER
			MAX-ACCESS read-only
			STATUS current
			DESCRIPTION
				"The number of inbound packets which were chosen
				to be discarded even though no errors had been
				detected to prevent their being deliverable to a
				higher-layer protocol.  One possible reason for
				discarding such a packet could be to free up
				buffer space."
			::= { onuPonMibPerformEntry 13 }

				-- 1.3.6.1.4.1.5875.800.3.54.3.1.14
		ifInErrors OBJECT-TYPE
			SYNTAX INTEGER
			MAX-ACCESS read-only
			STATUS current
			DESCRIPTION
				"The number of inbound packets that contained
				errors preventing them from being deliverable to a
				higher-layer protocol."
			::= { onuPonMibPerformEntry 14 }

				-- 1.3.6.1.4.1.5875.800.3.54.3.1.15
		ifInUnknownProtos OBJECT-TYPE
			SYNTAX INTEGER
			MAX-ACCESS read-only
			STATUS current
			DESCRIPTION
				"The number of packets received via the interface
				which were discarded because of an unknown or
				unsupported protocol."
			::= { onuPonMibPerformEntry 15 }

				-- 1.3.6.1.4.1.5875.800.3.54.3.1.16
		ifOutOctets OBJECT-TYPE
			SYNTAX INTEGER
			MAX-ACCESS read-only
			STATUS current
			DESCRIPTION
				"The total number of octets transmitted out of the
				interface, including framing characters."
			::= { onuPonMibPerformEntry 16 }

				-- 1.3.6.1.4.1.5875.800.3.54.3.1.17
		ifOutUcastPkts OBJECT-TYPE
			SYNTAX INTEGER
			MAX-ACCESS read-only
			STATUS current
			DESCRIPTION
				"The total number of packets that higher-level
				protocols requested be transmitted to a
				subnetwork-unicast address, including those that
				were discarded or not sent."
			::= { onuPonMibPerformEntry 17 }

				-- 1.3.6.1.4.1.5875.800.3.54.3.1.18
		ifOutNUcastPkts OBJECT-TYPE
			SYNTAX INTEGER
			MAX-ACCESS read-only
			STATUS current
			DESCRIPTION
				"The total number of packets that higher-level
				protocols requested be transmitted to a non-
				unicast (i.e., a subnetwork-broadcast or
				subnetwork-multicast) address, including those
				that were discarded or not sent."
			::= { onuPonMibPerformEntry 18 }

				-- 1.3.6.1.4.1.5875.800.3.54.3.1.19
		ifOutDiscards OBJECT-TYPE
			SYNTAX INTEGER
			MAX-ACCESS read-only
			STATUS current
			DESCRIPTION
				"The number of outbound packets which were chosen
				to be discarded even though no errors had been
				detected to prevent their being transmitted.  One
				possible reason for discarding such a packet could
				be to free up buffer space."
			::= { onuPonMibPerformEntry 19 }

				-- 1.3.6.1.4.1.5875.800.3.54.3.1.20
		ifOutErrors OBJECT-TYPE
			SYNTAX INTEGER
			MAX-ACCESS read-only
			STATUS current
			DESCRIPTION
				"The number of outbound packets that could not be
				transmitted because of errors."
			::= { onuPonMibPerformEntry 20 }

				-- 1.3.6.1.4.1.5875.800.3.54.3.1.21
		inflowsBIP OBJECT-TYPE
			SYNTAX Integer32 (0..1024)
			MAX-ACCESS read-only
			STATUS current
			DESCRIPTION
				"Port Traffic Collection Extending Part"
			::= { onuPonMibPerformEntry 21 }

				-- 1.3.6.1.4.1.5875.800.3.54.3.1.22
		outflowsBIP OBJECT-TYPE
			SYNTAX Integer32 (0..1024)
			MAX-ACCESS read-only
			STATUS current
			DESCRIPTION
				"Port Traffic Collection Extending Part"
			::= { onuPonMibPerformEntry 22 }

				-- 1.3.6.1.4.1.5875.800.3.54.3.1.32
		ifOutMulticastPkts OBJECT-TYPE
			SYNTAX Counter32
			MAX-ACCESS read-only
			STATUS current
			DESCRIPTION
				"The total number of packets that higher-level protocols
				requested be transmitted, and which were addressed to a
				multicast address at this sub-layer, including those that
				were discarded or not sent.  For a MAC layer protocol, this
				includes both Group and Functional addresses.
				
				Discontinuities in the value of this counter can occur at
				re-initialization of the management system, and at other
				times as indicated by the value of
				ifCounterDiscontinuityTime."
			::= { onuPonMibPerformEntry 32 }

				-- 1.3.6.1.4.1.5875.800.3.54.3.1.33
		ifInBroadcastPkts OBJECT-TYPE
			SYNTAX Counter32
			MAX-ACCESS read-only
			STATUS current
			DESCRIPTION
				"The number of packets, delivered by this sub-layer to a
				higher (sub-)layer, which were addressed to a broadcast
				address at this sub-layer.
				
				Discontinuities in the value of this counter can occur at
				re-initialization of the management system, and at other
				times as indicated by the value of
				ifCounterDiscontinuityTime."
			::= { onuPonMibPerformEntry 33 }

				-- 1.3.6.1.4.1.5875.800.3.54.3.1.34
		ifInMulticastPkts OBJECT-TYPE
			SYNTAX Counter32
			MAX-ACCESS read-only
			STATUS current
			DESCRIPTION
				"The number of packets, delivered by this sub-layer to a
				higher (sub-)layer, which were addressed to a multicast
				address at this sub-layer.  For a MAC layer protocol, this
				includes both Group and Functional addresses.
				
				Discontinuities in the value of this counter can occur at
				re-initialization of the management system, and at other
				
				
				times as indicated by the value of
				ifCounterDiscontinuityTime."
			::= { onuPonMibPerformEntry 34 }

				-- 1.3.6.1.4.1.5875.800.3.54.3.1.35
		ifOutBroadcastPkts OBJECT-TYPE
			SYNTAX Counter32
			MAX-ACCESS read-only
			STATUS current
			DESCRIPTION
				"The total number of packets that higher-level protocols
				requested be transmitted, and which were addressed to a
				broadcast address at this sub-layer, including those that
				were discarded or not sent.
				
				Discontinuities in the value of this counter can occur at
				re-initialization of the management system, and at other
				
				
				times as indicated by the value of
				ifCounterDiscontinuityTime."
			::= { onuPonMibPerformEntry 35 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.36
		ifHCInOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 36 }

				-- 1.3.6.1.4.1.5875.800.3.54.3.1.37
		ifHCInUcastPkts OBJECT-TYPE
			SYNTAX Counter64
			MAX-ACCESS read-only
			STATUS current
			DESCRIPTION
				"The number of packets, delivered by this sub-layer to a
				higher (sub-)layer, which were not addressed to a multicast
				or broadcast address at this sub-layer.  This object is a
				64-bit version of ifInUcastPkts.
				
				Discontinuities in the value of this counter can occur at
				re-initialization of the management system, and at other
				times as indicated by the value of
				ifCounterDiscontinuityTime."
			::= { onuPonMibPerformEntry 37 }

				-- 1.3.6.1.4.1.5875.800.3.54.3.1.38
		ifHCInMulticastPkts OBJECT-TYPE
			SYNTAX Counter64
			MAX-ACCESS read-only
			STATUS current
			DESCRIPTION
				"The number of packets, delivered by this sub-layer to a
				higher (sub-)layer, which were addressed to a multicast
				address at this sub-layer.  For a MAC layer protocol, this
				includes both Group and Functional addresses.  This object
				is a 64-bit version of ifInMulticastPkts.
				
				Discontinuities in the value of this counter can occur at
				re-initialization of the management system, and at other
				times as indicated by the value of
				ifCounterDiscontinuityTime."
			::= { onuPonMibPerformEntry 38 }

				-- 1.3.6.1.4.1.5875.800.3.54.3.1.39
		ifHCInBroadcastPkts OBJECT-TYPE
			SYNTAX Counter64
			MAX-ACCESS read-only
			STATUS current
			DESCRIPTION
				"The number of packets, delivered by this sub-layer to a
				higher (sub-)layer, which were addressed to a broadcast
				address at this sub-layer.  This object is a 64-bit version
				of ifInBroadcastPkts.
				
				Discontinuities in the value of this counter can occur at
				re-initialization of the management system, and at other
				times as indicated by the value of
				ifCounterDiscontinuityTime."
			::= { onuPonMibPerformEntry 39 }

				-- 1.3.6.1.4.1.5875.800.3.54.3.1.40
		ifHCOutOctets OBJECT-TYPE
			SYNTAX Counter64
			MAX-ACCESS read-only
			STATUS current
			DESCRIPTION
				"The total number of octets transmitted out of the
				interface, including framing characters.  This object is a
				64-bit version of ifOutOctets.
				
				Discontinuities in the value of this counter can occur at
				re-initialization of the management system, and at other
				times as indicated by the value of
				ifCounterDiscontinuityTime."
			::= { onuPonMibPerformEntry 40 }

				-- 1.3.6.1.4.1.5875.800.3.54.3.1.41
		ifHCOutUcastPkts OBJECT-TYPE
			SYNTAX Counter64
			MAX-ACCESS read-only
			STATUS current
			DESCRIPTION
				"The total number of packets that higher-level protocols
				requested be transmitted, and which were not addressed to a
				multicast or broadcast address at this sub-layer, including
				those that were discarded or not sent.  This object is a
				64-bit version of ifOutUcastPkts.
				
				Discontinuities in the value of this counter can occur at
				re-initialization of the management system, and at other
				times as indicated by the value of
				ifCounterDiscontinuityTime."
			::= { onuPonMibPerformEntry 41 }

				-- 1.3.6.1.4.1.5875.800.3.54.3.1.42
		ifHCOutMulticastPkts OBJECT-TYPE
			SYNTAX Counter64
			MAX-ACCESS read-only
			STATUS current
			DESCRIPTION
				"The total number of packets that higher-level protocols
				requested be transmitted, and which were addressed to a
				multicast address at this sub-layer, including those that
				were discarded or not sent.  For a MAC layer protocol, this
				includes both Group and Functional addresses.  This object
				is a 64-bit version of ifOutMulticastPkts.
				
				Discontinuities in the value of this counter can occur at
				re-initialization of the management system, and at other
				times as indicated by the value of
				ifCounterDiscontinuityTime."
			::= { onuPonMibPerformEntry 42 }

				-- 1.3.6.1.4.1.5875.800.3.54.3.1.43
		ifHCOutBroadcastPkts OBJECT-TYPE
			SYNTAX Counter64
			MAX-ACCESS read-only
			STATUS current
			DESCRIPTION
				"The total number of packets that higher-level protocols
				requested be transmitted, and which were addressed to a
				broadcast address at this sub-layer, including those that
				were discarded or not sent.  This object is a 64-bit version
				of ifOutBroadcastPkts.
				
				Discontinuities in the value of this counter can occur at
				re-initialization of the management system, and at other
				times as indicated by the value of
				ifCounterDiscontinuityTime."
			::= { onuPonMibPerformEntry 43 }

				-- 1.3.6.1.4.1.5875.800.3.54.3.1.44
		ifLinkUpDownTrapEnable OBJECT-TYPE
			SYNTAX INTEGER
				{
				enabled(1),
				disabled(2)
				}
			MAX-ACCESS read-write
			STATUS current
			DESCRIPTION
				"Indicates whether linkUp/linkDown traps should be generated
				for this interface.
				
				By default, this object should have the value enabled(1) for
				interfaces which do not operate on 'top' of any other
				interface (as defined in the ifStackTable), and disabled(2)
				otherwise."
			::= { onuPonMibPerformEntry 44 }

				-- 1.3.6.1.4.1.5875.800.3.54.3.1.45
		ifHighSpeed OBJECT-TYPE
			SYNTAX Gauge32
			MAX-ACCESS read-only
			STATUS current
			DESCRIPTION
				"An estimate of the interface's current bandwidth in units
				of 1,000,000 bits per second.  If this object reports a
				value of `n' then the speed of the interface is somewhere in
				the range of `n-500,000' to `n+499,999'.  For interfaces
				which do not vary in bandwidth or for those where no
				accurate estimation can be made, this object should contain
				the nominal bandwidth.  For a sub-layer which has no concept
				of bandwidth, this object should be zero."
			::= { onuPonMibPerformEntry 45 }

				-- 1.3.6.1.4.1.5875.800.3.54.3.1.46
		ifPromiscuousMode OBJECT-TYPE
			SYNTAX TruthValue
			MAX-ACCESS read-write
			STATUS current
			DESCRIPTION
				"This object has a value of false(2) if this interface only
				accepts packets/frames that are addressed to this station.
				This object has a value of true(1) when the station accepts
				all packets/frames transmitted on the media.  The value
				true(1) is only legal on certain types of media.  If legal,
				setting this object to a value of true(1) may require the
				interface to be reset before becoming effective.
				
				The value of ifPromiscuousMode does not affect the reception
				of broadcast and multicast packets/frames by the interface."
			::= { onuPonMibPerformEntry 46 }

				-- 1.3.6.1.4.1.5875.800.3.54.3.1.47
		ifConnectorPresent OBJECT-TYPE
			SYNTAX TruthValue
			MAX-ACCESS read-only
			STATUS current
			DESCRIPTION
				"This object has the value 'true(1)' if the interface
				sublayer has a physical connector and the value 'false(2)'
				otherwise."
			::= { onuPonMibPerformEntry 47 }

				-- 1.3.6.1.4.1.5875.800.3.54.3.1.48
		ifAlias OBJECT-TYPE
			SYNTAX DisplayString (SIZE (0..64))
			MAX-ACCESS read-write
			STATUS current
			DESCRIPTION
				"This object is an 'alias' name for the interface as
				specified by a network manager, and provides a non-volatile
				'handle' for the interface.
				
				On the first instantiation of an interface, the value of
				ifAlias associated with that interface is the zero-length
				string.  As and when a value is written into an instance of
				ifAlias through a network management set operation, then the
				agent must retain the supplied value in the ifAlias instance
				associated with the same interface for as long as that
				interface remains instantiated, including across all re-
				initializations/reboots of the network management system,
				including those which result in a change of the interface's
				ifIndex value.
				
				An example of the value which a network manager might store
				in this object for a WAN interface is the (Telco's) circuit
				number/identifier of the interface.
				
				Some agents may support write-access only for interfaces
				having particular values of ifType.  An agent which supports
				write access to this object is required to keep the value in
				non-volatile storage, but it may limit the length of new
				values depending on how much storage is already occupied by
				the current values for other interfaces."
			::= { onuPonMibPerformEntry 48 }

				-- 1.3.6.1.4.1.5875.800.3.54.3.1.49
		ifCounterDiscontinuityTime OBJECT-TYPE
			SYNTAX TimeStamp
			MAX-ACCESS read-only
			STATUS current
			DESCRIPTION
				"The value of sysUpTime on the most recent occasion at which
				any one or more of this interface's counters suffered a
				discontinuity.  The relevant counters are the specific
				instances associated with this interface of any Counter32 or
				
				
				Counter64 object contained in the ifTable or ifXTable.  If
				no such discontinuities have occurred since the last re-
				initialization of the local management subsystem, then this
				object contains a zero value."
			::= { onuPonMibPerformEntry 49 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.50
		ferfRecvGoodPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 50 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.51
		ferfRecvDiscardedPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 51 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.52
		ferfRecvErrorPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 52 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.53
		ferfSendGoodPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 53 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.54
		ferfSendDiscardedPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 54 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.55
		ferfSendErrorPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 55 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.56
		ferfRecv64OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 56 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.57
		ferfRecv65to127OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 57 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.58
		ferfRecv128to255OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 58 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.59
		ferfRecv256to511OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 59 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.60
		ferfRecv512to1023OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 60 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.61
		ferfRecv1024to1518OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 61 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.62
		ferfLossSignalSeconds OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 62 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.63
		ferfErroredSeconds OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 63 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.64
		ferfSeverelyErroredSeconds OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 64 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.65
		ferfUnavailableSeconds OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 65 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.66
		ferfDetectMonitorDiscardPacketNumber OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 66 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.67
		ferfRecvPauseFlowControlFrames OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 67 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.68
		ferfSendPauseFlowControlFrames OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 68 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.69
		ferfChecksumErrors OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 69 }

				-- 1.3.6.1.4.1.5875.800.3.54.3.1.70
		ferfFcsFrameCheckErrors OBJECT-TYPE
			SYNTAX INTEGER
			MAX-ACCESS read-only
			STATUS current
			DESCRIPTION
				"The total number of octets received on the
				interface, including framing characters."
			::= { onuPonMibPerformEntry 70 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.71
		ferfExcessiveCollisionStatistics OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 71 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.72
		ferfSingleCollisionSendOkFrames OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 72 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.73
		ferfMultipleCollisionsSendOkFrames OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 73 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.74
		ferfPortInFlow OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 74 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.3.1.75
		ferfPortOnuFlow OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuPonMibPerformEntry 75 }

				-- 1.3.6.1.4.1.5875.800.3.54.3.1.76
		lineCodeError OBJECT-TYPE
			SYNTAX Counter64
			MAX-ACCESS read-only
			STATUS current
			DESCRIPTION
				"Description."
			::= { onuPonMibPerformEntry 76 }

				-- 1.3.6.1.4.1.5875.800.3.54.4
		onuPonMibPerformTableNextScalar OBJECT-TYPE
			SYNTAX Integer32 (0..1024)
			MAX-ACCESS read-only
			STATUS current
			DESCRIPTION
				"Description"
			::= { mibPerformExtern 4 }

		
--                          the Interfaces table
-- The Interfaces table contains information on the entity's
-- interfaces.  Each interface is thought of as being
-- attached to a `subnetwork'.  Note that this term should
-- not be confused with `subnet' which refers to an
-- addressing partitioning scheme used in the Internet suite
-- of protocols.
		-- 1.3.6.1.4.1.5875.800.3.54.5
		onuFEMibPerformTable OBJECT-TYPE
			SYNTAX SEQUENCE OF OnuFEMibPerformEntry
			MAX-ACCESS not-accessible
			STATUS current
			DESCRIPTION
				"A list of interface entries.  The number of
				entries is given by the value of ifNumber."
			::= { mibPerformExtern 5 }

				-- 1.3.6.1.4.1.5875.800.3.54.5.1
		onuFEMibPerformEntry OBJECT-TYPE
			SYNTAX OnuFEMibPerformEntry
			MAX-ACCESS not-accessible
			STATUS current
			DESCRIPTION
				"An interface entry containing objects at the
				subnetwork layer and below for a particular
				interface."
			INDEX { portIndex }
			::= { onuFEMibPerformTable 1 }

		
		OnuFEMibPerformEntry ::=
			SEQUENCE { 
				onuFEifDescr
					DisplayString,
				onuFEifType
					INTEGER,
				onuFEifMtu
					INTEGER,
				onuFEifSpeed
					INTEGER,
				onuFEifPhysAddress
					PhysAddress,
				onuFEfifAdminStatus
					INTEGER,
				onuFEfifOperStatus
					INTEGER,
				onuFEifLastChange
					TimeTicks,
				onuFEifInOctets
					INTEGER,
				onuFEifInUcastPkts
					INTEGER,
				onuFEifInNUcastPkts
					INTEGER,
				onuFEifInDiscards
					INTEGER,
				onuFEifInErrors
					INTEGER,
				onuFEifInUnknownProtos
					INTEGER,
				onuFEifOutOctets
					INTEGER,
				onuFEifOutUcastPkts
					INTEGER,
				onuFEifOutNUcastPkts
					INTEGER,
				onuFEifOutDiscards
					INTEGER,
				onuFEifOutErrors
					INTEGER,
				onuFEinflowsBIP
					Integer32,
				onuFEoutflowsBIP
					Integer32,
				onuFEifOutMulticastPkts
					Counter32,
				onuFEifInBroadcastPkts
					Counter32,
				onuFEifInMulticastPkts
					Counter32,
				onuFEifOutBroadcastPkts
					Counter32,
				onuFEifHCInOctets
					Counter64,
				onuFEifHCInUcastPkts
					Counter64,
				onuFEifHCInMulticastPkts
					Counter64,
				onuFEifHCInBroadcastPkts
					Counter64,
				onuFEifHCOutOctets
					Counter64,
				onuFEifHCOutUcastPkts
					Counter64,
				onuFEifHCOutMulticastPkts
					Counter64,
				onuFEifHCOutBroadcastPkts
					Counter64,
				onuFEifLinkUpDownTrapEnable
					INTEGER,
				onuFEifHighSpeed
					Gauge32,
				onuFEifPromiscuousMode
					TruthValue,
				onuFEifConnectorPresent
					TruthValue,
				onuFEifAlias
					DisplayString,
				onuFEifCounterDiscontinuityTime
					TimeStamp,
				onuFEferfRecvGoodPackageOctets
					Counter64,
				onuFEferfRecvDiscardedPackageOctets
					Counter64,
				onuFEferfRecvErrorPackageOctets
					Counter64,
				onuFEferfSendGoodPackageOctets
					Counter64,
				onuFEferfSendDiscardedPackageOctets
					Counter64,
				onuFEferfSendErrorPackageOctets
					Counter64,
				onuFEferfRecv64OctetsLenPkts
					Counter64,
				onuFEferfRecv65to127OctetsLenPkts
					Counter64,
				onuFEferfRecv128to255OctetsLenPkts
					Counter64,
				onuFEferfRecv256to511OctetsLenPkts
					Counter64,
				onuFEferfRecv512to1023OctetsLenPkts
					Counter64,
				onuFEferfRecv1024to1518OctetsLenPkts
					Counter64,
				onuFEferfLossSignalSeconds
					Counter64,
				onuFEferfErroredSeconds
					Counter64,
				onuFEferfSeverelyErroredSeconds
					Counter64,
				onuFEferfUnavailableSeconds
					Counter64,
				onuFEferfDetectMonitorDiscardPacketNumber
					Counter64,
				onuFEerfRecvPauseFlowControlFrames
					Counter64,
				onuFEferfSendPauseFlowControlFrames
					Counter64,
				onuFEferfChecksumErrors
					Counter64,
				onuFEferfFcsFrameCheckErrors
					INTEGER,
				onuFEferfExcessiveCollisionStatistics
					Counter64,
				onuFEferfSingleCollisionSendOkFrames
					Counter64,
				onuFEferfMultipleCollisionsSendOkFrames
					Counter64,
				onuFEferfPortInFlow
					Counter64,
				onuFEferfPortOnuFlow
					Counter64
			 }
		-- 1.3.6.1.4.1.5875.800.3.54.5.1.2
		onuFEifDescr OBJECT-TYPE
			SYNTAX DisplayString (SIZE (0..255))
			MAX-ACCESS read-only
			STATUS current
			DESCRIPTION
				"A textual string containing information about the
				interface.  This string should include the name of
				the manufacturer, the product name and the version
				of the hardware interface."
			::= { onuFEMibPerformEntry 2 }

		
--                          none of the following
-- T1
-- european equiv. of T1
-- proprietary serial
-- CLNP over IP [11]
-- XNS over IP
-- generic SLIP
-- ULTRA technologies
-- T3
-- SMDS
		-- 1.3.6.1.4.1.5875.800.3.54.5.1.3
		onuFEifType OBJECT-TYPE
			SYNTAX INTEGER
				{
				other(1),
				regular1822(2),
				hdh1822(3),
				ddn-x25(4),
				rfc877-x25(5),
				ethernet-csmacd(6),
				iso88023-csmacd(7),
				iso88024-tokenBus(8),
				iso88025-tokenRing(9),
				iso88026-man(10),
				starLan(11),
				proteon-10Mbit(12),
				proteon-80Mbit(13),
				hyperchannel(14),
				fddi(15),
				lapb(16),
				sdlc(17),
				ds1(18),
				e1(19),
				basicISDN(20),
				primaryISDN(21),
				propPointToPointSerial(22),
				ppp(23),
				softwareLoopback(24),
				eon(25),
				ethernet-3Mbit(26),
				nsip(27),
				slip(28),
				ultra(29),
				ds3(30),
				sip(31),
				frame-relay(32)
				}
			MAX-ACCESS read-only
			STATUS current
			DESCRIPTION
				"The type of interface, distinguished according to
				the physical/link protocol(s) immediately `below'
				the network layer in the protocol stack."
			::= { onuFEMibPerformEntry 3 }

				-- 1.3.6.1.4.1.5875.800.3.54.5.1.4
		onuFEifMtu OBJECT-TYPE
			SYNTAX INTEGER
			MAX-ACCESS read-only
			STATUS current
			DESCRIPTION
				"The size of the largest datagram which can be
				sent/received on the interface, specified in
				octets.  For interfaces that are used for
				transmitting network datagrams, this is the size
				of the largest network datagram that can be sent
				on the interface."
			::= { onuFEMibPerformEntry 4 }

				-- 1.3.6.1.4.1.5875.800.3.54.5.1.5
		onuFEifSpeed OBJECT-TYPE
			SYNTAX INTEGER
			MAX-ACCESS read-only
			STATUS current
			DESCRIPTION
				"An estimate of the interface's current bandwidth
				in bits per second.  For interfaces which do not
				vary in bandwidth or for those where no accurate
				estimation can be made, this object should contain
				the nominal bandwidth."
			::= { onuFEMibPerformEntry 5 }

				-- 1.3.6.1.4.1.5875.800.3.54.5.1.6
		onuFEifPhysAddress OBJECT-TYPE
			SYNTAX PhysAddress
			MAX-ACCESS read-only
			STATUS current
			DESCRIPTION
				"The interface's address at the protocol layer
				immediately `below' the network layer in the
				protocol stack.  For interfaces which do not have
				such an address (e.g., a serial line), this object
				should contain an octet string of zero length."
			::= { onuFEMibPerformEntry 6 }

		
--                          ready to pass packets
-- in some test mode
		-- 1.3.6.1.4.1.5875.800.3.54.5.1.7
		onuFEfifAdminStatus OBJECT-TYPE
			SYNTAX INTEGER
				{
				up(1),
				down(2),
				testing(3)
				}
			MAX-ACCESS read-write
			STATUS current
			DESCRIPTION
				"The desired state of the interface.  The
				testing(3) state indicates that no operational
				packets can be passed."
			::= { onuFEMibPerformEntry 7 }

		
--                          ready to pass packets
-- in some test mode
		-- 1.3.6.1.4.1.5875.800.3.54.5.1.8
		onuFEfifOperStatus OBJECT-TYPE
			SYNTAX INTEGER
				{
				up(1),
				down(2),
				testing(3)
				}
			MAX-ACCESS read-only
			STATUS current
			DESCRIPTION
				"The current operational state of the interface.
				The testing(3) state indicates that no operational
				packets can be passed."
			::= { onuFEMibPerformEntry 8 }

				-- 1.3.6.1.4.1.5875.800.3.54.5.1.9
		onuFEifLastChange OBJECT-TYPE
			SYNTAX TimeTicks
			MAX-ACCESS read-only
			STATUS current
			DESCRIPTION
				"The value of sysUpTime at the time the interface
				entered its current operational state.  If the
				current state was entered prior to the last re-
				initialization of the local network management
				subsystem, then this object contains a zero
				value."
			::= { onuFEMibPerformEntry 9 }

				-- 1.3.6.1.4.1.5875.800.3.54.5.1.10
		onuFEifInOctets OBJECT-TYPE
			SYNTAX INTEGER
			MAX-ACCESS read-only
			STATUS current
			DESCRIPTION
				"The total number of octets received on the
				interface, including framing characters."
			::= { onuFEMibPerformEntry 10 }

				-- 1.3.6.1.4.1.5875.800.3.54.5.1.11
		onuFEifInUcastPkts OBJECT-TYPE
			SYNTAX INTEGER
			MAX-ACCESS read-only
			STATUS current
			DESCRIPTION
				"The number of subnetwork-unicast packets
				delivered to a higher-layer protocol."
			::= { onuFEMibPerformEntry 11 }

				-- 1.3.6.1.4.1.5875.800.3.54.5.1.12
		onuFEifInNUcastPkts OBJECT-TYPE
			SYNTAX INTEGER
			MAX-ACCESS read-only
			STATUS current
			DESCRIPTION
				"The number of non-unicast (i.e., subnetwork-
				broadcast or subnetwork-multicast) packets
				delivered to a higher-layer protocol."
			::= { onuFEMibPerformEntry 12 }

				-- 1.3.6.1.4.1.5875.800.3.54.5.1.13
		onuFEifInDiscards OBJECT-TYPE
			SYNTAX INTEGER
			MAX-ACCESS read-only
			STATUS current
			DESCRIPTION
				"The number of inbound packets which were chosen
				to be discarded even though no errors had been
				detected to prevent their being deliverable to a
				higher-layer protocol.  One possible reason for
				discarding such a packet could be to free up
				buffer space."
			::= { onuFEMibPerformEntry 13 }

				-- 1.3.6.1.4.1.5875.800.3.54.5.1.14
		onuFEifInErrors OBJECT-TYPE
			SYNTAX INTEGER
			MAX-ACCESS read-only
			STATUS current
			DESCRIPTION
				"The number of inbound packets that contained
				errors preventing them from being deliverable to a
				higher-layer protocol."
			::= { onuFEMibPerformEntry 14 }

				-- 1.3.6.1.4.1.5875.800.3.54.5.1.15
		onuFEifInUnknownProtos OBJECT-TYPE
			SYNTAX INTEGER
			MAX-ACCESS read-only
			STATUS current
			DESCRIPTION
				"The number of packets received via the interface
				which were discarded because of an unknown or
				unsupported protocol."
			::= { onuFEMibPerformEntry 15 }

				-- 1.3.6.1.4.1.5875.800.3.54.5.1.16
		onuFEifOutOctets OBJECT-TYPE
			SYNTAX INTEGER
			MAX-ACCESS read-only
			STATUS current
			DESCRIPTION
				"The total number of octets transmitted out of the
				interface, including framing characters."
			::= { onuFEMibPerformEntry 16 }

				-- 1.3.6.1.4.1.5875.800.3.54.5.1.17
		onuFEifOutUcastPkts OBJECT-TYPE
			SYNTAX INTEGER
			MAX-ACCESS read-only
			STATUS current
			DESCRIPTION
				"The total number of packets that higher-level
				protocols requested be transmitted to a
				subnetwork-unicast address, including those that
				were discarded or not sent."
			::= { onuFEMibPerformEntry 17 }

				-- 1.3.6.1.4.1.5875.800.3.54.5.1.18
		onuFEifOutNUcastPkts OBJECT-TYPE
			SYNTAX INTEGER
			MAX-ACCESS read-only
			STATUS current
			DESCRIPTION
				"The total number of packets that higher-level
				protocols requested be transmitted to a non-
				unicast (i.e., a subnetwork-broadcast or
				subnetwork-multicast) address, including those
				that were discarded or not sent."
			::= { onuFEMibPerformEntry 18 }

				-- 1.3.6.1.4.1.5875.800.3.54.5.1.19
		onuFEifOutDiscards OBJECT-TYPE
			SYNTAX INTEGER
			MAX-ACCESS read-only
			STATUS current
			DESCRIPTION
				"The number of outbound packets which were chosen
				to be discarded even though no errors had been
				detected to prevent their being transmitted.  One
				possible reason for discarding such a packet could
				be to free up buffer space."
			::= { onuFEMibPerformEntry 19 }

				-- 1.3.6.1.4.1.5875.800.3.54.5.1.20
		onuFEifOutErrors OBJECT-TYPE
			SYNTAX INTEGER
			MAX-ACCESS read-only
			STATUS current
			DESCRIPTION
				"The number of outbound packets that could not be
				transmitted because of errors."
			::= { onuFEMibPerformEntry 20 }

				-- 1.3.6.1.4.1.5875.800.3.54.5.1.21
		onuFEinflowsBIP OBJECT-TYPE
			SYNTAX Integer32 (0..1024)
			MAX-ACCESS read-only
			STATUS current
			DESCRIPTION
				"Port Traffic Collection Extending Part"
			::= { onuFEMibPerformEntry 21 }

				-- 1.3.6.1.4.1.5875.800.3.54.5.1.22
		onuFEoutflowsBIP OBJECT-TYPE
			SYNTAX Integer32 (0..1024)
			MAX-ACCESS read-only
			STATUS current
			DESCRIPTION
				"Port Traffic Collection Extending Part"
			::= { onuFEMibPerformEntry 22 }

				-- 1.3.6.1.4.1.5875.800.3.54.5.1.32
		onuFEifOutMulticastPkts OBJECT-TYPE
			SYNTAX Counter32
			MAX-ACCESS read-only
			STATUS current
			DESCRIPTION
				"The total number of packets that higher-level protocols
				requested be transmitted, and which were addressed to a
				multicast address at this sub-layer, including those that
				were discarded or not sent.  For a MAC layer protocol, this
				includes both Group and Functional addresses.
				
				Discontinuities in the value of this counter can occur at
				re-initialization of the management system, and at other
				times as indicated by the value of
				ifCounterDiscontinuityTime."
			::= { onuFEMibPerformEntry 32 }

				-- 1.3.6.1.4.1.5875.800.3.54.5.1.33
		onuFEifInBroadcastPkts OBJECT-TYPE
			SYNTAX Counter32
			MAX-ACCESS read-only
			STATUS current
			DESCRIPTION
				"The number of packets, delivered by this sub-layer to a
				higher (sub-)layer, which were addressed to a broadcast
				address at this sub-layer.
				
				Discontinuities in the value of this counter can occur at
				re-initialization of the management system, and at other
				times as indicated by the value of
				ifCounterDiscontinuityTime."
			::= { onuFEMibPerformEntry 33 }

				-- 1.3.6.1.4.1.5875.800.3.54.5.1.34
		onuFEifInMulticastPkts OBJECT-TYPE
			SYNTAX Counter32
			MAX-ACCESS read-only
			STATUS current
			DESCRIPTION
				"The number of packets, delivered by this sub-layer to a
				higher (sub-)layer, which were addressed to a multicast
				address at this sub-layer.  For a MAC layer protocol, this
				includes both Group and Functional addresses.
				
				Discontinuities in the value of this counter can occur at
				re-initialization of the management system, and at other
				
				
				times as indicated by the value of
				ifCounterDiscontinuityTime."
			::= { onuFEMibPerformEntry 34 }

				-- 1.3.6.1.4.1.5875.800.3.54.5.1.35
		onuFEifOutBroadcastPkts OBJECT-TYPE
			SYNTAX Counter32
			MAX-ACCESS read-only
			STATUS current
			DESCRIPTION
				"The total number of packets that higher-level protocols
				requested be transmitted, and which were addressed to a
				broadcast address at this sub-layer, including those that
				were discarded or not sent.
				
				Discontinuities in the value of this counter can occur at
				re-initialization of the management system, and at other
				
				
				times as indicated by the value of
				ifCounterDiscontinuityTime."
			::= { onuFEMibPerformEntry 35 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.36
		onuFEifHCInOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 36 }

				-- 1.3.6.1.4.1.5875.800.3.54.5.1.37
		onuFEifHCInUcastPkts OBJECT-TYPE
			SYNTAX Counter64
			MAX-ACCESS read-only
			STATUS current
			DESCRIPTION
				"The number of packets, delivered by this sub-layer to a
				higher (sub-)layer, which were not addressed to a multicast
				or broadcast address at this sub-layer.  This object is a
				64-bit version of ifInUcastPkts.
				
				Discontinuities in the value of this counter can occur at
				re-initialization of the management system, and at other
				times as indicated by the value of
				ifCounterDiscontinuityTime."
			::= { onuFEMibPerformEntry 37 }

				-- 1.3.6.1.4.1.5875.800.3.54.5.1.38
		onuFEifHCInMulticastPkts OBJECT-TYPE
			SYNTAX Counter64
			MAX-ACCESS read-only
			STATUS current
			DESCRIPTION
				"The number of packets, delivered by this sub-layer to a
				higher (sub-)layer, which were addressed to a multicast
				address at this sub-layer.  For a MAC layer protocol, this
				includes both Group and Functional addresses.  This object
				is a 64-bit version of ifInMulticastPkts.
				
				Discontinuities in the value of this counter can occur at
				re-initialization of the management system, and at other
				times as indicated by the value of
				ifCounterDiscontinuityTime."
			::= { onuFEMibPerformEntry 38 }

				-- 1.3.6.1.4.1.5875.800.3.54.5.1.39
		onuFEifHCInBroadcastPkts OBJECT-TYPE
			SYNTAX Counter64
			MAX-ACCESS read-only
			STATUS current
			DESCRIPTION
				"The number of packets, delivered by this sub-layer to a
				higher (sub-)layer, which were addressed to a broadcast
				address at this sub-layer.  This object is a 64-bit version
				of ifInBroadcastPkts.
				
				Discontinuities in the value of this counter can occur at
				re-initialization of the management system, and at other
				times as indicated by the value of
				ifCounterDiscontinuityTime."
			::= { onuFEMibPerformEntry 39 }

				-- 1.3.6.1.4.1.5875.800.3.54.5.1.40
		onuFEifHCOutOctets OBJECT-TYPE
			SYNTAX Counter64
			MAX-ACCESS read-only
			STATUS current
			DESCRIPTION
				"The total number of octets transmitted out of the
				interface, including framing characters.  This object is a
				64-bit version of ifOutOctets.
				
				Discontinuities in the value of this counter can occur at
				re-initialization of the management system, and at other
				times as indicated by the value of
				ifCounterDiscontinuityTime."
			::= { onuFEMibPerformEntry 40 }

				-- 1.3.6.1.4.1.5875.800.3.54.5.1.41
		onuFEifHCOutUcastPkts OBJECT-TYPE
			SYNTAX Counter64
			MAX-ACCESS read-only
			STATUS current
			DESCRIPTION
				"The total number of packets that higher-level protocols
				requested be transmitted, and which were not addressed to a
				multicast or broadcast address at this sub-layer, including
				those that were discarded or not sent.  This object is a
				64-bit version of ifOutUcastPkts.
				
				Discontinuities in the value of this counter can occur at
				re-initialization of the management system, and at other
				times as indicated by the value of
				ifCounterDiscontinuityTime."
			::= { onuFEMibPerformEntry 41 }

				-- 1.3.6.1.4.1.5875.800.3.54.5.1.42
		onuFEifHCOutMulticastPkts OBJECT-TYPE
			SYNTAX Counter64
			MAX-ACCESS read-only
			STATUS current
			DESCRIPTION
				"The total number of packets that higher-level protocols
				requested be transmitted, and which were addressed to a
				multicast address at this sub-layer, including those that
				were discarded or not sent.  For a MAC layer protocol, this
				includes both Group and Functional addresses.  This object
				is a 64-bit version of ifOutMulticastPkts.
				
				Discontinuities in the value of this counter can occur at
				re-initialization of the management system, and at other
				times as indicated by the value of
				ifCounterDiscontinuityTime."
			::= { onuFEMibPerformEntry 42 }

				-- 1.3.6.1.4.1.5875.800.3.54.5.1.43
		onuFEifHCOutBroadcastPkts OBJECT-TYPE
			SYNTAX Counter64
			MAX-ACCESS read-only
			STATUS current
			DESCRIPTION
				"The total number of packets that higher-level protocols
				requested be transmitted, and which were addressed to a
				broadcast address at this sub-layer, including those that
				were discarded or not sent.  This object is a 64-bit version
				of ifOutBroadcastPkts.
				
				Discontinuities in the value of this counter can occur at
				re-initialization of the management system, and at other
				times as indicated by the value of
				ifCounterDiscontinuityTime."
			::= { onuFEMibPerformEntry 43 }

				-- 1.3.6.1.4.1.5875.800.3.54.5.1.44
		onuFEifLinkUpDownTrapEnable OBJECT-TYPE
			SYNTAX INTEGER
				{
				enabled(1),
				disabled(2)
				}
			MAX-ACCESS read-write
			STATUS current
			DESCRIPTION
				"Indicates whether linkUp/linkDown traps should be generated
				for this interface.
				
				By default, this object should have the value enabled(1) for
				interfaces which do not operate on 'top' of any other
				interface (as defined in the ifStackTable), and disabled(2)
				otherwise."
			::= { onuFEMibPerformEntry 44 }

				-- 1.3.6.1.4.1.5875.800.3.54.5.1.45
		onuFEifHighSpeed OBJECT-TYPE
			SYNTAX Gauge32
			MAX-ACCESS read-only
			STATUS current
			DESCRIPTION
				"An estimate of the interface's current bandwidth in units
				of 1,000,000 bits per second.  If this object reports a
				value of `n' then the speed of the interface is somewhere in
				the range of `n-500,000' to `n+499,999'.  For interfaces
				which do not vary in bandwidth or for those where no
				accurate estimation can be made, this object should contain
				the nominal bandwidth.  For a sub-layer which has no concept
				of bandwidth, this object should be zero."
			::= { onuFEMibPerformEntry 45 }

				-- 1.3.6.1.4.1.5875.800.3.54.5.1.46
		onuFEifPromiscuousMode OBJECT-TYPE
			SYNTAX TruthValue
			MAX-ACCESS read-write
			STATUS current
			DESCRIPTION
				"This object has a value of false(2) if this interface only
				accepts packets/frames that are addressed to this station.
				This object has a value of true(1) when the station accepts
				all packets/frames transmitted on the media.  The value
				true(1) is only legal on certain types of media.  If legal,
				setting this object to a value of true(1) may require the
				interface to be reset before becoming effective.
				
				The value of ifPromiscuousMode does not affect the reception
				of broadcast and multicast packets/frames by the interface."
			::= { onuFEMibPerformEntry 46 }

				-- 1.3.6.1.4.1.5875.800.3.54.5.1.47
		onuFEifConnectorPresent OBJECT-TYPE
			SYNTAX TruthValue
			MAX-ACCESS read-only
			STATUS current
			DESCRIPTION
				"This object has the value 'true(1)' if the interface
				sublayer has a physical connector and the value 'false(2)'
				otherwise."
			::= { onuFEMibPerformEntry 47 }

				-- 1.3.6.1.4.1.5875.800.3.54.5.1.48
		onuFEifAlias OBJECT-TYPE
			SYNTAX DisplayString (SIZE (0..64))
			MAX-ACCESS read-write
			STATUS current
			DESCRIPTION
				"This object is an 'alias' name for the interface as
				specified by a network manager, and provides a non-volatile
				'handle' for the interface.
				
				On the first instantiation of an interface, the value of
				ifAlias associated with that interface is the zero-length
				string.  As and when a value is written into an instance of
				ifAlias through a network management set operation, then the
				agent must retain the supplied value in the ifAlias instance
				associated with the same interface for as long as that
				interface remains instantiated, including across all re-
				initializations/reboots of the network management system,
				including those which result in a change of the interface's
				ifIndex value.
				
				An example of the value which a network manager might store
				in this object for a WAN interface is the (Telco's) circuit
				number/identifier of the interface.
				
				Some agents may support write-access only for interfaces
				having particular values of ifType.  An agent which supports
				write access to this object is required to keep the value in
				non-volatile storage, but it may limit the length of new
				values depending on how much storage is already occupied by
				the current values for other interfaces."
			::= { onuFEMibPerformEntry 48 }

				-- 1.3.6.1.4.1.5875.800.3.54.5.1.49
		onuFEifCounterDiscontinuityTime OBJECT-TYPE
			SYNTAX TimeStamp
			MAX-ACCESS read-only
			STATUS current
			DESCRIPTION
				"The value of sysUpTime on the most recent occasion at which
				any one or more of this interface's counters suffered a
				discontinuity.  The relevant counters are the specific
				instances associated with this interface of any Counter32 or
				
				
				Counter64 object contained in the ifTable or ifXTable.  If
				no such discontinuities have occurred since the last re-
				initialization of the local management subsystem, then this
				object contains a zero value."
			::= { onuFEMibPerformEntry 49 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.50
		onuFEferfRecvGoodPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 50 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.51
		onuFEferfRecvDiscardedPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 51 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.52
		onuFEferfRecvErrorPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 52 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.53
		onuFEferfSendGoodPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 53 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.54
		onuFEferfSendDiscardedPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 54 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.55
		onuFEferfSendErrorPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 55 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.56
		onuFEferfRecv64OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 56 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.57
		onuFEferfRecv65to127OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 57 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.58
		onuFEferfRecv128to255OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 58 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.59
		onuFEferfRecv256to511OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 59 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.60
		onuFEferfRecv512to1023OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 60 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.61
		onuFEferfRecv1024to1518OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 61 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.62
		onuFEferfLossSignalSeconds OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 62 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.63
		onuFEferfErroredSeconds OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 63 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.64
		onuFEferfSeverelyErroredSeconds OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 64 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.65
		onuFEferfUnavailableSeconds OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 65 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.66
		onuFEferfDetectMonitorDiscardPacketNumber OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 66 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.67
		onuFEerfRecvPauseFlowControlFrames OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 67 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.68
		onuFEferfSendPauseFlowControlFrames OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 68 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.69
		onuFEferfChecksumErrors OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 69 }

				-- 1.3.6.1.4.1.5875.800.3.54.5.1.70
		onuFEferfFcsFrameCheckErrors OBJECT-TYPE
			SYNTAX INTEGER
			MAX-ACCESS read-only
			STATUS current
			DESCRIPTION
				"The total number of octets received on the
				interface, including framing characters."
			::= { onuFEMibPerformEntry 70 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.71
		onuFEferfExcessiveCollisionStatistics OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 71 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.72
		onuFEferfSingleCollisionSendOkFrames OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 72 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.73
		onuFEferfMultipleCollisionsSendOkFrames OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 73 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.74
		onuFEferfPortInFlow OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 74 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.5.1.75
		onuFEferfPortOnuFlow OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { onuFEMibPerformEntry 75 }

				-- 1.3.6.1.4.1.5875.800.3.54.6
		igmpMibPerformInfo OBJECT IDENTIFIER ::= { mibPerformExtern 6 }

				-- 1.3.6.1.4.1.5875.800.3.54.6.1
		igmpIptvServiceNum OBJECT-TYPE
			SYNTAX Integer32
			MAX-ACCESS read-only
			STATUS current
			DESCRIPTION
				"Description"
			::= { igmpMibPerformInfo 1 }

				-- 1.3.6.1.4.1.5875.800.3.54.6.2
		igmpIptvServiceandPortUpNum OBJECT-TYPE
			SYNTAX Integer32
			MAX-ACCESS read-only
			STATUS current
			DESCRIPTION
				"Description"
			::= { igmpMibPerformInfo 2 }

				-- 1.3.6.1.4.1.5875.800.3.54.6.3
		igmpIptvServiceandJoinIgmpNum OBJECT-TYPE
			SYNTAX Integer32
			MAX-ACCESS read-only
			STATUS current
			DESCRIPTION
				"Description"
			::= { igmpMibPerformInfo 3 }

		
--                          the Interfaces table
-- The Interfaces table contains information on the entity's
-- interfaces.  Each interface is thought of as being
-- attached to a `subnetwork'.  Note that this term should
-- not be confused with `subnet' which refers to an
-- addressing partitioning scheme used in the Internet suite
-- of protocols.
		-- 1.3.6.1.4.1.5875.800.3.54.7
		cardPonMibPerformTable OBJECT-TYPE
			SYNTAX SEQUENCE OF CardPonMibPerformEntry
			MAX-ACCESS not-accessible
			STATUS current
			DESCRIPTION
				"A list of interface entries.  The number of
				entries is given by the value of ifNumber."
			::= { mibPerformExtern 7 }

				-- 1.3.6.1.4.1.5875.800.3.54.7.1
		cardPonMibPerformEntry OBJECT-TYPE
			SYNTAX CardPonMibPerformEntry
			MAX-ACCESS not-accessible
			STATUS current
			DESCRIPTION
				"An interface entry containing objects at the
				subnetwork layer and below for a particular
				interface."
			INDEX { ifCardPonIndex }
			::= { cardPonMibPerformTable 1 }

		
		CardPonMibPerformEntry ::=
			SEQUENCE { 
				ifCardPonIndex
					Integer32,
				cardifDescr
					DisplayString,
				cardifType
					INTEGER,
				cardifMtu
					INTEGER,
				cardifSpeed
					INTEGER,
				cardifPhysAddress
					PhysAddress,
				cardifAdminStatus
					INTEGER,
				cardifOperStatus
					INTEGER,
				cardifLastChange
					TimeTicks,
				cardifInOctets
					INTEGER,
				cardifInUcastPkts
					INTEGER,
				cardifInNUcastPkts
					INTEGER,
				cardifInDiscards
					INTEGER,
				cardifInErrors
					INTEGER,
				cardifInUnknownProtos
					INTEGER,
				cardifOutOctets
					INTEGER,
				cardifOutUcastPkts
					INTEGER,
				cardifOutNUcastPkts
					INTEGER,
				cardifOutDiscards
					INTEGER,
				cardifOutErrors
					INTEGER,
				cardinflowsBIP
					Integer32,
				cardoutflowsBIP
					Integer32,
				cardifOutMulticastPkts
					Counter32,
				cardifInBroadcastPkts
					Counter32,
				cardifInMulticastPkts
					Counter32,
				cardifOutBroadcastPkts
					Counter32,
				cardifHCInOctets
					Counter64,
				cardifHCInUcastPkts
					Counter64,
				cardifHCInMulticastPkts
					Counter64,
				cardifHCInBroadcastPkts
					Counter64,
				cardifHCOutOctets
					Counter64,
				cardifHCOutUcastPkts
					Counter64,
				cardifHCOutMulticastPkts
					Counter64,
				cardifHCOutBroadcastPkts
					Counter64,
				cardifLinkUpDownTrapEnable
					INTEGER,
				cardifHighSpeed
					Gauge32,
				cardifPromiscuousMode
					TruthValue,
				cardifConnectorPresent
					TruthValue,
				cardifAlias
					DisplayString,
				cardifCounterDiscontinuityTime
					TimeStamp,
				cardferfRecvGoodPackageOctets
					Counter64,
				cardferfRecvDiscardedPackageOctets
					Counter64,
				cardferfRecvErrorPackageOctets
					Counter64,
				cardferfSendGoodPackageOctets
					Counter64,
				cardferfSendDiscardedPackageOctets
					Counter64,
				cardferfSendErrorPackageOctets
					Counter64,
				cardferfRecv64OctetsLenPkts
					Counter64,
				cardferfRecv65to127OctetsLenPkts
					Counter64,
				cardferfRecv128to255OctetsLenPkts
					Counter64,
				cardferfRecv256to511OctetsLenPkts
					Counter64,
				cardferfRecv512to1023OctetsLenPkts
					Counter64,
				cardferfRecv1024to1518OctetsLenPkts
					Counter64,
				cardferfLossSignalSeconds
					Counter64,
				cardferfErroredSeconds
					Counter64,
				cardferfSeverelyErroredSeconds
					Counter64,
				cardferfUnavailableSeconds
					Counter64,
				cardferfDetectMonitorDiscardPacketNumber
					Counter64,
				cardferfRecvPauseFlowControlFrames
					Counter64,
				cardferfSendPauseFlowControlFrames
					Counter64,
				cardferfChecksumErrors
					Counter64,
				cardferfFcsFrameCheckErrors
					INTEGER,
				cardferfExcessiveCollisionStatistics
					Counter64,
				cardferfSingleCollisionSendOkFrames
					Counter64,
				cardferfMultipleCollisionsSendOkFrames
					Counter64,
				cardferfPortInFlow
					Counter64,
				cardferfPortOnuFlow
					Counter64
			 }
		-- 1.3.6.1.4.1.5875.800.3.54.7.1.1
		ifCardPonIndex OBJECT-TYPE
			SYNTAX Integer32 (1..1000000)
			MAX-ACCESS read-only
			STATUS current
			DESCRIPTION
				"Description."
			::= { cardPonMibPerformEntry 1 }

				-- 1.3.6.1.4.1.5875.800.3.54.7.1.2
		cardifDescr OBJECT-TYPE
			SYNTAX DisplayString (SIZE (0..255))
			MAX-ACCESS read-only
			STATUS current
			DESCRIPTION
				"A textual string containing information about the
				interface.  This string should include the name of
				the manufacturer, the product name and the version
				of the hardware interface."
			::= { cardPonMibPerformEntry 2 }

		
--                          none of the following
-- T1
-- european equiv. of T1
-- proprietary serial
-- CLNP over IP [11]
-- XNS over IP
-- generic SLIP
-- ULTRA technologies
-- T3
-- SMDS
		-- 1.3.6.1.4.1.5875.800.3.54.7.1.3
		cardifType OBJECT-TYPE
			SYNTAX INTEGER
				{
				other(1),
				regular1822(2),
				hdh1822(3),
				ddn-x25(4),
				rfc877-x25(5),
				ethernet-csmacd(6),
				iso88023-csmacd(7),
				iso88024-tokenBus(8),
				iso88025-tokenRing(9),
				iso88026-man(10),
				starLan(11),
				proteon-10Mbit(12),
				proteon-80Mbit(13),
				hyperchannel(14),
				fddi(15),
				lapb(16),
				sdlc(17),
				ds1(18),
				e1(19),
				basicISDN(20),
				primaryISDN(21),
				propPointToPointSerial(22),
				ppp(23),
				softwareLoopback(24),
				eon(25),
				ethernet-3Mbit(26),
				nsip(27),
				slip(28),
				ultra(29),
				ds3(30),
				sip(31),
				frame-relay(32)
				}
			MAX-ACCESS read-only
			STATUS current
			DESCRIPTION
				"The type of interface, distinguished according to
				the physical/link protocol(s) immediately `below'
				the network layer in the protocol stack."
			::= { cardPonMibPerformEntry 3 }

				-- 1.3.6.1.4.1.5875.800.3.54.7.1.4
		cardifMtu OBJECT-TYPE
			SYNTAX INTEGER
			MAX-ACCESS read-only
			STATUS current
			DESCRIPTION
				"The size of the largest datagram which can be
				sent/received on the interface, specified in
				octets.  For interfaces that are used for
				transmitting network datagrams, this is the size
				of the largest network datagram that can be sent
				on the interface."
			::= { cardPonMibPerformEntry 4 }

				-- 1.3.6.1.4.1.5875.800.3.54.7.1.5
		cardifSpeed OBJECT-TYPE
			SYNTAX INTEGER
			MAX-ACCESS read-only
			STATUS current
			DESCRIPTION
				"An estimate of the interface's current bandwidth
				in bits per second.  For interfaces which do not
				vary in bandwidth or for those where no accurate
				estimation can be made, this object should contain
				the nominal bandwidth."
			::= { cardPonMibPerformEntry 5 }

				-- 1.3.6.1.4.1.5875.800.3.54.7.1.6
		cardifPhysAddress OBJECT-TYPE
			SYNTAX PhysAddress
			MAX-ACCESS read-only
			STATUS current
			DESCRIPTION
				"The interface's address at the protocol layer
				immediately `below' the network layer in the
				protocol stack.  For interfaces which do not have
				such an address (e.g., a serial line), this object
				should contain an octet string of zero length."
			::= { cardPonMibPerformEntry 6 }

		
--                          ready to pass packets
-- in some test mode
		-- 1.3.6.1.4.1.5875.800.3.54.7.1.7
		cardifAdminStatus OBJECT-TYPE
			SYNTAX INTEGER
				{
				up(1),
				down(2),
				testing(3)
				}
			MAX-ACCESS read-write
			STATUS current
			DESCRIPTION
				"The desired state of the interface.  The
				testing(3) state indicates that no operational
				packets can be passed."
			::= { cardPonMibPerformEntry 7 }

		
--                          ready to pass packets
-- in some test mode
		-- 1.3.6.1.4.1.5875.800.3.54.7.1.8
		cardifOperStatus OBJECT-TYPE
			SYNTAX INTEGER
				{
				up(1),
				down(2),
				testing(3)
				}
			MAX-ACCESS read-only
			STATUS current
			DESCRIPTION
				"The current operational state of the interface.
				The testing(3) state indicates that no operational
				packets can be passed."
			::= { cardPonMibPerformEntry 8 }

				-- 1.3.6.1.4.1.5875.800.3.54.7.1.9
		cardifLastChange OBJECT-TYPE
			SYNTAX TimeTicks
			MAX-ACCESS read-only
			STATUS current
			DESCRIPTION
				"The value of sysUpTime at the time the interface
				entered its current operational state.  If the
				current state was entered prior to the last re-
				initialization of the local network management
				subsystem, then this object contains a zero
				value."
			::= { cardPonMibPerformEntry 9 }

				-- 1.3.6.1.4.1.5875.800.3.54.7.1.10
		cardifInOctets OBJECT-TYPE
			SYNTAX INTEGER
			MAX-ACCESS read-only
			STATUS current
			DESCRIPTION
				"The total number of octets received on the
				interface, including framing characters."
			::= { cardPonMibPerformEntry 10 }

				-- 1.3.6.1.4.1.5875.800.3.54.7.1.11
		cardifInUcastPkts OBJECT-TYPE
			SYNTAX INTEGER
			MAX-ACCESS read-only
			STATUS current
			DESCRIPTION
				"The number of subnetwork-unicast packets
				delivered to a higher-layer protocol."
			::= { cardPonMibPerformEntry 11 }

				-- 1.3.6.1.4.1.5875.800.3.54.7.1.12
		cardifInNUcastPkts OBJECT-TYPE
			SYNTAX INTEGER
			MAX-ACCESS read-only
			STATUS current
			DESCRIPTION
				"The number of non-unicast (i.e., subnetwork-
				broadcast or subnetwork-multicast) packets
				delivered to a higher-layer protocol."
			::= { cardPonMibPerformEntry 12 }

				-- 1.3.6.1.4.1.5875.800.3.54.7.1.13
		cardifInDiscards OBJECT-TYPE
			SYNTAX INTEGER
			MAX-ACCESS read-only
			STATUS current
			DESCRIPTION
				"The number of inbound packets which were chosen
				to be discarded even though no errors had been
				detected to prevent their being deliverable to a
				higher-layer protocol.  One possible reason for
				discarding such a packet could be to free up
				buffer space."
			::= { cardPonMibPerformEntry 13 }

				-- 1.3.6.1.4.1.5875.800.3.54.7.1.14
		cardifInErrors OBJECT-TYPE
			SYNTAX INTEGER
			MAX-ACCESS read-only
			STATUS current
			DESCRIPTION
				"The number of inbound packets that contained
				errors preventing them from being deliverable to a
				higher-layer protocol."
			::= { cardPonMibPerformEntry 14 }

				-- 1.3.6.1.4.1.5875.800.3.54.7.1.15
		cardifInUnknownProtos OBJECT-TYPE
			SYNTAX INTEGER
			MAX-ACCESS read-only
			STATUS current
			DESCRIPTION
				"The number of packets received via the interface
				which were discarded because of an unknown or
				unsupported protocol."
			::= { cardPonMibPerformEntry 15 }

				-- 1.3.6.1.4.1.5875.800.3.54.7.1.16
		cardifOutOctets OBJECT-TYPE
			SYNTAX INTEGER
			MAX-ACCESS read-only
			STATUS current
			DESCRIPTION
				"The total number of octets transmitted out of the
				interface, including framing characters."
			::= { cardPonMibPerformEntry 16 }

				-- 1.3.6.1.4.1.5875.800.3.54.7.1.17
		cardifOutUcastPkts OBJECT-TYPE
			SYNTAX INTEGER
			MAX-ACCESS read-only
			STATUS current
			DESCRIPTION
				"The total number of packets that higher-level
				protocols requested be transmitted to a
				subnetwork-unicast address, including those that
				were discarded or not sent."
			::= { cardPonMibPerformEntry 17 }

				-- 1.3.6.1.4.1.5875.800.3.54.7.1.18
		cardifOutNUcastPkts OBJECT-TYPE
			SYNTAX INTEGER
			MAX-ACCESS read-only
			STATUS current
			DESCRIPTION
				"The total number of packets that higher-level
				protocols requested be transmitted to a non-
				unicast (i.e., a subnetwork-broadcast or
				subnetwork-multicast) address, including those
				that were discarded or not sent."
			::= { cardPonMibPerformEntry 18 }

				-- 1.3.6.1.4.1.5875.800.3.54.7.1.19
		cardifOutDiscards OBJECT-TYPE
			SYNTAX INTEGER
			MAX-ACCESS read-only
			STATUS current
			DESCRIPTION
				"The number of outbound packets which were chosen
				to be discarded even though no errors had been
				detected to prevent their being transmitted.  One
				possible reason for discarding such a packet could
				be to free up buffer space."
			::= { cardPonMibPerformEntry 19 }

				-- 1.3.6.1.4.1.5875.800.3.54.7.1.20
		cardifOutErrors OBJECT-TYPE
			SYNTAX INTEGER
			MAX-ACCESS read-only
			STATUS current
			DESCRIPTION
				"The number of outbound packets that could not be
				transmitted because of errors."
			::= { cardPonMibPerformEntry 20 }

				-- 1.3.6.1.4.1.5875.800.3.54.7.1.21
		cardinflowsBIP OBJECT-TYPE
			SYNTAX Integer32 (0..1024)
			MAX-ACCESS read-only
			STATUS current
			DESCRIPTION
				"Port Traffic Collection Extending Part"
			::= { cardPonMibPerformEntry 21 }

				-- 1.3.6.1.4.1.5875.800.3.54.7.1.22
		cardoutflowsBIP OBJECT-TYPE
			SYNTAX Integer32 (0..1024)
			MAX-ACCESS read-only
			STATUS current
			DESCRIPTION
				"Port Traffic Collection Extending Part"
			::= { cardPonMibPerformEntry 22 }

				-- 1.3.6.1.4.1.5875.800.3.54.7.1.32
		cardifOutMulticastPkts OBJECT-TYPE
			SYNTAX Counter32
			MAX-ACCESS read-only
			STATUS current
			DESCRIPTION
				"The total number of packets that higher-level protocols
				requested be transmitted, and which were addressed to a
				multicast address at this sub-layer, including those that
				were discarded or not sent.  For a MAC layer protocol, this
				includes both Group and Functional addresses.
				
				Discontinuities in the value of this counter can occur at
				re-initialization of the management system, and at other
				times as indicated by the value of
				ifCounterDiscontinuityTime."
			::= { cardPonMibPerformEntry 32 }

				-- 1.3.6.1.4.1.5875.800.3.54.7.1.33
		cardifInBroadcastPkts OBJECT-TYPE
			SYNTAX Counter32
			MAX-ACCESS read-only
			STATUS current
			DESCRIPTION
				"The number of packets, delivered by this sub-layer to a
				higher (sub-)layer, which were addressed to a broadcast
				address at this sub-layer.
				
				Discontinuities in the value of this counter can occur at
				re-initialization of the management system, and at other
				times as indicated by the value of
				ifCounterDiscontinuityTime."
			::= { cardPonMibPerformEntry 33 }

				-- 1.3.6.1.4.1.5875.800.3.54.7.1.34
		cardifInMulticastPkts OBJECT-TYPE
			SYNTAX Counter32
			MAX-ACCESS read-only
			STATUS current
			DESCRIPTION
				"The number of packets, delivered by this sub-layer to a
				higher (sub-)layer, which were addressed to a multicast
				address at this sub-layer.  For a MAC layer protocol, this
				includes both Group and Functional addresses.
				
				Discontinuities in the value of this counter can occur at
				re-initialization of the management system, and at other
				
				
				times as indicated by the value of
				ifCounterDiscontinuityTime."
			::= { cardPonMibPerformEntry 34 }

				-- 1.3.6.1.4.1.5875.800.3.54.7.1.35
		cardifOutBroadcastPkts OBJECT-TYPE
			SYNTAX Counter32
			MAX-ACCESS read-only
			STATUS current
			DESCRIPTION
				"The total number of packets that higher-level protocols
				requested be transmitted, and which were addressed to a
				broadcast address at this sub-layer, including those that
				were discarded or not sent.
				
				Discontinuities in the value of this counter can occur at
				re-initialization of the management system, and at other
				
				
				times as indicated by the value of
				ifCounterDiscontinuityTime."
			::= { cardPonMibPerformEntry 35 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.36
		cardifHCInOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 36 }

				-- 1.3.6.1.4.1.5875.800.3.54.7.1.37
		cardifHCInUcastPkts OBJECT-TYPE
			SYNTAX Counter64
			MAX-ACCESS read-only
			STATUS current
			DESCRIPTION
				"The number of packets, delivered by this sub-layer to a
				higher (sub-)layer, which were not addressed to a multicast
				or broadcast address at this sub-layer.  This object is a
				64-bit version of ifInUcastPkts.
				
				Discontinuities in the value of this counter can occur at
				re-initialization of the management system, and at other
				times as indicated by the value of
				ifCounterDiscontinuityTime."
			::= { cardPonMibPerformEntry 37 }

				-- 1.3.6.1.4.1.5875.800.3.54.7.1.38
		cardifHCInMulticastPkts OBJECT-TYPE
			SYNTAX Counter64
			MAX-ACCESS read-only
			STATUS current
			DESCRIPTION
				"The number of packets, delivered by this sub-layer to a
				higher (sub-)layer, which were addressed to a multicast
				address at this sub-layer.  For a MAC layer protocol, this
				includes both Group and Functional addresses.  This object
				is a 64-bit version of ifInMulticastPkts.
				
				Discontinuities in the value of this counter can occur at
				re-initialization of the management system, and at other
				times as indicated by the value of
				ifCounterDiscontinuityTime."
			::= { cardPonMibPerformEntry 38 }

				-- 1.3.6.1.4.1.5875.800.3.54.7.1.39
		cardifHCInBroadcastPkts OBJECT-TYPE
			SYNTAX Counter64
			MAX-ACCESS read-only
			STATUS current
			DESCRIPTION
				"The number of packets, delivered by this sub-layer to a
				higher (sub-)layer, which were addressed to a broadcast
				address at this sub-layer.  This object is a 64-bit version
				of ifInBroadcastPkts.
				
				Discontinuities in the value of this counter can occur at
				re-initialization of the management system, and at other
				times as indicated by the value of
				ifCounterDiscontinuityTime."
			::= { cardPonMibPerformEntry 39 }

				-- 1.3.6.1.4.1.5875.800.3.54.7.1.40
		cardifHCOutOctets OBJECT-TYPE
			SYNTAX Counter64
			MAX-ACCESS read-only
			STATUS current
			DESCRIPTION
				"The total number of octets transmitted out of the
				interface, including framing characters.  This object is a
				64-bit version of ifOutOctets.
				
				Discontinuities in the value of this counter can occur at
				re-initialization of the management system, and at other
				times as indicated by the value of
				ifCounterDiscontinuityTime."
			::= { cardPonMibPerformEntry 40 }

				-- 1.3.6.1.4.1.5875.800.3.54.7.1.41
		cardifHCOutUcastPkts OBJECT-TYPE
			SYNTAX Counter64
			MAX-ACCESS read-only
			STATUS current
			DESCRIPTION
				"The total number of packets that higher-level protocols
				requested be transmitted, and which were not addressed to a
				multicast or broadcast address at this sub-layer, including
				those that were discarded or not sent.  This object is a
				64-bit version of ifOutUcastPkts.
				
				Discontinuities in the value of this counter can occur at
				re-initialization of the management system, and at other
				times as indicated by the value of
				ifCounterDiscontinuityTime."
			::= { cardPonMibPerformEntry 41 }

				-- 1.3.6.1.4.1.5875.800.3.54.7.1.42
		cardifHCOutMulticastPkts OBJECT-TYPE
			SYNTAX Counter64
			MAX-ACCESS read-only
			STATUS current
			DESCRIPTION
				"The total number of packets that higher-level protocols
				requested be transmitted, and which were addressed to a
				multicast address at this sub-layer, including those that
				were discarded or not sent.  For a MAC layer protocol, this
				includes both Group and Functional addresses.  This object
				is a 64-bit version of ifOutMulticastPkts.
				
				Discontinuities in the value of this counter can occur at
				re-initialization of the management system, and at other
				times as indicated by the value of
				ifCounterDiscontinuityTime."
			::= { cardPonMibPerformEntry 42 }

				-- 1.3.6.1.4.1.5875.800.3.54.7.1.43
		cardifHCOutBroadcastPkts OBJECT-TYPE
			SYNTAX Counter64
			MAX-ACCESS read-only
			STATUS current
			DESCRIPTION
				"The total number of packets that higher-level protocols
				requested be transmitted, and which were addressed to a
				broadcast address at this sub-layer, including those that
				were discarded or not sent.  This object is a 64-bit version
				of ifOutBroadcastPkts.
				
				Discontinuities in the value of this counter can occur at
				re-initialization of the management system, and at other
				times as indicated by the value of
				ifCounterDiscontinuityTime."
			::= { cardPonMibPerformEntry 43 }

				-- 1.3.6.1.4.1.5875.800.3.54.7.1.44
		cardifLinkUpDownTrapEnable OBJECT-TYPE
			SYNTAX INTEGER
				{
				enabled(1),
				disabled(2)
				}
			MAX-ACCESS read-write
			STATUS current
			DESCRIPTION
				"Indicates whether linkUp/linkDown traps should be generated
				for this interface.
				
				By default, this object should have the value enabled(1) for
				interfaces which do not operate on 'top' of any other
				interface (as defined in the ifStackTable), and disabled(2)
				otherwise."
			::= { cardPonMibPerformEntry 44 }

				-- 1.3.6.1.4.1.5875.800.3.54.7.1.45
		cardifHighSpeed OBJECT-TYPE
			SYNTAX Gauge32
			MAX-ACCESS read-only
			STATUS current
			DESCRIPTION
				"An estimate of the interface's current bandwidth in units
				of 1,000,000 bits per second.  If this object reports a
				value of `n' then the speed of the interface is somewhere in
				the range of `n-500,000' to `n+499,999'.  For interfaces
				which do not vary in bandwidth or for those where no
				accurate estimation can be made, this object should contain
				the nominal bandwidth.  For a sub-layer which has no concept
				of bandwidth, this object should be zero."
			::= { cardPonMibPerformEntry 45 }

				-- 1.3.6.1.4.1.5875.800.3.54.7.1.46
		cardifPromiscuousMode OBJECT-TYPE
			SYNTAX TruthValue
			MAX-ACCESS read-write
			STATUS current
			DESCRIPTION
				"This object has a value of false(2) if this interface only
				accepts packets/frames that are addressed to this station.
				This object has a value of true(1) when the station accepts
				all packets/frames transmitted on the media.  The value
				true(1) is only legal on certain types of media.  If legal,
				setting this object to a value of true(1) may require the
				interface to be reset before becoming effective.
				
				The value of ifPromiscuousMode does not affect the reception
				of broadcast and multicast packets/frames by the interface."
			::= { cardPonMibPerformEntry 46 }

				-- 1.3.6.1.4.1.5875.800.3.54.7.1.47
		cardifConnectorPresent OBJECT-TYPE
			SYNTAX TruthValue
			MAX-ACCESS read-only
			STATUS current
			DESCRIPTION
				"This object has the value 'true(1)' if the interface
				sublayer has a physical connector and the value 'false(2)'
				otherwise."
			::= { cardPonMibPerformEntry 47 }

				-- 1.3.6.1.4.1.5875.800.3.54.7.1.48
		cardifAlias OBJECT-TYPE
			SYNTAX DisplayString (SIZE (0..64))
			MAX-ACCESS read-write
			STATUS current
			DESCRIPTION
				"This object is an 'alias' name for the interface as
				specified by a network manager, and provides a non-volatile
				'handle' for the interface.
				
				On the first instantiation of an interface, the value of
				ifAlias associated with that interface is the zero-length
				string.  As and when a value is written into an instance of
				ifAlias through a network management set operation, then the
				agent must retain the supplied value in the ifAlias instance
				associated with the same interface for as long as that
				interface remains instantiated, including across all re-
				initializations/reboots of the network management system,
				including those which result in a change of the interface's
				ifIndex value.
				
				An example of the value which a network manager might store
				in this object for a WAN interface is the (Telco's) circuit
				number/identifier of the interface.
				
				Some agents may support write-access only for interfaces
				having particular values of ifType.  An agent which supports
				write access to this object is required to keep the value in
				non-volatile storage, but it may limit the length of new
				values depending on how much storage is already occupied by
				the current values for other interfaces."
			::= { cardPonMibPerformEntry 48 }

				-- 1.3.6.1.4.1.5875.800.3.54.7.1.49
		cardifCounterDiscontinuityTime OBJECT-TYPE
			SYNTAX TimeStamp
			MAX-ACCESS read-only
			STATUS current
			DESCRIPTION
				"The value of sysUpTime on the most recent occasion at which
				any one or more of this interface's counters suffered a
				discontinuity.  The relevant counters are the specific
				instances associated with this interface of any Counter32 or
				
				
				Counter64 object contained in the ifTable or ifXTable.  If
				no such discontinuities have occurred since the last re-
				initialization of the local management subsystem, then this
				object contains a zero value."
			::= { cardPonMibPerformEntry 49 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.50
		cardferfRecvGoodPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 50 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.51
		cardferfRecvDiscardedPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 51 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.52
		cardferfRecvErrorPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 52 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.53
		cardferfSendGoodPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 53 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.54
		cardferfSendDiscardedPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 54 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.55
		cardferfSendErrorPackageOctets OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 55 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.56
		cardferfRecv64OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 56 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.57
		cardferfRecv65to127OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 57 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.58
		cardferfRecv128to255OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 58 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.59
		cardferfRecv256to511OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 59 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.60
		cardferfRecv512to1023OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 60 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.61
		cardferfRecv1024to1518OctetsLenPkts OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 61 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.62
		cardferfLossSignalSeconds OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 62 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.63
		cardferfErroredSeconds OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 63 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.64
		cardferfSeverelyErroredSeconds OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 64 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.65
		cardferfUnavailableSeconds OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 65 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.66
		cardferfDetectMonitorDiscardPacketNumber OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 66 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.67
		cardferfRecvPauseFlowControlFrames OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 67 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.68
		cardferfSendPauseFlowControlFrames OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 68 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.69
		cardferfChecksumErrors OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 69 }

				-- 1.3.6.1.4.1.5875.800.3.54.7.1.70
		cardferfFcsFrameCheckErrors OBJECT-TYPE
			SYNTAX INTEGER
			MAX-ACCESS read-only
			STATUS current
			DESCRIPTION
				"The total number of octets received on the
				interface, including framing characters."
			::= { cardPonMibPerformEntry 70 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.71
		cardferfExcessiveCollisionStatistics OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 71 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.72
		cardferfSingleCollisionSendOkFrames OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 72 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.73
		cardferfMultipleCollisionsSendOkFrames OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 73 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.74
		cardferfPortInFlow OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 74 }

		
--                          High Capacity Counter objects.  These objects are all
-- 64 bit versions of the "basic" ifTable counters.  These
-- objects all have the same basic semantics as their 32bit
-- counterparts, however, their syntax has been extended
-- to 64 bits.
 		-- 1.3.6.1.4.1.5875.800.3.54.7.1.75
		cardferfPortOnuFlow OBJECT-TYPE
			SYNTAX Counter64
			MAX-ACCESS read-only
			STATUS current
			DESCRIPTION
				"The total number of octets received on the interface,
				including framing characters.  This object is a 64-bit
				version of ifInOctets.
				
				Discontinuities in the value of this counter can occur at
				re-initialization of the management system, and at other
				times as indicated by the value of
				ifCounterDiscontinuityTime."
			::= { cardPonMibPerformEntry 75 }

				-- 1.3.6.1.4.1.5875.800.3.55
		onuWanServiceBwProfileQuery OBJECT IDENTIFIER ::= { oltData 55 }

				-- 1.3.6.1.4.1.5875.800.3.55.1
		onuWanServiceBwProfileQueryTable OBJECT-TYPE
			SYNTAX SEQUENCE OF OnuWanServiceBwProfileQueryEntry
			MAX-ACCESS not-accessible
			STATUS current
			DESCRIPTION
				"Description."
			::= { onuWanServiceBwProfileQuery 1 }

				-- 1.3.6.1.4.1.5875.800.3.55.1.1
		onuWanServiceBwProfileQueryEntry OBJECT-TYPE
			SYNTAX OnuWanServiceBwProfileQueryEntry
			MAX-ACCESS not-accessible
			STATUS current
			DESCRIPTION
				"Description."
			INDEX { onuIndex, onuwanIndex }
			::= { onuWanServiceBwProfileQueryTable 1 }

		
		OnuWanServiceBwProfileQueryEntry ::=
			SEQUENCE { 
				onuwanIndex
					Integer32,
				upBwProfileID
					Integer32,
				downBwProfileID
					Integer32
			 }
		-- 1.3.6.1.4.1.5875.800.3.55.1.1.1
		onuwanIndex OBJECT-TYPE
			SYNTAX Integer32 (0..8)
			MAX-ACCESS not-accessible
			STATUS current
			DESCRIPTION
				"Index (0-8)"
			::= { onuWanServiceBwProfileQueryEntry 1 }

				-- 1.3.6.1.4.1.5875.800.3.55.1.1.2
		upBwProfileID OBJECT-TYPE
			SYNTAX Integer32 (0..1024)
			MAX-ACCESS read-only
			STATUS current
			DESCRIPTION
				"0-1024"
			::= { onuWanServiceBwProfileQueryEntry 2 }

				-- 1.3.6.1.4.1.5875.800.3.55.1.1.3
		downBwProfileID OBJECT-TYPE
			SYNTAX Integer32 (0..1024)
			MAX-ACCESS read-only
			STATUS current
			DESCRIPTION
				"0-1024"
			::= { onuWanServiceBwProfileQueryEntry 3 }

				-- 1.3.6.1.4.1.5875.800.3.56
		qryOnuWhiteList OBJECT IDENTIFIER ::= { oltData 56 }

				-- 1.3.6.1.4.1.5875.800.3.56.1
		qryOnuPhyPasswdWhiteListTable OBJECT-TYPE
			SYNTAX SEQUENCE OF QryOnuPhyPasswdWhiteListEntry
			MAX-ACCESS not-accessible
			STATUS current
			DESCRIPTION
				"Description."
			::= { qryOnuWhiteList 1 }

				-- 1.3.6.1.4.1.5875.800.3.56.1.1
		qryOnuPhyPasswdWhiteListEntry OBJECT-TYPE
			SYNTAX QryOnuPhyPasswdWhiteListEntry
			MAX-ACCESS not-accessible
			STATUS current
			DESCRIPTION
				"Description."
			INDEX { passwdIndex }
			::= { qryOnuPhyPasswdWhiteListTable 1 }

		
		QryOnuPhyPasswdWhiteListEntry ::=
			SEQUENCE { 
				passwdIndex
					OCTET STRING,
				onuIdForWhiteList
					Integer32,
				passwdIdForWhiteList
					Integer32,
				slotForWhiteList
					Integer32,
				ponForWhiteList
					Integer32
			 }
		-- 1.3.6.1.4.1.5875.800.3.56.1.1.1
		passwdIndex OBJECT-TYPE
			SYNTAX OCTET STRING
			MAX-ACCESS read-only
			STATUS current
			DESCRIPTION
				"Description."
			::= { qryOnuPhyPasswdWhiteListEntry 1 }

				-- 1.3.6.1.4.1.5875.800.3.56.1.1.2
		onuIdForWhiteList OBJECT-TYPE
			SYNTAX Integer32
			MAX-ACCESS read-only
			STATUS current
			DESCRIPTION
				"Description."
			::= { qryOnuPhyPasswdWhiteListEntry 2 }

				-- 1.3.6.1.4.1.5875.800.3.56.1.1.3
		passwdIdForWhiteList OBJECT-TYPE
			SYNTAX Integer32
			MAX-ACCESS read-only
			STATUS current
			DESCRIPTION
				"Description."
			::= { qryOnuPhyPasswdWhiteListEntry 3 }

				-- 1.3.6.1.4.1.5875.800.3.56.1.1.4
		slotForWhiteList OBJECT-TYPE
			SYNTAX Integer32
			MAX-ACCESS read-only
			STATUS current
			DESCRIPTION
				"Description."
			::= { qryOnuPhyPasswdWhiteListEntry 4 }

				-- 1.3.6.1.4.1.5875.800.3.56.1.1.5
		ponForWhiteList OBJECT-TYPE
			SYNTAX Integer32
			MAX-ACCESS read-only
			STATUS current
			DESCRIPTION
				"Description."
			::= { qryOnuPhyPasswdWhiteListEntry 5 }

				-- 1.3.6.1.4.1.5875.800.3.57
		businessMode OBJECT IDENTIFIER ::= { oltData 57 }

				-- 1.3.6.1.4.1.5875.800.3.57.1
		businessModeTable OBJECT-TYPE
			SYNTAX SEQUENCE OF BusinessModeEntry
			MAX-ACCESS not-accessible
			STATUS current
			DESCRIPTION
				"Description."
			::= { businessMode 1 }

				-- 1.3.6.1.4.1.5875.800.3.57.1.1
		businessModeEntry OBJECT-TYPE
			SYNTAX BusinessModeEntry
			MAX-ACCESS not-accessible
			STATUS current
			DESCRIPTION
				"Description."
			INDEX { busiModeID }
			::= { businessModeTable 1 }

		
		BusinessModeEntry ::=
			SEQUENCE { 
				busiModeID
					Integer32,
				businessModeName
					OCTET STRING,
				businessModeServiceType
					Integer32,
				businessModeCVlanType
					Integer32,
				businessModeTranState
					Integer32,
				businessModeQinQState
					Integer32
			 }
		-- 1.3.6.1.4.1.5875.800.3.57.1.1.1
		busiModeID OBJECT-TYPE
			SYNTAX Integer32 (1..64)
			MAX-ACCESS read-only
			STATUS current
			DESCRIPTION
				"Business mode ID (Index)
				Index 1 to 64"
			::= { businessModeEntry 1 }

				-- 1.3.6.1.4.1.5875.800.3.57.1.1.2
		businessModeName OBJECT-TYPE
			SYNTAX OCTET STRING (SIZE (0..20))
			MAX-ACCESS read-only
			STATUS current
			DESCRIPTION
				"Business mode name
				
				No more than 20 bytes"
			::= { businessModeEntry 2 }

				-- 1.3.6.1.4.1.5875.800.3.57.1.1.3
		businessModeServiceType OBJECT-TYPE
			SYNTAX Integer32 (0..2)
			MAX-ACCESS read-only
			STATUS current
			DESCRIPTION
				"Service type
				0-nicast
				1-multicast
				2-IGMP Up Protocol"
			::= { businessModeEntry 3 }

				-- 1.3.6.1.4.1.5875.800.3.57.1.1.4
		businessModeCVlanType OBJECT-TYPE
			SYNTAX Integer32 (1 | 3)
			MAX-ACCESS read-only
			STATUS current
			DESCRIPTION
				"Cvlan type
				1-tag
				3-transparent
				"
			::= { businessModeEntry 4 }

				-- 1.3.6.1.4.1.5875.800.3.57.1.1.5
		businessModeTranState OBJECT-TYPE
			SYNTAX Integer32 (0..1)
			MAX-ACCESS read-only
			STATUS current
			DESCRIPTION
				"Translation state
				0-disable
				1-enable"
			::= { businessModeEntry 5 }

				-- 1.3.6.1.4.1.5875.800.3.57.1.1.6
		businessModeQinQState OBJECT-TYPE
			SYNTAX Integer32 (0..1)
			MAX-ACCESS read-only
			STATUS current
			DESCRIPTION
				"QinQ state
				0-disable
				1-enable"
			::= { businessModeEntry 6 }

				-- 1.3.6.1.4.1.5875.800.3.58
		wanIPReturn OBJECT IDENTIFIER ::= { oltData 58 }

				-- 1.3.6.1.4.1.5875.800.3.58.1
		wanIPReturnTable OBJECT-TYPE
			SYNTAX SEQUENCE OF WanIPReturnEntry
			MAX-ACCESS not-accessible
			STATUS current
			DESCRIPTION
				"Description."
			::= { wanIPReturn 1 }

				-- 1.3.6.1.4.1.5875.800.3.58.1.1
		wanIPReturnEntry OBJECT-TYPE
			SYNTAX WanIPReturnEntry
			MAX-ACCESS not-accessible
			STATUS current
			DESCRIPTION
				"Description."
			INDEX { onuIndex, wanIndex }
			::= { wanIPReturnTable 1 }

		
		WanIPReturnEntry ::=
			SEQUENCE { 
				getWanIPv4
					OCTET STRING,
				getWanIPv6
					OCTET STRING
			 }
		-- 1.3.6.1.4.1.5875.800.3.58.1.1.1
		getWanIPv4 OBJECT-TYPE
			SYNTAX OCTET STRING
			MAX-ACCESS read-only
			STATUS current
			DESCRIPTION
				"Description.
				IPv4:
				0-100"
			::= { wanIPReturnEntry 1 }

				-- 1.3.6.1.4.1.5875.800.3.58.1.1.2
		getWanIPv6 OBJECT-TYPE
			SYNTAX OCTET STRING
			MAX-ACCESS read-only
			STATUS current
			DESCRIPTION
				"Description.
				IPv6:
				0-200"
			::= { wanIPReturnEntry 2 }

				-- 1.3.6.1.4.1.5875.800.3.59
		onuMACReplace OBJECT IDENTIFIER ::= { oltData 59 }

				-- 1.3.6.1.4.1.5875.800.3.59.1
		onuMACReplaceTable OBJECT-TYPE
			SYNTAX SEQUENCE OF OnuMACReplaceEntry
			MAX-ACCESS not-accessible
			STATUS current
			DESCRIPTION
				"Description"
			::= { onuMACReplace 1 }

				-- 1.3.6.1.4.1.5875.800.3.59.1.1
		onuMACReplaceEntry OBJECT-TYPE
			SYNTAX OnuMACReplaceEntry
			MAX-ACCESS not-accessible
			STATUS current
			DESCRIPTION
				"Row Description"
			INDEX { onuIndex }
			::= { onuMACReplaceTable 1 }

		
		OnuMACReplaceEntry ::=
			SEQUENCE { 
				onuMACReplaceSlot
					Integer32,
				onuMACReplacePon
					Integer32,
				onuMACReplaceOnuId
					Integer32,
				onuMACReplaceMACBefore
					OCTET STRING,
				onuMACReplaceNewMACaddress
					OCTET STRING,
				onuMACReplaceStatus
					Integer32
			 }
		-- 1.3.6.1.4.1.5875.800.3.59.1.1.1
		onuMACReplaceSlot OBJECT-TYPE
			SYNTAX Integer32
			MAX-ACCESS read-only
			STATUS current
			DESCRIPTION
				"Slot number"
			::= { onuMACReplaceEntry 1 }

				-- 1.3.6.1.4.1.5875.800.3.59.1.1.2
		onuMACReplacePon OBJECT-TYPE
			SYNTAX Integer32
			MAX-ACCESS read-only
			STATUS current
			DESCRIPTION
				"Pon number"
			::= { onuMACReplaceEntry 2 }

				-- 1.3.6.1.4.1.5875.800.3.59.1.1.3
		onuMACReplaceOnuId OBJECT-TYPE
			SYNTAX Integer32
			MAX-ACCESS read-only
			STATUS current
			DESCRIPTION
				"Onu number"
			::= { onuMACReplaceEntry 3 }

				-- 1.3.6.1.4.1.5875.800.3.59.1.1.5
		onuMACReplaceMACBefore OBJECT-TYPE
			SYNTAX OCTET STRING
			MAX-ACCESS read-create
			STATUS current
			DESCRIPTION
				"Length must be 12 bytes, if it is GPON ONU,the last 8 characters must be 0-9 or a-f"
			::= { onuMACReplaceEntry 5 }

				-- 1.3.6.1.4.1.5875.800.3.59.1.1.6
		onuMACReplaceNewMACaddress OBJECT-TYPE
			SYNTAX OCTET STRING
			MAX-ACCESS read-create
			STATUS current
			DESCRIPTION
				"Length must be 12 bytes, if it is GPON ONU,the last 8 characters must be 0-9 or a-f"
			::= { onuMACReplaceEntry 6 }

				-- 1.3.6.1.4.1.5875.800.3.59.1.1.8
		onuMACReplaceStatus OBJECT-TYPE
			SYNTAX Integer32 (0..1)
			MAX-ACCESS read-create
			STATUS current
			DESCRIPTION
				"Description:
				4: replace
				Replace the old MAC with the new MAC;
				
				6: delete
				Connect to the new ONU MAC before you can delete this configuration, cancel the replacement."
			::= { onuMACReplaceEntry 8 }

				-- 1.3.6.1.4.1.5875.800.3.60
		alarmStatus OBJECT IDENTIFIER ::= { oltData 60 }

				-- 1.3.6.1.4.1.5875.800.3.60.1
		powerAlarmStatusTable OBJECT-TYPE
			SYNTAX SEQUENCE OF PowerAlarmStatusEntry
			MAX-ACCESS not-accessible
			STATUS current
			DESCRIPTION
				"Description"
			::= { alarmStatus 1 }

				-- 1.3.6.1.4.1.5875.800.3.60.1.1
		powerAlarmStatusEntry OBJECT-TYPE
			SYNTAX PowerAlarmStatusEntry
			MAX-ACCESS not-accessible
			STATUS current
			DESCRIPTION
				"Row Description"
			INDEX { powerIndex }
			::= { powerAlarmStatusTable 1 }

		
		PowerAlarmStatusEntry ::=
			SEQUENCE { 
				powerIndex
					Integer32,
				powerAlarmStatus
					INTEGER
			 }
		-- 1.3.6.1.4.1.5875.800.3.60.1.1.1
		powerIndex OBJECT-TYPE
			SYNTAX Integer32 (1..1024)
			MAX-ACCESS not-accessible
			STATUS current
			DESCRIPTION
				"Power Status"
			::= { powerAlarmStatusEntry 1 }

				-- 1.3.6.1.4.1.5875.800.3.60.1.1.2
		powerAlarmStatus OBJECT-TYPE
			SYNTAX INTEGER
				{
				normal(1),
				lowVoltage(2),
				fault(3)
				}
			MAX-ACCESS read-only
			STATUS current
			DESCRIPTION
				"1: Normal
				3: Power fault
				"
			::= { powerAlarmStatusEntry 2 }

				-- 1.3.6.1.4.1.5875.800.3.60.2
		fanAlarmStatusTable OBJECT-TYPE
			SYNTAX SEQUENCE OF FanAlarmStatusEntry
			MAX-ACCESS not-accessible
			STATUS current
			DESCRIPTION
				"Description"
			::= { alarmStatus 2 }

				-- 1.3.6.1.4.1.5875.800.3.60.2.1
		fanAlarmStatusEntry OBJECT-TYPE
			SYNTAX FanAlarmStatusEntry
			MAX-ACCESS not-accessible
			STATUS current
			DESCRIPTION
				"Row Description"
			INDEX { slotIndex }
			::= { fanAlarmStatusTable 1 }

		
		FanAlarmStatusEntry ::=
			SEQUENCE { 
				fanAlarmStatus
					INTEGER
			 }
		-- 1.3.6.1.4.1.5875.800.3.60.2.1.1
		fanAlarmStatus OBJECT-TYPE
			SYNTAX INTEGER
				{
				normal(1),
				stop(2),
				abnormity(3),
				nonChecking(4)
				}
			MAX-ACCESS read-only
			STATUS current
			DESCRIPTION
				"1: The fan is normal
				2: The fan stops rotating
				
				"
			::= { fanAlarmStatusEntry 1 }

				-- 1.3.6.1.4.1.5875.800.3.60.3
		currentAlarmTable OBJECT-TYPE
			SYNTAX SEQUENCE OF CurrentAlarmEntry
			MAX-ACCESS not-accessible
			STATUS current
			DESCRIPTION
				"Description"
			::= { alarmStatus 3 }

				-- 1.3.6.1.4.1.5875.800.3.60.3.1
		currentAlarmEntry OBJECT-TYPE
			SYNTAX CurrentAlarmEntry
			MAX-ACCESS not-accessible
			STATUS current
			DESCRIPTION
				"Row Description"
			INDEX { currentAlarmIndex }
			::= { currentAlarmTable 1 }

		
		CurrentAlarmEntry ::=
			SEQUENCE { 
				currentAlarmIndex
					Integer32,
				currentAlarmCode
					Integer32,
				currentAlarmIfIndex
					Integer32,
				currentAlarmStatus
					Integer32,
				currentAlarmStatusFlag
					Integer32,
				currentAlarmBeginTime
					DateAndTime,
				currentAlarmEndTime
					DateAndTime,
				currentAlarmType
					Integer32,
				currentAlarmAdditionalText
					OCTET STRING
			 }
		-- 1.3.6.1.4.1.5875.800.3.60.3.1.1
		currentAlarmIndex OBJECT-TYPE
			SYNTAX Integer32 (0..65535)
			MAX-ACCESS not-accessible
			STATUS current
			DESCRIPTION
				"Column Description"
			::= { currentAlarmEntry 1 }

				-- 1.3.6.1.4.1.5875.800.3.60.3.1.2
		currentAlarmCode OBJECT-TYPE
			SYNTAX Integer32
			MAX-ACCESS read-only
			STATUS current
			DESCRIPTION
				"Column Description"
			::= { currentAlarmEntry 2 }

				-- 1.3.6.1.4.1.5875.800.3.60.3.1.3
		currentAlarmIfIndex OBJECT-TYPE
			SYNTAX Integer32
			MAX-ACCESS read-only
			STATUS current
			DESCRIPTION
				"Column Description"
			::= { currentAlarmEntry 3 }

				-- 1.3.6.1.4.1.5875.800.3.60.3.1.4
		currentAlarmStatus OBJECT-TYPE
			SYNTAX Integer32
			MAX-ACCESS read-only
			STATUS current
			DESCRIPTION
				"Column Description"
			::= { currentAlarmEntry 4 }

				-- 1.3.6.1.4.1.5875.800.3.60.3.1.5
		currentAlarmStatusFlag OBJECT-TYPE
			SYNTAX Integer32
			MAX-ACCESS read-only
			STATUS current
			DESCRIPTION
				"Column Description"
			::= { currentAlarmEntry 5 }

				-- 1.3.6.1.4.1.5875.800.3.60.3.1.6
		currentAlarmBeginTime OBJECT-TYPE
			SYNTAX DateAndTime
			MAX-ACCESS read-only
			STATUS current
			DESCRIPTION
				"Column Description"
			::= { currentAlarmEntry 6 }

				-- 1.3.6.1.4.1.5875.800.3.60.3.1.7
		currentAlarmEndTime OBJECT-TYPE
			SYNTAX DateAndTime
			MAX-ACCESS read-only
			STATUS current
			DESCRIPTION
				"Column Description"
			::= { currentAlarmEntry 7 }

				-- 1.3.6.1.4.1.5875.800.3.60.3.1.8
		currentAlarmType OBJECT-TYPE
			SYNTAX Integer32
			MAX-ACCESS read-only
			STATUS current
			DESCRIPTION
				"Column Description"
			::= { currentAlarmEntry 8 }

				-- 1.3.6.1.4.1.5875.800.3.60.3.1.9
		currentAlarmAdditionalText OBJECT-TYPE
			SYNTAX OCTET STRING
			MAX-ACCESS read-only
			STATUS current
			DESCRIPTION
				"Column Description"
			::= { currentAlarmEntry 9 }

				-- 1.3.6.1.4.1.5875.800.3.60.4
		hisAlarmTable OBJECT-TYPE
			SYNTAX SEQUENCE OF HisAlarmEntry
			MAX-ACCESS not-accessible
			STATUS current
			DESCRIPTION
				"Description"
			::= { alarmStatus 4 }

				-- 1.3.6.1.4.1.5875.800.3.60.4.1
		hisAlarmEntry OBJECT-TYPE
			SYNTAX HisAlarmEntry
			MAX-ACCESS not-accessible
			STATUS current
			DESCRIPTION
				"Row Description"
			INDEX { hisAlarmIndex }
			::= { hisAlarmTable 1 }

		
		HisAlarmEntry ::=
			SEQUENCE { 
				hisAlarmIndex
					Integer32,
				hisAlarmCode
					Integer32,
				hisAlarmIfIndex
					Integer32,
				hisAlarmStatus
					Integer32,
				hisAlarmStatusFlag
					Integer32,
				hisAlarmBeginTime
					DateAndTime,
				hisAlarmEndTime
					DateAndTime,
				hisAlarmType
					Integer32,
				hisAlarmAdditionalText
					OCTET STRING
			 }
		-- 1.3.6.1.4.1.5875.800.3.60.4.1.1
		hisAlarmIndex OBJECT-TYPE
			SYNTAX Integer32 (1..65535)
			MAX-ACCESS not-accessible
			STATUS current
			DESCRIPTION
				"Column Description"
			::= { hisAlarmEntry 1 }

				-- 1.3.6.1.4.1.5875.800.3.60.4.1.2
		hisAlarmCode OBJECT-TYPE
			SYNTAX Integer32
			MAX-ACCESS read-only
			STATUS current
			DESCRIPTION
				"Column Description"
			::= { hisAlarmEntry 2 }

				-- 1.3.6.1.4.1.5875.800.3.60.4.1.3
		hisAlarmIfIndex OBJECT-TYPE
			SYNTAX Integer32
			MAX-ACCESS read-only
			STATUS current
			DESCRIPTION
				"Column Description"
			::= { hisAlarmEntry 3 }

				-- 1.3.6.1.4.1.5875.800.3.60.4.1.4
		hisAlarmStatus OBJECT-TYPE
			SYNTAX Integer32
			MAX-ACCESS read-only
			STATUS current
			DESCRIPTION
				"Column Description"
			::= { hisAlarmEntry 4 }

				-- 1.3.6.1.4.1.5875.800.3.60.4.1.5
		hisAlarmStatusFlag OBJECT-TYPE
			SYNTAX Integer32
			MAX-ACCESS read-only
			STATUS current
			DESCRIPTION
				"Column Description"
			::= { hisAlarmEntry 5 }

				-- 1.3.6.1.4.1.5875.800.3.60.4.1.6
		hisAlarmBeginTime OBJECT-TYPE
			SYNTAX DateAndTime
			MAX-ACCESS read-only
			STATUS current
			DESCRIPTION
				"Column Description"
			::= { hisAlarmEntry 6 }

				-- 1.3.6.1.4.1.5875.800.3.60.4.1.7
		hisAlarmEndTime OBJECT-TYPE
			SYNTAX DateAndTime
			MAX-ACCESS read-only
			STATUS current
			DESCRIPTION
				"Column Description"
			::= { hisAlarmEntry 7 }

				-- 1.3.6.1.4.1.5875.800.3.60.4.1.8
		hisAlarmType OBJECT-TYPE
			SYNTAX Integer32
			MAX-ACCESS read-only
			STATUS current
			DESCRIPTION
				"Column Description"
			::= { hisAlarmEntry 8 }

				-- 1.3.6.1.4.1.5875.800.3.60.4.1.9
		hisAlarmAdditionalText OBJECT-TYPE
			SYNTAX OCTET STRING
			MAX-ACCESS read-only
			STATUS current
			DESCRIPTION
				"Column Description"
			::= { hisAlarmEntry 9 }

		

		-- 1.3.6.1.4.1.5875.800.3.61
		lldp OBJECT IDENTIFIER ::= { oltData 61 }

		

		-- 1.3.6.1.4.1.5875.800.3.61.1
		lldpLocalInformation OBJECT IDENTIFIER ::= { lldp 1 }

		

		-- 1.3.6.1.4.1.5875.800.3.61.1.1
		lldpLocalStatus OBJECT IDENTIFIER ::= { lldpLocalInformation 1 }

		

		-- 1.3.6.1.4.1.5875.800.3.61.1.1.1
		lldpLocalEnableStatus OBJECT-TYPE
			SYNTAX Integer32
			MAX-ACCESS read-only
			STATUS current
			DESCRIPTION
				"1:Enable
				0:Disable"
			::= { lldpLocalStatus 1 }

		
		-- 1.3.6.1.4.1.5875.800.3.61.1.1.2
		lldpLocalManagementAddress OBJECT-TYPE
			SYNTAX OCTET STRING
			MAX-ACCESS read-only
			STATUS current
			DESCRIPTION
				"String type."
			::= { lldpLocalStatus 2 }

		
		-- 1.3.6.1.4.1.5875.800.3.61.1.1.3
		lldpLocalChassisId OBJECT-TYPE
			SYNTAX Integer32
			MAX-ACCESS read-write
			STATUS current
			DESCRIPTION
				"The max length is 32 byte."
			::= { lldpLocalStatus 3 }

		
		-- 1.3.6.1.4.1.5875.800.3.61.1.1.4
		lldpLocalSysName OBJECT-TYPE
			SYNTAX OCTET STRING
			MAX-ACCESS read-only
			STATUS current
			DESCRIPTION
				"The max length is 64 byte."
			::= { lldpLocalStatus 4 }

		
		-- 1.3.6.1.4.1.5875.800.3.61.1.1.5
		lldpLocalSysCapSupportednumber OBJECT-TYPE
			SYNTAX Integer32
			MAX-ACCESS read-only
			STATUS current
			DESCRIPTION
				"0-8"
			::= { lldpLocalStatus 5 }

		
		-- 1.3.6.1.4.1.5875.800.3.61.1.1.6
		lldpLocalSysCapEnablednumber OBJECT-TYPE
			SYNTAX Integer32
			MAX-ACCESS read-only
			STATUS current
			DESCRIPTION
				"0-8"
			::= { lldpLocalStatus 6 }

		
		-- 1.3.6.1.4.1.5875.800.3.61.1.1.7
		lldpLocalLLDPUpTime OBJECT-TYPE
			SYNTAX OCTET STRING
			MAX-ACCESS read-only
			STATUS current
			DESCRIPTION
				"The max length is 20 byte."
			::= { lldpLocalStatus 7 }

		
		-- 1.3.6.1.4.1.5875.800.3.61.1.1.8
		lldpLocalRemTablesLastChangeTime OBJECT-TYPE
			SYNTAX OCTET STRING
			MAX-ACCESS read-only
			STATUS current
			DESCRIPTION
				"The max length is 48 byte."
			::= { lldpLocalStatus 8 }

		
		-- 1.3.6.1.4.1.5875.800.3.61.1.1.9
		lldpLocalNeighborstotal OBJECT-TYPE
			SYNTAX INTEGER
			MAX-ACCESS read-only
			STATUS current
			DESCRIPTION
				"0-12"
			::= { lldpLocalStatus 9 }

		
		-- 1.3.6.1.4.1.5875.800.3.61.1.1.10
		lldpLocalPortIdNumber OBJECT-TYPE
			SYNTAX Integer32
			MAX-ACCESS read-only
			STATUS current
			DESCRIPTION
				"0-12"
			::= { lldpLocalStatus 10 }

		

		-- 1.3.6.1.4.1.5875.800.3.61.1.2
		lldpLocalSysCapSupported OBJECT IDENTIFIER ::= { lldpLocalInformation 2 }

		

		-- 1.3.6.1.4.1.5875.800.3.61.1.2.1
		lldpLocalSysCapSupportedTable OBJECT-TYPE
			SYNTAX SEQUENCE OF LldpLocalSysCapSupportedEntry
			MAX-ACCESS not-accessible
			STATUS current
			DESCRIPTION
				"Description."
			::= { lldpLocalSysCapSupported 1 }

		

		-- 1.3.6.1.4.1.5875.800.3.61.1.2.1.1
		lldpLocalSysCapSupportedEntry OBJECT-TYPE
			SYNTAX LldpLocalSysCapSupportedEntry
			MAX-ACCESS not-accessible
			STATUS current
			DESCRIPTION
				"Description."
			INDEX { lldpLocalSysCapSupportedIndex }
			::= { lldpLocalSysCapSupportedTable 1 }

		
		LldpLocalSysCapSupportedEntry ::=
			SEQUENCE { 
				lldpLocalSysCapSupportedIndex
					Integer32
			 }
		-- 1.3.6.1.4.1.5875.800.3.61.1.2.1.1.1
		lldpLocalSysCapSupportedIndex OBJECT-TYPE
			SYNTAX Integer32
			MAX-ACCESS read-only
			STATUS current
			DESCRIPTION
				"0:ChassisComponent
				1:interfaceAlias
				2:portComponent
				3:macAddress
				4:networkAddress
				5:interfaceName
				6:local"
			::= { lldpLocalSysCapSupportedEntry 1 }

		

		-- 1.3.6.1.4.1.5875.800.3.61.1.3
		lldpLocalSysCapEnabled OBJECT IDENTIFIER ::= { lldpLocalInformation 3 }

		

		-- 1.3.6.1.4.1.5875.800.3.61.1.3.1
		lldpLocalSysCapEnabledTable OBJECT-TYPE
			SYNTAX SEQUENCE OF LldpLocalSysCapEnabledEntry
			MAX-ACCESS not-accessible
			STATUS current
			DESCRIPTION
				"Description."
			::= { lldpLocalSysCapEnabled 1 }

		

		-- 1.3.6.1.4.1.5875.800.3.61.1.3.1.1
		lldpLocalSysCapEnabledEntry OBJECT-TYPE
			SYNTAX LldpLocalSysCapEnabledEntry
			MAX-ACCESS not-accessible
			STATUS current
			DESCRIPTION
				"Description."
			INDEX { lldpLocalSysCapEnabledIndex }
			::= { lldpLocalSysCapEnabledTable 1 }

		
		LldpLocalSysCapEnabledEntry ::=
			SEQUENCE { 
				lldpLocalSysCapEnabledIndex
					Integer32
			 }
		-- 1.3.6.1.4.1.5875.800.3.61.1.3.1.1.1
		lldpLocalSysCapEnabledIndex OBJECT-TYPE
			SYNTAX Integer32
			MAX-ACCESS read-only
			STATUS current
			DESCRIPTION
				"0:ChassisComponent
				1:interfaceAlias
				2:portComponent
				3:macAddress
				4:networkAddress
				5:interfaceName
				6:local"
			::= { lldpLocalSysCapEnabledEntry 1 }

		

		-- 1.3.6.1.4.1.5875.800.3.61.2
		lldpNeighborInformation OBJECT IDENTIFIER ::= { lldp 2 }

		

		-- 1.3.6.1.4.1.5875.800.3.61.2.1
		lldpNeighborStatus OBJECT IDENTIFIER ::= { lldpNeighborInformation 1 }

		

		-- 1.3.6.1.4.1.5875.800.3.61.2.1.1
		lldpNeighborStatusTable OBJECT-TYPE
			SYNTAX SEQUENCE OF LldpNeighborStatusEntry
			MAX-ACCESS not-accessible
			STATUS current
			DESCRIPTION
				"Description."
			::= { lldpNeighborStatus 1 }

		

		-- 1.3.6.1.4.1.5875.800.3.61.2.1.1.1
		lldpNeighborStatusEntry OBJECT-TYPE
			SYNTAX LldpNeighborStatusEntry
			MAX-ACCESS not-accessible
			STATUS current
			DESCRIPTION
				"Description."
			INDEX { lldpNeighborIfIndex }
			::= { lldpNeighborStatusTable 1 }

		
		LldpNeighborStatusEntry ::=
			SEQUENCE { 
				lldpNeighborIfIndex
					Integer32,
				lldpNeighborStatusPortId
					OCTET STRING,
				lldpNeighborManageAddress
					OCTET STRING,
				lldpNeighborChassisIdSubtype
					Integer32,
				lldpNeighborChassisId
					OCTET STRING,
				lldpNeighborPortIdSubtype
					Integer32,
				lldpNeighborPortId
					OCTET STRING,
				lldpNeighborPortDesc
					OCTET STRING,
				lldpNeighborSysName
					OBJECT IDENTIFIER,
				lldpNeighborSysDesc
					OBJECT IDENTIFIER,
				lldpNeighborExpiredtime
					Integer32,
				lldpNeighborSysCapSupportednumber
					Integer32,
				lldpNeighborSysCapEnablednumber
					Integer32
			 }

		-- 1.3.6.1.4.1.5875.800.3.61.2.1.1.1.1
		lldpNeighborIfIndex OBJECT-TYPE
			SYNTAX Integer32
			MAX-ACCESS read-only
			STATUS current
			DESCRIPTION
				"Description."
			::= { lldpNeighborStatusEntry 1 }
-- computational method: slot times 33554432 add port times 524288
		

		-- 1.3.6.1.4.1.5875.800.3.61.2.1.1.1.2
		lldpNeighborStatusPortId OBJECT-TYPE
			SYNTAX OCTET STRING
			MAX-ACCESS read-only
			STATUS current
			DESCRIPTION
				"The max length is 32 byte."
			::= { lldpNeighborStatusEntry 2 }

		

		-- 1.3.6.1.4.1.5875.800.3.61.2.1.1.1.3
		lldpNeighborManageAddress OBJECT-TYPE
			SYNTAX OCTET STRING
			MAX-ACCESS read-only
			STATUS current
			DESCRIPTION
				"String"
			::= { lldpNeighborStatusEntry 3 }

		

		-- 1.3.6.1.4.1.5875.800.3.61.2.1.1.1.4
		lldpNeighborChassisIdSubtype OBJECT-TYPE
			SYNTAX Integer32
			MAX-ACCESS read-only
			STATUS current
			DESCRIPTION
				"0:ChassisComponent
				1:interfaceAlias
				2:portComponent
				3:macAddress
				4:networkAddress
				5:interfaceName
				6:local"
			::= { lldpNeighborStatusEntry 4 }

		

		-- 1.3.6.1.4.1.5875.800.3.61.2.1.1.1.5
		lldpNeighborChassisId OBJECT-TYPE
			SYNTAX OCTET STRING
			MAX-ACCESS read-only
			STATUS current
			DESCRIPTION
				"The max length is 32 byte."
			::= { lldpNeighborStatusEntry 5 }

		

		-- 1.3.6.1.4.1.5875.800.3.61.2.1.1.1.6
		lldpNeighborPortIdSubtype OBJECT-TYPE
			SYNTAX Integer32
			MAX-ACCESS read-only
			STATUS current
			DESCRIPTION
				"0:ChassisComponent
				1:interfaceAlias
				2:portComponent
				3:macAddress
				4:networkAddress
				5:interfaceName
				6:local"
			::= { lldpNeighborStatusEntry 6 }

		

		-- 1.3.6.1.4.1.5875.800.3.61.2.1.1.1.7
		lldpNeighborPortId OBJECT-TYPE
			SYNTAX OCTET STRING
			MAX-ACCESS read-only
			STATUS current
			DESCRIPTION
				"The max length is 256 byte."
			::= { lldpNeighborStatusEntry 7 }

		

		-- 1.3.6.1.4.1.5875.800.3.61.2.1.1.1.8
		lldpNeighborPortDesc OBJECT-TYPE
			SYNTAX OCTET STRING
			MAX-ACCESS read-only
			STATUS current
			DESCRIPTION
				"The max length is 256 byte."
			::= { lldpNeighborStatusEntry 8 }

		

		-- 1.3.6.1.4.1.5875.800.3.61.2.1.1.1.9
		lldpNeighborSysName OBJECT-TYPE
			SYNTAX OBJECT IDENTIFIER
			MAX-ACCESS read-only
			STATUS current
			DESCRIPTION
				"The max length is 256 byte."
			::= { lldpNeighborStatusEntry 9 }

		

		-- 1.3.6.1.4.1.5875.800.3.61.2.1.1.1.10
		lldpNeighborSysDesc OBJECT-TYPE
			SYNTAX OBJECT IDENTIFIER
			MAX-ACCESS read-only
			STATUS current
			DESCRIPTION
				"The max length is 256 byte."
			::= { lldpNeighborStatusEntry 10 }

		

		-- 1.3.6.1.4.1.5875.800.3.61.2.1.1.1.11
		lldpNeighborExpiredtime OBJECT-TYPE
			SYNTAX Integer32
			MAX-ACCESS read-only
			STATUS current
			DESCRIPTION
				"Unit: Second"
			::= { lldpNeighborStatusEntry 11 }

		

		-- 1.3.6.1.4.1.5875.800.3.61.2.1.1.1.12
		lldpNeighborSysCapSupportednumber OBJECT-TYPE
			SYNTAX Integer32
			MAX-ACCESS read-only
			STATUS current
			DESCRIPTION
				"0-8"
			::= { lldpNeighborStatusEntry 12 }

		
--  0-8

		-- 1.3.6.1.4.1.5875.800.3.61.2.1.1.1.13
		lldpNeighborSysCapEnablednumber OBJECT-TYPE
			SYNTAX Integer32
			MAX-ACCESS read-only
			STATUS current
			DESCRIPTION
				"0-8"
			::= { lldpNeighborStatusEntry 13 }

		
--  0-8

		-- 1.3.6.1.4.1.5875.800.3.61.2.1.2
		lldpNeighborSysCapSupported OBJECT IDENTIFIER ::= { lldpNeighborStatus 2 }

		

		-- 1.3.6.1.4.1.5875.800.3.61.2.1.2.1
		lldpNeighborSysCapSupportedTable OBJECT-TYPE
			SYNTAX SEQUENCE OF LldpNeighborSysCapSupportedEntry
			MAX-ACCESS not-accessible
			STATUS current
			DESCRIPTION
				"Description."
			::= { lldpNeighborSysCapSupported 1 }

		

		-- 1.3.6.1.4.1.5875.800.3.61.2.1.2.1.1
		lldpNeighborSysCapSupportedEntry OBJECT-TYPE
			SYNTAX LldpNeighborSysCapSupportedEntry
			MAX-ACCESS not-accessible
			STATUS current
			DESCRIPTION
				"Description."
			INDEX { lldpNeighborSysCapSupportedIndex }
			::= { lldpNeighborSysCapSupportedTable 1 }

		
		LldpNeighborSysCapSupportedEntry ::=
			SEQUENCE { 
				lldpNeighborSysCapSupportedIndex
					Integer32
			 }
		-- 1.3.6.1.4.1.5875.800.3.61.2.1.2.1.1.1
		lldpNeighborSysCapSupportedIndex OBJECT-TYPE
			SYNTAX Integer32
			MAX-ACCESS read-only
			STATUS current
			DESCRIPTION
				"0:ChassisComponent
				1:interfaceAlias
				2:portComponent
				3:macAddress
				4:networkAddress
				5:interfaceName
				6:local"
			::= { lldpNeighborSysCapSupportedEntry 1 }

		

		-- 1.3.6.1.4.1.5875.800.3.61.2.1.3
		lldpNeighborSysCapEnabled OBJECT IDENTIFIER ::= { lldpNeighborStatus 3 }

		

		-- 1.3.6.1.4.1.5875.800.3.61.2.1.3.1
		lldpNeighborSysCapEnabledTable OBJECT-TYPE
			SYNTAX SEQUENCE OF LldpNeighborSysCapEnabledEntry
			MAX-ACCESS not-accessible
			STATUS current
			DESCRIPTION
				"Description."
			::= { lldpNeighborSysCapEnabled 1 }

		

		-- 1.3.6.1.4.1.5875.800.3.61.2.1.3.1.1
		lldpNeighborSysCapEnabledEntry OBJECT-TYPE
			SYNTAX LldpNeighborSysCapEnabledEntry
			MAX-ACCESS not-accessible
			STATUS current
			DESCRIPTION
				"Description."
			INDEX { lldpNeighborSysCapEnabledIndex }
			::= { lldpNeighborSysCapEnabledTable 1 }

		
		LldpNeighborSysCapEnabledEntry ::=
			SEQUENCE { 
				lldpNeighborSysCapEnabledIndex
					Integer32
			 }
		-- 1.3.6.1.4.1.5875.800.3.61.2.1.3.1.1.1
		lldpNeighborSysCapEnabledIndex OBJECT-TYPE
			SYNTAX Integer32
			MAX-ACCESS read-only
			STATUS current
			DESCRIPTION
				"0:ChassisComponent
				1:interfaceAlias
				2:portComponent
				3:macAddress
				4:networkAddress
				5:interfaceName
				6:local"
			::= { lldpNeighborSysCapEnabledEntry 1 }

				-- 1.3.6.1.4.1.5875.800.3.101
		objectIndex OBJECT IDENTIFIER ::= { oltData 101 }

		
		-- 1.3.6.1.4.1.5875.800.3.101.1
		slotObjectIndexTable OBJECT-TYPE
			SYNTAX SEQUENCE OF SlotObjectIndexEntry
			MAX-ACCESS not-accessible
			STATUS current
			DESCRIPTION
				"Description"
			::= { objectIndex 1 }

		
		-- 1.3.6.1.4.1.5875.800.3.101.1.1
		slotObjectIndexEntry OBJECT-TYPE
			SYNTAX SlotObjectIndexEntry
			MAX-ACCESS not-accessible
			STATUS current
			DESCRIPTION
				"Row Description"
			INDEX { slotIndex }
			::= { slotObjectIndexTable 1 }

		
		SlotObjectIndexEntry ::=
			SEQUENCE { 
				slotIndex
					Integer32
			 }

		-- 1.3.6.1.4.1.5875.800.3.101.1.1.1
		slotIndex OBJECT-TYPE
			SYNTAX Integer32 (1..1024)
			MAX-ACCESS read-only
			STATUS current
			DESCRIPTION
				"Slot Number (Index)
				1~18"
			::= { slotObjectIndexEntry 1 }

		
		-- 1.3.6.1.4.1.5875.800.3.101.2
		onuObjectIndexTable OBJECT-TYPE
			SYNTAX SEQUENCE OF OnuObjectIndexEntry
			MAX-ACCESS not-accessible
			STATUS current
			DESCRIPTION
				"Description"
			::= { objectIndex 2 }

		
		-- 1.3.6.1.4.1.5875.800.3.101.2.1
		onuObjectIndexEntry OBJECT-TYPE
			SYNTAX OnuObjectIndexEntry
			MAX-ACCESS not-accessible
			STATUS current
			DESCRIPTION
				"Row Description"
			INDEX { onuIndex }
			::= { onuObjectIndexTable 1 }

		
		OnuObjectIndexEntry ::=
			SEQUENCE { 
				onuIndex
					Unsigned32
			 }

		-- 1.3.6.1.4.1.5875.800.3.101.2.1.1
		onuIndex OBJECT-TYPE
			SYNTAX Unsigned32 (1..1024)
			MAX-ACCESS read-only
			STATUS current
			DESCRIPTION
				"ONU Number (Index)"
			::= { onuObjectIndexEntry 1 }

		
		-- 1.3.6.1.4.1.5875.800.3.101.3
		uplinkObjectIndexTable OBJECT-TYPE
			SYNTAX SEQUENCE OF UplinkObjectIndexEntry
			MAX-ACCESS not-accessible
			STATUS current
			DESCRIPTION
				"Description"
			::= { objectIndex 3 }

		
		-- 1.3.6.1.4.1.5875.800.3.101.3.1
		uplinkObjectIndexEntry OBJECT-TYPE
			SYNTAX UplinkObjectIndexEntry
			MAX-ACCESS not-accessible
			STATUS current
			DESCRIPTION
				"Row Description"
			INDEX { uplinkIndex }
			::= { uplinkObjectIndexTable 1 }

		
		UplinkObjectIndexEntry ::=
			SEQUENCE { 
				uplinkIndex
					Unsigned32
			 }

		-- 1.3.6.1.4.1.5875.800.3.101.3.1.1
		uplinkIndex OBJECT-TYPE
			SYNTAX Unsigned32 (1..1024)
			MAX-ACCESS read-only
			STATUS current
			DESCRIPTION
				"Column Description"
			::= { uplinkObjectIndexEntry 1 }

		
		-- 1.3.6.1.4.1.5875.800.3.101.4
		potsObjectIndexTable OBJECT-TYPE
			SYNTAX SEQUENCE OF PotsObjectIndexEntry
			MAX-ACCESS not-accessible
			STATUS current
			DESCRIPTION
				"Description"
			::= { objectIndex 4 }

		
		-- 1.3.6.1.4.1.5875.800.3.101.4.1
		potsObjectIndexEntry OBJECT-TYPE
			SYNTAX PotsObjectIndexEntry
			MAX-ACCESS not-accessible
			STATUS current
			DESCRIPTION
				"Row Description"
			INDEX { potsIndex }
			::= { potsObjectIndexTable 1 }

		
		PotsObjectIndexEntry ::=
			SEQUENCE { 
				potsIndex
					Unsigned32
			 }

		-- 1.3.6.1.4.1.5875.800.3.101.4.1.1
		potsIndex OBJECT-TYPE
			SYNTAX Unsigned32 (1..1024)
			MAX-ACCESS read-only
			STATUS current
			DESCRIPTION
				"Column Description"
			::= { potsObjectIndexEntry 1 }

		
		-- 1.3.6.1.4.1.5875.800.3.101.5
		portObjectIndexTable OBJECT-TYPE
			SYNTAX SEQUENCE OF PortObjectIndexEntry
			MAX-ACCESS not-accessible
			STATUS current
			DESCRIPTION
				"Description"
			::= { objectIndex 5 }

		
		-- 1.3.6.1.4.1.5875.800.3.101.5.1
		portObjectIndexEntry OBJECT-TYPE
			SYNTAX PortObjectIndexEntry
			MAX-ACCESS not-accessible
			STATUS current
			DESCRIPTION
				"Row Description"
			INDEX { portIndex }
			::= { portObjectIndexTable 1 }

		
		PortObjectIndexEntry ::=
			SEQUENCE { 
				portIndex
					Unsigned32
			 }

		-- 1.3.6.1.4.1.5875.800.3.101.5.1.1
		portIndex OBJECT-TYPE
			SYNTAX Unsigned32 (1..1024)
			MAX-ACCESS read-only
			STATUS current
			DESCRIPTION
				"Data Port Index"
			::= { portObjectIndexEntry 1 }

		
		-- 1.3.6.1.4.1.5875.800.3.101.6
		ponObjectIndexTable OBJECT-TYPE
			SYNTAX SEQUENCE OF PonObjectIndexEntry
			MAX-ACCESS not-accessible
			STATUS current
			DESCRIPTION
				"Description"
			::= { objectIndex 6 }

		
		-- 1.3.6.1.4.1.5875.800.3.101.6.1
		ponObjectIndexEntry OBJECT-TYPE
			SYNTAX PonObjectIndexEntry
			MAX-ACCESS not-accessible
			STATUS current
			DESCRIPTION
				"Row Description"
			INDEX { ponIndex }
			::= { ponObjectIndexTable 1 }

		
		PonObjectIndexEntry ::=
			SEQUENCE { 
				ponIndex
					Unsigned32
			 }

		-- 1.3.6.1.4.1.5875.800.3.101.6.1.1
		ponIndex OBJECT-TYPE
			SYNTAX Unsigned32 (1..1024)
			MAX-ACCESS read-only
			STATUS current
			DESCRIPTION
				"Column Description"
			::= { ponObjectIndexEntry 1 }

		
		-- 1.3.6.1.4.1.5875.800.1001
		equipTypeObjectId OBJECT IDENTIFIER ::= { standard 1001 }

		
		-- 1.3.6.1.4.1.5875.800.1001.1
		an5116v02 OBJECT-TYPE
			SYNTAX Integer32
			MAX-ACCESS read-only
			STATUS current
			DESCRIPTION
				"Description"
			::= { equipTypeObjectId 1 }

		
		-- 1.3.6.1.4.1.5875.800.1001.2
		an5116v06 OBJECT-TYPE
			SYNTAX Integer32
			MAX-ACCESS read-only
			STATUS current
			DESCRIPTION
				"Description"
			::= { equipTypeObjectId 2 }

		
		-- 1.3.6.1.4.1.5875.800.1001.11
		an5516v01 OBJECT-TYPE
			SYNTAX Integer32
			MAX-ACCESS read-only
			STATUS current
			DESCRIPTION
				"Description"
			::= { equipTypeObjectId 11 }

		
		-- 1.3.6.1.4.1.5875.800.1001.12
		an5516v04 OBJECT-TYPE
			SYNTAX Integer32
			MAX-ACCESS read-only
			STATUS current
			DESCRIPTION
				"Description"
			::= { equipTypeObjectId 12 }

		
		-- 1.3.6.1.4.1.5875.800.1001.14
		gT511606B OBJECT-TYPE
			SYNTAX Integer32
			MAX-ACCESS read-only
			STATUS current
			DESCRIPTION
				"Description"
			::= { equipTypeObjectId 14 }

		
		-- 1.3.6.1.4.1.5875.800.1001.21
		an6016v01 OBJECT-TYPE
			SYNTAX Integer32
			MAX-ACCESS read-only
			STATUS current
			DESCRIPTION
				"Description"
			::= { equipTypeObjectId 21 }

		
		-- 1.3.6.1.4.1.5875.800.1001.101
		an2200v02 OBJECT-TYPE
			SYNTAX Integer32
			MAX-ACCESS read-only
			STATUS current
			DESCRIPTION
				"Description"
			::= { equipTypeObjectId 101 }

		
		-- 1.3.6.1.4.1.5875.800.1001.111
		an3300v02 OBJECT-TYPE
			SYNTAX Integer32
			MAX-ACCESS read-only
			STATUS current
			DESCRIPTION
				"Description"
			::= { equipTypeObjectId 111 }

		
		-- 1.3.6.1.4.1.5875.800.1001.112
		an3300v03 OBJECT-TYPE
			SYNTAX Integer32
			MAX-ACCESS read-only
			STATUS current
			DESCRIPTION
				"Description"
			::= { equipTypeObjectId 112 }

		
		-- 1.3.6.1.4.1.5875.800.1001.121
		an5006v15 OBJECT-TYPE
			SYNTAX Integer32
			MAX-ACCESS read-only
			STATUS current
			DESCRIPTION
				"Description"
			::= { equipTypeObjectId 121 }

		
		-- 1.3.6.1.4.1.5875.800.1001.122
		an5006v16 OBJECT-TYPE
			SYNTAX Integer32
			MAX-ACCESS read-only
			STATUS current
			DESCRIPTION
				"Description"
			::= { equipTypeObjectId 122 }

		
		-- 1.3.6.1.4.1.5875.800.1001.131
		an5006v20 OBJECT-TYPE
			SYNTAX Integer32
			MAX-ACCESS read-only
			STATUS current
			DESCRIPTION
				"Description"
			::= { equipTypeObjectId 131 }

		
		-- 1.3.6.1.4.1.5875.800.1002
		fhOltDataGroup OBJECT IDENTIFIER ::= { standard 1002 }

		
		-- 1.3.6.1.4.1.5875.800.1002.1
		fhOltDataObjGroup OBJECT-GROUP
			OBJECTS { onuAuthNo1, onuSlotForPhysical, onuPonForPhysical, onuMacForPhysical, actionForPhysical, 
				onuAuthNo2, onuSlotForLogic, onuPonForLogic, onuSnForLogic, onuSnPasswordForLogic, 
				actionForLogic, applyCommand, macListId, slotNoForMacList, ponNoForMacList, 
				onuNoForMacList, onuTypeForMacList, macForMacList, passwordForMacList, actionForMacList, 
				snListId, slotNoForSnList, ponNoForSnList, onuNoForSnList, onuTypeForSnList, 
				snForSnList, passwordForSnList, actionForSnList, potsPortEnable, dataPortEnable, 
				oltPonEnable, bandwidthProfileId, bandwidthProfileName, upMinRate, upMaxRate, 
				downMinRate, downMaxRate, fixedRate, bandwidthProfileAction, fttbIfIndex, 
				attachBandwidthProfileId, attachBandwidthProfileName, unAttatchPortAttributeProfileAction, portAttributeProfileId, portAttributeProfileName, 
				autoNegotiation, speed, duplex, flowControl, portAttributeProfileAction, 
				attachPortAttributeProfileName, setDefaultPortAttributeProfileAction, ponBandwidthProfileId, ponBandwidthProfileName, ponUpMinRate, 
				ponUpMaxRate, ponDownMinRate, ponDownMaxRate, ponFixedRate, ponBandwidthProfileAction, 
				onuPonIfIndex, attachPonBandwidthProfileId, attachPonBandwidthProfileName, unAttatchPonBandwidthProfileAction, getNextBandwidthProfileId, 
				getNextPortAttributeProfileId, getNextPonBandwidthProfileId, serviceId, serviceType, cvlanMode, 
				cvlan, cvlanCos, tvlan, tvlanCos, svlan, 
				svlanCos, upMinBandWidth, upManBandWidth, serviceVlanName, qinqProfileName, 
				feServiceCfgAction, nextServiceId, feServiceCfgApplyCommand, attachQINQProfileId, attachQINQProfileName, 
				attachQINQSvlan, attachQINQTpid, attachQINQCos, attachQINQProfileAction, attchQinqProfileName, 
				qinqAttchAction, getOnuQinqProfileName, onuQinqProfileName, qinqServiceId, usMinBandwidth, 
				usMaxBandwidth, usBurstBandwidth, dsMinBandwidth, dsMaxBandwidth, dsBurstBandwidth, 
				qinqBandwidthCfgAction, qinqBandwidthCfgApply, qinqDomainName, qinqDomainAction, qinqDomainServiceNum, 
				nextQinqDomainServiceId, qinqDomainServiceId, qinqDomainServiceType, qinqDomainLayer1OldVlan, qinqDomainLayer1OldVlanCos, 
				qinqDomainLayer1VlanAction, qinqDomainLayer1VlanCos, qinqDomainLayer1Tpid, qinqDomainLayer1NewVlan, qinqDomainLayer2OldVlan, 
				qinqDomainLayer2OldVlanCos, qinqDomainLayer2VlanAction, qinqDomainLayer2VlanCos, qinqDomainLayer2Tpid, qinqDomainLayer2NewVlan, 
				qinqDomainUpRuleType, qinqDomainUpRuleValue, qinqDomainUpRuleOperation, qinqDomainDnRuleType, qinqDomainDnRuleValue, 
				qinqDomainDnRuleOperation, getNextQinqDomainServiceRuleID, qinqDomainServiceAction, qinqDomainServiceUpRuleType, qinqDomainServiceUpRuleValue, 
				qinqDomainServiceUpRuleOperation, qinqDomainServiceDnRuleType, qinqDomainServiceDnRuleValue, qinqDomainServiceDnRuleOperation, qinqDomainServiceRuleAction, 
				ftthPerformanceCardEnable, ftthIsPerformanceSupport, ftthPerformanceEnableFor5516, cpuUtilization, memUtilization, 
				currentTemperature, vlanID, framesUs, framesDs, octetsUs, 
				octetsDs, discardsUs, discardsDs, frameIndex, frameType, 
				frameName, slotNumOfFrame, cardType, cardHardwareVersion, cardSoftwateVersion, 
				cardStatus, cardNumOfPorts, cardAvailablePorts, cardCpuUtil, cardMemUtil, 
				portType, portEnableStatus, portOnlineStatus, portSpeed, portName, 
				portDesc, portMode, portVlan, portMac, portDefaultVlan, 
				portAutoneg, portMacNumberLimit, potsType, potsName, potsDesc, 
				potsEnableStatus, potsIdleStatus, onuPonType, onuPonName, onuPonDesc, 
				onuPonEnableStatus, onuPonSpeed, onuPonRxOpticalPower, onuPonTxOpticalPower, onuPonOpticalVltage, 
				onuPonOpticalCurrent, onuPonOpticalTemperature, onuPonIsOpticalPowerValid, onuPonUpstreamSpeed, oltPonType, 
				oltPonName, oltPonDesc, oltPonEnableStatus, oltPonOnlineStatus, oltPonSpeed, 
				oltPonTxOpticalPower, oltPonOpticalVltage, oltPonOpticalCurrent, oltPonOpticalTemperature, oltPonAuthOnuNum, 
				oltPonUpStreamSpeed, oltPonOpticalModuleType, uplinkType, uplinkName, uplinkDesc, 
				uplinkEnableStatus, uplinkSpeed, uplinkMacStr, oltPonOpticalStatisticsSwitch, onuNoRxOpticalPower, 
				oltPonRxOpticalPower, sysIp, sysMac, sysSoftVersion, sysHardVersion, 
				sysTemperature, sysAuthOnuNum, sysFtpServerIp, sysFtpServerName, sysFtpServerPwd, 
				sysFtpFilename, sysFtpAction, sysGateway, occupiedStatus, authCardType, 
				occupiedCardType, length, mgrCardType, mgrCardHandwareVersion, mgrCardSoftwareVession, 
				mgrCardWorkStatus, mgrCardCpuUtil, mgrCardMemUtil, onuAddressSlot, onuAddressPon, 
				onuAddressOnuId, onuAddressOnuIfIndex, authOnuListSlot, authOnuListPon, authOnuListOnuid, 
				authOnuListOnuType, authOnuListIp, authOnuListName, authOnuListSnLoid, authOnuListSnPwd, 
				authOnuListMac, onuStatus, authOnuSoftwareVersion, authOnuHardwareVersion, authOnuFirmwareVersion, 
				authOnuListOnuReboot, authOnuCpuUsage, authOnuMemoryUsage, authOnuWebSwitch, authOnuWebPort, 
				authOnuWebAdmin, authOnuWebAdminPassword, authOnuOpticalSwitch, authOnuWebServerSwitch, authOnuTelnetServerSwitch, 
				authOnuWebUNIswitch, authOnuTelnetUNIswitch, authOnuConsoleSwitch, authOnuMacNumberLimit, authOnuMacNumberLimitApply, 
				unauthOnuListOnuIndex, unauthOnuListSlot, unauthOnuListPon, unauthOnuListOnuType, unauthOnuListSnLoid, 
				unauthOnuListPwd, unauthOnuListMac, macAuthEnable, snAuthEnable, warrantType, 
				authMode, warrentCardType, vlanConfigId, serviceName, beginVlanId, 
				endVlanId, upLinkPort, tagStatus, globalVlanAction, nextGlobalVlanId, 
				onuMac, manageVlanName, portNo, tagStatus1, manageSvlan, 
				manageSvlanCos, mamageCvlan, mamageCvlanCos, onuIp, onuMask, 
				onuGateway, onuManageVlanAction, trunkGroupId, masterPort, memberPort, 
				trunkConfigAction, nextTrunkConfigId, upBandwidth, upAssureBandwidth, upFixedBandwidth, 
				onuPonCfgActon, save2Flash, onuAuthID, onuWhileListID, onuMacSlot, 
				onuMacPon, onuSNAuthID, onuSNWhilteListID, trapReceiveIp, community, 
				snmpTrapPort, snmpTrapVersion, snmpTrapReportVersion, snmpTrapCommunity, snmpTrapAction, 
				snmpCommunity, snmpCommunityPermission, snmpTrapIpv6, snmpTrapv6Port, snmpTrapv6Version, 
				snmpTrapReportv6Version, snmpTrapv6Community, snmpTrapv6Action, igmpMode, igmpProxyIp, 
				igmpProtocolVersion, robustnessVariable, queryRespInterval, lastQueryInterval, lastQueryCount, 
				queryInterval, groupMembInterval, igmpProfileName, igmpProfileAction, groupAddressBegin, 
				groupAddressEnd, igmpProfileGroupAuthority, igmpProfileGroupAction, igmpActiveMultiGroup, activeJoinPorts, 
				portCtrlEnable, igmpProfile, leaveMode, maxOnlineNum, portBandwidth, 
				portSignalVlan, portIgmpCfgAction, onuSlotForMacAuth, onuPonForMacAuth, onuNoForMacAuth, 
				onuTypeForMacAuth, macForMacAuth, passwordForMacAuth, actionForMacAuth, slotNoForSnAuth, 
				ponNoForSnMacAuth, onuNoForSnAuth, onuTypeForSnAuth, snForsnAuth, passwordForSnAuth, 
				actionForSnAuth, onuSvlanVid, onuCatvEnable, onuSNReplaceSlot, onuSNReplacePon, 
				onuSNReplaceOnuId, onuSNReplaceSnLoid, onuSNReplaceSnPwd, onuSNReplaceNewSnLoid, onuSNReplaceNewSnPwd, 
				onuSNReplaceStatus, gponRmtManageUrl, gponRmtManageUser, gponRmtManagePwd, gponRmtManageAction, 
				gponVEIPManagePathDsp, gponVEIPManagePathIPAddress, gponVEIPManagePathGateWay, gponVEIPManagePathPrimaryDns, gponVEIPManagePathSecondaryDns, 
				gponVEIPManagePathNetworkPort, gponVEIPManagePathCVlan, gponVEIPManagePathCVlanCos, gponVEIPManagePathIpMask, gponVEIPManagePathAction, 
				gponVEIPServiceTls, gponVEIPServiceCVlan, gponVEIPServiceCVlanCos, gponVEIPServiceTVlan, gponVEIPServiceTVlanCos, 
				gponVEIPServiceSVlan, gponVEIPServiceSVlanCos, gponVEIPServiceUsBandWidth, gponVEIPServiceDsBandWidth, gponVEIPServiceProfileName, 
				gponVEIPServiceAction, nextGponVEIPServiceID, gponFixedBandwidth, gponAssureBandwidth, gponMaxBandwidth, 
				gponBandwidthCfgAction, onuOpticalProfilename, recOptOverReport, recOptOverClear, recOptLowReport, 
				recOptLowClear, sendOptOverReport, sendOptiOverClear, sendOptLowReport, sendOptLowClear, 
				attachOptProfileId, attachOptProfileName, unattachOptiProfile, oltOptRecMaxthresh, oltOptRecMinthresh, 
				oltOptSendMaxthresh, oltOptSendMixthresh, wanMode, wanConnType, wanVlanId, 
				wanVlanCos, wanNatEnable, wanDsp, wanIpAddress, wanIPSubnet, 
				wanIpMask, wanMasterDns, wanSlaveDns, wanPPPoeProxy, wanPPPoeUsername, 
				wanPPPoePassword, wanPPPoeServer, wanPPPoeMode, wanQosEnable, wanVlanMode, 
				wantranslationstate, wanTranVlanID, wanTranCos, wanQinqState, wanTPID, 
				wanSvlanID, wanSvlanCos, wanDhcpRemoteID, wanbindport, wanServiceAction, 
				getNextwanIndex, applyWanAction, gponSerBwProName, gponSerBwProAction, getNextGponSerBwId, 
				fixBw, assureBw, maxBw, gponSerBwTypeAction, attachgponBwProfileId, 
				attachgponBwProfileName, unattachgponBwProfile, mibInflowsBIP, mibOutflowsBIP, powerAlarmStatus, 
				fanAlarmStatus, currentAlarmCode, currentAlarmIfIndex, currentAlarmStatus, currentAlarmStatusFlag, 
				currentAlarmBeginTime, currentAlarmEndTime, currentAlarmType, currentAlarmAdditionalText, hisAlarmCode, 
				hisAlarmIfIndex, hisAlarmStatus, hisAlarmStatusFlag, hisAlarmBeginTime, hisAlarmEndTime, 
				hisAlarmType, hisAlarmAdditionalText, slotIndex, onuIndex, uplinkIndex, 
				potsIndex, portIndex, ponIndex, an5116v02, an5116v06, 
				an5516v01, an5516v04, an6016v01, an2200v02, an3300v02, 
				an3300v03, an5006v15, an5006v16, an5006v20, downBwProfileID, 
				upBwProfileID, snmpExCommunityPermission, snmpExCommunity, outflowsBIP, inflowsBIP, 
				ifOutErrors, ifOutDiscards, ifOutNUcastPkts, ifOutUcastPkts, ifOutOctets, 
				ifInUnknownProtos, ifInErrors, ifInDiscards, ifInNUcastPkts, ifInUcastPkts, 
				ifInOctets, ifLastChange, ifOperStatus, ifAdminStatus, ifPhysAddress, 
				ifSpeed, ifMtu, ifType, ifDescr, nextGlobalVlanAttachPortIndex, 
				dnBandWidth, dnBandwidth, mibPerformExternTableNextScalar, ifCounterDiscontinuityTime, ifAlias, 
				ifConnectorPresent, ifPromiscuousMode, ifHighSpeed, ifLinkUpDownTrapEnable, ifHCOutBroadcastPkts, 
				ifHCOutMulticastPkts, ifHCOutUcastPkts, ifHCOutOctets, ifHCInBroadcastPkts, ifHCInMulticastPkts, 
				ifHCInUcastPkts, ifHCInOctets, ifOutBroadcastPkts, ifInMulticastPkts, ifInBroadcastPkts, 
				onuPonMibPerformTableNextScalar, igmpIptvServiceandJoinIgmpNum, igmpIptvServiceandPortUpNum, igmpIptvServiceNum, gT511606B, 
				igmpVlan }
			STATUS current
			DESCRIPTION 
				"Description."
			::= { fhOltDataGroup 1 }

		
		-- 1.3.6.1.4.1.5875.800.1002.2
		fhOltDataObjCompliance MODULE-COMPLIANCE
			STATUS current
			DESCRIPTION 
				"Description."
			MODULE -- this module
				MANDATORY-GROUPS { fhOltDataObjGroup }
			::= { fhOltDataGroup 2 }

		
	
	END

--
-- GEPON-OLT-COMMON-MIB.my
--

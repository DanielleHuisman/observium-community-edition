FIREBRICK-MIB DEFINITIONS ::= BEGIN

IMPORTS
    MODULE-IDENTITY,
    OBJECT-TYPE,
    Counter32,
    Integer32
    enterprises
            FROM SNMPv2-SMI
    TEXTUAL-CONVENTION,
    DisplayString
            FROM SNMPv2-TC
    MODULE-COMPLIANCE,
    OBJECT-GROUP
            FROM SNMPv2-CONF
    ;

firebrick MODULE-IDENTITY
        LAST-UPDATED    "202210081200Z"
        ORGANIZATION    "Observium Limited"
        CONTACT-INFO
                "Adam Armstrong
                Email: adama@observium.org"
        DESCRIPTION
                "Unofficial Firebrick MIB. For Observium use only."
        ::= { enterprises 24693 }

fbSensorObjects         OBJECT IDENTIFIER ::= { firebrick 1 }
firebrickNewStyle       OBJECT IDENTIFIER ::= { firebrick 100 }
fbL2tpObjects           OBJECT IDENTIFIER ::= { firebrick 1701 }
fbBgpObjects            OBJECT IDENTIFIER ::= { firebrick 179 }

fbSensorVoltage OBJECT-TYPE
    SYNTAX      INTEGER
    MAX-ACCESS  read-only
    STATUS      current
    DESCRIPTION
        "Firebrick voltage sensors. Reported in thousandths of a volt."
    ::= { fbSensorObjects 1 }

fbSensorTemperature OBJECT-TYPE
    SYNTAX      INTEGER
    MAX-ACCESS  read-only
    STATUS      current
    DESCRIPTION
        "Firebrick temperature sensors. Reported in thousandths of a degree celsius."
    ::= { fbSensorObjects 2 }

fbSensorFanspeed OBJECT-TYPE
    SYNTAX      INTEGER
    MAX-ACCESS  read-only
    STATUS      current
    DESCRIPTION
        "Firebrick fanspeed sensors. Reported in RPM."
    ::= { fbSensorObjects 3 }

fbL2tpTunnelStats           OBJECT IDENTIFIER ::= { fbL2tpObjects 1 }
fbL2tpSessionStats          OBJECT IDENTIFIER ::= { fbL2tpObjects 2 }

fbL2tpTunnelsFree           OBJECT-TYPE
    SYNTAX      INTEGER
    MAX-ACCESS  read-only
    STATUS      current
    DESCRIPTION
        "Number of tunnels in FREE state."
    ::= { fbL2tpTunnelStats 0 }

fbL2tpTunnelsOpening       OBJECT-TYPE
    SYNTAX      INTEGER
    MAX-ACCESS  read-only
    STATUS      current
    DESCRIPTION
        "Number of tunnels in OPENING state."
    ::= { fbL2tpTunnelStats 1 }

fbL2tpTunnelsLive       OBJECT-TYPE
    SYNTAX      INTEGER
    MAX-ACCESS  read-only
    STATUS      current
    DESCRIPTION
        "Number of tunnels in LIVE state."
    ::= { fbL2tpTunnelStats 2 }

fbL2tpTunnelsClosing       OBJECT-TYPE
    SYNTAX      INTEGER
    MAX-ACCESS  read-only
    STATUS      current
    DESCRIPTION
        "Number of tunnels in CLOSING state."
    ::= { fbL2tpTunnelStats 3 }

fbL2tpTunnelsFailed       OBJECT-TYPE
    SYNTAX      INTEGER
    MAX-ACCESS  read-only
    STATUS      current
    DESCRIPTION
        "Number of tunnels in FAILED state."
    ::= { fbL2tpTunnelStats 4 }

fbL2tpTunnelsClosed       OBJECT-TYPE
    SYNTAX      INTEGER
    MAX-ACCESS  read-only
    STATUS      current
    DESCRIPTION
        "Number of tunnels in FREE state."
    ::= { fbL2tpTunnelStats 5 }

fbL2tpSessionsFree       OBJECT-TYPE
    SYNTAX      INTEGER
    MAX-ACCESS  read-only
    STATUS      current
    DESCRIPTION
        "Number of sessions in FREE state."
    ::= { fbL2tpSessionStats 0 }

fbL2tpSessionsWaiting       OBJECT-TYPE
    SYNTAX      INTEGER
    MAX-ACCESS  read-only
    STATUS      current
    DESCRIPTION
        "Number of sessions in WAITING state."
    ::= { fbL2tpSessionStats 1 }

fbL2tpSessionsOpening       OBJECT-TYPE
    SYNTAX      INTEGER
    MAX-ACCESS  read-only
    STATUS      current
    DESCRIPTION
        "Number of sessions in FREE state."
    ::= { fbL2tpSessionStats 2 }

fbL2tpSessionsNegotiating       OBJECT-TYPE
    SYNTAX      INTEGER
    MAX-ACCESS  read-only
    STATUS      current
    DESCRIPTION
        "Number of sessions in NEGOTIATING state."
    ::= { fbL2tpSessionStats 3 }

fbL2tpSessionsAuthPending      OBJECT-TYPE
    SYNTAX      INTEGER
    MAX-ACCESS  read-only
    STATUS      current
    DESCRIPTION
        "Number of sessions in AUTH-PENDING state."
    ::= { fbL2tpSessionStats 4 }

fbL2tpSessionsStarted      OBJECT-TYPE
    SYNTAX      INTEGER
    MAX-ACCESS  read-only
    STATUS      current
    DESCRIPTION
        "Number of sessions in STARTED state."
    ::= { fbL2tpSessionStats 5 }

fbL2tpSessionsLive      OBJECT-TYPE
    SYNTAX      INTEGER
    MAX-ACCESS  read-only
    STATUS      current
    DESCRIPTION
        "Number of sessions in LIVE state."
    ::= { fbL2tpSessionStats 6 }

fbL2tpSessionsAcctPending      OBJECT-TYPE
    SYNTAX      INTEGER
    MAX-ACCESS  read-only
    STATUS      current
    DESCRIPTION
        "Number of sessions in ACCT-PENDING state."
    ::= { fbL2tpSessionStats 7 }

fbL2tpSessionsClosing      OBJECT-TYPE
    SYNTAX      INTEGER
    MAX-ACCESS  read-only
    STATUS      current
    DESCRIPTION
        "Number of sessions in CLOSING state."
    ::= { fbL2tpSessionStats 8 }

fbL2tpSessionsClosed      OBJECT-TYPE
    SYNTAX      INTEGER
    MAX-ACCESS  read-only
    STATUS      current
    DESCRIPTION
        "Number of sessions in CLOSED state."
    ::= { fbL2tpSessionStats 9 }


END

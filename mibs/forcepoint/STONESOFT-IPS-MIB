STONESOFT-IPS-MIB DEFINITIONS ::= BEGIN

IMPORTS
	MODULE-IDENTITY, OBJECT-TYPE, NOTIFICATION-TYPE
		FROM SNMPv2-SMI
	DisplayString, TimeStamp
		FROM SNMPv2-TC
	OBJECT-GROUP, NOTIFICATION-GROUP, MODULE-COMPLIANCE
		FROM SNMPv2-CONF
	stonesoftModules, stonesoftIPS
		FROM STONESOFT-SMI-MIB;

stonesoftIPSMibModule MODULE-IDENTITY
	LAST-UPDATED	"200701040000Z"
	ORGANIZATION	"Stonesoft Corp"
	CONTACT-INFO	"email: support@stonesoft.com"
	DESCRIPTION	"MIB for Stonesoft's IPS products"
	REVISION	"200701040000Z"
	DESCRIPTION	"First public revision"
	::= { stonesoftModules 3 }


ipsObjects  	OBJECT IDENTIFIER ::= { stonesoftIPS 1 }
ipsEvents  	OBJECT IDENTIFIER ::= { stonesoftIPS 2 }
ipsEventsV2	OBJECT IDENTIFIER ::= { ipsEvents 0 }
ipsConformance	OBJECT IDENTIFIER ::= { stonesoftIPS 3 } 

--
-- Ips objects
--
ipsSoftwareVersion	OBJECT-TYPE
			SYNTAX		DisplayString
			MAX-ACCESS	read-only
			STATUS		current
			DESCRIPTION
				"Version string of the IPS software"
			::= { ipsObjects 1 }

ipsSecurityPolicy	OBJECT-TYPE
			SYNTAX		DisplayString
			MAX-ACCESS	read-only
			STATUS		current
			DESCRIPTION
				"Name of the current security policy on the
				IPS"
			::= { ipsObjects 2 }

ipsPolicyTime		OBJECT-TYPE
			SYNTAX		TimeStamp
			MAX-ACCESS	read-only
			STATUS		current
			DESCRIPTION
				"The time when the security policy was 
				installed to the IPS"
			::= { ipsObjects 3 }

--
-- IPS events
-- 

ipsPolicyInstall         NOTIFICATION-TYPE
 			OBJECTS	        { ipsSecurityPolicy }
			STATUS		current
			DESCRIPTION 	"A IPS policy was (re)installed"
			::= {ipsEventsV2 1 }

-- Conformance information

ipsGroups		OBJECT IDENTIFIER ::= { ipsConformance 1 }
ipsCompliances 	OBJECT IDENTIFIER ::= { ipsConformance 2 }

ipsCompliance1 MODULE-COMPLIANCE
	STATUS current
	DESCRIPTION
		"The compliance statement for IPS"
	MODULE  -- this module --
		MANDATORY-GROUPS { ipsGeneralInformationGroup, 
				   ipsGeneralNotificationsGroup }
	::= { ipsCompliances 1 }


ipsGeneralInformationGroup OBJECT-GROUP
	OBJECTS	{ ipsSoftwareVersion, ipsSecurityPolicy, ipsPolicyTime }
	STATUS	current
	DESCRIPTION
		"A collection of objects giving general information about the
		 IPS"
	::= { ipsGroups 1 }

ipsGeneralNotificationsGroup NOTIFICATION-GROUP
	NOTIFICATIONS	{ ipsPolicyInstall }
	STATUS	current
	DESCRIPTION
		"A collection of notification giving information about
		 general events in the IPS"
	::= { ipsGroups 2 }

END

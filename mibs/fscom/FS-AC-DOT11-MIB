-- *******************************************************************
-- FS-AC-DOT11-MIB.mib : FS AC DOT11 MIB 
-- 
-- Oct 2009, kangxk@fs.com.cn
--
-- Copyright (c) 2009 by FS.COM Inc..
-- All rights reserved.
-- *******************************************************************

FS-AC-DOT11-MIB DEFINITIONS ::= BEGIN 
IMPORTS
    MODULE-IDENTITY,
    OBJECT-TYPE,
    Integer32
        FROM SNMPv2-SMI 
    TruthValue,
    MacAddress,
    DisplayString
        FROM SNMPv2-TC 
    MODULE-COMPLIANCE,
    OBJECT-GROUP        
        FROM SNMPv2-CONF
    fsMgmt          
        FROM FS-SMI;   
                         

-- **********************************************
-- * MODULE IDENTITY 
-- ********************************************** 
fsAcDot11MIB MODULE-IDENTITY 
    LAST-UPDATED    "200911290000Z"
    ORGANIZATION
        "FS.COM Inc.."
    CONTACT-INFO
        "Tel: 400-865-2852 
           E-mail: https://www.fs.com/live_chat_service_mail.html "
        
    DESCRIPTION
       "
       802.11N Module in AC for FS SNC
       This is AC device manage MIB.
       "
    REVISION      "200911290000Z"
    DESCRIPTION
       "Initial version of this MIB module."
          
    ::= { fsMgmt  65 }


-- ***************************************************************************
-- * Major sections 
-- ***************************************************************************
fsAcDot11MIBObjects OBJECT IDENTIFIER  ::= { fsAcDot11MIB 1 }
fsApDot11MIBObjects OBJECT IDENTIFIER  ::= { fsAcDot11MIB 2 }
fsWlanDot11MIBObjects OBJECT IDENTIFIER  ::= { fsAcDot11MIB 3 }

-- ***************************************************************************
-- * AC MIB object 
-- ***************************************************************************

-- linktest sta_mac
fsAcDot11LinkTestStaTable OBJECT-TYPE
    SYNTAX SEQUENCE OF FSAcDot11LinkTestStaEntry
    MAX-ACCESS not-accessible
    STATUS  current
    DESCRIPTION
            "DOT11 Link test a station."
    ::= { fsAcDot11MIBObjects 1 }

fsAcDot11LinkTestStaEntry OBJECT-TYPE
    SYNTAX FSAcDot11LinkTestStaEntry
    MAX-ACCESS not-accessible
    STATUS current
    DESCRIPTION
        "DOT11 Link test a station."
    INDEX   { fsAcDot11LinkMac }
    ::= { fsAcDot11LinkTestStaTable 1 }

FSAcDot11LinkTestStaEntry ::=
    SEQUENCE {
             fsAcDot11LinkMac MacAddress,
             fsAcDot11Link DisplayString
    }
    
fsAcDot11LinkMac OBJECT-TYPE
    SYNTAX MacAddress
    MAX-ACCESS not-accessible
    STATUS current
    DESCRIPTION
            "Link Test MAC."
    ::= { fsAcDot11LinkTestStaEntry 1 }
    
fsAcDot11Link OBJECT-TYPE
    SYNTAX DisplayString (SIZE (0..255))
    MAX-ACCESS read-only
    STATUS current
    DESCRIPTION
            "Link Test Detail."
    ::= { fsAcDot11LinkTestStaEntry 2 }

-- show client details mac
fsAcDot11ShowClientTable OBJECT-TYPE
    SYNTAX SEQUENCE OF FSAcDot11ShowClientEntry
    MAX-ACCESS not-accessible
    STATUS  current
    DESCRIPTION
            "Show client detail."
    ::= { fsAcDot11MIBObjects 2 }

fsAcDot11ShowClientEntry OBJECT-TYPE
    SYNTAX FSAcDot11ShowClientEntry
    MAX-ACCESS not-accessible
    STATUS current
    DESCRIPTION
        "Show client detail entry."
    INDEX   { fsAcDot11ClientMac }
    ::= { fsAcDot11ShowClientTable 1 }

FSAcDot11ShowClientEntry ::=
    SEQUENCE {
           fsAcDot11ClientMac MacAddress,
           fsAcDot11Client DisplayString
    }
    
fsAcDot11ClientMac OBJECT-TYPE
    SYNTAX MacAddress
    MAX-ACCESS not-accessible
    STATUS current
    DESCRIPTION
            "Client MAC."
    ::= { fsAcDot11ShowClientEntry 1 }
    
fsAcDot11Client OBJECT-TYPE
    SYNTAX DisplayString (SIZE (0..255))
    MAX-ACCESS read-only
    STATUS current
    DESCRIPTION
            "Client Detail."
    ::= { fsAcDot11ShowClientEntry 2 }

-- auth-timeout
fsAcDot11AuthTimeout OBJECT-TYPE
    SYNTAX  Integer32
    MAX-ACCESS  read-write
    STATUS  current
    DESCRIPTION
            "Auth timeout."
    ::= { fsAcDot11MIBObjects 3 }
    
-- country country_code
fsAcDot11CountryTable OBJECT-TYPE
    SYNTAX SEQUENCE OF FSAcDot11CountryEntry
    MAX-ACCESS not-accessible
    STATUS  current
    DESCRIPTION
            "The country code table."
    ::= { fsAcDot11MIBObjects 4 }

fsAcDot11CountryEntry OBJECT-TYPE
    SYNTAX FSAcDot11CountryEntry
    MAX-ACCESS not-accessible
    STATUS current
    DESCRIPTION
        "The country code entry."
    INDEX   { fsAcDot11CountryNum }
    ::= { fsAcDot11CountryTable 1 }

FSAcDot11CountryEntry ::=
    SEQUENCE {
        fsAcDot11CountryNum    Integer32,
        fsAcDot11Country       DisplayString,
        fsAcDot11CountryEnable TruthValue
    }

fsAcDot11CountryNum OBJECT-TYPE 
    SYNTAX Integer32
    MAX-ACCESS not-accessible 
    STATUS current 
    DESCRIPTION
        "Country Code Index NUM."
    ::= { fsAcDot11CountryEntry 1}

fsAcDot11Country OBJECT-TYPE
    SYNTAX DisplayString (SIZE (0..3))
    MAX-ACCESS read-write
    STATUS current
    DESCRIPTION
        "AC's Country code."
    ::= { fsAcDot11CountryEntry 2 }
    
fsAcDot11CountryEnable OBJECT-TYPE
    SYNTAX TruthValue
    MAX-ACCESS read-write
    STATUS current
    DESCRIPTION
        "AC's Country code enable."
    ::= { fsAcDot11CountryEntry 3 }


-- ***************************************************************************
-- * AP MIB object 
-- ***************************************************************************

-- (config-ap)#poe enable
fsApDot11PoeTable OBJECT-TYPE
    SYNTAX SEQUENCE OF FSApDot11PoeEntry
    MAX-ACCESS not-accessible 
    STATUS current 
    DESCRIPTION
      "FS AP POE MIB"
    ::={ fsApDot11MIBObjects 1 }

fsApDot11PoeEntry OBJECT-TYPE 
    SYNTAX FSApDot11PoeEntry
    MAX-ACCESS not-accessible
    STATUS current
    DESCRIPTION
      "AP ID is the index of this MIB table."
    INDEX { fsApDot11PoeAPID }
    ::={ fsApDot11PoeTable 1 }

FSApDot11PoeEntry ::=
    SEQUENCE {
        fsApDot11PoeAPID               INTEGER,
        fsApDot11PoeEnable             TruthValue    
    }
    
fsApDot11PoeAPID OBJECT-TYPE 
    SYNTAX TruthValue
    MAX-ACCESS not-accessible
    STATUS current 
    DESCRIPTION
      "AP ID"
    ::= { fsApDot11PoeEntry 1}
    
fsApDot11PoeEnable OBJECT-TYPE 
    SYNTAX TruthValue
    MAX-ACCESS read-write
    STATUS current 
    DESCRIPTION
      "POE Enable."
    ::= { fsApDot11PoeEntry 2}
    
-- (config-ap)#[no]chan-width {20 | 40}
fsApDot11ChannelTable OBJECT-TYPE
    SYNTAX SEQUENCE OF FSApDot11ChannelEntry
    MAX-ACCESS not-accessible 
    STATUS current 
    DESCRIPTION
      "FS AP Channel width MIB"
    ::={ fsApDot11MIBObjects 2 }

fsApDot11ChannelEntry OBJECT-TYPE 
    SYNTAX FSApDot11ChannelEntry
    MAX-ACCESS not-accessible
    STATUS current
    DESCRIPTION
      "AP ID is the index of this MIB table."
    INDEX { fsApDot11ChannelAPID  }
    ::={ fsApDot11ChannelTable 1 }

FSApDot11ChannelEntry ::=
    SEQUENCE {
        fsApDot11ChannelAPID            INTEGER,
        fsApDot11ChannelWidthA          INTEGER,
        fsApDot11ChannelWidthB          INTEGER
    }
    
fsApDot11ChannelAPID OBJECT-TYPE 
    SYNTAX INTEGER
    MAX-ACCESS not-accessible
    STATUS current 
    DESCRIPTION
      "AP ID"
    ::= { fsApDot11ChannelEntry 1}    
    
fsApDot11ChannelWidthA OBJECT-TYPE 
    SYNTAX INTEGER
    MAX-ACCESS read-write 
    STATUS current 
    DESCRIPTION
      "Radio 1 Channel width."
    DEFVAL { 20 }
    ::= { fsApDot11ChannelEntry 2}
  
fsApDot11ChannelWidthB OBJECT-TYPE 
    SYNTAX INTEGER
    MAX-ACCESS read-write 
    STATUS current 
    DESCRIPTION
      "Radio 2 Channel width."
    DEFVAL { 20 }
    ::= { fsApDot11ChannelEntry 3}  

-- (config-ap)#[no]antenne {receive|transmit} {number}
fsApDot11AntenneTable OBJECT-TYPE
    SYNTAX SEQUENCE OF FSApDot11AntenneEntry
    MAX-ACCESS not-accessible 
    STATUS current 
    DESCRIPTION
      "FS AP Antenne MIB"
    ::={ fsApDot11MIBObjects 3 }

fsApDot11AntenneEntry OBJECT-TYPE 
    SYNTAX FSApDot11AntenneEntry
    MAX-ACCESS not-accessible
    STATUS current
    DESCRIPTION
      "AP ID is the index of this MIB table."
    INDEX { fsApDot11AntenneAPID  }
    ::={ fsApDot11AntenneTable 1 }

FSApDot11AntenneEntry ::=
    SEQUENCE {
        fsApDot11AntenneAPID            INTEGER,
        fsApDot11AntenneRxA             INTEGER,
        fsApDot11AntenneTxA             INTEGER,
        fsApDot11AntenneRxB             INTEGER,
        fsApDot11AntenneTxB             INTEGER     
    }
    
fsApDot11AntenneAPID OBJECT-TYPE 
    SYNTAX INTEGER
    MAX-ACCESS not-accessible
    STATUS current 
    DESCRIPTION
      "AP ID"
    ::= { fsApDot11AntenneEntry 1}  
    
fsApDot11AntenneRxA OBJECT-TYPE 
    SYNTAX INTEGER (0..7)
    MAX-ACCESS read-write 
    STATUS current 
    DESCRIPTION
      "Radio 1 Antenne Receive."
    DEFVAL { 7 }
    ::= { fsApDot11AntenneEntry 2}
    
fsApDot11AntenneTxA OBJECT-TYPE 
    SYNTAX INTEGER (0..7)
    MAX-ACCESS read-write 
    STATUS current 
    DESCRIPTION
      "Radio 1 Antenne Transmit."
    DEFVAL { 7 }
    ::= { fsApDot11AntenneEntry 3}

fsApDot11AntenneRxB OBJECT-TYPE 
    SYNTAX INTEGER (0..7)
    MAX-ACCESS read-write 
    STATUS current 
    DESCRIPTION
      "Radio 2 Antenne Receive."
    DEFVAL { 7 }
    ::= { fsApDot11AntenneEntry 4}
    
fsApDot11AntenneTxB OBJECT-TYPE 
    SYNTAX INTEGER (0..7)
    MAX-ACCESS read-write 
    STATUS current 
    DESCRIPTION
      "Radio 2 Antenne Transmit."
    DEFVAL { 7 }
    ::= { fsApDot11AntenneEntry 5}


--***************************************************************************
--* WLAN MIB object 
--***************************************************************************

fsWlanDot11LoadTable OBJECT-TYPE
    SYNTAX SEQUENCE OF FSWlanDot11LoadTEntry
    MAX-ACCESS not-accessible 
    STATUS current 
    DESCRIPTION
      "FS WLAN Load MIB"
    ::={ fsWlanDot11MIBObjects 1 }

fsWlanDot11LoadTEntry  OBJECT-TYPE 
    SYNTAX FSWlanDot11LoadTEntry
    MAX-ACCESS not-accessible
    STATUS current
    DESCRIPTION
      "An agent MAY process one or more WLAN, which is identifed by fsApgWlanId.
      In other words, wlan ID is the index of this MIB table."
    INDEX { fsWlanDot11WlanId }
    ::={ fsWlanDot11LoadTable 1 }

FSWlanDot11LoadTEntry ::=
    SEQUENCE {
        fsWlanDot11WlanId             INTEGER,
        fsWlanDot11Enable             TruthValue,
        fsWlanDot11Window             INTEGER,
        fsWlanDot11Flow               INTEGER      
    }

fsWlanDot11WlanId OBJECT-TYPE 
    SYNTAX INTEGER
    MAX-ACCESS not-accessible
    STATUS current 
    DESCRIPTION
      "WLAN ID."
    ::= { fsWlanDot11LoadTEntry 1}


fsWlanDot11Enable OBJECT-TYPE 
    SYNTAX TruthValue
    MAX-ACCESS read-write
    STATUS current 
    DESCRIPTION
      "Load Balancing Enable."
    DEFVAL { false } 
    ::= { fsWlanDot11LoadTEntry 2}

fsWlanDot11Window OBJECT-TYPE 
    SYNTAX INTEGER (0..20)      
    MAX-ACCESS read-write
    STATUS current 
    DESCRIPTION
      "Load Balancing Window Clients"   
    ::= { fsWlanDot11LoadTEntry 3}

fsWlanDot11Flow OBJECT-TYPE 
    SYNTAX INTEGER (0..130)
    MAX-ACCESS read-write 
    STATUS current 
    DESCRIPTION
      "Load Balancing Flow Threshold"
    ::= { fsWlanDot11LoadTEntry 4}

--***************************************************************************
--* 802.11N MIB object 
--***************************************************************************
-- (config-ac)#11A 11nsupport

fsNetDot11AEnable OBJECT-TYPE 
    SYNTAX TruthValue
    MAX-ACCESS read-write
    STATUS current 
    DESCRIPTION
      "Radio 1 11N Enable."
    DEFVAL { true } 
    ::= { fsAcDot11MIBObjects 5}
    
fsNetDot11AMCS0 OBJECT-TYPE 
    SYNTAX TruthValue     
    MAX-ACCESS read-write
    STATUS current 
    DESCRIPTION
      "Radio 1 11N Support MCS 0"   
    ::= { fsAcDot11MIBObjects 6}

fsNetDot11AMCS1 OBJECT-TYPE 
    SYNTAX TruthValue     
    MAX-ACCESS read-write
    STATUS current 
    DESCRIPTION
      "Radio 1 11N Support MCS 1"   
    ::= { fsAcDot11MIBObjects 7}
    
fsNetDot11AMCS2 OBJECT-TYPE 
    SYNTAX TruthValue     
    MAX-ACCESS read-write
    STATUS current 
    DESCRIPTION
      "Radio 1 11N Support MCS 2"   
    ::= { fsAcDot11MIBObjects 8}

fsNetDot11AMCS3 OBJECT-TYPE 
    SYNTAX TruthValue     
    MAX-ACCESS read-write
    STATUS current 
    DESCRIPTION
      "Radio 1 11N Support MCS 3"   
    ::= { fsAcDot11MIBObjects 9}
    
fsNetDot11AMCS4 OBJECT-TYPE 
    SYNTAX TruthValue     
    MAX-ACCESS read-write
    STATUS current 
    DESCRIPTION
      "Radio 1 11N Support MCS 4"   
    ::= { fsAcDot11MIBObjects 10}
    
fsNetDot11AMCS5 OBJECT-TYPE 
    SYNTAX TruthValue     
    MAX-ACCESS read-write
    STATUS current 
    DESCRIPTION
      "Radio 1 11N Support MCS 5"   
    ::= { fsAcDot11MIBObjects 11}
    
fsNetDot11AMCS6 OBJECT-TYPE 
    SYNTAX TruthValue     
    MAX-ACCESS read-write
    STATUS current 
    DESCRIPTION
      "Radio 1 11N Support MCS 6"   
    ::= { fsAcDot11MIBObjects 12}

fsNetDot11AMCS7 OBJECT-TYPE 
    SYNTAX TruthValue     
    MAX-ACCESS read-write
    STATUS current 
    DESCRIPTION
      "Radio 1 11N Support MCS 7"   
    ::= { fsAcDot11MIBObjects 13}
    
fsNetDot11AMCS8 OBJECT-TYPE 
    SYNTAX TruthValue     
    MAX-ACCESS read-write
    STATUS current 
    DESCRIPTION
      "Radio 1 11N Support MCS 8"   
    ::= { fsAcDot11MIBObjects 14}
    
fsNetDot11AMCS9 OBJECT-TYPE 
    SYNTAX TruthValue     
    MAX-ACCESS read-write
    STATUS current 
    DESCRIPTION
      "Radio 1 11N Support MCS 9"   
    ::= { fsAcDot11MIBObjects 15}
    
fsNetDot11AMCS10 OBJECT-TYPE 
    SYNTAX TruthValue     
    MAX-ACCESS read-write
    STATUS current 
    DESCRIPTION
      "Radio 1 11N Support MCS 10"   
    ::= { fsAcDot11MIBObjects 16}
    
fsNetDot11AMCS11 OBJECT-TYPE 
    SYNTAX TruthValue     
    MAX-ACCESS read-write
    STATUS current 
    DESCRIPTION
      "Radio 1 11N Support MCS 11"   
    ::= { fsAcDot11MIBObjects 17}
    
fsNetDot11AMCS12 OBJECT-TYPE 
    SYNTAX TruthValue     
    MAX-ACCESS read-write
    STATUS current 
    DESCRIPTION
      "Radio 1 11N Support MCS 12"   
    ::= { fsAcDot11MIBObjects 18}
    
fsNetDot11AMCS13 OBJECT-TYPE 
    SYNTAX TruthValue     
    MAX-ACCESS read-write
    STATUS current 
    DESCRIPTION
      "Radio 1 11N Support MCS 13"   
    ::= { fsAcDot11MIBObjects 19}
    
fsNetDot11AMCS14 OBJECT-TYPE 
    SYNTAX TruthValue     
    MAX-ACCESS read-write
    STATUS current 
    DESCRIPTION
      "Radio 1 11N Support MCS 14"   
    ::= { fsAcDot11MIBObjects 20}
    
fsNetDot11AMCS15 OBJECT-TYPE 
    SYNTAX TruthValue     
    MAX-ACCESS read-write
    STATUS current 
    DESCRIPTION
      "Radio 1 11N Support MCS 15"   
    ::= { fsAcDot11MIBObjects 21}   

fsNetDot11AAMPDU OBJECT-TYPE 
    SYNTAX INTEGER (0..7)
    MAX-ACCESS read-write 
    STATUS current 
    DESCRIPTION
      "Radio 1 11N Support AMPUD"
    ::= { fsAcDot11MIBObjects 22}
    
-- (config-ac)#11nsupport enable radio 1

fsNetDot11BEnable OBJECT-TYPE 
    SYNTAX TruthValue
    MAX-ACCESS read-write
    STATUS current 
    DESCRIPTION
      "Radio 2 11N Enable."
    DEFVAL { true } 
    ::= { fsAcDot11MIBObjects 23}

fsNetDot11BMCS0 OBJECT-TYPE 
    SYNTAX INTEGER (0..15)      
    MAX-ACCESS read-write
    STATUS current 
    DESCRIPTION
      "Radio 2 11N Support MCS0"   
    ::= { fsAcDot11MIBObjects 24}
   
fsNetDot11BMCS1 OBJECT-TYPE 
    SYNTAX INTEGER (0..15)      
    MAX-ACCESS read-write
    STATUS current 
    DESCRIPTION
      "Radio 2 11N Support MCS1"   
    ::= { fsAcDot11MIBObjects 25}
   
fsNetDot11BMCS2 OBJECT-TYPE 
    SYNTAX INTEGER (0..15)      
    MAX-ACCESS read-write
    STATUS current 
    DESCRIPTION
      "Radio 2 11N Support MCS2"   
    ::= { fsAcDot11MIBObjects 26}
   
fsNetDot11BMCS3 OBJECT-TYPE 
    SYNTAX INTEGER (0..15)      
    MAX-ACCESS read-write
    STATUS current 
    DESCRIPTION
      "Radio 2 11N Support MCS3"   
    ::= { fsAcDot11MIBObjects 27}
   
fsNetDot11BMCS4 OBJECT-TYPE 
    SYNTAX INTEGER (0..15)      
    MAX-ACCESS read-write
    STATUS current 
    DESCRIPTION
      "Radio 2 11N Support MCS4"   
    ::= { fsAcDot11MIBObjects 28}
    
fsNetDot11BMCS5 OBJECT-TYPE 
    SYNTAX INTEGER (0..15)      
    MAX-ACCESS read-write
    STATUS current 
    DESCRIPTION
      "Radio 2 11N Support MCS5"   
    ::= { fsAcDot11MIBObjects 29}  
   
fsNetDot11BMCS6 OBJECT-TYPE 
    SYNTAX INTEGER (0..15)      
    MAX-ACCESS read-write
    STATUS current 
    DESCRIPTION
      "Radio 2 11N Support MCS6"   
    ::= { fsAcDot11MIBObjects 30}
   
fsNetDot11BMCS7 OBJECT-TYPE 
    SYNTAX INTEGER (0..15)      
    MAX-ACCESS read-write
    STATUS current 
    DESCRIPTION
      "Radio 2 11N Support MCS7"   
    ::= { fsAcDot11MIBObjects 31}
   
fsNetDot11BMCS8 OBJECT-TYPE 
    SYNTAX INTEGER (0..15)      
    MAX-ACCESS read-write
    STATUS current 
    DESCRIPTION
      "Radio 2 11N Support MCS8"   
    ::= { fsAcDot11MIBObjects 32}
    
fsNetDot11BMCS9 OBJECT-TYPE 
    SYNTAX INTEGER (0..15)      
    MAX-ACCESS read-write
    STATUS current 
    DESCRIPTION
      "Radio 2 11N Support MCS9"   
    ::= { fsAcDot11MIBObjects 33}
    
fsNetDot11BMCS10 OBJECT-TYPE 
    SYNTAX INTEGER (0..15)      
    MAX-ACCESS read-write
    STATUS current 
    DESCRIPTION
      "Radio 2 11N Support MCS10"   
    ::= { fsAcDot11MIBObjects 34}

fsNetDot11BMCS11 OBJECT-TYPE 
    SYNTAX INTEGER (0..15)      
    MAX-ACCESS read-write
    STATUS current 
    DESCRIPTION
      "Radio 2 11N Support MCS11"   
    ::= { fsAcDot11MIBObjects 35}
    
fsNetDot11BMCS12 OBJECT-TYPE 
    SYNTAX INTEGER (0..15)      
    MAX-ACCESS read-write
    STATUS current 
    DESCRIPTION
      "Radio 2 11N Support MCS12"   
    ::= { fsAcDot11MIBObjects 36}

fsNetDot11BMCS13 OBJECT-TYPE 
    SYNTAX INTEGER (0..15)      
    MAX-ACCESS read-write
    STATUS current 
    DESCRIPTION
      "Radio 2 11N Support MCS13"   
    ::= { fsAcDot11MIBObjects 37}
    
fsNetDot11BMCS14 OBJECT-TYPE 
    SYNTAX INTEGER (0..15)      
    MAX-ACCESS read-write
    STATUS current 
    DESCRIPTION
      "Radio 2 11N Support MCS14"   
    ::= { fsAcDot11MIBObjects 38}

fsNetDot11BMCS15 OBJECT-TYPE 
    SYNTAX INTEGER (0..15)      
    MAX-ACCESS read-write
    STATUS current 
    DESCRIPTION
      "Radio 2 11N Support MCS15"   
    ::= { fsAcDot11MIBObjects 39}
            
fsNetDot11BAMPDU OBJECT-TYPE 
    SYNTAX INTEGER (0..7)
    MAX-ACCESS read-write 
    STATUS current 
    DESCRIPTION
      "Radio 2 11N Support AMPUD"
    ::= { fsAcDot11MIBObjects 40}

-- (config-ac)#11gsupport radio 1
fsNetDot11AGEnable OBJECT-TYPE 
    SYNTAX TruthValue
    MAX-ACCESS read-write
    STATUS current 
    DESCRIPTION
      "Radio 1 11G Spport Enable."
    DEFVAL { true } 
    ::= { fsAcDot11MIBObjects 41}
    
-- (config-ac)#11gsupport radio 2
fsNetDot11BGEnable OBJECT-TYPE 
    SYNTAX TruthValue
    MAX-ACCESS read-write
    STATUS current 
    DESCRIPTION
      "Radio 2 11G Spport Enable."
    DEFVAL { true } 
    ::= { fsAcDot11MIBObjects 42}
    
    
--********************************************************************
--                                                                  **
--           conformance information                                **
--                                                                  **
--********************************************************************
fsAcDot11MIBConformance OBJECT IDENTIFIER ::= { fsAcDot11MIB 5 }
fsAcDot11MIBCompliances OBJECT IDENTIFIER ::= { fsAcDot11MIBConformance 1 }
fsAcDot11MIBGroups      OBJECT IDENTIFIER ::= { fsAcDot11MIBConformance 2 }


--********************************************************************
--                                                                  **
--           compliance statements                                  **
--                                                                  **
--********************************************************************
fsAcDot11MIBCompliance MODULE-COMPLIANCE
        STATUS  current
        DESCRIPTION
                "The compliance statement for entities which implement
                the FS Ac dot11 Manager."
        MODULE  -- this module
                MANDATORY-GROUPS { fsAcDot11MIBGroup}
        ::= { fsAcDot11MIBCompliances 1 }


--********************************************************************
--                                                                  **
--           units of conformance                                   **
--                                                                  **
--********************************************************************
fsAcDot11MIBGroup OBJECT-GROUP
        OBJECTS {
            fsAcDot11Link,
            fsAcDot11Client,
            fsAcDot11AuthTimeout,
            fsAcDot11Country,
            fsAcDot11CountryEnable,
            fsApDot11PoeEnable,
            fsApDot11ChannelWidthA,
            fsApDot11ChannelWidthB,
            fsApDot11AntenneRxA,
            fsApDot11AntenneTxA,
            fsApDot11AntenneRxB,
            fsApDot11AntenneTxB,
            fsWlanDot11Enable,
            fsWlanDot11Window,
            fsWlanDot11Flow,
            fsNetDot11AEnable,
            fsNetDot11AMCS0,
            fsNetDot11AMCS1,
            fsNetDot11AMCS2,
            fsNetDot11AMCS3,
            fsNetDot11AMCS4,
            fsNetDot11AMCS5,
            fsNetDot11AMCS6,
            fsNetDot11AMCS7,
            fsNetDot11AMCS8,
            fsNetDot11AMCS9,
            fsNetDot11AMCS10,
            fsNetDot11AMCS11,
            fsNetDot11AMCS12,
            fsNetDot11AMCS13,
            fsNetDot11AMCS14,
            fsNetDot11AMCS15,
            fsNetDot11AAMPDU,
            fsNetDot11BEnable,
            fsNetDot11BMCS0,
            fsNetDot11BMCS1,
            fsNetDot11BMCS2,
            fsNetDot11BMCS3,
            fsNetDot11BMCS4,
            fsNetDot11BMCS5,
            fsNetDot11BMCS6,
            fsNetDot11BMCS7,
            fsNetDot11BMCS8,
            fsNetDot11BMCS9,
            fsNetDot11BMCS10,
            fsNetDot11BMCS11,
            fsNetDot11BMCS12,
            fsNetDot11BMCS13,
            fsNetDot11BMCS14,
            fsNetDot11BMCS15,
            fsNetDot11BAMPDU,
            fsNetDot11AGEnable,
            fsNetDot11BGEnable    
        }
        STATUS  current
        DESCRIPTION
                "A collection of objects providing ac dot11 manager (echo) ability to a
                FS agent."
        ::= { fsAcDot11MIBGroups 1 }
END

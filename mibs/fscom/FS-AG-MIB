-- *****************************************************************
-- FS-ROUTE-AG-MIB.mib:  FS Route MIB file
-- Description: The MIB is designed to get 3G wireless safenet solution statistic information.
--
-- March 2002, Wuzg
--
-- Copyright (c) 2002 by FS.COM Inc..
-- All rights reserved.
-- 
-- *****************************************************************
--

-- MIB broken. Changed by Observium developers
-- FS-AG-MIB DEFINITIONS ::= BEGIN

    IMPORTS
        DisplayString,TEXTUAL-CONVENTION,TimeStamp
            FROM SNMPv2-TC
        IpAddress, Integer32, Counter32, Counter64, OBJECT-TYPE,
        MODULE-IDENTITY, Gauge32, NOTIFICATION-TYPE, Unsigned32
            FROM SNMPv2-SMI
        MODULE-COMPLIANCE, OBJECT-GROUP, NOTIFICATION-GROUP
            FROM SNMPv2-CONF
        fsMgmt
            FROM FS-SMI;
            
    fsAG MODULE-IDENTITY
        LAST-UPDATED "201102220000Z"            
        ORGANIZATION
            "FS.COM Inc.."
        CONTACT-INFO
            "Tel: 400-865-2852 
             E-mail: https://www.fs.com/live_chat_service_mail.html"  
        DESCRIPTION
            "The MIB is designed to get statistic information of
             3G wireless safenet. With this MIB, we can get information of a certain
             3G user or all users."
        REVISION      "201102220000Z"
        DESCRIPTION
                "Initial version of this MIB module."
        ::= { fsMgmt 95 }


-- ========================================================================
-- Node definitions
-- ========================================================================
--Begin the node of fsAGObjects.

    fsAGObjects OBJECT IDENTIFIER ::= { fsAG 1 }

-- ===============================================
-- Begin the table of fsApConfigTable_table.
-- ===============================================
    
    fsApConfigNumber OBJECT-TYPE
        SYNTAX ApConfigNumber
        ACCESS read-only
        STATUS current
        DESCRIPTION
            "The AP Number currently configured."
        ::= { fsApConfigTableEntry 1 }
        
    fsApConfigIndex OBJECT-TYPE
        SYNTAX fsApConfigIndex
        ACCESS read-only
        STATUS current
        DESCRIPTION
            "The AP Index currently configured."
        ::= { fsApConfigTableEntry 2 }
    
    fsApConfigMaxPtNumber OBJECT-TYPE
        SYNTAX fsApConfigMaxPtNumber
        ACCESS read-only
        STATUS current
        DESCRIPTION
            "The Max AP Number that could be configured."
        ::= { fsApConfigTableEntry 3 }
        
    fsApConfigCurrentPtNumber OBJECT-TYPE
        SYNTAX fsApConfigCurrentPtNumber
        ACCESS read-only
        STATUS current
        DESCRIPTION
            "The AP Port Number under configuration."
        ::= { fsApConfigTableEntry 4 }
    
    fsApConfigPortMember OBJECT-TYPE
        SYNTAX fsApConfigPortMember
        ACCESS read-only
        STATUS current
        DESCRIPTION
            "The AP Member Port under configuration."
        ::= { fsApConfigTableEntry 5}
        
    fsApConfigAction OBJECT-TYPE
        SYNTAX fsApConfigAction
        ACCESS read-write
        STATUS current
        DESCRIPTION
            "The AP Configuration Action."
        ::= { fsApConfigTableEntry 6 }
        
    fsApConfigBalance OBJECT-TYPE
        SYNTAX fsApConfigBalance
        ACCESS read-only
        STATUS current
        DESCRIPTION
            "The AP Balance Type."
        ::= { fsApConfigTableEntry 7 }
        
    fsApConfigStatus OBJECT-TYPE
        SYNTAX fsApConfigStatus
        ACCESS read-only
        STATUS current
        DESCRIPTION
            "The AP Configuration Status."
        ::= { fsApConfigTableEntry 8 }
        
    fsApConfigTableEntry ::=
        SEQUENCE {
            fsApConfigNumber
                Integer,
            fsApConfigIndex
                Integer,
            fsApConfigMaxPtNumber
                Integer,
            fsApConfigCurrentPtNumber
                DisplayString,
            fsApConfigPortMember
                DisplayString,
            fsApConfigAction
								Integer,
					  fsApConfigBalance
					      Integer,
					  fsApConfigStatus
					      Integer
        }
        
-- ===============================================
-- Begin the table of fsApPortMemberTable_table.
-- ===============================================

    fsApPortMemberPortIndex OBJECT-TYPE
        SYNTAX fsApPortMemberPortIndex
        ACCESS read-only
        STATUS current
        DESCRIPTION
            "The AP Member Port Index."
        ::= { fsApPortMemberTableEntry 1 }
        
    fsApPortMemberApNumber OBJECT-TYPE
        SYNTAX fsApPortMemberApNumber
        ACCESS read-only
        STATUS current
        DESCRIPTION
            "The member port number that AP aggregates."
        ::= { fsApPortMemberTableEntry 2 }
    
    fsApPortMemberAction OBJECT-TYPE
        SYNTAX fsApPortMemberAction
        ACCESS read-only
        STATUS current
        DESCRIPTION
            "The AP Member Port Action."
        ::= { fsApPortMemberTableEntry 3 }
        
    fsApPortMemberTableEntry ::=
        SEQUENCE {
            fsApPortMemberPortIndex
                Integer,
            fsApPortMemberApNumber
                Integer,
            fsApPortMemberAction
                Integer,
        }
        
END

-- *******************************************************************
-- FS-CAPWAP-MOBILITY-MIB.mib : FS MOBILITY MIB file
-- January 2009, shenyongjian
--
-- Copyright (c) 2009 by FS.COM Inc..
-- All rights reserved.
-- *******************************************************************
--
FS-CAPWAP-MOBILITY-MIB DEFINITIONS ::= BEGIN

IMPORTS
        IpAddress,
        OBJECT-TYPE,
        MODULE-IDENTITY,
        Counter32
                FROM SNMPv2-SMI
        MacAddress,
        DisplayString,
        RowStatus
                FROM SNMPv2-TC
        Ipv6Address
                FROM IPV6-TC
        InetAddressType,
        InetAddress
                FROM INET-ADDRESS-MIB
        MODULE-COMPLIANCE,
        OBJECT-GROUP
                FROM SNMPv2-CONF
        fsMgmt
                FROM FS-SMI;

fsMobilityMIB MODULE-IDENTITY
    LAST-UPDATED "200909180000Z"
    ORGANIZATION "FS.COM Inc.."
    CONTACT-INFO
        "
    Tel: 400-865-2852

    E-mail: https://www.fs.com/live_chat_service_mail.html"
    DESCRIPTION
        "This module defines roam mobility mibs."
    REVISION      "200909180000Z"
    DESCRIPTION
        "Initial version of this MIB module."
    ::= { fsMgmt 64}


--*****************define the roam mobility nodes********************
fsMobilityMIBObjects OBJECT IDENTIFIER   ::= {fsMobilityMIB 1}
fsMobility           OBJECT IDENTIFIER   ::= {fsMobilityMIBObjects 1}
fsMobilityIf         OBJECT IDENTIFIER   ::= {fsMobilityMIBObjects 2}
fsMobilityTrap       OBJECT IDENTIFIER   ::= {fsMobilityMIBObjects 3}

--********************************************************************
--                                                                  **
--                       MOBILITY GROUP MIB                         **
--                                                                  **
--********************************************************************

--*********1.Roam Mobility Group Entry***************
fsMobilityEntryTable OBJECT-TYPE
    SYNTAX SEQUENCE OF FSMobilityEntry
    MAX-ACCESS not-accessible
    STATUS current
    DESCRIPTION
         "Creat the roam mobility group"
    ::= {fsMobility 1}

fsMobilityEntry OBJECT-TYPE
    SYNTAX FSMobilityEntry
    MAX-ACCESS not-accessible
    STATUS current
    DESCRIPTION
         "The entry of roam mobility group table"
    INDEX  { fsRoamGroupId }
    ::= { fsMobilityEntryTable 1 }

FSMobilityEntry ::=
    SEQUENCE {
        fsRoamGroupId                    INTEGER,
        fsRoamGroupName                  DisplayString,
        fsRoamGroupMyAddress             IpAddress,
        fsRoamGroupMcEnable              INTEGER,
        fsRoamGroupMcAddress             IpAddress,
        fsRoamGroupKeepaliveCount        INTEGER,
        fsRoamGroupKeepaliveInterval     INTEGER,
        fsRoamGroupIsFast                INTEGER,
        fsRoamGroupCreateStatus          RowStatus,
        fsRoamGroupMyAddressIPv6         Ipv6Address
    }

--The group id of roam mobility group
fsRoamGroupId OBJECT-TYPE
     SYNTAX  INTEGER (0..8)
     MAX-ACCESS read-only
     STATUS current
     DESCRIPTION
              "The group id of roam mobility group"
     ::= { fsMobilityEntry 1 }

--The group name of roam mobility group
fsRoamGroupName OBJECT-TYPE
     SYNTAX  DisplayString
     MAX-ACCESS read-create
     STATUS current
     DESCRIPTION
              "The group name of roam mobility group"
     ::= { fsMobilityEntry 2 }

--The group ipv4 address of roam mobility group
fsRoamGroupMyAddress OBJECT-TYPE
     SYNTAX  IpAddress
     MAX-ACCESS read-only
     STATUS current
     DESCRIPTION
             "The group local ipv4 address of roam mobility group"
     ::= { fsMobilityEntry 3 }

--The flag whether the roam mobility group mc is enable
fsRoamGroupMcEnable OBJECT-TYPE
     SYNTAX  INTEGER
     MAX-ACCESS read-create
     STATUS current
     DESCRIPTION
              "The flag whether the roam mobility group mc is enable"
     ::= { fsMobilityEntry 4 }

--The multicast addr of roam mobility group
fsRoamGroupMcAddress OBJECT-TYPE
     SYNTAX  IpAddress
     MAX-ACCESS read-create
     STATUS current
     DESCRIPTION
             "The multicast addr of roam mobility group"
     ::= { fsMobilityEntry 5 }

--The keepalive count of roam mobility group
fsRoamGroupKeepaliveCount OBJECT-TYPE
     SYNTAX  INTEGER (2..30)
     MAX-ACCESS read-create
     STATUS current
     DESCRIPTION
              "The keepalive count of roam mobility group"
     ::= { fsMobilityEntry 6 }

--The keepalive interval of roam mobility group
fsRoamGroupKeepaliveInterval OBJECT-TYPE
     SYNTAX  INTEGER (1..30)
     MAX-ACCESS read-create
     STATUS current
     DESCRIPTION
              "The keepalive interval in seconds of roam mobility group"
     ::= { fsMobilityEntry 7 }

--The flag whether the roam mobility group run in fast roaming mode
fsRoamGroupIsFast OBJECT-TYPE
     SYNTAX  INTEGER
     MAX-ACCESS read-create
     STATUS current
     DESCRIPTION
              "The flag whether the roam mobility group run in fast roaming mode"
     ::= {fsMobilityEntry 8 }

--This object indicate the creat or delete of the table
fsRoamGroupCreateStatus OBJECT-TYPE
    SYNTAX   RowStatus
    MAX-ACCESS read-create
    STATUS   current
    DESCRIPTION
           "This object indicate the creat or delete of the Mobility table"
    ::= { fsMobilityEntry 9 }

--The group ipv6 address of roam mobility group
fsRoamGroupMyAddressIPv6 OBJECT-TYPE
     SYNTAX  Ipv6Address
     MAX-ACCESS read-only
     STATUS current
     DESCRIPTION
             "The group local ipv6 address of roam mobility group"
     ::= { fsMobilityEntry 10 }

--*********2.Roam Mobility Member Entry***************
fsMobilityMemberEntryTable OBJECT-TYPE
    SYNTAX SEQUENCE OF FSMobilityMemberEntry
    MAX-ACCESS not-accessible
    STATUS current
    DESCRIPTION
         "Creat the roam mobility group member"
    ::= {fsMobility 2}

fsMobilityMemberEntry OBJECT-TYPE
    SYNTAX FSMobilityMemberEntry
    MAX-ACCESS not-accessible
    STATUS current
    DESCRIPTION
         "The entry of roam mobility member"
    INDEX  { fsRoamMemberGroupId, fsRoamMemberPeerAddress }
    ::= { fsMobilityMemberEntryTable 1 }

FSMobilityMemberEntry ::=
    SEQUENCE {
        fsRoamMemberGroupId               INTEGER,
        fsRoamMemberPeerAddress           IpAddress,
        fsRoamMemberIsList                INTEGER,
        fsRoamMemberDataChannelIsOK       INTEGER,
        fsRoamMemberDataChannelFailTimes  INTEGER,
        fsRoamMemberDTLSIsClient          INTEGER,
        fsRoamMemberDTLSIsOK              INTEGER,
        fsRoamMemberCreateStatus          RowStatus
    }

--The group id of roam mobility group member
fsRoamMemberGroupId OBJECT-TYPE
     SYNTAX  INTEGER (0..8)
     MAX-ACCESS read-only
     STATUS current
     DESCRIPTION
              "The group id of roam mobility group"
     ::= { fsMobilityMemberEntry 1 }

--The peer ipv4 address of roam mobility group member
fsRoamMemberPeerAddress OBJECT-TYPE
     SYNTAX  IpAddress
     MAX-ACCESS read-only
     STATUS current
     DESCRIPTION
              "The peer ipv4 address of roam mobility group member"
     ::= { fsMobilityMemberEntry 2 }

--The flag whether roam mobility group member in roam list
fsRoamMemberIsList OBJECT-TYPE
 SYNTAX  INTEGER (0..1)
     MAX-ACCESS read-create
     STATUS current
     DESCRIPTION
             "The flag whether roam mobility group member in roam list"
     ::= { fsMobilityMemberEntry 3 }

--The flag whether the data channel of roam mobility group member is ok
fsRoamMemberDataChannelIsOK OBJECT-TYPE
     SYNTAX  INTEGER (0..1)
     MAX-ACCESS read-only
     STATUS current
     DESCRIPTION
             "The flag whether the data channel of roam mobility group member is ok"
     ::= { fsMobilityMemberEntry 4 }

--The Fail times of the data channel of roam mobility group member
fsRoamMemberDataChannelFailTimes OBJECT-TYPE
     SYNTAX  INTEGER
     MAX-ACCESS read-only
     STATUS current
     DESCRIPTION
              "The Fail times of the data channel of roam mobility group member"
     ::= { fsMobilityMemberEntry 5 }

--The flag whether the roam group member is client
fsRoamMemberDTLSIsClient OBJECT-TYPE
     SYNTAX  INTEGER
     MAX-ACCESS read-only
     STATUS current
     DESCRIPTION
             "The flag whether the roam mobility group member is client"
     ::= { fsMobilityMemberEntry 6 }

--The flag whether the roam group member dtls is ok
fsRoamMemberDTLSIsOK OBJECT-TYPE
     SYNTAX  INTEGER (0..1)
     MAX-ACCESS read-only
     STATUS current
     DESCRIPTION
             "The flag whether the roam mobility group member dtls is ok"
     ::= { fsMobilityMemberEntry 7 }

--This object indicate the creat or delete of the table
fsRoamMemberCreateStatus OBJECT-TYPE
     SYNTAX   RowStatus
     MAX-ACCESS read-create
     STATUS   current
     DESCRIPTION
           "This object indicate the creat or delete of the Mobility table"
     ::= { fsMobilityMemberEntry 8 }

--*********3.creat the AP control entry***************
fsAPCtrlCreatEntryTable OBJECT-TYPE
   SYNTAX SEQUENCE OF FSAPCtrlCreatEntry
   MAX-ACCESS not-accessible
   STATUS current
   DESCRIPTION
          "Creat the AP control block"
   ::= {fsMobility 3}

fsAPCtrlCreatEntry OBJECT-TYPE
   SYNTAX FSAPCtrlCreatEntry
   MAX-ACCESS not-accessible
   STATUS current
   DESCRIPTION
          "The entry of the AP control block"
   INDEX { fsAPName }
   ::= { fsAPCtrlCreatEntryTable 1}

FSAPCtrlCreatEntry ::=
    SEQUENCE {
        fsAPName                DisplayString,
        fsPriority              INTEGER,
        fsPrimaryACIP           IpAddress,
        fsPrimaryACName         DisplayString,
        fsSecondaryACIP         IpAddress,
        fsSecondaryACName       DisplayString,
        fsTertiaryACIP          IpAddress,
        fsTertiaryACName        DisplayString,
        fsAPCtrlCreatStatus     RowStatus
    }

--The AP control block name
fsAPName OBJECT-TYPE
     SYNTAX DisplayString
     MAX-ACCESS not-accessible
     STATUS current
     DESCRIPTION
             "The name of the AP control block"
     ::= { fsAPCtrlCreatEntry 1}

--The priority of AP control block
fsPriority OBJECT-TYPE
    SYNTAX INTEGER (1..4)
    MAX-ACCESS read-create
    STATUS current
    DESCRIPTION
            "The priority of AP control block"
    ::= { fsAPCtrlCreatEntry 2 }

--The primary AC  ip of AP control block
fsPrimaryACIP OBJECT-TYPE
    SYNTAX IpAddress
    MAX-ACCESS read-create
    STATUS current
    DESCRIPTION
            "The primary AC IP of AP control block"
    ::= { fsAPCtrlCreatEntry 3 }

--The primary AC Name of AP control block
fsPrimaryACName OBJECT-TYPE
     SYNTAX  DisplayString
     MAX-ACCESS read-create
     STATUS current
     DESCRIPTION
              "The primary AC Name of AP control block"
     ::= { fsAPCtrlCreatEntry 4 }

--The secondary AC  ip of AP control block
fsSecondaryACIP OBJECT-TYPE
    SYNTAX IpAddress
    MAX-ACCESS read-create
    STATUS current
    DESCRIPTION
            "The secondary AC IP of AP control block"
    ::= { fsAPCtrlCreatEntry 5 }

--The secondary AC Name of AP control block
fsSecondaryACName OBJECT-TYPE
     SYNTAX  DisplayString
     MAX-ACCESS read-create
     STATUS current
     DESCRIPTION
              "The secondary AC Name of AP control block"
     ::= { fsAPCtrlCreatEntry 6 }

--The tertiary AC  ip of AP control block
fsTertiaryACIP OBJECT-TYPE
    SYNTAX IpAddress
    MAX-ACCESS read-create
    STATUS current
    DESCRIPTION
            "The tertiary AC IP of AP control block"
    ::= { fsAPCtrlCreatEntry 7 }

--The tertiary AC Name of AP control block
fsTertiaryACName OBJECT-TYPE
     SYNTAX  DisplayString
     MAX-ACCESS read-create
     STATUS current
     DESCRIPTION
              "The tertiary AC Name of AP control block"
     ::= { fsAPCtrlCreatEntry 8 }

--The object indicates the creat or delete of the AP control table
fsAPCtrlCreatStatus OBJECT-TYPE
    SYNTAX RowStatus
    MAX-ACCESS read-create
    STATUS current
    DESCRIPTION
           "The flag of the AP control table"
    ::= {fsAPCtrlCreatEntry 9}


--*********5.creat the Wlan control entry***************
fsWLANCtrlCreatEntryTable OBJECT-TYPE
   SYNTAX SEQUENCE OF FSWLANCtrlCreatEntry
   MAX-ACCESS not-accessible
   STATUS current
   DESCRIPTION
          "Creat the WLAN control block"
   ::= {fsMobility 4}

fsWLANCtrlCreatEntry OBJECT-TYPE
   SYNTAX FSWLANCtrlCreatEntry
   MAX-ACCESS not-accessible
   STATUS current
   DESCRIPTION
          "The entry of the WLAN group control block"
   INDEX { fsWLANID }
   ::= { fsWLANCtrlCreatEntryTable 1}

FSWLANCtrlCreatEntry ::=
    SEQUENCE {
         fsWLANID              INTEGER,
         fsAnchorACIPaddr      IpAddress,
         fsWLANCtrlCreatStatus RowStatus,
         fsAnchorACIPaddrIPv6  Ipv6Address
    }

--the name of WLAN
fsWLANID OBJECT-TYPE
     SYNTAX INTEGER
     MAX-ACCESS read-only
     STATUS current
     DESCRIPTION
             "The name of the wlan"
     ::= { fsWLANCtrlCreatEntry 1 }

--the anchor ac ipv4 address of wlan
fsAnchorACIPaddr OBJECT-TYPE
     SYNTAX IpAddress
     MAX-ACCESS read-create
     STATUS current
     DESCRIPTION
             "The anchor ac ip address of wlan"
     ::= { fsWLANCtrlCreatEntry 2 }

--the object indicate creat or delete of the WLAN control table
fsWLANCtrlCreatStatus  OBJECT-TYPE
    SYNTAX RowStatus
    MAX-ACCESS read-create
    STATUS current
    DESCRIPTION
           "the object indicate creat or delete of the WLAN control table"
    ::= { fsWLANCtrlCreatEntry 3 }

--the anchor ac ipv6 address of wlan
fsAnchorACIPaddrIPv6 OBJECT-TYPE
     SYNTAX Ipv6Address
     MAX-ACCESS read-create
     STATUS current
     DESCRIPTION
             "The anchor ac ipv6 address of wlan"
     ::= { fsWLANCtrlCreatEntry 4 }

--***************simple param***************
--6 ping the other AC in the mobility
fsMobilityACPing OBJECT-TYPE
     SYNTAX IpAddress
     MAX-ACCESS read-write
     STATUS current
     DESCRIPTION
              "Ping the other AC in the mobility"
     ::= {fsMobility 5}

--7 Handoff Requests Received of Global Mobility Statistics
fsGlobalHandoffRequestsReceived OBJECT-TYPE
      SYNTAX INTEGER
      MAX-ACCESS read-write
      STATUS current
      DESCRIPTION
               "Handoff requests received of global mobility statistics"
      ::= {fsMobility 6}

--8 Handoff End Requests Received
fsGlobalHandoffEndRequestsReceived OBJECT-TYPE
     SYNTAX INTEGER
     MAX-ACCESS read-write
     STATUS current
     DESCRIPTION
             "Handoff end requests received"
     ::= {fsMobility 7}

--9 State Transitions Disabllowed
fsGlobalStateTransitionsDisabled OBJECT-TYPE
     SYNTAX INTEGER
     MAX-ACCESS read-write
     STATUS current
     DESCRIPTION
             "State transitions Disallowed"
     ::= {fsMobility 8}

--10 Resource Unavailable
fsGlobalResourceUnavailable OBJECT-TYPE
     SYNTAX INTEGER
     MAX-ACCESS read-write
     STATUS current
     DESCRIPTION
            "Resource Unavailable"
     ::= {fsMobility 9}

--11 Handoff Requests Ignored
fsRespondeHandoffRequestIgnored OBJECT-TYPE
      SYNTAX INTEGER
      MAX-ACCESS read-write
      STATUS current
      DESCRIPTION
             "Handoff Requests Ignored"
      ::= {fsMobility 10}

--12 Ping Pong Handoff Requests Dropped
fsRespondePingPongHandoffRequestsDropped OBJECT-TYPE
      SYNTAX INTEGER
      MAX-ACCESS read-write
      STATUS current
      DESCRIPTION
             "Ping Pong handoff Requests Dropped"
      ::= {fsMobility 11}

--13 Handoff Requests Drooped
fsRespondeHandoffRequestsDroped OBJECT-TYPE
      SYNTAX INTEGER
      MAX-ACCESS read-write
      STATUS current
      DESCRIPTION
             "Handoff Requests Droped"
      ::= {fsMobility 12}

--14 Handoff Requests Denied
fsRespondeHandoffRequestsDenied OBJECT-TYPE
      SYNTAX INTEGER
      MAX-ACCESS read-write
      STATUS current
      DESCRIPTION
             "Handoff Requests Denied"
      ::= {fsMobility 13}

--15 Client Handoff as local
fsRespondeClientHandoffasLocal OBJECT-TYPE
      SYNTAX INTEGER
      MAX-ACCESS read-write
      STATUS current
      DESCRIPTION
             "Client Handoff as local"
      ::= {fsMobility 14}

--16 Client Handoff as Foreign
fsRespondeClientHandoffasForeign OBJECT-TYPE
      SYNTAX INTEGER
      MAX-ACCESS read-write
      STATUS current
      DESCRIPTION
             "Client Handoff as Foreign"
      ::= {fsMobility 15}

--17 Anchor Requests Received
fsRespondeAnchorRequestsReceived OBJECT-TYPE
      SYNTAX INTEGER
      MAX-ACCESS read-write
      STATUS current
      DESCRIPTION
             "Anchor Requests Received"
      ::= {fsMobility 16}

--18 Anchor Requests Denied
fsRespondeAnchorRequestDenied OBJECT-TYPE
      SYNTAX INTEGER
      MAX-ACCESS read-write
      STATUS current
      DESCRIPTION
             "Anchor Requests Denied"
      ::= {fsMobility 17}

--19 Anchor Transferred
fsRespondeAnchorTransferred OBJECT-TYPE
      SYNTAX INTEGER
      MAX-ACCESS read-write
      STATUS current
      DESCRIPTION
             "Anchor Transferred"
      ::= {fsMobility 18}

--20 Handoff Requests Sent
fsInitHandoffRequestsSent OBJECT-TYPE
      SYNTAX INTEGER
      MAX-ACCESS read-write
      STATUS current
      DESCRIPTION
             "Handoff Requests Sent"
      ::= {fsMobility 19}

--21 Handoff Replies Received
fsInitHandoffReplyReceived OBJECT-TYPE
      SYNTAX INTEGER
      MAX-ACCESS read-write
      STATUS current
      DESCRIPTION
             "Handoff Replies Received"
      ::= {fsMobility 20}

--22 Handoff as local reveived
fsInitHandoffasLocalReceived OBJECT-TYPE
      SYNTAX INTEGER
      MAX-ACCESS read-write
      STATUS current
      DESCRIPTION
             "Handoff as local received"
      ::= {fsMobility 21}

--23 Handoff as Foreign Received
fsInitHandoffasForeignReceived OBJECT-TYPE
       SYNTAX INTEGER
       MAX-ACCESS read-write
       STATUS current
       DESCRIPTION
              "Handoff as Foreign Received"
       ::= {fsMobility 22}

--24 Handoff Denys Received
fsInitHandoffDenyReceived OBJECT-TYPE
        SYNTAX INTEGER
        MAX-ACCESS read-write
        STATUS current
        DESCRIPTION
              "Handoff Denys Received"
        ::= {fsMobility 23}

--25 Anchor Request Sent
fsInitAnchorRequestSent OBJECT-TYPE
         SYNTAX INTEGER
         MAX-ACCESS read-write
         STATUS current
         DESCRIPTION
                "Anchor Request Sent"
         ::= {fsMobility 24}

--26 Anchor Deny Received
fsInitAnchorDenyReceived OBJECT-TYPE
         SYNTAX INTEGER
         MAX-ACCESS read-write
         STATUS current
         DESCRIPTION
                "Anchor Deny Received"
         ::= {fsMobility 25}

--27 AP priority enable
fsAPPriorityEnable OBJECT-TYPE
         SYNTAX INTEGER
         MAX-ACCESS read-write
         STATUS current
         DESCRIPTION
                "AP priority enable"
         ::= {fsMobility 26}

--28 The primary backup ac ip of ALL AP control block
fsPrimaryBackUpACIP OBJECT-TYPE
    SYNTAX IpAddress
    MAX-ACCESS read-create
    STATUS current
    DESCRIPTION
            "The primary backup AC IP of ALL AP control block"
    ::= { fsMobility 27 }

--29 The primary backup ac name of ALL AP control block
fsPrimaryBackUpACName OBJECT-TYPE
     SYNTAX  DisplayString
     MAX-ACCESS read-create
     STATUS current
     DESCRIPTION
              "The primary backup ac name of ALL AP control block"
     ::= { fsMobility 28 }

--30 The secondary backup ac ip of ALL AP control block
fsSecondaryBackUpACIP OBJECT-TYPE
    SYNTAX IpAddress
    MAX-ACCESS read-create
    STATUS current
    DESCRIPTION
            "The secondary backup AC IP of ALL AP control block"
    ::= { fsMobility 29 }

--31 The secondary backup ac name of ALL AP control block
fsSecondaryBackUpACName OBJECT-TYPE
     SYNTAX  DisplayString
     MAX-ACCESS read-create
     STATUS current
     DESCRIPTION
              "The secondary backup ac name of ALL AP control block"
     ::= { fsMobility 30 }

--32 The teriary backup ac ip of ALL AP control block
fsTeriaryBackUpACip OBJECT-TYPE
    SYNTAX IpAddress
    MAX-ACCESS read-create
    STATUS current
    DESCRIPTION
            "The teriary backup AC IP of ALL AP control block"
    ::= { fsMobility 31 }

--33 The teriary backup ac name of ALL AP control block
fsTeriaryBackUpACName OBJECT-TYPE
     SYNTAX  DisplayString
     MAX-ACCESS read-create
     STATUS current
     DESCRIPTION
              "The teriary backup ac name of ALL AP control block"
     ::= { fsMobility 32 }

--34 The roaming successful times which in the same control domain (local roam)
fsACIntraRoam OBJECT-TYPE
     SYNTAX  Counter32
     MAX-ACCESS read-only
     STATUS current
     DESCRIPTION
              "The roaming successful times which in the same control domain"
     ::= { fsMobility 33 }

--35 The roaming out successful times which in the different control domain (inter ac roam)
fsACInterRoamIn OBJECT-TYPE
     SYNTAX  Counter32
     MAX-ACCESS read-only
     STATUS current
     DESCRIPTION
              "The roaming in successful times which in the different control domain"
     ::= { fsMobility 34 }

--36 The roaming in successful times which in the different control domain (inter ac roam)
fsACInterRoamOut OBJECT-TYPE
     SYNTAX  Counter32
     MAX-ACCESS read-only
     STATUS current
     DESCRIPTION
              "The roaming out successful times which in the different control domain"
     ::= { fsMobility 35 }

--37 ping the other IPv6 member in the mobility group
fsMobilityACPingIPv6 OBJECT-TYPE
     SYNTAX Ipv6Address
     MAX-ACCESS read-write
     STATUS current
     DESCRIPTION
              "Ping the other IPv6 AC in the mobility"
     ::= {fsMobility 36}

--*********38.Roam Mobility Member Entry***************
fsMobilityIPv6MemberEntryTable OBJECT-TYPE
    SYNTAX SEQUENCE OF FSMobilityIPv6MemberEntry
    MAX-ACCESS not-accessible
    STATUS current
    DESCRIPTION
         "Creat the roam mobility group member"
    ::= {fsMobility 37}

fsMobilityIPv6MemberEntry OBJECT-TYPE
    SYNTAX FSMobilityIPv6MemberEntry
    MAX-ACCESS not-accessible
    STATUS current
    DESCRIPTION
         "The entry of roam mobility member"
    INDEX  { fsRoamIPv6MemberGroupId, fsRoamIPv6MemberPeerAddress }
    ::= { fsMobilityIPv6MemberEntryTable 1 }

FSMobilityIPv6MemberEntry ::=
    SEQUENCE {
        fsRoamIPv6MemberGroupId                 INTEGER,
        fsRoamIPv6MemberPeerAddress             Ipv6Address,
        fsRoamIPv6MemberIsList                  INTEGER,
        fsRoamIPv6MemberDataChannelIsOK         INTEGER,
        fsRoamIPv6MemberDataChannelFailTimes    INTEGER,
        fsRoamIPv6MemberDTLSIsClient            INTEGER,
        fsRoamIPv6MemberDTLSIsOK                INTEGER,
        fsRoamIPv6MemberCreateStatus            RowStatus
    }

--The group id of roam mobility group member
fsRoamIPv6MemberGroupId OBJECT-TYPE
     SYNTAX  INTEGER (0..8)
     MAX-ACCESS read-only
     STATUS current
     DESCRIPTION
              "The group id of roam mobility group"
     ::= { fsMobilityIPv6MemberEntry 1 }

--The peer ipv4 address of roam mobility group member
fsRoamIPv6MemberPeerAddress OBJECT-TYPE
     SYNTAX  Ipv6Address
     MAX-ACCESS read-only
     STATUS current
     DESCRIPTION
              "The peer ipv4 address of roam mobility group member"
     ::= { fsMobilityIPv6MemberEntry 2 }

--The flag whether roam mobility group member in roam list
fsRoamIPv6MemberIsList OBJECT-TYPE
 SYNTAX  INTEGER (0..1)
     MAX-ACCESS read-create
     STATUS current
     DESCRIPTION
             "The flag whether roam mobility group member in roam list"
     ::= { fsMobilityIPv6MemberEntry 3 }

--The flag whether the data channel of roam mobility group member is ok
fsRoamIPv6MemberDataChannelIsOK OBJECT-TYPE
     SYNTAX  INTEGER (0..1)
     MAX-ACCESS read-only
     STATUS current
     DESCRIPTION
             "The flag whether the data channel of roam mobility group member is ok"
     ::= { fsMobilityIPv6MemberEntry 4 }

--The Fail times of the data channel of roam mobility group member
fsRoamIPv6MemberDataChannelFailTimes OBJECT-TYPE
     SYNTAX  INTEGER
     MAX-ACCESS read-only
     STATUS current
     DESCRIPTION
              "The Fail times of the data channel of roam mobility group member"
     ::= { fsMobilityIPv6MemberEntry 5 }

--The flag whether the roam group member is client
fsRoamIPv6MemberDTLSIsClient OBJECT-TYPE
     SYNTAX  INTEGER
     MAX-ACCESS read-only
     STATUS current
     DESCRIPTION
             "The flag whether the roam mobility group member is client"
     ::= { fsMobilityIPv6MemberEntry 6 }

--The flag whether the roam group member dtls is ok
fsRoamIPv6MemberDTLSIsOK OBJECT-TYPE
     SYNTAX  INTEGER (0..1)
     MAX-ACCESS read-only
     STATUS current
     DESCRIPTION
             "The flag whether the roam mobility group member dtls is ok"
     ::= { fsMobilityIPv6MemberEntry 7 }

--This object indicate the creat or delete of the table
fsRoamIPv6MemberCreateStatus OBJECT-TYPE
     SYNTAX   RowStatus
     MAX-ACCESS read-create
     STATUS   current
     DESCRIPTION
           "This object indicate the creat or delete of the Mobility table"
     ::= { fsMobilityIPv6MemberEntry 8 }

--*********39.Roam Mobility User***************
fsMobilityUserEntryTable OBJECT-TYPE
    SYNTAX SEQUENCE OF FSMobilityUserEntry
    MAX-ACCESS not-accessible
    STATUS current
    DESCRIPTION
         "Show the mobility user"
    ::= {fsMobility 38}

fsMobilityUserEntry OBJECT-TYPE
    SYNTAX FSMobilityUserEntry
    MAX-ACCESS not-accessible
    STATUS current
    DESCRIPTION
         "The entry of mobility user"
    INDEX  { fsRoamUserMac }
    ::= { fsMobilityUserEntryTable 1 }

FSMobilityUserEntry ::=
    SEQUENCE {
        fsRoamUserMac                           MacAddress,
        fsRoamUserRoamType                      INTEGER,
        fsRoamUserRoamOutAcAddressType          InetAddressType,
        fsRoamUserRoamOutAcAddress              InetAddress,
        fsRoamUserRoamInAcAddressType           InetAddressType,
        fsRoamUserRoamInAcAddress               InetAddress,
        fsRoamUserRoamOutApMac                  MacAddress,
        fsRoamUserRoamInApMac                   MacAddress,
        fsRoamUserRoamOutVid                    INTEGER,
        fsRoamUserRoamInVid                     INTEGER
    }

--The STA MAC of mobility user entry
fsRoamUserMac OBJECT-TYPE
     SYNTAX  MacAddress
     MAX-ACCESS read-only
     STATUS current
     DESCRIPTION
              "The STA MAC of mobility user entry"
     ::= { fsMobilityUserEntry 1 }
     
--The Roam Type of mobility user entry
fsRoamUserRoamType OBJECT-TYPE
     SYNTAX  INTEGER
     MAX-ACCESS read-only
     STATUS current
     DESCRIPTION
              "The Roam Type of mobility user entry"
     ::= { fsMobilityUserEntry 2 }
     
--The RO-AC Address Type of mobility user entry
fsRoamUserRoamOutAcAddressType OBJECT-TYPE
     SYNTAX  InetAddressType
     MAX-ACCESS read-only
     STATUS current
     DESCRIPTION
              "The RO-AC Address Type of mobility user entry"
     ::= { fsMobilityUserEntry 3 }
     
--The RO-AC Address of mobility user entry
fsRoamUserRoamOutAcAddress OBJECT-TYPE
     SYNTAX  InetAddress
     MAX-ACCESS read-only
     STATUS current
     DESCRIPTION
              "The RO-AC Address of mobility user entry"
     ::= { fsMobilityUserEntry 4 }
    
--The RI-AC Address Type of mobility user entry
fsRoamUserRoamInAcAddressType OBJECT-TYPE
     SYNTAX  InetAddressType
     MAX-ACCESS read-only
     STATUS current
     DESCRIPTION
              "The RI-AC Address Type of mobility user entry"
     ::= { fsMobilityUserEntry 5 }
     
--The RI-AC Address of mobility user entry
fsRoamUserRoamInAcAddress OBJECT-TYPE
     SYNTAX  InetAddress
     MAX-ACCESS read-only
     STATUS current
     DESCRIPTION
              "The RI-AC Address of mobility user entry"
     ::= { fsMobilityUserEntry 6 }

--The RO-AP MAC of mobility user entry
fsRoamUserRoamOutApMac OBJECT-TYPE
     SYNTAX  MacAddress
     MAX-ACCESS read-only
     STATUS current
     DESCRIPTION
              "The RO-AP MAC of mobility user entry"
     ::= { fsMobilityUserEntry 7 }
     
--The RI-AP MAC of mobility user entry
fsRoamUserRoamInApMac OBJECT-TYPE
     SYNTAX  MacAddress
     MAX-ACCESS read-only
     STATUS current
     DESCRIPTION
              "The RI-AP MAC of mobility user entry"
     ::= { fsMobilityUserEntry 8 }
    
--The RO-VLAN of mobility user entry
fsRoamUserRoamOutVid OBJECT-TYPE
     SYNTAX  INTEGER
     MAX-ACCESS read-only
     STATUS current
     DESCRIPTION
              "The RO-VLAN of mobility user entry"
     ::= { fsMobilityUserEntry 9 }
     
--The RI-VLAN of mobility user entry
fsRoamUserRoamInVid OBJECT-TYPE
     SYNTAX  INTEGER
     MAX-ACCESS read-only
     STATUS current
     DESCRIPTION
              "The RI-VLAN of mobility user entry"
     ::= { fsMobilityUserEntry 10 }
     
--*********40.Roam Mobility Track Entry***************
fsMobilityTrackEntryTable OBJECT-TYPE
    SYNTAX SEQUENCE OF FSMobilityTrackEntry
    MAX-ACCESS not-accessible
    STATUS current
    DESCRIPTION
         "Show the roam track of user"
    ::= {fsMobility 39}

fsMobilityTrackEntry OBJECT-TYPE
    SYNTAX FSMobilityTrackEntry
    MAX-ACCESS not-accessible
    STATUS current
    DESCRIPTION
         "The entry of roam mobility track"
    INDEX  { fsRoamTrackStaMac, fsRoamTrackId }
    ::= { fsMobilityTrackEntryTable 1 }

FSMobilityTrackEntry ::=
    SEQUENCE {
        fsRoamTrackStaMac                       MacAddress,
        fsRoamTrackId                           INTEGER,
        fsRoamTrackAcAddressType                InetAddressType,
        fsRoamTrackAcAddress                    InetAddress,
        fsRoamTrackApMac                        MacAddress,
        fsRoamTrackRadioId                      INTEGER,
        fsRoamTrackStaIp                        IpAddress,
        fsRoamTrackStaIpv6                      Ipv6Address,
        fsRoamTrackStaOnlineTime                INTEGER
    }

--The STA MAC of roam mobility track entry
fsRoamTrackStaMac OBJECT-TYPE
     SYNTAX  MacAddress
     MAX-ACCESS read-only
     STATUS current
     DESCRIPTION
              "The STA MAC of roam mobility track entry"
     ::= { fsMobilityTrackEntry 1 }

--The TrackId of roam mobility track entry
fsRoamTrackId OBJECT-TYPE
     SYNTAX  INTEGER
     MAX-ACCESS read-only
     STATUS current
     DESCRIPTION
              "The TrackId of roam mobility track entry"
     ::= { fsMobilityTrackEntry 2 }

--The AC Address Type of roam mobility track entry
fsRoamTrackAcAddressType OBJECT-TYPE
     SYNTAX  InetAddressType
     MAX-ACCESS read-only
     STATUS current
     DESCRIPTION
             "The AC Address Type of roam mobility track entry"
     ::= { fsMobilityTrackEntry 3 }

--The AC Address of roam mobility track entry
fsRoamTrackAcAddress OBJECT-TYPE
     SYNTAX  InetAddress
     MAX-ACCESS read-only
     STATUS current
     DESCRIPTION
             "The AC Address Type of roam mobility track entry"
     ::= { fsMobilityTrackEntry 4 }
     
--The AP Mac of roam mobility track entry
fsRoamTrackApMac OBJECT-TYPE
     SYNTAX  MacAddress
     MAX-ACCESS read-only
     STATUS current
     DESCRIPTION
              "The AP Mac of roam mobility track entry"
     ::= { fsMobilityTrackEntry 5 }

--The RadioId of roam mobility track entry
fsRoamTrackRadioId OBJECT-TYPE
     SYNTAX  INTEGER
     MAX-ACCESS read-only
     STATUS current
     DESCRIPTION
             "The RadioId of roam mobility track entry"
     ::= { fsMobilityTrackEntry 6 }

--The STA IPv4 Address of roam mobility track entry
fsRoamTrackStaIp OBJECT-TYPE
     SYNTAX  IpAddress
     MAX-ACCESS read-only
     STATUS current
     DESCRIPTION
             "The STA IPv4 Address of roam mobility track entry"
     ::= { fsMobilityTrackEntry 7 }

--The STA IPv6 Address of roam mobility track entry
fsRoamTrackStaIpv6 OBJECT-TYPE
     SYNTAX  Ipv6Address
     MAX-ACCESS read-only
     STATUS current
     DESCRIPTION
             "The STA IPv6 Address of roam mobility track entry"
     ::= { fsMobilityTrackEntry 8 }
     
--The STA online time of roam mobility track entry
fsRoamTrackStaOnlineTime OBJECT-TYPE
     SYNTAX  INTEGER
     MAX-ACCESS read-only
     STATUS current
     DESCRIPTION
             "The STA online time of roam mobility track entry"
     ::= { fsMobilityTrackEntry 9 }

--*********40.Roam Mobility User Json***************
fsMobilityUserJsonTable OBJECT-TYPE
    SYNTAX  SEQUENCE OF FSMobilityUserJsonEntry
    MAX-ACCESS  not-accessible
    STATUS  current
    DESCRIPTION
            "Show the mobility user json table."
    ::= { fsMobility 40 }

fsMobilityUserJsonEntry OBJECT-TYPE
    SYNTAX  FSMobilityUserJsonEntry
    MAX-ACCESS  not-accessible
    STATUS  current
    DESCRIPTION
        "Show the mobility user json entry."
    INDEX   { fsMobilityUserJsonMacAddr}
    ::= { fsMobilityUserJsonTable 1 }

FSMobilityUserJsonEntry ::=
    SEQUENCE {
        fsMobilityUserJsonMacAddr            MacAddress,
        fsMobilityUserJsonContent            OCTET STRING
     }
         
fsMobilityUserJsonMacAddr  OBJECT-TYPE
    SYNTAX  MacAddress
    MAX-ACCESS  read-only
    STATUS  current
    DESCRIPTION
            "The STA's mac address."
    ::= { fsMobilityUserJsonEntry 1}
    
fsMobilityUserJsonContent OBJECT-TYPE
    SYNTAX  OCTET STRING (SIZE (1..1023))
    MAX-ACCESS  read-only
    STATUS  current
    DESCRIPTION
            "This object represents the sta roam content with json format."
    ::= { fsMobilityUserJsonEntry 2}

fsMobilityMIBCompliances OBJECT IDENTIFIER ::={fsMobilityIf 1}
fsMobilityMIBGroups      OBJECT IDENTIFIER ::={fsMobilityIf 2}

--compliance statements
fsMobilityMIBCompliance MODULE-COMPLIANCE
      STATUS current
      DESCRIPTION
               "The compliance statement for entities which implement the CAPWAP MOBILITY MIB"
      MODULE -- this module
             MANDATORY-GROUPS{ fsMobilityMIBGroup
             }
      ::= { fsMobilityMIBCompliances 1}

--units of conformance
fsMobilityMIBGroup OBJECT-GROUP
      OBJECTS {
--ROAM GROUP
        fsRoamGroupName,
        fsRoamGroupMyAddress,
        fsRoamGroupMcEnable,
        fsRoamGroupMcAddress,
        fsRoamGroupKeepaliveCount,
        fsRoamGroupKeepaliveInterval,
        fsRoamGroupIsFast,
        fsRoamGroupCreateStatus,
--ROAM MEMBER
        fsRoamMemberIsList,
        fsRoamMemberDataChannelIsOK,
        fsRoamMemberDataChannelFailTimes,
        fsRoamMemberDTLSIsClient,
        fsRoamMemberDTLSIsOK,
        fsRoamMemberCreateStatus,
--AP  MEMBER
        fsPriority,
        fsPrimaryACIP,
        fsPrimaryACName,
        fsSecondaryACIP,
        fsSecondaryACName,
        fsTertiaryACIP,
        fsTertiaryACName,
        fsAPCtrlCreatStatus,
--WLAN MEMBER
        fsAnchorACIPaddr,
        fsWLANCtrlCreatStatus,
--Mobility staticstic
        fsGlobalHandoffRequestsReceived,
        fsGlobalHandoffEndRequestsReceived,
        fsGlobalStateTransitionsDisabled,
        fsGlobalResourceUnavailable,
        fsRespondeHandoffRequestIgnored,
        fsRespondePingPongHandoffRequestsDropped,
        fsRespondeHandoffRequestsDroped,
        fsRespondeHandoffRequestsDenied,
        fsRespondeClientHandoffasLocal,
        fsRespondeClientHandoffasForeign,
        fsRespondeAnchorRequestsReceived,
        fsRespondeAnchorRequestDenied,
        fsRespondeAnchorTransferred,
        fsInitHandoffRequestsSent,
        fsInitHandoffReplyReceived,
        fsInitHandoffasLocalReceived,
        fsInitHandoffasForeignReceived,
        fsInitHandoffDenyReceived,
        fsInitAnchorRequestSent,
        fsInitAnchorDenyReceived,
        fsAPPriorityEnable,
        fsPrimaryBackUpACIP,
        fsPrimaryBackUpACName,
        fsSecondaryBackUpACIP,
        fsSecondaryBackUpACName,
        fsTeriaryBackUpACip,
        fsTeriaryBackUpACName,
        fsACIntraRoam,
        fsACInterRoamIn,
        fsACInterRoamOut,
        fsMobilityACPingIPv6,
--ROAM IPv6 Member
        fsRoamIPv6MemberGroupId,
        fsRoamIPv6MemberPeerAddress,
        fsRoamIPv6MemberIsList,
        fsRoamIPv6MemberDataChannelIsOK,
        fsRoamIPv6MemberDataChannelFailTimes,
        fsRoamIPv6MemberDTLSIsClient,
        fsRoamIPv6MemberDTLSIsOK,
        fsRoamIPv6MemberCreateStatus,
--ROAM User Entry
        fsRoamUserMac,
        fsRoamUserRoamType,
        fsRoamUserRoamOutAcAddressType,
        fsRoamUserRoamOutAcAddress,
        fsRoamUserRoamInAcAddressType,
        fsRoamUserRoamInAcAddress,
        fsRoamUserRoamOutApMac,
        fsRoamUserRoamInApMac,
        fsRoamUserRoamOutVid,
        fsRoamUserRoamInVid,
--ROAM Track Entry
        fsRoamTrackStaMac,
        fsRoamTrackId,
        fsRoamTrackAcAddressType,
        fsRoamTrackAcAddress,
        fsRoamTrackApMac,
        fsRoamTrackRadioId,
        fsRoamTrackStaIp,
        fsRoamTrackStaIpv6,
        fsRoamTrackStaOnlineTime
      }
      STATUS current
      DESCRIPTION
               "A collection of objects providing mobility configure."
      ::= {fsMobilityMIBGroups 1 }


fsMobilityTrapSta       OBJECT IDENTIFIER ::= { fsMobilityTrap 1 }
fsMobilityTrapStaIf     OBJECT IDENTIFIER ::= { fsMobilityTrap 2 }

-- ****************************************
--
--               Notify nodes
--
-- ****************************************
fsMobilityNotifyApMac OBJECT-TYPE
    SYNTAX      MacAddress
    MAX-ACCESS  accessible-for-notify
    STATUS      current
    DESCRIPTION
        "Represents the unique identifier of a WTP."
    ::= { fsMobilityTrapSta 1 }

fsMobilityNotifyStaMac OBJECT-TYPE
    SYNTAX      MacAddress
    MAX-ACCESS  accessible-for-notify
    STATUS      current
    DESCRIPTION
        "Represents the unique identifier of a STA."
    ::= { fsMobilityTrapSta 2 }

fsMobilityNotifyApIp OBJECT-TYPE
    SYNTAX      IpAddress
    MAX-ACCESS  accessible-for-notify
    STATUS      current
    DESCRIPTION
        "Represents the Ip address of a WTP."
    ::= { fsMobilityTrapSta 3 }

fsMobilityNotifyStaIp OBJECT-TYPE
    SYNTAX      IpAddress
    MAX-ACCESS  accessible-for-notify
    STATUS      current
    DESCRIPTION
        "Represents the Ip of a STA."
    ::= { fsMobilityTrapSta 4 }

fsMobilityNotifyStaOperType OBJECT-TYPE
    SYNTAX      INTEGER
    MAX-ACCESS  accessible-for-notify
    STATUS      current
    DESCRIPTION
        "Represents the STA operation, 1-del,2-add,3-roaming,4-ipupdate,5-ipv6update"
    ::= { fsMobilityTrapSta 5 }

fsMobilityNotifyStaApRadioId OBJECT-TYPE
    SYNTAX      INTEGER(1..2)
    MAX-ACCESS  accessible-for-notify
    STATUS      current
    DESCRIPTION
        "Represents the radio id which STA attach."
    ::= { fsMobilityTrapSta 6 }

fsMobilityNotifyStaApRadioType OBJECT-TYPE
    SYNTAX      INTEGER (1..2)
    MAX-ACCESS  accessible-for-notify
    STATUS      current
    DESCRIPTION
              "1--802.11b
               2--802.11a"
    ::= { fsMobilityTrapSta 7 }

fsMobilityNotifyStaVlanId OBJECT-TYPE
    SYNTAX      INTEGER (1..4094)
    MAX-ACCESS  accessible-for-notify
    STATUS      current
    DESCRIPTION
              "Vlan Id the sta belongs to"
    ::= { fsMobilityTrapSta 8 }

fsMobilityNotifyStaWlanId OBJECT-TYPE
    SYNTAX      INTEGER (1..4095)
    MAX-ACCESS  accessible-for-notify
    STATUS      current
    DESCRIPTION
              "Wlan Id the sta belongs to"
    ::= { fsMobilityTrapSta 9 }

fsMobilityNotifyStaIpv6 OBJECT-TYPE
    SYNTAX      Ipv6Address
    MAX-ACCESS  accessible-for-notify
    STATUS      current
    DESCRIPTION
              "Sta ipv6 address."
    ::= { fsMobilityTrapSta 10 }

fsMobilityNotifyStaAssoAuthMode  OBJECT-TYPE
    SYNTAX  INTEGER {
        open(0),
        wep(1),
        dot1x-wep(2),
        dot1x-wpa(3),
        dot1x-wpa2(4),
        mab(5),
        psk-wpa(6),
        psk-wpa2(7),
        wapi(8)
    }
    MAX-ACCESS  accessible-for-notify
    STATUS  current
    DESCRIPTION
            "The Sta associate authentication mode."
    ::= { fsMobilityTrapSta 11}

fsMobilityNotifyStaNetAuthMode  OBJECT-TYPE
    SYNTAX  INTEGER {
        open(0),
        web(1)
    }
    MAX-ACCESS  accessible-for-notify
    STATUS  current
    DESCRIPTION
            "The Sta's authentication mode after associated."
    ::= { fsMobilityTrapSta 12}

fsMobilityNotifyStaSsid  OBJECT-TYPE
    SYNTAX  DisplayString
    MAX-ACCESS  accessible-for-notify
    STATUS  current
    DESCRIPTION
            "The wlan ssid with the sta associated."
    ::= { fsMobilityTrapSta 13}

fsMobilityNotifyStaLinkRate  OBJECT-TYPE
    SYNTAX  INTEGER
    MAX-ACCESS  accessible-for-notify
    STATUS  current
    DESCRIPTION
            "The link rate with the sta associated, unit: 1kbps."
    ::= { fsMobilityTrapSta 14}

fsMobilityNotifyStaCurChan  OBJECT-TYPE
    SYNTAX  INTEGER
    MAX-ACCESS  accessible-for-notify
    STATUS  current
    DESCRIPTION
            "The Sta current use channel after associated."
    ::= { fsMobilityTrapSta 15}

fsMobilityNotifyStaClientType  OBJECT-TYPE
    SYNTAX  DisplayString
    MAX-ACCESS  accessible-for-notify
    STATUS  current
    DESCRIPTION
            "The Sta's type."
    ::= { fsMobilityTrapSta 16}

fsMobilityNotifyStaRssi OBJECT-TYPE
    SYNTAX  INTEGER
    MAX-ACCESS  accessible-for-notify
    STATUS  current
    DESCRIPTION
            "The Sta's RSSI."
    ::= { fsMobilityTrapSta 17}

fsMobilityNotifyStaReason OBJECT-TYPE
    SYNTAX  DisplayString
    MAX-ACCESS  accessible-for-notify
    STATUS  current
    DESCRIPTION
            "The Sta's down reason."
    ::= { fsMobilityTrapSta 18}

fsMobilityNotifyStaOper NOTIFICATION-TYPE
    OBJECTS     {
                  fsMobilityNotifyApMac,
                  fsMobilityNotifyStaMac,
                  fsMobilityNotifyApIp,
                  fsMobilityNotifyStaIp,
                  fsMobilityNotifyStaOperType,
                  fsMobilityNotifyStaApRadioId,
                  fsMobilityNotifyStaApRadioType,
                  fsMobilityNotifyStaVlanId,
                  fsMobilityNotifyStaWlanId,
                  fsMobilityNotifyStaIpv6,
                  fsMobilityNotifyStaAssoAuthMode,
                  fsMobilityNotifyStaNetAuthMode,
                  fsMobilityNotifyStaSsid,
                  fsMobilityNotifyStaLinkRate,
                  fsMobilityNotifyStaCurChan,
                  fsMobilityNotifyStaClientType,
                  fsMobilityNotifyStaRssi,
                  fsMobilityNotifyStaReason
                }
    STATUS      current
    DESCRIPTION
        "This notification is sent by the AC when a sta enter or quit or ip update."
    ::= { fsMobilityTrapStaIf 1 }

END

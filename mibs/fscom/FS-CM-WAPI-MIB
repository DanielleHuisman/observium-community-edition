-- *******************************************************************
-- FS-CM-WAPI-MIB.mib : FS WAPI MIB according the standards of China Mobile file
-- February 2010, liangbaitian
--
-- Copyright (c) 2010 by FS.COM Inc..
-- All rights reserved.
-- *******************************************************************
FS-CM-WAPI-MIB DEFINITIONS ::= BEGIN
    IMPORTS
        MODULE-IDENTITY,
        OBJECT-TYPE,
        Integer32,
        Counter32,
        IpAddress,
        Unsigned32
            FROM SNMPv2-SMI
        TruthValue,
        DisplayString,
        MacAddress,
        RowStatus
            FROM SNMPv2-TC
        Gauge
            FROM RFC1155-SMI
        MODULE-COMPLIANCE,
        NOTIFICATION-GROUP,
        OBJECT-GROUP
            FROM SNMPv2-CONF
        fsApgWlanId
            FROM FS-AC-MGMT-MIB
        ifIndex
            FROM RFC1213-MIB
        fsMgmt
            FROM FS-SMI;
--*******************************************
--* module definition
--*******************************************
cmStandardmibmodule MODULE-IDENTITY
    LAST-UPDATED    "201002260000Z"
    ORGANIZATION
        "FS.COM Inc.."
    CONTACT-INFO
        "Tel: 400-865-2852
           E-mail: https://www.fs.com/live_chat_service_mail.html "

    DESCRIPTION
       "
       Wlan software private MIB for FS SNC according to the China
       Mobile standard. This is device manage MIB.
       "
    REVISION      "201002280000Z"
    DESCRIPTION
       "Initial version of this MIB module."

    ::= { fsMgmt  70 }

cmStandardMIBObjects OBJECT IDENTIFIER  ::= { cmStandardmibmodule 1 }
cmStandardCompliances OBJECT IDENTIFIER  ::= { cmStandardmibmodule 2 }
cmStandardGroup OBJECT IDENTIFIER  ::= { cmStandardmibmodule 3 }

--**************************************************
--* apAttributeInfoTable begins * 
--**************************************************
apAttributeInfoTable  OBJECT-TYPE
    SYNTAX SEQUENCE OF ApAttributeInfoEntry
    MAX-ACCESS not-accessible
    STATUS current
    DESCRIPTION
      "The attribute information table."
    ::={ cmStandardMIBObjects 1 }


apAttributeInfoEntry  OBJECT-TYPE
    SYNTAX ApAttributeInfoEntry
    MAX-ACCESS not-accessible
    STATUS current
    DESCRIPTION
      "The attribute information entry."
    INDEX { fsApgWlanId }
    ::={ apAttributeInfoTable 1 }

ApAttributeInfoEntry ::=
    SEQUENCE {
        apSysNEId                   DisplayString,
        apSysHostName               DisplayString,
        apSysLocation               DisplayString,
        apManufacturer              DisplayString,
        apSysVersion                DisplayString,
        apMacAddressConnectedWithAC	DisplayString,
        apCurrentBSSID              DisplayString,
        apMaxSimultUsers            INTEGER,
        apMaxSimultTraffic          INTEGER,
        apUpTime                    INTEGER
    }

apSysNEId OBJECT-TYPE
    SYNTAX DisplayString (SIZE(16..255))
    MAX-ACCESS read-write
    STATUS current
    DESCRIPTION
        "Network elements encoding of AP, unifiedly defined by
        China Mobile. It's length is not less than 16."
    ::= { apAttributeInfoEntry 1 }

apSysHostName OBJECT-TYPE
    SYNTAX DisplayString (SIZE(40..255))
    MAX-ACCESS read-write
    STATUS current
    DESCRIPTION
        "The AP device name, in line with the naming
        convention of China Mobile. It's length will not be
        shorter than 40."
    ::= { apAttributeInfoEntry 2 }

apSysLocation OBJECT-TYPE
    SYNTAX DisplayString
    MAX-ACCESS read-write
    STATUS current
    DESCRIPTION
        "The location information of the AP device, in detail
        including the name of hot-point or the floor number of
        the machine room."
    ::= { apAttributeInfoEntry 3 }

apManufacturer OBJECT-TYPE
    SYNTAX DisplayString
    MAX-ACCESS read-write
    STATUS current
    DESCRIPTION
        "The manufactureer of the ap device."
    ::= { apAttributeInfoEntry 4 }

apSysVersion OBJECT-TYPE
    SYNTAX DisplayString
    MAX-ACCESS read-write
    STATUS current
    DESCRIPTION
        "The version of network elements."
    ::= { apAttributeInfoEntry 5 }

apMacAddressConnectedWithAC OBJECT-TYPE
    SYNTAX DisplayString
    MAX-ACCESS read-write
    STATUS current
    DESCRIPTION
        "The interface of AP which connects with AC."
    ::= { apAttributeInfoEntry 6 }

 apCurrentBSSID OBJECT-TYPE
    SYNTAX DisplayString
    MAX-ACCESS read-write
    STATUS current
    DESCRIPTION
        "The current bssid of the AP device."
    ::= { apAttributeInfoEntry 7 }

apMaxSimultUsers OBJECT-TYPE
    SYNTAX INTEGER
    MAX-ACCESS read-write
    STATUS current
    DESCRIPTION
        "The MAX count of the users the AP device"
    ::= { apAttributeInfoEntry 8 }

apMaxSimultTraffic OBJECT-TYPE
    SYNTAX INTEGER
    MAX-ACCESS read-write
    STATUS current
    DESCRIPTION
        "The MAX traffic the AP can handle."
    ::= { apAttributeInfoEntry 9 }

apUpTime OBJECT-TYPE
    SYNTAX INTEGER
    MAX-ACCESS read-write
    STATUS current
    DESCRIPTION
        "The run time of the AP."
    ::= { apAttributeInfoEntry 10 }

--**************************************************
--* apAttributeInfoTable ends
--**************************************************

--**************************************************
--* apconfigurationInfoTable begins
--**************************************************
apconfigurationInfoTable  OBJECT-TYPE
    SYNTAX SEQUENCE OF ApconfigurationInfoEntry
    MAX-ACCESS not-accessible
    STATUS current
    DESCRIPTION
      "The table used to apac the configuration information of ap/ac."
    ::={ cmStandardMIBObjects 2 }

apconfigurationInfoEntry  OBJECT-TYPE
    SYNTAX ApconfigurationInfoEntry
    MAX-ACCESS not-accessible
    STATUS current
    DESCRIPTION
      "The entry of the table used to apac the configuration information of ap/ac."
    INDEX { fsApgWlanId }
    ::={ apconfigurationInfoTable 1 }


ApconfigurationInfoEntry ::=
    SEQUENCE {
        apIPAddress         IpAddress,
        apIpAdEntNetMask    IpAddress,
        apWorkingMode       INTEGER,
        apBGmode            INTEGER
    }

apIPAddress OBJECT-TYPE
    SYNTAX IpAddress
    MAX-ACCESS read-write
    STATUS current
    DESCRIPTION
        "The ip of AP."
    ::= { apconfigurationInfoEntry 1 }

apIpAdEntNetMask OBJECT-TYPE
    SYNTAX IpAddress
    MAX-ACCESS read-write
    STATUS current
    DESCRIPTION
        "The netmask of the AP ip."
    ::= { apconfigurationInfoEntry 2 }

apWorkingMode OBJECT-TYPE
    SYNTAX INTEGER
    MAX-ACCESS read-write
    STATUS current
    DESCRIPTION
        "The working mode of ap."
    ::= { apconfigurationInfoEntry 3 }

apBGmode OBJECT-TYPE
    SYNTAX INTEGER
    MAX-ACCESS read-write
    STATUS current
    DESCRIPTION
        "The collection point."
    ::= { apconfigurationInfoEntry 4 }

--**************************************************
--* apconfigurationInfoTable ends
--**************************************************

--**************************************************
--* apacWAPIconfigurationInfoTable begins
--**************************************************
apacWAPIconfigurationInfoTable OBJECT-TYPE
    SYNTAX SEQUENCE OF ApacWAPIconfigurationInfoEntry
    MAX-ACCESS not-accessible
    STATUS current
    DESCRIPTION
        "The WAPI configuration information table used to apac."
    ::= { cmStandardMIBObjects 3 }

apacWAPIconfigurationInfoEntry OBJECT-TYPE
    SYNTAX ApacWAPIconfigurationInfoEntry
    MAX-ACCESS not-accessible
    STATUS current
    DESCRIPTION
        "The WAPI configuration information entry."
    INDEX
        { fsApgWlanId }
    ::= { apacWAPIconfigurationInfoTable 1 }

ApacWAPIconfigurationInfoEntry ::=
    SEQUENCE {
        apWAPIAuthMode                  TruthValue,
        acWAPIAuthMode                  TruthValue,
        acWAPIASIPAddress               IpAddress,
        acWAPICertInstalled             TruthValue,
        cpuHandleAbility                OCTET STRING,
        memoryCapacity                  OCTET STRING,
        flashmemCapacity                OCTET STRING,
        support80211g                   OCTET STRING,
        apWAPIMaxUserNum                INTEGER,
        peruserWAPIMaxBindwithAllocated INTEGER,
        mutiModeAccesssimultStatus      TruthValue
    }

apWAPIAuthMode OBJECT-TYPE
    SYNTAX TruthValue
    MAX-ACCESS read-write
    STATUS current
    DESCRIPTION
        "Whether the WAPI security architecture of ap is enabled."
    ::= { apacWAPIconfigurationInfoEntry 1 }

acWAPIAuthMode OBJECT-TYPE
    SYNTAX TruthValue
    MAX-ACCESS read-write
    STATUS current
    DESCRIPTION
        "Whether the WAPI security architecture of ac is enabled."
    ::= { apacWAPIconfigurationInfoEntry 2 }

acWAPIASIPAddress OBJECT-TYPE
    SYNTAX IpAddress
    MAX-ACCESS read-write
    STATUS current
    DESCRIPTION
        "The ip of the WAPI AS under the AC configuration."
    ::= { apacWAPIconfigurationInfoEntry 3 }

acWAPICertInstalled OBJECT-TYPE
    SYNTAX TruthValue
    MAX-ACCESS read-write
    STATUS current
    DESCRIPTION
        "Whether the WAPI security architecture of ac is enabled."
    ::= { apacWAPIconfigurationInfoEntry 4 }

cpuHandleAbility OBJECT-TYPE
    SYNTAX OCTET STRING
    MAX-ACCESS read-write
    STATUS current
    DESCRIPTION
        "The ability the CPU handle tasks."
    ::= { apacWAPIconfigurationInfoEntry 5 }

memoryCapacity OBJECT-TYPE
    SYNTAX OCTET STRING
    MAX-ACCESS read-write
    STATUS current
    DESCRIPTION
        "The capability of the memory."
    ::= { apacWAPIconfigurationInfoEntry 6 }

flashmemCapacity OBJECT-TYPE
    SYNTAX OCTET STRING
    MAX-ACCESS read-write
    STATUS current
    DESCRIPTION
        "The capability of the flash memory."
    ::= { apacWAPIconfigurationInfoEntry 7 }

support80211g OBJECT-TYPE
    SYNTAX OCTET STRING
    MAX-ACCESS read-write
    STATUS current
    DESCRIPTION
        "Whether supports the IEEE 802.11g standard."
    ::= { apacWAPIconfigurationInfoEntry 8 }

apWAPIMaxUserNum OBJECT-TYPE
    SYNTAX INTEGER
    MAX-ACCESS read-write
    STATUS current
    DESCRIPTION
        "The max count of the ac's users under the special WAPI mode."
    ::= { apacWAPIconfigurationInfoEntry 9 }

peruserWAPIMaxBindwithAllocated OBJECT-TYPE
    SYNTAX INTEGER
    MAX-ACCESS read-write
    STATUS current
    DESCRIPTION
        "The max value of the bindwith allocated per user under the
        special WAPI mode.."
    ::= { apacWAPIconfigurationInfoEntry 10 }

mutiModeAccesssimultStatus OBJECT-TYPE
    SYNTAX TruthValue
    MAX-ACCESS read-write
    STATUS current
    DESCRIPTION
        "Whether it is in the muti-mode simulaneously."
    ::= { apacWAPIconfigurationInfoEntry 11 }
--**************************************************
--* apacWAPIconfigurationInfoTable ends
--**************************************************

--***************************************************************************
-- *  the gb15629dot11wapiConfigExtraTable table
-- ************************************************************************
gb15629dot11wapiConfigExtraTable OBJECT-TYPE
    SYNTAX SEQUENCE OF Gb15629dot11wapiConfigExtraEntry
    MAX-ACCESS not-accessible
    STATUS current
    DESCRIPTION

        " Extra configuration of the attributes of security, allow the agent has several entities by the
        table form. "
    ::= { cmStandardMIBObjects 4 }

gb15629dot11wapiConfigExtraEntry OBJECT-TYPE
    SYNTAX Gb15629dot11wapiConfigExtraEntry
    MAX-ACCESS not-accessible
    STATUS current
    DESCRIPTION

        " an item of the gb15629dot11wapiConfigTable, an agent may has several interfaces, each
        interface has a unique MAC address.the interfaces of this criterion and the context interfaces
        of the Internet standard MIB are corresponding one by one. So the entity of ifIndex can be
        used directly to identify the right object entity defined here.

        ifIndex – each interface of this criterion is expreesed by an ifEntry. The interface table
        of the MIB module is indexed by ifIndex. "
    INDEX
        {
            ifIndex
        }
    ::= { gb15629dot11wapiConfigExtraTable 1 }

Gb15629dot11wapiConfigExtraEntry ::=
    SEQUENCE {
        gb15629dot11wapiGroupCipherRequested                DisplayString,
        gb15629dot11wapiConfigUnicastCipher                 DisplayString,
        gb15629dot11wapiConfigUnicastCipherEnabled          TruthValue,
        gb15629dot11wapiConfigUnicastCipherSize             Unsigned32,
        gb15629dot11wapiConfigAuthenticationSuite           DisplayString,
        gb15629dot11wapiConfigAuthenticationSuiteEnabled    TruthValue
    }

gb15629dot11wapiGroupCipherRequested OBJECT-TYPE
    SYNTAX DisplayString
    MAX-ACCESS read-only
    STATUS current
    DESCRIPTION

        " Muticast cipher suites of the last requirements. "
    ::= { gb15629dot11wapiConfigExtraEntry 1 }

gb15629dot11wapiConfigUnicastCipher OBJECT-TYPE
    SYNTAX DisplayString
    MAX-ACCESS read-only
    STATUS current
    DESCRIPTION

        " The unicast key suite the entry supports. "
    ::= { gb15629dot11wapiConfigExtraEntry 2 }

gb15629dot11wapiConfigUnicastCipherEnabled OBJECT-TYPE
    SYNTAX TruthValue
    MAX-ACCESS read-write
    STATUS current
    DESCRIPTION

        "This attribute means whether the object enables or disable the unicast key."
    ::= { gb15629dot11wapiConfigExtraEntry 3 }

gb15629dot11wapiConfigUnicastCipherSize OBJECT-TYPE
    SYNTAX Unsigned32
    MAX-ACCESS read-write
    STATUS current
    DESCRIPTION
        "This bits of the unicast key length."
    ::= { gb15629dot11wapiConfigExtraEntry 4 }

gb15629dot11wapiConfigAuthenticationSuite OBJECT-TYPE
    SYNTAX DisplayString
    MAX-ACCESS read-only
    STATUS current
    DESCRIPTION

        " The AKM suite. "
    ::= { gb15629dot11wapiConfigExtraEntry 5 }

gb15629dot11wapiConfigAuthenticationSuiteEnabled OBJECT-TYPE
    SYNTAX TruthValue
    MAX-ACCESS read-write
    STATUS current
    DESCRIPTION

        "Whther the AKM suite is in the status 'enbaled' or 'prohabited'."
    ::= { gb15629dot11wapiConfigExtraEntry 6 }

--********************************************************************
-- *  gb15629dot11wapiConfigExtraTable ends here
-- *****************************************************************

--**************************************************
--* softorHardwareconfigInfoTable begins
--**************************************************
apacsoftorHardwareconfigInfoTable OBJECT-TYPE
    SYNTAX SEQUENCE OF SoftorHardwareconfigInfoEntry
    MAX-ACCESS not-accessible
    STATUS current
    DESCRIPTION
        "The table inluding the software or hardware configuration
        information of the AP/AC."
    ::= { cmStandardMIBObjects 5 }

apacsoftorHardwareconfigInfoEntry OBJECT-TYPE
    SYNTAX SoftorHardwareconfigInfoEntry
    MAX-ACCESS not-accessible
    STATUS current
    DESCRIPTION
        "The table inluding the software or hardware configuration
        information of the AP/AC."
    INDEX
    { fsApgWlanId }
    ::= { apacsoftorHardwareconfigInfoTable 1 }

SoftorHardwareconfigInfoEntry ::=
    SEQUENCE {
        apSoftwareName          OCTET STRING,
        apSoftwareVersion       DisplayString,
        apSoftwareVendor        DisplayString,
        acSoftwareName          OCTET STRING,
        acSoftwareVersion       DisplayString,
        acSoftwareVendor        DisplayString
    }
    
apSoftwareName OBJECT-TYPE
    SYNTAX OCTET STRING
    MAX-ACCESS read-write
    STATUS current
    DESCRIPTION
        "The software name of the ap system."
    ::= { apacsoftorHardwareconfigInfoEntry 1 }

apSoftwareVersion OBJECT-TYPE
    SYNTAX DisplayString
    MAX-ACCESS read-write
    STATUS current
    DESCRIPTION
        "The software version of the ap system."
    ::= { apacsoftorHardwareconfigInfoEntry 2 }

apSoftwareVendor OBJECT-TYPE
    SYNTAX DisplayString
    MAX-ACCESS read-write
    STATUS current
    DESCRIPTION
        "The software vendor of the ap system."
    ::= { apacsoftorHardwareconfigInfoEntry 3 }


acSoftwareName OBJECT-TYPE
    SYNTAX OCTET STRING
    MAX-ACCESS read-write
    STATUS current
    DESCRIPTION
        "The software name of the ac system."
    ::= { apacsoftorHardwareconfigInfoEntry 4 }

acSoftwareVersion OBJECT-TYPE
    SYNTAX DisplayString
    MAX-ACCESS read-write
    STATUS current
    DESCRIPTION
        "The software version of the ac system."
    ::= { apacsoftorHardwareconfigInfoEntry 5 }

acSoftwareVendor OBJECT-TYPE
    SYNTAX DisplayString
    MAX-ACCESS read-write
    STATUS current
    DESCRIPTION
        "The software vendor of the ac system."
    ::= { apacsoftorHardwareconfigInfoEntry 6 }

--**************************************************
--* softorHardwareconfigInfoTable ends
--**************************************************

--**************************************************
--* apPhyInterfaceConfigurationParametersTable begins
--**************************************************
apPhyInterfaceConfigurationParametersTable OBJECT-TYPE
    SYNTAX SEQUENCE OF APPhyInterfaceConfigurationParametersEntry
    MAX-ACCESS not-accessible
    STATUS current
    DESCRIPTION
        "The table inluding the physical interface configuration
        parameters of the AP/AC."
    ::= { cmStandardMIBObjects 6 }

apPhyInterfaceConfigurationParametersEntry OBJECT-TYPE
    SYNTAX APPhyInterfaceConfigurationParametersEntry
    MAX-ACCESS not-accessible
    STATUS current
    DESCRIPTION
        "The entry of phyInterfaceConfigurationParametersTable."
    INDEX
        {
            fsApgWlanId
        }
    ::= { apPhyInterfaceConfigurationParametersTable 1 }

APPhyInterfaceConfigurationParametersEntry ::=
    SEQUENCE {
        apIfNumber          INTEGER,
        apIfDescr           DisplayString,
        apIfType            INTEGER,
        apIfMtu             INTEGER,
        apIfSpeed           Gauge,
        apIfPhysAddress     OCTET STRING
    }

apIfNumber OBJECT-TYPE
    SYNTAX INTEGER
    MAX-ACCESS read-write
    STATUS current
    DESCRIPTION
        "The count of the physical interfaces of ap."
    ::= { apPhyInterfaceConfigurationParametersEntry 1 }

apIfDescr OBJECT-TYPE
    SYNTAX DisplayString (SIZE (0..255))
    MAX-ACCESS read-write
    STATUS current
    DESCRIPTION
        "The description of the ap interfaces."
    ::= { apPhyInterfaceConfigurationParametersEntry 2 }

apIfType OBJECT-TYPE
    SYNTAX INTEGER
    MAX-ACCESS read-write
    STATUS current
    DESCRIPTION
        "The style of the ap interfaces."
    ::= { apPhyInterfaceConfigurationParametersEntry 3 }

apIfMtu OBJECT-TYPE
    SYNTAX INTEGER
    MAX-ACCESS read-write
    STATUS current
    DESCRIPTION
        "The max mtu of the ap interfaces."
    ::= { apPhyInterfaceConfigurationParametersEntry 4 }

apIfSpeed OBJECT-TYPE
    SYNTAX Gauge
    MAX-ACCESS read-write
    STATUS current
    DESCRIPTION
        "The speed of the ap interfaces."
    ::= { apPhyInterfaceConfigurationParametersEntry 5 }

apIfPhysAddress OBJECT-TYPE
    SYNTAX OCTET STRING
    MAX-ACCESS read-write
    STATUS current
    DESCRIPTION
        "The physical address of the ap interfaces."
    ::= { apPhyInterfaceConfigurationParametersEntry 6 }

--**************************************************
--* apPhyInterfaceConfigurationParametersTable ends
--**************************************************

--**************************************************
--* radioInterfacePerformanceParameterTable begins
--**************************************************
radioInterfacePerformanceParameterTable OBJECT-TYPE
    SYNTAX SEQUENCE OF RadioInterfacePerformanceParameterEntry
    MAX-ACCESS not-accessible
    STATUS current
    DESCRIPTION
        "The table inluding Radio Interface Performance Parameter
        Of the AP/AC."
    ::= { cmStandardMIBObjects 7 }

radioInterfacePerformanceParameterEntry OBJECT-TYPE
    SYNTAX RadioInterfacePerformanceParameterEntry
    MAX-ACCESS not-accessible
    STATUS current
    DESCRIPTION
        "The entry of radioInterfacePerformanceParameterTable."
    INDEX
    { fsApgWlanId }
    ::= { radioInterfacePerformanceParameterTable 1 }

RadioInterfacePerformanceParameterEntry ::=
    SEQUENCE {
        apUplinkUpdownTimes                 Counter32,
        apDownlinkUpdownTimes               Counter32
    }

apUplinkUpdownTimes OBJECT-TYPE
    SYNTAX Counter32
    MAX-ACCESS read-write
    STATUS current
    DESCRIPTION
        "Updown times of the Wireless uplink port of the AP ."
    ::= { radioInterfacePerformanceParameterEntry 1 }

apDownlinkUpdownTimes OBJECT-TYPE
    SYNTAX Counter32
    MAX-ACCESS read-write
    STATUS current
    DESCRIPTION
        "Updown times of the Wireless downlink port of the AP ."
    ::= { radioInterfacePerformanceParameterEntry 2 }

--**************************************************
--* radioInterfacePerformanceParameterTable ends
--**************************************************

--**************************************************
--* Traps begin here
--**************************************************
cmStandardWAPITrapsObjects  OBJECT IDENTIFIER  ::= { cmStandardmibmodule 4 }
cmStandardWAPITraps         OBJECT IDENTIFIER  ::= { cmStandardmibmodule 0 }

apDown NOTIFICATION-TYPE
    STATUS  current
    DESCRIPTION
            " This trap will be sent when the ap will close down."
    ::= { cmStandardWAPITraps 1 }

apSysStart NOTIFICATION-TYPE
    STATUS  current
    DESCRIPTION
            " This trap will be sent when the ap want to restart itself."
    ::= { cmStandardWAPITraps 2 }

apIPChangeAlarm NOTIFICATION-TYPE
    OBJECTS {
        apOriginalIP,
        apCurrentIP
    }
    STATUS  current
    DESCRIPTION
            " This trap will be sent when the ap want to restart itself."
    ::= { cmStandardWAPITraps 3 }


flashWriteFail NOTIFICATION-TYPE
    STATUS  current
    DESCRIPTION
            " This trap will be sent when the ap fails to write the buffer."
    ::= { cmStandardWAPITraps 4 }

userwithInvalidCerficationInbreakNetwork NOTIFICATION-TYPE
    OBJECTS {
        fsWAPIClientIP,
        fsWAPIClientOtherInfo
    }
    STATUS  current
    DESCRIPTION
            " This trap will be sent when detecting an user accesses the network
            with invlid certification."
    ::= { cmStandardWAPITraps 5 }

stationRepititiveAttack NOTIFICATION-TYPE
    OBJECTS {
        fsWAPIIllegalClientIP,
        fsWAPIIllegalClientOtherInfo
    }
    STATUS  current
    DESCRIPTION
            " This trap will be sent when detecting an illegal client catches the
            packets of the WAPI authentication process of legal client and pretend
            to be legal client to authenticate."
    ::= { cmStandardWAPITraps 6 }

tamperAttack NOTIFICATION-TYPE
    OBJECTS {
        fsWAPIIllegalClientIP,
        fsWAPIIllegalClientOtherInfo
    }
    STATUS  current
    DESCRIPTION
            " This trap will be sent when detecting an illegal client catches the
            packets of the WAPI authentication process of legal client, modifies
            the bytes of the authentication code of the packets and uses the packets
            to pass the WAPI authentication."
    ::= { cmStandardWAPITraps 7 }

lowSafeLevelAttack NOTIFICATION-TYPE
    OBJECTS {
        fsWAPIIllegalClientIP,
        fsWAPIIllegalClientOtherInfo
    }
    STATUS  current
    DESCRIPTION
            " This trap will be sent when detecting an illegal client catches the
            packets of the WAPI authentication process of legal client, modifies
            the bytes of the authentication code of the packets to lower the safe
            level and uses the packets to pass the WAPI authentication."
    ::= { cmStandardWAPITraps 8 }

addressRedirectionAttack NOTIFICATION-TYPE
    OBJECTS {
        fsWAPIIllegalClientIP,
        fsWAPIIllegalClientOtherInfo
    }
    STATUS  current
    DESCRIPTION
            " This trap will be sent when detecting an client passes the authentication
            process, but the destination address of the 802.11 head of the WPI frame."
    ::= { cmStandardWAPITraps 9 }

apOriginalIP OBJECT-TYPE
    SYNTAX      IpAddress
    MAX-ACCESS  read-write
    STATUS      current
    DESCRIPTION
            " The original ipaddress of the ap."
    ::= { cmStandardWAPITrapsObjects 1 }

apCurrentIP OBJECT-TYPE
    SYNTAX      IpAddress
    MAX-ACCESS  read-write
    STATUS      current
    DESCRIPTION
            " The current ipaddress of the ap."
    ::= { cmStandardWAPITrapsObjects 2 }

fsWAPIClientIP OBJECT-TYPE
    SYNTAX      IpAddress
    MAX-ACCESS  read-write
    STATUS      current
    DESCRIPTION
            " The current ipaddress of the client."
    ::= { cmStandardWAPITrapsObjects 3 }

fsWAPIClientOtherInfo OBJECT-TYPE
    SYNTAX      DisplayString
    MAX-ACCESS  read-write
    STATUS      current
    DESCRIPTION
            " Other information of the client."
    ::= { cmStandardWAPITrapsObjects 4 }

fsWAPIIllegalClientIP OBJECT-TYPE
    SYNTAX      IpAddress
    MAX-ACCESS  read-write
    STATUS      current
    DESCRIPTION
            " The ipaddress of the illegal client."
    ::= { cmStandardWAPITrapsObjects 5 }

fsWAPIIllegalClientOtherInfo OBJECT-TYPE
    SYNTAX      DisplayString
    MAX-ACCESS  read-write
    STATUS      current
    DESCRIPTION
            " Other information of the illegal client."
    ::= { cmStandardWAPITrapsObjects 6 }

--**************************************************
--* Traps end here
--**************************************************

-- ********************************************************************
-- * Compliance Statements - RSN
-- ********************************************************************
cmStandardCompliance MODULE-COMPLIANCE
    STATUS current
    DESCRIPTION
          "The compliance statement for CM-MIB."
    MODULE -- this module
    MANDATORY-GROUPS
        {
            cmStandardBase
        }
    -- OPTIONAL-GROUPS {dot11RSNPMKcachingGroup }
::= { cmStandardCompliances 2 }


-- ********************************************************************
-- * Groups - units of conformance - RSN
-- *****************************************************************

cmStandardBase OBJECT-GROUP
    OBJECTS {
        apSysNEId,
        apSysHostName,
        apSysLocation,
        apManufacturer,
        apSysVersion,
        apMacAddressConnectedWithAC,
        apCurrentBSSID,
        apMaxSimultUsers,
        apMaxSimultTraffic,
        apUpTime,
        apIPAddress,
        apIpAdEntNetMask,
        apWorkingMode,
        apBGmode,
        apWAPIAuthMode,
        acWAPIAuthMode,
        acWAPIASIPAddress,
        acWAPICertInstalled,
        cpuHandleAbility,
        memoryCapacity,
        flashmemCapacity,
        support80211g,
        apWAPIMaxUserNum,
        peruserWAPIMaxBindwithAllocated,
        mutiModeAccesssimultStatus,
        gb15629dot11wapiGroupCipherRequested,
        gb15629dot11wapiConfigUnicastCipher,
        gb15629dot11wapiConfigUnicastCipherEnabled,
        gb15629dot11wapiConfigUnicastCipherSize,
        gb15629dot11wapiConfigAuthenticationSuite,
        gb15629dot11wapiConfigAuthenticationSuiteEnabled,
        apSoftwareName,
        apSoftwareVersion,
        apSoftwareVendor,
        acSoftwareName,
        acSoftwareVersion,
        acSoftwareVendor,
        apIfNumber,
        apIfDescr,
        apIfType,
        apIfMtu,
        apIfSpeed,
        apIfPhysAddress,
        apUplinkUpdownTimes,
        apDownlinkUpdownTimes,
        apOriginalIP,
        apCurrentIP,
        fsWAPIClientIP,
        fsWAPIClientOtherInfo,
        fsWAPIIllegalClientIP,
        fsWAPIIllegalClientOtherInfo
    }
    STATUS current
    DESCRIPTION
        "The dot11RSNBase object class provides the necessary support for
        managing RSNA functionality in the STA."
    ::= { cmStandardGroup 1 }

END

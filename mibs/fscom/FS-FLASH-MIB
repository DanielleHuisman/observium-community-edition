-- *****************************************************************
-- FS-FLASH-MIB.mib:  FS Flash MIB file
--
-- October 2009, linshuangfeng
--
-- Copyright (c) 2009 by FS.COM Inc..
-- All rights reserved.
-- 
-- *****************************************************************
--

FS-FLASH-MIB DEFINITIONS ::= BEGIN

IMPORTS
        MODULE-IDENTITY,
        OBJECT-TYPE,
        Unsigned32
                FROM SNMPv2-SMI
        DisplayString
                FROM SNMPv2-TC
        MODULE-COMPLIANCE,
        OBJECT-GROUP
                FROM SNMPv2-CONF
        fsMgmt
                FROM FS-SMI;

fsFlashMIB MODULE-IDENTITY
        LAST-UPDATED "200910090000Z"
        ORGANIZATION "FS.COM Inc.."
        CONTACT-INFO
                " 
                Tel: 400-865-2852 

                E-mail: https://www.fs.com/live_chat_service_mail.html"
        DESCRIPTION
                "This module defines fs system mibs."
        REVISION      "200910090000Z"
        DESCRIPTION
                "Initial version of this MIB module."
        ::= { fsMgmt 47}


fsFlashMIBObjects OBJECT IDENTIFIER ::= { fsFlashMIB 1 }

    
fsFlashDeviceTable OBJECT-TYPE
  SYNTAX      SEQUENCE OF FSFlashDeviceEntry
  MAX-ACCESS  not-accessible
  STATUS      current
  DESCRIPTION
    "A table of flash device entries. Each of the
     objects provides the flash device information."
  ::= { fsFlashMIBObjects 1 }

fsFlashDeviceEntry OBJECT-TYPE
  SYNTAX      FSFlashDeviceEntry
  MAX-ACCESS  not-accessible
  STATUS      current
  DESCRIPTION
    "An entry in the flash device table."
  INDEX { fsFlashDeviceIndex }
  ::= { fsFlashDeviceTable 1 }

FSFlashDeviceEntry ::=
  SEQUENCE {
    fsFlashDeviceIndex  Unsigned32,
    fsFlashDeviceName   DisplayString,
    fsFlashDeviceSize   Unsigned32,
    fsFlashDeviceUsed   Unsigned32,
    fsFlashDeviceFree   Unsigned32
  }
    
fsFlashDeviceIndex OBJECT-TYPE
    SYNTAX        Unsigned32
    MAX-ACCESS    read-only
    STATUS        current
    DESCRIPTION
        "An index that uniquely represents a flash device."
    ::= { fsFlashDeviceEntry 1 }

fsFlashDeviceName OBJECT-TYPE
    SYNTAX        DisplayString
    MAX-ACCESS    read-only
    STATUS        current
    DESCRIPTION
        "A textual name assigned to the flash device."
    ::= { fsFlashDeviceEntry 2 }
    
fsFlashDeviceSize OBJECT-TYPE
    SYNTAX        Unsigned32
    MAX-ACCESS    read-only
    STATUS        current
    DESCRIPTION
        "This is the total size of the flash device."
    ::= { fsFlashDeviceEntry 3 }

fsFlashDeviceUsed OBJECT-TYPE
    SYNTAX        Unsigned32
    MAX-ACCESS    read-only
    STATUS        current
    DESCRIPTION
        "This is the used size of the flash device."
    ::= { fsFlashDeviceEntry 4 }

fsFlashDeviceFree OBJECT-TYPE
    SYNTAX        Unsigned32
    MAX-ACCESS    read-only
    STATUS        current
    DESCRIPTION
        "This is the free size of the flash device."
    ::= { fsFlashDeviceEntry 5 }
        
fsBootromDeviceTable OBJECT-TYPE
  SYNTAX      SEQUENCE OF FSBootromDeviceEntry
  MAX-ACCESS  not-accessible
  STATUS      current
  DESCRIPTION
    "A table of bootrom device entries. Each of the
     objects provides the bootrom device information."
  ::= { fsFlashMIBObjects 2 }

fsBootromDeviceEntry OBJECT-TYPE
  SYNTAX      FSBootromDeviceEntry
  MAX-ACCESS  not-accessible
  STATUS      current
  DESCRIPTION
    "An entry in the bootrom device table."
  INDEX { fsBootromDeviceIndex }
  ::= { fsBootromDeviceTable 1 }

FSBootromDeviceEntry ::=
  SEQUENCE {
    fsBootromDeviceIndex  Unsigned32,
    fsBootromDeviceName   DisplayString,
    fsBootromDeviceSize   Unsigned32
  }
    
fsBootromDeviceIndex OBJECT-TYPE
    SYNTAX        Unsigned32
    MAX-ACCESS    read-only
    STATUS        current
    DESCRIPTION
        "An index that uniquely represents a bootrom device."
    ::= { fsBootromDeviceEntry 1 }

fsBootromDeviceName OBJECT-TYPE
    SYNTAX        DisplayString
    MAX-ACCESS    read-only
    STATUS        current
    DESCRIPTION
        "A textual name assigned to the bootrom device."
    ::= { fsBootromDeviceEntry 2 }  
    
fsBootromDeviceSize OBJECT-TYPE
    SYNTAX        Unsigned32
    MAX-ACCESS    read-only
    STATUS        current
    DESCRIPTION
        "This is the total size of the bootrom device."
    ::= { fsBootromDeviceEntry 3 }
    
fsFlashMIBConformance OBJECT IDENTIFIER ::= { fsFlashMIB 2 }
fsFlashMIBCompliances OBJECT IDENTIFIER ::= { fsFlashMIBConformance 1 }
fsFlashMIBGroups      OBJECT IDENTIFIER ::= { fsFlashMIBConformance 2 }


-- compliance statements

fsFlashMIBCompliance MODULE-COMPLIANCE
        STATUS  current
        DESCRIPTION
                "The compliance statement for entities which implement
                the FS Flash MIB"
        MODULE  -- this module
                MANDATORY-GROUPS { fsFlashMIBGroup
                 }
        ::= { fsFlashMIBCompliances 1 }
                
-- units of conformance

fsFlashMIBGroup OBJECT-GROUP
        OBJECTS {
          fsFlashDeviceIndex,
          fsFlashDeviceName,
          fsFlashDeviceSize,
          fsFlashDeviceUsed,
          fsFlashDeviceFree
        }
        STATUS  current
        DESCRIPTION
                "A collection of objects providing flash information to a FS agent."
        ::= { fsFlashMIBGroups 1 } 
  
fsBootromDeviceMIBGroup OBJECT-GROUP
        OBJECTS {
          fsBootromDeviceIndex,
          fsBootromDeviceName,
          fsBootromDeviceSize
        }
        STATUS  current
        DESCRIPTION
                "A collection of objects providing bootrom device information to a FS agent."
        ::= { fsFlashMIBGroups 2 } 
  
END

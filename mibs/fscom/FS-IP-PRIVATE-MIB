-- *******************************************************************
-- FS-IP-PRIVATE-MIB.mib : FS AC IP MIB file
-- May 2010, humin
--
-- Copyright (c) 2009 by FS.COM Inc..
-- All rights reserved.
-- *******************************************************************
--
FS-IP-PRIVATE-MIB DEFINITIONS ::= BEGIN

IMPORTS
        IpAddress,
        OBJECT-TYPE,
        MODULE-IDENTITY,
        NOTIFICATION-TYPE,
        Counter32
                FROM SNMPv2-SMI
        MacAddress,
        DisplayString,
        RowStatus
                FROM SNMPv2-TC
        MODULE-COMPLIANCE,
        NOTIFICATION-GROUP,
        OBJECT-GROUP
                FROM SNMPv2-CONF
        fsMgmt
                FROM FS-SMI; 
                
fsIPPrivateMgmt MODULE-IDENTITY
    LAST-UPDATED "200909180000Z"
    ORGANIZATION "FS.COM Inc.."
    CONTACT-INFO
        " 
    Tel: 400-865-2852

    E-mail: https://www.fs.com/live_chat_service_mail.html"
    DESCRIPTION
        "This module defines ac management mibs."
    REVISION      "200909180000Z"
    DESCRIPTION
        "Initial version of this MIB module."
    ::= { fsMgmt 73}

-- ******** define the notify nodes *************
fsIPPrivateAcNotificationsMIBObjects OBJECT IDENTIFIER ::= { fsIPPrivateMgmt 1 }
fsIPPrivateAcNtfObjects              OBJECT IDENTIFIER ::= { fsIPPrivateAcNotificationsMIBObjects 1 }
fsIPPrivateAcNotifications           OBJECT IDENTIFIER ::= { fsIPPrivateAcNotificationsMIBObjects 2 }

-- ****************************************
--
--               Notify nodes
--
-- ****************************************
fsIPPrivateAcNotifyIpv4AddressChangeType OBJECT-TYPE
    SYNTAX      INTEGER
    MAX-ACCESS  accessible-for-notify
    STATUS      current
    DESCRIPTION
        "Represents the AC Ipv4 address change operation, 0-del,1-add."
    ::= { fsIPPrivateAcNtfObjects 1 }

fsIPPrivateAcNotifyIpv4ChangeAddress OBJECT-TYPE
    SYNTAX      IpAddress
    MAX-ACCESS  accessible-for-notify
    STATUS      current
    DESCRIPTION
        "Represents the AC Ipv4 address which is changing."
    ::= { fsIPPrivateAcNtfObjects 2 }

fsIPPrivateAcNotifyIpv4ChangeAddressMask OBJECT-TYPE
    SYNTAX      IpAddress
    MAX-ACCESS  accessible-for-notify
    STATUS      current
    DESCRIPTION
        "Represents the AC Ipv4 address's mask which is changing."
    ::= { fsIPPrivateAcNtfObjects 3 }

fsIPPrivateAcNotifyIpv4ChangeIfIndex OBJECT-TYPE
    SYNTAX      INTEGER
    MAX-ACCESS  accessible-for-notify
    STATUS      current
    DESCRIPTION
        "Represents the AC Ipv4 address change on which interface."
    ::= { fsIPPrivateAcNtfObjects 4 }

fsIPPrivateAcNotifyChangeIpv4AddressAlarm NOTIFICATION-TYPE
    OBJECTS     {
                  fsIPPrivateAcNotifyIpv4AddressChangeType,
                  fsIPPrivateAcNotifyIpv4ChangeAddress,
                  fsIPPrivateAcNotifyIpv4ChangeAddressMask,
                  fsIPPrivateAcNotifyIpv4ChangeIfIndex
                }
    STATUS      current
    DESCRIPTION
        "This notification is sent by the AC when an AC's Ipv4 address is changed."
    ::= { fsIPPrivateAcNotifications 1 }

--********************************************************************
--                                                                  **
--                ac query ap's ip information	                    **
--                                                                  **
--********************************************************************    
fsIPPrivateAcQueryApMIBObject OBJECT IDENTIFIER ::= { fsIPPrivateAcNotificationsMIBObjects 3 }
fsIPPrivateAcQueryApInfo      OBJECT IDENTIFIER ::= { fsIPPrivateAcQueryApMIBObject 1}

--********************************************************************
--                                                                  **
--            table about ac query ap's ip information              **
--                                                                  **
--******************************************************************** 
fsIPPrivateAcQueryApMIBTable OBJECT-TYPE
    SYNTAX  SEQUENCE OF FSIPPrivateApInfoEntry
    MAX-ACCESS  not-accessible
    STATUS  current
    DESCRIPTION
            "The Ap IP information."
    ::= { fsIPPrivateAcQueryApInfo 1 }

fsIPPrivateApInfoEntry OBJECT-TYPE
    SYNTAX  FSIPPrivateApInfoEntry
    MAX-ACCESS  not-accessible
    STATUS  current
    DESCRIPTION
        "Get the Ap IP information."
    INDEX   { fsIPPrivateAcApMacAddr,
              fsIPPrivateAcApIp}
    ::= { fsIPPrivateAcQueryApMIBTable 1 }

FSIPPrivateApInfoEntry ::=
    SEQUENCE {
        fsIPPrivateAcApMacAddr                 MacAddress,
        fsIPPrivateAcApIp                      IpAddress,
        fsIPPrivateAcApMask                    IpAddress,
        fsIPPrivateAcApGateway                 IpAddress						
    }

fsIPPrivateAcApMacAddr OBJECT-TYPE
    SYNTAX  MacAddress
    MAX-ACCESS  read-only
    STATUS  current
    DESCRIPTION
            "The AP's ethernet mac address."
    ::= { fsIPPrivateApInfoEntry 1}
    
fsIPPrivateAcApIp OBJECT-TYPE
    SYNTAX  IpAddress
    MAX-ACCESS  read-only
    STATUS  current
    DESCRIPTION
        "The AP's IP address."
    ::= { fsIPPrivateApInfoEntry 2}
		
fsIPPrivateAcApMask OBJECT-TYPE
    SYNTAX  IpAddress	   
    MAX-ACCESS  read-only
    STATUS  current
    DESCRIPTION
    	"The AP's MASK address."
    ::= { fsIPPrivateApInfoEntry 3}				
    
fsIPPrivateAcApGateway OBJECT-TYPE
    SYNTAX  IpAddress	   
    MAX-ACCESS  read-only
    STATUS  current
    DESCRIPTION
    	"The AP's Gateway address."
    ::= { fsIPPrivateApInfoEntry 4}


--********************************************************************
--                                                                  **
--           conformance information                                **
--                                                                  **
--********************************************************************
fsIPPrivateMIBConformance OBJECT IDENTIFIER ::= { fsIPPrivateMgmt 2 }
fsIPPrivateMIBCompliances OBJECT IDENTIFIER ::= { fsIPPrivateMIBConformance 1 }
fsIPPrivateMIBGroups      OBJECT IDENTIFIER ::= { fsIPPrivateMIBConformance 2 }


--********************************************************************
--                                                                  **
--           compliance statements                                  **
--                                                                  **
--********************************************************************
-- fsIPPrivateMIBCompliance MODULE-COMPLIANCE
--        STATUS  current
--        DESCRIPTION
--                "The compliance statement for entities which implement
--                the FS Ac Manager Ac"
--        MODULE
--                MANDATORY-GROUPS { fsAcIPPrivateMIBGroup, fsAcIPPrivateTrapGroup }
--        ::= { fsIPPrivateMIBCompliances 1 }
        

--********************************************************************
--                                                                  **
--           units of conformance                                   **
--                                                                  **
--********************************************************************
fsIPPrivateMIBGroup OBJECT-GROUP
        OBJECTS {
            fsIPPrivateAcNotifyIpv4AddressChangeType,
            fsIPPrivateAcNotifyIpv4ChangeAddress,
            fsIPPrivateAcNotifyIpv4ChangeAddressMask,
            fsIPPrivateAcNotifyIpv4ChangeIfIndex,
            fsIPPrivateAcApMacAddr,
            fsIPPrivateAcApIp,
            fsIPPrivateAcApMask,
            fsIPPrivateAcApGateway 
        }
        STATUS  current
        DESCRIPTION
                "A collection of objects providing ac manager (echo) ability to a
                FS agent."
        ::= { fsIPPrivateMIBGroups 1 }

fsIPPrivateTrapGroup NOTIFICATION-GROUP
    NOTIFICATIONS {
        fsIPPrivateAcNotifyChangeIpv4AddressAlarm
    }
    STATUS  current
    DESCRIPTION
        "A collection of traps providing ac manager (echo) ability to a
         FS agent."
    ::= { fsIPPrivateMIBGroups 2 }
    
END

-- *****************************************************************
-- FS-LICENSE-MIB.mib:  FS License MIB
--
-- Oct 2009, jiangxh
--
-- Copyright (c) 2009 by FS.COM Inc..
-- All rights reserved.
-- *****************************************************************
--

FS-LICENSE-MIB DEFINITIONS ::= BEGIN

IMPORTS
        MODULE-IDENTITY,
        OBJECT-TYPE,
        Integer32
                FROM SNMPv2-SMI
        DisplayString
                FROM SNMPv2-TC
        MODULE-COMPLIANCE,
        OBJECT-GROUP
                FROM SNMPv2-CONF
        fsMgmt
                FROM FS-SMI;

fsLicenseMIB MODULE-IDENTITY
        LAST-UPDATED "200909180000Z"
        ORGANIZATION "FS.COM Inc.."
        CONTACT-INFO
            " 
        Tel: 400-865-2852

        E-mail: https://www.fs.com/live_chat_service_mail.html"
        DESCRIPTION
                "This module defines fs license mibs."
        REVISION      "200909180000Z"
        DESCRIPTION
                "Initial version of this MIB module."
        ::= { fsMgmt 57}

fsLicenseMIBObjects OBJECT IDENTIFIER ::= { fsLicenseMIB 1 }

fsShowLicense OBJECT-TYPE
    SYNTAX      Integer32
    MAX-ACCESS  read-only
    STATUS      current
    DESCRIPTION
            "This object represents the support of AP nums."
    ::= { fsLicenseMIBObjects 1 }    
    
fsLicenseTable OBJECT-TYPE
  SYNTAX      SEQUENCE OF FSLicenseEntry
  MAX-ACCESS  not-accessible
  STATUS      current
  DESCRIPTION
    "A table of license entries. Each of the
     objects indicate the license configured."
  ::= { fsLicenseMIBObjects 2 }

fsLicenseEntry OBJECT-TYPE
  SYNTAX      FSLicenseEntry
  MAX-ACCESS  not-accessible
  STATUS      current
  DESCRIPTION
    "An entry in the license table."
  INDEX { fsLicenseIndex }
  ::= { fsLicenseTable 1 }

FSLicenseEntry ::=
  SEQUENCE {
    fsLicenseIndex  	Integer32,
    fsLicenseString   DisplayString,
    fsLicenseValue   	Integer32
  }
    
fsLicenseIndex OBJECT-TYPE
    SYNTAX        Integer32
    MAX-ACCESS    not-accessible
    STATUS        current
    DESCRIPTION
        "An index that uniquely represents a license."
    ::= { fsLicenseEntry 1 }
    
fsLicenseString OBJECT-TYPE
    SYNTAX        DisplayString
    MAX-ACCESS    read-write
    STATUS        current
    DESCRIPTION
        "The license configured."
    ::= { fsLicenseEntry 2 } 
   
fsLicenseValue OBJECT-TYPE
    SYNTAX        Integer32
    MAX-ACCESS    read-only
    STATUS        current
    DESCRIPTION
        "This is the support numbers of APs for the license."
    ::= { fsLicenseEntry 3 }

fsLicenseMIBConformance OBJECT IDENTIFIER ::= { fsLicenseMIB 2 }
fsLicenseMIBCompliances OBJECT IDENTIFIER ::= { fsLicenseMIBConformance 1 }
fsLicenseMIBGroups      OBJECT IDENTIFIER ::= { fsLicenseMIBConformance 2 }


-- compliance statements

fsLicenseMIBCompliance MODULE-COMPLIANCE
        STATUS  current
        DESCRIPTION
                "The compliance statement for entities which implement
                the FS License MIB"
        MODULE  -- this module
                MANDATORY-GROUPS { fsLicenseMIBGroup
                }
        ::= { fsLicenseMIBCompliances 1 }
                
-- units of conformance

fsLicenseMIBGroup OBJECT-GROUP
        OBJECTS {
               fsShowLicense, 
               fsLicenseString,
               fsLicenseValue 
        }
        STATUS  current
        DESCRIPTION
                "A collection of objects providing license information and
                opertion to a FS agent."
        ::= { fsLicenseMIBGroups 1 } 

END

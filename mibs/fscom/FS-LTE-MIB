-- *******************************************************************
-- FS-LTE-MIB.mib : FS MIB
-- February 2016, zhengrongying	
--
-- Copyright (c) 2010 by FS.COM Inc..
-- All rights reserved.
-- *******************************************************************
FS-LTE-MIB DEFINITIONS ::= BEGIN
        IMPORTS
        MODULE-IDENTITY,
        OBJECT-TYPE,
        Integer32,
        Counter32,
        Counter64,
        IpAddress,
        Unsigned32
            FROM SNMPv2-SMI
        TruthValue,
        DisplayString,
        MacAddress,
        RowStatus
            FROM SNMPv2-TC
        Gauge
            FROM RFC1155-SMI
        MODULE-COMPLIANCE,
        NOTIFICATION-GROUP,
        OBJECT-GROUP
            FROM SNMPv2-CONF   
        ifIndex
            FROM RFC1213-MIB
        TimeTicks
            FROM SNMPv2-SMI    
        fsMgmt
            FROM FS-SMI;

--*******************************************
--* module definition
--*******************************************
fsLteMIB MODULE-IDENTITY
    LAST-UPDATED    "201002260000Z"
    ORGANIZATION
        "FS.COM Inc.."
    CONTACT-INFO
        "Tel: 400-865-2852
           E-mail: https://www.fs.com/live_chat_service_mail.html "

    DESCRIPTION
       "
       Wlan software private MIB for FS SNC according to the China
       Mobile standard. This is device manage MIB.
       "
    REVISION      "201002280000Z"
    DESCRIPTION
       "Initial version of this MIB module."

    ::= { fsMgmt  148 }

--*******************************************
--* module definition end
--*******************************************                                   
lteEnbSystemInfoConfigObjects OBJECT IDENTIFIER  ::= { fsLteMIB 1 }
--************************************************** lteEnbSystemInfoConfigObjects
--* lteEnbGeneralInfoConfigTable begins * 
--**************************************************
lteEnbGeneralInfoConfigTable  OBJECT-TYPE
    SYNTAX SEQUENCE OF LteEnbGeneralInfoConfigEntry
    MAX-ACCESS not-accessible
    STATUS current
    DESCRIPTION
      "The general information configure table."
    ::={ lteEnbSystemInfoConfigObjects 1 }   

lteEnbGeneralInfoConfigEntry OBJECT-TYPE
    SYNTAX  LteEnbGeneralInfoConfigEntry   
    MAX-ACCESS  not-accessible
    STATUS  current
    DESCRIPTION
        "The general information configure table."
    INDEX   { lteEnbMacAddr }
    ::= { lteEnbGeneralInfoConfigTable 1 }

LteEnbGeneralInfoConfigEntry ::=
    SEQUENCE {
        lteEnbMacAddr					MacAddress,		
        lteEnbName						DisplayString, 
        lteEnbDLBandWidth				INTEGER,     
        lteEnbMCC						INTEGER,
        lteEnbMNC						INTEGER,  
        lteEnbTac						INTEGER,
        lteEnbFrameType				INTEGER,
		lteEnbTddConfig				INTEGER,    
		lteEnbTddConfigS				INTEGER,
		lteEnbPrefixType				INTEGER,
		lteEnbFreqBandIndicator		INTEGER,
		lteEnbDownlinkFrequency		INTEGER,
		lteEnbUplinkFrequencyOffset	INTEGER,
		lteEnbTxmode					INTEGER,
		lteEnbNidCell					INTEGER,
		lteEnbRsPower					INTEGER,   
		lteEnbReset					INTEGER,    
		lteEnbTxpower               INTEGER,
		lteEnbqRxLvlmin             INTEGER,
		lteEnbPdschRsPower			INTEGER,    
		lteEnbPuschP0Nominal        INTEGER,  
		lteEnbPuschAlpha			INTEGER,     
		lteEnbPucchP0Nominal		INTEGER,  		
		lteEnbDtchTimer             INTEGER,
		lteEnbLB                    INTEGER,
		lteEnbICIC                  INTEGER,
		lteEnbEdgeRbStart           INTEGER,
		lteEnbEdgeRbEnd             INTEGER,
		lteEnbEdgeRsrpThold     INTEGER,
		lteEnbEdgeDifThold      INTEGER,
		lteEnbMeas               INTEGER,
		lteEnbMeasGap            INTEGER,
		lteEnbMeasCarrfreq1    INTEGER, 
		lteEnbMeasCarrfreq2    INTEGER, 
		lteEnbMeasA1Thold      INTEGER,
		lteEnbMeasA2Thold      INTEGER,
		lteEnbMeasA3Offset     INTEGER,
		lteEnbMeasA3Hys        INTEGER,
		lteEnbMeasA3TimeTrig   INTEGER,
		lteEnbMeasA3RpIntval   INTEGER,
		lteEnbID               INTEGER
}
    
lteEnbMacAddr OBJECT-TYPE
    SYNTAX MacAddress 
    MAX-ACCESS read-only
    STATUS current
    DESCRIPTION
        "The mac address of enb."
    ::= { lteEnbGeneralInfoConfigEntry 1 }    

lteEnbName OBJECT-TYPE
    SYNTAX DisplayString
    MAX-ACCESS read-write
    STATUS current
    DESCRIPTION
        "The name of enb."
    ::= { lteEnbGeneralInfoConfigEntry 2 }

lteEnbDLBandWidth  OBJECT-TYPE
    SYNTAX INTEGER  {
    	bandwidth-5M(25),
    	bandwidth-10M(50),
    	bandwidth-15M(75),
    	bandwidth-20M(100)
    }
    MAX-ACCESS read-write
    STATUS current
    DESCRIPTION
        "The dl bandwidth of enb. "
    ::= { lteEnbGeneralInfoConfigEntry 3 }   
    
lteEnbMCC  OBJECT-TYPE
    SYNTAX INTEGER  (0..999)
    MAX-ACCESS read-write
    STATUS current
    DESCRIPTION
        "The Mobile Country Code of enb."
    ::= { lteEnbGeneralInfoConfigEntry 4 }    
    
lteEnbMNC  OBJECT-TYPE
    SYNTAX INTEGER  (0..999)
    MAX-ACCESS read-write
    STATUS current
    DESCRIPTION
        "The Mobile Network Code of enb."
    ::= { lteEnbGeneralInfoConfigEntry 5 }

lteEnbTac  OBJECT-TYPE
    SYNTAX INTEGER 
    MAX-ACCESS read-write
    STATUS current
    DESCRIPTION
        "The Tracking Area Code of enb."
    ::= { lteEnbGeneralInfoConfigEntry 6 }
lteEnbFrameType  OBJECT-TYPE
    SYNTAX INTEGER {
    	fdd(0),
    	tdd(1)
    }
    MAX-ACCESS read-write
    STATUS current
    DESCRIPTION
        "The Frame type of enb: fdd or tdd."
    ::= { lteEnbGeneralInfoConfigEntry 7 }  
    
lteEnbTddConfig   OBJECT-TYPE
    SYNTAX INTEGER  (0..2)
    MAX-ACCESS read-write
    STATUS current
    DESCRIPTION
        "The tdd config in enb.only valid in frame type is tdd."
    ::= { lteEnbGeneralInfoConfigEntry 8 }  
    
lteEnbTddConfigS   OBJECT-TYPE
    SYNTAX INTEGER   (1..10)
    MAX-ACCESS read-write
    STATUS current
    DESCRIPTION
        "Tdd config Specil subframe num.only valid in frame type is tdd <0 - 10>."
    ::= { lteEnbGeneralInfoConfigEntry 9 }   
    
lteEnbPrefixType   OBJECT-TYPE
    SYNTAX INTEGER 
    MAX-ACCESS read-write
    STATUS current
    DESCRIPTION
        "Tdd enb prefix type."
    ::= { lteEnbGeneralInfoConfigEntry 10 }
    
lteEnbFreqBandIndicator   OBJECT-TYPE
    SYNTAX INTEGER 
    MAX-ACCESS read-write
    STATUS current
    DESCRIPTION
        "The enb current Freq band Indicator."
    ::= { lteEnbGeneralInfoConfigEntry 11 }    
        
lteEnbDownlinkFrequency    OBJECT-TYPE
    SYNTAX INTEGER 
    MAX-ACCESS read-write
    STATUS current
    DESCRIPTION
        "The enb downlink freqency."
    ::= { lteEnbGeneralInfoConfigEntry 12 }    

lteEnbUplinkFrequencyOffset    OBJECT-TYPE
    SYNTAX INTEGER 
    MAX-ACCESS read-write
    STATUS current
    DESCRIPTION
        "The enb uplink freqency offset"
    ::= { lteEnbGeneralInfoConfigEntry 13 }
              
lteEnbTxmode    OBJECT-TYPE
    SYNTAX INTEGER (2..4)
    MAX-ACCESS read-write
    STATUS current
    DESCRIPTION
        "The enb tx mode"
    ::= { lteEnbGeneralInfoConfigEntry 14 } 
    
lteEnbNidCell    OBJECT-TYPE
    SYNTAX INTEGER 
    MAX-ACCESS read-write
    STATUS current
    DESCRIPTION
        "The enb cell id"
    ::= { lteEnbGeneralInfoConfigEntry 15 }   
lteEnbRsPower   OBJECT-TYPE
    SYNTAX INTEGER 
    MAX-ACCESS read-write
    STATUS current
    DESCRIPTION
        "The enb Reference power"
    ::= { lteEnbGeneralInfoConfigEntry 16 }

lteEnbReset   OBJECT-TYPE
    SYNTAX INTEGER 
    MAX-ACCESS read-write
    STATUS current
    DESCRIPTION
        "The enb Reset flag"
    ::= { lteEnbGeneralInfoConfigEntry 17 } 

lteEnbTxpower   OBJECT-TYPE
    SYNTAX INTEGER 
    MAX-ACCESS read-write
    STATUS current
    DESCRIPTION
        "The enb TX Power"
    ::= { lteEnbGeneralInfoConfigEntry 18 } 
lteEnbqRxLvlmin   OBJECT-TYPE
    SYNTAX INTEGER 
    MAX-ACCESS read-write
    STATUS current
    DESCRIPTION
        "The ue min rx level "
    ::= { lteEnbGeneralInfoConfigEntry 19 } 
lteEnbPdschRsPower   OBJECT-TYPE
    SYNTAX INTEGER 
    MAX-ACCESS read-write
    STATUS current
    DESCRIPTION
        "The enb pdsch reference power"
    ::= { lteEnbGeneralInfoConfigEntry 20 }         
lteEnbPuschP0Nominal        OBJECT-TYPE
    SYNTAX INTEGER 
    MAX-ACCESS read-write
    STATUS current
    DESCRIPTION
        "The enb pusch P0 nominal"
    ::= { lteEnbGeneralInfoConfigEntry 21 } 
  
lteEnbPuschAlpha			OBJECT-TYPE
    SYNTAX INTEGER 
    MAX-ACCESS read-write
    STATUS current
    DESCRIPTION
        "The enb pusch alpha"
    ::= { lteEnbGeneralInfoConfigEntry 22 } 
     
lteEnbPucchP0Nominal		OBJECT-TYPE
    SYNTAX INTEGER 
    MAX-ACCESS read-write
    STATUS current
    DESCRIPTION
        "The enb pucch nominal"
    ::= { lteEnbGeneralInfoConfigEntry 23 } 

lteEnbDtchTimer             OBJECT-TYPE
    SYNTAX INTEGER 
    MAX-ACCESS read-write
    STATUS current
    DESCRIPTION
        "The enb Dtch timer val"
    ::= { lteEnbGeneralInfoConfigEntry 24 } 

lteEnbLB                    OBJECT-TYPE
    SYNTAX INTEGER  {
    	enable(1),
    	disable(0)
    }
    MAX-ACCESS read-write
    STATUS current
    DESCRIPTION
        "The enb load balance config"
    ::= { lteEnbGeneralInfoConfigEntry 25 } 

lteEnbICIC                  OBJECT-TYPE
    SYNTAX INTEGER   {
    	enable(1),
    	disable(0)
    }
    MAX-ACCESS read-write
    STATUS current
    DESCRIPTION
        "The enb ICIC config"
    ::= { lteEnbGeneralInfoConfigEntry 26 } 

lteEnbEdgeRbStart           OBJECT-TYPE
    SYNTAX INTEGER 
    MAX-ACCESS read-write
    STATUS current
    DESCRIPTION
        "The enodeb Edge RB start"
    ::= { lteEnbGeneralInfoConfigEntry 27 } 

lteEnbEdgeRbEnd             OBJECT-TYPE
    SYNTAX INTEGER 
    MAX-ACCESS read-write
    STATUS current
    DESCRIPTION
        "The enodeb Edge RB end"
    ::= { lteEnbGeneralInfoConfigEntry 28 } 

lteEnbEdgeRsrpThold     OBJECT-TYPE
    SYNTAX INTEGER 
    MAX-ACCESS read-write
    STATUS current
    DESCRIPTION
        "The enb Edge rsrp threshold"
    ::= { lteEnbGeneralInfoConfigEntry 29 } 

lteEnbEdgeDifThold      OBJECT-TYPE
    SYNTAX INTEGER 
    MAX-ACCESS read-write
    STATUS current
    DESCRIPTION
        "The enb edge diff threshold"
    ::= { lteEnbGeneralInfoConfigEntry 30 } 

lteEnbMeas               OBJECT-TYPE
    SYNTAX INTEGER    {
    	enable(1),
    	disable(0)
    }
    MAX-ACCESS read-write
    STATUS current
    DESCRIPTION
        "The enb measure"
    ::= { lteEnbGeneralInfoConfigEntry 31 } 

lteEnbMeasGap            OBJECT-TYPE
    SYNTAX INTEGER   {
    	enable(1),
    	disable(0)
    }
    MAX-ACCESS read-write
    STATUS current
    DESCRIPTION
        "The enb measure gap config"
    ::= { lteEnbGeneralInfoConfigEntry 32 } 

lteEnbMeasCarrfreq1    OBJECT-TYPE
    SYNTAX INTEGER 
    MAX-ACCESS read-write
    STATUS current
    DESCRIPTION
        "The enb measure carrier frequence 1"
    ::= { lteEnbGeneralInfoConfigEntry 33 } 
 
lteEnbMeasCarrfreq2    OBJECT-TYPE
    SYNTAX INTEGER 
    MAX-ACCESS read-write
    STATUS current
    DESCRIPTION
        "The enb measure carrier frequence 2"
    ::= { lteEnbGeneralInfoConfigEntry 34 } 
 
lteEnbMeasA1Thold      OBJECT-TYPE
    SYNTAX INTEGER 
    MAX-ACCESS read-write
    STATUS current
    DESCRIPTION
        "The eNodeB measure event A1 threshold"
    ::= { lteEnbGeneralInfoConfigEntry 35 } 

lteEnbMeasA2Thold      OBJECT-TYPE
    SYNTAX INTEGER 
    MAX-ACCESS read-write
    STATUS current
    DESCRIPTION
        "The eNodeB measure event A2 threshold "
    ::= { lteEnbGeneralInfoConfigEntry 36 } 

lteEnbMeasA3Offset     OBJECT-TYPE
    SYNTAX INTEGER 
    MAX-ACCESS read-write
    STATUS current
    DESCRIPTION
        "The eNodeB measure event A3 Offset"
    ::= { lteEnbGeneralInfoConfigEntry 37 } 
lteEnbMeasA3Hys        OBJECT-TYPE
    SYNTAX INTEGER 
    MAX-ACCESS read-write
    STATUS current
    DESCRIPTION
        "The eNodeB measure event A3 hysteresis"
    ::= { lteEnbGeneralInfoConfigEntry 38 } 

lteEnbMeasA3TimeTrig   OBJECT-TYPE
    SYNTAX  INTEGER {    
    	ms0(0), 
    	ms40(1), 
    	ms64(2), 
    	ms80(3), 
    	ms100(4), 
    	ms128(5), 
    	ms160(6), 
    	ms256(7),
    	ms320(8), 
    	ms480(9), 
    	ms512(10),
    	ms640(11),
        ms1024(12),
        ms1280(13),
        ms2560(14), 
        ms5120(15)
    }
    MAX-ACCESS read-write
    STATUS current
    DESCRIPTION
        "The eNodeB measure event A3 timer trigger"
    ::= { lteEnbGeneralInfoConfigEntry 39 } 

lteEnbMeasA3RpIntval   OBJECT-TYPE
	SYNTAX  INTEGER {    
    	 ms120(0), 
    	 ms240(1), 
    	 ms480(2), 
    	 ms640(3), 
		 ms1024(4), 
		 ms2048(5), 
		 ms5120(6), 
		 ms10240(7), 
		 min1(8), 
		 min6(9), 
		 min12(10),
		 min30(11), 
		 min60(12),
         spare3(13), 
		 spare2(14), 
		 spare1(15)    
	}
    MAX-ACCESS read-write
    STATUS current
    DESCRIPTION
        "The eNodeB measure event A3 report intval"
    ::= { lteEnbGeneralInfoConfigEntry 40 }      
    
lteEnbID   OBJECT-TYPE
    SYNTAX INTEGER 
    MAX-ACCESS read-write
    STATUS current
    DESCRIPTION
        "The eNodeB id"
    ::= { lteEnbGeneralInfoConfigEntry 41 }

--**************************************************
--* lteEnbGeneralInfoConfigTable ends * 
--*************************************************       
--*********************************************************************************  
--lteUEInfoGetObjects begins
--*********************************************************************************
 
lteUEInfoGetObjects        OBJECT IDENTIFIER  ::= { fsLteMIB 2 }
lteUEInfoGetTable  OBJECT-TYPE
    SYNTAX SEQUENCE OF LteUEInfoGetEntry
    MAX-ACCESS not-accessible
    STATUS current
    DESCRIPTION
      "The UE info in ac."
    ::={ lteUEInfoGetObjects 1 }

lteUEInfoGetEntry OBJECT-TYPE
    SYNTAX  LteUEInfoGetEntry
    MAX-ACCESS  not-accessible
    STATUS  current
    DESCRIPTION
        "The UE info in ac"
    INDEX   { lteUEImsi }
    ::= { lteUEInfoGetTable 1 }
    
LteUEInfoGetEntry ::=
    SEQUENCE {      
    	lteUEImsi					   	DisplayString, 
        lteUEIpaddr                    	IpAddress,
       	lteUEGuti                      	DisplayString,
       	lteUEUptime						TimeTicks,
       	lteUERxpkt						Counter64,
     	lteUETxpkt						Counter64,
     	lteUECellId						INTEGER,
     	lteUEIsAttached					INTEGER,
     	lteUECapbility                  INTEGER,
     	lteUEAssoEnbMac                 MacAddress,
     	lteUERrcState                   INTEGER,    	
       	lteUERxbytes				    Counter64,
     	lteUETxbytes					Counter64 	
    }  

lteUEImsi  OBJECT-TYPE
    SYNTAX  DisplayString
    MAX-ACCESS  read-only
    STATUS  current
    DESCRIPTION
            "ue imsi."
    ::= { lteUEInfoGetEntry 1}    

lteUEIpaddr  OBJECT-TYPE
    SYNTAX  IpAddress
    MAX-ACCESS  read-write
    STATUS  current
    DESCRIPTION
            "ue ip addr."
    ::= { lteUEInfoGetEntry 2}
            
lteUEGuti  OBJECT-TYPE
    SYNTAX  DisplayString
    MAX-ACCESS  read-only
    STATUS  current
    DESCRIPTION
            "ue guti."
    ::= { lteUEInfoGetEntry 3}
       
lteUEUptime  OBJECT-TYPE
    SYNTAX  TimeTicks
    MAX-ACCESS  read-only
    STATUS  current
    DESCRIPTION
            "ue attach to nas time."
    ::= { lteUEInfoGetEntry 4}
        
lteUERxpkt  OBJECT-TYPE
    SYNTAX  Counter64
    MAX-ACCESS  read-only
    STATUS  current
    DESCRIPTION
            "ue receive packages number."
    ::= { lteUEInfoGetEntry 5}    

lteUETxpkt  OBJECT-TYPE
    SYNTAX  Counter64
    MAX-ACCESS  read-only
    STATUS  current
    DESCRIPTION
            "ue transmit packages number."
    ::= { lteUEInfoGetEntry 6}
lteUECellId  OBJECT-TYPE
    SYNTAX  INTEGER
    MAX-ACCESS  read-only
    STATUS  current
    DESCRIPTION
            "ue associate cell id."
    ::= { lteUEInfoGetEntry 7}
lteUEIsAttached  OBJECT-TYPE
    SYNTAX  INTEGER
    MAX-ACCESS  read-only
    STATUS  current
    DESCRIPTION
            "ue is attached to nas."
    ::= { lteUEInfoGetEntry 8}
lteUECapbility  OBJECT-TYPE
    SYNTAX  INTEGER
    MAX-ACCESS  read-only
    STATUS  current
    DESCRIPTION
            "ue capbility."
    ::= { lteUEInfoGetEntry 9}
                                                   
lteUEAssoEnbMac  OBJECT-TYPE
    SYNTAX  MacAddress
    MAX-ACCESS  read-only
    STATUS  current
    DESCRIPTION
            "ue associate enb mac address."
    ::= { lteUEInfoGetEntry 10}
lteUERrcState  OBJECT-TYPE
     SYNTAX  INTEGER {
         connected(1),
         dis-connected(0)
    }    MAX-ACCESS  read-only
    STATUS  current
    DESCRIPTION
            "ue rrc state."
    ::= { lteUEInfoGetEntry 11}    
 
lteUERxbytes  OBJECT-TYPE
    SYNTAX  Counter64
    MAX-ACCESS  read-only
    STATUS  current
    DESCRIPTION
            "ue receive packages bytes."
    ::= { lteUEInfoGetEntry 12}    

lteUETxbytes  OBJECT-TYPE
    SYNTAX  Counter64
    MAX-ACCESS  read-only
    STATUS  current
    DESCRIPTION
            "ue transmit packages bytes."
    ::= { lteUEInfoGetEntry 13}

          
--**************************************************
--* lteUEInfoGetObjects ends * 
--**************************************************      

lteEnbInfoGetObjects OBJECT IDENTIFIER  ::= { fsLteMIB 3 }
--*********************************************************************************  
--lteEnbInfoGetObjects begins
--********************************************************************************* 
lteEnbInfoGetTable  OBJECT-TYPE
    SYNTAX SEQUENCE OF LteEnbInfoGetEntry
    MAX-ACCESS not-accessible
    STATUS current
    DESCRIPTION
      "The general information configure table."
    ::={ lteEnbInfoGetObjects 1 }   

lteEnbInfoGetEntry OBJECT-TYPE
    SYNTAX  LteEnbInfoGetEntry   
    MAX-ACCESS  not-accessible
    STATUS  current
    DESCRIPTION
        "The general information configure table."
    INDEX   { lteEnbMacAddr }
    ::= { lteEnbInfoGetTable 1 }

LteEnbInfoGetEntry ::=
    SEQUENCE {	
        lteEnbNameInfo					DisplayString,  
		lteEnbFreqBandNumber			INTEGER,
        lteEnbUENumber					INTEGER
        }
       
lteEnbNameInfo OBJECT-TYPE
    SYNTAX DisplayString 
    MAX-ACCESS read-only
    STATUS current
    DESCRIPTION
        "The name of enb."
    ::= { lteEnbInfoGetEntry 1 } 

lteEnbFreqBandNumber OBJECT-TYPE
    SYNTAX INTEGER 
    MAX-ACCESS read-only
    STATUS current
    DESCRIPTION
        "The band number of enb."
    ::= { lteEnbInfoGetEntry 2 }   
lteEnbUENumber OBJECT-TYPE
    SYNTAX INTEGER 
    MAX-ACCESS read-only
    STATUS current
    DESCRIPTION
        "The UE number connected to this enb."
    ::= { lteEnbInfoGetEntry 3 }  


--*********************************************************************************  
--lteEnbInfoGetObjects ends
--*********************************************************************************
--**************************************************            
--* lteEpcStatusEntry starts * 
--************************************************** 
lteEpcStatusEntry        OBJECT IDENTIFIER  ::= { fsLteMIB 4 }     
lteEpcAttachUENumber OBJECT-TYPE
    SYNTAX INTEGER 
    MAX-ACCESS read-write
    STATUS current
    DESCRIPTION
        "the ue number attached to this epc."
    ::= { lteEpcStatusEntry 1 }                       

--**************************************************            
--* lteEpcStatusEntry ends * 
--**************************************************        
--**************************************************            
--* lteEpcConfigEntry starts * 
--************************************************** 
lteEpcConfigEntry        OBJECT IDENTIFIER  ::= { fsLteMIB 5 }     
lteEpcEEA OBJECT-TYPE
    SYNTAX INTEGER 
    MAX-ACCESS read-write
    STATUS current
    DESCRIPTION
        "the ue number attached to this epc."
    ::= { lteEpcConfigEntry 1 }    
                     
lteEpcEIA OBJECT-TYPE
    SYNTAX INTEGER 
    MAX-ACCESS read-write
    STATUS current
    DESCRIPTION
        "the EIA value epc."
    ::= { lteEpcConfigEntry 2 }
                             
lteEpcMMECode OBJECT-TYPE
    SYNTAX INTEGER 
    MAX-ACCESS read-write
    STATUS current
    DESCRIPTION
        "the MME value."
    ::= { lteEpcConfigEntry 3 }

lteEpcMMEGid OBJECT-TYPE
    SYNTAX INTEGER 
    MAX-ACCESS read-write
    STATUS current
    DESCRIPTION
        "the MME Gid value epc."
    ::= { lteEpcConfigEntry 4 }
    
lteEpcMCC OBJECT-TYPE
    SYNTAX INTEGER 
    MAX-ACCESS read-write
    STATUS current
    DESCRIPTION
        "the MCC value."
    ::= { lteEpcConfigEntry 5 }  
    
lteEpcMNC OBJECT-TYPE
    SYNTAX INTEGER 
    MAX-ACCESS read-write
    STATUS current
    DESCRIPTION
        "the epc MNC."
    ::= { lteEpcConfigEntry 6 }    
                                             
lteEpcEnbKeepalivetimer OBJECT-TYPE
    SYNTAX INTEGER 
    MAX-ACCESS read-write
    STATUS current
    DESCRIPTION
        "the ENodeB keep alive timer value."
    ::= { lteEpcConfigEntry 7 }   
    
lteEpcDNS OBJECT-TYPE
    SYNTAX IpAddress 
    MAX-ACCESS read-write
    STATUS current
    DESCRIPTION
        "the DNS address."
    ::= { lteEpcConfigEntry 8 }

--**************************************************            
--* lteEpcStatusEntry ends * 
--************************************************** 


lteUEIMSIMapIpObjects        OBJECT IDENTIFIER  ::= { fsLteMIB 6 }     
lteUEIMSIMapIpTable  OBJECT-TYPE
    SYNTAX SEQUENCE OF LteUEIMSIMapIpEntry
    MAX-ACCESS not-accessible
    STATUS current
    DESCRIPTION
      "The general information configure table."
    ::={ lteUEIMSIMapIpObjects 1 }   

lteUEIMSIMapIpEntry OBJECT-TYPE
    SYNTAX  LteUEIMSIMapIpEntry   
    MAX-ACCESS  not-accessible
    STATUS  current
    DESCRIPTION
        "The general information configure table."
    INDEX   { lteUEIMSI }
    ::= { lteUEIMSIMapIpTable 1 }

LteUEIMSIMapIpEntry ::=
    SEQUENCE {	
        lteUEIMSI					DisplayString,  
		lteUEIP						IpAddress,
        lteUERowStatus				RowStatus
        }
       
lteUEIMSI OBJECT-TYPE
    SYNTAX DisplayString 
    MAX-ACCESS read-create
    STATUS current
    DESCRIPTION
        "The UE imsi."
    ::= { lteUEIMSIMapIpEntry 1 }

lteUEIP OBJECT-TYPE
    SYNTAX IpAddress 
    MAX-ACCESS read-create
    STATUS current
    DESCRIPTION
        "The UE ip."
    ::= { lteUEIMSIMapIpEntry 2 } 
lteUERowStatus    OBJECT-TYPE
    SYNTAX  RowStatus
    MAX-ACCESS  read-create
    STATUS  current
    DESCRIPTION
            "The status column used for creating and
         deleting instances of the columnar objects in the table."
    ::= { lteUEIMSIMapIpEntry 3}  
                         
--**************************************************
--* lteFSTrapObjects begins * 
--**************************************************    
lteFSAlarmTraps            	OBJECT IDENTIFIER  ::= { fsLteMIB 7 }  
--**************apSystemAlarmTraps start ************************************
lteEnbOnlineTraps    NOTIFICATION-TYPE
    OBJECTS {    
        eNodeBmac,
        eNodeBname
    }
    STATUS  current
    DESCRIPTION
            " This trap will be sent when the enodeB online."
    ::= { lteFSAlarmTraps 1 }               

lteEnbOfflineTraps    NOTIFICATION-TYPE
    OBJECTS {    
        eNodeBmac,
        eNodeBname
    }
    STATUS  current
    DESCRIPTION
            " This trap will be sent when the enodeB offline."
    ::= { lteFSAlarmTraps 2 }  

lteUEAttachedTraps    NOTIFICATION-TYPE
    OBJECTS {
        ueIMSI,
        ueIpaddr
    } 
    STATUS  current
    DESCRIPTION
            " This trap will be sent when the UE Attached."
    ::= { lteFSAlarmTraps 3 }               

lteUEDetachedTraps    NOTIFICATION-TYPE
    OBJECTS {
        ueIMSI,
        ueIpaddr
    } 
    STATUS  current
    DESCRIPTION
            " This trap will be sent when the UE Detached."
    ::= { lteFSAlarmTraps 4 }
     
lteFSAlarmTrapObjects            	OBJECT IDENTIFIER  ::= { fsLteMIB 8 }  

--***************lteFSAlarmTrapObjects*************
eNodeBmac OBJECT-TYPE
    SYNTAX MacAddress
    MAX-ACCESS read-only
    STATUS current
    DESCRIPTION
        "enb mac address"
    ::= { lteFSAlarmTrapObjects 1 }
    
eNodeBname    OBJECT-TYPE
    SYNTAX      DisplayString
    MAX-ACCESS  read-only
    STATUS      current
    DESCRIPTION
        " enodeb name"
    ::= { lteFSAlarmTrapObjects 2 }  
    
ueIMSI OBJECT-TYPE
    SYNTAX DisplayString
    MAX-ACCESS read-only
    STATUS current
    DESCRIPTION
        "UE IMSI"
    ::= { lteFSAlarmTrapObjects 3 }
    
ueIpaddr    OBJECT-TYPE
    SYNTAX      IpAddress
    MAX-ACCESS  read-only
    STATUS      current
    DESCRIPTION
        " ue IP address "
    ::= { lteFSAlarmTrapObjects 4 }  
END

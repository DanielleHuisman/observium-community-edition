-- **********************************************************************
-- FS-MPLS-L3VPN-RES-MIB.mib: FS Mpls L3vpn Resource Statics MIB file
--
-- March 2013, WangMeng
--
-- Copyright (c) 2013 by FS.COM Inc..
-- All rights reserved.
--
-- **********************************************************************

FS-MPLS-L3VPN-RES-MIB DEFINITIONS ::= BEGIN
IMPORTS
   MODULE-IDENTITY,
   OBJECT-TYPE,
   Integer32
      FROM SNMPv2-SMI                                     -- [RFC2578]
   MODULE-COMPLIANCE, OBJECT-GROUP
      FROM SNMPv2-CONF                                    -- [RFC2580]
   RowStatus, StorageType, DisplayString
      FROM SNMPv2-TC                                      -- [RFC2579]
   InetAddress, InetAddressType
      FROM INET-ADDRESS-MIB                               -- [RFC4001]
   mplsL3VpnVrfName
      FROM MPLS-L3VPN-STD-MIB
   bgp4PathAttrIpAddrPrefix,
   bgp4PathAttrIpAddrPrefixLen,
   bgp4PathAttrPeer
      FROM BGP4-MIB
   fsMgmt
      FROM FS-SMI;

-- **********************************************************************
-- * MODULE IDENTITY
-- **********************************************************************
fsmplsL3VpnResMIB MODULE-IDENTITY
   LAST-UPDATED "201302210000Z"
   ORGANIZATION "FS.COM Inc.."
   CONTACT-INFO
                "Tel: 400-865-2852
                E-mail: https://www.fs.com/live_chat_service_mail.html"                  
   DESCRIPTION
        "This MIB contains managed object definitions for the
         neighbors' parameters of the
         Layer-3 Multiprotocol Label Switching Virtual
         Private Networks.

        Copyright (C) The Internet Society (2006).  This
        version of this MIB module is part of RFC4382; see
        the RFC itself for full legal notices."
  -- Revision history.
  REVISION
      "201302210000Z"
   DESCRIPTION
      "Initial version.  Published as RFC 4382."
   ::= { fsMgmt 123 }

fsmplsL3VpnResMIBObjects OBJECT IDENTIFIER ::= {fsmplsL3VpnResMIB 1}

-- **********************************************************************
-- * fsmplsL3VpnResTable table
-- **********************************************************************
fsmplsL3VpnResTable  OBJECT-TYPE
    SYNTAX        SEQUENCE OF FSmplsL3VpnResEntry
    MAX-ACCESS    not-accessible
    STATUS        current
    DESCRIPTION
       "This table specifies import/export RT resources on
        VRF and the RT/RD resource in VPNV4 route.
        Entries in this table define the map for VRF and 
		VPNV4 neighbor."
    ::= { fsmplsL3VpnResMIBObjects 1 }

fsmplsL3VpnResEntry  OBJECT-TYPE
    SYNTAX        FSmplsL3VpnResEntry
    MAX-ACCESS    not-accessible
    STATUS        current
    DESCRIPTION
       "An entry in this table is created by an LSR for
        every VRF capable of supporting MPLS L3VPN.  The
        indexing provides an ordering of VRFs name and
		VPNV4 neighber address"
    INDEX       { fsmplsL3VpnResPeAddr,
                  fsmplsL3VpnResVrfName}
    ::= { fsmplsL3VpnResTable 1 }

FSmplsL3VpnResEntry ::= SEQUENCE {
    fsmplsL3VpnResPeAddr        InetAddress,
    fsmplsL3VpnResVrfName      	DisplayString,
    fsmplsL3VpnResRtCollect     DisplayString,
    fsmplsL3VpnResRdCollect     DisplayString,
    fsmplsL3VpnResIntfAddr      InetAddress,
    fsmplsL3VpnResImptRt        DisplayString,
	fsmplsL3VpnResExptRt        DisplayString
}

fsmplsL3VpnResPeAddr OBJECT-TYPE
          SYNTAX InetAddress
          MAX-ACCESS read-only
          STATUS current
          DESCRIPTION
              "This attribute shall specify the remote address of
                the bgp neighbor in Layer-3 Multiprotocol Label
                Switching Virtual Private Networks. "
           ::= { fsmplsL3VpnResEntry 1 }

fsmplsL3VpnResVrfName OBJECT-TYPE
          SYNTAX DisplayString
          MAX-ACCESS read-only
          STATUS current
          DESCRIPTION
              "This attribute shall specify the name of VPN instance. "
           ::= { fsmplsL3VpnResEntry 2 }

fsmplsL3VpnResRtCollect OBJECT-TYPE
          SYNTAX DisplayString
          MAX-ACCESS read-write
          STATUS current
          DESCRIPTION
              "This attribute shall specify RT collection in route which learned from VPNV4 neighbor. "
           ::= { fsmplsL3VpnResEntry 3 }

fsmplsL3VpnResRdCollect OBJECT-TYPE
          SYNTAX DisplayString
          MAX-ACCESS read-only
          STATUS current
          DESCRIPTION
              "This attribute shall specify RD collection in route which learned from VPNV4 neighbor. "
           ::= { fsmplsL3VpnResEntry 4 }

fsmplsL3VpnResIntfAddr OBJECT-TYPE
          SYNTAX        InetAddress
          MAX-ACCESS    read-only
          STATUS        current
          DESCRIPTION
              "This attribute shall specify the local address which used to connect VPNV4 neighbor。"
          ::= { fsmplsL3VpnResEntry 5 }

fsmplsL3VpnResImptRt OBJECT-TYPE
          SYNTAX     DisplayString
          MAX-ACCESS read-only
          STATUS     current
          DESCRIPTION 
              "This attribute shall specify import RT configured on VPN instance."
          ::= { fsmplsL3VpnResEntry 6 }

fsmplsL3VpnResExptRt OBJECT-TYPE
          SYNTAX     DisplayString
          MAX-ACCESS read-only
          STATUS     current
          DESCRIPTION
              "This attribute shall specify export RT configured on VPN instance."
          ::= { fsmplsL3VpnResEntry 7 }
-- **********************************************************************
-- * End of fsmplsL3VpnResTable table
-- **********************************************************************

END

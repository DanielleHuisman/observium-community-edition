-- *****************************************************************
-- FS-PATCH-MIB.mib:  FS patch MIB file
--
-- Sep 2016, gaojinli
--
-- Copyright (c) 2016 by FS.COM Inc..
-- All rights reserved.
-- 
-- *****************************************************************
--

FS-PATCH-MIB DEFINITIONS ::= BEGIN

IMPORTS
        MODULE-IDENTITY,
        OBJECT-TYPE,
        Integer32,
        Unsigned32,
        Counter64,
        IpAddress
                FROM SNMPv2-SMI
        TruthValue,
        DisplayString,
        RowStatus,
        MacAddress
                FROM SNMPv2-TC
        MODULE-COMPLIANCE,
        OBJECT-GROUP
                FROM SNMPv2-CONF
        IfIndex,
        ConfigStatus
                FROM FS-TC        
        fsMgmt
                FROM FS-SMI;
				
fsPatchMIB MODULE-IDENTITY
        LAST-UPDATED "201609230000Z"
        ORGANIZATION "FS.COM Inc.."
        CONTACT-INFO
                " 
                Tel: 400-865-2852 

                E-mail: https://www.fs.com/live_chat_service_mail.html"
        DESCRIPTION
                "This module defines fs system patch mibs."
        REVISION      "201609230000Z"
        DESCRIPTION
                "Initial version of this MIB module."
        ::= { fsMgmt 151}

fsPatchMIBObjects OBJECT IDENTIFIER ::= { fsPatchMIB 1 }

fsPatchTable OBJECT-TYPE
        SYNTAX SEQUENCE OF FSPatchEntry
        MAX-ACCESS not-accessible
        STATUS current
        DESCRIPTION
               "A table of patch entries."
        ::= { fsPatchMIBObjects 1 }

fsPatchEntry OBJECT-TYPE
        SYNTAX FSPatchEntry
        MAX-ACCESS not-accessible
        STATUS current
        DESCRIPTION
                "Entry contains patch details."  
        INDEX { fsPatchDevIndex,
                fsPatchCmpntIndex}
        ::= { fsPatchTable 1 }

FSPatchEntry ::=
        SEQUENCE {
                fsPatchDevIndex Integer32,
                fsPatchCmpntIndex  Integer32,
                fsPatchDevId Integer32,
                fsPatchSlotId  Integer32,
                fsPatchCpuId Integer32,
                fsPatchExist DisplayString,
                fsPatchName DisplayString,
                fsPatchBranch DisplayString,
                fsPatchCmpntName DisplayString,
                fsPatchSize Counter64,
                fsPatchStatus DisplayString,
                fsPatchVersion  DisplayString,
                fsPatchInstallTime DisplayString,
                fsPatchDescription DisplayString
        }

fsPatchDevIndex OBJECT-TYPE
        SYNTAX        Integer32
        MAX-ACCESS read-only
        STATUS current
        DESCRIPTION
            "An index that represents a Devices."
        ::= { fsPatchEntry 1 }
		
fsPatchCmpntIndex OBJECT-TYPE
        SYNTAX        Integer32
        MAX-ACCESS read-only
        STATUS current
        DESCRIPTION
            "An index that represents a Patch Component."
        ::= { fsPatchEntry 2 }

fsPatchDevId OBJECT-TYPE
        SYNTAX        Integer32
        MAX-ACCESS read-only
        STATUS current
        DESCRIPTION
            "Device Identification."
        ::= { fsPatchEntry 3 }
		
fsPatchSlotId OBJECT-TYPE
        SYNTAX        Integer32
        MAX-ACCESS read-only
        STATUS current
        DESCRIPTION
            "Slot Identification."
        ::= { fsPatchEntry 4 }
		
fsPatchCpuId OBJECT-TYPE
        SYNTAX        Integer32
        MAX-ACCESS read-only
        STATUS current
        DESCRIPTION
            "Cpu Identification."
        ::= { fsPatchEntry 5 }
		
fsPatchExist OBJECT-TYPE
        SYNTAX        DisplayString
        MAX-ACCESS read-only
        STATUS current
        DESCRIPTION
            "Whether there is a Patch exist in the system."
        ::= { fsPatchEntry 6 }

fsPatchName OBJECT-TYPE
        SYNTAX        DisplayString
        MAX-ACCESS    read-only
        STATUS        current
        DESCRIPTION
            "The Patch Name."
        ::= { fsPatchEntry 7 }
		
fsPatchBranch OBJECT-TYPE
        SYNTAX        DisplayString
        MAX-ACCESS    read-only
        STATUS        current
        DESCRIPTION
            "The Patch Branch."
        ::= { fsPatchEntry 8 }
		
fsPatchCmpntName OBJECT-TYPE
        SYNTAX        DisplayString
        MAX-ACCESS    read-only
        STATUS        current
        DESCRIPTION
            "The Component name of a Patch."
        ::= { fsPatchEntry 9 }
		
fsPatchSize OBJECT-TYPE
        SYNTAX        Counter64
        MAX-ACCESS    read-only
        STATUS        current
        DESCRIPTION
            "The size of the Patch Component."
        ::= { fsPatchEntry 10 }
		
fsPatchStatus OBJECT-TYPE
        SYNTAX        DisplayString
        MAX-ACCESS    read-only
        STATUS        current
        DESCRIPTION
            "Currtent status of the Patch."
        ::= { fsPatchEntry 11 }
		
fsPatchVersion OBJECT-TYPE
        SYNTAX        DisplayString
        MAX-ACCESS    read-only
        STATUS        current
        DESCRIPTION
            "The Patch Version."
        ::= { fsPatchEntry 12 }
		
fsPatchInstallTime OBJECT-TYPE
        SYNTAX        DisplayString
        MAX-ACCESS    read-only
        STATUS        current
        DESCRIPTION
            "The Patch Install time."
        ::= { fsPatchEntry 13 }
		
fsPatchDescription OBJECT-TYPE
        SYNTAX        DisplayString
        MAX-ACCESS    read-only
        STATUS        current
        DESCRIPTION
            "The Patch Description."
        ::= { fsPatchEntry 14 }

END

-- *****************************************************************
-- This mib was extracted from draft-ietf-pim-mib-v2-01.txt
--
-- January 2003, zhenggao
--
-- Copyright (c) 2003 by FS.COM Inc..
-- All rights reserved.
-- 
-- *****************************************************************
FS-PIM-MIB DEFINITIONS ::= BEGIN

IMPORTS
    MODULE-IDENTITY, 
    OBJECT-TYPE, 
    NOTIFICATION-TYPE,
    Integer32, 
    IpAddress, 
    TimeTicks  
        FROM SNMPv2-SMI
    DisplayString, 
    RowStatus, 
    TruthValue            
        FROM SNMPv2-TC
    MODULE-COMPLIANCE,
    NOTIFICATION-GROUP,
    OBJECT-GROUP
        FROM SNMPv2-CONF
    ipMRouteGroup, 
    ipMRouteSource,
    ipMRouteSourceMask, 
    ipMRouteNextHopGroup,
    ipMRouteNextHopSource, 
    ipMRouteNextHopSourceMask,
    ipMRouteNextHopIfIndex,
    ipMRouteNextHopAddress           
        FROM IPMROUTE-STD-MIB
    EnabledStatus                
        FROM P-BRIDGE-MIB 
    fsMgmt                
        FROM FS-SMI
    InterfaceIndex                   
        FROM IF-MIB;

fsPimMIB MODULE-IDENTITY
    LAST-UPDATED "200301200000Z"
    ORGANIZATION "FS.COM Inc.."
    CONTACT-INFO
        "
        Tel: 400-865-2852
        
        E-mail:  https://www.fs.com/live_chat_service_mail.html"
    DESCRIPTION
        "This module defines fs Pim mibs."
    REVISION      "200301200000Z"
    DESCRIPTION
        "Initial version of this MIB module."
    ::= { fsMgmt 27}

fsPimMIBObjects OBJECT IDENTIFIER ::= { fsPimMIB 1 }

fsPimTraps      OBJECT IDENTIFIER ::= { fsPimMIBObjects 2 }

fsPim           OBJECT IDENTIFIER ::= { fsPimMIBObjects 1 }

fsPimJoinPruneInterval OBJECT-TYPE
    SYNTAX     Integer32
    UNITS      "seconds"
    MAX-ACCESS read-write
    STATUS     current
    DESCRIPTION
        "The default interval at which periodic PIM-SM Join/Prune
         messages are to be sent."
    DEFVAL { 60 }
    ::= { fsPim 1 }

-- The PIM Interface Table

fsPimInterfaceTable OBJECT-TYPE
    SYNTAX     SEQUENCE OF FSPimInterfaceEntry
    MAX-ACCESS not-accessible
    STATUS     current
    DESCRIPTION
        "The (conceptual) table listing the router's PIM interfaces.
         IGMP and PIM are enabled on all interfaces listed in this
         table."
    ::= { fsPim 2 }

fsPimInterfaceEntry OBJECT-TYPE
    SYNTAX     FSPimInterfaceEntry
    MAX-ACCESS not-accessible
    STATUS     current
    DESCRIPTION
        "An entry (conceptual row) in the fsPimInterfaceTable."
    INDEX      { fsPimInterfaceIfIndex }
    ::= { fsPimInterfaceTable 1 }

FSPimInterfaceEntry ::= SEQUENCE {
    fsPimInterfaceIfIndex                   InterfaceIndex,
    fsPimInterfaceAddress                   IpAddress,
    fsPimInterfaceNetMask                   IpAddress,
    fsPimInterfaceMode                      INTEGER,
    fsPimInterfaceDR                        IpAddress,
    fsPimInterfaceHelloInterval             Integer32,
    fsPimInterfaceJoinPruneInterval         Integer32,
    fsPimInterfaceCBSRPreference            Integer32,
    fsPimInterfaceTrigHelloInterval         Integer32,
    fsPimInterfaceHelloHoldtime             Integer32,
    fsPimInterfaceLanPruneDelay             INTEGER,
    fsPimInterfacePropagationDelay          Integer32,
    fsPimInterfaceOverrideInterval          Integer32,
    fsPimInterfaceGenerationID              INTEGER,
    fsPimInterfaceJoinPruneHoldtime         Integer32,
    fsPimInterfaceGraftRetryInterval        Integer32,
    fsPimInterfaceMaxGraftRetries           Integer32,
    fsPimInterfaceSRTTLThreshold            Integer32,
    fsPimInterfaceLanDelayEnabled           TruthValue,
    fsPimInterfaceSRCapable                 TruthValue,
    fsPimInterfaceDRPriority                Integer32,
    fsPimInterfaceNbrCounter                Integer32,     
    fsPimInterfaceBsrBorderEnabled          EnabledStatus,     
    fsPimInterfaceCountIn                   Integer32,
    fsPimInterfaceCountOut                  Integer32,
    fsPimInterfaceEnabled                   EnabledStatus, 
    fsPimNeighborFilterAcl                  DisplayString, 
    fsPimDrSupportAddressBound              DisplayString
}

fsPimInterfaceIfIndex OBJECT-TYPE
    SYNTAX     InterfaceIndex
    MAX-ACCESS not-accessible
    STATUS     current
    DESCRIPTION
        "The ifIndex value of this PIM interface."
    ::= { fsPimInterfaceEntry 1 }

fsPimInterfaceAddress OBJECT-TYPE
    SYNTAX     IpAddress
    MAX-ACCESS read-only
    STATUS     current
    DESCRIPTION
        "The IP address of the PIM interface."
    ::= { fsPimInterfaceEntry 2 }

fsPimInterfaceNetMask OBJECT-TYPE
    SYNTAX     IpAddress
    MAX-ACCESS read-only
    STATUS     current
    DESCRIPTION
        "The network mask for the IP address of the PIM interface."
    ::= { fsPimInterfaceEntry 3 }

fsPimInterfaceMode OBJECT-TYPE
    SYNTAX     INTEGER { dense(1), sparse(2), sparseDense(3) }
    MAX-ACCESS read-write
    STATUS     current
    DESCRIPTION
        "The configured mode of this PIM interface.  A value of
         sparseDense is only valid for PIMv1."
    DEFVAL     { dense }
    ::= { fsPimInterfaceEntry 4 }

fsPimInterfaceDR OBJECT-TYPE
    SYNTAX     IpAddress
    MAX-ACCESS read-only
    STATUS     current
    DESCRIPTION
        "The Designated Router on this PIM interface."
    ::= { fsPimInterfaceEntry 5 }

fsPimInterfaceHelloInterval OBJECT-TYPE
    SYNTAX     Integer32(0..65535)
    UNITS      "seconds"
    MAX-ACCESS read-write
    STATUS     current
    DESCRIPTION
        "The frequency at which PIM Hello messages are transmitted
         on this interface."
    DEFVAL     { 30 }
    ::= { fsPimInterfaceEntry 6 }

fsPimInterfaceJoinPruneInterval OBJECT-TYPE
    SYNTAX     Integer32
    UNITS      "seconds"
    MAX-ACCESS read-write
    STATUS     current
    DESCRIPTION
        "The frequency at which PIM Join/Prune messages are
         transmitted on this PIM interface.  The default value of
         this object is the pimJoinPruneInterval."
    ::= { fsPimInterfaceEntry 7 }

fsPimInterfaceCBSRPreference OBJECT-TYPE
    SYNTAX     Integer32 (-1..255)
    MAX-ACCESS read-write
    STATUS     current
    DESCRIPTION
        "The preference value for the local interface as a candidate
         bootstrap router.  The value of -1 is used to indicate that
         the local interface is not a candidate BSR interface."
    DEFVAL     { 0 }
    ::= { fsPimInterfaceEntry 8 }

fsPimInterfaceTrigHelloInterval OBJECT-TYPE 
    SYNTAX Integer32 
    UNITS "seconds"
    MAX-ACCESS read-write
    STATUS current
    DESCRIPTION 
        "The maximum time before a triggered PIM Hello message 
         is transmitted on this interface."
    DEFVAL { 5 } 
    ::= { fsPimInterfaceEntry 9 } 

fsPimInterfaceHelloHoldtime OBJECT-TYPE 
    SYNTAX Integer32 (0..65535) 
    UNITS "seconds"
    MAX-ACCESS read-write
    STATUS current
    DESCRIPTION 
        "The value set in the Holdtime field of Hello messages 
         transmitted on this interface.  This should be 3.5 
         times the value of pimInterfaceHelloInterval."
    DEFVAL { 105 } 
    ::= { fsPimInterfaceEntry 10 } 

fsPimInterfaceLanPruneDelay OBJECT-TYPE 
    SYNTAX INTEGER { off (2), on (1) }
    MAX-ACCESS read-write
    STATUS current
    DESCRIPTION 
        "Turns the LAN Prune Delay Option off and on on this 
         interface."
    DEFVAL { off }
    ::= { fsPimInterfaceEntry 11 }

fsPimInterfacePropagationDelay OBJECT-TYPE 
    SYNTAX Integer32 (0..32767)
    UNITS "milliseconds"
    MAX-ACCESS read-write
    STATUS current
    DESCRIPTION
        "The value inserted into the LAN Prune Delay field of a 
         LAN Prune Delay option on this interface."
    DEFVAL { 500 } 
    ::= { fsPimInterfaceEntry 12 }

fsPimInterfaceOverrideInterval OBJECT-TYPE 
    SYNTAX Integer32 (0..65535)
    MAX-ACCESS read-write
    STATUS current
    DESCRIPTION
        "The value inserted into the Override Interval field of 
         a LAN Prune Delay option on this interface."
    DEFVAL { 2500 } 
    ::= { fsPimInterfaceEntry 13 } 

fsPimInterfaceGenerationID OBJECT-TYPE 
    SYNTAX INTEGER { off (2), on (1) }
    MAX-ACCESS read-write
    STATUS current
    DESCRIPTION 
        "Turns the Generation ID Option off and on on this 
         interface."
    DEFVAL {off} 
    ::= { fsPimInterfaceEntry 14 }

fsPimInterfaceJoinPruneHoldtime OBJECT-TYPE
    SYNTAX Integer32 (0..65535)
    UNITS "seconds"
    MAX-ACCESS read-write
    STATUS current
    DESCRIPTION
        "The value inserted into the Holdtime field of a Join/
         Prune message sent on this interface.  The value should
         be 3.5 times pimInterfaceJoinPruneInterval."
    DEFVAL { 210 }
    ::= { fsPimInterfaceEntry 15 }

fsPimInterfaceGraftRetryInterval OBJECT-TYPE 
    SYNTAX Integer32
    UNITS "seconds"
    MAX-ACCESS read-write
    STATUS current
    DESCRIPTION
        "The interval a PIM router waits for a Graft Ack before 
         resending a Graft on this interface."
    DEFVAL { 3 } 
    ::= { fsPimInterfaceEntry 16 } 

fsPimInterfaceMaxGraftRetries OBJECT-TYPE 
    SYNTAX Integer32 
    MAX-ACCESS read-write
    STATUS current
    DESCRIPTION
        "The maximum number of times this router will resend a 
         Graft on this interface."
    DEFVAL { 2 } 
    ::= { fsPimInterfaceEntry 17 }

fsPimInterfaceSRTTLThreshold OBJECT-TYPE 
    SYNTAX Integer32 
    MAX-ACCESS read-write
    STATUS current
    DESCRIPTION
        "The Time To Live in a PIM-DM Refresh message at
         which it is not forwarded on this interface."
    DEFVAL { 0 }
    ::= { fsPimInterfaceEntry 18 }

fsPimInterfaceLanDelayEnabled OBJECT-TYPE 
    SYNTAX TruthValue
    MAX-ACCESS read-only
    STATUS current
    DESCRIPTION
        "Evaluates to TRUE if all routers on this interface are
         using the LAN Prune Delay Option."
    ::= { fsPimInterfaceEntry 19 }

fsPimInterfaceSRCapable OBJECT-TYPE 
    SYNTAX TruthValue
    MAX-ACCESS read-only
    STATUS current
    DESCRIPTION
        "Evaluates to TRUE if all routers on this interface are
         using the State Refresh Capable Option."
    ::= { fsPimInterfaceEntry 20 }

fsPimInterfaceDRPriority OBJECT-TYPE
    SYNTAX Integer32
    MAX-ACCESS read-write
    STATUS current
    DESCRIPTION
        "The Designater Router Priority inserted into the DR
         priority option on this interface."
    DEFVAL { 1 } 
    ::= { fsPimInterfaceEntry 21 }

fsPimInterfaceNbrCounter OBJECT-TYPE
    SYNTAX Integer32
    MAX-ACCESS read-only
    STATUS current
    DESCRIPTION
        "The number of interface's neighbour."
    ::= { fsPimInterfaceEntry 22 }
    
fsPimInterfaceBsrBorderEnabled    OBJECT-TYPE
    SYNTAX    EnabledStatus
    MAX-ACCESS read-write
    STATUS current
    DESCRIPTION
        "Enabled means Define a PIM bootstrap message boundary 
         for the PIM domain,use disabled to remove the PIM border."
    DEFVAL {disabled}
    ::= { fsPimInterfaceEntry 23 }
    
fsPimInterfaceCountIn       OBJECT-TYPE
    SYNTAX Integer32
    MAX-ACCESS read-only
    STATUS current
    DESCRIPTION 
        "Number of packets into  the interface since the 
         router has been up."
    ::= { fsPimInterfaceEntry 24 }

fsPimInterfaceCountOut       OBJECT-TYPE
    SYNTAX Integer32
    MAX-ACCESS read-only
    STATUS current
    DESCRIPTION 
        "Number of packets out of the interface 
         since the router has been up."
    ::= { fsPimInterfaceEntry 25 }

fsPimInterfaceEnabled OBJECT-TYPE 
    SYNTAX EnabledStatus
    MAX-ACCESS read-write
    STATUS current
    DESCRIPTION
        "use the ip pim command in interface configuration mode. 
         To disable PIM on the interface, use the no form of this 
         command."
    DEFVAL{disabled}
    ::= { fsPimInterfaceEntry 26 } 

fsPimNeighborFilterAcl   OBJECT-TYPE
    SYNTAX     DisplayString
    MAX-ACCESS read-write
    STATUS current
    DESCRIPTION
        "The name of the neighbor filter address list,which limits
         the scope of  the neighbor,The default value means all 
         neighbors will be allowed."
    DEFVAL{""}
    ::= { fsPimInterfaceEntry 27}    
    
fsPimDrSupportAddressBound    OBJECT-TYPE
    SYNTAX     DisplayString
    MAX-ACCESS read-write
    STATUS current
    DESCRIPTION 
        "The name of the DR support address  list,which limits the scope of 
         the souce address ,this will be only used when the interface is DR,
         The default value means all souce address will be allowed."
    DEFVAL{""}
    ::= { fsPimInterfaceEntry 28 }

--
-- The PIM Neighbor Table
--
fsPimNeighborTable OBJECT-TYPE
    SYNTAX     SEQUENCE OF FSPimNeighborEntry
    MAX-ACCESS not-accessible
    STATUS     current
    DESCRIPTION
        "The (conceptual) table listing the router's PIM neighbors."
    ::= { fsPim 3 }

fsPimNeighborEntry OBJECT-TYPE
    SYNTAX     FSPimNeighborEntry
    MAX-ACCESS not-accessible
    STATUS     current
    DESCRIPTION
        "An entry (conceptual row) in the fsPimNeighborTable."
    INDEX      { fsPimNeighborAddress }
    ::= { fsPimNeighborTable 1 }

FSPimNeighborEntry ::= SEQUENCE {
   fsPimNeighborAddress          IpAddress,
   fsPimNeighborIfIndex          InterfaceIndex,
   fsPimNeighborUpTime           TimeTicks,
   fsPimNeighborExpiryTime       TimeTicks,
   fsPimNeighborMode             INTEGER,
   fsPimNeighborLanPruneDelay    Integer32,
   fsPimNeighborOverrideInterval Integer32,
   fsPimNeighborTBit             Integer32,
   fsPimNeighborSRCapable        TruthValue,
   fsPimNeighborDRPresent        TruthValue
}

fsPimNeighborAddress OBJECT-TYPE
    SYNTAX     IpAddress
    MAX-ACCESS not-accessible
    STATUS     current
    DESCRIPTION
        "The IP address of the PIM neighbor for which this entry
         contains information."
    ::= { fsPimNeighborEntry 1 }

fsPimNeighborIfIndex OBJECT-TYPE
    SYNTAX     InterfaceIndex
    MAX-ACCESS read-only
    STATUS     current
    DESCRIPTION
        "The value of ifIndex for the interface used to reach this
         PIM neighbor."
    ::= { fsPimNeighborEntry 2 }

fsPimNeighborUpTime OBJECT-TYPE
    SYNTAX     TimeTicks
    MAX-ACCESS read-only
    STATUS     current
    DESCRIPTION
        "The time since this PIM neighbor (last) became a neighbor
         of the local router."
    ::= { fsPimNeighborEntry 3 }

fsPimNeighborExpiryTime OBJECT-TYPE
    SYNTAX     TimeTicks
    MAX-ACCESS read-only
    STATUS     current
    DESCRIPTION
        "The minimum time remaining before this PIM neighbor will be
         aged out."
    ::= { fsPimNeighborEntry 4 }
    
fsPimNeighborMode OBJECT-TYPE
    SYNTAX     INTEGER { dense(1), sparse(2) }
    MAX-ACCESS read-only
    STATUS     deprecated
    DESCRIPTION
        "The active PIM mode of this neighbor.  This object is
         deprecated for PIMv2 routers since all neighbors on the
         interface must be either dense or sparse as determined by
         the protocol running on the interface."
    ::= { fsPimNeighborEntry 5 }                   

fsPimNeighborLanPruneDelay OBJECT-TYPE 
    SYNTAX Integer32
    MAX-ACCESS read-only
    STATUS current
    DESCRIPTION
        "The value of LAN Prune Delay field of the LAN Prune 
         Delay Option received from this neighbor.  A value of 
         0 indicates that no LAN Prune Delay Option was 
         received from this neigbor."
    ::= { fsPimNeighborEntry 6 }

fsPimNeighborOverrideInterval OBJECT-TYPE 
    SYNTAX Integer32
    MAX-ACCESS read-only
    STATUS current
    DESCRIPTION
        "The value of Override Interval field of the LAN Prune
         Delay Option received from this neighbor.  A value of 
         0 indicates that no LAN Prune Delay Option was
         received from this neigbor."
    ::= { fsPimNeighborEntry 7 }

fsPimNeighborTBit OBJECT-TYPE 
    SYNTAX Integer32
    MAX-ACCESS read-only
    STATUS current
    DESCRIPTION
        "The value of the T bit field of the LAN Prune
         Delay Option received from this neighbor.  The T bit
         specifies the ability of the neighbor to disable
         join suppression."
    ::= { fsPimNeighborEntry 8 }

fsPimNeighborSRCapable OBJECT-TYPE 
    SYNTAX TruthValue
    MAX-ACCESS read-only
    STATUS current
    DESCRIPTION
        "Evaluates to TRUE if this neighbor is using the State
         Refresh Capable Option."
    ::= { fsPimNeighborEntry 9 }

fsPimNeighborDRPresent OBJECT-TYPE 
    SYNTAX TruthValue
    MAX-ACCESS read-only
    STATUS current
    DESCRIPTION
        "Evaluates to TRUE if this neighbor is using the
         Designated Router Option."
    ::= { fsPimNeighborEntry 10 }

--
-- The PIM IP Multicast Route Table
--

fsPimIpMRouteTable OBJECT-TYPE
    SYNTAX     SEQUENCE OF FSPimIpMRouteEntry
    MAX-ACCESS not-accessible
    STATUS     current
    DESCRIPTION
        "The (conceptual) table listing PIM-specific information on
         a subset of the rows of the ipMRouteTable defined in the IP
         Multicast MIB."
    ::= { fsPim 4 }

fsPimIpMRouteEntry OBJECT-TYPE
    SYNTAX     FSPimIpMRouteEntry
    MAX-ACCESS not-accessible
    STATUS     current
    DESCRIPTION
        "An entry (conceptual row) in the pimIpMRouteTable.  There
         is one entry per entry in the ipMRouteTable whose incoming
         interface is running PIM."
    INDEX      { ipMRouteGroup, ipMRouteSource, ipMRouteSourceMask }
    ::= { fsPimIpMRouteTable 1 }

FSPimIpMRouteEntry ::= SEQUENCE {
  fsPimIpMRouteUpstreamAssertTimer   TimeTicks,
  fsPimIpMRouteAssertMetric          Integer32,
  fsPimIpMRouteAssertMetricPref      Integer32,
  fsPimIpMRouteAssertRPTBit          TruthValue,
  fsPimIpMRouteFlags                 INTEGER,
  fsPimIpMRouteRPFNeighbor           IpAddress,
  fsPimIpMRouteSourceTimer           TimeTicks,
  fsPimIpMRouteOriginatorSRTTL       Integer32
}

fsPimIpMRouteUpstreamAssertTimer OBJECT-TYPE
    SYNTAX     TimeTicks
    MAX-ACCESS read-only
    STATUS     current
    DESCRIPTION
        "The time remaining before the router changes its upstream
         neighbor back to its RPF neighbor.  This timer is called the
         Assert timer in the PIM Sparse and Dense mode specification.
         A value of 0 indicates that no Assert has changed the
            upstream neighbor away from the RPF neighbor."
    ::= { fsPimIpMRouteEntry 1 }

fsPimIpMRouteAssertMetric OBJECT-TYPE
    SYNTAX     Integer32
    MAX-ACCESS read-only
    STATUS     current
    DESCRIPTION
        "The metric advertised by the assert winner on the upstream
         interface, or 0 if no such assert is in received."
    ::= { fsPimIpMRouteEntry 2 }

fsPimIpMRouteAssertMetricPref OBJECT-TYPE
    SYNTAX     Integer32
    MAX-ACCESS read-only
    STATUS     current
    DESCRIPTION
        "The preference advertised by the assert winner on the
         upstream interface, or 0 if no such assert is in effect."
    ::= { fsPimIpMRouteEntry 3 }

fsPimIpMRouteAssertRPTBit OBJECT-TYPE
    SYNTAX     TruthValue
    MAX-ACCESS read-only
    STATUS     current
    DESCRIPTION
        "The value of the RPT-bit advertised by the assert winner on
         the upstream interface, or false if no such assert is in
         effect."
    ::= { fsPimIpMRouteEntry 4 }

fsPimIpMRouteFlags OBJECT-TYPE
    SYNTAX  INTEGER {
                  rpt(0),
                  spt(1) 
                 }
    MAX-ACCESS read-only
    STATUS     current
    DESCRIPTION
        "This object describes PIM-specific flags related to a
         multicast state entry.  See the PIM Sparse Mode
         specification for the meaning of the RPT and SPT bits."
    ::= { fsPimIpMRouteEntry 5 }

fsPimIpMRouteRPFNeighbor OBJECT-TYPE 
    SYNTAX IpAddress
    MAX-ACCESS read-only
    STATUS current
    DESCRIPTION 
        "The IP Address of the current RPF neighbor.  If there
         is an upstream Assert Winner, it will be the RPF
         neighbor.  Otherwise, the RPF neighbor will be
         the next hop indicated by unicast routing."
    ::= { fsPimIpMRouteEntry 6 }

fsPimIpMRouteSourceTimer OBJECT-TYPE 
    SYNTAX TimeTicks
    MAX-ACCESS read-only
    STATUS current
    DESCRIPTION 
        "The time before this router ceases originating State
         Refresh messages for this route."
    ::= { fsPimIpMRouteEntry 7 }
    
fsPimIpMRouteOriginatorSRTTL  OBJECT-TYPE
    SYNTAX Integer32
    MAX-ACCESS read-only
    STATUS current
    DESCRIPTION
        "The TTL used in State Refresh messages originated by
         this router for this route."
    ::= { fsPimIpMRouteEntry 8 }

--
-- The PIM Next Hop Table
--

fsPimIpMRouteNextHopTable OBJECT-TYPE
    SYNTAX     SEQUENCE OF FSPimIpMRouteNextHopEntry
    MAX-ACCESS not-accessible
    STATUS     current
    DESCRIPTION
        "The (conceptual) table listing PIM-specific information on
         a subset of the rows of the ipMRouteNextHopTable defined in
         the IP Multicast MIB."
    ::= { fsPim 5 }
fsPimIpMRouteNextHopEntry OBJECT-TYPE
    SYNTAX     FSPimIpMRouteNextHopEntry
    MAX-ACCESS not-accessible
    STATUS     current
    DESCRIPTION
        "An entry (conceptual row) in the pimIpMRouteNextHopTable.
         There is one entry per entry in the ipMRouteNextHopTable
         whose interface is running PIM and whose
         ipMRouteNextHopState is pruned(1)."
    INDEX   { ipMRouteNextHopGroup, ipMRouteNextHopSource,
              ipMRouteNextHopSourceMask, ipMRouteNextHopIfIndex,
              ipMRouteNextHopAddress }
    ::= { fsPimIpMRouteNextHopTable 1 }

FSPimIpMRouteNextHopEntry ::= SEQUENCE {
   fsPimIpMRouteNextHopPruneReason       INTEGER,
   fsPimIpMRouteNextHopAssertWinner      IpAddress,
   fsPimIpMRouteNextHopAssertTimer       TimeTicks,
   fsPimIpMRouteNextHopAssertMetric      Integer32,
   fsPimIpMRouteNextHopAssertMetricPref  Integer32,
   fsPimIpMRouteNextHopJoinPruneTimer    TimeTicks
    }

fsPimIpMRouteNextHopPruneReason OBJECT-TYPE
    SYNTAX   INTEGER {
                     other (1),
                     prune (2),
                     assert (3)
                     }
    MAX-ACCESS read-only
    STATUS     current
    DESCRIPTION
        "This object indicates why the downstream interface was
         pruned, whether in response to a PIM prune message or due to
         PIM Assert processing."
    ::= { fsPimIpMRouteNextHopEntry 1 }      

fsPimIpMRouteNextHopAssertWinner OBJECT-TYPE 
    SYNTAX IpAddress
    MAX-ACCESS read-only
    STATUS current
    DESCRIPTION 
        "The IP Address of the Assert Winner."
    ::= { fsPimIpMRouteNextHopEntry 2 }

fsPimIpMRouteNextHopAssertTimer OBJECT-TYPE 
    SYNTAX TimeTicks
    MAX-ACCESS read-only
    STATUS current
    DESCRIPTION
        "The time remaining before the PIM router leaves the
         current Assert state.  A value of 0 indicates that the
         router is in the No Info state."
    ::= { fsPimIpMRouteNextHopEntry 3 }

fsPimIpMRouteNextHopAssertMetric OBJECT-TYPE 
    SYNTAX Integer32
    MAX-ACCESS read-only
    STATUS current
    DESCRIPTION
        "The metric advertised by the Assert Winner."
    ::= { fsPimIpMRouteNextHopEntry 4 }

fsPimIpMRouteNextHopAssertMetricPref OBJECT-TYPE 
    SYNTAX Integer32
    MAX-ACCESS read-only
    STATUS current
    DESCRIPTION
        "The metric preference advertised by the Assert Winner."
    ::= { fsPimIpMRouteNextHopEntry 5 }

fsPimIpMRouteNextHopJoinPruneTimer OBJECT-TYPE 
    SYNTAX TimeTicks
    MAX-ACCESS read-only
    STATUS current
    DESCRIPTION
        "The time remaining before the PIM router reverts to
         default operation on this interface.  PIM-SM will 
         cease forwarding, PIM-DM will resume forwarding."
    ::= { fsPimIpMRouteNextHopEntry 6 }

--
-- The PIM RP-Set Table 
--
fsPimRPSetTable OBJECT-TYPE
    SYNTAX     SEQUENCE OF FSPimRPSetEntry
    MAX-ACCESS not-accessible
    STATUS     current
    DESCRIPTION
        "The (conceptual) table listing PIM information for
         candidate Rendezvous Points (RPs) for IP multicast groups.
         When the local router is the BSR, this information is
         obtained from received Candidate-RP-Advertisements.  When
         the local router is not the BSR, this information is
         obtained from received RP-Set messages."
    ::= { fsPim 6 }

fsPimRPSetEntry OBJECT-TYPE
    SYNTAX     FSPimRPSetEntry
    MAX-ACCESS not-accessible
    STATUS     current
    DESCRIPTION
        "An entry (conceptual row) in the pimRPSetTable."
    INDEX   { fsPimRPSetComponent, fsPimRPSetGroupAddress,
              fsPimRPSetGroupMask, fsPimRPSetAddress }
    ::= { fsPimRPSetTable 1 }

FSPimRPSetEntry ::= SEQUENCE {
     fsPimRPSetGroupAddress    IpAddress, 
   fsPimRPSetGroupMask       IpAddress,
   fsPimRPSetAddress         IpAddress,
   fsPimRPSetHoldTime        Integer32,
   fsPimRPSetExpiryTime      TimeTicks,
   fsPimRPSetComponent       Integer32,
   fsPimRPSetUpTime          TimeTicks
    }

fsPimRPSetGroupAddress OBJECT-TYPE
    SYNTAX     IpAddress
    MAX-ACCESS not-accessible
    STATUS     current
    DESCRIPTION
        "The IP multicast group address which, when combined with
         pimRPSetGroupMask, gives the group prefix for which this
         entry contains information about the Candidate-RP."
    ::= { fsPimRPSetEntry 1 }
    
fsPimRPSetGroupMask OBJECT-TYPE
    SYNTAX     IpAddress
    MAX-ACCESS not-accessible
    STATUS     current
    DESCRIPTION
        "The multicast group address mask which, when combined with
         pimRPSetGroupAddress, gives the group prefix for which this
         entry contains information about the Candidate-RP."
    ::= { fsPimRPSetEntry 2 }

fsPimRPSetAddress OBJECT-TYPE
    SYNTAX     IpAddress
    MAX-ACCESS not-accessible
    STATUS     current
    DESCRIPTION
        "The IP address of the Candidate-RP."
    ::= { fsPimRPSetEntry 3 }

fsPimRPSetHoldTime OBJECT-TYPE
    SYNTAX     Integer32 (0..255)
    UNITS      "seconds"
    MAX-ACCESS read-only
    STATUS     current
    DESCRIPTION
        "The holdtime of a Candidate-RP."
    ::= { fsPimRPSetEntry 4 }

fsPimRPSetExpiryTime OBJECT-TYPE
    SYNTAX     TimeTicks
    MAX-ACCESS read-only
    STATUS     current
    DESCRIPTION
        "The minimum time remaining before the Candidate-RP will be
         declared down."
    ::= { fsPimRPSetEntry 5 }
    
fsPimRPSetComponent OBJECT-TYPE
    SYNTAX     Integer32 (1..255)
    MAX-ACCESS not-accessible
    STATUS     current
    DESCRIPTION
        " A number uniquely identifying the component.  Each
          protocol instance connected to a separate domain should have
          a different index value."
    ::= { fsPimRPSetEntry 6 }

fsPimRPSetUpTime  OBJECT-TYPE
    SYNTAX     TimeTicks
    MAX-ACCESS read-only
    STATUS     current
    DESCRIPTION
        " Length of time that this rp has been up."
    ::= { fsPimRPSetEntry 7 }


--
-- The PIM Component Table
--
fsPimComponentTable OBJECT-TYPE
    SYNTAX     SEQUENCE OF FSPimComponentEntry
    MAX-ACCESS not-accessible
    STATUS     current
    DESCRIPTION
        "The (conceptual) table containing objects specific to a PIM
         domain.  One row exists for each domain to which the router
         is connected.  A PIM-SM domain is defined as an area of the
         network over which Bootstrap messages are forwarded.
         Typically, a PIM-SM router will be a member of exactly one
         domain.  This table also supports, however, routers which
         may form a border between two PIM-SM domains and do not
         forward Bootstrap messages between them."
    ::= { fsPim 7 }

fsPimComponentEntry OBJECT-TYPE
    SYNTAX     FSPimComponentEntry
    MAX-ACCESS not-accessible
    STATUS     current
    DESCRIPTION
        "An entry (conceptual row) in the starPimComponentTable."
    INDEX      { fsPimComponentIndex }
    ::= { fsPimComponentTable 1 }

FSPimComponentEntry ::= SEQUENCE {
    fsPimComponentIndex                  Integer32,
    fsPimComponentBSRAddress             IpAddress,
    fsPimComponentBSRExpiryTime          TimeTicks,
    fsPimComponentCRPHoldTime            Integer32,
    fsPimComponentBSRUptime              TimeTicks,
    fsPimComponentBSRPriority            Integer32,
    fsPimComponentBSRHashMaskLength      Integer32,
    fsPimComponentBSRNextBsrMessage      TimeTicks,
    fsPimComponentNextCandRPAdv          TimeTicks
    }

fsPimComponentIndex OBJECT-TYPE
    SYNTAX     Integer32 (1..255)
    MAX-ACCESS not-accessible
    STATUS     current
    DESCRIPTION
        "A number uniquely identifying the component.  Each protocol
         instance connected to a separate domain should have a
         different index value.  Routers that only support membership
         in a single PIM-SM domain should use a pimComponentIndex
         value of 1."
    ::= { fsPimComponentEntry 1 }

fsPimComponentBSRAddress OBJECT-TYPE
    SYNTAX     IpAddress
    MAX-ACCESS read-only
    STATUS     current
    DESCRIPTION
        "The IP address of the bootstrap router (BSR) for the local
         PIM region."
    ::= { fsPimComponentEntry 2 }

fsPimComponentBSRExpiryTime OBJECT-TYPE
    SYNTAX     TimeTicks
    MAX-ACCESS read-only
    STATUS     current
    DESCRIPTION
        "The minimum time remaining before the bootstrap router in
         the local domain will be declared down.  For candidate BSRs,
         this is the time until the component sends an RP-Set
         message.  For other routers, this is the time until it may
         accept an RP-Set message from a lower candidate BSR."
    ::= { fsPimComponentEntry 3 }

fsPimComponentCRPHoldTime OBJECT-TYPE
    SYNTAX     Integer32 (0..255)
    UNITS      "seconds"
    MAX-ACCESS read-create
    STATUS     current
    DESCRIPTION
        "The holdtime of the component when it is a candidate RP in
         the local domain."
    ::= { fsPimComponentEntry 4 }

fsPimComponentBSRUptime   OBJECT-TYPE
    SYNTAX     TimeTicks
    MAX-ACCESS read-only
    STATUS     current
    DESCRIPTION
        "Length of time that this router has been up."
    ::= { fsPimComponentEntry 5 }

fsPimComponentBSRPriority  OBJECT-TYPE
    SYNTAX     Integer32
    MAX-ACCESS read-only
    STATUS     current
    DESCRIPTION
        "The Priority of Bsr."
    ::= { fsPimComponentEntry 6 }

fsPimComponentBSRHashMaskLength    OBJECT-TYPE
    SYNTAX     Integer32
    MAX-ACCESS read-only
    STATUS     current
    DESCRIPTION
        "Length of a mask (32 bits maximum) that is to be ANDed with
         the group address before the hash function is called."
    ::= { fsPimComponentEntry 7 }

fsPimComponentBSRNextBsrMessage    OBJECT-TYPE
    SYNTAX     TimeTicks
    MAX-ACCESS read-only
    STATUS     current
    DESCRIPTION
        "Time (in hours, minutes, and seconds) in which the next
         bootstrap message is due from this BSR."
    ::= { fsPimComponentEntry 8 }

fsPimComponentNextCandRPAdv    OBJECT-TYPE
    SYNTAX     TimeTicks
    MAX-ACCESS read-only
    STATUS     current
    DESCRIPTION
        "Time (in hours, minutes, and seconds) in which the next
         candidate RP advertisement will be sent."
    ::= { fsPimComponentEntry 9}

--
-- PIM State Refresh Objects
--
fsPimSourceLifetime OBJECT-TYPE 
    SYNTAX Integer32 
    UNITS "seconds"
    MAX-ACCESS read-write
    STATUS current
    DESCRIPTION
        "The maximum time this router will continue to
         originate State Refresh messages in the absence of
         traffic from the source itself."
    DEFVAL { 2100 }
    ::= { fsPim 8 }
    
fsPimStateRefreshInterval OBJECT-TYPE 
    SYNTAX Integer32 (1..255) 
    UNITS "seconds"
    MAX-ACCESS read-write
    STATUS current
    DESCRIPTION
        "The interval between successive State Refresh
         messages originated by this router."
    DEFVAL { 60 }
    ::= { fsPim 9 } 

fsPimStateRefreshLimitInterval OBJECT-TYPE 
    SYNTAX Integer32
    MAX-ACCESS read-write
    STATUS current
    DESCRIPTION
        "This router will not forward successive State Refresh
         messages received at less than this interval."
    DEFVAL { 0 } 
    ::= { fsPim 10 } 

fsPimStateRefreshTimeToLive OBJECT-TYPE 
    SYNTAX Integer32
    MAX-ACCESS read-write
    STATUS current
    DESCRIPTION
        "The TTL to be used by this router's originated State
         Refresh messages if the data packet's TTL is not
         recorded."
    DEFVAL { 16 } 
::= { fsPim 11 }

fsPimBsrCandidateGroup  OBJECT IDENTIFIER    ::= { fsPim 12 }

fsPimBsrCandidateIfindex     OBJECT-TYPE 
    SYNTAX Integer32
    MAX-ACCESS read-write  
    STATUS current
    DESCRIPTION 
        "Interface type and number on this router from which the bootstrap router
         address is derived, to make it a candidate. This interface must be enabled
         with Protocol Independent Multicast (PIM)."
::= { fsPimBsrCandidateGroup 1 }

fsPimBsrCandidateHashMaskLength     OBJECT-TYPE 
    SYNTAX Integer32(0..32)
    MAX-ACCESS read-write
    STATUS current
    DESCRIPTION 
        "Length of a mask (32 bits maximum) that is to be ANDed with
         the group address before the hash function is called. All 
         groups with the same seed hash (correspond) to the same RP.
         if fsPimBsrCandidateIfindex is 0,then set this value is 
         not valid."
    DEFVAL { 0 }
::= { fsPimBsrCandidateGroup 2 }

fsPimBsrCandidatePriority     OBJECT-TYPE 
    SYNTAX Integer32(0..255)
    MAX-ACCESS read-write
    STATUS current
    DESCRIPTION 
        "The BSR with the larger priority is preferred. If the priority 
         values are the same, the router with the larger IP address is 
         the BSR.if fsPimBsrCandidateIfindex is 0,then set this value 
         is not valid"
    DEFVAL { 0 }
::= { fsPimBsrCandidateGroup 3 }

fsPimRPTable   OBJECT-TYPE
    SYNTAX     SEQUENCE OF FSPimRPEntry
    MAX-ACCESS not-accessible
    STATUS     current 
    DESCRIPTION 
        "The (conceptual) table listing PIM version 2 information
         for the Rendezvous Points (RPs) for IP multicast groups."
    ::= { fsPim 13 }


fsPimRPEntry OBJECT-TYPE
    SYNTAX     FSPimRPEntry
    MAX-ACCESS not-accessible
    STATUS     current
    DESCRIPTION
        "An entry (conceptual row) in the pimRPTable."
    INDEX      { fsPimRPGroupAddress }
    ::= { fsPimRPTable 1 }

FSPimRPEntry ::= SEQUENCE {
   fsPimRPGroupAddress           IpAddress, 
   fsPimRPAddress                IpAddress,
   fsPimRPExpiryTime             TimeTicks, 
   fsPimRPNextRPReachableIn      TimeTicks  
}

fsPimRPGroupAddress OBJECT-TYPE
    SYNTAX     IpAddress
    MAX-ACCESS not-accessible
    STATUS     current
    DESCRIPTION
        "The IP multicast group address which, when combined with
         pimRPSetGroupMask, gives the group prefix for which this
         entry contains information about the Candidate-RP."
    ::= { fsPimRPEntry 1 }

fsPimRPAddress OBJECT-TYPE
    SYNTAX     IpAddress
    MAX-ACCESS read-only
    STATUS     current
    DESCRIPTION
        "The IP address of the RP."
    ::= { fsPimRPEntry 2 }

fsPimRPExpiryTime OBJECT-TYPE
    SYNTAX     TimeTicks
    MAX-ACCESS read-only
    STATUS     current
    DESCRIPTION
        "The minimum time remaining before the RP will be
         declared down.  If the local router is not the BSR, this
         value is 0."
    ::= { fsPimRPEntry 3 }

fsPimRPNextRPReachableIn   OBJECT-TYPE
    SYNTAX     TimeTicks
    MAX-ACCESS read-only
    STATUS     current
    DESCRIPTION
        "Indicates the time the next RP-reachable message will be sent.
         Time is expressed in hours:minutes:seconds."
    ::= { fsPimRPEntry 4 }


--
--static RP Table
--
fsPimStaticRPTable   OBJECT-TYPE
    SYNTAX     SEQUENCE OF FSPimStaticRPEntry
    MAX-ACCESS not-accessible
    STATUS     current 
    DESCRIPTION 
        "The (conceptual) table listing PIM version 2 information
         for the Rendezvous Points (RPs) for IP multicast groups."
    ::= { fsPim 14 }

fsPimStaticRPEntry OBJECT-TYPE
    SYNTAX     FSPimStaticRPEntry
    MAX-ACCESS not-accessible
    STATUS     current
    DESCRIPTION
        "An entry (conceptual row) in the pimStaticRPTable."
    INDEX      { fsPimStaticRPAddress }
    ::= { fsPimStaticRPTable 1 }

FSPimStaticRPEntry ::= SEQUENCE {   
   fsPimStaticRPAddress                IpAddress, 
   fsPimStaticRPAddressIsOverride      EnabledStatus, 
   fsPimStaticRPAclName                DisplayString,
   fsPimStaticRPStatus                 RowStatus
    }

fsPimStaticRPAddress OBJECT-TYPE
    SYNTAX     IpAddress
    MAX-ACCESS not-accessible
    STATUS     current
    DESCRIPTION
            "The IP address of the RP."
    ::= { fsPimStaticRPEntry 1 }

fsPimStaticRPAddressIsOverride   OBJECT-TYPE
    SYNTAX   EnabledStatus
    MAX-ACCESS read-create
    STATUS current
    DESCRIPTION 
        "Indicates that if there is a conflict, the RP configured with
         this command prevails over the RP learned by Bsr-RP."
    DEFVAL { disabled }
::= { fsPimStaticRPEntry  2 }

fsPimStaticRPAclName    OBJECT-TYPE
    SYNTAX        DisplayString
    MAX-ACCESS    read-create
    STATUS current
    DESCRIPTION 
        "Name of an access list that defines for which
         multicast groups the RP should be used,the 
         default value means all groups should be 
         used."
    DEFVAL { "" }
::= { fsPimStaticRPEntry  3 }

fsPimStaticRPStatus   OBJECT-TYPE
    SYNTAX     RowStatus
    MAX-ACCESS read-create
    STATUS current
    DESCRIPTION 
        "The status of this entry.  Creating the entry enables PIM
         on the interface; destroying the entry disables PIM on the
         interface."
    ::= {fsPimStaticRPEntry  4}

fsPimRpCandidateTable   OBJECT-TYPE
    SYNTAX     SEQUENCE OF FSPimRpCandidateEntry
    MAX-ACCESS not-accessible
    STATUS     current 
    DESCRIPTION 
        "The (conceptual) table listing the IP multicast groups for
         which the local router is to advertise itself as a
         Candidate-RP when the value of pimComponentCRPHoldTime is
         non-zero.  If this table is empty, then the local router
         will advertise itself as a Candidate-RP for all groups
         (providing the value of pimComponentCRPHoldTime is non-
         zero)."
    ::= { fsPim 15 } 

fsPimRpCandidateEntry OBJECT-TYPE
    SYNTAX     FSPimRpCandidateEntry
    MAX-ACCESS not-accessible
    STATUS     current
    DESCRIPTION
        "An entry (conceptual row) in the pimRpCandidateTable."
    INDEX      {  fsPimRpCandidateIfindex }
    ::= { fsPimRpCandidateTable 1 }

FSPimRpCandidateEntry ::= SEQUENCE {   
    fsPimRpCandidateIfindex         InterfaceIndex,
    fsPimRpCandidateAclName         DisplayString,
    fsPimRpCandidateStatus          RowStatus
    }

fsPimRpCandidateIfindex  OBJECT-TYPE
    SYNTAX InterfaceIndex
    MAX-ACCESS not-accessible
    STATUS current
    DESCRIPTION 
        "IP address associated with this interface type and number 
         is advertised as a candidate RP address."
    ::= { fsPimRpCandidateEntry 1 }
    
fsPimRpCandidateAclName    OBJECT-TYPE
    SYNTAX        DisplayString
    MAX-ACCESS    read-create
    STATUS current
    DESCRIPTION 
        "The name of Acl list,that defines the group
         prefixes that are advertised in association 
         with the RP address,the default value means
         all groups will be advertised in association
         with the RP address."
    DEFVAL { "" }
    ::= { fsPimRpCandidateEntry 2 }

fsPimRpCandidateStatus   OBJECT-TYPE
    SYNTAX     RowStatus
    MAX-ACCESS read-create
    STATUS current
    DESCRIPTION 
        "The status of this entry.  Creating the entry enables PIM
         on the interface; destroying the entry disables PIM on the
         interface."
    ::= {fsPimRpCandidateEntry 3}
    
-- PIM Traps
fsPimNeighborLoss NOTIFICATION-TYPE
    OBJECTS {
       fsPimNeighborIfIndex
    }
    STATUS             current
    DESCRIPTION
        "A pimNeighborLoss trap signifies the loss of an adjacency
         with a neighbor.  This trap should be generated when the
         neighbor timer expires, and the router has no other
         neighbors on the same interface with a lower IP address than
         itself."
    ::= { fsPimTraps 1 }

 
-- compliance statements
fsPimMIBConformance OBJECT IDENTIFIER ::= { fsPimMIB 2 }
fsPimMIBCompliances OBJECT IDENTIFIER ::= { fsPimMIBConformance 1 }
fsPimMIBGroups      OBJECT IDENTIFIER ::= { fsPimMIBConformance 2 }

fsPimMIBCompliance MODULE-COMPLIANCE
        STATUS  current
        DESCRIPTION
                "The compliance statement for entities which implement
                the FS Pim MIB"
        MODULE  -- this module
                MANDATORY-GROUPS { fsPimMIBGroup
                 }
                       
        ::= { fsPimMIBCompliances 1 }

        
-- units of conformance

fsPimMIBGroup OBJECT-GROUP
        OBJECTS {
        fsPimJoinPruneInterval,
        fsPimInterfaceAddress,
        fsPimInterfaceNetMask,
        fsPimInterfaceMode,
        fsPimInterfaceDR,
        fsPimInterfaceHelloInterval,
        fsPimInterfaceJoinPruneInterval,
        fsPimInterfaceCBSRPreference,
        fsPimInterfaceTrigHelloInterval,
        fsPimInterfaceHelloHoldtime,
        fsPimInterfaceLanPruneDelay,
        fsPimInterfacePropagationDelay,
        fsPimInterfaceOverrideInterval,
        fsPimInterfaceGenerationID,
        fsPimInterfaceJoinPruneHoldtime,
        fsPimInterfaceGraftRetryInterval,
        fsPimInterfaceMaxGraftRetries,
        fsPimInterfaceSRTTLThreshold,
        fsPimInterfaceLanDelayEnabled,
        fsPimInterfaceSRCapable,
        fsPimInterfaceDRPriority,
        fsPimInterfaceNbrCounter,     
        fsPimInterfaceBsrBorderEnabled,     
        fsPimInterfaceCountIn,
        fsPimInterfaceCountOut,
        fsPimInterfaceEnabled, 
        fsPimNeighborFilterAcl, 
        fsPimDrSupportAddressBound,
        fsPimNeighborIfIndex,
        fsPimNeighborUpTime,
        fsPimNeighborExpiryTime,
        fsPimNeighborMode,
        fsPimNeighborLanPruneDelay,
        fsPimNeighborOverrideInterval,
        fsPimNeighborTBit,
        fsPimNeighborSRCapable,
        fsPimNeighborDRPresent,
        fsPimIpMRouteUpstreamAssertTimer,
        fsPimIpMRouteAssertMetric,
        fsPimIpMRouteAssertMetricPref,
        fsPimIpMRouteAssertRPTBit,
        fsPimIpMRouteFlags,
        fsPimIpMRouteRPFNeighbor,
        fsPimIpMRouteSourceTimer,
        fsPimIpMRouteOriginatorSRTTL,
        fsPimIpMRouteNextHopPruneReason,
        fsPimIpMRouteNextHopAssertWinner,
        fsPimIpMRouteNextHopAssertTimer,
        fsPimIpMRouteNextHopAssertMetric,
        fsPimIpMRouteNextHopAssertMetricPref,
        fsPimIpMRouteNextHopJoinPruneTimer,
        fsPimRPSetHoldTime,
        fsPimRPSetExpiryTime,
        fsPimRPSetUpTime,
        fsPimComponentBSRAddress,
        fsPimComponentBSRExpiryTime,
        fsPimComponentCRPHoldTime,
        fsPimComponentBSRUptime,
        fsPimComponentBSRPriority,
        fsPimComponentBSRHashMaskLength,
        fsPimComponentBSRNextBsrMessage,
        fsPimComponentNextCandRPAdv,
        fsPimSourceLifetime,
        fsPimStateRefreshInterval, 
        fsPimStateRefreshLimitInterval,
        fsPimStateRefreshTimeToLive,
        fsPimBsrCandidateIfindex,
        fsPimBsrCandidateHashMaskLength,
        fsPimBsrCandidatePriority,
        fsPimRPAddress,
        fsPimRPExpiryTime,  
        fsPimRPNextRPReachableIn,
        fsPimStaticRPAddressIsOverride, 
        fsPimStaticRPAclName,
        fsPimStaticRPStatus,
        fsPimRpCandidateAclName,
        fsPimRpCandidateStatus
        }
        STATUS  current
        DESCRIPTION
                "A collection of objects providing pim management and
                opertion to a FS agent."
        ::= { fsPimMIBGroups 1 } 
        
fsPimNotifyGroup NOTIFICATION-GROUP
       NOTIFICATIONS { fsPimNeighborLoss }
       STATUS     current
       DESCRIPTION
              "The collection of objects which are used to specify 
               notifications for pim."
       ::= { fsPimMIBGroups 2 } 

END

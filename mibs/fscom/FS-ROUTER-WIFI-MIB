-- ****************************************************************
-- FS WIFI Configuration and Statistics MIB
--   
-- DEC 2014, Xiongyang
--   
-- Copyright (c) 2014 by FS.COM Inc..
-- All rights reserved.
--   
-- ****************************************************************


-- Start module
FS-ROUTER-WIFI-MIB DEFINITIONS ::= BEGIN

-- Start external defined node
IMPORTS
    MODULE-IDENTITY,
    OBJECT-TYPE,
    Integer32,
    Counter32,
    Gauge32,
    Unsigned32,
    Counter64,
    IpAddress
        FROM SNMPv2-SMI
    MODULE-COMPLIANCE,
    OBJECT-GROUP
        FROM SNMPv2-CONF
    TEXTUAL-CONVENTION,
    DisplayString,
    MacAddress,
    RowStatus,
    TruthValue
        FROM SNMPv2-TC
    InterfaceIndex
        FROM IF-MIB
    fsMgmt
        FROM FS-SMI;
-- End external defined node


-- Start root node
fsWifiMIB MODULE-IDENTITY
        LAST-UPDATED "201412290000Z"
        ORGANIZATION "FS.COM Inc.."
        CONTACT-INFO
                "E-mail: https://www.fs.com/live_chat_service_mail.html"
        DESCRIPTION
                "This module defines fs wifi mibs."

        REVISION    "201412290000Z"
        DESCRIPTION
                "Initial version of this MIB module."
        ::= { fsMgmt 133}
        
        FSEableType ::= TEXTUAL-CONVENTION
          STATUS  current
          DESCRIPTION
             "enable or disable."
          SYNTAX INTEGER {
                     enable(1),
                     disable(2)
                         }

       FSWlanType ::= TEXTUAL-CONVENTION
          STATUS  current
          DESCRIPTION
             "wlan type."
          SYNTAX INTEGER {
                     ap(1),
                     station(2)
                         }
       
       FSIsolateType ::= TEXTUAL-CONVENTION
          STATUS  current
          DESCRIPTION
             "wlan ap Isolate type."
          SYNTAX INTEGER {
                     isolate(1),
                     noisolate(2)
                         } 
                         
       FSAuthenticationType ::= TEXTUAL-CONVENTION
          STATUS  current
          DESCRIPTION
             "authentication type."
          SYNTAX INTEGER {
                     open(1),
                     share-key(2)
                         } 
         
       FSWapPskCiphersType ::= TEXTUAL-CONVENTION
          STATUS  current
          DESCRIPTION
             "authentication type."
          SYNTAX INTEGER {
                     aes(1),
                     tkip(2),
                     auto(3)
                         }   
                         
       FSWifiChanWidthType ::= TEXTUAL-CONVENTION
          STATUS  current
          DESCRIPTION
             "Chanle Width type."
          SYNTAX INTEGER {
                     twenty(1),
                     forty(2)
                         }   
       FSWifiSlotType ::= TEXTUAL-CONVENTION
          STATUS  current
          DESCRIPTION
             "Slot type."
          SYNTAX INTEGER {
                     short(1),
                     long(2)
                         } 
       
       FSWifiFreChanelType ::= TEXTUAL-CONVENTION
          STATUS  current
          DESCRIPTION
             "Chanle Width type."
          SYNTAX INTEGER {
                     two-point-four(1),
                     five(2)
                         }              
                            
-- End root node
  
        fsWifiMIBObjects OBJECT IDENTIFIER ::= { fsWifiMIB 1 } 
     -- WIFI MIB    


-- Node definitions
        fsWifiDot11radioSupportObjects OBJECT IDENTIFIER ::= { fsWifiMIBObjects  1 } 
        fsWifiWlanObjects OBJECT IDENTIFIER ::= { fsWifiMIBObjects  2 }
        fsWifiDot11radioIfConfigObjects OBJECT IDENTIFIER ::= { fsWifiMIBObjects 3 }
--      fsWifiDot11radioIfApplyObjects OBJECT IDENTIFIER ::= { fsWifiMIBObjects 4 }
        fsWifiWlanAssociateObjects OBJECT IDENTIFIER ::= { fsWifiMIBObjects 4 }        
 
-- Start wifiwlan objects       
        fsWifiDot11radioSupportTable OBJECT-TYPE  
            SYNTAX SEQUENCE OF FSWifiDot11radioSupportEntry
            MAX-ACCESS            not-accessible
            STATUS                current
            DESCRIPTION
                "the router support the wifi ability ,
                 include radio index,ap number,station number"
            ::= { fsWifiDot11radioSupportObjects 1 }
                
        fsWifiDot11radioSupportEntry OBJECT-TYPE
            SYNTAX FSWifiDot11radioSupportEntry
            MAX-ACCESS not-accessible
            STATUS current
            DESCRIPTION
                "the router support the wifi ability entry."
            INDEX { fsWifiDot11radioIndex }
            ::= { fsWifiDot11radioSupportTable 1 } 
        
        FSWifiDot11radioSupportEntry::=
            SEQUENCE { 
            	fsWifiDot11radioIndex
            		Integer32,
                fsWifiDot11radioApMaxCnt
            		Integer32, 
                fsWifiDot11radioStationMaxCnt
            		Integer32   
             }                
        
        fsWifiDot11radioIndex OBJECT-TYPE
            SYNTAX Integer32
            MAX-ACCESS read-only
            STATUS current
            DESCRIPTION
                "the wifi radio interface index."
            ::= { fsWifiDot11radioSupportEntry 1 }

        fsWifiDot11radioApMaxCnt OBJECT-TYPE
            SYNTAX Integer32
            MAX-ACCESS read-only
            STATUS current
            DESCRIPTION
                "the wifi radio interface support max ap count."
            ::= { fsWifiDot11radioSupportEntry 2 } 
        
        fsWifiDot11radioStationMaxCnt OBJECT-TYPE
            SYNTAX Integer32
            MAX-ACCESS read-only
            STATUS current
            DESCRIPTION
                "the wifi radio interface support max station count."
            ::= { fsWifiDot11radioSupportEntry 3 }

        fsWifiWlanIndexNext OBJECT-TYPE
            SYNTAX                INTEGER
            MAX-ACCESS            read-only
            STATUS                current
            DESCRIPTION   "This object contains an appropriate value to be used
                          for fsWifiWlanIndexNext when creating entries in the
                          fsWifiWlanTable. The value 0 indicates that no
                          unassigned entries are available."
            ::= { fsWifiWlanObjects 1 }
        
        fsWifiVlanIndexNext OBJECT-TYPE
            SYNTAX                INTEGER
            MAX-ACCESS            read-only
            STATUS                current
            DESCRIPTION   "This object contains an appropriate value to be used
                          for fsWifiVlanIndexNext when creating entries in the
                          fsWifiWlanTable. The value 0 indicates that no
                          unassigned entries are available."
            ::= { fsWifiWlanObjects 2 }  
               
        fsWifiWlanTable OBJECT-TYPE
            SYNTAX SEQUENCE OF FSWifiWlanEntry
            MAX-ACCESS not-accessible
            STATUS current
            DESCRIPTION
                "A table of wifi wlan templet."
            ::= { fsWifiWlanObjects 3 }
        
        fsWifiWlanEntry OBJECT-TYPE
            SYNTAX FSWifiWlanEntry
            MAX-ACCESS not-accessible
            STATUS current
            DESCRIPTION
                "Wifi wlan temple entry."
            INDEX { fsWifiWlanIndex }
            ::= { fsWifiWlanTable 1 }
   
        FSWifiWlanEntry ::=
            SEQUENCE { 
            	fsWifiWlanIndex
            		Integer32,
                fsWifiWlanType
                    FSWlanType,   
                fsWifiWlanSsidName
                    DisplayString,
                fsWifiWlanVlanId
                    Integer32, 
                fsWifiWlanRowStatus           
                    RowStatus,
                fsWifiWlanBroadcastSsid
                    FSEableType,
                fsWifiWlanIsolate
                    FSIsolateType,
                fsWifiWlanBssStaLimit
                    Integer32,  
                rujieWifiWlanSecurityType 
                    BITS, 
                fsWifiWlanAuthenticationSetKey
                    DisplayString,
                fsWifiWlanWepAuthenticationType  
                    FSAuthenticationType, 
                fsWifiWlanWpaPskCiphersType    
                    FSWapPskCiphersType, 
                fsWifiWlanPassphrase 
                    DisplayString,
                fsWifiWlanDot11RadioIfindex
                    Integer32,
                fsWifiWlanDot11RadioSubIfindex
                    Integer32
                             }
             
        fsWifiWlanIndex OBJECT-TYPE
            SYNTAX Integer32(1..15)
            MAX-ACCESS read-only
            STATUS current
            DESCRIPTION
                "The wlan index"
            ::= { fsWifiWlanEntry 1 }
                    
        fsWifiWlanType OBJECT-TYPE
            SYNTAX FSWlanType
            MAX-ACCESS read-write
            STATUS current
            DESCRIPTION
                "Wlan type ap or station."
            ::= { fsWifiWlanEntry 2 }

        fsWifiWlanSsidName OBJECT-TYPE
            SYNTAX DisplayString(SIZE (1..32))
            MAX-ACCESS read-write
            STATUS current
            DESCRIPTION
                "Wlan ssid name"
            ::= { fsWifiWlanEntry 3 }
        
        fsWifiWlanVlanId OBJECT-TYPE
            SYNTAX Integer32(1..4095)
            MAX-ACCESS read-write
            STATUS current
            DESCRIPTION
                "Wlan vlan id"
            ::= { fsWifiWlanEntry 4 }   
            
        fsWifiWlanRowStatus OBJECT-TYPE
            SYNTAX RowStatus
            MAX-ACCESS read-write
            STATUS current
            DESCRIPTION
                "create/modify/delete wlan"
            ::= { fsWifiWlanEntry 5 }

        
        fsWifiWlanBroadcastSsid OBJECT-TYPE
            SYNTAX FSEableType
            MAX-ACCESS read-write
            STATUS current
            DESCRIPTION
                "BroadcastSsid enable or disable"
            ::= { fsWifiWlanEntry 6}
        
        fsWifiWlanIsolate OBJECT-TYPE
            SYNTAX FSIsolateType
            MAX-ACCESS read-write
            STATUS current
            DESCRIPTION
                "Isolate ap"
            ::= { fsWifiWlanEntry 7 }
        
        fsWifiWlanBssStaLimit OBJECT-TYPE
            SYNTAX Integer32
            MAX-ACCESS read-write
            STATUS current
            DESCRIPTION
                "the number of user count of bss"
            ::= { fsWifiWlanEntry 8 }
        
        rujieWifiWlanSecurityType OBJECT-TYPE
            SYNTAX BITS {
               null(0),
               wep(1),
               wpa-psk(2),
               wpa2-psk(3)
            }
            MAX-ACCESS read-write
            STATUS current
            DESCRIPTION
                "wlan security type"
            ::= { fsWifiWlanEntry 9 }
                        
        fsWifiWlanAuthenticationSetKey OBJECT-TYPE
            SYNTAX DisplayString
            MAX-ACCESS read-write
            STATUS current
            DESCRIPTION
                "wlan security authentication type"
            ::= { fsWifiWlanEntry 10 }
        
            
        fsWifiWlanWepAuthenticationType OBJECT-TYPE
            SYNTAX FSAuthenticationType
            MAX-ACCESS read-write
            STATUS current
            DESCRIPTION
                "the wep authentication type"
            ::= { fsWifiWlanEntry 11 }
 
 		fsWifiWlanWpaPskCiphersType OBJECT-TYPE
            SYNTAX FSWapPskCiphersType
            MAX-ACCESS read-write
            STATUS current
            DESCRIPTION
                "Wpa-psk ciphers type."
            ::= { fsWifiWlanEntry 12 }   

        fsWifiWlanPassphrase OBJECT-TYPE
            SYNTAX DisplayString
            MAX-ACCESS read-write
            STATUS current
            DESCRIPTION
                "The station connect ap setkey ."
            ::= { fsWifiWlanEntry 13 }   
             
        fsWifiWlanDot11RadioIfindex OBJECT-TYPE
            SYNTAX Integer32
            MAX-ACCESS read-only
            STATUS current
            DESCRIPTION
                "the ifindex of interface dot11radio"
            ::= { fsWifiWlanEntry 14 }  
            
        fsWifiWlanDot11RadioSubIfindex OBJECT-TYPE
            SYNTAX Integer32
            MAX-ACCESS read-only
            STATUS current
            DESCRIPTION
                "the ifindex of subinterface dot11radio"
            ::= { fsWifiWlanEntry 15 } 
                   
-- End wifi wlan objects         

-- Start Dot11radio interface config objects       
        fsWifiDot11radioIfConfigTable OBJECT-TYPE
            SYNTAX SEQUENCE OF FSWifiDot11radioIfConfigEntry
            MAX-ACCESS not-accessible
            STATUS current
            DESCRIPTION
                "A table of wifi Dot11radio interface config."
            ::= { fsWifiDot11radioIfConfigObjects 1 } 
            
         fsWifiDot11radioIfConfigEntry OBJECT-TYPE
            SYNTAX FSWifiDot11radioIfConfigEntry
            MAX-ACCESS not-accessible
            STATUS current
            DESCRIPTION
                "wifi Dot11radio interface config entry."
            INDEX { fsWifiDot11radioIfConfigIfIndex }
            ::= { fsWifiDot11radioIfConfigTable 1 }    
            
         
         FSWifiDot11radioIfConfigEntry ::=
            SEQUENCE { 
            	fsWifiDot11radioIfConfigIfIndex
            	    Integer32, 
                fsWifiDot11radioIfConfigRowStatus           
                    RowStatus, 
                fsWifiDot11radioIfConfigFreBand
                    FSWifiFreChanelType,
                fsWifiDot11radioIfConfigChannel
                    Integer32,
                fsWifiDot11radioIfConfigChanWidth
                    FSWifiChanWidthType,
                fsWifiDot11radioIfConfigCountryCode
                    DisplayString,
                fsWifiDot11radioIfConfigPowerLocal
                    Integer32,
                fsWifiDot11radioIfConfigWirelessProSupport 
                    BITS,
                fsWifiDot11radioIfConfigStaLimit
                    Integer32,
                fsWifiDot11radioIfConfig20ShortGiEnable
                    FSEableType, 
                fsWifiDot11radioIfConfig40ShortGiEnable
                    FSEableType,
                fsWifiDot11radioIfConfigShortPreambleEnable
                    FSEableType,
                fsWifiDot11radioIfConfigSlottime 
                    FSWifiSlotType,
                fsWifiDot11radioIfConfigRtsThreshold
                    Integer32, 
                fsWifiDot11radioIfConfigFragmentThreshold  
                    Integer32, 
                fsWifiDot11radioIfConfigResponseRssi 
                    Integer32,  
                fsWifiDot11radioIfConfigEnableQos
                    FSEableType,
                fsWifiDot11radioIfConfigEdcaClientBgAifsn
                    Integer32,
                fsWifiDot11radioIfConfigEdcaClientBgCwmin 
                    Integer32,
                fsWifiDot11radioIfConfigEdcaClientBgCwmax
                    Integer32,
                fsWifiDot11radioIfConfigEdcaClientBgTxop
                    Integer32,
                fsWifiDot11radioIfConfigEdcaClientBeAifsn
                    Integer32,
                fsWifiDot11radioIfConfigEdcaClientBeCwmin 
                    Integer32,
                fsWifiDot11radioIfConfigEdcaClientBeCwmax
                    Integer32,
                fsWifiDot11radioIfConfigEdcaClientBeTxop
                    Integer32,
                fsWifiDot11radioIfConfigEdcaClientViAifsn
                    Integer32,
                fsWifiDot11radioIfConfigEdcaClientViCwmin 
                    Integer32,
                fsWifiDot11radioIfConfigEdcaClientViCwmax
                    Integer32,
                fsWifiDot11radioIfConfigEdcaClientViTxop
                    Integer32, 
                fsWifiDot11radioIfConfigEdcaClientVoAifsn
                    Integer32,
                fsWifiDot11radioIfConfigEdcaClientVoCwmin 
                    Integer32,
                fsWifiDot11radioIfConfigEdcaClientVoCwmax
                    Integer32,
                fsWifiDot11radioIfConfigEdcaClientVoTxop
                    Integer32,
                fsWifiDot11radioIfConfigEdcaRadioBgAifsn
                    Integer32,
                fsWifiDot11radioIfConfigEdcaRadioBgCwmin 
                    Integer32,
                fsWifiDot11radioIfConfigEdcaRadioBgCwmax
                    Integer32,
                fsWifiDot11radioIfConfigEdcaRadioBgTxop
                    Integer32,
                fsWifiDot11radioIfConfigEdcaRadioBeAifsn
                    Integer32,
                fsWifiDot11radioIfConfigEdcaRadioBeCwmin 
                    Integer32,
                fsWifiDot11radioIfConfigEdcaRadioBeCwmax
                    Integer32,
                fsWifiDot11radioIfConfigEdcaRadioBeTxop
                    Integer32,
                fsWifiDot11radioIfConfigEdcaRadioViAifsn
                    Integer32,
                fsWifiDot11radioIfConfigEdcaRadioViCwmin 
                    Integer32,
                fsWifiDot11radioIfConfigEdcaRadioViCwmax
                    Integer32,
                fsWifiDot11radioIfConfigEdcaRadioViTxop
                    Integer32, 
                fsWifiDot11radioIfConfigEdcaRadioVoAifsn
                    Integer32,
                fsWifiDot11radioIfConfigEdcaRadioVoCwmin 
                    Integer32,
                fsWifiDot11radioIfConfigEdcaRadioVoCwmax
                    Integer32,
                fsWifiDot11radioIfConfigEdcaRadioVoTxop
                    Integer32,
                fsWifiDot11radioIfConfigAntennaTransChainmask
                    Integer32,
                fsWifiDot11radioIfConfigAntennaReceiveChainmask
                    Integer32,   
                fsWifiDot11radioIfConfigBeaconDtimPeriod
                    Integer32,
                fsWifiDot11radioIfConfigBeaconPeriod
                    Integer32, 
                fsWifiDot11radioIfConfigRetrieShortTime
                    Integer32, 
                fsWifiDot11radioIfConfigRetrieLongTime
                    Integer32, 
                fsWifiDot11radioIfConfigStaIdleTimeout
                    Integer32,
                fsWifiDot11radioIfConfigWlanIdList
                    BITS
                }                             
                             
       fsWifiDot11radioIfConfigIfIndex OBJECT-TYPE
            SYNTAX Integer32
            MAX-ACCESS read-only
            STATUS current
            DESCRIPTION
                "The Dot11radio interface index ."
            ::= { fsWifiDot11radioIfConfigEntry 1 }
            
       fsWifiDot11radioIfConfigRowStatus OBJECT-TYPE
            SYNTAX RowStatus
            MAX-ACCESS read-write
            STATUS current
            DESCRIPTION
                "create/modify/delete ."
            ::= { fsWifiDot11radioIfConfigEntry 2 }           
                         
       fsWifiDot11radioIfConfigFreBand OBJECT-TYPE
            SYNTAX FSWifiFreChanelType
            MAX-ACCESS read-write
            STATUS current
            DESCRIPTION
                "The Dot11radio frequency band  ."
            ::= { fsWifiDot11radioIfConfigEntry 3 }   
        
        fsWifiDot11radioIfConfigChannel OBJECT-TYPE
            SYNTAX Integer32
            MAX-ACCESS read-write
            STATUS current
            DESCRIPTION
                "The Dot11radio work Chanel num."
            ::= { fsWifiDot11radioIfConfigEntry 4 } 
            
        fsWifiDot11radioIfConfigChanWidth OBJECT-TYPE
            SYNTAX FSWifiChanWidthType
            MAX-ACCESS read-write
            STATUS current
            DESCRIPTION
                "The Dot11radio Chanel width ."
            ::= { fsWifiDot11radioIfConfigEntry 5 }   
            
        fsWifiDot11radioIfConfigCountryCode OBJECT-TYPE
            SYNTAX DisplayString
            MAX-ACCESS read-write
            STATUS current
            DESCRIPTION
                "The Dot11radio country code."
            ::= { fsWifiDot11radioIfConfigEntry 6 } 
        
         fsWifiDot11radioIfConfigPowerLocal OBJECT-TYPE
            SYNTAX Integer32(1..100)
            MAX-ACCESS read-write
            STATUS current
            DESCRIPTION
                "The Dot11radio power local percent."
            ::= { fsWifiDot11radioIfConfigEntry 7 }
                            
        fsWifiDot11radioIfConfigWirelessProSupport OBJECT-TYPE
             SYNTAX BITS {
               null(0),
               b(1),
               g(2),
               n(3)
            }

            MAX-ACCESS read-write
            STATUS current
            DESCRIPTION
                "The Dot11radio Support wireless protocol ."
            ::= { fsWifiDot11radioIfConfigEntry 8 } 
                           
        fsWifiDot11radioIfConfigStaLimit OBJECT-TYPE
            SYNTAX Integer32(1..60)
            MAX-ACCESS read-write
            STATUS current
            DESCRIPTION
                "The Dot11radio Sta Limit ."
            ::= { fsWifiDot11radioIfConfigEntry 9 }
                    
        fsWifiDot11radioIfConfig20ShortGiEnable OBJECT-TYPE
            SYNTAX FSEableType
            MAX-ACCESS read-write
            STATUS current
            DESCRIPTION
                "The Dot11radio 20ShortGi enable."
            ::= { fsWifiDot11radioIfConfigEntry 10 }
        
        fsWifiDot11radioIfConfig40ShortGiEnable OBJECT-TYPE
            SYNTAX FSEableType
            MAX-ACCESS read-write
            STATUS current
            DESCRIPTION
                "The Dot11radio 40ShortGi enable ."
            ::= { fsWifiDot11radioIfConfigEntry 11 }

                    
        fsWifiDot11radioIfConfigShortPreambleEnable OBJECT-TYPE
            SYNTAX FSEableType
            MAX-ACCESS read-write
            STATUS current
            DESCRIPTION
                "The Dot11radio ShortPreamble enable ."
            ::= { fsWifiDot11radioIfConfigEntry 12 } 
        
        fsWifiDot11radioIfConfigSlottime OBJECT-TYPE
            SYNTAX FSWifiSlotType
            MAX-ACCESS read-write
            STATUS current
            DESCRIPTION
                "The Dot11radio slot time ."
            ::= { fsWifiDot11radioIfConfigEntry 13 } 
    
        fsWifiDot11radioIfConfigRtsThreshold OBJECT-TYPE
            SYNTAX Integer32(257..2347)
            MAX-ACCESS read-write
            STATUS current
            DESCRIPTION
                "The Dot11radio rts thresholx ."
            ::= { fsWifiDot11radioIfConfigEntry 14 }
        
        fsWifiDot11radioIfConfigFragmentThreshold OBJECT-TYPE
            SYNTAX Integer32(256..2346)
            MAX-ACCESS read-write
            STATUS current
            DESCRIPTION
                "The Dot11radio fragment threshold ."
            ::= { fsWifiDot11radioIfConfigEntry 15 }
        
        fsWifiDot11radioIfConfigResponseRssi OBJECT-TYPE
            SYNTAX Integer32(0..100)
            MAX-ACCESS read-write
            STATUS current
            DESCRIPTION
                "The Dot11radio response rss ."
            ::= { fsWifiDot11radioIfConfigEntry 16 }
            
        fsWifiDot11radioIfConfigEnableQos OBJECT-TYPE
            SYNTAX FSEableType
            MAX-ACCESS read-write
            STATUS current
            DESCRIPTION
                "The Dot11radio qos enable or disable ."
            ::= { fsWifiDot11radioIfConfigEntry 17 }
            
        fsWifiDot11radioIfConfigEdcaClientBgAifsn OBJECT-TYPE
            SYNTAX Integer32(1..15) 
            MAX-ACCESS read-write
            STATUS current
            DESCRIPTION
                "The Dot11radio edca client back-groud aifsn value."
            ::= { fsWifiDot11radioIfConfigEntry 18 } 
        
        fsWifiDot11radioIfConfigEdcaClientBgCwmin OBJECT-TYPE
            SYNTAX Integer32(1..15) 
            MAX-ACCESS read-write
            STATUS current
            DESCRIPTION
                "The Dot11radio edca client back-groud cwmin value."
            ::= { fsWifiDot11radioIfConfigEntry 19 }
        
        fsWifiDot11radioIfConfigEdcaClientBgCwmax OBJECT-TYPE
            SYNTAX Integer32(1..15) 
            MAX-ACCESS read-write
            STATUS current
            DESCRIPTION
                "The Dot11radio edca client back-groud cwmax value."
            ::= { fsWifiDot11radioIfConfigEntry 20 }
        
        fsWifiDot11radioIfConfigEdcaClientBgTxop OBJECT-TYPE
            SYNTAX Integer32(0..255) 
            MAX-ACCESS read-write
            STATUS current
            DESCRIPTION
                "The Dot11radio edca client back-groud txop value."
            ::= { fsWifiDot11radioIfConfigEntry 21 } 
            
        fsWifiDot11radioIfConfigEdcaClientBeAifsn OBJECT-TYPE
            SYNTAX Integer32(1..15) 
            MAX-ACCESS read-write
            STATUS current
            DESCRIPTION
                "The Dot11radio edca client best-effort aifsn value."
            ::= { fsWifiDot11radioIfConfigEntry 22 } 
        
        fsWifiDot11radioIfConfigEdcaClientBeCwmin OBJECT-TYPE
            SYNTAX Integer32(1..15) 
            MAX-ACCESS read-write
            STATUS current
            DESCRIPTION
                "The Dot11radio edca client best-effort cwmin value."
            ::= { fsWifiDot11radioIfConfigEntry 23 }
        
        fsWifiDot11radioIfConfigEdcaClientBeCwmax OBJECT-TYPE
            SYNTAX Integer32(1..15) 
            MAX-ACCESS read-write
            STATUS current
            DESCRIPTION
                "The Dot11radio edca client best-effort cwmax value."
            ::= { fsWifiDot11radioIfConfigEntry 24 }
        
        fsWifiDot11radioIfConfigEdcaClientBeTxop OBJECT-TYPE
            SYNTAX Integer32(0..255) 
            MAX-ACCESS read-write
            STATUS current
            DESCRIPTION
                "The Dot11radio edca client best-effort txop value."
            ::= { fsWifiDot11radioIfConfigEntry 25 }   
        
        fsWifiDot11radioIfConfigEdcaClientViAifsn OBJECT-TYPE
            SYNTAX Integer32(1..15) 
            MAX-ACCESS read-write
            STATUS current
            DESCRIPTION
                "The Dot11radio edca client video aifsn value."
            ::= { fsWifiDot11radioIfConfigEntry 26 } 
        
        fsWifiDot11radioIfConfigEdcaClientViCwmin OBJECT-TYPE
            SYNTAX Integer32(1..15) 
            MAX-ACCESS read-write
            STATUS current
            DESCRIPTION
                "The Dot11radio edca client video cwmin value."
            ::= { fsWifiDot11radioIfConfigEntry 27 }
        
        fsWifiDot11radioIfConfigEdcaClientViCwmax OBJECT-TYPE
            SYNTAX Integer32(1..15) 
            MAX-ACCESS read-write
            STATUS current
            DESCRIPTION
                "The Dot11radio edca client video cwmax value."
            ::= { fsWifiDot11radioIfConfigEntry 28 }
        
        fsWifiDot11radioIfConfigEdcaClientViTxop OBJECT-TYPE
            SYNTAX Integer32(0..255) 
            MAX-ACCESS read-write
            STATUS current
            DESCRIPTION
                "The Dot11radio edca client video txop value."
            ::= { fsWifiDot11radioIfConfigEntry 29 }

        fsWifiDot11radioIfConfigEdcaClientVoAifsn OBJECT-TYPE
            SYNTAX Integer32(1..15) 
            MAX-ACCESS read-write
            STATUS current
            DESCRIPTION
                "The Dot11radio edca client voice aifsn value."
            ::= { fsWifiDot11radioIfConfigEntry 30 } 
        
        fsWifiDot11radioIfConfigEdcaClientVoCwmin OBJECT-TYPE
            SYNTAX Integer32(1..15) 
            MAX-ACCESS read-write
            STATUS current
            DESCRIPTION
                "The Dot11radio edca client voice cwmin value."
            ::= { fsWifiDot11radioIfConfigEntry 31 }
        
        fsWifiDot11radioIfConfigEdcaClientVoCwmax OBJECT-TYPE
            SYNTAX Integer32(1..15) 
            MAX-ACCESS read-write
            STATUS current
            DESCRIPTION
                "The Dot11radio edca client voice cwmax value."
            ::= { fsWifiDot11radioIfConfigEntry 32 }
        
        fsWifiDot11radioIfConfigEdcaClientVoTxop OBJECT-TYPE
            SYNTAX Integer32(0..255) 
            MAX-ACCESS read-write
            STATUS current
            DESCRIPTION
                "The Dot11radio edca client voice txop value."
            ::= { fsWifiDot11radioIfConfigEntry 33 }
        
        fsWifiDot11radioIfConfigEdcaRadioBgAifsn OBJECT-TYPE
            SYNTAX Integer32(1..15) 
            MAX-ACCESS read-write
            STATUS current
            DESCRIPTION
                "The Dot11radio edca Radio back-groud aifsn value."
            ::= { fsWifiDot11radioIfConfigEntry 34 } 
        
        fsWifiDot11radioIfConfigEdcaRadioBgCwmin OBJECT-TYPE
            SYNTAX Integer32(1..15) 
            MAX-ACCESS read-write
            STATUS current
            DESCRIPTION
                "The Dot11radio edca Radio back-groud cwmin value."
            ::= { fsWifiDot11radioIfConfigEntry 35 }
        
        fsWifiDot11radioIfConfigEdcaRadioBgCwmax OBJECT-TYPE
            SYNTAX Integer32(1..15) 
            MAX-ACCESS read-write
            STATUS current
            DESCRIPTION
                "The Dot11radio edca Radio back-groud cwmax value."
            ::= { fsWifiDot11radioIfConfigEntry 36 }
        
        fsWifiDot11radioIfConfigEdcaRadioBgTxop OBJECT-TYPE
            SYNTAX Integer32(0..255) 
            MAX-ACCESS read-write
            STATUS current
            DESCRIPTION
                "The Dot11radio edca Radio back-groud txop value."
            ::= { fsWifiDot11radioIfConfigEntry 37 } 
            
        fsWifiDot11radioIfConfigEdcaRadioBeAifsn OBJECT-TYPE
            SYNTAX Integer32(1..15) 
            MAX-ACCESS read-write
            STATUS current
            DESCRIPTION
                "The Dot11radio edca Radio best-effort aifsn value."
            ::= { fsWifiDot11radioIfConfigEntry 38 } 
        
        fsWifiDot11radioIfConfigEdcaRadioBeCwmin OBJECT-TYPE
            SYNTAX Integer32(1..15) 
            MAX-ACCESS read-write
            STATUS current
            DESCRIPTION
                "The Dot11radio edca Radio best-effort cwmin value."
            ::= { fsWifiDot11radioIfConfigEntry 39 }
        
        fsWifiDot11radioIfConfigEdcaRadioBeCwmax OBJECT-TYPE
            SYNTAX Integer32(1..15) 
            MAX-ACCESS read-write
            STATUS current
            DESCRIPTION
                "The Dot11radio edca Radio best-effort cwmax value."
            ::= { fsWifiDot11radioIfConfigEntry 40 }
        
        fsWifiDot11radioIfConfigEdcaRadioBeTxop OBJECT-TYPE
            SYNTAX Integer32(0..255) 
            MAX-ACCESS read-write
            STATUS current
            DESCRIPTION
                "The Dot11radio edca Radio best-effort txop value."
            ::= { fsWifiDot11radioIfConfigEntry 41 }   
        
        fsWifiDot11radioIfConfigEdcaRadioViAifsn OBJECT-TYPE
            SYNTAX Integer32(1..15) 
            MAX-ACCESS read-write
            STATUS current
            DESCRIPTION
                "The Dot11radio edca Radio video aifsn value."
            ::= { fsWifiDot11radioIfConfigEntry 42 } 
        
        fsWifiDot11radioIfConfigEdcaRadioViCwmin OBJECT-TYPE
            SYNTAX Integer32(1..15) 
            MAX-ACCESS read-write
            STATUS current
            DESCRIPTION
                "The Dot11radio edca Radio video cwmin value."
            ::= { fsWifiDot11radioIfConfigEntry 43 }
        
        fsWifiDot11radioIfConfigEdcaRadioViCwmax OBJECT-TYPE
            SYNTAX Integer32(1..15) 
            MAX-ACCESS read-write
            STATUS current
            DESCRIPTION
                "The Dot11radio edca Radio video cwmax value."
            ::= { fsWifiDot11radioIfConfigEntry 44 }
        
        fsWifiDot11radioIfConfigEdcaRadioViTxop OBJECT-TYPE
            SYNTAX Integer32(0..255) 
            MAX-ACCESS read-write
            STATUS current
            DESCRIPTION
                "The Dot11radio edca Radio video txop value."
            ::= { fsWifiDot11radioIfConfigEntry 45 }

        fsWifiDot11radioIfConfigEdcaRadioVoAifsn OBJECT-TYPE
            SYNTAX Integer32(1..15) 
            MAX-ACCESS read-write
            STATUS current
            DESCRIPTION
                "The Dot11radio edca Radio voice aifsn value."
            ::= { fsWifiDot11radioIfConfigEntry 46 } 
        
        fsWifiDot11radioIfConfigEdcaRadioVoCwmin OBJECT-TYPE
            SYNTAX Integer32(1..15) 
            MAX-ACCESS read-write
            STATUS current
            DESCRIPTION
                "The Dot11radio edca Radio voice cwmin value."
            ::= { fsWifiDot11radioIfConfigEntry 47 }
        
        fsWifiDot11radioIfConfigEdcaRadioVoCwmax OBJECT-TYPE
            SYNTAX Integer32(1..15) 
            MAX-ACCESS read-write
            STATUS current
            DESCRIPTION
                "The Dot11radio edca Radio voice cwmax value."
            ::= { fsWifiDot11radioIfConfigEntry 48 }
        
        fsWifiDot11radioIfConfigEdcaRadioVoTxop OBJECT-TYPE
            SYNTAX Integer32(0..255) 
            MAX-ACCESS read-write
            STATUS current
            DESCRIPTION
                "The Dot11radio edca Radio voice txop value."
            ::= { fsWifiDot11radioIfConfigEntry 49 }
       
        fsWifiDot11radioIfConfigAntennaTransChainmask  OBJECT-TYPE
            SYNTAX Integer32(1..3) 
            MAX-ACCESS read-write
            STATUS current
            DESCRIPTION
                "The Dot11radio antenna transmit chainmask."
            ::= { fsWifiDot11radioIfConfigEntry 50 }
            
        fsWifiDot11radioIfConfigAntennaReceiveChainmask  OBJECT-TYPE
            SYNTAX Integer32(1..3) 
            MAX-ACCESS read-write
            STATUS current
            DESCRIPTION
                "The Dot11radio antenna receive chainmask."
            ::= { fsWifiDot11radioIfConfigEntry 51 }
                       
        fsWifiDot11radioIfConfigBeaconDtimPeriod  OBJECT-TYPE
            SYNTAX Integer32(1..255) 
            MAX-ACCESS read-write
            STATUS current
            DESCRIPTION
                "The Dot11radio beacon dtim period ."
            ::= { fsWifiDot11radioIfConfigEntry 52 }
                  
        fsWifiDot11radioIfConfigBeaconPeriod  OBJECT-TYPE
            SYNTAX Integer32(200..1000) 
            MAX-ACCESS read-write
            STATUS current
            DESCRIPTION
                "The Dot11radio beacon period."
            ::= { fsWifiDot11radioIfConfigEntry 53 }
                    
         fsWifiDot11radioIfConfigRetrieShortTime  OBJECT-TYPE
            SYNTAX Integer32(1..7) 
            MAX-ACCESS read-write
            STATUS current
            DESCRIPTION
                "The Dot11radio short frame retrie times."
            ::= { fsWifiDot11radioIfConfigEntry 54 }
                     
         fsWifiDot11radioIfConfigRetrieLongTime  OBJECT-TYPE
            SYNTAX Integer32(1..4) 
            MAX-ACCESS read-write
            STATUS current
            DESCRIPTION
                "The Dot11radio long frame retrie times."
            ::= { fsWifiDot11radioIfConfigEntry 55 }
                    
          fsWifiDot11radioIfConfigStaIdleTimeout  OBJECT-TYPE
            SYNTAX Integer32(60..86400) 
            MAX-ACCESS read-write
            STATUS current
            DESCRIPTION
                "The Dot11radio Station idle timeout"
            ::= { fsWifiDot11radioIfConfigEntry 56 }
                   
          fsWifiDot11radioIfConfigWlanIdList  OBJECT-TYPE
            SYNTAX BITS {
               w0(0), 
               w1(1),
               w2(2),
               w3(3),
               w4(4),
               w5(5),
               w6(6),
               w7(7),
               w8(8),
               w9(9),
               w10(10),
               w11(11),
               w12(12), 
               w13(13),
               w14(14),
               w15(15)
            }
            MAX-ACCESS read-write
            STATUS current
            DESCRIPTION
                "The Dot11radio Station idle timeout"
            ::= { fsWifiDot11radioIfConfigEntry 57 }

             
-- End Dot11radio interface config objects                                                                
 
-- Start Dot11radio interface apply objects        
--        fsWifiDot11radioIfApplyTable OBJECT-TYPE
--            SYNTAX SEQUENCE OF FSWifiDot11radioIfApplyEntry
--            MAX-ACCESS not-accessible
--            STATUS current
--            DESCRIPTION
--                "A table of wifi Dot11radio interface wlan Apply."
--            ::= { fsWifiDot11radioIfApplyObjects 1 } 
--            
--         fsWifiDot11radioIfApplyEntry OBJECT-TYPE
--            SYNTAX FSWifiDot11radioIfApplyEntry
--            MAX-ACCESS not-accessible
--            STATUS current
--            DESCRIPTION
--                "wifi Dot11radio interface Apply entry."
--            INDEX { fsWifiDot11radioIfApplyIfIndex }
--            ::= { fsWifiDot11radioIfApplyTable 1 }    
--            
--         
--        FSWifiDot11radioIfApplyEntry ::=
--            SEQUENCE { 
--            	fsWifiDot11radioIfApplyIfIndex
--            		Integer32,  
--                fsWifiDot11radioIfApplyRowStatus           
--                    RowStatus,  
--                fsWifiDot11radioIfApplyVlanId
--                    Integer32,  
--                fsWifiDot11radioIfApplyIpAddress
--                    IpAddress,
--                fsWifiDot11radioIfApplyMaskAddress
--                    IpAddress, 
--                fsWifiDot11radioIfApplyStaDhcpEnable
--                    FSEableType,
--                fsWifiDot11radioIfApplyStaNatEnable
--                    FSEableType
--                }                                              
--                   
--         fsWifiDot11radioIfApplyIfIndex OBJECT-TYPE
--            SYNTAX Integer32
--            MAX-ACCESS not-accessible
--            STATUS current
--            DESCRIPTION
--                "The Dot11radio interface Apply index ."
--            ::= { fsWifiDot11radioIfApplyEntry 1 } 
--            
--         fsWifiDot11radioIfApplyRowStatus OBJECT-TYPE
--            SYNTAX RowStatus
--            MAX-ACCESS read-write
--            STATUS current
--            DESCRIPTION
--                "The Dot11radio interface Apply/delete."
--            ::= { fsWifiDot11radioIfApplyEntry 2 }
--               
--         fsWifiDot11radioIfApplyVlanId OBJECT-TYPE
--            SYNTAX Integer32
--            MAX-ACCESS read-write
--            STATUS current
--            DESCRIPTION
--                "The Dot11radio interface Apply vlan id."
--            ::= { fsWifiDot11radioIfApplyEntry 3 }  
--                   
--         fsWifiDot11radioIfApplyIpAddress OBJECT-TYPE
--            SYNTAX IpAddress
--            MAX-ACCESS read-write
--            STATUS current
--            DESCRIPTION
--                "The Dot11radio interface Apply station ip address ."
--            ::= { fsWifiDot11radioIfApplyEntry 4 } 
--                                
--         fsWifiDot11radioIfApplyMaskAddress OBJECT-TYPE
--            SYNTAX IpAddress
--            MAX-ACCESS read-write
--            STATUS current
--            DESCRIPTION
--                "The Dot11radio interface Apply station ip address mask ."
--            ::= { fsWifiDot11radioIfApplyEntry 5 }
--            
--         fsWifiDot11radioIfApplyStaDhcpEnable OBJECT-TYPE
--            SYNTAX FSEableType
--            MAX-ACCESS read-write
--            STATUS current
--            DESCRIPTION
--                "The Dot11radio interface Apply station dhcp enable ."
--            ::= { fsWifiDot11radioIfApplyEntry 6 }
--         
--         fsWifiDot11radioIfApplyStaNatEnable OBJECT-TYPE
--            SYNTAX FSEableType
--            MAX-ACCESS read-write
--            STATUS current
--            DESCRIPTION
--                "The Dot11radio interface Apply station nat enable ."
--            ::= { fsWifiDot11radioIfApplyEntry 7 }    
-- End Dot11radio interface apply objects 

-- Start Wlan associate objects            
         fsWifiWlanAssociateTable OBJECT-TYPE
            SYNTAX SEQUENCE OF FSWifiWlanAssociateEntry
            MAX-ACCESS not-accessible
            STATUS current
            DESCRIPTION
                "A table of wifi wlan associate infromation."
            ::= { fsWifiWlanAssociateObjects 1 }    
            
          fsWifiWlanAssociateEntry OBJECT-TYPE
            SYNTAX FSWifiWlanAssociateEntry
            MAX-ACCESS not-accessible
            STATUS current
            DESCRIPTION
                "wifi wlan associate infromation entry."
            INDEX {fsWifiWlanAssociateWlanId ,fsWifiWlanAssociateStaMacAdress}
            ::= { fsWifiWlanAssociateTable 1 } 
                      
          FSWifiWlanAssociateEntry ::=
            SEQUENCE { 
            	fsWifiWlanAssociateWlanId
            	    Integer32, 
                fsWifiWlanAssociateStaMacAdress
                    DisplayString, 
                fsWifiWlanAssociateSsidName
                    DisplayString,      
                fsWifiWlanAssociateStaIpAdress
                    IpAddress,
                fsWifiWlanAssociateStaMaskAdress
                    IpAddress,
                fsWifiWlanAssociateStaSigalStrength
                    Integer32,
                fsWifiWlanAssociateStaConnectTime
                    DisplayString,
                fsWifiWlanAssociateStaConnectTimeLength
                    DisplayString,
                fsWifiWlanAssociateStaGate
                    IpAddress,  
                fsWifiWlanAssociateStaDns
                    IpAddress
                }   
        
        fsWifiWlanAssociateWlanId OBJECT-TYPE
            SYNTAX Integer32
            MAX-ACCESS read-only
            STATUS current
            DESCRIPTION
                "The Dot11radio wlan id ."
            ::= { fsWifiWlanAssociateEntry 1 }  
            
        fsWifiWlanAssociateStaMacAdress OBJECT-TYPE
            SYNTAX DisplayString
            MAX-ACCESS read-only
            STATUS current
            DESCRIPTION
                "The Dot11radio mac address ."
            ::= { fsWifiWlanAssociateEntry 2 } 
            
        fsWifiWlanAssociateSsidName OBJECT-TYPE
            SYNTAX DisplayString
            MAX-ACCESS read-only
            STATUS current
            DESCRIPTION
                "The Dot11radio ssid name ."
            ::= { fsWifiWlanAssociateEntry 3 }
            
        fsWifiWlanAssociateStaIpAdress OBJECT-TYPE
            SYNTAX IpAddress
            MAX-ACCESS read-only
            STATUS current
            DESCRIPTION
                "The Dot11radio associate station ip ."
            ::= { fsWifiWlanAssociateEntry 4 } 
        
        fsWifiWlanAssociateStaMaskAdress OBJECT-TYPE
            SYNTAX IpAddress
            MAX-ACCESS read-only
            STATUS current
            DESCRIPTION
                "The Dot11radio associate station mask address."
            ::= { fsWifiWlanAssociateEntry 5 }
    
        fsWifiWlanAssociateStaSigalStrength OBJECT-TYPE
            SYNTAX Integer32
            MAX-ACCESS read-only
            STATUS current
            DESCRIPTION
                "The Dot11radio associate signal strength ."
            ::= { fsWifiWlanAssociateEntry 6 }  
            
        fsWifiWlanAssociateStaConnectTime OBJECT-TYPE
            SYNTAX DisplayString
            MAX-ACCESS read-only
            STATUS current
            DESCRIPTION
                "The Dot11radio associate station time ."
            ::= { fsWifiWlanAssociateEntry 7 } 
        
        fsWifiWlanAssociateStaConnectTimeLength OBJECT-TYPE
            SYNTAX DisplayString
            MAX-ACCESS read-only
            STATUS current
            DESCRIPTION
                "The Dot11radio associate station time length ."
            ::= { fsWifiWlanAssociateEntry 8 }  
                    
        fsWifiWlanAssociateStaGate OBJECT-TYPE
            SYNTAX IpAddress
            MAX-ACCESS read-only
            STATUS current
            DESCRIPTION
                "The Dot11radio associate station gate address ."
            ::= { fsWifiWlanAssociateEntry 9 } 
            
        fsWifiWlanAssociateStaDns OBJECT-TYPE
            SYNTAX IpAddress
            MAX-ACCESS read-only
            STATUS current
            DESCRIPTION
                "The Dot11radio associate station dns address ."
            ::= { fsWifiWlanAssociateEntry 10 }       

-- End Wlan associate objects         
END
-- End module

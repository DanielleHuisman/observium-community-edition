-- *****************************************************************
-- FS-SMI.mib: The MIB is designed to get SMM(short message management) statistic information of 3G router .
--
-- March 2002, Wuzg
-- 
-- Copyright (c) 2002 by FS.COM Inc..
-- All rights reserved.
-- 
-- *****************************************************************
--

FS-SMM-MIB DEFINITIONS ::= BEGIN
    IMPORTS
        MODULE-IDENTITY,
        NOTIFICATION-TYPE,
        OBJECT-TYPE,
        IpAddress,
        Integer32,
        Counter32,
        Counter64,
        Gauge32,
        Unsigned32
            FROM SNMPv2-SMI
        MODULE-COMPLIANCE,
        OBJECT-GROUP,
        NOTIFICATION-GROUP
            FROM SNMPv2-CONF
        DisplayString,
        TEXTUAL-CONVENTION,
        TimeStamp
            FROM SNMPv2-TC
        fsMgmt
            FROM FS-SMI;

    fsSmmMIB MODULE-IDENTITY
        LAST-UPDATED "201212100000Z"            
        ORGANIZATION
            "FS.COM Inc.."
        CONTACT-INFO
            "Tel: 400-865-2852 
             E-mail: https://www.fs.com/live_chat_service_mail.html"  
        DESCRIPTION
            "The MIB is designed to get SMM statistic information of 3G router.
            With this MIB, we can get information of a certain 3G user or all users."
        REVISION      "201212100000Z"
        DESCRIPTION
                "Initial version of this MIB module."
        ::= { fsMgmt 120 }       

    fsSmmObjects OBJECT IDENTIFIER ::= { fsSmmMIB 1 }
    fsSmmTrapObjects OBJECT IDENTIFIER ::= { fsSmmMIB 2 }
    fsSmmTraps OBJECT IDENTIFIER ::= { fsSmmMIB 3 }
  
-- ===============================================
-- Begin the scalar parameters
-- =============================================== 
    fsReportSimBillSwitch OBJECT-TYPE
        SYNTAX Unsigned32
        MAX-ACCESS read-write
        STATUS current
        DESCRIPTION
            "The switch of reporting sim bill."
        ::= { fsSmmObjects 1 }
    
    fsQuerySimBillCmd OBJECT-TYPE
        SYNTAX OCTET STRING (SIZE (0..256))
        MAX-ACCESS read-write
        STATUS current
        DESCRIPTION
            "The cmd of query sim bill"
        ::= { fsSmmObjects 2 }
			
-- ===============================================
-- Begin the table of fsSmsUseTable.
-- ===============================================
    fsSmsUseTable OBJECT-TYPE
        SYNTAX SEQUENCE OF FSSmsUseEntry
        MAX-ACCESS not-accessible
        STATUS current
        DESCRIPTION
            "The statistic information of sms."
        ::= { fsSmmObjects 3 }
    
    fsSmsUseEntry OBJECT-TYPE
        SYNTAX FSSmsUseEntry
        MAX-ACCESS not-accessible
        STATUS current
        DESCRIPTION
            "The statistic information of sms."
        INDEX { fsSimImsi }
        ::= { fsSmsUseTable 1 }
    
    FSSmsUseEntry ::=
        SEQUENCE {
            fsSimImsi
                DisplayString,
            fsSmsUseCnt
           	    Unsigned32
        }
   
    fsSimImsi OBJECT-TYPE
        SYNTAX DisplayString (SIZE (0..20))
        MAX-ACCESS read-only
        STATUS current
        DESCRIPTION
            "The imsi of sim card."
        ::= { fsSmsUseEntry 1 } 
    
    fsSmsUseCnt OBJECT-TYPE
        SYNTAX Unsigned32
        MAX-ACCESS read-only
        STATUS current
        DESCRIPTION
            "The sms count of using"
        ::= { fsSmsUseEntry 2 }  
		
-- ===============================================
-- Begin the trap bindvar.
-- ===============================================
    fsSimBillTrapObjects OBJECT IDENTIFIER ::= { fsSmmTrapObjects 1 }
    fsQuerySimBillContent OBJECT-TYPE
        SYNTAX OCTET STRING (SIZE (0..1024))
        MAX-ACCESS accessible-for-notify
        STATUS current
        DESCRIPTION
            "The sim bill content of query "
        ::= { fsSimBillTrapObjects 1 }
 
    fsReportSimBillContent OBJECT-TYPE
        SYNTAX OCTET STRING (SIZE (0..1024))
        MAX-ACCESS accessible-for-notify
        STATUS current
        DESCRIPTION
            "The sim bill content of report "
        ::= { fsSimBillTrapObjects 2 }


-- ===============================================
-- Begin the fsSimBillTrap.
-- =============================================== 
	fsSimBillNotifications OBJECT IDENTIFIER ::= { fsSmmTraps 1 } 
    fsQuerySimBill NOTIFICATION-TYPE
        OBJECTS { fsQuerySimBillContent }
        STATUS current
        DESCRIPTION
            "This notification is sim bill content of query."
        ::= { fsSimBillNotifications 1 }

    fsReportSimBill NOTIFICATION-TYPE
        OBJECTS { fsReportSimBillContent }
        STATUS current
        DESCRIPTION
            "This notification is sim bill content of report."
        ::= { fsSimBillNotifications 2 }     
       

    
END

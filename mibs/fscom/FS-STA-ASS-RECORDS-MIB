-- *******************************************************************
-- FS-STA-ASS-RECORDS-MIB.mib : FS STA ASSIATION RECORDS MIB 
-- 
-- JUNE 2011, chenfg1
--
-- Copyright (c) 2011 by FS.COM Inc..
-- All rights reserved.
-- *******************************************************************
--
FS-STA-ASS-RECORDS-MIB DEFINITIONS ::= BEGIN

IMPORTS 
        MODULE-IDENTITY, 
        OBJECT-TYPE,
		Integer32,
	    NOTIFICATION-TYPE,	
        Unsigned32,
        IpAddress
                FROM SNMPv2-SMI
        OBJECT-GROUP,
        MODULE-COMPLIANCE
                FROM SNMPv2-CONF
        TruthValue,
        RowStatus,
        DisplayString,
        MacAddress,
        DateAndTime
                FROM SNMPv2-TC 
        fsMgmt
                FROM FS-SMI
        fsIfIndex 
                FROM FS-INTERFACE-MIB;

--********************************************************************
--*  MODULE IDENTITY
--********************************************************************

fsStaAssRecordsMIB    MODULE-IDENTITY
       LAST-UPDATED       "201111100000Z"
       ORGANIZATION       "FS.COM Inc.."
       CONTACT-INFO  
                " 
                Tel: 400-865-2852 

                E-mail: https://www.fs.com/live_chat_service_mail.html"

        DESCRIPTION             
                "This MIB is intended to get the sta assoiation records"
        
        REVISION      "200911100000Z"
        DESCRIPTION
                "Initial version of this MIB module. "
        ::= { fsMgmt 101 }

fsStaAssRecordsMIBTrap    OBJECT IDENTIFIER 
    ::= { fsStaAssRecordsMIB 0 }

fsStaAssRecordsMIBObjects OBJECT IDENTIFIER 
    ::= { fsStaAssRecordsMIB 1 }

fsStaAssRecordsGrobal OBJECT IDENTIFIER
	::= { fsStaAssRecordsMIBObjects 1 }

fsStaAssRecordsByMAC OBJECT IDENTIFIER
	::= { fsStaAssRecordsMIBObjects 2 }

fsStaAssRecordsByTime OBJECT IDENTIFIER
	::= { fsStaAssRecordsMIBObjects 3 }

fsStaAssRecordsByAP OBJECT IDENTIFIER
	::= { fsStaAssRecordsMIBObjects 4 }
	
fsStaAssSignalByMAC OBJECT IDENTIFIER
	::= { fsStaAssRecordsMIBObjects 5 }

fsStaAssRetryByMAC OBJECT IDENTIFIER
	::= { fsStaAssRecordsMIBObjects 6 }	

fsStaAssStatistic OBJECT IDENTIFIER
	::= { fsStaAssRecordsMIBObjects 7 }		
	
--*******************************************************************
--fsStaAssRecordsTable:  get sta association grobal static by mac
--*******************************************************************
    fsStaAssRecordsGrobalTable  OBJECT-TYPE
         SYNTAX      SEQUENCE OF FSStaAssRecordsGrobalEntry
         MAX-ACCESS  not-accessible
         STATUS      current
         DESCRIPTION
                     "A table listing the sta association process survey records,
                      can be search record by mac."
         ::= { fsStaAssRecordsGrobal 1 }
   
    fsStaAssRecordsGrobalEntry OBJECT-TYPE
         SYNTAX      FSStaAssRecordsGrobalEntry
         MAX-ACCESS  not-accessible
         STATUS      current
         DESCRIPTION
                     "Get sta association records by mac."
         INDEX       { fsStaMacGrobalAddress }
         ::= { fsStaAssRecordsGrobalTable  1 }

    FSStaAssRecordsGrobalEntry ::= SEQUENCE {             
             fsStaMacGrobalAddress        MacAddress,       
             fsStaMacGrobalAPName         DisplayString,    
             fsStaMacGrobalISUP           INTEGER,          
             fsStaMacGrobalStartime       DateAndTime,      
             fsStaMacGrobalupdowntimes    Unsigned32,       
             fsStaMacGrobalroamtimes      Unsigned32,      
	     fsStaMacGrobaltotaltimes     Unsigned32,
	     fsStaMacGrobalrealdowntimes  Unsigned32,
	     fsStaMacGrobalSSID           DisplayString
             }

    fsStaMacGrobalAddress OBJECT-TYPE
         SYNTAX      MacAddress
         MAX-ACCESS  not-accessible
         STATUS      current
         DESCRIPTION
                     "Sta Mac address."
         ::= { fsStaAssRecordsGrobalEntry 1 }

    fsStaMacGrobalAPName OBJECT-TYPE
         SYNTAX      DisplayString(SIZE(1..64))
         MAX-ACCESS  read-only
         STATUS      current
         DESCRIPTION
                     "ap name."
         ::= { fsStaAssRecordsGrobalEntry 2 }

    fsStaMacGrobalISUP OBJECT-TYPE
         SYNTAX      INTEGER {
                      up(0),
                      down(1)
                     }
         MAX-ACCESS  read-only
         STATUS      current
         DESCRIPTION
                     "Sta is active or not."
         ::= { fsStaAssRecordsGrobalEntry 3 }

    fsStaMacGrobalStartime OBJECT-TYPE
         SYNTAX      DateAndTime
         MAX-ACCESS  read-only
         STATUS      current
         DESCRIPTION
                     "Sta active time."
         ::= { fsStaAssRecordsGrobalEntry 4 }

    fsStaMacGrobalupdowntimes OBJECT-TYPE
         SYNTAX      Unsigned32
         MAX-ACCESS  read-only
         STATUS      current
         DESCRIPTION
                     "Sta up and down times."
         ::= { fsStaAssRecordsGrobalEntry 5 }

    fsStaMacGrobalroamtimes OBJECT-TYPE
         SYNTAX      Unsigned32
         MAX-ACCESS  read-only
         STATUS      current
         DESCRIPTION
                     "Sta roam times."
         ::= { fsStaAssRecordsGrobalEntry 6 }
		 
    fsStaMacGrobaltotaltimes OBJECT-TYPE
         SYNTAX      Unsigned32
         MAX-ACCESS  read-only
         STATUS      current
         DESCRIPTION
                     "Sta total times(join\leave\delete\roam)."
         ::= { fsStaAssRecordsGrobalEntry 7 }
		 
    fsStaMacGrobalrealdowntimes OBJECT-TYPE
         SYNTAX      Unsigned32
         MAX-ACCESS  read-only
         STATUS      current
         DESCRIPTION
                     "Sta real down times(sta join after leave within 5s)."
         ::= { fsStaAssRecordsGrobalEntry 8 }		 

    fsStaMacGrobalSSID OBJECT-TYPE
         SYNTAX      DisplayString(SIZE(1..64))
         MAX-ACCESS  read-only
         STATUS      current
         DESCRIPTION
                     "STA curent ssid."
         ::= { fsStaAssRecordsGrobalEntry 9 }
		 
--*******************************************************************
--fsStaAssRecordsByMACTable  :  get sta association records by mac
--*******************************************************************
    fsStaAssRecordsByMACTable  OBJECT-TYPE
         SYNTAX      SEQUENCE OF FSStaAssRecordsByMACEntry
         MAX-ACCESS  not-accessible
         STATUS      current
         DESCRIPTION
                     "A table listing the sta association process detail records,
                      can be search record by mac."
         ::= { fsStaAssRecordsByMAC 1 }
   
    fsStaAssRecordsByMACEntry OBJECT-TYPE
         SYNTAX      FSStaAssRecordsByMACEntry
         MAX-ACCESS  not-accessible
         STATUS      current
         DESCRIPTION
                     "Get sta association records by mac."
         INDEX       { fsStaMacAddress,
                       fsStaMacindex}
         ::= { fsStaAssRecordsByMACTable  1 }

    FSStaAssRecordsByMACEntry ::= SEQUENCE {        
             fsStaMacAddress      MacAddress,      
             fsStaMacindex        Unsigned32,     
             fsStaAsstime         DateAndTime,    
             fsStaAssAction       INTEGER,
             fsStaAssSubAction    INTEGER,			 
             fsStaAssResult       INTEGER,       
             fsStaAssReason       INTEGER,       
             fsStaAssApNamePre    DisplayString,   
             fsStaAssApNameNow    DisplayString,   
             fsStaAssSignalQua    INTEGER,        
             fsStaAssRoamtype     INTEGER,
             fsStaAssjitter       INTEGER,
             fsStaAssjointimes    Unsigned32,
             fsStaAsslatelytime   DateAndTime,
             fsStaAssSSID         DisplayString
             			 
             }
    fsStaMacAddress OBJECT-TYPE
         SYNTAX      MacAddress
         MAX-ACCESS  not-accessible
         STATUS      current
         DESCRIPTION
                     "Sta Mac address."
         ::= { fsStaAssRecordsByMACEntry 1 }

    fsStaMacindex OBJECT-TYPE
         SYNTAX      Unsigned32
         MAX-ACCESS  not-accessible
         STATUS      current
         DESCRIPTION
                     "the index of Sta mac."
         ::= { fsStaAssRecordsByMACEntry 2 }
		 
    fsStaAsstime OBJECT-TYPE
         SYNTAX      DateAndTime
         MAX-ACCESS  read-only
         STATUS      current
         DESCRIPTION
                     "Sta association time."
         ::= { fsStaAssRecordsByMACEntry 3 }
		 
    fsStaAssAction OBJECT-TYPE
         SYNTAX      INTEGER {
                      join(1),
                      leave(2),
                      roam(3),
                      delete(4)
                     }
         MAX-ACCESS  read-only
         STATUS      current
         DESCRIPTION
                     "Sta association action."
         ::= { fsStaAssRecordsByMACEntry 4 }		 
		 
    fsStaAssSubAction OBJECT-TYPE
         SYNTAX      INTEGER 
         MAX-ACCESS  read-only
         STATUS      current
         DESCRIPTION
                     "Sta association sub action."
         ::= { fsStaAssRecordsByMACEntry 5 }
		 
    fsStaAssResult OBJECT-TYPE
         SYNTAX      INTEGER {
                      success(0),
                      failed(1)
                     }
         MAX-ACCESS  read-only
         STATUS      current
         DESCRIPTION
                     "Sta association action resoult."
         ::= { fsStaAssRecordsByMACEntry 6 }

    fsStaAssReason OBJECT-TYPE
         SYNTAX      INTEGER
         MAX-ACCESS  read-only
         STATUS      current
         DESCRIPTION
                     "Sta association action reason."
         ::= { fsStaAssRecordsByMACEntry 7 }

    fsStaAssApNamePre OBJECT-TYPE
         SYNTAX      DisplayString(SIZE(1..64))
         MAX-ACCESS  read-only
         STATUS      current
         DESCRIPTION
                     "Sta preference ap-id."
         ::= { fsStaAssRecordsByMACEntry 8 }

    fsStaAssApNameNow OBJECT-TYPE
         SYNTAX      DisplayString(SIZE(1..64))
         MAX-ACCESS  read-only
         STATUS      current
         DESCRIPTION
                     "Sta now ap-id."
         ::= { fsStaAssRecordsByMACEntry 9 }

    fsStaAssSignalQua OBJECT-TYPE
         SYNTAX      INTEGER
         MAX-ACCESS  read-only
         STATUS      current
         DESCRIPTION
                     "Sta signal quality."
         ::= { fsStaAssRecordsByMACEntry 10 }
		 
    fsStaAssRoamtype OBJECT-TYPE
         SYNTAX      INTEGER
         MAX-ACCESS  read-only
         STATUS      current
         DESCRIPTION
                     "Sta roam type."
         ::= { fsStaAssRecordsByMACEntry 11 }		 

    fsStaAssjitter OBJECT-TYPE
         SYNTAX      INTEGER
         MAX-ACCESS  read-only
         STATUS      current
         DESCRIPTION
                     "Sta association action jitter or not."
         ::= { fsStaAssRecordsByMACEntry 12}
		 
    fsStaAssjointimes OBJECT-TYPE
         SYNTAX      Unsigned32
         MAX-ACCESS  read-only
         STATUS      current
         DESCRIPTION
                     "Sta association join times."
         ::= { fsStaAssRecordsByMACEntry 13 }

    fsStaAsslatelytime OBJECT-TYPE
         SYNTAX      DateAndTime
         MAX-ACCESS  read-only
         STATUS      current
         DESCRIPTION
                     "Sta association lately join time."
         ::= { fsStaAssRecordsByMACEntry 14 }

    fsStaAssSSID OBJECT-TYPE
         SYNTAX      DisplayString
         MAX-ACCESS  read-only
         STATUS      current
         DESCRIPTION
                     "Sta association ssid."
         ::= { fsStaAssRecordsByMACEntry 15 }		 
		 
		 
--*******************************************************************************
--fsStaAssRecordsSearchByTime  :  search sta association records macs by time
--*******************************************************************************
    fsStaAssRecordsSearchByTimeTable  OBJECT-TYPE
         SYNTAX      SEQUENCE OF FSStaAssRecordsSearchByTimeEntry
         MAX-ACCESS  not-accessible
         STATUS      current
         DESCRIPTION
                     "A table listing the sta association process detail records,
                      can be search record by the time of sta association."
         ::= { fsStaAssRecordsByTime 1 }
   
    fsStaAssRecordsSearchByTimeEntry OBJECT-TYPE
         SYNTAX      FSStaAssRecordsSearchByTimeEntry
         MAX-ACCESS  not-accessible
         STATUS      current
         DESCRIPTION
                     "Get sta association records by mac."
         INDEX       { fsStaUptimeLow, 
                       fsStaUptimeHigh,
                       fsStaDowntimeLow,
                       fsStaDowntimeHigh,
                       fsStaTimeindex }
         ::= { fsStaAssRecordsSearchByTimeTable  1 }


    FSStaAssRecordsSearchByTimeEntry ::= SEQUENCE {      
             fsStaUptimeLow        DateAndTime,           
             fsStaUptimeHigh       DateAndTime,           
             fsStaDowntimeLow      DateAndTime,          
             fsStaDowntimeHigh     DateAndTime,          
             fsStaTimeindex        Unsigned32,            
             fsStaTimeMac          MacAddress,           
             fsStaTimeAPName       DisplayString,      
             fsStaTimeISUP         INTEGER,            
             fsStaTimeStartime     DateAndTime,          
             fsStaTimeupdowntimes  Unsigned32,         
             fsStaTimeroamtimes    Unsigned32,           
             fsStaTimertotaltimes  Unsigned32,
             fsStaTimerjitter      INTEGER,
             fsStaTimerjointimes   Unsigned32,
             fsStaTimerlatelytime  DateAndTime,
             fsStaTimerSSID        DisplayString			 
             }

    fsStaUptimeLow OBJECT-TYPE
         SYNTAX      DateAndTime
         MAX-ACCESS  not-accessible
         STATUS      current
         DESCRIPTION
                     "the low time of Sta active time range."
         ::= { fsStaAssRecordsSearchByTimeEntry 1 }

    fsStaUptimeHigh OBJECT-TYPE
         SYNTAX      DateAndTime
         MAX-ACCESS  not-accessible
         STATUS      current
         DESCRIPTION
                     "the high time of Sta active time range."
         ::= { fsStaAssRecordsSearchByTimeEntry 2 }

    fsStaDowntimeLow OBJECT-TYPE
         SYNTAX      DateAndTime
         MAX-ACCESS  not-accessible
         STATUS      current
         DESCRIPTION
                     "the low time of Sta down time range."
         ::= { fsStaAssRecordsSearchByTimeEntry 3 }

    fsStaDowntimeHigh OBJECT-TYPE
         SYNTAX      DateAndTime
         MAX-ACCESS  not-accessible
         STATUS      current
         DESCRIPTION
                     "the high time of Sta down time range."
         ::= { fsStaAssRecordsSearchByTimeEntry 4 }

    fsStaTimeindex OBJECT-TYPE
         SYNTAX      Unsigned32
         MAX-ACCESS  not-accessible
         STATUS      current
         DESCRIPTION
                     "the index of Sta mac."
         ::= { fsStaAssRecordsSearchByTimeEntry 5 }

    fsStaTimeMac OBJECT-TYPE
         SYNTAX      MacAddress
         MAX-ACCESS  read-only
         STATUS      current
         DESCRIPTION
                     "Sta Mac address."
         ::= { fsStaAssRecordsSearchByTimeEntry 6 }

    fsStaTimeAPName OBJECT-TYPE
         SYNTAX      DisplayString(SIZE(1..64))
         MAX-ACCESS  read-only
         STATUS      current
         DESCRIPTION
                     "ap name."
         ::= { fsStaAssRecordsSearchByTimeEntry 7 }

    fsStaTimeISUP OBJECT-TYPE
         SYNTAX      INTEGER {
                      up(0),
                      down(1)
                     }
         MAX-ACCESS  read-only
         STATUS      current
         DESCRIPTION
                     "Sta is active or not."
         ::= { fsStaAssRecordsSearchByTimeEntry 8 }

    fsStaTimeStartime OBJECT-TYPE
         SYNTAX      DateAndTime
         MAX-ACCESS  read-only
         STATUS      current
         DESCRIPTION
                     "Sta active time."
         ::= { fsStaAssRecordsSearchByTimeEntry 9 }

    fsStaTimeupdowntimes OBJECT-TYPE
         SYNTAX      Unsigned32
         MAX-ACCESS  read-only
         STATUS      current
         DESCRIPTION
                     "Sta up and down times."
         ::= { fsStaAssRecordsSearchByTimeEntry 10 }

    fsStaTimeroamtimes OBJECT-TYPE
         SYNTAX      Unsigned32
         MAX-ACCESS  read-only
         STATUS      current
         DESCRIPTION
                     "Sta roam times."
         ::= { fsStaAssRecordsSearchByTimeEntry 11 }
		 
    fsStaTimertotaltimes OBJECT-TYPE
         SYNTAX      Unsigned32
         MAX-ACCESS  read-only
         STATUS      current
         DESCRIPTION
                     "Sta total times(join\leave\delete\roam)."
         ::= { fsStaAssRecordsSearchByTimeEntry 12 }		 

    fsStaTimerjitter OBJECT-TYPE
         SYNTAX      INTEGER
         MAX-ACCESS  read-only
         STATUS      current
         DESCRIPTION
                     "Sta association action jitter or not."
         ::= { fsStaAssRecordsSearchByTimeEntry 13}
		 
    fsStaTimerjointimes OBJECT-TYPE
         SYNTAX      Unsigned32
         MAX-ACCESS  read-only
         STATUS      current
         DESCRIPTION
                     "Sta association join times."
         ::= { fsStaAssRecordsSearchByTimeEntry 14 }

    fsStaTimerlatelytime OBJECT-TYPE
         SYNTAX      DateAndTime
         MAX-ACCESS  read-only
         STATUS      current
         DESCRIPTION
                     "Sta association lately join time."
         ::= { fsStaAssRecordsSearchByTimeEntry 15 }

    fsStaTimerSSID OBJECT-TYPE
         SYNTAX      DisplayString
         MAX-ACCESS  read-only
         STATUS      current
         DESCRIPTION
                     "Sta association ssid."
         ::= { fsStaAssRecordsSearchByTimeEntry 16 }				 
		 
--*******************************************************************************
--fsStaAssRecordsSearchByAPTable :  search sta association records macs by AP
--*******************************************************************************
    fsStaAssRecordsSearchByAPTable  OBJECT-TYPE
         SYNTAX      SEQUENCE OF FSStaAssRecordsSearchByAPEntry
         MAX-ACCESS  not-accessible
         STATUS      current
         DESCRIPTION
                     "A table listing the sta association process detail records,
                      can be search record by ap which sta associatied."
         ::= { fsStaAssRecordsByAP 1 }
   
    fsStaAssRecordsSearchByAPEntry OBJECT-TYPE
         SYNTAX      FSStaAssRecordsSearchByAPEntry
         MAX-ACCESS  not-accessible
         STATUS      current
         DESCRIPTION
                     "Get sta association records by ap."
         INDEX       { fsStaAPAPName,
                       fsStaAPindex }
         ::= { fsStaAssRecordsSearchByAPTable  1 }


    FSStaAssRecordsSearchByAPEntry ::= SEQUENCE {    
             fsStaAPAPName       DisplayString,    
             fsStaAPindex        Unsigned32,      
             fsStaAPMac          MacAddress,       
             fsStaAPISUP         INTEGER,          
             fsStaAPStartime     DateAndTime,      
             fsStaAPupdowntimes  Unsigned32,       
             fsStaAProamtimes    Unsigned32,       
             fsStaAPtotaltimes   Unsigned32,
	     fsStaAPjitter       INTEGER,
             fsStaAPjointimes    Unsigned32,
             fsStaAPlatelytime   DateAndTime,
             fsStaAPSSID         DisplayString					 
             }

    fsStaAPAPName OBJECT-TYPE
         SYNTAX      DisplayString(SIZE(1..64))
         MAX-ACCESS  not-accessible
         STATUS      current
         DESCRIPTION
                     "ap name."
         ::= { fsStaAssRecordsSearchByAPEntry 1 }

    fsStaAPindex OBJECT-TYPE
         SYNTAX      Unsigned32
         MAX-ACCESS  not-accessible
         STATUS      current
         DESCRIPTION
                     "the index of Sta mac."
         ::= { fsStaAssRecordsSearchByAPEntry 2 }


    fsStaAPMac OBJECT-TYPE
         SYNTAX      MacAddress
         MAX-ACCESS  read-only
         STATUS      current
         DESCRIPTION
                     "Sta Mac address."
         ::= { fsStaAssRecordsSearchByAPEntry 3 }

    fsStaAPISUP OBJECT-TYPE
         SYNTAX      INTEGER {
                      up(0),
                      down(1)
                     }
         MAX-ACCESS  read-only
         STATUS      current
         DESCRIPTION
                     "Sta is active or not."
         ::= { fsStaAssRecordsSearchByAPEntry 4 }

    fsStaAPStartime OBJECT-TYPE
         SYNTAX      DateAndTime
         MAX-ACCESS  read-only
         STATUS      current
         DESCRIPTION
                     "Sta active time."
         ::= { fsStaAssRecordsSearchByAPEntry 5 }

    fsStaAPupdowntimes OBJECT-TYPE
         SYNTAX      Unsigned32
         MAX-ACCESS  read-only
         STATUS      current
         DESCRIPTION
                     "Sta up and down times."
         ::= { fsStaAssRecordsSearchByAPEntry 6 }

    fsStaAProamtimes OBJECT-TYPE
         SYNTAX      Unsigned32
         MAX-ACCESS  read-only
         STATUS      current
         DESCRIPTION
                     "Sta roam times."
         ::= { fsStaAssRecordsSearchByAPEntry 7 }
		 
    fsStaAPtotaltimes OBJECT-TYPE
         SYNTAX      Unsigned32
         MAX-ACCESS  read-only
         STATUS      current
         DESCRIPTION
                     "Sta total times(join\leave\delete\roam)."
         ::= { fsStaAssRecordsSearchByAPEntry 8 }
		 
    fsStaAPjitter OBJECT-TYPE
         SYNTAX      INTEGER
         MAX-ACCESS  read-only
         STATUS      current
         DESCRIPTION
                     "Sta association action jitter or not."
         ::= { fsStaAssRecordsSearchByAPEntry 9}
		 
    fsStaAPjointimes OBJECT-TYPE
         SYNTAX      Unsigned32
         MAX-ACCESS  read-only
         STATUS      current
         DESCRIPTION
                     "Sta association join times."
         ::= { fsStaAssRecordsSearchByAPEntry 10 }

    fsStaAPlatelytime OBJECT-TYPE
         SYNTAX      DateAndTime
         MAX-ACCESS  read-only
         STATUS      current
         DESCRIPTION
                     "Sta association lately join time."
         ::= { fsStaAssRecordsSearchByAPEntry 11 }

    fsStaAPSSID OBJECT-TYPE
         SYNTAX      DisplayString
         MAX-ACCESS  read-only
         STATUS      current
         DESCRIPTION
                     "Sta association ssid."
         ::= { fsStaAssRecordsSearchByAPEntry 12 }		

--*******************************************************************
--fsStaAssSignalByMACTable  :  get sta association signal by mac
--*******************************************************************
    fsStaAssSignalByMACTable  OBJECT-TYPE
         SYNTAX      SEQUENCE OF FSStaAssSignalByMACEntry
         MAX-ACCESS  not-accessible
         STATUS      current
         DESCRIPTION
                     "A table listing the sta association process detail signal,
                      can be search by mac."
         ::= { fsStaAssSignalByMAC 1 }
   
    fsStaAssSignalByMACEntry OBJECT-TYPE
         SYNTAX      FSStaAssSignalByMACEntry
         MAX-ACCESS  not-accessible
         STATUS      current
         DESCRIPTION
                     "Get sta association signal by mac."
         INDEX       { fsStaSignalMacAddress,
                       fsStaSignalMacindex}
         ::= { fsStaAssSignalByMACTable  1 }

    FSStaAssSignalByMACEntry ::= SEQUENCE {        
             fsStaSignalMacAddress      MacAddress,      
             fsStaSignalMacindex        Unsigned32,     
             fsStaSignaltime            DateAndTime,    
             fsStaSignalValue           INTEGER
             }
    fsStaSignalMacAddress OBJECT-TYPE
         SYNTAX      MacAddress
         MAX-ACCESS  not-accessible
         STATUS      current
         DESCRIPTION
                     "Sta Mac address."
         ::= { fsStaAssSignalByMACEntry 1 }

    fsStaSignalMacindex OBJECT-TYPE
         SYNTAX      Unsigned32
         MAX-ACCESS  not-accessible
         STATUS      current
         DESCRIPTION
                     "the index of Sta mac."
         ::= { fsStaAssSignalByMACEntry 2 }
		 
    fsStaSignaltime OBJECT-TYPE
         SYNTAX      DateAndTime
         MAX-ACCESS  read-only
         STATUS      current
         DESCRIPTION
                     "Sta time of signal."
         ::= { fsStaAssSignalByMACEntry 3 }
		 
    fsStaSignalValue OBJECT-TYPE
         SYNTAX      INTEGER 
         MAX-ACCESS  read-only
         STATUS      current
         DESCRIPTION
                     "the signal value."
         ::= { fsStaAssSignalByMACEntry 4 }

--*******************************************************************
--fsStaAssRetryByMACTable  :  get sta retry packet value by mac
--*******************************************************************
    fsStaAssRetryByMACTable  OBJECT-TYPE
         SYNTAX      SEQUENCE OF FSStaAssRetryByMACEntry
         MAX-ACCESS  not-accessible
         STATUS      current
         DESCRIPTION
                     "A table listing the sta association process detail signal,
                      can be search by mac."
         ::= { fsStaAssRetryByMAC 1 }
   
    fsStaAssRetryByMACEntry OBJECT-TYPE
         SYNTAX      FSStaAssRetryByMACEntry
         MAX-ACCESS  not-accessible
         STATUS      current
         DESCRIPTION
                     "Get sta association signal by mac."
         INDEX       { fsStaRetryMacAddress,
                       fsStaRetryMacindex}
         ::= { fsStaAssRetryByMACTable  1 }

    FSStaAssRetryByMACEntry ::= SEQUENCE {        
             fsStaRetryMacAddress      MacAddress,      
             fsStaRetryMacindex        Unsigned32,     
             fsStaRetrytime            DateAndTime,    
             fsStaRetryValue           INTEGER
             }
    fsStaRetryMacAddress OBJECT-TYPE
         SYNTAX      MacAddress
         MAX-ACCESS  not-accessible
         STATUS      current
         DESCRIPTION
                     "Sta Mac address."
         ::= { fsStaAssRetryByMACEntry 1 }

    fsStaRetryMacindex OBJECT-TYPE
         SYNTAX      Unsigned32
         MAX-ACCESS  not-accessible
         STATUS      current
         DESCRIPTION
                     "the index of Sta mac."
         ::= { fsStaAssRetryByMACEntry 2 }
		 
    fsStaRetrytime OBJECT-TYPE
         SYNTAX      DateAndTime
         MAX-ACCESS  read-only
         STATUS      current
         DESCRIPTION
                     "Sta time of signal."
         ::= { fsStaAssRetryByMACEntry 3 }
		 
    fsStaRetryValue OBJECT-TYPE
         SYNTAX      INTEGER 
         MAX-ACCESS  read-only
         STATUS      current
         DESCRIPTION
                     "the retry value."
         ::= { fsStaAssRetryByMACEntry 4 }		

--*******************************************************************
--statistics data
--*******************************************************************
    fsAssStatisticsTotalsta OBJECT-TYPE
         SYNTAX      Unsigned32 
         MAX-ACCESS  read-only
         STATUS      current
         DESCRIPTION
                     "the total sta."
         ::= { fsStaAssStatistic 1 }	

    fsAssStatisticsTotalinfo OBJECT-TYPE
         SYNTAX      Unsigned32 
         MAX-ACCESS  read-only
         STATUS      current
         DESCRIPTION
                     "the total info."
         ::= { fsStaAssStatistic 2 }	
		 
    fsAssStatisticsdown OBJECT-TYPE
         SYNTAX      Unsigned32 
         MAX-ACCESS  read-only
         STATUS      current
         DESCRIPTION
                     "the down sta within one hour."
         ::= { fsStaAssStatistic 3 }			 

    fsAssStatisticsObligate1 OBJECT-TYPE
         SYNTAX      Unsigned32 
         MAX-ACCESS  read-only
         STATUS      current
         DESCRIPTION
                     "the obligate 2."
         ::= { fsStaAssStatistic 4 }					 

    fsAssStatisticsObligate2 OBJECT-TYPE
         SYNTAX      Unsigned32 
         MAX-ACCESS  read-only
         STATUS      current
         DESCRIPTION
                     "the obligate 2."
         ::= { fsStaAssStatistic 5 }			 
		 
    fsAssStatisticsObligate3 OBJECT-TYPE
         SYNTAX      Unsigned32 
         MAX-ACCESS  read-only
         STATUS      current
         DESCRIPTION
                     "the obligate 2."
         ::= { fsStaAssStatistic 6 }					 
		 
fsStaAssRecordsMIBConformance OBJECT IDENTIFIER ::= { fsStaAssRecordsMIB 2 }
fsStaAssRecordsMIBCompliances OBJECT IDENTIFIER ::= { fsStaAssRecordsMIBConformance 1 }
fsStaAssRecordsMIBGroups      OBJECT IDENTIFIER ::= { fsStaAssRecordsMIBConformance 2 }


-- compliance statements

fsStaAssRecordsMIBCompliance MODULE-COMPLIANCE
        STATUS  current
        DESCRIPTION
                "The compliance statement for entities which implement
                the FS Sta Association Records"
        MODULE  -- this module
                MANDATORY-GROUPS { 
                                  fsStaAssRecordsGrobalMIBroup,
                                  fsStaAssRecordsMIBroup,
                                  fsStaAssRecordsSearchByTimeMIBroup,
                                  fsStaAssRecordsSearchByAPMIBroup,
				  fsStaAssSignalSearchByMACMIBroup,
				  fsStaAssRetrySearchByMACMIBroup,
				  fsStaAssStatisticsMIBroup
                }
        ::= { fsStaAssRecordsMIBCompliances 1 }
                
-- units of conformance

fsStaAssRecordsGrobalMIBroup OBJECT-GROUP
        OBJECTS {
             fsStaMacGrobalAPName,  
             fsStaMacGrobalISUP,           
             fsStaMacGrobalStartime,       
             fsStaMacGrobalupdowntimes,     
             fsStaMacGrobalroamtimes,    
             fsStaMacGrobaltotaltimes,    
             fsStaMacGrobalrealdowntimes, 
             fsStaMacGrobalSSID          
        }
        STATUS  current
        DESCRIPTION
                "A table listing the sta association process survey records,
                      can be search record by mac."
        ::= { fsStaAssRecordsMIBGroups 1 } 

fsStaAssRecordsMIBroup OBJECT-GROUP
        OBJECTS {
             fsStaAsstime,  
             fsStaAssAction,    
             fsStaAssSubAction,   		 
             fsStaAssResult,       
             fsStaAssReason,        
             fsStaAssApNamePre,    
             fsStaAssApNameNow,     
             fsStaAssSignalQua,   
             fsStaAssRoamtype,    
             fsStaAssjitter,       
             fsStaAssjointimes,    
             fsStaAsslatelytime,  
	     fsStaAssSSID        
        }
        STATUS  current
        DESCRIPTION
                "A table listing the sta association process detail records,
                      can be search record by mac."
        ::= { fsStaAssRecordsMIBGroups 2 } 

fsStaAssRecordsSearchByTimeMIBroup OBJECT-GROUP
        OBJECTS {
             fsStaTimeMac,
             fsStaTimeAPName,
             fsStaTimeISUP,
             fsStaTimeStartime,
             fsStaTimeupdowntimes,
             fsStaTimeroamtimes,
             fsStaTimertotaltimes,
             fsStaTimerjitter,
             fsStaTimerjointimes,   
             fsStaTimerlatelytime,  
             fsStaTimerSSID       				 
        }
        STATUS  current
        DESCRIPTION
                "A table listing the sta association process detail records,
                      can be search record by the time of sta association."
        ::= { fsStaAssRecordsMIBGroups 3 } 

fsStaAssRecordsSearchByAPMIBroup OBJECT-GROUP
        OBJECTS {
             fsStaAPMac,
             fsStaAPISUP,
             fsStaAPStartime,
             fsStaAPupdowntimes,
             fsStaAProamtimes,
             fsStaAPtotaltimes,
             fsStaAPjitter,   
             fsStaAPjointimes,   
             fsStaAPlatelytime,  
             fsStaAPSSID       
        }
        STATUS  current
        DESCRIPTION
                "A table listing the sta association process detail records,
                      can be search record by ap which sta associatied."
        ::= { fsStaAssRecordsMIBGroups 4 } 

fsStaAssSignalSearchByMACMIBroup OBJECT-GROUP
        OBJECTS {
             fsStaSignaltime,    
             fsStaSignalValue
        }
        STATUS  current
        DESCRIPTION
                "A table listing the sta association process detail signal,
                      can be search record by mac."
        ::= { fsStaAssRecordsMIBGroups 5 } 

fsStaAssRetrySearchByMACMIBroup OBJECT-GROUP
        OBJECTS {
             fsStaRetrytime,    
             fsStaRetryValue
        }
        STATUS  current
        DESCRIPTION
                "A table listing the sta association process detail retry packet,
                      can be search record by mac."
        ::= { fsStaAssRecordsMIBGroups 6 } 		

fsStaAssStatisticsMIBroup OBJECT-GROUP
        OBJECTS {
             fsAssStatisticsTotalsta,    
             fsAssStatisticsTotalinfo,
	     fsAssStatisticsdown,
	     fsAssStatisticsObligate1,
	     fsAssStatisticsObligate2,
	     fsAssStatisticsObligate3
        }
        STATUS  current
        DESCRIPTION
                "statistics of troubleshooting."
        ::= { fsStaAssRecordsMIBGroups 7 } 				
		
END

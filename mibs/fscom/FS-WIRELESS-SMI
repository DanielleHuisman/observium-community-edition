-- *****************************************************************
-- FS-WIRELESS-SMI.mib: FS Wireless SMI File
-- 
-- July 2007, Wuzg
-- 
-- Copyright (c) 2007 by FS.COM Inc..
-- All rights reserved.
-- 
-- *****************************************************************
--

FS-WIRELESS-SMI DEFINITIONS ::= BEGIN

IMPORTS
        MODULE-IDENTITY,
        OBJECT-IDENTITY
                FROM SNMPv2-SMI
        products
                FROM FS-SMI;
                
wireless        OBJECT IDENTIFIER ::= { products 3 }

wirelessMib MODULE-IDENTITY
        LAST-UPDATED "200707040000Z"
        ORGANIZATION "FS.COM Inc.."
        CONTACT-INFO
                " 
                Tel: 400-865-2852 

                E-mail: https://www.fs.com/live_chat_service_mail.html"
        DESCRIPTION
                "The Structure of Management Information for the
                 FS enterprise."
        REVISION      "200707040000Z"
        DESCRIPTION
                "Initial version of this MIB module."
        ::= { wireless 1 }        

fsWirelessProducts OBJECT-IDENTITY
        STATUS  current
        DESCRIPTION
                "fsWirelessProducts is the root OBJECT IDENTIFIER from
                which sysObjectID values are assigned for wireless product.
                Actual values are defined in FS-PRODUCTS-MIB."
        ::= { wirelessMib 1 }

fsWirelessMgmt OBJECT-IDENTITY
        STATUS  current
        DESCRIPTION
                "fsWirelessMgmt is the main subtree for those functional mib."
        ::= { wirelessMib 2 }
        
END

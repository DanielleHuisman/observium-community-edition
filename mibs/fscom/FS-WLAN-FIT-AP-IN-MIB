-- *******************************************************************
-- FS-WLAN-FIT-AP-IN-MIB.mib : FS MIB
-- May 2010, ruanyucheng
--
-- Copyright (c) 2010 by FS.COM Inc..
-- All rights reserved.
-- *******************************************************************
FS-WLAN-FIT-AP-IN-MIB DEFINITIONS ::= BEGIN
    IMPORTS
        MODULE-IDENTITY,
        OBJECT-TYPE,
        Integer32,
        Counter32,
        IpAddress,
        TimeTicks,
        Unsigned32
            FROM SNMPv2-SMI
        TruthValue,
        DisplayString,
        MacAddress,
        RowStatus
            FROM SNMPv2-TC
        Gauge
            FROM RFC1155-SMI
        MODULE-COMPLIANCE,
        NOTIFICATION-GROUP,
        OBJECT-GROUP
            FROM SNMPv2-CONF
        fsStaMacAddr,    
        fsApApName,
        fsApCfgRadioId,    
        fsApMacAddr,
        fsApgWlanId
            FROM FS-AC-MGMT-MIB
        ifIndex
            FROM RFC1213-MIB
        fsMgmt
            FROM FS-SMI;
--*******************************************
--* module definition
--*******************************************
fsFitApMibModule MODULE-IDENTITY
    LAST-UPDATED    "201002260000Z"
    ORGANIZATION
        "FS.COM Inc.."
    CONTACT-INFO
        "Tel: 400-865-2852
           E-mail: https://www.fs.com/live_chat_service_mail.html "

    DESCRIPTION
       "
       Wlan software private MIB for FS SNC according to the China
       Mobile standard. This is device manage MIB.
       "
    REVISION      "201002280000Z"
    DESCRIPTION
       "Initial version of this MIB module."

    ::= { fsMgmt  83 }

fsAlarmTrapsObjects       OBJECT IDENTIFIER  ::= { fsFitApMibModule 10 }
fsAlarmTraps              OBJECT IDENTIFIER  ::= { fsFitApMibModule 0 }
--**************************************************
--* apFSTrapObjects begins * 
--**************************************************
fsWIDSIllegalAlarmTrap NOTIFICATION-TYPE
    OBJECTS {
        fsWIDSSuspiciousType,
        fsWIDSSuspiciousDeviceMac,
        fsWIDSSuspiciousDeviceExtensionInfo
    }
    STATUS  current
    DESCRIPTION
            " This trap will be sent at once when detecting an suspicious AP."
    ::= { fsAlarmTraps 1 }  
    
fsTelMtWorkModeChgTrap    NOTIFICATION-TYPE
    OBJECTS {
        fsAPCurrentPMMode,
        fsChgWorkModeAPMac
    }
    STATUS  current
    DESCRIPTION
            " This trap will be sent when the ap monitor workMode Change."
    ::= { fsAlarmTraps 2 }    

    
fsAttackAlarm   NOTIFICATION-TYPE
		OBJECTS {
        fsAttackType,
        fsAttackCilentIP,
        fsAttackCilentExternInfo
    }
    STATUS  current
    DESCRIPTION
            " This trap will be sent when Attack has Appeared ."
    ::= { fsAlarmTraps 4 }         
----------------------------------------------------
----------------------------------------------------
fsWIDSSuspiciousType  OBJECT-TYPE
    SYNTAX      DisplayString  (SIZE(1..40))
    MAX-ACCESS  read-write
    STATUS      current
    DESCRIPTION
        " Suspicious ap type , eg: nonlicet AP   or disturb AP."
    ::= { fsAlarmTrapsObjects 1 }

fsWIDSSuspiciousDeviceMac OBJECT-TYPE
    SYNTAX      MacAddress
    MAX-ACCESS  read-write
    STATUS      current
    DESCRIPTION
        " The macaddress of the suspicious device."
    ::= { fsAlarmTrapsObjects 2 }

fsWIDSSuspiciousDeviceExtensionInfo OBJECT-TYPE
    SYNTAX      DisplayString  (SIZE(1..40))
    MAX-ACCESS  read-write
    STATUS      current
    DESCRIPTION
        " The information left for the future extension."
    ::= { fsAlarmTrapsObjects 3 }  
    
fsAPCurrentPMMode     OBJECT-TYPE
    SYNTAX      DisplayString  (SIZE(1..40))
    MAX-ACCESS  read-write
    STATUS      current
    DESCRIPTION
        " The information for the current ap monitor workMode ."
    ::= { fsAlarmTrapsObjects 4 }        
    
fsChgWorkModeAPMac  OBJECT-TYPE
    SYNTAX      MacAddress
    MAX-ACCESS  read-write
    STATUS      current
    DESCRIPTION
        " The macaddress of the ap device."
    ::= { fsAlarmTrapsObjects 7 }  
    
fsAttackType  OBJECT-TYPE
    SYNTAX      DisplayString  (SIZE(1..40))
    MAX-ACCESS  read-write
    STATUS      current
    DESCRIPTION
        " The attack type string ."
    ::= { fsAlarmTrapsObjects 8 } 
    
fsAttackCilentIP OBJECT-TYPE
    SYNTAX      IpAddress
    MAX-ACCESS  read-write
    STATUS      current
    DESCRIPTION
            " The ipaddress of the attack client."
    ::= { fsAlarmTrapsObjects 9 }
    
fsAttackCilentExternInfo  OBJECT-TYPE
    SYNTAX      DisplayString  (SIZE(1..40))
    MAX-ACCESS  read-write
    STATUS      current
    DESCRIPTION
        " The attack extern info string ."
    ::= { fsAlarmTrapsObjects 10 }   
   
--**************************************************
--* apFSTrapObjects ends * 
--**************************************************
fsSystemInfoConfigObjects     OBJECT IDENTIFIER  ::= { fsFitApMibModule 1 }
fsDomain   OBJECT-TYPE
    SYNTAX DisplayString
    MAX-ACCESS read-only
    STATUS current
    DESCRIPTION
        "The Product Domain."
    ::= { fsSystemInfoConfigObjects 1 }
    
fsPhySeparatedEnable   OBJECT-TYPE
    SYNTAX INTEGER {
          off(0),
          on(1)
    }
    MAX-ACCESS read-write
    STATUS current
    DESCRIPTION
        "virtual phy separated enable config ,0:off 1:on."
    ::= { fsSystemInfoConfigObjects 2 }      
    
fsForfendDosAttackEnable   OBJECT-TYPE
    SYNTAX INTEGER {
          off(0),
          on(1)
    }
    MAX-ACCESS read-write
    STATUS current
    DESCRIPTION
        "Forfend DOS Attack config ,0:off 1:on."
    ::= { fsSystemInfoConfigObjects 3 } 
    
fsAcTrafficLoadBalancing OBJECT-TYPE
    SYNTAX TruthValue 
    MAX-ACCESS read-write
    STATUS current
    DESCRIPTION         
        " AC Traffic Load Balancing enable. "
    ::= { fsSystemInfoConfigObjects 4 }  
    
fsAcTrafficLoadBalanceThreshold    OBJECT-TYPE
    SYNTAX Integer32 
    MAX-ACCESS read-write
    STATUS current
    DESCRIPTION         
        " AC Traffic Load Balancing Threshold value . "
    ::= { fsSystemInfoConfigObjects 5 }  
    
fsAcTrafficOtherAPThresholdValue   OBJECT-TYPE
    SYNTAX Integer32 
    MAX-ACCESS read-write
    STATUS current
    DESCRIPTION         
        " other AP Traffic Threshold value . "
    ::= { fsSystemInfoConfigObjects 6 }    

fsAcAPWIDSScanningMode   OBJECT-TYPE
    SYNTAX INTEGER 
    MAX-ACCESS read-write
    STATUS current
    DESCRIPTION         
        " config AP WIDS scanning mode , 
        0: all channel scanning  1: auto select channel scanning . "
    ::= { fsSystemInfoConfigObjects 7 }  
    
fsAcAPLegitimateMode    OBJECT-TYPE
    SYNTAX INTEGER 
    MAX-ACCESS read-only
    STATUS current
    DESCRIPTION         
        " config AP Legitimate Mode value 
         0:legal ap 1: Illegal ap 2: Disturb AP . "
    ::= { fsSystemInfoConfigObjects 8 }    
    
fsAcAPTreatMode     OBJECT-TYPE
    SYNTAX INTEGER 
    MAX-ACCESS read-only
    STATUS current
    DESCRIPTION         
        " config Illegal AP Process mode 0:DOS attrack  1: disturb AP. "
    ::= { fsSystemInfoConfigObjects 9 }  
    
fsAcAssociationFailureTotalTimes  OBJECT-TYPE
    SYNTAX      Counter32
    MAX-ACCESS  read-only
    STATUS      current
    DESCRIPTION
        " The total times the association fails on AC."
    ::= { fsSystemInfoConfigObjects 10 }
    
fsAcAirIfRxTotalDataFrams  OBJECT-TYPE
    SYNTAX      Counter32
    MAX-ACCESS  read-only
    STATUS      current
    DESCRIPTION
        " The air interface total Rx Data Farms on AC."
    ::= { fsSystemInfoConfigObjects 11 }   

fsAcAirIfTxTotalDataFrams  OBJECT-TYPE
    SYNTAX      Counter32
    MAX-ACCESS  read-only
    STATUS      current
    DESCRIPTION
        " The air interface total Tx Data Farms on AC."
    ::= { fsSystemInfoConfigObjects 12 }  
    
fsAcAirIfTxTotalLostFrams  OBJECT-TYPE
    SYNTAX      Counter32
    MAX-ACCESS  read-only
    STATUS      current
    DESCRIPTION
        " The air interface total Tx Losted Data Farms on AC."
    ::= { fsSystemInfoConfigObjects 13 } 
    
fsAcAirIfTxAssociateFrams   OBJECT-TYPE
    SYNTAX      Counter32
    MAX-ACCESS  read-only
    STATUS      current
    DESCRIPTION
        " The air interface total Tx Associate  Farms on AC."
    ::= { fsSystemInfoConfigObjects 14 } 
    
fsAcAirIfRxAssociateFrams   OBJECT-TYPE
    SYNTAX      Counter32
    MAX-ACCESS  read-only
    STATUS      current
    DESCRIPTION
        " The air interface total Rx Associate  Farms on AC."
    ::= { fsSystemInfoConfigObjects 15 } 
 
fsAcAirIfBeaconTotalFrams  OBJECT-TYPE
    SYNTAX      Counter32
    MAX-ACCESS  read-only
    STATUS      current
    DESCRIPTION
        " The air interface total Beacon Farms on AC."
    ::= { fsSystemInfoConfigObjects 16 } 
    
fsAcAirIfRxTotalDataBytes   OBJECT-TYPE
    SYNTAX      Counter32
    MAX-ACCESS  read-only
    STATUS      current
    DESCRIPTION
        " The air interface total Rx right Data Bytes on AC."
    ::= { fsSystemInfoConfigObjects 17 }   
    
fsAcAirIfTxTotalDataBytes   OBJECT-TYPE
    SYNTAX      Counter32
    MAX-ACCESS  read-only
    STATUS      current
    DESCRIPTION
        " The air interface total Tx right Data Bytes on AC."
    ::= { fsSystemInfoConfigObjects 18 } 
    
fsAcAirRxFlux   OBJECT-TYPE
    SYNTAX      INTEGER
    MAX-ACCESS  read-only
    STATUS      current
    DESCRIPTION
        " The air interface Uplink Flux  on AC."
    ::= { fsSystemInfoConfigObjects 19 }               
    
fsAcAirTxFlux   OBJECT-TYPE
    SYNTAX      INTEGER
    MAX-ACCESS  read-only
    STATUS      current
    DESCRIPTION
        " The air interface Downlink Flux  on AC."
    ::= { fsSystemInfoConfigObjects 20 }  
        
    
--*******************************************
--   apAPInfoConfigTable starts
--******************************************* 
fsInfoConfigObjects  OBJECT IDENTIFIER  ::= { fsFitApMibModule 2 } 
fsInfoConfigTable  OBJECT-TYPE
    SYNTAX SEQUENCE OF FSApInfoConfigTableEntry
    MAX-ACCESS not-accessible
    STATUS current
    DESCRIPTION
      "ap configuration Info table."
    ::={ fsInfoConfigObjects 1 } 
    
fsInfoConfigTableEntry    OBJECT-TYPE
    SYNTAX  FSApInfoConfigTableEntry
    MAX-ACCESS  not-accessible
    STATUS  current
    DESCRIPTION
        "ap configuration Info table."
    INDEX   { fsApMacAddr }
    ::= { fsInfoConfigTable 1 }    
    
FSApInfoConfigTableEntry  ::=
    SEQUENCE {
        fsAcAPWIDSWorkMode              INTEGER
    }  
    
fsAcAPWIDSWorkMode  OBJECT-TYPE
    SYNTAX INTEGER 
    MAX-ACCESS read-write
    STATUS current
    DESCRIPTION         
        " config AP WIDS work mode, 0: WIDS disabled  1:only support monitor 
        2:support AP monotor and access . "
    ::= { fsInfoConfigTableEntry 1 }       
--*******************************************
--   apAPInfoConfigTable ends
--*******************************************          

fsStationConfigObjects        OBJECT IDENTIFIER  ::= { fsFitApMibModule 4 } 
--**************************************************
--* apapAC Station CONFIG starts * 
--**************************************************
fsConfigStaInfoTable OBJECT-TYPE
    SYNTAX SEQUENCE OF FSApConfigStaInfoTableEntry
    MAX-ACCESS not-accessible
    STATUS current
    DESCRIPTION
      "AC Config Station."
    ::={ fsStationConfigObjects 1 }

fsConfigStaInfoTableEntry OBJECT-TYPE
    SYNTAX  FSApConfigStaInfoTableEntry
    MAX-ACCESS  not-accessible
    STATUS  current
    DESCRIPTION
        "AC Config AP Bandwith max."
    INDEX   { fsStaMacAddr }
    ::= { fsConfigStaInfoTable 1 }
    
FSApConfigStaInfoTableEntry ::=
    SEQUENCE {
    		fsACconfigAPBandwith         Integer32
    }  

fsACconfigAPBandwith   OBJECT-TYPE
    SYNTAX Integer32
    MAX-ACCESS read-write
    STATUS current
    DESCRIPTION
        "AC Config AP Bandwith max."
    ::= { fsConfigStaInfoTableEntry 1 }  
--**************************************************
--* apapAC Station CONFIG ends * 
--**************************************************    

--apWlanIdSecurityCfgObjects        OBJECT IDENTIFIER  ::= { fsFitApMibModule 5 } 

--**************************************************
--* apapAC WlanIdSecurity CONFIG starts * 
--**************************************************  
--apSecurityCfgTable OBJECT-TYPE
--    SYNTAX SEQUENCE OF ApSecurityCfgTableEntry
--    MAX-ACCESS not-accessible
--    STATUS current
--    DESCRIPTION
--      "AP security  config."
--    ::={ apWlanIdSecurityCfgObjects 1 }

--apSecurityCfgTableEntry OBJECT-TYPE
--    SYNTAX  ApSecurityCfgTableEntry
--    MAX-ACCESS  not-accessible
--    STATUS  current
--    DESCRIPTION
--        "AP security  config."
--    INDEX   { fsgWlanId }
--    ::= { apSecurityCfgTable 1 }
    
--ApSecurityCfgTableEntry ::=
--    SEQUENCE {
--    		apsecurityMode                        INTEGER,       in china mobile node ApSSIDConfigTableEntry 
--    		apAuthenMode                          INTEGER,       in china mobile node apSSIDConfigTableEntry
--    		apSecurityCiphers                     INTEGER,       in china mobile node apSSIDConfigTableEntry
--    		apWEPCipherKeyIndex                   INTEGER,       in china mobile node apSecurityConfigTableEntry
--        apWEPCipherKeyValue                   DisplayString, in china mobile node apSecurityConfigTableEntry
--        apWEPCipherKeyCharType                INTEGER,       in china mobile node apSecurityConfigTableEntry
--        apPSKCipherKeyValue                   DisplayString, in china mobile node apSecurityConfigTableEntry
--        apPSKCipherKeyCharType                INTEGER,       in china mobile node apSecurityConfigTableEntry
--        apWAPIASIPAddress                     IpAddress,     in china mobile node apSecurityConfigTableEntry
--        apWAPIIsInstalledCer                  TruthValue,    in china mobile node apSecurityConfigTableEntry
--        apWAPIConfigVersion                   Integer32,     in china mobile node apWAPIExternInfoConfigTableEntry
--        apWAPIControlledAuthControl           TruthValue,    in china mobile node apWAPIExternInfoConfigTableEntry
--        apWAPIControlledPortControl           INTEGER,       in china mobile node apWAPIExternInfoConfigTableEntry
--        apWAPIOptionImplemented               TruthValue,    in china mobile node apWAPIExternInfoConfigTableEntry
--        apWAPIPreauthenticationImplemented    TruthValue,
--        apWAPIEnabled                         TruthValue,
--        apWAPIPreauthEnabled                  TruthValue,
--        apWAPIUnicastKeysSupported            Unsigned32,
--        apWAPIUnicastRekeyMethod              INTEGER,
--        apWAPIUnicastRekeyTime                Unsigned32,
--        apWAPIUnicastRekeyPackets             Unsigned32,
--        apWAPIMulticastCipher                 OCTET STRING,
--        apWAPIMulticastRekeyMethod            INTEGER,
--        apWAPIMulticastRekeyTime              Unsigned32,
--        apWAPIMulticastRekeyPackets  	        Unsigned32,
--        apWAPIMulticastRekeyStrict  	        TruthValue,
--        apWAPIPSKValue 	                      OCTET STRING,
--        apWAPICertificateUpdateCount 	        Unsigned32,
--        apWAPIUnicastUpdateCount  	          Unsigned32,
--        apWAPIMulticastCipherSize 	          Unsigned32,
--        apWAPIBKReauthThreshold 	            Unsigned32,
--        apWAPISATimeout 	                    Unsigned32,
--        apWAPIAuthSuiteSelected 	            OCTET STRING,
--        apWAPIUnicastCipherSelected 	        OCTET STRING,
--        apWAPIMulticastCipherSelected 	      OCTET STRING,
--        apWAPIBKIDUsed 	                      OCTET STRING,
--        apWAPIAuthSuiteRequested 	            OCTET STRING,
--        apWAPIUnicastCipherRequested 	        OCTET STRING,
--        apWAPIMulticastCipherRequested 	      OCTET STRING,
--        apWAPIUnicastCipher                   OCTET STRING,
--        apWAPIUnicastCipherEnabled            TruthValue,
--        apWAPIUnicastCipherSize               Unsigned32,
--        apWAPIAuthenticationSuite             OCTET STRING,
--        apWAPIAuthenticationSuiteEnabled      TruthValue      in china mobile node apWAPIExternInfoConfigTableEntry
--    }  
        
--**************************************************
--* apapAC Security CONFIG ends * 
--**************************************************  
--**************************************************
--* apapAirIfInfoStatisticsTable starts * 
--************************************************** 
fsAirIfStatisticsObjects     OBJECT IDENTIFIER  ::= { fsFitApMibModule 6 }
fsAirIfInfoStatisticsTable OBJECT-TYPE
    SYNTAX SEQUENCE OF FSApAirIfInfoStatisticsTableEntry
    MAX-ACCESS not-accessible
    STATUS current
    DESCRIPTION
      "get air interface parameters statistics."
    ::={ fsAirIfStatisticsObjects 1 }
  
fsAirIfInfoStatisticsTableEntry OBJECT-TYPE
    SYNTAX  FSApAirIfInfoStatisticsTableEntry
    MAX-ACCESS  not-accessible
    STATUS  current
    DESCRIPTION
        "get  AP Associa Fail times "
    INDEX   { fsApgWlanId,fsApMacAddr }
    ::= { fsAirIfInfoStatisticsTable 1 }

FSApAirIfInfoStatisticsTableEntry ::=
    SEQUENCE {
       fsRxTotalDataFrams     Counter32,
       fsTxTotalDataFrams     Counter32,
       fsTxLostDataFrams      Counter32,   
       fsTxAssociateFrams     Counter32,
       fsRxAssociateFrams     Counter32,
       fsBeaconFrams          Counter32,
       fsRxTotalDataBytes     Counter32,
       fsTxTotalDataBytes     Counter32,
       fsRESUtilization       INTEGER
    }
    
fsRxTotalDataFrams  OBJECT-TYPE
    SYNTAX Counter32
    MAX-ACCESS read-only
    STATUS current
    DESCRIPTION
        "ap total Rx Data Frams."
    ::= { fsAirIfInfoStatisticsTableEntry 1 }  
    
fsTxTotalDataFrams   OBJECT-TYPE
    SYNTAX Counter32
    MAX-ACCESS read-only
    STATUS current
    DESCRIPTION
        "ap total Tx Data Frams."
    ::= { fsAirIfInfoStatisticsTableEntry 2 }  
    
fsTxLostDataFrams   OBJECT-TYPE
    SYNTAX Counter32
    MAX-ACCESS read-only
    STATUS current
    DESCRIPTION
        "ap total Tx Lost Data Frams."
    ::= { fsAirIfInfoStatisticsTableEntry 3 }   
    
fsTxAssociateFrams  OBJECT-TYPE
    SYNTAX Counter32
    MAX-ACCESS read-only
    STATUS current
    DESCRIPTION
        "ap total Tx Associate Frams."
    ::= { fsAirIfInfoStatisticsTableEntry 4 } 
    
fsRxAssociateFrams   OBJECT-TYPE
    SYNTAX Counter32
    MAX-ACCESS read-only
    STATUS current
    DESCRIPTION
        "ap total Rx Associate Frams."
    ::= { fsAirIfInfoStatisticsTableEntry 5 }    
    
fsBeaconFrams    OBJECT-TYPE
    SYNTAX Counter32
    MAX-ACCESS read-only
    STATUS current
    DESCRIPTION
        "ap Beacon Total Frams."
    ::= { fsAirIfInfoStatisticsTableEntry 6 }  
    
fsRxTotalDataBytes   OBJECT-TYPE
    SYNTAX Counter32
    MAX-ACCESS read-only
    STATUS current
    DESCRIPTION
        "ap total Rx Data Bytes."
    ::= { fsAirIfInfoStatisticsTableEntry 7 }  
    
fsTxTotalDataBytes   OBJECT-TYPE
    SYNTAX Counter32
    MAX-ACCESS read-only
    STATUS current
    DESCRIPTION
        "ap total Tx Data Bytes."
    ::= { fsAirIfInfoStatisticsTableEntry 8 }    
    
fsRESUtilization   OBJECT-TYPE
    SYNTAX INTEGER
    MAX-ACCESS read-only
    STATUS current
    DESCRIPTION
        "ap Resource Utilization."
    ::= { fsAirIfInfoStatisticsTableEntry 9 }


--**************************************************
--* apAirIfInfoStatisticsTable starts * 
--************************************************** 
fsAirIfTxResendDataTable OBJECT-TYPE
    SYNTAX SEQUENCE OF FSApAirIfTxResendDataTableEntry
    MAX-ACCESS not-accessible
    STATUS current
    DESCRIPTION
      "get air interface Resend Data frames."
    ::={ fsAirIfStatisticsObjects 2 }
    
fsAirIfTxResendDataTableEntry OBJECT-TYPE
    SYNTAX  FSApAirIfTxResendDataTableEntry
    MAX-ACCESS  not-accessible
    STATUS  current
    DESCRIPTION
        "get air interface Resend Data frames"
    INDEX   { fsStaMacAddr }
    ::= { fsAirIfTxResendDataTable 1 }

FSApAirIfTxResendDataTableEntry ::=
    SEQUENCE {
          fsStaResendDataFrams  Counter32
    }   
   
fsStaResendDataFrams    OBJECT-TYPE
    SYNTAX Counter32
    MAX-ACCESS read-only
    STATUS current
    DESCRIPTION
        "station total Resend Data Frams."
    ::= { fsAirIfTxResendDataTableEntry 1 }
    
            
--**************************************************
--* apapAirIfInfoStatisticsTable ends * 
--************************************************** 

--**************************************************
--* apTermServiceStatistics starts * 
--************************************************** 

fsTermServiceStatistics              OBJECT IDENTIFIER  ::= { fsFitApMibModule 7 }
fsTermServiceStatisticsWithSSID      OBJECT IDENTIFIER  ::= { fsTermServiceStatistics 1 } 
fsTermServiceStatisticsWithAP        OBJECT IDENTIFIER  ::= { fsTermServiceStatistics 2 } 
fsTermServiceSTatisticsWithStation   OBJECT IDENTIFIER  ::= { fsTermServiceStatistics 3 } 

fsTermServiceStaticWithSSIDTable  OBJECT-TYPE
    SYNTAX SEQUENCE OF FSApTermServiceStaticWithSSIDTableEntry
    MAX-ACCESS not-accessible
    STATUS current
    DESCRIPTION
      "get Term Service Statistics With SSID."
    ::={ fsTermServiceStatisticsWithSSID 1 }
  
fsTermServiceStaticWithSSIDTableEntry OBJECT-TYPE
    SYNTAX  FSApTermServiceStaticWithSSIDTableEntry
    MAX-ACCESS  not-accessible
    STATUS  current
    DESCRIPTION
        "get Term Service Statistics With SSID"
    INDEX   { fsApgWlanId }
    ::= { fsTermServiceStaticWithSSIDTable 1 }

FSApTermServiceStaticWithSSIDTableEntry ::=
    SEQUENCE { 
           fsTotalUserNum                                INTEGER,  
           fsCurrentUserNum                              INTEGER,  
           fsStaReqAccessTimes                           INTEGER,
           fsRspStaAccessReqTimes                        INTEGER,
           fsStaAccessSucessTimes                        INTEGER,
           fsIneffiLinkVerifyFailTime                    INTEGER,
           fsTimeoutLinkVerifyFailTime                   INTEGER,
           fsInefficiencyLinkVerifyFailTime              INTEGER,
           fsOtherReasonLinkVerifyFailTime               INTEGER,
           fsIneffiAssociationFailTime                   INTEGER,
           fsTimeoutAssociationFailTime                  INTEGER,
           fsInefficiencyAssociationFailTime             INTEGER,
           fsOtherReasonAssociationFailTime              INTEGER,
           fsTotalReassociationAtmptTimes                INTEGER,
           fsTotalReassociationSuccessTimes              INTEGER,
           fsIneffiReassociationFailTime                 INTEGER,
           fsTimeoutReassociationFailTime                INTEGER,
           fsInefficiencyReassociationFailTime           INTEGER,
           fsOtherReasonReassociationFailTime            INTEGER,
           fsTotalIdentificationAtmptTimes               INTEGER,
           fsTotalIdentificationSuccessTimes             INTEGER,
           fsPwdErrorIdentifyFailTime                    INTEGER,
           fsIneffiIdentificationFailTime                INTEGER,
           fsTimeoutIdentificationFailTime               INTEGER,
           fsInefficiencyIdentificationFailTime          INTEGER,
           fsOtherReasonIdentificationFailTime           INTEGER,
           fsTotalRemoveLinkVerifyFailTimes              INTEGER,
           fsLeaveAPCoverageRemoveLinkVerifyFailTimes    INTEGER,
           fsInefficiencyRemoveLinkVerifyFailTime        INTEGER,
           fsLinkVerifyFailRemoveLinkVerifyFailTime      INTEGER,
           fsOtherReasonRemoveLinkVerifyFailTime         INTEGER,
           fsTotalRemoveLinkAssociationTimes             INTEGER,
           fsLeaveAPCoverageRemoveAssociationFailTimes   INTEGER,
           fsInefficiencyRemoveAssociationFailTime       INTEGER,
           fsAssociationFailRemoveAssociationFailTime    INTEGER,
           fsOtherReasonRemoveAssociationFailTime        INTEGER         
    }

fsTotalUserNum OBJECT-TYPE
    SYNTAX INTEGER
    MAX-ACCESS read-only
    STATUS current
    DESCRIPTION
        "Total user number that have connected to the AP."
    ::= { fsTermServiceStaticWithSSIDTableEntry 1}
    
fsCurrentUserNum   OBJECT-TYPE
    SYNTAX INTEGER
    MAX-ACCESS read-only
    STATUS current
    DESCRIPTION
        "Total current user number that have connected to the AP."
    ::= { fsTermServiceStaticWithSSIDTableEntry 2}  
    
fsStaReqAccessTimes OBJECT-TYPE
    SYNTAX INTEGER
    MAX-ACCESS read-only
    STATUS current
    DESCRIPTION
        "station request to access to AP times."
    ::= { fsTermServiceStaticWithSSIDTableEntry 3}    

fsRspStaAccessReqTimes  OBJECT-TYPE
    SYNTAX INTEGER
    MAX-ACCESS read-only
    STATUS current
    DESCRIPTION
        "ap response station access request times."
    ::= { fsTermServiceStaticWithSSIDTableEntry 4}    
    
fsStaAccessSucessTimes  OBJECT-TYPE
    SYNTAX INTEGER
    MAX-ACCESS read-only
    STATUS current
    DESCRIPTION
        "sta success to connet to ap times."
    ::= { fsTermServiceStaticWithSSIDTableEntry 5}      

fsIneffiLinkVerifyFailTime OBJECT-TYPE
    SYNTAX INTEGER
    MAX-ACCESS read-only
    STATUS current
    DESCRIPTION
        "Total link verify failure times due to algorithm or transform SN discrepancy."
    ::= { fsTermServiceStaticWithSSIDTableEntry 6}

fsTimeoutLinkVerifyFailTime OBJECT-TYPE
    SYNTAX INTEGER
    MAX-ACCESS read-only
    STATUS current
    DESCRIPTION
        "Total link verify failure times due to timeout."
    ::= { fsTermServiceStaticWithSSIDTableEntry 7}
    
fsInefficiencyLinkVerifyFailTime OBJECT-TYPE
    SYNTAX INTEGER
    MAX-ACCESS read-only
    STATUS current
    DESCRIPTION
        "Total link verify failure times due to inefficiency."
    ::= { fsTermServiceStaticWithSSIDTableEntry 8}
    
fsOtherReasonLinkVerifyFailTime OBJECT-TYPE
    SYNTAX INTEGER
    MAX-ACCESS read-only
    STATUS current
    DESCRIPTION
        "Total link verify failure times due to other reason."
    ::= { fsTermServiceStaticWithSSIDTableEntry 9}
    
fsIneffiAssociationFailTime OBJECT-TYPE
    SYNTAX INTEGER
    MAX-ACCESS read-only
    STATUS current
    DESCRIPTION
        "Total Association failure times due to algorithm or transform SN discrepancy."
    ::= { fsTermServiceStaticWithSSIDTableEntry 10}

fsTimeoutAssociationFailTime OBJECT-TYPE
    SYNTAX INTEGER
    MAX-ACCESS read-only
    STATUS current
    DESCRIPTION
        "Total Association failure times due to timeout."
    ::= { fsTermServiceStaticWithSSIDTableEntry 11}
    
fsInefficiencyAssociationFailTime OBJECT-TYPE
    SYNTAX INTEGER
    MAX-ACCESS read-only
    STATUS current
    DESCRIPTION
        "Total Association failure times due to inefficiency."
    ::= { fsTermServiceStaticWithSSIDTableEntry 12}
    
fsOtherReasonAssociationFailTime OBJECT-TYPE
    SYNTAX INTEGER
    MAX-ACCESS read-only
    STATUS current
    DESCRIPTION
        "Total Association failure times due to other reason."
    ::= { fsTermServiceStaticWithSSIDTableEntry 13}
    
fsTotalReassociationAtmptTimes OBJECT-TYPE
    SYNTAX INTEGER
    MAX-ACCESS read-only
    STATUS current
    DESCRIPTION
        "Total re-association attempt times."
    ::= { fsTermServiceStaticWithSSIDTableEntry 14}
    
fsTotalReassociationSuccessTimes OBJECT-TYPE
    SYNTAX INTEGER
    MAX-ACCESS read-only
    STATUS current
    DESCRIPTION
        "Total re-association success times."
    ::= { fsTermServiceStaticWithSSIDTableEntry 15}

fsIneffiReassociationFailTime OBJECT-TYPE
    SYNTAX INTEGER
    MAX-ACCESS read-only
    STATUS current
    DESCRIPTION
        "Total Reassociation failure times due to algorithm or transform SN discrepancy."
    ::= { fsTermServiceStaticWithSSIDTableEntry 16}

fsTimeoutReassociationFailTime OBJECT-TYPE
    SYNTAX INTEGER
    MAX-ACCESS read-only
    STATUS current
    DESCRIPTION
        "Total Reassociation failure times due to timeout."
    ::= { fsTermServiceStaticWithSSIDTableEntry 17}
    
fsInefficiencyReassociationFailTime OBJECT-TYPE
    SYNTAX INTEGER
    MAX-ACCESS read-only
    STATUS current
    DESCRIPTION
        "Total Reassociation failure times due to inefficiency."
    ::= { fsTermServiceStaticWithSSIDTableEntry 18}
    
fsOtherReasonReassociationFailTime OBJECT-TYPE
    SYNTAX INTEGER
    MAX-ACCESS read-only
    STATUS current
    DESCRIPTION
        "Total Reassociation failure times due to other reason."
    ::= { fsTermServiceStaticWithSSIDTableEntry 19}
    
fsTotalIdentificationAtmptTimes OBJECT-TYPE
    SYNTAX INTEGER
    MAX-ACCESS read-only
    STATUS current
    DESCRIPTION
        "Total Identification attempt times."
    ::= { fsTermServiceStaticWithSSIDTableEntry 20}
    
fsTotalIdentificationSuccessTimes OBJECT-TYPE
    SYNTAX INTEGER
    MAX-ACCESS read-only
    STATUS current
    DESCRIPTION
        "Total Identification success times."
    ::= { fsTermServiceStaticWithSSIDTableEntry 21}
    
fsPwdErrorIdentifyFailTime OBJECT-TYPE
    SYNTAX INTEGER
    MAX-ACCESS read-only
    STATUS current
    DESCRIPTION
        "Total identification failure times due to password error."
    ::= { fsTermServiceStaticWithSSIDTableEntry 22}    

fsIneffiIdentificationFailTime OBJECT-TYPE
    SYNTAX INTEGER
    MAX-ACCESS read-only
    STATUS current
    DESCRIPTION
        "Total Identification failure times due to algorithm or transform SN discrepancy."
    ::= { fsTermServiceStaticWithSSIDTableEntry 23}

fsTimeoutIdentificationFailTime OBJECT-TYPE
    SYNTAX INTEGER
    MAX-ACCESS read-only
    STATUS current
    DESCRIPTION
        "Total Identification failure times due to timeout."
    ::= { fsTermServiceStaticWithSSIDTableEntry 24}
    
fsInefficiencyIdentificationFailTime OBJECT-TYPE
    SYNTAX INTEGER
    MAX-ACCESS read-only
    STATUS current
    DESCRIPTION
        "Total Identification failure times due to inefficiency."
    ::= { fsTermServiceStaticWithSSIDTableEntry 25}
    
fsOtherReasonIdentificationFailTime OBJECT-TYPE
    SYNTAX INTEGER
    MAX-ACCESS read-only
    STATUS current
    DESCRIPTION
        "Total Identification failure times due to other reason."
    ::= { fsTermServiceStaticWithSSIDTableEntry 26}
    
fsTotalRemoveLinkVerifyFailTimes OBJECT-TYPE
    SYNTAX INTEGER
    MAX-ACCESS read-only
    STATUS current
    DESCRIPTION
        "Total failure times of removing link verification."
    ::= { fsTermServiceStaticWithSSIDTableEntry 27} 
    
fsLeaveAPCoverageRemoveLinkVerifyFailTimes OBJECT-TYPE
    SYNTAX INTEGER
    MAX-ACCESS read-only
    STATUS current
    DESCRIPTION
        "Total failure times due to leaving AP coverage area."
    ::= { fsTermServiceStaticWithSSIDTableEntry 28}   
    
fsInefficiencyRemoveLinkVerifyFailTime OBJECT-TYPE
    SYNTAX INTEGER
    MAX-ACCESS read-only
    STATUS current
    DESCRIPTION
        "Total remove link failure times due to inefficiency."
    ::= { fsTermServiceStaticWithSSIDTableEntry 29}  
    
fsLinkVerifyFailRemoveLinkVerifyFailTime OBJECT-TYPE
    SYNTAX INTEGER
    MAX-ACCESS read-only
    STATUS current
    DESCRIPTION
        "Total remove link failure times due to link verify failure."
    ::= { fsTermServiceStaticWithSSIDTableEntry 30}      

fsOtherReasonRemoveLinkVerifyFailTime OBJECT-TYPE
    SYNTAX INTEGER
    MAX-ACCESS read-only
    STATUS current
    DESCRIPTION
        "Total remove link failure times due to other reason."
    ::= { fsTermServiceStaticWithSSIDTableEntry 31} 

fsTotalRemoveLinkAssociationTimes OBJECT-TYPE
    SYNTAX INTEGER
    MAX-ACCESS read-only
    STATUS current
    DESCRIPTION
        "Total failure times of removing association."
    ::= { fsTermServiceStaticWithSSIDTableEntry 32}  
    
fsLeaveAPCoverageRemoveAssociationFailTimes OBJECT-TYPE
    SYNTAX INTEGER
    MAX-ACCESS read-only
    STATUS current
    DESCRIPTION
        "Total remove association failure times due to leaving AP coverage area."
    ::= { fsTermServiceStaticWithSSIDTableEntry 33}   
    
fsInefficiencyRemoveAssociationFailTime OBJECT-TYPE
    SYNTAX INTEGER
    MAX-ACCESS read-only
    STATUS current
    DESCRIPTION
        "Total remove association failure times due to inefficiency."
    ::= { fsTermServiceStaticWithSSIDTableEntry 34}  
    
fsAssociationFailRemoveAssociationFailTime OBJECT-TYPE
    SYNTAX INTEGER
    MAX-ACCESS read-only
    STATUS current
    DESCRIPTION
        "Total remove association failure times due to link verify failure."
    ::= { fsTermServiceStaticWithSSIDTableEntry 35}      

fsOtherReasonRemoveAssociationFailTime OBJECT-TYPE
    SYNTAX INTEGER
    MAX-ACCESS read-only
    STATUS current
    DESCRIPTION
        "Total remove association failure times due to other reason."
    ::= { fsTermServiceStaticWithSSIDTableEntry 36}
--*************************************************   
--*************************************************
fsTermServiceStationWithStationTable OBJECT-TYPE
    SYNTAX SEQUENCE OF FSTermServiceStationWithStationTableEntry
    MAX-ACCESS not-accessible
    STATUS current
    DESCRIPTION
        "Statistic of user MAC address by SSID."
    ::= { fsTermServiceSTatisticsWithStation 1	 }

fsTermServiceStationWithStationTableEntry OBJECT-TYPE
    SYNTAX FSTermServiceStationWithStationTableEntry
    MAX-ACCESS not-accessible
    STATUS current
    DESCRIPTION
        "The entry of apTermServiceStationWithStationTable."
    INDEX
    { fsApgWlanId,fsStaMacAddr}
    ::= { fsTermServiceStationWithStationTable 1 }

FSTermServiceStationWithStationTableEntry ::=
    SEQUENCE {
        fsStaAssociateTime         Counter32,
        fsRxStaDataFrams           Counter32,
        fsRXStaErrorFrams          Counter32,
        fsTxStaDataFrams           Counter32,
        fsReSendDataFrams          Counter32,
        fsStaRxAvgSpeed            INTEGER,
        fsStaTxAvgSpeed            INTEGER,
        fsStaThroughput            INTEGER,
        fsStaSignalStrength        INTEGER,
        fsStaSignalNoise           INTEGER
    } 
  
   
fsStaAssociateTime  OBJECT-TYPE
    SYNTAX Counter32
    MAX-ACCESS read-only
    STATUS current
    DESCRIPTION
        "station Associate to ap time ,unit is minute."
    ::= { fsTermServiceStationWithStationTableEntry 2}   
    
fsRxStaDataFrams   OBJECT-TYPE
    SYNTAX Counter32
    MAX-ACCESS read-only
    STATUS current
    DESCRIPTION
        "ap Rx station Data Frames ."
    ::= { fsTermServiceStationWithStationTableEntry 3}   
    
fsRXStaErrorFrams   OBJECT-TYPE
    SYNTAX Counter32
    MAX-ACCESS read-only
    STATUS current
    DESCRIPTION
        "ap Rx station Error Frames ."
    ::= { fsTermServiceStationWithStationTableEntry 4} 
    
fsTxStaDataFrams    OBJECT-TYPE
    SYNTAX Counter32
    MAX-ACCESS read-only
    STATUS current
    DESCRIPTION
        "ap Tx station Data Frames ."
    ::= { fsTermServiceStationWithStationTableEntry 5}     
    
fsReSendDataFrams    OBJECT-TYPE
    SYNTAX Counter32
    MAX-ACCESS read-only
    STATUS current
    DESCRIPTION
        "ap Resend station Data Frames ."
    ::= { fsTermServiceStationWithStationTableEntry 6}    
    
fsStaRxAvgSpeed OBJECT-TYPE
    SYNTAX INTEGER
    MAX-ACCESS read-only
    STATUS current
    DESCRIPTION
        "ap Send  to station average DATA speed ."
    ::= { fsTermServiceStationWithStationTableEntry 7}  
    
fsStaTxAvgSpeed   OBJECT-TYPE
    SYNTAX INTEGER
    MAX-ACCESS read-only
    STATUS current
    DESCRIPTION
        "ap Send  from station average DATA speed ."
    ::= { fsTermServiceStationWithStationTableEntry 8}  
    
fsStaThroughput  OBJECT-TYPE
    SYNTAX INTEGER
    MAX-ACCESS read-only
    STATUS current
    DESCRIPTION
        "station Throughput ."
    ::= { fsTermServiceStationWithStationTableEntry 9}  
    
fsStaSignalStrength  OBJECT-TYPE
    SYNTAX INTEGER
    MAX-ACCESS read-only
    STATUS current
    DESCRIPTION
        "ap receive station signal strength ."
    ::= { fsTermServiceStationWithStationTableEntry 10}   
    
fsStaSignalNoise  OBJECT-TYPE
    SYNTAX INTEGER
    MAX-ACCESS read-only
    STATUS current
    DESCRIPTION
        "ap receive station signal noise ."
    ::= { fsTermServiceStationWithStationTableEntry 11}                    
--*************************************************

---------------------------------------------------
---------------------------------------------------
fsTermServiceStaticWithAPTable  OBJECT-TYPE
    SYNTAX SEQUENCE OF FSTermServiceStaticWithAPTableEntry
    MAX-ACCESS not-accessible
    STATUS current
    DESCRIPTION
      "get Term Service Statistics With AP."
    ::={ fsTermServiceStatisticsWithAP 1 }
  
fsTermServiceStaticWithAPTableEntry OBJECT-TYPE
    SYNTAX  FSTermServiceStaticWithAPTableEntry
    MAX-ACCESS  not-accessible
    STATUS  current
    DESCRIPTION
        "get Term Service Statistics With AP"
    INDEX   { fsApMacAddr }
    ::= { fsTermServiceStaticWithAPTable 1 }

FSTermServiceStaticWithAPTableEntry ::=
    SEQUENCE {     
          fsUserAccumulateTime     Counter32,
          fsAssociaFailTimes       Counter32
          
    }
fsUserAccumulateTime OBJECT-TYPE
    SYNTAX Counter32
    MAX-ACCESS read-only
    STATUS current
    DESCRIPTION
        "Total accumulation time of all users that have connected to the AP."
    ::= { fsTermServiceStaticWithAPTableEntry 1}
    
fsAssociaFailTimes   OBJECT-TYPE
    SYNTAX Counter32
    MAX-ACCESS read-only
    STATUS current
    DESCRIPTION
        "Total Associate Fail times for the AP."
    ::= { fsTermServiceStaticWithAPTableEntry 2}  
--**************************************************
--* apTermServiceStatistics ends * 
--**************************************************

fsDOT11WIDSParamObjects     OBJECT IDENTIFIER  ::= { fsFitApMibModule 8 }
--**************************************************
--* apDot11WIDSInfoTable begins
--**************************************************
fsDot11WIDSInfoTable OBJECT-TYPE
    SYNTAX SEQUENCE OF FSDot11WIDSInfoEntry
    MAX-ACCESS not-accessible
    STATUS current
    DESCRIPTION
      "The table used to acac the configuration information of ac/ac."
    ::={ fsDOT11WIDSParamObjects 1 }

fsDot11WIDSInfoEntry OBJECT-TYPE
    SYNTAX FSDot11WIDSInfoEntry
    MAX-ACCESS not-accessible
    STATUS current
    DESCRIPTION
      "The entry of the table used to acac the configuration information of ac/ac."
    INDEX { fsDot11WIDSLocalIndex }
    ::={ fsDot11WIDSInfoTable 1 }

FSDot11WIDSInfoEntry ::=
    SEQUENCE {
        fsDot11WIDSLocalIndex                       INTEGER,
        fsDot11WIDSpermittedSSID                    DisplayString,
        fsDot11WIDSpermitBSSID                      MacAddress,
        fsDot11WIDSDeviceOUI                        DisplayString,
        fsDot11WIDSSuspiciousAPBSS                  MacAddress,
        fsDot11WIDSSuspiciousAPCount                INTEGER,
        fsDot11WIDSMomentFirstTimeDetectedSusAP     TimeTicks,
        fsDot11WIDSMomentLastTimeDetectedSusAP      TimeTicks,
        fsDot11WIDSSuspiciousAPSSID                 DisplayString,
        fsDot11WIDSSuspiciousAPMaxSignalStrength    INTEGER,
        fsDot11WIDSSuspiciousAPUsingChannel         INTEGER,
        fsDot11WIDSSuspiciousAPFrameEncrption       INTEGER,
        fsDot11WIDSSuspiciousAPNeedsDealingTag      TruthValue,
        fsDot11WIDSSuspiciousAPIgnoredTag           TruthValue,
        fsDot11WIDSSuspiciousSTAMAC                 MacAddress,
        fsDot11WIDSAPCountDetectingSuspiciousSTA    INTEGER,
        fsDot11WIDSMomentFirstTimeDetectedSusSTA    TimeTicks,
        fsDot11WIDSMomentLastTimeDetectedSusSTA     TimeTicks,
        fsDot11WIDSBSSIDSuspiciousSTAAccessing      MacAddress,
        fsDot11WIDSSuspiciousSTAMaxSignalStrength   INTEGER,
        fsDot11WIDSSuspiciousSTAUsingChannel        INTEGER,
        fsDot11WIDSSuspiciousSTAWorksInAdhocMode    TruthValue,
        fsDot11WIDSSuspiciousSTANeedsDealingTag     TruthValue,
        fsDot11WIDSSuspiciousSTAIgnoredTag          TruthValue,
        fsDot11WIDSFloodAttackDetectSwitch          TruthValue,
        fsDot11WIDSSpoofAttackDetectSwitch          TruthValue,
        fsDot11WIDSWeakIVDetectSwitch               TruthValue,
        fsDot11WIDSClearIllegalEquipmentHistroyTag  TruthValue,
        fsDot11WIDSClearAttackDetectionHistroyTag   TruthValue,
        fsDot11WIDSClearAttackDetectionStaticsTag   TruthValue
    }
    
fsDot11WIDSLocalIndex  OBJECT-TYPE
    SYNTAX  INTEGER
    MAX-ACCESS  not-accessible
    STATUS      current
    DESCRIPTION
        " The dot11 wids local index num ."
    ::= { fsDot11WIDSInfoEntry 1 }

fsDot11WIDSpermittedSSID OBJECT-TYPE
    SYNTAX  DisplayString
    MAX-ACCESS  read-only
    STATUS      current
    DESCRIPTION
        " The ssid permitted to access the service."
    ::= { fsDot11WIDSInfoEntry 2 }

fsDot11WIDSpermitBSSID OBJECT-TYPE
    SYNTAX  MacAddress
    MAX-ACCESS  read-only
    STATUS      current
    DESCRIPTION
        " The bssid permitted to access the service."
    ::= { fsDot11WIDSInfoEntry 3 }

fsDot11WIDSDeviceOUI OBJECT-TYPE
    SYNTAX  DisplayString
    MAX-ACCESS  read-only
    STATUS      current
    DESCRIPTION
        " The OUI whose device is permitted to provide the service."
    ::= { fsDot11WIDSInfoEntry 4 }

fsDot11WIDSSuspiciousAPBSS OBJECT-TYPE
    SYNTAX  MacAddress
    MAX-ACCESS  read-only
    STATUS      current
    DESCRIPTION
        " The BSS MAC of the Suspicious AP."
    ::= { fsDot11WIDSInfoEntry 5 }

fsDot11WIDSSuspiciousAPCount OBJECT-TYPE
    SYNTAX  INTEGER
    MAX-ACCESS  read-only
    STATUS      current
    DESCRIPTION
        " The count of the Suspicious AP."
    ::= { fsDot11WIDSInfoEntry 6 }

fsDot11WIDSMomentFirstTimeDetectedSusAP OBJECT-TYPE
    SYNTAX  TimeTicks
    MAX-ACCESS  read-only
    STATUS      current
    DESCRIPTION
        " The moment when the AP is detected as the Suspicious AP at the first time."
    ::= { fsDot11WIDSInfoEntry 7 }

fsDot11WIDSMomentLastTimeDetectedSusAP OBJECT-TYPE
    SYNTAX  TimeTicks
    MAX-ACCESS  read-only
    STATUS      current
    DESCRIPTION
        " The moment when the AP is detected as the Suspicious AP at the last time."
    ::= { fsDot11WIDSInfoEntry 8 }

fsDot11WIDSSuspiciousAPSSID OBJECT-TYPE
    SYNTAX  DisplayString
    MAX-ACCESS  read-only
    STATUS      current
    DESCRIPTION
        " The SSID of the Suspicious AP."
    ::= { fsDot11WIDSInfoEntry 9 }

fsDot11WIDSSuspiciousAPMaxSignalStrength OBJECT-TYPE
    SYNTAX  INTEGER
    MAX-ACCESS  read-only
    STATUS      current
    DESCRIPTION
        " The max signal strength of the Suspicious AP."
    ::= { fsDot11WIDSInfoEntry 10 }

fsDot11WIDSSuspiciousAPUsingChannel OBJECT-TYPE
    SYNTAX  INTEGER
    MAX-ACCESS  read-only
    STATUS      current
    DESCRIPTION
        " The channel the Suspicious AP is in."
    ::= { fsDot11WIDSInfoEntry 11 }

fsDot11WIDSSuspiciousAPFrameEncrption OBJECT-TYPE
    SYNTAX  INTEGER
    MAX-ACCESS  read-only
    STATUS      current
    DESCRIPTION
        " The frame encrption of the Suspicious AP."
    ::= { fsDot11WIDSInfoEntry 12 }

fsDot11WIDSSuspiciousAPNeedsDealingTag OBJECT-TYPE
    SYNTAX  TruthValue
    MAX-ACCESS  read-only
    STATUS      current
    DESCRIPTION
        " The tag telling whether it needs to deal the Suspicious AP."
    ::= { fsDot11WIDSInfoEntry 13 }

fsDot11WIDSSuspiciousAPIgnoredTag OBJECT-TYPE
    SYNTAX  TruthValue
    MAX-ACCESS  read-only
    STATUS      current
    DESCRIPTION
        " The tag telling whether to ignore the Suspicious AP."
    ::= { fsDot11WIDSInfoEntry 14 }

fsDot11WIDSSuspiciousSTAMAC OBJECT-TYPE
    SYNTAX  MacAddress
    MAX-ACCESS  read-only
    STATUS      current
    DESCRIPTION
        " The MAC of the the Suspicious STA."
    ::= { fsDot11WIDSInfoEntry 15 }

fsDot11WIDSAPCountDetectingSuspiciousSTA OBJECT-TYPE
    SYNTAX  INTEGER
    MAX-ACCESS  read-only
    STATUS      current
    DESCRIPTION
        " The AP count which is detecting the Suspicious STA."
    ::= { fsDot11WIDSInfoEntry 16 }

fsDot11WIDSMomentFirstTimeDetectedSusSTA OBJECT-TYPE
    SYNTAX  TimeTicks
    MAX-ACCESS  read-only
    STATUS      current
    DESCRIPTION
        " The moment when the STA is detected as the Suspicious STA at the first time."
    ::= { fsDot11WIDSInfoEntry 17 }

fsDot11WIDSMomentLastTimeDetectedSusSTA OBJECT-TYPE
    SYNTAX  TimeTicks
    MAX-ACCESS  read-only
    STATUS      current
    DESCRIPTION
        " The moment when the AP is detected as the Suspicious AP at the last time."
    ::= { fsDot11WIDSInfoEntry 18 }

fsDot11WIDSBSSIDSuspiciousSTAAccessing OBJECT-TYPE
    SYNTAX  MacAddress
    MAX-ACCESS  read-only
    STATUS      current
    DESCRIPTION
        " The BSSID which the the Suspicious STA is trying to access."
    ::= { fsDot11WIDSInfoEntry 19 }

fsDot11WIDSSuspiciousSTAMaxSignalStrength OBJECT-TYPE
    SYNTAX  INTEGER
    MAX-ACCESS  read-only
    STATUS      current
    DESCRIPTION
        " The max signal strength of the Suspicious STA."
    ::= { fsDot11WIDSInfoEntry 20 }

fsDot11WIDSSuspiciousSTAUsingChannel OBJECT-TYPE
    SYNTAX  INTEGER
    MAX-ACCESS  read-only
    STATUS      current
    DESCRIPTION
        " The channel the Suspicious sta is in."
    ::= { fsDot11WIDSInfoEntry 21 }

fsDot11WIDSSuspiciousSTAWorksInAdhocMode OBJECT-TYPE
    SYNTAX  TruthValue
    MAX-ACCESS  read-only
    STATUS      current
    DESCRIPTION
        " The tag whether the Suspicious STA is working in the Ad hoc mode."
    ::= { fsDot11WIDSInfoEntry 22 }


fsDot11WIDSSuspiciousSTANeedsDealingTag OBJECT-TYPE
    SYNTAX  TruthValue
    MAX-ACCESS  read-only
    STATUS      current
    DESCRIPTION
        " The tag telling whether it needs to deal the Suspicious STA."
    ::= { fsDot11WIDSInfoEntry 23 }

fsDot11WIDSSuspiciousSTAIgnoredTag OBJECT-TYPE
    SYNTAX  TruthValue
    MAX-ACCESS  read-write
    STATUS      current
    DESCRIPTION
        " The tag telling whether to ignore the Suspicious STA."
    ::= { fsDot11WIDSInfoEntry 24 }

fsDot11WIDSFloodAttackDetectSwitch OBJECT-TYPE
    SYNTAX  TruthValue
    MAX-ACCESS  read-write
    STATUS      current
    DESCRIPTION
        " This tag tells whether to enable flooding attack detecting."
    ::= { fsDot11WIDSInfoEntry 25 }

fsDot11WIDSSpoofAttackDetectSwitch OBJECT-TYPE
    SYNTAX  TruthValue
    MAX-ACCESS  read-write
    STATUS      current
    DESCRIPTION
        " This tag tells whether to enable spoof attack detecting."
    ::= { fsDot11WIDSInfoEntry 26 }

fsDot11WIDSWeakIVDetectSwitch OBJECT-TYPE
    SYNTAX  TruthValue
    MAX-ACCESS  read-write
    STATUS      current
    DESCRIPTION
        "This tag tells whether to enable weak IV detecting."
    ::= { fsDot11WIDSInfoEntry 27 }

fsDot11WIDSClearIllegalEquipmentHistroyTag OBJECT-TYPE
    SYNTAX  TruthValue
    MAX-ACCESS  read-write
    STATUS      current
    DESCRIPTION
        " This tag tells whether to clear the illegal equipment history."
    ::= { fsDot11WIDSInfoEntry 28 }

fsDot11WIDSClearAttackDetectionHistroyTag OBJECT-TYPE
    SYNTAX  TruthValue
    MAX-ACCESS  read-write
    STATUS      current
    DESCRIPTION
        " This tag tells whether to clear the attack detection history."
    ::= { fsDot11WIDSInfoEntry 29 }

fsDot11WIDSClearAttackDetectionStaticsTag OBJECT-TYPE
    SYNTAX  TruthValue
    MAX-ACCESS  read-write
    STATUS      current
    DESCRIPTION
        " This tag tells whether to clear the attack detection statics."
    ::= { fsDot11WIDSInfoEntry 30 }

--**************************************************
--* apDot11WIDSInfoTable ends
--**************************************************
--**************************************************
--* apDot11LawlessApInfoTable   starts
--**************************************************
fsDot11LawlessApInfoTable OBJECT-TYPE
    SYNTAX SEQUENCE OF FSDot11LawlessApInfoTableEntry
    MAX-ACCESS not-accessible
    STATUS current
    DESCRIPTION
      "The table used to display Lawless AP info t"
    ::={ fsDOT11WIDSParamObjects 2 }

fsDot11LawlessApInfoTableEntry OBJECT-TYPE
    SYNTAX FSDot11LawlessApInfoTableEntry
    MAX-ACCESS not-accessible
    STATUS current
    DESCRIPTION
      "The table used to display Lawless AP info "
    INDEX { fsLawlessAPIndex }
    ::={ fsDot11LawlessApInfoTable 1 }

FSDot11LawlessApInfoTableEntry ::=
    SEQUENCE {
          fsLawlessAPIndex               INTEGER,   
          fsLawlessAPSignalStrength      Integer32,
          fsLawlessAPSignalSNR           Integer32,
          fsLawlessAPChannelNum          INTEGER,
          fsLawlessAPSSIDName            DisplayString,   
          fsLawlessAPMacaddr             MacAddress,
          fsLawlessAPTreatMode           INTEGER
                        
    }
    
fsLawlessAPIndex     OBJECT-TYPE
    SYNTAX  INTEGER
    MAX-ACCESS  not-accessible
    STATUS      current
    DESCRIPTION
        " This is Lawless AP local Index number ."
    ::= { fsDot11LawlessApInfoTableEntry 1 }
    
fsLawlessAPSignalStrength    OBJECT-TYPE
    SYNTAX  Integer32
    MAX-ACCESS  read-only
    STATUS      current
    DESCRIPTION
        " This is Lawless AP signal Strength ."
    ::= { fsDot11LawlessApInfoTableEntry 2 } 
    
fsLawlessAPSignalSNR   OBJECT-TYPE
    SYNTAX  Integer32
    MAX-ACCESS  read-only
    STATUS      current
    DESCRIPTION
        " This is Lawless AP signal SNR ."
    ::= { fsDot11LawlessApInfoTableEntry 3 }   
    
fsLawlessAPChannelNum    OBJECT-TYPE
    SYNTAX  INTEGER
    MAX-ACCESS  read-only
    STATUS      current
    DESCRIPTION
        " This is Lawless AP Channel Number ."
    ::= { fsDot11LawlessApInfoTableEntry 4 }   
    
fsLawlessAPSSIDName  OBJECT-TYPE
    SYNTAX  DisplayString
    MAX-ACCESS  read-only
    STATUS      current
    DESCRIPTION
        " This is Lawless AP SSID Name display ."
    ::= { fsDot11LawlessApInfoTableEntry 5 }  
    
fsLawlessAPMacaddr  OBJECT-TYPE
    SYNTAX  MacAddress
    MAX-ACCESS  read-only
    STATUS      current
    DESCRIPTION
        " This is Lawless AP BSSID <MAC_ADDRESS> ."
    ::= { fsDot11LawlessApInfoTableEntry 6 }     

fsLawlessAPTreatMode   OBJECT-TYPE
    SYNTAX  INTEGER 
    MAX-ACCESS  read-only
    STATUS      current
    DESCRIPTION
        " This is Lawless AP Treat mode detail 1: DosAttack state
          2: disturb User connect to lawless AP ."
    ::= { fsDot11LawlessApInfoTableEntry 7 }     
         
--**************************************************
--* apLawlessApInfoTable   ends
--**************************************************

--**************************************************
--* apDot11UndefinedApInfoTable   starts
--**************************************************
fsDot11UndefinedApInfoTable OBJECT-TYPE
    SYNTAX SEQUENCE OF FSDot11UndefinedApInfoTableEntry
    MAX-ACCESS not-accessible
    STATUS current
    DESCRIPTION
      "The table used to display Undefined AP info t"
    ::={ fsDOT11WIDSParamObjects 3 }

fsDot11UndefinedApInfoTableEntry OBJECT-TYPE
    SYNTAX FSDot11UndefinedApInfoTableEntry
    MAX-ACCESS not-accessible
    STATUS current
    DESCRIPTION
      "The table used to display Undefined AP info "
    INDEX { fsUndefinedAPIndex }
    ::={ fsDot11UndefinedApInfoTable 1 }

FSDot11UndefinedApInfoTableEntry ::=
    SEQUENCE {
          fsUndefinedAPIndex               INTEGER,   
          fsUndefinedAPSignalStrength      Integer32,
          fsUndefinedAPSignalSNR           Integer32,
          fsUndefinedAPChannelNum          INTEGER,
          fsUndefinedAPSSIDName            DisplayString,   
          fsUndefinedAPMacaddr             MacAddress,
          fsUndefinedAPTreatMode           INTEGER
                        
    }
    
fsUndefinedAPIndex     OBJECT-TYPE
    SYNTAX  INTEGER
    MAX-ACCESS  not-accessible
    STATUS      current
    DESCRIPTION
        " This is Undefined AP local Index number ."
    ::= { fsDot11UndefinedApInfoTableEntry 1 }
    
fsUndefinedAPSignalStrength    OBJECT-TYPE
    SYNTAX  Integer32
    MAX-ACCESS  read-only
    STATUS      current
    DESCRIPTION
        " This is Undefined AP signal Strength ."
    ::= { fsDot11UndefinedApInfoTableEntry 2 } 
    
fsUndefinedAPSignalSNR   OBJECT-TYPE
    SYNTAX  Integer32
    MAX-ACCESS  read-only
    STATUS      current
    DESCRIPTION
        " This is Undefined AP signal SNR ."
    ::= { fsDot11UndefinedApInfoTableEntry 3 }   
    
fsUndefinedAPChannelNum    OBJECT-TYPE
    SYNTAX  INTEGER
    MAX-ACCESS  read-only
    STATUS      current
    DESCRIPTION
        " This is Undefined AP Channel Number ."
    ::= { fsDot11UndefinedApInfoTableEntry 4 }   
    
fsUndefinedAPSSIDName  OBJECT-TYPE
    SYNTAX  DisplayString
    MAX-ACCESS  read-only
    STATUS      current
    DESCRIPTION
        " This is Undefined AP SSID Name display ."
    ::= { fsDot11UndefinedApInfoTableEntry 5 }  
    
fsUndefinedAPMacaddr  OBJECT-TYPE
    SYNTAX  MacAddress
    MAX-ACCESS  read-only
    STATUS      current
    DESCRIPTION
        " This is Undefined AP BSSID <MAC_ADDRESS> ."
    ::= { fsDot11UndefinedApInfoTableEntry 6 }     

fsUndefinedAPTreatMode   OBJECT-TYPE
    SYNTAX  INTEGER 
    MAX-ACCESS  read-only
    STATUS      current
    DESCRIPTION
        " This is Undefined AP Treat mode detail 1: DosAttack state
          2: disturb User connect to lawless AP ."
    ::= { fsDot11UndefinedApInfoTableEntry 7 }     
         
--**************************************************
--* fsUndefinedApInfoTable   ends
--**************************************************

--**************************************************
--* apDot11LegalityApInfoTable   starts
--**************************************************
fsDot11LegalityApInfoTable OBJECT-TYPE
    SYNTAX SEQUENCE OF FSDot11LegalityApInfoTableEntry
    MAX-ACCESS not-accessible
    STATUS current
    DESCRIPTION
      "The table used to display Legality AP info t"
    ::={ fsDOT11WIDSParamObjects 4 }

fsDot11LegalityApInfoTableEntry OBJECT-TYPE
    SYNTAX FSDot11LegalityApInfoTableEntry
    MAX-ACCESS not-accessible
    STATUS current
    DESCRIPTION
      "The table used to display Legality AP info "
    INDEX { fsLegalityAPIndex }
    ::={ fsDot11LegalityApInfoTable 1 }

FSDot11LegalityApInfoTableEntry ::=
    SEQUENCE {
          fsLegalityAPIndex               INTEGER,   
          fsLegalityAPSignalStrength      Integer32,
          fsLegalityAPSignalSNR           Integer32,
          fsLegalityAPChannelNum          INTEGER,
          fsLegalityAPSSIDName            DisplayString,   
          fsLegalityAPMacaddr             MacAddress,
          fsLegalityAPTreatMode           INTEGER
                        
    }
    
fsLegalityAPIndex     OBJECT-TYPE
    SYNTAX  INTEGER
    MAX-ACCESS  not-accessible
    STATUS      current
    DESCRIPTION
        " This is Legality AP local Index number ."
    ::= { fsDot11LegalityApInfoTableEntry 1 }
    
fsLegalityAPSignalStrength    OBJECT-TYPE
    SYNTAX  Integer32
    MAX-ACCESS  read-only
    STATUS      current
    DESCRIPTION
        " This is Legality AP signal Strength ."
    ::= { fsDot11LegalityApInfoTableEntry 2 } 
    
fsLegalityAPSignalSNR   OBJECT-TYPE
    SYNTAX  Integer32
    MAX-ACCESS  read-only
    STATUS      current
    DESCRIPTION
        " This is Legality AP signal SNR ."
    ::= { fsDot11LegalityApInfoTableEntry 3 }   
    
fsLegalityAPChannelNum    OBJECT-TYPE
    SYNTAX  INTEGER
    MAX-ACCESS  read-only
    STATUS      current
    DESCRIPTION
        " This is Legality AP Channel Number ."
    ::= { fsDot11LegalityApInfoTableEntry 4 }   
    
fsLegalityAPSSIDName  OBJECT-TYPE
    SYNTAX  DisplayString
    MAX-ACCESS  read-only
    STATUS      current
    DESCRIPTION
        " This is Legality AP SSID Name display ."
    ::= { fsDot11LegalityApInfoTableEntry 5 }  
    
fsLegalityAPMacaddr  OBJECT-TYPE
    SYNTAX  MacAddress
    MAX-ACCESS  read-only
    STATUS      current
    DESCRIPTION
        " This is Legality AP BSSID <MAC_ADDRESS> ."
    ::= { fsDot11LegalityApInfoTableEntry 6 }     

fsLegalityAPTreatMode   OBJECT-TYPE
    SYNTAX  INTEGER 
    MAX-ACCESS  read-only
    STATUS      current
    DESCRIPTION
        " This is Legality AP Treat mode detail 1: DosAttack state
          2: disturb User connect to lawless AP ."
    ::= { fsDot11LegalityApInfoTableEntry 7 }     
         
--**************************************************
--* fsLegalityApInfoTable   ends
--**************************************************

--**********************************************
--*  apSSIDListCreateTable starts
--**********************************************
--apSSIDConfigObjects              OBJECT IDENTIFIER  ::= { fsFitApMibModule 9 }   please see china mobile node ApSSIDListCreateTableEntry
--apSSIDListCreateTable OBJECT-TYPE
--    SYNTAX SEQUENCE OF ApSSIDListCreateTableEntry
--    MAX-ACCESS not-accessible
--    STATUS current
--    DESCRIPTION
--      "The SSID list manegment for ap."
--    ::={ apSSIDConfigObjects 1 }

--apSSIDListCreateTableEntry OBJECT-TYPE
--    SYNTAX  ApSSIDListCreateTableEntry
--    MAX-ACCESS  not-accessible
--    STATUS  current
--    DESCRIPTION
--        "The SSID list manegment for ap"
--    INDEX   {fsgWlanId} 
--    ::= { apSSIDListCreateTable 1 }
    
--ApSSIDListCreateTableEntry ::=
--    SEQUENCE {
--         apListBSSIDAddr   MacAddress,
--         apSSIDRadioNum    INTEGER,
--         apSSIDApMACaddr   MacAddress
--    }
--**********************************************
--*apSSIDListCreateTable ends
--**********************************************
END

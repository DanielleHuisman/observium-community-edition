-- *****************************************************************
-- FS-WLAN-WLOG-MIB.mib:  FS WLAN WLOG MIB file
--
-- October 2012, jiangweifeng
-- 
-- Copyright (c) 2012 by FS.COM Inc..
-- All rights reserved.
-- *****************************************************************


FS-WLAN-WLOG-MIB DEFINITIONS ::= BEGIN

IMPORTS
    MODULE-IDENTITY, 
    OBJECT-TYPE,
    Integer32,
    IpAddress
        FROM SNMPv2-SMI
    MacAddress,
    DisplayString
        FROM SNMPv2-TC
    InetAddress,
    InetAddressType
        FROM INET-ADDRESS-MIB
    fsMgmt
        FROM FS-SMI;

fsWlanWlogMIB MODULE-IDENTITY
    LAST-UPDATED "201210100000Z"
    ORGANIZATION "FS.COM Inc.."
    CONTACT-INFO
            " 
            Tel: 400-865-2852 
                
            E-mail: https://www.fs.com/live_chat_service_mail.html"
    DESCRIPTION
            "This module defines wlan wlog mibs."
    REVISION  "201210100000Z"
    DESCRIPTION
            "Initial version of this mib."
    ::= { fsMgmt 118 }

-- ******** define the notify nodes ***************
fsWlanWlogNotificationsMIBObjects OBJECT IDENTIFIER      ::= { fsWlanWlogMIB 1 }
fsWlanWlogNtfObjects       OBJECT IDENTIFIER ::= { fsWlanWlogNotificationsMIBObjects 1 }
fsWlanWlogNotifications     OBJECT IDENTIFIER ::= { fsWlanWlogNotificationsMIBObjects 2 }

-- ****************************************
--
--               Notifications Objects
--
-- ****************************************
fsWlogNotifyApName OBJECT-TYPE
    SYNTAX      DisplayString
    MAX-ACCESS  accessible-for-notify
    STATUS      current
    DESCRIPTION
        "Represents the name of a WTP."
    ::= { fsWlanWlogNtfObjects 1 }

fsWlogNotifyApMac OBJECT-TYPE
    SYNTAX      MacAddress
    MAX-ACCESS  accessible-for-notify
    STATUS      current
    DESCRIPTION
        "Represents the unique identifier of a WTP."
    ::= { fsWlanWlogNtfObjects 2 }

fsWlogNotifyApIp OBJECT-TYPE
    SYNTAX      InetAddress
    MAX-ACCESS  accessible-for-notify
    STATUS      current
    DESCRIPTION
        "Represents the Ip address of a WTP."
    ::= { fsWlanWlogNtfObjects 3 }

fsWlogNotifyApCwDownId OBJECT-TYPE
    SYNTAX      INTEGER
    MAX-ACCESS  accessible-for-notify
    STATUS      current
    DESCRIPTION
        "Represents the identification for a WTP's capwap down incident."
    ::= { fsWlanWlogNtfObjects 4 }

fsWlogNotifyApCwDownReason OBJECT-TYPE
    SYNTAX      DisplayString
    MAX-ACCESS  accessible-for-notify
    STATUS      current
    DESCRIPTION
        "Represents the reason for a WTP's capwap down."
    ::= { fsWlanWlogNtfObjects 5 }

-- **** define AP ethernet interface statistics table ****
fsWlogNotifyApIntfStatTable OBJECT-TYPE
    SYNTAX      SEQUENCE OF FSWlogNotifyApIntfStatEntry
    MAX-ACCESS  accessible-for-notify
    STATUS      current
    DESCRIPTION
        "Represents the ethernet interface statistics table of a WTP."
    ::= { fsWlanWlogNtfObjects 6 }

fsWlogNotifyApIntfStatEntry OBJECT-TYPE
    SYNTAX      FSWlogNotifyApIntfStatEntry
    MAX-ACCESS  accessible-for-notify
    STATUS      current
    DESCRIPTION
        "Represents the WTP ethernet interface statistics table Entry."
    INDEX   { fsWlogNotifyApIntfName}
    ::= { fsWlogNotifyApIntfStatTable 1 }

FSWlogNotifyApIntfStatEntry ::=
    SEQUENCE {
        fsWlogNotifyApIntfName                    DisplayString,
        fsWlogNotifyApIntfInputRate               INTEGER,
        fsWlogNotifyApIntfOutputRate              INTEGER,
        fsWlogNotifyApIntfUnicastInputPkts        INTEGER,
        fsWlogNotifyApIntfUnicastOutputPkts       INTEGER,
        fsWlogNotifyApIntfMulticastInputPkts      INTEGER,
        fsWlogNotifyApIntfMulticastOutputPkts     INTEGER,
        fsWlogNotifyApIntfBroadcastInputPkts      INTEGER,
        fsWlogNotifyApIntfBroadcastOutputPkts     INTEGER,
        fsWlogNotifyApIntfErrorInputPkts          INTEGER,
        fsWlogNotifyApIntfErrorOutputPkts         INTEGER
     }

fsWlogNotifyApIntfName OBJECT-TYPE
    SYNTAX      DisplayString
    MAX-ACCESS  accessible-for-notify
    STATUS      current
    DESCRIPTION
        "Represents the name of a interface of a WTP."
    ::= { fsWlogNotifyApIntfStatEntry 1 }

fsWlogNotifyApIntfInputRate OBJECT-TYPE
    SYNTAX      INTEGER
    MAX-ACCESS  accessible-for-notify
    STATUS      current
    DESCRIPTION
        "AP's ethernet interface's input rate(Kbps) in 5 mins."
    ::= { fsWlogNotifyApIntfStatEntry 2 }

fsWlogNotifyApIntfOutputRate OBJECT-TYPE
    SYNTAX      INTEGER
    MAX-ACCESS  accessible-for-notify
    STATUS      current
    DESCRIPTION
        "AP's ethernet interface's output rate(Kbps) in 5 mins."
    ::= { fsWlogNotifyApIntfStatEntry 3 }

fsWlogNotifyApIntfUnicastInputPkts OBJECT-TYPE
    SYNTAX      INTEGER
    MAX-ACCESS  accessible-for-notify
    STATUS      current
    DESCRIPTION
        "AP's ethernet interface's unicast input packets."
    ::= { fsWlogNotifyApIntfStatEntry 4 }

fsWlogNotifyApIntfUnicastOutputPkts OBJECT-TYPE
    SYNTAX      INTEGER
    MAX-ACCESS  accessible-for-notify
    STATUS      current
    DESCRIPTION
        "AP's ethernet interface's unicast output packets."
    ::= { fsWlogNotifyApIntfStatEntry 5 }

fsWlogNotifyApIntfMulticastInputPkts OBJECT-TYPE
    SYNTAX      INTEGER
    MAX-ACCESS  accessible-for-notify
    STATUS      current
    DESCRIPTION
        "AP's ethernet interface's multicast input packets."
    ::= { fsWlogNotifyApIntfStatEntry 6 }

fsWlogNotifyApIntfMulticastOutputPkts OBJECT-TYPE
    SYNTAX      INTEGER
    MAX-ACCESS  accessible-for-notify
    STATUS      current
    DESCRIPTION
        "AP's ethernet interface's multicast output packets."
    ::= { fsWlogNotifyApIntfStatEntry 7 }

fsWlogNotifyApIntfBroadcastInputPkts OBJECT-TYPE
    SYNTAX      INTEGER
    MAX-ACCESS  accessible-for-notify
    STATUS      current
    DESCRIPTION
        "AP's ethernet interface's broadcast input packets."
    ::= { fsWlogNotifyApIntfStatEntry 8 }

fsWlogNotifyApIntfBroadcastOutputPkts OBJECT-TYPE
    SYNTAX      INTEGER
    MAX-ACCESS  accessible-for-notify
    STATUS      current
    DESCRIPTION
        "AP's ethernet interface's broadcast output packets."
    ::= { fsWlogNotifyApIntfStatEntry 9 }

fsWlogNotifyApIntfErrorInputPkts OBJECT-TYPE
    SYNTAX      INTEGER
    MAX-ACCESS  accessible-for-notify
    STATUS      current
    DESCRIPTION
        "AP's ethernet interface's error input packets."
    ::= { fsWlogNotifyApIntfStatEntry 10 }

fsWlogNotifyApIntfErrorOutputPkts OBJECT-TYPE
    SYNTAX      INTEGER
    MAX-ACCESS  accessible-for-notify
    STATUS      current
    DESCRIPTION
        "AP's ethernet interface's error output packets."
    ::= { fsWlogNotifyApIntfStatEntry 11 }

-- **** define AP's radio statistics table ****
fsWlogNotifyApRadioStatTable OBJECT-TYPE
    SYNTAX      SEQUENCE OF FSWlogNotifyApRadioStatEntry
    MAX-ACCESS  accessible-for-notify
    STATUS      current
    DESCRIPTION
        "Represents the radio statistics table of a WTP."
    ::= { fsWlanWlogNtfObjects 7 }

fsWlogNotifyApRadioStatEntry OBJECT-TYPE
    SYNTAX      FSWlogNotifyApRadioStatEntry
    MAX-ACCESS  accessible-for-notify
    STATUS      current
    DESCRIPTION
        "Represents the WTP radio statistics table Entry."
    INDEX   { fsWlogNotifyApRadioId}
    ::= { fsWlogNotifyApRadioStatTable 1 }

FSWlogNotifyApRadioStatEntry ::=
    SEQUENCE {
        fsWlogNotifyApRadioId             INTEGER,
        fsWlogNotifyApRadioWorkChnl       INTEGER,
        fsWlogNotifyApRadioPower          INTEGER,
        fsWlogNotifyApRadioRssi           INTEGER,
        fsWlogNotifyApRadioErrFrame       INTEGER,
        fsWlogNotifyApRadioRetrsmit       INTEGER,
        fsWlogNotifyApRadioTotalStaNum    INTEGER,
        fsWlogNotifyApRadioWebStaNum      INTEGER,
        fsWlogNotifyApRadioD1xStaNum      INTEGER
     }

fsWlogNotifyApRadioId OBJECT-TYPE
    SYNTAX      INTEGER
    MAX-ACCESS  accessible-for-notify
    STATUS      current
    DESCRIPTION
        "AP's radio id."
    ::= { fsWlogNotifyApRadioStatEntry 1 }

fsWlogNotifyApRadioWorkChnl OBJECT-TYPE
    SYNTAX      INTEGER
    MAX-ACCESS  accessible-for-notify
    STATUS      current
    DESCRIPTION
        "AP's radio work channel."
    ::= { fsWlogNotifyApRadioStatEntry 2 }

fsWlogNotifyApRadioPower OBJECT-TYPE
    SYNTAX      INTEGER
    MAX-ACCESS  accessible-for-notify
    STATUS      current
    DESCRIPTION
        "AP's radio work power."
    ::= { fsWlogNotifyApRadioStatEntry 3 }

fsWlogNotifyApRadioRssi OBJECT-TYPE
    SYNTAX      INTEGER
    MAX-ACCESS  accessible-for-notify
    STATUS      current
    DESCRIPTION
        "AP's radio 's RSSI(received signal strength indicator)."
    ::= { fsWlogNotifyApRadioStatEntry 4 }

fsWlogNotifyApRadioErrFrame OBJECT-TYPE
    SYNTAX      INTEGER
    MAX-ACCESS  accessible-for-notify
    STATUS      current
    DESCRIPTION
        "AP's radio's total error frame number."
    ::= { fsWlogNotifyApRadioStatEntry 5 }

fsWlogNotifyApRadioRetrsmit OBJECT-TYPE
    SYNTAX      INTEGER
    MAX-ACCESS  accessible-for-notify
    STATUS      current
    DESCRIPTION
        "AP's radio's total Retransmitted frame number."
    ::= { fsWlogNotifyApRadioStatEntry 6 }

fsWlogNotifyApRadioTotalStaNum OBJECT-TYPE
    SYNTAX      INTEGER
    MAX-ACCESS  accessible-for-notify
    STATUS      current
    DESCRIPTION
        "AP's radio's total online sta number."
    ::= { fsWlogNotifyApRadioStatEntry 7 }

fsWlogNotifyApRadioWebStaNum OBJECT-TYPE
    SYNTAX      INTEGER
    MAX-ACCESS  accessible-for-notify
    STATUS      current
    DESCRIPTION
        "AP's radio's web authenticated sta number."
    ::= { fsWlogNotifyApRadioStatEntry 8 }

fsWlogNotifyApRadioD1xStaNum OBJECT-TYPE
    SYNTAX      INTEGER
    MAX-ACCESS  accessible-for-notify
    STATUS      current
    DESCRIPTION
        "AP's radio's dot1x authenticated sta number."
    ::= { fsWlogNotifyApRadioStatEntry 9 }

-- **** define STA Operation notification objects ****
fsWlogNotifyStaMac OBJECT-TYPE
    SYNTAX      MacAddress
    MAX-ACCESS  accessible-for-notify
    STATUS      current
    DESCRIPTION
        "Represents the unique identifier of a STA."
    ::= { fsWlanWlogNtfObjects 8 }

fsWlogNotifyStaIp OBJECT-TYPE
    SYNTAX      IpAddress
    MAX-ACCESS  accessible-for-notify
    STATUS      current
    DESCRIPTION
        "Represents Ipv4 address of a STA."
    ::= { fsWlanWlogNtfObjects 9 }

fsWlogNotifyStaIpv6 OBJECT-TYPE
    SYNTAX      InetAddress
    MAX-ACCESS  accessible-for-notify
    STATUS      current
    DESCRIPTION
        "Represents Ipv6 address of a STA."
    ::= { fsWlanWlogNtfObjects 10 }

fsWlogNotifySsid OBJECT-TYPE
    SYNTAX      DisplayString
    MAX-ACCESS  accessible-for-notify
    STATUS      current
    DESCRIPTION
        "Represents the Wlan Ssid."
    ::= { fsWlanWlogNtfObjects 11 }

fsWlogNotifyStaRssi OBJECT-TYPE
    SYNTAX      INTEGER
    MAX-ACCESS  accessible-for-notify
    STATUS      current
    DESCRIPTION
        "Represents STA's RSSI(received signal strength indicator)."
    ::= { fsWlanWlogNtfObjects 12 }

fsWlogNotifyStaLinkrate OBJECT-TYPE
    SYNTAX      INTEGER
    MAX-ACCESS  accessible-for-notify
    STATUS      current
    DESCRIPTION
        "Represents STA's link rate(Kbps)."
    ::= { fsWlanWlogNtfObjects 13 }

fsWlogNotifyStaOperType OBJECT-TYPE
    SYNTAX      INTEGER
    MAX-ACCESS  accessible-for-notify
    STATUS      current
    DESCRIPTION
        "Represents the STA's normal operation, 
        1-associate,
        2-disassociate,
        3-roam in,
        4-roam out,
        5-ip update,
        6-ipv6 update."
    ::= { fsWlanWlogNtfObjects 14 }

fsWlogNotifyStaAbnormalOperType OBJECT-TYPE
    SYNTAX      INTEGER
    MAX-ACCESS  accessible-for-notify
    STATUS      current
    DESCRIPTION
        "Represents the STA's abnormal operation, 
        1-associate fail,
        2-offline,
        3-roam fail,
        4-dot1x authenticate fail,
        5-web authenticate fail."
    ::= { fsWlanWlogNtfObjects 15 }

fsWlogNotifyStaOperReason OBJECT-TYPE
    SYNTAX      DisplayString
    MAX-ACCESS  accessible-for-notify
    STATUS      current
    DESCRIPTION
        "Represents the reason of STA's abnormal operation"
    ::= { fsWlanWlogNtfObjects 16 }

-- ****************************************
--
--               Notify nodes
--
-- ****************************************
fsNotifyApCapwapDownReason NOTIFICATION-TYPE
    OBJECTS     {
                  fsWlogNotifyApName,
                  fsWlogNotifyApMac,
                  fsWlogNotifyApIp,
                  fsWlogNotifyApCwDownId,
                  fsWlogNotifyApCwDownReason
                }
    STATUS      current
    DESCRIPTION
        "This notification is sent by the AC when an AP's capwap down."
    ::= { fsWlanWlogNotifications 1 }

fsNotifyApCapwapDownIntf NOTIFICATION-TYPE
    OBJECTS     {
                  fsWlogNotifyApName,
                  fsWlogNotifyApMac,
                  fsWlogNotifyApIp,
                  fsWlogNotifyApCwDownId,
                  fsWlogNotifyApIntfName,
                  fsWlogNotifyApIntfInputRate,
                  fsWlogNotifyApIntfOutputRate,
                  fsWlogNotifyApIntfUnicastInputPkts,
                  fsWlogNotifyApIntfUnicastOutputPkts,
                  fsWlogNotifyApIntfMulticastInputPkts,
                  fsWlogNotifyApIntfMulticastOutputPkts,
                  fsWlogNotifyApIntfBroadcastInputPkts,
                  fsWlogNotifyApIntfBroadcastOutputPkts,
                  fsWlogNotifyApIntfErrorInputPkts,
                  fsWlogNotifyApIntfErrorOutputPkts
                }
    STATUS      current
    DESCRIPTION
        "This notification is sent by the AC when an AP's capwap down."
    ::= { fsWlanWlogNotifications 2 }

fsNotifyApCapwapDownRadio NOTIFICATION-TYPE
    OBJECTS     {
                  fsWlogNotifyApName,
                  fsWlogNotifyApMac,
                  fsWlogNotifyApIp,
                  fsWlogNotifyApCwDownId,
                  fsWlogNotifyApRadioId,
                  fsWlogNotifyApRadioWorkChnl,
                  fsWlogNotifyApRadioPower,
                  fsWlogNotifyApRadioRssi,
                  fsWlogNotifyApRadioErrFrame,
                  fsWlogNotifyApRadioRetrsmit,
                  fsWlogNotifyApRadioTotalStaNum,
                  fsWlogNotifyApRadioWebStaNum,
                  fsWlogNotifyApRadioD1xStaNum
                }
    STATUS      current
    DESCRIPTION
        "This notification is sent by the AC when an AP's capwap down."
    ::= { fsWlanWlogNotifications 3 }

fsNotifyStaOper NOTIFICATION-TYPE
    OBJECTS     {
                  fsWlogNotifyStaMac,
                  fsWlogNotifyStaIp,
                  fsWlogNotifyStaIpv6,
                  fsWlogNotifyStaRssi,
                  fsWlogNotifyStaLinkrate,
                  fsWlogNotifyApName,
                  fsWlogNotifySsid,
                  fsWlogNotifyStaOperType
                }
    STATUS      current
    DESCRIPTION
        "This notification is sent by the AC when an STA 
        associate/disassociate or roam in/out or ip address update."
    ::= { fsWlanWlogNotifications 4 }

fsNotifyStaAbnormalOper NOTIFICATION-TYPE
    OBJECTS     {
                  fsWlogNotifyStaMac,
                  fsWlogNotifyStaIp,
                  fsWlogNotifyStaIpv6,
                  fsWlogNotifyStaAbnormalOperType,
                  fsWlogNotifyStaOperReason
                }
    STATUS      current
    DESCRIPTION
        "This notification is sent by the AC when an STA 
        associate fail or abnormal offline or roam fail 
        or dot1x/web authenticate failed."
    ::= { fsWlanWlogNotifications 5 }

END

------------------------------------------------------------------------------
--
--  File           : ngponMib.mi2
--  Description    : gpon new platform configuration MIB
--  Version        : 1.0
--  Date           : July 14, 2016

--  Copyright (c) 2016-2020 Genexis Systems, Inc.  All Rights Reserved.
--
------------------------------------------------------------------------------

NGPON-MIB DEFINITIONS ::= BEGIN

IMPORTS
    MODULE-IDENTITY, OBJECT-TYPE,
    Counter32, Unsigned32, TimeTicks             FROM SNMPv2-SMI
    TimeInterval, RowStatus, TruthValue,  
      TEXTUAL-CONVENTION, MacAddress             FROM SNMPv2-TC
    dataCom                                      FROM ADMIN-MASTER-MIB
    MODULE-COMPLIANCE, OBJECT-GROUP              FROM SNMPv2-CONF;


ngpon           OBJECT IDENTIFIER ::= { dataCom 14 }



-- gpon function ------------------------------------------
gponConfig      OBJECT IDENTIFIER ::= { ngpon 1 }
gponStatus      OBJECT IDENTIFIER ::= { ngpon 2 }
oemTrue         OBJECT IDENTIFIER ::= { ngpon 3 }
gponSwitch      OBJECT IDENTIFIER ::= { ngpon 4 }

configDevice    OBJECT IDENTIFIER ::= { gponConfig 1 }
configSlot      OBJECT IDENTIFIER ::= { gponConfig 2 }
configPport     OBJECT IDENTIFIER ::= { gponConfig 3 }
configOnt       OBJECT IDENTIFIER ::= { gponConfig 4 }
statusDevice    OBJECT IDENTIFIER ::= { gponStatus 1 }
statusSlot      OBJECT IDENTIFIER ::= { gponStatus 2 }
statusPport     OBJECT IDENTIFIER ::= { gponStatus 3 }
statusOnt       OBJECT IDENTIFIER ::= { gponStatus 4 }
statusTrap      OBJECT IDENTIFIER ::= { gponStatus 5 }

--------------------------------------------------------------
------------------ 1.1. config device ----------------------
--------------------------------------------------------------
-- 1.1.1. deployControl
-- 1.1.2. deployInactive
-- 1.1.3. deployActive
-- 1.1.4. deployDemo
-- 1.1.5. configDeviceBaseInfo

-- 1.1.1. deployControl ------------------------------------
deployControl OBJECT IDENTIFIER ::= { configDevice 1 }

deployPermission  OBJECT-TYPE
    SYNTAX      INTEGER (0..1)
    MAX-ACCESS  read-write
    STATUS      current
    DESCRIPTION
        "Set deployPermission = 0 to request permission.
         Set deployPermission = 1 to release permission.
         When read, the value is always 0."
    ::= { deployControl 1 }

deployAction    OBJECT-TYPE
    SYNTAX      INTEGER (0..2)
    MAX-ACCESS  read-write
    STATUS      current
    DESCRIPTION
        "Set deployAction = 0 to active the deploy.
         Set deployAction = 1 to rebuild the deploy.
         Set deployAction = 2 to clear the deploy.
         When read, the value is always 0."
    ::= { deployControl 2 }

-- 1.1.2. deployInactive ----------------------------------
deployInactive OBJECT IDENTIFIER ::= { configDevice 2 }

-- 1.1.2.1. inactiveTrafficConfig 
-- 1.1.2.2. inactiveDbaTable
-- 1.1.2.3. inactiveLineCommonConfig
-- 1.1.2.4. inactiveLineSFUConfig
-- 1.1.2.5. inactiveLineHGUConfig
-- 1.1.2.6. inactiveRuleTable
-- 1.1.2.7. inactiveUniqueConfig
-- 1.1.2.8. inactiveCtrlMcastConfig   
-- 1.1.2.9. inactiveCtrlAlarmConfig

-- 1.1.2.1. inactiveTrafficConfig --------------------------
inactiveTrafficConfig OBJECT IDENTIFIER ::= { deployInactive 1 }

-- 1.1.2.1.1. inactiveVlanTable
-- 1.1.2.1.2. inactiveUsTrafficTable
-- 1.1.2.1.3. inactiveDsTrafficTable
-- 1.1.2.1.4. inactiveVlanPrimaryTable

-- 1.1.2.1.1. inactiveVlanTable --------------------------

inactiveVlanTable  OBJECT-TYPE
        SYNTAX      SEQUENCE OF InactiveVlanEntry
        MAX-ACCESS  not-accessible
        STATUS      current
        DESCRIPTION
            "inactive vlan table."
        ::= { inactiveTrafficConfig 1 }

inactiveVlanEntry  OBJECT-TYPE
        SYNTAX      InactiveVlanEntry
        MAX-ACCESS  not-accessible
        STATUS      current
        DESCRIPTION
            "entry of inactive vlan table"
        INDEX { inactiveVlanIndex, inactiveVlanSubIndex }
        ::= { inactiveVlanTable 1 }

InactiveVlanEntry  ::= 
        SEQUENCE 
        {
            inactiveVlanIndex         INTEGER,
            inactiveVlanSubIndex      INTEGER, 
            inactiveVlanAction        INTEGER,
            inactiveVlanOldVid        INTEGER,
            inactiveVlanOldPriority   INTEGER,
            inactiveVlanNewVid        INTEGER,
            inactiveVlanNewPriority   INTEGER,
            inactiveVlanRowStatus     RowStatus
        }

inactiveVlanIndex  OBJECT-TYPE    
    SYNTAX      INTEGER(0..2047)
    MAX-ACCESS  read-only
    STATUS      current
    DESCRIPTION
        "The index of inactive vlan table, should be inputted with <0-2047>.
         The range is not always fit, please see range in commands."
    ::= { inactiveVlanEntry 1 }

inactiveVlanSubIndex  OBJECT-TYPE    
    SYNTAX      INTEGER(1..32)
    MAX-ACCESS  read-only
    STATUS      current
    DESCRIPTION
        "The 2nd index of inactive vlan table, should be inputted with <1-32>."
    ::= { inactiveVlanEntry 2 }

inactiveVlanAction OBJECT-TYPE    
    SYNTAX      INTEGER(0..2)
    MAX-ACCESS  read-write
    STATUS      current
    DESCRIPTION
        "inactiveVlanAction:
         0  NULL
         1  translate
         2  add
         3  add default"
    ::= { inactiveVlanEntry 3 }

inactiveVlanOldVid  OBJECT-TYPE
    SYNTAX      INTEGER(1..4094)
    MAX-ACCESS  read-write
    STATUS      current
    DESCRIPTION
        "old vid, or inner vid, should in <1-4094>."
    ::= { inactiveVlanEntry 4 }

inactiveVlanOldPriority  OBJECT-TYPE
    SYNTAX      INTEGER(0..7)
    MAX-ACCESS  read-write
    STATUS      current
    DESCRIPTION
        "old priority, or inner priority, should in <0-7>."
    ::= { inactiveVlanEntry 5 }

inactiveVlanNewVid  OBJECT-TYPE
    SYNTAX      INTEGER(1..4094)
    MAX-ACCESS  read-write
    STATUS      current
    DESCRIPTION
        "new vid, or outer vid, or default vid, should in <1-4094>."
    ::= { inactiveVlanEntry 6 }

inactiveVlanNewPriority  OBJECT-TYPE
    SYNTAX      INTEGER(0..7)
    MAX-ACCESS  read-write
    STATUS      current
    DESCRIPTION
        "new priority, or outer priority, or default priority, should in <0-7>."
    ::= { inactiveVlanEntry 7 }

inactiveVlanRowStatus   OBJECT-TYPE    
    SYNTAX      RowStatus
    MAX-ACCESS  read-write
    STATUS      current
    DESCRIPTION
        "RowStatus"
    ::= { inactiveVlanEntry 8 }

-- 1.1.2.1.2. inactiveUsTrafficTable --------------------------

inactiveUsTrafficTable  OBJECT-TYPE
        SYNTAX      SEQUENCE OF InactiveUsTrafficEntry
        MAX-ACCESS  not-accessible
        STATUS      current
        DESCRIPTION
            "inactive us traffic table."
        ::= { inactiveTrafficConfig 2 }

inactiveUsTrafficEntry  OBJECT-TYPE
        SYNTAX      InactiveUsTrafficEntry
        MAX-ACCESS  not-accessible
        STATUS      current
        DESCRIPTION
            "entry of inactive us traffic table"
        INDEX { inactiveUsTrafficIndex }
        ::= { inactiveUsTrafficTable 1 }

InactiveUsTrafficEntry  ::= 
        SEQUENCE 
        {
            inactiveUsTrafficIndex       INTEGER,
            inactiveUsTrafficName        OCTET STRING,
            inactiveUsTrafficPq          INTEGER,
            inactiveUsTrafficCir         INTEGER,
            inactiveUsTrafficPir         INTEGER,
            inactiveUsTrafficCbs         INTEGER,
            inactiveUsTrafficPbs         INTEGER,
            inactiveUsTrafficRowStatus   RowStatus
        }

inactiveUsTrafficIndex  OBJECT-TYPE    
    SYNTAX      INTEGER(0..2047)
    MAX-ACCESS  read-only
    STATUS      current
    DESCRIPTION
        "The index of inactive us traffic table, should be inputted with <0-2047>.
         The range is not always fit, please see range in commands."
    ::= { inactiveUsTrafficEntry 1 }

inactiveUsTrafficName  OBJECT-TYPE
    SYNTAX      OCTET STRING (SIZE(0..255))
    MAX-ACCESS  read-write
    STATUS      current
    DESCRIPTION
        "us traffic name, max length: 128."
    ::= { inactiveUsTrafficEntry 2 }

inactiveUsTrafficPq OBJECT-TYPE    
    SYNTAX      INTEGER(0..7)
    MAX-ACCESS  read-write
    STATUS      current
    DESCRIPTION
        "The gemport priority queue, should be inputted with <0-7>."
    ::= { inactiveUsTrafficEntry 3 }

inactiveUsTrafficCir OBJECT-TYPE    
    SYNTAX      INTEGER(64..1310720)
    MAX-ACCESS  read-write
    STATUS      current
    DESCRIPTION
        "The gemport committed infomation rate, should be inputted with <64-10240000>.
         must to be divisible by 64kbps,must not less than 64 kbps."
    ::= { inactiveUsTrafficEntry 4 }

inactiveUsTrafficPir OBJECT-TYPE    
    SYNTAX      INTEGER(64..1310720)
    MAX-ACCESS  read-write
    STATUS      current
    DESCRIPTION
        "The gemport peek infomation rate, should be inputted with <64-10240000>.
         must to be divisible by 64kbps,must not less than 64 kbps."
    ::= { inactiveUsTrafficEntry 5 }

inactiveUsTrafficCbs OBJECT-TYPE    
    SYNTAX      INTEGER(2000..1310720)
    MAX-ACCESS  read-write
    STATUS      current
    DESCRIPTION
        "The gemport committed burst size, should be inputted with <2000-10240000>."
    ::= { inactiveUsTrafficEntry 6 }

inactiveUsTrafficPbs OBJECT-TYPE    
    SYNTAX      INTEGER(2000..1310720)
    MAX-ACCESS  read-write
    STATUS      current
    DESCRIPTION
        "The gemport peek burst size, should be inputted with <2000-10240000>."
    ::= { inactiveUsTrafficEntry 7 }

inactiveUsTrafficRowStatus   OBJECT-TYPE    
    SYNTAX      RowStatus
    MAX-ACCESS  read-write
    STATUS      current
    DESCRIPTION
        "RowStatus"
    ::= { inactiveUsTrafficEntry 8 }

-- 1.1.2.1.2. inactiveDsTrafficTable --------------------------

inactiveDsTrafficTable  OBJECT-TYPE
        SYNTAX      SEQUENCE OF InactiveDsTrafficEntry
        MAX-ACCESS  not-accessible
        STATUS      current
        DESCRIPTION
            "inactive ds traffic table."
        ::= { inactiveTrafficConfig 3 }

inactiveDsTrafficEntry  OBJECT-TYPE
        SYNTAX      InactiveDsTrafficEntry
        MAX-ACCESS  not-accessible
        STATUS      current
        DESCRIPTION
            "entry of inactive ds traffic table"
        INDEX { inactiveDsTrafficIndex }
        ::= { inactiveDsTrafficTable 1 }

InactiveDsTrafficEntry  ::= 
        SEQUENCE 
        {
            inactiveDsTrafficIndex       INTEGER,
            inactiveDsTrafficName        OCTET STRING,
            inactiveDsTrafficRate        INTEGER,
            inactiveDsTrafficBurst       INTEGER,
            inactiveDsTrafficRowStatus   RowStatus
        }

inactiveDsTrafficIndex  OBJECT-TYPE    
    SYNTAX      INTEGER(0..2047)
    MAX-ACCESS  read-only
    STATUS      current
    DESCRIPTION
        "The index of inactive ds traffic table, should be inputted with <0-2047>.
         The range is not always fit, please see range in commands."
    ::= { inactiveDsTrafficEntry 1 }

inactiveDsTrafficName  OBJECT-TYPE
    SYNTAX      OCTET STRING (SIZE(0..255))
    MAX-ACCESS  read-write
    STATUS      current
    DESCRIPTION
        "ds traffic name, max length: 128."
    ::= { inactiveDsTrafficEntry 2 }

inactiveDsTrafficRate OBJECT-TYPE    
    SYNTAX      INTEGER(0..1677215)
    MAX-ACCESS  read-write
    STATUS      current
    DESCRIPTION
        "The gemport ds bandwidth rate, should be inputted with <0-1677215>."
    ::= { inactiveDsTrafficEntry 3 }

inactiveDsTrafficBurst OBJECT-TYPE    
    SYNTAX      INTEGER(0..1677215)
    MAX-ACCESS  read-write
    STATUS      current
    DESCRIPTION
        "The gemport ds burst size, should be inputted with <0-1677215>."
    ::= { inactiveDsTrafficEntry 4 }

inactiveDsTrafficRowStatus   OBJECT-TYPE    
    SYNTAX      RowStatus
    MAX-ACCESS  read-write
    STATUS      current
    DESCRIPTION
        "RowStatus"
    ::= { inactiveDsTrafficEntry 5 }

-- 1.1.2.1.1. inactiveVlanPrimaryTable --------------------------

inactiveVlanPrimaryTable  OBJECT-TYPE
        SYNTAX      SEQUENCE OF InactiveVlanPrimaryEntry
        MAX-ACCESS  not-accessible
        STATUS      current
        DESCRIPTION
            "inactive vlan primary table."
        ::= { inactiveTrafficConfig 4 }

inactiveVlanPrimaryEntry  OBJECT-TYPE
        SYNTAX      InactiveVlanPrimaryEntry
        MAX-ACCESS  not-accessible
        STATUS      current
        DESCRIPTION
            "entry of inactive vlan primary table"
        INDEX { inactiveVlanPriIndex }
        ::= { inactiveVlanPrimaryTable 1 }

InactiveVlanPrimaryEntry  ::= 
        SEQUENCE 
        {
            inactiveVlanPriIndex        INTEGER,
            inactiveVlanPriName         OCTET STRING,
            inactiveVlanPriRowStatus    RowStatus
        }

inactiveVlanPriIndex  OBJECT-TYPE    
    SYNTAX      INTEGER(0..2047)
    MAX-ACCESS  read-only
    STATUS      current
    DESCRIPTION
        "The index of inactive vlan table, should be inputted with <0-2047>.
         The range is not always fit, please see range in commands."
    ::= { inactiveVlanPrimaryEntry 1 }

inactiveVlanPriName  OBJECT-TYPE
    SYNTAX      OCTET STRING (SIZE(0..255))
    MAX-ACCESS  read-write
    STATUS      current
    DESCRIPTION
        "name of inactive vlan entry."
    ::= { inactiveVlanPrimaryEntry 2 }

inactiveVlanPriRowStatus   OBJECT-TYPE    
    SYNTAX      RowStatus
    MAX-ACCESS  read-write
    STATUS      current
    DESCRIPTION
        "RowStatus"
    ::= { inactiveVlanPrimaryEntry 3 }

-- 1.1.2.2. inactiveDbaTable ------------------------------
inactiveDbaTable  OBJECT-TYPE
        SYNTAX      SEQUENCE OF InactiveDbaEntry
        MAX-ACCESS  not-accessible
        STATUS      current
        DESCRIPTION
            "inactive domain dba table"
        ::= { deployInactive 2 }

inactiveDbaEntry  OBJECT-TYPE
        SYNTAX      InactiveDbaEntry
        MAX-ACCESS  not-accessible
        STATUS      current
        DESCRIPTION
            "entry of inactive dba table"
        INDEX { inactiveDbaIndex }
        ::= { inactiveDbaTable 1 }

InactiveDbaEntry  ::= 
        SEQUENCE 
        {
            inactiveDbaIndex            INTEGER,
            inactiveDbaName             OCTET STRING,
            inactiveDbaType             INTEGER,
            inactiveDbaFixBandwidth     INTEGER,
            inactiveDbaAssuredBandwidth INTEGER,
            inactiveDbaMaxBandwidth     INTEGER,
            inactiveDbaRowStatus        RowStatus,
            inactiveDbaMethod           INTEGER
        }

inactiveDbaIndex OBJECT-TYPE    
    SYNTAX      INTEGER(0..127)
    MAX-ACCESS  read-only
    STATUS      current
    DESCRIPTION
        "The index of inactive dba table, should be inputted with <0-127>."
    ::= { inactiveDbaEntry 1 }

inactiveDbaName  OBJECT-TYPE
    SYNTAX      OCTET STRING (SIZE(0..255))
    MAX-ACCESS  read-write
    STATUS      current
    DESCRIPTION
        "inactive dba name, max length: 128."
    ::= { inactiveDbaEntry 2 }
    
inactiveDbaType OBJECT-TYPE
    SYNTAX      INTEGER(1..5)
    MAX-ACCESS  read-write
    STATUS      current
    DESCRIPTION
        "inactiveDbaType, 
         1  fixed bandwidth
         2  assured bandwidth
         3  assured and max bandwidth
         4  max bandwidth
         5  fixed and assured and max bandwidth"
    ::= { inactiveDbaEntry 3 }
    
inactiveDbaFixBandwidth OBJECT-TYPE
    SYNTAX      INTEGER(128..1310720)
    MAX-ACCESS  read-write
    STATUS      current
    DESCRIPTION
        "Must to be divisible by 64kbps, must not less than 128 kbps."
    ::= { inactiveDbaEntry 4 }

inactiveDbaAssuredBandwidth OBJECT-TYPE
    SYNTAX       INTEGER(0..1310592)
    MAX-ACCESS   read-write
    STATUS       current
    DESCRIPTION
        "Must to be divisible by 64kbps, Can be 0.  
         If not 0, it must be at least 256 kbps."
    ::= { inactiveDbaEntry 5 }

inactiveDbaMaxBandwidth OBJECT-TYPE
    SYNTAX      INTEGER(0..1310720)
    MAX-ACCESS  read-write
    STATUS      current
    DESCRIPTION
        "Must to be divisible by 64kbps, and must not be less than 
        the sum of assured BW plus fixedBW. 
        Must less than 1310720 kbps"
    ::= { inactiveDbaEntry 6 }    

inactiveDbaRowStatus    OBJECT-TYPE    
    SYNTAX      RowStatus
    MAX-ACCESS  read-write
    STATUS      current
    DESCRIPTION
        "RowStatus"
    ::= { inactiveDbaEntry 7 }

inactiveDbaMethod    OBJECT-TYPE    
    SYNTAX      INTEGER {
                NSR(0),
                SR(1)
                }
    MAX-ACCESS  read-write
    STATUS      current
    DESCRIPTION
        "dba method.
        0(default): not SR
        1: SR"
    ::= { inactiveDbaEntry 8 }

-- 1.1.2.3. inactiveLineCommonConfig ----------------------
inactiveLineCommonConfig OBJECT IDENTIFIER ::= { deployInactive 3 }

-- 1.1.2.3.1. inactiveLinePrimaryTable
-- 1.1.2.3.2. inactiveLineTcontTable
-- 1.1.2.3.3. inactiveLineGemportTable
-- 1.1.2.3.4. inactiveLineFlowmappingTable
-- 1.1.2.3.5. inactiveLineAttrMgmtTable
-- 1.1.2.3.6. inactiveLineCportTable
-- 1.1.2.3.7. inactiveLineAlarmRefTable

-- 1.1.2.3.1. inactiveLinePrimaryTable --------------------
inactiveLinePrimaryTable  OBJECT-TYPE
        SYNTAX      SEQUENCE OF InactiveLinePrimaryEntry
        MAX-ACCESS  not-accessible
        STATUS      current
        DESCRIPTION
            "inactive domain line primary table"
        ::= { inactiveLineCommonConfig 1 }

inactiveLinePrimaryEntry  OBJECT-TYPE
        SYNTAX      InactiveLinePrimaryEntry
        MAX-ACCESS  not-accessible
        STATUS      current
        DESCRIPTION
            "entry of inactive line primary table"
        INDEX { inactiveLineIndex }
        ::= { inactiveLinePrimaryTable 1 }

InactiveLinePrimaryEntry  ::= 
        SEQUENCE 
        {
            inactiveLineIndex          INTEGER,
            inactiveLineDeviceType     OCTET STRING,
            inactiveLineName           OCTET STRING,
            inactiveLineTrafficMode    INTEGER,
            inactiveLineMappingMode    INTEGER,
            inactiveLineRowStatus      RowStatus,
            inactiveLineFecSwitch      INTEGER
        }

inactiveLineIndex OBJECT-TYPE    
    SYNTAX      INTEGER(0..2047)
    MAX-ACCESS  read-only
    STATUS      current
    DESCRIPTION
        "The index of line primary table, should be inputted with <0-2047>.
         The range is not always fit, please see range in commands."
    ::= { inactiveLinePrimaryEntry 1 }

inactiveLineDeviceType  OBJECT-TYPE    
    SYNTAX      OCTET STRING (SIZE(7..16))
    MAX-ACCESS  read-write
    STATUS      current
    DESCRIPTION
        "inactiveLineDeviceType:
        x30-420   4ETH+2POTS SFU
        t10-100   1ETH SFU
        t10-420   4ETH+2POTS SFU
        t10-214   2ETH(1ETH+1iTV)+1POTS SFU
        t10-423   4ETH+2POTS+WIFI+USB HGU
        t10-427   4ETH(3ETH+1iTV)+2POTS+WIFI+USB HGU
        t10-403   4ETH+WIFI+USB HGU
        t60-100   1ETH SFU
        c40-100   1ETH SFU
        c30-420   4ETH+2POTS SFU
        c40-427   4ETH(3ETH+1iTV)+2POTS+WIFI+USB HGU
        c30-401   4ETH+WIFI HGU
        c30-423   4ETH+2POTS+WIFI+USB HGU
        c31-423   4ETH+2POTS+WIFI+USB HGU+SFU
        c30-214   2ETH(1ETH+1iTV)+1POTS SFU
        c40-210   1GE+1FE+1POTS HGU
        c30-400   4ETH SFU
        c40-201   2ETH+WIFI HGU
        c40-429   4ETH+2POTS+CATV+WIFI HGU
        c40-428   4ETH+2POTS+CATV HGU
        c40-218   2ETH+1POTS+CATV HGU
        m50-420   4ETH+2POTS SFU
        f10-427   4ETH(3ETH+1iTV)+2POTS+WIFI+USB HGU
        h60-100   1ETH SFU
        s10-214   2ETH(1ETH+1iTV)+1POTS HGU
        s30-100   1ETH SFU
        n20-100   1ETH SFU
        n20-400   4ETH SFU
        n40-100   1ETH SFU
        n70-400   4ETH SFU
        n71-400   4ETH SFU
        n71-408   4ETH+CATV SFU
        n71-401   4ETH+WIFI HGU
        n71-409   4ETH+CATV+WIFI HGU
        n40-428-1 4ETH+2POTS+CATV+PoE HGU
        n40-100-1 1ETH+PoE SFU
        n40-400-1 4ETH+PoE SFU
        n40-420-1 4ETH+2POTS+PoE HGU
        n40-429   4ETH+2POTS+CATV+WIFI HGU
        n40-800-1 8ETH+PoE MDU
        d10-423   4ETH+2POTS+WIFI+USB HGU
        l30-100   1ETH SFU
        l30-210   2ETH+1POTS SFU
        g40-108   1ETH+CATV SFU"
    ::= { inactiveLinePrimaryEntry 2 }

inactiveLineName OBJECT-TYPE
    SYNTAX      OCTET STRING (SIZE(0..255))
    MAX-ACCESS  read-write
    STATUS      current
    DESCRIPTION
        "line name, max length: 128."
    ::= { inactiveLinePrimaryEntry 3 }

inactiveLineTrafficMode OBJECT-TYPE    
    SYNTAX      INTEGER(0..1)
    MAX-ACCESS  read-write
    STATUS      current
    DESCRIPTION
        "inactiveLineTrafficMode:
         0  pri-queue: priority queue scheduling
         1  gem-car: GEM traffic control"
    ::= { inactiveLinePrimaryEntry 4 }

inactiveLineMappingMode OBJECT-TYPE    
    SYNTAX      INTEGER(0..6)
    MAX-ACCESS  read-write
    STATUS      current
    DESCRIPTION
        "inactiveLineMappingMode:
         0  vlan
         1  priority
         2  vlan-priority
         3  port
         4  port-vlan
         5  port-priority
         6  port-vlan-priority"
    ::= { inactiveLinePrimaryEntry 5 }

inactiveLineRowStatus OBJECT-TYPE    
    SYNTAX      RowStatus
    MAX-ACCESS  read-write
    STATUS      current
    DESCRIPTION
        "RowStatus"
    ::= { inactiveLinePrimaryEntry 6 }

inactiveLineFecSwitch OBJECT-TYPE    
    SYNTAX      INTEGER(0..1)
    MAX-ACCESS  read-write
    STATUS      current
    DESCRIPTION
        "inactiveLineFecSwitch:
         0  false (default)
         1  true"
    ::= { inactiveLinePrimaryEntry 7 }

-- 1.1.2.3.2. inactiveLineTcontTable ----------------------
inactiveLineTcontTable  OBJECT-TYPE
        SYNTAX      SEQUENCE OF InactiveLineTcontEntry
        MAX-ACCESS  not-accessible
        STATUS      current
        DESCRIPTION
            "inactive domain line tcont table, now only for tcont bind dba."
        ::= { inactiveLineCommonConfig 2 }

inactiveLineTcontEntry  OBJECT-TYPE
        SYNTAX      InactiveLineTcontEntry
        MAX-ACCESS  not-accessible
        STATUS      current
        DESCRIPTION
            "entry of inactive line tcont table"
        INDEX { inactiveLineIndexI, inactiveLineTcontIndex }
        ::= { inactiveLineTcontTable 1 }

InactiveLineTcontEntry  ::= 
        SEQUENCE 
        {
            inactiveLineIndexI             INTEGER,
            inactiveLineTcontIndex         INTEGER,
            inactiveLineTcontDbaIndex      INTEGER,
            inactiveLineTcontRowStatus     RowStatus
        }

inactiveLineIndexI OBJECT-TYPE    
    SYNTAX      INTEGER(0..2047)
    MAX-ACCESS  read-only
    STATUS      current
    DESCRIPTION
        "The 1st index of this table, should be inputted with <0-2047>.
         The range is not always fit, please see range in commands."
    ::= { inactiveLineTcontEntry 1 }

inactiveLineTcontIndex OBJECT-TYPE    
    SYNTAX      INTEGER(1..8)
    MAX-ACCESS  read-only
    STATUS      current
    DESCRIPTION
        "The index of tcont, the 2nd index of this table.
         Should in <1-8>."
    ::= { inactiveLineTcontEntry 2 }

inactiveLineTcontDbaIndex   OBJECT-TYPE    
    SYNTAX      INTEGER(0..127)
    MAX-ACCESS  read-write
    STATUS      current
    DESCRIPTION
        "The index of tcont bind dba, should be inputted with <0-127>."
    ::= { inactiveLineTcontEntry 3 }

inactiveLineTcontRowStatus  OBJECT-TYPE    
    SYNTAX      RowStatus
    MAX-ACCESS  read-write
    STATUS      current
    DESCRIPTION
        "RowStatus"
    ::= { inactiveLineTcontEntry 4 }

-- 1.1.2.3.3. inactiveLineGemportTable --------------------
inactiveLineGemportTable  OBJECT-TYPE
        SYNTAX      SEQUENCE OF InactiveLineGemportEntry
        MAX-ACCESS  not-accessible
        STATUS      current
        DESCRIPTION
            "inactive domain line gemport table."
        ::= { inactiveLineCommonConfig 3 }

inactiveLineGemportEntry  OBJECT-TYPE
        SYNTAX      InactiveLineGemportEntry
        MAX-ACCESS  not-accessible
        STATUS      current
        DESCRIPTION
            "entry of inactive line gemport table"
        INDEX { inactiveLineIndexII, inactiveLineGemportIndex }
        ::= { inactiveLineGemportTable 1 }

InactiveLineGemportEntry  ::= 
        SEQUENCE 
        {
            inactiveLineIndexII                  INTEGER,
            inactiveLineGemportIndex             INTEGER,
            inactiveLineGemportTcontId           INTEGER,
            inactiveLineGemportVlanProfileId     INTEGER,
            inactiveLineGemportUsProfileId       INTEGER,
            inactiveLineGemportDsProfileId       INTEGER,
            inactiveLineGemportRowStatus         RowStatus
        }

inactiveLineIndexII OBJECT-TYPE    
    SYNTAX      INTEGER(0..2047)
    MAX-ACCESS  read-only
    STATUS      current
    DESCRIPTION
        "The 1st index of this table, should be inputted with <0-2047>.
         The range is not always fit, please see range in commands."
    ::= { inactiveLineGemportEntry 1 }

inactiveLineGemportIndex OBJECT-TYPE    
    SYNTAX      INTEGER(1..24)
    MAX-ACCESS  read-only
    STATUS      current
    DESCRIPTION
        "The index of gemport, the 2nd index of this table.
         Should in <1-24>."
    ::= { inactiveLineGemportEntry 2 }

inactiveLineGemportTcontId  OBJECT-TYPE    
    SYNTAX      INTEGER(1..8)
    MAX-ACCESS  read-write
    STATUS      current
    DESCRIPTION
        "The gemport bind tcont index, should be inputted with <1-8>."
    ::= { inactiveLineGemportEntry 3 }

inactiveLineGemportVlanProfileId OBJECT-TYPE    
    SYNTAX      INTEGER(0..4095)
    MAX-ACCESS  read-write
    STATUS      current
    DESCRIPTION
        "The gemport vlan profile id, should be inputted with <0-4095>."
    ::= { inactiveLineGemportEntry 4 }

inactiveLineGemportUsProfileId OBJECT-TYPE    
    SYNTAX      INTEGER(0..4095)
    MAX-ACCESS  read-write
    STATUS      current
    DESCRIPTION
        "The gemport us traffic profile id, should be inputted with <0-4095>."
    ::= { inactiveLineGemportEntry 5 }

inactiveLineGemportDsProfileId OBJECT-TYPE    
    SYNTAX      INTEGER(0..4095)
    MAX-ACCESS  read-write
    STATUS      current
    DESCRIPTION
        "The gemport ds traffic profile id, should be inputted with <0-4095>."
    ::= { inactiveLineGemportEntry 6 }

inactiveLineGemportRowStatus OBJECT-TYPE    
    SYNTAX       RowStatus
    MAX-ACCESS   read-write
    STATUS       current
    DESCRIPTION
        "RowStatus"
    ::= { inactiveLineGemportEntry 7 }

-- 1.1.2.3.4. inactiveLineFlowmappingTable ----------------
inactiveLineFlowmappingTable  OBJECT-TYPE
        SYNTAX      SEQUENCE OF InactiveLineFlowmappingEntry
        MAX-ACCESS  not-accessible
        STATUS      current
        DESCRIPTION
            "inactive domain line flow mapping table."
        ::= { inactiveLineCommonConfig 4 }

inactiveLineFlowmappingEntry  OBJECT-TYPE
        SYNTAX      InactiveLineFlowmappingEntry
        MAX-ACCESS  not-accessible
        STATUS      current
        DESCRIPTION
            "entry of inactive line flow mapping table"
        INDEX { inactiveLineIndexIII, inactiveLineFlowmappingIndex }
        ::= { inactiveLineFlowmappingTable 1 }

InactiveLineFlowmappingEntry  ::= 
        SEQUENCE 
        {
            inactiveLineIndexIII             INTEGER,
            inactiveLineFlowmappingIndex     INTEGER,
            inactiveLineFlowmappingVid       INTEGER,
            inactiveLineFlowmappingPriority  INTEGER,
            inactiveLineFlowmappingEthport   INTEGER,
            inactiveLineFlowmappingGemport   INTEGER,
            inactiveLineFlowmappingType      INTEGER,
            inactiveLineFlowmappingRowStatus RowStatus
        }

inactiveLineIndexIII OBJECT-TYPE    
    SYNTAX      INTEGER(0..2047)
    MAX-ACCESS  read-only
    STATUS      current
    DESCRIPTION
        "The 1st index of this table, should be inputted with <0-2047>.
         The range is not always fit, please see range in commands."
    ::= { inactiveLineFlowmappingEntry 1 }

inactiveLineFlowmappingIndex OBJECT-TYPE    
    SYNTAX       INTEGER(0..47)
    MAX-ACCESS   read-only
    STATUS       current
    DESCRIPTION
        "The index of flowmapping, the 2nd index of this table. Should in <1-48>.
         The range is not always fit, please see range in commands."
    ::= { inactiveLineFlowmappingEntry 2 }

inactiveLineFlowmappingVid  OBJECT-TYPE    
    SYNTAX      INTEGER(1..4094)
    MAX-ACCESS  read-write
    STATUS      current
    DESCRIPTION
        "The flow mapping vid, should be inputted with <1-4094>."
    ::= { inactiveLineFlowmappingEntry 3 }

inactiveLineFlowmappingPriority OBJECT-TYPE    
    SYNTAX          INTEGER(0..8)
    MAX-ACCESS      read-write
    STATUS          current
    DESCRIPTION
        "The flow mapping priority, should be inputted with <0-8>.
         default value 8 means don't care 802.1p priority."
    ::= { inactiveLineFlowmappingEntry 4 }

inactiveLineFlowmappingEthport OBJECT-TYPE    
    SYNTAX       INTEGER(1..8)
    MAX-ACCESS   read-write
    STATUS       current
    DESCRIPTION
        "The flow mapping ethernet port id, should be inputted with <1-8>."
    ::= { inactiveLineFlowmappingEntry 5 }

inactiveLineFlowmappingGemport OBJECT-TYPE    
    SYNTAX         INTEGER(1..24)
    MAX-ACCESS     read-write
    STATUS         current
    DESCRIPTION
        "The flow mapping gem port id, should be inputted with <1-24>."
    ::= { inactiveLineFlowmappingEntry 6 }

inactiveLineFlowmappingType OBJECT-TYPE    
    SYNTAX         INTEGER(0..3)
    MAX-ACCESS     read-write
    STATUS         current
    DESCRIPTION
        "inactiveLineFlowmappingType:
        0  flowmapping not base port.
        1  flowmapping base eth port.
        2  flowmapping base veip port.
        3. flowmapping base iphost port."
    ::= { inactiveLineFlowmappingEntry 7 }

inactiveLineFlowmappingRowStatus OBJECT-TYPE    
    SYNTAX           RowStatus
    MAX-ACCESS       read-write
    STATUS           current
    DESCRIPTION
        "RowStatus"
    ::= { inactiveLineFlowmappingEntry 8 }

-- 1.1.2.3.5. inactiveLineAttrMgmtTable --------------------
inactiveLineAttrMgmtTable  OBJECT-TYPE
        SYNTAX      SEQUENCE OF InactiveLineAttrMgmtEntry
        MAX-ACCESS  not-accessible
        STATUS      current
        DESCRIPTION
            "inactive domain line attribute management table."
        ::= { inactiveLineCommonConfig 5 }

inactiveLineAttrMgmtEntry  OBJECT-TYPE
        SYNTAX      InactiveLineAttrMgmtEntry
        MAX-ACCESS  not-accessible
        STATUS      current
        DESCRIPTION
            "entry of inactive line attribute management table"
        INDEX { inactiveLineIndexIV, inactiveLineAttrMgmtIndex }
        ::= { inactiveLineAttrMgmtTable 1 }

InactiveLineAttrMgmtEntry  ::= 
        SEQUENCE 
        {
            inactiveLineIndexIV              INTEGER,
            inactiveLineAttrMgmtIndex        INTEGER,
            inactiveLineAttrMgmtNportType    INTEGER,
            inactiveLineAttrMgmtNport        INTEGER,
            inactiveLineAttrMgmtEtypeFilter  INTEGER,
            inactiveLineAttrMgmtVlanMode     INTEGER,
            inactiveLineAttrMgmtCvlanVid     INTEGER,
            inactiveLineAttrMgmtCvlanPri     INTEGER,
            inactiveLineAttrMgmtSvlanVid     INTEGER,
            inactiveLineAttrMgmtSvlanPri     INTEGER,
            inactiveLineAttrMgmtRowStatus    RowStatus
        }

inactiveLineIndexIV OBJECT-TYPE    
    SYNTAX      INTEGER(0..2047)
    MAX-ACCESS  read-only
    STATUS      current
    DESCRIPTION
        "The 1st index of this table, should be inputted with <0-2047>.
         The range is not always fit, please see range in commands."
    ::= { inactiveLineAttrMgmtEntry 1 }

inactiveLineAttrMgmtIndex OBJECT-TYPE    
    SYNTAX       INTEGER(0..63)
    MAX-ACCESS   read-only
    STATUS       current
    DESCRIPTION
        "The index of attribute management, the 2nd index of this table. Should in <1-64>."
    ::= { inactiveLineAttrMgmtEntry 2 }

inactiveLineAttrMgmtNportType OBJECT-TYPE    
    SYNTAX      INTEGER(1..3)
    MAX-ACCESS  read-write
    STATUS      current
    DESCRIPTION
        "inactiveLineAttrMgmtNportType:
         1  eth port in sfu
         2  veip port in hgu
         3  iphost virtual port, for voip, tdm, etc."
    ::= { inactiveLineAttrMgmtEntry 3 }

inactiveLineAttrMgmtNport OBJECT-TYPE    
    SYNTAX       INTEGER(1..64)
    MAX-ACCESS   read-write
    STATUS       current
    DESCRIPTION
        "The port of attribute management, if eport, should in <1-8>."
    ::= { inactiveLineAttrMgmtEntry 4 }

inactiveLineAttrMgmtEtypeFilter OBJECT-TYPE    
    SYNTAX      INTEGER(0..3)
    MAX-ACCESS  read-write
    STATUS      current
    DESCRIPTION
        "inactiveLineAttrMgmtEtypeFilter:
         0  no filter
         1  filter ipoe frame
         2  filter pppoe frame
         3  filter arp frame"
    ::= { inactiveLineAttrMgmtEntry 5 }

inactiveLineAttrMgmtVlanMode OBJECT-TYPE    
    SYNTAX      INTEGER(0..4)
    MAX-ACCESS  read-write
    STATUS      current
    DESCRIPTION
        "inactiveLineAttrMgmtVlanMode:
         0  transparent
         1  tag
         2  translation
         3  trunk
         4  QinQ"
    ::= { inactiveLineAttrMgmtEntry 6 }

inactiveLineAttrMgmtCvlanVid OBJECT-TYPE    
    SYNTAX      INTEGER(1..4094)
    MAX-ACCESS  read-write
    STATUS      current
    DESCRIPTION
        "cvlan vid, should be inputted with <1-4094>."
    ::= { inactiveLineAttrMgmtEntry 7 }

inactiveLineAttrMgmtCvlanPri OBJECT-TYPE    
    SYNTAX      INTEGER(0..8)
    MAX-ACCESS  read-write
    STATUS      current
    DESCRIPTION
        "The cvlan priority, should be inputted with <0-8>.
         Value 8 means don't care vlan priority."
    ::= { inactiveLineAttrMgmtEntry 8 }

inactiveLineAttrMgmtSvlanVid OBJECT-TYPE    
    SYNTAX      INTEGER(1..4094)
    MAX-ACCESS  read-write
    STATUS      current
    DESCRIPTION
        "svlan vid, should be inputted with <1-4094>."
    ::= { inactiveLineAttrMgmtEntry 9 }

inactiveLineAttrMgmtSvlanPri OBJECT-TYPE    
    SYNTAX      INTEGER(0..8)
    MAX-ACCESS  read-write
    STATUS      current
    DESCRIPTION
        "svlan priority, should be inputted with <0-8>.
         Value 8 means don't care vlan priority."
    ::= { inactiveLineAttrMgmtEntry 10 }

inactiveLineAttrMgmtRowStatus OBJECT-TYPE    
    SYNTAX       RowStatus
    MAX-ACCESS   read-write
    STATUS       current
    DESCRIPTION
        "RowStatus"
    ::= { inactiveLineAttrMgmtEntry 11 }

-- 1.1.2.3.6. inactiveLineCportTable --------------------
inactiveLineCportTable  OBJECT-TYPE
        SYNTAX      SEQUENCE OF InactiveLineCportEntry
        MAX-ACCESS  not-accessible
        STATUS      current
        DESCRIPTION
            "inactive domain line catv port management table."
        ::= { inactiveLineCommonConfig 6 }

inactiveLineCportEntry  OBJECT-TYPE
        SYNTAX      InactiveLineCportEntry
        MAX-ACCESS  not-accessible
        STATUS      current
        DESCRIPTION
            "entry of inactive line catv port management table"
        INDEX { inactiveLineIndexX, inactiveLineCportIndex }
        ::= { inactiveLineCportTable 1 }

InactiveLineCportEntry  ::= 
        SEQUENCE 
        {
            inactiveLineIndexX         INTEGER,
            inactiveLineCportIndex     INTEGER,
            inactiveLineCportSwitch    INTEGER,
            inactiveLineCportAgcMode   INTEGER,
            inactiveLineCportAgcRange  INTEGER
        }

inactiveLineIndexX OBJECT-TYPE    
    SYNTAX      INTEGER(0..2047)
    MAX-ACCESS  read-only
    STATUS      current
    DESCRIPTION
        "The 1st index of this table, should be inputted with <0-2047>.
         The range is not always fit, please see range in commands."
    ::= { inactiveLineCportEntry 1 }

inactiveLineCportIndex OBJECT-TYPE    
    SYNTAX       INTEGER(1..4)
    MAX-ACCESS   read-only
    STATUS       current
    DESCRIPTION
        "The index of catv port management, the 2nd index of this table. Should in <1-4>."
    ::= { inactiveLineCportEntry 2 }

inactiveLineCportSwitch OBJECT-TYPE    
    SYNTAX      INTEGER(0..1)
    MAX-ACCESS  read-write
    STATUS      current
    DESCRIPTION
        "inactiveLineCportSwitch:
         0  disable
         1  enable(default)"
    ::= { inactiveLineCportEntry 3 }

inactiveLineCportAgcMode OBJECT-TYPE    
    SYNTAX       INTEGER(0..2)
    MAX-ACCESS   read-write
    STATUS       current
    DESCRIPTION
        "inactiveLineCportAgcMode:
        0  No AGC
        1  Broadband RF AGC
        2  Optical AGC"
    ::= { inactiveLineCportEntry 4 }

inactiveLineCportAgcRange OBJECT-TYPE    
    SYNTAX      INTEGER(-120..60)
    MAX-ACCESS  read-write
    STATUS      current
    DESCRIPTION
        "catv port agc range, default: 0."
    ::= { inactiveLineCportEntry 5 }

-- 1.1.2.3.7. inactiveLineAlarmRefTable --------------------
inactiveLineAlarmRefTable  OBJECT-TYPE
        SYNTAX      SEQUENCE OF InactiveLineAlarmRefEntry
        MAX-ACCESS  not-accessible
        STATUS      current
        DESCRIPTION
            "inactive line alarm Reference table."
        ::= { inactiveLineCommonConfig 7 }

inactiveLineAlarmRefEntry  OBJECT-TYPE
        SYNTAX      InactiveLineAlarmRefEntry
        MAX-ACCESS  not-accessible
        STATUS      current
        DESCRIPTION
            "entry of inactive line alarm Reference table"
        INDEX { inactiveLineAlarmRefLIndex }
        ::= { inactiveLineAlarmRefTable 1 }

InactiveLineAlarmRefEntry  ::= 
        SEQUENCE 
        {
            inactiveLineAlarmRefLIndex    INTEGER,
            inactiveLineAlarmRefAIndex    INTEGER,
            inactiveLineAlarmRefAName     OCTET STRING,
            inactiveLineAlarmRefRowStatus RowStatus
        }

inactiveLineAlarmRefLIndex OBJECT-TYPE    
    SYNTAX      INTEGER(0..2047)
    MAX-ACCESS  read-only
    STATUS      current
    DESCRIPTION
        "The line index of this table, should be inputted with <0-2047>.
         The range is not always fit, please see range in commands."
    ::= { inactiveLineAlarmRefEntry 1 }

inactiveLineAlarmRefAIndex OBJECT-TYPE    
    SYNTAX       INTEGER(0..127)
    MAX-ACCESS   read-create
    STATUS       current
    DESCRIPTION
        "The index of alarm table to reference, Should in <0-127>."
    ::= { inactiveLineAlarmRefEntry 2 }

inactiveLineAlarmRefAName OBJECT-TYPE    
    SYNTAX      OCTET STRING (SIZE(1..128))
    MAX-ACCESS  read-create
    STATUS      current
    DESCRIPTION
        "The entry name of alarm table to reference, Should in <1-128>."
    ::= { inactiveLineAlarmRefEntry 3 }

inactiveLineAlarmRefRowStatus OBJECT-TYPE    
    SYNTAX      RowStatus
    MAX-ACCESS  read-create
    STATUS      current
    DESCRIPTION
        "The row status of inactive line alarm Reference table."
    ::= { inactiveLineAlarmRefEntry 4 }

-- 1.1.2.4. inactiveLineSFUConfig --------------------------
inactiveLineSFUConfig OBJECT IDENTIFIER ::= { deployInactive 4 }

-- 1.1.2.4.1. inactiveLineSFUTable
-- 1.1.2.4.2. inactiveLineSFUEthportTable

-- 1.1.2.4.1. inactiveLineSFUTable ------------------------
inactiveLineSFUTable  OBJECT-TYPE
        SYNTAX      SEQUENCE OF InactiveLineSFUEntry
        MAX-ACCESS  not-accessible
        STATUS      current
        DESCRIPTION
            "inactive domain line SFU primary table."
        ::= { inactiveLineSFUConfig 1 }

inactiveLineSFUEntry  OBJECT-TYPE
        SYNTAX      InactiveLineSFUEntry
        MAX-ACCESS  not-accessible
        STATUS      current
        DESCRIPTION
            "entry of inactive line sfu primary table"
        INDEX { inactiveLineIndexV }
        ::= { inactiveLineSFUTable 1 }

InactiveLineSFUEntry  ::= 
        SEQUENCE 
        {
            inactiveLineIndexV                  INTEGER,
            inactiveLineSfuLocalSwitch          INTEGER,
            inactiveLineSfuLoopDetectSwitch     INTEGER
        }

inactiveLineIndexV OBJECT-TYPE    
    SYNTAX      INTEGER(0..4095)
    MAX-ACCESS  read-only
    STATUS      current
    DESCRIPTION
        "The 1st index of this table, should be inputted with <0-4095>.
         The range is not always fit, please see range in commands."
    ::= { inactiveLineSFUEntry 1 }

inactiveLineSfuLocalSwitch OBJECT-TYPE    
    SYNTAX       INTEGER(0..1)
    MAX-ACCESS   read-write
    STATUS       current
    DESCRIPTION
        "inactiveLineSfuLocalSwitch:
         0  disable(default)
         1  enable."
    ::= { inactiveLineSFUEntry 2 }

inactiveLineSfuLoopDetectSwitch  OBJECT-TYPE    
    SYNTAX      INTEGER(0..1)
    MAX-ACCESS  read-write
    STATUS      current
    DESCRIPTION
        "inactiveLineSfuLoopDetectSwitch:
         0  disable(default)
         1  enable."
    ::= { inactiveLineSFUEntry 3 }

-- 1.1.2.4.2. inactiveLineSFUEthportTable ------------------
inactiveLineSFUEthportTable  OBJECT-TYPE
        SYNTAX      SEQUENCE OF InactiveLineSFUEthportEntry
        MAX-ACCESS  not-accessible
        STATUS      current
        DESCRIPTION
            "inactive domain line SFU ethernet port table."
        ::= { inactiveLineSFUConfig 2 }

inactiveLineSFUEthportEntry  OBJECT-TYPE
        SYNTAX      InactiveLineSFUEthportEntry
        MAX-ACCESS  not-accessible
        STATUS      current
        DESCRIPTION
            "entry of inactive line SFU ethernet port table"
        INDEX { inactiveLineIndexVI, inactiveLineSfuEthportIndex }
        ::= { inactiveLineSFUEthportTable 1 }

InactiveLineSFUEthportEntry  ::= 
        SEQUENCE 
        {
            inactiveLineIndexVI                     INTEGER,
            inactiveLineSfuEthportIndex             INTEGER,
            inactiveLineSfuEthportSwitch            INTEGER,
            inactiveLineSfuEthportFlowCtrlSwitch    INTEGER,
            inactiveLineSfuEthportLoopbackSwitch    INTEGER,
            inactiveLineSfuEthportFastLeaveSwitch   INTEGER,
            inactiveLineSfuEthportMaxGroups         INTEGER,
            inactiveLineSfuEthportMaxMacCount       INTEGER,
            inactiveLineSfuEthportMcastMode         INTEGER,
            inactiveLineSfuEthportDsIgmpControlType INTEGER,
            inactiveLineSfuEthportDsIgmpVid         INTEGER,
            inactiveLineSfuEthportDsIgmpPri         INTEGER,
            inactiveLineSfuEthportDsIgmpRowStatus   RowStatus,
            inactiveLineSfuEthportUsIgmpControlType INTEGER,
            inactiveLineSfuEthportUsIgmpVid         INTEGER,
            inactiveLineSfuEthportUsIgmpPri         INTEGER,
            inactiveLineSfuEthportUsIgmpRowStatus   RowStatus,
            inactiveLineSfuEthportBwCir             INTEGER,
            inactiveLineSfuEthportBwCbs             INTEGER,
            inactiveLineSfuEthportBwPir             INTEGER,
            inactiveLineSfuEthportBwPbs             INTEGER,
            inactiveLineSfuEthportBwRowStatus       RowStatus
        }

inactiveLineIndexVI OBJECT-TYPE    
    SYNTAX      INTEGER(0..2047)
    MAX-ACCESS  read-only
    STATUS      current
    DESCRIPTION
        "The 1st index of this table, should be inputted with <0-2047>.
         The range is not always fit, please see range in commands."
    ::= { inactiveLineSFUEthportEntry 1 }

inactiveLineSfuEthportIndex OBJECT-TYPE    
    SYNTAX      INTEGER(1..8)
    MAX-ACCESS  read-only
    STATUS      current
    DESCRIPTION
        "The index of SFU ethernet port, the 2nd index of this table. Should in <1-8>."
    ::= { inactiveLineSFUEthportEntry 2 }

inactiveLineSfuEthportSwitch OBJECT-TYPE    
    SYNTAX         INTEGER(0..1)
    MAX-ACCESS     read-write
    STATUS         current
    DESCRIPTION
        "inactiveLineSfuEthportSwitch:
         0  no shutdown(default)
         1  shutdown"
    ::= { inactiveLineSFUEthportEntry 3 }

inactiveLineSfuEthportFlowCtrlSwitch OBJECT-TYPE    
    SYNTAX         INTEGER(0..1)
    MAX-ACCESS     read-write
    STATUS         current
    DESCRIPTION
        "inactiveLineSfuEthportFlowCtrlSwitch:
         0  disable(default)
         1  enable"
    ::= { inactiveLineSFUEthportEntry 4 }

inactiveLineSfuEthportLoopbackSwitch OBJECT-TYPE    
    SYNTAX         INTEGER(0..1)
    MAX-ACCESS     read-write
    STATUS         current
    DESCRIPTION
        "inactiveLineSfuEthportLoopbackSwitch:
         0  disable(default)
         1  enable"
    ::= { inactiveLineSFUEthportEntry 5 }

inactiveLineSfuEthportFastLeaveSwitch OBJECT-TYPE    
    SYNTAX        INTEGER(0..1)
    MAX-ACCESS    read-write
    STATUS        current
    DESCRIPTION
        "inactiveLineSfuEthportFastLeaveSwitch:
         0  disable(default) 
         1  enable"
    ::= { inactiveLineSFUEthportEntry 6 }

inactiveLineSfuEthportMaxGroups OBJECT-TYPE    
    SYNTAX        INTEGER(1..128)
    MAX-ACCESS    read-write
    STATUS        current
    DESCRIPTION
        "The SFU ethernet port max igmp groups, should be inputted with <1-128>."
    ::= { inactiveLineSFUEthportEntry 7 }

inactiveLineSfuEthportMaxMacCount OBJECT-TYPE    
    SYNTAX          INTEGER(1..255)
    MAX-ACCESS      read-write
    STATUS          current
    DESCRIPTION
        "The SFU ethernet port max mac address count, should be inputted with <1-255>."
    ::= { inactiveLineSFUEthportEntry 8 }

inactiveLineSfuEthportMcastMode OBJECT-TYPE    
    SYNTAX         INTEGER(0..2)
    MAX-ACCESS     read-write
    STATUS         current
    DESCRIPTION
        "inactiveLineSfuEthportMcastMode(some ont not support):
         0  control
         1  igmp snooping
         2  unconcern(default)"
    ::= { inactiveLineSFUEthportEntry 9 }

inactiveLineSfuEthportDsIgmpControlType OBJECT-TYPE    
    SYNTAX          INTEGER(0..5)
    MAX-ACCESS      read-write
    STATUS          current
    DESCRIPTION
        "inactiveLineSfuEthportDsIgmpControlType:
         0  transparent(default, only for read)
         1  strip outer tag
         2  add tag
         3  replace tag
         4  replace only vid
         5  add only vid"
    ::= { inactiveLineSFUEthportEntry 10 }

inactiveLineSfuEthportDsIgmpVid OBJECT-TYPE    
    SYNTAX        INTEGER(1..4094)
    MAX-ACCESS    read-write
    STATUS        current
    DESCRIPTION
        "The SFU ethernet port downstream igmp and multicast control vid, 
        should be inputted with <1-4094>."
    ::= { inactiveLineSFUEthportEntry 11 }

inactiveLineSfuEthportDsIgmpPri OBJECT-TYPE    
    SYNTAX      INTEGER(0..7)
    MAX-ACCESS  read-write
    STATUS      current
    DESCRIPTION
        "The vlan priority, should be inputted with <0-7>."
    ::= { inactiveLineSFUEthportEntry 12 }

inactiveLineSfuEthportDsIgmpRowStatus OBJECT-TYPE    
    SYNTAX       RowStatus
    MAX-ACCESS   read-write
    STATUS       current
    DESCRIPTION
        "RowStatus for ethport ds igmp tag control."
    ::= { inactiveLineSFUEthportEntry 13 }

inactiveLineSfuEthportUsIgmpControlType OBJECT-TYPE    
    SYNTAX          INTEGER(0..4)
    MAX-ACCESS      read-write
    STATUS          current
    DESCRIPTION
        "inactiveLineSfuEthportUsIgmpControlType:
         0  transparent(default, only for read)
         1  add tag
         2  replace tag
         3  replace only vid
         4  add only vid"
    ::= { inactiveLineSFUEthportEntry 14 }

inactiveLineSfuEthportUsIgmpVid OBJECT-TYPE    
    SYNTAX        INTEGER(1..4094)
    MAX-ACCESS    read-write
    STATUS        current
    DESCRIPTION
        "The SFU ethernet port upstream igmp and multicast control vid, 
        should be inputted with <1-4094>."
    ::= { inactiveLineSFUEthportEntry 15 }

inactiveLineSfuEthportUsIgmpPri OBJECT-TYPE    
    SYNTAX      INTEGER(0..7)
    MAX-ACCESS  read-write
    STATUS      current
    DESCRIPTION
        "The vlan priority, should be inputted with <0-7>."
    ::= { inactiveLineSFUEthportEntry 16 }

inactiveLineSfuEthportUsIgmpRowStatus OBJECT-TYPE    
    SYNTAX       RowStatus
    MAX-ACCESS   read-write
    STATUS       current
    DESCRIPTION
        "RowStatus for ethport us igmp tag control."
    ::= { inactiveLineSFUEthportEntry 17 }

inactiveLineSfuEthportBwCir OBJECT-TYPE    
    SYNTAX       INTEGER(64..1024000)
    MAX-ACCESS   read-write
    STATUS       current
    DESCRIPTION
        "The SFU ethernet port bandwidth egress cir, should be inputted with <64-1024000>."
    ::= { inactiveLineSFUEthportEntry 18 }

inactiveLineSfuEthportBwCbs OBJECT-TYPE    
    SYNTAX       INTEGER(2..32000)
    MAX-ACCESS   read-write
    STATUS       current
    DESCRIPTION
        "The SFU ethernet port bandwidth egress cbs, should be inputted with <2-32000>."
    ::= { inactiveLineSFUEthportEntry 19 }

inactiveLineSfuEthportBwPir OBJECT-TYPE    
    SYNTAX       INTEGER(64..1024000)
    MAX-ACCESS   read-write
    STATUS       current
    DESCRIPTION
        "The SFU ethernet port bandwidth egress pir, should be inputted with <64-1024000>."
    ::= { inactiveLineSFUEthportEntry 20 }

inactiveLineSfuEthportBwPbs OBJECT-TYPE    
    SYNTAX       INTEGER(2..32000)
    MAX-ACCESS   read-write
    STATUS       current
    DESCRIPTION
        "The SFU ethernet port bandwidth egress pbs, should be inputted with <2-32000>."
    ::= { inactiveLineSFUEthportEntry 21 }

inactiveLineSfuEthportBwRowStatus OBJECT-TYPE    
    SYNTAX       RowStatus
    MAX-ACCESS   read-write
    STATUS       current
    DESCRIPTION
        "RowStatus for ethernet port bandwidth egress."
    ::= { inactiveLineSFUEthportEntry 22 }

-- 1.1.2.5. inactiveLineHGUConfig --------------------------
inactiveLineHGUConfig OBJECT IDENTIFIER ::= { deployInactive 5 }

-- 1.1.2.5.1. inactiveLineHGUTable

-- 1.1.2.5.1. inactiveLineHGUTable ------------------------
inactiveLineHGUTable  OBJECT-TYPE
        SYNTAX      SEQUENCE OF InactiveLineHGUEntry
        MAX-ACCESS  not-accessible
        STATUS      current
        DESCRIPTION
            "inactive domain line HGU table."
        ::= { inactiveLineHGUConfig 1 }

inactiveLineHGUEntry  OBJECT-TYPE
        SYNTAX      InactiveLineHGUEntry
        MAX-ACCESS  not-accessible
        STATUS      current
        DESCRIPTION
            "entry of inactive line HGU table"
        INDEX { inactiveLineIndexVIII }
        ::= { inactiveLineHGUTable 1 }

InactiveLineHGUEntry  ::= 
        SEQUENCE 
        {
            inactiveLineIndexVIII            INTEGER,
            inactiveLineHguSwitch            INTEGER,
            inactiveLineHguFastLeaveSwitch   INTEGER,
            inactiveLineHguMaxGroups         INTEGER,
            inactiveLineHguMaxMacCount       INTEGER,
            inactiveLineHguMcastMode         INTEGER,
            inactiveLineHguDsIgmpControlType INTEGER,
            inactiveLineHguDsIgmpVid         INTEGER,
            inactiveLineHguDsIgmpPri         INTEGER,
            inactiveLineHguDsIgmpRowStatus   RowStatus,
            inactiveLineHguUsIgmpControlType INTEGER,
            inactiveLineHguUsIgmpVid         INTEGER,
            inactiveLineHguUsIgmpPri         INTEGER,
            inactiveLineHguUsIgmpRowStatus   RowStatus,
            inactiveLineHguMcastEportSwitch  INTEGER
        }

inactiveLineIndexVIII OBJECT-TYPE    
    SYNTAX      INTEGER(0..2047)
    MAX-ACCESS  read-only
    STATUS      current
    DESCRIPTION
        "The 1st index of this table, should be inputted with <0-2047>.
         The range is not always fit, please see range in commands."
    ::= { inactiveLineHGUEntry 1 }

inactiveLineHguSwitch OBJECT-TYPE    
    SYNTAX         INTEGER(0..1)
    MAX-ACCESS     read-write
    STATUS         current
    DESCRIPTION
        "inactiveLineHguSwitch:
         0  no shutdown(default)
         1  shutdown"
    ::= { inactiveLineHGUEntry 2 }

inactiveLineHguFastLeaveSwitch OBJECT-TYPE    
    SYNTAX         INTEGER(0..1)
    MAX-ACCESS     read-write
    STATUS         current
    DESCRIPTION
        "inactiveLineHguFlowCtrlSwitch:
         0  disable(default)
         1  enable"
    ::= { inactiveLineHGUEntry 3 }

inactiveLineHguMaxGroups OBJECT-TYPE    
    SYNTAX        INTEGER(1..128)
    MAX-ACCESS    read-write
    STATUS        current
    DESCRIPTION
        "The HGU max igmp groups, should be inputted with <1-128>."
    ::= { inactiveLineHGUEntry 4 }

inactiveLineHguMaxMacCount OBJECT-TYPE    
    SYNTAX          INTEGER(1..255)
    MAX-ACCESS      read-write
    STATUS          current
    DESCRIPTION
        "The HGU max mac address count, should be inputted with <1-255>."
    ::= { inactiveLineHGUEntry 5 }

inactiveLineHguMcastMode OBJECT-TYPE    
    SYNTAX         INTEGER(0..2)
    MAX-ACCESS     read-write
    STATUS         current
    DESCRIPTION
        "inactiveLineHguMcastMode(some ont not support):
         0  control
         1  igmp snooping
         2  unconcern(default)"
    ::= { inactiveLineHGUEntry 6 }

inactiveLineHguDsIgmpControlType OBJECT-TYPE    
    SYNTAX          INTEGER(0..5)
    MAX-ACCESS      read-write
    STATUS          current
    DESCRIPTION
        "inactiveLineHguDsIgmpControlType:
         0  transparent(default)
         1  strip outer tag
         2  add tag
         3  replace tag
         4  replace only vid
         5  add only vid"
    ::= { inactiveLineHGUEntry 7 }

inactiveLineHguDsIgmpVid OBJECT-TYPE    
    SYNTAX        INTEGER(1..4094)
    MAX-ACCESS    read-write
    STATUS        current
    DESCRIPTION
        "The HGU downstream igmp and multicast control vid, 
        should be inputted with <1-4094>."
    ::= { inactiveLineHGUEntry 8 }

inactiveLineHguDsIgmpPri OBJECT-TYPE    
    SYNTAX      INTEGER(0..7)
    MAX-ACCESS  read-write
    STATUS      current
    DESCRIPTION
        "The vlan priority, should be inputted with <0-7>."
    ::= { inactiveLineHGUEntry 9 }

inactiveLineHguDsIgmpRowStatus OBJECT-TYPE    
    SYNTAX       RowStatus
    MAX-ACCESS   read-write
    STATUS       current
    DESCRIPTION
        "RowStatus for ds igmp tag control."
    ::= { inactiveLineHGUEntry 10 }

inactiveLineHguUsIgmpControlType OBJECT-TYPE    
    SYNTAX          INTEGER(0..4)
    MAX-ACCESS      read-write
    STATUS          current
    DESCRIPTION
        "inactiveLineHguUsIgmpControlType:
         0  transparent(default)
         1  add tag
         2  replace tag
         3  replace only vid
         4  add only vid"
    ::= { inactiveLineHGUEntry 11 }

inactiveLineHguUsIgmpVid OBJECT-TYPE    
    SYNTAX        INTEGER(1..4094)
    MAX-ACCESS    read-write
    STATUS        current
    DESCRIPTION
        "The HGU upstream igmp and multicast control vid, 
        should be inputted with <1-4094>."
    ::= { inactiveLineHGUEntry 12 }

inactiveLineHguUsIgmpPri OBJECT-TYPE    
    SYNTAX      INTEGER(0..7)
    MAX-ACCESS  read-write
    STATUS      current
    DESCRIPTION
        "The vlan priority, should be inputted with <0-7>."
    ::= { inactiveLineHGUEntry 13 }

inactiveLineHguUsIgmpRowStatus OBJECT-TYPE    
    SYNTAX       RowStatus
    MAX-ACCESS   read-write
    STATUS       current
    DESCRIPTION
        "RowStatus for us igmp tag control."
    ::= { inactiveLineHGUEntry 14 }

inactiveLineHguMcastEportSwitch OBJECT-TYPE    
    SYNTAX         INTEGER(0..1)
    MAX-ACCESS     read-write
    STATUS         current
    DESCRIPTION
        "inactiveLineHguMcastEportSwitch:
         0  disable Hgu ctrl mcast base on eport(default)
         1  enable Hgu ctrl mcast base on eport"
    ::= { inactiveLineHGUEntry 15 }

-- 1.1.2.6. inactiveRuleTable ------------------------------
inactiveRuleTable  OBJECT-TYPE
        SYNTAX      SEQUENCE OF InactiveRuleEntry
        MAX-ACCESS  not-accessible
        STATUS      current
        DESCRIPTION
            "inactive domain rule table"
        ::= { deployInactive 6 }

inactiveRuleEntry  OBJECT-TYPE
        SYNTAX      InactiveRuleEntry
        MAX-ACCESS  not-accessible
        STATUS      current
        DESCRIPTION
            "entry of inactive rule table"
        INDEX { inactiveRuleIndex }
        ::= { inactiveRuleTable 1 }

InactiveRuleEntry  ::= 
        SEQUENCE 
        {
            inactiveRuleIndex              INTEGER,
            inactiveRuleName               OCTET STRING,
            inactiveRuleAction             INTEGER,
            inactiveRuleAuthMode           INTEGER,
            inactiveRuleAuthSn             OCTET STRING,
            inactiveRuleAuthPw             OCTET STRING,
            inactiveRuleAuthLoid           OCTET STRING,
            inactiveRuleAuthLopw           OCTET STRING,
            inactiveRuleAssignedSlot       OCTET STRING,
            inactiveRuleAssignedPport      OCTET STRING,
            inactiveRuleAssignedOnt        OCTET STRING,
            inactiveRuleLineIndexesStr     OCTET STRING,
            inactiveRuleDefaultLine        INTEGER,
            inactiveRuleRowStatus          RowStatus,
            inactiveRuleOnceOnSwitch       INTEGER,
            inactiveRuleOnceOnAgingTime    INTEGER,
            inactiveRuleAuthSnFmt          INTEGER,
            inactiveRuleAuthPwFmt          INTEGER,
            inactiveRuleOntStatus          INTEGER
       }

inactiveRuleIndex OBJECT-TYPE    
    SYNTAX      INTEGER(0..2047)
    MAX-ACCESS  read-only
    STATUS      current
    DESCRIPTION
        "The index of rule table, should be inputted with <0-2047>.
         The range is not always fit, please see range in commands."
    ::= { inactiveRuleEntry 1 }

inactiveRuleName OBJECT-TYPE
    SYNTAX      OCTET STRING (SIZE(0..255))
    MAX-ACCESS  read-write
    STATUS      current
    DESCRIPTION
        "rule description, max length: 128."
    ::= { inactiveRuleEntry 2 }

inactiveRuleAction OBJECT-TYPE    
    SYNTAX      INTEGER(0..1)
    MAX-ACCESS  read-write
    STATUS      current
    DESCRIPTION
        "inactiveRuleAction:
         0  permit
         1  deny"
    ::= { inactiveRuleEntry 3 }

inactiveRuleAuthMode OBJECT-TYPE    
    SYNTAX      INTEGER(0..5)
    MAX-ACCESS  read-write
    STATUS      current
    DESCRIPTION
        "inactiveRuleAuthMode:
         0  auth mode sn
         1  auth mode pw
         2  auth mode sn_pw
         3  auth mode loid
         4  auth mode lopw
         5  auth mode loid_lopw"
    ::= { inactiveRuleEntry 4 }

inactiveRuleAuthSn  OBJECT-TYPE
    SYNTAX      OCTET STRING (SIZE(13..16))
    MAX-ACCESS  read-write
    STATUS      current
    DESCRIPTION
        "auth sn, mix(string-hex) format or hex format.
         length: 
           mix: 13
           hex: 16
         you can use '*' represents any one character or hexadecimal number."
    ::= { inactiveRuleEntry 5 }

inactiveRuleAuthPw  OBJECT-TYPE
    SYNTAX      OCTET STRING (SIZE(1..20))
    MAX-ACCESS  read-write
    STATUS      current
    DESCRIPTION
        "auth password, string format or hex format.
         max length: 
           string: 10
           hex:    20
         you can use '*' represents any one character or hexadecimal number"
    ::= { inactiveRuleEntry 6 }

inactiveRuleAuthLoid  OBJECT-TYPE
    SYNTAX      OCTET STRING (SIZE(0..255))
    MAX-ACCESS  read-write
    STATUS      current
    DESCRIPTION
        "auth loid, string format, max length: 24.
         you can use '*' represents any one character or hexadecimal number"
    ::= { inactiveRuleEntry 7 }

inactiveRuleAuthLopw  OBJECT-TYPE
    SYNTAX      OCTET STRING (SIZE(0..255))
    MAX-ACCESS  read-write
    STATUS      current
    DESCRIPTION
        "auth logic password, string format, max length: 12.
         you can use '*' represents any one character or hexadecimal number"
    ::= { inactiveRuleEntry 8 }

inactiveRuleAssignedSlot OBJECT-TYPE    
    SYNTAX       OCTET STRING (SIZE(0..255))
    MAX-ACCESS   read-write
    STATUS       current
    DESCRIPTION
        "slot id pre assigned. if not configed, its '-'."
    ::= { inactiveRuleEntry 9 }

inactiveRuleAssignedPport OBJECT-TYPE    
    SYNTAX        OCTET STRING (SIZE(0..255))
    MAX-ACCESS    read-write
    STATUS        current
    DESCRIPTION
        "pon port id pre assigned. if not configed, its '-'."
    ::= { inactiveRuleEntry 10 }

inactiveRuleAssignedOnt OBJECT-TYPE    
    SYNTAX      OCTET STRING (SIZE(0..255))
    MAX-ACCESS  read-write
    STATUS      current
    DESCRIPTION
        "ont id pre assigned. if not configed, its '-'."
    ::= { inactiveRuleEntry 11 }
    
inactiveRuleLineIndexesStr OBJECT-TYPE
    SYNTAX         OCTET STRING (SIZE(0..255))
    MAX-ACCESS     read-write
    STATUS         current
    DESCRIPTION
        "String joined by rule bind line indexes, such as '12,56,1023'.
         A rule can at most bind 8 line models."
    ::= { inactiveRuleEntry 12 }

inactiveRuleDefaultLine   OBJECT-TYPE    
    SYNTAX      INTEGER(0..2047)
    MAX-ACCESS  read-write
    STATUS      current
    DESCRIPTION
        "The index of rule default line, should be inputted with <1-4096>
         The range is not always fit, please see range in commands."
    ::= { inactiveRuleEntry 13 }

inactiveRuleRowStatus OBJECT-TYPE    
    SYNTAX      RowStatus
    MAX-ACCESS  read-write
    STATUS      current
    DESCRIPTION
        "RowStatus"
    ::= { inactiveRuleEntry 14 }

inactiveRuleOnceOnSwitch   OBJECT-TYPE    
    SYNTAX      INTEGER(0..1)
    MAX-ACCESS  read-write
    STATUS      current
    DESCRIPTION
        "inactiveUniqueOnceOnSwitch:
        0  always on(default)
        1  once on."
    ::= { inactiveRuleEntry 15 }

inactiveRuleOnceOnAgingTime   OBJECT-TYPE    
    SYNTAX      INTEGER(0..168)
    MAX-ACCESS  read-write
    STATUS      current
    DESCRIPTION
        "aging time, hour, default value 0, means don't care aging time."
    ::= { inactiveRuleEntry 16 }

inactiveRuleAuthSnFmt   OBJECT-TYPE    
    SYNTAX      INTEGER {
                mix(0),
                hex(1)
                }
    MAX-ACCESS  read-write
    STATUS      current
    DESCRIPTION
        "Serial number format, mixed or hexadecimal."
    ::= { inactiveRuleEntry 17 }

inactiveRuleAuthPwFmt   OBJECT-TYPE    
    SYNTAX      INTEGER {
                string(0),
                hex(1)
                }
    MAX-ACCESS  read-write
    STATUS      current
    DESCRIPTION
        "Password format, string or hexadecimal."
    ::= { inactiveRuleEntry 18 }

inactiveRuleOntStatus   OBJECT-TYPE    
    SYNTAX      INTEGER {
                Unused(0),
                Inused(1)
                }
    MAX-ACCESS  read-only
    STATUS      current
    DESCRIPTION
        "Ont status.
        0: Ont has never been online
        1: Ont online or offline"
    ::= { inactiveRuleEntry 19 }

-- 1.1.2.7. inactiveUniqueConfig --------------------------
inactiveUniqueConfig OBJECT IDENTIFIER ::= { deployInactive 7 }

-- 1.1.2.7.1. inactiveUniquePrimaryTable
-- 1.1.2.7.2. inactiveUniqueSipAgentInfoTable
-- 1.1.2.7.3. inactiveUniqueSipUserAddrTable
-- 1.1.2.7.4. inactiveUniqueSipUserInfoTable
-- 1.1.2.7.5. inactiveUniqueSipDigitMapTable
-- 1.1.2.7.6. inactiveUniqueGemportTable 
-- 1.1.2.7.7. inactiveUniqueCportTable
-- 1.1.2.7.8. inactiveUniqueEportTable
-- 1.1.2.7.9. inactiveUniqueTcontTable
-- 1.1.2.7.10. inactiveUniqueAlarmRefTable
-- 1.1.2.7.11. inactiveUniqueManageTable
-- 1.1.2.7.12. inactiveUniqueWanTable

-- 1.1.2.7.1. inactiveUniquePrimaryTable ------------------
inactiveUniquePrimaryTable  OBJECT-TYPE
        SYNTAX      SEQUENCE OF InactiveUniquePrimaryEntry
        MAX-ACCESS  not-accessible
        STATUS      current
        DESCRIPTION
            "inactive domain unique primary table"
        ::= { inactiveUniqueConfig 1 }

inactiveUniquePrimaryEntry  OBJECT-TYPE
        SYNTAX      InactiveUniquePrimaryEntry
        MAX-ACCESS  not-accessible
        STATUS      current
        DESCRIPTION
            "entry of inactive unique primary table"
        INDEX { inactiveUniqueIndex }
        ::= { inactiveUniquePrimaryTable 1 }

InactiveUniquePrimaryEntry  ::= 
        SEQUENCE 
        {
            inactiveUniqueIndex        INTEGER,
            inactiveUniqueName         OCTET STRING,
            inactiveUniqueSignFlag     INTEGER,
            inactiveUniqueSn           OCTET STRING,
            inactiveUniqueLoid         OCTET STRING,
            inactiveUniqueSlotId       INTEGER,
            inactiveUniquePportId      INTEGER,
            inactiveUniqueOntId        INTEGER,
            inactiveUniqueOntDesc      OCTET STRING,
            inactiveUniqueRowStatus    RowStatus,
            inactiveUniqueOnceOnSwitch       INTEGER,
            inactiveUniqueOnceOnAgingTime    INTEGER,
            inactiveUniqueRangingBalance     INTEGER
        }

inactiveUniqueIndex OBJECT-TYPE    
    SYNTAX      INTEGER(0..2047)
    MAX-ACCESS  read-only
    STATUS      current
    DESCRIPTION
        "The index of unique primary table, should be inputted with <0-2047>.
         The range is not always fit, please see range in commands."
    ::= { inactiveUniquePrimaryEntry 1 }

inactiveUniqueName OBJECT-TYPE
    SYNTAX      OCTET STRING (SIZE(0..255))
    MAX-ACCESS  read-write
    STATUS      current
    DESCRIPTION
        "unique name, max length: 128."
    ::= { inactiveUniquePrimaryEntry 2 }

inactiveUniqueSignFlag OBJECT-TYPE
    SYNTAX      INTEGER(1..3)
    MAX-ACCESS  read-write
    STATUS      current
    DESCRIPTION
        "inactiveUniqueSignFlag:
        1  mode sn
        2  mode loid
        3  mode slot-id/pport-id/ont-id."
    ::= { inactiveUniquePrimaryEntry 3 }

inactiveUniqueSn OBJECT-TYPE
    SYNTAX      OCTET STRING (SIZE(0..255))
    MAX-ACCESS  read-write
    STATUS      current
    DESCRIPTION
        "unique sn, now only support string-hex format, not support hex format, max length: 13."
    ::= { inactiveUniquePrimaryEntry 4 }

inactiveUniqueLoid OBJECT-TYPE
    SYNTAX      OCTET STRING (SIZE(0..255))
    MAX-ACCESS  read-write
    STATUS      current
    DESCRIPTION
        "unique loid, now only support string format, max length: 24."
    ::= { inactiveUniquePrimaryEntry 5 }

inactiveUniqueSlotId OBJECT-TYPE
    SYNTAX      INTEGER(0..0)
    MAX-ACCESS  read-write
    STATUS      current
    DESCRIPTION
        "slot id."
    ::= { inactiveUniquePrimaryEntry 6 }

inactiveUniquePportId OBJECT-TYPE
    SYNTAX      INTEGER(1..16)
    MAX-ACCESS  read-write
    STATUS      current
    DESCRIPTION
        "pon port id."
    ::= { inactiveUniquePrimaryEntry 7 }

inactiveUniqueOntId OBJECT-TYPE
    SYNTAX      INTEGER(1..128)
    MAX-ACCESS  read-write
    STATUS      current
    DESCRIPTION
        "ont id."
    ::= { inactiveUniquePrimaryEntry 8 }

inactiveUniqueOntDesc OBJECT-TYPE
    SYNTAX      OCTET STRING (SIZE(0..255))
    MAX-ACCESS  read-write
    STATUS      current
    DESCRIPTION
        "ont description, max length: 128."
    ::= { inactiveUniquePrimaryEntry 9 }

inactiveUniqueRowStatus OBJECT-TYPE    
    SYNTAX      RowStatus
    MAX-ACCESS  read-write
    STATUS      current
    DESCRIPTION
        "RowStatus"
    ::= { inactiveUniquePrimaryEntry 10 }

inactiveUniqueOnceOnSwitch   OBJECT-TYPE    
    SYNTAX      INTEGER(0..1)
    MAX-ACCESS  read-write
    STATUS      current
    DESCRIPTION
        "inactiveUniqueOnceOnSwitch:
        0  always on(default)
        1  once on."
    ::= { inactiveUniquePrimaryEntry 11 }

inactiveUniqueOnceOnAgingTime   OBJECT-TYPE    
    SYNTAX      INTEGER(0..168)
    MAX-ACCESS  read-write
    STATUS      current
    DESCRIPTION
        "aging time, default value 0, means don't care aging time."
    ::= { inactiveUniquePrimaryEntry 12 }

inactiveUniqueRangingBalance   OBJECT-TYPE    
    SYNTAX      INTEGER(-10000..10000)
    MAX-ACCESS  read-write
    STATUS      current
    DESCRIPTION
        "ranging balance, default value 0, unit: m."
    ::= { inactiveUniquePrimaryEntry 13 }

-- 1.1.2.7.2. inactiveUniqueSipAgentInfoTable --------------
inactiveUniqueSipAgentInfoTable  OBJECT-TYPE
        SYNTAX      SEQUENCE OF InactiveUniqueSipAgentInfoEntry
        MAX-ACCESS  not-accessible
        STATUS      current
        DESCRIPTION
            "inactive domain unique voip sip agent info table"
        ::= { inactiveUniqueConfig 2 }

inactiveUniqueSipAgentInfoEntry  OBJECT-TYPE
        SYNTAX      InactiveUniqueSipAgentInfoEntry
        MAX-ACCESS  not-accessible
        STATUS      current
        DESCRIPTION
            "entry of inactive unique voip sip agent info table"
        INDEX { inactiveUniqueIndexI }
        ::= { inactiveUniqueSipAgentInfoTable 1 }

InactiveUniqueSipAgentInfoEntry  ::= 
        SEQUENCE 
        {
            inactiveUniqueIndexI                INTEGER,
            inactiveUniqueSipProxyServerIp      OCTET STRING,
            inactiveUniqueSipOutboundProxyIp    OCTET STRING,
            inactiveUniqueSipRegisterServerIp   OCTET STRING,
            inactiveUniqueSipAgentInfoPort      INTEGER,
            inactiveUniqueSipAgentInfoRowStatus RowStatus
        }

inactiveUniqueIndexI OBJECT-TYPE    
    SYNTAX      INTEGER(0..2047)
    MAX-ACCESS  read-only
    STATUS      current
    DESCRIPTION
        "The index of unique primary table, should be inputted with <0-2047>.
         The range is not always fit, please see range in commands."
    ::= { inactiveUniqueSipAgentInfoEntry 1 }

inactiveUniqueSipProxyServerIp OBJECT-TYPE    
    SYNTAX      OCTET STRING (SIZE(1..64))
    MAX-ACCESS  read-write
    STATUS      current
    DESCRIPTION
        "voip sip agent info proxy server ip address."
    ::= { inactiveUniqueSipAgentInfoEntry 2 }

inactiveUniqueSipOutboundProxyIp OBJECT-TYPE    
    SYNTAX      OCTET STRING (SIZE(1..64))
    MAX-ACCESS  read-write
    STATUS      current
    DESCRIPTION
        "voip sip agent info outbound proxy ip address."
    ::= { inactiveUniqueSipAgentInfoEntry 3 }

inactiveUniqueSipRegisterServerIp OBJECT-TYPE    
    SYNTAX      OCTET STRING (SIZE(1..64))
    MAX-ACCESS  read-write
    STATUS      current
    DESCRIPTION
        "voip sip agent info register server ip address."
    ::= { inactiveUniqueSipAgentInfoEntry 4 }

inactiveUniqueSipAgentInfoPort OBJECT-TYPE    
    SYNTAX      INTEGER(1..65535)
    MAX-ACCESS  read-write
    STATUS      current
    DESCRIPTION
        "voip sip agent info port."
    ::= { inactiveUniqueSipAgentInfoEntry 5 }

inactiveUniqueSipAgentInfoRowStatus OBJECT-TYPE    
    SYNTAX      RowStatus
    MAX-ACCESS  read-write
    STATUS      current
    DESCRIPTION
        "RowStatus"
    ::= { inactiveUniqueSipAgentInfoEntry 6 }

-- 1.1.2.7.3. inactiveUniqueSipUserAddrTable --------------
inactiveUniqueSipUserAddrTable  OBJECT-TYPE
        SYNTAX      SEQUENCE OF InactiveUniqueSipUserAddrEntry
        MAX-ACCESS  not-accessible
        STATUS      current
        DESCRIPTION
            "inactive domain unique voip sip user ip address table"
        ::= { inactiveUniqueConfig 3 }

inactiveUniqueSipUserAddrEntry  OBJECT-TYPE
        SYNTAX      InactiveUniqueSipUserAddrEntry
        MAX-ACCESS  not-accessible
        STATUS      current
        DESCRIPTION
            "entry of inactive unique voip sip user ip address table"
        INDEX { inactiveUniqueIndexII }
        ::= { inactiveUniqueSipUserAddrTable 1 }

InactiveUniqueSipUserAddrEntry  ::= 
        SEQUENCE 
        {
            inactiveUniqueIndexII              INTEGER,
            inactiveUniqueSipuAddressIp        IpAddress,
            inactiveUniqueSipuAddressMask      IpAddress,
            inactiveUniqueSipuAddressVlan      INTEGER,
            inactiveUniqueSipuAddressPri       INTEGER,
            inactiveUniqueSipuAddressRowStatus RowStatus,
            inactiveUniqueSipuAddressGateway   IpAddress,
            inactiveUniqueSipuAddressMasterDns IpAddress,
            inactiveUniqueSipuAddressSlaveDns  IpAddress,
            inactiveUniqueSipuAddressHost      INTEGER,
            inactiveUniqueSipuAddressMode      INTEGER
        }

inactiveUniqueIndexII OBJECT-TYPE    
    SYNTAX      INTEGER(0..2047)
    MAX-ACCESS  read-only
    STATUS      current
    DESCRIPTION
        "The index of unique primary table, should be inputted with <0-2047>.
         The range is not always fit, please see range in commands."
    ::= { inactiveUniqueSipUserAddrEntry 1 }

inactiveUniqueSipuAddressIp OBJECT-TYPE    
    SYNTAX      IpAddress
    MAX-ACCESS  read-write
    STATUS      current
    DESCRIPTION
        "voip sip user ip address."
    ::= { inactiveUniqueSipUserAddrEntry 2 }

inactiveUniqueSipuAddressMask OBJECT-TYPE    
    SYNTAX      IpAddress
    MAX-ACCESS  read-write
    STATUS      current
    DESCRIPTION
        "voip sip user mask."
    ::= { inactiveUniqueSipUserAddrEntry 3 }

inactiveUniqueSipuAddressVlan OBJECT-TYPE    
    SYNTAX      INTEGER(1..4094)
    MAX-ACCESS  read-write
    STATUS      current
    DESCRIPTION
        "voip sip user vlan."
    ::= { inactiveUniqueSipUserAddrEntry 4 }

inactiveUniqueSipuAddressPri OBJECT-TYPE    
    SYNTAX      INTEGER(0..7)
    MAX-ACCESS  read-write
    STATUS      current
    DESCRIPTION
        "voip sip user priroty."
    ::= { inactiveUniqueSipUserAddrEntry 5 }

inactiveUniqueSipuAddressRowStatus OBJECT-TYPE    
    SYNTAX      RowStatus
    MAX-ACCESS  read-write
    STATUS      current
    DESCRIPTION
        "RowStatus"
    ::= { inactiveUniqueSipUserAddrEntry 6 }

inactiveUniqueSipuAddressGateway OBJECT-TYPE    
    SYNTAX      IpAddress
    MAX-ACCESS  read-write
    STATUS      current
    DESCRIPTION
        "voip sip user gateway."
    ::= { inactiveUniqueSipUserAddrEntry 7 }
    
inactiveUniqueSipuAddressMasterDns OBJECT-TYPE    
    SYNTAX      IpAddress
    MAX-ACCESS  read-write
    STATUS      current
    DESCRIPTION
        "voip sip user master DNS."
    ::= { inactiveUniqueSipUserAddrEntry 8 }
    
inactiveUniqueSipuAddressSlaveDns OBJECT-TYPE    
    SYNTAX      IpAddress
    MAX-ACCESS  read-write
    STATUS      current
    DESCRIPTION
        "voip sip user slave DNS."
    ::= { inactiveUniqueSipUserAddrEntry 9 }
    
inactiveUniqueSipuAddressHost OBJECT-TYPE    
    SYNTAX      INTEGER(1..4)
    MAX-ACCESS  read-write
    STATUS      current
    DESCRIPTION
        "voip sip user host."
    ::= { inactiveUniqueSipUserAddrEntry 10 }

inactiveUniqueSipuAddressMode OBJECT-TYPE    
    SYNTAX      INTEGER {
                static(0),
                dhcp(1)
                }
    MAX-ACCESS  read-write
    STATUS      current
    DESCRIPTION
        "voip sip user mode.
        0(default): static ip mode;
        1: dhcp mode."
    ::= { inactiveUniqueSipUserAddrEntry 11 }    

-- 1.1.2.7.4. inactiveUniqueSipUserInfoTable --------------
inactiveUniqueSipUserInfoTable  OBJECT-TYPE
        SYNTAX      SEQUENCE OF InactiveUniqueSipUserInfoEntry
        MAX-ACCESS  not-accessible
        STATUS      current
        DESCRIPTION
            "inactive domain unique voip sip user infomation table"
        ::= { inactiveUniqueConfig 4 }

inactiveUniqueSipUserInfoEntry  OBJECT-TYPE
        SYNTAX      InactiveUniqueSipUserInfoEntry
        MAX-ACCESS  not-accessible
        STATUS      current
        DESCRIPTION
            "entry of unique voip sip user infomation table"
        INDEX { inactiveUniqueIndexIII, inactiveUniqueSipuInfoIndex }
        ::= { inactiveUniqueSipUserInfoTable 1 }

InactiveUniqueSipUserInfoEntry  ::= 
        SEQUENCE 
        {
            inactiveUniqueIndexIII          INTEGER,
            inactiveUniqueSipuInfoIndex     INTEGER,
            inactiveUniqueSipuInfoUserName  OCTET STRING,
            inactiveUniqueSipuInfoPassword  OCTET STRING,
            inactiveUniqueSipuInfoTelephone OCTET STRING,
            inactiveUniqueSipuInfoRowStatus RowStatus
        }

inactiveUniqueIndexIII OBJECT-TYPE    
    SYNTAX      INTEGER(0..2047)
    MAX-ACCESS  read-only
    STATUS      current
    DESCRIPTION
        "The index of unique primary table, should be inputted with <0-2047>.
         The range is not always fit, please see range in commands."
    ::= { inactiveUniqueSipUserInfoEntry 1 }

inactiveUniqueSipuInfoIndex OBJECT-TYPE    
    SYNTAX      INTEGER(1..2)
    MAX-ACCESS  read-only
    STATUS      current
    DESCRIPTION
        "The index of voip sip user info, the 2nd index of this table. Should in <1-2>."
    ::= { inactiveUniqueSipUserInfoEntry 2 }

inactiveUniqueSipuInfoUserName OBJECT-TYPE    
    SYNTAX      OCTET STRING (SIZE(0..25))
    MAX-ACCESS  read-write
    STATUS      current
    DESCRIPTION
        "voip sip user infomation user name, max length: 25."
    ::= { inactiveUniqueSipUserInfoEntry 3 }

inactiveUniqueSipuInfoPassword OBJECT-TYPE    
    SYNTAX      OCTET STRING (SIZE(0..25))
    MAX-ACCESS  read-write
    STATUS      current
    DESCRIPTION
        "voip sip user infomation user name, max length: 25."
    ::= { inactiveUniqueSipUserInfoEntry 4 }

inactiveUniqueSipuInfoTelephone OBJECT-TYPE    
    SYNTAX      OCTET STRING (SIZE(0..25))
    MAX-ACCESS  read-write
    STATUS      current
    DESCRIPTION
        "voip sip user infomation user name, max length: 25."
    ::= { inactiveUniqueSipUserInfoEntry 5 }

inactiveUniqueSipuInfoRowStatus OBJECT-TYPE    
    SYNTAX      RowStatus
    MAX-ACCESS  read-write
    STATUS      current
    DESCRIPTION
        "RowStatus"
    ::= { inactiveUniqueSipUserInfoEntry 6 }

-- 1.1.2.7.5. inactiveUniqueSipDigitMapTable --------------
inactiveUniqueSipDigitMapTable  OBJECT-TYPE
        SYNTAX      SEQUENCE OF InactiveUniqueSipDigitMapEntry
        MAX-ACCESS  not-accessible
        STATUS      current
        DESCRIPTION
            "inactive domain unique voip sip digit map table"
        ::= { inactiveUniqueConfig 5 }

inactiveUniqueSipDigitMapEntry  OBJECT-TYPE
        SYNTAX      InactiveUniqueSipDigitMapEntry
        MAX-ACCESS  not-accessible
        STATUS      current
        DESCRIPTION
            "entry of inactive unique voip sip digit map table"
        INDEX { inactiveUniqueIndexIV, inactiveUniqueSipdMapIndex }
        ::= { inactiveUniqueSipDigitMapTable 1 }

InactiveUniqueSipDigitMapEntry  ::= 
        SEQUENCE 
        {
            inactiveUniqueIndexIV              INTEGER,
            inactiveUniqueSipdMapIndex         INTEGER,
            inactiveUniqueSipdMapDialPlanToken OCTET STRING,
            inactiveUniqueSipdMapRowStatus     RowStatus
        }

inactiveUniqueIndexIV OBJECT-TYPE    
    SYNTAX      INTEGER(0..2047)
    MAX-ACCESS  read-only
    STATUS      current
    DESCRIPTION
        "The index of unique primary table, should be inputted with <0-2047>.
         The range is not always fit, please see range in commands."
    ::= { inactiveUniqueSipDigitMapEntry 1 }

inactiveUniqueSipdMapIndex OBJECT-TYPE    
    SYNTAX      INTEGER(1..10)
    MAX-ACCESS  read-only
    STATUS      current
    DESCRIPTION
        "The index of voip digit map, the 2nd index of this table. Should in <1-10>."
    ::= { inactiveUniqueSipDigitMapEntry 2 }

inactiveUniqueSipdMapDialPlanToken OBJECT-TYPE    
    SYNTAX      OCTET STRING (SIZE(0..28))
    MAX-ACCESS  read-write
    STATUS      current
    DESCRIPTION
        "voip sip digit map dial plan token, max length: 28."
    ::= { inactiveUniqueSipDigitMapEntry 3 }

inactiveUniqueSipdMapRowStatus OBJECT-TYPE    
    SYNTAX      RowStatus
    MAX-ACCESS  read-write
    STATUS      current
    DESCRIPTION
        "RowStatus"
    ::= { inactiveUniqueSipDigitMapEntry 4 }

-- 1.1.2.7.6. inactiveUniqueGemportTable --------------------
inactiveUniqueGemportTable  OBJECT-TYPE
        SYNTAX      SEQUENCE OF InactiveUniqueGemportEntry
        MAX-ACCESS  not-accessible
        STATUS      current
        DESCRIPTION
            "inactive domain unique gemport table."
        ::= { inactiveUniqueConfig 6 }

inactiveUniqueGemportEntry  OBJECT-TYPE
        SYNTAX      InactiveUniqueGemportEntry
        MAX-ACCESS  not-accessible
        STATUS      current
        DESCRIPTION
            "entry of inactive unique gemport table"
        INDEX { inactiveUniqueIndexV, inactiveUniqueGemportIndex }
        ::= { inactiveUniqueGemportTable 1 }

InactiveUniqueGemportEntry  ::= 
        SEQUENCE 
        {
            inactiveUniqueIndexV                   INTEGER,
            inactiveUniqueGemportIndex             INTEGER,
            inactiveUniqueGemportVlanProfileId     INTEGER,
            inactiveUniqueGemportUsProfileId       INTEGER,
            inactiveUniqueGemportDsProfileId       INTEGER,
            inactiveUniqueGemportRowStatus         RowStatus
        }

inactiveUniqueIndexV OBJECT-TYPE    
    SYNTAX      INTEGER(0..2047)
    MAX-ACCESS  read-only
    STATUS      current
    DESCRIPTION
        "The 1st index of this table, should be inputted with <0-2047>.
         The range is not always fit, please see range in commands."
    ::= { inactiveUniqueGemportEntry 1 }

inactiveUniqueGemportIndex OBJECT-TYPE    
    SYNTAX      INTEGER(1..24)
    MAX-ACCESS  read-only
    STATUS      current
    DESCRIPTION
        "The index of gemport, the 2nd index of this table.
         Should in <1-24>."
    ::= { inactiveUniqueGemportEntry 2 }

inactiveUniqueGemportVlanProfileId OBJECT-TYPE    
    SYNTAX      INTEGER(0..4095)
    MAX-ACCESS  read-write
    STATUS      current
    DESCRIPTION
        "The gemport vlan profile id, should be inputted with <0-4095>."
    ::= { inactiveUniqueGemportEntry 3 }

inactiveUniqueGemportUsProfileId OBJECT-TYPE    
    SYNTAX      INTEGER(0..4095)
    MAX-ACCESS  read-write
    STATUS      current
    DESCRIPTION
        "The gemport us traffic profile id, should be inputted with <0-4095>."
    ::= { inactiveUniqueGemportEntry 4 }

inactiveUniqueGemportDsProfileId OBJECT-TYPE    
    SYNTAX      INTEGER(0..4095)
    MAX-ACCESS  read-write
    STATUS      current
    DESCRIPTION
        "The gemport ds traffic profile id, should be inputted with <0-4095>."
    ::= { inactiveUniqueGemportEntry 5 }

inactiveUniqueGemportRowStatus OBJECT-TYPE    
    SYNTAX       RowStatus
    MAX-ACCESS   read-write
    STATUS       current
    DESCRIPTION
        "RowStatus"
    ::= { inactiveUniqueGemportEntry 6 }

-- 1.1.2.7.7. inactiveUniqueCportTable --------------------
inactiveUniqueCportTable  OBJECT-TYPE
        SYNTAX      SEQUENCE OF InactiveUniqueCportEntry
        MAX-ACCESS  not-accessible
        STATUS      current
        DESCRIPTION
            "inactive domain unique catv port management table."
        ::= { inactiveUniqueConfig 7 }

inactiveUniqueCportEntry  OBJECT-TYPE
        SYNTAX      InactiveUniqueCportEntry
        MAX-ACCESS  not-accessible
        STATUS      current
        DESCRIPTION
            "entry of inactive unique catv port management table"
        INDEX { inactiveUniqueIndexVI, inactiveUniqueCportIndex }
        ::= { inactiveUniqueCportTable 1 }

InactiveUniqueCportEntry  ::= 
        SEQUENCE 
        {
            inactiveUniqueIndexVI        INTEGER,
            inactiveUniqueCportIndex     INTEGER,
            inactiveUniqueCportSwitch    INTEGER,
            inactiveUniqueCportAgcMode   INTEGER,
            inactiveUniqueCportAgcRange  INTEGER
        }

inactiveUniqueIndexVI OBJECT-TYPE    
    SYNTAX      INTEGER(0..2047)
    MAX-ACCESS  read-only
    STATUS      current
    DESCRIPTION
        "The 1st index of this table, should be inputted with <0-2047>.
         The range is not always fit, please see range in commands."
    ::= { inactiveUniqueCportEntry 1 }

inactiveUniqueCportIndex OBJECT-TYPE    
    SYNTAX       INTEGER(1..4)
    MAX-ACCESS   read-only
    STATUS       current
    DESCRIPTION
        "The index of catv port management, the 2nd index of this table. Should in <1-4>."
    ::= { inactiveUniqueCportEntry 2 }

inactiveUniqueCportSwitch OBJECT-TYPE    
    SYNTAX      INTEGER(0..1)
    MAX-ACCESS  read-write
    STATUS      current
    DESCRIPTION
        "inactiveUniqueCportSwitch:
         0  disable
         1  enable(default)"
    ::= { inactiveUniqueCportEntry 3 }

inactiveUniqueCportAgcMode OBJECT-TYPE    
    SYNTAX       INTEGER(0..2)
    MAX-ACCESS   read-write
    STATUS       current
    DESCRIPTION
        "inactiveUniqueCportAgcMode:
        0  No AGC
        1  Broadband RF AGC
        2  Optical AGC"
    ::= { inactiveUniqueCportEntry 4 }

inactiveUniqueCportAgcRange OBJECT-TYPE    
    SYNTAX      INTEGER(-120..60)
    MAX-ACCESS  read-write
    STATUS      current
    DESCRIPTION
        "catv port agc range, default: 0."
    ::= { inactiveUniqueCportEntry 5 }

-- 1.1.2.7.8. inactiveUniqueEportTable --------------------
inactiveUniqueEportTable  OBJECT-TYPE
        SYNTAX      SEQUENCE OF InactiveUniqueEportEntry
        MAX-ACCESS  not-accessible
        STATUS      current
        DESCRIPTION
            "inactive domain unique ethernet port management table."
        ::= { inactiveUniqueConfig 8 }

inactiveUniqueEportEntry  OBJECT-TYPE
        SYNTAX      InactiveUniqueEportEntry
        MAX-ACCESS  not-accessible
        STATUS      current
        DESCRIPTION
            "entry of inactive unique ethernet port management table"
        INDEX { inactiveUniqueIndexVII, inactiveUniqueEportIndex }
        ::= { inactiveUniqueEportTable 1 }

InactiveUniqueEportEntry  ::= 
        SEQUENCE 
        {
            inactiveUniqueIndexVII       INTEGER,
            inactiveUniqueEportIndex     INTEGER,
            inactiveUniqueEportSwitch    INTEGER,
            inactiveUniqueEportNegMode   INTEGER
        }

inactiveUniqueIndexVII OBJECT-TYPE    
    SYNTAX      INTEGER(0..2047)
    MAX-ACCESS  read-only
    STATUS      current
    DESCRIPTION
        "The 1st index of this table, should be inputted with <0-2047>.
         The range is not always fit, please see range in commands."
    ::= { inactiveUniqueEportEntry 1 }

inactiveUniqueEportIndex OBJECT-TYPE    
    SYNTAX       INTEGER(1..8)
    MAX-ACCESS   read-only
    STATUS       current
    DESCRIPTION
        "The index of ethernet port management, the 2nd index of this table. Should in <1-8>."
    ::= { inactiveUniqueEportEntry 2 }

inactiveUniqueEportSwitch OBJECT-TYPE    
    SYNTAX      INTEGER(0..1)
    MAX-ACCESS  read-write
    STATUS      current
    DESCRIPTION
        "inactiveUniqueEportSwitch:
         0  enable(default)
         1  disable"
    ::= { inactiveUniqueEportEntry 3 }
    -- 暂时尚未实现

inactiveUniqueEportNegMode OBJECT-TYPE    
    SYNTAX       INTEGER(0..23)
    MAX-ACCESS   read-write
    STATUS       current
    DESCRIPTION
        "neg mode contains duplex and speed.
        duplex: 0 auto, 1 full, 2 half
        speed: 0 auto, 1 10M, 2 100M, 3 1000M
        neg mode = duplex * 10 + speed.
        neg mode value 0 means auto duplex auto speed,
        value 11 means full duplex 10M, and so on."
        -- 模式和速率需要同时配，不想用比较麻烦的 rowstatus，用一个节点搞定算了。
        -- 个位数是速率，十位数是双工模式。例如：千兆半双工就是 23
    ::= { inactiveUniqueEportEntry 4 }

-- 1.1.2.7.9. inactiveUniqueTcontTable ----------------------
inactiveUniqueTcontTable  OBJECT-TYPE
        SYNTAX      SEQUENCE OF InactiveUniqueTcontEntry
        MAX-ACCESS  not-accessible
        STATUS      current
        DESCRIPTION
            "inactive domain unique tcont table, now only for tcont bind dba."
        ::= { inactiveUniqueConfig 9 }

inactiveUniqueTcontEntry  OBJECT-TYPE
        SYNTAX      InactiveUniqueTcontEntry
        MAX-ACCESS  not-accessible
        STATUS      current
        DESCRIPTION
            "entry of inactive unique tcont table"
        INDEX { inactiveUniqueIndexVIII, inactiveUniqueTcontIndex }
        ::= { inactiveUniqueTcontTable 1 }

InactiveUniqueTcontEntry  ::= 
        SEQUENCE 
        {
            inactiveUniqueIndexVIII          INTEGER,
            inactiveUniqueTcontIndex         INTEGER,
            inactiveUniqueTcontDbaIndex      INTEGER,
            inactiveUniqueTcontRowStatus     RowStatus
        }

inactiveUniqueIndexVIII OBJECT-TYPE    
    SYNTAX      INTEGER(0..2047)
    MAX-ACCESS  read-only
    STATUS      current
    DESCRIPTION
        "The 1st index of this table, should be inputted with <0-2047>.
         The range is not always fit, please see range in commands."
    ::= { inactiveUniqueTcontEntry 1 }

inactiveUniqueTcontIndex OBJECT-TYPE    
    SYNTAX      INTEGER(1..8)
    MAX-ACCESS  read-only
    STATUS      current
    DESCRIPTION
        "The index of tcont, the 2nd index of this table.
         Should in <1-8>."
    ::= { inactiveUniqueTcontEntry 2 }

inactiveUniqueTcontDbaIndex   OBJECT-TYPE    
    SYNTAX      INTEGER(0..127)
    MAX-ACCESS  read-write
    STATUS      current
    DESCRIPTION
        "The index of tcont bind dba, should be inputted with <0-127>."
    ::= { inactiveUniqueTcontEntry 3 }

inactiveUniqueTcontRowStatus  OBJECT-TYPE    
    SYNTAX      RowStatus
    MAX-ACCESS  read-write
    STATUS      current
    DESCRIPTION
        "RowStatus"
    ::= { inactiveUniqueTcontEntry 4 }

-- 1.1.2.7.10. inactiveUniqueAlarmRefTable --------------------
inactiveUniqueAlarmRefTable  OBJECT-TYPE
        SYNTAX      SEQUENCE OF InactiveUniqueAlarmRefEntry
        MAX-ACCESS  not-accessible
        STATUS      current
        DESCRIPTION
            "inactive unique alarm Reference table."
        ::= { inactiveUniqueConfig 10 }

inactiveUniqueAlarmRefEntry  OBJECT-TYPE
        SYNTAX      InactiveUniqueAlarmRefEntry
        MAX-ACCESS  not-accessible
        STATUS      current
        DESCRIPTION
            "entry of inactive unique alarm Reference table"
        INDEX { inactiveUniqueAlarmRefUIndex }
        ::= { inactiveUniqueAlarmRefTable 1 }

InactiveUniqueAlarmRefEntry  ::= 
        SEQUENCE 
        {
            inactiveUniqueAlarmRefUIndex    INTEGER,
            inactiveUniqueAlarmRefAIndex    INTEGER,
            inactiveUniqueAlarmRefAName     OCTET STRING,
            inactiveUniqueAlarmRefRowStatus RowStatus
        }

inactiveUniqueAlarmRefUIndex OBJECT-TYPE    
    SYNTAX      INTEGER(0..2047)
    MAX-ACCESS  read-only
    STATUS      current
    DESCRIPTION
        "The unique index of this table, should be inputted with <0-2047>.
         The range is not always fit, please see range in commands."
    ::= { inactiveUniqueAlarmRefEntry 1 }

inactiveUniqueAlarmRefAIndex OBJECT-TYPE    
    SYNTAX       INTEGER(0..127)
    MAX-ACCESS   read-create
    STATUS       current
    DESCRIPTION
        "The index of alarm table to reference, Should in <0-127>."
    ::= { inactiveUniqueAlarmRefEntry 2 }

inactiveUniqueAlarmRefAName OBJECT-TYPE    
    SYNTAX      OCTET STRING (SIZE(1..128))
    MAX-ACCESS  read-create
    STATUS      current
    DESCRIPTION
        "The entry name of alarm table to reference, Should in <1-128>."
    ::= { inactiveUniqueAlarmRefEntry 3 }

inactiveUniqueAlarmRefRowStatus OBJECT-TYPE    
    SYNTAX      RowStatus
    MAX-ACCESS  read-create
    STATUS      current
    DESCRIPTION
        "The row status of inactive unique alarm Reference table."
    ::= { inactiveUniqueAlarmRefEntry 4 }

-- 1.1.2.7.11. inactiveUniqueManageTable
inactiveUniqueManageTable  OBJECT-TYPE
        SYNTAX      SEQUENCE OF InactiveUniqueManageEntry
        MAX-ACCESS  not-accessible
        STATUS      current
        DESCRIPTION
            "inactive unique management table."
        ::= { inactiveUniqueConfig 11 }

inactiveUniqueManageEntry  OBJECT-TYPE
        SYNTAX      InactiveUniqueManageEntry
        MAX-ACCESS  not-accessible
        STATUS      current
        DESCRIPTION
            "entry of inactive unique management table"
        INDEX { inactiveUniqueManageIndex }
        ::= { inactiveUniqueManageTable 1 }

InactiveUniqueManageEntry  ::= 
        SEQUENCE 
        {
            inactiveUniqueManageIndex           INTEGER,
            inactiveUniqueManageProtocolPort80  INTEGER
        }

inactiveUniqueManageIndex OBJECT-TYPE    
    SYNTAX      INTEGER(0..2047)
    MAX-ACCESS  read-only
    STATUS      current
    DESCRIPTION
        "The unique index of this table, should be inputted with <0-2047>.
         The range is not always fit, please see range in commands."
    ::= { inactiveUniqueManageEntry 1 }

inactiveUniqueManageProtocolPort80 OBJECT-TYPE    
    SYNTAX      INTEGER { disable_discard(0),
                          disable_forward(1), 
                          enable_discard(2), 
                          enable_forward(3),
                          init(4) }
    MAX-ACCESS  read-write
    STATUS      current
    DESCRIPTION
        "set protocol-port-80 disable mode discard or enable mode forward."
    ::= { inactiveUniqueManageEntry 2 }

-- 1.1.2.7.12. inactiveUniqueWanTable
inactiveUniqueWanTable  OBJECT-TYPE
        SYNTAX      SEQUENCE OF InactiveUniqueWanEntry
        MAX-ACCESS  not-accessible
        STATUS      current
        DESCRIPTION
            "inactive unique wan table."
        ::= { inactiveUniqueConfig 12 }

inactiveUniqueWanEntry  OBJECT-TYPE
        SYNTAX      InactiveUniqueWanEntry
        MAX-ACCESS  not-accessible
        STATUS      current
        DESCRIPTION
            "entry of inactive unique wan table"
        INDEX { inactiveUniqueWanIndex, inactiveUniqueWanNo }
        ::= { inactiveUniqueWanTable 1 }

InactiveUniqueWanEntry  ::= 
        SEQUENCE 
        {
            inactiveUniqueWanIndex           INTEGER,
            inactiveUniqueWanNo              INTEGER,
            inactiveUniqueWanMode            INTEGER,
            inactiveUniqueWanVlan            INTEGER,
            inactiveUniqueWanPriority        INTEGER,
            inactiveUniqueWanPppoeUsername   OCTET STRING,
            inactiveUniqueWanPppoePassword   OCTET STRING,
            inactiveUniqueWanPppoeSerName    OCTET STRING,
            inactiveUniqueWanPppoeAuthMode   INTEGER,
            inactiveUniqueWanPppoeConnMode   INTEGER,
            inactiveUniqueWanPppoeNat        INTEGER,
            inactiveUniqueWanPppoeReleTime   INTEGER,
            inactiveUniqueWanStaticIp        IpAddress,
            inactiveUniqueWanStaticMask      IpAddress,
            inactiveUniqueWanStaticGateway   IpAddress,
            inactiveUniqueWanStaticMasterDns IpAddress,
            inactiveUniqueWanStaticSlaveDns  IpAddress,
            inactiveUniqueWanRowStatus       RowStatus
        }

inactiveUniqueWanIndex OBJECT-TYPE    
    SYNTAX      INTEGER(0..2047)
    MAX-ACCESS  read-only
    STATUS      current
    DESCRIPTION
        "The unique index of this table, should be inputted with <0-2047>.
         The range is not always fit, please see range in commands."
    ::= { inactiveUniqueWanEntry 1 }

inactiveUniqueWanNo OBJECT-TYPE    
    SYNTAX      INTEGER(1..4)
    MAX-ACCESS  read-only
    STATUS      current
    DESCRIPTION
        "The unique index of this table, should be inputted with <1-4>."
    ::= { inactiveUniqueWanEntry 2 }

inactiveUniqueWanMode OBJECT-TYPE    
    SYNTAX      INTEGER { pppoe(1),
                          dhcp(2),
                          static_ip(3) }
    MAX-ACCESS  read-write
    STATUS      current
    DESCRIPTION
        "The unique wan mode of this table, should be inputted with <1-3>."
    ::= { inactiveUniqueWanEntry 3 }

inactiveUniqueWanVlan OBJECT-TYPE    
    SYNTAX      INTEGER (0..4094)
    MAX-ACCESS  read-write
    STATUS      current
    DESCRIPTION
        "The unique wan vlan of this table, should be inputted with <1-4094>.
        0       - Initial value and cannot be set to this value.
        1..4094 - Valid Settings."
    ::= { inactiveUniqueWanEntry 4 }

inactiveUniqueWanPriority OBJECT-TYPE    
    SYNTAX      INTEGER(0..8)
    MAX-ACCESS  read-write
    STATUS      current
    DESCRIPTION
        "The unique wan vlan priority of this table, should be inputted with <0-7>.
        0..7 - Valid Settings.
        8    - Initial value and cannot be set to this value."
    ::= { inactiveUniqueWanEntry 5 }

inactiveUniqueWanPppoeUsername OBJECT-TYPE    
    SYNTAX      OCTET STRING (SIZE(0..128))
    MAX-ACCESS  read-write
    STATUS      current
    DESCRIPTION
        "The unique wan pppoe mode user name of this table.
        0      - Initial len and cannot be set to this len.
        1..128 - Valid Settings."
    ::= { inactiveUniqueWanEntry 6 }

inactiveUniqueWanPppoePassword OBJECT-TYPE    
    SYNTAX      OCTET STRING (SIZE(0..25))
    MAX-ACCESS  read-write
    STATUS      current
    DESCRIPTION
        "The unique wan pppoe mode password of this table.
        0      - Initial len and cannot be set to this len.
        1..25 - Valid Settings."
    ::= { inactiveUniqueWanEntry 7 }

inactiveUniqueWanPppoeSerName OBJECT-TYPE    
    SYNTAX      OCTET STRING (SIZE(0..128))
    MAX-ACCESS  read-write
    STATUS      current
    DESCRIPTION
        "The unique wan pppoe mode service name of this table.
        0      - Initial len and cannot be set to this len.
        1..128 - Valid Settings."
    ::= { inactiveUniqueWanEntry 8 }

inactiveUniqueWanPppoeAuthMode OBJECT-TYPE    
    SYNTAX      INTEGER { auto(0),
                          chap(1),
                          pap(2) }
    MAX-ACCESS  read-write
    STATUS      current
    DESCRIPTION
        "The unique wan pppoe mode authentication mode of this table.
        0 - auto (the default)
        1 - chap
        2 - pap"
    ::= { inactiveUniqueWanEntry 9 }

inactiveUniqueWanPppoeConnMode OBJECT-TYPE    
    SYNTAX      INTEGER { always(0),
                          demand(1) }
    MAX-ACCESS  read-write
    STATUS      current
    DESCRIPTION
        "The unique wan pppoe mode connection mode of this table.
        0 - always (the default)
        1 - demand"
    ::= { inactiveUniqueWanEntry 10 }

inactiveUniqueWanPppoeNat OBJECT-TYPE    
    SYNTAX      INTEGER { disable(0),
                          enable(1) }
    MAX-ACCESS  read-write
    STATUS      current
    DESCRIPTION
        "The unique wan pppoe mode NAT of this table.
        0 - disable
        1 - enable(the default)"
    ::= { inactiveUniqueWanEntry 11 }

inactiveUniqueWanPppoeReleTime OBJECT-TYPE    
    SYNTAX      INTEGER(0..65535)
    MAX-ACCESS  read-write
    STATUS      current
    DESCRIPTION
        "The unique wan pppoe mode release time of this table, should be inputted with <1-65535>.
        0       - Initial value and cannot be set to this value.
        1..65535 - Valid Settings."
    ::= { inactiveUniqueWanEntry 12 }

inactiveUniqueWanStaticIp OBJECT-TYPE    
    SYNTAX      IpAddress
    MAX-ACCESS  read-write
    STATUS      current
    DESCRIPTION
        "The unique wan static ip mode ip address of this table."
    ::= { inactiveUniqueWanEntry 13 }

inactiveUniqueWanStaticMask OBJECT-TYPE    
    SYNTAX      IpAddress
    MAX-ACCESS  read-write
    STATUS      current
    DESCRIPTION
        "The unique wan static ip mode ip mask of this table."
    ::= { inactiveUniqueWanEntry 14 }

inactiveUniqueWanStaticGateway OBJECT-TYPE    
    SYNTAX      IpAddress
    MAX-ACCESS  read-write
    STATUS      current
    DESCRIPTION
        "The unique wan static ip mode ip gateway of this table."
    ::= { inactiveUniqueWanEntry 15 }
    
inactiveUniqueWanStaticMasterDns OBJECT-TYPE    
    SYNTAX      IpAddress
    MAX-ACCESS  read-write
    STATUS      current
    DESCRIPTION
        "The unique wan static ip mode master DNS of this table."
    ::= { inactiveUniqueWanEntry 16 }

inactiveUniqueWanStaticSlaveDns OBJECT-TYPE    
    SYNTAX      IpAddress
    MAX-ACCESS  read-write
    STATUS      current
    DESCRIPTION
        "The unique wan static ip mode slave DNS of this table."
    ::= { inactiveUniqueWanEntry 17 }

inactiveUniqueWanRowStatus OBJECT-TYPE    
    SYNTAX      RowStatus
    MAX-ACCESS  read-write
    STATUS      current
    DESCRIPTION
        "RowStatus"
    ::= { inactiveUniqueWanEntry 18 }

-- 1.1.2.8. inactiveCtrlMcastConfig --------------------------
inactiveCtrlMcastConfig OBJECT IDENTIFIER ::= { deployInactive 8 }

-- 1.1.2.8.1. inactiveCtrlMcastTable 
-- 1.1.2.8.2. inactiveCtrlMcastOntTable 

-- 1.1.2.8.1. inactiveCtrlMcastTable --------------------------

inactiveCtrlMcastTable  OBJECT-TYPE
        SYNTAX      SEQUENCE OF InactiveCtrlMcastEntry
        MAX-ACCESS  not-accessible
        STATUS      current
        DESCRIPTION
            "inactive control multicast table."
        ::= { inactiveCtrlMcastConfig 1 }

inactiveCtrlMcastEntry  OBJECT-TYPE
        SYNTAX      InactiveCtrlMcastEntry
        MAX-ACCESS  not-accessible
        STATUS      current
        DESCRIPTION
            "entry of inactive control muticast table"
        INDEX { inactiveCtrlMcastIndex }
        ::= { inactiveCtrlMcastTable 1 }

InactiveCtrlMcastEntry  ::= 
        SEQUENCE 
        {
            inactiveCtrlMcastIndex        INTEGER,
            inactiveCtrlMcastName         OCTET STRING,
            inactiveCtrlMcastRowStatus    RowStatus
        }

inactiveCtrlMcastIndex  OBJECT-TYPE    
    SYNTAX      INTEGER(0..127)
    MAX-ACCESS  read-only
    STATUS      current
    DESCRIPTION
        "The index of inactive control multicast table, should be inputted with <0-127>.
         The range is not always fit, please see range in commands."
    ::= { inactiveCtrlMcastEntry 1 }

inactiveCtrlMcastName  OBJECT-TYPE
    SYNTAX      OCTET STRING (SIZE(0..255))
    MAX-ACCESS  read-write
    STATUS      current
    DESCRIPTION
        "name of inactive control multicast entry."
    ::= { inactiveCtrlMcastEntry 2 }

inactiveCtrlMcastRowStatus   OBJECT-TYPE    
    SYNTAX      RowStatus
    MAX-ACCESS  read-write
    STATUS      current
    DESCRIPTION
        "RowStatus"
    ::= { inactiveCtrlMcastEntry 3 }

-- 1.1.2.8.2. inactiveCtrlMcastOntTable ------------------------
inactiveCtrlMcastOntTable  OBJECT-TYPE
        SYNTAX      SEQUENCE OF InactiveCtrlMcastOntEntry
        MAX-ACCESS  not-accessible
        STATUS      current
        DESCRIPTION
            "inactive domain control multicast base ont table."
        ::= { inactiveCtrlMcastConfig 2 }

inactiveCtrlMcastOntEntry  OBJECT-TYPE
        SYNTAX      InactiveCtrlMcastOntEntry
        MAX-ACCESS  not-accessible
        STATUS      current
        DESCRIPTION
            "entry of inactive control multicast base ont table"
        INDEX { inactiveCtrlMcastIndexI, inactiveCtrlMcastEntryIndex }
        ::= { inactiveCtrlMcastOntTable 1 }

InactiveCtrlMcastOntEntry  ::= 
        SEQUENCE 
        {
            inactiveCtrlMcastIndexI        INTEGER,
            inactiveCtrlMcastEntryIndex    INTEGER,
            inactiveCtrlMcastAccessType    INTEGER,
            inactiveCtrlMcastVid           INTEGER,
            inactiveCtrlMcastSrcIp         IpAddress,
            inactiveCtrlMcastDstStartIp    IpAddress,
            inactiveCtrlMcastDstEndIp      IpAddress,
            inactiveCtrlMcastGroupBw       INTEGER,
            inactiveCtrlMcastDurationTimes INTEGER,
            inactiveCtrlMcastNumOfTimes    INTEGER,
            inactiveCtrlMcastTimeInterval  INTEGER,
            inactiveCtrlMcastResetTime     INTEGER,
            inactiveCtrlMcastNport         INTEGER,
            inactiveCtrlMcastOntRowStatus   RowStatus
        }

inactiveCtrlMcastIndexI OBJECT-TYPE    
    SYNTAX      INTEGER(0..127)
    MAX-ACCESS  read-only
    STATUS      current
    DESCRIPTION
        "The index of control multicast profile. Should in <0-127>."
    ::= { inactiveCtrlMcastOntEntry 1 }

inactiveCtrlMcastEntryIndex OBJECT-TYPE    
    SYNTAX      INTEGER(0..31)
    MAX-ACCESS  read-only
    STATUS      current
    DESCRIPTION
        "The index of control multicast entry, the 2nd index of this table. Should in <0-31>."
    ::= { inactiveCtrlMcastOntEntry 2 }

inactiveCtrlMcastAccessType OBJECT-TYPE    
    SYNTAX      INTEGER(0..3)
    MAX-ACCESS  read-write
    STATUS      current
    DESCRIPTION
        "inactiveCtrlMcastAccessType:
         0  del one entry
         1  clear all entry
         2  add permit entry
         3  add preview entry"
    ::= { inactiveCtrlMcastOntEntry 3 }

inactiveCtrlMcastVid OBJECT-TYPE    
    SYNTAX      INTEGER(1..4094)
    MAX-ACCESS  read-write
    STATUS      current
    DESCRIPTION
        "control multicast vlan id, should be <1-4094>."
    ::= { inactiveCtrlMcastOntEntry 4 }

inactiveCtrlMcastSrcIp OBJECT-TYPE    
    SYNTAX      IpAddress
    MAX-ACCESS  read-write
    STATUS      current
    DESCRIPTION
        "control multicast source ip address."
    ::= { inactiveCtrlMcastOntEntry 5 }

inactiveCtrlMcastDstStartIp OBJECT-TYPE    
    SYNTAX      IpAddress
    MAX-ACCESS  read-write
    STATUS      current
    DESCRIPTION
        "control multicast destination start ip address."
    ::= { inactiveCtrlMcastOntEntry 6 }

inactiveCtrlMcastDstEndIp OBJECT-TYPE    
    SYNTAX      IpAddress
    MAX-ACCESS  read-write
    STATUS      current
    DESCRIPTION
        "control multicast destination end ip address."
    ::= { inactiveCtrlMcastOntEntry 7 }

inactiveCtrlMcastGroupBw OBJECT-TYPE    
    SYNTAX      INTEGER(1..1024000)
    MAX-ACCESS  read-write
    STATUS      current
    DESCRIPTION
        "control multicast group bandwidth, should be <1-1024000>."
    ::= { inactiveCtrlMcastOntEntry 8 }

inactiveCtrlMcastDurationTimes OBJECT-TYPE    
    SYNTAX      INTEGER(10..6000)
    MAX-ACCESS  read-write
    STATUS      current
    DESCRIPTION
        "control multicast duration times, should be <10-6000>."
    ::= { inactiveCtrlMcastOntEntry 9 }

inactiveCtrlMcastNumOfTimes OBJECT-TYPE    
    SYNTAX      INTEGER(1..255)
    MAX-ACCESS  read-write
    STATUS      current
    DESCRIPTION
        "control multicast number of times, should be <1-255>."
    ::= { inactiveCtrlMcastOntEntry 10 }

inactiveCtrlMcastTimeInterval OBJECT-TYPE    
    SYNTAX      INTEGER(1..7200)
    MAX-ACCESS  read-write
    STATUS      current
    DESCRIPTION
        "control multicast time interval, should be <1-7200>."
    ::= { inactiveCtrlMcastOntEntry 11 }

inactiveCtrlMcastResetTime OBJECT-TYPE    
    SYNTAX      INTEGER(1..24)
    MAX-ACCESS  read-write
    STATUS      current
    DESCRIPTION
        "control multicast reset time o'clock, should be <1-24>."
    ::= { inactiveCtrlMcastOntEntry 12 }

inactiveCtrlMcastNport OBJECT-TYPE    
    SYNTAX      INTEGER(1..25)
    MAX-ACCESS  read-write
    STATUS      current
    DESCRIPTION
        "ethernet port number 1-24 of the entry assigned, default 25 means ctrl mcast base ont."
    ::= { inactiveCtrlMcastOntEntry 13 }

inactiveCtrlMcastOntRowStatus OBJECT-TYPE    
    SYNTAX       RowStatus
    MAX-ACCESS   read-write
    STATUS       current
    DESCRIPTION
        "RowStatus"
    ::= { inactiveCtrlMcastOntEntry 14 }


-- 1.1.2.9. inactiveCtrlAlarmConfig --------------------------
inactiveCtrlAlarmConfig OBJECT IDENTIFIER ::= { deployInactive 9 }

-- 1.1.2.9.1. inactiveCtrlAlarmTable 
-- 1.1.2.9.2. inactiveCtrlAlarmThrldTable 

-- 1.1.2.9.1. inactiveCtrlAlarmTable --------------------------
inactiveCtrlAlarmTable  OBJECT-TYPE
        SYNTAX      SEQUENCE OF InactiveCtrlAlarmEntry
        MAX-ACCESS  not-accessible
        STATUS      current
        DESCRIPTION
            "inactive control alarm table."
        ::= { inactiveCtrlAlarmConfig 1 }

inactiveCtrlAlarmEntry  OBJECT-TYPE
        SYNTAX      InactiveCtrlAlarmEntry
        MAX-ACCESS  not-accessible
        STATUS      current
        DESCRIPTION
            "entry of inactive control alarm table"
        INDEX { inactiveCtrlAlarmAimIndex }
        ::= { inactiveCtrlAlarmTable 1 }

InactiveCtrlAlarmEntry  ::= 
        SEQUENCE 
        {
            inactiveCtrlAlarmAimIndex			INTEGER,
            inactiveCtrlAlarmAimName			OCTET STRING,
            inactiveCtrlAlarmReferLine          OCTET STRING,
            inactiveCtrlAlarmReferUnique        OCTET STRING,
            inactiveCtrlAlarmRowStatus			RowStatus
        }

inactiveCtrlAlarmAimIndex  OBJECT-TYPE    
    SYNTAX      INTEGER(0..127)
    MAX-ACCESS  read-only
    STATUS      current
    DESCRIPTION
        "The index of inactive control alarm table, should be <0-127>.
         The range is not always fit, please see range in commands."
    ::= { inactiveCtrlAlarmEntry 1 }

inactiveCtrlAlarmAimName   OBJECT-TYPE    
    SYNTAX      OCTET STRING (SIZE(1..128))
    MAX-ACCESS  read-create
    STATUS      current
    DESCRIPTION
        "the name of aim."
    ::= { inactiveCtrlAlarmEntry 2 }

inactiveCtrlAlarmReferLine   OBJECT-TYPE    
    SYNTAX      OCTET STRING
    MAX-ACCESS  read-only
    STATUS      current
    DESCRIPTION
        "Line bitmap, each line references this aim."
    ::= { inactiveCtrlAlarmEntry 3 }

inactiveCtrlAlarmReferUnique   OBJECT-TYPE    
    SYNTAX      OCTET STRING
    MAX-ACCESS  read-only
    STATUS      current
    DESCRIPTION
        "Unique bitmap, each unique references this aim."
    ::= { inactiveCtrlAlarmEntry 4 }
                                        
inactiveCtrlAlarmRowStatus   OBJECT-TYPE    
    SYNTAX      RowStatus
    MAX-ACCESS  read-create
    STATUS      current
    DESCRIPTION
        "The inactive control alarm table rowStatus."
    ::= { inactiveCtrlAlarmEntry 5 }


-- 1.1.2.9.2. inactiveCtrlAlarmThrldTable  --------------------------
inactiveCtrlAlarmThrldTable  OBJECT-TYPE
        SYNTAX      SEQUENCE OF InactiveCtrlAlarmThrldEntry
        MAX-ACCESS  not-accessible
        STATUS      current
        DESCRIPTION
            "inactive control alarm threshold table."
        ::= { inactiveCtrlAlarmConfig 2 }

inactiveCtrlAlarmThrldEntry  OBJECT-TYPE
        SYNTAX      InactiveCtrlAlarmThrldEntry
        MAX-ACCESS  not-accessible
        STATUS      current
        DESCRIPTION
            "entry of inactive control alarm threshold table"
        INDEX { inactiveCtrlAlarmThrldAimIndex, inactiveCtrlAlarmThrldRxOrTx}
        ::= { inactiveCtrlAlarmThrldTable 1 }

InactiveCtrlAlarmThrldEntry  ::= 
        SEQUENCE 
        {
            inactiveCtrlAlarmThrldAimIndex	INTEGER,
            inactiveCtrlAlarmThrldRxOrTx	INTEGER,
            inactiveCtrlAlarmThrldHigh      INTEGER,
            inactiveCtrlAlarmThrldLow       INTEGER
       }

inactiveCtrlAlarmThrldAimIndex  OBJECT-TYPE    
    SYNTAX      INTEGER(0..127)
    MAX-ACCESS  read-only
    STATUS      current
    DESCRIPTION
        "The index of inactive control alarm threshold table, should be <0-127>.
         The range is not always fit, please see range in commands."
    ::= { inactiveCtrlAlarmThrldEntry 1 }
                                 
inactiveCtrlAlarmThrldRxOrTx    OBJECT-TYPE
    SYNTAX      INTEGER { none(0), rx(1), tx(2) }
    MAX-ACCESS  read-only
    STATUS      current
    DESCRIPTION
        "The secend index of inactive control alarm threshold entry."
    ::= { inactiveCtrlAlarmThrldEntry 2 }

inactiveCtrlAlarmThrldHigh   OBJECT-TYPE    
    SYNTAX      INTEGER(0..254)
    MAX-ACCESS  read-write
    STATUS      current
    DESCRIPTION
        "The high threshold of rx or tx alarm, The actual value is half the input value,
        if the threshold is rx, the actual value is the opposite."
    ::= { inactiveCtrlAlarmThrldEntry 3 }

inactiveCtrlAlarmThrldLow   OBJECT-TYPE    
    SYNTAX      INTEGER(0..254)
    MAX-ACCESS  read-write
    STATUS      current
    DESCRIPTION
        "The low threshold of rx or tx alarm, The actual value is half the input value,
        if the threshold is rx, the actual value is the opposite."
    ::= { inactiveCtrlAlarmThrldEntry 4 }


-- 1.1.3. deployActive ----------------------------------
deployActive OBJECT IDENTIFIER ::= { configDevice 3 }

-- 1.1.3.1. activeAuthTable 
-- 1.1.3.2. activeDbaTable
-- 1.1.3.3. activeLineCommonConfig
-- 1.1.3.4. activeLineSFUConfig
-- 1.1.3.5. activeLineHGUConfig
-- 1.1.3.6. activeRuleTable
-- 1.1.3.7. activeUniqueConfig

-- 1.1.3.1. activeAuthTable ------------------------------
activeAuthTable  OBJECT-TYPE
        SYNTAX      SEQUENCE OF ActiveAuthEntry
        MAX-ACCESS  not-accessible
        STATUS      current
        DESCRIPTION
            "active domain auth table"
        ::= { deployActive 1 }

activeAuthEntry  OBJECT-TYPE
        SYNTAX      ActiveAuthEntry
        MAX-ACCESS  not-accessible
        STATUS      current
        DESCRIPTION
            "entry of active auth table"
        INDEX { activeAuthIndex }
        ::= { activeAuthTable 1 }

ActiveAuthEntry  ::= 
        SEQUENCE 
        {
            activeAuthIndex         INTEGER,
            activeAuthDescription   OCTET STRING,
            activeAuthMode          INTEGER,
            activeAuthSn            OCTET STRING,
            activeAuthPw            OCTET STRING,
            activeAuthLoid          OCTET STRING,
            activeAuthLopw          OCTET STRING,
            activeAuthAssignedSlot  OCTET STRING,
            activeAuthAssignedPport OCTET STRING,
            activeAuthAssignedOnt   OCTET STRING
        }

activeAuthIndex  OBJECT-TYPE    
    SYNTAX      INTEGER(0..4095)
    MAX-ACCESS  read-only
    STATUS      current
    DESCRIPTION
        "The index of active auth table, should be inputted with <0-4095>.
         The range is not always fit, please see range in commands."
    ::= { activeAuthEntry 1 }

activeAuthDescription  OBJECT-TYPE
    SYNTAX      OCTET STRING (SIZE(0..255))
    MAX-ACCESS  read-only
    STATUS      current
    DESCRIPTION
        "auth description, max length: 128."
    ::= { activeAuthEntry 2 }

activeAuthMode OBJECT-TYPE    
    SYNTAX      INTEGER(0..5)
    MAX-ACCESS  read-only
    STATUS      current
    DESCRIPTION
        "activeAuthMode:
         0  auth mode sn
         1  auth mode pw
         2  auth mode sn_pw
         3  auth mode loid
         4  auth mode lopw
         5  auth mode loid_lopw"
    ::= { activeAuthEntry 3 }

activeAuthSn  OBJECT-TYPE
    SYNTAX      OCTET STRING (SIZE(0..255))
    MAX-ACCESS  read-only
    STATUS      current
    DESCRIPTION
        "auth sn, string-hex, max length: 16."
    ::= { activeAuthEntry 4 }

activeAuthPw  OBJECT-TYPE
    SYNTAX      OCTET STRING (SIZE(0..255))
    MAX-ACCESS  read-only
    STATUS      current
    DESCRIPTION
        "auth password, string, max length: 20."
    ::= { activeAuthEntry 5 }

activeAuthLoid  OBJECT-TYPE
    SYNTAX      OCTET STRING (SIZE(0..255))
    MAX-ACCESS  read-only
    STATUS      current
    DESCRIPTION
        "auth loid, max length: 24."
    ::= { activeAuthEntry 6 }

activeAuthLopw  OBJECT-TYPE
    SYNTAX      OCTET STRING (SIZE(0..255))
    MAX-ACCESS  read-only
    STATUS      current
    DESCRIPTION
        "auth logic password, max length: 12."
    ::= { activeAuthEntry 7 }

activeAuthAssignedSlot OBJECT-TYPE    
    SYNTAX       OCTET STRING (SIZE(0..255))
    MAX-ACCESS   read-only
    STATUS       current
    DESCRIPTION
        "slot id pre assigned. if not configed, its '-'."
    ::= { activeAuthEntry 8 }

activeAuthAssignedPport OBJECT-TYPE    
    SYNTAX        OCTET STRING (SIZE(0..255))
    MAX-ACCESS    read-only
    STATUS        current
    DESCRIPTION
        "pon port id pre assigned. if not configed, its '-'."
    ::= { activeAuthEntry 9 }

activeAuthAssignedOnt OBJECT-TYPE    
    SYNTAX      OCTET STRING (SIZE(0..255))
    MAX-ACCESS  read-only
    STATUS      current
    DESCRIPTION
        "ont id pre assigned. if not configed, its '-'."
    ::= { activeAuthEntry 10 }

-- 1.1.3.2. activeDbaTable ------------------------------
activeDbaTable  OBJECT-TYPE
        SYNTAX      SEQUENCE OF ActiveDbaEntry
        MAX-ACCESS  not-accessible
        STATUS      current
        DESCRIPTION
            "active domain dba table"
        ::= { deployActive 2 }

activeDbaEntry  OBJECT-TYPE
        SYNTAX      ActiveDbaEntry
        MAX-ACCESS  not-accessible
        STATUS      current
        DESCRIPTION
            "entry of active dba table"
        INDEX { activeDbaIndex }
        ::= { activeDbaTable 1 }

ActiveDbaEntry  ::= 
        SEQUENCE 
        {
            activeDbaIndex            INTEGER,
            activeDbaDescription      OCTET STRING,
            activeDbaType             INTEGER,
            activeDbaFixBandwidth     INTEGER,
            activeDbaAssuredBandwidth INTEGER,
            activeDbaMaxBandwidth     INTEGER
        }

activeDbaIndex OBJECT-TYPE    
    SYNTAX      INTEGER(0..127)
    MAX-ACCESS  read-only
    STATUS      current
    DESCRIPTION
        "The index of active dba table, should be inputted with <0-127>."
    ::= { activeDbaEntry 1 }

activeDbaDescription  OBJECT-TYPE
    SYNTAX      OCTET STRING (SIZE(0..255))
    MAX-ACCESS  read-only
    STATUS      current
    DESCRIPTION
        "active dba description, max length: 128."
    ::= { activeDbaEntry 2 }
    
activeDbaType OBJECT-TYPE
    SYNTAX      INTEGER(1..5)
    MAX-ACCESS  read-only
    STATUS      current
    DESCRIPTION
        "activeDbaType, 
         1  fixed bandwidth
         2  assured bandwidth
         3  assured and max bandwidth
         4  max bandwidth
         5  fixed and assured and max bandwidth"
    ::= { activeDbaEntry 3 }
    
activeDbaFixBandwidth OBJECT-TYPE
    SYNTAX      INTEGER(128..1310720)
    MAX-ACCESS  read-only
    STATUS      current
    DESCRIPTION
        "Must to be divisible by 64kbps, must not less than 128 kbps."
    ::= { activeDbaEntry 4 }

activeDbaAssuredBandwidth OBJECT-TYPE
    SYNTAX       INTEGER(0..1310592)
    MAX-ACCESS   read-only
    STATUS       current
    DESCRIPTION
        "Must to be divisible by 64kbps, Can be 0.  
         If not 0, it must be at least 256 kbps."
    ::= { activeDbaEntry 5 }

activeDbaMaxBandwidth OBJECT-TYPE
    SYNTAX      INTEGER(0..1310720)
    MAX-ACCESS  read-only
    STATUS      current
    DESCRIPTION
        "Must to be divisible by 64kbps, and must not be less than 
        the sum of assured BW plus fixedBW. 
        Must less than 1310720 kbps"
    ::= { activeDbaEntry 6 }    

-- 1.1.3.3. activeLineCommonConfig ----------------------
activeLineCommonConfig OBJECT IDENTIFIER ::= { deployActive 3 }

-- 1.1.3.3.1. activeLinePrimaryTable
-- 1.1.3.3.2. activeLineTcontTable
-- 1.1.3.3.3. activeLineGemportTable
-- 1.1.3.3.4. activeLineFlowmappingTable
-- 1.1.3.3.5. activeLineAttrMgmtTable

-- 1.1.3.3.1. activeLinePrimaryTable --------------------
activeLinePrimaryTable  OBJECT-TYPE
        SYNTAX      SEQUENCE OF ActiveLinePrimaryEntry
        MAX-ACCESS  not-accessible
        STATUS      current
        DESCRIPTION
            "active domain line primary table"
        ::= { activeLineCommonConfig 1 }

activeLinePrimaryEntry  OBJECT-TYPE
        SYNTAX      ActiveLinePrimaryEntry
        MAX-ACCESS  not-accessible
        STATUS      current
        DESCRIPTION
            "entry of active line primary table"
        INDEX { activeLineIndex }
        ::= { activeLinePrimaryTable 1 }

ActiveLinePrimaryEntry  ::= 
        SEQUENCE 
        {
            activeLineIndex          INTEGER,
            activeLineDeviceType     OCTET STRING,
            activeLineDescription    OCTET STRING,
            activeLineTrafficMode    INTEGER,
            activeLineMappingMode    INTEGER
        }

activeLineIndex OBJECT-TYPE    
    SYNTAX      INTEGER(0..4095)
    MAX-ACCESS  read-only
    STATUS      current
    DESCRIPTION
        "The index of line primary table, should be inputted with <0-4095>.
         The range is not always fit, please see range in commands."
    ::= { activeLinePrimaryEntry 1 }

activeLineDeviceType  OBJECT-TYPE    
    SYNTAX      OCTET STRING (SIZE(7..7))
    MAX-ACCESS  read-only
    STATUS      current
    DESCRIPTION
        "activeLineDeviceType:
            c30-214  2ETH(1ETH+1iTV)+1POTS SFU
            c30-400  4ETH SFU
            c30-401  4ETH+WIFI HGU
            c30-420  4ETH+2POTS SFU
            c30-423  4ETH+2POTS+WIFI+USB HGU
            c31-423  4ETH+2POTS+WIFI+USB HGU+SFU
            c40-100  1ETH SFU
            c40-201  2ETH+WIFI HGU
            c40-210  1GE+1FE+1POTS HGU
            c40-427  4ETH(3ETH+1iTV)+2POTS+WIFI+USB HGU
            d10-423  4ETH+2POTS+WIFI+USB HGU
            f10-427  4ETH(3ETH+1iTV)+2POTS+WIFI+USB HGU
            h60-100  1ETH SFU
            l30-100  1ETH SFU
            l30-210  2ETH+1POTS SFU
            m50-420  4ETH+2POTS SFU
            n20-100  1ETH SFU
            n20-400  4ETH SFU
            n40-100  1ETH SFU
            s10-214  2ETH(1ETH+1iTV)+1POTS HGU
            s30-100  1ETH SFU
            t10-100  1ETH SFU
            t10-214  2ETH(1ETH+1iTV)+1POTS SFU
            t10-403  4ETH+WIFI+USB HGU
            t10-420  4ETH+2POTS SFU
            t10-423  4ETH+2POTS+WIFI+USB HGU
            t10-427  4ETH(3ETH+1iTV)+2POTS+WIFI+USB HGU
            t60-100  1ETH SFU"
    ::= { activeLinePrimaryEntry 2 }

activeLineDescription OBJECT-TYPE
    SYNTAX      OCTET STRING (SIZE(0..255))
    MAX-ACCESS  read-only
    STATUS      current
    DESCRIPTION
        "line description, max length: 128."
    ::= { activeLinePrimaryEntry 3 }

activeLineTrafficMode OBJECT-TYPE    
    SYNTAX      INTEGER(0..1)
    MAX-ACCESS  read-only
    STATUS      current
    DESCRIPTION
        "activeLineTrafficMode:
         0  pri-queue: priority queue scheduling
         1  gem-car: GEM traffic control"
    ::= { activeLinePrimaryEntry 4 }

activeLineMappingMode OBJECT-TYPE    
    SYNTAX      INTEGER(0..6)
    MAX-ACCESS  read-only
    STATUS      current
    DESCRIPTION
        "activeLineMappingMode:
         0  vlan
         1  priority
         2  vlan-priority
         3  port
         4  port-vlan
         5  port-priority
         6  port-vlan-priority"
    ::= { activeLinePrimaryEntry 5 }

-- 1.1.3.3.2. activeLineTcontTable ----------------------
activeLineTcontTable  OBJECT-TYPE
        SYNTAX      SEQUENCE OF ActiveLineTcontEntry
        MAX-ACCESS  not-accessible
        STATUS      current
        DESCRIPTION
            "active domain line tcont table, now only for tcont bind dba."
        ::= { activeLineCommonConfig 2 }

activeLineTcontEntry  OBJECT-TYPE
        SYNTAX      ActiveLineTcontEntry
        MAX-ACCESS  not-accessible
        STATUS      current
        DESCRIPTION
            "entry of active line tcont table"
        INDEX { activeLineIndexI, activeLineTcontIndex }
        ::= { activeLineTcontTable 1 }

ActiveLineTcontEntry  ::= 
        SEQUENCE 
        {
            activeLineIndexI             INTEGER,
            activeLineTcontIndex         INTEGER,
            activeLineTcontDbaIndex      INTEGER
        }

activeLineIndexI OBJECT-TYPE    
    SYNTAX      INTEGER(0..4095)
    MAX-ACCESS  read-only
    STATUS      current
    DESCRIPTION
        "The index of line primary table, should be inputted with <0-4095>.
         The range is not always fit, please see range in commands."
    ::= { activeLineTcontEntry 1 }

activeLineTcontIndex OBJECT-TYPE    
    SYNTAX      INTEGER(1..8)
    MAX-ACCESS  read-only
    STATUS      current
    DESCRIPTION
        "The index of tcont, the 2nd index of this table.
         Should in <1-8>."
    ::= { activeLineTcontEntry 2 }

activeLineTcontDbaIndex   OBJECT-TYPE    
    SYNTAX      INTEGER(0..127)
    MAX-ACCESS  read-only
    STATUS      current
    DESCRIPTION
        "The index of tcont bind dba, should be inputted with <0-127>."
    ::= { activeLineTcontEntry 3 }

-- 1.1.3.3.3. activeLineGemportTable --------------------
activeLineGemportTable  OBJECT-TYPE
        SYNTAX      SEQUENCE OF ActiveLineGemportEntry
        MAX-ACCESS  not-accessible
        STATUS      current
        DESCRIPTION
            "active domain line gemport table."
        ::= { activeLineCommonConfig 3 }

activeLineGemportEntry  OBJECT-TYPE
        SYNTAX      ActiveLineGemportEntry
        MAX-ACCESS  not-accessible
        STATUS      current
        DESCRIPTION
            "entry of active line gemport table"
        INDEX { activeLineIndexII, activeLineGemportIndex }
        ::= { activeLineGemportTable 1 }

ActiveLineGemportEntry  ::= 
        SEQUENCE 
        {
            activeLineIndexII            INTEGER,
            activeLineGemportIndex       INTEGER,
            activeLineGemportVpStagged   INTEGER,
            activeLineGemportSvid        INTEGER,
            activeLineGemportPriority    INTEGER,
            activeLineGemportTcontId     INTEGER,
            activeLineGemportPq          INTEGER,
            activeLineGemportCir         INTEGER,
            activeLineGemportPir         INTEGER,
            activeLineGemportCbs         INTEGER,
            activeLineGemportPbs         INTEGER
        }

activeLineIndexII OBJECT-TYPE    
    SYNTAX      INTEGER(0..4095)
    MAX-ACCESS  read-only
    STATUS      current
    DESCRIPTION
        "The index of line primary table, should be inputted with <0-4095>.
         The range is not always fit, please see range in commands."
    ::= { activeLineGemportEntry 1 }

activeLineGemportIndex OBJECT-TYPE    
    SYNTAX      INTEGER(1..24)
    MAX-ACCESS  read-only
    STATUS      current
    DESCRIPTION
        "The index of gemport, the 2nd index of this table.
         Should in <1-24>."
    ::= { activeLineGemportEntry 2 }

activeLineGemportVpStagged OBJECT-TYPE    
    SYNTAX      INTEGER(0..1)
    MAX-ACCESS  read-only
    STATUS      current
    DESCRIPTION
        "activeLineGemportVpStagged:
        0  false
        1  true"
    ::= { activeLineGemportEntry 3 }

activeLineGemportSvid  OBJECT-TYPE    
    SYNTAX      INTEGER(1..4094)
    MAX-ACCESS  read-only
    STATUS      current
    DESCRIPTION
        "The gemport service vlan index, should be inputted with <1-4094>."
    ::= { activeLineGemportEntry 4 }

activeLineGemportPriority OBJECT-TYPE    
    SYNTAX      INTEGER(0..7)
    MAX-ACCESS  read-only
    STATUS      current
    DESCRIPTION
        "The gemport priority, should be inputted with <0-7>. Now not use."
    ::= { activeLineGemportEntry 5 }

activeLineGemportTcontId  OBJECT-TYPE    
    SYNTAX      INTEGER(1..8)
    MAX-ACCESS  read-only
    STATUS      current
    DESCRIPTION
        "The gemport bind tcont index, should be inputted with <1-8>."
    ::= { activeLineGemportEntry 6 }

activeLineGemportPq OBJECT-TYPE    
    SYNTAX      INTEGER(0..7)
    MAX-ACCESS  read-only
    STATUS      current
    DESCRIPTION
        "The gemport priority queue, should be inputted with <0-7>."
    ::= { activeLineGemportEntry 7 }

activeLineGemportCir OBJECT-TYPE    
    SYNTAX      INTEGER(64..1310720)
    MAX-ACCESS  read-only
    STATUS      current
    DESCRIPTION
        "The gemport committed infomation rate, should be inputted with <64-10240000>.
         must to be divisible by 64kbps,must not less than 64 kbps."
    ::= { activeLineGemportEntry 8 }

activeLineGemportPir OBJECT-TYPE    
    SYNTAX      INTEGER(64..1310720)
    MAX-ACCESS  read-only
    STATUS      current
    DESCRIPTION
        "The gemport peek infomation rate, should be inputted with <64-10240000>.
         must to be divisible by 64kbps,must not less than 64 kbps."
    ::= { activeLineGemportEntry 9 }

activeLineGemportCbs OBJECT-TYPE    
    SYNTAX      INTEGER(2000..1310720)
    MAX-ACCESS  read-only
    STATUS      current
    DESCRIPTION
        "The gemport committed burst size, should be inputted with <2000-10240000>."
    ::= { activeLineGemportEntry 10 }

activeLineGemportPbs OBJECT-TYPE    
    SYNTAX      INTEGER(2000..1310720)
    MAX-ACCESS  read-only
    STATUS      current
    DESCRIPTION
        "The gemport peek burst size, should be inputted with <2000-10240000>."
    ::= { activeLineGemportEntry 11 }

-- 1.1.3.3.4. activeLineFlowmappingTable ----------------
activeLineFlowmappingTable  OBJECT-TYPE
        SYNTAX      SEQUENCE OF ActiveLineFlowmappingEntry
        MAX-ACCESS  not-accessible
        STATUS      current
        DESCRIPTION
            "active domain line flow mapping table."
        ::= { activeLineCommonConfig 4 }

activeLineFlowmappingEntry  OBJECT-TYPE
        SYNTAX      ActiveLineFlowmappingEntry
        MAX-ACCESS  not-accessible
        STATUS      current
        DESCRIPTION
            "entry of active line flow mapping table"
        INDEX { activeLineIndexIII, activeLineFlowmappingIndex }
        ::= { activeLineFlowmappingTable 1 }

ActiveLineFlowmappingEntry  ::= 
        SEQUENCE 
        {
            activeLineIndexIII             INTEGER,
            activeLineFlowmappingIndex     INTEGER,
            activeLineFlowmappingVid       INTEGER,
            activeLineFlowmappingPriority  INTEGER,
            activeLineFlowmappingEthport   INTEGER,
            activeLineFlowmappingGemport   INTEGER,
            activeLineFlowmappingType      INTEGER
        }

activeLineIndexIII OBJECT-TYPE    
    SYNTAX      INTEGER(0..4095)
    MAX-ACCESS  read-only
    STATUS      current
    DESCRIPTION
        "The index of line primary table, should be inputted with <0-4095>.
         The range is not always fit, please see range in commands."
    ::= { activeLineFlowmappingEntry 1 }

activeLineFlowmappingIndex OBJECT-TYPE    
    SYNTAX       INTEGER(1..48)
    MAX-ACCESS   read-only
    STATUS       current
    DESCRIPTION
        "The index of flowmapping, the 2nd index of this table. Should in <1-48>.
         The range is not always fit, please see range in commands."
    ::= { activeLineFlowmappingEntry 2 }

activeLineFlowmappingVid  OBJECT-TYPE    
    SYNTAX      INTEGER(1..4094)
    MAX-ACCESS  read-only
    STATUS      current
    DESCRIPTION
        "The flow mapping vid, should be inputted with <1-4094>."
    ::= { activeLineFlowmappingEntry 3 }

activeLineFlowmappingPriority OBJECT-TYPE    
    SYNTAX          INTEGER(0..8)
    MAX-ACCESS      read-only
    STATUS          current
    DESCRIPTION
        "The flow mapping priority, should be inputted with <0-8>.
         Value 8 means don't care 802.1p priority."
    ::= { activeLineFlowmappingEntry 4 }

activeLineFlowmappingEthport OBJECT-TYPE    
    SYNTAX       INTEGER(1..8)
    MAX-ACCESS   read-only
    STATUS       current
    DESCRIPTION
        "The flow mapping ethernet port id, should be inputted with <1-8>."
    ::= { activeLineFlowmappingEntry 5 }

activeLineFlowmappingGemport OBJECT-TYPE    
    SYNTAX         INTEGER(1..24)
    MAX-ACCESS     read-only
    STATUS         current
    DESCRIPTION
        "The flow mapping gem port id, should be inputted with <1-24>."
    ::= { activeLineFlowmappingEntry 6 }

activeLineFlowmappingType OBJECT-TYPE    
    SYNTAX         INTEGER(0..3)
    MAX-ACCESS     read-only
    STATUS         current
    DESCRIPTION
        "activeLineFlowmappingType:
        0  flowmapping not base port.
        1  flowmapping base eth port.
        2  flowmapping base veip port.
        3. flowmapping base iphost port."
    ::= { activeLineFlowmappingEntry 7 }

-- 1.1.3.3.5. activeLineAttrMgmtTable --------------------
activeLineAttrMgmtTable  OBJECT-TYPE
        SYNTAX      SEQUENCE OF ActiveLineAttrMgmtEntry
        MAX-ACCESS  not-accessible
        STATUS      current
        DESCRIPTION
            "active domain line attribute management table."
        ::= { activeLineCommonConfig 5 }

activeLineAttrMgmtEntry  OBJECT-TYPE
        SYNTAX      ActiveLineAttrMgmtEntry
        MAX-ACCESS  not-accessible
        STATUS      current
        DESCRIPTION
            "entry of active line attribute management table"
        INDEX { activeLineIndexIV, activeLineAttrMgmtIndex }
        ::= { activeLineAttrMgmtTable 1 }

ActiveLineAttrMgmtEntry  ::= 
        SEQUENCE 
        {
            activeLineIndexIV              INTEGER,
            activeLineAttrMgmtIndex        INTEGER,
            activeLineAttrMgmtNportType    INTEGER,
            activeLineAttrMgmtNport        INTEGER,
            activeLineAttrMgmtEtypeFilter  INTEGER,
            activeLineAttrMgmtVlanMode     INTEGER,
            activeLineAttrMgmtCvlanVid     INTEGER,
            activeLineAttrMgmtCvlanPri     INTEGER,
            activeLineAttrMgmtSvlanVid     INTEGER,
            activeLineAttrMgmtSvlanPri     INTEGER
        }

activeLineIndexIV OBJECT-TYPE    
    SYNTAX      INTEGER(0..4095)
    MAX-ACCESS  read-only
    STATUS      current
    DESCRIPTION
        "The index of line primary table, should be inputted with <0-4095>.
         The range is not always fit, please see range in commands."
    ::= { activeLineAttrMgmtEntry 1 }

activeLineAttrMgmtIndex OBJECT-TYPE    
    SYNTAX       INTEGER(1..64)
    MAX-ACCESS   read-only
    STATUS       current
    DESCRIPTION
        "The index of attribute management, the 2nd index of this table. Should in <1-64>."
    ::= { activeLineAttrMgmtEntry 2 }

activeLineAttrMgmtNportType OBJECT-TYPE    
    SYNTAX      INTEGER(1..3)
    MAX-ACCESS  read-only
    STATUS      current
    DESCRIPTION
        "activeLineAttrMgmtNportType:
         1  eth port in sfu
         2  veip port in hgu
         3  iphost virtual port, for voip, tdm, etc."
    ::= { activeLineAttrMgmtEntry 3 }

activeLineAttrMgmtNport OBJECT-TYPE    
    SYNTAX       INTEGER(1..64)
    MAX-ACCESS   read-only
    STATUS       current
    DESCRIPTION
        "The port of attribute management, if eport, should in <1-8>."
    ::= { activeLineAttrMgmtEntry 4 }

activeLineAttrMgmtEtypeFilter OBJECT-TYPE    
    SYNTAX      INTEGER(0..3)
    MAX-ACCESS  read-only
    STATUS      current
    DESCRIPTION
        "activeLineAttrMgmtEtypeFilter:
         0  no filter
         1  filter ipoe frame
         2  filter pppoe frame
         3  filter arp frame"
    ::= { activeLineAttrMgmtEntry 5 }

activeLineAttrMgmtVlanMode OBJECT-TYPE    
    SYNTAX      INTEGER(0..4)
    MAX-ACCESS  read-only
    STATUS      current
    DESCRIPTION
        "activeLineAttrMgmtVlanMode:
         0  transparent
         1  tag
         2  translation
         3  trunk
         4  QinQ"
    ::= { activeLineAttrMgmtEntry 6 }

activeLineAttrMgmtCvlanVid OBJECT-TYPE    
    SYNTAX      INTEGER(1..4094)
    MAX-ACCESS  read-only
    STATUS      current
    DESCRIPTION
        "cvlan vid, should be inputted with <1-4094>."
    ::= { activeLineAttrMgmtEntry 7 }

activeLineAttrMgmtCvlanPri OBJECT-TYPE    
    SYNTAX      INTEGER(0..8)
    MAX-ACCESS  read-only
    STATUS      current
    DESCRIPTION
        "The cvlan priority, should be inputted with <0-8>.
         Value 8 means don't care vlan priority."
    ::= { activeLineAttrMgmtEntry 8 }

activeLineAttrMgmtSvlanVid OBJECT-TYPE    
    SYNTAX      INTEGER(1..4094)
    MAX-ACCESS  read-only
    STATUS      current
    DESCRIPTION
        "svlan vid, should be inputted with <1-4094>."
    ::= { activeLineAttrMgmtEntry 9 }

activeLineAttrMgmtSvlanPri OBJECT-TYPE    
    SYNTAX      INTEGER(0..8)
    MAX-ACCESS  read-only
    STATUS      current
    DESCRIPTION
        "svlan priority, should be inputted with <0-8>.
         Value 8 means don't care vlan priority."
    ::= { activeLineAttrMgmtEntry 10 }

-- 1.1.3.4. activeLineSFUConfig --------------------------
activeLineSFUConfig OBJECT IDENTIFIER ::= { deployActive 4 }

-- 1.1.3.4.1. activeLineSFUTable
-- 1.1.3.4.2. activeLineSFUEthportTable
-- 1.1.3.4.3. activeLineSFUCtrlMcastTable

-- 1.1.3.4.1. activeLineSFUTable ------------------------
activeLineSFUTable  OBJECT-TYPE
        SYNTAX      SEQUENCE OF ActiveLineSFUEntry
        MAX-ACCESS  not-accessible
        STATUS      current
        DESCRIPTION
            "active domain line SFU primary table."
        ::= { activeLineSFUConfig 1 }

activeLineSFUEntry  OBJECT-TYPE
        SYNTAX      ActiveLineSFUEntry
        MAX-ACCESS  not-accessible
        STATUS      current
        DESCRIPTION
            "entry of active line sfu primary table"
        INDEX { activeLineIndexV }
        ::= { activeLineSFUTable 1 }

ActiveLineSFUEntry  ::= 
        SEQUENCE 
        {
            activeLineIndexV                  INTEGER,
            activeLineSfuLocalSwitch          INTEGER,
            activeLineSfuLoopDetectSwitch     INTEGER
        }

activeLineIndexV OBJECT-TYPE    
    SYNTAX      INTEGER(0..4095)
    MAX-ACCESS  read-only
    STATUS      current
    DESCRIPTION
        "The index of line primary table, should be inputted with <0-4095>.
         The range is not always fit, please see range in commands."
    ::= { activeLineSFUEntry 1 }

activeLineSfuLocalSwitch OBJECT-TYPE    
    SYNTAX       INTEGER(0..1)
    MAX-ACCESS   read-only
    STATUS       current
    DESCRIPTION
        "activeLineSfuLocalSwitch:
         0  disable(default)
         1  enable."
    ::= { activeLineSFUEntry 2 }

activeLineSfuLoopDetectSwitch  OBJECT-TYPE    
    SYNTAX      INTEGER(0..1)
    MAX-ACCESS  read-only
    STATUS      current
    DESCRIPTION
        "activeLineSfuLoopDetectSwitch:
         0  disable(default)
         1  enable."
    ::= { activeLineSFUEntry 3 }

-- 1.1.3.4.2. activeLineSFUEthportTable ------------------
activeLineSFUEthportTable  OBJECT-TYPE
        SYNTAX      SEQUENCE OF ActiveLineSFUEthportEntry
        MAX-ACCESS  not-accessible
        STATUS      current
        DESCRIPTION
            "active domain line SFU ethernet port table."
        ::= { activeLineSFUConfig 2 }

activeLineSFUEthportEntry  OBJECT-TYPE
        SYNTAX      ActiveLineSFUEthportEntry
        MAX-ACCESS  not-accessible
        STATUS      current
        DESCRIPTION
            "entry of active line SFU ethernet port table"
        INDEX { activeLineIndexVI, activeLineSfuEthportIndex }
        ::= { activeLineSFUEthportTable 1 }

ActiveLineSFUEthportEntry  ::= 
        SEQUENCE 
        {
            activeLineIndexVI                     INTEGER,
            activeLineSfuEthportIndex             INTEGER,
            activeLineSfuEthportSwitch            INTEGER,
            activeLineSfuEthportFlowCtrlSwitch    INTEGER,
            activeLineSfuEthportLoopbackSwitch    INTEGER,
            activeLineSfuEthportFastLeaveSwitch   INTEGER,
            activeLineSfuEthportMaxGroups         INTEGER,
            activeLineSfuEthportMaxMacCount       INTEGER,
            activeLineSfuEthportMcastMode         INTEGER,
            activeLineSfuEthportDsIgmpControlType INTEGER,
            activeLineSfuEthportDsIgmpVid         INTEGER,
            activeLineSfuEthportDsIgmpPri         INTEGER,
            activeLineSfuEthportUsIgmpControlType INTEGER,
            activeLineSfuEthportUsIgmpVid         INTEGER,
            activeLineSfuEthportUsIgmpPri         INTEGER,
            activeLineSfuEthportBwCir             INTEGER,
            activeLineSfuEthportBwCbs             INTEGER,
            activeLineSfuEthportBwPir             INTEGER,
            activeLineSfuEthportBwPbs             INTEGER
        }

activeLineIndexVI OBJECT-TYPE    
    SYNTAX      INTEGER(0..4095)
    MAX-ACCESS  read-only
    STATUS      current
    DESCRIPTION
        "The index of line primary table, should be inputted with <0-4095>.
         The range is not always fit, please see range in commands."
    ::= { activeLineSFUEthportEntry 1 }

activeLineSfuEthportIndex OBJECT-TYPE    
    SYNTAX      INTEGER(1..8)
    MAX-ACCESS  read-only
    STATUS      current
    DESCRIPTION
        "The index of SFU ethernet port, the 2nd index of this table. Should in <1-8>."
    ::= { activeLineSFUEthportEntry 2 }

activeLineSfuEthportSwitch OBJECT-TYPE    
    SYNTAX         INTEGER(0..1)
    MAX-ACCESS     read-only
    STATUS         current
    DESCRIPTION
        "activeLineSfuEthportSwitch:
         0  no shutdown(default)
         1  shutdown"
    ::= { activeLineSFUEthportEntry 3 }

activeLineSfuEthportFlowCtrlSwitch OBJECT-TYPE    
    SYNTAX         INTEGER(0..1)
    MAX-ACCESS     read-only
    STATUS         current
    DESCRIPTION
        "activeLineSfuEthportFlowCtrlSwitch:
         0  disable(default)
         1  enable"
    ::= { activeLineSFUEthportEntry 4 }

activeLineSfuEthportLoopbackSwitch OBJECT-TYPE    
    SYNTAX         INTEGER(0..1)
    MAX-ACCESS     read-only
    STATUS         current
    DESCRIPTION
        "activeLineSfuEthportLoopbackSwitch:
         0  disable(default)
         1  enable"
    ::= { activeLineSFUEthportEntry 5 }

activeLineSfuEthportFastLeaveSwitch OBJECT-TYPE    
    SYNTAX        INTEGER(0..1)
    MAX-ACCESS    read-only
    STATUS        current
    DESCRIPTION
        "activeLineSfuEthportFastLeaveSwitch:
         0  disable(default) 
         1  enable"
    ::= { activeLineSFUEthportEntry 6 }

activeLineSfuEthportMaxGroups OBJECT-TYPE    
    SYNTAX        INTEGER(1..128)
    MAX-ACCESS    read-only
    STATUS        current
    DESCRIPTION
        "The SFU ethernet port max igmp groups, should be inputted with <1-128>."
    ::= { activeLineSFUEthportEntry 7 }

activeLineSfuEthportMaxMacCount OBJECT-TYPE    
    SYNTAX          INTEGER(1..255)
    MAX-ACCESS      read-only
    STATUS          current
    DESCRIPTION
        "The SFU ethernet port max mac address count, should be inputted with <1-255>."
    ::= { activeLineSFUEthportEntry 8 }

activeLineSfuEthportMcastMode OBJECT-TYPE    
    SYNTAX         INTEGER(0..2)
    MAX-ACCESS     read-only
    STATUS         current
    DESCRIPTION
        "activeLineSfuEthportMcastMode(some ont not support):
         0  unconcern(default)
         1  control
         2  igmp snooping"
    ::= { activeLineSFUEthportEntry 9 }

activeLineSfuEthportDsIgmpControlType OBJECT-TYPE    
    SYNTAX          INTEGER(0..5)
    MAX-ACCESS      read-only
    STATUS          current
    DESCRIPTION
        "activeLineSfuEthportDsIgmpControlType:
         0  transparent(default)
         1  strip outer tag
         2  add tag
         3  replace tag
         4  replace only vid
         5  add only vid"
    ::= { activeLineSFUEthportEntry 10 }

activeLineSfuEthportDsIgmpVid OBJECT-TYPE    
    SYNTAX        INTEGER(1..4094)
    MAX-ACCESS    read-only
    STATUS        current
    DESCRIPTION
        "The SFU ethernet port downstream igmp and multicast control vid, 
        should be inputted with <1-4094>."
    ::= { activeLineSFUEthportEntry 11 }

activeLineSfuEthportDsIgmpPri OBJECT-TYPE    
    SYNTAX      INTEGER(0..7)
    MAX-ACCESS  read-only
    STATUS      current
    DESCRIPTION
        "The vlan priority, should be inputted with <0-7>."
    ::= { activeLineSFUEthportEntry 12 }

activeLineSfuEthportUsIgmpControlType OBJECT-TYPE    
    SYNTAX          INTEGER(0..4)
    MAX-ACCESS      read-only
    STATUS          current
    DESCRIPTION
        "activeLineSfuEthportUsIgmpControlType:
         0  transparent(default, only for read)
         1  add tag
         2  replace tag
         3  replace only vid
         4  add only vid"
    ::= { activeLineSFUEthportEntry 13 }

activeLineSfuEthportUsIgmpVid OBJECT-TYPE    
    SYNTAX        INTEGER(1..4094)
    MAX-ACCESS    read-only
    STATUS        current
    DESCRIPTION
        "The SFU ethernet port upstream igmp and multicast control vid, 
        should be inputted with <1-4094>."
    ::= { activeLineSFUEthportEntry 14 }

activeLineSfuEthportUsIgmpPri OBJECT-TYPE    
    SYNTAX      INTEGER(0..7)
    MAX-ACCESS  read-only
    STATUS      current
    DESCRIPTION
        "The vlan priority, should be inputted with <0-7>."
    ::= { activeLineSFUEthportEntry 15 }

activeLineSfuEthportBwCir OBJECT-TYPE    
    SYNTAX       INTEGER(64..1024000)
    MAX-ACCESS   read-write
    STATUS       current
    DESCRIPTION
        "The SFU ethernet port bandwidth egress cir, should be inputted with <64-1024000>."
    ::= { activeLineSFUEthportEntry 16 }

activeLineSfuEthportBwCbs OBJECT-TYPE    
    SYNTAX       INTEGER(2..32000)
    MAX-ACCESS   read-write
    STATUS       current
    DESCRIPTION
        "The SFU ethernet port bandwidth egress cbs, should be inputted with <2-32000>."
    ::= { activeLineSFUEthportEntry 17 }

activeLineSfuEthportBwPir OBJECT-TYPE    
    SYNTAX       INTEGER(64..1024000)
    MAX-ACCESS   read-write
    STATUS       current
    DESCRIPTION
        "The SFU ethernet port bandwidth egress pir, should be inputted with <64-1024000>."
    ::= { activeLineSFUEthportEntry 18 }

activeLineSfuEthportBwPbs OBJECT-TYPE    
    SYNTAX       INTEGER(2..32000)
    MAX-ACCESS   read-write
    STATUS       current
    DESCRIPTION
        "The SFU ethernet port bandwidth egress pbs, should be inputted with <2-32000>."
    ::= { activeLineSFUEthportEntry 19 }

-- 1.1.3.4.3. activeLineSFUCtrlMcastTable ----------------
activeLineSFUCtrlMcastTable  OBJECT-TYPE
        SYNTAX      SEQUENCE OF ActiveLineSFUCtrlMcastEntry
        MAX-ACCESS  not-accessible
        STATUS      current
        DESCRIPTION
            "active domain line SFU ethernet port control multicast table."
        ::= { activeLineSFUConfig 3 }

activeLineSFUCtrlMcastEntry  OBJECT-TYPE
        SYNTAX      ActiveLineSFUCtrlMcastEntry
        MAX-ACCESS  not-accessible
        STATUS      current
        DESCRIPTION
            "entry of active line SFU ethernet port control multicast table"
        INDEX { activeLineIndexVII, activeLineSfuEthportIndexI, activeLineSfuCtrlMcastIndex }
        ::= { activeLineSFUCtrlMcastTable 1 }

ActiveLineSFUCtrlMcastEntry  ::= 
        SEQUENCE 
        {
            activeLineIndexVII                  INTEGER,
            activeLineSfuEthportIndexI          INTEGER,
            activeLineSfuCtrlMcastIndex         INTEGER,
            activeLineSfuCtrlMcastAccessType    INTEGER,
            activeLineSfuCtrlMcastVid           INTEGER,
            activeLineSfuCtrlMcastSrcIp         IpAddress,
            activeLineSfuCtrlMcastDstStartIp    IpAddress,
            activeLineSfuCtrlMcastDstEndIp      IpAddress,
            activeLineSfuCtrlMcastGroupBw       INTEGER,
            activeLineSfuCtrlMcastDurationTimes INTEGER,
            activeLineSfuCtrlMcastNumOfTimes    INTEGER,
            activeLineSfuCtrlMcastTimeInterval  INTEGER,
            activeLineSfuCtrlMcastResetTime     INTEGER
        }

activeLineIndexVII OBJECT-TYPE    
    SYNTAX      INTEGER(0..4095)
    MAX-ACCESS  read-only
    STATUS      current
    DESCRIPTION
        "The index of line primary table, should be inputted with <0-4095>.
         The range is not always fit, please see range in commands."
    ::= { activeLineSFUCtrlMcastEntry 1 }

activeLineSfuEthportIndexI OBJECT-TYPE    
    SYNTAX      INTEGER(1..8)
    MAX-ACCESS  read-only
    STATUS      current
    DESCRIPTION
        "The index of SFU ethernet port, the 2nd index of this table. Should in <1-8>."
    ::= { activeLineSFUCtrlMcastEntry 2 }

activeLineSfuCtrlMcastIndex OBJECT-TYPE    
    SYNTAX      INTEGER(0..31)
    MAX-ACCESS  read-only
    STATUS      current
    DESCRIPTION
        "The index of SFU ethernet port control multicast, the 3rd index of this table. Should in <0-31>."
    ::= { activeLineSFUCtrlMcastEntry 3 }

activeLineSfuCtrlMcastAccessType OBJECT-TYPE    
    SYNTAX      INTEGER(2..3)
    MAX-ACCESS  read-only
    STATUS      current
    DESCRIPTION
        "activeLineSfuCtrlMcastAccessType:
         0  del one entry    -- no use
         1  clear all entry  -- no use
         2  add permit entry
         3  add preview entry"
    ::= { activeLineSFUCtrlMcastEntry 4 }

activeLineSfuCtrlMcastVid OBJECT-TYPE    
    SYNTAX      INTEGER(1..4094)
    MAX-ACCESS  read-only
    STATUS      current
    DESCRIPTION
        "sfu control multicast vlan id, should be <1-4094>."
    ::= { activeLineSFUCtrlMcastEntry 5 }

activeLineSfuCtrlMcastSrcIp OBJECT-TYPE    
    SYNTAX      IpAddress
    MAX-ACCESS  read-only
    STATUS      current
    DESCRIPTION
        "sfu control multicast source ip address."
    ::= { activeLineSFUCtrlMcastEntry 6 }

activeLineSfuCtrlMcastDstStartIp OBJECT-TYPE    
    SYNTAX      IpAddress
    MAX-ACCESS  read-only
    STATUS      current
    DESCRIPTION
        "sfu control multicast destination start ip address. 224.0.1.0-239.255.255.255"
    ::= { activeLineSFUCtrlMcastEntry 7 }

activeLineSfuCtrlMcastDstEndIp OBJECT-TYPE    
    SYNTAX      IpAddress
    MAX-ACCESS  read-only
    STATUS      current
    DESCRIPTION
        "sfu control multicast destination end ip address. 224.0.1.0-239.255.255.255,
         must not smaller than the start ip address. "
    ::= { activeLineSFUCtrlMcastEntry 8 }

activeLineSfuCtrlMcastGroupBw OBJECT-TYPE    
    SYNTAX      INTEGER(1..1024000)
    MAX-ACCESS  read-only
    STATUS      current
    DESCRIPTION
        "sfu control multicast group bandwidth, should be <1-1024000>. default 5000."
    ::= { activeLineSFUCtrlMcastEntry 9 }

activeLineSfuCtrlMcastDurationTimes OBJECT-TYPE    
    SYNTAX      INTEGER(10..6000)
    MAX-ACCESS  read-only
    STATUS      current
    DESCRIPTION
        "sfu control multicast duration times, should be <10-6000>. default 120(s)."
    ::= { activeLineSFUCtrlMcastEntry 10 }

activeLineSfuCtrlMcastNumOfTimes OBJECT-TYPE    
    SYNTAX      INTEGER(1..255)
    MAX-ACCESS  read-only
    STATUS      current
    DESCRIPTION
        "sfu control multicast number of times, should be <1-255>. default 5."
    ::= { activeLineSFUCtrlMcastEntry 11 }

activeLineSfuCtrlMcastTimeInterval OBJECT-TYPE    
    SYNTAX      INTEGER(1..7200)
    MAX-ACCESS  read-only
    STATUS      current
    DESCRIPTION
        "sfu control multicast time interval, should be <1-7200>. default 120(s)."
    ::= { activeLineSFUCtrlMcastEntry 12 }

activeLineSfuCtrlMcastResetTime OBJECT-TYPE    
    SYNTAX      INTEGER(1..24)
    MAX-ACCESS  read-only
    STATUS      current
    DESCRIPTION
        "sfu control multicast reset time, should be <1-24>. default 5(o'clock)"
    ::= { activeLineSFUCtrlMcastEntry 13 }

-- 1.1.3.5. activeLineHGUConfig --------------------------
activeLineHGUConfig OBJECT IDENTIFIER ::= { deployActive 5 }

-- 1.1.3.5.1. activeLineHGUTable
-- 1.1.3.5.2. activeLineHGUCtrlMcastTable

-- 1.1.3.5.1. activeLineHGUTable ------------------------
activeLineHGUTable  OBJECT-TYPE
        SYNTAX      SEQUENCE OF ActiveLineHGUEntry
        MAX-ACCESS  not-accessible
        STATUS      current
        DESCRIPTION
            "active domain line HGU table."
        ::= { activeLineHGUConfig 1 }

activeLineHGUEntry  OBJECT-TYPE
        SYNTAX      ActiveLineHGUEntry
        MAX-ACCESS  not-accessible
        STATUS      current
        DESCRIPTION
            "entry of active line HGU table"
        INDEX { activeLineIndexVIII }
        ::= { activeLineHGUTable 1 }

ActiveLineHGUEntry  ::= 
        SEQUENCE 
        {
            activeLineIndexVIII            INTEGER,
            activeLineHguSwitch            INTEGER,
            activeLineHguFastLeaveSwitch   INTEGER,
            activeLineHguMaxGroups         INTEGER,
            activeLineHguMaxMacCount       INTEGER,
            activeLineHguMcastMode         INTEGER,
            activeLineHguDsIgmpControlType INTEGER,
            activeLineHguDsIgmpVid         INTEGER,
            activeLineHguDsIgmpPri         INTEGER,
            activeLineHguUsIgmpControlType INTEGER,
            activeLineHguUsIgmpVid         INTEGER,
            activeLineHguUsIgmpPri         INTEGER
        }

activeLineIndexVIII OBJECT-TYPE    
    SYNTAX      INTEGER(0..4095)
    MAX-ACCESS  read-only
    STATUS      current
    DESCRIPTION
        "The index of line primary table, should be inputted with <0-4095>.
         The range is not always fit, please see range in commands."
    ::= { activeLineHGUEntry 1 }

activeLineHguSwitch OBJECT-TYPE    
    SYNTAX         INTEGER(0..1)
    MAX-ACCESS     read-only
    STATUS         current
    DESCRIPTION
        "activeLineHguSwitch:
         0  no shutdown(default)
         1  shutdown"
    ::= { activeLineHGUEntry 2 }

activeLineHguFastLeaveSwitch OBJECT-TYPE    
    SYNTAX         INTEGER(0..1)
    MAX-ACCESS     read-only
    STATUS         current
    DESCRIPTION
        "activeLineHguFlowCtrlSwitch:
         0  disable(default)
         1  enable"
    ::= { activeLineHGUEntry 3 }

activeLineHguMaxGroups OBJECT-TYPE    
    SYNTAX        INTEGER(1..128)
    MAX-ACCESS    read-only
    STATUS        current
    DESCRIPTION
        "The HGU max igmp groups, should be inputted with <1-128>."
    ::= { activeLineHGUEntry 4 }

activeLineHguMaxMacCount OBJECT-TYPE    
    SYNTAX          INTEGER(1..255)
    MAX-ACCESS      read-only
    STATUS          current
    DESCRIPTION
        "The HGU max mac address count, should be inputted with <1-255>."
    ::= { activeLineHGUEntry 5 }

activeLineHguMcastMode OBJECT-TYPE    
    SYNTAX         INTEGER(0..2)
    MAX-ACCESS     read-only
    STATUS         current
    DESCRIPTION
        "activeLineHguMcastMode(some ont not support):
         0  unconcern(default)
         1  control
         2  igmp snooping"
    ::= { activeLineHGUEntry 6 }

activeLineHguDsIgmpControlType OBJECT-TYPE    
    SYNTAX          INTEGER(0..5)
    MAX-ACCESS      read-only
    STATUS          current
    DESCRIPTION
        "activeLineHguDsIgmpControlType:
         0  transparent(default)
         1  strip outer tag
         2  add tag
         3  replace tag
         4  replace only vid
         5  add only vid"
    ::= { activeLineHGUEntry 7 }

activeLineHguDsIgmpVid OBJECT-TYPE    
    SYNTAX        INTEGER(1..4094)
    MAX-ACCESS    read-only
    STATUS        current
    DESCRIPTION
        "The HGU downstream igmp and multicast control vid, 
        should be inputted with <1-4094>."
    ::= { activeLineHGUEntry 8 }

activeLineHguDsIgmpPri OBJECT-TYPE    
    SYNTAX      INTEGER(0..7)
    MAX-ACCESS  read-only
    STATUS      current
    DESCRIPTION
        "The vlan priority, should be inputted with <0-7>."
    ::= { activeLineHGUEntry 9 }

activeLineHguUsIgmpControlType OBJECT-TYPE    
    SYNTAX          INTEGER(0..4)
    MAX-ACCESS      read-only
    STATUS          current
    DESCRIPTION
        "activeLineHguUsIgmpControlType:
         0  transparent(default)
         1  add tag
         2  replace tag
         3  replace only vid
         4  add only vid"
    ::= { activeLineHGUEntry 10 }

activeLineHguUsIgmpVid OBJECT-TYPE    
    SYNTAX        INTEGER(1..4094)
    MAX-ACCESS    read-only
    STATUS        current
    DESCRIPTION
        "The HGU upstream igmp and multicast control vid, 
        should be inputted with <1-4094>."
    ::= { activeLineHGUEntry 11 }

activeLineHguUsIgmpPri OBJECT-TYPE    
    SYNTAX      INTEGER(0..7)
    MAX-ACCESS  read-only
    STATUS      current
    DESCRIPTION
        "The vlan priority, should be inputted with <0-7>."
    ::= { activeLineHGUEntry 12 }

-- 1.1.3.5.2. activeLineHGUCtrlMcastTable ----------------
activeLineHGUCtrlMcastTable  OBJECT-TYPE
        SYNTAX      SEQUENCE OF ActiveLineHGUCtrlMcastEntry
        MAX-ACCESS  not-accessible
        STATUS      current
        DESCRIPTION
            "active domain line HGU control multicast table."
        ::= { activeLineHGUConfig 2 }

activeLineHGUCtrlMcastEntry  OBJECT-TYPE
        SYNTAX      ActiveLineHGUCtrlMcastEntry
        MAX-ACCESS  not-accessible
        STATUS      current
        DESCRIPTION
            "entry of active line HGU control multicast table"
        INDEX { activeLineIndexIX, activeLineHguCtrlMcastIndex }
        ::= { activeLineHGUCtrlMcastTable 1 }

ActiveLineHGUCtrlMcastEntry  ::= 
        SEQUENCE 
        {
            activeLineIndexIX                   INTEGER,
            activeLineHguCtrlMcastIndex         INTEGER,
            activeLineHguCtrlMcastAccessType    INTEGER,
            activeLineHguCtrlMcastVid           INTEGER,
            activeLineHguCtrlMcastSrcIp         IpAddress,
            activeLineHguCtrlMcastDstStartIp    IpAddress,
            activeLineHguCtrlMcastDstEndIp      IpAddress,
            activeLineHguCtrlMcastGroupBw       INTEGER,
            activeLineHguCtrlMcastDurationTimes INTEGER,
            activeLineHguCtrlMcastNumOfTimes    INTEGER,
            activeLineHguCtrlMcastTimeInterval  INTEGER,
            activeLineHguCtrlMcastResetTime     INTEGER
        }

activeLineIndexIX OBJECT-TYPE    
    SYNTAX      INTEGER(0..4095)
    MAX-ACCESS  read-only
    STATUS      current
    DESCRIPTION
        "The index of line primary table, should be inputted with <0-4095>.
         The range is not always fit, please see range in commands."
    ::= { activeLineHGUCtrlMcastEntry 1 }

activeLineHguCtrlMcastIndex OBJECT-TYPE    
    SYNTAX      INTEGER(1..16)
    MAX-ACCESS  read-only
    STATUS      current
    DESCRIPTION
        "The index of HGU control multicast, the 2nd index of this table. Should in <1-16>."
    ::= { activeLineHGUCtrlMcastEntry 2 }

activeLineHguCtrlMcastAccessType OBJECT-TYPE    
    SYNTAX      INTEGER(0..3)
    MAX-ACCESS  read-only
    STATUS      current
    DESCRIPTION
        "activeLineHGUCtrlMcastAccessType:
         0  del one entry
         1  clear all entry
         2  add permit entry
         3  add preview entry"
    ::= { activeLineHGUCtrlMcastEntry 3 }

activeLineHguCtrlMcastVid OBJECT-TYPE    
    SYNTAX      INTEGER(1..4094)
    MAX-ACCESS  read-only
    STATUS      current
    DESCRIPTION
        "hgu control multicast vlan id, should be <1-4094>."
    ::= { activeLineHGUCtrlMcastEntry 4 }

activeLineHguCtrlMcastSrcIp OBJECT-TYPE    
    SYNTAX      IpAddress
    MAX-ACCESS  read-only
    STATUS      current
    DESCRIPTION
        "hgu control multicast source ip address."
    ::= { activeLineHGUCtrlMcastEntry 5 }

activeLineHguCtrlMcastDstStartIp OBJECT-TYPE    
    SYNTAX      IpAddress
    MAX-ACCESS  read-only
    STATUS      current
    DESCRIPTION
        "hgu control multicast destination start ip address."
    ::= { activeLineHGUCtrlMcastEntry 6 }

activeLineHguCtrlMcastDstEndIp OBJECT-TYPE    
    SYNTAX      IpAddress
    MAX-ACCESS  read-only
    STATUS      current
    DESCRIPTION
        "hgu control multicast destination end ip address."
    ::= { activeLineHGUCtrlMcastEntry 7 }

activeLineHguCtrlMcastGroupBw OBJECT-TYPE    
    SYNTAX      INTEGER(1..16)
    MAX-ACCESS  read-only
    STATUS      current
    DESCRIPTION
        "hgu control multicast group bandwidth, should be <x-x>."
    ::= { activeLineHGUCtrlMcastEntry 8 }

activeLineHguCtrlMcastDurationTimes OBJECT-TYPE    
    SYNTAX      INTEGER(1..16)
    MAX-ACCESS  read-only
    STATUS      current
    DESCRIPTION
        "hgu control multicast duration times, should be <x-x>."
    ::= { activeLineHGUCtrlMcastEntry 9 }

activeLineHguCtrlMcastNumOfTimes OBJECT-TYPE    
    SYNTAX      INTEGER(1..16)
    MAX-ACCESS  read-only
    STATUS      current
    DESCRIPTION
        "hgu control multicast number of times, should be <x-x>."
    ::= { activeLineHGUCtrlMcastEntry 10 }

activeLineHguCtrlMcastTimeInterval OBJECT-TYPE    
    SYNTAX      INTEGER(1..16)
    MAX-ACCESS  read-only
    STATUS      current
    DESCRIPTION
        "hgu control multicast time interval, should be <x-x>."
    ::= { activeLineHGUCtrlMcastEntry 11 }

activeLineHguCtrlMcastResetTime OBJECT-TYPE    
    SYNTAX      INTEGER(1..16)
    MAX-ACCESS  read-only
    STATUS      current
    DESCRIPTION
        "hgu control multicast reset time, should be <x-x>."
    ::= { activeLineHGUCtrlMcastEntry 12 }

-- 1.1.3.6. activeRuleTable ------------------------------
activeRuleTable  OBJECT-TYPE
        SYNTAX      SEQUENCE OF ActiveRuleEntry
        MAX-ACCESS  not-accessible
        STATUS      current
        DESCRIPTION
            "active domain rule table"
        ::= { deployActive 6 }

activeRuleEntry  OBJECT-TYPE
        SYNTAX      ActiveRuleEntry
        MAX-ACCESS  not-accessible
        STATUS      current
        DESCRIPTION
            "entry of active rule table"
        INDEX { activeRuleIndex }
        ::= { activeRuleTable 1 }

ActiveRuleEntry  ::= 
        SEQUENCE 
        {
            activeRuleIndex          INTEGER,
            activeRuleDescription    OCTET STRING,
            activeRuleAction         INTEGER,
            activeRuleAuthIndex      INTEGER,
            activeRuleLineIndexesStr OCTET STRING,
            activeRuleDefaultLine    INTEGER
        }

activeRuleIndex OBJECT-TYPE    
    SYNTAX      INTEGER(1..4096)
    MAX-ACCESS  read-only
    STATUS      current
    DESCRIPTION
        "The index of rule table, should be inputted with <1-4096>.
         The range is not always fit, please see range in commands."
    ::= { activeRuleEntry 1 }

activeRuleDescription OBJECT-TYPE
    SYNTAX      OCTET STRING (SIZE(0..255))
    MAX-ACCESS  read-only
    STATUS      current
    DESCRIPTION
        "rule description, max length: 128."
    ::= { activeRuleEntry 2 }

activeRuleAction OBJECT-TYPE    
    SYNTAX      INTEGER(0..1)
    MAX-ACCESS  read-only
    STATUS      current
    DESCRIPTION
        "activeRuleAction:
         0  permit
         1  deny"
    ::= { activeRuleEntry 3 }

activeRuleAuthIndex   OBJECT-TYPE    
    SYNTAX      INTEGER(1..4096)
    MAX-ACCESS  read-only
    STATUS      current
    DESCRIPTION
        "The index of rule bind auth, should be inputted with <1-4096>
         The range is not always fit, please see range in commands."
    ::= { activeRuleEntry 4 }
    
activeRuleLineIndexesStr OBJECT-TYPE
    SYNTAX         OCTET STRING (SIZE(0..255))
    MAX-ACCESS     read-only
    STATUS         current
    DESCRIPTION
        "String joined by rule bind line indexes, such as '12,56,1023'.
         A rule can at most bind 8 line models."
    ::= { activeRuleEntry 5 }

activeRuleDefaultLine   OBJECT-TYPE    
    SYNTAX      INTEGER(1..4096)
    MAX-ACCESS  read-only
    STATUS      current
    DESCRIPTION
        "The index of rule default line, should be inputted with <1-4096>
         The range is not always fit, please see range in commands."
    ::= { activeRuleEntry 6 }

-- 1.1.3.7. activeUniqueConfig --------------------------
activeUniqueConfig OBJECT IDENTIFIER ::= { deployActive 7 }

-- 1.1.3.7.1. activeUniquePrimaryTable
-- 1.1.3.7.2. activeUniqueSipAgentInfoTable
-- 1.1.3.7.3. activeUniqueSipUserAddrTable
-- 1.1.3.7.4. activeUniqueSipUserInfoTable
-- 1.1.3.7.5. activeUniqueSipDigitMapTable

-- 1.1.3.7.1. activeUniquePrimaryTable ------------------
activeUniquePrimaryTable  OBJECT-TYPE
        SYNTAX      SEQUENCE OF ActiveUniquePrimaryEntry
        MAX-ACCESS  not-accessible
        STATUS      current
        DESCRIPTION
            "active domain unique primary table"
        ::= { activeUniqueConfig 1 }

activeUniquePrimaryEntry  OBJECT-TYPE
        SYNTAX      ActiveUniquePrimaryEntry
        MAX-ACCESS  not-accessible
        STATUS      current
        DESCRIPTION
            "entry of active unique primary table"
        INDEX { activeUniqueIndex }
        ::= { activeUniquePrimaryTable 1 }

ActiveUniquePrimaryEntry  ::= 
        SEQUENCE 
        {
            activeUniqueIndex        INTEGER,
            activeUniqueDescription  OCTET STRING,
            activeUniqueSn           OCTET STRING
        }

activeUniqueIndex OBJECT-TYPE    
    SYNTAX      INTEGER(1..4096)
    MAX-ACCESS  read-only
    STATUS      current
    DESCRIPTION
        "The index of unique primary table, should be inputted with <1-4096>.
         The range is not always fit, please see range in commands."
    ::= { activeUniquePrimaryEntry 1 }

activeUniqueDescription OBJECT-TYPE
    SYNTAX      OCTET STRING (SIZE(0..255))
    MAX-ACCESS  read-only
    STATUS      current
    DESCRIPTION
        "unique description, max length: 128."
    ::= { activeUniquePrimaryEntry 2 }

activeUniqueSn OBJECT-TYPE
    SYNTAX      OCTET STRING (SIZE(0..255))
    MAX-ACCESS  read-only
    STATUS      current
    DESCRIPTION
        "unique sn, string-hex format, max length: 16."
    ::= { activeUniquePrimaryEntry 3 }

-- 1.1.3.7.2. activeUniqueSipAgentInfoTable --------------
activeUniqueSipAgentInfoTable  OBJECT-TYPE
        SYNTAX      SEQUENCE OF ActiveUniqueSipAgentInfoEntry
        MAX-ACCESS  not-accessible
        STATUS      current
        DESCRIPTION
            "active domain unique voip sip agent info table"
        ::= { activeUniqueConfig 2 }

activeUniqueSipAgentInfoEntry  OBJECT-TYPE
        SYNTAX      ActiveUniqueSipAgentInfoEntry
        MAX-ACCESS  not-accessible
        STATUS      current
        DESCRIPTION
            "entry of active unique voip sip agent info table"
        INDEX { activeUniqueIndexI }
        ::= { activeUniqueSipAgentInfoTable 1 }

ActiveUniqueSipAgentInfoEntry  ::= 
        SEQUENCE 
        {
            activeUniqueIndexI                INTEGER,
            activeUniqueSipProxyServerIp      IpAddress,
            activeUniqueSipOutboundProxyIp    IpAddress,
            activeUniqueSipRegisterServerIp   IpAddress,
            activeUniqueSipAgentInfoPort      INTEGER
        }

activeUniqueIndexI OBJECT-TYPE    
    SYNTAX      INTEGER(1..4096)
    MAX-ACCESS  read-only
    STATUS      current
    DESCRIPTION
        "The index of unique primary table, should be inputted with <1-4096>.
         The range is not always fit, please see range in commands."
    ::= { activeUniqueSipAgentInfoEntry 1 }

activeUniqueSipProxyServerIp OBJECT-TYPE    
    SYNTAX      IpAddress
    MAX-ACCESS  read-only
    STATUS      current
    DESCRIPTION
        "voip sip agent info proxy server ip address."
    ::= { activeUniqueSipAgentInfoEntry 2 }

activeUniqueSipOutboundProxyIp OBJECT-TYPE    
    SYNTAX      IpAddress
    MAX-ACCESS  read-only
    STATUS      current
    DESCRIPTION
        "voip sip agent info outbound proxy ip address."
    ::= { activeUniqueSipAgentInfoEntry 3 }

activeUniqueSipRegisterServerIp OBJECT-TYPE    
    SYNTAX      IpAddress
    MAX-ACCESS  read-only
    STATUS      current
    DESCRIPTION
        "voip sip agent info register server ip address."
    ::= { activeUniqueSipAgentInfoEntry 4 }

activeUniqueSipAgentInfoPort OBJECT-TYPE    
    SYNTAX      INTEGER(1..65535)
    MAX-ACCESS  read-only
    STATUS      current
    DESCRIPTION
        "voip sip agent info port."
    ::= { activeUniqueSipAgentInfoEntry 5 }

-- 1.1.3.7.3. activeUniqueSipUserAddrTable --------------
activeUniqueSipUserAddrTable  OBJECT-TYPE
        SYNTAX      SEQUENCE OF ActiveUniqueSipUserAddrEntry
        MAX-ACCESS  not-accessible
        STATUS      current
        DESCRIPTION
            "active domain unique voip sip user ip address table"
        ::= { activeUniqueConfig 3 }

activeUniqueSipUserAddrEntry  OBJECT-TYPE
        SYNTAX      ActiveUniqueSipUserAddrEntry
        MAX-ACCESS  not-accessible
        STATUS      current
        DESCRIPTION
            "entry of active unique voip sip user ip address table"
        INDEX { activeUniqueIndexII }
        ::= { activeUniqueSipUserAddrTable 1 }

ActiveUniqueSipUserAddrEntry  ::= 
        SEQUENCE 
        {
            activeUniqueIndexII              INTEGER,
            activeUniqueSipuAddressIp        IpAddress,
            activeUniqueSipuAddressMask      IpAddress,
            activeUniqueSipuAddressVlan      INTEGER,
            activeUniqueSipuAddressPri       INTEGER
        }

activeUniqueIndexII OBJECT-TYPE    
    SYNTAX      INTEGER(1..4096)
    MAX-ACCESS  read-only
    STATUS      current
    DESCRIPTION
        "The index of unique primary table, should be inputted with <1-4096>.
         The range is not always fit, please see range in commands."
    ::= { activeUniqueSipUserAddrEntry 1 }

activeUniqueSipuAddressIp OBJECT-TYPE    
    SYNTAX      IpAddress
    MAX-ACCESS  read-only
    STATUS      current
    DESCRIPTION
        "voip sip user ip address."
    ::= { activeUniqueSipUserAddrEntry 2 }

activeUniqueSipuAddressMask OBJECT-TYPE    
    SYNTAX      IpAddress
    MAX-ACCESS  read-only
    STATUS      current
    DESCRIPTION
        "voip sip user mask."
    ::= { activeUniqueSipUserAddrEntry 3 }

activeUniqueSipuAddressVlan OBJECT-TYPE    
    SYNTAX      INTEGER(1..4094)
    MAX-ACCESS  read-only
    STATUS      current
    DESCRIPTION
        "voip sip user vlan."
    ::= { activeUniqueSipUserAddrEntry 4 }

activeUniqueSipuAddressPri OBJECT-TYPE    
    SYNTAX      INTEGER(0..7)
    MAX-ACCESS  read-only
    STATUS      current
    DESCRIPTION
        "voip sip user priroty."
    ::= { activeUniqueSipUserAddrEntry 5 }

-- 1.1.3.7.4. activeUniqueSipUserInfoTable --------------
activeUniqueSipUserInfoTable  OBJECT-TYPE
        SYNTAX      SEQUENCE OF ActiveUniqueSipUserInfoEntry
        MAX-ACCESS  not-accessible
        STATUS      current
        DESCRIPTION
            "active domain unique voip sip user infomation table"
        ::= { activeUniqueConfig 4 }

activeUniqueSipUserInfoEntry  OBJECT-TYPE
        SYNTAX      ActiveUniqueSipUserInfoEntry
        MAX-ACCESS  not-accessible
        STATUS      current
        DESCRIPTION
            "entry of unique voip sip user infomation table"
        INDEX { activeUniqueIndexIII, activeUniqueSipuInfoIndex }
        ::= { activeUniqueSipUserInfoTable 1 }

ActiveUniqueSipUserInfoEntry  ::= 
        SEQUENCE 
        {
            activeUniqueIndexIII          INTEGER,
            activeUniqueSipuInfoIndex     INTEGER,
            activeUniqueSipuInfoUserName  OCTET STRING,
            activeUniqueSipuInfoPassword  OCTET STRING,
            activeUniqueSipuInfoTelephone OCTET STRING
        }

activeUniqueIndexIII OBJECT-TYPE    
    SYNTAX      INTEGER(1..4096)
    MAX-ACCESS  read-only
    STATUS      current
    DESCRIPTION
        "The index of unique primary table, should be inputted with <1-4096>.
         The range is not always fit, please see range in commands."
    ::= { activeUniqueSipUserInfoEntry 1 }

activeUniqueSipuInfoIndex OBJECT-TYPE    
    SYNTAX      INTEGER(1..2)
    MAX-ACCESS  read-only
    STATUS      current
    DESCRIPTION
        "The index of voip sip user info, the 2nd index of this table. Should in <1-2>."
    ::= { activeUniqueSipUserInfoEntry 2 }

activeUniqueSipuInfoUserName OBJECT-TYPE    
    SYNTAX      OCTET STRING (SIZE(0..25))
    MAX-ACCESS  read-only
    STATUS      current
    DESCRIPTION
        "voip sip user infomation user name, max length: 25."
    ::= { activeUniqueSipUserInfoEntry 3 }

activeUniqueSipuInfoPassword OBJECT-TYPE    
    SYNTAX      OCTET STRING (SIZE(0..25))
    MAX-ACCESS  read-only
    STATUS      current
    DESCRIPTION
        "voip sip user infomation user name, max length: 25."
    ::= { activeUniqueSipUserInfoEntry 4 }

activeUniqueSipuInfoTelephone OBJECT-TYPE    
    SYNTAX      OCTET STRING (SIZE(0..25))
    MAX-ACCESS  read-only
    STATUS      current
    DESCRIPTION
        "voip sip user infomation user name, max length: 25."
    ::= { activeUniqueSipUserInfoEntry 5 }

-- 1.1.3.7.5. activeUniqueSipDigitMapTable --------------
activeUniqueSipDigitMapTable  OBJECT-TYPE
        SYNTAX      SEQUENCE OF ActiveUniqueSipDigitMapEntry
        MAX-ACCESS  not-accessible
        STATUS      current
        DESCRIPTION
            "active domain unique voip sip digit map table"
        ::= { activeUniqueConfig 5 }

activeUniqueSipDigitMapEntry  OBJECT-TYPE
        SYNTAX      ActiveUniqueSipDigitMapEntry
        MAX-ACCESS  not-accessible
        STATUS      current
        DESCRIPTION
            "entry of active unique voip sip digit map table"
        INDEX { activeUniqueIndexIV, activeUniqueSipdMapIndex }
        ::= { activeUniqueSipDigitMapTable 1 }

ActiveUniqueSipDigitMapEntry  ::= 
        SEQUENCE 
        {
            activeUniqueIndexIV              INTEGER,
            activeUniqueSipdMapIndex         INTEGER,
            activeUniqueSipdMapDialPlanToken OCTET STRING
        }

activeUniqueIndexIV OBJECT-TYPE    
    SYNTAX      INTEGER(1..4096)
    MAX-ACCESS  read-only
    STATUS      current
    DESCRIPTION
        "The index of unique primary table, should be inputted with <1-4096>.
         The range is not always fit, please see range in commands."
    ::= { activeUniqueSipDigitMapEntry 1 }

activeUniqueSipdMapIndex OBJECT-TYPE    
    SYNTAX      INTEGER(1..10)
    MAX-ACCESS  read-only
    STATUS      current
    DESCRIPTION
        "The index of voip digit map, the 2nd index of this table. Should in <1-10>."
    ::= { activeUniqueSipDigitMapEntry 2 }

activeUniqueSipdMapDialPlanToken OBJECT-TYPE    
    SYNTAX      OCTET STRING (SIZE(0..28))
    MAX-ACCESS  read-only
    STATUS      current
    DESCRIPTION
        "voip sip digit map dial plan token, max length: 28."
    ::= { activeUniqueSipDigitMapEntry 3 }

-- 1.1.4. deployDemo ----------------------------------
deployDemo OBJECT IDENTIFIER ::= { configDevice 4 }

-- 1.1.4.1. demoAuthTable 
-- 1.1.4.2. demoDbaTable
-- 1.1.4.3. demoLineCommonConfig
-- 1.1.4.4. demoLineSFUConfig
-- 1.1.4.5. demoLineHGUConfig
-- 1.1.4.6. demoRuleTable
-- 1.1.4.7. demoUniqueConfig

-- 1.1.4.1. demoAuthTable ------------------------------
demoAuthTable  OBJECT-TYPE
        SYNTAX      SEQUENCE OF DemoAuthEntry
        MAX-ACCESS  not-accessible
        STATUS      current
        DESCRIPTION
            "demo domain auth table"
        ::= { deployDemo 1 }

demoAuthEntry  OBJECT-TYPE
        SYNTAX      DemoAuthEntry
        MAX-ACCESS  not-accessible
        STATUS      current
        DESCRIPTION
            "entry of demo auth table"
        INDEX { demoAuthIndex }
        ::= { demoAuthTable 1 }

DemoAuthEntry  ::= 
        SEQUENCE 
        {
            demoAuthIndex         INTEGER,
            demoAuthDescription   OCTET STRING,
            demoAuthMode          INTEGER,
            demoAuthSn            OCTET STRING,
            demoAuthPw            OCTET STRING,
            demoAuthLoid          OCTET STRING,
            demoAuthLopw          OCTET STRING,
            demoAuthAssignedSlot  OCTET STRING,
            demoAuthAssignedPport OCTET STRING,
            demoAuthAssignedOnt   OCTET STRING
        }

demoAuthIndex  OBJECT-TYPE    
    SYNTAX      INTEGER(0..4095)
    MAX-ACCESS  read-only
    STATUS      current
    DESCRIPTION
        "The index of demo auth table, should be inputted with <0-4095>.
         The range is not always fit, please see range in commands."
    ::= { demoAuthEntry 1 }

demoAuthDescription  OBJECT-TYPE
    SYNTAX      OCTET STRING (SIZE(0..255))
    MAX-ACCESS  read-only
    STATUS      current
    DESCRIPTION
        "auth description, max length: 128."
    ::= { demoAuthEntry 2 }

demoAuthMode OBJECT-TYPE    
    SYNTAX      INTEGER(0..5)
    MAX-ACCESS  read-only
    STATUS      current
    DESCRIPTION
        "demoAuthMode:
         0  auth mode sn
         1  auth mode pw
         2  auth mode sn_pw
         3  auth mode loid
         4  auth mode lopw
         5  auth mode loid_lopw"
    ::= { demoAuthEntry 3 }

demoAuthSn  OBJECT-TYPE
    SYNTAX      OCTET STRING (SIZE(0..255))
    MAX-ACCESS  read-only
    STATUS      current
    DESCRIPTION
        "auth sn, hex string, max length: 16."
    ::= { demoAuthEntry 4 }

demoAuthPw  OBJECT-TYPE
    SYNTAX      OCTET STRING (SIZE(0..255))
    MAX-ACCESS  read-only
    STATUS      current
    DESCRIPTION
        "auth password, hex string, max length: 20."
    ::= { demoAuthEntry 5 }

demoAuthLoid  OBJECT-TYPE
    SYNTAX      OCTET STRING (SIZE(0..255))
    MAX-ACCESS  read-only
    STATUS      current
    DESCRIPTION
        "auth loid, max length: 24."
    ::= { demoAuthEntry 6 }

demoAuthLopw  OBJECT-TYPE
    SYNTAX      OCTET STRING (SIZE(0..255))
    MAX-ACCESS  read-only
    STATUS      current
    DESCRIPTION
        "auth logic password, max length: 12."
    ::= { demoAuthEntry 7 }

demoAuthAssignedSlot OBJECT-TYPE    
    SYNTAX       OCTET STRING (SIZE(0..255))
    MAX-ACCESS   read-only
    STATUS       current
    DESCRIPTION
        "slot id pre assigned."
    ::= { demoAuthEntry 8 }

demoAuthAssignedPport OBJECT-TYPE    
    SYNTAX        OCTET STRING (SIZE(0..255))
    MAX-ACCESS    read-only
    STATUS        current
    DESCRIPTION
        "pon port id pre assigned."
    ::= { demoAuthEntry 9 }

demoAuthAssignedOnt OBJECT-TYPE    
    SYNTAX      OCTET STRING (SIZE(0..255))
    MAX-ACCESS  read-only
    STATUS      current
    DESCRIPTION
        "ont id pre assigned."
    ::= { demoAuthEntry 10 }

-- 1.1.4.2. demoDbaTable ------------------------------
demoDbaTable  OBJECT-TYPE
        SYNTAX      SEQUENCE OF DemoDbaEntry
        MAX-ACCESS  not-accessible
        STATUS      current
        DESCRIPTION
            "demo domain dba table"
        ::= { deployDemo 2 }

demoDbaEntry  OBJECT-TYPE
        SYNTAX      DemoDbaEntry
        MAX-ACCESS  not-accessible
        STATUS      current
        DESCRIPTION
            "entry of demo dba table"
        INDEX { demoDbaIndex }
        ::= { demoDbaTable 1 }

DemoDbaEntry  ::= 
        SEQUENCE 
        {
            demoDbaIndex            INTEGER,
            demoDbaDescription      OCTET STRING,
            demoDbaType             INTEGER,
            demoDbaFixBandwidth     INTEGER,
            demoDbaAssuredBandwidth INTEGER,
            demoDbaMaxBandwidth     INTEGER
        }

demoDbaIndex OBJECT-TYPE    
    SYNTAX      INTEGER(0..127)
    MAX-ACCESS  read-only
    STATUS      current
    DESCRIPTION
        "The index of demo dba table, should be inputted with <0-127>."
    ::= { demoDbaEntry 1 }

demoDbaDescription  OBJECT-TYPE
    SYNTAX      OCTET STRING (SIZE(0..255))
    MAX-ACCESS  read-only
    STATUS      current
    DESCRIPTION
        "demo dba description, max length: 128."
    ::= { demoDbaEntry 2 }
    
demoDbaType OBJECT-TYPE
    SYNTAX      INTEGER(1..5)
    MAX-ACCESS  read-only
    STATUS      current
    DESCRIPTION
        "demoDbaType, 
         1  fixed bandwidth
         2  assured bandwidth
         3  assured and max bandwidth
         4  max bandwidth
         5  fixed and assured and max bandwidth"
    ::= { demoDbaEntry 3 }
    
demoDbaFixBandwidth OBJECT-TYPE
    SYNTAX      INTEGER(128..1310720)
    MAX-ACCESS  read-only
    STATUS      current
    DESCRIPTION
        "Must to be divisible by 64kbps, must not less than 128 kbps."
    ::= { demoDbaEntry 4 }

demoDbaAssuredBandwidth OBJECT-TYPE
    SYNTAX       INTEGER(0..1310592)
    MAX-ACCESS   read-only
    STATUS       current
    DESCRIPTION
        "Must to be divisible by 64kbps, Can be 0.  
         If not 0, it must be at least 256 kbps."
    ::= { demoDbaEntry 5 }

demoDbaMaxBandwidth OBJECT-TYPE
    SYNTAX      INTEGER(0..1310720)
    MAX-ACCESS  read-only
    STATUS      current
    DESCRIPTION
        "Must to be divisible by 64kbps, and must not be less than 
        the sum of assured BW plus fixedBW. 
        Must less than 1310720 kbps"
    ::= { demoDbaEntry 6 }    

-- 1.1.4.3. demoLineCommonConfig ----------------------
demoLineCommonConfig OBJECT IDENTIFIER ::= { deployDemo 3 }

-- 1.1.4.3.1. demoLinePrimaryTable
-- 1.1.4.3.2. demoLineTcontTable
-- 1.1.4.3.3. demoLineGemportTable
-- 1.1.4.3.4. demoLineFlowmappingTable
-- 1.1.4.3.5. demoLineAttrMgmtTable

-- 1.1.4.3.1. demoLinePrimaryTable --------------------
demoLinePrimaryTable  OBJECT-TYPE
        SYNTAX      SEQUENCE OF DemoLinePrimaryEntry
        MAX-ACCESS  not-accessible
        STATUS      current
        DESCRIPTION
            "demo domain line primary table"
        ::= { demoLineCommonConfig 1 }

demoLinePrimaryEntry  OBJECT-TYPE
        SYNTAX      DemoLinePrimaryEntry
        MAX-ACCESS  not-accessible
        STATUS      current
        DESCRIPTION
            "entry of demo line primary table"
        INDEX { demoLineIndex }
        ::= { demoLinePrimaryTable 1 }

DemoLinePrimaryEntry  ::= 
        SEQUENCE 
        {
            demoLineIndex          INTEGER,
            demoLineDeviceType     OCTET STRING,
            demoLineDescription    OCTET STRING,
            demoLineTrafficMode    INTEGER,
            demoLineMappingMode    INTEGER
        }

demoLineIndex OBJECT-TYPE    
    SYNTAX      INTEGER(0..4095)
    MAX-ACCESS  read-only
    STATUS      current
    DESCRIPTION
        "The index of line primary table, should be inputted with <0-4095>.
         The range is not always fit, please see range in commands."
    ::= { demoLinePrimaryEntry 1 }

demoLineDeviceType  OBJECT-TYPE    
    SYNTAX      OCTET STRING(SIZE(7..7))
    MAX-ACCESS  read-only
    STATUS      current
    DESCRIPTION
        "demoLineDeviceType:
            c30-214  2ETH(1ETH+1iTV)+1POTS SFU
            c30-400  4ETH SFU
            c30-401  4ETH+WIFI HGU
            c30-420  4ETH+2POTS SFU
            c30-423  4ETH+2POTS+WIFI+USB HGU
            c31-423  4ETH+2POTS+WIFI+USB HGU+SFU
            c40-100  1ETH SFU
            c40-201  2ETH+WIFI HGU
            c40-210  1GE+1FE+1POTS HGU
            c40-427  4ETH(3ETH+1iTV)+2POTS+WIFI+USB HGU
            d10-423  4ETH+2POTS+WIFI+USB HGU
            f10-427  4ETH(3ETH+1iTV)+2POTS+WIFI+USB HGU
            h60-100  1ETH SFU
            l30-100  1ETH SFU
            l30-210  2ETH+1POTS SFU
            m50-420  4ETH+2POTS SFU
            n20-100  1ETH SFU
            n20-400  4ETH SFU
            n40-100  1ETH SFU
            s10-214  2ETH(1ETH+1iTV)+1POTS HGU
            s30-100  1ETH SFU
            t10-100  1ETH SFU
            t10-214  2ETH(1ETH+1iTV)+1POTS SFU
            t10-403  4ETH+WIFI+USB HGU
            t10-420  4ETH+2POTS SFU
            t10-423  4ETH+2POTS+WIFI+USB HGU
            t10-427  4ETH(3ETH+1iTV)+2POTS+WIFI+USB HGU
            t60-100  1ETH SFU"
    ::= { demoLinePrimaryEntry 2 }

demoLineDescription OBJECT-TYPE
    SYNTAX      OCTET STRING (SIZE(0..255))
    MAX-ACCESS  read-only
    STATUS      current
    DESCRIPTION
        "line description, max length: 128."
    ::= { demoLinePrimaryEntry 3 }

demoLineTrafficMode OBJECT-TYPE    
    SYNTAX      INTEGER(0..1)
    MAX-ACCESS  read-only
    STATUS      current
    DESCRIPTION
        "demoLineTrafficMode:
         0  pri-queue: priority queue scheduling
         1  gem-car: GEM traffic control"
    ::= { demoLinePrimaryEntry 4 }

demoLineMappingMode OBJECT-TYPE    
    SYNTAX      INTEGER(0..6)
    MAX-ACCESS  read-only
    STATUS      current
    DESCRIPTION
        "demoLineMappingMode:
         0  vlan
         1  priority
         2  vlan-priority
         3  port
         4  port-vlan
         5  port-priority
         6  port-vlan-priority"
    ::= { demoLinePrimaryEntry 5 }

-- 1.1.4.3.2. demoLineTcontTable ----------------------
demoLineTcontTable  OBJECT-TYPE
        SYNTAX      SEQUENCE OF DemoLineTcontEntry
        MAX-ACCESS  not-accessible
        STATUS      current
        DESCRIPTION
            "demo domain line tcont table, now only for tcont bind dba."
        ::= { demoLineCommonConfig 2 }

demoLineTcontEntry  OBJECT-TYPE
        SYNTAX      DemoLineTcontEntry
        MAX-ACCESS  not-accessible
        STATUS      current
        DESCRIPTION
            "entry of demo line tcont table"
        INDEX { demoLineIndex, demoLineTcontIndex }
        ::= { demoLineTcontTable 1 }

DemoLineTcontEntry  ::= 
        SEQUENCE 
        {
            demoLineTcontIndex         INTEGER,
            demoLineTcontDbaIndex      INTEGER
        }

demoLineTcontIndex OBJECT-TYPE    
    SYNTAX      INTEGER(1..8)
    MAX-ACCESS  read-only
    STATUS      current
    DESCRIPTION
        "The index of tcont, the 2nd index of this table.
         Should in <1-8>."
    ::= { demoLineTcontEntry 1 }

demoLineTcontDbaIndex   OBJECT-TYPE    
    SYNTAX      INTEGER(0..127)
    MAX-ACCESS  read-only
    STATUS      current
    DESCRIPTION
        "The index of tcont bind dba, should be inputted with <0-127>."
    ::= { demoLineTcontEntry 2 }

-- 1.1.4.3.3. demoLineGemportTable --------------------
demoLineGemportTable  OBJECT-TYPE
        SYNTAX      SEQUENCE OF DemoLineGemportEntry
        MAX-ACCESS  not-accessible
        STATUS      current
        DESCRIPTION
            "demo domain line gemport table."
        ::= { demoLineCommonConfig 3 }

demoLineGemportEntry  OBJECT-TYPE
        SYNTAX      DemoLineGemportEntry
        MAX-ACCESS  not-accessible
        STATUS      current
        DESCRIPTION
            "entry of demo line gemport table"
        INDEX { demoLineIndex, demoLineGemportIndex }
        ::= { demoLineGemportTable 1 }

DemoLineGemportEntry  ::= 
        SEQUENCE 
        {
            demoLineGemportIndex       INTEGER,
            demoLineGemportSvid        INTEGER,
            demoLineGemportTcontId     INTEGER,
            demoLineGemportCir         INTEGER,
            demoLineGemportPir         INTEGER,
            demoLineGemportCbs         INTEGER,
            demoLineGemportPbs         INTEGER,
            demoLineGemportPq          INTEGER
        }

demoLineGemportIndex OBJECT-TYPE    
    SYNTAX      INTEGER(1..24)
    MAX-ACCESS  read-only
    STATUS      current
    DESCRIPTION
        "The index of gemport, the 2nd index of this table.
         Should in <1-24>."
    ::= { demoLineGemportEntry 1 }

demoLineGemportSvid  OBJECT-TYPE    
    SYNTAX      INTEGER(1..4094)
    MAX-ACCESS  read-only
    STATUS      current
    DESCRIPTION
        "The gemport service vlan index, should be inputted with <1-4094>."
    ::= { demoLineGemportEntry 2 }

demoLineGemportTcontId  OBJECT-TYPE    
    SYNTAX      INTEGER(1..8)
    MAX-ACCESS  read-only
    STATUS      current
    DESCRIPTION
        "The gemport bind tcont index, should be inputted with <1-8>."
    ::= { demoLineGemportEntry 3 }

demoLineGemportCir OBJECT-TYPE    
    SYNTAX      INTEGER(64..1310720)
    MAX-ACCESS  read-only
    STATUS      current
    DESCRIPTION
        "The gemport committed infomation rate, should be inputted with <64-1310720>.
         must to be divisible by 64kbps,must not less than 64 kbps."
    ::= { demoLineGemportEntry 4 }

demoLineGemportPir OBJECT-TYPE    
    SYNTAX      INTEGER(64..1310720)
    MAX-ACCESS  read-only
    STATUS      current
    DESCRIPTION
        "The gemport peek infomation rate, should be inputted with <64-1310720>.
         must to be divisible by 64kbps,must not less than 64 kbps."
    ::= { demoLineGemportEntry 5 }

demoLineGemportCbs OBJECT-TYPE    
    SYNTAX      INTEGER(2000..1310720)
    MAX-ACCESS  read-only
    STATUS      current
    DESCRIPTION
        "The gemport committed burst size, should be inputted with <2000-1310720>."
    ::= { demoLineGemportEntry 6 }

demoLineGemportPbs OBJECT-TYPE    
    SYNTAX      INTEGER(2000..1310720)
    MAX-ACCESS  read-only
    STATUS      current
    DESCRIPTION
        "The gemport peek burst size, should be inputted with <2000-1310720>."
    ::= { demoLineGemportEntry 7 }

demoLineGemportPq OBJECT-TYPE    
    SYNTAX      INTEGER(0..7)
    MAX-ACCESS  read-only
    STATUS      current
    DESCRIPTION
        "The gemport priority queue, should be inputted with <0-7>."
    ::= { demoLineGemportEntry 8 }

-- 1.1.4.3.4. demoLineFlowmappingTable ----------------
demoLineFlowmappingTable  OBJECT-TYPE
        SYNTAX      SEQUENCE OF DemoLineFlowmappingEntry
        MAX-ACCESS  not-accessible
        STATUS      current
        DESCRIPTION
            "demo domain line flow mapping table."
        ::= { demoLineCommonConfig 4 }

demoLineFlowmappingEntry  OBJECT-TYPE
        SYNTAX      DemoLineFlowmappingEntry
        MAX-ACCESS  not-accessible
        STATUS      current
        DESCRIPTION
            "entry of demo line flow mapping table"
        INDEX { demoLineIndex, demoLineFlowmappingIndex }
        ::= { demoLineFlowmappingTable 1 }

DemoLineFlowmappingEntry  ::= 
        SEQUENCE 
        {
            demoLineFlowmappingIndex     INTEGER,
            demoLineFlowmappingVid       INTEGER,
            demoLineFlowmappingPriority  INTEGER,
            demoLineFlowmappingEthport   INTEGER,
            demoLineFlowmappingGemport   INTEGER,
            demoLineFlowmappingType      INTEGER
        }

demoLineFlowmappingIndex OBJECT-TYPE    
    SYNTAX       INTEGER(1..48)
    MAX-ACCESS   read-only
    STATUS       current
    DESCRIPTION
        "The index of flowmapping, the 2nd index of this table. Should in <1-48>.
         The range is not always fit, please see range in commands."
    ::= { demoLineFlowmappingEntry 1 }

demoLineFlowmappingVid  OBJECT-TYPE    
    SYNTAX      INTEGER(1..4094)
    MAX-ACCESS  read-only
    STATUS      current
    DESCRIPTION
        "The flow mapping vid, should be inputted with <1-4094>."
    ::= { demoLineFlowmappingEntry 2 }

demoLineFlowmappingPriority OBJECT-TYPE    
    SYNTAX          INTEGER(0..8)
    MAX-ACCESS      read-only
    STATUS          current
    DESCRIPTION
        "The flow mapping priority, should be inputted with <0-8>.
         Value 8 means don't care 802.1p priority."
    ::= { demoLineFlowmappingEntry 3 }

demoLineFlowmappingEthport OBJECT-TYPE    
    SYNTAX       INTEGER(1..8)
    MAX-ACCESS   read-only
    STATUS       current
    DESCRIPTION
        "The flow mapping ethernet port id, should be inputted with <1-8>."
    ::= { demoLineFlowmappingEntry 4 }

demoLineFlowmappingGemport OBJECT-TYPE    
    SYNTAX         INTEGER(1..24)
    MAX-ACCESS     read-only
    STATUS         current
    DESCRIPTION
        "The flow mapping gem port id, should be inputted with <1-24>."
    ::= { demoLineFlowmappingEntry 5 }

demoLineFlowmappingType OBJECT-TYPE    
    SYNTAX         INTEGER(0..3)
    MAX-ACCESS     read-only
    STATUS         current
    DESCRIPTION
        "demoLineFlowmappingType:
        0  flowmapping not base port.
        1  flowmapping base eth port.
        2  flowmapping base veip port.
        3. flowmapping base iphost port."
    ::= { demoLineFlowmappingEntry 6 }

-- 1.1.4.3.5. demoLineAttrMgmtTable --------------------
demoLineAttrMgmtTable  OBJECT-TYPE
        SYNTAX      SEQUENCE OF DemoLineAttrMgmtEntry
        MAX-ACCESS  not-accessible
        STATUS      current
        DESCRIPTION
            "demo domain line attribute management table."
        ::= { demoLineCommonConfig 5 }

demoLineAttrMgmtEntry  OBJECT-TYPE
        SYNTAX      DemoLineAttrMgmtEntry
        MAX-ACCESS  not-accessible
        STATUS      current
        DESCRIPTION
            "entry of demo line attribute management table"
        INDEX { demoLineIndex, demoLineAttrMgmtIndex }
        ::= { demoLineAttrMgmtTable 1 }

DemoLineAttrMgmtEntry  ::= 
        SEQUENCE 
        {
            demoLineAttrMgmtIndex        INTEGER,
            demoLineAttrMgmtNport        INTEGER,
            demoLineAttrMgmtVlanMode     INTEGER,
            demoLineAttrMgmtNportType    INTEGER,
            demoLineAttrMgmtEtypeFilter  INTEGER,
            demoLineAttrMgmtCvlanVid     INTEGER,
            demoLineAttrMgmtCvlanPri     INTEGER,
            demoLineAttrMgmtSvlanVid     INTEGER,
            demoLineAttrMgmtSvlanPri     INTEGER
        }

demoLineAttrMgmtIndex OBJECT-TYPE    
    SYNTAX       INTEGER(1..64)
    MAX-ACCESS   read-only
    STATUS       current
    DESCRIPTION
        "The index of attribute management, the 2nd index of this table. Should in <1-64>."
    ::= { demoLineAttrMgmtEntry 1 }

demoLineAttrMgmtNport OBJECT-TYPE    
    SYNTAX       INTEGER(1..64)
    MAX-ACCESS   read-only
    STATUS       current
    DESCRIPTION
        "The port of attribute management, if eport, should in <1-8>."
    ::= { demoLineAttrMgmtEntry 2 }

demoLineAttrMgmtVlanMode OBJECT-TYPE    
    SYNTAX      INTEGER(0..4)
    MAX-ACCESS  read-only
    STATUS      current
    DESCRIPTION
        "demoLineAttrMgmtVlanMode:
         0  transparent
         1  tag
         2  translation
         3  trunk
         4  QinQ"
    ::= { demoLineAttrMgmtEntry 3 }

demoLineAttrMgmtNportType OBJECT-TYPE    
    SYNTAX      INTEGER(1..3)
    MAX-ACCESS  read-only
    STATUS      current
    DESCRIPTION
        "demoLineAttrMgmtNportType:
         1  eth port in sfu
         2  veip port in hgu
         3  iphost virtual port, for voip, tdm, etc."
    ::= { demoLineAttrMgmtEntry 4 }

demoLineAttrMgmtEtypeFilter OBJECT-TYPE    
    SYNTAX      INTEGER(0..3)
    MAX-ACCESS  read-only
    STATUS      current
    DESCRIPTION
        "demoLineAttrMgmtEtypeFilter:
         0  no filter
         1  filter ipoe frame
         2  filter pppoe frame
         3  filter arp frame"
    ::= { demoLineAttrMgmtEntry 5 }

demoLineAttrMgmtCvlanVid OBJECT-TYPE    
    SYNTAX      INTEGER(1..4094)
    MAX-ACCESS  read-only
    STATUS      current
    DESCRIPTION
        "cvlan vid, should be inputted with <1-4094>."
    ::= { demoLineAttrMgmtEntry 6 }

demoLineAttrMgmtCvlanPri OBJECT-TYPE    
    SYNTAX      INTEGER(0..8)
    MAX-ACCESS  read-only
    STATUS      current
    DESCRIPTION
        "The cvlan priority, should be inputted with <0-8>.
         Value 8 means don't care vlan priority."
    ::= { demoLineAttrMgmtEntry 7 }

demoLineAttrMgmtSvlanVid OBJECT-TYPE    
    SYNTAX      INTEGER(1..4094)
    MAX-ACCESS  read-only
    STATUS      current
    DESCRIPTION
        "svlan vid, should be inputted with <1-4094>."
    ::= { demoLineAttrMgmtEntry 8 }

demoLineAttrMgmtSvlanPri OBJECT-TYPE    
    SYNTAX      INTEGER(0..8)
    MAX-ACCESS  read-only
    STATUS      current
    DESCRIPTION
        "svlan priority, should be inputted with <0-8>.
         Value 8 means don't care vlan priority."
    ::= { demoLineAttrMgmtEntry 9 }

-- 1.1.4.4. demoLineSFUConfig --------------------------
demoLineSFUConfig OBJECT IDENTIFIER ::= { deployDemo 4 }

-- 1.1.4.4.1. demoLineSFUTable
-- 1.1.4.4.2. demoLineSFUEthportTable
-- 1.1.4.4.3. demoLineSFUCtrlMcastTable

-- 1.1.4.4.1. demoLineSFUTable ------------------------
demoLineSFUTable  OBJECT-TYPE
        SYNTAX      SEQUENCE OF DemoLineSFUEntry
        MAX-ACCESS  not-accessible
        STATUS      current
        DESCRIPTION
            "demo domain line SFU primary table."
        ::= { demoLineSFUConfig 1 }

demoLineSFUEntry  OBJECT-TYPE
        SYNTAX      DemoLineSFUEntry
        MAX-ACCESS  not-accessible
        STATUS      current
        DESCRIPTION
            "entry of demo line sfu primary table"
        INDEX { demoLineIndex }
        ::= { demoLineSFUTable 1 }

DemoLineSFUEntry  ::= 
        SEQUENCE 
        {
            demoLineSfuLocalSwitch          INTEGER,
            demoLineSfuLoopDetectSwitch     INTEGER
        }

demoLineSfuLocalSwitch OBJECT-TYPE    
    SYNTAX       INTEGER(0..1)
    MAX-ACCESS   read-only
    STATUS       current
    DESCRIPTION
        "demoLineSfuLocalSwitch:
         0  disable(default)
         1  enable."
    ::= { demoLineSFUEntry 1 }

demoLineSfuLoopDetectSwitch  OBJECT-TYPE    
    SYNTAX      INTEGER(0..1)
    MAX-ACCESS  read-only
    STATUS      current
    DESCRIPTION
        "demoLineSfuLoopDetectSwitch:
         0  disable(default)
         1  enable."
    ::= { demoLineSFUEntry 2 }

-- 1.1.4.4.2. demoLineSFUEthportTable ------------------
demoLineSFUEthportTable  OBJECT-TYPE
        SYNTAX      SEQUENCE OF DemoLineSFUEthportEntry
        MAX-ACCESS  not-accessible
        STATUS      current
        DESCRIPTION
            "demo domain line SFU ethernet port table."
        ::= { demoLineSFUConfig 2 }

demoLineSFUEthportEntry  OBJECT-TYPE
        SYNTAX      DemoLineSFUEthportEntry
        MAX-ACCESS  not-accessible
        STATUS      current
        DESCRIPTION
            "entry of demo line SFU ethernet port table"
        INDEX { demoLineIndex, demoLineSfuEthportIndex }
        ::= { demoLineSFUEthportTable 1 }

DemoLineSFUEthportEntry  ::= 
        SEQUENCE 
        {
            demoLineSfuEthportIndex             INTEGER,
            demoLineSfuEthportSwitch            INTEGER,
            demoLineSfuEthportFlowCtrlSwitch    INTEGER,
            demoLineSfuEthportLoopbackSwitch    INTEGER,
            demoLineSfuEthportBwEgress          INTEGER,
            demoLineSfuEthportFastLeaveSwitch   INTEGER,
            demoLineSfuEthportMaxGroups         INTEGER,
            demoLineSfuEthportMaxMacCount       INTEGER,
            demoLineSfuEthportMcastMode         INTEGER,
            demoLineSfuEthportDsIgmpControlType INTEGER,
            demoLineSfuEthportDsIgmpVid         INTEGER,
            demoLineSfuEthportDsIgmpPri         INTEGER,
            demoLineSfuEthportUsIgmpControlType INTEGER,
            demoLineSfuEthportUsIgmpVid         INTEGER,
            demoLineSfuEthportUsIgmpPri         INTEGER
        }

demoLineSfuEthportIndex OBJECT-TYPE    
    SYNTAX      INTEGER(1..8)
    MAX-ACCESS  read-only
    STATUS      current
    DESCRIPTION
        "The index of SFU ethernet port, the 2nd index of this table. Should in <1-8>."
    ::= { demoLineSFUEthportEntry 1 }

demoLineSfuEthportSwitch OBJECT-TYPE    
    SYNTAX         INTEGER(0..1)
    MAX-ACCESS     read-only
    STATUS         current
    DESCRIPTION
        "demoLineSfuEthportSwitch:
         0  no shutdown(default)
         1  shutdown"
    ::= { demoLineSFUEthportEntry 2 }

demoLineSfuEthportFlowCtrlSwitch OBJECT-TYPE    
    SYNTAX         INTEGER(0..1)
    MAX-ACCESS     read-only
    STATUS         current
    DESCRIPTION
        "demoLineSfuEthportFlowCtrlSwitch:
         0  disable(default)
         1  enable"
    ::= { demoLineSFUEthportEntry 3 }

demoLineSfuEthportLoopbackSwitch OBJECT-TYPE    
    SYNTAX         INTEGER(0..1)
    MAX-ACCESS     read-only
    STATUS         current
    DESCRIPTION
        "demoLineSfuEthportLoopbackSwitch:
         0  disable(default)
         1  enable"
    ::= { demoLineSFUEthportEntry 4 }

demoLineSfuEthportBwEgress OBJECT-TYPE    
    SYNTAX       INTEGER(64..1023936)
    MAX-ACCESS   read-only
    STATUS       current
    DESCRIPTION
        "The SFU ethernet port max bandwidth egress, should be inputted with <64-1023936>."
    ::= { demoLineSFUEthportEntry 5 }

demoLineSfuEthportFastLeaveSwitch OBJECT-TYPE    
    SYNTAX        INTEGER(0..1)
    MAX-ACCESS    read-only
    STATUS        current
    DESCRIPTION
        "demoLineSfuEthportFastLeaveSwitch:
         0  disable(default) 
         1  enable"
    ::= { demoLineSFUEthportEntry 6 }

demoLineSfuEthportMaxGroups OBJECT-TYPE    
    SYNTAX        INTEGER(1..128)
    MAX-ACCESS    read-only
    STATUS        current
    DESCRIPTION
        "The SFU ethernet port max igmp groups, should be inputted with <1-128>."
    ::= { demoLineSFUEthportEntry 7 }

demoLineSfuEthportMaxMacCount OBJECT-TYPE    
    SYNTAX          INTEGER(1..255)
    MAX-ACCESS      read-only
    STATUS          current
    DESCRIPTION
        "The SFU ethernet port max mac address count, should be inputted with <1-255>."
    ::= { demoLineSFUEthportEntry 8 }

demoLineSfuEthportMcastMode OBJECT-TYPE    
    SYNTAX         INTEGER(0..2)
    MAX-ACCESS     read-only
    STATUS         current
    DESCRIPTION
        "demoLineSfuEthportMcastMode(some ont not support):
         0  unconcern(default)
         1  control
         2  igmp snooping"
    ::= { demoLineSFUEthportEntry 9 }

demoLineSfuEthportDsIgmpControlType OBJECT-TYPE    
    SYNTAX          INTEGER(0..5)
    MAX-ACCESS      read-only
    STATUS          current
    DESCRIPTION
        "demoLineSfuEthportDsIgmpControlType:
         0  transparent(default)
         1  strip outer tag
         2  add tag
         3  replace tag
         4  replace only vid
         5  add only vid"
    ::= { demoLineSFUEthportEntry 10 }

demoLineSfuEthportDsIgmpVid OBJECT-TYPE    
    SYNTAX        INTEGER(1..4094)
    MAX-ACCESS    read-only
    STATUS        current
    DESCRIPTION
        "The SFU ethernet port downstream igmp and multicast control vid, 
        should be inputted with <1-4094>."
    ::= { demoLineSFUEthportEntry 11 }

demoLineSfuEthportDsIgmpPri OBJECT-TYPE    
    SYNTAX      INTEGER(0..7)
    MAX-ACCESS  read-only
    STATUS      current
    DESCRIPTION
        "The vlan priority, should be inputted with <0-7>."
    ::= { demoLineSFUEthportEntry 12 }

demoLineSfuEthportUsIgmpControlType OBJECT-TYPE    
    SYNTAX          INTEGER(0..5)
    MAX-ACCESS      read-only
    STATUS          current
    DESCRIPTION
        "demoLineSfuEthportUsIgmpControlType:
         0  transparent(default)
         1  strip outer tag
         2  add tag
         3  replace tag
         4  replace only vid
         5  add only vid"
    ::= { demoLineSFUEthportEntry 13 }

demoLineSfuEthportUsIgmpVid OBJECT-TYPE    
    SYNTAX        INTEGER(1..4094)
    MAX-ACCESS    read-only
    STATUS        current
    DESCRIPTION
        "The SFU ethernet port upstream igmp and multicast control vid, 
        should be inputted with <1-4094>."
    ::= { demoLineSFUEthportEntry 14 }

demoLineSfuEthportUsIgmpPri OBJECT-TYPE    
    SYNTAX      INTEGER(0..7)
    MAX-ACCESS  read-only
    STATUS      current
    DESCRIPTION
        "The vlan priority, should be inputted with <0-7>."
    ::= { demoLineSFUEthportEntry 15 }

-- 1.1.4.4.3. demoLineSFUCtrlMcastTable ----------------
demoLineSFUCtrlMcastTable  OBJECT-TYPE
        SYNTAX      SEQUENCE OF DemoLineSFUCtrlMcastEntry
        MAX-ACCESS  not-accessible
        STATUS      current
        DESCRIPTION
            "demo domain line SFU ethernet port control multicast table."
        ::= { demoLineSFUConfig 3 }

demoLineSFUCtrlMcastEntry  OBJECT-TYPE
        SYNTAX      DemoLineSFUCtrlMcastEntry
        MAX-ACCESS  not-accessible
        STATUS      current
        DESCRIPTION
            "entry of demo line SFU ethernet port control multicast table"
        INDEX { demoLineIndex, demoLineSfuEthportIndex, demoLineSfuCtrlMcastIndex }
        ::= { demoLineSFUCtrlMcastTable 1 }

DemoLineSFUCtrlMcastEntry  ::= 
        SEQUENCE 
        {
            demoLineSfuCtrlMcastIndex         INTEGER,
            demoLineSfuCtrlMcastAccessType    INTEGER,
            demoLineSfuCtrlMcastVid           INTEGER,
            demoLineSfuCtrlMcastSrcIp         IpAddress,
            demoLineSfuCtrlMcastDstStartIp    IpAddress,
            demoLineSfuCtrlMcastDstEndIp      IpAddress,
            demoLineSfuCtrlMcastGroupBw       INTEGER,
            demoLineSfuCtrlMcastDurationTimes INTEGER,
            demoLineSfuCtrlMcastNumOfTimes    INTEGER,
            demoLineSfuCtrlMcastTimeInterval  INTEGER,
            demoLineSfuCtrlMcastResetTime     INTEGER
        }

demoLineSfuCtrlMcastIndex OBJECT-TYPE    
    SYNTAX      INTEGER(1..16)
    MAX-ACCESS  read-only
    STATUS      current
    DESCRIPTION
        "The index of SFU ethernet port control multicast, the 3rd index of this table. Should in <1-16>."
    ::= { demoLineSFUCtrlMcastEntry 1 }

demoLineSfuCtrlMcastAccessType OBJECT-TYPE    
    SYNTAX      INTEGER(0..3)
    MAX-ACCESS  read-only
    STATUS      current
    DESCRIPTION
        "demoLineSfuCtrlMcastAccessType:
         0  del one entry
         1  clear all entry
         2  add permit entry
         3  add preview entry"
    ::= { demoLineSFUCtrlMcastEntry 2 }

demoLineSfuCtrlMcastVid OBJECT-TYPE    
    SYNTAX      INTEGER(1..4094)
    MAX-ACCESS  read-only
    STATUS      current
    DESCRIPTION
        "sfu control multicast vlan id, should be <1-4094>."
    ::= { demoLineSFUCtrlMcastEntry 3 }

demoLineSfuCtrlMcastSrcIp OBJECT-TYPE    
    SYNTAX      IpAddress
    MAX-ACCESS  read-only
    STATUS      current
    DESCRIPTION
        "sfu control multicast source ip address."
    ::= { demoLineSFUCtrlMcastEntry 4 }

demoLineSfuCtrlMcastDstStartIp OBJECT-TYPE    
    SYNTAX      IpAddress
    MAX-ACCESS  read-only
    STATUS      current
    DESCRIPTION
        "sfu control multicast destination start ip address."
    ::= { demoLineSFUCtrlMcastEntry 5 }

demoLineSfuCtrlMcastDstEndIp OBJECT-TYPE    
    SYNTAX      IpAddress
    MAX-ACCESS  read-only
    STATUS      current
    DESCRIPTION
        "sfu control multicast destination end ip address."
    ::= { demoLineSFUCtrlMcastEntry 6 }

demoLineSfuCtrlMcastGroupBw OBJECT-TYPE    
    SYNTAX      INTEGER(1..16)
    MAX-ACCESS  read-only
    STATUS      current
    DESCRIPTION
        "sfu control multicast group bandwidth, should be <x-x>."
    ::= { demoLineSFUCtrlMcastEntry 7 }

demoLineSfuCtrlMcastDurationTimes OBJECT-TYPE    
    SYNTAX      INTEGER(1..16)
    MAX-ACCESS  read-only
    STATUS      current
    DESCRIPTION
        "sfu control multicast duration times, should be <x-x>."
    ::= { demoLineSFUCtrlMcastEntry 8 }

demoLineSfuCtrlMcastNumOfTimes OBJECT-TYPE    
    SYNTAX      INTEGER(1..16)
    MAX-ACCESS  read-only
    STATUS      current
    DESCRIPTION
        "sfu control multicast number of times, should be <x-x>."
    ::= { demoLineSFUCtrlMcastEntry 9 }

demoLineSfuCtrlMcastTimeInterval OBJECT-TYPE    
    SYNTAX      INTEGER(1..16)
    MAX-ACCESS  read-only
    STATUS      current
    DESCRIPTION
        "sfu control multicast time interval, should be <x-x>."
    ::= { demoLineSFUCtrlMcastEntry 10 }

demoLineSfuCtrlMcastResetTime OBJECT-TYPE    
    SYNTAX      INTEGER(1..16)
    MAX-ACCESS  read-only
    STATUS      current
    DESCRIPTION
        "sfu control multicast reset time, should be <x-x>."
    ::= { demoLineSFUCtrlMcastEntry 11 }

-- 1.1.4.5. demoLineHGUConfig --------------------------
demoLineHGUConfig OBJECT IDENTIFIER ::= { deployDemo 5 }

-- 1.1.4.5.1. demoLineHGUTable
-- 1.1.4.5.2. demoLineHGUCtrlMcastTable

-- 1.1.4.5.1. demoLineHGUTable ------------------------
demoLineHGUTable  OBJECT-TYPE
        SYNTAX      SEQUENCE OF DemoLineHGUEntry
        MAX-ACCESS  not-accessible
        STATUS      current
        DESCRIPTION
            "demo domain line HGU table."
        ::= { demoLineHGUConfig 1 }

demoLineHGUEntry  OBJECT-TYPE
        SYNTAX      DemoLineHGUEntry
        MAX-ACCESS  not-accessible
        STATUS      current
        DESCRIPTION
            "entry of demo line HGU table"
        INDEX { demoLineIndex }
        ::= { demoLineHGUTable 1 }

DemoLineHGUEntry  ::= 
        SEQUENCE 
        {
            demoLineHguSwitch            INTEGER,
            demoLineHguFastLeaveSwitch    INTEGER,
            demoLineHguMaxGroups         INTEGER,
            demoLineHguMaxMacCount       INTEGER,
            demoLineHguMcastMode         INTEGER,
            demoLineHguDsIgmpControlType INTEGER,
            demoLineHguDsIgmpVid         INTEGER,
            demoLineHguDsIgmpPri         INTEGER,
            demoLineHguUsIgmpControlType INTEGER,
            demoLineHguUsIgmpVid         INTEGER,
            demoLineHguUsIgmpPri         INTEGER
        }

demoLineHguSwitch OBJECT-TYPE    
    SYNTAX         INTEGER(0..1)
    MAX-ACCESS     read-only
    STATUS         current
    DESCRIPTION
        "demoLineHguSwitch:
         0  no shutdown(default)
         1  shutdown"
    ::= { demoLineHGUEntry 1 }

demoLineHguFastLeaveSwitch OBJECT-TYPE    
    SYNTAX         INTEGER(0..1)
    MAX-ACCESS     read-only
    STATUS         current
    DESCRIPTION
        "demoLineHguFlowCtrlSwitch:
         0  disable(default)
         1  enable"
    ::= { demoLineHGUEntry 2 }

demoLineHguMaxGroups OBJECT-TYPE    
    SYNTAX        INTEGER(1..128)
    MAX-ACCESS    read-only
    STATUS        current
    DESCRIPTION
        "The HGU max igmp groups, should be inputted with <1-128>."
    ::= { demoLineHGUEntry 3 }

demoLineHguMaxMacCount OBJECT-TYPE    
    SYNTAX          INTEGER(1..255)
    MAX-ACCESS      read-only
    STATUS          current
    DESCRIPTION
        "The HGU max mac address count, should be inputted with <1-255>."
    ::= { demoLineHGUEntry 4 }

demoLineHguMcastMode OBJECT-TYPE    
    SYNTAX         INTEGER(0..2)
    MAX-ACCESS     read-only
    STATUS         current
    DESCRIPTION
        "demoLineHguMcastMode(some ont not support):
         0  unconcern(default)
         1  control
         2  igmp snooping"
    ::= { demoLineHGUEntry 5 }

demoLineHguDsIgmpControlType OBJECT-TYPE    
    SYNTAX          INTEGER(0..5)
    MAX-ACCESS      read-only
    STATUS          current
    DESCRIPTION
        "demoLineHguDsIgmpControlType:
         0  transparent(default)
         1  strip outer tag
         2  add tag
         3  replace tag
         4  replace only vid
         5  add only vid"
    ::= { demoLineHGUEntry 6 }

demoLineHguDsIgmpVid OBJECT-TYPE    
    SYNTAX        INTEGER(1..4094)
    MAX-ACCESS    read-only
    STATUS        current
    DESCRIPTION
        "The HGU downstream igmp and multicast control vid, 
        should be inputted with <1-4094>."
    ::= { demoLineHGUEntry 7 }

demoLineHguDsIgmpPri OBJECT-TYPE    
    SYNTAX      INTEGER(0..7)
    MAX-ACCESS  read-only
    STATUS      current
    DESCRIPTION
        "The vlan priority, should be inputted with <0-7>."
    ::= { demoLineHGUEntry 8 }

demoLineHguUsIgmpControlType OBJECT-TYPE    
    SYNTAX          INTEGER(0..5)
    MAX-ACCESS      read-only
    STATUS          current
    DESCRIPTION
        "demoLineHguUsIgmpControlType:
         0  transparent(default)
         1  strip outer tag
         2  add tag
         3  replace tag
         4  replace only vid
         5  add only vid"
    ::= { demoLineHGUEntry 9 }

demoLineHguUsIgmpVid OBJECT-TYPE    
    SYNTAX        INTEGER(1..4094)
    MAX-ACCESS    read-only
    STATUS        current
    DESCRIPTION
        "The HGU upstream igmp and multicast control vid, 
        should be inputted with <1-4094>."
    ::= { demoLineHGUEntry 10 }

demoLineHguUsIgmpPri OBJECT-TYPE    
    SYNTAX      INTEGER(0..7)
    MAX-ACCESS  read-only
    STATUS      current
    DESCRIPTION
        "The vlan priority, should be inputted with <0-7>."
    ::= { demoLineHGUEntry 11 }

-- 1.1.4.5.2. demoLineHGUCtrlMcastTable ----------------
demoLineHGUCtrlMcastTable  OBJECT-TYPE
        SYNTAX      SEQUENCE OF DemoLineHGUCtrlMcastEntry
        MAX-ACCESS  not-accessible
        STATUS      current
        DESCRIPTION
            "demo domain line HGU control multicast table."
        ::= { demoLineHGUConfig 2 }

demoLineHGUCtrlMcastEntry  OBJECT-TYPE
        SYNTAX      DemoLineHGUCtrlMcastEntry
        MAX-ACCESS  not-accessible
        STATUS      current
        DESCRIPTION
            "entry of demo line HGU control multicast table"
        INDEX { demoLineIndex, demoLineHguCtrlMcastIndex }
        ::= { demoLineHGUCtrlMcastTable 1 }

DemoLineHGUCtrlMcastEntry  ::= 
        SEQUENCE 
        {
            demoLineHguCtrlMcastIndex         INTEGER,
            demoLineHguCtrlMcastAccessType    INTEGER,
            demoLineHguCtrlMcastVid           INTEGER,
            demoLineHguCtrlMcastSrcIp         IpAddress,
            demoLineHguCtrlMcastDstStartIp    IpAddress,
            demoLineHguCtrlMcastDstEndIp      IpAddress,
            demoLineHguCtrlMcastGroupBw       INTEGER,
            demoLineHguCtrlMcastDurationTimes INTEGER,
            demoLineHguCtrlMcastNumOfTimes    INTEGER,
            demoLineHguCtrlMcastTimeInterval  INTEGER,
            demoLineHguCtrlMcastResetTime     INTEGER
        }

demoLineHguCtrlMcastIndex OBJECT-TYPE    
    SYNTAX      INTEGER(1..16)
    MAX-ACCESS  read-only
    STATUS      current
    DESCRIPTION
        "The index of HGU control multicast, the 2nd index of this table. Should in <1-16>."
    ::= { demoLineHGUCtrlMcastEntry 1 }

demoLineHguCtrlMcastAccessType OBJECT-TYPE    
    SYNTAX      INTEGER(0..3)
    MAX-ACCESS  read-only
    STATUS      current
    DESCRIPTION
        "demoLineHGUCtrlMcastAccessType:
         0  del one entry
         1  clear all entry
         2  add permit entry
         3  add preview entry"
    ::= { demoLineHGUCtrlMcastEntry 2 }

demoLineHguCtrlMcastVid OBJECT-TYPE    
    SYNTAX      INTEGER(1..4094)
    MAX-ACCESS  read-only
    STATUS      current
    DESCRIPTION
        "hgu control multicast vlan id, should be <1-4094>."
    ::= { demoLineHGUCtrlMcastEntry 3 }

demoLineHguCtrlMcastSrcIp OBJECT-TYPE    
    SYNTAX      IpAddress
    MAX-ACCESS  read-only
    STATUS      current
    DESCRIPTION
        "hgu control multicast source ip address."
    ::= { demoLineHGUCtrlMcastEntry 4 }

demoLineHguCtrlMcastDstStartIp OBJECT-TYPE    
    SYNTAX      IpAddress
    MAX-ACCESS  read-only
    STATUS      current
    DESCRIPTION
        "hgu control multicast destination start ip address."
    ::= { demoLineHGUCtrlMcastEntry 5 }

demoLineHguCtrlMcastDstEndIp OBJECT-TYPE    
    SYNTAX      IpAddress
    MAX-ACCESS  read-only
    STATUS      current
    DESCRIPTION
        "hgu control multicast destination end ip address."
    ::= { demoLineHGUCtrlMcastEntry 6 }

demoLineHguCtrlMcastGroupBw OBJECT-TYPE    
    SYNTAX      INTEGER(1..16)
    MAX-ACCESS  read-only
    STATUS      current
    DESCRIPTION
        "hgu control multicast group bandwidth, should be <x-x>."
    ::= { demoLineHGUCtrlMcastEntry 7 }

demoLineHguCtrlMcastDurationTimes OBJECT-TYPE    
    SYNTAX      INTEGER(1..16)
    MAX-ACCESS  read-only
    STATUS      current
    DESCRIPTION
        "hgu control multicast duration times, should be <x-x>."
    ::= { demoLineHGUCtrlMcastEntry 8 }

demoLineHguCtrlMcastNumOfTimes OBJECT-TYPE    
    SYNTAX      INTEGER(1..16)
    MAX-ACCESS  read-only
    STATUS      current
    DESCRIPTION
        "hgu control multicast number of times, should be <x-x>."
    ::= { demoLineHGUCtrlMcastEntry 9 }

demoLineHguCtrlMcastTimeInterval OBJECT-TYPE    
    SYNTAX      INTEGER(1..16)
    MAX-ACCESS  read-only
    STATUS      current
    DESCRIPTION
        "hgu control multicast time interval, should be <x-x>."
    ::= { demoLineHGUCtrlMcastEntry 10 }

demoLineHguCtrlMcastResetTime OBJECT-TYPE    
    SYNTAX      INTEGER(1..16)
    MAX-ACCESS  read-only
    STATUS      current
    DESCRIPTION
        "hgu control multicast reset time, should be <x-x>."
    ::= { demoLineHGUCtrlMcastEntry 11 }

-- 1.1.4.6. demoRuleTable ------------------------------
demoRuleTable  OBJECT-TYPE
        SYNTAX      SEQUENCE OF DemoRuleEntry
        MAX-ACCESS  not-accessible
        STATUS      current
        DESCRIPTION
            "demo domain rule table"
        ::= { deployDemo 6 }

demoRuleEntry  OBJECT-TYPE
        SYNTAX      DemoRuleEntry
        MAX-ACCESS  not-accessible
        STATUS      current
        DESCRIPTION
            "entry of demo rule table"
        INDEX { demoRuleIndex }
        ::= { demoRuleTable 1 }

DemoRuleEntry  ::= 
        SEQUENCE 
        {
            demoRuleIndex          INTEGER,
            demoRuleDescription    OCTET STRING,
            demoRuleAction         INTEGER,
            demoRuleAuthIndex      INTEGER,
            demoRuleLineIndexesStr OCTET STRING
        }

demoRuleIndex OBJECT-TYPE    
    SYNTAX      INTEGER(1..4096)
    MAX-ACCESS  read-only
    STATUS      current
    DESCRIPTION
        "The index of rule table, should be inputted with <1-4096>.
         The range is not always fit, please see range in commands."
    ::= { demoRuleEntry 1 }

demoRuleDescription OBJECT-TYPE
    SYNTAX      OCTET STRING (SIZE(0..255))
    MAX-ACCESS  read-only
    STATUS      current
    DESCRIPTION
        "rule description, max length: 128."
    ::= { demoRuleEntry 2 }

demoRuleAction OBJECT-TYPE    
    SYNTAX      INTEGER(0..1)
    MAX-ACCESS  read-only
    STATUS      current
    DESCRIPTION
        "demoRuleAction:
         0  permit
         1  deny"
    ::= { demoRuleEntry 3 }

demoRuleAuthIndex   OBJECT-TYPE    
    SYNTAX      INTEGER(1..4096)
    MAX-ACCESS  read-only
    STATUS      current
    DESCRIPTION
        "The index of rule bind auth, should be inputted with <1-4096>
         The range is not always fit, please see range in commands."
    ::= { demoRuleEntry 4 }
    
demoRuleLineIndexesStr OBJECT-TYPE
    SYNTAX         OCTET STRING (SIZE(0..255))
    MAX-ACCESS     read-only
    STATUS         current
    DESCRIPTION
        "String joined by rule bind line indexes, such as '12,56,1023'.
         A rule can at most bind 8 line models."
    ::= { demoRuleEntry 5 }

-- 1.1.4.7. demoUniqueConfig --------------------------
demoUniqueConfig OBJECT IDENTIFIER ::= { deployDemo 7 }

-- 1.1.4.7.1. demoUniquePrimaryTable
-- 1.1.4.7.2. demoUniqueSipAgentInfoTable
-- 1.1.4.7.3. demoUniqueSipUserAddrTable
-- 1.1.4.7.4. demoUniqueSipUserInfoTable
-- 1.1.4.7.5. demoUniqueSipDigitMapTable

-- 1.1.4.7.1. demoUniquePrimaryTable ------------------
demoUniquePrimaryTable  OBJECT-TYPE
        SYNTAX      SEQUENCE OF DemoUniquePrimaryEntry
        MAX-ACCESS  not-accessible
        STATUS      current
        DESCRIPTION
            "demo domain unique primary table"
        ::= { demoUniqueConfig 1 }

demoUniquePrimaryEntry  OBJECT-TYPE
        SYNTAX      DemoUniquePrimaryEntry
        MAX-ACCESS  not-accessible
        STATUS      current
        DESCRIPTION
            "entry of demo unique primary table"
        INDEX { demoUniqueIndex }
        ::= { demoUniquePrimaryTable 1 }

DemoUniquePrimaryEntry  ::= 
        SEQUENCE 
        {
            demoUniqueIndex        INTEGER,
            demoUniqueDescription  OCTET STRING,
            demoUniqueSn           OCTET STRING
        }

demoUniqueIndex OBJECT-TYPE    
    SYNTAX      INTEGER(1..4096)
    MAX-ACCESS  read-only
    STATUS      current
    DESCRIPTION
        "The index of unique primary table, should be inputted with <1-4096>.
         The range is not always fit, please see range in commands."
    ::= { demoUniquePrimaryEntry 1 }

demoUniqueDescription OBJECT-TYPE
    SYNTAX      OCTET STRING (SIZE(0..255))
    MAX-ACCESS  read-only
    STATUS      current
    DESCRIPTION
        "unique description, max length: 128."
    ::= { demoUniquePrimaryEntry 2 }

demoUniqueSn OBJECT-TYPE
    SYNTAX      OCTET STRING (SIZE(0..255))
    MAX-ACCESS  read-only
    STATUS      current
    DESCRIPTION
        "unique sn, hex format, max length: 16."
    ::= { demoUniquePrimaryEntry 3 }

-- 1.1.4.7.2. demoUniqueSipAgentInfoTable --------------
demoUniqueSipAgentInfoTable  OBJECT-TYPE
        SYNTAX      SEQUENCE OF DemoUniqueSipAgentInfoEntry
        MAX-ACCESS  not-accessible
        STATUS      current
        DESCRIPTION
            "demo domain unique voip sip agent info table"
        ::= { demoUniqueConfig 2 }

demoUniqueSipAgentInfoEntry  OBJECT-TYPE
        SYNTAX      DemoUniqueSipAgentInfoEntry
        MAX-ACCESS  not-accessible
        STATUS      current
        DESCRIPTION
            "entry of demo unique voip sip agent info table"
        INDEX { demoUniqueIndex }
        ::= { demoUniqueSipAgentInfoTable 1 }

DemoUniqueSipAgentInfoEntry  ::= 
        SEQUENCE 
        {
            demoUniqueSipProxyServerIp      IpAddress,
            demoUniqueSipOutboundProxyIp    IpAddress,
            demoUniqueSipRegisterServerIp   IpAddress,
            demoUniqueSipAgentInfoPort      INTEGER
        }

demoUniqueSipProxyServerIp OBJECT-TYPE    
    SYNTAX      IpAddress
    MAX-ACCESS  read-only
    STATUS      current
    DESCRIPTION
        "voip sip agent info proxy server ip address."
    ::= { demoUniqueSipAgentInfoEntry 1 }

demoUniqueSipOutboundProxyIp OBJECT-TYPE    
    SYNTAX      IpAddress
    MAX-ACCESS  read-only
    STATUS      current
    DESCRIPTION
        "voip sip agent info outbound proxy ip address."
    ::= { demoUniqueSipAgentInfoEntry 2 }

demoUniqueSipRegisterServerIp OBJECT-TYPE    
    SYNTAX      IpAddress
    MAX-ACCESS  read-only
    STATUS      current
    DESCRIPTION
        "voip sip agent info register server ip address."
    ::= { demoUniqueSipAgentInfoEntry 3 }

demoUniqueSipAgentInfoPort OBJECT-TYPE    
    SYNTAX      INTEGER(1..65535)
    MAX-ACCESS  read-only
    STATUS      current
    DESCRIPTION
        "voip sip agent info port."
    ::= { demoUniqueSipAgentInfoEntry 4 }

-- 1.1.4.7.3. demoUniqueSipUserAddrTable --------------
demoUniqueSipUserAddrTable  OBJECT-TYPE
        SYNTAX      SEQUENCE OF DemoUniqueSipUserAddrEntry
        MAX-ACCESS  not-accessible
        STATUS      current
        DESCRIPTION
            "demo domain unique voip sip user ip address table"
        ::= { demoUniqueConfig 3 }

demoUniqueSipUserAddrEntry  OBJECT-TYPE
        SYNTAX      DemoUniqueSipUserAddrEntry
        MAX-ACCESS  not-accessible
        STATUS      current
        DESCRIPTION
            "entry of demo unique voip sip user ip address table"
        INDEX { demoUniqueIndex }
        ::= { demoUniqueSipUserAddrTable 1 }

DemoUniqueSipUserAddrEntry  ::= 
        SEQUENCE 
        {
            demoUniqueSipuAddressIp        IpAddress,
            demoUniqueSipuAddressMask      IpAddress,
            demoUniqueSipuAddressVlan      INTEGER
        }

demoUniqueSipuAddressIp OBJECT-TYPE    
    SYNTAX      IpAddress
    MAX-ACCESS  read-only
    STATUS      current
    DESCRIPTION
        "voip sip user ip address."
    ::= { demoUniqueSipUserAddrEntry 1 }

demoUniqueSipuAddressMask OBJECT-TYPE    
    SYNTAX      IpAddress
    MAX-ACCESS  read-only
    STATUS      current
    DESCRIPTION
        "voip sip user mask."
    ::= { demoUniqueSipUserAddrEntry 2 }

demoUniqueSipuAddressVlan OBJECT-TYPE    
    SYNTAX      INTEGER(1..4094)
    MAX-ACCESS  read-only
    STATUS      current
    DESCRIPTION
        "voip sip user vlan."
    ::= { demoUniqueSipUserAddrEntry 3 }

-- 1.1.4.7.4. demoUniqueSipUserInfoTable --------------
demoUniqueSipUserInfoTable  OBJECT-TYPE
        SYNTAX      SEQUENCE OF DemoUniqueSipUserInfoEntry
        MAX-ACCESS  not-accessible
        STATUS      current
        DESCRIPTION
            "demo domain unique voip sip user infomation table"
        ::= { demoUniqueConfig 4 }

demoUniqueSipUserInfoEntry  OBJECT-TYPE
        SYNTAX      DemoUniqueSipUserInfoEntry
        MAX-ACCESS  not-accessible
        STATUS      current
        DESCRIPTION
            "entry of unique voip sip user infomation table"
        INDEX { demoUniqueIndex, demoUniqueSipuInfoIndex }
        ::= { demoUniqueSipUserInfoTable 1 }

DemoUniqueSipUserInfoEntry  ::= 
        SEQUENCE 
        {
            demoUniqueSipuInfoIndex     INTEGER,
            demoUniqueSipuInfoUserName  OCTET STRING,
            demoUniqueSipuInfoPassword  OCTET STRING,
            demoUniqueSipuInfoTelephone OCTET STRING
        }

demoUniqueSipuInfoIndex OBJECT-TYPE    
    SYNTAX      INTEGER(1..2)
    MAX-ACCESS  read-only
    STATUS      current
    DESCRIPTION
        "The index of voip sip user info, the 2nd index of this table. Should in <1-2>."
    ::= { demoUniqueSipUserInfoEntry 1 }

demoUniqueSipuInfoUserName OBJECT-TYPE    
    SYNTAX      OCTET STRING (SIZE(0..25))
    MAX-ACCESS  read-only
    STATUS      current
    DESCRIPTION
        "voip sip user infomation user name, max length: 25."
    ::= { demoUniqueSipUserInfoEntry 2 }

demoUniqueSipuInfoPassword OBJECT-TYPE    
    SYNTAX      OCTET STRING (SIZE(0..25))
    MAX-ACCESS  read-only
    STATUS      current
    DESCRIPTION
        "voip sip user infomation user name, max length: 25."
    ::= { demoUniqueSipUserInfoEntry 3 }

demoUniqueSipuInfoTelephone OBJECT-TYPE    
    SYNTAX      OCTET STRING (SIZE(0..25))
    MAX-ACCESS  read-only
    STATUS      current
    DESCRIPTION
        "voip sip user infomation user name, max length: 25."
    ::= { demoUniqueSipUserInfoEntry 4 }

-- 1.1.4.7.5. demoUniqueSipDigitMapTable --------------
demoUniqueSipDigitMapTable  OBJECT-TYPE
        SYNTAX      SEQUENCE OF DemoUniqueSipDigitMapEntry
        MAX-ACCESS  not-accessible
        STATUS      current
        DESCRIPTION
            "demo domain unique voip sip digit map table"
        ::= { demoUniqueConfig 5 }

demoUniqueSipDigitMapEntry  OBJECT-TYPE
        SYNTAX      DemoUniqueSipDigitMapEntry
        MAX-ACCESS  not-accessible
        STATUS      current
        DESCRIPTION
            "entry of demo unique voip sip digit map table"
        INDEX { demoUniqueIndex, demoUniqueSipdMapIndex }
        ::= { demoUniqueSipDigitMapTable 1 }

DemoUniqueSipDigitMapEntry  ::= 
        SEQUENCE 
        {
            demoUniqueSipdMapIndex         INTEGER,
            demoUniqueSipdMapDialPlanToken OCTET STRING
        }

demoUniqueSipdMapIndex OBJECT-TYPE    
    SYNTAX      INTEGER(1..10)
    MAX-ACCESS  read-only
    STATUS      current
    DESCRIPTION
        "The index of voip digit map, the 2nd index of this table. Should in <1-10>."
    ::= { demoUniqueSipDigitMapEntry 1 }

demoUniqueSipdMapDialPlanToken OBJECT-TYPE    
    SYNTAX      OCTET STRING (SIZE(0..28))
    MAX-ACCESS  read-only
    STATUS      current
    DESCRIPTION
        "voip sip digit map dial plan token, max length: 28."
    ::= { demoUniqueSipDigitMapEntry 2 }

-- 1.1.5. configDeviceBaseInfo ----------------------------
configDeviceBaseInfo  OBJECT IDENTIFIER ::= { configDevice 5 }

idleTimeout     OBJECT-TYPE    
    SYNTAX      INTEGER(0..480)
    MAX-ACCESS  read-write
    STATUS      current
    DESCRIPTION
        "system idle timout, unit is minute."
    ::= { configDeviceBaseInfo 1 }

loggingDisplaySwitch   OBJECT-TYPE    
    SYNTAX      INTEGER(0..1)
    MAX-ACCESS  read-write
    STATUS      current
    DESCRIPTION
        "loggingDisplaySwitch:
        0  off(default)
        1  on"
    ::= { configDeviceBaseInfo 2 }

ontLoggingDisplaySwitch  OBJECT-TYPE    
    SYNTAX      INTEGER(0..1)
    MAX-ACCESS  read-write
    STATUS      current
    DESCRIPTION
        "ontLoggingDisplaySwitch:
        0  off(default)
        1  on."
    ::= { configDeviceBaseInfo 3 }

ponSwitchTable  OBJECT-TYPE
        SYNTAX      SEQUENCE OF PonSwitchEntry
        MAX-ACCESS  not-accessible
        STATUS      current
        DESCRIPTION
            "pon switch table."
        ::= { configDeviceBaseInfo 4 }

ponSwitchEntry  OBJECT-TYPE
        SYNTAX      PonSwitchEntry
        MAX-ACCESS  not-accessible
        STATUS      current
        DESCRIPTION
            "entry of pon switch table"
        INDEX { ponSwitchVlanIndex }
        ::= { ponSwitchTable 1 }

PonSwitchEntry  ::= 
        SEQUENCE 
        {
            ponSwitchVlanIndex    INTEGER,
            ponSwitchEnable       INTEGER,
            ponSwitchRowStatus    RowStatus
        }

ponSwitchVlanIndex OBJECT-TYPE    
    SYNTAX      INTEGER(1..4094)
    MAX-ACCESS  read-only
    STATUS      current
    DESCRIPTION
        "The index of this table, should be inputted with <1-4094>.
         The range is not always fit, please see range in commands."
    ::= { ponSwitchEntry 1 }

ponSwitchEnable OBJECT-TYPE    
    SYNTAX      INTEGER(1)
    MAX-ACCESS  read-only
    STATUS      current
    DESCRIPTION
        "1 -- enable pon-switch."
    ::= { ponSwitchEntry 2 }

ponSwitchRowStatus OBJECT-TYPE    
    SYNTAX       RowStatus
    MAX-ACCESS   read-write
    STATUS       current
    DESCRIPTION
        "RowStatus"
    ::= { ponSwitchEntry 3 }

deactiveOntIdList OBJECT-TYPE    
    SYNTAX      OCTET STRING (SIZE(0..255))
    MAX-ACCESS  read-write
    STATUS      current
    DESCRIPTION
        "deactive ont id list, such as 0/8/1-0/8/10,0/10/10"
    ::= { configDeviceBaseInfo 5 }

-- 1.1.6. configEdfa --------------------------------------
configEdfa         OBJECT IDENTIFIER ::= { configDevice 6 }

-- fixme: 不知道整数还是小数的，先统一采用字符串格式，由网管自行解析成需要的格式吧
edfaInternalTemperature     OBJECT-TYPE    
    SYNTAX      OCTET STRING (SIZE(0..255))
    MAX-ACCESS  read-only
    STATUS      current
    DESCRIPTION
        "edfa internal temperature, unit is ℃."
    ::= { configEdfa 1 }

edfaInputPower1  OBJECT-TYPE    
    SYNTAX      OCTET STRING (SIZE(0..255))
    MAX-ACCESS  read-only
    STATUS      current
    DESCRIPTION
        "edfa input power1, unit is dBm."
    ::= { configEdfa 2 }

edfaInputPower2  OBJECT-TYPE    
    SYNTAX      OCTET STRING (SIZE(0..255))
    MAX-ACCESS  read-only
    STATUS      current
    DESCRIPTION
        "edfa input power2, unit is dBm."
    ::= { configEdfa 3 }

edfaActualOutputPower  OBJECT-TYPE    
    SYNTAX      OCTET STRING (SIZE(0..255))
    MAX-ACCESS  read-only
    STATUS      current
    DESCRIPTION
        "edfa actual output power, unit is dBm."
    ::= { configEdfa 4 }

edfaOutputAttenuator  OBJECT-TYPE    
    SYNTAX      OCTET STRING (SIZE(0..255))
    MAX-ACCESS  read-write
    STATUS      current
    DESCRIPTION
        "edfa setting output attenuator, unit is dBm.
        range is -0.5 to 3."
    ::= { configEdfa 5 }

edfaSerialNumber  OBJECT-TYPE    
    SYNTAX      OCTET STRING (SIZE(0..255))
    MAX-ACCESS  read-only
    STATUS      current
    DESCRIPTION
        "edfa serial number."
    ::= { configEdfa 6 }

edfaPumpBias1   OBJECT-TYPE    
    SYNTAX      OCTET STRING (SIZE(0..255))
    MAX-ACCESS  read-only
    STATUS      current
    DESCRIPTION
        "edfa pump bias, unit is A."
    ::= { configEdfa 7 }
    
edfaPumpTemperature1   OBJECT-TYPE    
    SYNTAX      OCTET STRING (SIZE(0..255))
    MAX-ACCESS  read-only
    STATUS      current
    DESCRIPTION
        "edfa pump temperature, unit is ℃."
    ::= { configEdfa 8 }

edfaPumpTec1    OBJECT-TYPE    
    SYNTAX      OCTET STRING (SIZE(0..255))
    MAX-ACCESS  read-only
    STATUS      current
    DESCRIPTION
        "edfa pump temperature control current, unit is A."
    ::= { configEdfa 9 }

edfaPumpBias2   OBJECT-TYPE    
    SYNTAX      OCTET STRING (SIZE(0..255))
    MAX-ACCESS  read-only
    STATUS      current
    DESCRIPTION
        "edfa pump bias, unit is A."
    ::= { configEdfa 10 }
    
edfaPumpTemperature2   OBJECT-TYPE    
    SYNTAX      OCTET STRING (SIZE(0..255))
    MAX-ACCESS  read-only
    STATUS      current
    DESCRIPTION
        "edfa pump temperature, unit is ℃."
    ::= { configEdfa 11 }

edfaPumpTec2    OBJECT-TYPE    
    SYNTAX      OCTET STRING (SIZE(0..255))
    MAX-ACCESS  read-only
    STATUS      current
    DESCRIPTION
        "edfa pump temperature control current, unit is A."
    ::= { configEdfa 12 }

edfaPowerVoltage   OBJECT-TYPE    
    SYNTAX      OCTET STRING (SIZE(0..255))
    MAX-ACCESS  read-only
    STATUS      current
    DESCRIPTION
        "edfa power voltage, unit is V."
    ::= { configEdfa 13 }

edfaHostname    OBJECT-TYPE    
    SYNTAX      OCTET STRING (SIZE(0..32))
    MAX-ACCESS  read-write
    STATUS      current
    DESCRIPTION
        "edfa name of equipment."
    ::= { configEdfa 14 }

edfaReset       OBJECT-TYPE    
    SYNTAX      INTEGER(0..1)
    MAX-ACCESS  read-write
    STATUS      current
    DESCRIPTION
        "set edfaReset = 1 to reset all parameter."
    ::= { configEdfa 15 }

--------------------------------------------------------------
------------------ 1.2. config slot ------------------------
--------------------------------------------------------------


--------------------------------------------------------------
------------------ 1.3. config pport ----------------------
--------------------------------------------------------------
-- 1.3.1. ontFindConfigTable
-- 1.3.2. ontSilentConfigTable
-- 1.3.3. configPportPrimaryTable
-- 1.3.4. configPportFecTable

-- 1.3.1. ontFindConfigTable ------------------------------
ontFindConfigTable  OBJECT-TYPE
        SYNTAX      SEQUENCE OF OntFindConfigEntry
        MAX-ACCESS  not-accessible
        STATUS      current
        DESCRIPTION
            "ont find config table"
        ::= { configPport 1 }

ontFindConfigEntry  OBJECT-TYPE
        SYNTAX      OntFindConfigEntry
        MAX-ACCESS  not-accessible
        STATUS      current
        DESCRIPTION
            "entry of ont find config table"
        INDEX { cpSlotIndex, cpPportIndex }
        ::= { ontFindConfigTable 1 }

OntFindConfigEntry  ::= 
        SEQUENCE 
        {
            cpSlotIndex              INTEGER,
            cpPportIndex             INTEGER,
            ontFindConfigEnable      INTEGER,
            ontFindConfigInterval    INTEGER,
            ontFindConfigAgeEnable   INTEGER,
            ontFindConfigAgingTime   INTEGER,
            ontFindConfigMinDistance INTEGER,
            ontFindConfigMaxDistance INTEGER,
            ontFindDistanceRowStatus RowStatus
        }

cpSlotIndex     OBJECT-TYPE    
    SYNTAX      INTEGER(0..5)
    MAX-ACCESS  read-only
    STATUS      current
    DESCRIPTION
        "slot index, range <0-5>."
    ::= { ontFindConfigEntry 1 }

cpPportIndex    OBJECT-TYPE    
    SYNTAX      INTEGER(1..16)
    MAX-ACCESS  read-only
    STATUS      current
    DESCRIPTION
        "pon port index, range <1-16>."
    ::= { ontFindConfigEntry 2 }

ontFindConfigEnable OBJECT-TYPE    
    SYNTAX      INTEGER(0..1)
    MAX-ACCESS  read-write
    STATUS      current
    DESCRIPTION
        "ontFindConfigEnable:
         0  disable
         1  enable"
    ::= { ontFindConfigEntry 3 }

ontFindConfigInterval OBJECT-TYPE    
    SYNTAX      INTEGER(3..30)
    MAX-ACCESS  read-write
    STATUS      current
    DESCRIPTION
        "ont find interval time,range <3-30> seconds."
    ::= { ontFindConfigEntry 4 }

ontFindConfigAgeEnable OBJECT-TYPE    
    SYNTAX      INTEGER(0..1)
    MAX-ACCESS  read-write
    STATUS      current
    DESCRIPTION
        "ontFindConfigAgeEnable:
         0  disable
         1  enable"
    ::= { ontFindConfigEntry 5 }

ontFindConfigAgingTime OBJECT-TYPE    
    SYNTAX      INTEGER(1..86400)
    MAX-ACCESS  read-write
    STATUS      current
    DESCRIPTION
        "ont find list aging time,range <1-86400> seconds."
    ::= { ontFindConfigEntry 6 }

ontFindConfigMinDistance OBJECT-TYPE    
    SYNTAX      INTEGER(0..40)
    MAX-ACCESS  read-write
    STATUS      current
    DESCRIPTION
        "ont find min distance,range <0-40> km."
    ::= { ontFindConfigEntry 7 }

ontFindConfigMaxDistance OBJECT-TYPE    
    SYNTAX      INTEGER(0..60)
    MAX-ACCESS  read-write
    STATUS      current
    DESCRIPTION
        "ont find min distance,range <0-60> km."
    ::= { ontFindConfigEntry 8 }

ontFindDistanceRowStatus OBJECT-TYPE    
    SYNTAX       RowStatus
    MAX-ACCESS   read-write
    STATUS       current
    DESCRIPTION
        "RowStatus"
    ::= { ontFindConfigEntry 9 }

-- 1.3.2. ontSilentConfigTable ----------------------------
ontSilentConfigTable  OBJECT-TYPE
        SYNTAX      SEQUENCE OF OntSilentConfigEntry
        MAX-ACCESS  not-accessible
        STATUS      current
        DESCRIPTION
            "ont silent config table"
        ::= { configPport 2 }

ontSilentConfigEntry  OBJECT-TYPE
        SYNTAX      OntSilentConfigEntry
        MAX-ACCESS  not-accessible
        STATUS      current
        DESCRIPTION
            "entry of ont silent config table"
        INDEX { cpSlotIndexI, cpPportIndexI }
        ::= { ontSilentConfigTable 1 }

OntSilentConfigEntry  ::= 
        SEQUENCE 
        {
            cpSlotIndexI                  INTEGER,
            cpPportIndexI                 INTEGER,
            ontSilentConfigAuthFailEnable INTEGER,
            ontSilentConfigAuthFailTime   INTEGER,
            ontSilentConfigOfflineEnable  INTEGER,
            ontSilentConfigOfflineTime    INTEGER
        }

cpSlotIndexI    OBJECT-TYPE    
    SYNTAX      INTEGER(0..5)
    MAX-ACCESS  read-only
    STATUS      current
    DESCRIPTION
        "slot index, range <0-5>."
    ::= { ontSilentConfigEntry 1 }

cpPportIndexI   OBJECT-TYPE    
    SYNTAX      INTEGER(1..16)
    MAX-ACCESS  read-only
    STATUS      current
    DESCRIPTION
        "pon port index, range <1-16>."
    ::= { ontSilentConfigEntry 2 }

ontSilentConfigAuthFailEnable OBJECT-TYPE    
    SYNTAX      INTEGER(0..1)
    MAX-ACCESS  read-write
    STATUS      current
    DESCRIPTION
        "ontSilentConfigAuthFailEnable:
         0  disable
         1  enable"
    ::= { ontSilentConfigEntry 3 }

ontSilentConfigAuthFailTime OBJECT-TYPE    
    SYNTAX      INTEGER(1..86400)
    MAX-ACCESS  read-write
    STATUS      current
    DESCRIPTION
        "ont silent auth fail silence time, range <1-86400> seconds."
    ::= { ontSilentConfigEntry 4 }

ontSilentConfigOfflineEnable OBJECT-TYPE    
    SYNTAX      INTEGER(0..1)
    MAX-ACCESS  read-write
    STATUS      current
    DESCRIPTION
        "ontSilentConfigOfflineEnable:
         0  disable
         1  enable"
    ::= { ontSilentConfigEntry 5 }

ontSilentConfigOfflineTime OBJECT-TYPE    
    SYNTAX      INTEGER(1..86400)
    MAX-ACCESS  read-write
    STATUS      current
    DESCRIPTION
        "ont silent offline silence time, range <1-86400> seconds."
    ::= { ontSilentConfigEntry 6 }

-- config pport primary table ------------------------------------
configPportPrimaryTable  OBJECT-TYPE
        SYNTAX      SEQUENCE OF ConfigPportPrimaryEntry
        MAX-ACCESS  not-accessible
        STATUS      current
        DESCRIPTION
            "status pport primary table"
        ::= { configPport 3 }

configPportPrimaryEntry    OBJECT-TYPE
        SYNTAX      ConfigPportPrimaryEntry
        MAX-ACCESS  not-accessible
        STATUS      current
        DESCRIPTION
            "entry of ont find list table"
        INDEX { cpSlotIndexII, cpPportIndexII }
        ::= { configPportPrimaryTable 1 }

ConfigPportPrimaryEntry  ::= 
        SEQUENCE 
        {
            cpSlotIndexII             INTEGER,
            cpPportIndexII            INTEGER,
            pportAdminStatus          INTEGER,
            pportLaserEnable          INTEGER
        }

cpSlotIndexII   OBJECT-TYPE    
    SYNTAX      INTEGER(0..5)
    MAX-ACCESS  read-only
    STATUS      current
    DESCRIPTION
        "The index of slot, should in <0-5>."
    ::= { configPportPrimaryEntry 1 }

cpPportIndexII  OBJECT-TYPE    
    SYNTAX      INTEGER(1..16)
    MAX-ACCESS  read-only
    STATUS      current
    DESCRIPTION
        "The index of pon port, should in <1-16>."
    ::= { configPportPrimaryEntry 2 }

pportAdminStatus   OBJECT-TYPE    
    SYNTAX      INTEGER(0..1)
    MAX-ACCESS  read-write
    STATUS      current
    DESCRIPTION
        "pportAdminStatus:
         0  shutdown
         1  no shutdown(default)"
    ::= { configPportPrimaryEntry 3 }

pportLaserEnable      OBJECT-TYPE    
    SYNTAX      INTEGER(0..1)
    MAX-ACCESS  read-write
    STATUS      current
    DESCRIPTION
        "pportLaserEnable:
         0  disable
         1  enable(default)"
    ::= { configPportPrimaryEntry 4 }

-- config pport fec table ------------------------------------
configPportFecTable  OBJECT-TYPE
        SYNTAX      SEQUENCE OF ConfigPportFecEntry
        MAX-ACCESS  not-accessible
        STATUS      current
        DESCRIPTION
            "config pon port fec table"
        ::= { configPport 4 }

configPportFecEntry    OBJECT-TYPE
        SYNTAX      ConfigPportFecEntry
        MAX-ACCESS  not-accessible
        STATUS      current
        DESCRIPTION
            "entry of pon port fec table"
        INDEX { cpSlotIndexII, cpPportIndexII }
        ::= { configPportFecTable 1 }

ConfigPportFecEntry  ::= 
        SEQUENCE 
        {
            cpSlotIndexIII            INTEGER,
            cpPportIndexIII           INTEGER,
            pportFecStatus            INTEGER
        }

cpSlotIndexIII   OBJECT-TYPE    
    SYNTAX      INTEGER(0..5)
    MAX-ACCESS  read-only
    STATUS      current
    DESCRIPTION
        "The index of slot, should in <0-5>."
    ::= { configPportFecEntry 1 }

cpPportIndexIII  OBJECT-TYPE    
    SYNTAX      INTEGER(1..16)
    MAX-ACCESS  read-only
    STATUS      current
    DESCRIPTION
        "The index of pon port, should in <1-16>."
    ::= { configPportFecEntry 2 }

pportFecStatus   OBJECT-TYPE    
    SYNTAX      INTEGER(0..1)
    MAX-ACCESS  read-write
    STATUS      current
    DESCRIPTION
        "pportFecStatus:
         0  disable(default)
         1  enable"
    ::= { configPportFecEntry 3 }

--------------------------------------------------------------
------------------ 1.4. config ont ------------------------
--------------------------------------------------------------
-- 1.4.1. ontManageTable
-- 1.4.2. ontUpgradeTable
-- 1.4.3. ontPortTable

-- 1.4.1. ontManageTable ----------------------------------
ontManageTable      OBJECT-TYPE
        SYNTAX      SEQUENCE OF OntManageEntry
        MAX-ACCESS  not-accessible
        STATUS      current
        DESCRIPTION
            "ont management table, such as reboot, ont statistics ethport switch, etc."
        ::= { configOnt 1 }

ontManageEntry      OBJECT-TYPE
        SYNTAX      OntManageEntry
        MAX-ACCESS  not-accessible
        STATUS      current
        DESCRIPTION
            "entry of ont silent config table"
        INDEX { coSlotIndex, coPportIndex, coOntOnlineIndex }
        ::= { ontManageTable 1 }

OntManageEntry  ::= 
        SEQUENCE 
        {
            coSlotIndex        INTEGER,
            coPportIndex       INTEGER,
            coOntOnlineIndex   INTEGER,
            ontStatisticsEth   INTEGER,
            ontStatisticsGem   INTEGER,
            ontReboot          INTEGER,
            ontAdminState      INTEGER,
            ontFactorySet      INTEGER,
            protocolPort80     INTEGER,
            restoreFactory     INTEGER
        }

coSlotIndex     OBJECT-TYPE    
    SYNTAX      INTEGER(0..5)
    MAX-ACCESS  read-only
    STATUS      current
    DESCRIPTION
        "The index of slot, should in <0-5>."
    ::= { ontManageEntry 1 }

coPportIndex    OBJECT-TYPE    
    SYNTAX      INTEGER(1..16)
    MAX-ACCESS  read-only
    STATUS      current
    DESCRIPTION
        "The index of pon port, should in <1-16>."
    ::= { ontManageEntry 2 }

coOntOnlineIndex     OBJECT-TYPE    
    SYNTAX      INTEGER(1..128)
    MAX-ACCESS  read-only
    STATUS      current
    DESCRIPTION
        "Ont online index, the 3rd index of this table. range is <1-128>"
    ::= { ontManageEntry 3 }

ontStatisticsEth OBJECT-TYPE    
    SYNTAX      INTEGER(0..1)
    MAX-ACCESS  read-write
    STATUS      current
    DESCRIPTION
        "ontStatisticsEth:
         0  disable(default)
         1  enable."
    ::= { ontManageEntry 4 }

ontStatisticsGem OBJECT-TYPE    
    SYNTAX      INTEGER(0..1)
    MAX-ACCESS  read-write
    STATUS      current
    DESCRIPTION
        "ontStatisticsGem:
         0  disable(default)
         1  enable"
    ::= { ontManageEntry 5 }

ontReboot       OBJECT-TYPE    
    SYNTAX      INTEGER(0..1)
    MAX-ACCESS  read-write
    STATUS      current
    DESCRIPTION
        "set ontReboot=1 to reboot the ont, when read, always 0."
    ::= { ontManageEntry 6 }

ontAdminState   OBJECT-TYPE    
    SYNTAX      INTEGER(0..1)
    MAX-ACCESS  read-write
    STATUS      current
    DESCRIPTION
        "ontAdminState:
        0  deactive
        1  active(default)"
    ::= { ontManageEntry 7 }

ontFactorySet   OBJECT-TYPE    
    SYNTAX      INTEGER(0..1)
    MAX-ACCESS  read-write
    STATUS      current
    DESCRIPTION
        "set ontFactorySet=1 to factory setting the ont, when read, always 0."
    ::= { ontManageEntry 8 }

protocolPort80   OBJECT-TYPE    
    SYNTAX      INTEGER { disable_discard(0),
                          disable_forward(1), 
                          enable_discard(2), 
                          enable_forward(3),
                          init(4) }
    MAX-ACCESS  read-write
    STATUS      current
    DESCRIPTION
        "set protocol-port-80 disable mode discard or enable mode forward."
    ::= { ontManageEntry 9 }

restoreFactory   OBJECT-TYPE    
    SYNTAX      INTEGER { wan(0),
                          wifi(1) }
    MAX-ACCESS  read-write
    STATUS      current
    DESCRIPTION
        "factory setting restore.
        0: wan
        1: wifi"
    ::= { ontManageEntry 10 }
    
-- 1.4.2. ontUpgradeTable ----------------------------------
ontUpgradeTable OBJECT-IDENTITY
      STATUS current
      DESCRIPTION 
        "ont upgrade table"
      ::= { configOnt 2 }     
      
ontUpgradeEntry OBJECT IDENTIFIER ::= { ontUpgradeTable 1 }  
        
OntUpgradeEntry  ::=
        SEQUENCE 
        {
            ontUpgradeIdList       OCTET STRING,
            ontUpgradeSn           OCTET STRING,
            ontUpgradeParams       INTEGER,
            ontUpgradeRowStatus    RowStatus
        }

ontUpgradeIdList OBJECT-TYPE    
    SYNTAX      OCTET STRING (SIZE(0..255))
    MAX-ACCESS  read-write
    STATUS      current
    DESCRIPTION
        "ont upgrade ont-id list."
    ::= { ontUpgradeEntry 1 }

ontUpgradeSn OBJECT-TYPE    
    SYNTAX      OCTET STRING (SIZE(0..8))
    MAX-ACCESS  read-write
    STATUS      current
    DESCRIPTION
        "ont upgrade ont sn."
    ::= { ontUpgradeEntry 2 }

ontUpgradeParams OBJECT-TYPE    
    SYNTAX      INTEGER(0..3)
    MAX-ACCESS  read-write
    STATUS      current
    DESCRIPTION
        "ontUpgradeParams:
         0  ont upgrade
         1  ont upgrade commit.
         2  ont auto-reboot
         3  ont manual-reboot"
    ::= { ontUpgradeEntry 3 }

ontUpgradeRowStatus   OBJECT-TYPE    
    SYNTAX      RowStatus
    MAX-ACCESS  read-write
    STATUS      current
    DESCRIPTION
        "RowStatus"
    ::= { ontUpgradeEntry 4 }


-- 1.4.3. ontPortTable ----------------------------------
ontPortTable      OBJECT-TYPE
        SYNTAX      SEQUENCE OF OntPortEntry
        MAX-ACCESS  not-accessible
        STATUS      current
        DESCRIPTION
            "ont port table, port config."
        ::= { configOnt 3 }

ontPortEntry      OBJECT-TYPE
        SYNTAX      OntPortEntry
        MAX-ACCESS  not-accessible
        STATUS      current
        DESCRIPTION
            "entry of ont port config table"
        INDEX { ontPortSlotIndex, ontPortPportIndex, ontPortOntOnlineIndex, ontPortOntPortIndex }
        ::= { ontPortTable 1 }

OntPortEntry  ::= 
        SEQUENCE 
        {
            ontPortSlotIndex       INTEGER,
            ontPortPportIndex      INTEGER,
            ontPortOntOnlineIndex  INTEGER,
            ontPortOntPortIndex    INTEGER,
            ontPortShutdown        INTEGER
        }

ontPortSlotIndex     OBJECT-TYPE    
    SYNTAX      INTEGER(0..5)
    MAX-ACCESS  read-only
    STATUS      current
    DESCRIPTION
        "The index of slot, should in <0-5>."
    ::= { ontPortEntry 1 }

ontPortPportIndex    OBJECT-TYPE    
    SYNTAX      INTEGER(1..16)
    MAX-ACCESS  read-only
    STATUS      current
    DESCRIPTION
        "The index of pon port, should in <1-16>."
    ::= { ontPortEntry 2 }

ontPortOntOnlineIndex     OBJECT-TYPE    
    SYNTAX      INTEGER(1..128)
    MAX-ACCESS  read-only
    STATUS      current
    DESCRIPTION
        "Ont online index, the 3rd index of this table. range is <1-128>"
    ::= { ontPortEntry 3 }

ontPortOntPortIndex       OBJECT-TYPE    
    SYNTAX      INTEGER(1..24)
    MAX-ACCESS  read-only
    STATUS      current
    DESCRIPTION
        "Ont port index, the 4th index of this table, range is <1-24>"
    ::= { ontPortEntry 4 }

ontPortShutdown          OBJECT-TYPE    
    SYNTAX      INTEGER { enable(0), disable(1) }
    MAX-ACCESS  read-write
    STATUS      current
    DESCRIPTION
        "ontPortShutdown:
         0  enable(default)
         1  disable"
    ::= { ontPortEntry 5 }

--------------------------------------------------------------
------------------ 2.1. status device ----------------------
--------------------------------------------------------------
-- 2.1.1. deployStatus
-- 2.1.2. deployHistoryTable
-- 2.1.3. statusDeviceBaseInfo

-- 2.1.1. deployStatus ------------------------------------
deployStatus       OBJECT IDENTIFIER ::= { statusDevice 1 }

deployStatusUserName  OBJECT-TYPE    
    SYNTAX      OCTET STRING (SIZE(0..255))
    MAX-ACCESS  read-only
    STATUS      current
    DESCRIPTION
        "user name of deploy permission owner."
    ::= { deployStatus 1 }

deployStatusTerminal  OBJECT-TYPE    
    SYNTAX      OCTET STRING (SIZE(0..255))
    MAX-ACCESS  read-only
    STATUS      current
    DESCRIPTION
        "terminal of deploy permission owner."
    ::= { deployStatus 2 }

deployStatusUserIp  OBJECT-TYPE    
    SYNTAX      IpAddress
    MAX-ACCESS  read-only
    STATUS      current
    DESCRIPTION
        "ip address of deploy permission owner."
    ::= { deployStatus 3 }

deployStatusRequestTime  OBJECT-TYPE    
    SYNTAX      OCTET STRING (SIZE(0..255))
    MAX-ACCESS  read-only
    STATUS      current
    DESCRIPTION
        "request time of deploy permission owner."
    ::= { deployStatus 4 }

deployStatusLastActiveTime  OBJECT-TYPE    
    SYNTAX      OCTET STRING (SIZE(0..255))
    MAX-ACCESS  read-only
    STATUS      current
    DESCRIPTION
        "last active time of deploy permission owner."
    ::= { deployStatus 5 }

-- 2.1.2. deployHistoryTable ------------------------------
deployHistoryTable  OBJECT-TYPE
        SYNTAX      SEQUENCE OF DeployHistoryEntry
        MAX-ACCESS  not-accessible
        STATUS      current
        DESCRIPTION
            "deploy history table"
        ::= { statusDevice 2 }

deployHistoryEntry  OBJECT-TYPE
        SYNTAX      DeployHistoryEntry
        MAX-ACCESS  not-accessible
        STATUS      current
        DESCRIPTION
            "entry of deploy history table"
        INDEX { deployHistoryIndex }
        ::= { deployHistoryTable 1 }

DeployHistoryEntry  ::= 
        SEQUENCE 
        {
            deployHistoryIndex          INTEGER,
            deployHistoryUserName       OCTET STRING,
            deployHistoryTerminal       OCTET STRING,
            deployHistoryUserIp         IpAddress,
            deployHistoryRequestTime    OCTET STRING,
            deployHistoryActiveTimeList OCTET STRING,
            deployHistoryReleaseTime    OCTET STRING
        }

deployHistoryIndex OBJECT-TYPE    
    SYNTAX      INTEGER(0..19)
    MAX-ACCESS  read-only
    STATUS      current
    DESCRIPTION
        "index of deploy history table."
    ::= { deployHistoryEntry 1 }

deployHistoryUserName OBJECT-TYPE    
    SYNTAX      OCTET STRING (SIZE(0..255))
    MAX-ACCESS  read-only
    STATUS      current
    DESCRIPTION
        "user name of deploy history entry."
    ::= { deployHistoryEntry 2 }

deployHistoryTerminal OBJECT-TYPE    
    SYNTAX      OCTET STRING (SIZE(0..255))
    MAX-ACCESS  read-only
    STATUS      current
    DESCRIPTION
        "terminal of deploy history entry."
    ::= { deployHistoryEntry 3 }

deployHistoryUserIp OBJECT-TYPE    
    SYNTAX      IpAddress
    MAX-ACCESS  read-only
    STATUS      current
    DESCRIPTION
        "ip address of deploy history entry."
    ::= { deployHistoryEntry 4 }

deployHistoryRequestTime OBJECT-TYPE    
    SYNTAX      OCTET STRING (SIZE(0..255))
    MAX-ACCESS  read-only
    STATUS      current
    DESCRIPTION
        "request time of deploy history entry. format: yyyy-mm-dd hh:mm:ss"
    ::= { deployHistoryEntry 5 }

deployHistoryActiveTimeList OBJECT-TYPE    
    SYNTAX      OCTET STRING (SIZE(0..255))
    MAX-ACCESS  read-only
    STATUS      current
    DESCRIPTION
        "active time list of deploy history entry. format: yyyy-mm-dd hh:mm:ss,...,.."
    ::= { deployHistoryEntry 6 }

deployHistoryReleaseTime OBJECT-TYPE    
    SYNTAX      OCTET STRING (SIZE(0..255))
    MAX-ACCESS  read-only
    STATUS      current
    DESCRIPTION
        "release time of deploy history entry. format: yyyy-mm-dd hh:mm:ss"
    ::= { deployHistoryEntry 7 }

-- 2.1.3. statusDeviceBaseInfo ----------------------------
statusDeviceBaseInfo  OBJECT IDENTIFIER ::= { statusDevice 3 }

cpuUsePercent   OBJECT-TYPE    
    SYNTAX      INTEGER(0..100)
    MAX-ACCESS  read-only
    STATUS      current
    DESCRIPTION
        "The percentage of use CPU in current system."
    ::= { statusDeviceBaseInfo 1 }

memUsePercent   OBJECT-TYPE    
    SYNTAX      INTEGER(0..100)
    MAX-ACCESS  read-only
    STATUS      current
    DESCRIPTION
        "The percentage of use memory in current system."
    ::= { statusDeviceBaseInfo 2 }

switchChipTemperature  OBJECT-TYPE    
    SYNTAX      INTEGER(0..100)
    MAX-ACCESS  read-only
    STATUS      current
    DESCRIPTION
        "The temperature of switch chip in current system."
    ::= { statusDeviceBaseInfo 3 }

ponChipTemperature  OBJECT-TYPE    
    SYNTAX      INTEGER(0..100)
    MAX-ACCESS  read-only
    STATUS      current
    DESCRIPTION
        "The temperature of pon chip in current system."
    ::= { statusDeviceBaseInfo 4 }

ontImageName    OBJECT-TYPE
    SYNTAX      OCTET STRING (SIZE(0..255))
    MAX-ACCESS  read-only
    STATUS      current
    DESCRIPTION
        "ont image name "
    ::= { statusDeviceBaseInfo 5 }

ontImageLen     OBJECT-TYPE
    SYNTAX      INTEGER (0..26214400)
    MAX-ACCESS  read-only
    STATUS      current
    DESCRIPTION
        "ont image length "
    ::= { statusDeviceBaseInfo 6 }
    
--------------------------------------------------------------
------------------ 2.2. status slot ------------------------
--------------------------------------------------------------
-- 2.2.1. statusSlotPrimaryTable

-- slot status primary table ------------------------------
statusSlotPrimaryTable  OBJECT-TYPE
        SYNTAX      SEQUENCE OF StatusSlotPrimaryEntry
        MAX-ACCESS  not-accessible
        STATUS      current
        DESCRIPTION
            "slot status primary table"
        ::= { statusSlot 1 }

statusSlotPrimaryEntry    OBJECT-TYPE
        SYNTAX      StatusSlotPrimaryEntry
        MAX-ACCESS  not-accessible
        STATUS      current
        DESCRIPTION
            "entry of slot status primary table"
        INDEX { ssSlotIndex }
        ::= { statusSlotPrimaryTable 1 }

StatusSlotPrimaryEntry  ::= 
        SEQUENCE 
        {
            ssSlotIndex               INTEGER,
            slotState                 INTEGER,
            slotConfigType            INTEGER,
            slotTrueType              INTEGER,
            slotTypeIsPon             INTEGER,
            slotConnected             INTEGER,
            slotMac                   MacAddress,
            slotSwVersion             OCTET STRING,
            slotHwVersion             OCTET STRING
        }

ssSlotIndex      OBJECT-TYPE
    SYNTAX         INTEGER(0..5)
    MAX-ACCESS  read-only
    STATUS        current
    DESCRIPTION
        "slot index rang is 0 to 5"
    ::= { statusSlotPrimaryEntry 1 }

slotState    OBJECT-TYPE
    SYNTAX         INTEGER(0..10)
    MAX-ACCESS  read-only
    STATUS        current
    DESCRIPTION
    "typedef enum
    {
        STATUS_DOWN = 0,
        STATUS_INIT,
        STATUS_LOAD,
        STATUS_REG,
        STATUS_CONFIG,
        STATUS_ONLINE
    }SLOT_STATUS_ENUM;"
    ::= { statusSlotPrimaryEntry 2 }
    
slotConfigType    OBJECT-TYPE
    SYNTAX         INTEGER(0..10)
    MAX-ACCESS  read-only
    STATUS        current
    DESCRIPTION
    "typedef enum tag_BOARD_TYPE
    {
        BOARD_TYPE_NULL = 0,
        BOARD_TYPE_CONTROL_BCM5670,
        BOARD_TYPE_LINE_24_GE_FIBER_BCM56504,
        BOARD_TYPE_LINE_24_GE_COPPER_BCM56504,
        BOARD_TYPE_LINE_24_GE_COPPER_BCM56524,    
        BOARD_TYPE_LINE_8_10GE_FIBER_BCM56820,
        BOARD_TYPE_LINE_8PON_6GE_BCM56524,
        BOARD_TYPE_CONTROL_BCM56720,  
        BOARD_TYPE_LINE_8GPON_8GE_BCM56684,
        BOARD_TYPE_LINE_4pon_4_10GE_BCM56821,
        BOARD_TYPE_NUM
    }BOARD_TYPE;
    "
    ::= { statusSlotPrimaryEntry 3 }

slotTrueType    OBJECT-TYPE
    SYNTAX         INTEGER(0..10)
    MAX-ACCESS  read-only
    STATUS        current
    DESCRIPTION
    "typedef enum tag_BOARD_TYPE
    {
        BOARD_TYPE_NULL = 0,
        BOARD_TYPE_CONTROL_BCM5670,
        BOARD_TYPE_LINE_24_GE_FIBER_BCM56504,
        BOARD_TYPE_LINE_24_GE_COPPER_BCM56504,
        BOARD_TYPE_LINE_24_GE_COPPER_BCM56524,    
        BOARD_TYPE_LINE_8_10GE_FIBER_BCM56820,
        BOARD_TYPE_LINE_8PON_6GE_BCM56524,
        BOARD_TYPE_CONTROL_BCM56720,  
        BOARD_TYPE_LINE_8GPON_8GE_BCM56684,
        BOARD_TYPE_LINE_4pon_4_10GE_BCM56821,
        BOARD_TYPE_NUM
    }BOARD_TYPE;"
    ::= { statusSlotPrimaryEntry 4 }
    
slotTypeIsPon  OBJECT-TYPE
    SYNTAX         INTEGER(0..1)
    MAX-ACCESS  read-only
    STATUS        current
    DESCRIPTION
        "slotTypeIsPon:
         1  true
         0  false"
    ::= { statusSlotPrimaryEntry 5 }

slotConnected     OBJECT-TYPE
    SYNTAX         INTEGER(0..1)
    MAX-ACCESS  read-only
    STATUS        current
    DESCRIPTION
        "slotConnected:
         1  true
         0  false"
    ::= { statusSlotPrimaryEntry 6 }

slotMac  OBJECT-TYPE
    SYNTAX         MacAddress
    MAX-ACCESS  read-only
    STATUS        current
    DESCRIPTION
        "slot mac address"
    ::= { statusSlotPrimaryEntry 7 }

slotSwVersion    OBJECT-TYPE
    SYNTAX         OCTET STRING (SIZE(0..255))
    MAX-ACCESS  read-only
    STATUS        current
    DESCRIPTION
    "slotSwVersion"
    ::= { statusSlotPrimaryEntry 8 }

slotHwVersion    OBJECT-TYPE
    SYNTAX         OCTET STRING (SIZE(0..255))
    MAX-ACCESS  read-only
    STATUS        current
    DESCRIPTION
    "slotHwVersion"
    ::= { statusSlotPrimaryEntry 9 }


--------------------------------------------------------------
------------------ 2.3. status pport ----------------------
--------------------------------------------------------------
-- 2.3.1. ontFindListTable
-- 2.3.2. ontSilentListTable
-- 2.3.3. pportSfpTable
-- 2.3.4. statusPportPrimaryTable
-- 2.3.5. portUtilizationTable

-- ont find list table ------------------------------------
ontFindListTable  OBJECT-TYPE
        SYNTAX      SEQUENCE OF OntFindListEntry
        MAX-ACCESS  not-accessible
        STATUS      current
        DESCRIPTION
            "ont find list table"
        ::= { statusPport 1 }

ontFindListEntry    OBJECT-TYPE
        SYNTAX      OntFindListEntry
        MAX-ACCESS  not-accessible
        STATUS      current
        DESCRIPTION
            "entry of ont find list table"
        INDEX { spSlotIndex, spPportIndex, ontFindListListId }
        ::= { ontFindListTable 1 }

OntFindListEntry  ::= 
        SEQUENCE 
        {
            spSlotIndex               INTEGER,
            spPportIndex              INTEGER,
            ontFindListListId         INTEGER,
            ontFindListSn             OCTET STRING,
            ontFindListPw             OCTET STRING,
            ontFindListLoid           OCTET STRING,
            ontFindListLopw           OCTET STRING,
            ontFindListVendorId       OCTET STRING,
            ontFindListPriSwVer       OCTET STRING,
            ontFindListSecSwVer       OCTET STRING,
            ontFindListHwVer          OCTET STRING,
            ontFindListEquipId        OCTET STRING,
            ontFindListFirstFindTime  OCTET STRING,
            ontFindListLastFindTime   OCTET STRING,
            ontFindListFindCnt        OCTET STRING
        }

spSlotIndex     OBJECT-TYPE    
    SYNTAX      INTEGER(0..5)
    MAX-ACCESS  read-only
    STATUS      current
    DESCRIPTION
        "The index of slot, should in <0-5>."
    ::= { ontFindListEntry 1 }

spPportIndex    OBJECT-TYPE    
    SYNTAX      INTEGER(1..16)
    MAX-ACCESS  read-only
    STATUS      current
    DESCRIPTION
        "The index of pon port, should in <1-16>."
    ::= { ontFindListEntry 2 }

ontFindListListId OBJECT-TYPE    
    SYNTAX        INTEGER(0..255)
    MAX-ACCESS    read-only
    STATUS        current
    DESCRIPTION
        "The index of ont find list table."
    ::= { ontFindListEntry 3 }

ontFindListSn      OBJECT-TYPE
    SYNTAX         OCTET STRING (SIZE(0..255))
    MAX-ACCESS     read-only
    STATUS         current
    DESCRIPTION
        "serial number of ont find list entry."
    ::= { ontFindListEntry 4 }

ontFindListPw      OBJECT-TYPE
    SYNTAX         OCTET STRING (SIZE(0..255))
    MAX-ACCESS     read-only
    STATUS         current
    DESCRIPTION
        "password of ont find list entry."
    ::= { ontFindListEntry 5 }

ontFindListLoid    OBJECT-TYPE
    SYNTAX         OCTET STRING (SIZE(0..255))
    MAX-ACCESS     read-only
    STATUS         current
    DESCRIPTION
        "logic id of ont find list entry."
    ::= { ontFindListEntry 6 }

ontFindListLopw    OBJECT-TYPE
    SYNTAX         OCTET STRING (SIZE(0..255))
    MAX-ACCESS     read-only
    STATUS         current
    DESCRIPTION
        "logic password of ont find list entry."
    ::= { ontFindListEntry 7 }

ontFindListVendorId OBJECT-TYPE
    SYNTAX         OCTET STRING (SIZE(0..255))
    MAX-ACCESS     read-only
    STATUS         current
    DESCRIPTION
        "vendor id of ont find list entry."
    ::= { ontFindListEntry 8 }

ontFindListPriSwVer OBJECT-TYPE
    SYNTAX         OCTET STRING (SIZE(0..255))
    MAX-ACCESS     read-only
    STATUS         current
    DESCRIPTION
        "primary software version of ont find list entry."
    ::= { ontFindListEntry 9 }

ontFindListSecSwVer OBJECT-TYPE
    SYNTAX         OCTET STRING (SIZE(0..255))
    MAX-ACCESS     read-only
    STATUS         current
    DESCRIPTION
        "secondary software version of ont find list entry."
    ::= { ontFindListEntry 10 }

ontFindListHwVer   OBJECT-TYPE
    SYNTAX         OCTET STRING (SIZE(0..255))
    MAX-ACCESS     read-only
    STATUS         current
    DESCRIPTION
        "hardware version of ont find list entry."
    ::= { ontFindListEntry 11 }

ontFindListEquipId OBJECT-TYPE
    SYNTAX         OCTET STRING (SIZE(0..255))
    MAX-ACCESS     read-only
    STATUS         current
    DESCRIPTION
        "equipment id of ont find list entry."
    ::= { ontFindListEntry 12 }

ontFindListFirstFindTime OBJECT-TYPE
    SYNTAX         OCTET STRING (SIZE(0..255))
    MAX-ACCESS     read-only
    STATUS         current
    DESCRIPTION
        "first find time of ont find list entry."
    ::= { ontFindListEntry 13 }

ontFindListLastFindTime OBJECT-TYPE
    SYNTAX         OCTET STRING (SIZE(0..255))
    MAX-ACCESS     read-only
    STATUS         current
    DESCRIPTION
        "last find time of ont find list entry."
    ::= { ontFindListEntry 14 }

ontFindListFindCnt OBJECT-TYPE
    SYNTAX         OCTET STRING (SIZE(0..255))
    MAX-ACCESS     read-only
    STATUS         current
    DESCRIPTION
        "find count of ont find list entry."
    ::= { ontFindListEntry 15 }

-- ont silent list table ----------------------------------
ontSilentListTable  OBJECT-TYPE
        SYNTAX      SEQUENCE OF OntSilentListEntry
        MAX-ACCESS  not-accessible
        STATUS      current
        DESCRIPTION
            "ont silent list table"
        ::= { statusPport 2 }

ontSilentListEntry  OBJECT-TYPE
        SYNTAX      OntSilentListEntry
        MAX-ACCESS  not-accessible
        STATUS      current
        DESCRIPTION
            "entry of ont find list table"
        INDEX { spSlotIndexI, spPportIndexI, ontSilentListListId }
        ::= { ontSilentListTable 1 }

OntSilentListEntry  ::= 
        SEQUENCE 
        {
            spSlotIndexI              INTEGER,
            spPportIndexI             INTEGER,
            ontSilentListListId       INTEGER,
            ontSilentListSn           OCTET STRING,
            ontSilentListTime         INTEGER,
            ontSilentListReason       OCTET STRING
        }

spSlotIndexI    OBJECT-TYPE    
    SYNTAX      INTEGER(0..5)
    MAX-ACCESS  read-only
    STATUS      current
    DESCRIPTION
        "The index of slot, should in <0-5>."
    ::= { ontSilentListEntry 1 }

spPportIndexI   OBJECT-TYPE    
    SYNTAX      INTEGER(1..16)
    MAX-ACCESS  read-only
    STATUS      current
    DESCRIPTION
        "The index of pon port, should in <1-16>."
    ::= { ontSilentListEntry 2 }

ontSilentListListId OBJECT-TYPE    
    SYNTAX        INTEGER(1..128)
    MAX-ACCESS    read-only
    STATUS        current
    DESCRIPTION
        "The index of ont silent list table."
    ::= { ontSilentListEntry 3 }

ontSilentListSn    OBJECT-TYPE
    SYNTAX         OCTET STRING (SIZE(0..255))
    MAX-ACCESS     read-only
    STATUS         current
    DESCRIPTION
        "serial number of ont silent list entry."
    ::= { ontSilentListEntry 4 }

ontSilentListTime OBJECT-TYPE    
    SYNTAX        INTEGER(1..86400)
    MAX-ACCESS    read-only
    STATUS        current
    DESCRIPTION
        "remain time of ont silent list entry, unit is second."
    ::= { ontSilentListEntry 5 }

ontSilentListReason OBJECT-TYPE
    SYNTAX         OCTET STRING (SIZE(0..255))
    MAX-ACCESS     read-only
    STATUS         current
    DESCRIPTION
        "silent reason of ont silent list entry."
    ::= { ontSilentListEntry 6 }

-- 2.3.1. pportSfpTable ------------------------------
pportSfpTable  OBJECT-TYPE
        SYNTAX      SEQUENCE OF PportSfpEntry
        MAX-ACCESS  not-accessible
        STATUS      current
        DESCRIPTION
            "pport sfp info table"
        ::= { statusPport 3 }

pportSfpEntry  OBJECT-TYPE
        SYNTAX      PportSfpEntry
        MAX-ACCESS  not-accessible
        STATUS      current
        DESCRIPTION
            "entry of pport sfp info table"
        INDEX { spSlotIndexII, spPportIndexII }
        ::= { pportSfpTable 1 }

PportSfpEntry  ::= 
        SEQUENCE 
        {
            spSlotIndexII            INTEGER,
            spPportIndexII           INTEGER,
            sfpTransceiverType       OCTET STRING,
            sfpCompliance            OCTET STRING,
            sfpConnectorType         OCTET STRING,
            sfpWaveLength            OCTET STRING,
            sfpTransferDistance      OCTET STRING,
            sfpDigitalDiagMonitor    OCTET STRING,
            sfpManuSerialNumber      OCTET STRING,
            sfpManufacturingDate     OCTET STRING,
            sfpVendorName            OCTET STRING,
            sfpTemperature           OCTET STRING,
            sfpVoltage               OCTET STRING,
            sfpBiasCurrent           OCTET STRING,
            sfpBiasHighThreshold     OCTET STRING,
            sfpBiasLowThreshold      OCTET STRING,
            sfpRXPower               OCTET STRING,
            sfpRXPowerHighThreshold  OCTET STRING,
            sfpRXPowerLowThreshold   OCTET STRING,
            sfpTXPower               OCTET STRING,
            sfpTXPowerHighThreshold  OCTET STRING,
            sfpTXPowerLowThreshold   OCTET STRING,
            sfpExist                 INTEGER,
            sfpLinkState             INTEGER,
            sfpModuleType            INTEGER,
            sfpModuleSubType         INTEGER,
            sfpUsedType              INTEGER,
            sfpPartNumber            OCTET STRING
        }

spSlotIndexII   OBJECT-TYPE    
    SYNTAX      INTEGER(0..5)
    MAX-ACCESS  read-only
    STATUS      current
    DESCRIPTION
        "The index of slot, should in <0-5>."
    ::= { pportSfpEntry 1 }

spPportIndexII  OBJECT-TYPE    
    SYNTAX      INTEGER(1..16)
    MAX-ACCESS  read-only
    STATUS      current
    DESCRIPTION
        "The index of pon port, should in <1-16>."
    ::= { pportSfpEntry 2 }

sfpTransceiverType OBJECT-TYPE
    SYNTAX         OCTET STRING (SIZE(0..255))
    MAX-ACCESS     read-only
    STATUS         current
    DESCRIPTION
        "Sfp transceiver type."
    ::= { pportSfpEntry 3 }

sfpCompliance      OBJECT-TYPE
    SYNTAX         OCTET STRING (SIZE(0..255))
    MAX-ACCESS     read-only
    STATUS         current
    DESCRIPTION
        "Sfp compliance."
    ::= { pportSfpEntry 4 }

sfpConnectorType   OBJECT-TYPE
    SYNTAX         OCTET STRING (SIZE(0..255))
    MAX-ACCESS     read-only
    STATUS         current
    DESCRIPTION
        "Sfp connector type."
    ::= { pportSfpEntry 5 }
    
sfpWaveLength   OBJECT-TYPE
    SYNTAX      OCTET STRING (SIZE(0..255))
    MAX-ACCESS  read-only
    STATUS      current
    DESCRIPTION
        "Sfp wave length."
    ::= { pportSfpEntry 6 }

sfpTransferDistance OBJECT-TYPE
    SYNTAX          OCTET STRING (SIZE(0..255))
    MAX-ACCESS      read-only
    STATUS          current
    DESCRIPTION
        "Sfp transfer distance."
    ::= { pportSfpEntry 7 }

sfpDigitalDiagMonitor OBJECT-TYPE
    SYNTAX            OCTET STRING (SIZE(0..255))
    MAX-ACCESS        read-only
    STATUS            current
    DESCRIPTION
        "Sfp digital diagnostic monitoring."
    ::= { pportSfpEntry 8 }

sfpManuSerialNumber  OBJECT-TYPE
    SYNTAX           OCTET STRING (SIZE(0..255))
    MAX-ACCESS       read-only
    STATUS           current
    DESCRIPTION
        "Sfp manufacturing serial number."
    ::= { pportSfpEntry 9 }

sfpManufacturingDate OBJECT-TYPE
    SYNTAX           OCTET STRING (SIZE(0..255))
    MAX-ACCESS       read-only
    STATUS           current
    DESCRIPTION
        "Sfp manufacturing date."
    ::= { pportSfpEntry 10 }

sfpVendorName      OBJECT-TYPE
    SYNTAX         OCTET STRING (SIZE(0..255))
    MAX-ACCESS     read-only
    STATUS         current
    DESCRIPTION
        "Sfp vendor name."
    ::= { pportSfpEntry 11 }

sfpTemperature  OBJECT-TYPE
    SYNTAX      OCTET STRING (SIZE(0..255))
    MAX-ACCESS  read-only
    STATUS      current
    DESCRIPTION
        "Sfp temperature(°C)."
    ::= { pportSfpEntry 12 }    

sfpVoltage      OBJECT-TYPE
    SYNTAX      OCTET STRING (SIZE(0..255))
    MAX-ACCESS  read-only
    STATUS      current
    DESCRIPTION
        "Sfp voltage(V)."
    ::= { pportSfpEntry 13 }    

sfpBiasCurrent  OBJECT-TYPE
    SYNTAX      OCTET STRING (SIZE(0..255))
    MAX-ACCESS  read-only
    STATUS      current
    DESCRIPTION
        "Sfp bias current(mA)."
    ::= { pportSfpEntry 14 }    
    
sfpBiasHighThreshold OBJECT-TYPE
    SYNTAX           OCTET STRING (SIZE(0..255))
    MAX-ACCESS       read-only
    STATUS           current
    DESCRIPTION
        "Sfp bias high threshold(mA)."
    ::= { pportSfpEntry 15 }    
    
sfpBiasLowThreshold OBJECT-TYPE
    SYNTAX          OCTET STRING (SIZE(0..255))
    MAX-ACCESS      read-only
    STATUS          current
    DESCRIPTION
        "Sfp bias low threshold(mA)."
    ::= { pportSfpEntry 16 }   
     
sfpRXPower      OBJECT-TYPE
    SYNTAX      OCTET STRING (SIZE(0..255))
    MAX-ACCESS  read-only
    STATUS      current
    DESCRIPTION
        "Sfp rx power(dBm)."
    ::= { pportSfpEntry 17 }    
    
sfpRXPowerHighThreshold OBJECT-TYPE
    SYNTAX              OCTET STRING (SIZE(0..255))
    MAX-ACCESS          read-only
    STATUS              current
    DESCRIPTION
        "Sfp rx power high threshold(dBm)."
    ::= { pportSfpEntry 18 }    
    
sfpRXPowerLowThreshold OBJECT-TYPE
    SYNTAX             OCTET STRING (SIZE(0..255))
    MAX-ACCESS         read-only
    STATUS             current
    DESCRIPTION
        "Sfp rx power low threshold(dBm)."
    ::= { pportSfpEntry 19 }    
    
sfpTXPower      OBJECT-TYPE
    SYNTAX      OCTET STRING (SIZE(0..255))
    MAX-ACCESS  read-only
    STATUS      current
    DESCRIPTION
        "Sfp tx power(dBm)."
    ::= { pportSfpEntry 20 }    
    
sfpTXPowerHighThreshold OBJECT-TYPE
    SYNTAX              OCTET STRING (SIZE(0..255))
    MAX-ACCESS          read-only
    STATUS              current
    DESCRIPTION
        "Sfp tx power high threshold(dBm)."
    ::= { pportSfpEntry 21 }    
    
sfpTXPowerLowThreshold OBJECT-TYPE
    SYNTAX             OCTET STRING (SIZE(0..255))
    MAX-ACCESS         read-only
    STATUS             current
    DESCRIPTION
        "Sfp tx power low threshold(dBm)."
    ::= { pportSfpEntry 22 }    

sfpExist               OBJECT-TYPE
    SYNTAX             INTEGER(0..1)
    MAX-ACCESS         read-only
    STATUS             current
    DESCRIPTION
        "sfpExist:
        0  false
        1  true"
    ::= { pportSfpEntry 23 }    

sfpLinkState           OBJECT-TYPE
    SYNTAX             INTEGER(0..1)
    MAX-ACCESS         read-only
    STATUS             current
    DESCRIPTION
        "sfpLinkState:
        0  link down
        1  link up"
    ::= { pportSfpEntry 24 }    

sfpModuleType          OBJECT-TYPE
    SYNTAX             INTEGER(0..1)
    MAX-ACCESS         read-only
    STATUS             current
    DESCRIPTION
        "sfpModuleType:
        0  unknown
        1  GPON"
    ::= { pportSfpEntry 25 }    

sfpModuleSubType       OBJECT-TYPE
    SYNTAX             INTEGER(0..2)
    MAX-ACCESS         read-only
    STATUS             current
    DESCRIPTION
        "sfpModuleSubType:
        0  unknown
        1  Class B+
        2  Class C+"
    ::= { pportSfpEntry 26 }    

sfpUsedType            OBJECT-TYPE
    SYNTAX             INTEGER(0..1)
    MAX-ACCESS         read-only
    STATUS             current
    DESCRIPTION
        "sfpModuleSubType:
        0  unknown
        1  ONT"
    ::= { pportSfpEntry 27 }    

sfpPartNumber  OBJECT-TYPE
    SYNTAX           OCTET STRING (SIZE(0..255))
    MAX-ACCESS       read-only
    STATUS           current
    DESCRIPTION
        "Sfp manufacturing type."
    ::= { pportSfpEntry 28 }

-- status pport primary table
statusPportPrimaryTable  OBJECT-TYPE
        SYNTAX      SEQUENCE OF StatusPportPrimaryEntry
        MAX-ACCESS  not-accessible
        STATUS      current
        DESCRIPTION
            "status pport primary table"
        ::= { statusPport 4 }

statusPportPrimaryEntry    OBJECT-TYPE
        SYNTAX      StatusPportPrimaryEntry
        MAX-ACCESS  not-accessible
        STATUS      current
        DESCRIPTION
            "entry of ont find list table"
        INDEX { spSlotIndexIII, spPportIndexIII }
        ::= { statusPportPrimaryTable 1 }

StatusPportPrimaryEntry  ::= 
        SEQUENCE 
        {
            spSlotIndexIII            INTEGER,
            spPportIndexIII           INTEGER,
            pportLinkStatus           INTEGER
        }

spSlotIndexIII  OBJECT-TYPE    
    SYNTAX      INTEGER(0..5)
    MAX-ACCESS  read-only
    STATUS      current
    DESCRIPTION
        "The index of slot, should in <0-5>."
    ::= { statusPportPrimaryEntry 1 }

spPportIndexIII OBJECT-TYPE    
    SYNTAX      INTEGER(1..16)
    MAX-ACCESS  read-only
    STATUS      current
    DESCRIPTION
        "The index of pon port, should in <1-16>."
    ::= { statusPportPrimaryEntry 2 }

pportLinkStatus      OBJECT-TYPE    
    SYNTAX      INTEGER(0..1)
    MAX-ACCESS  read-only
    STATUS      current
    DESCRIPTION
        "pportLinkStatus:
         0  link down
         1  link up"
    ::= { statusPportPrimaryEntry 3 }

-- port utilization table ------------------------------------
portUtilizationTable  OBJECT-TYPE
        SYNTAX      SEQUENCE OF PortUtilizationEntry
        MAX-ACCESS  not-accessible
        STATUS      current
        DESCRIPTION
            "port utilization table"
        ::= { statusPport 5 }

portUtilizationEntry    OBJECT-TYPE
        SYNTAX      PortUtilizationEntry
        MAX-ACCESS  not-accessible
        STATUS      current
        DESCRIPTION
            "entry of port utilization table"
        INDEX { spSlotIndexPort, spPortIndex }
        ::= { portUtilizationTable 1 }

PortUtilizationEntry  ::= 
        SEQUENCE 
        {
            spSlotIndexPort           INTEGER,
            spPortIndex               INTEGER,
            spUtilizeTxOctetsRate     INTEGER,
            spUtilizeRxOctetsRate     INTEGER,
            spUtilizeTxBwThoughput    INTEGER,
            spUtilizeRxBwThoughput    INTEGER,
            spUtilizeTxPktsRate       INTEGER,
            spUtilizeRxPktsRate       INTEGER,
            spUtilizeTxOctetsMaxRate  INTEGER,
            spUtilizeRxOctetsMaxRate  INTEGER
        }

spSlotIndexPort OBJECT-TYPE    
    SYNTAX      INTEGER(0..5)
    MAX-ACCESS  read-only
    STATUS      current
    DESCRIPTION
        "The index of slot, should in <0-5>."
    ::= { portUtilizationEntry 1 }

spPortIndex     OBJECT-TYPE    
    SYNTAX      INTEGER(1..16)
    MAX-ACCESS  read-only
    STATUS      current
    DESCRIPTION
        "The index of port, should in <1-16>."
    ::= { portUtilizationEntry 2 }

spUtilizeTxOctetsRate  OBJECT-TYPE    
    SYNTAX      INTEGER(0..10000)
    MAX-ACCESS  read-only
    STATUS      current
    DESCRIPTION
        "port tx octets rate."
    ::= { portUtilizationEntry 3 }

spUtilizeRxOctetsRate  OBJECT-TYPE    
    SYNTAX      INTEGER(0..10000)
    MAX-ACCESS  read-only
    STATUS      current
    DESCRIPTION
        "port rx octets rate."
    ::= { portUtilizationEntry 4 }

spUtilizeTxBwThoughput  OBJECT-TYPE    
    SYNTAX      INTEGER(0..100)
    MAX-ACCESS  read-only
    STATUS      current
    DESCRIPTION
        "port tx bandwidth thoughput."
    ::= { portUtilizationEntry 5 }

spUtilizeRxBwThoughput  OBJECT-TYPE    
    SYNTAX      INTEGER(0..100)
    MAX-ACCESS  read-only
    STATUS      current
    DESCRIPTION
        "port rx bandwidth thoughput."
    ::= { portUtilizationEntry 6 }

spUtilizeTxPktsRate  OBJECT-TYPE    
    SYNTAX      INTEGER(0..1600000000)
    MAX-ACCESS  read-only
    STATUS      current
    DESCRIPTION
        "port tx packets rate."
    ::= { portUtilizationEntry 7 }

spUtilizeRxPktsRate  OBJECT-TYPE    
    SYNTAX      INTEGER(0..1600000000)
    MAX-ACCESS  read-only
    STATUS      current
    DESCRIPTION
        "port rx packets rate."
    ::= { portUtilizationEntry 8 }

spUtilizeTxOctetsMaxRate  OBJECT-TYPE    
    SYNTAX      INTEGER(0..10000)
    MAX-ACCESS  read-only
    STATUS      current
    DESCRIPTION
        "port tx octets max rate."
    ::= { portUtilizationEntry 9 }

spUtilizeRxOctetsMaxRate  OBJECT-TYPE    
    SYNTAX      INTEGER(0..10000)
    MAX-ACCESS  read-only
    STATUS      current
    DESCRIPTION
        "port rx octets max rate."
    ::= { portUtilizationEntry 10 }

--------------------------------------------------------------
------------------ 2.4. status ont ------------------------
--------------------------------------------------------------
-- 2.4.1 ontInfo
-- 2.4.2 ontEthPortInfo
-- 2.4.3 ontGemPortInfo
-- 2.4.4 ontWanInfo
-- 2.4.5 ontPotsInfo

-- ont infomation ------------------------------------------
ontInfo       OBJECT IDENTIFIER ::= { statusOnt 1 }

-- 2.4.1.1 ontBaseInfoTable
-- 2.4.1.2 ontVersionInfoTable
-- 2.4.1.3 ontCapabilityTable
-- 2.4.1.4 ontOpticalInfoTable
-- 2.4.1.5 ontProfileInfoTable
-- 2.4.1.6 ontUpgradeStatusTable
-- 2.4.1.7 ontStatisticsTable
-- 2.4.1.8 ontUtilizationTable
-- 2.4.1.9 ontOpticalSwTable
-- 2.4.1.10 ontMacAddrTable

-- ont base status table ----------------------------------
ontBaseInfoTable    OBJECT-TYPE
        SYNTAX      SEQUENCE OF OntBaseInfoEntry
        MAX-ACCESS  not-accessible
        STATUS      current
        DESCRIPTION
            "ont base infomation table"
        ::= { ontInfo 1 }

ontBaseInfoEntry    OBJECT-TYPE
        SYNTAX      OntBaseInfoEntry
        MAX-ACCESS  not-accessible
        STATUS      current
        DESCRIPTION
            "entry of ont base infomation table"
        INDEX { soSlotIndex, soPportIndex, soOntIndex }
        ::= { ontBaseInfoTable 1 }

OntBaseInfoEntry  ::= 
        SEQUENCE 
        {
            soSlotIndex        INTEGER,
            soPportIndex       INTEGER,
            soOntIndex         INTEGER,
            ontDescription     OCTET STRING,
            ontDeviceType      OCTET STRING,
            ontRunStatus       INTEGER,
            ontDistance        OCTET STRING,
            ontSn              OCTET STRING,
            ontPw              OCTET STRING,
            ontLoid            OCTET STRING,
            ontLopw            OCTET STRING,
            ontOfflineReason   OCTET STRING,
            ontOnOfflineTime   OCTET STRING,
            ontUpDownTime      OCTET STRING
        }

soSlotIndex     OBJECT-TYPE    
    SYNTAX      INTEGER(0..5)
    MAX-ACCESS  read-only
    STATUS      current
    DESCRIPTION
        "The index of slot, should in <0-5>."
    ::= { ontBaseInfoEntry 1 }

soPportIndex    OBJECT-TYPE    
    SYNTAX      INTEGER(1..16)
    MAX-ACCESS  read-only
    STATUS      current
    DESCRIPTION
        "The index of pon port, should in <1-16>."
    ::= { ontBaseInfoEntry 2 }

soOntIndex      OBJECT-TYPE    
    SYNTAX      INTEGER(1..128)
    MAX-ACCESS  read-only
    STATUS      current
    DESCRIPTION
        "The index of ont, the 3rd index of this table.
         Should in <1-128>."
    ::= { ontBaseInfoEntry 3 }

ontDescription  OBJECT-TYPE
    SYNTAX      OCTET STRING (SIZE(0..255))
    MAX-ACCESS  read-only
    STATUS      current
    DESCRIPTION
        "ont description."
    ::= { ontBaseInfoEntry 4 }    

ontDeviceType   OBJECT-TYPE
    SYNTAX      OCTET STRING (SIZE(0..255))
    MAX-ACCESS  read-only
    STATUS      current
    DESCRIPTION
        "ont device type."
    ::= { ontBaseInfoEntry 5 }    

ontRunStatus    OBJECT-TYPE
    SYNTAX      INTEGER(0..1)
    MAX-ACCESS  read-only
    STATUS      current
    DESCRIPTION
        "ontRunStatus:
         0  offline
         1  online"
    ::= { ontBaseInfoEntry 6 }    

ontDistance     OBJECT-TYPE
    SYNTAX      OCTET STRING (SIZE(0..255))
    MAX-ACCESS  read-only
    STATUS      current
    DESCRIPTION
        "ont distance."
    ::= { ontBaseInfoEntry 7 }    

ontSn           OBJECT-TYPE
    SYNTAX      OCTET STRING (SIZE(0..255))
    MAX-ACCESS  read-only
    STATUS      current
    DESCRIPTION
        "ont serial number, hex string format."
    ::= { ontBaseInfoEntry 8 }    

ontPw           OBJECT-TYPE
    SYNTAX      OCTET STRING (SIZE(0..255))
    MAX-ACCESS  read-only
    STATUS      current
    DESCRIPTION
        "ont password, hex string format."
    ::= { ontBaseInfoEntry 9 }    

ontLoid         OBJECT-TYPE
    SYNTAX      OCTET STRING (SIZE(0..255))
    MAX-ACCESS  read-only
    STATUS      current
    DESCRIPTION
        "logical ont id, Charactor format."
    ::= { ontBaseInfoEntry 10 }    

ontLopw         OBJECT-TYPE
    SYNTAX      OCTET STRING (SIZE(0..255))
    MAX-ACCESS  read-only
    STATUS      current
    DESCRIPTION
        "logical ont password, Charactor format."
    ::= { ontBaseInfoEntry 11 }    

ontOfflineReason  OBJECT-TYPE
    SYNTAX      OCTET STRING (SIZE(0..255))
    MAX-ACCESS  read-only
    STATUS      current
    DESCRIPTION
		"ont off line reason. 
		0:	NONE                    Reason get fail                     原因获取失败
		1:	DEACTIVATION            ONT DEACTIVED                       ONT去激活
		2:	ACK_TIMEOUT             ONT acknowledge time out            ONT确认响应超时
		3:	SFI                     Signal fail of ONT                  ONT信号失效
		4:	TIWI                    Transmission interface warning      ONT传输端口警示
		5:	PASSWORD_AUTHENTICATION ONT password authentication fail    ONT密码认证失败
		6:	LOSI                    Loss of signal for ONT              ONT上行信号丢失
		7:	LOS                     Loss of signal for OLT              OLT上行信号丢失
		8:	LOKI                    Loss of key synch with ONT          ONT同步密钥丢失
		9:	RERANGE_FAILURE         ONT re-ranging fail                 ONT重测距失败
		10:	LOFI                    Loss of frame of ONT                ONT上行帧丢失
		11:	POWER_OFF               ONT power off                       ONT掉电
		12:	UNKNOWN                 UNKNOWN                             未知   
		13:	LOAMI                   Loss of PLOAM for ONT               ONT上行PLOAM丢失
		"
    ::= { ontBaseInfoEntry 12 }    

ontOnOfflineTime   OBJECT-TYPE
    SYNTAX      OCTET STRING (SIZE(0..255))
    MAX-ACCESS  read-only
    STATUS      current
    DESCRIPTION
        "ont on/off line time."
    ::= { ontBaseInfoEntry 13 }    

ontUpDownTime   OBJECT-TYPE
    SYNTAX      OCTET STRING (SIZE(0..255))
    MAX-ACCESS  read-only
    STATUS      current
    DESCRIPTION
        "ont up/down time."
    ::= { ontBaseInfoEntry 14 }    

-- ont version info table ----------------------------------
ontVersionInfoTable OBJECT-TYPE
        SYNTAX      SEQUENCE OF OntVersionInfoEntry
        MAX-ACCESS  not-accessible
        STATUS      current
        DESCRIPTION
            "ont version info table"
        ::= { ontInfo 2 }

ontVersionInfoEntry OBJECT-TYPE
        SYNTAX      OntVersionInfoEntry
        MAX-ACCESS  not-accessible
        STATUS      current
        DESCRIPTION
            "entry of ont version info table"
        INDEX { soSlotIndexI, soPportIndexI, soOntIndexI }
        ::= { ontVersionInfoTable 1 }

OntVersionInfoEntry  ::= 
        SEQUENCE 
        {
            soSlotIndexI         INTEGER,
            soPportIndexI        INTEGER,
            soOntIndexI          INTEGER,
            ontVendorId          OCTET STRING,
            ontVersion           OCTET STRING,
            ontEquipmentId       OCTET STRING,
            ontMainSwVersion     OCTET STRING,
            ontSecondSwVersion   OCTET STRING
        }

soSlotIndexI    OBJECT-TYPE    
    SYNTAX      INTEGER(0..5)
    MAX-ACCESS  read-only
    STATUS      current
    DESCRIPTION
        "The index of slot, should in <0-5>."
    ::= { ontVersionInfoEntry 1 }

soPportIndexI   OBJECT-TYPE    
    SYNTAX      INTEGER(1..16)
    MAX-ACCESS  read-only
    STATUS      current
    DESCRIPTION
        "The index of pon port, should in <1-16>."
    ::= { ontVersionInfoEntry 2 }

soOntIndexI     OBJECT-TYPE    
    SYNTAX      INTEGER(1..128)
    MAX-ACCESS  read-only
    STATUS      current
    DESCRIPTION
        "The index of ont, the 3rd index of this table.
         Should in <1-128>."
    ::= { ontVersionInfoEntry 3 }

ontVendorId     OBJECT-TYPE
    SYNTAX      OCTET STRING (SIZE(0..255))
    MAX-ACCESS  read-only
    STATUS      current
    DESCRIPTION
        "ont vendor id."
    ::= { ontVersionInfoEntry 4 }    

ontVersion      OBJECT-TYPE
    SYNTAX      OCTET STRING (SIZE(0..255))
    MAX-ACCESS  read-only
    STATUS      current
    DESCRIPTION
        "ont version."
    ::= { ontVersionInfoEntry 5 }    

ontEquipmentId  OBJECT-TYPE
    SYNTAX      OCTET STRING (SIZE(0..255))
    MAX-ACCESS  read-only
    STATUS      current
    DESCRIPTION
        "ont equipment id."
    ::= { ontVersionInfoEntry 6 }    

ontMainSwVersion OBJECT-TYPE
    SYNTAX       OCTET STRING (SIZE(0..255))
    MAX-ACCESS   read-only
    STATUS       current
    DESCRIPTION
        "ont primary software version."
    ::= { ontVersionInfoEntry 7 }    

ontSecondSwVersion OBJECT-TYPE
    SYNTAX         OCTET STRING (SIZE(0..255))
    MAX-ACCESS     read-only
    STATUS         current
    DESCRIPTION
        "ont secondary software version."
    ::= { ontVersionInfoEntry 8 }    

-- ont capability info table ------------------------------
ontCapabilityTable  OBJECT-TYPE
        SYNTAX      SEQUENCE OF OntCapabilityEntry
        MAX-ACCESS  not-accessible
        STATUS      current
        DESCRIPTION
            "ont capability info table."
        ::= { ontInfo 3 }

ontCapabilityEntry OBJECT-TYPE
        SYNTAX      OntCapabilityEntry
        MAX-ACCESS  not-accessible
        STATUS      current
        DESCRIPTION
            "entry of ont capability info table"
        INDEX { soSlotIndexII, soPportIndexII, soOntIndexII }
        ::= { ontCapabilityTable 1 }

OntCapabilityEntry  ::= 
        SEQUENCE 
        {
            soSlotIndexII           INTEGER,
            soPportIndexII          INTEGER,
            soOntIndexII            INTEGER,
            ontCapEquipId           OCTET STRING,
            ontUplinkPonPortsNum    INTEGER,
            ontPotsPortsNum         INTEGER,
            ontEthPortsNum          INTEGER,
            ontTdmPortsNum          INTEGER,
            ontMocaPortsNum         INTEGER,
            ontCatvAniPortsNum      INTEGER,
            ontCatvUniPortsNum      INTEGER,
            ontTcontsNum            INTEGER,
            ontGemPortsNum          INTEGER,
            ontTrafficSchedulersNum INTEGER,
            ontPqsInTconts          OCTET STRING,
            ontIpConfigSupport      OCTET STRING,
            ontFlowCtrlType         OCTET STRING,
            ontTXpowerCutOffSupport OCTET STRING,
            ontDbaMethod            OCTET STRING
        }

soSlotIndexII   OBJECT-TYPE    
    SYNTAX      INTEGER(0..5)
    MAX-ACCESS  read-only
    STATUS      current
    DESCRIPTION
        "The index of slot, should in <0-5>."
    ::= { ontCapabilityEntry 1 }

soPportIndexII  OBJECT-TYPE    
    SYNTAX      INTEGER(1..16)
    MAX-ACCESS  read-only
    STATUS      current
    DESCRIPTION
        "The index of pon port, should in <1-16>."
    ::= { ontCapabilityEntry 2 }

soOntIndexII    OBJECT-TYPE    
    SYNTAX      INTEGER(1..128)
    MAX-ACCESS  read-only
    STATUS      current
    DESCRIPTION
        "The index of ont, the 3rd index of this table.
         Should in <1-128>."
    ::= { ontCapabilityEntry 3 }

ontCapEquipId   OBJECT-TYPE
    SYNTAX      OCTET STRING (SIZE(0..255))
    MAX-ACCESS  read-only
    STATUS      current
    DESCRIPTION
        "ont equipment id."
    ::= { ontCapabilityEntry 4 }    

ontUplinkPonPortsNum OBJECT-TYPE
    SYNTAX           INTEGER(1..8)
    MAX-ACCESS       read-only
    STATUS           current
    DESCRIPTION
        "number of uplink PON ports."
    ::= { ontCapabilityEntry 5 }    

ontPotsPortsNum OBJECT-TYPE
    SYNTAX      INTEGER(1..8)
    MAX-ACCESS  read-only
    STATUS      current
    DESCRIPTION
        "number of POTS ports."
    ::= { ontCapabilityEntry 6 }    

ontEthPortsNum  OBJECT-TYPE
    SYNTAX      INTEGER(1..8)
    MAX-ACCESS  read-only
    STATUS      current
    DESCRIPTION
        "number of ETH ports."
    ::= { ontCapabilityEntry 7 }    

ontTdmPortsNum  OBJECT-TYPE
    SYNTAX      INTEGER(1..8)
    MAX-ACCESS  read-only
    STATUS      current
    DESCRIPTION
        "number of TDM ports."
    ::= { ontCapabilityEntry 8 }    

ontMocaPortsNum OBJECT-TYPE
    SYNTAX      INTEGER(1..8)
    MAX-ACCESS  read-only
    STATUS      current
    DESCRIPTION
        "number of MOCA ports."
    ::= { ontCapabilityEntry 9 }    

ontCatvAniPortsNum OBJECT-TYPE
    SYNTAX         INTEGER(1..8)
    MAX-ACCESS     read-only
    STATUS         current
    DESCRIPTION
        "number of CATV ANI ports."
    ::= { ontCapabilityEntry 10 }    

ontCatvUniPortsNum OBJECT-TYPE
    SYNTAX         INTEGER(1..8)
    MAX-ACCESS     read-only
    STATUS         current
    DESCRIPTION
        "number of CATV UNI ports."
    ::= { ontCapabilityEntry 11 }    

ontTcontsNum    OBJECT-TYPE
    SYNTAX      INTEGER(1..8)
    MAX-ACCESS  read-only
    STATUS      current
    DESCRIPTION
        "number of T-CONTs."
    ::= { ontCapabilityEntry 12 }    

ontGemPortsNum  OBJECT-TYPE
    SYNTAX      INTEGER(1..8)
    MAX-ACCESS  read-only
    STATUS      current
    DESCRIPTION
        "number of GEM ports."
    ::= { ontCapabilityEntry 13 }    

ontTrafficSchedulersNum OBJECT-TYPE
    SYNTAX              INTEGER(1..8)
    MAX-ACCESS          read-only
    STATUS              current
    DESCRIPTION
        "number of traffic schedulers."
    ::= { ontCapabilityEntry 14 }    

ontPqsInTconts     OBJECT-TYPE
    SYNTAX         OCTET STRING (SIZE(0..255))
    MAX-ACCESS     read-only
    STATUS         current
    DESCRIPTION
        "ont support ip configuration or not."
    ::= { ontCapabilityEntry 15 }    

ontIpConfigSupport OBJECT-TYPE
    SYNTAX         OCTET STRING (SIZE(0..255))
    MAX-ACCESS     read-only
    STATUS         current
    DESCRIPTION
        "ont support ip configuration or not."
    ::= { ontCapabilityEntry 16 }    


ontFlowCtrlType OBJECT-TYPE
    SYNTAX      OCTET STRING (SIZE(0..255))
    MAX-ACCESS  read-only
    STATUS      current
    DESCRIPTION
        "ont flow control type."
    ::= { ontCapabilityEntry 17 }    

ontTXpowerCutOffSupport OBJECT-TYPE
    SYNTAX              OCTET STRING (SIZE(0..255))
    MAX-ACCESS          read-only
    STATUS              current
    DESCRIPTION
        "ont support TX power cut off or not."
    ::= { ontCapabilityEntry 18 }    

ontDbaMethod OBJECT-TYPE
    SYNTAX              OCTET STRING (SIZE(0..255))
    MAX-ACCESS          read-only
    STATUS              current
    DESCRIPTION
        "ont dba method.
        NSR(default): not support SR
        SR: support SR
        -: invalid"
    ::= { ontCapabilityEntry 19 }  
    
-- ont optical info table ----------------------------------
ontOpticalInfoTable OBJECT-TYPE
        SYNTAX      SEQUENCE OF OntOpticalInfoEntry
        MAX-ACCESS  not-accessible
        STATUS      current
        DESCRIPTION
            "ont optical info table"
        ::= { ontInfo 4 }

ontOpticalInfoEntry OBJECT-TYPE
        SYNTAX      OntOpticalInfoEntry
        MAX-ACCESS  not-accessible
        STATUS      current
        DESCRIPTION
            "entry of ont optical info table"
        INDEX { soSlotIndexIII, soPportIndexIII, soOntIndexIII }
        ::= { ontOpticalInfoTable 1 }

OntOpticalInfoEntry  ::= 
        SEQUENCE 
        {
            soSlotIndexIII   INTEGER,
            soPportIndexIII  INTEGER,
            soOntIndexIII    INTEGER,
            ontVoltage       OCTET STRING,
            ontRXPower       OCTET STRING,
            ontTXPower       OCTET STRING,
            ontBiasCurrent   OCTET STRING,
            ontTemperature   OCTET STRING,
            ontRxCatvPower   OCTET STRING,
            ontTxCatvPower   OCTET STRING,
            ontOltRxPower    OCTET STRING,
            ontOltTxPower    OCTET STRING
        }

soSlotIndexIII  OBJECT-TYPE    
    SYNTAX      INTEGER(0..5)
    MAX-ACCESS  read-only
    STATUS      current
    DESCRIPTION
        "The index of slot, should in <0-5>."
    ::= { ontOpticalInfoEntry 1 }

soPportIndexIII OBJECT-TYPE    
    SYNTAX      INTEGER(1..16)
    MAX-ACCESS  read-only
    STATUS      current
    DESCRIPTION
        "The index of pon port, should in <1-16>."
    ::= { ontOpticalInfoEntry 2 }

soOntIndexIII   OBJECT-TYPE    
    SYNTAX      INTEGER(1..128)
    MAX-ACCESS  read-only
    STATUS      current
    DESCRIPTION
        "The index of ont, the 3rd index of this table.
         Should in <1-128>."
    ::= { ontOpticalInfoEntry 3 }

ontVoltage      OBJECT-TYPE
    SYNTAX      OCTET STRING (SIZE(0..255))
    MAX-ACCESS  read-only
    STATUS      current
    DESCRIPTION
        "ont power feed voltage(V)."
    ::= { ontOpticalInfoEntry 4 }    

ontRXPower      OBJECT-TYPE
    SYNTAX      OCTET STRING (SIZE(0..255))
    MAX-ACCESS  read-only
    STATUS      current
    DESCRIPTION
        "ont received optical power(dBm)."
    ::= { ontOpticalInfoEntry 5 }    

ontTXPower      OBJECT-TYPE
    SYNTAX      OCTET STRING (SIZE(0..255))
    MAX-ACCESS  read-only
    STATUS      current
    DESCRIPTION
        "ont mean optical launch power(dBm)."
    ::= { ontOpticalInfoEntry 6 }    

ontBiasCurrent  OBJECT-TYPE
    SYNTAX      OCTET STRING (SIZE(0..255))
    MAX-ACCESS  read-only
    STATUS      current
    DESCRIPTION
        "ont laser bias current(uA)."
    ::= { ontOpticalInfoEntry 7 }    

ontTemperature  OBJECT-TYPE
    SYNTAX      OCTET STRING (SIZE(0..255))
    MAX-ACCESS  read-only
    STATUS      current
    DESCRIPTION
        "ont temperature(°C)."
    ::= { ontOpticalInfoEntry 8 }

ontRxCatvPower  OBJECT-TYPE
    SYNTAX      OCTET STRING (SIZE(0..255))
    MAX-ACCESS  read-only
    STATUS      current
    DESCRIPTION
        "ont received catv power(dBm)."
    ::= { ontOpticalInfoEntry 9 }

ontTxCatvPower  OBJECT-TYPE
    SYNTAX      OCTET STRING (SIZE(0..255))
    MAX-ACCESS  read-only
    STATUS      current
    DESCRIPTION
        "ont transmitted catv power(dBmV)."
    ::= { ontOpticalInfoEntry 10 }

ontOltRxPower   OBJECT-TYPE
    SYNTAX      OCTET STRING (SIZE(0..255))
    MAX-ACCESS  read-only
    STATUS      current
    DESCRIPTION
        "olt received ont power(dBm)."
    ::= { ontOpticalInfoEntry 11 }

ontOltTxPower   OBJECT-TYPE
    SYNTAX      OCTET STRING (SIZE(0..255))
    MAX-ACCESS  read-only
    STATUS      current
    DESCRIPTION
        "olt transmitted power(dBm)."
    ::= { ontOpticalInfoEntry 12 }

-- ont profile info table ----------------------------------
ontProfileInfoTable OBJECT-TYPE
        SYNTAX      SEQUENCE OF OntProfileInfoEntry
        MAX-ACCESS  not-accessible
        STATUS      current
        DESCRIPTION
            "ont optical info table"
        ::= { ontInfo 5 }

ontProfileInfoEntry OBJECT-TYPE
        SYNTAX      OntProfileInfoEntry
        MAX-ACCESS  not-accessible
        STATUS      current
        DESCRIPTION
            "entry of ont profile info table"
        INDEX { soSlotIndexIV, soPportIndexIV, soOntIndexIV }
        ::= { ontProfileInfoTable 1 }

OntProfileInfoEntry  ::= 
        SEQUENCE 
        {
            soSlotIndexIV        INTEGER,
            soPportIndexIV       INTEGER,
            soOntIndexIV         INTEGER,
            ontProfileSn         OCTET STRING,
            ontProfileVlanIdxes  OCTET STRING,
            ontProfileVlanNames  OCTET STRING,
            ontProfileUsIdxes    OCTET STRING,
            ontProfileUsNames    OCTET STRING,
            ontProfileDsIdxes    OCTET STRING,
            ontProfileDsNames    OCTET STRING,
            ontProfileDbaIdxes   OCTET STRING,
            ontProfileDbaNames   OCTET STRING,
            ontProfileLineIdx    INTEGER,
            ontProfileLineName   OCTET STRING,
            ontProfileRuleIdx    INTEGER,
            ontProfileRuleName   OCTET STRING,
            ontProfileUniqueIdx  OCTET STRING,
            ontProfileUniqueName OCTET STRING
        }

soSlotIndexIV   OBJECT-TYPE    
    SYNTAX      INTEGER(0..5)
    MAX-ACCESS  read-only
    STATUS      current
    DESCRIPTION
        "The index of slot, should in <0-5>."
    ::= { ontProfileInfoEntry 1 }

soPportIndexIV  OBJECT-TYPE    
    SYNTAX      INTEGER(1..16)
    MAX-ACCESS  read-only
    STATUS      current
    DESCRIPTION
        "The index of pon port, should in <1-16>."
    ::= { ontProfileInfoEntry 2 }

soOntIndexIV    OBJECT-TYPE    
    SYNTAX      INTEGER(1..128)
    MAX-ACCESS  read-only
    STATUS      current
    DESCRIPTION
        "The index of ont, the 3rd index of this table.
         Should in <1-128>."
    ::= { ontProfileInfoEntry 3 }

ontProfileSn    OBJECT-TYPE
    SYNTAX      OCTET STRING (SIZE(0..255))
    MAX-ACCESS  read-only
    STATUS      current
    DESCRIPTION
        "ont sn"
    ::= { ontProfileInfoEntry 4 }    

ontProfileVlanIdxes  OBJECT-TYPE
    SYNTAX      OCTET STRING (SIZE(0..255))
    MAX-ACCESS  read-only
    STATUS      current
    DESCRIPTION
        "vlan indexes ont used, such as '100,200,233'. if no vlan used, '-'."
    ::= { ontProfileInfoEntry 5 }    

ontProfileVlanNames  OBJECT-TYPE
    SYNTAX      OCTET STRING (SIZE(0..255))
    MAX-ACCESS  read-only
    STATUS      current
    DESCRIPTION
        "vlan names ont used, such as 'INDEX_100,INDEX_200,INDEX_233'. if no vlan used, '-'.
        Name list may too long to show. Suggest use ontProfileVlanIdxes above."
        -- 每个 name 的最大长度是 127，如果配的很长，而且使用了多个条目，就有可能超过 255 个
        -- 字节。此时返回值会截取到少于 255 字节（但不截掉最后一个逗号','，以表示还有没返回的）
    ::= { ontProfileInfoEntry 6 }    

ontProfileUsIdxes  OBJECT-TYPE
    SYNTAX      OCTET STRING (SIZE(0..255))
    MAX-ACCESS  read-only
    STATUS      current
    DESCRIPTION
        "us traffic indexes ont used, such as '100,200,233'. if no us traffic used, '-'."
    ::= { ontProfileInfoEntry 7 }    

ontProfileUsNames  OBJECT-TYPE
    SYNTAX      OCTET STRING (SIZE(0..255))
    MAX-ACCESS  read-only
    STATUS      current
    DESCRIPTION
        "us traffic names ont used, such as 'INDEX_100,INDEX_200,INDEX_233'. if no us used, '-'.
        Name list may too long to show. Suggest use ontProfileVlanIdxes above."
        -- 每个 name 的最大长度是 127，如果配的很长，而且使用了多个条目，就有可能超过 255 个
        -- 字节。此时返回值会截取到少于 255 字节（但不截掉最后一个逗号','，以表示还有没返回的）
    ::= { ontProfileInfoEntry 8 }    

ontProfileDsIdxes  OBJECT-TYPE
    SYNTAX      OCTET STRING (SIZE(0..255))
    MAX-ACCESS  read-only
    STATUS      current
    DESCRIPTION
        "ds traffic indexes ont used, such as '100,200,233'. if no ds traffic used, '-'."
    ::= { ontProfileInfoEntry 9 }    

ontProfileDsNames  OBJECT-TYPE
    SYNTAX      OCTET STRING (SIZE(0..255))
    MAX-ACCESS  read-only
    STATUS      current
    DESCRIPTION
        "ds traffic names ont used, such as 'INDEX_100,INDEX_200,INDEX_233'. if no ds used, '-'.
        Name list may too long to show. Suggest use ontProfileVlanIdxes above."
        -- 每个 name 的最大长度是 127，如果配的很长，而且使用了多个条目，就有可能超过 255 个
        -- 字节。此时返回值会截取到少于 255 字节（但不截掉最后一个逗号','，以表示还有没返回的）
    ::= { ontProfileInfoEntry 10 }    

ontProfileDbaIdxes  OBJECT-TYPE
    SYNTAX      OCTET STRING (SIZE(0..255))
    MAX-ACCESS  read-only
    STATUS      current
    DESCRIPTION
        "dba indexes ont used, such as '100,200,233'. if no dba used, '-'."
    ::= { ontProfileInfoEntry 11 }    

ontProfileDbaNames  OBJECT-TYPE
    SYNTAX      OCTET STRING (SIZE(0..255))
    MAX-ACCESS  read-only
    STATUS      current
    DESCRIPTION
        "dba names ont used, such as 'INDEX_100,INDEX_200,INDEX_233'. if no dba used, '-'.
        Name list may too long to show. Suggest use ontProfileVlanIdxes above."
        -- 每个 name 的最大长度是 127，如果配的很长，而且使用了多个条目，就有可能超过 255 个
        -- 字节。此时返回值会截取到少于 255 字节（但不截掉最后一个逗号','，以表示还有没返回的）
    ::= { ontProfileInfoEntry 12 }    

ontProfileLineIdx  OBJECT-TYPE
    SYNTAX      INTEGER(1..4096)
    MAX-ACCESS  read-only
    STATUS      current
    DESCRIPTION
        "line id ont used."
    ::= { ontProfileInfoEntry 13 }    

ontProfileLineName  OBJECT-TYPE
    SYNTAX      OCTET STRING (SIZE(0..255))
    MAX-ACCESS  read-only
    STATUS      current
    DESCRIPTION
        "line name ont used."
    ::= { ontProfileInfoEntry 14 }    

ontProfileRuleIdx  OBJECT-TYPE
    SYNTAX      INTEGER(1..4096)
    MAX-ACCESS  read-only
    STATUS      current
    DESCRIPTION
        "rule id ont used."
    ::= { ontProfileInfoEntry 15 }    

ontProfileRuleName  OBJECT-TYPE
    SYNTAX      OCTET STRING (SIZE(0..255))
    MAX-ACCESS  read-only
    STATUS      current
    DESCRIPTION
        "rule name ont used."
    ::= { ontProfileInfoEntry 16 }    

ontProfileUniqueIdx OBJECT-TYPE
    SYNTAX      OCTET STRING (SIZE(0..255))
    MAX-ACCESS  read-only
    STATUS      current
    DESCRIPTION
        "unique id ont used. if no unique used, '-'"
    ::= { ontProfileInfoEntry 17 }    

ontProfileUniqueName OBJECT-TYPE
    SYNTAX      OCTET STRING (SIZE(0..255))
    MAX-ACCESS  read-only
    STATUS      current
    DESCRIPTION
        "unique name ont used. if no unique used, '-'"
    ::= { ontProfileInfoEntry 18 }    

-- ont upgrade status table --------------------------------
ontUpgradeStatusTable OBJECT-TYPE
        SYNTAX      SEQUENCE OF OntUpgradeStatusEntry
        MAX-ACCESS  not-accessible
        STATUS      current
        DESCRIPTION
            "ont upgrade status table"
        ::= { ontInfo 6 }

ontUpgradeStatusEntry OBJECT-TYPE
        SYNTAX      OntUpgradeStatusEntry
        MAX-ACCESS  not-accessible
        STATUS      current
        DESCRIPTION
            "entry of ont upgrade status table"
        INDEX { soSlotIndexV, soPportIndexV, soOntIndexV }
        ::= { ontUpgradeStatusTable 1 }

OntUpgradeStatusEntry  ::= 
        SEQUENCE 
        {
            soSlotIndexV          INTEGER,
            soPportIndexV         INTEGER,
            soOntIndexV           INTEGER,
            ontUpgradeActiveVer   OCTET STRING,
            ontUpgradeInactiveVer OCTET STRING,
            ontUpgradeStatus      OCTET STRING
        }

soSlotIndexV    OBJECT-TYPE    
    SYNTAX      INTEGER(0..5)
    MAX-ACCESS  read-only
    STATUS      current
    DESCRIPTION
        "The index of slot, should in <0-5>."
    ::= { ontUpgradeStatusEntry 1 }

soPportIndexV   OBJECT-TYPE    
    SYNTAX      INTEGER(1..16)
    MAX-ACCESS  read-only
    STATUS      current
    DESCRIPTION
        "The index of pon port, should in <1-16>."
    ::= { ontUpgradeStatusEntry 2 }

soOntIndexV     OBJECT-TYPE    
    SYNTAX      INTEGER(1..128)
    MAX-ACCESS  read-only
    STATUS      current
    DESCRIPTION
        "The index of ont, the 3rd index of this table.
         Should in <1-128>."
    ::= { ontUpgradeStatusEntry 3 }

ontUpgradeActiveVer OBJECT-TYPE
    SYNTAX      OCTET STRING (SIZE(0..255))
    MAX-ACCESS  read-only
    STATUS      current
    DESCRIPTION
        "ont upgrade active version."
    ::= { ontUpgradeStatusEntry 4 }    

ontUpgradeInactiveVer OBJECT-TYPE
    SYNTAX      OCTET STRING (SIZE(0..255))
    MAX-ACCESS  read-only
    STATUS      current
    DESCRIPTION
        "ont upgrade inactive version."
    ::= { ontUpgradeStatusEntry 5 }    

ontUpgradeStatus OBJECT-TYPE
    SYNTAX      OCTET STRING (SIZE(0..255))
    MAX-ACCESS  read-only
    STATUS      current
    DESCRIPTION
        "ont upgrade status, such as success, crc error, timeout, offline, 0%-100%."
    ::= { ontUpgradeStatusEntry 6 }    

-- ont statistics table ------------------------------------
ontStatisticsTable OBJECT-TYPE
        SYNTAX      SEQUENCE OF OntStatisticsEntry
        MAX-ACCESS  not-accessible
        STATUS      current
        DESCRIPTION
            "ont statistics table"
        ::= { ontInfo 7 }

ontStatisticsEntry  OBJECT-TYPE
        SYNTAX      OntStatisticsEntry
        MAX-ACCESS  not-accessible
        STATUS      current
        DESCRIPTION
            "entry of ont statistics table"
        INDEX { soSlotIndexX, soPportIndexX, soOntIndexX }
        ::= { ontStatisticsTable 1 }

OntStatisticsEntry  ::= 
        SEQUENCE 
        {
            soSlotIndexX          INTEGER,
            soPportIndexX         INTEGER,
            soOntIndexX           INTEGER,
            ontUsFrames           OCTET STRING,
            ontUsBytes            OCTET STRING,
            ontDsFrames           OCTET STRING,
            ontDsBytes            OCTET STRING,
            ontUsRate             OCTET STRING,
            ontDsRate             OCTET STRING
        }

soSlotIndexX    OBJECT-TYPE    
    SYNTAX      INTEGER(0..5)
    MAX-ACCESS  read-only
    STATUS      current
    DESCRIPTION
        "The index of slot, should in <0-5>."
    ::= { ontStatisticsEntry 1 }

soPportIndexX   OBJECT-TYPE    
    SYNTAX      INTEGER(1..16)
    MAX-ACCESS  read-only
    STATUS      current
    DESCRIPTION
        "The index of pon port, should in <1-16>."
    ::= { ontStatisticsEntry 2 }

soOntIndexX     OBJECT-TYPE    
    SYNTAX      INTEGER(1..128)
    MAX-ACCESS  read-only
    STATUS      current
    DESCRIPTION
        "The index of ont, the 3rd index of this table.
         Should in <1-128>."
    ::= { ontStatisticsEntry 3 }

ontUsFrames     OBJECT-TYPE
    SYNTAX      OCTET STRING (SIZE(0..255))
    MAX-ACCESS  read-only
    STATUS      current
    DESCRIPTION
        "ont upstream frames."
    ::= { ontStatisticsEntry 4 }    

ontUsBytes      OBJECT-TYPE
    SYNTAX      OCTET STRING (SIZE(0..255))
    MAX-ACCESS  read-only
    STATUS      current
    DESCRIPTION
        "ont upstream bytes."
    ::= { ontStatisticsEntry 5 }    

ontDsFrames     OBJECT-TYPE
    SYNTAX      OCTET STRING (SIZE(0..255))
    MAX-ACCESS  read-only
    STATUS      current
    DESCRIPTION
        "ont downstream frames."
    ::= { ontStatisticsEntry 6 }    

ontDsBytes      OBJECT-TYPE
    SYNTAX      OCTET STRING (SIZE(0..255))
    MAX-ACCESS  read-only
    STATUS      current
    DESCRIPTION
        "ont downstream bytes."
    ::= { ontStatisticsEntry 7 }    

ontUsRate       OBJECT-TYPE
    SYNTAX      OCTET STRING (SIZE(0..255))
    MAX-ACCESS  read-only
    STATUS      current
    DESCRIPTION
        "ont upstream rate."
    ::= { ontStatisticsEntry 8 }    

ontDsRate       OBJECT-TYPE
    SYNTAX      OCTET STRING (SIZE(0..255))
    MAX-ACCESS  read-only
    STATUS      current
    DESCRIPTION
        "ont downstream rate."
    ::= { ontStatisticsEntry 9 }    

-- ont utilization table ------------------------------------
ontUtilizationTable  OBJECT-TYPE
        SYNTAX      SEQUENCE OF OntUtilizationEntry
        MAX-ACCESS  not-accessible
        STATUS      current
        DESCRIPTION
            "ont utilization table"
        ::= { ontInfo 8 }

ontUtilizationEntry    OBJECT-TYPE
        SYNTAX      OntUtilizationEntry
        MAX-ACCESS  not-accessible
        STATUS      current
        DESCRIPTION
            "entry of ont utilization table"
        INDEX { soSlotIndexXII, soPportIndexXII, soOntIndexXII }
        ::= { ontUtilizationTable 1 }

OntUtilizationEntry  ::= 
        SEQUENCE 
        {
            soSlotIndexXII            INTEGER,
            soPportIndexXII           INTEGER,
            soOntIndexXII             INTEGER,
            soUtilizeTxOctetsRate     INTEGER,
            soUtilizeRxOctetsRate     INTEGER,
            soUtilizeTxPktsRate       INTEGER,
            soUtilizeRxPktsRate       INTEGER,
            soUtilizeTxOctets         INTEGER,
            soUtilizeRxOctets         INTEGER,
            soUtilizeTxPktsError      INTEGER,
            soUtilizeRxPktsError      INTEGER,
            soUtilizeTxPktsDiscard    INTEGER,
            soUtilizeRxPktsDiscard    INTEGER,
            soUtilizeTxThroughput     INTEGER,
            soUtilizeRxThroughput     INTEGER
        }

soSlotIndexXII  OBJECT-TYPE    
    SYNTAX      INTEGER(0..5)
    MAX-ACCESS  read-only
    STATUS      current
    DESCRIPTION
        "The index of slot, should in <0-5>."
    ::= { ontUtilizationEntry 1 }

soPportIndexXII OBJECT-TYPE    
    SYNTAX      INTEGER(1..16)
    MAX-ACCESS  read-only
    STATUS      current
    DESCRIPTION
        "The index of pon port, should in <1-16>."
    ::= { ontUtilizationEntry 2 }

soOntIndexXII   OBJECT-TYPE    
    SYNTAX      INTEGER(1..128)
    MAX-ACCESS  read-only
    STATUS      current
    DESCRIPTION
        "The index of ont, the 3rd index of this table.
         Should in <1-128>."
    ::= { ontUtilizationEntry 3 }

soUtilizeTxOctetsRate  OBJECT-TYPE    
    SYNTAX      INTEGER(0..10000)
    MAX-ACCESS  read-only
    STATUS      current
    DESCRIPTION
        "ont tx octets rate."
    ::= { ontUtilizationEntry 4 }

soUtilizeRxOctetsRate  OBJECT-TYPE    
    SYNTAX      INTEGER(0..10000)
    MAX-ACCESS  read-only
    STATUS      current
    DESCRIPTION
        "ont rx octets rate."
    ::= { ontUtilizationEntry 5 }

soUtilizeTxPktsRate  OBJECT-TYPE    
    SYNTAX      INTEGER(0..1600000000)
    MAX-ACCESS  read-only
    STATUS      current
    DESCRIPTION
        "ont tx packets rate(pps)."
    ::= { ontUtilizationEntry 6 }

soUtilizeRxPktsRate  OBJECT-TYPE    
    SYNTAX      INTEGER(0..1600000000)
    MAX-ACCESS  read-only
    STATUS      current
    DESCRIPTION
        "ont rx packets rate(pps)."
    ::= { ontUtilizationEntry 7 }

soUtilizeTxOctets  OBJECT-TYPE    
    SYNTAX      INTEGER(0..1600000000)
    MAX-ACCESS  read-only
    STATUS      current
    DESCRIPTION
        "ont tx octets in 15 minutes."
    ::= { ontUtilizationEntry 8 }

soUtilizeRxOctets  OBJECT-TYPE    
    SYNTAX      INTEGER(0..1600000000)
    MAX-ACCESS  read-only
    STATUS      current
    DESCRIPTION
        "ont rx octets in 15 minutes."
    ::= { ontUtilizationEntry 9 }

soUtilizeTxPktsError  OBJECT-TYPE    
    SYNTAX      INTEGER(0..10000)
    MAX-ACCESS  read-only
    STATUS      current
    DESCRIPTION
        "port tx packets error in 15 minute."
    ::= { ontUtilizationEntry 10 }

soUtilizeRxPktsError  OBJECT-TYPE    
    SYNTAX      INTEGER(0..10000)
    MAX-ACCESS  read-only
    STATUS      current
    DESCRIPTION
        "port rx packets error in 15 minute."
    ::= { ontUtilizationEntry 11 }

soUtilizeTxPktsDiscard  OBJECT-TYPE    
    SYNTAX      INTEGER(0..10000)
    MAX-ACCESS  read-only
    STATUS      current
    DESCRIPTION
        "port tx packets discard in 15 minute."
    ::= { ontUtilizationEntry 12 }

soUtilizeRxPktsDiscard  OBJECT-TYPE    
    SYNTAX      INTEGER(0..10000)
    MAX-ACCESS  read-only
    STATUS      current
    DESCRIPTION
        "port rx packets discard in 15 minute."
    ::= { ontUtilizationEntry 13 }

soUtilizeTxThroughput  OBJECT-TYPE    
    SYNTAX      INTEGER(0..100)
    MAX-ACCESS  read-only
    STATUS      current
    DESCRIPTION
        "port tx throughput."
    ::= { ontUtilizationEntry 14 }

soUtilizeRxThroughput  OBJECT-TYPE    
    SYNTAX      INTEGER(0..100)
    MAX-ACCESS  read-only
    STATUS      current
    DESCRIPTION
        "port rx throughput."
    ::= { ontUtilizationEntry 15 }

-- ont optical software table ----------------------------------
ontOpticalSwTable   OBJECT-TYPE
        SYNTAX      SEQUENCE OF OntOpticalSwEntry
        MAX-ACCESS  not-accessible
        STATUS      current
        DESCRIPTION
            "ont optical software table"
        ::= { ontInfo 9 }

ontOpticalSwEntry   OBJECT-TYPE
        SYNTAX      OntOpticalSwEntry
        MAX-ACCESS  not-accessible
        STATUS      current
        DESCRIPTION
            "entry of ont optical software table"
        INDEX { soSlotIndexXV, soPportIndexXV, soOntIndexXV }
        ::= { ontOpticalSwTable 1 }

OntOpticalSwEntry  ::= 
        SEQUENCE 
        {
            soSlotIndexXV     INTEGER,
            soPportIndexXV    INTEGER,
            soOntIndexXV      INTEGER,
            ontVoltageI       OCTET STRING,
            ontRXPowerI       OCTET STRING,
            ontTXPowerI       OCTET STRING,
            ontBiasCurrentI   OCTET STRING,
            ontTemperatureI   OCTET STRING,
            ontRxCatvPowerI   OCTET STRING,
            ontTxCatvPowerI   OCTET STRING
        }

soSlotIndexXV   OBJECT-TYPE    
    SYNTAX      INTEGER(0..5)
    MAX-ACCESS  read-only
    STATUS      current
    DESCRIPTION
        "The index of slot, should in <0-5>."
    ::= { ontOpticalSwEntry 1 }

soPportIndexXV  OBJECT-TYPE    
    SYNTAX      INTEGER(1..16)
    MAX-ACCESS  read-only
    STATUS      current
    DESCRIPTION
        "The index of pon port, should in <1-16>."
    ::= { ontOpticalSwEntry 2 }

soOntIndexXV    OBJECT-TYPE    
    SYNTAX      INTEGER(1..128)
    MAX-ACCESS  read-only
    STATUS      current
    DESCRIPTION
        "The index of ont, the 3rd index of this table.
         Should in <1-128>."
    ::= { ontOpticalSwEntry 3 }

ontVoltageI     OBJECT-TYPE
    SYNTAX      OCTET STRING (SIZE(0..255))
    MAX-ACCESS  read-only
    STATUS      current
    DESCRIPTION
        "ont power feed voltage(V)."
    ::= { ontOpticalSwEntry 4 }    

ontRXPowerI     OBJECT-TYPE
    SYNTAX      OCTET STRING (SIZE(0..255))
    MAX-ACCESS  read-only
    STATUS      current
    DESCRIPTION
        "ont received optical power(dBm)."
    ::= { ontOpticalSwEntry 5 }    

ontTXPowerI     OBJECT-TYPE
    SYNTAX      OCTET STRING (SIZE(0..255))
    MAX-ACCESS  read-only
    STATUS      current
    DESCRIPTION
        "ont mean optical launch power(dBm)."
    ::= { ontOpticalSwEntry 6 }    

ontBiasCurrentI OBJECT-TYPE
    SYNTAX      OCTET STRING (SIZE(0..255))
    MAX-ACCESS  read-only
    STATUS      current
    DESCRIPTION
        "ont laser bias current(uA)."
    ::= { ontOpticalSwEntry 7 }    

ontTemperatureI OBJECT-TYPE
    SYNTAX      OCTET STRING (SIZE(0..255))
    MAX-ACCESS  read-only
    STATUS      current
    DESCRIPTION
        "ont temperature(°C)."
    ::= { ontOpticalSwEntry 8 }

ontRxCatvPowerI OBJECT-TYPE
    SYNTAX      OCTET STRING (SIZE(0..255))
    MAX-ACCESS  read-only
    STATUS      current
    DESCRIPTION
        "ont received catv power(dBm)."
    ::= { ontOpticalSwEntry 9 }

ontTxCatvPowerI OBJECT-TYPE
    SYNTAX      OCTET STRING (SIZE(0..255))
    MAX-ACCESS  read-only
    STATUS      current
    DESCRIPTION
        "ont transmitted catv power(dBmV)."
    ::= { ontOpticalSwEntry 10 }

-- ont mac address table ----------------------------------
ontMacAddrTable   OBJECT-TYPE
        SYNTAX      SEQUENCE OF OntMacAddrEntry
        MAX-ACCESS  not-accessible
        STATUS      current
        DESCRIPTION
            "ont mac address table"
        ::= { ontInfo 10 }

ontMacAddrEntry   OBJECT-TYPE
        SYNTAX      OntMacAddrEntry
        MAX-ACCESS  not-accessible
        STATUS      current
        DESCRIPTION
            "entry of ont mac address table"
        INDEX { ontMacAddrVid,  ontMacAddress}
        ::= { ontMacAddrTable 1 }

OntMacAddrEntry  ::= 
        SEQUENCE 
        {
            ontMacAddrVid     INTEGER,
            ontMacAddress     MacAddress,
            ontMacAddrSlot    INTEGER,
            ontMacAddrPport   INTEGER,
            ontMacAddrOnt     INTEGER,
            ontMacAddrSn      OCTET STRING,
            ontMacAddrGemU    INTEGER,
            ontMacAddrGem     INTEGER
        }

ontMacAddrVid   OBJECT-TYPE    
    SYNTAX      INTEGER(1..4094)
    MAX-ACCESS  read-only
    STATUS      current
    DESCRIPTION
        "The vlan id index of ontMacAddrTable, should in <1-4094>."
    ::= { ontMacAddrEntry 1 }

ontMacAddress  OBJECT-TYPE    
    SYNTAX      MacAddress
    MAX-ACCESS  read-only
    STATUS      current
    DESCRIPTION
        "The mac address index of ontMacAddrTable."
    ::= { ontMacAddrEntry 2 }

ontMacAddrSlot    OBJECT-TYPE    
    SYNTAX      INTEGER(0..11)
    MAX-ACCESS  read-only
    STATUS      current
    DESCRIPTION
        "The slot of ontMacAddrEntry, should in <0-11>.
         Should in <1-128>."
    ::= { ontMacAddrEntry 3 }

ontMacAddrPport     OBJECT-TYPE
    SYNTAX      INTEGER (1..16)
    MAX-ACCESS  read-only
    STATUS      current
    DESCRIPTION
        "The pon port of ontMacAddrEntry, should in <1-16>"
    ::= { ontMacAddrEntry 4 }    

ontMacAddrOnt     OBJECT-TYPE
    SYNTAX      INTEGER (1..128)
    MAX-ACCESS  read-only
    STATUS      current
    DESCRIPTION
        "The ont id of ontMacAddrEntry, should in <1-128>"
    ::= { ontMacAddrEntry 5 }   

ontMacAddrSn     OBJECT-TYPE
    SYNTAX      OCTET STRING (SIZE(0..255))
    MAX-ACCESS  read-only
    STATUS      current
    DESCRIPTION
        "The ont sn of ontMacAddrEntry."
    ::= { ontMacAddrEntry 6 }

ontMacAddrGemU     OBJECT-TYPE
    SYNTAX      INTEGER (0..1024)
    MAX-ACCESS  read-only
    STATUS      current
    DESCRIPTION
        "The ont user gem of ontMacAddrEntry, should in <1-1024>
        0: none
        1-1024: valid"
    ::= { ontMacAddrEntry 7 }  

ontMacAddrGem     OBJECT-TYPE
    SYNTAX      INTEGER (0..4095)
    MAX-ACCESS  read-only
    STATUS      current
    DESCRIPTION
        "The ont gem of ontMacAddrEntry, should in <0-4095>"
    ::= { ontMacAddrEntry 8 }  


-- ont ethernet port infomation ----------------------------
ontEthPortInfo       OBJECT IDENTIFIER ::= { statusOnt 2 }

-- 2.4.2.1 ontEthportStateTable
-- 2.4.2.2 ontEthportStatisRecTable
-- 2.4.2.3 ontEthportStatisSentTable
-- 2.4.2.4 ontEthportUtilizationTable
    
-- ont ethport state table --------------------------------
ontEthportStateTable   OBJECT-TYPE
        SYNTAX       SEQUENCE OF OntEthportStateEntry
        MAX-ACCESS   not-accessible
        STATUS       current
        DESCRIPTION
            "ont ethport state table"
        ::= { ontEthPortInfo 1 }

ontEthportStateEntry   OBJECT-TYPE
        SYNTAX       OntEthportStateEntry
        MAX-ACCESS   not-accessible
        STATUS       current
        DESCRIPTION
            "entry of ont ethport state table"
        INDEX { soSlotIndexVI, soPportIndexVI, soOntIndexVI, soOntEthportIndex }
        ::= { ontEthportStateTable 1 }

OntEthportStateEntry  ::= 
        SEQUENCE 
        {
            soSlotIndexVI           INTEGER,
            soPportIndexVI          INTEGER,
            soOntIndexVI            INTEGER,
            soOntEthportIndex       INTEGER,
            ontEthportAdminStatus   OCTET STRING,
            ontEthportConnectState  OCTET STRING,
            ontEthportPortSpeed     OCTET STRING
        }

soSlotIndexVI   OBJECT-TYPE    
    SYNTAX      INTEGER(0..5)
    MAX-ACCESS  read-only
    STATUS      current
    DESCRIPTION
        "The index of slot, should in <0-5>."
    ::= { ontEthportStateEntry 1 }

soPportIndexVI  OBJECT-TYPE    
    SYNTAX      INTEGER(1..16)
    MAX-ACCESS  read-only
    STATUS      current
    DESCRIPTION
        "The index of pon port, should in <1-16>."
    ::= { ontEthportStateEntry 2 }

soOntIndexVI    OBJECT-TYPE    
    SYNTAX      INTEGER(1..128)
    MAX-ACCESS  read-only
    STATUS      current
    DESCRIPTION
        "The index of ont, the 3rd index of this table.
         Should in <1-128>."
    ::= { ontEthportStateEntry 3 }

soOntEthportIndex   OBJECT-TYPE    
    SYNTAX      INTEGER(1..8)
    MAX-ACCESS  read-only
    STATUS      current
    DESCRIPTION
        "The index of ont ethernet port, the 4th index of this table.
         range <1-n> is determined by ont type, the max n is 2.4."
    ::= { ontEthportStateEntry 4 }

ontEthportAdminStatus OBJECT-TYPE
    SYNTAX            OCTET STRING (SIZE(0..255))
    MAX-ACCESS        read-only
    STATUS            current
    DESCRIPTION
        "ont ethernet port admin status:
         0  enable
         1  disable."
    ::= { ontEthportStateEntry 5 }    

ontEthportConnectState OBJECT-TYPE
    SYNTAX           OCTET STRING (SIZE(0..255))
    MAX-ACCESS       read-only
    STATUS           current
    DESCRIPTION
        "ont ethernet port connect state."
    ::= { ontEthportStateEntry 6 }    

ontEthportPortSpeed  OBJECT-TYPE
    SYNTAX           OCTET STRING (SIZE(0..255))
    MAX-ACCESS       read-only
    STATUS           current
    DESCRIPTION
        "ont ethernet port speed."
        -- 1，2，3  分别是十兆百兆千兆全双工 
        -- 17,18,19 分别是十兆百兆千兆半双工
    ::= { ontEthportStateEntry 7 }    

-- ont etherport statistics receive table ----------------------    
ontEthportStatisRecTable    OBJECT-TYPE
        SYNTAX  SEQUENCE OF OntEthportStatisRecEntry
        MAX-ACCESS  not-accessible
        STATUS  current
        DESCRIPTION
            "ont etherport statistics receive table"
        ::= { ontEthPortInfo 2 }

ontEthportStatisRecEntry  OBJECT-TYPE
        SYNTAX     OntEthportStatisRecEntry
        MAX-ACCESS  not-accessible
        STATUS    current
        DESCRIPTION
            "entry of ont etherport statistics receive table"
        INDEX { soSlotIndexVII, soPportIndexVII, soOntIndexVII, soOntEthportIndexI }
        ::= { ontEthportStatisRecTable 1 }
  
OntEthportStatisRecEntry  ::=
        SEQUENCE
        {
            soSlotIndexVII                 INTEGER,
            soPportIndexVII                INTEGER,
            soOntIndexVII                  INTEGER,
            soOntEthportIndexI             INTEGER,
            ontEthportRecFrames            INTEGER,
            ontEthportRecUniFrames         INTEGER,
            ontEthportRecMulFrames         INTEGER,
            ontEthportRecBroFrames         INTEGER,
            ontEthportRec64Frames          INTEGER,
            ontEthportRec65Frames          INTEGER,
            ontEthportRec128Frames         INTEGER,
            ontEthportRec256Frames         INTEGER,
            ontEthportRec512Frames         INTEGER,
            ontEthportRec1024Frames        INTEGER,
            ontEthportRecUndFrames         INTEGER,
            ontEthportRecOveFrames         INTEGER,
            ontEthportRecFragments         INTEGER,
            ontEthportRecJabbers           INTEGER,
            ontEthportRecFcsFrames         INTEGER,
            ontEthportDisFrames            INTEGER,
            ontEthportRecAliFrames         INTEGER,
            ontEthportMacRecFrames         INTEGER,
            ontEthportPppFrames            INTEGER,
            ontEthportBufReceive           INTEGER,
            ontEthportRecBytes             INTEGER
        }

soSlotIndexVII  OBJECT-TYPE    
    SYNTAX      INTEGER(0..5)
    MAX-ACCESS  read-only
    STATUS      current
    DESCRIPTION
        "The index of slot, should in <0-5>."
    ::= { ontEthportStatisRecEntry 1 }

soPportIndexVII OBJECT-TYPE    
    SYNTAX      INTEGER(1..16)
    MAX-ACCESS  read-only
    STATUS      current
    DESCRIPTION
        "The index of pon port, should in <1-16>."
    ::= { ontEthportStatisRecEntry 2 }

soOntIndexVII   OBJECT-TYPE    
    SYNTAX      INTEGER(1..128)
    MAX-ACCESS  read-only
    STATUS      current
    DESCRIPTION
        "The index of ont, the 3rd index of this table.
         Should in <1-128>."
    ::= { ontEthportStatisRecEntry 3 }

soOntEthportIndexI   OBJECT-TYPE    
    SYNTAX      INTEGER(1..8)
    MAX-ACCESS  read-only
    STATUS      current
    DESCRIPTION
        "The index of ont ethernet port, the 4th index of this table.
         range <1-n> is determined by ont type, the max n is 2.4."
    ::= { ontEthportStatisRecEntry 4 }
  
ontEthportRecFrames OBJECT-TYPE
    SYNTAX        INTEGER (0..4294967295)
    MAX-ACCESS    read-only
    STATUS        current
    DESCRIPTION
        "Received frames"
    ::= { ontEthportStatisRecEntry 5 }

ontEthportRecUniFrames OBJECT-TYPE
    SYNTAX           INTEGER (0..4294967295)
    MAX-ACCESS       read-only
    STATUS           current
    DESCRIPTION
        "Received unicast frames"
    ::= { ontEthportStatisRecEntry 6 }

ontEthportRecMulFrames OBJECT-TYPE
    SYNTAX           INTEGER (0..4294967295)
    MAX-ACCESS       read-only
    STATUS           current
    DESCRIPTION
        "Received multicast frames"
    ::= { ontEthportStatisRecEntry 7 }

ontEthportRecBroFrames OBJECT-TYPE
    SYNTAX           INTEGER (0..4294967295)
    MAX-ACCESS       read-only
    STATUS           current
    DESCRIPTION
        "Received broadcast frames"
    ::= { ontEthportStatisRecEntry 8 }

ontEthportRec64Frames OBJECT-TYPE
    SYNTAX          INTEGER (0..4294967295)
    MAX-ACCESS      read-only
    STATUS          current
    DESCRIPTION
        "Received 64-byte frames"
    ::= { ontEthportStatisRecEntry 9 }

ontEthportRec65Frames  OBJECT-TYPE
    SYNTAX          INTEGER (0..4294967295)
    MAX-ACCESS      read-only
    STATUS          current
    DESCRIPTION
        "Received 65~127-byte frames"
    ::= { ontEthportStatisRecEntry 10 }

ontEthportRec128Frames OBJECT-TYPE
    SYNTAX           INTEGER (0..4294967295)
    MAX-ACCESS       read-only
    STATUS           current
    DESCRIPTION
        "Received 128~255-byte frames"
    ::= { ontEthportStatisRecEntry 11 }

ontEthportRec256Frames OBJECT-TYPE
    SYNTAX           INTEGER (0..4294967295)
    MAX-ACCESS       read-only
    STATUS           current
    DESCRIPTION
        "Received 256~511-byte frames"
    ::= { ontEthportStatisRecEntry 12 }

ontEthportRec512Frames OBJECT-TYPE
    SYNTAX           INTEGER (0..4294967295)
    MAX-ACCESS       read-only
    STATUS           current
    DESCRIPTION
        "Received 512~1023-byte frames"
    ::= { ontEthportStatisRecEntry 13 }

ontEthportRec1024Frames OBJECT-TYPE
    SYNTAX            INTEGER (0..4294967295)
    MAX-ACCESS        read-only
    STATUS             current
    DESCRIPTION
        "Received 1024~1518-byte frames"
    ::= { ontEthportStatisRecEntry 14 }

ontEthportRecUndFrames OBJECT-TYPE
    SYNTAX           INTEGER (0..4294967295)
    MAX-ACCESS       read-only
    STATUS           current
    DESCRIPTION
        "Received undersize frames"
    ::= { ontEthportStatisRecEntry 15 }
  
ontEthportRecOveFrames OBJECT-TYPE
    SYNTAX           INTEGER (0..4294967295)
    MAX-ACCESS       read-only
    STATUS           current
    DESCRIPTION
      "Received oversize frames"
    ::= { ontEthportStatisRecEntry 16 }

ontEthportRecFragments OBJECT-TYPE
    SYNTAX           INTEGER (0..4294967295)
    MAX-ACCESS       read-only
    STATUS           current
    DESCRIPTION
        "Received fragments"
    ::= { ontEthportStatisRecEntry 17 }
  
ontEthportRecJabbers OBJECT-TYPE
    SYNTAX         INTEGER (0..4294967295)
    MAX-ACCESS     read-only
    STATUS         current
    DESCRIPTION
        "Received jabbers"
    ::= { ontEthportStatisRecEntry 18 }

ontEthportRecFcsFrames OBJECT-TYPE
    SYNTAX           INTEGER (0..4294967295)
    MAX-ACCESS       read-only
    STATUS           current
    DESCRIPTION
        "Received FCS error frames"
    ::= { ontEthportStatisRecEntry 19 }
  
ontEthportDisFrames OBJECT-TYPE
    SYNTAX        INTEGER (0..4294967295)
    MAX-ACCESS    read-only
    STATUS        current
    DESCRIPTION
        "Discard frames"
    ::= { ontEthportStatisRecEntry 20 }

ontEthportRecAliFrames OBJECT-TYPE
    SYNTAX           INTEGER (0..4294967295)
    MAX-ACCESS       read-only
    STATUS           current
    DESCRIPTION
        "Received alignment error frames"
    ::= { ontEthportStatisRecEntry 21 }

ontEthportMacRecFrames OBJECT-TYPE
    SYNTAX            INTEGER (0..4294967295)
    MAX-ACCESS       read-only
    STATUS           current
    DESCRIPTION
        "MAC sub-layer received error frames"
    ::= { ontEthportStatisRecEntry 22 }

ontEthportPppFrames OBJECT-TYPE
    SYNTAX        INTEGER (0..4294967295)
    MAX-ACCESS    read-only
    STATUS        current
    DESCRIPTION
        "PPPOE filtered frames"
    ::= { ontEthportStatisRecEntry 23 }

ontEthportBufReceive OBJECT-TYPE
    SYNTAX         INTEGER (0..4294967295)
    MAX-ACCESS     read-only
    STATUS         current
    DESCRIPTION
        "Buffer overflows on receive"
    ::= { ontEthportStatisRecEntry 24 }

ontEthportRecBytes OBJECT-TYPE
    SYNTAX       INTEGER (0..4294967295)
    MAX-ACCESS   read-only
    STATUS       current
    DESCRIPTION
        "Received bytes"
    ::= { ontEthportStatisRecEntry 25 }

-- ont etherport statistics sent table ----------------------    
ontEthportStatisSentTable    OBJECT-TYPE
        SYNTAX  SEQUENCE OF OntEthportStatisSentEntry
        MAX-ACCESS  not-accessible
        STATUS  current
        DESCRIPTION
            "ont etherport statistics sent table"
        ::= { ontEthPortInfo 3 }

ontEthportStatisSentEntry  OBJECT-TYPE
        SYNTAX     OntEthportStatisSentEntry
        MAX-ACCESS  not-accessible
        STATUS    current
        DESCRIPTION
            "entry of ont etherport statistics sent table"
        INDEX { soSlotIndexXI, soPportIndexXI, soOntIndexXI, soOntEthportIndexIII }
        ::= { ontEthportStatisSentTable 1 }
  
OntEthportStatisSentEntry  ::=
        SEQUENCE
        {
            soSlotIndexXI                  INTEGER,
            soPportIndexXI                 INTEGER,
            soOntIndexXI                   INTEGER,
            soOntEthportIndexIII           INTEGER,
            ontEthportSenFrames            INTEGER,
            ontEthportSenUniFrames         INTEGER,
            ontEthportSenMulFrames         INTEGER,
            ontEthportSenBroFrames         INTEGER,
            ontEthportCarFrames            INTEGER,
            ontEthportSqeMessages          INTEGER,
            ontEthportSenSinFrames         INTEGER,
            ontEthportSenMulColFrames      INTEGER,
            ontEthportSenExcFrames         INTEGER,
            ontEthportLatFrames            INTEGER,
            ontEthportMacSenFrames         INTEGER,
            ontEthportBufTransmit          INTEGER,
            ontEthportSentBytes            INTEGER
        }

soSlotIndexXI   OBJECT-TYPE    
    SYNTAX      INTEGER(0..5)
    MAX-ACCESS  read-only
    STATUS      current
    DESCRIPTION
        "The index of slot, should in <0-5>."
    ::= { ontEthportStatisSentEntry 1 }

soPportIndexXI  OBJECT-TYPE    
    SYNTAX      INTEGER(1..16)
    MAX-ACCESS  read-only
    STATUS      current
    DESCRIPTION
        "The index of pon port, should in <1-16>."
    ::= { ontEthportStatisSentEntry 2 }

soOntIndexXI    OBJECT-TYPE    
    SYNTAX      INTEGER(1..128)
    MAX-ACCESS  read-only
    STATUS      current
    DESCRIPTION
        "The index of ont, the 3rd index of this table.
         Should in <1-128>."
    ::= { ontEthportStatisSentEntry 3 }

soOntEthportIndexIII   OBJECT-TYPE    
    SYNTAX      INTEGER(1..8)
    MAX-ACCESS  read-only
    STATUS      current
    DESCRIPTION
        "The index of ont ethernet port, the 4th index of this table.
         range <1-n> is determined by ont type, the max n is 2.4."
    ::= { ontEthportStatisSentEntry 4 }

ontEthportSenFrames OBJECT-TYPE
    SYNTAX        INTEGER (0..4294967295)
    MAX-ACCESS    read-only
    STATUS        current
    DESCRIPTION
        "Sent frames"
    ::= { ontEthportStatisSentEntry 5 }

ontEthportSenUniFrames OBJECT-TYPE
    SYNTAX           INTEGER (0..4294967295)
    MAX-ACCESS       read-only
    STATUS           current
    DESCRIPTION
        "Sent unicast frames"
    ::= { ontEthportStatisSentEntry 6 }

ontEthportSenMulFrames OBJECT-TYPE
    SYNTAX           INTEGER (0..4294967295)
    MAX-ACCESS       read-only
    STATUS           current
    DESCRIPTION
        "Sent multicast frames"
    ::= { ontEthportStatisSentEntry 7 }

ontEthportSenBroFrames OBJECT-TYPE
    SYNTAX           INTEGER (0..4294967295)
    MAX-ACCESS       read-only
    STATUS           current
    DESCRIPTION
        "Sent broadcast frames"
    ::= { ontEthportStatisSentEntry 8 }

ontEthportCarFrames OBJECT-TYPE
    SYNTAX        INTEGER (0..4294967295)
    MAX-ACCESS    read-only
    STATUS        current
    DESCRIPTION
        "Carrier sense error frames"
    ::= { ontEthportStatisSentEntry 9 }

ontEthportSqeMessages OBJECT-TYPE
    SYNTAX          INTEGER (0..4294967295)
    MAX-ACCESS      read-only
    STATUS          current
    DESCRIPTION
        "SQE test error messages"
    ::= { ontEthportStatisSentEntry 10 }
  
ontEthportSenSinFrames OBJECT-TYPE
    SYNTAX           INTEGER (0..4294967295)
    MAX-ACCESS       read-only
    STATUS           current
    DESCRIPTION
        "Sent single collision frames"
    ::= { ontEthportStatisSentEntry 11 }

ontEthportSenMulColFrames OBJECT-TYPE
    SYNTAX              INTEGER (0..4294967295)
    MAX-ACCESS          read-only
    STATUS              current
    DESCRIPTION
        "Sent multiple collision frames"
    ::= { ontEthportStatisSentEntry 12 }

ontEthportSenExcFrames OBJECT-TYPE
    SYNTAX           INTEGER (0..4294967295)
    MAX-ACCESS       read-only
    STATUS           current
    DESCRIPTION
        "Sent excessive collision frames"
    ::= { ontEthportStatisSentEntry 13 }
  
ontEthportLatFrames OBJECT-TYPE
    SYNTAX        INTEGER (0..4294967295)
    MAX-ACCESS    read-only
    STATUS        current
    DESCRIPTION
        "Late collision frames"
    ::= { ontEthportStatisSentEntry 14 }

ontEthportMacSenFrames OBJECT-TYPE
    SYNTAX           INTEGER (0..4294967295)
    MAX-ACCESS       read-only
    STATUS           current
    DESCRIPTION
        "MAC sub-layer sent error frames"
    ::= { ontEthportStatisSentEntry 15 }

ontEthportBufTransmit OBJECT-TYPE
    SYNTAX          INTEGER (0..4294967295)
    MAX-ACCESS      read-only
    STATUS          current
    DESCRIPTION
        "Buffer overflows on transmit"
    ::= { ontEthportStatisSentEntry 16 }

ontEthportSentBytes OBJECT-TYPE
    SYNTAX          INTEGER (0..4294967295)
    MAX-ACCESS      read-only
    STATUS          current
    DESCRIPTION
        "Sent bytes "
    ::= { ontEthportStatisSentEntry 17 }

-- ont ethport utilization table ------------------------
ontEthportUtilizationTable OBJECT-TYPE
        SYNTAX       SEQUENCE OF OntEthportUtilizationEntry
        MAX-ACCESS   not-accessible
        STATUS       current
        DESCRIPTION
            "ont ethport multicast mac table"
        ::= { ontEthPortInfo 4 }

ontEthportUtilizationEntry   OBJECT-TYPE
        SYNTAX       OntEthportUtilizationEntry
        MAX-ACCESS   not-accessible
        STATUS       current
        DESCRIPTION
            "entry of ont ethport multicast mac table"
        INDEX { soSlotIndexVIII, soPportIndexVIII, soOntIndexVIII, soOntEthportIndexII }
        ::= { ontEthportUtilizationTable 1 }

OntEthportUtilizationEntry  ::= 
        SEQUENCE 
        {
            soSlotIndexVIII                INTEGER,
            soPportIndexVIII               INTEGER,
            soOntIndexVIII                 INTEGER,
            soOntEthportIndexII            INTEGER,
            soEportUtilizeTxOctetsRate     INTEGER,
            soEportUtilizeRxOctetsRate     INTEGER,
            soEportUtilizeTxPktsRate       INTEGER,
            soEportUtilizeRxPktsRate       INTEGER,
            soEportUtilizeTxOctets         INTEGER,
            soEportUtilizeRxOctets         INTEGER,
            soEportUtilizeTxPktsError      INTEGER,
            soEportUtilizeRxPktsError      INTEGER,
            soEportUtilizeTxPktsDiscard    INTEGER,
            soEportUtilizeRxPktsDiscard    INTEGER
        }

soSlotIndexVIII OBJECT-TYPE    
    SYNTAX      INTEGER(0..5)
    MAX-ACCESS  read-only
    STATUS      current
    DESCRIPTION
        "The index of slot, should in <0-5>."
    ::= { ontEthportUtilizationEntry 1 }

soPportIndexVIII OBJECT-TYPE    
    SYNTAX      INTEGER(1..16)
    MAX-ACCESS  read-only
    STATUS      current
    DESCRIPTION
        "The index of pon port, should in <1-16>."
    ::= { ontEthportUtilizationEntry 2 }

soOntIndexVIII  OBJECT-TYPE    
    SYNTAX      INTEGER(1..128)
    MAX-ACCESS  read-only
    STATUS      current
    DESCRIPTION
        "The index of ont, the 3rd index of this table.
         Should in <1-128>."
    ::= { ontEthportUtilizationEntry 3 }

soOntEthportIndexII   OBJECT-TYPE    
    SYNTAX      INTEGER(1..8)
    MAX-ACCESS  read-only
    STATUS      current
    DESCRIPTION
        "The index of ont ethernet port, the 4th index of this table.
         range <1-n> is determined by ont type, the max n is 2.4."
    ::= { ontEthportUtilizationEntry 4 }

soEportUtilizeTxOctetsRate  OBJECT-TYPE    
    SYNTAX      INTEGER(0..10000)
    MAX-ACCESS  read-only
    STATUS      current
    DESCRIPTION
        "ont tx octets rate."
    ::= { ontEthportUtilizationEntry 5 }

soEportUtilizeRxOctetsRate  OBJECT-TYPE    
    SYNTAX      INTEGER(0..10000)
    MAX-ACCESS  read-only
    STATUS      current
    DESCRIPTION
        "ont rx octets rate."
    ::= { ontEthportUtilizationEntry 6 }

soEportUtilizeTxPktsRate  OBJECT-TYPE    
    SYNTAX      INTEGER(0..1600000000)
    MAX-ACCESS  read-only
    STATUS      current
    DESCRIPTION
        "ont tx packets rate(pps)."
    ::= { ontEthportUtilizationEntry 7 }

soEportUtilizeRxPktsRate  OBJECT-TYPE    
    SYNTAX      INTEGER(0..1600000000)
    MAX-ACCESS  read-only
    STATUS      current
    DESCRIPTION
        "ont rx packets rate(pps)."
    ::= { ontEthportUtilizationEntry 8 }

soEportUtilizeTxOctets  OBJECT-TYPE    
    SYNTAX      INTEGER(0..1600000000)
    MAX-ACCESS  read-only
    STATUS      current
    DESCRIPTION
        "ont tx octets in 15 minutes."
    ::= { ontEthportUtilizationEntry 9 }

soEportUtilizeRxOctets  OBJECT-TYPE    
    SYNTAX      INTEGER(0..1600000000)
    MAX-ACCESS  read-only
    STATUS      current
    DESCRIPTION
        "ont rx octets in 15 minutes."
    ::= { ontEthportUtilizationEntry 10 }

soEportUtilizeTxPktsError  OBJECT-TYPE    
    SYNTAX      INTEGER(0..10000)
    MAX-ACCESS  read-only
    STATUS      current
    DESCRIPTION
        "port tx packets error in 15 minute."
    ::= { ontEthportUtilizationEntry 11 }

soEportUtilizeRxPktsError  OBJECT-TYPE    
    SYNTAX      INTEGER(0..10000)
    MAX-ACCESS  read-only
    STATUS      current
    DESCRIPTION
        "port rx packets error in 15 minute."
    ::= { ontEthportUtilizationEntry 12 }

soEportUtilizeTxPktsDiscard  OBJECT-TYPE    
    SYNTAX      INTEGER(0..10000)
    MAX-ACCESS  read-only
    STATUS      current
    DESCRIPTION
        "port tx packets discard in 15 minute."
    ::= { ontEthportUtilizationEntry 13 }

soEportUtilizeRxPktsDiscard  OBJECT-TYPE    
    SYNTAX      INTEGER(0..10000)
    MAX-ACCESS  read-only
    STATUS      current
    DESCRIPTION
        "port rx packets discard in 15 minute."
    ::= { ontEthportUtilizationEntry 14 }


-- ont gemport infomation ----------------------------------
ontGemPortInfo       OBJECT IDENTIFIER ::= { statusOnt 3 }

-- 2.4.3.1 ontGemportStatisticsTable

-- ont gemport statistics table ----------------------------
ontGemportStatisticsTable OBJECT-TYPE
        SYNTAX       SEQUENCE OF OntGemportStatisticsEntry
        MAX-ACCESS   not-accessible
        STATUS       current
        DESCRIPTION
            "ont gemport statistics table"
        ::= { ontGemPortInfo 1 }

ontGemportStatisticsEntry   OBJECT-TYPE
        SYNTAX       OntGemportStatisticsEntry
        MAX-ACCESS   not-accessible
        STATUS       current
        DESCRIPTION
            "entry of ont gemport statistics table"
        INDEX { soSlotIndexIX, soPportIndexIX, soOntIndexIX, ontGemportStaFrameType, ontGemportStaIndex }
        ::= { ontGemportStatisticsTable 1 }

OntGemportStatisticsEntry  ::= 
        SEQUENCE 
        {
            soSlotIndexIX             INTEGER,
            soPportIndexIX            INTEGER,
            soOntIndexIX              INTEGER,
            ontGemportStaFrameType    INTEGER,
            ontGemportStaIndex        INTEGER,
            ontGemportStaUpdateData   INTEGER,
            ontGemportLostFrame       INTEGER,
            ontGemportRecFrame        INTEGER,
            ontGemportRecBlock        INTEGER,
            ontGemportSentFrame       INTEGER,
            ontGemportSentBlock       INTEGER
        }

soSlotIndexIX   OBJECT-TYPE    
    SYNTAX      INTEGER(0..5)
    MAX-ACCESS  read-only
    STATUS      current
    DESCRIPTION
        "The index of slot, should in <0-5>."
    ::= { ontGemportStatisticsEntry 1 }

soPportIndexIX  OBJECT-TYPE    
    SYNTAX      INTEGER(1..16)
    MAX-ACCESS  read-only
    STATUS      current
    DESCRIPTION
        "The index of pon port, should in <1-16>."
    ::= { ontGemportStatisticsEntry 2 }

soOntIndexIX    OBJECT-TYPE    
    SYNTAX      INTEGER(1..128)
    MAX-ACCESS  read-only
    STATUS      current
    DESCRIPTION
        "The index of ont, the 3rd index of this table.
         Should in <1-128>."
    ::= { ontGemportStatisticsEntry 3 }

ontGemportStaFrameType OBJECT-TYPE
        SYNTAX       INTEGER(0..2)
        MAX-ACCESS   read-only
        STATUS       current
        DESCRIPTION
            "ontGemportStaFrameTpte:
             0----unicast
             1----multicast
             2----broadcast"
        ::= { ontGemportStatisticsEntry 4 }

ontGemportStaIndex   OBJECT-TYPE    
        SYNTAX       INTEGER(1..24)
        MAX-ACCESS   read-only
        STATUS       current
        DESCRIPTION
            "ontGemportStaIndex:
             The index should be inputed with <1-24>"
        ::= { ontGemportStatisticsEntry 5 }

ontGemportStaUpdateData OBJECT-TYPE    
    SYNTAX      INTEGER(0..2)
    MAX-ACCESS  read-write
    STATUS      current
    DESCRIPTION
        "Set ontGemportStaUpdateData=2 to update data of the entry.
         then you can read this node. still 2 means update incomplete,
         0 means update successfully, 1 means update failed.
         If you don't update the data of the entry, the value you get
         maybe not newest."
    ::= { ontGemportStatisticsEntry 6 }

ontGemportLostFrame  OBJECT-TYPE
    SYNTAX       INTEGER (0..4294967295)
    MAX-ACCESS   read-only
    STATUS       current
    DESCRIPTION
         "ontGemportLostFrame"
    ::= { ontGemportStatisticsEntry 7 }

ontGemportRecFrame   OBJECT-TYPE
    SYNTAX       INTEGER (0..4294967295)
    MAX-ACCESS   read-only
    STATUS       current
    DESCRIPTION
         "ontGemportRecFrame"
    ::= { ontGemportStatisticsEntry 8 }

ontGemportRecBlock   OBJECT-TYPE
    SYNTAX       INTEGER (0..4294967295)
    MAX-ACCESS   read-only
    STATUS       current
    DESCRIPTION
         "ontGemportRecBlock"
    ::= { ontGemportStatisticsEntry 9 }

ontGemportSentFrame  OBJECT-TYPE
    SYNTAX       INTEGER (0..4294967295)
    MAX-ACCESS   read-only
    STATUS       current
    DESCRIPTION
         "ontGemportSentFrame"
    ::= { ontGemportStatisticsEntry 10 }

ontGemportSentBlock  OBJECT-TYPE
    SYNTAX       INTEGER (0..4294967295)
    MAX-ACCESS   read-only
    STATUS       current
    DESCRIPTION
         "ontGemportSentBlock"
    ::= { ontGemportStatisticsEntry 11 }

-- ont wan infomation --------------------------------------
ontWanInfo       OBJECT IDENTIFIER ::= { statusOnt 4 }

-- 2.4.4.1 ontWanInfoTable

-- ont wan infomation table --------------------------------
ontWanInfoTable      OBJECT-TYPE
        SYNTAX       SEQUENCE OF OntWanInfoEntry
        MAX-ACCESS   not-accessible
        STATUS       current
        DESCRIPTION
            "ont wan infomation table"
        ::= { ontWanInfo 1 }

ontWanInfoEntry      OBJECT-TYPE
        SYNTAX       OntWanInfoEntry
        MAX-ACCESS   not-accessible
        STATUS       current
        DESCRIPTION
            "entry of ont wan infomation table"
        INDEX { soSlotIndexXIII, soPportIndexXIII, soOntIndexXIII, ontWanIndex}
        ::= { ontWanInfoTable 1 }

OntWanInfoEntry  ::= 
        SEQUENCE 
        {
            soSlotIndexXIII           INTEGER,
            soPportIndexXIII          INTEGER,
            soOntIndexXIII            INTEGER,
            ontWanIndex               INTEGER,
            ontWanServerType          OCTET STRING,
            ontWanIp                  IpAddress,
            ontWanMask                IpAddress,
            ontWanGateway             IpAddress,
            ontWanPriDns              IpAddress,
            ontWanSecDns              IpAddress
        }

soSlotIndexXIII OBJECT-TYPE    
    SYNTAX      INTEGER(0..5)
    MAX-ACCESS  read-only
    STATUS      current
    DESCRIPTION
        "The index of slot, should in <0-5>."
    ::= { ontWanInfoEntry 1 }

soPportIndexXIII OBJECT-TYPE    
    SYNTAX      INTEGER(1..16)
    MAX-ACCESS  read-only
    STATUS      current
    DESCRIPTION
        "The index of pon port, should in <1-16>."
    ::= { ontWanInfoEntry 2 }

soOntIndexXIII  OBJECT-TYPE    
    SYNTAX      INTEGER(1..128)
    MAX-ACCESS  read-only
    STATUS      current
    DESCRIPTION
        "The index of ont, the 3rd index of this table.
         Should in <1-128>."
    ::= { ontWanInfoEntry 3 }

ontWanIndex      OBJECT-TYPE    
    SYNTAX       INTEGER(1..4)
    MAX-ACCESS   read-only
    STATUS       current
    DESCRIPTION
        "ontWanIndex:
         The index should be inputed with <1-4>"
    ::= { ontWanInfoEntry 4 }

ontWanServerType OBJECT-TYPE    
    SYNTAX      OCTET STRING (SIZE(0..255))
    MAX-ACCESS  read-write
    STATUS      current
    DESCRIPTION
        "ont wan server type."
        -- 业务类型(IPTV TR069 INTERNET VOIP可组合，如IPTV_TR069_INTERNET_VOIP) 
    ::= { ontWanInfoEntry 5 }

ontWanIp         OBJECT-TYPE
    SYNTAX       IpAddress
    MAX-ACCESS   read-only
    STATUS       current
    DESCRIPTION
         "ontGemportLostFrame"
    ::= { ontWanInfoEntry 6 }

ontWanMask       OBJECT-TYPE
    SYNTAX       IpAddress
    MAX-ACCESS   read-only
    STATUS       current
    DESCRIPTION
         "ontGemportRecFrame"
    ::= { ontWanInfoEntry 7 }

ontWanGateway    OBJECT-TYPE
    SYNTAX       IpAddress
    MAX-ACCESS   read-only
    STATUS       current
    DESCRIPTION
         "ontGemportRecBlock"
    ::= { ontWanInfoEntry 8 }

ontWanPriDns     OBJECT-TYPE
    SYNTAX       IpAddress
    MAX-ACCESS   read-only
    STATUS       current
    DESCRIPTION
         "ontWanInfoEntry"
    ::= { ontWanInfoEntry 9 }

ontWanSecDns     OBJECT-TYPE
    SYNTAX       IpAddress
    MAX-ACCESS   read-only
    STATUS       current
    DESCRIPTION
         "ontGemportSentBlock"
    ::= { ontWanInfoEntry 10 }

-- ont pots infomation --------------------------------------
ontPotsInfo       OBJECT IDENTIFIER ::= { statusOnt 5 }

-- 2.4.5.1 ontPotsInfoTable

-- ont pots infomation table --------------------------------
ontPotsInfoTable      OBJECT-TYPE
        SYNTAX       SEQUENCE OF OntPotsInfoEntry
        MAX-ACCESS   not-accessible
        STATUS       current
        DESCRIPTION
            "ont pots infomation table"
        ::= { ontPotsInfo 1 }

ontPotsInfoEntry      OBJECT-TYPE
        SYNTAX       OntPotsInfoEntry
        MAX-ACCESS   not-accessible
        STATUS       current
        DESCRIPTION
            "entry of ont pots infomation table"
        INDEX { soSlotIndexXIV, soPportIndexXIV, soOntIndexXIV, ontPotsIndex}
        ::= { ontPotsInfoTable 1 }

OntPotsInfoEntry  ::= 
        SEQUENCE 
        {
            soSlotIndexXIV            INTEGER,
            soPportIndexXIV           INTEGER,
            soOntIndexXIV             INTEGER,
            ontPotsIndex              INTEGER,
            ontPotsStatus             INTEGER
        }

soSlotIndexXIV  OBJECT-TYPE    
    SYNTAX      INTEGER(0..5)
    MAX-ACCESS  read-only
    STATUS      current
    DESCRIPTION
        "The index of slot, should in <0-5>."
    ::= { ontPotsInfoEntry 1 }

soPportIndexXIV OBJECT-TYPE    
    SYNTAX      INTEGER(1..16)
    MAX-ACCESS  read-only
    STATUS      current
    DESCRIPTION
        "The index of pon port, should in <1-16>."
    ::= { ontPotsInfoEntry 2 }

soOntIndexXIV   OBJECT-TYPE    
    SYNTAX      INTEGER(1..128)
    MAX-ACCESS  read-only
    STATUS      current
    DESCRIPTION
        "The index of ont, the 3rd index of this table.
         Should in <1-128>."
    ::= { ontPotsInfoEntry 3 }

ontPotsIndex     OBJECT-TYPE    
    SYNTAX       INTEGER(1..2)
    MAX-ACCESS   read-only
    STATUS       current
    DESCRIPTION
        "ontWanIndex:
         The index should be inputed with <1-2>"
    ::= { ontPotsInfoEntry 4 }

ontPotsStatus   OBJECT-TYPE    
    SYNTAX      INTEGER(0..14)
    MAX-ACCESS  read-write
    STATUS      current
    DESCRIPTION
        "typedef enum tag_M_ONT_POTS_STATUS
        {
        /*  0 */ POTS_STATUS_INIT = 0,                       /* None/initial */
        /*  1 */ POTS_STATUS_REGISTERED,                     /* Registered */
        /*  2 */ POTS_STATUS_IN_SESSION,                     /* In session */
        /*  3 */ POTS_STATUS_REG_ICMP_ERR,                   /* Failed registration –icmp error */
        /*  4 */ POTS_STATUS_REG_TCP_FAIL,                   /* Failed registration –failed tcp */  
        /*  5 */ POTS_STATUS_REG_TMOUT,                      /* Failed registration –timeout */
        /*  6 */ POTS_STATUS_REG_AUTH_FAIL,                  /* Failed registration - failed authentication */
        /*  7 */ POTS_STATUS_REG_SRV_FAIL,                   /* Failed registration - server fail code */
        /*  8 */ POTS_STATUS_INV_ICMP_ERR,                   /* Failed invite –icmp error */
        /*  9 */ POTS_STATUS_INV_TCP_FAIL,                   /* Failed invite –failed tcp */
        /* 10 */ POTS_STATUS_INV_AUTH_FAIL,                  /* Failed invite –failed authentication */
        /* 11 */ POTS_STATUS_INV_TMOUT,                      /* Failed invite –timeout */
        /* 12 */ POTS_STATUS_INV_SRV_FAIL,                   /* Failed invite –server fail code */
        /* 13 */ POTS_STATUS_PORT_NOT_CFG,                   /* Port not configured */
        /* 14 */ POTS_STATUS_CFG_DONE,                       /* Config done */
                 POTS_STATUS_SUM
        }M_ONT_POTS_STATUS;"
    ::= { ontPotsInfoEntry 5 }

--------------------------------------------------------------
------------------ 2.5. status trap ------------------------
--------------------------------------------------------------
-- 2.5.1. deviceTrap
-- 2.5.2. slotTrap
-- 2.5.3. portTrap
-- 2.5.4. ontTrap
-- 2.5.5. ontPortTrap
-- 2.5.6. trapInfo
-- 2.5.7. trapSetThreshold
-- 2.5.8. trapClearThreshold


------ deviceTrap ------------------------------------------
deviceTrap        OBJECT IDENTIFIER ::= { statusTrap 1 }

oltSwitchOverTrap NOTIFICATION-TYPE
        STATUS  current
        DESCRIPTION
            "olt contrl-board switchover trap."
             --olt主控板主备倒换 
        ::= { deviceTrap 1 }

oltFanStatusTrap NOTIFICATION-TYPE
        OBJECTS { gponTrapSlotId, gponTrapExtraInfo }
        STATUS  current
        DESCRIPTION
            "olt fan status change trap.
            gponTrapExtraInfo:
            1  stop
            2  start
            3  remove
            4  insert"
             --olt风扇状态trap 
        ::= { deviceTrap 2 }

oltPowerStatusTrap NOTIFICATION-TYPE
        OBJECTS { gponTrapSlotId, gponTrapExtraInfo }
        STATUS  current
        DESCRIPTION
            "olt power status trap."
             --olt电源状态trap   true
        ::= { deviceTrap 3 }

oltTemperatureTrap NOTIFICATION-TYPE
        OBJECTS { gponTrapStatus, gponTrapExtraInfo }
        STATUS  current
        DESCRIPTION
            "olt switch chip temperature trap.
            gponTrapExtraInfo:
            1  low 
            2  high"
             --olt 交换芯片温度trap  true
        ::= { deviceTrap 4 }

oltPonTemperatureTrap NOTIFICATION-TYPE
        OBJECTS { gponTrapStatus, gponTrapExtraInfo }
        STATUS  current
        DESCRIPTION
            "olt pon chip temperature trap.
            gponTrapExtraInfo:
            1  low
            2  high"
             --olt pon 芯片温度trap  true
        ::= { deviceTrap 5 }

unitOfflineAlarmTrap NOTIFICATION-TYPE
        OBJECTS { gponTrapStatus }
        STATUS  current
        DESCRIPTION
            "unit offline alarm trap."
             --olt offline 告警  true
        ::= { deviceTrap 6 }

oltDgTrap NOTIFICATION-TYPE
        OBJECTS { gponTrapStatus }
        STATUS  current
        DESCRIPTION
            "unit dying gasp trap."
             --olt 掉电告警
        ::= { deviceTrap 7 }

edfaTrap NOTIFICATION-TYPE
        OBJECTS { gponTrapExtraInfo, gponTrapSfpPerformanceStatus }
        STATUS  current
        DESCRIPTION
            "edfa trap.
            gponTrapExtraInfo:
            1  Optical Input Power 1
            2  Optical Input Power 2
            3  Optical Output Power
            4  Pump 1 Bias Current
            5  Pump 1 Pump Temperature
            6  Pump 1 Pump Tec
            7  Pump 2 Bias Current
            8  Pump 2 Pump Temperature
            9  Pump 2 Pump Tec
            10  DC Voltage
            11  Internal Temperature"
        ::= { deviceTrap 8 }

oltDooralmTrap NOTIFICATION-TYPE
        OBJECTS { gponTrapStatus }
        STATUS  current
        DESCRIPTION
            "olt door alarm trap."
             --olt 开箱告警
        ::= { deviceTrap 9 }

warningPortAlarmTrap NOTIFICATION-TYPE
        OBJECTS { gponTrapWarnPortIndex, gponTrapWarnPortAlarm }
        STATUS  current
        DESCRIPTION
            "Warning port alarm."
             --olt 告警端口告警
        ::= { deviceTrap 10 }

------ slotTrap --------------------------------------------
slotTrap          OBJECT IDENTIFIER ::= { statusTrap 2 }

oltBoardStatusTrap NOTIFICATION-TYPE
        OBJECTS { gponTrapSlotId, gponTrapExtraInfo }
        STATUS  current
        DESCRIPTION
            "olt board status trap."
             --olt 板状态改变（包括主控，业务板插入，移除，连接）
        ::= { slotTrap 1 }

------ portTrap ------------------------------------------
portTrap          OBJECT IDENTIFIER ::= { statusTrap 3 }

oltPortRingTrap NOTIFICATION-TYPE
        OBJECTS { gponTrapSlotId, gponTrapPortId, gponTrapStatus }
        STATUS  current
        DESCRIPTION
            "olt port ring trap."
             --olt端口环路trap 
        ::= { portTrap 1 }

oltPortSdTrap NOTIFICATION-TYPE
        OBJECTS { gponTrapSlotId, gponTrapPortId, gponTrapStatus }
        STATUS  current
        DESCRIPTION
            "olt port sd trap."
             --olt端口 sd trap   true
        ::= { portTrap 2 }

oltPportLOSTrap NOTIFICATION-TYPE
        OBJECTS { gponTrapSlotId, gponTrapPortId, gponTrapStatus }
        STATUS  current
        DESCRIPTION
            "olt pon port LOS trap. "
             --olt pon 端口 LOS trap  true
        ::= { portTrap 3 }

oltPortSfpTcrossTrap NOTIFICATION-TYPE
        OBJECTS { gponTrapSlotId, gponTrapPortId, gponTrapOntId, gponTrapStatus, gponTrapExtraInfo }
        STATUS  current
        DESCRIPTION
            "olt sfp threshold crossing alert trap.
             gponTrapExtraInfo:
             1  recieve high
             2  recieve low
             3  send high
             4  send low"
             --olt 光模块参数越限告警 trap
        ::= { portTrap 4 }

oltPortSfpUnplugTrap NOTIFICATION-TYPE
        OBJECTS { gponTrapSlotId, gponTrapPortId, gponTrapStatus, gponTrapSn }
        STATUS  current
        DESCRIPTION
            "olt pon port sfp unplug trap. "
             --olt pon 端口光模块被拔出 trap  true
        ::= { portTrap 5 }

oltPortUdldTrap NOTIFICATION-TYPE
        OBJECTS { gponTrapSlotId, gponTrapPortId, gponTrapExtraInfo }
        STATUS  current
        DESCRIPTION
            "UniDirectional Link Detection trap. 
            gponTrapExtraInfo:
            1  Undetermined
            2  Unidirectional
            3  Bidirectional"
             --olt 端口单向链路检测 trap  true
             -- 1 未确定 2 单通 3 双通
        ::= { portTrap 6 }

oltPportLOFTrap NOTIFICATION-TYPE
        OBJECTS { gponTrapSlotId, gponTrapPortId, gponTrapStatus }
        STATUS  current
        DESCRIPTION
            "olt pon port LOF trap. "
             --olt pon 端口 LOF trap  true
        ::= { portTrap 7 }

oltPortCRCTrap NOTIFICATION-TYPE
        OBJECTS { gponTrapSlotId, gponTrapPortId, gponTrapStatus }
        STATUS  current
        DESCRIPTION
            "olt port CRC trap. "
             --olt 端口 CRC trap 
        ::= { portTrap 8 }

oltPportRegOverTrap NOTIFICATION-TYPE
        OBJECTS { gponTrapSlotId, gponTrapPortId, gponTrapStatus }
        STATUS  current
        DESCRIPTION
            "olt pon port register over trap. "
             --olt pon 端口注册个数越限 trap
        ::= { portTrap 9 }

------ ontTrap --------------------------------------------
ontTrap           OBJECT IDENTIFIER ::= { statusTrap 4 }

ontOnlineStatusTrap NOTIFICATION-TYPE
        OBJECTS { gponTrapSlotId, gponTrapPortId, gponTrapOntId, gponTrapStatus, gponTrapSn, gponTrapLoid }
        STATUS  current
        DESCRIPTION
            "ont online status trap."
             --ont上下线状态trap   true
        ::= { ontTrap 1 }

ont9843Trap NOTIFICATION-TYPE
        OBJECTS { gponTrapSlotId, gponTrapPortId, gponTrapOntId, gponTrapExtraInfo }
        STATUS  current
        DESCRIPTION
            "ont 984.3 warning trap.
             gponTrapExtraInfo: warning type:
             1  LOSi
             2  LOFi
             3  DOWi
             4  SFi
             5  SDi
             6  LCDGi
             7  RDIi
             8  SUFi
             9  DFi
             10 LOAi
             11 LOKi
             12 TIWi
             13 DGi
             14 LOAMi
             15 MEMi
             16 MISi
             17 PEEi
             18 ERRi
             19 REIi"
             --ont 984.3 告警 trap  true
        ::= { ontTrap 2 }

ontRogueTrap NOTIFICATION-TYPE
        OBJECTS { gponTrapSlotId, gponTrapPortId, gponTrapOntId, gponTrapStatus, gponTrapExtraInfo }
        STATUS  current
        DESCRIPTION
            "Rogue ont trap.
             gponTrapExtraInfo: rogue type:
             1  continuous 
             2  intermittent "
             --流氓ont trap（包括长发光和间歇性发光）
        ::= { ontTrap 3 }

ontAuthFailTrap NOTIFICATION-TYPE
        OBJECTS { gponTrapSlotId, gponTrapPortId, gponTrapSn }
        STATUS  current
        DESCRIPTION
            "ont authentication failure trap."
             --ont认证失败trap
        ::= { ontTrap 4 }

ontSfpTcrossTrap NOTIFICATION-TYPE
        OBJECTS { gponTrapSlotId, gponTrapPortId, gponTrapOntId, gponTrapStatus, gponTrapExtraInfo }
        STATUS  current
        DESCRIPTION
            "ont sfp threshold crossing alert trap.
             gponTrapExtraInfo:
             1  recieve high
             2  recieve low
             3  send high
             4  send low"
             --olt 光模块参数越限告警 trap
        ::= { ontTrap 5 }

------ ontPortTrap ------------------------------------------
ontPortTrap       OBJECT IDENTIFIER ::= { statusTrap 5 }

ontEthPortStatusTrap NOTIFICATION-TYPE
        OBJECTS { gponTrapSlotId, gponTrapPortId, gponTrapOntId, gponTrapOntEthportId, gponTrapStatus }
        STATUS  current
        DESCRIPTION
            "ont ethernet port status trap."
             --ont以太网端口状态trap
        ::= { ontPortTrap 1 }

ontEthPortRingTrap NOTIFICATION-TYPE
        OBJECTS { gponTrapSlotId, gponTrapPortId, gponTrapOntId, gponTrapOntEthportId, gponTrapStatus }
        STATUS  current
        DESCRIPTION
            "ont ethernet port ring trap."
             --ont以太网端口环路trap
        ::= { ontPortTrap 2 }

ontPotsH248Trap NOTIFICATION-TYPE
        OBJECTS { gponTrapSlotId, gponTrapPortId, gponTrapOntId, gponTrapExtraId, gponTrapStatus }
        STATUS  current
        DESCRIPTION
            "ont pots h248 link trap.
            gponTrapExtraId: ont pots number"
             --ont语音端口链路告警trap
        ::= { ontPortTrap 3 }

        
------ trapInfo --------------------------------------
trapInfo          OBJECT IDENTIFIER ::= { statusTrap 6 }

gponTrapSlotId OBJECT-TYPE
      SYNTAX INTEGER
      MAX-ACCESS accessible-for-notify
      STATUS current
      DESCRIPTION
        "slot-id/fan-id/power-id in trap "
      ::= { trapInfo 1 }

gponTrapPortId OBJECT-TYPE
      SYNTAX INTEGER
      MAX-ACCESS accessible-for-notify
      STATUS current
      DESCRIPTION
        "port id in trap "
      ::= { trapInfo 2 }

gponTrapOntId OBJECT-TYPE
      SYNTAX INTEGER
      MAX-ACCESS accessible-for-notify
      STATUS current
      DESCRIPTION
        "ont id in trap "
      ::= { trapInfo 3 }

gponTrapOntEthportId OBJECT-TYPE
      SYNTAX INTEGER
      MAX-ACCESS accessible-for-notify
      STATUS current
      DESCRIPTION
        "ont ethernet port id in trap "
      ::= { trapInfo 4 }

gponTrapExtraId OBJECT-TYPE
      SYNTAX INTEGER
      MAX-ACCESS accessible-for-notify
      STATUS current
      DESCRIPTION
        "other id in trap, etc."
      ::= { trapInfo 5 }

gponTrapStatus OBJECT-TYPE
      SYNTAX INTEGER
      MAX-ACCESS accessible-for-notify
      STATUS current
      DESCRIPTION
        "1 alarm/linkdown/offline/open box
         0 clear/linkup/online/close box"
      ::= { trapInfo 6 }

gponTrapExtraInfo OBJECT-TYPE
      SYNTAX INTEGER
      MAX-ACCESS accessible-for-notify
      STATUS current
      DESCRIPTION
        "trap extra infomation"
      ::= { trapInfo 7 }

gponTrapSn OBJECT-TYPE
      SYNTAX OCTET STRING
      MAX-ACCESS accessible-for-notify
      STATUS current
      DESCRIPTION
        "sn use for trap."
      ::= { trapInfo 8 }

gponTrapLoid OBJECT-TYPE
      SYNTAX OCTET STRING
      MAX-ACCESS accessible-for-notify
      STATUS current
      DESCRIPTION
        "sn use for trap."
      ::= { trapInfo 9 }

gponTrapSfpPerformanceStatus OBJECT-TYPE
      SYNTAX INTEGER
      MAX-ACCESS accessible-for-notify
      STATUS current
      DESCRIPTION
        "0 normal
         1 lolo
         2 lo
         3 hi
         4 hihi"
      ::= { trapInfo 10 }

gponTrapWarnPortIndex OBJECT-TYPE
      SYNTAX INTEGER
      MAX-ACCESS accessible-for-notify
      STATUS current
      DESCRIPTION
        "Warn index 1 to 8"
      ::= { trapInfo 11 }

gponTrapWarnPortAlarm OBJECT-TYPE
      SYNTAX INTEGER
      MAX-ACCESS accessible-for-notify
      STATUS current
      DESCRIPTION
        "0 clear
         1 warn"
      ::= { trapInfo 12 }
      
------ trapSetThreshold --------------------------------------
trapSetThreshold        OBJECT IDENTIFIER ::= { statusTrap 7 }

thresholdTemperatureHigh   OBJECT-TYPE
    SYNTAX      INTEGER (-99..99)
    MAX-ACCESS  read-write
    STATUS      current
    DESCRIPTION
        "temperature high threshold, default 60(℃)."
    ::= { trapSetThreshold 1 }

thresholdTemperatureLow   OBJECT-TYPE
    SYNTAX      INTEGER (-99..99)
    MAX-ACCESS  read-write
    STATUS      current
    DESCRIPTION
        "temperature low threshold, default -25(℃)."
    ::= { trapSetThreshold 2 }

thresholdRegOnt OBJECT-TYPE
    SYNTAX      INTEGER (0..128)
    MAX-ACCESS  read-write
    STATUS      current
    DESCRIPTION
        "ont register number threshold, default 64."
    ::= { trapSetThreshold 3 }

edfaThresholdTable     OBJECT-TYPE
        SYNTAX      SEQUENCE OF EdfaThresholdEntry
        MAX-ACCESS  not-accessible
        STATUS      current
        DESCRIPTION
            "edfa threshold table"
        ::= { trapSetThreshold 4 }

edfaThresholdEntry   OBJECT-TYPE
        SYNTAX      EdfaThresholdEntry
        MAX-ACCESS  not-accessible
        STATUS      current
        DESCRIPTION
            "entry of edfa threshold table"
        INDEX { tntitInputId }
        ::= { edfaThresholdTable 1 }

EdfaThresholdEntry  ::= 
        SEQUENCE 
        {
            edfaTrapIndex         INTEGER,
            edfaTrapDescription   OCTET STRING,
            edfaTrapEnableSwitch  INTEGER,
            edfaThresholdLoLo     OCTET STRING,
            edfaThresholdLo       OCTET STRING,
            edfaThresholdHi       OCTET STRING,
            edfaThresholdHiHi     OCTET STRING
        }

edfaTrapIndex   OBJECT-TYPE    
    SYNTAX      INTEGER(1..11)
    MAX-ACCESS  read-only
    STATUS      current
    DESCRIPTION
        "The index of edfa trap, see gponTrapExtraInfo in edfaTrap description."
    ::= { edfaThresholdEntry 1 }

edfaTrapDescription   OBJECT-TYPE    
    SYNTAX      OCTET STRING (SIZE(0..255))
    MAX-ACCESS  read-only
    STATUS      current
    DESCRIPTION
        "The description of edfa trap, see gponTrapExtraInfo in edfaTrap description."
    ::= { edfaThresholdEntry 2 }

edfaTrapEnableSwitch   OBJECT-TYPE    
    SYNTAX      INTEGER(0..1)
    MAX-ACCESS  read-write
    STATUS      current
    DESCRIPTION
        "edfaTrapEnableSwitch:
        0  disable
        1  enable."
    ::= { edfaThresholdEntry 3 }

edfaThresholdLoLo   OBJECT-TYPE    
    SYNTAX      OCTET STRING (SIZE(0..16))
    MAX-ACCESS  read-write
    STATUS      current
    DESCRIPTION
        "edfa threshold lolo."
    ::= { edfaThresholdEntry 4 }

edfaThresholdLo   OBJECT-TYPE    
    SYNTAX      OCTET STRING (SIZE(0..16))
    MAX-ACCESS  read-write
    STATUS      current
    DESCRIPTION
        "edfa threshold lo."
    ::= { edfaThresholdEntry 5 }

edfaThresholdHi   OBJECT-TYPE    
    SYNTAX      OCTET STRING (SIZE(0..16))
    MAX-ACCESS  read-write
    STATUS      current
    DESCRIPTION
        "edfa threshold hi."
    ::= { edfaThresholdEntry 6 }

edfaThresholdHiHi   OBJECT-TYPE    
    SYNTAX      OCTET STRING (SIZE(0..16))
    MAX-ACCESS  read-write
    STATUS      current
    DESCRIPTION
        "edfa threshold hihi."
    ::= { edfaThresholdEntry 7 }

------ trapClearThreshold --------------------------------------
trapClearThreshold        OBJECT IDENTIFIER ::= { statusTrap 8 }


--------------------------------------------------------------
------------------ 3. oemTrue ------------------------------
--------------------------------------------------------------
trueXmlOntConfig         OBJECT IDENTIFIER ::= { oemTrue 1 }

txocSlotId OBJECT-TYPE
    SYNTAX INTEGER
    MAX-ACCESS read-write
    STATUS current
    DESCRIPTION
      "ont slot id. "
    ::= { trueXmlOntConfig 1 }

txocPportId OBJECT-TYPE
    SYNTAX INTEGER
    MAX-ACCESS read-write
    STATUS current
    DESCRIPTION
      "ont pport id. "
    ::= { trueXmlOntConfig 2 }

txocOntId OBJECT-TYPE
    SYNTAX INTEGER
    MAX-ACCESS read-write
    STATUS current
    DESCRIPTION
      "ont id. "
    ::= { trueXmlOntConfig 3 }

txocServerIp OBJECT-TYPE    
    SYNTAX      IpAddress
    MAX-ACCESS  read-write
    STATUS      current
    DESCRIPTION
        "xml tftp server ip address."
    ::= { trueXmlOntConfig 4 }

txocSn OBJECT-TYPE    
    SYNTAX      OCTET STRING (SIZE(0..255))
    MAX-ACCESS  read-write
    STATUS      current
    DESCRIPTION
        "xml sn."
    ::= { trueXmlOntConfig 5 }

txocCrc OBJECT-TYPE
    SYNTAX INTEGER
    MAX-ACCESS read-write
    STATUS current
    DESCRIPTION
      "xml crc. "
    ::= { trueXmlOntConfig 6 }

trueNameToIndex        OBJECT IDENTIFIER ::= { oemTrue 2 }
  -- 将模板名字转换成 index

tntiName        OBJECT-TYPE    
    SYNTAX      OCTET STRING (SIZE(0..255))
    MAX-ACCESS  read-write
    STATUS      current
    DESCRIPTION
        "profile name."
    ::= { trueNameToIndex 1 }

tntiType        OBJECT-TYPE    
    SYNTAX      INTEGER
    MAX-ACCESS  read-write
    STATUS      current
    DESCRIPTION
        "tntiType:
        1  dba
        2  vlan
        3  us traffic
        4  ds traffic
        5  line
        6  rule
        7  unique."
    ::= { trueNameToIndex 2 }

tntiStatus      OBJECT-TYPE    
    SYNTAX      INTEGER
    MAX-ACCESS  read-only
    STATUS      current
    DESCRIPTION
        "tntiStatus:
        1  exist
        2  not exist
        3  full(& not exist)."
    ::= { trueNameToIndex 3 }

tntiIndex       OBJECT-TYPE    
    SYNTAX      INTEGER
    MAX-ACCESS  read-only
    STATUS      current
    DESCRIPTION
        "1. if tntiStatus is 1(exist), tntiIndex is the index of tntiName.
         2. if tntiStatus is 2(not exist), tntiIndex is the index of an empty entry.
         3. if titiStatus is 3(full), tntiIndex is M_INVALID((ulong)-20)."
    ::= { trueNameToIndex 4 }

-- true name to index table ----------------------------------
trueNameToIndexTable     OBJECT-TYPE
        SYNTAX      SEQUENCE OF TrueNameToIndexEntry
        MAX-ACCESS  not-accessible
        STATUS      current
        DESCRIPTION
            "true name to index table"
        ::= { oemTrue 3 }

trueNameToIndexEntry   OBJECT-TYPE
        SYNTAX      TrueNameToIndexEntry
        MAX-ACCESS  not-accessible
        STATUS      current
        DESCRIPTION
            "entry of true name to index table"
        INDEX { tntitInputId }
        ::= { trueNameToIndexTable 1 }

TrueNameToIndexEntry  ::= 
        SEQUENCE 
        {
            tntitInputId       INTEGER,
            tntitName          OCTET STRING,
            tntitType          INTEGER,
            tntitStatus        INTEGER,
            tntitProfileId     INTEGER
        }

tntitInputId    OBJECT-TYPE    
    SYNTAX      INTEGER(0..4294967295)
    MAX-ACCESS  read-only
    STATUS      current
    DESCRIPTION
        "The index of socket, should in <0-4294967295>."
    ::= { trueNameToIndexEntry 1 }

tntitName       OBJECT-TYPE    
    SYNTAX      OCTET STRING (SIZE(0..255))
    MAX-ACCESS  read-write
    STATUS      current
    DESCRIPTION
        "profile name."
    ::= { trueNameToIndexEntry 2 }

tntitType       OBJECT-TYPE    
    SYNTAX      INTEGER
    MAX-ACCESS  read-write
    STATUS      current
    DESCRIPTION
        "tntiType:
        1  dba
        2  vlan
        3  us traffic
        4  ds traffic
        5  line
        6  rule
        7  unique."
    ::= { trueNameToIndexEntry 3 }

tntitStatus     OBJECT-TYPE    
    SYNTAX      INTEGER
    MAX-ACCESS  read-only
    STATUS      current
    DESCRIPTION
        "tntiStatus:
        1  exist
        2  not exist
        3  full(& not exist)."
    ::= { trueNameToIndexEntry 4 }

tntitProfileId  OBJECT-TYPE    
    SYNTAX      INTEGER
    MAX-ACCESS  read-only
    STATUS      current
    DESCRIPTION
        "1. if tntiStatus is 1(exist), tntitProfileId is the index of tntiName.
         2. if tntiStatus is 2(not exist), tntitProfileId is the index of an empty entry.
         3. if titiStatus is 3(full), tntitProfileId is M_INVALID((ulong)-20)."
    ::= { trueNameToIndexEntry 5 }

--------------------------------------------------------------
------------------ 4. gponSwitch --------------------------
--------------------------------------------------------------
gponUdld              OBJECT IDENTIFIER ::= { gponSwitch 1 }
gponPower             OBJECT IDENTIFIER ::= { gponSwitch 2 }
gponFan               OBJECT IDENTIFIER ::= { gponSwitch 3 }

-- gpon udld if table ----------------------------------
gponUdldIfTable     OBJECT-TYPE
        SYNTAX      SEQUENCE OF GponUdldIfEntry
        MAX-ACCESS  not-accessible
        STATUS      current
        DESCRIPTION
            "gpon udld if table"
        ::= { gponUdld 1 }

gponUdldIfEntry     OBJECT-TYPE
        SYNTAX      GponUdldIfEntry
        MAX-ACCESS  not-accessible
        STATUS      current
        DESCRIPTION
            "entry of gpon udld if table"
        INDEX { guIfSlotIndex, guIfEportIndex }
        ::= { gponUdldIfTable 1 }

GponUdldIfEntry  ::= 
        SEQUENCE 
        {
            guIfSlotIndex      INTEGER,
            guIfEportIndex     INTEGER,
            guIfWorkmode       INTEGER
        }

guIfSlotIndex   OBJECT-TYPE    
    SYNTAX      INTEGER(0..5)
    MAX-ACCESS  read-only
    STATUS      current
    DESCRIPTION
        "The index of slot, should in <0-5>."
    ::= { gponUdldIfEntry 1 }

guIfEportIndex  OBJECT-TYPE    
    SYNTAX      INTEGER(1..16)
    MAX-ACCESS  read-only
    STATUS      current
    DESCRIPTION
        "The index of eth port, should in <1-16>."
    ::= { gponUdldIfEntry 2 }

guIfWorkmode    OBJECT-TYPE    
    SYNTAX      INTEGER(0..1)
    MAX-ACCESS  read-write
    STATUS      current
    DESCRIPTION
        "guIfWorkmode: 
        0  normal
        1  aggressive."
    ::= { gponUdldIfEntry 3 }

guDelaydownTime OBJECT-TYPE
    SYNTAX INTEGER(1..5)
    MAX-ACCESS read-write
    STATUS current
    DESCRIPTION
      "udld delaydown-time, default 1(s). "
    ::= { gponUdld 2 }

-- gpon udld if table ----------------------------------
gponPowerTable      OBJECT-TYPE
        SYNTAX      SEQUENCE OF GponPowerEntry
        MAX-ACCESS  not-accessible
        STATUS      current
        DESCRIPTION
            "gpon power table"
        ::= { gponPower 1 }

gponPowerEntry      OBJECT-TYPE
        SYNTAX      GponPowerEntry
        MAX-ACCESS  not-accessible
        STATUS      current
        DESCRIPTION
            "entry of gpon power table"
        INDEX { powerIndex }
        ::= { gponPowerTable 1 }

GponPowerEntry  ::= 
        SEQUENCE 
        {
            powerIndex             INTEGER,
            powerInsertedStaus     INTEGER,
            powerRunningStatus     INTEGER
        }
    
powerIndex OBJECT-TYPE
    SYNTAX INTEGER {    
      power_0(0),
      power_1(1)
    }
    MAX-ACCESS read-only
    STATUS current
    DESCRIPTION 
      "Power index."
    ::= { gponPowerEntry 1 }
    
powerInsertedStaus OBJECT-TYPE
    SYNTAX INTEGER {
      empty(0),
      inserted(1)
    } 
    MAX-ACCESS read-only
    STATUS current
    DESCRIPTION
      "Power inserted status."
    ::= { gponPowerEntry 2 }
  
powerRunningStatus OBJECT-TYPE
    SYNTAX INTEGER {
      no_good(0),
      good(1)
    }
    MAX-ACCESS read-only 
    STATUS current
    DESCRIPTION 
      "Power running status."
    ::= { gponPowerEntry 3 }

gponFanInsertStatus OBJECT-TYPE
    SYNTAX INTEGER {
      empty(0),
      insert(1)
    }
    MAX-ACCESS read-only
    STATUS current
    DESCRIPTION
      "Fan insert status. "
    ::= { gponFan 1 }
    
gponFanTable      OBJECT-TYPE
        SYNTAX      SEQUENCE OF GponFanEntry
        MAX-ACCESS  not-accessible
        STATUS      current
        DESCRIPTION
            "gpon fan table"
        ::= { gponFan 2 }

gponFanEntry      OBJECT-TYPE
        SYNTAX      GponFanEntry
        MAX-ACCESS  not-accessible
        STATUS      current
        DESCRIPTION
            "entry of gpon fan table"
        INDEX { fanIndex }
        ::= { gponFanTable 1 }

GponFanEntry  ::= 
        SEQUENCE 
        {
            fanIndex             INTEGER,
            fanSpeed     INTEGER
        }
    
fanIndex OBJECT-TYPE
    SYNTAX INTEGER 
    MAX-ACCESS read-only
    STATUS current
    DESCRIPTION 
      "Fan index."
    ::= { gponFanEntry 1 }
    
fanSpeed OBJECT-TYPE
    SYNTAX INTEGER 
    MAX-ACCESS read-only
    STATUS current
    DESCRIPTION
      "Fan speed in rpm."
    ::= { gponFanEntry 2 }
END

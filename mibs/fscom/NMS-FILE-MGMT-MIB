NMS-FILE-MGMT-MIB  DEFINITIONS ::= BEGIN

	IMPORTS
        MODULE-IDENTITY,
        OBJECT-TYPE
            FROM SNMPv2-SMI
        
                  
        DisplayString
			FROM RFC1213-MIB
        nmsMgmt
            FROM NMS-SMI 
        DateAndTime
            FROM SNMPv2-TC;
                        
nmsFileMgmtMIB  MODULE-IDENTITY
        LAST-UPDATED    "201512020000Z"
        ORGANIZATION    ""
        CONTACT-INFO
                	""
			
        DESCRIPTION
                "           "
        ::= { nmsMgmt 185 }



--nmsIfObjects   OBJECT IDENTIFIER ::= { nmsIfMIB 1 }  

fileTransferManagement OBJECT-IDENTITY
STATUS current
DESCRIPTION
"
文件传输节点"
::= { nmsFileMgmtMIB 1 }
fileTransferTable OBJECT-TYPE
SYNTAX SEQUENCE OF FileTransferEntry
MAX-ACCESS not-accessible
STATUS current
DESCRIPTION
"
文件传输进程表"
::= { fileTransferManagement 1 }
fileTransferEntry OBJECT-TYPE
SYNTAX FileTransferEntry
MAX-ACCESS not-accessible
STATUS current
DESCRIPTION
" "
INDEX { fileTransferIndex }
::= { fileTransferTable 1 }
FileTransferEntry ::=
SEQUENCE {
fileTransferIndex
INTEGER,
fileTransferProtocolType
INTEGER,
serverIpAddress
IpAddress,
ftpUserName
DisplayString,
ftpUserPassword
DisplayString,
transferFileSrcNamePath
DisplayString,

transferFileDstNamePath
DisplayString,
transferAction
INTEGER,
transferStatus
INTEGER
}
fileTransferIndex OBJECT-TYPE
SYNTAX INTEGER (1..10)
MAX-ACCESS not-accessible
STATUS current
DESCRIPTION
"
文件传送进程流水号"
::= { fileTransferEntry 1 }
fileTransferProtocolType OBJECT-TYPE
SYNTAX INTEGER
{
ftp(1),
tftp(2)
}
MAX-ACCESS read-write
STATUS current
DESCRIPTION
"
该进程使用的文件传输协议类型"
::= { fileTransferEntry 2 }
serverIpAddress OBJECT-TYPE
SYNTAX IpAddress
MAX-ACCESS read-write
STATUS current
DESCRIPTION
"
该进程使用的服务器IP地址"
::= { fileTransferEntry 3 }
ftpUserName OBJECT-TYPE
SYNTAX DisplayString
MAX-ACCESS read-write
STATUS current

DESCRIPTION
"
该进程使用的用户名，仅适用于FTP协议"
::= { fileTransferEntry 4 }
ftpUserPassword OBJECT-TYPE
SYNTAX DisplayString
MAX-ACCESS read-write
STATUS current
DESCRIPTION
"
该进程使用的密码，仅适用于FTP协议"
::= { fileTransferEntry 5 }
transferFileSrcNamePath OBJECT-TYPE
SYNTAX DisplayString
MAX-ACCESS read-write
STATUS current
DESCRIPTION
"
该进程对应的文件源名称路径，比如‘/tftproot/file/image.bin"
::= { fileTransferEntry 6 }
transferFileDstNamePath OBJECT-TYPE
SYNTAX DisplayString
MAX-ACCESS read-write
STATUS current
DESCRIPTION
"
该进程对应的文件目的名称路径，比如‘/tftproot/file/image.bin"
::= { fileTransferEntry 7 }
transferAction OBJECT-TYPE
SYNTAX INTEGER
{
noOperation(1),
put(2),
get(3),
halt(4)
}
MAX-ACCESS read-write
STATUS current
DESCRIPTION

"
该进程对应的文件传输动作
noOperation(1) - 表示没有任何传输操作，用于默认设置和其他操作完成后恢复值
put(2) - 上传文件
get(3) - 下载文件
halt(4) - 停止文件传送"
::= { fileTransferEntry 8 }
transferStatus OBJECT-TYPE
SYNTAX INTEGER
{
idle(1),
inProgress(2),
success(3),
failure(4)
}
MAX-ACCESS read-only
STATUS current
DESCRIPTION
"
该进程对应的文件传输状态
idle(1) - 空闲
inProgress(2) - 正在传送中
success(3) - 传送成功
failure(4) - 传送失败"
::= { fileTransferEntry 9 }


fileInfoManagementTable OBJECT-TYPE
SYNTAX SEQUENCE OF FileInfoManagementEntry
MAX-ACCESS not-accessible
STATUS current
DESCRIPTION
"
OLT文件信息管理表
It is done by file list per directionary.
Please walk filePath for the file lists in the specified
path. If leave it NULL or walk fileInfoManagementEntry,
the file list of the root directionary shall be returned
"
::= { fileTransferManagement 2 }
fileInfoManagementEntry OBJECT-TYPE

SYNTAX FileInfoManagementEntry
MAX-ACCESS not-accessible
STATUS current
DESCRIPTION
" "
INDEX { filePath, fileName }
::= { fileInfoManagementTable 1 }
FileInfoManagementEntry ::=
SEQUENCE {
filePath
DisplayString,
fileName
DisplayString,
fileSize
Counter32,
fileModifyTime
DateAndTime,
fileManagementAction
INTEGER,
fileAttribute
INTEGER
}
filePath OBJECT-TYPE
SYNTAX DisplayString
MAX-ACCESS not-accessible
STATUS current
DESCRIPTION
"
File path
It shall be started with a length octet, followed with path string. The length octet
shall indicate the number of character octets, excluding length itself.
For example, 0x05 41 42 43 44 45, respresents ABCDE
It shall be ended with '/', which is used to distinguish the two DisplayString
indexes. For example, if the path is flash/root, filePath shall be set to flash/root/.
"
::= { fileInfoManagementEntry 1 }
fileName OBJECT-TYPE
SYNTAX DisplayString
MAX-ACCESS not-accessible

STATUS current
DESCRIPTION
"
File name. MUST not include '/' character and MUST not be NULL.
It shall be started with a length octet, followed with name string. The length octet
shall indicate the number of character octets, excluding length itself.
For example, 0x05 41 42 43 44 45, respresents ABCDE
"
::= { fileInfoManagementEntry 2 }
fileSize OBJECT-TYPE
SYNTAX Counter32
UNITS "bytes"
MAX-ACCESS read-only
STATUS current
DESCRIPTION
"
文件大小，以字节为单位"
::= { fileInfoManagementEntry 3 }
fileModifyTime OBJECT-TYPE
SYNTAX DateAndTime
MAX-ACCESS read-only
STATUS current
DESCRIPTION
"
文件修改时间"
::= { fileInfoManagementEntry 4 }
fileManagementAction OBJECT-TYPE
SYNTAX INTEGER
{
noOperation(1),
erase(2)
}
MAX-ACCESS read-write
STATUS current
DESCRIPTION
"
对文件施加的动作
noOperation(1) - 表示没有任何传输操作，用于默认设置和其他操作完成后恢复值
erase(2) - 文件删除"

::= { fileInfoManagementEntry 5 }
fileAttribute OBJECT-TYPE
SYNTAX INTEGER
{
file(1), -- It is a file
dir(2) -- It is a directionary
}
MAX-ACCESS read-only
STATUS current
DESCRIPTION
"
The attribute of the file"
::= { fileInfoManagementEntry 6 }



        
              
              
                 
END

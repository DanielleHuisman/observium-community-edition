NSCRTV-EPON-ONU-MIB DEFINITIONS ::= BEGIN

IMPORTS
    MODULE-IDENTITY, OBJECT-TYPE, Counter32, Unsigned32, TimeTicks
        FROM SNMPv2-SMI
    DateAndTime, MacAddress, TimeStamp, RowStatus, TruthValue, DisplayString, TEXTUAL-CONVENTION
        FROM SNMPv2-TC
    EponDeviceIndex, EponCardIndex, EponPortIndex, EponAlarmCode, EponAlarmInstance, EponSeverityType,
    AutoNegotiationTechAbility, TAddress, EponStats15MinRecordType, EponStats24HourRecordType, EponStatsThresholdType
		FROM NSCRTV-EPONEOC-EPON-MIB
    onuObjects
        FROM NSCRTV-EPONEOC-EPON-MIB;
        
--------------------------------------------------------------------------------
--  onuObjects[ONU属性管理项](1.3.6.1.4.1.17409.2.3.4)
--------------------------------------------------------------------------------  
    onuInfoTable  OBJECT-TYPE
        SYNTAX      SEQUENCE OF OnuInfoEntry
        MAX-ACCESS  not-accessible
        STATUS      current
        DESCRIPTION
            "A list of onuInfoTable entries. "
        ::= {onuObjects 1 }
        
    onuInfoEntry  OBJECT-TYPE
        SYNTAX      OnuInfoEntry
        MAX-ACCESS  not-accessible
        STATUS      current
        DESCRIPTION  
            "The onuInfoEntry Information"
        INDEX       { onuDeviceIndex }   
        ::={onuInfoTable 1 }   
        
    OnuInfoEntry ::= SEQUENCE {
        onuDeviceIndex              EponDeviceIndex, 
        onuName                     DisplayString,
        onuType                     INTEGER,
        onuIpAddress                IpAddress,
        onuIpSubnetMask             IpAddress,
        onuIpGateway                IpAddress,
        onuMacAddress               MacAddress,
        onuOperationStatus          INTEGER,
        onuAdminStatus              INTEGER,
        onuChipVendor               DisplayString,
        onuChipType                 DisplayString,
        onuChipVersion              DisplayString,
        onuSoftwareVersion          DisplayString,
        onuFirmwareVersion          DisplayString,
        onuTestDistance             INTEGER,
        onuLlidId                   INTEGER,
        resetONU                    INTEGER,
        onuTimeSinceLastRegister  Counter32,
        onuMgmtCvlan        INTEGER,
        onuMgmtSvlan        INTEGER,
        onuMgmtPriority       INTEGER,
        onuMgmtSnmpTrapHost     IpAddress,
        onuMgmtSnmpCommunityForRead   DisplayString,
        onuMgmtSnmpCommunityForWrite  DisplayString
      } 

    onuDeviceIndex  OBJECT-TYPE
        SYNTAX      EponDeviceIndex
        MAX-ACCESS  not-accessible
        STATUS      current
        DESCRIPTION
            "onuDevice Index"
        ::= {onuInfoEntry 1 }        
        
    onuName  OBJECT-TYPE
        SYNTAX      DisplayString
        MAX-ACCESS  read-write 
        STATUS      current
        DESCRIPTION
            "onu Name"
        ::= {onuInfoEntry 2 }   
        
    onuType  OBJECT-TYPE
        SYNTAX      INTEGER
          {
            fixed(1),
            chassisBased(2)
          }
        MAX-ACCESS  read-only 
        STATUS      current
        DESCRIPTION
            "onu Type            
            fixed(1)        - not slot concept
            chassisBased(2) - port is indexed by coupling slot ID"
        ::= {onuInfoEntry 3 }             
   
    onuIpAddress  OBJECT-TYPE
        SYNTAX      IpAddress
        MAX-ACCESS  read-write 
        STATUS      current
        DESCRIPTION
            "onu Ip Address"
        ::= {onuInfoEntry 4 }    
        
    onuIpSubnetMask  OBJECT-TYPE
        SYNTAX      IpAddress
        MAX-ACCESS  read-write 
        STATUS      current
        DESCRIPTION
            "onu Ip Subnet Mask"
        ::= {onuInfoEntry 5 }  
        
    onuIpGateway  OBJECT-TYPE
        SYNTAX      IpAddress
        MAX-ACCESS  read-write 
        STATUS      current
        DESCRIPTION
            "onu Ip Gateway"
        ::= {onuInfoEntry 6 }   
        
    onuMacAddress  OBJECT-TYPE
        SYNTAX      MacAddress
        MAX-ACCESS  read-only 
        STATUS      current
        DESCRIPTION
            "onuMac Address"
        ::= {onuInfoEntry 7 }  
        
    onuOperationStatus  OBJECT-TYPE
        SYNTAX      INTEGER {
        up(1),
        down(2),
        testing(3)
        }
        MAX-ACCESS  read-only 
        STATUS      current
        DESCRIPTION
            "onu Operation Status"
        ::= {onuInfoEntry 8 }   
        
    onuAdminStatus  OBJECT-TYPE
        SYNTAX      INTEGER {
        up(1),
        down(2),
        testing(3)
        }
        MAX-ACCESS  read-write 
        STATUS      current
        DESCRIPTION
            "onu Admin Status"
        ::= {onuInfoEntry 9 }      
        
    onuChipVendor  OBJECT-TYPE
        SYNTAX      DisplayString
        MAX-ACCESS  read-only 
        STATUS      current
        DESCRIPTION
            "onu Chip Vendor"
        ::= {onuInfoEntry 10 }     
        
    onuChipType  OBJECT-TYPE
        SYNTAX      DisplayString
        MAX-ACCESS  read-only 
        STATUS      current
        DESCRIPTION
            "onu Chip Type"
        ::= {onuInfoEntry 11 } 
        
    onuChipVersion  OBJECT-TYPE
        SYNTAX      DisplayString
        MAX-ACCESS  read-only 
        STATUS      current
        DESCRIPTION
            "onu Chip Version"
        ::= {onuInfoEntry 12 }   
        
    onuSoftwareVersion  OBJECT-TYPE
        SYNTAX      DisplayString
        MAX-ACCESS  read-only 
        STATUS      current
        DESCRIPTION
            "onu Software Version"
        ::= {onuInfoEntry 13 }    
        
    onuFirmwareVersion  OBJECT-TYPE
        SYNTAX      DisplayString
        MAX-ACCESS  read-only 
        STATUS      current
        DESCRIPTION
            "onu Firmware Version"
        ::= {onuInfoEntry 14 }     
     
    onuTestDistance  OBJECT-TYPE
        SYNTAX      INTEGER
        UNITS   "Meter"
        MAX-ACCESS  read-only 
        STATUS      current
        DESCRIPTION
            "onu Test Distance"
        ::= {onuInfoEntry 15 }  
        
    onuLlidId  OBJECT-TYPE
        SYNTAX      INTEGER
        MAX-ACCESS  read-only 
        STATUS      current
        DESCRIPTION
            "onu Llid Id"
        ::= {onuInfoEntry 16 }     
        
    resetONU  OBJECT-TYPE
        SYNTAX      INTEGER { reset(1) }
        MAX-ACCESS  read-write 
        STATUS      current
        DESCRIPTION
            "reset ONU"
        ::= {onuInfoEntry 17 }   
    
    onuTimeSinceLastRegister  OBJECT-TYPE
        SYNTAX      Counter32
        UNITS   "seconds"
        MAX-ACCESS  read-only 
        STATUS      current
        DESCRIPTION
            "The number of seconds, since the time when the ONU is registered"
        ::= {onuInfoEntry 18 }        

    onuMgmtCvlan  OBJECT-TYPE
        SYNTAX      INTEGER
        MAX-ACCESS  read-write 
        STATUS      current
        DESCRIPTION
            "CVLAN ID of management data for the ONU"
        ::= {onuInfoEntry 19 }  

    onuMgmtSvlan  OBJECT-TYPE
        SYNTAX      INTEGER
        MAX-ACCESS  read-write 
        STATUS      optional
        DESCRIPTION
            "SVLAN ID of management data for the ONU
            Set to 0, means only single VLAN is supported, no SVLAN concept,
            for the ONU management"
        ::= {onuInfoEntry 20 } 

    onuMgmtPriority  OBJECT-TYPE
        SYNTAX      INTEGER (0..7)
        MAX-ACCESS  read-write 
        STATUS      optional
        DESCRIPTION
            "Tagged dot1p priority of management data for the ONU"
        ::= {onuInfoEntry 21 }
    onuMgmtSnmpTrapHost  OBJECT-TYPE
        SYNTAX      IpAddress
        MAX-ACCESS  read-write 
        STATUS      current
        DESCRIPTION
            "The host IP address, to which the ONU will send trap."
        ::= {onuInfoEntry 22 }

    onuMgmtSnmpCommunityForRead  OBJECT-TYPE
        SYNTAX      DisplayString
        MAX-ACCESS  read-write 
        STATUS      current
        DESCRIPTION
            "The read SNMP community to the ONU."
        ::= {onuInfoEntry 23 }
   
    onuMgmtSnmpCommunityForWrite  OBJECT-TYPE
        SYNTAX      DisplayString
        MAX-ACCESS  read-write 
        STATUS      current
        DESCRIPTION
            "The write SNMP community to the ONU."
        ::= {onuInfoEntry 24 }
           
    onuPonPortOpticalTransmissionPropertyTable  OBJECT-TYPE
        SYNTAX      SEQUENCE OF OnuPonPortOpticalTransmissionPropertyEntry
        MAX-ACCESS  not-accessible
        STATUS      current
        DESCRIPTION
            "
            This table is designed for both OLT and ONU 
        Applied Obj  - Descriptions of Index
      ------------------------------------------------------------------
        OLT      - OnuNum of EponDeviceIndex TC shall be set to 0,
                 onuPonPortOpticalTransmissionPropertyCardIndex, and 
                 onuPonPortOpticalTransmissionPropertyPortIndex set to 
                 65535 indicates meaningless
        ONU      - Set EponDeviceIndex TC to corresponding ONU ID,
                   onuPonPortOpticalTransmissionPropertyCardIndex, and 
                   onuPonPortOpticalTransmissionPropertyPortIndex set to the 
                   corresponding value
      "
        ::= {onuObjects 2 }
        
    onuPonPortOpticalTransmissionPropertyEntry  OBJECT-TYPE
        SYNTAX      OnuPonPortOpticalTransmissionPropertyEntry
        MAX-ACCESS  not-accessible
        STATUS      current
        DESCRIPTION  
            "The onuPonPortOpticalTransmissionPropertyEntry Information"
        INDEX       { onuPonPortOpticalTransmissionPropertyDeviceIndex, onuPonPortOpticalTransmissionPropertyCardIndex,onuPonPortOpticalTransmissionPropertyPortIndex }   
        ::={onuPonPortOpticalTransmissionPropertyTable 1 }   
        
    OnuPonPortOpticalTransmissionPropertyEntry ::= SEQUENCE {
        onuPonPortOpticalTransmissionPropertyDeviceIndex     EponDeviceIndex,  
        onuPonPortOpticalTransmissionPropertyCardIndex       INTEGER,
        onuPonPortOpticalTransmissionPropertyPortIndex       INTEGER,        
        onuReceivedOpticalPower                              INTEGER,
        onuTramsmittedOpticalPower                           INTEGER,
        onuBiasCurrent                                       INTEGER,
        onuWorkingVoltage                                    INTEGER,
        onuWorkingTemperature                                INTEGER     
      } 

    onuPonPortOpticalTransmissionPropertyDeviceIndex  OBJECT-TYPE
        SYNTAX      EponDeviceIndex
        MAX-ACCESS  not-accessible
        STATUS      current
        DESCRIPTION
            "Device Index of the ONU."
        ::= {onuPonPortOpticalTransmissionPropertyEntry 1 }      
 
     onuPonPortOpticalTransmissionPropertyCardIndex  OBJECT-TYPE
        SYNTAX      INTEGER
        MAX-ACCESS  not-accessible
        STATUS      current
        DESCRIPTION
            "Card Index in the ONU. Shall set to 0, if ONU is not a modulized 
            device"
        ::= {onuPonPortOpticalTransmissionPropertyEntry 2 }  
        
    onuPonPortOpticalTransmissionPropertyPortIndex  OBJECT-TYPE
        SYNTAX      INTEGER
        MAX-ACCESS  not-accessible
        STATUS      current
        DESCRIPTION
            "Port Index in the Pon card of ONU"
        ::= {onuPonPortOpticalTransmissionPropertyEntry 3 }          
    onuReceivedOpticalPower  OBJECT-TYPE
        SYNTAX      INTEGER
        UNITS   "centi-dBm"
        MAX-ACCESS  read-only 
        STATUS      current
        DESCRIPTION
            "received Optical Power"
        ::= {onuPonPortOpticalTransmissionPropertyEntry 4 }    
        
    onuTramsmittedOpticalPower  OBJECT-TYPE
        SYNTAX      INTEGER
        UNITS   "centi-dBm"
        MAX-ACCESS  read-only 
        STATUS      current
        DESCRIPTION
            "tramsmitted Optical Power"
        ::= {onuPonPortOpticalTransmissionPropertyEntry 5 }               
        
    onuBiasCurrent  OBJECT-TYPE
        SYNTAX      INTEGER
        UNITS   "centi-mA"
        MAX-ACCESS  read-only 
        STATUS      current
        DESCRIPTION
            "biasCurrent"
        ::= {onuPonPortOpticalTransmissionPropertyEntry 6 }  

    onuWorkingVoltage  OBJECT-TYPE
        SYNTAX      INTEGER
        UNITS   "centi-mV"
        MAX-ACCESS  read-only 
        STATUS      current
        DESCRIPTION
            "onuworking Voltage"
        ::= {onuPonPortOpticalTransmissionPropertyEntry 7 }  
        
    onuWorkingTemperature  OBJECT-TYPE
        SYNTAX      INTEGER
        UNITS   "Centi-degree centigrade"
       MAX-ACCESS  read-only 
        STATUS      current
        DESCRIPTION
            "working Temperature"
        ::= {onuPonPortOpticalTransmissionPropertyEntry 8 } 
          
    onuCapabilityTable  OBJECT-TYPE
        SYNTAX      SEQUENCE OF OnuCapabilityEntry
        MAX-ACCESS  not-accessible
        STATUS      current
        DESCRIPTION
            "A list of onuInfoTable entries. "
        ::= {onuObjects 3 }
        
    onuCapabilityEntry  OBJECT-TYPE
        SYNTAX      OnuCapabilityEntry
        MAX-ACCESS  not-accessible
        STATUS      current
        DESCRIPTION  
            "The onuCapabilityEntry Information"
        INDEX       { onuCapabilityDeviceIndex }   
        ::={onuCapabilityTable 1 }   
        
    OnuCapabilityEntry ::= SEQUENCE {   
        onuCapabilityDeviceIndex     EponDeviceIndex,   
        onuGePortNum                 INTEGER,
        onuGePortBitmap              OCTET STRING,
        onuFePortNum                 INTEGER,
        onuFePortBitmap              OCTET STRING,
        onuQueueNumUplink            INTEGER,    
        onuMaxQueueNumUplink         INTEGER,    
        onuQueueNumDownlink          INTEGER,    
        onuMaxQueueNumDownlink       INTEGER,    
        onuFecEnable                 TruthValue,    
        onuEncryptMode               INTEGER,    
        onuEncryptKeyExchangeTime    TimeTicks
      } 
       
    onuCapabilityDeviceIndex  OBJECT-TYPE
        SYNTAX      EponDeviceIndex
        MAX-ACCESS  not-accessible
        STATUS      current
        DESCRIPTION
            "onu Device Index"
        ::= {onuCapabilityEntry 1 }   
        
    onuGePortNum  OBJECT-TYPE
        SYNTAX      INTEGER
        MAX-ACCESS  read-only 
        STATUS      current
        DESCRIPTION
            "gePort Num"
        ::= {onuCapabilityEntry 2 }    

    onuGePortBitmap  OBJECT-TYPE
        SYNTAX      OCTET STRING
        MAX-ACCESS  read-only 
        STATUS      current
        DESCRIPTION
            "gePort Bitmap
            
            In slot+port pair list manner. Suppose each slot support up to 64 ports.
            One octet to indentify slot and 8 octets to identify portbitmap for
            the slot. The bitmap definition is internet sequence. The most left bit 
            is for port 1 of the slot, the most right bit is for port 64 of the slot.            
            If the slot cannot support 64 ports, set the bits of not supported ports
            to 0.            
            If the port is GE port, set the corresponding bit to 1.                 
            Since the slot num depends on each individual device, the object is variable
            length. If the device is fixed box (not modulized), set the slot number to 
            255. Then the network management system could ignore the slot info.            
            It is not necessary to list the slot doesn't support GE port.                        
            For example, if have 4 GE ports, of: 1/4, 1/6, 2/3, 4/17,
            the object will be presented in:
            01 14 00 00 00 00 00 00 00
            02 20 00 00 00 00 00 00 00
            04 00 00 80 00 00 00 00 00            
            Another example, for fixed box, if have 4 ge ports of 4,6,10,17, the object
            will be presented as:
            FF 14 40 10 00 00 00 00
            "
        ::= {onuCapabilityEntry 3 }  
        
    onuFePortNum  OBJECT-TYPE
        SYNTAX      INTEGER
        MAX-ACCESS  read-only 
        STATUS      current
        DESCRIPTION
            "fePort Num"
        ::= {onuCapabilityEntry 4 }    
        
    onuFePortBitmap  OBJECT-TYPE
        SYNTAX      OCTET STRING
        MAX-ACCESS  read-only 
        STATUS      current
        DESCRIPTION
            "fePort Bitmap
            
            In slot+port pair list manner. Suppose each slot support up to 64 ports.
            One octet to indentify slot and 8 octets to identify portbitmap for
            the slot. The bitmap definition is internet sequence. The most left bit 
            is for port 1 of the slot, the most right bit is for port 64 of the slot.            
            If the slot cannot support 64 ports, set the bits of not supported ports
            to 0.            
            If the port is FE port, set the corresponding bit to 1.                 
            Since the slot num depends on each individual device, the object is variable
            length. If the device is fixed box (not modulized), set the slot number to 
            255. Then the network management system could ignore the slot info.            
            It is not necessary to list the slot doesn't support FE port.                        
            For example, if have 4 FE ports, of: 1/4, 1/6, 2/3, 4/17,
            the object will be presented in:
            01 14 00 00 00 00 00 00 00
            02 20 00 00 00 00 00 00 00
            04 00 00 80 00 00 00 00 00            
            Another example, for fixed box, if have 4 FE ports of 4,6,10,17, the object
            will be presented as:
            FF 14 40 10 00 00 00 00
            "
        ::= {onuCapabilityEntry 5 }     
        
    onuQueueNumUplink  OBJECT-TYPE
        SYNTAX      INTEGER
        MAX-ACCESS  read-only 
        STATUS      current
        DESCRIPTION
            "queue Num Uplink"
        ::= {onuCapabilityEntry 6 }     
        
    onuMaxQueueNumUplink  OBJECT-TYPE
        SYNTAX      INTEGER
        MAX-ACCESS  read-only 
        STATUS      current
        DESCRIPTION
            "max Queue Num Uplink"
        ::= {onuCapabilityEntry 7 }  
        
    onuQueueNumDownlink  OBJECT-TYPE
        SYNTAX      INTEGER
        MAX-ACCESS  read-only 
        STATUS      current
        DESCRIPTION
            "queue Num Downlink"
        ::= {onuCapabilityEntry 8 }  
        
    onuMaxQueueNumDownlink  OBJECT-TYPE
        SYNTAX      INTEGER
        MAX-ACCESS  read-only 
        STATUS      current
        DESCRIPTION
            "max Queue Num Downlink"
        ::= {onuCapabilityEntry 9 }    
        
     onuFecEnable  OBJECT-TYPE
        SYNTAX      TruthValue
        MAX-ACCESS  read-write 
        STATUS      current
        DESCRIPTION
            "fec Enable"
        ::= {onuCapabilityEntry 10 }  
        
    onuEncryptMode  OBJECT-TYPE
        SYNTAX      INTEGER {
                aes128(1),
                ctcTripleChurning(2),
                other(3)
                       }
        MAX-ACCESS  read-only 
        STATUS      current
        DESCRIPTION
            "encrypt Mode"
        ::= {onuCapabilityEntry 11 }    
        
    onuEncryptKeyExchangeTime  OBJECT-TYPE
        SYNTAX      TimeTicks
        MAX-ACCESS  read-only 
        STATUS      current
        DESCRIPTION
            "encryptKeyExchange Time"
        ::= {onuCapabilityEntry 12 }                                                                                                    


    slaTable  OBJECT-TYPE
        SYNTAX      SEQUENCE OF SlaEntry
        MAX-ACCESS  not-accessible
        STATUS      current
        DESCRIPTION
            "A list of slaTable entries. "
        ::= {onuObjects 4 }
        
    slaEntry  OBJECT-TYPE
        SYNTAX      SlaEntry
        MAX-ACCESS  not-accessible
        STATUS      current
        DESCRIPTION  
            "The slaEntry Information"
        INDEX       { slaIndex }   
        ::={slaTable 1 }   
        
    SlaEntry ::= SEQUENCE {
        slaIndex               EponDeviceIndex,  
        slaDsFixedBW             INTEGER,
        slaDsPeakBW              INTEGER,
        slaDsCommittedBW         INTEGER,  
        slaUsFixedBW             INTEGER,
        slaUsPeakBW              INTEGER,
        slaUsCommittedBW         INTEGER              
      } 
     
    slaIndex  OBJECT-TYPE
        SYNTAX      EponDeviceIndex
        MAX-ACCESS  not-accessible
        STATUS      current
        DESCRIPTION
            "sla Index"
        ::= {slaEntry 1 }  
         
    slaDsFixedBW  OBJECT-TYPE
        SYNTAX      INTEGER
        UNITS   "kbps"
        MAX-ACCESS  read-write 
        STATUS      current
        DESCRIPTION
            "Downstream sla FixedBW"
        ::= {slaEntry 2 }  
        
    slaDsPeakBW  OBJECT-TYPE
        SYNTAX      INTEGER
        UNITS   "kbps"
        MAX-ACCESS  read-write 
        STATUS      current
        DESCRIPTION
            "Downstream sla PeakBW"
        ::= {slaEntry 3 }    
        
    slaDsCommittedBW  OBJECT-TYPE
        SYNTAX      INTEGER
        UNITS   "kbps"
        MAX-ACCESS  read-write 
        STATUS      current
        DESCRIPTION
            "Downstream sla CommittedBW"
        ::= {slaEntry 4 }                               
 
    slaUsFixedBW  OBJECT-TYPE
        SYNTAX      INTEGER
        UNITS   "kbps"
        MAX-ACCESS  read-write 
        STATUS      current
        DESCRIPTION
            "Upstream sla FixedBW"
        ::= {slaEntry 5 }  
        
    slaUsPeakBW  OBJECT-TYPE
        SYNTAX      INTEGER
        UNITS   "kbps"
        MAX-ACCESS  read-write 
        STATUS      current
        DESCRIPTION
            "Upstream sla PeakBW"
        ::= {slaEntry 6 }    
        
    slaUsCommittedBW  OBJECT-TYPE
        SYNTAX      INTEGER
        UNITS   "kbps"
        MAX-ACCESS  read-write 
        STATUS      current
        DESCRIPTION
            "Upstream sla CommittedBW"
        ::= {slaEntry 7 }
        

  onuAuthenticationManagement OBJECT-IDENTITY
    STATUS current
    DESCRIPTION 
      ""
    ::= { onuObjects 5 }

onuAuthenticationPolicy  OBJECT-TYPE
        SYNTAX      INTEGER{
                     acceptAll(1),
                     rejectNotConfigured(2)
                     }          
        MAX-ACCESS  read-write
        STATUS      current
        DESCRIPTION
            "
            Define the behavior on the auth policy            
            acceptAll(1) - Disable ONU authentication, all ONU could register
                           to OLT
            rejectNotConfigured(2) - Only the relationship b/w ONU ID and MAC address defined
                     in onuAuthenticationPreConfigTable could register to OLT.
            "
        ::= {onuAuthenticationManagement 1 }  
          
        
    onuAuthenticationPreConfigTable  OBJECT-TYPE
        SYNTAX      SEQUENCE OF OnuAuthenticationPreConfigEntry
        MAX-ACCESS  not-accessible
        STATUS      current
        DESCRIPTION
            "A list of onuAuthenticationPreConfigTable entries. "
        ::= {onuAuthenticationManagement 2 }
        
    onuAuthenticationPreConfigEntry  OBJECT-TYPE
        SYNTAX      OnuAuthenticationPreConfigEntry
        MAX-ACCESS  not-accessible
        STATUS      current
        DESCRIPTION  
            "The onuAuthenticationPreConfigEntry Information"
        INDEX       { onuAuthenOnuId }   
        ::={onuAuthenticationPreConfigTable 1 }   
        
    OnuAuthenticationPreConfigEntry ::= SEQUENCE {
        onuAuthenOnuId                            EponDeviceIndex,  
        onuAuthenMacAddress                       MacAddress,
        onuAuthenAction                           INTEGER,
        onuAuthenRowStatus                        INTEGER
      } 
         

    onuAuthenOnuId  OBJECT-TYPE
        SYNTAX      EponDeviceIndex
        MAX-ACCESS  not-accessible
        STATUS      current
        DESCRIPTION
            "onu logical ID"
        ::= {onuAuthenticationPreConfigEntry 1 } 

    onuAuthenMacAddress  OBJECT-TYPE
        SYNTAX      MacAddress
        MAX-ACCESS  read-create 
        STATUS      current
        DESCRIPTION
            "onu Mac Address"
        ::= {onuAuthenticationPreConfigEntry 2 }   
        
    onuAuthenAction  OBJECT-TYPE
        SYNTAX      INTEGER {
                accept(1),
                reject(2)
                  }
        MAX-ACCESS  read-create 
        STATUS      current
        DESCRIPTION
            "Authen Action
            
            This is optional in function"
        ::= {onuAuthenticationPreConfigEntry 3 } 

    onuAuthenRowStatus  OBJECT-TYPE
        SYNTAX      INTEGER
        MAX-ACCESS  read-create 
        STATUS      current
        DESCRIPTION
            "authen Row Status"
        ::= {onuAuthenticationPreConfigEntry 4 }
          
    onuAuthenticationBlockTable  OBJECT-TYPE
        SYNTAX      SEQUENCE OF OnuAuthenticationBlockEntry
        MAX-ACCESS  not-accessible
        STATUS      current
        DESCRIPTION
            "A list of onuAuthenticationBlockTable entries. "
        ::= {onuAuthenticationManagement 3 }
        
    onuAuthenticationBlockEntry  OBJECT-TYPE
        SYNTAX      OnuAuthenticationBlockEntry
        MAX-ACCESS  not-accessible
        STATUS      current
        DESCRIPTION  
            "The onuAuthenticationBlockEntry Information"
        INDEX       { onuAuthenBlockOnuId }   
        ::={onuAuthenticationBlockTable 1 }   
        
    OnuAuthenticationBlockEntry ::= SEQUENCE {
        onuAuthenBlockOnuId                   EponDeviceIndex,
        onuAuthenBlockMacAddress              MacAddress,
        authenTime                            TimeTicks     
      }    
        
       
    onuAuthenBlockOnuId  OBJECT-TYPE
        SYNTAX      EponDeviceIndex
        MAX-ACCESS  not-accessible
        STATUS      current
        DESCRIPTION
            "ONU Id"
        ::= {onuAuthenticationBlockEntry 1 }   
        
    onuAuthenBlockMacAddress  OBJECT-TYPE
        SYNTAX      MacAddress
        MAX-ACCESS  read-only
        STATUS      current
        DESCRIPTION
            "Mac Address"
        ::= {onuAuthenticationBlockEntry 2 }  
        
    authenTime  OBJECT-TYPE
        SYNTAX      TimeTicks
        MAX-ACCESS  read-only
        STATUS      current
        DESCRIPTION
            "authen Time"
        ::= {onuAuthenticationBlockEntry 3 }   
        
-------------------------------onu qos------------------------------
    onuClassificationEntryTable  OBJECT-TYPE
        SYNTAX      SEQUENCE OF onuClassificationEntry
        MAX-ACCESS  not-accessible
        STATUS      current
        DESCRIPTION
            "A list of onuClassificationEntryTable   entries. "
        ::= { onuObjects 6 }
        
    onuClassificationEntry  OBJECT-TYPE
        SYNTAX      onuClassificationEntry
        MAX-ACCESS  not-accessible
        STATUS      current
        DESCRIPTION  
            "The onuClassificationEntry Information"
        INDEX   { onuClassificationDeviceIndex,onuClassificationCardIndex,uniClassificationPortIndex,onuClassificationRuleIndex }   
        ::={ onuClassificationEntryTable   1 }   
        
    onuClassificationEntry ::= SEQUENCE {
        onuClassificationDeviceIndex          EponDeviceIndex,
        onuClassificationCardIndex            EponCardIndex,
        uniClassificationPortIndex            EponPortIndex,
        onuClassificationRuleIndex            INTEGER,
        onuClassificationPrecedence           INTEGER,
        onuClassificationDestQueue            INTEGER,
        onuClassificationPriMarking           INTEGER,
        onuClassificationClause1Flag           INTEGER,
        onuClassificationClause1FieldSelect    INTEGER,
        onuClassificationClause1Operator       INTEGER,
        onuClassificationClause1Value          OCTET STRING,
        onuClassificationClause2Flag           INTEGER,
        onuClassificationClause2FieldSelect    INTEGER,
        onuClassificationClause2Operator       INTEGER,
        onuClassificationClause2Value          OCTET STRING,
        onuClassificationClause3Flag           INTEGER,
        onuClassificationClause3FieldSelect    INTEGER,
        onuClassificationClause3Operator       INTEGER,
        onuClassificationClause3Value          OCTET STRING,
        onuClassificationClause4Flag           INTEGER,
        onuClassificationClause4FieldSelect    INTEGER,
        onuClassificationClause4Operator       INTEGER,
        onuClassificationClause4Value          OCTET STRING,
        onuClassificationClause5Flag           INTEGER,
        onuClassificationClause5FieldSelect    INTEGER,
        onuClassificationClause5Operator       INTEGER,
        onuClassificationClause5Value          OCTET STRING,
        onuClassificationClause6Flag           INTEGER,  
        onuClassificationClause6FieldSelect    INTEGER,
        onuClassificationClause6Operator       INTEGER,
        onuClassificationClause6Value          OCTET STRING,
        onuClassificationClause7Flag           INTEGER,
        onuClassificationClause7FieldSelect    INTEGER,
        onuClassificationClause7Operator       INTEGER,
        onuClassificationClause7Value          OCTET STRING,
        onuClassificationClause8Flag           INTEGER,    
        onuClassificationClause8FieldSelect    INTEGER,    
        onuClassificationClause8Operator       INTEGER,    
        onuClassificationClause8Value          OCTET STRING,
        OnuClassificationRowStatus                  INTEGER
        }
       
    onuClassificationDeviceIndex          OBJECT-TYPE
        SYNTAX      EponDeviceIndex
        MAX-ACCESS  not-accessible
        STATUS      current
        DESCRIPTION
            "设备索引 "
        ::= { onuClassificationEntry   1 }   
        
    onuClassificationCardIndex            OBJECT-TYPE
        SYNTAX      EponCardIndex
        MAX-ACCESS  not-accessible
        STATUS      current
        DESCRIPTION
            "板卡索引"
        ::= { onuClassificationEntry  2 }  

    uniClassificationPortIndex            OBJECT-TYPE
        SYNTAX      EponPortIndex
        MAX-ACCESS  not-accessible
        STATUS      current
        DESCRIPTION
            "端口索引"
        ::= { onuClassificationEntry  3 }  

    onuClassificationRuleIndex            OBJECT-TYPE
        SYNTAX      INTEGER (1..8)
        MAX-ACCESS  not-accessible
        STATUS      current
        DESCRIPTION
            "规则索引号"
        ::= { onuClassificationEntry  4 }

    onuClassificationPrecedence           OBJECT-TYPE
        SYNTAX      INTEGER (1..8)
        MAX-ACCESS  read-create
        STATUS      current
        DESCRIPTION
            "规则优先级"
        ::= { onuClassificationEntry  5 }
   
    onuClassificationDestQueue            OBJECT-TYPE
        SYNTAX      INTEGER  (1..4)
        MAX-ACCESS  read-create
        STATUS      current
        DESCRIPTION
            "目标优先级队列"
        ::= { onuClassificationEntry  6 }

    onuClassificationPriMarking           OBJECT-TYPE
        SYNTAX      INTEGER  (0..7)
        MAX-ACCESS  read-create
        STATUS      current
        DESCRIPTION
            "优先级标签"
        ::= { onuClassificationEntry  7 }

    onuClassificationClause1Flag           OBJECT-TYPE
        SYNTAX      INTEGER(1..2)
        MAX-ACCESS  read-create
        STATUS      current
        DESCRIPTION
            "是否有效,1:有效 2：无效"
        ::= { onuClassificationEntry  8 }

    onuClassificationClause1FieldSelect    OBJECT-TYPE
        SYNTAX      INTEGER
        MAX-ACCESS read-create
        STATUS      current
        DESCRIPTION
            "规则类型，0：基于源mac  1：基于目的mac  2：基于vlanid  3：基于以太网类型   4：基于源ip  5：基于目的ip  6：基于ip
协议类型  7：基于TOS/DSCP 
8：基于L4源端口   9：基于L4目的端口"
        ::= { onuClassificationEntry  9 }

   onuClassificationClause1Operator       OBJECT-TYPE
        SYNTAX      INTEGER
        MAX-ACCESS  read-create
        STATUS      current
        DESCRIPTION
            "操作符，1：等于  2：不等于  3：小于等于 4：大于等于  5：存在即匹配6：不存在即匹配    7：总匹配"
        ::= { onuClassificationEntry  10 }

    onuClassificationClause1Value          OBJECT-TYPE
        SYNTAX      OCTET STRING (SIZE (6))
        MAX-ACCESS  read-create
        STATUS      current
        DESCRIPTION
            "内容"
        ::= { onuClassificationEntry  11 }

    onuClassificationClause2Flag           OBJECT-TYPE
        SYNTAX      INTEGER(1..2)
        MAX-ACCESS  read-create
        STATUS      current
        DESCRIPTION
            "是否有效,1:有效 2：无效"
        ::= { onuClassificationEntry  12 }

    onuClassificationClause2FieldSelect    OBJECT-TYPE
        SYNTAX      INTEGER
        MAX-ACCESS read-create
        STATUS      current
        DESCRIPTION
            "规则类型，0：基于源mac  1：基于目的mac  2：基于vlanid  3：基于以太网类型   4：基于源ip  5：基于目的ip  6：基于ip
协议类型  7：基于TOS/DSCP 
8：基于L4源端口   9：基于L4目的端口"
        ::= { onuClassificationEntry  13 }

   onuClassificationClause2Operator       OBJECT-TYPE
        SYNTAX      INTEGER
        MAX-ACCESS  read-create
        STATUS      current
        DESCRIPTION
            "操作符，1：等于  2：不等于  3：小于等于 4：大于等于  5：存在即匹配6：不存在即匹配    7：总匹配"
        ::= { onuClassificationEntry  14 }

    onuClassificationClause2Value          OBJECT-TYPE
        SYNTAX      OCTET STRING (SIZE (6))
        MAX-ACCESS  read-create
        STATUS      current
        DESCRIPTION
            "内容"
        ::= { onuClassificationEntry  15 }

    onuClassificationClause3Flag           OBJECT-TYPE
        SYNTAX      INTEGER(1..2)
        MAX-ACCESS  read-create
        STATUS      current
        DESCRIPTION
            "是否有效,1:有效 2：无效"
        ::= { onuClassificationEntry  16 }

    onuClassificationClause3FieldSelect    OBJECT-TYPE
        SYNTAX      INTEGER
        MAX-ACCESS read-create
        STATUS      current
        DESCRIPTION
            "规则类型，0：基于源mac  1：基于目的mac  2：基于vlanid  3：基于以太网类型   4：基于源ip  5：基于目的ip  6：基于ip
协议类型  7：基于TOS/DSCP 
8：基于L4源端口   9：基于L4目的端口"
        ::= { onuClassificationEntry  17 }

   onuClassificationClause3Operator       OBJECT-TYPE
        SYNTAX      INTEGER
        MAX-ACCESS  read-create
        STATUS      current
        DESCRIPTION
            "操作符，1：等于  2：不等于  3：小于等于 4：大于等于  5：存在即匹配6：不存在即匹配    7：总匹配"
        ::= { onuClassificationEntry  18 }

    onuClassificationClause3Value          OBJECT-TYPE
        SYNTAX      OCTET STRING (SIZE (6))
        MAX-ACCESS  read-create
        STATUS      current
        DESCRIPTION
            "内容"
        ::= { onuClassificationEntry  19 }

    onuClassificationClause4Flag           OBJECT-TYPE
        SYNTAX      INTEGER(1..2)
        MAX-ACCESS  read-create
        STATUS      current
        DESCRIPTION
            "是否有效,1:有效 2：无效"
        ::= { onuClassificationEntry  20 }

    onuClassificationClause4FieldSelect    OBJECT-TYPE
        SYNTAX      INTEGER
        MAX-ACCESS read-create
        STATUS      current
        DESCRIPTION
            "规则类型，0：基于源mac  1：基于目的mac  2：基于vlanid  3：基于以太网类型   4：基于源ip  5：基于目的ip  6：基于ip

协议类型  7：基于TOS/DSCP 
8：基于L4源端口   9：基于L4目的端口"
        ::= { onuClassificationEntry  21 }

    onuClassificationClause4Operator       OBJECT-TYPE
        SYNTAX      INTEGER
        MAX-ACCESS  read-create
        STATUS      current
        DESCRIPTION
            "操作符，1：等于  2：不等于  3：小于等于 4：大于等于  5：存在即匹配6：不存在即匹配    7：总匹配"
        ::= { onuClassificationEntry  22 }

    onuClassificationClause4Value          OBJECT-TYPE
        SYNTAX      OCTET STRING (SIZE (6))
        MAX-ACCESS  read-create
        STATUS      current
        DESCRIPTION
            "内容"
        ::= { onuClassificationEntry  23 }

    onuClassificationClause5Flag           OBJECT-TYPE
        SYNTAX      INTEGER(1..2)
        MAX-ACCESS  read-create
        STATUS      current
        DESCRIPTION
            "是否有效,1:有效 2：无效"
        ::= { onuClassificationEntry  24 }

    onuClassificationClause5FieldSelect    OBJECT-TYPE
        SYNTAX      INTEGER
        MAX-ACCESS read-create
        STATUS      current
        DESCRIPTION
            "规则类型，0：基于源mac  1：基于目的mac  2：基于vlanid  3：基于以太网类型   4：基于源ip  5：基于目的ip  6：基于ip
协议类型  7：基于TOS/DSCP 
8：基于L4源端口   9：基于L4目的端口"
        ::= { onuClassificationEntry  25 }

   onuClassificationClause5Operator       OBJECT-TYPE
        SYNTAX      INTEGER
        MAX-ACCESS  read-create
        STATUS      current
        DESCRIPTION
            "操作符，1：等于  2：不等于  3：小于等于 4：大于等于  5：存在即匹配6：不存在即匹配    7：总匹配"
        ::= { onuClassificationEntry  26 }

    onuClassificationClause5Value          OBJECT-TYPE
        SYNTAX      OCTET STRING (SIZE (6))
        MAX-ACCESS  read-create
        STATUS      current
        DESCRIPTION
            "内容"
        ::= { onuClassificationEntry  27 }

    onuClassificationClause6Flag           OBJECT-TYPE
        SYNTAX      INTEGER(1..2)
        MAX-ACCESS  read-create
        STATUS      current
        DESCRIPTION
            "是否有效,1:有效 2：无效"
        ::= { onuClassificationEntry  28 }

    onuClassificationClause6FieldSelect    OBJECT-TYPE
        SYNTAX      INTEGER
        MAX-ACCESS read-create
        STATUS      current
        DESCRIPTION
            "规则类型，0：基于源mac  1：基于目的mac  2：基于vlanid  3：基于以太网类型   4：基于源ip  5：基于目的ip  6：基于ip

协议类型  7：基于TOS/DSCP 
8：基于L4源端口   9：基于L4目的端口"
        ::= { onuClassificationEntry  29 }

    onuClassificationClause6Operator       OBJECT-TYPE
        SYNTAX      INTEGER
        MAX-ACCESS  read-create
        STATUS      current
        DESCRIPTION
            "操作符，1：等于  2：不等于  3：小于等于 4：大于等于  5：存在即匹配6：不存在即匹配    7：总匹配"
        ::= { onuClassificationEntry  30 }

    onuClassificationClause6Value          OBJECT-TYPE
        SYNTAX      OCTET STRING (SIZE (6))
        MAX-ACCESS  read-create
        STATUS      current
        DESCRIPTION
            "内容"
        ::= { onuClassificationEntry  31 }

    onuClassificationClause7Flag           OBJECT-TYPE
        SYNTAX      INTEGER(1..2)
        MAX-ACCESS  read-create
        STATUS      current
        DESCRIPTION
            "是否有效,1:有效 2：无效"
        ::= { onuClassificationEntry  32 }

    onuClassificationClause7FieldSelect    OBJECT-TYPE
        SYNTAX      INTEGER
        MAX-ACCESS read-create
        STATUS      current
        DESCRIPTION
            "规则类型，0：基于源mac  1：基于目的mac  2：基于vlanid  3：基于以太网类型   4：基于源ip  5：基于目的ip  6：基于ip

协议类型  7：基于TOS/DSCP 
8：基于L4源端口   9：基于L4目的端口"
        ::= { onuClassificationEntry  33 }

    onuClassificationClause7Operator       OBJECT-TYPE
        SYNTAX      INTEGER
        MAX-ACCESS  read-create
        STATUS      current
        DESCRIPTION
            "操作符，1：等于  2：不等于  3：小于等于 4：大于等于  5：存在即匹配6：不存在即匹配    7：总匹配"
        ::= { onuClassificationEntry  34 }

    onuClassificationClause7Value          OBJECT-TYPE
        SYNTAX      OCTET STRING (SIZE (6))
        MAX-ACCESS  read-create
        STATUS      current
        DESCRIPTION
            "内容"
        ::= { onuClassificationEntry  35 }

    onuClassificationClause8Flag           OBJECT-TYPE
        SYNTAX      INTEGER(1..2)
        MAX-ACCESS  read-create
        STATUS      current
        DESCRIPTION
            "是否有效,1:有效 2：无效"
        ::= { onuClassificationEntry  36 }

    onuClassificationClause8FieldSelect    OBJECT-TYPE
        SYNTAX      INTEGER
        MAX-ACCESS read-create
        STATUS      current
        DESCRIPTION
            "规则类型，0：基于源mac  1：基于目的mac  2：基于vlanid  3：基于以太网类型   4：基于源ip  5：基于目的ip  6：基于ip

协议类型  7：基于TOS/DSCP 
8：基于L4源端口   9：基于L4目的端口"
        ::= { onuClassificationEntry  37 }

    onuClassificationClause8Operator       OBJECT-TYPE
        SYNTAX      INTEGER
        MAX-ACCESS  read-create
        STATUS      current
        DESCRIPTION
            "操作符，1：等于  2：不等于  3：小于等于 4：大于等于  5：存在即匹配6：不存在即匹配    7：总匹配"
        ::= { onuClassificationEntry  38 }

    onuClassificationClause8Value          OBJECT-TYPE
        SYNTAX      OCTET STRING (SIZE (6))
        MAX-ACCESS  read-create
        STATUS      current
        DESCRIPTION
            "内容"
        ::= { onuClassificationEntry  39 }

    OnuClassificationRowStatus                  OBJECT-TYPE
        SYNTAX      INTEGER
        MAX-ACCESS  read-create
        STATUS      current
        DESCRIPTION
            "行状态"
        ::= { onuClassificationEntry  40 }


-- onu opm
    nscrtvOnuOpAlarmConfigTable  OBJECT-TYPE
        SYNTAX      SEQUENCE OF nscrtvOnuOpAlarmConfigEntry
        MAX-ACCESS  not-accessible
        STATUS      current
        DESCRIPTION
            "A list of onuOpAlarmConfigTable  entries. "
        ::= { onuObjects  7 }

    nscrtvOnuOpAlarmConfigEntry OBJECT-TYPE
        SYNTAX      nscrtvOnuOpAlarmConfigEntry
        MAX-ACCESS  not-accessible
        STATUS      current
        DESCRIPTION  
            "The onuOpAlarmConfigEntry Information"
        INDEX   { onuOpmAlarmDeviceIndex }   
        ::={ nscrtvOnuOpAlarmConfigTable    1 } 
              
    nscrtvOnuOpAlarmConfigEntry ::= SEQUENCE {
            nscrtvOnuOpmAlarmDeviceIndex                EponDeviceIndex,
            nscrtvOnuOpmAlarmEnable                     INTEGER,
            nscrtvOnuThresholdTempHighAlarm             INTEGER,
            nscrtvOnuThresholdTempLowAlarm              INTEGER,
            nscrtvOnuThresholdTempHighWarning           INTEGER,
            nscrtvOnuThresholdTempLowWarning            INTEGER,
            nscrtvOnuThresholdVccHighAlarm              INTEGER,
            nscrtvOnuThresholdVccLowAlarm               INTEGER,
            nscrtvOnuThresholdVccHighWarning            INTEGER,
            nscrtvOnuThresholdVccLowWarning             INTEGER,
            nscrtvOnuThresholdTXPowerHighAlarm          INTEGER,
            nscrtvOnuThresholdTXPowerLowAlarm           INTEGER,
            nscrtvOnuThresholdTXPowerHighWarning        INTEGER,
            nscrtvOnuThresholdTXPowerLowWarning         INTEGER,
            nscrtvOnuThresholdRXPowerHighAlarm          INTEGER,
            nscrtvOnuThresholdRXPowerLowAlarm           INTEGER,
            nscrtvOnuThresholdRXPowerHighWarning        INTEGER,
            nscrtvOnuThresholdRXPowerLowWarning         INTEGER,
            nscrtvOnuAlarmconfigRowstatus               INTEGER
        }
       
    nscrtvOnuOpmAlarmDeviceIndex                OBJECT-TYPE
        SYNTAX      EponDeviceIndex
        MAX-ACCESS  not-accessible
        STATUS      current
        DESCRIPTION
            "设备索引 "
        ::= { nscrtvOnuOpAlarmConfigEntry 1 }   
        
    nscrtvOnuOpmAlarmEnable                     OBJECT-TYPE
        SYNTAX      INTEGER(1..2)
        MAX-ACCESS  read-create
        STATUS      current
        DESCRIPTION
            "ONU告警使能，1：关闭   2：开启"
        ::= { nscrtvOnuOpAlarmConfigEntry 2 }  

    nscrtvOnuThresholdTempHighAlarm      OBJECT-TYPE
        SYNTAX      INTEGER 
        MAX-ACCESS  read-create
        STATUS      current
        DESCRIPTION
            " onu温度高告警门限值，最大取值：+128℃, 以16位带符号二进制数表示，单位为1/256摄氏度。表示范围为-128℃～+128℃"
        ::= { nscrtvOnuOpAlarmConfigEntry 3 }
    
    nscrtvOnuThresholdTempLowAlarm       OBJECT-TYPE
        SYNTAX      INTEGER 
        MAX-ACCESS  read-create
        STATUS      current
        DESCRIPTION
            " onu温度低告警门限值，最小取值：-128℃ "
        ::= { nscrtvOnuOpAlarmConfigEntry 4 }

    nscrtvOnuThresholdTempHighWarning      OBJECT-TYPE
        SYNTAX      INTEGER 
        MAX-ACCESS  read-create
        STATUS      current
        DESCRIPTION
            " onu温度高警示门限值"
        ::= { nscrtvOnuOpAlarmConfigEntry 5 }

    nscrtvOnuThresholdTempLowWarning         OBJECT-TYPE
        SYNTAX      INTEGER 
        MAX-ACCESS  read-create
        STATUS      current
        DESCRIPTION
            " onu温度低警示门限值"
        ::= { nscrtvOnuOpAlarmConfigEntry 6 }  

    nscrtvOnuThresholdVccHighAlarm       OBJECT-TYPE
        SYNTAX      INTEGER 
        MAX-ACCESS  read-create
        STATUS      current
        DESCRIPTION
            " onu电压高告警门限值，最大取值：6.55V，以16位无符号整数表示（0～65535），单位为100微伏，表示范围为0～6.55伏特"
        ::= { nscrtvOnuOpAlarmConfigEntry 7 }
    
    nscrtvOnuThresholdVccLowAlarm      OBJECT-TYPE
        SYNTAX      INTEGER 
        MAX-ACCESS  read-create
        STATUS      current
        DESCRIPTION
            " onu电压低告警门限值，最小取值：0V"
        ::= { nscrtvOnuOpAlarmConfigEntry 8 }
    nscrtvOnuThresholdVccHighWarning     OBJECT-TYPE
        SYNTAX      INTEGER
        MAX-ACCESS  read-create
        STATUS      current
        DESCRIPTION
            " onu电压高警示门限值"
        ::= { nscrtvOnuOpAlarmConfigEntry 9 }
    
    nscrtvOnuThresholdVccLowWarning      OBJECT-TYPE
        SYNTAX      INTEGER
        MAX-ACCESS  read-create
        STATUS      current
        DESCRIPTION
            " onu电压低警示门限值"
        ::= { nscrtvOnuOpAlarmConfigEntry 10 }   

    nscrtvOnuThresholdTXPowerHighAlarm     OBJECT-TYPE
        SYNTAX      INTEGER
        MAX-ACCESS  read-create
        STATUS      current
        DESCRIPTION
            " onu发送功率高告警门限值，最大取值：6.5535毫瓦，以16位无符号整数表示（0～65535），单位为0.1微瓦（uW），表示范围为0～6.5535毫瓦（大约为-40dBm～+8.2 dBm）"
        ::= { nscrtvOnuOpAlarmConfigEntry 11}
    
    nscrtvOnuThresholdTXPowerLowAlarm       OBJECT-TYPE
        SYNTAX      INTEGER 
        MAX-ACCESS  read-create
        STATUS      current
        DESCRIPTION
            " onu发送功率低告警门限值，最小取值：0毫瓦"
        ::= { nscrtvOnuOpAlarmConfigEntry 12}

    nscrtvOnuThresholdTXPowerHighWarning       OBJECT-TYPE
        SYNTAX      INTEGER
        MAX-ACCESS  read-create
        STATUS      current
        DESCRIPTION
            " onu发送功率高警示门限值"
        ::= { nscrtvOnuOpAlarmConfigEntry 13}

    nscrtvOnuThresholdTXPowerLowWarning       OBJECT-TYPE
        SYNTAX      INTEGER 
        MAX-ACCESS  read-create
        STATUS      current
        DESCRIPTION
            " onu发送功率低警示门限值"
        ::= { nscrtvOnuOpAlarmConfigEntry 14}  

    nscrtvOnuThresholdRXPowerHighAlarm      OBJECT-TYPE
        SYNTAX      INTEGER
        MAX-ACCESS  read-create
        STATUS      current
        DESCRIPTION
            " onu接收功率高告警门限值，最大值：6.5535毫瓦，为ONU接受到的平均光功率，以16位无符号整数表示（0～65535），单位为0.1微瓦（uW），表示范围为0～6.5535毫瓦（大约为-40dBm～+8.2 dBm），在-30dBm到～10dBm"
        ::= { nscrtvOnuOpAlarmConfigEntry 15}
    
    nscrtvOnuThresholdRXPowerLowAlarm       OBJECT-TYPE
        SYNTAX      INTEGER
        MAX-ACCESS  read-create
        STATUS      current
        DESCRIPTION
            " onu接收功率低告警门限值，最小值：0 毫瓦"
        ::= { nscrtvOnuOpAlarmConfigEntry 16}

    nscrtvOnuThresholdRXPowerHighWarning        OBJECT-TYPE
        SYNTAX      INTEGER
        MAX-ACCESS  read-create
        STATUS      current
        DESCRIPTION
            " onu接收功率高警示门限值"
        ::= { nscrtvOnuOpAlarmConfigEntry 17}
    nscrtvOnuThresholdRXPowerLowWarning       OBJECT-TYPE
        SYNTAX      INTEGER
        MAX-ACCESS  read-create
        STATUS      current
        DESCRIPTION
            " onu接收功率低警示门限值"
        ::= { nscrtvOnuOpAlarmConfigEntry 18}

    nscrtvOnuAlarmconfigRowstatus          OBJECT-TYPE
        SYNTAX      INTEGER 
        MAX-ACCESS  read-create
        STATUS      current
        DESCRIPTION
            "行状态"
        ::= { nscrtvOnuOpAlarmConfigEntry 19}
--
-- END of NSCRTV-EPON-ONU-MIB
--

END

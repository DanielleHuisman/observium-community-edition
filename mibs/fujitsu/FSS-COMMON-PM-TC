--=============================================================================
-- Copyright (c) 2016 Fujitsu Network Communications, Inc. All Rights Reserved.
--=============================================================================

FSS-COMMON-PM-TC DEFINITIONS ::= BEGIN

IMPORTS
    MODULE-IDENTITY, Integer32, Unsigned32
        FROM SNMPv2-SMI
    TEXTUAL-CONVENTION
        FROM SNMPv2-TC
    fssCommon
        FROM FSS-COMMON-SMI
    DisplayString
        FROM SNMPv2-TC
    ;

fcTc MODULE-IDENTITY
    LAST-UPDATED "202007130000Z"
    ORGANIZATION
        "Fujitsu Network Communications, Inc."
    CONTACT-INFO
        "Fujitsu Technical Assistance Center (FTAC),
         1-800-USE-FTAC (1-800-873-3822)"
    DESCRIPTION
        "This MIB module contains common textual conventions (TC)
         used throughout the Fujitsu Network Communications, Inc.
         enterprise MIB.  It contains only those generic
         TCs potentially used in more than one MIB module."
    REVISION      "202007130000Z"
    DESCRIPTION
            "Added new Montypes:
               totalOpticalPowerReceiveAvg,
               opticalPowerReceiveLane1Avg,
               opticalPowerTransmitLane1Avg,
               opticalPowerReceiveLane2Avg,
               opticalPowerTransmitLane2Avg,
               opticalPowerReceiveLane3Avg,
               opticalPowerTransmitLane3Avg,
               opticalPowerReceiveLane4Avg,
               opticalPowerTransmitLane4Avg,
               chromaticDispersionAvg,
               opticalSignalNoiseRatioAvg,
               electricalSignalNoiseRatioAvg,
               errorVectorMagnitudeAvg,
               statusOfPolarizationAvg,
               polarizationDependentLossAvg,
               polarizationModeDispersionAvg"
    REVISION      "202007060000Z"
    DESCRIPTION
            "Added new Montypes:
               incomingAlignmentErroredSecond,
               backwardIncomingAlignmentErroredSecond,
               incomingAlignmentErroredSecondTCMi-down,
               backwardIncomingAlignmentErroredSecondTCMi-down"
    REVISION      "201907150000Z"
    DESCRIPTION
            "Added new Montypes for
               Error Vector Magnitude:
               errorVectorMagnitudeRatio,
               errorVectorMagnitudeMin,
               errorVectorMagnitudeMax
               Status Of Polarization:
               statusOfPolarization,
               statusOfPolarizationMin,
               statusOfPolarizationMax"
    REVISION      "201906170000Z"
    DESCRIPTION
            "Added new Montypes for electrical Signal Noise Ratio:
               electricalSignalNoiseRatio,
               electricalSignalNoiseRatioMin,
               electricalSignalNoiseRatioMax"
    REVISION      "201904010000Z"
    DESCRIPTION
            "Added new Montypes for CPU Usage:
               memoryUsage,
               memoryUsageMin,
               memoryUsageMax,
               memoryUsageAvg,
               cpuUsage,
               cpuUsageMin,
               cpuUsageMax,
               cpuUsageAvg"
    REVISION      "201807030000Z"
    DESCRIPTION
            "Added new Montypes for Data Encryption:
             DecryptionErroredSeconds"
    REVISION      "201805070000Z"
    DESCRIPTION
            "Added new Montypes for Sonet:
             severelyErroredFramingSecondSection,
             codingViolationLine,
             erroredSecondLine,
             severelyErroredSecondLine,
             unavailableSecondLine,
             failureCountLine"
    REVISION      "201803270000Z"
    DESCRIPTION
            "Added new ROADM PMs:
             opticalPowerTransmitDra"
    REVISION      "201708110000Z"
    DESCRIPTION
            "Added new FSC PMs:
             codingViolationSection erroredSecondSection and
             severelyErroredSecondSection"
    REVISION      "201707190000Z"
    DESCRIPTION
            "Added new OTN Protection PMs:
             protectionSwitchCount and protectionSwitchDuration"
    REVISION      "201704210000Z"
    DESCRIPTION
            "Added new OSC L2 PMs:
             inFrames, inFramesErr, outFrames, erroredSecondEthernet,
             severelyErroredSecondEthernet and unavailableSecondEthernet"
    REVISION      "201704190000Z"
    DESCRIPTION
            "Adding Data Encryption Montypes:
             framesEncrypted, framesDecrypted,
             framesDroppedForDecryptionError and encryptionErroredSeconds"
    REVISION      "201601200000Z"
    DESCRIPTION
            "Initial version for release."
    ::= { fssCommon 2 } -- See FSS-COMMON-SMI.mib

--=====================================================================--
-- Textual Conventions                                                 --
--=====================================================================--

FCMonType ::= TEXTUAL-CONVENTION
    STATUS  current
    DESCRIPTION
        "The possible Mon Types Supported."
    SYNTAX  INTEGER {
        prod-specific                   (0),        -- Project Specific TCA (see TCA Qualifier)
        temperature                     (1),
        temperatureMin                  (2),
        temperatureMax                  (3),
        temperatureAvg                  (4),
        shelfCurrentMax                 (5),
        opticalPowerReceive             (6),
        opticalPowerReceiveMin          (7),
        opticalPowerReceiveMax          (8),
        opticalPowerReceiveAvg          (9),
        totalOpticalPowerReceive        (10),
        totalOpticalPowerReceiveMin     (11),
        totalOpticalPowerReceiveMax     (12),
        opticalPowerTransmit            (13),
        opticalPowerTransmitMin         (14),
        opticalPowerTransmitMax         (15),
        opticalPowerTransmitAvg         (16),
        laserBiasCurrent                (17),
        opticalPowerReceiveLane1        (18),
        opticalPowerReceiveLane1Min     (19),
        opticalPowerReceiveLane1Max     (20),
        opticalPowerTransmitLane1       (21),
        opticalPowerTransmitLane1Min    (22),
        opticalPowerTransmitLane1Max    (23),
        laserBiasCurrentLane1           (24),
        opticalPowerReceiveLane2        (25),
        opticalPowerReceiveLane2Min     (26),
        opticalPowerReceiveLane2Max     (27),
        opticalPowerTransmitLane2       (28),
        opticalPowerTransmitLane2Min    (29),
        opticalPowerTransmitLane2Max    (30),
        laserBiasCurrentLane2           (31),
        opticalPowerReceiveLane3        (32),
        opticalPowerReceiveLane3Min     (33),
        opticalPowerReceiveLane3Max     (34),
        opticalPowerTransmitLane3       (35),
        opticalPowerTransmitLane3Min    (36),
        opticalPowerTransmitLane3Max    (37),

        laserBiasCurrentLane3           (38),
        opticalPowerReceiveLane4        (39),
        opticalPowerReceiveLane4Min     (40),
        opticalPowerReceiveLane4Max     (41),
        opticalPowerTransmitLane4       (42),
        opticalPowerTransmitLane4Min    (43),
        opticalPowerTransmitLane4Max    (44),
        laserBiasCurrentLane4           (45),

        chromaticDispersion             (46),
        chromaticDispersionMin          (47),
        chromaticDispersionMax          (48),

        opticalSignalNoiseRatio         (49),
        opticalSignalNoiseRatioMin      (50),
        opticalSignalNoiseRatioMax      (51),

        polarizationDependentLoss       (52),
        polarizationDependentLossMin    (53),
        polarizationDependentLossMax    (54),

        polarizationModeDispersion      (55),
        polarizationModeDispersionMin   (56),
        polarizationModeDispersionMax   (57),

        sD-FECuncorrectedBlocks         (58),
        sD-FECcorrectedBlocks           (59),
        sD-FECcorrectedBits             (60),
        preFECbitErrorRate              (61),
        erroredBlocks                   (62),
        fECcorrectedBits                (63),
        fECuncorrectedBlocks            (64),
        fECuncorrectedCodewords         (65),
        fECcorrectedCodewords           (66),
        fECcorrectedSymbols             (67),
        preFecBitErrorRate              (68),
        memoryUsage                     (69),
        memoryUsageMin                  (70),
        memoryUsageMax                  (71),
        memoryUsageAvg                  (72),
        cpuUsage                        (73),
        cpuUsageMin                     (74),
        cpuUsageMax                     (75),
        cpuUsageAvg                     (76),
        electricalSignalNoiseRatio      (77),
        electricalSignalNoiseRatioMin   (78),
        electricalSignalNoiseRatioMax   (79),

        errorVectorMagnitude            (80),
        errorVectorMagnitudeMin         (81),
        errorVectorMagnitudeMax         (82),
        statusOfPolarization            (83),
        statusOfPolarizationMin         (84),
        statusOfPolarizationMax         (85),

        totalOpticalPowerReceiveAvg     (86),
        opticalPowerReceiveLane1Avg     (87),
        opticalPowerTransmitLane1Avg    (88),
        opticalPowerReceiveLane2Avg     (89),
        opticalPowerTransmitLane2Avg    (90),
        opticalPowerReceiveLane3Avg     (91),
        opticalPowerTransmitLane3Avg    (92),
        opticalPowerReceiveLane4Avg     (93),
        opticalPowerTransmitLane4Avg    (94),
        chromaticDispersionAvg          (95),
        opticalSignalNoiseRatioAvg      (96),
        electricalSignalNoiseRatioAvg   (97),
        errorVectorMagnitudeAvg         (98),
        statusOfPolarizationAvg         (99),
        polarizationDependentLossAvg    (100),
        polarizationModeDispersionAvg   (101),

-- ETH PMs
        ifInUcastPkts                   (200),
        ifInBroadcastPkts               (201),
        ifInMulticastPkts               (202),
        ifInPauseFrames                 (203),
        ifInDiscards                    (204),
        ifInUnknownProtos               (205),
        ifInOctets                      (206),
        ifInError                       (207),
        ifOutUcastPkts                  (208),
        ifOutBroadcastPkts              (209),
        ifOutMulticastPkts              (210),
        ifOutPauseFrames                (211),
        ifOutDiscards                   (212),
        ifOutOctets                     (213),
        ifOutError                      (214),
        localFaultSeconds               (215),
        remoteFaultSeconds              (216),
        inFrames                        (217),
        inFramesErr                     (218),
        outFrames                       (219),
        erroredSecondEthernet           (220),
        severelyErroredSecondEthernet   (221),
        unavailableSecondEthernet       (222),

-- LOAM
        ifInUnsupportedLOAMDrop         (300),
        ifInLOAMPDU                     (301),
        ifOutLOAMPDU                    (302),
        ifInLoopbackPDU                 (304),
        ifOutLoopbackPDU                (305),

-- OTN
        codingViolation                                 (400),
        erroredSecond                                   (401),
        severelyErroredSecond                           (402),
        unavailableSecond                               (403),
        backgroundBlockErrors                           (404),
        backgroundBlockErrorRatio                       (405),
        severelyErroredSecondRatio                      (406),
        delayMeasurement                                (407),
        delayMeasurementMin                             (408),
        delayMeasurementMax                             (409),
        protectionSwitchCount                           (410),
        protectionSwitchDuration                        (411),
        codingViolationSection                          (412),
        erroredSecondSection                            (413),
        severelyErroredSecondSection                    (414),
        incomingAlignmentErroredSecond                  (415),
        incomingAlignmentErroredSecondTCM1-down         (416),
        incomingAlignmentErroredSecondTCM2-down         (417),
        incomingAlignmentErroredSecondTCM3-down         (418),
        incomingAlignmentErroredSecondTCM4-down         (419),
        incomingAlignmentErroredSecondTCM5-down         (420),
        incomingAlignmentErroredSecondTCM6-down         (421),
        backwardIncomingAlignmentErroredSecond          (422),
        backwardIncomingAlignmentErroredSecondTCM1-down (423),
        backwardIncomingAlignmentErroredSecondTCM2-down (424),
        backwardIncomingAlignmentErroredSecondTCM3-down (425),
        backwardIncomingAlignmentErroredSecondTCM4-down (426),
        backwardIncomingAlignmentErroredSecondTCM5-down (427),
        backwardIncomingAlignmentErroredSecondTCM6-down (428),

-- ROADM
        opticalPowerReceiveOts          (500),
        opticalPowerReceiveOtsMin       (501),
        opticalPowerReceiveOtsMax       (502),
        opticalPowerReceiveOtsAvg       (503),
        opticalPowerTransmitOts         (504),
        opticalPowerTransmitOtsMin      (505),
        opticalPowerTransmitOtsMax      (506),
        opticalPowerTransmitOtsAvg      (507),
        opticalPowerReceiveOms          (508),
        opticalPowerReceiveOmsMin       (509),
        opticalPowerReceiveOmsMax       (510),
        opticalPowerReceiveOmsAvg       (511),
        opticalPowerTransmitOms         (512),
        opticalPowerTransmitOmsMin      (513),
        opticalPowerTransmitOmsMax      (514),
        opticalPowerTransmitOmsAvg      (515),
        opticalPowerReceiveOsc          (516),
        opticalPowerReceiveOscMin       (517),
        opticalPowerReceiveOscMax       (518),
        opticalPowerReceiveOscAvg       (519),
        opticalPowerTransmitOsc         (520),
        opticalPowerTransmitOscMin      (521),
        opticalPowerTransmitOscMax      (522),
        opticalPowerTransmitOscAvg      (523),
        spanLoss                        (524),
        spanLossMin                     (525),
        spanLossMax                     (526),
        spanLossAvg                     (527),
        spanLossVariation               (528),
        spanLossVariationMin            (529),
        spanLossVariationMax            (530),
        spanLossVariationAvg            (531),
        reflectionPower                 (532),
        reflectionPowerMin              (533),
        reflectionPowerMax              (534),
        reflectionPowerAvg              (535),
        opticalPowerTransmitDra         (536),
        opticalPowerTransmitDraMin      (537),
        opticalPowerTransmitDraMax      (538),
        opticalPowerTransmitDraAvg      (539),

-- 10GE
        ifGoodOctets                    (600),
        ifFrameCheckSumErrors           (601),
        ifGoodFrames                    (602),
        ifPauseFrames                   (603),
        ifJumboFrames                   (604),
        ifOversizedFrames               (605),
        ifUndersizedFrames              (606),
        ifFragments                     (607),
        ifJabber                        (608),
        ifDropEvents                    (609),
        ifOctets                        (610),
        ifPackets                       (611),
        ifBroadcastPackets              (612),
        ifMulticastPackets              (613),
        ifFramesOfSize64                (614),
        ifFramesOfSize65To127           (615),
        ifFramesOfSize128To255          (616),
        ifFramesOfSize256To511          (617),
        ifFramesOfSize512To1023         (618),
        ifFramesOfSize1024To1518        (619),

-- Data Encryption
        framesEncrypted                 (620),
        framesDecrypted                 (621),
        framesDroppedForDecryptionError (622),
        encryptionErroredSeconds        (623),
        decryptionErroredSeconds        (624),

-- Sonet
        severelyErroredFramingSecondSection  (650),
        codingViolationLine                  (651),
        erroredSecondLine                    (652),
        severelyErroredSecondLine            (653),
        unavailableSecondLine                (654),
        failureCountLine                     (655)


    }

END

--=============================================================================
-- Copyright (c) 2016 Fujitsu Network Communications, Inc. All Rights Reserved.
--=============================================================================

FSS-COMMON-SMI DEFINITIONS ::= BEGIN

IMPORTS
    MODULE-IDENTITY, enterprises
        FROM SNMPv2-SMI;

fujitsu MODULE-IDENTITY
    LAST-UPDATED "201605131500Z" -- May 13, 2016
    ORGANIZATION
        "Fujitsu Network Communications, Inc."
    CONTACT-INFO 
        "Fujitsu Technical Assistance Center (FTAC),        
         1-800-USE-FTAC (1-800-873-3822)"
    DESCRIPTION 
        "This MIB module defines all of the base level headers 
         used for control of the Fujitsu Network Communications, Inc. 
         enterprises MIB tree.

         The main utility of this MIB module is to collect the
         MIB tree of the base objects in the fss branch."
    ::= { enterprises 211 }

product OBJECT IDENTIFIER               ::= { fujitsu 1 }

    transport OBJECT IDENTIFIER            ::= { product 24 }

        fssCommon OBJECT IDENTIFIER            ::= { transport 12 }

           fssInterfaces OBJECT IDENTIFIER            ::= { fssCommon 700 }
           fssRouting OBJECT IDENTIFIER            ::= { fssCommon 900 }
           fssProtocols OBJECT IDENTIFIER            ::= { fssCommon 1100 }

END

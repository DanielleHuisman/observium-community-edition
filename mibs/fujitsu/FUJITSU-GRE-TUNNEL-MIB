--=============================================================================
-- Copyright (c) 2017 Fujitsu Network Communications, Inc. All Rights Reserved.
--=============================================================================

FUJITSU-GRE-TUNNEL-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
    Ipv6Address
        FROM IPV6-TC
    ifIndex
        FROM IF-MIB
    fssInterfaces
        FROM FSS-COMMON-SMI
;

fSS-GRE-TUNNEL-INTERFACE MODULE-IDENTITY
    LAST-UPDATED "201701120000Z"
    ORGANIZATION "@ORGANIZATION"
    CONTACT-INFO "@CONTACT-INFO"
    DESCRIPTION "This module defines gre tunnel yang data model.

Copyright (c) 2017 Fujitsu Ltd.
All rights reserved. "
    REVISION "201701120000Z"
    DESCRIPTION "@REVISION-DESCRIPTION"
    ::= { fssInterfaces 1000 }

UnsignedByte ::= TEXTUAL-CONVENTION
    DISPLAY-HINT "d"
    STATUS      current
    DESCRIPTION "xs:unsignedByte"
    SYNTAX      Unsigned32 (0 .. 255)

String ::= TEXTUAL-CONVENTION
    DISPLAY-HINT "1t"
    STATUS      current
    DESCRIPTION "xs:string"
    SYNTAX      OCTET STRING

-- tagpath /interfaces-state/interface/tunnel-state/MTU
interfaces-stateInterfaceFssGRETable OBJECT-TYPE
    SYNTAX      SEQUENCE OF Interfaces-stateInterfaceFssGREEntry
    MAX-ACCESS  not-accessible
    STATUS      current
    DESCRIPTION ""
    ::= { fSS-GRE-TUNNEL-INTERFACE 1 }

-- tagpath /interfaces-state/interface/tunnel-state/MTU
interfaces-stateInterfaceFssGREEntry OBJECT-TYPE
    SYNTAX      Interfaces-stateInterfaceFssGREEntry
    MAX-ACCESS  not-accessible
    STATUS      current
    DESCRIPTION ""
    INDEX { ifIndex }
        ::= { interfaces-stateInterfaceFssGRETable 1 }

Interfaces-stateInterfaceFssGREEntry ::=
    SEQUENCE {
        tunnel-stateMTU Unsigned32,
        tunnel-statePackets-input Counter64,
        tunnel-stateInput-errors Counter64,
        tunnel-statePackets-output Counter64,
        tunnel-stateOutput-errors Counter64,
        tunnel-stateBytes Counter64
    }

-- tagpath /interfaces-state/interface/tunnel-state/MTU
tunnel-stateMTU OBJECT-TYPE
    SYNTAX      Unsigned32
    MAX-ACCESS  read-only
    STATUS      current
    DESCRIPTION ""
    ::= { interfaces-stateInterfaceFssGREEntry 1 }

-- tagpath /interfaces-state/interface/tunnel-state/packets-input
tunnel-statePackets-input OBJECT-TYPE
    SYNTAX      Counter64
    MAX-ACCESS  read-only
    STATUS      current
    DESCRIPTION ""
    ::= { interfaces-stateInterfaceFssGREEntry 2 }

-- tagpath /interfaces-state/interface/tunnel-state/input-errors
tunnel-stateInput-errors OBJECT-TYPE
    SYNTAX      Counter64
    MAX-ACCESS  read-only
    STATUS      current
    DESCRIPTION ""
    ::= { interfaces-stateInterfaceFssGREEntry 3 }

-- tagpath /interfaces-state/interface/tunnel-state/packets-output
tunnel-statePackets-output OBJECT-TYPE
    SYNTAX      Counter64
    MAX-ACCESS  read-only
    STATUS      current
    DESCRIPTION ""
    ::= { interfaces-stateInterfaceFssGREEntry 4 }

-- tagpath /interfaces-state/interface/tunnel-state/output-errors
tunnel-stateOutput-errors OBJECT-TYPE
    SYNTAX      Counter64
    MAX-ACCESS  read-only
    STATUS      current
    DESCRIPTION ""
    ::= { interfaces-stateInterfaceFssGREEntry 5 }

-- tagpath /interfaces-state/interface/tunnel-state/bytes
tunnel-stateBytes OBJECT-TYPE
    SYNTAX      Counter64
    MAX-ACCESS  read-only
    STATUS      current
    DESCRIPTION ""
    ::= { interfaces-stateInterfaceFssGREEntry 6 }

END

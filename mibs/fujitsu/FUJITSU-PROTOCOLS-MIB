--=============================================================================
-- Copyright (c) 2017 Fujitsu Network Communications, Inc. All Rights Reserved.
--=============================================================================

FUJITSU-PROTOCOLS-MIB DEFINITIONS ::= BEGIN
IMPORTS
    MODULE-IDENTITY, OBJECT-TYPE,
    Integer32, Unsigned32, Counter32, Counter64,
    Gauge32, IpAddress
        FROM SNMPv2-SMI
    TEXTUAL-CONVENTION, RowStatus, DateAndTime,
    TruthValue
        FROM SNMPv2-TC
    fssProtocols
        FROM FSS-COMMON-SMI
;

fUJITSU-PROTOCOLS-MIB MODULE-IDENTITY
    LAST-UPDATED "201604010000Z"
    ORGANIZATION "@ORGANIZATION"
    CONTACT-INFO "@CONTACT-INFO"
    DESCRIPTION "This module contains YANG definitions
for protocols involved.

Copyright (c) 2015 Fujitsu Ltd.
All rights reserved. "
    REVISION "201604010000Z"
    DESCRIPTION "@REVISION-DESCRIPTION"
    ::= { fssProtocols 1000 }

ConfdString ::= TEXTUAL-CONVENTION
    DISPLAY-HINT "1t"
    STATUS      current
    DESCRIPTION "xs: and confd: types mapped to strings"
    SYNTAX      OCTET STRING

String ::= TEXTUAL-CONVENTION
    DISPLAY-HINT "1t"
    STATUS      current
    DESCRIPTION "xs:string"
    SYNTAX      OCTET STRING

-- tagpath /protocols
protocols OBJECT IDENTIFIER ::= { fUJITSU-PROTOCOLS-MIB 1 }

-- tagpath /protocols/protocol
protocolsProtocolTable OBJECT-TYPE
    SYNTAX      SEQUENCE OF ProtocolsProtocolEntry
    MAX-ACCESS  not-accessible
    STATUS      current
    DESCRIPTION ""
    ::= { protocols 1 }

-- tagpath /protocols/protocol
protocolsProtocolEntry OBJECT-TYPE
    SYNTAX      ProtocolsProtocolEntry
    MAX-ACCESS  not-accessible
    STATUS      current
    DESCRIPTION ""
    INDEX { IMPLIED protocolsProtocolName }
        ::= { protocolsProtocolTable 1 }

ProtocolsProtocolEntry ::=
    SEQUENCE {
        protocolsProtocolName String,
        protocolsProtocolType ConfdString,
        protocolsProtocolRowstatus RowStatus
    }

-- tagpath /protocols/protocol/name
protocolsProtocolName OBJECT-TYPE
    SYNTAX      String
    MAX-ACCESS  not-accessible
    STATUS      current
    DESCRIPTION ""
    ::= { protocolsProtocolEntry 1 }

-- tagpath /protocols/protocol/type
protocolsProtocolType OBJECT-TYPE
    SYNTAX      ConfdString
    MAX-ACCESS  read-create
    STATUS      current
    DESCRIPTION ""
    ::= { protocolsProtocolEntry 2 }

-- tagpath /protocols/protocol/rowstatus
protocolsProtocolRowstatus OBJECT-TYPE
    SYNTAX      RowStatus
    MAX-ACCESS  read-create
    STATUS      current
    DESCRIPTION ""
    ::= { protocolsProtocolEntry 3 }

END

GBNPlatformOAMSntpClient-MIB DEFINITIONS ::= BEGIN

    IMPORTS
        MODULE-IDENTITY, OBJECT-TYPE,
        Counter32, Gauge32,
        Unsigned32, Integer32,
        IpAddress                               FROM SNMPv2-SMI

        RowStatus, TruthValue,
        DisplayString, MacAddress               FROM SNMPv2-TC

        MODULE-COMPLIANCE, OBJECT-GROUP         FROM SNMPv2-CONF

        gbnPlatformOAM                          FROM GBNPlatformOAM-MIB;


    gbnPlatformOAMSntpClient  MODULE-IDENTITY
        LAST-UPDATED    "0107152004Z"  -- July 15, 2004
        ORGANIZATION    "Greentech"
        CONTACT-INFO    "Adam Armstrong
                         E-mail: adama@observium.org"

        DESCRIPTION     "SNTP mib definition."

        REVISION        "0107152004Z"  -- July 15, 2004
        DESCRIPTION     "Initial MIB creation."

        ::= { gbnPlatformOAM 8 }

------------------------------------------------------------------------------
------------------------------------------------------------------------------
--  sntpClientGeneral:
------------------------------------------------------------------------------

    sntpClientGeneral         OBJECT IDENTIFIER ::= { gbnPlatformOAMSntpClient 1 }

    sntpClientMode OBJECT-TYPE
       SYNTAX  INTEGER  {
                        unicast (1),
                        anycast(2),
                        broadcast(4),
                        multicast(8) }
        MAX-ACCESS  read-write
        STATUS  current
        DESCRIPTION
            " SNTP client work "
        DEFVAL  { broadcast }
        ::= { sntpClientGeneral 1 }

    sntpClientPollInterval OBJECT-TYPE
        SYNTAX INTEGER( 64..1024 )
        MAX-ACCESS  read-write
        STATUS  current
        DESCRIPTION
            " Send the request interval, for unicast and broadcast any way "
        DEFVAL  { 1000 }
        ::= { sntpClientGeneral 2 }

    sntpClientRetransInterval OBJECT-TYPE
        SYNTAX INTEGER( 1..30 )
        MAX-ACCESS  read-write
        STATUS  current
        DESCRIPTION
            " Client request retransmission interval "
        DEFVAL  { 5 }
        ::= { sntpClientGeneral 3 }

    sntpClientRetransTimes OBJECT-TYPE
        SYNTAX INTEGER( 0..10 )
        MAX-ACCESS  read-write
        STATUS  current
        DESCRIPTION
            " Client does not receive the response, the number of retransmission requests for unicast and broadcast any way "
        DEFVAL  { 0 }
        ::= { sntpClientGeneral 4 }

    sntpClientServer OBJECT-TYPE
        SYNTAX IpAddress
        MAX-ACCESS  read-write
        STATUS  current
        DESCRIPTION
            " Are using the server address for the unicast and broadcast any way. "
        ::= { sntpClientGeneral 5 }

    sntpClientSynthFlag OBJECT-TYPE
        SYNTAX TruthValue
        MAX-ACCESS  read-only
        STATUS  current
        DESCRIPTION
            "Whether the time the client is synchronized. "
        ::= { sntpClientGeneral 6 }

    sntpClientState OBJECT-TYPE
        SYNTAX INTEGER
        MAX-ACCESS  read-only
        STATUS  current
        DESCRIPTION
            " The current state of the client, idle state or wait for a response message status. "
        ::= { sntpClientGeneral 7 }

    sntpClientLastSynthTime OBJECT-TYPE
        SYNTAX Integer32
        MAX-ACCESS  read-only
        STATUS  current
        DESCRIPTION
            " The last time the client synchronized time. "
        ::= { sntpClientGeneral 8 }

    sntpClientLastSynthErrno OBJECT-TYPE
        SYNTAX INTEGER
        MAX-ACCESS  read-only
        STATUS  current
        DESCRIPTION
            "If the client fails the last time synchronization error code."
        ::= { sntpClientGeneral 9 }

    sntpClientAdminStatus OBJECT-TYPE
        SYNTAX INTEGER{
                     enable(1),
                     disable(2)
                     }
        MAX-ACCESS  read-write
        STATUS  current
        DESCRIPTION
            " Clients open and closed. "
        ::= { sntpClientGeneral 10 }

    sntpClientBcastDelay OBJECT-TYPE
        SYNTAX INTEGER ( 1..9999 )
        MAX-ACCESS  read-write
        STATUS  current
        DESCRIPTION
            " Working in broadcast client mode, the estimated transmission delay (milliseconds)."
        ::= { sntpClientGeneral 11 }

     sntpClientMcastTtl OBJECT-TYPE
        SYNTAX INTEGER ( 1..255 )
        MAX-ACCESS  read-write
        STATUS  current
        DESCRIPTION
            " Work in multicast client mode, the TTL value. "
        ::= { sntpClientGeneral 12 }

      sntpClientAuthFlag OBJECT-TYPE
        SYNTAX TruthValue
        MAX-ACCESS  read-write
        STATUS  current
        DESCRIPTION
            "authentication enable flag"
        ::= { sntpClientGeneral 13 }

      sntpClientUniKeyID OBJECT-TYPE
        SYNTAX Unsigned32
        MAX-ACCESS  read-write
        STATUS  current
        DESCRIPTION
            "in client/server mode, client send request with this keyID"
        ::= { sntpClientGeneral 14 }

      sntpClientAnyKeyID OBJECT-TYPE
        SYNTAX Unsigned32
        MAX-ACCESS  read-write
        STATUS  current
        DESCRIPTION
            "in anycast mode, client send request with this keyID"
        ::= { sntpClientGeneral 15 }

------------------------------------------------------------------------------
--  sntpValidSrcTable:
------------------------------------------------------------------------------

  sntpClientValidServerTable OBJECT-TYPE
        SYNTAX   SEQUENCE OF SntpClientValidServerEntry
        MAX-ACCESS   not-accessible
        STATUS   current
        DESCRIPTION
           " Legitimate server segment table, SNTP packets according to time table to check the source address, only the source address is located in this newspaper literary talent in this table as legitimate messages, or discarded. Equivalent to access control lists. "
       ::= { gbnPlatformOAMSntpClient 2 }

    sntpClientValidServerEntry OBJECT-TYPE
        SYNTAX   SntpClientValidServerEntry
        MAX-ACCESS   not-accessible
        STATUS   current
        DESCRIPTION
           " Definition of a legitimate server list."
       INDEX { sntpClientValidServerNet, sntpClientValidServerMask }
       ::= { sntpClientValidServerTable 1 }

    SntpClientValidServerEntry ::=
        SEQUENCE {
            sntpClientValidServerNet
                IpAddress,
            sntpClientValidServerMask
                IpAddress,
            sntpClientValidServerRowStatus
                RowStatus
            }

    sntpClientValidServerNet OBJECT-TYPE
        SYNTAX   IpAddress
        MAX-ACCESS   read-only
        STATUS   current
        DESCRIPTION
           " Source address of the subnet number. "
        ::= { sntpClientValidServerEntry 1 }

    sntpClientValidServerMask OBJECT-TYPE
        SYNTAX   IpAddress
        MAX-ACCESS   read-only
        STATUS   current
        DESCRIPTION
           " Source address of the subnet mask. "
        ::= { sntpClientValidServerEntry 2 }

    sntpClientValidServerRowStatus OBJECT-TYPE
        SYNTAX   RowStatus
        MAX-ACCESS   read-write
        STATUS   current
        DESCRIPTION
           " Line state. "
        ::= { sntpClientValidServerEntry 3 }

------------------------------------------------------------------------------
--  sntpAuthKeyTable:
------------------------------------------------------------------------------

  sntpAuthKeyTable OBJECT-TYPE
        SYNTAX   SEQUENCE OF SntpAuthKeyEntry
        MAX-ACCESS   not-accessible
        STATUS   current
        DESCRIPTION
           "keys userd for SNTP authentication"
       ::= { gbnPlatformOAMSntpClient 3 }

    sntpAuthKeyEntry OBJECT-TYPE
        SYNTAX   SntpAuthKeyEntry
        MAX-ACCESS   not-accessible
        STATUS   current
        DESCRIPTION
           "define a key item."
       INDEX { sntpAuthKeyId }
       ::= { sntpAuthKeyTable 1 }

    SntpAuthKeyEntry ::=
        SEQUENCE {
            sntpAuthKeyId
                Unsigned32,
            sntpAuthKeyValue
                DisplayString (SIZE (1..16)),
            sntpAuthKeyTrustFlag
                TruthValue,
            sntpAuthKeyRowStatus
                RowStatus
            }

    sntpAuthKeyId OBJECT-TYPE
        SYNTAX   Unsigned32  ( 1..4294967295 )
        MAX-ACCESS   read-only
        STATUS   current
        DESCRIPTION
           "key number"
        ::= { sntpAuthKeyEntry 1 }

    sntpAuthKeyValue OBJECT-TYPE
        SYNTAX   DisplayString (SIZE (1..16))
        MAX-ACCESS   read-write
        STATUS   current
        DESCRIPTION
           "key value"
        ::= { sntpAuthKeyEntry 2 }

    sntpAuthKeyTrustFlag OBJECT-TYPE
        SYNTAX   TruthValue
        MAX-ACCESS   read-write
        STATUS   current
        DESCRIPTION
           "whether the key is trusted"
        ::= { sntpAuthKeyEntry 3 }

    sntpAuthKeyRowStatus OBJECT-TYPE
        SYNTAX   RowStatus
        MAX-ACCESS   read-write
        STATUS   current
        DESCRIPTION
           "row status"
        ::= { sntpAuthKeyEntry 4 }

   END

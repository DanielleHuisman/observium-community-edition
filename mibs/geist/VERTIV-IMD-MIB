VERTIV-IMD-MIB DEFINITIONS ::= BEGIN

IMPORTS

DisplayString FROM SNMPv2-TC
SnmpAdminString FROM SNMP-FRAMEWORK-MIB
MODULE-IDENTITY, OBJECT-TYPE, OBJECT-IDENTITY, enterprises, Integer32, Gauge32, NOTIFICATION-TYPE FROM SNMPv2-SMI
sysName FROM SNMPv2-MIB;

vertiv MODULE-IDENTITY
	LAST-UPDATED "201809100000Z"
	ORGANIZATION "Vertiv"
	CONTACT-INFO "support@geistglobal.com"
	DESCRIPTION "The MIB for Vertiv Products"
	REVISION "201809100000Z"
	DESCRIPTION "Modified for version 5 compliance"

	REVISION "201209110000Z"
	DESCRIPTION "Original version"
	::= { enterprises 21239 }

blackbird OBJECT IDENTIFIER
	::= { vertiv 5 }
imd OBJECT IDENTIFIER
	::= { blackbird 2 }

--###########################################################################################--
--deviceInfo--
--###########################################################################################--

deviceInfo OBJECT IDENTIFIER
	::= { imd 1 }

productTitle OBJECT-TYPE
	SYNTAX SnmpAdminString
	MAX-ACCESS read-only
	STATUS current
	DESCRIPTION
		"Product name"
	::= { deviceInfo 1 }

productVersion OBJECT-TYPE
	SYNTAX SnmpAdminString
	MAX-ACCESS read-only
	STATUS current
	DESCRIPTION
		"Product version"
	::= { deviceInfo 2 }

productFriendlyName OBJECT-TYPE
	SYNTAX SnmpAdminString
	MAX-ACCESS read-only
	STATUS current
	DESCRIPTION
		"User-assigned name"
	::= { deviceInfo 3 }

productMacAddress OBJECT-TYPE
	SYNTAX OCTET STRING
	MAX-ACCESS read-only
	STATUS current
	DESCRIPTION
		"Product's unique MAC address"
	::= { deviceInfo 4 }

deviceCount OBJECT-TYPE
	SYNTAX Integer32(0..5)
	MAX-ACCESS read-only
	STATUS current
	DESCRIPTION
		"Total number of devices on unit"
	::= { deviceInfo 6 }

temperatureUnits OBJECT-TYPE
	SYNTAX INTEGER {
			fahrenheit(0),
			celsius(1)
		}
	MAX-ACCESS read-write
	STATUS current
	DESCRIPTION
		"Current units for temperature/dewpoint values:
		0 = Degrees Fahrenheit
		1 = Degrees Celsius"
	::= { deviceInfo 7 }

productModelNumber OBJECT-TYPE
	SYNTAX SnmpAdminString
	MAX-ACCESS read-only
	STATUS current
	DESCRIPTION
		"Product model number (factory-assigned)"
	::= { deviceInfo 8 }

productPartNumber OBJECT-TYPE
	SYNTAX SnmpAdminString
	MAX-ACCESS read-only
	STATUS current
	DESCRIPTION
		"Product part number (factory-assigned)"
	::= { deviceInfo 9 }

productSerialNumber OBJECT-TYPE
	SYNTAX SnmpAdminString
	MAX-ACCESS read-only
	STATUS current
	DESCRIPTION
		"Product serial number (factory-assigned)"
	::= { deviceInfo 10 }

productPlatform OBJECT-TYPE
	SYNTAX SnmpAdminString
	MAX-ACCESS read-only
	STATUS current
	DESCRIPTION
		"Product platform"
	::= { deviceInfo 11 }

--###########################################################################################--
--pdu--
--###########################################################################################--

pdu OBJECT IDENTIFIER
	::= { imd 3 }

--###########################################################################################--
--pduMainTable--
--###########################################################################################--

pduMainTable OBJECT-TYPE
	SYNTAX SEQUENCE OF PduMainEntry
	MAX-ACCESS  not-accessible
	STATUS current
	DESCRIPTION
		"PDU general information"
	::= { pdu 1 }

pduMainEntry OBJECT-TYPE
	SYNTAX PduMainEntry
	MAX-ACCESS  not-accessible
	STATUS current
	DESCRIPTION
		"Entry in the pduMainTable table: each entry contains an index and other sensor details"
	INDEX { pduMainIndex }
	::= { pduMainTable 1 }

PduMainEntry ::= SEQUENCE {
	pduMainIndex				Integer32,
	pduMainSerial				DisplayString,
	pduMainName				SnmpAdminString,
	pduMainLabel				SnmpAdminString,
	pduMainAvail				Gauge32,
	pduMeterType				INTEGER,
	pduTotalName				SnmpAdminString,
	pduTotalLabel				SnmpAdminString,
	pduTotalRealPower				Gauge32,
	pduTotalApparentPower				Gauge32,
	pduTotalPowerFactor				Gauge32,
	pduTotalEnergy				Gauge32
}

pduMainIndex OBJECT-TYPE
	SYNTAX Integer32(1..100)
	MAX-ACCESS not-accessible
	STATUS current
	DESCRIPTION
		"Table entry index value"
	::= { pduMainEntry 1 }

pduMainSerial OBJECT-TYPE
	SYNTAX DisplayString
	MAX-ACCESS read-only
	STATUS current
	DESCRIPTION
		"Serial Number"
	::= { pduMainEntry 2 }

pduMainName OBJECT-TYPE
	SYNTAX SnmpAdminString(SIZE (1..25))
	MAX-ACCESS read-only
	STATUS current
	DESCRIPTION
		"PDU name (factory assigned)"
	::= { pduMainEntry 3 }

pduMainLabel OBJECT-TYPE
	SYNTAX SnmpAdminString(SIZE (0..25))
	MAX-ACCESS read-write
	STATUS current
	DESCRIPTION
		"PDU label (user-defined)"
	::= { pduMainEntry 4 }

pduMainAvail OBJECT-TYPE
	SYNTAX Gauge32
	MAX-ACCESS read-only
	STATUS current
	DESCRIPTION
		"Device availability:
		0 = Unavailable
		1 = Available
		2 = Partially Unavailable"
	::= { pduMainEntry 5 }

pduMeterType OBJECT-TYPE
	SYNTAX INTEGER {
			wye(0),
			delta(1)
			}
	MAX-ACCESS read-only
	STATUS current
	DESCRIPTION
		"Current meter type:
		0 = Wye
		1 = Delta"
	::= { pduMainEntry 6 }

pduTotalName OBJECT-TYPE
	SYNTAX SnmpAdminString(SIZE (1..25))
	MAX-ACCESS read-only
	STATUS current
	DESCRIPTION
		"Total Name (factory-assigned)"
	::= { pduMainEntry 7 }

pduTotalLabel OBJECT-TYPE
	SYNTAX SnmpAdminString(SIZE (0..25))
	MAX-ACCESS read-write
	STATUS current
	DESCRIPTION
		"Total Label (user-defined)"
	::= { pduMainEntry 8 }

pduTotalRealPower OBJECT-TYPE
	SYNTAX Gauge32(0..9999)
	UNITS "watts"
	MAX-ACCESS read-only
	STATUS current
	DESCRIPTION
		"PDU total real power"
	::= { pduMainEntry 9 }

pduTotalApparentPower OBJECT-TYPE
	SYNTAX Gauge32(0..9999)
	UNITS "volt-amps"
	MAX-ACCESS read-only
	STATUS current
	DESCRIPTION
		"PDU total apparent power"
	::= { pduMainEntry 10 }

pduTotalPowerFactor OBJECT-TYPE
	SYNTAX Gauge32(0..100)
	UNITS "%"
	MAX-ACCESS read-only
	STATUS current
	DESCRIPTION
		"PDU total power factor"
	::= { pduMainEntry 11 }

pduTotalEnergy OBJECT-TYPE
	SYNTAX Gauge32(0..9999000)
	UNITS "watt-hours"
	MAX-ACCESS read-only
	STATUS current
	DESCRIPTION
		"PDU total accumulated energy in watt-hours"
	::= { pduMainEntry 12 }

--###########################################################################################--
--pduPhaseTable--
--###########################################################################################--

pduPhaseTable OBJECT-TYPE
	SYNTAX SEQUENCE OF PduPhaseEntry
	MAX-ACCESS  not-accessible
	STATUS current
	DESCRIPTION
		"PDU phases information"
	::= { pdu 2 }

pduPhaseEntry OBJECT-TYPE
	SYNTAX PduPhaseEntry
	MAX-ACCESS  not-accessible
	STATUS current
	DESCRIPTION
		"Entry in the pduPhaseTable table: each entry contains an index and other sensor details"
	INDEX { pduPhaseIndex }
	::= { pduPhaseTable 1 }

PduPhaseEntry ::= SEQUENCE {
	pduPhaseIndex				Integer32,
	pduPhaseName				SnmpAdminString,
	pduPhaseLabel				SnmpAdminString,
	pduPhaseVoltage				Gauge32,
	pduPhaseVoltageMax				Gauge32,
	pduPhaseVoltageMin				Gauge32,
	pduPhaseVoltagePeak				Gauge32,
	pduPhaseCurrent				Gauge32,
	pduPhaseCurrentMax				Gauge32,
	pduPhaseCurrentMin				Gauge32,
	pduPhaseCurrentPeak				Gauge32,
	pduPhaseRealPower				Gauge32,
	pduPhaseApparentPower				Gauge32,
	pduPhasePowerFactor				Gauge32,
	pduPhaseEnergy				Gauge32
}

pduPhaseIndex OBJECT-TYPE
	SYNTAX Integer32(1..100)
	MAX-ACCESS not-accessible
	STATUS current
	DESCRIPTION
		"Table entry index value"
	::= { pduPhaseEntry 1 }

pduPhaseName OBJECT-TYPE
	SYNTAX SnmpAdminString(SIZE (1..25))
	MAX-ACCESS read-only
	STATUS current
	DESCRIPTION
		"PDU phase name (factory-assigned)"
	::= { pduPhaseEntry 2 }

pduPhaseLabel OBJECT-TYPE
	SYNTAX SnmpAdminString(SIZE (0..25))
	MAX-ACCESS read-write
	STATUS current
	DESCRIPTION
		"PDU phase label (user-defined)"
	::= { pduPhaseEntry 3 }

pduPhaseVoltage OBJECT-TYPE
	SYNTAX Gauge32(0..3100)
	UNITS "decivolts (rms)"
	MAX-ACCESS read-only
	STATUS current
	DESCRIPTION
		"PDU phase voltage in tenths of a volt"
	::= { pduPhaseEntry 4 }

pduPhaseVoltageMax OBJECT-TYPE
	SYNTAX Gauge32(0..3100)
	UNITS "decivolts (rms)"
	MAX-ACCESS read-only
	STATUS current
	DESCRIPTION
		"Highest RMS voltage measured on this phase, since power-up or last reset. The value is given in tenths of a volt"
	::= { pduPhaseEntry 5 }

pduPhaseVoltageMin OBJECT-TYPE
	SYNTAX Gauge32(0..3100)
	UNITS "decivolts (rms)"
	MAX-ACCESS read-only
	STATUS current
	DESCRIPTION
		"Lowest RMS voltage measured on this phase, since power-up or last reset. The value is given in tenths of a volt"
	::= { pduPhaseEntry 6 }

pduPhaseVoltagePeak OBJECT-TYPE
	SYNTAX Gauge32(0..4400)
	UNITS "decivolts"
	MAX-ACCESS read-only
	STATUS current
	DESCRIPTION
		"Highest instantaneous voltage measured on this phase, since power-up or last reset. The value is given in tenths of a volt.  This object may not exist on all platforms, due to hardware differences."
	::= { pduPhaseEntry 7 }

pduPhaseCurrent OBJECT-TYPE
	SYNTAX Gauge32(0..9900)
	UNITS "centiamps (rms)"
	MAX-ACCESS read-only
	STATUS current
	DESCRIPTION
		"PDU phase current reading in hundreths of an amp."
	::= { pduPhaseEntry 8 }

pduPhaseCurrentMax OBJECT-TYPE
	SYNTAX Gauge32(0..9900)
	UNITS "centiamps (rms)"
	MAX-ACCESS read-only
	STATUS current
	DESCRIPTION
		"Highest RMS current measured on this phase, since power-up or last reset. The value is given in hundreths of an amp."
	::= { pduPhaseEntry 9 }

pduPhaseCurrentMin OBJECT-TYPE
	SYNTAX Gauge32(0..9900)
	UNITS "centiamps (rms)"
	MAX-ACCESS read-only
	STATUS current
	DESCRIPTION
		"Lowest RMS current measured on this phase, since power-up or last reset. The value is given in hundreths of an amp."
	::= { pduPhaseEntry 10 }

pduPhaseCurrentPeak OBJECT-TYPE
	SYNTAX Gauge32(0..15000)
	UNITS "centiamps"
	MAX-ACCESS read-only
	STATUS current
	DESCRIPTION
		"Highest instantaneous current measured on ths phase, since power-up or last reset. The value is given in hundreths of an amp. This object may not exist on all platforms, due to hardware differences."
	::= { pduPhaseEntry 11 }

pduPhaseRealPower OBJECT-TYPE
	SYNTAX Gauge32(0..9999)
	UNITS "watts"
	MAX-ACCESS read-only
	STATUS current
	DESCRIPTION
		"Real power for phase in watts"
	::= { pduPhaseEntry 12 }

pduPhaseApparentPower OBJECT-TYPE
	SYNTAX Gauge32(0..9999)
	UNITS "volt-amps"
	MAX-ACCESS read-only
	STATUS current
	DESCRIPTION
		"Apparent power for phase in volt-amps"
	::= { pduPhaseEntry 13 }

pduPhasePowerFactor OBJECT-TYPE
	SYNTAX Gauge32(0..100)
	UNITS "%"
	MAX-ACCESS read-only
	STATUS current
	DESCRIPTION
		"Power factor for phase"
	::= { pduPhaseEntry 14 }

pduPhaseEnergy OBJECT-TYPE
	SYNTAX Gauge32(0..9999000)
	UNITS "watt-hours"
	MAX-ACCESS read-only
	STATUS current
	DESCRIPTION
		"Accumulated energy for phase in watt-hours"
	::= { pduPhaseEntry 15 }

--###########################################################################################--
--pduBreakerTable--
--###########################################################################################--

pduBreakerTable OBJECT-TYPE
	SYNTAX SEQUENCE OF PduBreakerEntry
	MAX-ACCESS  not-accessible
	STATUS current
	DESCRIPTION
		"PDU breaker information"
	::= { pdu 3 }

pduBreakerEntry OBJECT-TYPE
	SYNTAX PduBreakerEntry
	MAX-ACCESS  not-accessible
	STATUS current
	DESCRIPTION
		"Entry in the pduBreakerTable table: each entry contains an index and other sensor details"
	INDEX { pduBreakerIndex }
	::= { pduBreakerTable 1 }

PduBreakerEntry ::= SEQUENCE {
	pduBreakerIndex				Integer32,
	pduBreakerName				SnmpAdminString,
	pduBreakerLabel				SnmpAdminString,
	pduBreakerCurrent				Gauge32,
	pduBreakerCurrentMax				Gauge32,
	pduBreakerCurrentMin				Gauge32,
	pduBreakerCurrentPeak				Gauge32
}

pduBreakerIndex OBJECT-TYPE
	SYNTAX Integer32(1..100)
	MAX-ACCESS not-accessible
	STATUS current
	DESCRIPTION
		"Table entry index value"
	::= { pduBreakerEntry 1 }

pduBreakerName OBJECT-TYPE
	SYNTAX SnmpAdminString(SIZE (1..25))
	MAX-ACCESS read-only
	STATUS current
	DESCRIPTION
		"PDU breaker name (factory-assigned)"
	::= { pduBreakerEntry 2 }

pduBreakerLabel OBJECT-TYPE
	SYNTAX SnmpAdminString(SIZE (0..25))
	MAX-ACCESS read-write
	STATUS current
	DESCRIPTION
		"PDU breaker label (user-defined)"
	::= { pduBreakerEntry 3 }

pduBreakerCurrent OBJECT-TYPE
	SYNTAX Gauge32(0..9900)
	UNITS "centiamps (rms)"
	MAX-ACCESS read-only
	STATUS current
	DESCRIPTION
		"PDU breaker current reading in hundreths of an amp"
	::= { pduBreakerEntry 4 }

pduBreakerCurrentMax OBJECT-TYPE
	SYNTAX Gauge32(0..9900)
	UNITS "centiamps (rms)"
	MAX-ACCESS read-only
	STATUS current
	DESCRIPTION
		"Highest RMS current measured on this breaker, since power-up or last reset. The value is given in hundreths of an amp."
	::= { pduBreakerEntry 5 }

pduBreakerCurrentMin OBJECT-TYPE
	SYNTAX Gauge32(0..9900)
	UNITS "centiamps (rms)"
	MAX-ACCESS read-only
	STATUS current
	DESCRIPTION
		"Lowest RMS current measured on this breaker, since power-up or last reset. The value is given in hundreths of an amp."
	::= { pduBreakerEntry 6 }

pduBreakerCurrentPeak OBJECT-TYPE
	SYNTAX Gauge32(0..15000)
	UNITS "centiamps"
	MAX-ACCESS read-only
	STATUS current
	DESCRIPTION
		"Highest instantaneous current measured on this breaker, since power-up or last reset. The value is given in hundreths of an amp. This object may not exist on all platforms, due to hardware differences."
	::= { pduBreakerEntry 7 }

--###########################################################################################--
--pduLineTable--
--###########################################################################################--

pduLineTable OBJECT-TYPE
	SYNTAX SEQUENCE OF PduLineEntry
	MAX-ACCESS  not-accessible
	STATUS current
	DESCRIPTION
		"PDU line current information"
	::= { pdu 4 }

pduLineEntry OBJECT-TYPE
	SYNTAX PduLineEntry
	MAX-ACCESS  not-accessible
	STATUS current
	DESCRIPTION
		"Entry in the pduLineTable table: each entry contains an index and other sensor details"
	INDEX { pduLineIndex }
	::= { pduLineTable 1 }

PduLineEntry ::= SEQUENCE {
	pduLineIndex				Integer32,
	pduLineName				SnmpAdminString,
	pduLineLabel				SnmpAdminString,
	pduLineCurrent				Gauge32,
	pduLineCurrentMax				Gauge32,
	pduLineCurrentMin				Gauge32,
	pduLineCurrentPeak				Gauge32
}

pduLineIndex OBJECT-TYPE
	SYNTAX Integer32(1..100)
	MAX-ACCESS not-accessible
	STATUS current
	DESCRIPTION
		"Table entry index value"
	::= { pduLineEntry 1 }

pduLineName OBJECT-TYPE
	SYNTAX SnmpAdminString(SIZE (1..25))
	MAX-ACCESS read-only
	STATUS current
	DESCRIPTION
		"PDU line name (factory-assigned)"
	::= { pduLineEntry 2 }

pduLineLabel OBJECT-TYPE
	SYNTAX SnmpAdminString(SIZE (0..25))
	MAX-ACCESS read-write
	STATUS current
	DESCRIPTION
		"PDU line label (user-defined)"
	::= { pduLineEntry 3 }

pduLineCurrent OBJECT-TYPE
	SYNTAX Gauge32(0..9900)
	UNITS "centiamps (rms)"
	MAX-ACCESS read-only
	STATUS current
	DESCRIPTION
		"PDU line current reading in hundreths of an amp"
	::= { pduLineEntry 4 }

pduLineCurrentMax OBJECT-TYPE
	SYNTAX Gauge32(0..9900)
	UNITS "centiamps (rms)"
	MAX-ACCESS read-only
	STATUS current
	DESCRIPTION
		"Highest RMS current measured on this line, since power-up or last reset. The value is given in hundreths of an amp."
	::= { pduLineEntry 5 }

pduLineCurrentMin OBJECT-TYPE
	SYNTAX Gauge32(0..9900)
	UNITS "centiamps (rms)"
	MAX-ACCESS read-only
	STATUS current
	DESCRIPTION
		"Lowest RMS current measured on this line, since power-up or last reset. The value is given in hundreths of an amp."
	::= { pduLineEntry 6 }

pduLineCurrentPeak OBJECT-TYPE
	SYNTAX Gauge32(0..15000)
	UNITS "centiamps"
	MAX-ACCESS read-only
	STATUS current
	DESCRIPTION
		"Highest instantaneous current measured on this line, since power-up or last reset. The value is given in hundreths of an amp. This object may not exist on all platforms, due to hardware differences."
	::= { pduLineEntry 7 }

--###########################################################################################--
--tempSensorTable--
--###########################################################################################--

tempSensorTable OBJECT-TYPE
	SYNTAX SEQUENCE OF TempSensorEntry
	MAX-ACCESS  not-accessible
	STATUS current
	DESCRIPTION
		"Remote Temperature (RT) sensor"
	::= { imd 4 }

tempSensorEntry OBJECT-TYPE
	SYNTAX TempSensorEntry
	MAX-ACCESS  not-accessible
	STATUS current
	DESCRIPTION
		"Entry in the tempSensorTable table: each entry contains an index and other sensor details"
	INDEX { tempSensorIndex }
	::= { tempSensorTable 1 }

TempSensorEntry ::= SEQUENCE {
	tempSensorIndex				Integer32,
	tempSensorSerial				DisplayString,
	tempSensorLabel				SnmpAdminString,
	tempSensorAvail				Gauge32,
	tempSensorTemp				Integer32
}

tempSensorIndex OBJECT-TYPE
	SYNTAX Integer32(1..100)
	MAX-ACCESS not-accessible
	STATUS current
	DESCRIPTION
		"Table entry index value"
	::= { tempSensorEntry 1 }

tempSensorSerial OBJECT-TYPE
	SYNTAX DisplayString
	MAX-ACCESS read-only
	STATUS current
	DESCRIPTION
		"Serial Number"
	::= { tempSensorEntry 2 }

tempSensorLabel OBJECT-TYPE
	SYNTAX SnmpAdminString(SIZE (0..25))
	MAX-ACCESS read-write
	STATUS current
	DESCRIPTION
		"User-defined label"
	::= { tempSensorEntry 3 }

tempSensorAvail OBJECT-TYPE
	SYNTAX Gauge32
	MAX-ACCESS read-only
	STATUS current
	DESCRIPTION
		"Device availability:
		0 = Unavailable
		1 = Available
		2 = Partially Unavailable"
	::= { tempSensorEntry 4 }

tempSensorTemp OBJECT-TYPE
	SYNTAX Integer32(-400..2540)
	UNITS "decidegrees"
	MAX-ACCESS read-only
	STATUS current
	DESCRIPTION
		"Temperature in tenths of a degree. Units are given by temperatureUnits field in deviceInfo."
	::= { tempSensorEntry 5 }

--###########################################################################################--
--airFlowSensorTable--
--###########################################################################################--

airFlowSensorTable OBJECT-TYPE
	SYNTAX SEQUENCE OF AirFlowSensorEntry
	MAX-ACCESS  not-accessible
	STATUS current
	DESCRIPTION
		"Remote Airflow, Humidity, Temperature and Dewpoint (AFHT3) Sensor"
	::= { imd 5 }

airFlowSensorEntry OBJECT-TYPE
	SYNTAX AirFlowSensorEntry
	MAX-ACCESS  not-accessible
	STATUS current
	DESCRIPTION
		"Entry in the airFlowSensorTable table: each entry contains an index and other sensor details"
	INDEX { airFlowSensorIndex }
	::= { airFlowSensorTable 1 }

AirFlowSensorEntry ::= SEQUENCE {
	airFlowSensorIndex				Integer32,
	airFlowSensorSerial				DisplayString,
	airFlowSensorLabel				SnmpAdminString,
	airFlowSensorAvail				Gauge32,
	airFlowSensorTemp				Integer32,
	airFlowSensorFlow				Integer32,
	airFlowSensorHumidity				Integer32,
	airFlowSensorDewPoint				Integer32
}

airFlowSensorIndex OBJECT-TYPE
	SYNTAX Integer32(1..100)
	MAX-ACCESS not-accessible
	STATUS current
	DESCRIPTION
		"Table entry index value"
	::= { airFlowSensorEntry 1 }

airFlowSensorSerial OBJECT-TYPE
	SYNTAX DisplayString
	MAX-ACCESS read-only
	STATUS current
	DESCRIPTION
		"Serial Number"
	::= { airFlowSensorEntry 2 }

airFlowSensorLabel OBJECT-TYPE
	SYNTAX SnmpAdminString(SIZE (0..25))
	MAX-ACCESS read-write
	STATUS current
	DESCRIPTION
		"User-defined label"
	::= { airFlowSensorEntry 3 }

airFlowSensorAvail OBJECT-TYPE
	SYNTAX Gauge32
	MAX-ACCESS read-only
	STATUS current
	DESCRIPTION
		"Device availability:
		0 = Unavailable
		1 = Available
		2 = Partially Unavailable"
	::= { airFlowSensorEntry 4 }

airFlowSensorTemp OBJECT-TYPE
	SYNTAX Integer32(-400..2540)
	UNITS "decidegrees"
	MAX-ACCESS read-only
	STATUS current
	DESCRIPTION
		"Current reading for Temperature in tenths of degrees. Units are given by temperatureUnits field in deviceInfo"
	::= { airFlowSensorEntry 5 }

airFlowSensorFlow OBJECT-TYPE
	SYNTAX Integer32(0..100)
	MAX-ACCESS read-only
	STATUS current
	DESCRIPTION
		" Airflow reading. Still air will be less than 20, while rushing air will be around 100."
	::= { airFlowSensorEntry 6 }

airFlowSensorHumidity OBJECT-TYPE
	SYNTAX Integer32(0..100)
	UNITS "%"
	MAX-ACCESS read-only
	STATUS current
	DESCRIPTION
		"Humidity reading"
	::= { airFlowSensorEntry 7 }

airFlowSensorDewPoint OBJECT-TYPE
	SYNTAX Integer32(-400..2540)
	UNITS "decidegrees"
	MAX-ACCESS read-only
	STATUS current
	DESCRIPTION
		" Dewpoint reading in tenths of a degree. Units are given by temperatureUnits field in deviceInfo."
	::= { airFlowSensorEntry 8 }

--###########################################################################################--
--dewPointSensorTable--
--###########################################################################################--

dewPointSensorTable OBJECT-TYPE
	SYNTAX SEQUENCE OF DewPointSensorEntry
	MAX-ACCESS  not-accessible
	STATUS current
	DESCRIPTION
		"Remote Dew Point sensor"
	::= { imd 6 }

dewPointSensorEntry OBJECT-TYPE
	SYNTAX DewPointSensorEntry
	MAX-ACCESS  not-accessible
	STATUS current
	DESCRIPTION
		"Entry in the dewPointSensorTable table: each entry contains an index and other sensor details"
	INDEX { dewPointSensorIndex }
	::= { dewPointSensorTable 1 }

DewPointSensorEntry ::= SEQUENCE {
	dewPointSensorIndex				Integer32,
	dewPointSensorSerial				DisplayString,
	dewPointSensorName				DisplayString,
	dewPointSensorAvail				Gauge32,
	dewPointSensorTemp				Integer32,
	dewPointSensorHumidity				Integer32,
	dewPointSensorDewPoint				Integer32
}

dewPointSensorIndex OBJECT-TYPE
	SYNTAX Integer32(1..100)
	MAX-ACCESS not-accessible
	STATUS current
	DESCRIPTION
		"Table entry index value"
	::= { dewPointSensorEntry 1 }

dewPointSensorSerial OBJECT-TYPE
	SYNTAX DisplayString
	MAX-ACCESS read-only
	STATUS current
	DESCRIPTION
		"Serial Number"
	::= { dewPointSensorEntry 2 }

dewPointSensorName OBJECT-TYPE
	SYNTAX DisplayString
	MAX-ACCESS read-only
	STATUS current
	DESCRIPTION
		"User-defined label"
	::= { dewPointSensorEntry 3 }

dewPointSensorAvail OBJECT-TYPE
	SYNTAX Gauge32
	MAX-ACCESS read-only
	STATUS current
	DESCRIPTION
		"Device availability:
		0 = Unavailable
		1 = Available
		2 = Partially Unavailable"
	::= { dewPointSensorEntry 4 }

dewPointSensorTemp OBJECT-TYPE
	SYNTAX Integer32(-40..200)
	UNITS "decidegrees"
	MAX-ACCESS read-only
	STATUS current
	DESCRIPTION
		"Current reading for Temperature in tenths of degrees. Units are given by temperatureUnits field in deviceInfo"
	::= { dewPointSensorEntry 5 }

dewPointSensorHumidity OBJECT-TYPE
	SYNTAX Integer32(0..100)
	UNITS "%"
	MAX-ACCESS read-only
	STATUS current
	DESCRIPTION
		"Humidity reading"
	::= { dewPointSensorEntry 6 }

dewPointSensorDewPoint OBJECT-TYPE
	SYNTAX Integer32(-40..200)
	UNITS "decidegrees"
	MAX-ACCESS read-only
	STATUS current
	DESCRIPTION
		"Current reading for Dew-point in tenths of degrees. Units are given by temperatureUnits field in deviceInfo"
	::= { dewPointSensorEntry 7 }

--###########################################################################################--
--ccatSensorTable--
--###########################################################################################--

ccatSensorTable OBJECT-TYPE
	SYNTAX SEQUENCE OF CcatSensorEntry
	MAX-ACCESS  not-accessible
	STATUS current
	DESCRIPTION
		"Remote CCAT sensor"
	::= { imd 7 }

ccatSensorEntry OBJECT-TYPE
	SYNTAX CcatSensorEntry
	MAX-ACCESS  not-accessible
	STATUS current
	DESCRIPTION
		"Entry in the ccatSensorTable table: each entry contains an index and other sensor details"
	INDEX { ccatSensorIndex }
	::= { ccatSensorTable 1 }

CcatSensorEntry ::= SEQUENCE {
	ccatSensorIndex				Integer32,
	ccatSensorSerial				DisplayString,
	ccatSensorName				DisplayString,
	ccatSensorAvail				Gauge32,
	ccatSensorValue				Integer32,
	ccatSensorType				DisplayString,
	ccatSensorDescription				DisplayString
}

ccatSensorIndex OBJECT-TYPE
	SYNTAX Integer32(1..100)
	MAX-ACCESS not-accessible
	STATUS current
	DESCRIPTION
		"Table entry index value"
	::= { ccatSensorEntry 1 }

ccatSensorSerial OBJECT-TYPE
	SYNTAX DisplayString
	MAX-ACCESS read-only
	STATUS current
	DESCRIPTION
		"Serial Number"
	::= { ccatSensorEntry 2 }

ccatSensorName OBJECT-TYPE
	SYNTAX DisplayString
	MAX-ACCESS read-only
	STATUS current
	DESCRIPTION
		"User-defined label"
	::= { ccatSensorEntry 3 }

ccatSensorAvail OBJECT-TYPE
	SYNTAX Gauge32
	MAX-ACCESS read-only
	STATUS current
	DESCRIPTION
		"Device availability:
		0 = Unavailable
		1 = Available
		2 = Partially Unavailable"
	::= { ccatSensorEntry 4 }

ccatSensorValue OBJECT-TYPE
	SYNTAX Integer32(-100..5000)
	MAX-ACCESS read-only
	STATUS current
	DESCRIPTION
		"CCAT sensor reading"
	::= { ccatSensorEntry 5 }

ccatSensorType OBJECT-TYPE
	SYNTAX DisplayString
	MAX-ACCESS read-only
	STATUS current
	DESCRIPTION
		"CCAT sensor type"
	::= { ccatSensorEntry 6 }

ccatSensorDescription OBJECT-TYPE
	SYNTAX DisplayString
	MAX-ACCESS read-only
	STATUS current
	DESCRIPTION
		"CCAT sensor value description"
	::= { ccatSensorEntry 7 }

--###########################################################################################--
--t3hdSensorTable--
--###########################################################################################--

t3hdSensorTable OBJECT-TYPE
	SYNTAX SEQUENCE OF T3hdSensorEntry
	MAX-ACCESS  not-accessible
	STATUS current
	DESCRIPTION
		"Remote Temperature x 3, Humidity and Dewpoint Sensor"
	::= { imd 8 }

t3hdSensorEntry OBJECT-TYPE
	SYNTAX T3hdSensorEntry
	MAX-ACCESS  not-accessible
	STATUS current
	DESCRIPTION
		"Entry in the t3hdSensorTable table: each entry contains an index and other sensor details"
	INDEX { t3hdSensorIndex }
	::= { t3hdSensorTable 1 }

T3hdSensorEntry ::= SEQUENCE {
	t3hdSensorIndex				Integer32,
	t3hdSensorSerial				DisplayString,
	t3hdSensorLabel				SnmpAdminString,
	t3hdSensorAvail				Gauge32,
	t3hdSensorIntLabel				SnmpAdminString,
	t3hdSensorIntTemp				Integer32,
	t3hdSensorIntHumidity				Integer32,
	t3hdSensorIntDewPoint				Integer32,
	t3hdSensorExtAAvail				Gauge32,
	t3hdSensorExtALabel				SnmpAdminString,
	t3hdSensorExtATemp				Integer32,
	t3hdSensorExtBAvail				Gauge32,
	t3hdSensorExtBLabel				SnmpAdminString,
	t3hdSensorExtBTemp				Integer32
}

t3hdSensorIndex OBJECT-TYPE
	SYNTAX Integer32(1..100)
	MAX-ACCESS not-accessible
	STATUS current
	DESCRIPTION
		"Table entry index value"
	::= { t3hdSensorEntry 1 }

t3hdSensorSerial OBJECT-TYPE
	SYNTAX DisplayString
	MAX-ACCESS read-only
	STATUS current
	DESCRIPTION
		"Serial Number"
	::= { t3hdSensorEntry 2 }

t3hdSensorLabel OBJECT-TYPE
	SYNTAX SnmpAdminString(SIZE (0..25))
	MAX-ACCESS read-write
	STATUS current
	DESCRIPTION
		"User-defined label"
	::= { t3hdSensorEntry 3 }

t3hdSensorAvail OBJECT-TYPE
	SYNTAX Gauge32
	MAX-ACCESS read-only
	STATUS current
	DESCRIPTION
		"Device availability:
		0 = Unavailable
		1 = Available
		2 = Partially Unavailable"
	::= { t3hdSensorEntry 4 }

t3hdSensorIntLabel OBJECT-TYPE
	SYNTAX SnmpAdminString(SIZE (0..25))
	MAX-ACCESS read-write
	STATUS current
	DESCRIPTION
		"Internal label (user-defined)"
	::= { t3hdSensorEntry 5 }

t3hdSensorIntTemp OBJECT-TYPE
	SYNTAX Integer32(-400..2540)
	UNITS "decidegrees"
	MAX-ACCESS read-only
	STATUS current
	DESCRIPTION
		"Internal temperature in tenths of a degree. Units are given by temperatureUnits field in deviceInfo."
	::= { t3hdSensorEntry 6 }

t3hdSensorIntHumidity OBJECT-TYPE
	SYNTAX Integer32(0..100)
	UNITS "%"
	MAX-ACCESS read-only
	STATUS current
	DESCRIPTION
		"Internal Humidity"
	::= { t3hdSensorEntry 7 }

t3hdSensorIntDewPoint OBJECT-TYPE
	SYNTAX Integer32(-400..2540)
	UNITS "decidegrees"
	MAX-ACCESS read-only
	STATUS current
	DESCRIPTION
		"Internal dewpoint in tenths of a degree. Units are given by temperatureUnits field in deviceInfo."
	::= { t3hdSensorEntry 8 }

t3hdSensorExtAAvail OBJECT-TYPE
	SYNTAX Gauge32
	MAX-ACCESS read-only
	STATUS current
	DESCRIPTION
		"External A status:
		0 =Unavailable
		1 =Available"
	::= { t3hdSensorEntry 9 }

t3hdSensorExtALabel OBJECT-TYPE
	SYNTAX SnmpAdminString(SIZE (0..25))
	MAX-ACCESS read-write
	STATUS current
	DESCRIPTION
		"External A label (user-defined)"
	::= { t3hdSensorEntry 10 }

t3hdSensorExtATemp OBJECT-TYPE
	SYNTAX Integer32(-400..2540)
	UNITS "decidegrees"
	MAX-ACCESS read-only
	STATUS current
	DESCRIPTION
		" External A temperature in tenths of a degree. Units are given by temperatureUnits field in deviceInfo."
	::= { t3hdSensorEntry 11 }

t3hdSensorExtBAvail OBJECT-TYPE
	SYNTAX Gauge32
	MAX-ACCESS read-only
	STATUS current
	DESCRIPTION
		"External B status:
		0 = Unavailable
		1 = Available"
	::= { t3hdSensorEntry 12 }

t3hdSensorExtBLabel OBJECT-TYPE
	SYNTAX SnmpAdminString(SIZE (0..25))
	MAX-ACCESS read-write
	STATUS current
	DESCRIPTION
		"External B label (user-defined)"
	::= { t3hdSensorEntry 13 }

t3hdSensorExtBTemp OBJECT-TYPE
	SYNTAX Integer32(-400..2540)
	UNITS "decidegrees"
	MAX-ACCESS read-only
	STATUS current
	DESCRIPTION
		"External B temperature in tenths of a degree. Units are given by temperatureUnits field in deviceInfo."
	::= { t3hdSensorEntry 14 }

--###########################################################################################--
--thdSensorTable--
--###########################################################################################--

thdSensorTable OBJECT-TYPE
	SYNTAX SEQUENCE OF ThdSensorEntry
	MAX-ACCESS  not-accessible
	STATUS current
	DESCRIPTION
		"Remote Temperature, Humidity and Dewpoint (THD) Sensor"
	::= { imd 9 }

thdSensorEntry OBJECT-TYPE
	SYNTAX ThdSensorEntry
	MAX-ACCESS  not-accessible
	STATUS current
	DESCRIPTION
		"Entry in the thdSensorTable table: each entry contains an index and other sensor details"
	INDEX { thdSensorIndex }
	::= { thdSensorTable 1 }

ThdSensorEntry ::= SEQUENCE {
	thdSensorIndex				Integer32,
	thdSensorSerial				DisplayString,
	thdSensorLabel				SnmpAdminString,
	thdSensorAvail				Gauge32,
	thdSensorTemp				Integer32,
	thdSensorHumidity				Integer32,
	thdSensorDewPoint				Integer32
}

thdSensorIndex OBJECT-TYPE
	SYNTAX Integer32(1..100)
	MAX-ACCESS not-accessible
	STATUS current
	DESCRIPTION
		"Table entry index value"
	::= { thdSensorEntry 1 }

thdSensorSerial OBJECT-TYPE
	SYNTAX DisplayString
	MAX-ACCESS read-only
	STATUS current
	DESCRIPTION
		"Serial Number"
	::= { thdSensorEntry 2 }

thdSensorLabel OBJECT-TYPE
	SYNTAX SnmpAdminString(SIZE (0..25))
	MAX-ACCESS read-write
	STATUS current
	DESCRIPTION
		"User-defined label"
	::= { thdSensorEntry 3 }

thdSensorAvail OBJECT-TYPE
	SYNTAX Gauge32
	MAX-ACCESS read-only
	STATUS current
	DESCRIPTION
		"Device availability:
		0 = Unavailable
		1 = Available
		2 = Partially Unavailable"
	::= { thdSensorEntry 4 }

thdSensorTemp OBJECT-TYPE
	SYNTAX Integer32(-400..2540)
	UNITS "decidegrees"
	MAX-ACCESS read-only
	STATUS current
	DESCRIPTION
		" Temperature value in tenths of a degree. Units are given by temperatureUnits field in deviceInfo."
	::= { thdSensorEntry 5 }

thdSensorHumidity OBJECT-TYPE
	SYNTAX Integer32(0..100)
	UNITS "%"
	MAX-ACCESS read-only
	STATUS current
	DESCRIPTION
		"Humidity value"
	::= { thdSensorEntry 6 }

thdSensorDewPoint OBJECT-TYPE
	SYNTAX Integer32(-400..2540)
	UNITS "decidegrees"
	MAX-ACCESS read-only
	STATUS current
	DESCRIPTION
		"Dewpoint value in tenths of a degree. Units are given by temperatureUnits field in deviceInfo."
	::= { thdSensorEntry 7 }

--###########################################################################################--
--rpmSensorTable--
--###########################################################################################--

rpmSensorTable OBJECT-TYPE
	SYNTAX SEQUENCE OF RpmSensorEntry
	MAX-ACCESS  not-accessible
	STATUS current
	DESCRIPTION
		"Remote Power Manager Sensor"
	::= { imd 10 }

rpmSensorEntry OBJECT-TYPE
	SYNTAX RpmSensorEntry
	MAX-ACCESS  not-accessible
	STATUS current
	DESCRIPTION
		"Entry in the rpmSensorTable table: each entry contains an index and other sensor details"
	INDEX { rpmSensorIndex }
	::= { rpmSensorTable 1 }

RpmSensorEntry ::= SEQUENCE {
	rpmSensorIndex				Integer32,
	rpmSensorSerial				DisplayString,
	rpmSensorName				DisplayString,
	rpmSensorAvail				Gauge32,
	rpmSensorEnergy				Gauge32,
	rpmSensorVoltage				Gauge32,
	rpmSensorVoltageMax				Gauge32,
	rpmSensorVoltageMin				Gauge32,
	rpmSensorVoltagePeak				Gauge32,
	rpmSensorCurrent				Gauge32,
	rpmSensorRealPower				Gauge32,
	rpmSensorApparentPower				Gauge32,
	rpmSensorPowerFactor				Gauge32,
	rpmSensorOutlet1				Gauge32,
	rpmSensorOutlet2				Gauge32
}

rpmSensorIndex OBJECT-TYPE
	SYNTAX Integer32(1..100)
	MAX-ACCESS not-accessible
	STATUS current
	DESCRIPTION
		"Table entry index value"
	::= { rpmSensorEntry 1 }

rpmSensorSerial OBJECT-TYPE
	SYNTAX DisplayString
	MAX-ACCESS read-only
	STATUS current
	DESCRIPTION
		"Serial Number"
	::= { rpmSensorEntry 2 }

rpmSensorName OBJECT-TYPE
	SYNTAX DisplayString
	MAX-ACCESS read-only
	STATUS current
	DESCRIPTION
		"Friendly Name"
	::= { rpmSensorEntry 3 }

rpmSensorAvail OBJECT-TYPE
	SYNTAX Gauge32
	MAX-ACCESS read-only
	STATUS current
	DESCRIPTION
		"Device availability
		0 = Unavailable
		1 = Available
		2 = Partially Unavailable"
	::= { rpmSensorEntry 4 }

rpmSensorEnergy OBJECT-TYPE
	SYNTAX Gauge32
	UNITS "kWh"
	MAX-ACCESS read-only
	STATUS current
	DESCRIPTION
		"RPM Sensor Accumulated Energy"
	::= { rpmSensorEntry 5 }

rpmSensorVoltage OBJECT-TYPE
	SYNTAX Gauge32
	UNITS "Volts (rms)"
	MAX-ACCESS read-only
	STATUS current
	DESCRIPTION
		"RPM Sensor Voltage"
	::= { rpmSensorEntry 6 }

rpmSensorVoltageMax OBJECT-TYPE
	SYNTAX Gauge32
	UNITS "Volts (rms)"
	MAX-ACCESS read-only
	STATUS current
	DESCRIPTION
		"RPM Sensor Voltage (Max)"
	::= { rpmSensorEntry 7 }

rpmSensorVoltageMin OBJECT-TYPE
	SYNTAX Gauge32
	UNITS "Volts (rms)"
	MAX-ACCESS read-only
	STATUS current
	DESCRIPTION
		"RPM Sensor Voltage (Min)"
	::= { rpmSensorEntry 8 }

rpmSensorVoltagePeak OBJECT-TYPE
	SYNTAX Gauge32
	UNITS "Volts"
	MAX-ACCESS read-only
	STATUS current
	DESCRIPTION
		"RPM Sensor Voltage (Peak)"
	::= { rpmSensorEntry 9 }

rpmSensorCurrent OBJECT-TYPE
	SYNTAX Gauge32
	UNITS "0.1 Amps (rms)"
	MAX-ACCESS read-only
	STATUS current
	DESCRIPTION
		"RPM Sensor Current reading in deciAmps"
	::= { rpmSensorEntry 10 }

rpmSensorRealPower OBJECT-TYPE
	SYNTAX Gauge32
	UNITS "Watts"
	MAX-ACCESS read-only
	STATUS current
	DESCRIPTION
		"RPM Sensor Real Power"
	::= { rpmSensorEntry 11 }

rpmSensorApparentPower OBJECT-TYPE
	SYNTAX Gauge32
	UNITS "Volt-Amps"
	MAX-ACCESS read-only
	STATUS current
	DESCRIPTION
		"RPM Sensor Apparent Power"
	::= { rpmSensorEntry 12 }

rpmSensorPowerFactor OBJECT-TYPE
	SYNTAX Gauge32
	UNITS "%"
	MAX-ACCESS read-only
	STATUS current
	DESCRIPTION
		"RPM Sensor Power Factor"
	::= { rpmSensorEntry 13 }

rpmSensorOutlet1 OBJECT-TYPE
	SYNTAX Gauge32
	MAX-ACCESS read-only
	STATUS current
	DESCRIPTION
		"RPM Sensor Outlet 1 State: 0 = off, 1 = on"
	::= { rpmSensorEntry 14 }

rpmSensorOutlet2 OBJECT-TYPE
	SYNTAX Gauge32
	MAX-ACCESS read-only
	STATUS current
	DESCRIPTION
		"RPM Sensor Outlet 2 State:
		0 = off
		1 = on"
	::= { rpmSensorEntry 15 }

--###########################################################################################--
--a2dSensorTable--
--###########################################################################################--

a2dSensorTable OBJECT-TYPE
	SYNTAX SEQUENCE OF A2dSensorEntry
	MAX-ACCESS  not-accessible
	STATUS current
	DESCRIPTION
		"Analog measurement (A2D) sensor (voltage, current, or dry-contact)"
	::= { imd 11 }

a2dSensorEntry OBJECT-TYPE
	SYNTAX A2dSensorEntry
	MAX-ACCESS  not-accessible
	STATUS current
	DESCRIPTION
		"Entry in the a2dSensorTable table: each entry contains an index and other sensor details"
	INDEX { a2dSensorIndex }
	::= { a2dSensorTable 1 }

A2dSensorEntry ::= SEQUENCE {
	a2dSensorIndex				Integer32,
	a2dSensorSerial				DisplayString,
	a2dSensorLabel				SnmpAdminString,
	a2dSensorAvail				Gauge32,
	a2dSensorValue				Integer32,
	a2dSensorDisplayValue				SnmpAdminString,
	a2dSensorMode				INTEGER,
	a2dSensorUnits				SnmpAdminString,
	a2dSensorMin				Integer32,
	a2dSensorMax				Integer32,
	a2dSensorLowLabel				SnmpAdminString,
	a2dSensorHighLabel				SnmpAdminString,
	a2dSensorAnalogLabel				SnmpAdminString
}

a2dSensorIndex OBJECT-TYPE
	SYNTAX Integer32(1..100)
	MAX-ACCESS not-accessible
	STATUS current
	DESCRIPTION
		"Table entry index value"
	::= { a2dSensorEntry 1 }

a2dSensorSerial OBJECT-TYPE
	SYNTAX DisplayString
	MAX-ACCESS read-only
	STATUS current
	DESCRIPTION
		"Serial Number"
	::= { a2dSensorEntry 2 }

a2dSensorLabel OBJECT-TYPE
	SYNTAX SnmpAdminString(SIZE (0..25))
	MAX-ACCESS read-write
	STATUS current
	DESCRIPTION
		"User-defined label"
	::= { a2dSensorEntry 3 }

a2dSensorAvail OBJECT-TYPE
	SYNTAX Gauge32
	MAX-ACCESS read-only
	STATUS current
	DESCRIPTION
		"Device availability:
		0 = Unavailable
		1 = Available
		2 = Partially Unavailable"
	::= { a2dSensorEntry 4 }

a2dSensorValue OBJECT-TYPE
	SYNTAX Integer32(-1000000..1000000)
	MAX-ACCESS read-only
	STATUS current
	DESCRIPTION
		"Analog measurement value, within either a user-defined or preset range, depending on a2dSensorMode."
	::= { a2dSensorEntry 5 }

a2dSensorDisplayValue OBJECT-TYPE
	SYNTAX SnmpAdminString(SIZE (0..25))
	MAX-ACCESS read-only
	STATUS current
	DESCRIPTION
		" For current/voltage modes, the analog value is given as a string. In binary modes, the value is either a2dSensorLowLabel or a2dSensorHighLabel, based on a2dSensorValue."
	::= { a2dSensorEntry 6 }

a2dSensorMode OBJECT-TYPE
	SYNTAX INTEGER {
			door(1),
			powerFailure(2),
			flood(3),
			wscLeak(4),
			wscFault(5),
			smoke(6),
			ivsNegGnd(7),
			ivsPosGnd(8),
			customVoltage(9),
			customBinary(10),
			customCurrent(11)
			}
	MAX-ACCESS read-write
	STATUS current
	DESCRIPTION
		"Binary modes have two states represented by the values 0 (low) or 1 (high). These correspond to a2dSensorLowLabel and a2dSensorHighLabel. Current and voltage modes provide a scaled value from a2dSensorMin to a2dSensorMax. Analog modes: 1 =Door (binary) 2 =Power failure (binary) 3 =Flood (binary) 4 =Water-sensing cable leak (binary) 5 =Water-sensing cable fault (binary) 6 =Smoke alarm (binary) 7 =Isolated voltage negative ground (voltage) 8 =Isolated voltage positive ground (voltage) 9 =Custom voltage (voltage) 10 =Custom binary (binary) 11 =Custom current (current)"
	::= { a2dSensorEntry 7 }

a2dSensorUnits OBJECT-TYPE
	SYNTAX SnmpAdminString(SIZE (0..7))
	MAX-ACCESS read-write
	STATUS current
	DESCRIPTION
		"The units for the analog value. If a2dSensorMode is customVoltage(9) or customCurrent(11), then this field has a user-defined value. Otherwise, the value is fixed, based on mode."
	::= { a2dSensorEntry 8 }

a2dSensorMin OBJECT-TYPE
	SYNTAX Integer32(-1000000..1000000)
	MAX-ACCESS read-write
	STATUS current
	DESCRIPTION
		"Minimum analog value, given as an integer. The analog measurement is scaled to the range a2dSensorMin to a2dSensorMax. If a2dSensorMode is customVoltage(9) or customCurrent(11), then this field has a user-defined value. Otherwise, the value is fixed, based on mode."
	::= { a2dSensorEntry 9 }

a2dSensorMax OBJECT-TYPE
	SYNTAX Integer32(-1000000..1000000)
	MAX-ACCESS read-write
	STATUS current
	DESCRIPTION
		"Maximum analog value, given as an integer. The analog measurement is scaled to the range a2dSensorMin to a2dSensorMax. If a2dSensorMode is customVoltage(9) or customCurrent(11), then this field has a user-defined value. Otherwise, the value is fixed, based on mode."
	::= { a2dSensorEntry 10 }

a2dSensorLowLabel OBJECT-TYPE
	SYNTAX SnmpAdminString(SIZE (0..25))
	MAX-ACCESS read-write
	STATUS current
	DESCRIPTION
		"Label for 0 (low) binary value. This field is only applicable if a2dSensorMode is one of the binary modes. If a2dSensorMode is customBinary(10), then this field is user-defined. Otherwise, it has a pre-defined value based on the mode."
	::= { a2dSensorEntry 11 }

a2dSensorHighLabel OBJECT-TYPE
	SYNTAX SnmpAdminString(SIZE (0..25))
	MAX-ACCESS read-write
	STATUS current
	DESCRIPTION
		"Label for 1 (high) binary value. The field is only applicable if a2dSensorMode is one of the binary modes. If a2dSensorMode is customBinary(10), then this field is user-defined. Otherwise, it has a pre-defined value based on the mode."
	::= { a2dSensorEntry 12 }

a2dSensorAnalogLabel OBJECT-TYPE
	SYNTAX SnmpAdminString(SIZE (0..25))
	MAX-ACCESS read-write
	STATUS current
	DESCRIPTION
		" Label for the analog measurement"
	::= { a2dSensorEntry 13 }

common OBJECT IDENTIFIER ::= { vertiv 42 }
identity OBJECT IDENTIFIER ::= { common 1 }

wd15 OBJECT-IDENTITY
	STATUS current
	DESCRIPTION
		"Value (OID) used to identify a WD-15 unit"
	::= { identity 31 }

wd100 OBJECT-IDENTITY
	STATUS current
	DESCRIPTION
		"Value (OID) used to identify a WD-100 unit"
	::= { identity 32 }

i02 OBJECT-IDENTITY
	STATUS current
	DESCRIPTION
		"Value (OID) used to identify a GU1 (I-02) unit"
	::= { identity 52 }

--###########################################################################################--
--Notifications--
--###########################################################################################--

trap OBJECT IDENTIFIER ::= { imd 32767 }
trapPrefix OBJECT IDENTIFIER ::= { trap 0 }

trapObj OBJECT IDENTIFIER ::= { trap 1 }

trapSeverity OBJECT-TYPE
	SYNTAX INTEGER {
			none(0),
			warning(1),
			alarm(2)
			}
	MAX-ACCESS  accessible-for-notify
	STATUS current
	DESCRIPTION
		"Indicates the severity of the trap:
		0 = None,
		1 = Warning,
		2 = Alarm"
	::= { trapObj 1 }

trapThreshType OBJECT-TYPE
	SYNTAX INTEGER {
			low(1),
			high(2)
			}
	MAX-ACCESS  accessible-for-notify
	STATUS current
	DESCRIPTION
		"Only sent for threshold alarms.  Identifies the threshold type:
		1 = Low, 
		2 = High"
	::= { trapObj 2 }

internalTestNOTIFY NOTIFICATION-TYPE
	STATUS current
	DESCRIPTION
		"Test SNMP Trap"
	::= { trapPrefix 10101 }

--#####deviceInfo#####--

--#####pdu#####--

--#####pduMainTable#####--

pduMainAvailNOTIFY NOTIFICATION-TYPE
	OBJECTS {
			pduMainAvail,
			trapSeverity,
			sysName,
			pduMainLabel
			}
	STATUS current
	DESCRIPTION "PDU availability trap"
	::= { trapPrefix 10305 }

pduMainAvailCLEAR NOTIFICATION-TYPE
	OBJECTS {
			pduMainAvail,
			trapSeverity,
			sysName,
			pduMainLabel
			}
	STATUS current
	DESCRIPTION "PDU availability clear trap"
	::= { trapPrefix 20305 }

pduTotalRealPowerNOTIFY NOTIFICATION-TYPE
	OBJECTS {
			pduTotalRealPower,
			trapThreshType,
			trapSeverity,
			sysName,
			pduMainLabel,
			pduTotalLabel
			}
	STATUS current
	DESCRIPTION "PDU total real power trap"
	::= { trapPrefix 10309 }

pduTotalRealPowerCLEAR NOTIFICATION-TYPE
	OBJECTS {
			pduTotalRealPower,
			trapThreshType,
			trapSeverity,
			sysName,
			pduMainLabel,
			pduTotalLabel
			}
	STATUS current
	DESCRIPTION "PDU total real power clear trap"
	::= { trapPrefix 20309 }

pduTotalApparentPowerNOTIFY NOTIFICATION-TYPE
	OBJECTS {
			pduTotalApparentPower,
			trapThreshType,
			trapSeverity,
			sysName,
			pduMainLabel,
			pduTotalLabel
			}
	STATUS current
	DESCRIPTION "PDU total apparent power trap"
	::= { trapPrefix 10310 }

pduTotalApparentPowerCLEAR NOTIFICATION-TYPE
	OBJECTS {
			pduTotalApparentPower,
			trapThreshType,
			trapSeverity,
			sysName,
			pduMainLabel,
			pduTotalLabel
			}
	STATUS current
	DESCRIPTION "PDU total apparent power clear trap"
	::= { trapPrefix 20310 }

pduTotalPowerFactorNOTIFY NOTIFICATION-TYPE
	OBJECTS {
			pduTotalPowerFactor,
			trapThreshType,
			trapSeverity,
			sysName,
			pduMainLabel,
			pduTotalLabel
			}
	STATUS current
	DESCRIPTION "PDU total power factor trap"
	::= { trapPrefix 10311 }

pduTotalPowerFactorCLEAR NOTIFICATION-TYPE
	OBJECTS {
			pduTotalPowerFactor,
			trapThreshType,
			trapSeverity,
			sysName,
			pduMainLabel,
			pduTotalLabel
			}
	STATUS current
	DESCRIPTION "PDU total power factor clear trap"
	::= { trapPrefix 20311 }

pduTotalEnergyNOTIFY NOTIFICATION-TYPE
	OBJECTS {
			pduTotalEnergy,
			trapThreshType,
			trapSeverity,
			sysName,
			pduMainLabel,
			pduTotalLabel
			}
	STATUS current
	DESCRIPTION "PDU total energy trap"
	::= { trapPrefix 10312 }

pduTotalEnergyCLEAR NOTIFICATION-TYPE
	OBJECTS {
			pduTotalEnergy,
			trapThreshType,
			trapSeverity,
			sysName,
			pduMainLabel,
			pduTotalLabel
			}
	STATUS current
	DESCRIPTION "PDU total energy clear trap"
	::= { trapPrefix 20312 }

--#####pduPhaseTable#####--

pduPhaseVoltageNOTIFY NOTIFICATION-TYPE
	OBJECTS {
			pduPhaseVoltage,
			trapThreshType,
			trapSeverity,
			sysName,
			pduMainLabel,
			pduPhaseLabel
			}
	STATUS current
	DESCRIPTION "PDU phase voltage trap"
	::= { trapPrefix 10324 }

pduPhaseVoltageCLEAR NOTIFICATION-TYPE
	OBJECTS {
			pduPhaseVoltage,
			trapThreshType,
			trapSeverity,
			sysName,
			pduMainLabel,
			pduPhaseLabel
			}
	STATUS current
	DESCRIPTION "PDU phase voltage clear trap"
	::= { trapPrefix 20324 }

pduPhaseVoltageMaxNOTIFY NOTIFICATION-TYPE
	OBJECTS {
			pduPhaseVoltageMax,
			trapThreshType,
			trapSeverity,
			sysName,
			pduMainLabel,
			pduPhaseLabel
			}
	STATUS current
	DESCRIPTION "PDU phase voltage (max) trap"
	::= { trapPrefix 10325 }

pduPhaseVoltageMaxCLEAR NOTIFICATION-TYPE
	OBJECTS {
			pduPhaseVoltageMax,
			trapThreshType,
			trapSeverity,
			sysName,
			pduMainLabel,
			pduPhaseLabel
			}
	STATUS current
	DESCRIPTION "PDU phase voltage (max) clear trap"
	::= { trapPrefix 20325 }

pduPhaseVoltageMinNOTIFY NOTIFICATION-TYPE
	OBJECTS {
			pduPhaseVoltageMin,
			trapThreshType,
			trapSeverity,
			sysName,
			pduMainLabel,
			pduPhaseLabel
			}
	STATUS current
	DESCRIPTION "PDU phase voltage (min) trap"
	::= { trapPrefix 10326 }

pduPhaseVoltageMinCLEAR NOTIFICATION-TYPE
	OBJECTS {
			pduPhaseVoltageMin,
			trapThreshType,
			trapSeverity,
			sysName,
			pduMainLabel,
			pduPhaseLabel
			}
	STATUS current
	DESCRIPTION "PDU phase voltage (min) clear trap"
	::= { trapPrefix 20326 }

pduPhaseVoltagePeakNOTIFY NOTIFICATION-TYPE
	OBJECTS {
			pduPhaseVoltagePeak,
			trapThreshType,
			trapSeverity,
			sysName,
			pduMainLabel,
			pduPhaseLabel
			}
	STATUS current
	DESCRIPTION "PDU phase voltage (peak) trap"
	::= { trapPrefix 10327 }

pduPhaseVoltagePeakCLEAR NOTIFICATION-TYPE
	OBJECTS {
			pduPhaseVoltagePeak,
			trapThreshType,
			trapSeverity,
			sysName,
			pduMainLabel,
			pduPhaseLabel
			}
	STATUS current
	DESCRIPTION "PDU phase voltage (peak) clear trap"
	::= { trapPrefix 20327 }

pduPhaseCurrentNOTIFY NOTIFICATION-TYPE
	OBJECTS {
			pduPhaseCurrent,
			trapThreshType,
			trapSeverity,
			sysName,
			pduMainLabel,
			pduPhaseLabel
			}
	STATUS current
	DESCRIPTION "PDU phase current trap"
	::= { trapPrefix 10328 }

pduPhaseCurrentCLEAR NOTIFICATION-TYPE
	OBJECTS {
			pduPhaseCurrent,
			trapThreshType,
			trapSeverity,
			sysName,
			pduMainLabel,
			pduPhaseLabel
			}
	STATUS current
	DESCRIPTION "PDU phase current clear trap"
	::= { trapPrefix 20328 }

pduPhaseCurrentMaxNOTIFY NOTIFICATION-TYPE
	OBJECTS {
			pduPhaseCurrentMax,
			trapThreshType,
			trapSeverity,
			sysName,
			pduMainLabel,
			pduPhaseLabel
			}
	STATUS current
	DESCRIPTION "PDU phase current (max) trap"
	::= { trapPrefix 10329 }

pduPhaseCurrentMaxCLEAR NOTIFICATION-TYPE
	OBJECTS {
			pduPhaseCurrentMax,
			trapThreshType,
			trapSeverity,
			sysName,
			pduMainLabel,
			pduPhaseLabel
			}
	STATUS current
	DESCRIPTION "PDU phase current (max) clear trap"
	::= { trapPrefix 20329 }

pduPhaseCurrentMinNOTIFY NOTIFICATION-TYPE
	OBJECTS {
			pduPhaseCurrentMin,
			trapThreshType,
			trapSeverity,
			sysName,
			pduMainLabel,
			pduPhaseLabel
			}
	STATUS current
	DESCRIPTION "PDU phase current (min) trap"
	::= { trapPrefix 10330 }

pduPhaseCurrentMinCLEAR NOTIFICATION-TYPE
	OBJECTS {
			pduPhaseCurrentMin,
			trapThreshType,
			trapSeverity,
			sysName,
			pduMainLabel,
			pduPhaseLabel
			}
	STATUS current
	DESCRIPTION "PDU phase current (min) clear trap"
	::= { trapPrefix 20330 }

pduPhaseCurrentPeakNOTIFY NOTIFICATION-TYPE
	OBJECTS {
			pduPhaseCurrentPeak,
			trapThreshType,
			trapSeverity,
			sysName,
			pduMainLabel,
			pduPhaseLabel
			}
	STATUS current
	DESCRIPTION "PDU phase current (peak) trap"
	::= { trapPrefix 10331 }

pduPhaseCurrentPeakCLEAR NOTIFICATION-TYPE
	OBJECTS {
			pduPhaseCurrentPeak,
			trapThreshType,
			trapSeverity,
			sysName,
			pduMainLabel,
			pduPhaseLabel
			}
	STATUS current
	DESCRIPTION "PDU phase current (peak) clear trap"
	::= { trapPrefix 20331 }

pduPhaseRealPowerNOTIFY NOTIFICATION-TYPE
	OBJECTS {
			pduPhaseRealPower,
			trapThreshType,
			trapSeverity,
			sysName,
			pduMainLabel,
			pduPhaseLabel
			}
	STATUS current
	DESCRIPTION "PDU phase real power trap"
	::= { trapPrefix 10332 }

pduPhaseRealPowerCLEAR NOTIFICATION-TYPE
	OBJECTS {
			pduPhaseRealPower,
			trapThreshType,
			trapSeverity,
			sysName,
			pduMainLabel,
			pduPhaseLabel
			}
	STATUS current
	DESCRIPTION "PDU phase real power clear trap"
	::= { trapPrefix 20332 }

pduPhaseApparentPowerNOTIFY NOTIFICATION-TYPE
	OBJECTS {
			pduPhaseApparentPower,
			trapThreshType,
			trapSeverity,
			sysName,
			pduMainLabel,
			pduPhaseLabel
			}
	STATUS current
	DESCRIPTION "PDU phase apparent power trap"
	::= { trapPrefix 10333 }

pduPhaseApparentPowerCLEAR NOTIFICATION-TYPE
	OBJECTS {
			pduPhaseApparentPower,
			trapThreshType,
			trapSeverity,
			sysName,
			pduMainLabel,
			pduPhaseLabel
			}
	STATUS current
	DESCRIPTION "PDU phase apparent power clear trap"
	::= { trapPrefix 20333 }

pduPhasePowerFactorNOTIFY NOTIFICATION-TYPE
	OBJECTS {
			pduPhasePowerFactor,
			trapThreshType,
			trapSeverity,
			sysName,
			pduMainLabel,
			pduPhaseLabel
			}
	STATUS current
	DESCRIPTION "PDU phase power factor trap"
	::= { trapPrefix 10334 }

pduPhasePowerFactorCLEAR NOTIFICATION-TYPE
	OBJECTS {
			pduPhasePowerFactor,
			trapThreshType,
			trapSeverity,
			sysName,
			pduMainLabel,
			pduPhaseLabel
			}
	STATUS current
	DESCRIPTION "PDU phase power factor clear trap"
	::= { trapPrefix 20334 }

pduPhaseEnergyNOTIFY NOTIFICATION-TYPE
	OBJECTS {
			pduPhaseEnergy,
			trapThreshType,
			trapSeverity,
			sysName,
			pduMainLabel,
			pduPhaseLabel
			}
	STATUS current
	DESCRIPTION "PDU phase energy trap"
	::= { trapPrefix 10335 }

pduPhaseEnergyCLEAR NOTIFICATION-TYPE
	OBJECTS {
			pduPhaseEnergy,
			trapThreshType,
			trapSeverity,
			sysName,
			pduMainLabel,
			pduPhaseLabel
			}
	STATUS current
	DESCRIPTION "PDU phase energy clear trap"
	::= { trapPrefix 20335 }

--#####pduBreakerTable#####--

pduBreakerCurrentNOTIFY NOTIFICATION-TYPE
	OBJECTS {
			pduBreakerCurrent,
			trapThreshType,
			trapSeverity,
			sysName,
			pduMainLabel,
			pduBreakerLabel
			}
	STATUS current
	DESCRIPTION "PDU breaker current trap"
	::= { trapPrefix 10354 }

pduBreakerCurrentCLEAR NOTIFICATION-TYPE
	OBJECTS {
			pduBreakerCurrent,
			trapThreshType,
			trapSeverity,
			sysName,
			pduMainLabel,
			pduBreakerLabel
			}
	STATUS current
	DESCRIPTION "PDU breaker current clear trap"
	::= { trapPrefix 20354 }

pduBreakerCurrentMaxNOTIFY NOTIFICATION-TYPE
	OBJECTS {
			pduBreakerCurrentMax,
			trapThreshType,
			trapSeverity,
			sysName,
			pduMainLabel,
			pduBreakerLabel
			}
	STATUS current
	DESCRIPTION "PDU breaker current (max) trap"
	::= { trapPrefix 10355 }

pduBreakerCurrentMaxCLEAR NOTIFICATION-TYPE
	OBJECTS {
			pduBreakerCurrentMax,
			trapThreshType,
			trapSeverity,
			sysName,
			pduMainLabel,
			pduBreakerLabel
			}
	STATUS current
	DESCRIPTION "PDU breaker current (max) clear trap"
	::= { trapPrefix 20355 }

pduBreakerCurrentMinNOTIFY NOTIFICATION-TYPE
	OBJECTS {
			pduBreakerCurrentMin,
			trapThreshType,
			trapSeverity,
			sysName,
			pduMainLabel,
			pduBreakerLabel
			}
	STATUS current
	DESCRIPTION "PDU breaker current (min) trap"
	::= { trapPrefix 10356 }

pduBreakerCurrentMinCLEAR NOTIFICATION-TYPE
	OBJECTS {
			pduBreakerCurrentMin,
			trapThreshType,
			trapSeverity,
			sysName,
			pduMainLabel,
			pduBreakerLabel
			}
	STATUS current
	DESCRIPTION "PDU breaker current (min) clear trap"
	::= { trapPrefix 20356 }

pduBreakerCurrentPeakNOTIFY NOTIFICATION-TYPE
	OBJECTS {
			pduBreakerCurrentPeak,
			trapThreshType,
			trapSeverity,
			sysName,
			pduMainLabel,
			pduBreakerLabel
			}
	STATUS current
	DESCRIPTION "PDU breaker current (peak) trap"
	::= { trapPrefix 10357 }

pduBreakerCurrentPeakCLEAR NOTIFICATION-TYPE
	OBJECTS {
			pduBreakerCurrentPeak,
			trapThreshType,
			trapSeverity,
			sysName,
			pduMainLabel,
			pduBreakerLabel
			}
	STATUS current
	DESCRIPTION "PDU breaker current (peak) clear trap"
	::= { trapPrefix 20357 }

--#####pduLineTable#####--

pduLineCurrentNOTIFY NOTIFICATION-TYPE
	OBJECTS {
			pduLineCurrent,
			trapThreshType,
			trapSeverity,
			sysName,
			pduMainLabel,
			pduLineLabel
			}
	STATUS current
	DESCRIPTION "PDU line current trap"
	::= { trapPrefix 10374 }

pduLineCurrentCLEAR NOTIFICATION-TYPE
	OBJECTS {
			pduLineCurrent,
			trapThreshType,
			trapSeverity,
			sysName,
			pduMainLabel,
			pduLineLabel
			}
	STATUS current
	DESCRIPTION "PDU line current clear trap"
	::= { trapPrefix 20374 }

pduLineCurrentMaxNOTIFY NOTIFICATION-TYPE
	OBJECTS {
			pduLineCurrentMax,
			trapThreshType,
			trapSeverity,
			sysName,
			pduMainLabel,
			pduLineLabel
			}
	STATUS current
	DESCRIPTION "PDU line current (max) trap"
	::= { trapPrefix 10375 }

pduLineCurrentMaxCLEAR NOTIFICATION-TYPE
	OBJECTS {
			pduLineCurrentMax,
			trapThreshType,
			trapSeverity,
			sysName,
			pduMainLabel,
			pduLineLabel
			}
	STATUS current
	DESCRIPTION "PDU line current (max) clear trap"
	::= { trapPrefix 20375 }

pduLineCurrentMinNOTIFY NOTIFICATION-TYPE
	OBJECTS {
			pduLineCurrentMin,
			trapThreshType,
			trapSeverity,
			sysName,
			pduMainLabel,
			pduLineLabel
			}
	STATUS current
	DESCRIPTION "PDU line current (min) trap"
	::= { trapPrefix 10376 }

pduLineCurrentMinCLEAR NOTIFICATION-TYPE
	OBJECTS {
			pduLineCurrentMin,
			trapThreshType,
			trapSeverity,
			sysName,
			pduMainLabel,
			pduLineLabel
			}
	STATUS current
	DESCRIPTION "PDU line current (min) clear trap"
	::= { trapPrefix 20376 }

pduLineCurrentPeakNOTIFY NOTIFICATION-TYPE
	OBJECTS {
			pduLineCurrentPeak,
			trapThreshType,
			trapSeverity,
			sysName,
			pduMainLabel,
			pduLineLabel
			}
	STATUS current
	DESCRIPTION "PDU line current (peak) trap"
	::= { trapPrefix 10377 }

pduLineCurrentPeakCLEAR NOTIFICATION-TYPE
	OBJECTS {
			pduLineCurrentPeak,
			trapThreshType,
			trapSeverity,
			sysName,
			pduMainLabel,
			pduLineLabel
			}
	STATUS current
	DESCRIPTION "PDU line current (peak) clear trap"
	::= { trapPrefix 20377 }

--#####tempSensorTable#####--

tempSensorAvailNOTIFY NOTIFICATION-TYPE
	OBJECTS {
			tempSensorAvail,
			trapSeverity,
			sysName,
			tempSensorLabel
			}
	STATUS current
	DESCRIPTION "RT availability trap"
	::= { trapPrefix 10404 }

tempSensorAvailCLEAR NOTIFICATION-TYPE
	OBJECTS {
			tempSensorAvail,
			trapSeverity,
			sysName,
			tempSensorLabel
			}
	STATUS current
	DESCRIPTION "RT availability clear trap"
	::= { trapPrefix 20404 }

tempSensorTempNOTIFY NOTIFICATION-TYPE
	OBJECTS {
			tempSensorTemp,
			temperatureUnits,
			trapThreshType,
			trapSeverity,
			sysName,
			tempSensorLabel
			}
	STATUS current
	DESCRIPTION "RT temperature trap"
	::= { trapPrefix 10405 }

tempSensorTempCLEAR NOTIFICATION-TYPE
	OBJECTS {
			tempSensorTemp,
			temperatureUnits,
			trapThreshType,
			trapSeverity,
			sysName,
			tempSensorLabel
			}
	STATUS current
	DESCRIPTION "RT temperature clear trap"
	::= { trapPrefix 20405 }

--#####airFlowSensorTable#####--

airFlowSensorAvailNOTIFY NOTIFICATION-TYPE
	OBJECTS {
			airFlowSensorAvail,
			trapSeverity,
			sysName,
			airFlowSensorLabel
			}
	STATUS current
	DESCRIPTION "AFHT3 availability trap"
	::= { trapPrefix 10504 }

airFlowSensorAvailCLEAR NOTIFICATION-TYPE
	OBJECTS {
			airFlowSensorAvail,
			trapSeverity,
			sysName,
			airFlowSensorLabel
			}
	STATUS current
	DESCRIPTION "AFHT3 availability clear trap"
	::= { trapPrefix 20504 }

airFlowSensorTempNOTIFY NOTIFICATION-TYPE
	OBJECTS {
			airFlowSensorTemp,
			temperatureUnits,
			trapThreshType,
			trapSeverity,
			sysName,
			airFlowSensorLabel
			}
	STATUS current
	DESCRIPTION "AFHT3 temperature trap"
	::= { trapPrefix 10505 }

airFlowSensorTempCLEAR NOTIFICATION-TYPE
	OBJECTS {
			airFlowSensorTemp,
			temperatureUnits,
			trapThreshType,
			trapSeverity,
			sysName,
			airFlowSensorLabel
			}
	STATUS current
	DESCRIPTION "AFHT3 temperature clear trap"
	::= { trapPrefix 20505 }

airFlowSensorFlowNOTIFY NOTIFICATION-TYPE
	OBJECTS {
			airFlowSensorFlow,
			trapThreshType,
			trapSeverity,
			sysName,
			airFlowSensorLabel
			}
	STATUS current
	DESCRIPTION "AFHT3 airflow trap"
	::= { trapPrefix 10506 }

airFlowSensorFlowCLEAR NOTIFICATION-TYPE
	OBJECTS {
			airFlowSensorFlow,
			trapThreshType,
			trapSeverity,
			sysName,
			airFlowSensorLabel
			}
	STATUS current
	DESCRIPTION "AFHT3 airflow clear trap"
	::= { trapPrefix 20506 }

airFlowSensorHumidityNOTIFY NOTIFICATION-TYPE
	OBJECTS {
			airFlowSensorHumidity,
			trapThreshType,
			trapSeverity,
			sysName,
			airFlowSensorLabel
			}
	STATUS current
	DESCRIPTION "AFHT3 humidity trap"
	::= { trapPrefix 10507 }

airFlowSensorHumidityCLEAR NOTIFICATION-TYPE
	OBJECTS {
			airFlowSensorHumidity,
			trapThreshType,
			trapSeverity,
			sysName,
			airFlowSensorLabel
			}
	STATUS current
	DESCRIPTION "AFHT3 humidity clear trap"
	::= { trapPrefix 20507 }

airFlowSensorDewPointNOTIFY NOTIFICATION-TYPE
	OBJECTS {
			airFlowSensorDewPoint,
			temperatureUnits,
			trapThreshType,
			trapSeverity,
			sysName,
			airFlowSensorLabel
			}
	STATUS current
	DESCRIPTION "AFHT3 dewpoint trap"
	::= { trapPrefix 10508 }

airFlowSensorDewPointCLEAR NOTIFICATION-TYPE
	OBJECTS {
			airFlowSensorDewPoint,
			temperatureUnits,
			trapThreshType,
			trapSeverity,
			sysName,
			airFlowSensorLabel
			}
	STATUS current
	DESCRIPTION "AFHT3 dewpoint clear trap"
	::= { trapPrefix 20508 }

--#####dewPointSensorTable#####--

dewPointSensorAvailNOTIFY NOTIFICATION-TYPE
	OBJECTS {
			dewPointSensorAvail,
			trapSeverity,
			sysName,
			dewPointSensorName
			}
	STATUS current
	DESCRIPTION "Dewpoint available trap"
	::= { trapPrefix 10604 }

dewPointSensorAvailCLEAR NOTIFICATION-TYPE
	OBJECTS {
			dewPointSensorAvail,
			trapSeverity,
			sysName,
			dewPointSensorName
			}
	STATUS current
	DESCRIPTION "Dewpoint available clear trap"
	::= { trapPrefix 20604 }

dewPointSensorTempNOTIFY NOTIFICATION-TYPE
	OBJECTS {
			dewPointSensorTemp,
			temperatureUnits,
			trapThreshType,
			trapSeverity,
			sysName,
			dewPointSensorName
			}
	STATUS current
	DESCRIPTION "Dewpoint temperature trap"
	::= { trapPrefix 10605 }

dewPointSensorTempCLEAR NOTIFICATION-TYPE
	OBJECTS {
			dewPointSensorTemp,
			temperatureUnits,
			trapThreshType,
			trapSeverity,
			sysName,
			dewPointSensorName
			}
	STATUS current
	DESCRIPTION "Dewpoint temperature clear trap"
	::= { trapPrefix 20605 }

dewPointSensorHumidityNOTIFY NOTIFICATION-TYPE
	OBJECTS {
			dewPointSensorHumidity,
			trapThreshType,
			trapSeverity,
			sysName,
			dewPointSensorName
			}
	STATUS current
	DESCRIPTION "Dewpoint humidity trap"
	::= { trapPrefix 10606 }

dewPointSensorHumidityCLEAR NOTIFICATION-TYPE
	OBJECTS {
			dewPointSensorHumidity,
			trapThreshType,
			trapSeverity,
			sysName,
			dewPointSensorName
			}
	STATUS current
	DESCRIPTION "Dewpoint humidity clear trap"
	::= { trapPrefix 20606 }

dewPointSensorDewPointNOTIFY NOTIFICATION-TYPE
	OBJECTS {
			dewPointSensorDewPoint,
			temperatureUnits,
			trapThreshType,
			trapSeverity,
			sysName,
			dewPointSensorName
			}
	STATUS current
	DESCRIPTION "Dewpoint dewpoint trap"
	::= { trapPrefix 10607 }

dewPointSensorDewPointCLEAR NOTIFICATION-TYPE
	OBJECTS {
			dewPointSensorDewPoint,
			temperatureUnits,
			trapThreshType,
			trapSeverity,
			sysName,
			dewPointSensorName
			}
	STATUS current
	DESCRIPTION "Dewpoint dewpoint clear trap"
	::= { trapPrefix 20607 }

--#####ccatSensorTable#####--

ccatSensorAvailNOTIFY NOTIFICATION-TYPE
	OBJECTS {
			ccatSensorAvail,
			trapSeverity,
			sysName,
			ccatSensorName
			}
	STATUS current
	DESCRIPTION "CCAT available trap"
	::= { trapPrefix 10704 }

ccatSensorAvailCLEAR NOTIFICATION-TYPE
	OBJECTS {
			ccatSensorAvail,
			trapSeverity,
			sysName,
			ccatSensorName
			}
	STATUS current
	DESCRIPTION "CCAT available clear trap"
	::= { trapPrefix 20704 }

ccatSensorValueNOTIFY NOTIFICATION-TYPE
	OBJECTS {
			ccatSensorValue,
			trapThreshType,
			trapSeverity,
			sysName,
			ccatSensorType,
			ccatSensorName
			}
	STATUS current
	DESCRIPTION "CCAT measurement trap"
	::= { trapPrefix 10705 }

ccatSensorValueCLEAR NOTIFICATION-TYPE
	OBJECTS {
			ccatSensorValue,
			trapThreshType,
			trapSeverity,
			sysName,
			ccatSensorType,
			ccatSensorName
			}
	STATUS current
	DESCRIPTION "CCAT measurement clear trap"
	::= { trapPrefix 20705 }

--#####t3hdSensorTable#####--

t3hdSensorAvailNOTIFY NOTIFICATION-TYPE
	OBJECTS {
			t3hdSensorAvail,
			trapSeverity,
			sysName,
			t3hdSensorLabel
			}
	STATUS current
	DESCRIPTION "T3HD availability trap"
	::= { trapPrefix 10804 }

t3hdSensorAvailCLEAR NOTIFICATION-TYPE
	OBJECTS {
			t3hdSensorAvail,
			trapSeverity,
			sysName,
			t3hdSensorLabel
			}
	STATUS current
	DESCRIPTION "T3HD availability clear trap"
	::= { trapPrefix 20804 }

t3hdSensorIntTempNOTIFY NOTIFICATION-TYPE
	OBJECTS {
			t3hdSensorIntTemp,
			temperatureUnits,
			trapThreshType,
			trapSeverity,
			sysName,
			t3hdSensorLabel,
			t3hdSensorIntLabel
			}
	STATUS current
	DESCRIPTION "T3HD Internal temperature trap"
	::= { trapPrefix 10806 }

t3hdSensorIntTempCLEAR NOTIFICATION-TYPE
	OBJECTS {
			t3hdSensorIntTemp,
			temperatureUnits,
			trapThreshType,
			trapSeverity,
			sysName,
			t3hdSensorLabel,
			t3hdSensorIntLabel
			}
	STATUS current
	DESCRIPTION "T3HD Internal temperature clear trap"
	::= { trapPrefix 20806 }

t3hdSensorIntHumidityNOTIFY NOTIFICATION-TYPE
	OBJECTS {
			t3hdSensorIntHumidity,
			trapThreshType,
			trapSeverity,
			sysName,
			t3hdSensorLabel,
			t3hdSensorIntLabel
			}
	STATUS current
	DESCRIPTION "T3HD Internal humidity trap"
	::= { trapPrefix 10807 }

t3hdSensorIntHumidityCLEAR NOTIFICATION-TYPE
	OBJECTS {
			t3hdSensorIntHumidity,
			trapThreshType,
			trapSeverity,
			sysName,
			t3hdSensorLabel,
			t3hdSensorIntLabel
			}
	STATUS current
	DESCRIPTION "T3HD Internal humidity clear trap"
	::= { trapPrefix 20807 }

t3hdSensorIntDewPointNOTIFY NOTIFICATION-TYPE
	OBJECTS {
			t3hdSensorIntDewPoint,
			temperatureUnits,
			trapThreshType,
			trapSeverity,
			sysName,
			t3hdSensorLabel,
			t3hdSensorIntLabel
			}
	STATUS current
	DESCRIPTION "T3HD dewpoint trap"
	::= { trapPrefix 10808 }

t3hdSensorIntDewPointCLEAR NOTIFICATION-TYPE
	OBJECTS {
			t3hdSensorIntDewPoint,
			temperatureUnits,
			trapThreshType,
			trapSeverity,
			sysName,
			t3hdSensorLabel,
			t3hdSensorIntLabel
			}
	STATUS current
	DESCRIPTION "T3HD dewpoint clear trap"
	::= { trapPrefix 20808 }

t3hdSensorExtATempNOTIFY NOTIFICATION-TYPE
	OBJECTS {
			t3hdSensorExtATemp,
			temperatureUnits,
			trapThreshType,
			trapSeverity,
			sysName,
			t3hdSensorLabel,
			t3hdSensorExtALabel
			}
	STATUS current
	DESCRIPTION "T3HD External A temperature trap"
	::= { trapPrefix 10811 }

t3hdSensorExtATempCLEAR NOTIFICATION-TYPE
	OBJECTS {
			t3hdSensorExtATemp,
			temperatureUnits,
			trapThreshType,
			trapSeverity,
			sysName,
			t3hdSensorLabel,
			t3hdSensorExtALabel
			}
	STATUS current
	DESCRIPTION "T3HD External A temperature clear trap"
	::= { trapPrefix 20811 }

t3hdSensorExtBTempNOTIFY NOTIFICATION-TYPE
	OBJECTS {
			t3hdSensorExtBTemp,
			temperatureUnits,
			trapThreshType,
			trapSeverity,
			sysName,
			t3hdSensorLabel,
			t3hdSensorExtBLabel
			}
	STATUS current
	DESCRIPTION "T3HD External B temperature trap"
	::= { trapPrefix 10814 }

t3hdSensorExtBTempCLEAR NOTIFICATION-TYPE
	OBJECTS {
			t3hdSensorExtBTemp,
			temperatureUnits,
			trapThreshType,
			trapSeverity,
			sysName,
			t3hdSensorLabel,
			t3hdSensorExtBLabel
			}
	STATUS current
	DESCRIPTION "T3HD External B temperature clear trap"
	::= { trapPrefix 20814 }

--#####thdSensorTable#####--

thdSensorAvailNOTIFY NOTIFICATION-TYPE
	OBJECTS {
			thdSensorAvail,
			trapSeverity,
			sysName,
			thdSensorLabel
			}
	STATUS current
	DESCRIPTION "THD availability trap"
	::= { trapPrefix 10904 }

thdSensorAvailCLEAR NOTIFICATION-TYPE
	OBJECTS {
			thdSensorAvail,
			trapSeverity,
			sysName,
			thdSensorLabel
			}
	STATUS current
	DESCRIPTION "THD availability clear trap"
	::= { trapPrefix 20904 }

thdSensorTempNOTIFY NOTIFICATION-TYPE
	OBJECTS {
			thdSensorTemp,
			temperatureUnits,
			trapThreshType,
			trapSeverity,
			sysName,
			thdSensorLabel
			}
	STATUS current
	DESCRIPTION "THD temperature trap"
	::= { trapPrefix 10905 }

thdSensorTempCLEAR NOTIFICATION-TYPE
	OBJECTS {
			thdSensorTemp,
			temperatureUnits,
			trapThreshType,
			trapSeverity,
			sysName,
			thdSensorLabel
			}
	STATUS current
	DESCRIPTION "THD temperature clear trap"
	::= { trapPrefix 20905 }

thdSensorHumidityNOTIFY NOTIFICATION-TYPE
	OBJECTS {
			thdSensorHumidity,
			trapThreshType,
			trapSeverity,
			sysName,
			thdSensorLabel
			}
	STATUS current
	DESCRIPTION "THD humidity trap"
	::= { trapPrefix 10906 }

thdSensorHumidityCLEAR NOTIFICATION-TYPE
	OBJECTS {
			thdSensorHumidity,
			trapThreshType,
			trapSeverity,
			sysName,
			thdSensorLabel
			}
	STATUS current
	DESCRIPTION "THD humidity clear trap"
	::= { trapPrefix 20906 }

thdSensorDewPointNOTIFY NOTIFICATION-TYPE
	OBJECTS {
			thdSensorDewPoint,
			temperatureUnits,
			trapThreshType,
			trapSeverity,
			sysName,
			thdSensorLabel
			}
	STATUS current
	DESCRIPTION "THD dewpoint trap"
	::= { trapPrefix 10907 }

thdSensorDewPointCLEAR NOTIFICATION-TYPE
	OBJECTS {
			thdSensorDewPoint,
			temperatureUnits,
			trapThreshType,
			trapSeverity,
			sysName,
			thdSensorLabel
			}
	STATUS current
	DESCRIPTION "THD dewpoint clear trap"
	::= { trapPrefix 20907 }

--#####rpmSensorTable#####--

rpmSensorAvailNOTIFY NOTIFICATION-TYPE
	OBJECTS {
			rpmSensorAvail,
			trapSeverity,
			sysName,
			rpmSensorName
			}
	STATUS current
	DESCRIPTION "RPM available trap"
	::= { trapPrefix 11004 }

rpmSensorAvailCLEAR NOTIFICATION-TYPE
	OBJECTS {
			rpmSensorAvail,
			trapSeverity,
			sysName,
			rpmSensorName
			}
	STATUS current
	DESCRIPTION "RPM available clear trap"
	::= { trapPrefix 21004 }

rpmSensorEnergyNOTIFY NOTIFICATION-TYPE
	OBJECTS {
			rpmSensorEnergy,
			trapThreshType,
			trapSeverity,
			sysName,
			rpmSensorName
			}
	STATUS current
	DESCRIPTION "RPM energy trap"
	::= { trapPrefix 11005 }

rpmSensorEnergyCLEAR NOTIFICATION-TYPE
	OBJECTS {
			rpmSensorEnergy,
			trapThreshType,
			trapSeverity,
			sysName,
			rpmSensorName
			}
	STATUS current
	DESCRIPTION "RPM energy clear trap"
	::= { trapPrefix 21005 }

rpmSensorVoltageNOTIFY NOTIFICATION-TYPE
	OBJECTS {
			rpmSensorVoltage,
			trapThreshType,
			trapSeverity,
			sysName,
			rpmSensorName
			}
	STATUS current
	DESCRIPTION "RPM voltage trap"
	::= { trapPrefix 11006 }

rpmSensorVoltageCLEAR NOTIFICATION-TYPE
	OBJECTS {
			rpmSensorVoltage,
			trapThreshType,
			trapSeverity,
			sysName,
			rpmSensorName
			}
	STATUS current
	DESCRIPTION "RPM voltage clear trap"
	::= { trapPrefix 21006 }

rpmSensorVoltageMaxNOTIFY NOTIFICATION-TYPE
	OBJECTS {
			rpmSensorVoltageMax,
			trapThreshType,
			trapSeverity,
			sysName,
			rpmSensorName
			}
	STATUS current
	DESCRIPTION "RPM voltage (max) trap"
	::= { trapPrefix 11007 }

rpmSensorVoltageMaxCLEAR NOTIFICATION-TYPE
	OBJECTS {
			rpmSensorVoltageMax,
			trapThreshType,
			trapSeverity,
			sysName,
			rpmSensorName
			}
	STATUS current
	DESCRIPTION "RPM voltage (max) clear trap"
	::= { trapPrefix 21007 }

rpmSensorVoltageMinNOTIFY NOTIFICATION-TYPE
	OBJECTS {
			rpmSensorVoltageMin,
			trapThreshType,
			trapSeverity,
			sysName,
			rpmSensorName
			}
	STATUS current
	DESCRIPTION "RPM voltage (min) trap"
	::= { trapPrefix 11008 }

rpmSensorVoltageMinCLEAR NOTIFICATION-TYPE
	OBJECTS {
			rpmSensorVoltageMin,
			trapThreshType,
			trapSeverity,
			sysName,
			rpmSensorName
			}
	STATUS current
	DESCRIPTION "RPM voltage (min) clear trap"
	::= { trapPrefix 21008 }

rpmSensorVoltagePeakNOTIFY NOTIFICATION-TYPE
	OBJECTS {
			rpmSensorVoltagePeak,
			trapThreshType,
			trapSeverity,
			sysName,
			rpmSensorName
			}
	STATUS current
	DESCRIPTION "RPM voltage (peak) trap"
	::= { trapPrefix 11009 }

rpmSensorVoltagePeakCLEAR NOTIFICATION-TYPE
	OBJECTS {
			rpmSensorVoltagePeak,
			trapThreshType,
			trapSeverity,
			sysName,
			rpmSensorName
			}
	STATUS current
	DESCRIPTION "RPM voltage (peak) clear trap"
	::= { trapPrefix 21009 }

rpmSensorCurrentNOTIFY NOTIFICATION-TYPE
	OBJECTS {
			rpmSensorCurrent,
			trapThreshType,
			trapSeverity,
			sysName,
			rpmSensorName
			}
	STATUS current
	DESCRIPTION "RPM current trap"
	::= { trapPrefix 11010 }

rpmSensorCurrentCLEAR NOTIFICATION-TYPE
	OBJECTS {
			rpmSensorCurrent,
			trapThreshType,
			trapSeverity,
			sysName,
			rpmSensorName
			}
	STATUS current
	DESCRIPTION "RPM current clear trap"
	::= { trapPrefix 21010 }

rpmSensorRealPowerNOTIFY NOTIFICATION-TYPE
	OBJECTS {
			rpmSensorRealPower,
			trapThreshType,
			trapSeverity,
			sysName,
			rpmSensorName
			}
	STATUS current
	DESCRIPTION "RPM real power trap"
	::= { trapPrefix 11011 }

rpmSensorRealPowerCLEAR NOTIFICATION-TYPE
	OBJECTS {
			rpmSensorRealPower,
			trapThreshType,
			trapSeverity,
			sysName,
			rpmSensorName
			}
	STATUS current
	DESCRIPTION "RPM real power clear trap"
	::= { trapPrefix 21011 }

rpmSensorApparentPowerNOTIFY NOTIFICATION-TYPE
	OBJECTS {
			rpmSensorApparentPower,
			trapThreshType,
			trapSeverity,
			sysName,
			rpmSensorName
			}
	STATUS current
	DESCRIPTION "RPM apparent power trap"
	::= { trapPrefix 11012 }

rpmSensorApparentPowerCLEAR NOTIFICATION-TYPE
	OBJECTS {
			rpmSensorApparentPower,
			trapThreshType,
			trapSeverity,
			sysName,
			rpmSensorName
			}
	STATUS current
	DESCRIPTION "RPM apparent power clear trap"
	::= { trapPrefix 21012 }

rpmSensorPowerFactorNOTIFY NOTIFICATION-TYPE
	OBJECTS {
			rpmSensorPowerFactor,
			trapSeverity,
			trapThreshType,
			sysName,
			rpmSensorName
			}
	STATUS current
	DESCRIPTION "RPM power factor trap"
	::= { trapPrefix 11013 }

rpmSensorPowerFactorCLEAR NOTIFICATION-TYPE
	OBJECTS {
			rpmSensorPowerFactor,
			trapSeverity,
			trapThreshType,
			sysName,
			rpmSensorName
			}
	STATUS current
	DESCRIPTION "RPM power factor clear trap"
	::= { trapPrefix 21013 }

--#####a2dSensorTable#####--

a2dSensorAvailNOTIFY NOTIFICATION-TYPE
	OBJECTS {
			a2dSensorAvail,
			trapSeverity,
			sysName,
			a2dSensorLabel
			}
	STATUS current
	DESCRIPTION "A2D availability trap"
	::= { trapPrefix 11104 }

a2dSensorAvailCLEAR NOTIFICATION-TYPE
	OBJECTS {
			a2dSensorAvail,
			trapSeverity,
			sysName,
			a2dSensorLabel
			}
	STATUS current
	DESCRIPTION "A2D availability clear trap"
	::= { trapPrefix 21104 }

a2dSensorValueNOTIFY NOTIFICATION-TYPE
	OBJECTS {
			a2dSensorValue,
			trapThreshType,
			trapSeverity,
			sysName,
			a2dSensorLabel,
			a2dSensorAnalogLabel,
			a2dSensorDisplayValue
			}
	STATUS current
	DESCRIPTION "A2D measurement trap"
	::= { trapPrefix 11105 }

a2dSensorValueCLEAR NOTIFICATION-TYPE
	OBJECTS {
			a2dSensorValue,
			trapThreshType,
			trapSeverity,
			sysName,
			a2dSensorLabel,
			a2dSensorAnalogLabel,
			a2dSensorDisplayValue
			}
	STATUS current
	DESCRIPTION "A2D measurement clear trap"
	::= { trapPrefix 21105 }

END

VERTIV-QUETZAL-MIB DEFINITIONS ::= BEGIN

IMPORTS

DisplayString, TEXTUAL-CONVENTION FROM SNMPv2-TC
MODULE-IDENTITY, OBJECT-TYPE, enterprises, Gauge32,
Integer32, Unsigned32, OBJECT-IDENTITY FROM SNMPv2-SMI;

vertiv MODULE-IDENTITY
	LAST-UPDATED "201908300000Z"
	ORGANIZATION "Vertiv"
	CONTACT-INFO "support@geistglobal.com"
	DESCRIPTION
		"Vertiv Quetzal MIB (legacy)
		Note: This MIB is deprecated and will be replaced by VERTIV-V5-MIB"

	REVISION "201908300000Z"
	DESCRIPTION
		"Removed all pdu amps max and volts max fields"

	REVISION "201906060000Z"
	DESCRIPTION
		"Updated pduOutletSwitchControl description"

	REVISION "201801190000Z"
	DESCRIPTION
		"Changed fields in pduOutletSwitchTable to read-write, allowing for
		configuration of outlet delays and Power-On Actions."

	REVISION "201606290000Z"
	DESCRIPTION
		"MIB revisions to reflect SNMP changes for new architecture. In
		particular, the STATUS of all fields have been changed to deprecated."

	REVISION "201209210000Z"
	DESCRIPTION
		"Initial version"
	::= { enterprises 21239 }

DeviceSerial ::= TEXTUAL-CONVENTION
	STATUS deprecated
	DESCRIPTION
		"Unique serial number used to identify a device. A serial number is a
		string, with a length of 16. The string will only contain the
		characters 0 to 9, and A to F."
	SYNTAX OCTET STRING (SIZE (1..16))

DeviceStatus ::= TEXTUAL-CONVENTION
	STATUS deprecated
	DESCRIPTION
		"Indicates the condition of the device"
	SYNTAX INTEGER {
			ok(1),
			notFound(2),
			ioError(3),
			unknown(4),
			deleted(5)
			}

DeviceLabel ::= TEXTUAL-CONVENTION
	STATUS deprecated
	DESCRIPTION
		"User-defined device name"
	SYNTAX OCTET STRING (SIZE (0..32))

TemperatureUnits ::= TEXTUAL-CONVENTION
	STATUS deprecated
	DESCRIPTION
		"Used to tell the units of a temperature reading"
	SYNTAX INTEGER {
			fahrenheit(1),
			celsius(2)
			}

TemperatureValue ::= TEXTUAL-CONVENTION
	DISPLAY-HINT "d-1"
	STATUS deprecated
	DESCRIPTION
		"0.1 degree"
	SYNTAX Integer32

DeciAmps ::= TEXTUAL-CONVENTION
	DISPLAY-HINT "d-1"
	STATUS deprecated
	DESCRIPTION
		"0.1 Amps"
	SYNTAX Gauge32

quetzal OBJECT IDENTIFIER ::= { vertiv 6 }

devices OBJECT IDENTIFIER ::= { quetzal 1 }

legacyPDU OBJECT IDENTIFIER ::= { devices 99 }

rtafhd3 OBJECT IDENTIFIER ::= { devices 3 }

rt OBJECT IDENTIFIER ::= { devices 8 }

t3hd OBJECT IDENTIFIER ::= { devices 9 }

thd OBJECT IDENTIFIER ::= { devices 10 }

--###########################################################################################--
--pduBaseDeltaTable--
--###########################################################################################--

pduBaseDeltaTable OBJECT-TYPE
	SYNTAX SEQUENCE OF PduBaseDeltaEntry
	MAX-ACCESS  not-accessible
	STATUS deprecated
	DESCRIPTION
		"Base table for a delta-wired PDU. It contains general information
		about the PDU. Entries in sub-tables provide data for channels, groups
		and outlets. The system creates these sub-table entries based on
		hardware and configuration options, set at the factory."
	::= { legacyPDU 1 }

pduBaseDeltaEntry OBJECT-TYPE
	SYNTAX PduBaseDeltaEntry
	MAX-ACCESS  not-accessible
	STATUS deprecated
	DESCRIPTION
		"Entry for a delta PDU device. This table will only have an entry if
		the main device is a delta-wired PDU."
	INDEX { pduBaseDeltaIndex }
	::= { pduBaseDeltaTable 1 }

PduBaseDeltaEntry ::= SEQUENCE {
	pduBaseDeltaIndex				Unsigned32,
	pduBaseDeltaSerial				DeviceSerial,
	pduBaseDeltaLabel				DeviceLabel,
	pduBaseDeltaStatus				DeviceStatus,
	pduBaseDeltaKWattHrsTotal				Gauge32,
	pduBaseDeltaRealPowerTotal				Gauge32,
	pduBaseDeltaAmpsA				DeciAmps,
	pduBaseDeltaAmpsB				DeciAmps,
	pduBaseDeltaAmpsC				DeciAmps
}

pduBaseDeltaIndex OBJECT-TYPE
	SYNTAX Unsigned32(1..64)
	MAX-ACCESS not-accessible
	STATUS deprecated
	DESCRIPTION
		"Table entry index value"
	::= { pduBaseDeltaEntry 1 }

pduBaseDeltaSerial OBJECT-TYPE
	SYNTAX DeviceSerial
	MAX-ACCESS read-only
	STATUS deprecated
	DESCRIPTION
		"PDU's unique ID, used as a reference for channels, groups and outlets"
	::= { pduBaseDeltaEntry 2 }

pduBaseDeltaLabel OBJECT-TYPE
	SYNTAX DeviceLabel
	MAX-ACCESS read-write
	STATUS deprecated
	DESCRIPTION
		"User-defined name for the delta PDU device"
	::= { pduBaseDeltaEntry 3 }

pduBaseDeltaStatus OBJECT-TYPE
	SYNTAX DeviceStatus
	MAX-ACCESS read-only
	STATUS deprecated
	DESCRIPTION
		"Condition of the device"
	::= { pduBaseDeltaEntry 4 }

pduBaseDeltaKWattHrsTotal OBJECT-TYPE
	SYNTAX Gauge32
	MAX-ACCESS read-only
	STATUS deprecated
	DESCRIPTION
		"Total kilowatt hours for the delta PDU"
	::= { pduBaseDeltaEntry 5 }

pduBaseDeltaRealPowerTotal OBJECT-TYPE
	SYNTAX Gauge32
	MAX-ACCESS read-only
	STATUS deprecated
	DESCRIPTION
		"Total real power for the delta PDU"
	::= { pduBaseDeltaEntry 6 }

pduBaseDeltaAmpsA OBJECT-TYPE
	SYNTAX DeciAmps
	MAX-ACCESS read-only
	STATUS deprecated
	DESCRIPTION
		"Current reading for A"
	::= { pduBaseDeltaEntry 7 }

pduBaseDeltaAmpsB OBJECT-TYPE
	SYNTAX DeciAmps
	MAX-ACCESS read-only
	STATUS deprecated
	DESCRIPTION
		"Current reading for B"
	::= { pduBaseDeltaEntry 8 }

pduBaseDeltaAmpsC OBJECT-TYPE
	SYNTAX DeciAmps
	MAX-ACCESS read-only
	STATUS deprecated
	DESCRIPTION
		"Current reading for C"
	::= { pduBaseDeltaEntry 9 }

--###########################################################################################--
--pduBaseWyeTable--
--###########################################################################################--

pduBaseWyeTable OBJECT-TYPE
	SYNTAX SEQUENCE OF PduBaseWyeEntry
	MAX-ACCESS  not-accessible
	STATUS deprecated
	DESCRIPTION
		"Base table for a Wye-wired PDU. It contains general information about
		the PDU. Entries in sub-tables provide data for channels, groups and
		outlets. The system creates these sub-table entries based on hardware,
		wiring, and configuration options, set at the factory."
	::= { legacyPDU 2 }

pduBaseWyeEntry OBJECT-TYPE
	SYNTAX PduBaseWyeEntry
	MAX-ACCESS  not-accessible
	STATUS deprecated
	DESCRIPTION
		"Entry for a Wye-wired PDU device. This table will only have an entry
		if the PDU uses a Wye wiring."
	INDEX { pduBaseWyeIndex }
	::= { pduBaseWyeTable 1 }

PduBaseWyeEntry ::= SEQUENCE {
	pduBaseWyeIndex				Unsigned32,
	pduBaseWyeSerial				DeviceSerial,
	pduBaseWyeLabel				DeviceLabel,
	pduBaseWyeStatus				DeviceStatus,
	pduBaseWyeKWattHrsTotal				Gauge32,
	pduBaseWyeRealPowerTotal				Gauge32,
	pduBaseWyeChannelCount				Unsigned32
}

pduBaseWyeIndex OBJECT-TYPE
	SYNTAX Unsigned32(1..64)
	MAX-ACCESS not-accessible
	STATUS deprecated
	DESCRIPTION
		"Table entry index value"
	::= { pduBaseWyeEntry 1 }

pduBaseWyeSerial OBJECT-TYPE
	SYNTAX DeviceSerial
	MAX-ACCESS read-only
	STATUS deprecated
	DESCRIPTION
		"PDU's unique ID, used as a reference for channels, groups and outlets"
	::= { pduBaseWyeEntry 2 }

pduBaseWyeLabel OBJECT-TYPE
	SYNTAX DeviceLabel
	MAX-ACCESS read-write
	STATUS deprecated
	DESCRIPTION
		"User-defined name for the PDU"
	::= { pduBaseWyeEntry 3 }

pduBaseWyeStatus OBJECT-TYPE
	SYNTAX DeviceStatus
	MAX-ACCESS read-only
	STATUS deprecated
	DESCRIPTION
		"Condition of the device"
	::= { pduBaseWyeEntry 4 }

pduBaseWyeKWattHrsTotal OBJECT-TYPE
	SYNTAX Gauge32
	MAX-ACCESS read-only
	STATUS deprecated
	DESCRIPTION
		"Total kilowatt hours for the PDU"
	::= { pduBaseWyeEntry 5 }

pduBaseWyeRealPowerTotal OBJECT-TYPE
	SYNTAX Gauge32
	MAX-ACCESS read-only
	STATUS deprecated
	DESCRIPTION
		"Total real power used by the PDU"
	::= { pduBaseWyeEntry 6 }

pduBaseWyeChannelCount OBJECT-TYPE
	SYNTAX Unsigned32(1..3)
	MAX-ACCESS read-only
	STATUS deprecated
	DESCRIPTION
		"Count of the total number of Wye channels. Data for these channels is
		found in the pduChannelWyeTable."
	::= { pduBaseWyeEntry 7 }

--###########################################################################################--
--pduChannelDeltaTable--
--###########################################################################################--

pduChannelDeltaTable OBJECT-TYPE
	SYNTAX SEQUENCE OF PduChannelDeltaEntry
	MAX-ACCESS  not-accessible
	STATUS deprecated
	DESCRIPTION
		"The pduChannelDeltaTable contains specific channel information for a
		delta PDU."
	::= { legacyPDU 3 }

pduChannelDeltaEntry OBJECT-TYPE
	SYNTAX PduChannelDeltaEntry
	MAX-ACCESS  not-accessible
	STATUS deprecated
	DESCRIPTION
		"Each entry represents a delta channel. Entries are indexed by the PDU
		instance number and a channel id number. This table will only have
		entries if a corresponding delta PDU exists."
	INDEX { pduBaseDeltaIndex, pduChannelDeltaID }
	::= { pduChannelDeltaTable 1 }

PduChannelDeltaEntry ::= SEQUENCE {
	pduChannelDeltaID				Unsigned32,
	pduChannelDeltaLabel				DeviceLabel,
	pduChannelDeltaName				DisplayString,
	pduChannelDeltaKWattHrs				Gauge32,
	pduChannelDeltaVolts				Gauge32,
	pduChannelDeltaRealPower				Gauge32,
	pduChannelDeltaApparentPower				Gauge32,
	pduChannelDeltaPowerFactor				Gauge32,
	pduChannelDeltaAmps				DeciAmps
}

pduChannelDeltaID OBJECT-TYPE
	SYNTAX Unsigned32(1..3)
	MAX-ACCESS read-only
	STATUS deprecated
	DESCRIPTION
		"Delta channel id number"
	::= { pduChannelDeltaEntry 1 }

pduChannelDeltaLabel OBJECT-TYPE
	SYNTAX DeviceLabel
	MAX-ACCESS read-write
	STATUS deprecated
	DESCRIPTION
		"User-defined name for this channel"
	::= { pduChannelDeltaEntry 2 }

pduChannelDeltaName OBJECT-TYPE
	SYNTAX DisplayString
	MAX-ACCESS read-only
	STATUS deprecated
	DESCRIPTION
		"Factory-assigned name for this channel"
	::= { pduChannelDeltaEntry 3 }

pduChannelDeltaKWattHrs OBJECT-TYPE
	SYNTAX Gauge32
	MAX-ACCESS read-only
	STATUS deprecated
	DESCRIPTION
		"Kilowatt hours for this channel"
	::= { pduChannelDeltaEntry 4 }

pduChannelDeltaVolts OBJECT-TYPE
	SYNTAX Gauge32
	MAX-ACCESS read-only
	STATUS deprecated
	DESCRIPTION
		"Volt reading"
	::= { pduChannelDeltaEntry 5 }

pduChannelDeltaRealPower OBJECT-TYPE
	SYNTAX Gauge32
	MAX-ACCESS read-only
	STATUS deprecated
	DESCRIPTION
		"Real power"
	::= { pduChannelDeltaEntry 7 }

pduChannelDeltaApparentPower OBJECT-TYPE
	SYNTAX Gauge32
	MAX-ACCESS read-only
	STATUS deprecated
	DESCRIPTION
		"Apparent Power"
	::= { pduChannelDeltaEntry 8 }

pduChannelDeltaPowerFactor OBJECT-TYPE
	SYNTAX Gauge32
	MAX-ACCESS read-only
	STATUS deprecated
	DESCRIPTION
		"Power Factor"
	::= { pduChannelDeltaEntry 9 }

pduChannelDeltaAmps OBJECT-TYPE
	SYNTAX DeciAmps
	MAX-ACCESS read-only
	STATUS deprecated
	DESCRIPTION
		"Current reading"
	::= { pduChannelDeltaEntry 10 }

--###########################################################################################--
--pduChannelWyeTable--
--###########################################################################################--

pduChannelWyeTable OBJECT-TYPE
	SYNTAX SEQUENCE OF PduChannelWyeEntry
	MAX-ACCESS  not-accessible
	STATUS deprecated
	DESCRIPTION
		"The pduChannelWyeTable contains specific channel information for a
		wye-wired PDU."
	::= { legacyPDU 4 }

pduChannelWyeEntry OBJECT-TYPE
	SYNTAX PduChannelWyeEntry
	MAX-ACCESS  not-accessible
	STATUS deprecated
	DESCRIPTION
		"Each entry represents a wye channel. Entries are indexed by the
		instance number of a PDU and a channel id number. This table will only
		have entries if a corresponding wye-wired PDU exists."
	INDEX { pduBaseWyeIndex, pduChannelWyeID }
	::= { pduChannelWyeTable 1 }

PduChannelWyeEntry ::= SEQUENCE {
	pduChannelWyeID				Unsigned32,
	pduChannelWyeLabel				DeviceLabel,
	pduChannelWyeName				DisplayString,
	pduChannelWyeKWattHrs				Gauge32,
	pduChannelWyeVolts				Gauge32,
	pduChannelWyeAmps				DeciAmps,
	pduChannelWyeRealPower				Gauge32,
	pduChannelWyeApparentPower				Gauge32,
	pduChannelWyePowerFactor				Gauge32
}

pduChannelWyeID OBJECT-TYPE
	SYNTAX Unsigned32(1..3)
	MAX-ACCESS read-only
	STATUS deprecated
	DESCRIPTION
		"Wye channel id"
	::= { pduChannelWyeEntry 1 }

pduChannelWyeLabel OBJECT-TYPE
	SYNTAX DeviceLabel
	MAX-ACCESS read-write
	STATUS deprecated
	DESCRIPTION
		"User-defined name for this channel"
	::= { pduChannelWyeEntry 2 }

pduChannelWyeName OBJECT-TYPE
	SYNTAX DisplayString
	MAX-ACCESS read-only
	STATUS deprecated
	DESCRIPTION
		"Factory-assigned name for this channel"
	::= { pduChannelWyeEntry 3 }

pduChannelWyeKWattHrs OBJECT-TYPE
	SYNTAX Gauge32
	MAX-ACCESS read-only
	STATUS deprecated
	DESCRIPTION
		"Kilowatt hours"
	::= { pduChannelWyeEntry 4 }

pduChannelWyeVolts OBJECT-TYPE
	SYNTAX Gauge32
	MAX-ACCESS read-only
	STATUS deprecated
	DESCRIPTION
		"Volt reading"
	::= { pduChannelWyeEntry 5 }

pduChannelWyeAmps OBJECT-TYPE
	SYNTAX DeciAmps
	MAX-ACCESS read-only
	STATUS deprecated
	DESCRIPTION
		"Current reading"
	::= { pduChannelWyeEntry 7 }

pduChannelWyeRealPower OBJECT-TYPE
	SYNTAX Gauge32
	MAX-ACCESS read-only
	STATUS deprecated
	DESCRIPTION
		"Real power"
	::= { pduChannelWyeEntry 9 }

pduChannelWyeApparentPower OBJECT-TYPE
	SYNTAX Gauge32
	MAX-ACCESS read-only
	STATUS deprecated
	DESCRIPTION
		"Apparent power"
	::= { pduChannelWyeEntry 10 }

pduChannelWyePowerFactor OBJECT-TYPE
	SYNTAX Gauge32
	MAX-ACCESS read-only
	STATUS deprecated
	DESCRIPTION
		"Power factor"
	::= { pduChannelWyeEntry 11 }

--###########################################################################################--
--pduGroupTable--
--###########################################################################################--

pduGroupTable OBJECT-TYPE
	SYNTAX SEQUENCE OF PduGroupEntry
	MAX-ACCESS  not-accessible
	STATUS deprecated
	DESCRIPTION
		"Contains meter readings per outlet group"
	::= { legacyPDU 5 }

pduGroupEntry OBJECT-TYPE
	SYNTAX PduGroupEntry
	MAX-ACCESS  not-accessible
	STATUS deprecated
	DESCRIPTION
		"Each entry represents an outlet group for a specific PDU. Groups are
		indexed by a PDU instance number and a group id number. The
		pduGroupIndex corresponds to a matching instance number in a base PDU
		table. For group entries to exist, a PDU that supports groups must
		also exist."
	INDEX { pduGroupIndex, pduGroupID }
	::= { pduGroupTable 1 }

PduGroupEntry ::= SEQUENCE {
	pduGroupIndex				Unsigned32,
	pduGroupSerial				DeviceSerial,
	pduGroupID				Unsigned32,
	pduGroupLabel				DeviceLabel,
	pduGroupName				DisplayString,
	pduGroupAmps				DeciAmps,
	pduGroupApparentPower				Gauge32,
	pduGroupPowerFactor				Gauge32,
	pduGroupRealPower				Gauge32,
	pduGroupVolts				Gauge32,
	pduGroupWattHours				Gauge32
}

pduGroupIndex OBJECT-TYPE
	SYNTAX Unsigned32(1..64)
	MAX-ACCESS not-accessible
	STATUS deprecated
	DESCRIPTION
		"Table entry index value"
	::= { pduGroupEntry 1 }

pduGroupSerial OBJECT-TYPE
	SYNTAX DeviceSerial
	MAX-ACCESS read-only
	STATUS deprecated
	DESCRIPTION
		"Serial number of an existing base PDU"
	::= { pduGroupEntry 2 }

pduGroupID OBJECT-TYPE
	SYNTAX Unsigned32(1..8)
	MAX-ACCESS read-only
	STATUS deprecated
	DESCRIPTION
		"Group id number"
	::= { pduGroupEntry 3 }

pduGroupLabel OBJECT-TYPE
	SYNTAX DeviceLabel
	MAX-ACCESS read-write
	STATUS deprecated
	DESCRIPTION
		"User-defined name for this group"
	::= { pduGroupEntry 4 }

pduGroupName OBJECT-TYPE
	SYNTAX DisplayString
	MAX-ACCESS read-only
	STATUS deprecated
	DESCRIPTION
		"Factory-assigned name for this group"
	::= { pduGroupEntry 5 }

pduGroupAmps OBJECT-TYPE
	SYNTAX DeciAmps
	MAX-ACCESS read-only
	STATUS deprecated
	DESCRIPTION
		"Total amps for outlet group"
	::= { pduGroupEntry 6 }

pduGroupApparentPower OBJECT-TYPE
	SYNTAX Gauge32
	MAX-ACCESS read-only
	STATUS deprecated
	DESCRIPTION
		"Total apparent-power for outlet group"
	::= { pduGroupEntry 8 }

pduGroupPowerFactor OBJECT-TYPE
	SYNTAX Gauge32
	MAX-ACCESS read-only
	STATUS deprecated
	DESCRIPTION
		"Total power-factor for outlet group"
	::= { pduGroupEntry 9 }

pduGroupRealPower OBJECT-TYPE
	SYNTAX Gauge32
	MAX-ACCESS read-only
	STATUS deprecated
	DESCRIPTION
		"Total real-power for outlet group"
	::= { pduGroupEntry 10 }

pduGroupVolts OBJECT-TYPE
	SYNTAX Gauge32
	MAX-ACCESS read-only
	STATUS deprecated
	DESCRIPTION
		"Volts reading for outlet group"
	::= { pduGroupEntry 11 }

pduGroupWattHours OBJECT-TYPE
	SYNTAX Gauge32
	MAX-ACCESS read-only
	STATUS deprecated
	DESCRIPTION
		"Watt-hours reading for outlet group"
	::= { pduGroupEntry 13 }

--###########################################################################################--
--pduOutletMainTable--
--###########################################################################################--

pduOutletMainTable OBJECT-TYPE
	SYNTAX SEQUENCE OF PduOutletMainEntry
	MAX-ACCESS  not-accessible
	STATUS deprecated
	DESCRIPTION
		"Outlet data common to all outlet types. Other tables provide
		additional data, based on the outlet type."
	::= { legacyPDU 6 }

pduOutletMainEntry OBJECT-TYPE
	SYNTAX PduOutletMainEntry
	MAX-ACCESS  not-accessible
	STATUS deprecated
	DESCRIPTION
		"One entry per outlet. Each entry corresponds to an outlet on a PDU, so
		they are indexed by the PDU's instance number and an outlet id number.
		The pduOutletMainIndex corresponds to an instance number for an
		existing PDU."
	INDEX { pduOutletMainIndex, pduOutletMainID }
	::= { pduOutletMainTable 1 }

PduOutletMainEntry ::= SEQUENCE {
	pduOutletMainIndex				Unsigned32,
	pduOutletMainSerial				DeviceSerial,
	pduOutletMainID				Unsigned32,
	pduOutletMainLabel				DeviceLabel,
	pduOutletMainName				DisplayString,
	pduOutletMainGroup				DisplayString,
	pduOutletMainURL				DisplayString
}

pduOutletMainIndex OBJECT-TYPE
	SYNTAX Unsigned32(1..64)
	MAX-ACCESS not-accessible
	STATUS deprecated
	DESCRIPTION
		"Table entry index value"
	::= { pduOutletMainEntry 1 }

pduOutletMainSerial OBJECT-TYPE
	SYNTAX DeviceSerial
	MAX-ACCESS read-only
	STATUS deprecated
	DESCRIPTION
		"Serial number of an existing PDU device"
	::= { pduOutletMainEntry 2 }

pduOutletMainID OBJECT-TYPE
	SYNTAX Unsigned32(1..64)
	MAX-ACCESS read-only
	STATUS deprecated
	DESCRIPTION
		"Outlet id number"
	::= { pduOutletMainEntry 3 }

pduOutletMainLabel OBJECT-TYPE
	SYNTAX DeviceLabel
	MAX-ACCESS read-write
	STATUS deprecated
	DESCRIPTION
		"User-defined outlet name"
	::= { pduOutletMainEntry 4 }

pduOutletMainName OBJECT-TYPE
	SYNTAX DisplayString
	MAX-ACCESS read-only
	STATUS deprecated
	DESCRIPTION
		"Factory-assigned outlet name"
	::= { pduOutletMainEntry 5 }

pduOutletMainGroup OBJECT-TYPE
	SYNTAX DisplayString
	MAX-ACCESS read-only
	STATUS deprecated
	DESCRIPTION
		"Outlet's group name"
	::= { pduOutletMainEntry 6 }

pduOutletMainURL OBJECT-TYPE
	SYNTAX DisplayString
	MAX-ACCESS read-only
	STATUS deprecated
	DESCRIPTION
		"Link info for outlet"
	::= { pduOutletMainEntry 7 }

--###########################################################################################--
--pduOutletSwitchTable--
--###########################################################################################--

pduOutletSwitchTable OBJECT-TYPE
	SYNTAX SEQUENCE OF PduOutletSwitchEntry
	MAX-ACCESS  not-accessible
	STATUS deprecated
	DESCRIPTION
		"Contains entries for outlets that support switching. This table
		supplements the corresponding entries in pduOutletMainTable."
	::= { legacyPDU 7 }

pduOutletSwitchEntry OBJECT-TYPE
	SYNTAX PduOutletSwitchEntry
	MAX-ACCESS  not-accessible
	STATUS deprecated
	DESCRIPTION
		"One entry is created per switching outlet. These entries correspond to
		an outlet entry in pduOutletMainTable. Each entry in this table uses
		the index and outlet id from the pduOutletMainTable."
	INDEX { pduOutletMainIndex, pduOutletMainID }
	::= { pduOutletSwitchTable 1 }

PduOutletSwitchEntry ::= SEQUENCE {
	pduOutletSwitchState				INTEGER,
	pduOutletSwitchStateChangeTime				Unsigned32,
	pduOutletSwitchCurrentAction				INTEGER,
	pduOutletSwitchOnDelay				Unsigned32,
	pduOutletSwitchOffDelay				Unsigned32,
	pduOutletSwitchRebootDelay				Unsigned32,
	pduOutletSwitchRebootHold				Unsigned32,
	pduOutletSwitchStartupAction				INTEGER,
	pduOutletSwitchStartupStateDelay				Unsigned32,
	pduOutletSwitchControl				INTEGER
}

pduOutletSwitchState OBJECT-TYPE
	SYNTAX INTEGER {
			outletOff(0),
			outletOn(1),
			outletError(2)
			}
	MAX-ACCESS read-only
	STATUS deprecated
	DESCRIPTION
		"Switch state of the outlet"
	::= { pduOutletSwitchEntry 1 }

pduOutletSwitchStateChangeTime OBJECT-TYPE
	SYNTAX Unsigned32
	MAX-ACCESS read-only
	STATUS deprecated
	DESCRIPTION
		"Seconds until an action will occur"
	::= { pduOutletSwitchEntry 2 }

pduOutletSwitchCurrentAction OBJECT-TYPE
	SYNTAX INTEGER {
			manual(1),
			reboot(2),
			startUp(3),
			other(4)
			}
	MAX-ACCESS read-only
	STATUS deprecated
	DESCRIPTION
		"Outlet action in progress"
	::= { pduOutletSwitchEntry 3 }

pduOutletSwitchOnDelay OBJECT-TYPE
	SYNTAX Unsigned32
	MAX-ACCESS read-write
	STATUS deprecated
	DESCRIPTION
		"Delay used in turning the outlet on"
	::= { pduOutletSwitchEntry 4 }

pduOutletSwitchOffDelay OBJECT-TYPE
	SYNTAX Unsigned32
	MAX-ACCESS read-write
	STATUS deprecated
	DESCRIPTION
		"Delay used in turning the outlet off"
	::= { pduOutletSwitchEntry 5 }

pduOutletSwitchRebootDelay OBJECT-TYPE
	SYNTAX Unsigned32
	MAX-ACCESS read-write
	STATUS deprecated
	DESCRIPTION
		"Delay used prior to outlet reboot"
	::= { pduOutletSwitchEntry 6 }

pduOutletSwitchRebootHold OBJECT-TYPE
	SYNTAX Unsigned32
	MAX-ACCESS read-write
	STATUS deprecated
	DESCRIPTION
		"Time the outlet is kept off during a reboot"
	::= { pduOutletSwitchEntry 7 }

pduOutletSwitchStartupAction OBJECT-TYPE
	SYNTAX INTEGER {
			startOff(0),
			startOn(1),
			lastKnown(2)
			}
	MAX-ACCESS read-write
	STATUS deprecated
	DESCRIPTION
		"State the outlet should take at startup (first powered)"
	::= { pduOutletSwitchEntry 8 }

pduOutletSwitchStartupStateDelay OBJECT-TYPE
	SYNTAX Unsigned32
	MAX-ACCESS read-write
	STATUS deprecated
	DESCRIPTION
		"Delay from startup before the outlet changes to the StartupAction"
	::= { pduOutletSwitchEntry 9 }

pduOutletSwitchControl OBJECT-TYPE
	SYNTAX INTEGER {
			none(0),
			cancelActions(1),
			onNoDelay(2),
			onDelay(3),
			offNoDelay(4),
			offDelay(5),
			rebootNoDelay(6),
			rebootDelay(7)
			}
	MAX-ACCESS read-write
	STATUS deprecated
	DESCRIPTION
		"Used for manual control of the outlet. The default is none(0). When
		set, it keeps this value until the operation is complete. Then the
		value goes back to none(0). Outlet must be in manual mode to set,
		otherwise it causes an inconsistentValue error. Can be set to one of
		the following:
		1 = Cancel pending action
		2 = Turn outlet on without delay
		3 = After delay, turn outlet on
		4 = Turn outlet off without delay
		5 = After delay, turn outlet off
		6 = Reboot outlet without delay
		7 = After delay, reboot outlet"
	::= { pduOutletSwitchEntry 10 }

--###########################################################################################--
--pduOutletMeterTable--
--###########################################################################################--

pduOutletMeterTable OBJECT-TYPE
	SYNTAX SEQUENCE OF PduOutletMeterEntry
	MAX-ACCESS  not-accessible
	STATUS deprecated
	DESCRIPTION
		"Contains entries for outlets that support metering. This table
		supplements the corresponding entries in pduOutletMainTable."
	::= { legacyPDU 8 }

pduOutletMeterEntry OBJECT-TYPE
	SYNTAX PduOutletMeterEntry
	MAX-ACCESS  not-accessible
	STATUS deprecated
	DESCRIPTION
		"One entry is created per metering outlet. These entries correspond to
		an outlet entry in pduOutletMainTable. Each entry in this table uses
		the index and outlet id from the pduOutletMainTable."
	INDEX { pduOutletMainIndex, pduOutletMainID }
	::= { pduOutletMeterTable 1 }

PduOutletMeterEntry ::= SEQUENCE {
	pduOutletMeterKWattHrs				Gauge32,
	pduOutletMeterAmps				DeciAmps,
	pduOutletMeterPower				Gauge32
}

pduOutletMeterKWattHrs OBJECT-TYPE
	SYNTAX Gauge32
	MAX-ACCESS read-only
	STATUS deprecated
	DESCRIPTION
		"Kilowatt hours for outlet"
	::= { pduOutletMeterEntry 1 }

pduOutletMeterAmps OBJECT-TYPE
	SYNTAX DeciAmps
	MAX-ACCESS read-only
	STATUS deprecated
	DESCRIPTION
		"Current reading for outlet"
	::= { pduOutletMeterEntry 2 }

pduOutletMeterPower OBJECT-TYPE
	SYNTAX Gauge32
	MAX-ACCESS read-only
	STATUS deprecated
	DESCRIPTION
		"Power measurement for outlet"
	::= { pduOutletMeterEntry 3 }

--###########################################################################################--
--rtafhd3Table--
--###########################################################################################--

rtafhd3Table OBJECT-TYPE
	SYNTAX SEQUENCE OF Rtafhd3Entry
	MAX-ACCESS  not-accessible
	STATUS deprecated
	DESCRIPTION
		"Combo airflow, temp, humidity and dewpoint sensor"
	::= { rtafhd3 1 }

rtafhd3Entry OBJECT-TYPE
	SYNTAX Rtafhd3Entry
	MAX-ACCESS  not-accessible
	STATUS deprecated
	DESCRIPTION
		"One entry per device. Indexed by an instance number."
	INDEX { rtafhd3Index }
	::= { rtafhd3Table 1 }

Rtafhd3Entry ::= SEQUENCE {
	rtafhd3Index				Unsigned32,
	rtafhd3Serial				DeviceSerial,
	rtafhd3Label				DeviceLabel,
	rtafhd3Status				DeviceStatus,
	rtafhd3Airflow				Gauge32,
	rtafhd3Humidity				Gauge32,
	rtafhd3Temp				TemperatureValue,
	rtafhd3DewPoint				TemperatureValue,
	rtafhd3TDUnits				TemperatureUnits
}

rtafhd3Index OBJECT-TYPE
	SYNTAX Unsigned32(1..64)
	MAX-ACCESS not-accessible
	STATUS deprecated
	DESCRIPTION
		"Table entry index value"
	::= { rtafhd3Entry 1 }

rtafhd3Serial OBJECT-TYPE
	SYNTAX DeviceSerial
	MAX-ACCESS read-only
	STATUS deprecated
	DESCRIPTION
		"Unique device id"
	::= { rtafhd3Entry 2 }

rtafhd3Label OBJECT-TYPE
	SYNTAX DeviceLabel
	MAX-ACCESS read-write
	STATUS deprecated
	DESCRIPTION
		"User-defined name"
	::= { rtafhd3Entry 3 }

rtafhd3Status OBJECT-TYPE
	SYNTAX DeviceStatus
	MAX-ACCESS read-only
	STATUS deprecated
	DESCRIPTION
		"Sensor condition"
	::= { rtafhd3Entry 4 }

rtafhd3Airflow OBJECT-TYPE
	SYNTAX Gauge32
	MAX-ACCESS read-only
	STATUS deprecated
	DESCRIPTION
		"Airflow reading"
	::= { rtafhd3Entry 5 }

rtafhd3Humidity OBJECT-TYPE
	SYNTAX Gauge32
	MAX-ACCESS read-only
	STATUS deprecated
	DESCRIPTION
		"Humidity reading"
	::= { rtafhd3Entry 6 }

rtafhd3Temp OBJECT-TYPE
	SYNTAX TemperatureValue
	MAX-ACCESS read-only
	STATUS deprecated
	DESCRIPTION
		"Temperature reading in units indicated by rtafhd3TDUnits."
	::= { rtafhd3Entry 7 }

rtafhd3DewPoint OBJECT-TYPE
	SYNTAX TemperatureValue
	MAX-ACCESS read-only
	STATUS deprecated
	DESCRIPTION
		"Dewpoint reading in units indicated by rtafhd3TDUnits."
	::= { rtafhd3Entry 8 }

rtafhd3TDUnits OBJECT-TYPE
	SYNTAX TemperatureUnits
	MAX-ACCESS read-only
	STATUS deprecated
	DESCRIPTION
		"Tells what units are used for temperature and dewpoint."
	::= { rtafhd3Entry 9 }

--###########################################################################################--
--rtTable--
--###########################################################################################--

rtTable OBJECT-TYPE
	SYNTAX SEQUENCE OF RtEntry
	MAX-ACCESS  not-accessible
	STATUS deprecated
	DESCRIPTION
		"Contains entries for remote temperature devices"
	::= { rt 1 }

rtEntry OBJECT-TYPE
	SYNTAX RtEntry
	MAX-ACCESS  not-accessible
	STATUS deprecated
	DESCRIPTION
		"One entry per device. Indexed by an instance number."
	INDEX { rtIndex }
	::= { rtTable 1 }

RtEntry ::= SEQUENCE {
	rtIndex				Unsigned32,
	rtSerial				DeviceSerial,
	rtLabel				DeviceLabel,
	rtStatus				DeviceStatus,
	rtTemp				TemperatureValue,
	rtUnits				TemperatureUnits
}

rtIndex OBJECT-TYPE
	SYNTAX Unsigned32(1..64)
	MAX-ACCESS not-accessible
	STATUS deprecated
	DESCRIPTION
		"Table entry index value"
	::= { rtEntry 1 }

rtSerial OBJECT-TYPE
	SYNTAX DeviceSerial
	MAX-ACCESS read-only
	STATUS deprecated
	DESCRIPTION
		"Unique device id"
	::= { rtEntry 2 }

rtLabel OBJECT-TYPE
	SYNTAX DeviceLabel
	MAX-ACCESS read-write
	STATUS deprecated
	DESCRIPTION
		"User-defined name"
	::= { rtEntry 3 }

rtStatus OBJECT-TYPE
	SYNTAX DeviceStatus
	MAX-ACCESS read-only
	STATUS deprecated
	DESCRIPTION
		"Device condition"
	::= { rtEntry 4 }

rtTemp OBJECT-TYPE
	SYNTAX TemperatureValue
	MAX-ACCESS read-only
	STATUS deprecated
	DESCRIPTION
		"Temperature reading. The units for this measurement are given by
		rtUnits."
	::= { rtEntry 5 }

rtUnits OBJECT-TYPE
	SYNTAX TemperatureUnits
	MAX-ACCESS read-only
	STATUS deprecated
	DESCRIPTION
		"Indicates what units rtTemp will be given in."
	::= { rtEntry 6 }

--###########################################################################################--
--t3hdTable--
--###########################################################################################--

t3hdTable OBJECT-TYPE
	SYNTAX SEQUENCE OF T3hdEntry
	MAX-ACCESS  not-accessible
	STATUS deprecated
	DESCRIPTION
		"Contains entries for T3HD devices"
	::= { t3hd 1 }

t3hdEntry OBJECT-TYPE
	SYNTAX T3hdEntry
	MAX-ACCESS  not-accessible
	STATUS deprecated
	DESCRIPTION
		"Each entry represents a T3HD device. They are indexed by an instance
		number."
	INDEX { t3hdIndex }
	::= { t3hdTable 1 }

T3hdEntry ::= SEQUENCE {
	t3hdIndex				Unsigned32,
	t3hdSerial				DeviceSerial,
	t3hdLabel				DeviceLabel,
	t3hdStatus				DeviceStatus,
	t3hdMainLabel				DeviceLabel,
	t3hdMainTemp				TemperatureValue,
	t3hdMainHumidity				Gauge32,
	t3hdMainDewPoint				TemperatureValue,
	t3hdExt1Status				INTEGER,
	t3hdExt1Label				DeviceLabel,
	t3hdExt1Temp				TemperatureValue,
	t3hdExt2Status				INTEGER,
	t3hdExt2Label				DeviceLabel,
	t3hdExt2Temp				TemperatureValue,
	t3hdTDUnits				TemperatureUnits
}

t3hdIndex OBJECT-TYPE
	SYNTAX Unsigned32(1..64)
	MAX-ACCESS not-accessible
	STATUS deprecated
	DESCRIPTION
		"Table entry index value"
	::= { t3hdEntry 1 }

t3hdSerial OBJECT-TYPE
	SYNTAX DeviceSerial
	MAX-ACCESS read-only
	STATUS deprecated
	DESCRIPTION
		"Unique device id"
	::= { t3hdEntry 2 }

t3hdLabel OBJECT-TYPE
	SYNTAX DeviceLabel
	MAX-ACCESS read-write
	STATUS deprecated
	DESCRIPTION
		"User-defined name"
	::= { t3hdEntry 3 }

t3hdStatus OBJECT-TYPE
	SYNTAX DeviceStatus
	MAX-ACCESS read-only
	STATUS deprecated
	DESCRIPTION
		"Device condition"
	::= { t3hdEntry 4 }

t3hdMainLabel OBJECT-TYPE
	SYNTAX DeviceLabel
	MAX-ACCESS read-write
	STATUS deprecated
	DESCRIPTION
		"User-defined label for measurements from the main device"
	::= { t3hdEntry 5 }

t3hdMainTemp OBJECT-TYPE
	SYNTAX TemperatureValue
	MAX-ACCESS read-only
	STATUS deprecated
	DESCRIPTION
		"Temperature reading from the main device"
	::= { t3hdEntry 6 }

t3hdMainHumidity OBJECT-TYPE
	SYNTAX Gauge32
	MAX-ACCESS read-only
	STATUS deprecated
	DESCRIPTION
		"Humidity reading from the main device"
	::= { t3hdEntry 7 }

t3hdMainDewPoint OBJECT-TYPE
	SYNTAX TemperatureValue
	MAX-ACCESS read-only
	STATUS deprecated
	DESCRIPTION
		"Dew Point value from the main device"
	::= { t3hdEntry 8 }

t3hdExt1Status OBJECT-TYPE
	SYNTAX INTEGER {
			unplugged(0),
			normal(1),
			error(2)
			}
	MAX-ACCESS read-only
	STATUS deprecated
	DESCRIPTION
		"Sensor status for external temp 1. The status is one of the following
		values:
		0 = Sensor unplugged
		1 = Normal operation
		2 = Sensor error"
	::= { t3hdEntry 9 }

t3hdExt1Label OBJECT-TYPE
	SYNTAX DeviceLabel
	MAX-ACCESS read-write
	STATUS deprecated
	DESCRIPTION
		"User-defined name for external temp 1"
	::= { t3hdEntry 10 }

t3hdExt1Temp OBJECT-TYPE
	SYNTAX TemperatureValue
	MAX-ACCESS read-only
	STATUS deprecated
	DESCRIPTION
		"Temperature reading from external temp 1"
	::= { t3hdEntry 11 }

t3hdExt2Status OBJECT-TYPE
	SYNTAX INTEGER {
			unplugged(0),
			normal(1),
			error(2)
			}
	MAX-ACCESS read-only
	STATUS deprecated
	DESCRIPTION
		"Sensor status for external temp 2. The status is one of the following
		values:
		0 = Sensor unplugged
		1 = Normal operation
		2 = Sensor error"
	::= { t3hdEntry 12 }

t3hdExt2Label OBJECT-TYPE
	SYNTAX DeviceLabel
	MAX-ACCESS read-write
	STATUS deprecated
	DESCRIPTION
		"User-defined name for external temp 2"
	::= { t3hdEntry 13 }

t3hdExt2Temp OBJECT-TYPE
	SYNTAX TemperatureValue
	MAX-ACCESS read-only
	STATUS deprecated
	DESCRIPTION
		"Temperature reading from external temp 2"
	::= { t3hdEntry 14 }

t3hdTDUnits OBJECT-TYPE
	SYNTAX TemperatureUnits
	MAX-ACCESS read-only
	STATUS deprecated
	DESCRIPTION
		"Tells what units are used for temperatures and dewpoint."
	::= { t3hdEntry 15 }

--###########################################################################################--
--thdTable--
--###########################################################################################--

thdTable OBJECT-TYPE
	SYNTAX SEQUENCE OF ThdEntry
	MAX-ACCESS  not-accessible
	STATUS deprecated
	DESCRIPTION
		"Contains entries for THD devices"
	::= { thd 1 }

thdEntry OBJECT-TYPE
	SYNTAX ThdEntry
	MAX-ACCESS  not-accessible
	STATUS deprecated
	DESCRIPTION
		"Each entry represents a THD device. They are indexed by an instance
		number."
	INDEX { thdIndex }
	::= { thdTable 1 }

ThdEntry ::= SEQUENCE {
	thdIndex				Unsigned32,
	thdSerial				DeviceSerial,
	thdLabel				DeviceLabel,
	thdStatus				DeviceStatus,
	thdTemp				TemperatureValue,
	thdHumidity				Gauge32,
	thdDewPoint				TemperatureValue,
	thdTDUnits				TemperatureUnits
}

thdIndex OBJECT-TYPE
	SYNTAX Unsigned32(1..64)
	MAX-ACCESS not-accessible
	STATUS deprecated
	DESCRIPTION
		"Table entry index value"
	::= { thdEntry 1 }

thdSerial OBJECT-TYPE
	SYNTAX DeviceSerial
	MAX-ACCESS read-only
	STATUS deprecated
	DESCRIPTION
		"Unique device id"
	::= { thdEntry 2 }

thdLabel OBJECT-TYPE
	SYNTAX DeviceLabel
	MAX-ACCESS read-write
	STATUS deprecated
	DESCRIPTION
		"User-defined name"
	::= { thdEntry 3 }

thdStatus OBJECT-TYPE
	SYNTAX DeviceStatus
	MAX-ACCESS read-only
	STATUS deprecated
	DESCRIPTION
		"Device condition"
	::= { thdEntry 4 }

thdTemp OBJECT-TYPE
	SYNTAX TemperatureValue
	MAX-ACCESS read-only
	STATUS deprecated
	DESCRIPTION
		"Temperature reading"
	::= { thdEntry 5 }

thdHumidity OBJECT-TYPE
	SYNTAX Gauge32
	MAX-ACCESS read-only
	STATUS deprecated
	DESCRIPTION
		"Humidity reading"
	::= { thdEntry 6 }

thdDewPoint OBJECT-TYPE
	SYNTAX TemperatureValue
	MAX-ACCESS read-only
	STATUS deprecated
	DESCRIPTION
		"Dew Point value"
	::= { thdEntry 7 }

thdTDUnits OBJECT-TYPE
	SYNTAX TemperatureUnits
	MAX-ACCESS read-only
	STATUS deprecated
	DESCRIPTION
		"Units used for temperature and dew point."
	::= { thdEntry 8 }

--###########################################################################################--
--common group--
--###########################################################################################--

common OBJECT IDENTIFIER ::= { vertiv 42 }

identity OBJECT IDENTIFIER ::= { common 1 }

r05 OBJECT-IDENTITY
	STATUS current
	DESCRIPTION
		"Value given for sysObjectID on R-Series units"
	::= { identity 15 }

i03 OBJECT-IDENTITY
	STATUS current
	DESCRIPTION
		"Value given for sysObjectID on IMD3 units"
	::= { identity 53 }

END

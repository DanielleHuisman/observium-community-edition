GUDEADS-EPC8X-MIB DEFINITIONS ::= BEGIN

IMPORTS
	enterprises,
	MODULE-IDENTITY,
	OBJECT-TYPE,
	NOTIFICATION-TYPE,
	Counter32,
	Integer32,
	IpAddress
		FROM SNMPv2-SMI
	OBJECT-GROUP,
	NOTIFICATION-GROUP
		FROM SNMPv2-CONF;

gudeads MODULE-IDENTITY
	LAST-UPDATED "200703051356Z"	-- Mar 5, 2007 1:56:00 PM
	ORGANIZATION "Gude Analog- und Digitalsysteme GmbH"
	CONTACT-INFO
		"http://www.gudeads.com/"
	DESCRIPTION
		""
	REVISION "200703051356Z"	-- Mar 5, 2007 1:56:00 PM
	DESCRIPTION
		"$Id: GUDEADS-EPC8X-MIB.txt,v 1.9 2008/08/06 15:14:23 petes1 Exp $"
	-- 1.3.6.1.4.1.28507
	::= { enterprises 28507 }


-- Notification Types
--

events OBJECT IDENTIFIER 
	-- 1.3.6.1.4.1.28507.1.0
	::= { gadsEPC8 0 }

epc8TrapIPTable OBJECT-TYPE
	SYNTAX  SEQUENCE OF Epc8TrapIPEntry
	MAX-ACCESS not-accessible
	STATUS  current
	DESCRIPTION
		"list of all Trap receiver"
	-- 1.3.6.1.4.1.28507.1.1.1.2
	::= { epc8SNMPaccess 2 }


gadsEPC8 OBJECT IDENTIFIER 
	-- 1.3.6.1.4.1.28507.1
	::= { gudeads 1 }

epc8TrapIPEntry OBJECT-TYPE
	SYNTAX  Epc8TrapIPEntry
	MAX-ACCESS not-accessible
	STATUS  current
	DESCRIPTION
		"an entry containing management
		informations regarding the list of trap
		receivers"
	INDEX {
		epc8TrapIPIndex }
	-- 1.3.6.1.4.1.28507.1.1.1.2.1
	::= { epc8TrapIPTable 1 }


Epc8TrapIPEntry ::= SEQUENCE {

	epc8TrapIPIndex Integer32,
	epc8TrapIPAddr  IpAddress,
	epc8TrapIPPort  Integer32 }


epc8TrapIPIndex OBJECT-TYPE
	SYNTAX  Integer32 (1..8)
	MAX-ACCESS not-accessible
	STATUS  current
	DESCRIPTION
		"A unique value, greater than zero, for each receiver slot."
	-- 1.3.6.1.4.1.28507.1.1.1.2.1.1
	::= { epc8TrapIPEntry 1 }


epc8TrapIPPort OBJECT-TYPE
	SYNTAX  Integer32 (0..1024)
	MAX-ACCESS read-write
	STATUS  current
	DESCRIPTION
		"IP Port specifying one Trap receiver slot.
		A value of  0 disables this slot."
	DEFVAL { 162 }
	-- 1.3.6.1.4.1.28507.1.1.1.2.1.3
	::= { epc8TrapIPEntry 3 }


epc8portNumber OBJECT-TYPE
	SYNTAX  Integer32 (1..8)
	MAX-ACCESS read-only
	STATUS  current
	DESCRIPTION
		"The number of PowerPorts"
	-- 1.3.6.1.4.1.28507.1.1.2.1
	::= { epc8powerports 1 }


epc8PortIndex OBJECT-TYPE
	SYNTAX  Integer32 (1..8)
	MAX-ACCESS not-accessible
	STATUS  current
	DESCRIPTION
		"A unique value, greater than zero, for each PowerPort."
	-- 1.3.6.1.4.1.28507.1.1.2.2.1.1
	::= { epc8portEntry 1 }


epc8PortStartupMode OBJECT-TYPE
	SYNTAX  INTEGER {
			off(0),
			on(1),
			laststate(2) }
	MAX-ACCESS read-write
	STATUS  current
	DESCRIPTION
		"set Mode of startup sequence (off, on , remember last state)"
	DEFVAL { off }
	-- 1.3.6.1.4.1.28507.1.1.2.2.1.5
	::= { epc8portEntry 5 }


epc8Sensors OBJECT IDENTIFIER 
	-- 1.3.6.1.4.1.28507.1.1.3
	::= { epc8Objects 3 }

epc8Irms OBJECT-TYPE
	SYNTAX  Integer32
	UNITS
		"mA"
	MAX-ACCESS read-only
	STATUS  current
	DESCRIPTION
		"actual rms Current, a value of -9999 indicates
		that data is not available"
	-- 1.3.6.1.4.1.28507.1.1.3.1
	::= { epc8Sensors 1 }


epc8SensorTable OBJECT-TYPE
	SYNTAX  SEQUENCE OF Epc8SensorEntry
	MAX-ACCESS not-accessible
	STATUS  current
	DESCRIPTION
		""
	-- 1.3.6.1.4.1.28507.1.1.3.2
	::= { epc8Sensors 2 }


epc8SensorEntry OBJECT-TYPE
	SYNTAX  Epc8SensorEntry
	MAX-ACCESS not-accessible
	STATUS  current
	DESCRIPTION
		""
	INDEX {
		epc8SensorIndex }
	-- 1.3.6.1.4.1.28507.1.1.3.2.1
	::= { epc8SensorTable 1 }


Epc8SensorEntry ::= SEQUENCE {

	epc8SensorIndex Integer32,
	epc8TempSensor  Integer32,
	epc8HygroSensor Integer32 }


epc8SensorIndex OBJECT-TYPE
	SYNTAX  Integer32 (1..2)
	MAX-ACCESS not-accessible
	STATUS  current
	DESCRIPTION
		""
	-- 1.3.6.1.4.1.28507.1.1.3.2.1.1
	::= { epc8SensorEntry 1 }


epc8TempSensor OBJECT-TYPE
	SYNTAX  Integer32
	UNITS
		"10th of degree Celsius"
	MAX-ACCESS read-only
	STATUS  current
	DESCRIPTION
		"actual temperature,  a value of -9999 indicates 
		that data is not available"
	-- 1.3.6.1.4.1.28507.1.1.3.2.1.2
	::= { epc8SensorEntry 2 }


epc8HygroSensor OBJECT-TYPE
	SYNTAX  Integer32
	UNITS
		"10th of percentage humidity"
	MAX-ACCESS read-only
	STATUS  current
	DESCRIPTION
		"actual humidity,  a value of -9999 indicates
		that data is not available"
	-- 1.3.6.1.4.1.28507.1.1.3.2.1.3
	::= { epc8SensorEntry 3 }



epcSwitchEvtPort1 NOTIFICATION-TYPE
	OBJECTS {
		epc8PortName,
		epc8PortState,
		epc8PortSwitchCount}
	STATUS  current
	DESCRIPTION
		"Event is triggered when a port is switched"
	-- 1.3.6.1.4.1.28507.1.0.1
	::= { events 1 }


epcSwitchEvtPort2 NOTIFICATION-TYPE
	OBJECTS {
		epc8PortName,
		epc8PortState,
		epc8PortSwitchCount}
	STATUS  current
	DESCRIPTION
		"Event is triggered when a port is switched"
	-- 1.3.6.1.4.1.28507.1.0.2
	::= { events 2 }


epcSwitchEvtPort3 NOTIFICATION-TYPE
	OBJECTS {
		epc8PortName,
		epc8PortState,
		epc8PortSwitchCount}
	STATUS  current
	DESCRIPTION
		"Event is triggered when a port is switched"
	-- 1.3.6.1.4.1.28507.1.0.3
	::= { events 3 }


epcSwitchEvtPort4 NOTIFICATION-TYPE
	OBJECTS {
		epc8PortName,
		epc8PortState,
		epc8PortSwitchCount}
	STATUS  current
	DESCRIPTION
		"Event is triggered when a port is switched"
	-- 1.3.6.1.4.1.28507.1.0.4
	::= { events 4 }


epcSwitchEvtPort5 NOTIFICATION-TYPE
	OBJECTS {
		epc8PortName,
		epc8PortState,
		epc8PortSwitchCount}
	STATUS  current
	DESCRIPTION
		"Event is triggered when a port is switched"
	-- 1.3.6.1.4.1.28507.1.0.5
	::= { events 5 }


epcSwitchEvtPort6 NOTIFICATION-TYPE
	OBJECTS {
		epc8PortName,
		epc8PortState,
		epc8PortSwitchCount}
	STATUS  current
	DESCRIPTION
		"Event is triggered when a port is switched"
	-- 1.3.6.1.4.1.28507.1.0.6
	::= { events 6 }


epcSwitchEvtPort7 NOTIFICATION-TYPE
	OBJECTS {
		epc8PortName,
		epc8PortState,
		epc8PortSwitchCount}
	STATUS  current
	DESCRIPTION
		"Event is triggered when a port is switched"
	-- 1.3.6.1.4.1.28507.1.0.7
	::= { events 7 }


epcSwitchEvtPort8 NOTIFICATION-TYPE
	OBJECTS {
		epc8PortName,
		epc8PortState,
		epc8PortSwitchCount}
	STATUS  current
	DESCRIPTION
		"Event is triggered when a port is switched"
	-- 1.3.6.1.4.1.28507.1.0.8
	::= { events 8 }

epc8SNMPaccess OBJECT IDENTIFIER 
	-- 1.3.6.1.4.1.28507.1.1.1
	::= { epc8Objects 1 }

epc8TrapCtrl OBJECT-TYPE
	SYNTAX  Integer32 (0..2)
	MAX-ACCESS read-write
	STATUS  current
	DESCRIPTION
		"0 = off
		1 = Ver. 1
		2 = Ver. 2c"
	-- 1.3.6.1.4.1.28507.1.1.1.1
	::= { epc8SNMPaccess 1 }


-- Scalars and Tables
--

epc8Objects OBJECT IDENTIFIER 
	-- 1.3.6.1.4.1.28507.1.1
	::= { gadsEPC8 1 }

epc8powerports OBJECT IDENTIFIER 
	-- 1.3.6.1.4.1.28507.1.1.2
	::= { epc8Objects 2 }

-- the Interfaces table
-- The Interfaces table contains information on the entity's
-- interfaces.  Each sub-layer below the internetwork-layer
-- of a network interface is considered to be an interface.

epc8portTable OBJECT-TYPE
	SYNTAX  SEQUENCE OF Epc8portEntry
	MAX-ACCESS not-accessible
	STATUS  current
	DESCRIPTION
		"list of all EPC Powerports"
	-- 1.3.6.1.4.1.28507.1.1.2.2
	::= { epc8powerports 2 }


epc8portEntry OBJECT-TYPE
	SYNTAX  Epc8portEntry
	MAX-ACCESS not-accessible
	STATUS  current
	DESCRIPTION
		"An entry containing management information applicable to a
		particular powerport."
	INDEX {
		epc8PortIndex }
	-- 1.3.6.1.4.1.28507.1.1.2.2.1
	::= { epc8portTable 1 }


Epc8portEntry ::= SEQUENCE {

	epc8PortIndex        Integer32,
	epc8PortName         OCTET STRING,
	epc8PortState        INTEGER,
	epc8PortSwitchCount  Counter32,
	epc8PortStartupMode  INTEGER,
	epc8PortStartupDelay Integer32,
	epc8PortRepowerTime  Integer32 }


epc8PortName OBJECT-TYPE
	SYNTAX  OCTET STRING (SIZE (0..15))
	MAX-ACCESS read-only
	STATUS  current
	DESCRIPTION
		"A textual string containing name of a PowerPort."
	-- 1.3.6.1.4.1.28507.1.1.2.2.1.2
	::= { epc8portEntry 2 }


epc8PortState OBJECT-TYPE
	SYNTAX  INTEGER {
			off(0),
			on(1) }
	MAX-ACCESS read-write
	STATUS  current
	DESCRIPTION
		"current state a PowerPort"
	-- 1.3.6.1.4.1.28507.1.1.2.2.1.3
	::= { epc8portEntry 3 }


epc8PortStartupDelay OBJECT-TYPE
	SYNTAX  Integer32
	UNITS
		"seconds"
	MAX-ACCESS read-write
	STATUS  current
	DESCRIPTION
		"Delay in sec for startup action"
	DEFVAL { 0 }
	-- 1.3.6.1.4.1.28507.1.1.2.2.1.6
	::= { epc8portEntry 6 }


epc8PortRepowerTime OBJECT-TYPE
	SYNTAX  Integer32 (0..65535)
	UNITS
		"seconds"
	MAX-ACCESS read-write
	STATUS  current
	DESCRIPTION
		"Delay in sec for repower port after switching off"
	DEFVAL { 0 }
	-- 1.3.6.1.4.1.28507.1.1.2.2.1.7
	::= { epc8portEntry 7 }


epc8PortSwitchCount OBJECT-TYPE
	SYNTAX  Counter32
	MAX-ACCESS read-only
	STATUS  current
	DESCRIPTION
		"The total number of switch actions ocurred on a PowerPort.
		Does not count switch commands which will not switch
		the ralay state, so just real relay switches are displayed here."
	-- 1.3.6.1.4.1.28507.1.1.2.2.1.4
	::= { epc8portEntry 4 }


epc8TrapIPAddr OBJECT-TYPE
	SYNTAX  IpAddress
	MAX-ACCESS read-write
	STATUS  current
	DESCRIPTION
		"IP Address specifying one Trap receiver slot.
		A value of '00000000'H disables this slot."
	DEFVAL { '00000000'H }
	-- 1.3.6.1.4.1.28507.1.1.1.2.1.2
	::= { epc8TrapIPEntry 2 }


-- Conformance
--

epc8Conf OBJECT IDENTIFIER 
	-- 1.3.6.1.4.1.28507.1.3
	::= { gadsEPC8 3 }

-- Groups
--

epc8Groups OBJECT IDENTIFIER 
	-- 1.3.6.1.4.1.28507.1.3.1
	::= { epc8Conf 1 }

-- Compliance
--

epc8Compls OBJECT IDENTIFIER 
	-- 1.3.6.1.4.1.28507.1.3.2
	::= { epc8Conf 2 }


epc8TempEvtSen1 NOTIFICATION-TYPE
	OBJECTS {
		epc8TempSensor}
	STATUS  current
	DESCRIPTION
		"temperature limits exceeded"
	-- 1.3.6.1.4.1.28507.1.0.9
	::= { events 9 }


epc8TempEvtSen2 NOTIFICATION-TYPE
	OBJECTS {
		epc8TempSensor}
	STATUS  current
	DESCRIPTION
		"temperature limits exceeded"
	-- 1.3.6.1.4.1.28507.1.0.10
	::= { events 10 }


epc8HygroEvtSen1 NOTIFICATION-TYPE
	OBJECTS {
		epc8HygroSensor}
	STATUS  current
	DESCRIPTION
		"hygro limits exceeded"
	-- 1.3.6.1.4.1.28507.1.0.11
	::= { events 11 }


epc8HygroEvtSen2 NOTIFICATION-TYPE
	OBJECTS {
		epc8HygroSensor}
	STATUS  current
	DESCRIPTION
		"hygro limits exceeded"
	-- 1.3.6.1.4.1.28507.1.0.12
	::= { events 12 }

epc8BasicGroup OBJECT-GROUP
	OBJECTS {
		epc8portNumber,
		epc8PortName,
		epc8PortState,
		epc8PortSwitchCount,
		epc8TrapCtrl,
		epc8TrapIPAddr,
		epc8TrapIPPort,
		epc8PortStartupMode,
		epc8PortStartupDelay,
		epc8PortRepowerTime,
		epc8Irms,
		epc8TempSensor,
		epc8HygroSensor }
	STATUS  current
	DESCRIPTION
		"Basic objects."
	-- 1.3.6.1.4.1.28507.1.3.1.1
	::= { epc8Groups 1 }

epc8NotificationGroup NOTIFICATION-GROUP
	NOTIFICATIONS {
		epcSwitchEvtPort1,
		epcSwitchEvtPort2,
		epcSwitchEvtPort3,
		epcSwitchEvtPort4,
		epcSwitchEvtPort5,
		epcSwitchEvtPort6,
		epcSwitchEvtPort7,
		epcSwitchEvtPort8,
		epc8TempEvtSen1,
		epc8HygroEvtSen1,
		epc8TempEvtSen2,
		epc8HygroEvtSen2 }
	STATUS  current
	DESCRIPTION
		""
	-- 1.3.6.1.4.1.28507.1.3.1.2
	::= { epc8Groups 2 }

END

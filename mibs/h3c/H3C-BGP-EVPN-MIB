-- =============================================================================
-- Copyright (c) 2004-2017 Hangzhou H3C Tech. Co., Ltd. All rights reserved.
--
-- Description: This MIB module contains managed object definitions for
--              Border Gateway Protocol (BGP) Ethernet Virtual Private Network (EVPN).
-- Reference:
-- Version: V1.0
-- History:
--   V1.0 2017-11-20 Initial version Created by AnXiaoFeng
-- =============================================================================
H3C-BGP-EVPN-MIB DEFINITIONS ::= BEGIN
IMPORTS
    MODULE-IDENTITY, OBJECT-TYPE,
    Integer32, Unsigned32, IpAddress
        FROM SNMPv2-SMI
    TruthValue
        FROM SNMPv2-TC
    h3cCommon
        FROM HUAWEI-3COM-OID-MIB;

-- =============================================================================
-- module identity part
-- =============================================================================
h3cBgpEvpn MODULE-IDENTITY
    LAST-UPDATED "201711291431Z"
    ORGANIZATION
        "Hangzhou H3C Technologies Co., Ltd."
    CONTACT-INFO
        "Platform Team Hangzhou H3C Technologies Co., Ltd.
        Hai-Dian District Beijing P.R. China
        http://www.h3c.com
        Zip:100085"
    DESCRIPTION
        "This MIB contains managed object definitions for the
         Border Gateway Protocol (BGP) Ethernet Virtual Private
         Network (EVPN) as defined in : ."
    REVISION
        "201711291431Z"
    DESCRIPTION
        "modified according to review suggestions."
    REVISION
        "201711041431Z"
    DESCRIPTION
        "Initial version of this MIB."
    ::= { h3cCommon 172 }

-- =============================================================================
-- object definition begin
-- =============================================================================
h3cBgpEvpnObjects OBJECT IDENTIFIER ::= { h3cBgpEvpn 1 }
h3cBgpEvpnConf    OBJECT IDENTIFIER ::= { h3cBgpEvpnObjects 1 }

-- =============================================================================
-- h3cBgpEvpnNbrAddrTable Definition
-- =============================================================================
h3cBgpEvpnNbrAddrTable OBJECT-TYPE
    SYNTAX      SEQUENCE OF H3cBgpEvpnNbrAddrEntry
    MAX-ACCESS  not-accessible
    STATUS      current
    DESCRIPTION
        "This table specifies per-interface BGP EVPN neighbor
         addresses for both PEs and CEs."
    ::= { h3cBgpEvpnConf 1 }

h3cBgpEvpnNbrAddrEntry OBJECT-TYPE
    SYNTAX      H3cBgpEvpnNbrAddrEntry
    MAX-ACCESS  not-accessible
    STATUS      current
    DESCRIPTION
        "An entry in this table is created by an LSR for
         every VRF capable of supporting BGP EVPN.  The
         indexing provides an ordering of BGP prefixes
         per VRF."
    INDEX {
            h3cBgpEvpnNbrAddr
          }
    ::= { h3cBgpEvpnNbrAddrTable 1 }

H3cBgpEvpnNbrAddrEntry ::= SEQUENCE {
    h3cBgpEvpnNbrAddr         IpAddress,
    h3cBgpEvpnNbrAsNumber     Unsigned32
}

h3cBgpEvpnNbrAddr OBJECT-TYPE
    SYNTAX      IpAddress
    MAX-ACCESS  not-accessible
    STATUS      current
    DESCRIPTION
        "Denotes the BGP neighbor address."
    ::= { h3cBgpEvpnNbrAddrEntry 1 }

h3cBgpEvpnNbrAsNumber OBJECT-TYPE
    SYNTAX      Unsigned32
    MAX-ACCESS  read-only
    STATUS      current
    DESCRIPTION
        "The Autonomous System that the BGP's neighbor in."
    ::= { h3cBgpEvpnNbrAddrEntry 2 }

-- =============================================================================
-- End of h3cBgpEvpnNbrAddrTable Definition
-- =============================================================================

-- =============================================================================
-- h3cBgpEvpnNbrPrefixTable Definition
-- =============================================================================
h3cBgpEvpnNbrPrefixTable OBJECT-TYPE
    SYNTAX      SEQUENCE OF H3cBgpEvpnNbrPrefixEntry
    MAX-ACCESS  not-accessible
    STATUS      current
    DESCRIPTION
        "This table specifies per-VRF vpnv4 multi-protocol
         prefixes supported by BGP EVPN"
    ::= { h3cBgpEvpnConf 2 }

h3cBgpEvpnNbrPrefixEntry OBJECT-TYPE
    SYNTAX      H3cBgpEvpnNbrPrefixEntry
    MAX-ACCESS  not-accessible
    STATUS      current
    DESCRIPTION
        "An entry in this table is created by an LSR for
         every BGP prefix associated with a VRF supporting a
         BGP EVPN.  The indexing provides an ordering of
         BGP prefixes per VRF."
    INDEX {
            h3cBgpEvpnPAtrRD,
            h3cBgpEvpnPAtrPeer,
            h3cBgpEvpnPAtrAddrPrefixLen,
            h3cBgpEvpnPAtrAddrPrefix
          }
    ::= { h3cBgpEvpnNbrPrefixTable 1 }

H3cBgpEvpnNbrPrefixEntry ::= SEQUENCE {
    h3cBgpEvpnPAtrRD              OCTET STRING,
    h3cBgpEvpnPAtrPeer            OCTET STRING,
    h3cBgpEvpnPAtrAddrPrefixLen   Integer32,
    h3cBgpEvpnPAtrAddrPrefix      IpAddress,
    h3cBgpEvpnPAtrRouteType       Unsigned32,
    h3cBgpEvpnPAtrOrigin          INTEGER,
    h3cBgpEvpnPAtrASPathSegment   OCTET STRING,
    h3cBgpEvpnPAtrNextHop         IpAddress,
    h3cBgpEvpnPAtrMultiExitDisc   Integer32,
    h3cBgpEvpnPAtrLocalPref       Integer32,
    h3cBgpEvpnPAtrIGMPFlags       INTEGER,
    h3cBgpEvpnPAtrMaxRespTime     Unsigned32,
    h3cBgpEvpnPAtrPMSITunnel      OCTET STRING,
    h3cBgpEvpnPAtrL2VNI           Unsigned32,
    h3cBgpEvpnPAtrL3VNI           Unsigned32,
    h3cBgpEvpnPAtrBest            TruthValue,
    h3cBgpEvpnPAtrUnknown         OCTET STRING
}

h3cBgpEvpnPAtrRD OBJECT-TYPE
    SYNTAX      OCTET STRING (SIZE (3..21))
    MAX-ACCESS  not-accessible
    STATUS      current
    DESCRIPTION
        "The route distinguisher."
    ::= { h3cBgpEvpnNbrPrefixEntry 1 }

h3cBgpEvpnPAtrPeer OBJECT-TYPE
    SYNTAX      OCTET STRING (SIZE (1..86))
    MAX-ACCESS  not-accessible
    STATUS      current
    DESCRIPTION
        "The IP address of the peer where the path
         information was learned."
    ::= { h3cBgpEvpnNbrPrefixEntry 2 }

h3cBgpEvpnPAtrAddrPrefixLen OBJECT-TYPE
    SYNTAX      Integer32  (0..300)
    MAX-ACCESS  not-accessible
    STATUS      current
    DESCRIPTION
       "Length in bits of the Network
        Layer Reachability Information field."
    ::= { h3cBgpEvpnNbrPrefixEntry 3 }

h3cBgpEvpnPAtrAddrPrefix OBJECT-TYPE
    SYNTAX      IpAddress
    MAX-ACCESS  not-accessible
    STATUS      current
    DESCRIPTION
        "The EVPN information in the Network Layer
        Reachability Information field. BGP EVPN
        prefix includes:
        [1][ESI][EthernetTagID]:
           ESI: each Ethernet segment(ES) is identified
           by a unique non-zero identifier called an
           Ethernet Segment Identifier.
           EthernetTagID: This attribute identifies a
           particular broadcast domain in an EVPN instance.
        [2][EthernetTagID][MACLength][MAC][IPAddressLength][IPAddress]
        [3][EthernetTagID][IPAddressLength][IPAddress]
        [4][ESI][IPAddressLength][IPAddress]
        [5][EthernetTagID][IPAddressLength][IPAddress]
        [6][EthernetTagID][MulticastSourceLength]
           [MulticastSourceAddress][MulticastGroupLength]
           [MulticastGroupAddress][OriginatorRouterLength]
           [OriginatorRouterAddress]
        [7][ESI][EthernetTagID][MulticastSourceLength]
           [MulticastSourceAddress][MulticastGroupLength]
           [MulticastGroupAddress][OriginatorRouterLength]
           [OriginatorRouterAddress][LeaveGroupSyn]
           LeaveGroupSyn: This attribute identifies the
           specific (x, G) leave group synchronization
           procedure initiated by the advertising PE,
           which increments the value whenever it
           initiates a procedure.
        [8][ESI][EthernetTagID][MulticastSourceLength]
           [MulticastSourceAddress][MulticastGroupLength]
           [MulticastGroupAddress][OriginatorRouterLength]
           [OriginatorRouterAddress][LeaveGroupSyn]"
    ::= { h3cBgpEvpnNbrPrefixEntry 4 }

h3cBgpEvpnPAtrRouteType OBJECT-TYPE
    SYNTAX      Unsigned32
    MAX-ACCESS  read-only
    STATUS      current
    DESCRIPTION
        "Defines the following Route Types:
         1 - Ethernet Auto-Discovery (A-D) route
         2 - MAC/IP Advertisement route
         3 - Inclusive Multicast Ethernet Tag route
         4 - Ethernet Segment route
         5 - IP Prefix Route
         6 - Selective Multicast Ethernet Tag Route
         7 - IGMP Join Synch Route
         8 - IGMP Leave Synch Route"
    ::= { h3cBgpEvpnNbrPrefixEntry 5 }

h3cBgpEvpnPAtrOrigin OBJECT-TYPE
    SYNTAX      INTEGER { igp(1),-- networks are interior
                          egp(2),-- networks learned via EGP
                          incomplete(3) -- undetermined
                        }
    MAX-ACCESS  read-only
    STATUS      current
    DESCRIPTION
        "The ultimate origin of the path
         information."
    ::= { h3cBgpEvpnNbrPrefixEntry 6 }

h3cBgpEvpnPAtrASPathSegment OBJECT-TYPE
    SYNTAX      OCTET STRING (SIZE (2..255))
    MAX-ACCESS  read-only
    STATUS      current
    DESCRIPTION
        "The sequence of AS path segments.  Each AS
         path segment is represented by a triple
         <type, length, value>.

          The type is a 1-octet field which has two
          possible values:
              1      AS_SET: unordered set of ASs a
                     route in the UPDATE
                     message has traversed
              2      AS_SEQUENCE: ordered set of ASs
                     a route in the UPDATE
                     message has traversed.
                     The length is a 1-octet field containing the
                     number of ASs in the value field.

                     The value field contains one or more AS
                     numbers, each AS is represented in the octet
                     string as a pair of octets according to the
                     following algorithm:
                     first-byte-of-pair = ASNumber / 256;
                     second-byte-of-pair = ASNumber & 255;"
    ::= { h3cBgpEvpnNbrPrefixEntry 7 }

h3cBgpEvpnPAtrNextHop OBJECT-TYPE
    SYNTAX      IpAddress
    MAX-ACCESS  read-only
    STATUS      current
    DESCRIPTION
        "The address of the router that should be
         used for the destination network.  This address is
         the NEXT_HOP address received in the UPDATE packet."
    ::= { h3cBgpEvpnNbrPrefixEntry 8 }

h3cBgpEvpnPAtrMultiExitDisc OBJECT-TYPE
    SYNTAX      Integer32 (-1..2147483647)
    MAX-ACCESS  read-only
    STATUS      current
    DESCRIPTION
        "The MED attribute received in the UPDATE packet.
         When the actual value is range from 2147483647 to
         4294967295,the return value will be 2147483647."
    ::= { h3cBgpEvpnNbrPrefixEntry 9 }

h3cBgpEvpnPAtrLocalPref OBJECT-TYPE
    SYNTAX      Integer32 (-1..2147483647)
    MAX-ACCESS  read-only
    STATUS      current
    DESCRIPTION
        "The local preference attribute received in the UPDATE packet.
         When the actual value is range from 2147483647 to 4294967295,
         the return value will be 2147483647."
    ::= { h3cBgpEvpnNbrPrefixEntry 10 }

h3cBgpEvpnPAtrIGMPFlags OBJECT-TYPE
    SYNTAX      INTEGER { igmpv1(1),
                          igmpv2(2),
                          igmpv3(3)
                        }
    MAX-ACCESS  read-only
    STATUS      current
    DESCRIPTION
        "This attribute indicates support for IGMP version."
    ::= { h3cBgpEvpnNbrPrefixEntry 11 }

h3cBgpEvpnPAtrMaxRespTime OBJECT-TYPE
    SYNTAX      Unsigned32
    UNITS       "ms"
    MAX-ACCESS  read-only
    STATUS      current
    DESCRIPTION
        "The Maximum Response Time is the duration of (x, G)
         leave group synchronization procedure."
    ::= { h3cBgpEvpnNbrPrefixEntry 12 }

h3cBgpEvpnPAtrPMSITunnel OBJECT-TYPE
    SYNTAX      OCTET STRING (SIZE (9..21))
    MAX-ACCESS  read-only
    STATUS      current
    DESCRIPTION
        "This attribute identifies the
         P-tunnel used for sending broadcast."
    ::= { h3cBgpEvpnNbrPrefixEntry 13 }

h3cBgpEvpnPAtrL2VNI OBJECT-TYPE
    SYNTAX      Unsigned32
    MAX-ACCESS  read-only
    STATUS      current
    DESCRIPTION
         "L2 VXLAN ID."
    ::= { h3cBgpEvpnNbrPrefixEntry 14 }

h3cBgpEvpnPAtrL3VNI OBJECT-TYPE
    SYNTAX      Unsigned32
    MAX-ACCESS  read-only
    STATUS      current
    DESCRIPTION
         "L3 VXLAN ID."
    ::= { h3cBgpEvpnNbrPrefixEntry 15 }

h3cBgpEvpnPAtrBest OBJECT-TYPE
    SYNTAX      TruthValue
    MAX-ACCESS  read-only
    STATUS      current
    DESCRIPTION
        "An indication of whether this route
         was chosen as the best BGP4 route for
         this destination."
    ::= { h3cBgpEvpnNbrPrefixEntry 16 }

h3cBgpEvpnPAtrUnknown OBJECT-TYPE
    SYNTAX      OCTET STRING (SIZE(0..255))
    MAX-ACCESS  read-only
    STATUS      current
    DESCRIPTION
        "One or more path attributes not
         understood by this BGP4 speaker."
    ::= { h3cBgpEvpnNbrPrefixEntry 17 }

-- =============================================================================
-- End of h3cBgpEvpnNbrPrefixTable Definition
-- =============================================================================
-- End of H3C-BGP-EVPN-MIB
END

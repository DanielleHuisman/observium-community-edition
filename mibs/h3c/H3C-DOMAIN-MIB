-- ==================================================================
-- Copyright (C) 2004-2017 by H3C Technologies. All rights reserved.
--
-- Description: Domain MIB
-- Reference:
-- Version: V2.1
-- History:
-- V1.0 2005.03.23 The initial version, created by Xulei
-- V1.1 2005.06.03 updated by Xulei
--      Updated the SMIv2 syntax of some MIB objects
-- V1.2 2006.03.27 updated by yuanzhijie
--      1. Modified the description of h3cDomainSchemeRowStatus
--      2. Added h3cDomainSchemeAAAType, h3cDomainSchemeAAAName,
--         and h3cDomainSchemeAccessMode
--      3. Changed the value range for objects h3cDomainAuthSchemeName
--         and h3cDomainAcctSchemeName
-- V1.3 2007.03.07 updated by yangyang
--      Changed the SYNTAX of h3cDomainName and h3cDomainDefault
-- V1.4 2008.11.25 updated by ouzhili
--      Added enumeration value vlanlist(3) to object h3cDomainVlanAssignMode
-- V1.5 2008.12.30 updated by dupengfei
--      Added h3cDomainCurrentAccessNum
-- V1.6 2009.08.05 updated by huxiulan
--      Added enumeration value reserved(12) to object h3cAccessModeofDomainScheme
-- V1.7 2012.05.20 updated by qiuchunxia
--      Added h3cDomainIdleCutTime
--      2012.10.15 updated by liubo
--      Added enumeration value ldap(5) to object h3cDomainSchemeMode
-- V1.8 2013.02.28 updated by xuyonggang
--      Changed h3cDomainSchemeAccessMode
-- V1.9 2013.4.25 updated by qiuchunxia
--      Deleted the range of h3cDomainIdleCutMaxTime
-- V2.0 2013.11.25 updated by zhangdexu
--      Changed the range of h3cDomainDefault and h3cDomainName
-- V2.1 2017.6.3 updated by yuhua
--      Added h3cDomainGlobalStat, h3cDomainStatTable, h3cDomainIPPoolStatTable,
--      h3cDomainServiceType, h3cDomainIpPoolName, and h3cDomainIpv6PoolName
--      2017.10.13 updated by yangliping
--      Changed h3cDomainGlobalStat and h3cDomainStatTable
-- ==================================================================
H3C-DOMAIN-MIB DEFINITIONS ::= BEGIN
    IMPORTS
        h3cCommon
            FROM HUAWEI-3COM-OID-MIB
        Integer32, OBJECT-TYPE, MODULE-IDENTITY, TimeTicks, Unsigned32
            FROM SNMPv2-SMI
        InetAddressType, InetAddress
            FROM INET-ADDRESS-MIB
        RowStatus, TruthValue, TEXTUAL-CONVENTION
            FROM SNMPv2-TC;

    h3cDomain MODULE-IDENTITY
        LAST-UPDATED "201710130000Z"            -- October 13, 2017 at 00:00 GMT
        ORGANIZATION
            "Hangzhou H3C Tech. Co., Ltd."
        CONTACT-INFO
            "Platform Team Hangzhou H3C Tech. Co., Ltd.
            Hai-Dian District Beijing P.R. China
            http://www.h3c.com
            Zip:100085
            "
        DESCRIPTION
            "The MIB module is used for managing domain."

--  Revision history

    REVISION     "201710130000Z"          -- October 13, 2017 at 00:00 GMT
        DESCRIPTION  "Changed h3cDomainGlobalStat and h3cDomainStatTable"

    REVISION     "201706030000Z"          -- June 03, 2017 at 00:00 GMT
        DESCRIPTION  "Added h3cDomainGlobalStat, h3cDomainStatTable, h3cDomainIPPoolStatTable,
                  h3cDomainServiceType, h3cDomainIpPoolName, and h3cDomainIpv6PoolName"

    REVISION     "201311250000Z"          -- November 25, 2013 at 00:00 GMT
        DESCRIPTION  "Changed the range of h3cDomainDefault and h3cDomainName"

    REVISION     "201304250000Z"          -- April 25, 2013 at 00:00 GMT
        DESCRIPTION  "Deleted the range of h3cDomainIdleCutMaxTime"

    REVISION     "201302280000Z"          -- February 28, 2013 at 00:00 GMT
        DESCRIPTION  "Changed h3cDomainSchemeAccessMode"

    REVISION     "201210150000Z"          -- October 15, 2012 at 00:00 GMT
        DESCRIPTION  "Added enumeration value ldap(5) to object h3cDomainSchemeMode"

    REVISION     "201205200000Z"          -- May 20, 2012 at 00:00 GMT
        DESCRIPTION  "Added h3cDomainIdleCutTime"

    REVISION     "200908050000Z"          -- August 5, 2009 at 00:00 GMT
        DESCRIPTION  "Added enumeration value reserved(12) to object h3cAccessModeofDomainScheme"

    REVISION     "200812300000Z"          -- December 30, 2008 at 00:00 GMT
        DESCRIPTION  "Added h3cDomainCurrentAccessNum"

    REVISION     "200811250000Z"          -- November 25, 2008 at 00:00 GMT
        DESCRIPTION  "Added enumeration value vlanlist(3) to object h3cDomainVlanAssignMode"

    REVISION     "200703070000Z"          -- March 7, 2007 at 00:00 GMT
        DESCRIPTION  "Changed the SYNTAX of h3cDomainName and h3cDomainDefault"

    REVISION     "200603270000Z"          -- March 27, 2006 at 00:00 GMT
        DESCRIPTION  "1. Modified the description of h3cDomainSchemeRowStatus
                  2. Added h3cDomainSchemeAAAType, h3cDomainSchemeAAAName,
                     and h3cDomainSchemeAccessMode
                  3. Changed the value range for objects h3cDomainAuthSchemeName
                     and h3cDomainAcctSchemeName"

    REVISION     "200506300000Z"          -- June 30, 2005 at 00:00 GMT
        DESCRIPTION  "Updated the SMIv2 syntax of some MIB objects"

    REVISION     "200503230000Z"          -- March 23, 2005 at 00:00 GMT
        DESCRIPTION  "The initial version, created"

    ::= { h3cCommon 46 }

    H3cModeOfDomainScheme ::= TEXTUAL-CONVENTION
        STATUS current
        DESCRIPTION
        "The scheme mode of the domain.
        none: indicates the domain has no scheme.
        local:indicates the domain will use local-server as a scheme.
        radius:indicates the domain will use radius scheme.
        tacacs:indicates the domain will use tacacs scheme.
        ldap:indicates the domain will use ldap scheme."
        SYNTAX INTEGER
        {
            none(1),
            local(2),
            radius(3),
            tacacs(4),
            ldap(5)
        }

    H3cAAATypeDomainScheme ::= TEXTUAL-CONVENTION
        STATUS current
        DESCRIPTION
        "The service type of the server."
        SYNTAX INTEGER
        {
            accounting(1),
            authentication(2),
            authorization(3),
            none(4)
        }

  H3cAccessModeofDomainScheme ::= TEXTUAL-CONVENTION
        STATUS current
        DESCRIPTION
        "The access mode of the domain."
        SYNTAX INTEGER
        {
            default(1),
            login(2),
            lanAccess(3),
            portal(4),
            ppp(5),
            gcm(6),
            dvpn(7),
            dhcp(8),
            voice(9),
            superauthen(10),
            command(11),
            reserved(12)
        }

    h3cDomainControl OBJECT IDENTIFIER ::= { h3cDomain 1 }

    h3cDomainDefault OBJECT-TYPE
        SYNTAX      OCTET STRING (SIZE (1..255))
        MAX-ACCESS  read-write
        STATUS      current
        DESCRIPTION
        "Specifies default domain on the equipment.  Default value is 'system'."
    ::=  { h3cDomainControl 1 }


    h3cDomainTables OBJECT IDENTIFIER ::= { h3cDomain 2 }

    h3cDomainInfoTable OBJECT-TYPE
        SYNTAX  SEQUENCE OF H3cDomainInfoEntry
        MAX-ACCESS  not-accessible
        STATUS  current
        DESCRIPTION
        "The (conceptual) table listing the domains."
    ::= { h3cDomainTables 1 }

    h3cDomainInfoEntry OBJECT-TYPE
        SYNTAX  H3cDomainInfoEntry
        MAX-ACCESS  not-accessible
        STATUS  current
        DESCRIPTION
        "An entry (conceptual row) representing a domain."
        INDEX { h3cDomainName }
    ::= { h3cDomainInfoTable 1 }

    H3cDomainInfoEntry ::= SEQUENCE {
        h3cDomainName                   OCTET STRING,
        h3cDomainState                  INTEGER,
        h3cDomainMaxAccessNum           Integer32,
        h3cDomainVlanAssignMode         INTEGER,
        h3cDomainIdleCutEnable          TruthValue,
        h3cDomainIdleCutMaxTime         Integer32,
        h3cDomainIdleCutMinFlow         Integer32,
        h3cDomainMessengerEnable        TruthValue,
        h3cDomainMessengerLimitTime     Integer32,
        h3cDomainMessengerSpanTime      Integer32,
        h3cDomainSelfServiceEnable      TruthValue,
        h3cDomainSelfServiceURL         OCTET STRING,
        h3cDomainAccFailureAction       INTEGER,
        h3cDomainRowStatus              RowStatus,
        h3cDomainCurrentAccessNum       Integer32,
        h3cDomainIdleCutTime            TimeTicks,
        h3cDomainServiceType            INTEGER,
        h3cDomainIpPoolName             OCTET STRING,
        h3cDomainIpv6PoolName           OCTET STRING }

    h3cDomainName   OBJECT-TYPE
        SYNTAX  OCTET STRING (SIZE (1..255))
        MAX-ACCESS  not-accessible
        STATUS  current
        DESCRIPTION
        "An index uniquely identifies a domain. "
    ::= { h3cDomainInfoEntry  1 }

    h3cDomainState   OBJECT-TYPE
        SYNTAX INTEGER
        {
            active(1),
            block(2)
        }
        MAX-ACCESS  read-create
        STATUS  current
        DESCRIPTION
        "The state of the domain, which reflects whether the domain is active.
        Default value is active."
    ::= { h3cDomainInfoEntry  2 }

    h3cDomainMaxAccessNum   OBJECT-TYPE
        SYNTAX Integer32
        MAX-ACCESS  read-create
        STATUS  current
        DESCRIPTION
        "The maximum number which the domain allows to access.  If the value
        is set to 0, the access limit will be disabled."
    ::= { h3cDomainInfoEntry  3 }

    h3cDomainVlanAssignMode   OBJECT-TYPE
        SYNTAX INTEGER
        {
            integer(1),
            string(2),
            vlanlist(3)
        }
        MAX-ACCESS  read-create
        STATUS  current
        DESCRIPTION
        "The vlan assignment mode.  The mode SHOULD be the same as the mode of
        corresponding server.
        1 (integer) - Integer Vlan assignment mode.
        2 (string)  - String Vlan assignment mode.
        3 (vlanlist)  - VLAN-List Vlan assignment mode.
        The default value is integer."
    ::= { h3cDomainInfoEntry  4 }

    h3cDomainIdleCutEnable   OBJECT-TYPE
        SYNTAX TruthValue
        MAX-ACCESS  read-create
        STATUS  current
        DESCRIPTION
        "The idle cut control.  Setting this attribute to true, the connection will be
        cut when the flow is less than h3cDomainIdleCutMinFlow and lasts
        h3cDomainIdleCutMaxTime. Default value is false."
    ::= { h3cDomainInfoEntry  5 }

    h3cDomainIdleCutMaxTime   OBJECT-TYPE
        SYNTAX Integer32
        MAX-ACCESS  read-create
        STATUS  current
        DESCRIPTION
        "The maximal time of idle-cut.  The unit is minute.  If the value of
        h3cDomainIdleCutEnable is false, the value of h3cDomainIdleCutMaxTime
        is meaningless."
    ::= { h3cDomainInfoEntry  6 }

    h3cDomainIdleCutMinFlow   OBJECT-TYPE
        SYNTAX Integer32(1..10240000)
        MAX-ACCESS  read-create
        STATUS  current
        DESCRIPTION
        "The minimal flow of idle-cut.  The unit is byte. If the value of
        h3cDomainIdleCutEnable is false, the value of h3cDomainIdleCutMinFlow
        is meaningless."
    ::= { h3cDomainInfoEntry  7 }

    h3cDomainMessengerEnable   OBJECT-TYPE
        SYNTAX TruthValue
        MAX-ACCESS  read-create
        STATUS  current
        DESCRIPTION
        "The messenger service control.  If set h3cDomainMessengerEnable to true,
        h3cDomainMessengerLimitTime and h3cDomainMessengerSpanTime must be
        set to valid values.  Default value is false."
    ::= { h3cDomainInfoEntry  8 }

    h3cDomainMessengerLimitTime   OBJECT-TYPE
        SYNTAX Integer32(1..60)
        MAX-ACCESS  read-create
        STATUS  current
        DESCRIPTION
        "The messenger service limit time.  The unit is minute.  If the value of
        h3cDomainMessengerEnable is false, the value of h3cDomainMessengerLimitTime
        is meaningless."
    ::= { h3cDomainInfoEntry  9 }

    h3cDomainMessengerSpanTime   OBJECT-TYPE
        SYNTAX Integer32(5..60)
        MAX-ACCESS  read-create
        STATUS  current
        DESCRIPTION
        "The messenger service span time.  The unit is minute.
        It must be a multiple of 5.  If the value of h3cDomainMessengerEnable is false,
        the value of h3cDomainMessengerSpanTime is meaningless."
    ::= { h3cDomainInfoEntry  10 }

    h3cDomainSelfServiceEnable   OBJECT-TYPE
        SYNTAX TruthValue
        MAX-ACCESS  read-create
        STATUS  current
        DESCRIPTION
        "The self service control.  If set h3cDomainSelfServiceEnable to true,
        h3cDomainSelfServiceURL must be set to a valid value.
        Default value is FALSE."
    ::= { h3cDomainInfoEntry  11 }

    h3cDomainSelfServiceURL   OBJECT-TYPE
        SYNTAX OCTET STRING (SIZE (1..64))
        MAX-ACCESS  read-create
        STATUS  current
        DESCRIPTION
        "Self-service URL(Uniform Resource Locator) of the domain."
    ::= { h3cDomainInfoEntry  12 }

    h3cDomainAccFailureAction   OBJECT-TYPE
        SYNTAX INTEGER
        {
            ignore(1),
            reject(2)
        }
        MAX-ACCESS  read-create
        STATUS  current
        DESCRIPTION
        "Defines the action that authentication should be taken if
        authentication succeeds but the associated accounting start
        fails.
        1 (ignore) - treat as authentication success; ignore
            accounting start failure.
        2 (reject) - treat as authentication failed if
            corresponding accounting start fails.
        Default value is reject."
    ::= { h3cDomainInfoEntry  13 }

    h3cDomainRowStatus   OBJECT-TYPE
        SYNTAX   RowStatus
        MAX-ACCESS  read-create
        STATUS   current
        DESCRIPTION
        "This object is responsible for managing the creation, deletion and modification
        of rows, which supports active status and CreateAndGo, Destroy operation. To destroy
        an existent row, the domain of the row MUST NOT be used by user."
    ::= { h3cDomainInfoEntry 14 }

    h3cDomainCurrentAccessNum   OBJECT-TYPE
        SYNTAX   Integer32
        MAX-ACCESS  read-only
        STATUS   current
        DESCRIPTION
        "The current access number of the domain."
    ::= { h3cDomainInfoEntry 15 }

    h3cDomainIdleCutTime   OBJECT-TYPE
        SYNTAX TimeTicks
        MAX-ACCESS  read-only
        STATUS  current
        DESCRIPTION
        "Authentication aging time.  If no packet is transmitted during the aging time,
        the authentication is aged out."
    ::= { h3cDomainInfoEntry  16 }

    h3cDomainServiceType   OBJECT-TYPE
        SYNTAX INTEGER
        {
            hsi(1),
            stb(2),
            voip(3)
        }
        MAX-ACCESS  read-create
        STATUS  current
        DESCRIPTION
        "Service type of users in the domain, including hsi(1), stb(2), and voip(3).
         The default value is hsi.

         The High Speed Internet (hsi) service is applicable to users that access the
         network through PPP, 802.1X, or IPoE. If this service is used, the multicast feature of
         the access module is disabled to save system resources.

         The Set Top Box (stb) service is applicable to users that access the network
         through stb. If this service is used, the multicast feature of the access module
         is enabled to improve the performance of the multicast module.

         The Voice over IP (voip) service is applicable to users that access the network
         through IP phones. If this service is used, the Quality of Service (QoS) module
         increases the priority of voice traffic to reduce the transmission delay for
         IP phone users.

        Default value is hsi."
    ::= { h3cDomainInfoEntry  17 }

    h3cDomainIpPoolName   OBJECT-TYPE
        SYNTAX OCTET STRING (SIZE (0..63))
        MAX-ACCESS  read-create
        STATUS  current
        DESCRIPTION
        "Specifies an IPv4 address pool for users in the domain."
    ::= { h3cDomainInfoEntry  18 }

    h3cDomainIpv6PoolName   OBJECT-TYPE
        SYNTAX OCTET STRING (SIZE (0..63))
        MAX-ACCESS  read-create
        STATUS  current
        DESCRIPTION
        "Specifies an IPv6 address pool for users in the domain."
    ::= { h3cDomainInfoEntry  19 }

    -- ----------------------------------------------------------------------
    -- Scheme Table
    -- ----------------------------------------------------------------------
    h3cDomainSchemeTable OBJECT-TYPE
        SYNTAX  SEQUENCE OF H3cDomainSchemeEntry
        MAX-ACCESS  not-accessible
        STATUS  current
        DESCRIPTION
        "The (conceptual) table listing schemes of all domains."
    ::= { h3cDomainTables 2 }

    h3cDomainSchemeEntry OBJECT-TYPE
        SYNTAX  H3cDomainSchemeEntry
        MAX-ACCESS  not-accessible
        STATUS  current
        DESCRIPTION
        "An entry (conceptual row) representing an IP pool of a domain"
        INDEX { h3cDomainName, h3cDomainSchemeIndex }
    ::= { h3cDomainSchemeTable 1 }

    H3cDomainSchemeEntry ::= SEQUENCE {
        h3cDomainSchemeIndex            Integer32,
        h3cDomainSchemeMode             H3cModeOfDomainScheme,
        h3cDomainAuthSchemeName         OCTET STRING,
        h3cDomainAcctSchemeName         OCTET STRING,
        h3cDomainSchemeRowStatus        RowStatus,
        h3cDomainSchemeAAAType          H3cAAATypeDomainScheme,
        h3cDomainSchemeAAAName          OCTET STRING,
        h3cDomainSchemeAccessMode       H3cAccessModeofDomainScheme
        }

    h3cDomainSchemeIndex   OBJECT-TYPE
        SYNTAX Integer32
        MAX-ACCESS  not-accessible
        STATUS  current
        DESCRIPTION
        "The scheme index of domain, which is an identifier of a domain scheme."
    ::= { h3cDomainSchemeEntry  1 }

    h3cDomainSchemeMode   OBJECT-TYPE
        SYNTAX H3cModeOfDomainScheme
        MAX-ACCESS  read-create
        STATUS  current
        DESCRIPTION
        "The scheme mode of the domain.  Setting h3cDomainSchemeMode to none(1) indicates
        the domain has none scheme.  Setting h3cDomainSchemeMode to local(2) indicates the
        domain will use local-server as a scheme.  Setting h3cDomainSchemeMode to radius(3),
        tacacs(4) or ldap(5) indicates the domain will use radius, tacacs or ldap scheme.  If set
        h3cDomainSchemeMode to radius(3), tacacs(4) or ldap(5), h3cDomainAuthSchemeName and
        h3cDomainAcctSchemeName must be set to valid values.  And if h3cDomainSchemeMode is
        set to none(1) or local(2), the value of h3cDomainAuthSchemeName and h3cDomainAcctSchemeName
        will be ignored."
    ::= { h3cDomainSchemeEntry  2 }

    h3cDomainAuthSchemeName   OBJECT-TYPE
        SYNTAX OCTET STRING (SIZE (0..32))
        MAX-ACCESS  read-create
        STATUS  current
        DESCRIPTION
        "The authentication scheme name of domain.  If h3cDomainSchemeMode is set to radius,
        tacacs or ldap, the h3cDomainAuthSchemeName must be configured with a valid value."
    ::= { h3cDomainSchemeEntry  3 }

    h3cDomainAcctSchemeName   OBJECT-TYPE
        SYNTAX OCTET STRING (SIZE (0..32))
        MAX-ACCESS  read-create
        STATUS  current
        DESCRIPTION
        "The accounting scheme name of the domain. If h3cDomainSchemeMode is set to radius
        or tacacs, the h3cDomainAcctSchemeName must be configured with a valid value."
    ::= { h3cDomainSchemeEntry  4 }

    h3cDomainSchemeRowStatus   OBJECT-TYPE
        SYNTAX RowStatus
        MAX-ACCESS  read-create
        STATUS  current
        DESCRIPTION
        "This object is responsible for managing the creation, deletion and modification
        of rows, which supports active status and createAndGo, destroy operation. To
        create a new row, h3cDomainSchemeMode must be specified. To destroy an existent
        row, the scheme of the row MUST NOT be used by user."
    ::= { h3cDomainSchemeEntry  5 }

    h3cDomainSchemeAAAType    OBJECT-TYPE
        SYNTAX     H3cAAATypeDomainScheme
        MAX-ACCESS  read-create
        STATUS  current
        DESCRIPTION
        "Service Type of the server."
   ::= { h3cDomainSchemeEntry  6 }

    h3cDomainSchemeAAAName       OBJECT-TYPE
         SYNTAX      OCTET STRING(SIZE (0..32))
         MAX-ACCESS  read-create
         STATUS  current
         DESCRIPTION
         "The scheme name of the domain, whether the scheme represents accounting,
          authentication or authorization references the object h3cDomainSchemeAAAType.
          The value of the object must be valid if the value of h3cDomainSchemeMode
          is radius or tacacs, the value of the object will be ignored if the value
          of h3cDomainSchemeMode is none or local. If the domain has no scheme,
          there will be a null string. If this object is supported, the objects
          h3cDomainAuthSchemeName and h3cDomainAcctSchemeName will be ignored."
    ::= { h3cDomainSchemeEntry  7 }

    h3cDomainSchemeAccessMode    OBJECT-TYPE
         SYNTAX      H3cAccessModeofDomainScheme
         MAX-ACCESS  read-create
         STATUS  current
         DESCRIPTION
         "The access mode of the domain scheme."
    ::= { h3cDomainSchemeEntry  8 }

    -- ----------------------------------------------------------------------
    -- IP pool Table
    -- ----------------------------------------------------------------------
    h3cDomainIpPoolTable OBJECT-TYPE
        SYNTAX  SEQUENCE OF H3cDomainIpPoolEntry
        MAX-ACCESS  not-accessible
        STATUS  current
        DESCRIPTION
        "The (conceptual) table listing IP pools of all domains."
    ::= { h3cDomainTables 3 }

    h3cDomainIpPoolEntry OBJECT-TYPE
        SYNTAX  H3cDomainIpPoolEntry
        MAX-ACCESS  not-accessible
        STATUS  current
        DESCRIPTION
        "An entry (conceptual row) representing an IP pool of a domain."
        INDEX { h3cDomainName, h3cDomainIpPoolNum }
    ::= { h3cDomainIpPoolTable 1 }

    H3cDomainIpPoolEntry ::= SEQUENCE {
        h3cDomainIpPoolNum              Integer32,
        h3cDomainIpPoolLowIpAddrType    InetAddressType,
        h3cDomainIpPoolLowIpAddr        InetAddress,
        h3cDomainIpPoolLen              Integer32,
        h3cDomainIpPoolRowStatus        RowStatus }


    h3cDomainIpPoolNum   OBJECT-TYPE
        SYNTAX   Integer32(0..99)
        MAX-ACCESS  not-accessible
        STATUS   current
        DESCRIPTION
        "The number of IP pool, which is an identifier of an IP pool."
    ::= { h3cDomainIpPoolEntry 1 }


    h3cDomainIpPoolLowIpAddrType   OBJECT-TYPE
        SYNTAX   InetAddressType
        MAX-ACCESS  read-create
        STATUS   current
        DESCRIPTION
        "The low IP addresses type (IPv4 or IPv6) of IP pool."
    ::= { h3cDomainIpPoolEntry 2 }


    h3cDomainIpPoolLowIpAddr   OBJECT-TYPE
        SYNTAX   InetAddress
        MAX-ACCESS  read-create
        STATUS   current
        DESCRIPTION
        "The low IP address of IP pool."
    ::= { h3cDomainIpPoolEntry 3 }


    h3cDomainIpPoolLen   OBJECT-TYPE
        SYNTAX   Integer32
        MAX-ACCESS  read-create
        STATUS   current
        DESCRIPTION
        "The length of IP pool.  Default value is 1."
    ::= { h3cDomainIpPoolEntry 4 }

   h3cDomainIpPoolRowStatus   OBJECT-TYPE
        SYNTAX   RowStatus
        MAX-ACCESS  read-create
        STATUS   current
        DESCRIPTION
        "This object is responsible for managing the creation, deletion and modification
        of rows, which supports active status and CreateAndGo, Destroy operation.  To
        create a new row, h3cDomainIpPoolNum and h3cDomainIpPoolLowIpAddr must be specified.
        To destroy an existent row, the IP pool of this row MUST NOT be used by user."
    ::= { h3cDomainIpPoolEntry 5 }

    -- ----------------------------------------------------------------------
    -- Domain Statistics Table
    -- ----------------------------------------------------------------------
    h3cDomainStatTable OBJECT-TYPE
        SYNTAX  SEQUENCE OF H3cDomainStatEntry
        MAX-ACCESS  not-accessible
        STATUS  current
        DESCRIPTION
        "The (conceptual) table listing Domain statistics."
    ::= { h3cDomainTables 4 }

    h3cDomainStatEntry OBJECT-TYPE
        SYNTAX  H3cDomainStatEntry
        MAX-ACCESS  not-accessible
        STATUS  current
        DESCRIPTION
        "An entry (conceptual row) representing statistics of a domain."
        INDEX { h3cDomainName }
    ::= { h3cDomainStatTable 1 }

    H3cDomainStatEntry ::= SEQUENCE {
        h3cDomainAccessedNum          Unsigned32,
        h3cDomainOnlineNum            Unsigned32,
        h3cDomainOnlinePPPUser        Unsigned32,
        h3cDomainOnlineIPoEUser       Unsigned32,
        h3cDomainOnlinePPPoEUser      Unsigned32,
        h3cDomainOnlinePPPoAUser      Unsigned32,
        h3cDomainOnlinePPPoFRUser     Unsigned32,
        h3cDomainOnlineLacUser        Unsigned32,
        h3cDomainOnlineLnsUser        Unsigned32,
        h3cDomainOnlineIPoEBindAuthUser   Unsigned32,
        h3cDomainOnlineIPoEWebAuthUser    Unsigned32,
        h3cDomainOnlineLeasedUser     Unsigned32}

    h3cDomainAccessedNum   OBJECT-TYPE
        SYNTAX   Unsigned32
        MAX-ACCESS  read-only
        STATUS   current
        DESCRIPTION
        "Total number of users in the domain."
    ::= { h3cDomainStatEntry 1 }


    h3cDomainOnlineNum   OBJECT-TYPE
        SYNTAX   Unsigned32
        MAX-ACCESS  read-only
        STATUS   current
        DESCRIPTION
        "Number of online users in the domain."
    ::= { h3cDomainStatEntry 2 }


    h3cDomainOnlinePPPUser   OBJECT-TYPE
        SYNTAX   Unsigned32
        MAX-ACCESS  read-only
        STATUS   current
        DESCRIPTION
        "Number of online PPP users in the domain."
    ::= { h3cDomainStatEntry 3 }

    h3cDomainOnlineIPoEUser   OBJECT-TYPE
        SYNTAX   Unsigned32
        MAX-ACCESS  read-only
        STATUS   current
        DESCRIPTION
        "Number of online IPoE users in the domain."
    ::= { h3cDomainStatEntry 4 }

    h3cDomainOnlinePPPoEUser   OBJECT-TYPE
        SYNTAX   Unsigned32
        MAX-ACCESS  read-only
        STATUS   current
        DESCRIPTION
        "Number of online PPPoE users in the domain."
    ::= { h3cDomainStatEntry 5 }

    h3cDomainOnlinePPPoAUser   OBJECT-TYPE
        SYNTAX   Unsigned32
        MAX-ACCESS  read-only
        STATUS   current
        DESCRIPTION
        "Number of online PPPoA users in the domain."
    ::= { h3cDomainStatEntry 6 }

    h3cDomainOnlinePPPoFRUser   OBJECT-TYPE
        SYNTAX   Unsigned32
        MAX-ACCESS  read-only
        STATUS   current
        DESCRIPTION
        "Number of online PPPoFR users in the domain."
    ::= { h3cDomainStatEntry 7 }

    h3cDomainOnlineLacUser   OBJECT-TYPE
        SYNTAX   Unsigned32
        MAX-ACCESS  read-only
        STATUS   current
        DESCRIPTION
        "Number of online LAC users in the domain."
    ::= { h3cDomainStatEntry 8 }

    h3cDomainOnlineLnsUser   OBJECT-TYPE
        SYNTAX   Unsigned32
        MAX-ACCESS  read-only
        STATUS   current
        DESCRIPTION
        "Number of online LNS users in the domain."
    ::= { h3cDomainStatEntry 9 }

    h3cDomainOnlineIPoEBindAuthUser   OBJECT-TYPE
        SYNTAX   Unsigned32
        MAX-ACCESS  read-only
        STATUS   current
        DESCRIPTION
        "Number of online IPoE users that use bind authentication in the domain."
    ::= { h3cDomainStatEntry 10 }

    h3cDomainOnlineIPoEWebAuthUser   OBJECT-TYPE
        SYNTAX   Unsigned32
        MAX-ACCESS  read-only
        STATUS   current
        DESCRIPTION
        "Number of online IPoE users that use WEB authentication in the domain."
    ::= { h3cDomainStatEntry 11 }

    h3cDomainOnlineLeasedUser   OBJECT-TYPE
        SYNTAX   Unsigned32
        MAX-ACCESS  read-only
        STATUS   current
        DESCRIPTION
        "Number of online IPoE Leased users in the domain."
    ::= { h3cDomainStatEntry 12 }

    -- ----------------------------------------------------------------------
    -- Domain IP Pool Statistics Table
    -- ----------------------------------------------------------------------
    h3cDomainIPPoolStatTable OBJECT-TYPE
        SYNTAX  SEQUENCE OF H3cDomainIPPoolStatEntry
        MAX-ACCESS  not-accessible
        STATUS  current
        DESCRIPTION
        "The (conceptual) table listing IP pool statistics."
    ::= { h3cDomainTables 5 }

    h3cDomainIPPoolStatEntry OBJECT-TYPE
        SYNTAX  H3cDomainIPPoolStatEntry
        MAX-ACCESS  not-accessible
        STATUS  current
        DESCRIPTION
        "An entry (conceptual row) representing statistics of an IP pool."
        INDEX { h3cDomainName }
    ::= { h3cDomainIPPoolStatTable 1 }

    H3cDomainIPPoolStatEntry ::= SEQUENCE {
        h3cDomainIPTotalNum      Unsigned32,
        h3cDomainIPUsedNum       Unsigned32,
        h3cDomainIPConflictNum   Unsigned32,
        h3cDomainIPExcludeNum    Unsigned32,
        h3cDomainIPIdleNum       Unsigned32,
        h3cDomainIPUsedPercent   OCTET STRING }


    h3cDomainIPTotalNum   OBJECT-TYPE
        SYNTAX   Unsigned32
        MAX-ACCESS  read-only
        STATUS  current
        DESCRIPTION
        "Total number of addresses in the IP pool."
    ::= { h3cDomainIPPoolStatEntry 1 }


    h3cDomainIPUsedNum    OBJECT-TYPE
        SYNTAX   Unsigned32
        MAX-ACCESS  read-only
        STATUS  current
        DESCRIPTION
        "Number of addresses already used in the IP pool."
    ::= { h3cDomainIPPoolStatEntry 2 }


    h3cDomainIPConflictNum   OBJECT-TYPE
        SYNTAX   Unsigned32
        MAX-ACCESS  read-only
        STATUS  current
        DESCRIPTION
        "Number of conflicting addresses in the IP pool."
    ::= { h3cDomainIPPoolStatEntry 3 }


    h3cDomainIPExcludeNum   OBJECT-TYPE
        SYNTAX   Unsigned32
        MAX-ACCESS  read-only
        STATUS   current
        DESCRIPTION
        "Number of addresses excluded from the IP pool."
    ::= { h3cDomainIPPoolStatEntry 4 }

   h3cDomainIPIdleNum   OBJECT-TYPE
        SYNTAX   Unsigned32
        MAX-ACCESS  read-only
        STATUS  current
        DESCRIPTION
        "Number of idle addresses in the IP pool."
    ::= { h3cDomainIPPoolStatEntry 5 }

    h3cDomainIPUsedPercent   OBJECT-TYPE
        SYNTAX OCTET STRING (SIZE (0..32))
        MAX-ACCESS  read-only
        STATUS   current
        DESCRIPTION
        "Address occupancy rate in the IP pool."
    ::= { h3cDomainIPPoolStatEntry 6 }

    -- ----------------------------------------------------------------------
    -- Domain Global Statistics Table
    -- ----------------------------------------------------------------------
    h3cDomainGlobalStat OBJECT IDENTIFIER ::= { h3cDomain 3 }

    h3cDomainGlobalAccessedNum  OBJECT-TYPE
        SYNTAX   Unsigned32
        MAX-ACCESS  read-only
        STATUS   current
        DESCRIPTION
        "Number of users in all domains."
    ::=  { h3cDomainGlobalStat 1 }

    h3cDomainGlobalOnlineNum  OBJECT-TYPE
        SYNTAX   Unsigned32
        MAX-ACCESS  read-only
        STATUS   current
        DESCRIPTION
        "Number of online users in all domains."
    ::=  { h3cDomainGlobalStat 2 }

    h3cDomainGlobalOnlinePPPUser  OBJECT-TYPE
        SYNTAX   Unsigned32
        MAX-ACCESS  read-only
        STATUS   current
        DESCRIPTION
        "Number of online PPP users in all domains."
    ::=  { h3cDomainGlobalStat 3 }

    h3cDomainGlobalOnlineIPoEUser  OBJECT-TYPE
        SYNTAX   Unsigned32
        MAX-ACCESS  read-only
        STATUS   current
        DESCRIPTION
        "Number of online IPoE users in all domains."
    ::=  { h3cDomainGlobalStat 4 }

    h3cDomainGlobalOnlinePPPoEUser  OBJECT-TYPE
        SYNTAX   Unsigned32
        MAX-ACCESS  read-only
        STATUS   current
        DESCRIPTION
        "Number of online PPPoE users in all domains."
    ::=  { h3cDomainGlobalStat 5 }

    h3cDomainGlobalOnlinePPPoAUser  OBJECT-TYPE
        SYNTAX   Unsigned32
        MAX-ACCESS  read-only
        STATUS   current
        DESCRIPTION
        "Number of online PPPoA users in all domains."
    ::=  { h3cDomainGlobalStat 6 }

    h3cDomainGlobalOnlinePPPoFRUser  OBJECT-TYPE
        SYNTAX   Unsigned32
        MAX-ACCESS  read-only
        STATUS   current
        DESCRIPTION
        "Number of online PPPoFR users in all domains."
    ::=  { h3cDomainGlobalStat 7 }

    h3cDomainGlobalOnlineLacUser  OBJECT-TYPE
        SYNTAX   Unsigned32
        MAX-ACCESS  read-only
        STATUS   current
        DESCRIPTION
        "Number of online LAC users in all domains."
    ::=  { h3cDomainGlobalStat 8 }

    h3cDomainGlobalOnlineLnsUser  OBJECT-TYPE
        SYNTAX   Unsigned32
        MAX-ACCESS  read-only
        STATUS   current
        DESCRIPTION
        "Number of online LNS users in all domains."
    ::=  { h3cDomainGlobalStat 9 }

    h3cDomainGlobalOnlineIPoEBindAuthUser  OBJECT-TYPE
        SYNTAX   Unsigned32
        MAX-ACCESS  read-only
        STATUS   current
        DESCRIPTION
        "Number of online IPoE users that use bind authentication in all domains."
    ::=  { h3cDomainGlobalStat 10 }

    h3cDomainGlobalOnlineIPoEWebAuthUser  OBJECT-TYPE
        SYNTAX   Unsigned32
        MAX-ACCESS  read-only
        STATUS   current
        DESCRIPTION
        "Number of online IPoE users that use WEB authentication in all domains."
    ::=  { h3cDomainGlobalStat 11 }

    h3cDomainGlobalOnlineLeasedUser  OBJECT-TYPE
        SYNTAX   Unsigned32
        MAX-ACCESS  read-only
        STATUS   current
        DESCRIPTION
        "Number of online IPoE Leased users in all domains."
    ::=  { h3cDomainGlobalStat 12 }
END

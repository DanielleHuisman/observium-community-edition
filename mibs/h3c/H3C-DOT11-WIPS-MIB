-- =============================================================================
-- Copyright (c) 2004-2016 Hangzhou H3C Tech. Co., Ltd.  All rights reserved.
--
-- Description:
--   The file defines a MIB to provide wireless intrusion prevention service
--   feature.
-- Reference:
-- Version: V1.1
-- History:
--   V1.0 created by sunanzhi
--     Initial version 2015-03-20
--        2015-12-08 updated by sunanzhi
--     Modify the node name of H3cDot11WIPSVsdEntry,H3cDot11WIPSAp2VsdEntry,
--     H3cDot11WIPSApRadioEntry,H3cDot11WIPSDctAPEntry,
--     H3cDot11WIPSDctStaEntry
--     Add new objects H3cDot11WIPSRuleEntry,H3cDot11WIPSAlySigRuleEntry,
--     H3cDot11WIPSAlyClaRuleEntry,H3cDot11WIPSTrustMacEntry,
--     H3cDot11WIPSBlockMacEntry,H3cDot11WIPSManulClaEntry,
--     H3cDot11WIPSTrustOuiEntry,H3cDot11WIPSTrustSSidEntry,
--     H3cDot11WIPSMalfDtcEntry,H3cDot11WIPSLgeDutEntry,
--     H3cDot11WIPSRtLmtEntry,H3cDot11WIPSDtcAckEntry,
--     H3cDot11WIPSDtcDevTimeEntry,H3cDot11WIPSApimperEntry,
--     H3cDot11WIPSDctSoftApEntry,H3cDot11WIPSPowerSaveEntry,
--     H3cDot11WIPSIgnListMacEntry,H3cDot11WIPSHoneyPotEntry,
--     H3cDot11WIPSAPFldEntry,H3cDot11WIPSCtmManualsEntry,
--     H3cDot11WIPSCtmSensorEntry,H3cDot11WIPSInvOuiStateEntry,
--     H3cDot11WIPSAPClaAuthEntry,H3cDot11WIPSAPClaCltOnlEntry,
--     H3cDot11WIPSAPClaDiscrEntry,H3cDot11WIPSAPClaRssiEntry,
--     H3cDot11WIPSAPClaUpdurEntry,H3cDot11WIPSAPClaOuiEntry,
--     H3cDot11WIPSAPClaSryEntry,H3cDot11WIPSAPClaSsidEntry,
--     H3cDot11WIPSDtcSigEntry,H3cDot11WIPSPolicyEntry,
--     H3cDot11WIPSSigFrameTypeEntry,H3cDot11WIPSCtmEntry,
--     H3cDot11WIPSSigPatternEntry,H3cDot11WIPSSigSeqNumEntry,
--     H3cDot11WIPSSigSsidEntry,H3cDot11WIPSSigSsidLengthEntry,
--     H3cDot11WIPSFldDetectEntry,H3cDot11WIPSSignatureMacEntry,
--     H3cDot11WIPSRadioCfgEntry,H3cDot11WIPSNatDetectEntry,
--     H3cDot11WIPSApAssoCltEntry,H3cDot11WIPSApRpSenEntry,
--     H3cDot11WIPSCtmRecEntry,H3cDot11WIPSDevEntry,H3cDot11WIPSCtmDevEntry,
--     H3cDot11WIPSCltProbeEntry,H3cDot11WIPSPbeStaEntry,
--     H3cDot11WIPSCltRptApEntry,H3cDot11WIPSNatDtcCltEntry,
--     H3cDot11WIPSAckStaEntry
--   V1.1 2016-02-17 updated by sunanzhi
--     Modify the objects H3cDot11WIPSEncryptMethod,H3cDot11WIPSAuthMethod
--     H3cDot11WIPSAPSecurityType,h3cDot11WIPSDctAPSSID
--        2016-03-28 updated by sunanzhi
--     Delete the objects H3cDot11WIPSCltProbeEntry,H3cDot11WIPSPbeStaEntry
--     H3cDot11WIPSRadioCfgEntry
-- =============================================================================
H3C-DOT11-WIPS-MIB DEFINITIONS ::= BEGIN

IMPORTS
    TimeTicks, Integer32, Unsigned32, OBJECT-TYPE, MODULE-IDENTITY
        FROM SNMPv2-SMI
    TruthValue, RowStatus, MacAddress, TEXTUAL-CONVENTION
        FROM SNMPv2-TC
    h3cDot11
        FROM HUAWEI-3COM-OID-MIB;

h3cDot11WIPS MODULE-IDENTITY
    LAST-UPDATED "201603280951Z"        -- March 28, 2016 at 09:51 GMT
    ORGANIZATION
        "Hangzhou H3C Technologies Co., Ltd."
    CONTACT-INFO
        "Platform Team Hangzhou H3C Technologies Co., Ltd.
        Hai-Dian District Beijing P.R. China
        http://www.h3c.com
        Zip:100085
        "
    DESCRIPTION
        "This MIB provides information about the Wireless Intrusion
        Prevention System (WIPS) feature.

        WIPS is designed to protect an area that is serviced by
        a wireless network.
        It aids in early detection of malicious outsider attacks
        and intrusions via wireless networks, and takes countermeasures
        to ensure the wireless environment security.
        "
    REVISION "201603280951Z"        -- March 28, 2016 at 09:51 GMT
    DESCRIPTION
        "Delete table for probe."
    REVISION "201602161051Z"        -- February 16, 2016 at 10:51 GMT
    DESCRIPTION
        "Modify objects."
    REVISION "201512081551Z"        -- December 08, 2015 at 15:51 GMT
    DESCRIPTION
        "Add new objects."
    REVISION "201503311351Z"        -- March 31, 2015 at 13:51 GMT
    DESCRIPTION
        "The initial revision of this MIB module."
    ::= {  h3cDot11 15 }

--
-- Textual conventions
--
H3cDot11WIPSEnabledStatus ::= TEXTUAL-CONVENTION
    STATUS      current
    DESCRIPTION
        "The enable status values for objects.
        Values include enabled and disbaled."
    SYNTAX      INTEGER { enabled(1), disabled(2) }

H3cDot11WIPSRtLmtType ::= TEXTUAL-CONVENTION
    STATUS current
    DESCRIPTION
        "Represents the type of rate limit configuration."
    SYNTAX INTEGER
        {
        ap(1),
        client(4)
        }

H3cDot11WIPSDeviceType ::= TEXTUAL-CONVENTION
    STATUS current
    DESCRIPTION
        "Represents the type of device."
    SYNTAX INTEGER
        {
        ap(1),
        client(2)
        }

H3cDot11WIPSPolicyTypeValue ::= TEXTUAL-CONVENTION
    STATUS current
    DESCRIPTION
        "Represents the type of policy."
    SYNTAX INTEGER
        {
        classification(1),
        countermeasure(2),
        detect(3),
        signature(4)
        }

H3cDot11WIPSClassifyType ::= TEXTUAL-CONVENTION
   STATUS current
   DESCRIPTION
        "Represents the category of the device detected by WIPS."
   SYNTAX INTEGER
       {
       none(1),
       authorizedap(2),
       misconfiguredap(3),
       rogueap(4),
       externalap(5),
       adhoc(6),
       meshap(7),
       potentialauthorizedap(8),
       potentialrogueap(9),
       potentialexternalap(10),
       uncategorizedap(11),
       authorizedclient(12),
       unauthorizedclient(13),
       misassociaionclient(14),
       uncategorizedclient(15)
       }

H3cDot11WIPSRadioType ::= TEXTUAL-CONVENTION
    STATUS current
    DESCRIPTION
        "Represents AP 802.11 radio type of 802.11a/b/g/n as per
        the standard.
        The following values are supported:
        dot11a  - 802.11a
        dot11b  - 802.11b
        dot11g  - 802.11g
        dot11n  - 802.11n
        dot11gn  - 802.11gn
        dot11an  - 802.11an
        dot11ac  - 802.11ac
        dot11gac  - 802.11gac"
    SYNTAX INTEGER
        {
        dot11a(1),
        dot11b(2),
        dot11g(4),
        dot11n(8),
        dot11gn(16),
        dot11an(32),
        dot11ac(64),
        dot11gac(128)
        }

H3cDot11WIPSDevStatus ::= TEXTUAL-CONVENTION
    STATUS current
    DESCRIPTION
        "Represents the status of devices detected by WIPS."
    SYNTAX INTEGER
        {
        active(1),
        inactive(2)
        }

H3cDot11WIPSAPType ::= TEXTUAL-CONVENTION
    STATUS current
    DESCRIPTION
        "Represents the type of AP detected by WIPS."
    SYNTAX INTEGER
        {
        normal(1),
        adhoc(2),
        mesh(3)
        }


H3cDot11WIPSDevClassifyWay ::= TEXTUAL-CONVENTION
    STATUS current
    DESCRIPTION
        "Represents the method that the device is categorized."
    SYNTAX INTEGER
        {
        manual(1),
        invalidOUI(2),
        trustlist(3),
        blocklist(4),
        associated(5),
        userdefined(6),
        auto(7)
        }

H3cDot11WIPSAPClassifyType ::= TEXTUAL-CONVENTION
    STATUS current
    DESCRIPTION
        "Represents the category of the AP detected by WIPS."
    SYNTAX INTEGER
        {
        authorized(1),
        misconfigured(2),
        rogue(3),
        external(4),
        adhoc(5),
        mesh(6),
        potentialAuthorized(7),
        potentialRogue(8),
        potentialExternal(9),
        uncategorized(10)
        }

H3cDot11WIPSStaClassifyType ::= TEXTUAL-CONVENTION
    STATUS current
    DESCRIPTION
        "Represents the category of the client detected by WIPS."
    SYNTAX INTEGER
        {
        authorized(1),
        unauthorized(2),
        misassociated(3),
        uncategorized(4)
        }

H3cDot11WIPSChannel ::= TEXTUAL-CONVENTION
    DISPLAY-HINT "d"
    STATUS current
    DESCRIPTION
        "Represents the channel number."
    SYNTAX Integer32 (1..224)

H3cDot11WIPSEncryptMethod ::= TEXTUAL-CONVENTION
    DISPLAY-HINT "d"
    STATUS current
    DESCRIPTION
        "Represents the frame encryption cipher types(bitmap) for
        frames on IEEE 802.11 radio interfaces.
        The MIB defines TC by referring to the 802.11i protocol.
        The following bits are supported:
        first bit:    none,
        second bit:   wep,
        third bit:    wep40,
        fourth bit:   tkip
        fifth bit:    reserve
        sixth bit:    ccmp
        seventh bit:  wep104
        eighth bit:   wep128"
    SYNTAX Integer32 (1..65535)

H3cDot11WIPSAuthMethod ::= TEXTUAL-CONVENTION
    DISPLAY-HINT "d"
    STATUS current
    DESCRIPTION
        "Represents the key management mode(bitmap), compliant with 802.11i.
        The following bits are supported:
        first bit:   none         - No key management mode is specified,
        second bit:  dot1x        - 802.1X authentication.
        third bit:   psk          - Pre-shared key authentication,
        fourth bit:  other        - Other authentication."
    SYNTAX Integer32 (1..65535)

H3cDot11WIPSAPSecurityType ::= TEXTUAL-CONVENTION
    DISPLAY-HINT "d"
    STATUS current
    DESCRIPTION
        "Represents the AP security type(bitmap).
        The following bits are supported:
        first bit:   none,
        second bit:  wpa2,
        third bit:   wpa,
        fourth bit:  wlanex
        fifth bit:   wep"
    SYNTAX Integer32 (1..255)

H3cDot11WIPSMalformedType ::= TEXTUAL-CONVENTION
    STATUS current
    DESCRIPTION
        "Represents the category of malformed packet."
    SYNTAX INTEGER
        {
        duplicatedie(1),
        fatajack(2),
        illegalibssess(3),
        invalidaddresscombination(4),
        invalidassocreq(5),
        invalidauth(6),
        invaliddeauthcode(7),
        invaliddisassoccode(8),
        invalidhtie(9),
        invalidielength(10),
        invalidpktlength(11),
        nullproberesp(13),
        overfloweapolkey(14),
        overflowssid(15),
        redundantie(16)
        }

H3cDot11WIPSCtmType ::= TEXTUAL-CONVENTION
    STATUS current
    DESCRIPTION
        "Represents the category of countermeasure method."
    SYNTAX INTEGER
        {
        externalAp(1),
        misassociationClient(2),
        misconfiguredAp(3),
        potentialAuthorizedAp(4),
        potentialExternalAp(5),
        potentialRogueAp(6),
        rogueAp(7),
        unauthorizedClient(8),
        uncategorizedAp(9),
        uncategorizedClient(10),
        attack(11),
        adhoc(12)
        }

H3cDot11WIPSRuleTypes ::= TEXTUAL-CONVENTION
    STATUS current
    DESCRIPTION
        "Represents the type of rule"
    SYNTAX INTEGER
        {
        signature(4),
        apclassfication(5)
        }

H3cDot11WIPSSigFrameTypes ::= TEXTUAL-CONVENTION
    STATUS current
    DESCRIPTION
        "Represents the type of signature frame configuration."
    SYNTAX INTEGER
        {
        management(1),
        control(2),
        data(3)
        }

H3cDot11WIPSSigFrameSubTypes ::= TEXTUAL-CONVENTION
    STATUS current
    DESCRIPTION
        "Represents the type of signature manage frame configuration."
    SYNTAX INTEGER
        {
        assocerq(1),
        assocresp(2),
        probereq(3),
        beacon(4),
        disasso(5),
        auth(6),
        deauth(7)
        }

H3cDot11WIPSSigSsidMatchTypes ::= TEXTUAL-CONVENTION
    STATUS current
    DESCRIPTION
        "Represents the match type of signature ssid configuration."
    SYNTAX INTEGER
        {
        equal(1),
        notequal(2),
        include(3),
        notinclude(4)
        }

H3cDot11WIPSSigMacMacType ::= TEXTUAL-CONVENTION
    STATUS current
    DESCRIPTION
        "Represents the mac type of signature ssid configuration."
    SYNTAX INTEGER
        {
        source(1),
        destination(2),
        bssid(3)
        }

H3cDot11WIPSManualAPType ::= TEXTUAL-CONVENTION
    STATUS current
    DESCRIPTION
        "Represents the type of AP manual classification."
    SYNTAX INTEGER
        {
       authap(1),
       misconfiguredap(2),
        rogueap(3),
        externalap(4)
        }

H3cDot11WIPSDtcAckTypes ::= TEXTUAL-CONVENTION
    STATUS current
    DESCRIPTION
        "Represents the type of attack detect."
    SYNTAX INTEGER
        {
        apspoof(1),
        clientspoof(4),
        weakiv(6),
        windowsbridge(7),
        fortymhz(8),
        omerta(11),
        disassoc(12),
        deauth(13),
        prohibitedchannel(14),
        authunencryptedap(16),
        authunencryptedclient(17),
        hotspot(18),
        greenmode(19),
        tableoverflow(20),
        mitm(22),
        wirelessbridge(23),
        apchannelchange(25)
        }

H3cDot11WIPSDtcDevTimeTypes ::= TEXTUAL-CONVENTION
    STATUS current
    DESCRIPTION
        "Represents the type of device time."
    SYNTAX INTEGER
        {
        deviceap(1),
        deviceclient(2)
        }

H3cDot11WIPSFldDctType ::= TEXTUAL-CONVENTION
    STATUS current
    DESCRIPTION
        "Represents the type of flood detect."
    SYNTAX INTEGER
        {
        associationrequest(1),
        authentication(2),
        beacon(3),
        blockack(4),
        cts(5),
        deauthentication(6),
        disassociation(7),
        eapolstart(8),
        nulldata(9),
        proberequest(10),
        reassociationrequest(11),
        rts(12),
        eapollogoff(13),
        eapfailure(14),
        eapsuccess(15)
        }

H3cDot11WIPSAPClaAuthMethods ::= TEXTUAL-CONVENTION
    STATUS current
    DESCRIPTION
        "Represents the type of AP classification method."
    SYNTAX INTEGER
        {
        none(1),
        dot1x(2),
        psk(3),
        other(5)
        }


H3cDot11WIPSAPClassifyCmpType ::= TEXTUAL-CONVENTION
    STATUS current
    DESCRIPTION
        "Represents the compare type of AP classification method.
        The following values are supported:
        equal         - equal.
        include       - include."
    SYNTAX INTEGER
        {
        equal(1),
        include(3)
        }

H3cDot11WIPSAPClasSsidCmpType ::= TEXTUAL-CONVENTION
    STATUS current
    DESCRIPTION
        "Represents the compare type of AP classification ssid.
        The following values are supported:
        equal         - equal.
        not equal     - not equal.
        include       - include.
        not include   - not include."
    SYNTAX INTEGER
        {
        equal(1),
        notequal(2),
        include(3),
        notinclude(4)
        }


H3cDot11WIPSAPClaSecurityType ::= TEXTUAL-CONVENTION
    STATUS current
    DESCRIPTION
        "Represents the type of AP classification security.
        clear   1
        wpa2   2
        wpa    3
        wep    9"
    SYNTAX INTEGER
        {
        clear(1),
        wpa2(2),
        wpa(3),
        wep(9)
        }

H3cDot11WIPSAlyAPClaRuleType ::= TEXTUAL-CONVENTION
    STATUS current
    DESCRIPTION
        "Represents the category of apply AP classification rule."
    SYNTAX INTEGER
        {
        rogue(1),
        external(2),
        misconfigured(3),
        authorized(4)
        }

H3cDot11WIPSOuiAddress ::= TEXTUAL-CONVENTION
    DISPLAY-HINT "1x:"
    STATUS       current
    DESCRIPTION
        "Represents an 802 OUI address represented in the
        `canonical' order defined by IEEE 802.1a, i.e., as if it
        were transmitted least significant bit first, even though
        802.5 (in contrast to other 802.x protocols) requires MAC
        addresses to be transmitted most significant bit first."
    SYNTAX       OCTET STRING (SIZE (3))

--
-- Node definitions
--
h3cDot11WIPSConfigGroup OBJECT IDENTIFIER ::= { h3cDot11WIPS 1 }
h3cDot11WIPSDataGroup OBJECT IDENTIFIER ::= { h3cDot11WIPS 2 }

h3cDot11WIPSVsdTable OBJECT-TYPE
    SYNTAX SEQUENCE OF H3cDot11WIPSVsdEntry
    MAX-ACCESS not-accessible
    STATUS current
    DESCRIPTION
        "The table provides information about virtual security domains (VSDs)."
    ::= { h3cDot11WIPSConfigGroup 1 }

h3cDot11WIPSVsdEntry OBJECT-TYPE
    SYNTAX H3cDot11WIPSVsdEntry
    MAX-ACCESS not-accessible
    STATUS current
    DESCRIPTION
        "Each entry contains information about one VSD."
    INDEX { h3cDot11WIPSVsdName }
    ::= { h3cDot11WIPSVsdTable 1 }

H3cDot11WIPSVsdEntry ::= SEQUENCE {
        h3cDot11WIPSVsdName                      OCTET STRING,
        h3cDot11WIPSVsdRowStatus                 RowStatus,
        h3cDot11WIPSVsdDetectPolicy              OCTET STRING,
        h3cDot11WIPSVsdCtmPolicy                 OCTET STRING,
        h3cDot11WIPSVsdSignaturePolicy           OCTET STRING,
        h3cDot11WIPSVsdClasPolicy                OCTET STRING
     }

h3cDot11WIPSVsdName OBJECT-TYPE
    SYNTAX OCTET STRING (SIZE (1..63))
    MAX-ACCESS not-accessible
    STATUS current
    DESCRIPTION
        "Represents the name of the virtual security domain."
    ::= { h3cDot11WIPSVsdEntry 1 }

h3cDot11WIPSVsdRowStatus OBJECT-TYPE
    SYNTAX RowStatus
    MAX-ACCESS read-create
    STATUS current
    DESCRIPTION
        "The status of this table entry."
    ::= { h3cDot11WIPSVsdEntry 2 }

h3cDot11WIPSVsdDetectPolicy OBJECT-TYPE
    SYNTAX OCTET STRING (SIZE (0..63))
    MAX-ACCESS read-create
    STATUS current
    DESCRIPTION
        "Represents the name of the attack detect policy attached to the VSD,
        zero-length for not config."
    ::= { h3cDot11WIPSVsdEntry 3 }

h3cDot11WIPSVsdCtmPolicy OBJECT-TYPE
    SYNTAX OCTET STRING (SIZE (0..63))
    MAX-ACCESS read-create
    STATUS current
    DESCRIPTION
        "Represents the name of the countermeasure policy attached to the VSD,
        zero-length for not config."
    ::= { h3cDot11WIPSVsdEntry 4 }

h3cDot11WIPSVsdSignaturePolicy OBJECT-TYPE
    SYNTAX OCTET STRING (SIZE (0..63))
    MAX-ACCESS read-create
    STATUS current
    DESCRIPTION
        "Represents the name of the signature policy attached to the VSD,
        zero-length for not config."
    ::= { h3cDot11WIPSVsdEntry 5 }

h3cDot11WIPSVsdClasPolicy OBJECT-TYPE
    SYNTAX OCTET STRING (SIZE (0..63))
    MAX-ACCESS read-create
    STATUS current
    DESCRIPTION
        "Represents the name of the malformed packet detect policy attached
        to the VSD,zero-length for not config."
    ::= { h3cDot11WIPSVsdEntry 6 }

h3cDot11WIPSAp2VsdTable OBJECT-TYPE
    SYNTAX SEQUENCE OF H3cDot11WIPSAp2VsdEntry
    MAX-ACCESS not-accessible
    STATUS current
    DESCRIPTION
        "The table defines sensors attached to VSDs."
    ::= { h3cDot11WIPSConfigGroup 2 }

h3cDot11WIPSAp2VsdEntry OBJECT-TYPE
    SYNTAX H3cDot11WIPSAp2VsdEntry
    MAX-ACCESS not-accessible
    STATUS current
    DESCRIPTION
        "Each entry contains information about a sensor in a VSD."
    INDEX { h3cDot11WIPSAp2VsdApName }
    ::= { h3cDot11WIPSAp2VsdTable 1 }

H3cDot11WIPSAp2VsdEntry ::= SEQUENCE {
        h3cDot11WIPSAp2VsdApName        OCTET STRING,
        h3cDot11WIPSAp2VsdRowStatus     RowStatus,
        h3cDot11WIPSAp2VsdVsdName       OCTET STRING
     }

h3cDot11WIPSAp2VsdApName OBJECT-TYPE
    SYNTAX OCTET STRING (SIZE (1..64))
    MAX-ACCESS not-accessible
    STATUS current
    DESCRIPTION
        "Represents the sensor name."
    ::= { h3cDot11WIPSAp2VsdEntry 1 }

h3cDot11WIPSAp2VsdRowStatus OBJECT-TYPE
    SYNTAX RowStatus
    MAX-ACCESS read-create
    STATUS current
    DESCRIPTION
        "The status of this table entry."
    ::= { h3cDot11WIPSAp2VsdEntry 2 }

h3cDot11WIPSAp2VsdVsdName OBJECT-TYPE
    SYNTAX OCTET STRING (SIZE (1..63))
    MAX-ACCESS read-create
    STATUS current
    DESCRIPTION
        "Represents the name of a virtual security domain."
    ::= { h3cDot11WIPSAp2VsdEntry 3 }


h3cDot11WIPSApRadioTable OBJECT-TYPE
    SYNTAX SEQUENCE OF H3cDot11WIPSApRadioEntry
    MAX-ACCESS not-accessible
    STATUS current
    DESCRIPTION
        "The table contains the enable status of WIPS on radios of sensors."
    ::= { h3cDot11WIPSConfigGroup 3 }

h3cDot11WIPSApRadioEntry OBJECT-TYPE
    SYNTAX H3cDot11WIPSApRadioEntry
    MAX-ACCESS not-accessible
    STATUS current
    DESCRIPTION
        "Each entry contains the enable status
         of WIPS on one radio of a sensor."
    INDEX { h3cDot11WIPSApRadioApName, h3cDot11WIPSApRadioRadioID }
    ::= { h3cDot11WIPSApRadioTable 1 }

H3cDot11WIPSApRadioEntry ::= SEQUENCE {
        h3cDot11WIPSApRadioApName       OCTET STRING,
        h3cDot11WIPSApRadioRadioID      Integer32,
        h3cDot11WIPSApRadioStatus       H3cDot11WIPSEnabledStatus
     }

h3cDot11WIPSApRadioApName OBJECT-TYPE
    SYNTAX OCTET STRING (SIZE (1..64))
    MAX-ACCESS not-accessible
    STATUS current
    DESCRIPTION
        "Represents the sensor name."
    ::= { h3cDot11WIPSApRadioEntry 1 }

h3cDot11WIPSApRadioRadioID OBJECT-TYPE
    SYNTAX Integer32 (1..4)
    MAX-ACCESS not-accessible
    STATUS current
    DESCRIPTION
        "Represents a radio identifier."
    ::= { h3cDot11WIPSApRadioEntry 2 }

h3cDot11WIPSApRadioStatus OBJECT-TYPE
    SYNTAX  H3cDot11WIPSEnabledStatus
    MAX-ACCESS read-write
    STATUS current
    DESCRIPTION
        "The enable status of WIPS on the radio."
    ::= { h3cDot11WIPSApRadioEntry 3 }

h3cDot11WIPSRuleTable OBJECT-TYPE
    SYNTAX SEQUENCE OF H3cDot11WIPSRuleEntry
    MAX-ACCESS not-accessible
    STATUS current
    DESCRIPTION
        "The table defines signature rule or ap-class rule."
    ::= { h3cDot11WIPSConfigGroup 4 }

h3cDot11WIPSRuleEntry OBJECT-TYPE
    SYNTAX H3cDot11WIPSRuleEntry
    MAX-ACCESS not-accessible
    STATUS current
    DESCRIPTION
        "Each entry contains information about
         signature rule or ap-class rule."
    INDEX { h3cDot11WIPSRuleType, h3cDot11WIPSRuleId }
    ::= { h3cDot11WIPSRuleTable 1 }

H3cDot11WIPSRuleEntry ::= SEQUENCE {
        h3cDot11WIPSRuleType                H3cDot11WIPSRuleTypes,
        h3cDot11WIPSRuleId                  Integer32,
        h3cDot11WIPSRuleRowStatus           RowStatus
     }

h3cDot11WIPSRuleType OBJECT-TYPE
    SYNTAX H3cDot11WIPSRuleTypes
    MAX-ACCESS not-accessible
    STATUS current
    DESCRIPTION
        "Represents the rule type."
    ::= { h3cDot11WIPSRuleEntry 1 }

h3cDot11WIPSRuleId OBJECT-TYPE
    SYNTAX Integer32 (1..65535)
    MAX-ACCESS not-accessible
    STATUS current
    DESCRIPTION
        "Represents the rule id."
    ::= { h3cDot11WIPSRuleEntry 2 }

h3cDot11WIPSRuleRowStatus OBJECT-TYPE
    SYNTAX RowStatus
    MAX-ACCESS read-create
    STATUS current
    DESCRIPTION
        "The status of this table entry."
    ::= { h3cDot11WIPSRuleEntry 3 }

h3cDot11WIPSAlySigRuleTable OBJECT-TYPE
    SYNTAX SEQUENCE OF H3cDot11WIPSAlySigRuleEntry
    MAX-ACCESS not-accessible
    STATUS current
    DESCRIPTION
        "The table provides information about applying signature rule."
    ::= { h3cDot11WIPSConfigGroup 5 }

h3cDot11WIPSAlySigRuleEntry OBJECT-TYPE
    SYNTAX H3cDot11WIPSAlySigRuleEntry
    MAX-ACCESS not-accessible
    STATUS current
    DESCRIPTION
        "Each entry contains information about applying signature rule."
    INDEX { h3cDot11WIPSAlySigPolicyName, h3cDot11WIPSAlySigRuleID }
    ::= { h3cDot11WIPSAlySigRuleTable 1 }

H3cDot11WIPSAlySigRuleEntry ::= SEQUENCE {
        h3cDot11WIPSAlySigPolicyName                OCTET STRING,
        h3cDot11WIPSAlySigRuleID                    Integer32,
        h3cDot11WIPSAlySigRowStatus                 RowStatus
     }

h3cDot11WIPSAlySigPolicyName OBJECT-TYPE
    SYNTAX OCTET STRING (SIZE (1..63))
    MAX-ACCESS not-accessible
    STATUS current
    DESCRIPTION
        "Represents the name of signature policy name."
    ::= { h3cDot11WIPSAlySigRuleEntry 1 }

h3cDot11WIPSAlySigRuleID OBJECT-TYPE
    SYNTAX Integer32 (1..65535)
    MAX-ACCESS not-accessible
    STATUS current
    DESCRIPTION
        "Represents the rule id of signature."
    ::= { h3cDot11WIPSAlySigRuleEntry 2 }

h3cDot11WIPSAlySigRowStatus OBJECT-TYPE
    SYNTAX RowStatus
    MAX-ACCESS read-create
    STATUS current
    DESCRIPTION
        "The status of this table entry."
    ::= { h3cDot11WIPSAlySigRuleEntry 3 }

h3cDot11WIPSAlyClaRuleTable OBJECT-TYPE
    SYNTAX SEQUENCE OF H3cDot11WIPSAlyClaRuleEntry
    MAX-ACCESS not-accessible
    STATUS current
    DESCRIPTION
        "The table provides information about applying classification rule."
    ::= { h3cDot11WIPSConfigGroup 6 }

h3cDot11WIPSAlyClaRuleEntry OBJECT-TYPE
    SYNTAX H3cDot11WIPSAlyClaRuleEntry
    MAX-ACCESS not-accessible
    STATUS current
    DESCRIPTION
        "Each entry contains information about applying classification rule."
    INDEX { h3cDot11WIPSAlyClaPolicyName, h3cDot11WIPSAlyClasRuleID }
    ::= { h3cDot11WIPSAlyClaRuleTable 1 }

H3cDot11WIPSAlyClaRuleEntry ::= SEQUENCE {
        h3cDot11WIPSAlyClaPolicyName           OCTET STRING,
        h3cDot11WIPSAlyClasRuleID              Integer32,
        h3cDot11WIPSAlyClaRuleType             H3cDot11WIPSAlyAPClaRuleType,
        h3cDot11WIPSAlyClaRuleLevel            Integer32,
        h3cDot11WIPSAlyClaRowStatus            RowStatus
     }

h3cDot11WIPSAlyClaPolicyName OBJECT-TYPE
    SYNTAX OCTET STRING (SIZE (1..63))
    MAX-ACCESS not-accessible
    STATUS current
    DESCRIPTION
        "Represents the name of classification policy name."
    ::= { h3cDot11WIPSAlyClaRuleEntry 1 }

h3cDot11WIPSAlyClasRuleID OBJECT-TYPE
    SYNTAX Integer32 (1..65535)
    MAX-ACCESS not-accessible
    STATUS current
    DESCRIPTION
        "Represents the rule id of classification."
    ::= { h3cDot11WIPSAlyClaRuleEntry 2 }

h3cDot11WIPSAlyClaRuleType OBJECT-TYPE
    SYNTAX H3cDot11WIPSAlyAPClaRuleType
    MAX-ACCESS read-create
    STATUS current
    DESCRIPTION
        "The type of applying classfication rule."
    ::= { h3cDot11WIPSAlyClaRuleEntry 3 }

h3cDot11WIPSAlyClaRuleLevel OBJECT-TYPE
    SYNTAX Integer32 (1..100)
    MAX-ACCESS read-create
    STATUS current
    DESCRIPTION
        "The level of applying classfication rule."
    ::= { h3cDot11WIPSAlyClaRuleEntry 4 }

h3cDot11WIPSAlyClaRowStatus OBJECT-TYPE
    SYNTAX RowStatus
    MAX-ACCESS read-create
    STATUS current
    DESCRIPTION
        "The status of this table entry."
    ::= { h3cDot11WIPSAlyClaRuleEntry 5 }

h3cDot11WIPSTrustMacTable OBJECT-TYPE
    SYNTAX SEQUENCE OF H3cDot11WIPSTrustMacEntry
    MAX-ACCESS not-accessible
    STATUS current
    DESCRIPTION
        "The table defines adding a MacAdress to the trust-device-list(TDL)"
    ::= { h3cDot11WIPSConfigGroup 7 }

h3cDot11WIPSTrustMacEntry OBJECT-TYPE
    SYNTAX H3cDot11WIPSTrustMacEntry
    MAX-ACCESS not-accessible
    STATUS current
    DESCRIPTION
        "Each entry contains information about a Mac in a TDL."
    INDEX { h3cDot11WIPSTrustMacPolicyName, h3cDot11WIPSTrustMacAddress }
    ::= { h3cDot11WIPSTrustMacTable 1 }

H3cDot11WIPSTrustMacEntry ::= SEQUENCE {
        h3cDot11WIPSTrustMacPolicyName     OCTET STRING,
        h3cDot11WIPSTrustMacAddress        MacAddress,
        h3cDot11WIPSTrustMacRowStatus      RowStatus
     }

h3cDot11WIPSTrustMacPolicyName OBJECT-TYPE
    SYNTAX OCTET STRING (SIZE (1..63))
    MAX-ACCESS not-accessible
    STATUS current
    DESCRIPTION
        "Represents the classification policy name."
    ::= { h3cDot11WIPSTrustMacEntry 1 }

h3cDot11WIPSTrustMacAddress OBJECT-TYPE
    SYNTAX MacAddress
    MAX-ACCESS not-accessible
    STATUS current
    DESCRIPTION
        "Represents the MAC address."
    ::= { h3cDot11WIPSTrustMacEntry 2 }

h3cDot11WIPSTrustMacRowStatus OBJECT-TYPE
    SYNTAX RowStatus
    MAX-ACCESS read-create
    STATUS current
    DESCRIPTION
        "The status of this table entry."
    ::= { h3cDot11WIPSTrustMacEntry 3 }

h3cDot11WIPSBlockMacTable OBJECT-TYPE
    SYNTAX SEQUENCE OF H3cDot11WIPSBlockMacEntry
    MAX-ACCESS not-accessible
    STATUS current
    DESCRIPTION
        "The table defines add MacAdress to the static-forbidden-list(SFL)"
    ::= { h3cDot11WIPSConfigGroup 8 }

h3cDot11WIPSBlockMacEntry OBJECT-TYPE
    SYNTAX H3cDot11WIPSBlockMacEntry
    MAX-ACCESS not-accessible
    STATUS current
    DESCRIPTION
        "Each entry contains information about a Mac in a SFL."
    INDEX { h3cDot11WIPSBlockMacPolicyName, h3cDot11WIPSBlockMacAddress }
    ::= { h3cDot11WIPSBlockMacTable 1 }

H3cDot11WIPSBlockMacEntry ::= SEQUENCE {
        h3cDot11WIPSBlockMacPolicyName       OCTET STRING,
        h3cDot11WIPSBlockMacAddress          MacAddress,
        h3cDot11WIPSBlockMacRowStatus        RowStatus
     }

h3cDot11WIPSBlockMacPolicyName OBJECT-TYPE
    SYNTAX OCTET STRING (SIZE (1..63))
    MAX-ACCESS not-accessible
    STATUS current
    DESCRIPTION
        "Represents the classification policy name."
    ::= { h3cDot11WIPSBlockMacEntry 1 }

h3cDot11WIPSBlockMacAddress OBJECT-TYPE
    SYNTAX MacAddress
    MAX-ACCESS not-accessible
    STATUS current
    DESCRIPTION
        "Represents the MAC address."
    ::= { h3cDot11WIPSBlockMacEntry 2 }

h3cDot11WIPSBlockMacRowStatus OBJECT-TYPE
    SYNTAX RowStatus
    MAX-ACCESS read-create
    STATUS current
    DESCRIPTION
        "The status of this table entry."
    ::= { h3cDot11WIPSBlockMacEntry 3 }

h3cDot11WIPSManulClaTable OBJECT-TYPE
    SYNTAX SEQUENCE OF H3cDot11WIPSManulClaEntry
    MAX-ACCESS not-accessible
    STATUS current
    DESCRIPTION
        "The table contains the manual classify information."
    ::= { h3cDot11WIPSConfigGroup 9 }

h3cDot11WIPSManulClaEntry OBJECT-TYPE
    SYNTAX H3cDot11WIPSManulClaEntry
    MAX-ACCESS not-accessible
    STATUS current
    DESCRIPTION
        "Each entry contains the address specified manually in a policy."
    INDEX { h3cDot11WIPSManulClaPlyName, h3cDot11WIPSManulClaMac }
    ::= { h3cDot11WIPSManulClaTable 1 }

H3cDot11WIPSManulClaEntry ::= SEQUENCE {
        h3cDot11WIPSManulClaPlyName        OCTET STRING,
        h3cDot11WIPSManulClaMac            MacAddress,
        h3cDot11WIPSManulClassifyType      H3cDot11WIPSManualAPType,
        h3cDot11WIPSManuClaRowStatus       RowStatus
     }

h3cDot11WIPSManulClaPlyName OBJECT-TYPE
    SYNTAX OCTET STRING (SIZE (1..63))
    MAX-ACCESS not-accessible
    STATUS current
    DESCRIPTION
        "Represents the policy name."
    ::= { h3cDot11WIPSManulClaEntry 1 }

h3cDot11WIPSManulClaMac OBJECT-TYPE
    SYNTAX MacAddress
    MAX-ACCESS not-accessible
    STATUS current
    DESCRIPTION
        "Represents the MAC address of AP."
    ::= { h3cDot11WIPSManulClaEntry 2 }

h3cDot11WIPSManulClassifyType OBJECT-TYPE
    SYNTAX  H3cDot11WIPSManualAPType
    MAX-ACCESS read-create
    STATUS current
    DESCRIPTION
        "The classification type of AP."
    ::= { h3cDot11WIPSManulClaEntry 3 }

h3cDot11WIPSManuClaRowStatus OBJECT-TYPE
    SYNTAX RowStatus
    MAX-ACCESS read-create
    STATUS current
    DESCRIPTION
        "The status of this table entry."
    ::= { h3cDot11WIPSManulClaEntry 4 }

h3cDot11WIPSTrustOuiTable OBJECT-TYPE
    SYNTAX SEQUENCE OF H3cDot11WIPSTrustOuiEntry
    MAX-ACCESS not-accessible
    STATUS current
    DESCRIPTION
        "The table provides information about trust oui."
    ::= { h3cDot11WIPSConfigGroup 10 }

h3cDot11WIPSTrustOuiEntry OBJECT-TYPE
    SYNTAX H3cDot11WIPSTrustOuiEntry
    MAX-ACCESS not-accessible
    STATUS current
    DESCRIPTION
        "Each entry contains information about trust oui."
    INDEX { h3cDot11WIPSTrustOuiPolicyName, h3cDot11WIPSTrustOuiMac }
    ::= { h3cDot11WIPSTrustOuiTable 1 }

H3cDot11WIPSTrustOuiEntry ::= SEQUENCE {
        h3cDot11WIPSTrustOuiPolicyName                OCTET STRING,
        h3cDot11WIPSTrustOuiMac                       H3cDot11WIPSOuiAddress,
        h3cDot11WIPSTrustOuiRowStatus                 RowStatus
     }

h3cDot11WIPSTrustOuiPolicyName OBJECT-TYPE
    SYNTAX OCTET STRING (SIZE (1..63))
    MAX-ACCESS not-accessible
    STATUS current
    DESCRIPTION
        "Represents the name of classification policy name."
    ::= { h3cDot11WIPSTrustOuiEntry 1 }

h3cDot11WIPSTrustOuiMac OBJECT-TYPE
    SYNTAX H3cDot11WIPSOuiAddress
    MAX-ACCESS not-accessible
    STATUS current
    DESCRIPTION
        "Represents the address of trust oui."
    ::= { h3cDot11WIPSTrustOuiEntry 2 }

h3cDot11WIPSTrustOuiRowStatus OBJECT-TYPE
    SYNTAX RowStatus
    MAX-ACCESS read-create
    STATUS current
    DESCRIPTION
        "The status of this table entry."
    ::= { h3cDot11WIPSTrustOuiEntry 3 }

h3cDot11WIPSTrustSSidTable OBJECT-TYPE
    SYNTAX SEQUENCE OF H3cDot11WIPSTrustSSidEntry
    MAX-ACCESS not-accessible
    STATUS current
    DESCRIPTION
        "The table defines add one SSID to the trust-device-list(TDL)"
    ::= { h3cDot11WIPSConfigGroup 11 }

h3cDot11WIPSTrustSSidEntry OBJECT-TYPE
    SYNTAX H3cDot11WIPSTrustSSidEntry
    MAX-ACCESS not-accessible
    STATUS current
    DESCRIPTION
        "Each entry contains information about a SSID in a TDL."
    INDEX { h3cDot11WIPSTrustSSidPlyName, h3cDot11WIPSTrustSSidName }
    ::= { h3cDot11WIPSTrustSSidTable 1 }

H3cDot11WIPSTrustSSidEntry ::= SEQUENCE {
        h3cDot11WIPSTrustSSidPlyName          OCTET STRING,
        h3cDot11WIPSTrustSSidName             OCTET STRING,
        h3cDot11WIPSTrustSSidRowStatus        RowStatus
     }

h3cDot11WIPSTrustSSidPlyName OBJECT-TYPE
    SYNTAX OCTET STRING (SIZE (1..63))
    MAX-ACCESS not-accessible
    STATUS current
    DESCRIPTION
        "Represents the classification policy name."
    ::= { h3cDot11WIPSTrustSSidEntry 1 }

h3cDot11WIPSTrustSSidName OBJECT-TYPE
    SYNTAX OCTET STRING (SIZE (1..32))
    MAX-ACCESS not-accessible
    STATUS current
    DESCRIPTION
        "Represents the SSID name."
    ::= { h3cDot11WIPSTrustSSidEntry 2 }

h3cDot11WIPSTrustSSidRowStatus OBJECT-TYPE
    SYNTAX RowStatus
    MAX-ACCESS read-create
    STATUS current
    DESCRIPTION
        "The status of this table entry."
    ::= { h3cDot11WIPSTrustSSidEntry 3 }

h3cDot11WIPSMalfDtcTable OBJECT-TYPE
    SYNTAX SEQUENCE OF H3cDot11WIPSMalfDtcEntry
    MAX-ACCESS not-accessible
    STATUS current
    DESCRIPTION
        "The table contains the malformed packet detect information."
    ::= { h3cDot11WIPSConfigGroup 12 }

h3cDot11WIPSMalfDtcEntry OBJECT-TYPE
    SYNTAX H3cDot11WIPSMalfDtcEntry
    MAX-ACCESS not-accessible
    STATUS current
    DESCRIPTION
        "Each entry contains the malformed type in a detect policy."
    INDEX { h3cDot11WIPSMalfDtcPolicyName, h3cDot11WIPSMalfDtcType }
    ::= { h3cDot11WIPSMalfDtcTable 1 }

H3cDot11WIPSMalfDtcEntry ::= SEQUENCE {
        h3cDot11WIPSMalfDtcPolicyName       OCTET STRING,
        h3cDot11WIPSMalfDtcType             H3cDot11WIPSMalformedType,
        h3cDot11WIPSMalfDtcQuietTime        Integer32,
        h3cDot11WIPSMalfDtciStatus          H3cDot11WIPSEnabledStatus
     }

h3cDot11WIPSMalfDtcPolicyName OBJECT-TYPE
    SYNTAX OCTET STRING (SIZE (1..63))
    MAX-ACCESS not-accessible
    STATUS current
    DESCRIPTION
        "Represents the policy name."
    ::= { h3cDot11WIPSMalfDtcEntry 1 }

h3cDot11WIPSMalfDtcType OBJECT-TYPE
    SYNTAX  H3cDot11WIPSMalformedType
    MAX-ACCESS not-accessible
    STATUS current
    DESCRIPTION
        "The malformed type of detect."
    ::= { h3cDot11WIPSMalfDtcEntry 2 }

h3cDot11WIPSMalfDtcQuietTime OBJECT-TYPE
    SYNTAX Integer32 (5..604800)
    MAX-ACCESS read-write
    STATUS current
    DESCRIPTION
        "Represents the quiet time."
    ::= { h3cDot11WIPSMalfDtcEntry 3 }

h3cDot11WIPSMalfDtciStatus OBJECT-TYPE
    SYNTAX  H3cDot11WIPSEnabledStatus
    MAX-ACCESS read-write
    STATUS current
    DESCRIPTION
        "The enable status of malformed detect."
    ::= { h3cDot11WIPSMalfDtcEntry 4 }

h3cDot11WIPSLgeDutTable OBJECT-TYPE
    SYNTAX SEQUENCE OF H3cDot11WIPSLgeDutEntry
    MAX-ACCESS not-accessible
    STATUS current
    DESCRIPTION
        "The table contains the infomation about
         large duration malformed detect."
    ::= { h3cDot11WIPSConfigGroup 13 }

h3cDot11WIPSLgeDutEntry OBJECT-TYPE
    SYNTAX H3cDot11WIPSLgeDutEntry
    MAX-ACCESS not-accessible
    STATUS current
    DESCRIPTION
        "Each entry contains the infomation about
         large duration malformed detect."
    INDEX { h3cDot11WIPSLgeDutPolicyName }
    ::= { h3cDot11WIPSLgeDutTable 1 }

H3cDot11WIPSLgeDutEntry ::= SEQUENCE {
        h3cDot11WIPSLgeDutPolicyName           OCTET STRING,
        h3cDot11WIPSLgeDutThreshold            Integer32,
        h3cDot11WIPSLgeDutQuietTime            Integer32,
        h3cDot11WIPSLgeDutStatus               H3cDot11WIPSEnabledStatus
     }

h3cDot11WIPSLgeDutPolicyName OBJECT-TYPE
    SYNTAX OCTET STRING (SIZE (1..63))
    MAX-ACCESS not-accessible
    STATUS current
    DESCRIPTION
        "Represents the detect policy name."
    ::= { h3cDot11WIPSLgeDutEntry 1 }

h3cDot11WIPSLgeDutThreshold OBJECT-TYPE
    SYNTAX Integer32 (1..32767)
    MAX-ACCESS read-write
    STATUS current
    DESCRIPTION
        "Represents large duration malformed detect threshold."
    ::= { h3cDot11WIPSLgeDutEntry 2 }

h3cDot11WIPSLgeDutQuietTime OBJECT-TYPE
    SYNTAX Integer32 (5..604800)
    MAX-ACCESS read-write
    STATUS current
    DESCRIPTION
        "Represents large duration malformed detect quiet time ."
    ::= { h3cDot11WIPSLgeDutEntry 3 }

h3cDot11WIPSLgeDutStatus OBJECT-TYPE
    SYNTAX  H3cDot11WIPSEnabledStatus
    MAX-ACCESS read-write
    STATUS current
    DESCRIPTION
        "The enable status of large duration malformed detect."
    ::= { h3cDot11WIPSLgeDutEntry 4 }

h3cDot11WIPSRtLmtTable OBJECT-TYPE
    SYNTAX SEQUENCE OF H3cDot11WIPSRtLmtEntry
    MAX-ACCESS not-accessible
    STATUS current
    DESCRIPTION
        "The table defines the control of AP learned the devices rate."
    ::= { h3cDot11WIPSConfigGroup 14 }

h3cDot11WIPSRtLmtEntry OBJECT-TYPE
    SYNTAX H3cDot11WIPSRtLmtEntry
    MAX-ACCESS not-accessible
    STATUS current
    DESCRIPTION
        "Each entry contains information about a control of AP learned rate ."
    INDEX { h3cDot11WIPSRtLmtPolicyName, h3cDot11WIPSRtLmtRtLmtType }
    ::= { h3cDot11WIPSRtLmtTable 1 }

H3cDot11WIPSRtLmtEntry ::= SEQUENCE {
        h3cDot11WIPSRtLmtPolicyName       OCTET STRING,
        h3cDot11WIPSRtLmtRtLmtType        H3cDot11WIPSRtLmtType,
        h3cDot11WIPSRtLmtInterval         Integer32,
        h3cDot11WIPSRtLmtThreshold        Integer32,
        h3cDot11WIPSRtLmtQuiet            Integer32,
        h3cDot11WIPSRtLmtStatus           H3cDot11WIPSEnabledStatus
     }

h3cDot11WIPSRtLmtPolicyName OBJECT-TYPE
    SYNTAX OCTET STRING (SIZE (1..63))
    MAX-ACCESS not-accessible
    STATUS current
    DESCRIPTION
        "Represents the classification policy name."
    ::= { h3cDot11WIPSRtLmtEntry 1 }

h3cDot11WIPSRtLmtRtLmtType OBJECT-TYPE
    SYNTAX  H3cDot11WIPSRtLmtType
    MAX-ACCESS not-accessible
    STATUS current
    DESCRIPTION
        "Represents the device type."
    ::= { h3cDot11WIPSRtLmtEntry 2 }

h3cDot11WIPSRtLmtInterval OBJECT-TYPE
    SYNTAX Integer32(1..3600)
    MAX-ACCESS read-write
    STATUS current
    DESCRIPTION
        "The statistics cycle of AP learned device."
    ::= { h3cDot11WIPSRtLmtEntry 3 }

h3cDot11WIPSRtLmtThreshold OBJECT-TYPE
    SYNTAX Integer32(1..4096)
    MAX-ACCESS read-write
    STATUS current
    DESCRIPTION
        "The maximum devices number of AP learned."
    ::= { h3cDot11WIPSRtLmtEntry 4 }

h3cDot11WIPSRtLmtQuiet OBJECT-TYPE
    SYNTAX Integer32(1200..3600)
    MAX-ACCESS read-write
    STATUS current
    DESCRIPTION
        "Represents a quiet time after the warning log had been sent."
    ::= { h3cDot11WIPSRtLmtEntry 5 }

h3cDot11WIPSRtLmtStatus OBJECT-TYPE
    SYNTAX H3cDot11WIPSEnabledStatus
    MAX-ACCESS read-write
    STATUS current
    DESCRIPTION
        "The enable status of the control of AP learned the devices rate."
    ::= { h3cDot11WIPSRtLmtEntry 6 }

h3cDot11WIPSDtcAckTable OBJECT-TYPE
    SYNTAX SEQUENCE OF H3cDot11WIPSDtcAckEntry
    MAX-ACCESS not-accessible
    STATUS current
    DESCRIPTION
        "The table contains the infomation about detect attack."
    ::= { h3cDot11WIPSConfigGroup 15 }

h3cDot11WIPSDtcAckEntry OBJECT-TYPE
    SYNTAX H3cDot11WIPSDtcAckEntry
    MAX-ACCESS not-accessible
    STATUS current
    DESCRIPTION
        "Each entry contains the infomation about detect attack."
    INDEX { h3cDot11WIPSDtcAckPolicyName, h3cDot11WIPSDtcAckType }
    ::= { h3cDot11WIPSDtcAckTable 1 }

H3cDot11WIPSDtcAckEntry ::= SEQUENCE {
        h3cDot11WIPSDtcAckPolicyName            OCTET STRING,
        h3cDot11WIPSDtcAckType                  H3cDot11WIPSDtcAckTypes,
        h3cDot11WIPSDtcAckQuietTime             Integer32,
        h3cDot11WIPSDtcAckInterval              Integer32,
        h3cDot11WIPSDtcAckThreshold             Integer32,
        h3cDot11WIPSDtcAckStatus                H3cDot11WIPSEnabledStatus
     }

h3cDot11WIPSDtcAckPolicyName OBJECT-TYPE
    SYNTAX OCTET STRING (SIZE (1..63))
    MAX-ACCESS not-accessible
    STATUS current
    DESCRIPTION
        "Represents the detect policy name."
    ::= { h3cDot11WIPSDtcAckEntry 1 }

h3cDot11WIPSDtcAckType OBJECT-TYPE
    SYNTAX H3cDot11WIPSDtcAckTypes
    MAX-ACCESS not-accessible
    STATUS current
    DESCRIPTION
        "Represents the detect attack type."
    ::= { h3cDot11WIPSDtcAckEntry 2 }


h3cDot11WIPSDtcAckQuietTime OBJECT-TYPE
    SYNTAX Integer32 (5..604800)
    MAX-ACCESS read-write
    STATUS current
    DESCRIPTION
        "Represents detect attack quiet time ."
    ::= { h3cDot11WIPSDtcAckEntry 3 }

h3cDot11WIPSDtcAckInterval OBJECT-TYPE
    SYNTAX Integer32 (1..3600)
    MAX-ACCESS read-write
    STATUS current
    DESCRIPTION
        "Represents detect attack  interval."
    ::= { h3cDot11WIPSDtcAckEntry 4 }

h3cDot11WIPSDtcAckThreshold OBJECT-TYPE
    SYNTAX Integer32 (1..100000)
    MAX-ACCESS read-write
    STATUS current
    DESCRIPTION
        "Represents detect attack threshold."
    ::= { h3cDot11WIPSDtcAckEntry 5 }

h3cDot11WIPSDtcAckStatus OBJECT-TYPE
    SYNTAX  H3cDot11WIPSEnabledStatus
    MAX-ACCESS read-write
    STATUS current
    DESCRIPTION
        "The enable status of detect attack."
    ::= { h3cDot11WIPSDtcAckEntry 6 }

h3cDot11WIPSDtcDevTimeTable OBJECT-TYPE
    SYNTAX SEQUENCE OF H3cDot11WIPSDtcDevTimeEntry
    MAX-ACCESS not-accessible
    STATUS current
    DESCRIPTION
        "The table contains the infomation about detect device time."
    ::= { h3cDot11WIPSConfigGroup 16 }

h3cDot11WIPSDtcDevTimeEntry OBJECT-TYPE
    SYNTAX H3cDot11WIPSDtcDevTimeEntry
    MAX-ACCESS not-accessible
    STATUS current
    DESCRIPTION
        "Each entry contains the infomation about detect device time."
    INDEX { h3cDot11WIPSDtcDevTimePlyName, h3cDot11WIPSDtcDevTimeType }
    ::= { h3cDot11WIPSDtcDevTimeTable 1 }

H3cDot11WIPSDtcDevTimeEntry ::= SEQUENCE {
        h3cDot11WIPSDtcDevTimePlyName         OCTET STRING,
        h3cDot11WIPSDtcDevTimeType            H3cDot11WIPSDtcDevTimeTypes,
        h3cDot11WIPSDtcDevTimeInactive        Integer32,
        h3cDot11WIPSDtcDevTimeAging           Integer32,
        h3cDot11WIPSDtcDevTimeStatus          H3cDot11WIPSEnabledStatus
     }

h3cDot11WIPSDtcDevTimePlyName OBJECT-TYPE
    SYNTAX OCTET STRING (SIZE (1..63))
    MAX-ACCESS not-accessible
    STATUS current
    DESCRIPTION
        "Represents the detect policy name."
    ::= { h3cDot11WIPSDtcDevTimeEntry 1 }

h3cDot11WIPSDtcDevTimeType OBJECT-TYPE
    SYNTAX H3cDot11WIPSDtcDevTimeTypes
    MAX-ACCESS not-accessible
    STATUS current
    DESCRIPTION
        "Represents the detect device time type."
    ::= { h3cDot11WIPSDtcDevTimeEntry 2 }

h3cDot11WIPSDtcDevTimeInactive OBJECT-TYPE
    SYNTAX Integer32 (60..1200)
    MAX-ACCESS read-write
    STATUS current
    DESCRIPTION
        "Represents detect device time inactive time."
    ::= { h3cDot11WIPSDtcDevTimeEntry 3 }

h3cDot11WIPSDtcDevTimeAging OBJECT-TYPE
    SYNTAX Integer32 (120..86400)
    MAX-ACCESS read-write
    STATUS current
    DESCRIPTION
        "Represents detect device time aging time."
    ::= { h3cDot11WIPSDtcDevTimeEntry 4 }

h3cDot11WIPSDtcDevTimeStatus OBJECT-TYPE
    SYNTAX  H3cDot11WIPSEnabledStatus
    MAX-ACCESS read-write
    STATUS current
    DESCRIPTION
        "The enable status of detect device time."
    ::= { h3cDot11WIPSDtcDevTimeEntry 5 }

h3cDot11WIPSApimperTable OBJECT-TYPE
    SYNTAX SEQUENCE OF H3cDot11WIPSApimperEntry
    MAX-ACCESS not-accessible
    STATUS current
    DESCRIPTION
        "The table provides information about AP impersonation."
    ::= { h3cDot11WIPSConfigGroup 17 }

h3cDot11WIPSApimperEntry OBJECT-TYPE
    SYNTAX H3cDot11WIPSApimperEntry
    MAX-ACCESS not-accessible
    STATUS current
    DESCRIPTION
        "Each entry contains information about one AP impersonation."
    INDEX { h3cDot11WIPSApimperPolicyName }
    ::= { h3cDot11WIPSApimperTable 1 }

H3cDot11WIPSApimperEntry ::= SEQUENCE {
        h3cDot11WIPSApimperPolicyName      OCTET STRING,
        h3cDot11WIPSApimperQuiet           Integer32,
        h3cDot11WIPSApimperStatus          H3cDot11WIPSEnabledStatus
      }

h3cDot11WIPSApimperPolicyName OBJECT-TYPE
    SYNTAX OCTET STRING (SIZE (1..63))
    MAX-ACCESS not-accessible
    STATUS current
    DESCRIPTION
        "Represents the name of policy."
    ::= { h3cDot11WIPSApimperEntry 1 }

h3cDot11WIPSApimperQuiet OBJECT-TYPE
    SYNTAX Integer32 (5..604800)
    MAX-ACCESS read-write
    STATUS current
    DESCRIPTION
        "The quiet of this table entry."
    ::= { h3cDot11WIPSApimperEntry 2 }

h3cDot11WIPSApimperStatus OBJECT-TYPE
    SYNTAX H3cDot11WIPSEnabledStatus
    MAX-ACCESS read-write
    STATUS current
    DESCRIPTION
        "The status of this table entry."
    ::= { h3cDot11WIPSApimperEntry 3 }

h3cDot11WIPSDctSoftApTable OBJECT-TYPE
    SYNTAX SEQUENCE OF H3cDot11WIPSDctSoftApEntry
    MAX-ACCESS not-accessible
    STATUS current
    DESCRIPTION
        "The table contains the enable status of detect of soft AP."
    ::= { h3cDot11WIPSConfigGroup 18 }

h3cDot11WIPSDctSoftApEntry OBJECT-TYPE
    SYNTAX H3cDot11WIPSDctSoftApEntry
    MAX-ACCESS not-accessible
    STATUS current
    DESCRIPTION
        "Each entry contains the enable status of detect a soft AP."
    INDEX { h3cDot11WIPSDctSoftApPlyName }
    ::= { h3cDot11WIPSDctSoftApTable 1 }

H3cDot11WIPSDctSoftApEntry ::= SEQUENCE {
        h3cDot11WIPSDctSoftApPlyName      OCTET STRING,
        h3cDot11WIPSDctSoftApThold        Integer32,
        h3cDot11WIPSDctSoftApStatus       H3cDot11WIPSEnabledStatus
     }

h3cDot11WIPSDctSoftApPlyName OBJECT-TYPE
    SYNTAX OCTET STRING (SIZE (1..63))
    MAX-ACCESS not-accessible
    STATUS current
    DESCRIPTION
        "Represents the detect policy name."
    ::= { h3cDot11WIPSDctSoftApEntry 1 }

h3cDot11WIPSDctSoftApThold OBJECT-TYPE
    SYNTAX Integer32 (5..600)
    MAX-ACCESS read-write
    STATUS current
    DESCRIPTION
        "Represents a convert time."
    ::= { h3cDot11WIPSDctSoftApEntry 2 }

h3cDot11WIPSDctSoftApStatus OBJECT-TYPE
    SYNTAX  H3cDot11WIPSEnabledStatus
    MAX-ACCESS read-write
    STATUS current
    DESCRIPTION
        "The enable status of detect a soft AP."
    ::= { h3cDot11WIPSDctSoftApEntry 3 }

h3cDot11WIPSPowerSaveTable OBJECT-TYPE
    SYNTAX SEQUENCE OF H3cDot11WIPSPowerSaveEntry
    MAX-ACCESS not-accessible
    STATUS current
    DESCRIPTION
        "This table contains the power-save detect information."
    ::= { h3cDot11WIPSConfigGroup 19 }

h3cDot11WIPSPowerSaveEntry OBJECT-TYPE
    SYNTAX H3cDot11WIPSPowerSaveEntry
    MAX-ACCESS not-accessible
    STATUS current
    DESCRIPTION
        "Each entry contains information about power-save detect."
    INDEX { h3cDot11WIPSPowerSavePlyName }
    ::= { h3cDot11WIPSPowerSaveTable 1 }

H3cDot11WIPSPowerSaveEntry ::= SEQUENCE {
        h3cDot11WIPSPowerSavePlyName       OCTET STRING,
        h3cDot11WIPSPowerSaveInterval      Integer32,
        h3cDot11WIPSPowerSaveMinOffPkt     Integer32,
        h3cDot11WIPSPowerSaveOnOffPct      Integer32,
        h3cDot11WIPSPowerSaveQuiet         Integer32,
        h3cDot11WIPSPowerSaveStatus        H3cDot11WIPSEnabledStatus
     }

h3cDot11WIPSPowerSavePlyName OBJECT-TYPE
    SYNTAX OCTET STRING (SIZE (1..63))
    MAX-ACCESS not-accessible
    STATUS current
    DESCRIPTION
        "Represents the policy name."
    ::= { h3cDot11WIPSPowerSaveEntry 1 }

h3cDot11WIPSPowerSaveInterval OBJECT-TYPE
    SYNTAX Integer32 (1..3600)
    MAX-ACCESS read-write
    STATUS current
    DESCRIPTION
        "Represents the interval of power-save detect."
    ::= { h3cDot11WIPSPowerSaveEntry 2 }

h3cDot11WIPSPowerSaveMinOffPkt OBJECT-TYPE
    SYNTAX Integer32 (10..150)
    MAX-ACCESS read-write
    STATUS current
    DESCRIPTION
        "Represents the minoffpacket of power-save detect."
    ::= { h3cDot11WIPSPowerSaveEntry 3 }

h3cDot11WIPSPowerSaveOnOffPct OBJECT-TYPE
    SYNTAX Integer32 (0..100)
    MAX-ACCESS read-write
    STATUS current
    DESCRIPTION
        "Represents the onoffpercent of power-save detect."
    ::= { h3cDot11WIPSPowerSaveEntry 4 }

h3cDot11WIPSPowerSaveQuiet OBJECT-TYPE
    SYNTAX Integer32 (5..604800)
    MAX-ACCESS read-write
    STATUS current
    DESCRIPTION
        "Represents the quiettime of power-save detect."
    ::= { h3cDot11WIPSPowerSaveEntry 5 }

h3cDot11WIPSPowerSaveStatus OBJECT-TYPE
    SYNTAX H3cDot11WIPSEnabledStatus
    MAX-ACCESS read-write
    STATUS current
    DESCRIPTION
        "Represents the enabled status of power-save detect."
    ::= { h3cDot11WIPSPowerSaveEntry 6 }

h3cDot11WIPSIgnListMacTable OBJECT-TYPE
    SYNTAX SEQUENCE OF H3cDot11WIPSIgnListMacEntry
    MAX-ACCESS not-accessible
    STATUS current
    DESCRIPTION
        "The table defines ignore list MAC."
    ::= { h3cDot11WIPSConfigGroup 20 }

h3cDot11WIPSIgnListMacEntry OBJECT-TYPE
    SYNTAX H3cDot11WIPSIgnListMacEntry
    MAX-ACCESS not-accessible
    STATUS current
    DESCRIPTION
        "Each entry contains information about ignore list MAC."
    INDEX { h3cDot11WIPSIgnListMacMacAddr }
    ::= { h3cDot11WIPSIgnListMacTable 1 }

H3cDot11WIPSIgnListMacEntry ::= SEQUENCE {
        h3cDot11WIPSIgnListMacMacAddr        MacAddress,
        h3cDot11WIPSIgnListMacRowStus        RowStatus
     }

h3cDot11WIPSIgnListMacMacAddr OBJECT-TYPE
    SYNTAX MacAddress
    MAX-ACCESS not-accessible
    STATUS current
    DESCRIPTION
        "Represents the MAC address."
    ::= { h3cDot11WIPSIgnListMacEntry 1 }

h3cDot11WIPSIgnListMacRowStus OBJECT-TYPE
    SYNTAX RowStatus
    MAX-ACCESS read-create
    STATUS current
    DESCRIPTION
        "The status of this table entry."
    ::= { h3cDot11WIPSIgnListMacEntry 2 }

h3cDot11WIPSHoneyPotTable OBJECT-TYPE
    SYNTAX SEQUENCE OF H3cDot11WIPSHoneyPotEntry
    MAX-ACCESS not-accessible
    STATUS current
    DESCRIPTION
        "The table defines the detect of honey-pot."
    ::= { h3cDot11WIPSConfigGroup 21 }

h3cDot11WIPSHoneyPotEntry OBJECT-TYPE
    SYNTAX H3cDot11WIPSHoneyPotEntry
    MAX-ACCESS not-accessible
    STATUS current
    DESCRIPTION
        "Each entry contains the enable status of detect honey-pot."
    INDEX { h3cDot11WIPSHoneyPotPlyName }
    ::= { h3cDot11WIPSHoneyPotTable 1 }

H3cDot11WIPSHoneyPotEntry ::= SEQUENCE {
        h3cDot11WIPSHoneyPotPlyName        OCTET STRING,
        h3cDot11WIPSHoneyPotSim            Integer32,
        h3cDot11WIPSHoneyPotQuiet          Integer32,
        h3cDot11WIPSHoneyPotStatus         H3cDot11WIPSEnabledStatus
     }

h3cDot11WIPSHoneyPotPlyName OBJECT-TYPE
    SYNTAX OCTET STRING (SIZE (1..63))
    MAX-ACCESS not-accessible
    STATUS current
    DESCRIPTION
        "Represents the detect policy name."
    ::= { h3cDot11WIPSHoneyPotEntry 1 }

h3cDot11WIPSHoneyPotSim OBJECT-TYPE
    SYNTAX Integer32 (70..100)
    MAX-ACCESS read-write
    STATUS current
    DESCRIPTION
        "Represents the similarity-value of matching SSID."
    ::= { h3cDot11WIPSHoneyPotEntry 2 }

h3cDot11WIPSHoneyPotQuiet OBJECT-TYPE
     SYNTAX Integer32 (5..604800)
     MAX-ACCESS read-write
     STATUS current
     DESCRIPTION
         "Represents a quiet time after the warning log had been sent."
     ::= { h3cDot11WIPSHoneyPotEntry 3 }

h3cDot11WIPSHoneyPotStatus OBJECT-TYPE
    SYNTAX  H3cDot11WIPSEnabledStatus
    MAX-ACCESS read-write
    STATUS current
    DESCRIPTION
        "The enable status of detect honey-pot."
    ::= { h3cDot11WIPSHoneyPotEntry 4 }

h3cDot11WIPSAPFldTable OBJECT-TYPE
    SYNTAX SEQUENCE OF H3cDot11WIPSAPFldEntry
    MAX-ACCESS not-accessible
    STATUS current
    DESCRIPTION
        "The table defines the detect of AP-flood."
    ::= { h3cDot11WIPSConfigGroup 22 }

h3cDot11WIPSAPFldEntry OBJECT-TYPE
    SYNTAX H3cDot11WIPSAPFldEntry
    MAX-ACCESS not-accessible
    STATUS current
    DESCRIPTION
        "Each entry contains the enable status of detect AP-flood."
    INDEX { h3cDot11WIPSAPFldPolicyName }
    ::= { h3cDot11WIPSAPFldTable 1 }

H3cDot11WIPSAPFldEntry ::= SEQUENCE {
        h3cDot11WIPSAPFldPolicyName        OCTET STRING,
        h3cDot11WIPSAPFldApnum             Integer32,
        h3cDot11WIPSAPFldExceed            Integer32,
        h3cDot11WIPSAPFldQuiet             Integer32,
        h3cDot11WIPSAPFldStatus            H3cDot11WIPSEnabledStatus
     }

h3cDot11WIPSAPFldPolicyName OBJECT-TYPE
    SYNTAX OCTET STRING (SIZE (1..63))
    MAX-ACCESS not-accessible
    STATUS current
    DESCRIPTION
        "Represents the detect policy name."
    ::= { h3cDot11WIPSAPFldEntry 1 }

h3cDot11WIPSAPFldApnum OBJECT-TYPE
    SYNTAX Integer32 (10..200)
    MAX-ACCESS read-write
    STATUS current
    DESCRIPTION
        "Represents allowable AP devices number in a wireless network."
    ::= { h3cDot11WIPSAPFldEntry 2 }

h3cDot11WIPSAPFldExceed OBJECT-TYPE
     SYNTAX Integer32 (10..200)
     MAX-ACCESS read-write
     STATUS current
     DESCRIPTION
         "Represents the allowable maximum AP devices number had exceed."
     ::= { h3cDot11WIPSAPFldEntry 3 }

h3cDot11WIPSAPFldQuiet OBJECT-TYPE
     SYNTAX Integer32 (5..604800)
     MAX-ACCESS read-write
     STATUS current
     DESCRIPTION
         "Represents a quiet time after the warning log had been sent."
     ::= { h3cDot11WIPSAPFldEntry 4 }

h3cDot11WIPSAPFldStatus OBJECT-TYPE
    SYNTAX  H3cDot11WIPSEnabledStatus
    MAX-ACCESS read-write
    STATUS current
    DESCRIPTION
        "The enable status of detect AP-flood."
    ::= { h3cDot11WIPSAPFldEntry 5 }

h3cDot11WIPSCtmManualsTable OBJECT-TYPE
    SYNTAX SEQUENCE OF H3cDot11WIPSCtmManualsEntry
    MAX-ACCESS not-accessible
    STATUS current
    DESCRIPTION
        "This table contains the manual countermeasure information."
    ::= { h3cDot11WIPSConfigGroup 23 }

h3cDot11WIPSCtmManualsEntry OBJECT-TYPE
    SYNTAX H3cDot11WIPSCtmManualsEntry
    MAX-ACCESS not-accessible
    STATUS current
    DESCRIPTION
        "Each entry contains information about manual countermeasure."
    INDEX { h3cDot11WIPSCtmManualsPlyName, h3cDot11WIPSCtmManualsMacAddr }
    ::= { h3cDot11WIPSCtmManualsTable 1 }

H3cDot11WIPSCtmManualsEntry ::= SEQUENCE {
        h3cDot11WIPSCtmManualsPlyName    OCTET STRING,
        h3cDot11WIPSCtmManualsMacAddr    MacAddress,
        h3cDot11WIPSCtmManualsRowStus     RowStatus
     }

h3cDot11WIPSCtmManualsPlyName OBJECT-TYPE
    SYNTAX OCTET STRING (SIZE (1..63))
    MAX-ACCESS not-accessible
    STATUS current
    DESCRIPTION
        "Represents the policy name."
    ::= { h3cDot11WIPSCtmManualsEntry 1 }

h3cDot11WIPSCtmManualsMacAddr OBJECT-TYPE
    SYNTAX MacAddress
    MAX-ACCESS not-accessible
    STATUS current
    DESCRIPTION
        "Represents the MAC address."
    ::= { h3cDot11WIPSCtmManualsEntry 2 }

h3cDot11WIPSCtmManualsRowStus OBJECT-TYPE
    SYNTAX RowStatus
    MAX-ACCESS read-create
    STATUS current
    DESCRIPTION
        "The status of this table entry."
    ::= { h3cDot11WIPSCtmManualsEntry 3 }

h3cDot11WIPSCtmSensorTable OBJECT-TYPE
    SYNTAX SEQUENCE OF H3cDot11WIPSCtmSensorEntry

    MAX-ACCESS not-accessible
    STATUS current
    DESCRIPTION
        "The table contains the countermeasure all sensor information."
    ::= { h3cDot11WIPSConfigGroup 24 }

h3cDot11WIPSCtmSensorEntry OBJECT-TYPE
    SYNTAX H3cDot11WIPSCtmSensorEntry
    MAX-ACCESS not-accessible
    STATUS current
    DESCRIPTION
        "Each entry contains information about countermeasure all sensor."
    INDEX { h3cDot11WIPSCtmSensorPolicyName }
    ::= { h3cDot11WIPSCtmSensorTable 1 }

H3cDot11WIPSCtmSensorEntry ::= SEQUENCE {
        h3cDot11WIPSCtmSensorPolicyName        OCTET STRING,
        h3cDot11WIPSCtmSensoriStatus           H3cDot11WIPSEnabledStatus
     }

h3cDot11WIPSCtmSensorPolicyName OBJECT-TYPE
    SYNTAX OCTET STRING (SIZE (1..63))
    MAX-ACCESS not-accessible
    STATUS current
    DESCRIPTION
        "Represents the policy name."
    ::= { h3cDot11WIPSCtmSensorEntry 1 }

h3cDot11WIPSCtmSensoriStatus OBJECT-TYPE
    SYNTAX  H3cDot11WIPSEnabledStatus
    MAX-ACCESS read-write
    STATUS current
    DESCRIPTION
        "The status of this table entry."
    ::= { h3cDot11WIPSCtmSensorEntry 2 }


h3cDot11WIPSInvOuiStateTable OBJECT-TYPE
    SYNTAX SEQUENCE OF H3cDot11WIPSInvOuiStateEntry
    MAX-ACCESS not-accessible
    STATUS current
    DESCRIPTION
        "The table contains the invalid OUI classification information."
    ::= { h3cDot11WIPSConfigGroup 25 }

h3cDot11WIPSInvOuiStateEntry OBJECT-TYPE
    SYNTAX H3cDot11WIPSInvOuiStateEntry
    MAX-ACCESS not-accessible
    STATUS current
    DESCRIPTION
        "Each entry contains about status of invalid OUI classification."
    INDEX { h3cDot11WIPSInvOuiStaPlyName }
    ::= { h3cDot11WIPSInvOuiStateTable 1 }

H3cDot11WIPSInvOuiStateEntry ::= SEQUENCE {
        h3cDot11WIPSInvOuiStaPlyName       OCTET STRING,
        h3cDot11WIPSInvOuiStaiStatus       H3cDot11WIPSEnabledStatus
     }

h3cDot11WIPSInvOuiStaPlyName OBJECT-TYPE
    SYNTAX OCTET STRING (SIZE (1..63))
    MAX-ACCESS not-accessible
    STATUS current
    DESCRIPTION
        "Represents the policy name."
    ::= { h3cDot11WIPSInvOuiStateEntry 1 }

h3cDot11WIPSInvOuiStaiStatus OBJECT-TYPE
    SYNTAX  H3cDot11WIPSEnabledStatus
    MAX-ACCESS read-write
    STATUS current
    DESCRIPTION
        "The enable status of invalid OUI classification."
    ::= { h3cDot11WIPSInvOuiStateEntry 2 }

h3cDot11WIPSAPClaAuthTable OBJECT-TYPE
    SYNTAX SEQUENCE OF H3cDot11WIPSAPClaAuthEntry
    MAX-ACCESS not-accessible
    STATUS current
    DESCRIPTION
        "The table contains the enable status of
         WIPS AP classification authentication."
    ::= { h3cDot11WIPSConfigGroup 26 }

h3cDot11WIPSAPClaAuthEntry OBJECT-TYPE
    SYNTAX H3cDot11WIPSAPClaAuthEntry
    MAX-ACCESS not-accessible
    STATUS current
    DESCRIPTION
        "Each entry contains the enable status of
         WIPS AP classification authentication."
    INDEX { h3cDot11WIPSAPClaAuthRuleID }
    ::= { h3cDot11WIPSAPClaAuthTable 1 }

H3cDot11WIPSAPClaAuthEntry ::= SEQUENCE {
        h3cDot11WIPSAPClaAuthRuleID        Integer32,
        h3cDot11WIPSAPClaAuthMethod        H3cDot11WIPSAPClaAuthMethods,
        h3cDot11WIPSAPClaAuthType          H3cDot11WIPSAPClassifyCmpType,
        h3cDot11WIPSAPClaAuthStatus        H3cDot11WIPSEnabledStatus
     }

h3cDot11WIPSAPClaAuthRuleID OBJECT-TYPE
    SYNTAX Integer32 (1..65535)
    MAX-ACCESS not-accessible
    STATUS current
    DESCRIPTION
        "Represents the rule ID."
    ::= { h3cDot11WIPSAPClaAuthEntry 1 }

h3cDot11WIPSAPClaAuthMethod OBJECT-TYPE
    SYNTAX H3cDot11WIPSAPClaAuthMethods
    MAX-ACCESS read-write
    STATUS current
    DESCRIPTION
        "Represents the AP classification authentication method."
    ::= { h3cDot11WIPSAPClaAuthEntry 2 }

h3cDot11WIPSAPClaAuthType OBJECT-TYPE
    SYNTAX H3cDot11WIPSAPClassifyCmpType
    MAX-ACCESS read-write
    STATUS current
    DESCRIPTION
        "Represents the AP classification authentication compare type."
    ::= { h3cDot11WIPSAPClaAuthEntry 3 }

h3cDot11WIPSAPClaAuthStatus OBJECT-TYPE
    SYNTAX  H3cDot11WIPSEnabledStatus
    MAX-ACCESS read-write
    STATUS current
    DESCRIPTION
        "The enable status of AP classification authentication."
    ::= { h3cDot11WIPSAPClaAuthEntry 4 }

h3cDot11WIPSAPClaCltOnlTable OBJECT-TYPE
    SYNTAX SEQUENCE OF H3cDot11WIPSAPClaCltOnlEntry
    MAX-ACCESS not-accessible
    STATUS current
    DESCRIPTION
        "The table contains the enable status of
         AP classification clinet online."
    ::= { h3cDot11WIPSConfigGroup 27 }

h3cDot11WIPSAPClaCltOnlEntry OBJECT-TYPE
    SYNTAX H3cDot11WIPSAPClaCltOnlEntry
    MAX-ACCESS not-accessible
    STATUS current
    DESCRIPTION
        "Each entry contains the enable status of
         AP classification clinet online."
    INDEX { h3cDot11WIPSAPClaCltOnlRuleID }
    ::= { h3cDot11WIPSAPClaCltOnlTable 1 }

H3cDot11WIPSAPClaCltOnlEntry ::= SEQUENCE {
        h3cDot11WIPSAPClaCltOnlRuleID      Integer32,
        h3cDot11WIPSAPClaCltOnlV1          Integer32,
        h3cDot11WIPSAPClaCltOnlV2          Integer32,
        h3cDot11WIPSAPClaCltOnlSts         H3cDot11WIPSEnabledStatus
     }

h3cDot11WIPSAPClaCltOnlRuleID OBJECT-TYPE
    SYNTAX Integer32 (1..65535)
    MAX-ACCESS not-accessible
    STATUS current
    DESCRIPTION
        "Represents the rule ID."
    ::= { h3cDot11WIPSAPClaCltOnlEntry 1 }

h3cDot11WIPSAPClaCltOnlV1 OBJECT-TYPE
    SYNTAX Integer32 (0..128)
    MAX-ACCESS read-write
    STATUS current
    DESCRIPTION
        "Represents the AP classification clinet online value1."
    ::= { h3cDot11WIPSAPClaCltOnlEntry 2 }

h3cDot11WIPSAPClaCltOnlV2 OBJECT-TYPE
    SYNTAX Integer32 (0..128)
    MAX-ACCESS read-write
    STATUS current
    DESCRIPTION
        "Represents the AP classification clinet online value2."
    ::= { h3cDot11WIPSAPClaCltOnlEntry 3 }

h3cDot11WIPSAPClaCltOnlSts OBJECT-TYPE
    SYNTAX  H3cDot11WIPSEnabledStatus
    MAX-ACCESS read-write
    STATUS current
    DESCRIPTION
        "The enable status of WIPS AP classification clinet online."
    ::= { h3cDot11WIPSAPClaCltOnlEntry 4 }

h3cDot11WIPSAPClaDiscrTable OBJECT-TYPE
    SYNTAX SEQUENCE OF H3cDot11WIPSAPClaDiscrEntry
    MAX-ACCESS not-accessible
    STATUS current
    DESCRIPTION
        "The table contains the enable status of AP classification discover."
    ::= { h3cDot11WIPSConfigGroup 28 }

h3cDot11WIPSAPClaDiscrEntry OBJECT-TYPE
    SYNTAX H3cDot11WIPSAPClaDiscrEntry
    MAX-ACCESS not-accessible
    STATUS current
    DESCRIPTION
        "Each entry contains the enable status of AP classification discover."
    INDEX { h3cDot11WIPSAPClaDiscrRuleID }
    ::= { h3cDot11WIPSAPClaDiscrTable 1 }

H3cDot11WIPSAPClaDiscrEntry ::= SEQUENCE {
        h3cDot11WIPSAPClaDiscrRuleID       Integer32,
        h3cDot11WIPSAPClaDiscrV1           Integer32,
        h3cDot11WIPSAPClaDiscrV2           Integer32,
        h3cDot11WIPSAPClaDiscrSta          H3cDot11WIPSEnabledStatus
     }

h3cDot11WIPSAPClaDiscrRuleID OBJECT-TYPE
    SYNTAX Integer32 (1..65535)
    MAX-ACCESS not-accessible
    STATUS current
    DESCRIPTION
        "Represents the rule ID."
    ::= { h3cDot11WIPSAPClaDiscrEntry 1 }

h3cDot11WIPSAPClaDiscrV1 OBJECT-TYPE
    SYNTAX Integer32 (1..128)
    MAX-ACCESS read-write
    STATUS current
    DESCRIPTION
        "Represents the AP classification discover value1."
    ::= { h3cDot11WIPSAPClaDiscrEntry 2 }

h3cDot11WIPSAPClaDiscrV2 OBJECT-TYPE
    SYNTAX Integer32 (1..128)
    MAX-ACCESS read-write
    STATUS current
    DESCRIPTION
        "Represents the AP classification discover value2."
    ::= { h3cDot11WIPSAPClaDiscrEntry 3 }

h3cDot11WIPSAPClaDiscrSta OBJECT-TYPE
    SYNTAX  H3cDot11WIPSEnabledStatus
    MAX-ACCESS read-write
    STATUS current
    DESCRIPTION
        "The enable status of AP classification discover."
    ::= { h3cDot11WIPSAPClaDiscrEntry 4 }

--
-- APClassifyRssi
--
h3cDot11WIPSAPClaRssiTable OBJECT-TYPE
    SYNTAX SEQUENCE OF H3cDot11WIPSAPClaRssiEntry
    MAX-ACCESS not-accessible
    STATUS current
    DESCRIPTION
        "The table contains the enable status of AP classification rssi."
    ::= { h3cDot11WIPSConfigGroup 29 }

h3cDot11WIPSAPClaRssiEntry OBJECT-TYPE
    SYNTAX H3cDot11WIPSAPClaRssiEntry
    MAX-ACCESS not-accessible
    STATUS current
    DESCRIPTION
        "Each entry contains the enable status of AP classification rssi."
    INDEX { h3cDot11WIPSAPClaRssiRuleID }
    ::= { h3cDot11WIPSAPClaRssiTable 1 }

H3cDot11WIPSAPClaRssiEntry ::= SEQUENCE {
        h3cDot11WIPSAPClaRssiRuleID        Integer32,
        h3cDot11WIPSAPClaRssiV1            Integer32,
        h3cDot11WIPSAPClaRssiV2            Integer32,
        h3cDot11WIPSAPClaRssiSta           H3cDot11WIPSEnabledStatus
     }

h3cDot11WIPSAPClaRssiRuleID OBJECT-TYPE
    SYNTAX Integer32 (1..65535)
    MAX-ACCESS not-accessible
    STATUS current
    DESCRIPTION
        "Represents the rule ID."
    ::= { h3cDot11WIPSAPClaRssiEntry 1 }

h3cDot11WIPSAPClaRssiV1 OBJECT-TYPE
    SYNTAX Integer32 (0..100)
    MAX-ACCESS read-write
    STATUS current
    DESCRIPTION
        "Represents the AP classification rssi value1."
    ::= { h3cDot11WIPSAPClaRssiEntry 2 }

h3cDot11WIPSAPClaRssiV2 OBJECT-TYPE
    SYNTAX Integer32 (0..100)
    MAX-ACCESS read-write
    STATUS current
    DESCRIPTION
        "Represents the AP classification rssi value2."
    ::= { h3cDot11WIPSAPClaRssiEntry 3 }

h3cDot11WIPSAPClaRssiSta OBJECT-TYPE
    SYNTAX  H3cDot11WIPSEnabledStatus
    MAX-ACCESS read-write
    STATUS current
    DESCRIPTION
        "The enable status of AP classification rssi."
    ::= { h3cDot11WIPSAPClaRssiEntry 4 }

h3cDot11WIPSAPClaUpdurTable OBJECT-TYPE
    SYNTAX SEQUENCE OF H3cDot11WIPSAPClaUpdurEntry
    MAX-ACCESS not-accessible
    STATUS current
    DESCRIPTION
        "The table contains the enable status of AP classification upduration."
    ::= { h3cDot11WIPSConfigGroup 30 }

h3cDot11WIPSAPClaUpdurEntry OBJECT-TYPE
    SYNTAX H3cDot11WIPSAPClaUpdurEntry
    MAX-ACCESS not-accessible
    STATUS current
    DESCRIPTION
        "Each entry contains the enable status of AP classification upduration."
    INDEX { h3cDot11WIPSAPClaUpdurRuleID }
    ::= { h3cDot11WIPSAPClaUpdurTable 1 }

H3cDot11WIPSAPClaUpdurEntry ::= SEQUENCE {
        h3cDot11WIPSAPClaUpdurRuleID       Integer32,
        h3cDot11WIPSAPClaUpdurV1           Integer32,
        h3cDot11WIPSAPClaUpdurV2           Integer32,
        h3cDot11WIPSAPClaUpdurSta          H3cDot11WIPSEnabledStatus
     }

h3cDot11WIPSAPClaUpdurRuleID OBJECT-TYPE
    SYNTAX Integer32 (1..65535)
    MAX-ACCESS not-accessible
    STATUS current
    DESCRIPTION
        "Represents the rule ID."
    ::= { h3cDot11WIPSAPClaUpdurEntry 1 }

h3cDot11WIPSAPClaUpdurV1 OBJECT-TYPE
    SYNTAX Integer32 (0..2592000)
    MAX-ACCESS read-write
    STATUS current
    DESCRIPTION
        "Represents the AP classification upduration value1."
    ::= { h3cDot11WIPSAPClaUpdurEntry 2 }

h3cDot11WIPSAPClaUpdurV2 OBJECT-TYPE
    SYNTAX Integer32 (0..2592000)
    MAX-ACCESS read-write
    STATUS current
    DESCRIPTION
        "Represents the AP classification upduration value2."
    ::= { h3cDot11WIPSAPClaUpdurEntry 3 }

h3cDot11WIPSAPClaUpdurSta OBJECT-TYPE
    SYNTAX  H3cDot11WIPSEnabledStatus
    MAX-ACCESS read-write
    STATUS current
    DESCRIPTION
        "The enable status of AP classification upduration."
    ::= { h3cDot11WIPSAPClaUpdurEntry 4 }

h3cDot11WIPSAPClaOuiTable OBJECT-TYPE
    SYNTAX SEQUENCE OF H3cDot11WIPSAPClaOuiEntry
    MAX-ACCESS not-accessible
    STATUS current
    DESCRIPTION
        "The table contains the enable status of AP classification oui."
    ::= { h3cDot11WIPSConfigGroup 31 }

h3cDot11WIPSAPClaOuiEntry OBJECT-TYPE
    SYNTAX H3cDot11WIPSAPClaOuiEntry
    MAX-ACCESS not-accessible
    STATUS current
    DESCRIPTION
        "Each entry contains the enable status of AP classification oui."
    INDEX { h3cDot11WIPSAPClaOuiRuleID }
    ::= { h3cDot11WIPSAPClaOuiTable 1 }

H3cDot11WIPSAPClaOuiEntry ::= SEQUENCE {
        h3cDot11WIPSAPClaOuiRuleID        Integer32,
        h3cDot11WIPSAPClaOuiMac           H3cDot11WIPSOuiAddress,
        h3cDot11WIPSAPClaOuiStatus        H3cDot11WIPSEnabledStatus
     }

h3cDot11WIPSAPClaOuiRuleID OBJECT-TYPE
    SYNTAX Integer32 (1..65535)
    MAX-ACCESS not-accessible
    STATUS current
    DESCRIPTION
        "Represents the rule ID."
    ::= { h3cDot11WIPSAPClaOuiEntry 1 }

h3cDot11WIPSAPClaOuiMac OBJECT-TYPE
    SYNTAX H3cDot11WIPSOuiAddress
    MAX-ACCESS read-write
    STATUS current
    DESCRIPTION
        "Represents the AP classification oui."
    ::= { h3cDot11WIPSAPClaOuiEntry 2 }

h3cDot11WIPSAPClaOuiStatus OBJECT-TYPE
    SYNTAX  H3cDot11WIPSEnabledStatus
    MAX-ACCESS read-write
    STATUS current
    DESCRIPTION
        "The enable status of AP classification oui."
    ::= { h3cDot11WIPSAPClaOuiEntry 3 }

h3cDot11WIPSAPClaSryTable OBJECT-TYPE
    SYNTAX SEQUENCE OF H3cDot11WIPSAPClaSryEntry
    MAX-ACCESS not-accessible
    STATUS current
    DESCRIPTION
        "The table contains the enable status of AP classification security."
    ::= { h3cDot11WIPSConfigGroup 32 }

h3cDot11WIPSAPClaSryEntry OBJECT-TYPE
    SYNTAX H3cDot11WIPSAPClaSryEntry
    MAX-ACCESS not-accessible
    STATUS current
    DESCRIPTION
        "Each entry contains the enable status of AP classification security."
    INDEX { h3cDot11WIPSAPClaSryRuleID }
    ::= { h3cDot11WIPSAPClaSryTable 1 }

H3cDot11WIPSAPClaSryEntry ::= SEQUENCE {
        h3cDot11WIPSAPClaSryRuleID         Integer32,
        h3cDot11WIPSAPClaSryType           H3cDot11WIPSAPClaSecurityType,
        h3cDot11WIPSAPClaSryCmpType        H3cDot11WIPSAPClassifyCmpType,
        h3cDot11WIPSAPClaSrySta            H3cDot11WIPSEnabledStatus
     }

h3cDot11WIPSAPClaSryRuleID OBJECT-TYPE
    SYNTAX Integer32 (1..65535)
    MAX-ACCESS not-accessible
    STATUS current
    DESCRIPTION
        "Represents the rule ID."
    ::= { h3cDot11WIPSAPClaSryEntry 1 }

h3cDot11WIPSAPClaSryType OBJECT-TYPE
    SYNTAX H3cDot11WIPSAPClaSecurityType
    MAX-ACCESS read-write
    STATUS current
    DESCRIPTION
        "Represents the AP classification security."
    ::= { h3cDot11WIPSAPClaSryEntry 2 }

h3cDot11WIPSAPClaSryCmpType OBJECT-TYPE
    SYNTAX H3cDot11WIPSAPClassifyCmpType
    MAX-ACCESS read-write
    STATUS current
    DESCRIPTION
        "Represents the AP classification security."
    ::= { h3cDot11WIPSAPClaSryEntry 3 }

h3cDot11WIPSAPClaSrySta OBJECT-TYPE
    SYNTAX  H3cDot11WIPSEnabledStatus
    MAX-ACCESS read-write
    STATUS current
    DESCRIPTION
        "The enable status of AP classification security."
    ::= { h3cDot11WIPSAPClaSryEntry 4 }

h3cDot11WIPSAPClaSsidTable OBJECT-TYPE
    SYNTAX SEQUENCE OF H3cDot11WIPSAPClaSsidEntry
    MAX-ACCESS not-accessible
    STATUS current
    DESCRIPTION
        "The table contains the enable status of AP classification ssid."
    ::= { h3cDot11WIPSConfigGroup 33 }

h3cDot11WIPSAPClaSsidEntry OBJECT-TYPE
    SYNTAX H3cDot11WIPSAPClaSsidEntry
    MAX-ACCESS not-accessible
    STATUS current
    DESCRIPTION
        "Each entry contains the enable status of AP classification ssid."
    INDEX { h3cDot11WIPSAPClaSsidRuleID }
    ::= { h3cDot11WIPSAPClaSsidTable 1 }

H3cDot11WIPSAPClaSsidEntry ::= SEQUENCE {
        h3cDot11WIPSAPClaSsidRuleID         Integer32,
        h3cDot11WIPSAPClaSsidName           OCTET STRING,
        h3cDot11WIPSAPClaSsidcase           TruthValue,
        h3cDot11WIPSAPClaSsidCmpType        H3cDot11WIPSAPClasSsidCmpType,
        h3cDot11WIPSAPClaSsidStatus         H3cDot11WIPSEnabledStatus
     }

h3cDot11WIPSAPClaSsidRuleID OBJECT-TYPE
    SYNTAX Integer32 (1..65535)
    MAX-ACCESS not-accessible
    STATUS current
    DESCRIPTION
        "Represents the rule ID."
    ::= { h3cDot11WIPSAPClaSsidEntry 1 }

h3cDot11WIPSAPClaSsidName OBJECT-TYPE
    SYNTAX OCTET STRING (SIZE (1..32))
    MAX-ACCESS read-write
    STATUS current
    DESCRIPTION
        "Represents the AP classification ssid name."
    ::= { h3cDot11WIPSAPClaSsidEntry 2 }

h3cDot11WIPSAPClaSsidcase OBJECT-TYPE
    SYNTAX TruthValue
    MAX-ACCESS read-write
    STATUS current
    DESCRIPTION
        "Represents the AP classification case-sensitive."
    ::= { h3cDot11WIPSAPClaSsidEntry 3 }

h3cDot11WIPSAPClaSsidCmpType OBJECT-TYPE
    SYNTAX H3cDot11WIPSAPClasSsidCmpType
    MAX-ACCESS read-write
    STATUS current
    DESCRIPTION
        "Represents the AP classification ssid compare type."
    ::= { h3cDot11WIPSAPClaSsidEntry 4 }

h3cDot11WIPSAPClaSsidStatus OBJECT-TYPE
    SYNTAX  H3cDot11WIPSEnabledStatus
    MAX-ACCESS read-write
    STATUS current
    DESCRIPTION
        "The enable status of AP classification ssid."
    ::= { h3cDot11WIPSAPClaSsidEntry 5 }

h3cDot11WIPSDtcSigTable OBJECT-TYPE
    SYNTAX SEQUENCE OF H3cDot11WIPSDtcSigEntry
    MAX-ACCESS not-accessible
    STATUS current
    DESCRIPTION
        "The table provides information about detect signature."
    ::= { h3cDot11WIPSConfigGroup 34 }

h3cDot11WIPSDtcSigEntry OBJECT-TYPE
    SYNTAX H3cDot11WIPSDtcSigEntry
    MAX-ACCESS not-accessible
    STATUS current
    DESCRIPTION
        "Each entry contains information about signature detect."
    INDEX { h3cDot11WIPSDtcSigPolicyName }
    ::= { h3cDot11WIPSDtcSigTable 1 }

H3cDot11WIPSDtcSigEntry ::= SEQUENCE {
        h3cDot11WIPSDtcSigPolicyName               OCTET STRING,
        h3cDot11WIPSDtcSigInterval                 Integer32,
        h3cDot11WIPSDtcSigQuiet                    Integer32,
        h3cDot11WIPSDtcSigThreshold                Integer32,
        h3cDot11WIPSDtcSigStatus                   H3cDot11WIPSEnabledStatus
      }

h3cDot11WIPSDtcSigPolicyName OBJECT-TYPE
    SYNTAX OCTET STRING (SIZE (1..63))
    MAX-ACCESS not-accessible
    STATUS current
    DESCRIPTION
        "Represents the name of the policy."
    ::= { h3cDot11WIPSDtcSigEntry 1 }

h3cDot11WIPSDtcSigInterval OBJECT-TYPE
    SYNTAX Integer32 (1..3600)
    MAX-ACCESS read-write
    STATUS current
    DESCRIPTION
        "Represents the interval of signature detect."
    ::= { h3cDot11WIPSDtcSigEntry 2 }

h3cDot11WIPSDtcSigQuiet OBJECT-TYPE
    SYNTAX Integer32 (5..604800)
    MAX-ACCESS read-write
    STATUS current
    DESCRIPTION
        "Represents the quiet of signature detect."
    ::= { h3cDot11WIPSDtcSigEntry 3 }

h3cDot11WIPSDtcSigThreshold OBJECT-TYPE
    SYNTAX Integer32 (1..100000)
    MAX-ACCESS read-write
    STATUS current
    DESCRIPTION
        "Represents the threshold of signature detect."
    ::= { h3cDot11WIPSDtcSigEntry 4 }

h3cDot11WIPSDtcSigStatus OBJECT-TYPE
    SYNTAX H3cDot11WIPSEnabledStatus
    MAX-ACCESS read-write
    STATUS current
    DESCRIPTION
        "The status of this table entry."
    ::= { h3cDot11WIPSDtcSigEntry 5 }

h3cDot11WIPSPolicyTable OBJECT-TYPE
    SYNTAX SEQUENCE OF H3cDot11WIPSPolicyEntry
    MAX-ACCESS not-accessible
    STATUS current
    DESCRIPTION
        "The table provides information about policy."
    ::= { h3cDot11WIPSConfigGroup 35 }

h3cDot11WIPSPolicyEntry OBJECT-TYPE
    SYNTAX H3cDot11WIPSPolicyEntry
    MAX-ACCESS not-accessible
    STATUS current
    DESCRIPTION
        "Each entry contains the enable status of policy configuration."
    INDEX { h3cDot11WIPSPolicyType ,h3cDot11WIPSPolicyName}
    ::= { h3cDot11WIPSPolicyTable 1 }

H3cDot11WIPSPolicyEntry ::= SEQUENCE {
        h3cDot11WIPSPolicyType                 H3cDot11WIPSPolicyTypeValue,
        h3cDot11WIPSPolicyName                 OCTET STRING,
        h3cDot11WIPSPolicyRowStatus            RowStatus
     }

h3cDot11WIPSPolicyType OBJECT-TYPE
    SYNTAX H3cDot11WIPSPolicyTypeValue
    MAX-ACCESS not-accessible
    STATUS current
    DESCRIPTION
        "Represents the type of policy."
    ::= { h3cDot11WIPSPolicyEntry 1 }

h3cDot11WIPSPolicyName OBJECT-TYPE
    SYNTAX OCTET STRING (SIZE (1..63))
    MAX-ACCESS not-accessible
    STATUS current
    DESCRIPTION
        "Represents the name of the policy."
    ::= { h3cDot11WIPSPolicyEntry 2 }

h3cDot11WIPSPolicyRowStatus OBJECT-TYPE
    SYNTAX RowStatus
    MAX-ACCESS read-create
    STATUS current
    DESCRIPTION
        "The status of this table entry."
    ::= { h3cDot11WIPSPolicyEntry 3 }

h3cDot11WIPSSigFrameTypeTable OBJECT-TYPE
    SYNTAX SEQUENCE OF H3cDot11WIPSSigFrameTypeEntry
    MAX-ACCESS not-accessible
    STATUS current
    DESCRIPTION
        "The table contains the enable status of signature frame type."
    ::= { h3cDot11WIPSConfigGroup 36 }

h3cDot11WIPSSigFrameTypeEntry OBJECT-TYPE
    SYNTAX H3cDot11WIPSSigFrameTypeEntry
    MAX-ACCESS not-accessible
    STATUS current
    DESCRIPTION
        "Each entry contains the status of signature frame type."
    INDEX { h3cDot11WIPSSigFrameTypeRuleId }
    ::= { h3cDot11WIPSSigFrameTypeTable 1 }

H3cDot11WIPSSigFrameTypeEntry ::= SEQUENCE {
        h3cDot11WIPSSigFrameTypeRuleId         Integer32,
        h3cDot11WIPSSigFrameType               H3cDot11WIPSSigFrameTypes,
        h3cDot11WIPSSigFrameSubType            H3cDot11WIPSSigFrameSubTypes,
        h3cDot11WIPSSigFrameTypeStatus         H3cDot11WIPSEnabledStatus
     }

h3cDot11WIPSSigFrameTypeRuleId OBJECT-TYPE
    SYNTAX Integer32 (1..65535)
    MAX-ACCESS not-accessible
    STATUS current
    DESCRIPTION
        "Represents the signature rule ID."
    ::= { h3cDot11WIPSSigFrameTypeEntry 1 }

h3cDot11WIPSSigFrameType OBJECT-TYPE
    SYNTAX H3cDot11WIPSSigFrameTypes
    MAX-ACCESS read-write
    STATUS current
    DESCRIPTION
        "Represents the signature frame type."
    ::= { h3cDot11WIPSSigFrameTypeEntry 2 }

h3cDot11WIPSSigFrameSubType OBJECT-TYPE
    SYNTAX H3cDot11WIPSSigFrameSubTypes
    MAX-ACCESS read-write
    STATUS current
    DESCRIPTION
        "Represents the signature frame subtype."
    ::= { h3cDot11WIPSSigFrameTypeEntry 3 }

h3cDot11WIPSSigFrameTypeStatus OBJECT-TYPE
    SYNTAX  H3cDot11WIPSEnabledStatus
    MAX-ACCESS read-write
    STATUS current
    DESCRIPTION
        "The enable status of signature frame type."
    ::= { h3cDot11WIPSSigFrameTypeEntry 4 }

h3cDot11WIPSCtmTable OBJECT-TYPE
    SYNTAX SEQUENCE OF H3cDot11WIPSCtmEntry
    MAX-ACCESS not-accessible
    STATUS current
    DESCRIPTION
        "The table contains the countermeasure commands."
    ::= { h3cDot11WIPSConfigGroup 37 }

h3cDot11WIPSCtmEntry OBJECT-TYPE
    SYNTAX H3cDot11WIPSCtmEntry
    MAX-ACCESS not-accessible
    STATUS current
    DESCRIPTION
        "Each entry contains the enable command of countermeasure."
    INDEX { h3cDot11WIPSCtmPolicyName, h3cDot11WIPSCtmClassifyType }
    ::= { h3cDot11WIPSCtmTable 1 }

H3cDot11WIPSCtmEntry ::= SEQUENCE {
        h3cDot11WIPSCtmPolicyName       OCTET STRING,
        h3cDot11WIPSCtmClassifyType     H3cDot11WIPSCtmType,
        h3cDot11WIPSCtmStatus           H3cDot11WIPSEnabledStatus
     }

h3cDot11WIPSCtmPolicyName OBJECT-TYPE
    SYNTAX OCTET STRING (SIZE (1..63))
    MAX-ACCESS not-accessible
    STATUS current
    DESCRIPTION
        "Represents the countermeasure policy name."
    ::= { h3cDot11WIPSCtmEntry 1 }

h3cDot11WIPSCtmClassifyType OBJECT-TYPE
    SYNTAX H3cDot11WIPSCtmType
    MAX-ACCESS not-accessible
    STATUS current
    DESCRIPTION
        "Represents a countermeasure command identifier."
    ::= { h3cDot11WIPSCtmEntry 2 }

h3cDot11WIPSCtmStatus OBJECT-TYPE
    SYNTAX  H3cDot11WIPSEnabledStatus
    MAX-ACCESS read-write
    STATUS current
    DESCRIPTION
        "The enable status of one countermeasure command."
    ::= { h3cDot11WIPSCtmEntry 3 }

h3cDot11WIPSSigPatternTable OBJECT-TYPE
    SYNTAX SEQUENCE OF H3cDot11WIPSSigPatternEntry
    MAX-ACCESS not-accessible
    STATUS current
    DESCRIPTION
        "The table defines signature pattern."
    ::= { h3cDot11WIPSConfigGroup 38 }

h3cDot11WIPSSigPatternEntry OBJECT-TYPE
    SYNTAX H3cDot11WIPSSigPatternEntry
    MAX-ACCESS not-accessible
    STATUS current
    DESCRIPTION
        "Each entry contains information about signature pattern."
    INDEX { h3cDot11WIPSSigPatternRuleId, h3cDot11WIPSSigPatternNum }
    ::= { h3cDot11WIPSSigPatternTable 1 }

H3cDot11WIPSSigPatternEntry ::= SEQUENCE {
        h3cDot11WIPSSigPatternRuleId           Integer32,
        h3cDot11WIPSSigPatternNum              Integer32,
        h3cDot11WIPSSigPatternOffset           Integer32,
        h3cDot11WIPSSigPatternMask             OCTET STRING,
        h3cDot11WIPSSigPatternValue1           Integer32,
        h3cDot11WIPSSigPatternValue2           Integer32,
        h3cDot11WIPSSigPatternFromPld          TruthValue,
        h3cDot11WIPSSigPatternRowStatus        RowStatus
     }

h3cDot11WIPSSigPatternRuleId OBJECT-TYPE
    SYNTAX Integer32 (1..65535)
    MAX-ACCESS not-accessible
    STATUS current
    DESCRIPTION
        "Represents the signature pattern rule id."
    ::= { h3cDot11WIPSSigPatternEntry 1 }

h3cDot11WIPSSigPatternNum OBJECT-TYPE
    SYNTAX Integer32 (0..65535)
    MAX-ACCESS not-accessible
    STATUS current
    DESCRIPTION
        "Represents the signature pattern pattern number."
    ::= { h3cDot11WIPSSigPatternEntry 2 }

h3cDot11WIPSSigPatternOffset OBJECT-TYPE
    SYNTAX Integer32 (0..2346)
    MAX-ACCESS read-create
    STATUS current
    DESCRIPTION
        "Represents the signature pattern offset."
    ::= { h3cDot11WIPSSigPatternEntry 3 }

h3cDot11WIPSSigPatternMask OBJECT-TYPE
    SYNTAX OCTET STRING (SIZE (1..4))
    MAX-ACCESS read-create
    STATUS current
    DESCRIPTION
        "Represents the signature pattern mask."
    ::= { h3cDot11WIPSSigPatternEntry 4 }

h3cDot11WIPSSigPatternValue1 OBJECT-TYPE
    SYNTAX Integer32 (0..65535)
    MAX-ACCESS read-create
    STATUS current
    DESCRIPTION
        "Represents the signature pattern value1."
    ::= { h3cDot11WIPSSigPatternEntry 5 }

h3cDot11WIPSSigPatternValue2 OBJECT-TYPE
    SYNTAX Integer32 (0..65535)
    MAX-ACCESS read-create
    STATUS current
    DESCRIPTION
        "Represents the signature pattern value2."
    ::= { h3cDot11WIPSSigPatternEntry 6 }

h3cDot11WIPSSigPatternFromPld OBJECT-TYPE
    SYNTAX TruthValue
    MAX-ACCESS read-create
    STATUS current
    DESCRIPTION
        "Represents the signature pattern frome payload."
    ::= { h3cDot11WIPSSigPatternEntry 7 }

h3cDot11WIPSSigPatternRowStatus OBJECT-TYPE
    SYNTAX RowStatus
    MAX-ACCESS read-create
    STATUS current
    DESCRIPTION
        "The status of this table entry."
    ::= { h3cDot11WIPSSigPatternEntry 8 }

h3cDot11WIPSSigSeqNumTable OBJECT-TYPE
    SYNTAX SEQUENCE OF H3cDot11WIPSSigSeqNumEntry
    MAX-ACCESS not-accessible
    STATUS current
    DESCRIPTION
        "The table contains the infomation about signature sequence number."
    ::= { h3cDot11WIPSConfigGroup 39 }

h3cDot11WIPSSigSeqNumEntry OBJECT-TYPE
    SYNTAX H3cDot11WIPSSigSeqNumEntry
    MAX-ACCESS not-accessible
    STATUS current
    DESCRIPTION
        "Each entry contains the infomation about signature sequence number."
    INDEX { h3cDot11WIPSSigSeqNumRuleId }
    ::= { h3cDot11WIPSSigSeqNumTable 1 }

H3cDot11WIPSSigSeqNumEntry ::= SEQUENCE {
        h3cDot11WIPSSigSeqNumRuleId          Integer32,
        h3cDot11WIPSSigSeqNumValue1          Integer32,
        h3cDot11WIPSSigSeqNumValue2          Integer32,
        h3cDot11WIPSSigSeqNumStatus          H3cDot11WIPSEnabledStatus
     }

h3cDot11WIPSSigSeqNumRuleId OBJECT-TYPE
    SYNTAX Integer32 (1..65535)
    MAX-ACCESS not-accessible
    STATUS current
    DESCRIPTION
        "Represents the signature rule ID."
    ::= { h3cDot11WIPSSigSeqNumEntry 1 }

h3cDot11WIPSSigSeqNumValue1 OBJECT-TYPE
    SYNTAX Integer32 (0..4095)
    MAX-ACCESS read-write
    STATUS current
    DESCRIPTION
        "Represents sequence number value1."
    ::= { h3cDot11WIPSSigSeqNumEntry 2 }

h3cDot11WIPSSigSeqNumValue2 OBJECT-TYPE
    SYNTAX Integer32 (0..4095)
    MAX-ACCESS read-write
    STATUS current
    DESCRIPTION
        "Represents sequence number value2 ."
    ::= { h3cDot11WIPSSigSeqNumEntry 3 }

h3cDot11WIPSSigSeqNumStatus OBJECT-TYPE
    SYNTAX  H3cDot11WIPSEnabledStatus
    MAX-ACCESS read-write
    STATUS current
    DESCRIPTION
        "The enable status of signature sequence number."
    ::= { h3cDot11WIPSSigSeqNumEntry 4 }

h3cDot11WIPSSigSsidTable OBJECT-TYPE
    SYNTAX SEQUENCE OF H3cDot11WIPSSigSsidEntry
    MAX-ACCESS not-accessible
    STATUS current
    DESCRIPTION
        "The table contains the infomation about signature SSID."
    ::= { h3cDot11WIPSConfigGroup 40 }

h3cDot11WIPSSigSsidEntry OBJECT-TYPE
    SYNTAX H3cDot11WIPSSigSsidEntry
    MAX-ACCESS not-accessible
    STATUS current
    DESCRIPTION
        "Each entry contains the infomation about signature SSID."
    INDEX { h3cDot11WIPSSigSsidRuleId }
    ::= { h3cDot11WIPSSigSsidTable 1 }

H3cDot11WIPSSigSsidEntry ::= SEQUENCE {
        h3cDot11WIPSSigSsidRuleId            Integer32,
        h3cDot11WIPSSigSsidSsid              OCTET STRING,
        h3cDot11WIPSSigSsidCase              TruthValue,
        h3cDot11WIPSSigSsidMatchType         H3cDot11WIPSSigSsidMatchTypes,
        h3cDot11WIPSSigSsidStatus            H3cDot11WIPSEnabledStatus
     }

h3cDot11WIPSSigSsidRuleId OBJECT-TYPE
    SYNTAX Integer32 (1..65535)
    MAX-ACCESS not-accessible
    STATUS current
    DESCRIPTION
        "Represents the signature rule ID."
    ::= { h3cDot11WIPSSigSsidEntry 1 }

h3cDot11WIPSSigSsidSsid OBJECT-TYPE
    SYNTAX OCTET STRING (SIZE (1..32))
    MAX-ACCESS read-write
    STATUS current
    DESCRIPTION
        "Represents the name of signature SSID."
    ::= { h3cDot11WIPSSigSsidEntry 2 }

h3cDot11WIPSSigSsidCase OBJECT-TYPE
    SYNTAX TruthValue
    MAX-ACCESS read-write
    STATUS current
    DESCRIPTION
        "Represents the case sensitive of signature SSID."
    ::= { h3cDot11WIPSSigSsidEntry 3 }

h3cDot11WIPSSigSsidMatchType OBJECT-TYPE
    SYNTAX H3cDot11WIPSSigSsidMatchTypes
    MAX-ACCESS read-write
    STATUS current
    DESCRIPTION
        "Represents the match type of signature SSID."
    ::= { h3cDot11WIPSSigSsidEntry 4 }

h3cDot11WIPSSigSsidStatus OBJECT-TYPE
    SYNTAX  H3cDot11WIPSEnabledStatus
    MAX-ACCESS read-write
    STATUS current
    DESCRIPTION
        "The enable status of signature SSID."
    ::= { h3cDot11WIPSSigSsidEntry 5 }

h3cDot11WIPSSigSsidLengthTable OBJECT-TYPE
    SYNTAX SEQUENCE OF H3cDot11WIPSSigSsidLengthEntry
    MAX-ACCESS not-accessible
    STATUS current
    DESCRIPTION
        "The table contains the infomation about signature SSID length."
    ::= { h3cDot11WIPSConfigGroup 41 }

h3cDot11WIPSSigSsidLengthEntry OBJECT-TYPE
    SYNTAX H3cDot11WIPSSigSsidLengthEntry
    MAX-ACCESS not-accessible
    STATUS current
    DESCRIPTION
        "Each entry contains the infomation about signature SSID length."
    INDEX { h3cDot11WIPSSigSsidLengthRuleId }
    ::= { h3cDot11WIPSSigSsidLengthTable 1 }

H3cDot11WIPSSigSsidLengthEntry ::= SEQUENCE {
        h3cDot11WIPSSigSsidLengthRuleId          Integer32,
        h3cDot11WIPSSigSsidLengthValue1          Integer32,
        h3cDot11WIPSSigSsidLengthValue2          Integer32,
        h3cDot11WIPSSigSsidLengthStatus          H3cDot11WIPSEnabledStatus
     }

h3cDot11WIPSSigSsidLengthRuleId OBJECT-TYPE
    SYNTAX Integer32 (1..65535)
    MAX-ACCESS not-accessible
    STATUS current
    DESCRIPTION
        "Represents the signature rule ID."
    ::= { h3cDot11WIPSSigSsidLengthEntry 1 }

h3cDot11WIPSSigSsidLengthValue1 OBJECT-TYPE
    SYNTAX Integer32 (1..32)
    MAX-ACCESS read-write
    STATUS current
    DESCRIPTION
        "Represents signature SSID length value1."
    ::= { h3cDot11WIPSSigSsidLengthEntry 2 }

h3cDot11WIPSSigSsidLengthValue2 OBJECT-TYPE
    SYNTAX Integer32 (1..32)
    MAX-ACCESS read-write
    STATUS current
    DESCRIPTION
        "Represents signature SSID length value2 ."
    ::= { h3cDot11WIPSSigSsidLengthEntry 3 }

h3cDot11WIPSSigSsidLengthStatus OBJECT-TYPE
    SYNTAX  H3cDot11WIPSEnabledStatus
    MAX-ACCESS read-write
    STATUS current
    DESCRIPTION
        "The enable status of signature SSID length."
    ::= { h3cDot11WIPSSigSsidLengthEntry 4 }

h3cDot11WIPSFldDetectTable OBJECT-TYPE
    SYNTAX SEQUENCE OF H3cDot11WIPSFldDetectEntry
    MAX-ACCESS not-accessible
    STATUS current
    DESCRIPTION
        "This table contains the flood detect information."
    ::= { h3cDot11WIPSConfigGroup 42 }

h3cDot11WIPSFldDetectEntry OBJECT-TYPE
    SYNTAX H3cDot11WIPSFldDetectEntry
    MAX-ACCESS not-accessible
    STATUS current
    DESCRIPTION
        "Each entry contains information about one type of flood detect."
    INDEX { h3cDot11WIPSFldDetectPlyName, h3cDot11WIPSFldDetectType }
    ::= { h3cDot11WIPSFldDetectTable 1 }

H3cDot11WIPSFldDetectEntry ::= SEQUENCE {
        h3cDot11WIPSFldDetectPlyName       OCTET STRING,
        h3cDot11WIPSFldDetectType          H3cDot11WIPSFldDctType,
        h3cDot11WIPSFldDetectInter         Integer32,
        h3cDot11WIPSFldDetectThresh        Integer32,
        h3cDot11WIPSFldDetectQuiet         Integer32,
        h3cDot11WIPSFldDetectStatus        H3cDot11WIPSEnabledStatus
     }

h3cDot11WIPSFldDetectPlyName OBJECT-TYPE
    SYNTAX OCTET STRING (SIZE (1..63))
    MAX-ACCESS not-accessible
    STATUS current
    DESCRIPTION
        "Represents the policy name of detect."
    ::= { h3cDot11WIPSFldDetectEntry 1 }

h3cDot11WIPSFldDetectType OBJECT-TYPE
    SYNTAX H3cDot11WIPSFldDctType
    MAX-ACCESS not-accessible
    STATUS current
    DESCRIPTION
        "Represents the type of flood detect."
    ::= { h3cDot11WIPSFldDetectEntry 2 }

h3cDot11WIPSFldDetectInter OBJECT-TYPE
    SYNTAX Integer32 (1..3600)
    MAX-ACCESS read-write
    STATUS current
    DESCRIPTION
        "Represents the interval of flood detect."
    ::= { h3cDot11WIPSFldDetectEntry 3 }

h3cDot11WIPSFldDetectThresh OBJECT-TYPE
    SYNTAX Integer32 (1..100000)
    MAX-ACCESS read-write
    STATUS current
    DESCRIPTION
        "Represents the threshold of flood detect."
    ::= { h3cDot11WIPSFldDetectEntry 4 }

h3cDot11WIPSFldDetectQuiet OBJECT-TYPE
    SYNTAX Integer32 (5..604800)
    MAX-ACCESS read-write
    STATUS current
    DESCRIPTION
        "Represents the quiet time of flood detect."
    ::= { h3cDot11WIPSFldDetectEntry 5 }

h3cDot11WIPSFldDetectStatus OBJECT-TYPE
    SYNTAX H3cDot11WIPSEnabledStatus
    MAX-ACCESS read-write
    STATUS current
    DESCRIPTION
         "The enable status of flood detect."
    ::= { h3cDot11WIPSFldDetectEntry 6 }

h3cDot11WIPSSignatureMacTable OBJECT-TYPE
    SYNTAX SEQUENCE OF H3cDot11WIPSSignatureMacEntry
    MAX-ACCESS not-accessible
    STATUS current
    DESCRIPTION
        "The table contains the infomation about signature MAC address."
    ::= { h3cDot11WIPSConfigGroup 43 }

h3cDot11WIPSSignatureMacEntry OBJECT-TYPE
    SYNTAX H3cDot11WIPSSignatureMacEntry
    MAX-ACCESS not-accessible
    STATUS current
    DESCRIPTION
        "Each entry contains the infomation about signature MAC address."
    INDEX { h3cDot11WIPSSignatureMacRuleId }
    ::= { h3cDot11WIPSSignatureMacTable 1 }

H3cDot11WIPSSignatureMacEntry ::= SEQUENCE {
        h3cDot11WIPSSignatureMacRuleId           Integer32,
        h3cDot11WIPSSignatureMacMacTyp           H3cDot11WIPSSigMacMacType,
        h3cDot11WIPSSignatureMacMacAdd           MacAddress,
        h3cDot11WIPSSignatureMacStatus           H3cDot11WIPSEnabledStatus
     }

h3cDot11WIPSSignatureMacRuleId OBJECT-TYPE
    SYNTAX Integer32 (1..65535)
    MAX-ACCESS not-accessible
    STATUS current
    DESCRIPTION
        "Represents the signature rule ID."
    ::= { h3cDot11WIPSSignatureMacEntry 1 }

h3cDot11WIPSSignatureMacMacTyp OBJECT-TYPE
    SYNTAX H3cDot11WIPSSigMacMacType
    MAX-ACCESS read-write
    STATUS current
    DESCRIPTION
        "Represents the type of signature MAC address."
    ::= { h3cDot11WIPSSignatureMacEntry 2 }

h3cDot11WIPSSignatureMacMacAdd OBJECT-TYPE
    SYNTAX MacAddress
    MAX-ACCESS read-write
    STATUS current
    DESCRIPTION
        "Represents the MAC address of signature MAC address."
    ::= { h3cDot11WIPSSignatureMacEntry 3 }

h3cDot11WIPSSignatureMacStatus OBJECT-TYPE
    SYNTAX  H3cDot11WIPSEnabledStatus
    MAX-ACCESS read-write
    STATUS current
    DESCRIPTION
        "The enable status of signature MAC address."
    ::= { h3cDot11WIPSSignatureMacEntry 4 }

h3cDot11WIPSNatDetectTable OBJECT-TYPE
    SYNTAX SEQUENCE OF H3cDot11WIPSNatDetectEntry
    MAX-ACCESS not-accessible
    STATUS current
    DESCRIPTION
        "The table contains the enable status of WIPS NAT detect."
    ::= { h3cDot11WIPSConfigGroup 45 }

h3cDot11WIPSNatDetectEntry OBJECT-TYPE
    SYNTAX H3cDot11WIPSNatDetectEntry
    MAX-ACCESS not-accessible
    STATUS current
    DESCRIPTION
        "Each entry contains the enable status of NAT detect."
    INDEX { h3cDot11WIPSNatDetectApName }
    ::= { h3cDot11WIPSNatDetectTable 1 }

H3cDot11WIPSNatDetectEntry ::= SEQUENCE {
        h3cDot11WIPSNatDetectApName       OCTET STRING,
        h3cDot11WIPSNatDetectStatus       H3cDot11WIPSEnabledStatus
     }

h3cDot11WIPSNatDetectApName OBJECT-TYPE
    SYNTAX OCTET STRING (SIZE (1..64))
    MAX-ACCESS not-accessible
    STATUS current
    DESCRIPTION
        "Represents the name of AP."
    ::= { h3cDot11WIPSNatDetectEntry 1 }

h3cDot11WIPSNatDetectStatus OBJECT-TYPE
    SYNTAX  H3cDot11WIPSEnabledStatus
    MAX-ACCESS read-write
    STATUS current
    DESCRIPTION
        "The enable status of NAT detect on AP."
    ::= { h3cDot11WIPSNatDetectEntry 2 }

h3cDot11WIPSDctAPTable OBJECT-TYPE
    SYNTAX SEQUENCE OF H3cDot11WIPSDctAPEntry
    MAX-ACCESS not-accessible
    STATUS current
    DESCRIPTION
        "The table contains BSS information for APs
         detected by WIPS."
    ::= { h3cDot11WIPSDataGroup 1 }

h3cDot11WIPSDctAPEntry OBJECT-TYPE
    SYNTAX H3cDot11WIPSDctAPEntry
    MAX-ACCESS not-accessible
    STATUS current
    DESCRIPTION
        "Each entry contains BSS information for one AP."
    INDEX { h3cDot11WIPSDctAPVSD, h3cDot11WIPSDctAPMac }
    ::= { h3cDot11WIPSDctAPTable 1 }

H3cDot11WIPSDctAPEntry ::= SEQUENCE {
        h3cDot11WIPSDctAPVSD               OCTET STRING,
        h3cDot11WIPSDctAPMac               MacAddress,
        h3cDot11WIPSDctAPClassifyWay       H3cDot11WIPSDevClassifyWay,
        h3cDot11WIPSDctAPClassifyType      H3cDot11WIPSAPClassifyType,
        h3cDot11WIPSDctAPSeverityLevel     Unsigned32,
        h3cDot11WIPSDctAPStatus            H3cDot11WIPSDevStatus,
        h3cDot11WIPSDctAPStatusDut         TimeTicks,
        h3cDot11WIPSDctAPVendor            OCTET STRING,
        h3cDot11WIPSDctAPSSID              OCTET STRING,
        h3cDot11WIPSDctAPSecurity          H3cDot11WIPSAPSecurityType,
        h3cDot11WIPSDctAPEncryptMethod     H3cDot11WIPSEncryptMethod,
        h3cDot11WIPSDctAPAuthMethod        H3cDot11WIPSAuthMethod,
        h3cDot11WIPSDctAPRadioType         H3cDot11WIPSRadioType,
        h3cDot11WIPSDctAPWorkChannel       H3cDot11WIPSChannel,
        h3cDot11WIPSDctAPIsCountered       TruthValue,
        h3cDot11WIPSDctAPAttachStaNum      Integer32,
        h3cDot11WIPSDctAPRptSensorNum      Integer32,
        h3cDot11WIPSDctAPIsBdcastSSID      TruthValue,
        h3cDot11WIPSDctAPType              H3cDot11WIPSAPType,
        h3cDot11WIPSDctAPIsQosSported      TruthValue,
        h3cDot11WIPSDctAPBeaconItv         Integer32,
        h3cDot11WIPSDctAPUpDuration        TimeTicks
     }

h3cDot11WIPSDctAPVSD OBJECT-TYPE
    SYNTAX OCTET STRING (SIZE (1..63))
    MAX-ACCESS not-accessible
    STATUS current
    DESCRIPTION
        "Represents the virtual security domain in which the BSS was detected."
    ::= { h3cDot11WIPSDctAPEntry 1 }

h3cDot11WIPSDctAPMac OBJECT-TYPE
    SYNTAX MacAddress
    MAX-ACCESS not-accessible
    STATUS current
    DESCRIPTION
        "Represents the Basic Service Set."
    ::= { h3cDot11WIPSDctAPEntry 2 }

h3cDot11WIPSDctAPClassifyWay OBJECT-TYPE
    SYNTAX H3cDot11WIPSDevClassifyWay
    MAX-ACCESS read-only
    STATUS current
    DESCRIPTION
        "Represents by which way the AP is categorized."
    ::= { h3cDot11WIPSDctAPEntry 3 }

h3cDot11WIPSDctAPClassifyType OBJECT-TYPE
    SYNTAX H3cDot11WIPSAPClassifyType
    MAX-ACCESS read-only
    STATUS current
    DESCRIPTION
        "Represents the category of the AP."
    ::= { h3cDot11WIPSDctAPEntry 4 }

h3cDot11WIPSDctAPSeverityLevel OBJECT-TYPE
    SYNTAX Unsigned32 (0..100)
    MAX-ACCESS read-only
    STATUS current
    DESCRIPTION
        "Represents the security level of the detected AP."
    ::= { h3cDot11WIPSDctAPEntry 5 }

h3cDot11WIPSDctAPStatus OBJECT-TYPE
    SYNTAX H3cDot11WIPSDevStatus
    MAX-ACCESS read-only
    STATUS current
    DESCRIPTION
        "Represents the status of the AP detected by WIPS."
    ::= { h3cDot11WIPSDctAPEntry 6 }

h3cDot11WIPSDctAPStatusDut OBJECT-TYPE
    SYNTAX TimeTicks
    MAX-ACCESS read-only
    STATUS current
    DESCRIPTION
        "Represents the duration of the AP status."
    ::= { h3cDot11WIPSDctAPEntry 7 }

h3cDot11WIPSDctAPVendor OBJECT-TYPE
    SYNTAX OCTET STRING (SIZE (0..127))
    MAX-ACCESS read-only
    STATUS current
    DESCRIPTION
        "Represents the vendor of the AP detected by WIPS."
    ::= { h3cDot11WIPSDctAPEntry 8 }

h3cDot11WIPSDctAPSSID OBJECT-TYPE
    SYNTAX OCTET STRING (SIZE (0..32))
    MAX-ACCESS read-only
    STATUS current
    DESCRIPTION
        "Represents the SSID that is broadcast by the AP."
    ::= { h3cDot11WIPSDctAPEntry 9 }

h3cDot11WIPSDctAPSecurity OBJECT-TYPE
    SYNTAX H3cDot11WIPSAPSecurityType
    MAX-ACCESS read-only
    STATUS current
    DESCRIPTION
        "Represents the security suites of the detected AP."
    ::= { h3cDot11WIPSDctAPEntry 10 }

h3cDot11WIPSDctAPEncryptMethod OBJECT-TYPE
    SYNTAX H3cDot11WIPSEncryptMethod
    MAX-ACCESS read-only
    STATUS current
    DESCRIPTION
        "Represents the encryption method used by the detected AP."
    ::= { h3cDot11WIPSDctAPEntry 11 }

h3cDot11WIPSDctAPAuthMethod OBJECT-TYPE
    SYNTAX H3cDot11WIPSAuthMethod
    MAX-ACCESS read-only
    STATUS current
    DESCRIPTION
        "Represents the authentication method used by the detected AP."
    ::= { h3cDot11WIPSDctAPEntry 12 }

h3cDot11WIPSDctAPRadioType OBJECT-TYPE
    SYNTAX H3cDot11WIPSRadioType
    MAX-ACCESS read-only
    STATUS current
    DESCRIPTION
        "Represents the radio type used by the detected AP."
    ::= { h3cDot11WIPSDctAPEntry 13 }

h3cDot11WIPSDctAPWorkChannel OBJECT-TYPE
    SYNTAX H3cDot11WIPSChannel
    MAX-ACCESS read-only
    STATUS current
    DESCRIPTION
        "Represents the radio channel on which the detected AP operates."
    ::= { h3cDot11WIPSDctAPEntry 14 }

h3cDot11WIPSDctAPIsCountered OBJECT-TYPE
    SYNTAX TruthValue
    MAX-ACCESS read-only
    STATUS current
    DESCRIPTION
        "Represents whether WIPS has taken countermeasures on the detected AP."
    ::= { h3cDot11WIPSDctAPEntry 15 }

h3cDot11WIPSDctAPAttachStaNum OBJECT-TYPE
    SYNTAX Integer32
    MAX-ACCESS read-only
    STATUS current
    DESCRIPTION
        "Represents the number of clients associated with the detected AP."
    ::= { h3cDot11WIPSDctAPEntry 16 }

h3cDot11WIPSDctAPRptSensorNum OBJECT-TYPE
    SYNTAX Integer32
    MAX-ACCESS read-only
    STATUS current
    DESCRIPTION
        "Represents the number of sensors that have detected the AP."
    ::= { h3cDot11WIPSDctAPEntry 17 }

h3cDot11WIPSDctAPIsBdcastSSID OBJECT-TYPE
    SYNTAX TruthValue
    MAX-ACCESS read-only
    STATUS current
    DESCRIPTION
        "Represents whether the detected AP is broadcasting the SSID."
    ::= { h3cDot11WIPSDctAPEntry 18 }

h3cDot11WIPSDctAPType OBJECT-TYPE
    SYNTAX H3cDot11WIPSAPType
    MAX-ACCESS read-only
    STATUS current
    DESCRIPTION
        "Represents the type of the detected AP."
    ::= { h3cDot11WIPSDctAPEntry 19 }

h3cDot11WIPSDctAPIsQosSported OBJECT-TYPE
    SYNTAX TruthValue
    MAX-ACCESS read-only
    STATUS current
    DESCRIPTION
        "Represents the support of the detected AP for QoS."
    ::= { h3cDot11WIPSDctAPEntry 20 }

h3cDot11WIPSDctAPBeaconItv OBJECT-TYPE
    SYNTAX Integer32
    MAX-ACCESS read-only
    STATUS current
    DESCRIPTION
        "Represents the beacon interval of the detected AP."
    ::= { h3cDot11WIPSDctAPEntry 21 }

h3cDot11WIPSDctAPUpDuration OBJECT-TYPE
    SYNTAX TimeTicks
    MAX-ACCESS read-only
    STATUS current
    DESCRIPTION
        "Represents the amount of time that has elapsed since AP
        started to work, which is calculated by using beacon/probe
        response frame."
    ::= { h3cDot11WIPSDctAPEntry 22 }

h3cDot11WIPSDctStaTable OBJECT-TYPE
    SYNTAX SEQUENCE OF H3cDot11WIPSDctStaEntry
    MAX-ACCESS not-accessible
    STATUS current
    DESCRIPTION
        "The table contains information about stations detected by WIPS."
    ::= { h3cDot11WIPSDataGroup 2 }

h3cDot11WIPSDctStaEntry OBJECT-TYPE
    SYNTAX H3cDot11WIPSDctStaEntry
    MAX-ACCESS not-accessible
    STATUS current
    DESCRIPTION
        "Each entry contains information about a station
        detected by WIPS."
    INDEX { h3cDot11WIPSDctStaVSD, h3cDot11WIPSDctStaMac }
    ::= { h3cDot11WIPSDctStaTable 1 }

H3cDot11WIPSDctStaEntry ::= SEQUENCE {
        h3cDot11WIPSDctStaVSD               OCTET STRING,
        h3cDot11WIPSDctStaMac               MacAddress,
        h3cDot11WIPSDctStaAssocBSSID        MacAddress,
        h3cDot11WIPSDctStaClassifyWay       H3cDot11WIPSDevClassifyWay,
        h3cDot11WIPSDctStaClassifyType      H3cDot11WIPSStaClassifyType,
        h3cDot11WIPSDctStaSeverityLevel     Unsigned32,
        h3cDot11WIPSDctStaIsDissociate      TruthValue,
        h3cDot11WIPSDctStaStatus            H3cDot11WIPSDevStatus,
        h3cDot11WIPSDctStaStatusDurat       TimeTicks,
        h3cDot11WIPSDctStaVendor            OCTET STRING,
        h3cDot11WIPSDctStaRadioType         H3cDot11WIPSRadioType,
        h3cDot11WIPSDctStaRptSensorNum      Integer32,
        h3cDot11WIPSDctStaWorkChannel       H3cDot11WIPSChannel,
        h3cDot11WIPSDctStaIsCountered       TruthValue
     }

h3cDot11WIPSDctStaVSD OBJECT-TYPE
    SYNTAX OCTET STRING (SIZE (1..63))
    MAX-ACCESS not-accessible
    STATUS current
    DESCRIPTION
        "Represents the virtual security domain in
         which the station was detected."
    ::= { h3cDot11WIPSDctStaEntry 1 }

h3cDot11WIPSDctStaMac OBJECT-TYPE
    SYNTAX MacAddress
    MAX-ACCESS not-accessible
    STATUS current
    DESCRIPTION
        "Represents the MAC address of the station."
    ::= { h3cDot11WIPSDctStaEntry 2 }

h3cDot11WIPSDctStaAssocBSSID OBJECT-TYPE
    SYNTAX MacAddress
    MAX-ACCESS read-only
    STATUS current
    DESCRIPTION
        "Represents the BSSID with which the station is associated."
    ::= { h3cDot11WIPSDctStaEntry 3 }

h3cDot11WIPSDctStaClassifyWay OBJECT-TYPE
    SYNTAX H3cDot11WIPSDevClassifyWay
    MAX-ACCESS read-only
    STATUS current
    DESCRIPTION
        "Represents the method that the client is categorized."
    ::= { h3cDot11WIPSDctStaEntry 4 }

h3cDot11WIPSDctStaClassifyType OBJECT-TYPE
    SYNTAX H3cDot11WIPSStaClassifyType
    MAX-ACCESS read-only
    STATUS current
    DESCRIPTION
        "Represents the category of the client."
    ::= { h3cDot11WIPSDctStaEntry 5 }

h3cDot11WIPSDctStaSeverityLevel OBJECT-TYPE
    SYNTAX Unsigned32 (0..100)
    MAX-ACCESS read-only
    STATUS current
    DESCRIPTION
        "Represents the security level of the detected client."
    ::= { h3cDot11WIPSDctStaEntry 6 }

h3cDot11WIPSDctStaIsDissociate OBJECT-TYPE
    SYNTAX TruthValue
    MAX-ACCESS read-only
    STATUS current
    DESCRIPTION
        "Represents whether the detected client is dissociated."
    ::= { h3cDot11WIPSDctStaEntry 7 }

h3cDot11WIPSDctStaStatus OBJECT-TYPE
    SYNTAX H3cDot11WIPSDevStatus
    MAX-ACCESS read-only
    STATUS current
    DESCRIPTION
        "Represents the status of the station detected by WIPS."
    ::= { h3cDot11WIPSDctStaEntry 8 }

h3cDot11WIPSDctStaStatusDurat OBJECT-TYPE
    SYNTAX TimeTicks
    MAX-ACCESS read-only
    STATUS current
    DESCRIPTION
        "Represents the duration of the client status."
    ::= { h3cDot11WIPSDctStaEntry 9 }

h3cDot11WIPSDctStaVendor OBJECT-TYPE
    SYNTAX OCTET STRING (SIZE (0..127))
    MAX-ACCESS read-only
    STATUS current
    DESCRIPTION
        "Represents the vendor of the station detected by WIPS."
    ::= { h3cDot11WIPSDctStaEntry 10 }

h3cDot11WIPSDctStaRadioType OBJECT-TYPE
    SYNTAX H3cDot11WIPSRadioType
    MAX-ACCESS read-only
    STATUS current
    DESCRIPTION
        "Represents the radio type used by the detected station."
    ::= { h3cDot11WIPSDctStaEntry 11 }

h3cDot11WIPSDctStaRptSensorNum OBJECT-TYPE
    SYNTAX Integer32
    MAX-ACCESS read-only
    STATUS current
    DESCRIPTION
        "Represents the number of sensors that have detected the station."
    ::= { h3cDot11WIPSDctStaEntry 12 }

h3cDot11WIPSDctStaWorkChannel OBJECT-TYPE
    SYNTAX H3cDot11WIPSChannel
    MAX-ACCESS read-only
    STATUS current
    DESCRIPTION
        "Represents on which radio channel that the WIPS sensor detected
        the station."
    ::= { h3cDot11WIPSDctStaEntry 13 }

h3cDot11WIPSDctStaIsCountered OBJECT-TYPE
    SYNTAX TruthValue
    MAX-ACCESS read-only
    STATUS current
    DESCRIPTION
        "Represents whether WIPS has taken countermeasures
         on the detected client."
    ::= { h3cDot11WIPSDctStaEntry 14 }

--
-- ApAssociatecltTable data3
--
h3cDot11WIPSApAssoCltTable OBJECT-TYPE
    SYNTAX SEQUENCE OF H3cDot11WIPSApAssoCltEntry
    MAX-ACCESS not-accessible
    STATUS current
    DESCRIPTION
        "The table contains information about associated client by WIPS."
    ::= { h3cDot11WIPSDataGroup 3 }

h3cDot11WIPSApAssoCltEntry OBJECT-TYPE
    SYNTAX H3cDot11WIPSApAssoCltEntry
    MAX-ACCESS not-accessible
    STATUS current
    DESCRIPTION
        "Each entry contains information about a associated client by WIPS."
    INDEX { h3cDot11WIPSApAssoCltVSDName,
            h3cDot11WIPSApAssoCltApMacAddr,
            h3cDot11WIPSApAssoCltClMacAddr }
    ::= { h3cDot11WIPSApAssoCltTable 1 }

H3cDot11WIPSApAssoCltEntry ::= SEQUENCE {
        h3cDot11WIPSApAssoCltVSDName                    OCTET STRING,
        h3cDot11WIPSApAssoCltApMacAddr                  MacAddress,
        h3cDot11WIPSApAssoCltClMacAddr                  MacAddress,
        h3cDot11WIPSApAssoCltIsAsso                     TruthValue
     }

h3cDot11WIPSApAssoCltVSDName OBJECT-TYPE
    SYNTAX OCTET STRING (SIZE (1..63))
    MAX-ACCESS not-accessible
    STATUS current
    DESCRIPTION
        "Represents the virtual security domain in
         which the client had Associated."
    ::= { h3cDot11WIPSApAssoCltEntry 1 }

h3cDot11WIPSApAssoCltApMacAddr OBJECT-TYPE
    SYNTAX MacAddress
    MAX-ACCESS not-accessible
    STATUS current
    DESCRIPTION
        "Represents the MAC address of the AP."
    ::= { h3cDot11WIPSApAssoCltEntry 2 }

h3cDot11WIPSApAssoCltClMacAddr OBJECT-TYPE
    SYNTAX MacAddress
    MAX-ACCESS not-accessible
    STATUS current
    DESCRIPTION
        "Represents the MAC address of the Client."
    ::= { h3cDot11WIPSApAssoCltEntry 3 }

h3cDot11WIPSApAssoCltIsAsso OBJECT-TYPE
    SYNTAX TruthValue
    MAX-ACCESS read-only
    STATUS current
    DESCRIPTION
        "Represents whether WIPS had taken associated on the detected client."
    ::= { h3cDot11WIPSApAssoCltEntry 4 }

h3cDot11WIPSApRpSenTable OBJECT-TYPE
    SYNTAX SEQUENCE OF H3cDot11WIPSApRpSenEntry
    MAX-ACCESS not-accessible
    STATUS current
    DESCRIPTION
        "This table contains information about AP report sensors."
    ::= { h3cDot11WIPSDataGroup 4 }

h3cDot11WIPSApRpSenEntry OBJECT-TYPE
    SYNTAX H3cDot11WIPSApRpSenEntry
    MAX-ACCESS not-accessible
    STATUS current
    DESCRIPTION
        "Each entry contains information about one device in a VSD."
    INDEX { h3cDot11WIPSApRpSenVsdName,
            h3cDot11WIPSApRpSenMacAddr,
            h3cDot11WIPSApRpSenName }
    ::= { h3cDot11WIPSApRpSenTable 1 }

H3cDot11WIPSApRpSenEntry ::= SEQUENCE {
        h3cDot11WIPSApRpSenVsdName             OCTET STRING,
        h3cDot11WIPSApRpSenMacAddr             MacAddress,
        h3cDot11WIPSApRpSenName                OCTET STRING,
        h3cDot11WIPSApRpSenRadioID             Integer32,
        h3cDot11WIPSApRpSenRssi                Integer32,
        h3cDot11WIPSApRpSenChannel             Integer32,
        h3cDot11WIPSApRpSenFirstRpTime         OCTET STRING,
        h3cDot11WIPSApRpSenLastRpTime          OCTET STRING
     }

h3cDot11WIPSApRpSenVsdName OBJECT-TYPE
    SYNTAX OCTET STRING (SIZE (1..63))
    MAX-ACCESS not-accessible
    STATUS current
    DESCRIPTION
        "Represents the name of the VSD."
    ::= { h3cDot11WIPSApRpSenEntry 1 }

h3cDot11WIPSApRpSenMacAddr OBJECT-TYPE
    SYNTAX MacAddress
    MAX-ACCESS not-accessible
    STATUS current
    DESCRIPTION
        "Represents the MAC address of the sensor."
    ::= { h3cDot11WIPSApRpSenEntry 2 }

h3cDot11WIPSApRpSenName OBJECT-TYPE
    SYNTAX OCTET STRING (SIZE (1..64))
    MAX-ACCESS not-accessible
    STATUS current
    DESCRIPTION
        "Represents the name of the sensor."
    ::= { h3cDot11WIPSApRpSenEntry 3 }

h3cDot11WIPSApRpSenRadioID  OBJECT-TYPE
    SYNTAX Integer32
    MAX-ACCESS read-only
    STATUS current
    DESCRIPTION
        "Represents the radio ID."
    ::= { h3cDot11WIPSApRpSenEntry 4 }

h3cDot11WIPSApRpSenRssi  OBJECT-TYPE
    SYNTAX Integer32
    MAX-ACCESS read-only
    STATUS current
    DESCRIPTION
        "Represents the rssi of AP."
    ::= { h3cDot11WIPSApRpSenEntry 5 }

h3cDot11WIPSApRpSenChannel  OBJECT-TYPE
    SYNTAX Integer32
    MAX-ACCESS read-only
    STATUS current
    DESCRIPTION
        "Represents the channel of AP."
    ::= { h3cDot11WIPSApRpSenEntry 6 }

h3cDot11WIPSApRpSenFirstRpTime  OBJECT-TYPE
    SYNTAX OCTET STRING (SIZE (1..256))
    MAX-ACCESS read-only
    STATUS current
    DESCRIPTION
        "Represents the first report time of AP."
    ::= { h3cDot11WIPSApRpSenEntry 7 }

h3cDot11WIPSApRpSenLastRpTime  OBJECT-TYPE
    SYNTAX OCTET STRING (SIZE (1..256))
    MAX-ACCESS read-only
    STATUS current
    DESCRIPTION
        "Represents the last report time of AP."
    ::= { h3cDot11WIPSApRpSenEntry 8 }

h3cDot11WIPSCtmRecTable OBJECT-TYPE
    SYNTAX SEQUENCE OF H3cDot11WIPSCtmRecEntry
    MAX-ACCESS not-accessible
    STATUS current
    DESCRIPTION
        "The table provides information about virtual security domains (VSDs)."
    ::= { h3cDot11WIPSDataGroup 5 }

h3cDot11WIPSCtmRecEntry OBJECT-TYPE
    SYNTAX H3cDot11WIPSCtmRecEntry
    MAX-ACCESS not-accessible
    STATUS current
    DESCRIPTION
        "Each entry contains information about one VSD."
    INDEX { h3cDot11WIPSCtmRecVsdName,
            h3cDot11WIPSCtmRecMacAddress,
            h3cDot11WIPSCtmRecCount }
    ::= { h3cDot11WIPSCtmRecTable 1 }

H3cDot11WIPSCtmRecEntry ::= SEQUENCE {
        h3cDot11WIPSCtmRecVsdName                  OCTET STRING,
        h3cDot11WIPSCtmRecMacAddress               MacAddress,
        h3cDot11WIPSCtmRecCount                    Integer32,
        h3cDot11WIPSCtmRecSensorName               OCTET STRING,
        h3cDot11WIPSCtmRecDeviceType               H3cDot11WIPSDeviceType,
        h3cDot11WIPSCtmRecClassifyType             H3cDot11WIPSClassifyType,
        h3cDot11WIPSCtmRecRadioId                  Integer32,
        h3cDot11WIPSCtmRecCounterTime              OCTET STRING
    }

h3cDot11WIPSCtmRecVsdName OBJECT-TYPE
    SYNTAX OCTET STRING (SIZE (1..63))
    MAX-ACCESS not-accessible
    STATUS current
    DESCRIPTION
        "Represents the name of the virtual security domain."
    ::= { h3cDot11WIPSCtmRecEntry 1 }

h3cDot11WIPSCtmRecMacAddress OBJECT-TYPE
    SYNTAX MacAddress
    MAX-ACCESS not-accessible
    STATUS current
    DESCRIPTION
        "Represents the MAC address."
    ::= { h3cDot11WIPSCtmRecEntry 2 }

h3cDot11WIPSCtmRecCount OBJECT-TYPE
    SYNTAX Integer32 (1..1024)
    MAX-ACCESS not-accessible
    STATUS current
    DESCRIPTION
        "Represents the count of countermeasure record."
    ::= { h3cDot11WIPSCtmRecEntry 3 }

h3cDot11WIPSCtmRecSensorName OBJECT-TYPE
    SYNTAX OCTET STRING (SIZE (1..64))
    MAX-ACCESS read-only
    STATUS current
    DESCRIPTION
        "Represents the name of countermeasure sensor."
    ::= { h3cDot11WIPSCtmRecEntry 4 }

h3cDot11WIPSCtmRecDeviceType OBJECT-TYPE
    SYNTAX H3cDot11WIPSDeviceType
    MAX-ACCESS read-only
    STATUS current
    DESCRIPTION
        "Represents the type of device."
    ::= { h3cDot11WIPSCtmRecEntry 5 }

h3cDot11WIPSCtmRecClassifyType OBJECT-TYPE
    SYNTAX H3cDot11WIPSClassifyType
    MAX-ACCESS read-only
    STATUS current
    DESCRIPTION
        "Represents the type of device classification."
    ::= { h3cDot11WIPSCtmRecEntry 6 }

h3cDot11WIPSCtmRecRadioId OBJECT-TYPE
    SYNTAX Integer32
    MAX-ACCESS read-only
    STATUS current
    DESCRIPTION
        "Represents the radio ID of countermeasure sensor."
    ::= { h3cDot11WIPSCtmRecEntry 7 }

h3cDot11WIPSCtmRecCounterTime OBJECT-TYPE
    SYNTAX OCTET STRING (SIZE (1..256))
    MAX-ACCESS read-only
    STATUS current
    DESCRIPTION
        "Represents the time of countermeasure."
    ::= { h3cDot11WIPSCtmRecEntry 8 }

h3cDot11WIPSDevTable OBJECT-TYPE
    SYNTAX SEQUENCE OF H3cDot11WIPSDevEntry
    MAX-ACCESS not-accessible
    STATUS current
    DESCRIPTION
        "The table contains variedly devices type information."
    ::= { h3cDot11WIPSDataGroup 7 }

h3cDot11WIPSDevEntry OBJECT-TYPE
    SYNTAX H3cDot11WIPSDevEntry
    MAX-ACCESS not-accessible
    STATUS current
    DESCRIPTION
        "Each entry contains one type of devices information."
    INDEX { h3cDot11WIPSDevVSDName }
    ::= { h3cDot11WIPSDevTable 1 }

H3cDot11WIPSDevEntry ::= SEQUENCE {
        h3cDot11WIPSDevVSDName                 OCTET STRING,
        h3cDot11WIPSDevTotalApNum              Integer32,
        h3cDot11WIPSDevTotalClinetNum          Integer32,
        h3cDot11WIPSDevAuthApNum               Integer32,
        h3cDot11WIPSDevMisConfigApNum          Integer32,
        h3cDot11WIPSDevRogueApNum              Integer32,
        h3cDot11WIPSDevExternalApNum           Integer32,
        h3cDot11WIPSDevAdhocNum                Integer32,
        h3cDot11WIPSDevMeshApNum               Integer32,
        h3cDot11WIPSDevpotenAuthApNum          Integer32,
        h3cDot11WIPSDevpotenRogueApNum         Integer32,
        h3cDot11WIPSDevPotenExtApNum           Integer32,
        h3cDot11WIPSDevUncateApNum             Integer32,
        h3cDot11WIPSDevAuthClinetNum           Integer32,
        h3cDot11WIPSDevUnauthClinetNum         Integer32,
        h3cDot11WIPSDevMisAssocltNum           Integer32,
        h3cDot11WIPSDevUncatecltNum            Integer32
     }

h3cDot11WIPSDevVSDName OBJECT-TYPE
    SYNTAX OCTET STRING (SIZE (1..63))
    MAX-ACCESS not-accessible
    STATUS current
    DESCRIPTION
        "Represents the virtual security domain in one type device."
    ::= { h3cDot11WIPSDevEntry 1 }

h3cDot11WIPSDevTotalApNum OBJECT-TYPE
    SYNTAX Integer32
    MAX-ACCESS read-only
    STATUS current
    DESCRIPTION
        "Represents the total number of detected AP."
    ::= { h3cDot11WIPSDevEntry 2 }

h3cDot11WIPSDevTotalClinetNum OBJECT-TYPE
    SYNTAX Integer32
    MAX-ACCESS read-only
    STATUS current
    DESCRIPTION
        "Represents the total number of detected client."
    ::= { h3cDot11WIPSDevEntry 3 }

h3cDot11WIPSDevAuthApNum OBJECT-TYPE
    SYNTAX Integer32
    MAX-ACCESS read-only
    STATUS current
    DESCRIPTION
        "Represents the number of detected authenticated AP."
    ::= { h3cDot11WIPSDevEntry 4 }

h3cDot11WIPSDevMisConfigApNum OBJECT-TYPE
    SYNTAX Integer32
    MAX-ACCESS read-only
    STATUS current
    DESCRIPTION
        "Represents the number of detected misconfiguration AP."
    ::= { h3cDot11WIPSDevEntry 5 }

h3cDot11WIPSDevRogueApNum OBJECT-TYPE
    SYNTAX Integer32
    MAX-ACCESS read-only
    STATUS current
    DESCRIPTION
        "Represents the number of detected rouge AP."
    ::= { h3cDot11WIPSDevEntry 6 }

h3cDot11WIPSDevExternalApNum OBJECT-TYPE
    SYNTAX Integer32
    MAX-ACCESS read-only
    STATUS current
    DESCRIPTION
        "Represents the number of detected external AP."
    ::= { h3cDot11WIPSDevEntry 7 }

h3cDot11WIPSDevAdhocNum OBJECT-TYPE
    SYNTAX Integer32
    MAX-ACCESS read-only
    STATUS current
    DESCRIPTION
        "Represents the number of detected ad-hoc AP."
    ::= { h3cDot11WIPSDevEntry 8 }

h3cDot11WIPSDevMeshApNum OBJECT-TYPE
    SYNTAX Integer32
    MAX-ACCESS read-only
    STATUS current
    DESCRIPTION
        "Represents the number of detected mesh-AP."
    ::= { h3cDot11WIPSDevEntry 9 }

h3cDot11WIPSDevpotenAuthApNum OBJECT-TYPE
    SYNTAX Integer32
    MAX-ACCESS read-only
    STATUS current
    DESCRIPTION
        "Represents the number of detected potential authenticated AP."
    ::= { h3cDot11WIPSDevEntry 10 }

h3cDot11WIPSDevpotenRogueApNum OBJECT-TYPE
    SYNTAX Integer32
    MAX-ACCESS read-only
    STATUS current
    DESCRIPTION
        "Represents the number of detected potential rogue AP."
    ::= { h3cDot11WIPSDevEntry 11 }

h3cDot11WIPSDevPotenExtApNum OBJECT-TYPE
    SYNTAX Integer32
    MAX-ACCESS read-only
    STATUS current
    DESCRIPTION
        "Represents the number of detected potential external AP."
    ::= { h3cDot11WIPSDevEntry 12 }

h3cDot11WIPSDevUncateApNum OBJECT-TYPE
    SYNTAX Integer32
    MAX-ACCESS read-only
    STATUS current
    DESCRIPTION
        "Represents the number of detected uncategorized AP."
    ::= { h3cDot11WIPSDevEntry 13 }

h3cDot11WIPSDevAuthClinetNum OBJECT-TYPE
    SYNTAX Integer32
    MAX-ACCESS read-only
    STATUS current
    DESCRIPTION
        "Represents the number of detected authenticated clinet."
    ::= { h3cDot11WIPSDevEntry 14 }

h3cDot11WIPSDevUnauthClinetNum OBJECT-TYPE
    SYNTAX Integer32
    MAX-ACCESS read-only
    STATUS current
    DESCRIPTION
        "Represents the number of detected unauthenticated client."
    ::= { h3cDot11WIPSDevEntry 15 }

h3cDot11WIPSDevMisAssocltNum OBJECT-TYPE
    SYNTAX Integer32
    MAX-ACCESS read-only
    STATUS current
    DESCRIPTION
        "Represents the number of detected misassociated client."
    ::= { h3cDot11WIPSDevEntry 16 }

h3cDot11WIPSDevUncatecltNum OBJECT-TYPE
    SYNTAX Integer32
    MAX-ACCESS read-only
    STATUS current
    DESCRIPTION
        "Represents the number of detected uncategorized client."
    ::= { h3cDot11WIPSDevEntry 17 }


h3cDot11WIPSCtmDevTable OBJECT-TYPE
    SYNTAX SEQUENCE OF H3cDot11WIPSCtmDevEntry
    MAX-ACCESS not-accessible
    STATUS current
    DESCRIPTION
        "This table contains information about countermeasure device in a VSD."
    ::= { h3cDot11WIPSDataGroup 8 }

h3cDot11WIPSCtmDevEntry OBJECT-TYPE
    SYNTAX H3cDot11WIPSCtmDevEntry
    MAX-ACCESS not-accessible
    STATUS current
    DESCRIPTION
        "Each entry contains countermeasure information about device in a VSD."
    INDEX { h3cDot11WIPSCtmDevVsdName }
    ::= { h3cDot11WIPSCtmDevTable 1 }

H3cDot11WIPSCtmDevEntry ::= SEQUENCE {
        h3cDot11WIPSCtmDevVsdName                  OCTET STRING,
        h3cDot11WIPSCtmDevTotalApNum               Integer32,
        h3cDot11WIPSCtmDevTotalStaNum              Integer32,
        h3cDot11WIPSCtmDevMisCfgApNum              Integer32,
        h3cDot11WIPSCtmDevRogueApNum               Integer32,
        h3cDot11WIPSCtmDevExternalApNum            Integer32,
        h3cDot11WIPSCtmDevpotAuthApNum             Integer32,
        h3cDot11WIPSCtmDevpotRguApNum              Integer32,
        h3cDot11WIPSCtmDevpotenExtApNum            Integer32,
        h3cDot11WIPSCtmDevUncateApNum              Integer32,
        h3cDot11WIPSCtmDevUnauthStaNum             Integer32,
        h3cDot11WIPSCtmDevMisAssCltNum             Integer32,
        h3cDot11WIPSCtmDevUncatecltNum             Integer32,
        h3cDot11WIPSCtmDevAttackerNum              Integer32,
        h3cDot11WIPSCtmDevManuNum                  Integer32,
        h3cDot11WIPSCtmDevStaCauseByAP             Integer32
     }

h3cDot11WIPSCtmDevVsdName OBJECT-TYPE
    SYNTAX OCTET STRING (SIZE (1..63))
    MAX-ACCESS not-accessible
    STATUS current
    DESCRIPTION
        "Represents the vsd name."
    ::= { h3cDot11WIPSCtmDevEntry 1 }

h3cDot11WIPSCtmDevTotalApNum OBJECT-TYPE
    SYNTAX Integer32
    MAX-ACCESS read-only
    STATUS current
    DESCRIPTION
        "Represents the total number of coutermeasured AP."
    ::= { h3cDot11WIPSCtmDevEntry 2 }

h3cDot11WIPSCtmDevTotalStaNum OBJECT-TYPE
    SYNTAX Integer32
    MAX-ACCESS read-only
    STATUS current
    DESCRIPTION
        "Represents the total number of coutermeasured client."
    ::= { h3cDot11WIPSCtmDevEntry 3 }

h3cDot11WIPSCtmDevMisCfgApNum OBJECT-TYPE
    SYNTAX Integer32
    MAX-ACCESS read-only
    STATUS current
    DESCRIPTION
        "Represents the number of coutermeasured misconfiguration AP."
    ::= { h3cDot11WIPSCtmDevEntry 4 }

h3cDot11WIPSCtmDevRogueApNum OBJECT-TYPE
    SYNTAX Integer32
    MAX-ACCESS read-only
    STATUS current
    DESCRIPTION
        "Represents the number of coutermeasured rouge AP."
    ::= { h3cDot11WIPSCtmDevEntry 5 }

h3cDot11WIPSCtmDevExternalApNum OBJECT-TYPE
    SYNTAX Integer32
    MAX-ACCESS read-only
    STATUS current
    DESCRIPTION
        "Represents the number of coutermeasured external AP."
    ::= { h3cDot11WIPSCtmDevEntry 6 }

h3cDot11WIPSCtmDevpotAuthApNum OBJECT-TYPE
    SYNTAX Integer32
    MAX-ACCESS read-only
    STATUS current
    DESCRIPTION
        "Represents the number of coutermeasured potential authenticated AP."
    ::= { h3cDot11WIPSCtmDevEntry 7 }

h3cDot11WIPSCtmDevpotRguApNum OBJECT-TYPE
    SYNTAX Integer32
    MAX-ACCESS read-only
    STATUS current
    DESCRIPTION
        "Represents the number of coutermeasured potential rogue AP."
    ::= { h3cDot11WIPSCtmDevEntry 8 }

h3cDot11WIPSCtmDevpotenExtApNum OBJECT-TYPE
    SYNTAX Integer32
    MAX-ACCESS read-only
    STATUS current
    DESCRIPTION
        "Represents the number of coutermeasured potential external AP."
    ::= { h3cDot11WIPSCtmDevEntry 9 }

h3cDot11WIPSCtmDevUncateApNum OBJECT-TYPE
    SYNTAX Integer32
    MAX-ACCESS read-only
    STATUS current
    DESCRIPTION
        "Represents the number of coutermeasured uncategorized AP."
    ::= { h3cDot11WIPSCtmDevEntry 10 }

h3cDot11WIPSCtmDevUnauthStaNum OBJECT-TYPE
    SYNTAX Integer32
    MAX-ACCESS read-only
    STATUS current
    DESCRIPTION
        "Represents the number of coutermeasured unauthenticated client."
    ::= { h3cDot11WIPSCtmDevEntry 11 }

h3cDot11WIPSCtmDevMisAssCltNum OBJECT-TYPE
    SYNTAX Integer32
    MAX-ACCESS read-only
    STATUS current
    DESCRIPTION
        "Represents the number of coutermeasured misassociated client."
    ::= { h3cDot11WIPSCtmDevEntry 12 }

h3cDot11WIPSCtmDevUncatecltNum OBJECT-TYPE
    SYNTAX Integer32
    MAX-ACCESS read-only
    STATUS current
    DESCRIPTION
        "Represents the number of coutermeasured uncategorized client."
    ::= { h3cDot11WIPSCtmDevEntry 13 }

h3cDot11WIPSCtmDevAttackerNum OBJECT-TYPE
    SYNTAX Integer32
    MAX-ACCESS read-only
    STATUS current
    DESCRIPTION
        "Represents the number of coutermeasured attackers."
    ::= { h3cDot11WIPSCtmDevEntry 14 }

h3cDot11WIPSCtmDevManuNum OBJECT-TYPE
    SYNTAX Integer32
    MAX-ACCESS read-only
    STATUS current
    DESCRIPTION
        "Represents the number of manual coutermeasure."
    ::= { h3cDot11WIPSCtmDevEntry 15 }

h3cDot11WIPSCtmDevStaCauseByAP OBJECT-TYPE
    SYNTAX Integer32
    MAX-ACCESS read-only
    STATUS current
    DESCRIPTION
        "Represents the number of station caused by coutermeasured AP."
    ::= { h3cDot11WIPSCtmDevEntry 16 }

h3cDot11WIPSCltRptApTable OBJECT-TYPE
    SYNTAX SEQUENCE OF H3cDot11WIPSCltRptApEntry
    MAX-ACCESS not-accessible
    STATUS current
    DESCRIPTION
        "The table contains information about stations Report by Sensor."
    ::= { h3cDot11WIPSDataGroup 11 }

h3cDot11WIPSCltRptApEntry OBJECT-TYPE
    SYNTAX H3cDot11WIPSCltRptApEntry
    MAX-ACCESS not-accessible
    STATUS current
    DESCRIPTION
        "Each entry contains information about a probe station."
    INDEX { h3cDot11WIPSCltRptApVSDName,
            h3cDot11WIPSCltRptApDevMac,
            h3cDot11WIPSCltRptApSensorName }
    ::= { h3cDot11WIPSCltRptApTable 1 }

H3cDot11WIPSCltRptApEntry ::= SEQUENCE {
        h3cDot11WIPSCltRptApVSDName        OCTET STRING,
        h3cDot11WIPSCltRptApDevMac         MacAddress,
        h3cDot11WIPSCltRptApSensorName     OCTET STRING,
        h3cDot11WIPSCltReportApRadioId     Integer32,
        h3cDot11WIPSCltRptApRSSI           Integer32,
        h3cDot11WIPSCltRptApWorkChannel    H3cDot11WIPSChannel,
        h3cDot11WIPSCltRptApFirstTime      OCTET STRING,
        h3cDot11WIPSCltRptApLastTime       OCTET STRING,
        h3cDot11WIPSCltRptApAssocMac       MacAddress
     }

h3cDot11WIPSCltRptApVSDName OBJECT-TYPE
    SYNTAX OCTET STRING (SIZE (1..63))
    MAX-ACCESS not-accessible
    STATUS current
    DESCRIPTION
        "Represents the virtual security domain in
         which the client was detected."
    ::= { h3cDot11WIPSCltRptApEntry 1 }

h3cDot11WIPSCltRptApDevMac OBJECT-TYPE
    SYNTAX MacAddress
    MAX-ACCESS not-accessible
    STATUS current
    DESCRIPTION
        "Represents the device MAC address of the client."
    ::= { h3cDot11WIPSCltRptApEntry 2 }

h3cDot11WIPSCltRptApSensorName OBJECT-TYPE
    SYNTAX OCTET STRING (SIZE (1..64))
    MAX-ACCESS not-accessible
    STATUS current
    DESCRIPTION
        "Represents the sensor name in which the client was detected."
    ::= { h3cDot11WIPSCltRptApEntry 3 }

h3cDot11WIPSCltReportApRadioId OBJECT-TYPE
    SYNTAX Integer32
    MAX-ACCESS read-only
    STATUS current
    DESCRIPTION
        "Represents the radio id that have detected the client."
    ::= { h3cDot11WIPSCltRptApEntry 4 }

h3cDot11WIPSCltRptApRSSI OBJECT-TYPE
    SYNTAX Integer32
    MAX-ACCESS read-only
    STATUS current
    DESCRIPTION
        "Represents the RSSI of the client."
    ::= { h3cDot11WIPSCltRptApEntry 5 }

h3cDot11WIPSCltRptApWorkChannel OBJECT-TYPE
    SYNTAX H3cDot11WIPSChannel
    MAX-ACCESS read-only
    STATUS current
    DESCRIPTION
        "Represents on which radio channel that
         the WIPS sensor detected the client."
    ::= { h3cDot11WIPSCltRptApEntry 6 }

h3cDot11WIPSCltRptApFirstTime OBJECT-TYPE
    SYNTAX OCTET STRING (SIZE (1..256))
    MAX-ACCESS read-only
    STATUS current
    DESCRIPTION
        "Represents the First Report Time of the client."
    ::= { h3cDot11WIPSCltRptApEntry 7 }

h3cDot11WIPSCltRptApLastTime OBJECT-TYPE
    SYNTAX OCTET STRING (SIZE (1..256))
    MAX-ACCESS read-only
    STATUS current
    DESCRIPTION
        "Represents the Last Report Time of the client."
    ::= { h3cDot11WIPSCltRptApEntry 8 }

h3cDot11WIPSCltRptApAssocMac OBJECT-TYPE
    SYNTAX MacAddress
    MAX-ACCESS read-only
    STATUS current
    DESCRIPTION
        "Represents the association MAC address of the client."
    ::= { h3cDot11WIPSCltRptApEntry 9 }

h3cDot11WIPSNatDtcCltTable OBJECT-TYPE
    SYNTAX SEQUENCE OF H3cDot11WIPSNatDtcCltEntry
    MAX-ACCESS not-accessible
    STATUS current
    DESCRIPTION
        "The table contains information about NAT client detected by WIPS."
    ::= { h3cDot11WIPSDataGroup 12 }

h3cDot11WIPSNatDtcCltEntry OBJECT-TYPE
    SYNTAX H3cDot11WIPSNatDtcCltEntry
    MAX-ACCESS not-accessible
    STATUS current
    DESCRIPTION
        "Each entry contains information about a NAT detect client."
    INDEX { h3cDot11WIPSNatDtcCltMac }
    ::= { h3cDot11WIPSNatDtcCltTable 1 }

H3cDot11WIPSNatDtcCltEntry ::= SEQUENCE {
        h3cDot11WIPSNatDtcCltMac           MacAddress,
        h3cDot11WIPSNatDtcCltFirstTime     OCTET STRING,
        h3cDot11WIPSNatDtcCltLastTime      OCTET STRING,
        h3cDot11WIPSNatDtcCltDuraTime      Integer32
     }

h3cDot11WIPSNatDtcCltMac OBJECT-TYPE
    SYNTAX MacAddress
    MAX-ACCESS not-accessible
    STATUS current
    DESCRIPTION
        "Represents the MAC address of the NAT detect client."
    ::= { h3cDot11WIPSNatDtcCltEntry 1 }

h3cDot11WIPSNatDtcCltFirstTime OBJECT-TYPE
    SYNTAX OCTET STRING (SIZE (1..256))
    MAX-ACCESS read-only
    STATUS current
    DESCRIPTION
        "Represents the first report time of the NAT detect client."
    ::= { h3cDot11WIPSNatDtcCltEntry 2 }

h3cDot11WIPSNatDtcCltLastTime OBJECT-TYPE
    SYNTAX OCTET STRING (SIZE (1..256))
    MAX-ACCESS read-only
    STATUS current
    DESCRIPTION
        "Represents the last report time of the NAT detect client."
    ::= { h3cDot11WIPSNatDtcCltEntry 3 }

h3cDot11WIPSNatDtcCltDuraTime OBJECT-TYPE
    SYNTAX Integer32
    MAX-ACCESS read-only
    STATUS current
    DESCRIPTION
        "Represents the duration of the NAT detect client."
    ::= { h3cDot11WIPSNatDtcCltEntry 4 }

h3cDot11WIPSAckStaTable OBJECT-TYPE
    SYNTAX SEQUENCE OF H3cDot11WIPSAckStaEntry
    MAX-ACCESS not-accessible
    STATUS current
    DESCRIPTION
        "This table contains information about attack statistics."
    ::= { h3cDot11WIPSDataGroup 13 }

h3cDot11WIPSAckStaEntry OBJECT-TYPE
    SYNTAX H3cDot11WIPSAckStaEntry
    MAX-ACCESS not-accessible
    STATUS current
    DESCRIPTION
        "Each entry contains information about
         a attack statistics on the sensor."
    INDEX { h3cDot11WIPSAckStaSensorName }
    ::= { h3cDot11WIPSAckStaTable 1 }

H3cDot11WIPSAckStaEntry ::= SEQUENCE {
        h3cDot11WIPSAckStaSensorName                   OCTET STRING,
        h3cDot11WIPSAckStaAssReqFld                    Integer32,
        h3cDot11WIPSAckStaAuthFld                      Integer32,
        h3cDot11WIPSAckStaBeaconFld                    Integer32,
        h3cDot11WIPSAckStaBlkAckFld                    Integer32,
        h3cDot11WIPSAckStaCtsFld                       Integer32,
        h3cDot11WIPSAckStaDeauthFld                    Integer32,
        h3cDot11WIPSAckStaDisassFld                    Integer32,
        h3cDot11WIPSAckStaEpolSatFld                   Integer32,
        h3cDot11WIPSAckStaNullDataFld                  Integer32,
        h3cDot11WIPSAckStaProReqFld                    Integer32,
        h3cDot11WIPSAckStaReassFld                     Integer32,
        h3cDot11WIPSAckStaRtsFld                       Integer32,
        h3cDot11WIPSAckStaEapLgoffFld                  Integer32,
        h3cDot11WIPSAckStaEapFailFld                   Integer32,
        h3cDot11WIPSAckStaEapSucFld                    Integer32,
        h3cDot11WIPSAckStaDupIeMalf                    Integer32,
        h3cDot11WIPSAckStaFataJackMalf                 Integer32,
        h3cDot11WIPSAckStaEssMalf                      Integer32,
        h3cDot11WIPSAckStaInvComMalf                   Integer32,
        h3cDot11WIPSAckStaInvAssReqMalf                Integer32,
        h3cDot11WIPSAckStaInvAuthMalf                  Integer32,
        h3cDot11WIPSAckStaInvDeauthMalf                Integer32,
        h3cDot11WIPSAckStaInvDisMalf                   Integer32,
        h3cDot11WIPSAckStaInvHtIeMalf                  Integer32,
        h3cDot11WIPSAckStaInvIeLenMalf                 Integer32,
        h3cDot11WIPSAckStaInvPktLthMalf                Integer32,
        h3cDot11WIPSAckStaLgeDutMalf                   Integer32,
        h3cDot11WIPSAckStaNProRespMalf                 Integer32,
        h3cDot11WIPSAckStaOverflEapMalf                Integer32,
        h3cDot11WIPSAckStaOverfSsidMalf                Integer32,
        h3cDot11WIPSAckStaRedundIeMalf                 Integer32,
        h3cDot11WIPSAckStaApSpoofAp                    Integer32,
        h3cDot11WIPSAckStaApSpoofclt                   Integer32,
        h3cDot11WIPSAckStaApSpoofAdhoc                 Integer32,
        h3cDot11WIPSAckStaAdhocSpoofAp                 Integer32,
        h3cDot11WIPSAckStacltSpoofAp                   Integer32,
        h3cDot11WIPSAckStaWeakIv                       Integer32,
        h3cDot11WIPSAckStaApRate                       Integer32,
        h3cDot11WIPSAckStacltRate                      Integer32,
        h3cDot11WIPSAckStaSignatureRule                Integer32,
        h3cDot11WIPSAckSta40Mhz                        Integer32,
        h3cDot11WIPSAckStaPowerSave                    Integer32,
        h3cDot11WIPSAckStaWinBdg                       Integer32,
        h3cDot11WIPSAckStaOmerta                       Integer32,
        h3cDot11WIPSAckStaSoftAp                       Integer32,
        h3cDot11WIPSAckStaBroadDis                     Integer32,
        h3cDot11WIPSAckStaBroadDeauth                  Integer32,
        h3cDot11WIPSAckStaApImp                        Integer32,
        h3cDot11WIPSAckStaHtGreenField                 Integer32,
        h3cDot11WIPSAckStaWireBdg                      Integer32,
        h3cDot11WIPSAckStaApFld                        Integer32,
        h3cDot11WIPSAckStaAssociaOverf                 Integer32
    }

h3cDot11WIPSAckStaSensorName OBJECT-TYPE
    SYNTAX OCTET STRING (SIZE (1..64))
    MAX-ACCESS not-accessible
    STATUS current
    DESCRIPTION
        "Represents the sensor name."
    ::= { h3cDot11WIPSAckStaEntry 1 }

h3cDot11WIPSAckStaAssReqFld OBJECT-TYPE
    SYNTAX Integer32
    MAX-ACCESS read-only
    STATUS current
    DESCRIPTION
        "Represents the statistics number of association request packet flood."
    ::= { h3cDot11WIPSAckStaEntry 2 }

h3cDot11WIPSAckStaAuthFld OBJECT-TYPE
    SYNTAX Integer32
    MAX-ACCESS read-only
    STATUS current
    DESCRIPTION
        "Represents the statistics number of authentication packet flood."
    ::= { h3cDot11WIPSAckStaEntry 3 }

h3cDot11WIPSAckStaBeaconFld OBJECT-TYPE
    SYNTAX Integer32
    MAX-ACCESS read-only
    STATUS current
    DESCRIPTION
        "Represents the statistics number of beacon packet flood."
    ::= { h3cDot11WIPSAckStaEntry 4 }

h3cDot11WIPSAckStaBlkAckFld OBJECT-TYPE
    SYNTAX Integer32
    MAX-ACCESS read-only
    STATUS current
    DESCRIPTION
        "Represents the statistics number of block ack packet flood."
    ::= { h3cDot11WIPSAckStaEntry 5 }

h3cDot11WIPSAckStaCtsFld OBJECT-TYPE
    SYNTAX Integer32
    MAX-ACCESS read-only
    STATUS current
    DESCRIPTION
        "Represents the statistics number of cts packet flood."
    ::= { h3cDot11WIPSAckStaEntry 6 }

h3cDot11WIPSAckStaDeauthFld OBJECT-TYPE
    SYNTAX Integer32
    MAX-ACCESS read-only
    STATUS current
    DESCRIPTION
        "Represents the statistics number of deauthentication packet flood."
    ::= { h3cDot11WIPSAckStaEntry 7 }

h3cDot11WIPSAckStaDisassFld OBJECT-TYPE
    SYNTAX Integer32
    MAX-ACCESS read-only
    STATUS current
    DESCRIPTION
        "Represents the statistics number of disassociation packet flood."
    ::= { h3cDot11WIPSAckStaEntry 8 }

h3cDot11WIPSAckStaEpolSatFld OBJECT-TYPE
    SYNTAX Integer32
    MAX-ACCESS read-only
    STATUS current
    DESCRIPTION
        "Represents the statistics number of eapol-start packet flood."
    ::= { h3cDot11WIPSAckStaEntry 9 }

h3cDot11WIPSAckStaNullDataFld OBJECT-TYPE
    SYNTAX Integer32
    MAX-ACCESS read-only
    STATUS current
    DESCRIPTION
        "Represents the statistics number of null-data packet flood."
    ::= { h3cDot11WIPSAckStaEntry 10 }
h3cDot11WIPSAckStaProReqFld OBJECT-TYPE
    SYNTAX Integer32
    MAX-ACCESS read-only
    STATUS current
    DESCRIPTION
        "Represents the statistics number of probe request packet flood."
    ::= { h3cDot11WIPSAckStaEntry 11 }

h3cDot11WIPSAckStaReassFld OBJECT-TYPE
    SYNTAX Integer32
    MAX-ACCESS read-only
    STATUS current
    DESCRIPTION
        "Represents the statistics number of
         reassociation request packet flood."
    ::= { h3cDot11WIPSAckStaEntry 12 }

h3cDot11WIPSAckStaRtsFld OBJECT-TYPE
    SYNTAX Integer32
    MAX-ACCESS read-only
    STATUS current
    DESCRIPTION
        "Represents the statistics number of rts packet flood."
    ::= { h3cDot11WIPSAckStaEntry 13 }

h3cDot11WIPSAckStaEapLgoffFld OBJECT-TYPE
    SYNTAX Integer32
    MAX-ACCESS read-only
    STATUS current
    DESCRIPTION
        "Represents the statistics number of eapol-logoff packet flood."
    ::= { h3cDot11WIPSAckStaEntry 14 }

h3cDot11WIPSAckStaEapFailFld OBJECT-TYPE
    SYNTAX Integer32
    MAX-ACCESS read-only
    STATUS current
    DESCRIPTION
        "Represents the statistics number of eap-failure packet flood."
    ::= { h3cDot11WIPSAckStaEntry 15 }

h3cDot11WIPSAckStaEapSucFld OBJECT-TYPE
    SYNTAX Integer32
    MAX-ACCESS read-only
    STATUS current
    DESCRIPTION
        "Represents the statistics number of eap-success packet flood."
    ::= { h3cDot11WIPSAckStaEntry 16 }

h3cDot11WIPSAckStaDupIeMalf OBJECT-TYPE
    SYNTAX Integer32
    MAX-ACCESS read-only
    STATUS current
    DESCRIPTION
        "Represents the statistics number of duplicated IE malform."
    ::= { h3cDot11WIPSAckStaEntry 17 }

h3cDot11WIPSAckStaFataJackMalf OBJECT-TYPE
    SYNTAX Integer32
    MAX-ACCESS read-only
    STATUS current
    DESCRIPTION
        "Represents the statistics number of fata jack malform."
    ::= { h3cDot11WIPSAckStaEntry 18 }

h3cDot11WIPSAckStaEssMalf OBJECT-TYPE
    SYNTAX Integer32
    MAX-ACCESS read-only
    STATUS current
    DESCRIPTION
        "Represents the statistics number of illegal IBSS ESS malform."
    ::= { h3cDot11WIPSAckStaEntry 19 }

h3cDot11WIPSAckStaInvComMalf OBJECT-TYPE
    SYNTAX Integer32
    MAX-ACCESS read-only
    STATUS current
    DESCRIPTION
        "Represents the statistics number of
         invalid address combination malform."
    ::= { h3cDot11WIPSAckStaEntry 20 }

h3cDot11WIPSAckStaInvAssReqMalf OBJECT-TYPE
    SYNTAX Integer32
    MAX-ACCESS read-only
    STATUS current
    DESCRIPTION
        "Represents the statistics number of
         invalid authentication request malform."
    ::= { h3cDot11WIPSAckStaEntry 21 }

h3cDot11WIPSAckStaInvAuthMalf OBJECT-TYPE
    SYNTAX Integer32
    MAX-ACCESS read-only
    STATUS current
    DESCRIPTION
        "Represents the statistics number of invalid authentication malform."
    ::= { h3cDot11WIPSAckStaEntry 22 }

h3cDot11WIPSAckStaInvDeauthMalf OBJECT-TYPE
    SYNTAX Integer32
    MAX-ACCESS read-only
    STATUS current
    DESCRIPTION
        "Represents the statistics number of
         invalid deauthentication code malform."
    ::= { h3cDot11WIPSAckStaEntry 23 }

h3cDot11WIPSAckStaInvDisMalf OBJECT-TYPE
    SYNTAX Integer32
    MAX-ACCESS read-only
    STATUS current
    DESCRIPTION
        "Represents the statistics number of invalid disassocited code malform."
    ::= { h3cDot11WIPSAckStaEntry 24 }

h3cDot11WIPSAckStaInvHtIeMalf OBJECT-TYPE
    SYNTAX Integer32
    MAX-ACCESS read-only
    STATUS current
    DESCRIPTION
        "Represents the statistics number of invalid HT IE malform."
    ::= { h3cDot11WIPSAckStaEntry 25 }

h3cDot11WIPSAckStaInvIeLenMalf OBJECT-TYPE
    SYNTAX Integer32
    MAX-ACCESS read-only
    STATUS current
    DESCRIPTION
        "Represents the statistics number of invalid IE length malform."
    ::= { h3cDot11WIPSAckStaEntry 26 }

h3cDot11WIPSAckStaInvPktLthMalf OBJECT-TYPE
    SYNTAX Integer32
    MAX-ACCESS read-only
    STATUS current
    DESCRIPTION
        "Represents the statistics number of invalid packet length malform."
    ::= { h3cDot11WIPSAckStaEntry 27 }

h3cDot11WIPSAckStaLgeDutMalf OBJECT-TYPE
    SYNTAX Integer32
    MAX-ACCESS read-only
    STATUS current
    DESCRIPTION
        "Represents the statistics number of large duration malform."
    ::= { h3cDot11WIPSAckStaEntry 28 }

h3cDot11WIPSAckStaNProRespMalf OBJECT-TYPE
    SYNTAX Integer32
    MAX-ACCESS read-only
    STATUS current
    DESCRIPTION
        "Represents the statistics number of null probe response malform."
    ::= { h3cDot11WIPSAckStaEntry 29 }

h3cDot11WIPSAckStaOverflEapMalf OBJECT-TYPE
    SYNTAX Integer32
    MAX-ACCESS read-only
    STATUS current
    DESCRIPTION
        "Represents the statistics number of overflow eapol key malform."
    ::= { h3cDot11WIPSAckStaEntry 30 }

h3cDot11WIPSAckStaOverfSsidMalf OBJECT-TYPE
    SYNTAX Integer32
    MAX-ACCESS read-only
    STATUS current
    DESCRIPTION
        "Represents the statistics number of overflow SSID malform."
    ::= { h3cDot11WIPSAckStaEntry 31 }

h3cDot11WIPSAckStaRedundIeMalf OBJECT-TYPE
    SYNTAX Integer32
    MAX-ACCESS read-only
    STATUS current
    DESCRIPTION
        "Represents the statistics number of redundant IE malform."
    ::= { h3cDot11WIPSAckStaEntry 32 }

h3cDot11WIPSAckStaApSpoofAp OBJECT-TYPE
    SYNTAX Integer32
    MAX-ACCESS read-only
    STATUS current
    DESCRIPTION
        "Represents the statistics number of AP spoof AP."
    ::= { h3cDot11WIPSAckStaEntry 33 }

h3cDot11WIPSAckStaApSpoofclt OBJECT-TYPE
    SYNTAX Integer32
    MAX-ACCESS read-only
    STATUS current
    DESCRIPTION
        "Represents the statistics number of AP spoof client."
    ::= { h3cDot11WIPSAckStaEntry 34 }

h3cDot11WIPSAckStaApSpoofAdhoc OBJECT-TYPE
    SYNTAX Integer32
    MAX-ACCESS read-only
    STATUS current
    DESCRIPTION
        "Represents the statistics number of AP spoof adhoc."
    ::= { h3cDot11WIPSAckStaEntry 35 }

h3cDot11WIPSAckStaAdhocSpoofAp OBJECT-TYPE
    SYNTAX Integer32
    MAX-ACCESS read-only
    STATUS current
    DESCRIPTION
        "Represents the statistics number of adhoc spoof AP."
    ::= { h3cDot11WIPSAckStaEntry 36 }

h3cDot11WIPSAckStacltSpoofAp OBJECT-TYPE
    SYNTAX Integer32
    MAX-ACCESS read-only
    STATUS current
    DESCRIPTION
        "Represents the statistics number of client spoof AP."
    ::= { h3cDot11WIPSAckStaEntry 37 }

h3cDot11WIPSAckStaWeakIv OBJECT-TYPE
    SYNTAX Integer32
    MAX-ACCESS read-only
    STATUS current
    DESCRIPTION
        "Represents the statistics number of weak-iv."
    ::= { h3cDot11WIPSAckStaEntry 38 }

h3cDot11WIPSAckStaApRate OBJECT-TYPE
    SYNTAX Integer32
    MAX-ACCESS read-only
    STATUS current
    DESCRIPTION
        "Represents the statistics number of AP rate."
    ::= { h3cDot11WIPSAckStaEntry 39 }

h3cDot11WIPSAckStacltRate OBJECT-TYPE
    SYNTAX Integer32
    MAX-ACCESS read-only
    STATUS current
    DESCRIPTION
        "Represents the statistics number of client rate."
    ::= { h3cDot11WIPSAckStaEntry 40 }

h3cDot11WIPSAckStaSignatureRule OBJECT-TYPE
    SYNTAX Integer32
    MAX-ACCESS read-only
    STATUS current
    DESCRIPTION
        "Represents the statistics number of signature detect."
    ::= { h3cDot11WIPSAckStaEntry 41 }

h3cDot11WIPSAckSta40Mhz OBJECT-TYPE
    SYNTAX Integer32
    MAX-ACCESS read-only
    STATUS current
    DESCRIPTION
        "Represents the statistics number of 40MHZ detect."
    ::= { h3cDot11WIPSAckStaEntry 42 }

h3cDot11WIPSAckStaPowerSave OBJECT-TYPE
    SYNTAX Integer32
    MAX-ACCESS read-only
    STATUS current
    DESCRIPTION
        "Represents the statistics number of power save detect."
    ::= { h3cDot11WIPSAckStaEntry 43 }

h3cDot11WIPSAckStaWinBdg OBJECT-TYPE
    SYNTAX Integer32
    MAX-ACCESS read-only
    STATUS current
    DESCRIPTION
        "Represents the statistics number of window bridge detect."
    ::= { h3cDot11WIPSAckStaEntry 44 }

h3cDot11WIPSAckStaOmerta OBJECT-TYPE
    SYNTAX Integer32
    MAX-ACCESS read-only
    STATUS current
    DESCRIPTION
        "Represents the statistics number of omerta detect."
    ::= { h3cDot11WIPSAckStaEntry 45 }

h3cDot11WIPSAckStaSoftAp OBJECT-TYPE
    SYNTAX Integer32
    MAX-ACCESS read-only
    STATUS current
    DESCRIPTION
        "Represents the statistics number of soft AP detect."
    ::= { h3cDot11WIPSAckStaEntry 46 }

h3cDot11WIPSAckStaBroadDis OBJECT-TYPE
    SYNTAX Integer32
    MAX-ACCESS read-only
    STATUS current
    DESCRIPTION
        "Represents the statistics number of broadcast diassociated detect."
    ::= { h3cDot11WIPSAckStaEntry 47 }

h3cDot11WIPSAckStaBroadDeauth OBJECT-TYPE
    SYNTAX Integer32
    MAX-ACCESS read-only
    STATUS current
    DESCRIPTION
        "Represents the statistics number of broadcast deauthentication detect."
    ::= { h3cDot11WIPSAckStaEntry 48 }

h3cDot11WIPSAckStaApImp OBJECT-TYPE
    SYNTAX Integer32
    MAX-ACCESS read-only
    STATUS current
    DESCRIPTION
        "Represents the statistics number of AP impersonate."
    ::= { h3cDot11WIPSAckStaEntry 49 }

h3cDot11WIPSAckStaHtGreenField OBJECT-TYPE
    SYNTAX Integer32
    MAX-ACCESS read-only
    STATUS current
    DESCRIPTION
        "Represents the statistics number of HT green field."
    ::= { h3cDot11WIPSAckStaEntry 50 }

h3cDot11WIPSAckStaWireBdg OBJECT-TYPE
    SYNTAX Integer32
    MAX-ACCESS read-only
    STATUS current
    DESCRIPTION
        "Represents the statistics number of wireless bridge."
    ::= { h3cDot11WIPSAckStaEntry 51 }

h3cDot11WIPSAckStaApFld OBJECT-TYPE
    SYNTAX Integer32
    MAX-ACCESS read-only
    STATUS current
    DESCRIPTION
        "Represents the statistics number of AP flood."
    ::= { h3cDot11WIPSAckStaEntry 52 }

h3cDot11WIPSAckStaAssociaOverf OBJECT-TYPE
    SYNTAX Integer32
    MAX-ACCESS read-only
    STATUS current
    DESCRIPTION
        "Represents the statistics number of associated overflow."
    ::= { h3cDot11WIPSAckStaEntry 53 }

END

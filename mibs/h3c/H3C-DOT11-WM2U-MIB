-- =============================================================================
-- Copyright (c) 2004-2016 Hangzhou H3C Tech. Co., Ltd.  All rights reserved.
--
-- Description:
--   The file defines a MIB for the wireless multicast to unicast (WM2U) feature,
--   which is used to improve multicast performance.
-- Reference:
-- Version: V1.1
-- History:
--   V1.0 created by sunanzhi
--     Initial version 2015-04-27
--   V1.1 2016-1-25 updated by sunanzhi
--     Modify H3cDot11WM2UAgingTimeEntry
-- =============================================================================
H3C-DOT11-WM2U-MIB DEFINITIONS ::= BEGIN

IMPORTS
    TimeTicks, Unsigned32, OBJECT-TYPE, MODULE-IDENTITY
        FROM SNMPv2-SMI
    MacAddress, TEXTUAL-CONVENTION
        FROM SNMPv2-TC
    InetAddress, InetAddressType
        FROM INET-ADDRESS-MIB   -- [RFC4001]
    h3cDot11
        FROM HUAWEI-3COM-OID-MIB;

h3cDot11WM2U MODULE-IDENTITY
    LAST-UPDATED "201601251020Z"        -- January 25, 2016 at 10:20 GMT
    ORGANIZATION
        "Hangzhou H3C Technologies Co., Ltd."
    CONTACT-INFO
        "Platform Team Hangzhou H3C Technologies Co., Ltd.
        Hai-Dian District Beijing P.R. China
        http://www.h3c.com
        Zip:100085
        "
    DESCRIPTION
        "This MIB provides information about the WM2U feature."
    REVISION "201601251020Z"        -- January 25, 2016 at 10:20 GMT
    DESCRIPTION
        "Modify H3cDot11WM2UAgingTimeEntry."
    REVISION "201503311551Z"        -- March 31, 2015 at 13:51 GMT
    DESCRIPTION
        "The initial revision of this MIB module."
    ::= {  h3cDot11 16 }

--
-- Textual conventions
--
H3cDot11WM2UEnableStatus ::= TEXTUAL-CONVENTION
        STATUS      current
        DESCRIPTION
            "The enable status values for objects.
            Values include enabled and disbaled."
        SYNTAX      INTEGER { enabled(1), disabled(2) }

H3cDot11WM2UAction ::= TEXTUAL-CONVENTION
        STATUS      current
        DESCRIPTION
            "Action to take when the number of clients exceeds the threshold."
        SYNTAX  INTEGER
            {
            drop(1),
            unicast(2),
            multicast(3)
            }

H3cDot11WM2UGroupVersion ::= TEXTUAL-CONVENTION
        STATUS      current
        DESCRIPTION
            "Multicast protocol version."
        SYNTAX  INTEGER
            {
            igmpv1orv2(1),
            igmpv3(2),
            mldv1(3),
            mldv2(4)
            }

H3cDot11WM2UGroupMode ::= TEXTUAL-CONVENTION
        STATUS      current
        DESCRIPTION
            "Multicast source filtering mode."
        SYNTAX  INTEGER
            {
            include(1),
            exclude(2)
            }


--
-- Node definitions
--
h3cDot11WM2UConfigGroup OBJECT IDENTIFIER ::= { h3cDot11WM2U 1 }
h3cDot11WM2UDataGroup OBJECT IDENTIFIER ::= { h3cDot11WM2U 2 }

h3cDot11WM2USrvTempStatesTable OBJECT-TYPE
    SYNTAX SEQUENCE OF H3cDot11WM2USrvTempStatesEntry
    MAX-ACCESS not-accessible
    STATUS current
    DESCRIPTION
        "The table contains the enable status of WM2U in service templates."
    ::= { h3cDot11WM2UConfigGroup 1 }

h3cDot11WM2USrvTempStatesEntry OBJECT-TYPE
    SYNTAX H3cDot11WM2USrvTempStatesEntry
    MAX-ACCESS not-accessible
    STATUS current
    DESCRIPTION
        "Each entry contains the enable status of WM2U in a service template."
    INDEX { h3cDot11WM2USrvTempName,  h3cDot11WM2USrvTempAddressType}
    ::= { h3cDot11WM2USrvTempStatesTable 1 }

H3cDot11WM2USrvTempStatesEntry ::= SEQUENCE {
        h3cDot11WM2USrvTempName                    OCTET STRING,
        h3cDot11WM2USrvTempAddressType                  InetAddressType,
        h3cDot11WM2USrvTempState                   H3cDot11WM2UEnableStatus
     }

h3cDot11WM2USrvTempName OBJECT-TYPE
    SYNTAX OCTET STRING (SIZE (1..63))
    MAX-ACCESS not-accessible
    STATUS current
    DESCRIPTION
        "Represents the name of the service template."
    ::= { h3cDot11WM2USrvTempStatesEntry 1 }

h3cDot11WM2USrvTempAddressType OBJECT-TYPE
    SYNTAX InetAddressType
    MAX-ACCESS not-accessible
    STATUS current
    DESCRIPTION
        "Represents the address type."
    ::= { h3cDot11WM2USrvTempStatesEntry 2 }

h3cDot11WM2USrvTempState OBJECT-TYPE
    SYNTAX H3cDot11WM2UEnableStatus
    MAX-ACCESS read-write
    STATUS current
    DESCRIPTION
        "The enable status of WM2U."
    ::= { h3cDot11WM2USrvTempStatesEntry 3 }

h3cDot11WM2UAgingTimeTable OBJECT-TYPE
    SYNTAX SEQUENCE OF H3cDot11WM2UAgingTimeEntry
    MAX-ACCESS not-accessible
    STATUS current
    DESCRIPTION
        "The table contains WM2U entry aging information."
    ::= { h3cDot11WM2UConfigGroup 2 }

h3cDot11WM2UAgingTimeEntry OBJECT-TYPE
    SYNTAX H3cDot11WM2UAgingTimeEntry
    MAX-ACCESS not-accessible
    STATUS current
    DESCRIPTION
        "Each entry contains the aging time for an address type."
    INDEX { h3cDot11WM2UAgingAddressType }
    ::= { h3cDot11WM2UAgingTimeTable 1 }

H3cDot11WM2UAgingTimeEntry ::= SEQUENCE {
        h3cDot11WM2UAgingAddressType                    InetAddressType,
        h3cDot11WM2UAgingTime                           Unsigned32,
        h3cDot11WM2UAgingTimeState                      H3cDot11WM2UEnableStatus
     }

h3cDot11WM2UAgingAddressType OBJECT-TYPE
    SYNTAX InetAddressType
    MAX-ACCESS not-accessible
    STATUS current
    DESCRIPTION
        "Represents the address type."
    ::= { h3cDot11WM2UAgingTimeEntry 1 }

h3cDot11WM2UAgingTime OBJECT-TYPE
    SYNTAX Unsigned32 (60..3600)
    UNITS   "seconds"
    MAX-ACCESS read-write
    STATUS current
    DESCRIPTION
        "Represents the aging time."
    ::= { h3cDot11WM2UAgingTimeEntry 2 }

h3cDot11WM2UAgingTimeState OBJECT-TYPE
    SYNTAX H3cDot11WM2UEnableStatus
    MAX-ACCESS read-write
    STATUS current
    DESCRIPTION
        "The configuration status of the aging time."
    ::= { h3cDot11WM2UAgingTimeEntry 3 }

h3cDot11WM2UClientEtyLmtTable OBJECT-TYPE
    SYNTAX SEQUENCE OF H3cDot11WM2UClientEtyLmtEntry
    MAX-ACCESS not-accessible
    STATUS current
    DESCRIPTION
        "The table contains the WM2U entry limit for each client."
    ::= { h3cDot11WM2UConfigGroup 3 }

h3cDot11WM2UClientEtyLmtEntry OBJECT-TYPE
    SYNTAX H3cDot11WM2UClientEtyLmtEntry
    MAX-ACCESS not-accessible
    STATUS current
    DESCRIPTION
        "Each entry contains the WM2U entry limit for each client of an
        address type."
    INDEX { h3cDot11WM2UClientEtyAddrType }
    ::= { h3cDot11WM2UClientEtyLmtTable 1 }

H3cDot11WM2UClientEtyLmtEntry ::= SEQUENCE {
        h3cDot11WM2UClientEtyAddrType                InetAddressType,
        h3cDot11WM2UClientValue                         Unsigned32,
        h3cDot11WM2UClientState                         H3cDot11WM2UEnableStatus
     }

h3cDot11WM2UClientEtyAddrType OBJECT-TYPE
    SYNTAX InetAddressType
    MAX-ACCESS not-accessible
    STATUS current
    DESCRIPTION
        "Represents the address type."
    ::= { h3cDot11WM2UClientEtyLmtEntry 1 }

h3cDot11WM2UClientValue OBJECT-TYPE
    SYNTAX Unsigned32 (8..1024)
    MAX-ACCESS read-write
    STATUS current
    DESCRIPTION
        "Maximum number of WM2U entries for each client of the address type."
    ::= { h3cDot11WM2UClientEtyLmtEntry 2 }

h3cDot11WM2UClientState OBJECT-TYPE
    SYNTAX H3cDot11WM2UEnableStatus
    MAX-ACCESS read-write
    STATUS current
    DESCRIPTION
        "The enable status of the per-client WM2U entry limit."
    ::= { h3cDot11WM2UClientEtyLmtEntry 3 }

h3cDot11WM2UGlobalEtyLmtTable OBJECT-TYPE
    SYNTAX SEQUENCE OF H3cDot11WM2UGlobalEntryLmtsEntry
    MAX-ACCESS not-accessible
    STATUS current
    DESCRIPTION
        "The table contains the WM2U table size."
    ::= { h3cDot11WM2UConfigGroup 4 }

h3cDot11WM2UGlobalEtyLmtEntry OBJECT-TYPE
    SYNTAX H3cDot11WM2UGlobalEntryLmtsEntry
    MAX-ACCESS not-accessible
    STATUS current
    DESCRIPTION
        "Each entry contains the WM2U table size for an address type."
    INDEX { h3cDot11WM2UGlobalEtyAddrType }
    ::= { h3cDot11WM2UGlobalEtyLmtTable 1 }

H3cDot11WM2UGlobalEntryLmtsEntry ::= SEQUENCE {
        h3cDot11WM2UGlobalEtyAddrType                InetAddressType,
        h3cDot11WM2UGlobalValue                         Unsigned32,
        h3cDot11WM2UGlobalState                         H3cDot11WM2UEnableStatus
     }

h3cDot11WM2UGlobalEtyAddrType OBJECT-TYPE
    SYNTAX InetAddressType
    MAX-ACCESS not-accessible
    STATUS current
    DESCRIPTION
        "Represents the address type."
    ::= { h3cDot11WM2UGlobalEtyLmtEntry 1 }

h3cDot11WM2UGlobalValue OBJECT-TYPE
    SYNTAX Unsigned32 (8..8192)
    MAX-ACCESS read-write
    STATUS current
    DESCRIPTION
        "WM2U table size(The maximum number of entries that the WM2U table
        can contain)."
    ::= { h3cDot11WM2UGlobalEtyLmtEntry 2 }

h3cDot11WM2UGlobalState OBJECT-TYPE
    SYNTAX H3cDot11WM2UEnableStatus
    MAX-ACCESS read-write
    STATUS current
    DESCRIPTION
        "The enable status of the WM2U table size setting."
    ::= { h3cDot11WM2UGlobalEtyLmtEntry 3 }

h3cDot11WM2UFwdClientLmtsTable OBJECT-TYPE
    SYNTAX SEQUENCE OF H3cDot11WM2UFwdClientLmtsEntry
    MAX-ACCESS not-accessible
    STATUS current
    DESCRIPTION
        "The table contains the limit on the number of clients of each address
        type in the WM2U table."
    ::= { h3cDot11WM2UConfigGroup 5 }

h3cDot11WM2UFwdClientLmtsEntry OBJECT-TYPE
    SYNTAX H3cDot11WM2UFwdClientLmtsEntry
    MAX-ACCESS not-accessible
    STATUS current
    DESCRIPTION
        "Each entry contains the limit on the number of clients of an address
        type in the WM2U table."
    INDEX { h3cDot11WM2UFwdClientAddrType }
    ::= { h3cDot11WM2UFwdClientLmtsTable 1 }

H3cDot11WM2UFwdClientLmtsEntry ::= SEQUENCE {
        h3cDot11WM2UFwdClientAddrType                InetAddressType,
        h3cDot11WM2UFwdClientValue                      Unsigned32,
        h3cDot11WM2UFwdClientAction                     H3cDot11WM2UAction,
        h3cDot11WM2UFwdClientState                      H3cDot11WM2UEnableStatus
     }

h3cDot11WM2UFwdClientAddrType OBJECT-TYPE
    SYNTAX InetAddressType
    MAX-ACCESS not-accessible
    STATUS current
    DESCRIPTION
        "Represents the address type."
    ::= { h3cDot11WM2UFwdClientLmtsEntry 1 }

h3cDot11WM2UFwdClientValue OBJECT-TYPE
    SYNTAX Unsigned32 (1..256)
    MAX-ACCESS read-write
    STATUS current
    DESCRIPTION
        "Limit on the number of clients of the address type."
    ::= { h3cDot11WM2UFwdClientLmtsEntry 2 }

h3cDot11WM2UFwdClientAction OBJECT-TYPE
    SYNTAX H3cDot11WM2UAction
    MAX-ACCESS read-write
    STATUS current
    DESCRIPTION
        "Action to take when the number of clients exceeds the limit."
    ::= { h3cDot11WM2UFwdClientLmtsEntry 3 }

h3cDot11WM2UFwdClientState OBJECT-TYPE
    SYNTAX H3cDot11WM2UEnableStatus
    MAX-ACCESS read-write
    STATUS current
    DESCRIPTION
        "The enable status of the client limit."
    ::= { h3cDot11WM2UFwdClientLmtsEntry 4 }

h3cDot11WM2URateLimitsTable OBJECT-TYPE
    SYNTAX SEQUENCE OF H3cDot11WM2URateLimitsEntry
    MAX-ACCESS not-accessible
    STATUS current
    DESCRIPTION
        "The table contains multicast packet rate limit information."
    ::= { h3cDot11WM2UConfigGroup 6 }

h3cDot11WM2URateLimitsEntry OBJECT-TYPE
    SYNTAX H3cDot11WM2URateLimitsEntry
    MAX-ACCESS not-accessible
    STATUS current
    DESCRIPTION
        "Each entry contains the packet rate limit for an address type."
    INDEX { h3cDot11WM2URateLmtsAddrType }
    ::= { h3cDot11WM2URateLimitsTable 1 }

H3cDot11WM2URateLimitsEntry ::= SEQUENCE {
        h3cDot11WM2URateLmtsAddrType                 InetAddressType,
        h3cDot11WM2UInterval                            Unsigned32,
        h3cDot11WM2UThreshold                           Unsigned32,
        h3cDot11WM2URateLmtsState                       H3cDot11WM2UEnableStatus
     }

h3cDot11WM2URateLmtsAddrType OBJECT-TYPE
    SYNTAX InetAddressType
    MAX-ACCESS not-accessible
    STATUS current
    DESCRIPTION
        "Represents the address type."
    ::= { h3cDot11WM2URateLimitsEntry 1 }

h3cDot11WM2UInterval OBJECT-TYPE
    SYNTAX Unsigned32 (60..3600)
    UNITS  "seconds"
    MAX-ACCESS read-write
    STATUS current
    DESCRIPTION
        "Interval for calculating the incoming multicast packet rate,
         unit for seconds."
    ::= { h3cDot11WM2URateLimitsEntry 2 }

h3cDot11WM2UThreshold OBJECT-TYPE
    SYNTAX Unsigned32 (1..100000)
    MAX-ACCESS read-write
    STATUS current
    DESCRIPTION
        "Threshold on the number of multicast packets received over the
        specified interval."
    ::= { h3cDot11WM2URateLimitsEntry 3 }

h3cDot11WM2URateLmtsState OBJECT-TYPE
    SYNTAX H3cDot11WM2UEnableStatus
    MAX-ACCESS read-write
    STATUS current
    DESCRIPTION
        "The enable status of IGMP packet rate limiting."
    ::= { h3cDot11WM2URateLimitsEntry 4 }

h3cDot11WM2UClientsTable OBJECT-TYPE
    SYNTAX SEQUENCE OF H3cDot11WM2UClientsEntry
    MAX-ACCESS not-accessible
    STATUS current
    DESCRIPTION
        "The table contains WM2U client information."
    ::= { h3cDot11WM2UDataGroup 1 }

h3cDot11WM2UClientsEntry OBJECT-TYPE
    SYNTAX H3cDot11WM2UClientsEntry
    MAX-ACCESS not-accessible
    STATUS current
    DESCRIPTION
        "Each entry contains information about a client."
    INDEX { h3cDot11WM2UClientMacAddress }
    ::= { h3cDot11WM2UClientsTable 1 }

H3cDot11WM2UClientsEntry ::= SEQUENCE {
        h3cDot11WM2UClientMacAddress                    MacAddress,
        h3cDot11WM2UDuration                            TimeTicks,
        h3cDot11WM2UGroupNum4                           Unsigned32,
        h3cDot11WM2UGroupNum6                           Unsigned32
     }

h3cDot11WM2UClientMacAddress OBJECT-TYPE
    SYNTAX MacAddress
    MAX-ACCESS not-accessible
    STATUS current
    DESCRIPTION
        "Client MAC address."
    ::= { h3cDot11WM2UClientsEntry 1 }

h3cDot11WM2UDuration OBJECT-TYPE
    SYNTAX TimeTicks
    MAX-ACCESS read-only
    STATUS current
    DESCRIPTION
        "The amount of time that has elapsed since the client was discovered."
    ::= { h3cDot11WM2UClientsEntry 2 }

h3cDot11WM2UGroupNum4 OBJECT-TYPE
    SYNTAX Unsigned32
    MAX-ACCESS read-only
    STATUS current
    DESCRIPTION
        "The number of IGMP multicast groups that the client has joined."
    ::= { h3cDot11WM2UClientsEntry 3 }

h3cDot11WM2UGroupNum6 OBJECT-TYPE
    SYNTAX Unsigned32
    MAX-ACCESS read-only
    STATUS current
    DESCRIPTION
        "The number of MLD multicast groups that the client has joined."
    ::= { h3cDot11WM2UClientsEntry 4 }

h3cDot11WM2UGroupsTable OBJECT-TYPE
    SYNTAX SEQUENCE OF H3cDot11WM2UGroupsEntry
    MAX-ACCESS not-accessible
    STATUS current
    DESCRIPTION
        "The table contains WM2U group information."
    ::= { h3cDot11WM2UDataGroup 2 }

h3cDot11WM2UGroupsEntry OBJECT-TYPE
    SYNTAX H3cDot11WM2UGroupsEntry
    MAX-ACCESS not-accessible
    STATUS current
    DESCRIPTION
        "Each entry contains information about each group."
    INDEX { h3cDot11WM2UGrpMacAddress, h3cDot11WM2UGrpAddressType, h3cDot11WM2UAddress }
    ::= { h3cDot11WM2UGroupsTable 1 }

H3cDot11WM2UGroupsEntry ::= SEQUENCE {
        h3cDot11WM2UGrpMacAddress                       MacAddress,
        h3cDot11WM2UGrpAddressType                      InetAddressType,
        h3cDot11WM2UAddress                             InetAddress,
        h3cDot11WM2UVersion                             H3cDot11WM2UGroupVersion,
        h3cDot11WM2UMode                                H3cDot11WM2UGroupMode,
        h3cDot11WM2USourceNum                           Unsigned32,
        h3cDot11WM2UGrpDurLastRefTime                   TimeTicks
     }

h3cDot11WM2UGrpMacAddress OBJECT-TYPE
    SYNTAX MacAddress
    MAX-ACCESS not-accessible
    STATUS current
    DESCRIPTION
        "Client MAC address."
    ::= { h3cDot11WM2UGroupsEntry 1 }

h3cDot11WM2UGrpAddressType OBJECT-TYPE
    SYNTAX InetAddressType
    MAX-ACCESS not-accessible
    STATUS current
    DESCRIPTION
        "Represents the address type."
    ::= { h3cDot11WM2UGroupsEntry 2 }

h3cDot11WM2UAddress OBJECT-TYPE
    SYNTAX InetAddress
    MAX-ACCESS not-accessible
    STATUS current
    DESCRIPTION
        "Multicast group address."
    ::= { h3cDot11WM2UGroupsEntry 3 }

h3cDot11WM2UVersion OBJECT-TYPE
    SYNTAX H3cDot11WM2UGroupVersion
    MAX-ACCESS read-only
    STATUS current
    DESCRIPTION
        "The version of the group."
    ::= { h3cDot11WM2UGroupsEntry 4 }

h3cDot11WM2UMode OBJECT-TYPE
    SYNTAX H3cDot11WM2UGroupMode
    MAX-ACCESS read-only
    STATUS current
    DESCRIPTION
        "The source filtering mode of the group."
    ::= { h3cDot11WM2UGroupsEntry 5 }

h3cDot11WM2USourceNum OBJECT-TYPE
    SYNTAX Unsigned32
    MAX-ACCESS read-only
    STATUS current
    DESCRIPTION
        "The number of multicast sources."
    ::= { h3cDot11WM2UGroupsEntry 6 }

h3cDot11WM2UGrpDurLastRefTime OBJECT-TYPE
    SYNTAX TimeTicks
    MAX-ACCESS read-only
    STATUS current
    DESCRIPTION
        "The amount of time that has elapsed since the multicast group
        entry was created."
    ::= { h3cDot11WM2UGroupsEntry 7 }

h3cDot11WM2USourcesTable OBJECT-TYPE
    SYNTAX SEQUENCE OF H3cDot11WM2USourcesEntry
    MAX-ACCESS not-accessible
    STATUS current
    DESCRIPTION
        "The table contains WM2U source information."
    ::= { h3cDot11WM2UDataGroup 3 }

h3cDot11WM2USourcesEntry OBJECT-TYPE
    SYNTAX H3cDot11WM2USourcesEntry
    MAX-ACCESS not-accessible
    STATUS current
    DESCRIPTION
        "Each entry contains information about a multicast source."
    INDEX { h3cDot11WM2USrcMacAddress, h3cDot11WM2USrcAddressType, h3cDot11WM2UGroupAddress, h3cDot11WM2USourceAddress }
    ::= { h3cDot11WM2USourcesTable 1 }

H3cDot11WM2USourcesEntry ::= SEQUENCE {
        h3cDot11WM2USrcMacAddress                       MacAddress,
        h3cDot11WM2USrcAddressType                      InetAddressType,
        h3cDot11WM2UGroupAddress                        InetAddress,
        h3cDot11WM2USourceAddress                       InetAddress,
        h3cDot11WM2USrcDurLastRefTime                   TimeTicks
     }

h3cDot11WM2USrcMacAddress OBJECT-TYPE
    SYNTAX MacAddress
    MAX-ACCESS not-accessible
    STATUS current
    DESCRIPTION
        "Client MAC address."
    ::= { h3cDot11WM2USourcesEntry 1 }

h3cDot11WM2USrcAddressType OBJECT-TYPE
    SYNTAX InetAddressType
    MAX-ACCESS not-accessible
    STATUS current
    DESCRIPTION
        "Represents the address type."
    ::= { h3cDot11WM2USourcesEntry 2 }

h3cDot11WM2UGroupAddress OBJECT-TYPE
    SYNTAX InetAddress
    MAX-ACCESS not-accessible
    STATUS current
    DESCRIPTION
        "Multicast group address."
    ::= { h3cDot11WM2USourcesEntry 3 }

h3cDot11WM2USourceAddress OBJECT-TYPE
    SYNTAX InetAddress
    MAX-ACCESS not-accessible
    STATUS current
    DESCRIPTION
        "Source address."
    ::= { h3cDot11WM2USourcesEntry 4 }

h3cDot11WM2USrcDurLastRefTime OBJECT-TYPE
    SYNTAX TimeTicks
    MAX-ACCESS read-only
    STATUS current
    DESCRIPTION
        "The amount of time that has elapsed since the source was added
        to the multicast group."
    ::= { h3cDot11WM2USourcesEntry 5 }

END

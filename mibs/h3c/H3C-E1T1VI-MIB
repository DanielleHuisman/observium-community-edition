-- =============================================================
-- Copyright (c) 2004-2015 Hangzhou H3C Tech. Co., Ltd. All rights reserved.
--
-- Description: E1T1VI MIB
-- Reference:
-- Version: V1.3
-- History:
--   V1.0 2007-04-05 Initial Version by yandehan
--   V1.1 2009-06-08 modified by TONGWEI
--        Added h3cE1T1VIUsingTimeslotsRatio
--          and h3cE1T1VINotifications
--   V1.2 2010-04-08 modified by TONGWEI
--        Added h3cE1T1VIGeneral
--   V1.3 2015-08-19 modified by YUHAIYAN
--        Added h3cE1T1VITimeslotsUsedUpCount
--          and h3cE1T1VITimeslotSampleInterval
--          and h3cE1T1VIUsingTimeslotsPeak
--          and h3cE1T1VITrapTimeSlotsThreshold
--       Modified h3cE1T1VITrapTimeSlot
-- =============================================================
H3C-E1T1VI-MIB DEFINITIONS ::= BEGIN
    IMPORTS
        MODULE-IDENTITY, OBJECT-TYPE, Integer32, Unsigned32, NOTIFICATION-TYPE
            FROM SNMPv2-SMI
        ifIndex ,ifDescr
            FROM IF-MIB
        h3cCommon
            FROM HUAWEI-3COM-OID-MIB;


-- =============================================================
-- E1T1VI Module
-- =============================================================
h3cE1T1VI MODULE-IDENTITY
    LAST-UPDATED    "201508191800Z"         -- Aug. 19, 2015 at 18:00 GMT
    ORGANIZATION
        "Hangzhou H3C Technologies Co., Ltd."
    CONTACT-INFO
        "Platform Team H3C Technologies Co., Ltd.
         Hai-Dian District Beijing P.R. China
         http://www.h3c.com
         Zip: 100085"
    DESCRIPTION
        "This MIB provides E1/T1 voice interface information that are
        excluded by RFC 1213 and RFC 2233"
    REVISION        "201508191800Z"
    DESCRIPTION
        "Added h3cE1T1VITimeslotsUsedUpCount
         and h3cE1T1VITimeslotSampleInterval
         and h3cE1T1VIUsingTimeslotsPeak
         and h3cE1T1VITrapTimeSlotThreshold
         Modified h3cE1T1VITrapTimeSlot"
    REVISION        "201004081855Z"
    DESCRIPTION
        "To fix bugs in the MIB file."
    REVISION        "200906081741Z"
    DESCRIPTION
        "To fix bugs in the MIB file."
    REVISION        "200704051542Z"
    DESCRIPTION
        "Initial version of this MIB module."
    ::= { h3cCommon 76 }


h3cE1T1VITable OBJECT-TYPE
    SYNTAX      SEQUENCE OF H3cE1T1VIEntry
    MAX-ACCESS  not-accessible
    STATUS      current
    DESCRIPTION
        "This table contains E1/T1 voice interface information,
        such as the total number of using time slot."
    ::= { h3cE1T1VI 1 }

h3cE1T1VIEntry OBJECT-TYPE
    SYNTAX      H3cE1T1VIEntry
    MAX-ACCESS  not-accessible
    STATUS      current
    DESCRIPTION
        "This entry contains E1/T1 voice interface information.
        The index of this Entry is ifIndex defined in ifTable
        of RFC1213-MIB."
    INDEX
        {
            ifIndex
        }
    ::= { h3cE1T1VITable 1 }

H3cE1T1VIEntry ::= SEQUENCE
    {
        h3cE1T1VIUsingTimeslots    Integer32,
        h3cE1T1VIUsingTimeslotsRatio    Integer32,
        h3cE1T1VITimeslotsUsedUpCount    Unsigned32,
        h3cE1T1VITimeslotSampleInterval    Integer32,
        h3cE1T1VIUsingTimeslotsPeak    Integer32,
        h3cE1T1VITrapTimeSlotsThreshold    Integer32
    }

h3cE1T1VIUsingTimeslots OBJECT-TYPE
    SYNTAX      Integer32
    MAX-ACCESS  read-only
    STATUS      current
    DESCRIPTION
        "The total number of using time slots on this interface."
    ::= { h3cE1T1VIEntry 1 }

h3cE1T1VIUsingTimeslotsRatio OBJECT-TYPE
    SYNTAX      Integer32
    MAX-ACCESS  read-only
    STATUS      current
    DESCRIPTION
        "The total ratio of using time slots on this interface."
    ::= { h3cE1T1VIEntry 2 }

h3cE1T1VITimeslotsUsedUpCount OBJECT-TYPE
    SYNTAX      Unsigned32
    MAX-ACCESS  read-only
    STATUS      current
    DESCRIPTION
        "Total number of times that all time slots were used up on this interface."
    ::= { h3cE1T1VIEntry 3 }

h3cE1T1VITimeslotSampleInterval OBJECT-TYPE
    SYNTAX      Integer32
    MAX-ACCESS  read-write
    STATUS      current
    DESCRIPTION
        "Sampling interval in seconds for used time slots on this interface."
    ::= { h3cE1T1VIEntry 4 }

h3cE1T1VIUsingTimeslotsPeak OBJECT-TYPE
    SYNTAX      Integer32
    MAX-ACCESS  read-only
    STATUS      current
    DESCRIPTION
        "The peak number of used time slots in the entire sampling period on this interface."
    ::= { h3cE1T1VIEntry 5 }

h3cE1T1VITrapTimeSlotsThreshold OBJECT-TYPE
    SYNTAX      Integer32
    MAX-ACCESS  read-write
    STATUS      current
    DESCRIPTION
        "When the number of used time slots reaches the threshold, the h3cE1T1VITrapTimeSlot trap will
         be sent.  The valid range is from 1 to total number of time slots on the interface."
    ::= { h3cE1T1VIEntry 6 }


h3cE1T1VINotifications OBJECT IDENTIFIER ::= { h3cE1T1VI 2 }
h3cE1T1VITrapPrefix    OBJECT IDENTIFIER ::= { h3cE1T1VINotifications 0 }

h3cE1T1VITrapTimeSlot NOTIFICATION-TYPE
    OBJECTS { ifIndex, ifDescr }
    STATUS current
    DESCRIPTION
        "This trap is sent to the manager under the following
         condition: The number of used time slots of an E1/T1
         interface reaches the threshold."
    ::= { h3cE1T1VITrapPrefix 1 }

h3cE1T1VIGeneral  OBJECT IDENTIFIER ::= { h3cE1T1VI 3 }

h3cE1T1VITrapTimeSlotEnable OBJECT-TYPE
    SYNTAX  INTEGER {
            enable(1),
            disable(2)
        }
    MAX-ACCESS  read-write
    STATUS      current
    DESCRIPTION
        "This attribute controls whether the h3cE1T1VITrapTimeSlot trap will
        be sent or not."
    DEFVAL { enable }
    ::= { h3cE1T1VIGeneral 1 }

END

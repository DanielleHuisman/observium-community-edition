-- =================================================================
-- Copyright (c) 2004-2018 Hangzhou H3C Tech. Co., Ltd.  All rights reserved.
--
-- Description: The definition of Entity Vendortype OID
-- Reference:
-- Version: V4.68
-- History:
-- V1.0 2004.05.13  Created by lvzhenfeng, modified by gaolong.
-- V1.1 2004.05.22  Adjusted by gaolong and lvzhenfeng.
--   1. Adjust module name to h3cEntityVendorTypeOID and its location is set to { h3c 3 }.
--   2. Rename module name prefix from h3cevtModule to h3cevtModuleRt_
--   and h3cevtModuleSw_ for routers and switches seperately.
--   3. Add h3cevtSubModuleRouter and h3cevtSubModuleSwitch under h3cevtModule.
--   4. Split port type into two groups, one for routers, another for switches.
-- V1.11 2004-06-17 add h3cevtHotSwapFan node by limeng for garibaldi
-- V1.12 2004-07-19 add h3cevtModuleSwitchType {117-138}
-- V1.13 2004-07-29 add h3cevtPortSwitchType {50-58}
-- V1.14 2004-08-12 add h3cevtModuleSw_LSA1FP8U(h3cevtModuleSwitchType 139)
-- V1.15 2004-08-25 change enumeration name
--                     from h3cevtModuleSw_LS81SFCA(120) to h3cevtModuleSw_LS81SRPG0(120),
--                     from h3cevtModuleSw_LS81SFCB(121) to h3cevtModuleSw_LS81SRPG1(121),
--                     from h3cevtModuleSw_LS81SFCC(122) to h3cevtModuleSw_LS81SRPG2(122),
--                     from h3cevtModuleSw_LS81SFCD(123) to h3cevtModuleSw_LS81SRPG3(123).
--                  modify comments for these enumerations as well.
-- V1.2  2004-08-26 add sub identifier of h3cevtPortSwitchType from 59 to 71.
-- V1.21 2004-09-08 add sub identifier of h3cevtModuleSwitchType from 140 to 148.
-- V1.3  2004-09-14 add subidentifier under h3cevtModuleSwitchType from 149 to 157 by wangyahui
--                  add subidentifier under h3cevtModuleSwitchType from 158 to 159 by kangyinan
--                  add subidentifier under h3cevtModuleSwitchType from 72 to 93 by wangyahui
--                  add subidentifier under h3cevtModuleSwitchType from 94 to 96 by kangyinan
--                  add type description for h3cevtModuleSw_SP4, h3cevtModuleSw_UP1, h3cevtModuleSw_XP4 by kangyinan
-- V2.0  2004-10-12 updated by gaolong
--                  Change all underscore('_') characters to hyphen characters('-') because underscore character is not allowed in MIB module.
--                  Remove some adjacent hyphens
-- V2.1  2004-10-19 add subidentifier under h3cevtModuleSwitchType from 160 to 162 by kangyinan
--                  add subidentifier under h3cevtPortSwitchType 97 by kangyinan
-- V2.2  2004-09-18 add sub identifier for h3cevtModuleRouterType from 111 to 117 by taotao
-- V2.3  2004-11-18 add sub identifier 2 under h3cevtFan by liyutao
-- V2.4  2004-11-23 add subidentifier under h3cevtModuleSwitchType from 163 to 166 by zhangchengmei
-- V2.5  2004-12-04 add subidentifier 118 under h3cevtModuleRouterType by lizhiyong
-- V2.6  2004-12-23 add sub identifier 4 to 7 under h3cevtPowerSupply by Zhangjianfeng
--                  add sub identifier 167 to 169 under h3cevtModuleSwitchType by Zhangjianfeng
-- V2.7  2004-12-26 add subidentifier 170 under h3cevtModuleSwitchType by wangyahui
-- v2.8  2004-12-23 add subidentifier under h3cevtModuleSwitchType from 171 to 172 and
--                  add sub identifier 98 to 99 under h3cevtPortSwitchType by liyue
-- V2.9  2004-12-26 add sub identifier 173 under h3cevtModuleSwitchType by Zhangjianfeng
--                  add sub identifier 100 for 24G cascade port under h3cevtPort by Zhangjianfeng
-- V3.0  2004-01-07 add subidentifier 174 and 175 under h3cevtModuleSwitchType by wangyahui
-- V3.1  2005-01-31 add subidentifier 176 under h3cevtModuleSwitchType by wangyahui
-- V3.2  2005-02-26 add subidentifier 177 under h3cevtModuleSwitchType by zhangchengmei
--                  add subidentifier 101 to 137 under h3cevtPortSwitchType by zhangchengmei
--                  add subidentifier 178 under h3cevtModuleSwitchType by zhouqiang
--                  add subidentifier 138 under h3cevtPortSwitchType by zhouqiang
--                  add subidentifier 179 to 180 under h3cevtModuleSwitchType by wangyahui
--                  remove trailing spaces
-- V3.3  2005-03-22 add subidentifier 181 to 187 under h3cevtModuleSwitchType by zhangchengmei
-- V3.4  2004-12-29 add subidentifier 119 to 120 under h3cevtModuleRouterType by lizhiyong
-- V3.5  2005-04-12 add subidentifier 141 to 144 under h3cevtModuleRouterType by yinxiaoyu
--                  add subidentifier 30 to 33 under h3cevtPortRouterType by yinxiaoyu
-- V3.6  2005-04-07 add subidentifier 121 to 140 under h3cevtModuleRouterType by taotao
--                  change the name of subidentifier 118 under h3cevtModuleRouterType by taotao
--                  adjust file format
-- V3.7  2005-05-10 add subidentifier 188 to 216 under h3cevtModuleSwitchType by zhangchengmei
-- V3.8  2005-06-12 add subidentifier 145 to 149 under h3cevtModuleRouterType,
--                  add subidentifier 34 under h3cevtPortRouterType by wanghanlin
-- V3.9  2005-06-22 add subidentifier 150 under h3cevtModuleRouterType by yinxiaoyu
-- V4.0  2005-07-18 add subidentifier 217 to 219 under h3cevtModuleSwitchType by yangliming
--                  add subidentifier 139 to 142 under h3cevtPortSwitchType by wangyahui
-- V4.01 2005-07-29 add subidentifier 220 to 225 under h3cevtModuleSwitchType by wangyahui
-- V4.02 2005-07-21 change the name of subidentifier 183 under h3cevtModuleSwitchType,
--                  add subidentifier 226 to 227 under h3cevtModuleSwitchType by zhangchengmei
--       2005-08-29 add subidentifier 143 under h3cevtPortSwitchType by qianxiaoyu
--                  add subidentifier 151 to 161 under h3cevtModuleRouterType by taotao
--                  add subidentifier 35 to 41 under h3cevtPortRouterType by taotao
-- V4.03 2005-09-07 add h3cevtCPU and h3cevtGeneralCPU by taotao
--                  add subidentifier 162 to 163 under h3cevtModuleRouterType by taotao
--                  adjust file format by gaolong
-- V4.04 2005-09-13 add subidentifier 228 to 253 under h3cevtModuleSwitchType by zhangchengmei
--       2005-09-13 add subidentifier 257 to 268 under h3cevtModuleSwitchType by zhangchengmei
-- V4.05 2005-11-04 add subidentifier 144 to 149 under h3cevtPortSwitchType by zhangchengmei
--                  add subidentifier 150 under h3cevtPortSwitchType by huangyuetao
--                  add subidentifier 269 to 271 under h3cevtModuleSwitchType by yangxiaopeng
--                  add subidentifier 272 under h3cevtModuleSwitchType by qianxiaoyu
--                  add subidentifier 164 to 165 under h3cevtModuleRouterType by xuejiayong
-- V4.06 2005-11-24 add subidentifier 500 to 501 under h3cevtModuleSwitchType by wangyahui
-- V4.07 2005-11-28 add subidentifier 300 to 316 under h3cevtModuleSwitchType by zhangchengmei
-- V4.08 2005-12-09 add subidentifier 220 to 223 under h3cevtModuleRouterType by taotao
-- V4.09 2005-12-30 add subidentifier 151 to 170 under h3cevtPortSwitchType by zhangchengmei
-- V4.10 2006-01-04 add subidentifier 701 under h3cevtModuleSwitchType by qianxiaoyu
-- V4.11 2006-02-12 add subidentifier 200 to 219 under h3cevtModuleRouterType by liutinghai
--                  add subidentifier 702 under h3cevtModuleSwitchType by chenxiaohui
--                  add subidentifier 600 under h3cevtModuleRouterType by qujin
--                  add subidentifier 317 under h3cevtModuleSwitchType by zhangchengmei
-- V4.12 2006-02-24 add subidentifier 703 under h3cevtModuleSwitchType by chijuntao
--                  add subidentifier 224 to 228 under h3cevtModuleRouterType by taotao
-- V4.13 2006-02-27 add subidentifier 171 to 174 under h3cevtPortSwitchType by wangshunli
--                  add subidentifier 318 to 336 under h3cevtModuleSwitchType by zhaiyingying
-- V4.14 2006-03-14 add subidentifier 175 under h3cevtPortSwitchType by wangyahui
--                  add subidentifier 502 to 504 under h3cevtModuleSwitchType by wangyahui
-- V4.15 2006-04-03 add subidentifier 176 under h3cevtPortSwitchType by wangyahui
-- V4.16 2006-04-26 add subidentifier 229 to 233 under h3cevtModuleRouterType by taotao
-- V4.17 2006-04-21 add subidentifier 337 to 340 under h3cevtModuleSwitchType by zhaiyingying
-- V4.18 2006-06-05 add subidentifier 704 to 705 under h3cevtModuleSwitchType by zhangxianguo
--                  add subidentifier 505 to 506 under h3cevtModuleSwitchType by zhangjianfeng
--                  add subidentifier 341 to 349 under h3cevtModuleSwitchType by zhaiyingying
--                  add subidentifier 177 to 178 under h3cevtPortSwitchType by zhangjianfeng
--                  add subidentifier 179 to 180 under h3cevtPortSwitchType by zhangxianguo
-- V4.19 2006-08-23 add subidentifier 507 to 509 under h3cevtModuleSwitchType by wangyahui
--                  modify object name of subidentifier 502 and 503 under h3cevtModuleSwitchType by wangyahui
--                  add subidentifier 234 to 235 under h3cevtModuleRouterType by liutinghai
--                  add subidentifier 350 to 357 under h3cevtModuleSwitchType by zhaiyingying
-- V4.20 2006-09-26 add subidentifier 510 to 514 under h3cevtModuleSwitchType by wangyahui
--                  add subidentifier 601 to 603 under h3cevtModuleRouterType by zhoujianming
--                  add subidentifier 236 to 239 under h3cevtModuleRouterType by qikai
--                  add subidentifier 240 to 241 under h3cevtModuleRouterType by liutinghai
--                  add subidentifier 800 to 801 under h3cevtModuleSwitchType by luoguixing
-- V4.21 2006-10-26 add subidentifier 358 to 370 under h3cevtModuleSwitchType by zhaiyingying
--                  add subidentifier 183 under h3cevtPortSwitchType by zhaiyingying
--                  add subidentifier 515 to 526 under h3cevtModuleSwitchType by wangyahui
--                  add subidentifier 181 to 182 under h3cevtPortSwitchType by wangyahui
-- V4.22 2006-11-02 add subidentifier 527 to 536 under h3cevtModuleSwitchType by wangyahui
--                  modify description of 511 to 513 under h3cevtModuleSwitchType by wangyahui
--       2006-11-10 add subidentifier 371 to 378 under h3cevtModuleSwitchType by shuxiongtao
--       2006-11-08 add subidentifier 184 to 185 under h3cevtPortSwitchType by zhaiyingying
-- V4.23 2006-12-04 add subidentifier 242 to 243 under h3cevtModuleRouterType by liutinghai
-- V4.24 2006-01-24 add subidentifier 244 to 245 under h3cevtModuleRouterType by liutinghai
-- V4.25 2007-03-19 add subidentifier 537 under h3cevtModuleSwitchType by wangyahui
-- V4.26 2007-04-12 add subidentifier 538 to 542 under h3cevtModuleSwitchType by wangyahui
-- V4.27 2007-04-25 add subidentifier 706 under h3cevtModuleSwitchType by zhangzongyi
--                  add subidentifier 379 to 380 under h3cevtModuleSwitchType by zhaiyingying
--                  add subidentifier 246 to 250 under h3cevtModuleRouterType by liutinghai
--                  add subidentifier 42 under h3cevtPortRouterType by liutinghai
-- V4.28 2007-05-28 add subidentifier 707 under h3cevtModuleSwitchType by ligaoxu
--                  add subidentifier 381 to 392 under h3cevtModuleSwitchType by shuxiongtao
--                  modify name of subidentifier 371 and 374 under h3cevtModuleSwitchType by shuxiongtao
--                  add subidentifier 251 to 253 under h3cevtModuleRouterType by qikai
--                  add subidentifier 254 to 255 under h3cevtModuleRouterType by liutinghai
--                  add subidentifier 186 under h3cevtPortSwitchType by jinzhaoqiong
-- V4.29 2007-07-09 add subidentifier 543 to 551 under h3cevtModuleSwitchType by zhangjianfeng
--                  add subidentifier 552 to 554 under h3cevtModuleSwitchType by wangyahui
-- V4.30 2007-07-26 add subidentifier 400 under h3cevtModuleRouterType by xuejiayong
--                  add subidentifier 708 under h3cevtModuleSwitchType by xiuyihong
--                  add subidentifier 256 to 258 under h3cevtModuleRouterType by qikai
--                  add subidentifier 259 to 263 under h3cevtModuleRouterType by liutinghai
--                  add subidentifier 3 to 5 under h3cevtOther by gaolong
-- V4.31 2007-08-27 add subidentifier 187 to 188 under h3cevtPortSwitchType by ruanhan
--                  add subidentifier 802 to 804 under h3cevtModuleSwitchType by luoguixing
--                  add subidentifier 393 to 397 under h3cevtModuleSwitchType by shuxiongtao
-- V4.32 2007-09-25 add subidentifier 555 to 559 under h3cevtModuleSwitchType by wangyahui
--                  add subidentifier 805 under h3cevtModuleSwitchType by luoguixing
--                  add subidentifier 401 to 403 under h3cevtModuleRouterType by tanwen
--                  add subidentifier 43 under h3cevtPortRouterType by qikai
--                  add subidentifier 266 to 267 under h3cevtModuleRouterType by qikai
--                  add subidentifier 398 to 399 under h3cevtModuleSwitchType by hexuefei
-- V4.33 2007-10-22 add subidentifier 189 under h3cevtPortSwitchType by liaoxin
--                  add subidentifier 268 under h3cevtModuleRouterType by liutinghai
-- V4.34 2007-11-26 add subidentifier 269 to 273 under h3cevtModuleRouterType by liutinghai
--                  add subidentifier 274 to 276 under h3cevtModuleRouterType by qikai
--                  add subidentifier 404 to 406 under h3cevtModuleRouterType by chaiyaqin
--                  add subidentifier 400 to 407 under h3cevtModuleSwitchType by shuxiongtao
-- V4.35 2007-12-27 add subidentifier 277 to 278 under h3cevtModuleRouterType by liutinghai
--                  add subidentifier 560 to 568 under h3cevtModuleSwitchType by wangyahui
-- V4.36 2008-01-30 add subidentifier 408 under h3cevtModuleSwitchType by hexuefei
--                  add subidentifier 569 to 572 under h3cevtModuleSwitchType by wangyahui
--                  add subidentifier 279 to 280 under h3cevtModuleRouterType by qikai
--                  add subidentifier 190 under h3cevtPortSwitchType by liujingya
-- V4.37 2008-02-20 add subidentifier 720 to 724 under h3cevtModuleSwitchType by chaiyaqin
--                  add subidentifier 573 to 574 under h3cevtModuleSwitchType by zhangjianfeng
--                  modify name of subidentifier 546 and 550 under h3cevtModuleSwitchType by zhangjianfeng
--                  add subidentifier 575 to 576 under h3cevtModuleSwitchType by wangyahui
--                  add subidentifier 281 under h3cevtModuleRouterType by liutinghai
-- V4.38 2008-03-31 add subidentifier 806 to 808 under h3cevtModuleSwitchType by luoguixing
--                  add subidentifier 709 to 715 under h3cevtModuleSwitchType by wangcong
--                  add subidentifier 191 to 196 under h3cevtPortSwitchType by wangcong
--                  add subidentifier 44 under h3cevtPortRouterType by liutinghai
--                  add subidentifier 409 to 431 under h3cevtModuleSwitchType by zhaiyingying
--                  add subidentifier 432 under h3cevtModuleSwitchType by shuxiongtao
-- V4.39 2008-04-29 add subidentifier 577 to 589 under h3cevtModuleSwitchType by wangyahui
--                  add subidentifier 407 to 409 under h3cevtModuleRouterType by tanwen
-- V4.40 2008-05-31 add subidentifier 410 to 413 under h3cevtModuleRouterType by tanwen
--                  add subidentifier 282 to 284 under h3cevtModuleRouterType by qikai
--                  add subidentifier 285 to 286 under h3cevtModuleRouterType by liutinghai
-- V4.41 2008-07-28 add subidentifier 590 to 592 under h3cevtModuleSwitchType by wangyahui
--                  add subidentifier 287 to 289 under h3cevtModuleRouterType by qikai
--                  add subidentifier 290 to 291 under h3cevtModuleRouterType by liutinghai
--                  add subidentifier 45 to 46 under h3cevtPortRouterType by liutinghai
--                  add subidentifier 809 to 810 under h3cevtModuleSwitchType by luoguixing
-- V4.42 2008-08-26 modify name of 379 and 399 under h3cevtModuleSwitchType by wangwei
--                  modify description of 408 under h3cevtModuleSwitchType by wangwei
--                  modify name and description of 804 under h3cevtModuleSwitchType by wangwei
--                  add subidentifier 433 to 434 under h3cevtModuleSwitchType by wangwei
--                  add subidentifier 593 to 595 under h3cevtModuleSwitchType by wangyahui
--                  modify name and description of 256 and 288 under h3cevtPortRouterType by qikai
--                  add subidentifier 292 to 293 under h3cevtPortRouterType by qikai
-- V4.43 2008-10-13 add subidentifier 725 under h3cevtModuleSwitchType by ruanhan
--                  add subidentifier 197 under h3cevtPortSwitchType by ruanhan
--                  add subidentifier 811 under h3cevtModuleSwitchType by luoguixing
--                  add subidentifier 596 to 601 under h3cevtModuleSwitchType by wangyahui
-- V4.44 2008-11-04 add subidentifier 294 under h3cevtPortRouterType by qikai
--                  add subidentifier 414 under h3cevtModuleRouterType by tanwen
-- V4.45 2008-12-01 add subidentifier 602 to 619 under h3cevtModuleSwitchType by wangyahui
--                  add subidentifier 435 to 442 under h3cevtModuleSwitchType by zhaiyingying
--                  modify name of 546 under h3cevtModuleSwitchType by zhangjianfeng
--                  add subidentifier 295 under h3cevtPortRouterType by qikai
--                  add subidentifier 443 under h3cevtModuleSwitchType by shuxiongtao
-- V4.46 2008-12-25 add subidentifier 620 to 622 under h3cevtModuleSwitchType by wangyahui
--                  add subidentifier 716 to 718 under h3cevtModuleSwitchType by zhangshilin
--                  add subidentifier 444 to 445 under h3cevtModuleSwitchType by wangchang
-- V4.47 2009-03-02 add subidentifier 446 to 452 under h3cevtModuleSwitchType by wangchang
--                  add subidentifier 719 under h3cevtModuleSwitchType by zhangshilin
--                  add subidentifier 623 to 633 under h3cevtModuleSwitchType by wangyahui
-- V4.48 2009-03-31 add subidentifier 415 under h3cevtModuleRouterType by tanwen
--                  add subidentifier 296 under h3cevtPortRouterType by qikai
--                  add subidentifier 297 to 298 under h3cevtPortRouterType by qianjialin
--                  add subidentifier 453 to 464 under h3cevtModuleSwitchType by huyinxing
-- V4.49 2009-07-02 add subidentifier 299 to 302 under h3cevtModuleRouterType by qikai
--                  add subidentifier 303 under h3cevtModuleRouterType by chenfeihu
--                  add subidentifier 304 to 307 under h3cevtModuleRouterType by qianjialin
--                  add subidentifier 634 to 637 under h3cevtModuleSwitchType by wangyahui
--                  add subidentifier 604 to 606 under h3cevtModuleRouterType by chenjianhui
--                  add subidentifier 465 to 468 under h3cevtModuleSwitchType by zhaiyingying
--                  add subidentifier 469 to 472 under h3cevtModuleSwitchType by huyinxing
--                  add subidentifier 198 under h3cevtPortSwitchType by huyinxing
--                  add subidentifier 199 under h3cevtPortSwitchType by zhangjianfeng
-- V4.50 2009-08-28 add subidentifier 638 to 640 under h3cevtModuleSwitchType by wangyahui
--                  add subidentifier 308 to 310 under h3cevtModuleRouterType by qianjialin
-- V4.51 2009-11-09 add subidentifier 726 under h3cevtModuleSwitchType by ruanhan
--                  add subidentifier 641 under h3cevtModuleSwitchType by wangyahui
--                  add subidentifier 473 to 477 under h3cevtModuleSwitchType by yudongyang
--                  add subidentifier 478 to 485 under h3cevtModuleSwitchType by heweibin
-- V4.52 2009-12-31 add subidentifier 200 to 201 under h3cevtPortSwitchType by zhanghaiyang
--                  add subidentifier 642 to 651 under h3cevtModuleSwitchType by wangyahui
--                  add subidentifier 416 under h3cevtModuleRouterType by lixiaomin
--                  add subidentifier 486 under h3cevtModuleSwitchType by yudongyang
--                  add subidentifier 727 to 728 under h3cevtModuleSwitchType by xiaobing
--                  add subidentifier 652 to 659 under h3cevtModuleSwitchType by wangyahui
--                  add subidentifier 487 to 488 under h3cevtModuleSwitchType by huyinxing
--                  add subidentifier 660 to 662 under h3cevtModuleSwitchType by wangyahui
--                  add subidentifier 202 to 203 under h3cevtPortSwitchType by yangdonghong
-- V4.53 2010-03-03 add subidentifier 812 under h3cevtModuleSwitchType by mashuhang
--                  add subidentifier 489 to 497 under h3cevtModuleSwitchType by liubuxiang
--                  add subidentifier 498 to 499 under h3cevtModuleSwitchType by shikejun
--                  add subidentifier 900 under h3cevtModuleSwitchType by yangqiulin
--                  add subidentifier 901 to 902 under h3cevtModuleSwitchType by huyinxing
-- V4.54 2010-04-21 add subidentifier 903 to 904 under h3cevtModuleSwitchType by huyinxing
--                  add subidentifier 905 to 907 under h3cevtModuleSwitchType by shikejun
--                  add subidentifier 663 to 685 under h3cevtModuleSwitchType by wangyahui
--                  add subidentifier 813 under h3cevtModuleSwitchType by mashuhang
--                  add subidentifier 729 under h3cevtModuleSwitchType by zhangshilin
--                  add subidentifier 908 to 913 under h3cevtModuleSwitchType by yangbin
--                  add subidentifier 914 to 918 under h3cevtModuleSwitchType by huyinxing
--                  add subidentifier 5000 to 5011 under h3cevtModuleRouterType by qianjialin
--                  add subidentifier 919 to 927 under h3cevtModuleSwitchType by langgaoyi
-- V4.55 2011-01-31 add subidentifier 417 under h3cevtModuleRouterType by tanwen
--                  add subidentifier 311 to 314 under h3cevtModuleRouterType by qianjialin
--                  add subidentifier 686 to 691 under h3cevtModuleSwitchType by wangyahui
--                  add subidentifier 928 to 929 under h3cevtModuleSwitchType by langgaoyi
-- V4.56 2011-04-22 add subidentifier 930 under h3cevtModuleSwitchType by liuhui
--                  add subidentifier 814 to 815 under h3cevtModuleSwitchType by mashuhang
--                  add subidentifier 692 to 694 under h3cevtModuleSwitchType by wangyahui
--                  add subidentifier 204 under h3cevtPortSwitchType by yangliming
-- V4.57 2011-06-30 add subidentifier 695, 1201 to 1211 under h3cevtModuleSwitchType by wangyahui
--                  add subidentifier 205 to 207 under h3cevtPortSwitchType by gaoruichang
-- V4.58 2011-08-31 add subidentifier 696 to 697 under h3cevtModuleSwitchType by langgaoyi
--                  add subidentifier 208 under h3cevtPortSwitchType by wangshunli
--                  add subidentifier 931 to 933 under h3cevtModuleSwitchType by langgaoyi
--                  add subidentifier 934 under h3cevtModuleSwitchType by zhaohonghai
-- V4.59 2012-04-20 add subidentifier 935 to 938, 942 under h3cevtModuleSwitchType by wangjiangnan
--                  add subidentifier 1212 to 1218 under h3cevtModuleSwitchType by wangyahui
--                  add subidentifier 939 to 941 under h3cevtModuleSwitchType by herui
--                  modify name of 205 to 207 under h3cevtPortSwitchType by xvman
--                  add subidentifier 350 to 360 under h3cevtModuleRouterType by chenfeihu
--                  add subidentifier 943 to 945 under h3cevtModuleSwitchType by langgaoyi
--                  add subidentifier 209, 211 under h3cevtPortSwitchType by wangyahui
--                  add subidentifier 730 to 731 under h3cevtModuleSwitchType by panxiyuan
--                  add subidentifier 210 under h3cevtPortSwitchType by panxiyuan
--                  add subidentifier 315 to 349 under h3cevtModuleRouterType by qianjialin
--                  add subidentifier 946 to 948 under h3cevtModuleSwitchType by zhangheng
--                  add subidentifier 949 to 956 under h3cevtModuleSwitchType by zhengjiang
--                  add subidentifier 957 under h3cevtModuleSwitchType by zhaohonghai
--                  add subidentifier 361 to 372 under h3cevtModuleRouterType by qianjialin
--                  add subidentifier 212 under h3cevtPortSwitchType by wangyahui
--                  add subidentifier 732 under h3cevtModuleSwitchType by houchengshuai
--                  add subidentifier 1219 to 1230 under h3cevtModuleSwitchType by wangyahui
-- V4.60 2013-01-07 add subidentifier 733 under h3cevtModuleSwitchType by shixuemei
--                  add subidentifier 958 to 959 under hh3cevtModuleSwitchType by zhaohonghai
--                  add subidentifier 960 to 965, 996 under h3cevtModuleSwitchType by zhangheng
--                  add subidentifier 966 to 988 under h3cevtModuleSwitchType by yebiaoxiang
--                  add subidentifier 989 to 995 under h3cevtModuleSwitchType by zhaohonghai
--                  add subidentifier 1231 to 1255 under h3cevtModuleSwitchType by wangyahui
--                  add subidentifier 373 to 388 under h3cevtModuleRouterType by qianjialin
--                  add subidentifier 1400 to 1410 under h3cevtModuleSwitchType by qizhenglin
--                  add subidentifier 213 to 219 under h3cevtPortSwitchType by yebiaoxiang
--                  add subidentifier 47 under h3cevtPortRouterType by qianjialin
--                  add subidentifier 418 under h3cevtModuleRouterType by tanwen
--                  modify name of 673, 1214, 1215 under h3cevtModuleSwitchType by wangyahui
-- V4.61 2013-04-26 add subidentifier 1256 to 1269 under h3cevtModuleSwitchType by wangyahui
--                  add subidentifier 607 to 610 under h3cevtModuleRouterType by jiangwendong
--                  add subidentifier 220 to 222 under h3cevtPortSwitchType by jiangyongjiang
--                  add subidentifier 389 to 392 under h3cevtModuleRouterType by chenfeihu
--                  add subidentifier 393 to 398 under h3cevtModuleRouterType by qianjialin
--                  modify name of 975 to 982 under h3cevtModuleSwitchType by lihaijun
--                  add subidentifier 997 to 1015 under h3cevtModuleSwitchType by chenke
--                  add subidentifier 1016 to 1018 under h3cevtModuleSwitchType by jiangyongjiang
--                  add subidentifier 1270 to 1273 under h3cevtModuleSwitchType by sunzhenxing
--                  add subidentifier 1 to 8 under h3cevtModuleCommonCards by zhouxiaodong
-- V4.62 2013-10-10 add subidentifier 419 to 431 under h3cevtModuleRouterType by tanwen
--                  add subidentifier 611 under h3cevtModuleRouterType by jiangwendong
--                  add subidentifier 399, 800 to 804, 807 under h3cevtModuleRouterType by qianjialin
--                  add subidentifier 805 to 806 under h3cevtModuleRouterType by chenfeihu
--                  add subidentifier 1274 to 1279, 1293 to 1296 under h3cevtModuleSwitchType by lihaijun
--                  add subidentifier 1019 to 1024 under h3cevtModuleSwitchType by zhaohonghai
--                  add subidentifier 1280 to 1287, 1298 to 1306 under h3cevtModuleSwitchType by sunzhenxing
--                  add subidentifier 1025, 1028, 1029, 1050 under h3cevtModuleSwitchType by jiangyongjiang
--                  add subidentifier 1026 to 1027, 1030 to 1049 under h3cevtModuleSwitchType by chenke
--                  add subidentifier 816 under h3cevtModuleSwitchType by luoguixing
--                  add subidentifier 1288 to 1292, 1297 under h3cevtModuleSwitchType by wujili
--                  modify name of 1234 to 1236 under h3cevtModuleSwitchType by lihaijun
--                  add subidentifier 48 to 49 under h3cevtPortRouterType by jiangwendong
--                  add subidentifier 223 to 224 under h3cevtPortSwitchType by jiangyongjiang
-- V4.63 2014-01-26 add subidentifier 432 under h3cevtModuleRouterType by zhaowenbin
--                  add subidentifier 808 to 809, 814 under h3cevtModuleRouterType by qianjialin
--                  add subidentifier 810 to 813, 815 to 817 under h3cevtModuleRouterType by chenfeihu
--                  add subidentifier 734 to 739 under h3cevtModuleSwitchType by panxiyuan
--                  modify name of 1032 to 1041 under h3cevtModuleSwitchType by chenke
--                  add subidentifier 1051 to 1055 under h3cevtModuleSwitchType by zhaohonghai
--                  add subidentifier 1056 to 1058 under h3cevtModuleSwitchType by chenke
--                  add subidentifier 1307 to 1313 under h3cevtModuleSwitchType by wujili
--                  add subidentifier 1314 to 1316 under h3cevtModuleSwitchType by lihaijun
--                  add subidentifier 1317 to 1319 under h3cevtModuleSwitchType by sunzhenxing
--                  add subidentifier 1320 to 1326 under h3cevtModuleSwitchType by jiangyongjiang
-- V4.64 2014-04-25 add subidentifier 1059 to 1069 under h3cevtPortSwitchType by youhua
--                  add subidentifier 1070 to 1102 under h3cevtModuleSwitchType by chenke
--                  add subidentifier 1103 to 1107 under h3cevtModuleSwitchType by lihaijun
--                  add subidentifier 1108 under h3cevtModuleSwitchType by zhaohonghai
--                  add subidentifier 1327 to 1328 under h3cevtModuleSwitchType by sunzhenxing
--                  add subidentifier 1329 to 1331 under h3cevtModuleSwitchType by lihaijun
--                  add subidentifier 1332 to 1371 under h3cevtModuleSwitchType by jiangyongjiang
--                  add subidentifier 1372 to 1373 under h3cevtModuleSwitchType by sunzhenxing
--                  modify name of 733 under h3cevtModuleSwitchType by maoyun
--                  add subidentifier 740 to 743 h3cevtModuleSwitchType by tanxiaopeng
--                  add subidentifier 433 under h3cevtModuleRouterType by zhaowenbin
--                  add subidentifier 818 to 822, 824 to 825 under h3cevtModuleRouterType by chenfeihu
--                  add subidentifier 823 under h3cevtModuleRouterType by qianjialin
--                  add subidentifier 50 to 51 under h3cevtPortRouterType by chenfeihu
--                  add subidentifier 225 to 232 under h3cevtPortSwitchType by pantao
--                  modify name of 1400, remove 1401 to 1410 under h3cevtModuleSwitchType by qizhenglin
-- V4.65 2014-09-18 add subidentifier 434 under h3cevtModuleRouterType by zhaowenbin
--                  add subidentifier 612 to 615 under h3cevtModuleRouterType by jiangwendong
--                  add subidentifier 826 to 833, 840 under h3cevtModuleRouterType by qianjialin
--                  add subidentifier 834 to 839 under h3cevtModuleRouterType by chenfeihu
--                  add subidentifier 52 under h3cevtPortRouterType by jiangwendong
--                  add subidentifier 744 h3cevtModuleSwitchType by tanxiaopeng
--                  add subidentifier 1109 to 1117 under h3cevtModuleSwitchType by chenke
--                  add subidentifier 1118 to 1119, 1375 to 1376 under h3cevtModuleSwitchType by lihaijun
--                  add subidentifier 1374, 1382 to 1385 under h3cevtModuleSwitchType by jiangyongjiang
--                  add subidentifier 1377 to 1381, 1386 to 1389 under h3cevtModuleSwitchType by sunzhenxing
--                  modify description of 1010 under h3cevtModuleSwitchType by chenke
--                  modify name of 1320 to 1325, 1332 to 1371 under h3cevtModuleSwitchType by jiangyongjiang
--                  add subidentifier 8 to 35 under h3cevtPowerSupply, 3 to 23 under h3cevtFan by jiangyongjiang
-- V4.66 2015-04-18 add subidentifier 435 under h3cevtModuleRouterType by zhaowenbin
--                  add subidentifier 841 to 854 under h3cevtModuleRouterType by qianjialin
--                  add subidentifier 855 to 858 under h3cevtModuleRouterType by zhaohonghai
--                  add subidentifier 745 to 747 h3cevtModuleSwitchType by tanxiaopeng
--                  add subidentifier 748 h3cevtModuleSwitchType by wangshunli
--                  add subidentifier 1120 to 1125, 1127 to 1128, 1390 to 1397,
--                                    1647 to 1649, 1667 to 1673 under h3cevtModuleSwitchType by lihaijun
--                  add subidentifier 1126 under h3cevtModuleSwitchType by chenke
--                  add subidentifier 1129 to 1144 under h3cevtPortSwitchType by youhua
--                  add subidentifier 1398, 1399, 1600 to 1605, 1623 to 1646,
--                                    1650 to 1652, 1660 to 1666, 1674 to 1685
--                                    under h3cevtModuleSwitchType by jiangyongjiang
--                  add subidentifier 1606 to 1622 under h3cevtModuleSwitchType by sunzhenxing
--                  add subidentifier 1653 to 1659 under h3cevtModuleSwitchType by zhaiwanqing
--                  add subidentifier 233 to 237, 239 to 253 under h3cevtPortSwitchType by pantao
--                  add subidentifier 238 under h3cevtPortSwitchType by chenke
--                  modify name of 1315 and 1316 under h3cevtModuleSwitchType by lihaijun
-- V4.67 2016-04-02 add subidentifier 436 to 437, 448 to 449 under h3cevtModuleRouterType by zhaowenbin
--                  add subidentifier 438 to 439 and 616 to 618 under h3cevtModuleRouterType by sunqingyan
--                  add subidentifier 440 under h3cevtModuleRouterType by chengaishuang
--                  add subidentifier 441 to 446 under h3cevtModuleRouterType by yaoshuo
--                  add subidentifier 447 under h3cevtModuleRouterType by dongchanghai
--                  modify name of 856 to 858 under h3cevtModuleSwitchType by zhaohonghai
--                  add subidentifier 859 to 862 under h3cevtModuleRouterType by zhaohonghai
--                  add subidentifier 863 under h3cevtModuleRouterType by qianjialin
--                  add subidentifier 864 to 878 under h3cevtModuleRouterType by chenfeihu
--                  add subidentifier 879 to 884 under h3cevtModuleRouterType by fujuan
--                  add subidentifier 749 under h3cevtModuleSwitchType by wangshunli
--                  add subidentifier 750 under h3cevtModuleSwitchType by yangjianlin
--                  add subidentifier 751 to 752 h3cevtModuleSwitchType by mengfanhua
--                  add subidentifier 753 to 756 under h3cevtModuleSwitchType by songkeke
--                  add subidentifier 1145, 1149 under h3cevtPortSwitchType by youhua
--                  add subidentifier 1146 to 1148, 1150 to 1154 under h3cevtPortSwitchType by chenke
--                  add subidentifier 1686 to 1694, 1710 to 1722, 1742 to 1760, 1767 to 1784, 1789 to 1793
--                                    under h3cevtModuleSwitchType by jiangyongjiang
--                  add subidentifier 1695 to 1696 under h3cevtModuleSwitchType by zhaiwanqing
--                  add subidentifier 1697 to 1709, 1723 to 1741, 1761 to 1766, 1785 to 1788, 1794 to 1805
--                                    under h3cevtModuleSwitchType by lihaijun
--                  add subidentifier 53 to 54 under h3cevtPortRouterType by chenfeihu
--                  add subidentifier 55 under h3cevtPortRouterType by fujuan
--                  add subidentifier 56 under h3cevtPortRouterType by qianjialin
--                  modify name of 1128 under h3cevtModuleSwitchType by lihaijun
--                  modify description of 1673 under h3cevtModuleSwitchType by lihaijun
--                  add subidentifier 254 to 262, 264 to 265 under h3cevtPortSwitchType by guolei
--                  add subidentifier 263 under h3cevtPortSwitchType by zhanghuimin
-- V4.68 2018-04-13 add subidentifier 1806 to 1829 under h3cevtModuleSwitchType by jiangyongjiang
--                  add subidentifier 266 under h3cevtPortSwitchType by guolei
--                  add subidentifier 1830 to 1841 under h3cevtModuleSwitchType by lihaijun
--                  add subidentifier 757 to 758 under h3cevtModuleSwitchType by wangshunli
--                  add subidentifier 1842 under h3cevtModuleSwitchType by zhaoshihong
--                  add subidentifier 1843 to 1846 under h3cevtModuleSwitchType by jiangyongjiang
--                  add subidentifier 759 under h3cevtModuleSwitchType by mengfanhua
--                  add subidentifier 1847 under h3cevtModuleSwitchType by jiangyongjiang
--                  add subidentifier 619 to 620 under h3cevtModuleRouterType by songyanqing
--                  add subidentifier 1848 to 1849 under h3cevtModuleSwitchType by lihaijun
--                  add subidentifier 885 to 886 under h3cevtModuleRouterType by zhaohonghai
--                  add subidentifier 1850 to 1852 under h3cevtModuleSwitchType by jiangyongjiang
--                  add subidentifier 1853 to 1857 under h3cevtModuleSwitchType by lihaijun
--                  add subidentifier 1858 to 1862 under h3cevtModuleSwitchType by lihaijun
--                  add subidentifier 1863 to 1893 under h3cevtModuleSwitchType by jiangyongjiang
--                  add subidentifier 1155 to 1170 under h3cevtModuleSwitchType by chenke
--                  add subidentifier 1894 to 1895 under h3cevtModuleSwitchType by lihaijun
--                  add subidentifier 1896 under h3cevtModuleSwitchType by jiangyongjiang
--                  add subidentifier 267 under h3cevtPortSwitchType by guolei
--                  add subidentifier 887 to 889 under h3cevtModuleRouterType by mazheng
--                  add subidentifier 1171 to 1176 under h3cevtModuleSwitchType by chenke
--                  add subidentifier 1897 to 1904 under h3cevtModuleSwitchType by jiangyongjiang
--                  add subidentifier 1905 h3cevtModuleSwitchType by liuyanpeng
--                  add subidentifier 450 to 454 h3cevtModuleRouterType by dongchanghai
--                  add subidentifier 1906 to 1907 h3cevtModuleSwitchType by jiangyongjiang
--                  add subidentifier 1908 h3cevtModuleSwitchType by liuyanpeng
--                  add subidentifier 1177 to 1181 under h3cevtModuleSwitchType by chenke
--                  add subidentifier 760 to 762 h3cevtModuleSwitchType by mengfanhua
--                  add subidentifier 890 to 894 under h3cevtModuleRouterType by fujuan
--                  modify name of subidentifier 872 and 873 under h3cevtModuleRouterType by fujuan
--                  add subidentifier 1909 to 1910 under h3cevtModuleSwitchType by lihaijun
--                  add subidentifier 455 to 456 h3cevtModuleRouterType by yaoshuo
--                  add subidentifier 1911 to 1935 under h3cevtModuleSwitchType by jiangyongjiang
--                  add subidentifier 457 under h3cevtModuleRouterType by lizhifeng
--                  add subidentifier 895 to 899 under h3cevtModuleRouterType by zhaohonghai
--                  add subidentifier 1936 to 1938 under h3cevtModuleSwitchType by zhangkun
--                  add subidentifier 1939 to 1941 under h3cevtModuleSwitchType by jiangyongjiang
--                  add subidentifier 6 to 8 under h3cevtOther by chenke
--                  add subidentifier 458 to 462 under h3cevtModuleRouterType by wangchunlei
--                  add subidentifier 900 to 906 under h3cevtModuleRouterType by fujuan
--                  add subidentifier 1182 under h3cevtModuleSwitchType by youhua
--                  add subidentifier 1942 under h3cevtModuleSwitchType by lihaijun
--                  add subidentifier 1943 to 1953 under h3cevtModuleSwitchType by jiangyongjiang
--                  add subidentifier 463 to 468 under h3cevtModuleRouterType by dongchanghai
--                  add subidentifier 1183 to 1196 under h3cevtModuleSwitchType by chenke
--                  add subidentifier 907 to 921 under h3cevtModuleRouterType by zhongchao
--                  add subidentifier 763 to 764 under h3cevtModuleSwitchType by sunfang
--                  add subidentifier 1954 to 1957 under h3cevtModuleSwitchType by lihaijun
--                  add subidentifier 1958 to 1972 under h3cevtModuleSwitchType by jiangyongjiang
--                  add subidentifier 1973 to 1979 h3cevtModuleSwitchType by lihaijun
--                  add subidentifier 1980 to 1981 h3cevtModuleSwitchType by jiangyongjiang
--                  add subidentifier 274 to 279 under h3cevtModuleSwitchType by guolei
--                  add subidentifier 469 under h3cevtModuleRouterType by maxiaojie
--                  add subidentifier 470 to 473 under h3cevtModuleSwitchType by fuzhanfeng
--                  add subidentifier 765 under h3cevtModuleSwitchType by mengfanhua
--                  add subidentifier 1982 to 1985 h3cevtModuleSwitchType by  lihaijun
--                  add subidentifier 1986 to 2003 h3cevtModuleSwitchType by  jiangyongjiang
--                  add subidentifier 922 under h3cevtModuleRouterType by mazheng
--                  add subidentifier 58 under h3cevtPortRouterType by liuhua
--                  add subidentifier 474 to 477 under h3cevtModuleSwitchType by tanyan
--                  add subidentifier 2004 to 2005 h3cevtModuleSwitchType by  lihaijun
--                  add subidentifier 2006 to 2008 h3cevtModuleSwitchType by  jiangyongjiang
--                  add subidentifier 2009 to 2015 h3cevtModuleSwitchType by  lihaijun
--                  add subidentifier 1401 to 1424 under h3cevtModuleSwitchType by chenke
--                  add subidentifier 923 under h3cevtModuleRouterType by zhongchao
--                  add subidentifier 924 to 933 under h3cevtModuleRouterType by fujuan
--                  add subidentifier 766 to 768 under h3cevtModuleSwitchType by wangshunli
--                  add subidentifier 482 to 483 under h3cevtModuleSwitchType by cuipeilei
--                  add subidentifier 35 to 37 under h3cevtPowerSupply by wangchunlei
--                  add subidentifier 24 to 25 under  h3cevtFan by wangchunlei
--                  add subidentifier 484 to 489 under h3cevtModuleSwitchType by wangchunlei
--                  add subidentifier 938 under h3cevtModuleRouterType by fujuan
--                  add subidentifier 491 to 492 under h3cevtModuleSwitchType by fuzhanfeng
--                  add subidentifier 939 under h3cevtModuleRouterType by zhongchao
--                  add subidentifier 769 under h3cevtModuleSwitchType by yangjianlin
--                  add subidentifier 940 to 945 under h3cevtModuleRouterType by fujuan
--                  add subidentifier 946 to 953 under h3cevtModuleRouterType by zhaochao
--                  add subidentifier 493 under h3cevtModuleSwitchType by liyujun
--                  add subidentifier 2016 to 2017 h3cevtModuleSwitchType by  jiangyongjiang
--                  add subidentifier 769 to 770 under h3cevtModuleSwitchType by yangjianlin
--                  add subidentifier 494 to 497 under h3cevtModuleSwitchType by yangyuan
--                  add subidentifier 2018 to 2021 h3cevtModuleSwitchType by  lihaijun
--                  add subidentifier 280 under h3cevtPortSwitchType by yuanzhi
--                  add subidentifier 2022 to 2033 h3cevtModuleSwitchType by  jiangyongjiang
--                  add subidentifier 281 to 283 under h3cevtPortSw by wangshunli
--                  add subidentifier 954 to 958 under h3cevtModuleRouterType by fujuan
--                  add subidentifier 959 to 960 under h3cevtModuleRouterType by zhongchao
--                  add subidentifier 284 to 285 under h3cevtPortSwitchType by guolei
--                  add subidentifier 771 to 775 under h3cevtModuleSwitchType by wangshunli
--                  add subidentifier 961 to 962 under h3cevtModuleRouterType by fujuan
--                  add subidentifier 963 to 965 under h3cevtModuleRouterType by zhongchao
-- =================================================================
H3C-ENTITY-VENDORTYPE-OID-MIB DEFINITIONS ::= BEGIN

IMPORTS
    MODULE-IDENTITY
        FROM SNMPv2-SMI
    h3c
        FROM HUAWEI-3COM-OID-MIB;


h3cEntityVendorTypeOID MODULE-IDENTITY

        LAST-UPDATED "200903310000Z"
        ORGANIZATION
            "Hangzhou H3C Technologies Co., Ltd."
        CONTACT-INFO
            "Platform Team H3C Technologies Co., Ltd.
            Hai-Dian District Beijing P.R. China
            Zip:100085
            http://www.h3c.com"
        DESCRIPTION
            "The private MIB includes the definition of the object
            identifiers on products, which are used by the
            entPhysicalTable of the ENTITY-MIB to uniquely identify the
            type of each physical entry."
        ::= { h3c 3 }

h3cEntityVendortypeObjects   OBJECT IDENTIFIER ::= { h3cEntityVendorTypeOID 1 }

-- This MIB assigns OIDs for use as the values of entPhysicalVendorType.
-- The subtrees in which the OID values are assigned, are structured
-- into a hierarchy based on the values of RFC 2037's PhysicalClass
-- textual convention.  For reference, the definition of PhysicalClass
-- is as follows:
--
--      PhysicalClass ::= TEXTUAL-CONVENTION
--      STATUS          current
--      DESCRIPTION
--             "An enumerated value which provides an indication of the
--              general hardware type of a particular physical entity."
--      SYNTAX      INTEGER  {
--              other(1),
--              unknown(2),
--              chassis(3),
--              backplane(4),
--              container(5),    e.g. slot or daughter-card holder
--              powerSupply(6),
--              fan(7),
--              sensor(8),
--              module(9),       e.g. plug-in card or daughter-card
--              port(10),
--              stack(11)        e.g., stack of multiple chassis entities
--          }
--

h3cevtOther     OBJECT IDENTIFIER ::= { h3cEntityVendortypeObjects 1 }

-- May be defined detailed in future.

h3cevtOtherUnknownCard  OBJECT IDENTIFIER ::= { h3cevtOther 1 }
h3cevtCPU               OBJECT IDENTIFIER ::= { h3cevtOther 2 }
h3cevtDOM               OBJECT IDENTIFIER ::= { h3cevtOther 3 }  -- Disk on Module
h3cevtCFCard            OBJECT IDENTIFIER ::= { h3cevtOther 4 }  -- Compact Flash Card
h3cevtHardDisk          OBJECT IDENTIFIER ::= { h3cevtOther 5 }  -- Hard Disk
h3cevtSDCard            OBJECT IDENTIFIER ::= { h3cevtOther 6 }  -- Secure Digital Memory Card

-- h3cevtGeneralCPU is a general vendor type of CPU.  It is used only for
-- general purpose.  It is strongly recommended that this object should not
-- be used to present the specific CPU vendor type in most cases.  More
-- accurate and clear vendor types should be defined to present specific CPU.
h3cevtGeneralCPU        OBJECT IDENTIFIER ::= { h3cevtCPU 1 }


h3cevtUnknown   OBJECT IDENTIFIER ::= { h3cEntityVendortypeObjects 2 }

h3cevtChassis   OBJECT IDENTIFIER ::= { h3cEntityVendortypeObjects 3 }

-- chassis OID assignments
-- May be substituted by sysObjectID.  So none is assigned at present.

--
-- backplane
--   The enumeration 'backplane' is applicable if the physical
--   entity class is some sort of device for aggregating and
--   forwarding networking traffic, such as a shared backplane in
--   a modular ethernet switch.  Note that an agent may model a
--   backplane as a single physical entity, which is actually
--   implemented as multiple discrete physical components (within
--   a chassis or stack).
--

h3cevtBackplane     OBJECT IDENTIFIER ::= { h3cEntityVendortypeObjects 4 }

--
-- h3cevtContainer section:
--
h3cevtContainer     OBJECT IDENTIFIER ::= { h3cEntityVendortypeObjects 5 }

--
-- h3cevtPowerSupply section:
--
h3cevtPowerSupply   OBJECT IDENTIFIER ::= { h3cEntityVendortypeObjects 6 }
h3cevtPowerSupplyAC            OBJECT IDENTIFIER ::= { h3cevtPowerSupply 2 }
h3cevtPowerSupplyDC            OBJECT IDENTIFIER ::= { h3cevtPowerSupply 3 }
h3cevtPowerSupplySTD130W       OBJECT IDENTIFIER ::= { h3cevtPowerSupply 4 }     -- Standard 130W PSU
h3cevtPowerSupplySTD180W       OBJECT IDENTIFIER ::= { h3cevtPowerSupply 5 }     -- Standard 180W PSU
h3cevtPowerSupplyPOE24Port     OBJECT IDENTIFIER ::= { h3cevtPowerSupply 6 }     -- 24 Port POE PSU 480W
h3cevtPowerSupplyPOE48Port     OBJECT IDENTIFIER ::= { h3cevtPowerSupply 7 }     -- 48 Port POE PSU 480W
h3cevtPowerSupplyLSUM1AC2500   OBJECT IDENTIFIER ::= { h3cevtPowerSupply 8 }
h3cevtPowerSupplyLSUM2AC2500   OBJECT IDENTIFIER ::= { h3cevtPowerSupply 9 }
h3cevtPowerSupplyLSUM1DC2400   OBJECT IDENTIFIER ::= { h3cevtPowerSupply 10 }
h3cevtPowerSupplyLSUM1AC1200   OBJECT IDENTIFIER ::= { h3cevtPowerSupply 11 }
h3cevtPowerSupplyLSQM1DC2400   OBJECT IDENTIFIER ::= { h3cevtPowerSupply 12 }
h3cevtPowerSupplyLSUM5AC2500   OBJECT IDENTIFIER ::= { h3cevtPowerSupply 13 }
h3cevtPowerSupplyLSUM5DC2400   OBJECT IDENTIFIER ::= { h3cevtPowerSupply 14 }
h3cevtPowerSupplyLSUM6DC2400   OBJECT IDENTIFIER ::= { h3cevtPowerSupply 15 }
h3cevtPowerSupplyLSUM6AC2500   OBJECT IDENTIFIER ::= { h3cevtPowerSupply 16 }
h3cevtPowerSupplyLSQM1AC1400   OBJECT IDENTIFIER ::= { h3cevtPowerSupply 17 }
h3cevtPowerSupplyLSQM1DC1400   OBJECT IDENTIFIER ::= { h3cevtPowerSupply 18 }
h3cevtPowerSupplyLSQM1AC2800   OBJECT IDENTIFIER ::= { h3cevtPowerSupply 19 }
h3cevtPowerSupplyLSQM2AC1400   OBJECT IDENTIFIER ::= { h3cevtPowerSupply 20 }
h3cevtPowerSupplyLSQM1AC6000   OBJECT IDENTIFIER ::= { h3cevtPowerSupply 21 }
h3cevtPowerSupplyLSQM2AC6000   OBJECT IDENTIFIER ::= { h3cevtPowerSupply 22 }
h3cevtPowerSupplyLSQM1AC300    OBJECT IDENTIFIER ::= { h3cevtPowerSupply 23 }
h3cevtPowerSupplyLSQM1AC650    OBJECT IDENTIFIER ::= { h3cevtPowerSupply 24 }
h3cevtPowerSupplyLSQM1DC650    OBJECT IDENTIFIER ::= { h3cevtPowerSupply 25 }
h3cevtPowerSupplyLSQM1PWRSPA   OBJECT IDENTIFIER ::= { h3cevtPowerSupply 26 }
h3cevtPowerSupplyLSWM1RPS800   OBJECT IDENTIFIER ::= { h3cevtPowerSupply 27 }
h3cevtPowerSupplyLSQM7AC1400   OBJECT IDENTIFIER ::= { h3cevtPowerSupply 28 }
h3cevtPowerSupplyLSQM7DC1400   OBJECT IDENTIFIER ::= { h3cevtPowerSupply 29 }
h3cevtPowerSupplyLSQM7AC2800   OBJECT IDENTIFIER ::= { h3cevtPowerSupply 30 }
h3cevtPowerSupplyLSQM7AC6000   OBJECT IDENTIFIER ::= { h3cevtPowerSupply 31 }
h3cevtPowerSupplyLSQM7AC300    OBJECT IDENTIFIER ::= { h3cevtPowerSupply 32 }
h3cevtPowerSupplyLSQM7AC650    OBJECT IDENTIFIER ::= { h3cevtPowerSupply 33 }
h3cevtPowerSupplyLSQM7DC650    OBJECT IDENTIFIER ::= { h3cevtPowerSupply 34 }
h3cevtPowerSupplyLSWM2RPS800   OBJECT IDENTIFIER ::= { h3cevtPowerSupply 35 }
h3cevtPowerSupplySecPathAC     OBJECT IDENTIFIER ::= { h3cevtPowerSupply 36 }    -- F5000-NSUM1AC650-650W
h3cevtPowerSupplySecPathDC     OBJECT IDENTIFIER ::= { h3cevtPowerSupply 37}     -- F5000-NSUM1DC650-650W
--
-- h3cevtFan section:
--
h3cevtFan       OBJECT IDENTIFIER ::= { h3cEntityVendortypeObjects 7 }
h3cevtHotSwapFan       OBJECT IDENTIFIER ::=  { h3cevtFan 1 }
h3cevtNonHotSwapFan    OBJECT IDENTIFIER ::=  { h3cevtFan 2 }
h3cevtFanLSUM110504    OBJECT IDENTIFIER ::=  { h3cevtFan 3 }
h3cevtFanLSUM110508    OBJECT IDENTIFIER ::=  { h3cevtFan 4 }
h3cevtFanLSUM110508V   OBJECT IDENTIFIER ::=  { h3cevtFan 5 }
h3cevtFanLSUM110512    OBJECT IDENTIFIER ::=  { h3cevtFan 6 }
h3cevtFanLSUM210512    OBJECT IDENTIFIER ::=  { h3cevtFan 7 }
h3cevtFanLSUM510504    OBJECT IDENTIFIER ::=  { h3cevtFan 8 }
h3cevtFanLSUM510508    OBJECT IDENTIFIER ::=  { h3cevtFan 9 }
h3cevtFanLSUM510508V   OBJECT IDENTIFIER ::=  { h3cevtFan 10 }
h3cevtFanLSUM510512U   OBJECT IDENTIFIER ::=  { h3cevtFan 11 }
h3cevtFanLSUM510512D   OBJECT IDENTIFIER ::=  { h3cevtFan 12 }
h3cevtFanLSUM511908V   OBJECT IDENTIFIER ::=  { h3cevtFan 13 }
h3cevtFanLSQM17502E    OBJECT IDENTIFIER ::=  { h3cevtFan 14 }
h3cevtFanLSQM17503E    OBJECT IDENTIFIER ::=  { h3cevtFan 15 }
h3cevtFanLSQM17503ES   OBJECT IDENTIFIER ::=  { h3cevtFan 16 }
h3cevtFanLSQM17506E    OBJECT IDENTIFIER ::=  { h3cevtFan 17 }
h3cevtFanLSQM17506EV   OBJECT IDENTIFIER ::=  { h3cevtFan 18 }
h3cevtFanLSQM17510E    OBJECT IDENTIFIER ::=  { h3cevtFan 19 }
h3cevtFanLSQM57503     OBJECT IDENTIFIER ::=  { h3cevtFan 20 }
h3cevtFanLSQM57502     OBJECT IDENTIFIER ::=  { h3cevtFan 21 }
h3cevtFanLSQM57506     OBJECT IDENTIFIER ::=  { h3cevtFan 22 }
h3cevtFanLSQM57510     OBJECT IDENTIFIER ::=  { h3cevtFan 23 }
h3cevtHotSwapFan-NSUM1BFANSC         OBJECT IDENTIFIER ::=  { h3cevtFan 24 }   -- F5000-NSUM1BFANSC
h3cevtHotSwapFan-NSUM1BFANSCB        OBJECT IDENTIFIER ::=  { h3cevtFan 25 }   -- F5000-NSUM1BFANSCB
--
-- h3cevtSensor section:
--
h3cevtSensor        OBJECT IDENTIFIER ::= { h3cEntityVendortypeObjects 8 }
h3cevtSensorTemperature     OBJECT IDENTIFIER ::= { h3cevtSensor 1 }
h3cevtSensorVoltage         OBJECT IDENTIFIER ::= { h3cevtSensor 2 }
h3cevtSensorFanSpeed        OBJECT IDENTIFIER ::= { h3cevtSensor 3 }


--
-- h3cevtModule section:
--
h3cevtModule        OBJECT IDENTIFIER ::= { h3cEntityVendortypeObjects 9 }

-- h3cevtModule is subdivided into sections like Router and Switch. These represent
-- cards used only on the router and switch.
-- h3cevtModuleCommonCards contains cards that can be used interchangeably
-- across more than one platform


-- Acronyms used in the h3cevtModule section:
--

h3cevtModuleUnknownCard     OBJECT IDENTIFIER ::= { h3cevtModule 1 }

-- h3cevtModuleCommonCards - cards and subcards common to more
-- than one platform
h3cevtModuleCommonCards     OBJECT IDENTIFIER ::= { h3cevtModule 2 }

h3cevtModuleBoxCEN                         OBJECT IDENTIFIER ::= { h3cevtModuleCommonCards 1 }
h3cevtModuleBoxIRF48GE                     OBJECT IDENTIFIER ::= { h3cevtModuleCommonCards 2 }
h3cevtModuleBoxIRF24GE24TGE                OBJECT IDENTIFIER ::= { h3cevtModuleCommonCards 3 }
h3cevtModuleChassisMpu                     OBJECT IDENTIFIER ::= { h3cevtModuleCommonCards 4 }
h3cevtModuleLPU48GE                        OBJECT IDENTIFIER ::= { h3cevtModuleCommonCards 5 }
h3cevtModuleLPU4GE4Serial                  OBJECT IDENTIFIER ::= { h3cevtModuleCommonCards 6 }
h3cevtModuleLPU4GE4Pos                     OBJECT IDENTIFIER ::= { h3cevtModuleCommonCards 7 }
h3cevtModuleLPU4GE4E1                      OBJECT IDENTIFIER ::= { h3cevtModuleCommonCards 8 }


-- h3cevtModuleRouterType cards are slot-cards specific to the Router.
h3cevtModuleRouterType      OBJECT IDENTIFIER ::= { h3cevtModule 3 }

--h3cevtModuleRt-Unavailable               OBJECT IDENTIFIER ::= { h3cevtModuleRouterType 1 }
h3cevtModuleRt-As                          OBJECT IDENTIFIER ::= { h3cevtModuleRouterType 2 }
h3cevtModuleRt-Sa                          OBJECT IDENTIFIER ::= { h3cevtModuleRouterType 3 }
h3cevtModuleRt-Bi                          OBJECT IDENTIFIER ::= { h3cevtModuleRouterType 4 }
h3cevtModuleRt-E12                         OBJECT IDENTIFIER ::= { h3cevtModuleRouterType 5 }
h3cevtModuleRt-E14                         OBJECT IDENTIFIER ::= { h3cevtModuleRouterType 6 }
h3cevtModuleRt-Fe1                         OBJECT IDENTIFIER ::= { h3cevtModuleRouterType 7 }
h3cevtModuleRt-E1                          OBJECT IDENTIFIER ::= { h3cevtModuleRouterType 8 }
h3cevtModuleRt-Fe2                         OBJECT IDENTIFIER ::= { h3cevtModuleRouterType 9 }
h3cevtModuleRt-Vi2                         OBJECT IDENTIFIER ::= { h3cevtModuleRouterType 11 }
h3cevtModuleRt-Vi4                         OBJECT IDENTIFIER ::= { h3cevtModuleRouterType 12 }
h3cevtModuleRt-Vi30                        OBJECT IDENTIFIER ::= { h3cevtModuleRouterType 13 }
h3cevtModuleRt-S1b                         OBJECT IDENTIFIER ::= { h3cevtModuleRouterType 14 }
h3cevtModuleRt-Sa2                         OBJECT IDENTIFIER ::= { h3cevtModuleRouterType 15 }
h3cevtModuleRt-As16                        OBJECT IDENTIFIER ::= { h3cevtModuleRouterType 16 }
h3cevtModuleRt-New8as                      OBJECT IDENTIFIER ::= { h3cevtModuleRouterType 17 }
h3cevtModuleRt-Sa1                         OBJECT IDENTIFIER ::= { h3cevtModuleRouterType 18 }
h3cevtModuleRt-Fxs2                        OBJECT IDENTIFIER ::= { h3cevtModuleRouterType 19 }
h3cevtModuleRt-Fxo2                        OBJECT IDENTIFIER ::= { h3cevtModuleRouterType 20 }
h3cevtModuleRt-Em2                         OBJECT IDENTIFIER ::= { h3cevtModuleRouterType 21 }
h3cevtModuleRt-Fxs4                        OBJECT IDENTIFIER ::= { h3cevtModuleRouterType 22 }
h3cevtModuleRt-Fxo4                        OBJECT IDENTIFIER ::= { h3cevtModuleRouterType 23 }
h3cevtModuleRt-Em4                         OBJECT IDENTIFIER ::= { h3cevtModuleRouterType 24 }
h3cevtModuleRt-Sab                         OBJECT IDENTIFIER ::= { h3cevtModuleRouterType 25 }
h3cevtModuleRt-E1vi                        OBJECT IDENTIFIER ::= { h3cevtModuleRouterType 26 }
h3cevtModuleRt-Am12                        OBJECT IDENTIFIER ::= { h3cevtModuleRouterType 27 }
h3cevtModuleRt-Am6                         OBJECT IDENTIFIER ::= { h3cevtModuleRouterType 28 }
h3cevtModuleRt-Ndec                        OBJECT IDENTIFIER ::= { h3cevtModuleRouterType 29 }
h3cevtModuleRt-Newsa2                      OBJECT IDENTIFIER ::= { h3cevtModuleRouterType 30 }
h3cevtModuleRt-Aux                         OBJECT IDENTIFIER ::= { h3cevtModuleRouterType 31 }
h3cevtModuleRt-Console                     OBJECT IDENTIFIER ::= { h3cevtModuleRouterType 32 }
h3cevtModuleRt-Sic-wan                     OBJECT IDENTIFIER ::= { h3cevtModuleRouterType 33 }
h3cevtModuleRt-Sic-1fe                     OBJECT IDENTIFIER ::= { h3cevtModuleRouterType 34 }
h3cevtModuleRt-Sic-1sa                     OBJECT IDENTIFIER ::= { h3cevtModuleRouterType 35 }
h3cevtModuleRt-Sic-3as                     OBJECT IDENTIFIER ::= { h3cevtModuleRouterType 36 }
h3cevtModuleRt-Sic-1e1                     OBJECT IDENTIFIER ::= { h3cevtModuleRouterType 37 }
h3cevtModuleRt-Sic-1t1                     OBJECT IDENTIFIER ::= { h3cevtModuleRouterType 38 }
h3cevtModuleRt-Sic-1bu                     OBJECT IDENTIFIER ::= { h3cevtModuleRouterType 39 }
h3cevtModuleRt-Sic-2bu                     OBJECT IDENTIFIER ::= { h3cevtModuleRouterType 40 }
h3cevtModuleRt-Sic-1bs                     OBJECT IDENTIFIER ::= { h3cevtModuleRouterType 41 }
h3cevtModuleRt-Sic-2bs                     OBJECT IDENTIFIER ::= { h3cevtModuleRouterType 42 }
h3cevtModuleRt-Sic-1am                     OBJECT IDENTIFIER ::= { h3cevtModuleRouterType 43 }
h3cevtModuleRt-Sic-2am                     OBJECT IDENTIFIER ::= { h3cevtModuleRouterType 44 }
h3cevtModuleRt-Sic-1em                     OBJECT IDENTIFIER ::= { h3cevtModuleRouterType 45 }
h3cevtModuleRt-Sic-2em                     OBJECT IDENTIFIER ::= { h3cevtModuleRouterType 46 }
h3cevtModuleRt-Sic-1fxs                    OBJECT IDENTIFIER ::= { h3cevtModuleRouterType 47 }
h3cevtModuleRt-Sic-2fxs                    OBJECT IDENTIFIER ::= { h3cevtModuleRouterType 48 }
h3cevtModuleRt-Sic-1fxo                    OBJECT IDENTIFIER ::= { h3cevtModuleRouterType 49 }
h3cevtModuleRt-Sic-2fxo                    OBJECT IDENTIFIER ::= { h3cevtModuleRouterType 50 }
h3cevtModuleRt-Fcm6                        OBJECT IDENTIFIER ::= { h3cevtModuleRouterType 51 }
h3cevtModuleRt-Sa8                         OBJECT IDENTIFIER ::= { h3cevtModuleRouterType 52 }
h3cevtModuleRt-T11                         OBJECT IDENTIFIER ::= { h3cevtModuleRouterType 53 }
h3cevtModuleRt-T12                         OBJECT IDENTIFIER ::= { h3cevtModuleRouterType 54 }
h3cevtModuleRt-T14                         OBJECT IDENTIFIER ::= { h3cevtModuleRouterType 55 }
h3cevtModuleRt-T1vi                        OBJECT IDENTIFIER ::= { h3cevtModuleRouterType 56 }
h3cevtModuleRt-Fcm4                        OBJECT IDENTIFIER ::= { h3cevtModuleRouterType 57 }
h3cevtModuleRt-Fcm2                        OBJECT IDENTIFIER ::= { h3cevtModuleRouterType 58 }
h3cevtModuleRt-Rtb21ce3                    OBJECT IDENTIFIER ::= { h3cevtModuleRouterType 59 }
h3cevtModuleRt-Ame6                        OBJECT IDENTIFIER ::= { h3cevtModuleRouterType 60 }
h3cevtModuleRt-Ame12                       OBJECT IDENTIFIER ::= { h3cevtModuleRouterType 61 }
h3cevtModuleRt-E11-f                       OBJECT IDENTIFIER ::= { h3cevtModuleRouterType 65 }
h3cevtModuleRt-E12-f                       OBJECT IDENTIFIER ::= { h3cevtModuleRouterType 66 }
h3cevtModuleRt-E14-f                       OBJECT IDENTIFIER ::= { h3cevtModuleRouterType 67 }
h3cevtModuleRt-T11-f                       OBJECT IDENTIFIER ::= { h3cevtModuleRouterType 68 }
h3cevtModuleRt-T12-f                       OBJECT IDENTIFIER ::= { h3cevtModuleRouterType 69 }
h3cevtModuleRt-T14-f                       OBJECT IDENTIFIER ::= { h3cevtModuleRouterType 70 }
h3cevtModuleRt-E11-f-17                    OBJECT IDENTIFIER ::= { h3cevtModuleRouterType 71 }
h3cevtModuleRt-T11-f-17                    OBJECT IDENTIFIER ::= { h3cevtModuleRouterType 72 }
h3cevtModuleRt-Rtb21ct3                    OBJECT IDENTIFIER ::= { h3cevtModuleRouterType 73 }
h3cevtModuleRt-Atmadsl1                    OBJECT IDENTIFIER ::= { h3cevtModuleRouterType 74 }
h3cevtModuleRt-Atmadsl2                    OBJECT IDENTIFIER ::= { h3cevtModuleRouterType 75 }
h3cevtModuleRt-Atm155m                     OBJECT IDENTIFIER ::= { h3cevtModuleRouterType 76 }
h3cevtModuleRt-Ase8                        OBJECT IDENTIFIER ::= { h3cevtModuleRouterType 77 }
h3cevtModuleRt-Ase16                       OBJECT IDENTIFIER ::= { h3cevtModuleRouterType 78 }
h3cevtModuleRt-Sae4                        OBJECT IDENTIFIER ::= { h3cevtModuleRouterType 79 }
h3cevtModuleRt-Sae2                        OBJECT IDENTIFIER ::= { h3cevtModuleRouterType 80 }
h3cevtModuleRt-Atmshdsl1                   OBJECT IDENTIFIER ::= { h3cevtModuleRouterType 90 }
h3cevtModuleRt-Atmshdsl2                   OBJECT IDENTIFIER ::= { h3cevtModuleRouterType 91 }
h3cevtModuleRt-Atmshdsl4                   OBJECT IDENTIFIER ::= { h3cevtModuleRouterType 92 }
h3cevtModuleRt-Atm25m                      OBJECT IDENTIFIER ::= { h3cevtModuleRouterType 93 }
h3cevtModuleRt-Atme3                       OBJECT IDENTIFIER ::= { h3cevtModuleRouterType 94 }
h3cevtModuleRt-Atmt3                       OBJECT IDENTIFIER ::= { h3cevtModuleRouterType 95 }
h3cevtModuleRt-Xdsl-fec                    OBJECT IDENTIFIER ::= { h3cevtModuleRouterType 96 }
h3cevtModuleRt-Xdsl-adsl                   OBJECT IDENTIFIER ::= { h3cevtModuleRouterType 97 }
h3cevtModuleRt-Xdsl-gshdsl                 OBJECT IDENTIFIER ::= { h3cevtModuleRouterType 98 }
h3cevtModuleRt-Xdsl-bri                    OBJECT IDENTIFIER ::= { h3cevtModuleRouterType 99 }
h3cevtModuleRt-Xdsl-scc                    OBJECT IDENTIFIER ::= { h3cevtModuleRouterType 100 }
h3cevtModuleRt-Ge1                         OBJECT IDENTIFIER ::= { h3cevtModuleRouterType 101 }
h3cevtModuleRt-Pos155m                     OBJECT IDENTIFIER ::= { h3cevtModuleRouterType 102 }
h3cevtModuleRt-Cpos                        OBJECT IDENTIFIER ::= { h3cevtModuleRouterType 103 }
h3cevtModuleRt-Fe1op                       OBJECT IDENTIFIER ::= { h3cevtModuleRouterType 104 }
h3cevtModuleRt-Sae8                        OBJECT IDENTIFIER ::= { h3cevtModuleRouterType 105 }
h3cevtModuleRt-Atm155m-mm                  OBJECT IDENTIFIER ::= { h3cevtModuleRouterType 106 }
h3cevtModuleRt-Atm155m-sm                  OBJECT IDENTIFIER ::= { h3cevtModuleRouterType 107 }
h3cevtModuleRt-Atm155m-sml                 OBJECT IDENTIFIER ::= { h3cevtModuleRouterType 108 }
h3cevtModuleRt-Fe1op-sfx                   OBJECT IDENTIFIER ::= { h3cevtModuleRouterType 109 }
h3cevtModuleRt-Fe1op-mfx                   OBJECT IDENTIFIER ::= { h3cevtModuleRouterType 110 }
h3cevtModuleRt-Cpos-t1                     OBJECT IDENTIFIER ::= { h3cevtModuleRouterType 111 }
h3cevtModuleRt-Ge1op                       OBJECT IDENTIFIER ::= { h3cevtModuleRouterType 112 }
h3cevtModuleRt-Ge2op                       OBJECT IDENTIFIER ::= { h3cevtModuleRouterType 113 }
h3cevtModuleRt-Ge2                         OBJECT IDENTIFIER ::= { h3cevtModuleRouterType 114 }
h3cevtModuleRt-Fix-1wan                    OBJECT IDENTIFIER ::= { h3cevtModuleRouterType 115 }
h3cevtModuleRt-Fix-1sae                    OBJECT IDENTIFIER ::= { h3cevtModuleRouterType 116 }
h3cevtModuleRt-Cavium                      OBJECT IDENTIFIER ::= { h3cevtModuleRouterType 117 }
h3cevtModuleRt-Sic1Eth                     OBJECT IDENTIFIER ::= { h3cevtModuleRouterType 118 }
h3cevtModuleRt-atm1ADSLI                   OBJECT IDENTIFIER ::= { h3cevtModuleRouterType 119 }
h3cevtModuleRt-atm2ADSLI                   OBJECT IDENTIFIER ::= { h3cevtModuleRouterType 120 }
h3cevtModuleRt-fix-e11                     OBJECT IDENTIFIER ::= { h3cevtModuleRouterType 121 }
h3cevtModuleRt-fix-t11                     OBJECT IDENTIFIER ::= { h3cevtModuleRouterType 122 }
h3cevtModuleRt-e18-75                      OBJECT IDENTIFIER ::= { h3cevtModuleRouterType 123 }
h3cevtModuleRt-e18-120                     OBJECT IDENTIFIER ::= { h3cevtModuleRouterType 124 }
h3cevtModuleRt-t18                         OBJECT IDENTIFIER ::= { h3cevtModuleRouterType 125 }
h3cevtModuleRt-sic-1vifxs                  OBJECT IDENTIFIER ::= { h3cevtModuleRouterType 126 }
h3cevtModuleRt-sic-1vifxo                  OBJECT IDENTIFIER ::= { h3cevtModuleRouterType 127 }
h3cevtModuleRt-sic-2vifxs                  OBJECT IDENTIFIER ::= { h3cevtModuleRouterType 128 }
h3cevtModuleRt-sic-2vifxo                  OBJECT IDENTIFIER ::= { h3cevtModuleRouterType 129 }
h3cevtModuleRt-xdsl-fec-new                OBJECT IDENTIFIER ::= { h3cevtModuleRouterType 130 }
h3cevtModuleRt-xdsl-sa                     OBJECT IDENTIFIER ::= { h3cevtModuleRouterType 131 }
h3cevtModuleRt-bs4                         OBJECT IDENTIFIER ::= { h3cevtModuleRouterType 132 }
h3cevtModuleRt-ima-8e175                   OBJECT IDENTIFIER ::= { h3cevtModuleRouterType 133 }
h3cevtModuleRt-ima-8e1120                  OBJECT IDENTIFIER ::= { h3cevtModuleRouterType 134 }
h3cevtModuleRt-ima-4e175                   OBJECT IDENTIFIER ::= { h3cevtModuleRouterType 135 }
h3cevtModuleRt-ima-4e1120                  OBJECT IDENTIFIER ::= { h3cevtModuleRouterType 136 }
h3cevtModuleRt-ima-8t1                     OBJECT IDENTIFIER ::= { h3cevtModuleRouterType 137 }
h3cevtModuleRt-ima-4t1                     OBJECT IDENTIFIER ::= { h3cevtModuleRouterType 138 }
h3cevtModuleRt-sic-1t1f                    OBJECT IDENTIFIER ::= { h3cevtModuleRouterType 139 }
h3cevtModuleRT-SIC-1E1F                    OBJECT IDENTIFIER ::= { h3cevtModuleRouterType 140 }
h3cevtModuleRt-VG-16fxs                    OBJECT IDENTIFIER ::= { h3cevtModuleRouterType 141 }
h3cevtModuleRt-VG-32fxs                    OBJECT IDENTIFIER ::= { h3cevtModuleRouterType 142 }
h3cevtModuleRt-VG-8fxo                     OBJECT IDENTIFIER ::= { h3cevtModuleRouterType 143 }
h3cevtModuleRt-VG-2fe                      OBJECT IDENTIFIER ::= { h3cevtModuleRouterType 144 }
h3cevtModuleRt-sib                         OBJECT IDENTIFIER ::= { h3cevtModuleRouterType 145 } -- SIB card
h3cevtModuleRt-cie32                       OBJECT IDENTIFIER ::= { h3cevtModuleRouterType 146 } -- 32M SSRAM CIE card
h3cevtModuleRt-cie64                       OBJECT IDENTIFIER ::= { h3cevtModuleRouterType 147 } -- 64M SSRAM CIE card
h3cevtModuleRt-cie96                       OBJECT IDENTIFIER ::= { h3cevtModuleRouterType 148 } -- 96M SSRAM CIE card
h3cevtModuleRt-Fe4                         OBJECT IDENTIFIER ::= { h3cevtModuleRouterType 149 } -- 4FE card
h3cevtModuleRt-fxs4fxo1                    OBJECT IDENTIFIER ::= { h3cevtModuleRouterType 150 } -- 4 Port Foreign Exchange Station and 1 Port Foreign Exchange Office Interface
h3cevtModuleRt-atm1shdsl4wire              OBJECT IDENTIFIER ::= { h3cevtModuleRouterType 151 } -- G.SHDSL 4 wire MIM card, 1 port
h3cevtModuleRt-atmIma4shdsl                OBJECT IDENTIFIER ::= { h3cevtModuleRouterType 152 } -- G.SHDSL 8 wire MIM card, 4 ports
h3cevtModuleRt-ls4                         OBJECT IDENTIFIER ::= { h3cevtModuleRouterType 153 } -- 4 Ports Layer 2 Lanswitch Module
h3cevtModuleRt-ls8                         OBJECT IDENTIFIER ::= { h3cevtModuleRouterType 154 } -- 8 Ports Layer 2 Lanswitch Module
h3cevtModuleRt-ls16                        OBJECT IDENTIFIER ::= { h3cevtModuleRouterType 155 } -- 16 Ports Layer 2 Lanswitch Module
h3cevtModuleRt-sic-adls2plus-isdn          OBJECT IDENTIFIER ::= { h3cevtModuleRouterType 156 } -- ADLS2Plus SIC card, ISDN port
h3cevtModuleRt-sic-adls2plus-pots          OBJECT IDENTIFIER ::= { h3cevtModuleRouterType 157 } -- ADLS2Plus SIC card, POTS port
h3cevtModuleRt-ft3                         OBJECT IDENTIFIER ::= { h3cevtModuleRouterType 158 } -- 1 Port Fractional T3 module
h3cevtModuleRt-ce32                        OBJECT IDENTIFIER ::= { h3cevtModuleRouterType 159 } -- 2 Port Channelized E3 module
h3cevtModuleRt-bsv2                        OBJECT IDENTIFIER ::= { h3cevtModuleRouterType 160 } -- 2 Port BSV module
h3cevtModuleRt-bsv4                        OBJECT IDENTIFIER ::= { h3cevtModuleRouterType 161 } -- 4 Port BSV module
h3cevtModuleRt-RPU                         OBJECT IDENTIFIER ::= { h3cevtModuleRouterType 162 } -- Route processing unit
h3cevtModuleRt-ERPU                        OBJECT IDENTIFIER ::= { h3cevtModuleRouterType 163 } -- Enhanced route processing unit
h3cevtModuleRt-SSL                         OBJECT IDENTIFIER ::= { h3cevtModuleRouterType 164 } -- SSL Encrypt Card
h3cevtModuleRt-NSA                         OBJECT IDENTIFIER ::= { h3cevtModuleRouterType 165 } -- NSA Encrypt Card

--
-- 166 to 199 reserved for other devices
--


--
-- 200 to 399 reserved for normal routers part I
--
h3cevtModuleRT-SIC-1GEC                    OBJECT IDENTIFIER ::= { h3cevtModuleRouterType 200 } -- 1-Port 10M/100M/1000M COMBO Ethernet Interface SIC Module
h3cevtModuleRT-24FSW                       OBJECT IDENTIFIER ::= { h3cevtModuleRouterType 201 } -- 24-Port 10M/100M and 2-Port 1000BASE-T/1000BASE-X(COMBO) Ethernet L2 Switch Module
h3cevtModuleRT-24FSWP                      OBJECT IDENTIFIER ::= { h3cevtModuleRouterType 202 } -- 24-Port 10M/100M(WITH POE) and 2-Port 1000BASE-T/1000BASE-X(COMBO) Ethernet L2 Switch Module
h3cevtModuleRT-16FSW                       OBJECT IDENTIFIER ::= { h3cevtModuleRouterType 203 } -- 16-Port 10M/100M Ethernet L2 Switch Module
h3cevtModuleRT-16FSWP                      OBJECT IDENTIFIER ::= { h3cevtModuleRouterType 204 } -- 16-Port 10M/100M(WITH POE) Ethernet L2 Switch Module
h3cevtModuleRT-1VE1                        OBJECT IDENTIFIER ::= { h3cevtModuleRouterType 205 } -- 1-Port Voice E1 Module
h3cevtModuleRT-1VT1                        OBJECT IDENTIFIER ::= { h3cevtModuleRouterType 206 } -- 1-Port Voice T1 Module
h3cevtModuleRT-2VE1                        OBJECT IDENTIFIER ::= { h3cevtModuleRouterType 207 } -- 2-Port Voice E1 Module
h3cevtModuleRT-2VT1                        OBJECT IDENTIFIER ::= { h3cevtModuleRouterType 208 } -- 2-Port Voice T1 Module
h3cevtModuleRT-SIC-4FSW                    OBJECT IDENTIFIER ::= { h3cevtModuleRouterType 209 } -- 4-Port 10M/100M Ethernet L2 Switch Module (RJ45)
h3cevtModuleRT-SIC-4FSWP                   OBJECT IDENTIFIER ::= { h3cevtModuleRouterType 210 } -- 4-Port 10M/100M Ethernet L2 Switch Module(RJ45,WITH POE)
h3cevtModuleRT-DSIC-9FSW                   OBJECT IDENTIFIER ::= { h3cevtModuleRouterType 211 } -- 9-Port 10M/100M Ethernet L2 Switch Module(RJ45)
h3cevtModuleRT-DSIC-9FSWP                  OBJECT IDENTIFIER ::= { h3cevtModuleRouterType 212 } -- 9-Port 10M/100M Ethernet L2 Switch Module(RJ45,WITH POE)
h3cevtModuleRT-SIC-1VE1                    OBJECT IDENTIFIER ::= { h3cevtModuleRouterType 213 } -- 1-Port Voice E1 SIC Interface Module
h3cevtModuleRT-SIC-1VT1                    OBJECT IDENTIFIER ::= { h3cevtModuleRouterType 214 } -- 1-Port Voice T1 SIC Interface Module
h3cevtModuleRT-VCPM                        OBJECT IDENTIFIER ::= { h3cevtModuleRouterType 215 } -- Voice Co-Processing Module
h3cevtModuleRT-VPM                         OBJECT IDENTIFIER ::= { h3cevtModuleRouterType 216 } -- 32-Channels Voice Processing Module
h3cevtModuleRT-VPMA                        OBJECT IDENTIFIER ::= { h3cevtModuleRouterType 217 } -- 16-Channels Voice Processing Module
h3cevtModuleRT-VPMB                        OBJECT IDENTIFIER ::= { h3cevtModuleRouterType 218 } -- 8-Channels Voice Processing Module
h3cevtModuleRT-VPMC                        OBJECT IDENTIFIER ::= { h3cevtModuleRouterType 219 } -- 24-Channels Voice Processing Module
h3cevtModuleRt-fe18-75                     OBJECT IDENTIFIER ::= { h3cevtModuleRouterType 220 } -- 8 Port FE1(75 O) module
h3cevtModuleRt-fe18-120                    OBJECT IDENTIFIER ::= { h3cevtModuleRouterType 221 } -- 8 Port FE1(120 O) module
h3cevtModuleRt-ft18                        OBJECT IDENTIFIER ::= { h3cevtModuleRouterType 222 } -- 8 Port FT1 module
h3cevtModuleRt-CF                          OBJECT IDENTIFIER ::= { h3cevtModuleRouterType 223 } -- Compact Flash Card
h3cevtModuleRt-bsv2-v2                     OBJECT IDENTIFIER ::= { h3cevtModuleRouterType 224 } -- 2 Port BSV Version 2
h3cevtModuleRt-e1vi1-v2                    OBJECT IDENTIFIER ::= { h3cevtModuleRouterType 225 } -- E1VI Version 2
h3cevtModuleRt-e1vi2                       OBJECT IDENTIFIER ::= { h3cevtModuleRouterType 226 } -- 2 Port E1VI
h3cevtModuleRt-t1vi1-v2                    OBJECT IDENTIFIER ::= { h3cevtModuleRouterType 227 } -- T1VI Version 2
h3cevtModuleRt-t1vi2                       OBJECT IDENTIFIER ::= { h3cevtModuleRouterType 228 } -- 2 Port T1VI
h3cevtModuleRt-osm                         OBJECT IDENTIFIER ::= { h3cevtModuleRouterType 229 } -- Open Service Module
h3cevtModuleRt-sd707                       OBJECT IDENTIFIER ::= { h3cevtModuleRouterType 230 } -- Encryption Accelerator
h3cevtModuleRt-dm-epri                     OBJECT IDENTIFIER ::= { h3cevtModuleRouterType 231 } -- E1 Pri Digital Modem
h3cevtModuleRt-dm-tpri                     OBJECT IDENTIFIER ::= { h3cevtModuleRouterType 232 } -- T1 Pri Digital Modem
h3cevtModuleRt-ERPU-H                      OBJECT IDENTIFIER ::= { h3cevtModuleRouterType 233 } -- Enhanced route processing unit with only one optic GE interface
h3cevtModuleRT-SIC-1BSV                    OBJECT IDENTIFIER ::= { h3cevtModuleRouterType 234 } -- 1-Port Bri S/T VoiceInterface SIC Module
h3cevtModuleRT-SIC-2BSV                    OBJECT IDENTIFIER ::= { h3cevtModuleRouterType 235 } -- 2-Port Bri S/T VoiceInterface SIC Module
h3cevtModuleRt-gbe8                        OBJECT IDENTIFIER ::= { h3cevtModuleRouterType 236 } -- 8-Port Gigabit Ethernet interface card
h3cevtModuleRt-gbe4                        OBJECT IDENTIFIER ::= { h3cevtModuleRouterType 237 } -- 4-Port Gigabit Ethernet interface card
h3cevtModuleRt-cpos2-v2                    OBJECT IDENTIFIER ::= { h3cevtModuleRouterType 238 } -- 2-Port Channelized Low speed POS interface card
h3cevtModuleRt-cpos1-v2                    OBJECT IDENTIFIER ::= { h3cevtModuleRouterType 239 } -- 1-Port Channelized Low speed POS interface card
h3cevtModuleRt-oap                         OBJECT IDENTIFIER ::= { h3cevtModuleRouterType 240 } -- Open Application Platform
h3cevtModuleRT-48FSWP                      OBJECT IDENTIFIER ::= { h3cevtModuleRouterType 241 } -- 46-Port 10M/100M(With PoE) and 2-Port 1000BASE-T(With PoE) Ethernet L2 Switch Module
h3cevtModuleRT-48FSW                       OBJECT IDENTIFIER ::= { h3cevtModuleRouterType 242 } -- 46-Port 10M/100M and 2-Port 1000BASE-T Ethernet L2 Switch Module
h3cevtModuleRT-ASM                         OBJECT IDENTIFIER ::= { h3cevtModuleRouterType 243 } -- Anti-virus Security Module
h3cevtModuleRT-SIC-1FEF                    OBJECT IDENTIFIER ::= { h3cevtModuleRouterType 244 } -- 1-Port 100M SFP Interface SIC Module
h3cevtModuleRT-XMIM-24FSW                  OBJECT IDENTIFIER ::= { h3cevtModuleRouterType 245 } -- 24-Port 10M/100MBASE-TX Ethernet L2 Switch Interface XMIM-Module
h3cevtModuleRT-WLAN-AG-1RADIO              OBJECT IDENTIFIER ::= { h3cevtModuleRouterType 246 } -- Mini PCI Interface 802.11ag Radio Frequency Adapter Card
h3cevtModuleRT-1CE3                        OBJECT IDENTIFIER ::= { h3cevtModuleRouterType 247 } -- 1-port E3/CE3/FE3 Compatible Interface Module,(M)
h3cevtModuleRT-XMIM-16FSW                  OBJECT IDENTIFIER ::= { h3cevtModuleRouterType 248 } -- 16-Port 10M/100MBASE-TX Ethernet L2 Switch Interface XMIM-Module
h3cevtModuleRT-OAPS                        OBJECT IDENTIFIER ::= { h3cevtModuleRouterType 249 } -- Open Application System-Smart
h3cevtModuleRT-NAM                         OBJECT IDENTIFIER ::= { h3cevtModuleRouterType 250 } -- Network Analysis Module
h3cevtModuleRT-RPE-X1                      OBJECT IDENTIFIER ::= { h3cevtModuleRouterType 251 } -- Route Processing Engine
h3cevtModuleRT-FIP-100                     OBJECT IDENTIFIER ::= { h3cevtModuleRouterType 252 } -- Flexible Interface Platform-100
h3cevtModuleRT-FIP-200                     OBJECT IDENTIFIER ::= { h3cevtModuleRouterType 253 } -- Flexible Interface Platform-200
h3cevtModuleRT-SIC-8AS                     OBJECT IDENTIFIER ::= { h3cevtModuleRouterType 254 } -- 8-Port Asynchronous Serial
h3cevtModuleRT-WAAM                        OBJECT IDENTIFIER ::= { h3cevtModuleRouterType 255 } -- WAN Application Acceleration Module
h3cevtModuleRt-msp4p-OC3c                  OBJECT IDENTIFIER ::= { h3cevtModuleRouterType 256 } -- 4 Port Multi-Speed POS Interface Module (OC-3c Mode)
h3cevtModuleRt-1pos-oc48                   OBJECT IDENTIFIER ::= { h3cevtModuleRouterType 257 } -- 1 Port Super-Speed POS Interface Card
h3cevtModuleRt-xgbe                        OBJECT IDENTIFIER ::= { h3cevtModuleRouterType 258 } -- 1-Port 10GBASE-R/W Ethernet Optical Interface Card
h3cevtModuleRT-EADM                        OBJECT IDENTIFIER ::= { h3cevtModuleRouterType 259 } -- EAD Integrated Module
h3cevtModuleRT-VCM                         OBJECT IDENTIFIER ::= { h3cevtModuleRouterType 260 } -- Voice Convergence Module
h3cevtModuleRT-SIC-2FXS1FXO                OBJECT IDENTIFIER ::= { h3cevtModuleRouterType 261 } -- 2FXS+1FXO Interface SIC-Module
h3cevtModuleRT-8FXS8FXO                    OBJECT IDENTIFIER ::= { h3cevtModuleRouterType 262 } -- 8FXS+8FXO Interface Module
h3cevtModuleRT-16FXS                       OBJECT IDENTIFIER ::= { h3cevtModuleRouterType 263 } -- 16-port FXS Interface Module
h3cevtModuleRT-OAPS-ICM                    OBJECT IDENTIFIER ::= { h3cevtModuleRouterType 264 } -- OAPS Information Communication Module
h3cevtModuleRT-OAP-ICM                     OBJECT IDENTIFIER ::= { h3cevtModuleRouterType 265 } -- OAP Information Communication Module
h3cevtModuleRT-8fe                         OBJECT IDENTIFIER ::= { h3cevtModuleRouterType 266 } -- 8-Port 100M Ethernet Electrical Interface Module
h3cevtModuleRT-4gbp                        OBJECT IDENTIFIER ::= { h3cevtModuleRouterType 267 } -- 4-Port GigaBit Ethernet Optical Interface Module(SFP)
h3cevtModuleRT-MPU-G2                      OBJECT IDENTIFIER ::= { h3cevtModuleRouterType 268 } -- Main Processor Unit
h3cevtModuleRT-OAPS-OCE                    OBJECT IDENTIFIER ::= { h3cevtModuleRouterType 269 } -- OAPS Office Communication Engine
h3cevtModuleRT-OAP-OCE                     OBJECT IDENTIFIER ::= { h3cevtModuleRouterType 270 } -- OAP Office Communication Engine
h3cevtModuleRT-OAPS-ICE                    OBJECT IDENTIFIER ::= { h3cevtModuleRouterType 271 } -- OAPS Information Communication Engine
h3cevtModuleRT-OAP-ICE                     OBJECT IDENTIFIER ::= { h3cevtModuleRouterType 272 } -- OAP Information Communication Module
h3cevtModuleRT-SIC-16AS                    OBJECT IDENTIFIER ::= { h3cevtModuleRouterType 273 } -- 16-Port Asynchronous Serial
h3cevtModuleRT-SPE-FWM                     OBJECT IDENTIFIER ::= { h3cevtModuleRouterType 274 } -- Gigabit Firewall Module
h3cevtModuleRT-cls2p                       OBJECT IDENTIFIER ::= { h3cevtModuleRouterType 275 } -- 2 Port Channelized 155M POS to E3/T3 Interface Module
h3cevtModuleRT-cls1p                       OBJECT IDENTIFIER ::= { h3cevtModuleRouterType 276 } -- 1 Port Channelized 155M POS to E3/T3 Interface Module
h3cevtModuleRT-SIC-2E1-F                   OBJECT IDENTIFIER ::= { h3cevtModuleRouterType 277 } -- 2-Port Fractional E1 Interface SIC-Module
h3cevtModuleRT-SIC-1E1-F-V2                OBJECT IDENTIFIER ::= { h3cevtModuleRouterType 278 } -- 1-Port Fractional E1 Interface SIC-Module
h3cevtModuleRT-MCU                         OBJECT IDENTIFIER ::= { h3cevtModuleRouterType 279 } -- Main Control Unit
h3cevtModuleRT-ACU                         OBJECT IDENTIFIER ::= { h3cevtModuleRouterType 280 } -- Access Control Unit
h3cevtModuleRT-1ATM-OC3                    OBJECT IDENTIFIER ::= { h3cevtModuleRouterType 281 } -- 1-Port Asynchronous Transfer Mode OC3 Board
h3cevtModuleRT-RSE-X1                      OBJECT IDENTIFIER ::= { h3cevtModuleRouterType 282 } -- Main Processing Unit With XAUI Switch
h3cevtModuleRT-FIP-210                     OBJECT IDENTIFIER ::= { h3cevtModuleRouterType 283 } -- Multi-core CPU Line Processing Board with 2 Combo GE Ports
h3cevtModuleRT-1expa                       OBJECT IDENTIFIER ::= { h3cevtModuleRouterType 284 } -- 1 Port Ten Gigabit Interface Module
h3cevtModuleRT-WLAN-SIC-N-1RADIO           OBJECT IDENTIFIER ::= { h3cevtModuleRouterType 285 } -- 1 wlan-radio 802.11n sic Interface Board
h3cevtModuleRT-WLAN-SIC-BG-1RADIO          OBJECT IDENTIFIER ::= { h3cevtModuleRouterType 286 } -- 1 wlan-radio 802.11b/g sic Interface Board
h3cevtModuleRT-al2p                        OBJECT IDENTIFIER ::= { h3cevtModuleRouterType 287 } -- 2 Port 155M ATM Interface Module
h3cevtModuleRT-msp2p-OC3c                  OBJECT IDENTIFIER ::= { h3cevtModuleRouterType 288 } -- 2-Port Multi-speed POS Interface Module (OC-3c Mode)
h3cevtModuleRT-8gbp                        OBJECT IDENTIFIER ::= { h3cevtModuleRouterType 289 } -- 8-Port GigaBit Ethernet Optical Interface Module(SFP)
h3cevtModuleRT-SIC-EPON                    OBJECT IDENTIFIER ::= { h3cevtModuleRouterType 290 } -- 1-Port Ethernet Passive Optical Network SIC Card(SFF)
h3cevtModuleRT-SIC-3G-GSM-H3               OBJECT IDENTIFIER ::= { h3cevtModuleRouterType 291 } -- 3G Wireless WAN Interface SIC Module Supporting GPRS/EDGE/UMTS/HSDPA
h3cevtModuleRT-msp2p-OC12c                 OBJECT IDENTIFIER ::= { h3cevtModuleRouterType 292 } -- 2-Port Multi-speed POS Interface Module (OC-12c Mode)
h3cevtModuleRt-msp4p-OC12c                 OBJECT IDENTIFIER ::= { h3cevtModuleRouterType 293 } -- 4-Port Multi-Speed POS Interface Module (OC-12c Mode)
h3cevtModuleRt-al1p                        OBJECT IDENTIFIER ::= { h3cevtModuleRouterType 294 } -- 1-Port 155M ATM Interface Module
h3cevtModuleRt-OAP-100                     OBJECT IDENTIFIER ::= { h3cevtModuleRouterType 295 } -- Open Application Platform Module
h3cevtModuleRt-FIP-110                     OBJECT IDENTIFIER ::= { h3cevtModuleRouterType 296 } -- Flexible Interface Platform-110
h3cevtModuleRt-OSM-SSM                     OBJECT IDENTIFIER ::= { h3cevtModuleRouterType 297 } -- OSM Security Services Module
h3cevtModuleRt-OAP-SSM                     OBJECT IDENTIFIER ::= { h3cevtModuleRouterType 298 } -- OAP Security Services Module
h3cevtModuleRt-rs2p                        OBJECT IDENTIFIER ::= { h3cevtModuleRouterType 299 } -- 2-Port OC-48c/STM-16c RPR Interface Module
h3cevtModuleRt-SAP-48GBE                   OBJECT IDENTIFIER ::= { h3cevtModuleRouterType 300 } -- 48-Port 1000Base-T Gigabit Ethernet Interface Module
h3cevtModuleRt-SAP-48GBP                   OBJECT IDENTIFIER ::= { h3cevtModuleRouterType 301 } -- 48-Port 1000BASE Ethernet Optical Interface Module
h3cevtModuleRt-SAP-24GBP                   OBJECT IDENTIFIER ::= { h3cevtModuleRouterType 302 } -- 24-Port 1000BASE Ethernet Optical Interface Module
h3cevtModuleRt-SPE-SSL                     OBJECT IDENTIFIER ::= { h3cevtModuleRouterType 303 } -- SSL VPN Module
h3cevtModuleRt-SIC-AUDIO                   OBJECT IDENTIFIER ::= { h3cevtModuleRouterType 304 } -- MOH and PAGE Interface SIC Module Supporting MOH/PAGE/DOOR RELAY
h3cevtModuleRt-FIC-1E1POS-H3               OBJECT IDENTIFIER ::= { h3cevtModuleRouterType 305 } -- 1-Port E1 POS Interface FIC Module
h3cevtModuleRt-DSIC-4FXS1FXO               OBJECT IDENTIFIER ::= { h3cevtModuleRouterType 306 } -- 4FXS+1FXO Interface DSIC-Module
h3cevtModuleRt-FIC-CPOS                    OBJECT IDENTIFIER ::= { h3cevtModuleRouterType 307 } -- 1-Port CPOS Interface Module
h3cevtModuleRt-DSIC-1SHDSL-8W              OBJECT IDENTIFIER ::= { h3cevtModuleRouterType 308 } -- 1-Port 8 Wire SHDSL Interface DSIC Module
h3cevtModuleRt-SIC-3G-TD                   OBJECT IDENTIFIER ::= { h3cevtModuleRouterType 309 } -- 1 Port TD-Cellular Interface SIC-Module
h3cevtModuleRt-SIC-3G-CDMA                 OBJECT IDENTIFIER ::= { h3cevtModuleRouterType 310 } -- 1 Port CDMA-Cellular Interface SIC-Module
h3cevtModuleRt-SIC-3G-HSPA                 OBJECT IDENTIFIER ::= { h3cevtModuleRouterType 311 } -- 1 Port HSPA-Cellular Interface SIC-Module
h3cevtModuleRt-FIC-OAP-V2                  OBJECT IDENTIFIER ::= { h3cevtModuleRouterType 312 } -- Open Application Platform V2 FIC Module
h3cevtModuleRt-MIM-OAP-V2                  OBJECT IDENTIFIER ::= { h3cevtModuleRouterType 313 } -- Open Application Platform V2 MIM Module
h3cevtModuleRt-MIM-OAPS-V2                 OBJECT IDENTIFIER ::= { h3cevtModuleRouterType 314 } -- Open Application System-Smart V2 MIM Module
h3cevtModuleRt-HMIM-1CT3                   OBJECT IDENTIFIER ::= { h3cevtModuleRouterType 315 } -- 1 Port Channelized T3 Interface HMIM Module
h3cevtModuleRt-HMIM-1CE3                   OBJECT IDENTIFIER ::= { h3cevtModuleRouterType 316 } -- 1 Port Channelized E3 Interface HMIM Module
h3cevtModuleRt-HMIM-1POS                   OBJECT IDENTIFIER ::= { h3cevtModuleRouterType 317 } -- 1 Port POS Interface HMIM Module
h3cevtModuleRt-HMIM-2SAE                   OBJECT IDENTIFIER ::= { h3cevtModuleRouterType 318 } -- 2 Port SAE Interface HMIM Module
h3cevtModuleRt-HMIM-4SAE                   OBJECT IDENTIFIER ::= { h3cevtModuleRouterType 319 } -- 4 Port SAE Interface HMIM Module
h3cevtModuleRt-HMIM-8SAE                   OBJECT IDENTIFIER ::= { h3cevtModuleRouterType 320 } -- 8 Port SAE Interface HMIM Module
h3cevtModuleRt-HMIM-8ASE                   OBJECT IDENTIFIER ::= { h3cevtModuleRouterType 321 } -- 8 Port ASE Interface HMIM Module
h3cevtModuleRt-HMIM-16ASE                  OBJECT IDENTIFIER ::= { h3cevtModuleRouterType 322 } -- 16 Port ASE Interface HMIM Module
h3cevtModuleRt-HMIM-1E1                    OBJECT IDENTIFIER ::= { h3cevtModuleRouterType 323 } -- 1 Port E1 Interface HMIM Module
h3cevtModuleRt-HMIM-2E1                    OBJECT IDENTIFIER ::= { h3cevtModuleRouterType 324 } -- 2 Port E1 Interface HMIM Module
h3cevtModuleRt-HMIM-4E1                    OBJECT IDENTIFIER ::= { h3cevtModuleRouterType 325 } -- 4 Port E1 Interface HMIM Module
h3cevtModuleRt-HMIM-8E1-75                 OBJECT IDENTIFIER ::= { h3cevtModuleRouterType 326 } -- 8 Port E1(75 o) Interface HMIM Module
h3cevtModuleRt-HMIM-1E1-F                  OBJECT IDENTIFIER ::= { h3cevtModuleRouterType 327 } -- 1 Port E1-F Interface HMIM Module
h3cevtModuleRt-HMIM-2E1-F                  OBJECT IDENTIFIER ::= { h3cevtModuleRouterType 328 } -- 2 Port E1-F Interface HMIM Module
h3cevtModuleRt-HMIM-4E1-F                  OBJECT IDENTIFIER ::= { h3cevtModuleRouterType 329 } -- 4 Port E1-F Interface HMIM Module
h3cevtModuleRt-HMIM-8E1-F-75               OBJECT IDENTIFIER ::= { h3cevtModuleRouterType 330 } -- 8 Port E1-F(75 o) Interface HMIM Module
h3cevtModuleRt-HMIM-6AM                    OBJECT IDENTIFIER ::= { h3cevtModuleRouterType 331 } -- 6 Port AM Interface HMIM Module
h3cevtModuleRt-HMIM-6FCM                   OBJECT IDENTIFIER ::= { h3cevtModuleRouterType 332 } -- 6 Port FCM Interface HMIM Module
h3cevtModuleRt-HMIM-2T1                    OBJECT IDENTIFIER ::= { h3cevtModuleRouterType 333 } -- 2 Port T1 Interface HMIM Module
h3cevtModuleRt-HMIM-4T1-F                  OBJECT IDENTIFIER ::= { h3cevtModuleRouterType 334 } -- 4 Port T1-F Interface HMIM Module
h3cevtModuleRt-HMIM-8T1                    OBJECT IDENTIFIER ::= { h3cevtModuleRouterType 335 } -- 8 Port T1 Interface HMIM Module
h3cevtModuleRt-HMIM-8T1-F                  OBJECT IDENTIFIER ::= { h3cevtModuleRouterType 336 } -- 8 Port T1-F Interface HMIM Module
h3cevtModuleRt-HMIM-1VE1                   OBJECT IDENTIFIER ::= { h3cevtModuleRouterType 337 } -- 1 Port Voice E1 Interface HMIM Module
h3cevtModuleRt-HMIM-1VT1                   OBJECT IDENTIFIER ::= { h3cevtModuleRouterType 338 } -- 1 Port Voice T1 Interface HMIM Module
h3cevtModuleRt-HMIM-2VE1                   OBJECT IDENTIFIER ::= { h3cevtModuleRouterType 339 } -- 2 Port Voice E1 Interface HMIM Module
h3cevtModuleRt-HMIM-2VT1                   OBJECT IDENTIFIER ::= { h3cevtModuleRouterType 340 } -- 2 Port Voice T1 Interface HMIM Module
h3cevtModuleRt-HMIM-8FXS8FXO               OBJECT IDENTIFIER ::= { h3cevtModuleRouterType 341 } -- 8FXS + 8FXO Interface HMIM Module
h3cevtModuleRt-HMIM-16FXS                  OBJECT IDENTIFIER ::= { h3cevtModuleRouterType 342 } -- 16 Port FXS Interface HMIM Module
h3cevtModuleRt-HMIM-4FXS                   OBJECT IDENTIFIER ::= { h3cevtModuleRouterType 343 } -- 4 Port FXS Interface HMIM Module
h3cevtModuleRt-HMIM-4FXO                   OBJECT IDENTIFIER ::= { h3cevtModuleRouterType 344 } -- 4 Port FXO Interface HMIM Module
h3cevtModuleRt-HMIM-4EM                    OBJECT IDENTIFIER ::= { h3cevtModuleRouterType 345 } -- 4 Port E&M Interface HMIM Module
h3cevtModuleRt-HMIM-4BSV                   OBJECT IDENTIFIER ::= { h3cevtModuleRouterType 346 } -- 4 Port Bri S/T Voice Interface HMIM Module
h3cevtModuleRt-SIC-CNDE                    OBJECT IDENTIFIER ::= { h3cevtModuleRouterType 347 } -- CNDE Crypto Engine SIC-Module
h3cevtModuleRt-ESM-CNDE                    OBJECT IDENTIFIER ::= { h3cevtModuleRouterType 348 } -- CNDE Crypto Engine ESM-Module
h3cevtModuleRt-ESM-CNDE-M                  OBJECT IDENTIFIER ::= { h3cevtModuleRouterType 349 } -- CNDE Crypto Engine MiniPCI-ESM-Module
h3cevtModuleRt-SR6602-X1                   OBJECT IDENTIFIER ::= { h3cevtModuleRouterType 350 } -- 2U Router Host(4GE Combo/2 HIM slot)
h3cevtModuleRt-SR6602-X2                   OBJECT IDENTIFIER ::= { h3cevtModuleRouterType 351 } -- 2U Router Host(4GE Combo/2 10G SFP+/2 HIM slot)
h3cevtModuleRt-MCP-X1                      OBJECT IDENTIFIER ::= { h3cevtModuleRouterType 352 } -- Main Controller and Processor X1
h3cevtModuleRt-MCP-X2                      OBJECT IDENTIFIER ::= { h3cevtModuleRouterType 353 } -- Main Controller and Processor X2
h3cevtModuleRt-FIP-10                      OBJECT IDENTIFIER ::= { h3cevtModuleRouterType 354 } -- Flexible Interface Platform 10
h3cevtModuleRt-FIP-20                      OBJECT IDENTIFIER ::= { h3cevtModuleRouterType 355 } -- Flexible Interface Platform 20
h3cevtModuleRt-RSE-X2                      OBJECT IDENTIFIER ::= { h3cevtModuleRouterType 356 } -- Route Switch Engine X2
h3cevtModuleRt-FIP-600                     OBJECT IDENTIFIER ::= { h3cevtModuleRouterType 357 } -- Flexible Interface Platform 600
h3cevtModuleRt-SAP-4EXP                    OBJECT IDENTIFIER ::= { h3cevtModuleRouterType 358 } -- 4-Port 10GBASE-R/W Ethernet Optical Interface Module(SFP+)
h3cevtModuleRt-SFE-X1                      OBJECT IDENTIFIER ::= { h3cevtModuleRouterType 359 } -- Switch Fabric Engine X1
h3cevtModuleRt-SFE-A1                      OBJECT IDENTIFIER ::= { h3cevtModuleRouterType 360 } -- Switch Fabric Engine A1
h3cevtModuleRt-HMIM-24GSW                  OBJECT IDENTIFIER ::= { h3cevtModuleRouterType 361 } -- 24-Port 10M/100M/1000MBASE-T Ethernet L2 Switch Interface HMIM_Module
h3cevtModuleRt-HMIM-24GSWP                 OBJECT IDENTIFIER ::= { h3cevtModuleRouterType 362 } -- 24-Port 10M/100M/1000MBASE-T(WITH POE) Ethernet L2 Switch Interface HMIM_Module
h3cevtModuleRt-MPU100                      OBJECT IDENTIFIER ::= { h3cevtModuleRouterType 363 } -- Main Processing Unit 100
h3cevtModuleRt-SPU100                      OBJECT IDENTIFIER ::= { h3cevtModuleRouterType 364 } -- Service Processing Unit 100
h3cevtModuleRt-SPU200                      OBJECT IDENTIFIER ::= { h3cevtModuleRouterType 365 } -- Service Processing Unit 200
h3cevtModuleRt-WLAN-N-1RADIO               OBJECT IDENTIFIER ::= { h3cevtModuleRouterType 366 } -- Mini PCI Interface 802.11n Radio Frequency Adapter Card
h3cevtModuleRt-3G-CDMA                     OBJECT IDENTIFIER ::= { h3cevtModuleRouterType 367 } -- 1 Port CDMA-Cellular Interface Adapter Card
h3cevtModuleRt-3G-WCDMA                    OBJECT IDENTIFIER ::= { h3cevtModuleRouterType 368 } -- 1 Port WCDMA-Cellular Interface Adapter Card
h3cevtModuleRt-3G-HSPAPLUS                 OBJECT IDENTIFIER ::= { h3cevtModuleRouterType 369 } -- 1 Port HSPA+-Cellular Interface Adapter Card
h3cevtModuleRt-VPM-128                     OBJECT IDENTIFIER ::= { h3cevtModuleRouterType 370 } -- 128-VoiceChannel VPM Module
h3cevtModuleRt-VPM-256                     OBJECT IDENTIFIER ::= { h3cevtModuleRouterType 371 } -- 256-VoiceChannel VPM Module
h3cevtModuleRt-VPM-512                     OBJECT IDENTIFIER ::= { h3cevtModuleRouterType 372 } -- 512-VoiceChannel VPM Module
h3cevtModuleRt-HMIM-8GEE                   OBJECT IDENTIFIER ::= { h3cevtModuleRouterType 373 } -- 8-port copper GigabitEthernet HMIM Module
h3cevtModuleRt-HMIM-4GEE                   OBJECT IDENTIFIER ::= { h3cevtModuleRouterType 374 } -- 4-port copper GigabitEthernet HMIM Module
h3cevtModuleRt-HMIM-2GEE                   OBJECT IDENTIFIER ::= { h3cevtModuleRouterType 375 } -- 2-port copper GigabitEthernet HMIM Module
h3cevtModuleRt-HMIM-8GEF                   OBJECT IDENTIFIER ::= { h3cevtModuleRouterType 376 } -- 8-port fiber GigabitEthernet HMIM Module
h3cevtModuleRt-HMIM-4GEF                   OBJECT IDENTIFIER ::= { h3cevtModuleRouterType 377 } -- 4-port fiber GigabitEthernet HMIM Module
h3cevtModuleRt-HMIM-2GEF                   OBJECT IDENTIFIER ::= { h3cevtModuleRouterType 378 } -- 2-port fiber GigabitEthernet HMIM Module
h3cevtModuleRt-SPU300                      OBJECT IDENTIFIER ::= { h3cevtModuleRouterType 379 } -- Service Processing Unit 300
h3cevtModuleRt-HMIM-1CPOS                  OBJECT IDENTIFIER ::= { h3cevtModuleRouterType 380 } -- 1-port CPOS Interface HMIM Module
h3cevtModuleRt-HMIM-2CPOS                  OBJECT IDENTIFIER ::= { h3cevtModuleRouterType 381 } -- 2-port CPOS Interface HMIM Module
h3cevtModuleRt-SPU100-5080                 OBJECT IDENTIFIER ::= { h3cevtModuleRouterType 382 } -- Service Processing Unit 100
h3cevtModuleRt-SPU200-5080                 OBJECT IDENTIFIER ::= { h3cevtModuleRouterType 383 } -- Service Processing Unit 200
h3cevtModuleRt-SPU300-5080                 OBJECT IDENTIFIER ::= { h3cevtModuleRouterType 384 } -- Service Processing Unit 300
h3cevtModuleRt-4G-LTE-Verizon              OBJECT IDENTIFIER ::= { h3cevtModuleRouterType 385 } -- 1 Port 4G-LTE-Verizon-Cellular Interface Adapter Card
h3cevtModuleRt-4G-LTE-Global               OBJECT IDENTIFIER ::= { h3cevtModuleRouterType 386 } -- 1 Port 4G-LTE-Global-Cellular Interface Adapter Card
h3cevtModuleRt-HMIM-1ATM-OC3               OBJECT IDENTIFIER ::= { h3cevtModuleRouterType 387 } -- 1-Port OC3 ATM MM/SM/SML HMIM Module
h3cevtModuleRt-SIC-1E1-V2                  OBJECT IDENTIFIER ::= { h3cevtModuleRouterType 388 } -- 1-Port E1/CE1/PRI Interface SIC Module
h3cevtModuleRt-FIP-300                     OBJECT IDENTIFIER ::= { h3cevtModuleRouterType 389 } -- Flexible Interface Platform 300
h3cevtModuleRt-FIP-310                     OBJECT IDENTIFIER ::= { h3cevtModuleRouterType 390 } -- Flexible Interface Platform 310
h3cevtModuleRt-TS8P                        OBJECT IDENTIFIER ::= { h3cevtModuleRouterType 391 } -- 8-Port OC-3c/OC-12c POS or Gigabit Ethernet Optical Interface Module(SFP)
h3cevtModuleRt-4G4P                        OBJECT IDENTIFIER ::= { h3cevtModuleRouterType 392 } -- 4-Port Gigabit Ethernet Optical Interface and 4-Port OC-3c POS Interface Module(SFP)
h3cevtModuleRt-SIC-4G-LTE-V                OBJECT IDENTIFIER ::= { h3cevtModuleRouterType 393 } -- 1 Port 4G-LTE-Verizon-Cellular Interface SIC-Module
h3cevtModuleRt-SIC-4G-LTE-A                OBJECT IDENTIFIER ::= { h3cevtModuleRouterType 394 } -- 1 Port 4G-LTE-AT&T-Cellular Interface SIC-Module
h3cevtModuleRt-SIC-4G-LTE-G                OBJECT IDENTIFIER ::= { h3cevtModuleRouterType 395 } -- 1 Port 4G-LTE-Global-Cellular Interface SIC-Module
h3cevtModuleRt-SIC-2SAE                    OBJECT IDENTIFIER ::= { h3cevtModuleRouterType 396 } -- 2 Port SAE Interface SIC Module
h3cevtModuleRt-SIC-4SAE                    OBJECT IDENTIFIER ::= { h3cevtModuleRouterType 397 } -- 4 Port SAE Interface SIC Module
h3cevtModuleRt-HMIM-OAP                    OBJECT IDENTIFIER ::= { h3cevtModuleRouterType 398 } -- Open Application Platform HMIM Interface Module with Cloud Virtualization Kernel
h3cevtModuleRt-HMIM-8GSW                   OBJECT IDENTIFIER ::= { h3cevtModuleRouterType 399 } -- 8-Port 10M/100M/1000MBASE-T Ethernet L2 Switch Interface HMIM-Module,including 2 Combo Ports

--
-- 400 to 599 reserved for security routers
--
h3cevtModuleRt-IPU                         OBJECT IDENTIFIER ::= { h3cevtModuleRouterType 400 } -- IPS Processing Unit
h3cevtModuleRt-MIM2GEBE-PCIE               OBJECT IDENTIFIER ::= { h3cevtModuleRouterType 401 } -- 2-port UTM GigabitEthernet Interface Module
h3cevtModuleRt-HIM12GE-PCIE                OBJECT IDENTIFIER ::= { h3cevtModuleRouterType 402 } -- 12-port GigabitEthernet Interface Module
h3cevtModuleRt-HIM2XGE-PCIE                OBJECT IDENTIFIER ::= { h3cevtModuleRouterType 403 } -- 2-port Ten-GigabitEthernet Interface Module
h3cevtModuleRt-IPU-T1000-M                 OBJECT IDENTIFIER ::= { h3cevtModuleRouterType 404 } -- IPS Processing Unit for T1000-M Mainboard Module
h3cevtModuleRt-IPU-GX4C                    OBJECT IDENTIFIER ::= { h3cevtModuleRouterType 405 } -- 4 Port Gigabit Fiber Module
h3cevtModuleRt-IPU-GT4C                    OBJECT IDENTIFIER ::= { h3cevtModuleRouterType 406 } -- 4 Port 1000BASE-T Module
h3cevtModuleRt-RPU-IAG2000-A               OBJECT IDENTIFIER ::= { h3cevtModuleRouterType 407 } -- Intelligence Application Gateway Module
h3cevtModuleRt-RPU-AFD1000-A               OBJECT IDENTIFIER ::= { h3cevtModuleRouterType 408 } -- Anomaly Flow Detector Module
h3cevtModuleRt-RPU-F5000-A                 OBJECT IDENTIFIER ::= { h3cevtModuleRouterType 409 } -- Advanced Firewall Module
h3cevtModuleRt-ACG-8800S3-MPU              OBJECT IDENTIFIER ::= { h3cevtModuleRouterType 410 } -- Main Control Unit,with 24 1000BASE-X/100BASE-FX Optical Ports,including 8 Combo Ports,SFP Req
h3cevtModuleRt-T5000S3-MPU                 OBJECT IDENTIFIER ::= { h3cevtModuleRouterType 411 } -- Main Control Unit,with 24 1000BASE-X/100BASE-FX Optical Ports,including 8 Combo Ports,SFP Req
h3cevtModuleRt-NS21S2MSPB0                 OBJECT IDENTIFIER ::= { h3cevtModuleRouterType 412 } -- Multi Service Processing Module
h3cevtModuleRt-NS11S2MSPB0                 OBJECT IDENTIFIER ::= { h3cevtModuleRouterType 413 } -- Multi Service Processing Module
h3cevtModuleRt-NSQ1WLAN                    OBJECT IDENTIFIER ::= { h3cevtModuleRouterType 414 } -- Dual-Band,Multi-Mode 802.11a/b/g Wireless LAN card
h3cevtModuleRt-NSQ1GP4U0                   OBJECT IDENTIFIER ::= { h3cevtModuleRouterType 415 } -- 4 Port Gigabit Fiber Module
h3cevtModuleRt-NSQ1GP8C40                  OBJECT IDENTIFIER ::= { h3cevtModuleRouterType 416 } -- 12-Port GigabitEthernet Interface Module,with 4 Combo Ports,8 Fiber Ports
h3cevtModuleRt-NSQ1XS2U0                   OBJECT IDENTIFIER ::= { h3cevtModuleRouterType 417 } -- 2-Port Ten GigabitEthernet Interface Module
h3cevtModuleRt-NSQ1G24XS60                 OBJECT IDENTIFIER ::= { h3cevtModuleRouterType 418 } -- 12-copper 12-fiber and 6-XGE Interface Module
h3cevtModuleRt-NSQ1TGX4EA0                 OBJECT IDENTIFIER ::= { h3cevtModuleRouterType 419 } -- 4-XGE Fabric Interface Module
h3cevtModuleRt-NSQ1FAB08D0                 OBJECT IDENTIFIER ::= { h3cevtModuleRouterType 420 } -- Switch Module
h3cevtModuleRt-NSQ1TGS32SF0                OBJECT IDENTIFIER ::= { h3cevtModuleRouterType 421 } -- 32-XGE Fabric Interface Module
h3cevtModuleRt-NSQ1QGS4SF0                 OBJECT IDENTIFIER ::= { h3cevtModuleRouterType 422 } -- 4-XGE Fabric Interface Module
h3cevtModuleRt-NSQ1GP24TXEA0               OBJECT IDENTIFIER ::= { h3cevtModuleRouterType 423 } -- 16-GE Fabric,8-GE Combo,2-XGE Interface Module
h3cevtModuleRt-NSQ1GP48EB0                 OBJECT IDENTIFIER ::= { h3cevtModuleRouterType 424 } -- 48-GE Fabric Interface Module
h3cevtModuleRt-NSQ1FWCEA0                  OBJECT IDENTIFIER ::= { h3cevtModuleRouterType 425 } -- Firewall Module
h3cevtModuleRt-NSQ1GT48EA0                 OBJECT IDENTIFIER ::= { h3cevtModuleRouterType 426 } -- 48-GE Copper Interface
h3cevtModuleRt-NSQ1TGS8EA0                 OBJECT IDENTIFIER ::= { h3cevtModuleRouterType 427 } -- 8-XGE Fabric Interface
h3cevtModuleRt-NSQ1FAB04B0                 OBJECT IDENTIFIER ::= { h3cevtModuleRouterType 428 } -- Switch Module
h3cevtModuleRt-NSQ1FAB12D0                 OBJECT IDENTIFIER ::= { h3cevtModuleRouterType 429 } -- Switch Module
h3cevtModuleRt-NSQ1SUPB0                   OBJECT IDENTIFIER ::= { h3cevtModuleRouterType 430 } -- Main Control Module
h3cevtModuleRt-VFW1000                     OBJECT IDENTIFIER ::= { h3cevtModuleRouterType 431 } -- Virtual Firwall Gateway module over virtual machine
h3cevtModuleRt-NSQ1CGC2SE0                 OBJECT IDENTIFIER ::= { h3cevtModuleRouterType 432 } -- 2 Port 100GBASE Ethernet Optical Interface Board(CFP)(SE)
h3cevtModuleRt-VLB1000                     OBJECT IDENTIFIER ::= { h3cevtModuleRouterType 433 } -- Virtual LB module over virtual machine
h3cevtModuleRt-NSQM1GT4PFC                 OBJECT IDENTIFIER ::= { h3cevtModuleRouterType 434 } -- 4 Port GigabitEthernet Interface
h3cevtModuleRt-NSQM1FWDFG0                 OBJECT IDENTIFIER ::= { h3cevtModuleRouterType 435 } -- Firewall Module
h3cevtModuleRt-NSQM1NATDFGA0               OBJECT IDENTIFIER ::= { h3cevtModuleRouterType 436 } -- NAT A module
h3cevtModuleRt-NSQM1NATDFGB0               OBJECT IDENTIFIER ::= { h3cevtModuleRouterType 437 } -- NAT B module
h3cevtModuleRt-VFW2000                     OBJECT IDENTIFIER ::= { h3cevtModuleRouterType 438 } -- Virtual Firwall Gateway module over physical machine
h3cevtModuleRt-VLB2000                     OBJECT IDENTIFIER ::= { h3cevtModuleRouterType 439 } -- Virtual LB module ver physical machine
h3cevtModuleRt-NSQM1IPSDFG0                OBJECT IDENTIFIER ::= { h3cevtModuleRouterType 440 } -- NSQM1IPSDFG0
h3cevtModuleRt-NSQM1FWDFGB0                OBJECT IDENTIFIER ::= { h3cevtModuleRouterType 441 } -- NSQM1FWDFGB0-SecBlade IV
h3cevtModuleRt-NSQM1FWDFGC0                OBJECT IDENTIFIER ::= { h3cevtModuleRouterType 442 } -- NSQM1FWDFGC0-SecBlade IV
h3cevtModuleRt-NSQM1FWDFGA1                OBJECT IDENTIFIER ::= { h3cevtModuleRouterType 443 } -- NSQM1FWDFGA1-SecBlade IV
h3cevtModuleRt-NSQM1FWDFGB1                OBJECT IDENTIFIER ::= { h3cevtModuleRouterType 444 } -- NSQM1FWDFGB1-SecBlade IV
h3cevtModuleRt-NSQM1FWDFGC1                OBJECT IDENTIFIER ::= { h3cevtModuleRouterType 445 } -- NSQM1FWDFGC1-SecBlade IV
h3cevtModuleRt-NSQM1FWDFGD1                OBJECT IDENTIFIER ::= { h3cevtModuleRouterType 446 } -- NSQM1FWDFGD1-SecBlade IV
h3cevtModuleRt-NSQM1SUPC0                  OBJECT IDENTIFIER ::= { h3cevtModuleRouterType 447 } -- SecPath T9000-NSQM1SUPC0
h3cevtModuleRt-NSQM1TG4FBA                 OBJECT IDENTIFIER ::= { h3cevtModuleRouterType 448 } -- SecPath F1000-NSQM1TG4FBA
h3cevtModuleRt-NSQM1GP4FBA                 OBJECT IDENTIFIER ::= { h3cevtModuleRouterType 449 } -- SecPath F1000-NSQM1GP4FBA
h3cevtModuleRt-NSQM2MPUC0                  OBJECT IDENTIFIER ::= { h3cevtModuleRouterType 450 } -- H3C M9008-S FW  NSQM2MPUC0
h3cevtModuleRt-NSQM2TGS16SF0               OBJECT IDENTIFIER ::= { h3cevtModuleRouterType 451 } -- H3C M9008-S FW  NSQM2TGS16SF0
h3cevtModuleRt-NSQM2QGS4SC0                OBJECT IDENTIFIER ::= { h3cevtModuleRouterType 452 } -- H3C M9008-S FW  NSQM2QGS4SC0
h3cevtModuleRt-NSQM2GP24TSSC0              OBJECT IDENTIFIER ::= { h3cevtModuleRouterType 453 } -- H3C M9008-S FW  NSQM2GP24TSSC0
h3cevtModuleRt-NSQM2FWDSC0                 OBJECT IDENTIFIER ::= { h3cevtModuleRouterType 454 } -- H3C M9008-S FW  NSQM2FWDSC0
h3cevtModuleRt-NSQM1ADEDFGA0               OBJECT IDENTIFIER ::= { h3cevtModuleRouterType 455 } -- NSQM1ADEDFGA0-SecBlade IV ADE A module
h3cevtModuleRt-NSQM2FWDSCA0                OBJECT IDENTIFIER ::= { h3cevtModuleRouterType 456 } -- H3C M9000-S FW NSQM2FWDSCA0-SecBlade IV
h3cevtModuleRt-NSQM1TGS32QSSG0             OBJECT IDENTIFIER ::= { h3cevtModuleRouterType 457 } -- SecPath M9000-NSQM1TGS32QSSG0
h3cevtModuleRt-NSQM1GT4PFCA                OBJECT IDENTIFIER ::= { h3cevtModuleRouterType 458 } -- 4 Port GigabitEthernet Interface Module
h3cevtModuleRt-NSQM1TG8A                   OBJECT IDENTIFIER ::= { h3cevtModuleRouterType 459 } -- 8 Port Ten-GigabitEthernet Interface Module
h3cevtModuleRt-NSQM1QG2A                   OBJECT IDENTIFIER ::= { h3cevtModuleRouterType 460 } -- 2 Port Forty-GigabitEthernet Interface Module
h3cevtModuleRt-NSQM1GT8A                   OBJECT IDENTIFIER ::= { h3cevtModuleRouterType 461 } -- 8-Port Gigabit Ethernet interface Module
h3cevtModuleRt-NSQM1GP8A                   OBJECT IDENTIFIER ::= { h3cevtModuleRouterType 462 } -- 8 Port Fabric GigabitEthernet Interface Module
h3cevtModuleRt-NSQM1MBFE0                  OBJECT IDENTIFIER ::= { h3cevtModuleRouterType 463 } -- H3C SecPath M9008-S  NSQM1MBFE0
h3cevtModuleRt-NSQM2MBFD0                  OBJECT IDENTIFIER ::= { h3cevtModuleRouterType 464 } -- H3C SecPath M9008-S NSQM2MBFD0
h3cevtModuleRt-NSQM2QG2TG8GP40             OBJECT IDENTIFIER ::= { h3cevtModuleRouterType 465 } -- H3C  SecPath M9008-S  NSQM2QG2TG8GP40
h3cevtModuleRt-NSQM2QG4GP40                OBJECT IDENTIFIER ::= { h3cevtModuleRouterType 466 } -- H3C  SecPath M9008-S  NSQM2QG4GP40
h3cevtModuleRt-NSQM2TG16GP40               OBJECT IDENTIFIER ::= { h3cevtModuleRouterType 467 } -- H3C SecPath M9008-S  NSQM2TG16GP40
h3cevtModuleRt-NSQM1CGQ20                  OBJECT IDENTIFIER ::= { h3cevtModuleRouterType 468 } -- H3C SecPath M9008-S  NSQM1CGQ20
h3cevtModuleRt-NSQM2FWDFG0                 OBJECT IDENTIFIER ::= { h3cevtModuleRouterType 469 } -- H3C M9000-S FW NSQM2FWDFG0-SecBlade IV
h3cevtModuleRt-NSQM2TMPUC0                 OBJECT IDENTIFIER ::= { h3cevtModuleRouterType 470 } -- H3C SecPath T9000-S-NSQM2TMPUC0
h3cevtModuleRt-NSQM2IPSDSCA0               OBJECT IDENTIFIER ::= { h3cevtModuleRouterType 471 } -- H3C SecPath T9000-S-NSQM2IPSDSCA0-SecBlade IV
h3cevtModuleRt-NSQM2AC1400                 OBJECT IDENTIFIER ::= { h3cevtModuleRouterType 472 } -- H3C SecPath M9000-S-NSQM2AC1400
h3cevtModuleRt-NSQM2DC1400                 OBJECT IDENTIFIER ::= { h3cevtModuleRouterType 473 } -- H3C SecPath M9000-S-NSQM2DC1400
h3cevtModuleRt-NSQM1F1KGM0                 OBJECT IDENTIFIER ::= { h3cevtModuleRouterType 474} -- F1000 GM Crypto Module
h3cevtModuleRt-NSQM1F1KGM0-context         OBJECT IDENTIFIER ::= { h3cevtModuleRouterType 475} -- F1000 GM Crypto Module
h3cevtModuleRt-NSQM1F5KGM0                 OBJECT IDENTIFIER ::= { h3cevtModuleRouterType 476} -- F5000 GM Crypto Module
h3cevtModuleRt-NSQM1F5KGM0-context         OBJECT IDENTIFIER ::= { h3cevtModuleRouterType 477} -- F5000 GM Crypto Module
h3cevtModuleRt-NSQM2QG2GP40                OBJECT IDENTIFIER ::= { h3cevtModuleRouterType 478 } -- H3C SecPath M9000-NSQM2QG2GP40
h3cevtModuleRt-NSQM2TG8GP40                OBJECT IDENTIFIER ::= { h3cevtModuleRouterType 479 } -- H3C SecPath M9000-NSQM2TG8GP40

h3cevtModuleRt-NSQM2ADEDSCA0               OBJECT IDENTIFIER ::= { h3cevtModuleRouterType 482 } -- H3C M9000-S FW NSQM2ADEDSCA0-SecBlade IV
h3cevtModuleRt-NSQM2IPSDSCB0               OBJECT IDENTIFIER ::= { h3cevtModuleRouterType 483 } -- H3C M9000-S FW NSQM2IPSDSCB0-SecBlade IV
h3cevtModuleRt-NSQM1G4XS4                  OBJECT IDENTIFIER ::= { h3cevtModuleRouterType 484 } -- 4-GE Fabric,4-XGE Fabric Interface Module
h3cevtModuleRt-NSUM1GT4PFCA                OBJECT IDENTIFIER ::= { h3cevtModuleRouterType 485 } -- 4 Port GigabitEthernet Interface Module
h3cevtModuleRt-NSUM1TG8A                   OBJECT IDENTIFIER ::= { h3cevtModuleRouterType 486 } -- 8 Port Ten-GigabitEthernet Interface Module
h3cevtModuleRt-NSUM1QG2A                   OBJECT IDENTIFIER ::= { h3cevtModuleRouterType 487 } -- 2 Port Forty-GigabitEthernet Interface Module
h3cevtModuleRt-NSUM1GT8A                   OBJECT IDENTIFIER ::= { h3cevtModuleRouterType 488 } -- 8-Port Gigabit Ethernet interface Module
h3cevtModuleRt-NSUM1GP8A                   OBJECT IDENTIFIER ::= { h3cevtModuleRouterType 489 } -- 8 Port Fabric GigabitEthernet Interface Module

h3cevtModuleRt-NSQM2MPUD0                  OBJECT IDENTIFIER ::= { h3cevtModuleRouterType 491 } -- H3C SecPath M9000-S- NSQM2MPUD0
h3cevtModuleRt-NSQM1GMDSCA1                OBJECT IDENTIFIER ::= { h3cevtModuleRouterType 492 } -- H3C SecPath M9000-GM- NSQM1GMDSCA1
h3cevtModuleRt-NSQM1MPULA                  OBJECT IDENTIFIER ::= { h3cevtModuleRouterType 493} -- SecPath F50X0-D NSQM1MPULA
h3cevtModuleRt-NSQM1MPULA2                 OBJECT IDENTIFIER ::= { h3cevtModuleRouterType 494} -- SecPath F5000-AK515 NSQM1MPULA2
h3cevtModuleRt-NSQM1GT8A2                  OBJECT IDENTIFIER ::= { h3cevtModuleRouterType 495} -- SecPath F5000-AK515 NSQM1GT8A2
h3cevtModuleRt-NSQM1GP4TG4A2               OBJECT IDENTIFIER ::= { h3cevtModuleRouterType 496} -- SecPath F5000-AK515 NSQM1GP4TG4A2
h3cevtModuleRt-NSQM1GP2TG6A2               OBJECT IDENTIFIER ::= { h3cevtModuleRouterType 497} -- SecPath F5000-AK515 NSQM1GP2TG6A2
h3cevtModuleRt-NSQM1TG4FBA7                OBJECT IDENTIFIER ::= { h3cevtModuleRouterType 498} -- SecPath F1000-AK-NSQM1TG4FBA7

-- 600 to 799 reserved for voice router--
h3cevtModuleRt-VG-8fxs                     OBJECT IDENTIFIER ::= { h3cevtModuleRouterType 600 } -- 8 Port Foreign Exchange Station module
h3cevtModuleRt-VG-24fxs                    OBJECT IDENTIFIER ::= { h3cevtModuleRouterType 601 } -- 24 Port Foreign Exchange Station module
h3cevtModuleRt-VG-24fxs24fxo               OBJECT IDENTIFIER ::= { h3cevtModuleRouterType 602 } -- 24 Port Foreign Exchange Station and 24 Port Foreign Exchange Office module
h3cevtModuleRt-VG-MPU                      OBJECT IDENTIFIER ::= { h3cevtModuleRouterType 603 } -- Media Processing Unit
h3cevtModuleRt-MIM-VCX-CONNECT-P-3C        OBJECT IDENTIFIER ::= { h3cevtModuleRouterType 604 } -- MIM VCX Connect Primary module
h3cevtModuleRt-MIM-VCX-CONNECT-S-3C        OBJECT IDENTIFIER ::= { h3cevtModuleRouterType 605 } -- MIM VCX Connect Secondary module
h3cevtModuleRt-MIM-VCX-3C                  OBJECT IDENTIFIER ::= { h3cevtModuleRouterType 606 } -- MIM VCX Enterprise module
h3cevtModuleRt-VNIC-VMXNET3                OBJECT IDENTIFIER ::= { h3cevtModuleRouterType 607 } -- 1 Port Gigabit Ethernet interface virtual VMXNET3 module
h3cevtModuleRt-VNIC-E1000                  OBJECT IDENTIFIER ::= { h3cevtModuleRouterType 608 } -- 1 Port Gigabit Ethernet interface virtual E1000 module
h3cevtModuleRt-VNIC-VIRTIO                 OBJECT IDENTIFIER ::= { h3cevtModuleRouterType 609 } -- 1 Port Gigabit Ethernet interface virtual VIRTIO module
h3cevtModuleRt-VNIC-RTL8139                OBJECT IDENTIFIER ::= { h3cevtModuleRouterType 610 } -- 1 Port Gigabit Ethernet interface virtual RTL8139 module
h3cevtModuleRt-VNIC-IXGBEVF                OBJECT IDENTIFIER ::= { h3cevtModuleRouterType 611 } -- 1 Port Ten-Gigabit Ethernet interface virtual IXGBEVF module
h3cevtModuleRt-IXGBE-2XGE                  OBJECT IDENTIFIER ::= { h3cevtModuleRouterType 612 } -- 2 Port Ten-Gigabit Ethernet interface IXGBE module
h3cevtModuleRt-TG3-4GE                     OBJECT IDENTIFIER ::= { h3cevtModuleRouterType 613 } -- 4 Port Gigabit Ethernet interface TG3 module
h3cevtModuleRt-MPUV16                      OBJECT IDENTIFIER ::= { h3cevtModuleRouterType 614 } -- Main Processing Unit over virtual machine
h3cevtModuleRt-MPUP6                       OBJECT IDENTIFIER ::= { h3cevtModuleRouterType 615 } -- Main Processing Unit over physical machine
h3cevtModuleRt-IGB-1GE                     OBJECT IDENTIFIER ::= { h3cevtModuleRouterType 616 } -- 1 Port Gigabit Ethernet interface IGB module
h3cevtModuleRt-IGB-2GE                     OBJECT IDENTIFIER ::= { h3cevtModuleRouterType 617 } -- 2 Port Gigabit Ethernet interface IGB module
h3cevtModuleRt-IGB-4GE                     OBJECT IDENTIFIER ::= { h3cevtModuleRouterType 618 } -- 4 Port Gigabit Ethernet interface IGB module
h3cevtModuleRt-VLNS1000                    OBJECT IDENTIFIER ::= { h3cevtModuleRouterType 619 } -- Virtual L2TP Network Server over virtual machine
h3cevtModuleRt-VLNS2000                    OBJECT IDENTIFIER ::= { h3cevtModuleRouterType 620 } -- Virtual L2TP Network Server over physical machine


--
-- 800 to 999 reserved for normal routers part II
--
h3cevtModuleRt-SIC-4GSW                    OBJECT IDENTIFIER ::= { h3cevtModuleRouterType 800 } -- 4-Port 10M/100M/1000MBASE-T Ethernet L2 Switch Interface SIC-Module
h3cevtModuleRt-SIC-4GSWP                   OBJECT IDENTIFIER ::= { h3cevtModuleRouterType 801 } -- 4-Port 10M/100M/1000MBASE-T(WITH POE) Ethernet L2 Switch Interface SIC-Module
h3cevtModuleRt-SIC-1GEC-V2                 OBJECT IDENTIFIER ::= { h3cevtModuleRouterType 802 } -- 1-Port Combo Gigabit Ethernet Interface SIC-Module
h3cevtModuleRt-4G-LTE-ATT                  OBJECT IDENTIFIER ::= { h3cevtModuleRouterType 803 } -- 1 Port 4G-LTE-ATT-Cellular Interface Adapter Card
h3cevtModuleRt-4G-TD-LTE                   OBJECT IDENTIFIER ::= { h3cevtModuleRouterType 804 } -- 1 Port 4G-TD-LTE-Cellular Interface Adapter Card
h3cevtModuleRt-FIP-240                     OBJECT IDENTIFIER ::= { h3cevtModuleRouterType 805 } -- Flexible Interface Platform 240
h3cevtModuleRt-8GBP-V2                     OBJECT IDENTIFIER ::= { h3cevtModuleRouterType 806 } -- 8-Port GigaBit Ethernet Optical Interface Module(SFP) V2
h3cevtModuleRt-HMIM-CNDE                   OBJECT IDENTIFIER ::= { h3cevtModuleRouterType 807 } -- CNDE Crypto Engine HMIM-Module
h3cevtModuleRt-4G-LTE-Mobile               OBJECT IDENTIFIER ::= { h3cevtModuleRouterType 808 } -- 1 Port 4G-LTE-Mobile-Cellular Interface Adapter Card
h3cevtModuleRt-SIC-4G-LTE-M                OBJECT IDENTIFIER ::= { h3cevtModuleRouterType 809 } -- 1 Port 4G-LTE/TD-SCDMA/WCDMA Cellular Interface SIC-Module
h3cevtModuleRt-CRSE-X3                     OBJECT IDENTIFIER ::= { h3cevtModuleRouterType 810 } -- Carrier Route Switch Engine X3
h3cevtModuleRt-CFIP-300                    OBJECT IDENTIFIER ::= { h3cevtModuleRouterType 811 } -- Carrier Flexible Interface Platform 300
h3cevtModuleRt-CFIP-310                    OBJECT IDENTIFIER ::= { h3cevtModuleRouterType 812 } -- Carrier Flexible Interface Platform 310
h3cevtModuleRt-CSAP-4EXP                   OBJECT IDENTIFIER ::= { h3cevtModuleRouterType 813 } -- Carrier 4-Port 10GBASE-R/W Ethernet Optical Interface Module(SFP+)
h3cevtModuleRt-RSU                         OBJECT IDENTIFIER ::= { h3cevtModuleRouterType 814 } -- Route Switch Unit
h3cevtModuleRt-CFIP-610                    OBJECT IDENTIFIER ::= { h3cevtModuleRouterType 815 } -- Carrier Flexible Interface Platform 610
h3cevtModuleRt-2EXP                        OBJECT IDENTIFIER ::= { h3cevtModuleRouterType 816 } -- 2-Port 10GBASE-R/W Ethernet Optical Interface Module(SFP+)
h3cevtModuleRt-16GBP                       OBJECT IDENTIFIER ::= { h3cevtModuleRouterType 817 } -- 16-Port Gigabit Ethernet Optical Interface Module(SFP)
h3cevtModuleRt-CFIP-240                    OBJECT IDENTIFIER ::= { h3cevtModuleRouterType 818 } -- Carrier Flexible Interface Platform 240
h3cevtModuleRt-RSE-X3                      OBJECT IDENTIFIER ::= { h3cevtModuleRouterType 819 } -- Route Switch Engine X3
h3cevtModuleRt-SAP-8EXP                    OBJECT IDENTIFIER ::= { h3cevtModuleRouterType 820 } -- 8-Port 10GBASE-R/W Ethernet Optical Interface Module(SFP+)
h3cevtModuleRt-SAP-16EXP                   OBJECT IDENTIFIER ::= { h3cevtModuleRouterType 821 } -- 16-Port 10GBASE-R/W Ethernet Optical Interface Module(SFP+)
h3cevtModuleRt-PU1P                        OBJECT IDENTIFIER ::= { h3cevtModuleRouterType 822 } -- 1-Port 10G POS/RPR Interface Module(XFP)
h3cevtModuleRt-RSU100                      OBJECT IDENTIFIER ::= { h3cevtModuleRouterType 823 } -- Router Switch Unit 100
h3cevtModuleRt-SAP-2QGP                    OBJECT IDENTIFIER ::= { h3cevtModuleRouterType 824 } -- 2-Port 40GBASE Ethernet Optical Interface Module(QSFP+)
h3cevtModuleRt-CSFE-X1                     OBJECT IDENTIFIER ::= { h3cevtModuleRouterType 825 } -- Carrier Switch Fabric Engine X1
h3cevtModuleRt-RIC-4GEE                    OBJECT IDENTIFIER ::= { h3cevtModuleRouterType 826 } -- 4-Port 10M/100M/1000MBASE-T Ethernet Interface RIC-Module
h3cevtModuleRt-RIC-4GEF                    OBJECT IDENTIFIER ::= { h3cevtModuleRouterType 827 } -- 4-Port 1000M Base-F Optical Ethernet Interface RIC-Module
h3cevtModuleRt-RIC-8GEE                    OBJECT IDENTIFIER ::= { h3cevtModuleRouterType 828 } -- 8-Port 10M/100M/1000MBASE-T Ethernet Interface RIC-Module
h3cevtModuleRt-RIC-8GEF                    OBJECT IDENTIFIER ::= { h3cevtModuleRouterType 829 } -- 8-Port 1000M Base-F Optical Ethernet Interface RIC-Module
h3cevtModuleRt-RIC-1XGEF                   OBJECT IDENTIFIER ::= { h3cevtModuleRouterType 830 } -- 1-Port Ten-GigabitEthernet Optical Interface RIC-Module
h3cevtModuleRt-HMIM-1E1POS                 OBJECT IDENTIFIER ::= { h3cevtModuleRouterType 831 } -- 1 PORT E1 Interface HMIM-Module
h3cevtModuleRt-DHMIM-1DM                   OBJECT IDENTIFIER ::= { h3cevtModuleRouterType 832 } -- 1 PORT E1 Interface DHMIM-Module
h3cevtModuleRt-DHMIM-1E1POS1DM             OBJECT IDENTIFIER ::= { h3cevtModuleRouterType 833 } -- 1 PORT E1 Interface DHMIM-Module
h3cevtModuleRt-RPE-X3                      OBJECT IDENTIFIER ::= { h3cevtModuleRouterType 834 } -- Route Processing Engine X3
h3cevtModuleRt-CRPE-X3                     OBJECT IDENTIFIER ::= { h3cevtModuleRouterType 835 } -- Carrier Route Processing Engine X3
h3cevtModuleRt-SAP-28GE                    OBJECT IDENTIFIER ::= { h3cevtModuleRouterType 836 } -- 16-Port SFP and 12-Port Combo GE Module
h3cevtModuleRt-SAP-20GE2XP                 OBJECT IDENTIFIER ::= { h3cevtModuleRouterType 837 } -- 16-Port SFP 4-Port Combo GE and 2-Port 10GE Module
h3cevtModuleRt-SFE-L1                      OBJECT IDENTIFIER ::= { h3cevtModuleRouterType 838 } -- Switch Fabric Engine L1
h3cevtModuleRt-FIP-640                     OBJECT IDENTIFIER ::= { h3cevtModuleRouterType 839 } -- Flexible Interface Platform 640
h3cevtModuleRt-HMIM-8GSWF                  OBJECT IDENTIFIER ::= { h3cevtModuleRouterType 840 } -- 8-Port 1000M Base-F Optical Ethernet L2 Switch Interface HMIM_Module, including 4 Combo Ports
h3cevtModuleRt-HMIM-8E1T1                  OBJECT IDENTIFIER ::= { h3cevtModuleRouterType 841 } -- 8-port E1/CE1/T1/CT1/PRI HMIM Module
h3cevtModuleRt-HMIM-4E1T1                  OBJECT IDENTIFIER ::= { h3cevtModuleRouterType 842 } -- 4-port E1/CE1/T1/CT1/PRI HMIM Module
h3cevtModuleRt-HMIM-2E1T1                  OBJECT IDENTIFIER ::= { h3cevtModuleRouterType 843 } -- 2-port E1/CE1/T1/CT1/PRI HMIM Module
h3cevtModuleRt-HMIM-8E1T1-F                OBJECT IDENTIFIER ::= { h3cevtModuleRouterType 844 } -- 8-port E1/T1/Fractional E1/T1 HMIM Module
h3cevtModuleRt-HMIM-4E1T1-F                OBJECT IDENTIFIER ::= { h3cevtModuleRouterType 845 } -- 4-port E1/T1/Fractional E1/T1 HMIM Module
h3cevtModuleRt-HMIM-2E1T1-F                OBJECT IDENTIFIER ::= { h3cevtModuleRouterType 846 } -- 2-port E1/T1/Fractional E1/T1 HMIM Module
h3cevtModuleRt-SIC-3G-HSPA-V2              OBJECT IDENTIFIER ::= { h3cevtModuleRouterType 847 } -- 1 Port HSPA-Cellular Interface SIC-Module V2
h3cevtModuleRt-SIC-4GSWF                   OBJECT IDENTIFIER ::= { h3cevtModuleRouterType 848 } -- 4-Port 1000M Base-F Optical Ethernet L2 Switch Interface SIC-Module
h3cevtModuleRt-SIC-4G-LTE-G-V2             OBJECT IDENTIFIER ::= { h3cevtModuleRouterType 849 } -- 1 Port 4G-LTE-G-V2 Cellular Interface SIC-Module
h3cevtModuleRt-SIC-4G-LTE-A-V2             OBJECT IDENTIFIER ::= { h3cevtModuleRouterType 850 } -- 1 Port 4G-LTE-A-V2 Cellular Interface SIC-Module
h3cevtModuleRt-SIC-4G-LTE-V-V2             OBJECT IDENTIFIER ::= { h3cevtModuleRouterType 851 } -- 1 Port 4G-LTE-V-V2 Cellular Interface SIC-Module
h3cevtModuleRt-MPU60                       OBJECT IDENTIFIER ::= { h3cevtModuleRouterType 852 } -- Main Processing Unit 60
h3cevtModuleRt-SPU                         OBJECT IDENTIFIER ::= { h3cevtModuleRouterType 853 } -- Service Processing Unit
h3cevtModuleRt-SIC-1VE1T1                  OBJECT IDENTIFIER ::= { h3cevtModuleRouterType 854 } -- 1-Port E1/T1 Voice SIC Module,Domestic&Overseas Version
h3cevtModuleRt-CFIP-700                    OBJECT IDENTIFIER ::= { h3cevtModuleRouterType 855 } -- Carrier Flexible Interface Platform 700
h3cevtModuleRt-HIM-20GBP-H3                OBJECT IDENTIFIER ::= { h3cevtModuleRouterType 856 } -- 20-Port Gigabit Ethernet Optical Interface Module(SFP)
h3cevtModuleRt-HIM-4EXP-H3                 OBJECT IDENTIFIER ::= { h3cevtModuleRouterType 857 } -- 4-Port 10GBASE-R/W Ethernet Optical Interface Module(SFP+)
h3cevtModuleRt-HIM-2EXP-H3                 OBJECT IDENTIFIER ::= { h3cevtModuleRouterType 858 } -- 2-Port 10GBASE-R/W Ethernet Optical Interface Module(SFP+)
h3cevtModuleRt-HIM-8GBE-V3                 OBJECT IDENTIFIER ::= { h3cevtModuleRouterType 859 } -- 8-port GigaBit Ethernet Electrical Interface Module
h3cevtModuleRt-HIM-4GBE-V3                 OBJECT IDENTIFIER ::= { h3cevtModuleRouterType 860 } -- 4-port GigaBit Ethernet Electrical Interface Module
h3cevtModuleRt-HIM-8GBP-V3                 OBJECT IDENTIFIER ::= { h3cevtModuleRouterType 861 } -- 8-Port GigaBit Ethernet Optical Interface Module(SFP)
h3cevtModuleRt-HIM-4GBP-V3                 OBJECT IDENTIFIER ::= { h3cevtModuleRouterType 862 } -- 4-Port GigaBit Ethernet Optical Interface Module(SFP)
h3cevtModuleRt-SIC-AP                      OBJECT IDENTIFIER ::= { h3cevtModuleRouterType 863 } -- 1-Port AP SIC Module,Domestic&Overseas Version
h3cevtModuleRt-MPU-04B                     OBJECT IDENTIFIER ::= { h3cevtModuleRouterType 864 } -- CR Main Processing Unit B for 04 Chassis
h3cevtModuleRt-MPU-16B                     OBJECT IDENTIFIER ::= { h3cevtModuleRouterType 865 } -- CR Main Processing Unit B for 08 and 16 Chassis
h3cevtModuleRt-MPU-16E                     OBJECT IDENTIFIER ::= { h3cevtModuleRouterType 866 } -- CR Main Processing Unit E for 08 and 16 Chassis
h3cevtModuleRt-SFU-04D-H                   OBJECT IDENTIFIER ::= { h3cevtModuleRouterType 867 } -- CR Switching Fabric Unit(HD) for 04 Chassis
h3cevtModuleRt-SFU-08C-H                   OBJECT IDENTIFIER ::= { h3cevtModuleRouterType 868 } -- CR Switching Fabric Unit(HC) for 08 Chassis
h3cevtModuleRt-SFU-08D-H                   OBJECT IDENTIFIER ::= { h3cevtModuleRouterType 869 } -- CR Switching Fabric Unit(HD) for 08 Chassis
h3cevtModuleRt-SFU-16B-H                   OBJECT IDENTIFIER ::= { h3cevtModuleRouterType 870 } -- CR Switching Fabric Unit(HB) for 16 Chassis
h3cevtModuleRt-SFU-16C-H                   OBJECT IDENTIFIER ::= { h3cevtModuleRouterType 871 } -- CR Switching Fabric Unit(HC) for 16 Chassis
h3cevtModuleRt-LPU-CQ12                    OBJECT IDENTIFIER ::= { h3cevtModuleRouterType 872 } -- CR 12-Port 100G Ethernet Optical Interface Module
h3cevtModuleRt-LPU-4004                    OBJECT IDENTIFIER ::= { h3cevtModuleRouterType 873 } -- CR Flexible Interface Module 4004
h3cevtModuleRt-HIC-PU02                    OBJECT IDENTIFIER ::= { h3cevtModuleRouterType 874 } -- CR 2-Port 10G POS Optical Interface Card
h3cevtModuleRt-HIC-XP12                    OBJECT IDENTIFIER ::= { h3cevtModuleRouterType 875 } -- CR 12-Port 10G Ethernet Optical Interface Card
h3cevtModuleRt-HIC-GP12                    OBJECT IDENTIFIER ::= { h3cevtModuleRouterType 876 } -- CR 12-Port Gigabit Ethernet Optical Interface Card
h3cevtModuleRt-HIC-QQ03                    OBJECT IDENTIFIER ::= { h3cevtModuleRouterType 877 } -- CR 3-Port 40G Ethernet Optical Interface Card(QSFP+)
h3cevtModuleRt-HIC-CC01                    OBJECT IDENTIFIER ::= { h3cevtModuleRouterType 878 } -- CR 1-Port 100G Ethernet Optical Interface Card(CFP2)
h3cevtModuleRt-HIC-CP01                    OBJECT IDENTIFIER ::= { h3cevtModuleRouterType 879 } -- CR 1-Port 100G Ethernet Optical Interface Card(CFP)
h3cevtModuleRt-MPU-16C                     OBJECT IDENTIFIER ::= { h3cevtModuleRouterType 880 } -- CR Main Processing Unit C for 08 and 16 Chassis
h3cevtModuleRt-MPU-100-X1                  OBJECT IDENTIFIER ::= { h3cevtModuleRouterType 881 } -- Main Processing Unit 100-X1
h3cevtModuleRt-SPU-100-X1                  OBJECT IDENTIFIER ::= { h3cevtModuleRouterType 882 } -- Service Processing Unit 100-X1
h3cevtModuleRt-SPU-200-X1                  OBJECT IDENTIFIER ::= { h3cevtModuleRouterType 883 } -- Service Processing Unit 200-X1
h3cevtModuleRt-SPU-400-X1                  OBJECT IDENTIFIER ::= { h3cevtModuleRouterType 884 } -- Service Processing Unit 400-X1
h3cevtModuleRt-HIM-10GB2EXP-H3             OBJECT IDENTIFIER ::= { h3cevtModuleRouterType 885 } -- 10-port 1000BASE-X Ethernet Optical Interface(SFP)+2-port 10GBASE-R/W Ethernet Optical Interface Card(SFP+)
h3cevtModuleRt-HIM-11GB1EXP-H3             OBJECT IDENTIFIER ::= { h3cevtModuleRouterType 886 } -- 11-port 1000BASE-X Ethernet Optical Interface(SFP)+1-port 10GBASE-R/W Ethernet Optical Interface Card(SFP+)
h3cevtModuleRt-HMIM-1E3T3                  OBJECT IDENTIFIER ::= { h3cevtModuleRouterType 887 } -- 1-port T3 HMIM-Module
h3cevtModuleRt-SIC-4G-CNDE                 OBJECT IDENTIFIER ::= { h3cevtModuleRouterType 888 } -- 1-port 4G LTE and CNDE SIC Module
h3cevtModuleRt-SIC-D4G-CNDE                OBJECT IDENTIFIER ::= { h3cevtModuleRouterType 889 } -- 2-port 4G LTE and CNDE SIC Module
h3cevtModuleRt-LPU-CC08                    OBJECT IDENTIFIER ::= { h3cevtModuleRouterType 890 } -- CR 8-Port 100G Ethernet Optical Interface Module
h3cevtModuleRt-LPU-2002                    OBJECT IDENTIFIER ::= { h3cevtModuleRouterType 891 } -- CR Flexible Interface Module 2002
h3cevtModuleRt-LPU-XP20CC02                OBJECT IDENTIFIER ::= { h3cevtModuleRouterType 892 } -- CR 20-Port 10G Ethernet Optical Interface Module and 2-Port 100G Ethernet Optical Interface Module
h3cevtModuleRt-LPU-XP40                    OBJECT IDENTIFIER ::= { h3cevtModuleRouterType 893 } -- CR 40-Port 10G Ethernet Optical Interface Module
h3cevtModuleRt-LPU-CC04                    OBJECT IDENTIFIER ::= { h3cevtModuleRouterType 894 } -- CR 4-Port 100G Ethernet Optical Interface Module
h3cevtModuleRt-FIP-680                     OBJECT IDENTIFIER ::= { h3cevtModuleRouterType 895 } -- Service Processing Unit(680)
h3cevtModuleRt-MIC-XP4L                    OBJECT IDENTIFIER ::= { h3cevtModuleRouterType 896 } -- 4-port 10GBASE-R/W Ethernet Optical Interface Card(SFP+,LC)
h3cevtModuleRt-MIM-1T3-V2                  OBJECT IDENTIFIER ::= { h3cevtModuleRouterType 897 } -- 1-port T3 Interface Card
h3cevtModuleRt-MIC-GP4L                    OBJECT IDENTIFIER ::= { h3cevtModuleRouterType 898 } -- 4-Port 1000BASE-X COMBO Interface Card,(SFP,LC)
h3cevtModuleRt-MIC-GP8L                    OBJECT IDENTIFIER ::= { h3cevtModuleRouterType 899 } -- 8-Port 1000BASE-X Optical Interface Card,(SFP,LC)
h3cevtModuleRt-MPU-19A                     OBJECT IDENTIFIER ::= { h3cevtModuleRouterType 900 } -- CR Main Processing Unit A for 19 Chassis
h3cevtModuleRt-MPU-19B                     OBJECT IDENTIFIER ::= { h3cevtModuleRouterType 901 } -- CR Main Processing Unit B for 19 Chassis
h3cevtModuleRt-SFU-20C                     OBJECT IDENTIFIER ::= { h3cevtModuleRouterType 902 } -- CR Switching Fabric Unit(HC) for 20 Chassis
h3cevtModuleRt-MSFU-20B                    OBJECT IDENTIFIER ::= { h3cevtModuleRouterType 903 } -- CR Multi-Switching Fabric Unit(HB) for 20 Chassis
h3cevtModuleRt-MSFU-20C                    OBJECT IDENTIFIER ::= { h3cevtModuleRouterType 904 } -- CR Multi-Switching Fabric Unit(HC) for 20 Chassis
h3cevtModuleRt-MCCU-24A                    OBJECT IDENTIFIER ::= { h3cevtModuleRouterType 905 } -- CR Multi-Control Connection A Unit for 24 Chassis
h3cevtModuleRt-MFCU-24A                    OBJECT IDENTIFIER ::= { h3cevtModuleRouterType 906 } -- CR Multi-Fabric Connection A Unit for 24 Chassis
h3cevtModuleRt-RIC-8E1                     OBJECT IDENTIFIER ::= { h3cevtModuleRouterType 907 } -- 8-Port E1/CE1/PRI Interface RIC-Module
h3cevtModuleRt-RIC-1XGEF4GEF               OBJECT IDENTIFIER ::= { h3cevtModuleRouterType 908 } -- 1-Port 10M/100M/1000M/10000MBASE-F and 4-Port 10M/100M/1000MBASE-F Ethernet Interface 1XGEF4GEFModule
h3cevtModuleRt-RIC-TU01A                   OBJECT IDENTIFIER ::= { h3cevtModuleRouterType 909 } -- 1-Port 10M/100M/1000M/10000MBASE-F and 4-Port 10M/100M/1000MBASE-F Ethernet Interface TU01AModule
h3cevtModuleRt-SPE-S1                      OBJECT IDENTIFIER ::= { h3cevtModuleRouterType 910 } -- Service Processing Engine S1
h3cevtModuleRt-SPE-S3                      OBJECT IDENTIFIER ::= { h3cevtModuleRouterType 911 } -- Service Processing Engine S3
h3cevtModuleRt-SPU-600-X1                  OBJECT IDENTIFIER ::= { h3cevtModuleRouterType 912 } -- Service Processing Unit 600-X1
h3cevtModuleRt-RIC-CP08                    OBJECT IDENTIFIER ::= { h3cevtModuleRouterType 913 } -- 8-Port E1/CE1/PRI Interface RIC-Module
h3cevtModuleRt-MIC-SP4L                    OBJECT IDENTIFIER ::= { h3cevtModuleRouterType 914 } -- 4-Port OC-3/STM-1 POS/CPOS/ATM or 1-Port OC-12/STM-4 POS/ATM Optical Interface Card,(SFP,LC)
h3cevtModuleRt-MIC-ET16L                   OBJECT IDENTIFIER ::= { h3cevtModuleRouterType 915 } -- 16-Port E1/T1 Electrical Interface Card
h3cevtModuleRt-MIC-CLP4L                   OBJECT IDENTIFIER ::= { h3cevtModuleRouterType 916 } -- 4-Port OC-3/STM-1 CPOS/POS Optical Interface Card,(SFP,LC)
h3cevtModuleRt-MIC-CLP2L                   OBJECT IDENTIFIER ::= { h3cevtModuleRouterType 917 } -- 2-Port OC-3/STM-1 CPOS/POS Optical Interface Card,(SFP,LC)
h3cevtModuleRt-MIC-SP8L                    OBJECT IDENTIFIER ::= { h3cevtModuleRouterType 918 } -- 8-Port OC-3c/STM-1c POS Optical Interface Card
h3cevtModuleRt-HMIM-8EM                    OBJECT IDENTIFIER ::= { h3cevtModuleRouterType 919 } -- 8-Port E&M Interface HMIM-Module
h3cevtModuleRt-SFU                         OBJECT IDENTIFIER ::= { h3cevtModuleRouterType 920 } -- Switching Fabric Unit
h3cevtModuleRt-SFE-L2                      OBJECT IDENTIFIER ::= { h3cevtModuleRouterType 921 } -- Switching Fabric Engine L2
h3cevtModuleRt-SFU-UNFIXED                 OBJECT IDENTIFIER ::= { h3cevtModuleRouterType 922 } -- Unfixed Switching Fabric Unit
h3cevtModuleRt-FIP-380                     OBJECT IDENTIFIER ::= { h3cevtModuleRouterType 923 } -- Flexible Interface Platform-380
h3cevtModuleRt-19K-MPU-08A                 OBJECT IDENTIFIER ::= { h3cevtModuleRouterType 924 } -- CR Main Processing Unit A for 08 Chassis
h3cevtModuleRt-19K-MPU-16A                 OBJECT IDENTIFIER ::= { h3cevtModuleRouterType 925 } -- CR Main Processing Unit A for 16 Chassis
h3cevtModuleRt-19K-SFU-08C                 OBJECT IDENTIFIER ::= { h3cevtModuleRouterType 926 } -- CR Switching Fabric Unit(HC) for 08 Chassis
h3cevtModuleRt-19K-SFU-16C                 OBJECT IDENTIFIER ::= { h3cevtModuleRouterType 927 } -- CR Switching Fabric Unit(HC) for 16 Chassis
h3cevtModuleRt-19K-LPU-CC08                OBJECT IDENTIFIER ::= { h3cevtModuleRouterType 928 } -- CR 8-Port 100G Ethernet Optical Interface Module
h3cevtModuleRt-19K-LPU-2002                OBJECT IDENTIFIER ::= { h3cevtModuleRouterType 929 } -- CR Flexible Interface Module 2002
h3cevtModuleRt-19K-LPU-XP20CC02            OBJECT IDENTIFIER ::= { h3cevtModuleRouterType 930 } -- CR 20-Port 10G Ethernet Optical Interface Module and 2-Port 100G Ethernet Optical Interface Module
h3cevtModuleRt-19K-LPU-XP40                OBJECT IDENTIFIER ::= { h3cevtModuleRouterType 931 } -- CR 40-Port 10G Ethernet Optical Interface Module
h3cevtModuleRt-19K-LPU-CC04                OBJECT IDENTIFIER ::= { h3cevtModuleRouterType 932 } -- CR 4-Port 100G Ethernet Optical Interface Module
h3cevtModuleRt-19K-LPU-CQ12                OBJECT IDENTIFIER ::= { h3cevtModuleRouterType 933 } -- CR 12-Port 100G Ethernet Optical Interface Module
h3cevtModuleRt-MIC-X-GT8                   OBJECT IDENTIFIER ::= { h3cevtModuleRouterType 934 } -- 8-Port 10/100/1000BASE-T Electronic Multi-functional Interface Card
h3cevtModuleRt-MIC-X-GP4GT4                OBJECT IDENTIFIER ::= { h3cevtModuleRouterType 935 } -- 4-Port 10/100/1000BASE-T Electronic + 4-Port 1000BASE-X Optical Multi-functional Interface Card
h3cevtModuleRt-MIC-X-GP10                  OBJECT IDENTIFIER ::= { h3cevtModuleRouterType 936 } -- 10-Port 1000BASE-X Optical Multi-functional Interface Card
h3cevtModuleRt-MIC-X-GP8                   OBJECT IDENTIFIER ::= { h3cevtModuleRouterType 937 } -- 8-Port 1000BASE-X Optical Multi-functional Interface Card
h3cevtModuleRt-19K-LPU-4004                OBJECT IDENTIFIER ::= { h3cevtModuleRouterType 938 } -- CR Flexible Interface Module 4004
h3cevtModuleRt-FIP-260                     OBJECT IDENTIFIER ::= { h3cevtModuleRouterType 939 } -- Flexible Interface Platform-260
h3cevtModuleRt-LPU-XP72                    OBJECT IDENTIFIER ::= { h3cevtModuleRouterType 940 } -- CR 72-Port 10G Ethernet Optical Interface Module
h3cevtModuleRt-LPU-XP48                    OBJECT IDENTIFIER ::= { h3cevtModuleRouterType 941 } -- CR 48-Port 10G Ethernet Optical Interface Module
h3cevtModuleRt-LPU-CC04B                   OBJECT IDENTIFIER ::= { h3cevtModuleRouterType 942 } -- CR 4-Port 100G Ethernet Optical Interface Module
h3cevtModuleRt-LPU-2002B                   OBJECT IDENTIFIER ::= { h3cevtModuleRouterType 943 } -- CR Flexible Interface Module 2002B
h3cevtModuleRt-LPU-1001B                   OBJECT IDENTIFIER ::= { h3cevtModuleRouterType 944 } -- CR Flexible Interface Module 1001B
h3cevtModuleRt-19K-MSFU-08A                OBJECT IDENTIFIER ::= { h3cevtModuleRouterType 945 } -- CR Multi-Switching Fabric Unit for 8 Chassis
h3cevtModuleRt-Sic-AP220                   OBJECT IDENTIFIER ::= { h3cevtModuleRouterType 946 } -- SIC-AP220 External Antennas 3 Streams Dual Radio
h3cevtModuleRt-FIP-660                     OBJECT IDENTIFIER ::= { h3cevtModuleRouterType 947 } -- Flexible Interface Platform 660
h3cevtModuleRT-MIC-X-ET16                  OBJECT IDENTIFIER ::= { h3cevtModuleRouterType 948 } -- 16-Port E1/T1 Electrical Interface Card,(RJ45)
h3cevtModuleRT-MIC-X-SP4                   OBJECT IDENTIFIER ::= { h3cevtModuleRouterType 949 } -- 4-Port OC-3/STM-1 POS or 1-Port OC-12/STM-4 POS Optical Interface Card,(SFP)
h3cevtModuleRT-MIC-X-SP8                   OBJECT IDENTIFIER ::= { h3cevtModuleRouterType 950 } -- 8-Port OC-3c/STM-1c POS Optical Interface Card,(SFP)
h3cevtModuleRT-MIC-X-CLP2                  OBJECT IDENTIFIER ::= { h3cevtModuleRouterType 951 } -- 2-Port OC-3/STM-1 CPOS Optical Interface Card,(SFP)
h3cevtModuleRT-MIC-X-CLP4                  OBJECT IDENTIFIER ::= { h3cevtModuleRouterType 952 } -- 4-Port OC-3/STM-1 CPOS Optical Interface Card,(SFP)
h3cevtModuleRt-SPU-300                     OBJECT IDENTIFIER ::= { h3cevtModuleRouterType 953 } -- ICG Service Processing Unit 300(10GE Combo)
h3cevtModuleRt-19K-LPU-XP72                OBJECT IDENTIFIER ::= { h3cevtModuleRouterType 954 } -- 72-Port 10G Ethernet Optical Interface Module for 19 chassis
h3cevtModuleRt-19K-LPU-XP48                OBJECT IDENTIFIER ::= { h3cevtModuleRouterType 955 } -- 48-Port 10G Ethernet Optical Interface Module for 19 chassis
h3cevtModuleRt-19K-LPU-2002B               OBJECT IDENTIFIER ::= { h3cevtModuleRouterType 956 } -- Flexible Interface Module 2002B for 19 chassis
h3cevtModuleRt-19K-LPU-CC04B               OBJECT IDENTIFIER ::= { h3cevtModuleRouterType 957 } -- 4-Port 100G Ethernet Optical Interface Module for 19 chassis
h3cevtModuleRt-19K-MPU-16B                 OBJECT IDENTIFIER ::= { h3cevtModuleRouterType 958 } -- Main Processing Unit B for 19016 Chassis
h3cevtModuleRT-RPE-X5                      OBJECT IDENTIFIER ::= { h3cevtModuleRouterType 959 } -- Route Processing Engine X5
h3cevtModuleRT-RPE-X5E                     OBJECT IDENTIFIER ::= { h3cevtModuleRouterType 960 } -- Route Processing Engine X5E
h3cevtModuleRt-HIC-PS04                    OBJECT IDENTIFIER ::= { h3cevtModuleRouterType 961 } -- CR 4-Port non-channelized POS(155M/622M/2.5G) Interface Card,Sub Module
h3cevtModuleRt-HIC-PL08                    OBJECT IDENTIFIER ::= { h3cevtModuleRouterType 962 } -- CR 8-Port non-channelized POS(155M) Interface Card,Sub Module
h3cevtModuleRT-MIC-X-XP2                   OBJECT IDENTIFIER ::= { h3cevtModuleRouterType 963 } -- 2-Port 1000BASE-R-SFP+ Optical Multi-functional Interface Card
h3cevtModuleRT-MIC-X-XP4                   OBJECT IDENTIFIER ::= { h3cevtModuleRouterType 964 } -- 4-Port 1000BASE-R-SFP+ Optical Multi-functional Interface Card
h3cevtModuleRT-MIC-X-XP4W                  OBJECT IDENTIFIER ::= { h3cevtModuleRouterType 965 } -- 4-Port 1000BASE-R-SFP+ Optical Multi-functional Interface Card(Support LAN/WAN mode)

-- 1000 to 4999 for united assignment
--


--
-- reserved for other brands from 5000
--
hpevtModuleRt-SIC-EPRI                     OBJECT IDENTIFIER ::= { h3cevtModuleRouterType 5000 } -- 1-Port E1/CE1/PRI Interface Card
hpevtModuleRt-MIM-1E1-V2                   OBJECT IDENTIFIER ::= { h3cevtModuleRouterType 5001 } -- 1-Port CE1/PRI Interface Module
hpevtModuleRt-MIM-1E1-F-V2                 OBJECT IDENTIFIER ::= { h3cevtModuleRouterType 5002 } -- 1-Port E1 & Fractional E1 Interface Module
hpevtModuleRt-MIM-2E1-F-V2                 OBJECT IDENTIFIER ::= { h3cevtModuleRouterType 5003 } -- 2-Port E1 & Fractional E1 Interface Module
hpevtModuleRt-MIM-4E1-F-V2                 OBJECT IDENTIFIER ::= { h3cevtModuleRouterType 5004 } -- 4-Port E1 & Fractional E1 Interface Module
hpevtModuleRt-MIM-8E1-75                   OBJECT IDENTIFIER ::= { h3cevtModuleRouterType 5005 } -- 8-port E1/CE1/PRI Module(75ohm)
hpevtModuleRt-MIM-8E1-75-F                 OBJECT IDENTIFIER ::= { h3cevtModuleRouterType 5006 } -- 8-Port E1 Module-Fractional(75ohm)
hpevtModuleRt-MIM-8T1                      OBJECT IDENTIFIER ::= { h3cevtModuleRouterType 5007 } -- 8-Port T1 Interface Module
hpevtModuleRt-MIM-8T1-F                    OBJECT IDENTIFIER ::= { h3cevtModuleRouterType 5008 } -- 8-Port T1 Module-Fractional
hpevtModuleRt-MIM-IMA-8E1-75               OBJECT IDENTIFIER ::= { h3cevtModuleRouterType 5009 } -- 8-Port E1 ATM IMA Interface Module(75ohm)
hpevtModuleRt-FIC-2E1-V3                   OBJECT IDENTIFIER ::= { h3cevtModuleRouterType 5010 } -- 2-Port E1/CE1/PRI Interface FIC Module
hpevtModuleRt-FIC-IMA-8T1-V2               OBJECT IDENTIFIER ::= { h3cevtModuleRouterType 5011 } -- 8-Port T1 ATM IMA Interface FIC Module


-- h3cevtModuleSwitchType cards are slot-cards specific to the Switch.
h3cevtModuleSwitchType  OBJECT IDENTIFIER ::= { h3cevtModule 4 }

--h3cevtModuleNULL(0),
h3cevtModuleSw-10OR100M                    OBJECT IDENTIFIER ::= { h3cevtModuleSwitchType 1 }
h3cevtModuleSw-1000BASE-LX-SM              OBJECT IDENTIFIER ::= { h3cevtModuleSwitchType 2 }
h3cevtModuleSw-1000BASE-SX-MM              OBJECT IDENTIFIER ::= { h3cevtModuleSwitchType 3 }
h3cevtModuleSw-1000BASE-TX                 OBJECT IDENTIFIER ::= { h3cevtModuleSwitchType 4 }
h3cevtModuleSw-100M-SINGLEMODE-FX          OBJECT IDENTIFIER ::= { h3cevtModuleSwitchType 5 }
h3cevtModuleSw-100M-MULTIMODE-FX           OBJECT IDENTIFIER ::= { h3cevtModuleSwitchType 6 }
h3cevtModuleSw-100M-100BASE-TX             OBJECT IDENTIFIER ::= { h3cevtModuleSwitchType 7 }
h3cevtModuleSw-100M-HUB                    OBJECT IDENTIFIER ::= { h3cevtModuleSwitchType 8 }
h3cevtModuleSw-VDSL                        OBJECT IDENTIFIER ::= { h3cevtModuleSwitchType 9 }
h3cevtModuleSw-STACK                       OBJECT IDENTIFIER ::= { h3cevtModuleSwitchType 10 }
h3cevtModuleSw-1000BASE-ZENITH-FX          OBJECT IDENTIFIER ::= { h3cevtModuleSwitchType 11 }
h3cevtModuleSw-1000BASE-LONG-FX            OBJECT IDENTIFIER ::= { h3cevtModuleSwitchType 12 }
h3cevtModuleSw-ADSL                        OBJECT IDENTIFIER ::= { h3cevtModuleSwitchType 13 }
h3cevtModuleSw-4T10OR100-4FX100SM          OBJECT IDENTIFIER ::= { h3cevtModuleSwitchType 14 }
h3cevtModuleSw-4T10OR100-4FX100MM          OBJECT IDENTIFIER ::= { h3cevtModuleSwitchType 15 }
h3cevtModuleSw-VSPL                        OBJECT IDENTIFIER ::= { h3cevtModuleSwitchType 16 }
h3cevtModuleSw-ASPL                        OBJECT IDENTIFIER ::= { h3cevtModuleSwitchType 17 }
h3cevtModuleSw-1000M-SFP                   OBJECT IDENTIFIER ::= { h3cevtModuleSwitchType 18 }
h3cevtModuleSw-LS82O2CM                    OBJECT IDENTIFIER ::= { h3cevtModuleSwitchType 19 }
h3cevtModuleSw-LS82P2CM                    OBJECT IDENTIFIER ::= { h3cevtModuleSwitchType 20 }
h3cevtModuleSw-LS82O4GM                    OBJECT IDENTIFIER ::= { h3cevtModuleSwitchType 21 }
h3cevtModuleSw-LS82GB4C                    OBJECT IDENTIFIER ::= { h3cevtModuleSwitchType 22 }
h3cevtModuleSw-LS82GT4C                    OBJECT IDENTIFIER ::= { h3cevtModuleSwitchType 23 }
h3cevtModuleSw-LS82ST4C                    OBJECT IDENTIFIER ::= { h3cevtModuleSwitchType 24 }
h3cevtModuleSw-BOARD-LS82DSPU              OBJECT IDENTIFIER ::= { h3cevtModuleSwitchType 25 }
h3cevtModuleSw-BOARD-LS81GP8U              OBJECT IDENTIFIER ::= { h3cevtModuleSwitchType 26 }
h3cevtModuleSw-BOARD-LS82GT20              OBJECT IDENTIFIER ::= { h3cevtModuleSwitchType 27 }
h3cevtModuleSw-BOARD-LS82FE48              OBJECT IDENTIFIER ::= { h3cevtModuleSwitchType 28 }
h3cevtModuleSw-LS82T24B                    OBJECT IDENTIFIER ::= { h3cevtModuleSwitchType 29 }
h3cevtModuleSw-LSB1SRPA                    OBJECT IDENTIFIER ::= { h3cevtModuleSwitchType 30 }
h3cevtModuleSw-LSB1FT48A                   OBJECT IDENTIFIER ::= { h3cevtModuleSwitchType 31 }
h3cevtModuleSw-LSB1FT48B                   OBJECT IDENTIFIER ::= { h3cevtModuleSwitchType 32 }
h3cevtModuleSw-LSB1F48GA                   OBJECT IDENTIFIER ::= { h3cevtModuleSwitchType 33 }
h3cevtModuleSw-LSB1F48GB                   OBJECT IDENTIFIER ::= { h3cevtModuleSwitchType 34 }
h3cevtModuleSw-LSB1FP20A                   OBJECT IDENTIFIER ::= { h3cevtModuleSwitchType 35 }
h3cevtModuleSw-LSB1FP20B                   OBJECT IDENTIFIER ::= { h3cevtModuleSwitchType 36 }
h3cevtModuleSw-FT48A                       OBJECT IDENTIFIER ::= { h3cevtModuleSwitchType 37 }
h3cevtModuleSw-GP4U                        OBJECT IDENTIFIER ::= { h3cevtModuleSwitchType 38 }
h3cevtModuleSw-GP2U                        OBJECT IDENTIFIER ::= { h3cevtModuleSwitchType 39 }
h3cevtModuleSw-TGX1A                       OBJECT IDENTIFIER ::= { h3cevtModuleSwitchType 40 }
h3cevtModuleSw-1000BASE-LX-SM-IR-SC        OBJECT IDENTIFIER ::= { h3cevtModuleSwitchType 41 }
h3cevtModuleSw-1000BASE-SX-MM-SR-SC        OBJECT IDENTIFIER ::= { h3cevtModuleSwitchType 42 }
h3cevtModuleSw-1000BASE-T-RJ45             OBJECT IDENTIFIER ::= { h3cevtModuleSwitchType 43 }
h3cevtModuleSw-100BASE-FX-SM-IR-SC         OBJECT IDENTIFIER ::= { h3cevtModuleSwitchType 44 }
h3cevtModuleSw-100BASE-FX-MM-SR-SC         OBJECT IDENTIFIER ::= { h3cevtModuleSwitchType 45 }
h3cevtModuleSw-GIGA-STACK-1M-PC            OBJECT IDENTIFIER ::= { h3cevtModuleSwitchType 46 }
h3cevtModuleSw-1000BASE-LX-SM-VLR-LC       OBJECT IDENTIFIER ::= { h3cevtModuleSwitchType 47 }
h3cevtModuleSw-1000BASE-LX-SM-LR-LC        OBJECT IDENTIFIER ::= { h3cevtModuleSwitchType 48 }
h3cevtModuleSw-100BASE-FX-SM-LR-SC         OBJECT IDENTIFIER ::= { h3cevtModuleSwitchType 49 }
h3cevtModuleSw-1000BASE-X-GBIC             OBJECT IDENTIFIER ::= { h3cevtModuleSwitchType 50 }
h3cevtModuleSw-100M-SINGLEMODE-FX-LC       OBJECT IDENTIFIER ::= { h3cevtModuleSwitchType 51 }
h3cevtModuleSw-100M-MULTIMODE-FX-LC        OBJECT IDENTIFIER ::= { h3cevtModuleSwitchType 52 }
h3cevtModuleSw-1000BASE-4SFP               OBJECT IDENTIFIER ::= { h3cevtModuleSwitchType 53 }
h3cevtModuleSw-1000BASE-4GBIC              OBJECT IDENTIFIER ::= { h3cevtModuleSwitchType 54 }
h3cevtModuleSw-1000BASE-FIXED-4SFP         OBJECT IDENTIFIER ::= { h3cevtModuleSwitchType 55 }
h3cevtModuleSw-1000BASE-FIXED-4GBIC        OBJECT IDENTIFIER ::= { h3cevtModuleSwitchType 56 }
h3cevtModuleSw-LSB1GP12A                   OBJECT IDENTIFIER ::= { h3cevtModuleSwitchType 57 }
h3cevtModuleSw-LSB1GP12B                   OBJECT IDENTIFIER ::= { h3cevtModuleSwitchType 58 }
h3cevtModuleSw-LSB1TGX1A                   OBJECT IDENTIFIER ::= { h3cevtModuleSwitchType 59 }
h3cevtModuleSw-LSB1TGX1B                   OBJECT IDENTIFIER ::= { h3cevtModuleSwitchType 60 }
h3cevtModuleSw-LSB1P4G8A                   OBJECT IDENTIFIER ::= { h3cevtModuleSwitchType 61 }
h3cevtModuleSw-LSB1P4G8B                   OBJECT IDENTIFIER ::= { h3cevtModuleSwitchType 62 }
h3cevtModuleSw-LSB1A4G8A                   OBJECT IDENTIFIER ::= { h3cevtModuleSwitchType 63 }
h3cevtModuleSw-LSB1A4G8B                   OBJECT IDENTIFIER ::= { h3cevtModuleSwitchType 64 }
h3cevtModuleSw-FT48C                       OBJECT IDENTIFIER ::= { h3cevtModuleSwitchType 65 }
h3cevtModuleSw-FP20                        OBJECT IDENTIFIER ::= { h3cevtModuleSwitchType 66 }
h3cevtModuleSw-BOARD-LS81FT48              OBJECT IDENTIFIER ::= { h3cevtModuleSwitchType 67 }
h3cevtModuleSw-BOARD-LS81GB8U              OBJECT IDENTIFIER ::= { h3cevtModuleSwitchType 68 }
h3cevtModuleSw-BOARD-LS81GT8U              OBJECT IDENTIFIER ::= { h3cevtModuleSwitchType 69 }
h3cevtModuleSw-BOARD-LS81FS24              OBJECT IDENTIFIER ::= { h3cevtModuleSwitchType 70 }
h3cevtModuleSw-BOARD-LS81FM24              OBJECT IDENTIFIER ::= { h3cevtModuleSwitchType 71 }
h3cevtModuleSw-BOARD-LS82GP20              OBJECT IDENTIFIER ::= { h3cevtModuleSwitchType 72 }
h3cevtModuleSw-LSB1SRPB                    OBJECT IDENTIFIER ::= { h3cevtModuleSwitchType 73 }
h3cevtModuleSw-LSB1F32GA                   OBJECT IDENTIFIER ::= { h3cevtModuleSwitchType 74 }
h3cevtModuleSw-LSB1F32GB                   OBJECT IDENTIFIER ::= { h3cevtModuleSwitchType 75 }
h3cevtModuleSw-LSB2FT48A                   OBJECT IDENTIFIER ::= { h3cevtModuleSwitchType 76 }
h3cevtModuleSw-LSB2FT48B                   OBJECT IDENTIFIER ::= { h3cevtModuleSwitchType 77 }
h3cevtModuleSw-LSB1GT12A                   OBJECT IDENTIFIER ::= { h3cevtModuleSwitchType 78 }
h3cevtModuleSw-LSB1GT12B                   OBJECT IDENTIFIER ::= { h3cevtModuleSwitchType 79 }
h3cevtModuleSw-PC4U                        OBJECT IDENTIFIER ::= { h3cevtModuleSwitchType 80 }
h3cevtModuleSw-FT32A                       OBJECT IDENTIFIER ::= { h3cevtModuleSwitchType 81 }
h3cevtModuleSw-GT4U                        OBJECT IDENTIFIER ::= { h3cevtModuleSwitchType 82 }
h3cevtModuleSw-BOARD-LS83FP20A             OBJECT IDENTIFIER ::= { h3cevtModuleSwitchType 83 }
h3cevtModuleSw-BOARD-LS82HGMU              OBJECT IDENTIFIER ::= { h3cevtModuleSwitchType 84 }
h3cevtModuleSw-LSB1GP8TB                   OBJECT IDENTIFIER ::= { h3cevtModuleSwitchType 85 }
h3cevtModuleSw-LSB1GP8TC                   OBJECT IDENTIFIER ::= { h3cevtModuleSwitchType 86 }
h3cevtModuleSw-LSB1GT8PB                   OBJECT IDENTIFIER ::= { h3cevtModuleSwitchType 87 }
h3cevtModuleSw-LSB1GT8PC                   OBJECT IDENTIFIER ::= { h3cevtModuleSwitchType 88 }
h3cevtModuleSw-LSB1FT48C                   OBJECT IDENTIFIER ::= { h3cevtModuleSwitchType 89 }
h3cevtModuleSw-LSB1FP20C                   OBJECT IDENTIFIER ::= { h3cevtModuleSwitchType 90 }
h3cevtModuleSw-LSB1F32GC                   OBJECT IDENTIFIER ::= { h3cevtModuleSwitchType 91 }
h3cevtModuleSw-LSB1GT12C                   OBJECT IDENTIFIER ::= { h3cevtModuleSwitchType 92 }
h3cevtModuleSw-LSB1GP12C                   OBJECT IDENTIFIER ::= { h3cevtModuleSwitchType 93 }
h3cevtModuleSw-LSB1P4G8C                   OBJECT IDENTIFIER ::= { h3cevtModuleSwitchType 94 }
h3cevtModuleSw-LSB1TGX1C                   OBJECT IDENTIFIER ::= { h3cevtModuleSwitchType 95 }
h3cevtModuleSw-LSB1GT24B                   OBJECT IDENTIFIER ::= { h3cevtModuleSwitchType 96 }
h3cevtModuleSw-LSB1GT24C                   OBJECT IDENTIFIER ::= { h3cevtModuleSwitchType 97 }
h3cevtModuleSw-LSB1GP24B                   OBJECT IDENTIFIER ::= { h3cevtModuleSwitchType 98 }
h3cevtModuleSw-LSB1GP24C                   OBJECT IDENTIFIER ::= { h3cevtModuleSwitchType 99 }
h3cevtModuleSw-LSB1XP2B                    OBJECT IDENTIFIER ::= { h3cevtModuleSwitchType 100 }
h3cevtModuleSw-LSB1XP2C                    OBJECT IDENTIFIER ::= { h3cevtModuleSwitchType 101 }
h3cevtModuleSw-LSB1GV48B                   OBJECT IDENTIFIER ::= { h3cevtModuleSwitchType 102 }
h3cevtModuleSw-LSB1GV48C                   OBJECT IDENTIFIER ::= { h3cevtModuleSwitchType 103 }
h3cevtModuleSw-LSB1SRPC                    OBJECT IDENTIFIER ::= { h3cevtModuleSwitchType 104 }
h3cevtModuleSw-LSB1SRP1N0                  OBJECT IDENTIFIER ::= { h3cevtModuleSwitchType 105 }
h3cevtModuleSw-LSB1SRP1N1                  OBJECT IDENTIFIER ::= { h3cevtModuleSwitchType 106 }
h3cevtModuleSw-LSB1SRP1N2                  OBJECT IDENTIFIER ::= { h3cevtModuleSwitchType 107 }
h3cevtModuleSw-GT24                        OBJECT IDENTIFIER ::= { h3cevtModuleSwitchType 108 }
h3cevtModuleSw-GP24                        OBJECT IDENTIFIER ::= { h3cevtModuleSwitchType 109 }
h3cevtModuleSw-XP2                         OBJECT IDENTIFIER ::= { h3cevtModuleSwitchType 110 }
h3cevtModuleSw-GV48                        OBJECT IDENTIFIER ::= { h3cevtModuleSwitchType 111 }
h3cevtModuleSw-LSG1GP8U                    OBJECT IDENTIFIER ::= { h3cevtModuleSwitchType 112 }
h3cevtModuleSw-LSG1GT8U                    OBJECT IDENTIFIER ::= { h3cevtModuleSwitchType 113 }
h3cevtModuleSw-LSG1TG1U                    OBJECT IDENTIFIER ::= { h3cevtModuleSwitchType 114 }
h3cevtModuleSw-LSG1TD1U                    OBJECT IDENTIFIER ::= { h3cevtModuleSwitchType 115 }
h3cevtModuleSw-LSB2FT48C                   OBJECT IDENTIFIER ::= { h3cevtModuleSwitchType 116 } -- 48-Ports 100Base-TX Ethernet Interface module C
h3cevtModuleSw-LSB1GT48B                   OBJECT IDENTIFIER ::= { h3cevtModuleSwitchType 117 } -- 48-Ports 10/100/1000Base-T Ethernet Interface Module B
h3cevtModuleSw-LSB1GT48C                   OBJECT IDENTIFIER ::= { h3cevtModuleSwitchType 118 } -- 48-Ports 10/100/1000Base-T Ethernet Interface Module C
h3cevtModuleSw-LS81GT48                    OBJECT IDENTIFIER ::= { h3cevtModuleSwitchType 119 } -- 48 Port Gigabit Ethernet Electric Interface Unit
h3cevtModuleSw-LS81SRPG0                   OBJECT IDENTIFIER ::= { h3cevtModuleSwitchType 120 } -- Salience III, Switch and Route Processing Board
h3cevtModuleSw-LS81SRPG1                   OBJECT IDENTIFIER ::= { h3cevtModuleSwitchType 121 } -- Salience III Plus
h3cevtModuleSw-LS81SRPG2                   OBJECT IDENTIFIER ::= { h3cevtModuleSwitchType 122 } -- Salience III Lite
h3cevtModuleSw-LS81SRPG3                   OBJECT IDENTIFIER ::= { h3cevtModuleSwitchType 123 } -- Salience III Edge
--h3cevtModuleSw-LS81SRPG                  OBJECT IDENTIFIER ::= { h3cevtModuleSwitchType 124 } Switch And Route Processing Unit, Salience III. not used.
h3cevtModuleSw-SR01SRPUB                   OBJECT IDENTIFIER ::= { h3cevtModuleSwitchType 125 } -- Switching and Route Processing Unit
h3cevtModuleSw-SR01SRPUA                   OBJECT IDENTIFIER ::= { h3cevtModuleSwitchType 126 } -- Switching and Route Processing Unit
h3cevtModuleSw-SR01GP12L                   OBJECT IDENTIFIER ::= { h3cevtModuleSwitchType 127 } -- 12-Port 1000Base-X Ethernet SFP Optical Interface Line Card(L)
h3cevtModuleSw-SR01GP12W                   OBJECT IDENTIFIER ::= { h3cevtModuleSwitchType 128 } -- 12-Port 1000Base-X Ethernet SFP Optical Interface Line Card(W)
h3cevtModuleSw-SR01FT48L                   OBJECT IDENTIFIER ::= { h3cevtModuleSwitchType 129 } -- 48-Port 10/100Base-TX Ethernet RJ45 Electrical Interface Line Card (L)
h3cevtModuleSw-SR01FT48W                   OBJECT IDENTIFIER ::= { h3cevtModuleSwitchType 130 } -- 48-Port 10/100Base-TX Ethernet RJ45 Electrical Interface Line Card (W)
h3cevtModuleSw-SR01XK1W                    OBJECT IDENTIFIER ::= { h3cevtModuleSwitchType 131 } -- 1-Port 10GBase-R Ethernet XENPAK Optical Interface Line Card (W)
h3cevtModuleSw-SR01FP20W                   OBJECT IDENTIFIER ::= { h3cevtModuleSwitchType 132 } -- 20-Port 100Base-FX Ethernet SFP Optical Interface Line Card (W)
h3cevtModuleSw-SR01GT12W                   OBJECT IDENTIFIER ::= { h3cevtModuleSwitchType 133 } -- 12-Port 10/100/1000Base-T Ethernet RJ45 Electrical Interface Line Card (W)
h3cevtModuleSw-SR01F32GL                   OBJECT IDENTIFIER ::= { h3cevtModuleSwitchType 134 } -- 32-Port 10/100Base-TX Ethernet RJ45 Electrical Interface + 4-Port 1000Base-X Ethernet SFP Optical interface Line Card (L)
h3cevtModuleSw-SR01F32GW                   OBJECT IDENTIFIER ::= { h3cevtModuleSwitchType 135 } -- 32-Port 10/100Base-TX Ethernet RJ45 Electrical Interface  + 4-Port 1000Base-X  Ethernet SFP Optical interface Line Card (W)
h3cevtModuleSw-SR01GT8PL                   OBJECT IDENTIFIER ::= { h3cevtModuleSwitchType 136 } -- 8-Port 10/100/1000Base-T Ethernet RJ45 Electrical Interface + 4-Port 1000Base-X Ethernet SFP Optical Line Card (L)
h3cevtModuleSw-SR01GT8PW                   OBJECT IDENTIFIER ::= { h3cevtModuleSwitchType 137 } -- 8-Port 10/100/1000Base-T Ethernet RJ45 Electrical Interface + 4-Port 1000Base-X Ethernet SFP Optical Line Card (W)
h3cevtModuleSw-SR01P4G8W                   OBJECT IDENTIFIER ::= { h3cevtModuleSwitchType 138 } -- 4-Port 155M POS Optical Interface + 8-Port 1000Base-X Ethernet SFP Optical Interface Line Card (W)
h3cevtModuleSw-LSA1FP8U                    OBJECT IDENTIFIER ::= { h3cevtModuleSwitchType 139 } -- 8 Ports 100Base-FX Ethernet SFP Card
h3cevtModuleSw-LSB1SP4B                    OBJECT IDENTIFIER ::= { h3cevtModuleSwitchType 140 } -- 4-Port OC-48 POS SFP Optical Interface Board B
h3cevtModuleSw-LSB1SP4C                    OBJECT IDENTIFIER ::= { h3cevtModuleSwitchType 141 } -- 4-Port OC-48 POS SFP Optical Interface Board C
h3cevtModuleSw-LSB1UP1B                    OBJECT IDENTIFIER ::= { h3cevtModuleSwitchType 142 } -- 1-Port OC-192 POS XFP Optical Interface Board B
h3cevtModuleSw-LSB1UP1C                    OBJECT IDENTIFIER ::= { h3cevtModuleSwitchType 143 } -- 1-Port OC-192 POS XFP Optical Interface Board C
h3cevtModuleSw-LSB1XP4B                    OBJECT IDENTIFIER ::= { h3cevtModuleSwitchType 144 } -- 4-Port 10GBase Ethernet XFP Optical Interface Board B
h3cevtModuleSw-LSB1XP4C                    OBJECT IDENTIFIER ::= { h3cevtModuleSwitchType 145 } -- 4-Port 10GBase Ethernet XFP Optical Interface Board C
h3cevtModuleSw-SP4                         OBJECT IDENTIFIER ::= { h3cevtModuleSwitchType 146 } -- 4-Port OC-48 POS SFP Optical Interface Module
h3cevtModuleSw-UP1                         OBJECT IDENTIFIER ::= { h3cevtModuleSwitchType 147 } -- 1-Port OC-192 POS XFP Optical Interface Module
h3cevtModuleSw-XP4                         OBJECT IDENTIFIER ::= { h3cevtModuleSwitchType 148 } -- 4-Port 10GBase Ethernet XFP Optical Interface Module
h3cevtModuleSw-LS81VSNP                    OBJECT IDENTIFIER ::= { h3cevtModuleSwitchType 149 } -- VerSatile Network Processing Board
h3cevtModuleSw-LS81T12P                    OBJECT IDENTIFIER ::= { h3cevtModuleSwitchType 150 } -- 12-Port 1000Base-T Gigabit Ethernet Interface(RJ45)+4-Port 1000BASE-X  Gigabit Ethernet Optical Interface Board(SFP,LC)
h3cevtModuleSw-LS81P12T                    OBJECT IDENTIFIER ::= { h3cevtModuleSwitchType 151 } -- 12-Port 1000BASE-X Gigabit Ethernet Optical Interface(SFP,LC)+4-Port 1000BASE-T Gigabit Ethernet Interface Board(RJ45)
h3cevtModuleSw-LS81GP8UB                   OBJECT IDENTIFIER ::= { h3cevtModuleSwitchType 152 } -- 8-Port 1000M Ethernet Optical Interface Board(SFP,LC),LC Connector
h3cevtModuleSw-LS81FT48E                   OBJECT IDENTIFIER ::= { h3cevtModuleSwitchType 153 } -- 48-Port 100M Ethernet Electrical Interface Switch Unit(RJ45)
h3cevtModuleSw-LS81GP4UB                   OBJECT IDENTIFIER ::= { h3cevtModuleSwitchType 154 } -- 4-Port 1000M Ethernet Optical Interface Board(SFP,LC)
h3cevtModuleSw-LS81GT8UE                   OBJECT IDENTIFIER ::= { h3cevtModuleSwitchType 155 } -- 8-Port 1000M Ethernet Electrical Interface Switch Unit (RJ45)
h3cevtModuleSw-LS81GT48A                   OBJECT IDENTIFIER ::= { h3cevtModuleSwitchType 156 } -- 48 Port Gigabit Ethernet Electric Interface Unit
h3cevtModuleSw-LS81FP48                    OBJECT IDENTIFIER ::= { h3cevtModuleSwitchType 157 } -- 48 Port 100M Ethernet Optical Interface Board(SFP,LC)
h3cevtModuleSw-LSB1XK1B                    OBJECT IDENTIFIER ::= { h3cevtModuleSwitchType 158 } -- 1-Port 10GBase-R Ethernet XENPAK Optical Interface Board B
h3cevtModuleSw-LSB1XK1C                    OBJECT IDENTIFIER ::= { h3cevtModuleSwitchType 159 } -- 1-Port 10GBase-R Ethernet XENPAK Optical Interface Board C
h3cevtModuleSw-SR01SRPUC                   OBJECT IDENTIFIER ::= { h3cevtModuleSwitchType 160 } -- Switching and Route Processing Unit C
h3cevtModuleSw-SR01SRPUD                   OBJECT IDENTIFIER ::= { h3cevtModuleSwitchType 161 } -- Switching and Route Processing Unit D
h3cevtModuleSw-SR01SRPUE                   OBJECT IDENTIFIER ::= { h3cevtModuleSwitchType 162 } -- Switching and Route Processing Unit E
h3cevtModuleSw-LSB1SRP1N3                  OBJECT IDENTIFIER ::= { h3cevtModuleSwitchType 163 } -- Switching and Route Process Unit, Clock Module
h3cevtModuleSw-LSB1VP2B                    OBJECT IDENTIFIER ::= { h3cevtModuleSwitchType 164 } -- 2*10G Resilient Packet Ring Interface Line Card
h3cevtModuleSw-LSB1NATB                    OBJECT IDENTIFIER ::= { h3cevtModuleSwitchType 165 } -- NAT Service Processing Card (B)
h3cevtModuleSw-LSB1VPNB                    OBJECT IDENTIFIER ::= { h3cevtModuleSwitchType 166 } -- VPN Service Processing Card (B)
h3cevtModuleSw-LSGP8P                      OBJECT IDENTIFIER ::= { h3cevtModuleSwitchType 167 } -- 8-Port 1000M SFP Module
h3cevtModuleSw-LSXK1P                      OBJECT IDENTIFIER ::= { h3cevtModuleSwitchType 168 } -- 1-Port 10G Xenpak Module
h3cevtModuleSw-LSXP2P                      OBJECT IDENTIFIER ::= { h3cevtModuleSwitchType 169 } -- 2-Port 10G XFP Module
h3cevtModuleSw-LS81FT48F                   OBJECT IDENTIFIER ::= { h3cevtModuleSwitchType 170 } -- 48-Port 100M Ethernet Electrical Interface Switch Unit(RJ45)
h3cevtModuleSw-LS81PT8G                    OBJECT IDENTIFIER ::= { h3cevtModuleSwitchType 171 } -- 8 Port 1000BASE-X Gigabit Passive Optical Line Interface Board
h3cevtModuleSw-LS81PT4G                    OBJECT IDENTIFIER ::= { h3cevtModuleSwitchType 172 } -- 4 Port 1000BASE-X Gigabit Passive Optical Line Interface Board
h3cevtModuleSw-LSSTK24G                    OBJECT IDENTIFIER ::= { h3cevtModuleSwitchType 173 } -- 24G Stacking Ports Module
h3cevtModuleSw-LS82GT20A                   OBJECT IDENTIFIER ::= { h3cevtModuleSwitchType 174 } -- 20-Port 1000Base-T Gigabit Ethernet Electrical Interface Board(RJ45), BCM5697
h3cevtModuleSw-LS82GP20A                   OBJECT IDENTIFIER ::= { h3cevtModuleSwitchType 175 } -- 20-Port 1000BASE-X Gigabit Ethernet Optical Interface Board(SFP,LC), BCM5697
h3cevtModuleSw-LS81TGX1C                   OBJECT IDENTIFIER ::= { h3cevtModuleSwitchType 176 } -- 1-Port 10G Base-R Ethernet Board
h3cevtModuleSw-VP2                         OBJECT IDENTIFIER ::= { h3cevtModuleSwitchType 177 } -- 2*10G Resilient Packet Ring Interface Module
h3cevtModuleSw-LSA1FB8U                    OBJECT IDENTIFIER ::= { h3cevtModuleSwitchType 178 } -- 8-Port 100Base-Fx BIDI Ethernet Board
h3cevtModuleSw-LS81T12PE                   OBJECT IDENTIFIER ::= { h3cevtModuleSwitchType 179 } -- 12-Port 1000Base-T GE Interface+4-Port 1000BASE-X GE Optical Interface Board(SFP,LC)
h3cevtModuleSw-LS81P12TE                   OBJECT IDENTIFIER ::= { h3cevtModuleSwitchType 180 } -- 12-Port 1000BASE-X GE Optical Interface(SFP,LC)+4-Port 1000 BASE-T GE Interface Board(RJ45)
h3cevtModuleSw-LSB1SRP2N0                  OBJECT IDENTIFIER ::= { h3cevtModuleSwitchType 181 } -- Switching and Route Process Unit,12*LPU
h3cevtModuleSw-LSB1SRP2N3                  OBJECT IDENTIFIER ::= { h3cevtModuleSwitchType 182 } -- Switching and Route Process Unit, Clock Module
h3cevtModuleSw-LSB1GV48DB                  OBJECT IDENTIFIER ::= { h3cevtModuleSwitchType 183 } -- 48 Ports 1000Base-T Ethernet Interface Line Card with POE(DB)
h3cevtModuleSw-LSB1FW8B                    OBJECT IDENTIFIER ::= { h3cevtModuleSwitchType 184 } -- Firewall Service Processing Board with 8GE (B)
h3cevtModuleSw-LSB1IPSEC8B                 OBJECT IDENTIFIER ::= { h3cevtModuleSwitchType 185 } -- VPN Service Processing Board with 8GE (B)
h3cevtModuleSw-LSB1IDSB                    OBJECT IDENTIFIER ::= { h3cevtModuleSwitchType 186 } -- IDS Service Processing Board (B)
h3cevtModuleSw-LSB1IPSB                    OBJECT IDENTIFIER ::= { h3cevtModuleSwitchType 187 } -- IPS Service Processing Board (B)
h3cevtModuleSw-LSB2FT48CA                  OBJECT IDENTIFIER ::= { h3cevtModuleSwitchType 188 } -- 48 Ports 100Base-TX Ethernet Line Card (CA)
h3cevtModuleSw-LSB1FP20CA                  OBJECT IDENTIFIER ::= { h3cevtModuleSwitchType 189 } -- 20 Ports 100Base-FX Ethernet Interface Service Card (CA)
h3cevtModuleSw-LSB1F32GCA                  OBJECT IDENTIFIER ::= { h3cevtModuleSwitchType 190 } -- 32 Ports FE and 4 Ports GE Line Card(CA)
h3cevtModuleSw-LSB1P4G8CA                  OBJECT IDENTIFIER ::= { h3cevtModuleSwitchType 191 } -- 4 Ports OC-3c POS and 8 Ports GE Line Card(CA)
h3cevtModuleSw-LSB1GT12CA                  OBJECT IDENTIFIER ::= { h3cevtModuleSwitchType 192 } -- 12 Ports 1000Base-T Ethernet Interface Line Card(CA)
h3cevtModuleSw-LSB1GT24CA                  OBJECT IDENTIFIER ::= { h3cevtModuleSwitchType 193 } -- 24 Ports 1000Base-T Ethernet Interface Line Card(CA)
h3cevtModuleSw-LSB1GP12CA                  OBJECT IDENTIFIER ::= { h3cevtModuleSwitchType 194 } -- 12 Ports 1000Base Ethernet Optical Interface Service Card(CA)
h3cevtModuleSw-LSB1GP24CA                  OBJECT IDENTIFIER ::= { h3cevtModuleSwitchType 195 } -- 24 Ports 1000Base-X Ethernet Interface Line Card (CA)
h3cevtModuleSw-LSB1GT8PCA                  OBJECT IDENTIFIER ::= { h3cevtModuleSwitchType 196 } -- 8 Ports 1000Base-T Ethernet Interface & 4 Ports 1000Base-X Ethernet SFP Interface Line Card(CA)
h3cevtModuleSw-LSB1XP2CA                   OBJECT IDENTIFIER ::= { h3cevtModuleSwitchType 197 } -- 2-Port 10GBase-R/W Ethernet XFP Optical Interface Card(CA)
h3cevtModuleSw-LSB1XK1CA                   OBJECT IDENTIFIER ::= { h3cevtModuleSwitchType 198 } -- 10GBase-R Ethernet XENPAK Optical Interface Line Card(CA)
h3cevtModuleSw-LSB1XP4CA                   OBJECT IDENTIFIER ::= { h3cevtModuleSwitchType 199 } -- 4-Port 10GBase-R/X Ethernet Optical Interface Line Card(CA)
h3cevtModuleSw-LSB1UP1CA                   OBJECT IDENTIFIER ::= { h3cevtModuleSwitchType 200 } -- Single Port OC-192c POS XFP Optical Interface Card(CA)
h3cevtModuleSw-LSB1SP4CA                   OBJECT IDENTIFIER ::= { h3cevtModuleSwitchType 201 } -- 4-Port OC-48c POS SFP Optical Interface Card(CA)
h3cevtModuleSw-LSB1VP2CA                   OBJECT IDENTIFIER ::= { h3cevtModuleSwitchType 202 } -- 2*10G RPR Process Unit(CA)
h3cevtModuleSw-SR01FT48WA                  OBJECT IDENTIFIER ::= { h3cevtModuleSwitchType 203 } -- 48 Ports 100Base-TX Ethernet Line Card (WA)
h3cevtModuleSw-SR01FP20WA                  OBJECT IDENTIFIER ::= { h3cevtModuleSwitchType 204 } -- 20 Ports 100Base-FX Ethernet Interface Service Card (WA)
h3cevtModuleSw-SR01F32GWA                  OBJECT IDENTIFIER ::= { h3cevtModuleSwitchType 205 } -- 32 Ports FE and 4 Ports GE Line Card(WA)
h3cevtModuleSw-SR01P4G8WA                  OBJECT IDENTIFIER ::= { h3cevtModuleSwitchType 206 } -- 4 Ports OC-3c POS and 8 Ports GE Line Card(WA)
h3cevtModuleSw-SR01GT12WA                  OBJECT IDENTIFIER ::= { h3cevtModuleSwitchType 207 } -- 12 Ports 1000Base-T Ethernet Interface Line Card(WA)
h3cevtModuleSw-SR01GT24WA                  OBJECT IDENTIFIER ::= { h3cevtModuleSwitchType 208 } -- 24 Ports 1000Base-T Ethernet Interface Line Card(WA)
h3cevtModuleSw-SR01GP12WA                  OBJECT IDENTIFIER ::= { h3cevtModuleSwitchType 209 } -- 12 Ports 1000Base Ethernet Optical Interface Service Card(WA)
h3cevtModuleSw-SR01GP24WA                  OBJECT IDENTIFIER ::= { h3cevtModuleSwitchType 210 } -- 24 Ports 1000Base-X Ethernet Interface Line Card (WA)
h3cevtModuleSw-SR01GT8PWA                  OBJECT IDENTIFIER ::= { h3cevtModuleSwitchType 211 } -- 8 Ports 1000Base-T Ethernet Interface & 4 Ports 1000Base-X Ethernet SFP Interface Line Card(WA)
h3cevtModuleSw-SR01XP2WA                   OBJECT IDENTIFIER ::= { h3cevtModuleSwitchType 212 } -- 2-Port 10GBase-R/W Ethernet XFP Optical Interface Card(WA)
h3cevtModuleSw-SR01XK1WA                   OBJECT IDENTIFIER ::= { h3cevtModuleSwitchType 213 } -- 10GBase-R Ethernet XENPAK Optical Interface Line Card(WA)
h3cevtModuleSw-SR01UP1WA                   OBJECT IDENTIFIER ::= { h3cevtModuleSwitchType 214 } -- Single Port OC-192c POS XFP Optical Interface Card(WA)
h3cevtModuleSw-SR01SP4WA                   OBJECT IDENTIFIER ::= { h3cevtModuleSwitchType 215 } -- 4-Port OC-48c POS SFP Optical Interface Card(WA)
h3cevtModuleSw-GP8U                        OBJECT IDENTIFIER ::= { h3cevtModuleSwitchType 216 } -- 8-Port 1000Base-X SFP Optical Interface Module
h3cevtModuleSw-LSEXP1P                     OBJECT IDENTIFIER ::= { h3cevtModuleSwitchType 217 } -- Single 10G SFP Optical Interface Module
h3cevtModuleSw-LSEXK1P                     OBJECT IDENTIFIER ::= { h3cevtModuleSwitchType 218 } -- Single 10G XENPAK Interface Module
h3cevtModuleSw-LSEXS1P                     OBJECT IDENTIFIER ::= { h3cevtModuleSwitchType 219 } -- Single 10G STACK Interface Module
h3cevtModuleSw-LS81GP48                    OBJECT IDENTIFIER ::= { h3cevtModuleSwitchType 220 } -- 48-Port 1000M Ethernet Optical Interface Board(SFP,LC),LC Connector
h3cevtModuleSw-LS81GT48B                   OBJECT IDENTIFIER ::= { h3cevtModuleSwitchType 221 } -- 48-Port 1000Base-T Gigabit Ethernet Interface Board(RJ45)
h3cevtModuleSw-LS81T16P                    OBJECT IDENTIFIER ::= { h3cevtModuleSwitchType 222 } -- 16-Port 1000Base-T Gigabit Ethernet Interface(RJ45) + 8-Port 1000BASE-X Gigabit Ethernet Optical Interface Board(SFP,LC)
h3cevtModuleSw-LS81T32P                    OBJECT IDENTIFIER ::= { h3cevtModuleSwitchType 223 } -- 32-Port 1000Base-T Gigabit Ethernet Interface(RJ45) + 16-Port 1000BASE-X Gigabit Ethernet Optical Interface Board(SFP,LC)
h3cevtModuleSw-LS81TGX2                    OBJECT IDENTIFIER ::= { h3cevtModuleSwitchType 224 } -- 2-Port 10GBASE Ethernet Interface Board(XFP,LC)
h3cevtModuleSw-LS81TGX4                    OBJECT IDENTIFIER ::= { h3cevtModuleSwitchType 225 } -- 4-Port 10GBASE Ethernet Interface Module(XFP,LC),XG
h3cevtModuleSw-LSB1GV48DA                  OBJECT IDENTIFIER ::= { h3cevtModuleSwitchType 226 } -- 48 Ports 1000Base-T Ethernet Interface Line Card with POE(DA)
h3cevtModuleSw-SR01GV48VB                  OBJECT IDENTIFIER ::= { h3cevtModuleSwitchType 227 } -- 48 Ports 1000Base-T Ethernet Interface Line Card with POE(VB)
h3cevtModuleSw-LSB1GT24DB                  OBJECT IDENTIFIER ::= { h3cevtModuleSwitchType 228 } -- 24 Ports 1000Base-T Ethernet Interface Line Card(DB)
h3cevtModuleSw-LSB1GP24DB                  OBJECT IDENTIFIER ::= { h3cevtModuleSwitchType 229 } -- 24 Ports 1000Base-X Ethernet Interface Line Card(DB)
h3cevtModuleSw-LSB1GP24DC                  OBJECT IDENTIFIER ::= { h3cevtModuleSwitchType 230 } -- 24 Ports 1000Base-X Ethernet Interface Line Card(DC)
h3cevtModuleSw-LSB1FW8DB                   OBJECT IDENTIFIER ::= { h3cevtModuleSwitchType 231 } -- 8-port 1000BASE-X (SFP) Firewall Service Card(DB)
h3cevtModuleSw-LSB1IPSEC8DB                OBJECT IDENTIFIER ::= { h3cevtModuleSwitchType 232 } -- 8-port 1000BASE-X (SFP) IPSEC Service Card(DB)
h3cevtModuleSw-SR01GT24VB                  OBJECT IDENTIFIER ::= { h3cevtModuleSwitchType 233 } -- 24 Ports 1000Base-T Ethernet Interface Line Card(VB)
h3cevtModuleSw-SR01GP24VC                  OBJECT IDENTIFIER ::= { h3cevtModuleSwitchType 234 } -- 24 Ports 1000Base-X Ethernet Interface Line Card(VC)
h3cevtModuleSw-SR01VP2WA                   OBJECT IDENTIFIER ::= { h3cevtModuleSwitchType 235 } -- 2*10G RPR Process Unit(WA)
h3cevtModuleSw-SR01FW8VB                   OBJECT IDENTIFIER ::= { h3cevtModuleSwitchType 236 } -- 8-port 1000BASE-X (SFP) Firewall Service Card(VB)
h3cevtModuleSw-SR01IPSEC8VB                OBJECT IDENTIFIER ::= { h3cevtModuleSwitchType 237 } -- 8-port 1000BASE-X (SFP) IPSEC Service Card(VB)
h3cevtModuleSw-SR01NATL                    OBJECT IDENTIFIER ::= { h3cevtModuleSwitchType 238 } -- NAT Service Processing Card (L)
h3cevtModuleSw-SR01VPNL                    OBJECT IDENTIFIER ::= { h3cevtModuleSwitchType 239 } -- VPN Service Processing Card (L)
h3cevtModuleSw-LSB1GP24CB                  OBJECT IDENTIFIER ::= { h3cevtModuleSwitchType 240 } -- 24 Ports 1000Base-X Ethernet Interface Line Card(CB)
h3cevtModuleSw-LSB1GP48DB                  OBJECT IDENTIFIER ::= { h3cevtModuleSwitchType 241 } -- 48-Port Gigabit Ethernet Optical Interface Line Card(DB)
h3cevtModuleSw-LSB1XP2CB                   OBJECT IDENTIFIER ::= { h3cevtModuleSwitchType 242 } -- 2-Port 10Gigabit Ethernet Optical Interface Card(CB)
h3cevtModuleSw-XP4L                        OBJECT IDENTIFIER ::= { h3cevtModuleSwitchType 243 } -- 4 Port 1000BASE Optic Interface Module (XFP)
h3cevtModuleSw-LSB1XP4LDB                  OBJECT IDENTIFIER ::= { h3cevtModuleSwitchType 244 } -- 4-Port 10GBase-R/W Ethernet XFP Optical Interface Line Speed Card(DB)
h3cevtModuleSw-LSB1XP4LDC                  OBJECT IDENTIFIER ::= { h3cevtModuleSwitchType 245 } -- 4-Port 10GBase-R/W Ethernet XFP Optical Interface Line Speed Card(DC)
h3cevtModuleSw-AHP4                        OBJECT IDENTIFIER ::= { h3cevtModuleSwitchType 246 } -- 2-Port OC-3 ATM and 2-Port OC-3/12 ATM Interface Module (SFP)
h3cevtModuleSw-LSB1AHP4GCA                 OBJECT IDENTIFIER ::= { h3cevtModuleSwitchType 247 } -- 2-Port OC-3 ATM and 2-Port OC-3/12 ATM and 8-Port 1000Base-X Ethernet Optical Interface Line Card(CA)
h3cevtModuleSw-CLP4                        OBJECT IDENTIFIER ::= { h3cevtModuleSwitchType 248 } -- 4 Ports OC-3/STM-1 CPOS Optical Interface Module (SFP)
h3cevtModuleSw-LSB1CLP4GCA                 OBJECT IDENTIFIER ::= { h3cevtModuleSwitchType 249 } -- 4 Ports OC-3/STM-1 CPOS Optical Interface and 4-Port 1000Base-X Ethernet Optical Interface Line Card(CA)
h3cevtModuleSw-ET32                        OBJECT IDENTIFIER ::= { h3cevtModuleSwitchType 250 } -- 32-Port Channelized E1/T1 Interface Module
h3cevtModuleSw-LSB1ET32GCA                 OBJECT IDENTIFIER ::= { h3cevtModuleSwitchType 251 } -- 32-Port Channelized E1/T1 Interface and 4-Port 1000Base-X Ethernet Optical Interface Line Card(CA)
h3cevtModuleSw-LSB1IDSDB                   OBJECT IDENTIFIER ::= { h3cevtModuleSwitchType 252 } -- Intrusion Detection Service Card(DB)
h3cevtModuleSw-LSB1SRP2N1                  OBJECT IDENTIFIER ::= { h3cevtModuleSwitchType 253 } -- Switching and Route Processing Board,8*LPU
h3cevtModuleSw-BOARD-LS82SRPB              OBJECT IDENTIFIER ::= { h3cevtModuleSwitchType 254 }
h3cevtModuleSw-BORAD-LS83SRPC              OBJECT IDENTIFIER ::= { h3cevtModuleSwitchType 255 }
h3cevtModuleSw-Main                        OBJECT IDENTIFIER ::= { h3cevtModuleSwitchType 256 }
h3cevtModuleSw-LSB1SRP2N2                  OBJECT IDENTIFIER ::= { h3cevtModuleSwitchType 257 } -- Switching and Route Processing Board,5*LPU
h3cevtModuleSw-LSB1NAMB                    OBJECT IDENTIFIER ::= { h3cevtModuleSwitchType 258 } -- NAM Service Processing Card (B)
h3cevtModuleSw-RSP2                        OBJECT IDENTIFIER ::= { h3cevtModuleSwitchType 259 } -- 2*2.5G Resilient Packet Ring Interface
h3cevtModuleSw-LSB1RSP2CA                  OBJECT IDENTIFIER ::= { h3cevtModuleSwitchType 260 } -- 2*2.5G Resilient Packet Ring Interface Line Card(CA)
h3cevtModuleSw-SR01XP4LVC                  OBJECT IDENTIFIER ::= { h3cevtModuleSwitchType 261 } -- 4-Port 10GBase-R/W Ethernet XFP Optical Interface Line Speed Card(VC)
h3cevtModuleSw-SR01AHP4GWA                 OBJECT IDENTIFIER ::= { h3cevtModuleSwitchType 262 } -- 2-Port OC-3 ATM and 2-Port OC-3/12 ATM and 8-Port 1000Base-X Ethernet Optical Interface Line Card(WA)
h3cevtModuleSw-SR01CLP4GWA                 OBJECT IDENTIFIER ::= { h3cevtModuleSwitchType 263 } -- 4 Ports OC-3/STM-1 CPOS Optical Interface and 4-Port 1000Base-X Ethernet Optical Interface Line Card(WA)
h3cevtModuleSw-SR01ET32GWA                 OBJECT IDENTIFIER ::= { h3cevtModuleSwitchType 264 } -- 32-Port Channelized E1/T1 Interface and 4-Port 1000Base-X Ethernet Optical Interface Line Card(WA)
h3cevtModuleSw-SR01IDSVB                   OBJECT IDENTIFIER ::= { h3cevtModuleSwitchType 265 } -- Intrusion Detection Service Card(VB)
h3cevtModuleSw-SR01SRPUF                   OBJECT IDENTIFIER ::= { h3cevtModuleSwitchType 266 } -- Switching and Route Processing Board,12*LPU
h3cevtModuleSw-SR01NAML                    OBJECT IDENTIFIER ::= { h3cevtModuleSwitchType 267 } -- NAM Service Processing Card (L)
h3cevtModuleSw-SR01RSP2WA                  OBJECT IDENTIFIER ::= { h3cevtModuleSwitchType 268 } -- 2*2.5G Resilient Packet Ring Interface Line Card(WA)
h3cevtModuleSw-LSPM1XP1P                   OBJECT IDENTIFIER ::= { h3cevtModuleSwitchType 269 } -- 1-Port 10G XFP Module
h3cevtModuleSw-LSPM1XP2P                   OBJECT IDENTIFIER ::= { h3cevtModuleSwitchType 270 } -- 2-Port 10G XFP Module
h3cevtModuleSw-LSPM1CX2P                   OBJECT IDENTIFIER ::= { h3cevtModuleSwitchType 271 } -- 2-Port 10G CX4 Module
h3cevtModuleSw-STK-1000BASE-T              OBJECT IDENTIFIER ::= { h3cevtModuleSwitchType 272 } -- Single Port 1000BASE-T Stack Ethernet Interface Card

--
-- 273 to 299 reserved for other product
--


--
-- 300 to 499 reserved for advanced switches part I
--
h3cevtModuleSw-LSB1SRP1M0                  OBJECT IDENTIFIER ::= { h3cevtModuleSwitchType 300 } -- Switching and Route Process Unit,2*LPU or 3*LPU
h3cevtModuleSw-LSB1SRP1M1                  OBJECT IDENTIFIER ::= { h3cevtModuleSwitchType 301 } -- Switching and Route Process Unit
h3cevtModuleSw-LSB1GP12DB                  OBJECT IDENTIFIER ::= { h3cevtModuleSwitchType 302 } -- 12 Ports 1000Base Ethernet Optical Interface Service Card(DB)
h3cevtModuleSw-LSB1GT12DB                  OBJECT IDENTIFIER ::= { h3cevtModuleSwitchType 303 } -- 12 Ports 1000Base-T Ethernet Interface Line Card(DB)
h3cevtModuleSw-LSB1XK1DB                   OBJECT IDENTIFIER ::= { h3cevtModuleSwitchType 304 } -- 10GBase-R Ethernet XENPAK Optical Interface Line Card(DB)
h3cevtModuleSw-LSB1XP2DB                   OBJECT IDENTIFIER ::= { h3cevtModuleSwitchType 305 } -- 2-Port 10GBase-R/W Ethernet XFP Optical Interface Card(DB)
h3cevtModuleSw-LSB1XP2DC                   OBJECT IDENTIFIER ::= { h3cevtModuleSwitchType 306 } -- 2-Port 10GBase-R/W Ethernet XFP Optical Interface Card(DC)
h3cevtModuleSw-LSB1GT48LDB                 OBJECT IDENTIFIER ::= { h3cevtModuleSwitchType 307 } -- 48-Port Gigabit Ethernet RJ45 Electrical Interface Card (DB)
h3cevtModuleSw-LSB1XP4TDB                  OBJECT IDENTIFIER ::= { h3cevtModuleSwitchType 308 } -- 4-Port 10GBase-R/W Ethernet XFP Optical Interface Line Speed Test Card(DB)
h3cevtModuleSw-LSB1XP4TDC                  OBJECT IDENTIFIER ::= { h3cevtModuleSwitchType 309 } -- 4-Port 10GBase-R/W Ethernet XFP Optical Interface Line Speed Test Card(DC)
h3cevtModuleSw-LSB1RSP2DC                  OBJECT IDENTIFIER ::= { h3cevtModuleSwitchType 310 } -- 2*2.5G Resilient Packet Ring Interface Line Card(DC)
h3cevtModuleSw-LSB1VP2DC                   OBJECT IDENTIFIER ::= { h3cevtModuleSwitchType 311 } -- 2*10G Resilient Packet Ring Process Unit(DC)
h3cevtModuleSw-LSB1XP4DB                   OBJECT IDENTIFIER ::= { h3cevtModuleSwitchType 312 } -- 4-Port 10GBase-R/X Ethernet Optical Interface Line Card(DB)
h3cevtModuleSw-LSB1SRP2E0                  OBJECT IDENTIFIER ::= { h3cevtModuleSwitchType 313 } -- Switching and Route Process Unit,12*LPU
h3cevtModuleSw-LSB1SRP2E1                  OBJECT IDENTIFIER ::= { h3cevtModuleSwitchType 314 } -- Switching and Route Process Unit,8*LPU
h3cevtModuleSw-LSB1SRP2E2                  OBJECT IDENTIFIER ::= { h3cevtModuleSwitchType 315 } -- Switching and Route Process Unit,5*LPU
h3cevtModuleSw-LSB1SRP2E3                  OBJECT IDENTIFIER ::= { h3cevtModuleSwitchType 316 } -- Switching and Route Process Unit, Clock module
h3cevtModuleSw-SR01SRPUQ                   OBJECT IDENTIFIER ::= { h3cevtModuleSwitchType 317 } -- Switching and Route Processing Unit Q
h3cevtModuleSw-AHP1                        OBJECT IDENTIFIER ::= { h3cevtModuleSwitchType 318 } -- 1-Port OC-12c(3c)/STM-4(1) ATM Optical Interface Module(SFP)
h3cevtModuleSw-AHP2                        OBJECT IDENTIFIER ::= { h3cevtModuleSwitchType 319 } -- 2-Port OC-12c(3c)/STM-4(1) ATM Optical Interface Module(SFP)
h3cevtModuleSw-CLP1                        OBJECT IDENTIFIER ::= { h3cevtModuleSwitchType 320 } -- 1-Port OC-3/STM-1 CPOS Optical Interface Module(SFP)
h3cevtModuleSw-CLP2                        OBJECT IDENTIFIER ::= { h3cevtModuleSwitchType 321 } -- 2-Port OC-3/STM-1 CPOS Optical Interface Module(SFP)
h3cevtModuleSw-ET16                        OBJECT IDENTIFIER ::= { h3cevtModuleSwitchType 322 } -- 16-Port Channelized E1/T1 Interface Module
h3cevtModuleSw-LSB1SRP1NA0                 OBJECT IDENTIFIER ::= { h3cevtModuleSwitchType 323 } -- Switching and Route Process Unit,12*LPU
h3cevtModuleSw-LSB1SRP1NA1                 OBJECT IDENTIFIER ::= { h3cevtModuleSwitchType 324 } -- Switching and Route Process Unit,8*LPU
h3cevtModuleSw-LSB1SRP1NA2                 OBJECT IDENTIFIER ::= { h3cevtModuleSwitchType 325 } -- Switching and Route Process Unit,5*LPU
h3cevtModuleSw-LSB1SRP1NA3                 OBJECT IDENTIFIER ::= { h3cevtModuleSwitchType 326 } -- Switching and Route Process Unit, Clock module
h3cevtModuleSw-SR01AHP1GWA                 OBJECT IDENTIFIER ::= { h3cevtModuleSwitchType 327 } -- 1-Port OC-12c(3c)/STM-4(1) ATM Optical Interface and 4-Port 1000Base-X Ethernet Optical Interface Line Card(WA)
h3cevtModuleSw-SR01AHP2GWA                 OBJECT IDENTIFIER ::= { h3cevtModuleSwitchType 328 } -- 2-Port OC-12c(3c)/STM-4(1) ATM Optical Interface and 4-Port 1000Base-X Ethernet Optical Interface Line Card(WA)
h3cevtModuleSw-SR01CLP1GWA                 OBJECT IDENTIFIER ::= { h3cevtModuleSwitchType 329 } -- 1-Port OC-3/STM-1 CPOS Optical Interface and 4-Port 1000Base-X Ethernet Optical Interface Line Card(WA)
h3cevtModuleSw-SR01CLP2GWA                 OBJECT IDENTIFIER ::= { h3cevtModuleSwitchType 330 } -- 2-Port OC-3/STM-1 CPOS Optical Interface and 4-Port 1000Base-X Ethernet Optical Interface Line Card(WA)
h3cevtModuleSw-SR01ET16GWA                 OBJECT IDENTIFIER ::= { h3cevtModuleSwitchType 331 } -- 16-Port Channelized E1/T1 Interface and  4-Port 1000Base-X Ethernet Optical Interface Line Card(WA)
h3cevtModuleSw-SR01GP12VB                  OBJECT IDENTIFIER ::= { h3cevtModuleSwitchType 332 } -- 12-Port Gigabit Ethernet Optical Interface Card(VB)
h3cevtModuleSw-SR01XK1VB                   OBJECT IDENTIFIER ::= { h3cevtModuleSwitchType 333 } -- 1-Port 10Gigabit Ethernet Optical Interface Card(VB)
h3cevtModuleSw-SR01XP2VC                   OBJECT IDENTIFIER ::= { h3cevtModuleSwitchType 334 } -- 2-Port 10GBase-RW Ethernet XFP Optical Interface Line Card(VC)
h3cevtModuleSw-SR01XP4LVB                  OBJECT IDENTIFIER ::= { h3cevtModuleSwitchType 335 } -- 4-Port 10GBase-R/W Ethernet XFP Optical Interface Line Speed Card(VB)
h3cevtModuleSw-SR01SRPUEA                  OBJECT IDENTIFIER ::= { h3cevtModuleSwitchType 336 } -- Switching and Route Process Unit, Clock Module
h3cevtModuleSw-LSB1SRP1N4                  OBJECT IDENTIFIER ::= { h3cevtModuleSwitchType 337 } -- Switching and Route Process Unit, 12*LPU
h3cevtModuleSw-LSB1SRP1N5                  OBJECT IDENTIFIER ::= { h3cevtModuleSwitchType 338 } -- Switching and Route Process Unit, 8*LPU
h3cevtModuleSw-LSB1SRP1N6                  OBJECT IDENTIFIER ::= { h3cevtModuleSwitchType 339 } -- Switching and Route Process Unit, 5*LPU
h3cevtModuleSw-LSB1SRP1N7                  OBJECT IDENTIFIER ::= { h3cevtModuleSwitchType 340 } -- Switching and Route Process Unit, Clock Module
h3cevtModuleSw-LSB1SRP2N4                  OBJECT IDENTIFIER ::= { h3cevtModuleSwitchType 341 } -- Switching and Route Process Unit, 12*LPU
h3cevtModuleSw-LSB1SRP2N5                  OBJECT IDENTIFIER ::= { h3cevtModuleSwitchType 342 } -- Switching and Route Process Unit, 8*LPU
h3cevtModuleSw-LSB1SRP2N6                  OBJECT IDENTIFIER ::= { h3cevtModuleSwitchType 343 } -- Switching and Route Process Unit, 5*LPU
h3cevtModuleSw-LSB1SRP2N7                  OBJECT IDENTIFIER ::= { h3cevtModuleSwitchType 344 } -- Switching and Route Process Unit, Clock Module
h3cevtModuleSw-LSB1SRP1NA4                 OBJECT IDENTIFIER ::= { h3cevtModuleSwitchType 345 } -- Switching and Route Process Unit, 12*LPU
h3cevtModuleSw-LSB1SRP1NA5                 OBJECT IDENTIFIER ::= { h3cevtModuleSwitchType 346 } -- Switching and Route Process Unit, 8*LPU
h3cevtModuleSw-LSB1SRP1NA6                 OBJECT IDENTIFIER ::= { h3cevtModuleSwitchType 347 } -- Switching and Route Process Unit, 5*LPU
h3cevtModuleSw-LSB1SRP1NA7                 OBJECT IDENTIFIER ::= { h3cevtModuleSwitchType 348 } -- Switching and Route Process Unit, Clock Module
h3cevtModuleSw-LSB2GV48DA                  OBJECT IDENTIFIER ::= { h3cevtModuleSwitchType 349 } -- 48-Ports 1000Base-T Ethernet Interface Line Card with POE(DA)
h3cevtModuleSw-LSB1RGP2GDB                 OBJECT IDENTIFIER ::= { h3cevtModuleSwitchType 350 } -- 2-Port GE RPR and 8-Port GE Optical Interface Service Card(DB)
h3cevtModuleSw-LSB1RGP4GDB                 OBJECT IDENTIFIER ::= { h3cevtModuleSwitchType 351 } -- 4-Port GE RPR and 8-Port GE Optical Interface Service Card(DB)
h3cevtModuleSw-LSB2GP24DB                  OBJECT IDENTIFIER ::= { h3cevtModuleSwitchType 352 } -- 24-Port 1000BASE-X  Interface Module(DB),(SFP,LC)
h3cevtModuleSw-LSB2GP24DC                  OBJECT IDENTIFIER ::= { h3cevtModuleSwitchType 353 } -- 24-Port 1000BASE-X  Interface Module(DC),(SFP,LC)
h3cevtModuleSw-LSB2GT24DB                  OBJECT IDENTIFIER ::= { h3cevtModuleSwitchType 354 } -- 24-Port 10/100/1000BASE-T Interface Module(DB),(RJ45)
h3cevtModuleSw-LSB2FW8DB                   OBJECT IDENTIFIER ::= { h3cevtModuleSwitchType 355 } -- 8-Port 1000BASE-X Interface Firewall Service Module(DB),(SFP,LC)
h3cevtModuleSw-LSB2IPSEC8DB                OBJECT IDENTIFIER ::= { h3cevtModuleSwitchType 356 } -- 8-Port 1000BASE-X Interface IPSEC Service Module(DB),(SFP,LC)
h3cevtModuleSw-LSB2GV48DB                  OBJECT IDENTIFIER ::= { h3cevtModuleSwitchType 357 } -- 48-Port 10/100/1000BASE-T Interface Module(DB),(PoE,RJ45)
h3cevtModuleSw-RGP2                        OBJECT IDENTIFIER ::= { h3cevtModuleSwitchType 358 } -- 2-Port GE Resilient Packet Ring Interface Module
h3cevtModuleSw-RGP4                        OBJECT IDENTIFIER ::= { h3cevtModuleSwitchType 359 } -- 4-Port GE Resilient Packet Ring Interface Module
h3cevtModuleSw-SR02FW8VB                   OBJECT IDENTIFIER ::= { h3cevtModuleSwitchType 360 } -- 8-Port 1000BASE-X Interface Firewall Service Module(VB),(SFP,LC)
h3cevtModuleSw-SR02IPSEC8VB                OBJECT IDENTIFIER ::= { h3cevtModuleSwitchType 361 } -- 8-Port 1000BASE-X Interface IPSEC Service Module(VB),(SFP,LC)
h3cevtModuleSw-LSB2SRP1N0                  OBJECT IDENTIFIER ::= { h3cevtModuleSwitchType 362 } -- Switching and Route Process Unit, 12*LPU
h3cevtModuleSw-LSB2SRP1N1                  OBJECT IDENTIFIER ::= { h3cevtModuleSwitchType 363 } -- Switching and Route Process Unit, 8*LPU
h3cevtModuleSw-LSB2SRP1N2                  OBJECT IDENTIFIER ::= { h3cevtModuleSwitchType 364 } -- Switching and Route Process Unit, 5*LPU
h3cevtModuleSw-LSB2SRP1N3                  OBJECT IDENTIFIER ::= { h3cevtModuleSwitchType 365 } -- Switching and Route Process Unit, Clock module
h3cevtModuleSw-LSB2SRP1N4                  OBJECT IDENTIFIER ::= { h3cevtModuleSwitchType 366 } -- Switching and Route Process Unit, 12*LPU
h3cevtModuleSw-LSB2SRP1N5                  OBJECT IDENTIFIER ::= { h3cevtModuleSwitchType 367 } -- Switching and Route Process Unit, 8*LPU
h3cevtModuleSw-LSB2SRP1N6                  OBJECT IDENTIFIER ::= { h3cevtModuleSwitchType 368 } -- Switching and Route Process Unit, 5*LPU
h3cevtModuleSw-LSB2SRP1N7                  OBJECT IDENTIFIER ::= { h3cevtModuleSwitchType 369 } -- Switching and Route Process Unit, Clock module
h3cevtModuleSw-SR02SRPUE                   OBJECT IDENTIFIER ::= { h3cevtModuleSwitchType 370 } -- Switching and Route Process Unit, Clock module
h3cevtModuleSw-SR01LN1BQH0                 OBJECT IDENTIFIER ::= { h3cevtModuleSwitchType 371 } -- Single XG Service Board(BQH)
h3cevtModuleSw-SR01DXP1L                   OBJECT IDENTIFIER ::= { h3cevtModuleSwitchType 372 } -- 1-Port 10GBASE-R/W Ethernet Optical Interface Card,(XFP,LC)
h3cevtModuleSw-SR01DGP10L                  OBJECT IDENTIFIER ::= { h3cevtModuleSwitchType 373 } -- 10-Port 1000BASE-X Optical Interface Card,(SFP,LC)
h3cevtModuleSw-SR01DRSP2L                  OBJECT IDENTIFIER ::= { h3cevtModuleSwitchType 374 } -- 2-Port 2.5G RPR Optical Interface Card,(SFP,LC)
h3cevtModuleSw-SR01DRUP1L                  OBJECT IDENTIFIER ::= { h3cevtModuleSwitchType 375 } -- 1-Port 10G RPR Optical Interface Card,(XFP,LC)
h3cevtModuleSw-SR01DGP20R                  OBJECT IDENTIFIER ::= { h3cevtModuleSwitchType 376 } -- 20-Port 1000BASE-X Optical Interface Card,(SFP,LC)
h3cevtModuleSw-SR01DPLP8L                  OBJECT IDENTIFIER ::= { h3cevtModuleSwitchType 377 } -- 8-Port 155M POS Optical Interface Card,(SFP,LC)
h3cevtModuleSw-SR01DXP2R                   OBJECT IDENTIFIER ::= { h3cevtModuleSwitchType 378 } -- 2-Port 10GBASE-R/W Ethernet Optical Interface Card,(XFP,LC)
h3cevtModuleSw-LSB1FW2A0                   OBJECT IDENTIFIER ::= { h3cevtModuleSwitchType 379 } -- Gigabit Firewall Card, 4 Gigabit Port for Management
h3cevtModuleSw-LSB1GP48LDB                 OBJECT IDENTIFIER ::= { h3cevtModuleSwitchType 380 } -- 48-Port Line Rate Gigabit Ethernet Optical Interface Card(DB)
h3cevtModuleSw-SR01LN1BNA0                 OBJECT IDENTIFIER ::= { h3cevtModuleSwitchType 381 } -- Single XG Service Board(BNA)
h3cevtModuleSw-SR01LN2BQH0                 OBJECT IDENTIFIER ::= { h3cevtModuleSwitchType 382 } -- Dual XG Service Board(BQH)
h3cevtModuleSw-SR01LN2BNA0                 OBJECT IDENTIFIER ::= { h3cevtModuleSwitchType 383 } -- Dual XG Service Board(BNA)
h3cevtModuleSw-SR01DGT20R                  OBJECT IDENTIFIER ::= { h3cevtModuleSwitchType 384 } -- 20-Port 10/100/1000BASE-T Electrical Interface Card,(RJ45)
h3cevtModuleSw-SR01DPSP4L                  OBJECT IDENTIFIER ::= { h3cevtModuleSwitchType 385 } -- 4-Port 2.5G POS Optical Interface Card(SFP,LC)
h3cevtModuleSw-SR01DPUP1L                  OBJECT IDENTIFIER ::= { h3cevtModuleSwitchType 386 } -- 1-Port 10G POS Optical Interface Card,(XFP,LC)
h3cevtModuleSw-SR01DPL2G6L                 OBJECT IDENTIFIER ::= { h3cevtModuleSwitchType 387 } -- 2-Port 155M POS Optical Interface(SFP,LC)+6-Port 1000BASE-X Optical Interface Card(SFP,LC)
h3cevtModuleSw-SR01DPH2G6L                 OBJECT IDENTIFIER ::= { h3cevtModuleSwitchType 388 } -- 2-Port 622M POS Optical Interface(SFP,LC)+6-Port 1000BASE-X Optical Interface Card(SFP,LC)
h3cevtModuleSw-SR01DPS2G4L                 OBJECT IDENTIFIER ::= { h3cevtModuleSwitchType 389 } -- 2-Port 2.5G POS Optical Interface(SFP,LC)+4-Port 1000BASE-X Optical Interface Card(SFP,LC)
h3cevtModuleSw-SR01DCL1G8L                 OBJECT IDENTIFIER ::= { h3cevtModuleSwitchType 390 } -- 1-Port 155M CPOS Optical Interface(SFP,LC)+8-Port 1000BASE-X Optical Interface Card(SFP,LC)
h3cevtModuleSw-SR01DCL2G8L                 OBJECT IDENTIFIER ::= { h3cevtModuleSwitchType 391 } -- 2-Port 155M CPOS Optical Interface(SFP,LC)+8-Port 1000BASE-X Optical Interface Card(SFP,LC)
h3cevtModuleSw-SR01DET8G8L                 OBJECT IDENTIFIER ::= { h3cevtModuleSwitchType 392 } -- 8-Port E1/T1 Electrical Interface(RJ45)+8-Port 1000BASE-X Optical Interface Card(SFP,LC)
h3cevtModuleSw-SR02SRP2E3                  OBJECT IDENTIFIER ::= { h3cevtModuleSwitchType 393 } -- Switching and Route Process Unit, Clock module
h3cevtModuleSw-SR02SRP1E3                  OBJECT IDENTIFIER ::= { h3cevtModuleSwitchType 394 } -- Switching and Route Process Unit, Clock module
h3cevtModuleSw-SR02SRP1M3                  OBJECT IDENTIFIER ::= { h3cevtModuleSwitchType 395 } -- Switching and Route Process Unit, Clock module
h3cevtModuleSw-SR01DQCP4L                  OBJECT IDENTIFIER ::= { h3cevtModuleSwitchType 396 } -- 4-Port OC-3c/OC-12c/OC-48c POS/GE Optical Interface Card,(SFP,LC)
h3cevtModuleSw-SR01DTCP8L                  OBJECT IDENTIFIER ::= { h3cevtModuleSwitchType 397 } -- 8-Port OC-3c/OC-12c POS/GE Optical Interface Card,(SFP,LC)
h3cevtModuleSw-LSB1AFC1A0                  OBJECT IDENTIFIER ::= { h3cevtModuleSwitchType 398 } -- Anomaly Flow Cleaner Board
h3cevtModuleSw-LSB1SSL1A0                  OBJECT IDENTIFIER ::= { h3cevtModuleSwitchType 399 } -- SSL VPN High-end Board
h3cevtModuleSw-IMNAM                       OBJECT IDENTIFIER ::= { h3cevtModuleSwitchType 400 } -- Net Analysis Service Processing Board
h3cevtModuleSw-IMNAT                       OBJECT IDENTIFIER ::= { h3cevtModuleSwitchType 401 } -- Network Address Translation Service Processing Board
h3cevtModuleSw-PICAHP1L                    OBJECT IDENTIFIER ::= { h3cevtModuleSwitchType 402 } -- 1-Port OC-12c/STM-4c ATM Optical Interface Card,(SFP,LC)
h3cevtModuleSw-PICALP4L                    OBJECT IDENTIFIER ::= { h3cevtModuleSwitchType 403 } -- 4-Port OC-3c/STM-1c ATM Optical Interface Card,(SFP,LC)
h3cevtModuleSw-PICCHP4L                    OBJECT IDENTIFIER ::= { h3cevtModuleSwitchType 404 } -- 4-Port 622M CPOS Optical Interface Card(SFP,LC)
h3cevtModuleSw-PICCHS1G4L                  OBJECT IDENTIFIER ::= { h3cevtModuleSwitchType 405 } -- 1-Port 622M CPOS Optical Interface(Channelized to E3/T3)+4-Port 1000BASE-X Optical Interface Card(SFP,LC)
h3cevtModuleSw-PICCLS4G4L                  OBJECT IDENTIFIER ::= { h3cevtModuleSwitchType 406 } -- 4-Port 155M CPOS Optical Interface(Channelized to E3/T3)+4-Port 1000BASE-X Optical Interface Card(SFP,LC)
h3cevtModuleSw-PICCSP1L                    OBJECT IDENTIFIER ::= { h3cevtModuleSwitchType 407 } -- 1-Port 2.5G CPOS Optical Interface Card(SFP,LC)
h3cevtModuleSw-LSB1ACG1A0                  OBJECT IDENTIFIER ::= { h3cevtModuleSwitchType 408 } -- Application Control Gateway Board
h3cevtModuleSw-LST1MRPNC1                  OBJECT IDENTIFIER ::= { h3cevtModuleSwitchType 409 } -- Management and Route Process Unit
h3cevtModuleSw-LST1SF18B1                  OBJECT IDENTIFIER ::= { h3cevtModuleSwitchType 410 } -- S12518 Switch Fabric Card
h3cevtModuleSw-LST1SF08B1                  OBJECT IDENTIFIER ::= { h3cevtModuleSwitchType 411 } -- S12508 Switch Fabric Card
h3cevtModuleSw-LST1GT48LEC1                OBJECT IDENTIFIER ::= { h3cevtModuleSwitchType 412 } -- 48-Port 10/100/1000BASE-T Interface Module(LEC),(RJ45)
h3cevtModuleSw-LST1GP48LEC1                OBJECT IDENTIFIER ::= { h3cevtModuleSwitchType 413 } -- 48-Port 1000BASE-X Interface Module (LEC),(SFP,LC)
h3cevtModuleSw-LST1XP4LEC1                 OBJECT IDENTIFIER ::= { h3cevtModuleSwitchType 414 } -- 4-Port 10GBASE-R/W Interface Module (LEC),(XFP,LC)
h3cevtModuleSw-LST1XP8LEC1                 OBJECT IDENTIFIER ::= { h3cevtModuleSwitchType 415 } -- 8-Port 10GBASE-R/W Interface Module (LEC),(XFP,LC)
h3cevtModuleSw-LSR1SRP2B1                  OBJECT IDENTIFIER ::= { h3cevtModuleSwitchType 416 } -- Switching and Route Process Unit
h3cevtModuleSw-LSR1SRP2C1                  OBJECT IDENTIFIER ::= { h3cevtModuleSwitchType 417 } -- Switching and Route Process Unit
h3cevtModuleSw-LSR1SRP2B2                  OBJECT IDENTIFIER ::= { h3cevtModuleSwitchType 418 } -- Switching and Route Process Unit
h3cevtModuleSw-LSR1SRP2C2                  OBJECT IDENTIFIER ::= { h3cevtModuleSwitchType 419 } -- Switching and Route Process Unit
h3cevtModuleSw-LSR1GT24LEC1                OBJECT IDENTIFIER ::= { h3cevtModuleSwitchType 420 } -- 16-Port 10/100/1000BASE-T Interface and 8-port 1000BASE-T/1000BASE-X Combo Interface Service Card(LEC)
h3cevtModuleSw-LSR1GP24LEB1                OBJECT IDENTIFIER ::= { h3cevtModuleSwitchType 421 } -- 16-Port 1000BASE-X Interface and 8-port 1000BASE-T/1000BASE-X Combo Interface Service Card(LEB)
h3cevtModuleSw-LSR1GP24LEC1                OBJECT IDENTIFIER ::= { h3cevtModuleSwitchType 422 } -- 16-Port 1000BASE-X Interface and 8-port 1000BASE-T/1000BASE-X Combo Interface Service Card(LEC)
h3cevtModuleSw-LSR1GT48LEB1                OBJECT IDENTIFIER ::= { h3cevtModuleSwitchType 423 } -- 48-Port 10/100/1000BASE-T Interface Module(LEB),(RJ45)
h3cevtModuleSw-LSR1GT48LEC1                OBJECT IDENTIFIER ::= { h3cevtModuleSwitchType 424 } -- 48-Port 10/100/1000BASE-T Interface Module(LEC),(RJ45)
h3cevtModuleSw-LSR1GP48LEB1                OBJECT IDENTIFIER ::= { h3cevtModuleSwitchType 425 } -- 48-Port 1000BASE-X Interface Module(LEB),(SFP,LC)
h3cevtModuleSw-LSR1GP48LEC1                OBJECT IDENTIFIER ::= { h3cevtModuleSwitchType 426 } -- 48-Port 1000BASE-X Interface Module(LEC),(SFP,LC)
h3cevtModuleSw-LSR2GV48REB1                OBJECT IDENTIFIER ::= { h3cevtModuleSwitchType 427 } -- 48-Port 10/100/1000BASE-T Interface Module(REB),(PoE,RJ45)
h3cevtModuleSw-LSR1XP2LEB1                 OBJECT IDENTIFIER ::= { h3cevtModuleSwitchType 428 } -- 2-Port 10GBase-R/W Interface Module (LEB),(XFP,LC)
h3cevtModuleSw-LSR1XP2LEC1                 OBJECT IDENTIFIER ::= { h3cevtModuleSwitchType 429 } -- 2-Port 10GBase-R/W Interface Module (LEC),(XFP,LC)
h3cevtModuleSw-LSR1XP4LEB1                 OBJECT IDENTIFIER ::= { h3cevtModuleSwitchType 430 } -- 4-Port 10GBase-R/W Interface Module (LEB),(XFP,LC)
h3cevtModuleSw-LSR1XP4LEC1                 OBJECT IDENTIFIER ::= { h3cevtModuleSwitchType 431 } -- 4-Port 10GBase-R/W Interface Module (LEC),(XFP,LC)
h3cevtModuleSw-IMFW                        OBJECT IDENTIFIER ::= { h3cevtModuleSwitchType 432 } -- Firewall Service Processing Board
h3cevtModuleSw-LSB1LB1A0                   OBJECT IDENTIFIER ::= { h3cevtModuleSwitchType 433 } -- Load Balance Board
h3cevtModuleSw-LSB1IPS1A0                  OBJECT IDENTIFIER ::= { h3cevtModuleSwitchType 434 } -- Gigabit IPS Card
h3cevtModuleSw-LST1GT48LEB1                OBJECT IDENTIFIER ::= { h3cevtModuleSwitchType 435 } -- 48-Port 10/100/1000BASE-T Interface Module(LEB),(RJ45)
h3cevtModuleSw-LST1GP48LEB1                OBJECT IDENTIFIER ::= { h3cevtModuleSwitchType 436 } -- 48-Port 1000BASE-X Interface Module (LEB),(SFP,LC)
h3cevtModuleSw-LST1XP4LEB1                 OBJECT IDENTIFIER ::= { h3cevtModuleSwitchType 437 } -- 4-Port 10GBASE-R/W Interface Module (LEB),(XFP,LC)
h3cevtModuleSw-LST1XP8LEB1                 OBJECT IDENTIFIER ::= { h3cevtModuleSwitchType 438 } -- 8-Port 10GBASE-R/W Interface Module (LEB),(XFP,LC)
h3cevtModuleSw-LST1XP32REB1                OBJECT IDENTIFIER ::= { h3cevtModuleSwitchType 439 } -- 32-Port 10GBASE-R Interface Module (REB),(SFP+,LC)
h3cevtModuleSw-LST1XP32REC1                OBJECT IDENTIFIER ::= { h3cevtModuleSwitchType 440 } -- 32-Port 10GBASE-R Interface Module (REC),(SFP+,LC)
h3cevtModuleSw-LSR1FW2A1                   OBJECT IDENTIFIER ::= { h3cevtModuleSwitchType 441 } -- Firewall Service Module
h3cevtModuleSw-LSR1SSL1A1                  OBJECT IDENTIFIER ::= { h3cevtModuleSwitchType 442 } -- SSL VPN Service Module
h3cevtModuleSw-SR01DET32G2L                OBJECT IDENTIFIER ::= { h3cevtModuleSwitchType 443 } -- 32-Port E1/T1 75ohm Electrical Interface(DB56 Female Socket)+2-Port 1000BASE-X Optical Interface Card(SFP,LC)
h3cevtModuleSw-LSR1GP24LEF1                OBJECT IDENTIFIER ::= { h3cevtModuleSwitchType 444 } -- 16-Port 1000BASE-X Interface and 8-port 1000BASE-T/1000BASE-X Combo Interface Service Card(LEF)
h3cevtModuleSw-LSR1XP4LEF1                 OBJECT IDENTIFIER ::= { h3cevtModuleSwitchType 445 } -- 4-Port 10GBASE-R/W Interface Module (LEF),(XFP,LC)
h3cevtModuleSw-LSR1LB1A1                   OBJECT IDENTIFIER ::= { h3cevtModuleSwitchType 446 } -- Load Balance Module
h3cevtModuleSw-LSR1NSM1A1                  OBJECT IDENTIFIER ::= { h3cevtModuleSwitchType 447 } -- NetStream Module
h3cevtModuleSw-LSR1ACG1A1                  OBJECT IDENTIFIER ::= { h3cevtModuleSwitchType 448 } -- Application Control Gateway Service Module
h3cevtModuleSw-LSR1IPS1A1                  OBJECT IDENTIFIER ::= { h3cevtModuleSwitchType 449 } -- Intrusion Protection System Service Module
h3cevtModuleSw-LSR2GP24LEB1                OBJECT IDENTIFIER ::= { h3cevtModuleSwitchType 450 } -- 16-Port 1000BASE-X Interface and 8-port 1000BASE-T/1000BASE-X Combo Interface Service Card(LEB)
h3cevtModuleSw-LSR2GT24LEB1                OBJECT IDENTIFIER ::= { h3cevtModuleSwitchType 451 } -- 16-Port 10/100/1000BASE-T Interface and 8-port 1000BASE-T/1000BASE-X Combo Interface Service Card(LEB)
h3cevtModuleSw-LSR2GT48LEB1                OBJECT IDENTIFIER ::= { h3cevtModuleSwitchType 452 } -- 48-Port 10/100/1000BASE-T Interface Module(LEB),(RJ45)
h3cevtModuleSw-SPC-GP24L                   OBJECT IDENTIFIER ::= { h3cevtModuleSwitchType 453 } -- 24-Port 1000BASE-X Interface Service Card,(SFP,LC)
h3cevtModuleSw-SPC-GT48L                   OBJECT IDENTIFIER ::= { h3cevtModuleSwitchType 454 } -- 48-Port 10/100/1000BASE-T Interface Module,(RJ45)
h3cevtModuleSw-SPC-GP48L                   OBJECT IDENTIFIER ::= { h3cevtModuleSwitchType 455 } -- 48-Port 1000BASE-X Interface Module,(SFP,LC)
h3cevtModuleSw-SPC-XP2L                    OBJECT IDENTIFIER ::= { h3cevtModuleSwitchType 456 } -- 2-Port 10GBASE-R/W Interface Service Card,(XFP,LC)
h3cevtModuleSw-SPC-XP4L                    OBJECT IDENTIFIER ::= { h3cevtModuleSwitchType 457 } -- 4-Port 10GBase-R/W Interface Module,(XFP,LC)
h3cevtModuleSw-SR06SRP2E3                  OBJECT IDENTIFIER ::= { h3cevtModuleSwitchType 458 } -- SDI,Routing Switch Processing Board
h3cevtModuleSw-SPE-2010-E                  OBJECT IDENTIFIER ::= { h3cevtModuleSwitchType 459 } -- SDI,Single XG Service Board
h3cevtModuleSw-SPE-2020-E                  OBJECT IDENTIFIER ::= { h3cevtModuleSwitchType 460 } -- SDI,Dual XG Service Board
h3cevtModuleSw-SPC-XP4L-S-SDI              OBJECT IDENTIFIER ::= { h3cevtModuleSwitchType 461 } -- SDI 4-Port 10GBase-R/W Interface Module,(XFP,LC)
h3cevtModuleSw-SPC-GT48L-SDI               OBJECT IDENTIFIER ::= { h3cevtModuleSwitchType 462 } -- SDI 48-Port 10/100/1000BASE-T Interface Module,(RJ45)
h3cevtModuleSw-SPC-GP48L-S-SDI             OBJECT IDENTIFIER ::= { h3cevtModuleSwitchType 463 } -- SDI 48-Port 1000BASE-X Interface Module,(SFP,LC)
h3cevtModuleSw-SPC-SR02OPMA0               OBJECT IDENTIFIER ::= { h3cevtModuleSwitchType 464 } -- Single Mode 1310&1550nm Optical Protect Board(LC)
h3cevtModuleSw-LSR1XP16REB1                OBJECT IDENTIFIER ::= { h3cevtModuleSwitchType 465 } -- 16-Port 10GBASE-R Interface Module (REB),(SFP+,LC)
h3cevtModuleSw-LSR1GP48LEF1                OBJECT IDENTIFIER ::= { h3cevtModuleSwitchType 466 } -- 48-Port 1000BASE-X Interface Module (LEF),(SFP,LC)
h3cevtModuleSw-LST1GP48LEF1                OBJECT IDENTIFIER ::= { h3cevtModuleSwitchType 467 } -- 48-Port 1000BASE-X Interface Module (LEF),(SFP,LC)
h3cevtModuleSw-LST1XP8LEF1                 OBJECT IDENTIFIER ::= { h3cevtModuleSwitchType 468 } -- 8-Port 10GBASE-R/W Interface Module (LEF),(XFP,LC)
h3cevtModuleSw-SPE-1010-II                 OBJECT IDENTIFIER ::= { h3cevtModuleSwitchType 469 } -- Single XG Service Board-II
h3cevtModuleSw-SPE-1010-E-II               OBJECT IDENTIFIER ::= { h3cevtModuleSwitchType 470 } -- Enhanced Single XG Service Board-II
h3cevtModuleSw-SPE-1020-II                 OBJECT IDENTIFIER ::= { h3cevtModuleSwitchType 471 } -- Double XG Service Board-II
h3cevtModuleSw-SPE-1020-E-II               OBJECT IDENTIFIER ::= { h3cevtModuleSwitchType 472 } -- Enhanced Double XG Service Board-II
h3cevtModuleSw-LST1FW2A1                   OBJECT IDENTIFIER ::= { h3cevtModuleSwitchType 473 } -- Firewall Board (LEC)
h3cevtModuleSw-LST1NSM1A1                  OBJECT IDENTIFIER ::= { h3cevtModuleSwitchType 474 } -- NetStream Service Board (LEC)
h3cevtModuleSw-LST1LB1A1                   OBJECT IDENTIFIER ::= { h3cevtModuleSwitchType 475 } -- Load Balancing Board (LEC)
h3cevtModuleSw-LST1ACG1A1                  OBJECT IDENTIFIER ::= { h3cevtModuleSwitchType 476 } -- Application Control Gateway Board Module (LEC)
h3cevtModuleSw-LST1IPS1A1                  OBJECT IDENTIFIER ::= { h3cevtModuleSwitchType 477 } -- Gigabit Intrusion Prevention System Module (LEC)
h3cevtModuleSw-LSR1DRUP1L1                 OBJECT IDENTIFIER ::= { h3cevtModuleSwitchType 478 } -- 1-Port OC-192c/STM-64c RPR Optical Interface Card,(XFP,LC)
h3cevtModuleSw-LSR1DPUP1L1                 OBJECT IDENTIFIER ::= { h3cevtModuleSwitchType 479 } -- 1-Port OC-192c/STM-64c POS Optical Interface Card,(XFP,LC)
h3cevtModuleSw-LSR1DPSP4L1                 OBJECT IDENTIFIER ::= { h3cevtModuleSwitchType 480 } -- 4-Port OC-48c/STM-16c POS Optical Interface Card,(SFP,LC)
h3cevtModuleSw-LSR1DTCP8L1                 OBJECT IDENTIFIER ::= { h3cevtModuleSwitchType 481 } -- 8-Port OC-3c/OC-12c POS/GE Optical Interface Card,(SFP,LC)
h3cevtModuleSw-LSR1DXP1L1                  OBJECT IDENTIFIER ::= { h3cevtModuleSwitchType 482 } -- 1-Port 10GBASE-R/W Ethernet Optical Interface Card,(XPF,LC)
h3cevtModuleSw-LSR1DGP10L1                 OBJECT IDENTIFIER ::= { h3cevtModuleSwitchType 483 } -- 10-Port 1000BASE-X Optical Interface Card,(SFP,LC)
h3cevtModuleSw-LSR1LN1BNL1                 OBJECT IDENTIFIER ::= { h3cevtModuleSwitchType 484 } -- Single Service Processing Board
h3cevtModuleSw-LSR1LN2BL1                  OBJECT IDENTIFIER ::= { h3cevtModuleSwitchType 485 } -- Dual Serivice Processing Board
h3cevtModuleSw-LSR1SRP2D1                  OBJECT IDENTIFIER ::= { h3cevtModuleSwitchType 486 } -- Switching and Route Process Unit With Clock
h3cevtModuleSw-IM-NAT-II                   OBJECT IDENTIFIER ::= { h3cevtModuleSwitchType 487 } -- Network Address Translation Service Processing Board,II
h3cevtModuleSw-IM-NAM-II                   OBJECT IDENTIFIER ::= { h3cevtModuleSwitchType 488 } -- Net Analysis Service Processing Board,II
h3cevtModuleSw-CR-MRP-I                    OBJECT IDENTIFIER ::= { h3cevtModuleSwitchType 489 } -- Management and Route Unit With OAM Module and Clock Module
h3cevtModuleSw-CR-SF18C                    OBJECT IDENTIFIER ::= { h3cevtModuleSwitchType 490 } -- Switch Fabric Card
h3cevtModuleSw-CR-SF08C                    OBJECT IDENTIFIER ::= { h3cevtModuleSwitchType 491 } -- Switch Fabric Card
h3cevtModuleSw-CR-SPC-XP8LEF               OBJECT IDENTIFIER ::= { h3cevtModuleSwitchType 492 } -- 8-Port 10GBASE-R/W Interface Module,(XFP,LC)
h3cevtModuleSw-CR-SPC-XP4LEF               OBJECT IDENTIFIER ::= { h3cevtModuleSwitchType 493 } -- 4-Port 10GBASE-R/W Interface Module,(XFP,LC)
h3cevtModuleSw-CR-SPC-GP48LEF              OBJECT IDENTIFIER ::= { h3cevtModuleSwitchType 494 } -- 48-Port 1000BASE-X Interface Module,(SFP,LC)
h3cevtModuleSw-CR-SPC-GT48LEF              OBJECT IDENTIFIER ::= { h3cevtModuleSwitchType 495 } -- 48-Port 10/100/1000BASE-T Interface Module
h3cevtModuleSw-CR-SPE-3020-E               OBJECT IDENTIFIER ::= { h3cevtModuleSwitchType 496 } -- Double XG Service Board (Enhanced)
h3cevtModuleSw-CR-SPC-PUP4L-E              OBJECT IDENTIFIER ::= { h3cevtModuleSwitchType 497 } -- 4-Port 10G POS Optical Interface Module,(XFP,LC)
h3cevtModuleSw-LST1SF08C1                  OBJECT IDENTIFIER ::= { h3cevtModuleSwitchType 498 } -- Switch Fabric Card
h3cevtModuleSw-LST1SF18C1                  OBJECT IDENTIFIER ::= { h3cevtModuleSwitchType 499 } -- Switch Fabric Card

--
-- 500 to 699 reserved for secondary switches part I
--
h3cevtModuleSw-LS81GP16TM                  OBJECT IDENTIFIER ::= { h3cevtModuleSwitchType 500 } -- 12-port 1000BASE-X SFP Interface and 4-port 1000BASE-T/1000BASE-X Combo Interface Metro Switch and Route Processing Board
h3cevtModuleSw-LS81VP4C                    OBJECT IDENTIFIER ::= { h3cevtModuleSwitchType 501 } -- 4-port 1000BASE-X SFP Interface Virtual Daughter Card
h3cevtModuleSw-LS8M1PT8P0                  OBJECT IDENTIFIER ::= { h3cevtModuleSwitchType 502 } -- 8-Port 1000BASE-PX Optical Line Interface Board, SFP Req
h3cevtModuleSw-LS8M1PT8GB0                 OBJECT IDENTIFIER ::= { h3cevtModuleSwitchType 503 } -- 8-Port 1000BASE-PX20 Gigabit Passive Optical Line Interface Board B(20km, SFF), SC Connector
h3cevtModuleSw-LS8M1PT4GB0                 OBJECT IDENTIFIER ::= { h3cevtModuleSwitchType 504 } -- 4-Port 1000BASE-PX20 Gigabit Passive Optical Line Interface Board B(20km, SFF), SC Connector
h3cevtModuleSw-LS81GP2R                    OBJECT IDENTIFIER ::= { h3cevtModuleSwitchType 505 } -- 2-port 1000M Ethernet Optical Interface RPR Board
h3cevtModuleSw-LS81GP4R                    OBJECT IDENTIFIER ::= { h3cevtModuleSwitchType 506 } -- 4-port 1000M Ethernet Optical Interface RPR Board
h3cevtModuleSw-LS81IPSECA                  OBJECT IDENTIFIER ::= { h3cevtModuleSwitchType 507 } -- IPSec Service Board
h3cevtModuleSw-LS81FWA                     OBJECT IDENTIFIER ::= { h3cevtModuleSwitchType 508 } -- Firewall Service Board
h3cevtModuleSw-LS82VSNP                    OBJECT IDENTIFIER ::= { h3cevtModuleSwitchType 509 } -- Versatile Network Processing Service Module (PBR/NAT/NetStream) with 12-port 1000BASE-X SFP, XGBUS Uplink
h3cevtModuleSw-LSQ1GV48SA                  OBJECT IDENTIFIER ::= { h3cevtModuleSwitchType 510 } -- 48-Port 1000Base-T Gigabit Ethernet Interface Board(RJ45)
h3cevtModuleSw-LSQ1SRPB                    OBJECT IDENTIFIER ::= { h3cevtModuleSwitchType 511 } -- Salience VI
h3cevtModuleSw-LSQ1SRP2XB                  OBJECT IDENTIFIER ::= { h3cevtModuleSwitchType 512 } -- Salience VI-10GE
h3cevtModuleSw-LSQ1SRP1CB                  OBJECT IDENTIFIER ::= { h3cevtModuleSwitchType 513 } -- Salience VI-Turbo
h3cevtModuleSw-LSQ1FV48SA                  OBJECT IDENTIFIER ::= { h3cevtModuleSwitchType 514 } -- 48-Port 100M Ethernet Electrical Interface Switch Unit(RJ45)
h3cevtModuleSw-LSD1MPUA                    OBJECT IDENTIFIER ::= { h3cevtModuleSwitchType 515 } -- Main Control Unit
h3cevtModuleSw-LSD1GP20A0                  OBJECT IDENTIFIER ::= { h3cevtModuleSwitchType 516 } -- 16-port 1000BASE-X SFP Interface and 4-port 1000BASE-T/1000BASE-X Combo Interface Line Card
h3cevtModuleSw-LSD1GP20TA0                 OBJECT IDENTIFIER ::= { h3cevtModuleSwitchType 517 } -- 16-port 1000BASE-X SFP Interface and 4-port 1000BASE-T/1000BASE-X Combo Interface and 16 1000BASE-T Interface Line Card
h3cevtModuleSw-LSD1GP36A0                  OBJECT IDENTIFIER ::= { h3cevtModuleSwitchType 518 } -- 32-port 1000BASE-X SFP Interface and 4-port 1000BASE-T/1000BASE-X Combo Interface Line Card
h3cevtModuleSw-LSD1GP20XA0                 OBJECT IDENTIFIER ::= { h3cevtModuleSwitchType 519 } -- 16-port 1000BASE-X SFP Interface and 4-port 1000BASE-T/1000BASE-X Combo Interface and 2-port 10GBASE-X XFP Interface Line Card
h3cevtModuleSw-LSD1GP20EA0                 OBJECT IDENTIFIER ::= { h3cevtModuleSwitchType 520 } -- 16-port 1000BASE-X SFP Interface and 4-port 1000BASE-T/1000BASE-X Combo Interface and 2-port GE RPR Interface Line Card
h3cevtModuleSw-LSD1GP20RA0                 OBJECT IDENTIFIER ::= { h3cevtModuleSwitchType 521 } -- 16-port 1000BASE-X SFP Interface and 4-port 1000BASE-T/1000BASE-X Combo Interface and 2-port OC48 RPR Interface Line Card
h3cevtModuleSw-LSD1GP16A0                  OBJECT IDENTIFIER ::= { h3cevtModuleSwitchType 522 } -- 16-port 1000BASE-X SFP Ethernet Interface SubCard
h3cevtModuleSw-LSD1GT16A0                  OBJECT IDENTIFIER ::= { h3cevtModuleSwitchType 523 } -- 16-port 1000BASE-T Ethernet Interface SubCard
h3cevtModuleSw-LSD1XP2A0                   OBJECT IDENTIFIER ::= { h3cevtModuleSwitchType 524 } -- 2-port 10GBASE-X XFP Ethernet Interface SubCard
h3cevtModuleSw-LSD1EP2A0                   OBJECT IDENTIFIER ::= { h3cevtModuleSwitchType 525 } -- 2-port 1000BASE-T Ethernet RPR Interface SubCard
h3cevtModuleSw-LSD1RP2A0                   OBJECT IDENTIFIER ::= { h3cevtModuleSwitchType 526 } -- 2-port OC48 RPR Interface SubCard
h3cevtModuleSw-LSQ1GV48SC                  OBJECT IDENTIFIER ::= { h3cevtModuleSwitchType 527 } -- 48-Port 1000Base-T Gigabit Ethernet Interface Board(RJ45)-POE
h3cevtModuleSw-LSQ1FP48SA                  OBJECT IDENTIFIER ::= { h3cevtModuleSwitchType 528 } -- 48 Port 100M Ethernet Optical Interface Board(SFP,LC)
h3cevtModuleSw-LSQ1GP24SC                  OBJECT IDENTIFIER ::= { h3cevtModuleSwitchType 529 } -- 24 Port 1000BASE-X Ethernet Optical Interface Board(SFP,LC)
h3cevtModuleSw-LSQ1GT24SC                  OBJECT IDENTIFIER ::= { h3cevtModuleSwitchType 530 } -- 24-Port 1000BASE-T Ethernet Interface Board (RJ45)
h3cevtModuleSw-LSQ1TGX2SC                  OBJECT IDENTIFIER ::= { h3cevtModuleSwitchType 531 } -- 2-Port 10GBASE Ethernet Optical Interface Board(XFP,LC)
h3cevtModuleSw-LSQ1GP12EA                  OBJECT IDENTIFIER ::= { h3cevtModuleSwitchType 532 } -- 12-Port 1000BASE-X Ethernet Optical Interface Board(SFP,LC)
h3cevtModuleSw-LSQ1TGX1EA                  OBJECT IDENTIFIER ::= { h3cevtModuleSwitchType 533 } -- 1-Port 10GBASE Ethernet Optical Interface Module(XFP,LC)
h3cevtModuleSw-LSQ1P24XGSC                 OBJECT IDENTIFIER ::= { h3cevtModuleSwitchType 534 } -- 24-Port 1000BASE-X Gigabit Ethernet Optical Interface(SFP,LC)+2-Port 10GBASE Ethernet Optical Interface Board(XFP,LC)
h3cevtModuleSw-LSQ1T24XGSC                 OBJECT IDENTIFIER ::= { h3cevtModuleSwitchType 535 } -- 24-Port 1000BASE-T Gigabit Ethernet Interface(RJ45)+2-Port 10GBASE Ethernet Optical Interface Board(XFP,LC)
h3cevtModuleSw-LS81TGX1B                   OBJECT IDENTIFIER ::= { h3cevtModuleSwitchType 536 } -- 1 Port 10GBase-R Ethernet Interface Board(XENPAK,SC)
h3cevtModuleSw-LSQ1PT4PSC0                 OBJECT IDENTIFIER ::= { h3cevtModuleSwitchType 537 } -- 4-Port 1000Base-PX Optical Line Terminal(EPON OLT SFP,SC)+8-Port 1000BASE-X Optical Interface Board(SFP,LC)
h3cevtModuleSw-LS81SRPG13                  OBJECT IDENTIFIER ::= { h3cevtModuleSwitchType 538 } -- Salience V, Switch and Route Processing Board
h3cevtModuleSw-LS81SRPG14                  OBJECT IDENTIFIER ::= { h3cevtModuleSwitchType 539 } -- Salience V Edge
h3cevtModuleSw-LS81SRPG15                  OBJECT IDENTIFIER ::= { h3cevtModuleSwitchType 540 } -- Salience V Plus
h3cevtModuleSw-LSQ1GP48SC0                 OBJECT IDENTIFIER ::= { h3cevtModuleSwitchType 541 } -- 48-Port 1000BASE Ethernet Optical Interface Board(SFP,LC)
h3cevtModuleSw-LSQ1GP12SC0                 OBJECT IDENTIFIER ::= { h3cevtModuleSwitchType 542 } -- 12-Port 1000BASE-X Ethernet Optical Interface Board(SFP,LC)
h3cevtModuleSw-LSD1SRPA                    OBJECT IDENTIFIER ::= { h3cevtModuleSwitchType 543 } -- Salience VIII 160
h3cevtModuleSw-LSD1SRPB                    OBJECT IDENTIFIER ::= { h3cevtModuleSwitchType 544 } -- Salience VIII 480
h3cevtModuleSw-LSD1SRPC                    OBJECT IDENTIFIER ::= { h3cevtModuleSwitchType 545 } -- Salience VIII 800
h3cevtModuleSw-LSD1GT16PES0                OBJECT IDENTIFIER ::= { h3cevtModuleSwitchType 546 } -- 16-Port 10/100/1000BASE-T and 8-Port 100/1000BASE-X SFP Interface Card
h3cevtModuleSw-LSD1GP24ES0                 OBJECT IDENTIFIER ::= { h3cevtModuleSwitchType 547 } -- 24-Port 1000BASE-X Ethernet SFP Interface Card
h3cevtModuleSw-LSD1GT24XES0                OBJECT IDENTIFIER ::= { h3cevtModuleSwitchType 548 } -- 24-Port 10/100/1000BASE-T and 2-port 10GBASE-X Ethernet XFP Optical Interface Card
h3cevtModuleSw-LSD1GP24XES0                OBJECT IDENTIFIER ::= { h3cevtModuleSwitchType 549 } -- 24-Port 1000BASE-X Ethernet SFP interface and 2-port 10GBASE-X Ethernet XFP Optical Interface Card
h3cevtModuleSw-LSD1XP2ES0                  OBJECT IDENTIFIER ::= { h3cevtModuleSwitchType 550 } -- 2-Port 10GBASE-X Ethernet XFP Optical Interface Card
h3cevtModuleSw-LSD1GP48ES0                 OBJECT IDENTIFIER ::= { h3cevtModuleSwitchType 551 } -- 48-Port 1000BASE-X Ethernet SFP Interface Card
h3cevtModuleSw-LSQ1MPUA0                   OBJECT IDENTIFIER ::= { h3cevtModuleSwitchType 552 } -- Master Process Board
h3cevtModuleSw-LSQ1MPUA1                   OBJECT IDENTIFIER ::= { h3cevtModuleSwitchType 553 } -- Master Process Unit
h3cevtModuleSw-LSQ1FWBSC0                  OBJECT IDENTIFIER ::= { h3cevtModuleSwitchType 554 } -- Gigabit Firewall Card, 4 Gigabit Port for Management
h3cevtModuleSw-LSQ1PT8PSC0                 OBJECT IDENTIFIER ::= { h3cevtModuleSwitchType 555 } -- 8-Port 1000Base-PX Optical Line Terminal(EPON OLT SFP,SC)+8-Port 1000BASE-X Optical Interface Board(SFP,LC)
h3cevtModuleSw-LSQ1PT16PSC0                OBJECT IDENTIFIER ::= { h3cevtModuleSwitchType 556 } -- 16-Port 1000Base-PX Optical Line Terminal(EPON OLT SFP,SC)+8-Port 1000BASE-X Optical Interface Board(SFP,LC)
h3cevtModuleSw-SA11MPUA0                   OBJECT IDENTIFIER ::= { h3cevtModuleSwitchType 557 } -- SmartEngine I-Lite
h3cevtModuleSw-SA11MPUB0                   OBJECT IDENTIFIER ::= { h3cevtModuleSwitchType 558 } -- SmartEngine I
h3cevtModuleSw-LSQ1AFCBSC0                 OBJECT IDENTIFIER ::= { h3cevtModuleSwitchType 559 } -- Anomaly Flow Cleaner Board Interface Board(SFP,LC)
h3cevtModuleSw-LSQ1MPUB0                   OBJECT IDENTIFIER ::= { h3cevtModuleSwitchType 560 } -- Salience VI-Lite
h3cevtModuleSw-LSQ1MPUB1                   OBJECT IDENTIFIER ::= { h3cevtModuleSwitchType 561 } -- Salience VI-Lite
h3cevtModuleSw-LSQ1PT4PSC1                 OBJECT IDENTIFIER ::= { h3cevtModuleSwitchType 562 } -- 4-Port 1000Base-PX Optical Line Terminal(EPON OLT SFP,SC)+8-Port 1000BASE-X Optical Interface Board(SFP,LC)
h3cevtModuleSw-LSQ1PT8PSC1                 OBJECT IDENTIFIER ::= { h3cevtModuleSwitchType 563 } -- 8-Port 1000Base-PX Optical Line Terminal(EPON OLT SFP,SC)+8-Port 1000BASE-X Optical Interface Board(SFP,LC)
h3cevtModuleSw-LSQ1PT16PSC1                OBJECT IDENTIFIER ::= { h3cevtModuleSwitchType 564 } -- 16-Port 1000Base-PX Optical Line Terminal(EPON OLT SFP,SC)+8-Port 1000BASE-X Optical Interface Board(SFP,LC)
h3cevtModuleSw-LSQ1FP48USA0                OBJECT IDENTIFIER ::= { h3cevtModuleSwitchType 565 } -- 48-Port 100M Ethernet Optical Interface Switch Unit(SFP,LC)
h3cevtModuleSw-LSQ1FP48USA1                OBJECT IDENTIFIER ::= { h3cevtModuleSwitchType 566 } -- 48-Port 100M Ethernet Optical Interface Switch Unit(SFP,LC)
h3cevtModuleSw-LSQ1FV48USA0                OBJECT IDENTIFIER ::= { h3cevtModuleSwitchType 567 } -- 48-Port 100M Ethernet Electrical Interface Switch Unit(RJ45),PoE
h3cevtModuleSw-LSQ1FV48USA1                OBJECT IDENTIFIER ::= { h3cevtModuleSwitchType 568 } -- 48-Port 100M Ethernet Electrical Interface Switch Unit(RJ45),PoE
h3cevtModuleSw-LSQ1SRPD0                   OBJECT IDENTIFIER ::= { h3cevtModuleSwitchType 569 } -- Switch and Route Processing Unit, Salience VI-Plus
h3cevtModuleSw-LSQ1CGP24TSC0               OBJECT IDENTIFIER ::= { h3cevtModuleSwitchType 570 } -- Switching and Routing Processing Unit with 24 1000BASE-X Gigabit Ethernet Optical Ports,including 8 Combo Ports,SFP Req.
h3cevtModuleSw-LSQ1GP24TSC0                OBJECT IDENTIFIER ::= { h3cevtModuleSwitchType 571 } -- 16-Port 1000BASE-X Gigabit Ethernet Optical(SFP,LC) And 8-Port 10/100/1000BASE-T RJ45/1000BASE-X SFP Combo Interface Board
h3cevtModuleSw-LSQ1ACGASC0                 OBJECT IDENTIFIER ::= { h3cevtModuleSwitchType 572 } -- Application Control Gateway Board
h3cevtModuleSw-LSD1XP1ES0                  OBJECT IDENTIFIER ::= { h3cevtModuleSwitchType 573 } -- 1-Port 10GBASE-X Ethernet XFP Optical Interface Card
h3cevtModuleSw-LSD1GP12ES0                 OBJECT IDENTIFIER ::= { h3cevtModuleSwitchType 574 } -- 12-Port 1000BASE-X Ethernet SFP Interface Card
h3cevtModuleSw-LSQ1SRP12GB0                OBJECT IDENTIFIER ::= { h3cevtModuleSwitchType 575 } -- Switch And Route Processing Unit with 12 1000BASE Ethernet Optical Interfaces(SFP,LC),Salience VI-GE
h3cevtModuleSw-LSQ1GV40PSC0                OBJECT IDENTIFIER ::= { h3cevtModuleSwitchType 576 } -- 40-Port 10/100/1000BASE-T Electrical(RJ45) And 8-Port 1000BASE-X Optical Ethernet Interface Board(SFP,LC),PoE
h3cevtModuleSw-LSQ1FWBSC1                  OBJECT IDENTIFIER ::= { h3cevtModuleSwitchType 577 } -- Firewall Board
h3cevtModuleSw-LSQ1NSMSC0                  OBJECT IDENTIFIER ::= { h3cevtModuleSwitchType 578 } -- NetStream Board
h3cevtModuleSw-LSQ1NSMSC1                  OBJECT IDENTIFIER ::= { h3cevtModuleSwitchType 579 } -- NetStream Board
h3cevtModuleSw-LSQ1AFDBSC0                 OBJECT IDENTIFIER ::= { h3cevtModuleSwitchType 580 } -- Anomaly Flow Detector Board
h3cevtModuleSw-LS81MPUB                    OBJECT IDENTIFIER ::= { h3cevtModuleSwitchType 581 } -- Salience IV
h3cevtModuleSw-LS81FP48XL                  OBJECT IDENTIFIER ::= { h3cevtModuleSwitchType 582 } -- 48-Port 100M Ethernet Optical Interface Module,(SFP,LC)
h3cevtModuleSw-LS81FT48XL                  OBJECT IDENTIFIER ::= { h3cevtModuleSwitchType 583 } -- 48-Port 10/100M Ethernet Electrical Interface Module(RJ45)
h3cevtModuleSw-LS81GP12XL                  OBJECT IDENTIFIER ::= { h3cevtModuleSwitchType 584 } -- 12-Port 1000/100M Ethernet Optical Interface Module(SFP,LC)
h3cevtModuleSw-LS81GP24XL                  OBJECT IDENTIFIER ::= { h3cevtModuleSwitchType 585 } -- 24-Port 1000/100M Ethernet Optical Interface Module(SFP,LC)
h3cevtModuleSw-LS81GP48XL                  OBJECT IDENTIFIER ::= { h3cevtModuleSwitchType 586 } -- 48-Port 1000/100M Ethernet Optical Interface Module(SFP,LC)
h3cevtModuleSw-LS81GT24XL                  OBJECT IDENTIFIER ::= { h3cevtModuleSwitchType 587 } -- 24-Port 10/100/1000M Ethernet Electrical Interface Module(RJ45)
h3cevtModuleSw-LS81GT48XL                  OBJECT IDENTIFIER ::= { h3cevtModuleSwitchType 588 } -- 48-Port 10/100/1000M Ethernet Electrical Interface Module(RJ45)
h3cevtModuleSw-LS81TGX2XL                  OBJECT IDENTIFIER ::= { h3cevtModuleSwitchType 589 } -- 2-Port 10GBASE Ethernet Optical Interface Module(XFP,LC)
h3cevtModuleSw-LSQ1GV48SD0                 OBJECT IDENTIFIER ::= { h3cevtModuleSwitchType 590 } -- 48-Port 1000Base-T Gigabit Ethernet Interface Board(RJ45),PoE
h3cevtModuleSw-LSQ1GP48EB0                 OBJECT IDENTIFIER ::= { h3cevtModuleSwitchType 591 } -- 48-Port Enhanced 1000BASE-X Ethernet Optical Interface Board(SFP,LC)
h3cevtModuleSw-LSQ1IPSSC0                  OBJECT IDENTIFIER ::= { h3cevtModuleSwitchType 592 } -- Gigabit IPS Card
h3cevtModuleSw-LSQ1GV48SD1                 OBJECT IDENTIFIER ::= { h3cevtModuleSwitchType 593 } -- 48-Port 1000Base-T Gigabit Ethernet Interface Board(RJ45),PoE
h3cevtModuleSw-LSQ1GP48SD0                 OBJECT IDENTIFIER ::= { h3cevtModuleSwitchType 594 } -- 48-Port 1000BASE-X Gigabit Ethernet Optical Interface(SFP,LC) Interface Board
h3cevtModuleSw-LSQ1GP48SD1                 OBJECT IDENTIFIER ::= { h3cevtModuleSwitchType 595 } -- 48-Port 1000BASE-X Gigabit Ethernet Optical Interface(SFP,LC) Interface Board
h3cevtModuleSw-LSQ1SRPA0                   OBJECT IDENTIFIER ::= { h3cevtModuleSwitchType 596 } -- Salience VI-Smart
h3cevtModuleSw-LSQ1SRPA1                   OBJECT IDENTIFIER ::= { h3cevtModuleSwitchType 597 } -- Salience VI-Smart
h3cevtModuleSw-LSQ2FP48SA0                 OBJECT IDENTIFIER ::= { h3cevtModuleSwitchType 598 } -- 48 Port 100M Ethernet Optical Interface Board(SFP,LC)
h3cevtModuleSw-LSQ2FP48SA1                 OBJECT IDENTIFIER ::= { h3cevtModuleSwitchType 599 } -- 48 Port 100M Ethernet Optical Interface Board(SFP,LC)
h3cevtModuleSw-LSQ2FT48SA0                 OBJECT IDENTIFIER ::= { h3cevtModuleSwitchType 600 } -- 48-Port 100M Ethernet Electrical Interface Switch Unit(RJ45)
h3cevtModuleSw-LSQ2FT48SA1                 OBJECT IDENTIFIER ::= { h3cevtModuleSwitchType 601 } -- 48-Port 100M Ethernet Electrical Interface Switch Unit(RJ45)
h3cevtModuleSw-LSQ1GV24PSC0                OBJECT IDENTIFIER ::= { h3cevtModuleSwitchType 602 } -- 24-Port 10/100/1000BASE-T Electrical(RJ45) Interface Board,including 4 Combo Ports,SFP Req,PoE,No Spell
h3cevtModuleSw-LSQ1GV24PSC1                OBJECT IDENTIFIER ::= { h3cevtModuleSwitchType 603 } -- 24-Port 10/100/1000BASE-T Electrical(RJ45) Interface Board,including 4 Combo Ports,SFP Req,PoE,No Spell
h3cevtModuleSw-LSQ1CGV24PSC0               OBJECT IDENTIFIER ::= { h3cevtModuleSwitchType 604 } -- Switching and Routing Processing Unit with 24 10/100/1000BASE-T Electrical Ports(RJ45),including 4 Combo Ports,SFP Req,PoE,No Spell
h3cevtModuleSw-LSQ1CGV24PSC1               OBJECT IDENTIFIER ::= { h3cevtModuleSwitchType 605 } -- Switching and Routing Processing Unit with 24 10/100/1000BASE-T Electrical Ports(RJ45),including 4 Combo Ports,SFP Req,PoE,No Spell
h3cevtModuleSw-LSQ1GP24TEB0                OBJECT IDENTIFIER ::= { h3cevtModuleSwitchType 606 } -- 16-Port 1000BASE-X Gigabit Ethernet Optical Interface(SFP,LC)+8-Port Combo Interface Board
h3cevtModuleSw-LSQ1GP24TEB1                OBJECT IDENTIFIER ::= { h3cevtModuleSwitchType 607 } -- 16-Port 1000BASE-X Gigabit Ethernet Optical Interface(SFP,LC)+8-Port Combo Interface Board
h3cevtModuleSw-LSQ1GP24TSD0                OBJECT IDENTIFIER ::= { h3cevtModuleSwitchType 608 } -- 16-Port 1000BASE-X Gigabit Ethernet Optical Interface(SFP,LC)+8-Port Combo Interface Board
h3cevtModuleSw-LSQ1GP24TSD1                OBJECT IDENTIFIER ::= { h3cevtModuleSwitchType 609 } -- 16-Port 1000BASE-X Gigabit Ethernet Optical Interface(SFP,LC)+8-Port Combo Interface Board
h3cevtModuleSw-LSQ1GP24TXSD0               OBJECT IDENTIFIER ::= { h3cevtModuleSwitchType 610 } -- 16-Port GE Optical Interface(SFP,LC)+8-Port Combo Interface+2-Port 10GE Optical Interface Board(XFP,LC)
h3cevtModuleSw-LSQ1GP24TXSD1               OBJECT IDENTIFIER ::= { h3cevtModuleSwitchType 611 } -- 16-Port GE Optical Interface(SFP,LC)+8-Port Combo Interface+2-Port 10GE Optical Interface Board(XFP,LC)
h3cevtModuleSw-LSQ1TGX2EB0                 OBJECT IDENTIFIER ::= { h3cevtModuleSwitchType 612 } -- 2-Port 10GBASE Ethernet Optical Interface Board(XFP,LC)
h3cevtModuleSw-LSQ1TGX2EB1                 OBJECT IDENTIFIER ::= { h3cevtModuleSwitchType 613 } -- 2-Port 10GBASE Ethernet Optical Interface Board(XFP,LC)
h3cevtModuleSw-LSQ1TGX2SD0                 OBJECT IDENTIFIER ::= { h3cevtModuleSwitchType 614 } -- 2-Port 10GBASE Ethernet Optical Interface Board(XFP,LC)
h3cevtModuleSw-LSQ1TGX2SD1                 OBJECT IDENTIFIER ::= { h3cevtModuleSwitchType 615 } -- 2-Port 10GBASE Ethernet Optical Interface Board(XFP,LC)
h3cevtModuleSw-LSQ1TGX4SD0                 OBJECT IDENTIFIER ::= { h3cevtModuleSwitchType 616 } -- 4-Port 10GBASE Ethernet Optical Interface Board(XFP,LC)
h3cevtModuleSw-LSQ1TGX4SD1                 OBJECT IDENTIFIER ::= { h3cevtModuleSwitchType 617 } -- 4-Port 10GBASE Ethernet Optical Interface Board(XFP,LC)
h3cevtModuleSw-LSQ1TGX8SD0                 OBJECT IDENTIFIER ::= { h3cevtModuleSwitchType 618 } -- 8-Port 10GBASE Ethernet Optical Interface Board(XFP,LC)
h3cevtModuleSw-LSQ1TGX8SD1                 OBJECT IDENTIFIER ::= { h3cevtModuleSwitchType 619 } -- 8-Port 10GBASE Ethernet Optical Interface Board(XFP,LC)
h3cevtModuleSw-LSQ1GP48EB1                 OBJECT IDENTIFIER ::= { h3cevtModuleSwitchType 620 } -- 48-Port Enhanced 1000BASE-X Ethernet Optical Interface Board(SFP,LC)
h3cevtModuleSw-LSQ1TGX4EB0                 OBJECT IDENTIFIER ::= { h3cevtModuleSwitchType 621 } -- 4-Port 10GBASE Ethernet Optical Interface Board(XFP,LC)
h3cevtModuleSw-LSQ1TGX4EB1                 OBJECT IDENTIFIER ::= { h3cevtModuleSwitchType 622 } -- 4-Port 10GBASE Ethernet Optical Interface Board(XFP,LC)
h3cevtModuleSw-LSQ1GP12SC3                 OBJECT IDENTIFIER ::= { h3cevtModuleSwitchType 623 } -- 12-Port 1000BASE-X Ethernet Optical Interface Board(SFP,LC)
h3cevtModuleSw-LSQ1GP24TSC3                OBJECT IDENTIFIER ::= { h3cevtModuleSwitchType 624 } -- 16-Port 1000BASE-X Gigabit Ethernet Optical(SFP,LC) And 8-Port 10/100/1000BASE-T RJ45/1000BASE-X SFP Combo Interface Board
h3cevtModuleSw-LSQ1GP48SC3                 OBJECT IDENTIFIER ::= { h3cevtModuleSwitchType 625 } -- 48-Port 1000BASE Ethernet Optical Interface Board(SFP,LC)
h3cevtModuleSw-LSQ1GV48SC3                 OBJECT IDENTIFIER ::= { h3cevtModuleSwitchType 626 } -- 48-Port 1000Base-T Gigabit Ethernet Interface Board(RJ45),PoE
h3cevtModuleSw-LSQ1MPUA3                   OBJECT IDENTIFIER ::= { h3cevtModuleSwitchType 627 } -- Master Process Board
h3cevtModuleSw-LSQ1SRP1CB3                 OBJECT IDENTIFIER ::= { h3cevtModuleSwitchType 628 } -- Salience VI-Turbo
h3cevtModuleSw-LSQ1SRPA3                   OBJECT IDENTIFIER ::= { h3cevtModuleSwitchType 629 } -- Salience VI-Smart
h3cevtModuleSw-LSQ2FP48SA3                 OBJECT IDENTIFIER ::= { h3cevtModuleSwitchType 630 } -- 48 Port 100M Ethernet Optical Interface Board(SFP,LC)
h3cevtModuleSw-LSQ2FT48SA3                 OBJECT IDENTIFIER ::= { h3cevtModuleSwitchType 631 } -- 48-Port 100M Ethernet Electrical Interface Switch Unit(RJ45)
h3cevtModuleSw-LSQ1MPUB3                   OBJECT IDENTIFIER ::= { h3cevtModuleSwitchType 632 } -- Salience VI-Lite
h3cevtModuleSw-LSQ1CGP24TSC3               OBJECT IDENTIFIER ::= { h3cevtModuleSwitchType 633 } -- Switching and Routing Processing Unit with 24 1000BASE-X Gigabit Ethernet Optical Ports,including 8 Combo Ports,SFP Req.
h3cevtModuleSw-LSQ1MPUB4                   OBJECT IDENTIFIER ::= { h3cevtModuleSwitchType 634 } -- Salience VI-Lite
h3cevtModuleSw-LSQ1SRPD4                   OBJECT IDENTIFIER ::= { h3cevtModuleSwitchType 635 } -- Salience VI-Plus
h3cevtModuleSw-LSQ1SSLSC0                  OBJECT IDENTIFIER ::= { h3cevtModuleSwitchType 636 } -- SSL VPN Service Board(B)
h3cevtModuleSw-LSQ1LBSC0                   OBJECT IDENTIFIER ::= { h3cevtModuleSwitchType 637 } -- Gigabit Load Balancing Card
h3cevtModuleSw-LSQ1NAT24SC0                OBJECT IDENTIFIER ::= { h3cevtModuleSwitchType 638 } -- NAT/NetStream-Supported Line Processing Unit with 24 10/100/1000BASE-T Electrical Ports(RJ45),including Combo Ports,Upgradeable to PoE
h3cevtModuleSw-LSQ1SRP12GB4                OBJECT IDENTIFIER ::= { h3cevtModuleSwitchType 639 } -- Salience VI-GE
h3cevtModuleSw-LSQ1TGS8SC0                 OBJECT IDENTIFIER ::= { h3cevtModuleSwitchType 640 } -- 8-Port 10GBASE Ethernet SFP+ Optical Interface Board
h3cevtModuleSw-LSQ3PT4PSC0                 OBJECT IDENTIFIER ::= { h3cevtModuleSwitchType 641 } -- 4-Port 1000Base-PX Optical Line Terminal(EPON OLT SFP,SC)+8-Port 1000BASE-X Optical Interface Board(SFP,LC)
h3cevtModuleSw-EWPXM2MPUB0                 OBJECT IDENTIFIER ::= { h3cevtModuleSwitchType 642 } -- Salience VI-Lite
h3cevtModuleSw-EWPXM2SRP12GB0              OBJECT IDENTIFIER ::= { h3cevtModuleSwitchType 643 } -- Salience VI-GE
h3cevtModuleSw-EWPXM2SRPD0                 OBJECT IDENTIFIER ::= { h3cevtModuleSwitchType 644 } -- Salience VI-Plus
h3cevtModuleSw-EWPXM2GP24TSD0              OBJECT IDENTIFIER ::= { h3cevtModuleSwitchType 645 } -- 16-Port 1000BASE-X Ethernet Optical Interface(SFP Req.)+8-Port Combo Interface Module
h3cevtModuleSw-EWPXM2GP24TXSD0             OBJECT IDENTIFIER ::= { h3cevtModuleSwitchType 646 } -- 16-Port 1000BASE-X Ethernet Optical Interface(SFP Req.)+8-Port Combo Interface+2-Port 10GE Optical Interface(XFP Req.) Module
h3cevtModuleSw-EWPXM2TGX4SD0               OBJECT IDENTIFIER ::= { h3cevtModuleSwitchType 647 } -- 4-Port 10GBASE Ethernet Optical Interface Module,XFP Req
h3cevtModuleSw-EWPXM2GP48SD0               OBJECT IDENTIFIER ::= { h3cevtModuleSwitchType 648 } -- 48-Port 1000BASE-X Gigabit Ethernet Optical Interface Module,SFP Req
h3cevtModuleSw-EWPXM2GP24TSC0              OBJECT IDENTIFIER ::= { h3cevtModuleSwitchType 649 } -- 24-Port 1000BASE-X/100BASE-FX Optical  Interface Module,including 8 Combo Ports,SFP Req
h3cevtModuleSw-EWPXM2TGX2SC0               OBJECT IDENTIFIER ::= { h3cevtModuleSwitchType 650 } -- 2-Port 10GBASE Ethernet Optical Interface Module,XFP Req
h3cevtModuleSw-EWPXM2GP48SC0               OBJECT IDENTIFIER ::= { h3cevtModuleSwitchType 651 } -- 48-Port 1000BASE-X/100BASE-FX Ethernet Optical Interface Module,SFP Req
h3cevtModuleSw-LS7500-GP48-SC              OBJECT IDENTIFIER ::= { h3cevtModuleSwitchType 652 } -- 48-Port 1000BASE-X/100BASE-FX Ethernet Optical Interface Module(SFP,LC)
h3cevtModuleSw-LS7500-GP48-SD              OBJECT IDENTIFIER ::= { h3cevtModuleSwitchType 653 } -- 48-Port 1000BASE-X Gigabit Ethernet Optical Interface Module(SFP,LC)
h3cevtModuleSw-LS7500-GT48-SC              OBJECT IDENTIFIER ::= { h3cevtModuleSwitchType 654 } -- 48-Port 10/100/1000BASE-TX Ethernet Interface Module(RJ45)
h3cevtModuleSw-LS7500-GT48-SD              OBJECT IDENTIFIER ::= { h3cevtModuleSwitchType 655 } -- 48-Port 10/100/1000BASE-T Ethernet Interface Module(RJ45)
h3cevtModuleSw-LS7500-SRPG1                OBJECT IDENTIFIER ::= { h3cevtModuleSwitchType 656 } -- Main Control Unit
h3cevtModuleSw-LS7500-SRPG2                OBJECT IDENTIFIER ::= { h3cevtModuleSwitchType 657 } -- Salience VI-Lite
h3cevtModuleSw-LS7500-XP4-SD               OBJECT IDENTIFIER ::= { h3cevtModuleSwitchType 658 } -- 4-Port 10GBASE Ethernet Optical Interface Module(XFP,LC)
h3cevtModuleSw-LS7500-XP8-SD               OBJECT IDENTIFIER ::= { h3cevtModuleSwitchType 659 } -- 8-Port 10GBASE Ethernet Optical Interface Module(XFP,LC)
h3cevtModuleSw-LSQ4PT4PSC0                 OBJECT IDENTIFIER ::= { h3cevtModuleSwitchType 660 } -- 4-Port 1000Base-PX Optical Line Terminal(EPON OLT SFP,SC)+8-Port 1000BASE-X Optical Interface Board(SFP,LC)
h3cevtModuleSw-LSQ4PT8PSC0                 OBJECT IDENTIFIER ::= { h3cevtModuleSwitchType 661 } -- 8-Port 1000Base-PX Optical Line Terminal(EPON OLT SFP,SC)+8-Port 1000BASE-X Optical Interface Board(SFP,LC)
h3cevtModuleSw-LSQ4PT16PSC0                OBJECT IDENTIFIER ::= { h3cevtModuleSwitchType 662 } -- 16-Port 1000Base-PX Optical Line Terminal(EPON OLT SFP,SC)+8-Port 1000BASE-X Optical Interface Board(SFP,LC)
h3cevtModuleSw-LSQ1GP24TSA0                OBJECT IDENTIFIER ::= { h3cevtModuleSwitchType 663 } -- 16-Port 1000BASE-X Gigabit Ethernet Optical(SFP,LC) And 8-Port 10/100/1000BASE-T RJ45/1000BASE-X SFP Combo Interface Board
h3cevtModuleSw-LSQ1GV24PSA0                OBJECT IDENTIFIER ::= { h3cevtModuleSwitchType 664 } -- 24-Port 10/100/1000BASE-T Electrical(RJ45) Interface Board,including 4 Combo Ports,SFP Req,Upgradeable to PoE
h3cevtModuleSw-LSQ1SRPD3                   OBJECT IDENTIFIER ::= { h3cevtModuleSwitchType 665 } -- Salience VI-Plus
h3cevtModuleSw-LSQ1SUPA0                   OBJECT IDENTIFIER ::= { h3cevtModuleSwitchType 666 } -- Supervisor Engine Board
h3cevtModuleSw-LSU1FAB04A0                 OBJECT IDENTIFIER ::= { h3cevtModuleSwitchType 667 } -- Switch Fabric Board
h3cevtModuleSw-LSU1FAB08A0                 OBJECT IDENTIFIER ::= { h3cevtModuleSwitchType 668 } -- Switch Fabric Board
h3cevtModuleSw-LSU1TGS8EA0                 OBJECT IDENTIFIER ::= { h3cevtModuleSwitchType 669 } -- 8-Port 10GBASE Ethernet SFP+ Optical Interface Board(EA)
h3cevtModuleSw-LSU1TGS8EB0                 OBJECT IDENTIFIER ::= { h3cevtModuleSwitchType 670 } -- 8-Port 10GBASE Ethernet SFP+ Optical Interface Board
h3cevtModuleSw-LSU1TGS8SE0                 OBJECT IDENTIFIER ::= { h3cevtModuleSwitchType 671 } -- 8-Port 10GBASE Ethernet SFP+ Optical Interface Board(SE)
h3cevtModuleSw-LSUTGS16SC0                 OBJECT IDENTIFIER ::= { h3cevtModuleSwitchType 672 } -- 16-Port 10GBASE Ethernet SFP+ Optical Interface Board
h3cevtModuleSw-LSU1SUPA0                   OBJECT IDENTIFIER ::= { h3cevtModuleSwitchType 673 } -- Supervisor Engine Board
h3cevtModuleSw-LSU1GP24TXEA0               OBJECT IDENTIFIER ::= { h3cevtModuleSwitchType 674 } -- 16-Port 1000BASE-X Optical Interface(SFP,LC)+8-Port Combo Interface+2-Port 10GE Optical Interface Board(XFP,LC)(EA)
h3cevtModuleSw-LSU1GP24TXEB0               OBJECT IDENTIFIER ::= { h3cevtModuleSwitchType 675 } -- 16-Port 1000BASE-X Optical Interface(SFP,LC)+8-Port Combo Interface+2-Port 10GE Optical Interface Board(XFP,LC)(EB)
h3cevtModuleSw-LSU1GP24TXSE0               OBJECT IDENTIFIER ::= { h3cevtModuleSwitchType 676 } -- 16-Port 1000BASE-X Optical Interface(SFP,LC)+8-Port Combo Interface+2-Port 10GE Optical Interface Board(XFP,LC)(SE)
h3cevtModuleSw-LSU1GP48EA0                 OBJECT IDENTIFIER ::= { h3cevtModuleSwitchType 677 } -- 48-Port 1000BASE-X Gigabit Ethernet Optical Interface(SFP,LC) Interface Board(EA)
h3cevtModuleSw-LSU1GP48EB0                 OBJECT IDENTIFIER ::= { h3cevtModuleSwitchType 678 } -- 48-Port Enhanced 1000BASE-X Ethernet Optical Interface Board(SFP,LC)(EB)
h3cevtModuleSw-LSU1GP48SE0                 OBJECT IDENTIFIER ::= { h3cevtModuleSwitchType 679 } -- 48-Port 1000BASE Ethernet Optical Interface Board(SFP,LC)(SE)
h3cevtModuleSw-LSU1GT48EA0                 OBJECT IDENTIFIER ::= { h3cevtModuleSwitchType 680 } -- 48-Port 1000Base-T Gigabit Ethernet Interface Board(RJ45)(EA)
h3cevtModuleSw-LSU1GT48SE0                 OBJECT IDENTIFIER ::= { h3cevtModuleSwitchType 681 } -- 48-Port 1000Base-T Gigabit Ethernet Interface Board(RJ45)(SE)
h3cevtModuleSw-LSU1TGX4EA0                 OBJECT IDENTIFIER ::= { h3cevtModuleSwitchType 682 } -- 4-Port 10GBASE Ethernet Optical Interface Board(XFP,LC)(EA)
h3cevtModuleSw-LSU1TGX4EB0                 OBJECT IDENTIFIER ::= { h3cevtModuleSwitchType 683 } -- 4-Port 10GBASE Ethernet Optical Interface Board(XFP,LC)(EB)
h3cevtModuleSw-LSU1TGX4SE0                 OBJECT IDENTIFIER ::= { h3cevtModuleSwitchType 684 } -- 4-Port 10GBASE Ethernet Optical Interface Board(XFP,LC)(SE)
h3cevtModuleSw-LSQ1FAB08A0                 OBJECT IDENTIFIER ::= { h3cevtModuleSwitchType 685 } -- Switching Fabric Board
h3cevtModuleSw-EWPX2WCMD0                  OBJECT IDENTIFIER ::= { h3cevtModuleSwitchType 686 } -- Access Controller Card
h3cevtModuleSw-LSQ1WCMD0                   OBJECT IDENTIFIER ::= { h3cevtModuleSwitchType 687 } -- Access Controller Card
h3cevtModuleSw-LSQ1IAGSC0                  OBJECT IDENTIFIER ::= { h3cevtModuleSwitchType 688 } -- Wireless&IAG Service Card
h3cevtModuleSw-LSU1GP24TSE0                OBJECT IDENTIFIER ::= { h3cevtModuleSwitchType 689 } -- 16-Port 1000BASE-X Optical Interface(SFP,LC)+8-Port Combo Interface Board(SE)
h3cevtModuleSw-LSQ1TGS16SC0                OBJECT IDENTIFIER ::= { h3cevtModuleSwitchType 690 } -- 16-Port 10GBASE Ethernet SFP+ Optical Interface Board
h3cevtModuleSw-EWPX2TGS16SC0               OBJECT IDENTIFIER ::= { h3cevtModuleSwitchType 691 } -- 16-Port 10GBASE Ethernet SFP+ Optical Interface Board
h3cevtModuleSw-LSQ1SUPA3                   OBJECT IDENTIFIER ::= { h3cevtModuleSwitchType 692 } -- Supervisor Engine Board
h3cevtModuleSw-LSQ1FAB04A3                 OBJECT IDENTIFIER ::= { h3cevtModuleSwitchType 693 } -- 320G Switch Fabric Board
h3cevtModuleSw-LSQ1FAB08A3                 OBJECT IDENTIFIER ::= { h3cevtModuleSwitchType 694 } -- 640G Switch Fabric Board
h3cevtModuleSw-LSQ1GT48SC0                 OBJECT IDENTIFIER ::= { h3cevtModuleSwitchType 695 } -- 48-Port 1000Base-T Gigabit Ethernet Interface Board(RJ45)
h3cevtModuleSw-LSR2SRP2C1                  OBJECT IDENTIFIER ::= { h3cevtModuleSwitchType 696 } -- Management and Route Process Unit
h3cevtModuleSw-LSR2SRP2C2                  OBJECT IDENTIFIER ::= { h3cevtModuleSwitchType 697 } -- Management and Route Process Unit

--
-- 700 to 799 reserved for primary switches
--
h3cevtModuleSw-1000BASE-X-COMBO            OBJECT IDENTIFIER ::= { h3cevtModuleSwitchType 701 } -- Single port 10/100/1000BASE-T/1000BASE-X Combo Interface Board
h3cevtModuleSw-EPON-1000M                  OBJECT IDENTIFIER ::= { h3cevtModuleSwitchType 702 } -- Optical Network Unit Interface Board
h3cevtModuleSw-1000BASE-FIXED-2SFP-T-2RJ45         OBJECT IDENTIFIER ::= { h3cevtModuleSwitchType 703 } -- 2 port 10/100/1000BASE-T and 2 port 1000BASE-X Interface Board
h3cevtModuleSw-100M-1550-BIDI              OBJECT IDENTIFIER ::= { h3cevtModuleSwitchType 704 }  -- 100BASE-X BIDI Interface Board, Tx 1550nm, Rx 1310nm
h3cevtModuleSw-100M-1310-BIDI              OBJECT IDENTIFIER ::= { h3cevtModuleSwitchType 705 }  -- 100BASE-X reverse Interface Board, Tx 1310nm, Rx 1550nm
h3cevtModuleSw-1000BASE-FIXED-4RJ45-4SFP-COMBO     OBJECT IDENTIFIER ::= { h3cevtModuleSwitchType 706 } -- 4 port 10/100/1000BASE-T and 4 port 1000BASE-X COMBO Interface Board
h3cevtModuleSw-LSH1PK2T                    OBJECT IDENTIFIER ::= { h3cevtModuleSwitchType 707 } -- OSM Interface Board
h3cevtModuleSw-LSPM2GP2P                   OBJECT IDENTIFIER ::= { h3cevtModuleSwitchType 708 } -- 2-Port 1000BASE-X SFP Module
h3cevtModuleSw-LSWM1GT16P                  OBJECT IDENTIFIER ::= { h3cevtModuleSwitchType 709 } -- 16-Port 10/100/1000BASE-T Ethernet Electrical Interface Module
h3cevtModuleSw-LSWM1GP16P                  OBJECT IDENTIFIER ::= { h3cevtModuleSwitchType 710 } -- 16-Port 100/1000BASE-X Ethernet Optical Interface Module
h3cevtModuleSw-LSWM1XP2P                   OBJECT IDENTIFIER ::= { h3cevtModuleSwitchType 711 } -- 2-Port 10G Ethernet XFP Optical Interface Module
h3cevtModuleSw-LSWM1XP4P                   OBJECT IDENTIFIER ::= { h3cevtModuleSwitchType 712 } -- 4-Port 10G Ethernet XFP Optical Interface Module
h3cevtModuleSw-LSWM1SP2P                   OBJECT IDENTIFIER ::= { h3cevtModuleSwitchType 713 } -- 2-Port 10G Ethernet SFP PLUS Optical Interface Module
h3cevtModuleSw-LSWM1SP4P                   OBJECT IDENTIFIER ::= { h3cevtModuleSwitchType 714 } -- 4-Port 10G Ethernet SFP PLUS Optical Interface Module
h3cevtModuleSw-LSWM148POEM                 OBJECT IDENTIFIER ::= { h3cevtModuleSwitchType 715 } -- 48 Port Mid Power PoE Module
h3cevtModuleSw-LSWM1FW10                   OBJECT IDENTIFIER ::= { h3cevtModuleSwitchType 716 } -- RMI CPU XLR 732, with Firewall software
h3cevtModuleSw-LSWM1WCM10                  OBJECT IDENTIFIER ::= { h3cevtModuleSwitchType 717 } -- RMI CPU XLR 732, with Wireless Access Controller software
h3cevtModuleSw-LSWM1IPS10                  OBJECT IDENTIFIER ::= { h3cevtModuleSwitchType 718 } -- RMI CPU XLR 732, with IPS/AV software
h3cevtModuleSw-LSWM1WCM20                  OBJECT IDENTIFIER ::= { h3cevtModuleSwitchType 719 } -- RMI CPU XLR 408, with Wireless Access Controller software
h3cevtModuleSw-IPS-T1000-M                 OBJECT IDENTIFIER ::= { h3cevtModuleSwitchType 720 } -- IPS for T1000-M mainboard module
h3cevtModuleSw-IPS-T1000-A                 OBJECT IDENTIFIER ::= { h3cevtModuleSwitchType 721 } -- IPS for T1000-A mainboard module
h3cevtModuleSw-IPS-T1000-S                 OBJECT IDENTIFIER ::= { h3cevtModuleSwitchType 722 } -- IPS for T1000-S mainboard module
h3cevtModuleSw-IPS-GX4C                    OBJECT IDENTIFIER ::= { h3cevtModuleSwitchType 723 } -- four-port-gigabit-fiber-board－module
h3cevtModuleSw-IPS-GT4C                    OBJECT IDENTIFIER ::= { h3cevtModuleSwitchType 724 } -- four-port-1000BASET-board－module
h3cevtModuleSw-LSPM2SP2P                   OBJECT IDENTIFIER ::= { h3cevtModuleSwitchType 725 } -- 2-Port 10G Ethernet SFP PLUS Optical Interface Module
h3cevtModuleSw-LSPM2SP2PA                  OBJECT IDENTIFIER ::= { h3cevtModuleSwitchType 726 } -- 2-Port Second Version SFP+ Module
h3cevtModuleSw-LSP5GP8P                    OBJECT IDENTIFIER ::= { h3cevtModuleSwitchType 727 } -- 8-Port 1G Ethernet SFP Optical Interface Module
h3cevtModuleSw-LSP5GT8P                    OBJECT IDENTIFIER ::= { h3cevtModuleSwitchType 728 } -- 8-Port 10/100/1000BASE-T Ethernet Electrical Interface Module
h3cevtModuleSw-LSWM1FC4P                   OBJECT IDENTIFIER ::= { h3cevtModuleSwitchType 729 } -- 4-Port 8G Fibre Channel Interface Module
h3cevtModuleSw-LSW1XGT4P0                  OBJECT IDENTIFIER ::= { h3cevtModuleSwitchType 730 } -- 4-Port 10G Ethernet Copper Interface Module
h3cevtModuleSw-LSW1XGT2P0                  OBJECT IDENTIFIER ::= { h3cevtModuleSwitchType 731 } -- 2-Port 10G Ethernet Copper Interface Module
h3cevtModuleSw-LSP1XGT2P                   OBJECT IDENTIFIER ::= { h3cevtModuleSwitchType 732 } -- 2-Port 10G Ethernet Copper Interface Board
h3cevtModuleSw-LSPM3XGT2P                  OBJECT IDENTIFIER ::= { h3cevtModuleSwitchType 733 } -- 2-Port 1/10G BASE-T Ethernet Copper Interface Module
h3cevtModuleSw-LSWM2QP2P                   OBJECT IDENTIFIER ::= { h3cevtModuleSwitchType 734 } -- 2-Port QSFP+ Interface Module
h3cevtModuleSw-LSWM2XGT2PM                 OBJECT IDENTIFIER ::= { h3cevtModuleSwitchType 735 } -- 2-Port 10G Ethernet Copper Interface Module with MACsec
h3cevtModuleSw-LSWM2SP2PM                  OBJECT IDENTIFIER ::= { h3cevtModuleSwitchType 736 } -- 2-Port SFP+ Interface Module with MACsec
h3cevtModuleSw-LSWM2SP8PM                  OBJECT IDENTIFIER ::= { h3cevtModuleSwitchType 737 } -- 8-Port SFP+ Interface Module with MACsec
h3cevtModuleSw-LSWM2SP8P                   OBJECT IDENTIFIER ::= { h3cevtModuleSwitchType 738 } -- 8-Port SFP+ Interface Module
h3cevtModuleSw-LSWM2XGT8PM                 OBJECT IDENTIFIER ::= { h3cevtModuleSwitchType 739 } -- 8-Port 10G Ethernet Copper Interface Module with MACsec
h3cevtModuleSw-LSWM18QC                    OBJECT IDENTIFIER ::= { h3cevtModuleSwitchType 740 } -- 8-Port QSFP+ Module
h3cevtModuleSw-LSWM124XG2Q                 OBJECT IDENTIFIER ::= { h3cevtModuleSwitchType 741 } -- 24-Port SFP+ and 2-Port QSFP+ Module
h3cevtModuleSw-LSWM124XGT2Q                OBJECT IDENTIFIER ::= { h3cevtModuleSwitchType 742 } -- 24-Port 10G BASE-T and 2-Port QSFP+ Module
h3cevtModuleSw-LSWM124XG2QL                OBJECT IDENTIFIER ::= { h3cevtModuleSwitchType 743 } -- 24-Port SFP+ and 2-Port QSFP+ Module
h3cevtModuleSw-LSWM124XG2QFC               OBJECT IDENTIFIER ::= { h3cevtModuleSwitchType 744 } -- 24-Port 8G Fibre Channel Interface and 2-Port QSFP+ Module
h3cevtModuleSw-LSWM18QC0                   OBJECT IDENTIFIER ::= { h3cevtModuleSwitchType 745 } -- 8-Port QSFP+ Module
h3cevtModuleSw-LSWM124XGT2Q0               OBJECT IDENTIFIER ::= { h3cevtModuleSwitchType 746 } -- 24-Port 10G BASE-T and 2-Port QSFP+ Module
h3cevtModuleSw-LSWM124XG2QL0               OBJECT IDENTIFIER ::= { h3cevtModuleSwitchType 747 } -- 24-Port SFP+ and 2-Port QSFP+ Module
h3cevtModuleSw-LSP6G4T6P                   OBJECT IDENTIFIER ::= { h3cevtModuleSwitchType 748 } -- 6-Port SFP and 2-port 10/100/1000BASE-T COMBO and 2 port 10/100/1000BASE-T Interface Module
h3cevtModuleSw-LSPM6QP2PS                  OBJECT IDENTIFIER ::= { h3cevtModuleSwitchType 749 } -- 2-Port QSFP+ Stack Interface Module
h3cevtModuleSw-LSWM12H2Q                   OBJECT IDENTIFIER ::= { h3cevtModuleSwitchType 750 } -- 2-Port QSFP28 and 2-Port QSFP+ Module
h3cevtModuleSw-LSWM18CQ                    OBJECT IDENTIFIER ::= { h3cevtModuleSwitchType 751 } -- 8-Port QSFP28 Module
h3cevtModuleSw-LSWM116Q                    OBJECT IDENTIFIER ::= { h3cevtModuleSwitchType 752 } -- 16-Port QSFP+ Module
h3cevtModuleSw-LSPM6FWD                    OBJECT IDENTIFIER ::= { h3cevtModuleSwitchType 753 } -- Next Generation Firewall Module
h3cevtModuleSw-DS-3E-2XT-H                 OBJECT IDENTIFIER ::= { h3cevtModuleSwitchType 754 } -- 2-Port 10G Ethernet Copper Interface Module with MACsec
h3cevtModuleSw-DS-3E-2XF-H                 OBJECT IDENTIFIER ::= { h3cevtModuleSwitchType 755 } -- 2-Port SFP+ Interface Module with MACsec
h3cevtModuleSw-DS-3E-2QX-H                 OBJECT IDENTIFIER ::= { h3cevtModuleSwitchType 756 } -- 2-Port QSFP+ Stack Interface Module
h3cevtModuleSw-LSPM4G4T6P                  OBJECT IDENTIFIER ::= { h3cevtModuleSwitchType 757 } -- 6-Port SFP and 2-port 10/100/1000BASE-T COMBO and 2 port 10/100/1000BASE-T Interface Module
h3cevtModuleSw-LSWM4SP8PM                  OBJECT IDENTIFIER ::= { h3cevtModuleSwitchType 758 } -- 8-Port SFP+ Interface Module with MACsec
h3cevtModuleSw-LSWM124TG2H                 OBJECT IDENTIFIER ::= { h3cevtModuleSwitchType 759 } -- 24-Port SFP28 and 2-Port QSFP28 Module
h3cevtModuleSw-LSWM18CQ0                   OBJECT IDENTIFIER ::= { h3cevtModuleSwitchType 760 } -- 8-Port QSFP28 Module
h3cevtModuleSw-LSWM116Q0                   OBJECT IDENTIFIER ::= { h3cevtModuleSwitchType 761 } -- 16-Port QSFP+ Module
h3cevtModuleSw-LSWM124TG2H0                OBJECT IDENTIFIER ::= { h3cevtModuleSwitchType 762 } -- 24-Port SFP28 and 2-Port QSFP28 Module
h3cevtModuleSw-LSWM2ZQP2P                  OBJECT IDENTIFIER ::= { h3cevtModuleSwitchType 763 } -- 2-Port QSFP28 Module
h3cevtModuleSw-LSWM2ZSP8P                  OBJECT IDENTIFIER ::= { h3cevtModuleSwitchType 764 } -- 8-Port SFP28 Module
h3cevtModuleSw-LSWM18CQMSEC                OBJECT IDENTIFIER ::= { h3cevtModuleSwitchType 765 } -- 8-Port QSFP28 MACSEC Module
h3cevtModuleSw-LSWM2MGT8P                  OBJECT IDENTIFIER ::= { h3cevtModuleSwitchType 766 } -- 8-Port SmartGE (5/2.5/1G) Interface Module
h3cevtModuleSw-LSWM2XMGT8P                 OBJECT IDENTIFIER ::= { h3cevtModuleSwitchType 767 } -- 8-Port SmartGE (10/5/2.5/1G) Interface Module
h3cevtModuleSw-LSWM2ZSP2P                  OBJECT IDENTIFIER ::= { h3cevtModuleSwitchType 768 } -- 2-Port SFP28 Interface Module
h3cevtModuleSw-LSWM116FC                   OBJECT IDENTIFIER ::= { h3cevtModuleSwitchType 769 } -- 16-Ports SFP28 Ethernet Optical Interface Module with 16G/32G FC
h3cevtModuleSw-LSWM216FC                   OBJECT IDENTIFIER ::= { h3cevtModuleSwitchType 770 } -- 16-Ports SFP28 Ethernet Optical Interface Module with 16G/32G FC
h3cevtModuleSw-LSWM2SP2PB                  OBJECT IDENTIFIER ::= { h3cevtModuleSwitchType 771 } -- 2-Port SFP+ Interface Module
h3cevtModuleSw-LSWM2SP4PB                  OBJECT IDENTIFIER ::= { h3cevtModuleSwitchType 772 } -- 4-Port SFP+ Interface Module
h3cevtModuleSw-LSWM2SP24P                  OBJECT IDENTIFIER ::= { h3cevtModuleSwitchType 773 } -- 24-Port SFP+ Interface Module
h3cevtModuleSw-LSWM2SP12P2Q                OBJECT IDENTIFIER ::= { h3cevtModuleSwitchType 774 } -- 12-Port SFP+ and 2-Port QSFP+ Interface Module
h3cevtModuleSw-LSWM2SP12P2QA               OBJECT IDENTIFIER ::= { h3cevtModuleSwitchType 775 } -- 12-Port SFP+ and 2-Port QSFP+ Interface Module with wider size

--
-- 800 to 899 reserved for WLAN products
--
h3cevtModuleSw-WX5002MPU                   OBJECT IDENTIFIER ::= { h3cevtModuleSwitchType 800 } -- Wireless Lan Control Board with 2-port 1000BASE-T/1000BASE-X Combo Interface
h3cevtModuleSw-LS8M1WCMA                   OBJECT IDENTIFIER ::= { h3cevtModuleSwitchType 801 } -- Wireless Lan Service Board
h3cevtModuleSw-EWPX1G24XA0                 OBJECT IDENTIFIER ::= { h3cevtModuleSwitchType 802 } -- 24-Port 1000BASE-T Gigabit Ethernet Interface(RJ45) and 4-port 1000BASE-T/1000BASE-X Combo Interface and 2-port 10GBASE Interface Line Card
h3cevtModuleSw-LSQ1WCMB0                   OBJECT IDENTIFIER ::= { h3cevtModuleSwitchType 803 } -- 1 Port 10GBASE Interface Board
h3cevtModuleSw-LSB1WCM2A0                  OBJECT IDENTIFIER ::= { h3cevtModuleSwitchType 804 } -- Wireless Controller Module Board
h3cevtModuleSw-EWPX1WCMB0                  OBJECT IDENTIFIER ::= { h3cevtModuleSwitchType 805 } -- 1 Port 10GBASE Interface Board
h3cevtModuleSw-EWPX1G24XC0                 OBJECT IDENTIFIER ::= { h3cevtModuleSwitchType 806 } -- 24-Port 1000BASE-T Gigabit Ethernet Interface(RJ45) and 4-port 1000BASE-T/1000BASE-X Combo Interface Line Card
h3cevtModuleSw-EWPX1WCMC0                  OBJECT IDENTIFIER ::= { h3cevtModuleSwitchType 807 } -- 1-Port 1000BASE-T Gigabit Ethernet of wireless Lan Service Board
h3cevtModuleSw-EWPX1FWA0                   OBJECT IDENTIFIER ::= { h3cevtModuleSwitchType 808 } -- Firewall Service Board
h3cevtModuleSw-EWPX1G10XC0                 OBJECT IDENTIFIER ::= { h3cevtModuleSwitchType 809 } -- 8-Port 1000BASE-T Gigabit Ethernet Interface(RJ45) and 2-port 1000BASE-X SFP Interface Line Card
h3cevtModuleSw-EWPX1WCM10C0                OBJECT IDENTIFIER ::= { h3cevtModuleSwitchType 810 } -- 1-Port 1000BASE-T Gigabit Ethernet of wireless Lan Service Board
h3cevtModuleSw-LSR1WCM2A1                  OBJECT IDENTIFIER ::= { h3cevtModuleSwitchType 811 } -- 1-Port 1000BASE-T Gigabit Ethernet of wireless Lan Service Board
h3cevtModuleSw-EWPX1WAP0                   OBJECT IDENTIFIER ::= { h3cevtModuleSwitchType 812 } -- Encryption Card
h3cevtModuleSw-EWPX1WCMD0                  OBJECT IDENTIFIER ::= { h3cevtModuleSwitchType 813 } -- 2 Port 10GBASE Interface Board
h3cevtModuleSw-EWPX1G24XCE0                OBJECT IDENTIFIER ::= { h3cevtModuleSwitchType 814 } -- 24-Port 1000BASE-T Gigabit Ethernet Interface(RJ45) and 4-port 1000BASE-T/1000BASE-X Combo Interface Line Card
h3cevtModuleSw-EWPX1WCMCE0                 OBJECT IDENTIFIER ::= { h3cevtModuleSwitchType 815 } -- 2-Port 1000BASE-T Gigabit Ethernet of wireless Lan Service Board
h3cevtModuleSw-EWPX1G24XD0                 OBJECT IDENTIFIER ::= { h3cevtModuleSwitchType 816 } -- 4-Port 10GBASE-T and 24-Port 1000BASE-T Gigabit Ethernet of wireless Lan Service Board

--
-- 900 to 1199 reserved for advanced switches part II
--
h3cevtModuleSw-LSR1DRSP2L1                 OBJECT IDENTIFIER ::= { h3cevtModuleSwitchType 900 } -- 2-Port OC-48c/STM-16c RPR Optical Interface Card,(SFP,LC)
h3cevtModuleSw-PIC-CLF2G8L                 OBJECT IDENTIFIER ::= { h3cevtModuleSwitchType 901 } -- 2-Port 155M CPOS Optical Interface(SFP,LC)+8-Port 1000BASE-X Optical Interface Card(SFP,LC)
h3cevtModuleSw-PIC-CLF4G8L                 OBJECT IDENTIFIER ::= { h3cevtModuleSwitchType 902 } -- 4-Port 155M CPOS Optical Interface(SFP,LC)+8-Port 1000BASE-X Optical Interface Card(SFP,LC)
h3cevtModuleSw-SR02SRP2F3                  OBJECT IDENTIFIER ::= { h3cevtModuleSwitchType 903 } -- Routing Switch Processing Board(2F)
h3cevtModuleSw-SR02SRP1F3                  OBJECT IDENTIFIER ::= { h3cevtModuleSwitchType 904 } -- Routing Switch Processing Board(1F)
h3cevtModuleSw-LST1GT48LEA1                OBJECT IDENTIFIER ::= { h3cevtModuleSwitchType 905 } -- 48-Port 10/100/1000BASE-T Interface Module(LEA),(RJ45)
h3cevtModuleSw-LST1GP48LEA1                OBJECT IDENTIFIER ::= { h3cevtModuleSwitchType 906 } -- 48-Port 1000BASE-X Interface Module(LEA),(SFP,LC)
h3cevtModuleSw-LST2XP8LEA1                 OBJECT IDENTIFIER ::= { h3cevtModuleSwitchType 907 } -- 8-Port 10GBASE-R Interface Module(LEA),(SFP+,LC)
h3cevtModuleSw-LST1GT48LEY1                OBJECT IDENTIFIER ::= { h3cevtModuleSwitchType 908 } -- 48-Port 10/100/1000BASE-T Interface Module(LEY),(RJ45)
h3cevtModuleSw-LST1GP48LEY1                OBJECT IDENTIFIER ::= { h3cevtModuleSwitchType 909 } -- 48-Port 1000BASE-X Interface Module(LEY),(SFP,LC)
h3cevtModuleSw-LST1XP32REY1                OBJECT IDENTIFIER ::= { h3cevtModuleSwitchType 910 } -- 32-Port 10GBASE-R Interface Module(REY),(SFP+,LC)
h3cevtModuleSw-LST1XP8LEY1                 OBJECT IDENTIFIER ::= { h3cevtModuleSwitchType 911 } -- 8-Port 10GBASE-R/W Interface Module(LEY),(XFP,LC)
h3cevtModuleSw-LST1GP48LEZ1                OBJECT IDENTIFIER ::= { h3cevtModuleSwitchType 912 } -- 48-Port 1000BASE-X Interface Module(LEZ),(SFP,LC)
h3cevtModuleSw-LST1XP8LEZ1                 OBJECT IDENTIFIER ::= { h3cevtModuleSwitchType 913 } -- 8-Port 10GBASE-R/W Interface Module(LEZ),(XFP,LC)
h3cevtModuleSw-IM-FW-II                    OBJECT IDENTIFIER ::= { h3cevtModuleSwitchType 914 } -- Firewall Service Processing Board-II
h3cevtModuleSw-IM-IPS                      OBJECT IDENTIFIER ::= { h3cevtModuleSwitchType 915 } -- Intrusion Prevention System Service Processing Board
h3cevtModuleSw-IM-SSL                      OBJECT IDENTIFIER ::= { h3cevtModuleSwitchType 916 } -- SSL VPN Service Processing Board
h3cevtModuleSw-IM-LB                       OBJECT IDENTIFIER ::= { h3cevtModuleSwitchType 917 } -- Load Balance Service Processing Board
h3cevtModuleSw-IM-ACG                      OBJECT IDENTIFIER ::= { h3cevtModuleSwitchType 918 } -- Application Control Gateway Service Processing Board
h3cevtModuleSw-LSR1XP16REC1                OBJECT IDENTIFIER ::= { h3cevtModuleSwitchType 919 } -- 16-Port 10GBASE-R Interface Module(REC),(SFP+,LC)
h3cevtModuleSw-LST2XP8LEB1                 OBJECT IDENTIFIER ::= { h3cevtModuleSwitchType 920 } -- 8-Port 10GBASE-R/W Interface Module(LEB),(XFP,LC)
h3cevtModuleSw-LST2XP8LEC1                 OBJECT IDENTIFIER ::= { h3cevtModuleSwitchType 921 } -- 8-Port 10GBASE-R/W Interface Module(LEC),(XFP,LC)
h3cevtModuleSw-LST2XP8LEF1                 OBJECT IDENTIFIER ::= { h3cevtModuleSwitchType 922 } -- 8-Port 10GBASE-R/W Interface Module(LEF),(XFP,LC)
h3cevtModuleSw-LSR2XP4LEB1                 OBJECT IDENTIFIER ::= { h3cevtModuleSwitchType 923 } -- 4-Port 10GBase-R/W Interface Module(LEB),(XFP,LC)
h3cevtModuleSw-LSR2XP4LEC1                 OBJECT IDENTIFIER ::= { h3cevtModuleSwitchType 924 } -- 4-Port 10GBase-R/W Interface Module(LEC),(XFP,LC)
h3cevtModuleSw-LST2XP32REB1                OBJECT IDENTIFIER ::= { h3cevtModuleSwitchType 925 } -- 32-Port 10GBASE-R Interface Module(REB),(SFP+,LC)
h3cevtModuleSw-LST2XP32REC1                OBJECT IDENTIFIER ::= { h3cevtModuleSwitchType 926 } -- 32-Port 10GBASE-R Interface Module(REC),(SFP+,LC)
h3cevtModuleSw-LSR1WCM3A1                  OBJECT IDENTIFIER ::= { h3cevtModuleSwitchType 927 } -- Access Controller Module
h3cevtModuleSw-LST1XP16LEB1                OBJECT IDENTIFIER ::= { h3cevtModuleSwitchType 928 } -- 16-Port 10GBASE-R Interface Module (LEB),(SFP+,LC)
h3cevtModuleSw-LST1XP16LEC1                OBJECT IDENTIFIER ::= { h3cevtModuleSwitchType 929 } -- 16-Port 10GBASE-R Interface Module (LEC),(SFP+,LC)
h3cevtModuleSw-CR-SPC-XP4L-E-I             OBJECT IDENTIFIER ::= { h3cevtModuleSwitchType 930 } -- 4-Port 10GBASE-R/W Optical Interface Module,(XFP,LC)
h3cevtModuleSw-LST2MRPNC1                  OBJECT IDENTIFIER ::= { h3cevtModuleSwitchType 931 } -- Management and Route Process Unit
h3cevtModuleSw-LST2SF08C1                  OBJECT IDENTIFIER ::= { h3cevtModuleSwitchType 932 } -- Switch Fabric Card
h3cevtModuleSw-LST2SF18C1                  OBJECT IDENTIFIER ::= { h3cevtModuleSwitchType 933 } -- Switch Fabric Card
h3cevtModuleSw-SR02SRP2G3                  OBJECT IDENTIFIER ::= { h3cevtModuleSwitchType 934 } -- Routing Switch Processing Board(2G)
h3cevtModuleSw-CR-SPE-3020-E-I             OBJECT IDENTIFIER ::= { h3cevtModuleSwitchType 935 } -- CR15LN3CNA1, Dual Service Processing Board
h3cevtModuleSw-CR-SPC-PUP4L-E-I            OBJECT IDENTIFIER ::= { h3cevtModuleSwitchType 936 } -- 4-Port 10G POS Optical Interface Board(Enhanced),(XFP,LC)
h3cevtModuleSw-CR-SPC-XP4LEF-I             OBJECT IDENTIFIER ::= { h3cevtModuleSwitchType 937 } -- 4-Port 10GBASE-R/W Interface Module (LEF),(XFP,LC)
h3cevtModuleSw-CR-SPC-XP8LEF-I             OBJECT IDENTIFIER ::= { h3cevtModuleSwitchType 938 } -- 8-Port 10GBASE-R/W Interface Module (LEF),(XFP,LC)
h3cevtModuleSw-LST3XP8LEB1                 OBJECT IDENTIFIER ::= { h3cevtModuleSwitchType 939 } -- 8-Port 10GBASE-R Interface Module (LEB),(XFP,LC)
h3cevtModuleSw-LST3XP8LEC1                 OBJECT IDENTIFIER ::= { h3cevtModuleSwitchType 940 } -- 8-Port 10GBASE-R Interface Module (LEC),(XFP,LC)
h3cevtModuleSw-LST1FW3A1                   OBJECT IDENTIFIER ::= { h3cevtModuleSwitchType 941 } -- Firewall Board
h3cevtModuleSw-CR-IM-NAM1A                 OBJECT IDENTIFIER ::= { h3cevtModuleSwitchType 942 } -- CR1M1NAM1A1, Network Analysis Service Module, Domestic&Overseas Version
h3cevtModuleSw-LSR2SRP2B1                  OBJECT IDENTIFIER ::= { h3cevtModuleSwitchType 943 } -- Management and Route Process Unit
h3cevtModuleSw-LSR2SRP2B2                  OBJECT IDENTIFIER ::= { h3cevtModuleSwitchType 944 } -- Management and Route Process Unit
h3cevtModuleSw-LSR2SRP2D1                  OBJECT IDENTIFIER ::= { h3cevtModuleSwitchType 945 } -- Management and Route Process Unit
h3cevtModuleSw-LST3XP8LEY1                 OBJECT IDENTIFIER ::= { h3cevtModuleSwitchType 946 } -- 8-Port 10GBASE-R/W Interface Module (LEY),(XFP,LC)
h3cevtModuleSw-LST2XP32REY1                OBJECT IDENTIFIER ::= { h3cevtModuleSwitchType 947 } -- 32-Port 10GBASE-R Interface Module(REY),(SFP+,LC)
h3cevtModuleSw-LST1XP16LEY1                OBJECT IDENTIFIER ::= { h3cevtModuleSwitchType 948 } -- 16-Port 10GBASE-R Interface Module (LEY),(SFP+,LC)
h3cevtModuleSw-SR0M2SRP2G3                 OBJECT IDENTIFIER ::= { h3cevtModuleSwitchType 949 } -- Routing Switch Processing Board(2G)
h3cevtModuleSw-SR0M2SRP1G3                 OBJECT IDENTIFIER ::= { h3cevtModuleSwitchType 950 } -- Routing Switch Processing Board(1G)
h3cevtModuleSw-SPC-GP48LA                  OBJECT IDENTIFIER ::= { h3cevtModuleSwitchType 951 } -- 48-Port 1000BASE-X Interface Service Module,(SFP,LC)
h3cevtModuleSw-SPC-GT48LA                  OBJECT IDENTIFIER ::= { h3cevtModuleSwitchType 952 } -- 48-Port 10/100/1000BASE-T Interface Service Module,(RJ45)
h3cevtModuleSw-SPC-XP4LA                   OBJECT IDENTIFIER ::= { h3cevtModuleSwitchType 953 } -- 4-Port 10GBase-R/W Interface Service Module,(XFP,LC)
h3cevtModuleSw-SPC-XP2LA                   OBJECT IDENTIFIER ::= { h3cevtModuleSwitchType 954 } -- 2-Port 10GBASE-R/W Interface Service Module,(XFP,LC)
h3cevtModuleSw-SPC-GP24LA                  OBJECT IDENTIFIER ::= { h3cevtModuleSwitchType 955 } -- 16-Port 1000BASE-X Interface(SFP,LC)+8-Port Combo Interface Service Module
h3cevtModuleSw-SPC-XP16RA                  OBJECT IDENTIFIER ::= { h3cevtModuleSwitchType 956 } -- 16-Port 10GBASE-R Optical Interface Service Module(RA),(SFP+,LC)
h3cevtModuleSw-CR-IM-FW1A                  OBJECT IDENTIFIER ::= { h3cevtModuleSwitchType 957 } -- Firewall Service Processing Board
h3cevtModuleSw-SPC-XP16R                   OBJECT IDENTIFIER ::= { h3cevtModuleSwitchType 958 } -- 16-Port 10GBASE-R Optical Interface Service Module(R),(SFP+,LC)
h3cevtModuleSw-CR-IM-LB1A                  OBJECT IDENTIFIER ::= { h3cevtModuleSwitchType 959 } -- Load Balancing Service Processing Board
h3cevtModuleSw-LST1GT48LEC2                OBJECT IDENTIFIER ::= { h3cevtModuleSwitchType 960 } -- 48-Port 10/100/1000BASE-T Interface Module(LEC),(RJ45)
h3cevtModuleSw-LST1GP48LEC2                OBJECT IDENTIFIER ::= { h3cevtModuleSwitchType 961 } -- 48-Port 1000BASE-X Interface Module (LEC),(SFP,LC)
h3cevtModuleSw-LST1XP16LEC2                OBJECT IDENTIFIER ::= { h3cevtModuleSwitchType 962 } -- 16-Port 10GBASE-R Interface Module (LEC),(SFP+,LC)
h3cevtModuleSw-LST2XP8LEC2                 OBJECT IDENTIFIER ::= { h3cevtModuleSwitchType 963 } -- 8-Port 10GBASE-R/W Interface Module(LEC),(XFP,LC)
h3cevtModuleSw-LST2XP32REC2                OBJECT IDENTIFIER ::= { h3cevtModuleSwitchType 964 } -- 32-Port 10GBASE-R Interface Module(REC),(SFP+,LC)
h3cevtModuleSw-CR-IM-MAC1A                 OBJECT IDENTIFIER ::= { h3cevtModuleSwitchType 965 } -- Master Access Control Service Module
h3cevtModuleSw-LST1XP48LFD1                OBJECT IDENTIFIER ::= { h3cevtModuleSwitchType 966 } -- 48-Port 10GBASE-R Interface Module (LFD),(SFP+,LC)
h3cevtModuleSw-LST1XP40RFD1                OBJECT IDENTIFIER ::= { h3cevtModuleSwitchType 967 } -- 40-Port 10GBASE-R Interface Module (RFD),(SFP+,LC)
h3cevtModuleSw-LST1XP40RFG1                OBJECT IDENTIFIER ::= { h3cevtModuleSwitchType 968 } -- 40-Port 10GBASE-R/W Interface Module (RFG),(SFP+,LC)
h3cevtModuleSw-LST1XLP16RFD1               OBJECT IDENTIFIER ::= { h3cevtModuleSwitchType 969 } -- 16-Port 40GBASE-R Interface Module (RFD),(QSFP+,LC)
h3cevtModuleSw-LST1CP4RFD1                 OBJECT IDENTIFIER ::= { h3cevtModuleSwitchType 970 } -- 4-Port 100GBASE-R Interface Module (RFD),(CFP,LC)
h3cevtModuleSw-LST1CP4RFG1                 OBJECT IDENTIFIER ::= { h3cevtModuleSwitchType 971 } -- 4-Port 100GBASE-R Interface Module (RFG),(CFP,LC)
h3cevtModuleSw-LST1SF08E1                  OBJECT IDENTIFIER ::= { h3cevtModuleSwitchType 972 } -- Switch Fabric Card
h3cevtModuleSw-LST1SF18E1                  OBJECT IDENTIFIER ::= { h3cevtModuleSwitchType 973 } -- Switch Fabric Card
h3cevtModuleSw-LST1MRPNE1                  OBJECT IDENTIFIER ::= { h3cevtModuleSwitchType 974 } -- Management and Route Process Unit
h3cevtModuleSw-LSX1CGX8FC0                 OBJECT IDENTIFIER ::= { h3cevtModuleSwitchType 975 } -- 8-Port 100GBASE-R Interface Module (FC),(CXP,MPO)
h3cevtModuleSw-LSX1CGX8FC1                 OBJECT IDENTIFIER ::= { h3cevtModuleSwitchType 976 } -- 8-Port 100GBASE-R Interface Module (FC),(CXP,MPO)
h3cevtModuleSw-LSX1QGS24FC0                OBJECT IDENTIFIER ::= { h3cevtModuleSwitchType 977 } -- 24-Port 40GBASE-R Interface Module (FC),(QSFP+)
h3cevtModuleSw-LSX1QGS24FC1                OBJECT IDENTIFIER ::= { h3cevtModuleSwitchType 978 } -- 24-Port 40GBASE-R Interface Module (FC),(QSFP+)
h3cevtModuleSw-LSX1TGS24FC0                OBJECT IDENTIFIER ::= { h3cevtModuleSwitchType 979 } -- 24-Port 10GBASE-R Interface Module (FC),(SFP+,LC)
h3cevtModuleSw-LSX1TGS24FC1                OBJECT IDENTIFIER ::= { h3cevtModuleSwitchType 980 } -- 24-Port 10GBASE-R Interface Module (FC),(SFP+,LC)
h3cevtModuleSw-LSX1TGS48FC0                OBJECT IDENTIFIER ::= { h3cevtModuleSwitchType 981 } -- 48-Port 10GBASE-R Interface Module (FC),(SFP+,LC)
h3cevtModuleSw-LSX1TGS48FC1                OBJECT IDENTIFIER ::= { h3cevtModuleSwitchType 982 } -- 48-Port 10GBASE-R Interface Module (FC),(SFP+,LC)
h3cevtModuleSw-LST1XP48LFD2                OBJECT IDENTIFIER ::= { h3cevtModuleSwitchType 983 } -- 48-Port 10GBASE-R Interface Module (LFD),(SFP+,LC)
h3cevtModuleSw-LST1XP40RFD2                OBJECT IDENTIFIER ::= { h3cevtModuleSwitchType 984 } -- 40-Port 10GBASE-R Interface Module (RFD),(SFP+,LC)
h3cevtModuleSw-LST1XP40RFG2                OBJECT IDENTIFIER ::= { h3cevtModuleSwitchType 985 } -- 40-Port 10GBASE-R/W Interface Module (RFG),(SFP+,LC)
h3cevtModuleSw-LST1XLP16RFD2               OBJECT IDENTIFIER ::= { h3cevtModuleSwitchType 986 } -- 16-Port 40GBASE-R Interface Module (RFD),(QSFP+)
h3cevtModuleSw-LST1CP4RFD2                 OBJECT IDENTIFIER ::= { h3cevtModuleSwitchType 987 } -- 4-Port 100GBASE-R Interface Module (RFD),(CFP)
h3cevtModuleSw-LST1CP4RFG2                 OBJECT IDENTIFIER ::= { h3cevtModuleSwitchType 988 } -- 4-Port 100GBASE-R Interface Module (RFG),(CFP)
h3cevtModuleSw-MPE-1004                    OBJECT IDENTIFIER ::= { h3cevtModuleSwitchType 989 } -- Multi-Service Processing Engine
h3cevtModuleSw-MIC-GP4L                    OBJECT IDENTIFIER ::= { h3cevtModuleSwitchType 990 } -- 4-Port 1000BASE-X COMBO Interface Card,(SFP,LC)
h3cevtModuleSw-MIC-GP8L                    OBJECT IDENTIFIER ::= { h3cevtModuleSwitchType 991 } -- 8-Port 1000BASE-X Optical Interface Card,(SFP,LC)
h3cevtModuleSw-MIC-SP4L                    OBJECT IDENTIFIER ::= { h3cevtModuleSwitchType 992 } -- 4-Port OC-3/STM-1 POS/CPOS/ATM or 1-Port OC-12/STM-4 POS/ATM Optical Interface Card,(SFP,LC)
h3cevtModuleSw-MIC-ET16L                   OBJECT IDENTIFIER ::= { h3cevtModuleSwitchType 993 } -- 16-Port E1/T1 Electrical Interface Card
h3cevtModuleSw-MIC-CLP4L                   OBJECT IDENTIFIER ::= { h3cevtModuleSwitchType 994 } -- 4-Port OC-3/STM-1 CPOS/POS Optical Interface Card,(SFP,LC)
h3cevtModuleSw-MIC-CLP2L                   OBJECT IDENTIFIER ::= { h3cevtModuleSwitchType 995 } -- 2-Port OC-3/STM-1 CPOS/POS Optical Interface Card,(SFP,LC)
h3cevtModuleSw-LST1IPS2A1                  OBJECT IDENTIFIER ::= { h3cevtModuleSwitchType 996 } -- Intrusion Prevention System Module
h3cevtModuleSw-SFC-04B                     OBJECT IDENTIFIER ::= { h3cevtModuleSwitchType 997 } -- Switch Fabric Card(B Type)
h3cevtModuleSw-SFC-04D                     OBJECT IDENTIFIER ::= { h3cevtModuleSwitchType 998 } -- Switch Fabric Card(D Type)
h3cevtModuleSw-SFC-08B                     OBJECT IDENTIFIER ::= { h3cevtModuleSwitchType 999 } -- Switch Fabric Card(B Type)
h3cevtModuleSw-SFC-08D                     OBJECT IDENTIFIER ::= { h3cevtModuleSwitchType 1000 } -- Switch Fabric Card(D Type)
h3cevtModuleSw-SFC-12B                     OBJECT IDENTIFIER ::= { h3cevtModuleSwitchType 1001 } -- Switch Fabric Card(B Type)
h3cevtModuleSw-SFC-12D                     OBJECT IDENTIFIER ::= { h3cevtModuleSwitchType 1002 } -- Switch Fabric Card(D Type)
h3cevtModuleSw-SR05SRP1H1                  OBJECT IDENTIFIER ::= { h3cevtModuleSwitchType 1003 } -- Routing Switch Processing Unit(1H)
h3cevtModuleSw-SPC-GP24LA1                 OBJECT IDENTIFIER ::= { h3cevtModuleSwitchType 1004 } -- 16-Port 1000BASE-X Ethernet Optical Interface(SFP,LC)+8-Port Combo Interface Module(A Type)
h3cevtModuleSw-SPC-GP24XP2LA               OBJECT IDENTIFIER ::= { h3cevtModuleSwitchType 1005 } -- 16-Port 1000BASE-X Ethernet Optical Interface(SFP,LC)+8-Port Combo Interface+2-Port 10GE Optical Interface Module(XFP,LC)(A Type)
h3cevtModuleSw-SPC-GP48LA1                 OBJECT IDENTIFIER ::= { h3cevtModuleSwitchType 1006 } -- 48-Port 1000BASE-X Ethernet Optical Interface Module(SFP,LC)(A Type)
h3cevtModuleSw-SPC-GP48LB                  OBJECT IDENTIFIER ::= { h3cevtModuleSwitchType 1007 } -- 48-Port Enhanced 1000BASE-X Ethernet Optical Interface Module(SFP,LC)(B Type)
h3cevtModuleSw-SPC-XP2LA1                  OBJECT IDENTIFIER ::= { h3cevtModuleSwitchType 1008 } -- 2-Port 10GBASE Ethernet Optical Interface Module(XFP,LC)(A Type)
h3cevtModuleSw-SPC-XP4LA1                  OBJECT IDENTIFIER ::= { h3cevtModuleSwitchType 1009 } -- 4-Port 10GBASE Ethernet Optical Interface Module(XFP,LC)(A Type)
h3cevtModuleSw-SPC-XP4LB                   OBJECT IDENTIFIER ::= { h3cevtModuleSwitchType 1010 } -- 4-Port Enhanced 10GBASE Ethernet Optical Interface Module(XFP,LC)(B Type)
h3cevtModuleSw-SPC-XP8LA                   OBJECT IDENTIFIER ::= { h3cevtModuleSwitchType 1011 } -- 8-Port 10GBASE Ethernet Optical Interface Module(SFP+,LC)(A Type)
h3cevtModuleSw-SPC-XP8LB                   OBJECT IDENTIFIER ::= { h3cevtModuleSwitchType 1012 } -- 8-Port Enhanced 10GBASE Ethernet Optical Interface Module(SFP+,LC)(B Type)
h3cevtModuleSw-SPC-XP48LA                  OBJECT IDENTIFIER ::= { h3cevtModuleSwitchType 1013 } -- 48-Port 10GBASE Ethernet Optical Interface Module(SFP+,LC)(A Type)
h3cevtModuleSw-SPC-XLP8LA                  OBJECT IDENTIFIER ::= { h3cevtModuleSwitchType 1014 } -- 8-Port 40GBASE Ethernet Optical Interface Module(QSFP+,MPO)(A Type)
h3cevtModuleSw-SPC-GP24XP2LB               OBJECT IDENTIFIER ::= { h3cevtModuleSwitchType 1015 } -- 16-Port 1000BASE-X Optical Interface(SFP,LC)+8-Port Combo Interface+2-Port 10GE Optical Interface Module(XFP,LC)(B Type)
h3cevtModuleSw-LST1MRPNE2                  OBJECT IDENTIFIER ::= { h3cevtModuleSwitchType 1016 } -- Management and Route Process Unit
h3cevtModuleSw-LST2FW3A1                   OBJECT IDENTIFIER ::= { h3cevtModuleSwitchType 1017 } -- Firewall Board
h3cevtModuleSw-LST1ADE1A1                  OBJECT IDENTIFIER ::= { h3cevtModuleSwitchType 1018 } -- Load Balancing Board
h3cevtModuleSw-CR-MRP-II                   OBJECT IDENTIFIER ::= { h3cevtModuleSwitchType 1019 } -- Management and Route Unit-II
h3cevtModuleSw-CR-SF08E                    OBJECT IDENTIFIER ::= { h3cevtModuleSwitchType 1020 } -- Switch Fabric Module(E)
h3cevtModuleSw-CR-SF18E                    OBJECT IDENTIFIER ::= { h3cevtModuleSwitchType 1021 } -- Switch Fabric Module(E)
h3cevtModuleSw-CR-SPC-XP40RC               OBJECT IDENTIFIER ::= { h3cevtModuleSwitchType 1022 } -- 40-Port 10GBASE-R/W Optical Interface Module(RC),(SFP+,LC)
h3cevtModuleSw-CR-SPC-XP40RB               OBJECT IDENTIFIER ::= { h3cevtModuleSwitchType 1023 } -- 40-Port 10GBASE-R Ethernet Optical Interface Module(RB),(SFP+,LC)
h3cevtModuleSw-CR-SPC-CP4RC                OBJECT IDENTIFIER ::= { h3cevtModuleSwitchType 1024 } -- 4-Port 100GBASE Ethernet Optical Interface Module(RC),(CFP)
h3cevtModuleSw-LST1FW3C1                   OBJECT IDENTIFIER ::= { h3cevtModuleSwitchType 1025 } -- Firewall Board
h3cevtModuleSw-LSU1FWCEA0                  OBJECT IDENTIFIER ::= { h3cevtModuleSwitchType 1026 } -- Firewall Board
h3cevtModuleSw-SPC-GT48LA1                 OBJECT IDENTIFIER ::= { h3cevtModuleSwitchType 1027 } -- 48-Port 10/100/1000BASE-T Ethernet Interface Module(RJ45)(A Type)
h3cevtModuleSw-LST1XP20RFD1                OBJECT IDENTIFIER ::= { h3cevtModuleSwitchType 1028 } -- 20-Port 10GBASE-R Interface Module (RFD),(SFP+,LC)
h3cevtModuleSw-LST1XP20RFD2                OBJECT IDENTIFIER ::= { h3cevtModuleSwitchType 1029 } -- 20-Port 10GBASE-R Interface Module (RFD),(SFP+,LC)
h3cevtModuleSw-MPE-1104                    OBJECT IDENTIFIER ::= { h3cevtModuleSwitchType 1030 } -- 4-Port Multiservice Processing Engine
h3cevtModuleSw-SPEX-1204                   OBJECT IDENTIFIER ::= { h3cevtModuleSwitchType 1031 } -- 4-Port 10G Processing Engine
h3cevtModuleSw-SPC-GP44XP4LCX              OBJECT IDENTIFIER ::= { h3cevtModuleSwitchType 1032 } -- 44-Port 100/1000BASE-X Ethernet Optical Interface Module(SFP,LC)+4-Port 10GBASE Ethernet Optical Interface Module(SFP+,LC)(C Type)
h3cevtModuleSw-SPC-GP44XP4LAX              OBJECT IDENTIFIER ::= { h3cevtModuleSwitchType 1033 } -- 44-Port 100/1000BASE-X Ethernet Optical Interface Module(SFP,LC)+4-Port 10GBASE Ethernet Optical Interface Module(SFP+,LC)(A Type)
h3cevtModuleSw-SPC-XP24LCX                 OBJECT IDENTIFIER ::= { h3cevtModuleSwitchType 1034 } -- 24-Port 10GBASE Ethernet Optical Interface Module(SFP+,LC)(C Type)
h3cevtModuleSw-SPC-XP24LAX                 OBJECT IDENTIFIER ::= { h3cevtModuleSwitchType 1035 } -- 24-Port 10GBASE Ethernet Optical Interface Module(SFP+,LC)(A Type)
h3cevtModuleSw-SPC-XP12LCX                 OBJECT IDENTIFIER ::= { h3cevtModuleSwitchType 1036 } -- 12-Port 10GBASE Ethernet Optical Interface Module(SFP+,LC)(C Type)
h3cevtModuleSw-SPC-XP12LAX                 OBJECT IDENTIFIER ::= { h3cevtModuleSwitchType 1037 } -- 12-Port 10GBASE Ethernet Optical Interface Module(SFP+,LC)(A Type)
h3cevtModuleSw-SPC-XLP6LCX                 OBJECT IDENTIFIER ::= { h3cevtModuleSwitchType 1038 } -- 6-Port 40GBASE Ethernet Optical Interface Module(QSFP+,MPO)(C Type)
h3cevtModuleSw-SPC-XLP6LAX                 OBJECT IDENTIFIER ::= { h3cevtModuleSwitchType 1039 } -- 6-Port 40GBASE Ethernet Optical Interface Module(QSFP+,MPO)(A Type)
h3cevtModuleSw-SPC-CP1LCX                  OBJECT IDENTIFIER ::= { h3cevtModuleSwitchType 1040 } -- 1-Port 100GBASE Ethernet Optical Interface Module(CFP,LC)(C Type)
h3cevtModuleSw-SPC-CP1LAX                  OBJECT IDENTIFIER ::= { h3cevtModuleSwitchType 1041 } -- 1-Port 100GBASE Ethernet Optical Interface Module(CFP,LC)(A Type)
h3cevtModuleSw-SPC-CP2LB                   OBJECT IDENTIFIER ::= { h3cevtModuleSwitchType 1042 } -- 2-Port 100GBASE Ethernet Optical Interface Module(CFP,LC)(B Type)
h3cevtModuleSw-SPC-CP2LA                   OBJECT IDENTIFIER ::= { h3cevtModuleSwitchType 1043 } -- 2-Port 100GBASE Ethernet Optical Interface Module(CFP,LC)(A Type)
h3cevtModuleSw-SR05SRP1L1                  OBJECT IDENTIFIER ::= { h3cevtModuleSwitchType 1044 } -- Management and Route Process Unit(1L1)
h3cevtModuleSw-SR05SRP1L3                  OBJECT IDENTIFIER ::= { h3cevtModuleSwitchType 1045 } -- Management and Route Process Unit(1L3)
h3cevtModuleSw-SFC-04-4                    OBJECT IDENTIFIER ::= { h3cevtModuleSwitchType 1046 } -- Short-circuit Card Slot 4
h3cevtModuleSw-SFC-04-3                    OBJECT IDENTIFIER ::= { h3cevtModuleSwitchType 1047 } -- Short-circuit Card Slot 3
h3cevtModuleSw-SFC-04-2                    OBJECT IDENTIFIER ::= { h3cevtModuleSwitchType 1048 } -- Short-circuit Card Slot 2
h3cevtModuleSw-SFC-04-1                    OBJECT IDENTIFIER ::= { h3cevtModuleSwitchType 1049 } -- Short-circuit Card Slot 1
h3cevtModuleSw-LST1NSM2C1                  OBJECT IDENTIFIER ::= { h3cevtModuleSwitchType 1050 } -- NetStream Service Board
h3cevtModuleSw-CR-SPC-XP20RB               OBJECT IDENTIFIER ::= { h3cevtModuleSwitchType 1051 } -- 20-Port 10GBASE-R Ethernet Optical Interface Module(RB),(SFP+,LC)
h3cevtModuleSw-SR07SRPUA1                  OBJECT IDENTIFIER ::= { h3cevtModuleSwitchType 1052 } -- Management and Route Process Unit(UA1)
h3cevtModuleSw-SR07SRPUB3                  OBJECT IDENTIFIER ::= { h3cevtModuleSwitchType 1053 } -- Management and Route Process Unit(UB1)
h3cevtModuleSw-SR07SRPUC3                  OBJECT IDENTIFIER ::= { h3cevtModuleSwitchType 1054 } -- Management and Route Process Unit
h3cevtModuleSw-SR07MPUA1                   OBJECT IDENTIFIER ::= { h3cevtModuleSwitchType 1055 } -- Management and Route Process Unit
h3cevtModuleSw-SR07SRPUB1                  OBJECT IDENTIFIER ::= { h3cevtModuleSwitchType 1056 } -- Management and Route Process Unit(UB1)
h3cevtModuleSw-SR07SRPUC1                  OBJECT IDENTIFIER ::= { h3cevtModuleSwitchType 1057 } -- Management and Route Process Unit
h3cevtModuleSw-MIC-MS4L                    OBJECT IDENTIFIER ::= { h3cevtModuleSwitchType 1058 } -- 4-Port Multi-Service Optical Interface Card,Domestic&Overseas Version
h3cevtModuleSw-SPC-GP44XP4LC               OBJECT IDENTIFIER ::= { h3cevtModuleSwitchType 1059 } -- 44-Port 100/1000BASE-X Ethernet Optical Interface Board(SFP,LC)+4-Port 10GBASE Ethernet Optical Interface Board(SFP+,LC)(C Type)
h3cevtModuleSw-SPC-GP44XP4LA               OBJECT IDENTIFIER ::= { h3cevtModuleSwitchType 1060 } -- 44-Port 100/1000BASE-X Ethernet Optical Interface Board(SFP,LC)+4-Port 10GBASE Ethernet Optical Interface Board(SFP+,LC)(A Type)
h3cevtModuleSw-SPC-XLP2XP4LC               OBJECT IDENTIFIER ::= { h3cevtModuleSwitchType 1061 } -- 2-Port 40GBASE Ethernet Optical Interface Board(QSFP+,MPO)+4-Port 10GBASE Ethernet Optical Interface Board(SFP+,LC)(C Type)
h3cevtModuleSw-SPC-XP12LC                  OBJECT IDENTIFIER ::= { h3cevtModuleSwitchType 1062 } -- 12-Port 10GBASE Ethernet Optical Interface Board(SFP+,LC)(C Type)
h3cevtModuleSw-SPC-CP1LC                   OBJECT IDENTIFIER ::= { h3cevtModuleSwitchType 1063 } -- 1-Port 100GBASE Ethernet Optical Interface Module(CFP,LC)(C Type)
h3cevtModuleSw-SPC-XP24LC                  OBJECT IDENTIFIER ::= { h3cevtModuleSwitchType 1064 } -- 24-Port 10GBASE Ethernet Optical Interface Board(SFP+,LC)(C Type)
h3cevtModuleSw-SR07SRPUD3                  OBJECT IDENTIFIER ::= { h3cevtModuleSwitchType 1065 } -- Management and Route Process Unit(UD1)
h3cevtModuleSw-SR07MPUA3                   OBJECT IDENTIFIER ::= { h3cevtModuleSwitchType 1066 } -- Management and Route Process Unit(For 02 Chassis)
h3cevtModuleSw-MPEX-1304                   OBJECT IDENTIFIER ::= { h3cevtModuleSwitchType 1067 } -- 4-Port Multiservice Processing Engine
h3cevtModuleSw-MIC-GP10L1                  OBJECT IDENTIFIER ::= { h3cevtModuleSwitchType 1068 } -- 6-Port 1000BASE-X Optical Interface Card(SFP,LC)+4-Port 1000BASE-X/10GBASE Optical Interface Card(SFP+,LC)
h3cevtModuleSw-SR07SRPUB                   OBJECT IDENTIFIER ::= { h3cevtModuleSwitchType 1069 } -- Management and Route Processing Unit(UB3)
h3cevtModuleSw-CMPE-1104                   OBJECT IDENTIFIER ::= { h3cevtModuleSwitchType 1070 } -- 4-Port Multiservice Processing Engine
h3cevtModuleSw-CSFC-04-1                   OBJECT IDENTIFIER ::= { h3cevtModuleSwitchType 1071 } -- Fabric Card Slot 1
h3cevtModuleSw-CSFC-04-2                   OBJECT IDENTIFIER ::= { h3cevtModuleSwitchType 1072 } -- Fabric Card Slot 2
h3cevtModuleSw-CSFC-04-3                   OBJECT IDENTIFIER ::= { h3cevtModuleSwitchType 1073 } -- Fabric Card Slot 3
h3cevtModuleSw-CSFC-04-4                   OBJECT IDENTIFIER ::= { h3cevtModuleSwitchType 1074 } -- Fabric Card Slot 4
h3cevtModuleSw-CSFC-04B                    OBJECT IDENTIFIER ::= { h3cevtModuleSwitchType 1075 } -- Switch Fabric Card(B Type)
h3cevtModuleSw-CSFC-04D                    OBJECT IDENTIFIER ::= { h3cevtModuleSwitchType 1076 } -- Switch Fabric Card(D Type)
h3cevtModuleSw-CSFC-08B                    OBJECT IDENTIFIER ::= { h3cevtModuleSwitchType 1077 } -- Switch Fabric Card(B Type)
h3cevtModuleSw-CSFC-08D                    OBJECT IDENTIFIER ::= { h3cevtModuleSwitchType 1078 } -- Switch Fabric Card(D Type)
h3cevtModuleSw-CSFC-12B                    OBJECT IDENTIFIER ::= { h3cevtModuleSwitchType 1079 } -- Switch Fabric Card(B Type)
h3cevtModuleSw-CSFC-12D                    OBJECT IDENTIFIER ::= { h3cevtModuleSwitchType 1080 } -- Switch Fabric Card(D Type)
h3cevtModuleSw-CSPC-CP1LCX                 OBJECT IDENTIFIER ::= { h3cevtModuleSwitchType 1081 } -- 1-Port 100GBASE Ethernet Optical Interface Module(CFP,LC)(C Type)
h3cevtModuleSw-CSPC-CP2LB                  OBJECT IDENTIFIER ::= { h3cevtModuleSwitchType 1082 } -- 2-Port 100GBASE Ethernet Optical Interface Module(CFP,LC)(B Type)
h3cevtModuleSw-CSPC-GP24LA1                OBJECT IDENTIFIER ::= { h3cevtModuleSwitchType 1083 } -- 16-Port 1000BASE-X Ethernet Optical Interface(SFP,LC)+8-Port Combo Interface Module(A Type)
h3cevtModuleSw-CSPC-GP24XP2LB              OBJECT IDENTIFIER ::= { h3cevtModuleSwitchType 1084 } -- 16-Port 1000BASE-X Optical Interface(SFP,LC)+8-Port Combo Interface+2-Port 10GE Optical Interface Module(XFP,LC)(B Type)
h3cevtModuleSw-CSPC-GP44XP4LCX             OBJECT IDENTIFIER ::= { h3cevtModuleSwitchType 1085 } -- 44-Port 1000BASE-X Ethernet Optical Interface Module(SFP,LC)+4-Port 10GBASE Ethernet Optical Interface Module(SFP+,LC)(C Type)
h3cevtModuleSw-CSPC-GP48LB                 OBJECT IDENTIFIER ::= { h3cevtModuleSwitchType 1086 } -- 48-Port Enhanced 1000BASE-X Ethernet Optical Interface Module(SFP,LC)(B Type)
h3cevtModuleSw-CSPC-GT48LA1                OBJECT IDENTIFIER ::= { h3cevtModuleSwitchType 1087 } -- 48-Port 10/100/1000BASE-T Ethernet Interface Module(RJ45)(A Type)
h3cevtModuleSw-CSPC-XLP6LCX                OBJECT IDENTIFIER ::= { h3cevtModuleSwitchType 1088 } -- 6-Port 40GBASE Ethernet Optical Interface Module(QSFP+,MPO)(C Type)
h3cevtModuleSw-CSPC-XP2LA1                 OBJECT IDENTIFIER ::= { h3cevtModuleSwitchType 1089 } -- 2-Port 10GBASE Ethernet Optical Interface Module(XFP,LC)(A Type)
h3cevtModuleSw-CSPC-XP4LB                  OBJECT IDENTIFIER ::= { h3cevtModuleSwitchType 1090 } -- 4-Port Enhanced 10GBASE Ethernet Optical Interface Module(XFP,LC)(B Type)
h3cevtModuleSw-CSPC-XP8LB                  OBJECT IDENTIFIER ::= { h3cevtModuleSwitchType 1091 } -- 8-Port Enhanced 10GBASE Ethernet Optical Interface Module(SFP+,LC)(B Type)
h3cevtModuleSw-CSPC-XP12LAX                OBJECT IDENTIFIER ::= { h3cevtModuleSwitchType 1092 } -- 12-Port 10GBASE Ethernet Optical Interface Module(SFP+,LC)(A Type)
h3cevtModuleSw-CSPC-XP12LCX                OBJECT IDENTIFIER ::= { h3cevtModuleSwitchType 1093 } -- 12-Port 10GBASE Ethernet Optical Interface Module(SFP+,LC)(C Type)
h3cevtModuleSw-CSPC-XP24LAX                OBJECT IDENTIFIER ::= { h3cevtModuleSwitchType 1094 } -- 24-Port 10GBASE Ethernet Optical Interface Module(SFP+,LC)(A Type)
h3cevtModuleSw-CSPC-XP24LCX                OBJECT IDENTIFIER ::= { h3cevtModuleSwitchType 1095 } -- 24-Port 10GBASE Ethernet Optical Interface Module(SFP+,LC)(C Type)
h3cevtModuleSw-CSPC-CSPEX-1204             OBJECT IDENTIFIER ::= { h3cevtModuleSwitchType 1096 } -- 4-Port 10G Processing Engine
h3cevtModuleSw-CSR05SRP1L1                 OBJECT IDENTIFIER ::= { h3cevtModuleSwitchType 1097 } -- Management and Route Process Unit(1L1)
h3cevtModuleSw-CSR05SRP1L3                 OBJECT IDENTIFIER ::= { h3cevtModuleSwitchType 1098 } -- Management and Route Process Unit(1L3)
h3cevtModuleSw-CSR07MPUA1                  OBJECT IDENTIFIER ::= { h3cevtModuleSwitchType 1099 } -- Management and Route Processing Unit
h3cevtModuleSw-CSR07SRPUA1                 OBJECT IDENTIFIER ::= { h3cevtModuleSwitchType 1100 } -- Management and Route Processing Unit(UA1)
h3cevtModuleSw-CSR07SRPUB1                 OBJECT IDENTIFIER ::= { h3cevtModuleSwitchType 1101 } -- Management and Route Processing Unit(UB1)
h3cevtModuleSw-CSR07SRPUC1                 OBJECT IDENTIFIER ::= { h3cevtModuleSwitchType 1102 } -- Management and Route Processing Unit
h3cevtModuleSw-LSXM1CGX8FX1                OBJECT IDENTIFIER ::= { h3cevtModuleSwitchType 1103 } -- 8-Port 100GBASE Ethernet Optical Interface Module(CXP)(FX)
h3cevtModuleSw-LSXM1QGS24FX1               OBJECT IDENTIFIER ::= { h3cevtModuleSwitchType 1104 } -- 24-Port 40GBASE Ethernet Optical Interface Module(QSFP+)(FX)
h3cevtModuleSw-LSXM1TGS48FX1               OBJECT IDENTIFIER ::= { h3cevtModuleSwitchType 1105 } -- 48-Port 10GBASE Ethernet Optical Interface Module(SFP+,LC)(FX)
h3cevtModuleSw-LSXM1QGS12FX1               OBJECT IDENTIFIER ::= { h3cevtModuleSwitchType 1106 } -- 12-Port 40GBASE Ethernet Optical Interface Module(QSFP+)(FX)
h3cevtModuleSw-LSXM1TGT48FX1               OBJECT IDENTIFIER ::= { h3cevtModuleSwitchType 1107 } -- 48-Port 10GBASE-T Ethernet Electrical Interface Module(RJ45)(FX)
h3cevtModuleSw-LSU1IPSBEA0                 OBJECT IDENTIFIER ::= { h3cevtModuleSwitchType 1108 } -- Intrusion Prevention System Module
h3cevtModuleSw-PIC-GP10L                   OBJECT IDENTIFIER ::= { h3cevtModuleSwitchType 1109 } -- 10-Port 1000BASE-X Optical Interface Card,(SFP,LC)
h3cevtModuleSw-PIC-XP1L                    OBJECT IDENTIFIER ::= { h3cevtModuleSwitchType 1110 } -- 1-Port 10GBASE-R/W Ethernet Optical Interface Card,(XFP,LC)
h3cevtModuleSw-PIC-PUP1L                   OBJECT IDENTIFIER ::= { h3cevtModuleSwitchType 1111 } -- 1-Port 10G POS Optical Interface Card,(XFP,LC)
h3cevtModuleSw-PIC-PSP4L                   OBJECT IDENTIFIER ::= { h3cevtModuleSwitchType 1112 } -- 4-Port 2.5G POS Optical Interface Card(SFP,LC)
h3cevtModuleSw-PIC-PS2G4L                  OBJECT IDENTIFIER ::= { h3cevtModuleSwitchType 1113 } -- 2-Port 2.5G POS Optical Interface(SFP,LC)+4-Port 1000BASE-X Optical Interface Card(SFP,LC)
h3cevtModuleSw-PIC-PL2G6L                  OBJECT IDENTIFIER ::= { h3cevtModuleSwitchType 1114 } -- 2-Port 155M POS Optical Interface(SFP,LC)+6-Port 1000BASE-X Optical Interface Card(SFP,LC)
h3cevtModuleSw-PIC-TCP8L                   OBJECT IDENTIFIER ::= { h3cevtModuleSwitchType 1115 } -- 8-Port OC-3c/OC-12c POS/GE Optical Interface Card,(SFP,LC)
h3cevtModuleSw-PIC-CSP1L                   OBJECT IDENTIFIER ::= { h3cevtModuleSwitchType 1116 } -- 1-Port 2.5G CPOS Optical Interface Card(SFP,LC)
h3cevtModuleSw-PIC-PH2G6L                  OBJECT IDENTIFIER ::= { h3cevtModuleSwitchType 1117 } -- 2-Port 622M POS Optical Interface(SFP,LC)+6-Port 1000BASE-X Optical Interface Card(SFP,LC)
h3cevtModuleSw-LSXM1CGP12FX1               OBJECT IDENTIFIER ::= { h3cevtModuleSwitchType 1118 } -- 12-Port 100GBASE Ethernet Optical Interface Module(CFP2)(FX)
h3cevtModuleSw-LSXM1CGP8FX1                OBJECT IDENTIFIER ::= { h3cevtModuleSwitchType 1119 } -- 8-Port 100GBASE Ethernet Optical Interface Module(CFP2)(FX)
h3cevtModuleSw-LSXM1GT48FX1                OBJECT IDENTIFIER ::= { h3cevtModuleSwitchType 1120 } -- 48-Port 1000Base-T Gigabit Ethernet Interface Board(RJ45)
h3cevtModuleSw-LSXM1GT48FX0                OBJECT IDENTIFIER ::= { h3cevtModuleSwitchType 1121 } -- 48-Port 1000Base-T Gigabit Ethernet Interface Board(RJ45)
h3cevtModuleSw-LSXM1GP48FX1                OBJECT IDENTIFIER ::= { h3cevtModuleSwitchType 1122 } -- 48-Port 1000BASE Ethernet SFP Optical Interface Board
h3cevtModuleSw-LSXM1GP48FX0                OBJECT IDENTIFIER ::= { h3cevtModuleSwitchType 1123 } -- 48-Port 1000BASE Ethernet SFP Optical Interface Board
h3cevtModuleSw-LSXM1TGS24FX0               OBJECT IDENTIFIER ::= { h3cevtModuleSwitchType 1124 } -- 24-Port 10GBASE Ethernet SFP+ Optical Interface Board
h3cevtModuleSw-LSXM1TGS24FX1               OBJECT IDENTIFIER ::= { h3cevtModuleSwitchType 1125 } -- 24-Port 10GBASE Ethernet SFP+ Optical Interface Board
h3cevtModuleSw-MIC-SP8L                    OBJECT IDENTIFIER ::= { h3cevtModuleSwitchType 1126 } -- 8-Port OC-3c/STM-1c POS Optical Interface Card
h3cevtModuleSw-LSXM1TGS48FE1               OBJECT IDENTIFIER ::= { h3cevtModuleSwitchType 1127 } -- 48-Port 10GBASE Ethernet SFP+ Optical Interface Board(FE)
h3cevtModuleSw-LSXM1QGS24FE1               OBJECT IDENTIFIER ::= { h3cevtModuleSwitchType 1128 } -- 24-Port 40GBASE Ethernet Optical Interface Board(QSFP+)
h3cevtModuleSw-CSPEX-1504S                 OBJECT IDENTIFIER ::= { h3cevtModuleSwitchType 1129 } -- Multi-Service Processing Board
h3cevtModuleSw-CSPEX-1504X                 OBJECT IDENTIFIER ::= { h3cevtModuleSwitchType 1130 } -- Multi-Service Processing Board
h3cevtModuleSw-CSPEX-1404S                 OBJECT IDENTIFIER ::= { h3cevtModuleSwitchType 1131 } -- Multi-Service Processing Board
h3cevtModuleSw-CSPEX-1304S                 OBJECT IDENTIFIER ::= { h3cevtModuleSwitchType 1132 } -- Multi-Service Processing Board
h3cevtModuleSw-CSPEX-1404X                 OBJECT IDENTIFIER ::= { h3cevtModuleSwitchType 1133 } -- Multi-Service Processing Board
h3cevtModuleSw-CSPEX-1304X                 OBJECT IDENTIFIER ::= { h3cevtModuleSwitchType 1134 } -- Multi-Service Processing Board
h3cevtModuleSw-MIC-XP5L                    OBJECT IDENTIFIER ::= { h3cevtModuleSwitchType 1135 } -- 5-Port 10GBASE-R/W Ethernet Optical Interface Card,(SFP+,LC)
h3cevtModuleSw-MIC-XP2L                    OBJECT IDENTIFIER ::= { h3cevtModuleSwitchType 1136 } -- 2-Port 10GBASE-R/W Ethernet Optical Interface Card,(SFP+,LC)
h3cevtModuleSw-MIC-CP1L                    OBJECT IDENTIFIER ::= { h3cevtModuleSwitchType 1137 } -- 1-Port 100G Optical Interface Card,(CFP,LC)
h3cevtModuleSw-MIC-GP20L                   OBJECT IDENTIFIER ::= { h3cevtModuleSwitchType 1138 } -- 20-Port 1000BASE-X Ethernet Optical Interface Card,(SFP,LC),Monolithic
h3cevtModuleSw-MIC-GT20L                   OBJECT IDENTIFIER ::= { h3cevtModuleSwitchType 1139 } -- 20-Port 1000BASE-X Ethernet Electrical Interface Card,(RJ45,LC),Monolithic
h3cevtModuleSw-CEPC-XP48RX                 OBJECT IDENTIFIER ::= { h3cevtModuleSwitchType 1140 } -- 48-Port 10GBASE-R/W Interface Module,(SFP+,LC)
h3cevtModuleSw-CEPC-CP4RX                  OBJECT IDENTIFIER ::= { h3cevtModuleSwitchType 1141 } -- 4-Port 100GBASE Ethernet Optical Interface Board(CFP2)
h3cevtModuleSw-MIC-GP10L-V2                OBJECT IDENTIFIER ::= { h3cevtModuleSwitchType 1142 } -- 10-Port 1000BASE-X Optical Interface Card,(SFP,LC)
h3cevtModuleSw-CSR07SRPUD3                 OBJECT IDENTIFIER ::= { h3cevtModuleSwitchType 1143 } -- Management and Route Process Board(UD3)
h3cevtModuleSw-MIC-XP1L                    OBJECT IDENTIFIER ::= { h3cevtModuleSwitchType 1144 } -- 1-Port 10GBASE-R/W Ethernet Optical Interface Card,(SFP+,LC)
h3cevtModuleSw-CSFC-12E                    OBJECT IDENTIFIER ::= { h3cevtModuleSwitchType 1145 } -- Switch Fabric Board
h3cevtModuleSw-CEPC-XP24LX                 OBJECT IDENTIFIER ::= { h3cevtModuleSwitchType 1146 } -- 24-Port 10GBASE-R/W Interface Module,(SFP+,LC)
h3cevtModuleSw-IM-MSUX                     OBJECT IDENTIFIER ::= { h3cevtModuleSwitchType 1147 } -- Multi-Service Processing Board,Monolithic
h3cevtModuleSw-CSFC-12F                    OBJECT IDENTIFIER ::= { h3cevtModuleSwitchType 1148 } -- Switch Fabric Board, Monolithic
h3cevtModuleSw-CSR05SRP1N3                 OBJECT IDENTIFIER ::= { h3cevtModuleSwitchType 1149 } -- Main Processing Unit(1N3)
h3cevtModuleSw-CSPEX-1602X                 OBJECT IDENTIFIER ::= { h3cevtModuleSwitchType 1150 } -- Service Processing Unit(1602X)
h3cevtModuleSw-MIC-XP20L                   OBJECT IDENTIFIER ::= { h3cevtModuleSwitchType 1151 } -- 20-port 10GBASE-R/W Ethernet Optical Interface Card(SFP+,LC)
h3cevtModuleSw-MIC-CP2L                    OBJECT IDENTIFIER ::= { h3cevtModuleSwitchType 1152 } -- 2-port 100G Ethernet Optical Interface Card(CFP2,LC)
h3cevtModuleSw-IM-NGFWX-IV                 OBJECT IDENTIFIER ::= { h3cevtModuleSwitchType 1153 } -- Next Generation Firewall Module
h3cevtModuleSw-SFC-12E                     OBJECT IDENTIFIER ::= { h3cevtModuleSwitchType 1154 } -- Switch Fabric Board

h3cevtModuleSw-SPEX-1602X-E                OBJECT IDENTIFIER ::= { h3cevtModuleSwitchType 1155 } -- Service Processing Unit(1602X)-E
h3cevtModuleSw-SPEX-1602X-L                OBJECT IDENTIFIER ::= { h3cevtModuleSwitchType 1156 } -- Service Processing Unit(1602X)-L
h3cevtModuleSw-EPC-XP24LX-E                OBJECT IDENTIFIER ::= { h3cevtModuleSwitchType 1157 } -- 24-Port 10GBASE-R/W Ethernet Optical Interface Line Processing Unit (SFP+,LC)-E
h3cevtModuleSw-EPC-XP24LX-L                OBJECT IDENTIFIER ::= { h3cevtModuleSwitchType 1158 } -- 24-Port 10GBASE-R/W Ethernet Optical Interface Line Processing Unit (SFP+,LC)-L
h3cevtModuleSw-EPC-CP4RX-L                 OBJECT IDENTIFIER ::= { h3cevtModuleSwitchType 1159 } -- 4-Port 100GBASE Ethernet Optical Interface Line Processing Unit (CFP2)-L
h3cevtModuleSw-SPEX-1504X-E                OBJECT IDENTIFIER ::= { h3cevtModuleSwitchType 1160 } -- Service Processing Unit(1504X)-E
h3cevtModuleSw-SPEX-1504X-L                OBJECT IDENTIFIER ::= { h3cevtModuleSwitchType 1161 } -- Service Processing Unit(1504X)-L
h3cevtModuleSw-CSPEX-1602X-L               OBJECT IDENTIFIER ::= { h3cevtModuleSwitchType 1162 } -- Service Processing Unit(1602X)-L
h3cevtModuleSw-CEPC-XP24LX-L               OBJECT IDENTIFIER ::= { h3cevtModuleSwitchType 1163 } -- 24-Port 10GBASE-R/W Ethernet Optical Interface Line Processing Unit (SFP+,LC)-L
h3cevtModuleSw-CEPC-CP4RX-L                OBJECT IDENTIFIER ::= { h3cevtModuleSwitchType 1164 } -- 4-Port 100GBASE Ethernet Optical Interface Line Processing Unit(CFP2)-L
h3cevtModuleSw-MIC-CP1L-E                  OBJECT IDENTIFIER ::= { h3cevtModuleSwitchType 1165 } -- 1-port 100G Ethernet Optical Interface Card(CFP,LC)-E
h3cevtModuleSw-MIC-XP4L-E                  OBJECT IDENTIFIER ::= { h3cevtModuleSwitchType 1166 } -- 4-Port 10GBASE-R/W Ethernet Optical Interface Card,(SFP+,LC)-E
h3cevtModuleSw-MIC-XP16L-E                 OBJECT IDENTIFIER ::= { h3cevtModuleSwitchType 1167 } -- 16-port 10GBASE-R/W Ethernet Optical Interface Card(SFP+,LC)-E
h3cevtModuleSw-MIC-GP20L-E                 OBJECT IDENTIFIER ::= { h3cevtModuleSwitchType 1168 } -- 20-Port 1000BASE-X Ethernet Optical Interface Card,(SFP,LC)-E
h3cevtModuleSw-MIC-GP10L-V2-E              OBJECT IDENTIFIER ::= { h3cevtModuleSwitchType 1169 } -- 10-Port 1000BASE-X Ethernet Optical Interface Card(SFP,LC)-E
h3cevtModuleSw-MIC-GT20L-E                 OBJECT IDENTIFIER ::= { h3cevtModuleSwitchType 1170 } -- 20-Port 1000BASE-X Ethernet Electrical Interface Card,(RJ45,LC)-E
h3cevtModuleSw-CSR05SRP1P3                 OBJECT IDENTIFIER ::= { h3cevtModuleSwitchType 1171 } -- H3C CR16018-F Main Processing Unit(1P3)
h3cevtModuleSw-SR05SRP1P3                  OBJECT IDENTIFIER ::= { h3cevtModuleSwitchType 1172 } -- H3C SR8816-X Main Processing Unit(1P3)
h3cevtModuleSw-CSFC-16E                    OBJECT IDENTIFIER ::= { h3cevtModuleSwitchType 1173 } -- CR16018-F Fabric Module(E Type)
h3cevtModuleSw-SFC-16E                     OBJECT IDENTIFIER ::= { h3cevtModuleSwitchType 1174 } -- SR8816-X Fabric Module(E Type)
h3cevtModuleSw-CSFC-08E                    OBJECT IDENTIFIER ::= { h3cevtModuleSwitchType 1175 } -- CR16010-F Fabric Module(E Type)
h3cevtModuleSw-SFC-08E                     OBJECT IDENTIFIER ::= { h3cevtModuleSwitchType 1176 } -- SR8808-X Fabric Module(E Type)
h3cevtModuleSw-IM-SMUX                     OBJECT IDENTIFIER ::= { h3cevtModuleSwitchType 1177 } -- Security Monitor Unit (IM-SMUX)
h3cevtModuleSw-IM-IPSX-IV                  OBJECT IDENTIFIER ::= { h3cevtModuleSwitchType 1178 } -- Intrusion Prevention System Module
h3cevtModuleSw-IM-ACGX-IV                  OBJECT IDENTIFIER ::= { h3cevtModuleSwitchType 1179 } -- Application Control Gateway Module
h3cevtModuleSw-SFC-08E1                    OBJECT IDENTIFIER ::= { h3cevtModuleSwitchType 1180 } -- SR8808H-X Fabric Module(E Type)
h3cevtModuleSw-CSFC-08E1                   OBJECT IDENTIFIER ::= { h3cevtModuleSwitchType 1181 } -- CR16010H-F Fabric Module(E Type)
h3cevtModuleSw-IM-ACG1000X-IV              OBJECT IDENTIFIER ::= { h3cevtModuleSwitchType 1182 } -- H3C SecPath ACG1000-Blade-X Application Control Module(SR88-X SecBladeIV)
h3cevtModuleSw-MIC-QP1L                    OBJECT IDENTIFIER ::= { h3cevtModuleSwitchType 1183 } -- 1-port 40G Ethernet Optical Interface Card(QSFP+,LC)
h3cevtModuleSw-CSPEX-1804X                 OBJECT IDENTIFIER ::= { h3cevtModuleSwitchType 1184 } -- Service Processing Unit(1804X)
h3cevtModuleSw-MIC-CP2L-V2                 OBJECT IDENTIFIER ::= { h3cevtModuleSwitchType 1185 } -- 2-port 100G Ethernet Optical Interface Card(QSFP28)
h3cevtModuleSw-MIC-XP4L1                   OBJECT IDENTIFIER ::= { h3cevtModuleSwitchType 1186 } -- 4-port 10GBASE-R/W Ethernet Optical Interface Card 1(SFP+,LC)
h3cevtModuleSw-SFC-16T                     OBJECT IDENTIFIER ::= { h3cevtModuleSwitchType 1187 } -- SR8816-X Fabric Module(T Type)
h3cevtModuleSw-CSFC-16T                    OBJECT IDENTIFIER ::= { h3cevtModuleSwitchType 1188 } -- CR16018-F Fabric Module(T Type)
h3cevtModuleSw-SFC-08T                     OBJECT IDENTIFIER ::= { h3cevtModuleSwitchType 1189 } -- SR8808H-X Fabric Module(T Type)
h3cevtModuleSw-CSFC-08T                    OBJECT IDENTIFIER ::= { h3cevtModuleSwitchType 1190 } -- CR16010H-F Fabric Module(T Type)
h3cevtModuleSw-MIC-XP2L-LAN                OBJECT IDENTIFIER ::= { h3cevtModuleSwitchType 1191 } -- 2-port 10GBASE-R Ethernet Optical Interface Card(SFP+,LC)-LAN
h3cevtModuleSw-MIC-XP5L1                   OBJECT IDENTIFIER ::= { h3cevtModuleSwitchType 1192 } -- 5-port 10GBASE-R/W Ethernet Optical Interface Card(SFP+,LC)
h3cevtModuleSw-MIC-CP1L-V2                 OBJECT IDENTIFIER ::= { h3cevtModuleSwitchType 1193 } -- 1-port 100G Ethernet Optical Interface Card(CFP2,LC)
h3cevtModuleSw-CEPC-XP40LX                 OBJECT IDENTIFIER ::= { h3cevtModuleSwitchType 1194 } -- 40-port 10GBASE-R/W Ethernet Optical Interface Line Processing Unit Module(SFP+,LC)
h3cevtModuleSw-CEPC-CQ4LX                  OBJECT IDENTIFIER ::= { h3cevtModuleSwitchType 1195 } -- 4-port 100G Ethernet Optical Interface Line Processing Unit Module(QSFP28,LC)


--
-- 1200 to 1399 reserved for secondary switches part II
--
h3cevtModuleSw-LSU1QGC4SF0                 OBJECT IDENTIFIER ::= { h3cevtModuleSwitchType 1201 } -- 4 Port 40G BASE Ethernet Optical Interface Board(CFP,SC)(SF)
h3cevtModuleSw-LSU1QGS8SF0                 OBJECT IDENTIFIER ::= { h3cevtModuleSwitchType 1202 } -- 8-Port 40G BASE Ethernet Optical Interface Board(QSFP,MPO)(SF)
h3cevtModuleSw-LSU1TGS48SF0                OBJECT IDENTIFIER ::= { h3cevtModuleSwitchType 1203 } -- 48-Port 10GBASE Ethernet SFP+ Optical Interface Board
h3cevtModuleSw-LSU1QGS4SF0                 OBJECT IDENTIFIER ::= { h3cevtModuleSwitchType 1204 } -- 4-Port 40G BASE Ethernet Optical Interface Board(QSFP,MPO)(SF)
h3cevtModuleSw-LSU1TGS32SF0                OBJECT IDENTIFIER ::= { h3cevtModuleSwitchType 1205 } -- 32-Port 10GBASE Ethernet SFP+ Optical Interface Board
h3cevtModuleSw-LSU1FAB08D0                 OBJECT IDENTIFIER ::= { h3cevtModuleSwitchType 1206 } -- Switching Fabric Module
h3cevtModuleSw-LSU1FAB04B0                 OBJECT IDENTIFIER ::= { h3cevtModuleSwitchType 1207 } -- Switching Fabric Module
h3cevtModuleSw-LSU1FAB08B0                 OBJECT IDENTIFIER ::= { h3cevtModuleSwitchType 1208 } -- Switching Fabric Module
h3cevtModuleSw-LSU1FAB12D0                 OBJECT IDENTIFIER ::= { h3cevtModuleSwitchType 1209 } -- Switching Fabric Module
h3cevtModuleSw-LSU1FAB12B0                 OBJECT IDENTIFIER ::= { h3cevtModuleSwitchType 1210 } -- Switching Fabric Module
h3cevtModuleSw-LSU1FAB04D0                 OBJECT IDENTIFIER ::= { h3cevtModuleSwitchType 1211 } -- Switching Fabric Module
h3cevtModuleSw-LSQ1CTGS16SC0               OBJECT IDENTIFIER ::= { h3cevtModuleSwitchType 1212 } -- Supervisor Engine Board With 16-Port 10GBASE Ethernet SFP+ Optical Interfaces
h3cevtModuleSw-EWPX2CTGS16SC0              OBJECT IDENTIFIER ::= { h3cevtModuleSwitchType 1213 } -- Supervisor Engine Board With 16-Port 10GBASE Ethernet SFP+ Optical Interfaces
h3cevtModuleSw-LSU3WCMD0                   OBJECT IDENTIFIER ::= { h3cevtModuleSwitchType 1214 } -- Access Controller Card
h3cevtModuleSw-EWPX3WCMD0                  OBJECT IDENTIFIER ::= { h3cevtModuleSwitchType 1215 } -- Access Controller Card
h3cevtModuleSw-LSQ1QGS4SC0                 OBJECT IDENTIFIER ::= { h3cevtModuleSwitchType 1216 } -- 4-Port 40G BASE Ethernet Optical Interface Board(QSFP+,MPO)(SC)
h3cevtModuleSw-LSQ1QGC4SC0                 OBJECT IDENTIFIER ::= { h3cevtModuleSwitchType 1217 } -- 4 Port 40GBASE Ethernet Optical Interface Board(CFP)(SC)
h3cevtModuleSw-LSU1TGT24SF0                OBJECT IDENTIFIER ::= { h3cevtModuleSwitchType 1218 } -- 24-Port 10GBASE-T Ethernet Electrical Interface Board(RJ45)(SF)
h3cevtModuleSw-LSQ1QGS8SC3                 OBJECT IDENTIFIER ::= { h3cevtModuleSwitchType 1219 } -- 8-Port 40G BASE Ethernet Optical Interface Board(QSFP+,MPO)
h3cevtModuleSw-LSQ1TGS32SC3                OBJECT IDENTIFIER ::= { h3cevtModuleSwitchType 1220 } -- 32-Port 10GBASE Ethernet SFP+ Optical Interface Board
h3cevtModuleSw-LSQ1QGS4SC3                 OBJECT IDENTIFIER ::= { h3cevtModuleSwitchType 1221 } -- 4-Port 40GBASE Ethernet Optical Interface Board(QSFP+,MPO)(SC)
h3cevtModuleSw-LSQ1TGS48SC3                OBJECT IDENTIFIER ::= { h3cevtModuleSwitchType 1222 } -- 48-Port 10GBASE Ethernet SFP+ Optical Interface Board
h3cevtModuleSw-LSQ1QGC4SC3                 OBJECT IDENTIFIER ::= { h3cevtModuleSwitchType 1223 } -- 4-Port 40GBASE Ethernet Optical Interface Board(CFP)(SC)
h3cevtModuleSw-LSQ1FAB12D3                 OBJECT IDENTIFIER ::= { h3cevtModuleSwitchType 1224 } -- Switch Fabric Board
h3cevtModuleSw-LSQ1FAB08D3                 OBJECT IDENTIFIER ::= { h3cevtModuleSwitchType 1225 } -- Switching Fabric Module
h3cevtModuleSw-LSQ1FAB04D3                 OBJECT IDENTIFIER ::= { h3cevtModuleSwitchType 1226 } -- Switching Fabric Module
h3cevtModuleSw-LSQ1TGS8EB3                 OBJECT IDENTIFIER ::= { h3cevtModuleSwitchType 1227 } -- 8-Port 10GBASE Ethernet SFP+ Optical Interface Board
h3cevtModuleSw-LSQ1TGT24SC3                OBJECT IDENTIFIER ::= { h3cevtModuleSwitchType 1228 } -- 24-Port 10GBASE-T Ethernet Electrical Interface Board(RJ45)(SC)
h3cevtModuleSw-LSQ1FAB08B0                 OBJECT IDENTIFIER ::= { h3cevtModuleSwitchType 1229 } -- Switching Fabric Module
h3cevtModuleSw-EWPX2CTGS16SC               OBJECT IDENTIFIER ::= { h3cevtModuleSwitchType 1230 } -- Supervisor Engine Board With 16-Port 10GBASE Ethernet SFP+ Optical Interfaces
h3cevtModuleSw-LSU1SUPB0                   OBJECT IDENTIFIER ::= { h3cevtModuleSwitchType 1231 } -- Supervisor Engine Board
h3cevtModuleSw-LSQ1GP48SA0                 OBJECT IDENTIFIER ::= { h3cevtModuleSwitchType 1232 } -- 48-Port 1000BASE-X Ethernet Optical Interface Board(SFP,LC)
h3cevtModuleSw-LSQ1TGX2SA0                 OBJECT IDENTIFIER ::= { h3cevtModuleSwitchType 1233 } -- 2-Port 10GBASE Ethernet Optical Interface Board(XFP,LC)
h3cevtModuleSw-LSV1SRPUA1                  OBJECT IDENTIFIER ::= { h3cevtModuleSwitchType 1234 } -- Supervisor Engine Board
h3cevtModuleSw-LSV1QGS12SA1                OBJECT IDENTIFIER ::= { h3cevtModuleSwitchType 1235 } -- 12-Port 40G BASE Ethernet Optical Interface Board(QSFP+)
h3cevtModuleSw-LSV1MPUA1                   OBJECT IDENTIFIER ::= { h3cevtModuleSwitchType 1236 } -- Supervisor Engine Board
h3cevtModuleSw-LSX1SUP10A0                 OBJECT IDENTIFIER ::= { h3cevtModuleSwitchType 1237 } -- Supervisor Engine Board
h3cevtModuleSw-LSX1SUP16A0                 OBJECT IDENTIFIER ::= { h3cevtModuleSwitchType 1238 } -- Supervisor Engine Board
h3cevtModuleSw-LSX1SUP10A1                 OBJECT IDENTIFIER ::= { h3cevtModuleSwitchType 1239 } -- Supervisor Engine Board
h3cevtModuleSw-LSX1SUP16A1                 OBJECT IDENTIFIER ::= { h3cevtModuleSwitchType 1240 } -- Supervisor Engine Board
h3cevtModuleSw-LSX1FAB10B0                 OBJECT IDENTIFIER ::= { h3cevtModuleSwitchType 1241 } -- Switch Fabric Board
h3cevtModuleSw-LSX1FAB16B0                 OBJECT IDENTIFIER ::= { h3cevtModuleSwitchType 1242 } -- Switch Fabric Board
h3cevtModuleSw-LSX1FAB10B1                 OBJECT IDENTIFIER ::= { h3cevtModuleSwitchType 1243 } -- Switch Fabric Board
h3cevtModuleSw-LSX1FAB16B1                 OBJECT IDENTIFIER ::= { h3cevtModuleSwitchType 1244 } -- Switch Fabric Board
h3cevtModuleSw-LSX1QGS16EA0                OBJECT IDENTIFIER ::= { h3cevtModuleSwitchType 1245 } -- Switch Fabric Board16-Port 40G BASE Ethernet Optical Interface Board(QSFP+,MPO)
h3cevtModuleSw-LSX1TGS48EA0                OBJECT IDENTIFIER ::= { h3cevtModuleSwitchType 1246 } -- 48-Port 10GBASE Ethernet SFP+ Optical Interface Board
h3cevtModuleSw-LSX1QGS16EA1                OBJECT IDENTIFIER ::= { h3cevtModuleSwitchType 1247 } -- Switch Fabric Board16-Port 40G BASE Ethernet Optical Interface Board(QSFP+,MPO)
h3cevtModuleSw-LSX1TGS48EA1                OBJECT IDENTIFIER ::= { h3cevtModuleSwitchType 1248 } -- 48-Port 10GBASE Ethernet SFP+ Optical Interface Board
h3cevtModuleSw-LSU1TGT24SF9                OBJECT IDENTIFIER ::= { h3cevtModuleSwitchType 1249 } -- 24-Port 10GBASE-T Ethernet Electrical Interface Board(RJ45)(SF)
h3cevtModuleSw-LSU1QGS8SF9                 OBJECT IDENTIFIER ::= { h3cevtModuleSwitchType 1250 } -- 8-Port 40G BASE Ethernet Optical Interface Board(QSFP+,MPO)(SF)
h3cevtModuleSw-LSU1QGS4SF9                 OBJECT IDENTIFIER ::= { h3cevtModuleSwitchType 1251 } -- 4-Port 40GBASE Ethernet QSFP+ Optical Interface Board(QSFP+,MPO)(SF)
h3cevtModuleSw-LSU1TGS48SF9                OBJECT IDENTIFIER ::= { h3cevtModuleSwitchType 1252 } -- 48-Port 10GBASE Ethernet SFP+ Optical Interface Board
h3cevtModuleSw-LSU1TGS32SF9                OBJECT IDENTIFIER ::= { h3cevtModuleSwitchType 1253 } -- 32-Port 10GBASE Ethernet SFP+ Optical Interface Board
h3cevtModuleSw-LSU1FAB08D9                 OBJECT IDENTIFIER ::= { h3cevtModuleSwitchType 1254 } -- Switching Fabric Module
h3cevtModuleSw-LSU1SUPB9                   OBJECT IDENTIFIER ::= { h3cevtModuleSwitchType 1255 } -- Supervisor Engine Board
h3cevtModuleSw-LSQ3GV48SC0                 OBJECT IDENTIFIER ::= { h3cevtModuleSwitchType 1256 } -- 48-Port 1000Base-T Gigabit Ethernet Interface Board(RJ45), PoE Plus
h3cevtModuleSw-LSX1QGS12EC1                OBJECT IDENTIFIER ::= { h3cevtModuleSwitchType 1257 } -- 12-Port 40GBASE Ethernet Optical Interface Board(QSFP+)
h3cevtModuleSw-LSX1QGS12EC0                OBJECT IDENTIFIER ::= { h3cevtModuleSwitchType 1258 } -- 12-Port 40GBASE Ethernet Optical Interface Board(QSFP+)
h3cevtModuleSw-LSX1TGS48EC0                OBJECT IDENTIFIER ::= { h3cevtModuleSwitchType 1259 } -- 48-Port 10GBASE Ethernet SFP+ Optical Interface Board
h3cevtModuleSw-LSX1TGS48EC1                OBJECT IDENTIFIER ::= { h3cevtModuleSwitchType 1260 } -- 48-Port 10GBASE Ethernet SFP+ Optical Interface Board
h3cevtModuleSw-LSX1TGS24EC0                OBJECT IDENTIFIER ::= { h3cevtModuleSwitchType 1261 } -- 24-Port 10GBASE Ethernet SFP+ Optical Interface Board(EC)
h3cevtModuleSw-LSX1TGS24EC1                OBJECT IDENTIFIER ::= { h3cevtModuleSwitchType 1262 } -- 24-Port 10GBASE Ethernet SFP+ Optical Interface Board(EC)
h3cevtModuleSw-LSX1FAB10A0                 OBJECT IDENTIFIER ::= { h3cevtModuleSwitchType 1263 } -- Switch Fabric Board,For 10 Slots Chassis
h3cevtModuleSw-LSX1FAB16A1                 OBJECT IDENTIFIER ::= { h3cevtModuleSwitchType 1264 } -- Switch Fabric Board,For 16 Slots Chassis
h3cevtModuleSw-LSX1QGS12FB0                OBJECT IDENTIFIER ::= { h3cevtModuleSwitchType 1265 } -- 12-Port 40GBASE Ethernet Optical Interface Board(QSFP+)
h3cevtModuleSw-LSX1TGS24FB0                OBJECT IDENTIFIER ::= { h3cevtModuleSwitchType 1266 } -- 24-Port 10GBASE Ethernet SFP+ Optical Interface Board(FB)
h3cevtModuleSw-LSX1TGS48FB0                OBJECT IDENTIFIER ::= { h3cevtModuleSwitchType 1267 } -- 48-Port 10GBASE Ethernet SFP+ Optical Interface Board(FB)
h3cevtModuleSw-LSX1QGS12EB1                OBJECT IDENTIFIER ::= { h3cevtModuleSwitchType 1268 } -- 12-Port 40GBASE Ethernet Optical Interface Board(QSFP+)
h3cevtModuleSw-LSX1TGS24EB1                OBJECT IDENTIFIER ::= { h3cevtModuleSwitchType 1269 } -- 24-Port 10GBASE Ethernet SFP+ Optical Interface Board(EB)
h3cevtModuleSw-LSX1FAB10A1                 OBJECT IDENTIFIER ::= { h3cevtModuleSwitchType 1270 } -- Switch Fabric Board,For 10 Slots Chassis
h3cevtModuleSw-LSX1TGS48EB1                OBJECT IDENTIFIER ::= { h3cevtModuleSwitchType 1271 } -- 48-Port 10GBASE Ethernet SFP+ Optical Interface Board(EB)
h3cevtModuleSw-LSX1GP48EB1                 OBJECT IDENTIFIER ::= { h3cevtModuleSwitchType 1272 } -- 44-Port GE Optical Interface(SFP,LC)+4-Port 10GE Optical Interface Board(SFP+,LC)
h3cevtModuleSw-LSX1GP48FB0                 OBJECT IDENTIFIER ::= { h3cevtModuleSwitchType 1273 } -- 44-Port GE Optical Interface(SFP,LC)+4-Port 10GE Optical Interface Board(SFP+,LC)
h3cevtModuleSw-LSX1GT48FC0                 OBJECT IDENTIFIER ::= { h3cevtModuleSwitchType 1274 } -- 48-Port 1000Base-T Gigabit Ethernet Interface Module(RJ45)(FC)
h3cevtModuleSw-LSX1GT48FC1                 OBJECT IDENTIFIER ::= { h3cevtModuleSwitchType 1275 } -- 48-Port 1000Base-T Gigabit Ethernet Interface Module(RJ45)(FC)
h3cevtModuleSw-LSX1GP48FC0                 OBJECT IDENTIFIER ::= { h3cevtModuleSwitchType 1276 } -- 48-Port 1000BASE-X Gigabit Ethernet Optical Interface Module(SFP,LC)(FC)
h3cevtModuleSw-LSX1GP48FC1                 OBJECT IDENTIFIER ::= { h3cevtModuleSwitchType 1277 } -- 48-Port 1000BASE-X Gigabit Ethernet Optical Interface Module(SFP,LC)(FC)
h3cevtModuleSw-LSX1QGS12FC0                OBJECT IDENTIFIER ::= { h3cevtModuleSwitchType 1278 } -- 12-Port 40GBASE Ethernet Optical Interface Module(QSFP+)(FC)
h3cevtModuleSw-LSX1QGS12FC1                OBJECT IDENTIFIER ::= { h3cevtModuleSwitchType 1279 } -- 12-Port 40GBASE Ethernet Optical Interface Module(QSFP+)(FC)
h3cevtModuleSw-LSX2TGS48EA1                OBJECT IDENTIFIER ::= { h3cevtModuleSwitchType 1280 } -- 48-Port 10GBASE Ethernet SFP+ Optical Interface Board(EA)
h3cevtModuleSw-LSX1CGC4EB1                 OBJECT IDENTIFIER ::= { h3cevtModuleSwitchType 1281 } -- 4-Port 100GBASE Ethernet Optical Interface Board(CFP),Monolithic
h3cevtModuleSw-LSX1CGC4EC0                 OBJECT IDENTIFIER ::= { h3cevtModuleSwitchType 1282 } -- 4-Port 100GBASE Ethernet Optical Interface Board(CFP),Monolithic
h3cevtModuleSw-LSX1GT48EB1                 OBJECT IDENTIFIER ::= { h3cevtModuleSwitchType 1283 } -- 48-Port 1000Base-T Gigabit Ethernet Interface Board(RJ45)
h3cevtModuleSw-LSX1GT48FB0                 OBJECT IDENTIFIER ::= { h3cevtModuleSwitchType 1284 } -- 48-Port 1000Base-T Gigabit Ethernet Interface Board(RJ45)
h3cevtModuleSw-LSX1FAB16S1                 OBJECT IDENTIFIER ::= { h3cevtModuleSwitchType 1285 } -- Switch Fabric Board,For 16 Slots Chassis
h3cevtModuleSw-LSQ1SUPB3                   OBJECT IDENTIFIER ::= { h3cevtModuleSwitchType 1286 } -- Supervisor Engine Board
h3cevtModuleSw-LSU1CGC2SE0                 OBJECT IDENTIFIER ::= { h3cevtModuleSwitchType 1287 } -- 2 Port 100GBASE Ethernet Optical Interface Board(CFP)(SE)
h3cevtModuleSw-LSU1TGS16SF0                OBJECT IDENTIFIER ::= { h3cevtModuleSwitchType 1288 } -- 16-Port 10GBASE Ethernet SFP+ Optical Interface Board
h3cevtModuleSw-LSU1TGS8SF0                 OBJECT IDENTIFIER ::= { h3cevtModuleSwitchType 1289 } -- 8-Port 10GBASE Ethernet SFP+ Optical Interface Board
h3cevtModuleSw-LSQ1TGS4SC0                 OBJECT IDENTIFIER ::= { h3cevtModuleSwitchType 1290 } -- 4-Port 10GBASE Ethernet SFP+ Optical Interface Board
h3cevtModuleSw-LSU1GT48SE3                 OBJECT IDENTIFIER ::= { h3cevtModuleSwitchType 1291 } -- 48-Port 1000Base-T Gigabit Ethernet Interface Board(RJ45)
h3cevtModuleSw-LSU1GP48SE3                 OBJECT IDENTIFIER ::= { h3cevtModuleSwitchType 1292 } -- 48-Port 1000BASE Ethernet Optical Interface Board(SFP,LC)
h3cevtModuleSw-LSX1SUP10B0                 OBJECT IDENTIFIER ::= { h3cevtModuleSwitchType 1293 } -- Supervisor Engine Board
h3cevtModuleSw-LSX1SUP16B0                 OBJECT IDENTIFIER ::= { h3cevtModuleSwitchType 1294 } -- Supervisor Engine Board
h3cevtModuleSw-LSX1SUP10B1                 OBJECT IDENTIFIER ::= { h3cevtModuleSwitchType 1295 } -- Supervisor Engine Board
h3cevtModuleSw-LSX1SUP16B1                 OBJECT IDENTIFIER ::= { h3cevtModuleSwitchType 1296 } -- Supervisor Engine Board
h3cevtModuleSw-LSQ1CGV24PSC3               OBJECT IDENTIFIER ::= { h3cevtModuleSwitchType 1297 } -- Switching and Routing Processing Unit with 24 10/100/1000BASE-T Electrical Ports(RJ45),including 4 Combo Ports,SFP Req,PoE,No Spell
h3cevtModuleSw-LSQ1SRPA8                   OBJECT IDENTIFIER ::= { h3cevtModuleSwitchType 1298 } -- Supervisor Engine Board
h3cevtModuleSw-LSQ1CGP24TSC8               OBJECT IDENTIFIER ::= { h3cevtModuleSwitchType 1299 } -- Supervisor Engine Board
h3cevtModuleSw-LSQ1CGT24PSC8               OBJECT IDENTIFIER ::= { h3cevtModuleSwitchType 1300 } -- Supervisor Engine Board
h3cevtModuleSw-LSQ1GT24PSA8                OBJECT IDENTIFIER ::= { h3cevtModuleSwitchType 1301 } -- 24-Port 10/100/1000BASE-T Electrical(RJ45) Interface Board,including 4 Combo Ports,SFP Req,Upgradeable to PoE
h3cevtModuleSw-LSQ1GP24TSA8                OBJECT IDENTIFIER ::= { h3cevtModuleSwitchType 1302 } -- 16-Port 1000BASE-X Gigabit Ethernet Optical(SFP,LC) And 8-Port 10/100/1000BASE-T RJ45/1000BASE-X SFP Combo Interface Board
h3cevtModuleSw-LSQ1GT48SA8                 OBJECT IDENTIFIER ::= { h3cevtModuleSwitchType 1303 } -- 48-Port 1000Base-T Gigabit Ethernet Interface Board(RJ45)
h3cevtModuleSw-LSQ1GP48SA8                 OBJECT IDENTIFIER ::= { h3cevtModuleSwitchType 1304 } -- 48-Port 1000BASE-X Ethernet Optical Interface Board(SFP,LC)
h3cevtModuleSw-LSQ1TGS4SC8                 OBJECT IDENTIFIER ::= { h3cevtModuleSwitchType 1305 } -- 4-Port 10GBASE Ethernet SFP+ Optical Interface Board
h3cevtModuleSw-LSQ1TGS8SC8                 OBJECT IDENTIFIER ::= { h3cevtModuleSwitchType 1306 } -- 8-Port 10GBASE Ethernet SFP+ Optical Interface Board
h3cevtModuleSw-LSU1GT24SE3                 OBJECT IDENTIFIER ::= { h3cevtModuleSwitchType 1307 } -- 24-Port 1000BASE-T Ethernet Interface Board (RJ45)
h3cevtModuleSw-LSU1GP12SE3                 OBJECT IDENTIFIER ::= { h3cevtModuleSwitchType 1308 } -- 12-Port 1000BASE-X Ethernet Optical Interface Board(SFP,LC)
h3cevtModuleSw-LSU1GP24SE3                 OBJECT IDENTIFIER ::= { h3cevtModuleSwitchType 1309 } -- 24 Port 1000BASE-X Ethernet Optical Interface Board(SFP,LC)
h3cevtModuleSw-LSU1T24XGSE3                OBJECT IDENTIFIER ::= { h3cevtModuleSwitchType 1310 } -- 24-Port 1000BASE-T Gigabit Ethernet Interface(RJ45)+2-Port 10GBASE Ethernet Optical Interface Board(XFP,LC)
h3cevtModuleSw-LSU1P24XGSE3                OBJECT IDENTIFIER ::= { h3cevtModuleSwitchType 1311 } -- 24-Port 1000BASE-X Gigabit Ethernet Optical Interface(SFP,LC)+2-Port 10GBASE Ethernet Optical Interface Board(XFP,LC)
h3cevtModuleSw-LSU1GP24TSE3                OBJECT IDENTIFIER ::= { h3cevtModuleSwitchType 1312 } -- 16-Port 1000BASE-X Gigabit Ethernet Optical(SFP,LC) And 8-Port 10/100/1000BASE-T RJ45/1000BASE-X SFP Combo Interface Board
h3cevtModuleSw-LSU1GT40PSE3                OBJECT IDENTIFIER ::= { h3cevtModuleSwitchType 1313 } -- 40-Port 10/100/1000BASE-T Electrical(RJ45) And 8-Port 1000BASE-X Optical Ethernet Interface Board(SFP,LC),PoE
h3cevtModuleSw-LSV1TGS24SA1                OBJECT IDENTIFIER ::= { h3cevtModuleSwitchType 1314 } -- 24-Port 10G BASE Ethernet Optical Interface Board(SFP+)
h3cevtModuleSw-LSVM1SRPA1                  OBJECT IDENTIFIER ::= { h3cevtModuleSwitchType 1315 } -- Switching Fabric Module
h3cevtModuleSw-LSVM1SRPC1                  OBJECT IDENTIFIER ::= { h3cevtModuleSwitchType 1316 } -- Switching Fabric Module
h3cevtModuleSw-LSX1FAB16S0                 OBJECT IDENTIFIER ::= { h3cevtModuleSwitchType 1317 } -- Switch Fabric Board,For 16 Slots Chassis
h3cevtModuleSw-LSU1WCME0                   OBJECT IDENTIFIER ::= { h3cevtModuleSwitchType 1318 } -- Access Controller Service Board
h3cevtModuleSw-EWPX1WCME0                  OBJECT IDENTIFIER ::= { h3cevtModuleSwitchType 1319 } -- Access Controller Service Board
h3cevtModuleSw-LSUM1TGS48SG0               OBJECT IDENTIFIER ::= { h3cevtModuleSwitchType 1320 } -- 48-Port 10GBASE-R Ethernet SFP+ Optical Interface Board(SG)
h3cevtModuleSw-LSUM1QGS12SG0               OBJECT IDENTIFIER ::= { h3cevtModuleSwitchType 1321 } -- 12-Port 40GBASE-R Ethernet QSFP+ Optical Interface Board(SG)
h3cevtModuleSw-LSUM1GP44TSEC0              OBJECT IDENTIFIER ::= { h3cevtModuleSwitchType 1322 } -- 44-Port 1000BASE-R Ethernet SFP Optical Interface Board(EC)+4-Port 10GBASE-R Ethernet SFP+ Optical Interface Board(EC)
h3cevtModuleSw-LSUM1TGS24EC0               OBJECT IDENTIFIER ::= { h3cevtModuleSwitchType 1323 } -- 24-Port 10GBASE-R Ethernet SFP+ Optical Interface Board(EC)
h3cevtModuleSw-LSUM1QGS6EC0                OBJECT IDENTIFIER ::= { h3cevtModuleSwitchType 1324 } -- 6-Port 40GBASE-R Ethernet QSFP+ Optical Interface Board(EC)
h3cevtModuleSw-LSUM1CGC2EC0                OBJECT IDENTIFIER ::= { h3cevtModuleSwitchType 1325 } -- 2-Port 100GBASE-R Ethernet CFP Optical Interface Board(EC)
h3cevtModuleSw-LSU1CGC2SE9                 OBJECT IDENTIFIER ::= { h3cevtModuleSwitchType 1326 } -- 2 Port 100GBASE Ethernet Optical Interface Board(CFP)(SE)
h3cevtModuleSw-LSXM1QGS24EX1               OBJECT IDENTIFIER ::= { h3cevtModuleSwitchType 1327 } -- 24 Ports 40G BASE Ethernet Optical Interface Board(QSFP+,MPO),No Spell
h3cevtModuleSw-LSXM1QGS24FB0               OBJECT IDENTIFIER ::= { h3cevtModuleSwitchType 1328 } -- 24 Ports 40G BASE Ethernet Optical Interface Board(QSFP+,MPO),No Spell
h3cevtModuleSw-LSVM1QGS12FX1               OBJECT IDENTIFIER ::= { h3cevtModuleSwitchType 1329 } -- 12-Port 40G BASE Ethernet Optical Interface Module(QSFP+,MPO/LC)
h3cevtModuleSw-LSVM1TGS24FX1               OBJECT IDENTIFIER ::= { h3cevtModuleSwitchType 1330 } -- 24-Port 10G BASE Ethernet Optical Interface Module(SFP+,LC)
h3cevtModuleSw-LSVM1QGS6C2FX1              OBJECT IDENTIFIER ::= { h3cevtModuleSwitchType 1331 } -- 2-Port 100GBASE Ethernet Optical Interface(CXP,MPO)+6-Port 40GBASE Ethernet Optical Interface(QSFP+,MPO/LC)+4-Port 10G BASE Ethernet Optical Interface Module(SFP+,LC)
h3cevtModuleSw-LSQM2GP44TSSC0              OBJECT IDENTIFIER ::= { h3cevtModuleSwitchType 1332 } -- 44-Port GE Optical Interface(SFP,LC)+4-Port 10GE Optical Interface Board(SFP+,LC)(SC)
h3cevtModuleSw-LSQM2GP44TSSC3              OBJECT IDENTIFIER ::= { h3cevtModuleSwitchType 1333 } -- 44-Port GE Optical Interface(SFP,LC)+4-Port 10GE Optical Interface Board(SFP+,LC)(SC)
h3cevtModuleSw-LSQM2GP24TSSC0              OBJECT IDENTIFIER ::= { h3cevtModuleSwitchType 1334 } -- 24-Port GE Optical Interface(SFP,LC)+4-Port 10GE Optical Interface Board(SFP+,LC)(SC)
h3cevtModuleSw-LSQM2GP24TSSC3              OBJECT IDENTIFIER ::= { h3cevtModuleSwitchType 1335 } -- 24-Port GE Optical Interface(SFP,LC)+4-Port 10GE Optical Interface Board(SFP+,LC)(SC)
h3cevtModuleSw-LSQM2GT24PTSSC0             OBJECT IDENTIFIER ::= { h3cevtModuleSwitchType 1336 } -- 24-Port 1000Base-T Gigabit Ethernet Interface Board(RJ45)+20-Port GE Optical Interface(SFP,LC)+4-Port 10GE Optical Interface Board(SFP+,LC)(SC)
h3cevtModuleSw-LSQM2GT24PTSSC3             OBJECT IDENTIFIER ::= { h3cevtModuleSwitchType 1337 } -- 24-Port 1000Base-T Gigabit Ethernet Interface Board(RJ45)+20-Port GE Optical Interface(SFP,LC)+4-Port 10GE Optical Interface Board(SFP+,LC)(SC)
h3cevtModuleSw-LSQM2GT24TSSC0              OBJECT IDENTIFIER ::= { h3cevtModuleSwitchType 1338 } -- 24-Port 1000Base-T Gigabit Ethernet Interface Board(RJ45)+4-Port 10GE Optical Interface Board(SFP+,LC)(SC)
h3cevtModuleSw-LSQM2GT24TSSC3              OBJECT IDENTIFIER ::= { h3cevtModuleSwitchType 1339 } -- 24-Port 1000Base-T Gigabit Ethernet Interface Board(RJ45)+4-Port 10GE Optical Interface Board(SFP+,LC)(SC)
h3cevtModuleSw-LSQM2GT48SC0                OBJECT IDENTIFIER ::= { h3cevtModuleSwitchType 1340 } -- 48-Port 1000Base-T Gigabit Ethernet Interface Board(RJ45)(SC)
h3cevtModuleSw-LSQM2GT48SC3                OBJECT IDENTIFIER ::= { h3cevtModuleSwitchType 1341 } -- 48-Port 1000Base-T Gigabit Ethernet Interface Board(RJ45)(SC)
h3cevtModuleSw-LSQM4GV48SC0                OBJECT IDENTIFIER ::= { h3cevtModuleSwitchType 1342 } -- 48-Port 1000Base-T Gigabit Ethernet Interface Board(RJ45)(SC)-POE
h3cevtModuleSw-LSQM4GV48SC3                OBJECT IDENTIFIER ::= { h3cevtModuleSwitchType 1343 } -- 48-Port 1000Base-T Gigabit Ethernet Interface Board(RJ45)(SC)-POE
h3cevtModuleSw-LSQM2TGS16SF0               OBJECT IDENTIFIER ::= { h3cevtModuleSwitchType 1344 } -- 16-Port 10GE Optical Interface Board(SFP+,LC)(SF)
h3cevtModuleSw-LSQM2TGS16SF3               OBJECT IDENTIFIER ::= { h3cevtModuleSwitchType 1345 } -- 16-Port 10GE Optical Interface Board(SFP+,LC)(SF)
h3cevtModuleSw-LSQM2MPUD0                  OBJECT IDENTIFIER ::= { h3cevtModuleSwitchType 1346 } -- Supervisor Engine Board
h3cevtModuleSw-LSQM2MPUD3                  OBJECT IDENTIFIER ::= { h3cevtModuleSwitchType 1347 } -- Supervisor Engine Board
h3cevtModuleSw-LSQM3MPUA0                  OBJECT IDENTIFIER ::= { h3cevtModuleSwitchType 1348 } -- Supervisor Engine Board
h3cevtModuleSw-LSQM3MPUA3                  OBJECT IDENTIFIER ::= { h3cevtModuleSwitchType 1349 } -- Supervisor Engine Board
h3cevtModuleSw-LSUM2GP44TSSE0              OBJECT IDENTIFIER ::= { h3cevtModuleSwitchType 1350 } -- 44-Port GE Optical Interface(SFP,LC)+4-Port 10GE Optical Interface Board(SFP+,LC)(SE)
h3cevtModuleSw-LSUM2GP44TSSC3              OBJECT IDENTIFIER ::= { h3cevtModuleSwitchType 1351 } -- 44-Port GE Optical Interface(SFP,LC)+4-Port 10GE Optical Interface Board(SFP+,LC)(SC)
h3cevtModuleSw-LSUM2GP24TSSE0              OBJECT IDENTIFIER ::= { h3cevtModuleSwitchType 1352 } -- 24-Port GE Optical Interface(SFP,LC)+4-Port 10GE Optical Interface Board(SFP+,LC)(SE)
h3cevtModuleSw-LSUM2GP24TSSC3              OBJECT IDENTIFIER ::= { h3cevtModuleSwitchType 1353 } -- 24-Port GE Optical Interface(SFP,LC)+4-Port 10GE Optical Interface Board(SFP+,LC)(SC)
h3cevtModuleSw-LSUM2GT24PTSSE0             OBJECT IDENTIFIER ::= { h3cevtModuleSwitchType 1354 } -- 24-Port 1000Base-T Gigabit Ethernet Interface Board(RJ45)+20-Port GE Optical Interface(SFP,LC)+4-Port 10GE Optical Interface Board(SFP+,LC)(SE)
h3cevtModuleSw-LSUM2GT24PTSSC3             OBJECT IDENTIFIER ::= { h3cevtModuleSwitchType 1355 } -- 24-Port 1000Base-T Gigabit Ethernet Interface Board(RJ45)+20-Port GE Optical Interface(SFP,LC)+4-Port 10GE Optical Interface Board(SFP+,LC)(SC)
h3cevtModuleSw-LSUM2GT24TSSE0              OBJECT IDENTIFIER ::= { h3cevtModuleSwitchType 1356 } -- 24-Port 1000Base-T Gigabit Ethernet Interface Board(RJ45)+4-Port 10GE Optical Interface Board(SFP+,LC)(SE)
h3cevtModuleSw-LSUM2GT24TSSC3              OBJECT IDENTIFIER ::= { h3cevtModuleSwitchType 1357 } -- 24-Port 1000Base-T Gigabit Ethernet Interface Board(RJ45)+4-Port 10GE Optical Interface Board(SFP+,LC)(SC)
h3cevtModuleSw-LSUM2GT48SE0                OBJECT IDENTIFIER ::= { h3cevtModuleSwitchType 1358 } -- 48-Port 1000Base-T Gigabit Ethernet Interface Board(RJ45)(SE)
h3cevtModuleSw-LSUM2GT48SC3                OBJECT IDENTIFIER ::= { h3cevtModuleSwitchType 1359 } -- 48-Port 1000Base-T Gigabit Ethernet Interface Board(RJ45)(SC)
h3cevtModuleSw-LSUM2GV48SE0                OBJECT IDENTIFIER ::= { h3cevtModuleSwitchType 1360 } -- 48-Port 1000Base-T Gigabit Ethernet Interface Board(RJ45)(SE)-POE
h3cevtModuleSw-LSUM2GV48SC3                OBJECT IDENTIFIER ::= { h3cevtModuleSwitchType 1361 } -- 48-Port 1000Base-T Gigabit Ethernet Interface Board(RJ45)(SC)-POE
h3cevtModuleSw-LSUM2TGS16SF0               OBJECT IDENTIFIER ::= { h3cevtModuleSwitchType 1362 } -- 16-Port 10GE Optical Interface Board(SFP+,LC)(SF)
h3cevtModuleSw-LSUM2TGS16SF3               OBJECT IDENTIFIER ::= { h3cevtModuleSwitchType 1363 } -- 16-Port 10GE Optical Interface Board(SFP+,LC)(SF)
h3cevtModuleSw-LSUM1MPU06B0                OBJECT IDENTIFIER ::= { h3cevtModuleSwitchType 1364 } -- Supervisor Engine Board
h3cevtModuleSw-LSUM1MPU06B3                OBJECT IDENTIFIER ::= { h3cevtModuleSwitchType 1365 } -- Supervisor Engine Board
h3cevtModuleSw-LSUM1MPU10C0                OBJECT IDENTIFIER ::= { h3cevtModuleSwitchType 1366 } -- Supervisor Engine Board
h3cevtModuleSw-LSUM1MPU10C3                OBJECT IDENTIFIER ::= { h3cevtModuleSwitchType 1367 } -- Supervisor Engine Board
h3cevtModuleSw-LSUM1FAB06C0                OBJECT IDENTIFIER ::= { h3cevtModuleSwitchType 1368 } -- Switching Fabric Module
h3cevtModuleSw-LSUM1FAB06C3                OBJECT IDENTIFIER ::= { h3cevtModuleSwitchType 1369 } -- Switching Fabric Module
h3cevtModuleSw-LSUM1FAB10C0                OBJECT IDENTIFIER ::= { h3cevtModuleSwitchType 1370 } -- Switching Fabric Module
h3cevtModuleSw-LSUM1FAB10C3                OBJECT IDENTIFIER ::= { h3cevtModuleSwitchType 1371 } -- Switching Fabric Module
h3cevtModuleSw-LSXM1SUPA1                  OBJECT IDENTIFIER ::= { h3cevtModuleSwitchType 1372 } -- Supervisor Engine Module
h3cevtModuleSw-LSXM1SFF16B1                OBJECT IDENTIFIER ::= { h3cevtModuleSwitchType 1373 } -- Switch Fabric Board
h3cevtModuleSw-LSUM1SPMAEC0                OBJECT IDENTIFIER ::= { h3cevtModuleSwitchType 1374 } -- 4-Port Multiservice Processing Engine
h3cevtModuleSw-LSXM1SUPB1                  OBJECT IDENTIFIER ::= { h3cevtModuleSwitchType 1375 } -- Supervisor Engine Module
h3cevtModuleSw-LSXM1SFF08B1                OBJECT IDENTIFIER ::= { h3cevtModuleSwitchType 1376 } -- Switching Fabric Module,Type B(F1)
h3cevtModuleSw-LSXM1TGS4GPEB1              OBJECT IDENTIFIER ::= { h3cevtModuleSwitchType 1377 } -- 44-Port GE Optical Interface(SFP,LC)+4-Port 10GE Optical Interface Module(SFP+,LC)(EB)
h3cevtModuleSw-LSXM1TGS16EA1               OBJECT IDENTIFIER ::= { h3cevtModuleSwitchType 1378 } -- 16-Port 10GBASE Ethernet Optical Interface Module(SFP+,LC)(EA)
h3cevtModuleSw-LSXM1TGS8EA1                OBJECT IDENTIFIER ::= { h3cevtModuleSwitchType 1379 } -- 8-Port 10GBASE Ethernet Optical Interface Module(SFP+,LC)(EA)
h3cevtModuleSw-LSXM1QGS36FX1               OBJECT IDENTIFIER ::= { h3cevtModuleSwitchType 1380 } -- 36-Port 40GBASE Ethernet Optical Interface Module(QSFP+)(FX)
h3cevtModuleSw-LSXM1SFF16C1                OBJECT IDENTIFIER ::= { h3cevtModuleSwitchType 1381 } -- Switching Fabric Module
h3cevtModuleSw-LSQM3MPUB0                  OBJECT IDENTIFIER ::= { h3cevtModuleSwitchType 1382 } -- Supervisor Engine Board
h3cevtModuleSw-LSQM3MPUB3                  OBJECT IDENTIFIER ::= { h3cevtModuleSwitchType 1383 } -- Supervisor Engine Board
h3cevtModuleSw-LSQM2MPUC0                  OBJECT IDENTIFIER ::= { h3cevtModuleSwitchType 1384 } -- Supervisor Engine Board
h3cevtModuleSw-LSQM2MPUC3                  OBJECT IDENTIFIER ::= { h3cevtModuleSwitchType 1385 } -- Supervisor Engine Board
h3cevtModuleSw-LST1FW3B1                   OBJECT IDENTIFIER ::= { h3cevtModuleSwitchType 1386 } -- Firewall Board
h3cevtModuleSw-LSX1NSCEA1                  OBJECT IDENTIFIER ::= { h3cevtModuleSwitchType 1387 } -- NetStream Service Board
h3cevtModuleSw-LSX1FWCEA1                  OBJECT IDENTIFIER ::= { h3cevtModuleSwitchType 1388 } -- Firewall Service Board
h3cevtModuleSw-LSXM1ADECEA1                OBJECT IDENTIFIER ::= { h3cevtModuleSwitchType 1389 } -- Application Dilevery Engine Module,Domestic&Overseas Version
h3cevtModuleSw-LSXM1SFF16A1                OBJECT IDENTIFIER ::= { h3cevtModuleSwitchType 1390 } -- Switching Fabric Module
h3cevtModuleSw-LSV1MPUA0                   OBJECT IDENTIFIER ::= { h3cevtModuleSwitchType 1391 } -- Supervisor Engine Board
h3cevtModuleSw-LSVM1SRPA0                  OBJECT IDENTIFIER ::= { h3cevtModuleSwitchType 1392 } -- Switching Fabric Module
h3cevtModuleSw-LSVM1SRPC0                  OBJECT IDENTIFIER ::= { h3cevtModuleSwitchType 1393 } -- Switching Fabric Module
h3cevtModuleSw-LSV1QGS12SA0                OBJECT IDENTIFIER ::= { h3cevtModuleSwitchType 1394 } -- 12-Port 40G BASE Ethernet Optical Interface Board(QSFP+)
h3cevtModuleSw-LSVM1QGS12FX0               OBJECT IDENTIFIER ::= { h3cevtModuleSwitchType 1395 } -- 12-Port 40G BASE Ethernet Optical Interface Module(QSFP+,MPO/LC)
h3cevtModuleSw-LSVM1TGS24FX0               OBJECT IDENTIFIER ::= { h3cevtModuleSwitchType 1396 } -- 24-Port 10G BASE Ethernet Optical Interface Module(SFP+,LC)
h3cevtModuleSw-LSVM1QGS6C2FX0              OBJECT IDENTIFIER ::= { h3cevtModuleSwitchType 1397 } -- 2-Port 100GBASE Ethernet Optical Interface(CXP,MPO)+6-Port 40GBASE Ethernet Optical Interface(QSFP+,MPO/LC)+4-Port 10G BASE Ethernet Optical Interface Module(SFP+,LC)
h3cevtModuleSw-LSQ2FWBSC0                  OBJECT IDENTIFIER ::= { h3cevtModuleSwitchType 1398 } -- Gigabit Firewall Card, 4 Gigabit Port for Management
h3cevtModuleSw-LSQM1SRP8X2QE0              OBJECT IDENTIFIER ::= { h3cevtModuleSwitchType 1399 } -- Supervisor Engine Board With 8-Port 10GBASE Ethernet SFP+ Optical Interfaces+2-Port 40GBASE-R Ethernet QSFP+ Optical Interfaces

--
-- 1400 to 1599 reserved for switche RPU logical modules
--
h3cevtModulesw-PEX-Common                  OBJECT IDENTIFIER ::= { h3cevtModuleSwitchType 1400 } -- The general logical module type for PEX
h3cevtModuleSw-CSPEX-1812X                 OBJECT IDENTIFIER ::= { h3cevtModuleSwitchType 1401 } -- Service Processing Unit Module(1812X)
h3cevtModuleSw-CSPEX-1612X                 OBJECT IDENTIFIER ::= { h3cevtModuleSwitchType 1402 } -- Service Processing Unit Module(1612X)
h3cevtModuleSw-CSPEX-1512X                 OBJECT IDENTIFIER ::= { h3cevtModuleSwitchType 1403 } -- Service Processing Unit Module(1512X)
h3cevtModuleSw-NIC-XP20L                   OBJECT IDENTIFIER ::= { h3cevtModuleSwitchType 1404 } -- 20-port 10GBASE-R/W Ethernet Optical Interface Card Module(SFP+,LC)(NIC)
h3cevtModuleSw-NIC-XP10L                   OBJECT IDENTIFIER ::= { h3cevtModuleSwitchType 1405 } -- 10-port 10GBASE-R/W Ethernet Optical Interface Card Module(SFP+,LC)(NIC)
h3cevtModuleSw-NIC-CC2L                    OBJECT IDENTIFIER ::= { h3cevtModuleSwitchType 1406 } -- 2-port 100G Ethernet Optical Interface Card Module(CFP2,LC)(NIC)
h3cevtModuleSw-NIC-CC1L                    OBJECT IDENTIFIER ::= { h3cevtModuleSwitchType 1407 } -- 1-port 100G Ethernet Optical Interface Card Module(CFP2,LC)(NIC)
h3cevtModuleSw-NIC-XP5L                    OBJECT IDENTIFIER ::= { h3cevtModuleSwitchType 1408 } -- 5-port 10GBASE-R/W Ethernet Optical Interface Card Module(SFP+,LC)(NIC)
h3cevtModuleSw-NIC-GP20L                   OBJECT IDENTIFIER ::= { h3cevtModuleSwitchType 1409 } -- 20-port 1000BASE-X Ethernet Optical Interface Card Module(SFP,LC)(NIC)
h3cevtModuleSw-NIC-GT20L                   OBJECT IDENTIFIER ::= { h3cevtModuleSwitchType 1410 } -- 20-port 1000BASE-T Ethernet Copper Interface Card Module(RJ45)(NIC)
h3cevtModuleSw-MIC-CQ1L                    OBJECT IDENTIFIER ::= { h3cevtModuleSwitchType 1411 } -- 1-port 100G Ethernet Optical Interface Card Module(QSFP28,LC)
h3cevtModuleSw-MIC-XP10CQ1L                OBJECT IDENTIFIER ::= { h3cevtModuleSwitchType 1412 } -- 10-port 10GBASE-R/W Ethernet Optical Interface(SFP+,LC)+1-port 100G Ethernet Optical Interface Card Module(QSFP28,LC)
h3cevtModuleSw-CSPEX-1502X                 OBJECT IDENTIFIER ::= { h3cevtModuleSwitchType 1413 } -- Service Processing Unit(1502X)
h3cevtModuleSw-EPC-CP4RX                   OBJECT IDENTIFIER ::= { h3cevtModuleSwitchType 1414 } -- 4-port 100GBASE Ethernet Optical Line Processing Unit(CFP2)
h3cevtModuleSw-EPC-CQ4LX                   OBJECT IDENTIFIER ::= { h3cevtModuleSwitchType 1415 } -- 4-port 100GBASE Ethernet Optical Line Processing Unit(QSFP28)
h3cevtModuleSw-MIC-XP4L1-E                 OBJECT IDENTIFIER ::= { h3cevtModuleSwitchType 1416 } -- 4-port 10GBASE-R/W Ethernet Optical Interface Card 1(SFP+,LC)
h3cevtModuleSw-MIC-CQ1L-E                  OBJECT IDENTIFIER ::= { h3cevtModuleSwitchType 1417 } -- 1-port 100G Ethernet Optical Interface Card 1(QSFP28)
h3cevtModuleSw-MIC-XP8L                    OBJECT IDENTIFIER ::= { h3cevtModuleSwitchType 1418 } -- 8-port 10GBASE-R/W Ethernet Optical Interface Card (SFP+,LC)
h3cevtModuleSw-IM-OAPX                     OBJECT IDENTIFIER ::= { h3cevtModuleSwitchType 1419 } -- Universal Open Platform(IM-OAPX)
h3cevtModuleSw-MIC-GP20L1                  OBJECT IDENTIFIER ::= { h3cevtModuleSwitchType 1420 } -- 20-port 1000BASE-X Ethernet Optical Interface Card(SFP,LC)
h3cevtModuleSw-CSPEX-1802X                 OBJECT IDENTIFIER ::= { h3cevtModuleSwitchType 1421 } -- Service Processing Unit(1802X)
h3cevtModuleSw-MIC-CQ2L                    OBJECT IDENTIFIER ::= { h3cevtModuleSwitchType 1422 } -- 2-port 100G Ethernet Optical Interface Card(QSFP28,LC)
h3cevtModuleSw-IMMSUX                      OBJECT IDENTIFIER ::= { h3cevtModuleSwitchType 1423 } -- Universal Line Processing Unit(IM-MSUX)(China Telecom)
h3cevtModuleSw-CSPEX-1104-E                OBJECT IDENTIFIER ::= { h3cevtModuleSwitchType 1424 } -- Service Processing Unit(1104E)
--
-- 1600 to 1799 reserved for secondary switches part III
--
h3cevtModuleSw-LSUM2GP44TSSE9              OBJECT IDENTIFIER ::= { h3cevtModuleSwitchType 1600 } -- 44-Port GE Optical Interface(SFP,LC)+4-Port 10GE Optical Interface Board(SFP+,LC)(SE)
h3cevtModuleSw-LSUM2GP24TSSE9              OBJECT IDENTIFIER ::= { h3cevtModuleSwitchType 1601 } -- 24-Port GE Optical Interface(SFP,LC)+4-Port 10GE Optical Interface Board(SFP+,LC)(SE)
h3cevtModuleSw-LSUM2GT24TSSE9              OBJECT IDENTIFIER ::= { h3cevtModuleSwitchType 1602 } -- 24-Port 1000Base-T Gigabit Ethernet Interface Board(RJ45)+4-Port 10GE Optical Interface Board(SFP+,LC)(SE)
h3cevtModuleSw-LSUM2GT48SE9                OBJECT IDENTIFIER ::= { h3cevtModuleSwitchType 1603 } -- 48-Port 1000Base-T Gigabit Ethernet Interface Board(RJ45)(SE)
h3cevtModuleSw-LSUM1SUPD0                  OBJECT IDENTIFIER ::= { h3cevtModuleSwitchType 1604 } -- Supervisor Engine Board
h3cevtModuleSw-LSUM1SUPD9                  OBJECT IDENTIFIER ::= { h3cevtModuleSwitchType 1605 } -- Supervisor Engine Board
h3cevtModuleSw-LSXM1TGT48FX0               OBJECT IDENTIFIER ::= { h3cevtModuleSwitchType 1606 } -- 48-Port 10GBASE-T Ethernet Electrical Interface Module(RJ45)(FX)
h3cevtModuleSw-LSXM1TGS48FX0               OBJECT IDENTIFIER ::= { h3cevtModuleSwitchType 1607 } -- 48-Port 10GBASE-T Ethernet Electrical Interface Module(RJ45)(FX)
h3cevtModuleSw-LSXM1TGS48FE0               OBJECT IDENTIFIER ::= { h3cevtModuleSwitchType 1608 } -- 48-Port 10GBASE Ethernet Optical Interface Module(SFP+,LC)(FE)
h3cevtModuleSw-LSXM1QGS36FX0               OBJECT IDENTIFIER ::= { h3cevtModuleSwitchType 1609 } -- 36-Port 40GBASE Ethernet Optical Interface Module(QSFP+)(FX)
h3cevtModuleSw-LSXM1QGS24FX0               OBJECT IDENTIFIER ::= { h3cevtModuleSwitchType 1610 } -- 24-Port 40GBASE Ethernet Optical Interface Module(QSFP+)(FX)
h3cevtModuleSw-LSXM1QGS24FE0               OBJECT IDENTIFIER ::= { h3cevtModuleSwitchType 1611 } -- 24-Port 40GBASE Ethernet Optical Interface Module(QSFP+)(FE)
h3cevtModuleSw-LSXM1CGX8FX0                OBJECT IDENTIFIER ::= { h3cevtModuleSwitchType 1612 } -- 8-Port 100GBASE Ethernet Optical Interface Module(CXP)(FX)
h3cevtModuleSw-LSXM1CGP12FX0               OBJECT IDENTIFIER ::= { h3cevtModuleSwitchType 1613 } -- 12-Port 100GBASE Ethernet Optical Interface Module(CFP2)(FX)
h3cevtModuleSw-LSXM1SUPB0                  OBJECT IDENTIFIER ::= { h3cevtModuleSwitchType 1614 } -- Supervisor Engine Module
h3cevtModuleSw-LSXM1SFF16C0                OBJECT IDENTIFIER ::= { h3cevtModuleSwitchType 1615 } -- Switching Fabric Module,Type F(Class C)
h3cevtModuleSw-LSXM1SFF16A0                OBJECT IDENTIFIER ::= { h3cevtModuleSwitchType 1616 } -- Switching Fabric Module,Type F(Class A)
h3cevtModuleSw-LSXM1SFF08B0                OBJECT IDENTIFIER ::= { h3cevtModuleSwitchType 1617 } -- Switching Fabric Module,Type F(Class B)
h3cevtModuleSw-LSQM6GV48SC0                OBJECT IDENTIFIER ::= { h3cevtModuleSwitchType 1618 } -- 48-Port 10/100/1000BASE-T Ethernet Interface Module(RJ45),Upgradeable to PoE
h3cevtModuleSw-LSXM1SUP04B1                OBJECT IDENTIFIER ::= { h3cevtModuleSwitchType 1619 } -- Supervisor Engine Module
h3cevtModuleSw-LSXM1SFF04B1                OBJECT IDENTIFIER ::= { h3cevtModuleSwitchType 1620 } -- Switching Fabric Module,Type F(Class B)
h3cevtModuleSw-LSXM1SUP04B0                OBJECT IDENTIFIER ::= { h3cevtModuleSwitchType 1621 } -- Supervisor Engine Module
h3cevtModuleSw-LSXM1SFF04B0                OBJECT IDENTIFIER ::= { h3cevtModuleSwitchType 1622 } -- Switching Fabric Module,Type F(Class B)
h3cevtModuleSw-LSU1ADECEA0                 OBJECT IDENTIFIER ::= { h3cevtModuleSwitchType 1623 } -- Application Dilevery Engine Module,Domestic&Overseas Version
h3cevtModuleSw-LSU1NSCEA0                  OBJECT IDENTIFIER ::= { h3cevtModuleSwitchType 1624 } -- NetStream Service Board
h3cevtModuleSw-LSU3FWCEA0                  OBJECT IDENTIFIER ::= { h3cevtModuleSwitchType 1625 } -- Firewall Service Board
h3cevtModuleSw-LSXM1MPU06B3                OBJECT IDENTIFIER ::= { h3cevtModuleSwitchType 1626 } -- Supervisor Engine Board
h3cevtModuleSw-LSXM1MPU10C3                OBJECT IDENTIFIER ::= { h3cevtModuleSwitchType 1627 } -- Supervisor Engine Board
h3cevtModuleSw-LSXM1SUPD3                  OBJECT IDENTIFIER ::= { h3cevtModuleSwitchType 1628 } -- Supervisor Engine Board
h3cevtModuleSw-LSXM1FAB06C3                OBJECT IDENTIFIER ::= { h3cevtModuleSwitchType 1629 } -- Switching Fabric Module
h3cevtModuleSw-LSXM1FAB10C3                OBJECT IDENTIFIER ::= { h3cevtModuleSwitchType 1630 } -- Switching Fabric Module
h3cevtModuleSw-LSXM1FAB12D3                OBJECT IDENTIFIER ::= { h3cevtModuleSwitchType 1631 } -- Switching Fabric Module
h3cevtModuleSw-LSXM1FAB04D3                OBJECT IDENTIFIER ::= { h3cevtModuleSwitchType 1632 } -- Switching Fabric Module
h3cevtModuleSw-LSXM1FAB08D3                OBJECT IDENTIFIER ::= { h3cevtModuleSwitchType 1633 } -- Switching Fabric Module
h3cevtModuleSw-LSXM1GP44TSSE3              OBJECT IDENTIFIER ::= { h3cevtModuleSwitchType 1634 } -- 44-Port GE Optical Interface(SFP,LC)+4-Port 10GE Optical Interface Board(SFP+,LC)(SE)
h3cevtModuleSw-LSXM1GP24TSSE3              OBJECT IDENTIFIER ::= { h3cevtModuleSwitchType 1635 } -- 24-Port GE Optical Interface(SFP,LC)+4-Port 10GE Optical Interface Board(SFP+,LC)(SE)
h3cevtModuleSw-LSXM1GT24PTSSE3             OBJECT IDENTIFIER ::= { h3cevtModuleSwitchType 1636 } -- 24-Port 1000Base-T Gigabit Ethernet Interface Board(RJ45)+20-Port GE Optical Interface(SFP,LC)+4-Port 10GE Optical Interface Board(SFP+,LC)(SE)
h3cevtModuleSw-LSXM1GT48SE3                OBJECT IDENTIFIER ::= { h3cevtModuleSwitchType 1637 } -- 48-Port 1000Base-T Gigabit Ethernet Interface Board(RJ45)(SE)
h3cevtModuleSw-LSXM1TGS24EC3               OBJECT IDENTIFIER ::= { h3cevtModuleSwitchType 1638 } -- 24-Port 10GBASE-R Ethernet SFP+ Optical Interface Board(EC)
h3cevtModuleSw-LSXM1CGC2EC3                OBJECT IDENTIFIER ::= { h3cevtModuleSwitchType 1639 } -- 2-Port 100GBASE-R Ethernet CFP Optical Interface Board(EC)
h3cevtModuleSw-LSXM1TGT24SF3               OBJECT IDENTIFIER ::= { h3cevtModuleSwitchType 1640 } -- 24-Port 10GBASE-T Ethernet Electrical Interface Board(RJ45)(SF)
h3cevtModuleSw-LSXM1TGS16SF3               OBJECT IDENTIFIER ::= { h3cevtModuleSwitchType 1641 } -- 16-Port 10GE Optical Interface Board(SFP+,LC)(SF)
h3cevtModuleSw-LSXM1QGS12SG3               OBJECT IDENTIFIER ::= { h3cevtModuleSwitchType 1642 } -- 12-Port 40GBASE-R Ethernet QSFP+ Optical Interface Board(SG)
h3cevtModuleSw-LSXM1TGS48SG3               OBJECT IDENTIFIER ::= { h3cevtModuleSwitchType 1643 } -- 48-Port 10GBASE-R Ethernet SFP+ Optical Interface Board(SG)
h3cevtModuleSw-LSQM1FAB04B3                OBJECT IDENTIFIER ::= { h3cevtModuleSwitchType 1644 } -- Switching Fabric Module
h3cevtModuleSw-LSQM1FAB08B3                OBJECT IDENTIFIER ::= { h3cevtModuleSwitchType 1645 } -- Switching Fabric Module
h3cevtModuleSw-LSQM1FAB12B3                OBJECT IDENTIFIER ::= { h3cevtModuleSwitchType 1646 } -- Switching Fabric Module
h3cevtModuleSw-LSXM1SFF08A0                OBJECT IDENTIFIER ::= { h3cevtModuleSwitchType 1647 } -- Switching Fabric Board
h3cevtModuleSw-LSXM1SFF08A1                OBJECT IDENTIFIER ::= { h3cevtModuleSwitchType 1648 } -- Switching Fabric Board
h3cevtModuleSw-LSXM1FWDF1                  OBJECT IDENTIFIER ::= { h3cevtModuleSwitchType 1649 } -- FW IV Next Generation Firewall Module
h3cevtModuleSw-LSQM1PT8TSSC0               OBJECT IDENTIFIER ::= { h3cevtModuleSwitchType 1650 } -- 8-Port 1G EPON OLT Optical Interface(SFP,SC)+2-Port 10GE Optical Interface Board(SFP+,LC)(SC)
h3cevtModuleSw-LSQM1PT24TSSC0              OBJECT IDENTIFIER ::= { h3cevtModuleSwitchType 1651 } -- 24-Port 1G EPON OLT Optical Interface(SFP,SC)+2-Port 10GE Optical Interface Board(SFP+,LC)(SC)
h3cevtModuleSw-LSQM1TGS12EC0               OBJECT IDENTIFIER ::= { h3cevtModuleSwitchType 1652 } -- 12-Port 10GBASE-R Ethernet SFP+ Optical Interface Board(EC)
h3cevtModuleSw-LSX1M1CGQ32TB1              OBJECT IDENTIFIER ::= { h3cevtModuleSwitchType 1653 } -- 32-Port 100GBASE Ethernet Optical Interface Board(QSFP28),Monolithic,LF
h3cevtModuleSw-LSX1M1CGQ48TB1              OBJECT IDENTIFIER ::= { h3cevtModuleSwitchType 1654 } -- 48-Port 100GBASE Ethernet Optical Interface Board(QSFP28),Monolithic
h3cevtModuleSw-LSXM1QGS48TB1               OBJECT IDENTIFIER ::= { h3cevtModuleSwitchType 1655 } -- 48-Port 40GBASE Ethernet Optical Interface Board(QSFP+),Monolithic
h3cevtModuleSw-LSXM1SRT08E1                OBJECT IDENTIFIER ::= { h3cevtModuleSwitchType 1656 } -- Switch Fabric Board
h3cevtModuleSw-LSXM1SRT16E1                OBJECT IDENTIFIER ::= { h3cevtModuleSwitchType 1657 } -- Switch Fabric Board
h3cevtModuleSw-LSXM1SRT02E1                OBJECT IDENTIFIER ::= { h3cevtModuleSwitchType 1658 } -- Switch Fabric Board
h3cevtModuleSw-LSXM1SUP02B1                OBJECT IDENTIFIER ::= { h3cevtModuleSwitchType 1659 } -- Supervisor Engine Module
h3cevtModuleSw-LSUM1SUPC0                  OBJECT IDENTIFIER ::= { h3cevtModuleSwitchType 1660 } -- Supervisor Engine Board
h3cevtModuleSw-LSUM1SUPC3                  OBJECT IDENTIFIER ::= { h3cevtModuleSwitchType 1661 } -- Supervisor Engine Board
h3cevtModuleSw-LSXM1SUPC3                  OBJECT IDENTIFIER ::= { h3cevtModuleSwitchType 1662 } -- Supervisor Engine Board
h3cevtModuleSw-LSQM1GP44TSSE0              OBJECT IDENTIFIER ::= { h3cevtModuleSwitchType 1663 } -- 44-Port GE Optical Interface(SFP,LC)+4-Port 10GE Optical Interface Board(SFP+,LC)(SC)
h3cevtModuleSw-LSQM1GP24TSSE0              OBJECT IDENTIFIER ::= { h3cevtModuleSwitchType 1664 } -- 24-Port GE Optical Interface(SFP,LC)+4-Port 10GE Optical Interface Board(SFP+,LC)(SC)
h3cevtModuleSw-LSQM1GT48SE0                OBJECT IDENTIFIER ::= { h3cevtModuleSwitchType 1665 } -- 48-Port 1000Base-T Gigabit Ethernet Interface Board(RJ45)(SC)
h3cevtModuleSw-LSQM1GV48SE0                OBJECT IDENTIFIER ::= { h3cevtModuleSwitchType 1666 } -- 48-Port 1000Base-T Gigabit Ethernet Interface Board(RJ45)(SC)-POE
h3cevtModuleSw-LSXM1QGS12FX0               OBJECT IDENTIFIER ::= { h3cevtModuleSwitchType 1667 } -- 12-Port 40GBASE Ethernet Optical Interface Module(QSFP+)(FX)
h3cevtModuleSw-LSXM3QGS24FE1               OBJECT IDENTIFIER ::= { h3cevtModuleSwitchType 1668 } -- 24-Port 40GBASE Ethernet Optical Interface Module(QSFP+)(FE)
h3cevtModuleSw-LSXM3QGS24FX1               OBJECT IDENTIFIER ::= { h3cevtModuleSwitchType 1669 } -- 24-Port 40GBASE Ethernet Optical Interface Module(QSFP+)(FX)
h3cevtModuleSw-LSXM3QGS36FX1               OBJECT IDENTIFIER ::= { h3cevtModuleSwitchType 1670 } -- 36-Port 40GBASE Ethernet Optical Interface Module(QSFP+)(FX)
h3cevtModuleSw-LSXM3TGS48FE1               OBJECT IDENTIFIER ::= { h3cevtModuleSwitchType 1671 } -- 48-Port 10GBASE Ethernet Optical Interface Module(SFP+,LC)(FX)
h3cevtModuleSw-LSXM3TGS48FX1               OBJECT IDENTIFIER ::= { h3cevtModuleSwitchType 1672 } -- 48-Port 10GBASE Ethernet Optical Interface Module(SFP+,LC)(FX)
h3cevtModuleSw-LSXM2TGS48FX1               OBJECT IDENTIFIER ::= { h3cevtModuleSwitchType 1673 } -- 48-Port 10GBASE Ethernet Optical Interface Module(SFP+,LC)(FX)
h3cevtModuleSw-LSQM1MPU06B0                OBJECT IDENTIFIER ::= { h3cevtModuleSwitchType 1674 } -- Supervisor Engine Board
h3cevtModuleSw-LSQM1MPU10C0                OBJECT IDENTIFIER ::= { h3cevtModuleSwitchType 1675 } -- Supervisor Engine Board
h3cevtModuleSw-LSQM1FAB06C0                OBJECT IDENTIFIER ::= { h3cevtModuleSwitchType 1676 } -- Switching Fabric Module
h3cevtModuleSw-LSQM1FAB10C0                OBJECT IDENTIFIER ::= { h3cevtModuleSwitchType 1677 } -- Switching Fabric Module
h3cevtModuleSw-LSQM1QGS12SG0               OBJECT IDENTIFIER ::= { h3cevtModuleSwitchType 1678 } -- 12-Port 40GBASE-R Ethernet QSFP+ Optical Interface Board(SG)
h3cevtModuleSw-LSQM1TGS48SG0               OBJECT IDENTIFIER ::= { h3cevtModuleSwitchType 1679 } -- 48-Port 10GBASE-R Ethernet SFP+ Optical Interface Board(SG)
h3cevtModuleSw-LSQM1TGT24SF0               OBJECT IDENTIFIER ::= { h3cevtModuleSwitchType 1680 } -- 24-Port 10GBASE-T Ethernet Electrical Interface Board(RJ45)(SF)
h3cevtModuleSw-LSQM1QGS8A0                 OBJECT IDENTIFIER ::= { h3cevtModuleSwitchType 1681 } -- 8-Port QSFP+ Module
h3cevtModuleSw-LSQM1TGS24QSM0              OBJECT IDENTIFIER ::= { h3cevtModuleSwitchType 1682 } -- 24-Port SFP+ and 2-Port QSFP+ Module
h3cevtModuleSw-LSQM1TGT24QSM0              OBJECT IDENTIFIER ::= { h3cevtModuleSwitchType 1683 } -- 24-Port 10G BASE-T and 2-Port QSFP+ Module
h3cevtModuleSw-LSQM1TGS24QSA0              OBJECT IDENTIFIER ::= { h3cevtModuleSwitchType 1684 } -- 24-Port SFP+ and 2-Port QSFP+ Module
h3cevtModuleSw-LSUM1FWCEAB0                OBJECT IDENTIFIER ::= { h3cevtModuleSwitchType 1685 } -- Firewall Board
h3cevtModuleSw-LSQM2GP24TSSA0              OBJECT IDENTIFIER ::= { h3cevtModuleSwitchType 1686 } -- 24-Port GE Optical Interface(SFP,LC)+4-Port 10GE Optical Interface Board(SFP+,LC)(SA)
h3cevtModuleSw-LSQM2GT48SA0                OBJECT IDENTIFIER ::= { h3cevtModuleSwitchType 1687 } -- 48-Port 1000Base-T Gigabit Ethernet Interface Board(RJ45)(SA)
h3cevtModuleSw-LSQM2GP48SA0                OBJECT IDENTIFIER ::= { h3cevtModuleSwitchType 1688 } -- 48-Port 1000BASE-X Ethernet Optical Interface Board(SFP,LC)(SA)
h3cevtModuleSw-LSQM2GP24TSSA3              OBJECT IDENTIFIER ::= { h3cevtModuleSwitchType 1689 } -- 24-Port GE Optical Interface(SFP,LC)+4-Port 10GE Optical Interface Board(SFP+,LC)(SA)
h3cevtModuleSw-LSQM2GT48SA3                OBJECT IDENTIFIER ::= { h3cevtModuleSwitchType 1690 } -- 48-Port 1000Base-T Gigabit Ethernet Interface Board(RJ45)(SA)
h3cevtModuleSw-LSQM2GP48SA3                OBJECT IDENTIFIER ::= { h3cevtModuleSwitchType 1691 } -- 48-Port 1000BASE-X Ethernet Optical Interface Board(SFP,LC)(SA)
h3cevtModuleSw-LSUM2GP24TSSA0              OBJECT IDENTIFIER ::= { h3cevtModuleSwitchType 1692 } -- 24-Port GE Optical Interface(SFP,LC)+4-Port 10GE Optical Interface Board(SFP+,LC)(SA)
h3cevtModuleSw-LSUM2GT48SA0                OBJECT IDENTIFIER ::= { h3cevtModuleSwitchType 1693 } -- 48-Port 1000Base-T Gigabit Ethernet Interface Board(RJ45)(SA)
h3cevtModuleSw-LSUM2GP48SA0                OBJECT IDENTIFIER ::= { h3cevtModuleSwitchType 1694 } -- 48-Port 1000BASE-X Ethernet Optical Interface Board(SFP,LC)(SA)
h3cevtModuleSw-LSXM1SUPT1                  OBJECT IDENTIFIER ::= { h3cevtModuleSwitchType 1695 } -- Supervisor Engine Module
h3cevtModuleSw-LSXM1SUP02T1                OBJECT IDENTIFIER ::= { h3cevtModuleSwitchType 1696 } -- Supervisor Engine Module
h3cevtModuleSw-LSXM1SFF16B0                OBJECT IDENTIFIER ::= { h3cevtModuleSwitchType 1697 } -- Switch Fabric Board
h3cevtModuleSw-LSXM4TGS48FX1               OBJECT IDENTIFIER ::= { h3cevtModuleSwitchType 1698 } -- 48-Port 10GBASE Ethernet Optical Interface Module(SFP+,LC)(FX)
h3cevtModuleSw-LSXM4QGS24FX1               OBJECT IDENTIFIER ::= { h3cevtModuleSwitchType 1699 } -- 24-Port 40GBASE Ethernet Optical Interface Module(QSFP+)(FX)
h3cevtModuleSw-LSXM1TGS48FD1               OBJECT IDENTIFIER ::= { h3cevtModuleSwitchType 1700 } -- 48-Port 10GBASE Ethernet Optical Interface Module(SFP+,LC)(FD)
h3cevtModuleSw-LSXM1QGS24FD1               OBJECT IDENTIFIER ::= { h3cevtModuleSwitchType 1701 } -- 24-Port 40GBASE Ethernet Optical Interface Module(QSFP+)(FD)
h3cevtModuleSw-LSXM2QGS24FX1               OBJECT IDENTIFIER ::= { h3cevtModuleSwitchType 1702 } -- 24-Port 40GBASE Ethernet Optical Interface Module(QSFP+)(FX)
h3cevtModuleSw-LSXM1TGS48FD0               OBJECT IDENTIFIER ::= { h3cevtModuleSwitchType 1703 } -- 48-Port 10GBASE Ethernet Optical Interface Module(SFP+,LC)
h3cevtModuleSw-LSXM1QGS24FD0               OBJECT IDENTIFIER ::= { h3cevtModuleSwitchType 1704 } -- 24-Port 40GBASE Ethernet Optical Interface Module(QSFP+)(FD)
h3cevtModuleSw-LSXM2TGS48FX0               OBJECT IDENTIFIER ::= { h3cevtModuleSwitchType 1705 } -- 48-Port 10GBASE Ethernet Optical Interface Module(SFP+,LC)(FX)
h3cevtModuleSw-LSXM2QGS24FX0               OBJECT IDENTIFIER ::= { h3cevtModuleSwitchType 1706 } -- 24-Port 40GBASE Ethernet Optical Interface Module(QSFP+)(FX)
h3cevtModuleSw-LSXM4TGS48FX0               OBJECT IDENTIFIER ::= { h3cevtModuleSwitchType 1707 } -- 48-Port 10GBASE Ethernet Optical Interface Module(SFP+,LC)(FX)
h3cevtModuleSw-LSXM4QGS24FX0               OBJECT IDENTIFIER ::= { h3cevtModuleSwitchType 1708 } -- 24-Port 40GBASE Ethernet Optical Interface Module(QSFP+)(FX)
h3cevtModuleSw-LSXM1TGW48FX1               OBJECT IDENTIFIER ::= { h3cevtModuleSwitchType 1709 } -- 48-Port 10GBASE Ethernet WAN Optical Interface Module(SFP+,LC)(FX)
h3cevtModuleSw-LSUM1MPU10A0                OBJECT IDENTIFIER ::= { h3cevtModuleSwitchType 1710 } -- Supervisor Engine Board
h3cevtModuleSw-LSUM1FAB10A0                OBJECT IDENTIFIER ::= { h3cevtModuleSwitchType 1711 } -- Switching Fabric Module
h3cevtModuleSw-LSUM2TGS32QSSG0             OBJECT IDENTIFIER ::= { h3cevtModuleSwitchType 1712 } -- 32-Port 10GBASE-R Ethernet Optical Interface(SFP+,LC)+4-Port 40GBASE-R Ethernet Optical Interface Board(QSFP+,LC)(SG)
h3cevtModuleSw-LSUM2QGS12SG0               OBJECT IDENTIFIER ::= { h3cevtModuleSwitchType 1713 } -- 12-Port 40GBASE-R Ethernet QSFP+ Optical Interface Board(SG)
h3cevtModuleSw-LSUM2TGS48SG0               OBJECT IDENTIFIER ::= { h3cevtModuleSwitchType 1714 } -- 48-Port 10GBASE-R Ethernet SFP+ Optical Interface Board(SG)
h3cevtModuleSw-LSXM2QGS12SG3               OBJECT IDENTIFIER ::= { h3cevtModuleSwitchType 1715 } -- 12-Port 40GBASE-R Ethernet QSFP+ Optical Interface Board(SG)
h3cevtModuleSw-LSXM2TGS48SG3               OBJECT IDENTIFIER ::= { h3cevtModuleSwitchType 1716 } -- 48-Port 10GBASE-R Ethernet SFP+ Optical Interface Board(SG)
h3cevtModuleSw-LSUM1FWDEC0                 OBJECT IDENTIFIER ::= { h3cevtModuleSwitchType 1717 } -- Firewall Service Board
h3cevtModuleSw-LSQM1FWDSC0                 OBJECT IDENTIFIER ::= { h3cevtModuleSwitchType 1718 } -- Firewall Service Board
h3cevtModuleSw-LSQM1TGS48RSG0              OBJECT IDENTIFIER ::= { h3cevtModuleSwitchType 1719 } -- 48-Port 10GBASE-R Ethernet SFP+ Optical Interface Board(SG)
h3cevtModuleSw-LSQM2TGS48XSG0              OBJECT IDENTIFIER ::= { h3cevtModuleSwitchType 1720 } -- 48-Port 10GBASE-R Ethernet SFP+ Optical Interface Board(SG)
h3cevtModuleSw-LSQM2QGS12XSG0              OBJECT IDENTIFIER ::= { h3cevtModuleSwitchType 1721 } -- 12-Port 40GBASE-R Ethernet QSFP+ Optical Interface Board(SG)
h3cevtModuleSw-LSQM3GP44TSSC0              OBJECT IDENTIFIER ::= { h3cevtModuleSwitchType 1722 } -- 44-Port GE Optical Interface(SFP,LC)+4-Port 10GE Optical Interface Board(SFP+,LC)(SC)
h3cevtModuleSw-LSXM1CGQ36HB1               OBJECT IDENTIFIER ::= { h3cevtModuleSwitchType 1723 } -- 36-Port 100GBASE Ethernet Optical Interface Module(QSFP28)(HB)
h3cevtModuleSw-LSXM1CGQ36HC1               OBJECT IDENTIFIER ::= { h3cevtModuleSwitchType 1724 } -- 36-Port 100GBASE Ethernet Optical Interface Module(QSFP28)(HC)
h3cevtModuleSw-LSXM1CGQ18QGHB1             OBJECT IDENTIFIER ::= { h3cevtModuleSwitchType 1725 } -- 18-Port 100GBASE (QSFP28) + 18-Port 40GBASE Ethernet Optical Interface Module (QSFP+)(HB)
h3cevtModuleSw-LSXM1CGQ18QGHC1             OBJECT IDENTIFIER ::= { h3cevtModuleSwitchType 1726 } -- 18-Port 100GBASE (QSFP28) + 18-Port 40GBASE Ethernet Optical Interface Module (QSFP+)(HC)
h3cevtModuleSw-LSXM1QGS48HB1               OBJECT IDENTIFIER ::= { h3cevtModuleSwitchType 1727 } -- 48-Port 40GBASE Ethernet Optical Interface Module(QSFP+)(HB)
h3cevtModuleSw-LSXM1QGS48HC1               OBJECT IDENTIFIER ::= { h3cevtModuleSwitchType 1728 } -- 48-Port 40GBASE Ethernet Optical Interface Module(QSFP+)(HC)
h3cevtModuleSw-LSXM1TGS48C2HB1             OBJECT IDENTIFIER ::= { h3cevtModuleSwitchType 1729 } -- 48-Port 10G BASE Ethernet Optical Interface(SFP+,LC)+2-Port 100GBASE Ethernet Optical Interface Module(QSFP28)(HB)
h3cevtModuleSw-LSXM1SFH04D1                OBJECT IDENTIFIER ::= { h3cevtModuleSwitchType 1730 } -- Switch Fabric Board,Type H(Class D)
h3cevtModuleSw-LSXM1SFH08D1                OBJECT IDENTIFIER ::= { h3cevtModuleSwitchType 1731 } -- Switch Fabric Board For S12508X-AF,Type D(F2)
h3cevtModuleSw-LSXM1SFH12D1                OBJECT IDENTIFIER ::= { h3cevtModuleSwitchType 1732 } -- Fabric Module,Type H(Class D)
h3cevtModuleSw-LSXM1SFH16C1                OBJECT IDENTIFIER ::= { h3cevtModuleSwitchType 1733 } -- Switch Fabric Board,Type H(Class C)
h3cevtModuleSw-LSXM1GP48FD0                OBJECT IDENTIFIER ::= { h3cevtModuleSwitchType 1737 } -- 48-Port 1000BASE-X Gigabit Ethernet Optical Interface Module(SFP,LC)(FD)
h3cevtModuleSw-LSXM1GP48FD1                OBJECT IDENTIFIER ::= { h3cevtModuleSwitchType 1738 } -- 48-Port 1000BASE-X Gigabit Ethernet Optical Interface Module(SFP,LC)(FD)
h3cevtModuleSw-LSXM1GT48FD0                OBJECT IDENTIFIER ::= { h3cevtModuleSwitchType 1739 } -- 48-Port 1000Base-T Gigabit Ethernet Interface Module(RJ45)(FD)
h3cevtModuleSw-LSXM1GT48FD1                OBJECT IDENTIFIER ::= { h3cevtModuleSwitchType 1740 } -- 48-Port 1000Base-T Gigabit Ethernet Interface Module(RJ45)(FD)
h3cevtModuleSw-LSXM1FAB10B0                OBJECT IDENTIFIER ::= { h3cevtModuleSwitchType 1741 } -- Switching Fabric Module
h3cevtModuleSw-LSUM1MPU10A3                OBJECT IDENTIFIER ::= { h3cevtModuleSwitchType 1742 } -- Supervisor Engine Board
h3cevtModuleSw-LSUM1FAB10A3                OBJECT IDENTIFIER ::= { h3cevtModuleSwitchType 1743 } -- Switching Fabric Module
h3cevtModuleSw-LSQM1MPU10A0                OBJECT IDENTIFIER ::= { h3cevtModuleSwitchType 1744 } -- Supervisor Engine Board
h3cevtModuleSw-LSQM1FAB10A0                OBJECT IDENTIFIER ::= { h3cevtModuleSwitchType 1745 } -- Switching Fabric Module
h3cevtModuleSw-LSQM2TGS32QSXSG0            OBJECT IDENTIFIER ::= { h3cevtModuleSwitchType 1746 } -- 32-Port 10GBASE-R Ethernet Optical Interface(SFP+,LC)+4-Port 40GBASE-R Ethernet Optical Interface Board(QSFP+,LC)(SG)
h3cevtModuleSw-LSQM1TGS48RSG3              OBJECT IDENTIFIER ::= { h3cevtModuleSwitchType 1747 } -- 48-Port 10GBASE-R Ethernet SFP+ Optical Interface Board(SG)
h3cevtModuleSw-LSXM2TGS32QSSG3             OBJECT IDENTIFIER ::= { h3cevtModuleSwitchType 1748 } -- 32-Port 10GBASE-R Ethernet Optical Interface(SFP+,LC)+4-Port 40GBASE-R Ethernet Optical Interface Board(QSFP+,LC)(SG)
h3cevtModuleSw-LSUM1NSDEC0                 OBJECT IDENTIFIER ::= { h3cevtModuleSwitchType 1749 } -- NetStream Service Board
h3cevtModuleSw-LSQM1NSDSC0                 OBJECT IDENTIFIER ::= { h3cevtModuleSwitchType 1750 } -- NetStream Service Board
h3cevtModuleSw-LSQM1QGS4SC0                OBJECT IDENTIFIER ::= { h3cevtModuleSwitchType 1751 } -- 4-Port 40G BASE Ethernet Optical Interface Board(QSFP+,MPO)(SC)
h3cevtModuleSw-LLSQM2MPUD3                 OBJECT IDENTIFIER ::= { h3cevtModuleSwitchType 1752 } -- Supervisor Engine Board
h3cevtModuleSw-LLSQM3MPUB3                 OBJECT IDENTIFIER ::= { h3cevtModuleSwitchType 1753 } -- Supervisor Engine Board
h3cevtModuleSw-LSQM3MPUB4                  OBJECT IDENTIFIER ::= { h3cevtModuleSwitchType 1754 } -- Supervisor Engine Board
h3cevtModuleSw-LSQM2MPUDS0                 OBJECT IDENTIFIER ::= { h3cevtModuleSwitchType 1755 } -- Supervisor Engine Board
h3cevtModuleSw-LSQM4GV48SA0                OBJECT IDENTIFIER ::= { h3cevtModuleSwitchType 1756 } -- 48-Port 1000Base-T Gigabit Ethernet Interface Board(RJ45)(SA)-POE
h3cevtModuleSw-LSQM1WCMX20                 OBJECT IDENTIFIER ::= { h3cevtModuleSwitchType 1757 } -- Access Controller Service Board
h3cevtModuleSw-LSQM1WCMX40                 OBJECT IDENTIFIER ::= { h3cevtModuleSwitchType 1758 } -- Access Controller Service Board
h3cevtModuleSw-LSUM1WCMX20RT               OBJECT IDENTIFIER ::= { h3cevtModuleSwitchType 1759 } -- Access Controller Service Board
h3cevtModuleSw-LSUM1WCMX40RT               OBJECT IDENTIFIER ::= { h3cevtModuleSwitchType 1760 } -- Access Controller Service Board
h3cevtModuleSw-LSXM1CGQ18QGHB0             OBJECT IDENTIFIER ::= { h3cevtModuleSwitchType 1761 } -- 18-PORT 100GBASE Ethernet Optical Interface (QSFP28)/36-PORT 40GBASE Ethernet Optical Interface Module(QSFP+)(HB)
h3cevtModuleSw-LSXM1SFH08C0                OBJECT IDENTIFIER ::= { h3cevtModuleSwitchType 1762 } -- Fabric Module,Type H(Class C)
h3cevtModuleSw-LSXM1SFH08C1                OBJECT IDENTIFIER ::= { h3cevtModuleSwitchType 1763 } -- Fabric Module,Type H(Class C)
h3cevtModuleSw-LSXM2SFH16C0                OBJECT IDENTIFIER ::= { h3cevtModuleSwitchType 1764 } -- Fabric Module,Type H(Class C)
h3cevtModuleSw-LSXM2SFH16C1                OBJECT IDENTIFIER ::= { h3cevtModuleSwitchType 1765 } -- Fabric Module,Type H(Class C)
h3cevtModuleSw-LSXM1NSDF1                  OBJECT IDENTIFIER ::= { h3cevtModuleSwitchType 1766 } -- SecBlade IV NetStream Module
h3cevtModuleSw-LSUM2TGS48SG3               OBJECT IDENTIFIER ::= { h3cevtModuleSwitchType 1767 } -- 48-Port 10GBASE-R Ethernet SFP+ Optical Interface Board(SG)
h3cevtModuleSw-DS-3E7602-MPU               OBJECT IDENTIFIER ::= { h3cevtModuleSwitchType 1768 } -- Supervisor Engine Board
h3cevtModuleSw-DS-3E7606-MPU               OBJECT IDENTIFIER ::= { h3cevtModuleSwitchType 1769 } -- Supervisor Engine Board
h3cevtModuleSw-DS-3E7600-24T4X-SC          OBJECT IDENTIFIER ::= { h3cevtModuleSwitchType 1770 } -- 24-Port 1000Base-T Gigabit Ethernet Interface Board(RJ45)+4-Port 10GE Optical Interface Board(SFP+,LC)(SC)
h3cevtModuleSw-DS-3E7600-24F4X-SA          OBJECT IDENTIFIER ::= { h3cevtModuleSwitchType 1771 } -- 24-Port GE Optical Interface(SFP,LC)+4-Port 10GE Optical Interface Board(SFP+,LC)(SA)
h3cevtModuleSw-DS-3E7600-48T-SA            OBJECT IDENTIFIER ::= { h3cevtModuleSwitchType 1772 } -- 48-Port 1000Base-T Gigabit Ethernet Interface Board(RJ45)(SA)
h3cevtModuleSw-DS-3E7600-48F-SA            OBJECT IDENTIFIER ::= { h3cevtModuleSwitchType 1773 } -- 48-Port 1000BASE-X Ethernet Optical Interface Board(SFP,LC)(SA)
h3cevtModuleSw-DS-3E7600-24F4X-SC          OBJECT IDENTIFIER ::= { h3cevtModuleSwitchType 1774 } -- 24-Port GE Optical Interface(SFP,LC)+4-Port 10GE Optical Interface Board(SFP+,LC)(SC)
h3cevtModuleSw-DS-3E7600-44F4X-SC          OBJECT IDENTIFIER ::= { h3cevtModuleSwitchType 1775 } -- 44-Port GE Optical Interface(SFP,LC)+4-Port 10GE Optical Interface Board(SFP+,LC)(SC)
h3cevtModuleSw-DS-3E7600-48T-SC            OBJECT IDENTIFIER ::= { h3cevtModuleSwitchType 1776 } -- 48-Port 1000Base-T Gigabit Ethernet Interface Board(RJ45)(SC)
h3cevtModuleSw-DS-3E7600-16X-SC            OBJECT IDENTIFIER ::= { h3cevtModuleSwitchType 1777 } -- 16-Port 10GE Optical Interface Board(SFP+,LC)(SF)
h3cevtModuleSw-S7602-MPU                   OBJECT IDENTIFIER ::= { h3cevtModuleSwitchType 1778 } -- Supervisor Engine Board
h3cevtModuleSw-S7606-MPU                   OBJECT IDENTIFIER ::= { h3cevtModuleSwitchType 1779 } -- Supervisor Engine Board
h3cevtModuleSw-S76-24GT4XFSC               OBJECT IDENTIFIER ::= { h3cevtModuleSwitchType 1780 } -- 24-Port 1000Base-T Gigabit Ethernet Interface Board(RJ45)+4-Port 10GE Optical Interface Board(SFP+,LC)(SC)
h3cevtModuleSw-S76-24GF4XFSA               OBJECT IDENTIFIER ::= { h3cevtModuleSwitchType 1781 } -- 24-Port GE Optical Interface(SFP,LC)+4-Port 10GE Optical Interface Board(SFP+,LC)(SA)
h3cevtModuleSw-S76-48GTSA                  OBJECT IDENTIFIER ::= { h3cevtModuleSwitchType 1782 } -- 48-Port 1000Base-T Gigabit Ethernet Interface Board(RJ45)(SA)
h3cevtModuleSw-S76-48GFSA                  OBJECT IDENTIFIER ::= { h3cevtModuleSwitchType 1783 } -- 48-Port 1000BASE-X Ethernet Optical Interface Board(SFP,LC)(SA)
h3cevtModuleSw-S76-24GT20GF4XFSC           OBJECT IDENTIFIER ::= { h3cevtModuleSwitchType 1784 } -- 24-Port 1000Base-T Gigabit Ethernet Interface Board(RJ45)+20-Port GE Optical Interface(SFP,LC)+4-Port 10GE Optical Interface Board(SFP+,LC)(SC)
h3cevtModuleSw-LSXM1TGS48C2HB0             OBJECT IDENTIFIER ::= { h3cevtModuleSwitchType 1785 } -- 48-PORT 10GBASE Ethernet Optical Interface (SFP+,LC)+2-PORT 100GBASE Ethernet Optical Interface Module(QSFP28)(HB)
h3cevtModuleSw-LSXM1CGQ18QGHC0             OBJECT IDENTIFIER ::= { h3cevtModuleSwitchType 1786 } -- 18-PORT 100GBASE Ethernet Optical Interface (QSFP28)/36-PORT 40GBASE Ethernet Optical Interface Module(QSFP+)(HC)
h3cevtModuleSw-LSXM1TGS48HB1               OBJECT IDENTIFIER ::= { h3cevtModuleSwitchType 1787 } -- 48-Port 10G BASE Ethernet Optical Interface Module(SFP+,LC)(HB)
h3cevtModuleSw-LSXM1TGS48HB0               OBJECT IDENTIFIER ::= { h3cevtModuleSwitchType 1788 } -- 48-Port 10G BASE Ethernet Optical Interface Module(SFP+,LC)(HB)
h3cevtModuleSw-LSQM1CGP24TSSC0             OBJECT IDENTIFIER ::= { h3cevtModuleSwitchType 1789 } -- Supervisor Engine Board With 24-Port 1000BASE-X Ethernet SFP Optical Interface+4-Port 10GBASE-R Ethernet SFP+ Optical Interfaces
h3cevtModuleSw-LSQM1CGP24TSSA0             OBJECT IDENTIFIER ::= { h3cevtModuleSwitchType 1790 } -- Supervisor Engine Board With 24-Port 1000BASE-X Ethernet SFP Optical Interface+4-Port 10GBASE-R Ethernet SFP+ Optical Interfaces
h3cevtModuleSw-LSQM1CGT24TSSC0             OBJECT IDENTIFIER ::= { h3cevtModuleSwitchType 1791 } -- Supervisor Engine Board With 24-Port 10/100/1000BASE-T Ethernet Interface+4-Port 10GBASE-R Ethernet SFP+ Optical Interfaces
h3cevtModuleSw-LSQM1CGT24TSSA0             OBJECT IDENTIFIER ::= { h3cevtModuleSwitchType 1792 } -- Supervisor Engine Board With 24-Port 10/100/1000BASE-T Ethernet Interface+4-Port 10GBASE-R Ethernet SFP+ Optical Interfaces
h3cevtModuleSw-LSQM2GP24SA0                OBJECT IDENTIFIER ::= { h3cevtModuleSwitchType 1793 } -- 24-Port GE Optical Interface(SFP,LC)(SA)
h3cevtModuleSw-LSX1SUPH1                   OBJECT IDENTIFIER ::= { h3cevtModuleSwitchType 1794 } -- Supervisor Engine Board
h3cevtModuleSw-LSX1SUPH0                   OBJECT IDENTIFIER ::= { h3cevtModuleSwitchType 1795 } -- Supervisor Engine Board
h3cevtModuleSw-LSX1SUP04H1                 OBJECT IDENTIFIER ::= { h3cevtModuleSwitchType 1796 } -- Supervisor Engine Board
h3cevtModuleSw-LSX1SUP04H0                 OBJECT IDENTIFIER ::= { h3cevtModuleSwitchType 1797 } -- Supervisor Engine Board
h3cevtModuleSw-LSXM1SFH08D0                OBJECT IDENTIFIER ::= { h3cevtModuleSwitchType 1798 } -- Fabric Module,Type H(Class D)
h3cevtModuleSw-LSXM1SFH04D0                OBJECT IDENTIFIER ::= { h3cevtModuleSwitchType 1799 } -- Fabric Module,Type H(Class D)
--
-- 1800 for united assignment
--
h3cevtModuleSw-LSXM1SFH16C0                OBJECT IDENTIFIER ::= { h3cevtModuleSwitchType 1800 } -- Fabric Module,Type H(Class C+)
h3cevtModuleSw-LSXM1SFH12D0                OBJECT IDENTIFIER ::= { h3cevtModuleSwitchType 1801 } -- Fabric Module,Type H(Class D)
h3cevtModuleSw-LSXM1QGS48HB0               OBJECT IDENTIFIER ::= { h3cevtModuleSwitchType 1802 } -- 48-Port 40GBASE Ethernet Optical Interface Module(QSFP+)(HB)
h3cevtModuleSw-LSXM1QGS48HC0               OBJECT IDENTIFIER ::= { h3cevtModuleSwitchType 1803 } -- 48-Port 40GBASE Ethernet Optical Interface Module(QSFP+)(HC)
h3cevtModuleSw-LSXM1CGQ36HB0               OBJECT IDENTIFIER ::= { h3cevtModuleSwitchType 1804 } -- 36-Port 100GBASE Ethernet Optical Interface Module(QSFP28)(HB)
h3cevtModuleSw-LSXM1TGS48C2HC0             OBJECT IDENTIFIER ::= { h3cevtModuleSwitchType 1805 } -- 48-PORT 10GBASE Ethernet Optical Interface (SFP+,LC)+2-PORT 100GBASE Ethernet Optical Interface Module(QSFP28)(HC)
h3cevtModuleSw-LSQM2GP44TSSE0              OBJECT IDENTIFIER ::= { h3cevtModuleSwitchType 1806 } -- 44-Port GE Optical Interface(SFP,LC)+4-Port 10GE Optical Interface Board(SFP+,LC)(SE)
h3cevtModuleSw-LSQM2GP24TSSA8              OBJECT IDENTIFIER ::= { h3cevtModuleSwitchType 1807 } -- 24-Port GE Optical Interface(SFP,LC)+4-Port 10GE Optical Interface Board(SFP+,LC)(SA)
h3cevtModuleSw-LSQM2GT48SA8                OBJECT IDENTIFIER ::= { h3cevtModuleSwitchType 1808 } -- 48-Port 1000Base-T Gigabit Ethernet Interface Board(RJ45)(SA)
h3cevtModuleSw-LSQM2GP48SA8                OBJECT IDENTIFIER ::= { h3cevtModuleSwitchType 1809 } -- 48-Port 1000BASE-X Ethernet Optical Interface Board(SFP,LC)(SA)
h3cevtModuleSw-EWPXM1CGP24TSSC0            OBJECT IDENTIFIER ::= { h3cevtModuleSwitchType 1810 } -- Supervisor Engine Board With 24-Port 1000BASE-X Ethernet SFP Optical Interface+4-Port 10GBASE-R Ethernet SFP+ Optical Interfaces
h3cevtModuleSw-EWPXM3MPUB0                 OBJECT IDENTIFIER ::= { h3cevtModuleSwitchType 1811 } -- Supervisor Engine Board
h3cevtModuleSw-EWPXM2MPUDS0                OBJECT IDENTIFIER ::= { h3cevtModuleSwitchType 1812 } -- Supervisor Engine Board
h3cevtModuleSw-EWPXM2TGS16SF0              OBJECT IDENTIFIER ::= { h3cevtModuleSwitchType 1813 } -- 16-Port 10GE Optical Interface Board(SFP+,LC)(SF)
h3cevtModuleSw-EWPXM2GP44TSSC0             OBJECT IDENTIFIER ::= { h3cevtModuleSwitchType 1814 } -- 44-Port GE Optical Interface(SFP,LC)+4-Port 10GE Optical Interface Board(SFP+,LC)(SC)
h3cevtModuleSw-EWPXM2GP24TSSC0             OBJECT IDENTIFIER ::= { h3cevtModuleSwitchType 1815 } -- 24-Port GE Optical Interface(SFP,LC)+4-Port 10GE Optical Interface Board(SFP+,LC)(SC)
h3cevtModuleSw-EWPXM1MAC0F                 OBJECT IDENTIFIER ::= { h3cevtModuleSwitchType 1816 } -- Access Controller Service Board
h3cevtModuleSw-LSQM1CGP24TSSA8             OBJECT IDENTIFIER ::= { h3cevtModuleSwitchType 1817 } -- Supervisor Engine Board With 24-Port 1000BASE-X Ethernet SFP Optical Interface+4-Port 10GBASE-R Ethernet SFP+ Optical Interfaces
h3cevtModuleSw-LSQM1CGT24TSSA8             OBJECT IDENTIFIER ::= { h3cevtModuleSwitchType 1818 } -- Supervisor Engine Board With 24-Port 10/100/1000BASE-T Ethernet Interface+4-Port 10GBASE-R Ethernet SFP+ Optical Interfaces
h3cevtModuleSw-LSWM1FWD0                   OBJECT IDENTIFIER ::= { h3cevtModuleSwitchType 1819 } -- Firewall Service Board
h3cevtModuleSw-LSUM2MPU10C0                OBJECT IDENTIFIER ::= { h3cevtModuleSwitchType 1820 } -- Supervisor Engine Board
h3cevtModuleSw-LSQM2MPU10C0                OBJECT IDENTIFIER ::= { h3cevtModuleSwitchType 1821 } -- Supervisor Engine Board
h3cevtModuleSw-LSQM2MPU10C3                OBJECT IDENTIFIER ::= { h3cevtModuleSwitchType 1822 } -- Supervisor Engine Board
h3cevtModuleSw-LSUM2FAB10C0                OBJECT IDENTIFIER ::= { h3cevtModuleSwitchType 1823 } -- Switching Fabric Module
h3cevtModuleSw-LSQM2FAB10C0                OBJECT IDENTIFIER ::= { h3cevtModuleSwitchType 1824 } -- Switching Fabric Module
h3cevtModuleSw-LSQM2FAB10C3                OBJECT IDENTIFIER ::= { h3cevtModuleSwitchType 1825 } -- Switching Fabric Module
h3cevtModuleSw-LSUM2CQGS12SG0              OBJECT IDENTIFIER ::= { h3cevtModuleSwitchType 1826 } -- 12-Port 40GBASE-R QSFP+ or 4-Port 100GBASE-R QSFP28 Optical Interface Board(SG)
h3cevtModuleSw-LSXM2CQGS12SG3              OBJECT IDENTIFIER ::= { h3cevtModuleSwitchType 1827 } -- 12-Port 40GBASE-R QSFP+ or 4-Port 100GBASE-R QSFP28 Optical Interface Board(SG)
h3cevtModuleSw-LSQM2CQGS12XSG0             OBJECT IDENTIFIER ::= { h3cevtModuleSwitchType 1828 } -- 12-Port 40GBASE-R QSFP+ or 4-Port 100GBASE-R QSFP28 Optical Interface Board(SG)
h3cevtModuleSw-LSQM1CQGS12SG0              OBJECT IDENTIFIER ::= { h3cevtModuleSwitchType 1829 } -- 12-Port 40GBASE-R QSFP+ or 4-Port 100GBASE-R QSFP28 Optical Interface Board(SG)
h3cevtModuleSw-LSXM1CGQ6QGHB0              OBJECT IDENTIFIER ::= { h3cevtModuleSwitchType 1830 } -- 6-Port 100GBASE Ethernet Optical Interface(QSFP28)/12-Port 40GBASE Ethernet Optical Interface Module(QSFP+)(HB)
h3cevtModuleSw-LSXM1CGQ6QGHB1              OBJECT IDENTIFIER ::= { h3cevtModuleSwitchType 1831 } -- 6-Port 100GBASE Ethernet Optical Interface(QSFP28)/12-Port 40GBASE Ethernet Optical Interface Module(QSFP+)(HB)
h3cevtModuleSw-LSXM1CGQ6QGHC0              OBJECT IDENTIFIER ::= { h3cevtModuleSwitchType 1832 } -- 6-Port 100GBASE Ethernet Optical Interface(QSFP28)/12-Port 40GBASE Ethernet Optical Interface Module(QSFP+)(HC)
h3cevtModuleSw-LSXM1QGS36HB0               OBJECT IDENTIFIER ::= { h3cevtModuleSwitchType 1833 } -- 36-Port 40GBASE Ethernet Optical Interface Module(QSFP+)(HB)
h3cevtModuleSw-LSXM1QGS36HB1               OBJECT IDENTIFIER ::= { h3cevtModuleSwitchType 1834 } -- 36-Port 40GBASE Ethernet Optical Interface Module(QSFP+)(HB)
h3cevtModuleSw-LSXM1QGS36HC0               OBJECT IDENTIFIER ::= { h3cevtModuleSwitchType 1835 } -- 36-Port 40GBASE Ethernet Optical Interface Module(QSFP+)(HC)
h3cevtModuleSw-LSXM1SUPC0                  OBJECT IDENTIFIER ::= { h3cevtModuleSwitchType 1836 } -- Supervisor Engine Unit
h3cevtModuleSw-LSXM1SUPC1                  OBJECT IDENTIFIER ::= { h3cevtModuleSwitchType 1837 } -- Supervisor Engine Unit
h3cevtModuleSw-LSXM1SUP04H0                OBJECT IDENTIFIER ::= { h3cevtModuleSwitchType 1838 } -- Supervisor Engine Unit
h3cevtModuleSw-LSXM1SUP04H1                OBJECT IDENTIFIER ::= { h3cevtModuleSwitchType 1839 } -- Supervisor Engine Unit
h3cevtModuleSw-LSXM1SUPH0                  OBJECT IDENTIFIER ::= { h3cevtModuleSwitchType 1840 } -- Supervisor Engine Unit
h3cevtModuleSw-LSXM1SUPH1                  OBJECT IDENTIFIER ::= { h3cevtModuleSwitchType 1841 } -- Supervisor Engine Unit
h3cevtModuleSw-EWPXM2WCMD0F                OBJECT IDENTIFIER ::= { h3cevtModuleSwitchType 1842 } -- 20G Access Controller Module
h3cevtModuleSw-LSUM2QGS24RSG0              OBJECT IDENTIFIER ::= { h3cevtModuleSwitchType 1843 } -- 24-Port 40GBASE-R Ethernet QSFP+ Optical Interface Board(SG)
h3cevtModuleSw-LSQM1QGS24RSG0              OBJECT IDENTIFIER ::= { h3cevtModuleSwitchType 1844 } -- 24-Port 40GBASE-R Ethernet QSFP+ Optical Interface Board(SG)
h3cevtModuleSw-LSXM2QGS24RSG3              OBJECT IDENTIFIER ::= { h3cevtModuleSwitchType 1845 } -- 24-Port 40GBASE-R Ethernet QSFP+ Optical Interface Board(SG)
h3cevtModuleSw-LSQM2QGS24RXSG0             OBJECT IDENTIFIER ::= { h3cevtModuleSwitchType 1846 } -- 24-Port 40GBASE-R Ethernet QSFP+ Optical Interface Board(SG)
h3cevtModuleSw-LSQM2TGS48RSG0              OBJECT IDENTIFIER ::= { h3cevtModuleSwitchType 1847 } -- 48-Port 10GBASE-R Ethernet SFP+ Optical Interface Board(SG)
h3cevtModuleSw-LSXM1X86SUPE0               OBJECT IDENTIFIER ::= { h3cevtModuleSwitchType 1848 } -- Cloud Supervisor Engine Unit
h3cevtModuleSw-LSXM1X86SUPE1               OBJECT IDENTIFIER ::= { h3cevtModuleSwitchType 1849 } -- Cloud Supervisor Engine Unit
h3cevtModuleSw-LSQM1CGS2QSA0               OBJECT IDENTIFIER ::= { h3cevtModuleSwitchType 1850 } -- 2-Port 100G Ethernet Optical Interface(QSFP28)+2-Port 40G Ethernet Optical Interface Module(QSFP+)
h3cevtModuleSw-LSUM1ACGDEC0                OBJECT IDENTIFIER ::= { h3cevtModuleSwitchType 1851 } -- SecBlade IV Application Control Module
h3cevtModuleSw-LSQM1ACGDSC0                OBJECT IDENTIFIER ::= { h3cevtModuleSwitchType 1852 } -- SecBlade IV Application Control Module
h3cevtModuleSw-LSXM1CGQ36HF1               OBJECT IDENTIFIER ::= { h3cevtModuleSwitchType 1853 } -- 36-Port 100GBASE Ethernet Optical Interface Module(QSFP28)(HF)
h3cevtModuleSw-LSXM1QGS48HF1               OBJECT IDENTIFIER ::= { h3cevtModuleSwitchType 1854 } -- 48-Port 40GBASE Ethernet Optical Interface Module(QSFP+)(HF)
h3cevtModuleSw-LSXM1CGQ18QGHF1             OBJECT IDENTIFIER ::= { h3cevtModuleSwitchType 1855 } -- 18-PORT 100GBASE Ethernet Optical Interface(QSFP28)/36-Port 40GBASE Ethernet Optical Interface Module(QSFP+)(HF)
h3cevtModuleSw-LSXM1QGS36HF1               OBJECT IDENTIFIER ::= { h3cevtModuleSwitchType 1856 } -- 36-Port 40GBASE Ethernet Optical Interface Module(QSFP+)(HF)
h3cevtModuleSw-LSXM1CGQ6QGHF1              OBJECT IDENTIFIER ::= { h3cevtModuleSwitchType 1857 } -- 6-Port 100GBASE Ethernet Optical Interface(QSFP28)/12-Port 40GBASE Ethernet Optical Interface Module(QSFP+)(HF)
h3cevtModuleSw-LSXM1QGS48HF0               OBJECT IDENTIFIER ::= { h3cevtModuleSwitchType 1858 } -- 48-Port 40GBASE Ethernet Optical Interface Module(QSFP+)(HF)
h3cevtModuleSw-LSXM1CGQ18QGHF0             OBJECT IDENTIFIER ::= { h3cevtModuleSwitchType 1859 } -- 18-PORT 100GBASE Ethernet Optical Interface(QSFP28)/36-Port 40GBASE Ethernet Optical Interface Module(QSFP+)(HF)
h3cevtModuleSw-LSXM1CGQ6QGHF0              OBJECT IDENTIFIER ::= { h3cevtModuleSwitchType 1860 } -- 6-Port 100GBASE Ethernet Optical Interface(QSFP28)/12-Port 40GBASE Ethernet Optical Interface Module(QSFP+)(HF)
h3cevtModuleSw-LSXM1TGS48HF0               OBJECT IDENTIFIER ::= { h3cevtModuleSwitchType 1861 } -- 48-Port 10GBASE Ethernet Optical Interface Module(SFP+,LC)(HF)
h3cevtModuleSw-LSXM1TGS48HF1               OBJECT IDENTIFIER ::= { h3cevtModuleSwitchType 1862 } -- 48-Port 10GBASE Ethernet Optical Interface Module(SFP+,LC)(HF)
h3cevtModuleSw-LSQM1GP24FC3                OBJECT IDENTIFIER ::= { h3cevtModuleSwitchType 1863 } -- 24-Port 1000BASE-X Optical Interface Board(SFP,LC)
h3cevtModuleSw-LSQM1GP24FD3                OBJECT IDENTIFIER ::= { h3cevtModuleSwitchType 1864 } -- 24-Port 1000BASE-X Optical Interface Board(SFP,LC)
h3cevtModuleSw-LSQM1GP24TSFC3              OBJECT IDENTIFIER ::= { h3cevtModuleSwitchType 1865 } -- 24-Port 1000BASE-X Optical Interface(SFP,LC)+4-Port 10GBASE-R Ethernet Optical Interface Board(SFP+,LC)
h3cevtModuleSw-LSQM1GP24TSFD3              OBJECT IDENTIFIER ::= { h3cevtModuleSwitchType 1866 } -- 24-Port 1000BASE-X Optical Interface(SFP,LC)+4-Port 10GBASE-R Ethernet Optical Interface Board(SFP+,LC)
h3cevtModuleSw-LSQM1GP40TS8FD0             OBJECT IDENTIFIER ::= { h3cevtModuleSwitchType 1867 } -- 40-Port 1000BASE-X Optical Interface(SFP,LC)+8-Port 10GBASE-R Ethernet Optical Interface Board(SFP+,LC)
h3cevtModuleSw-LSQM1GP48FC3                OBJECT IDENTIFIER ::= { h3cevtModuleSwitchType 1868 } -- 48-Port 1000BASE-X Optical Interface Board(SFP,LC)
h3cevtModuleSw-LSQM1GP48FD0                OBJECT IDENTIFIER ::= { h3cevtModuleSwitchType 1869 } -- 48-Port 1000BASE-X Optical Interface Board(SFP,LC)
h3cevtModuleSw-LSQM1GP48FD3                OBJECT IDENTIFIER ::= { h3cevtModuleSwitchType 1870 } -- 48-Port 1000BASE-X Optical Interface Board(SFP,LC)
h3cevtModuleSw-LSQM1GT48FC3                OBJECT IDENTIFIER ::= { h3cevtModuleSwitchType 1871 } -- 48-Port 10/100/1000BASE-T Electrical Interface Board(RJ45)
h3cevtModuleSw-LSQM1GT48FD0                OBJECT IDENTIFIER ::= { h3cevtModuleSwitchType 1872 } -- 48-Port 10/100/1000BASE-T Electrical Interface Board(RJ45)
h3cevtModuleSw-LSQM1GT48FD3                OBJECT IDENTIFIER ::= { h3cevtModuleSwitchType 1873 } -- 48-Port 10/100/1000BASE-T Electrical Interface Board(RJ45)
h3cevtModuleSw-LSQM1TGS24FC3               OBJECT IDENTIFIER ::= { h3cevtModuleSwitchType 1874 } -- 24-Port 10GBASE-R Ethernet Optical Interface Board(SFP+,LC)
h3cevtModuleSw-LSQM1TGS24FD0               OBJECT IDENTIFIER ::= { h3cevtModuleSwitchType 1875 } -- 24-Port 10GBASE-R Ethernet Optical Interface Board(SFP+,LC)
h3cevtModuleSw-LSQM1TGS24FD3               OBJECT IDENTIFIER ::= { h3cevtModuleSwitchType 1876 } -- 24-Port 10GBASE-R Ethernet Optical Interface Board(SFP+,LC)
h3cevtModuleSw-LSQM1TGS24XFD0              OBJECT IDENTIFIER ::= { h3cevtModuleSwitchType 1877 } -- 24-Port 10GBASE-R Ethernet Optical Interface Board(SFP+,LC)
h3cevtModuleSw-LSQM1TGS48RFE0              OBJECT IDENTIFIER ::= { h3cevtModuleSwitchType 1878 } -- 48-Port 10GBASE-R Ethernet Optical Interface Board(SFP+,LC)
h3cevtModuleSw-LSQM1TGS8FC3                OBJECT IDENTIFIER ::= { h3cevtModuleSwitchType 1879 } -- 8-Port 10GBASE-R Ethernet Optical Interface Board(SFP+,LC)
h3cevtModuleSw-LSQM1TGS8FD3                OBJECT IDENTIFIER ::= { h3cevtModuleSwitchType 1880 } -- 8-Port 10GBASE-R Ethernet Optical Interface Board(SFP+,LC)
h3cevtModuleSw-LSUM1GP40TS8FD0             OBJECT IDENTIFIER ::= { h3cevtModuleSwitchType 1881 } -- 40-Port 1000BASE-X Optical Interface(SFP,LC)+8-Port 10GBASE-R Ethernet Optical Interface Board(SFP+,LC)
h3cevtModuleSw-LSUM1GP48FD0                OBJECT IDENTIFIER ::= { h3cevtModuleSwitchType 1882 } -- 48-Port 1000BASE-X Optical Interface Board(SFP,LC)
h3cevtModuleSw-LSUM1GP48FD3                OBJECT IDENTIFIER ::= { h3cevtModuleSwitchType 1883 } -- 48-Port 1000BASE-X Optical Interface Board(SFP,LC)
h3cevtModuleSw-LSUM1GT48FD0                OBJECT IDENTIFIER ::= { h3cevtModuleSwitchType 1884 } -- 48-Port 10/100/1000BASE-T Electrical Interface Board(RJ45)
h3cevtModuleSw-LSUM1GT48FD3                OBJECT IDENTIFIER ::= { h3cevtModuleSwitchType 1885 } -- 48-Port 10/100/1000BASE-T Electrical Interface Board(RJ45)
h3cevtModuleSw-LSUM1TGS24FD0               OBJECT IDENTIFIER ::= { h3cevtModuleSwitchType 1886 } -- 24-Port 10GBASE-R Ethernet Optical Interface Board(SFP+,LC)
h3cevtModuleSw-LSUM1TGS24FD3               OBJECT IDENTIFIER ::= { h3cevtModuleSwitchType 1887 } -- 24-Port 10GBASE-R Ethernet Optical Interface Board(SFP+,LC)
h3cevtModuleSw-LSXM1GP40TS8FD0             OBJECT IDENTIFIER ::= { h3cevtModuleSwitchType 1888 } -- 40-Port 1000BASE-X Optical Interface(SFP,LC)+8-Port 10GBASE-R Ethernet Optical Interface Board(SFP+,LC)
h3cevtModuleSw-LSXM1GT48FD3                OBJECT IDENTIFIER ::= { h3cevtModuleSwitchType 1889 } -- 48-Port 10/100/1000BASE-T Electrical Interface Board(RJ45)
h3cevtModuleSw-LSXM1TGS24FD3               OBJECT IDENTIFIER ::= { h3cevtModuleSwitchType 1890 } -- 24-Port 10GBASE-R Ethernet Optical Interface Board(SFP+,LC)
h3cevtModuleSw-LSQM1MPUS10C3               OBJECT IDENTIFIER ::= { h3cevtModuleSwitchType 1891 } -- Supervisor Engine Board
h3cevtModuleSw-LSQM1MPUSA3                 OBJECT IDENTIFIER ::= { h3cevtModuleSwitchType 1892 } -- Supervisor Engine Board
h3cevtModuleSw-LSQM2SUPA3                  OBJECT IDENTIFIER ::= { h3cevtModuleSwitchType 1893 } -- Supervisor Engine Board
h3cevtModuleSw-LSXM1SFH16E1                OBJECT IDENTIFIER ::= { h3cevtModuleSwitchType 1894 } -- S12516X-AF Fabric Module,Type H(Class E)
h3cevtModuleSw-LSXM1SFH16E0                OBJECT IDENTIFIER ::= { h3cevtModuleSwitchType 1895 } -- S12516X-AF Fabric Module,Type H(Class E)
h3cevtModuleSw-LSXM1GP40TS8FD3             OBJECT IDENTIFIER ::= { h3cevtModuleSwitchType 1896 } -- 40-Port 1000BASE-X Optical Interface(SFP,LC)+8-Port 10GBASE-R Ethernet Optical Interface Board(SFP+,LC)
h3cevtModuleSw-LSQM1MPUS10C0               OBJECT IDENTIFIER ::= { h3cevtModuleSwitchType 1897 } -- Supervisor Engine Board
h3cevtModuleSw-LSQM1MPUSA0                 OBJECT IDENTIFIER ::= { h3cevtModuleSwitchType 1898 } -- Supervisor Engine Board
h3cevtModuleSw-LSQM2SUPA0                  OBJECT IDENTIFIER ::= { h3cevtModuleSwitchType 1899 } -- Supervisor Engine Board
h3cevtModuleSw-LSQM1TGS16FC3               OBJECT IDENTIFIER ::= { h3cevtModuleSwitchType 1900 } -- 16-Port 10GBASE-R Ethernet SFP+ Optical Interface Board(FC)
h3cevtModuleSw-LSQM1TGS16FD0               OBJECT IDENTIFIER ::= { h3cevtModuleSwitchType 1901 } -- 16-Port 10GBASE-R Ethernet SFP+ Optical Interface Board(FD)
h3cevtModuleSw-LSQM1TGS16FD3               OBJECT IDENTIFIER ::= { h3cevtModuleSwitchType 1902 } -- 16-Port 10GBASE-R Ethernet SFP+ Optical Interface Board(FD)
h3cevtModuleSw-LSQM2TGS48SG0               OBJECT IDENTIFIER ::= { h3cevtModuleSwitchType 1903 } -- 48-Port 10GBASE-R Ethernet SFP+ Optical Interface Board(SG)
h3cevtModuleSw-LSQM2TGS48SG3               OBJECT IDENTIFIER ::= { h3cevtModuleSwitchType 1904 } -- 48-Port 10GBASE-R Ethernet SFP+ Optical Interface Board(SG)
h3cevtModuleSw-LSXM1CGQ48HB1               OBJECT IDENTIFIER ::= { h3cevtModuleSwitchType 1905 } -- 48-Port 100GBASE Ethernet Optical Interface Module(QSFP+)(HB)
h3cevtModuleSw-LSQM1MPUS06A8               OBJECT IDENTIFIER ::= { h3cevtModuleSwitchType 1906 } -- Supervisor Engine Board
h3cevtModuleSw-LSQM1TGS16FD8               OBJECT IDENTIFIER ::= { h3cevtModuleSwitchType 1907 } -- 16-Port 10GBASE-R Ethernet SFP+ Optical Interface Board(FD)
h3cevtModuleSw-LSXM1SFH08E1                OBJECT IDENTIFIER ::= { h3cevtModuleSwitchType 1908 } -- Fabric Module,Type H(Class E)

h3cevtModuleSw-LSXM1SFH08CC0               OBJECT IDENTIFIER ::= { h3cevtModuleSwitchType 1909 } -- S12508M-AF Fabric Module,Type H(Class C)
h3cevtModuleSw-LSXM1SUP08C0                OBJECT IDENTIFIER ::= { h3cevtModuleSwitchType 1910 } -- S12508M-AF Supervisor Engine Unit
h3cevtModuleSw-LSUM2FAB04D0                OBJECT IDENTIFIER ::= { h3cevtModuleSwitchType 1911 } -- Switching Fabric Module
h3cevtModuleSw-LSUM2FAB04D3                OBJECT IDENTIFIER ::= { h3cevtModuleSwitchType 1912 } -- Switching Fabric Module
h3cevtModuleSw-LSXM2FAB04D3                OBJECT IDENTIFIER ::= { h3cevtModuleSwitchType 1913 } -- Switching Fabric Module
h3cevtModuleSw-LSUM2FAB04B0                OBJECT IDENTIFIER ::= { h3cevtModuleSwitchType 1914 } -- Switching Fabric Module
h3cevtModuleSw-LSUM2FAB04B3                OBJECT IDENTIFIER ::= { h3cevtModuleSwitchType 1915 } -- Switching Fabric Module
h3cevtModuleSw-LSUM2FAB08D0                OBJECT IDENTIFIER ::= { h3cevtModuleSwitchType 1916 } -- Switching Fabric Module
h3cevtModuleSw-LSUM2FAB08D3                OBJECT IDENTIFIER ::= { h3cevtModuleSwitchType 1917 } -- Switching Fabric Module
h3cevtModuleSw-LSXM2FAB08D3                OBJECT IDENTIFIER ::= { h3cevtModuleSwitchType 1918 } -- Switching Fabric Module
h3cevtModuleSw-LSUM2FAB08B0                OBJECT IDENTIFIER ::= { h3cevtModuleSwitchType 1919 } -- Switching Fabric Module
h3cevtModuleSw-LSUM2FAB08B3                OBJECT IDENTIFIER ::= { h3cevtModuleSwitchType 1920 } -- Switching Fabric Module
h3cevtModuleSw-LSUM2FAB12D0                OBJECT IDENTIFIER ::= { h3cevtModuleSwitchType 1921 } -- Switching Fabric Module
h3cevtModuleSw-LSUM2FAB12D3                OBJECT IDENTIFIER ::= { h3cevtModuleSwitchType 1922 } -- Switching Fabric Module
h3cevtModuleSw-LSXM2FAB12D3                OBJECT IDENTIFIER ::= { h3cevtModuleSwitchType 1923 } -- Switching Fabric Module
h3cevtModuleSw-LSUM2FAB12B0                OBJECT IDENTIFIER ::= { h3cevtModuleSwitchType 1924 } -- Switching Fabric Module
h3cevtModuleSw-LSUM2FAB12B3                OBJECT IDENTIFIER ::= { h3cevtModuleSwitchType 1925 } -- Switching Fabric Module
h3cevtModuleSw-LSQM1CGS2FE0                OBJECT IDENTIFIER ::= { h3cevtModuleSwitchType 1926 } -- 2-Port 100GBASE-R Ethernet QSFP28 Optical Interface Board(FE)
h3cevtModuleSw-LSQM1CGS2FE3                OBJECT IDENTIFIER ::= { h3cevtModuleSwitchType 1927 } -- 2-Port 100GBASE-R Ethernet QSFP28 Optical Interface Board(FE)
h3cevtModuleSw-LSQM1CGS2XFE0               OBJECT IDENTIFIER ::= { h3cevtModuleSwitchType 1928 } -- 2-Port 100GBASE-R Ethernet QSFP28 Optical Interface Board(FE)
h3cevtModuleSw-LSUM1CGS2FE0                OBJECT IDENTIFIER ::= { h3cevtModuleSwitchType 1929 } -- 2-Port 100GBASE-R Ethernet QSFP28 Optical Interface Board(FE)
h3cevtModuleSw-LSUM1CGS2FE3                OBJECT IDENTIFIER ::= { h3cevtModuleSwitchType 1930 } -- 2-Port 100GBASE-R Ethernet QSFP28 Optical Interface Board(FE)
h3cevtModuleSw-LSXM1CGS2FE3                OBJECT IDENTIFIER ::= { h3cevtModuleSwitchType 1931 } -- 2-Port 100GBASE-R Ethernet QSFP28 Optical Interface Board(FE)
h3cevtModuleSw-LSUM1TGS16FD0               OBJECT IDENTIFIER ::= { h3cevtModuleSwitchType 1932 } -- 16-Port 10GBASE-R Ethernet SFP+ Optical Interface Board(FD)
h3cevtModuleSw-LSUM1TGS16FD3               OBJECT IDENTIFIER ::= { h3cevtModuleSwitchType 1933 } -- 16-Port 10GBASE-R Ethernet SFP+ Optical Interface Board(FD)
h3cevtModuleSw-LSQM1TGS16XFD0              OBJECT IDENTIFIER ::= { h3cevtModuleSwitchType 1934 } -- 16-Port 10GBASE-R Ethernet SFP+ Optical Interface Board(FD)
h3cevtModuleSw-LSQM1GP40TS8FC3             OBJECT IDENTIFIER ::= { h3cevtModuleSwitchType 1935 } -- 40-Port 1000BASE-X Optical Interface(SFP,LC)+8-Port 10GBASE-R Ethernet Optical Interface Board(SFP+,LC)
h3cevtModuleSw-S76-16XFSF                  OBJECT IDENTIFIER ::= { h3cevtModuleSwitchType 1936 } -- 16-Port 10GE Optical Interface Board(SFP+,LC)(SF)
h3cevtModuleSw-S76-24EP2XFSC-OLT           OBJECT IDENTIFIER ::= { h3cevtModuleSwitchType 1937 } -- 24-Port 1G EPON OLT Optical Interface(SFP,SC)+2-Port 10GE Optical Interface Board(SFP+,LC)(SC)
h3cevtModuleSw-DS-3E7600-24T20F4X-SC       OBJECT IDENTIFIER ::= { h3cevtModuleSwitchType 1938 } -- 24-Port 1000Base-T Gigabit Ethernet Interface Board(RJ45)+20-Port GE Optical Interface(SFP,LC)+4-Port 10GE Optical Interface Board(SFP+,LC)(SC)
h3cevtModuleSw-LSUM1FAB04E0                OBJECT IDENTIFIER ::= { h3cevtModuleSwitchType 1939 } -- Switching Fabric Module
h3cevtModuleSw-LSUM1FAB08E0                OBJECT IDENTIFIER ::= { h3cevtModuleSwitchType 1940 } -- Switching Fabric Module
h3cevtModuleSw-LSUM1FAB12E0                OBJECT IDENTIFIER ::= { h3cevtModuleSwitchType 1941 } -- Switching Fabric Module
h3cevtModuleSw-LSXM1CGQ8FX1                OBJECT IDENTIFIER ::= { h3cevtModuleSwitchType 1942 } -- 8-Port 100GBASE Ethernet Optical Interface Module(QSFP28)(FX)
h3cevtModuleSw-LSQM1IPSDSC0                OBJECT IDENTIFIER ::= { h3cevtModuleSwitchType 1943 } -- SecBlade IV Intrusion Prevention System Module
h3cevtModuleSw-LSQM2ACGDSC0                OBJECT IDENTIFIER ::= { h3cevtModuleSwitchType 1944 } -- SecBlade IV Application Control Module
h3cevtModuleSw-LSQM1ADEDSC0                OBJECT IDENTIFIER ::= { h3cevtModuleSwitchType 1945 } -- SecBlade IV Load Balancing Module
h3cevtModuleSw-LSWM1ADED0                  OBJECT IDENTIFIER ::= { h3cevtModuleSwitchType 1946 } -- SecBlade IV Load Balancing Card
h3cevtModuleSw-LSWM1IPSD0                  OBJECT IDENTIFIER ::= { h3cevtModuleSwitchType 1947 } -- SecBlade IV Intrusion Prevention System Card
h3cevtModuleSw-LSQM1GP40TS8FD3             OBJECT IDENTIFIER ::= { h3cevtModuleSwitchType 1948 } -- 40-Port 1000BASE-X Optical Interface(SFP,LC)+8-Port 10GBASE-R Ethernet Optical Interface Board(SFP+,LC)
h3cevtModuleSw-LSUM1SUPXD0                 OBJECT IDENTIFIER ::= { h3cevtModuleSwitchType 1949 } -- Supervisor Engine Board
h3cevtModuleSw-LSUM1CQGS32SF0              OBJECT IDENTIFIER ::= { h3cevtModuleSwitchType 1950 } -- 32-Port 40GBASE-R QSFP+ or 16-Port 100GBASE-R QSFP28 Optical Interface Board(SF)
h3cevtModuleSw-LSUM1TGS48XSG0              OBJECT IDENTIFIER ::= { h3cevtModuleSwitchType 1951 } -- 48-Port 10GBASE-R Ethernet SFP+ Optical Interface Board(SG)
h3cevtModuleSw-LSUM1FAB08XE0               OBJECT IDENTIFIER ::= { h3cevtModuleSwitchType 1952 } -- Switching Fabric Module
h3cevtModuleSw-LSUM1FAB16XD0               OBJECT IDENTIFIER ::= { h3cevtModuleSwitchType 1953 } -- Switching Fabric Module
h3cevtModuleSw-LSXM1SFH02E0                OBJECT IDENTIFIER ::= { h3cevtModuleSwitchType 1954 } -- Switching Fabric Module
h3cevtModuleSw-LSXM1SFH02E1                OBJECT IDENTIFIER ::= { h3cevtModuleSwitchType 1955 } -- Switching Fabric Module
h3cevtModuleSw-LSXM1SFH12C0                OBJECT IDENTIFIER ::= { h3cevtModuleSwitchType 1956 } -- Fabric Module,Type H(Class C)
h3cevtModuleSw-LSXM1SFH12C1                OBJECT IDENTIFIER ::= { h3cevtModuleSwitchType 1957 } -- Fabric Module,Type H(Class C)
h3cevtModuleSw-LSUM1CQGS12XSG0             OBJECT IDENTIFIER ::= { h3cevtModuleSwitchType 1958 } -- 12-Port 40GBASE-R QSFP+ or 4-Port 100GBASE-R QSFP28 Optical Interface Board(SG)
h3cevtModuleSw-LSQM1CTGS24QSFD0            OBJECT IDENTIFIER ::= { h3cevtModuleSwitchType 1959 } -- Supervisor Engine Board With 24-Port 10GBASE-R SFP+ Optical Interface+2-Port 40GBASE-R QSFP+ Optical Interfaces or 1-Port 100GBASE-R QSFP28 Optical Interfaces
h3cevtModuleSw-LSQM1TGS24QSFD0             OBJECT IDENTIFIER ::= { h3cevtModuleSwitchType 1960 } -- 24-Port 10GBASE-R Optical Interface(SFP+,LC)+2-Port 40GBASE-R Optical Interface Board(QSFP+) or 1-Port 100GBASE-R Optical Interface Board(QSFP28)
h3cevtModuleSw-LSUM1WBCZ720RT              OBJECT IDENTIFIER ::= { h3cevtModuleSwitchType 1961 } -- Access Controller Service Board
h3cevtModuleSw-LSQM1WBCZ720                OBJECT IDENTIFIER ::= { h3cevtModuleSwitchType 1962 } -- Access Controller Service Board
h3cevtModuleSw-DS-3E7610-X-MPU             OBJECT IDENTIFIER ::= { h3cevtModuleSwitchType 1963 } -- Supervisor Engine Board
h3cevtModuleSw-DS-3E7610-X-CLOS            OBJECT IDENTIFIER ::= { h3cevtModuleSwitchType 1964 } -- Switching Fabric Module
h3cevtModuleSw-DS-3E7610-X-32X4QX-SF       OBJECT IDENTIFIER ::= { h3cevtModuleSwitchType 1965 } -- 32-Port 10GBASE-R Ethernet Optical Interface(SFP+,LC)+4-Port 40GBASE-R Ethernet Optical Interface Board(QSFP+,LC)(SF)
h3cevtModuleSw-DS-3E7610-X-16X-SF          OBJECT IDENTIFIER ::= { h3cevtModuleSwitchType 1966 } -- 16-Port 10GBASE-R Ethernet SFP+ Optical
h3cevtModuleSw-DS-3E7610-X-44F4X-SE        OBJECT IDENTIFIER ::= { h3cevtModuleSwitchType 1967 } -- 44-Port GE Optical Interface(SFP,LC)+4-Port 10GE Optical Interface Board(SFP+,LC)(SE)
h3cevtModuleSw-DS-3E7610-X-48T-SE          OBJECT IDENTIFIER ::= { h3cevtModuleSwitchType 1968 } -- 48-Port 1000Base-T Gigabit Ethernet Interface Board(RJ45)(SE)
h3cevtModuleSw-LSQM2GT24PTSSC8             OBJECT IDENTIFIER ::= { h3cevtModuleSwitchType 1969 } -- 24-Port 1000Base-T Gigabit Ethernet Interface Board(RJ45)+20-Port GE Optical Interface(SFP,LC)+4-Port 10GE Optical Interface Board(SFP+,LC)(SC)
h3cevtModuleSw-LSQM1CGP24TSSC8             OBJECT IDENTIFIER ::= { h3cevtModuleSwitchType 1970 } -- Supervisor Engine Board With 24-Port 1000BASE-X Ethernet SFP Optical Interface+4-Port 10GBASE-R Ethernet SFP+ Optical Interfaces
h3cevtModuleSw-LSQM1CGT24TSSC8             OBJECT IDENTIFIER ::= { h3cevtModuleSwitchType 1971 } -- Supervisor Engine Board With 24-Port 10/100/1000BASE-T Ethernet Interface+4-Port 10GBASE-R Ethernet SFP+ Optical Interfaces
h3cevtModuleSw-LSQM1MPUS06B8               OBJECT IDENTIFIER ::= { h3cevtModuleSwitchType 1972 } -- Supervisor Engine Board
h3cevtModuleSw-LSVM1MPUB1                  OBJECT IDENTIFIER ::= { h3cevtModuleSwitchType 1973 } -- Supervisor Engine Unit
h3cevtModuleSw-LSXM1TGS24QGMODHB0          OBJECT IDENTIFIER ::= { h3cevtModuleSwitchType 1974 } -- 24-Port 10GBASE Ethernet Optical Interface(SFP+,LC)+4-Port 40GBASE Ethernet Optical Interface Module(QSFP+)(HB),With 1 Expansion Slot
h3cevtModuleSw-LSXM1TGS24QGMODHB1          OBJECT IDENTIFIER ::= { h3cevtModuleSwitchType 1975 } -- 24-Port 10GBASE Ethernet Optical Interface(SFP+,LC)+4-Port 40GBASE Ethernet Optical Interface Module(QSFP+)(HB),With 1 Expansion Slot
h3cevtModuleSw-LSXM1TGS48QGHA0             OBJECT IDENTIFIER ::= { h3cevtModuleSwitchType 1976 } -- 48-Port 10GBASE Ethernet Optical Interface(SFP+,LC)+4-Port 40GBASE Ethernet Optical Interface Module(QSFP+)(HA)
h3cevtModuleSw-LSXM1TGS48QGHA1             OBJECT IDENTIFIER ::= { h3cevtModuleSwitchType 1977 } -- 48-Port 10GBASE Ethernet Optical Interface(SFP+,LC)+4-Port 40GBASE Ethernet Optical Interface Module(QSFP+)(HA)
h3cevtModuleSw-LSXM1CGC2A0                 OBJECT IDENTIFIER ::= { h3cevtModuleSwitchType 1978 } -- 2-Ports 100G CFP Ethernet Optical Interface Module(CFP)
h3cevtModuleSw-LSXM1CGC2A1                 OBJECT IDENTIFIER ::= { h3cevtModuleSwitchType 1979 } -- 2-Ports 100G CFP Ethernet Optical Interface Module(CFP)
h3cevtModuleSw-LSQM2FWDSC0                 OBJECT IDENTIFIER ::= { h3cevtModuleSwitchType 1980 } -- Firewall Service Board
h3cevtModuleSw-LSQM1XPT12TSFD0             OBJECT IDENTIFIER ::= { h3cevtModuleSwitchType 1981 } -- 12-Port 10/1GBASE EPON OLT Optical Interface(XFP,LC)+8-Port 10GBASE-R Ethernet Optical Interface Board(SFP+,LC)
h3cevtModuleSw-LSXM1QGS24HB0               OBJECT IDENTIFIER ::= { h3cevtModuleSwitchType 1982 } -- 24-Port 40GBASE Ethernet Optical Interface Module(QSFP+)(HB)
h3cevtModuleSw-LSXM1QGS24HB1               OBJECT IDENTIFIER ::= { h3cevtModuleSwitchType 1983 } -- 24-Port 40GBASE Ethernet Optical Interface Module(QSFP+)(HB)
h3cevtModuleSw-LSXM1QGS24HC0               OBJECT IDENTIFIER ::= { h3cevtModuleSwitchType 1984 } -- 24-Port 40GBASE Ethernet Optical Interface Module(QSFP+)(HC)
h3cevtModuleSw-LSXM1SUP01B1                OBJECT IDENTIFIER ::= { h3cevtModuleSwitchType 1985 } -- Supervisor Engine Board
h3cevtModuleSw-LSCM1SUP03A0                OBJECT IDENTIFIER ::= { h3cevtModuleSwitchType 1986 } -- Supervisor Engine Board
h3cevtModuleSw-LSCM1SUP03A0-Z              OBJECT IDENTIFIER ::= { h3cevtModuleSwitchType 1987 } -- Supervisor Engine Board
h3cevtModuleSw-LSCM1MPUS06A0               OBJECT IDENTIFIER ::= { h3cevtModuleSwitchType 1988 } -- Supervisor Engine Board
h3cevtModuleSw-LSCM1MPUS06A0-Z             OBJECT IDENTIFIER ::= { h3cevtModuleSwitchType 1989 } -- Supervisor Engine Board
h3cevtModuleSw-LSCM1GT48SC0                OBJECT IDENTIFIER ::= { h3cevtModuleSwitchType 1990 } -- 48-Port 10/100/1000BASE-T Electrical Interface Board(RJ45)(SC)
h3cevtModuleSw-LSCM1GT48SC0-Z              OBJECT IDENTIFIER ::= { h3cevtModuleSwitchType 1991 } -- 48-Port 10/100/1000BASE-T Electrical Interface Board(RJ45)(SC)
h3cevtModuleSw-LSCM1TGS48SE0               OBJECT IDENTIFIER ::= { h3cevtModuleSwitchType 1992 } -- 48-Port 10GBASE-R Ethernet SFP+ Optical Interface Board(SE)
h3cevtModuleSw-LSCM1TGS48SE0-Z             OBJECT IDENTIFIER ::= { h3cevtModuleSwitchType 1993 } -- 48-Port 10GBASE-R Ethernet SFP+ Optical Interface Board(SE)
h3cevtModuleSw-LSCM1QGS8CSSE0              OBJECT IDENTIFIER ::= { h3cevtModuleSwitchType 1994 } -- 8-Port 40GBASE-R QSFP+ + 4-Port 100GBASE-R QSFP28 Optical Interface Board(SE)
h3cevtModuleSw-LSCM1QGS8CSSE0-Z            OBJECT IDENTIFIER ::= { h3cevtModuleSwitchType 1995 } -- 8-Port 40GBASE-R QSFP+ + 4-Port 100GBASE-R QSFP28 Optical Interface Board(SE)
h3cevtModuleSw-LSWM2SP4P                   OBJECT IDENTIFIER ::= { h3cevtModuleSwitchType 1996 } -- 4-Port 10GBASE-R Ethernet SFP+ Optical Interface Module
h3cevtModuleSw-LSWM2SP4P-Z                 OBJECT IDENTIFIER ::= { h3cevtModuleSwitchType 1997 } -- 4-Port 10GBASE-R Ethernet SFP+ Optical Interface Module
h3cevtModuleSw-LSQM1MPUS10B0               OBJECT IDENTIFIER ::= { h3cevtModuleSwitchType 1998 } -- Supervisor Engine Board
h3cevtModuleSw-LSQM1MPUS10B3               OBJECT IDENTIFIER ::= { h3cevtModuleSwitchType 1999 } -- Supervisor Engine Board
h3cevtModuleSw-LSQM1MPUSC0                 OBJECT IDENTIFIER ::= { h3cevtModuleSwitchType 2000 } -- Supervisor Engine Board
h3cevtModuleSw-LSQM1MPUSC3                 OBJECT IDENTIFIER ::= { h3cevtModuleSwitchType 2001 } -- Supervisor Engine Board
h3cevtModuleSw-LSQM2GP24TSSC8              OBJECT IDENTIFIER ::= { h3cevtModuleSwitchType 2002 } -- 24-Port 1000BASE-X Optical Interface(SFP,LC)+4-Port 10GBASE-R Ethernet Optical Interface Board(SFP+,LC)(SC)
h3cevtModuleSw-LSQM2GT24TSSC8              OBJECT IDENTIFIER ::= { h3cevtModuleSwitchType 2003 } -- 24-Port 10/100/1000BASE-T Electrical Interface(RJ45)+4-Port 10GBASE-R Ethernet Optical Interface Board(SFP+,LC)(SC)
h3cevtModuleSw-LSXM1TGS24CGMODHD0          OBJECT IDENTIFIER ::= { h3cevtModuleSwitchType 2004 } -- 24-Port 10GBASE Ethernet Optical Interface(SFP+,LC)+4-Port 100GBASE Ethernet Optical Interface Module(QSFP28)(HD),With 1 Expansion Slot
h3cevtModuleSw-LSXM1TGS24CGMODHD1          OBJECT IDENTIFIER ::= { h3cevtModuleSwitchType 2005 } -- 24-Port 10GBASE Ethernet Optical Interface(SFP+,LC)+4-Port 100GBASE Ethernet Optical Interface Module(QSFP28)(HD),With 1 Expansion Slot
h3cevtModuleSw-LSQM1TGS16GPSA0             OBJECT IDENTIFIER ::= { h3cevtModuleSwitchType 2006 } -- 24-Port 1000BASE-R Ethernet Optical Interface(SFP,LC)+16-Port 10GBASE-R Ethernet Optical Interface Board(SFP+,LC)
h3cevtModuleSw-EWPXM2TGS48SG0              OBJECT IDENTIFIER ::= { h3cevtModuleSwitchType 2007 } -- 48-Port 10GBASE-R Ethernet SFP+ Optical Interface Board(SG)
h3cevtModuleSw-EWPXM1TGS16FD0              OBJECT IDENTIFIER ::= { h3cevtModuleSwitchType 2008 } -- 16-Port 10GBASE-R Ethernet SFP+ Optical Interface Board(FD)
h3cevtModuleSw-LSXM1CGQ36HF0               OBJECT IDENTIFIER ::= { h3cevtModuleSwitchType 2009 } -- 36-Port 100GBASE Ethernet Optical Interface Module(QSFP28)(HF)
h3cevtModuleSw-LSXM2SUPT0                  OBJECT IDENTIFIER ::= { h3cevtModuleSwitchType 2010 } -- Supervisor Engine Board
h3cevtModuleSw-LSXM2SUPT1                  OBJECT IDENTIFIER ::= { h3cevtModuleSwitchType 2011 } -- Supervisor Engine Board
h3cevtModuleSw-LSXM1SFT16E0                OBJECT IDENTIFIER ::= { h3cevtModuleSwitchType 2012 } -- Switch Fabric Board
h3cevtModuleSw-LSXM1SFT16E1                OBJECT IDENTIFIER ::= { h3cevtModuleSwitchType 2013 } -- Switch Fabric Board
h3cevtModuleSw-lsxM1CGQ36TD0               OBJECT IDENTIFIER ::= { h3cevtModuleSwitchType 2014 } -- 36-Port 100GBASE Ethernet Optical Interface Board(QSFP28)
h3cevtModuleSw-lsxM1CGQ36TD1               OBJECT IDENTIFIER ::= { h3cevtModuleSwitchType 2015 } -- 36-Port 100GBASE Ethernet Optical Interface Board(QSFP28)
h3cevtModuleSw-LSQM1TGT24FD0               OBJECT IDENTIFIER ::= { h3cevtModuleSwitchType 2016 } -- 24-Port 10GBASE-T Ethernet Copper Interface Module(RJ45)(FD)
h3cevtModuleSw-LSUM1TGT24FD0               OBJECT IDENTIFIER ::= { h3cevtModuleSwitchType 2017 } -- 24-Port 10GBASE-T Ethernet Copper Interface Module(RJ45)(FD)
h3cevtModuleSw-LSXM2SFT08E0                OBJECT IDENTIFIER ::= { h3cevtModuleSwitchType 2018 } -- S12508F-AF Fabric Module,Type T(Class E)
h3cevtModuleSw-LSXM2SFT08E1                OBJECT IDENTIFIER ::= { h3cevtModuleSwitchType 2019 } -- S12508F-AF Fabric Module,Type T(Class E)
h3cevtModuleSw-LSXM1CCP8HF0                OBJECT IDENTIFIER ::= { h3cevtModuleSwitchType 2020 } -- 8-Port 200GBASE Ethernet Optical Interface Module(CFP2)(HF)
h3cevtModuleSw-LSXM1CCP8HF1                OBJECT IDENTIFIER ::= { h3cevtModuleSwitchType 2021 } -- 8-Port 200GBASE Ethernet Optical Interface Module(CFP2)(HF)
h3cevtModuleSw-LSUM1MPUS06XEC0             OBJECT IDENTIFIER ::= { h3cevtModuleSwitchType 2022 } -- Supervisor Engine Board
h3cevtModuleSw-LSUM1FAB06XEC0              OBJECT IDENTIFIER ::= { h3cevtModuleSwitchType 2023 } -- Switching Fabric Module
h3cevtModuleSw-LSUM1TGS48SH0               OBJECT IDENTIFIER ::= { h3cevtModuleSwitchType 2024 } -- 48-Port 10G Ethernet Optical Interface Module(SFP+,LC)(SH)
h3cevtModuleSw-LSUM1CGS8SH0                OBJECT IDENTIFIER ::= { h3cevtModuleSwitchType 2025 } -- 8-Port 100G Ethernet Optical Interface Module(QSFP28)(SH)
h3cevtModuleSw-LSUM1TFGS24CSSH0            OBJECT IDENTIFIER ::= { h3cevtModuleSwitchType 2026 } -- 24-Port 25G Ethernet Optical Interface(SFP28)+4-Port 100G Ethernet Optical Interface Module(QSFP28)(SH)
h3cevtModuleSw-LSUM1CGS20XSH0              OBJECT IDENTIFIER ::= { h3cevtModuleSwitchType 2027 } -- 20-Port 100G Ethernet Optical Interface Module(QSFP28)(SH)
h3cevtModuleSw-S8610-MPU                   OBJECT IDENTIFIER ::= { h3cevtModuleSwitchType 2028 } -- Supervisor Engine Board
h3cevtModuleSw-S8610-NET                   OBJECT IDENTIFIER ::= { h3cevtModuleSwitchType 2029 } -- Switching Fabric Module
h3cevtModuleSw-S86-44GF4XFSE               OBJECT IDENTIFIER ::= { h3cevtModuleSwitchType 2030 } -- 44-Port GE Optical Interface(SFP,LC)+4-Port 10GE Optical Interface Board(SFP+,LC)(SE)
h3cevtModuleSw-S86-48GTSE                  OBJECT IDENTIFIER ::= { h3cevtModuleSwitchType 2031 } -- 48-Port 1000Base-T Gigabit Ethernet Interface Board(RJ45)(SE)
h3cevtModuleSw-S86-12QFSG                  OBJECT IDENTIFIER ::= { h3cevtModuleSwitchType 2032 } -- 12-Port 40GBASE-R Ethernet QSFP+ Optical Interface Board(SG)
h3cevtModuleSw-S86-48XFSG                  OBJECT IDENTIFIER ::= { h3cevtModuleSwitchType 2033 } -- 48-Port 10GBASE-R Ethernet SFP+ Optical Interface Board(SG)
-- Here define submodule for routers
h3cevtSubModuleRouter       OBJECT IDENTIFIER ::= { h3cevtModule 5 }


-- Here define submodule for switches
h3cevtSubModuleSwitch       OBJECT IDENTIFIER ::= { h3cevtModule 6 }
-- Here define Compact Flash
h3cevtModuleCFCard          OBJECT IDENTIFIER ::= { h3cevtModule 7 }

-- Here define Secure Digital Memory Card
h3cevtModuleSDCard          OBJECT IDENTIFIER ::= { h3cevtModule 8 }

--
-- h3cevtPort section:
--
h3cevtPort          OBJECT IDENTIFIER ::= { h3cEntityVendortypeObjects 10 }

h3cevtPortUnknownPorts      OBJECT IDENTIFIER ::= { h3cevtPort 1 }
h3cevtPortCommonPorts       OBJECT IDENTIFIER ::= { h3cevtPort 2 }
h3cevtPortRouterType        OBJECT IDENTIFIER ::= { h3cevtPort 3 }
h3cevtPortSwitchType        OBJECT IDENTIFIER ::= { h3cevtPort 4 }


-- Below are ports used to router
h3cevtPortRt-Async          OBJECT IDENTIFIER ::= { h3cevtPortRouterType 1 }    -- Async interface
h3cevtPortRt-Analogmodem    OBJECT IDENTIFIER ::= { h3cevtPortRouterType 2 }    -- Analog modem interface
h3cevtPortRt-Atm            OBJECT IDENTIFIER ::= { h3cevtPortRouterType 3 }
h3cevtPortRt-AtmAdsl        OBJECT IDENTIFIER ::= { h3cevtPortRouterType 4 }
h3cevtPortRt-AtmShdsl       OBJECT IDENTIFIER ::= { h3cevtPortRouterType 5 }
h3cevtPortRt-AtmE1          OBJECT IDENTIFIER ::= { h3cevtPortRouterType 6 }
h3cevtPortRt-AtmT1          OBJECT IDENTIFIER ::= { h3cevtPortRouterType 7 }
h3cevtPortRt-AtmE3          OBJECT IDENTIFIER ::= { h3cevtPortRouterType 8 }
h3cevtPortRt-AtmT3          OBJECT IDENTIFIER ::= { h3cevtPortRouterType 9 }
h3cevtPortRt-Atm622M        OBJECT IDENTIFIER ::= { h3cevtPortRouterType 10 }
h3cevtPortRt-AtmImaE1       OBJECT IDENTIFIER ::= { h3cevtPortRouterType 11 }
h3cevtPortRt-AtmImaT1       OBJECT IDENTIFIER ::= { h3cevtPortRouterType 12 }
h3cevtPortRt-Atm25M         OBJECT IDENTIFIER ::= { h3cevtPortRouterType 13 }
h3cevtPortRt-Bri            OBJECT IDENTIFIER ::= { h3cevtPortRouterType 14 }
h3cevtPortRt-Console        OBJECT IDENTIFIER ::= { h3cevtPortRouterType 15 }
h3cevtPortRt-E1             OBJECT IDENTIFIER ::= { h3cevtPortRouterType 16 }
h3cevtPortRt-E3             OBJECT IDENTIFIER ::= { h3cevtPortRouterType 17 }
h3cevtPortRt-T1             OBJECT IDENTIFIER ::= { h3cevtPortRouterType 18 }
h3cevtPortRt-T3             OBJECT IDENTIFIER ::= { h3cevtPortRouterType 19 }
h3cevtPortRt-Cpos           OBJECT IDENTIFIER ::= { h3cevtPortRouterType 20 }
h3cevtPortRt-Ethernet       OBJECT IDENTIFIER ::= { h3cevtPortRouterType 21 }
h3cevtPortRt-Serial         OBJECT IDENTIFIER ::= { h3cevtPortRouterType 22 }
h3cevtPortRt-E1f            OBJECT IDENTIFIER ::= { h3cevtPortRouterType 23 }
h3cevtPortRt-T1f            OBJECT IDENTIFIER ::= { h3cevtPortRouterType 24 }
h3cevtPortRt-Pos            OBJECT IDENTIFIER ::= { h3cevtPortRouterType 25 }
h3cevtPortRt-Ge             OBJECT IDENTIFIER ::= { h3cevtPortRouterType 26 }
h3cevtPortRt-Aux            OBJECT IDENTIFIER ::= { h3cevtPortRouterType 27 }
-- h3cevtPortRt-Null         OBJECT IDENTIFIER ::= { h3cevtPortRouterType 28 }   reserved
-- h3cevtPortRt-Max          OBJECT IDENTIFIER ::= { h3cevtPortRouterType 29 }   reserved
h3cevtPortRt-VG-Fxs         OBJECT IDENTIFIER ::= { h3cevtPortRouterType 30 }
h3cevtPortRt-VG-Fxo         OBJECT IDENTIFIER ::= { h3cevtPortRouterType 31 }
h3cevtPortRt-VG-E1vi        OBJECT IDENTIFIER ::= { h3cevtPortRouterType 32 }
h3cevtPortRt-VG-T1vi        OBJECT IDENTIFIER ::= { h3cevtPortRouterType 33 }
h3cevtPortRt-Usb            OBJECT IDENTIFIER ::= { h3cevtPortRouterType 34 }
h3cevtPortRt-Ndec           OBJECT IDENTIFIER ::= { h3cevtPortRouterType 35 }   -- NDEC port, Encrypt card version 1.0
h3cevtPortRt-Cavium         OBJECT IDENTIFIER ::= { h3cevtPortRouterType 36 }   -- NDEC port, Encrypt card version 2.0
h3cevtPortRt-Fcm            OBJECT IDENTIFIER ::= { h3cevtPortRouterType 37 }   -- POS/Fast connect module port
h3cevtPortRt-E1vi           OBJECT IDENTIFIER ::= { h3cevtPortRouterType 38 }   -- E1VI port
h3cevtPortRt-T1vi           OBJECT IDENTIFIER ::= { h3cevtPortRouterType 39 }   -- T1VI port
h3cevtPortRt-Vi             OBJECT IDENTIFIER ::= { h3cevtPortRouterType 40 }   -- Voice port
h3cevtPortRt-Adls2Plus      OBJECT IDENTIFIER ::= { h3cevtPortRouterType 41 }   -- ADSL2Plus port
h3cevtPortRt-RADIO-AG       OBJECT IDENTIFIER ::= { h3cevtPortRouterType 42 }   -- 802.11ag Radio port
h3cevtPortRt-1exp           OBJECT IDENTIFIER ::= { h3cevtPortRouterType 43 }   -- 10GBASE-R/W Ethernet port
h3cevtPortRt-G-SHDSL-BIS    OBJECT IDENTIFIER ::= { h3cevtPortRouterType 44 }   -- 4 wire G.SHDSL.BIS interface
h3cevtPortRt-ONU-1000BASE-BX-SFF-SC    OBJECT IDENTIFIER ::= { h3cevtPortRouterType 45 }   -- 1000 BASE-BX SFF SC ONU Interface
h3cevtPortRt-CELLULAR       OBJECT IDENTIFIER ::= { h3cevtPortRouterType 46 }   -- 3G Wireless WAN Interface
h3cevtPortRt-CELLULAR-ETHERNET         OBJECT IDENTIFIER ::= { h3cevtPortRouterType 47 }   -- 3G Wireless WAN Interface for Ethernet mode
h3cevtPortRt-VGe            OBJECT IDENTIFIER ::= { h3cevtPortRouterType 48 } -- virtual Ge port
h3cevtPortRt-VXGe           OBJECT IDENTIFIER ::= { h3cevtPortRouterType 49 } -- virtual XGe port
h3cevtPortRt-Xpos           OBJECT IDENTIFIER ::= { h3cevtPortRouterType 50 } -- 10G POS port
h3cevtPortRt-Fge            OBJECT IDENTIFIER ::= { h3cevtPortRouterType 51 } -- 40G Ethernet port
h3cevtPortRt-XGe            OBJECT IDENTIFIER ::= { h3cevtPortRouterType 52 } -- 10G Ethernet port
h3cevtPortRt-HgeQsfp28Lc    OBJECT IDENTIFIER ::= { h3cevtPortRouterType 53 } -- 100G Ethernet Port with QSFP28 Form Factor and LC Connector
h3cevtPortRt-HgeCfp2Lc      OBJECT IDENTIFIER ::= { h3cevtPortRouterType 54 } -- 100G Ethernet Port with CFP2 Form Factor and LC Connector
h3cevtPortRt-HgeCfpLc       OBJECT IDENTIFIER ::= { h3cevtPortRouterType 55 } -- 100G Ethernet Port with CFP Form Factor and LC Connector
h3cevtPortRt-GeM12          OBJECT IDENTIFIER ::= { h3cevtPortRouterType 56 } -- Gigabit Ethernet Port with M12 Form Connector
h3cevtPortRt-VMEth          OBJECT IDENTIFIER ::= { h3cevtPortRouterType 57 } -- Virtual Machine Ethernet Port
h3cevtPortRt-FiberGe        OBJECT IDENTIFIER ::= { h3cevtPortRouterType 58 } -- 1G Fiber Ethernet port

-- Below are ports used to switches
--h3cevtPortSw-Unknown              OBJECT IDENTIFIER ::= { h3cevtPortSwitchType 0 }
h3cevtPortSw-10or100M               OBJECT IDENTIFIER ::= { h3cevtPortSwitchType 1 }
h3cevtPortSw-1000BaseLxSm           OBJECT IDENTIFIER ::= { h3cevtPortSwitchType 2 }
h3cevtPortSw-1000BaseSxMm           OBJECT IDENTIFIER ::= { h3cevtPortSwitchType 3 }
h3cevtPortSw-1000BaseTx             OBJECT IDENTIFIER ::= { h3cevtPortSwitchType 4 }
h3cevtPortSw-100MSinglemodeFx       OBJECT IDENTIFIER ::= { h3cevtPortSwitchType 5 }
h3cevtPortSw-100MMultimodeFx        OBJECT IDENTIFIER ::= { h3cevtPortSwitchType 6 }
h3cevtPortSw-100M100BaseTx          OBJECT IDENTIFIER ::= { h3cevtPortSwitchType 7 }
h3cevtPortSw-100MHub                OBJECT IDENTIFIER ::= { h3cevtPortSwitchType 8 }
h3cevtPortSw-Vdsl                   OBJECT IDENTIFIER ::= { h3cevtPortSwitchType 9 }
h3cevtPortSw-Stack                  OBJECT IDENTIFIER ::= { h3cevtPortSwitchType 10 }
h3cevtPortSw-1000BaseZenithFx       OBJECT IDENTIFIER ::= { h3cevtPortSwitchType 11 }
h3cevtPortSw-1000BaseLongFx         OBJECT IDENTIFIER ::= { h3cevtPortSwitchType 12 }
h3cevtPortSw-Adsl                   OBJECT IDENTIFIER ::= { h3cevtPortSwitchType 13 }
h3cevtPortSw-10or100MDb             OBJECT IDENTIFIER ::= { h3cevtPortSwitchType 14 }
h3cevtPortSw-10GBaseLrSm            OBJECT IDENTIFIER ::= { h3cevtPortSwitchType 15 }
h3cevtPortSw-10GBaseLx4Mm           OBJECT IDENTIFIER ::= { h3cevtPortSwitchType 16 }
h3cevtPortSw-10GBaseLx4Sm           OBJECT IDENTIFIER ::= { h3cevtPortSwitchType 17 }
h3cevtPortSw-100MLongFx             OBJECT IDENTIFIER ::= { h3cevtPortSwitchType 18 }
h3cevtPortSw-1000BaseCx             OBJECT IDENTIFIER ::= { h3cevtPortSwitchType 19 }
h3cevtPortSw-1000BaseZenithFxLc     OBJECT IDENTIFIER ::= { h3cevtPortSwitchType 20 }
h3cevtPortSw-1000BaseLongFxLc       OBJECT IDENTIFIER ::= { h3cevtPortSwitchType 21 }
h3cevtPortSw-100MSmFxSc             OBJECT IDENTIFIER ::= { h3cevtPortSwitchType 22 }
h3cevtPortSw-100MMmFxSc             OBJECT IDENTIFIER ::= { h3cevtPortSwitchType 23 }
h3cevtPortSw-100MSmFxLc             OBJECT IDENTIFIER ::= { h3cevtPortSwitchType 24 }
h3cevtPortSw-100MMmFxLc             OBJECT IDENTIFIER ::= { h3cevtPortSwitchType 25 }
h3cevtPortSw-GbicNoConnector        OBJECT IDENTIFIER ::= { h3cevtPortSwitchType 26 }
h3cevtPortSw-Gbic1000BaseT          OBJECT IDENTIFIER ::= { h3cevtPortSwitchType 27 }
h3cevtPortSw-Gbic1000BaseLx         OBJECT IDENTIFIER ::= { h3cevtPortSwitchType 28 }
h3cevtPortSw-Gbic1000BaseSx         OBJECT IDENTIFIER ::= { h3cevtPortSwitchType 29 }
h3cevtPortSw-Gbic1000BaseZx         OBJECT IDENTIFIER ::= { h3cevtPortSwitchType 30 }
h3cevtPortSw-ComboNoConnector       OBJECT IDENTIFIER ::= { h3cevtPortSwitchType 31 }
h3cevtPortSw-Combo1000BaseLx        OBJECT IDENTIFIER ::= { h3cevtPortSwitchType 32 }
h3cevtPortSw-Combo1000BaseLxFiber   OBJECT IDENTIFIER ::= { h3cevtPortSwitchType 33 }
h3cevtPortSw-Combo1000BaseLxCopper  OBJECT IDENTIFIER ::= { h3cevtPortSwitchType 34 }
h3cevtPortSw-Combo1000BaseSx        OBJECT IDENTIFIER ::= { h3cevtPortSwitchType 35 }
h3cevtPortSw-Combo1000BaseSxFiber   OBJECT IDENTIFIER ::= { h3cevtPortSwitchType 36 }
h3cevtPortSw-Combo1000BaseSxCopper  OBJECT IDENTIFIER ::= { h3cevtPortSwitchType 37 }
h3cevtPortSw-Combo1000BaseZx        OBJECT IDENTIFIER ::= { h3cevtPortSwitchType 38 }
h3cevtPortSw-Combo1000BaseZxFiber   OBJECT IDENTIFIER ::= { h3cevtPortSwitchType 39 }
h3cevtPortSw-Combo1000BaseZxCopper  OBJECT IDENTIFIER ::= { h3cevtPortSwitchType 40 }
h3cevtPortSw-155PosSxMmf            OBJECT IDENTIFIER ::= { h3cevtPortSwitchType 41 }
h3cevtPortSw-155PosLxSmf            OBJECT IDENTIFIER ::= { h3cevtPortSwitchType 42 }

-- added by Garibaldi
h3cevtPortSw-1000BASE-T             OBJECT IDENTIFIER ::= { h3cevtPortSwitchType 43 }  -- 1000 Base-T Port
h3cevtPortSw-1000BASE-SX-SFP        OBJECT IDENTIFIER ::= { h3cevtPortSwitchType 44 }  -- 1000 Base-SX SFP Port
h3cevtPortSw-1000BASE-LX-SFP        OBJECT IDENTIFIER ::= { h3cevtPortSwitchType 45 }  -- 1000 Base-LX SFP Port
h3cevtPortSw-1000BASE-T-AN-SFP      OBJECT IDENTIFIER ::= { h3cevtPortSwitchType 46 }  -- 1000 Base-T AN SFP Port
h3cevtPortSw-10GBASE-LX4-XENPAK     OBJECT IDENTIFIER ::= { h3cevtPortSwitchType 47 }  -- 10G Base-LX4 XENPAK Port
h3cevtPortSw-10GBASE-LR-XENPAK      OBJECT IDENTIFIER ::= { h3cevtPortSwitchType 48 }  -- 10G Base-LR XENPAK Port
h3cevtPortSw-10GBASE-CX4            OBJECT IDENTIFIER ::= { h3cevtPortSwitchType 49 }  -- 10G Base-CX4 Port
h3cevtPortSw-1000BASE-ZX-SFP        OBJECT IDENTIFIER ::= { h3cevtPortSwitchType 50 }  -- 1000 Base-ZX SFP Port
h3cevtPortSw-1000BASE-MM-SFP        OBJECT IDENTIFIER ::= { h3cevtPortSwitchType 51 }  -- 1000 Base-MM SFP Port
h3cevtPortSw-100BASE-SX-SFP         OBJECT IDENTIFIER ::= { h3cevtPortSwitchType 52 }  -- 100 Base-SX SFP Port
h3cevtPortSw-100BASE-LX-SFP         OBJECT IDENTIFIER ::= { h3cevtPortSwitchType 53 }  -- 100 Base-LX SFP Port
h3cevtPortSw-100BASE-T-AN-SFP       OBJECT IDENTIFIER ::= { h3cevtPortSwitchType 54 }  -- 100 Base-T SFP Port
h3cevtPortSw-100BASE-ZX-SFP         OBJECT IDENTIFIER ::= { h3cevtPortSwitchType 55 }  -- 100 Base-ZX SFP Port
h3cevtPortSw-100BASE-MM-SFP         OBJECT IDENTIFIER ::= { h3cevtPortSwitchType 56 }  -- 100 Base-MM SFP Port
h3cevtPortSw-SFP-NO-CONNECTOR       OBJECT IDENTIFIER ::= { h3cevtPortSwitchType 57 }  -- No Connector SFP Port
h3cevtPortSw-SFP-UNKNOWN-CONNECTOR  OBJECT IDENTIFIER ::= { h3cevtPortSwitchType 58 }  -- Unknown SFP Port
h3cevtPortSw-POS-NO-CONNECTOR       OBJECT IDENTIFIER ::= { h3cevtPortSwitchType 59 }  -- POS no connector
h3cevtPortSw-10G-BASE-SR            OBJECT IDENTIFIER ::= { h3cevtPortSwitchType 60 }  -- 10GBASE-SR Fiber Optic Transceivers with SC Connector
h3cevtPortSw-10G-BASE-ER            OBJECT IDENTIFIER ::= { h3cevtPortSwitchType 61 }  -- 10GBASE-ER Fiber Optic Transceivers with SC Connector
h3cevtPortSw-10G-BASE-LX4           OBJECT IDENTIFIER ::= { h3cevtPortSwitchType 62 }  -- 10GBASE-LX4 Fiber Optic Transceivers with SC Connector
h3cevtPortSw-10G-BASE-SW            OBJECT IDENTIFIER ::= { h3cevtPortSwitchType 63 }  -- 10GBASE-SW Fiber Optic Transceivers with SC Connector
h3cevtPortSw-10G-BASE-LW            OBJECT IDENTIFIER ::= { h3cevtPortSwitchType 64 }  -- 10GBASE-LW Fiber Optic Transceivers with SC Connector
h3cevtPortSw-10G-BASE-EW            OBJECT IDENTIFIER ::= { h3cevtPortSwitchType 65 }  -- 10GBASE-EW Fiber Optic Transceivers with SC Connector
h3cevtPortSw-10G-LR-SM-LC           OBJECT IDENTIFIER ::= { h3cevtPortSwitchType 66 }  -- 10GBASE-LR Single Mode Fiber Optic Transceivers with LC Connector
h3cevtPortSw-10G-SR-MM-LC           OBJECT IDENTIFIER ::= { h3cevtPortSwitchType 67 }  -- 10GBASE-SR Multi Mode Fiber Optic Transceivers with LC Connector
h3cevtPortSw-10G-ER-SM-LC           OBJECT IDENTIFIER ::= { h3cevtPortSwitchType 68 }  -- 10GBASE-ER Single Mode Fiber Optic Transceivers with LC Connector
h3cevtPortSw-10G-LW-SM-LC           OBJECT IDENTIFIER ::= { h3cevtPortSwitchType 69 }  -- 10GBASE-LW Single Mode Fiber Optic Transceivers with LC Connector
h3cevtPortSw-10G-SW-MM-LC           OBJECT IDENTIFIER ::= { h3cevtPortSwitchType 70 }  -- 10GBASE-SW Multi Mode Fiber Optic Transceivers with LC Connector
h3cevtPortSw-10G-EW-SM-LC           OBJECT IDENTIFIER ::= { h3cevtPortSwitchType 71 }  -- 10GBASE-EW Single Mode Fiber Optic Transceivers with LC Connector
h3cevtPortSw-100BASE-SM-MTRJ        OBJECT IDENTIFIER ::= { h3cevtPortSwitchType 72 }  -- 100 Base-SM MTRJ Port
h3cevtPortSw-100BASE-MM-MTRJ        OBJECT IDENTIFIER ::= { h3cevtPortSwitchType 73 }  -- 100 Base-MM MTRJ Port
h3cevtPortSw-XFP-NO-CONNECTOR       OBJECT IDENTIFIER ::= { h3cevtPortSwitchType 74 }  -- XFP without Transceiver
h3cevtPortSw-XFP-10GBASE-SR         OBJECT IDENTIFIER ::= { h3cevtPortSwitchType 75 }  -- 10GBASE-SR XFP Transceiver
h3cevtPortSw-XFP-10GBASE-LR         OBJECT IDENTIFIER ::= { h3cevtPortSwitchType 76 }  -- 10GBASE-LR XFP Transceiver
h3cevtPortSw-XFP-10GBASE-ER         OBJECT IDENTIFIER ::= { h3cevtPortSwitchType 77 }  -- 10GBASE-ER XFP Transceiver
h3cevtPortSw-XFP-10GBASE-SW         OBJECT IDENTIFIER ::= { h3cevtPortSwitchType 78 }  -- 10GBASE-SW XFP Transceiver
h3cevtPortSw-XFP-10GBASE-LW         OBJECT IDENTIFIER ::= { h3cevtPortSwitchType 79 }  -- 10GBASE-LW XFP Transceiver
h3cevtPortSw-XFP-10GBASE-EW         OBJECT IDENTIFIER ::= { h3cevtPortSwitchType 80 }  -- 10GBASE-EW XFP Transceiver
h3cevtPortSw-XFP-10GBASE-CX4        OBJECT IDENTIFIER ::= { h3cevtPortSwitchType 81 }  -- 10GBASE-CX4 XFP Transceiver
h3cevtPortSw-XFP-10GBASE-LX4        OBJECT IDENTIFIER ::= { h3cevtPortSwitchType 82 }  -- 10GBASE-LX4 XFP Transceiver
h3cevtPortSw-XFP-UNKNOWN            OBJECT IDENTIFIER ::= { h3cevtPortSwitchType 83 }  -- Unknown  XFP Transceiver
h3cevtPortSw-XPK-NOCONNECTOR        OBJECT IDENTIFIER ::= { h3cevtPortSwitchType 84 }  -- Xenpak without Transceiver
h3cevtPortSw-XPK-10GBASE-SR         OBJECT IDENTIFIER ::= { h3cevtPortSwitchType 85 }  -- 10GBASE-SR Xenpak Transceiver
h3cevtPortSw-XPK-10GBASE-LR         OBJECT IDENTIFIER ::= { h3cevtPortSwitchType 86 }  -- 10GBASE-LR Xenpak Transceiver
h3cevtPortSw-XPK-10GBASE-ER         OBJECT IDENTIFIER ::= { h3cevtPortSwitchType 87 }  -- 10GBASE-ER Xenpak Transceiver
h3cevtPortSw-XPK-10GBASE-SW         OBJECT IDENTIFIER ::= { h3cevtPortSwitchType 88 }  -- 10GBASE-SW Xenpak Transceiver
h3cevtPortSw-XPK-10GBASE-LW         OBJECT IDENTIFIER ::= { h3cevtPortSwitchType 89 }  -- 10GBASE-LW Xenpak Transceiver
h3cevtPortSw-XPK-10GBASE-EW         OBJECT IDENTIFIER ::= { h3cevtPortSwitchType 90 }  -- 10GBASE-EW Xenpak Transceiver
h3cevtPortSw-XPK-10GBASE-CX4        OBJECT IDENTIFIER ::= { h3cevtPortSwitchType 91 }  -- 10GBASE-CX4 Xenpak Transceiver
h3cevtPortSw-XPK-10GBASE-LX4        OBJECT IDENTIFIER ::= { h3cevtPortSwitchType 92 }  -- 10GBASE-LX4 Xenpak Transceiver
h3cevtPortSw-XPK-UNKNOWN            OBJECT IDENTIFIER ::= { h3cevtPortSwitchType 93 }  -- Unknown Xenpak Transceiver
h3cevtPortSw-POS-OC48-SR-SM-LC      OBJECT IDENTIFIER ::= { h3cevtPortSwitchType 94 }  -- OC48-SR Single Mode Fiber Optic Transceivers with LC Connector
h3cevtPortSw-POS-OC48-IR-SM-LC      OBJECT IDENTIFIER ::= { h3cevtPortSwitchType 95 }  -- OC48-IR Single Mode Fiber Optic Transceivers with LC Connector
h3cevtPortSw-POS-OC48-LR-SM-LC      OBJECT IDENTIFIER ::= { h3cevtPortSwitchType 96 }  -- OC48-LR Single Mode Fiber Optic Transceivers with LC Connector
h3cevtPortSw-10G-BASE-CX4           OBJECT IDENTIFIER ::= { h3cevtPortSwitchType 97 }  -- 10G BASE-CX4 Electrical Interface
h3cevtPortSw-OLT-1000BASE-BX-SFF-SC OBJECT IDENTIFIER ::= { h3cevtPortSwitchType 98 }  -- 1000 BASE-BX SFF SC OLT Interface
h3cevtPortSw-ONU-1000BASE-BX-SFF-SC OBJECT IDENTIFIER ::= { h3cevtPortSwitchType 99 }  -- 1000 BASE-BX SFF SC ONU Interface
h3cevtPortSw-24G-CASCADE            OBJECT IDENTIFIER ::= { h3cevtPortSwitchType 100 }  -- 24G Cascade port
h3cevtPortSw-POS-OC3-SR-MM          OBJECT IDENTIFIER ::= { h3cevtPortSwitchType 101 }  -- STM1/OC3 Short Reach Multi Mode Fiber Optic Transceivers with LC Connector
h3cevtPortSw-POS-OC3-IR-SM          OBJECT IDENTIFIER ::= { h3cevtPortSwitchType 102 }  -- STM1/OC3 Intermediate Reach Single Mode Fiber Optic Transceivers with LC Connector
h3cevtPortSw-POS-OC3-IR-1-SM        OBJECT IDENTIFIER ::= { h3cevtPortSwitchType 103 }  -- STM1/OC3 Intermediate Reach Single Mode Fiber Optic Transceivers with LC Connector(variation 1)
h3cevtPortSw-POS-OC3-IR-2-SM        OBJECT IDENTIFIER ::= { h3cevtPortSwitchType 104 }  -- STM1/OC3 Intermediate Reach Single Mode Fiber Optic Transceivers with LC Connector(variation 2)
h3cevtPortSw-POS-OC3-LR-SM          OBJECT IDENTIFIER ::= { h3cevtPortSwitchType 105 }  -- STM1/OC3 Long Reach Single Mode Fiber Optic Transceivers with LC Connector
h3cevtPortSw-POS-OC3-LR-1-SM        OBJECT IDENTIFIER ::= { h3cevtPortSwitchType 106 }  -- STM1/OC3 Long Reach Single Mode Fiber Optic Transceivers with LC Connector(variation 1)
h3cevtPortSw-POS-OC3-LR-2-SM        OBJECT IDENTIFIER ::= { h3cevtPortSwitchType 107 }  -- STM1/OC3 Long Reach Single Mode Fiber Optic Transceivers with LC Connector(variation 2)
h3cevtPortSw-POS-OC3-LR-3-SM        OBJECT IDENTIFIER ::= { h3cevtPortSwitchType 108 }  -- STM1/OC3 Long Reach Single Mode Fiber Optic Transceivers with LC Connector(variation 3)
h3cevtPortSw-POS-OC12-SR-MM         OBJECT IDENTIFIER ::= { h3cevtPortSwitchType 109 }  -- STM4/OC12 Short Reach Multi Mode Fiber Optic Transceivers with LC Connector
h3cevtPortSw-POS-OC12-IR-SM         OBJECT IDENTIFIER ::= { h3cevtPortSwitchType 110 }  -- STM4/OC12 Intermediate Reach Single Mode Fiber Optic Transceivers with LC Connector
h3cevtPortSw-POS-OC12-IR-1-SM       OBJECT IDENTIFIER ::= { h3cevtPortSwitchType 111 }  -- STM4/OC12 Intermediate Reach Single Mode Fiber Optic Transceivers with LC Connector(variation 1)
h3cevtPortSw-POS-OC12-IR-2-SM       OBJECT IDENTIFIER ::= { h3cevtPortSwitchType 112 }  -- STM4/OC12 Intermediate Reach Single Mode Fiber Optic Transceivers with LC Connector(variation 2)
h3cevtPortSw-POS-OC12-LR-SM         OBJECT IDENTIFIER ::= { h3cevtPortSwitchType 113 }  -- STM4/OC12 Long Reach Single Mode Fiber Optic Transceivers with LC Connector
h3cevtPortSw-POS-OC12-LR-1-SM       OBJECT IDENTIFIER ::= { h3cevtPortSwitchType 114 }  -- STM4/OC12 Long Reach Single Mode Fiber Optic Transceivers with LC Connector(variation 1)
h3cevtPortSw-POS-OC12-LR-2-SM       OBJECT IDENTIFIER ::= { h3cevtPortSwitchType 115 }  -- STM4/OC12 Long Reach Single Mode Fiber Optic Transceivers with LC Connector(variation 2)
h3cevtPortSw-POS-OC12-LR-3-SM       OBJECT IDENTIFIER ::= { h3cevtPortSwitchType 116 }  -- STM4/OC12 Long Reach Single Mode Fiber Optic Transceivers with LC Connector(variation 3)
h3cevtPortSw-POS-OC48-SR-SM         OBJECT IDENTIFIER ::= { h3cevtPortSwitchType 117 }  -- STM16/OC48 Short Reach Single Mode Fiber Optic Transceivers with LC Connector
h3cevtPortSw-POS-OC48-IR-SM         OBJECT IDENTIFIER ::= { h3cevtPortSwitchType 118 }  -- STM16/OC48 Intermediate Reach Single Mode Fiber Optic Transceivers with LC Connector
h3cevtPortSw-POS-OC48-IR-1-SM       OBJECT IDENTIFIER ::= { h3cevtPortSwitchType 119 }  -- STM16/OC48 Intermediate Reach Single Mode Fiber Optic Transceivers with LC Connector(variation 1)
h3cevtPortSw-POS-OC48-IR-2-SM       OBJECT IDENTIFIER ::= { h3cevtPortSwitchType 120 }  -- STM16/OC48 Intermediate Reach Single Mode Fiber Optic Transceivers with LC Connector(variation 2)
h3cevtPortSw-POS-OC48-LR-SM         OBJECT IDENTIFIER ::= { h3cevtPortSwitchType 121 }  -- STM16/OC48 Long Reach Single Mode Fiber Optic Transceivers with LC Connector
h3cevtPortSw-POS-OC48-LR-1-SM       OBJECT IDENTIFIER ::= { h3cevtPortSwitchType 122 }  -- STM16/OC48 Long Reach Single Mode Fiber Optic Transceivers with LC Connector(variation 1)
h3cevtPortSw-POS-OC48-LR-2-SM       OBJECT IDENTIFIER ::= { h3cevtPortSwitchType 123 }  -- STM16/OC48 Long Reach Single Mode Fiber Optic Transceivers with LC Connector(variation 2)
h3cevtPortSw-POS-OC48-LR-3-SM       OBJECT IDENTIFIER ::= { h3cevtPortSwitchType 124 }  -- STM16/OC48 Long Reach Single Mode Fiber Optic Transceivers with LC Connector(variation 3)
h3cevtPortSw-POS-I-64-1             OBJECT IDENTIFIER ::= { h3cevtPortSwitchType 125 }  -- STM64/OC192 Interconnect Fiber Optic Transceivers with LC Connector(wavelength 1310nm G.652 fiber)
h3cevtPortSw-POS-I-64-2             OBJECT IDENTIFIER ::= { h3cevtPortSwitchType 126 }  -- STM64/OC192 Interconnect Fiber Optic Transceivers with LC Connector(wavelength 1550nm G.652 fiber)
h3cevtPortSw-POS-I-64-3             OBJECT IDENTIFIER ::= { h3cevtPortSwitchType 127 }  -- STM64/OC192 Interconnect Fiber Optic Transceivers with LC Connector(wavelength 1550nm G.653 fiber)
h3cevtPortSw-POS-I-64-5             OBJECT IDENTIFIER ::= { h3cevtPortSwitchType 128 }  -- STM64/OC192 Interconnect Fiber Optic Transceivers with LC Connector(wavelength 1550nm G.655 fiber)
h3cevtPortSw-POS-S-64-1             OBJECT IDENTIFIER ::= { h3cevtPortSwitchType 129 }  -- STM64/OC192 Short Haul Fiber Optic Transceivers with LC Connector(wavelength 1310nm G.652 fiber)
h3cevtPortSw-POS-S-64-2             OBJECT IDENTIFIER ::= { h3cevtPortSwitchType 130 }  -- STM64/OC192 Short Haul Fiber Optic Transceivers with LC Connector(wavelength 1550nm G.652 fiber)
h3cevtPortSw-POS-S-64-3             OBJECT IDENTIFIER ::= { h3cevtPortSwitchType 131 }  -- STM64/OC192 Short Haul Fiber Optic Transceivers with LC Connector(wavelength 1550nm G.653 fiber)
h3cevtPortSw-POS-S-64-5             OBJECT IDENTIFIER ::= { h3cevtPortSwitchType 132 }  -- STM64/OC192 Short Haul Fiber Optic Transceivers with LC Connector(wavelength 1550nm G.655 fiber)
h3cevtPortSw-POS-L-64-1             OBJECT IDENTIFIER ::= { h3cevtPortSwitchType 133 }  -- STM64/OC192 Long Haul Fiber Optic Transceivers with LC Connector(wavelength 1310nm G.652 fiber)
h3cevtPortSw-POS-L-64-2             OBJECT IDENTIFIER ::= { h3cevtPortSwitchType 134 }  -- STM64/OC192 Long Haul Fiber Optic Transceivers with LC Connector(wavelength 1550nm G.652 fiber)
h3cevtPortSw-POS-L-64-3             OBJECT IDENTIFIER ::= { h3cevtPortSwitchType 135 }  -- STM64/OC192 Long Haul Fiber Optic Transceivers with LC Connector(wavelength 1550nm G.653 fiber)
h3cevtPortSw-POS-V-64-2             OBJECT IDENTIFIER ::= { h3cevtPortSwitchType 136 }  -- STM64/OC192 Very Long Haul Fiber Optic Transceivers with LC Connector(wavelength 1550nm G.652 fiber)
h3cevtPortSw-POS-V-64-3             OBJECT IDENTIFIER ::= { h3cevtPortSwitchType 137 }  -- STM64/OC192 Very Long Haul Fiber Optic Transceivers with LC Connector(wavelength 1550nm G.653 fiber)
h3cevtPortSw-100BASE-FX-BIDI        OBJECT IDENTIFIER ::= { h3cevtPortSwitchType 138 }  -- 100 BASE-FX BIDI Port
h3cevtPortSw-100BASE-BX10-U-SFP     OBJECT IDENTIFIER ::= { h3cevtPortSwitchType 139 }  -- 100 BASE-BX10-U-SFP Port
h3cevtPortSw-100BASE-BX10-D-SFP     OBJECT IDENTIFIER ::= { h3cevtPortSwitchType 140 }  -- 100 BASE-BX10-D-SFP Port
h3cevtPortSw-1000BASE-BX10-U-SFP    OBJECT IDENTIFIER ::= { h3cevtPortSwitchType 141 }  -- 1000 BASE-BX10-U-SFP Port
h3cevtPortSw-1000BASE-BX10-D-SFP    OBJECT IDENTIFIER ::= { h3cevtPortSwitchType 142 }  -- 1000 BASE-BX10-D-SFP Port
h3cevtPortSw-STK-1000BASE-T         OBJECT IDENTIFIER ::= { h3cevtPortSwitchType 143 }  -- 1000 BASE-T Stack Port
h3cevtPortSw-RPR-PHYPOS-CONNECTOR     OBJECT IDENTIFIER ::= { h3cevtPortSwitchType 144 }  -- Resilient Packet Ring POS physical port
h3cevtPortSw-RPR-PHY10GE-CONNECTOR    OBJECT IDENTIFIER ::= { h3cevtPortSwitchType 145 }  -- 10G Resilient Packet Ring physical port
h3cevtPortSw-RPR-LOGICPOS-CONNECTOR   OBJECT IDENTIFIER ::= { h3cevtPortSwitchType 146 }  -- Resilient Packet Ring POS logical port
h3cevtPortSw-RPR-LOGIC10GE-CONNECTOR  OBJECT IDENTIFIER ::= { h3cevtPortSwitchType 147 }  -- 10G Resilient Packet Ring logical port
h3cevtPortSw-10GBASE-ZR               OBJECT IDENTIFIER ::= { h3cevtPortSwitchType 148 }  -- Fiber Optic Transceivers with SC Connector, XENPAK
h3cevtPortSw-TYPE-ERROR-CONNECTOR     OBJECT IDENTIFIER ::= { h3cevtPortSwitchType 149 }  -- Error Optic Transceivers type
h3cevtPortSw-10G-STACK                OBJECT IDENTIFIER ::= { h3cevtPortSwitchType 150 }  -- 10G Stack Port
h3cevtPortSw-155-ATM-SX-MMF             OBJECT IDENTIFIER ::= { h3cevtPortSwitchType 151 }  -- ATM OC-3 Multi-mode Short Reach Optical Transceiver
h3cevtPortSw-155-ATM-LX-SMF             OBJECT IDENTIFIER ::= { h3cevtPortSwitchType 152 }  -- ATM OC-3 Single Mode Long Reach Optical Transceiver
h3cevtPortSw-622-ATM-SX-MMF             OBJECT IDENTIFIER ::= { h3cevtPortSwitchType 153 }  -- ATM OC-12 Multi-mode Short Reach Optical Transceiver
h3cevtPortSw-622-ATM-LX-SMF             OBJECT IDENTIFIER ::= { h3cevtPortSwitchType 154 }  -- ATM OC-12 Single Mode Long Reach Optical Transceiver
h3cevtPortSw-155-ATM-NO-CONNECTOR       OBJECT IDENTIFIER ::= { h3cevtPortSwitchType 155 }  -- ATM OC-3 No Connector
h3cevtPortSw-622-ATM-NO-CONNECTOR       OBJECT IDENTIFIER ::= { h3cevtPortSwitchType 156 }  -- ATM OC-12 No Connector
h3cevtPortSw-155-CPOS-E1-NO-CONNECTOR   OBJECT IDENTIFIER ::= { h3cevtPortSwitchType 157 }  -- CPOS(E1) OC-3 No Connector
h3cevtPortSw-155-CPOS-T1-NO-CONNECTOR   OBJECT IDENTIFIER ::= { h3cevtPortSwitchType 158 }  -- CPOS(T1) OC-3 No Connector
h3cevtPortSw-622-CPOS-E1-NO-CONNECTOR   OBJECT IDENTIFIER ::= { h3cevtPortSwitchType 159 }  -- CPOS(E1) OC-12 No Connector
h3cevtPortSw-622-CPOS-T1-NO-CONNECTOR   OBJECT IDENTIFIER ::= { h3cevtPortSwitchType 160 }  -- CPOS(T1) OC-12 No Connector
h3cevtPortSw-155-CPOS-E1-SX-MMF         OBJECT IDENTIFIER ::= { h3cevtPortSwitchType 161 }  -- CPOS(E1) OC-3 Multi-mode Short Reach Optical Transceiver
h3cevtPortSw-155-CPOS-T1-SX-MMF         OBJECT IDENTIFIER ::= { h3cevtPortSwitchType 162 }  -- CPOS(T1) OC-3 Multi-mode Short Reach Optical Transceiver
h3cevtPortSw-155-CPOS-E1-LX-SMF         OBJECT IDENTIFIER ::= { h3cevtPortSwitchType 163 }  -- CPOS(E1) OC-3 Single Mode Long Reach Optical Transceiver
h3cevtPortSw-155-CPOS-T1-LX-SMF         OBJECT IDENTIFIER ::= { h3cevtPortSwitchType 164 }  -- CPOS(T1) OC-3 Single Mode Long Reach Optical Transceiver
h3cevtPortSw-622-CPOS-E1-SX-MMF         OBJECT IDENTIFIER ::= { h3cevtPortSwitchType 165 }  -- CPOS(E1) OC-12 Multi-mode Short Reach Optical Transceiver
h3cevtPortSw-622-CPOS-T1-SX-MMF         OBJECT IDENTIFIER ::= { h3cevtPortSwitchType 166 }  -- CPOS(T1) OC-12 Multi-mode Short Reach Optical Transceiver
h3cevtPortSw-622-CPOS-E1-LX-SMF         OBJECT IDENTIFIER ::= { h3cevtPortSwitchType 167 }  -- CPOS(E1) OC-12 Multi-mode Short Reach Optical Transceiver
h3cevtPortSw-622-CPOS-T1-LX-SMF         OBJECT IDENTIFIER ::= { h3cevtPortSwitchType 168 }  -- CPOS(T1) OC-12 Single Mode Long Reach Optical Transceiver
h3cevtPortSw-E1-CONNECTOR               OBJECT IDENTIFIER ::= { h3cevtPortSwitchType 169 }  -- E1 RJ45 Transceiver
h3cevtPortSw-T1-CONNECTOR               OBJECT IDENTIFIER ::= { h3cevtPortSwitchType 170 }  -- T1 RJ45 Transceiver
h3cevtPortSw-1000BASE-STK-SFP           OBJECT IDENTIFIER ::= { h3cevtPortSwitchType 171 }  -- 1-port 1000 Base-STK SFP Module
h3cevtPortSw-1000BASE-BIDI-SFP          OBJECT IDENTIFIER ::= { h3cevtPortSwitchType 172 }  -- 1-port 1000 Base-BIDI SFP Module
h3cevtPortSw-1000BASE-CWDM-SFP          OBJECT IDENTIFIER ::= { h3cevtPortSwitchType 173 }  -- 1-port 1000 Base-CWDM SFP Module
h3cevtPortSw-100BASE-BIDI-SFP           OBJECT IDENTIFIER ::= { h3cevtPortSwitchType 174 }  -- 1-port 100 Base-BIDI SFP Module
h3cevtPortSw-OLT-1000BASE-PX-SFP        OBJECT IDENTIFIER ::= { h3cevtPortSwitchType 175 }  -- 1000BASE-PX SFP OLT Interface
h3cevtPortSw-OLT-1000BASE-NO-CONNECTOR  OBJECT IDENTIFIER ::= { h3cevtPortSwitchType 176 }  -- 1000BASE OLT No Connector
h3cevtPortSw-RPR-PHYGE-CONNECTOR        OBJECT IDENTIFIER ::= { h3cevtPortSwitchType 177 }  -- Resilient Packet Ring GE physical port
h3cevtPortSw-RPR-LOGICGE-CONNECTOR      OBJECT IDENTIFIER ::= { h3cevtPortSwitchType 178 }  -- Resilient Packet Ring GE logical port
h3cevtPortSw-100M-1550-BIDI             OBJECT IDENTIFIER ::= { h3cevtPortSwitchType 179 }  -- Single Port 100M Ethernet Bi-direction Optical Interface Module(TX1550nm, RX1310nm, 15km, SC)
h3cevtPortSw-100M-1310-BIDI             OBJECT IDENTIFIER ::= { h3cevtPortSwitchType 180 }  -- Single Port 100M Ethernet Bi-direction Optical reverse Interface Module(TX1310nm, RX1550nm, 15km, SC)
h3cevtPortSw-RPR-PHYOC48-CONNECTOR      OBJECT IDENTIFIER ::= { h3cevtPortSwitchType 181 }  -- Resilient Packet Ring OC48 physical port
h3cevtPortSw-RPR-LOGICOC48-CONNECTOR    OBJECT IDENTIFIER ::= { h3cevtPortSwitchType 182 }  -- Resilient Packet Ring OC48 logical port
h3cevtPortSw-100-1000-BASE-LX-SMF       OBJECT IDENTIFIER ::= { h3cevtPortSwitchType 183 }  -- 100BASE-LX/1000BASE-LX Single Mode Fiber Optic Transceivers
h3cevtPortSw-10G-ZW-SM-LC               OBJECT IDENTIFIER ::= { h3cevtPortSwitchType 184 }  -- 10GBASE-ZW Single Mode Fiber Optic Transceivers with LC Connector
h3cevtPortSw-10G-ZR-SM-LC               OBJECT IDENTIFIER ::= { h3cevtPortSwitchType 185 }  -- 10GBASE-ZR Single Mode Fiber Optic Transceivers with LC Connector
h3cevtPortSw-XPK-10GBASE-ZR             OBJECT IDENTIFIER ::= { h3cevtPortSwitchType 186 }  -- 10GBASE-ZR Xenpak Transceiver:LH80,SM1550
h3cevtPortSw-SGMII-100-BASE-LX-SFP      OBJECT IDENTIFIER ::= { h3cevtPortSwitchType 187 }  -- SGMII-100-BASE-LX-SFP Transceiver
h3cevtPortSw-SGMII-100-BASE-FX-SFP      OBJECT IDENTIFIER ::= { h3cevtPortSwitchType 188 }  -- SGMII-100-BASE-FX-SFP Transceiver
h3cevtPortSw-WLAN-RADIO                 OBJECT IDENTIFIER ::= { h3cevtPortSwitchType 189 }  -- WLAN-RADIO Transceiver
h3cevtPortSw-CABLE                      OBJECT IDENTIFIER ::= { h3cevtPortSwitchType 190 }  -- Cable Port
h3cevtPortSw-SFP-PLUS-NO-CONNECTOR      OBJECT IDENTIFIER ::= { h3cevtPortSwitchType 191 }  -- SFP+ without Transceiver
h3cevtPortSw-SFP-PLUS-10GBASE-SR        OBJECT IDENTIFIER ::= { h3cevtPortSwitchType 192 }  -- 10GBASE-SR SFP+ Transceiver
h3cevtPortSw-SFP-PLUS-10GBASE-LR        OBJECT IDENTIFIER ::= { h3cevtPortSwitchType 193 }  -- 10GBASE-LR SFP+ Transceiver
h3cevtPortSw-SFP-PLUS-10GBASE-LRM       OBJECT IDENTIFIER ::= { h3cevtPortSwitchType 194 }  -- 10GBASE-LRM SFP+ Transceiver
h3cevtPortSw-SFP-PLUS-10GBASE-Cu        OBJECT IDENTIFIER ::= { h3cevtPortSwitchType 195 }  -- 10GBASE-Cu SFP+ Transceiver
h3cevtPortSw-SFP-PLUS-UNKNOWN           OBJECT IDENTIFIER ::= { h3cevtPortSwitchType 196 }  -- Unknown SFP+ Transceiver
h3cevtPortSw-SFP-PLUS-STACK-CONNECTOR   OBJECT IDENTIFIER ::= { h3cevtPortSwitchType 197 }  -- SFP+ STACK Transceiver
h3cevtPortSw-POS-L-64-4                 OBJECT IDENTIFIER ::= { h3cevtPortSwitchType 198 }  -- STM64/OC192 Long Haul Fiber Optic Transceivers with LC Connector(wavelength 1550nm G.653 fiber)
h3cevtPortSw-MINISAS-HD-STACK-CONNECTOR OBJECT IDENTIFIER ::= { h3cevtPortSwitchType 199 }  -- MiniSAS HD STACK Transceiver
h3cevtPortSw-ONU-1000BASE-PX-SFF        OBJECT IDENTIFIER ::= { h3cevtPortSwitchType 200 }  -- 1000BASE-PX SFF ONU Interface
h3cevtPortSw-RS485                      OBJECT IDENTIFIER ::= { h3cevtPortSwitchType 201 }  -- RS-485 Interface
h3cevtPortSw-SFP-PLUS-10GBASE-ER        OBJECT IDENTIFIER ::= { h3cevtPortSwitchType 202 }  -- 10GBASE-ER SFP+ Transceiver
h3cevtPortSw-SFP-PLUS-10GBASE-ZR        OBJECT IDENTIFIER ::= { h3cevtPortSwitchType 203 }  -- 10GBASE-ZR SFP+ Transceiver
h3cevtPortSw-XFP-10GBASE-ZR             OBJECT IDENTIFIER ::= { h3cevtPortSwitchType 204 }  -- 10GBASE-ZR XFP Transceiver
h3cevtPortSw-QSFP-PLUS-40GBASE-SR4      OBJECT IDENTIFIER ::= { h3cevtPortSwitchType 205 }  -- 40BASE-SR4 QSFP+ Optical Transceiver
h3cevtPortSw-QSFP-PLUS-STACK-CONNECTOR  OBJECT IDENTIFIER ::= { h3cevtPortSwitchType 206 }  -- QSFP+ STACK Transceiver
h3cevtPortSw-QSFP-PLUS-TO-4SFP-PLUS-STACK-CONNECTOR OBJECT IDENTIFIER ::= { h3cevtPortSwitchType 207 }  -- QSFP+ to 4 SFP+ STACK Transceiver
h3cevtPortSw-SFP-STACK-CONNECTOR        OBJECT IDENTIFIER ::= { h3cevtPortSwitchType 208 }  -- SFP STACK Transceiver
h3cevtPortSw-QSFP-NO-CONNECTOR          OBJECT IDENTIFIER ::= { h3cevtPortSwitchType 209 }  -- QSFP No Connector
h3cevtPortSw-10GBase-T                  OBJECT IDENTIFIER ::= { h3cevtPortSwitchType 210 }  -- 10G Base-T Port
h3cevtPortSw-CFP-NO-CONNECTOR           OBJECT IDENTIFIER ::= { h3cevtPortSwitchType 211 }  -- CFP No Connector
h3cevtPortSw-CFP-40GBASE-LR4            OBJECT IDENTIFIER ::= { h3cevtPortSwitchType 212 }  -- 40GBASE-LR4 CFP Transceiver
h3cevtPortSw-QSFP-PLUS-NO-CONNECTOR     OBJECT IDENTIFIER ::= { h3cevtPortSwitchType 213 }  -- QSFP+ No Connector
h3cevtPortSw-QSFP-PLUS-40GBASE-LR4      OBJECT IDENTIFIER ::= { h3cevtPortSwitchType 214 }  -- 40GBASE-LR4 QSFP+ Optical Transceiver
h3cevtPortSw-CFP-40GBASE-SR4            OBJECT IDENTIFIER ::= { h3cevtPortSwitchType 215 }  -- 40GBASE-SR4 CFP Optical Transceiver
h3cevtPortSw-CFP-100GBASE-LR4           OBJECT IDENTIFIER ::= { h3cevtPortSwitchType 216 }  -- 100GBASE-LR4 CFP Optical Transceiver
h3cevtPortSw-CFP-100GBASE-SR10          OBJECT IDENTIFIER ::= { h3cevtPortSwitchType 217 }  -- 100GBASE-SR10 CFP Optical Transceiver
h3cevtPortSw-CXP-100GBASE-SR10          OBJECT IDENTIFIER ::= { h3cevtPortSwitchType 218 }  -- 100GBASE-SR10 CXP Optical Transceiver
h3cevtPortSw-CXP-NO-CONNECTOR           OBJECT IDENTIFIER ::= { h3cevtPortSwitchType 219 }  -- CXP No Connector
h3cevtPortSw-TRANSCEIVER-UNKNOWN        OBJECT IDENTIFIER ::= { h3cevtPortSwitchType 220 }  -- Unknown Transceiver
h3cevtPortSw-QSFP-PLUS-UNKNOWN          OBJECT IDENTIFIER ::= { h3cevtPortSwitchType 221 }  -- Unknown QSFP+ Transceiver
h3cevtPortSw-CFP-UNKNOWN                OBJECT IDENTIFIER ::= { h3cevtPortSwitchType 222 }  -- Unknown CFP Transceiver
h3cevtPortSw-QSFP-PLUS-40GBASE-CSR4     OBJECT IDENTIFIER ::= { h3cevtPortSwitchType 223 }  -- 40GBASE-CSR4 QSFP+ Optical Transceiver
h3cevtPortSw-CFP-40GBASE-ER4            OBJECT IDENTIFIER ::= { h3cevtPortSwitchType 224 }  -- 40GBASE-ER4 CFP Optical Transceiver
h3cevtPortSw-SFP-1000BASE-BIDI          OBJECT IDENTIFIER ::= { h3cevtPortSwitchType 225 }  -- 1000BASE SFP Bi-direction Optical Transceiver
h3cevtPortSw-SFP-PLUS-10GBASE-ZR-DWDM   OBJECT IDENTIFIER ::= { h3cevtPortSwitchType 226 }  -- 10GBase-ZR SFP+ DWDM Optical Transceiver
h3cevtPortSw-QSFP-PLUS-40GBASE-PSM      OBJECT IDENTIFIER ::= { h3cevtPortSwitchType 227 }  -- 40GBASE QSFP+ Parallel SingleMode Optical Transceiver
h3cevtPortSw-SFP-8GFC-SW                OBJECT IDENTIFIER ::= { h3cevtPortSwitchType 228 }  -- SFP 8G FC Optical Transceiver short wave
h3cevtPortSw-SFP-8GFC-LW                OBJECT IDENTIFIER ::= { h3cevtPortSwitchType 229 }  -- SFP 8G FC Optical Transceiver long wave
h3cevtPortSw-CXP-100GBASE-AOC           OBJECT IDENTIFIER ::= { h3cevtPortSwitchType 230 }  -- 100GBASE CXP Active Optical Cable
h3cevtPortSw-QSFP-PLUS-ACTIVE-STACK-CONNECTOR  OBJECT IDENTIFIER ::= { h3cevtPortSwitchType 231 }  -- QSFP+ Active STACK Transceiver
h3cevtPortSw-QSFP-PLUS-TO-4SFP-PLUS-ACTIVE-STACK-CONNECTOR  OBJECT IDENTIFIER ::= { h3cevtPortSwitchType 232 }  -- QSFP+ to 4 SFP+ Active STACK Transceiver
h3cevtPortSw-CFP2-100GBASE-LR4          OBJECT IDENTIFIER ::= { h3cevtPortSwitchType 233 }  -- 100GBASE-LR4 CFP2 Optical Transceiver
h3cevtPortSw-CFP2-100GBASE-SR10         OBJECT IDENTIFIER ::= { h3cevtPortSwitchType 234 }  -- 100GBASE-SR10 CFP2 Optical Transceiver
h3cevtPortSw-QSFP-PLUS-ACTIVE-OPTICAL-CABLE  OBJECT IDENTIFIER ::= { h3cevtPortSwitchType 235 }  -- QSFP+ AOC
h3cevtPortSw-QSFP-PLUS-TO-4SFP-PLUS-ACTIVE-OPTICAL-CABLE OBJECT IDENTIFIER ::= { h3cevtPortSwitchType 236 }  -- QSFP+ to 4 SFP+ AOC
h3cevtPortSw-SFP-PLUS-ACTIVE-OPTICAL-CABLE   OBJECT IDENTIFIER ::= { h3cevtPortSwitchType 237 }  -- SFP+ AOC
h3cevtPortSw-CFP2-NO-CONNECTOR         OBJECT IDENTIFIER ::= { h3cevtPortSwitchType 238 }  -- CFP2 No Connector
h3cevtPortSw-QSFP28-NO-CONNECTOR       OBJECT IDENTIFIER ::= { h3cevtPortSwitchType 239 }  -- QSFP28 No Connector
h3cevtPortSw-QSFP28-100GBASE-SR4       OBJECT IDENTIFIER ::= { h3cevtPortSwitchType 240 }  -- 100BASE-SR4 QSFP28 Optical Transceiver
h3cevtPortSw-QSFP28-100GBASE-LR4       OBJECT IDENTIFIER ::= { h3cevtPortSwitchType 241 }  -- 100GBASE-LR4 QSFP28 Optical Transceiver
h3cevtPortSw-QSFP28-100GBASE-ER4       OBJECT IDENTIFIER ::= { h3cevtPortSwitchType 242 }  -- 100GBASE-ER4 QSFP28 Optical Transceiver
h3cevtPortSw-QSFP28-100GBASE-PSM4      OBJECT IDENTIFIER ::= { h3cevtPortSwitchType 243 }  -- 100GBASE-PSM4 QSFP28 Optical Transceiver
h3cevtPortSw-QSFP28-100GBASE-CWDM4     OBJECT IDENTIFIER ::= { h3cevtPortSwitchType 244 }  -- 100GBASE-CWDM4 QSFP28 Optical Transceiver
h3cevtPortSw-QSFP28-STACK-CONNECTOR    OBJECT IDENTIFIER ::= { h3cevtPortSwitchType 245 }  -- QSFP28 STACK Transceiver
h3cevtPortSw-QSFP28-TO-4SFP28-STACK-CONNECTOR  OBJECT IDENTIFIER ::= { h3cevtPortSwitchType 246 }  -- QSFP28 to 4 SFP28 STACK Transceiver
h3cevtPortSw-QSFP28-ACTIVE-STACK-CONNECTOR     OBJECT IDENTIFIER ::= { h3cevtPortSwitchType 247 }  -- QSFP28 Active STACK Transceiver
h3cevtPortSw-QSFP28-TO-4SFP28-ACTIVE-STACK-CONNECTOR   OBJECT IDENTIFIER ::= { h3cevtPortSwitchType 248 }  -- QSFP28 to 4 SFP28 Active STACK Transceiver
h3cevtPortSw-QSFP28-ACTIVE-OPTICAL-CABLE       OBJECT IDENTIFIER ::= { h3cevtPortSwitchType 249 }  -- QSFP28 AOC
h3cevtPortSw-QSFP28-TO-4SFP28-ACTIVE-OPTICAL-CABLE OBJECT IDENTIFIER ::= { h3cevtPortSwitchType 250 }  -- QSFP28 to 4 SFP28 AOC
h3cevtPortSw-QSFP-PLUS-40GBASE-LM4     OBJECT IDENTIFIER ::= { h3cevtPortSwitchType 251 }  -- 40BASE-LM4 QSFP+ Optical Transceiver
h3cevtPortSw-QSFP-PLUS-40GBASE-SWDM4   OBJECT IDENTIFIER ::= { h3cevtPortSwitchType 252 }  -- 40BASE-SWDM4 QSFP+ Optical Transceiver
h3cevtPortSw-CFP-100GBASE-ER4          OBJECT IDENTIFIER ::= { h3cevtPortSwitchType 253 }  -- 100GBASE-ER4 CFP Transceiver
h3cevtPortSw-QSFP-PLUS-40GBASE-ER4     OBJECT IDENTIFIER ::= { h3cevtPortSwitchType 254 }  -- 40BASE-ER4 QSFP+ Optical Transceiver
h3cevtPortSw-QSFP-PLUS-40GBASE-ER4L    OBJECT IDENTIFIER ::= { h3cevtPortSwitchType 255 }  -- 40BASE-ER4L QSFP+ Optical Transceiver
h3cevtPortSw-QSFP-PLUS-40GBASE-BIDI    OBJECT IDENTIFIER ::= { h3cevtPortSwitchType 256 }  -- 40BASE-BIDI QSFP+ Optical Transceiver
h3cevtPortSw-QSFP-PLUS-40GBASE-LR4L    OBJECT IDENTIFIER ::= { h3cevtPortSwitchType 257 }  -- 40BASE-LR4L QSFP+ Optical Transceiver
h3cevtPortSw-CFP2-100GBASE-eSR10       OBJECT IDENTIFIER ::= { h3cevtPortSwitchType 258 }  -- 100GBASE-eSR10 CFP2 Optical Transceiver
h3cevtPortSw-TUNABLE-SFP-PLUS-10GBASE-ZR-DWDM  OBJECT IDENTIFIER ::= { h3cevtPortSwitchType 259 }  -- 10GBase-ZR Tunable SFP+ DWDM Optical Transceiver
h3cevtPortSw-SFP28-25GBASE-SR          OBJECT IDENTIFIER ::= { h3cevtPortSwitchType 260 }  -- 25GBASE-SR SFP28 Optical Transceiver
h3cevtPortSw-SFP28-ACTIVE-OPTICAL-CABLE    OBJECT IDENTIFIER ::= { h3cevtPortSwitchType 261 }  -- SFP28 AOC
h3cevtPortSw-SFP28-STACK-CONNECTOR     OBJECT IDENTIFIER ::= { h3cevtPortSwitchType 262 }  -- SFP28 STACK Transceiver
h3cevtPortSw-2DOT5GBASE-T              OBJECT IDENTIFIER ::= { h3cevtPortSwitchType 263 }  -- 2dot5G Base-T Port
h3cevtPortSw-QSFP28-100GBASE-SWDM4     OBJECT IDENTIFIER ::= { h3cevtPortSwitchType 264 }  -- 100GBASE-SWDM4 QSFP28 Optical Transceiver
h3cevtPortSw-QSFP28-100GBASE-eSWDM4    OBJECT IDENTIFIER ::= { h3cevtPortSwitchType 265 }  -- 100GBASE-eSWDM4 QSFP28 Optical Transceiver
h3cevtPortSw-SFP-PLUS-10GBASE-T        OBJECT IDENTIFIER ::= { h3cevtPortSwitchType 266 }  -- 10GBase-T SFP+ Transceiver
h3cevtPortSw-QSFP28-100GBASE-eSR4       OBJECT IDENTIFIER ::= { h3cevtPortSwitchType 267 }  -- 100BASE-eSR4 QSFP28 Optical Transceiver
h3cevtPortSw-QSFP28-100GBASE-BIDI       OBJECT IDENTIFIER ::= { h3cevtPortSwitchType 268 }  -- 100GBASE-BIDI QSFP28 Optical Transceiver
h3cevtPortSw-QSFP28-100GBASE-WDM2       OBJECT IDENTIFIER ::= { h3cevtPortSwitchType 269 }  -- 100GBASE-WDM2 QSFP28 Optical Transceiver
h3cevtPortSw-SFP28-25GBASE-LR           OBJECT IDENTIFIER ::= { h3cevtPortSwitchType 270 }  -- 25GBASE-LR SFP28 Optical Transceiver
h3cevtPortSw-CFP2-100GBASE-ER4          OBJECT IDENTIFIER ::= { h3cevtPortSwitchType 271 }  -- 100GBASE-ER4 CFP2 Optical Transceiver
h3cevtPortSw-CFP2-DCO-200GBASE-ZR          OBJECT IDENTIFIER ::= { h3cevtPortSwitchType 272 }  -- 200GBASE-ZR CFP2-DCO Optical Transceiver
h3cevtPortSw-CFP2-100GBASE-ER4L          OBJECT IDENTIFIER ::= { h3cevtPortSwitchType 273 }  -- 100GBASE-ER4L CFP2 Optical Transceiver
h3cevtPortSw-SFP-16GFC-SW                OBJECT IDENTIFIER ::= { h3cevtPortSwitchType 274 }  -- SFP 16G FC Optical Transceiver short wave
h3cevtPortSw-SFP-16GFC-LW                OBJECT IDENTIFIER ::= { h3cevtPortSwitchType 275 }  -- SFP 16G FC Optical Transceiver long wave
h3cevtPortSw-SFP-32GFC-SW                OBJECT IDENTIFIER ::= { h3cevtPortSwitchType 276 }  -- SFP 32G FC Optical Transceiver short wave
h3cevtPortSw-SFP-32GFC-LW                OBJECT IDENTIFIER ::= { h3cevtPortSwitchType 277 }  -- SFP 32G FC Optical Transceiver long wave
h3cevtPortSw-XFP-10GBASE-PR-D3               OBJECT IDENTIFIER ::= { h3cevtPortSwitchType 278 }  -- XFP 10GBase PR-D3 Optical Transceiver
h3cevtPortSw-XFP-10GBASE-PRX-D3               OBJECT IDENTIFIER ::= { h3cevtPortSwitchType 279 }  -- XFP 10GBase PRX-D3 Optical Transceiver
h3cevtPortSw-5GBASE-T                    OBJECT IDENTIFIER ::= { h3cevtPortSwitchType 280 }  -- 5G Base-T Port
h3cevtPortSw-QSFP28-UNKNOWN              OBJECT IDENTIFIER ::= { h3cevtPortSwitchType 281 }  -- Unknown QSFP28 Transceiver
h3cevtPortSw-SFP28-UNKNOWN               OBJECT IDENTIFIER ::= { h3cevtPortSwitchType 282 }  -- Unknown SFP28 Transceiver
h3cevtPortSw-SFP28-NO-CONNECTOR          OBJECT IDENTIFIER ::= { h3cevtPortSwitchType 283 }  -- SFP28 No Connector
h3cevtPortSw-SFP-PLUS-9-8GCRPI-IR        OBJECT IDENTIFIER ::= { h3cevtPortSwitchType 284 }  -- 9.8GCRPI-IR SFP+ Transceiver
h3cevtPortSw-SFP-PLUS-9-8GCRPI-LR        OBJECT IDENTIFIER ::= { h3cevtPortSwitchType 285 }  -- 9.8GCRPI-LR SFP+ Transceiver
--
-- h3cevtStack section:
--
h3cevtStack     OBJECT IDENTIFIER ::= { h3cEntityVendortypeObjects 11 }


END

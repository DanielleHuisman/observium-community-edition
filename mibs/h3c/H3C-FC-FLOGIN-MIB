-- =====================================================================
-- Copyright (c) 2004-2013 Hangzhou H3C Tech. Co., Ltd. All rights reserved.
--
-- Description:
--      This MIB module is used for representing fabric login information.
-- Reference:
-- Version: V1.0
-- History:
--   V1.0 Initial version
--        created by qiaoxinghua 2013-02-27
-- =====================================================================
H3C-FC-FLOGIN-MIB DEFINITIONS ::= BEGIN

IMPORTS
    OBJECT-TYPE, MODULE-IDENTITY
        FROM SNMPv2-SMI
    TruthValue
        FROM SNMPv2-TC
    H3cFcNameId, H3cFcAddressId, H3cFcBbCredit,
    H3cFcClassOfServices, H3cFcRxMTU
        FROM H3C-FC-TC-MIB
    h3cSan, h3cVsanIndex
        FROM H3C-VSAN-MIB
    ifIndex
        FROM IF-MIB;

h3cFcFLogin MODULE-IDENTITY
    LAST-UPDATED   "201302271100Z"
    ORGANIZATION
        "Hangzhou H3C Tech. Co., Ltd."
    CONTACT-INFO
        "Platform Team Hangzhou H3C Tech. Co., Ltd.
         Hai-Dian District Beijing P.R. China
         http://www.h3c.com
         Zip:100085
        "
    DESCRIPTION
        "This MIB module is for representing fabric login information."
    REVISION       "201302271100Z"
    DESCRIPTION
        "Initial version of this MIB module."
    ::= { h3cSan 3 }

--
-- Node definitions
--
h3cFcFLoginMibObjects OBJECT IDENTIFIER ::= { h3cFcFLogin 1 }

h3cFcFLoginTable OBJECT-TYPE
    SYNTAX SEQUENCE OF H3cFcFLoginEntry
    MAX-ACCESS         not-accessible
    STATUS             current
    DESCRIPTION
        "A table of Fibre Channel related service parameters
         used to represent the fabric login information in accord
         with each Nx_Port attached to a particular Fibre Channel
         port in a particular VSAN (Virtual Storage Area Network).

         Each entry is created by a fabric switch when an Nx_Port
         successfully logged in to it explicitly or implicitly,
         and is deleted when the port logged out."
    ::= { h3cFcFLoginMibObjects 1 }

h3cFcFLoginEntry OBJECT-TYPE
    SYNTAX      H3cFcFLoginEntry
    MAX-ACCESS  not-accessible
    STATUS      current
    DESCRIPTION
        "A group of Fibre Channel related service parameters
         used to represent fabric login information of a specific
         Nx_Port."
    INDEX { ifIndex,
            h3cVsanIndex,
            h3cFcFLoginIndex }
    ::= { h3cFcFLoginTable 1 }

H3cFcFLoginEntry ::=
    SEQUENCE {
        h3cFcFLoginIndex
            H3cFcAddressId,
        h3cFcFLoginPortNodeWWN
            H3cFcNameId,
        h3cFcFLoginPortWWN
            H3cFcNameId,
        h3cFcFLoginPortFcId
            H3cFcAddressId,
        h3cFcFLoginRxBbCredit
            H3cFcBbCredit,
        h3cFcFLoginTxBbCredit
            H3cFcBbCredit,
        h3cFcFLoginClass2RxMTU
            H3cFcRxMTU,
        h3cFcFLoginClass3RxMTU
            H3cFcRxMTU,
        h3cFcFLoginSuppClassRequested
            H3cFcClassOfServices,
        h3cFcFLoginClass2ReqAgreed
            TruthValue,
        h3cFcFLoginClass3ReqAgreed
            TruthValue
       }

h3cFcFLoginIndex OBJECT-TYPE
    SYNTAX      H3cFcAddressId
    MAX-ACCESS  not-accessible
    STATUS      current
    DESCRIPTION
        "The index of current fabric login entry.  The Fibre Channel
         address identifier is used to identify the associated Nx_Port
         of this entry."
    ::= { h3cFcFLoginEntry 1 }

h3cFcFLoginPortNodeWWN OBJECT-TYPE
    SYNTAX      H3cFcNameId
    MAX-ACCESS  read-only
    STATUS      current
    DESCRIPTION
        "The world wide name of the Remote Node to which the
         logged-in Nx_Port belongs."
    ::= { h3cFcFLoginEntry 2 }

h3cFcFLoginPortWWN OBJECT-TYPE
    SYNTAX      H3cFcNameId
    MAX-ACCESS  read-only
    STATUS      current
    DESCRIPTION
        "The world wide name of the logged-in Nx_Port."
    ::= { h3cFcFLoginEntry 3 }

h3cFcFLoginPortFcId OBJECT-TYPE
    SYNTAX      H3cFcAddressId
    MAX-ACCESS  read-only
    STATUS      current
    DESCRIPTION
        "The Fibre Channel address identifier that has been
         assigned by the fabric to the logged-in Nx_Port."
    ::= { h3cFcFLoginEntry 4 }

h3cFcFLoginRxBbCredit OBJECT-TYPE
    SYNTAX      H3cFcBbCredit
    MAX-ACCESS  read-only
    STATUS      current
    DESCRIPTION
        "The maximum number of buffers available for a recipient to
         receive frames from the logged-in Nx_Port in Class2, Class3.
         The object is used in the buffer-to-buffer flow control from
         the logged-in Nx_Port to Fx_Port."
    ::= { h3cFcFLoginEntry 5 }

h3cFcFLoginTxBbCredit OBJECT-TYPE
    SYNTAX      H3cFcBbCredit
    MAX-ACCESS  read-only
    STATUS      current
    DESCRIPTION
        "The total number of buffers available for a sender to transmit
        frames to the logged-in Nx_Port in Class2, Class3.
        The object is used in the buffer-to-buffer flow control from
        Fx_Port to the logged-in Nx_Port."
    ::= { h3cFcFLoginEntry 6 }

h3cFcFLoginClass2RxMTU OBJECT-TYPE
    SYNTAX      H3cFcRxMTU
    MAX-ACCESS  read-only
    STATUS      current
    DESCRIPTION
        "The object specifies the Maximum Transmission Unit of an
         Fibre Channel frame that can be received by the logged-in
         Nx_Port in Class 2 service."
    ::= { h3cFcFLoginEntry 7 }

h3cFcFLoginClass3RxMTU OBJECT-TYPE
    SYNTAX      H3cFcRxMTU
    MAX-ACCESS  read-only
    STATUS      current
    DESCRIPTION
        "The object specifies the Maximum Transmission Unit of an
         Fibre Channel frame that can be received by the logged-in
         Nx_Port in Class 3 service."
    ::= { h3cFcFLoginEntry 8 }

h3cFcFLoginSuppClassRequested OBJECT-TYPE
    SYNTAX      H3cFcClassOfServices
    MAX-ACCESS  read-only
    STATUS      current
    DESCRIPTION
        "The object indicating the supported Classes that the logged-in
         Nx_Port has requested."
    ::= { h3cFcFLoginEntry 9 }

h3cFcFLoginClass2ReqAgreed OBJECT-TYPE
    SYNTAX      TruthValue
    MAX-ACCESS  read-only
    STATUS      current
    DESCRIPTION
        "The object indicating whether the Fx_Port has agreed to support
         Class 2 delivery that the logged-in Nx_Port requested.  It's
         meaningful only when the Class 2 delivery has been requested."
    ::= { h3cFcFLoginEntry 10 }

h3cFcFLoginClass3ReqAgreed OBJECT-TYPE
    SYNTAX      TruthValue
    MAX-ACCESS  read-only
    STATUS      current
    DESCRIPTION
        "The object indicating whether the Fx_Port has agreed to support
         Class 3 delivery that the logged-in Nx_Port requested.  It's
         meaningful only when the Class 3 delivery has been requested."
    ::= { h3cFcFLoginEntry 11 }

END

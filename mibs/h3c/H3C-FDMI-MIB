-- =============================================================================
-- Copyright (c) 2004-2013 Hangzhou H3C Tech. Co., Ltd.  All rights reserved.
--
-- Description:
--      This MIB module is for monitoring Fabric Device Management
--      Interface(FDMI) related entities.
-- Reference:
-- Version: V1.1
-- History:
--      V1.0 created by c04378
--      V1.1 Modified by q08977 2013-4-28
--           Change the oid of 'h3cFdmi' from h3cCommon.131 to h3cSan.7
-- =============================================================================
H3C-FDMI-MIB DEFINITIONS ::= BEGIN

IMPORTS
    h3cSan                                FROM H3C-VSAN-MIB
    MODULE-IDENTITY, OBJECT-TYPE,
    Unsigned32                             FROM SNMPv2-SMI
    SnmpAdminString                        FROM SNMP-FRAMEWORK-MIB
    FcNameIdOrZero                         FROM FC-MGMT-MIB
    T11FabricIndex                         FROM T11-TC-MIB         -- [RFC4439]
    fcmInstanceIndex                       FROM FC-MGMT-MIB;       -- [RFC4044]

h3cFdmi MODULE-IDENTITY
    LAST-UPDATED    "201206180000Z"
    ORGANIZATION
        "Hangzhou H3C Technologies Co., Ltd."
    CONTACT-INFO
        "Platform Team Hangzhou H3C Technologies Co., Ltd.
        Hai-Dian District Beijing P.R. China
        http://www.h3c.com
        Zip: 100085"
    DESCRIPTION
        "This MIB module is for monitoring Fabric Device Management
        Interface (FDMI) related entities.  This MIB
        module defines objects for managing the devices such as
        Host Bus Adapter (HBA).  It provides device information
        which has been registered with an Fibre Channel (FC) fabric using FDMI.
        For more information on FDMI, refer to Fibre Channel
        Generic Services-6 Section 6.7 : Fabric Device
        Management Interface."
    REVISION        "201206180000Z"
    DESCRIPTION
        "Initial version of this MIB module."
    ::= { h3cSan 7 }

h3cFdmiObjects OBJECT IDENTIFIER
    ::= { h3cFdmi 1 }

h3cFdmiInfo OBJECT IDENTIFIER
    ::= { h3cFdmiObjects 1 }

--
-- HBA information Table
--

h3cFdmiHbaInfoTable  OBJECT-TYPE
    SYNTAX       SEQUENCE OF H3cFdmiHbaInfoEntry
    MAX-ACCESS   not-accessible
    STATUS       current
    DESCRIPTION
        "This table lists all the HBAs registered with the
        Fabric Device Management Interface."
    ::= { h3cFdmiInfo 1 }

h3cFdmiHbaInfoEntry OBJECT-TYPE
    SYNTAX      H3cFdmiHbaInfoEntry
    MAX-ACCESS  not-accessible
    STATUS      current
    DESCRIPTION
        "An entry (conceptual row) in this table.  It
        provides information that has been registered with FDMI
        by a HBA, on the Virtual Storage Area Network (VSAN)
        where the registration was received.
        If the HBA has registered some but not all of the
        information represented by the columnar objects in this
        table, then the value of the unregistered objects will
        be either the zero-length string (for string-based
        objects) or the zero value (for integer-based objects)."
    INDEX       {
                    fcmInstanceIndex,
                    h3cFdmiHbaInfoFabricIndex,
                    h3cFdmiHbaInfoId
                }
    ::= { h3cFdmiHbaInfoTable 1 }

H3cFdmiHbaInfoEntry ::= SEQUENCE {
    h3cFdmiHbaInfoFabricIndex    T11FabricIndex,
    h3cFdmiHbaInfoId             FcNameIdOrZero,
    h3cFdmiHbaInfoNodeName       FcNameIdOrZero,
    h3cFdmiHbaInfoMfg            SnmpAdminString,
    h3cFdmiHbaInfoSn             SnmpAdminString,
    h3cFdmiHbaInfoModel          SnmpAdminString,
    h3cFdmiHbaInfoModelDescr     SnmpAdminString,
    h3cFdmiHbaInfoHwVer          SnmpAdminString,
    h3cFdmiHbaInfoDriverVer      SnmpAdminString,
    h3cFdmiHbaInfoOptROMVer      SnmpAdminString,
    h3cFdmiHbaInfoFwVer          SnmpAdminString,
    h3cFdmiHbaInfoOSInfo         SnmpAdminString,
    h3cFdmiHbaInfoMaxCTPayload   Unsigned32
}

h3cFdmiHbaInfoFabricIndex OBJECT-TYPE
    SYNTAX                T11FabricIndex
    MAX-ACCESS            not-accessible
    STATUS                current
    DESCRIPTION
        "The ID of the VSAN."
    ::= { h3cFdmiHbaInfoEntry 1 }

h3cFdmiHbaInfoId OBJECT-TYPE
    SYNTAX      FcNameIdOrZero
    MAX-ACCESS  not-accessible
    STATUS      current
    DESCRIPTION
        "The World Wide Name (WWN) of this HBA."
    REFERENCE
        "Fibre Channel Generic Services-6 Rev 9.4
        Section 6.7.4.5.1 ."
    ::= {h3cFdmiHbaInfoEntry  2}

h3cFdmiHbaInfoNodeName OBJECT-TYPE
    SYNTAX      FcNameIdOrZero
    MAX-ACCESS  read-only
    STATUS      current
    DESCRIPTION
        "The WWN of the node containing this HBA. "
    REFERENCE
        "Fibre Channel Generic Services-6 Rev 9.4
        Section 6.7.4.4.2.6 ."
    ::= {h3cFdmiHbaInfoEntry  3}

h3cFdmiHbaInfoMfg OBJECT-TYPE
    SYNTAX      SnmpAdminString
    MAX-ACCESS  read-only
    STATUS      current
    DESCRIPTION
        "The name of the manufacturer of this HBA."
    REFERENCE
        "Fibre Channel Generic Services-6 Rev 9.4
        Section 6.7.4.4.2.2 ."
    ::= {h3cFdmiHbaInfoEntry  4}

h3cFdmiHbaInfoSn OBJECT-TYPE
    SYNTAX      SnmpAdminString
    MAX-ACCESS  read-only
    STATUS      current
    DESCRIPTION
        "The serial number of this HBA."
    REFERENCE
        "Fibre Channel Generic Services-6 Rev 9.4
        Section 6.7.4.4.2.3 ."
    ::= {h3cFdmiHbaInfoEntry  5}

h3cFdmiHbaInfoModel OBJECT-TYPE
    SYNTAX      SnmpAdminString
    MAX-ACCESS  read-only
    STATUS      current
    DESCRIPTION
        "The model of this HBA."
    REFERENCE
        "Fibre Channel Generic Services-6 Rev 9.4
        Section 6.7.4.4.2.4 ."
    ::= {h3cFdmiHbaInfoEntry  6}

h3cFdmiHbaInfoModelDescr OBJECT-TYPE
    SYNTAX      SnmpAdminString
    MAX-ACCESS  read-only
    STATUS      current
    DESCRIPTION
        "The string that describes the model of this HBA."
    REFERENCE
        "Fibre Channel Generic Services-6 Rev 9.4
        Section 6.7.4.4.2.5 ."
    ::= {h3cFdmiHbaInfoEntry  7}

h3cFdmiHbaInfoHwVer OBJECT-TYPE
    SYNTAX      SnmpAdminString
    MAX-ACCESS  read-only
    STATUS      current
    DESCRIPTION
        "The hardware version of this HBA."
    REFERENCE
        "Fibre Channel Generic Services-6 Rev 9.4
        Section 6.7.4.4.2.8 ."
    ::= {h3cFdmiHbaInfoEntry  8}

h3cFdmiHbaInfoDriverVer OBJECT-TYPE
    SYNTAX      SnmpAdminString
    MAX-ACCESS  read-only
    STATUS      current
    DESCRIPTION
        "The version of the driver software controlling
        this HBA."
    REFERENCE
        "Fibre Channel Generic Services-6 Rev 9.4
        Section 6.7.4.4.2.9 ."
    ::= {h3cFdmiHbaInfoEntry  9}

h3cFdmiHbaInfoOptROMVer OBJECT-TYPE
    SYNTAX      SnmpAdminString
    MAX-ACCESS  read-only
    STATUS      current
    DESCRIPTION
        "The version of the Option ROM or the BIOS of this HBA."
    REFERENCE
        "Fibre Channel Generic Services-6 Rev 9.4
        Section 6.7.4.4.2.10 ."
    ::= {h3cFdmiHbaInfoEntry  10}

h3cFdmiHbaInfoFwVer OBJECT-TYPE
    SYNTAX      SnmpAdminString
    MAX-ACCESS  read-only
    STATUS      current
    DESCRIPTION
        "The version of the firmware executed by this HBA."
    REFERENCE
        "Fibre Channel Generic Services-6 Rev 9.4
        Section 6.7.4.4.2.11 ."
    ::= {h3cFdmiHbaInfoEntry  11}

h3cFdmiHbaInfoOSInfo OBJECT-TYPE
    SYNTAX      SnmpAdminString
    MAX-ACCESS  read-only
    STATUS      current
    DESCRIPTION
        "The type and version of the operating system
        controlling this HBA."
    REFERENCE
        "Fibre Channel Generic Services-6 Rev 9.4
        Section 6.7.4.4.2.12 ."
    ::= {h3cFdmiHbaInfoEntry  12}

h3cFdmiHbaInfoMaxCTPayload OBJECT-TYPE
    SYNTAX      Unsigned32
    MAX-ACCESS  read-only
    STATUS      current
    DESCRIPTION
        "The maximum size of the Common Transport (CT) payload
        including all CT headers but no FC frame headers,
        that may be sent or received by application software
        resident in the host containing this HBA.
        The unit is 32-bit words."
    REFERENCE
        "Fibre Channel Generic Services-6 Rev 9.4
        Section 6.7.4.4.2.13 ."
    ::= {h3cFdmiHbaInfoEntry  13}

-- HBA port information

h3cFdmiHbaPortTable  OBJECT-TYPE
    SYNTAX     SEQUENCE OF H3cFdmiHbaPortEntry
    MAX-ACCESS not-accessible
    STATUS     current
    DESCRIPTION
        "List of ports registered with Fabric Device
        Management Interface."
    ::= { h3cFdmiInfo 2 }

h3cFdmiHbaPortEntry OBJECT-TYPE
    SYNTAX     H3cFdmiHbaPortEntry
    MAX-ACCESS not-accessible
    STATUS     current
    DESCRIPTION
        "An entry (conceptual row) in this table.  It
        contains information about the Nx_port on the HBA,
        on the VSAN where the registration of the HBA
        with FDMI was received.
        If the HBA has registered some but not all of the
        information represented by the columnar objects in this
        table, then the value of the unregistered objects will
        be either the zero-length string (for string-based
        objects) or the zero value (for integer-based objects)."
    INDEX      {
                   fcmInstanceIndex,
                   h3cFdmiHbaInfoFabricIndex,
                   h3cFdmiHbaInfoId,
                   h3cFdmiHbaPortId
               }
    ::= { h3cFdmiHbaPortTable 1 }

H3cFdmiHbaPortEntry ::= SEQUENCE {
        h3cFdmiHbaPortId                   FcNameIdOrZero,
        h3cFdmiHbaPortSupportedFC4Type     OCTET STRING,
        h3cFdmiHbaPortSupportedSpeed       Unsigned32,
        h3cFdmiHbaPortCurrentSpeed         Unsigned32,
        h3cFdmiHbaPortMaxFrameSize         Unsigned32,
        h3cFdmiHbaPortOsDevName            SnmpAdminString,
        h3cFdmiHbaPortHostName             SnmpAdminString
}

h3cFdmiHbaPortId OBJECT-TYPE
    SYNTAX      FcNameIdOrZero
    MAX-ACCESS  not-accessible
    STATUS      current
    DESCRIPTION
        "The WWN of the port."
    REFERENCE
        "Fibre Channel Generic Services-6 Rev 9.4
        Section 6.7.4.4.3.3 ."
    ::= {h3cFdmiHbaPortEntry  1}

h3cFdmiHbaPortSupportedFC4Type OBJECT-TYPE
    SYNTAX      OCTET STRING (SIZE (0 | 32))
    MAX-ACCESS  read-only
    STATUS      current
    DESCRIPTION
        "The supported FC-4 types attribute registered for this
        port on this VSAN.  This is an array of 256 bits (32 bytes).
        The order of the bits in the 256-bit (32-byte) value is
        represented in network-byte order.
        If no FC-4 types has been registered, then the
        value of this object is the zero-length string."
    REFERENCE
        "Fibre Channel Generic Services-6 Rev 9.4
        Section 6.7.4.4.3.6 and Section 5.2.3.8 . "
    ::= {h3cFdmiHbaPortEntry  2}

h3cFdmiHbaPortSupportedSpeed OBJECT-TYPE
    SYNTAX      Unsigned32
    MAX-ACCESS  read-only
    STATUS      current
    DESCRIPTION
        "The supported speed registered for this port on this
        VSAN.  It is a bitmask that indicates the Fibre Channel
        Transmission Speeds that are supported on this port."
    REFERENCE
        "Fibre Channel Generic Services-6 Rev 9.4
        Section 6.7.4.4.3.8 ."
    ::= {h3cFdmiHbaPortEntry  3}

h3cFdmiHbaPortCurrentSpeed OBJECT-TYPE
    SYNTAX      Unsigned32
    MAX-ACCESS  read-only
    STATUS      current
    DESCRIPTION
        "The current speed registered for this port on this
        VSAN.  It is a bitmask that indicates the Fibre Channel
        Transmission Speed at which this port is currently operating."
    REFERENCE
        "Fibre Channel Generic Services-6 Rev 9.4
        Section 6.7.4.4.3.9 ."
    ::= {h3cFdmiHbaPortEntry  4}

h3cFdmiHbaPortMaxFrameSize OBJECT-TYPE
    SYNTAX      Unsigned32
    MAX-ACCESS  read-only
    STATUS      current
    DESCRIPTION
        "The maximum frame size attribute registered for this
        port on this VSAN.  The unit is bytes."
    REFERENCE
        "Fibre Channel Generic Services-6 Rev 9.4
        Section 6.7.4.4.3.10 ."
    ::= {h3cFdmiHbaPortEntry  5}

h3cFdmiHbaPortOsDevName OBJECT-TYPE
    SYNTAX      SnmpAdminString
    MAX-ACCESS  read-only
    STATUS      current
    DESCRIPTION
        "The OS device name attribute registered for this port
        on this VSAN."
    REFERENCE
        "Fibre Channel Generic Services-6 Rev 9.4
        Section 6.7.4.4.3.11 ."
    ::= {h3cFdmiHbaPortEntry  6}

h3cFdmiHbaPortHostName OBJECT-TYPE
    SYNTAX      SnmpAdminString
    MAX-ACCESS  read-only
    STATUS      current
    DESCRIPTION
        "The name of the host associated with this port."
    REFERENCE
        "Fibre Channel Generic Services-6, Late Comment
        Section 6.7.4.4.3.12 ."
    ::= {h3cFdmiHbaPortEntry  7}

END

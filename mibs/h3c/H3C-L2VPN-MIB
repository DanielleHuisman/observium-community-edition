-- =============================================================================
-- Copyright (c) 2004-2018 Hangzhou H3C Tech. Co., Ltd. All rights reserved.
--
-- Description: Layer 2 Virtual Private Network (L2VPN) MIB
-- Reference:
-- Version: V1.1
-- History:
-- V1.1 2018-01-17 Modified by Chenjuxi
--   Add node h3cL2vpnPwcFlowLabel
--      2017-11-21 Modified by Chenjian
--   Add h3cL2vpnLinkTable
--      2016-09-30 Modified by Liyun
--   Add h3cL2vpnAcCfgTable and h3cL2vpnPwCfgTable
-- V1.0 2015-01-16 Created by Yanneng
-- =============================================================================
H3C-L2VPN-MIB DEFINITIONS ::= BEGIN

IMPORTS
        RowStatus, TruthValue, DisplayString
    FROM SNMPv2-TC
        InterfaceIndexOrZero
    FROM IF-MIB
        MODULE-IDENTITY,
        OBJECT-TYPE,
        Unsigned32,
        IpAddress,
        NOTIFICATION-TYPE
    FROM SNMPv2-SMI
        InterfaceIndex
    FROM IF-MIB
        h3cCommon
    FROM HUAWEI-3COM-OID-MIB;

-- =============================================================================
-- module identity part
-- =============================================================================
h3cL2vpn MODULE-IDENTITY
    LAST-UPDATED "201801171500Z"       -- Jan 17, 2018 at 15:00 GMT
    ORGANIZATION
        "Hangzhou H3C Tech. Co., Ltd."
    CONTACT-INFO
        "Platform Team Hangzhou H3C Tech. Co., Ltd.
        Hai-Dian District Beijing P.R. China
        http://www.h3c.com
        Zip:100085
        "
    DESCRIPTION
        "Added node h3cL2vpnPwcFlowLabel."
    REVISION
        "201801171500Z"   -- Jan 17, 2018 at 15:00 GMT
    DESCRIPTION
        "Added h3cL2vpnLinkTable."
    REVISION
        "201711211500Z"   -- Nov 21, 2017 at 15:00 GMT
    DESCRIPTION
        "Added h3cL2vpnAcCfgTable and h3cL2vpnPwCfgTable."
    REVISION
        "201609301800Z"   -- Sept 30, 2016 at 18:00 GMT
    DESCRIPTION
        "This MIB contains objects to manage L2VPN."
    REVISION
        "201501160000Z"   -- Jan 16, 2015 at 00:00 GMT
    DESCRIPTION
        "Initial version."
    ::= { h3cCommon 162 }

-- ==================================================================
-- =================== h3cL2VpnPwNotifications definition ==========
-- ==================================================================

h3cL2vpnPwNotifications OBJECT IDENTIFIER ::= { h3cL2vpn 0 }

-- ==================================================================
-- ======================= h3cL2vpnGlobalTable definition ==========
-- ==================================================================

h3cL2vpnGlobalTable OBJECT IDENTIFIER ::= { h3cL2vpn 2 }

h3cL2vpnPwcTable OBJECT-TYPE
    SYNTAX      SEQUENCE OF H3cL2vpnPwcEntry
    MAX-ACCESS  not-accessible
    STATUS      current
    DESCRIPTION
        "This table contains pseudowire (PW) class information."
    ::= { h3cL2vpnGlobalTable 1 }

h3cL2vpnPwcEntry OBJECT-TYPE
    SYNTAX      H3cL2vpnPwcEntry
    MAX-ACCESS  not-accessible
    STATUS      current
    DESCRIPTION
        "Provides information about a PW class entry."
    INDEX
        {
            h3cL2vpnPwcName
        }
    ::= { h3cL2vpnPwcTable 1 }

H3cL2vpnPwcEntry ::= SEQUENCE
    {
        h3cL2vpnPwcName             OCTET STRING,
        h3cL2vpnPwcCvType           INTEGER,
        h3cL2vpnPwcCcType           INTEGER,
        h3cL2vpnPwcControlWord      TruthValue,
        h3cL2vpnPwcPwType           INTEGER,
        h3cL2vpnPwcRowStatus        RowStatus,
        h3cL2vpnPwcFlowLabel        INTEGER
    }

h3cL2vpnPwcName OBJECT-TYPE
    SYNTAX      OCTET STRING(SIZE(1..19))
    MAX-ACCESS  not-accessible
    STATUS      current
    DESCRIPTION
        "PW class name."
    ::= { h3cL2vpnPwcEntry 1 }

h3cL2vpnPwcCvType OBJECT-TYPE
    SYNTAX      INTEGER
    {
        unknown(1),
        bfd(2),
        rawBFD(3)
    }
    MAX-ACCESS  read-create
    STATUS      current
    DESCRIPTION
        "Virtual Circuit Connectivity Verification (VCCV) Bidirectional
         Forwarding Detection (BFD) type."
    ::= { h3cL2vpnPwcEntry 2 }

h3cL2vpnPwcCcType OBJECT-TYPE
    SYNTAX      INTEGER
    {
        unknown(1),
        controlWord(2),
        routerAlert(3),
        ttl(4)
    }
    MAX-ACCESS  read-create
    STATUS      current
    DESCRIPTION
        "Virtual Circuit Connectivity Verification (VCCV) Control Channel
        (CC) type."
    ::= { h3cL2vpnPwcEntry 3 }

h3cL2vpnPwcControlWord OBJECT-TYPE
    SYNTAX      TruthValue
    MAX-ACCESS  read-create
    STATUS      current
    DESCRIPTION
        "Whether control word is enabled."
    DEFVAL { false }
    ::= { h3cL2vpnPwcEntry 4 }

h3cL2vpnPwcPwType OBJECT-TYPE
    SYNTAX      INTEGER
    {
        vlan(4),
        ethernet(5)
    }
    MAX-ACCESS  read-create
    STATUS      current
    DESCRIPTION
        "PW encapsulation type."
    DEFVAL { vlan }
    ::= { h3cL2vpnPwcEntry 5 }

h3cL2vpnPwcRowStatus OBJECT-TYPE
    SYNTAX      RowStatus
    MAX-ACCESS  read-create
    STATUS      current
    DESCRIPTION
        "Operation status of this table entry.  A row entry cannot be modified
         when the value of this object is 'active'."
    ::= { h3cL2vpnPwcEntry 6 }

h3cL2vpnPwcFlowLabel OBJECT-TYPE
    SYNTAX      INTEGER
    {
        unknown(1),
        send(2),
        receive(3),
        both(4)
    }
    MAX-ACCESS  read-create
    STATUS      current
    DESCRIPTION
        "Flow label capability."
    DEFVAL { unknown }
    ::= { h3cL2vpnPwcEntry 7 }

-- ==================================================================
-- ======================= h3cL2vpnLinkTable definition ==========
-- ==================================================================

h3cL2vpnLinkTable OBJECT-TYPE
    SYNTAX      SEQUENCE OF H3cL2vpnLinkEntry
    MAX-ACCESS  not-accessible
    STATUS      current
    DESCRIPTION
        "This table contains L2VPN link information."
    ::= { h3cL2vpnGlobalTable 2 }

h3cL2vpnLinkEntry OBJECT-TYPE
    SYNTAX      H3cL2vpnLinkEntry
    MAX-ACCESS  not-accessible
    STATUS      current
    DESCRIPTION
        "Provides information about an L2VPN link entry."
    INDEX
        {
            h3cL2vpnLinkVsiIndex,
            h3cL2vpnLinkLinkID
        }
    ::= { h3cL2vpnLinkTable 1 }

H3cL2vpnLinkEntry ::= SEQUENCE
    {
        h3cL2vpnLinkVsiIndex        Unsigned32,
        h3cL2vpnLinkLinkID          Unsigned32,
        h3cL2vpnLinkType            INTEGER,
        h3cL2vpnLinkIfIndex         InterfaceIndex,
        h3cL2vpnLinkSrvID           Unsigned32,
        h3cL2vpnLinkTunnelID        Unsigned32
    }

h3cL2vpnLinkVsiIndex OBJECT-TYPE
    SYNTAX      Unsigned32
    MAX-ACCESS  not-accessible
    STATUS      current
    DESCRIPTION
        "Virtual Switch Instance (VSI) index of the l2vpn link.  The maximum
         value of unsigned32 means that the VSI index is invalid."
    ::= { h3cL2vpnLinkEntry 1 }

h3cL2vpnLinkLinkID OBJECT-TYPE
    SYNTAX      Unsigned32
    MAX-ACCESS  not-accessible
    STATUS      current
    DESCRIPTION
        "VSI link Identifier (ID) of the l2vpn link.  The maximum value of
         unsigned32 means that the VSI link ID is invalid."
    ::= { h3cL2vpnLinkEntry 2 }

h3cL2vpnLinkType OBJECT-TYPE
    SYNTAX      INTEGER
    {
        unknown(1),
        ac(2),
        tunnel(3)
    }
    MAX-ACCESS  read-only
    STATUS      current
    DESCRIPTION
        "Link type of the l2vpn link.  If the link type is neither Attachment
         Circuit (AC) nor tunnel, it returns 1."
    ::= { h3cL2vpnLinkEntry 3 }

h3cL2vpnLinkIfIndex OBJECT-TYPE
    SYNTAX      InterfaceIndex
    MAX-ACCESS  read-only
    STATUS      current
    DESCRIPTION
        "Interface index of the L2VPN link.  Value zero means that the interface
         index is invalid."
    ::= { h3cL2vpnLinkEntry 4 }

h3cL2vpnLinkSrvID OBJECT-TYPE
    SYNTAX      Unsigned32
    MAX-ACCESS  read-only
    STATUS      current
    DESCRIPTION
        "Service instance ID of the L2VPN link.  Value zero means that the
         service instance ID is invalid."
    ::= { h3cL2vpnLinkEntry 5 }

h3cL2vpnLinkTunnelID OBJECT-TYPE
    SYNTAX      Unsigned32
    MAX-ACCESS  read-only
    STATUS      current
    DESCRIPTION
        "The tunnel ID of the L2VPN link.  The maximum value of unsigned32 means
         that the tunnel ID is invalid."
    ::= { h3cL2vpnLinkEntry 6 }

-- ==================================================================
-- =======================h3cL2vpnVpwsTable definition  ============
-- ==================================================================

h3cL2vpnVpwsTable OBJECT IDENTIFIER ::= { h3cL2vpn 3 }

-- ==================================================================
-- =======================h3cL2vpnXcgTable definition  ============
-- ==================================================================
h3cL2vpnXcgTable OBJECT-TYPE
    SYNTAX      SEQUENCE OF H3cL2vpnXcgEntry
    MAX-ACCESS  not-accessible
    STATUS      current
    DESCRIPTION
        "This table contains cross-connect group information."
    ::= { h3cL2vpnVpwsTable 1 }

h3cL2vpnXcgEntry OBJECT-TYPE
    SYNTAX      H3cL2vpnXcgEntry
    MAX-ACCESS  not-accessible
    STATUS      current
    DESCRIPTION
        "Provides information about a cross-connect group entry."
    INDEX
        {
            h3cL2vpnXcgName
        }
    ::= { h3cL2vpnXcgTable 1 }

H3cL2vpnXcgEntry ::= SEQUENCE
    {
        h3cL2vpnXcgName            OCTET STRING,
        h3cL2vpnXcgAdminState      INTEGER,
        h3cL2vpnXcgRowStatus       RowStatus
    }

h3cL2vpnXcgName OBJECT-TYPE
    SYNTAX      OCTET STRING(SIZE(1..31))
    MAX-ACCESS  not-accessible
    STATUS      current
    DESCRIPTION
        "Cross-connect group name."
    ::= { h3cL2vpnXcgEntry 1 }

h3cL2vpnXcgAdminState OBJECT-TYPE
    SYNTAX      INTEGER
    {
        adminUp(1),
        adminDown(2)
    }
    MAX-ACCESS  read-create
    STATUS      current
    DESCRIPTION
        "The desired state of the cross-connect group.  The column doesn't exist
         when this group hasn't any connection."
    ::= { h3cL2vpnXcgEntry 2 }

h3cL2vpnXcgRowStatus OBJECT-TYPE
    SYNTAX      RowStatus
    MAX-ACCESS  read-create
    STATUS      current
    DESCRIPTION
        "Operation status of this table entry."
    ::= { h3cL2vpnXcgEntry 3 }
-- ==================================================================
-- ====================h3cL2vpnXcgConnTable definition  ============
-- ==================================================================
h3cL2vpnXcgConnTable OBJECT-TYPE
    SYNTAX      SEQUENCE OF H3cL2vpnXcgConnEntry
    MAX-ACCESS  not-accessible
    STATUS      current
    DESCRIPTION
        "This table contains cross-connect information."
    ::= { h3cL2vpnVpwsTable 2 }

h3cL2vpnXcgConnEntry OBJECT-TYPE
    SYNTAX      H3cL2vpnXcgConnEntry
    MAX-ACCESS  not-accessible
    STATUS      current
    DESCRIPTION
        "Provides information about a cross-connect entry."
    INDEX
        {
            h3cL2vpnXcgName,
            h3cL2vpnXcgConnName
        }
    ::= { h3cL2vpnXcgConnTable 1 }

H3cL2vpnXcgConnEntry ::= SEQUENCE
    {
        h3cL2vpnXcgConnName         OCTET STRING,
        h3cL2vpnXcgConnRowStatus    RowStatus
    }

h3cL2vpnXcgConnName OBJECT-TYPE
    SYNTAX      OCTET STRING(SIZE(1..20))
    MAX-ACCESS  not-accessible
    STATUS      current
    DESCRIPTION
        "Cross-connect name."
    ::= { h3cL2vpnXcgConnEntry 1 }

h3cL2vpnXcgConnRowStatus OBJECT-TYPE
    SYNTAX      RowStatus
    MAX-ACCESS  read-create
    STATUS      current
    DESCRIPTION
        "Operation status of this table entry."
    ::= { h3cL2vpnXcgConnEntry 2 }
-- ==================================================================
-- ====================h3cL2vpnXcgAcTable definition  ==============
-- ==================================================================
h3cL2vpnXcgAcTable OBJECT-TYPE
    SYNTAX      SEQUENCE OF H3cL2vpnXcgAcEntry
    MAX-ACCESS  not-accessible
    STATUS      current
    DESCRIPTION
        "This table contains information about attachment circuits (ACs)
         bound to cross-connects"
    ::= { h3cL2vpnVpwsTable 3 }

h3cL2vpnXcgAcEntry OBJECT-TYPE
    SYNTAX      H3cL2vpnXcgAcEntry
    MAX-ACCESS  not-accessible
    STATUS      current
    DESCRIPTION
        "Provides information about an attachment circuit entry."
    INDEX
        {
            h3cL2vpnXcgName,
            h3cL2vpnXcgConnName,
            h3cL2vpnXcgAcIfIndex,
            h3cL2vpnXcgAcEvcSrvInstId
        }
    ::= { h3cL2vpnXcgAcTable 1 }

H3cL2vpnXcgAcEntry ::= SEQUENCE
    {
        h3cL2vpnXcgAcIfIndex            InterfaceIndex,
        h3cL2vpnXcgAcEvcSrvInstId       Unsigned32,
        h3cL2vpnXcgAcAccessMode         INTEGER,
        h3cL2vpnXcgAcRowStatus          RowStatus
    }

h3cL2vpnXcgAcIfIndex OBJECT-TYPE
    SYNTAX      InterfaceIndex
    MAX-ACCESS  not-accessible
    STATUS      current
    DESCRIPTION
        "Index of the interface."
    ::= { h3cL2vpnXcgAcEntry 1 }

h3cL2vpnXcgAcEvcSrvInstId OBJECT-TYPE
    SYNTAX      Unsigned32
    MAX-ACCESS  not-accessible
    STATUS      current
    DESCRIPTION
        "Index of the service instance.  The value is always 0 when the
         interface isn't a layer 2 Ethernet interface."
    ::= { h3cL2vpnXcgAcEntry 2 }

h3cL2vpnXcgAcAccessMode OBJECT-TYPE
    SYNTAX      INTEGER
    {
        vlan(1),
        ethernet(2)
    }
    MAX-ACCESS  read-create
    STATUS      current
    DESCRIPTION
        "Access mode of the AC.  The value is meaningless when the
         interface isn't a layer 2 Ethernet interface."
    ::= { h3cL2vpnXcgAcEntry 3 }

h3cL2vpnXcgAcRowStatus OBJECT-TYPE
    SYNTAX      RowStatus
    MAX-ACCESS  read-create
    STATUS      current
    DESCRIPTION
        "Operation status of this table entry.  A row entry cannot be modified
         when the value of this object is 'active'."
    ::= { h3cL2vpnXcgAcEntry 4 }
-- ==================================================================
-- ====================h3cL2vpnXcgPwTable definition  ==============
-- ==================================================================
h3cL2vpnXcgPwTable OBJECT-TYPE
    SYNTAX      SEQUENCE OF H3cL2vpnXcgPwEntry
    MAX-ACCESS  not-accessible
    STATUS      current
    DESCRIPTION
        "This table contains PW information."
    ::= { h3cL2vpnVpwsTable 4 }

h3cL2vpnXcgPwEntry OBJECT-TYPE
    SYNTAX      H3cL2vpnXcgPwEntry
    MAX-ACCESS  not-accessible
    STATUS      current
    DESCRIPTION
        "Provides information about a PW entry."
    INDEX
        {
            h3cL2vpnXcgName,
            h3cL2vpnXcgConnName,
            h3cL2vpnXcgPwIndex
        }
    ::= { h3cL2vpnXcgPwTable 1 }

H3cL2vpnXcgPwEntry ::= SEQUENCE
    {
        h3cL2vpnXcgPwIndex            Unsigned32,
        h3cL2vpnXcgPwCfgType          INTEGER,
        h3cL2vpnXcgPwClassName        OCTET STRING,
        h3cL2vpnXcgPwTunnelPolicy     OCTET STRING,
        h3cL2vpnXcgPwPeerIp           IpAddress,
        h3cL2vpnXcgPwPwID             Unsigned32,
        h3cL2vpnXcgPwRowStatus        RowStatus
    }

h3cL2vpnXcgPwIndex OBJECT-TYPE
    SYNTAX      Unsigned32
    MAX-ACCESS  accessible-for-notify
    STATUS      current
    DESCRIPTION
        "A unique index for a PW."
    ::= { h3cL2vpnXcgPwEntry 1 }

h3cL2vpnXcgPwCfgType OBJECT-TYPE
    SYNTAX      INTEGER
    {
        primary(1),
        backup(2)
    }
    MAX-ACCESS  read-create
    STATUS      current
    DESCRIPTION
        "PW attribute."
    ::= { h3cL2vpnXcgPwEntry 2 }

h3cL2vpnXcgPwClassName OBJECT-TYPE
    SYNTAX      OCTET STRING(SIZE(1..19))
    MAX-ACCESS  read-create
    STATUS      current
    DESCRIPTION
        "PW class name."
    ::= { h3cL2vpnXcgPwEntry 3 }

h3cL2vpnXcgPwTunnelPolicy OBJECT-TYPE
    SYNTAX      OCTET STRING(SIZE(1..19))
    MAX-ACCESS  read-create
    STATUS      current
    DESCRIPTION
        "Tunnel policy name."
    ::= { h3cL2vpnXcgPwEntry 4 }

h3cL2vpnXcgPwPeerIp OBJECT-TYPE
    SYNTAX      IpAddress
    MAX-ACCESS  accessible-for-notify
    STATUS      current
    DESCRIPTION
        "Peer IP address."
    ::= { h3cL2vpnXcgPwEntry 5 }

h3cL2vpnXcgPwPwID OBJECT-TYPE
    SYNTAX      Unsigned32
    MAX-ACCESS  accessible-for-notify
    STATUS      current
    DESCRIPTION
        "PW identifier(ID)."
    ::= { h3cL2vpnXcgPwEntry 6 }

h3cL2vpnXcgPwRowStatus OBJECT-TYPE
    SYNTAX      RowStatus
    MAX-ACCESS  read-create
    STATUS      current
    DESCRIPTION
        "Operation status of this table entry.  A row entry cannot be modified
         when the value of this object is 'active'."
    ::= { h3cL2vpnXcgPwEntry 7 }
-- ==================================================================
-- ===============h3cL2vpnPwNotifications definition  ==============
-- ==================================================================
h3cL2vpnPwSwitchPtoB NOTIFICATION-TYPE
    OBJECTS
        {
            h3cL2vpnXcgPwIndex,
            h3cL2vpnXcgPwPeerIp,
            h3cL2vpnXcgPwPwID,
            h3cL2vpnXcgPwIndex,
            h3cL2vpnXcgPwPeerIp,
            h3cL2vpnXcgPwPwID
        }
    STATUS      current
    DESCRIPTION
        "This notification is generated when a primary-to-backup PW switching
         happens.  The first three elements show the primary PW,
         and the second three elements show the backup PW."
    ::= { h3cL2vpnPwNotifications 1 }

h3cL2vpnPwSwitchBtoP NOTIFICATION-TYPE
    OBJECTS
        {
            h3cL2vpnXcgPwIndex,
            h3cL2vpnXcgPwPeerIp,
            h3cL2vpnXcgPwPwID,
            h3cL2vpnXcgPwIndex,
            h3cL2vpnXcgPwPeerIp,
            h3cL2vpnXcgPwPwID
        }
    STATUS      current
    DESCRIPTION
        "This notification is generated when a backup-to-primary PW switching
         happens.  The first three elements show the backup PW,
         and the second three elements show the primary PW."
    ::= { h3cL2vpnPwNotifications 2 }
-- ==================================================================


-- ==================================================================
-- =======================h3cL2vpnAcTable definition  ============
-- ==================================================================

h3cL2vpnAcTable OBJECT IDENTIFIER ::= { h3cL2vpn 4 }

-- ==================================================================
-- ======================= h3cL2vpnAcCfgTable definition ==========
-- ==================================================================
h3cL2vpnAcCfgTable OBJECT-TYPE
    SYNTAX      SEQUENCE OF H3cL2vpnAcCfgEntry
    MAX-ACCESS  not-accessible
    STATUS      current
    DESCRIPTION
        "This table contains interface configurations and AC configurations."
    ::= { h3cL2vpnAcTable 1 }

h3cL2vpnAcCfgEntry OBJECT-TYPE
    SYNTAX      H3cL2vpnAcCfgEntry
    MAX-ACCESS  not-accessible
    STATUS      current
    DESCRIPTION
        "Each entry in this table describes information about interface
        configurations and AC configurations."
    INDEX
        {
            h3cL2vpnAcIfIndex,h3cL2vpnAcSrvId
        }
    ::= { h3cL2vpnAcCfgTable 1 }

H3cL2vpnAcCfgEntry ::= SEQUENCE
    {
        h3cL2vpnAcIfIndex            InterfaceIndex,
        h3cL2vpnAcSrvId              Unsigned32,
        h3cL2vpnAcIfName             DisplayString,
        h3cL2vpnAcVsiName            DisplayString,
        h3cL2vpnAcXcgName            DisplayString,
        h3cL2vpnAcXcgConnName        DisplayString,
        h3cL2vpnAcDot1qType          INTEGER,
        h3cL2vpnAcVLANID             Unsigned32
    }

h3cL2vpnAcIfIndex   OBJECT-TYPE
    SYNTAX      InterfaceIndex
    MAX-ACCESS  not-accessible
    STATUS      current
    DESCRIPTION
        "Index of the interface."
    ::= { h3cL2vpnAcCfgEntry 1 }

h3cL2vpnAcSrvId   OBJECT-TYPE
    SYNTAX      Unsigned32
    MAX-ACCESS  not-accessible
    STATUS      current
    DESCRIPTION
        "Index of the service instance.  The value is always 0 when the
        interface isn't a layer 2 Ethernet interface."
    ::= { h3cL2vpnAcCfgEntry 2 }

h3cL2vpnAcIfName OBJECT-TYPE
    SYNTAX      DisplayString (SIZE (0..255))
    MAX-ACCESS  read-only
    STATUS      current
    DESCRIPTION
        "The name of the interface."
    ::= { h3cL2vpnAcCfgEntry 3 }

h3cL2vpnAcVsiName OBJECT-TYPE
    SYNTAX      DisplayString (SIZE (0..255))
    MAX-ACCESS  read-only
    STATUS      current
    DESCRIPTION
        "The name of the VSI."
    ::= { h3cL2vpnAcCfgEntry 4 }

h3cL2vpnAcXcgName OBJECT-TYPE
    SYNTAX      DisplayString (SIZE (0..255))
    MAX-ACCESS  read-only
    STATUS      current
    DESCRIPTION
        "Cross-connect group name."
    ::= { h3cL2vpnAcCfgEntry 5 }

h3cL2vpnAcXcgConnName OBJECT-TYPE
    SYNTAX      DisplayString (SIZE (0..255))
    MAX-ACCESS  read-only
    STATUS      current
    DESCRIPTION
        "Cross-connect name."
    ::= { h3cL2vpnAcCfgEntry 6 }

h3cL2vpnAcDot1qType OBJECT-TYPE
    SYNTAX INTEGER
    {
        other(1),
        default(2),
        singletag(3)
    }
    MAX-ACCESS  read-only
    STATUS      current
    DESCRIPTION
        "This object indicates the configuration of VLAN IDs."
    ::= { h3cL2vpnAcCfgEntry 7 }

h3cL2vpnAcVLANID OBJECT-TYPE
    SYNTAX      Unsigned32
    MAX-ACCESS  read-only
    STATUS      current
    DESCRIPTION
        "When the interface is a layer 2 Ethernet interface, this
        object indicates the VLAN IDs assigned to this service instance.
        When the interface is a subinterface, this object indicates
        the outermost VLAN IDs in the VLAN-tagged packets."
    ::= { h3cL2vpnAcCfgEntry 8 }

-- ==================================================================
-- =======================h3cL2vpnPwTable definition  ============
-- ==================================================================

h3cL2vpnPwTable OBJECT IDENTIFIER ::= { h3cL2vpn 5 }

-- ==================================================================
-- ======================= h3cL2vpnPwCfgTable definition ==========
-- ==================================================================
h3cL2vpnPwCfgTable OBJECT-TYPE
    SYNTAX      SEQUENCE OF H3cL2vpnPwCfgEntry
    MAX-ACCESS  not-accessible
    STATUS      current
    DESCRIPTION
        "This table contains PW configuration."
    ::= { h3cL2vpnPwTable 1 }


h3cL2vpnPwCfgEntry OBJECT-TYPE
    SYNTAX      H3cL2vpnPwCfgEntry
    MAX-ACCESS  not-accessible
    STATUS      current
    DESCRIPTION
        "Each entry in this table describes configurations about a
        PW entry."
        INDEX
        {
            h3cL2vpnPwPeerIp, h3cL2vpnPwId
        }
    ::= { h3cL2vpnPwCfgTable 1 }

H3cL2vpnPwCfgEntry ::= SEQUENCE
    {
        h3cL2vpnPwPeerIp                IpAddress,
        h3cL2vpnPwId                    Unsigned32,
        h3cL2vpnPwAcIfIndex             InterfaceIndexOrZero,
        h3cL2vpnPwAcIfName              DisplayString,
        h3cL2vpnPwAcSrvId               Unsigned32,
        h3cL2vpnPwVsiName               DisplayString,
        h3cL2vpnPwXcgName               DisplayString,
        h3cL2vpnPwXcgConnName           DisplayString,
        h3cL2vpnPwQosDirection          INTEGER,
        h3cL2vpnPwInboundQosCir         Unsigned32,
        h3cL2vpnPwInboundQosCbs         Unsigned32,
        h3cL2vpnPwInboundQosEbs         Unsigned32,
        h3cL2vpnPwOutboundQosCir        Unsigned32,
        h3cL2vpnPwOutboundQosCbs        Unsigned32,
        h3cL2vpnPwOutboundQosEbs        Unsigned32
    }

h3cL2vpnPwPeerIp OBJECT-TYPE
    SYNTAX      IpAddress
    MAX-ACCESS  not-accessible
    STATUS      current
    DESCRIPTION
        "Peer IP address."
    ::= { h3cL2vpnPwCfgEntry 1 }

h3cL2vpnPwId OBJECT-TYPE
    SYNTAX      Unsigned32
    MAX-ACCESS  not-accessible
    STATUS      current
    DESCRIPTION
        "PW identifier (ID)."
    ::= { h3cL2vpnPwCfgEntry 2 }

h3cL2vpnPwAcIfIndex OBJECT-TYPE
    SYNTAX      InterfaceIndexOrZero
    MAX-ACCESS  read-only
    STATUS      current
    DESCRIPTION
        "Index of the AC interface."
    ::= { h3cL2vpnPwCfgEntry 3 }

h3cL2vpnPwAcIfName OBJECT-TYPE
    SYNTAX      DisplayString (SIZE (0..255))
    MAX-ACCESS  read-only
    STATUS      current
    DESCRIPTION
        "The name of the AC interface."
    ::= { h3cL2vpnPwCfgEntry 4 }

h3cL2vpnPwAcSrvId OBJECT-TYPE
    SYNTAX      Unsigned32
    MAX-ACCESS  read-only
    STATUS      current
    DESCRIPTION
        "Index of the service instance.  The value is always
        0 when the interface isn't a layer 2 Ethernet interface."
    ::= { h3cL2vpnPwCfgEntry 5 }

h3cL2vpnPwVsiName OBJECT-TYPE
    SYNTAX      DisplayString (SIZE (0..255))
    MAX-ACCESS  read-only
    STATUS      current
    DESCRIPTION
        "The name of the VSI."
    ::= { h3cL2vpnPwCfgEntry 6 }

h3cL2vpnPwXcgName OBJECT-TYPE
    SYNTAX      DisplayString (SIZE (0..255))
    MAX-ACCESS  read-only
    STATUS      current
    DESCRIPTION
        "Cross-connect group name."
    ::= { h3cL2vpnPwCfgEntry 7 }

h3cL2vpnPwXcgConnName OBJECT-TYPE
    SYNTAX      DisplayString (SIZE (0..255))
    MAX-ACCESS  read-only
    STATUS      current
    DESCRIPTION
        "Cross-connect name."
    ::= { h3cL2vpnPwCfgEntry 8 }

h3cL2vpnPwQosDirection OBJECT-TYPE
    SYNTAX      INTEGER
    {
        none(1),
        inbound(2),
        outbound(3),
        both(4)
    }
    MAX-ACCESS  read-only
    STATUS      current
    DESCRIPTION
        "Rate limit on the inbound or outbound direction."
    ::= { h3cL2vpnPwCfgEntry 9 }

h3cL2vpnPwInboundQosCir OBJECT-TYPE
    SYNTAX      Unsigned32
    MAX-ACCESS  read-only
    STATUS      current
    DESCRIPTION
        "Committed Information Rate on the inbound direction."
    ::= { h3cL2vpnPwCfgEntry 10 }

h3cL2vpnPwInboundQosCbs OBJECT-TYPE
    SYNTAX      Unsigned32
    MAX-ACCESS  read-only
    STATUS      current
    DESCRIPTION
        "Committed Burst Size on the inbound direction."
    ::= { h3cL2vpnPwCfgEntry 11 }

h3cL2vpnPwInboundQosEbs OBJECT-TYPE
    SYNTAX      Unsigned32
    MAX-ACCESS  read-only
    STATUS      current
    DESCRIPTION
        "Excess Burst Size on the inbound direction."
    ::= { h3cL2vpnPwCfgEntry 12 }

h3cL2vpnPwOutboundQosCir OBJECT-TYPE
    SYNTAX      Unsigned32
    MAX-ACCESS  read-only
    STATUS      current
    DESCRIPTION
        "Committed Information Rate on the outbound direction."
    ::= { h3cL2vpnPwCfgEntry 13 }

h3cL2vpnPwOutboundQosCbs OBJECT-TYPE
    SYNTAX      Unsigned32
    MAX-ACCESS  read-only
    STATUS      current
    DESCRIPTION
        "Committed Burst Size on the outbound direction."
    ::= { h3cL2vpnPwCfgEntry 14 }

h3cL2vpnPwOutboundQosEbs OBJECT-TYPE
    SYNTAX      Unsigned32
    MAX-ACCESS  read-only
    STATUS      current
    DESCRIPTION
        "Excess Burst Size on the outbound direction."
    ::= { h3cL2vpnPwCfgEntry 15 }
END

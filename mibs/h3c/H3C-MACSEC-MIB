-- ==========================================================================
-- Copyright (c) 2004-2015 Hangzhou H3C Tech. Co., Ltd.  All rights reserved.
--
-- Description: The file defines a MIB to provide MACSEC configuration
-- Reference:
-- Version: V1.0
-- History:
--   V1.0 2015-09-01 created by liubo
-- ==========================================================================
H3C-MACSEC-MIB DEFINITIONS ::= BEGIN

IMPORTS
    MODULE-IDENTITY, OBJECT-TYPE
        FROM SNMPv2-SMI
    InterfaceIndex
        FROM IF-MIB
    h3cCommon
        FROM HUAWEI-3COM-OID-MIB;

h3cMACsec MODULE-IDENTITY
    LAST-UPDATED "201509011615Z"
    ORGANIZATION
        "Hangzhou H3C Technologies Co., Ltd."
    CONTACT-INFO
        "Platform Team H3C Technologies Co., Ltd.
         Hai-Dian District Beijing P.R. China
         http://www.h3c.com
         Zip: 100085"
    DESCRIPTION
        "This MIB provides information for MACSEC configuration.
        MACSEC presents secure communication method."
    REVISION "201509011615Z"
    DESCRIPTION
        "Initial version."
    ::= { h3cCommon 163 }

h3cMACsecCFGObjects OBJECT IDENTIFIER ::= { h3cMACsec 1 }

-- ==========================================================================
-- h3cMACsecCFGPortTable OBJECT
-- ==========================================================================
h3cMACsecCFGPortTable OBJECT-TYPE
    SYNTAX SEQUENCE OF H3cMACsecCFGPortEntry
    MAX-ACCESS not-accessible
    STATUS current
    DESCRIPTION
    "The MACsec port table."
::= { h3cMACsecCFGObjects 1 }

h3cMACsecCFGPortEntry OBJECT-TYPE
    SYNTAX H3cMACsecCFGPortEntry
    MAX-ACCESS not-accessible
    STATUS current
    DESCRIPTION
    "The MACsec port entry."
    INDEX { h3cMACsecCFGPortIndex }
::= { h3cMACsecCFGPortTable 1 }

H3cMACsecCFGPortEntry ::= SEQUENCE {
    h3cMACsecCFGPortIndex         InterfaceIndex,
    h3cMACsecCFGPortPSKCKNName    OCTET STRING,
    h3cMACsecCFGPortPSKCAKValue   OCTET STRING }

h3cMACsecCFGPortIndex OBJECT-TYPE
    SYNTAX      InterfaceIndex
    MAX-ACCESS  not-accessible
    STATUS      current
    DESCRIPTION
    "An interface index indicates the port number associated with this port."
::= { h3cMACsecCFGPortEntry 1 }

h3cMACsecCFGPortPSKCKNName OBJECT-TYPE
    SYNTAX      OCTET STRING (SIZE(0..128))
    MAX-ACCESS  read-write
    STATUS      current
    DESCRIPTION
    "The connectivity asociation key name."
::= { h3cMACsecCFGPortEntry 2 }

h3cMACsecCFGPortPSKCAKValue OBJECT-TYPE
    SYNTAX      OCTET STRING (SIZE(0..128))
    MAX-ACCESS  read-write
    STATUS      current
    DESCRIPTION
    "The connectivity asociation key value."
::= { h3cMACsecCFGPortEntry 3 }

END

-- =================================================================
-- Copyright (c) 2004-2014 Hangzhou H3C Tech. Co., Ltd. All rights reserved.
--
-- Description: This MIB file is used for querying MP (Multilink PPP)
--              link status information.
-- Reference:
-- Version: V1.1
-- History:
--   V1.0 Initial version 2013-07-15
--   V1.1 2013-10-08 updated by jinlei 07761
--        Added enum active(1) and inactive(2) to h3cMpMemberlinkMpStatusV2
-- =================================================================
H3C-MP-V2-MIB DEFINITIONS ::= BEGIN

IMPORTS
    h3cCommon
        FROM HUAWEI-3COM-OID-MIB
    ifIndex
        FROM IF-MIB
    Integer32, Counter32, OBJECT-TYPE, MODULE-IDENTITY
        FROM SNMPv2-SMI
    DisplayString
        FROM SNMPv2-TC;

h3cMultilinkPPPV2 MODULE-IDENTITY
    LAST-UPDATED "201307150000Z"            -- July 15, 2013 at 00:00 GMT
    ORGANIZATION
        "Hangzhou H3C Tech. Co., Ltd."
    CONTACT-INFO
        "Platform Team Hangzhou H3C Tech. Co., Ltd.
         Hai-Dian District Beijing P.R. China
         http://www.h3c.com
         Zip:100085"
    DESCRIPTION
         "The H3C-MP-V2-MIB provides read access to MP(Multilink PPP) link
          status information. The information available through this MIB includes:
          the father channel, the bundled son channel, the slot on which son channels
          are bundled,
          the number of son channels, the bundle name,
          the statistics for lost fragments, reordered packets, unassigned packets,
          interleaved packets, and the received/sent sequence number, etc."
    REVISION "201307150000Z"        -- July 15, 2013 at 00:00 GMT
    DESCRIPTION
        "H3C-MP-V2-MIB module for managing MP(Multilink PPP)."
    ::= { h3cCommon 140 }


h3cMpObjectsV2 OBJECT IDENTIFIER ::= { h3cMultilinkPPPV2  1 }

h3cMpMultilinkV2Table OBJECT-TYPE
    SYNTAX SEQUENCE OF H3cMpMultilinkV2Entry
    MAX-ACCESS not-accessible
    STATUS current
    DESCRIPTION
        "This table describes the information of MP link.
         The index of this table is the interface index of MP group or
         VA (Virtual Access) interface."
    ::= { h3cMpObjectsV2 1 }

h3cMpMultilinkV2Entry OBJECT-TYPE
    SYNTAX H3cMpMultilinkV2Entry
    MAX-ACCESS not-accessible
    STATUS current
    DESCRIPTION
        "Each entry in this table describes the information of MP link.
         The available information includes:
         the father channel, the slot on which son channels are bundled,
         the number of bundled son channels,
         the statistics for lost fragments, reordered packets,
         unassigned packets, interleaved packets,
         and received/sent sequence number."
    INDEX { ifIndex }
    ::= { h3cMpMultilinkV2Table 1 }

H3cMpMultilinkV2Entry ::=
    SEQUENCE {
        h3cMpMultilinkDescrV2
            DisplayString,
        h3cMpBundleNameV2
            DisplayString,
        h3cMpBundledSlotV2
            Integer32,
        h3cMpBundledMemberCntV2
            Integer32,
        h3cMpLostFragmentsV2
            Counter32,
        h3cMpReorderedPktsV2
            Counter32,
        h3cMpUnassignedPktsV2
            Counter32,
        h3cMpInterleavedPktsV2
            Counter32,
        h3cMpRcvdSequenceV2
            Integer32,
        h3cMpSentSequenceV2
            Integer32
        }

h3cMpMultilinkDescrV2 OBJECT-TYPE
    SYNTAX DisplayString (SIZE (0..255))
    MAX-ACCESS read-only
    STATUS current
    DESCRIPTION
        "The interface name of the father interface on which son channels are bundled.
        It is the name of a Virtual Access or an MP group."
    ::= { h3cMpMultilinkV2Entry 1 }

h3cMpBundleNameV2 OBJECT-TYPE
    SYNTAX DisplayString (SIZE (0..255))
    MAX-ACCESS read-only
    STATUS current
    DESCRIPTION
        "The bundle name of the multilink.
        When authentication is configured, the bundle name is the authenticated
        user name; when authentication is not configured, the bundle name is
        multilink.
        "
    ::= { h3cMpMultilinkV2Entry 2 }

h3cMpBundledSlotV2 OBJECT-TYPE
    SYNTAX Integer32
    MAX-ACCESS read-only
    STATUS current
    DESCRIPTION
        "The slot on which son channels are bundled.
        "
    ::= { h3cMpMultilinkV2Entry 3 }

h3cMpBundledMemberCntV2 OBJECT-TYPE
    SYNTAX Integer32
    MAX-ACCESS read-only
    STATUS current
    DESCRIPTION
        "The number of the bundled son channel of the MP link. "
    ::= { h3cMpMultilinkV2Entry 4 }

h3cMpLostFragmentsV2 OBJECT-TYPE
    SYNTAX Counter32
    MAX-ACCESS read-only
    STATUS current
    DESCRIPTION
        "The number of fragments of the MP link discarded because
        bad fragments were received, or assembling the packet failed, etc."
    ::= { h3cMpMultilinkV2Entry 5 }

h3cMpReorderedPktsV2 OBJECT-TYPE
    SYNTAX Counter32
    MAX-ACCESS read-only
    STATUS current
    DESCRIPTION
        "The number of reordered incoming packets of the MP link.
        "
    ::= { h3cMpMultilinkV2Entry 6 }

h3cMpUnassignedPktsV2 OBJECT-TYPE
    SYNTAX Counter32
    MAX-ACCESS read-only
    STATUS current
    DESCRIPTION
        "The number of received packets of the MP link waiting for reordering.
        "
    ::= { h3cMpMultilinkV2Entry 7 }

h3cMpInterleavedPktsV2 OBJECT-TYPE
    SYNTAX Counter32
    MAX-ACCESS read-only
    STATUS current
    DESCRIPTION
        "The number of received packets of the MP link interleaved by the
        packets queued in RTPQ (Real-time Transport Protocol Queue) or
        LLQ (Low Latency Queue).
        "
    ::= { h3cMpMultilinkV2Entry 8 }

h3cMpRcvdSequenceV2 OBJECT-TYPE
    SYNTAX Integer32
    MAX-ACCESS read-only
    STATUS current
    DESCRIPTION
        "The current sequence number for the MP link to receive.
        "
    ::= { h3cMpMultilinkV2Entry 9 }

h3cMpSentSequenceV2 OBJECT-TYPE
    SYNTAX Integer32
    MAX-ACCESS read-only
    STATUS current
    DESCRIPTION
        "The current sequence number for the MP link to send.
        "
    ::= { h3cMpMultilinkV2Entry 10 }


h3cMpMemberlinkV2Table OBJECT-TYPE
    SYNTAX SEQUENCE OF H3cMpMemberlinkV2Entry
    MAX-ACCESS not-accessible
    STATUS current
    DESCRIPTION
        "This table describes the information of son channels of the MP link.
        The index of this table is the interface index of MP group or
        VA (Virtual Access) interface.
        "
    ::= { h3cMpObjectsV2 2 }

h3cMpMemberlinkV2Entry OBJECT-TYPE
    SYNTAX H3cMpMemberlinkV2Entry
    MAX-ACCESS not-accessible
    STATUS current
    DESCRIPTION
        "Each entry in this table describes the information of the bundled
        son channels of MP link. The available information includes:
        the interface index of the son channel,
        the interface name of the son channel.
        "
    INDEX { ifIndex, h3cMpMemberlinkSeqNumberV2 }
    ::= { h3cMpMemberlinkV2Table 1 }

H3cMpMemberlinkV2Entry ::=
    SEQUENCE {
        h3cMpMemberlinkSeqNumberV2
            Integer32,
        h3cMpMemberlinkIfIndexV2
            Integer32,
        h3cMpMemberlinkDescrV2
            DisplayString,
        h3cMpMemberlinkMpStatusV2
            INTEGER
    }

h3cMpMemberlinkSeqNumberV2 OBJECT-TYPE
    SYNTAX Integer32 (1..128)
    MAX-ACCESS read-only
    STATUS current
    DESCRIPTION
        "The bundled sequence number of the son channels of the MP link.
        This object is one of the index of the table.
        "
    ::= { h3cMpMemberlinkV2Entry 1 }

h3cMpMemberlinkIfIndexV2 OBJECT-TYPE
    SYNTAX Integer32
    MAX-ACCESS read-only
    STATUS current
    DESCRIPTION
        "The interface index of the son channels of the MP link.
        "
    ::= { h3cMpMemberlinkV2Entry 2 }

h3cMpMemberlinkDescrV2 OBJECT-TYPE
    SYNTAX DisplayString (SIZE (0..255))
    MAX-ACCESS read-only
    STATUS current
    DESCRIPTION
        "The interface name of the son channels of the MP link.
        "
    ::= { h3cMpMemberlinkV2Entry 3 }

h3cMpMemberlinkMpStatusV2 OBJECT-TYPE
    SYNTAX INTEGER
        {
            active(1),
            inactive(2)
        }
    MAX-ACCESS read-only
    STATUS current
    DESCRIPTION
        "The MP status of the son channels of the MP link.
        "
    ::= { h3cMpMemberlinkV2Entry 4 }

END

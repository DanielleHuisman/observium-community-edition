-- =============================================================================
-- Copyright (c) 2004-2014 Hangzhou H3C Tech. Co., Ltd. All rights reserved.
--
-- Description: Multiprotocol Label Switching Traffic Engineering MIB
-- Reference:
-- Version: V1.0
-- History:
--   V1.0 2013-06-13 Initial version Created by Neng Yan
-- =============================================================================
H3C-MPLSTE-MIB DEFINITIONS ::= BEGIN
IMPORTS
    MODULE-IDENTITY, OBJECT-TYPE, Unsigned32
        FROM SNMPv2-SMI
    RowStatus, TruthValue
        FROM SNMPv2-TC
    h3cCommon
        FROM HUAWEI-3COM-OID-MIB
    ;

-- =============================================================================
-- module identity part
-- =============================================================================
h3cMplsTe MODULE-IDENTITY
    LAST-UPDATED
        "201306131800Z"        -- Jan 13, 2013 at 18:00 GMT
    ORGANIZATION
        "Hangzhou H3C Technologies Co., Ltd."
    CONTACT-INFO
        "Platform Team Hangzhou H3C Technologies Co., Ltd.
         Hai-Dian District Beijing P.R. China
         http://www.h3c.com
         Zip:100085"
    DESCRIPTION
        "Multiprotocol Label Switching Traffic Engineering MIB"
    REVISION
        "201306131800Z"   -- Jan 13, 2013 at 18:00 GMT
    DESCRIPTION
        "Initial version of this MIB."
    ::= { h3cCommon 143 }

-- =============================================================================
-- object definition begin
-- =============================================================================
h3cMplsTeObjects      OBJECT IDENTIFIER ::= { h3cMplsTe 1 }

h3cMplsTeScalarGroup  OBJECT IDENTIFIER ::= { h3cMplsTeObjects 1 }

h3cMplsTeStatus    OBJECT-TYPE
    SYNTAX      TruthValue
    MAX-ACCESS  read-write
    STATUS      current
    DESCRIPTION
        "The global configuration of MPLS(Multiprotocol Label Switching)
        TE(Traffic Engineering)."
    ::= { h3cMplsTeScalarGroup 1 }

h3cMplsTeRsvpStatus    OBJECT-TYPE
    SYNTAX      TruthValue
    MAX-ACCESS  read-write
    STATUS      current
    DESCRIPTION
        "The global configuration of RSVP(Resource Reservation Protocol)."
    ::= { h3cMplsTeScalarGroup 2 }

-- =============================================================================
-- h3cMplsTeTable Definition
-- =============================================================================
h3cMplsTeTable     OBJECT-TYPE
    SYNTAX      SEQUENCE OF H3cMplsTeEntry
    MAX-ACCESS  not-accessible
    STATUS      current
    DESCRIPTION
        "A table for configuring MPLS TE parameters."
    ::= { h3cMplsTeObjects 2 }

h3cMplsTeEntry     OBJECT-TYPE
    SYNTAX      H3cMplsTeEntry
    MAX-ACCESS  not-accessible
    STATUS      current
    DESCRIPTION
        "An entry for configuring MPLS TE parameters."
    INDEX
    {
        h3cMplsTeIndex
    }
    ::= { h3cMplsTeTable 1 }

H3cMplsTeEntry ::=
    SEQUENCE
    {
        h3cMplsTeIndex                 Unsigned32,
        h3cMplsTeCapability            TruthValue,
        h3cMplsTeRowStatus             RowStatus
    }

h3cMplsTeIndex     OBJECT-TYPE
    SYNTAX      Unsigned32(1..4294967295)
    MAX-ACCESS  not-accessible
    STATUS      current
    DESCRIPTION
        "Index of TE interface."
    ::= { h3cMplsTeEntry 1 }

h3cMplsTeCapability    OBJECT-TYPE
    SYNTAX      TruthValue
    MAX-ACCESS  read-create
    STATUS      current
    DESCRIPTION
        "The TE capability of an interface."
    DEFVAL { false }
    ::= { h3cMplsTeEntry 2 }

h3cMplsTeRowStatus     OBJECT-TYPE
    SYNTAX      RowStatus
    MAX-ACCESS  read-create
    STATUS      current
    DESCRIPTION
        "Operation status of this table entry.  A row entry cannot
        be modified when the value of this object is 'active'."
    ::= { h3cMplsTeEntry 3 }
-- =============================================================================
-- End of h3cMplsTeTable Definition
-- =============================================================================

-- =============================================================================
-- h3cMplsTeRsvpTable Definition
-- =============================================================================
h3cMplsTeRsvpTable     OBJECT-TYPE
    SYNTAX      SEQUENCE OF H3cMplsTeRsvpEntry
    MAX-ACCESS  not-accessible
    STATUS      current
    DESCRIPTION
        "A table for configuring RSVP(Resource Reservation Protocol)
        TE parameters."
    ::= { h3cMplsTeObjects 3 }

h3cMplsTeRsvpEntry     OBJECT-TYPE
    SYNTAX      H3cMplsTeRsvpEntry
    MAX-ACCESS  not-accessible
    STATUS      current
    DESCRIPTION
        "An entry for configuring RSVP TE parameters."
    INDEX
    {
        h3cMplsTeRsvpIndex
    }
    ::= { h3cMplsTeRsvpTable 1 }

H3cMplsTeRsvpEntry ::=
    SEQUENCE
    {
        h3cMplsTeRsvpIndex                 Unsigned32,
        h3cMplsTeRsvpCapability            TruthValue,
        h3cMplsTeRsvpRowStatus             RowStatus
    }

h3cMplsTeRsvpIndex     OBJECT-TYPE
    SYNTAX      Unsigned32(1..4294967295)
    MAX-ACCESS  not-accessible
    STATUS      current
    DESCRIPTION
        "Index of RSVP interface."
    ::= { h3cMplsTeRsvpEntry 1 }

h3cMplsTeRsvpCapability    OBJECT-TYPE
    SYNTAX      TruthValue
    MAX-ACCESS  read-create
    STATUS      current
    DESCRIPTION
        "The RSVP capability of an interface."
    DEFVAL { false }
    ::= { h3cMplsTeRsvpEntry 2 }

h3cMplsTeRsvpRowStatus     OBJECT-TYPE
    SYNTAX      RowStatus
    MAX-ACCESS  read-create
    STATUS      current
    DESCRIPTION
        "Operation status of this table entry.  A row entry cannot
        be modified when the value of this object is 'active'."
    ::= { h3cMplsTeRsvpEntry 3 }
-- =============================================================================
-- End of h3cMplsTeRsvpTable Definition
-- =============================================================================

END

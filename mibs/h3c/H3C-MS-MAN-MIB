-- ====================================================================
-- Copyright (C) 2007 by H3C TECHNOLOGIES. All rights reserved.
--
-- Description: MS(Media Switch Server) Configuration management MIB
-- Reference:
-- Version: V1.0
-- History:
-- V1.0 Initial version 2007-04-13 created by zhoujianming
--- ===================================================================
H3C-MS-MAN-MIB DEFINITIONS ::= BEGIN

IMPORTS
    Unsigned32, OBJECT-TYPE, MODULE-IDENTITY, NOTIFICATION-TYPE
        FROM SNMPv2-SMI
    PhysicalIndex
        FROM ENTITY-MIB
    h3cSurveillanceMIB
        FROM HUAWEI-3COM-OID-MIB;

h3cMSMan MODULE-IDENTITY
    LAST-UPDATED "200708130000Z"  -- August 13, 2007  GMT
    ORGANIZATION
        "Hangzhou H3C Tech. Co., Ltd."
    CONTACT-INFO
        "Platform Team Hangzhou H3C Tech. Co., Ltd.
        Hai-Dian District Beijing P.R. China
        http://www.h3c.com
        Zip:100085
        "
    DESCRIPTION
        "This MIB is defined to manage MS components
        according to specific capability."
    ::= { h3cSurveillanceMIB 3 }

--
-- Node definitions
--

h3cMSManMIBObjects OBJECT IDENTIFIER ::= { h3cMSMan 1 }
--
-- statistical period
--
h3cMSStatisticalPeriod OBJECT-TYPE
    SYNTAX Unsigned32
    MAX-ACCESS read-write
    STATUS current
    DESCRIPTION
        "The statistical period of this entity, which unit is
        second and default value is 300 seconds."
    ::= { h3cMSManMIBObjects 1 }

h3cMSManMIBTables OBJECT IDENTIFIER ::= { h3cMSMan 2 }
--
-- forward table
--
h3cMSForwardTable OBJECT-TYPE
    SYNTAX SEQUENCE OF H3cMSForwardEntry
    MAX-ACCESS  not-accessible
    STATUS      current
    DESCRIPTION
        "MS Forward table, used to get the forwarding information
         of the entity. "
    ::= { h3cMSManMIBTables 1 }

h3cMSForwardEntry OBJECT-TYPE
    SYNTAX      H3cMSForwardEntry
    MAX-ACCESS  not-accessible
    STATUS      current
    DESCRIPTION
        "h3cMSForward table entry."
    INDEX { h3cMSForwardIndex }
    ::= { h3cMSForwardTable 1 }

H3cMSForwardEntry ::=
    SEQUENCE {
        h3cMSForwardIndex                   PhysicalIndex,
        h3cMSForwardMaxConnection           Unsigned32,
        h3cMSForwardConnectionThreshold     Unsigned32,
        h3cMSCurrentForwardConnection       Unsigned32,
        h3cMSPeriodForwardConnection        Unsigned32,
        h3cMSForwardTotalTime               Unsigned32,
        h3cMSForwardTotalConn               Unsigned32
     }
h3cMSForwardIndex OBJECT-TYPE
    SYNTAX PhysicalIndex
    MAX-ACCESS accessible-for-notify
    STATUS current
    DESCRIPTION
        "The value of this object is the entity index, which
         depends on the implementation of ENTITY-MIB. "
    ::= { h3cMSForwardEntry 1 }


h3cMSForwardMaxConnection OBJECT-TYPE
    SYNTAX      Unsigned32
    MAX-ACCESS  read-only
    STATUS      current
    DESCRIPTION
        "The maxium number of forward connections the entity can
        support."
    ::= { h3cMSForwardEntry 2 }

h3cMSForwardConnectionThreshold OBJECT-TYPE
    SYNTAX      Unsigned32
    MAX-ACCESS  read-write
    STATUS      current
    DESCRIPTION
        "The threshold of forward connections."
    ::= { h3cMSForwardEntry 3 }

h3cMSCurrentForwardConnection OBJECT-TYPE
    SYNTAX      Unsigned32
    MAX-ACCESS  read-only
    STATUS      current
    DESCRIPTION
        "Number of forward connections the entity provided
        in this time."
    ::= { h3cMSForwardEntry 4 }

h3cMSPeriodForwardConnection OBJECT-TYPE
    SYNTAX      Unsigned32
    MAX-ACCESS  read-only
    STATUS      current
    DESCRIPTION
        "The maxium number of forward connections within the
        last statistical period."
    ::= { h3cMSForwardEntry 5 }

h3cMSForwardTotalTime OBJECT-TYPE
    SYNTAX      Unsigned32
    MAX-ACCESS  read-only
    STATUS      current
    DESCRIPTION
        "The total forward connection time the entity has
        serviced since its startup."
    ::= { h3cMSForwardEntry 6 }

h3cMSForwardTotalConn OBJECT-TYPE
    SYNTAX      Unsigned32
    MAX-ACCESS  read-only
    STATUS      current
    DESCRIPTION
        "The total forward connection numbers the entity has
        serviced since its startup."
    ::= { h3cMSForwardEntry 7 }

--
-- VOD table
--
h3cMSVODTable OBJECT-TYPE
    SYNTAX SEQUENCE OF H3cMSVODEntry
    MAX-ACCESS  not-accessible
    STATUS      current
    DESCRIPTION
        "MS VOD(video on demand) table, used to get the VOD
        information of the entity."
    ::= { h3cMSManMIBTables 2 }

    h3cMSVODEntry OBJECT-TYPE
    SYNTAX      H3cMSVODEntry
    MAX-ACCESS  not-accessible
    STATUS      current
    DESCRIPTION
        "h3cMSVOD table entry."
    INDEX { h3cMSVODIndex }
    ::= { h3cMSVODTable 1 }

H3cMSVODEntry ::=
    SEQUENCE {
        h3cMSVODIndex                   PhysicalIndex,
        h3cMSVODMaxConnection           Unsigned32,
        h3cMSVODConnectionThreshold     Unsigned32,
        h3cMSCurrentVODConnection       Unsigned32,
        h3cMSPeriodVODMaxConnection     Unsigned32,
        h3cMSVODTotalTime               Unsigned32,
        h3cMSVODTotalConn               Unsigned32
     }
h3cMSVODIndex OBJECT-TYPE
    SYNTAX      PhysicalIndex
    MAX-ACCESS  accessible-for-notify
    STATUS      current
    DESCRIPTION
        "The value of this object is the entity index, which
        depends on the implementation of ENTITY-MIB. "
    ::= { h3cMSVODEntry 1 }

h3cMSVODMaxConnection OBJECT-TYPE
    SYNTAX      Unsigned32
    MAX-ACCESS  read-only
    STATUS      current
    DESCRIPTION
        "The maxium number of VOD connections the entity
        can support."
    ::= { h3cMSVODEntry 2 }

h3cMSVODConnectionThreshold OBJECT-TYPE
    SYNTAX      Unsigned32
    MAX-ACCESS  read-write
    STATUS      current
    DESCRIPTION
        "The threshold of VOD connections."
    ::= { h3cMSVODEntry 3 }

h3cMSCurrentVODConnection OBJECT-TYPE
    SYNTAX      Unsigned32
    MAX-ACCESS  read-only
    STATUS      current
    DESCRIPTION
        "Number of VOD connections the entity provided
        in this time."
    ::= { h3cMSVODEntry 4 }

h3cMSPeriodVODMaxConnection OBJECT-TYPE
    SYNTAX      Unsigned32
    MAX-ACCESS  read-only
    STATUS      current
    DESCRIPTION
        "The maxium number of VOD connections within the last
        statistical period."
    ::= { h3cMSVODEntry 5 }

h3cMSVODTotalTime OBJECT-TYPE
    SYNTAX      Unsigned32
    MAX-ACCESS  read-only
    STATUS      current
    DESCRIPTION
        "The total VOD connection time the entity has serviced
        since its startup."
    ::= { h3cMSVODEntry 6 }

h3cMSVODTotalConn OBJECT-TYPE
    SYNTAX      Unsigned32
    MAX-ACCESS  read-only
    STATUS      current
    DESCRIPTION
        "The total VOD connection numbers the entity has serviced
        since its startup."
    ::= { h3cMSVODEntry 7 }

--
-- Record table
--
h3cMSRecordTable OBJECT-TYPE
    SYNTAX SEQUENCE OF H3cMSRecordEntry
    MAX-ACCESS  not-accessible
    STATUS      current
    DESCRIPTION
        "MS Record table, used to get the record information of
        the entity."
    ::= { h3cMSManMIBTables 3 }

h3cMSRecordEntry OBJECT-TYPE
    SYNTAX      H3cMSRecordEntry
    MAX-ACCESS  not-accessible
    STATUS      current
    DESCRIPTION
        "h3cMSRecord table entry."
    INDEX { h3cMSRecordIndex }
    ::= { h3cMSRecordTable 1 }

H3cMSRecordEntry ::=
    SEQUENCE {
        h3cMSRecordIndex                    PhysicalIndex,
        h3cMSRecordMaxConnection            Unsigned32,
        h3cMSRecordConnectionThreshold      Unsigned32,
        h3cMSCurrentRecordConnection        Unsigned32,
        h3cMSPeriodRecordMaxConnection      Unsigned32,
        h3cMSRecordTotalTime                Unsigned32,
        h3cMSRecordTotalConn                Unsigned32
     }
h3cMSRecordIndex OBJECT-TYPE
    SYNTAX      PhysicalIndex
    MAX-ACCESS  accessible-for-notify
    STATUS      current
    DESCRIPTION
        "The value of this object is the entity index, which
        depends on the implementation of ENTITY-MIB. "
    ::= { h3cMSRecordEntry 1 }

h3cMSRecordMaxConnection OBJECT-TYPE
    SYNTAX      Unsigned32
    MAX-ACCESS  read-only
    STATUS      current
    DESCRIPTION
        "The maxium number of record connections the entity can
        support."
    ::= { h3cMSRecordEntry 2 }

h3cMSRecordConnectionThreshold OBJECT-TYPE
    SYNTAX      Unsigned32
    MAX-ACCESS  read-write
    STATUS      current
    DESCRIPTION
        "The threshold of record connections ."
    ::= { h3cMSRecordEntry 3 }

h3cMSCurrentRecordConnection OBJECT-TYPE
    SYNTAX      Unsigned32
    MAX-ACCESS  read-only
    STATUS      current
    DESCRIPTION
        "Number of record connections the entity provided in
        this time."
    ::= { h3cMSRecordEntry 4 }

h3cMSPeriodRecordMaxConnection OBJECT-TYPE
    SYNTAX      Unsigned32
    MAX-ACCESS  read-only
    STATUS      current
    DESCRIPTION
        "The maxium number of record connections within the
        last statistical period."
    ::= { h3cMSRecordEntry 5 }

h3cMSRecordTotalTime OBJECT-TYPE
    SYNTAX      Unsigned32
    MAX-ACCESS  read-only
    STATUS      current
    DESCRIPTION
        "The total record connection time the entity has
        serviced since its startup."
    ::= { h3cMSRecordEntry 6 }

h3cMSRecordTotalConn OBJECT-TYPE
    SYNTAX      Unsigned32
    MAX-ACCESS  read-only
    STATUS      current
    DESCRIPTION
        "The total record connection numbers the entity
        has serviced since its startup."
    ::= { h3cMSRecordEntry 7 }

--
-- Notification definitions
--
-- =================================================================
-- Traps are defined below.
h3cMSManMIBTrap OBJECT IDENTIFIER ::= { h3cMSMan 3 }

-- All trap definitions should be placed under this object.
h3cMSManTrapPrex OBJECT IDENTIFIER ::= { h3cMSManMIBTrap 0 }

h3cMSManVODConnectionThresholdTrap NOTIFICATION-TYPE
    OBJECTS
    {
        h3cMSVODIndex,
        h3cMSCurrentVODConnection,
        h3cMSVODConnectionThreshold
    }
    STATUS     current
    DESCRIPTION
        "Current VOD connection exceeds the threshold."
    ::= { h3cMSManTrapPrex 1 }

h3cMSManVODConnectionRecoverTrap NOTIFICATION-TYPE
    OBJECTS
    {
        h3cMSVODIndex,
        h3cMSCurrentVODConnection,
        h3cMSVODConnectionThreshold
    }
    STATUS    current
    DESCRIPTION
        "Current VOD connection recovers under the threshold."
    ::= { h3cMSManTrapPrex 2 }

h3cMSManForwardConnectionThresholdTrap NOTIFICATION-TYPE
    OBJECTS
    {
        h3cMSForwardIndex,
        h3cMSCurrentForwardConnection,
        h3cMSForwardConnectionThreshold
    }
    STATUS     current
    DESCRIPTION
        "Current forward connection exceeds the threshold."
    ::= { h3cMSManTrapPrex 3 }

h3cMSManForwardConnectionRecoverTrap NOTIFICATION-TYPE
    OBJECTS
    {
        h3cMSForwardIndex,
        h3cMSCurrentForwardConnection,
        h3cMSForwardConnectionThreshold
    }
    STATUS     current
    DESCRIPTION
        "Current forward connection recovers under the threshold."
    ::= { h3cMSManTrapPrex 4 }

h3cMSManRecordConnectionThresholdTrap NOTIFICATION-TYPE
    OBJECTS
    {
        h3cMSRecordIndex,
        h3cMSCurrentRecordConnection,
        h3cMSRecordConnectionThreshold
    }
    STATUS     current
    DESCRIPTION
        "Current record connection exceeds the threshold."
    ::= { h3cMSManTrapPrex 5 }

h3cMSManRecordConnectionRecoverTrap NOTIFICATION-TYPE
    OBJECTS
    {
        h3cMSRecordIndex,
        h3cMSCurrentRecordConnection,
        h3cMSRecordConnectionThreshold
    }
    STATUS     current
    DESCRIPTION
        "Current record connection recovers under the threshold."
    ::= { h3cMSManTrapPrex 6 }


END

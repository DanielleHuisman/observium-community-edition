-- =================================================================
-- Copyright (c) 2004-2015 Hangzhou H3C Tech. Co., Ltd. All rights reserved.
--
-- Description: OSPF (Open Shortest Path First) MIB
-- Reference:
-- Version: V1.0
-- History:
-- V1.0 2014-12-17 Created by Xu Jing
-- =================================================================
H3C-OSPF-MIB DEFINITIONS ::= BEGIN

IMPORTS
    IpAddress, Integer32, OBJECT-TYPE, MODULE-IDENTITY
        FROM SNMPv2-SMI
    h3cCommon
        FROM HUAWEI-3COM-OID-MIB;


h3cOspf MODULE-IDENTITY
    LAST-UPDATED "201412171700Z"
    ORGANIZATION
        "Hangzhou H3C Tech. Co., Ltd."
    CONTACT-INFO
        "Platform Team Hangzhou H3C Tech. Co., Ltd.
        Hai-Dian District Beijing P.R. China
        http://www.h3c.com
        Zip:100085
        "
    DESCRIPTION
        "This MIB file provides information about OSPF."
    REVISION "201412171700Z"
    DESCRIPTION
        "The initial version of this MIB file."
    ::= { h3cCommon 161 }

h3cOspfNetworkTable OBJECT-TYPE
    SYNTAX SEQUENCE OF H3cOspfNetworkEntry
    MAX-ACCESS not-accessible
    STATUS current
    DESCRIPTION
        "The table provides the configured parameters of OSPF networks."
    ::= { h3cOspf 1 }

h3cOspfNetworkEntry OBJECT-TYPE
    SYNTAX H3cOspfNetworkEntry
    MAX-ACCESS not-accessible
    STATUS current
    DESCRIPTION
        "Each entry contains information of each configured network."
    INDEX { h3cOspfProcessId, h3cOspfAreaId, h3cOspfNetworkIpAddr }
    ::= { h3cOspfNetworkTable 1 }

H3cOspfNetworkEntry ::=
    SEQUENCE {
        h3cOspfProcessId
            Integer32,
        h3cOspfAreaId
            IpAddress,
        h3cOspfNetworkIpAddr
            IpAddress,
        h3cOspfNetworkIpMask
            IpAddress
     }

h3cOspfProcessId OBJECT-TYPE
    SYNTAX Integer32 (1..65535)
    MAX-ACCESS not-accessible
    STATUS current
    DESCRIPTION
        "The process ID field indicates the OSPF process number."
    ::= { h3cOspfNetworkEntry 1 }

h3cOspfAreaId OBJECT-TYPE
    SYNTAX IpAddress
    MAX-ACCESS not-accessible
    STATUS current
    DESCRIPTION
        "A 32-bit integer uniquely identifying an area.
        Area ID 0.0.0.0 is used for the OSPF backbone."
    ::= { h3cOspfNetworkEntry 2 }

h3cOspfNetworkIpAddr OBJECT-TYPE
    SYNTAX IpAddress
    MAX-ACCESS not-accessible
    STATUS current
    DESCRIPTION
        "This field is the address of the network."
    ::= { h3cOspfNetworkEntry 3 }

h3cOspfNetworkIpMask OBJECT-TYPE
    SYNTAX IpAddress
    MAX-ACCESS read-only
    STATUS current
    DESCRIPTION
        "This field is the wildcard mask of the network."
    ::= { h3cOspfNetworkEntry 4 }

END

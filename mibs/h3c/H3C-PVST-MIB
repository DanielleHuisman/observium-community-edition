-- ===================================================================
-- Copyright (c) 2004-2014 Hangzhou H3C Tech. Co., Ltd. All rights reserved.
--
-- Description: Per-VLAN spanning tree (PVST) MIB
-- Reference:
-- Version: V1.0
-- History:
-- V1.0 2014-05-27 Created by wangmingjun.
-- ===================================================================
-- ===================================================================
--
-- Imported variables and types
--
-- ===================================================================

H3C-PVST-MIB DEFINITIONS ::= BEGIN

IMPORTS
    MODULE-IDENTITY, OBJECT-TYPE, Integer32, NOTIFICATION-TYPE
        FROM SNMPv2-SMI
    h3cCommon
        FROM HUAWEI-3COM-OID-MIB;

h3cPvst MODULE-IDENTITY
    LAST-UPDATED "201405270000Z"
    ORGANIZATION
        "Hangzhou H3C Tech. Co., Ltd."
    CONTACT-INFO
        "Platform Team Hangzhou H3C Tech. Co., Ltd.
         Hai-Dian District Beijing P.R. China
         http://www.h3c.com
         Zip:100085"
    DESCRIPTION
        "This MIB defines objects for managing Per-VLAN spanning tree (PVST)."
    REVISION "201405270000Z"
    DESCRIPTION
        "The initial version of this MIB file."
    ::= { h3cCommon  131 }

-- =========================
-- Subtrees in the PVST MIB
-- =========================

h3cPvstObjects
    OBJECT IDENTIFIER ::= { h3cPvst 1 }

h3cPvstNotifications
    OBJECT IDENTIFIER ::= { h3cPvst 2 }

--  ==================================================================
--  PVST objects table
--  ==================================================================

--  ===============================
--  PVST VLAN table
--  ===============================

h3cPvstVlanConfigTable OBJECT-TYPE
    SYNTAX SEQUENCE OF H3cPvstVlanConfigEntry
    MAX-ACCESS  not-accessible
    STATUS      current
    DESCRIPTION
        "PVST VLAN configuration table."
    ::= { h3cPvstObjects 1 }

h3cPvstVlanConfigEntry OBJECT-TYPE
    SYNTAX      H3cPvstVlanConfigEntry
    MAX-ACCESS  not-accessible
    STATUS      current
    DESCRIPTION
        "PVST VLAN configuration table entry."
    INDEX {
              h3cPvstVlanID
          }
    ::= { h3cPvstVlanConfigTable 1 }

H3cPvstVlanConfigEntry ::=
    SEQUENCE
    {
        h3cPvstVlanID      Integer32
    }

h3cPvstVlanID OBJECT-TYPE
    SYNTAX      Integer32(1..4094)
    MAX-ACCESS  read-only
    STATUS      current
    DESCRIPTION
        "The index of the VLAN configuration table."
    ::= { h3cPvstVlanConfigEntry 1 }

--  ===============================
--  PVST VLAN port table
--  ===============================

h3cPvstVlanPortConfigTable OBJECT-TYPE
    SYNTAX SEQUENCE OF H3cPvstVlanPortConfigEntry
    MAX-ACCESS  not-accessible
    STATUS      current
    DESCRIPTION
        "PVST VLAN port configuration table."
        ::= { h3cPvstObjects 2 }

h3cPvstVlanPortConfigEntry OBJECT-TYPE
    SYNTAX      H3cPvstVlanPortConfigEntry
    MAX-ACCESS  not-accessible
    STATUS      current
    DESCRIPTION
        "PVST VLAN port configuration table entry."
    INDEX {
              h3cPvstPortVlanID,
              h3cPvstPortIndex
          }
    ::= { h3cPvstVlanPortConfigTable 1 }

H3cPvstVlanPortConfigEntry ::=
    SEQUENCE
    {
        h3cPvstPortVlanID     Integer32,
        h3cPvstPortIndex      Integer32
    }

h3cPvstPortVlanID       OBJECT-TYPE
    SYNTAX      Integer32(1..4094)
    MAX-ACCESS  read-only
    STATUS      current
    DESCRIPTION
        "The index of the VLAN."
    ::={ h3cPvstVlanPortConfigEntry 1 }

h3cPvstPortIndex OBJECT-TYPE
    SYNTAX      Integer32(1..2147483647)
    MAX-ACCESS  read-only
    STATUS      current
    DESCRIPTION
        "The index of the bridge port."
    ::={ h3cPvstVlanPortConfigEntry 2 }

--  ==================================================================
--  PVST notification table
--  ==================================================================

h3cPvstEvents
    OBJECT IDENTIFIER ::= { h3cPvstNotifications 0 }

h3cPvstVlanPortDetectedTc NOTIFICATION-TYPE
    OBJECTS  { h3cPvstPortVlanID , h3cPvstPortIndex }
    STATUS   current
    DESCRIPTION
        "The SNMP trap is generated when a port detects
         a topology change in a VLAN."
    ::= { h3cPvstEvents 1 }

h3cPvstVlanPortRcvdTc NOTIFICATION-TYPE
    OBJECTS  { h3cPvstPortVlanID , h3cPvstPortIndex }
    STATUS   current
    DESCRIPTION
        "The SNMP trap is generated when a port receives
         a topology change in a VLAN."
    ::= { h3cPvstEvents 2 }

END

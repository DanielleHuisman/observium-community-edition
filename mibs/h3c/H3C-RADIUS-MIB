-- =================================================================
-- Copyright (c) 2004-2016 Hangzhou H3C Tech. Co., Ltd.  All rights reserved.
--
-- Description:
--
-- A configuration management and statistical MIB, includes configuration of
-- RADIUS Server, and statistics about accounting server which complements
-- the IETF standard MIB as described in RFC2620.  In addition, there are four
-- traps supported to notify client the RADIUS Server's down and up state.
--
-- Reference: RFC2866, RADIUS-AUTH-CLIENT-MIB, RADIUS-ACC-CLIENT-MIB
-- Version: V2.5
-- History:
--  V1.0 Initial version 2004-07-13
--  V1.1 2004-10-12 updated by gaolong
--       Set size of DisplayString from 0 to 255.
--  V1.2 2005-03-10 updated by xulei
--       Modified description of this MIB
--       Modified MAX-ACCESS of nodes in h3cRdInfoTable
--       Modified description of nodes in h3cRdInfoTable
--       Added nodes of h3cRdInfoTable
--       Added h3cRdAccInfoTable
--       Added h3cRadiusAccServerTable
--       Added Traps
--  V1.3 2005-05-08 updated by xulei
--       Modified MAX-ACCESS of h3cRdPrimAccState and h3cRdSecAccState
--  V1.4 2005-06-03 updated by xulei
--       Modified SYNTAX and DESCRIPTION of h3cRdAccPacketUnit
--  V1.5 2008-05-19 updated by yangxu
--       Added nodes of h3cRdAccInfoTable
--       Added node of h3cRdAcctOnEnable
--       Added node of h3cRdAcctOnSendTimes
--       Added node of h3cRdAcctOnSendInterval
--  V1.6 2008-07-18 updated by d04528
--       Added nodes of h3cRadiusAuthenticating
--       Added node of h3cRadiusAuthClient
--       Added node of h3cRadiusAuthServerTable
--       Added node of h3cRadiusAuthServerEntry
--       Added node of h3cRadiusAuthFailureTimes
--       Added node of h3cRadiusAuthTimeoutTimes
--       Added node of h3cRadiusAuthRejectTimes
--  V1.7 2009-04-30 update by h02978
--       Added node of h3cRdSecKey
--       Added node of h3cRdSecAccKey
--       Added node of h3cRadiusAuthServerUpTrap
--       Added node of h3cRadiusAccServerUpTrap
--  V1.8 2009-08-05 update by h02978
--       Added node of h3cRadiusAuthErrThreshold
--       Added node of h3cRadiusAuthErrTrap
--  V1.9 2010-03-29 Modifyed by x04730
--       Modify SYNTAX of h3cRdAccRealTime
--       2010-07-14 Modifyed by x04730
--       Modify SYNTAX of h3cRdQuietTime
--       Modify SYNTAX of h3cRdAccQuietTime
--       2010-08-26 update by y06401
--       Added h3cRadiusSchAuthTable
--       Added h3cRadiusSchAccTable
--  V2.0 2010-03-29 Modifyed by y07111
--       Added nodes of h3cRadiusStatistic
--       Added node of h3cRadiusStatAccReq
--       Added node of h3cRadiusStatAccAck
--       Added node of h3cRadiusStatLogoutReq
--       Added node of h3cRadiusStatLogoutAck
--  V2.1 2011-11-28, Added by xuyonggang
--       Added node of h3cRadiusServerTrapVarObjects
--       2012-02-28 Modifyed by y002965
--       Added table of h3cRdSecondaryAuthServerTable
--       Added table of h3cRdSecondaryAcctServerTable
--       Added node of h3cRdPrimVpnName
--       Added node of h3cRdSecVpnName
--       Added node of h3cRdAuthNasIpAddrType
--       Added node of h3cRdAuthNasIpAddr
--       Added node of h3cRdPrimAccVpnName
--       Added node of h3cRdSecAccVpnName
--       Added node of h3cRdAccNasIpAddrType
--       Added node of h3cRdAccNasIpAddr
--       Change the length of h3cRdSecAccKey
--       Change the length of h3cRdAccKey
--       Change the length of h3cRdSecKey
--       Change the length of h3cRdKey
--  V2.2 2012-10-11, Added by liubo
--       Added node of h3cRdAuthNasIpv6Addr
--       Added node of h3cRdAccNasIpv6Addr
--       Modified the length of h3cRdSecAccKey
--       Modified the length of h3cRdAccKey
--       Modified the length of h3cRdSecKey
--       Modified the length of h3cRdKey
--       Modified the length of h3cRdPrimVpnName
--       Modified the length of h3cRdSecVpnName
--       Modified the length of h3cRdPrimAccVpnName
--       Modified the length of h3cRdSecAccVpnName
--       Modified the length of h3cRdSecondaryAuthVpnName
--       Modified the length of h3cRdSecondaryAccVpnName
--       Modified the length of h3cRdSecondaryAuthKey
--       Modified the length of h3cRdSecondaryAccKey
--       Modified the default value and description of h3cRdAcctOnSendTimes
--  V2.3 2013-03-30, Modified by luyu
--       Modified description of h3cRdSecondaryAccUdpPort
--       Modified the default value and description of h3cRadiusSchAccPrimUdpPort
--       Modified the default value and description of h3cRadiusSchAccSecUdpPort
--  V2.4 2014-06-07, Modified by liubo
--       Modified description of h3cRdSecondaryAuthRowStatus
--       Modified description of h3cRdSecondaryAccRowStatus
--  V2.5 2016-11-03, Modified by yemingxia
--       Modified the value range of h3cRdAccRealTime
--       Added node of h3cRdAccRealTimeUnit
-- =================================================================
H3C-RADIUS-MIB DEFINITIONS ::= BEGIN
    IMPORTS
        h3cCommon
            FROM HUAWEI-3COM-OID-MIB
        IpAddress, Integer32, Counter32, OBJECT-TYPE, MODULE-IDENTITY, NOTIFICATION-TYPE,
        Unsigned32,Counter64, TimeTicks
            FROM SNMPv2-SMI
        RowStatus, TruthValue, DisplayString
            FROM SNMPv2-TC
        InetAddressType, InetAddress
            FROM INET-ADDRESS-MIB
        Ipv6Address
            FROM IPV6-TC
        radiusAuthServerIndex, radiusAuthServerAddress, radiusAuthClientServerPortNumber
            FROM RADIUS-AUTH-CLIENT-MIB
        radiusAccServerIndex, radiusAccServerAddress, radiusAccClientServerPortNumber
            FROM RADIUS-ACC-CLIENT-MIB;

    h3cRadius MODULE-IDENTITY
    LAST-UPDATED "201611031800Z"            -- June 7, 2014 at 18:00 GMT
    ORGANIZATION
        "Hangzhou H3C Technologies Co., Ltd."
    CONTACT-INFO
        "Platform Team Hangzhou H3C Technologies Co., Ltd.
        Hai-Dian District Beijing P.R. China
        http://www.h3c.com
        Zip:100085
        "
    DESCRIPTION
        "The H3C-RADIUS-MIB contains objects to
        Manage configuration and Monitor running state
        for RADIUS feature."
    REVISION "201611031800Z"        -- November 3, 2016 at 18:00 GMT
    DESCRIPTION
        "Modified the value range of h3cRdAccRealTime.
        Added node of h3cRdAccRealTimeUnit"
    REVISION "201406071800Z"        -- June 7, 2014 at 18:00 GMT
    DESCRIPTION
        "Modified description of h3cRdSecondaryAuthRowStatus.
        Modified description of h3cRdSecondaryAccRowStatus"
    ::= { h3cCommon 13 }

    h3cRdObjects OBJECT IDENTIFIER ::= { h3cRadius 1 }

    h3cRdInfoTable  OBJECT-TYPE
        SYNTAX SEQUENCE OF H3cRdInfoEntry
        MAX-ACCESS not-accessible
        STATUS current
        DESCRIPTION
        "The (conceptual) table listing RADIUS authentication servers."
    ::= { h3cRdObjects 1 }

    h3cRdInfoEntry OBJECT-TYPE
        SYNTAX H3cRdInfoEntry
        MAX-ACCESS not-accessible
        STATUS current
        DESCRIPTION
        "An entry (conceptual row) representing a RADIUS authentication server."
        INDEX { h3cRdGroupName }
    ::= { h3cRdInfoTable 1 }

    H3cRdInfoEntry ::= SEQUENCE {
        h3cRdGroupName          DisplayString,
        h3cRdPrimAuthIp         IpAddress,
        h3cRdPrimUdpPort        Integer32,
        h3cRdPrimState          INTEGER,
        h3cRdSecAuthIp          IpAddress,
        h3cRdSecUdpPort         Integer32,
        h3cRdSecState           INTEGER,
        h3cRdKey                DisplayString,
        h3cRdRetry              Integer32,
        h3cRdTimeout            Integer32,
        h3cRdPrimAuthIpAddrType InetAddressType,
        h3cRdPrimAuthIpAddr     InetAddress,
        h3cRdSecAuthIpAddrType  InetAddressType,
        h3cRdSecAuthIpAddr      InetAddress,
        h3cRdServerType         INTEGER,
        h3cRdQuietTime          Integer32,
        h3cRdUserNameFormat     INTEGER,
        h3cRdRowStatus          RowStatus,
        h3cRdSecKey             DisplayString,
        h3cRdPrimVpnName        DisplayString,
        h3cRdSecVpnName         DisplayString,
        h3cRdAuthNasIpAddrType  InetAddressType,
        h3cRdAuthNasIpAddr      IpAddress,
        h3cRdAuthNasIpv6Addr    Ipv6Address
        }

    h3cRdGroupName OBJECT-TYPE
        SYNTAX DisplayString(SIZE (1..32))
        MAX-ACCESS not-accessible
        STATUS current
        DESCRIPTION
        "The name of the RADIUS authentication group referred to in this table
        entry."
    ::= { h3cRdInfoEntry 1 }


    h3cRdPrimAuthIp OBJECT-TYPE
        SYNTAX IpAddress
        MAX-ACCESS read-create
        STATUS deprecated
        DESCRIPTION
        "The IP address of primary RADIUS authentication server."
    ::= { h3cRdInfoEntry 2 }

    h3cRdPrimUdpPort OBJECT-TYPE
        SYNTAX Integer32
        MAX-ACCESS read-create
        STATUS current
        DESCRIPTION
        "The UDP port the client is using to send requests to
        primary RADIUS authentication server.  Default value is 1812."
    ::= { h3cRdInfoEntry 3 }

    h3cRdPrimState OBJECT-TYPE
        SYNTAX INTEGER
        {
            active(1),
            block(2)
        }
        MAX-ACCESS read-create
        STATUS current
        DESCRIPTION
        "The state of the primary RADIUS authentication server.
        1 (active) The primary authentication server is in active state.
        2 (block)  The primary authentication server is in block state."
    ::= { h3cRdInfoEntry 4 }

    h3cRdSecAuthIp OBJECT-TYPE
        SYNTAX IpAddress
        MAX-ACCESS read-create
        STATUS deprecated
        DESCRIPTION
        "The IP address of secondary RADIUS authentication server."
    ::= { h3cRdInfoEntry 5 }

    h3cRdSecUdpPort OBJECT-TYPE
        SYNTAX Integer32
        MAX-ACCESS read-create
        STATUS current
        DESCRIPTION
        "The UDP port the client is using to send requests to
        secondary RADIUS authentication server.  Default value is 1812."
    ::= { h3cRdInfoEntry 6 }

    h3cRdSecState OBJECT-TYPE
        SYNTAX INTEGER
        {
            active(1),
            block(2)
        }
        MAX-ACCESS read-create
        STATUS current
        DESCRIPTION
        "The state of the secondary RADIUS authentication server.
        1 (active) The secondary authentication server is in active state.
        2 (block)  The secondary authentication server is in block state."
    ::= { h3cRdInfoEntry 7 }

    h3cRdKey OBJECT-TYPE
        SYNTAX DisplayString(SIZE (0..64))
        MAX-ACCESS read-create
        STATUS current
        DESCRIPTION
        "The secret shared between the RADIUS client and RADIUS
        authentication server used in encoding and decoding
        sensitive data.
        When read, h3cRdKey always returns an Octet String of length zero."
    ::= { h3cRdInfoEntry 8 }

    h3cRdRetry OBJECT-TYPE
        SYNTAX Integer32
        MAX-ACCESS read-create
        STATUS current
        DESCRIPTION
        "The number of attempts the client will make when trying to send
        requests to a server before it will consider the attempt failed.
        Default value is 3."
    ::= { h3cRdInfoEntry 9 }

    h3cRdTimeout OBJECT-TYPE
        SYNTAX Integer32
        MAX-ACCESS read-create
        STATUS current
        DESCRIPTION
        "The timeout value the client will use when sending requests to a server.
        The unit is second.  Default value is 3."
    ::= { h3cRdInfoEntry 10 }

    h3cRdPrimAuthIpAddrType OBJECT-TYPE
        SYNTAX InetAddressType
        MAX-ACCESS read-create
        STATUS current
        DESCRIPTION
        "The IP addresses type (IPv4 or IPv6) of primary RADIUS authentication
        server."
    ::= { h3cRdInfoEntry 11 }

    h3cRdPrimAuthIpAddr OBJECT-TYPE
        SYNTAX InetAddress
        MAX-ACCESS read-create
        STATUS current
        DESCRIPTION
        "The IP address of primary RADIUS authentication server."
    ::= { h3cRdInfoEntry 12 }

    h3cRdSecAuthIpAddrType OBJECT-TYPE
        SYNTAX InetAddressType
        MAX-ACCESS read-create
        STATUS current
        DESCRIPTION
        "The IP addresses type (IPv4 or IPv6) of secondary RADIUS authentication
        server."
    ::= { h3cRdInfoEntry 13 }

    h3cRdSecAuthIpAddr OBJECT-TYPE
        SYNTAX InetAddress
        MAX-ACCESS read-create
        STATUS current
        DESCRIPTION
        "The IP address of secondary RADIUS authentication server."
    ::= { h3cRdInfoEntry 14 }

    h3cRdServerType OBJECT-TYPE
        SYNTAX INTEGER
        {
            standard(1),
            iphotel(2),
            portal(3),
            extended(4)
        }
        MAX-ACCESS read-create
        STATUS current
        DESCRIPTION
        "Specify the type of RADIUS server.
        1 (standard) - Server based on RFC protocol(s).
        2 (iphotel) - Server for IP-Hotel or 201+ system.
        3 (portal) - Server for iTellin Portal system.
        4 (extended) - Server based on RADIUS extensions.
        Default type is standard."
    ::= { h3cRdInfoEntry 15 }

    h3cRdQuietTime OBJECT-TYPE
        SYNTAX Integer32 (0..255)
        MAX-ACCESS read-create
        STATUS current
        DESCRIPTION
        "The time for server returning active.  The unit is minute.
         When the value is 0, the server state retains active.  Default value is 5."
    ::= { h3cRdInfoEntry 16 }

    h3cRdUserNameFormat OBJECT-TYPE
        SYNTAX INTEGER
        {
            withoutdomain(1),
            withdomain(2),
            keeporignal(3)
        }
        MAX-ACCESS read-create
        STATUS current
        DESCRIPTION
        "Specify the user-name format that is sent to RADIUS server.
        1 (withoutdomain) - send the user-name without domain.
        2 (withdomain) - send the user-name with domain.
        3 (keeporignal) - send the user-name as it is entered.
        Default format is withdomain."
    ::= { h3cRdInfoEntry 17 }


    h3cRdRowStatus   OBJECT-TYPE
        SYNTAX   RowStatus
        MAX-ACCESS  read-create
        STATUS   current
        DESCRIPTION
        "This object is responsible for managing the creation, deletion and
        modification of rows, which support active status and CreateAndGo,
        Destroy operation.  To create a new row, h3cRdGroupName must be specified.
        To destroy an existent row, the h3cRdGroupName MUST NOT be referred by
        h3cDomainTable in h3cDomainRadiusGroupName column."
    ::= { h3cRdInfoEntry 18 }


    h3cRdSecKey OBJECT-TYPE
        SYNTAX DisplayString(SIZE (0..64))
        MAX-ACCESS read-create
        STATUS current
        DESCRIPTION
        "The secret shared between the RADIUS client and the secondary RADIUS
        authentication server used in encoding and decoding
        sensitive data.
        When read, h3cRdSecKey always returns an Octet String of length zero."
    ::= { h3cRdInfoEntry 19 }

    h3cRdPrimVpnName OBJECT-TYPE
        SYNTAX DisplayString(SIZE (0..31))
        MAX-ACCESS  read-create
        STATUS current
        DESCRIPTION
        "The human-readable name of the VPN in which the primary RADIUS
        authentication server is placed."
    ::= { h3cRdInfoEntry 20 }

    h3cRdSecVpnName OBJECT-TYPE
        SYNTAX DisplayString(SIZE (0..31))
        MAX-ACCESS  read-create
        STATUS current
        DESCRIPTION
        "The human-readable name of the VPN in which the secondary RADIUS
        authentication server is placed."
    ::= { h3cRdInfoEntry 21 }

    h3cRdAuthNasIpAddrType OBJECT-TYPE
        SYNTAX InetAddressType
        MAX-ACCESS read-create
        STATUS current
        DESCRIPTION
        "The type (IPv4 or IPv6) of the source IP used to communicate with
        RADIUS authentication server."
    ::= { h3cRdInfoEntry 22 }

    h3cRdAuthNasIpAddr OBJECT-TYPE
        SYNTAX IpAddress
        MAX-ACCESS read-create
        STATUS current
        DESCRIPTION
        "The source IPv4 address used to communicate with the RADIUS authentication
        server."
    ::= { h3cRdInfoEntry 23 }

    h3cRdAuthNasIpv6Addr OBJECT-TYPE
        SYNTAX Ipv6Address
        MAX-ACCESS read-create
        STATUS current
        DESCRIPTION
        "The source IPv6 address used to communicate with the RADIUS authentication
        server."
    ::= { h3cRdInfoEntry 24 }

-- ***********************************************************************
--
--  Accounting Server Table
--
-- ***********************************************************************
    h3cRdAccInfoTable  OBJECT-TYPE
        SYNTAX SEQUENCE OF H3cRdAccInfoEntry
        MAX-ACCESS not-accessible
        STATUS current
        DESCRIPTION
        "The (conceptual) table listing RADIUS accounting servers."
    ::= { h3cRdObjects 2 }

    h3cRdAccInfoEntry OBJECT-TYPE
        SYNTAX H3cRdAccInfoEntry
        MAX-ACCESS not-accessible
        STATUS current
        DESCRIPTION
        "An entry (conceptual row) representing a RADIUS accounting server."
        INDEX { h3cRdAccGroupName }
    ::= { h3cRdAccInfoTable 1 }


    H3cRdAccInfoEntry ::= SEQUENCE {
        h3cRdAccGroupName           DisplayString,
        h3cRdPrimAccIpAddrType      InetAddressType,
        h3cRdPrimAccIpAddr          InetAddress,
        h3cRdPrimAccUdpPort         Integer32,
        h3cRdPrimAccState           INTEGER,
        h3cRdSecAccIpAddrType       InetAddressType,
        h3cRdSecAccIpAddr           InetAddress,
        h3cRdSecAccUdpPort          Integer32,
        h3cRdSecAccState            INTEGER,
        h3cRdAccKey                 DisplayString,
        h3cRdAccRetry               Integer32,
        h3cRdAccTimeout             Integer32,
        h3cRdAccServerType          INTEGER,
        h3cRdAccQuietTime           Integer32,
        h3cRdAccFailureAction       INTEGER,
        h3cRdAccRealTime            Integer32,
        h3cRdAccRealTimeRetry       Integer32,
        h3cRdAccSaveStopPktEnable   TruthValue,
        h3cRdAccStopRetry           Integer32,
        h3cRdAccDataFlowUnit        INTEGER,
        h3cRdAccPacketUnit          INTEGER,
        h3cRdAccRowStatus           RowStatus,
        h3cRdAcctOnEnable           TruthValue,
        h3cRdAcctOnSendTimes        Integer32,
        h3cRdAcctOnSendInterval     Integer32,
        h3cRdSecAccKey              DisplayString,
        h3cRdPrimAccVpnName         DisplayString,
        h3cRdSecAccVpnName          DisplayString,
        h3cRdAccNasIpAddrType       InetAddressType,
        h3cRdAccNasIpAddr           IpAddress,
        h3cRdAccNasIpv6Addr         Ipv6Address,
        h3cRdAccRealTimeUnit        INTEGER
        }

    h3cRdAccGroupName OBJECT-TYPE
        SYNTAX DisplayString(SIZE (1..32))
        MAX-ACCESS not-accessible
        STATUS current
        DESCRIPTION
        "The name of the RADIUS group referred to in this table entry."
    ::= { h3cRdAccInfoEntry 1 }

    h3cRdPrimAccIpAddrType OBJECT-TYPE
        SYNTAX      InetAddressType
        MAX-ACCESS  read-create
        STATUS      current
        DESCRIPTION
        "The IP addresses type (IPv4 or IPv6) of primary RADIUS accounting server."
    ::= { h3cRdAccInfoEntry 2 }

    h3cRdPrimAccIpAddr OBJECT-TYPE
        SYNTAX      InetAddress
        MAX-ACCESS  read-create
        STATUS      current
        DESCRIPTION
        "The IP address of primary RADIUS accounting server."
    ::= { h3cRdAccInfoEntry 3 }

    h3cRdPrimAccUdpPort OBJECT-TYPE
        SYNTAX      Integer32
        MAX-ACCESS  read-create
        STATUS      current
        DESCRIPTION
        "The UDP port the client is using to send requests to primary
        RADIUS accounting server.  Default value is 1813."
    ::= { h3cRdAccInfoEntry 4 }

    h3cRdPrimAccState OBJECT-TYPE
        SYNTAX INTEGER
        {
            active(1),
            block(2)
        }
        MAX-ACCESS  read-create
        STATUS      current
        DESCRIPTION
        "The state of the primary RADIUS accounting server.
        1 (active) The primary accounting server is in active state.
        2 (block)  The primary accounting server is in block state."
    ::= { h3cRdAccInfoEntry 5 }

    h3cRdSecAccIpAddrType OBJECT-TYPE
        SYNTAX      InetAddressType
        MAX-ACCESS  read-create
        STATUS      current
        DESCRIPTION
        "The IP addresses type (IPv4 or IPv6) of secondary RADIUS accounting
        server."
    ::= { h3cRdAccInfoEntry 6 }

    h3cRdSecAccIpAddr OBJECT-TYPE
        SYNTAX      InetAddress
        MAX-ACCESS  read-create
        STATUS      current
        DESCRIPTION
        "The IP address of secondary RADIUS accounting server."
    ::= { h3cRdAccInfoEntry 7 }

    h3cRdSecAccUdpPort OBJECT-TYPE
        SYNTAX      Integer32
        MAX-ACCESS  read-create
        STATUS      current
        DESCRIPTION
        "The UDP port the client is using to send requests to secondary
        RADIUS accounting server.  Default value is 1813."
    ::= { h3cRdAccInfoEntry 8 }

    h3cRdSecAccState OBJECT-TYPE
        SYNTAX INTEGER
        {
            active(1),
            block(2)
        }
        MAX-ACCESS  read-create
        STATUS      current
        DESCRIPTION
        "The state of the secondary RADIUS accounting server.
        1 (active) The secondary accounting server is in active state.
        2 (block)  The secondary accounting server is in block state."
    ::= { h3cRdAccInfoEntry 9 }

    h3cRdAccKey OBJECT-TYPE
        SYNTAX DisplayString(SIZE (0..64))
        MAX-ACCESS read-create
        STATUS current
        DESCRIPTION
        "The secret shared between the RADIUS client and RADIUS
        accounting server used in encoding and decoding sensitive data.
        When read, h3cRdAccKey always returns an Octet String of length zero."
    ::= { h3cRdAccInfoEntry 10 }


    h3cRdAccRetry OBJECT-TYPE
        SYNTAX Integer32
        MAX-ACCESS read-create
        STATUS current
        DESCRIPTION
        "The number of attempt the client will make when trying to send
        requests to a server before it will consider the attempt failed.
        Default value is 3."
    ::= { h3cRdAccInfoEntry 11 }

    h3cRdAccTimeout OBJECT-TYPE
        SYNTAX Integer32
        MAX-ACCESS read-create
        STATUS current
        DESCRIPTION
        "The timeout value the client will use when sending requests to a server.
        The unit is second.  Default value is 3."
    ::= { h3cRdAccInfoEntry 12 }

    h3cRdAccServerType OBJECT-TYPE
        SYNTAX INTEGER
        {
            standard(1),
            iphotel(2),
            portal(3),
            extended(4)
        }
        MAX-ACCESS read-create
        STATUS current
        DESCRIPTION
        "Specify the type of RADIUS server.
        1 (standard) - Server based on RFC protocol(s).
        2 (iphotel) - Server for IP-Hotel or 201+ system.
        3 (portal) - Server for iTellin Portal system.
        4 (extended) - Server based on RADIUS extensions.
        Default type is standard."
    ::= { h3cRdAccInfoEntry 13 }

    h3cRdAccQuietTime OBJECT-TYPE
        SYNTAX Integer32 (0..255)
        MAX-ACCESS read-create
        STATUS current
        DESCRIPTION
        "The time for server returning active.  The unit is minute.
         When the value is 0, the server state retains active.  Default value is 5."
    ::= { h3cRdAccInfoEntry 14 }

    h3cRdAccFailureAction OBJECT-TYPE
        SYNTAX INTEGER
        {
            ignore(1),
            reject(2)
        }
        MAX-ACCESS read-create
        STATUS current
        DESCRIPTION
        "Defines the action that authentication should take if
        authentication succeeds but the associated accounting start
        fails.
        1 (ignore) - treat as authentication success; ignore
            accounting start failure.
        2 (reject) - treat as authentication failed if
            corresponding accounting start fails.
        Default value is 1(reject)."
    ::= { h3cRdAccInfoEntry 15 }

    h3cRdAccRealTime OBJECT-TYPE
        SYNTAX Integer32 (0..71582)
        MAX-ACCESS read-create
        STATUS current
        DESCRIPTION
        "Interval of realtime-accounting packets.
        The unit is defined by h3cRdAccRealTimeUnit.
        When the value is 0, the device doesn't send realtime-accounting
        packets.  Default value is 12 minutes."
    ::= { h3cRdAccInfoEntry 16 }

    h3cRdAccRealTimeRetry OBJECT-TYPE
        SYNTAX Integer32 (1..255)
        MAX-ACCESS read-create
        STATUS current
        DESCRIPTION
        "The number of attempt the client will make when trying to send
        realtime-accounting packet to accounting server before it will
        consider the attempt failed.  Default value is 5."
        DEFVAL { 5 }
    ::= { h3cRdAccInfoEntry 17 }

    h3cRdAccSaveStopPktEnable OBJECT-TYPE
        SYNTAX TruthValue
        MAX-ACCESS read-create
        STATUS current
        DESCRIPTION
        "The control of whether save stop-accounting packet in local buffer
        and resend later when the accounting server doesn't respond.  When
        SaveStopPktEnable is set to false, the value of AccStopRetry will be
        ignored.  Default value is true."
    ::= { h3cRdAccInfoEntry 18 }

    h3cRdAccStopRetry OBJECT-TYPE
        SYNTAX Integer32 (10..65535)
        MAX-ACCESS read-create
        STATUS current
        DESCRIPTION
        "The number of attempt the client will make when trying to send
        stop-accounting packet to accounting server.  Default value is 500."
    ::= { h3cRdAccInfoEntry 19 }

    h3cRdAccDataFlowUnit OBJECT-TYPE
        SYNTAX INTEGER
        {
            byte(1),
            kiloByte(2),
            megaByte(3),
            gigaByte(4)
        }
        MAX-ACCESS read-create
        STATUS current
        DESCRIPTION
        "Specify data flow format that is sent to RADIUS server.  The value
        SHOULD be set the same as the value of corresponding server.
        1 (byte) -  Specify 'byte' as the unit of data flow.
        2 (kiloByte) - Specify 'kilo-byte' as the unit of data flow.
        3 (megaByte) - Specify 'mega-byte' as the unit of data flow.
        4 (gigaByte) - Specify 'giga-byte' as the unit of data flow.
        Default value is 1."
    ::= { h3cRdAccInfoEntry 20 }

    h3cRdAccPacketUnit OBJECT-TYPE
        SYNTAX INTEGER
        {
            onePacket(1),
            kiloPacket(2),
            megaPacket(3),
            gigaPacket(4)
        }
        MAX-ACCESS read-create
        STATUS current
        DESCRIPTION
        "Specify packet format that is sent to RADIUS server.  The value
        SHOULD be set the same as the value of corresponding server.
        1 (onePacket)  - Specify 'one-packet' as the unit of packet.
        2 (kiloPacket) - Specify 'kilo-packet' as the unit of packet.
        3 (megaPacket) - Specify 'mega-packet' as the unit of packet.
        4 (gigaPacket) - Specify 'giga-packet' as the unit of packet.
        Default value is 1."
    ::= { h3cRdAccInfoEntry 21 }

    h3cRdAccRowStatus   OBJECT-TYPE
        SYNTAX   RowStatus
        MAX-ACCESS  read-create
        STATUS   current
        DESCRIPTION
        "This object is responsible for managing the creation, deletion and
        modification of rows, which support active status and CreateAndGo,
        Destroy operation.  To create a new row, h3cRdAccGroupName must be specified.
        To destroy an existent row, the h3cRdAccGroupName MUST NOT be referred by
        h3cDomainTable in h3cDomainRadiusGroupName column."
    ::= { h3cRdAccInfoEntry 22 }

    h3cRdAcctOnEnable OBJECT-TYPE
        SYNTAX TruthValue
        MAX-ACCESS read-create
        STATUS current
        DESCRIPTION
        "The control of Accounting-On function.  The Accounting-On function is
        used by the client to mark the start of accounting (for example, upon
        booting) by sending Accounting-On packets and to mark the end of
        accounting (for example, just before a scheduled reboot) by sending
        Accounting-Off packets.  Default value is false."
    ::= { h3cRdAccInfoEntry 23 }

    h3cRdAcctOnSendTimes OBJECT-TYPE
        SYNTAX Integer32
        MAX-ACCESS read-create
        STATUS current
        DESCRIPTION
        "The number of Accounting-On packets the client will send before it
        considers the accounting server failed.  Default value is 50."
        DEFVAL { 50 }
    ::= { h3cRdAccInfoEntry 24 }

    h3cRdAcctOnSendInterval OBJECT-TYPE
        SYNTAX Integer32
        MAX-ACCESS read-create
        STATUS current
        DESCRIPTION
        "Interval of Accounting-On packets.  The unit is second.
        Default value is 3."
        DEFVAL { 3 }
    ::= { h3cRdAccInfoEntry 25 }


    h3cRdSecAccKey OBJECT-TYPE
        SYNTAX DisplayString(SIZE (0..64))
        MAX-ACCESS read-create
        STATUS current
        DESCRIPTION
        "The secret shared between the RADIUS client and the secondary RADIUS
        accounting server used in encoding and decoding sensitive data.
        When read, h3cRdSecAccKey always returns an Octet String of length zero."
    ::= { h3cRdAccInfoEntry 26 }

    h3cRdPrimAccVpnName OBJECT-TYPE
        SYNTAX DisplayString(SIZE (0..31))
        MAX-ACCESS  read-create
        STATUS current
        DESCRIPTION
        "The human-readable name of the VPN in which the primary RADIUS
        accounting server is placed."
    ::= { h3cRdAccInfoEntry 27 }

    h3cRdSecAccVpnName OBJECT-TYPE
        SYNTAX DisplayString(SIZE (0..31))
        MAX-ACCESS  read-create
        STATUS current
        DESCRIPTION
        "The human-readable name of the VPN in which the secondary RADIUS
        accounting server is placed."
    ::= { h3cRdAccInfoEntry 28 }

    h3cRdAccNasIpAddrType OBJECT-TYPE
        SYNTAX InetAddressType
        MAX-ACCESS read-create
        STATUS current
        DESCRIPTION
        "The type (IPv4 or IPv6) of the source IP used to communicate with
        RADIUS accounting server."
    ::= { h3cRdAccInfoEntry 29 }

    h3cRdAccNasIpAddr OBJECT-TYPE
        SYNTAX IpAddress
        MAX-ACCESS read-create
        STATUS current
        DESCRIPTION
        "The source IPv4 address used to communicate with the RADIUS accounting
        server."
    ::= { h3cRdAccInfoEntry 30 }

    h3cRdAccNasIpv6Addr OBJECT-TYPE
        SYNTAX Ipv6Address
        MAX-ACCESS read-create
        STATUS current
        DESCRIPTION
        "The source IPv6 address used to communicate with the RADIUS accounting
        server."
    ::= { h3cRdAccInfoEntry 31 }

    h3cRdAccRealTimeUnit OBJECT-TYPE
        SYNTAX INTEGER
        {
            minute(0),
            second(1)
        }
        MAX-ACCESS read-create
        STATUS current
        DESCRIPTION
        "The interval unit of realtime-accounting packets.
        0  - minute.
        1  - second."
        DEFVAL { minute }
    ::= { h3cRdAccInfoEntry 32 }

-- ***********************************************************************
--
--  Global configurations
--
-- ***********************************************************************
    h3cRadiusGlobalConfig OBJECT IDENTIFIER ::= { h3cRdObjects 3 }

    h3cRadiusAuthErrThreshold OBJECT-TYPE
        SYNTAX Unsigned32 (1..100)
        UNITS "percentage"
        MAX-ACCESS read-write
        STATUS current
        DESCRIPTION
            "The threshold of authentication failure trap.  A trap will be sent
            when the percent of the unsuccessful authentication exceeds this threshold."
        DEFVAL { 30 }
        ::= { h3cRadiusGlobalConfig 1 }


-- ***********************************************************************
--
--  Secondary Authentication Server Table
--
-- ***********************************************************************
    h3cRdSecondaryAuthServerTable  OBJECT-TYPE
        SYNTAX SEQUENCE OF H3cRdSecondaryAuthServerEntry
        MAX-ACCESS not-accessible
        STATUS current
        DESCRIPTION
        "The (conceptual) table listing RADIUS secondary authentication servers."
    ::= { h3cRdObjects 4 }

    h3cRdSecondaryAuthServerEntry OBJECT-TYPE
        SYNTAX H3cRdSecondaryAuthServerEntry
        MAX-ACCESS not-accessible
        STATUS current
        DESCRIPTION
        "An entry (conceptual row) representing a RADIUS secondary authentication server."
        INDEX { h3cRdGroupName, h3cRdSecondaryAuthIpAddrType, h3cRdSecondaryAuthIpAddr,
                h3cRdSecondaryAuthVpnName, h3cRdSecondaryAuthUdpPort }
    ::= { h3cRdSecondaryAuthServerTable 1 }

    H3cRdSecondaryAuthServerEntry ::= SEQUENCE {
        h3cRdSecondaryAuthIpAddrType       InetAddressType,
        h3cRdSecondaryAuthIpAddr           InetAddress,
        h3cRdSecondaryAuthVpnName          DisplayString,
        h3cRdSecondaryAuthUdpPort          Integer32,
        h3cRdSecondaryAuthState            INTEGER,
        h3cRdSecondaryAuthKey              DisplayString,
        h3cRdSecondaryAuthRowStatus        RowStatus
        }

    h3cRdSecondaryAuthIpAddrType OBJECT-TYPE
        SYNTAX      InetAddressType
        MAX-ACCESS  not-accessible
        STATUS      current
        DESCRIPTION
        "The IP addresses type (IPv4 or IPv6) of secondary RADIUS authentication server."
    ::= { h3cRdSecondaryAuthServerEntry 1 }

    h3cRdSecondaryAuthIpAddr OBJECT-TYPE
        SYNTAX      InetAddress
        MAX-ACCESS  not-accessible
        STATUS      current
        DESCRIPTION
        "The IP address of secondary RADIUS authentication server."
    ::= { h3cRdSecondaryAuthServerEntry 2 }

    h3cRdSecondaryAuthVpnName OBJECT-TYPE
        SYNTAX DisplayString(SIZE (0..31))
        MAX-ACCESS  not-accessible
        STATUS current
        DESCRIPTION
        "The human-readable name of the VPN in which the secondary RADIUS
        authentication server is placed."
    ::= { h3cRdSecondaryAuthServerEntry 3 }

    h3cRdSecondaryAuthUdpPort OBJECT-TYPE
        SYNTAX      Integer32(1..65535)
        MAX-ACCESS  not-accessible
        STATUS      current
        DESCRIPTION
        "The UDP port the client is using to send requests to secondary
        RADIUS authentication server.  Default value is 1812."
    ::= { h3cRdSecondaryAuthServerEntry 4 }

    h3cRdSecondaryAuthState OBJECT-TYPE
        SYNTAX INTEGER
        {
            active(1),
            block(2)
        }
        MAX-ACCESS  read-create
        STATUS      current
        DESCRIPTION
        "The state of the secondary RADIUS authentication server.
        1 (active) The secondary authentication server is in active state.
        2 (block)  The secondary authentication server is in block state."
    ::= { h3cRdSecondaryAuthServerEntry 5 }

    h3cRdSecondaryAuthKey OBJECT-TYPE
        SYNTAX DisplayString(SIZE (0..64))
        MAX-ACCESS read-create
        STATUS current
        DESCRIPTION
        "The secret shared between the RADIUS client and the secondary RADIUS
        authentication server used in encoding and decoding sensitive data.
        When read, h3cRdSecondaryAuthKey always returns an Octet String of length zero."
    ::= { h3cRdSecondaryAuthServerEntry 6 }

    h3cRdSecondaryAuthRowStatus   OBJECT-TYPE
        SYNTAX   RowStatus
        MAX-ACCESS  read-create
        STATUS   current
        DESCRIPTION
        "This object is responsible for managing the creation, deletion and
        modification of rows, which support active status and CreateAndGo,
        Destroy operation.  To create a new row, h3cRdGroupName must be specified.
        The number of rows with the same h3cRdGroupName can't be more than 16."
    ::= { h3cRdSecondaryAuthServerEntry 7 }

-- ***********************************************************************
--
--  Secondary Accounting Server Table
--
-- ***********************************************************************
    h3cRdSecondaryAccServerTable  OBJECT-TYPE
        SYNTAX SEQUENCE OF H3cRdSecondaryAccServerEntry
        MAX-ACCESS not-accessible
        STATUS current
        DESCRIPTION
        "The (conceptual) table listing RADIUS secondary accounting servers."
    ::= { h3cRdObjects 5 }

    h3cRdSecondaryAccServerEntry OBJECT-TYPE
        SYNTAX H3cRdSecondaryAccServerEntry
        MAX-ACCESS not-accessible
        STATUS current
        DESCRIPTION
        "An entry (conceptual row) representing a RADIUS secondary accounting server."
        INDEX { h3cRdAccGroupName, h3cRdSecondaryAccIpAddrType, h3cRdSecondaryAccIpAddr,
                h3cRdSecondaryAccVpnName, h3cRdSecondaryAccUdpPort }
    ::= { h3cRdSecondaryAccServerTable 1 }

    H3cRdSecondaryAccServerEntry ::= SEQUENCE {
        h3cRdSecondaryAccIpAddrType       InetAddressType,
        h3cRdSecondaryAccIpAddr           InetAddress,
        h3cRdSecondaryAccVpnName          DisplayString,
        h3cRdSecondaryAccUdpPort          Integer32,
        h3cRdSecondaryAccState            INTEGER,
        h3cRdSecondaryAccKey              DisplayString,
        h3cRdSecondaryAccRowStatus        RowStatus
        }

    h3cRdSecondaryAccIpAddrType OBJECT-TYPE
        SYNTAX      InetAddressType
        MAX-ACCESS  not-accessible
        STATUS      current
        DESCRIPTION
        "The IP addresses type (IPv4 or IPv6) of secondary RADIUS accounting server."
    ::= { h3cRdSecondaryAccServerEntry 1 }

    h3cRdSecondaryAccIpAddr OBJECT-TYPE
        SYNTAX      InetAddress
        MAX-ACCESS  not-accessible
        STATUS      current
        DESCRIPTION
        "The IP address of secondary RADIUS accounting server."
    ::= { h3cRdSecondaryAccServerEntry 2 }

    h3cRdSecondaryAccVpnName OBJECT-TYPE
        SYNTAX DisplayString(SIZE (0..31))
        MAX-ACCESS  not-accessible
        STATUS current
        DESCRIPTION
        "The human-readable name of the VPN in which the secondary RADIUS
        accounting server is placed."
    ::= { h3cRdSecondaryAccServerEntry 3 }

    h3cRdSecondaryAccUdpPort OBJECT-TYPE
        SYNTAX      Integer32(1..65535)
        MAX-ACCESS  not-accessible
        STATUS      current
        DESCRIPTION
        "The UDP port the client is using to send requests to secondary
        RADIUS accounting server.  Default value is 1813."
    ::= { h3cRdSecondaryAccServerEntry 4 }

    h3cRdSecondaryAccState OBJECT-TYPE
        SYNTAX INTEGER
        {
            active(1),
            block(2)
        }
        MAX-ACCESS  read-create
        STATUS      current
        DESCRIPTION
        "The state of the secondary RADIUS accounting server.
        1 (active) The secondary accounting server is in active state.
        2 (block)  The secondary accounting server is in block state."
    ::= { h3cRdSecondaryAccServerEntry 5 }

    h3cRdSecondaryAccKey OBJECT-TYPE
        SYNTAX DisplayString(SIZE (0..64))
        MAX-ACCESS read-create
        STATUS current
        DESCRIPTION
        "The secret shared between the RADIUS client and the secondary RADIUS
        accounting server used in encoding and decoding sensitive data.
        When read, h3cRdSecondaryAccKey always returns an Octet String of length zero."
    ::= { h3cRdSecondaryAccServerEntry 6 }

    h3cRdSecondaryAccRowStatus   OBJECT-TYPE
        SYNTAX   RowStatus
        MAX-ACCESS  read-create
        STATUS   current
        DESCRIPTION
        "This object is responsible for managing the creation, deletion and
        modification of rows, which support active status and CreateAndGo,
        Destroy operation.  To create a new row, h3cRdAccGroupName must be specified.
        The number of rows with the same h3cRdAccGroupName can't be more than 16."
    ::= { h3cRdSecondaryAccServerEntry 7 }


-- ***********************************************************************
--
--  Supplement to RFC2620 RADIUS-ACC-CLIENT-MIB
--
-- ***********************************************************************

    h3cRadiusAccounting OBJECT IDENTIFIER ::= { h3cRadius 2 }

    h3cRadiusAccClient OBJECT IDENTIFIER ::= { h3cRadiusAccounting 1 }

    h3cRadiusAccServerTable OBJECT-TYPE
        SYNTAX  SEQUENCE OF H3cRadiusAccServerEntry
        MAX-ACCESS  not-accessible
        STATUS  current
        DESCRIPTION
        "The (conceptual) table listing the RADIUS accounting
        servers with which the client shares a secret."
    ::= { h3cRadiusAccClient 1 }

    h3cRadiusAccServerEntry OBJECT-TYPE
        SYNTAX  H3cRadiusAccServerEntry
        MAX-ACCESS  not-accessible
        STATUS  current
        DESCRIPTION
        "An entry (conceptual row) representing a RADIUS accounting
        server with which a client shares a secret."
        INDEX { radiusAccServerIndex }
    ::= { h3cRadiusAccServerTable 1 }

    H3cRadiusAccServerEntry ::= SEQUENCE {
        h3cRadiusAccClientStartRequests         Counter32,
        h3cRadiusAccClientStartResponses        Counter32,
        h3cRadiusAccClientInterimRequests       Counter32,
        h3cRadiusAccClientInterimResponses      Counter32,
        h3cRadiusAccClientStopRequests          Counter32,
        h3cRadiusAccClientStopResponses         Counter32 }

    h3cRadiusAccClientStartRequests   OBJECT-TYPE
        SYNTAX  Counter32
        MAX-ACCESS  read-only
        STATUS  current
        DESCRIPTION
        "The number of RADIUS accounting start request sent to this
        server."
    ::= { h3cRadiusAccServerEntry  1 }

    h3cRadiusAccClientStartResponses   OBJECT-TYPE
        SYNTAX  Counter32
        MAX-ACCESS  read-only
        STATUS  current
        DESCRIPTION
        "The number of RADIUS accounting start response received
        from this server."
    ::= { h3cRadiusAccServerEntry  2 }

    h3cRadiusAccClientInterimRequests   OBJECT-TYPE
        SYNTAX  Counter32
        MAX-ACCESS  read-only
        STATUS  current
        DESCRIPTION
        "The number of RADIUS interim accounting request sent to
        this server."
    ::= { h3cRadiusAccServerEntry  3 }

    h3cRadiusAccClientInterimResponses   OBJECT-TYPE
        SYNTAX  Counter32
        MAX-ACCESS  read-only
        STATUS  current
        DESCRIPTION
        "The number of RADIUS interim accounting response received
        from this server."
    ::= { h3cRadiusAccServerEntry  4 }

    h3cRadiusAccClientStopRequests   OBJECT-TYPE
        SYNTAX  Counter32
        MAX-ACCESS  read-only
        STATUS  current
        DESCRIPTION
        "The number of RADIUS stop accounting request sent to
        this RADIUS server."
    ::= { h3cRadiusAccServerEntry  5 }

    h3cRadiusAccClientStopResponses   OBJECT-TYPE
        SYNTAX  Counter32
        MAX-ACCESS  read-only
        STATUS  current
        DESCRIPTION
        "The number of RADIUS stop accounting response received
        from this server."
    ::= { h3cRadiusAccServerEntry  6 }

--------------------------------------------------------------
-- Traps
--------------------------------------------------------------

-- All trap definitions should be placed under this object.
    h3cRadiusServerTrap OBJECT IDENTIFIER ::= { h3cRadius 3 }

    h3cRadiusAuthServerDownTrap NOTIFICATION-TYPE
        OBJECTS     { radiusAuthServerAddress,
                     radiusAuthClientServerPortNumber,
                     h3cRadiusServerFirstTrapTime}
        STATUS      current
        DESCRIPTION
        "This trap is generated when the authentication RADIUS server
        doesn't respond client's requests for specified times."
    ::= { h3cRadiusServerTrap 1 }

    h3cRadiusAccServerDownTrap NOTIFICATION-TYPE
        OBJECTS     { radiusAccServerAddress,
                     radiusAccClientServerPortNumber,
                     h3cRadiusServerFirstTrapTime}
        STATUS      current
        DESCRIPTION
        "This trap is generated when the accounting RADIUS server
        doesn't respond client's requests for specified times."
    ::= { h3cRadiusServerTrap 2 }

    h3cRadiusServerTrapPrefix OBJECT IDENTIFIER ::= { h3cRadiusServerTrap 0 }

    h3cRadiusAuthServerUpTrap NOTIFICATION-TYPE
        OBJECTS     { radiusAuthServerAddress,
                     radiusAuthClientServerPortNumber,
                     h3cRadiusServerFirstTrapTime }
        STATUS      current
        DESCRIPTION
        "This trap is generated when the device finds that the state of
        RADIUS authentication server becomes reachable from unreachable."
    ::= { h3cRadiusServerTrapPrefix 1 }

    h3cRadiusAccServerUpTrap NOTIFICATION-TYPE
        OBJECTS     { radiusAccServerAddress,
                     radiusAccClientServerPortNumber,
                     h3cRadiusServerFirstTrapTime }
        STATUS      current
        DESCRIPTION
        "This trap is generated when the device finds that the state of
        RADIUS accounting server becomes reachable from unreachable."
    ::= { h3cRadiusServerTrapPrefix 2 }

    h3cRadiusAuthErrTrap NOTIFICATION-TYPE
        OBJECTS     { radiusAuthServerAddress,
                      radiusAuthClientServerPortNumber }
        STATUS      current
        DESCRIPTION
        "This trap is generated when the device finds that the percent of
        unsuccessful authentication exceeds a threshold, and the threshold
        is the value of node h3cRadiusAuthErrThreshold."
    ::= { h3cRadiusServerTrapPrefix 3 }

-- ***********************************************************************
--
--  Supplement to RFC2618 RADIUS-AUTH-CLIENT-MIB
--
-- ***********************************************************************

    h3cRadiusAuthenticating OBJECT IDENTIFIER ::= { h3cRadius 4 }

    h3cRadiusAuthClient OBJECT IDENTIFIER ::= { h3cRadiusAuthenticating 1 }

    h3cRadiusAuthServerTable OBJECT-TYPE
        SYNTAX  SEQUENCE OF H3cRadiusAuthServerEntry
        MAX-ACCESS  not-accessible
        STATUS  current
        DESCRIPTION
        "The (conceptual) table listing the RADIUS authenticating
        servers with which the client shares a secret."
    ::= { h3cRadiusAuthClient 1 }

    h3cRadiusAuthServerEntry OBJECT-TYPE
        SYNTAX  H3cRadiusAuthServerEntry
        MAX-ACCESS  not-accessible
        STATUS  current
        DESCRIPTION
        "An entry (conceptual row) representing a RADIUS authenticating
        server with which a client shares a secret."
        INDEX { radiusAuthServerIndex }
    ::= { h3cRadiusAuthServerTable 1 }

    H3cRadiusAuthServerEntry ::= SEQUENCE {
        h3cRadiusAuthFailureTimes         Counter32,
        h3cRadiusAuthTimeoutTimes        Counter32,
        h3cRadiusAuthRejectTimes       Counter32}

    h3cRadiusAuthFailureTimes   OBJECT-TYPE
        SYNTAX  Counter32
        MAX-ACCESS  read-only
        STATUS  current
        DESCRIPTION
        "The number of RADIUS authenticating failed to this server."
    ::= { h3cRadiusAuthServerEntry  1 }

    h3cRadiusAuthTimeoutTimes   OBJECT-TYPE
        SYNTAX  Counter32
        MAX-ACCESS  read-only
        STATUS  current
        DESCRIPTION
        "The number of RADIUS authenticating timeout to this server."
    ::= { h3cRadiusAuthServerEntry  2 }

    h3cRadiusAuthRejectTimes   OBJECT-TYPE
        SYNTAX  Counter32
        MAX-ACCESS  read-only
        STATUS  current
        DESCRIPTION
        "The number of RADIUS authenticating rejected to this server."
    ::= { h3cRadiusAuthServerEntry  3 }


-- ***********************************************************************
--
--  Radius Extend
--
-- ***********************************************************************
    h3cRadiusExtend OBJECT IDENTIFIER ::= { h3cRadius 5 }

    h3cRadiusExtendObjects OBJECT IDENTIFIER ::= { h3cRadiusExtend 1 }
    h3cRadiusExtendTables OBJECT IDENTIFIER ::= { h3cRadiusExtend 2 }
    h3cRadiusExtendTraps OBJECT IDENTIFIER ::= { h3cRadiusExtend 3 }

-- ***********************************************************************
--
--  Radius Scheme Authentication Table
--
-- ***********************************************************************
    h3cRadiusSchAuthTable OBJECT-TYPE
        SYNTAX SEQUENCE OF H3cRadiusSchAuthEntry
        MAX-ACCESS not-accessible
        STATUS current
        DESCRIPTION
        "The (conceptual) table listing RADIUS authentication servers."
    ::= { h3cRadiusExtendTables 1 }

    h3cRadiusSchAuthEntry OBJECT-TYPE
        SYNTAX H3cRadiusSchAuthEntry
        MAX-ACCESS not-accessible
        STATUS current
        DESCRIPTION
        "An entry (conceptual row) representing RADIUS authentication servers."
        INDEX { h3cRadiusSchAuthGroupName}
    ::= { h3cRadiusSchAuthTable 1 }

    H3cRadiusSchAuthEntry ::= SEQUENCE {
        h3cRadiusSchAuthGroupName           DisplayString,
        h3cRadiusSchAuthPrimIpAddr          IpAddress,
        h3cRadiusSchAuthPrimUdpPort         Integer32,
        h3cRadiusSchAuthPrimKey             DisplayString,
        h3cRadiusSchAuthSecIpAddr           IpAddress,
        h3cRadiusSchAuthSecUdpPort          Integer32,
        h3cRadiusSchAuthSecKey              DisplayString,
        h3cRadiusSchAuthRowStatus           RowStatus
        }

    h3cRadiusSchAuthGroupName OBJECT-TYPE
        SYNTAX DisplayString
        MAX-ACCESS not-accessible
        STATUS current
        DESCRIPTION
        "The name of the RADIUS authentication server group referred to in this table entry."
    ::= { h3cRadiusSchAuthEntry 1 }

    h3cRadiusSchAuthPrimIpAddr OBJECT-TYPE
        SYNTAX      IpAddress
        MAX-ACCESS  read-create
        STATUS      current
        DESCRIPTION
        "The IP address of primary RADIUS authenticaiton server."
    ::= { h3cRadiusSchAuthEntry 2 }

    h3cRadiusSchAuthPrimUdpPort OBJECT-TYPE
        SYNTAX      Integer32
        MAX-ACCESS  read-create
        STATUS      current
        DESCRIPTION
        "The UDP port the client is using to send requests to primary
        RADIUS authentication server.  Default value is 1812."
        DEFVAL { 1812 }
    ::= { h3cRadiusSchAuthEntry 3 }

    h3cRadiusSchAuthPrimKey OBJECT-TYPE
        SYNTAX DisplayString
        MAX-ACCESS read-create
        STATUS current
        DESCRIPTION
        "The secret shared between the RADIUS client and the primary RADIUS
        authentication server used in encoding and decoding sensitive data."
    ::= { h3cRadiusSchAuthEntry 4 }

    h3cRadiusSchAuthSecIpAddr OBJECT-TYPE
        SYNTAX      IpAddress
        MAX-ACCESS  read-create
        STATUS      current
        DESCRIPTION
        "The IP address of secondary RADIUS authenticaiton server."
    ::= { h3cRadiusSchAuthEntry 5 }

    h3cRadiusSchAuthSecUdpPort OBJECT-TYPE
        SYNTAX      Integer32
        MAX-ACCESS  read-create
        STATUS      current
        DESCRIPTION
        "The UDP port the client is using to send requests to secondary
        RADIUS authentication server.  Default value is 1812."
        DEFVAL { 1812 }
    ::= { h3cRadiusSchAuthEntry 6 }

    h3cRadiusSchAuthSecKey OBJECT-TYPE
        SYNTAX DisplayString
        MAX-ACCESS read-create
        STATUS current
        DESCRIPTION
        "The secret shared between the RADIUS client and the secondary RADIUS
        authentication server used in encoding and decoding sensitive data."
    ::= { h3cRadiusSchAuthEntry 7 }

    h3cRadiusSchAuthRowStatus   OBJECT-TYPE
        SYNTAX   RowStatus
        MAX-ACCESS  read-create
        STATUS   current
        DESCRIPTION
        "This object is responsible for managing the creation, deletion and
        modification of rows, which support active status and CreateAndGo,
        Destroy operation.
        To create a new row, h3cRadiusSchAuthGroupName must be specified,
        and this action will create a corresponding domain that
        h3cDomainRadiusGroupName is the same as h3cRadiusSchAuthGroupName.
        To destroy an existent row, the h3cRadiusSchAuthGroupName MUST NOT be
        referred by h3cDomainTable in h3cDomainRadiusGroupName column."
    ::= { h3cRadiusSchAuthEntry 8 }


-- ***********************************************************************
--
--  Radius Scheme Accounting Table
--
-- ***********************************************************************
    h3cRadiusSchAccTable OBJECT-TYPE
        SYNTAX SEQUENCE OF H3cRadiusSchAccEntry
        MAX-ACCESS not-accessible
        STATUS current
        DESCRIPTION
        "The (conceptual) table listing RADIUS accounting servers."
    ::= { h3cRadiusExtendTables 2 }

    h3cRadiusSchAccEntry OBJECT-TYPE
        SYNTAX H3cRadiusSchAccEntry
        MAX-ACCESS not-accessible
        STATUS current
        DESCRIPTION
        "An entry (conceptual row) representing RADIUS accounting servers."
        INDEX { h3cRadiusSchAccGroupName}
    ::= { h3cRadiusSchAccTable 1 }

    H3cRadiusSchAccEntry ::= SEQUENCE {
        h3cRadiusSchAccGroupName           DisplayString,
        h3cRadiusSchAccPrimIpAddr          IpAddress,
        h3cRadiusSchAccPrimUdpPort         Integer32,
        h3cRadiusSchAccPrimKey             DisplayString,
        h3cRadiusSchAccSecIpAddr           IpAddress,
        h3cRadiusSchAccSecUdpPort          Integer32,
        h3cRadiusSchAccSecKey              DisplayString,
        h3cRadiusSchAccRowStatus           RowStatus
        }

    h3cRadiusSchAccGroupName OBJECT-TYPE
        SYNTAX DisplayString
        MAX-ACCESS not-accessible
        STATUS current
        DESCRIPTION
        "The name of the RADIUS accounting server group referred to in this table entry."
    ::= { h3cRadiusSchAccEntry 1 }

    h3cRadiusSchAccPrimIpAddr OBJECT-TYPE
        SYNTAX      IpAddress
        MAX-ACCESS  read-create
        STATUS      current
        DESCRIPTION
        "The IP address of primary RADIUS accounting server."
    ::= { h3cRadiusSchAccEntry 2 }

    h3cRadiusSchAccPrimUdpPort OBJECT-TYPE
        SYNTAX      Integer32
        MAX-ACCESS  read-create
        STATUS      current
        DESCRIPTION
        "The UDP port the client is using to send requests to primary
        RADIUS accounting server.  Default value is 1813."
        DEFVAL { 1813 }
    ::= { h3cRadiusSchAccEntry 3 }

    h3cRadiusSchAccPrimKey OBJECT-TYPE
        SYNTAX DisplayString
        MAX-ACCESS read-create
        STATUS current
        DESCRIPTION
        "The secret shared between the RADIUS client and the primary RADIUS
        accounting server used in encoding and decoding sensitive data."
    ::= { h3cRadiusSchAccEntry 4 }

    h3cRadiusSchAccSecIpAddr OBJECT-TYPE
        SYNTAX      IpAddress
        MAX-ACCESS  read-create
        STATUS      current
        DESCRIPTION
        "The IP address of secondary RADIUS accounting server."
    ::= { h3cRadiusSchAccEntry 5 }

    h3cRadiusSchAccSecUdpPort OBJECT-TYPE
        SYNTAX      Integer32
        MAX-ACCESS  read-create
        STATUS      current
        DESCRIPTION
        "The UDP port the client is using to send requests to secondary
        RADIUS accounting server.  Default value is 1813."
        DEFVAL { 1813 }
    ::= { h3cRadiusSchAccEntry 6 }

    h3cRadiusSchAccSecKey OBJECT-TYPE
        SYNTAX DisplayString
        MAX-ACCESS read-create
        STATUS current
        DESCRIPTION
        "The secret shared between the RADIUS client and the secondary RADIUS
        accounting server used in encoding and decoding sensitive data."
    ::= { h3cRadiusSchAccEntry 7 }

    h3cRadiusSchAccRowStatus   OBJECT-TYPE
        SYNTAX   RowStatus
        MAX-ACCESS  read-create
        STATUS   current
        DESCRIPTION
        "This object is responsible for managing the creation, deletion and
        modification of rows, which support active status and CreateAndGo,
        Destroy operation.
        To create a new row, h3cRadiusSchAccGroupName must be specified,
        and this action will create a corresponding domain that
        h3cDomainRadiusGroupName is the same as h3cRadiusSchAccGroupName.
        To destroy an existent row, the h3cRadiusSchAccGroupName MUST NOT be
        referred by h3cDomainTable in h3cDomainRadiusGroupName column."
    ::= { h3cRadiusSchAccEntry 8 }
-- ***********************************************************************
--
-- RADIUS ACCOUNT STATISTIC
--
-- ***********************************************************************
h3cRadiusStatistic OBJECT IDENTIFIER ::= { h3cRadius 6 }

h3cRadiusStatAccReq OBJECT-TYPE
    SYNTAX      Counter64
    MAX-ACCESS  read-only
    STATUS      current
    DESCRIPTION
        "It shows the number of radius account request to the
        radius server."
    ::= { h3cRadiusStatistic 1 }

h3cRadiusStatAccAck OBJECT-TYPE
    SYNTAX      Counter64
    MAX-ACCESS  read-only
    STATUS      current
    DESCRIPTION
        "It shows the number of radius account response from the
         radius server."
    ::= { h3cRadiusStatistic 2 }

h3cRadiusStatLogoutReq OBJECT-TYPE
    SYNTAX      Counter64
    MAX-ACCESS  read-only
    STATUS      current
    DESCRIPTION
        "It shows the number of logout request to the radius server."
    ::= { h3cRadiusStatistic 3 }

h3cRadiusStatLogoutAck OBJECT-TYPE
    SYNTAX      Counter64
    MAX-ACCESS  read-only
    STATUS      current
    DESCRIPTION
        "It shows the number of logout response from the radius server."
    ::= { h3cRadiusStatistic 4 }

h3cRadiusServerTrapVarObjects OBJECT IDENTIFIER ::= { h3cRadius 7 }

h3cRadiusServerFirstTrapTime OBJECT-TYPE
    SYNTAX      TimeTicks
    MAX-ACCESS  accessible-for-notify
    STATUS      current
    DESCRIPTION
        "Represents the first trap time."
    ::= { h3cRadiusServerTrapVarObjects 1 }

END

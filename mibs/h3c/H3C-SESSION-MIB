-- =========================================================================
-- Copyright (c) 2004-2016 Hangzhou H3C Tech. Co., Ltd. All rights reserved.
--
-- Description: The MIB is designed to set session configuration or get session information.
-- Reference:
-- Version: V1.2
-- History:
--  V1.0 2013-12-20 created by liqian 04379
--       Initial version.
--  V1.1 2014-07-14 modified by songhaibin 03750
--       Add h3cSessionStatTCPCount, h3cSessionStatUDPCount,
--       h3cSessionStatOtherCount, h3cSessionStatTCPCreateRate,
--       h3cSessionStatUDPCreateRate, h3cSessionStatOtherCreateRate.
--  V1.2 2014-10-14 modified by songhaibin 03750
--       Add h3cSessionEntTCPTotal, h3cSessionEntUDPTotal,
--       h3cSessionEntOtherTotal, h3cSessionEntTable.
--       2016-12-25 modified by wangxiaohua 11458
--       Add h3cSessionStatDNSCount, h3cSessionStatFTPCount,
--       h3cSessionStatGTPCount, h3cSessionStatH323Count,
--       h3cSessionStatHTTPCount, h3cSessionStatILSCount,
--       h3cSessionStatMGCPCount, h3cSessionStatNBTCount,
--       h3cSessionStatPPTPCount, h3cSessionStatRSHCount,
--       h3cSessionStatRTSPCount, h3cSessionStatSCCPCount,
--       h3cSessionStatSIPCount, h3cSessionStatSMTPCount,
--       h3cSessionStatSQLNETCount, h3cSessionStatSSHCount,
--       h3cSessionStatTELNETCount, h3cSessionStatTFTPCount,
--       h3cSessionStatXDMCPCount.
-- =========================================================================
H3C-SESSION-MIB DEFINITIONS ::= BEGIN

IMPORTS
        h3cCommon
    FROM HUAWEI-3COM-OID-MIB
        Unsigned32, OBJECT-TYPE, MODULE-IDENTITY, Counter64
    FROM SNMPv2-SMI;

h3cSession MODULE-IDENTITY
    LAST-UPDATED "201612251105Z"   -- December 25, 2016
    ORGANIZATION
        "Hangzhou H3C Technologies Co., Ltd."
    CONTACT-INFO
        "Platform Team Hangzhou H3C Technologies Co., Ltd.
         Hai-Dian District Beijing P.R. China
         http://www.h3c.com
         Zip:100085"
    DESCRIPTION
        "The MIB is designed to manage sessions."

    -- Revision History
    REVISION "201612251105Z"  -- December 25, 2016
    DESCRIPTION
        "Add the h3cSessionStatDNSCount,
         h3cSessionStatFTPCount,
         h3cSessionStatGTPCount,
         h3cSessionStatH323Count,
         h3cSessionStatHTTPCount,
         h3cSessionStatILSCount,
         h3cSessionStatMGCPCount,
         h3cSessionStatNBTCount,
         h3cSessionStatPPTPCount,
         h3cSessionStatRSHCount,
         h3cSessionStatRTSPCount,
         h3cSessionStatSCCPCount,
         h3cSessionStatSIPCount,
         h3cSessionStatSMTPCount,
         h3cSessionStatSQLNETCount,
         h3cSessionStatSSHCount,
         h3cSessionStatTELNETCount,
         h3cSessionStatTFTPCount,
         h3cSessionStatXDMCPCount."
    REVISION "201410141830Z"
    DESCRIPTION
        "Add h3cSessionEntTCPTotal, h3cSessionEntUDPTotal, h3cSessionEntOtherTotal, h3cSessionEntTable."
    REVISION "201407151530Z"
    DESCRIPTION
        "The latest version of this MIB module."
    REVISION     "201312200000Z"  -- December 26, 2013
    DESCRIPTION  "Initial version."

    ::= { h3cCommon 149 }

--
-- Table definitions
--

h3cSessionTables OBJECT IDENTIFIER ::= { h3cSession 1 }
-- ----------------------------------------------------------------------
  -- Session statistic table
-- ----------------------------------------------------------------------
h3cSessionStatTable OBJECT-TYPE
    SYNTAX  SEQUENCE OF H3cSessionStatEntry
    MAX-ACCESS  not-accessible
    STATUS  current
    DESCRIPTION
    "The statistics of sessions."
::= { h3cSessionTables 1 }

h3cSessionStatEntry OBJECT-TYPE
    SYNTAX  H3cSessionStatEntry
    MAX-ACCESS  not-accessible
    STATUS  current
    DESCRIPTION
    "An entry (conceptual row) representing session statistics information."
    INDEX { h3cSessionStatChassis, h3cSessionStatSlot, h3cSessionStatCPUID }
::= { h3cSessionStatTable 1 }

H3cSessionStatEntry ::= SEQUENCE {
    h3cSessionStatChassis          Unsigned32,
    h3cSessionStatSlot             Unsigned32,
    h3cSessionStatCPUID            Unsigned32,
    h3cSessionStatCount            Unsigned32,
    h3cSessionStatCreateRate       Unsigned32,
    h3cSessionStatTCPCount         Unsigned32,
    h3cSessionStatUDPCount         Unsigned32,
    h3cSessionStatOtherCount       Unsigned32,
    h3cSessionStatTCPCreateRate    Unsigned32,
    h3cSessionStatUDPCreateRate    Unsigned32,
    h3cSessionStatOtherCreateRate  Unsigned32,
    h3cSessionStatTCPTotal         Counter64,
    h3cSessionStatUDPTotal         Counter64,
    h3cSessionStatOtherTotal       Counter64,
    h3cSessionStatDNSCount         Unsigned32,
    h3cSessionStatFTPCount         Unsigned32,
    h3cSessionStatGTPCount         Unsigned32,
    h3cSessionStatH323Count        Unsigned32,
    h3cSessionStatHTTPCount        Unsigned32,
    h3cSessionStatILSCount         Unsigned32,
    h3cSessionStatMGCPCount        Unsigned32,
    h3cSessionStatNBTCount         Unsigned32,
    h3cSessionStatPPTPCount        Unsigned32,
    h3cSessionStatRSHCount         Unsigned32,
    h3cSessionStatRTSPCount        Unsigned32,
    h3cSessionStatSCCPCount        Unsigned32,
    h3cSessionStatSIPCount         Unsigned32,
    h3cSessionStatSMTPCount        Unsigned32,
    h3cSessionStatSQLNETCount      Unsigned32,
    h3cSessionStatSSHCount         Unsigned32,
    h3cSessionStatTELNETCount      Unsigned32,
    h3cSessionStatTFTPCount        Unsigned32,
    h3cSessionStatXDMCPCount       Unsigned32
    }

h3cSessionStatChassis   OBJECT-TYPE
    SYNTAX Unsigned32(0..65534)
    MAX-ACCESS  not-accessible
    STATUS  current
    DESCRIPTION
    "An IRF member device ID."
::= { h3cSessionStatEntry  1 }

h3cSessionStatSlot    OBJECT-TYPE
    SYNTAX Unsigned32(0..65534)
    MAX-ACCESS  not-accessible
    STATUS  current
    DESCRIPTION
    "The slot where the card resides."
::= { h3cSessionStatEntry  2 }

h3cSessionStatCPUID   OBJECT-TYPE
    SYNTAX Unsigned32(0..7)
    MAX-ACCESS  not-accessible
    STATUS  current
    DESCRIPTION
    "CPU ID."
::= { h3cSessionStatEntry  3 }

h3cSessionStatCount  OBJECT-TYPE
    SYNTAX Unsigned32
    MAX-ACCESS  read-only
    STATUS  current
    DESCRIPTION
    "The number of current sessions."
::= { h3cSessionStatEntry  4 }

h3cSessionStatCreateRate     OBJECT-TYPE
    SYNTAX Unsigned32
    MAX-ACCESS  read-only
    STATUS  current
    DESCRIPTION
    "The number of sessions per second."
::= { h3cSessionStatEntry  5 }

h3cSessionStatTCPCount  OBJECT-TYPE
    SYNTAX Unsigned32
    MAX-ACCESS  read-only
    STATUS  current
    DESCRIPTION
    "The number of TCP sessions."
::= { h3cSessionStatEntry  6 }

h3cSessionStatUDPCount  OBJECT-TYPE
    SYNTAX Unsigned32
    MAX-ACCESS  read-only
    STATUS  current
    DESCRIPTION
    "The number of UDP sessions."
::= { h3cSessionStatEntry  7 }

h3cSessionStatOtherCount  OBJECT-TYPE
    SYNTAX Unsigned32
    MAX-ACCESS  read-only
    STATUS  current
    DESCRIPTION
    "The number of other sessions."
::= { h3cSessionStatEntry  8 }

h3cSessionStatTCPCreateRate  OBJECT-TYPE
    SYNTAX Unsigned32
    MAX-ACCESS  read-only
    STATUS  current
    DESCRIPTION
    "The number of TCP sessions per second."
::= { h3cSessionStatEntry  9 }

h3cSessionStatUDPCreateRate  OBJECT-TYPE
    SYNTAX Unsigned32
    MAX-ACCESS  read-only
    STATUS  current
    DESCRIPTION
    "The number of UDP sessions per second."
::= { h3cSessionStatEntry  10 }

h3cSessionStatOtherCreateRate  OBJECT-TYPE
    SYNTAX Unsigned32
    MAX-ACCESS  read-only
    STATUS  current
    DESCRIPTION
    "The number of other sessions per second."
::= { h3cSessionStatEntry  11 }

h3cSessionStatTCPTotal  OBJECT-TYPE
    SYNTAX Counter64
    MAX-ACCESS  read-only
    STATUS  current
    DESCRIPTION
    "The total number of TCP sessions created till now."
::= { h3cSessionStatEntry  12 }

h3cSessionStatUDPTotal  OBJECT-TYPE
    SYNTAX Counter64
    MAX-ACCESS  read-only
    STATUS  current
    DESCRIPTION
    "The total number of UDP sessions created till now."
::= { h3cSessionStatEntry  13 }

h3cSessionStatOtherTotal  OBJECT-TYPE
    SYNTAX Counter64
    MAX-ACCESS  read-only
    STATUS  current
    DESCRIPTION
    "The total number of Other sessions created till now."
::= { h3cSessionStatEntry  14 }

h3cSessionStatDNSCount  OBJECT-TYPE
    SYNTAX Unsigned32
    MAX-ACCESS  read-only
    STATUS  current
    DESCRIPTION
    "The number of DNS sessions."
::= { h3cSessionStatEntry  15 }

h3cSessionStatFTPCount  OBJECT-TYPE
    SYNTAX Unsigned32
    MAX-ACCESS  read-only
    STATUS  current
    DESCRIPTION
    "The number of FTP sessions."
::= { h3cSessionStatEntry  16 }

h3cSessionStatGTPCount  OBJECT-TYPE
    SYNTAX Unsigned32
    MAX-ACCESS  read-only
    STATUS  current
    DESCRIPTION
    "The number of GTP sessions."
::= { h3cSessionStatEntry  17 }

h3cSessionStatH323Count  OBJECT-TYPE
    SYNTAX Unsigned32
    MAX-ACCESS  read-only
    STATUS  current
    DESCRIPTION
    "The number of H323 sessions."
::= { h3cSessionStatEntry  18 }

h3cSessionStatHTTPCount  OBJECT-TYPE
    SYNTAX Unsigned32
    MAX-ACCESS  read-only
    STATUS  current
    DESCRIPTION
    "The number of HTTP sessions."
::= { h3cSessionStatEntry  19 }

h3cSessionStatILSCount  OBJECT-TYPE
    SYNTAX Unsigned32
    MAX-ACCESS  read-only
    STATUS  current
    DESCRIPTION
    "The number of ILS sessions."
::= { h3cSessionStatEntry  20 }

h3cSessionStatMGCPCount  OBJECT-TYPE
    SYNTAX Unsigned32
    MAX-ACCESS  read-only
    STATUS  current
    DESCRIPTION
    "The number of MGCP sessions."
::= { h3cSessionStatEntry  21 }

h3cSessionStatNBTCount  OBJECT-TYPE
    SYNTAX Unsigned32
    MAX-ACCESS  read-only
    STATUS  current
    DESCRIPTION
    "The number of NBT sessions."
::= { h3cSessionStatEntry  22 }

h3cSessionStatPPTPCount  OBJECT-TYPE
    SYNTAX Unsigned32
    MAX-ACCESS  read-only
    STATUS  current
    DESCRIPTION
    "The number of PPTP sessions."
::= { h3cSessionStatEntry  23 }

h3cSessionStatRSHCount  OBJECT-TYPE
    SYNTAX Unsigned32
    MAX-ACCESS  read-only
    STATUS  current
    DESCRIPTION
    "The number of RSH sessions."
::= { h3cSessionStatEntry  24 }

h3cSessionStatRTSPCount  OBJECT-TYPE
    SYNTAX Unsigned32
    MAX-ACCESS  read-only
    STATUS  current
    DESCRIPTION
    "The number of RTSP sessions."
::= { h3cSessionStatEntry  25 }

h3cSessionStatSCCPCount  OBJECT-TYPE
    SYNTAX Unsigned32
    MAX-ACCESS  read-only
    STATUS  current
    DESCRIPTION
    "The number of SCCP sessions."
::= { h3cSessionStatEntry  26 }

h3cSessionStatSIPCount  OBJECT-TYPE
    SYNTAX Unsigned32
    MAX-ACCESS  read-only
    STATUS  current
    DESCRIPTION
    "The number of SIP sessions."
::= { h3cSessionStatEntry  27 }

h3cSessionStatSMTPCount  OBJECT-TYPE
    SYNTAX Unsigned32
    MAX-ACCESS  read-only
    STATUS  current
    DESCRIPTION
    "The number of SMTP sessions."
::= { h3cSessionStatEntry  28 }

h3cSessionStatSQLNETCount  OBJECT-TYPE
    SYNTAX Unsigned32
    MAX-ACCESS  read-only
    STATUS  current
    DESCRIPTION
    "The number of SQLNET sessions."
::= { h3cSessionStatEntry  29 }

h3cSessionStatSSHCount  OBJECT-TYPE
    SYNTAX Unsigned32
    MAX-ACCESS  read-only
    STATUS  current
    DESCRIPTION
    "The number of SSH sessions."
::= { h3cSessionStatEntry  30 }

h3cSessionStatTELNETCount  OBJECT-TYPE
    SYNTAX Unsigned32
    MAX-ACCESS  read-only
    STATUS  current
    DESCRIPTION
    "The number of TELNET sessions."
::= { h3cSessionStatEntry  31 }

h3cSessionStatTFTPCount  OBJECT-TYPE
    SYNTAX Unsigned32
    MAX-ACCESS  read-only
    STATUS  current
    DESCRIPTION
    "The number of TFTP sessions."
::= { h3cSessionStatEntry  32 }

h3cSessionStatXDMCPCount  OBJECT-TYPE
    SYNTAX Unsigned32
    MAX-ACCESS  read-only
    STATUS  current
    DESCRIPTION
    "The number of XDMCP sessions."
::= { h3cSessionStatEntry  33 }

-- ----------------------------------------------------------------------
  -- Session statistic by entity table
-- ----------------------------------------------------------------------
h3cSessionEntTable OBJECT-TYPE
    SYNTAX  SEQUENCE OF H3cSessionEntEntry
    MAX-ACCESS  not-accessible
    STATUS  current
    DESCRIPTION
    "The statistics of sessions by entity."
::= { h3cSessionTables 2 }

h3cSessionEntEntry OBJECT-TYPE
    SYNTAX  H3cSessionEntEntry
    MAX-ACCESS  not-accessible
    STATUS  current
    DESCRIPTION
    "An entry (conceptual row) representing session statistics information."
    INDEX { h3cSessionEntIndex }
::= { h3cSessionEntTable 1 }

H3cSessionEntEntry ::= SEQUENCE {
    h3cSessionEntIndex            Unsigned32,
    h3cSessionEntCount            Unsigned32,
    h3cSessionEntCreateRate       Unsigned32,
    h3cSessionEntTCPCount         Unsigned32,
    h3cSessionEntUDPCount         Unsigned32,
    h3cSessionEntOtherCount       Unsigned32,
    h3cSessionEntTCPCreateRate    Unsigned32,
    h3cSessionEntUDPCreateRate    Unsigned32,
    h3cSessionEntOtherCreateRate  Unsigned32,
    h3cSessionEntTCPTotal         Counter64,
    h3cSessionEntUDPTotal         Counter64,
    h3cSessionEntOtherTotal       Counter64
    }

h3cSessionEntIndex   OBJECT-TYPE
    SYNTAX Unsigned32(1..2147483647)
    MAX-ACCESS  not-accessible
    STATUS  current
    DESCRIPTION
    "Device entity index."
::= { h3cSessionEntEntry  1 }

h3cSessionEntCount  OBJECT-TYPE
    SYNTAX Unsigned32
    MAX-ACCESS  read-only
    STATUS  current
    DESCRIPTION
    "The number of current sessions."
::= { h3cSessionEntEntry  2 }

h3cSessionEntCreateRate     OBJECT-TYPE
    SYNTAX Unsigned32
    MAX-ACCESS  read-only
    STATUS  current
    DESCRIPTION
    "The number of sessions per second."
::= { h3cSessionEntEntry  3 }

h3cSessionEntTCPCount  OBJECT-TYPE
    SYNTAX Unsigned32
    MAX-ACCESS  read-only
    STATUS  current
    DESCRIPTION
    "The number of TCP sessions."
::= { h3cSessionEntEntry  4 }

h3cSessionEntUDPCount  OBJECT-TYPE
    SYNTAX Unsigned32
    MAX-ACCESS  read-only
    STATUS  current
    DESCRIPTION
    "The number of UDP sessions."
::= { h3cSessionEntEntry  5 }

h3cSessionEntOtherCount  OBJECT-TYPE
    SYNTAX Unsigned32
    MAX-ACCESS  read-only
    STATUS  current
    DESCRIPTION
    "The number of other sessions."
::= { h3cSessionEntEntry  6 }

h3cSessionEntTCPCreateRate  OBJECT-TYPE
    SYNTAX Unsigned32
    MAX-ACCESS  read-only
    STATUS  current
    DESCRIPTION
    "The number of TCP sessions per second."
::= { h3cSessionEntEntry  7 }

h3cSessionEntUDPCreateRate  OBJECT-TYPE
    SYNTAX Unsigned32
    MAX-ACCESS  read-only
    STATUS  current
    DESCRIPTION
    "The number of UDP sessions per second."
::= { h3cSessionEntEntry  8 }

h3cSessionEntOtherCreateRate  OBJECT-TYPE
    SYNTAX Unsigned32
    MAX-ACCESS  read-only
    STATUS  current
    DESCRIPTION
    "The number of other sessions per second."
::= { h3cSessionEntEntry  9 }

h3cSessionEntTCPTotal  OBJECT-TYPE
    SYNTAX Counter64
    MAX-ACCESS  read-only
    STATUS  current
    DESCRIPTION
    "The total number of TCP sessions created till now."
::= { h3cSessionEntEntry  10 }

h3cSessionEntUDPTotal  OBJECT-TYPE
    SYNTAX Counter64
    MAX-ACCESS  read-only
    STATUS  current
    DESCRIPTION
    "The total number of UDP sessions created till now."
::= { h3cSessionEntEntry  11 }

h3cSessionEntOtherTotal  OBJECT-TYPE
    SYNTAX Counter64
    MAX-ACCESS  read-only
    STATUS  current
    DESCRIPTION
    "The total number of other sessions created till now."
::= { h3cSessionEntEntry  12 }

END

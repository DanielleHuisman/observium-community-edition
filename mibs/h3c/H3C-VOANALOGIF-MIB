-- ==========================================================================
-- Copyright (C) 2004 by H3C TECHNOLOGIES. All rights reserved.
--
-- Description: The purpose of this MIB file is to provide the definition of
--              the general analog voice interface configuration. 
-- Reference:
-- Version: V1.0
-- History:
-- V1.0 2005-03-22 Initial version, created by Yang Youku
-- ==========================================================================
H3C-VOANALOGIF-MIB DEFINITIONS ::= BEGIN

IMPORTS
    OBJECT-TYPE, MODULE-IDENTITY, Integer32
        FROM SNMPv2-SMI
    h3cVoice
        FROM HUAWEI-3COM-OID-MIB;   
    
    
    h3cVoiceAnalogInterface MODULE-IDENTITY 
        LAST-UPDATED "200503150000Z"
        ORGANIZATION                                   
            "Hangzhou H3C Tech. Co., Ltd."             
        CONTACT-INFO                                   
            "Platform Team Hangzhou H3C Tech. Co., Ltd.                              
            Hai-Dian District Beijing P.R. China       
            http://www.h3c.com                         
            Zip:100085                                 
            "                                          
        DESCRIPTION 
            "The MIB file is to provide the definition of the
            general analog voice interface configuration."
        REVISION "200503150000Z"
        DESCRIPTION 
            "The initial version of this MIB file."
        ::= { h3cVoice 3 }

    
    h3cVoAnalogIfCommonObjects OBJECT IDENTIFIER ::= 
                                        { h3cVoiceAnalogInterface 1 }

--======================================================================
--                  h3cVoAnalogIfCommonCfgTable
--
--======================================================================
    h3cVoAnalogIfCommonCfgTable OBJECT-TYPE
        SYNTAX SEQUENCE OF H3CVoAnalogIfCommonCfgEntry
        MAX-ACCESS not-accessible
        STATUS current
        DESCRIPTION
            "This table contains the information about configurable 
            parameters for an voice analog interface."
        ::= { h3cVoAnalogIfCommonObjects 1 }

    
    h3cVoAnalogIfCommonCfgEntry OBJECT-TYPE
        SYNTAX H3CVoAnalogIfCommonCfgEntry
        MAX-ACCESS not-accessible
        STATUS current
        DESCRIPTION
            "The entry of h3cVoAnalogIfCommonCfgTable, which is 
            automatically created when an analog voice module 
            has been found."
        INDEX { h3cVoAIfCfgPortIndex }
        ::= { h3cVoAnalogIfCommonCfgTable 1 }

    
    H3CVoAnalogIfCommonCfgEntry ::=
        SEQUENCE { 
            h3cVoAIfCfgPortIndex
                Integer32,
            h3cVoAIfCfgPortType
                INTEGER,
            h3cVoAIfCfgPortSubLine
                OCTET STRING
         }

    h3cVoAIfCfgPortIndex OBJECT-TYPE
        SYNTAX Integer32
        MAX-ACCESS not-accessible
        STATUS current
        DESCRIPTION
            "The index of a voice analog interface common configuration 
            table." 
        ::= { h3cVoAnalogIfCommonCfgEntry 1 }

    
    h3cVoAIfCfgPortType OBJECT-TYPE
        SYNTAX INTEGER
            {
            fxs(1),
            fxo(2),
            em(3)
            }
        MAX-ACCESS read-only
        STATUS current
        DESCRIPTION
            "This object indicates the type of a voice analog interface."
        ::= { h3cVoAnalogIfCommonCfgEntry 2 }


    h3cVoAIfCfgPortSubLine OBJECT-TYPE
        SYNTAX OCTET STRING
        MAX-ACCESS read-only
        STATUS current
        DESCRIPTION
            "This object indicates the port subscriber line name."
        ::= { h3cVoAnalogIfCommonCfgEntry 3 }


    
    h3cVoAnalogIfFXSObjects OBJECT IDENTIFIER ::= 
                                        { h3cVoiceAnalogInterface 2 }

--======================================================================
--                  h3cVoAnalogIfFXSCfgTable
--
--======================================================================
    h3cVoAnalogIfFXSCfgTable OBJECT-TYPE
        SYNTAX SEQUENCE OF H3CVoAnalogIfFXSCfgEntry
        MAX-ACCESS not-accessible
        STATUS current
        DESCRIPTION
            "This table contains the information about configurable 
            parameters for an analog fxs interface."
        ::= { h3cVoAnalogIfFXSObjects 1 }

    
    h3cVoAnalogIfFXSCfgEntry OBJECT-TYPE
        SYNTAX H3CVoAnalogIfFXSCfgEntry
        MAX-ACCESS not-accessible
        STATUS current
        DESCRIPTION
            "The entry of h3cVoAnalogIfFXSCfgTable, which is automatically   
            created when an analog fxs voice module has been found."
        INDEX { h3cVoAIfFXSCfgPortIndex }
        ::= { h3cVoAnalogIfFXSCfgTable 1 }

    
    H3CVoAnalogIfFXSCfgEntry ::=
        SEQUENCE { 
            h3cVoAIfFXSCfgPortIndex
                Integer32,
            h3cVoAIfFXSCfgCidDisplay
                INTEGER,
            h3cVoAIfFXSCfgCidSend
                INTEGER,
            h3cVoAIfFXSCfgCidType
                INTEGER,
            h3cVoAIfFXSCfgSubLine
                OCTET STRING
         }

    h3cVoAIfFXSCfgPortIndex OBJECT-TYPE
        SYNTAX Integer32
        MAX-ACCESS not-accessible
        STATUS current
        DESCRIPTION
            "The index of voice analog interface fxs configuration table." 
        ::= { h3cVoAnalogIfFXSCfgEntry 1 }

    h3cVoAIfFXSCfgCidDisplay OBJECT-TYPE
        SYNTAX INTEGER
            {
            enable(1),
            disable(2)
            }
        MAX-ACCESS read-write
        STATUS current
        DESCRIPTION
            "This object indicates whether displays the calling number
            of analog fxs interface or not."
        ::= { h3cVoAnalogIfFXSCfgEntry 3 }
        
    h3cVoAIfFXSCfgCidSend OBJECT-TYPE
        SYNTAX INTEGER
            {
            enable(1),
            disable(2)
            }
        MAX-ACCESS read-write
        STATUS current
        DESCRIPTION
            "This object indicates whether sends the calling number 
            of analog fxs interface or not."
        ::= { h3cVoAnalogIfFXSCfgEntry 4 }

    h3cVoAIfFXSCfgCidType OBJECT-TYPE
        SYNTAX INTEGER
            {
            complex(1),
            simple(2)
            }
        MAX-ACCESS read-write
        STATUS current
        DESCRIPTION
            "This object indicates the type of cid message on an analog
            fxs interface."
        DEFVAL { complex }
        ::= { h3cVoAnalogIfFXSCfgEntry 5 }

    h3cVoAIfFXSCfgSubLine OBJECT-TYPE
        SYNTAX OCTET STRING
        MAX-ACCESS read-only
        STATUS current
        DESCRIPTION
            "This object indicates the port subscriber line name."
        ::= { h3cVoAnalogIfFXSCfgEntry 6 }


--======================================================================
--                  h3cVoAnalogIfFXSTimerTable
--
--======================================================================
    h3cVoAnalogIfFXSTimerTable OBJECT-TYPE
        SYNTAX SEQUENCE OF H3CVoAnalogIfFXSTimerEntry
        MAX-ACCESS not-accessible
        STATUS current
        DESCRIPTION
            "This table contains the timer information for an 
            analog fxs interface."
        ::= { h3cVoAnalogIfFXSObjects 3 }

    
    h3cVoAnalogIfFXSTimerEntry OBJECT-TYPE
        SYNTAX H3CVoAnalogIfFXSTimerEntry
        MAX-ACCESS not-accessible
        STATUS current
        DESCRIPTION
            "The entry of h3cVoAnalogIfFXSTimerTable, which is automatically 
            created when an analog fxs voice module has been found."
        INDEX { h3cVoAIfFXSTimerPortIndex }
        ::= { h3cVoAnalogIfFXSTimerTable 1 }

    
    H3CVoAnalogIfFXSTimerEntry ::=
        SEQUENCE { 
            h3cVoAIfFXSTimerPortIndex
                Integer32,
            h3cVoAIfFXSTimerDialInterval
                Integer32,
            h3cVoAIfFXSTimerFirstDial
                Integer32,
            h3cVoAIfFXSTimerRingBack
                Integer32,
            h3cVoAIfFXSTimerSubLine
                OCTET STRING
         }

    h3cVoAIfFXSTimerPortIndex OBJECT-TYPE
        SYNTAX Integer32
        MAX-ACCESS not-accessible
        STATUS current
        DESCRIPTION
            "The index of a voice analog interface fxs timer table."
        ::= { h3cVoAnalogIfFXSTimerEntry 1 }

    h3cVoAIfFXSTimerDialInterval OBJECT-TYPE
        SYNTAX Integer32(1..300)
        MAX-ACCESS read-write
        STATUS current
        DESCRIPTION
            "The interval, in seconds, between two dialing numbers."               
        ::= { h3cVoAnalogIfFXSTimerEntry 4 }

    h3cVoAIfFXSTimerFirstDial OBJECT-TYPE
        SYNTAX Integer32(1..300)
        MAX-ACCESS read-write
        STATUS current
        DESCRIPTION
            "The period of time, in seconds, before dialing the first number."
        ::= { h3cVoAnalogIfFXSTimerEntry 5 }
    
    h3cVoAIfFXSTimerRingBack OBJECT-TYPE
        SYNTAX Integer32
        MAX-ACCESS read-write
        STATUS current
        DESCRIPTION
            "This object indicates the maximum duration the ring back
            to persist. Unit is second."
        ::= { h3cVoAnalogIfFXSTimerEntry 6 }

    h3cVoAIfFXSTimerSubLine OBJECT-TYPE
        SYNTAX OCTET STRING
        MAX-ACCESS read-only
        STATUS current
        DESCRIPTION
            "This object indicates the port subscriber line name."
        ::= { h3cVoAnalogIfFXSTimerEntry 7 }
    


    h3cVoAnalogIfFXOObjects OBJECT IDENTIFIER ::= { h3cVoiceAnalogInterface 3 }

--======================================================================
--                  h3cVoAnalogIfFXOCfgTable
--
--======================================================================
    h3cVoAnalogIfFXOCfgTable OBJECT-TYPE
        SYNTAX SEQUENCE OF H3CVoAnalogIfFXOCfgEntry
        MAX-ACCESS not-accessible
        STATUS current
        DESCRIPTION
            "This table contains the information about configurable 
            parameters for analog fxo voice interface."
        ::= { h3cVoAnalogIfFXOObjects 1 }

    
    h3cVoAnalogIfFXOCfgEntry OBJECT-TYPE
        SYNTAX H3CVoAnalogIfFXOCfgEntry
        MAX-ACCESS not-accessible
        STATUS current
        DESCRIPTION
            "The entry of h3cVoAnalogIfFXOCfgTable, which is automatically 
            created when an analog fxo interface has been found."
        INDEX { h3cVoAIfFXOCfgPortIndex }
        ::= { h3cVoAnalogIfFXOCfgTable 1 }

    
    H3CVoAnalogIfFXOCfgEntry ::=
        SEQUENCE { 
            h3cVoAIfFXOCfgPortIndex
                Integer32,
           h3cVoAIfFXOCfgArea
                INTEGER,
            h3cVoAIfFXOPreDialDelay
                Integer32,
            h3cVoAIfFXOCfgPortImpedance
                INTEGER,
            h3cVoAIfFXOCfgCidEnable
                INTEGER,
            h3cVoAnalogIfFXOCfgCidSend
                INTEGER,
            h3cVoAIfFXOCfgCidType
                INTEGER,
            h3cVoAIfFXOCfgSubLine
                OCTET STRING
         }

    h3cVoAIfFXOCfgPortIndex OBJECT-TYPE
        SYNTAX Integer32
        MAX-ACCESS not-accessible
        STATUS current
        DESCRIPTION
            "The index of voice analog interface fxo configuration 
            table."
        ::= { h3cVoAnalogIfFXOCfgEntry 1 }


    h3cVoAIfFXOCfgArea OBJECT-TYPE
        SYNTAX INTEGER
            {
            custom(1),
            europe(2),
            northmerica(3)
            }
        MAX-ACCESS read-write
        STATUS current
        DESCRIPTION
            "This object indicates the area where this product is
            used."
        ::= { h3cVoAnalogIfFXOCfgEntry 4 }

    
    h3cVoAIfFXOPreDialDelay OBJECT-TYPE
        SYNTAX Integer32(0..10)
        MAX-ACCESS read-write
        STATUS current
        DESCRIPTION
            "The maximum length of time, in seconds, of pre-dial 
            delay on the analog fxo interface."
        ::= { h3cVoAnalogIfFXOCfgEntry 5 }

    
    h3cVoAIfFXOCfgPortImpedance OBJECT-TYPE
        SYNTAX INTEGER 
            {
            australia(1),
            austria(2),
            belgiumLong(3),
            belgiumShort(4),
            brazil(5),
            germanSwiss(6),
            china(7),
            greece(8),
            czechRepublic(9),
            denmark(10),
            eTSIHarmanized(11),
            finland(12),
            france(13),
            hungary(14),
            india(15),
            italy(16),
            japan(17),
            korea(18),
            mexico(19),
            netherlands(20),
            norway(21),
            portugal(22),
            slovakia(23),
            spain(24),
            sweden(25),
            uk(26),
            usLoadedLine(27),
            usNonLoaded(28),
            usSpecialService(29),
            r550(30),
            r600(31),
            r650(32),
            r700(33),
            r750(34),
            r800(35),
            r850(36),
            r900(37),
            r950(38)
            }
        MAX-ACCESS read-write
        STATUS current
        DESCRIPTION
            "This object indicates the port impedance of a FXO interface."
        ::= { h3cVoAnalogIfFXOCfgEntry 6 }
        
    h3cVoAIfFXOCfgCidEnable OBJECT-TYPE
        SYNTAX INTEGER
            {
            enable(1),
            disable(2)
            }
        MAX-ACCESS read-write
        STATUS current
        DESCRIPTION
            "This object indicates whether enables the cid receiving 
            function on an analog fxo interface." 
        ::= { h3cVoAnalogIfFXOCfgEntry 7 }

    h3cVoAnalogIfFXOCfgCidSend OBJECT-TYPE
        SYNTAX INTEGER
            {
            enable(1),
            disable(2)
            }
        MAX-ACCESS read-write
        STATUS current
        DESCRIPTION
            "This object indicates whether sends the calling 
            number."
        ::= { h3cVoAnalogIfFXOCfgEntry 8 }

    h3cVoAIfFXOCfgCidType OBJECT-TYPE
        SYNTAX INTEGER
            {
            complex(1),
            simple(2)
            }
        MAX-ACCESS read-write
        STATUS current
        DESCRIPTION
            "This object indicates the type of cid message on an analog
             fxo interface." 
        ::= { h3cVoAnalogIfFXOCfgEntry 9 }

    h3cVoAIfFXOCfgSubLine OBJECT-TYPE
        SYNTAX OCTET STRING
        MAX-ACCESS read-only
        STATUS current
        DESCRIPTION
            "This object indicates the port subscriber line name."
        ::= { h3cVoAnalogIfFXOCfgEntry 10 }
    

--======================================================================
--                  h3cVoAnalogIfFXOTimerTable
--
--======================================================================
    h3cVoAnalogIfFXOTimerTable OBJECT-TYPE
        SYNTAX SEQUENCE OF H3CVoAnalogIfFXOTimerEntry
        MAX-ACCESS not-accessible
        STATUS current
        DESCRIPTION
            "This table contains the timer information for an 
            analog fxo interface."
        ::= { h3cVoAnalogIfFXOObjects 3 }

    
    h3cVoAnalogIfFXOTimerEntry OBJECT-TYPE
        SYNTAX H3CVoAnalogIfFXOTimerEntry
        MAX-ACCESS not-accessible
        STATUS current
        DESCRIPTION
            "The entry of h3cVoAnalogIfFXOTimerTable, which is automatically 
            created when an analog fxo interface has been found."
        INDEX { h3cVoAIfFXOTimerPortIndex }
        ::= { h3cVoAnalogIfFXOTimerTable 1 }

    
    H3CVoAnalogIfFXOTimerEntry ::=
        SEQUENCE { 
            h3cVoAIfFXOTimerPortIndex
                Integer32,
            h3cVoAIfFXOTimerDtmf
                Integer32,
            h3cVoAIfFXOTimerDtmfInterval
                Integer32,
            h3cVoAIfFXOTimerDialInterval
                Integer32,
            h3cVoAIfFXOTimerFirstDial
                Integer32,
            h3cVoAIfFXOTimerRingBack
                Integer32,
            h3cVoAIfFXOTimerSubLine
                OCTET STRING
         }

    h3cVoAIfFXOTimerPortIndex OBJECT-TYPE
        SYNTAX Integer32
        MAX-ACCESS not-accessible
        STATUS current
        DESCRIPTION
            "The index of voice analog interface fxo timer table." 
        ::= { h3cVoAnalogIfFXOTimerEntry 1 }

    
    h3cVoAIfFXOTimerDtmf OBJECT-TYPE
        SYNTAX Integer32
        MAX-ACCESS read-write
        STATUS current
        DESCRIPTION
            "This object indicates duration of DTMF(Dual Tone Multi-Frequency) 
            signal in milliseconds."
        ::= { h3cVoAnalogIfFXOTimerEntry 2 }

    
    h3cVoAIfFXOTimerDtmfInterval OBJECT-TYPE
        SYNTAX Integer32
        MAX-ACCESS read-write
        STATUS current
        DESCRIPTION
            "This object indicates DTMF(Dual Tone Multi-Frequency) sending 
            interval in milliseconds."
        ::= { h3cVoAnalogIfFXOTimerEntry 3 }

    h3cVoAIfFXOTimerDialInterval OBJECT-TYPE
        SYNTAX Integer32
        MAX-ACCESS read-write
        STATUS current
        DESCRIPTION
            "The interval, in seconds, between two dialing numbers." 
        ::= { h3cVoAnalogIfFXOTimerEntry 4 }

    h3cVoAIfFXOTimerFirstDial OBJECT-TYPE
        SYNTAX Integer32
        MAX-ACCESS read-write
        STATUS current
        DESCRIPTION
            "The period of time, in seconds, before dialing the first number." 
        ::= { h3cVoAnalogIfFXOTimerEntry 5 }
    
    h3cVoAIfFXOTimerRingBack OBJECT-TYPE
        SYNTAX Integer32
        MAX-ACCESS read-write
        STATUS current
        DESCRIPTION
            "This object indicates the maximum duration the ring back 
            to persist. Unit is second."
        ::= { h3cVoAnalogIfFXOTimerEntry 6 }

    h3cVoAIfFXOTimerSubLine OBJECT-TYPE
        SYNTAX OCTET STRING
        MAX-ACCESS read-only
        STATUS current
        DESCRIPTION
            "This object indicates the port subscriber line name."
        ::= { h3cVoAnalogIfFXOTimerEntry 7 }



    h3cVoAnalogIfEMObjects OBJECT IDENTIFIER ::= { h3cVoiceAnalogInterface 4 }

--======================================================================
--                  h3cVoAnalogIfEMCfgTable
--
--======================================================================
    h3cVoAnalogIfEMCfgTable OBJECT-TYPE
        SYNTAX SEQUENCE OF H3CVoAnalogIfEMCfgEntry
        MAX-ACCESS not-accessible
        STATUS current
        DESCRIPTION
            "This table contains the information about configurable 
            parameters for an analog EM interface."
        ::= { h3cVoAnalogIfEMObjects 1 }

    
    h3cVoAnalogIfEMCfgEntry OBJECT-TYPE
        SYNTAX H3CVoAnalogIfEMCfgEntry
        MAX-ACCESS not-accessible
        STATUS current
        DESCRIPTION
            "The entry of h3cVoAnalogIfEMCfgTable, which is automatically 
            created when an analog EM voice module has been found."
        INDEX { h3cVoAIfEMCfgPortIndex }
        ::= { h3cVoAnalogIfEMCfgTable 1 }

    
    H3CVoAnalogIfEMCfgEntry ::=
        SEQUENCE { 
            h3cVoAIfEMCfgPortIndex
                Integer32,
            h3cVoAIfEMCfgSignalMode
                INTEGER,
            h3cVoAIfEMCfgPhyParm
                INTEGER,
            h3cVoAIfEMCfgPhyType
                INTEGER,
            h3cVoAIfEMCfgTimeoutRing
                Integer32,
            h3cVoAIfEMCfgTimeoutWaitDigit
                Integer32,
            h3cVoAIfEMCfgSubLine
                OCTET STRING
         }

    h3cVoAIfEMCfgPortIndex OBJECT-TYPE
        SYNTAX Integer32
        MAX-ACCESS read-only
        STATUS current
        DESCRIPTION
            "The index of voice analog interface EM configuration table."
        ::= { h3cVoAnalogIfEMCfgEntry 1 }

    
    h3cVoAIfEMCfgSignalMode OBJECT-TYPE
        SYNTAX INTEGER
            {
            delayDial(1),
            immediateDial(2),
            winkStart(3)
            }
        MAX-ACCESS read-write
        STATUS current
        DESCRIPTION
            "This object indicates the signal modes of an analog 
            EM interfaces."
        ::= { h3cVoAnalogIfEMCfgEntry 2 }

    
    h3cVoAIfEMCfgPhyParm OBJECT-TYPE
        SYNTAX INTEGER
            {
            twoWiresOperation(1),
            fourWiresOperation(2)
            }
        MAX-ACCESS read-write
        STATUS current
        DESCRIPTION
            "This object indicates the operation of an analog EM 
            signal."
        ::= { h3cVoAnalogIfEMCfgEntry 3 }

    
    h3cVoAIfEMCfgPhyType OBJECT-TYPE
        SYNTAX INTEGER
            {
            type1(1),
            type2(2),
            type3(3),
            type5(5)
            }
        MAX-ACCESS read-write
        STATUS current
        DESCRIPTION
            "This object indicates the EM type of the 
            analog interface. "
        ::= { h3cVoAnalogIfEMCfgEntry 4 }

    
    h3cVoAIfEMCfgTimeoutRing OBJECT-TYPE
        SYNTAX Integer32(5..120)
        MAX-ACCESS read-write
        STATUS current
        DESCRIPTION
            "The maximum seconds, to wait for the ring back on the 
            EM interface."
        ::= { h3cVoAnalogIfEMCfgEntry 5 }

    
    h3cVoAIfEMCfgTimeoutWaitDigit OBJECT-TYPE
        SYNTAX Integer32
        MAX-ACCESS read-write
        STATUS current
        DESCRIPTION
            "The maximum length of time, in  seconds, to wait for called 
            number on an analog EM interface."
        ::= { h3cVoAnalogIfEMCfgEntry 6 }

    h3cVoAIfEMCfgSubLine OBJECT-TYPE
        SYNTAX OCTET STRING
        MAX-ACCESS read-only
        STATUS current
        DESCRIPTION
            "This object indicates the port subscriber line name."
        ::= { h3cVoAnalogIfEMCfgEntry 7 }


--======================================================================
--                  h3cVoAnalogIfEMTimerTable
--
--======================================================================
    h3cVoAnalogIfEMTimerTable OBJECT-TYPE
        SYNTAX SEQUENCE OF H3CVoAnalogIfEMTimerEntry
        MAX-ACCESS not-accessible
        STATUS current
        DESCRIPTION
            "This table contains the timer information for an analog 
            EM interface."
        ::= { h3cVoAnalogIfEMObjects 3 }

    
    h3cVoAnalogIfEMTimerEntry OBJECT-TYPE
        SYNTAX H3CVoAnalogIfEMTimerEntry
        MAX-ACCESS not-accessible
        STATUS current
        DESCRIPTION
            "The entry of h3cVoAnalogIfEMTimerTable, which is automatically
            created when an analog EM voice module has been found."
        INDEX { h3cVoAIfEMTimerPortIndex }
        ::= { h3cVoAnalogIfEMTimerTable 1 }

    
    H3CVoAnalogIfEMTimerEntry ::=
        SEQUENCE { 
            h3cVoAIfEMTimerPortIndex
                Integer32,
            h3cVoAIfEMTimerDtmf
                Integer32,
            h3cVoAIfEMTimerDtmfInterval
                Integer32,
            h3cVoAIfEMTimerSendWink
                Integer32,
            h3cVoAIfEMTimerWinkRising
                Integer32,
            h3cVoAIfEMTimerWinkHold
                Integer32,
            h3cVoAIfEMTimerDialoutDelay
                Integer32,
            h3cVoAIfEMTimerDelayRising
                Integer32,
            h3cVoAIfEMTimerDelayHold
                Integer32,
            h3cVoAIfEMTimerSubLine
                OCTET STRING
         }

    h3cVoAIfEMTimerPortIndex OBJECT-TYPE
        SYNTAX Integer32
        MAX-ACCESS read-only
        STATUS current
        DESCRIPTION
            "The index of voice analog interface EM timer table."
        ::= { h3cVoAnalogIfEMTimerEntry 1 }

    
    h3cVoAIfEMTimerDtmf OBJECT-TYPE
        SYNTAX Integer32
        MAX-ACCESS read-write
        STATUS current
        DESCRIPTION
            "This object indicates DTMF(Dual Tone Multi-Frequency) 
            sending duration in milliseconds." 
        ::= { h3cVoAnalogIfEMTimerEntry 2 }

    
    h3cVoAIfEMTimerDtmfInterval OBJECT-TYPE
        SYNTAX Integer32
        MAX-ACCESS read-write
        STATUS current
        DESCRIPTION
            "This object indicates DTMF(Dual Tone Multi-Frequency) 
            sending interval in milliseconds."
        ::= { h3cVoAnalogIfEMTimerEntry 3 }

    
    h3cVoAIfEMTimerSendWink OBJECT-TYPE
        SYNTAX Integer32(100..5000)
        MAX-ACCESS read-write
        STATUS current
        DESCRIPTION
            "This object indicates the maximum time in milliseconds
            between receiving seizure signal and sending wink signal. 
            This object can only take effect when h3cVoAIfEMCfgSignalMode 
            is set to 'winkStart'." 
        DEFVAL { 200 }
        ::= { h3cVoAnalogIfEMTimerEntry 5 }

    
    h3cVoAIfEMTimerWinkRising OBJECT-TYPE
        SYNTAX Integer32
        MAX-ACCESS read-write
        STATUS current
        DESCRIPTION
            "This object indicates the maximum time in milliseconds
            between sending seizure signal and receiving wink signal. 
            This object can only take effect when h3cVoAIfEMCfgSignalMode 
            is set to 'winkStart'." 
        ::= { h3cVoAnalogIfEMTimerEntry 6 }

    
    h3cVoAIfEMTimerWinkHold OBJECT-TYPE
        SYNTAX Integer32
        MAX-ACCESS read-write
        STATUS current
        DESCRIPTION
            "This object indicates the maximum duration in milliseconds
            to send wink signal. This object can only take effect 
            when h3cVoAIfEMCfgSignalMode is set to 'winkStart'."
        ::= { h3cVoAnalogIfEMTimerEntry 7 }

    
    h3cVoAIfEMTimerDialoutDelay OBJECT-TYPE
        SYNTAX Integer32
        MAX-ACCESS read-write
        STATUS current
        DESCRIPTION
            "This object indicates the maximum duration in milliseconds
            to send called digits. This object can only take effect 
            when h3cVoAIfEMCfgSignalMode is set to 'immediateDial'." 
        ::= { h3cVoAnalogIfEMTimerEntry 8 }

    
    h3cVoAIfEMTimerDelayRising OBJECT-TYPE
        SYNTAX Integer32
        MAX-ACCESS read-write
        STATUS current
        DESCRIPTION
            "This object indicates the maximum duration in milliseconds
            between receiveing seizure signal and sending delay signal. 
            This object can only take effect when 
            h3cVoAIfEMCfgSignalMode is set to 'delayDial'." 
        ::= { h3cVoAnalogIfEMTimerEntry 9 }

    
    h3cVoAIfEMTimerDelayHold OBJECT-TYPE
        SYNTAX Integer32
        MAX-ACCESS read-write
        STATUS current
        DESCRIPTION
            "This object indicates the maximum duration in milliseconds 
            to send delay signal. This object can only take effect when 
            h3cVoAIfEMCfgSignalMode is set to 'delayDial'."
        ::= { h3cVoAnalogIfEMTimerEntry 10 }

    h3cVoAIfEMTimerSubLine OBJECT-TYPE
        SYNTAX OCTET STRING
        MAX-ACCESS read-only
        STATUS current
        DESCRIPTION
            "This object indicates the port subscriber line name."
        ::= { h3cVoAnalogIfEMTimerEntry 11 }
    
END

-- =====================================================================
-- Copyright (c) 2004-2015 Hangzhou H3C Tech. Co., Ltd. All rights reserved.
--
-- Description:
--      This MIB module is for configuring and monitoring VSAN (Virtual
--      Storage Area Network) and domain management related entities.
-- Reference:
-- Version: V1.2
-- History:
--   V1.0 Initial version created by qiaoxinghua 2013-02-27
--   V1.1 Added h3cVsanDmDomainIdChangeNotify and
--        h3cVsanDmDomainIdChangeNotifyEnable by qiaoxinghua 2014-3-4
--   V1.2 Added h3cVsanName and h3cVsanWorkingMode
--        to h3cVsanTable by chengzhipeng 2014-05-09
--        Added h3cVsanFcIdTable and h3cVsanFcIdPersistencyTable by wangyuqiang 2014-07-25
-- =====================================================================
H3C-VSAN-MIB DEFINITIONS ::= BEGIN

IMPORTS
    OBJECT-TYPE, MODULE-IDENTITY, NOTIFICATION-TYPE, Counter32,
    Integer32
        FROM SNMPv2-SMI
    RowStatus, TruthValue
        FROM SNMPv2-TC
    SnmpAdminString
        FROM SNMP-FRAMEWORK-MIB
    H3cFcVsanIndex, H3cFcNameIdOrZero, H3cFcDomainPriority, H3cFcDomainId,
    H3cFcNameId, H3cFcAddressId, H3cFcDomainIdOrZero, H3cFcDmState, H3cFcDomainIdList
        FROM H3C-FC-TC-MIB
    ifIndex
        FROM IF-MIB
    h3cCommon
        FROM HUAWEI-3COM-OID-MIB;

h3cSan MODULE-IDENTITY
    LAST-UPDATED   "201407251840Z"
    ORGANIZATION
        "Hangzhou H3C Tech. Co., Ltd."
    CONTACT-INFO
        "Platform Team Hangzhou H3C Tech. Co., Ltd.
         Hai-Dian District Beijing P.R. China
         http://www.h3c.com
         Zip:100085
        "
    DESCRIPTION
        "This MIB module is for configuring and monitoring VSAN
         and domain management related entities."
    REVISION       "201407251840Z"
    DESCRIPTION
        "Added h3cVsanFcIdTable and h3cVsanFcIdPersistencyTable."
    REVISION       "201405091840Z"
    DESCRIPTION
        "Added h3cVsanName and h3cVsanWorkingMode."
    REVISION       "201403041550Z"
    DESCRIPTION
        "Added h3cVsanDmDomainIdChangeNotify and
         h3cVsanDmDomainIdChangeNotifyEnable."
    REVISION       "201302280940Z"
    DESCRIPTION
        "Initial version of this MIB module."

    ::= { h3cCommon 127 }

--
-- Node definitions
--
h3cVsan OBJECT IDENTIFIER ::= { h3cSan 1 }

h3cVsanMibObjects OBJECT IDENTIFIER ::= { h3cVsan 1 }

h3cVsanDmConfiguration OBJECT IDENTIFIER ::= { h3cVsanMibObjects 1 }

-- VSAN Table
h3cVsanTable  OBJECT-TYPE
    SYNTAX      SEQUENCE OF H3cVsanEntry
    MAX-ACCESS  not-accessible
    STATUS      current
    DESCRIPTION
        "A table contains all the VSANs configured on the device.  It can
         be used to manage and monitor the VSANs on local device."
    ::= { h3cVsanDmConfiguration 1 }

h3cVsanEntry OBJECT-TYPE
    SYNTAX      H3cVsanEntry
    MAX-ACCESS  not-accessible
    STATUS      current
    DESCRIPTION
        "An entry that contains information about a VSAN in the h3cVsanTable."
    INDEX { h3cVsanIndex }
    ::= { h3cVsanTable 1 }

H3cVsanEntry ::=
    SEQUENCE {
        h3cVsanIndex
            H3cFcVsanIndex,
        h3cVsanCoreSwitchName
            H3cFcNameIdOrZero,
        h3cVsanRowStatus
            RowStatus,
        h3cVsanName
            SnmpAdminString,
        h3cVsanWorkingMode
            Integer32
       }

h3cVsanIndex OBJECT-TYPE
    SYNTAX      H3cFcVsanIndex
    MAX-ACCESS  accessible-for-notify
    STATUS      current
    DESCRIPTION
        "The identifier of the VSAN."
    ::= { h3cVsanEntry 1 }

h3cVsanCoreSwitchName OBJECT-TYPE
    SYNTAX      H3cFcNameIdOrZero (SIZE(8 | 16))
    MAX-ACCESS  read-only
    STATUS      current
    DESCRIPTION
        "The Core Switch_Name of the VSAN, which is indicated by
         the switch's WWN(World Wide Name)."
    ::= { h3cVsanEntry 2 }

h3cVsanRowStatus OBJECT-TYPE
    SYNTAX      RowStatus
    MAX-ACCESS  read-create
    STATUS      current
    DESCRIPTION
        "RowStatus. Now only three states are supported:
         createAndGo, active, and destroy."
    ::= { h3cVsanEntry 3 }

h3cVsanName OBJECT-TYPE
    SYNTAX      SnmpAdminString(SIZE(0..32))
    MAX-ACCESS  read-create
    STATUS      current
    DESCRIPTION
        "The name of the VSAN.
         The default value of this object will be the
         string 'VSANxxxx' where xxxx is value of VSAN index
         expressed as 4 digits.  For example, if VSAN index is
         10, the default value of this object is 'VSAN0010'."
    ::= { h3cVsanEntry 4 }

h3cVsanWorkingMode OBJECT-TYPE
    SYNTAX      Integer32
    MAX-ACCESS  read-create
    STATUS      current
    DESCRIPTION
        "This object specifies the working modes the VSAN supports.
         The object has three available values:
         1: non-FCoE mode.
         2: FCF mode.
         3: NPV mode.

         The working mode of VSAN 4079 is always non-FCoE mode and cannot be
         converted.
         If the switch mode is not FCF-NPV mode, then the 'SET' operation
         on this object results in error.
         When creating a VSAN, the 'SET' operation including this object
         results in error.
         When the switch mode is FCF mode, working modes of all user VSANs
         are FCF mode.
         When the switch mode is NPV mode, working modes of all user VSANs
         are NPV mode.
         When the switch mode is FCF-NPV mode, the default working mode of
         a user VSAN is NPV mode.  If a VSAN has been created, the working mode
         can be converted from NPV mode to FCF mode, or vice versa."
    ::= { h3cVsanEntry 5 }

-- DM Configuration
h3cVsanDmTable     OBJECT-TYPE
    SYNTAX      SEQUENCE OF H3cVsanDmEntry
    MAX-ACCESS  not-accessible
    STATUS      current
    DESCRIPTION
        "A table contains domain management related configurations
         and information of VSANs.
         An entry in this table is created when corresponding VSAN
         is created, as well as deleted when the VSAN is deleted."
    ::= { h3cVsanDmConfiguration 2 }

h3cVsanDmEntry  OBJECT-TYPE
    SYNTAX      H3cVsanDmEntry
    MAX-ACCESS  not-accessible
    STATUS      current
    DESCRIPTION
        "An entry of domain management related configurations
         and information of a specified VSAN."
    INDEX { h3cVsanIndex }
    ::= { h3cVsanDmTable 1}

H3cVsanDmEntry ::=
    SEQUENCE {
              h3cVsanDmDomainConfigureEnable     TruthValue,
              h3cVsanDmFabricNameConfigured      H3cFcNameIdOrZero,
              h3cVsanDmPriorityConfigured        H3cFcDomainPriority,
              h3cVsanDmAllowedDomainIdList       H3cFcDomainIdList,
              h3cVsanDmDomainIdConfigured        H3cFcDomainIdOrZero,
              h3cVsanDmDomainIdTypeConfigured    INTEGER,
              h3cVsanDmAutoReconfigureEnable     TruthValue,
              h3cVsanDmDomainRestart             INTEGER,
              h3cVsanDmState                     H3cFcDmState,
              h3cVsanDmDomainIdAssigned          H3cFcDomainIdOrZero,
              h3cVsanDmPrincipalSwitchWWN        H3cFcNameId,
              h3cVsanDmLocalSwitchWWN            H3cFcNameId,
              h3cVsanDmPrincipalSwRunPriority    H3cFcDomainPriority,
              h3cVsanDmLocalSwRunPriority        H3cFcDomainPriority,
              h3cVsanDmPrincipalSwSlctCnt        Counter32,
              h3cVsanDmLocalPrincipalSwSlctCnt   Counter32,
              h3cVsanDmBFCnt                     Counter32,
              h3cVsanDmRCFCnt                    Counter32
             }

h3cVsanDmDomainConfigureEnable  OBJECT-TYPE
    SYNTAX          TruthValue
    MAX-ACCESS      read-write
    STATUS          current
    DESCRIPTION
        "To enable or disable the fabric configuration function
         in this VSAN.
         true:  enabled, the fabric will be built dynamically.
         false: disabled, the fabric should be built statically
                by manual configurations."
    DEFVAL          { true }
    ::= { h3cVsanDmEntry 1 }

h3cVsanDmFabricNameConfigured    OBJECT-TYPE
    SYNTAX          H3cFcNameIdOrZero
    MAX-ACCESS      read-write
    STATUS          current
    DESCRIPTION
        "Specifies the fabric name in this VSAN, and will use a
         zero-length octet string as default value if not configured.
         The fabric name specified here takes effect only if the
         value of h3cVsanDmDomainConfigureEnable is 'false', and the
         same fabric name should be configured for all switches in
         this VSAN.
         If the value of h3cVsanDmDomainConfigureEnable is 'true',
         the principal switch WWN is used as fabric name.
         The value should be set to zero-length when canceling
         a configured fabric name."
    ::= { h3cVsanDmEntry 2 }

h3cVsanDmPriorityConfigured    OBJECT-TYPE
    SYNTAX          H3cFcDomainPriority
    MAX-ACCESS      read-write
    STATUS          current
    DESCRIPTION
        "Specifies the priority of a switch in this VSAN, which
         is used during principal switch selection to cause one
         Switch to be favored over another."
    DEFVAL         { 128 }
    ::= { h3cVsanDmEntry 3 }

h3cVsanDmAllowedDomainIdList    OBJECT-TYPE
    SYNTAX          H3cFcDomainIdList
    MAX-ACCESS      read-write
    STATUS          current
    DESCRIPTION
        "Specifies the list of domain IDs that are allowed in the
         VSAN, and the configuration has different meanings in
         different scenarios:

         1. Principal switch: Can only assign domains IDs within
            the allowed domain ID list.  If the allowed domain ID
            list configured does not include any of the already
            assigned domain IDs or manually configured domain IDs,
            the configuration will fail.

         2. Non-principal switch: The manually configured domain
            ID must be within the allowed domain ID list, or
            the configuration will fail.  Besides, the domain ID
            assigned by principal switch must within the allowed
            domain ID list, or the switch will refuse the assigned
            domain ID and isolate the upstream interface.  If the
            runtime domain ID for a switch is beyond the new
            configured ID list, the configuration will fail.
         The default value is a zero-length octet string.  If This
         value is set with zero-length, the configuration will be
         cancelled in this VSAN."
    ::= { h3cVsanDmEntry 4 }

h3cVsanDmDomainIdConfigured    OBJECT-TYPE
    SYNTAX          H3cFcDomainIdOrZero
    MAX-ACCESS      read-write
    STATUS          current
    DESCRIPTION
        "Used to configure or cancel a domain ID for a switch in
         this VSAN.

         When this value is not zero, the domain ID type should
         be specified together via h3cVsanDmDomainIdTypeConfigured,
         or the default value of preferred type will be taken.
         The zero value is used to cancel the domain ID configured,
         and then, there is no need to specify its type.

         When statically build a fabric, the configured domain ID
         is the actual domain ID of the switch.  If this object is
         not manually configured, the switch will isolate all of
         its E_ports in this VSAN no matter what domain ID type is
         configured.

         When dynamically build a fabric, the configured domain ID
         is desired by the switch, but the domain ID assigned to
         the switch may not be the desired one.
         If a non-principal switch fails to obtain any domain ID
         from the principal switch, the non-principal switch will
         isolate the upstream link.
         If a non-principal switch obtains a domain ID from the
         principal switch other than the desired one, different
         actions will be taken according to different domain ID
         type configured:
          - If configured static type, The non-principal switch
            will isolate the upstream link and refuse other domain
            IDs assigned by the principal switch.
          - If configured preferred type, the non-principal switch
            will use the domain ID assigned by the principal switch."
    DEFVAL         { 0 }
    ::= { h3cVsanDmEntry 5 }

h3cVsanDmDomainIdTypeConfigured    OBJECT-TYPE
    SYNTAX          INTEGER {
                             static(1),
                             preferred(2)
                            }
    MAX-ACCESS      read-write
    STATUS          current
    DESCRIPTION
         "Specifies the type of configured domain ID, which can be
          static type or preferred type."
    DEFVAL         { preferred }
    ::= { h3cVsanDmEntry 6 }

h3cVsanDmAutoReconfigureEnable    OBJECT-TYPE
    SYNTAX          TruthValue
    MAX-ACCESS      read-write
    STATUS          current
    DESCRIPTION
        "Used to specify whether a disruptive reconfiguration will
         be automatically performed when the domain ID lists overlaps
         in fabric merging.

         The fabric reconfiguration function takes effect only when
         the value of h3cVsanDmDomainConfigureEnable is 'true'."
    DEFVAL         { false }
    ::= { h3cVsanDmEntry 7 }

h3cVsanDmDomainRestart    OBJECT-TYPE
    SYNTAX          INTEGER  {
                              noOperation(1),
                              nonDisruptive(2),
                              disruptive(3)
                             }
    MAX-ACCESS      read-write
    STATUS          current
    DESCRIPTION
        "Used to manually trigger a disruptive or non-disruptive
         reconfiguration of the fabric."
    DEFVAL         { noOperation }
    ::= { h3cVsanDmEntry 8 }

h3cVsanDmState         OBJECT-TYPE
    SYNTAX          H3cFcDmState
    MAX-ACCESS      read-only
    STATUS          current
    DESCRIPTION
        "Indicates the managing state of the domain in this VSAN."
    ::= { h3cVsanDmEntry 9 }

h3cVsanDmDomainIdAssigned    OBJECT-TYPE
    SYNTAX          H3cFcDomainIdOrZero
    MAX-ACCESS      read-only
    STATUS          current
    DESCRIPTION
        "Indicates the Domain ID of the local switch in this
         VSAN or zero if no Domain ID has been assigned."
    ::= { h3cVsanDmEntry 10 }

h3cVsanDmPrincipalSwitchWWN    OBJECT-TYPE
    SYNTAX          H3cFcNameId
    MAX-ACCESS      read-only
    STATUS          current
    DESCRIPTION
        "Indicates the WWN of the principal switch in this VSAN,
         or zero-length string if the identity of the principal
         switch is unknown."
    ::= { h3cVsanDmEntry 11 }

h3cVsanDmLocalSwitchWWN       OBJECT-TYPE
    SYNTAX          H3cFcNameId
    MAX-ACCESS      read-only
    STATUS          current
    DESCRIPTION
        "Indicates the WWN of the local switch in this VSAN."
    ::= { h3cVsanDmEntry 12 }

h3cVsanDmPrincipalSwRunPriority    OBJECT-TYPE
    SYNTAX          H3cFcDomainPriority
    MAX-ACCESS      read-only
    STATUS          current
    DESCRIPTION
        "Indicates the running priority of the principal switch in
         this VSAN."
    ::= { h3cVsanDmEntry 13 }

h3cVsanDmLocalSwRunPriority    OBJECT-TYPE
    SYNTAX          H3cFcDomainPriority
    MAX-ACCESS      read-only
    STATUS          current
    DESCRIPTION
        "Indicates the running priority of the local switch in
         this VSAN."
    ::= { h3cVsanDmEntry 14 }

h3cVsanDmPrincipalSwSlctCnt    OBJECT-TYPE
    SYNTAX          Counter32
    MAX-ACCESS      read-only
    STATUS          current
    DESCRIPTION
        "The times that local switch has participated in principal
         switch selection in this VSAN."
    ::= { h3cVsanDmEntry 15 }

h3cVsanDmLocalPrincipalSwSlctCnt    OBJECT-TYPE
    SYNTAX          Counter32
    MAX-ACCESS      read-only
    STATUS          current
    DESCRIPTION
        "The times that local switch was elected as principal switch
         in this VSAN."
    ::= { h3cVsanDmEntry 16 }

h3cVsanDmBFCnt   OBJECT-TYPE
    SYNTAX          Counter32
    MAX-ACCESS      read-only
    STATUS          current
    DESCRIPTION
        "The times that local switch has participated in a BF(Build
         Fabric) process in this VSAN."
    ::= { h3cVsanDmEntry 17 }

h3cVsanDmRCFCnt    OBJECT-TYPE
    SYNTAX          Counter32
    MAX-ACCESS      read-only
    STATUS          current
    DESCRIPTION
        "The times that local switch has participated in a RCF
         (Reconfigure Fabric) process in this VSAN."
    ::= { h3cVsanDmEntry 18 }

-- DM If Configuration
h3cVsanDmIfConfigTable  OBJECT-TYPE
    SYNTAX      SEQUENCE OF H3cVsanDmIfConfigEntry
    MAX-ACCESS  not-accessible
    STATUS      current
    DESCRIPTION
        "A table contains the FC(Fibre Channel) related interface
         configurations about domain management of a VSAN."
    ::= { h3cVsanDmConfiguration 3 }

h3cVsanDmIfConfigEntry  OBJECT-TYPE
    SYNTAX      H3cVsanDmIfConfigEntry
    MAX-ACCESS  not-accessible
    STATUS      current
    DESCRIPTION
        "An entry used for managing the FC related interface
         configurations about domain management of a VSAN.
         An entry can be created when any object in this table is
         set to non-default value, and be deleted when the objects
         in this table are set to default value."
    INDEX { ifIndex,
            h3cVsanIndex }
    ::= { h3cVsanDmIfConfigTable 1}

H3cVsanDmIfConfigEntry ::=
    SEQUENCE {
              h3cVsanDmIfConfigRcfReject
                TruthValue
             }

h3cVsanDmIfConfigRcfReject  OBJECT-TYPE
    SYNTAX          TruthValue
    MAX-ACCESS      read-write
    STATUS          current
    DESCRIPTION
        "Used to specify whether the RCF(Reconfigure Fabric) requests
         received in this VSAN should be rejected.
          - true:  the received RCF will be rejected.
          - false: the received RCF will be accepted."
    DEFVAL          { false }
    ::= { h3cVsanDmIfConfigEntry 1 }


-- VSAN FC ID Table

h3cVsanFcIdTable OBJECT-TYPE
    SYNTAX          SEQUENCE OF H3cVsanFcIdEntry
    MAX-ACCESS      not-accessible
    STATUS          current
    DESCRIPTION
        "This table contains FC ID information for each VSAN."
    ::= { h3cVsanDmConfiguration 4 }

h3cVsanFcIdEntry OBJECT-TYPE
    SYNTAX          H3cVsanFcIdEntry
    MAX-ACCESS      not-accessible
    STATUS          current
    DESCRIPTION
        "This entry provides FC ID information for a VSAN."
    INDEX  { h3cVsanIndex }
    ::= { h3cVsanFcIdTable 1 }

H3cVsanFcIdEntry ::= SEQUENCE {
        h3cVsanFreeFcIds                    Counter32,
        h3cVsanAssignedFcIds                Counter32,
        h3cVsanFcIdPersistency              TruthValue,
        h3cVsanFcIdPurge                    INTEGER
}

h3cVsanFreeFcIds OBJECT-TYPE
        SYNTAX      Counter32
        MAX-ACCESS  read-only
        STATUS      current
        DESCRIPTION
               "The number of FC IDs that are unassigned on this VSAN."
        ::= { h3cVsanFcIdEntry 1 }

h3cVsanAssignedFcIds OBJECT-TYPE
        SYNTAX      Counter32
        MAX-ACCESS  read-only
        STATUS      current
        DESCRIPTION
               "The number of FC IDs that are assigned on this VSAN."
        ::= { h3cVsanFcIdEntry 2 }

h3cVsanFcIdPersistency OBJECT-TYPE
    SYNTAX          TruthValue
    MAX-ACCESS      read-write
    STATUS          current
    DESCRIPTION
           "Enable or disable FC ID persistency on this VSAN.

           If this object is set to 'true', then all the FC ID
           assigned on this VSAN are made persistent on this VSAN, and
           all login entries automatically created in the
           h3cVsanFcIdPersistencyTable with h3cVsanFcIdPersistencyWwn
           equal to either WWN of the logged-in Nx_Port for which the
           FC ID was assigned and h3cVsanFcIdPersistencyType equal
           to 'dynamic'.

           If this object is set to 'false', then all the entries on
           this VSAN in dmFcIdPersistencyTable are deleted."
    DEFVAL { true }
    ::= { h3cVsanFcIdEntry 3 }

h3cVsanFcIdPurge OBJECT-TYPE
        SYNTAX      INTEGER {
                      noOp (1),
                      enable (2)
                    }
        MAX-ACCESS  read-write
        STATUS      current
        DESCRIPTION
               "This object is used to purge the FC ID
                persistency database on this VSAN.

               If the value of this object is 'enable', then
               all entries on this VSAN in the h3cVsanFcIdPersistencyTable with
               h3cVsanFcIdPersistencyType is 'dynamic' and
               h3cVsanFcIdPersistencyUsed is 'false' are
               purged from the persistency database."
        ::= { h3cVsanFcIdEntry 4 }

-- FC ID Persistency Table

h3cVsanFcIdPersistencyTable OBJECT-TYPE
    SYNTAX          SEQUENCE OF H3cVsanFcIdPersistencyEntry
    MAX-ACCESS      not-accessible
    STATUS          current
    DESCRIPTION
           "This table contains the FC IDs which are in the FC ID
           persistency database of each VSAN.

           If the FC ID persistency is enabled, FC devices would get
           the same FC IDs even if they disappear and appear again.

           The FC ID persistency database contains information
           about the FC IDs which are assigned to FC devices
           either statically (configured) or dynamically.

           An entry is automatically created when a FC ID is
           assigned and h3cVsanFcIdPersistency is 'true' on this VSAN.

           The entries can also be created and deleted via
           the h3cVsanFcIdPersistencyRowStatus object.

           If the object h3cVsanFcIdPurge is set to 'enable', an entry is
           deleted if its h3cVsanFcIdPersistencyType is 'dynamic' and
           h3cVsanFcIdPersistencyUsed is 'false'.

           If the h3cVsanFcIdPersistency is 'false', no
           entry can be created.

           If the h3cVsanDmDomainIdAssigned is changed on a VSAN, then all the
           entries on that VSAN in this table are deleted."
    ::= { h3cVsanDmConfiguration 5 }

h3cVsanFcIdPersistencyEntry OBJECT-TYPE
    SYNTAX          H3cVsanFcIdPersistencyEntry
    MAX-ACCESS      not-accessible
    STATUS          current
    DESCRIPTION
        "This entry provides FC ID persistency information for a VSAN."
    INDEX  { h3cVsanIndex, h3cVsanFcIdPersistencyWwn }
    ::= { h3cVsanFcIdPersistencyTable 1 }

H3cVsanFcIdPersistencyEntry ::= SEQUENCE {
       h3cVsanFcIdPersistencyWwn           H3cFcNameId,
       h3cVsanFcIdPersistencyFcId          H3cFcAddressId,
       h3cVsanFcIdPersistencyUsed          TruthValue,
       h3cVsanFcIdPersistencyType          INTEGER,
       h3cVsanFcIdPersistencyRowStatus     RowStatus
}

h3cVsanFcIdPersistencyWwn OBJECT-TYPE
        SYNTAX      H3cFcNameId
        MAX-ACCESS  not-accessible
        STATUS      current
        DESCRIPTION
               "This is either the port WWN of the FC device if the
               local port is an F_port.  The local port is the port on
               the local device to which the FC device is attached."
        ::= { h3cVsanFcIdPersistencyEntry 1 }

h3cVsanFcIdPersistencyFcId OBJECT-TYPE
        SYNTAX      H3cFcAddressId
        MAX-ACCESS  read-create
        STATUS      current
        DESCRIPTION
               "The FC ID assigned for this WWN on this VSAN.

               This object cannot be changed if either the value of
               h3cVsanFcIdPersistencyUsed is 'true' or if the
               new value being set is already assigned on this VSAN."
        ::= { h3cVsanFcIdPersistencyEntry 2 }

h3cVsanFcIdPersistencyUsed OBJECT-TYPE
    SYNTAX          TruthValue
    MAX-ACCESS      read-only
    STATUS          current
    DESCRIPTION
           "This object indicates this FC ID is used or not."
    ::= { h3cVsanFcIdPersistencyEntry 3 }

h3cVsanFcIdPersistencyType OBJECT-TYPE
    SYNTAX      INTEGER {
                   static (1),
                   dynamic (2)
                }
    MAX-ACCESS  read-create
    STATUS      current
    DESCRIPTION
           "The type of persistency of this FC ID."
    DEFVAL { static }
    ::= { h3cVsanFcIdPersistencyEntry 4 }

h3cVsanFcIdPersistencyRowStatus OBJECT-TYPE
    SYNTAX      RowStatus
    MAX-ACCESS  read-create
    STATUS      current
    DESCRIPTION
           "An entry cannot be created if h3cVsanFcIdPersistency is 'false'.
            An entry cannot be deleted if h3cVsanFcIdPersistencyUsed is 'true'."
    ::= { h3cVsanFcIdPersistencyEntry 5 }

-- DM Information
h3cVsanDmInformation  OBJECT IDENTIFIER ::= { h3cVsanMibObjects 2 }

h3cVsanDmDatabaseTable OBJECT-TYPE
    SYNTAX SEQUENCE OF H3cVsanDmDatabaseEntry
    MAX-ACCESS         not-accessible
    STATUS             current
    DESCRIPTION
        "A table specifies the information of the switch
         about all the Domain IDs which have been assigned
         in each of the VSANs."
    ::= { h3cVsanDmInformation 1 }

h3cVsanDmDatabaseEntry OBJECT-TYPE
    SYNTAX      H3cVsanDmDatabaseEntry
    MAX-ACCESS  not-accessible
    STATUS      current
    DESCRIPTION
        "An object in the h3cVsanDmDatabaseTable contains one
         Domain ID and the corresponding WWN of the switch in
         one VSAN."
    INDEX { h3cVsanIndex,
            h3cVsanDmDatabaseDomainId }
    ::= { h3cVsanDmDatabaseTable 1 }

H3cVsanDmDatabaseEntry ::=
    SEQUENCE {
        h3cVsanDmDatabaseDomainId
          H3cFcDomainId,
        h3cVsanDmDatabaseSwitchWWN
          H3cFcNameId
       }

h3cVsanDmDatabaseDomainId OBJECT-TYPE
    SYNTAX          H3cFcDomainId
    MAX-ACCESS      not-accessible
    STATUS          current
    DESCRIPTION
        "The Domain ID which has been assigned."
    ::= { h3cVsanDmDatabaseEntry 1 }

h3cVsanDmDatabaseSwitchWWN OBJECT-TYPE
    SYNTAX          H3cFcNameId
    MAX-ACCESS      read-only
    STATUS          current
    DESCRIPTION
        "The WWN of the switch to which the corresponding
         Domain ID has been assigned in the particular VSAN."
    ::= { h3cVsanDmDatabaseEntry 2 }

h3cVsanDmIfInfoTable OBJECT-TYPE
    SYNTAX SEQUENCE OF H3cVsanDmIfInfoEntry
    MAX-ACCESS         not-accessible
    STATUS             current
    DESCRIPTION
        "A table specifies the information of an interface
         in each of the VSANs."
    ::= { h3cVsanDmInformation 2 }

h3cVsanDmIfInfoEntry OBJECT-TYPE
    SYNTAX      H3cVsanDmIfInfoEntry
    MAX-ACCESS  not-accessible
    STATUS      current
    DESCRIPTION
        "A conceptual row in the h3cVsanDmIfInfoTable indicates the
         role information of the interface in the particular VSAN."
    INDEX { ifIndex,
            h3cVsanIndex }
    ::= { h3cVsanDmIfInfoTable 1 }

H3cVsanDmIfInfoEntry ::=
    SEQUENCE {
          h3cVsanDmIfInfoRole
            INTEGER
          }

h3cVsanDmIfInfoRole OBJECT-TYPE
    SYNTAX INTEGER {
                      nonPrincipal(1),
                      principalUpstream(2),
                      principalDownstream(3),
                      isolated(4),
                      unknown(5)
                   }
    MAX-ACCESS      read-only
    STATUS          current
    DESCRIPTION
        "The role of the interface in the VSAN.  The value specifications
         are listed as follows:

         nonPrincipal         - The state of the interface is not principal
                                interface in the VSAN.
         principalUpstream    - The state of the interface is upstream
                                principal interface in the VSAN.
         principalDownstream  - The state of the interface is downstream
                                principal interface in the VSAN.
         isolated             - The state of the interface is isolated in
                                the VSAN.
         unknown              - The state of the interface is unknown in
                                the VSAN."
    ::= { h3cVsanDmIfInfoEntry 1 }

-- DM Notifications
h3cVsanDmNotifications OBJECT IDENTIFIER ::= { h3cVsanMibObjects 3 }
h3cVsanDmNotificationPrefix  OBJECT IDENTIFIER
    ::= { h3cVsanDmNotifications 0 }

h3cVsanDmDomainIdNotAssignedNotify NOTIFICATION-TYPE
    OBJECTS {h3cVsanIndex,
             h3cVsanDmLocalSwitchWWN}
    STATUS current
    DESCRIPTION
        "This event will be triggered if a Domain ID is not
         assigned or configured, then the E_ports may be isolated
         in the VSAN. The conditions are listed as follows:

         1. If the switch has enabled the fabric configuration and
            a request for a configured static Domain ID is rejected
            or no other Domain ID is assigned, the E_ports will be
            isolated in the particular VSAN.
         2. If the switch does not enable the fabric configuration
            and a Domain ID is not configured, all of its E_ports
            will be isolated in the particular VSAN.

         The notification contains the WWN of the Switch and
         the index of the VSAN in which the event occurred."
   ::= { h3cVsanDmNotificationPrefix 1 }

h3cVsanDmNewPrincipalSwitchNotify NOTIFICATION-TYPE
    OBJECTS {h3cVsanIndex,
             h3cVsanDmLocalSwitchWWN}
    STATUS current
    DESCRIPTION
        "If a switch becomes the new Principal Switch in a VSAN, this
         notification is sent immediately after the election.

         The notification contains the WWN of the new Principal Switch
         and the index of the VSAN in which the transition occurred."
   ::= { h3cVsanDmNotificationPrefix 2 }

h3cVsanDmFabricChangeNotify NOTIFICATION-TYPE
    OBJECTS         { h3cVsanIndex }
    STATUS          current
    DESCRIPTION
        "This event will be triggered if a switch sends or receives a
         Build Fabric (BF) or a Reconfigure Fabric (RCF) message in a
         VSAN.

         The conditions a switch can receive or send a BF or a RCF are
         listed as follows:
         1. Two isolated fabrics in a VSAN merge into one fabric.  If
            the Domain ID lists do not overlap, the sent or received
            message is BF, other cases, it is RCF.
         2. If an upstream principal link which connects to principal
            switch and other switches become disconnected, the sent or
            received message is BF.
         3. A BF or RCF process is triggered manually by configuration.
         The notification contains the index of the VSAN in which a BF
         or a RCF was sent or received."
   ::= { h3cVsanDmNotificationPrefix 3 }

h3cVsanDmDomainIdChangeNotify NOTIFICATION-TYPE
    OBJECTS         { h3cVsanIndex,
                      h3cVsanDmDomainIdAssigned,
                      h3cVsanDmLocalSwitchWWN
                    }
    STATUS          current
    DESCRIPTION
        "This event will be triggered if the Domain ID of the local switch
         changed in a VSAN."
    ::= { h3cVsanDmNotificationPrefix 4 }

h3cVsanDmNotificationSwitch  OBJECT IDENTIFIER
   ::= { h3cVsanDmNotifications 1 }

h3cVsanDmFabricChangeNotifyEnable OBJECT-TYPE
    SYNTAX          TruthValue
    MAX-ACCESS      read-write
    STATUS          current
    DESCRIPTION
        "Specifies whether the h3cVsanDmFabricChangeNotify can be sent
         when a BF or RCF message was sent or received by a switch."
    DEFVAL          { false }
    ::= { h3cVsanDmNotificationSwitch 1 }

h3cVsanDmDomainIdChangeNotifyEnable OBJECT-TYPE
    SYNTAX          TruthValue
    MAX-ACCESS      read-write
    STATUS          current
    DESCRIPTION
        "Specifies whether the h3cVsanDmDomainIdChangeNotify can be sent
         when the Domain ID of the local switch changed in a VSAN."
    DEFVAL          { false }
    ::= { h3cVsanDmNotificationSwitch 2 }
END

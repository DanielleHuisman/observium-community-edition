-- =============================================================================
-- Copyright (c) 2004-2015 Hangzhou H3C Tech. Co., Ltd. All rights reserved.
--
-- Description:
--   The file defines a MIB that provides WLAN application configuration information.
-- Reference:
-- Version: V1.0
-- History:
--   V1.0 2015-05-26 Initial version, created by lifei (Richard)
-- =============================================================================
H3C-WLAN-FLEXAPP-CFG-MIB DEFINITIONS ::= BEGIN

IMPORTS
        TruthValue,
        MacAddress
    FROM SNMPv2-TC
        MODULE-IDENTITY,
        NOTIFICATION-TYPE,
        OBJECT-TYPE,
        Integer32,
        IpAddress
    FROM SNMPv2-SMI
        h3cDot11
    FROM H3C-DOT11-REF-MIB;

h3cWlanFlexAppCFG MODULE-IDENTITY
    LAST-UPDATED "201505261800Z"        -- May 26, 2015 at 18:00 GMT
    ORGANIZATION
        "Hangzhou H3C Technologies Co., Ltd."
    CONTACT-INFO
        "Platform Team Hangzhou H3C Technologies Co., Ltd.
         Hai-Dian District Beijing P.R. China
         http://www.h3c.com
         Zip: 100085"
    DESCRIPTION
        "This MIB provides information about WLAN application configuration."
    REVISION "201505261800Z"        -- May 26, 2015 at 18:00 GMT
    DESCRIPTION
        "Added new nodes."
    ::= { h3cDot11 19 }
--
-- Node definitions
--

h3cWlanModuleConfigGroup OBJECT IDENTIFIER ::= { h3cWlanFlexAppCFG 1 }
--  Module Group has the following children:
--  h3cWlanModuleConfigTable          ::= { h3cWlanModuleConfigGroup 1 }
--  h3cWlanModuleInfoTable            ::= { h3cWlanModuleConfigGroup 2 }

h3cWlanIOTConfigGroup OBJECT IDENTIFIER ::= { h3cWlanFlexAppCFG 2 }
--  IOT Configure Group has the following children:
--  h3cWlanIOTConfigTable             ::= { h3cWlanIOTConfigGroup 1 }

h3cWlanModuleNotifyGroup OBJECT IDENTIFIER ::= { h3cWlanFlexAppCFG 3 }
--  Module Notify Group has the following children:
--  h3cWlanModuleTraps ::= { h3cWlanModuleNotifyGroup 0 }
--  h3cWlanModuleTrapVarObjects ::= { h3cWlanModuleNotifyGroup 1 }

h3cWlanBLEConfigGroup OBJECT IDENTIFIER ::= { h3cWlanFlexAppCFG 4 }
--  BLE Configure Group has the following children:
--  h3cWlanBLEConfigTable             ::= { h3cWlanBLEConfigGroup 1 }
--  h3cWlanBLEModuleConfigTable       ::= { h3cWlanBLEConfigGroup 2 }

h3cWlanAEConfigGroup OBJECT IDENTIFIER ::= { h3cWlanFlexAppCFG 5 }
--  AE Configure Group has the following children:
--  h3cWlanAEConfigTable               ::= { h3cWlanAEConfigGroup 1 }
--  h3cWlanAERadioConfigTable          ::= { h3cWlanAEConfigGroup 2 }

h3cWlanCommonConfigGroup OBJECT IDENTIFIER ::= { h3cWlanFlexAppCFG 6 }
--  common Configure Group has the following children:
--  h3cWlanCommonConfigTable             ::= { h3cWlanCommonConfigGroup 1 }

h3cWlanCUPIDConfigGroup OBJECT IDENTIFIER ::= { h3cWlanFlexAppCFG 7 }
--  CUPID Configure Group has the following children:
--  h3cWlanCUPIDConfigTable             ::= { h3cWlanCUPIDConfigGroup 1 }

h3cWlanFPConfigGroup OBJECT IDENTIFIER ::= { h3cWlanFlexAppCFG 8 }
--  fingerprint Configure Group has the following children:
--  h3cWlanFPConfigTable             ::= { h3cWlanFPConfigGroup 1 }

-- *****************************************************************************
-- *  h3cWlanModuleConfigTable Definition
-- *****************************************************************************
h3cWlanModuleConfigTable OBJECT-TYPE
    SYNTAX      SEQUENCE OF H3cWlanModuleConfigEntry
    MAX-ACCESS  not-accessible
    STATUS      current
    DESCRIPTION
        "Administrators must configure module parameters for a module to operate."
    ::= { h3cWlanModuleConfigGroup 1 }

h3cWlanModuleConfigEntry OBJECT-TYPE
    SYNTAX      H3cWlanModuleConfigEntry
    MAX-ACCESS  not-accessible
    STATUS      current
    DESCRIPTION
        "Each entry contains module configuration information."
    INDEX
        {
            h3cWlanAPSerialID,
            h3cWlanModuleID
        }
    ::= { h3cWlanModuleConfigTable 1 }

H3cWlanModuleConfigEntry ::= SEQUENCE
    {
        h3cWlanAPSerialID               OCTET STRING,
        h3cWlanModuleID                 Integer32,
        h3cWlanModuleType               INTEGER,
        h3cWlanModuleStatus             TruthValue,
        h3cWlanModuleReset              INTEGER,
        h3cWlanModuleRstFac             INTEGER,
        h3cWlanModuleUpWareStatus       TruthValue,
        h3cWlanModuleTxPower            Integer32,
        h3cWlanModuleManualUpdate          OCTET STRING
    }

h3cWlanAPSerialID OBJECT-TYPE
    SYNTAX      OCTET STRING(SIZE(0..127))
    MAX-ACCESS  not-accessible
    STATUS      current
    DESCRIPTION
        "This object represents the serial ID of an AP."
    ::= { h3cWlanModuleConfigEntry 1 }

h3cWlanModuleID OBJECT-TYPE
    SYNTAX      Integer32(1..65535)
    MAX-ACCESS  not-accessible
    STATUS      current
    DESCRIPTION
        "This object represents the module ID of a module."
    ::= { h3cWlanModuleConfigEntry 2 }

h3cWlanModuleType OBJECT-TYPE
    SYNTAX      INTEGER
        {
          none(0),
          ble(1),
          iot(2)
        }
    MAX-ACCESS  read-write
    STATUS      current
    DESCRIPTION
        "This object represents the type of a module."
    ::= { h3cWlanModuleConfigEntry 3 }

h3cWlanModuleStatus OBJECT-TYPE
    SYNTAX      TruthValue
    MAX-ACCESS  read-write
    STATUS      current
    DESCRIPTION
        "This object represents the enabled or disabled status of a module."
    ::= { h3cWlanModuleConfigEntry 4 }

h3cWlanModuleReset OBJECT-TYPE
    SYNTAX      INTEGER
    {
      none(0),
      reboot(1)
    }
    MAX-ACCESS  read-write
    STATUS      current
    DESCRIPTION
        "When read the value from the node
         none: Represents the module has been rebooted and the status of the module is normal.
         When write the value to the node
         reboot: Represents module rebooting.  Other values are not supported."
    ::= { h3cWlanModuleConfigEntry 5 }

h3cWlanModuleRstFac OBJECT-TYPE
    SYNTAX      INTEGER
    {
      none(0),
      restore(1)
    }
    MAX-ACCESS  read-write
    STATUS      current
    DESCRIPTION
        "When read the value from the node
         none: Represents the module has been restored and the status of the module is normal.
         When write the value to the node
         restore: Represents module restoring.  Other values are not supported."
    ::= { h3cWlanModuleConfigEntry 6 }

h3cWlanModuleUpWareStatus OBJECT-TYPE
    SYNTAX      TruthValue
    MAX-ACCESS  read-write
    STATUS      current
    DESCRIPTION
        "This object represents the enabled or disabled status of module auto update."
    ::= { h3cWlanModuleConfigEntry 7 }

h3cWlanModuleTxPower OBJECT-TYPE
    SYNTAX      Integer32(1..4)
    MAX-ACCESS  read-write
    STATUS      current
    DESCRIPTION
        "This object represents the packet transmit power."
    ::= { h3cWlanModuleConfigEntry 8 }

h3cWlanModuleManualUpdate OBJECT-TYPE
    SYNTAX       OCTET STRING
    MAX-ACCESS   read-write
    STATUS       current
    DESCRIPTION
        "This object represents the file path for module firmware updating."
    ::= { h3cWlanModuleConfigEntry 9 }

-- *****************************************************************************
-- * End of h3cWlanModuleConfigTable Definition
-- *****************************************************************************

-- *****************************************************************************
-- *  h3cWlanModuleInfoTable Definition
-- *****************************************************************************
h3cWlanModuleInfoTable OBJECT-TYPE
    SYNTAX      SEQUENCE OF H3cWlanModuleInfoEntry
    MAX-ACCESS  not-accessible
    STATUS      current
    DESCRIPTION
        "The table contains information about each module of an AP."
    ::= { h3cWlanModuleConfigGroup 2 }

h3cWlanModuleInfoEntry OBJECT-TYPE
    SYNTAX      H3cWlanModuleInfoEntry
    MAX-ACCESS  not-accessible
    STATUS      current
    DESCRIPTION
        "Each entry contains IOT module information."
    INDEX
        {
            h3cDot11IOTAPSerialID,
            h3cDot11IOTModuleID
        }
    ::= { h3cWlanModuleInfoTable 1 }

H3cWlanModuleInfoEntry ::= SEQUENCE
    {
        h3cDot11IOTAPSerialID          OCTET STRING,
        h3cDot11IOTModuleID            Integer32,
        h3cDot11IOTModuleType          INTEGER,
        h3cDot11IOTModuleModel         OCTET STRING,
        h3cDot11IOTModuleHwVersion     OCTET STRING,
        h3cDot11IOTModuleSwVersion     OCTET STRING,
        h3cDot11IOTModuleSerialId      OCTET STRING
    }

h3cDot11IOTAPSerialID OBJECT-TYPE
    SYNTAX      OCTET STRING(SIZE(0..127))
    MAX-ACCESS  not-accessible
    STATUS      current
    DESCRIPTION
        "This object represents the serial ID of an AP."
    ::= { h3cWlanModuleInfoEntry 1 }

h3cDot11IOTModuleID OBJECT-TYPE
    SYNTAX      Integer32(1..65535)
    MAX-ACCESS  not-accessible
    STATUS      current
    DESCRIPTION
        "This object represents a module."
    ::= { h3cWlanModuleInfoEntry 2 }

h3cDot11IOTModuleType OBJECT-TYPE
    SYNTAX      INTEGER
        {
          none(0),
          h3c(1),
          iot(2)
        }
    MAX-ACCESS  read-only
    STATUS      current
    DESCRIPTION
        "This object represents the type of a module."
    ::= { h3cWlanModuleInfoEntry 3 }

h3cDot11IOTModuleModel OBJECT-TYPE
    SYNTAX      OCTET STRING
    MAX-ACCESS  read-only
    STATUS      current
    DESCRIPTION
        "This object represents the model of a module."
    ::= { h3cWlanModuleInfoEntry 4 }

h3cDot11IOTModuleHwVersion OBJECT-TYPE
    SYNTAX      OCTET STRING
    MAX-ACCESS  read-only
    STATUS      current
    DESCRIPTION
        "This object represents the hardware version of a module."
    ::= { h3cWlanModuleInfoEntry 5 }

h3cDot11IOTModuleSwVersion OBJECT-TYPE
    SYNTAX      OCTET STRING
    MAX-ACCESS  read-only
    STATUS      current
    DESCRIPTION
        "This object represents the software version of a module."
    ::= { h3cWlanModuleInfoEntry 6 }

h3cDot11IOTModuleSerialId OBJECT-TYPE
    SYNTAX      OCTET STRING
    MAX-ACCESS  read-only
    STATUS      current
    DESCRIPTION
        "This object represents the sequence ID of a module."
    ::= { h3cWlanModuleInfoEntry 7 }

-- *****************************************************************************
-- * End of h3cDot11APModuleInfoTable Definition
-- *****************************************************************************

-- *****************************************************************************
-- *  h3cWlanIOTConfigTable Definition
-- *****************************************************************************
h3cWlanIOTConfigTable OBJECT-TYPE
    SYNTAX      SEQUENCE OF H3cWlanIOTConfigEntry
    MAX-ACCESS  not-accessible
    STATUS      current
    DESCRIPTION
        "Administrators must configure IOT parameters."
    ::= { h3cWlanIOTConfigGroup 1 }

h3cWlanIOTConfigEntry OBJECT-TYPE
    SYNTAX      H3cWlanIOTConfigEntry
    MAX-ACCESS  not-accessible
    STATUS      current
    DESCRIPTION
        "Each entry contains module configuration information."
    INDEX
        {
            h3cWlanIOTAPSerialID
        }
    ::= { h3cWlanIOTConfigTable 1 }

H3cWlanIOTConfigEntry ::= SEQUENCE
    {
        h3cWlanIOTAPSerialID            OCTET STRING,
        h3cWlanIOTEngineAdd             IpAddress,
        h3cWlanIOTEnginePort            Integer32
    }

h3cWlanIOTAPSerialID OBJECT-TYPE
    SYNTAX      OCTET STRING(SIZE(0..127))
    MAX-ACCESS  not-accessible
    STATUS      current
    DESCRIPTION
        "This object represents the serial ID of an AP."
    ::= { h3cWlanIOTConfigEntry 1 }

h3cWlanIOTEngineAdd OBJECT-TYPE
    SYNTAX      IpAddress
    MAX-ACCESS  read-write
    STATUS      current
    DESCRIPTION
        "This object represents the IPv4 address of the location server."
    ::= { h3cWlanIOTConfigEntry 2 }

h3cWlanIOTEnginePort OBJECT-TYPE
    SYNTAX      Integer32(0..65535)
    MAX-ACCESS  read-write
    STATUS      current
    DESCRIPTION
        "This object represents the UDP port to listen for IOT messages from the server."
    ::= { h3cWlanIOTConfigEntry 3 }

-- *****************************************************************************
-- * End of h3cWlanIOTConfigTable Definition
-- *****************************************************************************

-- *****************************************************************************
-- *  h3cWlanModuleTraps Definition
-- *****************************************************************************
-- AP Management Notification

h3cWlanModuleTraps OBJECT IDENTIFIER
    ::= { h3cWlanModuleNotifyGroup 0 }

h3cWlanModuleInsertTrap NOTIFICATION-TYPE
    OBJECTS
        {
            h3cWlanTrapAPMacAddress,
            h3cWlanTrapModuleID,
            h3cWlanTrapModulePhyType,
            h3cWlanTrapModuleModel,
            h3cWlanTrapModuleHwVersion,
            h3cWlanTrapModuleSwVersion,
            h3cWlanTrapModuleSequenceId
        }
    STATUS current
    DESCRIPTION
        "This notification will be generated when an IOT module is inserted."
    ::= { h3cWlanModuleTraps 1 }

h3cWlanModuleRomveTrap NOTIFICATION-TYPE
    OBJECTS
        {
            h3cWlanTrapAPMacAddress,
            h3cWlanTrapModuleID,
            h3cWlanTrapModulePhyType,
            h3cWlanTrapModuleModel,
            h3cWlanTrapModuleHwVersion,
            h3cWlanTrapModuleSwVersion,
            h3cWlanTrapModuleSequenceId
        }
    STATUS current
    DESCRIPTION
        "This notification will be generated when an IOT module is removed."
    ::= { h3cWlanModuleTraps 2 }

h3cWlanModuleMissMatch NOTIFICATION-TYPE
    OBJECTS
        {
            h3cWlanTrapAPMacAddress,
            h3cWlanTrapModuleID,
            h3cWlanTrapModuleCfgType,
            h3cWlanTrapModulePhyType,
            h3cWlanTrapModuleModel
        }
    STATUS current
    DESCRIPTION
        "This notification will be generated when the configured
         type doesn't match the module type."
    ::= { h3cWlanModuleTraps 3 }

-- AP Management Notification variable object

h3cWlanModuleTrapVarObjects OBJECT IDENTIFIER
    ::= { h3cWlanModuleNotifyGroup 1 }

h3cWlanTrapAPMacAddress OBJECT-TYPE
    SYNTAX      MacAddress
    MAX-ACCESS  accessible-for-notify
    STATUS      current
    DESCRIPTION
        "This object represents the MAC address of an AP."
    ::= {h3cWlanModuleTrapVarObjects 1 }

h3cWlanTrapModuleID OBJECT-TYPE
    SYNTAX      Integer32
    MAX-ACCESS  accessible-for-notify
    STATUS      current
    DESCRIPTION
        "This object represents the ID of a module."
    ::= { h3cWlanModuleTrapVarObjects 2 }

h3cWlanTrapModuleCfgType OBJECT-TYPE
    SYNTAX      INTEGER
        {
          none(0),
          h3c(1),
          iot(2)
        }
    MAX-ACCESS  accessible-for-notify
    STATUS      current
    DESCRIPTION
        "This object represents the configuration type of a module."
    ::= { h3cWlanModuleTrapVarObjects 3 }

h3cWlanTrapModulePhyType OBJECT-TYPE
    SYNTAX      INTEGER
        {
          none(0),
          h3c(1),
          iot(2)
        }
    MAX-ACCESS  accessible-for-notify
    STATUS      current
    DESCRIPTION
        "This object represents the physical type of a module."
    ::= { h3cWlanModuleTrapVarObjects 4 }

h3cWlanTrapModuleModel OBJECT-TYPE
    SYNTAX      OCTET STRING
    MAX-ACCESS  accessible-for-notify
    STATUS      current
    DESCRIPTION
        "This object represents the model of a module."
    ::= { h3cWlanModuleTrapVarObjects 5 }

h3cWlanTrapModuleHwVersion OBJECT-TYPE
    SYNTAX      OCTET STRING
    MAX-ACCESS  accessible-for-notify
    STATUS      current
    DESCRIPTION
        "This object represents the hardware version of a module."
    ::= { h3cWlanModuleTrapVarObjects 6 }

h3cWlanTrapModuleSwVersion OBJECT-TYPE
    SYNTAX      OCTET STRING
    MAX-ACCESS  accessible-for-notify
    STATUS      current
    DESCRIPTION
        "This object represents the software version of a module."
    ::= { h3cWlanModuleTrapVarObjects 7 }

h3cWlanTrapModuleSequenceId OBJECT-TYPE
    SYNTAX      OCTET STRING
    MAX-ACCESS  accessible-for-notify
    STATUS      current
    DESCRIPTION
        "This object represents the sequence ID of a module."
    ::= { h3cWlanModuleTrapVarObjects 8 }

-- *****************************************************************************
-- * End of h3cWlanModuleTraps Definition
-- *****************************************************************************

-- *****************************************************************************
-- *  h3cWlanBLEConfigTable Definition
-- *****************************************************************************
h3cWlanBLEConfigTable OBJECT-TYPE
    SYNTAX      SEQUENCE OF H3cWlanBLEConfigEntry
    MAX-ACCESS  not-accessible
    STATUS      current
    DESCRIPTION
        "Administrators must configure Bluetooth Low Energy (BLE) parameters."
    ::= { h3cWlanBLEConfigGroup 1 }

h3cWlanBLEConfigEntry OBJECT-TYPE
    SYNTAX      H3cWlanBLEConfigEntry
    MAX-ACCESS  not-accessible
    STATUS      current
    DESCRIPTION
        "Each entry contains BLE location configuration information."
    INDEX
        {
            h3cWlanBLEAPSerialID
        }
    ::= { h3cWlanBLEConfigTable 1 }

H3cWlanBLEConfigEntry ::= SEQUENCE
    {
        h3cWlanBLEAPSerialID            OCTET STRING,
        h3cWlanBLEStatus                TruthValue,
        h3cWlanBLEEngineAdd             IpAddress,
        h3cWlanBLEEnginePort            Integer32,
        h3cWlanBLEVendorPort            Integer32,
        h3cWlanBLERssiStatus            TruthValue,
        h3cWlanBLERssiThreshold         Integer32,
        h3cWlanBLEConnectPassword       OCTET STRING,
        h3cWlanBLECommandPassword       OCTET STRING,
        h3cWlanBLEReportStatus          TruthValue,
        h3cWlanBLEReportInterval        Integer32,
        h3cWlanBLEAgingTime             Integer32,
        h3cWlanBLERealTimeReportStatus  TruthValue,
        h3cWlanBLERealTimePrefix        OCTET STRING
    }

h3cWlanBLEAPSerialID OBJECT-TYPE
    SYNTAX      OCTET STRING(SIZE(0..127))
    MAX-ACCESS  not-accessible
    STATUS      current
    DESCRIPTION
        "This object represents the serial ID of an AP."
    ::= { h3cWlanBLEConfigEntry 1 }

h3cWlanBLEStatus OBJECT-TYPE
    SYNTAX      TruthValue
    MAX-ACCESS  read-write
    STATUS      current
    DESCRIPTION
        "This object represents the enabled or disabled status of BLE location."
    ::= { h3cWlanBLEConfigEntry 2 }

h3cWlanBLEEngineAdd OBJECT-TYPE
    SYNTAX      IpAddress
    MAX-ACCESS  read-write
    STATUS      current
    DESCRIPTION
        "This object represents the server's IPv4 address to which BLE messages are sent."
    ::= { h3cWlanBLEConfigEntry 3 }

h3cWlanBLEEnginePort OBJECT-TYPE
    SYNTAX      Integer32(0..65535)
    MAX-ACCESS  read-write
    STATUS      current
    DESCRIPTION
        "This object represents the UDP port of the location server."
    ::= { h3cWlanBLEConfigEntry 4 }

h3cWlanBLEVendorPort OBJECT-TYPE
    SYNTAX      Integer32(1..65535)
    MAX-ACCESS  read-write
    STATUS      current
    DESCRIPTION
        "This object represents the UDP port to listen for BLE messages from the server."
    ::= { h3cWlanBLEConfigEntry 5 }

h3cWlanBLERssiStatus OBJECT-TYPE
    SYNTAX      TruthValue
    MAX-ACCESS  read-write
    STATUS      current
    DESCRIPTION
        "This object represents the enabled or disabled status of BLE RSSI-based packet filtering."
    ::= { h3cWlanBLEConfigEntry 6 }

h3cWlanBLERssiThreshold OBJECT-TYPE
    SYNTAX      Integer32(5..255)
    MAX-ACCESS  read-write
    STATUS      current
    DESCRIPTION
        "This object represents the max RSSI value of clients' packets."
    ::= { h3cWlanBLEConfigEntry 7 }

h3cWlanBLEConnectPassword OBJECT-TYPE
    SYNTAX      OCTET STRING(SIZE(0|4))
    MAX-ACCESS  read-write
    STATUS      current
    DESCRIPTION
        "This object represents the BLE module connection password."
    ::= { h3cWlanBLEConfigEntry 8 }

h3cWlanBLECommandPassword OBJECT-TYPE
    SYNTAX      OCTET STRING(SIZE(0|12))
    MAX-ACCESS  read-write
    STATUS      current
    DESCRIPTION
        "This object represents the BLE module command password."
    ::= { h3cWlanBLEConfigEntry 9 }

h3cWlanBLEReportStatus OBJECT-TYPE
    SYNTAX      TruthValue
    MAX-ACCESS  read-write
    STATUS      current
    DESCRIPTION
        "This object represents the enabled or disabled status of BLE location reporting."
    ::= { h3cWlanBLEConfigEntry 10 }

h3cWlanBLEReportInterval OBJECT-TYPE
    SYNTAX      Integer32(1..86400)
    UNITS       "Second"
    MAX-ACCESS  read-write
    STATUS      current
    DESCRIPTION
        "This object represents the interval at which an AP sends BLE messages to the server."
    ::= { h3cWlanBLEConfigEntry 11 }

h3cWlanBLEAgingTime OBJECT-TYPE
    SYNTAX      Integer32(60..3600)
    UNITS       "Second"
    MAX-ACCESS  read-write
    STATUS      current
    DESCRIPTION
        "This object represents the aging time for iBeacon devices."
    ::= { h3cWlanBLEConfigEntry 12 }

h3cWlanBLERealTimeReportStatus OBJECT-TYPE
    SYNTAX      TruthValue
    MAX-ACCESS  read-write
    STATUS      current
    DESCRIPTION
        "This object represents the enabled or disabled status of BLE realtime reporting."
    ::= { h3cWlanBLEConfigEntry 13 }

h3cWlanBLERealTimePrefix OBJECT-TYPE
    SYNTAX      OCTET STRING(SIZE(0|8..18))
    MAX-ACCESS  read-write
    STATUS      current
    DESCRIPTION
        "This object represents the manufacturer prefix of BLE devices to
         be located.  The prefix must be an even number."
    ::= { h3cWlanBLEConfigEntry 14 }

-- *****************************************************************************
-- * End of h3cWlanBLEConfigTable Definition
-- *****************************************************************************

-- *****************************************************************************
-- *  h3cWlanBLEModuleConfigTable Definition
-- *****************************************************************************
h3cWlanBLEModuleConfigTable OBJECT-TYPE
    SYNTAX      SEQUENCE OF H3cWlanBLEModuleConfigEntry
    MAX-ACCESS  not-accessible
    STATUS      current
    DESCRIPTION
        "Administrators must configure BLE module parameters."
    ::= { h3cWlanBLEConfigGroup 2 }

h3cWlanBLEModuleConfigEntry OBJECT-TYPE
    SYNTAX      H3cWlanBLEModuleConfigEntry
    MAX-ACCESS  not-accessible
    STATUS      current
    DESCRIPTION
        "Each entry contains BLE module configuration information."
    INDEX
        {
            h3cWlanBLEModuleAPSerialID,
            h3cWlanBLEModuleID
        }
    ::= { h3cWlanBLEModuleConfigTable 1 }

H3cWlanBLEModuleConfigEntry ::= SEQUENCE
    {
        h3cWlanBLEModuleAPSerialID   OCTET STRING,
        h3cWlanBLEModuleID           Integer32,
        h3cWlanBLEAdvReportStatus    TruthValue,
        h3cWlanBLEAdvReportInterval  Integer32,
        h3cWlanBLEAdvUUID            OCTET STRING,
        h3cWlanBLEAdvMajorID         Integer32,
        h3cWlanBLEAdvMinorID         Integer32
    }

h3cWlanBLEModuleAPSerialID OBJECT-TYPE
    SYNTAX      OCTET STRING(SIZE(0..127))
    MAX-ACCESS  not-accessible
    STATUS      current
    DESCRIPTION
        "This object represents the serial ID of an AP."
    ::= { h3cWlanBLEModuleConfigEntry 1 }

h3cWlanBLEModuleID OBJECT-TYPE
    SYNTAX      Integer32(1..65535)
    MAX-ACCESS  not-accessible
    STATUS      current
    DESCRIPTION
        "This object represents the ID of a module."
    ::= { h3cWlanBLEModuleConfigEntry 2 }

h3cWlanBLEAdvReportStatus OBJECT-TYPE
    SYNTAX      TruthValue
    MAX-ACCESS  read-write
    STATUS      current
    DESCRIPTION
        "This object represents the enabled or disabled status of BLE advertisement reporting."
    ::= { h3cWlanBLEModuleConfigEntry 3 }

h3cWlanBLEAdvReportInterval OBJECT-TYPE
    SYNTAX      Integer32(50..1000)
    UNITS       "Second"
    MAX-ACCESS  read-write
    STATUS      current
    DESCRIPTION
        "This object represents the interval at which a BLE module sends advertisement packets."
    ::= { h3cWlanBLEModuleConfigEntry 4 }

h3cWlanBLEAdvUUID OBJECT-TYPE
    SYNTAX      OCTET STRING(SIZE(0|32))
    MAX-ACCESS  read-write
    STATUS      current
    DESCRIPTION
        "This object represents the UUID of BLE advertisement packets."
    ::= { h3cWlanBLEModuleConfigEntry 5 }

h3cWlanBLEAdvMajorID OBJECT-TYPE
    SYNTAX      Integer32(0..65535)
    MAX-ACCESS  read-write
    STATUS      current
    DESCRIPTION
        "This object represents the major ID of BLE advertisement packets."
    ::= { h3cWlanBLEModuleConfigEntry 6 }

h3cWlanBLEAdvMinorID OBJECT-TYPE
    SYNTAX      Integer32(0..65535)
    MAX-ACCESS  read-write
    STATUS      current
    DESCRIPTION
        "This object represents the minor ID of BLE advertisement packets."
    ::= { h3cWlanBLEModuleConfigEntry 7 }

-- *****************************************************************************
-- * End of h3cWlanBLEModuleConfigTable Definition
-- *****************************************************************************

-- *****************************************************************************
-- *  h3cWlanAEConfigTable Definition
-- *****************************************************************************
h3cWlanAEConfigTable OBJECT-TYPE
    SYNTAX      SEQUENCE OF H3cWlanAEConfigEntry
    MAX-ACCESS  not-accessible
    STATUS      current
    DESCRIPTION
        "Administrators must configure AeroScout (AE) parameters."
    ::= { h3cWlanAEConfigGroup 1 }

h3cWlanAEConfigEntry OBJECT-TYPE
    SYNTAX      H3cWlanAEConfigEntry
    MAX-ACCESS  not-accessible
    STATUS      current
    DESCRIPTION
        "Each entry contains AE location configuration information."
    INDEX
        {
            h3cWlanAEAPSerialID
        }
    ::= { h3cWlanAEConfigTable 1 }

H3cWlanAEConfigEntry ::= SEQUENCE
    {
        h3cWlanAEAPSerialID          OCTET STRING,
        h3cWlanAEStatus              TruthValue,
        h3cWlanAEEngineAddr          IpAddress,
        h3cWlanAEEnginePort          Integer32,
        h3cWlanAEVendorPort          Integer32,
        h3cWlanAETimeStamp           INTEGER,
        h3cWlanAEVersion             INTEGER,
        h3cWlanAETagMultiAddr        MacAddress,
        h3cWlanAEEngineDetection     INTEGER,
        h3cWlanAEReportMode          INTEGER
    }

h3cWlanAEAPSerialID OBJECT-TYPE
    SYNTAX      OCTET STRING(SIZE(0..127))
    MAX-ACCESS  not-accessible
    STATUS      current
    DESCRIPTION
        "This object represents the serial ID of an AP."
    ::= { h3cWlanAEConfigEntry 1 }

h3cWlanAEStatus OBJECT-TYPE
    SYNTAX      TruthValue
    MAX-ACCESS  read-write
    STATUS      current
    DESCRIPTION
        "This object represents the enabled or disabled status of AE location."
    ::= { h3cWlanAEConfigEntry 2 }

h3cWlanAEEngineAddr OBJECT-TYPE
    SYNTAX      IpAddress
    MAX-ACCESS  read-write
    STATUS      current
    DESCRIPTION
        "This object represents the server's IPv4 address to which AE messages are sent."
    ::= { h3cWlanAEConfigEntry 3 }

h3cWlanAEEnginePort OBJECT-TYPE
    SYNTAX      Integer32(0..65535)
    MAX-ACCESS  read-write
    STATUS      current
    DESCRIPTION
        "This object represents the UDP port of the location server."
    ::= { h3cWlanAEConfigEntry 4 }

h3cWlanAEVendorPort OBJECT-TYPE
    SYNTAX      Integer32(1..65535)
    MAX-ACCESS  read-write
    STATUS      current
    DESCRIPTION
        "This object represents the UDP port to listen for AE messages from the server."
    ::= { h3cWlanAEConfigEntry 5 }

h3cWlanAETimeStamp OBJECT-TYPE
    SYNTAX      INTEGER
        {
          absolute(1),
          relative(2)
        }
    MAX-ACCESS  read-write
    STATUS      current
    DESCRIPTION
        "This object represents the enabled or disabled status of timestamp."
    ::= { h3cWlanAEConfigEntry 6 }

h3cWlanAEVersion OBJECT-TYPE
    SYNTAX      INTEGER
        {
          v2(2),
          v3(3)
        }
    MAX-ACCESS  read-write
    STATUS      current
    DESCRIPTION
        "This object represents the version of the AE protocol."
    ::= { h3cWlanAEConfigEntry 7 }

h3cWlanAETagMultiAddr OBJECT-TYPE
    SYNTAX      MacAddress
    MAX-ACCESS  read-write
    STATUS      current
    DESCRIPTION
        "This object represents Tag's multicast MAC address."
    ::= { h3cWlanAEConfigEntry 8 }
h3cWlanAEEngineDetection OBJECT-TYPE
    SYNTAX      INTEGER
        {
          static(1),
          dynamic(2)
        }
    MAX-ACCESS  read-write
    STATUS      current
    DESCRIPTION
        "This object represents the location mode."
    ::= { h3cWlanAEConfigEntry 9 }
h3cWlanAEReportMode OBJECT-TYPE
    SYNTAX      INTEGER
        {
          local(1),
          central(2)
        }
    MAX-ACCESS  read-write
    STATUS      current
    DESCRIPTION
        "This object represents the report mode."
    ::= { h3cWlanAEConfigEntry 10 }

-- *****************************************************************************
-- * End of h3cWlanAEConfigTable Definition
-- *****************************************************************************

-- *****************************************************************************
-- *  h3cWlanAERadioConfigTable Definition
-- *****************************************************************************
h3cWlanAERadioConfigTable OBJECT-TYPE
    SYNTAX      SEQUENCE OF H3cWlanAERadioConfigEntry
    MAX-ACCESS  not-accessible
    STATUS      current
    DESCRIPTION
        "Administrators must configure AE parameters."
    ::= { h3cWlanAEConfigGroup 2 }

h3cWlanAERadioConfigEntry OBJECT-TYPE
    SYNTAX      H3cWlanAERadioConfigEntry
    MAX-ACCESS  not-accessible
    STATUS      current
    DESCRIPTION
        "Each entry contains AE location configuration information."
    INDEX
        {
            h3cWlanAERadioAPSerialID,
            h3cWlanAEAPRadioID
        }
    ::= { h3cWlanAERadioConfigTable 1 }

H3cWlanAERadioConfigEntry ::= SEQUENCE
    {
        h3cWlanAERadioAPSerialID     OCTET STRING,
        h3cWlanAEAPRadioID           Integer32,
        h3cWlanAERadioStatus         TruthValue,
        h3cWlanAEMUStatus            TruthValue,
        h3cWlanAETagStatus           TruthValue
    }

h3cWlanAERadioAPSerialID OBJECT-TYPE
    SYNTAX      OCTET STRING(SIZE(0..127))
    MAX-ACCESS  not-accessible
    STATUS      current
    DESCRIPTION
        "This object represents the serial ID of an AP."
    ::= { h3cWlanAERadioConfigEntry 1 }

h3cWlanAEAPRadioID OBJECT-TYPE
    SYNTAX      Integer32(1..65535)
    MAX-ACCESS  not-accessible
    STATUS      current
    DESCRIPTION
        "This object represents the ID of a radio."
    ::= { h3cWlanAERadioConfigEntry 2 }

h3cWlanAERadioStatus OBJECT-TYPE
    SYNTAX      TruthValue
    MAX-ACCESS  read-write
    STATUS      current
    DESCRIPTION
        "This object represents the enabled or disabled status of radio-based location."
    ::= { h3cWlanAERadioConfigEntry 3 }

h3cWlanAEMUStatus OBJECT-TYPE
    SYNTAX      TruthValue
    MAX-ACCESS  read-write
    STATUS      current
    DESCRIPTION
        "This object represents the status of MU message reporting."
    ::= { h3cWlanAERadioConfigEntry 4 }

h3cWlanAETagStatus OBJECT-TYPE
    SYNTAX      TruthValue
    MAX-ACCESS  read-write
    STATUS      current
    DESCRIPTION
        "This object represents the status of Tag message reporting."
    ::= { h3cWlanAERadioConfigEntry 5 }

-- *****************************************************************************
-- * End of h3cWlanAERadioConfigTable Definition
-- *****************************************************************************

-- *****************************************************************************
-- *  h3cWlanCommonConfigTable Definition
-- *****************************************************************************
h3cWlanCommonConfigTable OBJECT-TYPE
    SYNTAX      SEQUENCE OF H3cWlanCommonConfigEntry
    MAX-ACCESS  not-accessible
    STATUS      current
    DESCRIPTION
        "Administrators must configure common parameters."
    ::= { h3cWlanCommonConfigGroup 1 }

h3cWlanCommonConfigEntry OBJECT-TYPE
    SYNTAX      H3cWlanCommonConfigEntry
    MAX-ACCESS  not-accessible
    STATUS      current
    DESCRIPTION
        "Each entry contains common configuration information."
    INDEX
        {
            h3cWlanCommonAPSerialID
        }
    ::= { h3cWlanCommonConfigTable 1 }

H3cWlanCommonConfigEntry ::= SEQUENCE
    {
        h3cWlanCommonAPSerialID                 OCTET STRING,
        h3cWlanDilutionStatus                   TruthValue,
        h3cWlanDilutionFactor                   Integer32,
        h3cWlanDilutionTimeout                  Integer32,
        h3cWlanIgnoreBeacon                     TruthValue,
        h3cWlanRateLimitStatus                  TruthValue,
        h3cWlanRateLimitCir                     Integer32,
        h3cWlanRateLimitCbs                     Integer32,
        h3cWlanClientRateLimitStatus            TruthValue,
        h3cWlanClientRateLimitCir               Integer32,
        h3cWlanClientRateLimitCbs               Integer32,
        h3cWlanRssiStatus                       TruthValue,
        h3cWlanRssiThreshold                    Integer32,
        h3cWlanIgnoreApFrame                    TruthValue
    }

h3cWlanCommonAPSerialID OBJECT-TYPE
    SYNTAX      OCTET STRING(SIZE(0..127))
    MAX-ACCESS  not-accessible
    STATUS      current
    DESCRIPTION
        "This object represents the serial ID of an AP."
    ::= { h3cWlanCommonConfigEntry 1 }

h3cWlanDilutionStatus OBJECT-TYPE
    SYNTAX      TruthValue
    MAX-ACCESS  read-write
    STATUS      current
    DESCRIPTION
        "This object represents the enabled or disabled status of packet dilution."
    ::= { h3cWlanCommonConfigEntry 2 }

h3cWlanDilutionFactor OBJECT-TYPE
    SYNTAX      Integer32(0..10000)
    MAX-ACCESS  read-write
    STATUS      current
    DESCRIPTION
        "This object represents the packet dilution factor."
    ::= { h3cWlanCommonConfigEntry 3 }

h3cWlanDilutionTimeout OBJECT-TYPE
    SYNTAX      Integer32(0..60)
    UNITS       "Second"
    MAX-ACCESS  read-write
    STATUS      current
    DESCRIPTION
        "This object represents the packet dilution timeout."
    ::= { h3cWlanCommonConfigEntry 4 }

h3cWlanIgnoreBeacon OBJECT-TYPE
    SYNTAX      TruthValue
    MAX-ACCESS  read-write
    STATUS      current
    DESCRIPTION
        "This object represents the enabled or disabled status of beacon ignoring."
    ::= { h3cWlanCommonConfigEntry 5 }

h3cWlanRateLimitStatus OBJECT-TYPE
    SYNTAX      TruthValue
    MAX-ACCESS  read-write
    STATUS      current
    DESCRIPTION
        "This object represents the enabled or disabled status of location packet rate limiting."
    ::= { h3cWlanCommonConfigEntry 6 }

h3cWlanRateLimitCir OBJECT-TYPE
    SYNTAX      Integer32(0|8..1300000)
    UNITS       "Kbps"
    MAX-ACCESS  read-write
    STATUS      current
    DESCRIPTION
        "This object represents the CIR for sending location packets."
    ::= { h3cWlanCommonConfigEntry 7 }

h3cWlanRateLimitCbs OBJECT-TYPE
    SYNTAX      Integer32(0|500..130000000)
    UNITS       "Bytes"
    MAX-ACCESS  read-write
    STATUS      current
    DESCRIPTION
        "This object represents the CBS for sending location packets."
    ::= { h3cWlanCommonConfigEntry 8 }

h3cWlanClientRateLimitStatus OBJECT-TYPE
    SYNTAX      TruthValue
    MAX-ACCESS  read-write
    STATUS      current
    DESCRIPTION
        "This object represents the enabled or disabled status of client packet rate limiting."
    ::= { h3cWlanCommonConfigEntry 9 }

h3cWlanClientRateLimitCir OBJECT-TYPE
    SYNTAX      Integer32(0..1300000)
    UNITS       "Kbps"
    MAX-ACCESS  read-write
    STATUS      current
    DESCRIPTION
        "This object represents the CIR for receiving client packets."
    ::= { h3cWlanCommonConfigEntry 10 }

h3cWlanClientRateLimitCbs OBJECT-TYPE
    SYNTAX      Integer32(0|80..130000000)
    UNITS       "Bytes"
    MAX-ACCESS  read-write
    STATUS      current
    DESCRIPTION
        "This object represents the CBS for receiving client packets."
    ::= { h3cWlanCommonConfigEntry 11 }

h3cWlanRssiStatus OBJECT-TYPE
    SYNTAX      TruthValue
    MAX-ACCESS  read-write
    STATUS      current
    DESCRIPTION
        "This object represents the enabled or disabled status of RSSI-based packet filtering."
    ::= { h3cWlanCommonConfigEntry 12 }

h3cWlanRssiThreshold OBJECT-TYPE
    SYNTAX      Integer32(5..100)
    MAX-ACCESS  read-write
    STATUS      current
    DESCRIPTION
        "This object represents the max RSSI value of clients' packets."
    ::= { h3cWlanCommonConfigEntry 13 }

h3cWlanIgnoreApFrame OBJECT-TYPE
    SYNTAX      TruthValue
    MAX-ACCESS  read-write
    STATUS      current
    DESCRIPTION
        "This object represents the enabled or disabled status of AP packet ignoring."
    ::= { h3cWlanCommonConfigEntry 14 }

-- *****************************************************************************
-- * End of h3cWlanCommonConfigTable Definition
-- *****************************************************************************

-- *****************************************************************************
-- *  h3cWlanCUPIDConfigTable Definition
-- *****************************************************************************
h3cWlanCUPIDConfigTable OBJECT-TYPE
    SYNTAX      SEQUENCE OF H3cWlanCUPIDConfigEntry
    MAX-ACCESS  not-accessible
    STATUS      current
    DESCRIPTION
        "Administrators must configure CUPID parameters."
    ::= { h3cWlanCUPIDConfigGroup 1 }

h3cWlanCUPIDConfigEntry OBJECT-TYPE
    SYNTAX      H3cWlanCUPIDConfigEntry
    MAX-ACCESS  not-accessible
    STATUS      current
    DESCRIPTION
        "Each entry contains CUPID location configuration information."
    INDEX
        {
            h3cWlanCupidAPSerialID
        }
    ::= { h3cWlanCUPIDConfigTable 1 }

H3cWlanCUPIDConfigEntry ::= SEQUENCE
    {
        h3cWlanCupidAPSerialID             OCTET STRING,
        h3cWlanCupidStatus                 TruthValue,
        h3cWlanCupidEngineAddr             IpAddress,
        h3cWlanCupidEnginePort             Integer32,
        h3cWlanCupidVendorPort             Integer32,
        h3cWlanCupidReportStatus           TruthValue,
        h3cWlanCupidReportInterval         Integer32,
        h3cWlanCupidUnassSta               TruthValue,
        h3cWlanCupidUnassMeasureSta        TruthValue,
        h3cWlanCupidReportMode             INTEGER,
        h3cWlanCUPIDReportFormat           INTEGER
    }

h3cWlanCupidAPSerialID OBJECT-TYPE
    SYNTAX      OCTET STRING(SIZE(0..127))
    MAX-ACCESS  not-accessible
    STATUS      current
    DESCRIPTION
        "This object represents the serial ID of an AP."
    ::= { h3cWlanCUPIDConfigEntry 1 }

h3cWlanCupidStatus OBJECT-TYPE
    SYNTAX      TruthValue
    MAX-ACCESS  read-write
    STATUS      current
    DESCRIPTION
        "This object represents the status of CUPID location."
    ::= { h3cWlanCUPIDConfigEntry 2 }

h3cWlanCupidEngineAddr OBJECT-TYPE
    SYNTAX      IpAddress
    MAX-ACCESS  read-write
    STATUS      current
    DESCRIPTION
        "This object represents the IPv4 address of the CUPID location server."
    ::= { h3cWlanCUPIDConfigEntry 3 }

h3cWlanCupidEnginePort OBJECT-TYPE
    SYNTAX      Integer32(0..65535)
    MAX-ACCESS  read-write
    STATUS      current
    DESCRIPTION
        "This object represents the UDP port of the CUPID location server."
    ::= { h3cWlanCUPIDConfigEntry 4 }

h3cWlanCupidVendorPort OBJECT-TYPE
    SYNTAX      Integer32(1..65535)
    MAX-ACCESS  read-write
    STATUS      current
    DESCRIPTION
        "This object represents the UDP port to listen for CUPID messages from the server."
    ::= { h3cWlanCUPIDConfigEntry 5 }

h3cWlanCupidReportStatus OBJECT-TYPE
    SYNTAX      TruthValue
    MAX-ACCESS  read-write
    STATUS      current
    DESCRIPTION
        "This object represents the status of CUPID location reporting."
    ::= { h3cWlanCUPIDConfigEntry 6 }

h3cWlanCupidReportInterval OBJECT-TYPE
    SYNTAX      Integer32(1..10)
    UNITS       "Second"
    MAX-ACCESS  read-write
    STATUS      current
    DESCRIPTION
        "This object represents the interval for sending CUPID location packets."
    ::= { h3cWlanCUPIDConfigEntry 7 }

h3cWlanCupidUnassSta OBJECT-TYPE
    SYNTAX      TruthValue
    MAX-ACCESS  read-write
    STATUS      current
    DESCRIPTION
        "This object represents the status of unassociated client information
         reporting for CUPID location."
    ::= { h3cWlanCUPIDConfigEntry 8 }

h3cWlanCupidUnassMeasureSta OBJECT-TYPE
    SYNTAX      TruthValue
    MAX-ACCESS  read-write
    STATUS      current
    DESCRIPTION
        "This object represents the status of CUPID location for unassociated clients."
    ::= { h3cWlanCUPIDConfigEntry 9 }

h3cWlanCupidReportMode OBJECT-TYPE
    SYNTAX      INTEGER
        {
          local(1),
          central(2)
        }
    MAX-ACCESS  read-write
    STATUS      current
    DESCRIPTION
        "This object represents the report mode."
    ::= { h3cWlanCUPIDConfigEntry 10 }

h3cWlanCUPIDReportFormat OBJECT-TYPE
    SYNTAX      INTEGER
        {
          general(1),
          lightweight(2)
        }
    MAX-ACCESS  read-write
    STATUS      current
    DESCRIPTION
        "This object represents the report format."
    ::= { h3cWlanCUPIDConfigEntry 11 }

-- *****************************************************************************
-- * End of h3cWlanCUPIDConfigTable Definition
-- *****************************************************************************

-- *****************************************************************************
-- *  h3cWlanFPConfigTable Definition
-- *****************************************************************************
h3cWlanFPConfigTable OBJECT-TYPE
    SYNTAX      SEQUENCE OF H3cWlanFPConfigEntry
    MAX-ACCESS  not-accessible
    STATUS      current
    DESCRIPTION
        "Administrators must configure RF fingerprinting parameters."
    ::= { h3cWlanFPConfigGroup 1 }

h3cWlanFPConfigEntry OBJECT-TYPE
    SYNTAX      H3cWlanFPConfigEntry
    MAX-ACCESS  not-accessible
    STATUS      current
    DESCRIPTION
        "Each entry contains RF fingerprinting configuration information."
    INDEX
        {
            h3cWlanFPAPSerialID
        }
    ::= { h3cWlanFPConfigTable 1 }

H3cWlanFPConfigEntry ::= SEQUENCE
    {
        h3cWlanFPAPSerialID         OCTET STRING,
        h3cWlanFPStatus             TruthValue,
        h3cWlanFPEngineAddr         IpAddress,
        h3cWlanFPEnginePort         Integer32,
        h3cWlanFPVendorPort         Integer32,
        h3cWlanFPRawFrameReport     TruthValue,
        h3cWlanFPMUReport           TruthValue,
        h3cWlanFPReportMode         INTEGER,
        h3cWlanFPReportFormat       INTEGER,
        h3cWlanFPTagMultiAddr       MacAddress
    }

h3cWlanFPAPSerialID OBJECT-TYPE
    SYNTAX      OCTET STRING(SIZE(0..127))
    MAX-ACCESS  not-accessible
    STATUS      current
    DESCRIPTION
        "This object represents the serial ID of an AP."
    ::= { h3cWlanFPConfigEntry 1 }

h3cWlanFPStatus OBJECT-TYPE
    SYNTAX      TruthValue
    MAX-ACCESS  read-write
    STATUS      current
    DESCRIPTION
        "This object represents the enabled or disabled status of RF fingerprinting."
    ::= { h3cWlanFPConfigEntry 2 }

h3cWlanFPEngineAddr OBJECT-TYPE
    SYNTAX      IpAddress
    MAX-ACCESS  read-write
    STATUS      current
    DESCRIPTION
        "This object represents the IPv4 address of the RF fingerprinting server."
    ::= { h3cWlanFPConfigEntry 3 }

h3cWlanFPEnginePort OBJECT-TYPE
    SYNTAX      Integer32(0..65535)
    MAX-ACCESS  read-write
    STATUS      current
    DESCRIPTION
        "This object represents the UDP port of the RF fingerprinting server."
    ::= { h3cWlanFPConfigEntry 4 }

h3cWlanFPVendorPort OBJECT-TYPE
    SYNTAX      Integer32(1..65535)
    MAX-ACCESS  read-write
    STATUS      current
    DESCRIPTION
        "This object represents the UDP port to listen for RF fingerprinting
         packets from the server."
    ::= { h3cWlanFPConfigEntry 5 }

h3cWlanFPRawFrameReport OBJECT-TYPE
    SYNTAX      TruthValue
    MAX-ACCESS  read-write
    STATUS      current
    DESCRIPTION
        "This object represents the status of raw frame reporting for RF fingerprinting."
    ::= { h3cWlanFPConfigEntry 6 }

h3cWlanFPMUReport OBJECT-TYPE
    SYNTAX      TruthValue
    MAX-ACCESS  read-write
    STATUS      current
    DESCRIPTION
        "This object represents the status of MU information reporting for RF fingerprinting."
    ::= { h3cWlanFPConfigEntry 7 }

h3cWlanFPReportMode OBJECT-TYPE
    SYNTAX      INTEGER
        {
          local(1),
          central(2)
        }
    MAX-ACCESS  read-write
    STATUS      current
    DESCRIPTION
        "This object represents the report mode."
    ::= { h3cWlanFPConfigEntry 8 }

h3cWlanFPReportFormat OBJECT-TYPE
    SYNTAX      INTEGER
        {
          general(1),
          lightweight(2),
          cupidhybrid(3)
        }
    MAX-ACCESS  read-write
    STATUS      current
    DESCRIPTION
        "This object represents the report format."
    ::= { h3cWlanFPConfigEntry 9 }

h3cWlanFPTagMultiAddr OBJECT-TYPE
    SYNTAX      MacAddress
    MAX-ACCESS  read-write
    STATUS      current
    DESCRIPTION
        "This object represents Tag's multicast MAC address."
    ::= { h3cWlanFPConfigEntry 10 }
-- *****************************************************************************
-- * End of h3cWlanFPConfigTable Definition
-- *****************************************************************************

END

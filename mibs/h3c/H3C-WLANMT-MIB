-- =============================================================================
-- Copyright (c) 2004-2015 Hangzhou H3C Tech. Co., Ltd.  All rights reserved.
--
-- Description:
--   The file defines a MIB to provide wlan access controler maitenace feature.
-- Reference:
-- Version: V1.0
-- History:
--   V1.0 created by haoshitong 10530
--     Initial version 2014-09-28
-- =============================================================================
H3C-WLANMT-MIB DEFINITIONS ::= BEGIN

IMPORTS
    Unsigned32, OBJECT-TYPE, MODULE-IDENTITY, Counter64
        FROM SNMPv2-SMI
    h3cCommon
        FROM HUAWEI-3COM-OID-MIB;

h3cWlanMt MODULE-IDENTITY
    LAST-UPDATED "201409281747Z"        -- September 28, 2014 at 14:50 GMT
    ORGANIZATION
        "Hangzhou H3C Technologies Co., Ltd."
    CONTACT-INFO
        "Platform Team Hangzhou H3C Technologies Co., Ltd.
        Hai-Dian District Beijing P.R. China
        http://www.h3c.com
        Zip:100085
        "
    DESCRIPTION
        "This MIB provides information about WlanMt(Wlan Maintenance) feature.

        WlanMt is designed to be employed in an area that is serviced
        by an existing wireless network.
        It reflect the running situation on VCpu whitch used to forward packets.
        These information include: VCpu-Usage(Past 5 secons), Total Rx\Tx\Drop
        packets per VCpu.
        "
    REVISION "201409281747Z"        -- September 28, 2014 at 14:50 GMT
    DESCRIPTION
        "The initial revision of this MIB module."
    ::= {  h3cCommon 157 }

--
-- Node definitions
--

h3cWlanMtVCpuInfoGroup OBJECT IDENTIFIER ::= { h3cWlanMt 1 }

h3cWlanMtVCpuInfoTable OBJECT-TYPE
    SYNTAX SEQUENCE OF H3cWlanMtVCpuInfoEntry
    MAX-ACCESS not-accessible
    STATUS current
    DESCRIPTION
        "The table represents the list of possible VCpu information."
    ::= { h3cWlanMtVCpuInfoGroup 1 }

h3cWlanMtVCpuInfoEntry OBJECT-TYPE
    SYNTAX H3cWlanMtVCpuInfoEntry
    MAX-ACCESS not-accessible
    STATUS current
    DESCRIPTION
        "Each entry contains possible information of each VCpu."
    INDEX { h3cWlanMtVcpuID }
    ::= { h3cWlanMtVCpuInfoTable 1 }

H3cWlanMtVCpuInfoEntry ::=
    SEQUENCE {
        h3cWlanMtVcpuID
            Unsigned32,
        h3cWlanMtVcpuUsage
            Unsigned32,
        h3cWlanMtVcpuRx
            Counter64,
        h3cWlanMtVcpuTx
            Counter64,
        h3cWlanMtVcpuDrop
            Counter64
    }

h3cWlanMtVcpuID OBJECT-TYPE
    SYNTAX Unsigned32 (0..255)
    MAX-ACCESS not-accessible
    STATUS current
    DESCRIPTION
        "Represents the Id of the VCpu."
    ::= { h3cWlanMtVCpuInfoEntry 1 }

h3cWlanMtVcpuUsage OBJECT-TYPE
    SYNTAX Unsigned32 (0..100)
    MAX-ACCESS read-only
    STATUS current
    DESCRIPTION
        "Represents the usage of the VCpu."
    ::= { h3cWlanMtVCpuInfoEntry 2 }

h3cWlanMtVcpuRx OBJECT-TYPE
    SYNTAX Counter64
    MAX-ACCESS read-only
    STATUS current
    DESCRIPTION
        "Represents the number of packets whitch vcpu has recieved."
    ::= { h3cWlanMtVCpuInfoEntry 3 }

h3cWlanMtVcpuTx OBJECT-TYPE
    SYNTAX Counter64
    MAX-ACCESS read-only
    STATUS current
    DESCRIPTION
        "Represents the number of packets whitch vcpu has transmitted."
    ::= { h3cWlanMtVCpuInfoEntry 4 }

h3cWlanMtVcpuDrop OBJECT-TYPE
    SYNTAX Counter64
    MAX-ACCESS read-only
    STATUS current
    DESCRIPTION
        "Represents the number of packets whitch vcpu has Dropped."
    ::= { h3cWlanMtVCpuInfoEntry 5 }

h3cWlanMtFrameToCpu OBJECT IDENTIFIER ::= { h3cWlanMt 2 }

h3cWlanMtToCpuTxFrameCnt OBJECT-TYPE
    SYNTAX      Counter64
    MAX-ACCESS read-only
    STATUS current
    DESCRIPTION
        "The total packets send to cpu successfully."
    ::= { h3cWlanMtFrameToCpu 1 }

h3cWlanMtToCpuDropFrameCnt OBJECT-TYPE
    SYNTAX      Counter64
    MAX-ACCESS read-only
    STATUS current
    DESCRIPTION
        "The total packets send to cpu failed."
    ::= { h3cWlanMtFrameToCpu 2 }

END

-- ============================================================================
-- Copyright (c) 2004 Hangzhou H3C Tech. Co., Ltd.  All rights reserved.
-- Description: This MIB will maintain the products MIB OID and management
--              properties root node for H3C products
--
-- Reference:
-- Version: V1.00
-- History:
--   V1.00 2006-04-19 created by longyin
-- ============================================================================
HH3C-OID-MIB DEFINITIONS ::= BEGIN
    IMPORTS
        enterprises
            FROM RFC1155-SMI;

-- Object under .enterprises
    hh3c OBJECT IDENTIFIER ::= { enterprises 25506 }

-- Object under .enterprises.hh3c
    hh3cProductId OBJECT IDENTIFIER ::= { hh3c 1 }
    hpNetworking  OBJECT IDENTIFIER ::= { hh3c 11 }

END

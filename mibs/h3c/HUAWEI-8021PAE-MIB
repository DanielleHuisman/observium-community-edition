-- ==================================================================
-- Copyright (C) 2002 by  H3C TECHNOLOGIES. All rights reserved.
-- 
-- Description: 802.1X MIB
-- Reference:
-- Version: V1.3
-- History:
-- 1) 2003-03-27 Fuzhenyu created  
-- 2) v1.1 2004-08-28 chaiyongfu 
--         change node  hwdot1xAuthServerTimeout's DEFVAL { 30 } to DEFVAL { 100 }
--    v1.2 2004-10-12 updated by gaolong
--         Import NOTIFICATION-TYPE
--         Remove chinese characters
--         Fix time format of  hwpaeExtMib.
--    v1.3 2007-10-23 updated by chaiyongfu
--         Add node hwdot1xAuthMethod, hwdot1xpaeportMcastTrigStatus,
--         hwdot1xpaeportHandshakeStatus
-- ==================================================================

HUAWEI-8021PAE-MIB DEFINITIONS ::= BEGIN

    IMPORTS
    huaweiMgmt          
        FROM HUAWEI-3COM-OID-MIB
    OBJECT-TYPE,Unsigned32,NOTIFICATION-TYPE
        FROM SNMPv2-SMI
    
    MODULE-IDENTITY
            FROM SNMPv2-SMI 
    MacAddress
        FROM SNMPv2-TC

    dot1xPaePortNumber
            FROM IEEE8021-PAE-MIB;          
   

     hwpaeExtMib MODULE-IDENTITY
            LAST-UPDATED "200106290000Z"
            ORGANIZATION
            "Hangzhou H3C Tech. Co., Ltd."
            CONTACT-INFO
            "Platform Team Hangzhou H3C Tech. Co., Ltd.
            Hai-Dian District Beijing P.R. China
            http://www.h3c.com
            Zip:100085
            "
            DESCRIPTION
            "this file extends IEEE8021-PAE-MIB(802.1x)"
            REVISION "200106290000Z"
            DESCRIPTION
            ""
            ::= { huaweiMgmt 22 }
   -- ============================================================
   -- groups in the PAE MIB
   -- ============================================================

   hwpaeExtMibObjects           OBJECT IDENTIFIER ::= { hwpaeExtMib 1 }    
   hwdot1xPaeSystem             OBJECT IDENTIFIER ::= { hwpaeExtMibObjects 1 }
   hwdot1xPaeAuthenticator      OBJECT IDENTIFIER ::= { hwpaeExtMibObjects 2 }
 
   -- ============================================================

    hwdot1xAuthQuietPeriod OBJECT-TYPE
            SYNTAX             Unsigned32
            MAX-ACCESS     read-write
            STATUS             current
            DESCRIPTION
                    "The value, in seconds, of the quietPeriod constant
                    currently in use by the Authenticator PAE state
                    machine."
            REFERENCE
                    " 9.4.1, quietPeriod"
            DEFVAL { 60 }
            ::= { hwdot1xPaeSystem 1 }

    hwdot1xAuthTxPeriod OBJECT-TYPE
            SYNTAX             Unsigned32
            MAX-ACCESS     read-write
            STATUS             current
            DESCRIPTION
                    "The value, in seconds, of the txPeriod constant
                    currently in use by the Authenticator PAE state
                    machine."
            REFERENCE
                    " 9.4.1, txPeriod"
            DEFVAL { 30 }
            ::= { hwdot1xPaeSystem 2 }

    hwdot1xAuthSuppTimeout OBJECT-TYPE
            SYNTAX             Unsigned32
            MAX-ACCESS     read-write
            STATUS             current
            DESCRIPTION
                   "The value, in seconds, of the suppTimeout constant
                   currently in use by the Backend Authentication state
                   machine."
            REFERENCE
                   " 9.4.1, suppTimeout"
            DEFVAL { 30 }
            ::= { hwdot1xPaeSystem 3 }

   hwdot1xAuthServerTimeout OBJECT-TYPE
           SYNTAX             Unsigned32
           MAX-ACCESS     read-write
           STATUS             current
           DESCRIPTION
                   "The value, in seconds, of the serverTimeout constant
                   currently in use by the Backend Authentication state
                   machine."
           REFERENCE
                   " 9.4.1, serverTimeout"
           DEFVAL { 100 }
           ::= { hwdot1xPaeSystem 4 }

   hwdot1xAuthMaxReq OBJECT-TYPE
           SYNTAX             Unsigned32
           MAX-ACCESS     read-write
           STATUS             current
           DESCRIPTION
                   "The value of the maxReq constant currently in use by
                   the Backend Authentication state machine."
           REFERENCE
                   " 9.4.1, maxReq"
           DEFVAL { 2 }
           ::= { hwdot1xPaeSystem 5 }

   hwdot1xAuthReAuthPeriod OBJECT-TYPE
           SYNTAX             Unsigned32
           MAX-ACCESS     read-write
           STATUS             current
           DESCRIPTION
                   "The value, in seconds, of the reAuthPeriod constant
                   currently in use by the Reauthentication Timer state
                   machine."
           REFERENCE
                   " 9.4.1, reAuthPeriod"
           DEFVAL  { 3600 }
           ::= { hwdot1xPaeSystem 6 }
 
   hwdot1xAuthMethod OBJECT-TYPE
           SYNTAX         INTEGER { chap(1), pap(2), eap(3) }
           MAX-ACCESS     read-write
           STATUS         current
           DESCRIPTION
                   "The value defines the 802.1X authenticatin method."
           REFERENCE
                   ""
           DEFVAL  { 1 }
           ::= { hwdot1xPaeSystem 7 }

   -- ============================================================
   -- The Authenticator Configuration Extracte Table
   -- ============================================================

   hwdot1xAuthConfigExtTable OBJECT-TYPE
           SYNTAX             SEQUENCE OF Hwdot1xAuthConfigExtEntry
           MAX-ACCESS     not-accessible
           STATUS             current
           DESCRIPTION
                   " table extends dot1xAuthConfigTable"
            REFERENCE
                    " 9.4.1 Authenticator Configuration"
            ::= { hwdot1xPaeAuthenticator 1 }

    hwdot1xAuthConfigExtEntry OBJECT-TYPE
            SYNTAX             Hwdot1xAuthConfigExtEntry
            MAX-ACCESS     not-accessible
            STATUS             current
            DESCRIPTION
                    " The configuration information for an Authenticator PAE."
            INDEX { dot1xPaePortNumber }
            ::= { hwdot1xAuthConfigExtTable 1 }
            
    Hwdot1xAuthConfigExtEntry   ::=
    SEQUENCE {
        hwdot1xpaeportAuthAdminStatus   INTEGER ,
        hwdot1xpaeportControlledType    INTEGER ,
        hwdot1xpaeportMaxUserNum        INTEGER ,
        hwdot1xpaeportUserNumNow		INTEGER ,
        hwdot1xpaeportClearStatistics	INTEGER ,
        hwdot1xpaeportMcastTrigStatus   INTEGER ,
        hwdot1xpaeportHandshakeStatus   INTEGER
        }
        
    hwdot1xpaeportAuthAdminStatus  OBJECT-TYPE
           SYNTAX             INTEGER { enabled( 1), disabled( 2) }
           MAX-ACCESS     read-write
           STATUS             current
           DESCRIPTION
                   "The administrative enable/disable state for Port Access Control in a port."
           REFERENCE
                   ""
           DEFVAL  {2}
           ::= { hwdot1xAuthConfigExtEntry 1 }
           
           
    hwdot1xpaeportControlledType  OBJECT-TYPE
           SYNTAX             INTEGER { port(1), mac(2) }
           MAX-ACCESS     read-write
           STATUS             current
           DESCRIPTION
                   "Port Access Control type , base port access control or base MAC access control"
           REFERENCE
                   ""
           DEFVAL  {2}
           ::= { hwdot1xAuthConfigExtEntry 2 }
           
    hwdot1xpaeportMaxUserNum  OBJECT-TYPE
           SYNTAX             INTEGER 
           MAX-ACCESS     read-write
           STATUS             current
           DESCRIPTION
                   "the max num of online user in a port"
           REFERENCE
                   ""
           DEFVAL  {256}
           ::= { hwdot1xAuthConfigExtEntry 3 }
          
    hwdot1xpaeportUserNumNow  OBJECT-TYPE
           SYNTAX             INTEGER 
           MAX-ACCESS     read-only
           STATUS             current
           DESCRIPTION
                   "the num of online user in a port now "
           REFERENCE
                   ""
           ::= { hwdot1xAuthConfigExtEntry 4 }             
      
        
    hwdot1xpaeportClearStatistics  OBJECT-TYPE
           SYNTAX             INTEGER {clear(1)}
           MAX-ACCESS     read-write
           STATUS             current
           DESCRIPTION
                   "Clear various Statistics viz. "
           REFERENCE
                   ""
           ::= { hwdot1xAuthConfigExtEntry 5 }    
           
           
    hwdot1xpaeportMcastTrigStatus  OBJECT-TYPE
           SYNTAX         INTEGER { enabled( 1), disabled( 2) }
           MAX-ACCESS     read-write
           STATUS         current
           DESCRIPTION
                   "The administrative enable/disable state for sending
                   muticast EAP_REQ/ID packet."
           REFERENCE
                   ""
           DEFVAL  {1}
           ::= { hwdot1xAuthConfigExtEntry 6 }
           
    hwdot1xpaeportHandshakeStatus  OBJECT-TYPE
           SYNTAX         INTEGER { enabled( 1 ), disabled( 2 ) }
           MAX-ACCESS     read-write
           STATUS         current
           DESCRIPTION
                   "The administrative enable/disable state for sending
                   handshake EAP_REQ/ID packet."
           REFERENCE
                   ""
           DEFVAL  {1}
           ::= { hwdot1xAuthConfigExtEntry 7 }

  -- trap defination
    hwdot1xPaeTraps             OBJECT IDENTIFIER ::= { hwpaeExtMibObjects 0 }

    supplicantproxycheck NOTIFICATION-TYPE 
      OBJECTS { proxycheckVlanId, proxycheckPortName, proxycheckMacAddr, proxycheckIpaddr, proxycheckUsrName }
      STATUS current
      DESCRIPTION ""
      ::= { hwdot1xPaeTraps 1 }

    proxycheckVlanId OBJECT-TYPE 
      SYNTAX INTEGER
      MAX-ACCESS accessible-for-notify
      STATUS current
      DESCRIPTION "."
      ::= { hwdot1xPaeTraps 2 }

    proxycheckPortName OBJECT-TYPE 
      SYNTAX OCTET STRING
      MAX-ACCESS accessible-for-notify
      STATUS current
      DESCRIPTION "."
      ::= { hwdot1xPaeTraps 3 }

    proxycheckMacAddr OBJECT-TYPE 
      SYNTAX MacAddress
      MAX-ACCESS accessible-for-notify
      STATUS current
      DESCRIPTION "."
      ::= { hwdot1xPaeTraps 4 }
      
    proxycheckIpaddr OBJECT-TYPE 
      SYNTAX IpAddress
      MAX-ACCESS accessible-for-notify
      STATUS current
      DESCRIPTION "."
      ::= { hwdot1xPaeTraps 5 } 
              
    proxycheckUsrName OBJECT-TYPE 
      SYNTAX OCTET STRING
      MAX-ACCESS accessible-for-notify
      STATUS current
      DESCRIPTION "."
      ::= { hwdot1xPaeTraps 6 }               
END

-- =================================================================
-- Copyright (C) 2003 by  H3C TECHNOLOGIES. All rights reserved.
--
-- Description: DHCP Relay MIB
-- Reference:
-- Version: V1.0
-- History:
--
-- =================================================================

    HUAWEI-DHCPR-MIB DEFINITIONS ::= BEGIN

        IMPORTS
            huaweiMgmt, hwDhcp
                FROM HUAWEI-3COM-OID-MIB
            ifIndex
                FROM RFC1213-MIB
            OBJECT-GROUP
                FROM SNMPv2-CONF
            IpAddress, Integer32, OBJECT-TYPE, MODULE-IDENTITY
                FROM SNMPv2-SMI
            RowStatus
                FROM SNMPv2-TC;

        hwDHCPRelayMib MODULE-IDENTITY
            LAST-UPDATED "200303010000Z"        -- March 01, 2003 at 00:00 GMT
            ORGANIZATION
                "Hangzhou H3C Tech. Co., Ltd."
            CONTACT-INFO
                "Platform Team Hangzhou H3C Tech. Co., Ltd.
                Hai-Dian District Beijing P.R. China
                http://www.h3c.com
                Zip:100085
                "
            DESCRIPTION
                "This MIB describes objects used for managing DHCP relay."
            REVISION "200302120000Z"        -- February 12, 2003 at 00:00 GMT
            DESCRIPTION
                "The initial revision of this MIB module."
            ::= { hwDhcp 1 }



--
-- Node definitions
--

        hwDHCPRelayMibObject OBJECT IDENTIFIER ::= { hwDHCPRelayMib 1 }

-- =================================================================
-- 1st Table of hwDHCPRelayMibObjects: hwDHCPRIPTable
-- =================================================================
        hwDHCPRIPTable OBJECT-TYPE
            SYNTAX SEQUENCE OF HwDHCPRIPEntry
            MAX-ACCESS not-accessible
            STATUS current
            DESCRIPTION
                "A table for configuring ip addresses for DHCP relay"
            ::= { hwDHCPRelayMibObject 1 }

        hwDHCPRIPEntry OBJECT-TYPE
            SYNTAX HwDHCPRIPEntry
            MAX-ACCESS not-accessible
            STATUS current
            DESCRIPTION
                "An entry for configuring ip addresses for DHCP
                relay"
            INDEX { ifIndex, hwDHCPRIPAddr }
            ::= { hwDHCPRIPTable 1 }

        HwDHCPRIPEntry ::=
            SEQUENCE {
                hwDHCPRIPAddr
                    IpAddress,
                hwDHCPRIPRowStatus
                    RowStatus
             }

        hwDHCPRIPAddr OBJECT-TYPE
            SYNTAX IpAddress
            MAX-ACCESS read-only
            STATUS current
            DESCRIPTION
                "Ip address for DHCP relay"
            ::= { hwDHCPRIPEntry 1 }

        hwDHCPRIPRowStatus OBJECT-TYPE
            SYNTAX RowStatus
            MAX-ACCESS read-create
            STATUS current
            DESCRIPTION
                "RowStatus. Three actions are used: active,
                createAndGo, destroy"
            ::= { hwDHCPRIPEntry 2 }

-- =================================================================
-- 2nd Table of hwDHCPRelayMibObjects: hwDHCPRSeletAllocateModeTable
-- =================================================================
        hwDHCPRSeletAllocateModeTable OBJECT-TYPE
            SYNTAX SEQUENCE OF HwDHCPRSeletAllocateModeEntry
            MAX-ACCESS not-accessible
            STATUS current
            DESCRIPTION
                "A table for selecting allocation mode of dhcp
                service"
            ::= { hwDHCPRelayMibObject 2 }

        hwDHCPRSeletAllocateModeEntry OBJECT-TYPE
            SYNTAX HwDHCPRSeletAllocateModeEntry
            MAX-ACCESS not-accessible
            STATUS current
            DESCRIPTION
                "An entry for configuring the allocation mode of
                DHCP service"
            INDEX { ifIndex }
            ::= { hwDHCPRSeletAllocateModeTable 1 }

        HwDHCPRSeletAllocateModeEntry ::=
            SEQUENCE {
                hwDHCPRSelectAllocateMode
                    INTEGER
             }

        hwDHCPRSelectAllocateMode OBJECT-TYPE
            SYNTAX INTEGER
                {
                global(0),
                interface(1),
                relay(2)
                }
            MAX-ACCESS read-write
            STATUS current
            DESCRIPTION
                "Allocation mode of DHCP service"
            ::= { hwDHCPRSeletAllocateModeEntry 1 }

--
-- Non-table objects
--
        hwDHCPRelayCycleStatus OBJECT-TYPE
            SYNTAX INTEGER
                {
                on(0),
                off(1)
                }
            MAX-ACCESS read-write
            STATUS current
            DESCRIPTION
                "Status of DHCP relay cycle mode"
            ::= { hwDHCPRelayMibObject 3 }

        hwDHCPRRxBadPktNum OBJECT-TYPE
            SYNTAX Integer32
            MAX-ACCESS read-only
            STATUS current
            DESCRIPTION
                "The total number of the bad packets received by
                DHCP relay"
            ::= { hwDHCPRelayMibObject 4 }

        hwDHCPRRxServerPktNum OBJECT-TYPE
            SYNTAX Integer32
            MAX-ACCESS read-only
            STATUS current
            DESCRIPTION
                "The total number of the packets received from
                DHCP servers by DHCP relay module"
            ::= { hwDHCPRelayMibObject 5 }

        hwDHCPRTxServerPktNum OBJECT-TYPE
            SYNTAX Integer32
            MAX-ACCESS read-only
            STATUS current
            DESCRIPTION
                "The total number of the packets transmited to
                DHCP servers by DHCP relay module"
            ::= { hwDHCPRelayMibObject 6 }

        hwDHCPRRxClientPktNum OBJECT-TYPE
            SYNTAX Integer32
            MAX-ACCESS read-only
            STATUS current
            DESCRIPTION
                "The total number of the packets received form DHCP
                clients by DHCP relay"
            ::= { hwDHCPRelayMibObject 7 }

        hwDHCPRTxClientPktNum OBJECT-TYPE
            SYNTAX Integer32
            MAX-ACCESS read-only
            STATUS current
            DESCRIPTION
                "The total number of the brodcast packets transmited
                to DHCP clients by DHCP relay"
            ::= { hwDHCPRelayMibObject 8 }

        hwDHCPRTxClientUniPktNum OBJECT-TYPE
            SYNTAX Integer32
            MAX-ACCESS read-only
            STATUS current
            DESCRIPTION
                "The total number of the unicast packets received
                form DHCP clients by DHCP relay"
            ::= { hwDHCPRelayMibObject 9 }

        hwDHCPRTxClientBroPktNum OBJECT-TYPE
            SYNTAX Integer32
            MAX-ACCESS read-only
            STATUS current
            DESCRIPTION
                "The total number of the brodcast packets received
                form DHCP clients by DHCP relay"
            ::= { hwDHCPRelayMibObject 10 }

        hwDHCPRelayDiscoverPktNum OBJECT-TYPE
            SYNTAX Integer32
            MAX-ACCESS read-only
            STATUS current
            DESCRIPTION
                "The total number of the DHCP Discover packets handled
                by DHCP relay"
            ::= { hwDHCPRelayMibObject 11 }

        hwDHCPRelayRequestPktNum OBJECT-TYPE
            SYNTAX Integer32
            MAX-ACCESS read-only
            STATUS current
            DESCRIPTION
                "The total number of the DHCP Request packets handled
                by DHCP relay"
            ::= { hwDHCPRelayMibObject 12 }

        hwDHCPRelayDeclinePktNum OBJECT-TYPE
            SYNTAX Integer32
            MAX-ACCESS read-only
            STATUS current
            DESCRIPTION
                "The total number of the DHCP Decline packets handled
                by DHCP relay"
            ::= { hwDHCPRelayMibObject 13 }

        hwDHCPRelayReleasePktNum OBJECT-TYPE
            SYNTAX Integer32
            MAX-ACCESS read-only
            STATUS current
            DESCRIPTION
                "The total number of the DHCP Release packets handled
                by DHCP relay"
            ::= { hwDHCPRelayMibObject 14 }

        hwDHCPRelayInformPktNum OBJECT-TYPE
            SYNTAX Integer32
            MAX-ACCESS read-only
            STATUS current
            DESCRIPTION
                "The total number of the DHCP Inform packets handled
                by DHCP relay"
            ::= { hwDHCPRelayMibObject 15 }

        hwDHCPRelayOfferPktNum OBJECT-TYPE
            SYNTAX Integer32
            MAX-ACCESS read-only
            STATUS current
            DESCRIPTION
                "The total number of the DHCP Offer packets handled
                by DHCP server"
            ::= { hwDHCPRelayMibObject 16 }

        hwDHCPRelayAckPktNum OBJECT-TYPE
            SYNTAX Integer32
            MAX-ACCESS read-only
            STATUS current
            DESCRIPTION
                "The total number of the DHCP Ack packets handled
                by DHCP relay"
            ::= { hwDHCPRelayMibObject 17 }

        hwDHCPRelayNakPktNum OBJECT-TYPE
            SYNTAX Integer32
            MAX-ACCESS read-only
            STATUS current
            DESCRIPTION
                "The total number of the DHCP Nak packets handled
                by DHCP relay"
            ::= { hwDHCPRelayMibObject 18 }

        hwDHCPRelayStatisticsReset OBJECT-TYPE
            SYNTAX INTEGER
                {
                invalid(0),
                reset(1)
                }
            MAX-ACCESS read-write
            STATUS current
            DESCRIPTION
                "Reset the above statictics information of handled
                packets by DHCP relay"
            ::= { hwDHCPRelayMibObject 19 }

        hwDHCPRelayMIBConformance OBJECT IDENTIFIER ::= { hwDHCPRelayMib 2 }

        hwDHCPRelayMIBCompliances OBJECT IDENTIFIER ::= { hwDHCPRelayMIBConformance 1 }

        hwDHCPRelayMIBGroups OBJECT IDENTIFIER ::= { hwDHCPRelayMIBConformance 2 }

        hwDHCPRelayMIBGroup OBJECT-GROUP
            OBJECTS { hwDHCPRIPAddr, hwDHCPRIPRowStatus, hwDHCPRSelectAllocateMode, hwDHCPRelayCycleStatus, hwDHCPRRxBadPktNum,
                hwDHCPRRxServerPktNum, hwDHCPRTxServerPktNum, hwDHCPRRxClientPktNum, hwDHCPRTxClientPktNum, hwDHCPRTxClientUniPktNum,
                hwDHCPRTxClientBroPktNum, hwDHCPRelayDiscoverPktNum, hwDHCPRelayRequestPktNum, hwDHCPRelayDeclinePktNum, hwDHCPRelayReleasePktNum,
                hwDHCPRelayInformPktNum, hwDHCPRelayOfferPktNum, hwDHCPRelayAckPktNum, hwDHCPRelayNakPktNum, hwDHCPRelayStatisticsReset
                 }
            STATUS current
            DESCRIPTION
                "The basic collection of objects providing management of
                DHCP realy."
            ::= { hwDHCPRelayMIBGroups 1 }


    END

-- ==========================================================================
-- Copyright (c) 2004-2011 New H3C Tech. Co., Ltd.  All rights reserved.
--
-- Description: AAA Nas-id mib
-- Reference:
-- Version: V1.0
-- History:
--   V1.0 2011-03-09 created by wangbin
-- ==========================================================================
HH3C-AAA-NASID-MIB DEFINITIONS ::= BEGIN

IMPORTS
    MODULE-IDENTITY, OBJECT-TYPE
        FROM SNMPv2-SMI
    hh3cCommon
        FROM HH3C-OID-MIB;

hh3cAAANasId MODULE-IDENTITY
    LAST-UPDATED "201103090945Z"
    ORGANIZATION
        "New H3C Technologies Co., Ltd."
    CONTACT-INFO
        "Platform Team New H3C Technologies Co., Ltd.
         Hai-Dian District Beijing P.R. China
         http://www.h3c.com
         Zip: 100085"
    DESCRIPTION
        "This MIB contains objects to
        manage configuration for AAA Nas-id feature.
        AAA presents authentication, authorization and accouting.
        NAS acts as the Network Access Server.
        Nas-id is an identifier that contains some strings identifying the NAS."
    REVISION "201103090945Z"
    DESCRIPTION
        "Initial version."
    ::= { hh3cCommon 114 }

hh3cAAANasIdObjects OBJECT IDENTIFIER ::= { hh3cAAANasId 1 }

-- ==========================================================================
-- hh3cAAANasIdTable OBJECT
-- ==========================================================================
hh3cAAANasIdTable OBJECT-TYPE
    SYNTAX SEQUENCE OF Hh3cAAANasIdEntry
    MAX-ACCESS not-accessible
    STATUS current
    DESCRIPTION
    "The AAA Nas-id table."
::= { hh3cAAANasIdObjects 1 }

hh3cAAANasIdEntry OBJECT-TYPE
    SYNTAX Hh3cAAANasIdEntry
    MAX-ACCESS not-accessible
    STATUS current
    DESCRIPTION
    "The AAA Nas-id entry."
    INDEX { hh3cAAANasIdName }
::= { hh3cAAANasIdTable 1 }

Hh3cAAANasIdEntry ::= SEQUENCE {
    hh3cAAANasIdName             OCTET STRING }

hh3cAAANasIdName OBJECT-TYPE
    SYNTAX      OCTET STRING (SIZE(1..64))
    MAX-ACCESS  read-only
    STATUS      current
    DESCRIPTION
    "The Nas-id name."
::= { hh3cAAANasIdEntry 1 }

END

-- ============================================================================
-- Copyright (c) 2004-2020 New H3C Tech. Co., Ltd. All rights reserved.
-- Description:  Control Plane disaster recovery Information MIB.
--               include :1.CPDR statistics information
-- Reference:
-- Version: V1.0
-- History:
-- V1.0 2020-11-13 created by tanjidong
-- ============================================================================
HH3C-CPDR-MIB DEFINITIONS ::= BEGIN
IMPORTS
    hh3cCommon
        FROM HH3C-OID-MIB
    OBJECT-TYPE, MODULE-IDENTITY, NOTIFICATION-TYPE
        FROM SNMPv2-SMI
    DisplayString
        FROM SNMPv2-TC;

hh3cCpdr MODULE-IDENTITY
    LAST-UPDATED "202011130000Z"
    ORGANIZATION
        "New H3C Tech. Co., Ltd."
    CONTACT-INFO
        "Platform Team New H3C Tech. Co., Ltd.
        Hai-Dian District Beijing P.R. China
        http://www.h3c.com
        Zip:100085
        "
    DESCRIPTION
        "The latest baseline."
    REVISION "202011130000Z"
    DESCRIPTION
        "The initial revision of this MIB module."
    ::= { hh3cCommon 199 }

--
-- Node definitions
--
--
-- Definitions of significant branches
--
hh3cCpdrObjects         OBJECT IDENTIFIER  ::= { hh3cCpdr 1 }
hh3cCpdrGroup           OBJECT IDENTIFIER  ::= { hh3cCpdrObjects 1 }

--
-- The hh3cCpdrGroupTable table
--

hh3cCpdrGroupTable  OBJECT-TYPE
    SYNTAX        SEQUENCE OF Hh3cCpdrGroupEntry
    MAX-ACCESS    not-accessible
    STATUS        current
    DESCRIPTION
        "A table containing control plane disaster recovery group specific variables
        for this cp disaster recovery implementation."
    ::= { hh3cCpdrGroup 1 }

hh3cCpdrGroupEntry  OBJECT-TYPE
    SYNTAX        Hh3cCpdrGroupEntry
    MAX-ACCESS    not-accessible
    STATUS        current
    DESCRIPTION
        "Basic information about a particular control plane disaster recovery group."
    INDEX     {IMPLIED hh3cCpdrGroupName }
    ::= { hh3cCpdrGroupTable 1 }

Hh3cCpdrGroupEntry ::= SEQUENCE {
    hh3cCpdrGroupName
        DisplayString,
    hh3cCpdrGroupRole
        INTEGER,
    hh3cCpdrMode
        INTEGER
    }

hh3cCpdrGroupName  OBJECT-TYPE
    SYNTAX        DisplayString (SIZE (1..32))
    MAX-ACCESS    read-only
    STATUS        current
    DESCRIPTION
        "The control plane disaster recovery group name."
    ::= { hh3cCpdrGroupEntry 1 }

hh3cCpdrGroupRole  OBJECT-TYPE
    SYNTAX        INTEGER
        {
            invalid (1),
            master (2),
            standBy (3)
        }
    MAX-ACCESS    read-only
    STATUS        current
    DESCRIPTION
        "The control plane disaster recovery group role."
    ::= { hh3cCpdrGroupEntry 2 }

hh3cCpdrMode  OBJECT-TYPE
    SYNTAX        INTEGER
        {
            hot (1),
            cold (2)
        }
    MAX-ACCESS    read-only
    STATUS        current
    DESCRIPTION
        "The control plane disaster recovery group mode."
    ::= { hh3cCpdrGroupEntry 3 }

hh3cCpdrTraps      OBJECT IDENTIFIER  ::= { hh3cCpdr 2 }
hh3cCpdrTrapsPrefix OBJECT IDENTIFIER ::= { hh3cCpdrTraps 0 }

--
-- The hh3cCpdrTraps trap
--

hh3cCpdrTrapRoleChange NOTIFICATION-TYPE
    OBJECTS { hh3cCpdrGroupName,
               hh3cCpdrGroupRole }
    STATUS  current
    DESCRIPTION
        "This trap is generated when the role of control plane disaster recovery group changes."
    ::= { hh3cCpdrTrapsPrefix 1 }

END

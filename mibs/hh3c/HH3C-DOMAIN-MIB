-- ==================================================================
-- Copyright (c) 2004-2021 New H3C Tech. Co., Ltd. All rights reserved.
--
-- Description: Domain MIB
-- Reference:
-- Version: V2.9
-- History:
-- V1.0 2005.03.23 The initial version, created by Xulei
-- V1.1 2005.06.03 updated by Xulei
--      Updated the SMIv2 syntax of some MIB objects
-- V1.2 2006.03.27 updated by yuanzhijie
--      1. Modified the description of hh3cDomainSchemeRowStatus
--      2. Added hh3cDomainSchemeAAAType, hh3cDomainSchemeAAAName,
--         and hh3cDomainSchemeAccessMode
--      3. Changed the value range for objects hh3cDomainAuthSchemeName
--         and hh3cDomainAcctSchemeName
-- V1.3 2007.03.07 updated by yangyang
--      Changed the SYNTAX of hh3cDomainName and hh3cDomainDefault
-- V1.4 2008.11.25 updated by ouzhili
--      Added enumeration value vlanlist(3) to object hh3cDomainVlanAssignMode
-- V1.5 2008.12.30 updated by dupengfei
--      Added hh3cDomainCurrentAccessNum
-- V1.6 2009.08.05 updated by huxiulan
--      Added enumeration value reserved(12) to object hh3cAccessModeofDomainScheme
-- V1.7 2012.05.20 updated by qiuchunxia
--      Added hh3cDomainIdleCutTime
--      2012.10.15 updated by liubo
--      Added enumeration value ldap(5) to object hh3cDomainSchemeMode
-- V1.8 2013.02.28 updated by xuyonggang
--      Changed hh3cDomainSchemeAccessMode
-- V1.9 2013.4.25 updated by qiuchunxia
--      Deleted the range of hh3cDomainIdleCutMaxTime
-- V2.0 2013.11.25 updated by zhangdexu
--      Changed the range of hh3cDomainDefault and hh3cDomainName
-- V2.1 2017.6.3 updated by yuhua
--      Added hh3cDomainGlobalStat, hh3cDomainStatTable, hh3cDomainIPPoolStatTable,
--      hh3cDomainServiceType, hh3cDomainIpPoolName, and hh3cDomainIpv6PoolName
--      2017.10.13 updated by yangliping
--      Changed hh3cDomainGlobalStat and hh3cDomainStatTable
-- V2.2 2018.11.27 updated by yuhua
--      Changed Hh3cDomainStatEntry, Hh3cDomainIPPoolStatEntry and hh3cDomainGlobalStat,
--      add hh3cDomainTraps
-- V2.3 2019.3.12 updated by yuhua
--      Added hh3cDomainIPv4PoolUpperValue, hh3cDomainIPv4PoolLowerValue, hh3cDomainIPv6PoolUpperValue, hh3cDomainIPv6PoolLowerValue,
--      hh3cUserIPv6AllocAlarm, hh3cUserIPv6AllocAlarmResume, hh3cUserIPv6LowlimitWarnAlarm,
--      hh3cUserIPv6LowlimitWarnResum, hh3cUserNDRAPfAllocAlarm, hh3cUserNDRAPfAllocAlarmResume,
--      hh3cUserNDRAPfLowlimitWarnAlarm, hh3cUserNDRAPfLowlimitWarnResume, hh3cUserPDPfAllocAlarm, hh3cUserPDPfAllocAlarmResume,
--      hh3cUserPDPfLowlimitWarnAlarm, hh3cUserPDPfLowlimitWarnResume
-- V2.4 2020.1.16 updated by liubo
--      1. Added hh3cDomainIpPoolGroupName, hh3cDomainIpv6PoolGroupName, hh3cDomainNdPrefixPoolName,
--      hh3cDomainNdPrefixPoolGroupName, hh3cDomainIpv6Prefix, hh3cDomainIpv6PrefixLength,
--      hh3cDomainNatBindingTable, hh3cDomainNatBindingUserGroupName, hh3cDomainNatBindingNatInstance
--      and hh3cDomainNatBindingRowStatus
--      2. Changed the MAX-ACCESS attribute value of hh3cDomainName to read-only
-- V2.5 2020.7.3 updated by liubo
--      Changed hh3cDomainIPv4PoolUpperValue, hh3cDomainIPv4PoolLowerValue, hh3cDomainIPv4PoolUpperValue
--      and hh3cDomainIPv6PoolLowerValue
-- V2.6 2020.11.20 updated by liubo
--      Added hh3cDomainUpStatTable
-- V2.7 2021.2.2 updated by liubo
--      Changed hh3cDomainUpStatTable
-- V2.8 2021.3.24 updated by jinyu
--      Added hh3cDomainActiveWebServerUrl, hh3cUserWebServerDownAlarm,
--      hh3cUserWebServerUpAlarm, hh3cUserWebServerChangeAlarm
-- V2.9 2021.9.3 updated by wudegen
--      Added hh3cDomainActiveWebServerIpv6Url, hh3cUserIPv6WebServerDownAlarm,
--      hh3cUserIPv6WebServerUpAlarm, hh3cUserIPv6WebServerChangeAlarm
-- ==================================================================
HH3C-DOMAIN-MIB DEFINITIONS ::= BEGIN
    IMPORTS
        hh3cCommon
            FROM HH3C-OID-MIB
        Integer32, OBJECT-TYPE, NOTIFICATION-TYPE, MODULE-IDENTITY, TimeTicks, Unsigned32
            FROM SNMPv2-SMI
        InetAddressType, InetAddress
            FROM INET-ADDRESS-MIB
        Ipv6AddressPrefix
            FROM IPV6-TC
        RowStatus, TruthValue, TEXTUAL-CONVENTION
            FROM SNMPv2-TC;

    hh3cDomain MODULE-IDENTITY
        LAST-UPDATED "202109030000Z"            -- September 03, 2021 at 00:00 GMT
        ORGANIZATION
            "New H3C Tech. Co., Ltd."
        CONTACT-INFO
            "Platform Team New H3C Tech. Co., Ltd.
            Hai-Dian District Beijing P.R. China
            http://www.h3c.com
            Zip:100085
            "
        DESCRIPTION
            "The MIB module is used for managing domain."

--  Revision history
    REVISION     "202109030000Z"          -- September 03, 2021 at 00:00 GMT
        DESCRIPTION  "Added hh3cDomainActiveWebServerIpv6Url, hh3cUserIPv6WebServerDownAlarm,
                  hh3cUserIPv6WebServerUpAlarm, hh3cUserIPv6WebServerChangeAlarm"

    REVISION     "202103240000Z"          -- March 24, 2021 at 00:00 GMT
        DESCRIPTION  "Added hh3cDomainActiveWebServerUrl, hh3cUserWebServerDownAlarm,
                  hh3cUserWebServerUpAlarm, hh3cUserWebServerChangeAlarm"

    REVISION     "202102020000Z"          -- February 02, 2021 at 00:00 GMT
        DESCRIPTION  "Changed hh3cDomainUpStatTable"

    REVISION     "202011200000Z"          -- November 20, 2020 at 00:00 GMT
        DESCRIPTION  "Added hh3cDomainUpStatTable"

    REVISION     "202007030000Z"          -- July 03, 2020 at 00:00 GMT
        DESCRIPTION  "Changed hh3cDomainIPv4PoolUpperValue, hh3cDomainIPv4PoolLowerValue, hh3cDomainIPv4PoolUpperValue
                      and hh3cDomainIPv6PoolLowerValue"

    REVISION     "202001160000Z"          -- January 16, 2020 at 00:00 GMT
        DESCRIPTION  "1. Added hh3cDomainIpPoolGroupName, hh3cDomainIpv6PoolGroupName, hh3cDomainNdPrefixPoolName,
                  hh3cDomainNdPrefixPoolGroupName, hh3cDomainIpv6Prefix, hh3cDomainIpv6PrefixLength,
                  hh3cDomainNatBindingTable, hh3cDomainNatBindingUserGroupName, hh3cDomainNatBindingNatInstance
                  and hh3cDomainNatBindingRowStatus
                  2. Changed the MAX-ACCESS attribute value of hh3cDomainName to read-only"

    REVISION     "201903120000Z"          -- March 11, 2019 at 00:00 GMT
        DESCRIPTION  "1.Changed hh3cDomainInfoTable, hh3cDomainTraps
                  2.Added hh3cDomainIPv4PoolUpperValue, hh3cDomainIPv4PoolLowerValue, hh3cDomainIPv6PoolUpperValue, hh3cDomainIPv6PoolLowerValue
                  3.Modify hh3cUserIPAllocAlarm, hh3cUserIPAllocAlarmResume, hh3cUserIPLowerlimitWarningAlarm, hh3cUserIPLowerlimitWarningResume
                  4.hh3cUserIPv6AllocAlarm, hh3cUserIPv6AllocAlarmResume, hh3cUserIPv6LowlimitWarnAlarm, hh3cUserIPv6LowlimitWarnResum, hh3cUserNDRAPfAllocAlarm,
                    hh3cUserNDRAPfAllocAlarmResume, hh3cUserNDRAPfLowlimitWarnAlarm, hh3cUserNDRAPfLowlimitWarnResume, hh3cUserPDPfAllocAlarm,
                    hh3cUserPDPfAllocAlarmResume, hh3cUserPDPfLowlimitWarnAlarm, hh3cUserPDPfLowlimitWarnResume"

    REVISION     "201811270000Z"          -- November 27, 2018 at 00:00 GMT
        DESCRIPTION  "Changed Hh3cDomainStatEntry, Hh3cDomainIPPoolStatEntry and hh3cDomainGlobalStat,
                      added hh3cDomainTraps"

    REVISION     "201710130000Z"          -- October 13, 2017 at 00:00 GMT
        DESCRIPTION  "Changed hh3cDomainGlobalStat and hh3cDomainStatTable"

    REVISION     "201706030000Z"          -- June 03, 2017 at 00:00 GMT
        DESCRIPTION  "Added hh3cDomainGlobalStat, hh3cDomainStatTable, hh3cDomainIPPoolStatTable,
                  hh3cDomainServiceType, hh3cDomainIpPoolName, and hh3cDomainIpv6PoolName"

    REVISION     "201311250000Z"          -- November 25, 2013 at 00:00 GMT
        DESCRIPTION  "Changed the range of hh3cDomainDefault and hh3cDomainName"

    REVISION     "201304250000Z"          -- April 25, 2013 at 00:00 GMT
        DESCRIPTION  "Deleted the range of hh3cDomainIdleCutMaxTime"

    REVISION     "201302280000Z"          -- February 28, 2013 at 00:00 GMT
        DESCRIPTION  "Changed hh3cDomainSchemeAccessMode"

    REVISION     "201210150000Z"          -- October 15, 2012 at 00:00 GMT
        DESCRIPTION  "Added enumeration value ldap(5) to object hh3cDomainSchemeMode"

    REVISION     "201205200000Z"          -- May 20, 2012 at 00:00 GMT
        DESCRIPTION  "Added hh3cDomainIdleCutTime"

    REVISION     "200908050000Z"          -- August 5, 2009 at 00:00 GMT
        DESCRIPTION  "Added enumeration value reserved(12) to object hh3cAccessModeofDomainScheme"

    REVISION     "200812300000Z"          -- December 30, 2008 at 00:00 GMT
        DESCRIPTION  "Added hh3cDomainCurrentAccessNum"

    REVISION     "200811250000Z"          -- November 25, 2008 at 00:00 GMT
        DESCRIPTION  "Added enumeration value vlanlist(3) to object hh3cDomainVlanAssignMode"

    REVISION     "200703070000Z"          -- March 7, 2007 at 00:00 GMT
        DESCRIPTION  "Changed the SYNTAX of hh3cDomainName and hh3cDomainDefault"

    REVISION     "200603270000Z"          -- March 27, 2006 at 00:00 GMT
        DESCRIPTION  "1. Modified the description of hh3cDomainSchemeRowStatus
                  2. Added hh3cDomainSchemeAAAType, hh3cDomainSchemeAAAName,
                     and hh3cDomainSchemeAccessMode
                  3. Changed the value range for objects hh3cDomainAuthSchemeName
                     and hh3cDomainAcctSchemeName"

    REVISION     "200506300000Z"          -- June 30, 2005 at 00:00 GMT
        DESCRIPTION  "Updated the SMIv2 syntax of some MIB objects"

    REVISION     "200503230000Z"          -- March 23, 2005 at 00:00 GMT
        DESCRIPTION  "The initial version, created"

    ::= { hh3cCommon 46 }

    Hh3cModeOfDomainScheme ::= TEXTUAL-CONVENTION
        STATUS current
        DESCRIPTION
        "The scheme mode of the domain.
        none: indicates the domain has no scheme.
        local:indicates the domain will use local-server as a scheme.
        radius:indicates the domain will use radius scheme.
        tacacs:indicates the domain will use tacacs scheme.
        ldap:indicates the domain will use ldap scheme."
        SYNTAX INTEGER
        {
            none(1),
            local(2),
            radius(3),
            tacacs(4),
            ldap(5)
        }

    Hh3cAAATypeDomainScheme ::= TEXTUAL-CONVENTION
        STATUS current
        DESCRIPTION
        "The service type of the server."
        SYNTAX INTEGER
        {
            accounting(1),
            authentication(2),
            authorization(3),
            none(4)
        }

    Hh3cAccessModeofDomainScheme ::= TEXTUAL-CONVENTION
        STATUS current
        DESCRIPTION
        "The access mode of the domain."
        SYNTAX INTEGER
        {
            default(1),
            login(2),
            lanAccess(3),
            portal(4),
            ppp(5),
            gcm(6),
            dvpn(7),
            dhcp(8),
            voice(9),
            superauthen(10),
            command(11),
            reserved(12)
        }

    hh3cDomainControl OBJECT IDENTIFIER ::= { hh3cDomain 1 }

    hh3cDomainDefault OBJECT-TYPE
        SYNTAX      OCTET STRING (SIZE (1..255))
        MAX-ACCESS  read-write
        STATUS      current
        DESCRIPTION
        "Specifies default domain on the equipment.  Default value is 'system'."
    ::=  { hh3cDomainControl 1 }


    hh3cDomainTables OBJECT IDENTIFIER ::= { hh3cDomain 2 }

    hh3cDomainInfoTable OBJECT-TYPE
        SYNTAX  SEQUENCE OF Hh3cDomainInfoEntry
        MAX-ACCESS  not-accessible
        STATUS  current
        DESCRIPTION
        "The (conceptual) table listing the domains."
    ::= { hh3cDomainTables 1 }

    hh3cDomainInfoEntry OBJECT-TYPE
        SYNTAX  Hh3cDomainInfoEntry
        MAX-ACCESS  not-accessible
        STATUS  current
        DESCRIPTION
        "An entry (conceptual row) representing a domain."
        INDEX { hh3cDomainName }
    ::= { hh3cDomainInfoTable 1 }

    Hh3cDomainInfoEntry ::= SEQUENCE {
        hh3cDomainName                   OCTET STRING,
        hh3cDomainState                  INTEGER,
        hh3cDomainMaxAccessNum           Integer32,
        hh3cDomainVlanAssignMode         INTEGER,
        hh3cDomainIdleCutEnable          TruthValue,
        hh3cDomainIdleCutMaxTime         Integer32,
        hh3cDomainIdleCutMinFlow         Integer32,
        hh3cDomainMessengerEnable        TruthValue,
        hh3cDomainMessengerLimitTime     Integer32,
        hh3cDomainMessengerSpanTime      Integer32,
        hh3cDomainSelfServiceEnable      TruthValue,
        hh3cDomainSelfServiceURL         OCTET STRING,
        hh3cDomainAccFailureAction       INTEGER,
        hh3cDomainRowStatus              RowStatus,
        hh3cDomainCurrentAccessNum       Integer32,
        hh3cDomainIdleCutTime            TimeTicks,
        hh3cDomainServiceType            INTEGER,
        hh3cDomainIpPoolName             OCTET STRING,
        hh3cDomainIpv6PoolName           OCTET STRING,
        hh3cDomainIPv4PoolUpperValue     Integer32,
        hh3cDomainIPv4PoolLowerValue     Integer32,
        hh3cDomainIPv6PoolUpperValue     Integer32,
        hh3cDomainIPv6PoolLowerValue     Integer32,
        hh3cDomainIpPoolGroupName        OCTET STRING,
        hh3cDomainIpv6PoolGroupName      OCTET STRING,
        hh3cDomainNdPrefixPoolName       OCTET STRING,
        hh3cDomainNdPrefixPoolGroupName  OCTET STRING,
        hh3cDomainIpv6Prefix             Ipv6AddressPrefix,
        hh3cDomainIpv6PrefixLength       Integer32,
        hh3cDomainActiveWebServerUrl     OCTET STRING,
        hh3cDomainActiveWebServerIpv6Url OCTET STRING}

    hh3cDomainName   OBJECT-TYPE
        SYNTAX  OCTET STRING (SIZE (1..255))
        MAX-ACCESS  read-only
        STATUS  current
        DESCRIPTION
        "An index uniquely identifies a domain. "
    ::= { hh3cDomainInfoEntry  1 }

    hh3cDomainState   OBJECT-TYPE
        SYNTAX INTEGER
        {
            active(1),
            block(2)
        }
        MAX-ACCESS  read-create
        STATUS  current
        DESCRIPTION
        "The state of the domain, which reflects whether the domain is active.
        Default value is active."
    ::= { hh3cDomainInfoEntry  2 }

    hh3cDomainMaxAccessNum   OBJECT-TYPE
        SYNTAX Integer32
        MAX-ACCESS  read-create
        STATUS  current
        DESCRIPTION
        "The maximum number which the domain allows to access.  If the value
        is set to 0, the access limit will be disabled."
    ::= { hh3cDomainInfoEntry  3 }

    hh3cDomainVlanAssignMode   OBJECT-TYPE
        SYNTAX INTEGER
        {
            integer(1),
            string(2),
            vlanlist(3)
        }
        MAX-ACCESS  read-create
        STATUS  current
        DESCRIPTION
        "The vlan assignment mode.  The mode SHOULD be the same as the mode of
        corresponding server.
        1 (integer) - Integer Vlan assignment mode.
        2 (string)  - String Vlan assignment mode.
        3 (vlanlist)  - VLAN-List Vlan assignment mode.
        The default value is integer."
    ::= { hh3cDomainInfoEntry  4 }

    hh3cDomainIdleCutEnable   OBJECT-TYPE
        SYNTAX TruthValue
        MAX-ACCESS  read-create
        STATUS  current
        DESCRIPTION
        "The idle cut control.  Setting this attribute to true, the connection will be
        cut when the flow is less than hh3cDomainIdleCutMinFlow and lasts
        hh3cDomainIdleCutMaxTime. Default value is false."
    ::= { hh3cDomainInfoEntry  5 }

    hh3cDomainIdleCutMaxTime   OBJECT-TYPE
        SYNTAX Integer32
        MAX-ACCESS  read-create
        STATUS  current
        DESCRIPTION
        "The maximal time of idle-cut.  The unit is minute.  If the value of
        hh3cDomainIdleCutEnable is false, the value of hh3cDomainIdleCutMaxTime
        is meaningless."
    ::= { hh3cDomainInfoEntry  6 }

    hh3cDomainIdleCutMinFlow   OBJECT-TYPE
        SYNTAX Integer32(1..10240000)
        MAX-ACCESS  read-create
        STATUS  current
        DESCRIPTION
        "The minimal flow of idle-cut.  The unit is byte. If the value of
        hh3cDomainIdleCutEnable is false, the value of hh3cDomainIdleCutMinFlow
        is meaningless."
    ::= { hh3cDomainInfoEntry  7 }

    hh3cDomainMessengerEnable   OBJECT-TYPE
        SYNTAX TruthValue
        MAX-ACCESS  read-create
        STATUS  current
        DESCRIPTION
        "The messenger service control.  If set hh3cDomainMessengerEnable to true,
        hh3cDomainMessengerLimitTime and hh3cDomainMessengerSpanTime must be
        set to valid values.  Default value is false."
    ::= { hh3cDomainInfoEntry  8 }

    hh3cDomainMessengerLimitTime   OBJECT-TYPE
        SYNTAX Integer32(1..60)
        MAX-ACCESS  read-create
        STATUS  current
        DESCRIPTION
        "The messenger service limit time.  The unit is minute.  If the value of
        hh3cDomainMessengerEnable is false, the value of hh3cDomainMessengerLimitTime
        is meaningless."
    ::= { hh3cDomainInfoEntry  9 }

    hh3cDomainMessengerSpanTime   OBJECT-TYPE
        SYNTAX Integer32(5..60)
        MAX-ACCESS  read-create
        STATUS  current
        DESCRIPTION
        "The messenger service span time.  The unit is minute.
        It must be a multiple of 5.  If the value of hh3cDomainMessengerEnable is false,
        the value of hh3cDomainMessengerSpanTime is meaningless."
    ::= { hh3cDomainInfoEntry  10 }

    hh3cDomainSelfServiceEnable   OBJECT-TYPE
        SYNTAX TruthValue
        MAX-ACCESS  read-create
        STATUS  current
        DESCRIPTION
        "The self service control.  If set hh3cDomainSelfServiceEnable to true,
        hh3cDomainSelfServiceURL must be set to a valid value.
        Default value is FALSE."
    ::= { hh3cDomainInfoEntry  11 }

    hh3cDomainSelfServiceURL   OBJECT-TYPE
        SYNTAX OCTET STRING (SIZE (1..64))
        MAX-ACCESS  read-create
        STATUS  current
        DESCRIPTION
        "Self-service URL(Uniform Resource Locator) of the domain."
    ::= { hh3cDomainInfoEntry  12 }

    hh3cDomainAccFailureAction   OBJECT-TYPE
        SYNTAX INTEGER
        {
            ignore(1),
            reject(2)
        }
        MAX-ACCESS  read-create
        STATUS  current
        DESCRIPTION
        "Defines the action that authentication should be taken if
        authentication succeeds but the associated accounting start
        fails.
        1 (ignore) - treat as authentication success; ignore
            accounting start failure.
        2 (reject) - treat as authentication failed if
            corresponding accounting start fails.
        Default value is reject."
    ::= { hh3cDomainInfoEntry  13 }

    hh3cDomainRowStatus   OBJECT-TYPE
        SYNTAX   RowStatus
        MAX-ACCESS  read-create
        STATUS   current
        DESCRIPTION
        "This object is responsible for managing the creation, deletion and modification
        of rows, which supports active status and CreateAndGo, Destroy operation. To destroy
        an existent row, the domain of the row MUST NOT be used by user."
    ::= { hh3cDomainInfoEntry 14 }

    hh3cDomainCurrentAccessNum   OBJECT-TYPE
        SYNTAX   Integer32
        MAX-ACCESS  read-only
        STATUS   current
        DESCRIPTION
        "The current access number of the domain."
    ::= { hh3cDomainInfoEntry 15 }

    hh3cDomainIdleCutTime   OBJECT-TYPE
        SYNTAX TimeTicks
        MAX-ACCESS  read-only
        STATUS  current
        DESCRIPTION
        "Authentication aging time.  If no packet is transmitted during the aging time,
        the authentication is aged out."
    ::= { hh3cDomainInfoEntry  16 }

    hh3cDomainServiceType   OBJECT-TYPE
        SYNTAX INTEGER
        {
            hsi(1),
            stb(2),
            voip(3)
        }
        MAX-ACCESS  read-create
        STATUS  current
        DESCRIPTION
        "Service type of users in the domain, including hsi(1), stb(2), and voip(3).
         The default value is hsi.

         The High Speed Internet (hsi) service is applicable to users that access the
         network through PPP, 802.1X, or IPoE. If this service is used, the multicast feature of
         the access module is disabled to save system resources.

         The Set Top Box (stb) service is applicable to users that access the network
         through stb. If this service is used, the multicast feature of the access module
         is enabled to improve the performance of the multicast module.

         The Voice over IP (voip) service is applicable to users that access the network
         through IP phones. If this service is used, the Quality of Service (QoS) module
         increases the priority of voice traffic to reduce the transmission delay for
         IP phone users.

        Default value is hsi."
    ::= { hh3cDomainInfoEntry  17 }

    hh3cDomainIpPoolName   OBJECT-TYPE
        SYNTAX OCTET STRING (SIZE (0..63))
        MAX-ACCESS  read-create
        STATUS  current
        DESCRIPTION
        "Specifies an IPv4 address pool for users in the domain."
    ::= { hh3cDomainInfoEntry  18 }

    hh3cDomainIpv6PoolName   OBJECT-TYPE
        SYNTAX OCTET STRING (SIZE (0..63))
        MAX-ACCESS  read-create
        STATUS  current
        DESCRIPTION
        "Specifies an IPv6 address pool for users in the domain."
    ::= { hh3cDomainInfoEntry  19 }

    hh3cDomainIPv4PoolUpperValue OBJECT-TYPE
        SYNTAX Integer32 (0..100)
        MAX-ACCESS read-create
        STATUS current
        DESCRIPTION
        "High alarm threshold for authorization IPv4 address usage, in percentage.
        Value 0 indicates that no alarm notifications will be generated for high
        authorization IPv4 address usage."
        ::= { hh3cDomainInfoEntry 20 }

    hh3cDomainIPv4PoolLowerValue OBJECT-TYPE
        SYNTAX Integer32 (0..100)
        MAX-ACCESS read-create
        STATUS current
        DESCRIPTION
        "Low alarm threshold for authorization IPv4 address usage, in percentage.
        Value 100 indicates that no alarm notifications will be generated for low
        authorization IPv4 address usage."
        ::= { hh3cDomainInfoEntry 21 }

    hh3cDomainIPv6PoolUpperValue OBJECT-TYPE
        SYNTAX Integer32 (0..100)
        MAX-ACCESS read-create
        STATUS current
        DESCRIPTION
        "High alarm threshold for authorization IPv6 address or prefix usage, in percentage.
        Value 0 indicates that no alarm notifications will be generated for high
        authorization IPv6 address or prefix usage."
        ::= { hh3cDomainInfoEntry 22 }

    hh3cDomainIPv6PoolLowerValue OBJECT-TYPE
        SYNTAX Integer32 (0..100)
        MAX-ACCESS read-create
        STATUS current
        DESCRIPTION
        "Low alarm threshold for authorization IPv6 address or prefix usage, in percentage.
        Value 100 indicates that no alarm notifications will be generated for low
        authorization IPv6 address or prefix usage."
        ::= { hh3cDomainInfoEntry 23 }

    hh3cDomainIpPoolGroupName   OBJECT-TYPE
        SYNTAX OCTET STRING (SIZE (0..63))
        MAX-ACCESS  read-create
        STATUS  current
        DESCRIPTION
        "IP address pool group authorized to users in the domain."
        DEFVAL { "" }
    ::= { hh3cDomainInfoEntry  24 }

    hh3cDomainIpv6PoolGroupName   OBJECT-TYPE
        SYNTAX OCTET STRING (SIZE (0..63))
        MAX-ACCESS  read-create
        STATUS  current
        DESCRIPTION
        "IPv6 address pool group authorized to users in the domain."
        DEFVAL { "" }
    ::= { hh3cDomainInfoEntry  25 }

    hh3cDomainNdPrefixPoolName   OBJECT-TYPE
        SYNTAX OCTET STRING (SIZE (0..63))
        MAX-ACCESS  read-create
        STATUS  current
        DESCRIPTION
        "IPv6 address ND prefix pool authorized to users in the domain."
        DEFVAL { "" }
    ::= { hh3cDomainInfoEntry  26 }

    hh3cDomainNdPrefixPoolGroupName   OBJECT-TYPE
        SYNTAX OCTET STRING (SIZE (0..63))
        MAX-ACCESS  read-create
        STATUS  current
        DESCRIPTION
        "IPv6 address ND prefix pool group authorized to users in the domain."
        DEFVAL { "" }
    ::= { hh3cDomainInfoEntry  27 }

    hh3cDomainIpv6Prefix   OBJECT-TYPE
        SYNTAX Ipv6AddressPrefix
        MAX-ACCESS  read-create
        STATUS  current
        DESCRIPTION
        "IPv6 address prefix authorized to users in the domain."
        DEFVAL { "" }
    ::= { hh3cDomainInfoEntry  28 }

    hh3cDomainIpv6PrefixLength   OBJECT-TYPE
        SYNTAX Integer32 (0..128)
        MAX-ACCESS  read-create
        STATUS  current
        DESCRIPTION
        "IPv6 address prefix length authorized to users in the domain."
        DEFVAL { 0 }
    ::= { hh3cDomainInfoEntry  29 }

    hh3cDomainActiveWebServerUrl   OBJECT-TYPE
        SYNTAX OCTET STRING (SIZE (0..255))
        MAX-ACCESS  read-only
        STATUS  current
        DESCRIPTION
        "Active URL(Uniform Resource Locator) of the Web server in ISP domain."
    ::= { hh3cDomainInfoEntry  30 }

    hh3cDomainActiveWebServerIpv6Url   OBJECT-TYPE
        SYNTAX OCTET STRING (SIZE (0..255))
        MAX-ACCESS  read-only
        STATUS  current
        DESCRIPTION
        "Active IPv6 URL of the Web server in ISP domain."
    ::= { hh3cDomainInfoEntry  31 }

    -- ----------------------------------------------------------------------
    -- Scheme Table
    -- ----------------------------------------------------------------------
    hh3cDomainSchemeTable OBJECT-TYPE
        SYNTAX  SEQUENCE OF Hh3cDomainSchemeEntry
        MAX-ACCESS  not-accessible
        STATUS  current
        DESCRIPTION
        "The (conceptual) table listing schemes of all domains."
    ::= { hh3cDomainTables 2 }

    hh3cDomainSchemeEntry OBJECT-TYPE
        SYNTAX  Hh3cDomainSchemeEntry
        MAX-ACCESS  not-accessible
        STATUS  current
        DESCRIPTION
        "An entry (conceptual row) representing an IP pool of a domain"
        INDEX { hh3cDomainName, hh3cDomainSchemeIndex }
    ::= { hh3cDomainSchemeTable 1 }

    Hh3cDomainSchemeEntry ::= SEQUENCE {
        hh3cDomainSchemeIndex            Integer32,
        hh3cDomainSchemeMode             Hh3cModeOfDomainScheme,
        hh3cDomainAuthSchemeName         OCTET STRING,
        hh3cDomainAcctSchemeName         OCTET STRING,
        hh3cDomainSchemeRowStatus        RowStatus,
        hh3cDomainSchemeAAAType          Hh3cAAATypeDomainScheme,
        hh3cDomainSchemeAAAName          OCTET STRING,
        hh3cDomainSchemeAccessMode       Hh3cAccessModeofDomainScheme
        }

    hh3cDomainSchemeIndex   OBJECT-TYPE
        SYNTAX Integer32
        MAX-ACCESS  not-accessible
        STATUS  current
        DESCRIPTION
        "The scheme index of domain, which is an identifier of a domain scheme."
    ::= { hh3cDomainSchemeEntry  1 }

    hh3cDomainSchemeMode   OBJECT-TYPE
        SYNTAX Hh3cModeOfDomainScheme
        MAX-ACCESS  read-create
        STATUS  current
        DESCRIPTION
        "The scheme mode of the domain.  Setting hh3cDomainSchemeMode to none(1) indicates
        the domain has none scheme.  Setting hh3cDomainSchemeMode to local(2) indicates the
        domain will use local-server as a scheme.  Setting hh3cDomainSchemeMode to radius(3),
        tacacs(4) or ldap(5) indicates the domain will use radius, tacacs or ldap scheme.  If set
        hh3cDomainSchemeMode to radius(3), tacacs(4) or ldap(5), hh3cDomainAuthSchemeName and
        hh3cDomainAcctSchemeName must be set to valid values.  And if hh3cDomainSchemeMode is
        set to none(1) or local(2), the value of hh3cDomainAuthSchemeName and hh3cDomainAcctSchemeName
        will be ignored."
    ::= { hh3cDomainSchemeEntry  2 }

    hh3cDomainAuthSchemeName   OBJECT-TYPE
        SYNTAX OCTET STRING (SIZE (0..32))
        MAX-ACCESS  read-create
        STATUS  current
        DESCRIPTION
        "The authentication scheme name of domain.  If hh3cDomainSchemeMode is set to radius,
        tacacs or ldap, the hh3cDomainAuthSchemeName must be configured with a valid value."
    ::= { hh3cDomainSchemeEntry  3 }

    hh3cDomainAcctSchemeName   OBJECT-TYPE
        SYNTAX OCTET STRING (SIZE (0..32))
        MAX-ACCESS  read-create
        STATUS  current
        DESCRIPTION
        "The accounting scheme name of the domain. If hh3cDomainSchemeMode is set to radius
        or tacacs, the hh3cDomainAcctSchemeName must be configured with a valid value."
    ::= { hh3cDomainSchemeEntry  4 }

    hh3cDomainSchemeRowStatus   OBJECT-TYPE
        SYNTAX RowStatus
        MAX-ACCESS  read-create
        STATUS  current
        DESCRIPTION
        "This object is responsible for managing the creation, deletion and modification
        of rows, which supports active status and createAndGo, destroy operation. To
        create a new row, hh3cDomainSchemeMode must be specified. To destroy an existent
        row, the scheme of the row MUST NOT be used by user."
    ::= { hh3cDomainSchemeEntry  5 }

    hh3cDomainSchemeAAAType    OBJECT-TYPE
        SYNTAX     Hh3cAAATypeDomainScheme
        MAX-ACCESS  read-create
        STATUS  current
        DESCRIPTION
        "Service Type of the server."
   ::= { hh3cDomainSchemeEntry  6 }

    hh3cDomainSchemeAAAName       OBJECT-TYPE
         SYNTAX      OCTET STRING(SIZE (0..32))
         MAX-ACCESS  read-create
         STATUS  current
         DESCRIPTION
         "The scheme name of the domain, whether the scheme represents accounting,
          authentication or authorization references the object hh3cDomainSchemeAAAType.
          The value of the object must be valid if the value of hh3cDomainSchemeMode
          is radius or tacacs, the value of the object will be ignored if the value
          of hh3cDomainSchemeMode is none or local. If the domain has no scheme,
          there will be a null string. If this object is supported, the objects
          hh3cDomainAuthSchemeName and hh3cDomainAcctSchemeName will be ignored."
    ::= { hh3cDomainSchemeEntry  7 }

    hh3cDomainSchemeAccessMode    OBJECT-TYPE
         SYNTAX      Hh3cAccessModeofDomainScheme
         MAX-ACCESS  read-create
         STATUS  current
         DESCRIPTION
         "The access mode of the domain scheme."
    ::= { hh3cDomainSchemeEntry  8 }

    -- ----------------------------------------------------------------------
    -- IP pool Table
    -- ----------------------------------------------------------------------
    hh3cDomainIpPoolTable OBJECT-TYPE
        SYNTAX  SEQUENCE OF Hh3cDomainIpPoolEntry
        MAX-ACCESS  not-accessible
        STATUS  current
        DESCRIPTION
        "The (conceptual) table listing IP pools of all domains."
    ::= { hh3cDomainTables 3 }

    hh3cDomainIpPoolEntry OBJECT-TYPE
        SYNTAX  Hh3cDomainIpPoolEntry
        MAX-ACCESS  not-accessible
        STATUS  current
        DESCRIPTION
        "An entry (conceptual row) representing an IP pool of a domain."
        INDEX { hh3cDomainName, hh3cDomainIpPoolNum }
    ::= { hh3cDomainIpPoolTable 1 }

    Hh3cDomainIpPoolEntry ::= SEQUENCE {
        hh3cDomainIpPoolNum              Integer32,
        hh3cDomainIpPoolLowIpAddrType    InetAddressType,
        hh3cDomainIpPoolLowIpAddr        InetAddress,
        hh3cDomainIpPoolLen              Integer32,
        hh3cDomainIpPoolRowStatus        RowStatus }


    hh3cDomainIpPoolNum   OBJECT-TYPE
        SYNTAX   Integer32(0..99)
        MAX-ACCESS  not-accessible
        STATUS   current
        DESCRIPTION
        "The number of IP pool, which is an identifier of an IP pool."
    ::= { hh3cDomainIpPoolEntry 1 }


    hh3cDomainIpPoolLowIpAddrType   OBJECT-TYPE
        SYNTAX   InetAddressType
        MAX-ACCESS  read-create
        STATUS   current
        DESCRIPTION
        "The low IP addresses type (IPv4 or IPv6) of IP pool."
    ::= { hh3cDomainIpPoolEntry 2 }


    hh3cDomainIpPoolLowIpAddr   OBJECT-TYPE
        SYNTAX   InetAddress
        MAX-ACCESS  read-create
        STATUS   current
        DESCRIPTION
        "The low IP address of IP pool."
    ::= { hh3cDomainIpPoolEntry 3 }


    hh3cDomainIpPoolLen   OBJECT-TYPE
        SYNTAX   Integer32
        MAX-ACCESS  read-create
        STATUS   current
        DESCRIPTION
        "The length of IP pool.  Default value is 1."
    ::= { hh3cDomainIpPoolEntry 4 }

   hh3cDomainIpPoolRowStatus   OBJECT-TYPE
        SYNTAX   RowStatus
        MAX-ACCESS  read-create
        STATUS   current
        DESCRIPTION
        "This object is responsible for managing the creation, deletion and modification
        of rows, which supports active status and CreateAndGo, Destroy operation.  To
        create a new row, hh3cDomainIpPoolNum and hh3cDomainIpPoolLowIpAddr must be specified.
        To destroy an existent row, the IP pool of this row MUST NOT be used by user."
    ::= { hh3cDomainIpPoolEntry 5 }

    -- ----------------------------------------------------------------------
    -- Domain Statistics Table
    -- ----------------------------------------------------------------------
    hh3cDomainStatTable OBJECT-TYPE
        SYNTAX  SEQUENCE OF Hh3cDomainStatEntry
        MAX-ACCESS  not-accessible
        STATUS  current
        DESCRIPTION
        "The (conceptual) table listing Domain statistics."
    ::= { hh3cDomainTables 4 }

    hh3cDomainStatEntry OBJECT-TYPE
        SYNTAX  Hh3cDomainStatEntry
        MAX-ACCESS  not-accessible
        STATUS  current
        DESCRIPTION
        "An entry (conceptual row) representing statistics of a domain."
        INDEX { hh3cDomainName }
    ::= { hh3cDomainStatTable 1 }

    Hh3cDomainStatEntry ::= SEQUENCE {
        hh3cDomainAccessedNum              Unsigned32,
        hh3cDomainOnlineNum                Unsigned32,
        hh3cDomainOnlinePPPUser            Unsigned32,
        hh3cDomainOnlineIPoEUser           Unsigned32,
        hh3cDomainOnlinePPPoEUser          Unsigned32,
        hh3cDomainOnlinePPPoAUser          Unsigned32,
        hh3cDomainOnlinePPPoFRUser         Unsigned32,
        hh3cDomainOnlineLacUser            Unsigned32,
        hh3cDomainOnlineLnsUser            Unsigned32,
        hh3cDomainOnlineIPoEBindAuthUser   Unsigned32,
        hh3cDomainOnlineIPoEWebAuthUser    Unsigned32,
        hh3cDomainOnlineLeasedUser         Unsigned32,
        hh3cDomainOnlineIPv4User           Unsigned32,
        hh3cDomainOnlineIPv6User           Unsigned32,
        hh3cDomainOnlineDualStackUser      Unsigned32}


    hh3cDomainAccessedNum   OBJECT-TYPE
        SYNTAX   Unsigned32
        MAX-ACCESS  read-only
        STATUS   current
        DESCRIPTION
        "Total number of users in the domain."
    ::= { hh3cDomainStatEntry 1 }


    hh3cDomainOnlineNum   OBJECT-TYPE
        SYNTAX   Unsigned32
        MAX-ACCESS  read-only
        STATUS   current
        DESCRIPTION
        "Number of online users in the domain."
    ::= { hh3cDomainStatEntry 2 }


    hh3cDomainOnlinePPPUser   OBJECT-TYPE
        SYNTAX   Unsigned32
        MAX-ACCESS  read-only
        STATUS   current
        DESCRIPTION
        "Number of online PPP users in the domain."
    ::= { hh3cDomainStatEntry 3 }

    hh3cDomainOnlineIPoEUser   OBJECT-TYPE
        SYNTAX   Unsigned32
        MAX-ACCESS  read-only
        STATUS   current
        DESCRIPTION
        "Number of online IPoE users in the domain."
    ::= { hh3cDomainStatEntry 4 }

    hh3cDomainOnlinePPPoEUser   OBJECT-TYPE
        SYNTAX   Unsigned32
        MAX-ACCESS  read-only
        STATUS   current
        DESCRIPTION
        "Number of online PPPoE users in the domain."
    ::= { hh3cDomainStatEntry 5 }

    hh3cDomainOnlinePPPoAUser   OBJECT-TYPE
        SYNTAX   Unsigned32
        MAX-ACCESS  read-only
        STATUS   current
        DESCRIPTION
        "Number of online PPPoA users in the domain."
    ::= { hh3cDomainStatEntry 6 }

    hh3cDomainOnlinePPPoFRUser   OBJECT-TYPE
        SYNTAX   Unsigned32
        MAX-ACCESS  read-only
        STATUS   current
        DESCRIPTION
        "Number of online PPPoFR users in the domain."
    ::= { hh3cDomainStatEntry 7 }

    hh3cDomainOnlineLacUser   OBJECT-TYPE
        SYNTAX   Unsigned32
        MAX-ACCESS  read-only
        STATUS   current
        DESCRIPTION
        "Number of online LAC users in the domain."
    ::= { hh3cDomainStatEntry 8 }

    hh3cDomainOnlineLnsUser   OBJECT-TYPE
        SYNTAX   Unsigned32
        MAX-ACCESS  read-only
        STATUS   current
        DESCRIPTION
        "Number of online LNS users in the domain."
    ::= { hh3cDomainStatEntry 9 }

    hh3cDomainOnlineIPoEBindAuthUser   OBJECT-TYPE
        SYNTAX   Unsigned32
        MAX-ACCESS  read-only
        STATUS   current
        DESCRIPTION
        "Number of online IPoE users that use bind authentication in the domain."
    ::= { hh3cDomainStatEntry 10 }

    hh3cDomainOnlineIPoEWebAuthUser   OBJECT-TYPE
        SYNTAX   Unsigned32
        MAX-ACCESS  read-only
        STATUS   current
        DESCRIPTION
        "Number of online IPoE users that use WEB authentication in the domain."
    ::= { hh3cDomainStatEntry 11 }

    hh3cDomainOnlineLeasedUser   OBJECT-TYPE
        SYNTAX   Unsigned32
        MAX-ACCESS  read-only
        STATUS   current
        DESCRIPTION
        "Number of online IPoE Leased users in the domain."
    ::= { hh3cDomainStatEntry 12 }

    hh3cDomainOnlineIPv4User   OBJECT-TYPE
        SYNTAX   Unsigned32
        MAX-ACCESS  read-only
        STATUS   current
        DESCRIPTION
        "Number of online IPv4 users in the domain."
    ::= { hh3cDomainStatEntry 13 }

    hh3cDomainOnlineIPv6User   OBJECT-TYPE
        SYNTAX   Unsigned32
        MAX-ACCESS  read-only
        STATUS   current
        DESCRIPTION
        "Number of online IPv6 users in the domain."
    ::= { hh3cDomainStatEntry 14 }

    hh3cDomainOnlineDualStackUser   OBJECT-TYPE
        SYNTAX   Unsigned32
        MAX-ACCESS  read-only
        STATUS   current
        DESCRIPTION
        "Number of online dual stack users in the domain."
    ::= { hh3cDomainStatEntry 15 }

    -- ----------------------------------------------------------------------
    -- Domain IP Pool Statistics Table
    -- ----------------------------------------------------------------------
    hh3cDomainIPPoolStatTable OBJECT-TYPE
        SYNTAX  SEQUENCE OF Hh3cDomainIPPoolStatEntry
        MAX-ACCESS  not-accessible
        STATUS  current
        DESCRIPTION
        "The (conceptual) table listing IP pool statistics."
    ::= { hh3cDomainTables 5 }

    hh3cDomainIPPoolStatEntry OBJECT-TYPE
        SYNTAX  Hh3cDomainIPPoolStatEntry
        MAX-ACCESS  not-accessible
        STATUS  current
        DESCRIPTION
        "An entry (conceptual row) representing statistics of an IP pool."
        INDEX { hh3cDomainName }
    ::= { hh3cDomainIPPoolStatTable 1 }

    Hh3cDomainIPPoolStatEntry ::= SEQUENCE {
        hh3cDomainIPTotalNum                Unsigned32,
        hh3cDomainIPUsedNum                 Unsigned32,
        hh3cDomainIPConflictNum             Unsigned32,
        hh3cDomainIPExcludeNum              Unsigned32,
        hh3cDomainIPIdleNum                 Unsigned32,
        hh3cDomainIPUsedPercent             OCTET STRING,
        hh3cDomainIPv6AddressTotalNum       Unsigned32,
        hh3cDomainIPv6AddressUsedNum        Unsigned32,
        hh3cDomainIPv6AddressFreeNum        Unsigned32,
        hh3cDomainIPv6AddressConflictNum    Unsigned32,
        hh3cDomainIPv6AddressExcludeNum     Unsigned32,
        hh3cDomainIPv6AddressUsedPercent    OCTET STRING,
        hh3cDomainNDRAPrefixTotalNum        Unsigned32,
        hh3cDomainNDRAPrefixUsedNum         Unsigned32,
        hh3cDomainNDRAPrefixFreeNum         Unsigned32,
        hh3cDomainNDRAPrefixConflictNum     Unsigned32,
        hh3cDomainNDRAPrefixExcludeNum      Unsigned32,
        hh3cDomainNDRAPrefixUsedPercent     OCTET STRING,
        hh3cDomainPDPrefixTotalNum          Unsigned32,
        hh3cDomainPDPrefixUsedNum           Unsigned32,
        hh3cDomainPDPrefixFreeNum           Unsigned32,
        hh3cDomainPDPrefixConflictNum       Unsigned32,
        hh3cDomainPDPrefixExcludeNum        Unsigned32,
        hh3cDomainPDPrefixUsedPercent       OCTET STRING }


    hh3cDomainIPTotalNum   OBJECT-TYPE
        SYNTAX   Unsigned32
        MAX-ACCESS  read-only
        STATUS  current
        DESCRIPTION
        "Total number of addresses in the IP pool."
    ::= { hh3cDomainIPPoolStatEntry 1 }


    hh3cDomainIPUsedNum    OBJECT-TYPE
        SYNTAX   Unsigned32
        MAX-ACCESS  read-only
        STATUS  current
        DESCRIPTION
        "Number of addresses already used in the IP pool."
    ::= { hh3cDomainIPPoolStatEntry 2 }


    hh3cDomainIPConflictNum   OBJECT-TYPE
        SYNTAX   Unsigned32
        MAX-ACCESS  read-only
        STATUS  current
        DESCRIPTION
        "Number of conflicting addresses in the IP pool."
    ::= { hh3cDomainIPPoolStatEntry 3 }


    hh3cDomainIPExcludeNum   OBJECT-TYPE
        SYNTAX   Unsigned32
        MAX-ACCESS  read-only
        STATUS   current
        DESCRIPTION
        "Number of addresses excluded from the IP pool."
    ::= { hh3cDomainIPPoolStatEntry 4 }

   hh3cDomainIPIdleNum   OBJECT-TYPE
        SYNTAX   Unsigned32
        MAX-ACCESS  read-only
        STATUS  current
        DESCRIPTION
        "Number of idle addresses in the IP pool."
    ::= { hh3cDomainIPPoolStatEntry 5 }

    hh3cDomainIPUsedPercent   OBJECT-TYPE
        SYNTAX OCTET STRING (SIZE (0..32))
        MAX-ACCESS  read-only
        STATUS   current
        DESCRIPTION
        "Address occupancy rate in the IP pool."
    ::= { hh3cDomainIPPoolStatEntry 6 }

    hh3cDomainIPv6AddressTotalNum   OBJECT-TYPE
        SYNTAX Unsigned32
        MAX-ACCESS  read-only
        STATUS   current
        DESCRIPTION
        "Total number of IPv6 addresses in the IP pool."
    ::= { hh3cDomainIPPoolStatEntry 7 }

    hh3cDomainIPv6AddressUsedNum   OBJECT-TYPE
        SYNTAX Unsigned32
        MAX-ACCESS  read-only
        STATUS   current
        DESCRIPTION
        "Number of IPv6 addresses already used in the IP pool."
    ::= { hh3cDomainIPPoolStatEntry 8 }

    hh3cDomainIPv6AddressFreeNum   OBJECT-TYPE
        SYNTAX Unsigned32
        MAX-ACCESS  read-only
        STATUS   current
        DESCRIPTION
        "Number of idle IPv6 addresses in the IP pool."
    ::= { hh3cDomainIPPoolStatEntry 9 }

    hh3cDomainIPv6AddressConflictNum   OBJECT-TYPE
        SYNTAX Unsigned32
        MAX-ACCESS  read-only
        STATUS   current
        DESCRIPTION
        "Number of conflicting IPv6 addresses in the IP pool."
    ::= { hh3cDomainIPPoolStatEntry 10 }

    hh3cDomainIPv6AddressExcludeNum   OBJECT-TYPE
        SYNTAX Unsigned32
        MAX-ACCESS  read-only
        STATUS   current
        DESCRIPTION
        "Number of IPv6 addresses excluded from the IP pool."
    ::= { hh3cDomainIPPoolStatEntry 11 }

    hh3cDomainIPv6AddressUsedPercent   OBJECT-TYPE
        SYNTAX OCTET STRING (SIZE (1..64))
        MAX-ACCESS  read-only
        STATUS   current
        DESCRIPTION
        "IPv6 Address occupancy rate in the IP pool.
        The value is in percentage.
        For example: 0.79 means the IPv6 Address occupancy rate in the IP pool is 0.79%."
    ::= { hh3cDomainIPPoolStatEntry 12 }

    hh3cDomainNDRAPrefixTotalNum   OBJECT-TYPE
        SYNTAX Unsigned32
        MAX-ACCESS  read-only
        STATUS   current
        DESCRIPTION
        "Total number of NDRA prefix addresses in the IP pool."
    ::= { hh3cDomainIPPoolStatEntry 13 }

    hh3cDomainNDRAPrefixUsedNum   OBJECT-TYPE
        SYNTAX Unsigned32
        MAX-ACCESS  read-only
        STATUS   current
        DESCRIPTION
        "Number of NDRA prefix addresses already used in the IP pool."
    ::= { hh3cDomainIPPoolStatEntry 14 }

    hh3cDomainNDRAPrefixFreeNum   OBJECT-TYPE
        SYNTAX Unsigned32
        MAX-ACCESS  read-only
        STATUS   current
        DESCRIPTION
        "Number of idle NDRA prefix addresses in the IP pool."
    ::= { hh3cDomainIPPoolStatEntry 15 }

    hh3cDomainNDRAPrefixConflictNum   OBJECT-TYPE
        SYNTAX Unsigned32
        MAX-ACCESS  read-only
        STATUS   current
        DESCRIPTION
        "Number of conflicting NDRA prefix addresses in the IP pool."
    ::= { hh3cDomainIPPoolStatEntry 16 }

    hh3cDomainNDRAPrefixExcludeNum   OBJECT-TYPE
        SYNTAX Unsigned32
        MAX-ACCESS  read-only
        STATUS   current
        DESCRIPTION
        "Number of NDRA prefix addresses excluded from the IP pool."
    ::= { hh3cDomainIPPoolStatEntry 17 }

    hh3cDomainNDRAPrefixUsedPercent   OBJECT-TYPE
        SYNTAX OCTET STRING (SIZE (1..64))
        MAX-ACCESS  read-only
        STATUS   current
        DESCRIPTION
        "NDRA prefix occupancy rate in the IP pool.
        The value is in percentage.
        For example: 0.79 means the NDRA prefix occupancy rate in the IP pool is 0.79%."
    ::= { hh3cDomainIPPoolStatEntry 18 }

    hh3cDomainPDPrefixTotalNum   OBJECT-TYPE
        SYNTAX Unsigned32
        MAX-ACCESS  read-only
        STATUS   current
        DESCRIPTION
        "Total number of PD prefix addresses in the IP pool."
    ::= { hh3cDomainIPPoolStatEntry 19 }

    hh3cDomainPDPrefixUsedNum   OBJECT-TYPE
        SYNTAX Unsigned32
        MAX-ACCESS  read-only
        STATUS   current
        DESCRIPTION
        "Number of PD prefix addresses already used in the IP pool."
    ::= { hh3cDomainIPPoolStatEntry 20 }

    hh3cDomainPDPrefixFreeNum   OBJECT-TYPE
        SYNTAX Unsigned32
        MAX-ACCESS  read-only
        STATUS   current
        DESCRIPTION
        "Number of idle PD prefix addresses in the IP pool."
    ::= { hh3cDomainIPPoolStatEntry 21 }

    hh3cDomainPDPrefixConflictNum   OBJECT-TYPE
        SYNTAX Unsigned32
        MAX-ACCESS  read-only
        STATUS   current
        DESCRIPTION
        "Number of conflicting PD prefix addresses in the IP pool."
    ::= { hh3cDomainIPPoolStatEntry 22 }

    hh3cDomainPDPrefixExcludeNum   OBJECT-TYPE
        SYNTAX Unsigned32
        MAX-ACCESS  read-only
        STATUS   current
        DESCRIPTION
        "Number of PD prefix addresses excluded from the IP pool."
    ::= { hh3cDomainIPPoolStatEntry 23 }

    hh3cDomainPDPrefixUsedPercent   OBJECT-TYPE
        SYNTAX OCTET STRING (SIZE (1..64))
        MAX-ACCESS  read-only
        STATUS   current
        DESCRIPTION
        "PD prefix occupancy rate in the IP pool.
        The value is in percentage.
        For example: 0.79 means the PD prefix occupancy rate in the IP pool is 0.79%."
    ::= { hh3cDomainIPPoolStatEntry 24 }

    -- ----------------------------------------------------------------------
    -- Domain NAT binding Table
    -- ----------------------------------------------------------------------
    hh3cDomainNatBindingTable OBJECT-TYPE
        SYNTAX  SEQUENCE OF Hh3cDomainNatBindingEntry
        MAX-ACCESS  not-accessible
        STATUS  current
        DESCRIPTION
        "The (conceptual) table lists user group-to-NAT instance bindings of
        all domains.  The device assigns an authenticated user to a load-sharing
        user group and uses the NAT instance associated with that user group
        to process the NAT service of the user."
    ::= { hh3cDomainTables 6 }

    hh3cDomainNatBindingEntry OBJECT-TYPE
        SYNTAX  Hh3cDomainNatBindingEntry
        MAX-ACCESS  not-accessible
        STATUS  current
        DESCRIPTION
        "An entry (conceptual row) lists user group-to-NAT instance bindings of a domain."
        INDEX { hh3cDomainName, hh3cDomainNatBindingUserGroupName }
    ::= { hh3cDomainNatBindingTable 1 }

    Hh3cDomainNatBindingEntry ::= SEQUENCE {
        hh3cDomainNatBindingUserGroupName  OCTET STRING,
        hh3cDomainNatBindingNatInstance    OCTET STRING,
        hh3cDomainNatBindingRowStatus      RowStatus
        }

    hh3cDomainNatBindingUserGroupName   OBJECT-TYPE
        SYNTAX OCTET STRING (SIZE (1..32))
        MAX-ACCESS  read-only
        STATUS   current
        DESCRIPTION
        "The user group name."
    ::= { hh3cDomainNatBindingEntry 1 }

    hh3cDomainNatBindingNatInstance   OBJECT-TYPE
        SYNTAX OCTET STRING (SIZE (1..31))
        MAX-ACCESS  read-create
        STATUS   current
        DESCRIPTION
        "The bound NAT instance."
    ::= { hh3cDomainNatBindingEntry 2 }

    hh3cDomainNatBindingRowStatus   OBJECT-TYPE
        SYNTAX   RowStatus
        MAX-ACCESS  read-create
        STATUS   current
        DESCRIPTION
        "This object is responsible for managing the creation, deletion and
         modification of rows. The object supports the active state and the
         CreateAndGo and Destroy operations."
    ::= { hh3cDomainNatBindingEntry 3 }

    -- ----------------------------------------------------------------------
    -- Domain UP Statistics Table
    -- ----------------------------------------------------------------------
    hh3cDomainUpStatTable OBJECT-TYPE
        SYNTAX  SEQUENCE OF Hh3cDomainUpStatEntry
        MAX-ACCESS  not-accessible
        STATUS  current
        DESCRIPTION
        "The (conceptual) table listing domain statistics on the user plane."
    ::= { hh3cDomainTables 7 }

    hh3cDomainUpStatEntry OBJECT-TYPE
        SYNTAX  Hh3cDomainUpStatEntry
        MAX-ACCESS  not-accessible
        STATUS  current
        DESCRIPTION
        "An entry (conceptual row) representing statistics of a domain on a user plane."
        INDEX { hh3cDomainName, hh3cDomainUpId }
    ::= { hh3cDomainUpStatTable 1 }

    Hh3cDomainUpStatEntry ::= SEQUENCE {
        hh3cDomainUpId                       Unsigned32,
        hh3cDomainUpAccessedNum              Unsigned32,
        hh3cDomainUpOnlineNum                Unsigned32,
        hh3cDomainUpOnlinePPPUser            Unsigned32,
        hh3cDomainUpOnlineIPoEUser           Unsigned32,
        hh3cDomainUpOnlinePPPoEUser          Unsigned32,
        hh3cDomainUpOnlinePPPoAUser          Unsigned32,
        hh3cDomainUpOnlinePPPoFRUser         Unsigned32,
        hh3cDomainUpOnlineLacUser            Unsigned32,
        hh3cDomainUpOnlineLnsUser            Unsigned32,
        hh3cDomainUpOnlineIPoEBindAuthUser   Unsigned32,
        hh3cDomainUpOnlineIPoEWebAuthUser    Unsigned32,
        hh3cDomainUpOnlineLeasedUser         Unsigned32,
        hh3cDomainUpOnlineIPv4User           Unsigned32,
        hh3cDomainUpOnlineIPv6User           Unsigned32,
        hh3cDomainUpOnlineDualStackUser      Unsigned32
  }

    hh3cDomainUpId  OBJECT-TYPE
        SYNTAX   Unsigned32 (1024..2047)
        MAX-ACCESS  not-accessible
        STATUS   current
        DESCRIPTION
        "User plane ID."
    ::= { hh3cDomainUpStatEntry 1 }

    hh3cDomainUpAccessedNum  OBJECT-TYPE
        SYNTAX   Unsigned32
        MAX-ACCESS  read-only
        STATUS   current
        DESCRIPTION
        "Number of users in the domain of the user plane."
    ::= { hh3cDomainUpStatEntry 2 }

    hh3cDomainUpOnlineNum  OBJECT-TYPE
        SYNTAX   Unsigned32
        MAX-ACCESS  read-only
        STATUS   current
        DESCRIPTION
        "Number of online users in the domain of the user plane."
    ::= { hh3cDomainUpStatEntry 3 }

    hh3cDomainUpOnlinePPPUser  OBJECT-TYPE
        SYNTAX   Unsigned32
        MAX-ACCESS  read-only
        STATUS   current
        DESCRIPTION
        "Number of online PPP users in the domain of the user plane."
    ::= { hh3cDomainUpStatEntry 4 }

    hh3cDomainUpOnlineIPoEUser  OBJECT-TYPE
        SYNTAX   Unsigned32
        MAX-ACCESS  read-only
        STATUS   current
        DESCRIPTION
        "Number of online IPoE users in the domain of the user plane."
    ::= { hh3cDomainUpStatEntry 5 }

    hh3cDomainUpOnlinePPPoEUser  OBJECT-TYPE
        SYNTAX   Unsigned32
        MAX-ACCESS  read-only
        STATUS   current
        DESCRIPTION
        "Number of online PPPoE users in the domain of the user plane."
    ::= { hh3cDomainUpStatEntry 6 }

    hh3cDomainUpOnlinePPPoAUser  OBJECT-TYPE
        SYNTAX   Unsigned32
        MAX-ACCESS  read-only
        STATUS   current
        DESCRIPTION
        "Number of online PPPoA users in the domain of the user plane."
    ::= { hh3cDomainUpStatEntry 7 }

    hh3cDomainUpOnlinePPPoFRUser  OBJECT-TYPE
        SYNTAX   Unsigned32
        MAX-ACCESS  read-only
        STATUS   current
        DESCRIPTION
        "Number of online PPPoFR users in the domain of the user plane."
    ::= { hh3cDomainUpStatEntry 8 }

    hh3cDomainUpOnlineLacUser  OBJECT-TYPE
        SYNTAX   Unsigned32
        MAX-ACCESS  read-only
        STATUS   current
        DESCRIPTION
        "Number of online LAC users in the domain of the user plane."
    ::= { hh3cDomainUpStatEntry 9 }

    hh3cDomainUpOnlineLnsUser  OBJECT-TYPE
        SYNTAX   Unsigned32
        MAX-ACCESS  read-only
        STATUS   current
        DESCRIPTION
        "Number of online LNS users in the domain of the user plane."
    ::= { hh3cDomainUpStatEntry 10 }

    hh3cDomainUpOnlineIPoEBindAuthUser  OBJECT-TYPE
        SYNTAX   Unsigned32
        MAX-ACCESS  read-only
        STATUS   current
        DESCRIPTION
        "Number of online IPoE users that use bind authentication in the domain of the user plane."
    ::= { hh3cDomainUpStatEntry 11 }

    hh3cDomainUpOnlineIPoEWebAuthUser  OBJECT-TYPE
        SYNTAX   Unsigned32
        MAX-ACCESS  read-only
        STATUS   current
        DESCRIPTION
        "Number of online IPoE users that use Web authentication in the domain of the user plane."
    ::=  { hh3cDomainUpStatEntry 12 }

    hh3cDomainUpOnlineLeasedUser  OBJECT-TYPE
        SYNTAX   Unsigned32
        MAX-ACCESS  read-only
        STATUS   current
        DESCRIPTION
        "Number of online IPoE leased users in the domain of the user plane."
    ::= { hh3cDomainUpStatEntry 13 }

    hh3cDomainUpOnlineIPv4User  OBJECT-TYPE
        SYNTAX   Unsigned32
        MAX-ACCESS  read-only
        STATUS   current
        DESCRIPTION
        "Total number of IPv4 online users in the domain of the user plane."
    ::= { hh3cDomainUpStatEntry 14 }

    hh3cDomainUpOnlineIPv6User  OBJECT-TYPE
        SYNTAX   Unsigned32
        MAX-ACCESS  read-only
        STATUS   current
        DESCRIPTION
        "Total number of IPv6 online users in the domain of the user plane."
    ::= { hh3cDomainUpStatEntry 15 }

    hh3cDomainUpOnlineDualStackUser  OBJECT-TYPE
        SYNTAX   Unsigned32
        MAX-ACCESS  read-only
        STATUS   current
        DESCRIPTION
        "Total number of dual-stack online users in the domain of the user plane."
    ::= { hh3cDomainUpStatEntry 16 }

    -- ----------------------------------------------------------------------
    -- Domain Global Statistics Table
    -- ----------------------------------------------------------------------
    hh3cDomainGlobalStat OBJECT IDENTIFIER ::= { hh3cDomain 3 }

    hh3cDomainGlobalAccessedNum  OBJECT-TYPE
        SYNTAX   Unsigned32
        MAX-ACCESS  read-only
        STATUS   current
        DESCRIPTION
        "Number of users in all domains."
    ::=  { hh3cDomainGlobalStat 1 }

    hh3cDomainGlobalOnlineNum  OBJECT-TYPE
        SYNTAX   Unsigned32
        MAX-ACCESS  read-only
        STATUS   current
        DESCRIPTION
        "Number of online users in all domains."
    ::=  { hh3cDomainGlobalStat 2 }

    hh3cDomainGlobalOnlinePPPUser  OBJECT-TYPE
        SYNTAX   Unsigned32
        MAX-ACCESS  read-only
        STATUS   current
        DESCRIPTION
        "Number of online PPP users in all domains."
    ::=  { hh3cDomainGlobalStat 3 }

    hh3cDomainGlobalOnlineIPoEUser  OBJECT-TYPE
        SYNTAX   Unsigned32
        MAX-ACCESS  read-only
        STATUS   current
        DESCRIPTION
        "Number of online IPoE users in all domains."
    ::=  { hh3cDomainGlobalStat 4 }

    hh3cDomainGlobalOnlinePPPoEUser  OBJECT-TYPE
        SYNTAX   Unsigned32
        MAX-ACCESS  read-only
        STATUS   current
        DESCRIPTION
        "Number of online PPPoE users in all domains."
    ::=  { hh3cDomainGlobalStat 5 }

    hh3cDomainGlobalOnlinePPPoAUser  OBJECT-TYPE
        SYNTAX   Unsigned32
        MAX-ACCESS  read-only
        STATUS   current
        DESCRIPTION
        "Number of online PPPoA users in all domains."
    ::=  { hh3cDomainGlobalStat 6 }

    hh3cDomainGlobalOnlinePPPoFRUser  OBJECT-TYPE
        SYNTAX   Unsigned32
        MAX-ACCESS  read-only
        STATUS   current
        DESCRIPTION
        "Number of online PPPoFR users in all domains."
    ::=  { hh3cDomainGlobalStat 7 }

    hh3cDomainGlobalOnlineLacUser  OBJECT-TYPE
        SYNTAX   Unsigned32
        MAX-ACCESS  read-only
        STATUS   current
        DESCRIPTION
        "Number of online LAC users in all domains."
    ::=  { hh3cDomainGlobalStat 8 }

    hh3cDomainGlobalOnlineLnsUser  OBJECT-TYPE
        SYNTAX   Unsigned32
        MAX-ACCESS  read-only
        STATUS   current
        DESCRIPTION
        "Number of online LNS users in all domains."
    ::=  { hh3cDomainGlobalStat 9 }

    hh3cDomainGlobalOnlineIPoEBindAuthUser  OBJECT-TYPE
        SYNTAX   Unsigned32
        MAX-ACCESS  read-only
        STATUS   current
        DESCRIPTION
        "Number of online IPoE users that use bind authentication in all domains."
    ::=  { hh3cDomainGlobalStat 10 }

    hh3cDomainGlobalOnlineIPoEWebAuthUser  OBJECT-TYPE
        SYNTAX   Unsigned32
        MAX-ACCESS  read-only
        STATUS   current
        DESCRIPTION
        "Number of online IPoE users that use WEB authentication in all domains."
    ::=  { hh3cDomainGlobalStat 11 }

    hh3cDomainGlobalOnlineLeasedUser  OBJECT-TYPE
        SYNTAX   Unsigned32
        MAX-ACCESS  read-only
        STATUS   current
        DESCRIPTION
        "Number of online IPoE Leased users in all domains."
    ::=  { hh3cDomainGlobalStat 12 }

    hh3cDomainGlobalTotalIPv4OnlineNum  OBJECT-TYPE
        SYNTAX   Unsigned32
        MAX-ACCESS  read-only
        STATUS   current
        DESCRIPTION
        "Total number of IPv4 online users in all domains."
    ::=  { hh3cDomainGlobalStat 13 }

    hh3cDomainGlobalTotalIPv6OnlineNum  OBJECT-TYPE
        SYNTAX   Unsigned32
        MAX-ACCESS  read-only
        STATUS   current
        DESCRIPTION
        "Total number of IPv6 online users in all domains."
    ::=  { hh3cDomainGlobalStat 14 }

    hh3cDomainGlobalTotalDualStackOnlineNum  OBJECT-TYPE
        SYNTAX   Unsigned32
        MAX-ACCESS  read-only
        STATUS   current
        DESCRIPTION
        "Total number of dual stack online users in all domains."
    ::=  { hh3cDomainGlobalStat 15 }

    -- ----------------------------------------------------------------------
    -- hh3cDomainTraps Table
    -- ----------------------------------------------------------------------
    hh3cDomainTraps      OBJECT IDENTIFIER ::= { hh3cDomain 5 }
    hh3cDomainTrapsDefine      OBJECT IDENTIFIER ::= { hh3cDomainTraps 0 }

    hh3cUserIPAllocAlarm NOTIFICATION-TYPE
            OBJECTS {hh3cDomainIPUsedPercent, hh3cDomainIPv4PoolUpperValue, hh3cDomainIPv4PoolLowerValue}
            STATUS current
            DESCRIPTION
                "
                1 Notice/Trap name:  Reach IP address allocable threshold
                2 Notice/Trap generation cause:  Reach the threshold set in domain
                3 Repair suggestions:
                    Check whether to renew the configuration of the BAS IP pool
                    Add new IP pool to this domain.
                "
            ::= { hh3cDomainTrapsDefine 1 }

    hh3cUserIPAllocAlarmResume NOTIFICATION-TYPE
            OBJECTS {hh3cDomainIPUsedPercent, hh3cDomainIPv4PoolUpperValue, hh3cDomainIPv4PoolLowerValue}
            STATUS current
            DESCRIPTION
                "
                1 Notice/Trap name:  Overallocated IP address recovery
                2 Notice/Trap generation cause:  Recover from a state where IP address allocable threshold are reached.
                3 Repair suggestions: NA.
                "
            ::= { hh3cDomainTrapsDefine 2 }

    hh3cUserIPLowerlimitWarningAlarm NOTIFICATION-TYPE
            OBJECTS {hh3cDomainIPUsedPercent, hh3cDomainIPv4PoolUpperValue, hh3cDomainIPv4PoolLowerValue}
            STATUS current
            DESCRIPTION
                "
                1 Notice/Trap name:  Reach IP address allocable lower limit threshold
                2 Notice/Trap generation cause:  Reach the lower limit threshold set in domain
                3 Repair suggestions:
                    Check the domain.
                "
            ::= { hh3cDomainTrapsDefine 3 }

    hh3cUserIPLowerlimitWarningResume NOTIFICATION-TYPE
            OBJECTS {hh3cDomainIPUsedPercent, hh3cDomainIPv4PoolUpperValue, hh3cDomainIPv4PoolLowerValue}
            STATUS current
            DESCRIPTION
                "
                1 Notice/Trap name:  Less-allocated IP address recovery
                2 Notice/Trap generation cause:  Recover from a state where IP address allocable lower limit threshold are reached.
                3 Repair suggestions: NA.
                "
            ::= { hh3cDomainTrapsDefine 4 }

    hh3cUserIPv6AllocAlarm NOTIFICATION-TYPE
            OBJECTS {hh3cDomainIPv6AddressUsedPercent, hh3cDomainIPv6PoolUpperValue, hh3cDomainIPv6PoolLowerValue }
            STATUS current
            DESCRIPTION
                "
                1 Notice/Trap name:  Reach IPv6 address allocable threshold
                2 Notice/Trap generation cause:  Reach the threshold set in domain
                3 Repair suggestions:
                    Check whether to renew the configuration of the BAS IPv6 address pool
                    Add new IPv6 address pool to this domain .
                "
            ::= { hh3cDomainTrapsDefine 5 }

    hh3cUserIPv6AllocAlarmResume NOTIFICATION-TYPE
            OBJECTS {hh3cDomainIPv6AddressUsedPercent, hh3cDomainIPv6PoolUpperValue, hh3cDomainIPv6PoolLowerValue }
            STATUS current
            DESCRIPTION
                "
                1 Notice/Trap name:  Overallocated IPv6 address recovery
                2 Notice/Trap generation cause:  Recover from a state where IPv6 address allocable threshold are reached.
                3 Repair suggestions: NA.
                "
            ::= { hh3cDomainTrapsDefine 6 }

    hh3cUserIPv6LowlimitWarnAlarm NOTIFICATION-TYPE
            OBJECTS {hh3cDomainIPv6AddressUsedPercent, hh3cDomainIPv6PoolUpperValue, hh3cDomainIPv6PoolLowerValue}
            STATUS current
            DESCRIPTION
                "
                1 Notice/Trap name:  Reach IPv6 address allocable lower limit threshold
                2 Notice/Trap generation cause:  Reach the lower limit threshold set at domain
                3 Repair suggestions:
                    Check the domain.
                "
            ::= { hh3cDomainTrapsDefine 7 }

    hh3cUserIPv6LowlimitWarnResume NOTIFICATION-TYPE
            OBJECTS {hh3cDomainIPv6AddressUsedPercent, hh3cDomainIPv6PoolUpperValue, hh3cDomainIPv6PoolLowerValue}
            STATUS current
            DESCRIPTION
                "
                1 Notice/Trap name:  Less-allocated IPv6 address recovery
                2 Notice/Trap generation cause:  Recover from a state where IPv6 address allocable lower limit threshold are reached.
                3 Repair suggestions: NA.
                "
            ::= { hh3cDomainTrapsDefine 8 }

    hh3cUserNDRAPfAllocAlarm NOTIFICATION-TYPE
            OBJECTS {hh3cDomainNDRAPrefixUsedPercent, hh3cDomainIPv6PoolUpperValue, hh3cDomainIPv6PoolLowerValue }
            STATUS current
            DESCRIPTION
                "
                1 Notice/Trap name:  Reach IPv6 NDRA prefix allocable threshold
                2 Notice/Trap generation cause: Reach the threshold set in domain
                3 Repair suggestions:
                    Check whether to renew the configuration of the BAS IPv6 NDRA prefix pool
                    Add new IPv6 NDRA prefix pool to this domain .
                "
            ::= { hh3cDomainTrapsDefine 9 }

    hh3cUserNDRAPfAllocAlarmResume NOTIFICATION-TYPE
            OBJECTS {hh3cDomainNDRAPrefixUsedPercent, hh3cDomainIPv6PoolUpperValue, hh3cDomainIPv6PoolLowerValue }
            STATUS current
            DESCRIPTION
                "
                1 Notice/Trap name:  Overallocated NDRA prefix recovery
                2 Notice/Trap generation cause:  Recover from a state where NDRA prefix allocable threshold are reached.
                3 Repair suggestions: NA.
                "
            ::= { hh3cDomainTrapsDefine 10 }

    hh3cUserNDRAPfLowlimitWarnAlarm NOTIFICATION-TYPE
            OBJECTS {hh3cDomainNDRAPrefixUsedPercent, hh3cDomainIPv6PoolUpperValue, hh3cDomainIPv6PoolLowerValue}
            STATUS current
            DESCRIPTION
                "
                1 Notice/Trap name:  Reach NDRA prefix allocable lower limit threshold
                2 Notice/Trap generation cause:  Reach the lower limit threshold set at domain
                3 Repair suggestions:
                    Check the domain.
                "
            ::= { hh3cDomainTrapsDefine 11 }

    hh3cUserNDRAPfLowlimitWarnResume NOTIFICATION-TYPE
            OBJECTS {hh3cDomainNDRAPrefixUsedPercent, hh3cDomainIPv6PoolUpperValue, hh3cDomainIPv6PoolLowerValue}
            STATUS current
            DESCRIPTION
                "
                1 Notice/Trap name:  Less-allocated NDRA prefix recovery
                2 Notice/Trap generation cause:  Recover from a state where NDRA Prefix allocable lower limit threshold are reached.
                3 Repair suggestions: NA.
                "
            ::= { hh3cDomainTrapsDefine 12 }

    hh3cUserPDPfAllocAlarm NOTIFICATION-TYPE
            OBJECTS {hh3cDomainPDPrefixUsedPercent, hh3cDomainIPv6PoolUpperValue, hh3cDomainIPv6PoolLowerValue }
            STATUS current
            DESCRIPTION
                "
                1 Notice/Trap name:  Reach IPv6 DHCPv6-PD prefix allocable threshold
                2 Notice/Trap generation cause:  Reach the threshold set in domain
                3 Repair suggestions:
                    Check whether to renew the configuration of the BAS IPv6 DHCPv6-PD prefix pool
                    Add new IPv6 DHCPv6-PD prefix pool to this domain .
                "
            ::= { hh3cDomainTrapsDefine 13 }

    hh3cUserPDPfAllocAlarmResume NOTIFICATION-TYPE
            OBJECTS {hh3cDomainPDPrefixUsedPercent, hh3cDomainIPv6PoolUpperValue, hh3cDomainIPv6PoolLowerValue }
            STATUS current
            DESCRIPTION
                "
                1 Notice/Trap name:  Overallocated IPv6 DHCPv6-PD prefix recovery
                2 Notice/Trap generation cause:  Recover from a state where IPv6 DHCPv6-PD Prefix allocable threshold are reached.
                3 Repair suggestions: NA.
                "
            ::= { hh3cDomainTrapsDefine 14 }

    hh3cUserPDPfLowlimitWarnAlarm NOTIFICATION-TYPE
            OBJECTS {hh3cDomainPDPrefixUsedPercent, hh3cDomainIPv6PoolUpperValue, hh3cDomainIPv6PoolLowerValue}
            STATUS current
            DESCRIPTION
                "
                1 Notice/Trap name:  Reach IPv6 DHCPv6-PD prefix allocable lower limit threshold
                2 Notice/Trap generation cause:  Reach the lower limit threshold set at domain
                3 Repair suggestions:
                    Check the domain.
                "
            ::= { hh3cDomainTrapsDefine 15 }

    hh3cUserPDPfLowlimitWarnResume NOTIFICATION-TYPE
            OBJECTS {hh3cDomainPDPrefixUsedPercent, hh3cDomainIPv6PoolUpperValue, hh3cDomainIPv6PoolLowerValue}
            STATUS current
            DESCRIPTION
                "
                1 Notice/Trap name:  Less-allocated IPv6 DHCPv6-PD prefix recovery
                2 Notice/Trap generation cause:  Recover from a state where IPv6 DHCPv6-PD Prefix allocable lower limit threshold are reached.
                3 Repair suggestions: NA.
                "
            ::= { hh3cDomainTrapsDefine 16 }

    hh3cUserWebServerDownAlarm NOTIFICATION-TYPE
            OBJECTS { hh3cDomainActiveWebServerUrl }
            STATUS current
            DESCRIPTION
                "
                This trap is generated when the Web server is not reachable.
                "
            ::= { hh3cDomainTrapsDefine 17 }

    hh3cUserWebServerUpAlarm NOTIFICATION-TYPE
            OBJECTS { hh3cDomainActiveWebServerUrl }
            STATUS current
            DESCRIPTION
                "
                This trap is generated when the Web server becomes reachable.
                "
            ::= { hh3cDomainTrapsDefine 18 }

    hh3cUserWebServerChangeAlarm NOTIFICATION-TYPE
            OBJECTS { hh3cDomainActiveWebServerUrl }
            STATUS current
            DESCRIPTION
                "
                This trap is generated when the valid URL of the Web Server changes.
                "
            ::= { hh3cDomainTrapsDefine 19 }

    hh3cUserIPv6WebServerDownAlarm NOTIFICATION-TYPE
            OBJECTS { hh3cDomainActiveWebServerIpv6Url }
            STATUS current
            DESCRIPTION
                "
                This trap is generated when the IPv6 Web server is not reachable.
                "
            ::= { hh3cDomainTrapsDefine 20 }

    hh3cUserIPv6WebServerUpAlarm NOTIFICATION-TYPE
            OBJECTS { hh3cDomainActiveWebServerIpv6Url }
            STATUS current
            DESCRIPTION
                "
                This trap is generated when the IPv6 Web server becomes reachable.
                "
            ::= { hh3cDomainTrapsDefine 21 }

    hh3cUserIPv6WebServerChangeAlarm NOTIFICATION-TYPE
            OBJECTS { hh3cDomainActiveWebServerIpv6Url }
            STATUS current
            DESCRIPTION
                "
                This trap is generated when the valid IPv6 URL of the Web Server changes.
                "
            ::= { hh3cDomainTrapsDefine 22 }
END

-- =============================================================
-- Copyright (c) 2004-2015 New H3C Tech. Co., Ltd. All rights reserved.
--
-- Description: E1T1VI MIB
-- Reference:
-- Version: V1.3
-- History:
--   V1.0 2007-04-05 Initial Version by yandehan
--   V1.1 2009-06-08 modified by TONGWEI
--        Added hh3cE1T1VIUsingTimeslotsRatio
--          and hh3cE1T1VINotifications
--   V1.2 2010-04-08 modified by TONGWEI
--        Added hh3cE1T1VIGeneral
--   V1.3 2015-08-19 modified by YUHAIYAN
--        Added hh3cE1T1VITimeslotsUsedUpCount
--          and hh3cE1T1VITimeslotSampleInterval
--          and hh3cE1T1VIUsingTimeslotsPeak
--          and hh3cE1T1VITrapTimeSlotsThreshold
--       Modified hh3cE1T1VITrapTimeSlot
-- =============================================================
HH3C-E1T1VI-MIB DEFINITIONS ::= BEGIN
    IMPORTS
        MODULE-IDENTITY, OBJECT-TYPE, Integer32, Unsigned32, NOTIFICATION-TYPE
            FROM SNMPv2-SMI
        ifIndex ,ifDescr
            FROM IF-MIB
        hh3cCommon
            FROM HH3C-OID-MIB;


-- =============================================================
-- E1T1VI Module
-- =============================================================
hh3cE1T1VI MODULE-IDENTITY
    LAST-UPDATED    "201508191800Z"         -- Aug. 19, 2015 at 18:00 GMT
    ORGANIZATION
        "New H3C Technologies Co., Ltd."
    CONTACT-INFO
        "Platform Team New H3C Technologies Co., Ltd.
         Hai-Dian District Beijing P.R. China
         http://www.h3c.com
         Zip: 100085"
    DESCRIPTION
        "This MIB provides E1/T1 voice interface information that are
        excluded by RFC 1213 and RFC 2233"
    REVISION        "201508191800Z"
    DESCRIPTION
        "Added hh3cE1T1VITimeslotsUsedUpCount
         and hh3cE1T1VITimeslotSampleInterval
         and hh3cE1T1VIUsingTimeslotsPeak
         and hh3cE1T1VITrapTimeSlotThreshold
         Modified hh3cE1T1VITrapTimeSlot"
    REVISION        "201004081855Z"
    DESCRIPTION
        "To fix bugs in the MIB file."
    REVISION        "200906081741Z"
    DESCRIPTION
        "To fix bugs in the MIB file."
    REVISION        "200704051542Z"
    DESCRIPTION
        "Initial version of this MIB module."
    ::= { hh3cCommon 76 }


hh3cE1T1VITable OBJECT-TYPE
    SYNTAX      SEQUENCE OF Hh3cE1T1VIEntry
    MAX-ACCESS  not-accessible
    STATUS      current
    DESCRIPTION
        "This table contains E1/T1 voice interface information,
        such as the total number of using time slot."
    ::= { hh3cE1T1VI 1 }

hh3cE1T1VIEntry OBJECT-TYPE
    SYNTAX      Hh3cE1T1VIEntry
    MAX-ACCESS  not-accessible
    STATUS      current
    DESCRIPTION
        "This entry contains E1/T1 voice interface information.
        The index of this Entry is ifIndex defined in ifTable
        of RFC1213-MIB."
    INDEX
        {
            ifIndex
        }
    ::= { hh3cE1T1VITable 1 }

Hh3cE1T1VIEntry ::= SEQUENCE
    {
        hh3cE1T1VIUsingTimeslots    Integer32,
        hh3cE1T1VIUsingTimeslotsRatio    Integer32,
        hh3cE1T1VITimeslotsUsedUpCount    Unsigned32,
        hh3cE1T1VITimeslotSampleInterval    Integer32,
        hh3cE1T1VIUsingTimeslotsPeak    Integer32,
        hh3cE1T1VITrapTimeSlotsThreshold    Integer32
    }

hh3cE1T1VIUsingTimeslots OBJECT-TYPE
    SYNTAX      Integer32
    MAX-ACCESS  read-only
    STATUS      current
    DESCRIPTION
        "The total number of using time slots on this interface."
    ::= { hh3cE1T1VIEntry 1 }

hh3cE1T1VIUsingTimeslotsRatio OBJECT-TYPE
    SYNTAX      Integer32
    MAX-ACCESS  read-only
    STATUS      current
    DESCRIPTION
        "The total ratio of using time slots on this interface."
    ::= { hh3cE1T1VIEntry 2 }

hh3cE1T1VITimeslotsUsedUpCount OBJECT-TYPE
    SYNTAX      Unsigned32
    MAX-ACCESS  read-only
    STATUS      current
    DESCRIPTION
        "Total number of times that all time slots were used up on this interface."
    ::= { hh3cE1T1VIEntry 3 }

hh3cE1T1VITimeslotSampleInterval OBJECT-TYPE
    SYNTAX      Integer32
    MAX-ACCESS  read-write
    STATUS      current
    DESCRIPTION
        "Sampling interval in seconds for used time slots on this interface."
    ::= { hh3cE1T1VIEntry 4 }

hh3cE1T1VIUsingTimeslotsPeak OBJECT-TYPE
    SYNTAX      Integer32
    MAX-ACCESS  read-only
    STATUS      current
    DESCRIPTION
        "The peak number of used time slots in the entire sampling period on this interface."
    ::= { hh3cE1T1VIEntry 5 }

hh3cE1T1VITrapTimeSlotsThreshold OBJECT-TYPE
    SYNTAX      Integer32
    MAX-ACCESS  read-write
    STATUS      current
    DESCRIPTION
        "When the number of used time slots reaches the threshold, the hh3cE1T1VITrapTimeSlot trap will
         be sent.  The valid range is from 1 to total number of time slots on the interface."
    ::= { hh3cE1T1VIEntry 6 }


hh3cE1T1VINotifications OBJECT IDENTIFIER ::= { hh3cE1T1VI 2 }
hh3cE1T1VITrapPrefix    OBJECT IDENTIFIER ::= { hh3cE1T1VINotifications 0 }

hh3cE1T1VITrapTimeSlot NOTIFICATION-TYPE
    OBJECTS { ifIndex, ifDescr }
    STATUS current
    DESCRIPTION
        "This trap is sent to the manager under the following
         condition: The number of used time slots of an E1/T1
         interface reaches the threshold."
    ::= { hh3cE1T1VITrapPrefix 1 }

hh3cE1T1VIGeneral  OBJECT IDENTIFIER ::= { hh3cE1T1VI 3 }

hh3cE1T1VITrapTimeSlotEnable OBJECT-TYPE
    SYNTAX  INTEGER {
            enable(1),
            disable(2)
        }
    MAX-ACCESS  read-write
    STATUS      current
    DESCRIPTION
        "This attribute controls whether the hh3cE1T1VITrapTimeSlot trap will
        be sent or not."
    DEFVAL { enable }
    ::= { hh3cE1T1VIGeneral 1 }

END

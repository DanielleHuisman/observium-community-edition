--  =================================================================
-- Copyright (c) 2004-2023 New H3C Tech. Co., Ltd. All rights reserved.
--
-- Description: This MIB provides information about Ethernet Synchronous
--              Messaging Channel feature.
-- Reference:
-- Version: V1.0
-- History:
-- V1.0 2023-02-20, Du Wei, Initial version
-- =================================================================
HH3C-ESMC-MIB DEFINITIONS ::= BEGIN

IMPORTS
    OBJECT-TYPE, MODULE-IDENTITY, NOTIFICATION-TYPE
        FROM SNMPv2-SMI
    hh3cCommon
        FROM HH3C-OID-MIB;

hh3cEsmc MODULE-IDENTITY
    LAST-UPDATED "202302200000Z"
    ORGANIZATION
        "New H3C Technologies Co., Ltd."
    CONTACT-INFO
        "No.466 Changhe Road, Binjiang District, Hangzhou, Zhejiang
        http://www.h3c.com
        Zip: 310052"
    DESCRIPTION
        "This MIB provides information about Ethernet Synchronous Messaging Channel feature."
    REVISION "202302200000Z"
    DESCRIPTION
        "The initial revision of this MIB module."
    ::= { hh3cCommon 260 }

--
-- Node definitions
--

hh3cEsmcNotifications OBJECT IDENTIFIER ::= { hh3cEsmc 1 }

hh3cEsmcNotification OBJECT IDENTIFIER ::= { hh3cEsmcNotifications 0 }

hh3cEsmcPacketLoss NOTIFICATION-TYPE
    OBJECTS { hh3cEsmcPortName }
    STATUS current
    DESCRIPTION
        "The trap is generated when esmc packet not received for more than 5000 ms."
    ::= { hh3cEsmcNotification 1 }

hh3cEsmcPacketLossResume NOTIFICATION-TYPE
    OBJECTS { hh3cEsmcPortName }
    STATUS current
    DESCRIPTION
        "The trap is generated when received esmc packet is normal."
    ::= { hh3cEsmcNotification 2 }

hh3cEsmcNotificationObjects OBJECT IDENTIFIER ::= { hh3cEsmcNotifications 1 }

hh3cEsmcPortName OBJECT-TYPE
    SYNTAX OCTET STRING
    MAX-ACCESS accessible-for-notify
    STATUS current
    DESCRIPTION
        "Port name."
    ::= { hh3cEsmcNotificationObjects 1 }

END

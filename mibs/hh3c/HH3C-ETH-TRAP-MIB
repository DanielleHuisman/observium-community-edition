-- =================================================================
-- Copyright (c) 2004-2023 New H3C Tech. Co., Ltd.  All rights reserved.
--
-- Description: ETH TRAP MIB File
-- Reference:
-- Version: V1.0
-- History:
-- V1.0 2023-04-21 created by yuanyuchen
-- =================================================================
HH3C-ETH-TRAP-MIB DEFINITIONS ::= BEGIN

IMPORTS
        hh3cCommon
    FROM HH3C-OID-MIB
        OBJECT-TYPE, MODULE-IDENTITY, NOTIFICATION-TYPE, Unsigned32
    FROM SNMPv2-SMI
        DisplayString, MacAddress
    FROM SNMPv2-TC;

hh3cEthTrap MODULE-IDENTITY
    LAST-UPDATED
        "202304210920Z"
    ORGANIZATION
        "New H3C Technologies Co., Ltd."
    CONTACT-INFO
        "No.466 Changhe Road, Binjiang District, Hangzhou, Zhejiang
         http://www.h3c.com
         Zip: 310052"
    DESCRIPTION
        "This MIB file defines the ETH trap warning feature only."
    REVISION
        "202304210920Z"
    DESCRIPTION
        "The initial version of this MIB file."
    ::= { hh3cCommon 262 }


hh3cEthTrapMlag OBJECT IDENTIFIER ::= { hh3cEthTrap 1 }

hh3cEthTrapsMlag OBJECT IDENTIFIER ::= { hh3cEthTrapMlag 0 }

-- hh3cEthTrapsMlag
hh3cEthTrapMlagSetDrvFailed NOTIFICATION-TYPE
    OBJECTS
        {
            hh3cEthTrapMlagSetDrvChassis,
            hh3cEthTrapMlagSetDrvSlot,
            hh3cEthTrapMlagSetDrvIfName,
            hh3cEthTrapMlagSetDrvMacAddress
        }
    STATUS      current
    DESCRIPTION
        "ETH m-lag failed to add the MAC address."
    ::= { hh3cEthTrapsMlag 1 }

hh3cEthTrapMlagObjects OBJECT IDENTIFIER ::= { hh3cEthTrapMlag 1 }

-- hh3cEthTrapMlagObjects
hh3cEthTrapMlagSetDrvChassis OBJECT-TYPE
    SYNTAX      Unsigned32
    MAX-ACCESS  accessible-for-notify
    STATUS      current
    DESCRIPTION
        "The information of chassis ID. If the value is 65535, the device is
         not a stacked device."
    ::= { hh3cEthTrapMlagObjects 1 }

hh3cEthTrapMlagSetDrvSlot OBJECT-TYPE
    SYNTAX      Unsigned32
    MAX-ACCESS  accessible-for-notify
    STATUS      current
    DESCRIPTION
    "The information of slot."
    ::= { hh3cEthTrapMlagObjects 2 }

hh3cEthTrapMlagSetDrvIfName OBJECT-TYPE
    SYNTAX      DisplayString (SIZE (1..255))
    MAX-ACCESS  accessible-for-notify
    STATUS      current
    DESCRIPTION
        "The information of interface name."
    ::= { hh3cEthTrapMlagObjects 3 }

hh3cEthTrapMlagSetDrvMacAddress OBJECT-TYPE
    SYNTAX      MacAddress
    MAX-ACCESS  accessible-for-notify
    STATUS      current
    DESCRIPTION
        "The information of mac address."
    ::= { hh3cEthTrapMlagObjects 4 }

END

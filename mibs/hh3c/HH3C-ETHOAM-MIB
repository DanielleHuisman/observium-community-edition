-- =================================================================
-- Copyright (c) 2004-2022 New H3C Tech. Co., Ltd. All rights reserved.
--
-- Description: Ethernet Operation, Administration,
--              and Maintenance(ETHOAM) MIB
-- Reference: IF-MIB
-- Version: V1.0
-- History:
--   V1.0 created by zhengjun
--     Initial version 2022-05-27
-- =================================================================
-- =================================================================
--
-- Import and definition
--
-- =================================================================
HH3C-ETHOAM-MIB DEFINITIONS ::= BEGIN

IMPORTS
    hh3cCommon
        FROM HH3C-OID-MIB
    MODULE-IDENTITY, NOTIFICATION-TYPE
        FROM SNMPv2-SMI
    dot3OamEventLogTimestamp, dot3OamEventLogOui, dot3OamEventLogType,
    dot3OamEventLogLocation
        FROM DOT3-OAM-MIB
    ifDescr, ifIndex
        FROM IF-MIB;

hh3cEthoam MODULE-IDENTITY
    LAST-UPDATED
        "202205271522Z"
    ORGANIZATION
        "New H3C Tech. Co., Ltd."
    CONTACT-INFO
        "Platform Team New H3C Tech. Co., Ltd.
        Hai-Dian District Beijing P.R. China
        http://www.h3c.com
        Zip:100085"
    DESCRIPTION
        "This MIB defines objects for managing Ethernet OAM.
        Ethernet OAM is a tool that monitors Layer 2 link status
        and addresses common link-related issues on the last mile."
    REVISION
        "202205271522Z"
    DESCRIPTION
        "Initial revision of the Ethoam MIB module."
    ::= { hh3cCommon  227 }

hh3cEthoamTrap            OBJECT IDENTIFIER ::= { hh3cEthoam 1 }
hh3cEthoamTrapPrefix      OBJECT IDENTIFIER ::= { hh3cEthoamTrap 0 }
hh3cEthoamNonThresholdRecovery NOTIFICATION-TYPE
    OBJECTS
        {
            ifIndex,
            ifDescr,
            dot3OamEventLogTimestamp,
            dot3OamEventLogOui,
            dot3OamEventLogType,
            dot3OamEventLogLocation
        }
    STATUS      current
    DESCRIPTION
        "A NonThresholdEventRecovery notification is sent when a local
        or remote non-threshold crossing event is recoverd"
    ::= { hh3cEthoamTrapPrefix 1 }

hh3cEthoamLoopbackFailed NOTIFICATION-TYPE
    OBJECTS
        {
            ifIndex,
            ifDescr
        }
    STATUS      current
    DESCRIPTION
        "A trap message is generated when a port
        fails to enable loopback test."
    ::= { hh3cEthoamTrapPrefix 2 }

END

-- =================================================================
-- Copyright (c) 2004-2022 New H3C Tech. Co., Ltd. All rights reserved.
--
-- Description: ftps mib
-- Reference:
-- Version: V1.0
-- History:
--  V1.0 Created by zhangfeng
--      2022-08-24 Initial version
-- =================================================================
HH3C-FTPS-MIB DEFINITIONS ::= BEGIN

IMPORTS
    hh3cCommon
        FROM HH3C-OID-MIB
    OBJECT-TYPE, MODULE-IDENTITY, NOTIFICATION-TYPE, Unsigned32
        FROM SNMPv2-SMI;

hh3cFtps MODULE-IDENTITY
    LAST-UPDATED "202208240000Z"
    ORGANIZATION
        "New H3C Tech. Co., Ltd."
    CONTACT-INFO
        "Platform Team New H3C Tech. Co., Ltd.
        Hai-Dian District Beijing P.R. China
        http://www.h3c.com
        Zip:100085"
    DESCRIPTION
        "The MIB module is used for ftp server."
    REVISION    "202208240000Z"
    DESCRIPTION    "The initial version."
    ::= { hh3cCommon 248 }

-- ==================================================================
--
-- FTPS trap parameters
--
-- ==================================================================
hh3cFtpsObjForTrap OBJECT IDENTIFIER ::= { hh3cFtps 1 }

hh3cFtpsLoginFailedTimes OBJECT-TYPE
    SYNTAX      Unsigned32
    MAX-ACCESS  accessible-for-notify
    STATUS      current
    DESCRIPTION
        "Users login failed times."
    ::= { hh3cFtpsObjForTrap 1 }

hh3cFtpsLoginFailedStatPeriod OBJECT-TYPE
    SYNTAX      Unsigned32
    UNITS       "minutes"
    MAX-ACCESS  accessible-for-notify
    STATUS      current
    DESCRIPTION
        "Users login failed statistic period."
    ::= { hh3cFtpsObjForTrap 2 }

-- ==================================================================
--
-- FTPS traps
--
-- ==================================================================
hh3cFtpsTraps OBJECT IDENTIFIER ::= { hh3cFtps 2 }
hh3cFtpsTrapsPrefix OBJECT IDENTIFIER ::= { hh3cFtpsTraps 0 }

hh3cFtpsLoginFailed NOTIFICATION-TYPE
    OBJECTS { hh3cFtpsLoginFailedTimes, hh3cFtpsLoginFailedStatPeriod }
    STATUS  current
    DESCRIPTION
        "Users failed to login ftp server too frequently."
    ::= { hh3cFtpsTrapsPrefix 1 }

hh3cFtpsLoginFailedClear NOTIFICATION-TYPE
    STATUS  current
    DESCRIPTION
        "The ftp user login-failed alarm was cleared."
    ::= { hh3cFtpsTrapsPrefix 2 }

END

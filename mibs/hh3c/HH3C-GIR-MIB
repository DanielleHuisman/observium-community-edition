-- =====================================================================
-- Copyright (c) 2004-2021 New H3C Tech.  Co., Ltd.  All rights reserved.
--
-- Description: GIR MIB
-- Reference:
-- Version: V1.0
-- History:
--   V1.0 Initial version, created by wangmeng
-- =====================================================================
HH3C-GIR-MIB DEFINITIONS ::= BEGIN

IMPORTS
    hh3cCommon
        FROM HH3C-OID-MIB
    Integer32, OBJECT-TYPE, MODULE-IDENTITY
        FROM SNMPv2-SMI;

hh3cGir MODULE-IDENTITY
    LAST-UPDATED "202107011126Z"    -- July 01, 2021 at 11:26 GMT
    ORGANIZATION
        "New H3C Technologies Co., Ltd."
    CONTACT-INFO
        "
        Platform Team New H3C Tech.  Co., Ltd.
        Hai-Dian District Beijing P.R.  China
        http://www.h3c.com
        Zip:100085
        "
    DESCRIPTION
        "
        Graceful insertion and removal (GIR) enables you to gracefully isolate
        the device from the network for device maintenance or upgrade.
        "

    REVISION "202107011126Z"
    DESCRIPTION
        "The initial revision of this MIB module."
    ::= { hh3cCommon 205 }

--
-- Node definitions
--

hh3cGirObjects OBJECT IDENTIFIER ::= { hh3cGir 1 }


hh3cGirSystemGroup OBJECT IDENTIFIER ::= { hh3cGirObjects 1 }


hh3cGirSystemMode OBJECT-TYPE
    SYNTAX INTEGER
        {
        normal(1),
        isolation(2),
        shutdown(3)
        }
    MAX-ACCESS read-write
    STATUS current
    DESCRIPTION
        "
        Change system mode.
        normal-Normal mode(Default).
        isolation-Maintenance mode by isolation.
        shutdown-Maintenance mode by shutdown.
        "
    ::= { hh3cGirSystemGroup 1 }

hh3cGirRevertDelayTime OBJECT-TYPE
    SYNTAX Integer32 (0 | 5..65535)
    UNITS "minutes"
    MAX-ACCESS read-write
    STATUS current
    DESCRIPTION
        "
        Auto change to normal mode after the specified amount of time in
        minutes.  If 0 is set, no switchback will be performed.
        "
    DEFVAL { 0 }
    ::= { hh3cGirSystemGroup 2 }


END

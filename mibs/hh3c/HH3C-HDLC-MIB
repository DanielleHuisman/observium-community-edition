-- =================================================================
-- Copyright (c) 2004-2022 New H3C Tech. Co., Ltd. All rights reserved.
--
-- Description: This MIB file is used for inquiring for HDLC(High-level
--              Data Link Control) information.
-- Reference:
-- Version:     V1.0
-- History:
--   V1.0 Initial version by wangzhenjun
-- =================================================================
HH3C-HDLC-MIB DEFINITIONS ::= BEGIN

IMPORTS
    hh3cCommon
        FROM HH3C-OID-MIB
    OBJECT-TYPE, MODULE-IDENTITY, NOTIFICATION-TYPE
        FROM SNMPv2-SMI
    DisplayString
        FROM SNMPv2-TC;



hh3cHDLC MODULE-IDENTITY
    LAST-UPDATED "202206140000Z"            -- June 14th, 2022 at 00:00 GMT
    ORGANIZATION
        "New H3C Technologies Co., Ltd."
    CONTACT-INFO
        "Platform Team New H3C Technologies Co., Ltd.
         Hai-Dian District Beijing P.R. China
         http://www.h3c.com
         Zip: 100085"
    DESCRIPTION
        "Supporting the loop detection trap for HDLC on an interface."
    REVISION    "202206140000Z"
    DESCRIPTION
        "Initial version"
    ::= { hh3cCommon 232 }

--
-- Node definitions
--

hh3cHDLCLoopbackDetectTrapOid OBJECT IDENTIFIER ::= { hh3cHDLC 1 }

hh3cHDLCLoopbackDetectIfName OBJECT-TYPE
    SYNTAX      DisplayString (SIZE (1..47))
    MAX-ACCESS  accessible-for-notify
    STATUS      current
    DESCRIPTION
        "The involved interface name of trap information."
    ::= { hh3cHDLCLoopbackDetectTrapOid 1 }

hh3cHDLCLoopbackDetectTrap OBJECT IDENTIFIER  ::= { hh3cHDLC 2 }

hh3cHDLCLoopbackDetectTrapPrefix OBJECT IDENTIFIER  ::= { hh3cHDLCLoopbackDetectTrap 0 }

hh3cHDLCLoopbackDetect NOTIFICATION-TYPE
    OBJECTS
    {
        hh3cHDLCLoopbackDetectIfName
    }
    STATUS      current
    DESCRIPTION
        "This trap is generated when a loop is detected."
    ::= { hh3cHDLCLoopbackDetectTrapPrefix 1 }

hh3cHDLCLoopbackDetectResume NOTIFICATION-TYPE
    OBJECTS
    {
        hh3cHDLCLoopbackDetectIfName
    }
    STATUS      current
    DESCRIPTION
        "This trap is generated when the loopback is removed."
    ::= { hh3cHDLCLoopbackDetectTrapPrefix 2 }

END

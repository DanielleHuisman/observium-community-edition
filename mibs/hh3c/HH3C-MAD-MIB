-- =================================================================
-- Copyright (c) 2004-2022 New H3C Tech. Co., Ltd. All rights reserved.
--
-- Description: Multi-active Detection mib
-- Reference:
-- Version: V1.0
-- History:
--   V1.0 Created by chenjie
--     Initial version 2022-09-08
-- =================================================================
HH3C-MAD-MIB DEFINITIONS ::= BEGIN

IMPORTS
        hh3cCommon
    FROM HH3C-OID-MIB
        MODULE-IDENTITY, NOTIFICATION-TYPE
    FROM SNMPv2-SMI;

hh3cMad MODULE-IDENTITY
    LAST-UPDATED "202209080000Z"
    ORGANIZATION
        "New H3C Technologies Co., Ltd."
    CONTACT-INFO
        "Platform Team New H3C Technologies Co., Ltd.
         Hai-Dian District Beijing P.R. China
         http://www.h3c.com
         Zip: 100085"
    DESCRIPTION
        "An IRF link failure causes an IRF fabric to split in multiple IRF fabrics operating with the same Layer 3 settings,
         including the same IP address. To avoid IP address collision and network issues, IRF uses multi-active detection
         (MAD) mechanisms to detect the presence of multiple identical IRF fabrics, handle collisions, and recover from faults.
        "
    REVISION "202209080000Z"
    DESCRIPTION
        "Initial version of this MIB module, including hh3cMadTrapPrex."
    ::= { hh3cCommon 253 }

hh3cMadTrap OBJECT IDENTIFIER ::= { hh3cMad 1 }
hh3cMadTrapPrex OBJECT IDENTIFIER ::= { hh3cMadTrap 0 }

hh3cMadConflictDetect NOTIFICATION-TYPE
    STATUS current
    DESCRIPTION
        "The notification is generated when the detect conflict."
    ::= { hh3cMadTrapPrex 1 }

hh3cMadConflictResume NOTIFICATION-TYPE
    STATUS current
    DESCRIPTION
        "The notification is generated when the detect conflict resume."
    ::= { hh3cMadTrapPrex 2 }

END

-- =============================================================================
-- Copyright (c) 2004-2022 New H3C Tech.  Co.  , Ltd.  All rights reserved.
--
-- Description: Multiprotocol Label Switching
--              Label Switched Path Verification MIB
-- Reference:
-- Version: V1.0
-- History:
--   V1.0 2022-07-13 Initial version Created by Zhujieyi
-- =============================================================================
HH3C-MPLSLSPV-MIB DEFINITIONS ::= BEGIN
IMPORTS
    MODULE-IDENTITY, OBJECT-TYPE, NOTIFICATION-TYPE
        FROM SNMPv2-SMI
    hh3cCommon
        FROM HH3C-OID-MIB
    ;

-- =============================================================================
-- module identity part
-- =============================================================================
hh3cMplsLspv MODULE-IDENTITY
    LAST-UPDATED
        "202207130853Z"   -- July 13, 2022 at 08:53 GMT
    ORGANIZATION
        "New H3C Technologies Co., Ltd."
    CONTACT-INFO
        "Platform Team New H3C Technologies Co., Ltd.
         Hai-Dian District Beijing P.R.  China
         http://www.h3c.com
         Zip:100085"
    DESCRIPTION
        "Multiprotocol Label Switching Label Switched Path Verification MIB"
    REVISION
        "202207130853Z"   -- July 13, 2022 at 08:54 GMT
    DESCRIPTION
        "Initial version of this MIB."
    ::= { hh3cCommon 241 }

-- =============================================================================
-- Top level components of this MIB module.
-- =============================================================================
hh3cMplsLspvNotifications OBJECT IDENTIFIER  ::= { hh3cMplsLspv 0 }

hh3cMplsLspvObjects       OBJECT IDENTIFIER  ::= { hh3cMplsLspv 1 }

hh3cMplsLspvScalarGroup   OBJECT IDENTIFIER  ::= { hh3cMplsLspvObjects 1 }

hh3cMplsLspvBaseInfo    OBJECT-TYPE
    SYNTAX      OCTET STRING (SIZE (1..127))
    MAX-ACCESS  accessible-for-notify
    STATUS      current
    DESCRIPTION
        "The base information of MPLS LSPV."
    ::= { hh3cMplsLspvScalarGroup 1 }

-- =============================================================================
-- Notifications
-- =============================================================================
hh3cMplsLspvPingProbe  NOTIFICATION-TYPE
    OBJECTS {  hh3cMplsLspvBaseInfo  }
    STATUS      current
    DESCRIPTION
      "This notification is generated when the device received
       LSPV Ping message in no response mode."
    ::= { hh3cMplsLspvNotifications 1 }

hh3cMplsLspvTracertProbe   NOTIFICATION-TYPE
    OBJECTS {  hh3cMplsLspvBaseInfo  }
    STATUS      current
    DESCRIPTION
      "This notification is generated when the device received
       LSPV Tracert message in no response mode."
    ::= { hh3cMplsLspvNotifications 2 }

-- =============================================================================
-- End of notifications.
-- =============================================================================

END

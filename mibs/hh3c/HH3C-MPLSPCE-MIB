-- =============================================================================
-- Copyright (c) 2004-2022 New H3C Tech.  Co.  , Ltd.  All rights reserved.
--
-- Description: Multiprotocol Label Switching Path Computation Element MIB
-- Reference:
-- Version: V1.0
-- History:
--   V1.0 2022-07-13 Initial version Created by Zhujieyi
--        2022-08-23 Modified by Zhujieyi, Added hh3cMplsPceDelegationInfo
-- =============================================================================
HH3C-MPLSPCE-MIB DEFINITIONS ::= BEGIN
IMPORTS
    MODULE-IDENTITY, OBJECT-TYPE, NOTIFICATION-TYPE
        FROM SNMPv2-SMI
    hh3cCommon
        FROM HH3C-OID-MIB
    ;

-- =============================================================================
-- module identity part
-- =============================================================================
hh3cMplsPce MODULE-IDENTITY
    LAST-UPDATED
        "202208230300Z"   -- August 23, 2022 at 03:00 GMT
    ORGANIZATION
        "New H3C Technologies Co., Ltd."
    CONTACT-INFO
        "Platform Team New H3C Technologies Co., Ltd.
         Hai-Dian District Beijing P.R.  China
         http://www.h3c.com
         Zip:100085"
    DESCRIPTION
        "Multiprotocol Label Switching Path Computation Element MIB"
    REVISION
        "202208230300Z"   -- August 23, 2022 at 03:00 GMT
    DESCRIPTION
        "Added hh3cMplsPceDelegationInfo."
    REVISION
        "202207130853Z"   -- July 13, 2022 at 08:54 GMT
    DESCRIPTION
        "Initial version of this MIB."
    ::= { hh3cCommon 240 }

-- =============================================================================
-- Top level components of this MIB module.
-- =============================================================================
hh3cMplsPceNotifications OBJECT IDENTIFIER  ::= { hh3cMplsPce 0 }

hh3cMplsPceObjects       OBJECT IDENTIFIER  ::= { hh3cMplsPce 1 }

hh3cMplsPceScalarGroup   OBJECT IDENTIFIER  ::= { hh3cMplsPceObjects 1 }

hh3cMplsPcePcepSessInfo    OBJECT-TYPE
    SYNTAX      OCTET STRING (SIZE (1..127))
    MAX-ACCESS  accessible-for-notify
    STATUS      current
    DESCRIPTION
        "The base information of MPLS PCEP Session."
    ::= { hh3cMplsPceScalarGroup 1 }

hh3cMplsPceDelegationInfo    OBJECT-TYPE
    SYNTAX      OCTET STRING (SIZE (1..127))
    MAX-ACCESS  accessible-for-notify
    STATUS      current
    DESCRIPTION
        "The base information of MPLS PCE Delegation."
    ::= { hh3cMplsPceScalarGroup 2 }

-- =============================================================================
-- Notifications
-- =============================================================================
hh3cMplsPcePcepSessDown  NOTIFICATION-TYPE
    OBJECTS {  hh3cMplsPcePcepSessInfo  }
    STATUS      current
    DESCRIPTION
      "This notification is generated when the PCEP Session changed to Down."
    ::= { hh3cMplsPceNotifications 1 }

hh3cMplsPcePcepSessUp  NOTIFICATION-TYPE
    OBJECTS {  hh3cMplsPcePcepSessInfo  }
    STATUS      current
    DESCRIPTION
      "This notification is generated when the PCEP Session changed to Up."
    ::= { hh3cMplsPceNotifications 2 }

hh3cMplsPceRetDelegation  NOTIFICATION-TYPE
    OBJECTS {  hh3cMplsPceDelegationInfo  }
    STATUS      current
    DESCRIPTION
      "This notification is generated when the PCE returned delegation
      for MPLS TE Tunnel."
    ::= { hh3cMplsPceNotifications 3 }

hh3cMplsPceRetDelegationClear  NOTIFICATION-TYPE
    OBJECTS {  hh3cMplsPceDelegationInfo  }
    STATUS      current
    DESCRIPTION
      "This notification is generated when the PCE delegated MPLS TE Tunnel."
    ::= { hh3cMplsPceNotifications 4 }

-- =============================================================================
-- End of notifications.
-- =============================================================================

END

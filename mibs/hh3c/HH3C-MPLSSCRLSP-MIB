-- =============================================================================
-- Copyright (c) 2004-2023 New H3C Tech.  Co.  , Ltd.  All rights reserved.
--
-- Description: Multiprotocol Label Switching Static Crlsp MIB
-- Reference:
-- Version: V1.1
-- History:
--   V1.0 2022-06-08 Initial version Created by Zhouwan
--   V1.1 2023-03-14 Modified by Long lewen, Modified hh3cMplsExtNotifications
-- =============================================================================
HH3C-MPLSSCRLSP-MIB DEFINITIONS ::= BEGIN
IMPORTS
    MODULE-IDENTITY, OBJECT-TYPE, NOTIFICATION-TYPE
        FROM SNMPv2-SMI
    hh3cCommon
        FROM HH3C-OID-MIB
    ;

-- =============================================================================
-- module identity part
-- =============================================================================
hh3cMplsScrlsp    MODULE-IDENTITY
    LAST-UPDATED
        "202303141400Z"   -- Mar 14, 2023 at 14:00 GMT
    ORGANIZATION
        "New H3C Technologies Co., Ltd."
    CONTACT-INFO
        "Platform Team New H3C Technologies Co., Ltd.
         Hai-Dian District Beijing P.R.  China
         http://www.h3c.com
         Zip:100085"
    DESCRIPTION
        "Multiprotocol Label Switching Static Crlsp MIB"
    REVISION
        "202303141400Z"   -- Mar 14, 2023 at 14:00 GMT
    DESCRIPTION
        "Modified hh3cMplsExtNotifications"
    REVISION
        "202206070920Z"   -- June 07, 2022 at 09:20 GMT
    DESCRIPTION
        "Initial version of this MIB."
    ::= { hh3cCommon 231 }

-- =============================================================================
-- Top level components of this MIB module.
-- =============================================================================
hh3cMplsScrlspNotifications OBJECT IDENTIFIER ::= { hh3cMplsScrlsp 0 }

hh3cMplsScrlspObjects       OBJECT IDENTIFIER ::= { hh3cMplsScrlsp 1 }

hh3cMplsScrlspScalarGroup   OBJECT IDENTIFIER ::= { hh3cMplsScrlspObjects 1 }

hh3cMplsScrlspBaseInfo    OBJECT-TYPE
    SYNTAX      OCTET STRING (SIZE (1..127))
    MAX-ACCESS  accessible-for-notify
    STATUS      current
    DESCRIPTION
        "The base information of MPLS static CRLSP."
    ::= { hh3cMplsScrlspScalarGroup 1 }

hh3cMplsScrlspExtInfo    OBJECT-TYPE
    SYNTAX      OCTET STRING (SIZE (1..127))
    MAX-ACCESS  accessible-for-notify
    STATUS      current
    DESCRIPTION
        "The external information of MPLS static CRLSP"
    ::= { hh3cMplsScrlspScalarGroup 2 }

-- =============================================================================
-- Notifications
-- =============================================================================
hh3cMplsScrlspDown  NOTIFICATION-TYPE
    OBJECTS {
            hh3cMplsScrlspBaseInfo,
            hh3cMplsScrlspExtInfo
            }
    STATUS      current
    DESCRIPTION
      "This notification is generated when the Static CRLSP changed to Down."
    ::= { hh3cMplsScrlspNotifications 1 }

hh3cMplsScrlspUp  NOTIFICATION-TYPE
    OBJECTS {
            hh3cMplsScrlspBaseInfo,
            hh3cMplsScrlspExtInfo
            }
    STATUS      current
    DESCRIPTION
      "This notification is generated when the Static CRLSP changed to Up."
    ::= { hh3cMplsScrlspNotifications 2 }

hh3cMplsScrlspLabelConflict    NOTIFICATION-TYPE
    OBJECTS {
            hh3cMplsScrlspBaseInfo,
            hh3cMplsScrlspExtInfo
            }
    STATUS      current
    DESCRIPTION
      "This notification is generated when the Segment Routing label is
      configured for another prefix segment."
    ::= { hh3cMplsScrlspNotifications 3 }

hh3cMplsScrlspLabelDup     NOTIFICATION-TYPE
    OBJECTS {
            hh3cMplsScrlspBaseInfo,
            hh3cMplsScrlspExtInfo
            }
    STATUS      current
    DESCRIPTION
      "This notification is generated when the Incoming label is duplicate."
    ::= { hh3cMplsScrlspNotifications 4 }

-- =============================================================================
-- End of notifications.
-- =============================================================================

END

-- ============================================================================
-- Copyright (c) 2004-2022 New H3C Tech. Co., Ltd. All rights reserved.
--
-- Description: The purpose of this MIB file is to provide the definition of
--              the IP netstream trap.
-- Reference:
-- Version: V1.0
-- History:
-- V1.0 2022-11-16
--   Initial version, created by wangyuqing
-- ============================================================================
HH3C-NETSTREAM4-MIB DEFINITIONS ::= BEGIN

IMPORTS
        hh3cCommon
    FROM HH3C-OID-MIB
        Unsigned32, OBJECT-TYPE, MODULE-IDENTITY, NOTIFICATION-TYPE
    FROM SNMPv2-SMI;

-- Node definitions
hh3cNetstream4 MODULE-IDENTITY
    LAST-UPDATED "202211231800Z"        -- Nov 23, 2022 at 18:00 GMT
    ORGANIZATION
        "New H3C Technologies Co., Ltd."
    CONTACT-INFO
        "Platform Team New H3C Technologies Co., Ltd.
         Hai-Dian District Beijing P.R. China
         http://www.h3c.com
         Zip: 100085"
    DESCRIPTION
        "This MIB file is to provide the definition of the IP netstream."
    REVISION "202211231800Z"
    DESCRIPTION
        "The initial version of this MIB file."
    ::= { hh3cCommon 256}

-- hh3cNetstream4TrapEntry
hh3cNetstream4TrapEntry OBJECT IDENTIFIER ::= { hh3cNetstream4 1 }

hh3cNetstream4TrapEntrys OBJECT IDENTIFIER  ::= { hh3cNetstream4TrapEntry 0 }

hh3cNetstream4TrapEntryTHAlarm NOTIFICATION-TYPE
    OBJECTS
        {
            hh3cNetstream4TrapEntrySpec,
            hh3cNetstream4TrapEntryChassis,
            hh3cNetstream4TrapEntrySlot
        }
    STATUS      current
    DESCRIPTION
        "If the number of netstream4 tables exceeds the maximum value of the board by 80%,
         a trap message is generated and sent to the remote monitoring device."
    ::= { hh3cNetstream4TrapEntrys 1 }

hh3cNetstream4TrapEntryTHResume NOTIFICATION-TYPE
    OBJECTS
        {
            hh3cNetstream4TrapEntrySpec,
            hh3cNetstream4TrapEntryChassis,
            hh3cNetstream4TrapEntrySlot
        }
    STATUS      current
    DESCRIPTION
        "If the number of Netstream4 tables drops below 70% of the board maximum,
         a trap message is generated and sent to the remote monitoring device."
    ::= { hh3cNetstream4TrapEntrys 2 }

hh3cNetstream4TrapEntryObjects OBJECT IDENTIFIER  ::= { hh3cNetstream4TrapEntry 1 }

-- hh3cNetstream4TrapEntryObjects

hh3cNetstream4TrapEntrySpec OBJECT-TYPE
    SYNTAX      Unsigned32
    MAX-ACCESS  accessible-for-notify
    STATUS      current
    DESCRIPTION
        "The Maximum number of entries in the IP netStream cache."
    ::= { hh3cNetstream4TrapEntryObjects 1 }

hh3cNetstream4TrapEntryChassis OBJECT-TYPE
    SYNTAX      Unsigned32
    MAX-ACCESS  accessible-for-notify
    STATUS      current
    DESCRIPTION
        "The information of chassis ID. If the value is 65535, the device is
        not a stacked device ."
    ::= { hh3cNetstream4TrapEntryObjects 2 }

hh3cNetstream4TrapEntrySlot OBJECT-TYPE
    SYNTAX      Unsigned32
    MAX-ACCESS  accessible-for-notify
    STATUS      current
    DESCRIPTION
        "The information of slot."
    ::= { hh3cNetstream4TrapEntryObjects 3 }

END

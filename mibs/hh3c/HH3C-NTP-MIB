-- =================================================================
-- Copyright (c) 2004-2022 New H3C Tech.  Co., Ltd.  All rights reserved.
--
-- Description: Network Time Protocol (NTP) Version 3, is used to synchronize
--              timekeeping among a set of distributed time servers and clients.
-- Reference:
-- Version: V2.2
-- History:
-- V1.0   <sunhaipeng>, <2003-03-19>, <initial>
-- V1.1   jinyi, 2004-12-02,
--        Fix syntax bugs and adjust format of the whole file.
-- V1.2  sunkai, 2006-03-23
--       Modified SYNTAX of hh3cNTPPeerKeyId.
-- V1.3  2010-03-05
--       Added hh3cNTPServerIP.
-- V1.4  2011-01-27
--       Added hh3cNTPSysPollSec, hh3cNTPSysClockSec.  Modified hh3cNTPServerIP.
-- V1.5  2012-04-13 by huangshengliang
--       change seconds to milliseconds.
-- V1.6  2013-05-29 by niuxuning
--       Modified local clock of hh3cNTPPeerStratum.
-- V1.7  2014-03-03 by wangjianming
--       Changed the state of hh3cNTPSysPeer to obsolete.
--       Added hh3cNTPSysSrcPeer.
-- V1.8  2016-09-14 by chenzichao
--       Corrected spelling of the word 'message'.
-- V1.9  2022-3-16 by yinwenyao kf8812
--       Added hh3cNTPSysOldServerIP for Trap by yinwenyao kf8812
--       Added hh3cNTPSysSrcVpnName for Trap by yinwenyao kf8812
--       Added hh3cNTPSysOldSrcVpnName for Trap by yinwenyao kf8812
--       Added hh3cNTPSysMaxDynamicSessions for Trap by yinwenyao kf8812
--       Added hh3cNTPSystemMIBTraps to hh3cNTPSystemMIB by yinwenyao kf8812
--       Added hh3cNTPSysStateChangeTrap by yinwenyao kf8812
--       Added hh3cNTPSysPeerChangeTrap by yinwenyao kf8812
--       Added hh3cNTPDynSessionLimit by yinwenyao kf8812
--       Added hh3cNTPDynSessionLimitResume by yinwenyao kf8812
-- V2.0  2022-06-28 by duwei
--       Added hh3cNTPSessionLimit
--       Added hh3cNTPSessionLimitResume
-- V2.1  2022-09-01 by duwei
--       Added hh3cNTPSysOldStratum,hh3cNTPSysTimeOffsetThres,
--       hh3cNTPSysTimeOffsetLimit for trap.
--       Added hh3cNTPSynchronizationLost.
--       Added hh3cNTPSynchronizationResume.
--       Added hh3cNTPSysStratumChange.
--       Added hh3cNTPTimeOffsetThresExceed.
--       Added hh3cNTPTimeOffsetThresResume.
--       Added hh3cNTPTimeOffsetLimit.
--       Added hh3cNTPTimeOffsetLimitResume.
-- V2.2  2022-09-01 by duwei
--       Added hh3cNTPSysLeapChangeTrap, hh3cNTPServerAbnormal,
--       hh3cNTPServerNormal, and hh3cNTPStepSetTimeFailed for trap.
-- =================================================================
HH3C-NTP-MIB DEFINITIONS ::= BEGIN

    IMPORTS
        IpAddress, Integer32, MODULE-IDENTITY, NOTIFICATION-TYPE, OBJECT-TYPE, Counter32, Unsigned32
            FROM SNMPv2-SMI
        RowStatus, TruthValue, DisplayString
            FROM SNMPv2-TC
        hh3cRhw
            FROM HH3C-OID-MIB;

        hh3cNTP MODULE-IDENTITY
            LAST-UPDATED "202212010000Z"
            ORGANIZATION
                "New H3C Tech.  Co., Ltd."
            CONTACT-INFO
                "Platform Team New H3C Tech.  Co., Ltd.
                Hai-Dian District Beijing P.R.  China
                http://www.h3c.com
                Zip:100085
                "
            DESCRIPTION
                "This MIB provides mechanisms to monitor a NTP server."
            REVISION "202212010000Z"
            DESCRIPTION
                "Add hh3cNTPSysLeapChangeTrap, hh3cNTPServerAbnormal,
                 hh3cNTPServerNormal, and hh3cNTPStepSetTimeFailed for trap."
            REVISION "202209010000Z"
            DESCRIPTION
                "Added hh3cNTPSysOldStratum,hh3cNTPSysTimeOffsetThres,
                 hh3cNTPSysTimeOffsetLimit for trap.
                 Added hh3cNTPSynchronizationLost.
                 Added hh3cNTPSynchronizationResume.
                 Added hh3cNTPSysStratumChange.
                 Added hh3cNTPTimeOffsetThresExceed.
                 Added hh3cNTPTimeOffsetThresResume.
                 Added hh3cNTPTimeOffsetLimit.
                 Added hh3cNTPTimeOffsetLimitResume."
            REVISION "202206280000Z"
            DESCRIPTION
                "Added hh3cNTPSessionLimit for trap.
                 Added hh3cNTPSessionLimitResume for trap."
            REVISION "202203160000Z"
            DESCRIPTION
                "Added hh3cNTPSysOldServerIP for Trap.
                 Added hh3cNTPSysSrcVpnName for Trap.
                 Added hh3cNTPSysOldSrcVpnName for Trap.
                 Added hh3cNTPSysMaxDynamicSessions for Trap.
                 Added hh3cNTPSystemMIBTraps to hh3cNTPSystemMIB.
                 Added hh3cNTPSysStateChangeTrap.
                 Added hh3cNTPSysPeerChangeTrap.
                 Added hh3cNTPSysDynamicSessionLimitReach.
                 Added hh3cNTPSysDynamicSessionLimitReachResume."
            REVISION "200303150000Z"
            DESCRIPTION
                "The initial revision of this MIB module."
            ::= { hh3cRhw 22 }

        hh3cNTPSystemMIB OBJECT IDENTIFIER ::= { hh3cNTP 1 }

    hh3cNTPSystemMIBObjects OBJECT IDENTIFIER ::= { hh3cNTPSystemMIB 1 }

    hh3cNTPSysLeap OBJECT-TYPE
        SYNTAX      INTEGER
            {
                noWarning(0),
                addSecond(1),
                subtractSecond(2),
                alarm(3)
            }
        MAX-ACCESS  read-only
        STATUS      current
        DESCRIPTION
            "Leap Indicator (LI): This is a two-bit code warning of an impending
            leap second to be inserted/deleted in the last minute of the current
            day, with bit 0 and bit 1, respectively, coded as follows:
            00, no warning
            01, last minute has 61 seconds
            10, last minute has 59 seconds)
            11, alarm condition (clock not synchronized)."
        ::= { hh3cNTPSystemMIBObjects 1 }

    hh3cNTPSysStratum OBJECT-TYPE
        SYNTAX      Integer32(1..16)
        MAX-ACCESS  read-only
        STATUS      current
        DESCRIPTION
            "This is an eight-bit integer indicating the stratum level
            of the local clock, with values defined as follows:
            0, unspecified
            1, primary reference (e.g.,, radio clock)
            2-255, secondary reference (via NTP)"
        ::= { hh3cNTPSystemMIBObjects 2 }

    hh3cNTPSysPrecision OBJECT-TYPE
        SYNTAX      Integer32(-20..20)
        MAX-ACCESS  read-only
        STATUS      current
        DESCRIPTION
            "Precision : This is a signed integer indicating the
            precision of the various clocks, in seconds to the nearest
            power of two.  The value must be rounded to the next larger
            power of two; for instance, a 50-Hz (20 ms) or 60-Hz (16.67ms)
            power-frequency clock would be assigned the value -5 (31.25 ms),
            while a 1000-Hz (1 ms) crystal-controlled clock would be assigned
            the value -9 (1.95 ms)."
        ::= { hh3cNTPSystemMIBObjects 3 }

    hh3cNTPSysRootdelay OBJECT-TYPE
        SYNTAX      OCTET STRING(SIZE(1..128))
        MAX-ACCESS  read-only
        STATUS      current
        DESCRIPTION
            "Root Delay : This is a signed fixed-point number indicating
            the total roundtrip delay to the primary reference source
            at the root of the synchronization subnet, in milliseconds.  Note
            that this variable can take on both positive and negative
            values, depending on clock precision and skew."
        ::= { hh3cNTPSystemMIBObjects 4 }

    hh3cNTPSysRootdispersion OBJECT-TYPE
        SYNTAX      OCTET STRING(SIZE(1..128))
        MAX-ACCESS  read-only
        STATUS      current
        DESCRIPTION
            "Root Dispersion : This is a signed fixed-point number
            indicating the maximum error relative to the primary
            reference source at the root of the synchronization
            subnet, in milliseconds.  Only positive values greater than
            zero are possible."
        ::= { hh3cNTPSystemMIBObjects 5 }

    hh3cNTPSysRefid OBJECT-TYPE
        SYNTAX      OCTET STRING(SIZE(1..128))
        MAX-ACCESS  read-only
        STATUS      current
        DESCRIPTION
            "Reference Clock Identifier : This is a 32-bit code
            identifying the particular reference clock.  In the
            case of stratum 0 (unspecified) or stratum 1 (primary
            reference source), this is a four-octet, left-justified,
            zero-padded ASCII string.
            Stratum, Code, Meaning
            0,       DCN,  DCN routing protocol
            0,       TSP,  TSP time protocol
            1,       ATOM, Atomic clock (calibrated)
            1,       WWVB, WWVB LF (band 5) radio
            1,       GOES, GOES UHF (band 9) satellite
            1,       WWV,  WWV HF (band 7) radio"
        ::= { hh3cNTPSystemMIBObjects 6 }

    hh3cNTPSysReftime OBJECT-TYPE
        SYNTAX      OCTET STRING(SIZE(1..128))
        MAX-ACCESS  read-only
        STATUS      current
        DESCRIPTION
            "Reference Timestamp : This is the local time, in
            timestamp format, when the local clock was last
            updated.  If the local clock has never been synchronized,
            the value is zero."
        ::= { hh3cNTPSystemMIBObjects 7 }

    hh3cNTPSysPoll OBJECT-TYPE
        SYNTAX      Integer32(-20..20)
        MAX-ACCESS  read-only
        STATUS      current
        DESCRIPTION
            "Poll Interval : This is a signed integer indicating
            the minimum interval between transmitted messages,
            in seconds as a power of two.  For instance, a value
            of six indicates a minimum interval of 64 seconds."
        ::= { hh3cNTPSystemMIBObjects 8 }

    hh3cNTPSysPeer OBJECT-TYPE
        SYNTAX      Integer32(0..2147483647)
        MAX-ACCESS  read-only
        STATUS      obsolete
        DESCRIPTION
            "This is a selector identifying the current synchronization
            source.  Usually this will be a pointer to a structure
            containing the peer variables.  The special value NULL indicates
            There is no currently valid synchronization source.
            hh3cNTPSysPeer is replaced by hh3cNTPSysSrcPeer.  Reading
            hh3cNTPSysPeer might fail because the syntax value range is limited,
            for example, when the synchronization source IP address is a Class C
            address."
        ::= { hh3cNTPSystemMIBObjects 9 }

    hh3cNTPSysState OBJECT-TYPE
        SYNTAX      INTEGER
            {
                noUpdateClock(0),
                getfreqInfo(1),
                clockBySet(2),
                clockBySetAndNoFreq(3),
                clockBySyns(4),
                findError(5)
            }
        MAX-ACCESS  read-only
        STATUS      current
        DESCRIPTION
            "This is a integer indicating the state of local clock."
        ::= { hh3cNTPSystemMIBObjects 10 }

    hh3cNTPSysOffset OBJECT-TYPE
        SYNTAX      OCTET STRING(SIZE(1..128))
        MAX-ACCESS  read-only
        STATUS      current
        DESCRIPTION
            "The offset of two clocks is the time difference between them, in milliseconds."
        ::= { hh3cNTPSystemMIBObjects 11 }

    hh3cNTPSysDrift OBJECT-TYPE
        SYNTAX      OCTET STRING(SIZE(1..128))
        MAX-ACCESS  read-only
        STATUS      current
        DESCRIPTION
            "Real clocks exhibit some variation in skew (second derivative of
            offset with time), which is called drift."
        ::= { hh3cNTPSystemMIBObjects 12 }

    hh3cNTPSysCompliance OBJECT-TYPE
        SYNTAX      OCTET STRING(SIZE(1..128))
        MAX-ACCESS  read-only
        STATUS      current
        DESCRIPTION
            "This is a string indicating the system error."
        ::= { hh3cNTPSystemMIBObjects 13 }

    hh3cNTPSysClock OBJECT-TYPE
        SYNTAX      OCTET STRING(SIZE(1..128))
        MAX-ACCESS  read-only
        STATUS      current
        DESCRIPTION
            "This is the current local time, in timestamp
            format.  Local time is derived from the hardware clock of the particular
            machine and increments at intervals depending on the design used."
        ::= { hh3cNTPSystemMIBObjects 14 }

    hh3cNTPSysStabil OBJECT-TYPE
        SYNTAX      OCTET STRING(SIZE(1..128))
        MAX-ACCESS  read-only
        STATUS      current
        DESCRIPTION
            "This is a indicating that stability of a clock is how well
            it can maintain a constant frequency."
        ::= { hh3cNTPSystemMIBObjects 15 }

    hh3cNTPSysAuthenticate OBJECT-TYPE
        SYNTAX      INTEGER
            {
                noAuthenticate(0),
                authenticate(1)
            }
        MAX-ACCESS  read-write
        STATUS      current
        DESCRIPTION
            "This is a integer indicating that system support authentication."
        ::= { hh3cNTPSystemMIBObjects 16 }

    hh3cNTPSysPollSec OBJECT-TYPE
        SYNTAX      Integer32 (2..1048576)
        MAX-ACCESS  read-write
        STATUS      current
        DESCRIPTION
            "PollSec Interval : This is a integer indicating the minimum
            interval between transmitted messages.  For instance, a value of
            six indicates a minimum interval of 6 seconds."
        ::= { hh3cNTPSystemMIBObjects 17 }

    hh3cNTPSysClockSec OBJECT-TYPE
        SYNTAX      Integer32
        MAX-ACCESS  read-only
        STATUS      current
        DESCRIPTION
            "This is the current local time, in integer format.
            Local time is derived from the hardware clock of the particular
            machine and increments at intervals depending on the design used."
        ::= { hh3cNTPSystemMIBObjects 18 }

    hh3cNTPServerIP OBJECT-TYPE
        SYNTAX      IpAddress
        MAX-ACCESS  read-write
        STATUS      current
        DESCRIPTION
            "The NTP server ip address.  It must be a unicast address,
            rather than a broadcast address, a multicast address or
            the IP address of the local clock.  To delete a configured
            NTP server ip address, please set hh3cNTPServerIP to 0."
        ::= { hh3cNTPSystemMIBObjects 19 }

    hh3cNTPSysSrcPeer OBJECT-TYPE
        SYNTAX      Unsigned32(0..4294967295)
        MAX-ACCESS  read-only
        STATUS      current
        DESCRIPTION
            "This is a selector identifying the current synchronization
            source.  Usually this will be a unsigned integer containing
            the peer variables.  The special value 0 indicates
            There is no currently valid synchronization source.
            This node will replace hh3cNTPSysPeer, because
            its value range is unlimited, and data type is changed from
            Integer32 to Unsigned32."
        ::= { hh3cNTPSystemMIBObjects 20 }

    hh3cNTPSysOldServerIP OBJECT-TYPE
        SYNTAX      IpAddress
        MAX-ACCESS  accessible-for-notify
        STATUS      current
        DESCRIPTION
            "The Old NTP server ip address. "
        ::= { hh3cNTPSystemMIBObjects 21 }

    hh3cNTPSysSrcVpnName OBJECT-TYPE
        SYNTAX      DisplayString (SIZE(0..255))
        MAX-ACCESS  accessible-for-notify
        STATUS      current
        DESCRIPTION
            "The NTP server VPN Name."
        ::= { hh3cNTPSystemMIBObjects 22 }

    hh3cNTPSysOldSrcVpnName OBJECT-TYPE
        SYNTAX      DisplayString (SIZE(0..255))
        MAX-ACCESS  accessible-for-notify
        STATUS      current
        DESCRIPTION
            "The Old NTP server VPN Name. "
        ::= { hh3cNTPSystemMIBObjects 23 }

    hh3cNTPSysMaxDynamicSessions OBJECT-TYPE
        SYNTAX      Unsigned32(0..4294967295)
        MAX-ACCESS  accessible-for-notify
        STATUS      current
        DESCRIPTION
            "Maximum number of NTP dynamic sessions."
        ::= { hh3cNTPSystemMIBObjects 24 }

    hh3cNTPSysMaxSessions OBJECT-TYPE
        SYNTAX Unsigned32
        MAX-ACCESS accessible-for-notify
        STATUS current
        DESCRIPTION
            "Maximum number of NTP sessions."
        ::= { hh3cNTPSystemMIBObjects 25 }

    hh3cNTPSysOldStratum OBJECT-TYPE
        SYNTAX Integer32 (1..16)
        MAX-ACCESS accessible-for-notify
        STATUS current
        DESCRIPTION
            "The old the stratum level of the local clock."
        ::= { hh3cNTPSystemMIBObjects 26 }

    hh3cNTPSysTimeOffsetThres OBJECT-TYPE
        SYNTAX OCTET STRING (SIZE (1..128))
        MAX-ACCESS accessible-for-notify
        STATUS current
        DESCRIPTION
            "Time offset alarm threshold, in milliseconds."
        ::= { hh3cNTPSystemMIBObjects 27 }

    hh3cNTPSysTimeOffsetLimit OBJECT-TYPE
        SYNTAX OCTET STRING (SIZE (1..128))
        MAX-ACCESS accessible-for-notify
        STATUS current
        DESCRIPTION
            "Clock synchronization offset threshold, in milliseconds."
        ::= { hh3cNTPSystemMIBObjects 28 }

--
-- Notification definitions
--
-- =================================================================
-- Traps are defined below.
hh3cNTPSystemMIBTraps OBJECT IDENTIFIER ::= { hh3cNTPSystemMIB 2 }

-- All trap definitions should be placed under this object.
hh3cNTPSystemMIBTrapPrefix OBJECT IDENTIFIER ::= { hh3cNTPSystemMIBTraps 0 }

-- All objects used for TRAP only are defined here.
hh3cNTPSysStateChangeTrap NOTIFICATION-TYPE
    OBJECTS
        {
            hh3cNTPSysState,
            hh3cNTPServerIP,
            hh3cNTPSysSrcVpnName
        }
    STATUS      current
    DESCRIPTION
        "The trap is generated when The NTP local clock state changed."
    ::= { hh3cNTPSystemMIBTrapPrefix 1 }

hh3cNTPSysPeerChangeTrap NOTIFICATION-TYPE
    OBJECTS
        {
            hh3cNTPSysOldServerIP,
            hh3cNTPSysOldSrcVpnName,
            hh3cNTPServerIP,
            hh3cNTPSysSrcVpnName
        }
    STATUS      current
    DESCRIPTION
        "The trap is generated when The peer specified by NTP has changed."
    ::= { hh3cNTPSystemMIBTrapPrefix 2 }

hh3cNTPDynSessionLimit NOTIFICATION-TYPE
    OBJECTS
        {
            hh3cNTPSysMaxDynamicSessions
        }
    STATUS      current
    DESCRIPTION
        "The trap is generated when The number of NTP dynamic sessions has reached the upper limit."
    ::= { hh3cNTPSystemMIBTrapPrefix 3 }

hh3cNTPDynSessionLimitResume NOTIFICATION-TYPE
    OBJECTS
        {
            hh3cNTPSysMaxDynamicSessions
        }
    STATUS      current
    DESCRIPTION
        "The trap is generated when The NTP dynamic session number below the limit."
    ::= { hh3cNTPSystemMIBTrapPrefix 4 }

hh3cNTPSessionLimit NOTIFICATION-TYPE
    OBJECTS { hh3cNTPSysMaxSessions }
    STATUS current
    DESCRIPTION
        "The trap is generated when the number of NTP sessions reaches the upper limit."
    ::= { hh3cNTPSystemMIBTrapPrefix 5 }

hh3cNTPSessionLimitResume NOTIFICATION-TYPE
    OBJECTS { hh3cNTPSysMaxSessions }
    STATUS current
    DESCRIPTION
        "The trap is generated when the number of NTP sessions drops below the limit."
    ::= { hh3cNTPSystemMIBTrapPrefix 6 }

hh3cNTPSynchronizationLost NOTIFICATION-TYPE
    OBJECTS { hh3cNTPSysState, hh3cNTPServerIP}
    STATUS current
    DESCRIPTION
        "The trap is generated when the local clock loses synchronization with the NTP server."
    ::= { hh3cNTPSystemMIBTrapPrefix 7 }

hh3cNTPSynchronizationResume NOTIFICATION-TYPE
    OBJECTS { hh3cNTPSysState, hh3cNTPServerIP}
    STATUS current
    DESCRIPTION
        "The trap is generated when the local clock resumes synchronization with the NTP server."
    ::= { hh3cNTPSystemMIBTrapPrefix 8 }

hh3cNTPSysStratumChange NOTIFICATION-TYPE
    OBJECTS { hh3cNTPSysStratum, hh3cNTPSysOldStratum }
    STATUS current
    DESCRIPTION
        "The trap is generated when the stratum level of the local clock changes."
    ::= { hh3cNTPSystemMIBTrapPrefix 9 }

hh3cNTPTimeOffsetThresExceed NOTIFICATION-TYPE
    OBJECTS { hh3cNTPSysOffset, hh3cNTPSysTimeOffsetThres }
    STATUS current
    DESCRIPTION
        "The trap is generated when the time offset between the clock source and
        the client reaches the threshold."
    ::= { hh3cNTPSystemMIBTrapPrefix 10 }

hh3cNTPTimeOffsetThresResume NOTIFICATION-TYPE
    OBJECTS { hh3cNTPSysOffset, hh3cNTPSysTimeOffsetThres }
    STATUS current
    DESCRIPTION
        "The trap is generated when the time offset between the clock source and
        the client drops below the threshold."
    ::= { hh3cNTPSystemMIBTrapPrefix 11 }

hh3cNTPTimeOffsetLimit NOTIFICATION-TYPE
    OBJECTS { hh3cNTPSysOffset, hh3cNTPSysTimeOffsetLimit }
    STATUS current
    DESCRIPTION
        "The trap is generated when the time offset between the clock source and
        the client over the upper limit for clock synchronization.
        The client will not synchronize with the clock source."
    ::= { hh3cNTPSystemMIBTrapPrefix 12 }

hh3cNTPTimeOffsetLimitResume NOTIFICATION-TYPE
    OBJECTS { hh3cNTPSysOffset, hh3cNTPSysTimeOffsetLimit }
    STATUS current
    DESCRIPTION
        "The trap is generated when the time offset between the clock source and
        the client drops below the upper limit for clock synchronization."
    ::= { hh3cNTPSystemMIBTrapPrefix 13 }

hh3cNTPSysLeapChangeTrap NOTIFICATION-TYPE
    OBJECTS { hh3cNTPSysLeap }
    STATUS current
    DESCRIPTION
        "The trap is generated when System Leap Indicator changed after clock update."
    ::= { hh3cNTPSystemMIBTrapPrefix 14 }

hh3cNTPServerAbnormal NOTIFICATION-TYPE
    OBJECTS { hh3cNTPServerIP }
    STATUS current
    DESCRIPTION
        "The trap is generated when NTP server state went abnormal."
    ::= { hh3cNTPSystemMIBTrapPrefix 15 }

hh3cNTPServerNormal NOTIFICATION-TYPE
    OBJECTS { hh3cNTPServerIP }
    STATUS current
    DESCRIPTION
        "The trap is generated when NTP server state returned to normal."
    ::= { hh3cNTPSystemMIBTrapPrefix 16 }

hh3cNTPStepSetTimeFailed NOTIFICATION-TYPE
    STATUS current
    DESCRIPTION
        "The trap is generated upon failure to set system time in the one-step adjustment process."
    ::= { hh3cNTPSystemMIBTrapPrefix 17 }

    hh3cNTPPeerMIB OBJECT IDENTIFIER ::= { hh3cNTP 2 }

    hh3cNTPPeerMIBObjects OBJECT IDENTIFIER ::= { hh3cNTPPeerMIB 1 }

    hh3cNTPPeerTable OBJECT-TYPE
        SYNTAX SEQUENCE OF Hh3cNTPPeerEntry
        MAX-ACCESS  not-accessible
        STATUS      current
        DESCRIPTION
            "This table provides information on the peers with
            which the local NTP server has associations.  The peers
            are also NTP servers but running on different hosts."
        ::= { hh3cNTPPeerMIBObjects 1 }

    hh3cNTPPeerEntry OBJECT-TYPE
        SYNTAX Hh3cNTPPeerEntry
        MAX-ACCESS  not-accessible
        STATUS      current
        DESCRIPTION
            "Each peers' entry provides NTP information retrieved
            from a particular peer NTP server.  Each peer is
            identified by a unique association identifier.
            Entries are automatically created when the user
            configures the NTP server to be associated with remote
            peers.  Similarly entries are deleted when the user
            removes the peer association from the NTP server.
            Entries can also be created by the management station
            by setting values for the following objects:
            hh3cNTPPeerRemAdr and making the hh3cNTPPeerRowStatus as
            'active'.  At the least, the management station has
            to set a value for hh3cNTPPeerRemAdr to make the
            row active."
    INDEX { hh3cNTPPeerRemAdr, hh3cNTPPeerHMode }
    ::= { hh3cNTPPeerTable 1 }

    Hh3cNTPPeerEntry ::=
        SEQUENCE
            {
                hh3cNTPPeerConfig            TruthValue,
                hh3cNTPPeerAuthenable        TruthValue,
                hh3cNTPPeerAuthentic         TruthValue,
                hh3cNTPPeerRemAdr            IpAddress,
                hh3cNTPPeerRemPort           Integer32,
                hh3cNTPPeerLocAdr            IpAddress,
                hh3cNTPPeerLocPort           Integer32,
                hh3cNTPPeerLeap              INTEGER,
                hh3cNTPPeerHMode             INTEGER,
                hh3cNTPPeerStratum           Integer32,
                hh3cNTPPeerPPoll             Integer32,
                hh3cNTPPeerHPoll             Integer32,
                hh3cNTPPeerPrecision         Integer32,
                hh3cNTPPeerRootDelay         OCTET STRING,
                hh3cNTPPeerRootDispersion    OCTET STRING,
                hh3cNTPPeerRefId             OCTET STRING,
                hh3cNTPPeerRefTime           OCTET STRING,
                hh3cNTPPeerOrg               OCTET STRING,
                hh3cNTPPeerRec               OCTET STRING,
                hh3cNTPPeerXmt               OCTET STRING,
                hh3cNTPPeerReach             Integer32,
                hh3cNTPPeerValid             Integer32,
                hh3cNTPPeerTimer             Integer32,
                hh3cNTPPeerDelay             OCTET STRING,
                hh3cNTPPeerOffset            OCTET STRING,
                hh3cNTPPeerJitter            OCTET STRING,
                hh3cNTPPeerDispersion        OCTET STRING,
                hh3cNTPPeerKeyId             Unsigned32,
                hh3cNTPPeerFiltDelay         OCTET STRING,
                hh3cNTPPeerFiltOffset        OCTET STRING,
                hh3cNTPPeerFiltError         OCTET STRING,
                hh3cNTPPeerPMode             INTEGER,
                hh3cNTPPeerReceived          Counter32,
                hh3cNTPPeerSent              Counter32,
                hh3cNTPPeerFlash             BITS,
                hh3cNTPPeerRowStatus         RowStatus
            }

    hh3cNTPPeerConfig OBJECT-TYPE
        SYNTAX TruthValue
        MAX-ACCESS  read-only
        STATUS      current
        DESCRIPTION
            "This is a bit indicating that the association was created
            from configuration information and should not be demobilized
            if the peer becomes unreachable."
        ::= { hh3cNTPPeerEntry 1 }

    hh3cNTPPeerAuthenable OBJECT-TYPE
        SYNTAX TruthValue
        MAX-ACCESS  read-only
        STATUS      current
        DESCRIPTION
            "This is a bit indicating that system support authentication."
        ::= { hh3cNTPPeerEntry 2 }

    hh3cNTPPeerAuthentic OBJECT-TYPE
        SYNTAX TruthValue
        MAX-ACCESS  read-only
        STATUS      current
        DESCRIPTION
            "This is a bit indicating that message pass authentication which is authentic."
        ::= { hh3cNTPPeerEntry 3 }

    hh3cNTPPeerRemAdr OBJECT-TYPE
        SYNTAX IpAddress
        MAX-ACCESS  not-accessible
        STATUS      current
        DESCRIPTION
            "The IP address of the peer.  When creating a new
            association, a value for this object should be set
            before the row is made active."
        ::= { hh3cNTPPeerEntry 4 }

    hh3cNTPPeerRemPort OBJECT-TYPE
        SYNTAX Integer32 (1..65535)
        MAX-ACCESS  read-only
        STATUS      current
        DESCRIPTION
            "The UDP port number on which the peer receives NTP messages."
        ::= { hh3cNTPPeerEntry 5 }

    hh3cNTPPeerLocAdr OBJECT-TYPE
        SYNTAX IpAddress
        MAX-ACCESS  read-only
        STATUS      current
        DESCRIPTION
            "The IP address of the local host.  Multi-homing can
             be supported using this object."
        ::= { hh3cNTPPeerEntry 6 }

    hh3cNTPPeerLocPort OBJECT-TYPE
        SYNTAX Integer32(1..65535)
        MAX-ACCESS  read-only
        STATUS      current
        DESCRIPTION
            "The UDP port number on which the local host receives NTP messages."
        ::= { hh3cNTPPeerEntry 7 }

    hh3cNTPPeerLeap OBJECT-TYPE
        SYNTAX INTEGER
            {
                noWarning(0),
                addSecond(1),
                subtractSecond(2),
                alarm(3)
            }
        MAX-ACCESS  read-only
        STATUS      current
        DESCRIPTION
            "This is a two-bit code warning of an impending leap
            second to be inserted in the NTP timescale.  The bits
            are set before 23:59 on the day of insertion and reset
            after 00:00 on the following day.  This causes the
            number of seconds (rollover interval) in the day of
            insertion to be increased or decreased by one.  The two
            bits are coded as below,
            00, no warning
            01, last minute has 61 seconds
            10, last minute has 59 seconds
            11, alarm condition (clock not synchronized)"
        ::= { hh3cNTPPeerEntry 8 }

    hh3cNTPPeerHMode OBJECT-TYPE
        SYNTAX INTEGER
            {
                unspecified (0),
                symmetricActive (1),
                symmetricPassive (2),
                client (3),
                server(4),
                broadcast (5),
                reservedControl (6),
                reservedPrivate (7),
                broadcastclient (8),
                multicastclient (9)
            }
        MAX-ACCESS  not-accessible
        STATUS      current
        DESCRIPTION
            "This is an integer indicating the association mode,
            with values coded as follows,
            0, unspecified
            1, symmetric active - A host operating in this mode
                    sends periodic messages regardless of the
                    reach ability state or stratum of its peer.  By
                    operating in this mode the host announces its
                    willingness to synchronize and be synchronized
                    by the peer
            2, symmetric passive - This type of association is
                    ordinarily created upon arrival of a message
                    from a peer operating in the symmetric active
                    mode and persists only as long as the peer is
                    reachable and operating at a stratum level
                    less than or equal to the host; otherwise, the
                    association is dissolved.  However, the
                    association will always persist until at least
                    one message has been sent in reply.  By
                    operating in this mode the host announces its
                    willingness to synchronize and be synchronized
                    by the peer
            3, client -  A host operating in this mode sends
                    periodic messages regardless of the
                    reach ability state or stratum of its peer.  By
                    operating in this mode the host, usually a LAN
                    workstation, announces its willingness to be
                    synchronized by, but not to synchronize the peer
            4, server - This type of association is ordinarily
                    created upon arrival of a client request message
                    and exists only in order to reply to that
                    request, after which the association is
                    dissolved.  By operating in this mode the host,
                    usually a LAN time server, announces its
                    willingness to synchronize, but not to be
                    synchronized by the peer
            5, broadcast - A host operating in this mode sends
                    periodic messages regardless of the
                    reach ability state or stratum of the peers.
                    By operating in this mode the host, usually a
                    LAN time server operating on a high-speed
                    broadcast medium, announces its willingness to
                    synchronize all of the peers, but not to be
                    synchronized by any of them
            6, reserved for NTP control messages
            7, reserved for private use
            8, broadcastclient
            9, multicastclient"
        ::= { hh3cNTPPeerEntry 9 }

    hh3cNTPPeerStratum OBJECT-TYPE
        SYNTAX      Integer32(0..255)
        MAX-ACCESS  read-only
        STATUS      current
        DESCRIPTION
            "This is a integer indicating the stratum level
            of the peer clock, with values defined as follows:
            0, unspecified
            1, primary reference (e.g.,, radio clock)
            2-255, secondary reference (via NTP)"
        ::= { hh3cNTPPeerEntry 10 }

    hh3cNTPPeerPPoll OBJECT-TYPE
        SYNTAX      Integer32(-20..20)
        MAX-ACCESS  read-only
        STATUS      current
        DESCRIPTION
            "The interval at which the peer polls the local host."
        ::= { hh3cNTPPeerEntry 11 }

    hh3cNTPPeerHPoll OBJECT-TYPE
        SYNTAX      Integer32(-20..20)
        MAX-ACCESS  read-only
        STATUS      current
        DESCRIPTION
            "The interval at which the local host polls the peer."
        ::= { hh3cNTPPeerEntry 12 }

    hh3cNTPPeerPrecision OBJECT-TYPE
        SYNTAX      Integer32(-20..20)
        MAX-ACCESS  read-only
        STATUS      current
        DESCRIPTION
            "This is a signed integer indicating the precision of
            the peer clock, in seconds to the nearest power of two.
            The value must be rounded to the next larger power of
            two; for instance, a 50-Hz (20 ms) or 60-Hz (16.67 ms)
            power-frequency clock would be assigned the value -5 (31.25 ms),
            while a 1000-Hz (1 ms) crystal-controlled clock would be assigned
            the value -9 (1.95 ms)."
        ::= { hh3cNTPPeerEntry 13 }

    hh3cNTPPeerRootDelay OBJECT-TYPE
        SYNTAX      OCTET STRING(SIZE(1..128))
        MAX-ACCESS  read-only
        STATUS      current
        DESCRIPTION
            "This is a signed fixed-point number indicating
            the total roundtrip delay to the primary reference source
            at the root of the synchronization subnet, in milliseconds.
            Note that this variable can take on both positive and negative
            values, depending on clock precision and skew."
        ::= { hh3cNTPPeerEntry 14 }

    hh3cNTPPeerRootDispersion OBJECT-TYPE
        SYNTAX      OCTET STRING(SIZE(1..128))
        MAX-ACCESS  read-only
        STATUS      current
        DESCRIPTION
            "This is a signed fixed-point number indicating
            the maximum error of the peer clock relative to
            the primary reference source at the root of the
            synchronization subnet, in milliseconds.  Only
            positive values greater than zero are possible."
        ::= { hh3cNTPPeerEntry 15 }

    hh3cNTPPeerRefId OBJECT-TYPE
        SYNTAX      OCTET STRING(SIZE(1..128))
        MAX-ACCESS  read-only
        STATUS      current
        DESCRIPTION
            "The reference identifier of the peer.
            This is a 32-bit code identifying the particular reference clock.
            In the case of stratum 0 (unspecified) or stratum 1 (primary
            reference source), this is a four-octet, left-justified,
            zero-padded ASCII string.
            Stratum, Code, Meaning
            0,       DCN,  DCN routing protocol
            0,       TSP,  TSP time protocol
            1,       ATOM, Atomic clock (calibrated)
            1,       WWVB, WWVB LF (band 5) radio
            1,       GOES, GOES UHF (band 9) satellite
            1,       WWV,  WWV HF (band 7) radio"
        ::= { hh3cNTPPeerEntry 16 }

    hh3cNTPPeerRefTime OBJECT-TYPE
        SYNTAX      OCTET STRING (SIZE(1..128))
        MAX-ACCESS  read-only
        STATUS      current
        DESCRIPTION
            "This is the local time at the peer, in timestamp format,
            when the local clock was last updated.  If the local clock has
            never been synchronized, the value is zero."
        ::= { hh3cNTPPeerEntry 17 }

    hh3cNTPPeerOrg OBJECT-TYPE
        SYNTAX      OCTET STRING(SIZE(1..128))
        MAX-ACCESS  read-only
        STATUS      current
        DESCRIPTION
            "This is the local time, in timestamp format,
            at the peer when it's latest NTP message was sent.
            If the peer becomes unreachable the value is set to zero"
        ::= { hh3cNTPPeerEntry 18 }

    hh3cNTPPeerRec OBJECT-TYPE
        SYNTAX      OCTET STRING(SIZE(1..128))
        MAX-ACCESS  read-only
        STATUS      current
        DESCRIPTION
            "This is the local time, in timestamp format,
            when the latest NTP message from the peer arrived.
            If the peer becomes unreachable the value is set to zero."
        ::= { hh3cNTPPeerEntry 19 }

    hh3cNTPPeerXmt OBJECT-TYPE
        SYNTAX      OCTET STRING(SIZE(1..128))
        MAX-ACCESS  read-only
        STATUS      current
        DESCRIPTION
            "This is the local time, in timestamp format,
            at which the NTP message departed the sender."
        ::= { hh3cNTPPeerEntry 20 }

    hh3cNTPPeerReach OBJECT-TYPE
        SYNTAX      Integer32(0..2147483647)
        MAX-ACCESS  read-only
        STATUS      current
        DESCRIPTION
            "This is a shift register of NTP.WINDOW bits used to
            determine the reach ability status of the peer,
            with bits entering from the least significant (rightmost) end.
            A peer is considered reachable if at least
            one bit in this register is set to one"
        ::= { hh3cNTPPeerEntry 21 }

    hh3cNTPPeerValid  OBJECT-TYPE
        SYNTAX      Integer32(0..255)
        MAX-ACCESS  read-only
        STATUS      current
        DESCRIPTION
            "This is an integer counter indicating the valid samples
            remaining in the filter register.  It is used to
            determine the reach ability state and when the
            poll interval should be increased or decreased."
        ::= { hh3cNTPPeerEntry 22 }

    hh3cNTPPeerTimer  OBJECT-TYPE
        SYNTAX      Integer32(0..2147483647)
        MAX-ACCESS  read-only
        STATUS      current
        DESCRIPTION
            "This is an integer counter used to control the
            interval of transmitted NTP messages from the local host to the peer."
        ::= { hh3cNTPPeerEntry 23 }

    hh3cNTPPeerDelay  OBJECT-TYPE
        SYNTAX      OCTET STRING(SIZE(1..128))
        MAX-ACCESS  read-only
        STATUS      current
        DESCRIPTION
            "This is a signed fixed-point number indicating
            the roundtrip delay of the peer clock relative to
            the local clock over the network path between them,
            in milliseconds.  Note that this variable can take on
            both positive and negative values, depending on
            clock precision and skew-error accumulation."
        ::= { hh3cNTPPeerEntry 24 }

    hh3cNTPPeerOffset OBJECT-TYPE
        SYNTAX      OCTET STRING(SIZE(1..128))
        MAX-ACCESS  read-only
        STATUS      current
        DESCRIPTION
            "This is a signed, fixed-point number indicating the offset
            of the peer clock relative to the local clock, in milliseconds."
        ::= { hh3cNTPPeerEntry 25 }

    hh3cNTPPeerJitter OBJECT-TYPE
        SYNTAX      OCTET STRING(SIZE(1..128))
        MAX-ACCESS  read-only
        STATUS      current
        DESCRIPTION
            "This is an indicating that peer of sample Variance"
        ::= { hh3cNTPPeerEntry 26 }

    hh3cNTPPeerDispersion OBJECT-TYPE
        SYNTAX      OCTET STRING(SIZE(1..128))
        MAX-ACCESS  read-only
        STATUS      current
        DESCRIPTION
            "This is a signed fixed-point number indicating the
            maximum error of the peer clock relative to the local
            clock over the network path between them, in milliseconds.
            Only positive values greater than zero are possible."
        ::= { hh3cNTPPeerEntry 27 }

    hh3cNTPPeerKeyId OBJECT-TYPE
        SYNTAX      Unsigned32(0..4294967295)
        MAX-ACCESS  read-only
        STATUS      current
        DESCRIPTION
            "This is an unsigned integer identifying the cryptographic
            key used to generate the message-authentication code."
        ::= { hh3cNTPPeerEntry 28 }

    hh3cNTPPeerFiltDelay OBJECT-TYPE
        SYNTAX      OCTET STRING(SIZE(1..128))
        MAX-ACCESS  read-only
        STATUS      current
        DESCRIPTION
            "Round-trip delay of the peer clock relative to the
            local clock over the network path between them, in
            milliseconds.  This variable can take on both positive
            and negative values, depending on clock precision
            and skew-error accumulation."
        ::= { hh3cNTPPeerEntry 29 }

    hh3cNTPPeerFiltOffset OBJECT-TYPE
        SYNTAX      OCTET STRING(SIZE(1..128))
        MAX-ACCESS  read-only
        STATUS      current
        DESCRIPTION
            "The offset of the peer clock relative to the local clock in milliseconds."
        ::= { hh3cNTPPeerEntry 30 }

    hh3cNTPPeerFiltError OBJECT-TYPE
        SYNTAX      OCTET STRING(SIZE(1..128))
        MAX-ACCESS  read-only
        STATUS      current
        DESCRIPTION
            "The maximum error of the peer clock relative to the
            local clock over the network path between them, in
            milliseconds.  Only positive values greater than zero
            are possible."
        ::= { hh3cNTPPeerEntry 31 }

    hh3cNTPPeerPMode OBJECT-TYPE
        SYNTAX INTEGER
            {
                unspecified (0),
                symmetricActive (1),
                symmetricPassive (2),
                client (3),
                server(4),
                broadcast (5),
                reservedControl (6),
                reservedPrivate (7),
                broadcastclient (8),
                multicastclient (9)
            }
        MAX-ACCESS  read-only
        STATUS      current
        DESCRIPTION
            "This is an integer indicating the association mode,
            with values coded as follows,
            0, unspecified
            1, symmetric active - A host operating in this mode
                    sends periodic messages regardless of the
                    reach ability state or stratum of its peer.  By
                    operating in this mode the host announces its
                    willingness to synchronize and be synchronized
                    by the peer
            2, symmetric passive - This type of association is
                    ordinarily created upon arrival of a message
                    from a peer operating in the symmetric active
                    mode and persists only as long as the peer is
                    reachable and operating at a stratum level
                    less than or equal to the host; otherwise, the
                    association is dissolved.  However, the
                    association will always persist until at least
                    one message has been sent in reply.  By
                    operating in this mode the host announces its
                    willingness to synchronize and be synchronized
                    by the peer
            3, client -  A host operating in this mode sends
                    periodic messages regardless of the
                    reach ability state or stratum of its peer.  By
                    operating in this mode the host, usually a LAN
                    workstation, announces its willingness to be
                    synchronized by, but not to synchronize the peer
            4, server - This type of association is ordinarily
                    created upon arrival of a client request message
                    and exists only in order to reply to that
                    request, after which the association is
                    dissolved.  By operating in this mode the host,
                    usually a LAN time server, announces its
                    willingness to synchronize, but not to be
                    synchronized by the peer
            5, broadcast - A host operating in this mode sends
                    periodic messages regardless of the
                    reach ability state or stratum of the peers.
                    By operating in this mode the host, usually a
                    LAN time server operating on a high-speed
                    broadcast medium, announces its willingness to
                    synchronize all of the peers, but not to be
                    synchronized by any of them
            6, reserved for NTP control messages
            7, reserved for private use
            8, broadcastclient
            9, multicastclient
            When creating a new peer association, if no value
            is specified for this object, it defaults to
            'symmetricActive'."
        ::= { hh3cNTPPeerEntry 32 }

    hh3cNTPPeerReceived OBJECT-TYPE
        SYNTAX      Counter32
        MAX-ACCESS  read-only
        STATUS      current
        DESCRIPTION
            "The number of received messages."
        ::= { hh3cNTPPeerEntry 33 }

    hh3cNTPPeerSent OBJECT-TYPE
        SYNTAX      Counter32
        MAX-ACCESS  read-only
        STATUS      current
        DESCRIPTION
            "The number of send messages."
        ::= { hh3cNTPPeerEntry 34 }

    hh3cNTPPeerFlash OBJECT-TYPE
        SYNTAX      BITS
            {
                recvRepeatMsg(0),              -- received repeated message
                recvremanMsg(1),               -- received remanufactured message
                unSynMsg(2),                   -- unsynchronized message
                dispBeyond(3),                 -- the peer dispersion beyond the mark
                unauthenticate(4),             -- the peer unauthenticate
                unSynClock(5),                 -- the peer clock is unsynchronized
                straBeyond(6),                 -- the peer stratum beyond the mark
                rootDispBeyond(7),             -- the peer rootdispersion beyond the mark
                noAuthen(8),                   -- the peer no authentication
                refuOperate(9)                 -- refuse operate
            }
        MAX-ACCESS  read-only
        STATUS      current
        DESCRIPTION
            "The information about the message."
        ::= { hh3cNTPPeerEntry 35 }

    hh3cNTPPeerRowStatus OBJECT-TYPE
        SYNTAX      RowStatus
        MAX-ACCESS  read-create
        STATUS      current
        DESCRIPTION
            "The status object for this row.  When a management
            station is creating a new row, it should set the
            value for cntpPeersPeerAddress at least, before the
            row can be made 'active'."
        ::= { hh3cNTPPeerEntry 36 }
END

-- =================================================================
-- Copyright (c) 2004-2022 New H3C Tech. Co., Ltd. All rights reserved.
--
-- Description: OSPFv3 (Open Shortest Path First version 3) MIB
-- Reference:
-- Version: V1.0
-- History:
-- V1.0 2022-07-05 Created pengqing
--                 Initial version.
-- =================================================================
HH3C-OSPFV3-MIB DEFINITIONS ::= BEGIN

IMPORTS
    IpAddress, Integer32, OBJECT-TYPE, MODULE-IDENTITY, NOTIFICATION-TYPE
        FROM SNMPv2-SMI
    DisplayString
        FROM SNMPv2-TC
    hh3cCommon
        FROM HH3C-OID-MIB;

hh3cOspfv3 MODULE-IDENTITY
    LAST-UPDATED "202207051002Z"
    ORGANIZATION
        "New H3C Tech. Co., Ltd."
    CONTACT-INFO
        "Platform Team New H3C Tech. Co., Ltd.
        Hai-Dian District Beijing P.R. China
        http://www.h3c.com
        Zip:100085
        "
    DESCRIPTION
        "This MIB file provides information about OSPFv3."
    REVISION "202207051002Z"
    DESCRIPTION
        "The initial version of this MIB file."
    ::= { hh3cCommon 239 }

hh3cOspfv3Notifications        OBJECT IDENTIFIER ::= { hh3cOspfv3 0 }
hh3cOspfv3NotificationObjects  OBJECT IDENTIFIER ::= { hh3cOspfv3 2 }

hh3cOspfv3ProcessIdForNotify OBJECT-TYPE
    SYNTAX Integer32 (1..65535)
    MAX-ACCESS accessible-for-notify
    STATUS current
    DESCRIPTION
        "The process ID field indicates the OSPFv3 process number."
    ::= { hh3cOspfv3NotificationObjects 1 }

hh3cOspfv3AreaIdForNotify OBJECT-TYPE
    SYNTAX IpAddress
    MAX-ACCESS accessible-for-notify
    STATUS current
    DESCRIPTION
        "A 32-bit integer uniquely identifying an area.
        Area ID 0.0.0.0 is used for the OSPFv3 backbone."
    ::= { hh3cOspfv3NotificationObjects 2 }

hh3cOspfv3IfName OBJECT-TYPE
    SYNTAX DisplayString (SIZE (1..255))
    MAX-ACCESS accessible-for-notify
    STATUS current
    DESCRIPTION
        "The interface name."
    ::= { hh3cOspfv3NotificationObjects 3 }

hh3cOspfv3RouterID OBJECT-TYPE
    SYNTAX IpAddress
    MAX-ACCESS accessible-for-notify
    STATUS current
    DESCRIPTION
        "The Router ID of OSPFv3 protocol."
    ::= { hh3cOspfv3NotificationObjects 4 }

hh3cOspfv3LastAuthKeyExpiry NOTIFICATION-TYPE
    OBJECTS {
        hh3cOspfv3ProcessIdForNotify,
        hh3cOspfv3AreaIdForNotify,
        hh3cOspfv3IfName,
        hh3cOspfv3RouterID
    }
    STATUS current
    DESCRIPTION
        "The last authentication key has expired or no active send key in keychain."
    ::= { hh3cOspfv3Notifications 1 }

END

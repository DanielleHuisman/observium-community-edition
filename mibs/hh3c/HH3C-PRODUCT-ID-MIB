-- ============================================================================
-- Copyright (c) 2004-2023 New H3C Tech. Co., Ltd.  All rights reserved.
--
-- Description: H3C Product OID MIB
-- Reference: HH3C-OID-MIB
-- Version: V2.02
-- History:
--   V1.00 2006-04-19 Initial version
--   V1.01 2006-05-09
--     Add OID 158 under hh3cProductId by gaolong
--   V1.02 2006-05-18
--     Add OID from 159 to 169 under hh3cProductId by gaolong
--     Add OID from 170 to 175 under hh3cProductId by longyin
--   V1.03 2006-05-31
--     Add OID from 176 to 178 under hh3cProductId by gaolong
--   V1.04 2006-06-08
--     Add OID from 179 to 188 under hh3cProductId by gaolong
--   V1.05 2006-07-14
--     Add OID from 189 to 192 under hh3cProductId by longyin
--   V1.06 2006-07-26
--     Add OID from 193 to 200 under hh3cProductId by gaolong
--   V1.07 2006-08-23
--     Add OID from 201 to 203 under hh3cProductId by gaolong
--   V1.08 2006-09-25
--     Add OID from 204 to 206 under hh3cProductId by gaolong
--   V1.09 2006-10-28
--     Modify name of OID 193 and 194 by gaolong
--   V1.10 2006-11-25
--     Add OID from 207 to 217 under hh3cProductId by gaolong
--   V1.11 2006-12-25
--     Add OEM object Identifier under hh3cProductId by gaolong
--   V1.12 2007-02-01
--     Add OID from 219 to 224 under hh3cProductId by gaolong
--   V1.13 2007-03-07
--     Add OID from 225 to 235 under hh3cProductId by gaolong
--   V1.14 2007-03-28
--     Add OID from 236 to 241 under hh3cProductId by gaolong
--   V1.15 2007-04-26
--     Add OID from 242 to 257 under hh3cProductId by gaolong
--   V1.16 2007-05-28
--     Add OID from 258 to 267 under hh3cProductId by gaolong
--   V1.17 2007-07-02
--     Add OID from 268 to 282 under hh3cProductId by gaolong
--     Remove OID 176 under hh3cProductId by gaolong
--   V1.18 2007-08-08
--     Add OID from 283 to 297 under hh3cProductId by gaolong
--   V1.19 2007-08-25
--     Add OID from 298 to 322 under hh3cProductId by longyin
--   V1.20 2007-09-25
--     Add OID from 323 to 330 under hh3cProductId by longyin
--   V1.21 2007-10-27
--     Add OID from 331 to 341 under hh3cProductId by longyin
--   V1.22 2007-11-26
--     Add OID from 342 to 346 under hh3cProductId by longyin
--   V1.23 2007-12-25
--     Add OID from 347 to 355 under hh3cProductId by longyin
--   V1.24 2008-01-25
--     Add OID from 356 to 370 under hh3cProductId by longyin
--   V1.25 2008-02-27
--     Add OID from 371 to 384 under hh3cProductId by longyin
--   V1.26 2008-03-27
--     Add OID from 385 to 394 under hh3cProductId by longyin
--   V1.27 2008-04-28
--     Modify name of OID 376 and 385 by songhao
--     Add OID from 395 to 414(except 399) under hh3cProductId by songhao
--   V1.28 2008-05-31
--     Modify name of OID 363 by songhao
--     Add OID from 415 to 419 under hh3cProductId by songhao
--   V1.29 2008-06-30
--     Add OID from 420 to 453 under hh3cProductId by songhao
--   V1.30 2008-07-25
--     Add OID from 454 to 459 under hh3cProductId by songhao
--   V1.31 2008-08-28
--     Add OID from 460 to 467 under hh3cProductId by songhao
--   V1.32 2008-10-10
--     Add OID from 468 to 469 under hh3cProductId by songhao
--   V1.33 2008-11-04
--     Add OID from 470 to 477 under hh3cProductId by songhao
--   V1.34 2008-12-01
--     Add OID from 478 to 487 under hh3cProductId by songhao
--   V1.35 2008-12-25
--     Add OID from 488 to 493 under hh3cProductId by shuaixiaojuan
--   V1.36 2009-02-27
--     Add OID from 494 to 505 under hh3cProductId by songhao
--   V1.37 2009-04-10
--     Add OID from 506 to 511 under hh3cProductId by songhao
--     Modify name of OID 505 by songhao
--   V1.38 2009-05-24
--     Add OID from 512 to 531 under hh3cProductId by songhao
--   V1.39 2009-07-03
--     Add OID 532 under hh3cProductId by songhao
--     Modify name of OID 340 and 341 by songhao
--   V1.40 2009-08-28
--     Add OID from 532 to 549 under hh3cProductId by songhao
--   V1.41 2009-11-06
--     Add OID from 550 to 562 under hh3cProductId by songhao
--     Modify name of OID 506 and 507 by songhao
--   V1.42 2009-11-30
--     Add OID from 563 to 571 under hh3cProductId by songhao
--     Modify name of OID 529 and 531 by songhao
--   V1.43 2010-01-11
--     Add OID from 572 to 599 under hh3cProductId by songhao
--   V1.44 2010-08-29 by songhao
--     Added OID from 600 to 649 under hh3cProductId
--     Modified name of OID 552 and 569 under hh3cProductId
--     Removed OID 552 and 553 under hh3cProductId
--     Added OID from 1 to 45 under hpSwitch
--     Added OID from 1 to 23 under hpRouter
--     Added OID from 1 to 3 under hpWireless
--     Added OID from 1 to 14 under hpSecurity
--   V1.45 2011-01-30 by songhao
--     Added OID from 650 to 689 under hh3cProductId
--     Modified name of OID 601 under hh3cProductId
--     Added OID from 46 to 68 under hpSwitch
--     Added OID from 24 to 51 under hpRouter
--     Added OID from 4 to 11 under hpWireless
--     Added OID from 15 to 20 under hpSecurity
--   V1.46 2011-03-10 by songhao
--     Modified name of 615 617 689 under hh3cProductId
--     Removed OID of 616 under hh3cProductId
--     Added OID from 69 to 80 under hpSwitch
--     Added OID 690 to 729 under hh3cProductId
--     Modified name of 11 to 15 under hpSwitch
--     Removed all hyphens under hpNetworking
--   V1.47 2011-04-22 by songhao
--     Added OID from 730 to 742 under hh3cProductId
--     Modified name of 16 to 23, 46 to 47, 62, 65 to 68 under hpSwitch
--     Added OID from 81 to 99 under hpSwitch
--     Added OID from 12 to 14 under hpWireless
--   V1.48 2011-06-30 by songhao
--     Added OID 743 to 747 under hh3cProductId
--     Added OID 100 to 107 under hpSwitch
--     Added OID 15 under hpWireless
--     Added OID 52 to 54 under hpRouter
--     Modified name of 24 to 38, 68 to 77 under hpSwitch
--     Modified name of 12 to 14 under hpWireless
--   V1.49 2011-08-31 by songhao
--     Added 748 under hh3cProductId
--     Modified name of 45, 100 under hpSwitch
--     Added OID 108 to 112 under hpSwitch
--   V1.50 2012-04-22 by songhao
--     Added 749 to 844 under hh3cProductId
--     Modified name of 690, 753 and 754 under hh3cProductId
--     Added OID 114 to 123 under hpSwitch
--     Modified name of 1 to 6, 39 to 45, 51, 78, 86 to 89, 100, 103, 108 to 112 under hpSwitch
--     Added OID 21, 22 under hpSecurity
--     Added OID 55 to 74 under hpRouter
--   V1.51 2013-01-07 by songhao
--     Added OID 845 to 893 under hh3cProductId
--     Added OID 113, 124 to 138 under hpSwitch
--     Added OID 75 to 99 under hpRouter
--     Added OID 16 to 25 under hpWireless
--     Added OID 23 to 24 under hpSecurity
--     Modified name of 842 under hh3cProductId
--     Modified name of 45, 121, 122 under hpSwitch
--     Modified name 55 to 69 under hpRouter
--   V1.52 2013-04-25 by songhao
--     Added OID 894 to 937 under hh3cProductId
--     Added OID 139 to 145 under hpSwitch
--     Added OID 100 to 102 under hpRouter
--     Modified name of 864, 865, 869, 883, 884 under hh3cProductId
--   V1.53 2013-10-09 by songhao
--     Added OID 938 to 1021 under hh3cProductId
--     Modified name of 865, 925 under hh3cProductId
--     Added OID 103 to 107 under hpRouter
--     Modified name 88, 90 under hpRouter
--     Added OID 146 to 150 under hpSwitch
--     Added OID 25 under hpSecurity
--   V1.54 2014-01-27 by songhao
--     Modified name of 1013 under hh3cProductId
--     Added OID 1022 to 1082 under hh3cProductId
--     Added OID 151 to 176 under hpSwitch
--     Added OID 110 under hpRouter
--     Added OID 26 under hpSecurity
--   V1.55 2014-04-27 by songhao
--     Added OID 1083 to 1112 under hh3cProductId
--     Added OID 177 to 204 under hpSwitch
--     Added OID 111 to 117 under hpRouter
--     Added OID 27 under hpSecurity
--   V1.56 2014-09-18 by songhao
--     Added OID 1113 to 1159 under hh3cProductId
--     Added OID 205 to 213 under hpSwitch
--     Added OID 118 to 127 under hpRouter
--   V1.57 2015-04-18 by songhao
--     Added OID 1160 to 1311 under hh3cProductId
--     Modified name of 1112, 1206, 1207 under hh3cProductId
--     Added OID 214 to 241 under hpSwitch
--     Modified name of 213 under hpSwitch
--     Added OID 128 to 135 under hpRouter
--     Added OID 28 under hpSecurity
--   V1.58 2016-04-02 by songhao
--     Added OID 1312 to 1508 under hh3cProductId
--     Modified name of 1295 under hh3cProductId
--     Added OID 242 to 272 under hpSwitch
--     Added OID 136 to 145 under hpRouter
--     Added OID 29 to 30 under hpSecurity
--     Added OID 1 to 17 under hh3cJointVendorHik
--     Added OID 1 to 9 under hh3cJointVendorDh
--   V1.59 2016-09-02 by songhao
--     Added OID 1509 to 2073 under hh3cProductId
--     Modified name of 1410-1412 under hh3cProductId
--     Added OID 273 to 283 under hpSwitch
--     Modified name of 1486-1489,1409 under hh3cProductId
--     Modified name of 1145-1147,1095,999,1419,157，1591-1592，1603-1612 1747 under hh3cProductId
--     Modified name of 146,204,213,225-227,235-237,242-243 under hpSwitch
--     Deleted 1535,1613 under hh3cProductId 20161019
--     Added OID 1535 under hh3cProductId 20161021
--     Added OID 1613 under hh3cProductId 20161109
--     Modified name of 273,278 under hpSwitch
--     Added OID 136 to 146 to 148 under hpRouter
--     Added OID 18 under hh3cJointVendorHik
--     Modified name of 282-286 under hpSwitch
--     Modified name of 1691,1692 under hh3cProductId
--     Modified name of 1515 under hh3cProductId
--     Modified name of 1891 under hh3cProductId 20170919
--     Modified name of 1891 under hh3cProductId 20170920
--     Modified name of 1505 under hh3cProductId 20171108
--     Modified name of 1873,1874 under hh3cProductId 20171122
--     Added OID 1-4 under hh3cJointVendorSrie  20171208
--     Added OID 5-6 under hh3cJointVendorSrie  20180102
--     Added OID 19-22 under hh3cJointVendorHik
--     Added OID 10-12 under hh3cJointVendorDh
--     Added OID 287-289 under hpSwitch  20180306
--     Modified name of 1675 under hh3cProductId 20180313
--     Modified name of 1-2 under hh3cJointVendorSrie 20180315
--   V1.60 2018-05-09 by jiliyan
--     Modified name of 18 under hh3cJointVendorHik 20180507
--     Modified name of 1503 under hh3cProductId 20180509
--     Modified name of 1953-1955, 2066 hh3cProductId 20180703
--     Added OID 2074 to 2147 under hh3cProductId
--     Added OID 290-292 under hpSwitch
--     Modified name of 2042-2043 under hh3cProductId 20180905
--     Modified name of 1963 under hh3cProductId 20181115
--   V1.61 2019-02-13 by jiliyan
--     Added OID 2148 to 2345 under hh3cProductId
--     add by qpp  jiliyan return modify
--     Added OID 23-32 under hh3cJointVendorHik by jiliyan
--     Modified name of 2041 under hh3cProductId 20190221
--     Modified name of 2266 under hh3cProductId 20190508
--     Added OID 33-34 hh3cJointVendorHik by jiliyan
--   V1.62 2019-07-16 by jiliyan
--     Added OID 2346 to 2404 under hh3cProductId
--     Added OID 35-36 under hh3cJointVendorHik
--     Added OID 13-17 under hh3cJointVendorDh
--     Modified name of 1641 under hh3cProductId
--   V1.63 2019-11-27 by jiliyan
--     Added OID 2405-2439 under hh3cProductId
--     Modified name of 1365-1366 1642 2252 under hh3cProductId
--     Modified name and id of 1368 1697 1700 under hh3cProductId
--     Added OID 37-43 under hh3cJointVendorHik
--   V1.64 2020-01-10 by jiliyan
--     Added OID 2440-2446 under hh3cProductId
--   V1.65 2020-02-18 by jiliyan
--     Added OID 2447-2448 under hh3cProductId
--   V1.66 2020-03-11 by jiliyan
--     Added OID 2449-2474 under hh3cProductId
--     Modified name and id of 2133 2348 under hh3cProductId
--     Deleted OID 2461 under hh3cProductId
--     Added OID 44-45 under hh3cJointVendorHik
--   V1.67 2020-04-13 by jiliyan
--     Added OID 2475-2488 under hh3cProductId
--     Modified name of 2442 2443 under hh3cProductId
--   V1.68 2020-05-14 by jiliyan
--     Added OID 2489-2545 under hh3cProductId
--     Added OID 149 under hpRouter
--     Added OID 293-294 under hpSwitch
--     Deleted OID 2083 under hh3cProductId for renamed with 2492
--   V1.69 2020-06-11 by jiliyan
--     Added OID 2546-2550 under hh3cProductId
--     Added OID 46-48 under hh3cJointVendorHik
--   V1.70 2020-07-09 by jiliyan
--     Added OID 2551-2573 under hh3cProductId
--   V1.71 2020-08-12 by jiliyan
--     Added OID 2574-2579 under hh3cProductId
--   V1.72 2020-09-16 by jiliyan
--     Added OID 2580-2597 under hh3cProductId
--     Modified name 2545 under hh3cProductId
--     Revert name of 2545
--   V1.73 2020-10-20 by jiliyan
--     Added OID 2598-2603 under hh3cProductId
--     Added OID 49 under hh3cJointVendorHik
--   V1.74 2020-11-12 by jiliyan
--     Added OID 2604-2632 under hh3cProductId
--     Modified name of oid 2498-2500 2507 2508 2512-2514 2519 2522 2523 2527
--   V1.75 2020-12-21 by jiliyan
--     Added OID 295-301 under hpSwitch
--     Added OID 2633-2641 under hh3cProductId
--   V1.76 2021-01-19 by jiliyan
--     Modified name of oid 2369-2372 2431-2434 2450-2452 under hh3cProductId
--   V1.77 2021-02-22 by jiliyan
--     Added OID 2642-2749 under hh3cProductId
--     Added OID 302 under hpSwitch
--     Modified name of oid 2431-2434 2654 under hh3cProductId
--     Added OID 50 under hh3cJointVendorHik
--   V1.78 2021-03-11 by jiliyan
--     Added OID 2750-2855 under hh3cProductId
--     Modified name of oid 2622-2625 2782-2784 under hh3cProductId
--     Modified oid of hh3cWX5560X from 2622 to 2794
--     Modified oid of hh3cF5000-AI160 from 2625 to 2795
--     Modified oid of hh3cS9825-64D  from 2263 to 2796
--     Modified oid of hh3cS9855-48CD8D from 2624 to 2797
--   V1.79 2021-04-12 by jiliyan
--     Added OID 2856-2878 under hh3cProductId
--     Added OID 303 under hpSwitch
--   V1.80 2021-05-13 by jiliyan
--     Modified name of oid 2643-2646 2648-2651 2662-2667 2670 2674 2677 2684 2687 2689-2702 2704-2709 2711 2727-2728 2730-2735 2737 under hh3cProductId
--     Added OID 2879-2920 under hh3cProductId
--     Added OID 304-313 under hpSwitch
--     Added OID 51-55 under hh3cJointVendorHik
--   V1.81 2021-06-16 by jiliyan
--     Added  2921-2958 under hh3cProductId
--     Added  18-28 under hh3cJointVendorDh
--     Added  56-66 under hh3cJointVendorHik
--   V1.82 2021-08-09 by jiliyan
--     Added  2959-2967 under hh3cProductId
--     Added  29-71 under hh3cJointVendorDh
--     Added  67 under hh3cJointVendorHik
--     Modified name of oid 2955 2956 under hh3cProductId
--   V1.83 2021-08-12 by jiliyan
--     Added  2968-2982 under hh3cProductId
--     Added  72-73 under hh3cJointVendorDh
--   V1.84 2021-09-22 by jiliyan
--     Added  3001-3004 under hh3cProductId
--     Added  74-77 under hh3cJointVendorDh
--     Added  hh3cJointVendorDzec under hh3cJointVendorId
--     Added  1-6 under hh3cJointVendorDzec
--   V1.85 2021-10-14 by jiliyan
--     Added  68 under hh3cJointVendorHik
--     Added  7 under hh3cJointVendorDzec
--     Added  78 under hh3cJointVendorDh
--     Modified name of oid 2829 2831 under hh3cProductId
--     Deleted name of oid 2943-2944 under hh3cProductId
--     Added  3005-3026 under hh3cProductId
--     Deleted 65 78 under hh3cJointVendorDh
--     Deleted 69 under hh3cJointVendorDh
--     Added 78-82 under hh3cJointVendorDh
--   V1.86 2021-11-08 by jiliyan
--     Added  3034-3061 under hh3cProductId
--     Modified name of oid 3039-3048 1907 1909 under hh3cProductId
--     Modified name of oid 68 under hh3cJointVendorHik
--     Added  8-11 under hh3cJointVendorDzec
--     Added  84-103 under hh3cJointVendorDh
--     Added  150-154 under hpRouter
--     Added  70-72 under hh3cJointVendorHik
--   V1.87 2021-12-15 by jiliyan
--     Added  3062-3079 under hh3cProductId
--     Added  73-74 under hh3cJointVendorHik
--     Added  314-317 under hpSwitch
--     Deleted  3062-3064 under hh3cProductId
--     Added 104-105 under hh3cJointVendorDh
--   V1.88 2022-02-08 by jiliyan
--     Added  3080-3084 under hh3cProductId
--   V1.89 2022-02-16 by jiliyan
--     Added  3085-3145 under hh3cProductId
--   V1.90 2022-03-25 by qupingping
--     Added  3146-3164 under hh3cProductId
--     Added  75-77 under hh3cJointVendorHik
--   V1.91 2022-04-20 by qupingping
--     Added  3165-3195 under hh3cProductId
--   V1.92 2022-05-20 by qupingping
--     Added  3196-3246 under hh3cProductId
--     Added  1-25 under hh3cJointVendorAis
--   V1.93 2022-06-30 by qupingping
--     Added  3247-3273 under hh3cProductId
--   V1.94 2022-07-27 by qupingping
--     Modified name of oid 2617 under hh3cProductId
--     Added 106 under hh3cJointVendorDh
--     Added 3274-3279 under hh3cProductId
--     Added 78 under hh3cJointVendorHik
--   V1.95 2022-08-27 by qupingping
--     Added 3304-3310 under hh3cProductId
--     Added 12 to 14 under hh3cJointVendorDzec
--     Added 81 under hh3cJointVendorHik
--     Deleted  3270-3271 under hh3cProductId
--     Added 15 under hh3cJointVendorHik
--   V1.96 2022-10-11 by qupingping
--     Added 155-157 under hpRouter
--     Modified name of oid 3237-3238 under hh3cProductId
--     Added 3327-3366 under hh3cProductId
--     Added 318-320 under hpSwitch
--   V1.97 2022-10-27 by qupingping
--     Added 3367-3433 under hh3cProductId
--     Added 82 to 83 under hh3cJointVendorHik
--   V1.98 2022-12-26 by qupingping
--     Added 3434-3465 under hh3cProductId
--     Added 321 under hpSwitch
--     Added 84 to 91 under hh3cJointVendorHik
--   V1.99 2023-01-01 by qupingping
--     Added 3466-3497 under hh3cProductId
--     Added 92-101 under hh3cJointVendorHik
--     Added 26-27 under hh3cJointVendorAis
--   V2.00 2023-02-11 by qupingping
--     Deleted 3468 under  hh3cProductId
--     Added 3498-3531 under hh3cProductId
--     Added 28-33 under hh3cJointVendorAis
--     Added 1-2 under hh3cJointVendorId
--   V2.01 2023-04-26 by qupingping
--     Modified name of oid 92&98 under hh3cProductId
--     Added 3532-3562 under hh3cProductId
--     Added 102-106 under hh3cJointVendorHik
--   V2.02 2023-05-26 by zhangyi
--     Added 3563-3591 under hh3cProductId
--     Added 322 under hpSwitch
--     Added 34-53 under hh3cJointVendorAis
-- ============================================================================
HH3C-PRODUCT-ID-MIB DEFINITIONS ::= BEGIN
    IMPORTS
        hh3cProductId, hpNetworking, hh3cJointVendorId
            FROM HH3C-OID-MIB;

-- H3C products

hh3c-s5500-28C-EI                   OBJECT IDENTIFIER ::= { hh3cProductId 1 }
hh3c-s5500-52C-EI                   OBJECT IDENTIFIER ::= { hh3cProductId 2 }
hh3c-s5500-28C-PWR-EI               OBJECT IDENTIFIER ::= { hh3cProductId 3 }
hh3c-s5500-52C-PWR-EI               OBJECT IDENTIFIER ::= { hh3cProductId 4 }
hh3c-s5500-28F-EI                   OBJECT IDENTIFIER ::= { hh3cProductId 5 }
hh3c-s5500-28C-EI-DC                OBJECT IDENTIFIER ::= { hh3cProductId 6 }
hh3c-s6100-20Q-SI                   OBJECT IDENTIFIER ::= { hh3cProductId 7 }
hh3c-s5500-28C-SI                   OBJECT IDENTIFIER ::= { hh3cProductId 8 }
hh3c-s5500-52C-SI                   OBJECT IDENTIFIER ::= { hh3cProductId 9 }
hh3c-s5500-28C-PWR-SI               OBJECT IDENTIFIER ::= { hh3cProductId 10 }
hh3c-s5500-52C-PWR-SI               OBJECT IDENTIFIER ::= { hh3cProductId 11 }
hh3c-s5510-24P                      OBJECT IDENTIFIER ::= { hh3cProductId 12 }
hh3c-s5510-24F                      OBJECT IDENTIFIER ::= { hh3cProductId 13 }
hh3c-s3610-28P                      OBJECT IDENTIFIER ::= { hh3cProductId 14 }
hh3c-s3610-52P                      OBJECT IDENTIFIER ::= { hh3cProductId 15 }
hh3c-s3610-28TP                     OBJECT IDENTIFIER ::= { hh3cProductId 16 }
hh3c-s3610-28F                      OBJECT IDENTIFIER ::= { hh3cProductId 17 }
hh3c-e126                           OBJECT IDENTIFIER ::= { hh3cProductId 18 }
hh3c-e328                           OBJECT IDENTIFIER ::= { hh3cProductId 19 }
hh3c-e352                           OBJECT IDENTIFIER ::= { hh3cProductId 20 }
hh3c-s3100-8C-SI                    OBJECT IDENTIFIER ::= { hh3cProductId 21 }
hh3c-s3100-16C-SI                   OBJECT IDENTIFIER ::= { hh3cProductId 22 }
hh3c-s3100-26C-SI                   OBJECT IDENTIFIER ::= { hh3cProductId 23 }
hh3c-s3100-8T-SI                    OBJECT IDENTIFIER ::= { hh3cProductId 24 }
hh3c-s3100-16T-SI                   OBJECT IDENTIFIER ::= { hh3cProductId 25 }
hh3c-s3100-26T-SI                   OBJECT IDENTIFIER ::= { hh3cProductId 26 }
hh3c-s3100-26TP-SI                  OBJECT IDENTIFIER ::= { hh3cProductId 27 }
hh3c-s5100-24P-EI                   OBJECT IDENTIFIER ::= { hh3cProductId 28 }
hh3c-s5100-26C-EI                   OBJECT IDENTIFIER ::= { hh3cProductId 29 }
hh3c-s5100-50C-EI                   OBJECT IDENTIFIER ::= { hh3cProductId 30 }
hh3c-s5100-48P-EI                   OBJECT IDENTIFIER ::= { hh3cProductId 31 }
hh3c-s3600-28P-SI                   OBJECT IDENTIFIER ::= { hh3cProductId 32 }
hh3c-s3600-52P-SI                   OBJECT IDENTIFIER ::= { hh3cProductId 33 }
hh3c-s3600-28TP-SI                  OBJECT IDENTIFIER ::= { hh3cProductId 34 }
hh3c-s3600-28P-PWR-SI               OBJECT IDENTIFIER ::= { hh3cProductId 35 }
hh3c-s3600-52P-PWR-SI               OBJECT IDENTIFIER ::= { hh3cProductId 36 }
hh3c-s3600-28P-EI                   OBJECT IDENTIFIER ::= { hh3cProductId 37 }
hh3c-s3600-52P-EI                   OBJECT IDENTIFIER ::= { hh3cProductId 38 }
hh3c-s3600-28P-PWR-EI               OBJECT IDENTIFIER ::= { hh3cProductId 39 }
hh3c-s3600-52P-PWR-EI               OBJECT IDENTIFIER ::= { hh3cProductId 40 }
hh3c-s3600-28F-EI                   OBJECT IDENTIFIER ::= { hh3cProductId 41 }
hh3c-s5600-26C                      OBJECT IDENTIFIER ::= { hh3cProductId 42 }
hh3c-s5600-50C                      OBJECT IDENTIFIER ::= { hh3cProductId 43 }
hh3c-s5600-26C-PWR                  OBJECT IDENTIFIER ::= { hh3cProductId 44 }
hh3c-s5600-50C-PWR                  OBJECT IDENTIFIER ::= { hh3cProductId 45 }
hh3c-s5600-26F                      OBJECT IDENTIFIER ::= { hh3cProductId 46 }
hh3c-s3600-52G-HI                   OBJECT IDENTIFIER ::= { hh3cProductId 47 }
hh3c-s3600-52P-HI                   OBJECT IDENTIFIER ::= { hh3cProductId 48 }
hh3c-s3600-28G-HI                   OBJECT IDENTIFIER ::= { hh3cProductId 49 }
hh3c-s3600-28P-HI                   OBJECT IDENTIFIER ::= { hh3cProductId 50 }
hh3c-s3600-52M-HI                   OBJECT IDENTIFIER ::= { hh3cProductId 51 }
hh3c-s7502                          OBJECT IDENTIFIER ::= { hh3cProductId 52 }
hh3c-s7503                          OBJECT IDENTIFIER ::= { hh3cProductId 53 }
hh3c-s7506                          OBJECT IDENTIFIER ::= { hh3cProductId 54 }
hh3c-s7506R                         OBJECT IDENTIFIER ::= { hh3cProductId 55 }
hh3c-ar28-09                        OBJECT IDENTIFIER ::= { hh3cProductId 57 }
hh3c-ar28-10                        OBJECT IDENTIFIER ::= { hh3cProductId 58 }
hh3c-ar28-11                        OBJECT IDENTIFIER ::= { hh3cProductId 59 }
hh3c-ar28-12                        OBJECT IDENTIFIER ::= { hh3cProductId 60 }
hh3c-ar28-13                        OBJECT IDENTIFIER ::= { hh3cProductId 61 }
hh3c-ar28-14                        OBJECT IDENTIFIER ::= { hh3cProductId 62 }
hh3c-ar28-30                        OBJECT IDENTIFIER ::= { hh3cProductId 63 }
hh3c-ar28-31                        OBJECT IDENTIFIER ::= { hh3cProductId 64 }
hh3c-ar28-40                        OBJECT IDENTIFIER ::= { hh3cProductId 65 }
hh3c-ar28-80                        OBJECT IDENTIFIER ::= { hh3cProductId 66 }
hh3c-ar46-20                        OBJECT IDENTIFIER ::= { hh3cProductId 67 }
hh3c-ar46-40                        OBJECT IDENTIFIER ::= { hh3cProductId 68 }
hh3c-ar46-80                        OBJECT IDENTIFIER ::= { hh3cProductId 69 }
hh3c-msr20-20                       OBJECT IDENTIFIER ::= { hh3cProductId 70 }
hh3c-msr20-21                       OBJECT IDENTIFIER ::= { hh3cProductId 71 }
hh3c-msr20-40                       OBJECT IDENTIFIER ::= { hh3cProductId 72 }
hh3c-msr30-20                       OBJECT IDENTIFIER ::= { hh3cProductId 73 }
hh3c-msr30-40                       OBJECT IDENTIFIER ::= { hh3cProductId 74 }
hh3c-msr30-60                       OBJECT IDENTIFIER ::= { hh3cProductId 75 }
hh3c-msr50-40                       OBJECT IDENTIFIER ::= { hh3cProductId 76 }
hh3c-msr50-60                       OBJECT IDENTIFIER ::= { hh3cProductId 77 }
hh3c-ar18-21                        OBJECT IDENTIFIER ::= { hh3cProductId 88 }
hh3c-ar18-21A                       OBJECT IDENTIFIER ::= { hh3cProductId 89 }
hh3c-ar18-21B                       OBJECT IDENTIFIER ::= { hh3cProductId 90 }
hh3c-ar18-22                        OBJECT IDENTIFIER ::= { hh3cProductId 91 }
hh3c-ar18-22-8                      OBJECT IDENTIFIER ::= { hh3cProductId 92 }
hh3c-ar18-22S-8                     OBJECT IDENTIFIER ::= { hh3cProductId 93 }
hh3c-ar18-22-24                     OBJECT IDENTIFIER ::= { hh3cProductId 94 }
hh3c-ar18-23-1                      OBJECT IDENTIFIER ::= { hh3cProductId 95 }
hh3c-ar18-23S-1                     OBJECT IDENTIFIER ::= { hh3cProductId 96 }
hh3c-ar18-30E                       OBJECT IDENTIFIER ::= { hh3cProductId 98 }
hh3c-ar18-31E                       OBJECT IDENTIFIER ::= { hh3cProductId 100 }
hh3c-ar18-32E                       OBJECT IDENTIFIER ::= { hh3cProductId 102 }
hh3c-ar18-33                        OBJECT IDENTIFIER ::= { hh3cProductId 103 }
hh3c-ar18-33E                       OBJECT IDENTIFIER ::= { hh3cProductId 104 }
hh3c-ar18-34                        OBJECT IDENTIFIER ::= { hh3cProductId 105 }
hh3c-ar18-34E                       OBJECT IDENTIFIER ::= { hh3cProductId 106 }
hh3c-ar18-35E                       OBJECT IDENTIFIER ::= { hh3cProductId 108 }
hh3c-ar18-63-1                      OBJECT IDENTIFIER ::= { hh3cProductId 109 }
hh3c-secpathF100-C                  OBJECT IDENTIFIER ::= { hh3cProductId 110 }
hh3c-secpathF100-A                  OBJECT IDENTIFIER ::= { hh3cProductId 111 }
hh3c-secpathF100-S                  OBJECT IDENTIFIER ::= { hh3cProductId 112 }
hh3c-secpathF100-E                  OBJECT IDENTIFIER ::= { hh3cProductId 113 }
hh3c-secpathF1000-S                 OBJECT IDENTIFIER ::= { hh3cProductId 114 }
hh3c-secpathF1000-A                 OBJECT IDENTIFIER ::= { hh3cProductId 115 }
hh3c-secpathF1800-A                 OBJECT IDENTIFIER ::= { hh3cProductId 116 }
hh3c-secpathV100-S                  OBJECT IDENTIFIER ::= { hh3cProductId 117 }
hh3c-secpathV1000-A                 OBJECT IDENTIFIER ::= { hh3cProductId 118 }
hh3c-secpathF100-AW                 OBJECT IDENTIFIER ::= { hh3cProductId 119 }
hh3c-secpathF1800-S                 OBJECT IDENTIFIER ::= { hh3cProductId 120 }
hh3c-secpathF1800-E                 OBJECT IDENTIFIER ::= { hh3cProductId 121 }
hh3c-secpoint                       OBJECT IDENTIFIER ::= { hh3cProductId 122 }
hh3c-vg10-10                        OBJECT IDENTIFIER ::= { hh3cProductId 123 }
hh3c-vg10-11                        OBJECT IDENTIFIER ::= { hh3cProductId 124 }
hh3c-vg10-40                        OBJECT IDENTIFIER ::= { hh3cProductId 125 }
hh3c-vg10-41                        OBJECT IDENTIFIER ::= { hh3cProductId 126 }
hh3c-vg21-08                        OBJECT IDENTIFIER ::= { hh3cProductId 127 }
hh3c-vg20-16                        OBJECT IDENTIFIER ::= { hh3cProductId 128 }
hh3c-vg20-32                        OBJECT IDENTIFIER ::= { hh3cProductId 129 }
hh3c-vg80-20                        OBJECT IDENTIFIER ::= { hh3cProductId 130 }
hh3c-xe200                          OBJECT IDENTIFIER ::= { hh3cProductId 131 }
hh3c-xe2000                         OBJECT IDENTIFIER ::= { hh3cProductId 132 }
hh3c-xe7200                         OBJECT IDENTIFIER ::= { hh3cProductId 133 }
hh3c-xe7300                         OBJECT IDENTIFIER ::= { hh3cProductId 134 }
hh3c-xe7500                         OBJECT IDENTIFIER ::= { hh3cProductId 135 }
hh3c-xe7600                         OBJECT IDENTIFIER ::= { hh3cProductId 136 }
hh3c-xe7205                         OBJECT IDENTIFIER ::= { hh3cProductId 137 }
hh3c-xe7305                         OBJECT IDENTIFIER ::= { hh3cProductId 138 }
hh3c-xe7505                         OBJECT IDENTIFIER ::= { hh3cProductId 139 }
hh3c-xe7605                         OBJECT IDENTIFIER ::= { hh3cProductId 140 }
hh3c-neoceanIX1000                  OBJECT IDENTIFIER ::= { hh3cProductId 141 }
hh3c-neoceanEX1000                  OBJECT IDENTIFIER ::= { hh3cProductId 142 }
hh3c-neoceanEX800                   OBJECT IDENTIFIER ::= { hh3cProductId 143 }
hh3c-neoceanIX5000                  OBJECT IDENTIFIER ::= { hh3cProductId 144 }
hh3c-neoceanIV5100                  OBJECT IDENTIFIER ::= { hh3cProductId 145 }
hh3c-neoceanIV5200                  OBJECT IDENTIFIER ::= { hh3cProductId 146 }
hh3c-s9502                          OBJECT IDENTIFIER ::= { hh3cProductId 147 }
hh3c-s9505                          OBJECT IDENTIFIER ::= { hh3cProductId 148 }
hh3c-s9508                          OBJECT IDENTIFIER ::= { hh3cProductId 149 }
hh3c-s9508V                         OBJECT IDENTIFIER ::= { hh3cProductId 150 }
hh3c-s9512                          OBJECT IDENTIFIER ::= { hh3cProductId 151 }
hh3c-sR8812                         OBJECT IDENTIFIER ::= { hh3cProductId 152 }
hh3c-sR8808                         OBJECT IDENTIFIER ::= { hh3cProductId 153 }
hh3c-sR8805                         OBJECT IDENTIFIER ::= { hh3cProductId 154 }
hh3c-sR8802                         OBJECT IDENTIFIER ::= { hh3cProductId 155 }
hh3c-e126-SI                        OBJECT IDENTIFIER ::= { hh3cProductId 156 }
hh3c-vg31-08                        OBJECT IDENTIFIER ::= { hh3cProductId 157 }
hh3c-dr834                          OBJECT IDENTIFIER ::= { hh3cProductId 158 }
hh3c-s7510E                         OBJECT IDENTIFIER ::= { hh3cProductId 159 }
hh3c-s5100-24P-SI                   OBJECT IDENTIFIER ::= { hh3cProductId 160 }
hh3c-s5100-48P-SI                   OBJECT IDENTIFIER ::= { hh3cProductId 161 }
hh3c-s5100-8P-SI                    OBJECT IDENTIFIER ::= { hh3cProductId 162 }
hh3c-s5100-16P-SI                   OBJECT IDENTIFIER ::= { hh3cProductId 163 }
hh3c-s5100-8P-EI                    OBJECT IDENTIFIER ::= { hh3cProductId 164 }
hh3c-s5100-16P-EI                   OBJECT IDENTIFIER ::= { hh3cProductId 165 }
hh3c-s5100-8P-PWR-EI                OBJECT IDENTIFIER ::= { hh3cProductId 166 }
hh3c-s5100-16P-PWR-EI               OBJECT IDENTIFIER ::= { hh3cProductId 167 }
hh3c-s5100-26C-PWR-EI               OBJECT IDENTIFIER ::= { hh3cProductId 168 }
hh3c-s5100-50C-PWR-EI               OBJECT IDENTIFIER ::= { hh3cProductId 169 }
hh3c-s3108TP-EI                     OBJECT IDENTIFIER ::= { hh3cProductId 170 }
hh3c-s3116TP-EI                     OBJECT IDENTIFIER ::= { hh3cProductId 171 }
hh3c-s3126TP-EI                     OBJECT IDENTIFIER ::= { hh3cProductId 172 }
hh3c-s3108TP-EI-PWR                 OBJECT IDENTIFIER ::= { hh3cProductId 173 }
hh3c-s3116TP-EI-PWR                 OBJECT IDENTIFIER ::= { hh3cProductId 174 }
hh3c-s3126TP-EI-PWR                 OBJECT IDENTIFIER ::= { hh3cProductId 175 }
hh3c-s5500M-20C                     OBJECT IDENTIFIER ::= { hh3cProductId 177 }
hh3c-s5500M-20F                     OBJECT IDENTIFIER ::= { hh3cProductId 178 }
hh3c-bR304plus                      OBJECT IDENTIFIER ::= { hh3cProductId 179 }
hh3c-s9505-V5                       OBJECT IDENTIFIER ::= { hh3cProductId 180 }
hh3c-s9512-V5                       OBJECT IDENTIFIER ::= { hh3cProductId 181 }
hh3c-s9508-V5                       OBJECT IDENTIFIER ::= { hh3cProductId 182 }
hh3c-s9508V-V5                      OBJECT IDENTIFIER ::= { hh3cProductId 183 }
hh3c-s9502-V5                       OBJECT IDENTIFIER ::= { hh3cProductId 184 }
hh3c-sR8802-V5                      OBJECT IDENTIFIER ::= { hh3cProductId 185 }
hh3c-sR8805-V5                      OBJECT IDENTIFIER ::= { hh3cProductId 186 }
hh3c-sR8812-V5                      OBJECT IDENTIFIER ::= { hh3cProductId 187 }
hh3c-sR8808-V5                      OBJECT IDENTIFIER ::= { hh3cProductId 188 }
hh3c-s3100-52P                      OBJECT IDENTIFIER ::= { hh3cProductId 189 }
hh3c-e152                           OBJECT IDENTIFIER ::= { hh3cProductId 190 }
hh3c-s2008                          OBJECT IDENTIFIER ::= { hh3cProductId 191 }
hh3c-s2026                          OBJECT IDENTIFIER ::= { hh3cProductId 192 }
hh3c-sr6602                         OBJECT IDENTIFIER ::= { hh3cProductId 193 }
hh3c-sr6608                         OBJECT IDENTIFIER ::= { hh3cProductId 194 }
hh3c-s3100-08TP-EI                  OBJECT IDENTIFIER ::= { hh3cProductId 195 }
hh3c-s3100-08TP-PWR-EI              OBJECT IDENTIFIER ::= { hh3cProductId 196 }
hh3c-s3100-16TP-EI                  OBJECT IDENTIFIER ::= { hh3cProductId 197 }
hh3c-s3100-16TP-PWR-EI              OBJECT IDENTIFIER ::= { hh3cProductId 198 }
hh3c-s3100-26TP-EI                  OBJECT IDENTIFIER ::= { hh3cProductId 199 }
hh3c-s3100-26TP-PWR-EI              OBJECT IDENTIFIER ::= { hh3cProductId 200 }
hh3c-s7502-v5                       OBJECT IDENTIFIER ::= { hh3cProductId 201 }
hh3c-vg80-21                        OBJECT IDENTIFIER ::= { hh3cProductId 202 }
hh3c-vg80-80                        OBJECT IDENTIFIER ::= { hh3cProductId 203 }
hh3c-wcm-wx5002                     OBJECT IDENTIFIER ::= { hh3cProductId 204 }
hh3c-wcm-wcma                       OBJECT IDENTIFIER ::= { hh3cProductId 205 }
hh3c-msr30-10                       OBJECT IDENTIFIER ::= { hh3cProductId 206 }
hh3c-s7502e                         OBJECT IDENTIFIER ::= { hh3cProductId 207 }
hh3c-s7503E                         OBJECT IDENTIFIER ::= { hh3cProductId 208 }
hh3c-s7506E                         OBJECT IDENTIFIER ::= { hh3cProductId 209 }
hh3c-s7506E-V                       OBJECT IDENTIFIER ::= { hh3cProductId 210 }
hh3c-secBlade-FW                    OBJECT IDENTIFIER ::= { hh3cProductId 211 }
hh3c-secBlade-IPSec                 OBJECT IDENTIFIER ::= { hh3cProductId 212 }
hh3c-s3100-8TP-SI                   OBJECT IDENTIFIER ::= { hh3cProductId 213 }
hh3c-s3100-16TP-SI                  OBJECT IDENTIFIER ::= { hh3cProductId 214 }
hh3c-e126A                          OBJECT IDENTIFIER ::= { hh3cProductId 215 }
hh3c-s3100-26TP-SI-B                OBJECT IDENTIFIER ::= { hh3cProductId 216 }
hh3c-msr30-16                       OBJECT IDENTIFIER ::= { hh3cProductId 217 }
-- This object is reserved for OEM. See in HH3C-OEM-PRODUCT-ID-MIB
hh3cOEMProductID                    OBJECT IDENTIFIER ::= { hh3cProductId 218 }
hh3c-s2126-ei                       OBJECT IDENTIFIER ::= { hh3cProductId 219 }
hh3c-e150-si                        OBJECT IDENTIFIER ::= { hh3cProductId 220 }
hh3c-msr30-11                       OBJECT IDENTIFIER ::= { hh3cProductId 221 }
hh3c-neoceanIX3040                  OBJECT IDENTIFIER ::= { hh3cProductId 222 }
hh3c-neoceanIX3080                  OBJECT IDENTIFIER ::= { hh3cProductId 223 }
hh3c-secpathF100-M                  OBJECT IDENTIFIER ::= { hh3cProductId 224 }
hh3c-neoceanVX1500                  OBJECT IDENTIFIER ::= { hh3cProductId 225 }
hh3c-neoceanIX1520                  OBJECT IDENTIFIER ::= { hh3cProductId 226 }
hh3c-neoceanIX1540                  OBJECT IDENTIFIER ::= { hh3cProductId 227 }
hh3c-wcm-wx5002-128ap               OBJECT IDENTIFIER ::= { hh3cProductId 228 }
hh3c-msr20-10                       OBJECT IDENTIFIER ::= { hh3cProductId 229 }
hh3c-msr20-11                       OBJECT IDENTIFIER ::= { hh3cProductId 230 }
hh3c-msr20-13                       OBJECT IDENTIFIER ::= { hh3cProductId 231 }
hh3c-msr20-15                       OBJECT IDENTIFIER ::= { hh3cProductId 232 }
hh3c-neoceanDL1008                  OBJECT IDENTIFIER ::= { hh3cProductId 233 }
hh3c-neoceanDL1008S                 OBJECT IDENTIFIER ::= { hh3cProductId 234 }
hh3c-neoceanDL1012                  OBJECT IDENTIFIER ::= { hh3cProductId 235 }
hh3c-s3610-52m                      OBJECT IDENTIFIER ::= { hh3cProductId 236 }
hh3c-IV5680                         OBJECT IDENTIFIER ::= { hh3cProductId 237 }
hh3c-IV5240                         OBJECT IDENTIFIER ::= { hh3cProductId 238 }
hh3c-F1000-E                        OBJECT IDENTIFIER ::= { hh3cProductId 239 }
hh3c-S5024P                         OBJECT IDENTIFIER ::= { hh3cProductId 240 }
hh3c-S5016P                         OBJECT IDENTIFIER ::= { hh3cProductId 241 }
hh3c-LSQ1FWBSC0                     OBJECT IDENTIFIER ::= { hh3cProductId 242 }
hh3c-LSB1FW2A0                      OBJECT IDENTIFIER ::= { hh3cProductId 243 }
hh3c-S3100-8TP-EI                   OBJECT IDENTIFIER ::= { hh3cProductId 244 }
hh3c-S3100-16TP-EI                  OBJECT IDENTIFIER ::= { hh3cProductId 245 }
hh3c-S3100-26TP-EI                  OBJECT IDENTIFIER ::= { hh3cProductId 246 }
hh3c-ET704                          OBJECT IDENTIFIER ::= { hh3cProductId 247 }
hh3c-ec1001                         OBJECT IDENTIFIER ::= { hh3cProductId 248 }
hh3c-ec1001-hf                      OBJECT IDENTIFIER ::= { hh3cProductId 249 }
hh3c-ec1004-hc                      OBJECT IDENTIFIER ::= { hh3cProductId 250 }
hh3c-ec2004-hf                      OBJECT IDENTIFIER ::= { hh3cProductId 251 }
hh3c-dc1001                         OBJECT IDENTIFIER ::= { hh3cProductId 252 }
hh3c-dm8000                         OBJECT IDENTIFIER ::= { hh3cProductId 253 }
hh3c-vm8000                         OBJECT IDENTIFIER ::= { hh3cProductId 254 }
hh3c-ms8000                         OBJECT IDENTIFIER ::= { hh3cProductId 255 }
hh3c-S3100-52TP                     OBJECT IDENTIFIER ::= { hh3cProductId 256 }
hh3c-msr20-12                       OBJECT IDENTIFIER ::= { hh3cProductId 257 }
hh3c-s1550E                         OBJECT IDENTIFIER ::= { hh3cProductId 258 }
hh3c-s1550                          OBJECT IDENTIFIER ::= { hh3cProductId 259 }
hh3c-s1526-EI                       OBJECT IDENTIFIER ::= { hh3cProductId 260 }
hh3c-msr20-12-T                     OBJECT IDENTIFIER ::= { hh3cProductId 261 }
hh3c-msr20-15-I                     OBJECT IDENTIFIER ::= { hh3cProductId 262 }
hh3c-msr20-15-N                     OBJECT IDENTIFIER ::= { hh3cProductId 263 }
hh3c-wx6100EWPX                     OBJECT IDENTIFIER ::= { hh3cProductId 264 }
hh3c-wx6100LSQ                      OBJECT IDENTIFIER ::= { hh3cProductId 265 }
hh3c-wx6100LSB                      OBJECT IDENTIFIER ::= { hh3cProductId 266 }
hh3c-wx6100SW                       OBJECT IDENTIFIER ::= { hh3cProductId 267 }
hh3c-dl1000                         OBJECT IDENTIFIER ::= { hh3cProductId 268 }
hh3c-dl1000s                        OBJECT IDENTIFIER ::= { hh3cProductId 269 }
hh3c-wa1208e-g                      OBJECT IDENTIFIER ::= { hh3cProductId 270 }
hh3c-wa1208e-dg                     OBJECT IDENTIFIER ::= { hh3cProductId 271 }
hh3c-wa1208e-ag                     OBJECT IDENTIFIER ::= { hh3cProductId 272 }
hh3c-wa1208e-agp                    OBJECT IDENTIFIER ::= { hh3cProductId 273 }
hh3c-S7501M-24T                     OBJECT IDENTIFIER ::= { hh3cProductId 274 }
hh3c-s7501M-24TP                    OBJECT IDENTIFIER ::= { hh3cProductId 275 }
hh3c-s7502M                         OBJECT IDENTIFIER ::= { hh3cProductId 276 }
hh3c-s7503M                         OBJECT IDENTIFIER ::= { hh3cProductId 277 }
hh3c-s7506M                         OBJECT IDENTIFIER ::= { hh3cProductId 278 }
hh3c-s7506M-V                       OBJECT IDENTIFIER ::= { hh3cProductId 279 }
hh3c-s7510M                         OBJECT IDENTIFIER ::= { hh3cProductId 280 }
hh3c-secpathT200                    OBJECT IDENTIFIER ::= { hh3cProductId 281 }
hh3c-secpathT200E                   OBJECT IDENTIFIER ::= { hh3cProductId 282 }
hh3c-cc600                          OBJECT IDENTIFIER ::= { hh3cProductId 283 }
hh3c-wa1208e-gp                     OBJECT IDENTIFIER ::= { hh3cProductId 284 }
hh3c-wb2321e-agp                    OBJECT IDENTIFIER ::= { hh3cProductId 285 }
hh3c-wh2520e-agp                    OBJECT IDENTIFIER ::= { hh3cProductId 286 }
hh3c-ICG2000                        OBJECT IDENTIFIER ::= { hh3cProductId 287 }
hh3c-ICG3000                        OBJECT IDENTIFIER ::= { hh3cProductId 288 }
hh3c-ICG5000                        OBJECT IDENTIFIER ::= { hh3cProductId 289 }
hh3c-S5520TP-SI                     OBJECT IDENTIFIER ::= { hh3cProductId 290 }
hh3c-wa2210-ag                      OBJECT IDENTIFIER ::= { hh3cProductId 291 }
hh3c-wa2220-ag                      OBJECT IDENTIFIER ::= { hh3cProductId 292 }
hh3c-wa2220e-ag                     OBJECT IDENTIFIER ::= { hh3cProductId 293 }
hh3c-wa2210x-g                      OBJECT IDENTIFIER ::= { hh3cProductId 294 }
hh3c-wa2220x-ag                     OBJECT IDENTIFIER ::= { hh3cProductId 295 }
hh3c-wa2220x-agp                    OBJECT IDENTIFIER ::= { hh3cProductId 296 }
hh3c-S3100-52TP-SI                  OBJECT IDENTIFIER ::= { hh3cProductId 297 }
hh3c-secpathASE5000-E               OBJECT IDENTIFIER ::= { hh3cProductId 298 }
hh3c-secpathASE5000-S               OBJECT IDENTIFIER ::= { hh3cProductId 299 }
hh3c-secpathU200-C                  OBJECT IDENTIFIER ::= { hh3cProductId 300 }
hh3c-secpathU200-S                  OBJECT IDENTIFIER ::= { hh3cProductId 301 }
hh3c-secpathU200-A                  OBJECT IDENTIFIER ::= { hh3cProductId 302 }
hh3c-secpathU200-M                  OBJECT IDENTIFIER ::= { hh3cProductId 303 }
hh3c-ec3016-hc                      OBJECT IDENTIFIER ::= { hh3cProductId 304 }
hh3c-dc1001-ff                      OBJECT IDENTIFIER ::= { hh3cProductId 305 }
hh3c-ecr3304-hf                     OBJECT IDENTIFIER ::= { hh3cProductId 306 }
hh3c-ecr3308-hd                     OBJECT IDENTIFIER ::= { hh3cProductId 307 }
hh3c-ecr3316-hc                     OBJECT IDENTIFIER ::= { hh3cProductId 308 }
hh3c-isc3000                        OBJECT IDENTIFIER ::= { hh3cProductId 309 }
hh3c-isc3100                        OBJECT IDENTIFIER ::= { hh3cProductId 310 }
hh3c-vm9000                         OBJECT IDENTIFIER ::= { hh3cProductId 311 }
hh3c-vm5000                         OBJECT IDENTIFIER ::= { hh3cProductId 312 }
hh3c-ms9000-vtdu                    OBJECT IDENTIFIER ::= { hh3cProductId 313 }
hh3c-ms9000-nru                     OBJECT IDENTIFIER ::= { hh3cProductId 314 }
hh3c-ums9005                        OBJECT IDENTIFIER ::= { hh3cProductId 315 }
hh3c-CS2104B                        OBJECT IDENTIFIER ::= { hh3cProductId 316 }
hh3c-CS2106B                        OBJECT IDENTIFIER ::= { hh3cProductId 317 }
hh3c-S5024E                         OBJECT IDENTIFIER ::= { hh3cProductId 318 }
hh3c-S5048E                         OBJECT IDENTIFIER ::= { hh3cProductId 319 }
hh3c-secpathF5000-A                 OBJECT IDENTIFIER ::= { hh3cProductId 320 }
hh3c-neoceanIX3240                  OBJECT IDENTIFIER ::= { hh3cProductId 321 }
hh3c-neoceanIX3620                  OBJECT IDENTIFIER ::= { hh3cProductId 322 }
hh3c-MSA7302                        OBJECT IDENTIFIER ::= { hh3cProductId 323 }
hh3c-MSA7306                        OBJECT IDENTIFIER ::= { hh3cProductId 324 }
hh3c-S7501E                         OBJECT IDENTIFIER ::= { hh3cProductId 325 }
hh3c-S3100-8C-EPON-EI               OBJECT IDENTIFIER ::= { hh3cProductId 326 }
hh3c-S3100-16C-EPON-EI              OBJECT IDENTIFIER ::= { hh3cProductId 327 }
hh3c-S3100-26C-EPON-EI              OBJECT IDENTIFIER ::= { hh3cProductId 328 }
hh3c-secBlade-LSQ1AFCBSC0           OBJECT IDENTIFIER ::= { hh3cProductId 329 }
hh3c-secBlade-LSB1AFC1A0            OBJECT IDENTIFIER ::= { hh3cProductId 330 }
hh3c-secpathF1000-C                 OBJECT IDENTIFIER ::= { hh3cProductId 331 }
hh3c-secpathF100-A-SI               OBJECT IDENTIFIER ::= { hh3cProductId 332 }
hh3c-secpathV100-E                  OBJECT IDENTIFIER ::= { hh3cProductId 333 }
hh3c-S5800-32C                      OBJECT IDENTIFIER ::= { hh3cProductId 334 }
hh3c-S5800-56C                      OBJECT IDENTIFIER ::= { hh3cProductId 335 }
hh3c-S5800-32C-PWR                  OBJECT IDENTIFIER ::= { hh3cProductId 336 }
hh3c-S5800-56C-PWR                  OBJECT IDENTIFIER ::= { hh3cProductId 337 }
hh3c-S5800-60C-PWR                  OBJECT IDENTIFIER ::= { hh3cProductId 338 }
hh3c-S5800-32F                      OBJECT IDENTIFIER ::= { hh3cProductId 339 }
hh3c-S5820X-28C                     OBJECT IDENTIFIER ::= { hh3cProductId 340 }
hh3c-S5820X-28S                     OBJECT IDENTIFIER ::= { hh3cProductId 341 }
hh3c-cc602                          OBJECT IDENTIFIER ::= { hh3cProductId 342 }
hh3c-cr400                          OBJECT IDENTIFIER ::= { hh3cProductId 343 }
hh3c-cc600E                         OBJECT IDENTIFIER ::= { hh3cProductId 344 }
hh3c-secpathT1000-M                 OBJECT IDENTIFIER ::= { hh3cProductId 345 }
hh3c-neoceanVX1540                  OBJECT IDENTIFIER ::= { hh3cProductId 346 }
hh3c-msr50-06                       OBJECT IDENTIFIER ::= { hh3cProductId 347 }
hh3c-secpathACG2000-M               OBJECT IDENTIFIER ::= { hh3cProductId 348 }
hh3c-secBlade-LSQ1ACGASC0           OBJECT IDENTIFIER ::= { hh3cProductId 349 }
hh3c-secBlade-LSB1ACG1A0            OBJECT IDENTIFIER ::= { hh3cProductId 350 }
hh3c-wx3024wcm                      OBJECT IDENTIFIER ::= { hh3cProductId 351 }
hh3c-wx3024lsw                      OBJECT IDENTIFIER ::= { hh3cProductId 352 }
hh3c-wx5004                         OBJECT IDENTIFIER ::= { hh3cProductId 353 }
hh3c-sr6604                         OBJECT IDENTIFIER ::= { hh3cProductId 354 }
hh3c-iag5000-A                      OBJECT IDENTIFIER ::= { hh3cProductId 355 }
hh3c-secBlade-SPE-FWM               OBJECT IDENTIFIER ::= { hh3cProductId 356 }
hh3c-ICG2200                        OBJECT IDENTIFIER ::= { hh3cProductId 357 }
hh3c-S7602                          OBJECT IDENTIFIER ::= { hh3cProductId 358 }
hh3c-S7603                          OBJECT IDENTIFIER ::= { hh3cProductId 359 }
hh3c-S7606                          OBJECT IDENTIFIER ::= { hh3cProductId 360 }
hh3c-S7606-V                        OBJECT IDENTIFIER ::= { hh3cProductId 361 }
hh3c-S7610                          OBJECT IDENTIFIER ::= { hh3cProductId 362 }
hh3c-wa2610e-agn                    OBJECT IDENTIFIER ::= { hh3cProductId 363 }
hh3c-wa2620e-agn                    OBJECT IDENTIFIER ::= { hh3cProductId 364 }
hh3c-wa1208e-g-v5                   OBJECT IDENTIFIER ::= { hh3cProductId 365 }
hh3c-wa1208e-dg-v5                  OBJECT IDENTIFIER ::= { hh3cProductId 366 }
hh3c-wa1208e-ag-v5                  OBJECT IDENTIFIER ::= { hh3cProductId 367 }
hh3c-wa1208e-agp-v5                 OBJECT IDENTIFIER ::= { hh3cProductId 368 }
hh3c-wa1208e-gp-v5                  OBJECT IDENTIFIER ::= { hh3cProductId 369 }
hh3c-S7503E-S                       OBJECT IDENTIFIER ::= { hh3cProductId 370 }
hh3c-secpathIAG2000-A               OBJECT IDENTIFIER ::= { hh3cProductId 371 }
hh3c-secpathT1000-A                 OBJECT IDENTIFIER ::= { hh3cProductId 372 }
hh3c-secpathT1000-S                 OBJECT IDENTIFIER ::= { hh3cProductId 373 }
hh3c-secBlade-EWPX1FWA0             OBJECT IDENTIFIER ::= { hh3cProductId 374 }
hh3c-secBlade-LSQ1NSMSC0            OBJECT IDENTIFIER ::= { hh3cProductId 375 }
hh3c-secBlade-LSQ1AFDBSC0           OBJECT IDENTIFIER ::= { hh3cProductId 376 }
hh3c-secBlade-LSQ1LBSC0             OBJECT IDENTIFIER ::= { hh3cProductId 377 }
hh3c-secBlade-LSB1LB1A0             OBJECT IDENTIFIER ::= { hh3cProductId 378 }
hh3c-neoceanIX1560                  OBJECT IDENTIFIER ::= { hh3cProductId 379 }
hh3c-neoceanEX1500S                 OBJECT IDENTIFIER ::= { hh3cProductId 380 }
hh3c-neoceanEX1520S                 OBJECT IDENTIFIER ::= { hh3cProductId 381 }
hh3c-neoceanEX1540S                 OBJECT IDENTIFIER ::= { hh3cProductId 382 }
hh3c-neoceanEX1560S                 OBJECT IDENTIFIER ::= { hh3cProductId 383 }
hh3c-ET716                          OBJECT IDENTIFIER ::= { hh3cProductId 384 }
hh3c-s3600-2P-OLT                   OBJECT IDENTIFIER ::= { hh3cProductId 385 }
hh3c-ER3200                         OBJECT IDENTIFIER ::= { hh3cProductId 386 }
hh3c-ER3100                         OBJECT IDENTIFIER ::= { hh3cProductId 387 }
hh3c-s9505E                         OBJECT IDENTIFIER ::= { hh3cProductId 388 }
hh3c-s9508E-V                       OBJECT IDENTIFIER ::= { hh3cProductId 389 }
hh3c-s9512E                         OBJECT IDENTIFIER ::= { hh3cProductId 390 }
hh3c-s12508                         OBJECT IDENTIFIER ::= { hh3cProductId 391 }
hh3c-s12518                         OBJECT IDENTIFIER ::= { hh3cProductId 392 }
hh3c-ET708                          OBJECT IDENTIFIER ::= { hh3cProductId 393 }
hh3c-ET724                          OBJECT IDENTIFIER ::= { hh3cProductId 394 }
hh3c-s2008TP-EA                     OBJECT IDENTIFIER ::= { hh3cProductId 395 }
hh3c-s2016TP-EA                     OBJECT IDENTIFIER ::= { hh3cProductId 396 }
hh3c-s2403TP-EA                     OBJECT IDENTIFIER ::= { hh3cProductId 397 }
hh3c-ICG2000-CT                     OBJECT IDENTIFIER ::= { hh3cProductId 398 }
hh3c-S3528P-EA                      OBJECT IDENTIFIER ::= { hh3cProductId 400 }
hh3c-S3552P-EA                      OBJECT IDENTIFIER ::= { hh3cProductId 401 }
hh3c-S3552F-EA                      OBJECT IDENTIFIER ::= { hh3cProductId 402 }
hh3c-S3528F-EA                      OBJECT IDENTIFIER ::= { hh3cProductId 403 }
hh3c-S3528TP-EA                     OBJECT IDENTIFIER ::= { hh3cProductId 404 }
hh3c-secpathAFD1000-A               OBJECT IDENTIFIER ::= { hh3cProductId 405 }
hh3c-secpathF100-C-EI               OBJECT IDENTIFIER ::= { hh3cProductId 406 }
hh3c-ER3260                         OBJECT IDENTIFIER ::= { hh3cProductId 407 }
hh3c-ICG800                         OBJECT IDENTIFIER ::= { hh3cProductId 408 }
hh3c-ICG800g                        OBJECT IDENTIFIER ::= { hh3cProductId 409 }
hh3c-ICG1000                        OBJECT IDENTIFIER ::= { hh3cProductId 410 }
hh3c-ICG1800                        OBJECT IDENTIFIER ::= { hh3cProductId 411 }
hh3c-neoceanIX3240E                 OBJECT IDENTIFIER ::= { hh3cProductId 412 }
hh3c-neoceanIX3620E                 OBJECT IDENTIFIER ::= { hh3cProductId 413 }
hh3c-neoceanIX3640E                 OBJECT IDENTIFIER ::= { hh3cProductId 414 }
hh3c-secpathACG8800-S3              OBJECT IDENTIFIER ::= { hh3cProductId 415 }
hh3c-secpathT5000-S3                OBJECT IDENTIFIER ::= { hh3cProductId 416 }
hh3c-secpathIAG2000-S               OBJECT IDENTIFIER ::= { hh3cProductId 417 }
hh3c-secpathACG8800-S3-NS21S2MSPB0  OBJECT IDENTIFIER ::= { hh3cProductId 418 }
hh3c-secpathT5000-S3-NS11S2MSPB0    OBJECT IDENTIFIER ::= { hh3cProductId 419 }
hh3c-msr3010                        OBJECT IDENTIFIER ::= { hh3cProductId 420 }
hh3c-msr3011E                       OBJECT IDENTIFIER ::= { hh3cProductId 421 }
hh3c-msr3011F                       OBJECT IDENTIFIER ::= { hh3cProductId 422 }
hh3c-secpathT200-A                  OBJECT IDENTIFIER ::= { hh3cProductId 423 }
hh3c-secpathT200-M                  OBJECT IDENTIFIER ::= { hh3cProductId 424 }
hh3c-secpathF100-C2                 OBJECT IDENTIFIER ::= { hh3cProductId 425 }
hh3c-DPtech-FW1000-GE               OBJECT IDENTIFIER ::= { hh3cProductId 426 }
hh3c-DPtech-FW1000-GA               OBJECT IDENTIFIER ::= { hh3cProductId 427 }
hh3c-DPtech-FW1000-GS               OBJECT IDENTIFIER ::= { hh3cProductId 428 }
hh3c-DPtech-FW1000-ME               OBJECT IDENTIFIER ::= { hh3cProductId 429 }
hh3c-DPtech-FW1000-MA               OBJECT IDENTIFIER ::= { hh3cProductId 430 }
hh3c-DPtech-FW1000-MM               OBJECT IDENTIFIER ::= { hh3cProductId 431 }
hh3c-DPtech-FW1000-MC               OBJECT IDENTIFIER ::= { hh3cProductId 432 }
hh3c-DPtech-UTM2000-MA              OBJECT IDENTIFIER ::= { hh3cProductId 433 }
hh3c-DPtech-UTM2000-MM              OBJECT IDENTIFIER ::= { hh3cProductId 434 }
hh3c-DPtech-UTM2000-MS              OBJECT IDENTIFIER ::= { hh3cProductId 435 }
hh3c-DPtech-IPS2000-GM              OBJECT IDENTIFIER ::= { hh3cProductId 436 }
hh3c-DPtech-IPS2000-MM              OBJECT IDENTIFIER ::= { hh3cProductId 437 }
hh3c-sr6616                         OBJECT IDENTIFIER ::= { hh3cProductId 438 }
hh3c-s3620-28TP-EI                  OBJECT IDENTIFIER ::= { hh3cProductId 439 }
hh3c-s3620-28P-EI                   OBJECT IDENTIFIER ::= { hh3cProductId 440 }
hh3c-s3620-52P-EI                   OBJECT IDENTIFIER ::= { hh3cProductId 441 }
hh3c-s3620-28P-PWR-EI               OBJECT IDENTIFIER ::= { hh3cProductId 442 }
hh3c-s3620-52P-PWR-EI               OBJECT IDENTIFIER ::= { hh3cProductId 443 }
hh3c-s3620-28F-EI                   OBJECT IDENTIFIER ::= { hh3cProductId 444 }
hh3c-s3620-52M                      OBJECT IDENTIFIER ::= { hh3cProductId 445 }
hh3c-s3620-52M-DC                   OBJECT IDENTIFIER ::= { hh3cProductId 446 }
hh3c-s3620-28C-EI                   OBJECT IDENTIFIER ::= { hh3cProductId 447 }
hh3c-wa2210e-ge                     OBJECT IDENTIFIER ::= { hh3cProductId 448 }
hh3c-wa2220x-age                    OBJECT IDENTIFIER ::= { hh3cProductId 449 }
hh3c-wa2210x-ge                     OBJECT IDENTIFIER ::= { hh3cProductId 450 }
hh3c-wb2320x-age                    OBJECT IDENTIFIER ::= { hh3cProductId 451 }
hh3c-neoceanEX1540                  OBJECT IDENTIFIER ::= { hh3cProductId 452 }
hh3c-S5810-50S                      OBJECT IDENTIFIER ::= { hh3cProductId 453 }
hh3c-secBlade-LSQ1IPSSC0            OBJECT IDENTIFIER ::= { hh3cProductId 454 }
hh3c-secBlade-LSB1IPS1A0            OBJECT IDENTIFIER ::= { hh3cProductId 455 }
hh3c-ER5100                         OBJECT IDENTIFIER ::= { hh3cProductId 456 }
hh3c-ER5200                         OBJECT IDENTIFIER ::= { hh3cProductId 457 }
hh3c-wx3010wcm                      OBJECT IDENTIFIER ::= { hh3cProductId 458 }
hh3c-wx3010lsw                      OBJECT IDENTIFIER ::= { hh3cProductId 459 }
hh3c-cc652E                         OBJECT IDENTIFIER ::= { hh3cProductId 460 }
hh3c-S5120-20P-SI                   OBJECT IDENTIFIER ::= { hh3cProductId 461 }
hh3c-S5120-28P-SI                   OBJECT IDENTIFIER ::= { hh3cProductId 462 }
hh3c-S5120-52P-SI                   OBJECT IDENTIFIER ::= { hh3cProductId 463 }
hh3c-S5120-28P-EI                   OBJECT IDENTIFIER ::= { hh3cProductId 464 }
hh3c-S5120-52P-EI                   OBJECT IDENTIFIER ::= { hh3cProductId 465 }
hh3c-S5120-28P-LPWR-EI              OBJECT IDENTIFIER ::= { hh3cProductId 466 }
hh3c-S5120-28P-PWR-EI               OBJECT IDENTIFIER ::= { hh3cProductId 467 }
hh3c-wx6100LSR                      OBJECT IDENTIFIER ::= { hh3cProductId 468 }
hh3c-s7506E-S                       OBJECT IDENTIFIER ::= { hh3cProductId 469 }
hh3c-ICG2000B                       OBJECT IDENTIFIER ::= { hh3cProductId 470 }
hh3c-ICG2000C                       OBJECT IDENTIFIER ::= { hh3cProductId 471 }
hh3c-S1626                          OBJECT IDENTIFIER ::= { hh3cProductId 472 }
hh3c-S1650                          OBJECT IDENTIFIER ::= { hh3cProductId 473 }
hh3c-S1626P                         OBJECT IDENTIFIER ::= { hh3cProductId 474 }
hh3c-neoceanIX3620S                 OBJECT IDENTIFIER ::= { hh3cProductId 475 }
hh3c-neoceanIX3080S                 OBJECT IDENTIFIER ::= { hh3cProductId 476 }
hh3c-ER3280g                        OBJECT IDENTIFIER ::= { hh3cProductId 477 }
hh3c-wa2610-agn                     OBJECT IDENTIFIER ::= { hh3cProductId 478 }
hh3c-wa2612-agn                     OBJECT IDENTIFIER ::= { hh3cProductId 479 }
hh3c-secpathT200-S                  OBJECT IDENTIFIER ::= { hh3cProductId 480 }
hh3c-secpathU200-CS                 OBJECT IDENTIFIER ::= { hh3cProductId 481 }
hh3c-secpathU200-CM                 OBJECT IDENTIFIER ::= { hh3cProductId 482 }
hh3c-secpathU200-CA                 OBJECT IDENTIFIER ::= { hh3cProductId 483 }
hh3c-secBlade-LSR1AFC2A1            OBJECT IDENTIFIER ::= { hh3cProductId 484 }
hh3c-secBlade-LSR1FW2A1             OBJECT IDENTIFIER ::= { hh3cProductId 485 }
hh3c-secBlade-LSR1LB1A1             OBJECT IDENTIFIER ::= { hh3cProductId 486 }
hh3c-secBlade-LSR1NSM1A1            OBJECT IDENTIFIER ::= { hh3cProductId 487 }
hh3c-cc650E                         OBJECT IDENTIFIER ::= { hh3cProductId 488 }
hh3c-LSWM1WCM10                     OBJECT IDENTIFIER ::= { hh3cProductId 489 }
hh3c-LSWM1WCM20                     OBJECT IDENTIFIER ::= { hh3cProductId 490 }
hh3c-EWPXM1WCMC0                    OBJECT IDENTIFIER ::= { hh3cProductId 491 }
hh3c-LSWM1IPS10                     OBJECT IDENTIFIER ::= { hh3cProductId 492 }
hh3c-LSWM1FW10                      OBJECT IDENTIFIER ::= { hh3cProductId 493 }
hh3c-secpathF1000-S-EI              OBJECT IDENTIFIER ::= { hh3cProductId 494 }
hh3c-secpathF1000-A-EI              OBJECT IDENTIFIER ::= { hh3cProductId 495 }
hh3c-msr50-06-V5                    OBJECT IDENTIFIER ::= { hh3cProductId 496 }
hh3c-secBlade-LSR1ACG1A1            OBJECT IDENTIFIER ::= { hh3cProductId 497 }
hh3c-secBlade-LSR1IPS1A1            OBJECT IDENTIFIER ::= { hh3cProductId 498 }
hh3c-S7602-S                        OBJECT IDENTIFIER ::= { hh3cProductId 499 }
hh3c-S7603-S                        OBJECT IDENTIFIER ::= { hh3cProductId 500 }
hh3c-S7606-S                        OBJECT IDENTIFIER ::= { hh3cProductId 501 }
hh3c-SSM-s5500G                     OBJECT IDENTIFIER ::= { hh3cProductId 502 }
hh3c-SSM-FIC                        OBJECT IDENTIFIER ::= { hh3cProductId 503 }
hh3c-SSM-MIM                        OBJECT IDENTIFIER ::= { hh3cProductId 504 }
hh3c-ER8300                         OBJECT IDENTIFIER ::= { hh3cProductId 505 }
hh3c-wa2610x-gnp                    OBJECT IDENTIFIER ::= { hh3cProductId 506 }
hh3c-wb2360x-anp                    OBJECT IDENTIFIER ::= { hh3cProductId 507 }
hh3c-wh2530x-dag                    OBJECT IDENTIFIER ::= { hh3cProductId 508 }
hh3c-wa2620-agn                     OBJECT IDENTIFIER ::= { hh3cProductId 509 }
hh3c-cc610E                         OBJECT IDENTIFIER ::= { hh3cProductId 510 }
hh3c-DPtech-FW1000-GT               OBJECT IDENTIFIER ::= { hh3cProductId 511 }
hh3c-s2008TP-EA-SI                  OBJECT IDENTIFIER ::= { hh3cProductId 512 }
hh3c-s2016TP-EA-SI                  OBJECT IDENTIFIER ::= { hh3cProductId 513 }
hh3c-s2403TP-EA-SI                  OBJECT IDENTIFIER ::= { hh3cProductId 514 }
hh3c-S5120-24P-EI                   OBJECT IDENTIFIER ::= { hh3cProductId 515 }
hh3c-S5120-48P-EI                   OBJECT IDENTIFIER ::= { hh3cProductId 516 }
hh3c-S5120-28C-EI                   OBJECT IDENTIFIER ::= { hh3cProductId 517 }
hh3c-S5120-52C-EI                   OBJECT IDENTIFIER ::= { hh3cProductId 518 }
hh3c-S5120-28C-PWR-EI               OBJECT IDENTIFIER ::= { hh3cProductId 519 }
hh3c-S5120-52C-PWR-EI               OBJECT IDENTIFIER ::= { hh3cProductId 520 }
hh3c-wx3008wcm                      OBJECT IDENTIFIER ::= { hh3cProductId 521 }
hh3c-wx3008lsw                      OBJECT IDENTIFIER ::= { hh3cProductId 522 }
hh3c-msr900                         OBJECT IDENTIFIER ::= { hh3cProductId 523 }
hh3c-msr920                         OBJECT IDENTIFIER ::= { hh3cProductId 524 }
hh3c-secBlade-LSQ1IAGSC0            OBJECT IDENTIFIER ::= { hh3cProductId 525 }
hh3c-WX7306                         OBJECT IDENTIFIER ::= { hh3cProductId 526 }
hh3c-WX7310                         OBJECT IDENTIFIER ::= { hh3cProductId 527 }
hh3c-Blade5310                      OBJECT IDENTIFIER ::= { hh3cProductId 528 }
hh3c-Blade55102                     OBJECT IDENTIFIER ::= { hh3cProductId 529 }
hh3c-Blade5512S                     OBJECT IDENTIFIER ::= { hh3cProductId 530 }
hh3c-Blade55110X                    OBJECT IDENTIFIER ::= { hh3cProductId 531 }
hh3c-wa2610e-gnp                    OBJECT IDENTIFIER ::= { hh3cProductId 532 }
hh3c-s3100-26TP-SI-UM               OBJECT IDENTIFIER ::= { hh3cProductId 533 }
hh3c-s3100-52TP-SI-UM               OBJECT IDENTIFIER ::= { hh3cProductId 534 }
hh3c-s5500-24P-SI                   OBJECT IDENTIFIER ::= { hh3cProductId 535 }
hh3c-s5500-48P-SI                   OBJECT IDENTIFIER ::= { hh3cProductId 536 }
hh3c-ME8000                         OBJECT IDENTIFIER ::= { hh3cProductId 537 }
hh3c-ME8600                         OBJECT IDENTIFIER ::= { hh3cProductId 538 }
hh3c-ME5000                         OBJECT IDENTIFIER ::= { hh3cProductId 539 }
hh3c-MG6060                         OBJECT IDENTIFIER ::= { hh3cProductId 540 }
hh3c-MG6050                         OBJECT IDENTIFIER ::= { hh3cProductId 541 }
hh3c-MG6050S                        OBJECT IDENTIFIER ::= { hh3cProductId 542 }
hh3c-MG9010                         OBJECT IDENTIFIER ::= { hh3cProductId 543 }
hh3c-MG9030                         OBJECT IDENTIFIER ::= { hh3cProductId 544 }
hh3c-MG9060                         OBJECT IDENTIFIER ::= { hh3cProductId 545 }
hh3c-neoceanVX1500-DC               OBJECT IDENTIFIER ::= { hh3cProductId 546 }
hh3c-cc620E                         OBJECT IDENTIFIER ::= { hh3cProductId 547 }
hh3c-SIVX-S3628                     OBJECT IDENTIFIER ::= { hh3cProductId 548 }
hh3c-SIVX-S5528                     OBJECT IDENTIFIER ::= { hh3cProductId 549 }
hh3c-SIVX-VS1500                    OBJECT IDENTIFIER ::= { hh3cProductId 550 }
hh3c-neoceanIX2540                  OBJECT IDENTIFIER ::= { hh3cProductId 551 }
hh3c-neoceanVX2500                  OBJECT IDENTIFIER ::= { hh3cProductId 552 }
hh3c-S5120-28P-PWR-SI               OBJECT IDENTIFIER ::= { hh3cProductId 555 }
hh3c-S5120-28P-HPWR-SI              OBJECT IDENTIFIER ::= { hh3cProductId 556 }
hh3c-F1000-E-DC                     OBJECT IDENTIFIER ::= { hh3cProductId 557 }
hh3c-S5028                          OBJECT IDENTIFIER ::= { hh3cProductId 558 }
hh3c-ET824                          OBJECT IDENTIFIER ::= { hh3cProductId 559 }
hh3c-OSM                            OBJECT IDENTIFIER ::= { hh3cProductId 560 }
hh3c-wx5002-v2                      OBJECT IDENTIFIER ::= { hh3cProductId 561 }
hh3c-wx5004-v2                      OBJECT IDENTIFIER ::= { hh3cProductId 562 }
hh3c-secpathT1000-C                 OBJECT IDENTIFIER ::= { hh3cProductId 563 }
hh3c-secBlade-LST1IPS1A1            OBJECT IDENTIFIER ::= { hh3cProductId 564 }
hh3c-secBlade-LST1FW2A1             OBJECT IDENTIFIER ::= { hh3cProductId 565 }
hh3c-secBlade-LST1LB1A1             OBJECT IDENTIFIER ::= { hh3cProductId 566 }
hh3c-secBlade-LST1NSM1A1            OBJECT IDENTIFIER ::= { hh3cProductId 567 }
hh3c-secBlade-EWPX2IAGSC0           OBJECT IDENTIFIER ::= { hh3cProductId 568 }
hh3c-F1000-A-EI                     OBJECT IDENTIFIER ::= { hh3cProductId 569 }
hh3c-wx6108E                        OBJECT IDENTIFIER ::= { hh3cProductId 570 }
hh3c-wx6112E                        OBJECT IDENTIFIER ::= { hh3cProductId 571 }
hh3c-s5500-34C-HI                   OBJECT IDENTIFIER ::= { hh3cProductId 572 }
hh3c-s5500-58C-HI                   OBJECT IDENTIFIER ::= { hh3cProductId 573 }
hh3c-wa1208e-gp-h20                 OBJECT IDENTIFIER ::= { hh3cProductId 574 }
hh3c-S5120-9P-SI                    OBJECT IDENTIFIER ::= { hh3cProductId 575 }
hh3c-S5120-9P-PWR-SI                OBJECT IDENTIFIER ::= { hh3cProductId 576 }
hh3c-S5120-9P-HPWR-SI               OBJECT IDENTIFIER ::= { hh3cProductId 577 }
hh3c-e528                           OBJECT IDENTIFIER ::= { hh3cProductId 578 }
hh3c-e552                           OBJECT IDENTIFIER ::= { hh3cProductId 579 }
hh3c-s3600V2-28TP-EI                OBJECT IDENTIFIER ::= { hh3cProductId 580 }
hh3c-s3600V2-52TP-EI                OBJECT IDENTIFIER ::= { hh3cProductId 581 }
hh3c-s3600V2-28TP-PWR-EI            OBJECT IDENTIFIER ::= { hh3cProductId 582 }
hh3c-s3600V2-52TP-PWR-EI            OBJECT IDENTIFIER ::= { hh3cProductId 583 }
hh3c-s3600V2-28F-EI                 OBJECT IDENTIFIER ::= { hh3cProductId 584 }
hh3c-s3600V2-28TP-SI                OBJECT IDENTIFIER ::= { hh3cProductId 585 }
hh3c-s3600V2-52TP-SI                OBJECT IDENTIFIER ::= { hh3cProductId 586 }
hh3c-s3600V2-28TP-PWR-SI            OBJECT IDENTIFIER ::= { hh3cProductId 587 }
hh3c-s3600V2-52TP-PWR-SI            OBJECT IDENTIFIER ::= { hh3cProductId 588 }
hh3c-s3500V2-28TP-EA                OBJECT IDENTIFIER ::= { hh3cProductId 589 }
hh3c-s3500V2-52TP-EA                OBJECT IDENTIFIER ::= { hh3cProductId 590 }
hh3c-s3500V2-28F-EA                 OBJECT IDENTIFIER ::= { hh3cProductId 591 }
hh3c-s3500V2-28TP-SI                OBJECT IDENTIFIER ::= { hh3cProductId 592 }
hh3c-s3500V2-52TP-SI                OBJECT IDENTIFIER ::= { hh3cProductId 593 }
hh3c-s9508E                         OBJECT IDENTIFIER ::= { hh3cProductId 594 }
hh3c-s12504                         OBJECT IDENTIFIER ::= { hh3cProductId 595 }
hh3c-ICG2000B-GT                    OBJECT IDENTIFIER ::= { hh3cProductId 596 }
hh3c-ICG3000B                       OBJECT IDENTIFIER ::= { hh3cProductId 597 }
hh3c-ICG3000S                       OBJECT IDENTIFIER ::= { hh3cProductId 598 }
hh3c-ICG5000B                       OBJECT IDENTIFIER ::= { hh3cProductId 599 }
hh3c-wh2640X-agnp                   OBJECT IDENTIFIER ::= { hh3cProductId 600 }
hh3c-wa2620X-agnp                   OBJECT IDENTIFIER ::= { hh3cProductId 601 }
hh3c-s3100-16TP-PWR-EI-F            OBJECT IDENTIFIER ::= { hh3cProductId 602 }
hh3c-cr16018                        OBJECT IDENTIFIER ::= { hh3cProductId 603 }
hh3c-cr16008                        OBJECT IDENTIFIER ::= { hh3cProductId 604 }
hh3c-cr16004                        OBJECT IDENTIFIER ::= { hh3cProductId 605 }
hh3c-F1000-A-SI                     OBJECT IDENTIFIER ::= { hh3cProductId 606 }
hh3c-F1000-E-SI                     OBJECT IDENTIFIER ::= { hh3cProductId 607 }
hh3c-secBlade-LST1ACG1A1            OBJECT IDENTIFIER ::= { hh3cProductId 608 }
hh3c-secBlade-SPE-IPS               OBJECT IDENTIFIER ::= { hh3cProductId 609 }
hh3c-secBlade-SPE-ACG               OBJECT IDENTIFIER ::= { hh3cProductId 610 }
hh3c-wx6103                         OBJECT IDENTIFIER ::= { hh3cProductId 611 }
hh3c-LSQ1WCMD0                      OBJECT IDENTIFIER ::= { hh3cProductId 612 }
hh3c-EWPX2WCMD0                     OBJECT IDENTIFIER ::= { hh3cProductId 613 }
hh3c-LSR1WCM3A1                     OBJECT IDENTIFIER ::= { hh3cProductId 614 }
hh3c-S5830-52SC                     OBJECT IDENTIFIER ::= { hh3cProductId 615 }
hh3c-S5830-106S                     OBJECT IDENTIFIER ::= { hh3cProductId 617 }
hh3c-ET814                          OBJECT IDENTIFIER ::= { hh3cProductId 618 }
hh3c-S5120-28P-LI                   OBJECT IDENTIFIER ::= { hh3cProductId 619 }
hh3c-S5120-52P-LI                   OBJECT IDENTIFIER ::= { hh3cProductId 620 }
hh3c-secBlade-IM-FW-II              OBJECT IDENTIFIER ::= { hh3cProductId 621 }
hh3c-secBlade-IM-LB                 OBJECT IDENTIFIER ::= { hh3cProductId 622 }
hh3c-secBlade-IM-SSL                OBJECT IDENTIFIER ::= { hh3cProductId 623 }
hh3c-ER2210C                        OBJECT IDENTIFIER ::= { hh3cProductId 625 }
hh3c-VCX-Connect-100                OBJECT IDENTIFIER ::= { hh3cProductId 626 }
hh3c-VCX-Connect-200                OBJECT IDENTIFIER ::= { hh3cProductId 627 }
hh3c-VCX-V7005                      OBJECT IDENTIFIER ::= { hh3cProductId 628 }
hh3c-VCX-V7205                      OBJECT IDENTIFIER ::= { hh3cProductId 629 }
hh3c-VCX-MIM                        OBJECT IDENTIFIER ::= { hh3cProductId 630 }
hh3c-VCX-Connect-MIM-Primary        OBJECT IDENTIFIER ::= { hh3cProductId 631 }
hh3c-VCX-Connect-MIM-Secondary      OBJECT IDENTIFIER ::= { hh3cProductId 632 }
hh3c-VCX-V7310                      OBJECT IDENTIFIER ::= { hh3cProductId 633 }
hh3c-secBlade-IM-IPS                OBJECT IDENTIFIER ::= { hh3cProductId 634 }
hh3c-secBlade-IM-ACG                OBJECT IDENTIFIER ::= { hh3cProductId 635 }
hh3c-s7508E-X                       OBJECT IDENTIFIER ::= { hh3cProductId 636 }
hh3c-s10504                         OBJECT IDENTIFIER ::= { hh3cProductId 637 }
hh3c-s10508                         OBJECT IDENTIFIER ::= { hh3cProductId 638 }
hh3c-s10508-V                       OBJECT IDENTIFIER ::= { hh3cProductId 639 }
hh3c-secBlade-SPE-FWM-200           OBJECT IDENTIFIER ::= { hh3cProductId 640 }
hh3c-secpathF1000-S-AI              OBJECT IDENTIFIER ::= { hh3cProductId 641 }
hh3c-wx3024e-wcm                    OBJECT IDENTIFIER ::= { hh3cProductId 642 }
hh3c-wx3024e-lsw                    OBJECT IDENTIFIER ::= { hh3cProductId 643 }
hh3c-ER2100                         OBJECT IDENTIFIER ::= { hh3cProductId 644 }
hh3c-S5820X-34TC                    OBJECT IDENTIFIER ::= { hh3cProductId 645 }
hh3c-S5820X-34SC                    OBJECT IDENTIFIER ::= { hh3cProductId 646 }
hh3c-S5820X-34C                     OBJECT IDENTIFIER ::= { hh3cProductId 647 }
hh3c-S5820X-64SC                    OBJECT IDENTIFIER ::= { hh3cProductId 648 }
hh3c-cc720E                         OBJECT IDENTIFIER ::= { hh3cProductId 649 }
hh3c-S2126T                         OBJECT IDENTIFIER ::= { hh3cProductId 650 }
hh3c-S5800-54S                      OBJECT IDENTIFIER ::= { hh3cProductId 651 }
hh3c-S5820X-26S                     OBJECT IDENTIFIER ::= { hh3cProductId 652 }
hh3c-S3100V2-8TP-SI                 OBJECT IDENTIFIER ::= { hh3cProductId 653 }
hh3c-S3100V2-16TP-SI                OBJECT IDENTIFIER ::= { hh3cProductId 654 }
hh3c-S3100V2-26TP-SI                OBJECT IDENTIFIER ::= { hh3cProductId 655 }
hh3c-E126B                          OBJECT IDENTIFIER ::= { hh3cProductId 656 }
hh3c-S3100V2-8TP-EI                 OBJECT IDENTIFIER ::= { hh3cProductId 657 }
hh3c-S3100V2-16TP-EI                OBJECT IDENTIFIER ::= { hh3cProductId 658 }
hh3c-S3100V2-26TP-EI                OBJECT IDENTIFIER ::= { hh3cProductId 659 }
hh3c-S3100V2-8TP-PWR-EI             OBJECT IDENTIFIER ::= { hh3cProductId 660 }
hh3c-S3100V2-16TP-PWR-EI            OBJECT IDENTIFIER ::= { hh3cProductId 661 }
hh3c-S3100V2-26TP-PWR-EI            OBJECT IDENTIFIER ::= { hh3cProductId 662 }
hh3c-S2008TP-EB                     OBJECT IDENTIFIER ::= { hh3cProductId 663 }
hh3c-S2016TP-EB                     OBJECT IDENTIFIER ::= { hh3cProductId 664 }
hh3c-S2403TP-EB                     OBJECT IDENTIFIER ::= { hh3cProductId 665 }
hh3c-S2008TP-PWR-EB                 OBJECT IDENTIFIER ::= { hh3cProductId 666 }
hh3c-S2016TP-PWR-EB                 OBJECT IDENTIFIER ::= { hh3cProductId 667 }
hh3c-S2403TP-PWR-EB                 OBJECT IDENTIFIER ::= { hh3cProductId 668 }
hh3c-S5800-LSW1FC4P0                OBJECT IDENTIFIER ::= { hh3cProductId 669 }
hh3c-S2403TP-EA-SI-D                OBJECT IDENTIFIER ::= { hh3cProductId 670 }
hh3c-S3528P-EA-D                    OBJECT IDENTIFIER ::= { hh3cProductId 671 }
hh3c-OAP-FIC-V2                     OBJECT IDENTIFIER ::= { hh3cProductId 672 }
hh3c-OAP-MIM-V2                     OBJECT IDENTIFIER ::= { hh3cProductId 673 }
hh3c-OAPS-MIM-V2                    OBJECT IDENTIFIER ::= { hh3cProductId 674 }
hh3c-S2008TP-PWR-EA                 OBJECT IDENTIFIER ::= { hh3cProductId 675 }
hh3c-S2008TP-PWR-EA-DC              OBJECT IDENTIFIER ::= { hh3cProductId 676 }
hh3c-S2016TP-PWR-EA                 OBJECT IDENTIFIER ::= { hh3cProductId 677 }
hh3c-S2403TP-PWR-EA                 OBJECT IDENTIFIER ::= { hh3cProductId 678 }
hh3c-S5120-24P-EI-D                 OBJECT IDENTIFIER ::= { hh3cProductId 679 }
hh3c-S5120-24P-PWR-EI-D             OBJECT IDENTIFIER ::= { hh3cProductId 680 }
hh3c-S5120-48P-EI-D                 OBJECT IDENTIFIER ::= { hh3cProductId 681 }
hh3c-S5024P-EI                      OBJECT IDENTIFIER ::= { hh3cProductId 682 }
hh3c-S5500-28C-EI-D                 OBJECT IDENTIFIER ::= { hh3cProductId 683 }
hh3c-S5500-52C-EI-D                 OBJECT IDENTIFIER ::= { hh3cProductId 684 }
hh3c-S5500-28F-EI-D                 OBJECT IDENTIFIER ::= { hh3cProductId 685 }
hh3c-S5500-28C-EI-DC-D              OBJECT IDENTIFIER ::= { hh3cProductId 686 }
hh3c-MG9050                         OBJECT IDENTIFIER ::= { hh3cProductId 687 }
hh3c-S5120-52SC-HI                  OBJECT IDENTIFIER ::= { hh3cProductId 688 }
hh3c-CE3000-32F-EI                  OBJECT IDENTIFIER ::= { hh3cProductId 689 }
hh3cS5830V224S                      OBJECT IDENTIFIER ::= { hh3cProductId 690 }
hh3cDC1801FH                        OBJECT IDENTIFIER ::= { hh3cProductId 691 }
hh3cDC2004FF                        OBJECT IDENTIFIER ::= { hh3cProductId 692 }
hh3cEC1101HF                        OBJECT IDENTIFIER ::= { hh3cProductId 693 }
hh3cEC1102HF                        OBJECT IDENTIFIER ::= { hh3cProductId 694 }
hh3cEC1501HF                        OBJECT IDENTIFIER ::= { hh3cProductId 695 }
hh3cEC1801HH                        OBJECT IDENTIFIER ::= { hh3cProductId 696 }
hh3cEC2516HF                        OBJECT IDENTIFIER ::= { hh3cProductId 697 }
hh3cEC2016HC                        OBJECT IDENTIFIER ::= { hh3cProductId 698 }
hh3cEC2016HC8CH                     OBJECT IDENTIFIER ::= { hh3cProductId 699 }
hh3cEC2016HC4CH                     OBJECT IDENTIFIER ::= { hh3cProductId 700 }
hh3cEC1504HF                        OBJECT IDENTIFIER ::= { hh3cProductId 701 }
hh3cHIC5421                         OBJECT IDENTIFIER ::= { hh3cProductId 702 }
hh3cHIC5401                         OBJECT IDENTIFIER ::= { hh3cProductId 703 }
hh3cHIC5221H                        OBJECT IDENTIFIER ::= { hh3cProductId 704 }
hh3cHIC5201H                        OBJECT IDENTIFIER ::= { hh3cProductId 705 }
hh3cVM8500                          OBJECT IDENTIFIER ::= { hh3cProductId 706 }
hh3cMS8500                          OBJECT IDENTIFIER ::= { hh3cProductId 707 }
hh3cDM8500                          OBJECT IDENTIFIER ::= { hh3cProductId 708 }
hh3cVX500                           OBJECT IDENTIFIER ::= { hh3cProductId 709 }
hh3cISC3000E                        OBJECT IDENTIFIER ::= { hh3cProductId 710 }
hh3cISC3000S                        OBJECT IDENTIFIER ::= { hh3cProductId 711 }
hh3cCC700E                          OBJECT IDENTIFIER ::= { hh3cProductId 712 }
hh3cDC1001FF                        OBJECT IDENTIFIER ::= { hh3cProductId 713 }
hh3cECR3316HC                       OBJECT IDENTIFIER ::= { hh3cProductId 714 }
hh3cECR3308HD                       OBJECT IDENTIFIER ::= { hh3cProductId 715 }
hh3cECR3316HC8CH                    OBJECT IDENTIFIER ::= { hh3cProductId 716 }
hh3cECR3316HC4CH                    OBJECT IDENTIFIER ::= { hh3cProductId 717 }
hh3cECR3308HD4CH                    OBJECT IDENTIFIER ::= { hh3cProductId 718 }
hh3cHIC65017L                       OBJECT IDENTIFIER ::= { hh3cProductId 719 }
hh3cEC2508HF                        OBJECT IDENTIFIER ::= { hh3cProductId 720 }
hh3cS3528EA                         OBJECT IDENTIFIER ::= { hh3cProductId 721 }
hh3cS3552TPEA                       OBJECT IDENTIFIER ::= { hh3cProductId 722 }
hh3cWP3024                          OBJECT IDENTIFIER ::= { hh3cProductId 723 }
hh3cWP3048                          OBJECT IDENTIFIER ::= { hh3cProductId 724 }
hh3cS3528FPEA                       OBJECT IDENTIFIER ::= { hh3cProductId 725 }
hh3cE328B                           OBJECT IDENTIFIER ::= { hh3cProductId 726 }
hh3cE352B                           OBJECT IDENTIFIER ::= { hh3cProductId 727 }
hh3cE152B                           OBJECT IDENTIFIER ::= { hh3cProductId 728 }
hh3cS3100V252TP                     OBJECT IDENTIFIER ::= { hh3cProductId 729 }
hh3cWP2008                          OBJECT IDENTIFIER ::= { hh3cProductId 730 }
hh3cWP2016                          OBJECT IDENTIFIER ::= { hh3cProductId 731 }
hh3cWP2024                          OBJECT IDENTIFIER ::= { hh3cProductId 732 }
hh3cWP5024                          OBJECT IDENTIFIER ::= { hh3cProductId 733 }
hh3cWP5048                          OBJECT IDENTIFIER ::= { hh3cProductId 734 }
hh3cS2052TPEA                       OBJECT IDENTIFIER ::= { hh3cProductId 735 }
hh3cS7604X                          OBJECT IDENTIFIER ::= { hh3cProductId 736 }
hh3cS7608X                          OBJECT IDENTIFIER ::= { hh3cProductId 737 }
hh3cS7608XV                         OBJECT IDENTIFIER ::= { hh3cProductId 738 }
hh3cWA3620iAGN                      OBJECT IDENTIFIER ::= { hh3cProductId 739 }
hh3cWA3628iAGN                      OBJECT IDENTIFIER ::= { hh3cProductId 740 }
hh3cWA3610iGN                       OBJECT IDENTIFIER ::= { hh3cProductId 741 }
hh3cCC750E                          OBJECT IDENTIFIER ::= { hh3cProductId 742 }
hh3cS5024FSI                        OBJECT IDENTIFIER ::= { hh3cProductId 743 }
hh3cS5820V252QF                     OBJECT IDENTIFIER ::= { hh3cProductId 744 }
hh3cWA2110GN                        OBJECT IDENTIFIER ::= { hh3cProductId 745 }
hh3cMSR2010E                        OBJECT IDENTIFIER ::= { hh3cProductId 746 }
hh3cS10512                          OBJECT IDENTIFIER ::= { hh3cProductId 747 }
hh3cS512028SCHI                     OBJECT IDENTIFIER ::= { hh3cProductId 748 }
hh3cWA1208EGNP                      OBJECT IDENTIFIER ::= { hh3cProductId 749 }
hh3cWA2610EGNPH20                   OBJECT IDENTIFIER ::= { hh3cProductId 750 }
hh3cWA2620iAGN                      OBJECT IDENTIFIER ::= { hh3cProductId 751 }
hh3cWA2610iGN                       OBJECT IDENTIFIER ::= { hh3cProductId 752 }
hh3cWA2612                          OBJECT IDENTIFIER ::= { hh3cProductId 753 }
hh3cWA2620                          OBJECT IDENTIFIER ::= { hh3cProductId 754 }
hh3cWB524                           OBJECT IDENTIFIER ::= { hh3cProductId 755 }
hh3cSecBladeLST1FW3A1               OBJECT IDENTIFIER ::= { hh3cProductId 756 }
hh3cSecBladeLSU1FWCEA0              OBJECT IDENTIFIER ::= { hh3cProductId 757 }
hh3cWX3010eWCM                      OBJECT IDENTIFIER ::= { hh3cProductId 758 }
hh3cWX3010eLSW                      OBJECT IDENTIFIER ::= { hh3cProductId 759 }
hh3cSR6602X1                        OBJECT IDENTIFIER ::= { hh3cProductId 760 }
hh3cSR6602X2                        OBJECT IDENTIFIER ::= { hh3cProductId 761 }
hh3cSecBladeCRIMNAM1A               OBJECT IDENTIFIER ::= { hh3cProductId 762 }
hh3cMSR2630                         OBJECT IDENTIFIER ::= { hh3cProductId 763 }
hh3cMSR3610AC                       OBJECT IDENTIFIER ::= { hh3cProductId 764 }
hh3cMSR3610DC                       OBJECT IDENTIFIER ::= { hh3cProductId 765 }
hh3cMSR3620AC                       OBJECT IDENTIFIER ::= { hh3cProductId 766 }
hh3cMSR3620DC                       OBJECT IDENTIFIER ::= { hh3cProductId 767 }
hh3cMSR3620POE                      OBJECT IDENTIFIER ::= { hh3cProductId 768 }
hh3cMSR3640                         OBJECT IDENTIFIER ::= { hh3cProductId 769 }
hh3cMSR3660                         OBJECT IDENTIFIER ::= { hh3cProductId 770 }
hh3cMSR5660                         OBJECT IDENTIFIER ::= { hh3cProductId 771 }
hh3cMSR5680                         OBJECT IDENTIFIER ::= { hh3cProductId 772 }
hh3cS512058CHI                      OBJECT IDENTIFIER ::= { hh3cProductId 773 }
hh3cS512034CHI                      OBJECT IDENTIFIER ::= { hh3cProductId 774 }
hh3cLSU3WCMD0                       OBJECT IDENTIFIER ::= { hh3cProductId 775 }
hh3cEWPX3WCMD0                      OBJECT IDENTIFIER ::= { hh3cProductId 776 }
hh3cS7612X                          OBJECT IDENTIFIER ::= { hh3cProductId 777 }
hh3cWX6103E                         OBJECT IDENTIFIER ::= { hh3cProductId 778 }
hh3cSecBladeCRIMFW1A                OBJECT IDENTIFIER ::= { hh3cProductId 779 }
hh3cHIC66216C                       OBJECT IDENTIFIER ::= { hh3cProductId 780 }
hh3cHIC66216L                       OBJECT IDENTIFIER ::= { hh3cProductId 781 }
hh3cHIC3401V                        OBJECT IDENTIFIER ::= { hh3cProductId 782 }
hh3cHIC3401VIR                      OBJECT IDENTIFIER ::= { hh3cProductId 783 }
hh3cHIC3421V                        OBJECT IDENTIFIER ::= { hh3cProductId 784 }
hh3cHIC3421VIR                      OBJECT IDENTIFIER ::= { hh3cProductId 785 }
hh3cSIC235IR1                       OBJECT IDENTIFIER ::= { hh3cProductId 786 }
hh3cSIC235IR3                       OBJECT IDENTIFIER ::= { hh3cProductId 787 }
hh3cSIC335EVIR                      OBJECT IDENTIFIER ::= { hh3cProductId 788 }
hh3cHIC5511I                        OBJECT IDENTIFIER ::= { hh3cProductId 789 }
hh3cHIC5521I                        OBJECT IDENTIFIER ::= { hh3cProductId 790 }
hh3cHIC5551I                        OBJECT IDENTIFIER ::= { hh3cProductId 791 }
hh3cHIC5421E                        OBJECT IDENTIFIER ::= { hh3cProductId 792 }
hh3cHIC5401E                        OBJECT IDENTIFIER ::= { hh3cProductId 793 }
hh3cHIC5421D                        OBJECT IDENTIFIER ::= { hh3cProductId 794 }
hh3cHIC5401D                        OBJECT IDENTIFIER ::= { hh3cProductId 795 }
hh3cHIC5621                         OBJECT IDENTIFIER ::= { hh3cProductId 796 }
hh3cHIC5601                         OBJECT IDENTIFIER ::= { hh3cProductId 797 }
hh3cHIC6501E                        OBJECT IDENTIFIER ::= { hh3cProductId 798 }
hh3cHIC6621E                        OBJECT IDENTIFIER ::= { hh3cProductId 799 }
hh3cSIC635                          OBJECT IDENTIFIER ::= { hh3cProductId 800 }
hh3cHIC6501IR                       OBJECT IDENTIFIER ::= { hh3cProductId 801 }
hh3cHIC6621IR                       OBJECT IDENTIFIER ::= { hh3cProductId 802 }
hh3cSIC635IR                        OBJECT IDENTIFIER ::= { hh3cProductId 803 }
hh3cEC2508HF4CH                     OBJECT IDENTIFIER ::= { hh3cProductId 804 }
hh3cEC2516HF8CH                     OBJECT IDENTIFIER ::= { hh3cProductId 805 }
hh3cECR3308HF                       OBJECT IDENTIFIER ::= { hh3cProductId 806 }
hh3cECR3316HF                       OBJECT IDENTIFIER ::= { hh3cProductId 807 }
hh3cISC3500E                        OBJECT IDENTIFIER ::= { hh3cProductId 808 }
hh3cISC3500S                        OBJECT IDENTIFIER ::= { hh3cProductId 809 }
hh3cECR3304HFE                      OBJECT IDENTIFIER ::= { hh3cProductId 810 }
hh3cECR3308HFE                      OBJECT IDENTIFIER ::= { hh3cProductId 811 }
hh3cECR3316HFE                      OBJECT IDENTIFIER ::= { hh3cProductId 812 }
hh3cISC3600                         OBJECT IDENTIFIER ::= { hh3cProductId 813 }
hh3cECR3204HW                       OBJECT IDENTIFIER ::= { hh3cProductId 814 }
hh3cECR3208HW                       OBJECT IDENTIFIER ::= { hh3cProductId 815 }
hh3cECR3216HW                       OBJECT IDENTIFIER ::= { hh3cProductId 816 }
hh3cEC2508HW                        OBJECT IDENTIFIER ::= { hh3cProductId 817 }
hh3cEC2516HW                        OBJECT IDENTIFIER ::= { hh3cProductId 818 }
hh3cISC2600                         OBJECT IDENTIFIER ::= { hh3cProductId 819 }
hh3cDC2808FH                        OBJECT IDENTIFIER ::= { hh3cProductId 820 }
hh3cCE300034C                       OBJECT IDENTIFIER ::= { hh3cProductId 821 }
hh3cCE300058C                       OBJECT IDENTIFIER ::= { hh3cProductId 822 }
hh3cSR6604X                         OBJECT IDENTIFIER ::= { hh3cProductId 823 }
hh3cSR6608X                         OBJECT IDENTIFIER ::= { hh3cProductId 824 }
hh3cSR6616X                         OBJECT IDENTIFIER ::= { hh3cProductId 825 }
hh3csecpathF100AG                   OBJECT IDENTIFIER ::= { hh3cProductId 826 }
hh3csecpathF100CG                   OBJECT IDENTIFIER ::= { hh3cProductId 827 }
hh3csecpathF100EG                   OBJECT IDENTIFIER ::= { hh3cProductId 828 }
hh3csecpathF100MG                   OBJECT IDENTIFIER ::= { hh3cProductId 829 }
hh3csecpathF100SG                   OBJECT IDENTIFIER ::= { hh3cProductId 830 }
hh3cS3100V226TPWiNet                OBJECT IDENTIFIER ::= { hh3cProductId 831 }
hh3cS550024PWiNet                   OBJECT IDENTIFIER ::= { hh3cProductId 832 }
hh3cS512028PPoeWiNet                OBJECT IDENTIFIER ::= { hh3cProductId 833 }
hh3cS512028PWiNet                   OBJECT IDENTIFIER ::= { hh3cProductId 834 }
hh3cS550034CPWRHI                   OBJECT IDENTIFIER ::= { hh3cProductId 835 }
hh3cS550058CPWRHI                   OBJECT IDENTIFIER ::= { hh3cProductId 836 }
hh3cS550034FHI                      OBJECT IDENTIFIER ::= { hh3cProductId 837 }
hh3cMSR930                          OBJECT IDENTIFIER ::= { hh3cProductId 838 }
hh3cMSV50                           OBJECT IDENTIFIER ::= { hh3cProductId 839 }
hh3cMSR930WiNet                     OBJECT IDENTIFIER ::= { hh3cProductId 840 }
hh3cMSR930GU                        OBJECT IDENTIFIER ::= { hh3cProductId 841 }
hh3cMSR930sa                        OBJECT IDENTIFIER ::= { hh3cProductId 842 }
hh3cMSR930GG                        OBJECT IDENTIFIER ::= { hh3cProductId 843 }
hh3cS5820V254QSGE                   OBJECT IDENTIFIER ::= { hh3cProductId 844 }
hh3cS5820V252Q                      OBJECT IDENTIFIER ::= { hh3cProductId 845 }
hh3cCC754E                          OBJECT IDENTIFIER ::= { hh3cProductId 846 }
hh3cWP5008                          OBJECT IDENTIFIER ::= { hh3cProductId 847 }
hh3cSecBladeCRIMLB1A                OBJECT IDENTIFIER ::= { hh3cProductId 848 }
hh3cS550034CHID                     OBJECT IDENTIFIER ::= { hh3cProductId 849 }
hh3cS550058CHID                     OBJECT IDENTIFIER ::= { hh3cProductId 850 }
hh3cS9505EV7                        OBJECT IDENTIFIER ::= { hh3cProductId 851 }
hh3cS9508EV7                        OBJECT IDENTIFIER ::= { hh3cProductId 852 }
hh3cS9508EVV7                       OBJECT IDENTIFIER ::= { hh3cProductId 853 }
hh3cS9512EV7                        OBJECT IDENTIFIER ::= { hh3cProductId 854 }
hh3cS12508V7                        OBJECT IDENTIFIER ::= { hh3cProductId 855 }
hh3cS12518V7                        OBJECT IDENTIFIER ::= { hh3cProductId 856 }
hh3cS12504V7                        OBJECT IDENTIFIER ::= { hh3cProductId 857 }
hh3csecpathF100CAI                  OBJECT IDENTIFIER ::= { hh3cProductId 858 }
hh3csecpathL1000A                   OBJECT IDENTIFIER ::= { hh3cProductId 859 }
hh3cWA2610E                         OBJECT IDENTIFIER ::= { hh3cProductId 860 }
hh3cWA2620E                         OBJECT IDENTIFIER ::= { hh3cProductId 861 }
hh3cWA2620X                         OBJECT IDENTIFIER ::= { hh3cProductId 862 }
hh3cWA2610X                         OBJECT IDENTIFIER ::= { hh3cProductId 863 }
hh3cS6802                           OBJECT IDENTIFIER ::= { hh3cProductId 864 }
hh3cS9804                           OBJECT IDENTIFIER ::= { hh3cProductId 865 }
hh3cSecBladeLSU1IPSBEA0             OBJECT IDENTIFIER ::= { hh3cProductId 866 }
hh3cSecBladeLST1IPS2A1              OBJECT IDENTIFIER ::= { hh3cProductId 867 }
hh3cMSR930W                         OBJECT IDENTIFIER ::= { hh3cProductId 868 }
hh3cMSR930WGU                       OBJECT IDENTIFIER ::= { hh3cProductId 869 }
hh3cSecPathF5000C                   OBJECT IDENTIFIER ::= { hh3cProductId 870 }
hh3cSecPathF5000S                   OBJECT IDENTIFIER ::= { hh3cProductId 871 }
hh3cS12510FDC                       OBJECT IDENTIFIER ::= { hh3cProductId 872 }
hh3cS12510FAC                       OBJECT IDENTIFIER ::= { hh3cProductId 873 }
hh3cS12510XDC                       OBJECT IDENTIFIER ::= { hh3cProductId 874 }
hh3cS12510XAC                       OBJECT IDENTIFIER ::= { hh3cProductId 875 }
hh3cS12508                          OBJECT IDENTIFIER ::= { hh3cProductId 876 }
hh3cS12518                          OBJECT IDENTIFIER ::= { hh3cProductId 877 }
hh3cS12516FDC                       OBJECT IDENTIFIER ::= { hh3cProductId 878 }
hh3cS12516FAC                       OBJECT IDENTIFIER ::= { hh3cProductId 879 }
hh3cS12516XDC                       OBJECT IDENTIFIER ::= { hh3cProductId 880 }
hh3cS12516XAC                       OBJECT IDENTIFIER ::= { hh3cProductId 881 }
hh3cMSR930GT                        OBJECT IDENTIFIER ::= { hh3cProductId 882 }
hh3cMSR2600GTC                      OBJECT IDENTIFIER ::= { hh3cProductId 883 }
hh3cMSR2600GUC                      OBJECT IDENTIFIER ::= { hh3cProductId 884 }
hh3csecpathF1000AG                  OBJECT IDENTIFIER ::= { hh3cProductId 885 }
hh3csecpathF1000CG                  OBJECT IDENTIFIER ::= { hh3cProductId 886 }
hh3csecpathF1000SG                  OBJECT IDENTIFIER ::= { hh3cProductId 887 }
hh3cSecBladeLSQ2FWBSCO              OBJECT IDENTIFIER ::= { hh3cProductId 888 }
hh3cWA2620AGN                       OBJECT IDENTIFIER ::= { hh3cProductId 889 }
hh3cVSR                             OBJECT IDENTIFIER ::= { hh3cProductId 890 }
hh3cVSR1001                         OBJECT IDENTIFIER ::= { hh3cProductId 891 }
hh3cVSR1004                         OBJECT IDENTIFIER ::= { hh3cProductId 892 }
hh3cVSR1008                         OBJECT IDENTIFIER ::= { hh3cProductId 893 }
hh3cS5120S28PEI                     OBJECT IDENTIFIER ::= { hh3cProductId 894 }
hh3cS5120S52PEI                     OBJECT IDENTIFIER ::= { hh3cProductId 895 }
hh3cMSR930WiNetW                    OBJECT IDENTIFIER ::= { hh3cProductId 896 }
hh3cWA3628iAGNX                     OBJECT IDENTIFIER ::= { hh3cProductId 897 }
hh3cS2110                           OBJECT IDENTIFIER ::= { hh3cProductId 898 }
hh3cS2110PWR                        OBJECT IDENTIFIER ::= { hh3cProductId 899 }
hh3cS2126                           OBJECT IDENTIFIER ::= { hh3cProductId 900 }
hh3cS2126PWR                        OBJECT IDENTIFIER ::= { hh3cProductId 901 }
hh3cS2152                           OBJECT IDENTIFIER ::= { hh3cProductId 902 }
hh3cWX5540WCM                       OBJECT IDENTIFIER ::= { hh3cProductId 903 }
hh3cWX5540LSW                       OBJECT IDENTIFIER ::= { hh3cProductId 904 }
hh3cWX5520WCM                       OBJECT IDENTIFIER ::= { hh3cProductId 905 }
hh3cWX5520LSW                       OBJECT IDENTIFIER ::= { hh3cProductId 906 }
hh3cMSR930WGT                       OBJECT IDENTIFIER ::= { hh3cProductId 907 }
hh3cICG5000T                        OBJECT IDENTIFIER ::= { hh3cProductId 908 }
hh3cICG6000                         OBJECT IDENTIFIER ::= { hh3cProductId 909 }
hh3cMSR2630WiNet                    OBJECT IDENTIFIER ::= { hh3cProductId 910 }
hh3cMSR3610WiNet                    OBJECT IDENTIFIER ::= { hh3cProductId 911 }
hh3cMSR3660WiNet                    OBJECT IDENTIFIER ::= { hh3cProductId 912 }
hh3cMSR260010                       OBJECT IDENTIFIER ::= { hh3cProductId 913 }
hh3cMSR260010WiNet                  OBJECT IDENTIFIER ::= { hh3cProductId 914 }
hh3cMSR260017                       OBJECT IDENTIFIER ::= { hh3cProductId 915 }
hh3cICG3000D                        OBJECT IDENTIFIER ::= { hh3cProductId 916 }
hh3cICG3000E                        OBJECT IDENTIFIER ::= { hh3cProductId 917 }
hh3cSecBladeLSU1ADECEA0             OBJECT IDENTIFIER ::= { hh3cProductId 918 }
hh3cSecBladeLST1ADE1A1              OBJECT IDENTIFIER ::= { hh3cProductId 919 }
hh3cSR8804X                         OBJECT IDENTIFIER ::= { hh3cProductId 920 }
hh3cSR8808X                         OBJECT IDENTIFIER ::= { hh3cProductId 921 }
hh3cSR8812X                         OBJECT IDENTIFIER ::= { hh3cProductId 922 }
hh3cCC710E                          OBJECT IDENTIFIER ::= { hh3cProductId 923 }
hh3cCC712E                          OBJECT IDENTIFIER ::= { hh3cProductId 924 }
hh3cS680032Q                        OBJECT IDENTIFIER ::= { hh3cProductId 925 }
hh3cS5008PV2EI                      OBJECT IDENTIFIER ::= { hh3cProductId 926 }
hh3cS5024PV2EI                      OBJECT IDENTIFIER ::= { hh3cProductId 927 }
hh3cS5048PV2EI                      OBJECT IDENTIFIER ::= { hh3cProductId 928 }
hh3cS2610                           OBJECT IDENTIFIER ::= { hh3cProductId 929 }
hh3cS2610PWR                        OBJECT IDENTIFIER ::= { hh3cProductId 930 }
hh3cS2626                           OBJECT IDENTIFIER ::= { hh3cProductId 931 }
hh3cS2626PWR                        OBJECT IDENTIFIER ::= { hh3cProductId 932 }
hh3cS2652                           OBJECT IDENTIFIER ::= { hh3cProductId 933 }
hh3cSimware7BoxCen                  OBJECT IDENTIFIER ::= { hh3cProductId 934 }
hh3cSimware7BoxIRF                  OBJECT IDENTIFIER ::= { hh3cProductId 935 }
hh3cSimware7ChassisDevice           OBJECT IDENTIFIER ::= { hh3cProductId 936 }
hh3cVSR1000                         OBJECT IDENTIFIER ::= { hh3cProductId 937 }
hh3csecpathM9000                    OBJECT IDENTIFIER ::= { hh3cProductId 938 }
hh3csecpathM9006                    OBJECT IDENTIFIER ::= { hh3cProductId 939 }
hh3csecpathM9010                    OBJECT IDENTIFIER ::= { hh3cProductId 940 }
hh3csecpathM9014                    OBJECT IDENTIFIER ::= { hh3cProductId 941 }
hh3cSecBladeIIINSQM1FWCEA0          OBJECT IDENTIFIER ::= { hh3cProductId 942 }
hh3cWB521X                          OBJECT IDENTIFIER ::= { hh3cProductId 943 }
hh3cWB511X                          OBJECT IDENTIFIER ::= { hh3cProductId 944 }
hh3cER3108G                         OBJECT IDENTIFIER ::= { hh3cProductId 945 }
hh3cER3108GW                        OBJECT IDENTIFIER ::= { hh3cProductId 946 }
hh3cS513028SEI                      OBJECT IDENTIFIER ::= { hh3cProductId 947 }
hh3cS513052SEI                      OBJECT IDENTIFIER ::= { hh3cProductId 948 }
hh3cS513028FEI                      OBJECT IDENTIFIER ::= { hh3cProductId 949 }
hh3cS513028SPWREI                   OBJECT IDENTIFIER ::= { hh3cProductId 950 }
hh3cS513052SPWREI                   OBJECT IDENTIFIER ::= { hh3cProductId 951 }
hh3cMSR360028                       OBJECT IDENTIFIER ::= { hh3cProductId 952 }
hh3cMSR360051                       OBJECT IDENTIFIER ::= { hh3cProductId 953 }
hh3cWA2612E                         OBJECT IDENTIFIER ::= { hh3cProductId 954 }
hh3cWA2622                          OBJECT IDENTIFIER ::= { hh3cProductId 955 }
hh3cS511010P                        OBJECT IDENTIFIER ::= { hh3cProductId 956 }
hh3cS511010PPWR                     OBJECT IDENTIFIER ::= { hh3cProductId 957 }
hh3cS511028P                        OBJECT IDENTIFIER ::= { hh3cProductId 958 }
hh3cS511028PPWR                     OBJECT IDENTIFIER ::= { hh3cProductId 959 }
hh3cS511052P                        OBJECT IDENTIFIER ::= { hh3cProductId 960 }
hh3cS511010PD                       OBJECT IDENTIFIER ::= { hh3cProductId 961 }
hh3cS511010PPWRD                    OBJECT IDENTIFIER ::= { hh3cProductId 962 }
hh3cS511028PD                       OBJECT IDENTIFIER ::= { hh3cProductId 963 }
hh3cS511028PPWRD                    OBJECT IDENTIFIER ::= { hh3cProductId 964 }
hh3cS511052PD                       OBJECT IDENTIFIER ::= { hh3cProductId 965 }
hh3cWX5510                          OBJECT IDENTIFIER ::= { hh3cProductId 966 }
hh3cS550028SCHI                     OBJECT IDENTIFIER ::= { hh3cProductId 967 }
hh3cS550052SCHI                     OBJECT IDENTIFIER ::= { hh3cProductId 968 }
hh3cS550028SCHID                    OBJECT IDENTIFIER ::= { hh3cProductId 969 }
hh3cS550052SCHID                    OBJECT IDENTIFIER ::= { hh3cProductId 970 }
hh3cLA2608                          OBJECT IDENTIFIER ::= { hh3cProductId 971 }
hh3cS311010TP                       OBJECT IDENTIFIER ::= { hh3cProductId 972 }
hh3cS311010TPPWR                    OBJECT IDENTIFIER ::= { hh3cProductId 973 }
hh3cS311026TP                       OBJECT IDENTIFIER ::= { hh3cProductId 974 }
hh3cS311026TPPWR                    OBJECT IDENTIFIER ::= { hh3cProductId 975 }
hh3cS311052TP                       OBJECT IDENTIFIER ::= { hh3cProductId 976 }
hh3cWA2610HGN                       OBJECT IDENTIFIER ::= { hh3cProductId 977 }
hh3cWA4620EACN                      OBJECT IDENTIFIER ::= { hh3cProductId 978 }
hh3cWA4620IACN                      OBJECT IDENTIFIER ::= { hh3cProductId 979 }
hh3cEWPX1MAC0                       OBJECT IDENTIFIER ::= { hh3cProductId 980 }
hh3cCRIMMAC1A                       OBJECT IDENTIFIER ::= { hh3cProductId 981 }
hh3cSecBladeIIILST1FW3B1            OBJECT IDENTIFIER ::= { hh3cProductId 982 }
hh3cWA2620iAGNX                     OBJECT IDENTIFIER ::= { hh3cProductId 983 }
hh3cS311010TPSI                     OBJECT IDENTIFIER ::= { hh3cProductId 984 }
hh3cS311026TPSI                     OBJECT IDENTIFIER ::= { hh3cProductId 985 }
hh3cS311052TPSI                     OBJECT IDENTIFIER ::= { hh3cProductId 986 }
hh3cS511010PSI                      OBJECT IDENTIFIER ::= { hh3cProductId 987 }
hh3cS511028PSI                      OBJECT IDENTIFIER ::= { hh3cProductId 988 }
hh3cS511052PSI                      OBJECT IDENTIFIER ::= { hh3cProductId 989 }
hh3cS3100V252TPWiNet                OBJECT IDENTIFIER ::= { hh3cProductId 990 }
hh3cS512052PWiNet                   OBJECT IDENTIFIER ::= { hh3cProductId 991 }
hh3cS550048PWiNet                   OBJECT IDENTIFIER ::= { hh3cProductId 992 }
hh3cS550028FWiNet                   OBJECT IDENTIFIER ::= { hh3cProductId 993 }
hh3CWA2620EX                        OBJECT IDENTIFIER ::= { hh3cProductId 994 }
hh3csecpathL5000S                   OBJECT IDENTIFIER ::= { hh3cProductId 995 }
hh3csecpathL5000C                   OBJECT IDENTIFIER ::= { hh3cProductId 996 }
hh3cCC721E                          OBJECT IDENTIFIER ::= { hh3cProductId 997 }
hh3cS5820V252QFU                    OBJECT IDENTIFIER ::= { hh3cProductId 998 }
hh3csecpathvFW1000                  OBJECT IDENTIFIER ::= { hh3cProductId 999 }
hh3cS7003                           OBJECT IDENTIFIER ::= { hh3cProductId 1000 }
hh3cS7006                           OBJECT IDENTIFIER ::= { hh3cProductId 1001 }
hh3csecpathF100CSI                  OBJECT IDENTIFIER ::= { hh3cProductId 1002 }
hh3cWX3510E                         OBJECT IDENTIFIER ::= { hh3cProductId 1003 }
hh3cWX3540E                         OBJECT IDENTIFIER ::= { hh3cProductId 1004 }
hh3cSecBladeLSU3FWCEA0              OBJECT IDENTIFIER ::= { hh3cProductId 1005 }
hh3cSecBladeLSU1NSCEA0              OBJECT IDENTIFIER ::= { hh3cProductId 1006 }
hh3cSecBladeLST1FW3C1               OBJECT IDENTIFIER ::= { hh3cProductId 1007 }
hh3cSecBladeLST1NSM2C1              OBJECT IDENTIFIER ::= { hh3cProductId 1008 }
hh3cSecBladeLSX1FWCEA1              OBJECT IDENTIFIER ::= { hh3cProductId 1009 }
hh3cSecBladeLSX1NSCEA1              OBJECT IDENTIFIER ::= { hh3cProductId 1010 }
hh3cWA2620AGNC                      OBJECT IDENTIFIER ::= { hh3cProductId 1011 }
hh3cWA2610GN                        OBJECT IDENTIFIER ::= { hh3cProductId 1012 }
hh3cWA2610GNE                       OBJECT IDENTIFIER ::= { hh3cProductId 1013 }
hh3cMSR800                          OBJECT IDENTIFIER ::= { hh3cProductId 1014 }
hh3cMSR800Wlan                      OBJECT IDENTIFIER ::= { hh3cProductId 1015 }
hh3cMSR80010                        OBJECT IDENTIFIER ::= { hh3cProductId 1016 }
hh3cMSR80010Wlan                    OBJECT IDENTIFIER ::= { hh3cProductId 1017 }
hh3cMSR830WiNet                     OBJECT IDENTIFIER ::= { hh3cProductId 1018 }
hh3cMSR83010WiNet                   OBJECT IDENTIFIER ::= { hh3cProductId 1019 }
hh3cMSR93010WiNet                   OBJECT IDENTIFIER ::= { hh3cProductId 1020 }
hh3cS9810                           OBJECT IDENTIFIER ::= { hh3cProductId 1021 }
hh3cFlexNetworkB6300XLG             OBJECT IDENTIFIER ::= { hh3cProductId 1022 }
hh3cFlexNetworkB6300GXG             OBJECT IDENTIFIER ::= { hh3cProductId 1023 }
hh3cMSR900E                         OBJECT IDENTIFIER ::= { hh3cProductId 1024 }
hh3cMSR900EWlan                     OBJECT IDENTIFIER ::= { hh3cProductId 1025 }
hh3cS513028SEID                     OBJECT IDENTIFIER ::= { hh3cProductId 1026 }
hh3cS513052SEID                     OBJECT IDENTIFIER ::= { hh3cProductId 1027 }
hh3cS513028FEID                     OBJECT IDENTIFIER ::= { hh3cProductId 1028 }
hh3cS513028SHPWREID                 OBJECT IDENTIFIER ::= { hh3cProductId 1029 }
hh3cS513052SPWREID                  OBJECT IDENTIFIER ::= { hh3cProductId 1030 }
hh3cS513028SHPWREI                  OBJECT IDENTIFIER ::= { hh3cProductId 1031 }
hh3cE528X                           OBJECT IDENTIFIER ::= { hh3cProductId 1032 }
hh3cE552X                           OBJECT IDENTIFIER ::= { hh3cProductId 1033 }
hh3cLSU1WCME0                       OBJECT IDENTIFIER ::= { hh3cProductId 1034 }
hh3cEWPX1WCME0                      OBJECT IDENTIFIER ::= { hh3cProductId 1035 }
hh3cSR8810XS                        OBJECT IDENTIFIER ::= { hh3cProductId 1036 }
hh3cSR8806XS                        OBJECT IDENTIFIER ::= { hh3cProductId 1037 }
hh3cSR8803XS                        OBJECT IDENTIFIER ::= { hh3cProductId 1038 }
hh3cSR8802XS                        OBJECT IDENTIFIER ::= { hh3cProductId 1039 }
hh3cSecPathF5020                    OBJECT IDENTIFIER ::= { hh3cProductId 1040 }
hh3cSecPathF5040                    OBJECT IDENTIFIER ::= { hh3cProductId 1041 }
hh3cRA100                           OBJECT IDENTIFIER ::= { hh3cProductId 1042 }
hh3cMSR930LM                        OBJECT IDENTIFIER ::= { hh3cProductId 1043 }
hh3cMSR930WLM                       OBJECT IDENTIFIER ::= { hh3cProductId 1044 }
hh3cMSR26005LMC                     OBJECT IDENTIFIER ::= { hh3cProductId 1045 }
hh3cS580032CEI                      OBJECT IDENTIFIER ::= { hh3cProductId 1046 }
hh3cS580056CEI                      OBJECT IDENTIFIER ::= { hh3cProductId 1047 }
hh3cS580032CPWREI                   OBJECT IDENTIFIER ::= { hh3cProductId 1048 }
hh3cS580056CPWREI                   OBJECT IDENTIFIER ::= { hh3cProductId 1049 }
hh3cS580056CEIM                     OBJECT IDENTIFIER ::= { hh3cProductId 1050 }
hh3cWB521XE                         OBJECT IDENTIFIER ::= { hh3cProductId 1051 }
hh3cWB521XH                         OBJECT IDENTIFIER ::= { hh3cProductId 1052 }
hh3cWX2540E                         OBJECT IDENTIFIER ::= { hh3cProductId 1053 }
hh3cWX360                           OBJECT IDENTIFIER ::= { hh3cProductId 1054 }
hh3cWX361                           OBJECT IDENTIFIER ::= { hh3cProductId 1055 }
hh3cWA2610EGNE                      OBJECT IDENTIFIER ::= { hh3cProductId 1056 }
hh3cSR6603F                         OBJECT IDENTIFIER ::= { hh3cProductId 1057 }
hh3cSR6605F                         OBJECT IDENTIFIER ::= { hh3cProductId 1058 }
hh3cSR6609F                         OBJECT IDENTIFIER ::= { hh3cProductId 1059 }
hh3cS556030SEI                      OBJECT IDENTIFIER ::= { hh3cProductId 1060 }
hh3cS556054SEI                      OBJECT IDENTIFIER ::= { hh3cProductId 1061 }
hh3cS556030CEI                      OBJECT IDENTIFIER ::= { hh3cProductId 1062 }
hh3cS556054CEI                      OBJECT IDENTIFIER ::= { hh3cProductId 1063 }
hh3cS556030CPWREI                   OBJECT IDENTIFIER ::= { hh3cProductId 1064 }
hh3cS556054CPWREI                   OBJECT IDENTIFIER ::= { hh3cProductId 1065 }
hh3cS556054QSEI                     OBJECT IDENTIFIER ::= { hh3cProductId 1066 }
hh3cRA200                           OBJECT IDENTIFIER ::= { hh3cProductId 1067 }
hh3cF1000CSI                        OBJECT IDENTIFIER ::= { hh3cProductId 1068 }
hh3cF100MSI                         OBJECT IDENTIFIER ::= { hh3cProductId 1069 }
hh3cF100ASI                         OBJECT IDENTIFIER ::= { hh3cProductId 1070 }
hh3cS5820V248S                      OBJECT IDENTIFIER ::= { hh3cProductId 1071 }
hh3cS630042QT                       OBJECT IDENTIFIER ::= { hh3cProductId 1072 }
hh3cS630042QF                       OBJECT IDENTIFIER ::= { hh3cProductId 1073 }
hh3cS630048S                        OBJECT IDENTIFIER ::= { hh3cProductId 1074 }
hh3cS630052QF                       OBJECT IDENTIFIER ::= { hh3cProductId 1075 }
hh3cFlexNetworkU830048G             OBJECT IDENTIFIER ::= { hh3cProductId 1076 }
hh3cFlexNetworkU830048XLGU          OBJECT IDENTIFIER ::= { hh3cProductId 1077 }
hh3cS5008PV2EIPWR                   OBJECT IDENTIFIER ::= { hh3cProductId 1078 }
hh3cS5024PV2EIPWR                   OBJECT IDENTIFIER ::= { hh3cProductId 1079 }
hh3cS511052PPWR                     OBJECT IDENTIFIER ::= { hh3cProductId 1080 }
hh3cS511052PPWRD                    OBJECT IDENTIFIER ::= { hh3cProductId 1081 }
hh3cNSC1000                         OBJECT IDENTIFIER ::= { hh3cProductId 1082 }
hh3cMS4308                          OBJECT IDENTIFIER ::= { hh3cProductId 1083 }
hh3cMS4308PWR                       OBJECT IDENTIFIER ::= { hh3cProductId 1084 }
hh3cS513028TPEI                     OBJECT IDENTIFIER ::= { hh3cProductId 1085 }
hh3cS513052TPEI                     OBJECT IDENTIFIER ::= { hh3cProductId 1086 }
hh3cS513028TPPWREI                  OBJECT IDENTIFIER ::= { hh3cProductId 1087 }
hh3cS513052TPPWREI                  OBJECT IDENTIFIER ::= { hh3cProductId 1088 }
hh3csecpathF1020                    OBJECT IDENTIFIER ::= { hh3cProductId 1089 }
hh3csecpathF1030                    OBJECT IDENTIFIER ::= { hh3cProductId 1090 }
hh3csecpathF1050                    OBJECT IDENTIFIER ::= { hh3cProductId 1091 }
hh3csecpathF1060                    OBJECT IDENTIFIER ::= { hh3cProductId 1092 }
hh3csecpathF1070                    OBJECT IDENTIFIER ::= { hh3cProductId 1093 }
hh3csecpathF1080                    OBJECT IDENTIFIER ::= { hh3cProductId 1094 }
hh3csecpathvLB1000                  OBJECT IDENTIFIER ::= { hh3cProductId 1095 }
hh3cS5864F                          OBJECT IDENTIFIER ::= { hh3cProductId 1096 }
hh3cS5864UF                         OBJECT IDENTIFIER ::= { hh3cProductId 1097 }
hh3cS5864TF                         OBJECT IDENTIFIER ::= { hh3cProductId 1098 }
hh3cS6348F                          OBJECT IDENTIFIER ::= { hh3cProductId 1099 }
hh3cS6348TF                         OBJECT IDENTIFIER ::= { hh3cProductId 1100 }
hh3cCR16006F                        OBJECT IDENTIFIER ::= { hh3cProductId 1101 }
hh3cCR16010F                        OBJECT IDENTIFIER ::= { hh3cProductId 1102 }
hh3cCR16014F                        OBJECT IDENTIFIER ::= { hh3cProductId 1103 }
hh3cSecPathM9000Context             OBJECT IDENTIFIER ::= { hh3cProductId 1104 }
hh3cICG3000SE                       OBJECT IDENTIFIER ::= { hh3cProductId 1105 }
hh3cS68004C                         OBJECT IDENTIFIER ::= { hh3cProductId 1106 }
hh3cS68002C                         OBJECT IDENTIFIER ::= { hh3cProductId 1107 }
hh3cSR8803F                         OBJECT IDENTIFIER ::= { hh3cProductId 1108 }
hh3cSR8805F                         OBJECT IDENTIFIER ::= { hh3cProductId 1109 }
hh3cSR8808F                         OBJECT IDENTIFIER ::= { hh3cProductId 1110 }
hh3cSR8812F                         OBJECT IDENTIFIER ::= { hh3cProductId 1111 }
hh3cS12516XAF                       OBJECT IDENTIFIER ::= { hh3cProductId 1112 }
hh3cvAC                             OBJECT IDENTIFIER ::= { hh3cProductId 1113 }
hh3cWX8700                          OBJECT IDENTIFIER ::= { hh3cProductId 1114 }
hh3cS556030FEI                      OBJECT IDENTIFIER ::= { hh3cProductId 1115 }
hh3cS5530CEID                       OBJECT IDENTIFIER ::= { hh3cProductId 1116 }
hh3cS5554CEID                       OBJECT IDENTIFIER ::= { hh3cProductId 1117 }
hh3cS5530CPWREID                    OBJECT IDENTIFIER ::= { hh3cProductId 1118 }
hh3cS5554CPWREID                    OBJECT IDENTIFIER ::= { hh3cProductId 1119 }
hh3cS5530FEID                       OBJECT IDENTIFIER ::= { hh3cProductId 1120 }
hh3cS513028SSI                      OBJECT IDENTIFIER ::= { hh3cProductId 1121 }
hh3cS513052SSI                      OBJECT IDENTIFIER ::= { hh3cProductId 1122 }
hh3cS513028FSI                      OBJECT IDENTIFIER ::= { hh3cProductId 1123 }
hh3cS556028SSI                      OBJECT IDENTIFIER ::= { hh3cProductId 1124 }
hh3cS556052SSI                      OBJECT IDENTIFIER ::= { hh3cProductId 1125 }
hh3cS556028FSI                      OBJECT IDENTIFIER ::= { hh3cProductId 1126 }
hh3cLA4608E                         OBJECT IDENTIFIER ::= { hh3cProductId 1127 }
hh3cWA4320ACN                       OBJECT IDENTIFIER ::= { hh3cProductId 1128 }
hh3cWA4320iACN                      OBJECT IDENTIFIER ::= { hh3cProductId 1129 }
hh3cWA4320iX                        OBJECT IDENTIFIER ::= { hh3cProductId 1130 }
hh3cWA4320TS                        OBJECT IDENTIFIER ::= { hh3cProductId 1131 }
hh3cWA4320TQ                        OBJECT IDENTIFIER ::= { hh3cProductId 1132 }
hh3cWA4320HACN                      OBJECT IDENTIFIER ::= { hh3cProductId 1133 }
hh3cS10506                          OBJECT IDENTIFIER ::= { hh3cProductId 1134 }
hh3cS10510                          OBJECT IDENTIFIER ::= { hh3cProductId 1135 }
hh3cS7606X                          OBJECT IDENTIFIER ::= { hh3cProductId 1136 }
hh3cS7610X                          OBJECT IDENTIFIER ::= { hh3cProductId 1137 }
hh3cMSR930AC                        OBJECT IDENTIFIER ::= { hh3cProductId 1138 }
hh3cMSR930ACWiNet                   OBJECT IDENTIFIER ::= { hh3cProductId 1139 }
hh3cSecPathACG1000E                 OBJECT IDENTIFIER ::= { hh3cProductId 1140 }
hh3cSecPathACG1000A                 OBJECT IDENTIFIER ::= { hh3cProductId 1141 }
hh3cSecPathACG1000M                 OBJECT IDENTIFIER ::= { hh3cProductId 1142 }
hh3cSecPathACG1000S                 OBJECT IDENTIFIER ::= { hh3cProductId 1143 }
hh3cSecPathACG1000C                 OBJECT IDENTIFIER ::= { hh3cProductId 1144 }
hh3cvBRAS1000                       OBJECT IDENTIFIER ::= { hh3cProductId 1145 }
hh3cVSR2000                         OBJECT IDENTIFIER ::= { hh3cProductId 1146 }
hh3cvBRAS2000                       OBJECT IDENTIFIER ::= { hh3cProductId 1147 }
hh3cS12508XAF                       OBJECT IDENTIFIER ::= { hh3cProductId 1148 }
hh3cLA3616SGM                       OBJECT IDENTIFIER ::= { hh3cProductId 1149 }
hh3cLA3616SGT                       OBJECT IDENTIFIER ::= { hh3cProductId 1150 }
hh3cLA3616EGM                       OBJECT IDENTIFIER ::= { hh3cProductId 1151 }
hh3cWAP722E                         OBJECT IDENTIFIER ::= { hh3cProductId 1152 }
hh3cWAP722                          OBJECT IDENTIFIER ::= { hh3cProductId 1153 }
hh3cER2100n                         OBJECT IDENTIFIER ::= { hh3cProductId 1154 }
hh3cER2100V2                        OBJECT IDENTIFIER ::= { hh3cProductId 1155 }
hh3cWX5560H                         OBJECT IDENTIFIER ::= { hh3cProductId 1156 }
hh3cWX5580H                         OBJECT IDENTIFIER ::= { hh3cProductId 1157 }
hh3cWAP621                          OBJECT IDENTIFIER ::= { hh3cProductId 1158 }
hh3cMSR810W                         OBJECT IDENTIFIER ::= { hh3cProductId 1159 }
hh3cER3260G2                        OBJECT IDENTIFIER ::= { hh3cProductId 1160 }
hh3cER5100G2                        OBJECT IDENTIFIER ::= { hh3cProductId 1161 }
hh3cER5200G2                        OBJECT IDENTIFIER ::= { hh3cProductId 1162 }
hh3cER6300G2                        OBJECT IDENTIFIER ::= { hh3cProductId 1163 }
hh3cER8300G2                        OBJECT IDENTIFIER ::= { hh3cProductId 1164 }
hh3cER8300G2X                       OBJECT IDENTIFIER ::= { hh3cProductId 1165 }
hh3cS99004F                         OBJECT IDENTIFIER ::= { hh3cProductId 1166 }
hh3cS990010F                        OBJECT IDENTIFIER ::= { hh3cProductId 1167 }
hh3cSecBladeLSU1ADECEA01            OBJECT IDENTIFIER ::= { hh3cProductId 1168 }
hh3cSecBladeLSXM1ADECEA1            OBJECT IDENTIFIER ::= { hh3cProductId 1169 }
hh3cS69002F                         OBJECT IDENTIFIER ::= { hh3cProductId 1170 }
hh3cS69004F                         OBJECT IDENTIFIER ::= { hh3cProductId 1171 }
hh3cS6348SF                         OBJECT IDENTIFIER ::= { hh3cProductId 1172 }
hh3cS6364F                          OBJECT IDENTIFIER ::= { hh3cProductId 1173 }
hh3cS5848F                          OBJECT IDENTIFIER ::= { hh3cProductId 1174 }
hh3cS1808G                          OBJECT IDENTIFIER ::= { hh3cProductId 1175 }
hh3cS1824G                          OBJECT IDENTIFIER ::= { hh3cProductId 1176 }
hh3cS1848G                          OBJECT IDENTIFIER ::= { hh3cProductId 1177 }
hh3cSecPathACG1010                  OBJECT IDENTIFIER ::= { hh3cProductId 1178 }
hh3cSecPathACG1020                  OBJECT IDENTIFIER ::= { hh3cProductId 1179 }
hh3cSecPathACG1030                  OBJECT IDENTIFIER ::= { hh3cProductId 1180 }
hh3cSecPathACG1040                  OBJECT IDENTIFIER ::= { hh3cProductId 1181 }
hh3cWX3510H                         OBJECT IDENTIFIER ::= { hh3cProductId 1182 }
hh3cWX3520H                         OBJECT IDENTIFIER ::= { hh3cProductId 1183 }
hh3cWX3540H                         OBJECT IDENTIFIER ::= { hh3cProductId 1184 }
hh3cWX5540H                         OBJECT IDENTIFIER ::= { hh3cProductId 1185 }
hh3cLA3608E                         OBJECT IDENTIFIER ::= { hh3cProductId 1186 }
hh3cLA3608EDB                       OBJECT IDENTIFIER ::= { hh3cProductId 1187 }
hh3cS513030SHI                      OBJECT IDENTIFIER ::= { hh3cProductId 1188 }
hh3cS513054SHI                      OBJECT IDENTIFIER ::= { hh3cProductId 1189 }
hh3cS513030CHI                      OBJECT IDENTIFIER ::= { hh3cProductId 1190 }
hh3cS513054CHI                      OBJECT IDENTIFIER ::= { hh3cProductId 1191 }
hh3cS513030CPWRHI                   OBJECT IDENTIFIER ::= { hh3cProductId 1192 }
hh3cS513054CPWRHI                   OBJECT IDENTIFIER ::= { hh3cProductId 1193 }
hh3cS513054QSHI                     OBJECT IDENTIFIER ::= { hh3cProductId 1194 }
hh3cS513030FHI                      OBJECT IDENTIFIER ::= { hh3cProductId 1195 }
hh3cS12516FAF                       OBJECT IDENTIFIER ::= { hh3cProductId 1196 }
hh3cS12508FAF                       OBJECT IDENTIFIER ::= { hh3cProductId 1197 }
hh3cS12504XAF                       OBJECT IDENTIFIER ::= { hh3cProductId 1198 }
hh3cS12504FAF                       OBJECT IDENTIFIER ::= { hh3cProductId 1199 }
hh3cMS410010TP                      OBJECT IDENTIFIER ::= { hh3cProductId 1200 }
hh3cMS410010TPPWR                   OBJECT IDENTIFIER ::= { hh3cProductId 1201 }
hh3cMS410026TP                      OBJECT IDENTIFIER ::= { hh3cProductId 1202 }
hh3cMS410026TPPWR                   OBJECT IDENTIFIER ::= { hh3cProductId 1203 }
hh3cMS430052P                       OBJECT IDENTIFIER ::= { hh3cProductId 1204 }
hh3cMS430028P                       OBJECT IDENTIFIER ::= { hh3cProductId 1205 }
hh3cIE410012TP                      OBJECT IDENTIFIER ::= { hh3cProductId 1206 }
hh3cIE410020TP                      OBJECT IDENTIFIER ::= { hh3cProductId 1207 }
hh3cIE410028F                       OBJECT IDENTIFIER ::= { hh3cProductId 1208 }
hh3cIE430028P                       OBJECT IDENTIFIER ::= { hh3cProductId 1209 }
hh3cS680054QF                       OBJECT IDENTIFIER ::= { hh3cProductId 1210 }
hh3cMS432028S                       OBJECT IDENTIFIER ::= { hh3cProductId 1211 }
hh3cMS432052S                       OBJECT IDENTIFIER ::= { hh3cProductId 1212 }
hh3cMS432028F                       OBJECT IDENTIFIER ::= { hh3cProductId 1213 }
hh3cMS432028SPWR                    OBJECT IDENTIFIER ::= { hh3cProductId 1214 }
hh3cMS452028TP                      OBJECT IDENTIFIER ::= { hh3cProductId 1215 }
hh3cMS452030F                       OBJECT IDENTIFIER ::= { hh3cProductId 1216 }
hh3cLA4310                          OBJECT IDENTIFIER ::= { hh3cProductId 1217 }
hh3cLA4310V                         OBJECT IDENTIFIER ::= { hh3cProductId 1218 }
hh3cLA4320                          OBJECT IDENTIFIER ::= { hh3cProductId 1219 }
hh3cLA4320V                         OBJECT IDENTIFIER ::= { hh3cProductId 1220 }
hh3cWA4320X                         OBJECT IDENTIFIER ::= { hh3cProductId 1221 }
hh3cLA4320X                         OBJECT IDENTIFIER ::= { hh3cProductId 1222 }
hh3cSecBlade4NSQM1FWDFG0            OBJECT IDENTIFIER ::= { hh3cProductId 1223 }
hh3cWX5510EV7                       OBJECT IDENTIFIER ::= { hh3cProductId 1224 }
hh3cWX5540EV7                       OBJECT IDENTIFIER ::= { hh3cProductId 1225 }
hh3cSecPathL1000E                   OBJECT IDENTIFIER ::= { hh3cProductId 1226 }
hh3cSecPathL1000M                   OBJECT IDENTIFIER ::= { hh3cProductId 1227 }
hh3cSecPathL1000S                   OBJECT IDENTIFIER ::= { hh3cProductId 1228 }
hh3cSecPathF5000Context             OBJECT IDENTIFIER ::= { hh3cProductId 1229 }
hh3cSecPathF1000Context             OBJECT IDENTIFIER ::= { hh3cProductId 1230 }
hh3cSecPathL5000Context             OBJECT IDENTIFIER ::= { hh3cProductId 1231 }
hh3cSecPathL1000Context             OBJECT IDENTIFIER ::= { hh3cProductId 1232 }
hh3cWA4320TQV                       OBJECT IDENTIFIER ::= { hh3cProductId 1233 }
hh3cMSR810WDB                       OBJECT IDENTIFIER ::= { hh3cProductId 1234 }
hh3cMSR810LM                        OBJECT IDENTIFIER ::= { hh3cProductId 1235 }
hh3cMSR810WLM                       OBJECT IDENTIFIER ::= { hh3cProductId 1236 }
hh3cS682032H                        OBJECT IDENTIFIER ::= { hh3cProductId 1237 }
hh3cS682054HF                       OBJECT IDENTIFIER ::= { hh3cProductId 1238 }
hh3cMSR5620                         OBJECT IDENTIFIER ::= { hh3cProductId 1239 }
hh3cMSR3620DP                       OBJECT IDENTIFIER ::= { hh3cProductId 1240 }
hh3cMSR810WWiNet                    OBJECT IDENTIFIER ::= { hh3cProductId 1241 }
hh3cMSR810LMWiNet                   OBJECT IDENTIFIER ::= { hh3cProductId 1242 }
hh3cRA100AC                         OBJECT IDENTIFIER ::= { hh3cProductId 1243 }
hh3cMSR360028WiNet                  OBJECT IDENTIFIER ::= { hh3cProductId 1244 }
hh3cMSR3620WiNet                    OBJECT IDENTIFIER ::= { hh3cProductId 1245 }
hh3cS680054QT                       OBJECT IDENTIFIER ::= { hh3cProductId 1246 }
hh3cS12504S                         OBJECT IDENTIFIER ::= { hh3cProductId 1247 }
hh3cS12506S                         OBJECT IDENTIFIER ::= { hh3cProductId 1248 }
hh3cS12510S                         OBJECT IDENTIFIER ::= { hh3cProductId 1249 }
hh3cS12508S                         OBJECT IDENTIFIER ::= { hh3cProductId 1250 }
hh3cS12512S                         OBJECT IDENTIFIER ::= { hh3cProductId 1251 }
hh3cS515024SPWREI                   OBJECT IDENTIFIER ::= { hh3cProductId 1252 }
hh3cS5150X16SEI                     OBJECT IDENTIFIER ::= { hh3cProductId 1253 }
hh3cS5150X16STEI                    OBJECT IDENTIFIER ::= { hh3cProductId 1254 }
hh3cSecPathF100AG2                  OBJECT IDENTIFIER ::= { hh3cProductId 1255 }
hh3cSecPathF1000CG2                 OBJECT IDENTIFIER ::= { hh3cProductId 1256 }
hh3cUISM831048G                     OBJECT IDENTIFIER ::= { hh3cProductId 1257 }
hh3cUISM832048XG                    OBJECT IDENTIFIER ::= { hh3cProductId 1258 }
hh3cUISM6300XLG                     OBJECT IDENTIFIER ::= { hh3cProductId 1259 }
hh3cMSR810                          OBJECT IDENTIFIER ::= { hh3cProductId 1260 }
hh3cSecPathW2001                    OBJECT IDENTIFIER ::= { hh3cProductId 1261 }
hh3cSecPathW2005                    OBJECT IDENTIFIER ::= { hh3cProductId 1262 }
hh3cSecPathW2010                    OBJECT IDENTIFIER ::= { hh3cProductId 1263 }
hh3cSecPathW2020                    OBJECT IDENTIFIER ::= { hh3cProductId 1264 }
hh3cSecPathW2040                    OBJECT IDENTIFIER ::= { hh3cProductId 1265 }
hh3cSecPathW2080                    OBJECT IDENTIFIER ::= { hh3cProductId 1266 }
hh3cSecPathW2200                    OBJECT IDENTIFIER ::= { hh3cProductId 1267 }
hh3cSecPathW1020D                   OBJECT IDENTIFIER ::= { hh3cProductId 1268 }
hh3cSecPathW1040D                   OBJECT IDENTIFIER ::= { hh3cProductId 1269 }
hh3cSecPathW1200D                   OBJECT IDENTIFIER ::= { hh3cProductId 1270 }
hh3cSecPathA2020                    OBJECT IDENTIFIER ::= { hh3cProductId 1271 }
hh3cSecPathA2100                    OBJECT IDENTIFIER ::= { hh3cProductId 1272 }
hh3cSecPathD2020                    OBJECT IDENTIFIER ::= { hh3cProductId 1273 }
hh3cSecPathD2050                    OBJECT IDENTIFIER ::= { hh3cProductId 1274 }
hh3cS556034CEI                      OBJECT IDENTIFIER ::= { hh3cProductId 1275 }
hh3cS513034CHI                      OBJECT IDENTIFIER ::= { hh3cProductId 1276 }
hh3cMS412026TP                      OBJECT IDENTIFIER ::= { hh3cProductId 1277 }
hh3cWA4330ACN                       OBJECT IDENTIFIER ::= { hh3cProductId 1278 }
hh3cMS4320S28F                      OBJECT IDENTIFIER ::= { hh3cProductId 1279 }
hh3cMS4320S28P                      OBJECT IDENTIFIER ::= { hh3cProductId 1280 }
hh3cMS452028S                       OBJECT IDENTIFIER ::= { hh3cProductId 1281 }
hh3cSecBlade3Context                OBJECT IDENTIFIER ::= { hh3cProductId 1282 }
hh3cMSR2630R                        OBJECT IDENTIFIER ::= { hh3cProductId 1283 }
hh3cMSR3610ACR                      OBJECT IDENTIFIER ::= { hh3cProductId 1284 }
hh3cMSR3620ACR                      OBJECT IDENTIFIER ::= { hh3cProductId 1285 }
hh3cMSR3640R                        OBJECT IDENTIFIER ::= { hh3cProductId 1286 }
hh3cMSR3660R                        OBJECT IDENTIFIER ::= { hh3cProductId 1287 }
hh3cMSR5660R                        OBJECT IDENTIFIER ::= { hh3cProductId 1288 }
hh3cMSR5680R                        OBJECT IDENTIFIER ::= { hh3cProductId 1289 }
hh3cMSR930R                         OBJECT IDENTIFIER ::= { hh3cProductId 1290 }
hh3cMSR930WR                        OBJECT IDENTIFIER ::= { hh3cProductId 1291 }
hh3cMSR260010R                      OBJECT IDENTIFIER ::= { hh3cProductId 1292 }
hh3cWX3010EV7                       OBJECT IDENTIFIER ::= { hh3cProductId 1293 }
hh3cWX3024EV7                       OBJECT IDENTIFIER ::= { hh3cProductId 1294 }
hh3cLSUM1WCMD0V7                    OBJECT IDENTIFIER ::= { hh3cProductId 1295 }
hh3cS556032CHI                      OBJECT IDENTIFIER ::= { hh3cProductId 1296 }
hh3cS556056CHI                      OBJECT IDENTIFIER ::= { hh3cProductId 1297 }
hh3cS556056CPWRHI                   OBJECT IDENTIFIER ::= { hh3cProductId 1298 }
hh3cS12502XAF                       OBJECT IDENTIFIER ::= { hh3cProductId 1299 }
hh3cNS228                           OBJECT IDENTIFIER ::= { hh3cProductId 1300 }
hh3cNS252                           OBJECT IDENTIFIER ::= { hh3cProductId 1301 }
hh3cSecBladeFW                      OBJECT IDENTIFIER ::= { hh3cProductId 1302 }
hh3cSecBladeADE                     OBJECT IDENTIFIER ::= { hh3cProductId 1303 }
hh3cSecBladeIIILSUM1FWCEAB0         OBJECT IDENTIFIER ::= { hh3cProductId 1304 }
hh3cS513028PSEI                     OBJECT IDENTIFIER ::= { hh3cProductId 1305 }
hh3cS7506EX                         OBJECT IDENTIFIER ::= { hh3cProductId 1306 }
hh3cS7510EX                         OBJECT IDENTIFIER ::= { hh3cProductId 1307 }
hh3cS7504EXS                        OBJECT IDENTIFIER ::= { hh3cProductId 1308 }
hh3cS7502EXS                        OBJECT IDENTIFIER ::= { hh3cProductId 1309 }
hh3cWA4320ACNPI                     OBJECT IDENTIFIER ::= { hh3cProductId 1310 }
hh3cWA4320ACNSI                     OBJECT IDENTIFIER ::= { hh3cProductId 1311 }
hh3cNER324                          OBJECT IDENTIFIER ::= { hh3cProductId 1312 }
hh3cNER214W                         OBJECT IDENTIFIER ::= { hh3cProductId 1313 }
hh3cWX2540EV7                       OBJECT IDENTIFIER ::= { hh3cProductId 1314 }
hh3cWX2540H                         OBJECT IDENTIFIER ::= { hh3cProductId 1315 }
hh3cWA4320ACNC                      OBJECT IDENTIFIER ::= { hh3cProductId 1316 }
hh3cWA4320                          OBJECT IDENTIFIER ::= { hh3cProductId 1317 }
hh3cWAP712                          OBJECT IDENTIFIER ::= { hh3cProductId 1318 }
hh3cUISM8380C                       OBJECT IDENTIFIER ::= { hh3cProductId 1319 }
hh3cUISM8380                        OBJECT IDENTIFIER ::= { hh3cProductId 1320 }
hh3cRA100E                          OBJECT IDENTIFIER ::= { hh3cProductId 1321 }
hh3cRA100EAC                        OBJECT IDENTIFIER ::= { hh3cProductId 1322 }
hh3cRA10                            OBJECT IDENTIFIER ::= { hh3cProductId 1323 }
hh3cRA10E                           OBJECT IDENTIFIER ::= { hh3cProductId 1324 }
hh3cLSU1WCME0V7                     OBJECT IDENTIFIER ::= { hh3cProductId 1325 }
hh3cEWPX1WCME0V7                    OBJECT IDENTIFIER ::= { hh3cProductId 1326 }
hh3cS556056FHI                      OBJECT IDENTIFIER ::= { hh3cProductId 1327 }
hh3cWAS120                          OBJECT IDENTIFIER ::= { hh3cProductId 1328 }
hh3cSecBlade4LSXM1FWDF1             OBJECT IDENTIFIER ::= { hh3cProductId 1329 }
hh3cSecPathvFW2000                  OBJECT IDENTIFIER ::= { hh3cProductId 1330 }
hh3cSecPathvLB2000                  OBJECT IDENTIFIER ::= { hh3cProductId 1331 }
hh3cSecBlade4S68                    OBJECT IDENTIFIER ::= { hh3cProductId 1332 }
hh3cSecPathT1020                    OBJECT IDENTIFIER ::= { hh3cProductId 1333 }
hh3cSecPathT1030                    OBJECT IDENTIFIER ::= { hh3cProductId 1334 }
hh3cSecPathT1050                    OBJECT IDENTIFIER ::= { hh3cProductId 1335 }
hh3cSecPathT1060                    OBJECT IDENTIFIER ::= { hh3cProductId 1336 }
hh3cSecPathT1080                    OBJECT IDENTIFIER ::= { hh3cProductId 1337 }
hh3cIE410012TPLI                    OBJECT IDENTIFIER ::= { hh3cProductId 1338 }
hh3cIE410012TPPWRLI                 OBJECT IDENTIFIER ::= { hh3cProductId 1339 }
hh3cSecPathACG1005                  OBJECT IDENTIFIER ::= { hh3cProductId 1340 }
hh3cSecPathACG1050                  OBJECT IDENTIFIER ::= { hh3cProductId 1341 }
hh3cSecPathACG1060                  OBJECT IDENTIFIER ::= { hh3cProductId 1342 }
hh3cSecPathACG1070                  OBJECT IDENTIFIER ::= { hh3cProductId 1343 }
hh3cSecPathACG1000B                 OBJECT IDENTIFIER ::= { hh3cProductId 1344 }
hh3cSecPathACG1000T                 OBJECT IDENTIFIER ::= { hh3cProductId 1345 }
hh3cSecPathACG1000P                 OBJECT IDENTIFIER ::= { hh3cProductId 1346 }
hh3cSecPathACG1000X                 OBJECT IDENTIFIER ::= { hh3cProductId 1347 }
hh3cSecPathT5010                    OBJECT IDENTIFIER ::= { hh3cProductId 1348 }
hh3cSecPathT5020                    OBJECT IDENTIFIER ::= { hh3cProductId 1349 }
hh3cSecPathT9006                    OBJECT IDENTIFIER ::= { hh3cProductId 1350 }
hh3cSecPathT9010                    OBJECT IDENTIFIER ::= { hh3cProductId 1351 }
hh3cSecPathT9014                    OBJECT IDENTIFIER ::= { hh3cProductId 1352 }
hh3cSecPathT9000NSQM1IPSDFG0        OBJECT IDENTIFIER ::= { hh3cProductId 1353 }
hh3cSecPathT9000NSQM1SUPC0          OBJECT IDENTIFIER ::= { hh3cProductId 1354 }
hh3cSecPathT5000Context             OBJECT IDENTIFIER ::= { hh3cProductId 1355 }
hh3cSecPathT1000Context             OBJECT IDENTIFIER ::= { hh3cProductId 1356 }
hh3cSecPathT9000Context             OBJECT IDENTIFIER ::= { hh3cProductId 1357 }

hh3cS690054QFF                      OBJECT IDENTIFIER ::= { hh3cProductId 1363 }
hh3cS690054QTF                      OBJECT IDENTIFIER ::= { hh3cProductId 1364 }
hh3cCR16004-X                       OBJECT IDENTIFIER ::= { hh3cProductId 1365 }
hh3cCR16008-X                       OBJECT IDENTIFIER ::= { hh3cProductId 1366 }
hh3cCR16016-X                       OBJECT IDENTIFIER ::= { hh3cProductId 1367 }
hh3cS5530SEID                       OBJECT IDENTIFIER ::= { hh3cProductId 1369 }
hh3cS5554SEID                       OBJECT IDENTIFIER ::= { hh3cProductId 1370 }
hh3cS5530SEIDH3                     OBJECT IDENTIFIER ::= { hh3cProductId 1371 }
hh3cS5554SEIDH3                     OBJECT IDENTIFIER ::= { hh3cProductId 1372 }
hh3cS5530CEIDH3                     OBJECT IDENTIFIER ::= { hh3cProductId 1373 }
hh3cS5554CEIDH3                     OBJECT IDENTIFIER ::= { hh3cProductId 1374 }
hh3cS5530CPWREIDH3                  OBJECT IDENTIFIER ::= { hh3cProductId 1375 }
hh3cS5554CPWREIDH3                  OBJECT IDENTIFIER ::= { hh3cProductId 1376 }
hh3cS5530FEIDH3                     OBJECT IDENTIFIER ::= { hh3cProductId 1377 }
hh3CWAP722S                         OBJECT IDENTIFIER ::= { hh3cProductId 1378 }
hh3cEWPX3WCMD0V7                    OBJECT IDENTIFIER ::= { hh3cProductId 1379 }
hh3cS5130-28S-WiNet                 OBJECT IDENTIFIER ::= { hh3cProductId 1380 }
hh3cS5130-52S-WiNet                 OBJECT IDENTIFIER ::= { hh3cProductId 1381 }
hh3cMSR810-PoE                      OBJECT IDENTIFIER ::= { hh3cProductId 1382 }
hh3cS5500-28X-WiNet                 OBJECT IDENTIFIER ::= { hh3cProductId 1383 }
hh3cS5500-52X-WiNet                 OBJECT IDENTIFIER ::= { hh3cProductId 1384 }
hh3cS3208-8P-OLT                    OBJECT IDENTIFIER ::= { hh3cProductId 1385 }
hh3cS3208-4P-OLT                    OBJECT IDENTIFIER ::= { hh3cProductId 1386 }
hh3cLA6608                          OBJECT IDENTIFIER ::= { hh3cProductId 1387 }
hh3cLA6616                          OBJECT IDENTIFIER ::= { hh3cProductId 1388 }
hh3cSecBlade4LSUM1FWDEC0            OBJECT IDENTIFIER ::= { hh3cProductId 1389 }
hh3cSecBlade4LSUM1NSDEC0            OBJECT IDENTIFIER ::= { hh3cProductId 1390 }
hh3cSecBlade4LSQM1FWDSC0            OBJECT IDENTIFIER ::= { hh3cProductId 1391 }
hh3cSecBlade4LSQM1NSDSC0            OBJECT IDENTIFIER ::= { hh3cProductId 1392 }
hh3cSecBlade4LSXM1NSDF1             OBJECT IDENTIFIER ::= { hh3cProductId 1393 }
hh3cS12512X-AF                      OBJECT IDENTIFIER ::= { hh3cProductId 1394 }
hh3cS6800-54HF                      OBJECT IDENTIFIER ::= { hh3cProductId 1395 }
hh3cS6800-54HT                      OBJECT IDENTIFIER ::= { hh3cProductId 1396 }
hh3cSecPathT9000-NSQM1IPSDFG0       OBJECT IDENTIFIER ::= { hh3cProductId 1397 }
hh3cSecPathF1010                    OBJECT IDENTIFIER ::= { hh3cProductId 1398 }
hh3cSecPathF1005                    OBJECT IDENTIFIER ::= { hh3cProductId 1399 }
hh3cSecPathF100-S-G2                OBJECT IDENTIFIER ::= { hh3cProductId 1400 }
hh3cSecPathF100-M-G2                OBJECT IDENTIFIER ::= { hh3cProductId 1401 }
hh3cSecPathF100-C-G2                OBJECT IDENTIFIER ::= { hh3cProductId 1402 }
hh3cWAC350                          OBJECT IDENTIFIER ::= { hh3cProductId 1403 }
hh3cWA4320-ACN-E                    OBJECT IDENTIFIER ::= { hh3cProductId 1404 }
hh3cWAP712C                         OBJECT IDENTIFIER ::= { hh3cProductId 1405 }
hh3cSecPathS10500Context            OBJECT IDENTIFIER ::= { hh3cProductId 1406 }
hh3cSecPathS7500EContext            OBJECT IDENTIFIER ::= { hh3cProductId 1407 }
hh3cWX2560H                         OBJECT IDENTIFIER ::= { hh3cProductId 1408 }
hh3cWX2560H-C                       OBJECT IDENTIFIER ::= { hh3cProductId 1409 }
hh3cMSG360-10                       OBJECT IDENTIFIER ::= { hh3cProductId 1410 }
hh3cMSG360-20                       OBJECT IDENTIFIER ::= { hh3cProductId 1411 }
hh3cMSG360-20N                      OBJECT IDENTIFIER ::= { hh3cProductId 1412 }
hh3cWX2510H                         OBJECT IDENTIFIER ::= { hh3cProductId 1413 }
hh3cWX2510H-F                       OBJECT IDENTIFIER ::= { hh3cProductId 1414 }
hh3cWX2540H-F                       OBJECT IDENTIFIER ::= { hh3cProductId 1415 }
hh3cSecBlade4LSPM6FWD               OBJECT IDENTIFIER ::= { hh3cProductId 1416 }
hh3cS6820-56HF                      OBJECT IDENTIFIER ::= { hh3cProductId 1417 }
hh3cS6820-4C                        OBJECT IDENTIFIER ::= { hh3cProductId 1418 }
hh3cS6890                           OBJECT IDENTIFIER ::= { hh3cProductId 1419 }
hh3cSecPathACG1000-AK110            OBJECT IDENTIFIER ::= { hh3cProductId 1420 }
hh3cSecPathACG1000-AK120            OBJECT IDENTIFIER ::= { hh3cProductId 1421 }
hh3cSecPathACG1000-AK130            OBJECT IDENTIFIER ::= { hh3cProductId 1422 }
hh3cSecPathACG1000-AK140            OBJECT IDENTIFIER ::= { hh3cProductId 1423 }
hh3cSecPathACG1000-AK150            OBJECT IDENTIFIER ::= { hh3cProductId 1424 }
hh3cSecPathACG1000-AK160            OBJECT IDENTIFIER ::= { hh3cProductId 1425 }
hh3cSecPathACG1000-AK170            OBJECT IDENTIFIER ::= { hh3cProductId 1426 }
hh3cSecPathACG1000-AK180            OBJECT IDENTIFIER ::= { hh3cProductId 1427 }
hh3cSecPathACG1000-BE-PWR           OBJECT IDENTIFIER ::= { hh3cProductId 1428 }
hh3cSecPathACG1000-SE-PWR           OBJECT IDENTIFIER ::= { hh3cProductId 1429 }
hh3cSecPathACG1005-PWR              OBJECT IDENTIFIER ::= { hh3cProductId 1430 }
hh3cSecBlade3FWContext              OBJECT IDENTIFIER ::= { hh3cProductId 1431 }
hh3cMINI-S26G                       OBJECT IDENTIFIER ::= { hh3cProductId 1432 }
hh3cMINI-S26                        OBJECT IDENTIFIER ::= { hh3cProductId 1433 }
hh3cMINI-S9G                        OBJECT IDENTIFIER ::= { hh3cProductId 1434 }
hh3cF100-C-EI                       OBJECT IDENTIFIER ::= { hh3cProductId 1435 }
hh3cF1000-AK110                     OBJECT IDENTIFIER ::= { hh3cProductId 1436 }
hh3cF1000-AK120                     OBJECT IDENTIFIER ::= { hh3cProductId 1437 }
hh3cF1000-AK130                     OBJECT IDENTIFIER ::= { hh3cProductId 1438 }
hh3cF1000-AK140                     OBJECT IDENTIFIER ::= { hh3cProductId 1439 }
hh3cF1000-AK150                     OBJECT IDENTIFIER ::= { hh3cProductId 1440 }
hh3cF1000-AK160                     OBJECT IDENTIFIER ::= { hh3cProductId 1441 }
hh3cF1000-AK170                     OBJECT IDENTIFIER ::= { hh3cProductId 1442 }
hh3cF1000-AK180                     OBJECT IDENTIFIER ::= { hh3cProductId 1443 }
hh3cF100-A-EI                       OBJECT IDENTIFIER ::= { hh3cProductId 1444 }
hh3cF100-E-G2                       OBJECT IDENTIFIER ::= { hh3cProductId 1445 }
hh3cF100-E-EI                       OBJECT IDENTIFIER ::= { hh3cProductId 1446 }
hh3cF1000-S-G2                      OBJECT IDENTIFIER ::= { hh3cProductId 1447 }
hh3cF1000-A-G2                      OBJECT IDENTIFIER ::= { hh3cProductId 1448 }
hh3cF1000-E-G2                      OBJECT IDENTIFIER ::= { hh3cProductId 1449 }
hh3cS5120-9P-WiNet                  OBJECT IDENTIFIER ::= { hh3cProductId 1450 }
hh3cS5120-9P-HPOE-WiNet             OBJECT IDENTIFIER ::= { hh3cProductId 1451 }
hh3cS5120-28P-HPOE-WiNet            OBJECT IDENTIFIER ::= { hh3cProductId 1452 }
hh3cS5130-28F-WiNet                 OBJECT IDENTIFIER ::= { hh3cProductId 1453 }
hh3cS5500V2-24P-WiNet               OBJECT IDENTIFIER ::= { hh3cProductId 1454 }
hh3cS5500V2-48P-WiNet               OBJECT IDENTIFIER ::= { hh3cProductId 1455 }
hh3cS5500V2-28F-WiNet               OBJECT IDENTIFIER ::= { hh3cProductId 1456 }
hh3cS5500V2-24P-SI                  OBJECT IDENTIFIER ::= { hh3cProductId 1457 }
hh3cS5500V2-28F-SI                  OBJECT IDENTIFIER ::= { hh3cProductId 1458 }
hh3cS5500V2-48P-SI                  OBJECT IDENTIFIER ::= { hh3cProductId 1459 }
hh3cS5560X-30C-EI                   OBJECT IDENTIFIER ::= { hh3cProductId 1460 }
hh3cS5560X-54C-EI                   OBJECT IDENTIFIER ::= { hh3cProductId 1461 }
hh3cS5560X-30C-PWR-EI               OBJECT IDENTIFIER ::= { hh3cProductId 1462 }
hh3cS5560X-54C-PWR-EI               OBJECT IDENTIFIER ::= { hh3cProductId 1463 }
hh3cS5130-54C-PWR-HI-H3             OBJECT IDENTIFIER ::= { hh3cProductId 1464 }
hh3cS5560-38C-HI-XG                 OBJECT IDENTIFIER ::= { hh3cProductId 1465 }
hh3cS5110-28P-PWR-E                 OBJECT IDENTIFIER ::= { hh3cProductId 1466 }
hh3cS5110-52P-PWR-E                 OBJECT IDENTIFIER ::= { hh3cProductId 1467 }
hh3cWX3010H-L                       OBJECT IDENTIFIER ::= { hh3cProductId 1468 }
hh3cWX3024H-L                       OBJECT IDENTIFIER ::= { hh3cProductId 1469 }
hh3cSecPathF5010-NSQZ1F5010         OBJECT IDENTIFIER ::= { hh3cProductId 1470 }
hh3cMSR2600-10-X1                   OBJECT IDENTIFIER ::= { hh3cProductId 1471 }
hh3cMSR3610-X1                      OBJECT IDENTIFIER ::= { hh3cProductId 1472 }
hh3cMSR3610-X1-DP                   OBJECT IDENTIFIER ::= { hh3cProductId 1473 }
hh3cMSR3610-X1-DP-DC                OBJECT IDENTIFIER ::= { hh3cProductId 1474 }
hh3cSecBlade4-LSPM6FWD              OBJECT IDENTIFIER ::= { hh3cProductId 1475 }
hh3cMSR3600-28-SI                   OBJECT IDENTIFIER ::= { hh3cProductId 1476 }
hh3cMSR3600-51-SI                   OBJECT IDENTIFIER ::= { hh3cProductId 1477 }
hh3cMSR3600-51F                     OBJECT IDENTIFIER ::= { hh3cProductId 1478 }
hh3cLSQM1WCMX40                     OBJECT IDENTIFIER ::= { hh3cProductId 1479 }
hh3cLSUM1WCMX40RT                   OBJECT IDENTIFIER ::= { hh3cProductId 1480 }
hh3cLSQM1WCMX20                     OBJECT IDENTIFIER ::= { hh3cProductId 1481 }
hh3cLSUM1WCMX20RT                   OBJECT IDENTIFIER ::= { hh3cProductId 1482 }
hh3cICG3000F                        OBJECT IDENTIFIER ::= { hh3cProductId 1483 }
hh3cICG3000F-DP                     OBJECT IDENTIFIER ::= { hh3cProductId 1484 }
hh3cICG5000G                        OBJECT IDENTIFIER ::= { hh3cProductId 1485 }
hh3cMSR830-6EI-WiNet                OBJECT IDENTIFIER ::= { hh3cProductId 1486 }
hh3cMSR830-5BEI-WiNet               OBJECT IDENTIFIER ::= { hh3cProductId 1487 }
hh3cMSR830-10BEI-WiNet              OBJECT IDENTIFIER ::= { hh3cProductId 1488 }
hh3cMSR830-6BHI-WiNet               OBJECT IDENTIFIER ::= { hh3cProductId 1489 }
hh3cMSR830-10BHI-WiNet              OBJECT IDENTIFIER ::= { hh3cProductId 1490 }
hh3cS6520-52QF-EI                   OBJECT IDENTIFIER ::= { hh3cProductId 1491 }
hh3cMSR3610-X1-DC                   OBJECT IDENTIFIER ::= { hh3cProductId 1492 }
hh3cWX3010H-X                       OBJECT IDENTIFIER ::= { hh3cProductId 1493 }
hh3cEWPXM2WCMD0F                    OBJECT IDENTIFIER ::= { hh3cProductId 1494 }
hh3cUIS-M8381                       OBJECT IDENTIFIER ::= { hh3cProductId 1495 }
hh3cUIS-M8381-C                     OBJECT IDENTIFIER ::= { hh3cProductId 1496 }
hh3cMSR810-LM-HK                    OBJECT IDENTIFIER ::= { hh3cProductId 1497 }
hh3cMSR810-W-LM-HK                  OBJECT IDENTIFIER ::= { hh3cProductId 1498 }
hh3cWA4320-ACN-D                    OBJECT IDENTIFIER ::= { hh3cProductId 1499 }
hh3cWA2620E-D                       OBJECT IDENTIFIER ::= { hh3cProductId 1500 }
hh3cWA4320H                         OBJECT IDENTIFIER ::= { hh3cProductId 1501 }
hh3cWA2610H                         OBJECT IDENTIFIER ::= { hh3cProductId 1502 }
hh3cS10508X                         OBJECT IDENTIFIER ::= { hh3cProductId 1503 }
hh3cS7503E-M                        OBJECT IDENTIFIER ::= { hh3cProductId 1504 }
hh3cSecblade-IV-FW-context          OBJECT IDENTIFIER ::= { hh3cProductId 1505 }
hh3cSecPathS6800-LSWM1FWD0-Context  OBJECT IDENTIFIER ::= { hh3cProductId 1506 }
hh3cS6520-42QF-EI                   OBJECT IDENTIFIER ::= { hh3cProductId 1507 }
hh3cS6520-48S-EI                    OBJECT IDENTIFIER ::= { hh3cProductId 1508 }
hh3cWT1020                          OBJECT IDENTIFIER ::= { hh3cProductId 1509 }
hh3cWT1010                          OBJECT IDENTIFIER ::= { hh3cProductId 1510 }
hh3cWT1004                          OBJECT IDENTIFIER ::= { hh3cProductId 1511 }
hh3cS5016PV2-EI                     OBJECT IDENTIFIER ::= { hh3cProductId 1512 }
hh3cWX3510H-F                       OBJECT IDENTIFIER ::= { hh3cProductId 1513 }
hh3cWX3520H-F                       OBJECT IDENTIFIER ::= { hh3cProductId 1514 }
hh3cEWPXM1MAC0F                     OBJECT IDENTIFIER ::= { hh3cProductId 1515 }
hh3cS68-ADE-LSWM1ADED0              OBJECT IDENTIFIER ::= { hh3cProductId 1516 }
hh3cS68-ADE-Context                 OBJECT IDENTIFIER ::= { hh3cProductId 1517 }
hh3cS68-IPS-LSWM1IPSD0              OBJECT IDENTIFIER ::= { hh3cProductId 1518 }
hh3cS68-IPS-Context                 OBJECT IDENTIFIER ::= { hh3cProductId 1519 }
hh3cS12508XS-AF                     OBJECT IDENTIFIER ::= { hh3cProductId 1520 }
hh3cS12508M-AF                      OBJECT IDENTIFIER ::= { hh3cProductId 1521 }
hh3cS5830X-54S                      OBJECT IDENTIFIER ::= { hh3cProductId 1522 }
hh3cS5560X-30F-EI                   OBJECT IDENTIFIER ::= { hh3cProductId 1523 }
hh3cS5560X-54F-EI                   OBJECT IDENTIFIER ::= { hh3cProductId 1524 }
hh3cSecPathGAP2000-B                OBJECT IDENTIFIER ::= { hh3cProductId 1525 }
hh3cSecPathGAP2000-S                OBJECT IDENTIFIER ::= { hh3cProductId 1526 }
hh3cSecPathGAP2000-A                OBJECT IDENTIFIER ::= { hh3cProductId 1527 }
hh3cSPM-X1-10                       OBJECT IDENTIFIER ::= { hh3cProductId 1528 }
hh3cSPM-X1-24                       OBJECT IDENTIFIER ::= { hh3cProductId 1529 }
hh3cWAC380-60                       OBJECT IDENTIFIER ::= { hh3cProductId 1530 }
hh3cWAC380-90                       OBJECT IDENTIFIER ::= { hh3cProductId 1531 }
hh3cWAC380-120                      OBJECT IDENTIFIER ::= { hh3cProductId 1532 }
hh3cMSG360-40                       OBJECT IDENTIFIER ::= { hh3cProductId 1533 }
hh3cS7003E                          OBJECT IDENTIFIER ::= { hh3cProductId 1534 }
hh3cS6800-54QF                      OBJECT IDENTIFIER ::= { hh3cProductId 1535 }
hh3cvLNS1000                        OBJECT IDENTIFIER ::= { hh3cProductId 1536 }
hh3cvLNS2000                        OBJECT IDENTIFIER ::= { hh3cProductId 1537 }
hh3cS6900-54HF-F                    OBJECT IDENTIFIER ::= { hh3cProductId 1538 }
hh3cSR88-SR0M1FWDFG0-SecBlade-IV-FW OBJECT IDENTIFIER ::= { hh3cProductId 1539 }
hh3cSecPathSR88ContextModule        OBJECT IDENTIFIER ::= { hh3cProductId 1540 }
hh3cWT1024-X                        OBJECT IDENTIFIER ::= { hh3cProductId 1541 }
hh3cWX3024H                         OBJECT IDENTIFIER ::= { hh3cProductId 1542 }
hh3cWX3010H                         OBJECT IDENTIFIER ::= { hh3cProductId 1543 }
hh3cACG1000-Blade-E                 OBJECT IDENTIFIER ::= { hh3cProductId 1544 }
hh3cACG1000-Blade-X                 OBJECT IDENTIFIER ::= { hh3cProductId 1545 }
hh3cS7603                           OBJECT IDENTIFIER ::= { hh3cProductId 1546 }
hh3cS7606                           OBJECT IDENTIFIER ::= { hh3cProductId 1547 }
hh3cS7610                           OBJECT IDENTIFIER ::= { hh3cProductId 1548 }
hh3cMSR830-10PBEI-WiNet             OBJECT IDENTIFIER ::= { hh3cProductId 1549 }
hh3cIE4300-12P                      OBJECT IDENTIFIER ::= { hh3cProductId 1550 }
hh3cIE4300-6P                       OBJECT IDENTIFIER ::= { hh3cProductId 1551 }
hh3cIE4300-8P-2S                    OBJECT IDENTIFIER ::= { hh3cProductId 1552 }
hh3cMSR810-LUS                      OBJECT IDENTIFIER ::= { hh3cProductId 1553 }
hh3cSecPath-ACG1000-BE              OBJECT IDENTIFIER ::= { hh3cProductId 1554 }
hh3cSecPath-ACG1000-SE              OBJECT IDENTIFIER ::= { hh3cProductId 1555 }
hh3cSecPath-F5080                   OBJECT IDENTIFIER ::= { hh3cProductId 1556 }
hh3cSecPath-F5060                   OBJECT IDENTIFIER ::= { hh3cProductId 1557 }
hh3cSecPath-F5030                   OBJECT IDENTIFIER ::= { hh3cProductId 1558 }
hh3cSecPath-F50X0-Context           OBJECT IDENTIFIER ::= { hh3cProductId 1559 }
hh3cS7503X                          OBJECT IDENTIFIER ::= { hh3cProductId 1560 }
hh3cS7506X                          OBJECT IDENTIFIER ::= { hh3cProductId 1561 }
hh3cS7510X                          OBJECT IDENTIFIER ::= { hh3cProductId 1562 }
hh3cSecPath-F100-C80-WiNet          OBJECT IDENTIFIER ::= { hh3cProductId 1563 }
hh3cSecPath-F100-C60-WiNet          OBJECT IDENTIFIER ::= { hh3cProductId 1564 }
hh3cSecPath-F1000-AK109             OBJECT IDENTIFIER ::= { hh3cProductId 1565 }
hh3cSecPath-F1000-AK108             OBJECT IDENTIFIER ::= { hh3cProductId 1566 }
hh3cS5130S-28P-PWR-EI               OBJECT IDENTIFIER ::= { hh3cProductId 1567 }
hh3cS5130S-28P-HPWR-EI              OBJECT IDENTIFIER ::= { hh3cProductId 1568 }
hh3cS5130S-28S-PWR-HI               OBJECT IDENTIFIER ::= { hh3cProductId 1569 }
hh3cS5130S-28S-PWR-EI               OBJECT IDENTIFIER ::= { hh3cProductId 1570 }
hh3cS5130S-28S-HPWR-EI              OBJECT IDENTIFIER ::= { hh3cProductId 1571 }
hh3cS5130S-52P-PWR-EI               OBJECT IDENTIFIER ::= { hh3cProductId 1572 }
hh3cS5130S-52S-PWR-EI               OBJECT IDENTIFIER ::= { hh3cProductId 1573 }
hh3cS5130S-52S-PWR-HI               OBJECT IDENTIFIER ::= { hh3cProductId 1574 }
hh3cS5130-54C-PWR-HI                OBJECT IDENTIFIER ::= { hh3cProductId 1575 }
hh3cS5130S-52F-EI                   OBJECT IDENTIFIER ::= { hh3cProductId 1576 }
hh3cSR8816-X                        OBJECT IDENTIFIER ::= { hh3cProductId 1577 }
hh3cCR16018-F                       OBJECT IDENTIFIER ::= { hh3cProductId 1578 }
hh3cMSR810-LMS                      OBJECT IDENTIFIER ::= { hh3cProductId 1579 }
hh3cM9008-S                         OBJECT IDENTIFIER ::= { hh3cProductId 1580 }
hh3cSecPathM9000-NSQM2FWDSC0-Context  OBJECT IDENTIFIER ::= { hh3cProductId 1581 }
hh3cNS316X                          OBJECT IDENTIFIER ::= { hh3cProductId 1582 }
hh3cMSG360-4                        OBJECT IDENTIFIER ::= { hh3cProductId 1583 }
hh3cMSG360-4-PWR                    OBJECT IDENTIFIER ::= { hh3cProductId 1584 }
hh3cS5130S-28S-EI                   OBJECT IDENTIFIER ::= { hh3cProductId 1585 }
hh3cS5130S-52S-EI                   OBJECT IDENTIFIER ::= { hh3cProductId 1586 }
hh3cS5130S-28P-EI                   OBJECT IDENTIFIER ::= { hh3cProductId 1587 }
hh3cS5130S-52P-EI                   OBJECT IDENTIFIER ::= { hh3cProductId 1588 }
hh3cS5130S-28S-HI                   OBJECT IDENTIFIER ::= { hh3cProductId 1589 }
hh3cS5130S-52S-HI                   OBJECT IDENTIFIER ::= { hh3cProductId 1590 }
hh3cS6920-32H-F                     OBJECT IDENTIFIER ::= { hh3cProductId 1591 }
hh3cS6920-4F                        OBJECT IDENTIFIER ::= { hh3cProductId 1592 }
hh3cS7006E                          OBJECT IDENTIFIER ::= { hh3cProductId 1593 }
hh3cSecPath-L1000-GL                OBJECT IDENTIFIER ::= { hh3cProductId 1594 }
hh3cWX3024H-F                       OBJECT IDENTIFIER ::= { hh3cProductId 1595 }
hh3cHS526X-S                        OBJECT IDENTIFIER ::= { hh3cProductId 1596 }
hh3cHS552X-S                        OBJECT IDENTIFIER ::= { hh3cProductId 1597 }
hh3cHS552X-E                        OBJECT IDENTIFIER ::= { hh3cProductId 1598 }
hh3cHS616X-E                        OBJECT IDENTIFIER ::= { hh3cProductId 1599 }
hh3cS12508XC-AF                     OBJECT IDENTIFIER ::= { hh3cProductId 1600 }
hh3cSecPathM9000-S-NSQM2FWDSCA0-Context                    OBJECT IDENTIFIER ::= { hh3cProductId 1601 }
hh3cSecPath-M9000-NSQM1TGS32QSSG0                          OBJECT IDENTIFIER ::= { hh3cProductId 1602 }
hh3cSecPath-S75E-S10500-LSQM1IPSDSC0-SecBlade-Context      OBJECT IDENTIFIER ::= { hh3cProductId 1603 }
hh3cSecPath-S75E-S10500-LSQM2ACGDSC0-SecBlade-IV-Context   OBJECT IDENTIFIER ::= { hh3cProductId 1604 }
hh3cSecPath-S75E-S10500-LSQM1ADEDSC0-SecBlade-IV-Context   OBJECT IDENTIFIER ::= { hh3cProductId 1605 }
hh3cSecPath-SR8800-X-IM-IPSX-IV-SecBlade-IV-Context        OBJECT IDENTIFIER ::= { hh3cProductId 1606 }
hh3cSecPath-SR8800-X-IM-ACGX-IV-SecBlade-IV-Context        OBJECT IDENTIFIER ::= { hh3cProductId 1607 }
hh3cS75E-S10500-SecBlade-IV-IPS                            OBJECT IDENTIFIER ::= { hh3cProductId 1608 }
hh3cS75E-S10500-SecBlade-IV-ADE                            OBJECT IDENTIFIER ::= { hh3cProductId 1609 }
hh3cS75E-S10500-SecBlade-IV-ACG                            OBJECT IDENTIFIER ::= { hh3cProductId 1610 }
hh3cSR8800-X-SecBlade-IV-IPS                               OBJECT IDENTIFIER ::= { hh3cProductId 1611 }
hh3cSR8800-X-SecBlade-IV-ACG                               OBJECT IDENTIFIER ::= { hh3cProductId 1612 }
hh3cACG1000-Blade-X-SR88                                   OBJECT IDENTIFIER ::= { hh3cProductId 1613 }
hh3cS1850-10P                       OBJECT IDENTIFIER ::= { hh3cProductId 1614 }
hh3cS1850-28P                       OBJECT IDENTIFIER ::= { hh3cProductId 1615 }
hh3cS1850-52P                       OBJECT IDENTIFIER ::= { hh3cProductId 1616 }
hh3cS1850-28P-PWR                   OBJECT IDENTIFIER ::= { hh3cProductId 1617 }
hh3cS2626-HPWR                      OBJECT IDENTIFIER ::= { hh3cProductId 1618 }
hh3cSecBlade-IV-ADE-Context         OBJECT IDENTIFIER ::= { hh3cProductId 1619 }
hh3cS6800-2C-FC                     OBJECT IDENTIFIER ::= { hh3cProductId 1620 }
hh3cSecPath-W2000-V                 OBJECT IDENTIFIER ::= { hh3cProductId 1621 }
hh3cSecPath-A2000-V                 OBJECT IDENTIFIER ::= { hh3cProductId 1622 }
hh3cNSQM1TG8A                       OBJECT IDENTIFIER ::= { hh3cProductId 1623 }
hh3cNSQM1QG2A                       OBJECT IDENTIFIER ::= { hh3cProductId 1624 }
hh3cNSQM1GT8A                       OBJECT IDENTIFIER ::= { hh3cProductId 1625 }
hh3cNSQM1GP8A                       OBJECT IDENTIFIER ::= { hh3cProductId 1626 }
hh3cNSQM1GT4PFCA                    OBJECT IDENTIFIER ::= { hh3cProductId 1627 }
hh3cS5560X-34S-EI                   OBJECT IDENTIFIER ::= { hh3cProductId 1628 }
hh3cS5560X-54S-EI                   OBJECT IDENTIFIER ::= { hh3cProductId 1629 }
hh3cS5500V2-34S-EI                  OBJECT IDENTIFIER ::= { hh3cProductId 1630 }
hh3cS5500V2-54S-EI                  OBJECT IDENTIFIER ::= { hh3cProductId 1631 }
hh3cS5500V2-30F-EI                  OBJECT IDENTIFIER ::= { hh3cProductId 1632 }
hh3cWP2024S                         OBJECT IDENTIFIER ::= { hh3cProductId 1633 }
hh3cWP5024S                         OBJECT IDENTIFIER ::= { hh3cProductId 1634 }
hh3cWP2008S                         OBJECT IDENTIFIER ::= { hh3cProductId 1635 }
hh3cWP5008S                         OBJECT IDENTIFIER ::= { hh3cProductId 1636 }
hh3cS3100V3-10TP-EI                 OBJECT IDENTIFIER ::= { hh3cProductId 1637 }
hh3cS3100V3-10TP-PWR-EI             OBJECT IDENTIFIER ::= { hh3cProductId 1638 }
hh3cS5130S-10P-EI                   OBJECT IDENTIFIER ::= { hh3cProductId 1639 }
hh3cS5130S-10P-HPWR-EI              OBJECT IDENTIFIER ::= { hh3cProductId 1640 }
hh3cCR19000-20                      OBJECT IDENTIFIER ::= { hh3cProductId 1641 }
hh3cCR19000-MC                      OBJECT IDENTIFIER ::= { hh3cProductId 1642 }
hh3cSR8808H-X                       OBJECT IDENTIFIER ::= { hh3cProductId 1643 }
hh3cCR16010H-F                      OBJECT IDENTIFIER ::= { hh3cProductId 1644 }
hh3cS3100V3-18TP-EI                 OBJECT IDENTIFIER ::= { hh3cProductId 1645 }
hh3cS3100V3-28TP-EI                 OBJECT IDENTIFIER ::= { hh3cProductId 1646 }
hh3cS3100V3-52TP-EI                 OBJECT IDENTIFIER ::= { hh3cProductId 1647 }
hh3cS3100V3-20TP-PWR-EI             OBJECT IDENTIFIER ::= { hh3cProductId 1648 }
hh3cS3100V3-28TP-PWR-EI             OBJECT IDENTIFIER ::= { hh3cProductId 1649 }
hh3cS5130S-12TP-EI                  OBJECT IDENTIFIER ::= { hh3cProductId 1650 }
hh3cS5130S-20P-EI                   OBJECT IDENTIFIER ::= { hh3cProductId 1651 }
hh3cS5130S-12TP-HPWR-EI             OBJECT IDENTIFIER ::= { hh3cProductId 1652 }
hh3cS5130S-20P-PWR-EI               OBJECT IDENTIFIER ::= { hh3cProductId 1653 }
hh3cS5528S-EI-D                     OBJECT IDENTIFIER ::= { hh3cProductId 1654 }
hh3cS5552S-EI-D                     OBJECT IDENTIFIER ::= { hh3cProductId 1655 }
hh3cS5528P-EI-D                     OBJECT IDENTIFIER ::= { hh3cProductId 1656 }
hh3cS5552P-EI-D                     OBJECT IDENTIFIER ::= { hh3cProductId 1657 }
hh3cS5528P-PWR-EI-D                 OBJECT IDENTIFIER ::= { hh3cProductId 1658 }
hh3cS5552P-PWR-EI-D                 OBJECT IDENTIFIER ::= { hh3cProductId 1659 }
hh3cWX1804H-PWR                     OBJECT IDENTIFIER ::= { hh3cProductId 1660 }
hh3cS10508X-V                       OBJECT IDENTIFIER ::= { hh3cProductId 1661 }
hh3cSecPath-F1000                   OBJECT IDENTIFIER ::= { hh3cProductId 1662 }
hh3cSecPath-L1000                   OBJECT IDENTIFIER ::= { hh3cProductId 1663 }
hh3cSecPath-T1000                   OBJECT IDENTIFIER ::= { hh3cProductId 1664 }
hh3cSecPath-F5000                   OBJECT IDENTIFIER ::= { hh3cProductId 1665 }
hh3cSecPath-L5000                   OBJECT IDENTIFIER ::= { hh3cProductId 1666 }
hh3cSecPath-T5000                   OBJECT IDENTIFIER ::= { hh3cProductId 1667 }
hh3cSecPath-M9000                   OBJECT IDENTIFIER ::= { hh3cProductId 1668 }
hh3cSecPath-T9000                   OBJECT IDENTIFIER ::= { hh3cProductId 1669 }
hh3cSecBlade-Security-Module        OBJECT IDENTIFIER ::= { hh3cProductId 1670 }
hh3cMSG360-10-PWR                   OBJECT IDENTIFIER ::= { hh3cProductId 1671 }
hh3cWX1810H-PWR                     OBJECT IDENTIFIER ::= { hh3cProductId 1672 }
hh3cWA5530                          OBJECT IDENTIFIER ::= { hh3cProductId 1673 }
hh3cWX3508H                         OBJECT IDENTIFIER ::= { hh3cProductId 1674 }
hh3cWX1820H                         OBJECT IDENTIFIER ::= { hh3cProductId 1675 }
hh3cWT2024-U                        OBJECT IDENTIFIER ::= { hh3cProductId 1676 }
hh3cWT1010-QU                       OBJECT IDENTIFIER ::= { hh3cProductId 1677 }
hh3cS5120V2-28P-SI                  OBJECT IDENTIFIER ::= { hh3cProductId 1678 }
hh3cS5120V2-52P-SI                  OBJECT IDENTIFIER ::= { hh3cProductId 1679 }
hh3cS5120V2-28P-LI                  OBJECT IDENTIFIER ::= { hh3cProductId 1680 }
hh3cS5120V2-28P-PWR-LI              OBJECT IDENTIFIER ::= { hh3cProductId 1681 }
hh3cS5120V2-28P-HPWR-LI             OBJECT IDENTIFIER ::= { hh3cProductId 1682 }
hh3cS5120V2-52P-LI                  OBJECT IDENTIFIER ::= { hh3cProductId 1683 }
hh3cS5120V2-52P-PWR-LI              OBJECT IDENTIFIER ::= { hh3cProductId 1684 }
hh3cMS4320S-28P-PWR                 OBJECT IDENTIFIER ::= { hh3cProductId 1685 }
hh3cS5120V2-10P-PWR-LI              OBJECT IDENTIFIER ::= { hh3cProductId 1686 }
hh3cS5120V2-20P-LI                  OBJECT IDENTIFIER ::= { hh3cProductId 1687 }
hh3cS5120V2-10P-LI                  OBJECT IDENTIFIER ::= { hh3cProductId 1688 }
hh3cMS4320S-20P-PWR                 OBJECT IDENTIFIER ::= { hh3cProductId 1689 }
hh3cS5120V2-10P-SI                  OBJECT IDENTIFIER ::= { hh3cProductId 1690 }
hh3cS5130S-28S-LI                   OBJECT IDENTIFIER ::= { hh3cProductId 1691 }
hh3cS5130S-52S-LI                   OBJECT IDENTIFIER ::= { hh3cProductId 1692 }
hh3cS5128S-EI-D                     OBJECT IDENTIFIER ::= { hh3cProductId 1693 }
hh3cS5152S-EI-D                     OBJECT IDENTIFIER ::= { hh3cProductId 1694 }
hh3cS5128P-EI-D                     OBJECT IDENTIFIER ::= { hh3cProductId 1695 }
hh3cS5152P-EI-D                     OBJECT IDENTIFIER ::= { hh3cProductId 1696 }
hh3cS5128P-PWR-EI-D                 OBJECT IDENTIFIER ::= { hh3cProductId 1697 }
hh3cS5152P-PWR-EI-D                 OBJECT IDENTIFIER ::= { hh3cProductId 1698 }
hh3cS5110P-EI-D                     OBJECT IDENTIFIER ::= { hh3cProductId 1699 }
hh3cS5110P-PWR-EI-D                 OBJECT IDENTIFIER ::= { hh3cProductId 1700 }
hh3cMSR3610-X1-WiNet                OBJECT IDENTIFIER ::= { hh3cProductId 1701 }
hh3cMSR3620-DP-WiNet                OBJECT IDENTIFIER ::= { hh3cProductId 1702 }
hh3cMSR2600-10-X1-WiNet             OBJECT IDENTIFIER ::= { hh3cProductId 1703 }
hh3cWT1024-X-EI                     OBJECT IDENTIFIER ::= { hh3cProductId 1704 }
hh3cWT1010-EI                       OBJECT IDENTIFIER ::= { hh3cProductId 1705 }
hh3cER3100G2                        OBJECT IDENTIFIER ::= { hh3cProductId 1706 }
hh3cER3200G2                        OBJECT IDENTIFIER ::= { hh3cProductId 1707 }
hh3cS6520XE-54QC-HI                 OBJECT IDENTIFIER ::= { hh3cProductId 1708 }
hh3cS6520XE-54HC-HI                 OBJECT IDENTIFIER ::= { hh3cProductId 1709 }
hh3cS10516X                         OBJECT IDENTIFIER ::= { hh3cProductId 1710 }
hh3cIE4300-28P-DP                   OBJECT IDENTIFIER ::= { hh3cProductId 1711 }
hh3cS5024FV2-EI                     OBJECT IDENTIFIER ::= { hh3cProductId 1712 }
hh3cS5024PV2-EI-HPWR                OBJECT IDENTIFIER ::= { hh3cProductId 1713 }
hh3cS5048PV2-EI-HPWR                OBJECT IDENTIFIER ::= { hh3cProductId 1714 }
hh3cE128C                           OBJECT IDENTIFIER ::= { hh3cProductId 1715 }
hh3cE152C                           OBJECT IDENTIFIER ::= { hh3cProductId 1716 }
hh3cMS4200-28TP                     OBJECT IDENTIFIER ::= { hh3cProductId 1717 }
hh3cMS4320S-52P                     OBJECT IDENTIFIER ::= { hh3cProductId 1718 }
hh3cS3100V3-10TP-SI                 OBJECT IDENTIFIER ::= { hh3cProductId 1719 }
hh3cS3100V3-18TP-SI                 OBJECT IDENTIFIER ::= { hh3cProductId 1720 }
hh3cS3100V3-28TP-SI                 OBJECT IDENTIFIER ::= { hh3cProductId 1721 }
hh3cMS4200-18TP                     OBJECT IDENTIFIER ::= { hh3cProductId 1722 }
hh3cMS4200-20TP-PWR                 OBJECT IDENTIFIER ::= { hh3cProductId 1723 }
hh3cMS4200-28TP-PWR                 OBJECT IDENTIFIER ::= { hh3cProductId 1724 }
hh3cS3100V3-52TP-SI                 OBJECT IDENTIFIER ::= { hh3cProductId 1725 }
hh3cS3100V3-28TP-PWR-SI             OBJECT IDENTIFIER ::= { hh3cProductId 1726 }
hh3cS3100V3-10TP-PWR-SI             OBJECT IDENTIFIER ::= { hh3cProductId 1727 }
hh3cS3100V3-20TP-PWR-SI             OBJECT IDENTIFIER ::= { hh3cProductId 1728 }
hh3cSecPath-S75E-LITE-LSQM2FWDSC0-SecBlade-Context      OBJECT IDENTIFIER ::= { hh3cProductId 1729 }
hh3cS75E-LITE-LSQM2FWDSC0-SecBlade-IV                   OBJECT IDENTIFIER ::= { hh3cProductId 1730 }
hh3cNSQM2AC1400-SecPath-M9000-S                         OBJECT IDENTIFIER ::= { hh3cProductId 1731 }
hh3cNSQM2DC1400-SecPath-M9000-S                         OBJECT IDENTIFIER ::= { hh3cProductId 1732 }
hh3cS6800-54QF-H3                   OBJECT IDENTIFIER ::= { hh3cProductId 1733 }
hh3cS6800-54QT-H3                   OBJECT IDENTIFIER ::= { hh3cProductId 1734 }
hh3cWA5620                          OBJECT IDENTIFIER ::= { hh3cProductId 1735 }
hh3cWA5620i-ACN                     OBJECT IDENTIFIER ::= { hh3cProductId 1736 }
hh3cWA5620E-T                       OBJECT IDENTIFIER ::= { hh3cProductId 1737 }
hh3cS12501X-AF                      OBJECT IDENTIFIER ::= { hh3cProductId 1738 }
hh3cS6520X-30QC-EI                  OBJECT IDENTIFIER ::= { hh3cProductId 1739 }
hh3cS6520X-54QC-EI                  OBJECT IDENTIFIER ::= { hh3cProductId 1740 }
hh3cS6520X-30QC-HI                  OBJECT IDENTIFIER ::= { hh3cProductId 1741 }
hh3cS6520X-54QC-HI                  OBJECT IDENTIFIER ::= { hh3cProductId 1742 }
hh3cS6520X-30HC-EI                  OBJECT IDENTIFIER ::= { hh3cProductId 1743 }
hh3cS6520X-54HC-EI                  OBJECT IDENTIFIER ::= { hh3cProductId 1744 }
hh3cS6520X-30HC-HI                  OBJECT IDENTIFIER ::= { hh3cProductId 1745 }
hh3cS6520X-54HC-HI                  OBJECT IDENTIFIER ::= { hh3cProductId 1746 }
hh3cS6900-54QF-F                    OBJECT IDENTIFIER ::= { hh3cProductId 1747 }
hh3cMSR3610-I-DP                    OBJECT IDENTIFIER ::= { hh3cProductId 1748 }
hh3cIE4500-28P                      OBJECT IDENTIFIER ::= { hh3cProductId 1749 }
hh3cF1000-AK115                     OBJECT IDENTIFIER ::= { hh3cProductId 1750 }
hh3cF1000-AK125                     OBJECT IDENTIFIER ::= { hh3cProductId 1751 }
hh3cF1000-AK135                     OBJECT IDENTIFIER ::= { hh3cProductId 1752 }
hh3cF1000-AK145                     OBJECT IDENTIFIER ::= { hh3cProductId 1753 }
hh3cF1000-AK155                     OBJECT IDENTIFIER ::= { hh3cProductId 1754 }
hh3cF1000-AK165                     OBJECT IDENTIFIER ::= { hh3cProductId 1755 }
hh3cF1000-AK175                     OBJECT IDENTIFIER ::= { hh3cProductId 1756 }
hh3cF1000-AK185                     OBJECT IDENTIFIER ::= { hh3cProductId 1757 }
hh3cS3210-16P                       OBJECT IDENTIFIER ::= { hh3cProductId 1758 }
hh3cS3210-8P                        OBJECT IDENTIFIER ::= { hh3cProductId 1759 }
hh3cSecPath-F5080-D                 OBJECT IDENTIFIER ::= { hh3cProductId 1760 }
hh3cSecPath-F5060-D                 OBJECT IDENTIFIER ::= { hh3cProductId 1761 }
hh3cSecPath-F5030-D                 OBJECT IDENTIFIER ::= { hh3cProductId 1762 }
hh3cSecPath-F50X0-D-NSQ1MPBHA       OBJECT IDENTIFIER ::= { hh3cProductId 1763 }
hh3cSecPath-F50X0-D-NSQM1MPULA      OBJECT IDENTIFIER ::= { hh3cProductId 1764 }
hh3cS5024PV3-HI-4X                  OBJECT IDENTIFIER ::= { hh3cProductId 1765 }
hh3cE528D-X-PWR                     OBJECT IDENTIFIER ::= { hh3cProductId 1766 }
hh3cE552D-X-PWR                     OBJECT IDENTIFIER ::= { hh3cProductId 1767 }
hh3cE528C-X                         OBJECT IDENTIFIER ::= { hh3cProductId 1768 }
hh3cE552C-X                         OBJECT IDENTIFIER ::= { hh3cProductId 1769 }
hh3cE528C-X-PWR                     OBJECT IDENTIFIER ::= { hh3cProductId 1770 }
hh3cE552C-X-PWR                     OBJECT IDENTIFIER ::= { hh3cProductId 1771 }
hh3cE528C                           OBJECT IDENTIFIER ::= { hh3cProductId 1772 }
hh3cE552C                           OBJECT IDENTIFIER ::= { hh3cProductId 1773 }
hh3cE528C-PWR                       OBJECT IDENTIFIER ::= { hh3cProductId 1774 }
hh3cE552C-PWR                       OBJECT IDENTIFIER ::= { hh3cProductId 1775 }
hh3cSecPath-ACG1000-AK210           OBJECT IDENTIFIER ::= { hh3cProductId 1776 }
hh3cSecPath-ACG1000-AK220           OBJECT IDENTIFIER ::= { hh3cProductId 1777 }
hh3cSecPath-ACG1000-AK230           OBJECT IDENTIFIER ::= { hh3cProductId 1778 }
hh3cSecPath-ACG1000-AK240           OBJECT IDENTIFIER ::= { hh3cProductId 1779 }
hh3cSecPath-ACG1000-AK250           OBJECT IDENTIFIER ::= { hh3cProductId 1780 }
hh3cSecPath-ACG1000-AK260           OBJECT IDENTIFIER ::= { hh3cProductId 1781 }
hh3cSecPath-ACG1000-AK270           OBJECT IDENTIFIER ::= { hh3cProductId 1782 }
hh3cSecPath-ACG1000-AK280           OBJECT IDENTIFIER ::= { hh3cProductId 1783 }
hh3cSecPath-ACG1010-X1              OBJECT IDENTIFIER ::= { hh3cProductId 1784 }
hh3cSecPath-ACG1030-X1              OBJECT IDENTIFIER ::= { hh3cProductId 1785 }
hh3cSecPath-ACG1050-X1              OBJECT IDENTIFIER ::= { hh3cProductId 1786 }
hh3cWS5850-28X-WiNet                OBJECT IDENTIFIER ::= { hh3cProductId 1787 }
hh3cWS5850-52X-WiNet                OBJECT IDENTIFIER ::= { hh3cProductId 1788 }
hh3cWS5810-28P-WiNet                OBJECT IDENTIFIER ::= { hh3cProductId 1789 }
hh3cWS5820-28P-WiNet                OBJECT IDENTIFIER ::= { hh3cProductId 1790 }
hh3cWS5820-52X-WiNet                OBJECT IDENTIFIER ::= { hh3cProductId 1791 }
hh3cWS5820-28X-WiNet                OBJECT IDENTIFIER ::= { hh3cProductId 1792 }
hh3cWS5820-28X-POE-WiNet            OBJECT IDENTIFIER ::= { hh3cProductId 1793 }
hh3cWS5820-28TP-POE-WiNet           OBJECT IDENTIFIER ::= { hh3cProductId 1794 }
hh3cSecPath-AFC2020                 OBJECT IDENTIFIER ::= { hh3cProductId 1795 }
hh3cSecPath-AFC2040                 OBJECT IDENTIFIER ::= { hh3cProductId 1796 }
hh3cSecPath-AFC2100                 OBJECT IDENTIFIER ::= { hh3cProductId 1797 }
hh3cSecPath-AFC2100-D               OBJECT IDENTIFIER ::= { hh3cProductId 1798 }
hh3cSecPath-AFC2200                 OBJECT IDENTIFIER ::= { hh3cProductId 1799 }
hh3cSecPath-AFC2600                 OBJECT IDENTIFIER ::= { hh3cProductId 1800 }
hh3cSecPath-F100-A-SI               OBJECT IDENTIFIER ::= { hh3cProductId 1801 }
hh3cSecPath-L1000-AK310             OBJECT IDENTIFIER ::= { hh3cProductId 1802 }
hh3cSecPath-L1000-C                 OBJECT IDENTIFIER ::= { hh3cProductId 1803 }
hh3cSecPath-L1000-AK320             OBJECT IDENTIFIER ::= { hh3cProductId 1804 }
hh3cSecPath-L100-C                  OBJECT IDENTIFIER ::= { hh3cProductId 1805 }
hh3cSecPath-L1000-AK330             OBJECT IDENTIFIER ::= { hh3cProductId 1806 }
hh3cSecPath-F1000-C-EI              OBJECT IDENTIFIER ::= { hh3cProductId 1807 }
hh3cMSR2600-6-X1                    OBJECT IDENTIFIER ::= { hh3cProductId 1808 }
hh3cICG2000D                        OBJECT IDENTIFIER ::= { hh3cProductId 1809 }
hh3cLA4616                          OBJECT IDENTIFIER ::= { hh3cProductId 1810 }
hh3cS5560S-28S-EI                   OBJECT IDENTIFIER ::= { hh3cProductId 1811 }
hh3cS5560S-52S-EI                   OBJECT IDENTIFIER ::= { hh3cProductId 1812 }
hh3cS5560S-28P-EI                   OBJECT IDENTIFIER ::= { hh3cProductId 1813 }
hh3cS5560S-52P-EI                   OBJECT IDENTIFIER ::= { hh3cProductId 1814 }
hh3cS5130S-28P-EI-M                 OBJECT IDENTIFIER ::= { hh3cProductId 1815 }
hh3cS5130S-52P-EI-M                 OBJECT IDENTIFIER ::= { hh3cProductId 1816 }
hh3cS5130S-28S-EI-M                 OBJECT IDENTIFIER ::= { hh3cProductId 1817 }
hh3cS5130S-52S-EI-M                 OBJECT IDENTIFIER ::= { hh3cProductId 1818 }
hh3cS5130S-28S-SI                   OBJECT IDENTIFIER ::= { hh3cProductId 1819 }
hh3cS5130S-52S-SI                   OBJECT IDENTIFIER ::= { hh3cProductId 1820 }
hh3cS5560S-28P-SI                   OBJECT IDENTIFIER ::= { hh3cProductId 1821 }
hh3cS5560S-52P-SI                   OBJECT IDENTIFIER ::= { hh3cProductId 1822 }
hh3cS5560S-28S-SI                   OBJECT IDENTIFIER ::= { hh3cProductId 1823 }
hh3cS5560S-52S-SI                   OBJECT IDENTIFIER ::= { hh3cProductId 1824 }
hh3cSecPath-L100-Context            OBJECT IDENTIFIER ::= { hh3cProductId 1825 }
hh3cS9820-64H                       OBJECT IDENTIFIER ::= { hh3cProductId 1826 }
hh3cSecPath-T9008-S                 OBJECT IDENTIFIER ::= { hh3cProductId 1827 }
hh3cSecPath-T9000-S-NSQM2IPSDSCA0-SecBlade-IV-Context  OBJECT IDENTIFIER ::= { hh3cProductId 1828 }
hh3cWBC560                          OBJECT IDENTIFIER ::= { hh3cProductId 1829 }
hh3cS6860-54HF                      OBJECT IDENTIFIER ::= { hh3cProductId 1830 }
hh3cS6860-54HT                      OBJECT IDENTIFIER ::= { hh3cProductId 1831 }
hh3cS6891                           OBJECT IDENTIFIER ::= { hh3cProductId 1832 }
hh3cS5560-54C-EI-G                  OBJECT IDENTIFIER ::= { hh3cProductId 1833 }
hh3cS5560-54F-EI-G                  OBJECT IDENTIFIER ::= { hh3cProductId 1834 }
hh3cS6520X-54XG-EI-G                OBJECT IDENTIFIER ::= { hh3cProductId 1835 }
hh3cS7503X-G                        OBJECT IDENTIFIER ::= { hh3cProductId 1836 }
hh3cS7506X-G                        OBJECT IDENTIFIER ::= { hh3cProductId 1837 }
hh3cS6520-16S-SI                    OBJECT IDENTIFIER ::= { hh3cProductId 1838 }
hh3cS6520-24S-SI                    OBJECT IDENTIFIER ::= { hh3cProductId 1839 }
hh3cS6520X-18C-SI                   OBJECT IDENTIFIER ::= { hh3cProductId 1840 }
hh3cS6520X-26C-SI                   OBJECT IDENTIFIER ::= { hh3cProductId 1841 }
hh3cS6520X-16ST-SI                  OBJECT IDENTIFIER ::= { hh3cProductId 1842 }
hh3cS6520X-24ST-SI                  OBJECT IDENTIFIER ::= { hh3cProductId 1843 }
hh3cS5130S-28TP-EI                  OBJECT IDENTIFIER ::= { hh3cProductId 1844 }
hh3cS5130S-52TP-EI                  OBJECT IDENTIFIER ::= { hh3cProductId 1845 }
hh3cS5130S-28F-EI                   OBJECT IDENTIFIER ::= { hh3cProductId 1846 }
hh3cS5130S-28MP-EI                  OBJECT IDENTIFIER ::= { hh3cProductId 1847 }
hh3cS5130S-10MS-UPWR-EI             OBJECT IDENTIFIER ::= { hh3cProductId 1848 }
hh3cS5130S-28MP-HPWR-EI             OBJECT IDENTIFIER ::= { hh3cProductId 1849 }
hh3cS5130S-52MP-EI                  OBJECT IDENTIFIER ::= { hh3cProductId 1850 }
hh3cMSR3620-G                       OBJECT IDENTIFIER ::= { hh3cProductId 1851 }
hh3cS5110V2-28P                     OBJECT IDENTIFIER ::= { hh3cProductId 1852 }
hh3cS5110V2-52P                     OBJECT IDENTIFIER ::= { hh3cProductId 1853 }
hh3cS5110V2-52P-PWR                 OBJECT IDENTIFIER ::= { hh3cProductId 1854 }
hh3cS5110V2-28P-SI                  OBJECT IDENTIFIER ::= { hh3cProductId 1855 }
hh3cS5110V2-52P-SI                  OBJECT IDENTIFIER ::= { hh3cProductId 1856 }
hh3cS5016PV3-EI                     OBJECT IDENTIFIER ::= { hh3cProductId 1857 }
hh3cS5024PV3-EI                     OBJECT IDENTIFIER ::= { hh3cProductId 1858 }
hh3cS5048PV3-EI                     OBJECT IDENTIFIER ::= { hh3cProductId 1859 }
hh3cS5024PV3-EI-PWR                 OBJECT IDENTIFIER ::= { hh3cProductId 1860 }
hh3cS5048PV3-EI-PWR                 OBJECT IDENTIFIER ::= { hh3cProductId 1861 }
hh3cS5110V2-28P-HPWR                OBJECT IDENTIFIER ::= { hh3cProductId 1862 }
hh3cS5024PV3-EI-HPWR                OBJECT IDENTIFIER ::= { hh3cProductId 1863 }
hh3cS5024FV3-EI                     OBJECT IDENTIFIER ::= { hh3cProductId 1864 }
hh3cS5552F-EI-D                     OBJECT IDENTIFIER ::= { hh3cProductId 1865 }
hh3cS5560-30C-EI-G                  OBJECT IDENTIFIER ::= { hh3cProductId 1866 }
hh3cS5560-30F-EI-G                  OBJECT IDENTIFIER ::= { hh3cProductId 1867 }
hh3cSecPath-F50X0-D-Context         OBJECT IDENTIFIER ::= { hh3cProductId 1868 }
hh3cMS4300V2-28P                    OBJECT IDENTIFIER ::= { hh3cProductId 1869 }
hh3cMS4300V2-52P                    OBJECT IDENTIFIER ::= { hh3cProductId 1870 }
hh3cWAC380-30                       OBJECT IDENTIFIER ::= { hh3cProductId 1871 }
hh3cWA5510E-T                       OBJECT IDENTIFIER ::= { hh3cProductId 1872 }
hh3cCR19000-8                       OBJECT IDENTIFIER ::= { hh3cProductId 1873 }
hh3cCR19000-16                      OBJECT IDENTIFIER ::= { hh3cProductId 1874 }
hh3cS6380-54QF                      OBJECT IDENTIFIER ::= { hh3cProductId 1875 }
hh3cS6380-54QT                      OBJECT IDENTIFIER ::= { hh3cProductId 1876 }
hh3cS6880-54HF                      OBJECT IDENTIFIER ::= { hh3cProductId 1877 }
hh3cSecPath-F5000-M                 OBJECT IDENTIFIER ::= { hh3cProductId 1878 }
hh3cSecPath-TAP2000-S               OBJECT IDENTIFIER ::= { hh3cProductId 1879 }
hh3cSecPath-TAP2000-A               OBJECT IDENTIFIER ::= { hh3cProductId 1880 }
hh3cSecPath-W2000-AK410             OBJECT IDENTIFIER ::= { hh3cProductId 1881 }
hh3cSecPath-W2000-AK420             OBJECT IDENTIFIER ::= { hh3cProductId 1882 }
hh3cSecPath-W2000-AK430             OBJECT IDENTIFIER ::= { hh3cProductId 1883 }
hh3cSecPath-W2000-AK440             OBJECT IDENTIFIER ::= { hh3cProductId 1884 }
hh3cSecPath-T5030                   OBJECT IDENTIFIER ::= { hh3cProductId 1885 }
hh3cSecPath-T5000-S                 OBJECT IDENTIFIER ::= { hh3cProductId 1886 }
hh3cSecPath-L5000-E                 OBJECT IDENTIFIER ::= { hh3cProductId 1887 }
hh3cSecPath-L5030                   OBJECT IDENTIFIER ::= { hh3cProductId 1888 }
hh3cSecPath-L5060                   OBJECT IDENTIFIER ::= { hh3cProductId 1889 }
hh3cSecPath-L5080                   OBJECT IDENTIFIER ::= { hh3cProductId 1890 }
hh3cSecPath-M9010-GM                OBJECT IDENTIFIER ::= { hh3cProductId 1891 }
hh3cWT1024-X-HI                     OBJECT IDENTIFIER ::= { hh3cProductId 1892 }
hh3cWA5530-SI                       OBJECT IDENTIFIER ::= { hh3cProductId 1893 }
hh3cSecPath-SysScan-S               OBJECT IDENTIFIER ::= { hh3cProductId 1894 }
hh3cSecPath-SysScan-M               OBJECT IDENTIFIER ::= { hh3cProductId 1895 }
hh3cSecPath-SysScan-A               OBJECT IDENTIFIER ::= { hh3cProductId 1896 }
hh3cSecPath-SysScan-V               OBJECT IDENTIFIER ::= { hh3cProductId 1897 }
hh3cSecPath-ACG1000-TE              OBJECT IDENTIFIER ::= { hh3cProductId 1898 }
hh3cSecPath-ACG1000-ME              OBJECT IDENTIFIER ::= { hh3cProductId 1899 }
hh3cSecPath-ACG1000-AE              OBJECT IDENTIFIER ::= { hh3cProductId 1900 }
hh3cSecPath-ACG1000-EE              OBJECT IDENTIFIER ::= { hh3cProductId 1901 }
hh3cSecPath-ACG1000-PE              OBJECT IDENTIFIER ::= { hh3cProductId 1902 }
hh3cSecPath-ACG1000-XE1             OBJECT IDENTIFIER ::= { hh3cProductId 1903 }
hh3cSecPath-ACG1070-X1              OBJECT IDENTIFIER ::= { hh3cProductId 1904 }
hh3cSecPath-ACG1060-X1              OBJECT IDENTIFIER ::= { hh3cProductId 1905 }
hh3cMSR3600-51-X1                   OBJECT IDENTIFIER ::= { hh3cProductId 1906 }
hh3cMSR3600-51-X1series             OBJECT IDENTIFIER ::= { hh3cProductId 1907 }
hh3cMSR3600-28-X1                   OBJECT IDENTIFIER ::= { hh3cProductId 1908 }
hh3cMSR3600-28-X1series             OBJECT IDENTIFIER ::= { hh3cProductId 1909 }
hh3cSecPath-L50X0-Context           OBJECT IDENTIFIER ::= { hh3cProductId 1910 }
hh3cSecPath-T50X0-Context           OBJECT IDENTIFIER ::= { hh3cProductId 1911 }
hh3cS6890-30HF                      OBJECT IDENTIFIER ::= { hh3cProductId 1912 }
hh3cS6850-56HF                      OBJECT IDENTIFIER ::= { hh3cProductId 1913 }
hh3cS9850-4C                        OBJECT IDENTIFIER ::= { hh3cProductId 1914 }
hh3cMSR3610-IE-DP                   OBJECT IDENTIFIER ::= { hh3cProductId 1915 }
hh3cMSR3610-G                       OBJECT IDENTIFIER ::= { hh3cProductId 1916 }
hh3cR3900-G                         OBJECT IDENTIFIER ::= { hh3cProductId 1917 }
hh3cIE4500-12P-PWR                  OBJECT IDENTIFIER ::= { hh3cProductId 1918 }
hh3cIE4550-12P-PWR                  OBJECT IDENTIFIER ::= { hh3cProductId 1919 }
hh3cS6520X-26MC-SI                  OBJECT IDENTIFIER ::= { hh3cProductId 1920 }
hh3cS6520X-26MC-UPWR-SI             OBJECT IDENTIFIER ::= { hh3cProductId 1921 }
hh3cS5552S-EI-D-H3                  OBJECT IDENTIFIER ::= { hh3cProductId 1922 }
hh3cS5552P-EI-D-H3                  OBJECT IDENTIFIER ::= { hh3cProductId 1923 }
hh3cS5152P-EI-D-H3                  OBJECT IDENTIFIER ::= { hh3cProductId 1924 }
hh3cS5552P-PWR-EI-D-H3              OBJECT IDENTIFIER ::= { hh3cProductId 1925 }
hh3cS5530F-EI-D-H5                  OBJECT IDENTIFIER ::= { hh3cProductId 1926 }
hh3cSecPath-W2010-G                 OBJECT IDENTIFIER ::= { hh3cProductId 1929 }
hh3cSecPath-W2020-G                 OBJECT IDENTIFIER ::= { hh3cProductId 1930 }
hh3cSecPath-W2040-G                 OBJECT IDENTIFIER ::= { hh3cProductId 1931 }
hh3cSecPath-W2080-G                 OBJECT IDENTIFIER ::= { hh3cProductId 1932 }
hh3cSecPath-W2200-G                 OBJECT IDENTIFIER ::= { hh3cProductId 1933 }
hh3cS5528F-EI-D                     OBJECT IDENTIFIER ::= { hh3cProductId 1934 }
hh3cS5528S-PWR-EI-D                 OBJECT IDENTIFIER ::= { hh3cProductId 1935 }
hh3cSecPath-D2010-G                 OBJECT IDENTIFIER ::= { hh3cProductId 1936 }
hh3cSecPath-D2020-G                 OBJECT IDENTIFIER ::= { hh3cProductId 1937 }
hh3cSecPath-D2030-G                 OBJECT IDENTIFIER ::= { hh3cProductId 1938 }
hh3cSecPath-D2050-G                 OBJECT IDENTIFIER ::= { hh3cProductId 1939 }
hh3cSecPath-T5060                   OBJECT IDENTIFIER ::= { hh3cProductId 1940 }
hh3cSecPath-T5080                   OBJECT IDENTIFIER ::= { hh3cProductId 1941 }
hh3cWAC381                          OBJECT IDENTIFIER ::= { hh3cProductId 1942 }
hh3cSecPath-A2020-G                 OBJECT IDENTIFIER ::= { hh3cProductId 1943 }
hh3cSecPath-A2100-G                 OBJECT IDENTIFIER ::= { hh3cProductId 1944 }
hh3cSecPath-A2200-G                 OBJECT IDENTIFIER ::= { hh3cProductId 1945 }
hh3cSecPath-A2000-AK610             OBJECT IDENTIFIER ::= { hh3cProductId 1946 }
hh3cSecPath-A2000-AK620             OBJECT IDENTIFIER ::= { hh3cProductId 1947 }
hh3cSecPath-F5000-AK515             OBJECT IDENTIFIER ::= { hh3cProductId 1948 }
hh3cSecPath-F5000-AK515-context     OBJECT IDENTIFIER ::= { hh3cProductId 1949 }
hh3cWX1840H                         OBJECT IDENTIFIER ::= { hh3cProductId 1950 }
hh3cWX3840H                         OBJECT IDENTIFIER ::= { hh3cProductId 1951 }
hh3cWX3820H                         OBJECT IDENTIFIER ::= { hh3cProductId 1952 }
hh3cMSR830-6HI-GL                      OBJECT IDENTIFIER ::= { hh3cProductId 1953 }
hh3cMSR830-10EI-GL                     OBJECT IDENTIFIER ::= { hh3cProductId 1954 }
hh3cMSR830-10HI-GL                     OBJECT IDENTIFIER ::= { hh3cProductId 1955 }
hh3cSecPath-F100-C-A5               OBJECT IDENTIFIER ::= { hh3cProductId 1956 }
hh3cMS4620-16S                      OBJECT IDENTIFIER ::= { hh3cProductId 1957 }
hh3cS5000-16X-EI                    OBJECT IDENTIFIER ::= { hh3cProductId 1958 }
hh3cISE3000-H                       OBJECT IDENTIFIER ::= { hh3cProductId 1959 }
hh3cISE3000                         OBJECT IDENTIFIER ::= { hh3cProductId 1960 }
hh3cIG4500-L                        OBJECT IDENTIFIER ::= { hh3cProductId 1961 }
hh3cLA4616-X1                       OBJECT IDENTIFIER ::= { hh3cProductId 1962 }
hh3cLA4616-X1-LM                    OBJECT IDENTIFIER ::= { hh3cProductId 1963 }
hh3cLSQM1WBCZ720                    OBJECT IDENTIFIER ::= { hh3cProductId 1964 }
hh3cLSUM1WBCZ720RT                  OBJECT IDENTIFIER ::= { hh3cProductId 1965 }
hh3cSecPath-F1000-C8160             OBJECT IDENTIFIER ::= { hh3cProductId 1966 }
hh3cSecPath-F1000-C8170             OBJECT IDENTIFIER ::= { hh3cProductId 1967 }
hh3cSecPath-F1000-C8180             OBJECT IDENTIFIER ::= { hh3cProductId 1968 }
hh3c-IG550                          OBJECT IDENTIFIER ::= { hh3cProductId 1969 }
hh3cSecPath-F1000-C8120             OBJECT IDENTIFIER ::= { hh3cProductId 1970 }
hh3cSecPath-F1000-C8130             OBJECT IDENTIFIER ::= { hh3cProductId 1971 }
hh3cSecPath-F1000-C8150             OBJECT IDENTIFIER ::= { hh3cProductId 1972 }
hh3cS6860-30HF                      OBJECT IDENTIFIER ::= { hh3cProductId 1973 }
hh3cIE4300-12P-PWR-M                OBJECT IDENTIFIER ::= { hh3cProductId 1974 }
hh3cMS4520V2-28S                    OBJECT IDENTIFIER ::= { hh3cProductId 1975 }
hh3cMS4520V2-30F                    OBJECT IDENTIFIER ::= { hh3cProductId 1976 }
hh3cMS4520V2-24TP                   OBJECT IDENTIFIER ::= { hh3cProductId 1977 }
hh3cMS4320V2-28S-PWR                OBJECT IDENTIFIER ::= { hh3cProductId 1978 }
hh3cMS4320V2-52S                    OBJECT IDENTIFIER ::= { hh3cProductId 1979 }
hh3cMS4320V2-28S                    OBJECT IDENTIFIER ::= { hh3cProductId 1980 }
hh3cMS4320V2-28F                    OBJECT IDENTIFIER ::= { hh3cProductId 1981 }
hh3cMS4320S-28F-H3                  OBJECT IDENTIFIER ::= { hh3cProductId 1982 }
hh3cMS4320S-28P-H3                  OBJECT IDENTIFIER ::= { hh3cProductId 1983 }
hh3cMS4048P                         OBJECT IDENTIFIER ::= { hh3cProductId 1984 }
hh3cMS4048                          OBJECT IDENTIFIER ::= { hh3cProductId 1985 }
hh3cNS128                           OBJECT IDENTIFIER ::= { hh3cProductId 1986 }
hh3cNS152                           OBJECT IDENTIFIER ::= { hh3cProductId 1987 }
hh3cS5024E-X                        OBJECT IDENTIFIER ::= { hh3cProductId 1988 }
hh3cS5048E-X                        OBJECT IDENTIFIER ::= { hh3cProductId 1989 }
hh3cS1850-28X                       OBJECT IDENTIFIER ::= { hh3cProductId 1990 }
hh3cS1850-52X                       OBJECT IDENTIFIER ::= { hh3cProductId 1991 }
hh3cS5024E-PWR-X                    OBJECT IDENTIFIER ::= { hh3cProductId 1992 }
hh3cS5048E-PWR-X                    OBJECT IDENTIFIER ::= { hh3cProductId 1993 }
hh3cS1850-28X-PWR                   OBJECT IDENTIFIER ::= { hh3cProductId 1994 }
hh3cS1850-52X-PWR                   OBJECT IDENTIFIER ::= { hh3cProductId 1995 }
hh3cWS5820-28P-POE-WiNet            OBJECT IDENTIFIER ::= { hh3cProductId 1996 }
hh3cWS5850-28F-WiNet                OBJECT IDENTIFIER ::= { hh3cProductId 1997 }
hh3cWS5850-28TP-WiNet               OBJECT IDENTIFIER ::= { hh3cProductId 1998 }
hh3cWS5850-52TP-WiNet               OBJECT IDENTIFIER ::= { hh3cProductId 1999 }
hh3cWS5820-52TP-WiNet               OBJECT IDENTIFIER ::= { hh3cProductId 2000 }
hh3cUAP300                          OBJECT IDENTIFIER ::= { hh3cProductId 2001 }
hh3cWA5630X                         OBJECT IDENTIFIER ::= { hh3cProductId 2002 }
hh3cWA5320X                         OBJECT IDENTIFIER ::= { hh3cProductId 2003 }
hh3cWA5320i                         OBJECT IDENTIFIER ::= { hh3cProductId 2004 }
hh3cWA5320X-SI                      OBJECT IDENTIFIER ::= { hh3cProductId 2005 }
hh3cWA5320X-E                       OBJECT IDENTIFIER ::= { hh3cProductId 2006 }
hh3cUAP380                          OBJECT IDENTIFIER ::= { hh3cProductId 2007 }
hh3cWAP723-W2                       OBJECT IDENTIFIER ::= { hh3cProductId 2008 }
hh3cWAP722X-W2                      OBJECT IDENTIFIER ::= { hh3cProductId 2009 }
hh3cWA5520-T                        OBJECT IDENTIFIER ::= { hh3cProductId 2010 }
hh3cWA5320-TI                       OBJECT IDENTIFIER ::= { hh3cProductId 2011 }
hh3cWA538-WW                        OBJECT IDENTIFIER ::= { hh3cProductId 2012 }
hh3cWA536-WW                        OBJECT IDENTIFIER ::= { hh3cProductId 2013 }
hh3cWA530X-WW                       OBJECT IDENTIFIER ::= { hh3cProductId 2014 }
hh3cWA5620X                         OBJECT IDENTIFIER ::= { hh3cProductId 2015 }
hh3cWA560-WW                        OBJECT IDENTIFIER ::= { hh3cProductId 2016 }
hh3cSecPath-F100-C50-WiNet          OBJECT IDENTIFIER ::= { hh3cProductId 2017 }
hh3cSecPath-F1000-C8110             OBJECT IDENTIFIER ::= { hh3cProductId 2018 }
hh3cSR8808M-X                       OBJECT IDENTIFIER ::= { hh3cProductId 2019 }
hh3cCR16010M-F                      OBJECT IDENTIFIER ::= { hh3cProductId 2020 }
hh3cCR16018F                        OBJECT IDENTIFIER ::= { hh3cProductId 2021 }
hh3cCR16010HF                       OBJECT IDENTIFIER ::= { hh3cProductId 2022 }
hh3cSR8808-X                        OBJECT IDENTIFIER ::= { hh3cProductId 2023 }
hh3cCR16010-F                       OBJECT IDENTIFIER ::= { hh3cProductId 2024 }
hh3cS6900-54HQF-F                   OBJECT IDENTIFIER ::= { hh3cProductId 2025 }
hh3cWA530-WW                        OBJECT IDENTIFIER ::= { hh3cProductId 2026 }
hh3cF1000-AK710                     OBJECT IDENTIFIER ::= { hh3cProductId 2027 }
hh3cF1000-AK711                     OBJECT IDENTIFIER ::= { hh3cProductId 2028 }
hh3cSecPath-F1070-GM                OBJECT IDENTIFIER ::= { hh3cProductId 2029 }
hh3cSecPath-F5020-GM                OBJECT IDENTIFIER ::= { hh3cProductId 2030 }
hh3cWX2560H-WiNet                   OBJECT IDENTIFIER ::= { hh3cProductId 2031 }
hh3cWX3508H-WiNet                   OBJECT IDENTIFIER ::= { hh3cProductId 2032 }
hh3cWX2510H-PWR-WiNet               OBJECT IDENTIFIER ::= { hh3cProductId 2033 }
hh3cSecPath-F1003-L                 OBJECT IDENTIFIER ::= { hh3cProductId 2034 }
hh3cSecPath-F1005-L                 OBJECT IDENTIFIER ::= { hh3cProductId 2035 }
hh3cMSR810-LM-GL                    OBJECT IDENTIFIER ::= { hh3cProductId 2036 }
hh3cMSR810-W-LM-GL                  OBJECT IDENTIFIER ::= { hh3cProductId 2037 }
hh3cMSR830-6EI-GL                   OBJECT IDENTIFIER ::= { hh3cProductId 2038 }
hh3cMSR2600-6-X1-GL                 OBJECT IDENTIFIER ::= { hh3cProductId 2039 }
hh3cMSR3600-28-SI-GL                OBJECT IDENTIFIER ::= { hh3cProductId 2040 }
hh3cMSR810-LM-CNDE-SJK              OBJECT IDENTIFIER ::= { hh3cProductId 2041 }
hh3cRX880008                        OBJECT IDENTIFIER ::= { hh3cProductId 2042 }
hh3cRX880016                        OBJECT IDENTIFIER ::= { hh3cProductId 2043 }
hh3cS10506X                         OBJECT IDENTIFIER ::= { hh3cProductId 2044 }
hh3cS10510X                         OBJECT IDENTIFIER ::= { hh3cProductId 2045 }
hh3cWT1024-Q                        OBJECT IDENTIFIER ::= { hh3cProductId 2046 }
hh3cWT1024-X-Q                      OBJECT IDENTIFIER ::= { hh3cProductId 2047 }
hh3cWT1024-X-QH                     OBJECT IDENTIFIER ::= { hh3cProductId 2048 }
hh3cSecPath-ACG1000-V50             OBJECT IDENTIFIER ::= { hh3cProductId 2049 }
hh3cSecPath-ACG1000-V100            OBJECT IDENTIFIER ::= { hh3cProductId 2050 }
hh3cSecPath-ACG1000-V200            OBJECT IDENTIFIER ::= { hh3cProductId 2051 }
hh3cSecPath-ACG1000-V400            OBJECT IDENTIFIER ::= { hh3cProductId 2052 }
hh3cSecPath-ACG1000-AK205           OBJECT IDENTIFIER ::= { hh3cProductId 2053 }
hh3cSecPath-F1000-C8102             OBJECT IDENTIFIER ::= { hh3cProductId 2054 }
hh3cSecPath-DLP2040-N               OBJECT IDENTIFIER ::= { hh3cProductId 2055 }
hh3cSecPath-DLP2100-N               OBJECT IDENTIFIER ::= { hh3cProductId 2056 }
hh3cSecPath-DLP2040-D               OBJECT IDENTIFIER ::= { hh3cProductId 2057 }
hh3cSecPath-DLP2040-M               OBJECT IDENTIFIER ::= { hh3cProductId 2058 }
hh3cSecPath-DLP2100-M               OBJECT IDENTIFIER ::= { hh3cProductId 2059 }
hh3cIG4300-L-R                      OBJECT IDENTIFIER ::= { hh3cProductId 2060 }
hh3cIG4300-R                        OBJECT IDENTIFIER ::= { hh3cProductId 2061 }
hh3cvEPC3200                        OBJECT IDENTIFIER ::= { hh3cProductId 2062 }
hh3cWAS6124-PWR                     OBJECT IDENTIFIER ::= { hh3cProductId 2063 }
hh3cWAS6124-HPWR                    OBJECT IDENTIFIER ::= { hh3cProductId 2064 }
hh3cWAS6148-PWR                     OBJECT IDENTIFIER ::= { hh3cProductId 2065 }
hh3cMSR830-4LM-WiNet                OBJECT IDENTIFIER ::= { hh3cProductId 2066 }
hh3cSecPath-F100-C-A6               OBJECT IDENTIFIER ::= { hh3cProductId 2067 }
hh3cSecPath-F100-C-A3               OBJECT IDENTIFIER ::= { hh3cProductId 2068 }
hh3cSecPath-F100-C-HI               OBJECT IDENTIFIER ::= { hh3cProductId 2069 }
hh3cSecPath-F100-S-HI               OBJECT IDENTIFIER ::= { hh3cProductId 2070 }
hh3cSecPath-F100-A-HI               OBJECT IDENTIFIER ::= { hh3cProductId 2071 }
hh3cSecPath-F1000-C-HI              OBJECT IDENTIFIER ::= { hh3cProductId 2072 }
hh3cSecPath-F1020-GM                OBJECT IDENTIFIER ::= { hh3cProductId 2073 }
hh3cS6860-30HT                      OBJECT IDENTIFIER ::= { hh3cProductId 2074 }
hh3cSecPath-AFC2020-R               OBJECT IDENTIFIER ::= { hh3cProductId 2075 }
hh3cSecPath-AFC2040-R               OBJECT IDENTIFIER ::= { hh3cProductId 2076 }
hh3cS5560S-28S-PWR-EI               OBJECT IDENTIFIER ::= { hh3cProductId 2077 }
hh3cS5560S-52S-PWR-EI               OBJECT IDENTIFIER ::= { hh3cProductId 2078 }
hh3cSecCenter-CSAP-NTA-C            OBJECT IDENTIFIER ::= { hh3cProductId 2079 }
hh3cSecCenter-CSAP-NTA-S            OBJECT IDENTIFIER ::= { hh3cProductId 2080 }
hh3cSecCenter-CSAP-NTA-A            OBJECT IDENTIFIER ::= { hh3cProductId 2081 }
hh3cSecCenter-CSAP-ATD-S            OBJECT IDENTIFIER ::= { hh3cProductId 2082 }
hh3cS9850-32H                       OBJECT IDENTIFIER ::= { hh3cProductId 2084 }
hh3cS6850-2C                        OBJECT IDENTIFIER ::= { hh3cProductId 2085 }
hh3cCPE3200-18                      OBJECT IDENTIFIER ::= { hh3cProductId 2086 }
hh3cSecPath-F100-C-A3-W             OBJECT IDENTIFIER ::= { hh3cProductId 2087 }
hh3cSecPath-F100-C-A5-W             OBJECT IDENTIFIER ::= { hh3cProductId 2088 }
hh3cSecPath-F100-C-A6-WL            OBJECT IDENTIFIER ::= { hh3cProductId 2089 }
hh3cEPC3208                         OBJECT IDENTIFIER ::= { hh3cProductId 2090 }
hh3cmcBBU3200                       OBJECT IDENTIFIER ::= { hh3cProductId 2091 }
hh3cS5500V2-28C-EI                  OBJECT IDENTIFIER ::= { hh3cProductId 2092 }
hh3cSecPath-F1090                   OBJECT IDENTIFIER ::= { hh3cProductId 2093 }
hh3cSecPath-F1090-Context           OBJECT IDENTIFIER ::= { hh3cProductId 2094 }
hh3cMSG360-22L-PWR                  OBJECT IDENTIFIER ::= { hh3cProductId 2095 }
hh3cRX8800-08                       OBJECT IDENTIFIER ::= { hh3cProductId 2096 }
hh3cRX8800-16                       OBJECT IDENTIFIER ::= { hh3cProductId 2097 }
hh3cMSG360-10s                      OBJECT IDENTIFIER ::= { hh3cProductId 2098 }
hh3cS5130S-28F-SI                   OBJECT IDENTIFIER ::= { hh3cProductId 2099 }
hh3cS5560S-28F-SI                   OBJECT IDENTIFIER ::= { hh3cProductId 2100 }
hh3cMS4200-10TP                     OBJECT IDENTIFIER ::= { hh3cProductId 2101 }
hh3cMS4300V2-10P                    OBJECT IDENTIFIER ::= { hh3cProductId 2102 }
hh3cSecPath-F5030-6GW               OBJECT IDENTIFIER ::= { hh3cProductId 2103 }
hh3cSecPath-AVG2000-B               OBJECT IDENTIFIER ::= { hh3cProductId 2104 }
hh3cSecPath-AVG2000-S               OBJECT IDENTIFIER ::= { hh3cProductId 2105 }
hh3cSecPath-AVG2000-A               OBJECT IDENTIFIER ::= { hh3cProductId 2106 }
hh3cSecPath-T5000-C                 OBJECT IDENTIFIER ::= { hh3cProductId 2107 }
hh3cSecPath-F1000-ServerBlade-S     OBJECT IDENTIFIER ::= { hh3cProductId 2108 }
hh3cSecPath-F1000-ServerBlade-A     OBJECT IDENTIFIER ::= { hh3cProductId 2109 }
hh3cmcBBU3100                       OBJECT IDENTIFIER ::= { hh3cProductId 2110 }
hh3cWX5860H                         OBJECT IDENTIFIER ::= { hh3cProductId 2111 }
hh3cSecPath-M9000-E8                OBJECT IDENTIFIER ::= { hh3cProductId 2112 }
hh3cSecPath-M9000-E16               OBJECT IDENTIFIER ::= { hh3cProductId 2113 }
hh3cSecPath-M9012-S                 OBJECT IDENTIFIER ::= { hh3cProductId 2114 }
hh3cMSR2630-XS                      OBJECT IDENTIFIER ::= { hh3cProductId 2115 }
hh3cMSR3600-28-XS                   OBJECT IDENTIFIER ::= { hh3cProductId 2116 }
hh3cMSR3610-XS                      OBJECT IDENTIFIER ::= { hh3cProductId 2117 }
hh3cMSR3620-XS                      OBJECT IDENTIFIER ::= { hh3cProductId 2118 }
hh3cMSR3610-I-XS                    OBJECT IDENTIFIER ::= { hh3cProductId 2119 }
hh3cMSR3610-IE-XS                   OBJECT IDENTIFIER ::= { hh3cProductId 2120 }
hh3cSecPath-D2000-V100              OBJECT IDENTIFIER ::= { hh3cProductId 2121 }
hh3cSecPath-M9000-S-6GW             OBJECT IDENTIFIER ::= { hh3cProductId 2122 }
hh3cS6550XE-56HF-HI                 OBJECT IDENTIFIER ::= { hh3cProductId 2123 }
hh3cS6520-22SG-SI                   OBJECT IDENTIFIER ::= { hh3cProductId 2124 }
hh3cS6520-30SG-SI                   OBJECT IDENTIFIER ::= { hh3cProductId 2125 }
hh3cS5000-22XG-EI                   OBJECT IDENTIFIER ::= { hh3cProductId 2126 }
hh3cS5000-30XG-EI                   OBJECT IDENTIFIER ::= { hh3cProductId 2127 }
hh3cSecPath-F3010-I                 OBJECT IDENTIFIER ::= { hh3cProductId 2128 }
hh3cSecPath-F3110-I                 OBJECT IDENTIFIER ::= { hh3cProductId 2129 }
hh3cSecPath-A3010-I                 OBJECT IDENTIFIER ::= { hh3cProductId 2130 }
hh3cSecPath-A3110-I                 OBJECT IDENTIFIER ::= { hh3cProductId 2131 }
hh3cNSQ1F1TGS6A                     OBJECT IDENTIFIER ::= { hh3cProductId 2132 }
hh3cRA5100-HI                       OBJECT IDENTIFIER ::= { hh3cProductId 2133 }
hh3cRA5200                          OBJECT IDENTIFIER ::= { hh3cProductId 2134 }
hh3cRA5300                          OBJECT IDENTIFIER ::= { hh3cProductId 2135 }
hh3cS6861-54QF                      OBJECT IDENTIFIER ::= { hh3cProductId 2136 }
hh3cS6861-54QT                      OBJECT IDENTIFIER ::= { hh3cProductId 2137 }
hh3cS6861-30QF                      OBJECT IDENTIFIER ::= { hh3cProductId 2138 }
hh3cMER3220                         OBJECT IDENTIFIER ::= { hh3cProductId 2139 }
hh3cMER5200                         OBJECT IDENTIFIER ::= { hh3cProductId 2140 }
hh3cMER8300                         OBJECT IDENTIFIER ::= { hh3cProductId 2141 }
hh3cMSR810-LMS-EA                   OBJECT IDENTIFIER ::= { hh3cProductId 2142 }
hh3cMSR2600-6-WiNet                 OBJECT IDENTIFIER ::= { hh3cProductId 2143 }
hh3cICG3000G                        OBJECT IDENTIFIER ::= { hh3cProductId 2144 }
hh3cIG4510-L                        OBJECT IDENTIFIER ::= { hh3cProductId 2145 }
hh3cIG4520-L                        OBJECT IDENTIFIER ::= { hh3cProductId 2146 }
hh3cMSR810-LME                      OBJECT IDENTIFIER ::= { hh3cProductId 2147 }
hh3cLS-12516G-AF                    OBJECT IDENTIFIER ::= { hh3cProductId 2148 }
hh3cLS-12508G-AF                    OBJECT IDENTIFIER ::= { hh3cProductId 2149 }
hh3cF1000-AI-90                     OBJECT IDENTIFIER ::= { hh3cProductId 2150 }
hh3cF1000-AI-80                     OBJECT IDENTIFIER ::= { hh3cProductId 2151 }
hh3cF1000-AI-70                     OBJECT IDENTIFIER ::= { hh3cProductId 2152 }
hh3cF1000-AI-60                     OBJECT IDENTIFIER ::= { hh3cProductId 2153 }
hh3cSecPath-AFC2020-D-G             OBJECT IDENTIFIER ::= { hh3cProductId 2154 }
hh3cSecPath-AFC2120-G               OBJECT IDENTIFIER ::= { hh3cProductId 2155 }
hh3cF1000-AK1414                    OBJECT IDENTIFIER ::= { hh3cProductId 2156 }
hh3cF1000-AK1424                    OBJECT IDENTIFIER ::= { hh3cProductId 2157 }
hh3cF1000-AK1434                    OBJECT IDENTIFIER ::= { hh3cProductId 2158 }
hh3cF1000-AK1514                    OBJECT IDENTIFIER ::= { hh3cProductId 2159 }
hh3cF1000-AK1524                    OBJECT IDENTIFIER ::= { hh3cProductId 2160 }
hh3cF1000-AK1534                    OBJECT IDENTIFIER ::= { hh3cProductId 2161 }
hh3cF1000-AK1614                    OBJECT IDENTIFIER ::= { hh3cProductId 2162 }
hh3cF1000-AI-50                     OBJECT IDENTIFIER ::= { hh3cProductId 2163 }
hh3cF1000-AI-30                     OBJECT IDENTIFIER ::= { hh3cProductId 2164 }
hh3cF1000-AI-20                     OBJECT IDENTIFIER ::= { hh3cProductId 2165 }
hh3cF5000-AI-20                     OBJECT IDENTIFIER ::= { hh3cProductId 2166 }
hh3cF5000-AI-40                     OBJECT IDENTIFIER ::= { hh3cProductId 2167 }
hh3cF5000-AK525                     OBJECT IDENTIFIER ::= { hh3cProductId 2168 }
hh3cF1000-AK1110                    OBJECT IDENTIFIER ::= { hh3cProductId 2169 }
hh3cF1000-AK1120                    OBJECT IDENTIFIER ::= { hh3cProductId 2170 }
hh3cF1000-AK1130                    OBJECT IDENTIFIER ::= { hh3cProductId 2171 }
hh3cF1000-AK1140                    OBJECT IDENTIFIER ::= { hh3cProductId 2172 }
hh3cF1000-AK1212                    OBJECT IDENTIFIER ::= { hh3cProductId 2173 }
hh3cF1000-AK1222                    OBJECT IDENTIFIER ::= { hh3cProductId 2174 }
hh3cF1000-AK1232                    OBJECT IDENTIFIER ::= { hh3cProductId 2175 }
hh3cF1000-AK1312                    OBJECT IDENTIFIER ::= { hh3cProductId 2176 }
hh3cF1000-AK1322                    OBJECT IDENTIFIER ::= { hh3cProductId 2177 }
hh3cF1000-AK1332                    OBJECT IDENTIFIER ::= { hh3cProductId 2178 }
hh3cF1000-GM-AK370                  OBJECT IDENTIFIER ::= { hh3cProductId 2179 }
hh3cF1000-GM-AK380                  OBJECT IDENTIFIER ::= { hh3cProductId 2180 }
hh3cT1000-AK340                     OBJECT IDENTIFIER ::= { hh3cProductId 2181 }
hh3cT1000-AK350                     OBJECT IDENTIFIER ::= { hh3cProductId 2182 }
hh3cWA5320X-L                       OBJECT IDENTIFIER ::= { hh3cProductId 2187 }
hh3cWA5330                          OBJECT IDENTIFIER ::= { hh3cProductId 2188 }
hh3cWA5530X                         OBJECT IDENTIFIER ::= { hh3cProductId 2189 }
hh3cS6520X-10XT-SI                  OBJECT IDENTIFIER ::= { hh3cProductId 2190 }
hh3cS6520X-16XT-SI                  OBJECT IDENTIFIER ::= { hh3cProductId 2191 }
hh3cSecPath-A2000-AK605             OBJECT IDENTIFIER ::= { hh3cProductId 2192 }
hh3cSecPath-A2000-AK630             OBJECT IDENTIFIER ::= { hh3cProductId 2193 }
hh3cSecPath-D2000-AK660             OBJECT IDENTIFIER ::= { hh3cProductId 2194 }
hh3cSecPath-SysScan-AK810           OBJECT IDENTIFIER ::= { hh3cProductId 2195 }
hh3cSecPath-GAP2000-AK820           OBJECT IDENTIFIER ::= { hh3cProductId 2196 }
hh3cF1000-920-AI                    OBJECT IDENTIFIER ::= { hh3cProductId 2197 }
hh3cF1000-930-AI                    OBJECT IDENTIFIER ::= { hh3cProductId 2198 }
hh3cF1000-950-AI                    OBJECT IDENTIFIER ::= { hh3cProductId 2199 }
hh3cF1000-960-AI                    OBJECT IDENTIFIER ::= { hh3cProductId 2200 }
hh3cF1000-970-AI                    OBJECT IDENTIFIER ::= { hh3cProductId 2201 }
hh3cF1000-980-AI                    OBJECT IDENTIFIER ::= { hh3cProductId 2202 }
hh3cF1000-990-AI                    OBJECT IDENTIFIER ::= { hh3cProductId 2203 }
hh3cEWPXM1WCMX100                   OBJECT IDENTIFIER ::= { hh3cProductId 2204 }
hh3cLSQM1WBCZ720X                   OBJECT IDENTIFIER ::= { hh3cProductId 2205 }
hh3cLSUM1WBCZ720XRT                 OBJECT IDENTIFIER ::= { hh3cProductId 2206 }
hh3cs5130s-16s-pwr-ei-mib           OBJECT IDENTIFIER ::= { hh3cProductId 2207 }
hh3cF5000-A                         OBJECT IDENTIFIER ::= { hh3cProductId 2208 }
hh3cSecPath-W2000-AK415             OBJECT IDENTIFIER ::= { hh3cProductId 2209 }
hh3cSecPath-W2000-AK425             OBJECT IDENTIFIER ::= { hh3cProductId 2210 }
hh3cSecPath-W2000-AK435             OBJECT IDENTIFIER ::= { hh3cProductId 2211 }
hh3cSecPath-W2000-AK445             OBJECT IDENTIFIER ::= { hh3cProductId 2212 }
hh3cSecPath-W2010-G2                OBJECT IDENTIFIER ::= { hh3cProductId 2213 }
hh3cSecPath-W2020-G2                OBJECT IDENTIFIER ::= { hh3cProductId 2214 }
hh3cSecPath-W2040-G2                OBJECT IDENTIFIER ::= { hh3cProductId 2215 }
hh3cSecPath-W2080-G2                OBJECT IDENTIFIER ::= { hh3cProductId 2216 }
hh3cSecPath-W2200-G2                OBJECT IDENTIFIER ::= { hh3cProductId 2217 }
hh3cSecPath-W2000-V-G2              OBJECT IDENTIFIER ::= { hh3cProductId 2218 }
hh3cSecPath-ACG1000-C9130           OBJECT IDENTIFIER ::= { hh3cProductId 2219 }
hh3cSecPath-ACG1000-C9150           OBJECT IDENTIFIER ::= { hh3cProductId 2220 }
hh3cSecPath-ACG1000-C9160           OBJECT IDENTIFIER ::= { hh3cProductId 2221 }
hh3cSecPath-ACG1000-C9170           OBJECT IDENTIFIER ::= { hh3cProductId 2222 }
hh3cLSQM2FWDSC8                     OBJECT IDENTIFIER ::= { hh3cProductId 2223 }
hh3cLSPM6FWD8                       OBJECT IDENTIFIER ::= { hh3cProductId 2224 }
hh3cIE4300-12P-AC                   OBJECT IDENTIFIER ::= { hh3cProductId 2225 }
hh3cIE4300-12P-PWR                  OBJECT IDENTIFIER ::= { hh3cProductId 2226 }
hh3cSecPath-L5000-AK535             OBJECT IDENTIFIER ::= { hh3cProductId 2227 }
hh3cF1000-AI-90-Context                     OBJECT IDENTIFIER ::= { hh3cProductId 2228 }
hh3cF1000-AI-80-Context                     OBJECT IDENTIFIER ::= { hh3cProductId 2229 }
hh3cF1000-AI-70-Context                     OBJECT IDENTIFIER ::= { hh3cProductId 2230 }
hh3cF1000-AI-60-Context                     OBJECT IDENTIFIER ::= { hh3cProductId 2231 }
hh3cF1000-AK1414-Context                    OBJECT IDENTIFIER ::= { hh3cProductId 2232 }
hh3cF1000-AK1424-Context                    OBJECT IDENTIFIER ::= { hh3cProductId 2233 }
hh3cF1000-AK1434-Context                    OBJECT IDENTIFIER ::= { hh3cProductId 2234 }
hh3cF1000-AK1514-Context                    OBJECT IDENTIFIER ::= { hh3cProductId 2235 }
hh3cF1000-AK1524-Context                    OBJECT IDENTIFIER ::= { hh3cProductId 2236 }
hh3cF1000-AK1534-Context                    OBJECT IDENTIFIER ::= { hh3cProductId 2237 }
hh3cF1000-AK1614-Context                    OBJECT IDENTIFIER ::= { hh3cProductId 2238 }
hh3cS5560S-28DP-SI                          OBJECT IDENTIFIER ::= { hh3cProductId 2239 }
hh3cS5500V3-48P-SI                          OBJECT IDENTIFIER ::= { hh3cProductId 2240 }
hh3cS5130S-28S-HPWR-LI                      OBJECT IDENTIFIER ::= { hh3cProductId 2241 }
hh3cS5560S-28F-EI                           OBJECT IDENTIFIER ::= { hh3cProductId 2242 }
hh3cS5560S-52F-EI                           OBJECT IDENTIFIER ::= { hh3cProductId 2243 }
hh3cS5130S-52S-PWR-LI                       OBJECT IDENTIFIER ::= { hh3cProductId 2244 }
hh3cS5120V2-12TP-HPWR-LI                    OBJECT IDENTIFIER ::= { hh3cProductId 2245 }
hh3cS5130S-28S-PWR-LI                       OBJECT IDENTIFIER ::= { hh3cProductId 2246 }
hh3cS5130S-28S-HPWR-EI-Q                    OBJECT IDENTIFIER ::= { hh3cProductId 2247 }
hh3cS5500V3-24P-SI                          OBJECT IDENTIFIER ::= { hh3cProductId 2248 }
hh3cWAP722XS-W2                             OBJECT IDENTIFIER ::= { hh3cProductId 2249 }
hh3cWA5530i                                 OBJECT IDENTIFIER ::= { hh3cProductId 2250 }
hh3cWA5530-LI                               OBJECT IDENTIFIER ::= { hh3cProductId 2251 }
hh3cvMEGW3200                               OBJECT IDENTIFIER ::= { hh3cProductId 2252 }
hh3cMSR3610-IE-ES                           OBJECT IDENTIFIER ::= { hh3cProductId 2253 }
hh3cMSR5610-WiNet                           OBJECT IDENTIFIER ::= { hh3cProductId 2254 }
hh3cNSQM1SSICASK1                           OBJECT IDENTIFIER ::= { hh3cProductId 2255 }
hh3cNSQM2AFC2000DGDSCA0                     OBJECT IDENTIFIER ::= { hh3cProductId 2256 }
hh3cS12506-XS                               OBJECT IDENTIFIER ::= { hh3cProductId 2257 }
hh3cS12508-XS                               OBJECT IDENTIFIER ::= { hh3cProductId 2258 }
hh3cS12510-XS                               OBJECT IDENTIFIER ::= { hh3cProductId 2259 }
hh3cS5850-54QS                              OBJECT IDENTIFIER ::= { hh3cProductId 2260 }
hh3cSecPath-ASM2020                         OBJECT IDENTIFIER ::= { hh3cProductId 2261 }
hh3cSecCenter-CSAP-SA-AK640                 OBJECT IDENTIFIER ::= { hh3cProductId 2262 }
hh3cSecCenter-CSAP-SA-AK645                 OBJECT IDENTIFIER ::= { hh3cProductId 2263 }
hh3cS6520-26Q-SI                            OBJECT IDENTIFIER ::= { hh3cProductId 2264 }
hh3cWS5850-28X-DP-WiNet                     OBJECT IDENTIFIER ::= { hh3cProductId 2265 }
hh3cWA5630X-LI                              OBJECT IDENTIFIER ::= { hh3cProductId 2266 }
hh3cWA5320i-LI                              OBJECT IDENTIFIER ::= { hh3cProductId 2267 }
hh3cS6520X-54XC-UPWR-SI                     OBJECT IDENTIFIER ::= { hh3cProductId 2268 }
hh3cS6520X-26XC-UPWR-SI                     OBJECT IDENTIFIER ::= { hh3cProductId 2269 }
hh3cS12500X2L                               OBJECT IDENTIFIER ::= { hh3cProductId 2270 }
hh3cWX2508H-PWR-LTE                         OBJECT IDENTIFIER ::= { hh3cProductId 2271 }
hh3cS5570-60C-EI                            OBJECT IDENTIFIER ::= { hh3cProductId 2272 }
hh3cS5570-60F-EI                            OBJECT IDENTIFIER ::= { hh3cProductId 2273 }
hh3cF1000-E-G3-Context                      OBJECT IDENTIFIER ::= { hh3cProductId 2274 }
hh3cF1000-C-G3-Context                      OBJECT IDENTIFIER ::= { hh3cProductId 2275 }
hh3cF1000-A-G3-Context                      OBJECT IDENTIFIER ::= { hh3cProductId 2276 }
hh3cF1000-A-G3                              OBJECT IDENTIFIER ::= { hh3cProductId 2277 }
hh3cF1000-S-G3                              OBJECT IDENTIFIER ::= { hh3cProductId 2278 }
hh3cF1000-C-G3                              OBJECT IDENTIFIER ::= { hh3cProductId 2279 }
hh3cF1000-S-G3-Context                      OBJECT IDENTIFIER ::= { hh3cProductId 2280 }
hh3cF1000-E-G3                              OBJECT IDENTIFIER ::= { hh3cProductId 2281 }
hh3cMS4100V2-52P                            OBJECT IDENTIFIER ::= { hh3cProductId 2282 }
hh3cMS4100V2-28P                            OBJECT IDENTIFIER ::= { hh3cProductId 2283 }
hh3cMS4100V2-10P-HPWR                       OBJECT IDENTIFIER ::= { hh3cProductId 2284 }
hh3cMS4100V2-10P                            OBJECT IDENTIFIER ::= { hh3cProductId 2285 }
hh3cMS4100V2-28P-HPWR                       OBJECT IDENTIFIER ::= { hh3cProductId 2286 }
hh3cF100-S80-WiNet                          OBJECT IDENTIFIER ::= { hh3cProductId 2287 }
hh3cF1000-V70                               OBJECT IDENTIFIER ::= { hh3cProductId 2288 }
hh3cF1000-S-VG                              OBJECT IDENTIFIER ::= { hh3cProductId 2289 }
hh3cF100-A80-WiNet                          OBJECT IDENTIFIER ::= { hh3cProductId 2290 }
hh3cF100-E-G3                               OBJECT IDENTIFIER ::= { hh3cProductId 2291 }
hh3cF100-M-G3                               OBJECT IDENTIFIER ::= { hh3cProductId 2292 }
hh3cF100-S-G3                               OBJECT IDENTIFIER ::= { hh3cProductId 2293 }
hh3cF100-C-G3                               OBJECT IDENTIFIER ::= { hh3cProductId 2294 }
hh3cF5000-V30                               OBJECT IDENTIFIER ::= { hh3cProductId 2295 }
hh3cF100-A-G3                               OBJECT IDENTIFIER ::= { hh3cProductId 2296 }
hh3cF1000-E-VG                              OBJECT IDENTIFIER ::= { hh3cProductId 2297 }
hh3cS12508G-AF                              OBJECT IDENTIFIER ::= { hh3cProductId 2298 }
hh3cS12516G-AF                              OBJECT IDENTIFIER ::= { hh3cProductId 2299 }
hh3cSecPath-ACG1000-AK265                   OBJECT IDENTIFIER ::= { hh3cProductId 2300 }
hh3cSecPath-ACG1000-AK255                   OBJECT IDENTIFIER ::= { hh3cProductId 2301 }
hh3cSecPath-ACG1000-AK275                   OBJECT IDENTIFIER ::= { hh3cProductId 2302 }
hh3cSecPath-ACG1000-AK225                   OBJECT IDENTIFIER ::= { hh3cProductId 2303 }
hh3cSecPath-ACG1000-AK215                   OBJECT IDENTIFIER ::= { hh3cProductId 2304 }
hh3cWA5320X-LI                              OBJECT IDENTIFIER ::= { hh3cProductId 2305 }
hh3cWA5530S                                 OBJECT IDENTIFIER ::= { hh3cProductId 2306 }
hh3cWT828Q                                  OBJECT IDENTIFIER ::= { hh3cProductId 2307 }
hh3cCR16018FA                               OBJECT IDENTIFIER ::= { hh3cProductId 2308 }
hh3cCR16010HFA                              OBJECT IDENTIFIER ::= { hh3cProductId 2309 }
hh3cCR16010H-FA                             OBJECT IDENTIFIER ::= { hh3cProductId 2310 }
hh3cCR16018-FA                              OBJECT IDENTIFIER ::= { hh3cProductId 2311 }
hh3cS5130S-52C-PWR-HI                       OBJECT IDENTIFIER ::= { hh3cProductId 2312 }
hh3cS5130S-28C-HI                           OBJECT IDENTIFIER ::= { hh3cProductId 2313 }
hh3cS5130S-28C-PWR-HI                       OBJECT IDENTIFIER ::= { hh3cProductId 2314 }
hh3cS5130S-52C-HI                           OBJECT IDENTIFIER ::= { hh3cProductId 2315 }
hh3cS5130S-52ST-PWR-EI                      OBJECT IDENTIFIER ::= { hh3cProductId 2316 }
hh3cS5130S-28PS-EI                          OBJECT IDENTIFIER ::= { hh3cProductId 2317 }
hh3cS5130S-28ST-EI                          OBJECT IDENTIFIER ::= { hh3cProductId 2318 }
hh3cS5130S-52ST-EI                          OBJECT IDENTIFIER ::= { hh3cProductId 2319 }
hh3cS5130S-28ST-PWR-EI                      OBJECT IDENTIFIER ::= { hh3cProductId 2320 }
hh3cL5000-SV500-Context                     OBJECT IDENTIFIER ::= { hh3cProductId 2321 }
hh3cL5000-SV500                             OBJECT IDENTIFIER ::= { hh3cProductId 2322 }
hh3cL5000-SV100                             OBJECT IDENTIFIER ::= { hh3cProductId 2323 }
hh3cS12508R                                 OBJECT IDENTIFIER ::= { hh3cProductId 2324 }
hh3cS12504R                                 OBJECT IDENTIFIER ::= { hh3cProductId 2325 }
hh3cS12516R                                 OBJECT IDENTIFIER ::= { hh3cProductId 2326 }
hh3c-SecPath-G9020                          OBJECT IDENTIFIER ::= { hh3cProductId 2327 }
hh3c-SecPath-ACG1000-AK285                  OBJECT IDENTIFIER ::= { hh3cProductId 2328 }
hh3c-SecPath-G9010                          OBJECT IDENTIFIER ::= { hh3cProductId 2329 }
hh3cL1090                                   OBJECT IDENTIFIER ::= { hh3cProductId 2330 }
hh3cL1000-AK390-Context                     OBJECT IDENTIFIER ::= { hh3cProductId 2331 }
hh3cL1090-Context                           OBJECT IDENTIFIER ::= { hh3cProductId 2332 }
hh3cL1000-AK390                             OBJECT IDENTIFIER ::= { hh3cProductId 2333 }
hh3c-SecPath-G9020-POS                      OBJECT IDENTIFIER ::= { hh3cProductId 2334 }
hh3c-SecPath-G9000-MC                       OBJECT IDENTIFIER ::= { hh3cProductId 2335 }
hh3c-SecPath-GAP2000-E                      OBJECT IDENTIFIER ::= { hh3cProductId 2336 }
hh3c-SecPath-G9010-PRE                      OBJECT IDENTIFIER ::= { hh3cProductId 2337 }
hh3c-SecPath-G9010-POS                      OBJECT IDENTIFIER ::= { hh3cProductId 2338 }
hh3c-SecPath-GAP2000-F                      OBJECT IDENTIFIER ::= { hh3cProductId 2339 }
hh3cS9820-8C                                OBJECT IDENTIFIER ::= { hh3cProductId 2340 }
hh3cWX2560H-LI                              OBJECT IDENTIFIER ::= { hh3cProductId 2341 }
hh3cWT1024-LI-Q                             OBJECT IDENTIFIER ::= { hh3cProductId 2342 }
hh3cWX2540H-LI                              OBJECT IDENTIFIER ::= { hh3cProductId 2343 }
hh3c-SecPath-G9020-PRE                      OBJECT IDENTIFIER ::= { hh3cProductId 2344 }
hh3c-SecPath-D2000-AK650                    OBJECT IDENTIFIER ::= { hh3cProductId 2345 }
hh3cF1030-GM                                OBJECT IDENTIFIER ::= { hh3cProductId 2346 }
hh3cF1000-AI-10                             OBJECT IDENTIFIER ::= { hh3cProductId 2347 }
hh3cRA5100                                  OBJECT IDENTIFIER ::= { hh3cProductId 2348 }
hh3cS7610E-X                                OBJECT IDENTIFIER ::= { hh3cProductId 2349 }
hh3cS7608E-X                                OBJECT IDENTIFIER ::= { hh3cProductId 2350 }
hh3cS7606E-X                                OBJECT IDENTIFIER ::= { hh3cProductId 2351 }
hh3cS7608E-X-V                              OBJECT IDENTIFIER ::= { hh3cProductId 2352 }
hh3cWA5340                                  OBJECT IDENTIFIER ::= { hh3cProductId 2353 }
hh3cF1030-GM-Context                        OBJECT IDENTIFIER ::= { hh3cProductId 2354 }
hh3cF1000-AI-10-Context                     OBJECT IDENTIFIER ::= { hh3cProductId 2355 }
hh3cF1000-V70-Context                       OBJECT IDENTIFIER ::= { hh3cProductId 2356 }
hh3cF100-C-G3-Context                       OBJECT IDENTIFIER ::= { hh3cProductId 2357 }
hh3cF100-E-G3-Context                       OBJECT IDENTIFIER ::= { hh3cProductId 2358 }
hh3cF100-A-G3-Context                       OBJECT IDENTIFIER ::= { hh3cProductId 2359 }
hh3cF100-M-G3-Context                       OBJECT IDENTIFIER ::= { hh3cProductId 2360 }
hh3cF100-S80-WiNet-Context                  OBJECT IDENTIFIER ::= { hh3cProductId 2361 }
hh3cF100-A80-WiNet-Context                  OBJECT IDENTIFIER ::= { hh3cProductId 2362 }
hh3cF1000-E-VG-Context                      OBJECT IDENTIFIER ::= { hh3cProductId 2363 }
hh3cF5000-V30-Context                       OBJECT IDENTIFIER ::= { hh3cProductId 2364 }
hh3cF1000-S-VG-Context                      OBJECT IDENTIFIER ::= { hh3cProductId 2365 }
hh3cF100-S-G3-Context                       OBJECT IDENTIFIER ::= { hh3cProductId 2366 }
hh3cS5560X-30F-HI                           OBJECT IDENTIFIER ::= { hh3cProductId 2367 }
hh3cS5560X-54F-HI                           OBJECT IDENTIFIER ::= { hh3cProductId 2368 }
hh3cS5590-28T8XC-HI                            OBJECT IDENTIFIER ::= { hh3cProductId 2369 }
hh3cS5590-28S8XC-HI                            OBJECT IDENTIFIER ::= { hh3cProductId 2370 }
hh3cS5590-48T4XC-HI                            OBJECT IDENTIFIER ::= { hh3cProductId 2371 }
hh3cS5590-48S4XC-HI                            OBJECT IDENTIFIER ::= { hh3cProductId 2372 }
hh3cF1010-L                                 OBJECT IDENTIFIER ::= { hh3cProductId 2373 }
hh3cF1010-L-Context                         OBJECT IDENTIFIER ::= { hh3cProductId 2374 }
hh3cIE4320S-50S                             OBJECT IDENTIFIER ::= { hh3cProductId 2375 }
hh3cIE4320S-26S                             OBJECT IDENTIFIER ::= { hh3cProductId 2376 }
hh3cMSR3610-IE-EAD                          OBJECT IDENTIFIER ::= { hh3cProductId 2377 }
hh3cSecPath-GAP2000-BE                      OBJECT IDENTIFIER ::= { hh3cProductId 2378 }
hh3cSecPath-GAP2000-SE                      OBJECT IDENTIFIER ::= { hh3cProductId 2379 }
hh3cSecPath-GAP2000-AE                      OBJECT IDENTIFIER ::= { hh3cProductId 2380 }
hh3cS7006X                                  OBJECT IDENTIFIER ::= { hh3cProductId 2381 }
hh3cS6805-54HT                              OBJECT IDENTIFIER ::= { hh3cProductId 2382 }
hh3cS6805-54HF                              OBJECT IDENTIFIER ::= { hh3cProductId 2383 }
hh3cC230                                    OBJECT IDENTIFIER ::= { hh3cProductId 2384 }
hh3cSecPath-T9012-S                         OBJECT IDENTIFIER ::= { hh3cProductId 2385 }
hh3cWX3510H-LI                              OBJECT IDENTIFIER ::= { hh3cProductId 2386 }
hh3cWX3520H-LI                              OBJECT IDENTIFIER ::= { hh3cProductId 2387 }
hh3cWBC580                                  OBJECT IDENTIFIER ::= { hh3cProductId 2388 }
hh3cS7003X                                  OBJECT IDENTIFIER ::= { hh3cProductId 2389 }
hh3cG310-P                                  OBJECT IDENTIFIER ::= { hh3cProductId 2390 }
hh3cG340                                    OBJECT IDENTIFIER ::= { hh3cProductId 2391 }
hh3cG304-P                                  OBJECT IDENTIFIER ::= { hh3cProductId 2392 }
hh3cWA538-JP                                OBJECT IDENTIFIER ::= { hh3cProductId 2393 }
hh3cF1000-AI-75-Context                     OBJECT IDENTIFIER ::= { hh3cProductId 2394 }
hh3cF1000-AI-65-Context                     OBJECT IDENTIFIER ::= { hh3cProductId 2395 }
hh3cF1000-AI-75                             OBJECT IDENTIFIER ::= { hh3cProductId 2396 }
hh3cF1010-DL                                OBJECT IDENTIFIER ::= { hh3cProductId 2397 }
hh3cF1010-DL-GM                             OBJECT IDENTIFIER ::= { hh3cProductId 2398 }
hh3cSecBlade-Context                        OBJECT IDENTIFIER ::= { hh3cProductId 2399 }
hh3cSecCenter-CSAP-SA-C                     OBJECT IDENTIFIER ::= { hh3cProductId 2400 }
hh3cSecPath-A2000-C                         OBJECT IDENTIFIER ::= { hh3cProductId 2401 }
hh3cSecPath-SysScan-C                       OBJECT IDENTIFIER ::= { hh3cProductId 2402 }
hh3cF1000-AI-65                             OBJECT IDENTIFIER ::= { hh3cProductId 2403 }
hh3cSecCenter-X6010                         OBJECT IDENTIFIER ::= { hh3cProductId 2404 }
hh3cS12500R-2L                              OBJECT IDENTIFIER ::= { hh3cProductId 2405 }
hh3cS5560X-58C-HI                           OBJECT IDENTIFIER ::= { hh3cProductId 2406 }
hh3cS5560X-34C-HI                           OBJECT IDENTIFIER ::= { hh3cProductId 2407 }
hh3cF1000-AI-35                             OBJECT IDENTIFIER ::= { hh3cProductId 2408 }
hh3cF1000-AI-25-Context                     OBJECT IDENTIFIER ::= { hh3cProductId 2409 }
hh3cF1000-AI-55-Context                     OBJECT IDENTIFIER ::= { hh3cProductId 2410 }
hh3cF1000-AI-35-Context                     OBJECT IDENTIFIER ::= { hh3cProductId 2411 }
hh3cF1000-AI-55                             OBJECT IDENTIFIER ::= { hh3cProductId 2412 }
hh3cF1000-AI-25                             OBJECT IDENTIFIER ::= { hh3cProductId 2413 }
hh3cLSWM116H                                OBJECT IDENTIFIER ::= { hh3cProductId 2414 }
hh3cF1070-GM-L-Context                      OBJECT IDENTIFIER ::= { hh3cProductId 2415 }
hh3cF1070-GM-L                              OBJECT IDENTIFIER ::= { hh3cProductId 2416 }
hh3cT1000-AI-50                             OBJECT IDENTIFIER ::= { hh3cProductId 2417 }
hh3cT1000-AI-50-Context                     OBJECT IDENTIFIER ::= { hh3cProductId 2418 }
hh3cT1000-AI-60                             OBJECT IDENTIFIER ::= { hh3cProductId 2419 }
hh3cT1000-AI-60-Context                     OBJECT IDENTIFIER ::= { hh3cProductId 2420 }
hh3cT1000-AI-70                             OBJECT IDENTIFIER ::= { hh3cProductId 2421 }
hh3cT1000-AI-70-Context                     OBJECT IDENTIFIER ::= { hh3cProductId 2422 }
hh3cT1000-AI-80                             OBJECT IDENTIFIER ::= { hh3cProductId 2423 }
hh3cT1000-AI-80-Context                     OBJECT IDENTIFIER ::= { hh3cProductId 2424 }
hh3cT1000-AI-90                             OBJECT IDENTIFIER ::= { hh3cProductId 2425 }
hh3cT1000-AI-90-Context                     OBJECT IDENTIFIER ::= { hh3cProductId 2426 }
hh3cS5130S-16S-UPWR-EI-Q                    OBJECT IDENTIFIER ::= { hh3cProductId 2427 }
hh3cS5130S-28S-UPWR-EI-Q                    OBJECT IDENTIFIER ::= { hh3cProductId 2428 }
hh3cS5130S-28S-UPWR-HI                      OBJECT IDENTIFIER ::= { hh3cProductId 2429 }
hh3cS5130S-28S-EI-DP                        OBJECT IDENTIFIER ::= { hh3cProductId 2430 }
hh3cS5590-48T4XC-EI-G                       OBJECT IDENTIFIER ::= { hh3cProductId 2431 }
hh3cS5590-28T8XC-EI-G                       OBJECT IDENTIFIER ::= { hh3cProductId 2432 }
hh3cS5590-48S4XC-EI-G                       OBJECT IDENTIFIER ::= { hh3cProductId 2433 }
hh3cS5590-28S8XC-EI-G                       OBJECT IDENTIFIER ::= { hh3cProductId 2434 }
hh3cSR6602I                                 OBJECT IDENTIFIER ::= { hh3cProductId 2435 }
hh3cSR6602IE                                OBJECT IDENTIFIER ::= { hh3cProductId 2436 }
hh3cvBRAS1000-CP                            OBJECT IDENTIFIER ::= { hh3cProductId 2437 }
hh3cvBRAS1000-UP                            OBJECT IDENTIFIER ::= { hh3cProductId 2438 }
hh3cWAS6108-HPWR                            OBJECT IDENTIFIER ::= { hh3cProductId 2439 }
hh3cSecPath-M9000-AD6                       OBJECT IDENTIFIER ::= { hh3cProductId 2440 }
hh3cNSQM5AIASKA1                            OBJECT IDENTIFIER ::= { hh3cProductId 2441 }
hh3cS12516CR                                OBJECT IDENTIFIER ::= { hh3cProductId 2442 }
hh3cS12508CR                                OBJECT IDENTIFIER ::= { hh3cProductId 2443 }
hh3cWX3520X                                 OBJECT IDENTIFIER ::= { hh3cProductId 2444 }
hh3cWX3540X                                 OBJECT IDENTIFIER ::= { hh3cProductId 2445 }
hh3cWX3510X                                 OBJECT IDENTIFIER ::= { hh3cProductId 2446 }
hh3cSecCenter-X6020                         OBJECT IDENTIFIER ::= { hh3cProductId 2447 }
hh3cMSR810-CNDE-SJK                         OBJECT IDENTIFIER ::= { hh3cProductId 2448 }
hh3cS6890-44HF                              OBJECT IDENTIFIER ::= { hh3cProductId 2449 }
hh3cS5500V3-28T8XC-HI                          OBJECT IDENTIFIER ::= { hh3cProductId 2450 }
hh3cS5500V3-28S8XC-HI                          OBJECT IDENTIFIER ::= { hh3cProductId 2451 }
hh3cS5500V3-48T4XC-HI                          OBJECT IDENTIFIER ::= { hh3cProductId 2452 }
hh3cSecPath-M9008-S-V                       OBJECT IDENTIFIER ::= { hh3cProductId 2453 }
hh3cSecPath-M9016-V                         OBJECT IDENTIFIER ::= { hh3cProductId 2454 }
hh3cSecPath-GAP2000-AK830                   OBJECT IDENTIFIER ::= { hh3cProductId 2455 }
hh3cS5130S-28S-LI-MM                        OBJECT IDENTIFIER ::= { hh3cProductId 2456 }
hh3cS5130S-28S-SI-MM                        OBJECT IDENTIFIER ::= { hh3cProductId 2457 }
hh3cS5130S-28S-LI-SM                        OBJECT IDENTIFIER ::= { hh3cProductId 2458 }
hh3cS5130S-28S-SI-SM                        OBJECT IDENTIFIER ::= { hh3cProductId 2459 }
hh3cES5530C                                 OBJECT IDENTIFIER ::= { hh3cProductId 2460 }
hh3cS12504G-AF                              OBJECT IDENTIFIER ::= { hh3cProductId 2462 }
hh3cIE4320-28P                              OBJECT IDENTIFIER ::= { hh3cProductId 2463 }
hh3cIE4320-28S-HPWR                         OBJECT IDENTIFIER ::= { hh3cProductId 2464 }
hh3cIE4320-28S                              OBJECT IDENTIFIER ::= { hh3cProductId 2465 }
hh3cS9910E                                  OBJECT IDENTIFIER ::= { hh3cProductId 2466 }
hh3cS9906E                                  OBJECT IDENTIFIER ::= { hh3cProductId 2467 }
hh3cSecPath-ACG1000-BA                      OBJECT IDENTIFIER ::= { hh3cProductId 2468 }
hh3cSeCenter-IAM-TAC                        OBJECT IDENTIFIER ::= { hh3cProductId 2469 }
hh3cSeCenter-IAM-PCM                        OBJECT IDENTIFIER ::= { hh3cProductId 2470 }
hh3cSecPath-EAA                             OBJECT IDENTIFIER ::= { hh3cProductId 2471 }
hh3cSeCenter-IAM-ACM                        OBJECT IDENTIFIER ::= { hh3cProductId 2472 }
hh3cSeCenter-IAM-MSM                        OBJECT IDENTIFIER ::= { hh3cProductId 2473 }
hh3cS6525XE-54HF-HI                         OBJECT IDENTIFIER ::= { hh3cProductId 2474 }
hh3cWA4320-TI                               OBJECT IDENTIFIER ::= { hh3cProductId 2475 }
hh3cvDSS3200                                OBJECT IDENTIFIER ::= { hh3cProductId 2476 }
hh3cvSCC3200                                OBJECT IDENTIFIER ::= { hh3cProductId 2477 }
hh3cIE4320-52P                              OBJECT IDENTIFIER ::= { hh3cProductId 2478 }
hh3cIE4320-52S                              OBJECT IDENTIFIER ::= { hh3cProductId 2479 }
hh3cMSG360-10-LTE                           OBJECT IDENTIFIER ::= { hh3cProductId 2480 }
hh3cS6825-54HF                              OBJECT IDENTIFIER ::= { hh3cProductId 2481 }
hh3cS5560X-30F-EIF                          OBJECT IDENTIFIER ::= { hh3cProductId 2482 }
hh3cSecPath-T9000-E8                        OBJECT IDENTIFIER ::= { hh3cProductId 2483 }
hh3cS3100V3-28TP-EI-DC                      OBJECT IDENTIFIER ::= { hh3cProductId 2484 }
hh3cS3100V3-18TP-EI-DC                      OBJECT IDENTIFIER ::= { hh3cProductId 2485 }
hh3cS3100V3-20TP-PWR-EI-DC                  OBJECT IDENTIFIER ::= { hh3cProductId 2486 }
hh3cIE4320-28S-PS1                          OBJECT IDENTIFIER ::= { hh3cProductId 2487 }
hh3cNSQM5AIASKB1                            OBJECT IDENTIFIER ::= { hh3cProductId 2488 }
hh3cSecPath-ACG1000-B100                    OBJECT IDENTIFIER ::= { hh3cProductId 2489 }
hh3cSecPath-ACG1000-B200                    OBJECT IDENTIFIER ::= { hh3cProductId 2490 }
hh3cSecPath-ACG1000-B300                    OBJECT IDENTIFIER ::= { hh3cProductId 2491 }
hh3cSecCenter-CSAP-ATD-A                    OBJECT IDENTIFIER ::= { hh3cProductId 2492 }
hh3cSecCenter-CSAP-ATD-P                    OBJECT IDENTIFIER ::= { hh3cProductId 2493 }
hh3cSecCenter-CSAP-ATD-E                    OBJECT IDENTIFIER ::= { hh3cProductId 2494 }
hh3cLSWM2XMGT2PM                            OBJECT IDENTIFIER ::= { hh3cProductId 2495 }
hh3cMS4520V2-30C                            OBJECT IDENTIFIER ::= { hh3cProductId 2496 }
hh3cMS4520V2-54C                            OBJECT IDENTIFIER ::= { hh3cProductId 2497 }
hh3cS5170-28S-EI                            OBJECT IDENTIFIER ::= { hh3cProductId 2498 }
hh3cS5570S-36F-EI                           OBJECT IDENTIFIER ::= { hh3cProductId 2499 }
hh3cS5570S-30MS-UPWR-EI                     OBJECT IDENTIFIER ::= { hh3cProductId 2500 }
hh3cS5500V3-54F-DP-SI                       OBJECT IDENTIFIER ::= { hh3cProductId 2501 }
hh3cS5500V3-54S-DP-SI                       OBJECT IDENTIFIER ::= { hh3cProductId 2502 }
hh3cS5500V3-54PS-SI                         OBJECT IDENTIFIER ::= { hh3cProductId 2503 }
hh3cS5554S-EI-D                             OBJECT IDENTIFIER ::= { hh3cProductId 2504 }
hh3cS5500V3-36F-SI                          OBJECT IDENTIFIER ::= { hh3cProductId 2505 }
hh3cS5120V3-28S-EI                          OBJECT IDENTIFIER ::= { hh3cProductId 2506 }
hh3cS5170-54S-EI                            OBJECT IDENTIFIER ::= { hh3cProductId 2507 }
hh3cS5570S-28S-EI                           OBJECT IDENTIFIER ::= { hh3cProductId 2508 }
hh3cS5120V3-54S-PWR-EI                      OBJECT IDENTIFIER ::= { hh3cProductId 2509 }
hh3cS5120V3-54S-EI                          OBJECT IDENTIFIER ::= { hh3cProductId 2510 }
hh3cS5500V3-54S-SI                          OBJECT IDENTIFIER ::= { hh3cProductId 2511 }
hh3cS5170-28S-HPWR-EI                       OBJECT IDENTIFIER ::= { hh3cProductId 2512 }
hh3cS5570S-54F-EI                           OBJECT IDENTIFIER ::= { hh3cProductId 2513 }
hh3cS5570S-28S-HPWR-EI                      OBJECT IDENTIFIER ::= { hh3cProductId 2514 }
hh3cS5500V3-28S-DP-SI                       OBJECT IDENTIFIER ::= { hh3cProductId 2515 }
hh3cS5500V3-28PS-SI                         OBJECT IDENTIFIER ::= { hh3cProductId 2516 }
hh3cS5500V3-28S-SI                          OBJECT IDENTIFIER ::= { hh3cProductId 2517 }
hh3cS5528S-HPWR-EI-D                        OBJECT IDENTIFIER ::= { hh3cProductId 2518 }
hh3cS5170-36F-EI                            OBJECT IDENTIFIER ::= { hh3cProductId 2519 }
hh3cS5120V3-28S-HPWR-EI                     OBJECT IDENTIFIER ::= { hh3cProductId 2520 }
hh3cS5554F-EI-D                             OBJECT IDENTIFIER ::= { hh3cProductId 2521 }
hh3cS5170-54S-PWR-EI                        OBJECT IDENTIFIER ::= { hh3cProductId 2522 }
hh3cS5570S-54S-EI                           OBJECT IDENTIFIER ::= { hh3cProductId 2523 }
hh3cS5500V3-36F-DP-SI                       OBJECT IDENTIFIER ::= { hh3cProductId 2524 }
hh3cS5120V3-28P-HPWR-SI                     OBJECT IDENTIFIER ::= { hh3cProductId 2525 }
hh3cS5120V3-54P-PWR-SI                      OBJECT IDENTIFIER ::= { hh3cProductId 2526 }
hh3cS5570S-54S-PWR-EI                       OBJECT IDENTIFIER ::= { hh3cProductId 2527 }
hh3cCR18000-16                              OBJECT IDENTIFIER ::= { hh3cProductId 2528 }
hh3cL1030                                   OBJECT IDENTIFIER ::= { hh3cProductId 2529 }
hh3cL1030-Context                           OBJECT IDENTIFIER ::= { hh3cProductId 2530 }
hh3cL1070                                   OBJECT IDENTIFIER ::= { hh3cProductId 2531 }
hh3cL1070-Context                           OBJECT IDENTIFIER ::= { hh3cProductId 2532 }
hh3cL1050                                   OBJECT IDENTIFIER ::= { hh3cProductId 2533 }
hh3cL1050-Context                           OBJECT IDENTIFIER ::= { hh3cProductId 2534 }
hh3cv5GC5100                                OBJECT IDENTIFIER ::= { hh3cProductId 2535 }
hh3cvUPF5100                                OBJECT IDENTIFIER ::= { hh3cProductId 2536 }
hh3cAC1016                                  OBJECT IDENTIFIER ::= { hh3cProductId 2537 }
hh3cAC1108                                  OBJECT IDENTIFIER ::= { hh3cProductId 2538 }
hh3cWX2560X                                 OBJECT IDENTIFIER ::= { hh3cProductId 2539 }
hh3cMAK206                                  OBJECT IDENTIFIER ::= { hh3cProductId 2540 }
hh3cWX2550X                                 OBJECT IDENTIFIER ::= { hh3cProductId 2541 }
hh3cMAK204                                  OBJECT IDENTIFIER ::= { hh3cProductId 2542 }
hh3chh3cmcBBU3120                           OBJECT IDENTIFIER ::= { hh3cProductId 2543 }
hh3cBBU5100                                 OBJECT IDENTIFIER ::= { hh3cProductId 2544 }
hh3cS6850-56HF-H1                           OBJECT IDENTIFIER ::= { hh3cProductId 2545 }
hh3cF5000-AI-15-Context                     OBJECT IDENTIFIER ::= { hh3cProductId 2546 }
hh3cF5000-AI-15                             OBJECT IDENTIFIER ::= { hh3cProductId 2547 }
hh3cNS-SecPath-M9000-AI-E4                  OBJECT IDENTIFIER ::= { hh3cProductId 2548 }
hh3cS6550X-32Q-HI                           OBJECT IDENTIFIER ::= { hh3cProductId 2549 }
hh3cS6550X-32H-HI                           OBJECT IDENTIFIER ::= { hh3cProductId 2550 }
hh3cIE4320-28F                              OBJECT IDENTIFIER ::= { hh3cProductId 2551 }
hh3cIE4320-12P-UPWR                         OBJECT IDENTIFIER ::= { hh3cProductId 2552 }
hh3cEPC3108                                 OBJECT IDENTIFIER ::= { hh3cProductId 2553 }
hh3cS5048PV5-EI-PWR                         OBJECT IDENTIFIER ::= { hh3cProductId 2554 }
hh3cS5048PV5-EI                             OBJECT IDENTIFIER ::= { hh3cProductId 2555 }
hh3cS5024PV5-EI-PWR                         OBJECT IDENTIFIER ::= { hh3cProductId 2556 }
hh3cS5016PV5-EI                             OBJECT IDENTIFIER ::= { hh3cProductId 2557 }
hh3cS5528S-EI-D-DP                          OBJECT IDENTIFIER ::= { hh3cProductId 2558 }
hh3cS5024PV5-EI                             OBJECT IDENTIFIER ::= { hh3cProductId 2559 }
hh3cS5024PV5-EI-HPWR                        OBJECT IDENTIFIER ::= { hh3cProductId 2560 }
hh3cMSR3610-IE-IG                           OBJECT IDENTIFIER ::= { hh3cProductId 2561 }
hh3cMSR3610-I-IG                            OBJECT IDENTIFIER ::= { hh3cProductId 2562 }
hh3cS1850V2-28P-HPWR                        OBJECT IDENTIFIER ::= { hh3cProductId 2563 }
hh3cS1850V2-10P                             OBJECT IDENTIFIER ::= { hh3cProductId 2564 }
hh3cS1850V2-26P-HPWR                        OBJECT IDENTIFIER ::= { hh3cProductId 2565 }
hh3cS1850V2-9P                              OBJECT IDENTIFIER ::= { hh3cProductId 2566 }
hh3cS1850V2-26P                             OBJECT IDENTIFIER ::= { hh3cProductId 2567 }
hh3cS5008PV5-EI-HPWR                        OBJECT IDENTIFIER ::= { hh3cProductId 2568 }
hh3cS1850V2-10P-PWR                         OBJECT IDENTIFIER ::= { hh3cProductId 2569 }
hh3cS1850V2-28P                             OBJECT IDENTIFIER ::= { hh3cProductId 2570 }
hh3cS1850V2-52P                             OBJECT IDENTIFIER ::= { hh3cProductId 2571 }
hh3cS5008PV5-EI                             OBJECT IDENTIFIER ::= { hh3cProductId 2572 }
hh3cSecPath-AFC2100-D-G                     OBJECT IDENTIFIER ::= { hh3cProductId 2573 }
hh3cF1000-905-AI                            OBJECT IDENTIFIER ::= { hh3cProductId 2574 }
hh3cF1000-910-AI                            OBJECT IDENTIFIER ::= { hh3cProductId 2575 }
hh3cIE4320-12P                              OBJECT IDENTIFIER ::= { hh3cProductId 2576 }
hh3cIE4320-6P-AC                            OBJECT IDENTIFIER ::= { hh3cProductId 2577 }
hh3cIE4320-20P                              OBJECT IDENTIFIER ::= { hh3cProductId 2578 }
hh3cIE4320-6P                               OBJECT IDENTIFIER ::= { hh3cProductId 2579 }
hh3cSecPath-NSQM1CGQ6SH0                    OBJECT IDENTIFIER ::= { hh3cProductId 2580 }
hh3cIE4320-10S-UPWR                         OBJECT IDENTIFIER ::= { hh3cProductId 2581 }
hh3cIE4320-10S                              OBJECT IDENTIFIER ::= { hh3cProductId 2582 }
hh3cWA6628                                  OBJECT IDENTIFIER ::= { hh3cProductId 2583 }
hh3cWA6638                                  OBJECT IDENTIFIER ::= { hh3cProductId 2584 }
hh3cWA6630X                                 OBJECT IDENTIFIER ::= { hh3cProductId 2585 }
hh3cWA6620X                                 OBJECT IDENTIFIER ::= { hh3cProductId 2586 }
hh3cWA6628E-T                               OBJECT IDENTIFIER ::= { hh3cProductId 2587 }
hh3cWA6622                                  OBJECT IDENTIFIER ::= { hh3cProductId 2588 }
hh3cWA6620                                  OBJECT IDENTIFIER ::= { hh3cProductId 2589 }
hh3cS3600V3-28TP-EI                         OBJECT IDENTIFIER ::= { hh3cProductId 2590 }
hh3cS3600V3-54TP-SI                         OBJECT IDENTIFIER ::= { hh3cProductId 2591 }
hh3cS3600V3-28TP-SI                         OBJECT IDENTIFIER ::= { hh3cProductId 2592 }
hh3cS3600V3-54TP-EI                         OBJECT IDENTIFIER ::= { hh3cProductId 2593 }
hh3cS3600V3-36F-EI                          OBJECT IDENTIFIER ::= { hh3cProductId 2594 }
hh3cF1000-T500                              OBJECT IDENTIFIER ::= { hh3cProductId 2595 }
hh3cF1000-T100                              OBJECT IDENTIFIER ::= { hh3cProductId 2596 }
hh3cF1000-T200                              OBJECT IDENTIFIER ::= { hh3cProductId 2597 }
hh3cRA5300-X                                OBJECT IDENTIFIER ::= { hh3cProductId 2598 }
hh3cSecPath-SysScan-SE                      OBJECT IDENTIFIER ::= { hh3cProductId 2599 }
hh3cSecPath-SysScan-ME                      OBJECT IDENTIFIER ::= { hh3cProductId 2600 }
hh3cSecPath-SysScan-AE                      OBJECT IDENTIFIER ::= { hh3cProductId 2601 }
hh3cSecPath-SysScan-VE                      OBJECT IDENTIFIER ::= { hh3cProductId 2602 }
hh3cS7503X-M-G                              OBJECT IDENTIFIER ::= { hh3cProductId 2603 }
hh3cIE4320-12P-PWR-M                        OBJECT IDENTIFIER ::= { hh3cProductId 2604 }
hh3cS2652V2                                 OBJECT IDENTIFIER ::= { hh3cProductId 2605 }
hh3cS2626V2-HPWR-EI                         OBJECT IDENTIFIER ::= { hh3cProductId 2606 }
hh3cS2626V2-HPWR                            OBJECT IDENTIFIER ::= { hh3cProductId 2607 }
hh3cS2626V2-EI                              OBJECT IDENTIFIER ::= { hh3cProductId 2608 }
hh3cS2610V2                                 OBJECT IDENTIFIER ::= { hh3cProductId 2609 }
hh3cS2626V2                                 OBJECT IDENTIFIER ::= { hh3cProductId 2610 }
hh3cS2626V2-PWR                             OBJECT IDENTIFIER ::= { hh3cProductId 2611 }
hh3cS2610V2-PWR                             OBJECT IDENTIFIER ::= { hh3cProductId 2612 }
hh3cS6813-24X6C                             OBJECT IDENTIFIER ::= { hh3cProductId 2613 }
hh3cS6812-48X6C                             OBJECT IDENTIFIER ::= { hh3cProductId 2614 }
hh3cS6813-48X6C                             OBJECT IDENTIFIER ::= { hh3cProductId 2615 }
hh3cS6812-24X6C                             OBJECT IDENTIFIER ::= { hh3cProductId 2616 }
hh3cS9820-8M                                OBJECT IDENTIFIER ::= { hh3cProductId 2617 }
hh3cSecCenter-X6010-T                       OBJECT IDENTIFIER ::= { hh3cProductId 2618 }
hh3cWBC580G2-HOSP                           OBJECT IDENTIFIER ::= { hh3cProductId 2619 }
hh3cWBC580G2-BASE                           OBJECT IDENTIFIER ::= { hh3cProductId 2620 }
hh3cWA4320i-X-R                             OBJECT IDENTIFIER ::= { hh3cProductId 2621 }
hh3cF1000-T500-W                            OBJECT IDENTIFIER ::= { hh3cProductId 2622 }
hh3cF1000-T200-W                            OBJECT IDENTIFIER ::= { hh3cProductId 2623 }
hh3cF1000-T100-W                            OBJECT IDENTIFIER ::= { hh3cProductId 2624 }
hh3c-SecPath-SysScan-Cloud                  OBJECT IDENTIFIER ::= { hh3cProductId 2625 }
hh3cF5000-E                                 OBJECT IDENTIFIER ::= { hh3cProductId 2626 }
hh3cF5000-AI160-Context                     OBJECT IDENTIFIER ::= { hh3cProductId 2627 }
hh3cF5000-AI120-Context                     OBJECT IDENTIFIER ::= { hh3cProductId 2628 }
hh3cF5000-AI120                             OBJECT IDENTIFIER ::= { hh3cProductId 2629 }
hh3cF5000-E-Context                         OBJECT IDENTIFIER ::= { hh3cProductId 2630 }
hh3cWX2540X-LI                              OBJECT IDENTIFIER ::= { hh3cProductId 2631 }
hh3cS7506X-S                                OBJECT IDENTIFIER ::= { hh3cProductId 2632 }
hh3cSecPath-M9000-X06                       OBJECT IDENTIFIER ::= { hh3cProductId 2633 }
hh3cSecPath-M9000-X10                       OBJECT IDENTIFIER ::= { hh3cProductId 2634 }
hh3cS5120V3-36F-SI                          OBJECT IDENTIFIER ::= { hh3cProductId 2635 }
hh3cS5120V3-36F-EI                          OBJECT IDENTIFIER ::= { hh3cProductId 2636 }
hh3cS5120V3-54P-EI                          OBJECT IDENTIFIER ::= { hh3cProductId 2637 }
hh3cS5120V3-28P-EI                          OBJECT IDENTIFIER ::= { hh3cProductId 2638 }
hh3cSecPath-D2000-AK665                     OBJECT IDENTIFIER ::= { hh3cProductId 2639 }
hh3cSecPath-D2015-G                         OBJECT IDENTIFIER ::= { hh3cProductId 2640 }
hh3cWCG382                                  OBJECT IDENTIFIER ::= { hh3cProductId 2641 }
hh3cSecCenter-CSAP-NTA                      OBJECT IDENTIFIER ::= { hh3cProductId 2642 }
hh3cF1000-C8395-Context                     OBJECT IDENTIFIER ::= { hh3cProductId 2643 }
hh3cF1000-E-G5                              OBJECT IDENTIFIER ::= { hh3cProductId 2644 }
hh3cF1000-9385-AI                           OBJECT IDENTIFIER ::= { hh3cProductId 2645 }
hh3cF1000-9385-AI-Context                   OBJECT IDENTIFIER ::= { hh3cProductId 2646 }
hh3cF1000-9390-AI                           OBJECT IDENTIFIER ::= { hh3cProductId 2647 }
hh3cF1000-E-G5-Context                      OBJECT IDENTIFIER ::= { hh3cProductId 2648 }
hh3cF1000-H-G5                              OBJECT IDENTIFIER ::= { hh3cProductId 2649 }
hh3cF1000-C8395                             OBJECT IDENTIFIER ::= { hh3cProductId 2650 }
hh3cF1000-H-G5-Context                      OBJECT IDENTIFIER ::= { hh3cProductId 2651 }
hh3cF1000-9390-AI-Context                   OBJECT IDENTIFIER ::= { hh3cProductId 2652 }
hh3cS5128S-HPWR-EI-D                        OBJECT IDENTIFIER ::= { hh3cProductId 2653 }
hh3cS5128S-EI-D-H3                          OBJECT IDENTIFIER ::= { hh3cProductId 2654 }
hh3cS5536F-EI-D                             OBJECT IDENTIFIER ::= { hh3cProductId 2655 }
hh3cSecPath-A2000-AK602                     OBJECT IDENTIFIER ::= { hh3cProductId 2656 }
hh3cSecPath-A2000-AK625                     OBJECT IDENTIFIER ::= { hh3cProductId 2657 }
hh3cSecPath-A2025-G                         OBJECT IDENTIFIER ::= { hh3cProductId 2658 }
hh3cSecPath-A2105-G                         OBJECT IDENTIFIER ::= { hh3cProductId 2659 }
hh3cSecPath-A2000-AK615                     OBJECT IDENTIFIER ::= { hh3cProductId 2660 }
hh3cSecPath-A2210-G                         OBJECT IDENTIFIER ::= { hh3cProductId 2661 }
hh3cF100-S-G5                               OBJECT IDENTIFIER ::= { hh3cProductId 2662 }
hh3cF1000-9320-AI                           OBJECT IDENTIFIER ::= { hh3cProductId 2663 }
hh3cF100-M-G5                               OBJECT IDENTIFIER ::= { hh3cProductId 2664 }
hh3cF1000-C8330                             OBJECT IDENTIFIER ::= { hh3cProductId 2665 }
hh3cF1000-9330-AI                           OBJECT IDENTIFIER ::= { hh3cProductId 2666 }
hh3cF100-A-G5                               OBJECT IDENTIFIER ::= { hh3cProductId 2667 }
hh3cF1000-AK1160                            OBJECT IDENTIFIER ::= { hh3cProductId 2668 }
hh3cF1000-AK1020                            OBJECT IDENTIFIER ::= { hh3cProductId 2669 }
hh3cF1000-730-HI                            OBJECT IDENTIFIER ::= { hh3cProductId 2670 }
hh3cF100-C-XI                               OBJECT IDENTIFIER ::= { hh3cProductId 2671 }
hh3cF1000-AK1180                            OBJECT IDENTIFIER ::= { hh3cProductId 2672 }
hh3cF1000-AK1030                            OBJECT IDENTIFIER ::= { hh3cProductId 2673 }
hh3cF1000-720-HI                            OBJECT IDENTIFIER ::= { hh3cProductId 2674 }
hh3cF1000-710-HI                            OBJECT IDENTIFIER ::= { hh3cProductId 2675 }
hh3cF100-C-G5                               OBJECT IDENTIFIER ::= { hh3cProductId 2676 }
hh3cF100-A81-WiNet                          OBJECT IDENTIFIER ::= { hh3cProductId 2677 }
hh3cF1000-AK1150                            OBJECT IDENTIFIER ::= { hh3cProductId 2678 }
hh3cF1000-AK1170                            OBJECT IDENTIFIER ::= { hh3cProductId 2679 }
hh3cF100-S-XI                               OBJECT IDENTIFIER ::= { hh3cProductId 2680 }
hh3cF1000-AK1010                            OBJECT IDENTIFIER ::= { hh3cProductId 2681 }
hh3cS5500V2-52C-EI                          OBJECT IDENTIFIER ::= { hh3cProductId 2682 }
hh3cF1000-S-G5-Context                      OBJECT IDENTIFIER ::= { hh3cProductId 2683 }
hh3cF1000-C-G5                              OBJECT IDENTIFIER ::= { hh3cProductId 2684 }
hh3cF1000-S-G5                              OBJECT IDENTIFIER ::= { hh3cProductId 2685 }
hh3cF1000-9370-AI                           OBJECT IDENTIFIER ::= { hh3cProductId 2686 }
hh3cF1000-9380-AI-Context                   OBJECT IDENTIFIER ::= { hh3cProductId 2687 }
hh3cF1000-750-HI                            OBJECT IDENTIFIER ::= { hh3cProductId 2688 }
hh3cF1000-9350-AI-Context                   OBJECT IDENTIFIER ::= { hh3cProductId 2689 }
hh3cF1000-9360-AI-Context                   OBJECT IDENTIFIER ::= { hh3cProductId 2690 }
hh3cF1000-C8350-Context                     OBJECT IDENTIFIER ::= { hh3cProductId 2691 }
hh3cF100-A91-WiNet-Context                  OBJECT IDENTIFIER ::= { hh3cProductId 2692 }
hh3cF1000-9360-AI                           OBJECT IDENTIFIER ::= { hh3cProductId 2693 }
hh3cF1000-C8390                             OBJECT IDENTIFIER ::= { hh3cProductId 2694 }
hh3cF1000-C-G5-LI-Context                   OBJECT IDENTIFIER ::= { hh3cProductId 2695 }
hh3cF100-A91-WiNet                          OBJECT IDENTIFIER ::= { hh3cProductId 2696 }
hh3cF1000-C-G5-Context                      OBJECT IDENTIFIER ::= { hh3cProductId 2697 }
hh3cF1000-C8370-Context                     OBJECT IDENTIFIER ::= { hh3cProductId 2698 }
hh3cF1000-740-HI-Context                    OBJECT IDENTIFIER ::= { hh3cProductId 2699 }
hh3cF1000-A-G5-Context                      OBJECT IDENTIFIER ::= { hh3cProductId 2700 }
hh3cF1000-C8380-Context                     OBJECT IDENTIFIER ::= { hh3cProductId 2701 }
hh3cF1000-A-G5                              OBJECT IDENTIFIER ::= { hh3cProductId 2702 }
hh3cF1000-C-XI-Context                      OBJECT IDENTIFIER ::= { hh3cProductId 2703 }
hh3cF1000-9350-AI                           OBJECT IDENTIFIER ::= { hh3cProductId 2704 }
hh3cF1000-740-HI                            OBJECT IDENTIFIER ::= { hh3cProductId 2705 }
hh3cF1000-C8385-Context                     OBJECT IDENTIFIER ::= { hh3cProductId 2706 }
hh3cF1000-9380-AI                           OBJECT IDENTIFIER ::= { hh3cProductId 2707 }
hh3cF100-E-G5                               OBJECT IDENTIFIER ::= { hh3cProductId 2708 }
hh3cF1000-C8360                             OBJECT IDENTIFIER ::= { hh3cProductId 2709 }
hh3cF1000-770-HI-Context                    OBJECT IDENTIFIER ::= { hh3cProductId 2710 }
hh3cF1000-C8385                             OBJECT IDENTIFIER ::= { hh3cProductId 2711 }
hh3cF1000-9370-AI-Context                   OBJECT IDENTIFIER ::= { hh3cProductId 2712 }
hh3cF1000-AK1342                            OBJECT IDENTIFIER ::= { hh3cProductId 2713 }
hh3cF1000-AK1272-Context                    OBJECT IDENTIFIER ::= { hh3cProductId 2714 }
hh3cF1000-AK1252                            OBJECT IDENTIFIER ::= { hh3cProductId 2715 }
hh3cF1000-AK1242-Context                    OBJECT IDENTIFIER ::= { hh3cProductId 2716 }
hh3cF1000-AK1252-Context                    OBJECT IDENTIFIER ::= { hh3cProductId 2717 }
hh3cF1000-AK1262                            OBJECT IDENTIFIER ::= { hh3cProductId 2718 }
hh3cF1000-AK1342-Context                    OBJECT IDENTIFIER ::= { hh3cProductId 2719 }
hh3cF1000-AK1272                            OBJECT IDENTIFIER ::= { hh3cProductId 2720 }
hh3cF1000-AK1352                            OBJECT IDENTIFIER ::= { hh3cProductId 2721 }
hh3cF1000-AK1262-Context                    OBJECT IDENTIFIER ::= { hh3cProductId 2722 }
hh3cF1000-AK1352-Context                    OBJECT IDENTIFIER ::= { hh3cProductId 2723 }
hh3cF1000-AK1362-Context                    OBJECT IDENTIFIER ::= { hh3cProductId 2724 }
hh3cF1000-AK1242                            OBJECT IDENTIFIER ::= { hh3cProductId 2725 }
hh3cF1000-AK1362                            OBJECT IDENTIFIER ::= { hh3cProductId 2726 }
hh3cF1000-C8380                             OBJECT IDENTIFIER ::= { hh3cProductId 2727 }
hh3cF1000-C8350                             OBJECT IDENTIFIER ::= { hh3cProductId 2728 }
hh3cF1000-770-HI                            OBJECT IDENTIFIER ::= { hh3cProductId 2729 }
hh3cF1000-E-XI-Context                      OBJECT IDENTIFIER ::= { hh3cProductId 2730 }
hh3cF1000-C8390-Context                     OBJECT IDENTIFIER ::= { hh3cProductId 2731 }
hh3cF1000-C-G5-LI                           OBJECT IDENTIFIER ::= { hh3cProductId 2732 }
hh3cF1000-C8370                             OBJECT IDENTIFIER ::= { hh3cProductId 2733 }
hh3cF1000-E-XI                              OBJECT IDENTIFIER ::= { hh3cProductId 2734 }
hh3cF1000-C8360-Context                     OBJECT IDENTIFIER ::= { hh3cProductId 2735 }
hh3cF1000-750-HI-Context                    OBJECT IDENTIFIER ::= { hh3cProductId 2736 }
hh3cF100-E-G5-Context                       OBJECT IDENTIFIER ::= { hh3cProductId 2737 }
hh3cF1000-C-XI                              OBJECT IDENTIFIER ::= { hh3cProductId 2738 }
hh3cSecPath-A2000-Cloud                     OBJECT IDENTIFIER ::= { hh3cProductId 2739 }
hh3cIE-Module-8P                            OBJECT IDENTIFIER ::= { hh3cProductId 2740 }
hh3cIE-Module-8G                            OBJECT IDENTIFIER ::= { hh3cProductId 2741 }
hh3cIE-Module-4G4P                          OBJECT IDENTIFIER ::= { hh3cProductId 2742 }
hh3cIE4520-30S-C                            OBJECT IDENTIFIER ::= { hh3cProductId 2743 }
hh3cIE4520-54S-C                            OBJECT IDENTIFIER ::= { hh3cProductId 2744 }
hh3cMSR-EAD-AK770                           OBJECT IDENTIFIER ::= { hh3cProductId 2745 }
hh3cSecPath-D2000-AK655                     OBJECT IDENTIFIER ::= { hh3cProductId 2746 }
hh3cSecPath-D2025-G                         OBJECT IDENTIFIER ::= { hh3cProductId 2747 }
hh3cSecPath-D2055-G                         OBJECT IDENTIFIER ::= { hh3cProductId 2748 }
hh3cSecPath-D2035-G                         OBJECT IDENTIFIER ::= { hh3cProductId 2749 }
hh3cS1850V2-52X-PWR                         OBJECT IDENTIFIER ::= { hh3cProductId 2750 }
hh3cS5120V3-20P-LI                          OBJECT IDENTIFIER ::= { hh3cProductId 2751 }
hh3cMS4320V3-28P                            OBJECT IDENTIFIER ::= { hh3cProductId 2752 }
hh3cMS4320V3-52P                            OBJECT IDENTIFIER ::= { hh3cProductId 2753 }
hh3cS5120V3-28P-LI                          OBJECT IDENTIFIER ::= { hh3cProductId 2754 }
hh3cS5120V3-52P-SI                          OBJECT IDENTIFIER ::= { hh3cProductId 2755 }
hh3cS5128S-EI-D-AC                          OBJECT IDENTIFIER ::= { hh3cProductId 2756 }
hh3cS5120V3-28S-HPWR-SI-Q                   OBJECT IDENTIFIER ::= { hh3cProductId 2757 }
hh3cS5048X-EI                               OBJECT IDENTIFIER ::= { hh3cProductId 2758 }
hh3cS5120V3-52P-PWR-LI                      OBJECT IDENTIFIER ::= { hh3cProductId 2759 }
hh3cS5024X-EI                               OBJECT IDENTIFIER ::= { hh3cProductId 2760 }
hh3cS5120V3-28S-LI                          OBJECT IDENTIFIER ::= { hh3cProductId 2761 }
hh3cS5120V3-28S-SI                          OBJECT IDENTIFIER ::= { hh3cProductId 2762 }
hh3cS5024X-PWR-EI                           OBJECT IDENTIFIER ::= { hh3cProductId 2763 }
hh3cS5048X-PWR-EI                           OBJECT IDENTIFIER ::= { hh3cProductId 2764 }
hh3cS5130S-52S-PWR-EI-AC                    OBJECT IDENTIFIER ::= { hh3cProductId 2765 }
hh3cS1850V2-52X                             OBJECT IDENTIFIER ::= { hh3cProductId 2766 }
hh3cS5120V3-52P-LI                          OBJECT IDENTIFIER ::= { hh3cProductId 2767 }
hh3cS5120V3-52S-PWR-LI                      OBJECT IDENTIFIER ::= { hh3cProductId 2768 }
hh3cS1850V2-28X-HPWR                        OBJECT IDENTIFIER ::= { hh3cProductId 2769 }
hh3cS5024X-HPWR-EI                          OBJECT IDENTIFIER ::= { hh3cProductId 2770 }
hh3cMS4320V3-28S-PWR                        OBJECT IDENTIFIER ::= { hh3cProductId 2771 }
hh3cS5130S-52P-PWR-EI-AC                    OBJECT IDENTIFIER ::= { hh3cProductId 2772 }
hh3cS5120V3-28P-HPWR-LI-Q                   OBJECT IDENTIFIER ::= { hh3cProductId 2773 }
hh3cS5120V3-28P-SI                          OBJECT IDENTIFIER ::= { hh3cProductId 2774 }
hh3cS5120V3-28P-PWR-LI                      OBJECT IDENTIFIER ::= { hh3cProductId 2775 }
hh3cS1850V2-28X                             OBJECT IDENTIFIER ::= { hh3cProductId 2776 }
hh3cMS4320V3-52S                            OBJECT IDENTIFIER ::= { hh3cProductId 2777 }
hh3cMS4320V3-28S                            OBJECT IDENTIFIER ::= { hh3cProductId 2778 }
hh3cS5120V3-52S-LI                          OBJECT IDENTIFIER ::= { hh3cProductId 2779 }
hh3cS5120V3-28S-PWR-LI                      OBJECT IDENTIFIER ::= { hh3cProductId 2780 }
hh3cS5120V3-52S-SI                          OBJECT IDENTIFIER ::= { hh3cProductId 2781 }
hh3cSecPath-F3015-I                         OBJECT IDENTIFIER ::= { hh3cProductId 2782 }
hh3cSecPath-F3115-I                         OBJECT IDENTIFIER ::= { hh3cProductId 2783 }
hh3cSecPath-A3115-I                         OBJECT IDENTIFIER ::= { hh3cProductId 2784 }
hh3cF1000-T1000                             OBJECT IDENTIFIER ::= { hh3cProductId 2785 }
hh3cF1000-AI-05                             OBJECT IDENTIFIER ::= { hh3cProductId 2786 }
hh3cF1000-AI-15                             OBJECT IDENTIFIER ::= { hh3cProductId 2787 }
hh3cSecPath-AFC2040-G2                      OBJECT IDENTIFIER ::= { hh3cProductId 2788 }
hh3cSecPath-AFC2100-G2                      OBJECT IDENTIFIER ::= { hh3cProductId 2789 }
hh3cSecPath-AFC2200-G2                      OBJECT IDENTIFIER ::= { hh3cProductId 2790 }
hh3cSecPath-AFC2400-G2                      OBJECT IDENTIFIER ::= { hh3cProductId 2791 }
hh3cSecPath-AFC2020-G2                      OBJECT IDENTIFIER ::= { hh3cProductId 2792 }
hh3cSecPath-AFC2000-D-G2                    OBJECT IDENTIFIER ::= { hh3cProductId 2793 }
hh3cWX5560X                                 OBJECT IDENTIFIER ::= { hh3cProductId 2794 }
hh3cF5000-AI160                             OBJECT IDENTIFIER ::= { hh3cProductId 2795 }
hh3cS9825-64D                               OBJECT IDENTIFIER ::= { hh3cProductId 2796 }
hh3cS9855-48CD8D                            OBJECT IDENTIFIER ::= { hh3cProductId 2797 }
hh3cWX5540X                                 OBJECT IDENTIFIER ::= { hh3cProductId 2798 }
hh3cWBC580G2-GL                             OBJECT IDENTIFIER ::= { hh3cProductId 2799 }
hh3cF1000-V50-Context                       OBJECT IDENTIFIER ::= { hh3cProductId 2800 }
hh3cF1000-V50                               OBJECT IDENTIFIER ::= { hh3cProductId 2801 }
hh3cCSAP-NTA-600                            OBJECT IDENTIFIER ::= { hh3cProductId 2802 }
hh3cCSAP-NTA-600-Context                    OBJECT IDENTIFIER ::= { hh3cProductId 2803 }
hh3cCSAP-NTA-500-Context                    OBJECT IDENTIFIER ::= { hh3cProductId 2804 }
hh3cCSAP-NTA-300                            OBJECT IDENTIFIER ::= { hh3cProductId 2805 }
hh3cCSAP-NTA-400                            OBJECT IDENTIFIER ::= { hh3cProductId 2806 }
hh3cCSAP-NTA-100-Context                    OBJECT IDENTIFIER ::= { hh3cProductId 2807 }
hh3cCSAP-NTA-100                            OBJECT IDENTIFIER ::= { hh3cProductId 2808 }
hh3cCSAP-NTA-200-Context                    OBJECT IDENTIFIER ::= { hh3cProductId 2809 }
hh3cCSAP-NTA-400-Context                    OBJECT IDENTIFIER ::= { hh3cProductId 2810 }
hh3cCSAP-NTA-500                            OBJECT IDENTIFIER ::= { hh3cProductId 2811 }
hh3cCSAP-NTA-300-Context                    OBJECT IDENTIFIER ::= { hh3cProductId 2812 }
hh3cCSAP-NTA-AK375                          OBJECT IDENTIFIER ::= { hh3cProductId 2813 }
hh3cCSAP-NTA-AK375-Context                  OBJECT IDENTIFIER ::= { hh3cProductId 2814 }
hh3cCSAP-NTA-200                            OBJECT IDENTIFIER ::= { hh3cProductId 2815 }
hh3cF1000-V90                               OBJECT IDENTIFIER ::= { hh3cProductId 2816 }
hh3cF1000-V60                               OBJECT IDENTIFIER ::= { hh3cProductId 2817 }
hh3cF1000-V90-Context                       OBJECT IDENTIFIER ::= { hh3cProductId 2818 }
hh3cF1000-V60-Context                       OBJECT IDENTIFIER ::= { hh3cProductId 2819 }
hh3cS7510X-G                                OBJECT IDENTIFIER ::= { hh3cProductId 2820 }
hh3cT1000-AK365                             OBJECT IDENTIFIER ::= { hh3cProductId 2821 }
hh3cT1000-AK355                             OBJECT IDENTIFIER ::= { hh3cProductId 2822 }
hh3cT1000-AK355-Context                     OBJECT IDENTIFIER ::= { hh3cProductId 2823 }
hh3cT1000-AK345                             OBJECT IDENTIFIER ::= { hh3cProductId 2824 }
hh3cT1000-AK345-Context                     OBJECT IDENTIFIER ::= { hh3cProductId 2825 }
hh3cT1000-AK365-Context                     OBJECT IDENTIFIER ::= { hh3cProductId 2826 }
hh3cWX2520X-LI                              OBJECT IDENTIFIER ::= { hh3cProductId 2827 }
hh3cWX2560X-LI                              OBJECT IDENTIFIER ::= { hh3cProductId 2828 }
hh3cS5590XP-48T4XC-HI-G                     OBJECT IDENTIFIER ::= { hh3cProductId 2829 }
hh3cS6520X-30XG-EI-G                        OBJECT IDENTIFIER ::= { hh3cProductId 2830 }
hh3cS5590XP-48S4XC-HI-G                     OBJECT IDENTIFIER ::= { hh3cProductId 2831 }
hh3cS5130S-30C-EI-G                         OBJECT IDENTIFIER ::= { hh3cProductId 2832 }
hh3cS6520X-54HT-EI-G                        OBJECT IDENTIFIER ::= { hh3cProductId 2833 }
hh3cS5130S-54C-EI-G                         OBJECT IDENTIFIER ::= { hh3cProductId 2834 }
hh3cS6520XP-54XG-EI-G                       OBJECT IDENTIFIER ::= { hh3cProductId 2835 }
hh3cBX608FE                                 OBJECT IDENTIFIER ::= { hh3cProductId 2836 }
hh3cBX720E                                  OBJECT IDENTIFIER ::= { hh3cProductId 2837 }
hh3cBX1020EF                                OBJECT IDENTIFIER ::= { hh3cProductId 2838 }
hh3cOM100                                   OBJECT IDENTIFIER ::= { hh3cProductId 2839 }
hh3cHN720E                                  OBJECT IDENTIFIER ::= { hh3cProductId 2840 }
hh3cBX1010E                                 OBJECT IDENTIFIER ::= { hh3cProductId 2841 }
hh3cHN608FE                                 OBJECT IDENTIFIER ::= { hh3cProductId 2842 }
hh3cBX720EF                                 OBJECT IDENTIFIER ::= { hh3cProductId 2843 }
hh3cHN720EF                                 OBJECT IDENTIFIER ::= { hh3cProductId 2844 }
hh3cMSR860-6EI-XS                           OBJECT IDENTIFIER ::= { hh3cProductId 2845 }
hh3cMSR3640-X1-HI                           OBJECT IDENTIFIER ::= { hh3cProductId 2846 }
hh3cMSR860-6HI-XS                           OBJECT IDENTIFIER ::= { hh3cProductId 2847 }
hh3cMSR3660-XS                              OBJECT IDENTIFIER ::= { hh3cProductId 2848 }
hh3cMSR3640-XS                              OBJECT IDENTIFIER ::= { hh3cProductId 2849 }
hh3cMSR3620-X1                              OBJECT IDENTIFIER ::= { hh3cProductId 2850 }
hh3cMSR3620-X1-XS                           OBJECT IDENTIFIER ::= { hh3cProductId 2851 }
hh3cMSR3640-X1                              OBJECT IDENTIFIER ::= { hh3cProductId 2852 }
hh3cS6800-54QF-H5                           OBJECT IDENTIFIER ::= { hh3cProductId 2853 }
hh3cS6826-48Y8C                             OBJECT IDENTIFIER ::= { hh3cProductId 2854 }
hh3cS9826-32C                               OBJECT IDENTIFIER ::= { hh3cProductId 2855 }
hh3cCSAP-NTA-V200                           OBJECT IDENTIFIER ::= { hh3cProductId 2856 }
hh3cCSAP-NTA-V1000                          OBJECT IDENTIFIER ::= { hh3cProductId 2857 }
hh3cADC1070                                 OBJECT IDENTIFIER ::= { hh3cProductId 2858 }
hh3cADC5010                                 OBJECT IDENTIFIER ::= { hh3cProductId 2859 }
hh3cADC5030                                 OBJECT IDENTIFIER ::= { hh3cProductId 2860 }
hh3cS6850-56HF-G                            OBJECT IDENTIFIER ::= { hh3cProductId 2861 }
hh3cS6805-56HF-G                            OBJECT IDENTIFIER ::= { hh3cProductId 2862 }
hh3cS1850V2-28P-HPWR-EI                     OBJECT IDENTIFIER ::= { hh3cProductId 2863 }
hh3cS1850V2-28P-EI                          OBJECT IDENTIFIER ::= { hh3cProductId 2864 }
hh3cS1850V2-52P-EI                          OBJECT IDENTIFIER ::= { hh3cProductId 2865 }
hh3cWA6322H-HI                              OBJECT IDENTIFIER ::= { hh3cProductId 2866 }
hh3cWA6338-HI                               OBJECT IDENTIFIER ::= { hh3cProductId 2867 }
hh3cWA6320S-E                               OBJECT IDENTIFIER ::= { hh3cProductId 2868 }
hh3cSecCenter-X6010-S                       OBJECT IDENTIFIER ::= { hh3cProductId 2869 }
hh3cSecPath-D2000-G510                      OBJECT IDENTIFIER ::= { hh3cProductId 2870 }
hh3cSecPath-A2000-G510                      OBJECT IDENTIFIER ::= { hh3cProductId 2871 }
hh3cSecPath-W2000-G510                      OBJECT IDENTIFIER ::= { hh3cProductId 2872 }
hh3cSecPath-GAP2000-G510                    OBJECT IDENTIFIER ::= { hh3cProductId 2873 }
hh3cSecPath-SysScan-G510                    OBJECT IDENTIFIER ::= { hh3cProductId 2874 }
hh3cCR16000-M8                              OBJECT IDENTIFIER ::= { hh3cProductId 2875 }
hh3cCR16000-M16                             OBJECT IDENTIFIER ::= { hh3cProductId 2876 }
hh3cS9850-32H-G                             OBJECT IDENTIFIER ::= { hh3cProductId 2877 }
hh3cS6805-56HT-G                            OBJECT IDENTIFIER ::= { hh3cProductId 2878 }
hh3cWX2580X                                 OBJECT IDENTIFIER ::= { hh3cProductId 2879 }
hh3cS5538C-PWR-EI-D                         OBJECT IDENTIFIER ::= { hh3cProductId 2880 }
hh3cS5538F-EI-D                             OBJECT IDENTIFIER ::= { hh3cProductId 2881 }
hh3cS5554C-EI-D-AC                          OBJECT IDENTIFIER ::= { hh3cProductId 2882 }
hh3cS5120V3-28P-HPWR-LI                     OBJECT IDENTIFIER ::= { hh3cProductId 2883 }
hh3cS5120V3-12TP-HPWR-LI                    OBJECT IDENTIFIER ::= { hh3cProductId 2884 }
hh3cS3100V3-28TP-PWR-EI-AC                  OBJECT IDENTIFIER ::= { hh3cProductId 2885 }
hh3cS5130S-28S-HPWR-EI-AC                   OBJECT IDENTIFIER ::= { hh3cProductId 2886 }
hh3cS5120V3-28S-HPWR-LI                     OBJECT IDENTIFIER ::= { hh3cProductId 2887 }
hh3cS5120V3-10P-LI                          OBJECT IDENTIFIER ::= { hh3cProductId 2888 }
hh3cS5120V3-10P-SI                          OBJECT IDENTIFIER ::= { hh3cProductId 2889 }
hh3cMS4320V3-28P-PWR                        OBJECT IDENTIFIER ::= { hh3cProductId 2890 }
hh3cWS5820-10P-WiNet                        OBJECT IDENTIFIER ::= { hh3cProductId 2891 }
hh3cS5130S-28P-HPWR-EI-AC                   OBJECT IDENTIFIER ::= { hh3cProductId 2892 }
hh3cMS4320V3-10P                            OBJECT IDENTIFIER ::= { hh3cProductId 2893 }
hh3cS5120V3-10P-PWR-LI                      OBJECT IDENTIFIER ::= { hh3cProductId 2894 }
hh3cMS4320V3-20P-PWR                        OBJECT IDENTIFIER ::= { hh3cProductId 2895 }
hh3cS6550X-56HF-HI                          OBJECT IDENTIFIER ::= { hh3cProductId 2896 }
hh3cS6880-48Y8C                             OBJECT IDENTIFIER ::= { hh3cProductId 2897 }
hh3cS6880-48X8C                             OBJECT IDENTIFIER ::= { hh3cProductId 2898 }
hh3cSecPath-DA2020                          OBJECT IDENTIFIER ::= { hh3cProductId 2899 }
hh3cSecPath-DM2030-D                        OBJECT IDENTIFIER ::= { hh3cProductId 2900 }
hh3cSecPath-DLP2020                         OBJECT IDENTIFIER ::= { hh3cProductId 2901 }
hh3cSecPath-DE2020                          OBJECT IDENTIFIER ::= { hh3cProductId 2902 }
hh3cSecPath-DE2010                          OBJECT IDENTIFIER ::= { hh3cProductId 2903 }
hh3cSecPath-DF2010                          OBJECT IDENTIFIER ::= { hh3cProductId 2904 }
hh3cSecPath-DLP2030                         OBJECT IDENTIFIER ::= { hh3cProductId 2905 }
hh3cSecPath-DM2020-D                        OBJECT IDENTIFIER ::= { hh3cProductId 2906 }
hh3cSecPath-DM2030-S                        OBJECT IDENTIFIER ::= { hh3cProductId 2907 }
hh3cSecPath-DM2010-S                        OBJECT IDENTIFIER ::= { hh3cProductId 2908 }
hh3cSecPath-DF2020                          OBJECT IDENTIFIER ::= { hh3cProductId 2909 }
hh3cSecPath-DF2030                          OBJECT IDENTIFIER ::= { hh3cProductId 2910 }
hh3cSecPath-DM2010-D                        OBJECT IDENTIFIER ::= { hh3cProductId 2911 }
hh3cSecPath-DLP2050                         OBJECT IDENTIFIER ::= { hh3cProductId 2912 }
hh3cSecPath-DM2020-S                        OBJECT IDENTIFIER ::= { hh3cProductId 2913 }
hh3cS5554S-EI-D-DP                          OBJECT IDENTIFIER ::= { hh3cProductId 2914 }
hh3cS5590-28P8XC-EI                         OBJECT IDENTIFIER ::= { hh3cProductId 2915 }
hh3cS5590-48P6XC-EI                         OBJECT IDENTIFIER ::= { hh3cProductId 2916 }
hh3cS5536F-EI-D-DP                          OBJECT IDENTIFIER ::= { hh3cProductId 2917 }
hh3cF1000-K1000                             OBJECT IDENTIFIER ::= { hh3cProductId 2918 }
hh3cMSR3610E-X1                             OBJECT IDENTIFIER ::= { hh3cProductId 2919 }
hh3cMSR3610E-X1-DP                          OBJECT IDENTIFIER ::= { hh3cProductId 2920 }
hh3cS6520X-54HF-HI                          OBJECT IDENTIFIER ::= { hh3cProductId 2921 }
hh3cS6520X-30HF-EI                          OBJECT IDENTIFIER ::= { hh3cProductId 2922 }
hh3cS6520X-54HF-EI                          OBJECT IDENTIFIER ::= { hh3cProductId 2923 }
hh3cS6520X-30HF-HI                          OBJECT IDENTIFIER ::= { hh3cProductId 2924 }
hh3cMSR1004S-5G                             OBJECT IDENTIFIER ::= { hh3cProductId 2925 }
hh3cMSR2600-15-X1                           OBJECT IDENTIFIER ::= { hh3cProductId 2926 }
hh3cSecCenter-X6030                         OBJECT IDENTIFIER ::= { hh3cProductId 2927 }
hh3cUS310-P                                 OBJECT IDENTIFIER ::= { hh3cProductId 2928 }
hh3cUS310                                   OBJECT IDENTIFIER ::= { hh3cProductId 2929 }
hh3cS1850V2-10P-PWR-EI                      OBJECT IDENTIFIER ::= { hh3cProductId 2930 }
hh3cS1850V2-9P-EI                           OBJECT IDENTIFIER ::= { hh3cProductId 2931 }
hh3cS1850V2-10P-EI                          OBJECT IDENTIFIER ::= { hh3cProductId 2932 }
hh3cICG2000H                                OBJECT IDENTIFIER ::= { hh3cProductId 2933 }
hh3cICG2000H-DC                             OBJECT IDENTIFIER ::= { hh3cProductId 2934 }
hh3cICG3000H-DP                             OBJECT IDENTIFIER ::= { hh3cProductId 2935 }
hh3cMSR2660-XS                              OBJECT IDENTIFIER ::= { hh3cProductId 2936 }
hh3cICG3000H-DP-DC                          OBJECT IDENTIFIER ::= { hh3cProductId 2937 }
hh3cMSR2600-12X-WiNet                       OBJECT IDENTIFIER ::= { hh3cProductId 2938 }
hh3cMSR1008                                 OBJECT IDENTIFIER ::= { hh3cProductId 2939 }
hh3cMSR2630E-X1                             OBJECT IDENTIFIER ::= { hh3cProductId 2940 }
hh3cMSR2680-XS                              OBJECT IDENTIFIER ::= { hh3cProductId 2941 }
hh3cMSR2610-13X-WiNet                       OBJECT IDENTIFIER ::= { hh3cProductId 2942 }
hh3cT1000-AI-65-Context                     OBJECT IDENTIFIER ::= { hh3cProductId 2945 }
hh3cT1000-AI-25                             OBJECT IDENTIFIER ::= { hh3cProductId 2946 }
hh3cT1000-AI-35                             OBJECT IDENTIFIER ::= { hh3cProductId 2947 }
hh3cT1000-AI-35-Context                     OBJECT IDENTIFIER ::= { hh3cProductId 2948 }
hh3cT1000-AI-25-Context                     OBJECT IDENTIFIER ::= { hh3cProductId 2949 }
hh3cT1000-AI-65                             OBJECT IDENTIFIER ::= { hh3cProductId 2950 }
hh3cT1000-AI-55                             OBJECT IDENTIFIER ::= { hh3cProductId 2951 }
hh3cT1000-AI-55-Context                     OBJECT IDENTIFIER ::= { hh3cProductId 2952 }
hh3cSecPath-GAP2000-BI                      OBJECT IDENTIFIER ::= { hh3cProductId 2953 }
hh3cWA6528i                                 OBJECT IDENTIFIER ::= { hh3cProductId 2954 }
hh3cS10512X-G                               OBJECT IDENTIFIER ::= { hh3cProductId 2955 }
hh3cS10506X-G                               OBJECT IDENTIFIER ::= { hh3cProductId 2956 }
hh3cS7506X-X                                OBJECT IDENTIFIER ::= { hh3cProductId 2957 }
hh3cS7510X-X                                OBJECT IDENTIFIER ::= { hh3cProductId 2958 }
hh3cL1000-AK325-Context                     OBJECT IDENTIFIER ::= { hh3cProductId 2959 }
hh3cL1000-AK325                             OBJECT IDENTIFIER ::= { hh3cProductId 2960 }
hh3cL1000-AK315-Context                     OBJECT IDENTIFIER ::= { hh3cProductId 2961 }
hh3cL1000-AK315                             OBJECT IDENTIFIER ::= { hh3cProductId 2962 }
hh3cSecPath-DS2000-MGT                      OBJECT IDENTIFIER ::= { hh3cProductId 2963 }
hh3cF1000-AK9210                            OBJECT IDENTIFIER ::= { hh3cProductId 2964 }
hh3cF1000-SASE100                           OBJECT IDENTIFIER ::= { hh3cProductId 2965 }
hh3cF1000-AK9110                            OBJECT IDENTIFIER ::= { hh3cProductId 2966 }
hh3cF1000-SASE200                           OBJECT IDENTIFIER ::= { hh3cProductId 2967 }
hh3cF5000-CN60-Context                      OBJECT IDENTIFIER ::= { hh3cProductId 2968 }
hh3cF5000-CN60                              OBJECT IDENTIFIER ::= { hh3cProductId 2969 }
hh3cF5000-CN30                              OBJECT IDENTIFIER ::= { hh3cProductId 2970 }
hh3cF5000-CN30-Context                      OBJECT IDENTIFIER ::= { hh3cProductId 2971 }
hh3cF5000-CN60-D                            OBJECT IDENTIFIER ::= { hh3cProductId 2972 }
hh3cF5000-CN60-D-Context                    OBJECT IDENTIFIER ::= { hh3cProductId 2973 }
hh3cMS4100V2-10P-EI                         OBJECT IDENTIFIER ::= { hh3cProductId 2974 }
hh3cMS4100V2-28P-HPWR-EI                    OBJECT IDENTIFIER ::= { hh3cProductId 2975 }
hh3cMS4100V2-52P-EI                         OBJECT IDENTIFIER ::= { hh3cProductId 2976 }
hh3cMS4100V2-28P-EI                         OBJECT IDENTIFIER ::= { hh3cProductId 2977 }
hh3cMS4100V2-10P-HPWR-EI                    OBJECT IDENTIFIER ::= { hh3cProductId 2978 }
hh3cMS4100V2-52P-PWR-EI                     OBJECT IDENTIFIER ::= { hh3cProductId 2979 }
hh3cLSPM6FWDB-Context                       OBJECT IDENTIFIER ::= { hh3cProductId 2980 }
hh3cLSPM6FWDB                               OBJECT IDENTIFIER ::= { hh3cProductId 2981 }
hh3cIE4320-12P-PWR-M-NAT                    OBJECT IDENTIFIER ::= { hh3cProductId 2982 }
hh3cWA6338                                  OBJECT IDENTIFIER ::= { hh3cProductId 2983 }
hh3cWA6638i                                 OBJECT IDENTIFIER ::= { hh3cProductId 2984 }
hh3cWA6628XM                                OBJECT IDENTIFIER ::= { hh3cProductId 2985 }
hh3cWA6330                                  OBJECT IDENTIFIER ::= { hh3cProductId 2986 }
hh3cWA6628X                                 OBJECT IDENTIFIER ::= { hh3cProductId 2987 }
hh3cWA6320-JP                               OBJECT IDENTIFIER ::= { hh3cProductId 2988 }
hh3cWA6320-SI                               OBJECT IDENTIFIER ::= { hh3cProductId 2989 }
hh3cWA6320                                  OBJECT IDENTIFIER ::= { hh3cProductId 2990 }
hh3cWA6526H                                 OBJECT IDENTIFIER ::= { hh3cProductId 2991 }
hh3cWA6630X-JP                              OBJECT IDENTIFIER ::= { hh3cProductId 2992 }
hh3cWA6636                                  OBJECT IDENTIFIER ::= { hh3cProductId 2993 }
hh3cWA6530                                  OBJECT IDENTIFIER ::= { hh3cProductId 2994 }
hh3cWA6322H                                 OBJECT IDENTIFIER ::= { hh3cProductId 2995 }
hh3cWA6320H-HI                              OBJECT IDENTIFIER ::= { hh3cProductId 2996 }
hh3cWA6322                                  OBJECT IDENTIFIER ::= { hh3cProductId 2997 }
hh3cWA6320H                                 OBJECT IDENTIFIER ::= { hh3cProductId 2998 }
hh3cWA6320H-XEPON                           OBJECT IDENTIFIER ::= { hh3cProductId 2999 }
hh3cWA6638-JP                               OBJECT IDENTIFIER ::= { hh3cProductId 3000 }
hh3cMSR3600-51-G-DP                         OBJECT IDENTIFIER ::= { hh3cProductId 3001 }
hh3cMSR3600-28-G-DP                         OBJECT IDENTIFIER ::= { hh3cProductId 3002 }
hh3cE510C-X-PWR-F                           OBJECT IDENTIFIER ::= { hh3cProductId 3003 }
hh3cE516C-X-PWR-F                           OBJECT IDENTIFIER ::= { hh3cProductId 3004 }
hh3cS5130S-52S-HI-EDF                       OBJECT IDENTIFIER ::= { hh3cProductId 3005 }
hh3cNFNX3-HDB3080-Context                   OBJECT IDENTIFIER ::= { hh3cProductId 3006 }
hh3cNFNX3-HDB3280                           OBJECT IDENTIFIER ::= { hh3cProductId 3007 }
hh3cNFNX3-HDB1780                           OBJECT IDENTIFIER ::= { hh3cProductId 3008 }
hh3cNFNX5-HD5280-Context                    OBJECT IDENTIFIER ::= { hh3cProductId 3009 }
hh3cNFNX3-HDB1080                           OBJECT IDENTIFIER ::= { hh3cProductId 3010 }
hh3cNFNX3-HDB1480                           OBJECT IDENTIFIER ::= { hh3cProductId 3011 }
hh3cNFNX5-HD6480                            OBJECT IDENTIFIER ::= { hh3cProductId 3012 }
hh3cNFNX3-HDB3280-Context                   OBJECT IDENTIFIER ::= { hh3cProductId 3013 }
hh3cNFNX3-HDB3080                           OBJECT IDENTIFIER ::= { hh3cProductId 3014 }
hh3cNFNX5-T6280                             OBJECT IDENTIFIER ::= { hh3cProductId 3015 }
hh3cNFNX3-HDB1180                           OBJECT IDENTIFIER ::= { hh3cProductId 3016 }
hh3cNFNX3-HDB1780-Context                   OBJECT IDENTIFIER ::= { hh3cProductId 3017 }
hh3cNFNX5-HD5280                            OBJECT IDENTIFIER ::= { hh3cProductId 3018 }
hh3cNFNX5-HD6480-Context                    OBJECT IDENTIFIER ::= { hh3cProductId 3019 }
hh3cNFNX5-T6280-Context                     OBJECT IDENTIFIER ::= { hh3cProductId 3020 }
hh3cvADC1000                                OBJECT IDENTIFIER ::= { hh3cProductId 3021 }
hh3cER3200G3                                OBJECT IDENTIFIER ::= { hh3cProductId 3022 }
hh3cUR7206                                  OBJECT IDENTIFIER ::= { hh3cProductId 3023 }
hh3cER3208G3                                OBJECT IDENTIFIER ::= { hh3cProductId 3024 }
hh3cER5200G3                                OBJECT IDENTIFIER ::= { hh3cProductId 3025 }
hh3cER3260G3                                OBJECT IDENTIFIER ::= { hh3cProductId 3026 }
hh3cS5136S-PWR-EI-D-G                       OBJECT IDENTIFIER ::= { hh3cProductId 3027 }
hh3cS5136F-EI-D-G                           OBJECT IDENTIFIER ::= { hh3cProductId 3028 }
hh3cS5136S-EI-D-G                           OBJECT IDENTIFIER ::= { hh3cProductId 3029 }
hh3cS5120V3-30MS-UPWR-DP-EI                 OBJECT IDENTIFIER ::= { hh3cProductId 3030 }
hh3cS5554S-EI-D-G                           OBJECT IDENTIFIER ::= { hh3cProductId 3031 }
hh3cS5136F-EI-D                             OBJECT IDENTIFIER ::= { hh3cProductId 3032 }
hh3cS5552F-EI-D-G                           OBJECT IDENTIFIER ::= { hh3cProductId 3033 }
hh3cUniCLoud-vFW2000-Context                OBJECT IDENTIFIER ::= { hh3cProductId 3034 }
hh3cUniCLoud-vFW1000                        OBJECT IDENTIFIER ::= { hh3cProductId 3035 }
hh3cUniCLoud-vFW2000                        OBJECT IDENTIFIER ::= { hh3cProductId 3036 }
hh3cUniCLoud-vFW1000-Context                OBJECT IDENTIFIER ::= { hh3cProductId 3037 }
hh3cS12500R-2XL                             OBJECT IDENTIFIER ::= { hh3cProductId 3038 }
hh3cADCNX5-HDB300-Context                   OBJECT IDENTIFIER ::= { hh3cProductId 3039 }
hh3cADCNX5-HD2000-Context                   OBJECT IDENTIFIER ::= { hh3cProductId 3040 }
hh3cADCNX5-HD1000-Context                   OBJECT IDENTIFIER ::= { hh3cProductId 3041 }
hh3cADCNX5-HDB300                           OBJECT IDENTIFIER ::= { hh3cProductId 3042 }
hh3cADCNX5-HD2000                           OBJECT IDENTIFIER ::= { hh3cProductId 3043 }
hh3cADCNX5-HD1000                           OBJECT IDENTIFIER ::= { hh3cProductId 3044 }
hh3cADCNX5-HD4000                           OBJECT IDENTIFIER ::= { hh3cProductId 3045 }
hh3cADCNX5-HD600-Context                    OBJECT IDENTIFIER ::= { hh3cProductId 3046 }
hh3cADCNX5-HD600                            OBJECT IDENTIFIER ::= { hh3cProductId 3047 }
hh3cADCNX5-HD4000-Context                   OBJECT IDENTIFIER ::= { hh3cProductId 3048 }
hh3cUniCloud-vLB1000                        OBJECT IDENTIFIER ::= { hh3cProductId 3049 }
hh3cWA6528X-E                               OBJECT IDENTIFIER ::= { hh3cProductId 3050 }
hh3cWTU630-IOT                              OBJECT IDENTIFIER ::= { hh3cProductId 3051 }
hh3cS3210S-16P-OLT                          OBJECT IDENTIFIER ::= { hh3cProductId 3052 }
hh3cS3210S-8P-OLT                           OBJECT IDENTIFIER ::= { hh3cProductId 3053 }
hh3cS7006ET                                 OBJECT IDENTIFIER ::= { hh3cProductId 3054 }
hh3cS7003ET                                 OBJECT IDENTIFIER ::= { hh3cProductId 3055 }
hh3cMSR810-SI                               OBJECT IDENTIFIER ::= { hh3cProductId 3056 }
hh3cMSR810-LM-EA                            OBJECT IDENTIFIER ::= { hh3cProductId 3057 }
hh3cMSR810-LM-SI                            OBJECT IDENTIFIER ::= { hh3cProductId 3058 }
hh3cMSR810-EI                               OBJECT IDENTIFIER ::= { hh3cProductId 3059 }
hh3cS12516E                                 OBJECT IDENTIFIER ::= { hh3cProductId 3060 }
hh3cICG2000D-EI                             OBJECT IDENTIFIER ::= { hh3cProductId 3061 }
hh3cS9820-8C-SAN                            OBJECT IDENTIFIER ::= { hh3cProductId 3065 }
hh3cS6850-56HF-SAN                          OBJECT IDENTIFIER ::= { hh3cProductId 3066 }
hh3cBBU5200                                 OBJECT IDENTIFIER ::= { hh3cProductId 3067 }
hh3cM9000-AI-E4-Context                     OBJECT IDENTIFIER ::= { hh3cProductId 3068 }
hh3cWA6320-HI                               OBJECT IDENTIFIER ::= { hh3cProductId 3069 }
hh3cWX2580X-LI                              OBJECT IDENTIFIER ::= { hh3cProductId 3070 }
hh3cE512C-MX-PWR-F                          OBJECT IDENTIFIER ::= { hh3cProductId 3071 }
hh3cE520C-MX-PWR-F                          OBJECT IDENTIFIER ::= { hh3cProductId 3072 }
hh3cE520C-MX-F                              OBJECT IDENTIFIER ::= { hh3cProductId 3073 }
hh3cE512C-X-PWR-F                           OBJECT IDENTIFIER ::= { hh3cProductId 3074 }
hh3cE512C-X-F                               OBJECT IDENTIFIER ::= { hh3cProductId 3075 }
hh3cE512C-MX-F                              OBJECT IDENTIFIER ::= { hh3cProductId 3076 }
hh3cE508C-X-PWR-F                           OBJECT IDENTIFIER ::= { hh3cProductId 3077 }
hh3cE552C-X-PS-F                            OBJECT IDENTIFIER ::= { hh3cProductId 3078 }
hh3cS6520X-54HC-UPWR-EI                     OBJECT IDENTIFIER ::= { hh3cProductId 3079 }
hh3cUS1750-10P-S                            OBJECT IDENTIFIER ::= { hh3cProductId 3080 }
hh3cUS536-F-S                               OBJECT IDENTIFIER ::= { hh3cProductId 3081 }
hh3cWAS1760-10P-S                           OBJECT IDENTIFIER ::= { hh3cProductId 3082 }
hh3cWAS1760-10P-HPWR-S                      OBJECT IDENTIFIER ::= { hh3cProductId 3083 }
hh3cUS1750-10P-HPWR-S                       OBJECT IDENTIFIER ::= { hh3cProductId 3084 }
hh3cLIS-vFW1000-V2                          OBJECT IDENTIFIER ::= { hh3cProductId 3085 }
hh3cLIS-vFW1000-V4                          OBJECT IDENTIFIER ::= { hh3cProductId 3086 }
hh3cLIS-vFW1000-V8                          OBJECT IDENTIFIER ::= { hh3cProductId 3087 }
hh3cS5170-36F-EI-DP                         OBJECT IDENTIFIER ::= { hh3cProductId 3088 }
hh3cS5170-54S-EI-DP                         OBJECT IDENTIFIER ::= { hh3cProductId 3089 }
hh3cF100-C-A1                               OBJECT IDENTIFIER ::= { hh3cProductId 3090 }
hh3cF100-C-A2                               OBJECT IDENTIFIER ::= { hh3cProductId 3091 }
hh3cUS1750-52P-PWR                          OBJECT IDENTIFIER ::= { hh3cProductId 3092 }
hh3cWAS6108                                 OBJECT IDENTIFIER ::= { hh3cProductId 3093 }
hh3cWAS1760-52P                             OBJECT IDENTIFIER ::= { hh3cProductId 3094 }
hh3cUS1750-28P-PWR                          OBJECT IDENTIFIER ::= { hh3cProductId 3095 }
hh3cUS528-X                                 OBJECT IDENTIFIER ::= { hh3cProductId 3096 }
hh3cUS328                                   OBJECT IDENTIFIER ::= { hh3cProductId 3097 }
hh3cUS1750-28P                              OBJECT IDENTIFIER ::= { hh3cProductId 3098 }
hh3cWAS1760-20P-HPWR                        OBJECT IDENTIFIER ::= { hh3cProductId 3099 }
hh3cUS552-X                                 OBJECT IDENTIFIER ::= { hh3cProductId 3100 }
hh3cWAS6148                                 OBJECT IDENTIFIER ::= { hh3cProductId 3101 }
hh3cUS528                                   OBJECT IDENTIFIER ::= { hh3cProductId 3102 }
hh3cUS1750-52P                              OBJECT IDENTIFIER ::= { hh3cProductId 3103 }
hh3cWAS1760-28P-HPWR                        OBJECT IDENTIFIER ::= { hh3cProductId 3104 }
hh3cWAS6124                                 OBJECT IDENTIFIER ::= { hh3cProductId 3105 }
hh3cWAS1760-28P                             OBJECT IDENTIFIER ::= { hh3cProductId 3106 }
hh3cWAS6124-X                               OBJECT IDENTIFIER ::= { hh3cProductId 3107 }
hh3cUS1750-28P-HPWR                         OBJECT IDENTIFIER ::= { hh3cProductId 3108 }
hh3cUS1750-20P-HPWR                         OBJECT IDENTIFIER ::= { hh3cProductId 3109 }
hh3cUS552                                   OBJECT IDENTIFIER ::= { hh3cProductId 3110 }
hh3cUS328-P                                 OBJECT IDENTIFIER ::= { hh3cProductId 3111 }
hh3cMSG370-12-PWR                           OBJECT IDENTIFIER ::= { hh3cProductId 3112 }
hh3cMSG370-16E-X                            OBJECT IDENTIFIER ::= { hh3cProductId 3113 }
hh3cMSG370-16                               OBJECT IDENTIFIER ::= { hh3cProductId 3114 }
hh3cMSG370-32-X                             OBJECT IDENTIFIER ::= { hh3cProductId 3115 }
hh3cS12516G-EF                              OBJECT IDENTIFIER ::= { hh3cProductId 3116 }
hh3cF5000-CN-G85-Context                    OBJECT IDENTIFIER ::= { hh3cProductId 3117 }
hh3cF5000-CN-G55                            OBJECT IDENTIFIER ::= { hh3cProductId 3118 }
hh3cF5000-CN-G65-Context                    OBJECT IDENTIFIER ::= { hh3cProductId 3119 }
hh3cF5000-CN-G65                            OBJECT IDENTIFIER ::= { hh3cProductId 3120 }
hh3cF5000-CN-G55-Context                    OBJECT IDENTIFIER ::= { hh3cProductId 3121 }
hh3cF5000-CN-G85                            OBJECT IDENTIFIER ::= { hh3cProductId 3122 }
hh3cS12508G-EF                              OBJECT IDENTIFIER ::= { hh3cProductId 3123 }
hh3cS3600V3-54TP-EI-DC                      OBJECT IDENTIFIER ::= { hh3cProductId 3124 }
hh3cUS328S-24G-4SFP-Switch                  OBJECT IDENTIFIER ::= { hh3cProductId 3125 }
hh3cUS528S-24G-4SFP-Switch                  OBJECT IDENTIFIER ::= { hh3cProductId 3126 }
hh3cUS552S-X-48G-2SFP-2SFPPlus-Switch       OBJECT IDENTIFIER ::= { hh3cProductId 3127 }
hh3cUS328-P-24G-PoEPlus-4SFP-Switch         OBJECT IDENTIFIER ::= { hh3cProductId 3128 }
hh3cUS528S-X-24G-2SFP-2SFPPlus-Switch       OBJECT IDENTIFIER ::= { hh3cProductId 3129 }
hh3cUS552S-48G-4SFP-Switch                  OBJECT IDENTIFIER ::= { hh3cProductId 3130 }
hh3cWA6528i-JP                              OBJECT IDENTIFIER ::= { hh3cProductId 3131 }
hh3cS9855-24B8D                             OBJECT IDENTIFIER ::= { hh3cProductId 3132 }
hh3cWA6526                                  OBJECT IDENTIFIER ::= { hh3cProductId 3133 }
hh3cWA6526E                                 OBJECT IDENTIFIER ::= { hh3cProductId 3134 }
hh3cWA6522                                  OBJECT IDENTIFIER ::= { hh3cProductId 3135 }
hh3cWA6520H-EGPON                           OBJECT IDENTIFIER ::= { hh3cProductId 3136 }
hh3cWA6520-C                                OBJECT IDENTIFIER ::= { hh3cProductId 3137 }
hh3cWA6520-HI                               OBJECT IDENTIFIER ::= { hh3cProductId 3138 }
hh3cWA6522-C                                OBJECT IDENTIFIER ::= { hh3cProductId 3139 }
hh3cWA6522H-HI                              OBJECT IDENTIFIER ::= { hh3cProductId 3140 }
hh3cWA6510E-T                               OBJECT IDENTIFIER ::= { hh3cProductId 3141 }
hh3cP3116                                   OBJECT IDENTIFIER ::= { hh3cProductId 3142 }
hh3cP3108-C                                 OBJECT IDENTIFIER ::= { hh3cProductId 3143 }
hh3cP3500                                   OBJECT IDENTIFIER ::= { hh3cProductId 3144 }
hh3cS10508X-G                               OBJECT IDENTIFIER ::= { hh3cProductId 3145 }
hh3cF1005-GM                                OBJECT IDENTIFIER ::= { hh3cProductId 3146 }
hh3cWA6520                                  OBJECT IDENTIFIER ::= { hh3cProductId 3147 }
hh3c-SecCenter-X6025                        OBJECT IDENTIFIER ::= { hh3cProductId 3148 }
hh3c-SecCenter-X6015                        OBJECT IDENTIFIER ::= { hh3cProductId 3149 }
hh3cMSR2600-15-X1-T                         OBJECT IDENTIFIER ::= { hh3cProductId 3150 }
hh3cMSR810-LM-EI                            OBJECT IDENTIFIER ::= { hh3cProductId 3151 }
hh3cS5130S-54S-HI-G                         OBJECT IDENTIFIER ::= { hh3cProductId 3152 }
hh3cS5130S-36S-HI-G                         OBJECT IDENTIFIER ::= { hh3cProductId 3153 }
hh3cS5130S-36F-HI-G                         OBJECT IDENTIFIER ::= { hh3cProductId 3154 }
hh3cS5130S-54S-PWR-HI-G                     OBJECT IDENTIFIER ::= { hh3cProductId 3155 }
hh3cS5130S-36S-PWR-HI-G                     OBJECT IDENTIFIER ::= { hh3cProductId 3156 }
hh3cS5130S-54S-EI-G                         OBJECT IDENTIFIER ::= { hh3cProductId 3157 }
hh3cS5130S-36S-EI-G                         OBJECT IDENTIFIER ::= { hh3cProductId 3158 }
hh3cS5130S-36F-EI-G                         OBJECT IDENTIFIER ::= { hh3cProductId 3159 }
hh3cS5130S-54S-PWR-EI-G                     OBJECT IDENTIFIER ::= { hh3cProductId 3160 }
hh3cS5130S-36S-PWR-EI-G                     OBJECT IDENTIFIER ::= { hh3cProductId 3161 }
hh3cNFNX3-HDD510-4G                         OBJECT IDENTIFIER ::= { hh3cProductId 3162 }
hh3cT1000-AK335-Context                     OBJECT IDENTIFIER ::= { hh3cProductId 3163 }
hh3cT1000-AK335                             OBJECT IDENTIFIER ::= { hh3cProductId 3164 }
hh3c-SecPath-GAP3000-SE                     OBJECT IDENTIFIER ::= { hh3cProductId 3165 }
hh3c-SecPath-GAP3000-AE                     OBJECT IDENTIFIER ::= { hh3cProductId 3166 }
hh3c-SecPath-GAP3000-BE                     OBJECT IDENTIFIER ::= { hh3cProductId 3167 }
hh3c-SecPath-A2000-AK601                    OBJECT IDENTIFIER ::= { hh3cProductId 3168 }
hh3c-SecPath-GAP2000-AK820L                 OBJECT IDENTIFIER ::= { hh3cProductId 3169 }
hh3cMSR1104S-W-CAT6                         OBJECT IDENTIFIER ::= { hh3cProductId 3170 }
hh3cMSR1104S-W                              OBJECT IDENTIFIER ::= { hh3cProductId 3171 }
hh3cS5552F-EI-D-G-H1                        OBJECT IDENTIFIER ::= { hh3cProductId 3172 }
hh3cS9820-64H-H1                            OBJECT IDENTIFIER ::= { hh3cProductId 3173 }
hh3cS6805-54HF-H1                           OBJECT IDENTIFIER ::= { hh3cProductId 3174 }
hh3cS6805-54HT-H1                           OBJECT IDENTIFIER ::= { hh3cProductId 3175 }
hh3cS9850-32H-H1                            OBJECT IDENTIFIER ::= { hh3cProductId 3176 }
hh3cS9850-4C-H1                             OBJECT IDENTIFIER ::= { hh3cProductId 3177 }
hh3cS5570S-28S-HPWR-EI-A                    OBJECT IDENTIFIER ::= { hh3cProductId 3178 }
hh3cS5570S-54S-PWR-EI-A                     OBJECT IDENTIFIER ::= { hh3cProductId 3179 }
hh3cS5580X-48T4YC-HI                        OBJECT IDENTIFIER ::= { hh3cProductId 3180 }
hh3cS5580X-32T4X4YC-HI                      OBJECT IDENTIFIER ::= { hh3cProductId 3181 }
hh3cS5580X-48S4YC-HI                        OBJECT IDENTIFIER ::= { hh3cProductId 3182 }
hh3cS5580X-32S8R4X4YC-HI                    OBJECT IDENTIFIER ::= { hh3cProductId 3183 }
hh3cS5580X-32P4X4YC-HI                      OBJECT IDENTIFIER ::= { hh3cProductId 3184 }
hh3cS5580X-48P4YC-HI                        OBJECT IDENTIFIER ::= { hh3cProductId 3185 }
hh3c-SecPath-F3200-I                        OBJECT IDENTIFIER ::= { hh3cProductId 3186 }
hh3c-SecPath-F3135-I                        OBJECT IDENTIFIER ::= { hh3cProductId 3187 }
hh3c-SecPath-A3135-I                        OBJECT IDENTIFIER ::= { hh3cProductId 3188 }
hh3c-SecPath-A3200-I                        OBJECT IDENTIFIER ::= { hh3cProductId 3189 }
hh3c-hh3cWA6520H                            OBJECT IDENTIFIER ::= { hh3cProductId 3190 }
hh3c-hh3cWX2880X                            OBJECT IDENTIFIER ::= { hh3cProductId 3191 }
hh3c-hh3cWX2860X                            OBJECT IDENTIFIER ::= { hh3cProductId 3192 }
hh3c-hh3cWX3840X                            OBJECT IDENTIFIER ::= { hh3cProductId 3193 }
hh3c-hh3cWX3820X                            OBJECT IDENTIFIER ::= { hh3cProductId 3194 }
hh3c-hh3cWX5860X                            OBJECT IDENTIFIER ::= { hh3cProductId 3195 }
hh3c-SecPath-ACG1000-AI-30                  OBJECT IDENTIFIER ::= { hh3cProductId 3196 }
hh3c-SecPath-ACG1000-AI-160                 OBJECT IDENTIFIER ::= { hh3cProductId 3197 }
hh3c-SecPath-ACG1000-AI-50                  OBJECT IDENTIFIER ::= { hh3cProductId 3198 }
hh3c-SecPath-ACG1000-T200                   OBJECT IDENTIFIER ::= { hh3cProductId 3199 }
hh3c-SecPath-ACG1000-AK2010                 OBJECT IDENTIFIER ::= { hh3cProductId 3200 }
hh3c-SecPath-ACG1000-AK2810                 OBJECT IDENTIFIER ::= { hh3cProductId 3201 }
hh3c-SecPath-ACG1000-AI-90                  OBJECT IDENTIFIER ::= { hh3cProductId 3202 }
hh3c-SecPath-ACG1000-AI-10                  OBJECT IDENTIFIER ::= { hh3cProductId 3203 }
hh3cFS5100-52F-EI-PS                        OBJECT IDENTIFIER ::= { hh3cProductId 3204 }
hh3cFS5100-20MS-PWR-EI                      OBJECT IDENTIFIER ::= { hh3cProductId 3205 }
hh3cFS5100-12S-PWR-EI                       OBJECT IDENTIFIER ::= { hh3cProductId 3206 }
hh3cFS5100-12S-EI                           OBJECT IDENTIFIER ::= { hh3cProductId 3207 }
hh3cFS5100-12MS-EI                          OBJECT IDENTIFIER ::= { hh3cProductId 3208 }
hh3cFS5100-12MS-PWR-EI                      OBJECT IDENTIFIER ::= { hh3cProductId 3209 }
hh3cFS5100-20MS-EI                          OBJECT IDENTIFIER ::= { hh3cProductId 3210 }
hh3cFS5100-8S-PWR-EI                        OBJECT IDENTIFIER ::= { hh3cProductId 3211 }
hh3c-SecPath-CCS8000                        OBJECT IDENTIFIER ::= { hh3cProductId 3212 }
hh3c-SecPath-AVG2000-BE                     OBJECT IDENTIFIER ::= { hh3cProductId 3213 }
hh3c-SecPath-CS8000-S                       OBJECT IDENTIFIER ::= { hh3cProductId 3214 }
hh3c-SecPath-BST8000                        OBJECT IDENTIFIER ::= { hh3cProductId 3215 }
hh3c-SecPath-KMS8000                        OBJECT IDENTIFIER ::= { hh3cProductId 3216 }
hh3c-SecPath-AVG2000-AE                     OBJECT IDENTIFIER ::= { hh3cProductId 3217 }
hh3c-SecPath-CS8000-A                       OBJECT IDENTIFIER ::= { hh3cProductId 3218 }
hh3cF1010-GM                                OBJECT IDENTIFIER ::= { hh3cProductId 3219 }
hh3cF1000-AI-03                             OBJECT IDENTIFIER ::= { hh3cProductId 3220 }
hh3chh3cMLag                                OBJECT IDENTIFIER ::= { hh3cProductId 3221 }
hh3cF5030-6GW-G                             OBJECT IDENTIFIER ::= { hh3cProductId 3222 }
hh3cF5030-6GW-G-Context                     OBJECT IDENTIFIER ::= { hh3cProductId 3223 }
hh3cF1000-T200-H1                           OBJECT IDENTIFIER ::= { hh3cProductId 3224 }
hh3cF1000-T200-H3                           OBJECT IDENTIFIER ::= { hh3cProductId 3225 }
hh3cF1003-L-C                               OBJECT IDENTIFIER ::= { hh3cProductId 3226 }
hh3cF1003-L-S                               OBJECT IDENTIFIER ::= { hh3cProductId 3227 }
hh3cF1000-Y300                              OBJECT IDENTIFIER ::= { hh3cProductId 3228 }
hh3cF1000-Y300-S                            OBJECT IDENTIFIER ::= { hh3cProductId 3229 }
hh3cF1000-Y500                              OBJECT IDENTIFIER ::= { hh3cProductId 3230 }
hh3cF1000-Y1000                             OBJECT IDENTIFIER ::= { hh3cProductId 3231 }
hh3cF1000-S1000                             OBJECT IDENTIFIER ::= { hh3cProductId 3232 }
hh3cNFNX3-HDD410                            OBJECT IDENTIFIER ::= { hh3cProductId 3233 }
hh3cNFNX3-HDD420                            OBJECT IDENTIFIER ::= { hh3cProductId 3234 }
hh3cNFNX3-HDB680                            OBJECT IDENTIFIER ::= { hh3cProductId 3235 }
hh3c-SecPath-ACG1000-AK2080                 OBJECT IDENTIFIER ::= { hh3cProductId 3236 }
hh3cWSG1840X                                OBJECT IDENTIFIER ::= { hh3cProductId 3237 }
hh3cWSG1812X-PWR                            OBJECT IDENTIFIER ::= { hh3cProductId 3238 }
hh3cWX2812X-PWR                             OBJECT IDENTIFIER ::= { hh3cProductId 3239 }
hh3cF1000-U1000                             OBJECT IDENTIFIER ::= { hh3cProductId 3240 }
hh3cF1000-U300                              OBJECT IDENTIFIER ::= { hh3cProductId 3241 }
hh3cF1000-U500                              OBJECT IDENTIFIER ::= { hh3cProductId 3242 }
hh3cIE4520-54S-C-SEC                        OBJECT IDENTIFIER ::= { hh3cProductId 3243 }
hh3cH3C-SecPath-M9000X-Context              OBJECT IDENTIFIER ::= { hh3cProductId 3244 }
hh3cT5030-G                                 OBJECT IDENTIFIER ::= { hh3cProductId 3245 }
hh3cT5030-G-Context                         OBJECT IDENTIFIER ::= { hh3cProductId 3246 }
hh3cMSR610                                  OBJECT IDENTIFIER ::= { hh3cProductId 3247 }
hh3cNS-SecPath-M9000-AI-X06                 OBJECT IDENTIFIER ::= { hh3cProductId 3248 }
hh3cNS-SecPath-M9000-AI-X10                 OBJECT IDENTIFIER ::= { hh3cProductId 3249 }
hh3cMSR3640-G                               OBJECT IDENTIFIER ::= { hh3cProductId 3250 }
hh3cS5008PV5-EI-S                           OBJECT IDENTIFIER ::= { hh3cProductId 3251 }
hh3cS5008PV5-EI-HPWR-S                      OBJECT IDENTIFIER ::= { hh3cProductId 3252 }
hh3cS5016PV5-EI-S                           OBJECT IDENTIFIER ::= { hh3cProductId 3253 }
hh3cM9000-AD6-Context                       OBJECT IDENTIFIER ::= { hh3cProductId 3254 }
hh3cL5000-AD920                             OBJECT IDENTIFIER ::= { hh3cProductId 3255 }
hh3cNFNX3-HDD410-4G                         OBJECT IDENTIFIER ::= { hh3cProductId 3256 }
hh3cNFNX3-HDD420-4G                         OBJECT IDENTIFIER ::= { hh3cProductId 3257 }
hh3cL5000-AD930                             OBJECT IDENTIFIER ::= { hh3cProductId 3258 }
hh3cS6530X-48Y8C                            OBJECT IDENTIFIER ::= { hh3cProductId 3259 }
hh3cS6530X-48X8C                            OBJECT IDENTIFIER ::= { hh3cProductId 3260 }
hh3cS6530X-24Y8C                            OBJECT IDENTIFIER ::= { hh3cProductId 3261 }
hh3cS6530X-24X8C                            OBJECT IDENTIFIER ::= { hh3cProductId 3262 }
hh3cL5000-CN530                             OBJECT IDENTIFIER ::= { hh3cProductId 3263 }
hh3cL5060-G-Context                         OBJECT IDENTIFIER ::= { hh3cProductId 3264 }
hh3cL5060-G                                 OBJECT IDENTIFIER ::= { hh3cProductId 3265 }
hh3cL5000-CN530-Context                     OBJECT IDENTIFIER ::= { hh3cProductId 3266 }
hh3c-SecPath-ACG1000-S300                   OBJECT IDENTIFIER ::= { hh3cProductId 3267 }
hh3c-SecPath-ACG1000-S1000                  OBJECT IDENTIFIER ::= { hh3cProductId 3268 }
hh3c-SecPath-ACG1000-S500                   OBJECT IDENTIFIER ::= { hh3cProductId 3269 }

hh3cF1000-U300-S                            OBJECT IDENTIFIER ::= { hh3cProductId 3272 }
hh3cF1000-U300-C                            OBJECT IDENTIFIER ::= { hh3cProductId 3273 }
hh3cIE4320-N-F16G4-16GE-SFP-4SFP-Switch     OBJECT IDENTIFIER ::= { hh3cProductId 3274 }
hh3cIE4320-G-F16G4-16GE-SFP-4SFP-Switch     OBJECT IDENTIFIER ::= { hh3cProductId 3275 }
hh3cIE4320-N-G16-16SFP-Switch               OBJECT IDENTIFIER ::= { hh3cProductId 3276 }
hh3cIE4320-G-G16-16SFP-Switch               OBJECT IDENTIFIER ::= { hh3cProductId 3277 }
hh3cIE4320-Z-E24G4-24GE-4SFP-Switch         OBJECT IDENTIFIER ::= { hh3cProductId 3278 }
hh3cT6260-54C                               OBJECT IDENTIFIER ::= { hh3cProductId 3279 }
hh3cT6230-28P                               OBJECT IDENTIFIER ::= { hh3cProductId 3280 }
hh3cT6230-52P                               OBJECT IDENTIFIER ::= { hh3cProductId 3281 }
hh3c-SecPath-DM2030-S-V                     OBJECT IDENTIFIER ::= { hh3cProductId 3282 }
hh3c-SecPath-DLP2050-V                      OBJECT IDENTIFIER ::= { hh3cProductId 3283 }
hh3c-SecPath-DF2030-V                       OBJECT IDENTIFIER ::= { hh3cProductId 3284 }
hh3c-SecPath-DM2020-S-V                     OBJECT IDENTIFIER ::= { hh3cProductId 3285 }
hh3c-SecPath-DF2010-V                       OBJECT IDENTIFIER ::= { hh3cProductId 3286 }
hh3c-SecPath-DM2030-D-V                     OBJECT IDENTIFIER ::= { hh3cProductId 3287 }
hh3c-SecPath-DA2020-V                       OBJECT IDENTIFIER ::= { hh3cProductId 3288 }
hh3c-SecPath-DF2020-V                       OBJECT IDENTIFIER ::= { hh3cProductId 3289 }
hh3c-SecPath-DM2010-D-V                     OBJECT IDENTIFIER ::= { hh3cProductId 3290 }
hh3c-SecPath-DM2020-D-V                     OBJECT IDENTIFIER ::= { hh3cProductId 3291 }
hh3c-SecPath-DLP2020-V                      OBJECT IDENTIFIER ::= { hh3cProductId 3292 }
hh3c-SecPath-DE2020-V                       OBJECT IDENTIFIER ::= { hh3cProductId 3293 }
hh3c-SecPath-DM2010-S-V                     OBJECT IDENTIFIER ::= { hh3cProductId 3294 }
hh3c-SecPath-DE2010-V                       OBJECT IDENTIFIER ::= { hh3cProductId 3295 }
hh3c-SecPath-DLP2030-V                      OBJECT IDENTIFIER ::= { hh3cProductId 3296 }
hh3c-SecPath-D2035-G2                       OBJECT IDENTIFIER ::= { hh3cProductId 3297 }
hh3c-SecPath-D2015-G2                       OBJECT IDENTIFIER ::= { hh3cProductId 3298 }
hh3c-SecPath-D2025-G2                       OBJECT IDENTIFIER ::= { hh3cProductId 3299 }
hh3c-SecPath-D2000-AK6615-G                 OBJECT IDENTIFIER ::= { hh3cProductId 3300 }
hh3c-SecPath-D2000-Cloud-G                  OBJECT IDENTIFIER ::= { hh3cProductId 3301 }
hh3c-SecPath-D2055-G2                       OBJECT IDENTIFIER ::= { hh3cProductId 3302 }
hh3c-SecPath-D2000-AK6625-G                 OBJECT IDENTIFIER ::= { hh3cProductId 3303 }
hh3cNFNX5-T6280-E                           OBJECT IDENTIFIER ::= { hh3cProductId 3304 }
hh3cNFNX5-T6280-E-Context                   OBJECT IDENTIFIER ::= { hh3cProductId 3305 }
hh3cSR6608-G                                OBJECT IDENTIFIER ::= { hh3cProductId 3306 }
hh3cS12500R-48Y8C                           OBJECT IDENTIFIER ::= { hh3cProductId 3307 }
hh3c-SecPath-D2000-AK6615                   OBJECT IDENTIFIER ::= { hh3cProductId 3308 }
hh3c-SecPath-D2000-AK6625                   OBJECT IDENTIFIER ::= { hh3cProductId 3309 }
hh3cWA6624X                                 OBJECT IDENTIFIER ::= { hh3cProductId 3310 }
hh3cF5000-CN160-Context                     OBJECT IDENTIFIER ::= { hh3cProductId 3311 }
hh3cF5000-CN160                             OBJECT IDENTIFIER ::= { hh3cProductId 3312 }
hh3cF5000-AI-85-Context                     OBJECT IDENTIFIER ::= { hh3cProductId 3313 }
hh3cF5000-AI-65                             OBJECT IDENTIFIER ::= { hh3cProductId 3314 }
hh3cF5000-AI-35                             OBJECT IDENTIFIER ::= { hh3cProductId 3315 }
hh3cF5000-AI-65-Context                     OBJECT IDENTIFIER ::= { hh3cProductId 3316 }
hh3cF5000-AI-85                             OBJECT IDENTIFIER ::= { hh3cProductId 3317 }
hh3cF5000-AI-35-Context                     OBJECT IDENTIFIER ::= { hh3cProductId 3318 }
hh3cS6116-48X                               OBJECT IDENTIFIER ::= { hh3cProductId 3319 }
hh3cS6116-48X-M                             OBJECT IDENTIFIER ::= { hh3cProductId 3320 }
hh3cUR7103                                  OBJECT IDENTIFIER ::= { hh3cProductId 3321 }
hh3cER2200G3                                OBJECT IDENTIFIER ::= { hh3cProductId 3322 }
hh3cUG8103                                  OBJECT IDENTIFIER ::= { hh3cProductId 3323 }
hh3cUG8206                                  OBJECT IDENTIFIER ::= { hh3cProductId 3324 }
hh3cUG-1800W                                OBJECT IDENTIFIER ::= { hh3cProductId 3325 }
hh3cERG3-1800W                              OBJECT IDENTIFIER ::= { hh3cProductId 3326 }
hh3c-SecPath-TAP8000-CE54L                  OBJECT IDENTIFIER ::= { hh3cProductId 3327 }
hh3c-SecPath-TAP8000-CE54H                  OBJECT IDENTIFIER ::= { hh3cProductId 3328 }
hh3c-SecPath-TAP8000-C32                    OBJECT IDENTIFIER ::= { hh3cProductId 3329 }
hh3c-SecPath-TAP8000-XE50                   OBJECT IDENTIFIER ::= { hh3cProductId 3330 }
hh3c-SecPath-TAP8000-CE54                   OBJECT IDENTIFIER ::= { hh3cProductId 3331 }
hh3c-SecPath-CP8000                         OBJECT IDENTIFIER ::= { hh3cProductId 3332 }
hh3c-SecPath-D2000-D                        OBJECT IDENTIFIER ::= { hh3cProductId 3333 }
hh3cFS5500-30UXS4Y2Q-EI                     OBJECT IDENTIFIER ::= { hh3cProductId 3334 }
hh3cFS5500-48UXS4Y2Q-EI                     OBJECT IDENTIFIER ::= { hh3cProductId 3335 }
hh3cFS5500-24UX2C-EI                        OBJECT IDENTIFIER ::= { hh3cProductId 3336 }

hh3cIE4520-8T4P6S-BA-Switch                 OBJECT IDENTIFIER ::= { hh3cProductId 3339 }
hh3cUR7208-P-E                              OBJECT IDENTIFIER ::= { hh3cProductId 3340 }
hh3cER3208G3-P-E                            OBJECT IDENTIFIER ::= { hh3cProductId 3341 }
hh3cS7608X-G                                OBJECT IDENTIFIER ::= { hh3cProductId 3342 }
hh3cS9820-4C-G                              OBJECT IDENTIFIER ::= { hh3cProductId 3343 }
hh3cS7606X-G                                OBJECT IDENTIFIER ::= { hh3cProductId 3344 }
hh3cP3602                                   OBJECT IDENTIFIER ::= { hh3cProductId 3345 }
hh3cP3615                                   OBJECT IDENTIFIER ::= { hh3cProductId 3346 }
hh3cP3617                                   OBJECT IDENTIFIER ::= { hh3cProductId 3347 }
hh3cP3608                                   OBJECT IDENTIFIER ::= { hh3cProductId 3348 }
hh3cMSR1104S-5G-CN                          OBJECT IDENTIFIER ::= { hh3cProductId 3349 }
hh3cMSR1104S-W-5G-CN                        OBJECT IDENTIFIER ::= { hh3cProductId 3350 }
hh3cS5024PV5-EI-S                           OBJECT IDENTIFIER ::= { hh3cProductId 3351 }
hh3cS5016PV5-EI-PWR-S                       OBJECT IDENTIFIER ::= { hh3cProductId 3352 }
hh3cS5024PV5-EI-PWR-S                       OBJECT IDENTIFIER ::= { hh3cProductId 3353 }
hh3cF1000-AK9160                            OBJECT IDENTIFIER ::= { hh3cProductId 3354 }
hh3cF1000-AK9190-Context                    OBJECT IDENTIFIER ::= { hh3cProductId 3355 }
hh3cF1000-AK9190                            OBJECT IDENTIFIER ::= { hh3cProductId 3356 }
hh3cF1000-AK9160-Context                    OBJECT IDENTIFIER ::= { hh3cProductId 3357 }
hh3cF1000-AK9180-Context                    OBJECT IDENTIFIER ::= { hh3cProductId 3358 }
hh3cF1000-AK9180                            OBJECT IDENTIFIER ::= { hh3cProductId 3359 }
hh3cMSR1004S-5G-CN                          OBJECT IDENTIFIER ::= { hh3cProductId 3360 }
hh3cF1000-T1000-E                           OBJECT IDENTIFIER ::= { hh3cProductId 3361 }
hh3cF1000-T1000-E-Context                   OBJECT IDENTIFIER ::= { hh3cProductId 3362 }
hh3cF1000-AK9150                            OBJECT IDENTIFIER ::= { hh3cProductId 3363 }
hh3cF1000-AK9109                            OBJECT IDENTIFIER ::= { hh3cProductId 3364 }
hh3cF1000-AK9150-Context                    OBJECT IDENTIFIER ::= { hh3cProductId 3365 }
hh3cF1000-AK9120                            OBJECT IDENTIFIER ::= { hh3cProductId 3366 }
hh3cF1003-M                                 OBJECT IDENTIFIER ::= { hh3cProductId 3367 }
hh3cF1003-C                                 OBJECT IDENTIFIER ::= { hh3cProductId 3368 }
hh3cF1003-S                                 OBJECT IDENTIFIER ::= { hh3cProductId 3369 }
hh3cF1000-AK1115                            OBJECT IDENTIFIER ::= { hh3cProductId 3370 }
hh3cF1000-AK1105                            OBJECT IDENTIFIER ::= { hh3cProductId 3371 }
hh3cF1000-AK1235-Context                    OBJECT IDENTIFIER ::= { hh3cProductId 3372 }
hh3cF1000-AK1235                            OBJECT IDENTIFIER ::= { hh3cProductId 3373 }
hh3cS5580X-32S8T4X4YC-HI                    OBJECT IDENTIFIER ::= { hh3cProductId 3374 }
hh3cS5580X-48T6Y-EI                         OBJECT IDENTIFIER ::= { hh3cProductId 3375 }
hh3cS5580S-48T6X-EI                         OBJECT IDENTIFIER ::= { hh3cProductId 3376 }
hh3cS5580S-24T6X-EI                         OBJECT IDENTIFIER ::= { hh3cProductId 3377 }
hh3cS5580X-24T6Y-EI                         OBJECT IDENTIFIER ::= { hh3cProductId 3378 }
hh3cWX2550X-LI                              OBJECT IDENTIFIER ::= { hh3cProductId 3379 }
hh3cSecCenter-X6005-Context                 OBJECT IDENTIFIER ::= { hh3cProductId 3380 }
hh3cSecCenter-X6005                         OBJECT IDENTIFIER ::= { hh3cProductId 3381 }
hh3cLSCM1FWDSD0                             OBJECT IDENTIFIER ::= { hh3cProductId 3382 }
hh3cLSCM2FWDSD0-Context                     OBJECT IDENTIFIER ::= { hh3cProductId 3383 }
hh3cLSCM2FWDSD0                             OBJECT IDENTIFIER ::= { hh3cProductId 3384 }
hh3cLSCM1FWDSD0-Context                     OBJECT IDENTIFIER ::= { hh3cProductId 3385 }

hh3cUAP672                                  OBJECT IDENTIFIER ::= { hh3cProductId 3386 }
hh3cMSG320-W                                OBJECT IDENTIFIER ::= { hh3cProductId 3387 }
hh3cWAP811H                                 OBJECT IDENTIFIER ::= { hh3cProductId 3388 }
hh3cAngel-SG880-PWR                         OBJECT IDENTIFIER ::= { hh3cProductId 3389 }
hh3cUAP673                                  OBJECT IDENTIFIER ::= { hh3cProductId 3390 }
hh3cG120-W                                  OBJECT IDENTIFIER ::= { hh3cProductId 3391 }
hh3cWAP622H-G                               OBJECT IDENTIFIER ::= { hh3cProductId 3392 }
hh3cWAP662H                                 OBJECT IDENTIFIER ::= { hh3cProductId 3393 }
hh3cWAP812                                  OBJECT IDENTIFIER ::= { hh3cProductId 3394 }
hh3cUAP672X                                 OBJECT IDENTIFIER ::= { hh3cProductId 3395 }
hh3cWAP212H                                 OBJECT IDENTIFIER ::= { hh3cProductId 3396 }
hh3cUSG330-PWR                              OBJECT IDENTIFIER ::= { hh3cProductId 3397 }
hh3cMSG880                                  OBJECT IDENTIFIER ::= { hh3cProductId 3398 }
hh3cWAP822H                                 OBJECT IDENTIFIER ::= { hh3cProductId 3399 }
hh3cWAP632H                                 OBJECT IDENTIFIER ::= { hh3cProductId 3400 }
hh3cWAP622H-U                               OBJECT IDENTIFIER ::= { hh3cProductId 3401 }
hh3cAngel-SG810                             OBJECT IDENTIFIER ::= { hh3cProductId 3402 }
hh3cZD-WAX18-S-M                            OBJECT IDENTIFIER ::= { hh3cProductId 3403 }
hh3cWAP662                                  OBJECT IDENTIFIER ::= { hh3cProductId 3404 }
hh3cWAP862                                  OBJECT IDENTIFIER ::= { hh3cProductId 3405 }
hh3cWAP862H                                 OBJECT IDENTIFIER ::= { hh3cProductId 3406 }
hh3cMSG326-W                                OBJECT IDENTIFIER ::= { hh3cProductId 3407 }
hh3cWAP822                                  OBJECT IDENTIFIER ::= { hh3cProductId 3408 }
hh3cUAP672H-LI                              OBJECT IDENTIFIER ::= { hh3cProductId 3409 }
hh3cWAP611H                                 OBJECT IDENTIFIER ::= { hh3cProductId 3410 }
hh3cWAP622-U                                OBJECT IDENTIFIER ::= { hh3cProductId 3411 }
hh3cAngel-AP872                             OBJECT IDENTIFIER ::= { hh3cProductId 3412 }
hh3cAngel-AP872X                            OBJECT IDENTIFIER ::= { hh3cProductId 3413 }
hh3cWX1200H-W                               OBJECT IDENTIFIER ::= { hh3cProductId 3414 }
hh3cWAP611H-U                               OBJECT IDENTIFIER ::= { hh3cProductId 3415 }
hh3cWAP622H                                 OBJECT IDENTIFIER ::= { hh3cProductId 3416 }
hh3cWAP622                                  OBJECT IDENTIFIER ::= { hh3cProductId 3417 }
hh3cMSG330-W                                OBJECT IDENTIFIER ::= { hh3cProductId 3418 }
hh3cUSG310                                  OBJECT IDENTIFIER ::= { hh3cProductId 3419 }
hh3cZD-WAX18-S-W                            OBJECT IDENTIFIER ::= { hh3cProductId 3420 }
hh3cUAP672H                                 OBJECT IDENTIFIER ::= { hh3cProductId 3421 }
hh3cZD-WAX18-S-X                            OBJECT IDENTIFIER ::= { hh3cProductId 3422 }
hh3cWAP611H-G                               OBJECT IDENTIFIER ::= { hh3cProductId 3423 }
hh3cG130-W                                  OBJECT IDENTIFIER ::= { hh3cProductId 3424 }
hh3cWA7638                                  OBJECT IDENTIFIER ::= { hh3cProductId 3425 }
hh3cMSG330                                  OBJECT IDENTIFIER ::= { hh3cProductId 3426 }
hh3cNSQM7SUPA0-CN                           OBJECT IDENTIFIER ::= { hh3cProductId 3427 }
hh3cNSQM7SUPB0-CN                           OBJECT IDENTIFIER ::= { hh3cProductId 3428 }
hh3cM9000-AD10                              OBJECT IDENTIFIER ::= { hh3cProductId 3429 }
hh3cL5000-AD820                             OBJECT IDENTIFIER ::= { hh3cProductId 3430 }
hh3cL5000-AD830                             OBJECT IDENTIFIER ::= { hh3cProductId 3431 }
hh3cWA6520H-JP                              OBJECT IDENTIFIER ::= { hh3cProductId 3432 }
hh3cWA6126-JP                               OBJECT IDENTIFIER ::= { hh3cProductId 3433 }
hh3cFS5100-8T2RX-EI                         OBJECT IDENTIFIER ::= { hh3cProductId 3434 }
hh3cFS5100-8P2RS-EI                         OBJECT IDENTIFIER ::= { hh3cProductId 3435 }
hh3cFS5100-8T2RS-EI                         OBJECT IDENTIFIER ::= { hh3cProductId 3436 }
hh3cFS5100-8P2RX-EI                         OBJECT IDENTIFIER ::= { hh3cProductId 3437 }
hh3cL5000-AD820-Context                     OBJECT IDENTIFIER ::= { hh3cProductId 3438 }
hh3cM9000-AD10-Context                      OBJECT IDENTIFIER ::= { hh3cProductId 3439 }
hh3cL5000-AD830-Context                     OBJECT IDENTIFIER ::= { hh3cProductId 3440 }
hh3cWA6520H-LI                              OBJECT IDENTIFIER ::= { hh3cProductId 3441 }
hh3cWA6520S-D                               OBJECT IDENTIFIER ::= { hh3cProductId 3442 }
hh3cMSG370-8-PWR                            OBJECT IDENTIFIER ::= { hh3cProductId 3443 }
hh3cWX2510X-LI                              OBJECT IDENTIFIER ::= { hh3cProductId 3444 }
hh3cWX2510X-PWR                             OBJECT IDENTIFIER ::= { hh3cProductId 3445 }
hh3cSecPath-D2000-C                         OBJECT IDENTIFIER ::= { hh3cProductId 3446 }
hh3c-SecPath-ACG1000-AK9203                 OBJECT IDENTIFIER ::= { hh3cProductId 3447 }
hh3c-SecPath-ACG1000-AK9201                 OBJECT IDENTIFIER ::= { hh3cProductId 3448 }
hh3c-SecPath-ACG1000-AK9205                 OBJECT IDENTIFIER ::= { hh3cProductId 3449 }
hh3c-SecPath-ACG1000-AK9210                 OBJECT IDENTIFIER ::= { hh3cProductId 3450 }
hh3cFS5300-24UXS6X-EI                       OBJECT IDENTIFIER ::= { hh3cProductId 3451 }
hh3cFS5300-48US4X2Q-EI                      OBJECT IDENTIFIER ::= { hh3cProductId 3452 }
hh3cF100-A-XI                               OBJECT IDENTIFIER ::= { hh3cProductId 3453 }
hh3cF1000-9310-AI                           OBJECT IDENTIFIER ::= { hh3cProductId 3454 }
hh3cF1000-C8320                             OBJECT IDENTIFIER ::= { hh3cProductId 3455 }
hh3cF1000-C8310                             OBJECT IDENTIFIER ::= { hh3cProductId 3456 }
hh3cF1000-9305-AI                           OBJECT IDENTIFIER ::= { hh3cProductId 3457 }
hh3cF1000-C8305                             OBJECT IDENTIFIER ::= { hh3cProductId 3458 }
hh3cS12500R-48C6D                           OBJECT IDENTIFIER ::= { hh3cProductId 3459 }
hh3cF5000-CN30-D                            OBJECT IDENTIFIER ::= { hh3cProductId 3460 }
hh3cF5000-CN30-D-Context                    OBJECT IDENTIFIER ::= { hh3cProductId 3461 }
hh3cS9910X                                  OBJECT IDENTIFIER ::= { hh3cProductId 3462 }
hh3cS9906X                                  OBJECT IDENTIFIER ::= { hh3cProductId 3463 }
hh3cWS5860-28XC-WiNet                       OBJECT IDENTIFIER ::= { hh3cProductId 3464 }
hh3cWS6520-30HF-WiNet                       OBJECT IDENTIFIER ::= { hh3cProductId 3465 }
hh3cMSR5680-X3                              OBJECT IDENTIFIER ::= { hh3cProductId 3466 }
hh3c-SecPath-SysScan-I                      OBJECT IDENTIFIER ::= { hh3cProductId 3467 }

hh3cIE4320-28P-S-24GE-4SFP-Switch           OBJECT IDENTIFIER ::= { hh3cProductId 3469 }
hh3cIE4320-28P-K-24GE-8Combo-4SFP-Switch    OBJECT IDENTIFIER ::= { hh3cProductId 3470 }
hh3cER3208G3-P                              OBJECT IDENTIFIER ::= { hh3cProductId 3471 }
hh3cUR7208-P                                OBJECT IDENTIFIER ::= { hh3cProductId 3472 }
hh3cWA6620XM                                OBJECT IDENTIFIER ::= { hh3cProductId 3473 }
hh3cS5130S-28S-EI-DC                        OBJECT IDENTIFIER ::= { hh3cProductId 3474 }
hh3cS5130S-52P-EI-Q                         OBJECT IDENTIFIER ::= { hh3cProductId 3475 }
hh3cS5120V3-28F-LI                          OBJECT IDENTIFIER ::= { hh3cProductId 3476 }
hh3cS1850V2-10P-HPWR-EI                     OBJECT IDENTIFIER ::= { hh3cProductId 3477 }
hh3cL5000-CN560-Context                     OBJECT IDENTIFIER ::= { hh3cProductId 3478 }
hh3cL5000-CN540-Context                     OBJECT IDENTIFIER ::= { hh3cProductId 3479 }
hh3cL5000-CN540                             OBJECT IDENTIFIER ::= { hh3cProductId 3480 }
hh3cL5000-CN560                             OBJECT IDENTIFIER ::= { hh3cProductId 3481 }
hh3cL5000-CN520                             OBJECT IDENTIFIER ::= { hh3cProductId 3482 }
hh3cL5000-CN520-Context                     OBJECT IDENTIFIER ::= { hh3cProductId 3483 }
hh3cS6850-56HF-H3                           OBJECT IDENTIFIER ::= { hh3cProductId 3484 }
hh3cSecPath-AFC2000-Manager                 OBJECT IDENTIFIER ::= { hh3cProductId 3485 }
hh3cSecPath-AFC2000-M                       OBJECT IDENTIFIER ::= { hh3cProductId 3486 }
hh3cSecPath-AFC2000-D                       OBJECT IDENTIFIER ::= { hh3cProductId 3487 }
hh3cSecPath-AFC2000-A                       OBJECT IDENTIFIER ::= { hh3cProductId 3488 }
hh3cSecPath-AFC2000-S                       OBJECT IDENTIFIER ::= { hh3cProductId 3489 }
hh3cER8300G3                                OBJECT IDENTIFIER ::= { hh3cProductId 3490 }
hh3cUR7608                                  OBJECT IDENTIFIER ::= { hh3cProductId 3491 }
hh3cUR7504                                  OBJECT IDENTIFIER ::= { hh3cProductId 3492 }
hh3cUR7808                                  OBJECT IDENTIFIER ::= { hh3cProductId 3493 }
hh3cER6300G3                                OBJECT IDENTIFIER ::= { hh3cProductId 3494 }
hh3cS10506X-G-POE                           OBJECT IDENTIFIER ::= { hh3cProductId 3495 }
hh3cSR6608-M                                OBJECT IDENTIFIER ::= { hh3cProductId 3496 }
hh3cWA6320-SI-H20                           OBJECT IDENTIFIER ::= { hh3cProductId 3497 }
hh3cDNR20008C-DN                            OBJECT IDENTIFIER ::= { hh3cProductId 3498 }
hh3cDNR20008M-DN                            OBJECT IDENTIFIER ::= { hh3cProductId 3499 }
hh3cF1000                                   OBJECT IDENTIFIER ::= { hh3cProductId 3500 }
hh3cF1000-Context                           OBJECT IDENTIFIER ::= { hh3cProductId 3501 }
hh3cSW5560                                  OBJECT IDENTIFIER ::= { hh3cProductId 3502 }
hh3cSW5560-F                                OBJECT IDENTIFIER ::= { hh3cProductId 3503 }
hh3cWA6522H-D                               OBJECT IDENTIFIER ::= { hh3cProductId 3504 }
hh3cWA7539                                  OBJECT IDENTIFIER ::= { hh3cProductId 3505 }
hh3cWA7538                                  OBJECT IDENTIFIER ::= { hh3cProductId 3506 }
hh3c-SecPath-F1000                          OBJECT IDENTIFIER ::= { hh3cProductId 3507 }
hh3c-SecPath-SysScan-CN80                   OBJECT IDENTIFIER ::= { hh3cProductId 3508 }
hh3c-SecPath-W2000-CN40                     OBJECT IDENTIFIER ::= { hh3cProductId 3509 }
hh3c-SecPath-SysScan-CN20                   OBJECT IDENTIFIER ::= { hh3cProductId 3510 }
hh3c-SecPath-A2000-CN80                     OBJECT IDENTIFIER ::= { hh3cProductId 3511 }
hh3c-SecPath-A2000-CN40                     OBJECT IDENTIFIER ::= { hh3cProductId 3512 }
hh3c-SecPath-W2000-CN20                     OBJECT IDENTIFIER ::= { hh3cProductId 3513 }
hh3c-SecPath-D2000-CN80                     OBJECT IDENTIFIER ::= { hh3cProductId 3514 }
hh3c-SecPath-D2000-CN40                     OBJECT IDENTIFIER ::= { hh3cProductId 3515 }
hh3c-SecPath-W2000-CN80                     OBJECT IDENTIFIER ::= { hh3cProductId 3516 }
hh3c-SecPath-D2000-CN20                     OBJECT IDENTIFIER ::= { hh3cProductId 3517 }
hh3c-SecPath-A2000-CN20                     OBJECT IDENTIFIER ::= { hh3cProductId 3518 }
hh3cS5130S-52MS-EI-G                        OBJECT IDENTIFIER ::= { hh3cProductId 3519 }
hh3cS5130S-32MS-EI-G                        OBJECT IDENTIFIER ::= { hh3cProductId 3520 }
hh3cS5130S-52MS-PWR-EI-G                    OBJECT IDENTIFIER ::= { hh3cProductId 3521 }
hh3cS5130S-32MS-HPWR-EI-G                   OBJECT IDENTIFIER ::= { hh3cProductId 3522 }
hh3cS5552S-EI-D-DP-G                        OBJECT IDENTIFIER ::= { hh3cProductId 3523 }
hh3cS5552S-EI-D-DP-DC-G                     OBJECT IDENTIFIER ::= { hh3cProductId 3524 }
hh3cS5532F-EI-D-G                           OBJECT IDENTIFIER ::= { hh3cProductId 3525 }
hh3cS5532F-EI-D-DC-G                        OBJECT IDENTIFIER ::= { hh3cProductId 3526 }
hh3c-Unistor-X18000-G6                      OBJECT IDENTIFIER ::= { hh3cProductId 3527 }
hh3cWA6520H-SI                              OBJECT IDENTIFIER ::= { hh3cProductId 3528 }
hh3c-SecPath-ACG1000-ME-G                   OBJECT IDENTIFIER ::= { hh3cProductId 3529 }
hh3c-SecPath-ACG1000-AE-G                   OBJECT IDENTIFIER ::= { hh3cProductId 3530 }
hh3cF1000-AK9130                            OBJECT IDENTIFIER ::= { hh3cProductId 3531 }
hh3cS9825-64D-H1                            OBJECT IDENTIFIER ::= { hh3cProductId 3532 }
hh3c-SecPath-WG                             OBJECT IDENTIFIER ::= { hh3cProductId 3533 }
hh3cCSAP-NTA-800-Context                    OBJECT IDENTIFIER ::= { hh3cProductId 3534 }
hh3cCSAP-NTA-800                            OBJECT IDENTIFIER ::= { hh3cProductId 3535 }
hh3cS5130V2-28S-LI-24GE-4SFP-PLUS-Switch    OBJECT IDENTIFIER ::= { hh3cProductId 3536 }
hh3cS5130V2-20P-LI-16GE-4SFP-Switch         OBJECT IDENTIFIER ::= { hh3cProductId 3537 }
hh3cS5130V2-12S-SI-8GE-4SFP-PLUS-Switch     OBJECT IDENTIFIER ::= { hh3cProductId 3538 }
hh3cS5130V2-28S-SI-24GE-4SFP-PLUS-Switch    OBJECT IDENTIFIER ::= { hh3cProductId 3539 }
hh3cS5130V2-52P-LI-48GE-4SFP-Switch         OBJECT IDENTIFIER ::= { hh3cProductId 3540 }
hh3cS5130V2-52P-SI-48GE-4SFP-Switch         OBJECT IDENTIFIER ::= { hh3cProductId 3541 }
hh3cSE-S5130-10S-8GE-2SFP-PLUS-Switch       OBJECT IDENTIFIER ::= { hh3cProductId 3542 }
hh3cS5130V2-10P-LI-8GE-2SFP-Switch          OBJECT IDENTIFIER ::= { hh3cProductId 3543 }
hh3cS5130V2-28P-SI-24GE-4SFP-Switch         OBJECT IDENTIFIER ::= { hh3cProductId 3544 }
hh3cS5130V2-28P-LI-24GE-4SFP-Switch         OBJECT IDENTIFIER ::= { hh3cProductId 3545 }
hh3cSE-S5130-18S-16GE-2SFP-PLUS-Switch      OBJECT IDENTIFIER ::= { hh3cProductId 3546 }
hh3cCR16005E-F                              OBJECT IDENTIFIER ::= { hh3cProductId 3547 }
hh3cCR16010E-F                              OBJECT IDENTIFIER ::= { hh3cProductId 3548 }
hh3cWA7539-JP                               OBJECT IDENTIFIER ::= { hh3cProductId 3549 }
hh3cUSG330V2-PWR                            OBJECT IDENTIFIER ::= { hh3cProductId 3550 }
hh3cUSG310V2                                OBJECT IDENTIFIER ::= { hh3cProductId 3551 }
hh3cUSG330V2                                OBJECT IDENTIFIER ::= { hh3cProductId 3552 }
hh3cS6510-50QS-24GE24SFP2QSFP-PLUS-Switch   OBJECT IDENTIFIER ::= { hh3cProductId 3553 }
hh3cSecPathM9000-CN04-NSQZ6M9000CN04        OBJECT IDENTIFIER ::= { hh3cProductId 3554 }
hh3cIE4500-28S-G                            OBJECT IDENTIFIER ::= { hh3cProductId 3555 }
hh3cIE4500-28F-G                            OBJECT IDENTIFIER ::= { hh3cProductId 3556 }
hh3cDXSS-SPSW-S2301                         OBJECT IDENTIFIER ::= { hh3cProductId 3557 }
hh3cDXSS-SPSW-S2311                         OBJECT IDENTIFIER ::= { hh3cProductId 3558 }
hh3cSW6850                                  OBJECT IDENTIFIER ::= { hh3cProductId 3559 }
hh3cSW9850                                  OBJECT IDENTIFIER ::= { hh3cProductId 3560 }
hh3cNDR-NSQSECLNDR02                        OBJECT IDENTIFIER ::= { hh3cProductId 3561 }
hh3cS6850-56HF-IM                           OBJECT IDENTIFIER ::= { hh3cProductId 3562 }
hh3cNSQZ1AFC2040DG                          OBJECT IDENTIFIER ::= { hh3cProductId 3563 }
hh3cNSQZ1AFC2200G                           OBJECT IDENTIFIER ::= { hh3cProductId 3564 }
hh3cWA6520H-HI                              OBJECT IDENTIFIER ::= { hh3cProductId 3565 }
hh3cIE4100-12TP-H1                          OBJECT IDENTIFIER ::= { hh3cProductId 3566 }
hh3cIE4100-12TP-H1-SC                       OBJECT IDENTIFIER ::= { hh3cProductId 3567 }
hh3cIE4100-20TP-H1                          OBJECT IDENTIFIER ::= { hh3cProductId 3568 }
hh3cIE4100-20TP-H1-SC                       OBJECT IDENTIFIER ::= { hh3cProductId 3569 }
hh3cIE4100-12TP-PWR-LI-H1                   OBJECT IDENTIFIER ::= { hh3cProductId 3570 }
hh3cIE4100-12TP-PWR-LI-H1-SC                OBJECT IDENTIFIER ::= { hh3cProductId 3571 }
hh3cIE4300-12P-H1                           OBJECT IDENTIFIER ::= { hh3cProductId 3572 }
hh3cIE4300-6P-H1                            OBJECT IDENTIFIER ::= { hh3cProductId 3573 }
hh3cT1000-AI-65-G                           OBJECT IDENTIFIER ::= { hh3cProductId 3574 }
hh3cT1000-AI-55-G-Context                   OBJECT IDENTIFIER ::= { hh3cProductId 3575 }
hh3cT1000-AI-70-G                           OBJECT IDENTIFIER ::= { hh3cProductId 3576 }
hh3cT1000-AI-55-G                           OBJECT IDENTIFIER ::= { hh3cProductId 3577 }
hh3cT1000-AI-65-G-Context                   OBJECT IDENTIFIER ::= { hh3cProductId 3578 }
hh3cT1000-AI-70-G-Context                   OBJECT IDENTIFIER ::= { hh3cProductId 3579 }
hh3cF1000-U500-H3                           OBJECT IDENTIFIER ::= { hh3cProductId 3580 }
hh3cF1000-T500-H3                           OBJECT IDENTIFIER ::= { hh3cProductId 3581 }
hh3cF1000-Y500-P                            OBJECT IDENTIFIER ::= { hh3cProductId 3582 }
hh3cMSR-3620X1-WiNet                        OBJECT IDENTIFIER ::= { hh3cProductId 3583 }
hh3cMSR-iMC                                 OBJECT IDENTIFIER ::= { hh3cProductId 3584 }
hh3cF5000-AI360-Context                     OBJECT IDENTIFIER ::= { hh3cProductId 3585 }
hh3cF5000-AI360                             OBJECT IDENTIFIER ::= { hh3cProductId 3586 }
hh3cS5560-52S-EI-G                          OBJECT IDENTIFIER ::= { hh3cProductId 3587 }
hh3cS5560-52F-EI-G                          OBJECT IDENTIFIER ::= { hh3cProductId 3588 }
hh3cS5560-28S-EI-G                          OBJECT IDENTIFIER ::= { hh3cProductId 3589 }
hh3cS5560-28F-EI-G                          OBJECT IDENTIFIER ::= { hh3cProductId 3590 }
hh3cS6850-56HF-CP                           OBJECT IDENTIFIER ::= { hh3cProductId 3591 }

-- HP A series products
-- OID of hpNetworking is 1.3.6.1.4.1.25506.11
hpSwitch                        OBJECT IDENTIFIER ::= { hpNetworking 1 }
hpRouter                        OBJECT IDENTIFIER ::= { hpNetworking 2 }
hpWireless                      OBJECT IDENTIFIER ::= { hpNetworking 3 }
hpSecurity                      OBJECT IDENTIFIER ::= { hpNetworking 4 }

-- begin hpSwitch
hp7502                          OBJECT IDENTIFIER ::= { hpSwitch 1 }
hp7503S                         OBJECT IDENTIFIER ::= { hpSwitch 2 }
hp7503                          OBJECT IDENTIFIER ::= { hpSwitch 3 }
hp7506                          OBJECT IDENTIFIER ::= { hpSwitch 4 }
hp7506V                         OBJECT IDENTIFIER ::= { hpSwitch 5 }
hp7510                          OBJECT IDENTIFIER ::= { hpSwitch 6 }
hpA36002POLT                    OBJECT IDENTIFIER ::= { hpSwitch 7 }
hpV190524                       OBJECT IDENTIFIER ::= { hpSwitch 8 }
hpV190524POE                    OBJECT IDENTIFIER ::= { hpSwitch 9 }
hpV190548                       OBJECT IDENTIFIER ::= { hpSwitch 10 }
hpA512016GSI                    OBJECT IDENTIFIER ::= { hpSwitch 11 }
hpA512024GSI                    OBJECT IDENTIFIER ::= { hpSwitch 12 }
hpA512048GSI                    OBJECT IDENTIFIER ::= { hpSwitch 13 }
hpA512024GPPOESI                OBJECT IDENTIFIER ::= { hpSwitch 14 }
hpA512024GPOESI                 OBJECT IDENTIFIER ::= { hpSwitch 15 }
hpA580024G                      OBJECT IDENTIFIER ::= { hpSwitch 16 }
hpA580024GPoEPlus               OBJECT IDENTIFIER ::= { hpSwitch 17 }
hpA580048G                      OBJECT IDENTIFIER ::= { hpSwitch 18 }
hpA580048GPoEPlus               OBJECT IDENTIFIER ::= { hpSwitch 19 }
hpA580024GSFP                   OBJECT IDENTIFIER ::= { hpSwitch 20 }
hpA580048GPoEPlus2SLOT          OBJECT IDENTIFIER ::= { hpSwitch 21 }
hpA5820X14XGSFPPlus2SLOT        OBJECT IDENTIFIER ::= { hpSwitch 22 }
hpA5820X24XGSFPPlus             OBJECT IDENTIFIER ::= { hpSwitch 23 }
hpA550024GEI2SLOT               OBJECT IDENTIFIER ::= { hpSwitch 24 }
hpA550048GEI2SLOT               OBJECT IDENTIFIER ::= { hpSwitch 25 }
hpA550024GPoEPlusEI2SLOT        OBJECT IDENTIFIER ::= { hpSwitch 26 }
hpA550048GPoEPlusEI2SLOT        OBJECT IDENTIFIER ::= { hpSwitch 27 }
hpA550024GSFPEI2SLOT            OBJECT IDENTIFIER ::= { hpSwitch 28 }
hpA550024GSI2SLOT               OBJECT IDENTIFIER ::= { hpSwitch 29 }
hpA550048GSI2SLOT               OBJECT IDENTIFIER ::= { hpSwitch 30 }
hpA550024GPoEPlusSI2SLOT        OBJECT IDENTIFIER ::= { hpSwitch 31 }
hpA550048GPoEPlusSI2SLOT        OBJECT IDENTIFIER ::= { hpSwitch 32 }
hpA512024GEI2SLOT               OBJECT IDENTIFIER ::= { hpSwitch 33 }
hpA512048GEI2SLOT               OBJECT IDENTIFIER ::= { hpSwitch 34 }
hpA512024GPoEPlusEI2SLOT        OBJECT IDENTIFIER ::= { hpSwitch 35 }
hpA512048GPoEPlusEI2SLOT        OBJECT IDENTIFIER ::= { hpSwitch 36 }
hpA512024GEI                    OBJECT IDENTIFIER ::= { hpSwitch 37 }
hpA512048GEI                    OBJECT IDENTIFIER ::= { hpSwitch 38 }
hp9505                          OBJECT IDENTIFIER ::= { hpSwitch 39 }
hp9508V                         OBJECT IDENTIFIER ::= { hpSwitch 40 }
hp9508                          OBJECT IDENTIFIER ::= { hpSwitch 41 }
hp9512                          OBJECT IDENTIFIER ::= { hpSwitch 42 }
hp12508                         OBJECT IDENTIFIER ::= { hpSwitch 43 }
hp12518                         OBJECT IDENTIFIER ::= { hpSwitch 44 }
hp12504AC                       OBJECT IDENTIFIER ::= { hpSwitch 45 }
hpA5800AF48G                    OBJECT IDENTIFIER ::= { hpSwitch 46 }
hpA5820AF24XG                   OBJECT IDENTIFIER ::= { hpSwitch 47 }
hp6125GXG                       OBJECT IDENTIFIER ::= { hpSwitch 51 }
hpA31008SI                      OBJECT IDENTIFIER ::= { hpSwitch 52 }
hpA310016SI                     OBJECT IDENTIFIER ::= { hpSwitch 53 }
hpA310024SI                     OBJECT IDENTIFIER ::= { hpSwitch 54 }
hpA31008EI                      OBJECT IDENTIFIER ::= { hpSwitch 55 }
hpA310016EI                     OBJECT IDENTIFIER ::= { hpSwitch 56 }
hpA310024EI                     OBJECT IDENTIFIER ::= { hpSwitch 57 }
hpA31008POEEI                   OBJECT IDENTIFIER ::= { hpSwitch 58 }
hpA310016POEEI                  OBJECT IDENTIFIER ::= { hpSwitch 59 }
hpA310024POEEI                  OBJECT IDENTIFIER ::= { hpSwitch 60 }
hpA580024GTAA                   OBJECT IDENTIFIER ::= { hpSwitch 61 }
hpA580024GPoEPlusTAA            OBJECT IDENTIFIER ::= { hpSwitch 62 }
hpA580024GSFPTAA                OBJECT IDENTIFIER ::= { hpSwitch 63 }
hpA580048GTAA                   OBJECT IDENTIFIER ::= { hpSwitch 64 }
hpA580048GPoEPlusTAA2SLOT       OBJECT IDENTIFIER ::= { hpSwitch 65 }
hpA580048GPoEPlusTAA            OBJECT IDENTIFIER ::= { hpSwitch 66 }
hpA5820X14XGSFPPlusTAA2SLOT     OBJECT IDENTIFIER ::= { hpSwitch 67 }
hpA5820X24XGSFPPlusTAA          OBJECT IDENTIFIER ::= { hpSwitch 68 }
hpA512024GEITAA2SLOT            OBJECT IDENTIFIER ::= { hpSwitch 69 }
hpA512048GEITAA2SLOT            OBJECT IDENTIFIER ::= { hpSwitch 70 }
hpA512024GPoEPlusEITAA2SLOT     OBJECT IDENTIFIER ::= { hpSwitch 71 }
hpA512048GPoEPlusEITAA2SLOT     OBJECT IDENTIFIER ::= { hpSwitch 72 }
hpA550024GSFPEITAA2SLOT         OBJECT IDENTIFIER ::= { hpSwitch 73 }
hpA550024GEITAA2SLOT            OBJECT IDENTIFIER ::= { hpSwitch 74 }
hpA550048GEITAA2SLOT            OBJECT IDENTIFIER ::= { hpSwitch 75 }
hpA550024GPoEPlusEITAA2SLOT     OBJECT IDENTIFIER ::= { hpSwitch 76 }
hpA550048GPoEPlusEITAA2SLOT     OBJECT IDENTIFIER ::= { hpSwitch 77 }
hp5920AF24XG                    OBJECT IDENTIFIER ::= { hpSwitch 78 }
hpA5830AF48G                    OBJECT IDENTIFIER ::= { hpSwitch 79 }
hpA5830AF96G                    OBJECT IDENTIFIER ::= { hpSwitch 80 }
hpV191016G                      OBJECT IDENTIFIER ::= { hpSwitch 81 }
hpV191024G                      OBJECT IDENTIFIER ::= { hpSwitch 82 }
hpV191024GPoE365W               OBJECT IDENTIFIER ::= { hpSwitch 83 }
hpV191024GPoE170W               OBJECT IDENTIFIER ::= { hpSwitch 84 }
hpV191048G                      OBJECT IDENTIFIER ::= { hpSwitch 85 }
hp10504                         OBJECT IDENTIFIER ::= { hpSwitch 86 }
hp10508                         OBJECT IDENTIFIER ::= { hpSwitch 87 }
hp10508V                        OBJECT IDENTIFIER ::= { hpSwitch 88 }
hp10512                         OBJECT IDENTIFIER ::= { hpSwitch 89 }
hpA360024V2EI                   OBJECT IDENTIFIER ::= { hpSwitch 90 }
hpA360048V2EI                   OBJECT IDENTIFIER ::= { hpSwitch 91 }
hpA360024PoEPlusV2EI            OBJECT IDENTIFIER ::= { hpSwitch 92 }
hpA360048PoEPlusV2EI            OBJECT IDENTIFIER ::= { hpSwitch 93 }
hpA360024SFPV2EI                OBJECT IDENTIFIER ::= { hpSwitch 94 }
hpA360024V2SI                   OBJECT IDENTIFIER ::= { hpSwitch 95 }
hpA360048V2SI                   OBJECT IDENTIFIER ::= { hpSwitch 96 }
hpA360024PoEPlusV2SI            OBJECT IDENTIFIER ::= { hpSwitch 97 }
hpA360048PoEPlusV2SI            OBJECT IDENTIFIER ::= { hpSwitch 98 }
hpA310048V2                     OBJECT IDENTIFIER ::= { hpSwitch 99 }
hp5900AF48XG4QSFPPlus           OBJECT IDENTIFIER ::= { hpSwitch 100 }
hpA550024G4SFPHI                OBJECT IDENTIFIER ::= { hpSwitch 101 }
hpA550048G4SFPHI                OBJECT IDENTIFIER ::= { hpSwitch 102 }
hp6125G                         OBJECT IDENTIFIER ::= { hpSwitch 103 }
hpA51208GSI                     OBJECT IDENTIFIER ::= { hpSwitch 104 }
hpA51208GPoEPlusSI              OBJECT IDENTIFIER ::= { hpSwitch 105 }
hpA51208GPPoEPlusSI             OBJECT IDENTIFIER ::= { hpSwitch 106 }
hpA5120AF48GHI                  OBJECT IDENTIFIER ::= { hpSwitch 107 }
hp12504DC                       OBJECT IDENTIFIER ::= { hpSwitch 108 }
hp12508DC                       OBJECT IDENTIFIER ::= { hpSwitch 109 }
hp12518DC                       OBJECT IDENTIFIER ::= { hpSwitch 110 }
hp12508AC                       OBJECT IDENTIFIER ::= { hpSwitch 111 }
hp12518AC                       OBJECT IDENTIFIER ::= { hpSwitch 112 }
hp5900AF48XGT4QSFPPlus          OBJECT IDENTIFIER ::= { hpSwitch 113 }
hp19108G                        OBJECT IDENTIFIER ::= { hpSwitch 114 }
hp19108GPoEPlus65W              OBJECT IDENTIFIER ::= { hpSwitch 115 }
hp19108GPoEPlus180W             OBJECT IDENTIFIER ::= { hpSwitch 116 }
hp5830AF48GTAA                  OBJECT IDENTIFIER ::= { hpSwitch 117 }
hp5830AF96GTAA                  OBJECT IDENTIFIER ::= { hpSwitch 118 }
hp7508H                         OBJECT IDENTIFIER ::= { hpSwitch 119 }
hp5900AF48G4XG2QSFPPlus         OBJECT IDENTIFIER ::= { hpSwitch 120 }
hp550048GPoEPlus4SFPHI          OBJECT IDENTIFIER ::= { hpSwitch 121 }
hp550024GPoEPlus4SFPHI          OBJECT IDENTIFIER ::= { hpSwitch 122 }
hp550024GSFPHI                  OBJECT IDENTIFIER ::= { hpSwitch 123 }
hp12504ACV7                     OBJECT IDENTIFIER ::= { hpSwitch 124 }
hp12504DCV7                     OBJECT IDENTIFIER ::= { hpSwitch 125 }
hp12508ACV7                     OBJECT IDENTIFIER ::= { hpSwitch 126 }
hp12508DCV7                     OBJECT IDENTIFIER ::= { hpSwitch 127 }
hp12518ACV7                     OBJECT IDENTIFIER ::= { hpSwitch 128 }
hp12518DCV7                     OBJECT IDENTIFIER ::= { hpSwitch 129 }
hp5900AF48XG4QSFPPlusTAA        OBJECT IDENTIFIER ::= { hpSwitch 130 }
hp5920AF24XGTAA                 OBJECT IDENTIFIER ::= { hpSwitch 131 }
hpV19108                        OBJECT IDENTIFIER ::= { hpSwitch 132 }
hpV19108PoEPlus                 OBJECT IDENTIFIER ::= { hpSwitch 133 }
hpV191024                       OBJECT IDENTIFIER ::= { hpSwitch 134 }
hpV191024PoEPlus                OBJECT IDENTIFIER ::= { hpSwitch 135 }
hpV191048                       OBJECT IDENTIFIER ::= { hpSwitch 136 }
hp6125XGXLG                     OBJECT IDENTIFIER ::= { hpSwitch 137 }
hp11908V                        OBJECT IDENTIFIER ::= { hpSwitch 138 }
hp550048GPoEPlus4SFPHITAA2Slot  OBJECT IDENTIFIER ::= { hpSwitch 139 }
hp550024GPoEPlus4SFPHITAA2Slot  OBJECT IDENTIFIER ::= { hpSwitch 140 }
hp550024GSFPHITAA2Slot          OBJECT IDENTIFIER ::= { hpSwitch 141 }
hpMoonshot45XGc                 OBJECT IDENTIFIER ::= { hpSwitch 142 }
hp12910AC                       OBJECT IDENTIFIER ::= { hpSwitch 143 }
hpFF593032QSFPPlus              OBJECT IDENTIFIER ::= { hpSwitch 144 }
hpFF593032QSFPPlusTAA           OBJECT IDENTIFIER ::= { hpSwitch 145 }
hpeFF7904                       OBJECT IDENTIFIER ::= { hpSwitch 146 }
hp12916AC                       OBJECT IDENTIFIER ::= { hpSwitch 147 }
hp12916DC                       OBJECT IDENTIFIER ::= { hpSwitch 148 }
hpFF5900CP48XG4QSFPPlus         OBJECT IDENTIFIER ::= { hpSwitch 149 }
hp5900CP48XG4QSFPPlus8GbFCBF    OBJECT IDENTIFIER ::= { hpSwitch 150 }
hp6125XLGTAA                    OBJECT IDENTIFIER ::= { hpSwitch 151 }
hp6125GXGTAA                    OBJECT IDENTIFIER ::= { hpSwitch 152 }
hp6125GTAA                      OBJECT IDENTIFIER ::= { hpSwitch 153 }
hp512024G4SFPXI2Slot            OBJECT IDENTIFIER ::= { hpSwitch 154 }
hp512048G4SFPXI2Slot            OBJECT IDENTIFIER ::= { hpSwitch 155 }
hp512024GPoEPlus4SFPXI2Slot     OBJECT IDENTIFIER ::= { hpSwitch 156 }
hp512048GPoEPlus4SFPXI2Slot     OBJECT IDENTIFIER ::= { hpSwitch 157 }
hp512024G4SFPXITAA2Slot         OBJECT IDENTIFIER ::= { hpSwitch 158 }
hp512048G4SFPXITAA2Slot         OBJECT IDENTIFIER ::= { hpSwitch 159 }
hp512024GPoEPlus4SFPXITAA2Slot  OBJECT IDENTIFIER ::= { hpSwitch 160 }
hp512048GPoEPlus4SFPXITAA2Slot  OBJECT IDENTIFIER ::= { hpSwitch 161 }
hp19208G                        OBJECT IDENTIFIER ::= { hpSwitch 162 }
hp19208GPoEPlus65W              OBJECT IDENTIFIER ::= { hpSwitch 163 }
hp19208GPoEPlus180W             OBJECT IDENTIFIER ::= { hpSwitch 164 }
hp192016G                       OBJECT IDENTIFIER ::= { hpSwitch 165 }
hp192024G                       OBJECT IDENTIFIER ::= { hpSwitch 166 }
hp192024GPoEPlus180W            OBJECT IDENTIFIER ::= { hpSwitch 167 }
hp192024GPoEPlus370W            OBJECT IDENTIFIER ::= { hpSwitch 168 }
hp192048G                       OBJECT IDENTIFIER ::= { hpSwitch 169 }
hp192048GPoEPlus370W            OBJECT IDENTIFIER ::= { hpSwitch 170 }
hpFF570040XG2QSFPPlusTAA        OBJECT IDENTIFIER ::= { hpSwitch 171 }
hpFF570040XG2QSFPPlus           OBJECT IDENTIFIER ::= { hpSwitch 172 }
hpFF570032XGT8XG2QSFPPlusTAA    OBJECT IDENTIFIER ::= { hpSwitch 173 }
hpFF570032XGT8XG2QSFPPlus       OBJECT IDENTIFIER ::= { hpSwitch 174 }
hpFF570048G4XG2QSFPPlusTAA      OBJECT IDENTIFIER ::= { hpSwitch 175 }
hpFF570048G4XG2QSFPPlus         OBJECT IDENTIFIER ::= { hpSwitch 176 }
hp16208G                        OBJECT IDENTIFIER ::= { hpSwitch 177 }
hp162024G                       OBJECT IDENTIFIER ::= { hpSwitch 178 }
hp162048G                       OBJECT IDENTIFIER ::= { hpSwitch 179 }
hp195024G2SFPPlus2XGT           OBJECT IDENTIFIER ::= { hpSwitch 180 }
hp195048G2SFPPlus2XGT           OBJECT IDENTIFIER ::= { hpSwitch 181 }
hp195024G2SFPPlus2XGTPoEPlus    OBJECT IDENTIFIER ::= { hpSwitch 182 }
hp195048G2SFPPlus2XGTPoEPlus    OBJECT IDENTIFIER ::= { hpSwitch 183 }
hp513024G4SFPPlusEI             OBJECT IDENTIFIER ::= { hpSwitch 184 }
hp513024GSFP4SFPPlusEI          OBJECT IDENTIFIER ::= { hpSwitch 185 }
hp513048G4SFPPlusEI             OBJECT IDENTIFIER ::= { hpSwitch 186 }
hp513024GPoEPlus4SFPPlus180WEI  OBJECT IDENTIFIER ::= { hpSwitch 187 }
hp513024GPoEPlus4SFPPlus370WEI  OBJECT IDENTIFIER ::= { hpSwitch 188 }
hp513048GPoEPlus4SFPPlus370WEI  OBJECT IDENTIFIER ::= { hpSwitch 189 }
hp513024G2SFPPlus2XGTEI         OBJECT IDENTIFIER ::= { hpSwitch 190 }
hp513048G2SFPPlus2XGTEI         OBJECT IDENTIFIER ::= { hpSwitch 191 }
hp513024GPoEPlus2SFPPlus2XGT370WEI  OBJECT IDENTIFIER ::= { hpSwitch 192 }
hp513048GPoEPlus2SFPPlus2XGT370WEI  OBJECT IDENTIFIER ::= { hpSwitch 193 }
hp513024G4SFPPlusEITAA          OBJECT IDENTIFIER ::= { hpSwitch 194 }
hp513024GSFP4SFPPlusEITAA       OBJECT IDENTIFIER ::= { hpSwitch 195 }
hp513048G4SFPPlusEITAA          OBJECT IDENTIFIER ::= { hpSwitch 196 }
hp513024GPoEPlus4SFPPlus180WEITAA   OBJECT IDENTIFIER ::= { hpSwitch 197 }
hp513024GPoEPlus4SFPPlus370WEITAA   OBJECT IDENTIFIER ::= { hpSwitch 198 }
hp513048GPoEPlus4SFPPlus370WEITAA   OBJECT IDENTIFIER ::= { hpSwitch 199 }
hp513024G2SFPPlus2XGTEITAA      OBJECT IDENTIFIER ::= { hpSwitch 200 }
hp513048G2SFPPlus2XGTEITAA      OBJECT IDENTIFIER ::= { hpSwitch 201 }
hp513024GPoEPlus2SFPPlus2XGT370WEITAA  OBJECT IDENTIFIER ::= { hpSwitch 202 }
hp513048GPoEPlus2SFPPlus2XGT370WEITAA  OBJECT IDENTIFIER ::= { hpSwitch 203 }
hpeFF7910                        OBJECT IDENTIFIER ::= { hpSwitch 204 }
hp5900AF48G4XG2QSFPPlusTAA      OBJECT IDENTIFIER ::= { hpSwitch 205 }
hp5900AF48XGT4QSFPPlusTAA       OBJECT IDENTIFIER ::= { hpSwitch 206 }
hpFF5900CP48XG4QSFPPlusTAA      OBJECT IDENTIFIER ::= { hpSwitch 207 }
hp513024G4SFPPlusEIBrazil       OBJECT IDENTIFIER ::= { hpSwitch 208 }
hp513048G4SFPPlusEIBrazil       OBJECT IDENTIFIER ::= { hpSwitch 209 }
hp513024GPoEPlus4SFPPlus370WEIBrazil    OBJECT IDENTIFIER ::= { hpSwitch 210 }
hp513048GPoEPlus4SFPPlus370WEIBrazil    OBJECT IDENTIFIER ::= { hpSwitch 211 }
hpThunderBird                   OBJECT IDENTIFIER ::= { hpSwitch 212 }
hpeFF12916E                     OBJECT IDENTIFIER ::= { hpSwitch 213 }
hpNJ50005GPoEPlusWalljack       OBJECT IDENTIFIER ::= { hpSwitch 214 }
hp551024G4SFPPlusHI1Slot        OBJECT IDENTIFIER ::= { hpSwitch 215 }
hp551048G4SFPPlusHI1Slot        OBJECT IDENTIFIER ::= { hpSwitch 216 }
hp551024GPoEPlus4SFPPlusHI1Slot OBJECT IDENTIFIER ::= { hpSwitch 217 }
hp551048GPoEPlus4SFPPlusHI1Slot OBJECT IDENTIFIER ::= { hpSwitch 218 }
hp551024GSFP4SFPPlusHI1Slot     OBJECT IDENTIFIER ::= { hpSwitch 219 }
hp551024G4SFPPlusHITAA1Slot     OBJECT IDENTIFIER ::= { hpSwitch 220 }
hp551048G4SFPPlusHITAA1Slot     OBJECT IDENTIFIER ::= { hpSwitch 221 }
hp551024GPoEPlus4SFPPlusHITAA1Slot  OBJECT IDENTIFIER ::= { hpSwitch 222 }
hp551048GPoEPlus4SFPPlusHITAA1Slot  OBJECT IDENTIFIER ::= { hpSwitch 223 }
hp551024GSFP4SFPPlusHITAA1Slot  OBJECT IDENTIFIER ::= { hpSwitch 224 }
hpeFF12910ACTAA                  OBJECT IDENTIFIER ::= { hpSwitch 225 }
hpeFF7904TAA                     OBJECT IDENTIFIER ::= { hpSwitch 226 }
hpeFF7910TAA                     OBJECT IDENTIFIER ::= { hpSwitch 227 }
hp6127XLG                       OBJECT IDENTIFIER ::= { hpSwitch 228 }
hpFF59302Slot2QSFPPlus          OBJECT IDENTIFIER ::= { hpSwitch 229 }
hpFF59302Slot2QSFPPlusTAA       OBJECT IDENTIFIER ::= { hpSwitch 230 }
hpFF59304Slot                   OBJECT IDENTIFIER ::= { hpSwitch 231 }
hpFF59304SlotTAA                OBJECT IDENTIFIER ::= { hpSwitch 232 }
hp6127XLGTAA                    OBJECT IDENTIFIER ::= { hpSwitch 233 }
hp195012XGT4SFPPlus             OBJECT IDENTIFIER ::= { hpSwitch 234 }
hpeFF12916ETAA                   OBJECT IDENTIFIER ::= { hpSwitch 235 }
hpeFF12908E                      OBJECT IDENTIFIER ::= { hpSwitch 236 }
hpeFF12908ETAA                   OBJECT IDENTIFIER ::= { hpSwitch 237 }
hpMoonshot45GcR10               OBJECT IDENTIFIER ::= { hpSwitch 238 }
hpMoonshot45XGcR16              OBJECT IDENTIFIER ::= { hpSwitch 239 }
hpMoonshot180XGcR16             OBJECT IDENTIFIER ::= { hpSwitch 240 }
hpMoonshot180XGcR40             OBJECT IDENTIFIER ::= { hpSwitch 241 }
hpeFF12904E                      OBJECT IDENTIFIER ::= { hpSwitch 242 }
hpeFF12904ETAA                   OBJECT IDENTIFIER ::= { hpSwitch 243 }
hp513024G4SFPPlus1SlotHI        OBJECT IDENTIFIER ::= { hpSwitch 244 }
hp513048G4SFPPlus1SlotHI        OBJECT IDENTIFIER ::= { hpSwitch 245 }
hp513024GPoEPlus4SFPPlus1SlotHI OBJECT IDENTIFIER ::= { hpSwitch 246 }
hp513048GPoEPlus4SFPPlus1SlotHI OBJECT IDENTIFIER ::= { hpSwitch 247 }
hp513024GPoEPlus4SFPPlus1SlotTAAHI  OBJECT IDENTIFIER ::= { hpSwitch 248 }
hp513048GPoEPlus4SFPPlus1SlotTAAHI  OBJECT IDENTIFIER ::= { hpSwitch 249 }
hp512048GSI                     OBJECT IDENTIFIER ::= { hpSwitch 250 }
hp512016GSI                     OBJECT IDENTIFIER ::= { hpSwitch 251 }
hp512024GSI                     OBJECT IDENTIFIER ::= { hpSwitch 252 }
hp512024GPoEPlus370WSI          OBJECT IDENTIFIER ::= { hpSwitch 253 }
hp51208GPoEPlus65WSI            OBJECT IDENTIFIER ::= { hpSwitch 254 }
hp51208GPoEPlus180WSI           OBJECT IDENTIFIER ::= { hpSwitch 255 }
hp7502JD242C                    OBJECT IDENTIFIER ::= { hpSwitch 256 }
hp7503JD240C                    OBJECT IDENTIFIER ::= { hpSwitch 257 }
hp7506JD239C                    OBJECT IDENTIFIER ::= { hpSwitch 258 }
hp7510JD238C                    OBJECT IDENTIFIER ::= { hpSwitch 259 }
hpFF595032Q28                   OBJECT IDENTIFIER ::= { hpSwitch 260 }
hpFF595032Q28TAA                OBJECT IDENTIFIER ::= { hpSwitch 261 }
hpFF590048XG4QSFF               OBJECT IDENTIFIER ::= { hpSwitch 262 }
hpFF590048XG4QSFFTAA            OBJECT IDENTIFIER ::= { hpSwitch 263 }
hpeFF594048SFPPlus6QSFP28       OBJECT IDENTIFIER ::= { hpSwitch 264 }
hpeFF594048XGT6QSFP28           OBJECT IDENTIFIER ::= { hpSwitch 265 }
hpeFF594048XGT6QSFPPlus         OBJECT IDENTIFIER ::= { hpSwitch 266 }
hpeFF594048SFPPlus6QSFPPlus     OBJECT IDENTIFIER ::= { hpSwitch 267 }
hpeFF594032QSFPPlus             OBJECT IDENTIFIER ::= { hpSwitch 268 }
hpeFF59402Slot                  OBJECT IDENTIFIER ::= { hpSwitch 269 }
hpeFF59404Slot                  OBJECT IDENTIFIER ::= { hpSwitch 270 }
hpeFF594048SFPPlus6QSFP28TAA    OBJECT IDENTIFIER ::= { hpSwitch 271 }
hpeFF594048XGT6QSFP28TAA        OBJECT IDENTIFIER ::= { hpSwitch 272 }
hpeFF12912E                     OBJECT IDENTIFIER ::= { hpSwitch 273 }
hpevLNS1000                     OBJECT IDENTIFIER ::= { hpSwitch 274 }
hpevLNS2000                     OBJECT IDENTIFIER ::= { hpSwitch 275 }
hpeFF595048SFP288QSFP28         OBJECT IDENTIFIER ::= { hpSwitch 276 }
hpeFF59504slot                  OBJECT IDENTIFIER ::= { hpSwitch 277 }
hpeFF12902E                     OBJECT IDENTIFIER ::= { hpSwitch 278 }
hpS58V3R652XG4QSFP2SFPPLUS      OBJECT IDENTIFIER ::= { hpSwitch 279 }
hpS58V3R652XG4QSFP2SFPPLUSTAA   OBJECT IDENTIFIER ::= { hpSwitch 280 }
hpeFF12901E                     OBJECT IDENTIFIER ::= { hpSwitch 281 }
hpe5980-48SFP-6QSFP28-ExtTable         OBJECT IDENTIFIER ::= { hpSwitch 282 }
hpe5980-48SFP-6QSFP28           OBJECT IDENTIFIER ::= { hpSwitch 283 }
hpeFlexFabric-5955-64QSFP28     OBJECT IDENTIFIER ::= { hpSwitch 284 }
hpeFlexFabric-5945-48SFP28-8QSFP28     OBJECT IDENTIFIER ::= { hpSwitch 285 }
hpeFlexFabric-5945-4-slot              OBJECT IDENTIFIER ::= { hpSwitch 286 }
hpe5710-30HF                    OBJECT IDENTIFIER ::= { hpSwitch 287 }
hpe5710-54HF                    OBJECT IDENTIFIER ::= { hpSwitch 288 }
hpe5710-54HT                    OBJECT IDENTIFIER ::= { hpSwitch 289 }
hpe5710-30HT                    OBJECT IDENTIFIER ::= { hpSwitch 290 }
hpeFlexFabric-5945-32QSFP28     OBJECT IDENTIFIER ::= { hpSwitch 291 }
hpeFlexFabric-5945-2-slot       OBJECT IDENTIFIER ::= { hpSwitch 292 }
hpe5130-48G-PoE-4SFP-XI         OBJECT IDENTIFIER ::= { hpSwitch 293 }
hpe5130-48G-4SFP-XI             OBJECT IDENTIFIER ::= { hpSwitch 294 }
hpe5140-24G-4SFP-EI             OBJECT IDENTIFIER ::= { hpSwitch 295 }
hpe5140-24G-SFP-4SFP-EI         OBJECT IDENTIFIER ::= { hpSwitch 296 }
hpe5140-48G-4SFP-EI             OBJECT IDENTIFIER ::= { hpSwitch 297 }
hpe5140-24G-PoE-4SFP-EI         OBJECT IDENTIFIER ::= { hpSwitch 298 }
hpe5140-48G-PoE-4SFP-EI         OBJECT IDENTIFIER ::= { hpSwitch 299 }
hpe5140-24G-POE-2SFP-2XGT-EI    OBJECT IDENTIFIER ::= { hpSwitch 300 }
hpe5140-48G-POE-2SFP-2XGT-EI    OBJECT IDENTIFIER ::= { hpSwitch 301 }
hpeFlexFabric-5944-48XGT-6QS28  OBJECT IDENTIFIER ::= { hpSwitch 302 }
hpe5901AF-48G-4XG-2QSFPPlus-Switch  OBJECT IDENTIFIER ::= { hpSwitch 303 }
hpe5140-8G-2SFP-2GT-EI-Sw           OBJECT IDENTIFIER ::= { hpSwitch 304 }
hpe5140-24G-2SFPPlus-2XGT-EI-Sw     OBJECT IDENTIFIER ::= { hpSwitch 305 }
hpe5520-24G-SFP-4SFPPlus-HI         OBJECT IDENTIFIER ::= { hpSwitch 306 }
hpe5520-24G-PoEPlus-4SFPPlus-HI     OBJECT IDENTIFIER ::= { hpSwitch 307 }
hpe5520-24G-4SFPPlus-HI             OBJECT IDENTIFIER ::= { hpSwitch 308 }
hpe5520-48G-4SFPPlus-HI             OBJECT IDENTIFIER ::= { hpSwitch 309 }
hpe5520-48G-PoEPlus-4SFPPlus-HI     OBJECT IDENTIFIER ::= { hpSwitch 310 }
hpe7506X                            OBJECT IDENTIFIER ::= { hpSwitch 311 }
hpe7503X                            OBJECT IDENTIFIER ::= { hpSwitch 312 }
hpe7510X                            OBJECT IDENTIFIER ::= { hpSwitch 313 }
hpe5140-24G-4SFPPlus1-slot-HI-Sw           OBJECT IDENTIFIER ::= { hpSwitch 314 }
hpe5140-48G-4SFPPlus1-slot-HI-Sw           OBJECT IDENTIFIER ::= { hpSwitch 315 }
hpe5140-24G-PoEPlus4SFPPlus1-slot-HI-Sw    OBJECT IDENTIFIER ::= { hpSwitch 316 }
hpe5140-48G-PoEPlus4SFPPlus1-slot-HI-Sw    OBJECT IDENTIFIER ::= { hpSwitch 317 }
hpe5600HI-24P-PoE8-MGig-1-Slot-Sw          OBJECT IDENTIFIER ::= { hpSwitch 318 }
hpe5600HI-48P-PoE8-MGig-4QSFPPlus-1s-Sw    OBJECT IDENTIFIER ::= { hpSwitch 319 }
hpe5960-24QSFP56-8QSFP-DD                  OBJECT IDENTIFIER ::= { hpSwitch 320 }
hpe5960-32QSFP-DD                          OBJECT IDENTIFIER ::= { hpSwitch 321 }
hpNW-CW-5120v3-8G-PoE-2SFP-Sw              OBJECT IDENTIFIER ::= { hpSwitch 322 }

-- begin hpRouter
hpAMSR900                       OBJECT IDENTIFIER ::= { hpRouter 1 }
hpAMSR920                       OBJECT IDENTIFIER ::= { hpRouter 2 }
hpAMSR2010                      OBJECT IDENTIFIER ::= { hpRouter 3 }
hpAMSR2011                      OBJECT IDENTIFIER ::= { hpRouter 4 }
hpAMSR2012                      OBJECT IDENTIFIER ::= { hpRouter 5 }
hpAMSR2012T                     OBJECT IDENTIFIER ::= { hpRouter 6 }
hpAMSR2013                      OBJECT IDENTIFIER ::= { hpRouter 7 }
hpAMSR2020                      OBJECT IDENTIFIER ::= { hpRouter 8 }
hpAMSR2021                      OBJECT IDENTIFIER ::= { hpRouter 9 }
hpAMSR2040                      OBJECT IDENTIFIER ::= { hpRouter 10 }
hpAMSR3010                      OBJECT IDENTIFIER ::= { hpRouter 11 }
hpAMSR3011E                     OBJECT IDENTIFIER ::= { hpRouter 12 }
hpAMSR3011F                     OBJECT IDENTIFIER ::= { hpRouter 13 }
hpAMSR3016                      OBJECT IDENTIFIER ::= { hpRouter 14 }
hpAMSR3020                      OBJECT IDENTIFIER ::= { hpRouter 15 }
hpAMSR3040                      OBJECT IDENTIFIER ::= { hpRouter 16 }
hpAMSR3060                      OBJECT IDENTIFIER ::= { hpRouter 17 }
hpAMSR5040                      OBJECT IDENTIFIER ::= { hpRouter 18 }
hpAMSR5060                      OBJECT IDENTIFIER ::= { hpRouter 19 }
hpA6602                         OBJECT IDENTIFIER ::= { hpRouter 20 }
hpA6604                         OBJECT IDENTIFIER ::= { hpRouter 21 }
hpA6608                         OBJECT IDENTIFIER ::= { hpRouter 22 }
hpA6616                         OBJECT IDENTIFIER ::= { hpRouter 23 }
hpAMSR900W                      OBJECT IDENTIFIER ::= { hpRouter 24 }
hpAMSR900WNA                    OBJECT IDENTIFIER ::= { hpRouter 25 }
hpAMSR920W                      OBJECT IDENTIFIER ::= { hpRouter 26 }
hpAMSR920WNA                    OBJECT IDENTIFIER ::= { hpRouter 27 }
hpAMSR2012W                     OBJECT IDENTIFIER ::= { hpRouter 28 }
hpAMSR2012TW                    OBJECT IDENTIFIER ::= { hpRouter 29 }
hpAMSR2012TWNA                  OBJECT IDENTIFIER ::= { hpRouter 30 }
hpAMSR2013W                     OBJECT IDENTIFIER ::= { hpRouter 31 }
hpAMSR2013WNA                   OBJECT IDENTIFIER ::= { hpRouter 32 }
hpAMSR2020S                     OBJECT IDENTIFIER ::= { hpRouter 33 }
hpAMSR2021S                     OBJECT IDENTIFIER ::= { hpRouter 34 }
hpAMSR2040S                     OBJECT IDENTIFIER ::= { hpRouter 35 }
hpAMSR3010DC                    OBJECT IDENTIFIER ::= { hpRouter 36 }
hpAMSR3016POE                   OBJECT IDENTIFIER ::= { hpRouter 37 }
hpAMSR3020AS                    OBJECT IDENTIFIER ::= { hpRouter 38 }
hpAMSR3020POE                   OBJECT IDENTIFIER ::= { hpRouter 39 }
hpAMSR3020DC                    OBJECT IDENTIFIER ::= { hpRouter 40 }
hpAMSR3040AS                    OBJECT IDENTIFIER ::= { hpRouter 41 }
hpAMSR3040POE                   OBJECT IDENTIFIER ::= { hpRouter 42 }
hpAMSR3040DC                    OBJECT IDENTIFIER ::= { hpRouter 43 }
hpAMSR3060AS                    OBJECT IDENTIFIER ::= { hpRouter 44 }
hpAMSR3060POE                   OBJECT IDENTIFIER ::= { hpRouter 45 }
hpAMSR3060DC                    OBJECT IDENTIFIER ::= { hpRouter 46 }
hpAMSR5040DC                    OBJECT IDENTIFIER ::= { hpRouter 47 }
hpAMSR5060DC                    OBJECT IDENTIFIER ::= { hpRouter 48 }
hpA8805                         OBJECT IDENTIFIER ::= { hpRouter 49 }
hpA8808                         OBJECT IDENTIFIER ::= { hpRouter 50 }
hpA8812                         OBJECT IDENTIFIER ::= { hpRouter 51 }
hpAOAPFICV2                     OBJECT IDENTIFIER ::= { hpRouter 52 }
hpAOAPMIMV2                     OBJECT IDENTIFIER ::= { hpRouter 53 }
hpAOAPSMIMV2                    OBJECT IDENTIFIER ::= { hpRouter 54 }
hpMSR2003AC                     OBJECT IDENTIFIER ::= { hpRouter 55 }
hpMSR3012AC                     OBJECT IDENTIFIER ::= { hpRouter 56 }
hpMSR3012DC                     OBJECT IDENTIFIER ::= { hpRouter 57 }
hpMSR3024AC                     OBJECT IDENTIFIER ::= { hpRouter 58 }
hpMSR3024DC                     OBJECT IDENTIFIER ::= { hpRouter 59 }
hpMSR3024POE                    OBJECT IDENTIFIER ::= { hpRouter 60 }
hpMSR3044                       OBJECT IDENTIFIER ::= { hpRouter 61 }
hpMSR3064                       OBJECT IDENTIFIER ::= { hpRouter 62 }
hpMSR4060                       OBJECT IDENTIFIER ::= { hpRouter 63 }
hpMSR4080                       OBJECT IDENTIFIER ::= { hpRouter 64 }
hpHSR6602G                      OBJECT IDENTIFIER ::= { hpRouter 65 }
hpHSR6602XG                     OBJECT IDENTIFIER ::= { hpRouter 66 }
hpHSR6802                       OBJECT IDENTIFIER ::= { hpRouter 67 }
hpHSR6804                       OBJECT IDENTIFIER ::= { hpRouter 68 }
hpHSR6808                       OBJECT IDENTIFIER ::= { hpRouter 69 }
hpMSR930                        OBJECT IDENTIFIER ::= { hpRouter 70 }
hpMSR930G                       OBJECT IDENTIFIER ::= { hpRouter 71 }
hpMSR931                        OBJECT IDENTIFIER ::= { hpRouter 72 }
hpMSR931G                       OBJECT IDENTIFIER ::= { hpRouter 73 }
hpMSR931GG                      OBJECT IDENTIFIER ::= { hpRouter 74 }
hpMSR930W                       OBJECT IDENTIFIER ::= { hpRouter 75 }
hpMSR9304GLTEV                  OBJECT IDENTIFIER ::= { hpRouter 76 }
hpMSR933                        OBJECT IDENTIFIER ::= { hpRouter 77 }
hpMSR933G                       OBJECT IDENTIFIER ::= { hpRouter 78 }
hpMSR935                        OBJECT IDENTIFIER ::= { hpRouter 79 }
hpMSR935W                       OBJECT IDENTIFIER ::= { hpRouter 80 }
hpMSR935G                       OBJECT IDENTIFIER ::= { hpRouter 81 }
hpMSR936W                       OBJECT IDENTIFIER ::= { hpRouter 82 }
hpMSR9304GLTEG                  OBJECT IDENTIFIER ::= { hpRouter 83 }
hpMSR930LE                      OBJECT IDENTIFIER ::= { hpRouter 84 }
hpMSR930GLE                     OBJECT IDENTIFIER ::= { hpRouter 85 }
hpMSR931LE                      OBJECT IDENTIFIER ::= { hpRouter 86 }
hpMSR931GLE                     OBJECT IDENTIFIER ::= { hpRouter 87 }
hpMSR931DGLE                    OBJECT IDENTIFIER ::= { hpRouter 88 }
hpMSR930WLE                     OBJECT IDENTIFIER ::= { hpRouter 89 }
hpMSR9304GLTEA                  OBJECT IDENTIFIER ::= { hpRouter 90 }
hpMSR933GLE                     OBJECT IDENTIFIER ::= { hpRouter 91 }
hpMSR935LE                      OBJECT IDENTIFIER ::= { hpRouter 92 }
hpMSR935WLE                     OBJECT IDENTIFIER ::= { hpRouter 93 }
hpMSR935GLE                     OBJECT IDENTIFIER ::= { hpRouter 94 }
hpMSR9304GLTEGLE                OBJECT IDENTIFIER ::= { hpRouter 95 }
hpVSR                           OBJECT IDENTIFIER ::= { hpRouter 96 }
hpVSR1001                       OBJECT IDENTIFIER ::= { hpRouter 97 }
hpVSR1004                       OBJECT IDENTIFIER ::= { hpRouter 98 }
hpVSR1008                       OBJECT IDENTIFIER ::= { hpRouter 99 }
hpMSR10038                      OBJECT IDENTIFIER ::= { hpRouter 100 }
hpMSR100414                     OBJECT IDENTIFIER ::= { hpRouter 101 }
hpVSR1000                       OBJECT IDENTIFIER ::= { hpRouter 102 }
hpMSR200424                     OBJECT IDENTIFIER ::= { hpRouter 103 }
hpMSR200448                     OBJECT IDENTIFIER ::= { hpRouter 104 }
hpHSR6602GTAA                   OBJECT IDENTIFIER ::= { hpRouter 105 }
hpHSR6602XGTAA                  OBJECT IDENTIFIER ::= { hpRouter 106 }
hpMSR10024                      OBJECT IDENTIFIER ::= { hpRouter 107 }
hpNSC1000                       OBJECT IDENTIFIER ::= { hpRouter 108 }
hpMSR930WNA                     OBJECT IDENTIFIER ::= { hpRouter 109 }
hpMSR935WNA                     OBJECT IDENTIFIER ::= { hpRouter 110 }
hpMSR2003TAA                    OBJECT IDENTIFIER ::= { hpRouter 111 }
hpMSR3024TAA                    OBJECT IDENTIFIER ::= { hpRouter 112 }
hpMSR3044TAA                    OBJECT IDENTIFIER ::= { hpRouter 113 }
hpMSR935TI                      OBJECT IDENTIFIER ::= { hpRouter 114 }
hpMSR933TI                      OBJECT IDENTIFIER ::= { hpRouter 115 }
hpMSR931TI                      OBJECT IDENTIFIER ::= { hpRouter 116 }
hpMSR10038S                     OBJECT IDENTIFIER ::= { hpRouter 117 }
hpMSR932                        OBJECT IDENTIFIER ::= { hpRouter 118 }
hpMSR932W                       OBJECT IDENTIFIER ::= { hpRouter 119 }
hpMSR932WNA                     OBJECT IDENTIFIER ::= { hpRouter 120 }
hpMSR9328                       OBJECT IDENTIFIER ::= { hpRouter 121 }
hpMSR9328W                      OBJECT IDENTIFIER ::= { hpRouter 122 }
hpMSR9328WNA                    OBJECT IDENTIFIER ::= { hpRouter 123 }
hpVBRAS1000                     OBJECT IDENTIFIER ::= { hpRouter 124 }
hpHSR6802E                      OBJECT IDENTIFIER ::= { hpRouter 125 }
hpHSR6804E                      OBJECT IDENTIFIER ::= { hpRouter 126 }
hpHSR6808E                      OBJECT IDENTIFIER ::= { hpRouter 127 }
hpMSR93204GLTEGV2               OBJECT IDENTIFIER ::= { hpRouter 128 }
hpMSR93204GLTEAVS               OBJECT IDENTIFIER ::= { hpRouter 129 }
hpMSR954                        OBJECT IDENTIFIER ::= { hpRouter 130 }
hpMSR954W                       OBJECT IDENTIFIER ::= { hpRouter 131 }
hpMSR954WLTEAM                  OBJECT IDENTIFIER ::= { hpRouter 132 }
hpMSR954WLTE                    OBJECT IDENTIFIER ::= { hpRouter 133 }
hpMSR958                        OBJECT IDENTIFIER ::= { hpRouter 134 }
hpMSR958POE                     OBJECT IDENTIFIER ::= { hpRouter 135 }
hpMSR930B                       OBJECT IDENTIFIER ::= { hpRouter 136 }
hpMSR930GB                      OBJECT IDENTIFIER ::= { hpRouter 137 }
hpMSR931B                       OBJECT IDENTIFIER ::= { hpRouter 138 }
hpMSR931GB                      OBJECT IDENTIFIER ::= { hpRouter 139 }
hpMSR931DGB                     OBJECT IDENTIFIER ::= { hpRouter 140 }
hpMSR935B                       OBJECT IDENTIFIER ::= { hpRouter 141 }
hpMSR935GB                      OBJECT IDENTIFIER ::= { hpRouter 142 }
hpMSR930WNAB                    OBJECT IDENTIFIER ::= { hpRouter 143 }
hpMSR954D4G                     OBJECT IDENTIFIER ::= { hpRouter 144 }
hpMSR3012ACE                    OBJECT IDENTIFIER ::= { hpRouter 145 }
hpMSR951R-W-AM                  OBJECT IDENTIFIER ::= { hpRouter 146 }
hpMSR951R-W-WW                  OBJECT IDENTIFIER ::= { hpRouter 147 }
hpMSR3004                       OBJECT IDENTIFIER ::= { hpRouter 148 }
hpMSR3620DP                     OBJECT IDENTIFIER ::= { hpRouter 149 }
hpMSR3046                       OBJECT IDENTIFIER ::= { hpRouter 150 }
hpMSR1002X4                     OBJECT IDENTIFIER ::= { hpRouter 151 }
hpMSR3048                       OBJECT IDENTIFIER ::= { hpRouter 152 }
hpMSR3026                       OBJECT IDENTIFIER ::= { hpRouter 153 }
hpMSR3016                       OBJECT IDENTIFIER ::= { hpRouter 154 }
hpMSR958X                       OBJECT IDENTIFIER ::= { hpRouter 155 }
hpMSR2003X                      OBJECT IDENTIFIER ::= { hpRouter 156 }
hpMSR954-V2                     OBJECT IDENTIFIER ::= { hpRouter 157 }


-- begin hpWireless
hpAWA2610EAGNFAT                OBJECT IDENTIFIER ::= { hpWireless 1 }
hpAWA2620EAGNFAT                OBJECT IDENTIFIER ::= { hpWireless 2 }
hpAWA2620AGNFAT                 OBJECT IDENTIFIER ::= { hpWireless 3 }
hpA7500LSQM3WCMB0               OBJECT IDENTIFIER ::= { hpWireless 4 }
hpA9500LSRM2WCM2A1              OBJECT IDENTIFIER ::= { hpWireless 5 }
hpA5800LSWM2WCM10               OBJECT IDENTIFIER ::= { hpWireless 6 }
hpA5800LSWM2WCM20               OBJECT IDENTIFIER ::= { hpWireless 7 }
hpAWX5004EWPXZ65004             OBJECT IDENTIFIER ::= { hpWireless 8 }
hpAWX5002EWPXZ75002             OBJECT IDENTIFIER ::= { hpWireless 9 }
hpA3000E                        OBJECT IDENTIFIER ::= { hpWireless 10 }
hpA3000ELSW                     OBJECT IDENTIFIER ::= { hpWireless 11 }
hpAWA3620AGN                    OBJECT IDENTIFIER ::= { hpWireless 12 }
hpAWA3622AGN                    OBJECT IDENTIFIER ::= { hpWireless 13 }
hpAWA3610GN                     OBJECT IDENTIFIER ::= { hpWireless 14 }
hpAWA2620XAGN                   OBJECT IDENTIFIER ::= { hpWireless 15 }
hpLSU3WCMD0                     OBJECT IDENTIFIER ::= { hpWireless 16 }
hpWX3024EWCM                    OBJECT IDENTIFIER ::= { hpWireless 17 }
hpWX3024ELSW                    OBJECT IDENTIFIER ::= { hpWireless 18 }
hpWX3010EWCM                    OBJECT IDENTIFIER ::= { hpWireless 19 }
hpWX3010ELSW                    OBJECT IDENTIFIER ::= { hpWireless 20 }
hpLSU3WCMD0TAA                  OBJECT IDENTIFIER ::= { hpWireless 21 }
hpWX3024ETAAWCM                 OBJECT IDENTIFIER ::= { hpWireless 22 }
hpWX3024ETAALSW                 OBJECT IDENTIFIER ::= { hpWireless 23 }
hpWX3010ETAAWCM                 OBJECT IDENTIFIER ::= { hpWireless 24 }
hpWX3010ETAALSW                 OBJECT IDENTIFIER ::= { hpWireless 25 }




-- begin hpSecurity
hpSecBladeIMFWII                OBJECT IDENTIFIER ::= { hpSecurity 1 }
hpSecBladeIMSSL                 OBJECT IDENTIFIER ::= { hpSecurity 2 }
hpSecBladeIMLB                  OBJECT IDENTIFIER ::= { hpSecurity 3 }
hpSecBladeLSQ1FWBSC0            OBJECT IDENTIFIER ::= { hpSecurity 4 }
hpSecBladeLSQM1LBC0             OBJECT IDENTIFIER ::= { hpSecurity 5 }
hpSecBladeLSQ1NSMSC0            OBJECT IDENTIFIER ::= { hpSecurity 6 }
hpSecBladeLSR1FW2A1             OBJECT IDENTIFIER ::= { hpSecurity 7 }
hpSecBladeLSR1LB1A1             OBJECT IDENTIFIER ::= { hpSecurity 8 }
hpSecBladeLSR1NSM1A1            OBJECT IDENTIFIER ::= { hpSecurity 9 }
hpSecBladeLST1FW2A1             OBJECT IDENTIFIER ::= { hpSecurity 10 }
hpSecBladeLST1LB1A1             OBJECT IDENTIFIER ::= { hpSecurity 11 }
hpSecBladeLST1NSM1A1            OBJECT IDENTIFIER ::= { hpSecurity 12 }
hpSecBladeLSWM1FW10             OBJECT IDENTIFIER ::= { hpSecurity 13 }
hpSecBladeSPEFWM200             OBJECT IDENTIFIER ::= { hpSecurity 14 }
hpAF5000                        OBJECT IDENTIFIER ::= { hpSecurity 15 }
hpAF1000E                       OBJECT IDENTIFIER ::= { hpSecurity 16 }
hpAU200S                        OBJECT IDENTIFIER ::= { hpSecurity 17 }
hpAU200A                        OBJECT IDENTIFIER ::= { hpSecurity 18 }
hpAF1000SEI                     OBJECT IDENTIFIER ::= { hpSecurity 19 }
hpAF1000AEI                     OBJECT IDENTIFIER ::= { hpSecurity 20 }
hpSecBladeLST1FW3A1             OBJECT IDENTIFIER ::= { hpSecurity 21 }
hpSecBladeLSU1FWCEA0            OBJECT IDENTIFIER ::= { hpSecurity 22 }
hpF5000C                        OBJECT IDENTIFIER ::= { hpSecurity 23 }
hpF5000S                        OBJECT IDENTIFIER ::= { hpSecurity 24 }
hpVFW1000                       OBJECT IDENTIFIER ::= { hpSecurity 25 }
hpSecBladeLSX1FWCEA1            OBJECT IDENTIFIER ::= { hpSecurity 26 }
hpVMSGVLB1000                   OBJECT IDENTIFIER ::= { hpSecurity 27 }
hpSecBlade3Context              OBJECT IDENTIFIER ::= { hpSecurity 28 }
hpvFW2000                       OBJECT IDENTIFIER ::= { hpSecurity 29 }
hpvLB2000                       OBJECT IDENTIFIER ::= { hpSecurity 30 }
-- Joint Vendor products

-- HIK products
-- OID of hh3cJointVendorHik is 1.3.6.1.4.1.25506.12.1.1
hh3cJointVendorHik              OBJECT IDENTIFIER ::= { hh3cJointVendorId 1 }

dS-3E2728F-H                    OBJECT IDENTIFIER ::= { hh3cJointVendorHik 1 }
dS-3E3530-H                     OBJECT IDENTIFIER ::= { hh3cJointVendorHik 2 }
dS-3E3528F-H                    OBJECT IDENTIFIER ::= { hh3cJointVendorHik 3 }
dS-3E3554-H                     OBJECT IDENTIFIER ::= { hh3cJointVendorHik 4 }
dS-3E3730-H                     OBJECT IDENTIFIER ::= { hh3cJointVendorHik 5 }
dS-3E3728F-H                    OBJECT IDENTIFIER ::= { hh3cJointVendorHik 6 }
dS-3E3754-H                     OBJECT IDENTIFIER ::= { hh3cJointVendorHik 7 }
dS-3E7602                       OBJECT IDENTIFIER ::= { hh3cJointVendorHik 8 }
dS-3E7606                       OBJECT IDENTIFIER ::= { hh3cJointVendorHik 9 }
dS-3E2310-H                     OBJECT IDENTIFIER ::= { hh3cJointVendorHik 10 }
dS-3E2318-H                     OBJECT IDENTIFIER ::= { hh3cJointVendorHik 11 }
dS-3E2326-H                     OBJECT IDENTIFIER ::= { hh3cJointVendorHik 12 }
dS-3E2528-H                     OBJECT IDENTIFIER ::= { hh3cJointVendorHik 13 }
dS-3E2552-H                     OBJECT IDENTIFIER ::= { hh3cJointVendorHik 14 }
dS-3E2310P-H                    OBJECT IDENTIFIER ::= { hh3cJointVendorHik 15 }
dS-3E2318P-H                    OBJECT IDENTIFIER ::= { hh3cJointVendorHik 16 }
dS-3E2326P-H                    OBJECT IDENTIFIER ::= { hh3cJointVendorHik 17 }
dS-3E7610X                      OBJECT IDENTIFIER ::= { hh3cJointVendorHik 18 }
ds-3E2528-H-B                   OBJECT IDENTIFIER ::= { hh3cJointVendorHik 19 }
ds-3E2552-H-B                   OBJECT IDENTIFIER ::= { hh3cJointVendorHik 20 }
ds-3E3926-H                     OBJECT IDENTIFIER ::= { hh3cJointVendorHik 21 }
ds-3E3950-H                     OBJECT IDENTIFIER ::= { hh3cJointVendorHik 22 }
dS-3E3528-H                     OBJECT IDENTIFIER ::= { hh3cJointVendorHik 23 }
dS-3E3552-H                     OBJECT IDENTIFIER ::= { hh3cJointVendorHik 24 }
dS-3E3528F-H-B                  OBJECT IDENTIFIER ::= { hh3cJointVendorHik 25 }
dS-3E3552F-H                    OBJECT IDENTIFIER ::= { hh3cJointVendorHik 26 }
dS-3E2728-H                     OBJECT IDENTIFIER ::= { hh3cJointVendorHik 27 }
dS-3E2752-H                     OBJECT IDENTIFIER ::= { hh3cJointVendorHik 28 }
dS-3E3728-H                     OBJECT IDENTIFIER ::= { hh3cJointVendorHik 29 }
dS-3E3752-H                     OBJECT IDENTIFIER ::= { hh3cJointVendorHik 30 }
dS-3E3728F-HB                   OBJECT IDENTIFIER ::= { hh3cJointVendorHik 31 }
dS-3E3752F-H                    OBJECT IDENTIFIER ::= { hh3cJointVendorHik 32 }
dS-3E7603                       OBJECT IDENTIFIER ::= { hh3cJointVendorHik 33 }
dS-3E12508                      OBJECT IDENTIFIER ::= { hh3cJointVendorHik 34 }
dS-DS-3E3752P-H                 OBJECT IDENTIFIER ::= { hh3cJointVendorHik 35 }
dS-DS-3E3728P-H                 OBJECT IDENTIFIER ::= { hh3cJointVendorHik 36 }
dS-DS-3E2428-H                  OBJECT IDENTIFIER ::= { hh3cJointVendorHik 37 }
dS-DS-3E2452-H                  OBJECT IDENTIFIER ::= { hh3cJointVendorHik 38 }
dS-DS-3E2428P-H                 OBJECT IDENTIFIER ::= { hh3cJointVendorHik 39 }
dS-DS-3E2410P-H                 OBJECT IDENTIFIER ::= { hh3cJointVendorHik 40 }
dS-DS-3E2420P-H                 OBJECT IDENTIFIER ::= { hh3cJointVendorHik 41 }
dS-DS-3E2418-H                  OBJECT IDENTIFIER ::= { hh3cJointVendorHik 42 }
dS-DS-3E2410-H                  OBJECT IDENTIFIER ::= { hh3cJointVendorHik 43 }
dS-DS-3E2520-H                  OBJECT IDENTIFIER ::= { hh3cJointVendorHik 44 }
dS-DS-3E2510-H                  OBJECT IDENTIFIER ::= { hh3cJointVendorHik 45 }
dS-3R200-L00H                   OBJECT IDENTIFIER ::= { hh3cJointVendorHik 46 }
dS-3R600-W04H                   OBJECT IDENTIFIER ::= { hh3cJointVendorHik 47 }
dS-3R400-L04H                   OBJECT IDENTIFIER ::= { hh3cJointVendorHik 48 }
dS-DS-3E2728F-HB                OBJECT IDENTIFIER ::= { hh3cJointVendorHik 49 }
dS-3WS128-H                     OBJECT IDENTIFIER ::= { hh3cJointVendorHik 50 }
dS-ZD-WS40-H                    OBJECT IDENTIFIER ::= { hh3cJointVendorHik 51 }
dS-ZD-WS80-H                    OBJECT IDENTIFIER ::= { hh3cJointVendorHik 52 }
dS-ZD-WS128-H                   OBJECT IDENTIFIER ::= { hh3cJointVendorHik 53 }
dS-DS-3E2528P-H                 OBJECT IDENTIFIER ::= { hh3cJointVendorHik 54 }
dS-DS-3E2552P-H                 OBJECT IDENTIFIER ::= { hh3cJointVendorHik 55 }
dS-ZD-S2552-H                   OBJECT IDENTIFIER ::= { hh3cJointVendorHik 56 }
dS-DS-3E2510P-H                 OBJECT IDENTIFIER ::= { hh3cJointVendorHik 57 }
dS-ZD-S2528P-H                  OBJECT IDENTIFIER ::= { hh3cJointVendorHik 58 }
dS-ZD-S2728-H                   OBJECT IDENTIFIER ::= { hh3cJointVendorHik 59 }
dS-ZD-S3552-H                   OBJECT IDENTIFIER ::= { hh3cJointVendorHik 60 }
dS-ZD-S2528-H                   OBJECT IDENTIFIER ::= { hh3cJointVendorHik 61 }
dS-ZD-S3728F-H                  OBJECT IDENTIFIER ::= { hh3cJointVendorHik 62 }
dS-ZD-S2752-H                   OBJECT IDENTIFIER ::= { hh3cJointVendorHik 63 }
dS-ZD-S3528-H                   OBJECT IDENTIFIER ::= { hh3cJointVendorHik 64 }
dS-ZD-S3728-H                   OBJECT IDENTIFIER ::= { hh3cJointVendorHik 65 }
dS-ZD-S2728F-H                  OBJECT IDENTIFIER ::= { hh3cJointVendorHik 66 }
dS-DS-3WS1024-H                 OBJECT IDENTIFIER ::= { hh3cJointVendorHik 67 }
dS-3R600-X04H-I4-8-480          OBJECT IDENTIFIER ::= { hh3cJointVendorHik 68 }
dS-ZD-R200-L00H                 OBJECT IDENTIFIER ::= { hh3cJointVendorHik 69 }
dS-ZD-R300-L00H                 OBJECT IDENTIFIER ::= { hh3cJointVendorHik 70 }
dS-3R600-X04H-I8-32-64          OBJECT IDENTIFIER ::= { hh3cJointVendorHik 71 }
dS-3R600-X04H-I4-16-480         OBJECT IDENTIFIER ::= { hh3cJointVendorHik 72 }
dS-3E7806                       OBJECT IDENTIFIER ::= { hh3cJointVendorHik 73 }
dS-3E7803                       OBJECT IDENTIFIER ::= { hh3cJointVendorHik 74 }
dS-DS-3WS288-H                  OBJECT IDENTIFIER ::= { hh3cJointVendorHik 75 }
dS-3E7803M                      OBJECT IDENTIFIER ::= { hh3cJointVendorHik 76 }
zD-S7803M                       OBJECT IDENTIFIER ::= { hh3cJointVendorHik 77 }
dS-DS-3E3728F-H                 OBJECT IDENTIFIER ::= { hh3cJointVendorHik 78 }
dS-DS-3E2552-H                  OBJECT IDENTIFIER ::= { hh3cJointVendorHik 79 }
dS-DS-3E2528-H                  OBJECT IDENTIFIER ::= { hh3cJointVendorHik 80 }
dS-3R3000-L08H                  OBJECT IDENTIFIER ::= { hh3cJointVendorHik 81 }
dS-3E12508X                     OBJECT IDENTIFIER ::= { hh3cJointVendorHik 82 }
dS-3E12512X                     OBJECT IDENTIFIER ::= { hh3cJointVendorHik 83 }
dS-ZD-WAX18-S-M                 OBJECT IDENTIFIER ::= { hh3cJointVendorHik 84 }
dS-ZD-WAX18-S-X                 OBJECT IDENTIFIER ::= { hh3cJointVendorHik 85 }
dS-ZD-WAX30-S-W                 OBJECT IDENTIFIER ::= { hh3cJointVendorHik 86 }
dS-DS-3E3916-H                  OBJECT IDENTIFIER ::= { hh3cJointVendorHik 87 }
dS-DS-3E3924-H                  OBJECT IDENTIFIER ::= { hh3cJointVendorHik 88 }
dS-DS-3E2728P-H                 OBJECT IDENTIFIER ::= { hh3cJointVendorHik 89 }
dS-DS-3E2520P-H                 OBJECT IDENTIFIER ::= { hh3cJointVendorHik 90 }
dS-DS-3E2752P-H                 OBJECT IDENTIFIER ::= { hh3cJointVendorHik 91 }

dS-ZD-S5200-16GF8GC4X-H         OBJECT IDENTIFIER ::= { hh3cJointVendorHik 92 }
dS-ZD-S5200-48GT4GF-H           OBJECT IDENTIFIER ::= { hh3cJointVendorHik 93 }
dS-ZD-S3200-24GT4X-H            OBJECT IDENTIFIER ::= { hh3cJointVendorHik 94 }
dS-ZD-S3200-48GT4X-H            OBJECT IDENTIFIER ::= { hh3cJointVendorHik 95 }
dS-ZD-S3200-24GT4GF-H           OBJECT IDENTIFIER ::= { hh3cJointVendorHik 96 }
dS-ZD-S3200P-24GP4GF-370W-H     OBJECT IDENTIFIER ::= { hh3cJointVendorHik 97 }
dS-ZD-S3200-24GF2GC2X-H         OBJECT IDENTIFIER ::= { hh3cJointVendorHik 98 }
dS-ZD-S5200-24GT4GF-H           OBJECT IDENTIFIER ::= { hh3cJointVendorHik 99 }
dS-ZD-S3200-48GT4GF-H           OBJECT IDENTIFIER ::= { hh3cJointVendorHik 100 }
dS-ZD-S5200-24GT4X-H            OBJECT IDENTIFIER ::= { hh3cJointVendorHik 101 }
dS-DS-3WA-X30                   OBJECT IDENTIFIER ::= { hh3cJointVendorHik 102 }
dS-DS-SG100-M280                OBJECT IDENTIFIER ::= { hh3cJointVendorHik 103 }
dS-DS-SG100-M200                OBJECT IDENTIFIER ::= { hh3cJointVendorHik 104 }
dS-DS-SG100-M280-Context        OBJECT IDENTIFIER ::= { hh3cJointVendorHik 105 }
dS-DS-SG100-M100                OBJECT IDENTIFIER ::= { hh3cJointVendorHik 106 }



-- DH products
-- OID of hh3cJointVendorDh is 1.3.6.1.4.1.25506.12.1.2
hh3cJointVendorDh               OBJECT IDENTIFIER ::= { hh3cJointVendorId 2 }

dH-S5500-24GF4XF                OBJECT IDENTIFIER ::= { hh3cJointVendorDh 1 }
dH-S5500-48GT4XF                OBJECT IDENTIFIER ::= { hh3cJointVendorDh 2 }
dH-S7602                        OBJECT IDENTIFIER ::= { hh3cJointVendorDh 3 }
dH-S7606                        OBJECT IDENTIFIER ::= { hh3cJointVendorDh 4 }
dH-S4100-8ET2GF                 OBJECT IDENTIFIER ::= { hh3cJointVendorDh 5 }
dH-S4100-24ET2GF                OBJECT IDENTIFIER ::= { hh3cJointVendorDh 6 }
dH-S4100-24ET2GF-PWR            OBJECT IDENTIFIER ::= { hh3cJointVendorDh 7 }
dH-S5500-24GT4GF                OBJECT IDENTIFIER ::= { hh3cJointVendorDh 8 }
dH-S5500-48GT4GF                OBJECT IDENTIFIER ::= { hh3cJointVendorDh 9 }
dH-S5500-48GT4GF-AC             OBJECT IDENTIFIER ::= { hh3cJointVendorDh 10 }
dH-S8610                        OBJECT IDENTIFIER ::= { hh3cJointVendorDh 11 }
dh-S6500-48XF2QF                OBJECT IDENTIFIER ::= { hh3cJointVendorDh 12 }
dh-S7603                        OBJECT IDENTIFIER ::= { hh3cJointVendorDh 13 }
dH-DH-S5500-48GT4XF-E           OBJECT IDENTIFIER ::= { hh3cJointVendorDh 14 }
dH-DH-S5500-24GT4GF-E           OBJECT IDENTIFIER ::= { hh3cJointVendorDh 15 }
dH-DH-S5600-48GT4XF             OBJECT IDENTIFIER ::= { hh3cJointVendorDh 16 }
dH-DH-S5500-24GF4XF-E           OBJECT IDENTIFIER ::= { hh3cJointVendorDh 17 }
dH-DH-AWA6220-O                 OBJECT IDENTIFIER ::= { hh3cJointVendorDh 18 }
dH-DH-AWA6330-C                 OBJECT IDENTIFIER ::= { hh3cJointVendorDh 19 }
dH-DH-AWA6220-W                 OBJECT IDENTIFIER ::= { hh3cJointVendorDh 20 }
dH-DH-AWA6220C-C                OBJECT IDENTIFIER ::= { hh3cJointVendorDh 21 }
dH-DH-AWA6220C-O                OBJECT IDENTIFIER ::= { hh3cJointVendorDh 22 }
dH-DH-AWA6330C-C                OBJECT IDENTIFIER ::= { hh3cJointVendorDh 23 }
dH-DH-AWA6220-C                 OBJECT IDENTIFIER ::= { hh3cJointVendorDh 24 }
dH-DH-AWA6220C-W                OBJECT IDENTIFIER ::= { hh3cJointVendorDh 25 }
dH-DH-AC10                      OBJECT IDENTIFIER ::= { hh3cJointVendorDh 26 }
dH-DA-AC64C                     OBJECT IDENTIFIER ::= { hh3cJointVendorDh 27 }
dH-DA-AC64                      OBJECT IDENTIFIER ::= { hh3cJointVendorDh 28 }
dh-DH-AS5900C-24GF4XF           OBJECT IDENTIFIER ::= { hh3cJointVendorDh 29 }
dh-DH-S5500-24GF4XF-A           OBJECT IDENTIFIER ::= { hh3cJointVendorDh 30 }
dh-DH-AS6900C-24GF4XF           OBJECT IDENTIFIER ::= { hh3cJointVendorDh 31 }
dh-DH-AS5500-8MGT2XF-370        OBJECT IDENTIFIER ::= { hh3cJointVendorDh 32 }
dh-DH-AS5600-24GF4XF            OBJECT IDENTIFIER ::= { hh3cJointVendorDh 33 }
dh-DH-AS5600-24GT4XF            OBJECT IDENTIFIER ::= { hh3cJointVendorDh 34 }
dh-DH-AS4300-24GT4GF            OBJECT IDENTIFIER ::= { hh3cJointVendorDh 35 }
dh-DH-AS5900C-24GT4XF           OBJECT IDENTIFIER ::= { hh3cJointVendorDh 36 }
dh-DH-AS5500-48GF4XF            OBJECT IDENTIFIER ::= { hh3cJointVendorDh 37 }
dh-DH-S5500-48GF4XF-A           OBJECT IDENTIFIER ::= { hh3cJointVendorDh 38 }
dh-DH-AS5600-48GF4XF            OBJECT IDENTIFIER ::= { hh3cJointVendorDh 39 }
dh-DH-AS6900C-48GT4XF           OBJECT IDENTIFIER ::= { hh3cJointVendorDh 40 }
dh-DH-AS3900C-24GT4GF-370       OBJECT IDENTIFIER ::= { hh3cJointVendorDh 41 }
dh-DH-AS5500-24GT4XF-370        OBJECT IDENTIFIER ::= { hh3cJointVendorDh 42 }
dh-DH-AS3900C-8GT2GF            OBJECT IDENTIFIER ::= { hh3cJointVendorDh 43 }
dh-DH-AS4300-48GT4GF            OBJECT IDENTIFIER ::= { hh3cJointVendorDh 44 }
dh-DH-AS5900C-48GT4XF           OBJECT IDENTIFIER ::= { hh3cJointVendorDh 45 }
dh-DH-S5500-24GT4XF-A           OBJECT IDENTIFIER ::= { hh3cJointVendorDh 46 }
dh-DH-AS3900C-48GT4GF           OBJECT IDENTIFIER ::= { hh3cJointVendorDh 47 }
dh-DH-AS6900C-24GT4XF           OBJECT IDENTIFIER ::= { hh3cJointVendorDh 48 }
dh-DH-AS4300-16GT4GF            OBJECT IDENTIFIER ::= { hh3cJointVendorDh 49 }
dh-DH-AS5500-48GT4XF-600        OBJECT IDENTIFIER ::= { hh3cJointVendorDh 50 }
dh-DH-AS3900C-24GT4GF           OBJECT IDENTIFIER ::= { hh3cJointVendorDh 51 }
dh-DH-AS4300-8GT2GF             OBJECT IDENTIFIER ::= { hh3cJointVendorDh 52 }
dh-DH-AS5900C-48GF4XF           OBJECT IDENTIFIER ::= { hh3cJointVendorDh 53 }
dh-DH-AS3900C-16GT4GF           OBJECT IDENTIFIER ::= { hh3cJointVendorDh 54 }
dh-DH-S5500-48GT4XF-A           OBJECT IDENTIFIER ::= { hh3cJointVendorDh 55 }
dh-DH-AS6900C-48GF4XF           OBJECT IDENTIFIER ::= { hh3cJointVendorDh 56 }
dh-DH-AS5500-24GT4XF            OBJECT IDENTIFIER ::= { hh3cJointVendorDh 57 }
dh-DH-AS3900C-8GT2GF-125        OBJECT IDENTIFIER ::= { hh3cJointVendorDh 58 }
dh-AR506C-E                     OBJECT IDENTIFIER ::= { hh3cJointVendorDh 59 }
dh-AR306-E                      OBJECT IDENTIFIER ::= { hh3cJointVendorDh 60 }
dh-AR506-E                      OBJECT IDENTIFIER ::= { hh3cJointVendorDh 61 }
dh-AR306C-H                     OBJECT IDENTIFIER ::= { hh3cJointVendorDh 62 }
dh-DH-S5600-48GT4XF-A           OBJECT IDENTIFIER ::= { hh3cJointVendorDh 63 }
dh-DH-S5600-24GT4XF-A           OBJECT IDENTIFIER ::= { hh3cJointVendorDh 64 }
dh-DH-AS5500-24MGT4XF-600       OBJECT IDENTIFIER ::= { hh3cJointVendorDh 66 }
dh-DH-S5600-24GF4XF-A           OBJECT IDENTIFIER ::= { hh3cJointVendorDh 67 }
dh-DH-S6600-48XF2QF-A           OBJECT IDENTIFIER ::= { hh3cJointVendorDh 68 }
dh-DH-AS6600-24XF2QF            OBJECT IDENTIFIER ::= { hh3cJointVendorDh 69 }
dh-DH-S5600-48GF4XF-A           OBJECT IDENTIFIER ::= { hh3cJointVendorDh 70 }
dh-DH-S6600-24XF2QF-A           OBJECT IDENTIFIER ::= { hh3cJointVendorDh 71 }
dh-AR722-E                      OBJECT IDENTIFIER ::= { hh3cJointVendorDh 72 }
dh-AR722C-E                     OBJECT IDENTIFIER ::= { hh3cJointVendorDh 73 }
dh-DH-SAG2000                   OBJECT IDENTIFIER ::= { hh3cJointVendorDh 74 }
dh-DH-ACG2000                   OBJECT IDENTIFIER ::= { hh3cJointVendorDh 75 }
dh-DH-ACG1000                   OBJECT IDENTIFIER ::= { hh3cJointVendorDh 76 }
dh-DH-SAG1000                   OBJECT IDENTIFIER ::= { hh3cJointVendorDh 77 }
dh-DH-SACG100-H                 OBJECT IDENTIFIER ::= { hh3cJointVendorDh 78 }
dh-DH-NGFW500                   OBJECT IDENTIFIER ::= { hh3cJointVendorDh 79 }
dh-DH-SACG300-H                 OBJECT IDENTIFIER ::= { hh3cJointVendorDh 80 }
dh-DH-NGFW800                   OBJECT IDENTIFIER ::= { hh3cJointVendorDh 81 }
dh-DH-NGFW200                   OBJECT IDENTIFIER ::= { hh3cJointVendorDh 82 }
dh-DH-NGFW300-I                 OBJECT IDENTIFIER ::= { hh3cJointVendorDh 83 }
dh-DH-NGFW5000-I                OBJECT IDENTIFIER ::= { hh3cJointVendorDh 84 }
dh-DH-NGFW5500-Context          OBJECT IDENTIFIER ::= { hh3cJointVendorDh 85 }
dh-DH-SACG1000-H-Context        OBJECT IDENTIFIER ::= { hh3cJointVendorDh 86 }
dh-DH-NGFW1000                  OBJECT IDENTIFIER ::= { hh3cJointVendorDh 87 }
dh-DH-NGFW2000-I                OBJECT IDENTIFIER ::= { hh3cJointVendorDh 88 }
dh-DH-SACG8000-H                OBJECT IDENTIFIER ::= { hh3cJointVendorDh 89 }
dh-DH-NGFW5000-Context          OBJECT IDENTIFIER ::= { hh3cJointVendorDh 90 }
dh-DH-NGFW2000                  OBJECT IDENTIFIER ::= { hh3cJointVendorDh 91 }
dh-DH-NGFW2000-I-Context        OBJECT IDENTIFIER ::= { hh3cJointVendorDh 92 }
dh-DH-SACG5000-H-Context        OBJECT IDENTIFIER ::= { hh3cJointVendorDh 93 }
dh-DH-NGFW5000-I-Context        OBJECT IDENTIFIER ::= { hh3cJointVendorDh 94 }
dh-DH-NGFW5500-I                OBJECT IDENTIFIER ::= { hh3cJointVendorDh 95 }
dh-DH-SACG5000-H                OBJECT IDENTIFIER ::= { hh3cJointVendorDh 96 }
dh-DH-NGFW5500-I-Context        OBJECT IDENTIFIER ::= { hh3cJointVendorDh 97 }
dh-DH-SACG1000-H                OBJECT IDENTIFIER ::= { hh3cJointVendorDh 98 }
dh-DH-NGFW5000                  OBJECT IDENTIFIER ::= { hh3cJointVendorDh 99 }
dh-DH-NGFW1000-Context          OBJECT IDENTIFIER ::= { hh3cJointVendorDh 100 }
dh-DH-NGFW5500                  OBJECT IDENTIFIER ::= { hh3cJointVendorDh 101 }
dh-DH-SACG8000-H-Context        OBJECT IDENTIFIER ::= { hh3cJointVendorDh 102 }
dh-DH-NGFW2000-Context          OBJECT IDENTIFIER ::= { hh3cJointVendorDh 103 }
dh-S7806                        OBJECT IDENTIFIER ::= { hh3cJointVendorDh 104 }
dh-S7803                        OBJECT IDENTIFIER ::= { hh3cJointVendorDh 105 }
dh-DH-S6500-48XF2QF             OBJECT IDENTIFIER ::= { hh3cJointVendorDh 106 }
dh-DH-S6500-48XF2QF-E           OBJECT IDENTIFIER ::= { hh3cJointVendorDh 107 }



-- SRIE products
-- OID of hh3cJointVendorSrie is 1.3.6.1.4.1.25506.12.1.3
hh3cJointVendorSrie             OBJECT IDENTIFIER ::= { hh3cJointVendorId 3 }

sRIE-SRHN5130S-52S-HI           OBJECT IDENTIFIER ::= { hh3cJointVendorSrie 1 }
sRIE-SRHN5130S-50S-HI           OBJECT IDENTIFIER ::= { hh3cJointVendorSrie 2 }

sRIE-SRHN-LSWM1FWD0-S-SecBlade-FireWall-context     OBJECT IDENTIFIER ::= { hh3cJointVendorSrie 3 }
sRIE-SRHN-LSWM1FWD0-S-SecBlade-FireWall-Module      OBJECT IDENTIFIER ::= { hh3cJointVendorSrie 4 }
sRIE-SRHN12508X-AF              OBJECT IDENTIFIER ::= { hh3cJointVendorSrie 5 }
sRIE-SRHN6800-54QF-H3           OBJECT IDENTIFIER ::= { hh3cJointVendorSrie 6 }


-- DZEC products
-- OID of hh3cJointVendorDzec is 1.3.6.1.4.1.25506.12.1.4
hh3cJointVendorDzec             OBJECT IDENTIFIER ::= { hh3cJointVendorId 4 }

dZEC-S7503X-M-G                 OBJECT IDENTIFIER ::= { hh3cJointVendorDzec 1 }
dZEC-S10508X                    OBJECT IDENTIFIER ::= { hh3cJointVendorDzec 2 }
dZEC-S5130S-52P-EI              OBJECT IDENTIFIER ::= { hh3cJointVendorDzec 3 }
dZEC-S5560S-52P-EI              OBJECT IDENTIFIER ::= { hh3cJointVendorDzec 4 }
dZEC-S5130S-28S-EI              OBJECT IDENTIFIER ::= { hh3cJointVendorDzec 5 }
dZEC-S5130S-28S-HI              OBJECT IDENTIFIER ::= { hh3cJointVendorDzec 6 }
dZEC-SR6604-X                   OBJECT IDENTIFIER ::= { hh3cJointVendorDzec 7 }
dZEC-S5570S-36F-EI              OBJECT IDENTIFIER ::= { hh3cJointVendorDzec 8 }
dZEC-SR6608-X                   OBJECT IDENTIFIER ::= { hh3cJointVendorDzec 9 }
dZEC-SR6608                     OBJECT IDENTIFIER ::= { hh3cJointVendorDzec 10 }
dZEC-S6805-54HF                 OBJECT IDENTIFIER ::= { hh3cJointVendorDzec 11 }
dZEC-SR8808H-X                  OBJECT IDENTIFIER ::= { hh3cJointVendorDzec 12 }
dZEC-S6520X-54XG-EI-G           OBJECT IDENTIFIER ::= { hh3cJointVendorDzec 13 }
dZEC-S12508G-AF                 OBJECT IDENTIFIER ::= { hh3cJointVendorDzec 14 }
dZEC-MSR56-60                   OBJECT IDENTIFIER ::= { hh3cJointVendorDzec 15 }
-- AIS products
-- OID of hh3cJointVendorAis is 1.3.6.1.4.1.25506.12.1.5
hh3cJointVendorAis             OBJECT IDENTIFIER ::= { hh3cJointVendorId 5 }


aIS-AISFW-F280                  OBJECT IDENTIFIER ::= { hh3cJointVendorAis 1 }
aIS-AISFW-F480                  OBJECT IDENTIFIER ::= { hh3cJointVendorAis 2 }
aIS-AISFW-F680                  OBJECT IDENTIFIER ::= { hh3cJointVendorAis 3 }
aIS-AISFW-F880                  OBJECT IDENTIFIER ::= { hh3cJointVendorAis 4 }
aIS-AISFW-F980                  OBJECT IDENTIFIER ::= { hh3cJointVendorAis 5 }
aIS-AISFW-F990                  OBJECT IDENTIFIER ::= { hh3cJointVendorAis 6 }
aIS-AISFW-F1020                 OBJECT IDENTIFIER ::= { hh3cJointVendorAis 7 }
aIS-AISFW-F1080                 OBJECT IDENTIFIER ::= { hh3cJointVendorAis 8 }
aIS-AISFW-F1080-Context         OBJECT IDENTIFIER ::= { hh3cJointVendorAis 9 }
aIS-AISFW-F2080                 OBJECT IDENTIFIER ::= { hh3cJointVendorAis 10 }
aIS-AISFW-F2080-Context         OBJECT IDENTIFIER ::= { hh3cJointVendorAis 11 }
aIS-AISFW-F4080                 OBJECT IDENTIFIER ::= { hh3cJointVendorAis 12 }
aIS-AISFW-F4080-Context         OBJECT IDENTIFIER ::= { hh3cJointVendorAis 13 }
aIS-AISFW-F8080                 OBJECT IDENTIFIER ::= { hh3cJointVendorAis 14 }
aIS-AISFW-F8080-Context         OBJECT IDENTIFIER ::= { hh3cJointVendorAis 15 }
aIS-AISFW-F12080                OBJECT IDENTIFIER ::= { hh3cJointVendorAis 16 }
aIS-AISFW-F12080-Context        OBJECT IDENTIFIER ::= { hh3cJointVendorAis 17 }
aIS-AISFW-F16080                OBJECT IDENTIFIER ::= { hh3cJointVendorAis 18 }
aIS-AISFW-F16080-Context        OBJECT IDENTIFIER ::= { hh3cJointVendorAis 19 }
aIS-AISTPS-T4080                OBJECT IDENTIFIER ::= { hh3cJointVendorAis 20 }
aIS-AISTPS-T4080-Context        OBJECT IDENTIFIER ::= { hh3cJointVendorAis 21 }
aIS-AISTPS-T8080                OBJECT IDENTIFIER ::= { hh3cJointVendorAis 22 }
aIS-AISTPS-T8080-Context        OBJECT IDENTIFIER ::= { hh3cJointVendorAis 23 }
aIS-AISTPS-T16080               OBJECT IDENTIFIER ::= { hh3cJointVendorAis 24 }
aIS-AISTPS-T16080-Context       OBJECT IDENTIFIER ::= { hh3cJointVendorAis 25 }
aIS-AISFW-Context               OBJECT IDENTIFIER ::= { hh3cJointVendorAis 26 }
aIS-AISFW                       OBJECT IDENTIFIER ::= { hh3cJointVendorAis 27 }


aIS-AISFW-vFW-4G                OBJECT IDENTIFIER ::= { hh3cJointVendorAis 28 }
aIS-AISFW-vFW-2G                OBJECT IDENTIFIER ::= { hh3cJointVendorAis 29 }
aIS-AISFW-vFW-40G               OBJECT IDENTIFIER ::= { hh3cJointVendorAis 30 }
aIS-AISFW-vFW-1G                OBJECT IDENTIFIER ::= { hh3cJointVendorAis 31 }
aIS-AISFW-vFW-20G               OBJECT IDENTIFIER ::= { hh3cJointVendorAis 32 }
aIS-AISFW-vFW-10G               OBJECT IDENTIFIER ::= { hh3cJointVendorAis 33 }

aIS-AISTPS-G980                 OBJECT IDENTIFIER ::= { hh3cJointVendorAis 34 }
aIS-AISTPS-G980-Context         OBJECT IDENTIFIER ::= { hh3cJointVendorAis 35 }
aIS-AISFW-G1080                 OBJECT IDENTIFIER ::= { hh3cJointVendorAis 36 }
aIS-AISFW-G2080                 OBJECT IDENTIFIER ::= { hh3cJointVendorAis 37 }
aIS-AISTPS-G2080-Context        OBJECT IDENTIFIER ::= { hh3cJointVendorAis 38 }
aIS-AISFW-G880                  OBJECT IDENTIFIER ::= { hh3cJointVendorAis 39 }
aIS-AISFW-G2080-Context         OBJECT IDENTIFIER ::= { hh3cJointVendorAis 40 }
aIS-AISFW-G880-Context          OBJECT IDENTIFIER ::= { hh3cJointVendorAis 41 }
aIS-AISFW-G1080-Context         OBJECT IDENTIFIER ::= { hh3cJointVendorAis 42 }
aIS-AISTPS-G2080                OBJECT IDENTIFIER ::= { hh3cJointVendorAis 43 }

aIS-AISFW-F490                  OBJECT IDENTIFIER ::= { hh3cJointVendorAis 44 }
aIS-AISFW-F290                  OBJECT IDENTIFIER ::= { hh3cJointVendorAis 45 }
aIS-AISFW-F690                  OBJECT IDENTIFIER ::= { hh3cJointVendorAis 46 }
aIS-AISTPS-T1080                OBJECT IDENTIFIER ::= { hh3cJointVendorAis 47 }
aIS-AISFW-F290-Context          OBJECT IDENTIFIER ::= { hh3cJointVendorAis 48 }
aIS-AISFW-F690-Context          OBJECT IDENTIFIER ::= { hh3cJointVendorAis 49 }
aIS-AISTPS-T1080-Context        OBJECT IDENTIFIER ::= { hh3cJointVendorAis 50 }
aIS-AISTPS-T880                 OBJECT IDENTIFIER ::= { hh3cJointVendorAis 51 }
aIS-AISTPS-T880-Context         OBJECT IDENTIFIER ::= { hh3cJointVendorAis 52 }
aIS-AISFW-F490-Context          OBJECT IDENTIFIER ::= { hh3cJointVendorAis 53 }

-- FNG products
-- OID of hh3cJointVendorFng is 1.3.6.1.4.1.25506.12.1.6
hh3cJointVendorFng              OBJECT IDENTIFIER ::= { hh3cJointVendorId 6 }

fNG-DNR20008C-DN                OBJECT IDENTIFIER ::= { hh3cJointVendorFng 1 }
fNG-DNR20008M-DN                OBJECT IDENTIFIER ::= { hh3cJointVendorFng 2 }
END

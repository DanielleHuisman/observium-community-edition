-- ============================================================================
-- Copyright (C) 2004-2022 New H3C Tech. Co., Ltd. All rights reserved.
--
-- Description: This MIB is used for configuration of SECP (security policy).
-- Reference:
-- Version: V1.0
-- History:
-- V1.0 created by jinzheyuan.
-- ============================================================================
HH3C-SECP-V9-MIB DEFINITIONS ::= BEGIN

IMPORTS
    hh3cCommon
        FROM  HH3C-OID-MIB
    OBJECT-TYPE, MODULE-IDENTITY,
    Unsigned32, Counter64
        FROM SNMPv2-SMI
    CounterBasedGauge64
        FROM HCNUM-TC;

--
-- Node definitions
--

hh3cSecpV9 MODULE-IDENTITY
    LAST-UPDATED "202205091725Z"        -- May 09, 2022 at 17:25 GMT
    ORGANIZATION
        "New H3C Technologies Co., Ltd."
    CONTACT-INFO
        "Platform Team New H3C Technologies Co., Ltd.
        Hai-Dian District Beijing P.R. China
        http://www.h3c.com
        Zip:100085
        "
    DESCRIPTION
        "Security policy management information base for managing devices
        that support security policy.
        "
    REVISION "202205091725Z"             -- May 09, 2022 at 17:25 GMT
    DESCRIPTION
        "The initial revision of this MIB module."
    ::= { hh3cCommon 224 }

--
-- Nodes of hh3cSecpV9Objects
--
hh3cSecpV9Objects OBJECT IDENTIFIER ::= { hh3cSecpV9 1 }

--
-- Nodes of hh3cSecpV9RunningInfoTable
--
hh3cSecpV9RunningInfoTable OBJECT-TYPE
    SYNTAX SEQUENCE OF Hh3cSecpV9RunningInfoEntry
    MAX-ACCESS not-accessible
    STATUS current
    DESCRIPTION
        "Security policy running information base."
    ::= { hh3cSecpV9Objects 1 }

hh3cSecpV9RunningInfoEntry OBJECT-TYPE
    SYNTAX Hh3cSecpV9RunningInfoEntry
    MAX-ACCESS not-accessible
    STATUS current
    DESCRIPTION
        "Security policy running information entry."
    INDEX
    {
        hh3cSecpV9RuleID
    }
    ::= { hh3cSecpV9RunningInfoTable 1 }

Hh3cSecpV9RunningInfoEntry ::=
    SEQUENCE
    {
        hh3cSecpV9RuleID
            Unsigned32,
        hh3cSecpV9MatchPacketCount
            Counter64,
        hh3cSecpV9LastMatchTime
            CounterBasedGauge64
    }

hh3cSecpV9RuleID OBJECT-TYPE
    SYNTAX Unsigned32
    MAX-ACCESS not-accessible
    STATUS current
    DESCRIPTION
        "Rule ID of security policy."
    ::= { hh3cSecpV9RunningInfoEntry 1 }

hh3cSecpV9MatchPacketCount OBJECT-TYPE
    SYNTAX Counter64
    MAX-ACCESS read-only
    STATUS current
    DESCRIPTION
        "Number of packets matching the rule."
    ::= { hh3cSecpV9RunningInfoEntry 2 }

hh3cSecpV9LastMatchTime OBJECT-TYPE
    SYNTAX CounterBasedGauge64
    MAX-ACCESS read-only
    STATUS current
    DESCRIPTION
        "Time elapsed since 1970/1/1 00:00:00 to the most recent match."
    ::= { hh3cSecpV9RunningInfoEntry 3 }

END

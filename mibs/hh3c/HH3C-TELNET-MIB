-- =================================================================
-- Copyright (c) 2004-2022 New H3C Tech. Co., Ltd. All rights reserved.
--
-- Description: telnet mib
-- Reference:
-- Version: V1.0
-- History:
--  V1.0 Created by zhangfeng
--      2022-08-24 Initial version
-- =================================================================
HH3C-TELNET-MIB DEFINITIONS ::= BEGIN

IMPORTS
    hh3cCommon
        FROM HH3C-OID-MIB
    OBJECT-TYPE, MODULE-IDENTITY, NOTIFICATION-TYPE, Unsigned32
        FROM SNMPv2-SMI;

hh3cTelnet MODULE-IDENTITY
    LAST-UPDATED "202208240000Z"
    ORGANIZATION
        "New H3C Tech. Co., Ltd."
    CONTACT-INFO
        "Platform Team New H3C Tech. Co., Ltd.
        Hai-Dian District Beijing P.R. China
        http://www.h3c.com
        Zip:100085"
    DESCRIPTION
        "The MIB module is used for telnet."
    REVISION    "202208240000Z"
    DESCRIPTION    "The initial version."
    ::= { hh3cCommon 249 }

hh3cTelnets OBJECT IDENTIFIER ::= { hh3cTelnet 1 }
-- ==================================================================
--
-- TELNETS trap parameters
--
-- ==================================================================
hh3cTelnetsObjForTrap OBJECT IDENTIFIER ::= { hh3cTelnets 1 }

hh3cTelnetsLoginFailedTimes OBJECT-TYPE
    SYNTAX      Unsigned32
    MAX-ACCESS  accessible-for-notify
    STATUS      current
    DESCRIPTION
        "Users login failed times."
    ::= { hh3cTelnetsObjForTrap 1 }

hh3cTelnetsLoginFailedStatPeriod OBJECT-TYPE
    SYNTAX      Unsigned32
    UNITS       "minutes"
    MAX-ACCESS  accessible-for-notify
    STATUS      current
    DESCRIPTION
        "Users login failed statistic period."
    ::= { hh3cTelnetsObjForTrap 2 }

-- ==================================================================
--
-- TELNETS traps
--
-- ==================================================================
hh3cTelnetsTraps OBJECT IDENTIFIER ::= { hh3cTelnets 2 }
hh3cTelnetsTrapsPrefix OBJECT IDENTIFIER ::= { hh3cTelnetsTraps 0 }

hh3cTelnetsLoginFailed NOTIFICATION-TYPE
    OBJECTS { hh3cTelnetsLoginFailedTimes, hh3cTelnetsLoginFailedStatPeriod }
    STATUS  current
    DESCRIPTION
        "Users failed to login telnet server too frequently."
    ::= { hh3cTelnetsTrapsPrefix 1 }

hh3cTelnetsLoginFailedClear NOTIFICATION-TYPE
    STATUS  current
    DESCRIPTION
        "The telnet user login-failed alarm was cleared."
    ::= { hh3cTelnetsTrapsPrefix 2 }

END

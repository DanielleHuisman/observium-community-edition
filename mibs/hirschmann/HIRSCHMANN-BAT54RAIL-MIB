HIRSCHMANN-BAT54RAIL-MIB DEFINITIONS ::= BEGIN

IMPORTS
    Integer32, OBJECT-TYPE, NOTIFICATION-TYPE, Counter32,
    TimeTicks, Counter64, enterprises, MODULE-IDENTITY,
    Gauge32, IpAddress
            FROM SNMPv2-SMI
    sysName, sysDescr
            FROM RFC1213-MIB
    DisplayString, MacAddress
            FROM SNMPv2-TC
    CounterBasedGauge64
            FROM HCNUM-TC;

bat54rail MODULE-IDENTITY
    LAST-UPDATED "201605151200Z"  -- May 15, 2016
    ORGANIZATION
            "Hirschmann Automation and Control GmbH"
    CONTACT-INFO
            "www.beldensolutions.com"
    DESCRIPTION
            "Management information base definitions"
    REVISION "201605151200Z"  -- 2020-07-08 Update
    DESCRIPTION
            "Release (9.12)"
    ::= { enterprises hirschmann(248) hmWlan(32) wlanMgt(16) 8 }

--
-- NODES
--
-- {NODE} 1.3.6.1.4.1.248.32.18.0
hmTrapGrp OBJECT IDENTIFIER ::= { bat54rail 0 }

-- {NODE} 1.3.6.1.4.1.248.32.18.0.0
hmTraps OBJECT IDENTIFIER ::= { hmTrapGrp 0 }

-- {NODE} 1.3.6.1.4.1.248.32.18.1
hmStatus OBJECT IDENTIFIER ::= { bat54rail 1 }

-- {SCALAR} 1.3.6.1.4.1.248.32.18.1.2
hmStatusOperatingTime OBJECT-TYPE
    SYNTAX     DisplayString
    MAX-ACCESS read-only
    STATUS     current
    DESCRIPTION
            "-- empty --"
    ::= { hmStatus 2 }

-- {NODE} 1.3.6.1.4.1.248.32.18.1.3
hmStatusWlan OBJECT IDENTIFIER ::= { hmStatus 3 }

-- {SCALAR} 1.3.6.1.4.1.248.32.18.1.3.11
hmStatusWlanDeleteValues OBJECT-TYPE
    SYNTAX     DisplayString
    MAX-ACCESS read-write
    STATUS     current
    DESCRIPTION
            "-- empty --"
    ::= { hmStatusWlan 11 }

-- {TABLE} 1.3.6.1.4.1.248.32.18.1.3.32
hmStatusWlanStationTableTable OBJECT-TYPE
    SYNTAX     SEQUENCE OF HmStatusWlanStationTableEntry
    MAX-ACCESS not-accessible
    STATUS     current
    DESCRIPTION
            "-- empty --"
    ::= { hmStatusWlan 32 }

-- {ROW} 1.3.6.1.4.1.248.32.18.1.3.32.1
hmStatusWlanStationTableEntry OBJECT-TYPE
    SYNTAX     HmStatusWlanStationTableEntry
    MAX-ACCESS not-accessible
    STATUS     current
    DESCRIPTION
            ""
    INDEX {
            hmStatusWlanStationTableEntryIndex
          }
    ::= { hmStatusWlanStationTableTable 1 }

HmStatusWlanStationTableEntry ::= SEQUENCE {
            hmStatusWlanStationTableEntryIndex Integer32,
            hmStatusWlanStationTableEntryMacAddress MacAddress,
            hmStatusWlanStationTableEntryTxBytes Counter64,
            hmStatusWlanStationTableEntryRxBytes Counter64,
            hmStatusWlanStationTableEntryIdentification DisplayString,
            hmStatusWlanStationTableEntryState INTEGER,
            hmStatusWlanStationTableEntryRxRate INTEGER,
            hmStatusWlanStationTableEntryKeyType INTEGER,
            hmStatusWlanStationTableEntryInterface INTEGER,
            hmStatusWlanStationTableEntryPowerSaving INTEGER,
            hmStatusWlanStationTableEntryListenInterval Integer32,
            hmStatusWlanStationTableEntryConnectTime Integer32,
            hmStatusWlanStationTableEntryAid Integer32,
            hmStatusWlanStationTableEntryThroughput DisplayString,
            hmStatusWlanStationTableEntryShortSlotTime INTEGER,
            hmStatusWlanStationTableEntryShortPreamble INTEGER,
            hmStatusWlanStationTableEntryNetwork INTEGER,
            hmStatusWlanStationTableEntryPhySignal Integer32,
            hmStatusWlanStationTableEntryIpv4Address IpAddress,
            hmStatusWlanStationTableEntryTxRate INTEGER,
            hmStatusWlanStationTableEntryMaxThroughput DisplayString,
            hmStatusWlanStationTableEntryBytesThroughput Integer32,
            hmStatusWlanStationTableEntryBytesMaxThroughput Integer32,
            hmStatusWlanStationTableEntryClBrgSupport INTEGER,
            hmStatusWlanStationTableEntryWpaVersion INTEGER,
            hmStatusWlanStationTableEntryLastEvent INTEGER,
            hmStatusWlanStationTableEntryTxLimit Integer32,
            hmStatusWlanStationTableEntryRxLimit Integer32,
            hmStatusWlanStationTableEntryQos INTEGER,
            hmStatusWlanStationTableEntryVlanId Integer32,
            hmStatusWlanStationTableEntryUserName DisplayString,
            hmStatusWlanStationTableEntryMacCheck INTEGER,
            hmStatusWlanStationTableEntryTxPackets Counter32,
            hmStatusWlanStationTableEntryRxPackets Counter32,
            hmStatusWlanStationTableEntryIdleTimeout Integer32,
            hmStatusWlanStationTableEntryLastError INTEGER,
            hmStatusWlanStationTableEntryShortGuardInterval INTEGER,
            hmStatusWlanStationTableEntry40mhzMode INTEGER,
            hmStatusWlanStationTableEntry40mhzIntolerant INTEGER,
            hmStatusWlanStationTableEntryMaxAMsduLen Integer32,
            hmStatusWlanStationTableEntryMaxAMpduLen Integer32,
            hmStatusWlanStationTableEntryEffTxRate Integer32,
            hmStatusWlanStationTableEntryEffRxRate Integer32,
            hmStatusWlanStationTableEntryApsd BITS,
            hmStatusWlanStationTableEntryIpv6Address IpAddress,
            hmStatusWlanStationTableEntrySmPwrsave INTEGER,
            hmStatusWlanStationTableEntryTxErrors Integer32,
            hmStatusWlanStationTableEntryTotalRetries Integer32,
            hmStatusWlanStationTableEntryAlarmState INTEGER,
            hmStatusWlanStationTableEntry40mhzCoexistence INTEGER,
            hmStatusWlanStationTableEntry20mhzRequested INTEGER,
            hmStatusWlanStationTableEntryRxStbc INTEGER,
            hmStatusWlanStationTableEntryLdpc INTEGER,
            hmStatusWlanStationTableEntryAutowds INTEGER,
            hmStatusWlanStationTableEntryFastRoaming INTEGER,
            hmStatusWlanStationTableEntryWpa2KeyManagement INTEGER,
            hmStatusWlanStationTableEntrySGIMask BITS,
            hmStatusWlanStationTableEntryChannelBandwidths BITS,
            hmStatusWlanStationTableEntryProtMgmtFrames INTEGER,
            hmStatusWlanStationTableEntryRxStbcHt INTEGER,
            hmStatusWlanStationTableEntryRxStbcVht INTEGER,
            hmStatusWlanStationTableEntryLDPCMask BITS,
            hmStatusWlanStationTableEntryOperationMode INTEGER,
            hmStatusWlanStationTableEntryBlockackTestResult INTEGER,
            hmStatusWlanStationTableEntryClBrgRoamingSupport INTEGER,
            hmStatusWlanStationTableEntryIpv6AddressTxt DisplayString
    }

-- {COLUMN} 1.3.6.1.4.1.248.32.18.1.3.32.1.1
hmStatusWlanStationTableEntryIndex OBJECT-TYPE
    SYNTAX     Integer32 (0..65535)
    MAX-ACCESS read-only
    STATUS     current
    DESCRIPTION
            "-- empty --"
    ::= { hmStatusWlanStationTableEntry 1 }

-- {COLUMN} 1.3.6.1.4.1.248.32.18.1.3.32.1.4
hmStatusWlanStationTableEntryMacAddress OBJECT-TYPE
    SYNTAX     MacAddress
    MAX-ACCESS read-only
    STATUS     current
    DESCRIPTION
            "-- empty --"
    ::= { hmStatusWlanStationTableEntry 4 }

-- {COLUMN} 1.3.6.1.4.1.248.32.18.1.3.32.1.6
hmStatusWlanStationTableEntryTxBytes OBJECT-TYPE
    SYNTAX     Counter64
    MAX-ACCESS read-only
    STATUS     current
    DESCRIPTION
            "-- empty --"
    ::= { hmStatusWlanStationTableEntry 6 }

-- {COLUMN} 1.3.6.1.4.1.248.32.18.1.3.32.1.7
hmStatusWlanStationTableEntryRxBytes OBJECT-TYPE
    SYNTAX     Counter64
    MAX-ACCESS read-only
    STATUS     current
    DESCRIPTION
            "-- empty --"
    ::= { hmStatusWlanStationTableEntry 7 }

-- {COLUMN} 1.3.6.1.4.1.248.32.18.1.3.32.1.9
hmStatusWlanStationTableEntryIdentification OBJECT-TYPE
    SYNTAX     DisplayString (SIZE(0..24))
    MAX-ACCESS read-only
    STATUS     current
    DESCRIPTION
            "-- empty --"
    ::= { hmStatusWlanStationTableEntry 9 }

-- {COLUMN} 1.3.6.1.4.1.248.32.18.1.3.32.1.10
hmStatusWlanStationTableEntryState OBJECT-TYPE
    SYNTAX     INTEGER {
                  eNone (0),
                  eAdhoc (1),
                  eAuthenticated (2),
                  eConnected (3),
                  eMacCheck (4),
                  eKeyHandshake (8),
                  eAssociated (9),
                  e1xNegotiation (10)
            }
    MAX-ACCESS read-only
    STATUS     current
    DESCRIPTION
            "-- empty --"
    ::= { hmStatusWlanStationTableEntry 10 }

-- {COLUMN} 1.3.6.1.4.1.248.32.18.1.3.32.1.13
hmStatusWlanStationTableEntryRxRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51)
            }
    MAX-ACCESS read-only
    STATUS     current
    DESCRIPTION
            "-- empty --"
    ::= { hmStatusWlanStationTableEntry 13 }

-- {COLUMN} 1.3.6.1.4.1.248.32.18.1.3.32.1.14
hmStatusWlanStationTableEntryKeyType OBJECT-TYPE
    SYNTAX     INTEGER {
                  eNone (0),
                  eUnknown (1),
                  eWep40Bits (5),
                  eWep104Bits (13),
                  eWep128Bits (16),
                  eTkip (64),
                  eAesOcb (65),
                  eAesCcm (66),
                  eBip (68)
            }
    MAX-ACCESS read-only
    STATUS     current
    DESCRIPTION
            "-- empty --"
    ::= { hmStatusWlanStationTableEntry 14 }

-- {COLUMN} 1.3.6.1.4.1.248.32.18.1.3.32.1.15
hmStatusWlanStationTableEntryInterface OBJECT-TYPE
    SYNTAX     INTEGER {
                  eWlan1 (0),
                  eWlan2 (1),
                  eWlan3 (2),
                  eWlan4 (3)
            }
    MAX-ACCESS read-only
    STATUS     current
    DESCRIPTION
            "-- empty --"
    ::= { hmStatusWlanStationTableEntry 15 }

-- {COLUMN} 1.3.6.1.4.1.248.32.18.1.3.32.1.16
hmStatusWlanStationTableEntryPowerSaving OBJECT-TYPE
    SYNTAX     INTEGER {
                  eUnknown (0),
                  eInactive (1),
                  eActive (2)
            }
    MAX-ACCESS read-only
    STATUS     current
    DESCRIPTION
            "-- empty --"
    ::= { hmStatusWlanStationTableEntry 16 }

-- {COLUMN} 1.3.6.1.4.1.248.32.18.1.3.32.1.17
hmStatusWlanStationTableEntryListenInterval OBJECT-TYPE
    SYNTAX     Integer32 (0..65535)
    MAX-ACCESS read-only
    STATUS     current
    DESCRIPTION
            "-- empty --"
    ::= { hmStatusWlanStationTableEntry 17 }

-- {COLUMN} 1.3.6.1.4.1.248.32.18.1.3.32.1.18
hmStatusWlanStationTableEntryConnectTime OBJECT-TYPE
    SYNTAX     Integer32 (0..2147483647)
    MAX-ACCESS read-only
    STATUS     current
    DESCRIPTION
            "-- empty --"
    ::= { hmStatusWlanStationTableEntry 18 }

-- {COLUMN} 1.3.6.1.4.1.248.32.18.1.3.32.1.19
hmStatusWlanStationTableEntryAid OBJECT-TYPE
    SYNTAX     Integer32 (0..65535)
    MAX-ACCESS read-only
    STATUS     current
    DESCRIPTION
            "-- empty --"
    ::= { hmStatusWlanStationTableEntry 19 }

-- {COLUMN} 1.3.6.1.4.1.248.32.18.1.3.32.1.20
hmStatusWlanStationTableEntryThroughput OBJECT-TYPE
    SYNTAX     DisplayString (SIZE(0..255))
    MAX-ACCESS read-only
    STATUS     current
    DESCRIPTION
            "-- empty --"
    ::= { hmStatusWlanStationTableEntry 20 }

-- {COLUMN} 1.3.6.1.4.1.248.32.18.1.3.32.1.21
hmStatusWlanStationTableEntryShortSlotTime OBJECT-TYPE
    SYNTAX     INTEGER {
                  eNo (0),
                  eYes (1)
            }
    MAX-ACCESS read-only
    STATUS     current
    DESCRIPTION
            "-- empty --"
    ::= { hmStatusWlanStationTableEntry 21 }

-- {COLUMN} 1.3.6.1.4.1.248.32.18.1.3.32.1.23
hmStatusWlanStationTableEntryShortPreamble OBJECT-TYPE
    SYNTAX     INTEGER {
                  eNo (0),
                  eYes (1)
            }
    MAX-ACCESS read-only
    STATUS     current
    DESCRIPTION
            "-- empty --"
    ::= { hmStatusWlanStationTableEntry 23 }

-- {COLUMN} 1.3.6.1.4.1.248.32.18.1.3.32.1.25
hmStatusWlanStationTableEntryNetwork OBJECT-TYPE
    SYNTAX     INTEGER {
                  e1 (0),
                  e2 (1),
                  e3 (2),
                  e4 (3),
                  e5 (4),
                  e6 (5),
                  e7 (6),
                  e8 (7),
                  e9 (8),
                  e10 (9),
                  e11 (10),
                  e12 (11),
                  e13 (12),
                  e14 (13),
                  e15 (14),
                  e16 (15)
            }
    MAX-ACCESS read-only
    STATUS     current
    DESCRIPTION
            "-- empty --"
    ::= { hmStatusWlanStationTableEntry 25 }

-- {COLUMN} 1.3.6.1.4.1.248.32.18.1.3.32.1.26
hmStatusWlanStationTableEntryPhySignal OBJECT-TYPE
    SYNTAX     Integer32 (0..65535)
    MAX-ACCESS read-only
    STATUS     current
    DESCRIPTION
            "-- empty --"
    ::= { hmStatusWlanStationTableEntry 26 }

-- {COLUMN} 1.3.6.1.4.1.248.32.18.1.3.32.1.27
hmStatusWlanStationTableEntryIpv4Address OBJECT-TYPE
    SYNTAX     IpAddress
    MAX-ACCESS read-only
    STATUS     current
    DESCRIPTION
            "-- empty --"
    ::= { hmStatusWlanStationTableEntry 27 }

-- {COLUMN} 1.3.6.1.4.1.248.32.18.1.3.32.1.28
hmStatusWlanStationTableEntryTxRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51)
            }
    MAX-ACCESS read-only
    STATUS     current
    DESCRIPTION
            "-- empty --"
    ::= { hmStatusWlanStationTableEntry 28 }

-- {COLUMN} 1.3.6.1.4.1.248.32.18.1.3.32.1.29
hmStatusWlanStationTableEntryMaxThroughput OBJECT-TYPE
    SYNTAX     DisplayString (SIZE(0..255))
    MAX-ACCESS read-only
    STATUS     current
    DESCRIPTION
            "-- empty --"
    ::= { hmStatusWlanStationTableEntry 29 }

-- {COLUMN} 1.3.6.1.4.1.248.32.18.1.3.32.1.30
hmStatusWlanStationTableEntryBytesThroughput OBJECT-TYPE
    SYNTAX     Integer32 (0..2147483647)
    MAX-ACCESS read-only
    STATUS     current
    DESCRIPTION
            "-- empty --"
    ::= { hmStatusWlanStationTableEntry 30 }

-- {COLUMN} 1.3.6.1.4.1.248.32.18.1.3.32.1.31
hmStatusWlanStationTableEntryBytesMaxThroughput OBJECT-TYPE
    SYNTAX     Integer32 (0..2147483647)
    MAX-ACCESS read-only
    STATUS     current
    DESCRIPTION
            "-- empty --"
    ::= { hmStatusWlanStationTableEntry 31 }

-- {COLUMN} 1.3.6.1.4.1.248.32.18.1.3.32.1.32
hmStatusWlanStationTableEntryClBrgSupport OBJECT-TYPE
    SYNTAX     INTEGER {
                  eNo (0),
                  eYes (1)
            }
    MAX-ACCESS read-only
    STATUS     current
    DESCRIPTION
            "-- empty --"
    ::= { hmStatusWlanStationTableEntry 32 }

-- {COLUMN} 1.3.6.1.4.1.248.32.18.1.3.32.1.33
hmStatusWlanStationTableEntryWpaVersion OBJECT-TYPE
    SYNTAX     INTEGER {
                  eNone (0),
                  eWpa1 (1),
                  eWpa2 (2)
            }
    MAX-ACCESS read-only
    STATUS     current
    DESCRIPTION
            "-- empty --"
    ::= { hmStatusWlanStationTableEntry 33 }

-- {COLUMN} 1.3.6.1.4.1.248.32.18.1.3.32.1.34
hmStatusWlanStationTableEntryLastEvent OBJECT-TYPE
    SYNTAX     INTEGER {
                  eNone (0),
                  eAuthSuccess (1),
                  eDeauth (2),
                  eAssocSuccess (3),
                  eReassocSuccess (4),
                  eDisassoc (5),
                  eRadiusSuccess (6),
                  eAuthReject (7),
                  eAssocReject (8),
                  eKeyhandshakeSuccess (9),
                  eKeyhandshakeTimeout (10),
                  eKeyhandshakeFailure (11),
                  eRadiusReject (12),
                  eSupervision (13),
                  e8021xSuccess (14),
                  e8021xFailure (15),
                  eIdleTimeout (16),
                  eAdminDeassoc (17),
                  eRoamed (18)
            }
    MAX-ACCESS read-only
    STATUS     current
    DESCRIPTION
            "-- empty --"
    ::= { hmStatusWlanStationTableEntry 34 }

-- {COLUMN} 1.3.6.1.4.1.248.32.18.1.3.32.1.35
hmStatusWlanStationTableEntryTxLimit OBJECT-TYPE
    SYNTAX     Integer32 (0..2147483647)
    MAX-ACCESS read-only
    STATUS     current
    DESCRIPTION
            "-- empty --"
    ::= { hmStatusWlanStationTableEntry 35 }

-- {COLUMN} 1.3.6.1.4.1.248.32.18.1.3.32.1.36
hmStatusWlanStationTableEntryRxLimit OBJECT-TYPE
    SYNTAX     Integer32 (0..2147483647)
    MAX-ACCESS read-only
    STATUS     current
    DESCRIPTION
            "-- empty --"
    ::= { hmStatusWlanStationTableEntry 36 }

-- {COLUMN} 1.3.6.1.4.1.248.32.18.1.3.32.1.37
hmStatusWlanStationTableEntryQos OBJECT-TYPE
    SYNTAX     INTEGER {
                  eNo (0),
                  eYes (1)
            }
    MAX-ACCESS read-only
    STATUS     current
    DESCRIPTION
            "-- empty --"
    ::= { hmStatusWlanStationTableEntry 37 }

-- {COLUMN} 1.3.6.1.4.1.248.32.18.1.3.32.1.38
hmStatusWlanStationTableEntryVlanId OBJECT-TYPE
    SYNTAX     Integer32 (0..65535)
    MAX-ACCESS read-only
    STATUS     current
    DESCRIPTION
            "-- empty --"
    ::= { hmStatusWlanStationTableEntry 38 }

-- {COLUMN} 1.3.6.1.4.1.248.32.18.1.3.32.1.39
hmStatusWlanStationTableEntryUserName OBJECT-TYPE
    SYNTAX     DisplayString (SIZE(0..255))
    MAX-ACCESS read-only
    STATUS     current
    DESCRIPTION
            "-- empty --"
    ::= { hmStatusWlanStationTableEntry 39 }

-- {COLUMN} 1.3.6.1.4.1.248.32.18.1.3.32.1.40
hmStatusWlanStationTableEntryMacCheck OBJECT-TYPE
    SYNTAX     INTEGER {
                  eNone (0),
                  eLocal (1),
                  eRadius (2)
            }
    MAX-ACCESS read-only
    STATUS     current
    DESCRIPTION
            "-- empty --"
    ::= { hmStatusWlanStationTableEntry 40 }

-- {COLUMN} 1.3.6.1.4.1.248.32.18.1.3.32.1.41
hmStatusWlanStationTableEntryTxPackets OBJECT-TYPE
    SYNTAX     Counter32
    MAX-ACCESS read-only
    STATUS     current
    DESCRIPTION
            "-- empty --"
    ::= { hmStatusWlanStationTableEntry 41 }

-- {COLUMN} 1.3.6.1.4.1.248.32.18.1.3.32.1.42
hmStatusWlanStationTableEntryRxPackets OBJECT-TYPE
    SYNTAX     Counter32
    MAX-ACCESS read-only
    STATUS     current
    DESCRIPTION
            "-- empty --"
    ::= { hmStatusWlanStationTableEntry 42 }

-- {COLUMN} 1.3.6.1.4.1.248.32.18.1.3.32.1.43
hmStatusWlanStationTableEntryIdleTimeout OBJECT-TYPE
    SYNTAX     Integer32 (0..2147483647)
    MAX-ACCESS read-only
    STATUS     current
    DESCRIPTION
            "-- empty --"
    ::= { hmStatusWlanStationTableEntry 43 }

-- {COLUMN} 1.3.6.1.4.1.248.32.18.1.3.32.1.44
hmStatusWlanStationTableEntryLastError OBJECT-TYPE
    SYNTAX     INTEGER {
                  eNone (0),
                  eAuthSuccess (1),
                  eDeauth (2),
                  eAssocSuccess (3),
                  eReassocSuccess (4),
                  eDisassoc (5),
                  eRadiusSuccess (6),
                  eAuthReject (7),
                  eAssocReject (8),
                  eKeyhandshakeSuccess (9),
                  eKeyhandshakeTimeout (10),
                  eKeyhandshakeFailure (11),
                  eRadiusReject (12),
                  eSupervision (13),
                  e8021xSuccess (14),
                  e8021xFailure (15),
                  eIdleTimeout (16),
                  eAdminDeassoc (17),
                  eRoamed (18)
            }
    MAX-ACCESS read-only
    STATUS     current
    DESCRIPTION
            "-- empty --"
    ::= { hmStatusWlanStationTableEntry 44 }

-- {COLUMN} 1.3.6.1.4.1.248.32.18.1.3.32.1.45
hmStatusWlanStationTableEntryShortGuardInterval OBJECT-TYPE
    SYNTAX     INTEGER {
                  eNo (0),
                  e20mhz (1),
                  e40mhz (2),
                  e2040mhz (3)
            }
    MAX-ACCESS read-only
    STATUS     current
    DESCRIPTION
            "-- empty --"
    ::= { hmStatusWlanStationTableEntry 45 }

-- {COLUMN} 1.3.6.1.4.1.248.32.18.1.3.32.1.46
hmStatusWlanStationTableEntry40mhzMode OBJECT-TYPE
    SYNTAX     INTEGER {
                  eNo (0),
                  eYes (1)
            }
    MAX-ACCESS read-only
    STATUS     current
    DESCRIPTION
            "-- empty --"
    ::= { hmStatusWlanStationTableEntry 46 }

-- {COLUMN} 1.3.6.1.4.1.248.32.18.1.3.32.1.47
hmStatusWlanStationTableEntry40mhzIntolerant OBJECT-TYPE
    SYNTAX     INTEGER {
                  eNo (0),
                  eYes (1)
            }
    MAX-ACCESS read-only
    STATUS     current
    DESCRIPTION
            "-- empty --"
    ::= { hmStatusWlanStationTableEntry 47 }

-- {COLUMN} 1.3.6.1.4.1.248.32.18.1.3.32.1.48
hmStatusWlanStationTableEntryMaxAMsduLen OBJECT-TYPE
    SYNTAX     Integer32 (0..2147483647)
    MAX-ACCESS read-only
    STATUS     current
    DESCRIPTION
            "-- empty --"
    ::= { hmStatusWlanStationTableEntry 48 }

-- {COLUMN} 1.3.6.1.4.1.248.32.18.1.3.32.1.49
hmStatusWlanStationTableEntryMaxAMpduLen OBJECT-TYPE
    SYNTAX     Integer32 (0..2147483647)
    MAX-ACCESS read-only
    STATUS     current
    DESCRIPTION
            "-- empty --"
    ::= { hmStatusWlanStationTableEntry 49 }

-- {COLUMN} 1.3.6.1.4.1.248.32.18.1.3.32.1.50
hmStatusWlanStationTableEntryEffTxRate OBJECT-TYPE
    SYNTAX     Integer32 (0..2147483647)
    MAX-ACCESS read-only
    STATUS     current
    DESCRIPTION
            "-- empty --"
    ::= { hmStatusWlanStationTableEntry 50 }

-- {COLUMN} 1.3.6.1.4.1.248.32.18.1.3.32.1.51
hmStatusWlanStationTableEntryEffRxRate OBJECT-TYPE
    SYNTAX     Integer32 (0..2147483647)
    MAX-ACCESS read-only
    STATUS     current
    DESCRIPTION
            "-- empty --"
    ::= { hmStatusWlanStationTableEntry 51 }

-- {COLUMN} 1.3.6.1.4.1.248.32.18.1.3.32.1.52
hmStatusWlanStationTableEntryApsd OBJECT-TYPE
    SYNTAX     BITS {
                  eNo (0),
                  eVo (4),
                  eVi (5),
                  eBk (6),
                  eBe (7)
            }
    MAX-ACCESS read-only
    STATUS     current
    DESCRIPTION
            "-- empty --"
    ::= { hmStatusWlanStationTableEntry 52 }

-- {COLUMN} 1.3.6.1.4.1.248.32.18.1.3.32.1.53
hmStatusWlanStationTableEntryIpv6Address OBJECT-TYPE
    SYNTAX     IpAddress
    MAX-ACCESS read-only
    STATUS     current
    DESCRIPTION
            "-- empty --"
    ::= { hmStatusWlanStationTableEntry 53 }

-- {COLUMN} 1.3.6.1.4.1.248.32.18.1.3.32.1.54
hmStatusWlanStationTableEntrySmPwrsave OBJECT-TYPE
    SYNTAX     INTEGER {
                  eInactive (0),
                  eStatic (1),
                  eDynamic (2)
            }
    MAX-ACCESS read-only
    STATUS     current
    DESCRIPTION
            "-- empty --"
    ::= { hmStatusWlanStationTableEntry 54 }

-- {COLUMN} 1.3.6.1.4.1.248.32.18.1.3.32.1.55
hmStatusWlanStationTableEntryTxErrors OBJECT-TYPE
    SYNTAX     Integer32 (0..2147483647)
    MAX-ACCESS read-only
    STATUS     current
    DESCRIPTION
            "-- empty --"
    ::= { hmStatusWlanStationTableEntry 55 }

-- {COLUMN} 1.3.6.1.4.1.248.32.18.1.3.32.1.56
hmStatusWlanStationTableEntryTotalRetries OBJECT-TYPE
    SYNTAX     Integer32 (0..2147483647)
    MAX-ACCESS read-only
    STATUS     current
    DESCRIPTION
            "-- empty --"
    ::= { hmStatusWlanStationTableEntry 56 }

-- {COLUMN} 1.3.6.1.4.1.248.32.18.1.3.32.1.57
hmStatusWlanStationTableEntryAlarmState OBJECT-TYPE
    SYNTAX     INTEGER {
                  eNo (0),
                  ePhySignal (1),
                  eTotalRetries (2),
                  eTxErrors (4)
            }
    MAX-ACCESS read-only
    STATUS     current
    DESCRIPTION
            "-- empty --"
    ::= { hmStatusWlanStationTableEntry 57 }

-- {COLUMN} 1.3.6.1.4.1.248.32.18.1.3.32.1.58
hmStatusWlanStationTableEntry40mhzCoexistence OBJECT-TYPE
    SYNTAX     INTEGER {
                  eNo (0),
                  eYes (1)
            }
    MAX-ACCESS read-only
    STATUS     current
    DESCRIPTION
            "-- empty --"
    ::= { hmStatusWlanStationTableEntry 58 }

-- {COLUMN} 1.3.6.1.4.1.248.32.18.1.3.32.1.59
hmStatusWlanStationTableEntry20mhzRequested OBJECT-TYPE
    SYNTAX     INTEGER {
                  eNo (0),
                  eYes (1)
            }
    MAX-ACCESS read-only
    STATUS     current
    DESCRIPTION
            "-- empty --"
    ::= { hmStatusWlanStationTableEntry 59 }

-- {COLUMN} 1.3.6.1.4.1.248.32.18.1.3.32.1.60
hmStatusWlanStationTableEntryRxStbc OBJECT-TYPE
    SYNTAX     INTEGER {
                  eNone (0),
                  eOne (1),
                  eTwo (2),
                  eThree (3)
            }
    MAX-ACCESS read-only
    STATUS     current
    DESCRIPTION
            "-- empty --"
    ::= { hmStatusWlanStationTableEntry 60 }

-- {COLUMN} 1.3.6.1.4.1.248.32.18.1.3.32.1.61
hmStatusWlanStationTableEntryLdpc OBJECT-TYPE
    SYNTAX     INTEGER {
                  eNo (0),
                  eYes (1)
            }
    MAX-ACCESS read-only
    STATUS     current
    DESCRIPTION
            "-- empty --"
    ::= { hmStatusWlanStationTableEntry 61 }

-- {COLUMN} 1.3.6.1.4.1.248.32.18.1.3.32.1.62
hmStatusWlanStationTableEntryAutowds OBJECT-TYPE
    SYNTAX     INTEGER {
                  eNone (0),
                  eExpress (1),
                  ePreconfigured (2)
            }
    MAX-ACCESS read-only
    STATUS     current
    DESCRIPTION
            "-- empty --"
    ::= { hmStatusWlanStationTableEntry 62 }

-- {COLUMN} 1.3.6.1.4.1.248.32.18.1.3.32.1.63
hmStatusWlanStationTableEntryFastRoaming OBJECT-TYPE
    SYNTAX     INTEGER {
                  eNo (0),
                  eYes (1)
            }
    MAX-ACCESS read-only
    STATUS     current
    DESCRIPTION
            "-- empty --"
    ::= { hmStatusWlanStationTableEntry 63 }

-- {COLUMN} 1.3.6.1.4.1.248.32.18.1.3.32.1.64
hmStatusWlanStationTableEntryWpa2KeyManagement OBJECT-TYPE
    SYNTAX     INTEGER {
                  eStandard (0),
                  eFastRoaming (1),
                  eSha256 (2),
                  eNone (255)
            }
    MAX-ACCESS read-only
    STATUS     current
    DESCRIPTION
            "-- empty --"
    ::= { hmStatusWlanStationTableEntry 64 }

-- {COLUMN} 1.3.6.1.4.1.248.32.18.1.3.32.1.65
hmStatusWlanStationTableEntrySGIMask OBJECT-TYPE
    SYNTAX     BITS {
                  eNo (0),
                  e160mhz (28),
                  e80mhz (29),
                  e40mhz (30),
                  e20mhz (31)
            }
    MAX-ACCESS read-only
    STATUS     current
    DESCRIPTION
            "Bit mask of short guard interval support per-CBW"
    ::= { hmStatusWlanStationTableEntry 65 }

-- {COLUMN} 1.3.6.1.4.1.248.32.18.1.3.32.1.66
hmStatusWlanStationTableEntryChannelBandwidths OBJECT-TYPE
    SYNTAX     BITS {
                  eT40mhz (26),
                  e80Plus80mhz (27),
                  e160mhz (28),
                  e80mhz (29),
                  e40mhz (30),
                  e20mhz (31)
            }
    MAX-ACCESS read-only
    STATUS     current
    DESCRIPTION
            "-- empty --"
    ::= { hmStatusWlanStationTableEntry 66 }

-- {COLUMN} 1.3.6.1.4.1.248.32.18.1.3.32.1.67
hmStatusWlanStationTableEntryProtMgmtFrames OBJECT-TYPE
    SYNTAX     INTEGER {
                  eNo (0),
                  eYes (1)
            }
    MAX-ACCESS read-only
    STATUS     current
    DESCRIPTION
            "-- empty --"
    ::= { hmStatusWlanStationTableEntry 67 }

-- {COLUMN} 1.3.6.1.4.1.248.32.18.1.3.32.1.68
hmStatusWlanStationTableEntryRxStbcHt OBJECT-TYPE
    SYNTAX     INTEGER {
                  eNone (0),
                  eOne (1),
                  eTwo (2),
                  eThree (3)
            }
    MAX-ACCESS read-only
    STATUS     current
    DESCRIPTION
            "-- empty --"
    ::= { hmStatusWlanStationTableEntry 68 }

-- {COLUMN} 1.3.6.1.4.1.248.32.18.1.3.32.1.69
hmStatusWlanStationTableEntryRxStbcVht OBJECT-TYPE
    SYNTAX     INTEGER {
                  eNone (0),
                  eOne (1),
                  eTwo (2),
                  eThree (3),
                  eFour (4),
                  eFive (5),
                  eSix (6),
                  eSeven (7)
            }
    MAX-ACCESS read-only
    STATUS     current
    DESCRIPTION
            "-- empty --"
    ::= { hmStatusWlanStationTableEntry 69 }

-- {COLUMN} 1.3.6.1.4.1.248.32.18.1.3.32.1.70
hmStatusWlanStationTableEntryLDPCMask OBJECT-TYPE
    SYNTAX     BITS {
                  eVht (30),
                  eHt (31)
            }
    MAX-ACCESS read-only
    STATUS     current
    DESCRIPTION
            "Bit mask of LDPC support per-PHY-Type"
    ::= { hmStatusWlanStationTableEntry 70 }

-- {COLUMN} 1.3.6.1.4.1.248.32.18.1.3.32.1.71
hmStatusWlanStationTableEntryOperationMode OBJECT-TYPE
    SYNTAX     INTEGER {
                  eUnknown (0),
                  e11b (1),
                  e11g (2),
                  e11a (3),
                  e11n (4)
            }
    MAX-ACCESS read-only
    STATUS     current
    DESCRIPTION
            "-- empty --"
    ::= { hmStatusWlanStationTableEntry 71 }

-- {COLUMN} 1.3.6.1.4.1.248.32.18.1.3.32.1.72
hmStatusWlanStationTableEntryBlockackTestResult OBJECT-TYPE
    SYNTAX     INTEGER {
                  eUnknown (0),
                  eOk (1),
                  eNotOk (2),
                  eNotApplicable (3)
            }
    MAX-ACCESS read-only
    STATUS     current
    DESCRIPTION
            "-- empty --"
    ::= { hmStatusWlanStationTableEntry 72 }

-- {COLUMN} 1.3.6.1.4.1.248.32.18.1.3.32.1.248
hmStatusWlanStationTableEntryClBrgRoamingSupport OBJECT-TYPE
    SYNTAX     INTEGER {
                  eNo (0),
                  eYes (1)
            }
    MAX-ACCESS read-only
    STATUS     current
    DESCRIPTION
            "-- empty --"
    ::= { hmStatusWlanStationTableEntry 248 }

-- {COLUMN} 1.3.6.1.4.1.248.32.18.1.3.32.1.565
hmStatusWlanStationTableEntryIpv6AddressTxt OBJECT-TYPE
    SYNTAX     DisplayString (SIZE(0..255))
    MAX-ACCESS read-only
    STATUS     current
    DESCRIPTION
            "-- empty --"
    ::= { hmStatusWlanStationTableEntry 565 }

-- {TABLE} 1.3.6.1.4.1.248.32.18.1.3.34
hmStatusWlanScanResultsTable OBJECT-TYPE
    SYNTAX     SEQUENCE OF HmStatusWlanScanResultsEntry
    MAX-ACCESS not-accessible
    STATUS     current
    DESCRIPTION
            "-- empty --"
    ::= { hmStatusWlan 34 }

-- {ROW} 1.3.6.1.4.1.248.32.18.1.3.34.1
hmStatusWlanScanResultsEntry OBJECT-TYPE
    SYNTAX     HmStatusWlanScanResultsEntry
    MAX-ACCESS not-accessible
    STATUS     current
    DESCRIPTION
            ""
    INDEX {
            hmStatusWlanScanResultsEntryBssid,
            hmStatusWlanScanResultsEntryInterface
          }
    ::= { hmStatusWlanScanResultsTable 1 }

HmStatusWlanScanResultsEntry ::= SEQUENCE {
            hmStatusWlanScanResultsEntryBssid MacAddress,
            hmStatusWlanScanResultsEntryNetworkName DisplayString,
            hmStatusWlanScanResultsEntryOperationMode INTEGER,
            hmStatusWlanScanResultsEntryBeaconPeriod Integer32,
            hmStatusWlanScanResultsEntryDtimPeriod Integer32,
            hmStatusWlanScanResultsEntryRadioChannel Integer32,
            hmStatusWlanScanResultsEntryPhySignal Integer32,
            hmStatusWlanScanResultsEntryNoiseLevel Integer32,
            hmStatusWlanScanResultsEntryLoad DisplayString,
            hmStatusWlanScanResultsEntryEncryption INTEGER,
            hmStatusWlanScanResultsEntryShortPreamble INTEGER,
            hmStatusWlanScanResultsEntryInterface INTEGER,
            hmStatusWlanScanResultsEntryRadioBand INTEGER,
            hmStatusWlanScanResultsEntry108mbpsMode INTEGER,
            hmStatusWlanScanResultsEntryShortSlotTime INTEGER,
            hmStatusWlanScanResultsEntryRate INTEGER,
            hmStatusWlanScanResultsEntryNonerpPresent INTEGER,
            hmStatusWlanScanResultsEntryCompression INTEGER,
            hmStatusWlanScanResultsEntryPcfFunctionality INTEGER,
            hmStatusWlanScanResultsEntryIdentification DisplayString,
            hmStatusWlanScanResultsEntryQos INTEGER,
            hmStatusWlanScanResultsEntryAge Integer32,
            hmStatusWlanScanResultsEntrySignalLevel Integer32,
            hmStatusWlanScanResultsEntryShortGuardInterval INTEGER,
            hmStatusWlanScanResultsEntryExtChannel INTEGER,
            hmStatusWlanScanResultsEntry40mhzMode INTEGER,
            hmStatusWlanScanResultsEntry40mhzIntolerant INTEGER,
            hmStatusWlanScanResultsEntryInterpointPeerName DisplayString,
            hmStatusWlanScanResultsEntryMaxAMpduLen Integer32,
            hmStatusWlanScanResultsEntryMaxAMsduLen Integer32,
            hmStatusWlanScanResultsEntryVendor DisplayString,
            hmStatusWlanScanResultsEntryEffRate Integer32,
            hmStatusWlanScanResultsEntry40mhzCoexistence INTEGER,
            hmStatusWlanScanResultsEntryPreAuthentication INTEGER,
            hmStatusWlanScanResultsEntryTxStbc INTEGER,
            hmStatusWlanScanResultsEntryRxStbc INTEGER,
            hmStatusWlanScanResultsEntryEapolPreauthFailed INTEGER,
            hmStatusWlanScanResultsEntryLdpc INTEGER,
            hmStatusWlanScanResultsEntryAutowds INTEGER,
            hmStatusWlanScanResultsEntrySGIMask BITS,
            hmStatusWlanScanResultsEntryChannelBandwidths BITS,
            hmStatusWlanScanResultsEntryChannelBandwidth INTEGER,
            hmStatusWlanScanResultsEntryClBrgSupport INTEGER,
            hmStatusWlanScanResultsEntryProtMgmtFrames INTEGER,
            hmStatusWlanScanResultsEntryTxPowerLimit DisplayString,
            hmStatusWlanScanResultsEntryTxSTBCMask BITS,
            hmStatusWlanScanResultsEntryRxStbcHt INTEGER,
            hmStatusWlanScanResultsEntryRxStbcVht INTEGER,
            hmStatusWlanScanResultsEntryLDPCMask BITS,
            hmStatusWlanScanResultsEntryClBrgRoamingSupport INTEGER
    }

-- {COLUMN} 1.3.6.1.4.1.248.32.18.1.3.34.1.1
hmStatusWlanScanResultsEntryBssid OBJECT-TYPE
    SYNTAX     MacAddress
    MAX-ACCESS read-only
    STATUS     current
    DESCRIPTION
            "-- empty --"
    ::= { hmStatusWlanScanResultsEntry 1 }

-- {COLUMN} 1.3.6.1.4.1.248.32.18.1.3.34.1.2
hmStatusWlanScanResultsEntryNetworkName OBJECT-TYPE
    SYNTAX     DisplayString (SIZE(0..255))
    MAX-ACCESS read-only
    STATUS     current
    DESCRIPTION
            "-- empty --"
    ::= { hmStatusWlanScanResultsEntry 2 }

-- {COLUMN} 1.3.6.1.4.1.248.32.18.1.3.34.1.3
hmStatusWlanScanResultsEntryOperationMode OBJECT-TYPE
    SYNTAX     INTEGER {
                  eNone (0),
                  eAdhoc (1),
                  eInfrastructure (2)
            }
    MAX-ACCESS read-only
    STATUS     current
    DESCRIPTION
            "hirschmann's description of operation mode"
    ::= { hmStatusWlanScanResultsEntry 3 }

-- {COLUMN} 1.3.6.1.4.1.248.32.18.1.3.34.1.6
hmStatusWlanScanResultsEntryBeaconPeriod OBJECT-TYPE
    SYNTAX     Integer32 (0..65535)
    MAX-ACCESS read-only
    STATUS     current
    DESCRIPTION
            "-- empty --"
    ::= { hmStatusWlanScanResultsEntry 6 }

-- {COLUMN} 1.3.6.1.4.1.248.32.18.1.3.34.1.7
hmStatusWlanScanResultsEntryDtimPeriod OBJECT-TYPE
    SYNTAX     Integer32 (0..65535)
    MAX-ACCESS read-only
    STATUS     current
    DESCRIPTION
            "-- empty --"
    ::= { hmStatusWlanScanResultsEntry 7 }

-- {COLUMN} 1.3.6.1.4.1.248.32.18.1.3.34.1.8
hmStatusWlanScanResultsEntryRadioChannel OBJECT-TYPE
    SYNTAX     Integer32 (0..255)
    MAX-ACCESS read-only
    STATUS     current
    DESCRIPTION
            "-- empty --"
    ::= { hmStatusWlanScanResultsEntry 8 }

-- {COLUMN} 1.3.6.1.4.1.248.32.18.1.3.34.1.10
hmStatusWlanScanResultsEntryPhySignal OBJECT-TYPE
    SYNTAX     Integer32 (0..65535)
    MAX-ACCESS read-only
    STATUS     current
    DESCRIPTION
            "-- empty --"
    ::= { hmStatusWlanScanResultsEntry 10 }

-- {COLUMN} 1.3.6.1.4.1.248.32.18.1.3.34.1.11
hmStatusWlanScanResultsEntryNoiseLevel OBJECT-TYPE
    SYNTAX     Integer32 (-128..127)
    MAX-ACCESS read-only
    STATUS     current
    DESCRIPTION
            "-- empty --"
    ::= { hmStatusWlanScanResultsEntry 11 }

-- {COLUMN} 1.3.6.1.4.1.248.32.18.1.3.34.1.12
hmStatusWlanScanResultsEntryLoad OBJECT-TYPE
    SYNTAX     DisplayString (SIZE(0..255))
    MAX-ACCESS read-only
    STATUS     current
    DESCRIPTION
            "-- empty --"
    ::= { hmStatusWlanScanResultsEntry 12 }

-- {COLUMN} 1.3.6.1.4.1.248.32.18.1.3.34.1.13
hmStatusWlanScanResultsEntryEncryption OBJECT-TYPE
    SYNTAX     INTEGER {
                  eNone (0),
                  eWep (1),
                  eTkip (2),
                  eAes (3),
                  eAesPlusTkip (4)
            }
    MAX-ACCESS read-only
    STATUS     current
    DESCRIPTION
            "-- empty --"
    ::= { hmStatusWlanScanResultsEntry 13 }

-- {COLUMN} 1.3.6.1.4.1.248.32.18.1.3.34.1.14
hmStatusWlanScanResultsEntryShortPreamble OBJECT-TYPE
    SYNTAX     INTEGER {
                  eNo (0),
                  eYes (1)
            }
    MAX-ACCESS read-only
    STATUS     current
    DESCRIPTION
            "-- empty --"
    ::= { hmStatusWlanScanResultsEntry 14 }

-- {COLUMN} 1.3.6.1.4.1.248.32.18.1.3.34.1.15
hmStatusWlanScanResultsEntryInterface OBJECT-TYPE
    SYNTAX     INTEGER {
                  eWlan1 (0),
                  eWlan2 (1),
                  eWlan3 (2),
                  eWlan4 (3)
            }
    MAX-ACCESS read-only
    STATUS     current
    DESCRIPTION
            "-- empty --"
    ::= { hmStatusWlanScanResultsEntry 15 }

-- {COLUMN} 1.3.6.1.4.1.248.32.18.1.3.34.1.16
hmStatusWlanScanResultsEntryRadioBand OBJECT-TYPE
    SYNTAX     INTEGER {
                  eUnknown (0),
                  e24ghz (1),
                  e5ghz (2)
            }
    MAX-ACCESS read-only
    STATUS     current
    DESCRIPTION
            "-- empty --"
    ::= { hmStatusWlanScanResultsEntry 16 }

-- {COLUMN} 1.3.6.1.4.1.248.32.18.1.3.34.1.17
hmStatusWlanScanResultsEntry108mbpsMode OBJECT-TYPE
    SYNTAX     INTEGER {
                  eNo (0),
                  eYes (1)
            }
    MAX-ACCESS read-only
    STATUS     current
    DESCRIPTION
            "-- empty --"
    ::= { hmStatusWlanScanResultsEntry 17 }

-- {COLUMN} 1.3.6.1.4.1.248.32.18.1.3.34.1.18
hmStatusWlanScanResultsEntryShortSlotTime OBJECT-TYPE
    SYNTAX     INTEGER {
                  eNo (0),
                  eYes (1)
            }
    MAX-ACCESS read-only
    STATUS     current
    DESCRIPTION
            "-- empty --"
    ::= { hmStatusWlanScanResultsEntry 18 }

-- {COLUMN} 1.3.6.1.4.1.248.32.18.1.3.34.1.19
hmStatusWlanScanResultsEntryRate OBJECT-TYPE
    SYNTAX     INTEGER {
                  eUnknown (0),
                  e1M (1),
                  e2M (2),
                  e5M (3),
                  e5M5 (4),
                  e8M (5),
                  e11M (6),
                  e6M (12),
                  e9M (13),
                  e12M (14),
                  e18M (15),
                  e24M (16),
                  e36M (17),
                  e48M (18),
                  e54M (19),
                  eT12M (20),
                  eT18M (21),
                  eT24M (22),
                  eT36M (23),
                  eT48M (24),
                  eT72M (25),
                  eT96M (26),
                  eT108M (27),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eHT4S26M (52),
                  eHT4S52M (53),
                  eHT4S78M (54),
                  eHT4S104M (55),
                  eHT4S156M (56),
                  eHT4S208M (57),
                  eHT4S234M (58),
                  eHT4S260M (59),
                  eHTDUP6M (60),
                  eHtMcs33 (61),
                  eHtMcs34 (62),
                  eHtMcs35 (63),
                  eHtMcs36 (64),
                  eHtMcs37 (65),
                  eHtMcs38 (66),
                  eHtMcs39 (67),
                  eHtMcs40 (68),
                  eHtMcs41 (69),
                  eHtMcs42 (70),
                  eHtMcs43 (71),
                  eHtMcs44 (72),
                  eHtMcs45 (73),
                  eHtMcs46 (74),
                  eHtMcs47 (75),
                  eHtMcs48 (76),
                  eHtMcs49 (77),
                  eHtMcs50 (78),
                  eHtMcs51 (79),
                  eHtMcs52 (80),
                  eHtMcs53 (81),
                  eHtMcs54 (82),
                  eHtMcs55 (83),
                  eHtMcs56 (84),
                  eHtMcs57 (85),
                  eHtMcs58 (86),
                  eHtMcs59 (87),
                  eHtMcs60 (88),
                  eHtMcs61 (89),
                  eHtMcs62 (90),
                  eHtMcs63 (91),
                  eHtMcs64 (92),
                  eHtMcs65 (93),
                  eHtMcs66 (94),
                  eHtMcs67 (95),
                  eHtMcs68 (96),
                  eHtMcs69 (97),
                  eHtMcs70 (98),
                  eHtMcs71 (99),
                  eHtMcs72 (100),
                  eHtMcs73 (101),
                  eHtMcs74 (102),
                  eHtMcs75 (103),
                  eHtMcs76 (104),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            "-- empty --"
    ::= { hmStatusWlanScanResultsEntry 19 }

-- {COLUMN} 1.3.6.1.4.1.248.32.18.1.3.34.1.20
hmStatusWlanScanResultsEntryNonerpPresent OBJECT-TYPE
    SYNTAX     INTEGER {
                  eNo (0),
                  eYes (1)
            }
    MAX-ACCESS read-only
    STATUS     current
    DESCRIPTION
            "-- empty --"
    ::= { hmStatusWlanScanResultsEntry 20 }

-- {COLUMN} 1.3.6.1.4.1.248.32.18.1.3.34.1.21
hmStatusWlanScanResultsEntryCompression OBJECT-TYPE
    SYNTAX     INTEGER {
                  eNo (0),
                  eYes (1)
            }
    MAX-ACCESS read-only
    STATUS     current
    DESCRIPTION
            "-- empty --"
    ::= { hmStatusWlanScanResultsEntry 21 }

-- {COLUMN} 1.3.6.1.4.1.248.32.18.1.3.34.1.22
hmStatusWlanScanResultsEntryPcfFunctionality OBJECT-TYPE
    SYNTAX     INTEGER {
                  eNone (0),
                  eDelivery (1),
                  eDeliveryPlusPolling (2)
            }
    MAX-ACCESS read-only
    STATUS     current
    DESCRIPTION
            "-- empty --"
    ::= { hmStatusWlanScanResultsEntry 22 }

-- {COLUMN} 1.3.6.1.4.1.248.32.18.1.3.34.1.23
hmStatusWlanScanResultsEntryIdentification OBJECT-TYPE
    SYNTAX     DisplayString (SIZE(0..16))
    MAX-ACCESS read-only
    STATUS     current
    DESCRIPTION
            "-- empty --"
    ::= { hmStatusWlanScanResultsEntry 23 }

-- {COLUMN} 1.3.6.1.4.1.248.32.18.1.3.34.1.24
hmStatusWlanScanResultsEntryQos OBJECT-TYPE
    SYNTAX     INTEGER {
                  eNo (0),
                  eYes (1)
            }
    MAX-ACCESS read-only
    STATUS     current
    DESCRIPTION
            "-- empty --"
    ::= { hmStatusWlanScanResultsEntry 24 }

-- {COLUMN} 1.3.6.1.4.1.248.32.18.1.3.34.1.25
hmStatusWlanScanResultsEntryAge OBJECT-TYPE
    SYNTAX     Integer32 (0..2147483647)
    MAX-ACCESS read-only
    STATUS     current
    DESCRIPTION
            "-- empty --"
    ::= { hmStatusWlanScanResultsEntry 25 }

-- {COLUMN} 1.3.6.1.4.1.248.32.18.1.3.34.1.26
hmStatusWlanScanResultsEntrySignalLevel OBJECT-TYPE
    SYNTAX     Integer32 (-32768..32767)
    MAX-ACCESS read-only
    STATUS     current
    DESCRIPTION
            "-- empty --"
    ::= { hmStatusWlanScanResultsEntry 26 }

-- {COLUMN} 1.3.6.1.4.1.248.32.18.1.3.34.1.27
hmStatusWlanScanResultsEntryShortGuardInterval OBJECT-TYPE
    SYNTAX     INTEGER {
                  eNo (0),
                  e20mhz (1),
                  e40mhz (2),
                  e2040mhz (3)
            }
    MAX-ACCESS read-only
    STATUS     current
    DESCRIPTION
            "-- empty --"
    ::= { hmStatusWlanScanResultsEntry 27 }

-- {COLUMN} 1.3.6.1.4.1.248.32.18.1.3.34.1.28
hmStatusWlanScanResultsEntryExtChannel OBJECT-TYPE
    SYNTAX     INTEGER {
                  eNone (0),
                  eAbove (1),
                  eBelow (3)
            }
    MAX-ACCESS read-only
    STATUS     current
    DESCRIPTION
            "-- empty --"
    ::= { hmStatusWlanScanResultsEntry 28 }

-- {COLUMN} 1.3.6.1.4.1.248.32.18.1.3.34.1.29
hmStatusWlanScanResultsEntry40mhzMode OBJECT-TYPE
    SYNTAX     INTEGER {
                  eNo (0),
                  eYes (1)
            }
    MAX-ACCESS read-only
    STATUS     current
    DESCRIPTION
            "-- empty --"
    ::= { hmStatusWlanScanResultsEntry 29 }

-- {COLUMN} 1.3.6.1.4.1.248.32.18.1.3.34.1.30
hmStatusWlanScanResultsEntry40mhzIntolerant OBJECT-TYPE
    SYNTAX     INTEGER {
                  eNo (0),
                  eYes (1)
            }
    MAX-ACCESS read-only
    STATUS     current
    DESCRIPTION
            "-- empty --"
    ::= { hmStatusWlanScanResultsEntry 30 }

-- {COLUMN} 1.3.6.1.4.1.248.32.18.1.3.34.1.31
hmStatusWlanScanResultsEntryInterpointPeerName OBJECT-TYPE
    SYNTAX     DisplayString (SIZE(0..24))
    MAX-ACCESS read-only
    STATUS     current
    DESCRIPTION
            "-- empty --"
    ::= { hmStatusWlanScanResultsEntry 31 }

-- {COLUMN} 1.3.6.1.4.1.248.32.18.1.3.34.1.32
hmStatusWlanScanResultsEntryMaxAMpduLen OBJECT-TYPE
    SYNTAX     Integer32 (0..2147483647)
    MAX-ACCESS read-only
    STATUS     current
    DESCRIPTION
            "-- empty --"
    ::= { hmStatusWlanScanResultsEntry 32 }

-- {COLUMN} 1.3.6.1.4.1.248.32.18.1.3.34.1.33
hmStatusWlanScanResultsEntryMaxAMsduLen OBJECT-TYPE
    SYNTAX     Integer32 (0..2147483647)
    MAX-ACCESS read-only
    STATUS     current
    DESCRIPTION
            "-- empty --"
    ::= { hmStatusWlanScanResultsEntry 33 }

-- {COLUMN} 1.3.6.1.4.1.248.32.18.1.3.34.1.34
hmStatusWlanScanResultsEntryVendor OBJECT-TYPE
    SYNTAX     DisplayString (SIZE(0..255))
    MAX-ACCESS read-only
    STATUS     current
    DESCRIPTION
            "-- empty --"
    ::= { hmStatusWlanScanResultsEntry 34 }

-- {COLUMN} 1.3.6.1.4.1.248.32.18.1.3.34.1.35
hmStatusWlanScanResultsEntryEffRate OBJECT-TYPE
    SYNTAX     Integer32 (0..2147483647)
    MAX-ACCESS read-only
    STATUS     current
    DESCRIPTION
            "-- empty --"
    ::= { hmStatusWlanScanResultsEntry 35 }

-- {COLUMN} 1.3.6.1.4.1.248.32.18.1.3.34.1.36
hmStatusWlanScanResultsEntry40mhzCoexistence OBJECT-TYPE
    SYNTAX     INTEGER {
                  eNo (0),
                  eYes (1)
            }
    MAX-ACCESS read-only
    STATUS     current
    DESCRIPTION
            "-- empty --"
    ::= { hmStatusWlanScanResultsEntry 36 }

-- {COLUMN} 1.3.6.1.4.1.248.32.18.1.3.34.1.37
hmStatusWlanScanResultsEntryPreAuthentication OBJECT-TYPE
    SYNTAX     INTEGER {
                  eNo (0),
                  eYes (1)
            }
    MAX-ACCESS read-only
    STATUS     current
    DESCRIPTION
            "-- empty --"
    ::= { hmStatusWlanScanResultsEntry 37 }

-- {COLUMN} 1.3.6.1.4.1.248.32.18.1.3.34.1.38
hmStatusWlanScanResultsEntryTxStbc OBJECT-TYPE
    SYNTAX     INTEGER {
                  eNo (0),
                  eYes (1)
            }
    MAX-ACCESS read-only
    STATUS     current
    DESCRIPTION
            "-- empty --"
    ::= { hmStatusWlanScanResultsEntry 38 }

-- {COLUMN} 1.3.6.1.4.1.248.32.18.1.3.34.1.39
hmStatusWlanScanResultsEntryRxStbc OBJECT-TYPE
    SYNTAX     INTEGER {
                  eNone (0),
                  eOne (1),
                  eTwo (2),
                  eThree (3)
            }
    MAX-ACCESS read-only
    STATUS     current
    DESCRIPTION
            "-- empty --"
    ::= { hmStatusWlanScanResultsEntry 39 }

-- {COLUMN} 1.3.6.1.4.1.248.32.18.1.3.34.1.40
hmStatusWlanScanResultsEntryEapolPreauthFailed OBJECT-TYPE
    SYNTAX     INTEGER {
                  eNo (0),
                  eYes (1)
            }
    MAX-ACCESS read-only
    STATUS     current
    DESCRIPTION
            "-- empty --"
    ::= { hmStatusWlanScanResultsEntry 40 }

-- {COLUMN} 1.3.6.1.4.1.248.32.18.1.3.34.1.41
hmStatusWlanScanResultsEntryLdpc OBJECT-TYPE
    SYNTAX     INTEGER {
                  eNo (0),
                  eYes (1)
            }
    MAX-ACCESS read-only
    STATUS     current
    DESCRIPTION
            "-- empty --"
    ::= { hmStatusWlanScanResultsEntry 41 }

-- {COLUMN} 1.3.6.1.4.1.248.32.18.1.3.34.1.42
hmStatusWlanScanResultsEntryAutowds OBJECT-TYPE
    SYNTAX     INTEGER {
                  eNo (0),
                  eYes (1)
            }
    MAX-ACCESS read-only
    STATUS     current
    DESCRIPTION
            "-- empty --"
    ::= { hmStatusWlanScanResultsEntry 42 }

-- {COLUMN} 1.3.6.1.4.1.248.32.18.1.3.34.1.43
hmStatusWlanScanResultsEntrySGIMask OBJECT-TYPE
    SYNTAX     BITS {
                  eNo (0),
                  e160mhz (28),
                  e80mhz (29),
                  e40mhz (30),
                  e20mhz (31)
            }
    MAX-ACCESS read-only
    STATUS     current
    DESCRIPTION
            "Bit mask of short guard interval support per-CBW"
    ::= { hmStatusWlanScanResultsEntry 43 }

-- {COLUMN} 1.3.6.1.4.1.248.32.18.1.3.34.1.44
hmStatusWlanScanResultsEntryChannelBandwidths OBJECT-TYPE
    SYNTAX     BITS {
                  eT40mhz (26),
                  e80Plus80mhz (27),
                  e160mhz (28),
                  e80mhz (29),
                  e40mhz (30),
                  e20mhz (31)
            }
    MAX-ACCESS read-only
    STATUS     current
    DESCRIPTION
            "-- empty --"
    ::= { hmStatusWlanScanResultsEntry 44 }

-- {COLUMN} 1.3.6.1.4.1.248.32.18.1.3.34.1.45
hmStatusWlanScanResultsEntryChannelBandwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { hmStatusWlanScanResultsEntry 45 }

-- {COLUMN} 1.3.6.1.4.1.248.32.18.1.3.34.1.46
hmStatusWlanScanResultsEntryClBrgSupport OBJECT-TYPE
    SYNTAX     INTEGER {
                  eNo (0),
                  eYes (1)
            }
    MAX-ACCESS read-only
    STATUS     current
    DESCRIPTION
            "-- empty --"
    ::= { hmStatusWlanScanResultsEntry 46 }

-- {COLUMN} 1.3.6.1.4.1.248.32.18.1.3.34.1.47
hmStatusWlanScanResultsEntryProtMgmtFrames OBJECT-TYPE
    SYNTAX     INTEGER {
                  eNo (0),
                  eOptional (1),
                  eMandatory (2)
            }
    MAX-ACCESS read-only
    STATUS     current
    DESCRIPTION
            "-- empty --"
    ::= { hmStatusWlanScanResultsEntry 47 }

-- {COLUMN} 1.3.6.1.4.1.248.32.18.1.3.34.1.48
hmStatusWlanScanResultsEntryTxPowerLimit OBJECT-TYPE
    SYNTAX     DisplayString (SIZE(0..255))
    MAX-ACCESS read-only
    STATUS     current
    DESCRIPTION
            "-- empty --"
    ::= { hmStatusWlanScanResultsEntry 48 }

-- {COLUMN} 1.3.6.1.4.1.248.32.18.1.3.34.1.49
hmStatusWlanScanResultsEntryTxSTBCMask OBJECT-TYPE
    SYNTAX     BITS {
                  eVht (30),
                  eHt (31)
            }
    MAX-ACCESS read-only
    STATUS     current
    DESCRIPTION
            "Bit mask of Tx STBC support per-PHY-Type"
    ::= { hmStatusWlanScanResultsEntry 49 }

-- {COLUMN} 1.3.6.1.4.1.248.32.18.1.3.34.1.50
hmStatusWlanScanResultsEntryRxStbcHt OBJECT-TYPE
    SYNTAX     INTEGER {
                  eNone (0),
                  eOne (1),
                  eTwo (2),
                  eThree (3)
            }
    MAX-ACCESS read-only
    STATUS     current
    DESCRIPTION
            "-- empty --"
    ::= { hmStatusWlanScanResultsEntry 50 }

-- {COLUMN} 1.3.6.1.4.1.248.32.18.1.3.34.1.51
hmStatusWlanScanResultsEntryRxStbcVht OBJECT-TYPE
    SYNTAX     INTEGER {
                  eNone (0),
                  eOne (1),
                  eTwo (2),
                  eThree (3),
                  eFour (4),
                  eFive (5),
                  eSix (6),
                  eSeven (7)
            }
    MAX-ACCESS read-only
    STATUS     current
    DESCRIPTION
            "-- empty --"
    ::= { hmStatusWlanScanResultsEntry 51 }

-- {COLUMN} 1.3.6.1.4.1.248.32.18.1.3.34.1.52
hmStatusWlanScanResultsEntryLDPCMask OBJECT-TYPE
    SYNTAX     BITS {
                  eVht (30),
                  eHt (31)
            }
    MAX-ACCESS read-only
    STATUS     current
    DESCRIPTION
            "Bit mask of LDPC support per-PHY-Type"
    ::= { hmStatusWlanScanResultsEntry 52 }

-- {COLUMN} 1.3.6.1.4.1.248.32.18.1.3.34.1.248
hmStatusWlanScanResultsEntryClBrgRoamingSupport OBJECT-TYPE
    SYNTAX     INTEGER {
                  eNo (0),
                  eYes (1)
            }
    MAX-ACCESS read-only
    STATUS     current
    DESCRIPTION
            "-- empty --"
    ::= { hmStatusWlanScanResultsEntry 248 }

-- {NODE} 1.3.6.1.4.1.248.32.18.1.3.36
hmStatusWlanInterpoints OBJECT IDENTIFIER ::= { hmStatusWlan 36 }

-- {TABLE} 1.3.6.1.4.1.248.32.18.1.3.36.1
hmStatusWlanInterpointsAccesspointListTable OBJECT-TYPE
    SYNTAX     SEQUENCE OF HmStatusWlanInterpointsAccesspointListEntry
    MAX-ACCESS not-accessible
    STATUS     current
    DESCRIPTION
            "-- empty --"
    ::= { hmStatusWlanInterpoints 1 }

-- {ROW} 1.3.6.1.4.1.248.32.18.1.3.36.1.1
hmStatusWlanInterpointsAccesspointListEntry OBJECT-TYPE
    SYNTAX     HmStatusWlanInterpointsAccesspointListEntry
    MAX-ACCESS not-accessible
    STATUS     current
    DESCRIPTION
            ""
    INDEX {
            hmStatusWlanInterpointsAccesspointListEntryIndex
          }
    ::= { hmStatusWlanInterpointsAccesspointListTable 1 }

HmStatusWlanInterpointsAccesspointListEntry ::= SEQUENCE {
            hmStatusWlanInterpointsAccesspointListEntryIndex INTEGER,
            hmStatusWlanInterpointsAccesspointListEntryMacAddress MacAddress,
            hmStatusWlanInterpointsAccesspointListEntryRxRate INTEGER,
            hmStatusWlanInterpointsAccesspointListEntryTxBytes Counter64,
            hmStatusWlanInterpointsAccesspointListEntryRxBytes Counter64,
            hmStatusWlanInterpointsAccesspointListEntryThroughput DisplayString,
            hmStatusWlanInterpointsAccesspointListEntryKeyingState INTEGER,
            hmStatusWlanInterpointsAccesspointListEntryRxPhySignal Integer32,
            hmStatusWlanInterpointsAccesspointListEntryLinkPhySignal Integer32,
            hmStatusWlanInterpointsAccesspointListEntryIdentification DisplayString,
            hmStatusWlanInterpointsAccesspointListEntryTxRate INTEGER,
            hmStatusWlanInterpointsAccesspointListEntryMaxThroughput DisplayString,
            hmStatusWlanInterpointsAccesspointListEntryBytesThroughput Integer32,
            hmStatusWlanInterpointsAccesspointListEntryBytesMaxThroughput Integer32,
            hmStatusWlanInterpointsAccesspointListEntryWpaVersion INTEGER,
            hmStatusWlanInterpointsAccesspointListEntryTxLimit Integer32,
            hmStatusWlanInterpointsAccesspointListEntryRxLimit Integer32,
            hmStatusWlanInterpointsAccesspointListEntryKeyHandshakeRole INTEGER,
            hmStatusWlanInterpointsAccesspointListEntryTxPackets Integer32,
            hmStatusWlanInterpointsAccesspointListEntryRxPackets Integer32,
            hmStatusWlanInterpointsAccesspointListEntryQos INTEGER,
            hmStatusWlanInterpointsAccesspointListEntryInterpointPeerName DisplayString,
            hmStatusWlanInterpointsAccesspointListEntryMaxAMsduLen Integer32,
            hmStatusWlanInterpointsAccesspointListEntryMaxAMpduLen Integer32,
            hmStatusWlanInterpointsAccesspointListEntry40mhzMode INTEGER,
            hmStatusWlanInterpointsAccesspointListEntryShortPreamble INTEGER,
            hmStatusWlanInterpointsAccesspointListEntryShortGuardInterval INTEGER,
            hmStatusWlanInterpointsAccesspointListEntryEffTxRate Integer32,
            hmStatusWlanInterpointsAccesspointListEntryEffRxRate Integer32,
            hmStatusWlanInterpointsAccesspointListEntryKeyType INTEGER,
            hmStatusWlanInterpointsAccesspointListEntryTxErrors Integer32,
            hmStatusWlanInterpointsAccesspointListEntryTotalRetries Integer32,
            hmStatusWlanInterpointsAccesspointListEntryAlarmState BITS,
            hmStatusWlanInterpointsAccesspointListEntryLinkActive INTEGER,
            hmStatusWlanInterpointsAccesspointListEntryRxStbc INTEGER,
            hmStatusWlanInterpointsAccesspointListEntryLdpc INTEGER,
            hmStatusWlanInterpointsAccesspointListEntryRemoteStatus INTEGER,
            hmStatusWlanInterpointsAccesspointListEntryWpa2KeyManagement INTEGER,
            hmStatusWlanInterpointsAccesspointListEntrySGIMask BITS,
            hmStatusWlanInterpointsAccesspointListEntryChannelBandwidths BITS,
            hmStatusWlanInterpointsAccesspointListEntryProtMgmtFrames INTEGER,
            hmStatusWlanInterpointsAccesspointListEntryRxStbcHt INTEGER,
            hmStatusWlanInterpointsAccesspointListEntryRxStbcVht INTEGER,
            hmStatusWlanInterpointsAccesspointListEntryLDPCMask BITS,
            hmStatusWlanInterpointsAccesspointListEntryOperationMode INTEGER,
            hmStatusWlanInterpointsAccesspointListEntryC2cIdentifier DisplayString
    }

-- {COLUMN} 1.3.6.1.4.1.248.32.18.1.3.36.1.1.1
hmStatusWlanInterpointsAccesspointListEntryIndex OBJECT-TYPE
    SYNTAX     INTEGER {
                  eP2p11 (1),
                  eP2p12 (2),
                  eP2p13 (3),
                  eP2p14 (4),
                  eP2p15 (5),
                  eP2p16 (6),
                  eP2p21 (7),
                  eP2p22 (8),
                  eP2p23 (9),
                  eP2p24 (10),
                  eP2p25 (11),
                  eP2p26 (12),
                  eP2p17 (32),
                  eP2p18 (33),
                  eP2p19 (34),
                  eP2p110 (35),
                  eP2p111 (36),
                  eP2p112 (37),
                  eP2p113 (38),
                  eP2p114 (39),
                  eP2p115 (40),
                  eP2p116 (41),
                  eP2p27 (64),
                  eP2p28 (65),
                  eP2p29 (66),
                  eP2p210 (67),
                  eP2p211 (68),
                  eP2p212 (69),
                  eP2p213 (70),
                  eP2p214 (71),
                  eP2p215 (72),
                  eP2p216 (73)
            }
    MAX-ACCESS read-only
    STATUS     current
    DESCRIPTION
            "-- empty --"
    ::= { hmStatusWlanInterpointsAccesspointListEntry 1 }

-- {COLUMN} 1.3.6.1.4.1.248.32.18.1.3.36.1.1.2
hmStatusWlanInterpointsAccesspointListEntryMacAddress OBJECT-TYPE
    SYNTAX     MacAddress
    MAX-ACCESS read-only
    STATUS     current
    DESCRIPTION
            "-- empty --"
    ::= { hmStatusWlanInterpointsAccesspointListEntry 2 }

-- {COLUMN} 1.3.6.1.4.1.248.32.18.1.3.36.1.1.5
hmStatusWlanInterpointsAccesspointListEntryRxRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51)
            }
    MAX-ACCESS read-only
    STATUS     current
    DESCRIPTION
            "-- empty --"
    ::= { hmStatusWlanInterpointsAccesspointListEntry 5 }

-- {COLUMN} 1.3.6.1.4.1.248.32.18.1.3.36.1.1.6
hmStatusWlanInterpointsAccesspointListEntryTxBytes OBJECT-TYPE
    SYNTAX     Counter64
    MAX-ACCESS read-only
    STATUS     current
    DESCRIPTION
            "-- empty --"
    ::= { hmStatusWlanInterpointsAccesspointListEntry 6 }

-- {COLUMN} 1.3.6.1.4.1.248.32.18.1.3.36.1.1.7
hmStatusWlanInterpointsAccesspointListEntryRxBytes OBJECT-TYPE
    SYNTAX     Counter64
    MAX-ACCESS read-only
    STATUS     current
    DESCRIPTION
            "-- empty --"
    ::= { hmStatusWlanInterpointsAccesspointListEntry 7 }

-- {COLUMN} 1.3.6.1.4.1.248.32.18.1.3.36.1.1.8
hmStatusWlanInterpointsAccesspointListEntryThroughput OBJECT-TYPE
    SYNTAX     DisplayString (SIZE(0..255))
    MAX-ACCESS read-only
    STATUS     current
    DESCRIPTION
            "-- empty --"
    ::= { hmStatusWlanInterpointsAccesspointListEntry 8 }

-- {COLUMN} 1.3.6.1.4.1.248.32.18.1.3.36.1.1.12
hmStatusWlanInterpointsAccesspointListEntryKeyingState OBJECT-TYPE
    SYNTAX     INTEGER {
                  eIdle (0),
                  ePending (1),
                  eDone (2)
            }
    MAX-ACCESS read-only
    STATUS     current
    DESCRIPTION
            "-- empty --"
    ::= { hmStatusWlanInterpointsAccesspointListEntry 12 }

-- {COLUMN} 1.3.6.1.4.1.248.32.18.1.3.36.1.1.13
hmStatusWlanInterpointsAccesspointListEntryRxPhySignal OBJECT-TYPE
    SYNTAX     Integer32 (0..65535)
    MAX-ACCESS read-only
    STATUS     current
    DESCRIPTION
            "-- empty --"
    ::= { hmStatusWlanInterpointsAccesspointListEntry 13 }

-- {COLUMN} 1.3.6.1.4.1.248.32.18.1.3.36.1.1.14
hmStatusWlanInterpointsAccesspointListEntryLinkPhySignal OBJECT-TYPE
    SYNTAX     Integer32 (0..65535)
    MAX-ACCESS read-only
    STATUS     current
    DESCRIPTION
            "-- empty --"
    ::= { hmStatusWlanInterpointsAccesspointListEntry 14 }

-- {COLUMN} 1.3.6.1.4.1.248.32.18.1.3.36.1.1.15
hmStatusWlanInterpointsAccesspointListEntryIdentification OBJECT-TYPE
    SYNTAX     DisplayString (SIZE(0..24))
    MAX-ACCESS read-only
    STATUS     current
    DESCRIPTION
            "-- empty --"
    ::= { hmStatusWlanInterpointsAccesspointListEntry 15 }

-- {COLUMN} 1.3.6.1.4.1.248.32.18.1.3.36.1.1.16
hmStatusWlanInterpointsAccesspointListEntryTxRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51)
            }
    MAX-ACCESS read-only
    STATUS     current
    DESCRIPTION
            "-- empty --"
    ::= { hmStatusWlanInterpointsAccesspointListEntry 16 }

-- {COLUMN} 1.3.6.1.4.1.248.32.18.1.3.36.1.1.17
hmStatusWlanInterpointsAccesspointListEntryMaxThroughput OBJECT-TYPE
    SYNTAX     DisplayString (SIZE(0..255))
    MAX-ACCESS read-only
    STATUS     current
    DESCRIPTION
            "-- empty --"
    ::= { hmStatusWlanInterpointsAccesspointListEntry 17 }

-- {COLUMN} 1.3.6.1.4.1.248.32.18.1.3.36.1.1.19
hmStatusWlanInterpointsAccesspointListEntryBytesThroughput OBJECT-TYPE
    SYNTAX     Integer32 (0..2147483647)
    MAX-ACCESS read-only
    STATUS     current
    DESCRIPTION
            "-- empty --"
    ::= { hmStatusWlanInterpointsAccesspointListEntry 19 }

-- {COLUMN} 1.3.6.1.4.1.248.32.18.1.3.36.1.1.20
hmStatusWlanInterpointsAccesspointListEntryBytesMaxThroughput OBJECT-TYPE
    SYNTAX     Integer32 (0..2147483647)
    MAX-ACCESS read-only
    STATUS     current
    DESCRIPTION
            "-- empty --"
    ::= { hmStatusWlanInterpointsAccesspointListEntry 20 }

-- {COLUMN} 1.3.6.1.4.1.248.32.18.1.3.36.1.1.21
hmStatusWlanInterpointsAccesspointListEntryWpaVersion OBJECT-TYPE
    SYNTAX     INTEGER {
                  eNone (0),
                  eWpa1 (1),
                  eWpa2 (2)
            }
    MAX-ACCESS read-only
    STATUS     current
    DESCRIPTION
            "-- empty --"
    ::= { hmStatusWlanInterpointsAccesspointListEntry 21 }

-- {COLUMN} 1.3.6.1.4.1.248.32.18.1.3.36.1.1.22
hmStatusWlanInterpointsAccesspointListEntryTxLimit OBJECT-TYPE
    SYNTAX     Integer32 (0..2147483647)
    MAX-ACCESS read-only
    STATUS     current
    DESCRIPTION
            "-- empty --"
    ::= { hmStatusWlanInterpointsAccesspointListEntry 22 }

-- {COLUMN} 1.3.6.1.4.1.248.32.18.1.3.36.1.1.23
hmStatusWlanInterpointsAccesspointListEntryRxLimit OBJECT-TYPE
    SYNTAX     Integer32 (0..2147483647)
    MAX-ACCESS read-only
    STATUS     current
    DESCRIPTION
            "-- empty --"
    ::= { hmStatusWlanInterpointsAccesspointListEntry 23 }

-- {COLUMN} 1.3.6.1.4.1.248.32.18.1.3.36.1.1.24
hmStatusWlanInterpointsAccesspointListEntryKeyHandshakeRole OBJECT-TYPE
    SYNTAX     INTEGER {
                  eNone (0),
                  eSupplicant (1),
                  eAuthenticator (2)
            }
    MAX-ACCESS read-only
    STATUS     current
    DESCRIPTION
            "-- empty --"
    ::= { hmStatusWlanInterpointsAccesspointListEntry 24 }

-- {COLUMN} 1.3.6.1.4.1.248.32.18.1.3.36.1.1.25
hmStatusWlanInterpointsAccesspointListEntryTxPackets OBJECT-TYPE
    SYNTAX     Integer32 (0..2147483647)
    MAX-ACCESS read-only
    STATUS     current
    DESCRIPTION
            "-- empty --"
    ::= { hmStatusWlanInterpointsAccesspointListEntry 25 }

-- {COLUMN} 1.3.6.1.4.1.248.32.18.1.3.36.1.1.26
hmStatusWlanInterpointsAccesspointListEntryRxPackets OBJECT-TYPE
    SYNTAX     Integer32 (0..2147483647)
    MAX-ACCESS read-only
    STATUS     current
    DESCRIPTION
            "-- empty --"
    ::= { hmStatusWlanInterpointsAccesspointListEntry 26 }

-- {COLUMN} 1.3.6.1.4.1.248.32.18.1.3.36.1.1.27
hmStatusWlanInterpointsAccesspointListEntryQos OBJECT-TYPE
    SYNTAX     INTEGER {
                  eNo (0),
                  eYes (1)
            }
    MAX-ACCESS read-only
    STATUS     current
    DESCRIPTION
            "-- empty --"
    ::= { hmStatusWlanInterpointsAccesspointListEntry 27 }

-- {COLUMN} 1.3.6.1.4.1.248.32.18.1.3.36.1.1.28
hmStatusWlanInterpointsAccesspointListEntryInterpointPeerName OBJECT-TYPE
    SYNTAX     DisplayString (SIZE(0..24))
    MAX-ACCESS read-only
    STATUS     current
    DESCRIPTION
            "-- empty --"
    ::= { hmStatusWlanInterpointsAccesspointListEntry 28 }

-- {COLUMN} 1.3.6.1.4.1.248.32.18.1.3.36.1.1.29
hmStatusWlanInterpointsAccesspointListEntryMaxAMsduLen OBJECT-TYPE
    SYNTAX     Integer32 (0..2147483647)
    MAX-ACCESS read-only
    STATUS     current
    DESCRIPTION
            "-- empty --"
    ::= { hmStatusWlanInterpointsAccesspointListEntry 29 }

-- {COLUMN} 1.3.6.1.4.1.248.32.18.1.3.36.1.1.30
hmStatusWlanInterpointsAccesspointListEntryMaxAMpduLen OBJECT-TYPE
    SYNTAX     Integer32 (0..2147483647)
    MAX-ACCESS read-only
    STATUS     current
    DESCRIPTION
            "-- empty --"
    ::= { hmStatusWlanInterpointsAccesspointListEntry 30 }

-- {COLUMN} 1.3.6.1.4.1.248.32.18.1.3.36.1.1.31
hmStatusWlanInterpointsAccesspointListEntry40mhzMode OBJECT-TYPE
    SYNTAX     INTEGER {
                  eNo (0),
                  eYes (1)
            }
    MAX-ACCESS read-only
    STATUS     current
    DESCRIPTION
            "-- empty --"
    ::= { hmStatusWlanInterpointsAccesspointListEntry 31 }

-- {COLUMN} 1.3.6.1.4.1.248.32.18.1.3.36.1.1.32
hmStatusWlanInterpointsAccesspointListEntryShortPreamble OBJECT-TYPE
    SYNTAX     INTEGER {
                  eNo (0),
                  eYes (1)
            }
    MAX-ACCESS read-only
    STATUS     current
    DESCRIPTION
            "-- empty --"
    ::= { hmStatusWlanInterpointsAccesspointListEntry 32 }

-- {COLUMN} 1.3.6.1.4.1.248.32.18.1.3.36.1.1.33
hmStatusWlanInterpointsAccesspointListEntryShortGuardInterval OBJECT-TYPE
    SYNTAX     INTEGER {
                  eNo (0),
                  e20mhz (1),
                  e40mhz (2),
                  e2040mhz (3)
            }
    MAX-ACCESS read-only
    STATUS     current
    DESCRIPTION
            "-- empty --"
    ::= { hmStatusWlanInterpointsAccesspointListEntry 33 }

-- {COLUMN} 1.3.6.1.4.1.248.32.18.1.3.36.1.1.34
hmStatusWlanInterpointsAccesspointListEntryEffTxRate OBJECT-TYPE
    SYNTAX     Integer32 (0..2147483647)
    MAX-ACCESS read-only
    STATUS     current
    DESCRIPTION
            "-- empty --"
    ::= { hmStatusWlanInterpointsAccesspointListEntry 34 }

-- {COLUMN} 1.3.6.1.4.1.248.32.18.1.3.36.1.1.35
hmStatusWlanInterpointsAccesspointListEntryEffRxRate OBJECT-TYPE
    SYNTAX     Integer32 (0..2147483647)
    MAX-ACCESS read-only
    STATUS     current
    DESCRIPTION
            "-- empty --"
    ::= { hmStatusWlanInterpointsAccesspointListEntry 35 }

-- {COLUMN} 1.3.6.1.4.1.248.32.18.1.3.36.1.1.36
hmStatusWlanInterpointsAccesspointListEntryKeyType OBJECT-TYPE
    SYNTAX     INTEGER {
                  eNone (0),
                  eUnknown (1),
                  eWep40Bits (5),
                  eWep104Bits (13),
                  eWep128Bits (16),
                  eTkip (64),
                  eAesOcb (65),
                  eAesCcm (66),
                  eBip (68)
            }
    MAX-ACCESS read-only
    STATUS     current
    DESCRIPTION
            "-- empty --"
    ::= { hmStatusWlanInterpointsAccesspointListEntry 36 }

-- {COLUMN} 1.3.6.1.4.1.248.32.18.1.3.36.1.1.37
hmStatusWlanInterpointsAccesspointListEntryTxErrors OBJECT-TYPE
    SYNTAX     Integer32 (0..2147483647)
    MAX-ACCESS read-only
    STATUS     current
    DESCRIPTION
            "-- empty --"
    ::= { hmStatusWlanInterpointsAccesspointListEntry 37 }

-- {COLUMN} 1.3.6.1.4.1.248.32.18.1.3.36.1.1.38
hmStatusWlanInterpointsAccesspointListEntryTotalRetries OBJECT-TYPE
    SYNTAX     Integer32 (0..2147483647)
    MAX-ACCESS read-only
    STATUS     current
    DESCRIPTION
            "-- empty --"
    ::= { hmStatusWlanInterpointsAccesspointListEntry 38 }

-- {COLUMN} 1.3.6.1.4.1.248.32.18.1.3.36.1.1.39
hmStatusWlanInterpointsAccesspointListEntryAlarmState OBJECT-TYPE
    SYNTAX     BITS {
                  eNo (0),
                  eTxErrors (29),
                  eTotalRetries (30),
                  ePhySignal (31)
            }
    MAX-ACCESS read-only
    STATUS     current
    DESCRIPTION
            "-- empty --"
    ::= { hmStatusWlanInterpointsAccesspointListEntry 39 }

-- {COLUMN} 1.3.6.1.4.1.248.32.18.1.3.36.1.1.40
hmStatusWlanInterpointsAccesspointListEntryLinkActive OBJECT-TYPE
    SYNTAX     INTEGER {
                  eNo (0),
                  eYes (1)
            }
    MAX-ACCESS read-only
    STATUS     current
    DESCRIPTION
            "-- empty --"
    ::= { hmStatusWlanInterpointsAccesspointListEntry 40 }

-- {COLUMN} 1.3.6.1.4.1.248.32.18.1.3.36.1.1.41
hmStatusWlanInterpointsAccesspointListEntryRxStbc OBJECT-TYPE
    SYNTAX     INTEGER {
                  eNone (0),
                  eOne (1),
                  eTwo (2),
                  eThree (3)
            }
    MAX-ACCESS read-only
    STATUS     current
    DESCRIPTION
            "-- empty --"
    ::= { hmStatusWlanInterpointsAccesspointListEntry 41 }

-- {COLUMN} 1.3.6.1.4.1.248.32.18.1.3.36.1.1.42
hmStatusWlanInterpointsAccesspointListEntryLdpc OBJECT-TYPE
    SYNTAX     INTEGER {
                  eNo (0),
                  eYes (1)
            }
    MAX-ACCESS read-only
    STATUS     current
    DESCRIPTION
            "-- empty --"
    ::= { hmStatusWlanInterpointsAccesspointListEntry 42 }

-- {COLUMN} 1.3.6.1.4.1.248.32.18.1.3.36.1.1.43
hmStatusWlanInterpointsAccesspointListEntryRemoteStatus OBJECT-TYPE
    SYNTAX     INTEGER {
                  eUnknown (0),
                  eNotOk (1),
                  eOk (2)
            }
    MAX-ACCESS read-only
    STATUS     current
    DESCRIPTION
            "-- empty --"
    ::= { hmStatusWlanInterpointsAccesspointListEntry 43 }

-- {COLUMN} 1.3.6.1.4.1.248.32.18.1.3.36.1.1.44
hmStatusWlanInterpointsAccesspointListEntryWpa2KeyManagement OBJECT-TYPE
    SYNTAX     INTEGER {
                  eStandard (0),
                  eFastRoaming (1),
                  eSha256 (2),
                  eNone (255)
            }
    MAX-ACCESS read-only
    STATUS     current
    DESCRIPTION
            "-- empty --"
    ::= { hmStatusWlanInterpointsAccesspointListEntry 44 }

-- {COLUMN} 1.3.6.1.4.1.248.32.18.1.3.36.1.1.45
hmStatusWlanInterpointsAccesspointListEntrySGIMask OBJECT-TYPE
    SYNTAX     BITS {
                  eNo (0),
                  e160mhz (28),
                  e80mhz (29),
                  e40mhz (30),
                  e20mhz (31)
            }
    MAX-ACCESS read-only
    STATUS     current
    DESCRIPTION
            "Bit mask of short guard interval support per-CBW"
    ::= { hmStatusWlanInterpointsAccesspointListEntry 45 }

-- {COLUMN} 1.3.6.1.4.1.248.32.18.1.3.36.1.1.46
hmStatusWlanInterpointsAccesspointListEntryChannelBandwidths OBJECT-TYPE
    SYNTAX     BITS {
                  eT40mhz (26),
                  e80Plus80mhz (27),
                  e160mhz (28),
                  e80mhz (29),
                  e40mhz (30),
                  e20mhz (31)
            }
    MAX-ACCESS read-only
    STATUS     current
    DESCRIPTION
            "-- empty --"
    ::= { hmStatusWlanInterpointsAccesspointListEntry 46 }

-- {COLUMN} 1.3.6.1.4.1.248.32.18.1.3.36.1.1.47
hmStatusWlanInterpointsAccesspointListEntryProtMgmtFrames OBJECT-TYPE
    SYNTAX     INTEGER {
                  eNo (0),
                  eYes (1)
            }
    MAX-ACCESS read-only
    STATUS     current
    DESCRIPTION
            "-- empty --"
    ::= { hmStatusWlanInterpointsAccesspointListEntry 47 }

-- {COLUMN} 1.3.6.1.4.1.248.32.18.1.3.36.1.1.48
hmStatusWlanInterpointsAccesspointListEntryRxStbcHt OBJECT-TYPE
    SYNTAX     INTEGER {
                  eNone (0),
                  eOne (1),
                  eTwo (2),
                  eThree (3)
            }
    MAX-ACCESS read-only
    STATUS     current
    DESCRIPTION
            "-- empty --"
    ::= { hmStatusWlanInterpointsAccesspointListEntry 48 }

-- {COLUMN} 1.3.6.1.4.1.248.32.18.1.3.36.1.1.49
hmStatusWlanInterpointsAccesspointListEntryRxStbcVht OBJECT-TYPE
    SYNTAX     INTEGER {
                  eNone (0),
                  eOne (1),
                  eTwo (2),
                  eThree (3),
                  eFour (4),
                  eFive (5),
                  eSix (6),
                  eSeven (7)
            }
    MAX-ACCESS read-only
    STATUS     current
    DESCRIPTION
            "-- empty --"
    ::= { hmStatusWlanInterpointsAccesspointListEntry 49 }

-- {COLUMN} 1.3.6.1.4.1.248.32.18.1.3.36.1.1.50
hmStatusWlanInterpointsAccesspointListEntryLDPCMask OBJECT-TYPE
    SYNTAX     BITS {
                  eVht (30),
                  eHt (31)
            }
    MAX-ACCESS read-only
    STATUS     current
    DESCRIPTION
            "Bit mask of LDPC support per-PHY-Type"
    ::= { hmStatusWlanInterpointsAccesspointListEntry 50 }

-- {COLUMN} 1.3.6.1.4.1.248.32.18.1.3.36.1.1.51
hmStatusWlanInterpointsAccesspointListEntryOperationMode OBJECT-TYPE
    SYNTAX     INTEGER {
                  eUnknown (0),
                  e11b (1),
                  e11g (2),
                  e11a (3),
                  e11n (4)
            }
    MAX-ACCESS read-only
    STATUS     current
    DESCRIPTION
            "-- empty --"
    ::= { hmStatusWlanInterpointsAccesspointListEntry 51 }

-- {COLUMN} 1.3.6.1.4.1.248.32.18.1.3.36.1.1.248
hmStatusWlanInterpointsAccesspointListEntryC2cIdentifier OBJECT-TYPE
    SYNTAX     DisplayString (SIZE(0..24))
    MAX-ACCESS read-only
    STATUS     current
    DESCRIPTION
            "-- empty --"
    ::= { hmStatusWlanInterpointsAccesspointListEntry 248 }

-- {TABLE} 1.3.6.1.4.1.248.32.18.1.3.36.3
hmStatusWlanInterpointsKeyListTable OBJECT-TYPE
    SYNTAX     SEQUENCE OF HmStatusWlanInterpointsKeyListEntry
    MAX-ACCESS not-accessible
    STATUS     current
    DESCRIPTION
            "-- empty --"
    ::= { hmStatusWlanInterpoints 3 }

-- {ROW} 1.3.6.1.4.1.248.32.18.1.3.36.3.1
hmStatusWlanInterpointsKeyListEntry OBJECT-TYPE
    SYNTAX     HmStatusWlanInterpointsKeyListEntry
    MAX-ACCESS not-accessible
    STATUS     current
    DESCRIPTION
            ""
    INDEX {
            hmStatusWlanInterpointsKeyListEntryIndex
          }
    ::= { hmStatusWlanInterpointsKeyListTable 1 }

HmStatusWlanInterpointsKeyListEntry ::= SEQUENCE {
            hmStatusWlanInterpointsKeyListEntryIndex INTEGER,
            hmStatusWlanInterpointsKeyListEntrySource INTEGER,
            hmStatusWlanInterpointsKeyListEntryKeyType INTEGER,
            hmStatusWlanInterpointsKeyListEntryKeyValue DisplayString,
            hmStatusWlanInterpointsKeyListEntryTsc DisplayString,
            hmStatusWlanInterpointsKeyListEntryAge Integer32,
            hmStatusWlanInterpointsKeyListEntryIvSequenceErrors Integer32,
            hmStatusWlanInterpointsKeyListEntryRscBe DisplayString,
            hmStatusWlanInterpointsKeyListEntryRscBk DisplayString,
            hmStatusWlanInterpointsKeyListEntryRscEe DisplayString,
            hmStatusWlanInterpointsKeyListEntryRscCl DisplayString,
            hmStatusWlanInterpointsKeyListEntryRscVi DisplayString,
            hmStatusWlanInterpointsKeyListEntryRscVo DisplayString,
            hmStatusWlanInterpointsKeyListEntryRscNc DisplayString,
            hmStatusWlanInterpointsKeyListEntryRscMgmt DisplayString
    }

-- {COLUMN} 1.3.6.1.4.1.248.32.18.1.3.36.3.1.1
hmStatusWlanInterpointsKeyListEntryIndex OBJECT-TYPE
    SYNTAX     INTEGER {
                  eP2p11 (1),
                  eP2p12 (2),
                  eP2p13 (3),
                  eP2p14 (4),
                  eP2p15 (5),
                  eP2p16 (6),
                  eP2p21 (7),
                  eP2p22 (8),
                  eP2p23 (9),
                  eP2p24 (10),
                  eP2p25 (11),
                  eP2p26 (12),
                  eP2p17 (32),
                  eP2p18 (33),
                  eP2p19 (34),
                  eP2p110 (35),
                  eP2p111 (36),
                  eP2p112 (37),
                  eP2p113 (38),
                  eP2p114 (39),
                  eP2p115 (40),
                  eP2p116 (41),
                  eP2p27 (64),
                  eP2p28 (65),
                  eP2p29 (66),
                  eP2p210 (67),
                  eP2p211 (68),
                  eP2p212 (69),
                  eP2p213 (70),
                  eP2p214 (71),
                  eP2p215 (72),
                  eP2p216 (73)
            }
    MAX-ACCESS read-only
    STATUS     current
    DESCRIPTION
            "-- empty --"
    ::= { hmStatusWlanInterpointsKeyListEntry 1 }

-- {COLUMN} 1.3.6.1.4.1.248.32.18.1.3.36.3.1.2
hmStatusWlanInterpointsKeyListEntrySource OBJECT-TYPE
    SYNTAX     INTEGER {
                  eNone (0),
                  eStatic (1),
                  eDynamic (2)
            }
    MAX-ACCESS read-only
    STATUS     current
    DESCRIPTION
            "-- empty --"
    ::= { hmStatusWlanInterpointsKeyListEntry 2 }

-- {COLUMN} 1.3.6.1.4.1.248.32.18.1.3.36.3.1.3
hmStatusWlanInterpointsKeyListEntryKeyType OBJECT-TYPE
    SYNTAX     INTEGER {
                  eNone (0),
                  eUnknown (1),
                  eWep40Bits (5),
                  eWep104Bits (13),
                  eWep128Bits (16),
                  eTkip (64),
                  eAesOcb (65),
                  eAesCcm (66),
                  eBip (68)
            }
    MAX-ACCESS read-only
    STATUS     current
    DESCRIPTION
            "-- empty --"
    ::= { hmStatusWlanInterpointsKeyListEntry 3 }

-- {COLUMN} 1.3.6.1.4.1.248.32.18.1.3.36.3.1.4
hmStatusWlanInterpointsKeyListEntryKeyValue OBJECT-TYPE
    SYNTAX     DisplayString (SIZE(0..255))
    MAX-ACCESS read-only
    STATUS     current
    DESCRIPTION
            "-- empty --"
    ::= { hmStatusWlanInterpointsKeyListEntry 4 }

-- {COLUMN} 1.3.6.1.4.1.248.32.18.1.3.36.3.1.5
hmStatusWlanInterpointsKeyListEntryTsc OBJECT-TYPE
    SYNTAX     DisplayString (SIZE(0..255))
    MAX-ACCESS read-only
    STATUS     current
    DESCRIPTION
            "-- empty --"
    ::= { hmStatusWlanInterpointsKeyListEntry 5 }

-- {COLUMN} 1.3.6.1.4.1.248.32.18.1.3.36.3.1.7
hmStatusWlanInterpointsKeyListEntryAge OBJECT-TYPE
    SYNTAX     Integer32 (0..2147483647)
    MAX-ACCESS read-only
    STATUS     current
    DESCRIPTION
            "-- empty --"
    ::= { hmStatusWlanInterpointsKeyListEntry 7 }

-- {COLUMN} 1.3.6.1.4.1.248.32.18.1.3.36.3.1.8
hmStatusWlanInterpointsKeyListEntryIvSequenceErrors OBJECT-TYPE
    SYNTAX     Integer32 (0..2147483647)
    MAX-ACCESS read-only
    STATUS     current
    DESCRIPTION
            "-- empty --"
    ::= { hmStatusWlanInterpointsKeyListEntry 8 }

-- {COLUMN} 1.3.6.1.4.1.248.32.18.1.3.36.3.1.16
hmStatusWlanInterpointsKeyListEntryRscBe OBJECT-TYPE
    SYNTAX     DisplayString (SIZE(0..255))
    MAX-ACCESS read-only
    STATUS     current
    DESCRIPTION
            "-- empty --"
    ::= { hmStatusWlanInterpointsKeyListEntry 16 }

-- {COLUMN} 1.3.6.1.4.1.248.32.18.1.3.36.3.1.17
hmStatusWlanInterpointsKeyListEntryRscBk OBJECT-TYPE
    SYNTAX     DisplayString (SIZE(0..255))
    MAX-ACCESS read-only
    STATUS     current
    DESCRIPTION
            "-- empty --"
    ::= { hmStatusWlanInterpointsKeyListEntry 17 }

-- {COLUMN} 1.3.6.1.4.1.248.32.18.1.3.36.3.1.19
hmStatusWlanInterpointsKeyListEntryRscEe OBJECT-TYPE
    SYNTAX     DisplayString (SIZE(0..255))
    MAX-ACCESS read-only
    STATUS     current
    DESCRIPTION
            "-- empty --"
    ::= { hmStatusWlanInterpointsKeyListEntry 19 }

-- {COLUMN} 1.3.6.1.4.1.248.32.18.1.3.36.3.1.20
hmStatusWlanInterpointsKeyListEntryRscCl OBJECT-TYPE
    SYNTAX     DisplayString (SIZE(0..255))
    MAX-ACCESS read-only
    STATUS     current
    DESCRIPTION
            "-- empty --"
    ::= { hmStatusWlanInterpointsKeyListEntry 20 }

-- {COLUMN} 1.3.6.1.4.1.248.32.18.1.3.36.3.1.21
hmStatusWlanInterpointsKeyListEntryRscVi OBJECT-TYPE
    SYNTAX     DisplayString (SIZE(0..255))
    MAX-ACCESS read-only
    STATUS     current
    DESCRIPTION
            "-- empty --"
    ::= { hmStatusWlanInterpointsKeyListEntry 21 }

-- {COLUMN} 1.3.6.1.4.1.248.32.18.1.3.36.3.1.22
hmStatusWlanInterpointsKeyListEntryRscVo OBJECT-TYPE
    SYNTAX     DisplayString (SIZE(0..255))
    MAX-ACCESS read-only
    STATUS     current
    DESCRIPTION
            "-- empty --"
    ::= { hmStatusWlanInterpointsKeyListEntry 22 }

-- {COLUMN} 1.3.6.1.4.1.248.32.18.1.3.36.3.1.23
hmStatusWlanInterpointsKeyListEntryRscNc OBJECT-TYPE
    SYNTAX     DisplayString (SIZE(0..255))
    MAX-ACCESS read-only
    STATUS     current
    DESCRIPTION
            "-- empty --"
    ::= { hmStatusWlanInterpointsKeyListEntry 23 }

-- {COLUMN} 1.3.6.1.4.1.248.32.18.1.3.36.3.1.24
hmStatusWlanInterpointsKeyListEntryRscMgmt OBJECT-TYPE
    SYNTAX     DisplayString (SIZE(0..255))
    MAX-ACCESS read-only
    STATUS     current
    DESCRIPTION
            "-- empty --"
    ::= { hmStatusWlanInterpointsKeyListEntry 24 }

-- {TABLE} 1.3.6.1.4.1.248.32.18.1.3.36.248
hmStatusWlanInterpointsC2cNeighborsListTable OBJECT-TYPE
    SYNTAX     SEQUENCE OF HmStatusWlanInterpointsC2cNeighborsListEntry
    MAX-ACCESS not-accessible
    STATUS     current
    DESCRIPTION
            "-- empty --"
    ::= { hmStatusWlanInterpoints 248 }

-- {ROW} 1.3.6.1.4.1.248.32.18.1.3.36.248.1
hmStatusWlanInterpointsC2cNeighborsListEntry OBJECT-TYPE
    SYNTAX     HmStatusWlanInterpointsC2cNeighborsListEntry
    MAX-ACCESS not-accessible
    STATUS     current
    DESCRIPTION
            ""
    INDEX {
            hmStatusWlanInterpointsC2cNeighborsListEntryMacAddress
          }
    ::= { hmStatusWlanInterpointsC2cNeighborsListTable 1 }

HmStatusWlanInterpointsC2cNeighborsListEntry ::= SEQUENCE {
            hmStatusWlanInterpointsC2cNeighborsListEntryMacAddress MacAddress,
            hmStatusWlanInterpointsC2cNeighborsListEntryInterface INTEGER,
            hmStatusWlanInterpointsC2cNeighborsListEntryRadioBand INTEGER,
            hmStatusWlanInterpointsC2cNeighborsListEntryRadioChannel Integer32,
            hmStatusWlanInterpointsC2cNeighborsListEntryPhySignal Integer32,
            hmStatusWlanInterpointsC2cNeighborsListEntrySignalLevel Integer32,
            hmStatusWlanInterpointsC2cNeighborsListEntryAge Integer32,
            hmStatusWlanInterpointsC2cNeighborsListEntryRate INTEGER,
            hmStatusWlanInterpointsC2cNeighborsListEntryEffRate Integer32,
            hmStatusWlanInterpointsC2cNeighborsListEntryNoiseLevel Integer32,
            hmStatusWlanInterpointsC2cNeighborsListEntryLoad Integer32,
            hmStatusWlanInterpointsC2cNeighborsListEntryC2cIdentifier DisplayString,
            hmStatusWlanInterpointsC2cNeighborsListEntryStatus INTEGER
    }

-- {COLUMN} 1.3.6.1.4.1.248.32.18.1.3.36.248.1.1
hmStatusWlanInterpointsC2cNeighborsListEntryMacAddress OBJECT-TYPE
    SYNTAX     MacAddress
    MAX-ACCESS read-only
    STATUS     current
    DESCRIPTION
            "-- empty --"
    ::= { hmStatusWlanInterpointsC2cNeighborsListEntry 1 }

-- {COLUMN} 1.3.6.1.4.1.248.32.18.1.3.36.248.1.2
hmStatusWlanInterpointsC2cNeighborsListEntryInterface OBJECT-TYPE
    SYNTAX     INTEGER {
                  eWlan1 (0),
                  eWlan2 (1),
                  eWlan3 (2),
                  eWlan4 (3)
            }
    MAX-ACCESS read-only
    STATUS     current
    DESCRIPTION
            "-- empty --"
    ::= { hmStatusWlanInterpointsC2cNeighborsListEntry 2 }

-- {COLUMN} 1.3.6.1.4.1.248.32.18.1.3.36.248.1.3
hmStatusWlanInterpointsC2cNeighborsListEntryRadioBand OBJECT-TYPE
    SYNTAX     INTEGER {
                  eUnknown (0),
                  e24ghz (1),
                  e5ghz (2)
            }
    MAX-ACCESS read-only
    STATUS     current
    DESCRIPTION
            "-- empty --"
    ::= { hmStatusWlanInterpointsC2cNeighborsListEntry 3 }

-- {COLUMN} 1.3.6.1.4.1.248.32.18.1.3.36.248.1.4
hmStatusWlanInterpointsC2cNeighborsListEntryRadioChannel OBJECT-TYPE
    SYNTAX     Integer32 (0..255)
    MAX-ACCESS read-only
    STATUS     current
    DESCRIPTION
            "-- empty --"
    ::= { hmStatusWlanInterpointsC2cNeighborsListEntry 4 }

-- {COLUMN} 1.3.6.1.4.1.248.32.18.1.3.36.248.1.5
hmStatusWlanInterpointsC2cNeighborsListEntryPhySignal OBJECT-TYPE
    SYNTAX     Integer32 (0..65535)
    MAX-ACCESS read-only
    STATUS     current
    DESCRIPTION
            "-- empty --"
    ::= { hmStatusWlanInterpointsC2cNeighborsListEntry 5 }

-- {COLUMN} 1.3.6.1.4.1.248.32.18.1.3.36.248.1.6
hmStatusWlanInterpointsC2cNeighborsListEntrySignalLevel OBJECT-TYPE
    SYNTAX     Integer32 (-32768..32767)
    MAX-ACCESS read-only
    STATUS     current
    DESCRIPTION
            "-- empty --"
    ::= { hmStatusWlanInterpointsC2cNeighborsListEntry 6 }

-- {COLUMN} 1.3.6.1.4.1.248.32.18.1.3.36.248.1.7
hmStatusWlanInterpointsC2cNeighborsListEntryAge OBJECT-TYPE
    SYNTAX     Integer32 (0..2147483647)
    MAX-ACCESS read-only
    STATUS     current
    DESCRIPTION
            "-- empty --"
    ::= { hmStatusWlanInterpointsC2cNeighborsListEntry 7 }

-- {COLUMN} 1.3.6.1.4.1.248.32.18.1.3.36.248.1.8
hmStatusWlanInterpointsC2cNeighborsListEntryRate OBJECT-TYPE
    SYNTAX     INTEGER {
                  eUnknown (0),
                  e1M (1),
                  e2M (2),
                  e5M (3),
                  e5M5 (4),
                  e8M (5),
                  e11M (6),
                  e6M (12),
                  e9M (13),
                  e12M (14),
                  e18M (15),
                  e24M (16),
                  e36M (17),
                  e48M (18),
                  e54M (19),
                  eT12M (20),
                  eT18M (21),
                  eT24M (22),
                  eT36M (23),
                  eT48M (24),
                  eT72M (25),
                  eT96M (26),
                  eT108M (27),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eHT4S26M (52),
                  eHT4S52M (53),
                  eHT4S78M (54),
                  eHT4S104M (55),
                  eHT4S156M (56),
                  eHT4S208M (57),
                  eHT4S234M (58),
                  eHT4S260M (59),
                  eHTDUP6M (60),
                  eHtMcs33 (61),
                  eHtMcs34 (62),
                  eHtMcs35 (63),
                  eHtMcs36 (64),
                  eHtMcs37 (65),
                  eHtMcs38 (66),
                  eHtMcs39 (67),
                  eHtMcs40 (68),
                  eHtMcs41 (69),
                  eHtMcs42 (70),
                  eHtMcs43 (71),
                  eHtMcs44 (72),
                  eHtMcs45 (73),
                  eHtMcs46 (74),
                  eHtMcs47 (75),
                  eHtMcs48 (76),
                  eHtMcs49 (77),
                  eHtMcs50 (78),
                  eHtMcs51 (79),
                  eHtMcs52 (80),
                  eHtMcs53 (81),
                  eHtMcs54 (82),
                  eHtMcs55 (83),
                  eHtMcs56 (84),
                  eHtMcs57 (85),
                  eHtMcs58 (86),
                  eHtMcs59 (87),
                  eHtMcs60 (88),
                  eHtMcs61 (89),
                  eHtMcs62 (90),
                  eHtMcs63 (91),
                  eHtMcs64 (92),
                  eHtMcs65 (93),
                  eHtMcs66 (94),
                  eHtMcs67 (95),
                  eHtMcs68 (96),
                  eHtMcs69 (97),
                  eHtMcs70 (98),
                  eHtMcs71 (99),
                  eHtMcs72 (100),
                  eHtMcs73 (101),
                  eHtMcs74 (102),
                  eHtMcs75 (103),
                  eHtMcs76 (104),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            "-- empty --"
    ::= { hmStatusWlanInterpointsC2cNeighborsListEntry 8 }

-- {COLUMN} 1.3.6.1.4.1.248.32.18.1.3.36.248.1.9
hmStatusWlanInterpointsC2cNeighborsListEntryEffRate OBJECT-TYPE
    SYNTAX     Integer32 (0..2147483647)
    MAX-ACCESS read-only
    STATUS     current
    DESCRIPTION
            "-- empty --"
    ::= { hmStatusWlanInterpointsC2cNeighborsListEntry 9 }

-- {COLUMN} 1.3.6.1.4.1.248.32.18.1.3.36.248.1.10
hmStatusWlanInterpointsC2cNeighborsListEntryNoiseLevel OBJECT-TYPE
    SYNTAX     Integer32 (-128..127)
    MAX-ACCESS read-only
    STATUS     current
    DESCRIPTION
            "-- empty --"
    ::= { hmStatusWlanInterpointsC2cNeighborsListEntry 10 }

-- {COLUMN} 1.3.6.1.4.1.248.32.18.1.3.36.248.1.11
hmStatusWlanInterpointsC2cNeighborsListEntryLoad OBJECT-TYPE
    SYNTAX     Integer32 (0..255)
    MAX-ACCESS read-only
    STATUS     current
    DESCRIPTION
            "-- empty --"
    ::= { hmStatusWlanInterpointsC2cNeighborsListEntry 11 }

-- {COLUMN} 1.3.6.1.4.1.248.32.18.1.3.36.248.1.12
hmStatusWlanInterpointsC2cNeighborsListEntryC2cIdentifier OBJECT-TYPE
    SYNTAX     DisplayString (SIZE(0..24))
    MAX-ACCESS read-only
    STATUS     current
    DESCRIPTION
            "-- empty --"
    ::= { hmStatusWlanInterpointsC2cNeighborsListEntry 12 }

-- {COLUMN} 1.3.6.1.4.1.248.32.18.1.3.36.248.1.13
hmStatusWlanInterpointsC2cNeighborsListEntryStatus OBJECT-TYPE
    SYNTAX     INTEGER {
                  eDeclined (1),
                  eDiscovery (2),
                  eConnecting (3),
                  eActive (4)
            }
    MAX-ACCESS read-only
    STATUS     current
    DESCRIPTION
            "-- empty --"
    ::= { hmStatusWlanInterpointsC2cNeighborsListEntry 13 }

-- {SCALAR} 1.3.6.1.4.1.248.32.18.1.3.37
hmStatusWlanDeassocStation OBJECT-TYPE
    SYNTAX     DisplayString
    MAX-ACCESS read-write
    STATUS     current
    DESCRIPTION
            "-- empty --"
    ::= { hmStatusWlan 37 }

-- {TABLE} 1.3.6.1.4.1.248.32.18.1.3.38
hmStatusWlanIappTableTable OBJECT-TYPE
    SYNTAX     SEQUENCE OF HmStatusWlanIappTableEntry
    MAX-ACCESS not-accessible
    STATUS     current
    DESCRIPTION
            "-- empty --"
    ::= { hmStatusWlan 38 }

-- {ROW} 1.3.6.1.4.1.248.32.18.1.3.38.1
hmStatusWlanIappTableEntry OBJECT-TYPE
    SYNTAX     HmStatusWlanIappTableEntry
    MAX-ACCESS not-accessible
    STATUS     current
    DESCRIPTION
            ""
    INDEX {
            hmStatusWlanIappTableEntryBssid,
            hmStatusWlanIappTableEntryIpAddress,
            hmStatusWlanIappTableEntryNetworkName
          }
    ::= { hmStatusWlanIappTableTable 1 }

HmStatusWlanIappTableEntry ::= SEQUENCE {
            hmStatusWlanIappTableEntryIpAddress IpAddress,
            hmStatusWlanIappTableEntryBssid MacAddress,
            hmStatusWlanIappTableEntryTimer Integer32,
            hmStatusWlanIappTableEntryTimeout Integer32,
            hmStatusWlanIappTableEntryCapabilities BITS,
            hmStatusWlanIappTableEntryNetworkName DisplayString
    }

-- {COLUMN} 1.3.6.1.4.1.248.32.18.1.3.38.1.1
hmStatusWlanIappTableEntryIpAddress OBJECT-TYPE
    SYNTAX     IpAddress
    MAX-ACCESS read-only
    STATUS     current
    DESCRIPTION
            "-- empty --"
    ::= { hmStatusWlanIappTableEntry 1 }

-- {COLUMN} 1.3.6.1.4.1.248.32.18.1.3.38.1.2
hmStatusWlanIappTableEntryBssid OBJECT-TYPE
    SYNTAX     MacAddress
    MAX-ACCESS read-only
    STATUS     current
    DESCRIPTION
            "-- empty --"
    ::= { hmStatusWlanIappTableEntry 2 }

-- {COLUMN} 1.3.6.1.4.1.248.32.18.1.3.38.1.3
hmStatusWlanIappTableEntryTimer OBJECT-TYPE
    SYNTAX     Integer32 (0..65535)
    MAX-ACCESS read-only
    STATUS     current
    DESCRIPTION
            "-- empty --"
    ::= { hmStatusWlanIappTableEntry 3 }

-- {COLUMN} 1.3.6.1.4.1.248.32.18.1.3.38.1.4
hmStatusWlanIappTableEntryTimeout OBJECT-TYPE
    SYNTAX     Integer32 (0..65535)
    MAX-ACCESS read-only
    STATUS     current
    DESCRIPTION
            "-- empty --"
    ::= { hmStatusWlanIappTableEntry 4 }

-- {COLUMN} 1.3.6.1.4.1.248.32.18.1.3.38.1.5
hmStatusWlanIappTableEntryCapabilities OBJECT-TYPE
    SYNTAX     BITS {
                  eForward (1),
                  ePrivacy (2)
            }
    MAX-ACCESS read-only
    STATUS     current
    DESCRIPTION
            "-- empty --"
    ::= { hmStatusWlanIappTableEntry 5 }

-- {COLUMN} 1.3.6.1.4.1.248.32.18.1.3.38.1.6
hmStatusWlanIappTableEntryNetworkName OBJECT-TYPE
    SYNTAX     DisplayString (SIZE(0..16))
    MAX-ACCESS read-only
    STATUS     current
    DESCRIPTION
            "-- empty --"
    ::= { hmStatusWlanIappTableEntry 6 }

-- {TABLE} 1.3.6.1.4.1.248.32.18.1.3.40
hmStatusWlanForeignStationsTable OBJECT-TYPE
    SYNTAX     SEQUENCE OF HmStatusWlanForeignStationsEntry
    MAX-ACCESS not-accessible
    STATUS     current
    DESCRIPTION
            "-- empty --"
    ::= { hmStatusWlan 40 }

-- {ROW} 1.3.6.1.4.1.248.32.18.1.3.40.1
hmStatusWlanForeignStationsEntry OBJECT-TYPE
    SYNTAX     HmStatusWlanForeignStationsEntry
    MAX-ACCESS not-accessible
    STATUS     current
    DESCRIPTION
            ""
    INDEX {
            hmStatusWlanForeignStationsEntryMacAddress
          }
    ::= { hmStatusWlanForeignStationsTable 1 }

HmStatusWlanForeignStationsEntry ::= SEQUENCE {
            hmStatusWlanForeignStationsEntryMacAddress MacAddress,
            hmStatusWlanForeignStationsEntryBssid MacAddress,
            hmStatusWlanForeignStationsEntryNetworkName DisplayString
    }

-- {COLUMN} 1.3.6.1.4.1.248.32.18.1.3.40.1.1
hmStatusWlanForeignStationsEntryMacAddress OBJECT-TYPE
    SYNTAX     MacAddress
    MAX-ACCESS read-only
    STATUS     current
    DESCRIPTION
            "-- empty --"
    ::= { hmStatusWlanForeignStationsEntry 1 }

-- {COLUMN} 1.3.6.1.4.1.248.32.18.1.3.40.1.2
hmStatusWlanForeignStationsEntryBssid OBJECT-TYPE
    SYNTAX     MacAddress
    MAX-ACCESS read-only
    STATUS     current
    DESCRIPTION
            "-- empty --"
    ::= { hmStatusWlanForeignStationsEntry 2 }

-- {COLUMN} 1.3.6.1.4.1.248.32.18.1.3.40.1.3
hmStatusWlanForeignStationsEntryNetworkName OBJECT-TYPE
    SYNTAX     DisplayString (SIZE(0..255))
    MAX-ACCESS read-only
    STATUS     current
    DESCRIPTION
            "-- empty --"
    ::= { hmStatusWlanForeignStationsEntry 3 }

-- {TABLE} 1.3.6.1.4.1.248.32.18.1.3.41
hmStatusWlanGroupEncryptionKeysTable OBJECT-TYPE
    SYNTAX     SEQUENCE OF HmStatusWlanGroupEncryptionKeysEntry
    MAX-ACCESS not-accessible
    STATUS     current
    DESCRIPTION
            "-- empty --"
    ::= { hmStatusWlan 41 }

-- {ROW} 1.3.6.1.4.1.248.32.18.1.3.41.1
hmStatusWlanGroupEncryptionKeysEntry OBJECT-TYPE
    SYNTAX     HmStatusWlanGroupEncryptionKeysEntry
    MAX-ACCESS not-accessible
    STATUS     current
    DESCRIPTION
            ""
    INDEX {
            hmStatusWlanGroupEncryptionKeysEntryIndex
          }
    ::= { hmStatusWlanGroupEncryptionKeysTable 1 }

HmStatusWlanGroupEncryptionKeysEntry ::= SEQUENCE {
            hmStatusWlanGroupEncryptionKeysEntryIndex DisplayString,
            hmStatusWlanGroupEncryptionKeysEntrySource INTEGER,
            hmStatusWlanGroupEncryptionKeysEntryKeyType INTEGER,
            hmStatusWlanGroupEncryptionKeysEntryKeyValue DisplayString,
            hmStatusWlanGroupEncryptionKeysEntryTsc DisplayString,
            hmStatusWlanGroupEncryptionKeysEntryAge Integer32,
            hmStatusWlanGroupEncryptionKeysEntryIvSequenceErrors Integer32,
            hmStatusWlanGroupEncryptionKeysEntryRscBe DisplayString,
            hmStatusWlanGroupEncryptionKeysEntryRscBk DisplayString,
            hmStatusWlanGroupEncryptionKeysEntryRscEe DisplayString,
            hmStatusWlanGroupEncryptionKeysEntryRscCl DisplayString,
            hmStatusWlanGroupEncryptionKeysEntryRscVi DisplayString,
            hmStatusWlanGroupEncryptionKeysEntryRscVo DisplayString,
            hmStatusWlanGroupEncryptionKeysEntryRscNc DisplayString,
            hmStatusWlanGroupEncryptionKeysEntryRscMgmt DisplayString
    }

-- {COLUMN} 1.3.6.1.4.1.248.32.18.1.3.41.1.1
hmStatusWlanGroupEncryptionKeysEntryIndex OBJECT-TYPE
    SYNTAX     DisplayString (SIZE(0..255))
    MAX-ACCESS read-only
    STATUS     current
    DESCRIPTION
            "-- empty --"
    ::= { hmStatusWlanGroupEncryptionKeysEntry 1 }

-- {COLUMN} 1.3.6.1.4.1.248.32.18.1.3.41.1.2
hmStatusWlanGroupEncryptionKeysEntrySource OBJECT-TYPE
    SYNTAX     INTEGER {
                  eNone (0),
                  eStatic (1),
                  eDynamic (2)
            }
    MAX-ACCESS read-only
    STATUS     current
    DESCRIPTION
            "-- empty --"
    ::= { hmStatusWlanGroupEncryptionKeysEntry 2 }

-- {COLUMN} 1.3.6.1.4.1.248.32.18.1.3.41.1.3
hmStatusWlanGroupEncryptionKeysEntryKeyType OBJECT-TYPE
    SYNTAX     INTEGER {
                  eNone (0),
                  eUnknown (1),
                  eWep40Bits (5),
                  eWep104Bits (13),
                  eWep128Bits (16),
                  eTkip (64),
                  eAesOcb (65),
                  eAesCcm (66),
                  eBip (68)
            }
    MAX-ACCESS read-only
    STATUS     current
    DESCRIPTION
            "-- empty --"
    ::= { hmStatusWlanGroupEncryptionKeysEntry 3 }

-- {COLUMN} 1.3.6.1.4.1.248.32.18.1.3.41.1.4
hmStatusWlanGroupEncryptionKeysEntryKeyValue OBJECT-TYPE
    SYNTAX     DisplayString (SIZE(0..255))
    MAX-ACCESS read-only
    STATUS     current
    DESCRIPTION
            "-- empty --"
    ::= { hmStatusWlanGroupEncryptionKeysEntry 4 }

-- {COLUMN} 1.3.6.1.4.1.248.32.18.1.3.41.1.5
hmStatusWlanGroupEncryptionKeysEntryTsc OBJECT-TYPE
    SYNTAX     DisplayString (SIZE(0..255))
    MAX-ACCESS read-only
    STATUS     current
    DESCRIPTION
            "-- empty --"
    ::= { hmStatusWlanGroupEncryptionKeysEntry 5 }

-- {COLUMN} 1.3.6.1.4.1.248.32.18.1.3.41.1.7
hmStatusWlanGroupEncryptionKeysEntryAge OBJECT-TYPE
    SYNTAX     Integer32 (0..2147483647)
    MAX-ACCESS read-only
    STATUS     current
    DESCRIPTION
            "-- empty --"
    ::= { hmStatusWlanGroupEncryptionKeysEntry 7 }

-- {COLUMN} 1.3.6.1.4.1.248.32.18.1.3.41.1.8
hmStatusWlanGroupEncryptionKeysEntryIvSequenceErrors OBJECT-TYPE
    SYNTAX     Integer32 (0..2147483647)
    MAX-ACCESS read-only
    STATUS     current
    DESCRIPTION
            "-- empty --"
    ::= { hmStatusWlanGroupEncryptionKeysEntry 8 }

-- {COLUMN} 1.3.6.1.4.1.248.32.18.1.3.41.1.16
hmStatusWlanGroupEncryptionKeysEntryRscBe OBJECT-TYPE
    SYNTAX     DisplayString (SIZE(0..255))
    MAX-ACCESS read-only
    STATUS     current
    DESCRIPTION
            "-- empty --"
    ::= { hmStatusWlanGroupEncryptionKeysEntry 16 }

-- {COLUMN} 1.3.6.1.4.1.248.32.18.1.3.41.1.17
hmStatusWlanGroupEncryptionKeysEntryRscBk OBJECT-TYPE
    SYNTAX     DisplayString (SIZE(0..255))
    MAX-ACCESS read-only
    STATUS     current
    DESCRIPTION
            "-- empty --"
    ::= { hmStatusWlanGroupEncryptionKeysEntry 17 }

-- {COLUMN} 1.3.6.1.4.1.248.32.18.1.3.41.1.19
hmStatusWlanGroupEncryptionKeysEntryRscEe OBJECT-TYPE
    SYNTAX     DisplayString (SIZE(0..255))
    MAX-ACCESS read-only
    STATUS     current
    DESCRIPTION
            "-- empty --"
    ::= { hmStatusWlanGroupEncryptionKeysEntry 19 }

-- {COLUMN} 1.3.6.1.4.1.248.32.18.1.3.41.1.20
hmStatusWlanGroupEncryptionKeysEntryRscCl OBJECT-TYPE
    SYNTAX     DisplayString (SIZE(0..255))
    MAX-ACCESS read-only
    STATUS     current
    DESCRIPTION
            "-- empty --"
    ::= { hmStatusWlanGroupEncryptionKeysEntry 20 }

-- {COLUMN} 1.3.6.1.4.1.248.32.18.1.3.41.1.21
hmStatusWlanGroupEncryptionKeysEntryRscVi OBJECT-TYPE
    SYNTAX     DisplayString (SIZE(0..255))
    MAX-ACCESS read-only
    STATUS     current
    DESCRIPTION
            "-- empty --"
    ::= { hmStatusWlanGroupEncryptionKeysEntry 21 }

-- {COLUMN} 1.3.6.1.4.1.248.32.18.1.3.41.1.22
hmStatusWlanGroupEncryptionKeysEntryRscVo OBJECT-TYPE
    SYNTAX     DisplayString (SIZE(0..255))
    MAX-ACCESS read-only
    STATUS     current
    DESCRIPTION
            "-- empty --"
    ::= { hmStatusWlanGroupEncryptionKeysEntry 22 }

-- {COLUMN} 1.3.6.1.4.1.248.32.18.1.3.41.1.23
hmStatusWlanGroupEncryptionKeysEntryRscNc OBJECT-TYPE
    SYNTAX     DisplayString (SIZE(0..255))
    MAX-ACCESS read-only
    STATUS     current
    DESCRIPTION
            "-- empty --"
    ::= { hmStatusWlanGroupEncryptionKeysEntry 23 }

-- {COLUMN} 1.3.6.1.4.1.248.32.18.1.3.41.1.24
hmStatusWlanGroupEncryptionKeysEntryRscMgmt OBJECT-TYPE
    SYNTAX     DisplayString (SIZE(0..255))
    MAX-ACCESS read-only
    STATUS     current
    DESCRIPTION
            "-- empty --"
    ::= { hmStatusWlanGroupEncryptionKeysEntry 24 }

-- {TABLE} 1.3.6.1.4.1.248.32.18.1.3.42
hmStatusWlanChannelScanResultsTable OBJECT-TYPE
    SYNTAX     SEQUENCE OF HmStatusWlanChannelScanResultsEntry
    MAX-ACCESS not-accessible
    STATUS     current
    DESCRIPTION
            "-- empty --"
    ::= { hmStatusWlan 42 }

-- {ROW} 1.3.6.1.4.1.248.32.18.1.3.42.1
hmStatusWlanChannelScanResultsEntry OBJECT-TYPE
    SYNTAX     HmStatusWlanChannelScanResultsEntry
    MAX-ACCESS not-accessible
    STATUS     current
    DESCRIPTION
            ""
    INDEX {
            hmStatusWlanChannelScanResultsEntryRadioBand,
            hmStatusWlanChannelScanResultsEntryRadioChannel,
            hmStatusWlanChannelScanResultsEntryInterface
          }
    ::= { hmStatusWlanChannelScanResultsTable 1 }

HmStatusWlanChannelScanResultsEntry ::= SEQUENCE {
            hmStatusWlanChannelScanResultsEntryRadioChannel Integer32,
            hmStatusWlanChannelScanResultsEntryInterface INTEGER,
            hmStatusWlanChannelScanResultsEntryScanned INTEGER,
            hmStatusWlanChannelScanResultsEntryNoiseLevel Integer32,
            hmStatusWlanChannelScanResultsEntryNumBss Integer32,
            hmStatusWlanChannelScanResultsEntryRadarDetected INTEGER,
            hmStatusWlanChannelScanResultsEntry108mbpsMode INTEGER,
            hmStatusWlanChannelScanResultsEntryRadioBand INTEGER,
            hmStatusWlanChannelScanResultsEntryPulseCount Integer32,
            hmStatusWlanChannelScanResultsEntryRemTime Integer32,
            hmStatusWlanChannelScanResultsEntryDfsState INTEGER,
            hmStatusWlanChannelScanResultsEntryRadarPattern DisplayString,
            hmStatusWlanChannelScanResultsEntryDfsScheme INTEGER,
            hmStatusWlanChannelScanResultsEntryUsage BITS,
            hmStatusWlanChannelScanResultsEntryScanAge Integer32,
            hmStatusWlanChannelScanResultsEntryNonHtBss INTEGER,
            hmStatusWlanChannelScanResultsEntryNonHtBssAge Integer32,
            hmStatusWlanChannelScanResultsEntry40mIntolerantBss INTEGER,
            hmStatusWlanChannelScanResultsEntry40mIntolerantBssAge Integer32,
            hmStatusWlanChannelScanResultsEntry40mIntolerantBssReported INTEGER,
            hmStatusWlanChannelScanResultsEntry40mIntolerantBssReportedAge Integer32,
            hmStatusWlanChannelScanResultsEntryChannelBandwidth INTEGER,
            hmStatusWlanChannelScanResultsEntryBgscanPriority Integer32
    }

-- {COLUMN} 1.3.6.1.4.1.248.32.18.1.3.42.1.1
hmStatusWlanChannelScanResultsEntryRadioChannel OBJECT-TYPE
    SYNTAX     Integer32 (0..255)
    MAX-ACCESS read-only
    STATUS     current
    DESCRIPTION
            "-- empty --"
    ::= { hmStatusWlanChannelScanResultsEntry 1 }

-- {COLUMN} 1.3.6.1.4.1.248.32.18.1.3.42.1.2
hmStatusWlanChannelScanResultsEntryInterface OBJECT-TYPE
    SYNTAX     INTEGER {
                  eWlan1 (0),
                  eWlan2 (1),
                  eWlan3 (2),
                  eWlan4 (3)
            }
    MAX-ACCESS read-only
    STATUS     current
    DESCRIPTION
            "-- empty --"
    ::= { hmStatusWlanChannelScanResultsEntry 2 }

-- {COLUMN} 1.3.6.1.4.1.248.32.18.1.3.42.1.3
hmStatusWlanChannelScanResultsEntryScanned OBJECT-TYPE
    SYNTAX     INTEGER {
                  eNo (0),
                  eYes (1)
            }
    MAX-ACCESS read-only
    STATUS     current
    DESCRIPTION
            "-- empty --"
    ::= { hmStatusWlanChannelScanResultsEntry 3 }

-- {COLUMN} 1.3.6.1.4.1.248.32.18.1.3.42.1.4
hmStatusWlanChannelScanResultsEntryNoiseLevel OBJECT-TYPE
    SYNTAX     Integer32 (-128..127)
    MAX-ACCESS read-only
    STATUS     current
    DESCRIPTION
            "-- empty --"
    ::= { hmStatusWlanChannelScanResultsEntry 4 }

-- {COLUMN} 1.3.6.1.4.1.248.32.18.1.3.42.1.6
hmStatusWlanChannelScanResultsEntryNumBss OBJECT-TYPE
    SYNTAX     Integer32 (0..65535)
    MAX-ACCESS read-only
    STATUS     current
    DESCRIPTION
            "-- empty --"
    ::= { hmStatusWlanChannelScanResultsEntry 6 }

-- {COLUMN} 1.3.6.1.4.1.248.32.18.1.3.42.1.7
hmStatusWlanChannelScanResultsEntryRadarDetected OBJECT-TYPE
    SYNTAX     INTEGER {
                  eNo (0),
                  eYes (1)
            }
    MAX-ACCESS read-only
    STATUS     current
    DESCRIPTION
            "-- empty --"
    ::= { hmStatusWlanChannelScanResultsEntry 7 }

-- {COLUMN} 1.3.6.1.4.1.248.32.18.1.3.42.1.8
hmStatusWlanChannelScanResultsEntry108mbpsMode OBJECT-TYPE
    SYNTAX     INTEGER {
                  eNo (0),
                  eYes (1)
            }
    MAX-ACCESS read-only
    STATUS     current
    DESCRIPTION
            "-- empty --"
    ::= { hmStatusWlanChannelScanResultsEntry 8 }

-- {COLUMN} 1.3.6.1.4.1.248.32.18.1.3.42.1.9
hmStatusWlanChannelScanResultsEntryRadioBand OBJECT-TYPE
    SYNTAX     INTEGER {
                  eUnknown (0),
                  e24ghz (1),
                  e5ghz (2)
            }
    MAX-ACCESS read-only
    STATUS     current
    DESCRIPTION
            "-- empty --"
    ::= { hmStatusWlanChannelScanResultsEntry 9 }

-- {COLUMN} 1.3.6.1.4.1.248.32.18.1.3.42.1.10
hmStatusWlanChannelScanResultsEntryPulseCount OBJECT-TYPE
    SYNTAX     Integer32 (0..2147483647)
    MAX-ACCESS read-only
    STATUS     current
    DESCRIPTION
            "-- empty --"
    ::= { hmStatusWlanChannelScanResultsEntry 10 }

-- {COLUMN} 1.3.6.1.4.1.248.32.18.1.3.42.1.11
hmStatusWlanChannelScanResultsEntryRemTime OBJECT-TYPE
    SYNTAX     Integer32 (0..2147483647)
    MAX-ACCESS read-only
    STATUS     current
    DESCRIPTION
            "-- empty --"
    ::= { hmStatusWlanChannelScanResultsEntry 11 }

-- {COLUMN} 1.3.6.1.4.1.248.32.18.1.3.42.1.12
hmStatusWlanChannelScanResultsEntryDfsState OBJECT-TYPE
    SYNTAX     INTEGER {
                  eClear (0),
                  eBlocked (1),
                  eUnknown (2)
            }
    MAX-ACCESS read-only
    STATUS     current
    DESCRIPTION
            "-- empty --"
    ::= { hmStatusWlanChannelScanResultsEntry 12 }

-- {COLUMN} 1.3.6.1.4.1.248.32.18.1.3.42.1.13
hmStatusWlanChannelScanResultsEntryRadarPattern OBJECT-TYPE
    SYNTAX     DisplayString (SIZE(0..40))
    MAX-ACCESS read-only
    STATUS     current
    DESCRIPTION
            "-- empty --"
    ::= { hmStatusWlanChannelScanResultsEntry 13 }

-- {COLUMN} 1.3.6.1.4.1.248.32.18.1.3.42.1.14
hmStatusWlanChannelScanResultsEntryDfsScheme OBJECT-TYPE
    SYNTAX     INTEGER {
                  eNone (0),
                  eEn301893V12 (1),
                  eEn301893V13 (2),
                  eEn302502 (4),
                  eFcc (8),
                  eJapan (16),
                  eEn301893V15 (32),
                  eEn301893V16 (64),
                  eEn301893V17 (256)
            }
    MAX-ACCESS read-only
    STATUS     current
    DESCRIPTION
            "-- empty --"
    ::= { hmStatusWlanChannelScanResultsEntry 14 }

-- {COLUMN} 1.3.6.1.4.1.248.32.18.1.3.42.1.15
hmStatusWlanChannelScanResultsEntryUsage OBJECT-TYPE
    SYNTAX     BITS {
                  eNone (0),
                  eOverlapScan (29),
                  eBackgroundScan (30),
                  eOperation (31)
            }
    MAX-ACCESS read-only
    STATUS     current
    DESCRIPTION
            "-- empty --"
    ::= { hmStatusWlanChannelScanResultsEntry 15 }

-- {COLUMN} 1.3.6.1.4.1.248.32.18.1.3.42.1.16
hmStatusWlanChannelScanResultsEntryScanAge OBJECT-TYPE
    SYNTAX     Integer32 (0..2147483647)
    MAX-ACCESS read-only
    STATUS     current
    DESCRIPTION
            "-- empty --"
    ::= { hmStatusWlanChannelScanResultsEntry 16 }

-- {COLUMN} 1.3.6.1.4.1.248.32.18.1.3.42.1.17
hmStatusWlanChannelScanResultsEntryNonHtBss OBJECT-TYPE
    SYNTAX     INTEGER {
                  eNo (0),
                  eYes (1)
            }
    MAX-ACCESS read-only
    STATUS     current
    DESCRIPTION
            "-- empty --"
    ::= { hmStatusWlanChannelScanResultsEntry 17 }

-- {COLUMN} 1.3.6.1.4.1.248.32.18.1.3.42.1.18
hmStatusWlanChannelScanResultsEntryNonHtBssAge OBJECT-TYPE
    SYNTAX     Integer32 (0..2147483647)
    MAX-ACCESS read-only
    STATUS     current
    DESCRIPTION
            "-- empty --"
    ::= { hmStatusWlanChannelScanResultsEntry 18 }

-- {COLUMN} 1.3.6.1.4.1.248.32.18.1.3.42.1.19
hmStatusWlanChannelScanResultsEntry40mIntolerantBss OBJECT-TYPE
    SYNTAX     INTEGER {
                  eNo (0),
                  eYes (1)
            }
    MAX-ACCESS read-only
    STATUS     current
    DESCRIPTION
            "-- empty --"
    ::= { hmStatusWlanChannelScanResultsEntry 19 }

-- {COLUMN} 1.3.6.1.4.1.248.32.18.1.3.42.1.20
hmStatusWlanChannelScanResultsEntry40mIntolerantBssAge OBJECT-TYPE
    SYNTAX     Integer32 (0..2147483647)
    MAX-ACCESS read-only
    STATUS     current
    DESCRIPTION
            "-- empty --"
    ::= { hmStatusWlanChannelScanResultsEntry 20 }

-- {COLUMN} 1.3.6.1.4.1.248.32.18.1.3.42.1.21
hmStatusWlanChannelScanResultsEntry40mIntolerantBssReported OBJECT-TYPE
    SYNTAX     INTEGER {
                  eNo (0),
                  eYes (1)
            }
    MAX-ACCESS read-only
    STATUS     current
    DESCRIPTION
            "-- empty --"
    ::= { hmStatusWlanChannelScanResultsEntry 21 }

-- {COLUMN} 1.3.6.1.4.1.248.32.18.1.3.42.1.22
hmStatusWlanChannelScanResultsEntry40mIntolerantBssReportedAge OBJECT-TYPE
    SYNTAX     Integer32 (0..2147483647)
    MAX-ACCESS read-only
    STATUS     current
    DESCRIPTION
            "-- empty --"
    ::= { hmStatusWlanChannelScanResultsEntry 22 }

-- {COLUMN} 1.3.6.1.4.1.248.32.18.1.3.42.1.23
hmStatusWlanChannelScanResultsEntryChannelBandwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { hmStatusWlanChannelScanResultsEntry 23 }

-- {COLUMN} 1.3.6.1.4.1.248.32.18.1.3.42.1.248
hmStatusWlanChannelScanResultsEntryBgscanPriority OBJECT-TYPE
    SYNTAX     Integer32 (0..255)
    MAX-ACCESS read-only
    STATUS     current
    DESCRIPTION
            "-- empty --"
    ::= { hmStatusWlanChannelScanResultsEntry 248 }

-- {NODE} 1.3.6.1.4.1.248.32.18.1.3.43
hmStatusWlanClient OBJECT IDENTIFIER ::= { hmStatusWlan 43 }

-- {TABLE} 1.3.6.1.4.1.248.32.18.1.3.43.1
hmStatusWlanClientIpv4TranslationTableTable OBJECT-TYPE
    SYNTAX     SEQUENCE OF HmStatusWlanClientIpv4TranslationTableEntry
    MAX-ACCESS not-accessible
    STATUS     current
    DESCRIPTION
            "-- empty --"
    ::= { hmStatusWlanClient 1 }

-- {ROW} 1.3.6.1.4.1.248.32.18.1.3.43.1.1
hmStatusWlanClientIpv4TranslationTableEntry OBJECT-TYPE
    SYNTAX     HmStatusWlanClientIpv4TranslationTableEntry
    MAX-ACCESS not-accessible
    STATUS     current
    DESCRIPTION
            ""
    INDEX {
            hmStatusWlanClientIpv4TranslationTableEntryIpAddress
          }
    ::= { hmStatusWlanClientIpv4TranslationTableTable 1 }

HmStatusWlanClientIpv4TranslationTableEntry ::= SEQUENCE {
            hmStatusWlanClientIpv4TranslationTableEntryIpAddress IpAddress,
            hmStatusWlanClientIpv4TranslationTableEntryMacAddress MacAddress,
            hmStatusWlanClientIpv4TranslationTableEntryAge Integer32,
            hmStatusWlanClientIpv4TranslationTableEntryInternal INTEGER
    }

-- {COLUMN} 1.3.6.1.4.1.248.32.18.1.3.43.1.1.1
hmStatusWlanClientIpv4TranslationTableEntryIpAddress OBJECT-TYPE
    SYNTAX     IpAddress
    MAX-ACCESS read-only
    STATUS     current
    DESCRIPTION
            "-- empty --"
    ::= { hmStatusWlanClientIpv4TranslationTableEntry 1 }

-- {COLUMN} 1.3.6.1.4.1.248.32.18.1.3.43.1.1.2
hmStatusWlanClientIpv4TranslationTableEntryMacAddress OBJECT-TYPE
    SYNTAX     MacAddress
    MAX-ACCESS read-only
    STATUS     current
    DESCRIPTION
            "-- empty --"
    ::= { hmStatusWlanClientIpv4TranslationTableEntry 2 }

-- {COLUMN} 1.3.6.1.4.1.248.32.18.1.3.43.1.1.3
hmStatusWlanClientIpv4TranslationTableEntryAge OBJECT-TYPE
    SYNTAX     Integer32 (0..2147483647)
    MAX-ACCESS read-only
    STATUS     current
    DESCRIPTION
            "-- empty --"
    ::= { hmStatusWlanClientIpv4TranslationTableEntry 3 }

-- {COLUMN} 1.3.6.1.4.1.248.32.18.1.3.43.1.1.4
hmStatusWlanClientIpv4TranslationTableEntryInternal OBJECT-TYPE
    SYNTAX     INTEGER {
                  eNo (0),
                  eYes (1)
            }
    MAX-ACCESS read-only
    STATUS     current
    DESCRIPTION
            "-- empty --"
    ::= { hmStatusWlanClientIpv4TranslationTableEntry 4 }

-- {TABLE} 1.3.6.1.4.1.248.32.18.1.3.43.10
hmStatusWlanClientPppoeIdTranslationTableTable OBJECT-TYPE
    SYNTAX     SEQUENCE OF HmStatusWlanClientPppoeIdTranslationTableEntry
    MAX-ACCESS not-accessible
    STATUS     current
    DESCRIPTION
            "-- empty --"
    ::= { hmStatusWlanClient 10 }

-- {ROW} 1.3.6.1.4.1.248.32.18.1.3.43.10.1
hmStatusWlanClientPppoeIdTranslationTableEntry OBJECT-TYPE
    SYNTAX     HmStatusWlanClientPppoeIdTranslationTableEntry
    MAX-ACCESS not-accessible
    STATUS     current
    DESCRIPTION
            ""
    INDEX {
            hmStatusWlanClientPppoeIdTranslationTableEntrySessionId
          }
    ::= { hmStatusWlanClientPppoeIdTranslationTableTable 1 }

HmStatusWlanClientPppoeIdTranslationTableEntry ::= SEQUENCE {
            hmStatusWlanClientPppoeIdTranslationTableEntrySessionId Integer32,
            hmStatusWlanClientPppoeIdTranslationTableEntryMacAddress MacAddress,
            hmStatusWlanClientPppoeIdTranslationTableEntryAge Integer32
    }

-- {COLUMN} 1.3.6.1.4.1.248.32.18.1.3.43.10.1.1
hmStatusWlanClientPppoeIdTranslationTableEntrySessionId OBJECT-TYPE
    SYNTAX     Integer32 (0..65535)
    MAX-ACCESS read-only
    STATUS     current
    DESCRIPTION
            "-- empty --"
    ::= { hmStatusWlanClientPppoeIdTranslationTableEntry 1 }

-- {COLUMN} 1.3.6.1.4.1.248.32.18.1.3.43.10.1.2
hmStatusWlanClientPppoeIdTranslationTableEntryMacAddress OBJECT-TYPE
    SYNTAX     MacAddress
    MAX-ACCESS read-only
    STATUS     current
    DESCRIPTION
            "-- empty --"
    ::= { hmStatusWlanClientPppoeIdTranslationTableEntry 2 }

-- {COLUMN} 1.3.6.1.4.1.248.32.18.1.3.43.10.1.3
hmStatusWlanClientPppoeIdTranslationTableEntryAge OBJECT-TYPE
    SYNTAX     Integer32 (0..2147483647)
    MAX-ACCESS read-only
    STATUS     current
    DESCRIPTION
            "-- empty --"
    ::= { hmStatusWlanClientPppoeIdTranslationTableEntry 3 }

-- {TABLE} 1.3.6.1.4.1.248.32.18.1.3.43.11
hmStatusWlanClientPppoeUniqTranslationTableTable OBJECT-TYPE
    SYNTAX     SEQUENCE OF HmStatusWlanClientPppoeUniqTranslationTableEntry
    MAX-ACCESS not-accessible
    STATUS     current
    DESCRIPTION
            "-- empty --"
    ::= { hmStatusWlanClient 11 }

-- {ROW} 1.3.6.1.4.1.248.32.18.1.3.43.11.1
hmStatusWlanClientPppoeUniqTranslationTableEntry OBJECT-TYPE
    SYNTAX     HmStatusWlanClientPppoeUniqTranslationTableEntry
    MAX-ACCESS not-accessible
    STATUS     current
    DESCRIPTION
            ""
    INDEX {
            hmStatusWlanClientPppoeUniqTranslationTableEntryHostUniqLen,
            hmStatusWlanClientPppoeUniqTranslationTableEntryHostUniq
          }
    ::= { hmStatusWlanClientPppoeUniqTranslationTableTable 1 }

HmStatusWlanClientPppoeUniqTranslationTableEntry ::= SEQUENCE {
            hmStatusWlanClientPppoeUniqTranslationTableEntryHostUniqLen Integer32,
            hmStatusWlanClientPppoeUniqTranslationTableEntryHostUniq DisplayString,
            hmStatusWlanClientPppoeUniqTranslationTableEntryMacAddress MacAddress,
            hmStatusWlanClientPppoeUniqTranslationTableEntryAge Integer32
    }

-- {COLUMN} 1.3.6.1.4.1.248.32.18.1.3.43.11.1.1
hmStatusWlanClientPppoeUniqTranslationTableEntryHostUniqLen OBJECT-TYPE
    SYNTAX     Integer32 (0..65535)
    MAX-ACCESS read-only
    STATUS     current
    DESCRIPTION
            "-- empty --"
    ::= { hmStatusWlanClientPppoeUniqTranslationTableEntry 1 }

-- {COLUMN} 1.3.6.1.4.1.248.32.18.1.3.43.11.1.2
hmStatusWlanClientPppoeUniqTranslationTableEntryHostUniq OBJECT-TYPE
    SYNTAX     DisplayString (SIZE(0..255))
    MAX-ACCESS read-only
    STATUS     current
    DESCRIPTION
            "-- empty --"
    ::= { hmStatusWlanClientPppoeUniqTranslationTableEntry 2 }

-- {COLUMN} 1.3.6.1.4.1.248.32.18.1.3.43.11.1.3
hmStatusWlanClientPppoeUniqTranslationTableEntryMacAddress OBJECT-TYPE
    SYNTAX     MacAddress
    MAX-ACCESS read-only
    STATUS     current
    DESCRIPTION
            "-- empty --"
    ::= { hmStatusWlanClientPppoeUniqTranslationTableEntry 3 }

-- {COLUMN} 1.3.6.1.4.1.248.32.18.1.3.43.11.1.4
hmStatusWlanClientPppoeUniqTranslationTableEntryAge OBJECT-TYPE
    SYNTAX     Integer32 (0..2147483647)
    MAX-ACCESS read-only
    STATUS     current
    DESCRIPTION
            "-- empty --"
    ::= { hmStatusWlanClientPppoeUniqTranslationTableEntry 4 }

-- {TABLE} 1.3.6.1.4.1.248.32.18.1.3.43.12
hmStatusWlanClientIpv6TranslationTableTable OBJECT-TYPE
    SYNTAX     SEQUENCE OF HmStatusWlanClientIpv6TranslationTableEntry
    MAX-ACCESS not-accessible
    STATUS     current
    DESCRIPTION
            "-- empty --"
    ::= { hmStatusWlanClient 12 }

-- {ROW} 1.3.6.1.4.1.248.32.18.1.3.43.12.1
hmStatusWlanClientIpv6TranslationTableEntry OBJECT-TYPE
    SYNTAX     HmStatusWlanClientIpv6TranslationTableEntry
    MAX-ACCESS not-accessible
    STATUS     current
    DESCRIPTION
            ""
    INDEX {
            hmStatusWlanClientIpv6TranslationTableEntryIpAddress
          }
    ::= { hmStatusWlanClientIpv6TranslationTableTable 1 }

HmStatusWlanClientIpv6TranslationTableEntry ::= SEQUENCE {
            hmStatusWlanClientIpv6TranslationTableEntryIpAddress IpAddress,
            hmStatusWlanClientIpv6TranslationTableEntryMacAddress MacAddress,
            hmStatusWlanClientIpv6TranslationTableEntryAge Integer32,
            hmStatusWlanClientIpv6TranslationTableEntryInternal INTEGER
    }

-- {COLUMN} 1.3.6.1.4.1.248.32.18.1.3.43.12.1.1
hmStatusWlanClientIpv6TranslationTableEntryIpAddress OBJECT-TYPE
    SYNTAX     IpAddress
    MAX-ACCESS read-only
    STATUS     current
    DESCRIPTION
            "-- empty --"
    ::= { hmStatusWlanClientIpv6TranslationTableEntry 1 }

-- {COLUMN} 1.3.6.1.4.1.248.32.18.1.3.43.12.1.2
hmStatusWlanClientIpv6TranslationTableEntryMacAddress OBJECT-TYPE
    SYNTAX     MacAddress
    MAX-ACCESS read-only
    STATUS     current
    DESCRIPTION
            "-- empty --"
    ::= { hmStatusWlanClientIpv6TranslationTableEntry 2 }

-- {COLUMN} 1.3.6.1.4.1.248.32.18.1.3.43.12.1.3
hmStatusWlanClientIpv6TranslationTableEntryAge OBJECT-TYPE
    SYNTAX     Integer32 (0..2147483647)
    MAX-ACCESS read-only
    STATUS     current
    DESCRIPTION
            "-- empty --"
    ::= { hmStatusWlanClientIpv6TranslationTableEntry 3 }

-- {COLUMN} 1.3.6.1.4.1.248.32.18.1.3.43.12.1.4
hmStatusWlanClientIpv6TranslationTableEntryInternal OBJECT-TYPE
    SYNTAX     INTEGER {
                  eNo (0),
                  eYes (1)
            }
    MAX-ACCESS read-only
    STATUS     current
    DESCRIPTION
            "-- empty --"
    ::= { hmStatusWlanClientIpv6TranslationTableEntry 4 }

-- {TABLE} 1.3.6.1.4.1.248.32.18.1.3.43.51
hmStatusWlanClientIfcsTable OBJECT-TYPE
    SYNTAX     SEQUENCE OF HmStatusWlanClientIfcsEntry
    MAX-ACCESS not-accessible
    STATUS     current
    DESCRIPTION
            ""
    ::= { hmStatusWlanClient 51 }

-- {ROW} 1.3.6.1.4.1.248.32.18.1.3.43.51.1
hmStatusWlanClientIfcsEntry OBJECT-TYPE
    SYNTAX     HmStatusWlanClientIfcsEntry
    MAX-ACCESS not-accessible
    STATUS     current
    DESCRIPTION
            ""
    INDEX {
            hmStatusWlanClientIfcsEntryIfc
          }
    ::= { hmStatusWlanClientIfcsTable 1 }

HmStatusWlanClientIfcsEntry ::= SEQUENCE {
            hmStatusWlanClientIfcsEntryIfc DisplayString,
            hmStatusWlanClientIfcsEntryState INTEGER,
            hmStatusWlanClientIfcsEntryStationMode INTEGER,
            hmStatusWlanClientIfcsEntryRxRate INTEGER,
            hmStatusWlanClientIfcsEntryThroughput DisplayString,
            hmStatusWlanClientIfcsEntryPhySignal Integer32,
            hmStatusWlanClientIfcsEntryTxRate INTEGER,
            hmStatusWlanClientIfcsEntryMaxThroughput DisplayString,
            hmStatusWlanClientIfcsEntryTxBytes Counter64,
            hmStatusWlanClientIfcsEntryRxBytes Counter64,
            hmStatusWlanClientIfcsEntryBytesThroughput Integer32,
            hmStatusWlanClientIfcsEntryBytesMaxThroughput Integer32,
            hmStatusWlanClientIfcsEntryClBrgSupport INTEGER,
            hmStatusWlanClientIfcsEntryWpaVersion INTEGER,
            hmStatusWlanClientIfcsEntryTxLimit Integer32,
            hmStatusWlanClientIfcsEntryRxLimit Integer32,
            hmStatusWlanClientIfcsEntryQos INTEGER,
            hmStatusWlanClientIfcsEntryTxPackets Counter32,
            hmStatusWlanClientIfcsEntryRxPackets Counter32,
            hmStatusWlanClientIfcsEntryLinkPhySignal Integer32,
            hmStatusWlanClientIfcsEntryAid Integer32,
            hmStatusWlanClientIfcsEntryIdentification DisplayString,
            hmStatusWlanClientIfcsEntryConnectTime Integer32,
            hmStatusWlanClientIfcsEntryLinkSignalLevel Integer32,
            hmStatusWlanClientIfcsEntryMaxAMpduLen Integer32,
            hmStatusWlanClientIfcsEntryMaxAMsduLen Integer32,
            hmStatusWlanClientIfcsEntryEffTxRate Integer32,
            hmStatusWlanClientIfcsEntryEffRxRate Integer32,
            hmStatusWlanClientIfcsEntryKeyType INTEGER,
            hmStatusWlanClientIfcsEntryTxErrors Integer32,
            hmStatusWlanClientIfcsEntryTotalRetries Integer32,
            hmStatusWlanClientIfcsEntryAlarmState INTEGER,
            hmStatusWlanClientIfcsEntryAllow40mhz INTEGER,
            hmStatusWlanClientIfcsEntryExtChannel INTEGER,
            hmStatusWlanClientIfcsEntry40mhzCoexistence INTEGER,
            hmStatusWlanClientIfcsEntryRxStbc INTEGER,
            hmStatusWlanClientIfcsEntryLdpc INTEGER,
            hmStatusWlanClientIfcsEntryWpa2KeyManagement INTEGER,
            hmStatusWlanClientIfcsEntryProtMgmtFrames INTEGER,
            hmStatusWlanClientIfcsEntryRxStbcHt INTEGER,
            hmStatusWlanClientIfcsEntryRxStbcVht INTEGER,
            hmStatusWlanClientIfcsEntryLDPCMask BITS,
            hmStatusWlanClientIfcsEntryOperationMode INTEGER,
            hmStatusWlanClientIfcsEntrySoftRoamCount Counter32
    }

-- {COLUMN} 1.3.6.1.4.1.248.32.18.1.3.43.51.1.1
hmStatusWlanClientIfcsEntryIfc OBJECT-TYPE
    SYNTAX     DisplayString (SIZE(0..255))
    MAX-ACCESS read-only
    STATUS     current
    DESCRIPTION
            "-- empty --"
    ::= { hmStatusWlanClientIfcsEntry 1 }

-- {COLUMN} 1.3.6.1.4.1.248.32.18.1.3.43.51.1.2
hmStatusWlanClientIfcsEntryState OBJECT-TYPE
    SYNTAX     INTEGER {
                  eNone (0),
                  eAuthenticated (2),
                  eConnected (3),
                  eJoined (5),
                  eScanning (6),
                  eChallenge (7),
                  eKeyHandshake (8),
                  eAssociated (9),
                  e1xNegotiation (10),
                  eWaitPmkCache (11)
            }
    MAX-ACCESS read-only
    STATUS     current
    DESCRIPTION
            "-- empty --"
    ::= { hmStatusWlanClientIfcsEntry 2 }

-- {COLUMN} 1.3.6.1.4.1.248.32.18.1.3.43.51.1.3
hmStatusWlanClientIfcsEntryStationMode OBJECT-TYPE
    SYNTAX     INTEGER {
                  eNone (0),
                  eAdhoc (1),
                  eInfrastructure (2)
            }
    MAX-ACCESS read-only
    STATUS     current
    DESCRIPTION
            "-- empty --"
    ::= { hmStatusWlanClientIfcsEntry 3 }

-- {COLUMN} 1.3.6.1.4.1.248.32.18.1.3.43.51.1.5
hmStatusWlanClientIfcsEntryRxRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51)
            }
    MAX-ACCESS read-only
    STATUS     current
    DESCRIPTION
            "-- empty --"
    ::= { hmStatusWlanClientIfcsEntry 5 }

-- {COLUMN} 1.3.6.1.4.1.248.32.18.1.3.43.51.1.6
hmStatusWlanClientIfcsEntryThroughput OBJECT-TYPE
    SYNTAX     DisplayString (SIZE(0..255))
    MAX-ACCESS read-only
    STATUS     current
    DESCRIPTION
            "-- empty --"
    ::= { hmStatusWlanClientIfcsEntry 6 }

-- {COLUMN} 1.3.6.1.4.1.248.32.18.1.3.43.51.1.7
hmStatusWlanClientIfcsEntryPhySignal OBJECT-TYPE
    SYNTAX     Integer32 (0..65535)
    MAX-ACCESS read-only
    STATUS     current
    DESCRIPTION
            "-- empty --"
    ::= { hmStatusWlanClientIfcsEntry 7 }

-- {COLUMN} 1.3.6.1.4.1.248.32.18.1.3.43.51.1.9
hmStatusWlanClientIfcsEntryTxRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51)
            }
    MAX-ACCESS read-only
    STATUS     current
    DESCRIPTION
            "-- empty --"
    ::= { hmStatusWlanClientIfcsEntry 9 }

-- {COLUMN} 1.3.6.1.4.1.248.32.18.1.3.43.51.1.10
hmStatusWlanClientIfcsEntryMaxThroughput OBJECT-TYPE
    SYNTAX     DisplayString (SIZE(0..255))
    MAX-ACCESS read-only
    STATUS     current
    DESCRIPTION
            "-- empty --"
    ::= { hmStatusWlanClientIfcsEntry 10 }

-- {COLUMN} 1.3.6.1.4.1.248.32.18.1.3.43.51.1.11
hmStatusWlanClientIfcsEntryTxBytes OBJECT-TYPE
    SYNTAX     Counter64
    MAX-ACCESS read-only
    STATUS     current
    DESCRIPTION
            "-- empty --"
    ::= { hmStatusWlanClientIfcsEntry 11 }

-- {COLUMN} 1.3.6.1.4.1.248.32.18.1.3.43.51.1.12
hmStatusWlanClientIfcsEntryRxBytes OBJECT-TYPE
    SYNTAX     Counter64
    MAX-ACCESS read-only
    STATUS     current
    DESCRIPTION
            "-- empty --"
    ::= { hmStatusWlanClientIfcsEntry 12 }

-- {COLUMN} 1.3.6.1.4.1.248.32.18.1.3.43.51.1.13
hmStatusWlanClientIfcsEntryBytesThroughput OBJECT-TYPE
    SYNTAX     Integer32 (0..2147483647)
    MAX-ACCESS read-only
    STATUS     current
    DESCRIPTION
            "-- empty --"
    ::= { hmStatusWlanClientIfcsEntry 13 }

-- {COLUMN} 1.3.6.1.4.1.248.32.18.1.3.43.51.1.14
hmStatusWlanClientIfcsEntryBytesMaxThroughput OBJECT-TYPE
    SYNTAX     Integer32 (0..2147483647)
    MAX-ACCESS read-only
    STATUS     current
    DESCRIPTION
            "-- empty --"
    ::= { hmStatusWlanClientIfcsEntry 14 }

-- {COLUMN} 1.3.6.1.4.1.248.32.18.1.3.43.51.1.15
hmStatusWlanClientIfcsEntryClBrgSupport OBJECT-TYPE
    SYNTAX     INTEGER {
                  eNo (0),
                  eYes (1)
            }
    MAX-ACCESS read-only
    STATUS     current
    DESCRIPTION
            "-- empty --"
    ::= { hmStatusWlanClientIfcsEntry 15 }

-- {COLUMN} 1.3.6.1.4.1.248.32.18.1.3.43.51.1.16
hmStatusWlanClientIfcsEntryWpaVersion OBJECT-TYPE
    SYNTAX     INTEGER {
                  eNone (0),
                  eWpa1 (1),
                  eWpa2 (2)
            }
    MAX-ACCESS read-only
    STATUS     current
    DESCRIPTION
            "-- empty --"
    ::= { hmStatusWlanClientIfcsEntry 16 }

-- {COLUMN} 1.3.6.1.4.1.248.32.18.1.3.43.51.1.17
hmStatusWlanClientIfcsEntryTxLimit OBJECT-TYPE
    SYNTAX     Integer32 (0..2147483647)
    MAX-ACCESS read-only
    STATUS     current
    DESCRIPTION
            "-- empty --"
    ::= { hmStatusWlanClientIfcsEntry 17 }

-- {COLUMN} 1.3.6.1.4.1.248.32.18.1.3.43.51.1.18
hmStatusWlanClientIfcsEntryRxLimit OBJECT-TYPE
    SYNTAX     Integer32 (0..2147483647)
    MAX-ACCESS read-only
    STATUS     current
    DESCRIPTION
            "-- empty --"
    ::= { hmStatusWlanClientIfcsEntry 18 }

-- {COLUMN} 1.3.6.1.4.1.248.32.18.1.3.43.51.1.19
hmStatusWlanClientIfcsEntryQos OBJECT-TYPE
    SYNTAX     INTEGER {
                  eNo (0),
                  eYes (1)
            }
    MAX-ACCESS read-only
    STATUS     current
    DESCRIPTION
            "-- empty --"
    ::= { hmStatusWlanClientIfcsEntry 19 }

-- {COLUMN} 1.3.6.1.4.1.248.32.18.1.3.43.51.1.20
hmStatusWlanClientIfcsEntryTxPackets OBJECT-TYPE
    SYNTAX     Counter32
    MAX-ACCESS read-only
    STATUS     current
    DESCRIPTION
            "-- empty --"
    ::= { hmStatusWlanClientIfcsEntry 20 }

-- {COLUMN} 1.3.6.1.4.1.248.32.18.1.3.43.51.1.21
hmStatusWlanClientIfcsEntryRxPackets OBJECT-TYPE
    SYNTAX     Counter32
    MAX-ACCESS read-only
    STATUS     current
    DESCRIPTION
            "-- empty --"
    ::= { hmStatusWlanClientIfcsEntry 21 }

-- {COLUMN} 1.3.6.1.4.1.248.32.18.1.3.43.51.1.22
hmStatusWlanClientIfcsEntryLinkPhySignal OBJECT-TYPE
    SYNTAX     Integer32 (0..65535)
    MAX-ACCESS read-only
    STATUS     current
    DESCRIPTION
            "-- empty --"
    ::= { hmStatusWlanClientIfcsEntry 22 }

-- {COLUMN} 1.3.6.1.4.1.248.32.18.1.3.43.51.1.23
hmStatusWlanClientIfcsEntryAid OBJECT-TYPE
    SYNTAX     Integer32 (0..65535)
    MAX-ACCESS read-only
    STATUS     current
    DESCRIPTION
            "-- empty --"
    ::= { hmStatusWlanClientIfcsEntry 23 }

-- {COLUMN} 1.3.6.1.4.1.248.32.18.1.3.43.51.1.24
hmStatusWlanClientIfcsEntryIdentification OBJECT-TYPE
    SYNTAX     DisplayString (SIZE(0..24))
    MAX-ACCESS read-only
    STATUS     current
    DESCRIPTION
            "-- empty --"
    ::= { hmStatusWlanClientIfcsEntry 24 }

-- {COLUMN} 1.3.6.1.4.1.248.32.18.1.3.43.51.1.25
hmStatusWlanClientIfcsEntryConnectTime OBJECT-TYPE
    SYNTAX     Integer32 (0..2147483647)
    MAX-ACCESS read-only
    STATUS     current
    DESCRIPTION
            "-- empty --"
    ::= { hmStatusWlanClientIfcsEntry 25 }

-- {COLUMN} 1.3.6.1.4.1.248.32.18.1.3.43.51.1.26
hmStatusWlanClientIfcsEntryLinkSignalLevel OBJECT-TYPE
    SYNTAX     Integer32 (-32768..32767)
    MAX-ACCESS read-only
    STATUS     current
    DESCRIPTION
            "-- empty --"
    ::= { hmStatusWlanClientIfcsEntry 26 }

-- {COLUMN} 1.3.6.1.4.1.248.32.18.1.3.43.51.1.27
hmStatusWlanClientIfcsEntryMaxAMpduLen OBJECT-TYPE
    SYNTAX     Integer32 (0..2147483647)
    MAX-ACCESS read-only
    STATUS     current
    DESCRIPTION
            "-- empty --"
    ::= { hmStatusWlanClientIfcsEntry 27 }

-- {COLUMN} 1.3.6.1.4.1.248.32.18.1.3.43.51.1.28
hmStatusWlanClientIfcsEntryMaxAMsduLen OBJECT-TYPE
    SYNTAX     Integer32 (0..2147483647)
    MAX-ACCESS read-only
    STATUS     current
    DESCRIPTION
            "-- empty --"
    ::= { hmStatusWlanClientIfcsEntry 28 }

-- {COLUMN} 1.3.6.1.4.1.248.32.18.1.3.43.51.1.29
hmStatusWlanClientIfcsEntryEffTxRate OBJECT-TYPE
    SYNTAX     Integer32 (0..2147483647)
    MAX-ACCESS read-only
    STATUS     current
    DESCRIPTION
            "-- empty --"
    ::= { hmStatusWlanClientIfcsEntry 29 }

-- {COLUMN} 1.3.6.1.4.1.248.32.18.1.3.43.51.1.30
hmStatusWlanClientIfcsEntryEffRxRate OBJECT-TYPE
    SYNTAX     Integer32 (0..2147483647)
    MAX-ACCESS read-only
    STATUS     current
    DESCRIPTION
            "-- empty --"
    ::= { hmStatusWlanClientIfcsEntry 30 }

-- {COLUMN} 1.3.6.1.4.1.248.32.18.1.3.43.51.1.31
hmStatusWlanClientIfcsEntryKeyType OBJECT-TYPE
    SYNTAX     INTEGER {
                  eNone (0),
                  eUnknown (1),
                  eWep40Bits (5),
                  eWep104Bits (13),
                  eWep128Bits (16),
                  eTkip (64),
                  eAesOcb (65),
                  eAesCcm (66),
                  eBip (68)
            }
    MAX-ACCESS read-only
    STATUS     current
    DESCRIPTION
            "-- empty --"
    ::= { hmStatusWlanClientIfcsEntry 31 }

-- {COLUMN} 1.3.6.1.4.1.248.32.18.1.3.43.51.1.32
hmStatusWlanClientIfcsEntryTxErrors OBJECT-TYPE
    SYNTAX     Integer32 (0..2147483647)
    MAX-ACCESS read-only
    STATUS     current
    DESCRIPTION
            "-- empty --"
    ::= { hmStatusWlanClientIfcsEntry 32 }

-- {COLUMN} 1.3.6.1.4.1.248.32.18.1.3.43.51.1.33
hmStatusWlanClientIfcsEntryTotalRetries OBJECT-TYPE
    SYNTAX     Integer32 (0..2147483647)
    MAX-ACCESS read-only
    STATUS     current
    DESCRIPTION
            "-- empty --"
    ::= { hmStatusWlanClientIfcsEntry 33 }

-- {COLUMN} 1.3.6.1.4.1.248.32.18.1.3.43.51.1.34
hmStatusWlanClientIfcsEntryAlarmState OBJECT-TYPE
    SYNTAX     INTEGER {
                  eNo (0),
                  ePhySignal (1),
                  eTotalRetries (2),
                  eTxErrors (4)
            }
    MAX-ACCESS read-only
    STATUS     current
    DESCRIPTION
            "-- empty --"
    ::= { hmStatusWlanClientIfcsEntry 34 }

-- {COLUMN} 1.3.6.1.4.1.248.32.18.1.3.43.51.1.35
hmStatusWlanClientIfcsEntryAllow40mhz OBJECT-TYPE
    SYNTAX     INTEGER {
                  eNo (0),
                  eYes (1)
            }
    MAX-ACCESS read-only
    STATUS     current
    DESCRIPTION
            "-- empty --"
    ::= { hmStatusWlanClientIfcsEntry 35 }

-- {COLUMN} 1.3.6.1.4.1.248.32.18.1.3.43.51.1.36
hmStatusWlanClientIfcsEntryExtChannel OBJECT-TYPE
    SYNTAX     INTEGER {
                  eNone (0),
                  eAbove (1),
                  eBelow (3)
            }
    MAX-ACCESS read-only
    STATUS     current
    DESCRIPTION
            "-- empty --"
    ::= { hmStatusWlanClientIfcsEntry 36 }

-- {COLUMN} 1.3.6.1.4.1.248.32.18.1.3.43.51.1.37
hmStatusWlanClientIfcsEntry40mhzCoexistence OBJECT-TYPE
    SYNTAX     INTEGER {
                  eNo (0),
                  eYes (1)
            }
    MAX-ACCESS read-only
    STATUS     current
    DESCRIPTION
            "-- empty --"
    ::= { hmStatusWlanClientIfcsEntry 37 }

-- {COLUMN} 1.3.6.1.4.1.248.32.18.1.3.43.51.1.38
hmStatusWlanClientIfcsEntryRxStbc OBJECT-TYPE
    SYNTAX     INTEGER {
                  eNone (0),
                  eOne (1),
                  eTwo (2),
                  eThree (3)
            }
    MAX-ACCESS read-only
    STATUS     current
    DESCRIPTION
            "-- empty --"
    ::= { hmStatusWlanClientIfcsEntry 38 }

-- {COLUMN} 1.3.6.1.4.1.248.32.18.1.3.43.51.1.39
hmStatusWlanClientIfcsEntryLdpc OBJECT-TYPE
    SYNTAX     INTEGER {
                  eNo (0),
                  eYes (1)
            }
    MAX-ACCESS read-only
    STATUS     current
    DESCRIPTION
            "-- empty --"
    ::= { hmStatusWlanClientIfcsEntry 39 }

-- {COLUMN} 1.3.6.1.4.1.248.32.18.1.3.43.51.1.40
hmStatusWlanClientIfcsEntryWpa2KeyManagement OBJECT-TYPE
    SYNTAX     INTEGER {
                  eStandard (0),
                  eFastRoaming (1),
                  eSha256 (2),
                  eNone (255)
            }
    MAX-ACCESS read-only
    STATUS     current
    DESCRIPTION
            "-- empty --"
    ::= { hmStatusWlanClientIfcsEntry 40 }

-- {COLUMN} 1.3.6.1.4.1.248.32.18.1.3.43.51.1.41
hmStatusWlanClientIfcsEntryProtMgmtFrames OBJECT-TYPE
    SYNTAX     INTEGER {
                  eNo (0),
                  eYes (1)
            }
    MAX-ACCESS read-only
    STATUS     current
    DESCRIPTION
            "-- empty --"
    ::= { hmStatusWlanClientIfcsEntry 41 }

-- {COLUMN} 1.3.6.1.4.1.248.32.18.1.3.43.51.1.42
hmStatusWlanClientIfcsEntryRxStbcHt OBJECT-TYPE
    SYNTAX     INTEGER {
                  eNone (0),
                  eOne (1),
                  eTwo (2),
                  eThree (3)
            }
    MAX-ACCESS read-only
    STATUS     current
    DESCRIPTION
            "-- empty --"
    ::= { hmStatusWlanClientIfcsEntry 42 }

-- {COLUMN} 1.3.6.1.4.1.248.32.18.1.3.43.51.1.43
hmStatusWlanClientIfcsEntryRxStbcVht OBJECT-TYPE
    SYNTAX     INTEGER {
                  eNone (0),
                  eOne (1),
                  eTwo (2),
                  eThree (3),
                  eFour (4),
                  eFive (5),
                  eSix (6),
                  eSeven (7)
            }
    MAX-ACCESS read-only
    STATUS     current
    DESCRIPTION
            "-- empty --"
    ::= { hmStatusWlanClientIfcsEntry 43 }

-- {COLUMN} 1.3.6.1.4.1.248.32.18.1.3.43.51.1.44
hmStatusWlanClientIfcsEntryLDPCMask OBJECT-TYPE
    SYNTAX     BITS {
                  eVht (30),
                  eHt (31)
            }
    MAX-ACCESS read-only
    STATUS     current
    DESCRIPTION
            "Bit mask of LDPC support per-PHY-Type"
    ::= { hmStatusWlanClientIfcsEntry 44 }

-- {COLUMN} 1.3.6.1.4.1.248.32.18.1.3.43.51.1.45
hmStatusWlanClientIfcsEntryOperationMode OBJECT-TYPE
    SYNTAX     INTEGER {
                  eUnknown (0),
                  e11b (1),
                  e11g (2),
                  e11a (3),
                  e11n (4)
            }
    MAX-ACCESS read-only
    STATUS     current
    DESCRIPTION
            "-- empty --"
    ::= { hmStatusWlanClientIfcsEntry 45 }

-- {COLUMN} 1.3.6.1.4.1.248.32.18.1.3.43.51.1.248
hmStatusWlanClientIfcsEntrySoftRoamCount OBJECT-TYPE
    SYNTAX     Counter32
    MAX-ACCESS read-only
    STATUS     current
    DESCRIPTION
            "-- empty --"
    ::= { hmStatusWlanClientIfcsEntry 248 }

-- {TABLE} 1.3.6.1.4.1.248.32.18.1.3.43.52
hmStatusWlanClientConnectionRejectsTable OBJECT-TYPE
    SYNTAX     SEQUENCE OF HmStatusWlanClientConnectionRejectsEntry
    MAX-ACCESS not-accessible
    STATUS     current
    DESCRIPTION
            "-- empty --"
    ::= { hmStatusWlanClient 52 }

-- {ROW} 1.3.6.1.4.1.248.32.18.1.3.43.52.1
hmStatusWlanClientConnectionRejectsEntry OBJECT-TYPE
    SYNTAX     HmStatusWlanClientConnectionRejectsEntry
    MAX-ACCESS not-accessible
    STATUS     current
    DESCRIPTION
            ""
    INDEX {
            hmStatusWlanClientConnectionRejectsEntryBssid,
            hmStatusWlanClientConnectionRejectsEntryInterface
          }
    ::= { hmStatusWlanClientConnectionRejectsTable 1 }

HmStatusWlanClientConnectionRejectsEntry ::= SEQUENCE {
            hmStatusWlanClientConnectionRejectsEntryBssid MacAddress,
            hmStatusWlanClientConnectionRejectsEntryInterface INTEGER,
            hmStatusWlanClientConnectionRejectsEntryAge Integer32,
            hmStatusWlanClientConnectionRejectsEntryEvent INTEGER,
            hmStatusWlanClientConnectionRejectsEntryStatusOrReason Integer32
    }

-- {COLUMN} 1.3.6.1.4.1.248.32.18.1.3.43.52.1.1
hmStatusWlanClientConnectionRejectsEntryBssid OBJECT-TYPE
    SYNTAX     MacAddress
    MAX-ACCESS read-only
    STATUS     current
    DESCRIPTION
            "-- empty --"
    ::= { hmStatusWlanClientConnectionRejectsEntry 1 }

-- {COLUMN} 1.3.6.1.4.1.248.32.18.1.3.43.52.1.2
hmStatusWlanClientConnectionRejectsEntryInterface OBJECT-TYPE
    SYNTAX     INTEGER {
                  eWlan1 (1),
                  eWlan2 (2)
            }
    MAX-ACCESS read-only
    STATUS     current
    DESCRIPTION
            "-- empty --"
    ::= { hmStatusWlanClientConnectionRejectsEntry 2 }

-- {COLUMN} 1.3.6.1.4.1.248.32.18.1.3.43.52.1.3
hmStatusWlanClientConnectionRejectsEntryAge OBJECT-TYPE
    SYNTAX     Integer32 (0..2147483647)
    MAX-ACCESS read-only
    STATUS     current
    DESCRIPTION
            "-- empty --"
    ::= { hmStatusWlanClientConnectionRejectsEntry 3 }

-- {COLUMN} 1.3.6.1.4.1.248.32.18.1.3.43.52.1.4
hmStatusWlanClientConnectionRejectsEntryEvent OBJECT-TYPE
    SYNTAX     INTEGER {
                  eDeauthenticate (1),
                  eDisassociate (2),
                  eAuthenticateReject (3),
                  eAssociateReject (4)
            }
    MAX-ACCESS read-only
    STATUS     current
    DESCRIPTION
            "-- empty --"
    ::= { hmStatusWlanClientConnectionRejectsEntry 4 }

-- {COLUMN} 1.3.6.1.4.1.248.32.18.1.3.43.52.1.5
hmStatusWlanClientConnectionRejectsEntryStatusOrReason OBJECT-TYPE
    SYNTAX     Integer32 (0..65535)
    MAX-ACCESS read-only
    STATUS     current
    DESCRIPTION
            "-- empty --"
    ::= { hmStatusWlanClientConnectionRejectsEntry 5 }

-- {TABLE} 1.3.6.1.4.1.248.32.18.1.3.43.248
hmStatusWlanClientRoamingStatisticsTable OBJECT-TYPE
    SYNTAX     SEQUENCE OF HmStatusWlanClientRoamingStatisticsEntry
    MAX-ACCESS not-accessible
    STATUS     current
    DESCRIPTION
            "-- empty --"
    ::= { hmStatusWlanClient 248 }

-- {ROW} 1.3.6.1.4.1.248.32.18.1.3.43.248.1
hmStatusWlanClientRoamingStatisticsEntry OBJECT-TYPE
    SYNTAX     HmStatusWlanClientRoamingStatisticsEntry
    MAX-ACCESS not-accessible
    STATUS     current
    DESCRIPTION
            ""
    INDEX {
            hmStatusWlanClientRoamingStatisticsEntryOldBssid,
            hmStatusWlanClientRoamingStatisticsEntryNewBssid
          }
    ::= { hmStatusWlanClientRoamingStatisticsTable 1 }

HmStatusWlanClientRoamingStatisticsEntry ::= SEQUENCE {
            hmStatusWlanClientRoamingStatisticsEntryOldBssid MacAddress,
            hmStatusWlanClientRoamingStatisticsEntryOldApName DisplayString,
            hmStatusWlanClientRoamingStatisticsEntryOldChannel Integer32,
            hmStatusWlanClientRoamingStatisticsEntryOldPhySignal Integer32,
            hmStatusWlanClientRoamingStatisticsEntryNewBssid MacAddress,
            hmStatusWlanClientRoamingStatisticsEntryNewApName DisplayString,
            hmStatusWlanClientRoamingStatisticsEntryNewChannel Integer32,
            hmStatusWlanClientRoamingStatisticsEntryNewPhySignal Integer32,
            hmStatusWlanClientRoamingStatisticsEntryRoamCount Counter32,
            hmStatusWlanClientRoamingStatisticsEntryAge Integer32
    }

-- {COLUMN} 1.3.6.1.4.1.248.32.18.1.3.43.248.1.1
hmStatusWlanClientRoamingStatisticsEntryOldBssid OBJECT-TYPE
    SYNTAX     MacAddress
    MAX-ACCESS read-only
    STATUS     current
    DESCRIPTION
            "-- empty --"
    ::= { hmStatusWlanClientRoamingStatisticsEntry 1 }

-- {COLUMN} 1.3.6.1.4.1.248.32.18.1.3.43.248.1.2
hmStatusWlanClientRoamingStatisticsEntryOldApName OBJECT-TYPE
    SYNTAX     DisplayString (SIZE(0..255))
    MAX-ACCESS read-only
    STATUS     current
    DESCRIPTION
            "-- empty --"
    ::= { hmStatusWlanClientRoamingStatisticsEntry 2 }

-- {COLUMN} 1.3.6.1.4.1.248.32.18.1.3.43.248.1.3
hmStatusWlanClientRoamingStatisticsEntryOldChannel OBJECT-TYPE
    SYNTAX     Integer32 (0..255)
    MAX-ACCESS read-only
    STATUS     current
    DESCRIPTION
            "-- empty --"
    ::= { hmStatusWlanClientRoamingStatisticsEntry 3 }

-- {COLUMN} 1.3.6.1.4.1.248.32.18.1.3.43.248.1.4
hmStatusWlanClientRoamingStatisticsEntryOldPhySignal OBJECT-TYPE
    SYNTAX     Integer32 (0..255)
    MAX-ACCESS read-only
    STATUS     current
    DESCRIPTION
            "-- empty --"
    ::= { hmStatusWlanClientRoamingStatisticsEntry 4 }

-- {COLUMN} 1.3.6.1.4.1.248.32.18.1.3.43.248.1.5
hmStatusWlanClientRoamingStatisticsEntryNewBssid OBJECT-TYPE
    SYNTAX     MacAddress
    MAX-ACCESS read-only
    STATUS     current
    DESCRIPTION
            "-- empty --"
    ::= { hmStatusWlanClientRoamingStatisticsEntry 5 }

-- {COLUMN} 1.3.6.1.4.1.248.32.18.1.3.43.248.1.6
hmStatusWlanClientRoamingStatisticsEntryNewApName OBJECT-TYPE
    SYNTAX     DisplayString (SIZE(0..255))
    MAX-ACCESS read-only
    STATUS     current
    DESCRIPTION
            "-- empty --"
    ::= { hmStatusWlanClientRoamingStatisticsEntry 6 }

-- {COLUMN} 1.3.6.1.4.1.248.32.18.1.3.43.248.1.7
hmStatusWlanClientRoamingStatisticsEntryNewChannel OBJECT-TYPE
    SYNTAX     Integer32 (0..255)
    MAX-ACCESS read-only
    STATUS     current
    DESCRIPTION
            "-- empty --"
    ::= { hmStatusWlanClientRoamingStatisticsEntry 7 }

-- {COLUMN} 1.3.6.1.4.1.248.32.18.1.3.43.248.1.8
hmStatusWlanClientRoamingStatisticsEntryNewPhySignal OBJECT-TYPE
    SYNTAX     Integer32 (0..255)
    MAX-ACCESS read-only
    STATUS     current
    DESCRIPTION
            "-- empty --"
    ::= { hmStatusWlanClientRoamingStatisticsEntry 8 }

-- {COLUMN} 1.3.6.1.4.1.248.32.18.1.3.43.248.1.9
hmStatusWlanClientRoamingStatisticsEntryRoamCount OBJECT-TYPE
    SYNTAX     Counter32
    MAX-ACCESS read-only
    STATUS     current
    DESCRIPTION
            "-- empty --"
    ::= { hmStatusWlanClientRoamingStatisticsEntry 9 }

-- {COLUMN} 1.3.6.1.4.1.248.32.18.1.3.43.248.1.10
hmStatusWlanClientRoamingStatisticsEntryAge OBJECT-TYPE
    SYNTAX     Integer32 (0..2147483647)
    MAX-ACCESS read-only
    STATUS     current
    DESCRIPTION
            "-- empty --"
    ::= { hmStatusWlanClientRoamingStatisticsEntry 10 }

-- {TABLE} 1.3.6.1.4.1.248.32.18.1.3.44
hmStatusWlanCompetingNetworksTable OBJECT-TYPE
    SYNTAX     SEQUENCE OF HmStatusWlanCompetingNetworksEntry
    MAX-ACCESS not-accessible
    STATUS     current
    DESCRIPTION
            "-- empty --"
    ::= { hmStatusWlan 44 }

-- {ROW} 1.3.6.1.4.1.248.32.18.1.3.44.1
hmStatusWlanCompetingNetworksEntry OBJECT-TYPE
    SYNTAX     HmStatusWlanCompetingNetworksEntry
    MAX-ACCESS not-accessible
    STATUS     current
    DESCRIPTION
            ""
    INDEX {
            hmStatusWlanCompetingNetworksEntryBssid,
            hmStatusWlanCompetingNetworksEntryInterface
          }
    ::= { hmStatusWlanCompetingNetworksTable 1 }

HmStatusWlanCompetingNetworksEntry ::= SEQUENCE {
            hmStatusWlanCompetingNetworksEntryBssid MacAddress,
            hmStatusWlanCompetingNetworksEntryNetworkName DisplayString,
            hmStatusWlanCompetingNetworksEntryOperationMode INTEGER,
            hmStatusWlanCompetingNetworksEntryBeaconPeriod Integer32,
            hmStatusWlanCompetingNetworksEntryDtimPeriod Integer32,
            hmStatusWlanCompetingNetworksEntryRadioChannel Integer32,
            hmStatusWlanCompetingNetworksEntryPhySignal Integer32,
            hmStatusWlanCompetingNetworksEntryNoiseLevel Integer32,
            hmStatusWlanCompetingNetworksEntryLoad DisplayString,
            hmStatusWlanCompetingNetworksEntryEncryption INTEGER,
            hmStatusWlanCompetingNetworksEntryShortPreamble INTEGER,
            hmStatusWlanCompetingNetworksEntryInterface INTEGER,
            hmStatusWlanCompetingNetworksEntryRadioBand INTEGER,
            hmStatusWlanCompetingNetworksEntry108mbpsMode INTEGER,
            hmStatusWlanCompetingNetworksEntryShortSlotTime INTEGER,
            hmStatusWlanCompetingNetworksEntryRate INTEGER,
            hmStatusWlanCompetingNetworksEntryNonerpPresent INTEGER,
            hmStatusWlanCompetingNetworksEntryCompression INTEGER,
            hmStatusWlanCompetingNetworksEntryPcfFunctionality INTEGER,
            hmStatusWlanCompetingNetworksEntryIdentification DisplayString,
            hmStatusWlanCompetingNetworksEntryQos INTEGER,
            hmStatusWlanCompetingNetworksEntryAge Integer32,
            hmStatusWlanCompetingNetworksEntrySignalLevel Integer32,
            hmStatusWlanCompetingNetworksEntryShortGuardInterval INTEGER,
            hmStatusWlanCompetingNetworksEntryExtChannel INTEGER,
            hmStatusWlanCompetingNetworksEntry40mhzMode INTEGER,
            hmStatusWlanCompetingNetworksEntry40mhzIntolerant INTEGER,
            hmStatusWlanCompetingNetworksEntryInterpointPeerName DisplayString,
            hmStatusWlanCompetingNetworksEntryMaxAMpduLen Integer32,
            hmStatusWlanCompetingNetworksEntryMaxAMsduLen Integer32,
            hmStatusWlanCompetingNetworksEntryVendor DisplayString,
            hmStatusWlanCompetingNetworksEntryEffRate Integer32,
            hmStatusWlanCompetingNetworksEntry40mhzCoexistence INTEGER,
            hmStatusWlanCompetingNetworksEntryPreAuthentication INTEGER,
            hmStatusWlanCompetingNetworksEntryTxStbc INTEGER,
            hmStatusWlanCompetingNetworksEntryRxStbc INTEGER,
            hmStatusWlanCompetingNetworksEntryEapolPreauthFailed INTEGER,
            hmStatusWlanCompetingNetworksEntryLdpc INTEGER,
            hmStatusWlanCompetingNetworksEntryAutowds INTEGER,
            hmStatusWlanCompetingNetworksEntrySGIMask BITS,
            hmStatusWlanCompetingNetworksEntryChannelBandwidths BITS,
            hmStatusWlanCompetingNetworksEntryChannelBandwidth INTEGER,
            hmStatusWlanCompetingNetworksEntryClBrgSupport INTEGER,
            hmStatusWlanCompetingNetworksEntryProtMgmtFrames INTEGER,
            hmStatusWlanCompetingNetworksEntryTxPowerLimit DisplayString,
            hmStatusWlanCompetingNetworksEntryTxSTBCMask BITS,
            hmStatusWlanCompetingNetworksEntryRxStbcHt INTEGER,
            hmStatusWlanCompetingNetworksEntryRxStbcVht INTEGER,
            hmStatusWlanCompetingNetworksEntryLDPCMask BITS,
            hmStatusWlanCompetingNetworksEntryClBrgRoamingSupport INTEGER
    }

-- {COLUMN} 1.3.6.1.4.1.248.32.18.1.3.44.1.1
hmStatusWlanCompetingNetworksEntryBssid OBJECT-TYPE
    SYNTAX     MacAddress
    MAX-ACCESS read-only
    STATUS     current
    DESCRIPTION
            "-- empty --"
    ::= { hmStatusWlanCompetingNetworksEntry 1 }

-- {COLUMN} 1.3.6.1.4.1.248.32.18.1.3.44.1.2
hmStatusWlanCompetingNetworksEntryNetworkName OBJECT-TYPE
    SYNTAX     DisplayString (SIZE(0..255))
    MAX-ACCESS read-only
    STATUS     current
    DESCRIPTION
            "-- empty --"
    ::= { hmStatusWlanCompetingNetworksEntry 2 }

-- {COLUMN} 1.3.6.1.4.1.248.32.18.1.3.44.1.3
hmStatusWlanCompetingNetworksEntryOperationMode OBJECT-TYPE
    SYNTAX     INTEGER {
                  eNone (0),
                  eAdhoc (1),
                  eInfrastructure (2)
            }
    MAX-ACCESS read-only
    STATUS     current
    DESCRIPTION
            "hirschmann's description of operation mode"
    ::= { hmStatusWlanCompetingNetworksEntry 3 }

-- {COLUMN} 1.3.6.1.4.1.248.32.18.1.3.44.1.6
hmStatusWlanCompetingNetworksEntryBeaconPeriod OBJECT-TYPE
    SYNTAX     Integer32 (0..65535)
    MAX-ACCESS read-only
    STATUS     current
    DESCRIPTION
            "-- empty --"
    ::= { hmStatusWlanCompetingNetworksEntry 6 }

-- {COLUMN} 1.3.6.1.4.1.248.32.18.1.3.44.1.7
hmStatusWlanCompetingNetworksEntryDtimPeriod OBJECT-TYPE
    SYNTAX     Integer32 (0..65535)
    MAX-ACCESS read-only
    STATUS     current
    DESCRIPTION
            "-- empty --"
    ::= { hmStatusWlanCompetingNetworksEntry 7 }

-- {COLUMN} 1.3.6.1.4.1.248.32.18.1.3.44.1.8
hmStatusWlanCompetingNetworksEntryRadioChannel OBJECT-TYPE
    SYNTAX     Integer32 (0..255)
    MAX-ACCESS read-only
    STATUS     current
    DESCRIPTION
            "-- empty --"
    ::= { hmStatusWlanCompetingNetworksEntry 8 }

-- {COLUMN} 1.3.6.1.4.1.248.32.18.1.3.44.1.10
hmStatusWlanCompetingNetworksEntryPhySignal OBJECT-TYPE
    SYNTAX     Integer32 (0..65535)
    MAX-ACCESS read-only
    STATUS     current
    DESCRIPTION
            "-- empty --"
    ::= { hmStatusWlanCompetingNetworksEntry 10 }

-- {COLUMN} 1.3.6.1.4.1.248.32.18.1.3.44.1.11
hmStatusWlanCompetingNetworksEntryNoiseLevel OBJECT-TYPE
    SYNTAX     Integer32 (-128..127)
    MAX-ACCESS read-only
    STATUS     current
    DESCRIPTION
            "-- empty --"
    ::= { hmStatusWlanCompetingNetworksEntry 11 }

-- {COLUMN} 1.3.6.1.4.1.248.32.18.1.3.44.1.12
hmStatusWlanCompetingNetworksEntryLoad OBJECT-TYPE
    SYNTAX     DisplayString (SIZE(0..255))
    MAX-ACCESS read-only
    STATUS     current
    DESCRIPTION
            "-- empty --"
    ::= { hmStatusWlanCompetingNetworksEntry 12 }

-- {COLUMN} 1.3.6.1.4.1.248.32.18.1.3.44.1.13
hmStatusWlanCompetingNetworksEntryEncryption OBJECT-TYPE
    SYNTAX     INTEGER {
                  eNone (0),
                  eWep (1),
                  eTkip (2),
                  eAes (3),
                  eAesPlusTkip (4)
            }
    MAX-ACCESS read-only
    STATUS     current
    DESCRIPTION
            "-- empty --"
    ::= { hmStatusWlanCompetingNetworksEntry 13 }

-- {COLUMN} 1.3.6.1.4.1.248.32.18.1.3.44.1.14
hmStatusWlanCompetingNetworksEntryShortPreamble OBJECT-TYPE
    SYNTAX     INTEGER {
                  eNo (0),
                  eYes (1)
            }
    MAX-ACCESS read-only
    STATUS     current
    DESCRIPTION
            "-- empty --"
    ::= { hmStatusWlanCompetingNetworksEntry 14 }

-- {COLUMN} 1.3.6.1.4.1.248.32.18.1.3.44.1.15
hmStatusWlanCompetingNetworksEntryInterface OBJECT-TYPE
    SYNTAX     INTEGER {
                  eWlan1 (0),
                  eWlan2 (1),
                  eWlan3 (2),
                  eWlan4 (3)
            }
    MAX-ACCESS read-only
    STATUS     current
    DESCRIPTION
            "-- empty --"
    ::= { hmStatusWlanCompetingNetworksEntry 15 }

-- {COLUMN} 1.3.6.1.4.1.248.32.18.1.3.44.1.16
hmStatusWlanCompetingNetworksEntryRadioBand OBJECT-TYPE
    SYNTAX     INTEGER {
                  eUnknown (0),
                  e24ghz (1),
                  e5ghz (2)
            }
    MAX-ACCESS read-only
    STATUS     current
    DESCRIPTION
            "-- empty --"
    ::= { hmStatusWlanCompetingNetworksEntry 16 }

-- {COLUMN} 1.3.6.1.4.1.248.32.18.1.3.44.1.17
hmStatusWlanCompetingNetworksEntry108mbpsMode OBJECT-TYPE
    SYNTAX     INTEGER {
                  eNo (0),
                  eYes (1)
            }
    MAX-ACCESS read-only
    STATUS     current
    DESCRIPTION
            "-- empty --"
    ::= { hmStatusWlanCompetingNetworksEntry 17 }

-- {COLUMN} 1.3.6.1.4.1.248.32.18.1.3.44.1.18
hmStatusWlanCompetingNetworksEntryShortSlotTime OBJECT-TYPE
    SYNTAX     INTEGER {
                  eNo (0),
                  eYes (1)
            }
    MAX-ACCESS read-only
    STATUS     current
    DESCRIPTION
            "-- empty --"
    ::= { hmStatusWlanCompetingNetworksEntry 18 }

-- {COLUMN} 1.3.6.1.4.1.248.32.18.1.3.44.1.19
hmStatusWlanCompetingNetworksEntryRate OBJECT-TYPE
    SYNTAX     INTEGER {
                  eUnknown (0),
                  e1M (1),
                  e2M (2),
                  e5M (3),
                  e5M5 (4),
                  e8M (5),
                  e11M (6),
                  e6M (12),
                  e9M (13),
                  e12M (14),
                  e18M (15),
                  e24M (16),
                  e36M (17),
                  e48M (18),
                  e54M (19),
                  eT12M (20),
                  eT18M (21),
                  eT24M (22),
                  eT36M (23),
                  eT48M (24),
                  eT72M (25),
                  eT96M (26),
                  eT108M (27),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eHT4S26M (52),
                  eHT4S52M (53),
                  eHT4S78M (54),
                  eHT4S104M (55),
                  eHT4S156M (56),
                  eHT4S208M (57),
                  eHT4S234M (58),
                  eHT4S260M (59),
                  eHTDUP6M (60),
                  eHtMcs33 (61),
                  eHtMcs34 (62),
                  eHtMcs35 (63),
                  eHtMcs36 (64),
                  eHtMcs37 (65),
                  eHtMcs38 (66),
                  eHtMcs39 (67),
                  eHtMcs40 (68),
                  eHtMcs41 (69),
                  eHtMcs42 (70),
                  eHtMcs43 (71),
                  eHtMcs44 (72),
                  eHtMcs45 (73),
                  eHtMcs46 (74),
                  eHtMcs47 (75),
                  eHtMcs48 (76),
                  eHtMcs49 (77),
                  eHtMcs50 (78),
                  eHtMcs51 (79),
                  eHtMcs52 (80),
                  eHtMcs53 (81),
                  eHtMcs54 (82),
                  eHtMcs55 (83),
                  eHtMcs56 (84),
                  eHtMcs57 (85),
                  eHtMcs58 (86),
                  eHtMcs59 (87),
                  eHtMcs60 (88),
                  eHtMcs61 (89),
                  eHtMcs62 (90),
                  eHtMcs63 (91),
                  eHtMcs64 (92),
                  eHtMcs65 (93),
                  eHtMcs66 (94),
                  eHtMcs67 (95),
                  eHtMcs68 (96),
                  eHtMcs69 (97),
                  eHtMcs70 (98),
                  eHtMcs71 (99),
                  eHtMcs72 (100),
                  eHtMcs73 (101),
                  eHtMcs74 (102),
                  eHtMcs75 (103),
                  eHtMcs76 (104),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            "-- empty --"
    ::= { hmStatusWlanCompetingNetworksEntry 19 }

-- {COLUMN} 1.3.6.1.4.1.248.32.18.1.3.44.1.20
hmStatusWlanCompetingNetworksEntryNonerpPresent OBJECT-TYPE
    SYNTAX     INTEGER {
                  eNo (0),
                  eYes (1)
            }
    MAX-ACCESS read-only
    STATUS     current
    DESCRIPTION
            "-- empty --"
    ::= { hmStatusWlanCompetingNetworksEntry 20 }

-- {COLUMN} 1.3.6.1.4.1.248.32.18.1.3.44.1.21
hmStatusWlanCompetingNetworksEntryCompression OBJECT-TYPE
    SYNTAX     INTEGER {
                  eNo (0),
                  eYes (1)
            }
    MAX-ACCESS read-only
    STATUS     current
    DESCRIPTION
            "-- empty --"
    ::= { hmStatusWlanCompetingNetworksEntry 21 }

-- {COLUMN} 1.3.6.1.4.1.248.32.18.1.3.44.1.22
hmStatusWlanCompetingNetworksEntryPcfFunctionality OBJECT-TYPE
    SYNTAX     INTEGER {
                  eNone (0),
                  eDelivery (1),
                  eDeliveryPlusPolling (2)
            }
    MAX-ACCESS read-only
    STATUS     current
    DESCRIPTION
            "-- empty --"
    ::= { hmStatusWlanCompetingNetworksEntry 22 }

-- {COLUMN} 1.3.6.1.4.1.248.32.18.1.3.44.1.23
hmStatusWlanCompetingNetworksEntryIdentification OBJECT-TYPE
    SYNTAX     DisplayString (SIZE(0..16))
    MAX-ACCESS read-only
    STATUS     current
    DESCRIPTION
            "-- empty --"
    ::= { hmStatusWlanCompetingNetworksEntry 23 }

-- {COLUMN} 1.3.6.1.4.1.248.32.18.1.3.44.1.24
hmStatusWlanCompetingNetworksEntryQos OBJECT-TYPE
    SYNTAX     INTEGER {
                  eNo (0),
                  eYes (1)
            }
    MAX-ACCESS read-only
    STATUS     current
    DESCRIPTION
            "-- empty --"
    ::= { hmStatusWlanCompetingNetworksEntry 24 }

-- {COLUMN} 1.3.6.1.4.1.248.32.18.1.3.44.1.25
hmStatusWlanCompetingNetworksEntryAge OBJECT-TYPE
    SYNTAX     Integer32 (0..2147483647)
    MAX-ACCESS read-only
    STATUS     current
    DESCRIPTION
            "-- empty --"
    ::= { hmStatusWlanCompetingNetworksEntry 25 }

-- {COLUMN} 1.3.6.1.4.1.248.32.18.1.3.44.1.26
hmStatusWlanCompetingNetworksEntrySignalLevel OBJECT-TYPE
    SYNTAX     Integer32 (-32768..32767)
    MAX-ACCESS read-only
    STATUS     current
    DESCRIPTION
            "-- empty --"
    ::= { hmStatusWlanCompetingNetworksEntry 26 }

-- {COLUMN} 1.3.6.1.4.1.248.32.18.1.3.44.1.27
hmStatusWlanCompetingNetworksEntryShortGuardInterval OBJECT-TYPE
    SYNTAX     INTEGER {
                  eNo (0),
                  e20mhz (1),
                  e40mhz (2),
                  e2040mhz (3)
            }
    MAX-ACCESS read-only
    STATUS     current
    DESCRIPTION
            "-- empty --"
    ::= { hmStatusWlanCompetingNetworksEntry 27 }

-- {COLUMN} 1.3.6.1.4.1.248.32.18.1.3.44.1.28
hmStatusWlanCompetingNetworksEntryExtChannel OBJECT-TYPE
    SYNTAX     INTEGER {
                  eNone (0),
                  eAbove (1),
                  eBelow (3)
            }
    MAX-ACCESS read-only
    STATUS     current
    DESCRIPTION
            "-- empty --"
    ::= { hmStatusWlanCompetingNetworksEntry 28 }

-- {COLUMN} 1.3.6.1.4.1.248.32.18.1.3.44.1.29
hmStatusWlanCompetingNetworksEntry40mhzMode OBJECT-TYPE
    SYNTAX     INTEGER {
                  eNo (0),
                  eYes (1)
            }
    MAX-ACCESS read-only
    STATUS     current
    DESCRIPTION
            "-- empty --"
    ::= { hmStatusWlanCompetingNetworksEntry 29 }

-- {COLUMN} 1.3.6.1.4.1.248.32.18.1.3.44.1.30
hmStatusWlanCompetingNetworksEntry40mhzIntolerant OBJECT-TYPE
    SYNTAX     INTEGER {
                  eNo (0),
                  eYes (1)
            }
    MAX-ACCESS read-only
    STATUS     current
    DESCRIPTION
            "-- empty --"
    ::= { hmStatusWlanCompetingNetworksEntry 30 }

-- {COLUMN} 1.3.6.1.4.1.248.32.18.1.3.44.1.31
hmStatusWlanCompetingNetworksEntryInterpointPeerName OBJECT-TYPE
    SYNTAX     DisplayString (SIZE(0..24))
    MAX-ACCESS read-only
    STATUS     current
    DESCRIPTION
            "-- empty --"
    ::= { hmStatusWlanCompetingNetworksEntry 31 }

-- {COLUMN} 1.3.6.1.4.1.248.32.18.1.3.44.1.32
hmStatusWlanCompetingNetworksEntryMaxAMpduLen OBJECT-TYPE
    SYNTAX     Integer32 (0..2147483647)
    MAX-ACCESS read-only
    STATUS     current
    DESCRIPTION
            "-- empty --"
    ::= { hmStatusWlanCompetingNetworksEntry 32 }

-- {COLUMN} 1.3.6.1.4.1.248.32.18.1.3.44.1.33
hmStatusWlanCompetingNetworksEntryMaxAMsduLen OBJECT-TYPE
    SYNTAX     Integer32 (0..2147483647)
    MAX-ACCESS read-only
    STATUS     current
    DESCRIPTION
            "-- empty --"
    ::= { hmStatusWlanCompetingNetworksEntry 33 }

-- {COLUMN} 1.3.6.1.4.1.248.32.18.1.3.44.1.34
hmStatusWlanCompetingNetworksEntryVendor OBJECT-TYPE
    SYNTAX     DisplayString (SIZE(0..255))
    MAX-ACCESS read-only
    STATUS     current
    DESCRIPTION
            "-- empty --"
    ::= { hmStatusWlanCompetingNetworksEntry 34 }

-- {COLUMN} 1.3.6.1.4.1.248.32.18.1.3.44.1.35
hmStatusWlanCompetingNetworksEntryEffRate OBJECT-TYPE
    SYNTAX     Integer32 (0..2147483647)
    MAX-ACCESS read-only
    STATUS     current
    DESCRIPTION
            "-- empty --"
    ::= { hmStatusWlanCompetingNetworksEntry 35 }

-- {COLUMN} 1.3.6.1.4.1.248.32.18.1.3.44.1.36
hmStatusWlanCompetingNetworksEntry40mhzCoexistence OBJECT-TYPE
    SYNTAX     INTEGER {
                  eNo (0),
                  eYes (1)
            }
    MAX-ACCESS read-only
    STATUS     current
    DESCRIPTION
            "-- empty --"
    ::= { hmStatusWlanCompetingNetworksEntry 36 }

-- {COLUMN} 1.3.6.1.4.1.248.32.18.1.3.44.1.37
hmStatusWlanCompetingNetworksEntryPreAuthentication OBJECT-TYPE
    SYNTAX     INTEGER {
                  eNo (0),
                  eYes (1)
            }
    MAX-ACCESS read-only
    STATUS     current
    DESCRIPTION
            "-- empty --"
    ::= { hmStatusWlanCompetingNetworksEntry 37 }

-- {COLUMN} 1.3.6.1.4.1.248.32.18.1.3.44.1.38
hmStatusWlanCompetingNetworksEntryTxStbc OBJECT-TYPE
    SYNTAX     INTEGER {
                  eNo (0),
                  eYes (1)
            }
    MAX-ACCESS read-only
    STATUS     current
    DESCRIPTION
            "-- empty --"
    ::= { hmStatusWlanCompetingNetworksEntry 38 }

-- {COLUMN} 1.3.6.1.4.1.248.32.18.1.3.44.1.39
hmStatusWlanCompetingNetworksEntryRxStbc OBJECT-TYPE
    SYNTAX     INTEGER {
                  eNone (0),
                  eOne (1),
                  eTwo (2),
                  eThree (3)
            }
    MAX-ACCESS read-only
    STATUS     current
    DESCRIPTION
            "-- empty --"
    ::= { hmStatusWlanCompetingNetworksEntry 39 }

-- {COLUMN} 1.3.6.1.4.1.248.32.18.1.3.44.1.40
hmStatusWlanCompetingNetworksEntryEapolPreauthFailed OBJECT-TYPE
    SYNTAX     INTEGER {
                  eNo (0),
                  eYes (1)
            }
    MAX-ACCESS read-only
    STATUS     current
    DESCRIPTION
            "-- empty --"
    ::= { hmStatusWlanCompetingNetworksEntry 40 }

-- {COLUMN} 1.3.6.1.4.1.248.32.18.1.3.44.1.41
hmStatusWlanCompetingNetworksEntryLdpc OBJECT-TYPE
    SYNTAX     INTEGER {
                  eNo (0),
                  eYes (1)
            }
    MAX-ACCESS read-only
    STATUS     current
    DESCRIPTION
            "-- empty --"
    ::= { hmStatusWlanCompetingNetworksEntry 41 }

-- {COLUMN} 1.3.6.1.4.1.248.32.18.1.3.44.1.42
hmStatusWlanCompetingNetworksEntryAutowds OBJECT-TYPE
    SYNTAX     INTEGER {
                  eNo (0),
                  eYes (1)
            }
    MAX-ACCESS read-only
    STATUS     current
    DESCRIPTION
            "-- empty --"
    ::= { hmStatusWlanCompetingNetworksEntry 42 }

-- {COLUMN} 1.3.6.1.4.1.248.32.18.1.3.44.1.43
hmStatusWlanCompetingNetworksEntrySGIMask OBJECT-TYPE
    SYNTAX     BITS {
                  eNo (0),
                  e160mhz (28),
                  e80mhz (29),
                  e40mhz (30),
                  e20mhz (31)
            }
    MAX-ACCESS read-only
    STATUS     current
    DESCRIPTION
            "Bit mask of short guard interval support per-CBW"
    ::= { hmStatusWlanCompetingNetworksEntry 43 }

-- {COLUMN} 1.3.6.1.4.1.248.32.18.1.3.44.1.44
hmStatusWlanCompetingNetworksEntryChannelBandwidths OBJECT-TYPE
    SYNTAX     BITS {
                  eT40mhz (26),
                  e80Plus80mhz (27),
                  e160mhz (28),
                  e80mhz (29),
                  e40mhz (30),
                  e20mhz (31)
            }
    MAX-ACCESS read-only
    STATUS     current
    DESCRIPTION
            "-- empty --"
    ::= { hmStatusWlanCompetingNetworksEntry 44 }

-- {COLUMN} 1.3.6.1.4.1.248.32.18.1.3.44.1.45
hmStatusWlanCompetingNetworksEntryChannelBandwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { hmStatusWlanCompetingNetworksEntry 45 }

-- {COLUMN} 1.3.6.1.4.1.248.32.18.1.3.44.1.46
hmStatusWlanCompetingNetworksEntryClBrgSupport OBJECT-TYPE
    SYNTAX     INTEGER {
                  eNo (0),
                  eYes (1)
            }
    MAX-ACCESS read-only
    STATUS     current
    DESCRIPTION
            "-- empty --"
    ::= { hmStatusWlanCompetingNetworksEntry 46 }

-- {COLUMN} 1.3.6.1.4.1.248.32.18.1.3.44.1.47
hmStatusWlanCompetingNetworksEntryProtMgmtFrames OBJECT-TYPE
    SYNTAX     INTEGER {
                  eNo (0),
                  eOptional (1),
                  eMandatory (2)
            }
    MAX-ACCESS read-only
    STATUS     current
    DESCRIPTION
            "-- empty --"
    ::= { hmStatusWlanCompetingNetworksEntry 47 }

-- {COLUMN} 1.3.6.1.4.1.248.32.18.1.3.44.1.48
hmStatusWlanCompetingNetworksEntryTxPowerLimit OBJECT-TYPE
    SYNTAX     DisplayString (SIZE(0..255))
    MAX-ACCESS read-only
    STATUS     current
    DESCRIPTION
            "-- empty --"
    ::= { hmStatusWlanCompetingNetworksEntry 48 }

-- {COLUMN} 1.3.6.1.4.1.248.32.18.1.3.44.1.49
hmStatusWlanCompetingNetworksEntryTxSTBCMask OBJECT-TYPE
    SYNTAX     BITS {
                  eVht (30),
                  eHt (31)
            }
    MAX-ACCESS read-only
    STATUS     current
    DESCRIPTION
            "Bit mask of Tx STBC support per-PHY-Type"
    ::= { hmStatusWlanCompetingNetworksEntry 49 }

-- {COLUMN} 1.3.6.1.4.1.248.32.18.1.3.44.1.50
hmStatusWlanCompetingNetworksEntryRxStbcHt OBJECT-TYPE
    SYNTAX     INTEGER {
                  eNone (0),
                  eOne (1),
                  eTwo (2),
                  eThree (3)
            }
    MAX-ACCESS read-only
    STATUS     current
    DESCRIPTION
            "-- empty --"
    ::= { hmStatusWlanCompetingNetworksEntry 50 }

-- {COLUMN} 1.3.6.1.4.1.248.32.18.1.3.44.1.51
hmStatusWlanCompetingNetworksEntryRxStbcVht OBJECT-TYPE
    SYNTAX     INTEGER {
                  eNone (0),
                  eOne (1),
                  eTwo (2),
                  eThree (3),
                  eFour (4),
                  eFive (5),
                  eSix (6),
                  eSeven (7)
            }
    MAX-ACCESS read-only
    STATUS     current
    DESCRIPTION
            "-- empty --"
    ::= { hmStatusWlanCompetingNetworksEntry 51 }

-- {COLUMN} 1.3.6.1.4.1.248.32.18.1.3.44.1.52
hmStatusWlanCompetingNetworksEntryLDPCMask OBJECT-TYPE
    SYNTAX     BITS {
                  eVht (30),
                  eHt (31)
            }
    MAX-ACCESS read-only
    STATUS     current
    DESCRIPTION
            "Bit mask of LDPC support per-PHY-Type"
    ::= { hmStatusWlanCompetingNetworksEntry 52 }

-- {COLUMN} 1.3.6.1.4.1.248.32.18.1.3.44.1.248
hmStatusWlanCompetingNetworksEntryClBrgRoamingSupport OBJECT-TYPE
    SYNTAX     INTEGER {
                  eNo (0),
                  eYes (1)
            }
    MAX-ACCESS read-only
    STATUS     current
    DESCRIPTION
            "-- empty --"
    ::= { hmStatusWlanCompetingNetworksEntry 248 }

-- {TABLE} 1.3.6.1.4.1.248.32.18.1.3.45
hmStatusWlanSeenClientsTable OBJECT-TYPE
    SYNTAX     SEQUENCE OF HmStatusWlanSeenClientsEntry
    MAX-ACCESS not-accessible
    STATUS     current
    DESCRIPTION
            "-- empty --"
    ::= { hmStatusWlan 45 }

-- {ROW} 1.3.6.1.4.1.248.32.18.1.3.45.1
hmStatusWlanSeenClientsEntry OBJECT-TYPE
    SYNTAX     HmStatusWlanSeenClientsEntry
    MAX-ACCESS not-accessible
    STATUS     current
    DESCRIPTION
            ""
    INDEX {
            hmStatusWlanSeenClientsEntryMacAddress,
            hmStatusWlanSeenClientsEntryInterface
          }
    ::= { hmStatusWlanSeenClientsTable 1 }

HmStatusWlanSeenClientsEntry ::= SEQUENCE {
            hmStatusWlanSeenClientsEntryMacAddress MacAddress,
            hmStatusWlanSeenClientsEntryInterface INTEGER,
            hmStatusWlanSeenClientsEntrySignalLevel Integer32,
            hmStatusWlanSeenClientsEntryAge Integer32,
            hmStatusWlanSeenClientsEntryNetworkName DisplayString,
            hmStatusWlanSeenClientsEntryRxPhySignal Integer32,
            hmStatusWlanSeenClientsEntryNumProbes Counter32,
            hmStatusWlanSeenClientsEntryVendor DisplayString,
            hmStatusWlanSeenClientsEntryNumProberspOk Counter32,
            hmStatusWlanSeenClientsEntryNumProberspBad Counter32,
            hmStatusWlanSeenClientsEntryRadioBand INTEGER,
            hmStatusWlanSeenClientsEntryNumProberspSuppressed Counter32
    }

-- {COLUMN} 1.3.6.1.4.1.248.32.18.1.3.45.1.1
hmStatusWlanSeenClientsEntryMacAddress OBJECT-TYPE
    SYNTAX     MacAddress
    MAX-ACCESS read-only
    STATUS     current
    DESCRIPTION
            "-- empty --"
    ::= { hmStatusWlanSeenClientsEntry 1 }

-- {COLUMN} 1.3.6.1.4.1.248.32.18.1.3.45.1.2
hmStatusWlanSeenClientsEntryInterface OBJECT-TYPE
    SYNTAX     INTEGER {
                  eWlan1 (0),
                  eWlan2 (1),
                  eWlan3 (2),
                  eWlan4 (3)
            }
    MAX-ACCESS read-only
    STATUS     current
    DESCRIPTION
            "-- empty --"
    ::= { hmStatusWlanSeenClientsEntry 2 }

-- {COLUMN} 1.3.6.1.4.1.248.32.18.1.3.45.1.3
hmStatusWlanSeenClientsEntrySignalLevel OBJECT-TYPE
    SYNTAX     Integer32 (-128..127)
    MAX-ACCESS read-only
    STATUS     current
    DESCRIPTION
            "-- empty --"
    ::= { hmStatusWlanSeenClientsEntry 3 }

-- {COLUMN} 1.3.6.1.4.1.248.32.18.1.3.45.1.4
hmStatusWlanSeenClientsEntryAge OBJECT-TYPE
    SYNTAX     Integer32 (0..2147483647)
    MAX-ACCESS read-only
    STATUS     current
    DESCRIPTION
            "-- empty --"
    ::= { hmStatusWlanSeenClientsEntry 4 }

-- {COLUMN} 1.3.6.1.4.1.248.32.18.1.3.45.1.5
hmStatusWlanSeenClientsEntryNetworkName OBJECT-TYPE
    SYNTAX     DisplayString (SIZE(0..32))
    MAX-ACCESS read-only
    STATUS     current
    DESCRIPTION
            "-- empty --"
    ::= { hmStatusWlanSeenClientsEntry 5 }

-- {COLUMN} 1.3.6.1.4.1.248.32.18.1.3.45.1.6
hmStatusWlanSeenClientsEntryRxPhySignal OBJECT-TYPE
    SYNTAX     Integer32 (0..65535)
    MAX-ACCESS read-only
    STATUS     current
    DESCRIPTION
            "-- empty --"
    ::= { hmStatusWlanSeenClientsEntry 6 }

-- {COLUMN} 1.3.6.1.4.1.248.32.18.1.3.45.1.7
hmStatusWlanSeenClientsEntryNumProbes OBJECT-TYPE
    SYNTAX     Counter32
    MAX-ACCESS read-only
    STATUS     current
    DESCRIPTION
            "-- empty --"
    ::= { hmStatusWlanSeenClientsEntry 7 }

-- {COLUMN} 1.3.6.1.4.1.248.32.18.1.3.45.1.8
hmStatusWlanSeenClientsEntryVendor OBJECT-TYPE
    SYNTAX     DisplayString (SIZE(0..255))
    MAX-ACCESS read-only
    STATUS     current
    DESCRIPTION
            "-- empty --"
    ::= { hmStatusWlanSeenClientsEntry 8 }

-- {COLUMN} 1.3.6.1.4.1.248.32.18.1.3.45.1.9
hmStatusWlanSeenClientsEntryNumProberspOk OBJECT-TYPE
    SYNTAX     Counter32
    MAX-ACCESS read-only
    STATUS     current
    DESCRIPTION
            "-- empty --"
    ::= { hmStatusWlanSeenClientsEntry 9 }

-- {COLUMN} 1.3.6.1.4.1.248.32.18.1.3.45.1.10
hmStatusWlanSeenClientsEntryNumProberspBad OBJECT-TYPE
    SYNTAX     Counter32
    MAX-ACCESS read-only
    STATUS     current
    DESCRIPTION
            "-- empty --"
    ::= { hmStatusWlanSeenClientsEntry 10 }

-- {COLUMN} 1.3.6.1.4.1.248.32.18.1.3.45.1.11
hmStatusWlanSeenClientsEntryRadioBand OBJECT-TYPE
    SYNTAX     INTEGER {
                  eUnknown (0),
                  e24ghz (1),
                  e5ghz (2)
            }
    MAX-ACCESS read-only
    STATUS     current
    DESCRIPTION
            "-- empty --"
    ::= { hmStatusWlanSeenClientsEntry 11 }

-- {COLUMN} 1.3.6.1.4.1.248.32.18.1.3.45.1.12
hmStatusWlanSeenClientsEntryNumProberspSuppressed OBJECT-TYPE
    SYNTAX     Counter32
    MAX-ACCESS read-only
    STATUS     current
    DESCRIPTION
            "-- empty --"
    ::= { hmStatusWlanSeenClientsEntry 12 }

-- {TABLE} 1.3.6.1.4.1.248.32.18.1.3.46
hmStatusWlanLogTableTable OBJECT-TYPE
    SYNTAX     SEQUENCE OF HmStatusWlanLogTableEntry
    MAX-ACCESS not-accessible
    STATUS     current
    DESCRIPTION
            "-- empty --"
    ::= { hmStatusWlan 46 }

-- {ROW} 1.3.6.1.4.1.248.32.18.1.3.46.1
hmStatusWlanLogTableEntry OBJECT-TYPE
    SYNTAX     HmStatusWlanLogTableEntry
    MAX-ACCESS not-accessible
    STATUS     current
    DESCRIPTION
            ""
    INDEX {
            hmStatusWlanLogTableEntryIndex
          }
    ::= { hmStatusWlanLogTableTable 1 }

HmStatusWlanLogTableEntry ::= SEQUENCE {
            hmStatusWlanLogTableEntryIndex Integer32,
            hmStatusWlanLogTableEntryTime DisplayString,
            hmStatusWlanLogTableEntryInterface INTEGER,
            hmStatusWlanLogTableEntryEvent DisplayString,
            hmStatusWlanLogTableEntryAddress MacAddress,
            hmStatusWlanLogTableEntryReason DisplayString
    }

-- {COLUMN} 1.3.6.1.4.1.248.32.18.1.3.46.1.1
hmStatusWlanLogTableEntryIndex OBJECT-TYPE
    SYNTAX     Integer32 (0..2147483647)
    MAX-ACCESS read-only
    STATUS     current
    DESCRIPTION
            "-- empty --"
    ::= { hmStatusWlanLogTableEntry 1 }

-- {COLUMN} 1.3.6.1.4.1.248.32.18.1.3.46.1.2
hmStatusWlanLogTableEntryTime OBJECT-TYPE
    SYNTAX     DisplayString (SIZE(0..255))
    MAX-ACCESS read-only
    STATUS     current
    DESCRIPTION
            "-- empty --"
    ::= { hmStatusWlanLogTableEntry 2 }

-- {COLUMN} 1.3.6.1.4.1.248.32.18.1.3.46.1.3
hmStatusWlanLogTableEntryInterface OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan22 (32),
                  eWlan23 (33),
                  eWlan24 (34),
                  eWlan25 (35),
                  eWlan26 (36),
                  eWlan27 (37),
                  eWlan28 (38),
                  eP2p11 (1025),
                  eP2p12 (1026),
                  eP2p13 (1027),
                  eP2p14 (1028),
                  eP2p15 (1029),
                  eP2p16 (1030),
                  eP2p21 (1031),
                  eP2p22 (1032),
                  eP2p23 (1033),
                  eP2p24 (1034),
                  eP2p25 (1035),
                  eP2p26 (1036),
                  eP2p17 (1056),
                  eP2p18 (1057),
                  eP2p19 (1058),
                  eP2p110 (1059),
                  eP2p111 (1060),
                  eP2p112 (1061),
                  eP2p113 (1062),
                  eP2p114 (1063),
                  eP2p115 (1064),
                  eP2p116 (1065),
                  eP2p27 (1088),
                  eP2p28 (1089),
                  eP2p29 (1090),
                  eP2p210 (1091),
                  eP2p211 (1092),
                  eP2p212 (1093),
                  eP2p213 (1094),
                  eP2p214 (1095),
                  eP2p215 (1096),
                  eP2p216 (1097)
            }
    MAX-ACCESS read-only
    STATUS     current
    DESCRIPTION
            "-- empty --"
    ::= { hmStatusWlanLogTableEntry 3 }

-- {COLUMN} 1.3.6.1.4.1.248.32.18.1.3.46.1.4
hmStatusWlanLogTableEntryEvent OBJECT-TYPE
    SYNTAX     DisplayString (SIZE(0..255))
    MAX-ACCESS read-only
    STATUS     current
    DESCRIPTION
            "-- empty --"
    ::= { hmStatusWlanLogTableEntry 4 }

-- {COLUMN} 1.3.6.1.4.1.248.32.18.1.3.46.1.5
hmStatusWlanLogTableEntryAddress OBJECT-TYPE
    SYNTAX     MacAddress
    MAX-ACCESS read-only
    STATUS     current
    DESCRIPTION
            "-- empty --"
    ::= { hmStatusWlanLogTableEntry 5 }

-- {COLUMN} 1.3.6.1.4.1.248.32.18.1.3.46.1.6
hmStatusWlanLogTableEntryReason OBJECT-TYPE
    SYNTAX     DisplayString (SIZE(0..255))
    MAX-ACCESS read-only
    STATUS     current
    DESCRIPTION
            "-- empty --"
    ::= { hmStatusWlanLogTableEntry 6 }

-- {TABLE} 1.3.6.1.4.1.248.32.18.1.3.47
hmStatusWlanPairwiseKeysTable OBJECT-TYPE
    SYNTAX     SEQUENCE OF HmStatusWlanPairwiseKeysEntry
    MAX-ACCESS not-accessible
    STATUS     current
    DESCRIPTION
            "-- empty --"
    ::= { hmStatusWlan 47 }

-- {ROW} 1.3.6.1.4.1.248.32.18.1.3.47.1
hmStatusWlanPairwiseKeysEntry OBJECT-TYPE
    SYNTAX     HmStatusWlanPairwiseKeysEntry
    MAX-ACCESS not-accessible
    STATUS     current
    DESCRIPTION
            ""
    INDEX {
            hmStatusWlanPairwiseKeysEntryIndex
          }
    ::= { hmStatusWlanPairwiseKeysTable 1 }

HmStatusWlanPairwiseKeysEntry ::= SEQUENCE {
            hmStatusWlanPairwiseKeysEntryIndex Integer32,
            hmStatusWlanPairwiseKeysEntryKeyType INTEGER,
            hmStatusWlanPairwiseKeysEntryKeyValue DisplayString,
            hmStatusWlanPairwiseKeysEntryTsc DisplayString,
            hmStatusWlanPairwiseKeysEntryAge Integer32,
            hmStatusWlanPairwiseKeysEntryIvSequenceErrors Integer32,
            hmStatusWlanPairwiseKeysEntryRscBe DisplayString,
            hmStatusWlanPairwiseKeysEntryRscBk DisplayString,
            hmStatusWlanPairwiseKeysEntryRscEe DisplayString,
            hmStatusWlanPairwiseKeysEntryRscCl DisplayString,
            hmStatusWlanPairwiseKeysEntryRscVi DisplayString,
            hmStatusWlanPairwiseKeysEntryRscVo DisplayString,
            hmStatusWlanPairwiseKeysEntryRscNc DisplayString,
            hmStatusWlanPairwiseKeysEntryRscMgmt DisplayString
    }

-- {COLUMN} 1.3.6.1.4.1.248.32.18.1.3.47.1.1
hmStatusWlanPairwiseKeysEntryIndex OBJECT-TYPE
    SYNTAX     Integer32 (0..65535)
    MAX-ACCESS read-only
    STATUS     current
    DESCRIPTION
            "-- empty --"
    ::= { hmStatusWlanPairwiseKeysEntry 1 }

-- {COLUMN} 1.3.6.1.4.1.248.32.18.1.3.47.1.3
hmStatusWlanPairwiseKeysEntryKeyType OBJECT-TYPE
    SYNTAX     INTEGER {
                  eNone (0),
                  eUnknown (1),
                  eWep40Bits (5),
                  eWep104Bits (13),
                  eWep128Bits (16),
                  eTkip (64),
                  eAesOcb (65),
                  eAesCcm (66),
                  eBip (68)
            }
    MAX-ACCESS read-only
    STATUS     current
    DESCRIPTION
            "-- empty --"
    ::= { hmStatusWlanPairwiseKeysEntry 3 }

-- {COLUMN} 1.3.6.1.4.1.248.32.18.1.3.47.1.4
hmStatusWlanPairwiseKeysEntryKeyValue OBJECT-TYPE
    SYNTAX     DisplayString (SIZE(0..255))
    MAX-ACCESS read-only
    STATUS     current
    DESCRIPTION
            "-- empty --"
    ::= { hmStatusWlanPairwiseKeysEntry 4 }

-- {COLUMN} 1.3.6.1.4.1.248.32.18.1.3.47.1.5
hmStatusWlanPairwiseKeysEntryTsc OBJECT-TYPE
    SYNTAX     DisplayString (SIZE(0..255))
    MAX-ACCESS read-only
    STATUS     current
    DESCRIPTION
            "-- empty --"
    ::= { hmStatusWlanPairwiseKeysEntry 5 }

-- {COLUMN} 1.3.6.1.4.1.248.32.18.1.3.47.1.7
hmStatusWlanPairwiseKeysEntryAge OBJECT-TYPE
    SYNTAX     Integer32 (0..2147483647)
    MAX-ACCESS read-only
    STATUS     current
    DESCRIPTION
            "-- empty --"
    ::= { hmStatusWlanPairwiseKeysEntry 7 }

-- {COLUMN} 1.3.6.1.4.1.248.32.18.1.3.47.1.8
hmStatusWlanPairwiseKeysEntryIvSequenceErrors OBJECT-TYPE
    SYNTAX     Integer32 (0..2147483647)
    MAX-ACCESS read-only
    STATUS     current
    DESCRIPTION
            "-- empty --"
    ::= { hmStatusWlanPairwiseKeysEntry 8 }

-- {COLUMN} 1.3.6.1.4.1.248.32.18.1.3.47.1.16
hmStatusWlanPairwiseKeysEntryRscBe OBJECT-TYPE
    SYNTAX     DisplayString (SIZE(0..255))
    MAX-ACCESS read-only
    STATUS     current
    DESCRIPTION
            "-- empty --"
    ::= { hmStatusWlanPairwiseKeysEntry 16 }

-- {COLUMN} 1.3.6.1.4.1.248.32.18.1.3.47.1.17
hmStatusWlanPairwiseKeysEntryRscBk OBJECT-TYPE
    SYNTAX     DisplayString (SIZE(0..255))
    MAX-ACCESS read-only
    STATUS     current
    DESCRIPTION
            "-- empty --"
    ::= { hmStatusWlanPairwiseKeysEntry 17 }

-- {COLUMN} 1.3.6.1.4.1.248.32.18.1.3.47.1.19
hmStatusWlanPairwiseKeysEntryRscEe OBJECT-TYPE
    SYNTAX     DisplayString (SIZE(0..255))
    MAX-ACCESS read-only
    STATUS     current
    DESCRIPTION
            "-- empty --"
    ::= { hmStatusWlanPairwiseKeysEntry 19 }

-- {COLUMN} 1.3.6.1.4.1.248.32.18.1.3.47.1.20
hmStatusWlanPairwiseKeysEntryRscCl OBJECT-TYPE
    SYNTAX     DisplayString (SIZE(0..255))
    MAX-ACCESS read-only
    STATUS     current
    DESCRIPTION
            "-- empty --"
    ::= { hmStatusWlanPairwiseKeysEntry 20 }

-- {COLUMN} 1.3.6.1.4.1.248.32.18.1.3.47.1.21
hmStatusWlanPairwiseKeysEntryRscVi OBJECT-TYPE
    SYNTAX     DisplayString (SIZE(0..255))
    MAX-ACCESS read-only
    STATUS     current
    DESCRIPTION
            "-- empty --"
    ::= { hmStatusWlanPairwiseKeysEntry 21 }

-- {COLUMN} 1.3.6.1.4.1.248.32.18.1.3.47.1.22
hmStatusWlanPairwiseKeysEntryRscVo OBJECT-TYPE
    SYNTAX     DisplayString (SIZE(0..255))
    MAX-ACCESS read-only
    STATUS     current
    DESCRIPTION
            "-- empty --"
    ::= { hmStatusWlanPairwiseKeysEntry 22 }

-- {COLUMN} 1.3.6.1.4.1.248.32.18.1.3.47.1.23
hmStatusWlanPairwiseKeysEntryRscNc OBJECT-TYPE
    SYNTAX     DisplayString (SIZE(0..255))
    MAX-ACCESS read-only
    STATUS     current
    DESCRIPTION
            "-- empty --"
    ::= { hmStatusWlanPairwiseKeysEntry 23 }

-- {COLUMN} 1.3.6.1.4.1.248.32.18.1.3.47.1.24
hmStatusWlanPairwiseKeysEntryRscMgmt OBJECT-TYPE
    SYNTAX     DisplayString (SIZE(0..255))
    MAX-ACCESS read-only
    STATUS     current
    DESCRIPTION
            "-- empty --"
    ::= { hmStatusWlanPairwiseKeysEntry 24 }

-- {TABLE} 1.3.6.1.4.1.248.32.18.1.3.48
hmStatusWlanRadiusCacheTable OBJECT-TYPE
    SYNTAX     SEQUENCE OF HmStatusWlanRadiusCacheEntry
    MAX-ACCESS not-accessible
    STATUS     current
    DESCRIPTION
            "-- empty --"
    ::= { hmStatusWlan 48 }

-- {ROW} 1.3.6.1.4.1.248.32.18.1.3.48.1
hmStatusWlanRadiusCacheEntry OBJECT-TYPE
    SYNTAX     HmStatusWlanRadiusCacheEntry
    MAX-ACCESS not-accessible
    STATUS     current
    DESCRIPTION
            ""
    INDEX {
            hmStatusWlanRadiusCacheEntryMacAddress
          }
    ::= { hmStatusWlanRadiusCacheTable 1 }

HmStatusWlanRadiusCacheEntry ::= SEQUENCE {
            hmStatusWlanRadiusCacheEntryMacAddress MacAddress,
            hmStatusWlanRadiusCacheEntryAllowed INTEGER,
            hmStatusWlanRadiusCacheEntryAge Integer32
    }

-- {COLUMN} 1.3.6.1.4.1.248.32.18.1.3.48.1.1
hmStatusWlanRadiusCacheEntryMacAddress OBJECT-TYPE
    SYNTAX     MacAddress
    MAX-ACCESS read-only
    STATUS     current
    DESCRIPTION
            "-- empty --"
    ::= { hmStatusWlanRadiusCacheEntry 1 }

-- {COLUMN} 1.3.6.1.4.1.248.32.18.1.3.48.1.2
hmStatusWlanRadiusCacheEntryAllowed OBJECT-TYPE
    SYNTAX     INTEGER {
                  eNo (0),
                  eYes (1)
            }
    MAX-ACCESS read-only
    STATUS     current
    DESCRIPTION
            "-- empty --"
    ::= { hmStatusWlanRadiusCacheEntry 2 }

-- {COLUMN} 1.3.6.1.4.1.248.32.18.1.3.48.1.3
hmStatusWlanRadiusCacheEntryAge OBJECT-TYPE
    SYNTAX     Integer32 (0..2147483647)
    MAX-ACCESS read-only
    STATUS     current
    DESCRIPTION
            "-- empty --"
    ::= { hmStatusWlanRadiusCacheEntry 3 }

-- {SCALAR} 1.3.6.1.4.1.248.32.18.1.3.49
hmStatusWlanClearLogTable OBJECT-TYPE
    SYNTAX     DisplayString
    MAX-ACCESS read-write
    STATUS     current
    DESCRIPTION
            "-- empty --"
    ::= { hmStatusWlan 49 }

-- {SCALAR} 1.3.6.1.4.1.248.32.18.1.3.50
hmStatusWlanClearSeenClientsTable OBJECT-TYPE
    SYNTAX     DisplayString
    MAX-ACCESS read-write
    STATUS     current
    DESCRIPTION
            "-- empty --"
    ::= { hmStatusWlan 50 }

-- {TABLE} 1.3.6.1.4.1.248.32.18.1.3.51
hmStatusWlanIfcsTable OBJECT-TYPE
    SYNTAX     SEQUENCE OF HmStatusWlanIfcsEntry
    MAX-ACCESS not-accessible
    STATUS     current
    DESCRIPTION
            ""
    ::= { hmStatusWlan 51 }

-- {ROW} 1.3.6.1.4.1.248.32.18.1.3.51.1
hmStatusWlanIfcsEntry OBJECT-TYPE
    SYNTAX     HmStatusWlanIfcsEntry
    MAX-ACCESS not-accessible
    STATUS     current
    DESCRIPTION
            ""
    INDEX {
            hmStatusWlanIfcsEntryIfc
          }
    ::= { hmStatusWlanIfcsTable 1 }

HmStatusWlanIfcsEntry ::= SEQUENCE {
            hmStatusWlanIfcsEntryIfc DisplayString,
            hmStatusWlanIfcsEntryMacAddress MacAddress,
            hmStatusWlanIfcsEntryOperating INTEGER,
            hmStatusWlanIfcsEntryQueuePackets Integer32,
            hmStatusWlanIfcsEntryCardId DisplayString,
            hmStatusWlanIfcsEntryFirmwareVersion DisplayString,
            hmStatusWlanIfcsEntrySerialNumber DisplayString,
            hmStatusWlanIfcsEntryNumStations Integer32,
            hmStatusWlanIfcsEntryOperationMode INTEGER,
            hmStatusWlanIfcsEntryTemperature DisplayString,
            hmStatusWlanIfcsEntryNumericTemperature Integer32
    }

-- {COLUMN} 1.3.6.1.4.1.248.32.18.1.3.51.1.1
hmStatusWlanIfcsEntryIfc OBJECT-TYPE
    SYNTAX     DisplayString (SIZE(0..255))
    MAX-ACCESS read-only
    STATUS     current
    DESCRIPTION
            "-- empty --"
    ::= { hmStatusWlanIfcsEntry 1 }

-- {COLUMN} 1.3.6.1.4.1.248.32.18.1.3.51.1.2
hmStatusWlanIfcsEntryMacAddress OBJECT-TYPE
    SYNTAX     MacAddress
    MAX-ACCESS read-only
    STATUS     current
    DESCRIPTION
            "-- empty --"
    ::= { hmStatusWlanIfcsEntry 2 }

-- {COLUMN} 1.3.6.1.4.1.248.32.18.1.3.51.1.3
hmStatusWlanIfcsEntryOperating OBJECT-TYPE
    SYNTAX     INTEGER {
                  eNo (0),
                  eYes (1)
            }
    MAX-ACCESS read-only
    STATUS     current
    DESCRIPTION
            "-- empty --"
    ::= { hmStatusWlanIfcsEntry 3 }

-- {COLUMN} 1.3.6.1.4.1.248.32.18.1.3.51.1.4
hmStatusWlanIfcsEntryQueuePackets OBJECT-TYPE
    SYNTAX     Integer32 (0..2147483647)
    MAX-ACCESS read-only
    STATUS     current
    DESCRIPTION
            "-- empty --"
    ::= { hmStatusWlanIfcsEntry 4 }

-- {COLUMN} 1.3.6.1.4.1.248.32.18.1.3.51.1.5
hmStatusWlanIfcsEntryCardId OBJECT-TYPE
    SYNTAX     DisplayString (SIZE(0..255))
    MAX-ACCESS read-only
    STATUS     current
    DESCRIPTION
            "-- empty --"
    ::= { hmStatusWlanIfcsEntry 5 }

-- {COLUMN} 1.3.6.1.4.1.248.32.18.1.3.51.1.6
hmStatusWlanIfcsEntryFirmwareVersion OBJECT-TYPE
    SYNTAX     DisplayString (SIZE(0..255))
    MAX-ACCESS read-only
    STATUS     current
    DESCRIPTION
            "-- empty --"
    ::= { hmStatusWlanIfcsEntry 6 }

-- {COLUMN} 1.3.6.1.4.1.248.32.18.1.3.51.1.7
hmStatusWlanIfcsEntrySerialNumber OBJECT-TYPE
    SYNTAX     DisplayString (SIZE(0..255))
    MAX-ACCESS read-only
    STATUS     current
    DESCRIPTION
            "-- empty --"
    ::= { hmStatusWlanIfcsEntry 7 }

-- {COLUMN} 1.3.6.1.4.1.248.32.18.1.3.51.1.8
hmStatusWlanIfcsEntryNumStations OBJECT-TYPE
    SYNTAX     Integer32 (0..65535)
    MAX-ACCESS read-only
    STATUS     current
    DESCRIPTION
            "-- empty --"
    ::= { hmStatusWlanIfcsEntry 8 }

-- {COLUMN} 1.3.6.1.4.1.248.32.18.1.3.51.1.9
hmStatusWlanIfcsEntryOperationMode OBJECT-TYPE
    SYNTAX     INTEGER {
                  eStation (0),
                  eAccessPoint (1),
                  eMonitor (2),
                  eManagedAp (4),
                  eProbe (5),
                  eManagedProbe (6)
            }
    MAX-ACCESS read-only
    STATUS     current
    DESCRIPTION
            "hirschmann's description of operation mode"
    ::= { hmStatusWlanIfcsEntry 9 }

-- {COLUMN} 1.3.6.1.4.1.248.32.18.1.3.51.1.10
hmStatusWlanIfcsEntryTemperature OBJECT-TYPE
    SYNTAX     DisplayString (SIZE(0..255))
    MAX-ACCESS read-only
    STATUS     current
    DESCRIPTION
            "-- empty --"
    ::= { hmStatusWlanIfcsEntry 10 }

-- {COLUMN} 1.3.6.1.4.1.248.32.18.1.3.51.1.11
hmStatusWlanIfcsEntryNumericTemperature OBJECT-TYPE
    SYNTAX     Integer32 (-32768..32767)
    MAX-ACCESS read-only
    STATUS     current
    DESCRIPTION
            "-- empty --"
    ::= { hmStatusWlanIfcsEntry 11 }

-- {TABLE} 1.3.6.1.4.1.248.32.18.1.3.52
hmStatusWlanByteTransportTable OBJECT-TYPE
    SYNTAX     SEQUENCE OF HmStatusWlanByteTransportEntry
    MAX-ACCESS not-accessible
    STATUS     current
    DESCRIPTION
            "-- empty --"
    ::= { hmStatusWlan 52 }

-- {ROW} 1.3.6.1.4.1.248.32.18.1.3.52.1
hmStatusWlanByteTransportEntry OBJECT-TYPE
    SYNTAX     HmStatusWlanByteTransportEntry
    MAX-ACCESS not-accessible
    STATUS     current
    DESCRIPTION
            ""
    INDEX {
            hmStatusWlanByteTransportEntryIfc
          }
    ::= { hmStatusWlanByteTransportTable 1 }

HmStatusWlanByteTransportEntry ::= SEQUENCE {
            hmStatusWlanByteTransportEntryIfc DisplayString,
            hmStatusWlanByteTransportEntryTxBytes Counter64,
            hmStatusWlanByteTransportEntryRxBytes Counter64,
            hmStatusWlanByteTransportEntryThroughput DisplayString,
            hmStatusWlanByteTransportEntryMaxThroughput DisplayString,
            hmStatusWlanByteTransportEntryBytesThroughput Integer32,
            hmStatusWlanByteTransportEntryBytesMaxThroughput Integer32
    }

-- {COLUMN} 1.3.6.1.4.1.248.32.18.1.3.52.1.1
hmStatusWlanByteTransportEntryIfc OBJECT-TYPE
    SYNTAX     DisplayString (SIZE(0..255))
    MAX-ACCESS read-only
    STATUS     current
    DESCRIPTION
            "-- empty --"
    ::= { hmStatusWlanByteTransportEntry 1 }

-- {COLUMN} 1.3.6.1.4.1.248.32.18.1.3.52.1.2
hmStatusWlanByteTransportEntryTxBytes OBJECT-TYPE
    SYNTAX     Counter64
    MAX-ACCESS read-only
    STATUS     current
    DESCRIPTION
            "-- empty --"
    ::= { hmStatusWlanByteTransportEntry 2 }

-- {COLUMN} 1.3.6.1.4.1.248.32.18.1.3.52.1.3
hmStatusWlanByteTransportEntryRxBytes OBJECT-TYPE
    SYNTAX     Counter64
    MAX-ACCESS read-only
    STATUS     current
    DESCRIPTION
            "-- empty --"
    ::= { hmStatusWlanByteTransportEntry 3 }

-- {COLUMN} 1.3.6.1.4.1.248.32.18.1.3.52.1.4
hmStatusWlanByteTransportEntryThroughput OBJECT-TYPE
    SYNTAX     DisplayString (SIZE(0..255))
    MAX-ACCESS read-only
    STATUS     current
    DESCRIPTION
            "-- empty --"
    ::= { hmStatusWlanByteTransportEntry 4 }

-- {COLUMN} 1.3.6.1.4.1.248.32.18.1.3.52.1.5
hmStatusWlanByteTransportEntryMaxThroughput OBJECT-TYPE
    SYNTAX     DisplayString (SIZE(0..255))
    MAX-ACCESS read-only
    STATUS     current
    DESCRIPTION
            "-- empty --"
    ::= { hmStatusWlanByteTransportEntry 5 }

-- {COLUMN} 1.3.6.1.4.1.248.32.18.1.3.52.1.6
hmStatusWlanByteTransportEntryBytesThroughput OBJECT-TYPE
    SYNTAX     Integer32 (0..2147483647)
    MAX-ACCESS read-only
    STATUS     current
    DESCRIPTION
            "-- empty --"
    ::= { hmStatusWlanByteTransportEntry 6 }

-- {COLUMN} 1.3.6.1.4.1.248.32.18.1.3.52.1.7
hmStatusWlanByteTransportEntryBytesMaxThroughput OBJECT-TYPE
    SYNTAX     Integer32 (0..2147483647)
    MAX-ACCESS read-only
    STATUS     current
    DESCRIPTION
            "-- empty --"
    ::= { hmStatusWlanByteTransportEntry 7 }

-- {TABLE} 1.3.6.1.4.1.248.32.18.1.3.53
hmStatusWlanPacketTransportTable OBJECT-TYPE
    SYNTAX     SEQUENCE OF HmStatusWlanPacketTransportEntry
    MAX-ACCESS not-accessible
    STATUS     current
    DESCRIPTION
            "-- empty --"
    ::= { hmStatusWlan 53 }

-- {ROW} 1.3.6.1.4.1.248.32.18.1.3.53.1
hmStatusWlanPacketTransportEntry OBJECT-TYPE
    SYNTAX     HmStatusWlanPacketTransportEntry
    MAX-ACCESS not-accessible
    STATUS     current
    DESCRIPTION
            ""
    INDEX {
            hmStatusWlanPacketTransportEntryIfc
          }
    ::= { hmStatusWlanPacketTransportTable 1 }

HmStatusWlanPacketTransportEntry ::= SEQUENCE {
            hmStatusWlanPacketTransportEntryIfc DisplayString,
            hmStatusWlanPacketTransportEntryRxPackets Counter32,
            hmStatusWlanPacketTransportEntryTxPackets Counter32,
            hmStatusWlanPacketTransportEntryRxBroadcasts Counter32,
            hmStatusWlanPacketTransportEntryRxMulticasts Counter32,
            hmStatusWlanPacketTransportEntryRxUnicasts Counter32,
            hmStatusWlanPacketTransportEntryTxBroadcasts Counter32,
            hmStatusWlanPacketTransportEntryTxMulticasts Counter32,
            hmStatusWlanPacketTransportEntryTxUnicasts Counter32,
            hmStatusWlanPacketTransportEntryTxAggregates Counter32,
            hmStatusWlanPacketTransportEntryTxAggrFrames Counter32,
            hmStatusWlanPacketTransportEntryRxAggregates Counter32,
            hmStatusWlanPacketTransportEntryRxAggrFrames Counter32,
            hmStatusWlanPacketTransportEntryRxAMsdu Counter32,
            hmStatusWlanPacketTransportEntryRxFft Counter32
    }

-- {COLUMN} 1.3.6.1.4.1.248.32.18.1.3.53.1.1
hmStatusWlanPacketTransportEntryIfc OBJECT-TYPE
    SYNTAX     DisplayString (SIZE(0..255))
    MAX-ACCESS read-only
    STATUS     current
    DESCRIPTION
            "-- empty --"
    ::= { hmStatusWlanPacketTransportEntry 1 }

-- {COLUMN} 1.3.6.1.4.1.248.32.18.1.3.53.1.2
hmStatusWlanPacketTransportEntryRxPackets OBJECT-TYPE
    SYNTAX     Counter32
    MAX-ACCESS read-only
    STATUS     current
    DESCRIPTION
            "-- empty --"
    ::= { hmStatusWlanPacketTransportEntry 2 }

-- {COLUMN} 1.3.6.1.4.1.248.32.18.1.3.53.1.3
hmStatusWlanPacketTransportEntryTxPackets OBJECT-TYPE
    SYNTAX     Counter32
    MAX-ACCESS read-only
    STATUS     current
    DESCRIPTION
            "-- empty --"
    ::= { hmStatusWlanPacketTransportEntry 3 }

-- {COLUMN} 1.3.6.1.4.1.248.32.18.1.3.53.1.4
hmStatusWlanPacketTransportEntryRxBroadcasts OBJECT-TYPE
    SYNTAX     Counter32
    MAX-ACCESS read-only
    STATUS     current
    DESCRIPTION
            "-- empty --"
    ::= { hmStatusWlanPacketTransportEntry 4 }

-- {COLUMN} 1.3.6.1.4.1.248.32.18.1.3.53.1.5
hmStatusWlanPacketTransportEntryRxMulticasts OBJECT-TYPE
    SYNTAX     Counter32
    MAX-ACCESS read-only
    STATUS     current
    DESCRIPTION
            "-- empty --"
    ::= { hmStatusWlanPacketTransportEntry 5 }

-- {COLUMN} 1.3.6.1.4.1.248.32.18.1.3.53.1.6
hmStatusWlanPacketTransportEntryRxUnicasts OBJECT-TYPE
    SYNTAX     Counter32
    MAX-ACCESS read-only
    STATUS     current
    DESCRIPTION
            "-- empty --"
    ::= { hmStatusWlanPacketTransportEntry 6 }

-- {COLUMN} 1.3.6.1.4.1.248.32.18.1.3.53.1.7
hmStatusWlanPacketTransportEntryTxBroadcasts OBJECT-TYPE
    SYNTAX     Counter32
    MAX-ACCESS read-only
    STATUS     current
    DESCRIPTION
            "-- empty --"
    ::= { hmStatusWlanPacketTransportEntry 7 }

-- {COLUMN} 1.3.6.1.4.1.248.32.18.1.3.53.1.8
hmStatusWlanPacketTransportEntryTxMulticasts OBJECT-TYPE
    SYNTAX     Counter32
    MAX-ACCESS read-only
    STATUS     current
    DESCRIPTION
            "-- empty --"
    ::= { hmStatusWlanPacketTransportEntry 8 }

-- {COLUMN} 1.3.6.1.4.1.248.32.18.1.3.53.1.9
hmStatusWlanPacketTransportEntryTxUnicasts OBJECT-TYPE
    SYNTAX     Counter32
    MAX-ACCESS read-only
    STATUS     current
    DESCRIPTION
            "-- empty --"
    ::= { hmStatusWlanPacketTransportEntry 9 }

-- {COLUMN} 1.3.6.1.4.1.248.32.18.1.3.53.1.12
hmStatusWlanPacketTransportEntryTxAggregates OBJECT-TYPE
    SYNTAX     Counter32
    MAX-ACCESS read-only
    STATUS     current
    DESCRIPTION
            "-- empty --"
    ::= { hmStatusWlanPacketTransportEntry 12 }

-- {COLUMN} 1.3.6.1.4.1.248.32.18.1.3.53.1.13
hmStatusWlanPacketTransportEntryTxAggrFrames OBJECT-TYPE
    SYNTAX     Counter32
    MAX-ACCESS read-only
    STATUS     current
    DESCRIPTION
            "-- empty --"
    ::= { hmStatusWlanPacketTransportEntry 13 }

-- {COLUMN} 1.3.6.1.4.1.248.32.18.1.3.53.1.14
hmStatusWlanPacketTransportEntryRxAggregates OBJECT-TYPE
    SYNTAX     Counter32
    MAX-ACCESS read-only
    STATUS     current
    DESCRIPTION
            "-- empty --"
    ::= { hmStatusWlanPacketTransportEntry 14 }

-- {COLUMN} 1.3.6.1.4.1.248.32.18.1.3.53.1.15
hmStatusWlanPacketTransportEntryRxAggrFrames OBJECT-TYPE
    SYNTAX     Counter32
    MAX-ACCESS read-only
    STATUS     current
    DESCRIPTION
            "-- empty --"
    ::= { hmStatusWlanPacketTransportEntry 15 }

-- {COLUMN} 1.3.6.1.4.1.248.32.18.1.3.53.1.16
hmStatusWlanPacketTransportEntryRxAMsdu OBJECT-TYPE
    SYNTAX     Counter32
    MAX-ACCESS read-only
    STATUS     current
    DESCRIPTION
            "-- empty --"
    ::= { hmStatusWlanPacketTransportEntry 16 }

-- {COLUMN} 1.3.6.1.4.1.248.32.18.1.3.53.1.17
hmStatusWlanPacketTransportEntryRxFft OBJECT-TYPE
    SYNTAX     Counter32
    MAX-ACCESS read-only
    STATUS     current
    DESCRIPTION
            "-- empty --"
    ::= { hmStatusWlanPacketTransportEntry 17 }

-- {TABLE} 1.3.6.1.4.1.248.32.18.1.3.54
hmStatusWlanErrorsTable OBJECT-TYPE
    SYNTAX     SEQUENCE OF HmStatusWlanErrorsEntry
    MAX-ACCESS not-accessible
    STATUS     current
    DESCRIPTION
            "-- empty --"
    ::= { hmStatusWlan 54 }

-- {ROW} 1.3.6.1.4.1.248.32.18.1.3.54.1
hmStatusWlanErrorsEntry OBJECT-TYPE
    SYNTAX     HmStatusWlanErrorsEntry
    MAX-ACCESS not-accessible
    STATUS     current
    DESCRIPTION
            ""
    INDEX {
            hmStatusWlanErrorsEntryIfc
          }
    ::= { hmStatusWlanErrorsTable 1 }

HmStatusWlanErrorsEntry ::= SEQUENCE {
            hmStatusWlanErrorsEntryIfc DisplayString,
            hmStatusWlanErrorsEntryRxErrors Counter32,
            hmStatusWlanErrorsEntryTxErrors Counter32,
            hmStatusWlanErrorsEntryStackErrors Counter32,
            hmStatusWlanErrorsEntryNicErrors Counter32,
            hmStatusWlanErrorsEntryQueueErrors Counter32,
            hmStatusWlanErrorsEntryTxDiscarded Counter32,
            hmStatusWlanErrorsEntryRetries Counter32,
            hmStatusWlanErrorsEntryMultipleRetries Counter32,
            hmStatusWlanErrorsEntryUndecryptables Counter32,
            hmStatusWlanErrorsEntryDupeDiscarded Counter32,
            hmStatusWlanErrorsEntryAged Counter32,
            hmStatusWlanErrorsEntryMichaelErrors Counter32,
            hmStatusWlanErrorsEntryIvSequenceErrors Counter32,
            hmStatusWlanErrorsEntryRxCrcErrors Counter32,
            hmStatusWlanErrorsEntrySoftRetries Counter32,
            hmStatusWlanErrorsEntryRxAggrDiscarded Counter32,
            hmStatusWlanErrorsEntryRxPhyErrors Counter32,
            hmStatusWlanErrorsEntryRxFifoOverflow Counter32,
            hmStatusWlanErrorsEntryTxFifoUnderflow Counter32,
            hmStatusWlanErrorsEntryBusErrors Counter32,
            hmStatusWlanErrorsEntryRxRestarts Counter32,
            hmStatusWlanErrorsEntryRxDscrUnderflow Counter32,
            hmStatusWlanErrorsEntryAgcCalibrateFailures Counter32,
            hmStatusWlanErrorsEntryBbTimeouts Counter32,
            hmStatusWlanErrorsEntryRxErrorRatio Counter32,
            hmStatusWlanErrorsEntryTxErrorRatio Counter32
    }

-- {COLUMN} 1.3.6.1.4.1.248.32.18.1.3.54.1.1
hmStatusWlanErrorsEntryIfc OBJECT-TYPE
    SYNTAX     DisplayString (SIZE(0..255))
    MAX-ACCESS read-only
    STATUS     current
    DESCRIPTION
            "-- empty --"
    ::= { hmStatusWlanErrorsEntry 1 }

-- {COLUMN} 1.3.6.1.4.1.248.32.18.1.3.54.1.2
hmStatusWlanErrorsEntryRxErrors OBJECT-TYPE
    SYNTAX     Counter32
    MAX-ACCESS read-only
    STATUS     current
    DESCRIPTION
            "-- empty --"
    ::= { hmStatusWlanErrorsEntry 2 }

-- {COLUMN} 1.3.6.1.4.1.248.32.18.1.3.54.1.3
hmStatusWlanErrorsEntryTxErrors OBJECT-TYPE
    SYNTAX     Counter32
    MAX-ACCESS read-only
    STATUS     current
    DESCRIPTION
            "-- empty --"
    ::= { hmStatusWlanErrorsEntry 3 }

-- {COLUMN} 1.3.6.1.4.1.248.32.18.1.3.54.1.4
hmStatusWlanErrorsEntryStackErrors OBJECT-TYPE
    SYNTAX     Counter32
    MAX-ACCESS read-only
    STATUS     current
    DESCRIPTION
            "-- empty --"
    ::= { hmStatusWlanErrorsEntry 4 }

-- {COLUMN} 1.3.6.1.4.1.248.32.18.1.3.54.1.5
hmStatusWlanErrorsEntryNicErrors OBJECT-TYPE
    SYNTAX     Counter32
    MAX-ACCESS read-only
    STATUS     current
    DESCRIPTION
            "-- empty --"
    ::= { hmStatusWlanErrorsEntry 5 }

-- {COLUMN} 1.3.6.1.4.1.248.32.18.1.3.54.1.6
hmStatusWlanErrorsEntryQueueErrors OBJECT-TYPE
    SYNTAX     Counter32
    MAX-ACCESS read-only
    STATUS     current
    DESCRIPTION
            "-- empty --"
    ::= { hmStatusWlanErrorsEntry 6 }

-- {COLUMN} 1.3.6.1.4.1.248.32.18.1.3.54.1.7
hmStatusWlanErrorsEntryTxDiscarded OBJECT-TYPE
    SYNTAX     Counter32
    MAX-ACCESS read-only
    STATUS     current
    DESCRIPTION
            "-- empty --"
    ::= { hmStatusWlanErrorsEntry 7 }

-- {COLUMN} 1.3.6.1.4.1.248.32.18.1.3.54.1.8
hmStatusWlanErrorsEntryRetries OBJECT-TYPE
    SYNTAX     Counter32
    MAX-ACCESS read-only
    STATUS     current
    DESCRIPTION
            "-- empty --"
    ::= { hmStatusWlanErrorsEntry 8 }

-- {COLUMN} 1.3.6.1.4.1.248.32.18.1.3.54.1.9
hmStatusWlanErrorsEntryMultipleRetries OBJECT-TYPE
    SYNTAX     Counter32
    MAX-ACCESS read-only
    STATUS     current
    DESCRIPTION
            "-- empty --"
    ::= { hmStatusWlanErrorsEntry 9 }

-- {COLUMN} 1.3.6.1.4.1.248.32.18.1.3.54.1.10
hmStatusWlanErrorsEntryUndecryptables OBJECT-TYPE
    SYNTAX     Counter32
    MAX-ACCESS read-only
    STATUS     current
    DESCRIPTION
            "-- empty --"
    ::= { hmStatusWlanErrorsEntry 10 }

-- {COLUMN} 1.3.6.1.4.1.248.32.18.1.3.54.1.11
hmStatusWlanErrorsEntryDupeDiscarded OBJECT-TYPE
    SYNTAX     Counter32
    MAX-ACCESS read-only
    STATUS     current
    DESCRIPTION
            "-- empty --"
    ::= { hmStatusWlanErrorsEntry 11 }

-- {COLUMN} 1.3.6.1.4.1.248.32.18.1.3.54.1.13
hmStatusWlanErrorsEntryAged OBJECT-TYPE
    SYNTAX     Counter32
    MAX-ACCESS read-only
    STATUS     current
    DESCRIPTION
            "-- empty --"
    ::= { hmStatusWlanErrorsEntry 13 }

-- {COLUMN} 1.3.6.1.4.1.248.32.18.1.3.54.1.14
hmStatusWlanErrorsEntryMichaelErrors OBJECT-TYPE
    SYNTAX     Counter32
    MAX-ACCESS read-only
    STATUS     current
    DESCRIPTION
            "-- empty --"
    ::= { hmStatusWlanErrorsEntry 14 }

-- {COLUMN} 1.3.6.1.4.1.248.32.18.1.3.54.1.15
hmStatusWlanErrorsEntryIvSequenceErrors OBJECT-TYPE
    SYNTAX     Counter32
    MAX-ACCESS read-only
    STATUS     current
    DESCRIPTION
            "-- empty --"
    ::= { hmStatusWlanErrorsEntry 15 }

-- {COLUMN} 1.3.6.1.4.1.248.32.18.1.3.54.1.16
hmStatusWlanErrorsEntryRxCrcErrors OBJECT-TYPE
    SYNTAX     Counter32
    MAX-ACCESS read-only
    STATUS     current
    DESCRIPTION
            "-- empty --"
    ::= { hmStatusWlanErrorsEntry 16 }

-- {COLUMN} 1.3.6.1.4.1.248.32.18.1.3.54.1.17
hmStatusWlanErrorsEntrySoftRetries OBJECT-TYPE
    SYNTAX     Counter32
    MAX-ACCESS read-only
    STATUS     current
    DESCRIPTION
            "-- empty --"
    ::= { hmStatusWlanErrorsEntry 17 }

-- {COLUMN} 1.3.6.1.4.1.248.32.18.1.3.54.1.18
hmStatusWlanErrorsEntryRxAggrDiscarded OBJECT-TYPE
    SYNTAX     Counter32
    MAX-ACCESS read-only
    STATUS     current
    DESCRIPTION
            "-- empty --"
    ::= { hmStatusWlanErrorsEntry 18 }

-- {COLUMN} 1.3.6.1.4.1.248.32.18.1.3.54.1.19
hmStatusWlanErrorsEntryRxPhyErrors OBJECT-TYPE
    SYNTAX     Counter32
    MAX-ACCESS read-only
    STATUS     current
    DESCRIPTION
            "-- empty --"
    ::= { hmStatusWlanErrorsEntry 19 }

-- {COLUMN} 1.3.6.1.4.1.248.32.18.1.3.54.1.20
hmStatusWlanErrorsEntryRxFifoOverflow OBJECT-TYPE
    SYNTAX     Counter32
    MAX-ACCESS read-only
    STATUS     current
    DESCRIPTION
            "-- empty --"
    ::= { hmStatusWlanErrorsEntry 20 }

-- {COLUMN} 1.3.6.1.4.1.248.32.18.1.3.54.1.21
hmStatusWlanErrorsEntryTxFifoUnderflow OBJECT-TYPE
    SYNTAX     Counter32
    MAX-ACCESS read-only
    STATUS     current
    DESCRIPTION
            "-- empty --"
    ::= { hmStatusWlanErrorsEntry 21 }

-- {COLUMN} 1.3.6.1.4.1.248.32.18.1.3.54.1.22
hmStatusWlanErrorsEntryBusErrors OBJECT-TYPE
    SYNTAX     Counter32
    MAX-ACCESS read-only
    STATUS     current
    DESCRIPTION
            "-- empty --"
    ::= { hmStatusWlanErrorsEntry 22 }

-- {COLUMN} 1.3.6.1.4.1.248.32.18.1.3.54.1.23
hmStatusWlanErrorsEntryRxRestarts OBJECT-TYPE
    SYNTAX     Counter32
    MAX-ACCESS read-only
    STATUS     current
    DESCRIPTION
            "-- empty --"
    ::= { hmStatusWlanErrorsEntry 23 }

-- {COLUMN} 1.3.6.1.4.1.248.32.18.1.3.54.1.24
hmStatusWlanErrorsEntryRxDscrUnderflow OBJECT-TYPE
    SYNTAX     Counter32
    MAX-ACCESS read-only
    STATUS     current
    DESCRIPTION
            "-- empty --"
    ::= { hmStatusWlanErrorsEntry 24 }

-- {COLUMN} 1.3.6.1.4.1.248.32.18.1.3.54.1.25
hmStatusWlanErrorsEntryAgcCalibrateFailures OBJECT-TYPE
    SYNTAX     Counter32
    MAX-ACCESS read-only
    STATUS     current
    DESCRIPTION
            "-- empty --"
    ::= { hmStatusWlanErrorsEntry 25 }

-- {COLUMN} 1.3.6.1.4.1.248.32.18.1.3.54.1.26
hmStatusWlanErrorsEntryBbTimeouts OBJECT-TYPE
    SYNTAX     Counter32
    MAX-ACCESS read-only
    STATUS     current
    DESCRIPTION
            "-- empty --"
    ::= { hmStatusWlanErrorsEntry 26 }

-- {COLUMN} 1.3.6.1.4.1.248.32.18.1.3.54.1.27
hmStatusWlanErrorsEntryRxErrorRatio OBJECT-TYPE
    SYNTAX     Counter32
    MAX-ACCESS read-only
    STATUS     current
    DESCRIPTION
            "-- empty --"
    ::= { hmStatusWlanErrorsEntry 27 }

-- {COLUMN} 1.3.6.1.4.1.248.32.18.1.3.54.1.28
hmStatusWlanErrorsEntryTxErrorRatio OBJECT-TYPE
    SYNTAX     Counter32
    MAX-ACCESS read-only
    STATUS     current
    DESCRIPTION
            "-- empty --"
    ::= { hmStatusWlanErrorsEntry 28 }

-- {TABLE} 1.3.6.1.4.1.248.32.18.1.3.55
hmStatusWlanWlanParameterTable OBJECT-TYPE
    SYNTAX     SEQUENCE OF HmStatusWlanWlanParameterEntry
    MAX-ACCESS not-accessible
    STATUS     current
    DESCRIPTION
            "-- empty --"
    ::= { hmStatusWlan 55 }

-- {ROW} 1.3.6.1.4.1.248.32.18.1.3.55.1
hmStatusWlanWlanParameterEntry OBJECT-TYPE
    SYNTAX     HmStatusWlanWlanParameterEntry
    MAX-ACCESS not-accessible
    STATUS     current
    DESCRIPTION
            ""
    INDEX {
            hmStatusWlanWlanParameterEntryIfc
          }
    ::= { hmStatusWlanWlanParameterTable 1 }

HmStatusWlanWlanParameterEntry ::= SEQUENCE {
            hmStatusWlanWlanParameterEntryIfc DisplayString,
            hmStatusWlanWlanParameterEntryRadioChannel Integer32,
            hmStatusWlanWlanParameterEntryRegulatoryDomain INTEGER,
            hmStatusWlanWlanParameterEntryPhyType INTEGER,
            hmStatusWlanWlanParameterEntryWepSupport INTEGER,
            hmStatusWlanWlanParameterEntryMaximumRate INTEGER,
            hmStatusWlanWlanParameterEntryTemperatureRange INTEGER,
            hmStatusWlanWlanParameterEntryPhyVariant DisplayString,
            hmStatusWlanWlanParameterEntryRadioBand INTEGER,
            hmStatusWlanWlanParameterEntrySupportedBands INTEGER,
            hmStatusWlanWlanParameterEntryNoiseLevel Integer32,
            hmStatusWlanWlanParameterEntrySupportsShortPreamble INTEGER,
            hmStatusWlanWlanParameterEntryTransmitPower DisplayString,
            hmStatusWlanWlanParameterEntry108mbpsMode INTEGER,
            hmStatusWlanWlanParameterEntrySupportsShortSlotTime INTEGER,
            hmStatusWlanWlanParameterEntryTkipSupport INTEGER,
            hmStatusWlanWlanParameterEntryAesSupport INTEGER,
            hmStatusWlanWlanParameterEntrySupportsCompression INTEGER,
            hmStatusWlanWlanParameterEntryMinimumRate INTEGER,
            hmStatusWlanWlanParameterEntryEirp DisplayString,
            hmStatusWlanWlanParameterEntryExcEirp INTEGER,
            hmStatusWlanWlanParameterEntryModemLoad Integer32,
            hmStatusWlanWlanParameterEntryBeaconPeriod Integer32,
            hmStatusWlanWlanParameterEntrySupportsShortGuardInterval INTEGER,
            hmStatusWlanWlanParameterEntrySupports40mhz INTEGER,
            hmStatusWlanWlanParameterEntryTxChains Integer32,
            hmStatusWlanWlanParameterEntryRxChains Integer32,
            hmStatusWlanWlanParameterEntrySupportedDfsSchemes BITS,
            hmStatusWlanWlanParameterEntrySupportedAntennas INTEGER,
            hmStatusWlanWlanParameterEntryRxStbc INTEGER,
            hmStatusWlanWlanParameterEntryLdpc INTEGER,
            hmStatusWlanWlanParameterEntryCountry INTEGER,
            hmStatusWlanWlanParameterEntrySupportsSpectralScan INTEGER,
            hmStatusWlanWlanParameterEntrySGIMask BITS,
            hmStatusWlanWlanParameterEntryChannelBandwidths BITS,
            hmStatusWlanWlanParameterEntryChannelBandwidth INTEGER,
            hmStatusWlanWlanParameterEntryProtMgmtFrames INTEGER,
            hmStatusWlanWlanParameterEntryRxStbcHt INTEGER,
            hmStatusWlanWlanParameterEntryRxStbcVht INTEGER,
            hmStatusWlanWlanParameterEntryLDPCMask BITS
    }

-- {COLUMN} 1.3.6.1.4.1.248.32.18.1.3.55.1.1
hmStatusWlanWlanParameterEntryIfc OBJECT-TYPE
    SYNTAX     DisplayString (SIZE(0..255))
    MAX-ACCESS read-only
    STATUS     current
    DESCRIPTION
            "-- empty --"
    ::= { hmStatusWlanWlanParameterEntry 1 }

-- {COLUMN} 1.3.6.1.4.1.248.32.18.1.3.55.1.3
hmStatusWlanWlanParameterEntryRadioChannel OBJECT-TYPE
    SYNTAX     Integer32 (0..255)
    MAX-ACCESS read-only
    STATUS     current
    DESCRIPTION
            "-- empty --"
    ::= { hmStatusWlanWlanParameterEntry 3 }

-- {COLUMN} 1.3.6.1.4.1.248.32.18.1.3.55.1.4
hmStatusWlanWlanParameterEntryRegulatoryDomain OBJECT-TYPE
    SYNTAX     INTEGER {
                  eUndefined (0),
                  eFcc (16),
                  eCanada (32),
                  eEuEtsi (48),
                  eSpain (49),
                  eFrance (50),
                  eMkkJapan (64),
                  eMkk2Japan (65),
                  eIsrael (80),
                  eWorld (96)
            }
    MAX-ACCESS read-only
    STATUS     current
    DESCRIPTION
            "-- empty --"
    ::= { hmStatusWlanWlanParameterEntry 4 }

-- {COLUMN} 1.3.6.1.4.1.248.32.18.1.3.55.1.5
hmStatusWlanWlanParameterEntryPhyType OBJECT-TYPE
    SYNTAX     INTEGER {
                  eProprietary (0),
                  eFhss (1),
                  eDsss (2),
                  eInfrared (3),
                  eOfdm (4),
                  eHrDsss (5),
                  eErp (6),
                  eHt (7),
                  eVht (9),
                  ePbcc (254)
            }
    MAX-ACCESS read-only
    STATUS     current
    DESCRIPTION
            "-- empty --"
    ::= { hmStatusWlanWlanParameterEntry 5 }

-- {COLUMN} 1.3.6.1.4.1.248.32.18.1.3.55.1.7
hmStatusWlanWlanParameterEntryWepSupport OBJECT-TYPE
    SYNTAX     INTEGER {
                  eNo (0),
                  eYes40Bits (1),
                  eYes104Bits (2),
                  eYes128Bits (3)
            }
    MAX-ACCESS read-only
    STATUS     current
    DESCRIPTION
            "-- empty --"
    ::= { hmStatusWlanWlanParameterEntry 7 }

-- {COLUMN} 1.3.6.1.4.1.248.32.18.1.3.55.1.8
hmStatusWlanWlanParameterEntryMaximumRate OBJECT-TYPE
    SYNTAX     INTEGER {
                  eUnknown (0),
                  e1M (1),
                  e2M (2),
                  e5M (3),
                  e5M5 (4),
                  e8M (5),
                  e11M (6),
                  e6M (12),
                  e9M (13),
                  e12M (14),
                  e18M (15),
                  e24M (16),
                  e36M (17),
                  e48M (18),
                  e54M (19),
                  eT12M (20),
                  eT18M (21),
                  eT24M (22),
                  eT36M (23),
                  eT48M (24),
                  eT72M (25),
                  eT96M (26),
                  eT108M (27),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eHT4S26M (52),
                  eHT4S52M (53),
                  eHT4S78M (54),
                  eHT4S104M (55),
                  eHT4S156M (56),
                  eHT4S208M (57),
                  eHT4S234M (58),
                  eHT4S260M (59),
                  eHTDUP6M (60),
                  eHtMcs33 (61),
                  eHtMcs34 (62),
                  eHtMcs35 (63),
                  eHtMcs36 (64),
                  eHtMcs37 (65),
                  eHtMcs38 (66),
                  eHtMcs39 (67),
                  eHtMcs40 (68),
                  eHtMcs41 (69),
                  eHtMcs42 (70),
                  eHtMcs43 (71),
                  eHtMcs44 (72),
                  eHtMcs45 (73),
                  eHtMcs46 (74),
                  eHtMcs47 (75),
                  eHtMcs48 (76),
                  eHtMcs49 (77),
                  eHtMcs50 (78),
                  eHtMcs51 (79),
                  eHtMcs52 (80),
                  eHtMcs53 (81),
                  eHtMcs54 (82),
                  eHtMcs55 (83),
                  eHtMcs56 (84),
                  eHtMcs57 (85),
                  eHtMcs58 (86),
                  eHtMcs59 (87),
                  eHtMcs60 (88),
                  eHtMcs61 (89),
                  eHtMcs62 (90),
                  eHtMcs63 (91),
                  eHtMcs64 (92),
                  eHtMcs65 (93),
                  eHtMcs66 (94),
                  eHtMcs67 (95),
                  eHtMcs68 (96),
                  eHtMcs69 (97),
                  eHtMcs70 (98),
                  eHtMcs71 (99),
                  eHtMcs72 (100),
                  eHtMcs73 (101),
                  eHtMcs74 (102),
                  eHtMcs75 (103),
                  eHtMcs76 (104),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            "-- empty --"
    ::= { hmStatusWlanWlanParameterEntry 8 }

-- {COLUMN} 1.3.6.1.4.1.248.32.18.1.3.55.1.9
hmStatusWlanWlanParameterEntryTemperatureRange OBJECT-TYPE
    SYNTAX     INTEGER {
                  eUnknown (0),
                  eCommercial0Plus40DegreeC (1),
                  eIndustrial30Plus70DegreeC (2)
            }
    MAX-ACCESS read-only
    STATUS     current
    DESCRIPTION
            "-- empty --"
    ::= { hmStatusWlanWlanParameterEntry 9 }

-- {COLUMN} 1.3.6.1.4.1.248.32.18.1.3.55.1.10
hmStatusWlanWlanParameterEntryPhyVariant OBJECT-TYPE
    SYNTAX     DisplayString (SIZE(0..15))
    MAX-ACCESS read-only
    STATUS     current
    DESCRIPTION
            "-- empty --"
    ::= { hmStatusWlanWlanParameterEntry 10 }

-- {COLUMN} 1.3.6.1.4.1.248.32.18.1.3.55.1.11
hmStatusWlanWlanParameterEntryRadioBand OBJECT-TYPE
    SYNTAX     INTEGER {
                  eUnknown (0),
                  e24ghz (1),
                  e5ghz (2)
            }
    MAX-ACCESS read-only
    STATUS     current
    DESCRIPTION
            "-- empty --"
    ::= { hmStatusWlanWlanParameterEntry 11 }

-- {COLUMN} 1.3.6.1.4.1.248.32.18.1.3.55.1.12
hmStatusWlanWlanParameterEntrySupportedBands OBJECT-TYPE
    SYNTAX     INTEGER {
                  eUnknown (0),
                  e24ghz (1),
                  e5ghz (2),
                  e24ghz5ghz (3)
            }
    MAX-ACCESS read-only
    STATUS     current
    DESCRIPTION
            "-- empty --"
    ::= { hmStatusWlanWlanParameterEntry 12 }

-- {COLUMN} 1.3.6.1.4.1.248.32.18.1.3.55.1.13
hmStatusWlanWlanParameterEntryNoiseLevel OBJECT-TYPE
    SYNTAX     Integer32 (-32768..32767)
    MAX-ACCESS read-only
    STATUS     current
    DESCRIPTION
            "-- empty --"
    ::= { hmStatusWlanWlanParameterEntry 13 }

-- {COLUMN} 1.3.6.1.4.1.248.32.18.1.3.55.1.14
hmStatusWlanWlanParameterEntrySupportsShortPreamble OBJECT-TYPE
    SYNTAX     INTEGER {
                  eNo (0),
                  eYes (1)
            }
    MAX-ACCESS read-only
    STATUS     current
    DESCRIPTION
            "-- empty --"
    ::= { hmStatusWlanWlanParameterEntry 14 }

-- {COLUMN} 1.3.6.1.4.1.248.32.18.1.3.55.1.15
hmStatusWlanWlanParameterEntryTransmitPower OBJECT-TYPE
    SYNTAX     DisplayString (SIZE(0..255))
    MAX-ACCESS read-only
    STATUS     current
    DESCRIPTION
            "-- empty --"
    ::= { hmStatusWlanWlanParameterEntry 15 }

-- {COLUMN} 1.3.6.1.4.1.248.32.18.1.3.55.1.16
hmStatusWlanWlanParameterEntry108mbpsMode OBJECT-TYPE
    SYNTAX     INTEGER {
                  eNo (0),
                  eYes (1)
            }
    MAX-ACCESS read-only
    STATUS     current
    DESCRIPTION
            "-- empty --"
    ::= { hmStatusWlanWlanParameterEntry 16 }

-- {COLUMN} 1.3.6.1.4.1.248.32.18.1.3.55.1.17
hmStatusWlanWlanParameterEntrySupportsShortSlotTime OBJECT-TYPE
    SYNTAX     INTEGER {
                  eNo (0),
                  eYes (1)
            }
    MAX-ACCESS read-only
    STATUS     current
    DESCRIPTION
            "-- empty --"
    ::= { hmStatusWlanWlanParameterEntry 17 }

-- {COLUMN} 1.3.6.1.4.1.248.32.18.1.3.55.1.18
hmStatusWlanWlanParameterEntryTkipSupport OBJECT-TYPE
    SYNTAX     INTEGER {
                  eNo (0),
                  eYes (1)
            }
    MAX-ACCESS read-only
    STATUS     current
    DESCRIPTION
            "-- empty --"
    ::= { hmStatusWlanWlanParameterEntry 18 }

-- {COLUMN} 1.3.6.1.4.1.248.32.18.1.3.55.1.19
hmStatusWlanWlanParameterEntryAesSupport OBJECT-TYPE
    SYNTAX     INTEGER {
                  eNo (0),
                  eOcb (1),
                  eCcm (2),
                  eOcbPlusCcm (3)
            }
    MAX-ACCESS read-only
    STATUS     current
    DESCRIPTION
            "-- empty --"
    ::= { hmStatusWlanWlanParameterEntry 19 }

-- {COLUMN} 1.3.6.1.4.1.248.32.18.1.3.55.1.20
hmStatusWlanWlanParameterEntrySupportsCompression OBJECT-TYPE
    SYNTAX     INTEGER {
                  eNo (0),
                  eYes (1)
            }
    MAX-ACCESS read-only
    STATUS     current
    DESCRIPTION
            "-- empty --"
    ::= { hmStatusWlanWlanParameterEntry 20 }

-- {COLUMN} 1.3.6.1.4.1.248.32.18.1.3.55.1.21
hmStatusWlanWlanParameterEntryMinimumRate OBJECT-TYPE
    SYNTAX     INTEGER {
                  eUnknown (0),
                  e1M (1),
                  e2M (2),
                  e5M (3),
                  e5M5 (4),
                  e8M (5),
                  e11M (6),
                  e6M (12),
                  e9M (13),
                  e12M (14),
                  e18M (15),
                  e24M (16),
                  e36M (17),
                  e48M (18),
                  e54M (19),
                  eT12M (20),
                  eT18M (21),
                  eT24M (22),
                  eT36M (23),
                  eT48M (24),
                  eT72M (25),
                  eT96M (26),
                  eT108M (27),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eHT4S26M (52),
                  eHT4S52M (53),
                  eHT4S78M (54),
                  eHT4S104M (55),
                  eHT4S156M (56),
                  eHT4S208M (57),
                  eHT4S234M (58),
                  eHT4S260M (59),
                  eHTDUP6M (60),
                  eHtMcs33 (61),
                  eHtMcs34 (62),
                  eHtMcs35 (63),
                  eHtMcs36 (64),
                  eHtMcs37 (65),
                  eHtMcs38 (66),
                  eHtMcs39 (67),
                  eHtMcs40 (68),
                  eHtMcs41 (69),
                  eHtMcs42 (70),
                  eHtMcs43 (71),
                  eHtMcs44 (72),
                  eHtMcs45 (73),
                  eHtMcs46 (74),
                  eHtMcs47 (75),
                  eHtMcs48 (76),
                  eHtMcs49 (77),
                  eHtMcs50 (78),
                  eHtMcs51 (79),
                  eHtMcs52 (80),
                  eHtMcs53 (81),
                  eHtMcs54 (82),
                  eHtMcs55 (83),
                  eHtMcs56 (84),
                  eHtMcs57 (85),
                  eHtMcs58 (86),
                  eHtMcs59 (87),
                  eHtMcs60 (88),
                  eHtMcs61 (89),
                  eHtMcs62 (90),
                  eHtMcs63 (91),
                  eHtMcs64 (92),
                  eHtMcs65 (93),
                  eHtMcs66 (94),
                  eHtMcs67 (95),
                  eHtMcs68 (96),
                  eHtMcs69 (97),
                  eHtMcs70 (98),
                  eHtMcs71 (99),
                  eHtMcs72 (100),
                  eHtMcs73 (101),
                  eHtMcs74 (102),
                  eHtMcs75 (103),
                  eHtMcs76 (104),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            "-- empty --"
    ::= { hmStatusWlanWlanParameterEntry 21 }

-- {COLUMN} 1.3.6.1.4.1.248.32.18.1.3.55.1.22
hmStatusWlanWlanParameterEntryEirp OBJECT-TYPE
    SYNTAX     DisplayString (SIZE(0..255))
    MAX-ACCESS read-only
    STATUS     current
    DESCRIPTION
            "-- empty --"
    ::= { hmStatusWlanWlanParameterEntry 22 }

-- {COLUMN} 1.3.6.1.4.1.248.32.18.1.3.55.1.23
hmStatusWlanWlanParameterEntryExcEirp OBJECT-TYPE
    SYNTAX     INTEGER {
                  eNo (0),
                  eYes (1)
            }
    MAX-ACCESS read-only
    STATUS     current
    DESCRIPTION
            "-- empty --"
    ::= { hmStatusWlanWlanParameterEntry 23 }

-- {COLUMN} 1.3.6.1.4.1.248.32.18.1.3.55.1.24
hmStatusWlanWlanParameterEntryModemLoad OBJECT-TYPE
    SYNTAX     Integer32 (0..255)
    MAX-ACCESS read-only
    STATUS     current
    DESCRIPTION
            "-- empty --"
    ::= { hmStatusWlanWlanParameterEntry 24 }

-- {COLUMN} 1.3.6.1.4.1.248.32.18.1.3.55.1.25
hmStatusWlanWlanParameterEntryBeaconPeriod OBJECT-TYPE
    SYNTAX     Integer32 (0..65535)
    MAX-ACCESS read-only
    STATUS     current
    DESCRIPTION
            "-- empty --"
    ::= { hmStatusWlanWlanParameterEntry 25 }

-- {COLUMN} 1.3.6.1.4.1.248.32.18.1.3.55.1.26
hmStatusWlanWlanParameterEntrySupportsShortGuardInterval OBJECT-TYPE
    SYNTAX     INTEGER {
                  eNo (0),
                  e20mhz (1),
                  e40mhz (2),
                  e2040mhz (3)
            }
    MAX-ACCESS read-only
    STATUS     current
    DESCRIPTION
            "-- empty --"
    ::= { hmStatusWlanWlanParameterEntry 26 }

-- {COLUMN} 1.3.6.1.4.1.248.32.18.1.3.55.1.28
hmStatusWlanWlanParameterEntrySupports40mhz OBJECT-TYPE
    SYNTAX     INTEGER {
                  eNo (0),
                  eYes (1)
            }
    MAX-ACCESS read-only
    STATUS     current
    DESCRIPTION
            "-- empty --"
    ::= { hmStatusWlanWlanParameterEntry 28 }

-- {COLUMN} 1.3.6.1.4.1.248.32.18.1.3.55.1.29
hmStatusWlanWlanParameterEntryTxChains OBJECT-TYPE
    SYNTAX     Integer32 (0..255)
    MAX-ACCESS read-only
    STATUS     current
    DESCRIPTION
            "-- empty --"
    ::= { hmStatusWlanWlanParameterEntry 29 }

-- {COLUMN} 1.3.6.1.4.1.248.32.18.1.3.55.1.30
hmStatusWlanWlanParameterEntryRxChains OBJECT-TYPE
    SYNTAX     Integer32 (0..255)
    MAX-ACCESS read-only
    STATUS     current
    DESCRIPTION
            "-- empty --"
    ::= { hmStatusWlanWlanParameterEntry 30 }

-- {COLUMN} 1.3.6.1.4.1.248.32.18.1.3.55.1.32
hmStatusWlanWlanParameterEntrySupportedDfsSchemes OBJECT-TYPE
    SYNTAX     BITS {
                  eNone (0),
                  eEn301893V16 (1),
                  eEn301893V15 (2),
                  eJapan (3),
                  eFcc (4),
                  eEn302502 (5),
                  eEn301893V13 (6),
                  eEn301893V12 (7),
                  eEn301893V17 (15)
            }
    MAX-ACCESS read-only
    STATUS     current
    DESCRIPTION
            "-- empty --"
    ::= { hmStatusWlanWlanParameterEntry 32 }

-- {COLUMN} 1.3.6.1.4.1.248.32.18.1.3.55.1.33
hmStatusWlanWlanParameterEntrySupportedAntennas OBJECT-TYPE
    SYNTAX     INTEGER {
                  eNA (0),
                  eAntenna1 (1),
                  eAntenna1Plus2 (3),
                  eAntenna1Plus3 (5),
                  eAntenna1Plus2Plus3 (7)
            }
    MAX-ACCESS read-only
    STATUS     current
    DESCRIPTION
            "-- empty --"
    ::= { hmStatusWlanWlanParameterEntry 33 }

-- {COLUMN} 1.3.6.1.4.1.248.32.18.1.3.55.1.34
hmStatusWlanWlanParameterEntryRxStbc OBJECT-TYPE
    SYNTAX     INTEGER {
                  eNone (0),
                  eOne (1),
                  eTwo (2),
                  eThree (3)
            }
    MAX-ACCESS read-only
    STATUS     current
    DESCRIPTION
            "-- empty --"
    ::= { hmStatusWlanWlanParameterEntry 34 }

-- {COLUMN} 1.3.6.1.4.1.248.32.18.1.3.55.1.35
hmStatusWlanWlanParameterEntryLdpc OBJECT-TYPE
    SYNTAX     INTEGER {
                  eNo (0),
                  eYes (1)
            }
    MAX-ACCESS read-only
    STATUS     current
    DESCRIPTION
            "-- empty --"
    ::= { hmStatusWlanWlanParameterEntry 35 }

-- {COLUMN} 1.3.6.1.4.1.248.32.18.1.3.55.1.36
hmStatusWlanWlanParameterEntryCountry OBJECT-TYPE
    SYNTAX     INTEGER {
                  eUnknown (0),
                  eAlbania (8),
                  eAlgeria (12),
                  eArgentina (32),
                  eAustralia (36),
                  eAustria (40),
                  eBahrain (48),
                  eBangladesh (50),
                  eBelgium (56),
                  eBosniaHerzegovina (70),
                  eBrazil (76),
                  eBruneiDarussalam (96),
                  eBulgaria (100),
                  eBelarus (112),
                  eCanada (124),
                  eChile (152),
                  eChina (156),
                  eTaiwan (158),
                  eColombia (170),
                  eCostaRica (188),
                  eCroatia (191),
                  eCyprus (196),
                  eCzech (203),
                  eDenmark (208),
                  eEcuador (218),
                  eEstonia (233),
                  eFinland (246),
                  eFrance (250),
                  eGermany (276),
                  eGhana (288),
                  eGreece (300),
                  eGuatemala (320),
                  eHonduras (340),
                  eHongKong (344),
                  eHungary (348),
                  eIceland (352),
                  eIndia (356),
                  eIndonesia (360),
                  eIreland (372),
                  eIsrael (376),
                  eItaly (380),
                  eJapan (392),
                  eJordan (400),
                  eSouthKorea (410),
                  eKuwait (414),
                  eLebanon (422),
                  eLatvia (428),
                  eLiechtenstein (438),
                  eLithuania (440),
                  eLuxembourg (442),
                  eMacau (446),
                  eMalaysia (458),
                  eMalta (470),
                  eMexico (484),
                  eMoldavia (498),
                  eMorocco (504),
                  eOman (512),
                  eNetherlands (528),
                  eNewZealand (554),
                  eNicaragua (558),
                  eNorway (578),
                  ePakistan (586),
                  ePanama (591),
                  eParaguay (600),
                  ePeru (604),
                  ePhilippines (608),
                  ePoland (616),
                  ePortugal (620),
                  ePuertoRico (630),
                  eQatar (634),
                  eRomania (642),
                  eRussia (643),
                  eSaudiArabia (682),
                  eSingapore (702),
                  eSlovak (703),
                  eSlovenia (705),
                  eSouthAfrica (710),
                  eSpain (724),
                  eSweden (752),
                  eSwitzerland (756),
                  eThailand (764),
                  eUnitedArabEmirates (784),
                  eTunisia (788),
                  eTurkey (792),
                  eUganda (800),
                  eUkraine (804),
                  eMacedonia (807),
                  eEgypt (818),
                  eUnitedKingdom (826),
                  eTanzania (834),
                  eUnitedStatesFcc (840),
                  eUruguay (858),
                  eVenezuela (862),
                  eEurope (998),
                  eEgalistan (999)
            }
    MAX-ACCESS read-only
    STATUS     current
    DESCRIPTION
            "-- empty --"
    ::= { hmStatusWlanWlanParameterEntry 36 }

-- {COLUMN} 1.3.6.1.4.1.248.32.18.1.3.55.1.37
hmStatusWlanWlanParameterEntrySupportsSpectralScan OBJECT-TYPE
    SYNTAX     INTEGER {
                  eNo (0),
                  eYes (1)
            }
    MAX-ACCESS read-only
    STATUS     current
    DESCRIPTION
            "-- empty --"
    ::= { hmStatusWlanWlanParameterEntry 37 }

-- {COLUMN} 1.3.6.1.4.1.248.32.18.1.3.55.1.38
hmStatusWlanWlanParameterEntrySGIMask OBJECT-TYPE
    SYNTAX     BITS {
                  eNo (0),
                  e160mhz (28),
                  e80mhz (29),
                  e40mhz (30),
                  e20mhz (31)
            }
    MAX-ACCESS read-only
    STATUS     current
    DESCRIPTION
            "Bit mask of short guard interval support per-CBW"
    ::= { hmStatusWlanWlanParameterEntry 38 }

-- {COLUMN} 1.3.6.1.4.1.248.32.18.1.3.55.1.39
hmStatusWlanWlanParameterEntryChannelBandwidths OBJECT-TYPE
    SYNTAX     BITS {
                  eT40mhz (26),
                  e80Plus80mhz (27),
                  e160mhz (28),
                  e80mhz (29),
                  e40mhz (30),
                  e20mhz (31)
            }
    MAX-ACCESS read-only
    STATUS     current
    DESCRIPTION
            "-- empty --"
    ::= { hmStatusWlanWlanParameterEntry 39 }

-- {COLUMN} 1.3.6.1.4.1.248.32.18.1.3.55.1.40
hmStatusWlanWlanParameterEntryChannelBandwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { hmStatusWlanWlanParameterEntry 40 }

-- {COLUMN} 1.3.6.1.4.1.248.32.18.1.3.55.1.41
hmStatusWlanWlanParameterEntryProtMgmtFrames OBJECT-TYPE
    SYNTAX     INTEGER {
                  eNo (0),
                  eYes (1)
            }
    MAX-ACCESS read-only
    STATUS     current
    DESCRIPTION
            "-- empty --"
    ::= { hmStatusWlanWlanParameterEntry 41 }

-- {COLUMN} 1.3.6.1.4.1.248.32.18.1.3.55.1.42
hmStatusWlanWlanParameterEntryRxStbcHt OBJECT-TYPE
    SYNTAX     INTEGER {
                  eNone (0),
                  eOne (1),
                  eTwo (2),
                  eThree (3)
            }
    MAX-ACCESS read-only
    STATUS     current
    DESCRIPTION
            "-- empty --"
    ::= { hmStatusWlanWlanParameterEntry 42 }

-- {COLUMN} 1.3.6.1.4.1.248.32.18.1.3.55.1.43
hmStatusWlanWlanParameterEntryRxStbcVht OBJECT-TYPE
    SYNTAX     INTEGER {
                  eNone (0),
                  eOne (1),
                  eTwo (2),
                  eThree (3),
                  eFour (4),
                  eFive (5),
                  eSix (6),
                  eSeven (7)
            }
    MAX-ACCESS read-only
    STATUS     current
    DESCRIPTION
            "-- empty --"
    ::= { hmStatusWlanWlanParameterEntry 43 }

-- {COLUMN} 1.3.6.1.4.1.248.32.18.1.3.55.1.44
hmStatusWlanWlanParameterEntryLDPCMask OBJECT-TYPE
    SYNTAX     BITS {
                  eVht (30),
                  eHt (31)
            }
    MAX-ACCESS read-only
    STATUS     current
    DESCRIPTION
            "Bit mask of LDPC support per-PHY-Type"
    ::= { hmStatusWlanWlanParameterEntry 44 }

-- {TABLE} 1.3.6.1.4.1.248.32.18.1.3.56
hmStatusWlanNetworksTable OBJECT-TYPE
    SYNTAX     SEQUENCE OF HmStatusWlanNetworksEntry
    MAX-ACCESS not-accessible
    STATUS     current
    DESCRIPTION
            "-- empty --"
    ::= { hmStatusWlan 56 }

-- {ROW} 1.3.6.1.4.1.248.32.18.1.3.56.1
hmStatusWlanNetworksEntry OBJECT-TYPE
    SYNTAX     HmStatusWlanNetworksEntry
    MAX-ACCESS not-accessible
    STATUS     current
    DESCRIPTION
            ""
    INDEX {
            hmStatusWlanNetworksEntryIfc
          }
    ::= { hmStatusWlanNetworksTable 1 }

HmStatusWlanNetworksEntry ::= SEQUENCE {
            hmStatusWlanNetworksEntryIfc DisplayString,
            hmStatusWlanNetworksEntryOperating INTEGER,
            hmStatusWlanNetworksEntryNetworkName DisplayString,
            hmStatusWlanNetworksEntryNumStations Integer32,
            hmStatusWlanNetworksEntryMcastPwrSave INTEGER,
            hmStatusWlanNetworksEntryBssid MacAddress,
            hmStatusWlanNetworksEntryVlanId Integer32,
            hmStatusWlanNetworksEntryApsd INTEGER,
            hmStatusWlanNetworksEntryRadioMode INTEGER,
            hmStatusWlanNetworksEntryAlarmState INTEGER,
            hmStatusWlanNetworksEntryBasicRate INTEGER,
            hmStatusWlanNetworksEntryMacFilter INTEGER,
            hmStatusWlanNetworksEntryAccessMode INTEGER
    }

-- {COLUMN} 1.3.6.1.4.1.248.32.18.1.3.56.1.1
hmStatusWlanNetworksEntryIfc OBJECT-TYPE
    SYNTAX     DisplayString (SIZE(0..255))
    MAX-ACCESS read-only
    STATUS     current
    DESCRIPTION
            "-- empty --"
    ::= { hmStatusWlanNetworksEntry 1 }

-- {COLUMN} 1.3.6.1.4.1.248.32.18.1.3.56.1.2
hmStatusWlanNetworksEntryOperating OBJECT-TYPE
    SYNTAX     INTEGER {
                  eNo (0),
                  eYes (1)
            }
    MAX-ACCESS read-only
    STATUS     current
    DESCRIPTION
            "-- empty --"
    ::= { hmStatusWlanNetworksEntry 2 }

-- {COLUMN} 1.3.6.1.4.1.248.32.18.1.3.56.1.3
hmStatusWlanNetworksEntryNetworkName OBJECT-TYPE
    SYNTAX     DisplayString (SIZE(0..255))
    MAX-ACCESS read-only
    STATUS     current
    DESCRIPTION
            "-- empty --"
    ::= { hmStatusWlanNetworksEntry 3 }

-- {COLUMN} 1.3.6.1.4.1.248.32.18.1.3.56.1.4
hmStatusWlanNetworksEntryNumStations OBJECT-TYPE
    SYNTAX     Integer32 (0..65535)
    MAX-ACCESS read-only
    STATUS     current
    DESCRIPTION
            "-- empty --"
    ::= { hmStatusWlanNetworksEntry 4 }

-- {COLUMN} 1.3.6.1.4.1.248.32.18.1.3.56.1.5
hmStatusWlanNetworksEntryMcastPwrSave OBJECT-TYPE
    SYNTAX     INTEGER {
                  eNo (0),
                  eYes (1)
            }
    MAX-ACCESS read-only
    STATUS     current
    DESCRIPTION
            "-- empty --"
    ::= { hmStatusWlanNetworksEntry 5 }

-- {COLUMN} 1.3.6.1.4.1.248.32.18.1.3.56.1.6
hmStatusWlanNetworksEntryBssid OBJECT-TYPE
    SYNTAX     MacAddress
    MAX-ACCESS read-only
    STATUS     current
    DESCRIPTION
            "-- empty --"
    ::= { hmStatusWlanNetworksEntry 6 }

-- {COLUMN} 1.3.6.1.4.1.248.32.18.1.3.56.1.7
hmStatusWlanNetworksEntryVlanId OBJECT-TYPE
    SYNTAX     Integer32 (0..65535)
    MAX-ACCESS read-only
    STATUS     current
    DESCRIPTION
            "-- empty --"
    ::= { hmStatusWlanNetworksEntry 7 }

-- {COLUMN} 1.3.6.1.4.1.248.32.18.1.3.56.1.8
hmStatusWlanNetworksEntryApsd OBJECT-TYPE
    SYNTAX     INTEGER {
                  eNo (0),
                  eYes (1)
            }
    MAX-ACCESS read-only
    STATUS     current
    DESCRIPTION
            "-- empty --"
    ::= { hmStatusWlanNetworksEntry 8 }

-- {COLUMN} 1.3.6.1.4.1.248.32.18.1.3.56.1.9
hmStatusWlanNetworksEntryRadioMode OBJECT-TYPE
    SYNTAX     INTEGER {
                  e11bgMixed (0),
                  e11gOnly (1),
                  e11bOnly (2),
                  e2mMixed (3),
                  eTurboG (4),
                  e11bgnMixed (5),
                  e2m11bgnMixed (6),
                  e11gnMixed (7),
                  eGreenfieldGn (8),
                  e11a (256),
                  eTurboA (257),
                  e11anMixed (259),
                  eGreenfieldAn (260),
                  eHalf11a (261),
                  eQuarter11a (262),
                  e11anacMixed (263),
                  e11nacMixed (264),
                  e11acOnly (265),
                  eNone (65535)
            }
    MAX-ACCESS read-only
    STATUS     current
    DESCRIPTION
            "-- empty --"
    ::= { hmStatusWlanNetworksEntry 9 }

-- {COLUMN} 1.3.6.1.4.1.248.32.18.1.3.56.1.10
hmStatusWlanNetworksEntryAlarmState OBJECT-TYPE
    SYNTAX     INTEGER {
                  eNo (0),
                  ePhySignal (1),
                  eTotalRetries (2),
                  eTxErrors (4)
            }
    MAX-ACCESS read-only
    STATUS     current
    DESCRIPTION
            "-- empty --"
    ::= { hmStatusWlanNetworksEntry 10 }

-- {COLUMN} 1.3.6.1.4.1.248.32.18.1.3.56.1.11
hmStatusWlanNetworksEntryBasicRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51)
            }
    MAX-ACCESS read-only
    STATUS     current
    DESCRIPTION
            "-- empty --"
    ::= { hmStatusWlanNetworksEntry 11 }

-- {COLUMN} 1.3.6.1.4.1.248.32.18.1.3.56.1.12
hmStatusWlanNetworksEntryMacFilter OBJECT-TYPE
    SYNTAX     INTEGER {
                  eYes (0),
                  eNo (1),
                  eLocalOnly (2),
                  eRadiusOnly (3)
            }
    MAX-ACCESS read-only
    STATUS     current
    DESCRIPTION
            "-- empty --"
    ::= { hmStatusWlanNetworksEntry 12 }

-- {COLUMN} 1.3.6.1.4.1.248.32.18.1.3.56.1.13
hmStatusWlanNetworksEntryAccessMode OBJECT-TYPE
    SYNTAX     INTEGER {
                  eNegative (0),
                  ePositive (1)
            }
    MAX-ACCESS read-only
    STATUS     current
    DESCRIPTION
            "-- empty --"
    ::= { hmStatusWlanNetworksEntry 13 }

-- {TABLE} 1.3.6.1.4.1.248.32.18.1.3.57
hmStatusWlanRadiosTable OBJECT-TYPE
    SYNTAX     SEQUENCE OF HmStatusWlanRadiosEntry
    MAX-ACCESS not-accessible
    STATUS     current
    DESCRIPTION
            "-- empty --"
    ::= { hmStatusWlan 57 }

-- {ROW} 1.3.6.1.4.1.248.32.18.1.3.57.1
hmStatusWlanRadiosEntry OBJECT-TYPE
    SYNTAX     HmStatusWlanRadiosEntry
    MAX-ACCESS not-accessible
    STATUS     current
    DESCRIPTION
            ""
    INDEX {
            hmStatusWlanRadiosEntryIfc
          }
    ::= { hmStatusWlanRadiosTable 1 }

HmStatusWlanRadiosEntry ::= SEQUENCE {
            hmStatusWlanRadiosEntryIfc DisplayString,
            hmStatusWlanRadiosEntryRadioBand INTEGER,
            hmStatusWlanRadiosEntryRadioChannel Integer32,
            hmStatusWlanRadiosEntryNoiseLevel Integer32,
            hmStatusWlanRadiosEntryModemLoad Integer32,
            hmStatusWlanRadiosEntryTransmitPower DisplayString,
            hmStatusWlanRadiosEntryEirp DisplayString,
            hmStatusWlanRadiosEntryExcEirp INTEGER,
            hmStatusWlanRadiosEntryBackgroundScan Integer32,
            hmStatusWlanRadiosEntryExtChannel INTEGER,
            hmStatusWlanRadiosEntryBackgroundScanUnit INTEGER,
            hmStatusWlanRadiosEntryDfsScheme INTEGER,
            hmStatusWlanRadiosEntryRadioMode INTEGER,
            hmStatusWlanRadiosEntry40mhzPermitted INTEGER,
            hmStatusWlanRadiosEntryRadarLoadThreshold Integer32,
            hmStatusWlanRadiosEntryShortSlotTime INTEGER,
            hmStatusWlanRadiosEntryAggregateTimeLimitUs Integer32,
            hmStatusWlanRadiosEntryChannelBandwidth INTEGER,
            hmStatusWlanRadiosEntryAllowPhyRestarts INTEGER
    }

-- {COLUMN} 1.3.6.1.4.1.248.32.18.1.3.57.1.1
hmStatusWlanRadiosEntryIfc OBJECT-TYPE
    SYNTAX     DisplayString (SIZE(0..255))
    MAX-ACCESS read-only
    STATUS     current
    DESCRIPTION
            "-- empty --"
    ::= { hmStatusWlanRadiosEntry 1 }

-- {COLUMN} 1.3.6.1.4.1.248.32.18.1.3.57.1.2
hmStatusWlanRadiosEntryRadioBand OBJECT-TYPE
    SYNTAX     INTEGER {
                  eUnknown (0),
                  e24ghz (1),
                  e5ghz (2)
            }
    MAX-ACCESS read-only
    STATUS     current
    DESCRIPTION
            "-- empty --"
    ::= { hmStatusWlanRadiosEntry 2 }

-- {COLUMN} 1.3.6.1.4.1.248.32.18.1.3.57.1.3
hmStatusWlanRadiosEntryRadioChannel OBJECT-TYPE
    SYNTAX     Integer32 (0..255)
    MAX-ACCESS read-only
    STATUS     current
    DESCRIPTION
            "-- empty --"
    ::= { hmStatusWlanRadiosEntry 3 }

-- {COLUMN} 1.3.6.1.4.1.248.32.18.1.3.57.1.5
hmStatusWlanRadiosEntryNoiseLevel OBJECT-TYPE
    SYNTAX     Integer32 (-32768..32767)
    MAX-ACCESS read-only
    STATUS     current
    DESCRIPTION
            "-- empty --"
    ::= { hmStatusWlanRadiosEntry 5 }

-- {COLUMN} 1.3.6.1.4.1.248.32.18.1.3.57.1.6
hmStatusWlanRadiosEntryModemLoad OBJECT-TYPE
    SYNTAX     Integer32 (0..255)
    MAX-ACCESS read-only
    STATUS     current
    DESCRIPTION
            "-- empty --"
    ::= { hmStatusWlanRadiosEntry 6 }

-- {COLUMN} 1.3.6.1.4.1.248.32.18.1.3.57.1.7
hmStatusWlanRadiosEntryTransmitPower OBJECT-TYPE
    SYNTAX     DisplayString (SIZE(0..255))
    MAX-ACCESS read-only
    STATUS     current
    DESCRIPTION
            "-- empty --"
    ::= { hmStatusWlanRadiosEntry 7 }

-- {COLUMN} 1.3.6.1.4.1.248.32.18.1.3.57.1.8
hmStatusWlanRadiosEntryEirp OBJECT-TYPE
    SYNTAX     DisplayString (SIZE(0..255))
    MAX-ACCESS read-only
    STATUS     current
    DESCRIPTION
            "-- empty --"
    ::= { hmStatusWlanRadiosEntry 8 }

-- {COLUMN} 1.3.6.1.4.1.248.32.18.1.3.57.1.9
hmStatusWlanRadiosEntryExcEirp OBJECT-TYPE
    SYNTAX     INTEGER {
                  eNo (0),
                  eYes (1)
            }
    MAX-ACCESS read-only
    STATUS     current
    DESCRIPTION
            "-- empty --"
    ::= { hmStatusWlanRadiosEntry 9 }

-- {COLUMN} 1.3.6.1.4.1.248.32.18.1.3.57.1.10
hmStatusWlanRadiosEntryBackgroundScan OBJECT-TYPE
    SYNTAX     Integer32 (0..2147483647)
    MAX-ACCESS read-only
    STATUS     current
    DESCRIPTION
            "-- empty --"
    ::= { hmStatusWlanRadiosEntry 10 }

-- {COLUMN} 1.3.6.1.4.1.248.32.18.1.3.57.1.11
hmStatusWlanRadiosEntryExtChannel OBJECT-TYPE
    SYNTAX     INTEGER {
                  eNone (0),
                  eAbove (1),
                  eBelow (3)
            }
    MAX-ACCESS read-only
    STATUS     current
    DESCRIPTION
            "-- empty --"
    ::= { hmStatusWlanRadiosEntry 11 }

-- {COLUMN} 1.3.6.1.4.1.248.32.18.1.3.57.1.12
hmStatusWlanRadiosEntryBackgroundScanUnit OBJECT-TYPE
    SYNTAX     INTEGER {
                  eSeconds (0),
                  eMilliseconds (1),
                  eMicroseconds (2),
                  eMinutes (3),
                  eHours (4),
                  eDays (5),
                  eWeeks (6),
                  eFortnights (7)
            }
    MAX-ACCESS read-only
    STATUS     current
    DESCRIPTION
            "-- empty --"
    ::= { hmStatusWlanRadiosEntry 12 }

-- {COLUMN} 1.3.6.1.4.1.248.32.18.1.3.57.1.13
hmStatusWlanRadiosEntryDfsScheme OBJECT-TYPE
    SYNTAX     INTEGER {
                  eNone (0),
                  eEn301893V12 (1),
                  eEn301893V13 (2),
                  eEn302502 (4),
                  eFcc (8),
                  eJapan (16),
                  eEn301893V15 (32),
                  eEn301893V16 (64),
                  eEn301893V17 (256)
            }
    MAX-ACCESS read-only
    STATUS     current
    DESCRIPTION
            "-- empty --"
    ::= { hmStatusWlanRadiosEntry 13 }

-- {COLUMN} 1.3.6.1.4.1.248.32.18.1.3.57.1.14
hmStatusWlanRadiosEntryRadioMode OBJECT-TYPE
    SYNTAX     INTEGER {
                  e11bgMixed (0),
                  e11gOnly (1),
                  e11bOnly (2),
                  e2mMixed (3),
                  eTurboG (4),
                  e11bgnMixed (5),
                  e2m11bgnMixed (6),
                  e11gnMixed (7),
                  eGreenfieldGn (8),
                  e11a (256),
                  eTurboA (257),
                  e11anMixed (259),
                  eGreenfieldAn (260),
                  eHalf11a (261),
                  eQuarter11a (262),
                  e11anacMixed (263),
                  e11nacMixed (264),
                  e11acOnly (265),
                  eNone (65535)
            }
    MAX-ACCESS read-only
    STATUS     current
    DESCRIPTION
            "-- empty --"
    ::= { hmStatusWlanRadiosEntry 14 }

-- {COLUMN} 1.3.6.1.4.1.248.32.18.1.3.57.1.15
hmStatusWlanRadiosEntry40mhzPermitted OBJECT-TYPE
    SYNTAX     INTEGER {
                  eNo (0),
                  eYes (1)
            }
    MAX-ACCESS read-only
    STATUS     current
    DESCRIPTION
            "-- empty --"
    ::= { hmStatusWlanRadiosEntry 15 }

-- {COLUMN} 1.3.6.1.4.1.248.32.18.1.3.57.1.16
hmStatusWlanRadiosEntryRadarLoadThreshold OBJECT-TYPE
    SYNTAX     Integer32 (0..255)
    MAX-ACCESS read-only
    STATUS     current
    DESCRIPTION
            "-- empty --"
    ::= { hmStatusWlanRadiosEntry 16 }

-- {COLUMN} 1.3.6.1.4.1.248.32.18.1.3.57.1.17
hmStatusWlanRadiosEntryShortSlotTime OBJECT-TYPE
    SYNTAX     INTEGER {
                  eNo (0),
                  eYes (1)
            }
    MAX-ACCESS read-only
    STATUS     current
    DESCRIPTION
            "-- empty --"
    ::= { hmStatusWlanRadiosEntry 17 }

-- {COLUMN} 1.3.6.1.4.1.248.32.18.1.3.57.1.18
hmStatusWlanRadiosEntryAggregateTimeLimitUs OBJECT-TYPE
    SYNTAX     Integer32 (0..2147483647)
    MAX-ACCESS read-only
    STATUS     current
    DESCRIPTION
            "-- empty --"
    ::= { hmStatusWlanRadiosEntry 18 }

-- {COLUMN} 1.3.6.1.4.1.248.32.18.1.3.57.1.19
hmStatusWlanRadiosEntryChannelBandwidth OBJECT-TYPE
    SYNTAX     INTEGER {
                  e20mhz (0),
                  e40mhz (1),
                  e80mhz (2),
                  e160mhz (3),
                  e80Plus80mhz (4),
                  eT40mhz (5)
            }
    MAX-ACCESS read-only
    STATUS     current
    DESCRIPTION
            "-- empty --"
    ::= { hmStatusWlanRadiosEntry 19 }

-- {COLUMN} 1.3.6.1.4.1.248.32.18.1.3.57.1.25
hmStatusWlanRadiosEntryAllowPhyRestarts OBJECT-TYPE
    SYNTAX     INTEGER {
                  eNo (0),
                  eYes (1)
            }
    MAX-ACCESS read-only
    STATUS     current
    DESCRIPTION
            "-- empty --"
    ::= { hmStatusWlanRadiosEntry 25 }

-- {TABLE} 1.3.6.1.4.1.248.32.18.1.3.58
hmStatusWlanQosParametersTable OBJECT-TYPE
    SYNTAX     SEQUENCE OF HmStatusWlanQosParametersEntry
    MAX-ACCESS not-accessible
    STATUS     current
    DESCRIPTION
            "-- empty --"
    ::= { hmStatusWlan 58 }

-- {ROW} 1.3.6.1.4.1.248.32.18.1.3.58.1
hmStatusWlanQosParametersEntry OBJECT-TYPE
    SYNTAX     HmStatusWlanQosParametersEntry
    MAX-ACCESS not-accessible
    STATUS     current
    DESCRIPTION
            ""
    INDEX {
            hmStatusWlanQosParametersEntryIfc,
            hmStatusWlanQosParametersEntryAccessCategory
          }
    ::= { hmStatusWlanQosParametersTable 1 }

HmStatusWlanQosParametersEntry ::= SEQUENCE {
            hmStatusWlanQosParametersEntryIfc DisplayString,
            hmStatusWlanQosParametersEntryAccessCategory INTEGER,
            hmStatusWlanQosParametersEntryTxop Integer32,
            hmStatusWlanQosParametersEntryCwmin Integer32,
            hmStatusWlanQosParametersEntryCwmax Integer32,
            hmStatusWlanQosParametersEntryAifs Integer32
    }

-- {COLUMN} 1.3.6.1.4.1.248.32.18.1.3.58.1.1
hmStatusWlanQosParametersEntryIfc OBJECT-TYPE
    SYNTAX     DisplayString (SIZE(0..255))
    MAX-ACCESS read-only
    STATUS     current
    DESCRIPTION
            "-- empty --"
    ::= { hmStatusWlanQosParametersEntry 1 }

-- {COLUMN} 1.3.6.1.4.1.248.32.18.1.3.58.1.2
hmStatusWlanQosParametersEntryAccessCategory OBJECT-TYPE
    SYNTAX     INTEGER {
                  eBestEffort (0),
                  eBackground (1),
                  eVideo (2),
                  eVoice (3)
            }
    MAX-ACCESS read-only
    STATUS     current
    DESCRIPTION
            "-- empty --"
    ::= { hmStatusWlanQosParametersEntry 2 }

-- {COLUMN} 1.3.6.1.4.1.248.32.18.1.3.58.1.3
hmStatusWlanQosParametersEntryTxop OBJECT-TYPE
    SYNTAX     Integer32 (0..2147483647)
    MAX-ACCESS read-only
    STATUS     current
    DESCRIPTION
            "-- empty --"
    ::= { hmStatusWlanQosParametersEntry 3 }

-- {COLUMN} 1.3.6.1.4.1.248.32.18.1.3.58.1.4
hmStatusWlanQosParametersEntryCwmin OBJECT-TYPE
    SYNTAX     Integer32 (0..65535)
    MAX-ACCESS read-only
    STATUS     current
    DESCRIPTION
            "-- empty --"
    ::= { hmStatusWlanQosParametersEntry 4 }

-- {COLUMN} 1.3.6.1.4.1.248.32.18.1.3.58.1.5
hmStatusWlanQosParametersEntryCwmax OBJECT-TYPE
    SYNTAX     Integer32 (0..65535)
    MAX-ACCESS read-only
    STATUS     current
    DESCRIPTION
            "-- empty --"
    ::= { hmStatusWlanQosParametersEntry 5 }

-- {COLUMN} 1.3.6.1.4.1.248.32.18.1.3.58.1.6
hmStatusWlanQosParametersEntryAifs OBJECT-TYPE
    SYNTAX     Integer32 (0..255)
    MAX-ACCESS read-only
    STATUS     current
    DESCRIPTION
            "-- empty --"
    ::= { hmStatusWlanQosParametersEntry 6 }

-- {TABLE} 1.3.6.1.4.1.248.32.18.1.3.59
hmStatusWlanQosPacketStatisticsTable OBJECT-TYPE
    SYNTAX     SEQUENCE OF HmStatusWlanQosPacketStatisticsEntry
    MAX-ACCESS not-accessible
    STATUS     current
    DESCRIPTION
            "-- empty --"
    ::= { hmStatusWlan 59 }

-- {ROW} 1.3.6.1.4.1.248.32.18.1.3.59.1
hmStatusWlanQosPacketStatisticsEntry OBJECT-TYPE
    SYNTAX     HmStatusWlanQosPacketStatisticsEntry
    MAX-ACCESS not-accessible
    STATUS     current
    DESCRIPTION
            ""
    INDEX {
            hmStatusWlanQosPacketStatisticsEntryIfc,
            hmStatusWlanQosPacketStatisticsEntryAccessCategory
          }
    ::= { hmStatusWlanQosPacketStatisticsTable 1 }

HmStatusWlanQosPacketStatisticsEntry ::= SEQUENCE {
            hmStatusWlanQosPacketStatisticsEntryIfc DisplayString,
            hmStatusWlanQosPacketStatisticsEntryAccessCategory INTEGER,
            hmStatusWlanQosPacketStatisticsEntryTxPackets Integer32,
            hmStatusWlanQosPacketStatisticsEntryTxDiscarded Integer32
    }

-- {COLUMN} 1.3.6.1.4.1.248.32.18.1.3.59.1.1
hmStatusWlanQosPacketStatisticsEntryIfc OBJECT-TYPE
    SYNTAX     DisplayString (SIZE(0..255))
    MAX-ACCESS read-only
    STATUS     current
    DESCRIPTION
            "-- empty --"
    ::= { hmStatusWlanQosPacketStatisticsEntry 1 }

-- {COLUMN} 1.3.6.1.4.1.248.32.18.1.3.59.1.2
hmStatusWlanQosPacketStatisticsEntryAccessCategory OBJECT-TYPE
    SYNTAX     INTEGER {
                  eBestEffort (0),
                  eBackground (1),
                  eVideo (2),
                  eVoice (3)
            }
    MAX-ACCESS read-only
    STATUS     current
    DESCRIPTION
            "-- empty --"
    ::= { hmStatusWlanQosPacketStatisticsEntry 2 }

-- {COLUMN} 1.3.6.1.4.1.248.32.18.1.3.59.1.3
hmStatusWlanQosPacketStatisticsEntryTxPackets OBJECT-TYPE
    SYNTAX     Integer32 (0..2147483647)
    MAX-ACCESS read-only
    STATUS     current
    DESCRIPTION
            "-- empty --"
    ::= { hmStatusWlanQosPacketStatisticsEntry 3 }

-- {COLUMN} 1.3.6.1.4.1.248.32.18.1.3.59.1.4
hmStatusWlanQosPacketStatisticsEntryTxDiscarded OBJECT-TYPE
    SYNTAX     Integer32 (0..2147483647)
    MAX-ACCESS read-only
    STATUS     current
    DESCRIPTION
            "-- empty --"
    ::= { hmStatusWlanQosPacketStatisticsEntry 4 }

-- {NODE} 1.3.6.1.4.1.248.32.18.1.3.60
hmStatusWlanPmkCaching OBJECT IDENTIFIER ::= { hmStatusWlan 60 }

-- {TABLE} 1.3.6.1.4.1.248.32.18.1.3.60.1
hmStatusWlanPmkCachingContentsTable OBJECT-TYPE
    SYNTAX     SEQUENCE OF HmStatusWlanPmkCachingContentsEntry
    MAX-ACCESS not-accessible
    STATUS     current
    DESCRIPTION
            "-- empty --"
    ::= { hmStatusWlanPmkCaching 1 }

-- {ROW} 1.3.6.1.4.1.248.32.18.1.3.60.1.1
hmStatusWlanPmkCachingContentsEntry OBJECT-TYPE
    SYNTAX     HmStatusWlanPmkCachingContentsEntry
    MAX-ACCESS not-accessible
    STATUS     current
    DESCRIPTION
            ""
    INDEX {
            hmStatusWlanPmkCachingContentsEntryAuthenticator,
            hmStatusWlanPmkCachingContentsEntrySupplicant
          }
    ::= { hmStatusWlanPmkCachingContentsTable 1 }

HmStatusWlanPmkCachingContentsEntry ::= SEQUENCE {
            hmStatusWlanPmkCachingContentsEntryAuthenticator MacAddress,
            hmStatusWlanPmkCachingContentsEntrySupplicant MacAddress,
            hmStatusWlanPmkCachingContentsEntryUserName DisplayString,
            hmStatusWlanPmkCachingContentsEntryVlanId Integer32,
            hmStatusWlanPmkCachingContentsEntryLifetime Integer32,
            hmStatusWlanPmkCachingContentsEntryExpired INTEGER,
            hmStatusWlanPmkCachingContentsEntrySource INTEGER
    }

-- {COLUMN} 1.3.6.1.4.1.248.32.18.1.3.60.1.1.1
hmStatusWlanPmkCachingContentsEntryAuthenticator OBJECT-TYPE
    SYNTAX     MacAddress
    MAX-ACCESS read-only
    STATUS     current
    DESCRIPTION
            "-- empty --"
    ::= { hmStatusWlanPmkCachingContentsEntry 1 }

-- {COLUMN} 1.3.6.1.4.1.248.32.18.1.3.60.1.1.2
hmStatusWlanPmkCachingContentsEntrySupplicant OBJECT-TYPE
    SYNTAX     MacAddress
    MAX-ACCESS read-only
    STATUS     current
    DESCRIPTION
            "-- empty --"
    ::= { hmStatusWlanPmkCachingContentsEntry 2 }

-- {COLUMN} 1.3.6.1.4.1.248.32.18.1.3.60.1.1.3
hmStatusWlanPmkCachingContentsEntryUserName OBJECT-TYPE
    SYNTAX     DisplayString (SIZE(0..255))
    MAX-ACCESS read-only
    STATUS     current
    DESCRIPTION
            "-- empty --"
    ::= { hmStatusWlanPmkCachingContentsEntry 3 }

-- {COLUMN} 1.3.6.1.4.1.248.32.18.1.3.60.1.1.4
hmStatusWlanPmkCachingContentsEntryVlanId OBJECT-TYPE
    SYNTAX     Integer32 (0..65535)
    MAX-ACCESS read-only
    STATUS     current
    DESCRIPTION
            "-- empty --"
    ::= { hmStatusWlanPmkCachingContentsEntry 4 }

-- {COLUMN} 1.3.6.1.4.1.248.32.18.1.3.60.1.1.5
hmStatusWlanPmkCachingContentsEntryLifetime OBJECT-TYPE
    SYNTAX     Integer32 (0..2147483647)
    MAX-ACCESS read-only
    STATUS     current
    DESCRIPTION
            "-- empty --"
    ::= { hmStatusWlanPmkCachingContentsEntry 5 }

-- {COLUMN} 1.3.6.1.4.1.248.32.18.1.3.60.1.1.6
hmStatusWlanPmkCachingContentsEntryExpired OBJECT-TYPE
    SYNTAX     INTEGER {
                  eNo (0),
                  eYes (1)
            }
    MAX-ACCESS read-only
    STATUS     current
    DESCRIPTION
            "-- empty --"
    ::= { hmStatusWlanPmkCachingContentsEntry 6 }

-- {COLUMN} 1.3.6.1.4.1.248.32.18.1.3.60.1.1.7
hmStatusWlanPmkCachingContentsEntrySource OBJECT-TYPE
    SYNTAX     INTEGER {
                  eUnknown (0),
                  eAuthentication (1),
                  ePreAuthentication (2),
                  eController (3)
            }
    MAX-ACCESS read-only
    STATUS     current
    DESCRIPTION
            "-- empty --"
    ::= { hmStatusWlanPmkCachingContentsEntry 7 }

-- {TABLE} 1.3.6.1.4.1.248.32.18.1.3.60.2
hmStatusWlanPmkCachingContentsNewTable OBJECT-TYPE
    SYNTAX     SEQUENCE OF HmStatusWlanPmkCachingContentsNewEntry
    MAX-ACCESS not-accessible
    STATUS     current
    DESCRIPTION
            ""
    ::= { hmStatusWlanPmkCaching 2 }

-- {ROW} 1.3.6.1.4.1.248.32.18.1.3.60.2.1
hmStatusWlanPmkCachingContentsNewEntry OBJECT-TYPE
    SYNTAX     HmStatusWlanPmkCachingContentsNewEntry
    MAX-ACCESS not-accessible
    STATUS     current
    DESCRIPTION
            ""
    INDEX {
            hmStatusWlanPmkCachingContentsNewEntryAuthenticator,
            hmStatusWlanPmkCachingContentsNewEntrySupplicant,
            hmStatusWlanPmkCachingContentsNewEntrySource
          }
    ::= { hmStatusWlanPmkCachingContentsNewTable 1 }

HmStatusWlanPmkCachingContentsNewEntry ::= SEQUENCE {
            hmStatusWlanPmkCachingContentsNewEntryAuthenticator MacAddress,
            hmStatusWlanPmkCachingContentsNewEntrySupplicant MacAddress,
            hmStatusWlanPmkCachingContentsNewEntryUserName DisplayString,
            hmStatusWlanPmkCachingContentsNewEntryVlanId Integer32,
            hmStatusWlanPmkCachingContentsNewEntryLifetime Integer32,
            hmStatusWlanPmkCachingContentsNewEntryExpired INTEGER,
            hmStatusWlanPmkCachingContentsNewEntrySource INTEGER
    }

-- {COLUMN} 1.3.6.1.4.1.248.32.18.1.3.60.2.1.1
hmStatusWlanPmkCachingContentsNewEntryAuthenticator OBJECT-TYPE
    SYNTAX     MacAddress
    MAX-ACCESS read-only
    STATUS     current
    DESCRIPTION
            "-- empty --"
    ::= { hmStatusWlanPmkCachingContentsNewEntry 1 }

-- {COLUMN} 1.3.6.1.4.1.248.32.18.1.3.60.2.1.2
hmStatusWlanPmkCachingContentsNewEntrySupplicant OBJECT-TYPE
    SYNTAX     MacAddress
    MAX-ACCESS read-only
    STATUS     current
    DESCRIPTION
            "-- empty --"
    ::= { hmStatusWlanPmkCachingContentsNewEntry 2 }

-- {COLUMN} 1.3.6.1.4.1.248.32.18.1.3.60.2.1.3
hmStatusWlanPmkCachingContentsNewEntryUserName OBJECT-TYPE
    SYNTAX     DisplayString (SIZE(0..255))
    MAX-ACCESS read-only
    STATUS     current
    DESCRIPTION
            "-- empty --"
    ::= { hmStatusWlanPmkCachingContentsNewEntry 3 }

-- {COLUMN} 1.3.6.1.4.1.248.32.18.1.3.60.2.1.4
hmStatusWlanPmkCachingContentsNewEntryVlanId OBJECT-TYPE
    SYNTAX     Integer32 (0..65535)
    MAX-ACCESS read-only
    STATUS     current
    DESCRIPTION
            "-- empty --"
    ::= { hmStatusWlanPmkCachingContentsNewEntry 4 }

-- {COLUMN} 1.3.6.1.4.1.248.32.18.1.3.60.2.1.5
hmStatusWlanPmkCachingContentsNewEntryLifetime OBJECT-TYPE
    SYNTAX     Integer32 (0..2147483647)
    MAX-ACCESS read-only
    STATUS     current
    DESCRIPTION
            "-- empty --"
    ::= { hmStatusWlanPmkCachingContentsNewEntry 5 }

-- {COLUMN} 1.3.6.1.4.1.248.32.18.1.3.60.2.1.6
hmStatusWlanPmkCachingContentsNewEntryExpired OBJECT-TYPE
    SYNTAX     INTEGER {
                  eNo (0),
                  eYes (1)
            }
    MAX-ACCESS read-only
    STATUS     current
    DESCRIPTION
            "-- empty --"
    ::= { hmStatusWlanPmkCachingContentsNewEntry 6 }

-- {COLUMN} 1.3.6.1.4.1.248.32.18.1.3.60.2.1.7
hmStatusWlanPmkCachingContentsNewEntrySource OBJECT-TYPE
    SYNTAX     INTEGER {
                  eUnknown (0),
                  eAuthentication (1),
                  ePreAuthentication (2),
                  eController (3)
            }
    MAX-ACCESS read-only
    STATUS     current
    DESCRIPTION
            "-- empty --"
    ::= { hmStatusWlanPmkCachingContentsNewEntry 7 }

-- {NODE} 1.3.6.1.4.1.248.32.18.1.3.61
hmStatusWlanSpectralScan OBJECT IDENTIFIER ::= { hmStatusWlan 61 }

-- {TABLE} 1.3.6.1.4.1.248.32.18.1.3.61.1
hmStatusWlanSpectralScanLogTable OBJECT-TYPE
    SYNTAX     SEQUENCE OF HmStatusWlanSpectralScanLogEntry
    MAX-ACCESS not-accessible
    STATUS     current
    DESCRIPTION
            "-- empty --"
    ::= { hmStatusWlanSpectralScan 1 }

-- {ROW} 1.3.6.1.4.1.248.32.18.1.3.61.1.1
hmStatusWlanSpectralScanLogEntry OBJECT-TYPE
    SYNTAX     HmStatusWlanSpectralScanLogEntry
    MAX-ACCESS not-accessible
    STATUS     current
    DESCRIPTION
            ""
    INDEX {
            hmStatusWlanSpectralScanLogEntryIndex
          }
    ::= { hmStatusWlanSpectralScanLogTable 1 }

HmStatusWlanSpectralScanLogEntry ::= SEQUENCE {
            hmStatusWlanSpectralScanLogEntryIndex Integer32,
            hmStatusWlanSpectralScanLogEntryInterface INTEGER,
            hmStatusWlanSpectralScanLogEntryTime DisplayString,
            hmStatusWlanSpectralScanLogEntryChannel Integer32,
            hmStatusWlanSpectralScanLogEntryFrequency Integer32,
            hmStatusWlanSpectralScanLogEntryRssi Integer32,
            hmStatusWlanSpectralScanLogEntryInterferenceType BITS
    }

-- {COLUMN} 1.3.6.1.4.1.248.32.18.1.3.61.1.1.1
hmStatusWlanSpectralScanLogEntryIndex OBJECT-TYPE
    SYNTAX     Integer32 (0..2147483647)
    MAX-ACCESS read-only
    STATUS     current
    DESCRIPTION
            "-- empty --"
    ::= { hmStatusWlanSpectralScanLogEntry 1 }

-- {COLUMN} 1.3.6.1.4.1.248.32.18.1.3.61.1.1.2
hmStatusWlanSpectralScanLogEntryInterface OBJECT-TYPE
    SYNTAX     INTEGER {
                  eWlan1 (1),
                  eWlan2 (2)
            }
    MAX-ACCESS read-only
    STATUS     current
    DESCRIPTION
            "-- empty --"
    ::= { hmStatusWlanSpectralScanLogEntry 2 }

-- {COLUMN} 1.3.6.1.4.1.248.32.18.1.3.61.1.1.3
hmStatusWlanSpectralScanLogEntryTime OBJECT-TYPE
    SYNTAX     DisplayString (SIZE(0..19))
    MAX-ACCESS read-only
    STATUS     current
    DESCRIPTION
            "-- empty --"
    ::= { hmStatusWlanSpectralScanLogEntry 3 }

-- {COLUMN} 1.3.6.1.4.1.248.32.18.1.3.61.1.1.4
hmStatusWlanSpectralScanLogEntryChannel OBJECT-TYPE
    SYNTAX     Integer32 (0..65535)
    MAX-ACCESS read-only
    STATUS     current
    DESCRIPTION
            "-- empty --"
    ::= { hmStatusWlanSpectralScanLogEntry 4 }

-- {COLUMN} 1.3.6.1.4.1.248.32.18.1.3.61.1.1.5
hmStatusWlanSpectralScanLogEntryFrequency OBJECT-TYPE
    SYNTAX     Integer32 (0..2147483647)
    MAX-ACCESS read-only
    STATUS     current
    DESCRIPTION
            "-- empty --"
    ::= { hmStatusWlanSpectralScanLogEntry 5 }

-- {COLUMN} 1.3.6.1.4.1.248.32.18.1.3.61.1.1.6
hmStatusWlanSpectralScanLogEntryRssi OBJECT-TYPE
    SYNTAX     Integer32 (0..65535)
    MAX-ACCESS read-only
    STATUS     current
    DESCRIPTION
            "-- empty --"
    ::= { hmStatusWlanSpectralScanLogEntry 6 }

-- {COLUMN} 1.3.6.1.4.1.248.32.18.1.3.61.1.1.7
hmStatusWlanSpectralScanLogEntryInterferenceType OBJECT-TYPE
    SYNTAX     BITS {
                  eWifi (2),
                  eContinuousWave (3),
                  eDect (4),
                  eFhss (5),
                  eMicrowave (6)
            }
    MAX-ACCESS read-only
    STATUS     current
    DESCRIPTION
            "-- empty --"
    ::= { hmStatusWlanSpectralScanLogEntry 7 }

-- {TABLE} 1.3.6.1.4.1.248.32.18.1.3.61.2
hmStatusWlanSpectralScanAllChannelsTable OBJECT-TYPE
    SYNTAX     SEQUENCE OF HmStatusWlanSpectralScanAllChannelsEntry
    MAX-ACCESS not-accessible
    STATUS     current
    DESCRIPTION
            "-- empty --"
    ::= { hmStatusWlanSpectralScan 2 }

-- {ROW} 1.3.6.1.4.1.248.32.18.1.3.61.2.1
hmStatusWlanSpectralScanAllChannelsEntry OBJECT-TYPE
    SYNTAX     HmStatusWlanSpectralScanAllChannelsEntry
    MAX-ACCESS not-accessible
    STATUS     current
    DESCRIPTION
            ""
    INDEX {
            hmStatusWlanSpectralScanAllChannelsEntryIndex
          }
    ::= { hmStatusWlanSpectralScanAllChannelsTable 1 }

HmStatusWlanSpectralScanAllChannelsEntry ::= SEQUENCE {
            hmStatusWlanSpectralScanAllChannelsEntryIndex Integer32,
            hmStatusWlanSpectralScanAllChannelsEntryInterface INTEGER,
            hmStatusWlanSpectralScanAllChannelsEntryChannel Integer32,
            hmStatusWlanSpectralScanAllChannelsEntryMicrowave BITS,
            hmStatusWlanSpectralScanAllChannelsEntryLastSeenMicrowave DisplayString,
            hmStatusWlanSpectralScanAllChannelsEntryFhss BITS,
            hmStatusWlanSpectralScanAllChannelsEntryLastSeenFhss DisplayString,
            hmStatusWlanSpectralScanAllChannelsEntryWifi BITS,
            hmStatusWlanSpectralScanAllChannelsEntryLastSeenWifi DisplayString,
            hmStatusWlanSpectralScanAllChannelsEntryContinuousWave BITS,
            hmStatusWlanSpectralScanAllChannelsEntryLastSeenContinuousWave DisplayString
    }

-- {COLUMN} 1.3.6.1.4.1.248.32.18.1.3.61.2.1.1
hmStatusWlanSpectralScanAllChannelsEntryIndex OBJECT-TYPE
    SYNTAX     Integer32 (0..2147483647)
    MAX-ACCESS read-only
    STATUS     current
    DESCRIPTION
            "-- empty --"
    ::= { hmStatusWlanSpectralScanAllChannelsEntry 1 }

-- {COLUMN} 1.3.6.1.4.1.248.32.18.1.3.61.2.1.2
hmStatusWlanSpectralScanAllChannelsEntryInterface OBJECT-TYPE
    SYNTAX     INTEGER {
                  eWlan1 (1),
                  eWlan2 (2)
            }
    MAX-ACCESS read-only
    STATUS     current
    DESCRIPTION
            "-- empty --"
    ::= { hmStatusWlanSpectralScanAllChannelsEntry 2 }

-- {COLUMN} 1.3.6.1.4.1.248.32.18.1.3.61.2.1.3
hmStatusWlanSpectralScanAllChannelsEntryChannel OBJECT-TYPE
    SYNTAX     Integer32 (0..255)
    MAX-ACCESS read-only
    STATUS     current
    DESCRIPTION
            "-- empty --"
    ::= { hmStatusWlanSpectralScanAllChannelsEntry 3 }

-- {COLUMN} 1.3.6.1.4.1.248.32.18.1.3.61.2.1.4
hmStatusWlanSpectralScanAllChannelsEntryMicrowave OBJECT-TYPE
    SYNTAX     BITS {
                  eNo (5),
                  eYes (6)
            }
    MAX-ACCESS read-only
    STATUS     current
    DESCRIPTION
            "-- empty --"
    ::= { hmStatusWlanSpectralScanAllChannelsEntry 4 }

-- {COLUMN} 1.3.6.1.4.1.248.32.18.1.3.61.2.1.5
hmStatusWlanSpectralScanAllChannelsEntryLastSeenMicrowave OBJECT-TYPE
    SYNTAX     DisplayString (SIZE(0..19))
    MAX-ACCESS read-only
    STATUS     current
    DESCRIPTION
            "-- empty --"
    ::= { hmStatusWlanSpectralScanAllChannelsEntry 5 }

-- {COLUMN} 1.3.6.1.4.1.248.32.18.1.3.61.2.1.6
hmStatusWlanSpectralScanAllChannelsEntryFhss OBJECT-TYPE
    SYNTAX     BITS {
                  eNo (5),
                  eYes (6)
            }
    MAX-ACCESS read-only
    STATUS     current
    DESCRIPTION
            "-- empty --"
    ::= { hmStatusWlanSpectralScanAllChannelsEntry 6 }

-- {COLUMN} 1.3.6.1.4.1.248.32.18.1.3.61.2.1.7
hmStatusWlanSpectralScanAllChannelsEntryLastSeenFhss OBJECT-TYPE
    SYNTAX     DisplayString (SIZE(0..19))
    MAX-ACCESS read-only
    STATUS     current
    DESCRIPTION
            "-- empty --"
    ::= { hmStatusWlanSpectralScanAllChannelsEntry 7 }

-- {COLUMN} 1.3.6.1.4.1.248.32.18.1.3.61.2.1.8
hmStatusWlanSpectralScanAllChannelsEntryWifi OBJECT-TYPE
    SYNTAX     BITS {
                  eNo (5),
                  eYes (6)
            }
    MAX-ACCESS read-only
    STATUS     current
    DESCRIPTION
            "-- empty --"
    ::= { hmStatusWlanSpectralScanAllChannelsEntry 8 }

-- {COLUMN} 1.3.6.1.4.1.248.32.18.1.3.61.2.1.9
hmStatusWlanSpectralScanAllChannelsEntryLastSeenWifi OBJECT-TYPE
    SYNTAX     DisplayString (SIZE(0..19))
    MAX-ACCESS read-only
    STATUS     current
    DESCRIPTION
            "-- empty --"
    ::= { hmStatusWlanSpectralScanAllChannelsEntry 9 }

-- {COLUMN} 1.3.6.1.4.1.248.32.18.1.3.61.2.1.10
hmStatusWlanSpectralScanAllChannelsEntryContinuousWave OBJECT-TYPE
    SYNTAX     BITS {
                  eNo (5),
                  eYes (6)
            }
    MAX-ACCESS read-only
    STATUS     current
    DESCRIPTION
            "-- empty --"
    ::= { hmStatusWlanSpectralScanAllChannelsEntry 10 }

-- {COLUMN} 1.3.6.1.4.1.248.32.18.1.3.61.2.1.11
hmStatusWlanSpectralScanAllChannelsEntryLastSeenContinuousWave OBJECT-TYPE
    SYNTAX     DisplayString (SIZE(0..19))
    MAX-ACCESS read-only
    STATUS     current
    DESCRIPTION
            "-- empty --"
    ::= { hmStatusWlanSpectralScanAllChannelsEntry 11 }

-- {NODE} 1.3.6.1.4.1.248.32.18.1.3.62
hmStatusWlanArpHandling OBJECT IDENTIFIER ::= { hmStatusWlan 62 }

-- {TABLE} 1.3.6.1.4.1.248.32.18.1.3.62.1
hmStatusWlanArpHandlingArpTableTable OBJECT-TYPE
    SYNTAX     SEQUENCE OF HmStatusWlanArpHandlingArpTableEntry
    MAX-ACCESS not-accessible
    STATUS     current
    DESCRIPTION
            "-- empty --"
    ::= { hmStatusWlanArpHandling 1 }

-- {ROW} 1.3.6.1.4.1.248.32.18.1.3.62.1.1
hmStatusWlanArpHandlingArpTableEntry OBJECT-TYPE
    SYNTAX     HmStatusWlanArpHandlingArpTableEntry
    MAX-ACCESS not-accessible
    STATUS     current
    DESCRIPTION
            ""
    INDEX {
            hmStatusWlanArpHandlingArpTableEntryAddress,
            hmStatusWlanArpHandlingArpTableEntryMacAddress
          }
    ::= { hmStatusWlanArpHandlingArpTableTable 1 }

HmStatusWlanArpHandlingArpTableEntry ::= SEQUENCE {
            hmStatusWlanArpHandlingArpTableEntryAddress IpAddress,
            hmStatusWlanArpHandlingArpTableEntryMacAddress MacAddress,
            hmStatusWlanArpHandlingArpTableEntryInterface INTEGER,
            hmStatusWlanArpHandlingArpTableEntryVlanId Integer32,
            hmStatusWlanArpHandlingArpTableEntryAge Integer32
    }

-- {COLUMN} 1.3.6.1.4.1.248.32.18.1.3.62.1.1.1
hmStatusWlanArpHandlingArpTableEntryAddress OBJECT-TYPE
    SYNTAX     IpAddress
    MAX-ACCESS read-only
    STATUS     current
    DESCRIPTION
            "-- empty --"
    ::= { hmStatusWlanArpHandlingArpTableEntry 1 }

-- {COLUMN} 1.3.6.1.4.1.248.32.18.1.3.62.1.1.2
hmStatusWlanArpHandlingArpTableEntryMacAddress OBJECT-TYPE
    SYNTAX     MacAddress
    MAX-ACCESS read-only
    STATUS     current
    DESCRIPTION
            "-- empty --"
    ::= { hmStatusWlanArpHandlingArpTableEntry 2 }

-- {COLUMN} 1.3.6.1.4.1.248.32.18.1.3.62.1.1.3
hmStatusWlanArpHandlingArpTableEntryInterface OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan22 (32),
                  eWlan23 (33),
                  eWlan24 (34),
                  eWlan25 (35),
                  eWlan26 (36),
                  eWlan27 (37),
                  eWlan28 (38)
            }
    MAX-ACCESS read-only
    STATUS     current
    DESCRIPTION
            "-- empty --"
    ::= { hmStatusWlanArpHandlingArpTableEntry 3 }

-- {COLUMN} 1.3.6.1.4.1.248.32.18.1.3.62.1.1.4
hmStatusWlanArpHandlingArpTableEntryVlanId OBJECT-TYPE
    SYNTAX     Integer32 (0..65535)
    MAX-ACCESS read-only
    STATUS     current
    DESCRIPTION
            "-- empty --"
    ::= { hmStatusWlanArpHandlingArpTableEntry 4 }

-- {COLUMN} 1.3.6.1.4.1.248.32.18.1.3.62.1.1.5
hmStatusWlanArpHandlingArpTableEntryAge OBJECT-TYPE
    SYNTAX     Integer32 (0..2147483647)
    MAX-ACCESS read-only
    STATUS     current
    DESCRIPTION
            "-- empty --"
    ::= { hmStatusWlanArpHandlingArpTableEntry 5 }

-- {TABLE} 1.3.6.1.4.1.248.32.18.1.3.62.2
hmStatusWlanArpHandlingNdTableTable OBJECT-TYPE
    SYNTAX     SEQUENCE OF HmStatusWlanArpHandlingNdTableEntry
    MAX-ACCESS not-accessible
    STATUS     current
    DESCRIPTION
            "-- empty --"
    ::= { hmStatusWlanArpHandling 2 }

-- {ROW} 1.3.6.1.4.1.248.32.18.1.3.62.2.1
hmStatusWlanArpHandlingNdTableEntry OBJECT-TYPE
    SYNTAX     HmStatusWlanArpHandlingNdTableEntry
    MAX-ACCESS not-accessible
    STATUS     current
    DESCRIPTION
            ""
    INDEX {
            hmStatusWlanArpHandlingNdTableEntryAddress,
            hmStatusWlanArpHandlingNdTableEntryMacAddress
          }
    ::= { hmStatusWlanArpHandlingNdTableTable 1 }

HmStatusWlanArpHandlingNdTableEntry ::= SEQUENCE {
            hmStatusWlanArpHandlingNdTableEntryAddress IpAddress,
            hmStatusWlanArpHandlingNdTableEntryMacAddress MacAddress,
            hmStatusWlanArpHandlingNdTableEntryInterface INTEGER,
            hmStatusWlanArpHandlingNdTableEntryVlanId Integer32,
            hmStatusWlanArpHandlingNdTableEntryAge Integer32
    }

-- {COLUMN} 1.3.6.1.4.1.248.32.18.1.3.62.2.1.1
hmStatusWlanArpHandlingNdTableEntryAddress OBJECT-TYPE
    SYNTAX     IpAddress
    MAX-ACCESS read-only
    STATUS     current
    DESCRIPTION
            "-- empty --"
    ::= { hmStatusWlanArpHandlingNdTableEntry 1 }

-- {COLUMN} 1.3.6.1.4.1.248.32.18.1.3.62.2.1.2
hmStatusWlanArpHandlingNdTableEntryMacAddress OBJECT-TYPE
    SYNTAX     MacAddress
    MAX-ACCESS read-only
    STATUS     current
    DESCRIPTION
            "-- empty --"
    ::= { hmStatusWlanArpHandlingNdTableEntry 2 }

-- {COLUMN} 1.3.6.1.4.1.248.32.18.1.3.62.2.1.3
hmStatusWlanArpHandlingNdTableEntryInterface OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan22 (32),
                  eWlan23 (33),
                  eWlan24 (34),
                  eWlan25 (35),
                  eWlan26 (36),
                  eWlan27 (37),
                  eWlan28 (38)
            }
    MAX-ACCESS read-only
    STATUS     current
    DESCRIPTION
            "-- empty --"
    ::= { hmStatusWlanArpHandlingNdTableEntry 3 }

-- {COLUMN} 1.3.6.1.4.1.248.32.18.1.3.62.2.1.4
hmStatusWlanArpHandlingNdTableEntryVlanId OBJECT-TYPE
    SYNTAX     Integer32 (0..65535)
    MAX-ACCESS read-only
    STATUS     current
    DESCRIPTION
            "-- empty --"
    ::= { hmStatusWlanArpHandlingNdTableEntry 4 }

-- {COLUMN} 1.3.6.1.4.1.248.32.18.1.3.62.2.1.5
hmStatusWlanArpHandlingNdTableEntryAge OBJECT-TYPE
    SYNTAX     Integer32 (0..2147483647)
    MAX-ACCESS read-only
    STATUS     current
    DESCRIPTION
            "-- empty --"
    ::= { hmStatusWlanArpHandlingNdTableEntry 5 }

-- {SCALAR} 1.3.6.1.4.1.248.32.18.1.3.62.11
hmStatusWlanArpHandlingArpRequestsAnswered OBJECT-TYPE
    SYNTAX     Integer32 (0..2147483647)
    MAX-ACCESS read-only
    STATUS     current
    DESCRIPTION
            "-- empty --"
    ::= { hmStatusWlanArpHandling 11 }

-- {SCALAR} 1.3.6.1.4.1.248.32.18.1.3.62.12
hmStatusWlanArpHandlingArpRequestsNotAnswered OBJECT-TYPE
    SYNTAX     Integer32 (0..2147483647)
    MAX-ACCESS read-only
    STATUS     current
    DESCRIPTION
            "-- empty --"
    ::= { hmStatusWlanArpHandling 12 }

-- {SCALAR} 1.3.6.1.4.1.248.32.18.1.3.62.13
hmStatusWlanArpHandlingArpRequestsDiscarded OBJECT-TYPE
    SYNTAX     Integer32 (0..2147483647)
    MAX-ACCESS read-only
    STATUS     current
    DESCRIPTION
            "-- empty --"
    ::= { hmStatusWlanArpHandling 13 }

-- {SCALAR} 1.3.6.1.4.1.248.32.18.1.3.62.14
hmStatusWlanArpHandlingNdSolicitationsAnswered OBJECT-TYPE
    SYNTAX     Integer32 (0..2147483647)
    MAX-ACCESS read-only
    STATUS     current
    DESCRIPTION
            "-- empty --"
    ::= { hmStatusWlanArpHandling 14 }

-- {SCALAR} 1.3.6.1.4.1.248.32.18.1.3.62.15
hmStatusWlanArpHandlingNdSolicitationsNotAnswered OBJECT-TYPE
    SYNTAX     Integer32 (0..2147483647)
    MAX-ACCESS read-only
    STATUS     current
    DESCRIPTION
            "-- empty --"
    ::= { hmStatusWlanArpHandling 15 }

-- {SCALAR} 1.3.6.1.4.1.248.32.18.1.3.62.16
hmStatusWlanArpHandlingNdSolicitationsDiscarded OBJECT-TYPE
    SYNTAX     Integer32 (0..2147483647)
    MAX-ACCESS read-only
    STATUS     current
    DESCRIPTION
            "-- empty --"
    ::= { hmStatusWlanArpHandling 16 }

-- {SCALAR} 1.3.6.1.4.1.248.32.18.1.3.62.99
hmStatusWlanArpHandlingDeleteValues OBJECT-TYPE
    SYNTAX     DisplayString
    MAX-ACCESS read-write
    STATUS     current
    DESCRIPTION
            "-- empty --"
    ::= { hmStatusWlanArpHandling 99 }

-- {NODE} 1.3.6.1.4.1.248.32.18.1.3.63
hmStatusWlanNoiseImmunity OBJECT IDENTIFIER ::= { hmStatusWlan 63 }

-- {TABLE} 1.3.6.1.4.1.248.32.18.1.3.63.1
hmStatusWlanNoiseImmunityCurrentParametersTable OBJECT-TYPE
    SYNTAX     SEQUENCE OF HmStatusWlanNoiseImmunityCurrentParametersEntry
    MAX-ACCESS not-accessible
    STATUS     current
    DESCRIPTION
            "-- empty --"
    ::= { hmStatusWlanNoiseImmunity 1 }

-- {ROW} 1.3.6.1.4.1.248.32.18.1.3.63.1.1
hmStatusWlanNoiseImmunityCurrentParametersEntry OBJECT-TYPE
    SYNTAX     HmStatusWlanNoiseImmunityCurrentParametersEntry
    MAX-ACCESS not-accessible
    STATUS     current
    DESCRIPTION
            ""
    INDEX {
            hmStatusWlanNoiseImmunityCurrentParametersEntryRadioBand,
            hmStatusWlanNoiseImmunityCurrentParametersEntryRadioChannel,
            hmStatusWlanNoiseImmunityCurrentParametersEntryInterface
          }
    ::= { hmStatusWlanNoiseImmunityCurrentParametersTable 1 }

HmStatusWlanNoiseImmunityCurrentParametersEntry ::= SEQUENCE {
            hmStatusWlanNoiseImmunityCurrentParametersEntryRadioChannel Integer32,
            hmStatusWlanNoiseImmunityCurrentParametersEntryInterface INTEGER,
            hmStatusWlanNoiseImmunityCurrentParametersEntryRadioBand INTEGER,
            hmStatusWlanNoiseImmunityCurrentParametersEntryNoisImmuLevel Integer32,
            hmStatusWlanNoiseImmunityCurrentParametersEntrySpurImmuLevel Integer32,
            hmStatusWlanNoiseImmunityCurrentParametersEntryFirStepLevel Integer32,
            hmStatusWlanNoiseImmunityCurrentParametersEntryOfdmWkSigDet INTEGER,
            hmStatusWlanNoiseImmunityCurrentParametersEntryCckWkSigDetTre Integer32,
            hmStatusWlanNoiseImmunityCurrentParametersEntryMrcCck INTEGER,
            hmStatusWlanNoiseImmunityCurrentParametersEntryAge Integer32,
            hmStatusWlanNoiseImmunityCurrentParametersEntryChannelBandwidth INTEGER
    }

-- {COLUMN} 1.3.6.1.4.1.248.32.18.1.3.63.1.1.1
hmStatusWlanNoiseImmunityCurrentParametersEntryRadioChannel OBJECT-TYPE
    SYNTAX     Integer32 (0..255)
    MAX-ACCESS read-only
    STATUS     current
    DESCRIPTION
            "-- empty --"
    ::= { hmStatusWlanNoiseImmunityCurrentParametersEntry 1 }

-- {COLUMN} 1.3.6.1.4.1.248.32.18.1.3.63.1.1.2
hmStatusWlanNoiseImmunityCurrentParametersEntryInterface OBJECT-TYPE
    SYNTAX     INTEGER {
                  eWlan1 (0),
                  eWlan2 (1),
                  eWlan3 (2),
                  eWlan4 (3)
            }
    MAX-ACCESS read-only
    STATUS     current
    DESCRIPTION
            "-- empty --"
    ::= { hmStatusWlanNoiseImmunityCurrentParametersEntry 2 }

-- {COLUMN} 1.3.6.1.4.1.248.32.18.1.3.63.1.1.9
hmStatusWlanNoiseImmunityCurrentParametersEntryRadioBand OBJECT-TYPE
    SYNTAX     INTEGER {
                  eUnknown (0),
                  e24ghz (1),
                  e5ghz (2)
            }
    MAX-ACCESS read-only
    STATUS     current
    DESCRIPTION
            "-- empty --"
    ::= { hmStatusWlanNoiseImmunityCurrentParametersEntry 9 }

-- {COLUMN} 1.3.6.1.4.1.248.32.18.1.3.63.1.1.11
hmStatusWlanNoiseImmunityCurrentParametersEntryNoisImmuLevel OBJECT-TYPE
    SYNTAX     Integer32 (0..255)
    MAX-ACCESS read-only
    STATUS     current
    DESCRIPTION
            ""
    ::= { hmStatusWlanNoiseImmunityCurrentParametersEntry 11 }

-- {COLUMN} 1.3.6.1.4.1.248.32.18.1.3.63.1.1.12
hmStatusWlanNoiseImmunityCurrentParametersEntrySpurImmuLevel OBJECT-TYPE
    SYNTAX     Integer32 (0..255)
    MAX-ACCESS read-only
    STATUS     current
    DESCRIPTION
            ""
    ::= { hmStatusWlanNoiseImmunityCurrentParametersEntry 12 }

-- {COLUMN} 1.3.6.1.4.1.248.32.18.1.3.63.1.1.13
hmStatusWlanNoiseImmunityCurrentParametersEntryFirStepLevel OBJECT-TYPE
    SYNTAX     Integer32 (0..255)
    MAX-ACCESS read-only
    STATUS     current
    DESCRIPTION
            "-- empty --"
    ::= { hmStatusWlanNoiseImmunityCurrentParametersEntry 13 }

-- {COLUMN} 1.3.6.1.4.1.248.32.18.1.3.63.1.1.14
hmStatusWlanNoiseImmunityCurrentParametersEntryOfdmWkSigDet OBJECT-TYPE
    SYNTAX     INTEGER {
                  eNo (0),
                  eYes (1)
            }
    MAX-ACCESS read-only
    STATUS     current
    DESCRIPTION
            ""
    ::= { hmStatusWlanNoiseImmunityCurrentParametersEntry 14 }

-- {COLUMN} 1.3.6.1.4.1.248.32.18.1.3.63.1.1.15
hmStatusWlanNoiseImmunityCurrentParametersEntryCckWkSigDetTre OBJECT-TYPE
    SYNTAX     Integer32 (0..255)
    MAX-ACCESS read-only
    STATUS     current
    DESCRIPTION
            ""
    ::= { hmStatusWlanNoiseImmunityCurrentParametersEntry 15 }

-- {COLUMN} 1.3.6.1.4.1.248.32.18.1.3.63.1.1.16
hmStatusWlanNoiseImmunityCurrentParametersEntryMrcCck OBJECT-TYPE
    SYNTAX     INTEGER {
                  eNo (0),
                  eYes (1)
            }
    MAX-ACCESS read-only
    STATUS     current
    DESCRIPTION
            "-- empty --"
    ::= { hmStatusWlanNoiseImmunityCurrentParametersEntry 16 }

-- {COLUMN} 1.3.6.1.4.1.248.32.18.1.3.63.1.1.17
hmStatusWlanNoiseImmunityCurrentParametersEntryAge OBJECT-TYPE
    SYNTAX     Integer32 (0..2147483647)
    MAX-ACCESS read-only
    STATUS     current
    DESCRIPTION
            "-- empty --"
    ::= { hmStatusWlanNoiseImmunityCurrentParametersEntry 17 }

-- {COLUMN} 1.3.6.1.4.1.248.32.18.1.3.63.1.1.18
hmStatusWlanNoiseImmunityCurrentParametersEntryChannelBandwidth OBJECT-TYPE
    SYNTAX     INTEGER {
                  e20mhz (0)
            }
    MAX-ACCESS read-only
    STATUS     current
    DESCRIPTION
            "-- empty --"
    ::= { hmStatusWlanNoiseImmunityCurrentParametersEntry 18 }

-- {TABLE} 1.3.6.1.4.1.248.32.18.1.3.63.2
hmStatusWlanNoiseImmunityLogTableTable OBJECT-TYPE
    SYNTAX     SEQUENCE OF HmStatusWlanNoiseImmunityLogTableEntry
    MAX-ACCESS not-accessible
    STATUS     current
    DESCRIPTION
            "-- empty --"
    ::= { hmStatusWlanNoiseImmunity 2 }

-- {ROW} 1.3.6.1.4.1.248.32.18.1.3.63.2.1
hmStatusWlanNoiseImmunityLogTableEntry OBJECT-TYPE
    SYNTAX     HmStatusWlanNoiseImmunityLogTableEntry
    MAX-ACCESS not-accessible
    STATUS     current
    DESCRIPTION
            ""
    INDEX {
            hmStatusWlanNoiseImmunityLogTableEntryIndex
          }
    ::= { hmStatusWlanNoiseImmunityLogTableTable 1 }

HmStatusWlanNoiseImmunityLogTableEntry ::= SEQUENCE {
            hmStatusWlanNoiseImmunityLogTableEntryIndex Integer32,
            hmStatusWlanNoiseImmunityLogTableEntryTime DisplayString,
            hmStatusWlanNoiseImmunityLogTableEntryInterface INTEGER,
            hmStatusWlanNoiseImmunityLogTableEntryRadioBand INTEGER,
            hmStatusWlanNoiseImmunityLogTableEntryRadioChannel Integer32,
            hmStatusWlanNoiseImmunityLogTableEntryEvent INTEGER,
            hmStatusWlanNoiseImmunityLogTableEntryParameter INTEGER,
            hmStatusWlanNoiseImmunityLogTableEntryValue Integer32
    }

-- {COLUMN} 1.3.6.1.4.1.248.32.18.1.3.63.2.1.1
hmStatusWlanNoiseImmunityLogTableEntryIndex OBJECT-TYPE
    SYNTAX     Integer32 (0..2147483647)
    MAX-ACCESS read-only
    STATUS     current
    DESCRIPTION
            "-- empty --"
    ::= { hmStatusWlanNoiseImmunityLogTableEntry 1 }

-- {COLUMN} 1.3.6.1.4.1.248.32.18.1.3.63.2.1.2
hmStatusWlanNoiseImmunityLogTableEntryTime OBJECT-TYPE
    SYNTAX     DisplayString (SIZE(0..255))
    MAX-ACCESS read-only
    STATUS     current
    DESCRIPTION
            "-- empty --"
    ::= { hmStatusWlanNoiseImmunityLogTableEntry 2 }

-- {COLUMN} 1.3.6.1.4.1.248.32.18.1.3.63.2.1.3
hmStatusWlanNoiseImmunityLogTableEntryInterface OBJECT-TYPE
    SYNTAX     INTEGER {
                  eWlan1 (0),
                  eWlan2 (1),
                  eWlan3 (2),
                  eWlan4 (3)
            }
    MAX-ACCESS read-only
    STATUS     current
    DESCRIPTION
            "-- empty --"
    ::= { hmStatusWlanNoiseImmunityLogTableEntry 3 }

-- {COLUMN} 1.3.6.1.4.1.248.32.18.1.3.63.2.1.4
hmStatusWlanNoiseImmunityLogTableEntryRadioBand OBJECT-TYPE
    SYNTAX     INTEGER {
                  eUnknown (0),
                  e24ghz (1),
                  e5ghz (2)
            }
    MAX-ACCESS read-only
    STATUS     current
    DESCRIPTION
            "-- empty --"
    ::= { hmStatusWlanNoiseImmunityLogTableEntry 4 }

-- {COLUMN} 1.3.6.1.4.1.248.32.18.1.3.63.2.1.5
hmStatusWlanNoiseImmunityLogTableEntryRadioChannel OBJECT-TYPE
    SYNTAX     Integer32 (0..255)
    MAX-ACCESS read-only
    STATUS     current
    DESCRIPTION
            "-- empty --"
    ::= { hmStatusWlanNoiseImmunityLogTableEntry 5 }

-- {COLUMN} 1.3.6.1.4.1.248.32.18.1.3.63.2.1.6
hmStatusWlanNoiseImmunityLogTableEntryEvent OBJECT-TYPE
    SYNTAX     INTEGER {
                  eValueChange (0),
                  eOfdmMaxImmunity (1),
                  eCckMaxImmunity (2),
                  eMinImmunity (3),
                  eNotAvailable (4),
                  eEventRepeated (5)
            }
    MAX-ACCESS read-only
    STATUS     current
    DESCRIPTION
            "-- empty --"
    ::= { hmStatusWlanNoiseImmunityLogTableEntry 6 }

-- {COLUMN} 1.3.6.1.4.1.248.32.18.1.3.63.2.1.7
hmStatusWlanNoiseImmunityLogTableEntryParameter OBJECT-TYPE
    SYNTAX     INTEGER {
                  eNone (0),
                  eNoiseImmunityLevel (1),
                  eOfdmWeakSignalDetection (2),
                  eCckWeakSignalDetectionThreshold (3),
                  eFirStepLevel (4),
                  eSpuriousImmunityLevel (5),
                  eMrcCck (8)
            }
    MAX-ACCESS read-only
    STATUS     current
    DESCRIPTION
            "-- empty --"
    ::= { hmStatusWlanNoiseImmunityLogTableEntry 7 }

-- {COLUMN} 1.3.6.1.4.1.248.32.18.1.3.63.2.1.8
hmStatusWlanNoiseImmunityLogTableEntryValue OBJECT-TYPE
    SYNTAX     Integer32 (0..255)
    MAX-ACCESS read-only
    STATUS     current
    DESCRIPTION
            "-- empty --"
    ::= { hmStatusWlanNoiseImmunityLogTableEntry 8 }

-- {TABLE} 1.3.6.1.4.1.248.32.18.1.3.64
hmStatusWlanEncryptionTable OBJECT-TYPE
    SYNTAX     SEQUENCE OF HmStatusWlanEncryptionEntry
    MAX-ACCESS not-accessible
    STATUS     current
    DESCRIPTION
            "-- empty --"
    ::= { hmStatusWlan 64 }

-- {ROW} 1.3.6.1.4.1.248.32.18.1.3.64.1
hmStatusWlanEncryptionEntry OBJECT-TYPE
    SYNTAX     HmStatusWlanEncryptionEntry
    MAX-ACCESS not-accessible
    STATUS     current
    DESCRIPTION
            ""
    INDEX {
            hmStatusWlanEncryptionEntryInterface
          }
    ::= { hmStatusWlanEncryptionTable 1 }

HmStatusWlanEncryptionEntry ::= SEQUENCE {
            hmStatusWlanEncryptionEntryInterface INTEGER,
            hmStatusWlanEncryptionEntryEncryption INTEGER,
            hmStatusWlanEncryptionEntryMethod INTEGER,
            hmStatusWlanEncryptionEntryWpaVersion INTEGER,
            hmStatusWlanEncryptionEntryWpa1SessionKeytypes INTEGER,
            hmStatusWlanEncryptionEntryWpa2SessionKeytypes INTEGER,
            hmStatusWlanEncryptionEntryProtMgmtFrames INTEGER,
            hmStatusWlanEncryptionEntryPmkCaching INTEGER,
            hmStatusWlanEncryptionEntryPreAuthentication INTEGER,
            hmStatusWlanEncryptionEntryOkc INTEGER,
            hmStatusWlanEncryptionEntryWpa2KeyManagement BITS,
            hmStatusWlanEncryptionEntryWpaPskNumWrongPassphrase Counter32,
            hmStatusWlanEncryptionEntryWpaPskNumSuccess Counter32,
            hmStatusWlanEncryptionEntryWpaPskNumFailures Counter32
    }

-- {COLUMN} 1.3.6.1.4.1.248.32.18.1.3.64.1.1
hmStatusWlanEncryptionEntryInterface OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan22 (32),
                  eWlan23 (33),
                  eWlan24 (34),
                  eWlan25 (35),
                  eWlan26 (36),
                  eWlan27 (37),
                  eWlan28 (38)
            }
    MAX-ACCESS read-only
    STATUS     current
    DESCRIPTION
            "-- empty --"
    ::= { hmStatusWlanEncryptionEntry 1 }

-- {COLUMN} 1.3.6.1.4.1.248.32.18.1.3.64.1.2
hmStatusWlanEncryptionEntryEncryption OBJECT-TYPE
    SYNTAX     INTEGER {
                  eNo (0),
                  eYes (2)
            }
    MAX-ACCESS read-only
    STATUS     current
    DESCRIPTION
            "-- empty --"
    ::= { hmStatusWlanEncryptionEntry 2 }

-- {COLUMN} 1.3.6.1.4.1.248.32.18.1.3.64.1.4
hmStatusWlanEncryptionEntryMethod OBJECT-TYPE
    SYNTAX     INTEGER {
                  eNone (0),
                  eWep40Bits (5),
                  eWep104Bits (13),
                  eWep128Bits (16),
                  e80211iWpaPsk (32),
                  e80211iWpa8021x (33),
                  eWep40Bits8021x (34),
                  eWep104Bits8021x (35),
                  eWep128Bits8021x (36)
            }
    MAX-ACCESS read-only
    STATUS     current
    DESCRIPTION
            "-- empty --"
    ::= { hmStatusWlanEncryptionEntry 4 }

-- {COLUMN} 1.3.6.1.4.1.248.32.18.1.3.64.1.9
hmStatusWlanEncryptionEntryWpaVersion OBJECT-TYPE
    SYNTAX     INTEGER {
                  eNone (0),
                  eWpa1 (2),
                  eWpa2 (4),
                  eWpa12 (6)
            }
    MAX-ACCESS read-only
    STATUS     current
    DESCRIPTION
            "-- empty --"
    ::= { hmStatusWlanEncryptionEntry 9 }

-- {COLUMN} 1.3.6.1.4.1.248.32.18.1.3.64.1.12
hmStatusWlanEncryptionEntryWpa1SessionKeytypes OBJECT-TYPE
    SYNTAX     INTEGER {
                  eNone (0),
                  eTkip (1),
                  eAes (2),
                  eTkipAes (3)
            }
    MAX-ACCESS read-only
    STATUS     current
    DESCRIPTION
            "-- empty --"
    ::= { hmStatusWlanEncryptionEntry 12 }

-- {COLUMN} 1.3.6.1.4.1.248.32.18.1.3.64.1.13
hmStatusWlanEncryptionEntryWpa2SessionKeytypes OBJECT-TYPE
    SYNTAX     INTEGER {
                  eNone (0),
                  eTkip (1),
                  eAes (2),
                  eTkipAes (3)
            }
    MAX-ACCESS read-only
    STATUS     current
    DESCRIPTION
            "-- empty --"
    ::= { hmStatusWlanEncryptionEntry 13 }

-- {COLUMN} 1.3.6.1.4.1.248.32.18.1.3.64.1.14
hmStatusWlanEncryptionEntryProtMgmtFrames OBJECT-TYPE
    SYNTAX     INTEGER {
                  eNo (0),
                  eOptional (1),
                  eMandatory (2)
            }
    MAX-ACCESS read-only
    STATUS     current
    DESCRIPTION
            "-- empty --"
    ::= { hmStatusWlanEncryptionEntry 14 }

-- {COLUMN} 1.3.6.1.4.1.248.32.18.1.3.64.1.15
hmStatusWlanEncryptionEntryPmkCaching OBJECT-TYPE
    SYNTAX     INTEGER {
                  eNo (0),
                  eYes (1)
            }
    MAX-ACCESS read-only
    STATUS     current
    DESCRIPTION
            "-- empty --"
    ::= { hmStatusWlanEncryptionEntry 15 }

-- {COLUMN} 1.3.6.1.4.1.248.32.18.1.3.64.1.16
hmStatusWlanEncryptionEntryPreAuthentication OBJECT-TYPE
    SYNTAX     INTEGER {
                  eNo (0),
                  eYes (1)
            }
    MAX-ACCESS read-only
    STATUS     current
    DESCRIPTION
            "-- empty --"
    ::= { hmStatusWlanEncryptionEntry 16 }

-- {COLUMN} 1.3.6.1.4.1.248.32.18.1.3.64.1.17
hmStatusWlanEncryptionEntryOkc OBJECT-TYPE
    SYNTAX     INTEGER {
                  eNo (0),
                  eYes (1)
            }
    MAX-ACCESS read-only
    STATUS     current
    DESCRIPTION
            "-- empty --"
    ::= { hmStatusWlanEncryptionEntry 17 }

-- {COLUMN} 1.3.6.1.4.1.248.32.18.1.3.64.1.19
hmStatusWlanEncryptionEntryWpa2KeyManagement OBJECT-TYPE
    SYNTAX     BITS {
                  eSha256 (5),
                  eFastRoaming (6),
                  eStandard (7)
            }
    MAX-ACCESS read-only
    STATUS     current
    DESCRIPTION
            "-- empty --"
    ::= { hmStatusWlanEncryptionEntry 19 }

-- {COLUMN} 1.3.6.1.4.1.248.32.18.1.3.64.1.20
hmStatusWlanEncryptionEntryWpaPskNumWrongPassphrase OBJECT-TYPE
    SYNTAX     Counter32
    MAX-ACCESS read-only
    STATUS     current
    DESCRIPTION
            "-- empty --"
    ::= { hmStatusWlanEncryptionEntry 20 }

-- {COLUMN} 1.3.6.1.4.1.248.32.18.1.3.64.1.21
hmStatusWlanEncryptionEntryWpaPskNumSuccess OBJECT-TYPE
    SYNTAX     Counter32
    MAX-ACCESS read-only
    STATUS     current
    DESCRIPTION
            "-- empty --"
    ::= { hmStatusWlanEncryptionEntry 21 }

-- {COLUMN} 1.3.6.1.4.1.248.32.18.1.3.64.1.22
hmStatusWlanEncryptionEntryWpaPskNumFailures OBJECT-TYPE
    SYNTAX     Counter32
    MAX-ACCESS read-only
    STATUS     current
    DESCRIPTION
            "-- empty --"
    ::= { hmStatusWlanEncryptionEntry 22 }

-- {TABLE} 1.3.6.1.4.1.248.32.18.1.3.66
hmStatusWlanTransmissionTable OBJECT-TYPE
    SYNTAX     SEQUENCE OF HmStatusWlanTransmissionEntry
    MAX-ACCESS not-accessible
    STATUS     current
    DESCRIPTION
            "-- empty --"
    ::= { hmStatusWlan 66 }

-- {ROW} 1.3.6.1.4.1.248.32.18.1.3.66.1
hmStatusWlanTransmissionEntry OBJECT-TYPE
    SYNTAX     HmStatusWlanTransmissionEntry
    MAX-ACCESS not-accessible
    STATUS     current
    DESCRIPTION
            ""
    INDEX {
            hmStatusWlanTransmissionEntryInterface
          }
    ::= { hmStatusWlanTransmissionTable 1 }

HmStatusWlanTransmissionEntry ::= SEQUENCE {
            hmStatusWlanTransmissionEntryInterface INTEGER,
            hmStatusWlanTransmissionEntryPacketSize Integer32,
            hmStatusWlanTransmissionEntryMinTxRate INTEGER,
            hmStatusWlanTransmissionEntryBasicRate INTEGER,
            hmStatusWlanTransmissionEntryRtsThreshold Integer32,
            hmStatusWlanTransmissionEntry11bPreamble INTEGER,
            hmStatusWlanTransmissionEntryMaxTxRate INTEGER,
            hmStatusWlanTransmissionEntryMinFragLen Integer32,
            hmStatusWlanTransmissionEntrySoftRetries Integer32,
            hmStatusWlanTransmissionEntryHardRetries Integer32,
            hmStatusWlanTransmissionEntryShortGuardInterval INTEGER,
            hmStatusWlanTransmissionEntryMaxSpatialStreams INTEGER,
            hmStatusWlanTransmissionEntrySendAggregates INTEGER,
            hmStatusWlanTransmissionEntryMinHtMcs INTEGER,
            hmStatusWlanTransmissionEntryMaxHtMcs INTEGER,
            hmStatusWlanTransmissionEntryMinSpatialStreams INTEGER,
            hmStatusWlanTransmissionEntryEapolRate INTEGER,
            hmStatusWlanTransmissionEntryMaxAggrPacketCount Integer32,
            hmStatusWlanTransmissionEntryProberspRetries Integer32,
            hmStatusWlanTransmissionEntryReceiveAggregates INTEGER,
            hmStatusWlanTransmissionEntryUseStbc INTEGER,
            hmStatusWlanTransmissionEntryUseLdpc INTEGER,
            hmStatusWlanTransmissionEntryConvertToUnicast BITS
    }

-- {COLUMN} 1.3.6.1.4.1.248.32.18.1.3.66.1.1
hmStatusWlanTransmissionEntryInterface OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan22 (32),
                  eWlan23 (33),
                  eWlan24 (34),
                  eWlan25 (35),
                  eWlan26 (36),
                  eWlan27 (37),
                  eWlan28 (38)
            }
    MAX-ACCESS read-only
    STATUS     current
    DESCRIPTION
            "-- empty --"
    ::= { hmStatusWlanTransmissionEntry 1 }

-- {COLUMN} 1.3.6.1.4.1.248.32.18.1.3.66.1.2
hmStatusWlanTransmissionEntryPacketSize OBJECT-TYPE
    SYNTAX     Integer32 (0..65535)
    MAX-ACCESS read-only
    STATUS     current
    DESCRIPTION
            "-- empty --"
    ::= { hmStatusWlanTransmissionEntry 2 }

-- {COLUMN} 1.3.6.1.4.1.248.32.18.1.3.66.1.3
hmStatusWlanTransmissionEntryMinTxRate OBJECT-TYPE
    SYNTAX     INTEGER {
                  eAuto (0),
                  e1M (1),
                  e2M (2),
                  e5M5 (4),
                  e11M (6),
                  e6M (8),
                  e9M (9),
                  e12M (10),
                  e18M (11),
                  e24M (12),
                  e36M (13),
                  e48M (14),
                  e54M (15)
            }
    MAX-ACCESS read-only
    STATUS     current
    DESCRIPTION
            "-- empty --"
    ::= { hmStatusWlanTransmissionEntry 3 }

-- {COLUMN} 1.3.6.1.4.1.248.32.18.1.3.66.1.4
hmStatusWlanTransmissionEntryBasicRate OBJECT-TYPE
    SYNTAX     INTEGER {
                  eAuto (0),
                  e1M (1),
                  e2M (2),
                  e5M5 (4),
                  e11M (6),
                  e6M (8),
                  e9M (9),
                  e12M (10),
                  e18M (11),
                  e24M (12),
                  e36M (13),
                  e48M (14),
                  e54M (15)
            }
    MAX-ACCESS read-only
    STATUS     current
    DESCRIPTION
            "-- empty --"
    ::= { hmStatusWlanTransmissionEntry 4 }

-- {COLUMN} 1.3.6.1.4.1.248.32.18.1.3.66.1.6
hmStatusWlanTransmissionEntryRtsThreshold OBJECT-TYPE
    SYNTAX     Integer32 (0..65535)
    MAX-ACCESS read-only
    STATUS     current
    DESCRIPTION
            "-- empty --"
    ::= { hmStatusWlanTransmissionEntry 6 }

-- {COLUMN} 1.3.6.1.4.1.248.32.18.1.3.66.1.7
hmStatusWlanTransmissionEntry11bPreamble OBJECT-TYPE
    SYNTAX     INTEGER {
                  eAuto (0),
                  eLong (1)
            }
    MAX-ACCESS read-only
    STATUS     current
    DESCRIPTION
            "-- empty --"
    ::= { hmStatusWlanTransmissionEntry 7 }

-- {COLUMN} 1.3.6.1.4.1.248.32.18.1.3.66.1.9
hmStatusWlanTransmissionEntryMaxTxRate OBJECT-TYPE
    SYNTAX     INTEGER {
                  eAuto (0),
                  e1M (1),
                  e2M (2),
                  e5M5 (4),
                  e11M (6),
                  e6M (8),
                  e9M (9),
                  e12M (10),
                  e18M (11),
                  e24M (12),
                  e36M (13),
                  e48M (14),
                  e54M (15)
            }
    MAX-ACCESS read-only
    STATUS     current
    DESCRIPTION
            "-- empty --"
    ::= { hmStatusWlanTransmissionEntry 9 }

-- {COLUMN} 1.3.6.1.4.1.248.32.18.1.3.66.1.10
hmStatusWlanTransmissionEntryMinFragLen OBJECT-TYPE
    SYNTAX     Integer32 (0..65535)
    MAX-ACCESS read-only
    STATUS     current
    DESCRIPTION
            "-- empty --"
    ::= { hmStatusWlanTransmissionEntry 10 }

-- {COLUMN} 1.3.6.1.4.1.248.32.18.1.3.66.1.11
hmStatusWlanTransmissionEntrySoftRetries OBJECT-TYPE
    SYNTAX     Integer32 (0..255)
    MAX-ACCESS read-only
    STATUS     current
    DESCRIPTION
            "-- empty --"
    ::= { hmStatusWlanTransmissionEntry 11 }

-- {COLUMN} 1.3.6.1.4.1.248.32.18.1.3.66.1.12
hmStatusWlanTransmissionEntryHardRetries OBJECT-TYPE
    SYNTAX     Integer32 (0..255)
    MAX-ACCESS read-only
    STATUS     current
    DESCRIPTION
            "-- empty --"
    ::= { hmStatusWlanTransmissionEntry 12 }

-- {COLUMN} 1.3.6.1.4.1.248.32.18.1.3.66.1.13
hmStatusWlanTransmissionEntryShortGuardInterval OBJECT-TYPE
    SYNTAX     INTEGER {
                  eAuto (0),
                  eNo (1)
            }
    MAX-ACCESS read-only
    STATUS     current
    DESCRIPTION
            "-- empty --"
    ::= { hmStatusWlanTransmissionEntry 13 }

-- {COLUMN} 1.3.6.1.4.1.248.32.18.1.3.66.1.14
hmStatusWlanTransmissionEntryMaxSpatialStreams OBJECT-TYPE
    SYNTAX     INTEGER {
                  eAuto (0),
                  eOne (1),
                  eTwo (2),
                  eThree (3)
            }
    MAX-ACCESS read-only
    STATUS     current
    DESCRIPTION
            "-- empty --"
    ::= { hmStatusWlanTransmissionEntry 14 }

-- {COLUMN} 1.3.6.1.4.1.248.32.18.1.3.66.1.15
hmStatusWlanTransmissionEntrySendAggregates OBJECT-TYPE
    SYNTAX     INTEGER {
                  eNo (0),
                  eYes (1)
            }
    MAX-ACCESS read-only
    STATUS     current
    DESCRIPTION
            "-- empty --"
    ::= { hmStatusWlanTransmissionEntry 15 }

-- {COLUMN} 1.3.6.1.4.1.248.32.18.1.3.66.1.16
hmStatusWlanTransmissionEntryMinHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-only
    STATUS     current
    DESCRIPTION
            "-- empty --"
    ::= { hmStatusWlanTransmissionEntry 16 }

-- {COLUMN} 1.3.6.1.4.1.248.32.18.1.3.66.1.17
hmStatusWlanTransmissionEntryMaxHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-only
    STATUS     current
    DESCRIPTION
            "-- empty --"
    ::= { hmStatusWlanTransmissionEntry 17 }

-- {COLUMN} 1.3.6.1.4.1.248.32.18.1.3.66.1.18
hmStatusWlanTransmissionEntryMinSpatialStreams OBJECT-TYPE
    SYNTAX     INTEGER {
                  eAuto (0),
                  eOne (1),
                  eTwo (2),
                  eThree (3)
            }
    MAX-ACCESS read-only
    STATUS     current
    DESCRIPTION
            "-- empty --"
    ::= { hmStatusWlanTransmissionEntry 18 }

-- {COLUMN} 1.3.6.1.4.1.248.32.18.1.3.66.1.19
hmStatusWlanTransmissionEntryEapolRate OBJECT-TYPE
    SYNTAX     INTEGER {
                  eLikeData (0),
                  e1M (1),
                  e2M (2),
                  e5M5 (4),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51)
            }
    MAX-ACCESS read-only
    STATUS     current
    DESCRIPTION
            "-- empty --"
    ::= { hmStatusWlanTransmissionEntry 19 }

-- {COLUMN} 1.3.6.1.4.1.248.32.18.1.3.66.1.20
hmStatusWlanTransmissionEntryMaxAggrPacketCount OBJECT-TYPE
    SYNTAX     Integer32 (0..255)
    MAX-ACCESS read-only
    STATUS     current
    DESCRIPTION
            "-- empty --"
    ::= { hmStatusWlanTransmissionEntry 20 }

-- {COLUMN} 1.3.6.1.4.1.248.32.18.1.3.66.1.21
hmStatusWlanTransmissionEntryProberspRetries OBJECT-TYPE
    SYNTAX     Integer32 (0..255)
    MAX-ACCESS read-only
    STATUS     current
    DESCRIPTION
            "-- empty --"
    ::= { hmStatusWlanTransmissionEntry 21 }

-- {COLUMN} 1.3.6.1.4.1.248.32.18.1.3.66.1.22
hmStatusWlanTransmissionEntryReceiveAggregates OBJECT-TYPE
    SYNTAX     INTEGER {
                  eNo (0),
                  eYes (1)
            }
    MAX-ACCESS read-only
    STATUS     current
    DESCRIPTION
            "-- empty --"
    ::= { hmStatusWlanTransmissionEntry 22 }

-- {COLUMN} 1.3.6.1.4.1.248.32.18.1.3.66.1.23
hmStatusWlanTransmissionEntryUseStbc OBJECT-TYPE
    SYNTAX     INTEGER {
                  eNo (0),
                  eYes (1)
            }
    MAX-ACCESS read-only
    STATUS     current
    DESCRIPTION
            "-- empty --"
    ::= { hmStatusWlanTransmissionEntry 23 }

-- {COLUMN} 1.3.6.1.4.1.248.32.18.1.3.66.1.24
hmStatusWlanTransmissionEntryUseLdpc OBJECT-TYPE
    SYNTAX     INTEGER {
                  eNo (0),
                  eYes (1)
            }
    MAX-ACCESS read-only
    STATUS     current
    DESCRIPTION
            "-- empty --"
    ::= { hmStatusWlanTransmissionEntry 24 }

-- {COLUMN} 1.3.6.1.4.1.248.32.18.1.3.66.1.25
hmStatusWlanTransmissionEntryConvertToUnicast OBJECT-TYPE
    SYNTAX     BITS {
                  eDhcp (31)
            }
    MAX-ACCESS read-only
    STATUS     current
    DESCRIPTION
            "-- empty --"
    ::= { hmStatusWlanTransmissionEntry 25 }

-- {TABLE} 1.3.6.1.4.1.248.32.18.1.3.70
hmStatusWlanVlanGroupkeyMappingTable OBJECT-TYPE
    SYNTAX     SEQUENCE OF HmStatusWlanVlanGroupkeyMappingEntry
    MAX-ACCESS not-accessible
    STATUS     current
    DESCRIPTION
            "-- empty --"
    ::= { hmStatusWlan 70 }

-- {ROW} 1.3.6.1.4.1.248.32.18.1.3.70.1
hmStatusWlanVlanGroupkeyMappingEntry OBJECT-TYPE
    SYNTAX     HmStatusWlanVlanGroupkeyMappingEntry
    MAX-ACCESS not-accessible
    STATUS     current
    DESCRIPTION
            ""
    INDEX {
            hmStatusWlanVlanGroupkeyMappingEntryNetwork,
            hmStatusWlanVlanGroupkeyMappingEntryVlanId
          }
    ::= { hmStatusWlanVlanGroupkeyMappingTable 1 }

HmStatusWlanVlanGroupkeyMappingEntry ::= SEQUENCE {
            hmStatusWlanVlanGroupkeyMappingEntryNetwork INTEGER,
            hmStatusWlanVlanGroupkeyMappingEntryVlanId Integer32,
            hmStatusWlanVlanGroupkeyMappingEntryGroupkeyIndex Integer32,
            hmStatusWlanVlanGroupkeyMappingEntrySource INTEGER
    }

-- {COLUMN} 1.3.6.1.4.1.248.32.18.1.3.70.1.1
hmStatusWlanVlanGroupkeyMappingEntryNetwork OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan22 (32),
                  eWlan23 (33),
                  eWlan24 (34),
                  eWlan25 (35),
                  eWlan26 (36),
                  eWlan27 (37),
                  eWlan28 (38)
            }
    MAX-ACCESS read-only
    STATUS     current
    DESCRIPTION
            "-- empty --"
    ::= { hmStatusWlanVlanGroupkeyMappingEntry 1 }

-- {COLUMN} 1.3.6.1.4.1.248.32.18.1.3.70.1.2
hmStatusWlanVlanGroupkeyMappingEntryVlanId OBJECT-TYPE
    SYNTAX     Integer32 (0..65535)
    MAX-ACCESS read-only
    STATUS     current
    DESCRIPTION
            "-- empty --"
    ::= { hmStatusWlanVlanGroupkeyMappingEntry 2 }

-- {COLUMN} 1.3.6.1.4.1.248.32.18.1.3.70.1.3
hmStatusWlanVlanGroupkeyMappingEntryGroupkeyIndex OBJECT-TYPE
    SYNTAX     Integer32 (0..255)
    MAX-ACCESS read-only
    STATUS     current
    DESCRIPTION
            "-- empty --"
    ::= { hmStatusWlanVlanGroupkeyMappingEntry 3 }

-- {COLUMN} 1.3.6.1.4.1.248.32.18.1.3.70.1.4
hmStatusWlanVlanGroupkeyMappingEntrySource OBJECT-TYPE
    SYNTAX     INTEGER {
                  eManual (1),
                  eAutomatic (2)
            }
    MAX-ACCESS read-only
    STATUS     current
    DESCRIPTION
            "-- empty --"
    ::= { hmStatusWlanVlanGroupkeyMappingEntry 4 }

-- {SCALAR} 1.3.6.1.4.1.248.32.18.1.3.100
hmStatusWlanDfsForceRescan OBJECT-TYPE
    SYNTAX     DisplayString
    MAX-ACCESS read-write
    STATUS     current
    DESCRIPTION
            "-- empty --"
    ::= { hmStatusWlan 100 }

-- {TABLE} 1.3.6.1.4.1.248.32.18.1.3.101
hmStatusWlanDfsStatisticsTable OBJECT-TYPE
    SYNTAX     SEQUENCE OF HmStatusWlanDfsStatisticsEntry
    MAX-ACCESS not-accessible
    STATUS     current
    DESCRIPTION
            "-- empty --"
    ::= { hmStatusWlan 101 }

-- {ROW} 1.3.6.1.4.1.248.32.18.1.3.101.1
hmStatusWlanDfsStatisticsEntry OBJECT-TYPE
    SYNTAX     HmStatusWlanDfsStatisticsEntry
    MAX-ACCESS not-accessible
    STATUS     current
    DESCRIPTION
            ""
    INDEX {
            hmStatusWlanDfsStatisticsEntryIfc
          }
    ::= { hmStatusWlanDfsStatisticsTable 1 }

HmStatusWlanDfsStatisticsEntry ::= SEQUENCE {
            hmStatusWlanDfsStatisticsEntryIfc INTEGER,
            hmStatusWlanDfsStatisticsEntryNumDetections Integer32,
            hmStatusWlanDfsStatisticsEntryLastDetection DisplayString
    }

-- {COLUMN} 1.3.6.1.4.1.248.32.18.1.3.101.1.1
hmStatusWlanDfsStatisticsEntryIfc OBJECT-TYPE
    SYNTAX     INTEGER {
                  eWlan1 (1),
                  eWlan2 (2)
            }
    MAX-ACCESS read-only
    STATUS     current
    DESCRIPTION
            "-- empty --"
    ::= { hmStatusWlanDfsStatisticsEntry 1 }

-- {COLUMN} 1.3.6.1.4.1.248.32.18.1.3.101.1.2
hmStatusWlanDfsStatisticsEntryNumDetections OBJECT-TYPE
    SYNTAX     Integer32 (0..2147483647)
    MAX-ACCESS read-only
    STATUS     current
    DESCRIPTION
            "-- empty --"
    ::= { hmStatusWlanDfsStatisticsEntry 2 }

-- {COLUMN} 1.3.6.1.4.1.248.32.18.1.3.101.1.3
hmStatusWlanDfsStatisticsEntryLastDetection OBJECT-TYPE
    SYNTAX     DisplayString (SIZE(0..21))
    MAX-ACCESS read-only
    STATUS     current
    DESCRIPTION
            "-- empty --"
    ::= { hmStatusWlanDfsStatisticsEntry 3 }

-- {NODE} 1.3.6.1.4.1.248.32.18.1.3.248
hmStatusWlanWirelessIds OBJECT IDENTIFIER ::= { hmStatusWlan 248 }

-- {TABLE} 1.3.6.1.4.1.248.32.18.1.3.248.1
hmStatusWlanWirelessIdsEventTableTable OBJECT-TYPE
    SYNTAX     SEQUENCE OF HmStatusWlanWirelessIdsEventTableEntry
    MAX-ACCESS not-accessible
    STATUS     current
    DESCRIPTION
            "-- empty --"
    ::= { hmStatusWlanWirelessIds 1 }

-- {ROW} 1.3.6.1.4.1.248.32.18.1.3.248.1.1
hmStatusWlanWirelessIdsEventTableEntry OBJECT-TYPE
    SYNTAX     HmStatusWlanWirelessIdsEventTableEntry
    MAX-ACCESS not-accessible
    STATUS     current
    DESCRIPTION
            ""
    INDEX {
            hmStatusWlanWirelessIdsEventTableEntryEventType,
            hmStatusWlanWirelessIdsEventTableEntryId
          }
    ::= { hmStatusWlanWirelessIdsEventTableTable 1 }

HmStatusWlanWirelessIdsEventTableEntry ::= SEQUENCE {
            hmStatusWlanWirelessIdsEventTableEntryEventType INTEGER,
            hmStatusWlanWirelessIdsEventTableEntryId Integer32,
            hmStatusWlanWirelessIdsEventTableEntryEventTime DisplayString,
            hmStatusWlanWirelessIdsEventTableEntryEventRate Integer32,
            hmStatusWlanWirelessIdsEventTableEntryInterface INTEGER,
            hmStatusWlanWirelessIdsEventTableEntryAttackerMac MacAddress
    }

-- {COLUMN} 1.3.6.1.4.1.248.32.18.1.3.248.1.1.1
hmStatusWlanWirelessIdsEventTableEntryEventType OBJECT-TYPE
    SYNTAX     INTEGER {
                  eEapolstart (1),
                  eProbebroad (2),
                  eDeauthenticatebroad (3),
                  eDeauthenticate (4),
                  eAssociatereq (5),
                  eReassociatereq (6),
                  eAuthenticate (7),
                  eDisassociate (8),
                  eGenericerror (9),
                  eBlockackAttack (10),
                  eDelba (11),
                  eNulldatadosattack (12),
                  eNulldatapsAttack (13),
                  ePsPollAttack (14),
                  eSmpsAttack (15),
                  eDisassociatebroad (17)
            }
    MAX-ACCESS read-only
    STATUS     current
    DESCRIPTION
            "-- empty --"
    ::= { hmStatusWlanWirelessIdsEventTableEntry 1 }

-- {COLUMN} 1.3.6.1.4.1.248.32.18.1.3.248.1.1.2
hmStatusWlanWirelessIdsEventTableEntryId OBJECT-TYPE
    SYNTAX     Integer32 (0..2147483647)
    MAX-ACCESS read-only
    STATUS     current
    DESCRIPTION
            "-- empty --"
    ::= { hmStatusWlanWirelessIdsEventTableEntry 2 }

-- {COLUMN} 1.3.6.1.4.1.248.32.18.1.3.248.1.1.3
hmStatusWlanWirelessIdsEventTableEntryEventTime OBJECT-TYPE
    SYNTAX     DisplayString (SIZE(0..255))
    MAX-ACCESS read-only
    STATUS     current
    DESCRIPTION
            "-- empty --"
    ::= { hmStatusWlanWirelessIdsEventTableEntry 3 }

-- {COLUMN} 1.3.6.1.4.1.248.32.18.1.3.248.1.1.4
hmStatusWlanWirelessIdsEventTableEntryEventRate OBJECT-TYPE
    SYNTAX     Integer32 (0..2147483647)
    MAX-ACCESS read-only
    STATUS     current
    DESCRIPTION
            "-- empty --"
    ::= { hmStatusWlanWirelessIdsEventTableEntry 4 }

-- {COLUMN} 1.3.6.1.4.1.248.32.18.1.3.248.1.1.5
hmStatusWlanWirelessIdsEventTableEntryInterface OBJECT-TYPE
    SYNTAX     INTEGER {
                  eWlan1 (0),
                  eWlan2 (1),
                  eAny (2)
            }
    MAX-ACCESS read-only
    STATUS     current
    DESCRIPTION
            "-- empty --"
    ::= { hmStatusWlanWirelessIdsEventTableEntry 5 }

-- {COLUMN} 1.3.6.1.4.1.248.32.18.1.3.248.1.1.6
hmStatusWlanWirelessIdsEventTableEntryAttackerMac OBJECT-TYPE
    SYNTAX     MacAddress
    MAX-ACCESS read-only
    STATUS     current
    DESCRIPTION
            "-- empty --"
    ::= { hmStatusWlanWirelessIdsEventTableEntry 6 }

-- {NODE} 1.3.6.1.4.1.248.32.18.1.3.248.2
hmStatusWlanWirelessIdsSig OBJECT IDENTIFIER ::= { hmStatusWlanWirelessIds 2 }

-- {NODE} 1.3.6.1.4.1.248.32.18.1.3.248.2.1
hmStatusWlanWirelessIdsSigAssociatereqflood OBJECT IDENTIFIER ::= { hmStatusWlanWirelessIdsSig 1 }

-- {SCALAR} 1.3.6.1.4.1.248.32.18.1.3.248.2.1.1
hmStatusWlanWirelessIdsSigAssociatereqfloodCounter OBJECT-TYPE
    SYNTAX     Integer32 (0..2147483647)
    MAX-ACCESS read-only
    STATUS     current
    DESCRIPTION
            "-- empty --"
    ::= { hmStatusWlanWirelessIdsSigAssociatereqflood 1 }

-- {SCALAR} 1.3.6.1.4.1.248.32.18.1.3.248.2.1.2
hmStatusWlanWirelessIdsSigAssociatereqfloodAlarmState OBJECT-TYPE
    SYNTAX     INTEGER {
                  eNone (0),
                  eLimitReached (1)
            }
    MAX-ACCESS read-only
    STATUS     current
    DESCRIPTION
            "-- empty --"
    ::= { hmStatusWlanWirelessIdsSigAssociatereqflood 2 }

-- {NODE} 1.3.6.1.4.1.248.32.18.1.3.248.2.2
hmStatusWlanWirelessIdsSigReassociatereqflood OBJECT IDENTIFIER ::= { hmStatusWlanWirelessIdsSig 2 }

-- {SCALAR} 1.3.6.1.4.1.248.32.18.1.3.248.2.2.1
hmStatusWlanWirelessIdsSigReassociatereqfloodCounter OBJECT-TYPE
    SYNTAX     Integer32 (0..2147483647)
    MAX-ACCESS read-only
    STATUS     current
    DESCRIPTION
            "-- empty --"
    ::= { hmStatusWlanWirelessIdsSigReassociatereqflood 1 }

-- {SCALAR} 1.3.6.1.4.1.248.32.18.1.3.248.2.2.2
hmStatusWlanWirelessIdsSigReassociatereqfloodAlarmState OBJECT-TYPE
    SYNTAX     INTEGER {
                  eNone (0),
                  eLimitReached (1)
            }
    MAX-ACCESS read-only
    STATUS     current
    DESCRIPTION
            "-- empty --"
    ::= { hmStatusWlanWirelessIdsSigReassociatereqflood 2 }

-- {NODE} 1.3.6.1.4.1.248.32.18.1.3.248.2.3
hmStatusWlanWirelessIdsSigAuthenticatereqflood OBJECT IDENTIFIER ::= { hmStatusWlanWirelessIdsSig 3 }

-- {SCALAR} 1.3.6.1.4.1.248.32.18.1.3.248.2.3.1
hmStatusWlanWirelessIdsSigAuthenticatereqfloodCounter OBJECT-TYPE
    SYNTAX     Integer32 (0..2147483647)
    MAX-ACCESS read-only
    STATUS     current
    DESCRIPTION
            "-- empty --"
    ::= { hmStatusWlanWirelessIdsSigAuthenticatereqflood 1 }

-- {SCALAR} 1.3.6.1.4.1.248.32.18.1.3.248.2.3.2
hmStatusWlanWirelessIdsSigAuthenticatereqfloodAlarmState OBJECT-TYPE
    SYNTAX     INTEGER {
                  eNone (0),
                  eLimitReached (1)
            }
    MAX-ACCESS read-only
    STATUS     current
    DESCRIPTION
            "-- empty --"
    ::= { hmStatusWlanWirelessIdsSigAuthenticatereqflood 2 }

-- {NODE} 1.3.6.1.4.1.248.32.18.1.3.248.2.4
hmStatusWlanWirelessIdsSigEapolstart OBJECT IDENTIFIER ::= { hmStatusWlanWirelessIdsSig 4 }

-- {SCALAR} 1.3.6.1.4.1.248.32.18.1.3.248.2.4.1
hmStatusWlanWirelessIdsSigEapolstartCounter OBJECT-TYPE
    SYNTAX     Integer32 (0..2147483647)
    MAX-ACCESS read-only
    STATUS     current
    DESCRIPTION
            "-- empty --"
    ::= { hmStatusWlanWirelessIdsSigEapolstart 1 }

-- {SCALAR} 1.3.6.1.4.1.248.32.18.1.3.248.2.4.2
hmStatusWlanWirelessIdsSigEapolstartAlarmState OBJECT-TYPE
    SYNTAX     INTEGER {
                  eNone (0),
                  eLimitReached (1)
            }
    MAX-ACCESS read-only
    STATUS     current
    DESCRIPTION
            "-- empty --"
    ::= { hmStatusWlanWirelessIdsSigEapolstart 2 }

-- {NODE} 1.3.6.1.4.1.248.32.18.1.3.248.2.5
hmStatusWlanWirelessIdsSigProbebroadcast OBJECT IDENTIFIER ::= { hmStatusWlanWirelessIdsSig 5 }

-- {SCALAR} 1.3.6.1.4.1.248.32.18.1.3.248.2.5.1
hmStatusWlanWirelessIdsSigProbebroadcastCounter OBJECT-TYPE
    SYNTAX     Integer32 (0..2147483647)
    MAX-ACCESS read-only
    STATUS     current
    DESCRIPTION
            "-- empty --"
    ::= { hmStatusWlanWirelessIdsSigProbebroadcast 1 }

-- {SCALAR} 1.3.6.1.4.1.248.32.18.1.3.248.2.5.2
hmStatusWlanWirelessIdsSigProbebroadcastAlarmState OBJECT-TYPE
    SYNTAX     INTEGER {
                  eNone (0),
                  eLimitReached (1)
            }
    MAX-ACCESS read-only
    STATUS     current
    DESCRIPTION
            "-- empty --"
    ::= { hmStatusWlanWirelessIdsSigProbebroadcast 2 }

-- {NODE} 1.3.6.1.4.1.248.32.18.1.3.248.2.6
hmStatusWlanWirelessIdsSigDisassociatebroadcast OBJECT IDENTIFIER ::= { hmStatusWlanWirelessIdsSig 6 }

-- {SCALAR} 1.3.6.1.4.1.248.32.18.1.3.248.2.6.1
hmStatusWlanWirelessIdsSigDisassociatebroadcastCounter OBJECT-TYPE
    SYNTAX     Integer32 (0..2147483647)
    MAX-ACCESS read-only
    STATUS     current
    DESCRIPTION
            "-- empty --"
    ::= { hmStatusWlanWirelessIdsSigDisassociatebroadcast 1 }

-- {SCALAR} 1.3.6.1.4.1.248.32.18.1.3.248.2.6.2
hmStatusWlanWirelessIdsSigDisassociatebroadcastAlarmState OBJECT-TYPE
    SYNTAX     INTEGER {
                  eNone (0),
                  eLimitReached (1)
            }
    MAX-ACCESS read-only
    STATUS     current
    DESCRIPTION
            "-- empty --"
    ::= { hmStatusWlanWirelessIdsSigDisassociatebroadcast 2 }

-- {NODE} 1.3.6.1.4.1.248.32.18.1.3.248.2.7
hmStatusWlanWirelessIdsSigDeauthenticatebroadcast OBJECT IDENTIFIER ::= { hmStatusWlanWirelessIdsSig 7 }

-- {SCALAR} 1.3.6.1.4.1.248.32.18.1.3.248.2.7.1
hmStatusWlanWirelessIdsSigDeauthenticatebroadcastCounter OBJECT-TYPE
    SYNTAX     Integer32 (0..2147483647)
    MAX-ACCESS read-only
    STATUS     current
    DESCRIPTION
            "-- empty --"
    ::= { hmStatusWlanWirelessIdsSigDeauthenticatebroadcast 1 }

-- {SCALAR} 1.3.6.1.4.1.248.32.18.1.3.248.2.7.2
hmStatusWlanWirelessIdsSigDeauthenticatebroadcastAlarmState OBJECT-TYPE
    SYNTAX     INTEGER {
                  eNone (0),
                  eLimitReached (1)
            }
    MAX-ACCESS read-only
    STATUS     current
    DESCRIPTION
            "-- empty --"
    ::= { hmStatusWlanWirelessIdsSigDeauthenticatebroadcast 2 }

-- {NODE} 1.3.6.1.4.1.248.32.18.1.3.248.2.8
hmStatusWlanWirelessIdsSigDisassociatereqflood OBJECT IDENTIFIER ::= { hmStatusWlanWirelessIdsSig 8 }

-- {SCALAR} 1.3.6.1.4.1.248.32.18.1.3.248.2.8.1
hmStatusWlanWirelessIdsSigDisassociatereqfloodCounter OBJECT-TYPE
    SYNTAX     Integer32 (0..2147483647)
    MAX-ACCESS read-only
    STATUS     current
    DESCRIPTION
            "-- empty --"
    ::= { hmStatusWlanWirelessIdsSigDisassociatereqflood 1 }

-- {SCALAR} 1.3.6.1.4.1.248.32.18.1.3.248.2.8.2
hmStatusWlanWirelessIdsSigDisassociatereqfloodAlarmState OBJECT-TYPE
    SYNTAX     INTEGER {
                  eNone (0),
                  eLimitReached (1)
            }
    MAX-ACCESS read-only
    STATUS     current
    DESCRIPTION
            "-- empty --"
    ::= { hmStatusWlanWirelessIdsSigDisassociatereqflood 2 }

-- {NODE} 1.3.6.1.4.1.248.32.18.1.3.248.2.9
hmStatusWlanWirelessIdsSigBlockackoutofwindow OBJECT IDENTIFIER ::= { hmStatusWlanWirelessIdsSig 9 }

-- {SCALAR} 1.3.6.1.4.1.248.32.18.1.3.248.2.9.1
hmStatusWlanWirelessIdsSigBlockackoutofwindowCounter OBJECT-TYPE
    SYNTAX     Integer32 (0..2147483647)
    MAX-ACCESS read-only
    STATUS     current
    DESCRIPTION
            "-- empty --"
    ::= { hmStatusWlanWirelessIdsSigBlockackoutofwindow 1 }

-- {SCALAR} 1.3.6.1.4.1.248.32.18.1.3.248.2.9.2
hmStatusWlanWirelessIdsSigBlockackoutofwindowAlarmState OBJECT-TYPE
    SYNTAX     INTEGER {
                  eNone (0),
                  eLimitReached (1)
            }
    MAX-ACCESS read-only
    STATUS     current
    DESCRIPTION
            "-- empty --"
    ::= { hmStatusWlanWirelessIdsSigBlockackoutofwindow 2 }

-- {NODE} 1.3.6.1.4.1.248.32.18.1.3.248.2.10
hmStatusWlanWirelessIdsSigBlockackafterdelba OBJECT IDENTIFIER ::= { hmStatusWlanWirelessIdsSig 10 }

-- {SCALAR} 1.3.6.1.4.1.248.32.18.1.3.248.2.10.1
hmStatusWlanWirelessIdsSigBlockackafterdelbaCounter OBJECT-TYPE
    SYNTAX     Integer32 (0..2147483647)
    MAX-ACCESS read-only
    STATUS     current
    DESCRIPTION
            "-- empty --"
    ::= { hmStatusWlanWirelessIdsSigBlockackafterdelba 1 }

-- {SCALAR} 1.3.6.1.4.1.248.32.18.1.3.248.2.10.2
hmStatusWlanWirelessIdsSigBlockackafterdelbaAlarmState OBJECT-TYPE
    SYNTAX     INTEGER {
                  eNone (0),
                  eLimitReached (1)
            }
    MAX-ACCESS read-only
    STATUS     current
    DESCRIPTION
            "-- empty --"
    ::= { hmStatusWlanWirelessIdsSigBlockackafterdelba 2 }

-- {NODE} 1.3.6.1.4.1.248.32.18.1.3.248.2.11
hmStatusWlanWirelessIdsSigNulldataflood OBJECT IDENTIFIER ::= { hmStatusWlanWirelessIdsSig 11 }

-- {SCALAR} 1.3.6.1.4.1.248.32.18.1.3.248.2.11.1
hmStatusWlanWirelessIdsSigNulldatafloodCounter OBJECT-TYPE
    SYNTAX     Integer32 (0..2147483647)
    MAX-ACCESS read-only
    STATUS     current
    DESCRIPTION
            "-- empty --"
    ::= { hmStatusWlanWirelessIdsSigNulldataflood 1 }

-- {SCALAR} 1.3.6.1.4.1.248.32.18.1.3.248.2.11.2
hmStatusWlanWirelessIdsSigNulldatafloodAlarmState OBJECT-TYPE
    SYNTAX     INTEGER {
                  eNone (0),
                  eLimitReached (1)
            }
    MAX-ACCESS read-only
    STATUS     current
    DESCRIPTION
            "-- empty --"
    ::= { hmStatusWlanWirelessIdsSigNulldataflood 2 }

-- {NODE} 1.3.6.1.4.1.248.32.18.1.3.248.2.12
hmStatusWlanWirelessIdsSigNullDataPSOv OBJECT IDENTIFIER ::= { hmStatusWlanWirelessIdsSig 12 }

-- {SCALAR} 1.3.6.1.4.1.248.32.18.1.3.248.2.12.1
hmStatusWlanWirelessIdsSigNullDataPSOvCounter OBJECT-TYPE
    SYNTAX     Integer32 (0..2147483647)
    MAX-ACCESS read-only
    STATUS     current
    DESCRIPTION
            "-- empty --"
    ::= { hmStatusWlanWirelessIdsSigNullDataPSOv 1 }

-- {SCALAR} 1.3.6.1.4.1.248.32.18.1.3.248.2.12.2
hmStatusWlanWirelessIdsSigNullDataPSOvAlarmState OBJECT-TYPE
    SYNTAX     INTEGER {
                  eNone (0),
                  eLimitReached (1)
            }
    MAX-ACCESS read-only
    STATUS     current
    DESCRIPTION
            "-- empty --"
    ::= { hmStatusWlanWirelessIdsSigNullDataPSOv 2 }

-- {NODE} 1.3.6.1.4.1.248.32.18.1.3.248.2.13
hmStatusWlanWirelessIdsSigPspolltiminterval OBJECT IDENTIFIER ::= { hmStatusWlanWirelessIdsSig 13 }

-- {SCALAR} 1.3.6.1.4.1.248.32.18.1.3.248.2.13.1
hmStatusWlanWirelessIdsSigPspolltimintervalCounter OBJECT-TYPE
    SYNTAX     Integer32 (0..2147483647)
    MAX-ACCESS read-only
    STATUS     current
    DESCRIPTION
            "-- empty --"
    ::= { hmStatusWlanWirelessIdsSigPspolltiminterval 1 }

-- {SCALAR} 1.3.6.1.4.1.248.32.18.1.3.248.2.13.2
hmStatusWlanWirelessIdsSigPspolltimintervalAlarmState OBJECT-TYPE
    SYNTAX     INTEGER {
                  eNone (0),
                  eLimitReached (1)
            }
    MAX-ACCESS read-only
    STATUS     current
    DESCRIPTION
            "-- empty --"
    ::= { hmStatusWlanWirelessIdsSigPspolltiminterval 2 }

-- {NODE} 1.3.6.1.4.1.248.32.18.1.3.248.2.14
hmStatusWlanWirelessIdsSigSmpsmultistream OBJECT IDENTIFIER ::= { hmStatusWlanWirelessIdsSig 14 }

-- {SCALAR} 1.3.6.1.4.1.248.32.18.1.3.248.2.14.1
hmStatusWlanWirelessIdsSigSmpsmultistreamCounter OBJECT-TYPE
    SYNTAX     Integer32 (0..2147483647)
    MAX-ACCESS read-only
    STATUS     current
    DESCRIPTION
            "-- empty --"
    ::= { hmStatusWlanWirelessIdsSigSmpsmultistream 1 }

-- {SCALAR} 1.3.6.1.4.1.248.32.18.1.3.248.2.14.2
hmStatusWlanWirelessIdsSigSmpsmultistreamAlarmState OBJECT-TYPE
    SYNTAX     INTEGER {
                  eNone (0),
                  eLimitReached (1)
            }
    MAX-ACCESS read-only
    STATUS     current
    DESCRIPTION
            "-- empty --"
    ::= { hmStatusWlanWirelessIdsSigSmpsmultistream 2 }

-- {NODE} 1.3.6.1.4.1.248.32.18.1.3.248.2.15
hmStatusWlanWirelessIdsSigDeauthenticatereqflood OBJECT IDENTIFIER ::= { hmStatusWlanWirelessIdsSig 15 }

-- {SCALAR} 1.3.6.1.4.1.248.32.18.1.3.248.2.15.1
hmStatusWlanWirelessIdsSigDeauthenticatereqfloodCounter OBJECT-TYPE
    SYNTAX     Integer32 (0..2147483647)
    MAX-ACCESS read-only
    STATUS     current
    DESCRIPTION
            "-- empty --"
    ::= { hmStatusWlanWirelessIdsSigDeauthenticatereqflood 1 }

-- {SCALAR} 1.3.6.1.4.1.248.32.18.1.3.248.2.15.2
hmStatusWlanWirelessIdsSigDeauthenticatereqfloodAlarmState OBJECT-TYPE
    SYNTAX     INTEGER {
                  eNone (0),
                  eLimitReached (1)
            }
    MAX-ACCESS read-only
    STATUS     current
    DESCRIPTION
            "-- empty --"
    ::= { hmStatusWlanWirelessIdsSigDeauthenticatereqflood 2 }

-- {NODE} 1.3.6.1.4.1.248.32.18.1.3.248.2.18
hmStatusWlanWirelessIdsSigSmpssinglestream OBJECT IDENTIFIER ::= { hmStatusWlanWirelessIdsSig 18 }

-- {SCALAR} 1.3.6.1.4.1.248.32.18.1.3.248.2.18.1
hmStatusWlanWirelessIdsSigSmpssinglestreamCounter OBJECT-TYPE
    SYNTAX     Integer32 (0..2147483647)
    MAX-ACCESS read-only
    STATUS     current
    DESCRIPTION
            "-- empty --"
    ::= { hmStatusWlanWirelessIdsSigSmpssinglestream 1 }

-- {SCALAR} 1.3.6.1.4.1.248.32.18.1.3.248.2.18.2
hmStatusWlanWirelessIdsSigSmpssinglestreamAlarmState OBJECT-TYPE
    SYNTAX     INTEGER {
                  eNone (0),
                  eLimitReached (1)
            }
    MAX-ACCESS read-only
    STATUS     current
    DESCRIPTION
            "-- empty --"
    ::= { hmStatusWlanWirelessIdsSigSmpssinglestream 2 }

-- {TABLE} 1.3.6.1.4.1.248.32.18.1.3.248.3
hmStatusWlanWirelessIdsIntruderTableTable OBJECT-TYPE
    SYNTAX     SEQUENCE OF HmStatusWlanWirelessIdsIntruderTableEntry
    MAX-ACCESS not-accessible
    STATUS     current
    DESCRIPTION
            "-- empty --"
    ::= { hmStatusWlanWirelessIds 3 }

-- {ROW} 1.3.6.1.4.1.248.32.18.1.3.248.3.1
hmStatusWlanWirelessIdsIntruderTableEntry OBJECT-TYPE
    SYNTAX     HmStatusWlanWirelessIdsIntruderTableEntry
    MAX-ACCESS not-accessible
    STATUS     current
    DESCRIPTION
            ""
    INDEX {
            hmStatusWlanWirelessIdsIntruderTableEntryMacAddress,
            hmStatusWlanWirelessIdsIntruderTableEntryAttackType
          }
    ::= { hmStatusWlanWirelessIdsIntruderTableTable 1 }

HmStatusWlanWirelessIdsIntruderTableEntry ::= SEQUENCE {
            hmStatusWlanWirelessIdsIntruderTableEntryMacAddress MacAddress,
            hmStatusWlanWirelessIdsIntruderTableEntryAttackType INTEGER,
            hmStatusWlanWirelessIdsIntruderTableEntryActive INTEGER,
            hmStatusWlanWirelessIdsIntruderTableEntryRssi Integer32,
            hmStatusWlanWirelessIdsIntruderTableEntryAttackRate Integer32,
            hmStatusWlanWirelessIdsIntruderTableEntryKnownClient INTEGER
    }

-- {COLUMN} 1.3.6.1.4.1.248.32.18.1.3.248.3.1.1
hmStatusWlanWirelessIdsIntruderTableEntryMacAddress OBJECT-TYPE
    SYNTAX     MacAddress
    MAX-ACCESS read-only
    STATUS     current
    DESCRIPTION
            "-- empty --"
    ::= { hmStatusWlanWirelessIdsIntruderTableEntry 1 }

-- {COLUMN} 1.3.6.1.4.1.248.32.18.1.3.248.3.1.2
hmStatusWlanWirelessIdsIntruderTableEntryAttackType OBJECT-TYPE
    SYNTAX     INTEGER {
                  eEapolstart (1),
                  eProbebroad (2),
                  eDeauthenticatebroad (3),
                  eDeauthenticate (4),
                  eAssociatereq (5),
                  eReassociatereq (6),
                  eAuthenticate (7),
                  eDisassociate (8),
                  eGenericerror (9),
                  eBlockackAttack (10),
                  eDelba (11),
                  eNulldatadosattack (12),
                  eNulldatapsAttack (13),
                  ePsPollAttack (14),
                  eSmpsAttack (15),
                  eDisassociatebroad (17)
            }
    MAX-ACCESS read-only
    STATUS     current
    DESCRIPTION
            "-- empty --"
    ::= { hmStatusWlanWirelessIdsIntruderTableEntry 2 }

-- {COLUMN} 1.3.6.1.4.1.248.32.18.1.3.248.3.1.3
hmStatusWlanWirelessIdsIntruderTableEntryActive OBJECT-TYPE
    SYNTAX     INTEGER {
                  eNo (0),
                  eYes (1)
            }
    MAX-ACCESS read-only
    STATUS     current
    DESCRIPTION
            "-- empty --"
    ::= { hmStatusWlanWirelessIdsIntruderTableEntry 3 }

-- {COLUMN} 1.3.6.1.4.1.248.32.18.1.3.248.3.1.4
hmStatusWlanWirelessIdsIntruderTableEntryRssi OBJECT-TYPE
    SYNTAX     Integer32 (0..65535)
    MAX-ACCESS read-only
    STATUS     current
    DESCRIPTION
            "-- empty --"
    ::= { hmStatusWlanWirelessIdsIntruderTableEntry 4 }

-- {COLUMN} 1.3.6.1.4.1.248.32.18.1.3.248.3.1.5
hmStatusWlanWirelessIdsIntruderTableEntryAttackRate OBJECT-TYPE
    SYNTAX     Integer32 (0..2147483647)
    MAX-ACCESS read-only
    STATUS     current
    DESCRIPTION
            "-- empty --"
    ::= { hmStatusWlanWirelessIdsIntruderTableEntry 5 }

-- {COLUMN} 1.3.6.1.4.1.248.32.18.1.3.248.3.1.6
hmStatusWlanWirelessIdsIntruderTableEntryKnownClient OBJECT-TYPE
    SYNTAX     INTEGER {
                  eNo (0),
                  eYes (1)
            }
    MAX-ACCESS read-only
    STATUS     current
    DESCRIPTION
            "-- empty --"
    ::= { hmStatusWlanWirelessIdsIntruderTableEntry 6 }

-- {NODE} 1.3.6.1.4.1.248.32.18.1.3.249
hmStatusWlanWlanLinkStatusLog OBJECT IDENTIFIER ::= { hmStatusWlan 249 }

-- {TABLE} 1.3.6.1.4.1.248.32.18.1.3.249.1
hmStatusWlanWlanLinkStatusLogAuditTable OBJECT-TYPE
    SYNTAX     SEQUENCE OF HmStatusWlanWlanLinkStatusLogAuditEntry
    MAX-ACCESS not-accessible
    STATUS     current
    DESCRIPTION
            "-- empty --"
    ::= { hmStatusWlanWlanLinkStatusLog 1 }

-- {ROW} 1.3.6.1.4.1.248.32.18.1.3.249.1.1
hmStatusWlanWlanLinkStatusLogAuditEntry OBJECT-TYPE
    SYNTAX     HmStatusWlanWlanLinkStatusLogAuditEntry
    MAX-ACCESS not-accessible
    STATUS     current
    DESCRIPTION
            ""
    INDEX {
            hmStatusWlanWlanLinkStatusLogAuditEntryRemoteMac
          }
    ::= { hmStatusWlanWlanLinkStatusLogAuditTable 1 }

HmStatusWlanWlanLinkStatusLogAuditEntry ::= SEQUENCE {
            hmStatusWlanWlanLinkStatusLogAuditEntryActiveSince DisplayString,
            hmStatusWlanWlanLinkStatusLogAuditEntryDownSince DisplayString,
            hmStatusWlanWlanLinkStatusLogAuditEntryRemoteMac MacAddress,
            hmStatusWlanWlanLinkStatusLogAuditEntryRemoteIp DisplayString,
            hmStatusWlanWlanLinkStatusLogAuditEntryLocalMac MacAddress,
            hmStatusWlanWlanLinkStatusLogAuditEntryLocalIp DisplayString,
            hmStatusWlanWlanLinkStatusLogAuditEntryLinkName DisplayString,
            hmStatusWlanWlanLinkStatusLogAuditEntryLinkType DisplayString,
            hmStatusWlanWlanLinkStatusLogAuditEntryCrtLinkPhySignal DisplayString,
            hmStatusWlanWlanLinkStatusLogAuditEntryAvgLinkPhySignal DisplayString,
            hmStatusWlanWlanLinkStatusLogAuditEntryMinLinkPhySignal DisplayString,
            hmStatusWlanWlanLinkStatusLogAuditEntryMaxLinkPhySignal DisplayString,
            hmStatusWlanWlanLinkStatusLogAuditEntryLinkFlapCount Integer32,
            hmStatusWlanWlanLinkStatusLogAuditEntryFrameLoss Integer32
    }

-- {COLUMN} 1.3.6.1.4.1.248.32.18.1.3.249.1.1.1
hmStatusWlanWlanLinkStatusLogAuditEntryActiveSince OBJECT-TYPE
    SYNTAX     DisplayString (SIZE(0..20))
    MAX-ACCESS read-only
    STATUS     current
    DESCRIPTION
            "-- empty --"
    ::= { hmStatusWlanWlanLinkStatusLogAuditEntry 1 }

-- {COLUMN} 1.3.6.1.4.1.248.32.18.1.3.249.1.1.2
hmStatusWlanWlanLinkStatusLogAuditEntryDownSince OBJECT-TYPE
    SYNTAX     DisplayString (SIZE(0..20))
    MAX-ACCESS read-only
    STATUS     current
    DESCRIPTION
            "-- empty --"
    ::= { hmStatusWlanWlanLinkStatusLogAuditEntry 2 }

-- {COLUMN} 1.3.6.1.4.1.248.32.18.1.3.249.1.1.3
hmStatusWlanWlanLinkStatusLogAuditEntryRemoteMac OBJECT-TYPE
    SYNTAX     MacAddress
    MAX-ACCESS read-only
    STATUS     current
    DESCRIPTION
            "-- empty --"
    ::= { hmStatusWlanWlanLinkStatusLogAuditEntry 3 }

-- {COLUMN} 1.3.6.1.4.1.248.32.18.1.3.249.1.1.4
hmStatusWlanWlanLinkStatusLogAuditEntryRemoteIp OBJECT-TYPE
    SYNTAX     DisplayString (SIZE(0..15))
    MAX-ACCESS read-only
    STATUS     current
    DESCRIPTION
            "-- empty --"
    ::= { hmStatusWlanWlanLinkStatusLogAuditEntry 4 }

-- {COLUMN} 1.3.6.1.4.1.248.32.18.1.3.249.1.1.5
hmStatusWlanWlanLinkStatusLogAuditEntryLocalMac OBJECT-TYPE
    SYNTAX     MacAddress
    MAX-ACCESS read-only
    STATUS     current
    DESCRIPTION
            "-- empty --"
    ::= { hmStatusWlanWlanLinkStatusLogAuditEntry 5 }

-- {COLUMN} 1.3.6.1.4.1.248.32.18.1.3.249.1.1.6
hmStatusWlanWlanLinkStatusLogAuditEntryLocalIp OBJECT-TYPE
    SYNTAX     DisplayString (SIZE(0..255))
    MAX-ACCESS read-only
    STATUS     current
    DESCRIPTION
            "-- empty --"
    ::= { hmStatusWlanWlanLinkStatusLogAuditEntry 6 }

-- {COLUMN} 1.3.6.1.4.1.248.32.18.1.3.249.1.1.7
hmStatusWlanWlanLinkStatusLogAuditEntryLinkName OBJECT-TYPE
    SYNTAX     DisplayString (SIZE(0..24))
    MAX-ACCESS read-only
    STATUS     current
    DESCRIPTION
            "-- empty --"
    ::= { hmStatusWlanWlanLinkStatusLogAuditEntry 7 }

-- {COLUMN} 1.3.6.1.4.1.248.32.18.1.3.249.1.1.8
hmStatusWlanWlanLinkStatusLogAuditEntryLinkType OBJECT-TYPE
    SYNTAX     DisplayString (SIZE(0..17))
    MAX-ACCESS read-only
    STATUS     current
    DESCRIPTION
            "-- empty --"
    ::= { hmStatusWlanWlanLinkStatusLogAuditEntry 8 }

-- {COLUMN} 1.3.6.1.4.1.248.32.18.1.3.249.1.1.9
hmStatusWlanWlanLinkStatusLogAuditEntryCrtLinkPhySignal OBJECT-TYPE
    SYNTAX     DisplayString (SIZE(0..19))
    MAX-ACCESS read-only
    STATUS     current
    DESCRIPTION
            "-- empty --"
    ::= { hmStatusWlanWlanLinkStatusLogAuditEntry 9 }

-- {COLUMN} 1.3.6.1.4.1.248.32.18.1.3.249.1.1.10
hmStatusWlanWlanLinkStatusLogAuditEntryAvgLinkPhySignal OBJECT-TYPE
    SYNTAX     DisplayString (SIZE(0..19))
    MAX-ACCESS read-only
    STATUS     current
    DESCRIPTION
            "-- empty --"
    ::= { hmStatusWlanWlanLinkStatusLogAuditEntry 10 }

-- {COLUMN} 1.3.6.1.4.1.248.32.18.1.3.249.1.1.11
hmStatusWlanWlanLinkStatusLogAuditEntryMinLinkPhySignal OBJECT-TYPE
    SYNTAX     DisplayString (SIZE(0..19))
    MAX-ACCESS read-only
    STATUS     current
    DESCRIPTION
            "-- empty --"
    ::= { hmStatusWlanWlanLinkStatusLogAuditEntry 11 }

-- {COLUMN} 1.3.6.1.4.1.248.32.18.1.3.249.1.1.12
hmStatusWlanWlanLinkStatusLogAuditEntryMaxLinkPhySignal OBJECT-TYPE
    SYNTAX     DisplayString (SIZE(0..19))
    MAX-ACCESS read-only
    STATUS     current
    DESCRIPTION
            "-- empty --"
    ::= { hmStatusWlanWlanLinkStatusLogAuditEntry 12 }

-- {COLUMN} 1.3.6.1.4.1.248.32.18.1.3.249.1.1.13
hmStatusWlanWlanLinkStatusLogAuditEntryLinkFlapCount OBJECT-TYPE
    SYNTAX     Integer32 (0..2147483647)
    MAX-ACCESS read-only
    STATUS     current
    DESCRIPTION
            "-- empty --"
    ::= { hmStatusWlanWlanLinkStatusLogAuditEntry 13 }

-- {COLUMN} 1.3.6.1.4.1.248.32.18.1.3.249.1.1.14
hmStatusWlanWlanLinkStatusLogAuditEntryFrameLoss OBJECT-TYPE
    SYNTAX     Integer32 (0..2147483647)
    MAX-ACCESS read-only
    STATUS     current
    DESCRIPTION
            "-- empty --"
    ::= { hmStatusWlanWlanLinkStatusLogAuditEntry 14 }

-- {TABLE} 1.3.6.1.4.1.248.32.18.1.3.249.2
hmStatusWlanWlanLinkStatusLogLogTableTable OBJECT-TYPE
    SYNTAX     SEQUENCE OF HmStatusWlanWlanLinkStatusLogLogTableEntry
    MAX-ACCESS not-accessible
    STATUS     current
    DESCRIPTION
            "-- empty --"
    ::= { hmStatusWlanWlanLinkStatusLog 2 }

-- {ROW} 1.3.6.1.4.1.248.32.18.1.3.249.2.1
hmStatusWlanWlanLinkStatusLogLogTableEntry OBJECT-TYPE
    SYNTAX     HmStatusWlanWlanLinkStatusLogLogTableEntry
    MAX-ACCESS not-accessible
    STATUS     current
    DESCRIPTION
            ""
    INDEX {
            hmStatusWlanWlanLinkStatusLogLogTableEntryIndex,
            hmStatusWlanWlanLinkStatusLogLogTableEntryRemoteMac
          }
    ::= { hmStatusWlanWlanLinkStatusLogLogTableTable 1 }

HmStatusWlanWlanLinkStatusLogLogTableEntry ::= SEQUENCE {
            hmStatusWlanWlanLinkStatusLogLogTableEntryIndex Integer32,
            hmStatusWlanWlanLinkStatusLogLogTableEntryTime DisplayString,
            hmStatusWlanWlanLinkStatusLogLogTableEntryActiveSince DisplayString,
            hmStatusWlanWlanLinkStatusLogLogTableEntryDownSince DisplayString,
            hmStatusWlanWlanLinkStatusLogLogTableEntryRemoteMac MacAddress,
            hmStatusWlanWlanLinkStatusLogLogTableEntryRemoteIp DisplayString,
            hmStatusWlanWlanLinkStatusLogLogTableEntryLocalMac MacAddress,
            hmStatusWlanWlanLinkStatusLogLogTableEntryLocalIp DisplayString,
            hmStatusWlanWlanLinkStatusLogLogTableEntryLinkName DisplayString,
            hmStatusWlanWlanLinkStatusLogLogTableEntryLinkType DisplayString,
            hmStatusWlanWlanLinkStatusLogLogTableEntryCrtLinkPhySignal DisplayString,
            hmStatusWlanWlanLinkStatusLogLogTableEntryAvgLinkPhySignal DisplayString,
            hmStatusWlanWlanLinkStatusLogLogTableEntryMinLinkPhySignal DisplayString,
            hmStatusWlanWlanLinkStatusLogLogTableEntryMaxLinkPhySignal DisplayString,
            hmStatusWlanWlanLinkStatusLogLogTableEntryLinkFlapCount Integer32,
            hmStatusWlanWlanLinkStatusLogLogTableEntryFrameLoss Integer32
    }

-- {COLUMN} 1.3.6.1.4.1.248.32.18.1.3.249.2.1.1
hmStatusWlanWlanLinkStatusLogLogTableEntryIndex OBJECT-TYPE
    SYNTAX     Integer32 (0..2147483647)
    MAX-ACCESS read-only
    STATUS     current
    DESCRIPTION
            "-- empty --"
    ::= { hmStatusWlanWlanLinkStatusLogLogTableEntry 1 }

-- {COLUMN} 1.3.6.1.4.1.248.32.18.1.3.249.2.1.2
hmStatusWlanWlanLinkStatusLogLogTableEntryTime OBJECT-TYPE
    SYNTAX     DisplayString (SIZE(0..20))
    MAX-ACCESS read-only
    STATUS     current
    DESCRIPTION
            "-- empty --"
    ::= { hmStatusWlanWlanLinkStatusLogLogTableEntry 2 }

-- {COLUMN} 1.3.6.1.4.1.248.32.18.1.3.249.2.1.3
hmStatusWlanWlanLinkStatusLogLogTableEntryActiveSince OBJECT-TYPE
    SYNTAX     DisplayString (SIZE(0..20))
    MAX-ACCESS read-only
    STATUS     current
    DESCRIPTION
            "-- empty --"
    ::= { hmStatusWlanWlanLinkStatusLogLogTableEntry 3 }

-- {COLUMN} 1.3.6.1.4.1.248.32.18.1.3.249.2.1.4
hmStatusWlanWlanLinkStatusLogLogTableEntryDownSince OBJECT-TYPE
    SYNTAX     DisplayString (SIZE(0..20))
    MAX-ACCESS read-only
    STATUS     current
    DESCRIPTION
            "-- empty --"
    ::= { hmStatusWlanWlanLinkStatusLogLogTableEntry 4 }

-- {COLUMN} 1.3.6.1.4.1.248.32.18.1.3.249.2.1.5
hmStatusWlanWlanLinkStatusLogLogTableEntryRemoteMac OBJECT-TYPE
    SYNTAX     MacAddress
    MAX-ACCESS read-only
    STATUS     current
    DESCRIPTION
            "-- empty --"
    ::= { hmStatusWlanWlanLinkStatusLogLogTableEntry 5 }

-- {COLUMN} 1.3.6.1.4.1.248.32.18.1.3.249.2.1.6
hmStatusWlanWlanLinkStatusLogLogTableEntryRemoteIp OBJECT-TYPE
    SYNTAX     DisplayString (SIZE(0..15))
    MAX-ACCESS read-only
    STATUS     current
    DESCRIPTION
            "-- empty --"
    ::= { hmStatusWlanWlanLinkStatusLogLogTableEntry 6 }

-- {COLUMN} 1.3.6.1.4.1.248.32.18.1.3.249.2.1.7
hmStatusWlanWlanLinkStatusLogLogTableEntryLocalMac OBJECT-TYPE
    SYNTAX     MacAddress
    MAX-ACCESS read-only
    STATUS     current
    DESCRIPTION
            "-- empty --"
    ::= { hmStatusWlanWlanLinkStatusLogLogTableEntry 7 }

-- {COLUMN} 1.3.6.1.4.1.248.32.18.1.3.249.2.1.8
hmStatusWlanWlanLinkStatusLogLogTableEntryLocalIp OBJECT-TYPE
    SYNTAX     DisplayString (SIZE(0..15))
    MAX-ACCESS read-only
    STATUS     current
    DESCRIPTION
            "-- empty --"
    ::= { hmStatusWlanWlanLinkStatusLogLogTableEntry 8 }

-- {COLUMN} 1.3.6.1.4.1.248.32.18.1.3.249.2.1.9
hmStatusWlanWlanLinkStatusLogLogTableEntryLinkName OBJECT-TYPE
    SYNTAX     DisplayString (SIZE(0..24))
    MAX-ACCESS read-only
    STATUS     current
    DESCRIPTION
            "-- empty --"
    ::= { hmStatusWlanWlanLinkStatusLogLogTableEntry 9 }

-- {COLUMN} 1.3.6.1.4.1.248.32.18.1.3.249.2.1.10
hmStatusWlanWlanLinkStatusLogLogTableEntryLinkType OBJECT-TYPE
    SYNTAX     DisplayString (SIZE(0..17))
    MAX-ACCESS read-only
    STATUS     current
    DESCRIPTION
            "-- empty --"
    ::= { hmStatusWlanWlanLinkStatusLogLogTableEntry 10 }

-- {COLUMN} 1.3.6.1.4.1.248.32.18.1.3.249.2.1.11
hmStatusWlanWlanLinkStatusLogLogTableEntryCrtLinkPhySignal OBJECT-TYPE
    SYNTAX     DisplayString (SIZE(0..19))
    MAX-ACCESS read-only
    STATUS     current
    DESCRIPTION
            "-- empty --"
    ::= { hmStatusWlanWlanLinkStatusLogLogTableEntry 11 }

-- {COLUMN} 1.3.6.1.4.1.248.32.18.1.3.249.2.1.12
hmStatusWlanWlanLinkStatusLogLogTableEntryAvgLinkPhySignal OBJECT-TYPE
    SYNTAX     DisplayString (SIZE(0..19))
    MAX-ACCESS read-only
    STATUS     current
    DESCRIPTION
            "-- empty --"
    ::= { hmStatusWlanWlanLinkStatusLogLogTableEntry 12 }

-- {COLUMN} 1.3.6.1.4.1.248.32.18.1.3.249.2.1.13
hmStatusWlanWlanLinkStatusLogLogTableEntryMinLinkPhySignal OBJECT-TYPE
    SYNTAX     DisplayString (SIZE(0..19))
    MAX-ACCESS read-only
    STATUS     current
    DESCRIPTION
            "-- empty --"
    ::= { hmStatusWlanWlanLinkStatusLogLogTableEntry 13 }

-- {COLUMN} 1.3.6.1.4.1.248.32.18.1.3.249.2.1.14
hmStatusWlanWlanLinkStatusLogLogTableEntryMaxLinkPhySignal OBJECT-TYPE
    SYNTAX     DisplayString (SIZE(0..19))
    MAX-ACCESS read-only
    STATUS     current
    DESCRIPTION
            "-- empty --"
    ::= { hmStatusWlanWlanLinkStatusLogLogTableEntry 14 }

-- {COLUMN} 1.3.6.1.4.1.248.32.18.1.3.249.2.1.15
hmStatusWlanWlanLinkStatusLogLogTableEntryLinkFlapCount OBJECT-TYPE
    SYNTAX     Integer32 (0..2147483647)
    MAX-ACCESS read-only
    STATUS     current
    DESCRIPTION
            "-- empty --"
    ::= { hmStatusWlanWlanLinkStatusLogLogTableEntry 15 }

-- {COLUMN} 1.3.6.1.4.1.248.32.18.1.3.249.2.1.16
hmStatusWlanWlanLinkStatusLogLogTableEntryFrameLoss OBJECT-TYPE
    SYNTAX     Integer32 (0..2147483647)
    MAX-ACCESS read-only
    STATUS     current
    DESCRIPTION
            "-- empty --"
    ::= { hmStatusWlanWlanLinkStatusLogLogTableEntry 16 }

-- {NODE} 1.3.6.1.4.1.248.32.18.1.4
hmStatusWan OBJECT IDENTIFIER ::= { hmStatus 4 }

-- {TABLE} 1.3.6.1.4.1.248.32.18.1.4.1
hmStatusWanByteTransportTable OBJECT-TYPE
    SYNTAX     SEQUENCE OF HmStatusWanByteTransportEntry
    MAX-ACCESS not-accessible
    STATUS     current
    DESCRIPTION
            "-- empty --"
    ::= { hmStatusWan 1 }

-- {ROW} 1.3.6.1.4.1.248.32.18.1.4.1.1
hmStatusWanByteTransportEntry OBJECT-TYPE
    SYNTAX     HmStatusWanByteTransportEntry
    MAX-ACCESS not-accessible
    STATUS     current
    DESCRIPTION
            ""
    INDEX {
            hmStatusWanByteTransportEntryIfc
          }
    ::= { hmStatusWanByteTransportTable 1 }

HmStatusWanByteTransportEntry ::= SEQUENCE {
            hmStatusWanByteTransportEntryIfc INTEGER,
            hmStatusWanByteTransportEntryCrxBytes Counter32,
            hmStatusWanByteTransportEntryRxBytes Counter32,
            hmStatusWanByteTransportEntryTxBytes Counter32,
            hmStatusWanByteTransportEntryCtxBytes Counter32
    }

-- {COLUMN} 1.3.6.1.4.1.248.32.18.1.4.1.1.1
hmStatusWanByteTransportEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusWanByteTransportEntry 1 }

-- {COLUMN} 1.3.6.1.4.1.248.32.18.1.4.1.1.2
hmStatusWanByteTransportEntryCrxBytes OBJECT-TYPE
    SYNTAX     Counter32
    MAX-ACCESS read-only
    STATUS     current
    DESCRIPTION
            "-- empty --"
    ::= { hmStatusWanByteTransportEntry 2 }

-- {COLUMN} 1.3.6.1.4.1.248.32.18.1.4.1.1.3
hmStatusWanByteTransportEntryRxBytes OBJECT-TYPE
    SYNTAX     Counter32
    MAX-ACCESS read-only
    STATUS     current
    DESCRIPTION
            "-- empty --"
    ::= { hmStatusWanByteTransportEntry 3 }

-- {COLUMN} 1.3.6.1.4.1.248.32.18.1.4.1.1.4
hmStatusWanByteTransportEntryTxBytes OBJECT-TYPE
    SYNTAX     Counter32
    MAX-ACCESS read-only
    STATUS     current
    DESCRIPTION
            "-- empty --"
    ::= { hmStatusWanByteTransportEntry 4 }

-- {COLUMN} 1.3.6.1.4.1.248.32.18.1.4.1.1.5
hmStatusWanByteTransportEntryCtxBytes OBJECT-TYPE
    SYNTAX     Counter32
    MAX-ACCESS read-only
    STATUS     current
    DESCRIPTION
            "-- empty --"
    ::= { hmStatusWanByteTransportEntry 5 }

-- {TABLE} 1.3.6.1.4.1.248.32.18.1.4.2
hmStatusWanPacketTransportTable OBJECT-TYPE
    SYNTAX     SEQUENCE OF HmStatusWanPacketTransportEntry
    MAX-ACCESS not-accessible
    STATUS     current
    DESCRIPTION
            "-- empty --"
    ::= { hmStatusWan 2 }

-- {ROW} 1.3.6.1.4.1.248.32.18.1.4.2.1
hmStatusWanPacketTransportEntry OBJECT-TYPE
    SYNTAX     HmStatusWanPacketTransportEntry
    MAX-ACCESS not-accessible
    STATUS     current
    DESCRIPTION
            ""
    INDEX {
            hmStatusWanPacketTransportEntryIfc
          }
    ::= { hmStatusWanPacketTransportTable 1 }

HmStatusWanPacketTransportEntry ::= SEQUENCE {
            hmStatusWanPacketTransportEntryIfc INTEGER,
            hmStatusWanPacketTransportEntryRx Counter32,
            hmStatusWanPacketTransportEntryTxTotal Counter32,
            hmStatusWanPacketTransportEntryTxNormal Counter32,
            hmStatusWanPacketTransportEntryTxReliable Counter32,
            hmStatusWanPacketTransportEntryTxUrgent Counter32
    }

-- {COLUMN} 1.3.6.1.4.1.248.32.18.1.4.2.1.1
hmStatusWanPacketTransportEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusWanPacketTransportEntry 1 }

-- {COLUMN} 1.3.6.1.4.1.248.32.18.1.4.2.1.2
hmStatusWanPacketTransportEntryRx OBJECT-TYPE
    SYNTAX     Counter32
    MAX-ACCESS read-only
    STATUS     current
    DESCRIPTION
            "-- empty --"
    ::= { hmStatusWanPacketTransportEntry 2 }

-- {COLUMN} 1.3.6.1.4.1.248.32.18.1.4.2.1.3
hmStatusWanPacketTransportEntryTxTotal OBJECT-TYPE
    SYNTAX     Counter32
    MAX-ACCESS read-only
    STATUS     current
    DESCRIPTION
            "-- empty --"
    ::= { hmStatusWanPacketTransportEntry 3 }

-- {COLUMN} 1.3.6.1.4.1.248.32.18.1.4.2.1.4
hmStatusWanPacketTransportEntryTxNormal OBJECT-TYPE
    SYNTAX     Counter32
    MAX-ACCESS read-only
    STATUS     current
    DESCRIPTION
            "-- empty --"
    ::= { hmStatusWanPacketTransportEntry 4 }

-- {COLUMN} 1.3.6.1.4.1.248.32.18.1.4.2.1.5
hmStatusWanPacketTransportEntryTxReliable OBJECT-TYPE
    SYNTAX     Counter32
    MAX-ACCESS read-only
    STATUS     current
    DESCRIPTION
            "-- empty --"
    ::= { hmStatusWanPacketTransportEntry 5 }

-- {COLUMN} 1.3.6.1.4.1.248.32.18.1.4.2.1.6
hmStatusWanPacketTransportEntryTxUrgent OBJECT-TYPE
    SYNTAX     Counter32
    MAX-ACCESS read-only
    STATUS     current
    DESCRIPTION
            "-- empty --"
    ::= { hmStatusWanPacketTransportEntry 6 }

-- {TABLE} 1.3.6.1.4.1.248.32.18.1.4.3
hmStatusWanErrorsTable OBJECT-TYPE
    SYNTAX     SEQUENCE OF HmStatusWanErrorsEntry
    MAX-ACCESS not-accessible
    STATUS     current
    DESCRIPTION
            "-- empty --"
    ::= { hmStatusWan 3 }

-- {ROW} 1.3.6.1.4.1.248.32.18.1.4.3.1
hmStatusWanErrorsEntry OBJECT-TYPE
    SYNTAX     HmStatusWanErrorsEntry
    MAX-ACCESS not-accessible
    STATUS     current
    DESCRIPTION
            ""
    INDEX {
            hmStatusWanErrorsEntryIfc
          }
    ::= { hmStatusWanErrorsTable 1 }

HmStatusWanErrorsEntry ::= SEQUENCE {
            hmStatusWanErrorsEntryIfc INTEGER,
            hmStatusWanErrorsEntryRxL1Error Counter32,
            hmStatusWanErrorsEntryRxL2Error Counter32,
            hmStatusWanErrorsEntryRxL3Error Counter32,
            hmStatusWanErrorsEntryStackError Counter32,
            hmStatusWanErrorsEntryTxError Counter32,
            hmStatusWanErrorsEntryQueueErrors Counter32
    }

-- {COLUMN} 1.3.6.1.4.1.248.32.18.1.4.3.1.1
hmStatusWanErrorsEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusWanErrorsEntry 1 }

-- {COLUMN} 1.3.6.1.4.1.248.32.18.1.4.3.1.2
hmStatusWanErrorsEntryRxL1Error OBJECT-TYPE
    SYNTAX     Counter32
    MAX-ACCESS read-only
    STATUS     current
    DESCRIPTION
            "-- empty --"
    ::= { hmStatusWanErrorsEntry 2 }

-- {COLUMN} 1.3.6.1.4.1.248.32.18.1.4.3.1.3
hmStatusWanErrorsEntryRxL2Error OBJECT-TYPE
    SYNTAX     Counter32
    MAX-ACCESS read-only
    STATUS     current
    DESCRIPTION
            "-- empty --"
    ::= { hmStatusWanErrorsEntry 3 }

-- {COLUMN} 1.3.6.1.4.1.248.32.18.1.4.3.1.4
hmStatusWanErrorsEntryRxL3Error OBJECT-TYPE
    SYNTAX     Counter32
    MAX-ACCESS read-only
    STATUS     current
    DESCRIPTION
            "-- empty --"
    ::= { hmStatusWanErrorsEntry 4 }

-- {COLUMN} 1.3.6.1.4.1.248.32.18.1.4.3.1.5
hmStatusWanErrorsEntryStackError OBJECT-TYPE
    SYNTAX     Counter32
    MAX-ACCESS read-only
    STATUS     current
    DESCRIPTION
            "-- empty --"
    ::= { hmStatusWanErrorsEntry 5 }

-- {COLUMN} 1.3.6.1.4.1.248.32.18.1.4.3.1.6
hmStatusWanErrorsEntryTxError OBJECT-TYPE
    SYNTAX     Counter32
    MAX-ACCESS read-only
    STATUS     current
    DESCRIPTION
            "-- empty --"
    ::= { hmStatusWanErrorsEntry 6 }

-- {COLUMN} 1.3.6.1.4.1.248.32.18.1.4.3.1.7
hmStatusWanErrorsEntryQueueErrors OBJECT-TYPE
    SYNTAX     Counter32
    MAX-ACCESS read-only
    STATUS     current
    DESCRIPTION
            "-- empty --"
    ::= { hmStatusWanErrorsEntry 7 }

-- {SCALAR} 1.3.6.1.4.1.248.32.18.1.4.4
hmStatusWanWanTxDiscarded OBJECT-TYPE
    SYNTAX     Counter32
    MAX-ACCESS read-only
    STATUS     current
    DESCRIPTION
            "-- empty --"
    ::= { hmStatusWan 4 }

-- {SCALAR} 1.3.6.1.4.1.248.32.18.1.4.5
hmStatusWanWanHeapPackets OBJECT-TYPE
    SYNTAX     Integer32 (0..2147483647)
    MAX-ACCESS read-only
    STATUS     current
    DESCRIPTION
            "-- empty --"
    ::= { hmStatusWan 5 }

-- {SCALAR} 1.3.6.1.4.1.248.32.18.1.4.6
hmStatusWanWanQueuePackets OBJECT-TYPE
    SYNTAX     Integer32 (0..2147483647)
    MAX-ACCESS read-only
    STATUS     current
    DESCRIPTION
            "-- empty --"
    ::= { hmStatusWan 6 }

-- {SCALAR} 1.3.6.1.4.1.248.32.18.1.4.7
hmStatusWanWanQueueErrors OBJECT-TYPE
    SYNTAX     Counter32
    MAX-ACCESS read-only
    STATUS     current
    DESCRIPTION
            "-- empty --"
    ::= { hmStatusWan 7 }

-- {TABLE} 1.3.6.1.4.1.248.32.18.1.4.8
hmStatusWanThroughputTable OBJECT-TYPE
    SYNTAX     SEQUENCE OF HmStatusWanThroughputEntry
    MAX-ACCESS not-accessible
    STATUS     current
    DESCRIPTION
            "-- empty --"
    ::= { hmStatusWan 8 }

-- {ROW} 1.3.6.1.4.1.248.32.18.1.4.8.1
hmStatusWanThroughputEntry OBJECT-TYPE
    SYNTAX     HmStatusWanThroughputEntry
    MAX-ACCESS not-accessible
    STATUS     current
    DESCRIPTION
            ""
    INDEX {
            hmStatusWanThroughputEntryIfc
          }
    ::= { hmStatusWanThroughputTable 1 }

HmStatusWanThroughputEntry ::= SEQUENCE {
            hmStatusWanThroughputEntryIfc INTEGER,
            hmStatusWanThroughputEntryRxSCurrent Integer32,
            hmStatusWanThroughputEntryTxSCurrent Integer32,
            hmStatusWanThroughputEntryRxSAverage Integer32,
            hmStatusWanThroughputEntryTxSAverage Integer32
    }

-- {COLUMN} 1.3.6.1.4.1.248.32.18.1.4.8.1.1
hmStatusWanThroughputEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusWanThroughputEntry 1 }

-- {COLUMN} 1.3.6.1.4.1.248.32.18.1.4.8.1.2
hmStatusWanThroughputEntryRxSCurrent OBJECT-TYPE
    SYNTAX     Integer32 (0..2147483647)
    MAX-ACCESS read-only
    STATUS     current
    DESCRIPTION
            "-- empty --"
    ::= { hmStatusWanThroughputEntry 2 }

-- {COLUMN} 1.3.6.1.4.1.248.32.18.1.4.8.1.3
hmStatusWanThroughputEntryTxSCurrent OBJECT-TYPE
    SYNTAX     Integer32 (0..2147483647)
    MAX-ACCESS read-only
    STATUS     current
    DESCRIPTION
            "-- empty --"
    ::= { hmStatusWanThroughputEntry 3 }

-- {COLUMN} 1.3.6.1.4.1.248.32.18.1.4.8.1.4
hmStatusWanThroughputEntryRxSAverage OBJECT-TYPE
    SYNTAX     Integer32 (0..2147483647)
    MAX-ACCESS read-only
    STATUS     current
    DESCRIPTION
            "-- empty --"
    ::= { hmStatusWanThroughputEntry 4 }

-- {COLUMN} 1.3.6.1.4.1.248.32.18.1.4.8.1.5
hmStatusWanThroughputEntryTxSAverage OBJECT-TYPE
    SYNTAX     Integer32 (0..2147483647)
    MAX-ACCESS read-only
    STATUS     current
    DESCRIPTION
            "-- empty --"
    ::= { hmStatusWanThroughputEntry 5 }

-- {SCALAR} 1.3.6.1.4.1.248.32.18.1.4.9
hmStatusWanDeleteValues OBJECT-TYPE
    SYNTAX     DisplayString
    MAX-ACCESS read-write
    STATUS     current
    DESCRIPTION
            "-- empty --"
    ::= { hmStatusWan 9 }

-- {SCALAR} 1.3.6.1.4.1.248.32.18.1.4.10
hmStatusWanConnections OBJECT-TYPE
    SYNTAX     Integer32 (0..2147483647)
    MAX-ACCESS read-only
    STATUS     current
    DESCRIPTION
            "-- empty --"
    ::= { hmStatusWan 10 }

-- {TABLE} 1.3.6.1.4.1.248.32.18.1.4.11
hmStatusWanMtuTable OBJECT-TYPE
    SYNTAX     SEQUENCE OF HmStatusWanMtuEntry
    MAX-ACCESS not-accessible
    STATUS     current
    DESCRIPTION
            "-- empty --"
    ::= { hmStatusWan 11 }

-- {ROW} 1.3.6.1.4.1.248.32.18.1.4.11.1
hmStatusWanMtuEntry OBJECT-TYPE
    SYNTAX     HmStatusWanMtuEntry
    MAX-ACCESS not-accessible
    STATUS     current
    DESCRIPTION
            ""
    INDEX {
            hmStatusWanMtuEntryPeer
          }
    ::= { hmStatusWanMtuTable 1 }

HmStatusWanMtuEntry ::= SEQUENCE {
            hmStatusWanMtuEntryPeer DisplayString,
            hmStatusWanMtuEntryMtu Integer32
    }

-- {COLUMN} 1.3.6.1.4.1.248.32.18.1.4.11.1.1
hmStatusWanMtuEntryPeer OBJECT-TYPE
    SYNTAX     DisplayString (SIZE(0..16))
    MAX-ACCESS read-only
    STATUS     current
    DESCRIPTION
            "-- empty --"
    ::= { hmStatusWanMtuEntry 1 }

-- {COLUMN} 1.3.6.1.4.1.248.32.18.1.4.11.1.2
hmStatusWanMtuEntryMtu OBJECT-TYPE
    SYNTAX     Integer32 (0..65535)
    MAX-ACCESS read-only
    STATUS     current
    DESCRIPTION
            "-- empty --"
    ::= { hmStatusWanMtuEntry 2 }

-- {SCALAR} 1.3.6.1.4.1.248.32.18.1.4.12
hmStatusWanEncryptedConnections OBJECT-TYPE
    SYNTAX     Integer32 (0..2147483647)
    MAX-ACCESS read-only
    STATUS     current
    DESCRIPTION
            "-- empty --"
    ::= { hmStatusWan 12 }

-- {NODE} 1.3.6.1.4.1.248.32.18.1.4.13
hmStatusWanIpAddresses OBJECT IDENTIFIER ::= { hmStatusWan 13 }

-- {TABLE} 1.3.6.1.4.1.248.32.18.1.4.13.1
hmStatusWanIpAddressesIpv4Table OBJECT-TYPE
    SYNTAX     SEQUENCE OF HmStatusWanIpAddressesIpv4Entry
    MAX-ACCESS not-accessible
    STATUS     current
    DESCRIPTION
            "-- empty --"
    ::= { hmStatusWanIpAddresses 1 }

-- {ROW} 1.3.6.1.4.1.248.32.18.1.4.13.1.1
hmStatusWanIpAddressesIpv4Entry OBJECT-TYPE
    SYNTAX     HmStatusWanIpAddressesIpv4Entry
    MAX-ACCESS not-accessible
    STATUS     current
    DESCRIPTION
            ""
    INDEX {
            hmStatusWanIpAddressesIpv4EntryPeer
          }
    ::= { hmStatusWanIpAddressesIpv4Table 1 }

HmStatusWanIpAddressesIpv4Entry ::= SEQUENCE {
            hmStatusWanIpAddressesIpv4EntryPeer DisplayString,
            hmStatusWanIpAddressesIpv4EntryType INTEGER,
            hmStatusWanIpAddressesIpv4EntryIpAddress IpAddress,
            hmStatusWanIpAddressesIpv4EntryIpNetmask IpAddress,
            hmStatusWanIpAddressesIpv4EntryGateway IpAddress,
            hmStatusWanIpAddressesIpv4EntryDnsDefault IpAddress,
            hmStatusWanIpAddressesIpv4EntryDnsBackup IpAddress,
            hmStatusWanIpAddressesIpv4EntryNbnsDefault IpAddress,
            hmStatusWanIpAddressesIpv4EntryNbnsBackup IpAddress,
            hmStatusWanIpAddressesIpv4EntryDomain DisplayString
    }

-- {COLUMN} 1.3.6.1.4.1.248.32.18.1.4.13.1.1.1
hmStatusWanIpAddressesIpv4EntryPeer OBJECT-TYPE
    SYNTAX     DisplayString (SIZE(0..16))
    MAX-ACCESS read-only
    STATUS     current
    DESCRIPTION
            "-- empty --"
    ::= { hmStatusWanIpAddressesIpv4Entry 1 }

-- {COLUMN} 1.3.6.1.4.1.248.32.18.1.4.13.1.1.2
hmStatusWanIpAddressesIpv4EntryType OBJECT-TYPE
    SYNTAX     INTEGER {
                  eStatic (1),
                  eDhcp (2),
                  ePpp (3),
                  eAutoconfig (4)
            }
    MAX-ACCESS read-only
    STATUS     current
    DESCRIPTION
            "-- empty --"
    ::= { hmStatusWanIpAddressesIpv4Entry 2 }

-- {COLUMN} 1.3.6.1.4.1.248.32.18.1.4.13.1.1.3
hmStatusWanIpAddressesIpv4EntryIpAddress OBJECT-TYPE
    SYNTAX     IpAddress
    MAX-ACCESS read-only
    STATUS     current
    DESCRIPTION
            "-- empty --"
    ::= { hmStatusWanIpAddressesIpv4Entry 3 }

-- {COLUMN} 1.3.6.1.4.1.248.32.18.1.4.13.1.1.4
hmStatusWanIpAddressesIpv4EntryIpNetmask OBJECT-TYPE
    SYNTAX     IpAddress
    MAX-ACCESS read-only
    STATUS     current
    DESCRIPTION
            "-- empty --"
    ::= { hmStatusWanIpAddressesIpv4Entry 4 }

-- {COLUMN} 1.3.6.1.4.1.248.32.18.1.4.13.1.1.5
hmStatusWanIpAddressesIpv4EntryGateway OBJECT-TYPE
    SYNTAX     IpAddress
    MAX-ACCESS read-only
    STATUS     current
    DESCRIPTION
            "-- empty --"
    ::= { hmStatusWanIpAddressesIpv4Entry 5 }

-- {COLUMN} 1.3.6.1.4.1.248.32.18.1.4.13.1.1.6
hmStatusWanIpAddressesIpv4EntryDnsDefault OBJECT-TYPE
    SYNTAX     IpAddress
    MAX-ACCESS read-only
    STATUS     current
    DESCRIPTION
            "-- empty --"
    ::= { hmStatusWanIpAddressesIpv4Entry 6 }

-- {COLUMN} 1.3.6.1.4.1.248.32.18.1.4.13.1.1.7
hmStatusWanIpAddressesIpv4EntryDnsBackup OBJECT-TYPE
    SYNTAX     IpAddress
    MAX-ACCESS read-only
    STATUS     current
    DESCRIPTION
            "-- empty --"
    ::= { hmStatusWanIpAddressesIpv4Entry 7 }

-- {COLUMN} 1.3.6.1.4.1.248.32.18.1.4.13.1.1.8
hmStatusWanIpAddressesIpv4EntryNbnsDefault OBJECT-TYPE
    SYNTAX     IpAddress
    MAX-ACCESS read-only
    STATUS     current
    DESCRIPTION
            "-- empty --"
    ::= { hmStatusWanIpAddressesIpv4Entry 8 }

-- {COLUMN} 1.3.6.1.4.1.248.32.18.1.4.13.1.1.9
hmStatusWanIpAddressesIpv4EntryNbnsBackup OBJECT-TYPE
    SYNTAX     IpAddress
    MAX-ACCESS read-only
    STATUS     current
    DESCRIPTION
            "-- empty --"
    ::= { hmStatusWanIpAddressesIpv4Entry 9 }

-- {COLUMN} 1.3.6.1.4.1.248.32.18.1.4.13.1.1.10
hmStatusWanIpAddressesIpv4EntryDomain OBJECT-TYPE
    SYNTAX     DisplayString (SIZE(0..35))
    MAX-ACCESS read-only
    STATUS     current
    DESCRIPTION
            "-- empty --"
    ::= { hmStatusWanIpAddressesIpv4Entry 10 }

-- {TABLE} 1.3.6.1.4.1.248.32.18.1.4.13.2
hmStatusWanIpAddressesIpv6Table OBJECT-TYPE
    SYNTAX     SEQUENCE OF HmStatusWanIpAddressesIpv6Entry
    MAX-ACCESS not-accessible
    STATUS     current
    DESCRIPTION
            "-- empty --"
    ::= { hmStatusWanIpAddresses 2 }

-- {ROW} 1.3.6.1.4.1.248.32.18.1.4.13.2.1
hmStatusWanIpAddressesIpv6Entry OBJECT-TYPE
    SYNTAX     HmStatusWanIpAddressesIpv6Entry
    MAX-ACCESS not-accessible
    STATUS     current
    DESCRIPTION
            ""
    INDEX {
            hmStatusWanIpAddressesIpv6EntryPeer
          }
    ::= { hmStatusWanIpAddressesIpv6Table 1 }

HmStatusWanIpAddressesIpv6Entry ::= SEQUENCE {
            hmStatusWanIpAddressesIpv6EntryPeer DisplayString,
            hmStatusWanIpAddressesIpv6EntryType INTEGER,
            hmStatusWanIpAddressesIpv6EntryIpAddress DisplayString,
            hmStatusWanIpAddressesIpv6EntryPrefixLength Integer32,
            hmStatusWanIpAddressesIpv6EntryGateway DisplayString,
            hmStatusWanIpAddressesIpv6EntryDnsDefault DisplayString,
            hmStatusWanIpAddressesIpv6EntryDnsBackup DisplayString,
            hmStatusWanIpAddressesIpv6EntryPrefix DisplayString,
            hmStatusWanIpAddressesIpv6EntryDomain DisplayString
    }

-- {COLUMN} 1.3.6.1.4.1.248.32.18.1.4.13.2.1.1
hmStatusWanIpAddressesIpv6EntryPeer OBJECT-TYPE
    SYNTAX     DisplayString (SIZE(0..16))
    MAX-ACCESS read-only
    STATUS     current
    DESCRIPTION
            "-- empty --"
    ::= { hmStatusWanIpAddressesIpv6Entry 1 }

-- {COLUMN} 1.3.6.1.4.1.248.32.18.1.4.13.2.1.2
hmStatusWanIpAddressesIpv6EntryType OBJECT-TYPE
    SYNTAX     INTEGER {
                  eUnknown (0),
                  eStatic (1),
                  eDhcp (2),
                  eAutoconfig (4),
                  eTunnel (5)
            }
    MAX-ACCESS read-only
    STATUS     current
    DESCRIPTION
            "-- empty --"
    ::= { hmStatusWanIpAddressesIpv6Entry 2 }

-- {COLUMN} 1.3.6.1.4.1.248.32.18.1.4.13.2.1.3
hmStatusWanIpAddressesIpv6EntryIpAddress OBJECT-TYPE
    SYNTAX     DisplayString (SIZE(0..255))
    MAX-ACCESS read-only
    STATUS     current
    DESCRIPTION
            "-- empty --"
    ::= { hmStatusWanIpAddressesIpv6Entry 3 }

-- {COLUMN} 1.3.6.1.4.1.248.32.18.1.4.13.2.1.4
hmStatusWanIpAddressesIpv6EntryPrefixLength OBJECT-TYPE
    SYNTAX     Integer32 (0..2147483647)
    MAX-ACCESS read-only
    STATUS     current
    DESCRIPTION
            "-- empty --"
    ::= { hmStatusWanIpAddressesIpv6Entry 4 }

-- {COLUMN} 1.3.6.1.4.1.248.32.18.1.4.13.2.1.5
hmStatusWanIpAddressesIpv6EntryGateway OBJECT-TYPE
    SYNTAX     DisplayString (SIZE(0..255))
    MAX-ACCESS read-only
    STATUS     current
    DESCRIPTION
            "-- empty --"
    ::= { hmStatusWanIpAddressesIpv6Entry 5 }

-- {COLUMN} 1.3.6.1.4.1.248.32.18.1.4.13.2.1.6
hmStatusWanIpAddressesIpv6EntryDnsDefault OBJECT-TYPE
    SYNTAX     DisplayString (SIZE(0..255))
    MAX-ACCESS read-only
    STATUS     current
    DESCRIPTION
            "-- empty --"
    ::= { hmStatusWanIpAddressesIpv6Entry 6 }

-- {COLUMN} 1.3.6.1.4.1.248.32.18.1.4.13.2.1.7
hmStatusWanIpAddressesIpv6EntryDnsBackup OBJECT-TYPE
    SYNTAX     DisplayString (SIZE(0..255))
    MAX-ACCESS read-only
    STATUS     current
    DESCRIPTION
            "-- empty --"
    ::= { hmStatusWanIpAddressesIpv6Entry 7 }

-- {COLUMN} 1.3.6.1.4.1.248.32.18.1.4.13.2.1.8
hmStatusWanIpAddressesIpv6EntryPrefix OBJECT-TYPE
    SYNTAX     DisplayString (SIZE(0..255))
    MAX-ACCESS read-only
    STATUS     current
    DESCRIPTION
            "-- empty --"
    ::= { hmStatusWanIpAddressesIpv6Entry 8 }

-- {COLUMN} 1.3.6.1.4.1.248.32.18.1.4.13.2.1.10
hmStatusWanIpAddressesIpv6EntryDomain OBJECT-TYPE
    SYNTAX     DisplayString (SIZE(0..35))
    MAX-ACCESS read-only
    STATUS     current
    DESCRIPTION
            "-- empty --"
    ::= { hmStatusWanIpAddressesIpv6Entry 10 }

-- {NODE} 1.3.6.1.4.1.248.32.18.1.4.20
hmStatusWanActions OBJECT IDENTIFIER ::= { hmStatusWan 20 }

-- {TABLE} 1.3.6.1.4.1.248.32.18.1.4.20.1
hmStatusWanActionsActionTableTable OBJECT-TYPE
    SYNTAX     SEQUENCE OF HmStatusWanActionsActionTableEntry
    MAX-ACCESS not-accessible
    STATUS     current
    DESCRIPTION
            "-- empty --"
    ::= { hmStatusWanActions 1 }

-- {ROW} 1.3.6.1.4.1.248.32.18.1.4.20.1.1
hmStatusWanActionsActionTableEntry OBJECT-TYPE
    SYNTAX     HmStatusWanActionsActionTableEntry
    MAX-ACCESS not-accessible
    STATUS     current
    DESCRIPTION
            ""
    INDEX {
            hmStatusWanActionsActionTableEntryTime
          }
    ::= { hmStatusWanActionsActionTableTable 1 }

HmStatusWanActionsActionTableEntry ::= SEQUENCE {
            hmStatusWanActionsActionTableEntryTime DisplayString,
            hmStatusWanActionsActionTableEntryAction DisplayString,
            hmStatusWanActionsActionTableEntryResult DisplayString
    }

-- {COLUMN} 1.3.6.1.4.1.248.32.18.1.4.20.1.1.1
hmStatusWanActionsActionTableEntryTime OBJECT-TYPE
    SYNTAX     DisplayString (SIZE(0..19))
    MAX-ACCESS read-only
    STATUS     current
    DESCRIPTION
            "-- empty --"
    ::= { hmStatusWanActionsActionTableEntry 1 }

-- {COLUMN} 1.3.6.1.4.1.248.32.18.1.4.20.1.1.2
hmStatusWanActionsActionTableEntryAction OBJECT-TYPE
    SYNTAX     DisplayString (SIZE(0..255))
    MAX-ACCESS read-only
    STATUS     current
    DESCRIPTION
            "-- empty --"
    ::= { hmStatusWanActionsActionTableEntry 2 }

-- {COLUMN} 1.3.6.1.4.1.248.32.18.1.4.20.1.1.3
hmStatusWanActionsActionTableEntryResult OBJECT-TYPE
    SYNTAX     DisplayString (SIZE(0..100))
    MAX-ACCESS read-only
    STATUS     current
    DESCRIPTION
            "-- empty --"
    ::= { hmStatusWanActionsActionTableEntry 3 }

-- {TABLE} 1.3.6.1.4.1.248.32.18.1.4.20.2
hmStatusWanActionsLockTableTable OBJECT-TYPE
    SYNTAX     SEQUENCE OF HmStatusWanActionsLockTableEntry
    MAX-ACCESS not-accessible
    STATUS     current
    DESCRIPTION
            "-- empty --"
    ::= { hmStatusWanActions 2 }

-- {ROW} 1.3.6.1.4.1.248.32.18.1.4.20.2.1
hmStatusWanActionsLockTableEntry OBJECT-TYPE
    SYNTAX     HmStatusWanActionsLockTableEntry
    MAX-ACCESS not-accessible
    STATUS     current
    DESCRIPTION
            ""
    INDEX {
            hmStatusWanActionsLockTableEntryIndex
          }
    ::= { hmStatusWanActionsLockTableTable 1 }

HmStatusWanActionsLockTableEntry ::= SEQUENCE {
            hmStatusWanActionsLockTableEntryIndex Integer32,
            hmStatusWanActionsLockTableEntryRemainingLocktime Integer32
    }

-- {COLUMN} 1.3.6.1.4.1.248.32.18.1.4.20.2.1.1
hmStatusWanActionsLockTableEntryIndex OBJECT-TYPE
    SYNTAX     Integer32 (0..65535)
    MAX-ACCESS read-only
    STATUS     current
    DESCRIPTION
            "-- empty --"
    ::= { hmStatusWanActionsLockTableEntry 1 }

-- {COLUMN} 1.3.6.1.4.1.248.32.18.1.4.20.2.1.2
hmStatusWanActionsLockTableEntryRemainingLocktime OBJECT-TYPE
    SYNTAX     Integer32 (0..2147483647)
    MAX-ACCESS read-only
    STATUS     current
    DESCRIPTION
            "-- empty --"
    ::= { hmStatusWanActionsLockTableEntry 2 }

-- {SCALAR} 1.3.6.1.4.1.248.32.18.1.4.21
hmStatusWanWanQueueMgtDrop OBJECT-TYPE
    SYNTAX     Counter32
    MAX-ACCESS read-only
    STATUS     current
    DESCRIPTION
            "-- empty --"
    ::= { hmStatusWan 21 }

-- {NODE} 1.3.6.1.4.1.248.32.18.1.4.30
hmStatusWanVlans OBJECT IDENTIFIER ::= { hmStatusWan 30 }

-- {SCALAR} 1.3.6.1.4.1.248.32.18.1.4.30.1
hmStatusWanVlansProviderList OBJECT-TYPE
    SYNTAX     Integer32 (0..2147483647)
    MAX-ACCESS read-only
    STATUS     current
    DESCRIPTION
            "-- empty --"
    ::= { hmStatusWanVlans 1 }

-- {TABLE} 1.3.6.1.4.1.248.32.18.1.4.30.2
hmStatusWanVlansVlansTable OBJECT-TYPE
    SYNTAX     SEQUENCE OF HmStatusWanVlansVlansEntry
    MAX-ACCESS not-accessible
    STATUS     current
    DESCRIPTION
            "-- empty --"
    ::= { hmStatusWanVlans 2 }

-- {ROW} 1.3.6.1.4.1.248.32.18.1.4.30.2.1
hmStatusWanVlansVlansEntry OBJECT-TYPE
    SYNTAX     HmStatusWanVlansVlansEntry
    MAX-ACCESS not-accessible
    STATUS     current
    DESCRIPTION
            ""
    INDEX {
            hmStatusWanVlansVlansEntryPeer
          }
    ::= { hmStatusWanVlansVlansTable 1 }

HmStatusWanVlansVlansEntry ::= SEQUENCE {
            hmStatusWanVlansVlansEntryPeer DisplayString,
            hmStatusWanVlansVlansEntryVlanId Integer32
    }

-- {COLUMN} 1.3.6.1.4.1.248.32.18.1.4.30.2.1.1
hmStatusWanVlansVlansEntryPeer OBJECT-TYPE
    SYNTAX     DisplayString (SIZE(0..16))
    MAX-ACCESS read-only
    STATUS     current
    DESCRIPTION
            "-- empty --"
    ::= { hmStatusWanVlansVlansEntry 1 }

-- {COLUMN} 1.3.6.1.4.1.248.32.18.1.4.30.2.1.2
hmStatusWanVlansVlansEntryVlanId OBJECT-TYPE
    SYNTAX     Integer32 (0..2147483647)
    MAX-ACCESS read-only
    STATUS     current
    DESCRIPTION
            "-- empty --"
    ::= { hmStatusWanVlansVlansEntry 2 }

-- {NODE} 1.3.6.1.4.1.248.32.18.1.5
hmStatusLan OBJECT IDENTIFIER ::= { hmStatus 5 }

-- {SCALAR} 1.3.6.1.4.1.248.32.18.1.5.7
hmStatusLanLanHeapPackets OBJECT-TYPE
    SYNTAX     Integer32 (0..2147483647)
    MAX-ACCESS read-only
    STATUS     current
    DESCRIPTION
            "-- empty --"
    ::= { hmStatusLan 7 }

-- {SCALAR} 1.3.6.1.4.1.248.32.18.1.5.11
hmStatusLanDeleteValues OBJECT-TYPE
    SYNTAX     DisplayString
    MAX-ACCESS read-write
    STATUS     current
    DESCRIPTION
            "-- empty --"
    ::= { hmStatusLan 11 }

-- {TABLE} 1.3.6.1.4.1.248.32.18.1.5.51
hmStatusLanInterfacesTable OBJECT-TYPE
    SYNTAX     SEQUENCE OF HmStatusLanInterfacesEntry
    MAX-ACCESS not-accessible
    STATUS     current
    DESCRIPTION
            "-- empty --"
    ::= { hmStatusLan 51 }

-- {ROW} 1.3.6.1.4.1.248.32.18.1.5.51.1
hmStatusLanInterfacesEntry OBJECT-TYPE
    SYNTAX     HmStatusLanInterfacesEntry
    MAX-ACCESS not-accessible
    STATUS     current
    DESCRIPTION
            ""
    INDEX {
            hmStatusLanInterfacesEntryIfc
          }
    ::= { hmStatusLanInterfacesTable 1 }

HmStatusLanInterfacesEntry ::= SEQUENCE {
            hmStatusLanInterfacesEntryIfc DisplayString,
            hmStatusLanInterfacesEntryQueuePackets Integer32,
            hmStatusLanInterfacesEntryLinkActive INTEGER
    }

-- {COLUMN} 1.3.6.1.4.1.248.32.18.1.5.51.1.1
hmStatusLanInterfacesEntryIfc OBJECT-TYPE
    SYNTAX     DisplayString (SIZE(0..255))
    MAX-ACCESS read-only
    STATUS     current
    DESCRIPTION
            "-- empty --"
    ::= { hmStatusLanInterfacesEntry 1 }

-- {COLUMN} 1.3.6.1.4.1.248.32.18.1.5.51.1.2
hmStatusLanInterfacesEntryQueuePackets OBJECT-TYPE
    SYNTAX     Integer32 (0..2147483647)
    MAX-ACCESS read-only
    STATUS     current
    DESCRIPTION
            "-- empty --"
    ::= { hmStatusLanInterfacesEntry 2 }

-- {COLUMN} 1.3.6.1.4.1.248.32.18.1.5.51.1.3
hmStatusLanInterfacesEntryLinkActive OBJECT-TYPE
    SYNTAX     INTEGER {
                  eNo (0),
                  eYes (1)
            }
    MAX-ACCESS read-only
    STATUS     current
    DESCRIPTION
            "-- empty --"
    ::= { hmStatusLanInterfacesEntry 3 }

-- {TABLE} 1.3.6.1.4.1.248.32.18.1.5.52
hmStatusLanByteTransportTable OBJECT-TYPE
    SYNTAX     SEQUENCE OF HmStatusLanByteTransportEntry
    MAX-ACCESS not-accessible
    STATUS     current
    DESCRIPTION
            "-- empty --"
    ::= { hmStatusLan 52 }

-- {ROW} 1.3.6.1.4.1.248.32.18.1.5.52.1
hmStatusLanByteTransportEntry OBJECT-TYPE
    SYNTAX     HmStatusLanByteTransportEntry
    MAX-ACCESS not-accessible
    STATUS     current
    DESCRIPTION
            ""
    INDEX {
            hmStatusLanByteTransportEntryIfc
          }
    ::= { hmStatusLanByteTransportTable 1 }

HmStatusLanByteTransportEntry ::= SEQUENCE {
            hmStatusLanByteTransportEntryIfc DisplayString,
            hmStatusLanByteTransportEntryTxBytes Counter64,
            hmStatusLanByteTransportEntryRxBytes Counter64,
            hmStatusLanByteTransportEntryThroughput DisplayString,
            hmStatusLanByteTransportEntryMaxThroughput DisplayString,
            hmStatusLanByteTransportEntryBytesThroughput Integer32,
            hmStatusLanByteTransportEntryBytesMaxThroughput Integer32
    }

-- {COLUMN} 1.3.6.1.4.1.248.32.18.1.5.52.1.1
hmStatusLanByteTransportEntryIfc OBJECT-TYPE
    SYNTAX     DisplayString (SIZE(0..255))
    MAX-ACCESS read-only
    STATUS     current
    DESCRIPTION
            "-- empty --"
    ::= { hmStatusLanByteTransportEntry 1 }

-- {COLUMN} 1.3.6.1.4.1.248.32.18.1.5.52.1.2
hmStatusLanByteTransportEntryTxBytes OBJECT-TYPE
    SYNTAX     Counter64
    MAX-ACCESS read-only
    STATUS     current
    DESCRIPTION
            "-- empty --"
    ::= { hmStatusLanByteTransportEntry 2 }

-- {COLUMN} 1.3.6.1.4.1.248.32.18.1.5.52.1.3
hmStatusLanByteTransportEntryRxBytes OBJECT-TYPE
    SYNTAX     Counter64
    MAX-ACCESS read-only
    STATUS     current
    DESCRIPTION
            "-- empty --"
    ::= { hmStatusLanByteTransportEntry 3 }

-- {COLUMN} 1.3.6.1.4.1.248.32.18.1.5.52.1.4
hmStatusLanByteTransportEntryThroughput OBJECT-TYPE
    SYNTAX     DisplayString (SIZE(0..255))
    MAX-ACCESS read-only
    STATUS     current
    DESCRIPTION
            "-- empty --"
    ::= { hmStatusLanByteTransportEntry 4 }

-- {COLUMN} 1.3.6.1.4.1.248.32.18.1.5.52.1.5
hmStatusLanByteTransportEntryMaxThroughput OBJECT-TYPE
    SYNTAX     DisplayString (SIZE(0..255))
    MAX-ACCESS read-only
    STATUS     current
    DESCRIPTION
            "-- empty --"
    ::= { hmStatusLanByteTransportEntry 5 }

-- {COLUMN} 1.3.6.1.4.1.248.32.18.1.5.52.1.6
hmStatusLanByteTransportEntryBytesThroughput OBJECT-TYPE
    SYNTAX     Integer32 (0..2147483647)
    MAX-ACCESS read-only
    STATUS     current
    DESCRIPTION
            "-- empty --"
    ::= { hmStatusLanByteTransportEntry 6 }

-- {COLUMN} 1.3.6.1.4.1.248.32.18.1.5.52.1.7
hmStatusLanByteTransportEntryBytesMaxThroughput OBJECT-TYPE
    SYNTAX     Integer32 (0..2147483647)
    MAX-ACCESS read-only
    STATUS     current
    DESCRIPTION
            "-- empty --"
    ::= { hmStatusLanByteTransportEntry 7 }

-- {TABLE} 1.3.6.1.4.1.248.32.18.1.5.53
hmStatusLanPacketTransportTable OBJECT-TYPE
    SYNTAX     SEQUENCE OF HmStatusLanPacketTransportEntry
    MAX-ACCESS not-accessible
    STATUS     current
    DESCRIPTION
            "-- empty --"
    ::= { hmStatusLan 53 }

-- {ROW} 1.3.6.1.4.1.248.32.18.1.5.53.1
hmStatusLanPacketTransportEntry OBJECT-TYPE
    SYNTAX     HmStatusLanPacketTransportEntry
    MAX-ACCESS not-accessible
    STATUS     current
    DESCRIPTION
            ""
    INDEX {
            hmStatusLanPacketTransportEntryIfc
          }
    ::= { hmStatusLanPacketTransportTable 1 }

HmStatusLanPacketTransportEntry ::= SEQUENCE {
            hmStatusLanPacketTransportEntryIfc DisplayString,
            hmStatusLanPacketTransportEntryRxPackets Counter32,
            hmStatusLanPacketTransportEntryTxPackets Counter32,
            hmStatusLanPacketTransportEntryRxBroadcasts Counter32,
            hmStatusLanPacketTransportEntryRxMulticasts Counter32,
            hmStatusLanPacketTransportEntryRxUnicasts Counter32,
            hmStatusLanPacketTransportEntryTxBroadcasts Counter32,
            hmStatusLanPacketTransportEntryTxMulticasts Counter32,
            hmStatusLanPacketTransportEntryTxUnicasts Counter32
    }

-- {COLUMN} 1.3.6.1.4.1.248.32.18.1.5.53.1.1
hmStatusLanPacketTransportEntryIfc OBJECT-TYPE
    SYNTAX     DisplayString (SIZE(0..255))
    MAX-ACCESS read-only
    STATUS     current
    DESCRIPTION
            "-- empty --"
    ::= { hmStatusLanPacketTransportEntry 1 }

-- {COLUMN} 1.3.6.1.4.1.248.32.18.1.5.53.1.2
hmStatusLanPacketTransportEntryRxPackets OBJECT-TYPE
    SYNTAX     Counter32
    MAX-ACCESS read-only
    STATUS     current
    DESCRIPTION
            "-- empty --"
    ::= { hmStatusLanPacketTransportEntry 2 }

-- {COLUMN} 1.3.6.1.4.1.248.32.18.1.5.53.1.3
hmStatusLanPacketTransportEntryTxPackets OBJECT-TYPE
    SYNTAX     Counter32
    MAX-ACCESS read-only
    STATUS     current
    DESCRIPTION
            "-- empty --"
    ::= { hmStatusLanPacketTransportEntry 3 }

-- {COLUMN} 1.3.6.1.4.1.248.32.18.1.5.53.1.4
hmStatusLanPacketTransportEntryRxBroadcasts OBJECT-TYPE
    SYNTAX     Counter32
    MAX-ACCESS read-only
    STATUS     current
    DESCRIPTION
            "-- empty --"
    ::= { hmStatusLanPacketTransportEntry 4 }

-- {COLUMN} 1.3.6.1.4.1.248.32.18.1.5.53.1.5
hmStatusLanPacketTransportEntryRxMulticasts OBJECT-TYPE
    SYNTAX     Counter32
    MAX-ACCESS read-only
    STATUS     current
    DESCRIPTION
            "-- empty --"
    ::= { hmStatusLanPacketTransportEntry 5 }

-- {COLUMN} 1.3.6.1.4.1.248.32.18.1.5.53.1.6
hmStatusLanPacketTransportEntryRxUnicasts OBJECT-TYPE
    SYNTAX     Counter32
    MAX-ACCESS read-only
    STATUS     current
    DESCRIPTION
            "-- empty --"
    ::= { hmStatusLanPacketTransportEntry 6 }

-- {COLUMN} 1.3.6.1.4.1.248.32.18.1.5.53.1.7
hmStatusLanPacketTransportEntryTxBroadcasts OBJECT-TYPE
    SYNTAX     Counter32
    MAX-ACCESS read-only
    STATUS     current
    DESCRIPTION
            "-- empty --"
    ::= { hmStatusLanPacketTransportEntry 7 }

-- {COLUMN} 1.3.6.1.4.1.248.32.18.1.5.53.1.8
hmStatusLanPacketTransportEntryTxMulticasts OBJECT-TYPE
    SYNTAX     Counter32
    MAX-ACCESS read-only
    STATUS     current
    DESCRIPTION
            "-- empty --"
    ::= { hmStatusLanPacketTransportEntry 8 }

-- {COLUMN} 1.3.6.1.4.1.248.32.18.1.5.53.1.9
hmStatusLanPacketTransportEntryTxUnicasts OBJECT-TYPE
    SYNTAX     Counter32
    MAX-ACCESS read-only
    STATUS     current
    DESCRIPTION
            "-- empty --"
    ::= { hmStatusLanPacketTransportEntry 9 }

-- {TABLE} 1.3.6.1.4.1.248.32.18.1.5.54
hmStatusLanErrorsTable OBJECT-TYPE
    SYNTAX     SEQUENCE OF HmStatusLanErrorsEntry
    MAX-ACCESS not-accessible
    STATUS     current
    DESCRIPTION
            "-- empty --"
    ::= { hmStatusLan 54 }

-- {ROW} 1.3.6.1.4.1.248.32.18.1.5.54.1
hmStatusLanErrorsEntry OBJECT-TYPE
    SYNTAX     HmStatusLanErrorsEntry
    MAX-ACCESS not-accessible
    STATUS     current
    DESCRIPTION
            ""
    INDEX {
            hmStatusLanErrorsEntryIfc
          }
    ::= { hmStatusLanErrorsTable 1 }

HmStatusLanErrorsEntry ::= SEQUENCE {
            hmStatusLanErrorsEntryIfc DisplayString,
            hmStatusLanErrorsEntryRxErrors Counter32,
            hmStatusLanErrorsEntryTxErrors Counter32,
            hmStatusLanErrorsEntryStackErrors Counter32,
            hmStatusLanErrorsEntryNicErrors Counter32,
            hmStatusLanErrorsEntryQueueErrors Counter32,
            hmStatusLanErrorsEntryRxCrcErrors Counter32,
            hmStatusLanErrorsEntryCollisions Counter32,
            hmStatusLanErrorsEntrySingleCollisions Counter32,
            hmStatusLanErrorsEntryMultipleCollisions Counter32,
            hmStatusLanErrorsEntryLateCollisions Counter32,
            hmStatusLanErrorsEntryExcessiveCollisions Counter32,
            hmStatusLanErrorsEntryRxAlignErrors Counter32,
            hmStatusLanErrorsEntryRxTooShort Counter32,
            hmStatusLanErrorsEntryRxTooLong Counter32,
            hmStatusLanErrorsEntryTxCarrier Counter32,
            hmStatusLanErrorsEntryTxDeferred Counter32,
            hmStatusLanErrorsEntryRxPhyErrors Counter32,
            hmStatusLanErrorsEntryRxFifoOverflow Counter32,
            hmStatusLanErrorsEntryTxDiscarded Counter32,
            hmStatusLanErrorsEntryRxDscrUnderflow Counter32
    }

-- {COLUMN} 1.3.6.1.4.1.248.32.18.1.5.54.1.1
hmStatusLanErrorsEntryIfc OBJECT-TYPE
    SYNTAX     DisplayString (SIZE(0..255))
    MAX-ACCESS read-only
    STATUS     current
    DESCRIPTION
            "-- empty --"
    ::= { hmStatusLanErrorsEntry 1 }

-- {COLUMN} 1.3.6.1.4.1.248.32.18.1.5.54.1.2
hmStatusLanErrorsEntryRxErrors OBJECT-TYPE
    SYNTAX     Counter32
    MAX-ACCESS read-only
    STATUS     current
    DESCRIPTION
            "-- empty --"
    ::= { hmStatusLanErrorsEntry 2 }

-- {COLUMN} 1.3.6.1.4.1.248.32.18.1.5.54.1.3
hmStatusLanErrorsEntryTxErrors OBJECT-TYPE
    SYNTAX     Counter32
    MAX-ACCESS read-only
    STATUS     current
    DESCRIPTION
            "-- empty --"
    ::= { hmStatusLanErrorsEntry 3 }

-- {COLUMN} 1.3.6.1.4.1.248.32.18.1.5.54.1.4
hmStatusLanErrorsEntryStackErrors OBJECT-TYPE
    SYNTAX     Counter32
    MAX-ACCESS read-only
    STATUS     current
    DESCRIPTION
            "-- empty --"
    ::= { hmStatusLanErrorsEntry 4 }

-- {COLUMN} 1.3.6.1.4.1.248.32.18.1.5.54.1.5
hmStatusLanErrorsEntryNicErrors OBJECT-TYPE
    SYNTAX     Counter32
    MAX-ACCESS read-only
    STATUS     current
    DESCRIPTION
            "-- empty --"
    ::= { hmStatusLanErrorsEntry 5 }

-- {COLUMN} 1.3.6.1.4.1.248.32.18.1.5.54.1.6
hmStatusLanErrorsEntryQueueErrors OBJECT-TYPE
    SYNTAX     Counter32
    MAX-ACCESS read-only
    STATUS     current
    DESCRIPTION
            "-- empty --"
    ::= { hmStatusLanErrorsEntry 6 }

-- {COLUMN} 1.3.6.1.4.1.248.32.18.1.5.54.1.7
hmStatusLanErrorsEntryRxCrcErrors OBJECT-TYPE
    SYNTAX     Counter32
    MAX-ACCESS read-only
    STATUS     current
    DESCRIPTION
            "-- empty --"
    ::= { hmStatusLanErrorsEntry 7 }

-- {COLUMN} 1.3.6.1.4.1.248.32.18.1.5.54.1.8
hmStatusLanErrorsEntryCollisions OBJECT-TYPE
    SYNTAX     Counter32
    MAX-ACCESS read-only
    STATUS     current
    DESCRIPTION
            "-- empty --"
    ::= { hmStatusLanErrorsEntry 8 }

-- {COLUMN} 1.3.6.1.4.1.248.32.18.1.5.54.1.9
hmStatusLanErrorsEntrySingleCollisions OBJECT-TYPE
    SYNTAX     Counter32
    MAX-ACCESS read-only
    STATUS     current
    DESCRIPTION
            "-- empty --"
    ::= { hmStatusLanErrorsEntry 9 }

-- {COLUMN} 1.3.6.1.4.1.248.32.18.1.5.54.1.10
hmStatusLanErrorsEntryMultipleCollisions OBJECT-TYPE
    SYNTAX     Counter32
    MAX-ACCESS read-only
    STATUS     current
    DESCRIPTION
            "-- empty --"
    ::= { hmStatusLanErrorsEntry 10 }

-- {COLUMN} 1.3.6.1.4.1.248.32.18.1.5.54.1.11
hmStatusLanErrorsEntryLateCollisions OBJECT-TYPE
    SYNTAX     Counter32
    MAX-ACCESS read-only
    STATUS     current
    DESCRIPTION
            "-- empty --"
    ::= { hmStatusLanErrorsEntry 11 }

-- {COLUMN} 1.3.6.1.4.1.248.32.18.1.5.54.1.12
hmStatusLanErrorsEntryExcessiveCollisions OBJECT-TYPE
    SYNTAX     Counter32
    MAX-ACCESS read-only
    STATUS     current
    DESCRIPTION
            "-- empty --"
    ::= { hmStatusLanErrorsEntry 12 }

-- {COLUMN} 1.3.6.1.4.1.248.32.18.1.5.54.1.13
hmStatusLanErrorsEntryRxAlignErrors OBJECT-TYPE
    SYNTAX     Counter32
    MAX-ACCESS read-only
    STATUS     current
    DESCRIPTION
            "-- empty --"
    ::= { hmStatusLanErrorsEntry 13 }

-- {COLUMN} 1.3.6.1.4.1.248.32.18.1.5.54.1.14
hmStatusLanErrorsEntryRxTooShort OBJECT-TYPE
    SYNTAX     Counter32
    MAX-ACCESS read-only
    STATUS     current
    DESCRIPTION
            "-- empty --"
    ::= { hmStatusLanErrorsEntry 14 }

-- {COLUMN} 1.3.6.1.4.1.248.32.18.1.5.54.1.15
hmStatusLanErrorsEntryRxTooLong OBJECT-TYPE
    SYNTAX     Counter32
    MAX-ACCESS read-only
    STATUS     current
    DESCRIPTION
            "-- empty --"
    ::= { hmStatusLanErrorsEntry 15 }

-- {COLUMN} 1.3.6.1.4.1.248.32.18.1.5.54.1.16
hmStatusLanErrorsEntryTxCarrier OBJECT-TYPE
    SYNTAX     Counter32
    MAX-ACCESS read-only
    STATUS     current
    DESCRIPTION
            "-- empty --"
    ::= { hmStatusLanErrorsEntry 16 }

-- {COLUMN} 1.3.6.1.4.1.248.32.18.1.5.54.1.17
hmStatusLanErrorsEntryTxDeferred OBJECT-TYPE
    SYNTAX     Counter32
    MAX-ACCESS read-only
    STATUS     current
    DESCRIPTION
            "-- empty --"
    ::= { hmStatusLanErrorsEntry 17 }

-- {COLUMN} 1.3.6.1.4.1.248.32.18.1.5.54.1.18
hmStatusLanErrorsEntryRxPhyErrors OBJECT-TYPE
    SYNTAX     Counter32
    MAX-ACCESS read-only
    STATUS     current
    DESCRIPTION
            "-- empty --"
    ::= { hmStatusLanErrorsEntry 18 }

-- {COLUMN} 1.3.6.1.4.1.248.32.18.1.5.54.1.19
hmStatusLanErrorsEntryRxFifoOverflow OBJECT-TYPE
    SYNTAX     Counter32
    MAX-ACCESS read-only
    STATUS     current
    DESCRIPTION
            "-- empty --"
    ::= { hmStatusLanErrorsEntry 19 }

-- {COLUMN} 1.3.6.1.4.1.248.32.18.1.5.54.1.20
hmStatusLanErrorsEntryTxDiscarded OBJECT-TYPE
    SYNTAX     Counter32
    MAX-ACCESS read-only
    STATUS     current
    DESCRIPTION
            "-- empty --"
    ::= { hmStatusLanErrorsEntry 20 }

-- {COLUMN} 1.3.6.1.4.1.248.32.18.1.5.54.1.21
hmStatusLanErrorsEntryRxDscrUnderflow OBJECT-TYPE
    SYNTAX     Counter32
    MAX-ACCESS read-only
    STATUS     current
    DESCRIPTION
            "-- empty --"
    ::= { hmStatusLanErrorsEntry 21 }

-- {SCALAR} 1.3.6.1.4.1.248.32.18.1.5.60
hmStatusLanLanQueueMgtDrop OBJECT-TYPE
    SYNTAX     Counter32
    MAX-ACCESS read-only
    STATUS     current
    DESCRIPTION
            "-- empty --"
    ::= { hmStatusLan 60 }

-- {NODE} 1.3.6.1.4.1.248.32.18.1.5.80
hmStatusLanIeee8021x OBJECT IDENTIFIER ::= { hmStatusLan 80 }

-- {TABLE} 1.3.6.1.4.1.248.32.18.1.5.80.1
hmStatusLanIeee8021xSupplicantIfcStateTable OBJECT-TYPE
    SYNTAX     SEQUENCE OF HmStatusLanIeee8021xSupplicantIfcStateEntry
    MAX-ACCESS not-accessible
    STATUS     current
    DESCRIPTION
            "-- empty --"
    ::= { hmStatusLanIeee8021x 1 }

-- {ROW} 1.3.6.1.4.1.248.32.18.1.5.80.1.1
hmStatusLanIeee8021xSupplicantIfcStateEntry OBJECT-TYPE
    SYNTAX     HmStatusLanIeee8021xSupplicantIfcStateEntry
    MAX-ACCESS not-accessible
    STATUS     current
    DESCRIPTION
            ""
    INDEX {
            hmStatusLanIeee8021xSupplicantIfcStateEntryIfc
          }
    ::= { hmStatusLanIeee8021xSupplicantIfcStateTable 1 }

HmStatusLanIeee8021xSupplicantIfcStateEntry ::= SEQUENCE {
            hmStatusLanIeee8021xSupplicantIfcStateEntryIfc INTEGER,
            hmStatusLanIeee8021xSupplicantIfcStateEntryMethod INTEGER,
            hmStatusLanIeee8021xSupplicantIfcStateEntryState INTEGER,
            hmStatusLanIeee8021xSupplicantIfcStateEntryAuthenticatorAddress MacAddress
    }

-- {COLUMN} 1.3.6.1.4.1.248.32.18.1.5.80.1.1.1
hmStatusLanIeee8021xSupplicantIfcStateEntryIfc OBJECT-TYPE
    SYNTAX     INTEGER {
                  eLan1 (1),
                  eLan2 (2)
            }
    MAX-ACCESS read-only
    STATUS     current
    DESCRIPTION
            "-- empty --"
    ::= { hmStatusLanIeee8021xSupplicantIfcStateEntry 1 }

-- {COLUMN} 1.3.6.1.4.1.248.32.18.1.5.80.1.1.2
hmStatusLanIeee8021xSupplicantIfcStateEntryMethod OBJECT-TYPE
    SYNTAX     INTEGER {
                  eNone (0),
                  eMd5 (1024),
                  eTls (3328),
                  eTtlsMd5 (5380),
                  eTtlsPap (5383),
                  eTtlsChap (5384),
                  eTtlsMschapv2 (5402),
                  eTtlsMschap (5567),
                  ePeapGtc (6406),
                  ePeapMschapv2 (6426)
            }
    MAX-ACCESS read-only
    STATUS     current
    DESCRIPTION
            "-- empty --"
    ::= { hmStatusLanIeee8021xSupplicantIfcStateEntry 2 }

-- {COLUMN} 1.3.6.1.4.1.248.32.18.1.5.80.1.1.3
hmStatusLanIeee8021xSupplicantIfcStateEntryState OBJECT-TYPE
    SYNTAX     INTEGER {
                  eIdle (0),
                  eUnauthorized (1),
                  eAuthorized (2)
            }
    MAX-ACCESS read-only
    STATUS     current
    DESCRIPTION
            "-- empty --"
    ::= { hmStatusLanIeee8021xSupplicantIfcStateEntry 3 }

-- {COLUMN} 1.3.6.1.4.1.248.32.18.1.5.80.1.1.4
hmStatusLanIeee8021xSupplicantIfcStateEntryAuthenticatorAddress OBJECT-TYPE
    SYNTAX     MacAddress
    MAX-ACCESS read-only
    STATUS     current
    DESCRIPTION
            "-- empty --"
    ::= { hmStatusLanIeee8021xSupplicantIfcStateEntry 4 }

-- {TABLE} 1.3.6.1.4.1.248.32.18.1.5.80.2
hmStatusLanIeee8021xAuthenticatorIfcStatusTable OBJECT-TYPE
    SYNTAX     SEQUENCE OF HmStatusLanIeee8021xAuthenticatorIfcStatusEntry
    MAX-ACCESS not-accessible
    STATUS     current
    DESCRIPTION
            "-- empty --"
    ::= { hmStatusLanIeee8021x 2 }

-- {ROW} 1.3.6.1.4.1.248.32.18.1.5.80.2.1
hmStatusLanIeee8021xAuthenticatorIfcStatusEntry OBJECT-TYPE
    SYNTAX     HmStatusLanIeee8021xAuthenticatorIfcStatusEntry
    MAX-ACCESS not-accessible
    STATUS     current
    DESCRIPTION
            ""
    INDEX {
            hmStatusLanIeee8021xAuthenticatorIfcStatusEntryIfc
          }
    ::= { hmStatusLanIeee8021xAuthenticatorIfcStatusTable 1 }

HmStatusLanIeee8021xAuthenticatorIfcStatusEntry ::= SEQUENCE {
            hmStatusLanIeee8021xAuthenticatorIfcStatusEntryIfc INTEGER,
            hmStatusLanIeee8021xAuthenticatorIfcStatusEntryOperating INTEGER,
            hmStatusLanIeee8021xAuthenticatorIfcStatusEntryMode INTEGER,
            hmStatusLanIeee8021xAuthenticatorIfcStatusEntryState INTEGER,
            hmStatusLanIeee8021xAuthenticatorIfcStatusEntryMacAddress MacAddress,
            hmStatusLanIeee8021xAuthenticatorIfcStatusEntryAuthCount Integer32
    }

-- {COLUMN} 1.3.6.1.4.1.248.32.18.1.5.80.2.1.1
hmStatusLanIeee8021xAuthenticatorIfcStatusEntryIfc OBJECT-TYPE
    SYNTAX     INTEGER {
                  eLan1 (1),
                  eLan2 (2)
            }
    MAX-ACCESS read-only
    STATUS     current
    DESCRIPTION
            "-- empty --"
    ::= { hmStatusLanIeee8021xAuthenticatorIfcStatusEntry 1 }

-- {COLUMN} 1.3.6.1.4.1.248.32.18.1.5.80.2.1.2
hmStatusLanIeee8021xAuthenticatorIfcStatusEntryOperating OBJECT-TYPE
    SYNTAX     INTEGER {
                  eNo (0),
                  eYes (1)
            }
    MAX-ACCESS read-only
    STATUS     current
    DESCRIPTION
            "-- empty --"
    ::= { hmStatusLanIeee8021xAuthenticatorIfcStatusEntry 2 }

-- {COLUMN} 1.3.6.1.4.1.248.32.18.1.5.80.2.1.3
hmStatusLanIeee8021xAuthenticatorIfcStatusEntryMode OBJECT-TYPE
    SYNTAX     INTEGER {
                  eSingleHost (0),
                  eMultipleHost (1),
                  eMultipleAuth (2)
            }
    MAX-ACCESS read-only
    STATUS     current
    DESCRIPTION
            "-- empty --"
    ::= { hmStatusLanIeee8021xAuthenticatorIfcStatusEntry 3 }

-- {COLUMN} 1.3.6.1.4.1.248.32.18.1.5.80.2.1.4
hmStatusLanIeee8021xAuthenticatorIfcStatusEntryState OBJECT-TYPE
    SYNTAX     INTEGER {
                  eOff (0),
                  eLinkLayerDown (1),
                  eOperating (2),
                  eUnauthenticated (3),
                  eAuthenticated (4),
                  eBlocked (5)
            }
    MAX-ACCESS read-only
    STATUS     current
    DESCRIPTION
            "-- empty --"
    ::= { hmStatusLanIeee8021xAuthenticatorIfcStatusEntry 4 }

-- {COLUMN} 1.3.6.1.4.1.248.32.18.1.5.80.2.1.5
hmStatusLanIeee8021xAuthenticatorIfcStatusEntryMacAddress OBJECT-TYPE
    SYNTAX     MacAddress
    MAX-ACCESS read-only
    STATUS     current
    DESCRIPTION
            "-- empty --"
    ::= { hmStatusLanIeee8021xAuthenticatorIfcStatusEntry 5 }

-- {COLUMN} 1.3.6.1.4.1.248.32.18.1.5.80.2.1.6
hmStatusLanIeee8021xAuthenticatorIfcStatusEntryAuthCount OBJECT-TYPE
    SYNTAX     Integer32 (0..2147483647)
    MAX-ACCESS read-only
    STATUS     current
    DESCRIPTION
            "-- empty --"
    ::= { hmStatusLanIeee8021xAuthenticatorIfcStatusEntry 6 }

-- {NODE} 1.3.6.1.4.1.248.32.18.1.5.81
hmStatusLanInterfaceBundling OBJECT IDENTIFIER ::= { hmStatusLan 81 }

-- {TABLE} 1.3.6.1.4.1.248.32.18.1.5.81.1
hmStatusLanInterfaceBundlingInterfacesTable OBJECT-TYPE
    SYNTAX     SEQUENCE OF HmStatusLanInterfaceBundlingInterfacesEntry
    MAX-ACCESS not-accessible
    STATUS     current
    DESCRIPTION
            "-- empty --"
    ::= { hmStatusLanInterfaceBundling 1 }

-- {ROW} 1.3.6.1.4.1.248.32.18.1.5.81.1.1
hmStatusLanInterfaceBundlingInterfacesEntry OBJECT-TYPE
    SYNTAX     HmStatusLanInterfaceBundlingInterfacesEntry
    MAX-ACCESS not-accessible
    STATUS     current
    DESCRIPTION
            ""
    INDEX {
            hmStatusLanInterfaceBundlingInterfacesEntryInterface
          }
    ::= { hmStatusLanInterfaceBundlingInterfacesTable 1 }

HmStatusLanInterfaceBundlingInterfacesEntry ::= SEQUENCE {
            hmStatusLanInterfaceBundlingInterfacesEntryInterface DisplayString,
            hmStatusLanInterfaceBundlingInterfacesEntryStatus INTEGER,
            hmStatusLanInterfaceBundlingInterfacesEntryInterfaceA INTEGER,
            hmStatusLanInterfaceBundlingInterfacesEntryInterfaceB INTEGER
    }

-- {COLUMN} 1.3.6.1.4.1.248.32.18.1.5.81.1.1.1
hmStatusLanInterfaceBundlingInterfacesEntryInterface OBJECT-TYPE
    SYNTAX     DisplayString (SIZE(0..255))
    MAX-ACCESS read-only
    STATUS     current
    DESCRIPTION
            "-- empty --"
    ::= { hmStatusLanInterfaceBundlingInterfacesEntry 1 }

-- {COLUMN} 1.3.6.1.4.1.248.32.18.1.5.81.1.1.2
hmStatusLanInterfaceBundlingInterfacesEntryStatus OBJECT-TYPE
    SYNTAX     INTEGER {
                  eIdle (0),
                  eConfigError (1),
                  eStatupError (2),
                  eRunning (3)
            }
    MAX-ACCESS read-only
    STATUS     current
    DESCRIPTION
            "-- empty --"
    ::= { hmStatusLanInterfaceBundlingInterfacesEntry 2 }

-- {COLUMN} 1.3.6.1.4.1.248.32.18.1.5.81.1.1.5
hmStatusLanInterfaceBundlingInterfacesEntryInterfaceA OBJECT-TYPE
    SYNTAX     INTEGER {
                  eNone (0),
                  eLan1 (256),
                  eLan2 (257),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311)
            }
    MAX-ACCESS read-only
    STATUS     current
    DESCRIPTION
            "-- empty --"
    ::= { hmStatusLanInterfaceBundlingInterfacesEntry 5 }

-- {COLUMN} 1.3.6.1.4.1.248.32.18.1.5.81.1.1.6
hmStatusLanInterfaceBundlingInterfacesEntryInterfaceB OBJECT-TYPE
    SYNTAX     INTEGER {
                  eNone (0),
                  eLan1 (256),
                  eLan2 (257),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311)
            }
    MAX-ACCESS read-only
    STATUS     current
    DESCRIPTION
            "-- empty --"
    ::= { hmStatusLanInterfaceBundlingInterfacesEntry 6 }

-- {TABLE} 1.3.6.1.4.1.248.32.18.1.5.81.2
hmStatusLanInterfaceBundlingByteTransportTable OBJECT-TYPE
    SYNTAX     SEQUENCE OF HmStatusLanInterfaceBundlingByteTransportEntry
    MAX-ACCESS not-accessible
    STATUS     current
    DESCRIPTION
            "-- empty --"
    ::= { hmStatusLanInterfaceBundling 2 }

-- {ROW} 1.3.6.1.4.1.248.32.18.1.5.81.2.1
hmStatusLanInterfaceBundlingByteTransportEntry OBJECT-TYPE
    SYNTAX     HmStatusLanInterfaceBundlingByteTransportEntry
    MAX-ACCESS not-accessible
    STATUS     current
    DESCRIPTION
            ""
    INDEX {
            hmStatusLanInterfaceBundlingByteTransportEntryIfc
          }
    ::= { hmStatusLanInterfaceBundlingByteTransportTable 1 }

HmStatusLanInterfaceBundlingByteTransportEntry ::= SEQUENCE {
            hmStatusLanInterfaceBundlingByteTransportEntryIfc DisplayString,
            hmStatusLanInterfaceBundlingByteTransportEntryTxBytes Counter64,
            hmStatusLanInterfaceBundlingByteTransportEntryRxBytes Counter64,
            hmStatusLanInterfaceBundlingByteTransportEntryThroughput DisplayString,
            hmStatusLanInterfaceBundlingByteTransportEntryMaxThroughput DisplayString,
            hmStatusLanInterfaceBundlingByteTransportEntryBytesThroughput Integer32,
            hmStatusLanInterfaceBundlingByteTransportEntryBytesMaxThrpt Integer32
    }

-- {COLUMN} 1.3.6.1.4.1.248.32.18.1.5.81.2.1.1
hmStatusLanInterfaceBundlingByteTransportEntryIfc OBJECT-TYPE
    SYNTAX     DisplayString (SIZE(0..255))
    MAX-ACCESS read-only
    STATUS     current
    DESCRIPTION
            "-- empty --"
    ::= { hmStatusLanInterfaceBundlingByteTransportEntry 1 }

-- {COLUMN} 1.3.6.1.4.1.248.32.18.1.5.81.2.1.2
hmStatusLanInterfaceBundlingByteTransportEntryTxBytes OBJECT-TYPE
    SYNTAX     Counter64
    MAX-ACCESS read-only
    STATUS     current
    DESCRIPTION
            "-- empty --"
    ::= { hmStatusLanInterfaceBundlingByteTransportEntry 2 }

-- {COLUMN} 1.3.6.1.4.1.248.32.18.1.5.81.2.1.3
hmStatusLanInterfaceBundlingByteTransportEntryRxBytes OBJECT-TYPE
    SYNTAX     Counter64
    MAX-ACCESS read-only
    STATUS     current
    DESCRIPTION
            "-- empty --"
    ::= { hmStatusLanInterfaceBundlingByteTransportEntry 3 }

-- {COLUMN} 1.3.6.1.4.1.248.32.18.1.5.81.2.1.4
hmStatusLanInterfaceBundlingByteTransportEntryThroughput OBJECT-TYPE
    SYNTAX     DisplayString (SIZE(0..255))
    MAX-ACCESS read-only
    STATUS     current
    DESCRIPTION
            "-- empty --"
    ::= { hmStatusLanInterfaceBundlingByteTransportEntry 4 }

-- {COLUMN} 1.3.6.1.4.1.248.32.18.1.5.81.2.1.5
hmStatusLanInterfaceBundlingByteTransportEntryMaxThroughput OBJECT-TYPE
    SYNTAX     DisplayString (SIZE(0..255))
    MAX-ACCESS read-only
    STATUS     current
    DESCRIPTION
            "-- empty --"
    ::= { hmStatusLanInterfaceBundlingByteTransportEntry 5 }

-- {COLUMN} 1.3.6.1.4.1.248.32.18.1.5.81.2.1.6
hmStatusLanInterfaceBundlingByteTransportEntryBytesThroughput OBJECT-TYPE
    SYNTAX     Integer32 (0..2147483647)
    MAX-ACCESS read-only
    STATUS     current
    DESCRIPTION
            "-- empty --"
    ::= { hmStatusLanInterfaceBundlingByteTransportEntry 6 }

-- {COLUMN} 1.3.6.1.4.1.248.32.18.1.5.81.2.1.7
hmStatusLanInterfaceBundlingByteTransportEntryBytesMaxThrpt OBJECT-TYPE
    SYNTAX     Integer32 (0..2147483647)
    MAX-ACCESS read-only
    STATUS     current
    DESCRIPTION
            "-- empty --"
    ::= { hmStatusLanInterfaceBundlingByteTransportEntry 7 }

-- {TABLE} 1.3.6.1.4.1.248.32.18.1.5.81.3
hmStatusLanInterfaceBundlingPacketTransportTable OBJECT-TYPE
    SYNTAX     SEQUENCE OF HmStatusLanInterfaceBundlingPacketTransportEntry
    MAX-ACCESS not-accessible
    STATUS     current
    DESCRIPTION
            "-- empty --"
    ::= { hmStatusLanInterfaceBundling 3 }

-- {ROW} 1.3.6.1.4.1.248.32.18.1.5.81.3.1
hmStatusLanInterfaceBundlingPacketTransportEntry OBJECT-TYPE
    SYNTAX     HmStatusLanInterfaceBundlingPacketTransportEntry
    MAX-ACCESS not-accessible
    STATUS     current
    DESCRIPTION
            ""
    INDEX {
            hmStatusLanInterfaceBundlingPacketTransportEntryIfc
          }
    ::= { hmStatusLanInterfaceBundlingPacketTransportTable 1 }

HmStatusLanInterfaceBundlingPacketTransportEntry ::= SEQUENCE {
            hmStatusLanInterfaceBundlingPacketTransportEntryIfc DisplayString,
            hmStatusLanInterfaceBundlingPacketTransportEntryRxPackets Counter32,
            hmStatusLanInterfaceBundlingPacketTransportEntryTxPackets Counter32,
            hmStatusLanInterfaceBundlingPacketTransportEntryRxBroadcasts Counter32,
            hmStatusLanInterfaceBundlingPacketTransportEntryRxMulticasts Counter32,
            hmStatusLanInterfaceBundlingPacketTransportEntryRxUnicasts Counter32,
            hmStatusLanInterfaceBundlingPacketTransportEntryTxBroadcasts Counter32,
            hmStatusLanInterfaceBundlingPacketTransportEntryTxMulticasts Counter32,
            hmStatusLanInterfaceBundlingPacketTransportEntryTxUnicasts Counter32
    }

-- {COLUMN} 1.3.6.1.4.1.248.32.18.1.5.81.3.1.1
hmStatusLanInterfaceBundlingPacketTransportEntryIfc OBJECT-TYPE
    SYNTAX     DisplayString (SIZE(0..255))
    MAX-ACCESS read-only
    STATUS     current
    DESCRIPTION
            "-- empty --"
    ::= { hmStatusLanInterfaceBundlingPacketTransportEntry 1 }

-- {COLUMN} 1.3.6.1.4.1.248.32.18.1.5.81.3.1.2
hmStatusLanInterfaceBundlingPacketTransportEntryRxPackets OBJECT-TYPE
    SYNTAX     Counter32
    MAX-ACCESS read-only
    STATUS     current
    DESCRIPTION
            "-- empty --"
    ::= { hmStatusLanInterfaceBundlingPacketTransportEntry 2 }

-- {COLUMN} 1.3.6.1.4.1.248.32.18.1.5.81.3.1.3
hmStatusLanInterfaceBundlingPacketTransportEntryTxPackets OBJECT-TYPE
    SYNTAX     Counter32
    MAX-ACCESS read-only
    STATUS     current
    DESCRIPTION
            "-- empty --"
    ::= { hmStatusLanInterfaceBundlingPacketTransportEntry 3 }

-- {COLUMN} 1.3.6.1.4.1.248.32.18.1.5.81.3.1.4
hmStatusLanInterfaceBundlingPacketTransportEntryRxBroadcasts OBJECT-TYPE
    SYNTAX     Counter32
    MAX-ACCESS read-only
    STATUS     current
    DESCRIPTION
            "-- empty --"
    ::= { hmStatusLanInterfaceBundlingPacketTransportEntry 4 }

-- {COLUMN} 1.3.6.1.4.1.248.32.18.1.5.81.3.1.5
hmStatusLanInterfaceBundlingPacketTransportEntryRxMulticasts OBJECT-TYPE
    SYNTAX     Counter32
    MAX-ACCESS read-only
    STATUS     current
    DESCRIPTION
            "-- empty --"
    ::= { hmStatusLanInterfaceBundlingPacketTransportEntry 5 }

-- {COLUMN} 1.3.6.1.4.1.248.32.18.1.5.81.3.1.6
hmStatusLanInterfaceBundlingPacketTransportEntryRxUnicasts OBJECT-TYPE
    SYNTAX     Counter32
    MAX-ACCESS read-only
    STATUS     current
    DESCRIPTION
            "-- empty --"
    ::= { hmStatusLanInterfaceBundlingPacketTransportEntry 6 }

-- {COLUMN} 1.3.6.1.4.1.248.32.18.1.5.81.3.1.7
hmStatusLanInterfaceBundlingPacketTransportEntryTxBroadcasts OBJECT-TYPE
    SYNTAX     Counter32
    MAX-ACCESS read-only
    STATUS     current
    DESCRIPTION
            "-- empty --"
    ::= { hmStatusLanInterfaceBundlingPacketTransportEntry 7 }

-- {COLUMN} 1.3.6.1.4.1.248.32.18.1.5.81.3.1.8
hmStatusLanInterfaceBundlingPacketTransportEntryTxMulticasts OBJECT-TYPE
    SYNTAX     Counter32
    MAX-ACCESS read-only
    STATUS     current
    DESCRIPTION
            "-- empty --"
    ::= { hmStatusLanInterfaceBundlingPacketTransportEntry 8 }

-- {COLUMN} 1.3.6.1.4.1.248.32.18.1.5.81.3.1.9
hmStatusLanInterfaceBundlingPacketTransportEntryTxUnicasts OBJECT-TYPE
    SYNTAX     Counter32
    MAX-ACCESS read-only
    STATUS     current
    DESCRIPTION
            "-- empty --"
    ::= { hmStatusLanInterfaceBundlingPacketTransportEntry 9 }

-- {TABLE} 1.3.6.1.4.1.248.32.18.1.5.81.4
hmStatusLanInterfaceBundlingErrorsTable OBJECT-TYPE
    SYNTAX     SEQUENCE OF HmStatusLanInterfaceBundlingErrorsEntry
    MAX-ACCESS not-accessible
    STATUS     current
    DESCRIPTION
            "-- empty --"
    ::= { hmStatusLanInterfaceBundling 4 }

-- {ROW} 1.3.6.1.4.1.248.32.18.1.5.81.4.1
hmStatusLanInterfaceBundlingErrorsEntry OBJECT-TYPE
    SYNTAX     HmStatusLanInterfaceBundlingErrorsEntry
    MAX-ACCESS not-accessible
    STATUS     current
    DESCRIPTION
            ""
    INDEX {
            hmStatusLanInterfaceBundlingErrorsEntryIfc
          }
    ::= { hmStatusLanInterfaceBundlingErrorsTable 1 }

HmStatusLanInterfaceBundlingErrorsEntry ::= SEQUENCE {
            hmStatusLanInterfaceBundlingErrorsEntryIfc DisplayString,
            hmStatusLanInterfaceBundlingErrorsEntryTxDiscarded Counter32
    }

-- {COLUMN} 1.3.6.1.4.1.248.32.18.1.5.81.4.1.1
hmStatusLanInterfaceBundlingErrorsEntryIfc OBJECT-TYPE
    SYNTAX     DisplayString (SIZE(0..255))
    MAX-ACCESS read-only
    STATUS     current
    DESCRIPTION
            "-- empty --"
    ::= { hmStatusLanInterfaceBundlingErrorsEntry 1 }

-- {COLUMN} 1.3.6.1.4.1.248.32.18.1.5.81.4.1.2
hmStatusLanInterfaceBundlingErrorsEntryTxDiscarded OBJECT-TYPE
    SYNTAX     Counter32
    MAX-ACCESS read-only
    STATUS     current
    DESCRIPTION
            "-- empty --"
    ::= { hmStatusLanInterfaceBundlingErrorsEntry 2 }

-- {NODE} 1.3.6.1.4.1.248.32.18.1.5.81.11
hmStatusLanInterfaceBundlingPrp OBJECT IDENTIFIER ::= { hmStatusLanInterfaceBundling 11 }

-- {TABLE} 1.3.6.1.4.1.248.32.18.1.5.81.11.1
hmStatusLanInterfaceBundlingPrpInterfacesTable OBJECT-TYPE
    SYNTAX     SEQUENCE OF HmStatusLanInterfaceBundlingPrpInterfacesEntry
    MAX-ACCESS not-accessible
    STATUS     current
    DESCRIPTION
            "-- empty --"
    ::= { hmStatusLanInterfaceBundlingPrp 1 }

-- {ROW} 1.3.6.1.4.1.248.32.18.1.5.81.11.1.1
hmStatusLanInterfaceBundlingPrpInterfacesEntry OBJECT-TYPE
    SYNTAX     HmStatusLanInterfaceBundlingPrpInterfacesEntry
    MAX-ACCESS not-accessible
    STATUS     current
    DESCRIPTION
            ""
    INDEX {
            hmStatusLanInterfaceBundlingPrpInterfacesEntryInterface
          }
    ::= { hmStatusLanInterfaceBundlingPrpInterfacesTable 1 }

HmStatusLanInterfaceBundlingPrpInterfacesEntry ::= SEQUENCE {
            hmStatusLanInterfaceBundlingPrpInterfacesEntryInterface DisplayString,
            hmStatusLanInterfaceBundlingPrpInterfacesEntryCnterrora Integer32,
            hmStatusLanInterfaceBundlingPrpInterfacesEntryCnterrorb Integer32,
            hmStatusLanInterfaceBundlingPrpInterfacesEntryCntreceiveda Integer32,
            hmStatusLanInterfaceBundlingPrpInterfacesEntryCntreceivedb Integer32,
            hmStatusLanInterfaceBundlingPrpInterfacesEntryCnterrwronglana Integer32,
            hmStatusLanInterfaceBundlingPrpInterfacesEntryCnterrwronglanb Integer32,
            hmStatusLanInterfaceBundlingPrpInterfacesEntryActivea INTEGER,
            hmStatusLanInterfaceBundlingPrpInterfacesEntryActiveb INTEGER,
            hmStatusLanInterfaceBundlingPrpInterfacesEntryCntuniquea Integer32,
            hmStatusLanInterfaceBundlingPrpInterfacesEntryCntuniqueb Integer32,
            hmStatusLanInterfaceBundlingPrpInterfacesEntryCntduplicatea Integer32,
            hmStatusLanInterfaceBundlingPrpInterfacesEntryCntduplicateb Integer32,
            hmStatusLanInterfaceBundlingPrpInterfacesEntryCntmultia Integer32,
            hmStatusLanInterfaceBundlingPrpInterfacesEntryCntmultib Integer32
    }

-- {COLUMN} 1.3.6.1.4.1.248.32.18.1.5.81.11.1.1.1
hmStatusLanInterfaceBundlingPrpInterfacesEntryInterface OBJECT-TYPE
    SYNTAX     DisplayString (SIZE(0..255))
    MAX-ACCESS read-only
    STATUS     current
    DESCRIPTION
            "-- empty --"
    ::= { hmStatusLanInterfaceBundlingPrpInterfacesEntry 1 }

-- {COLUMN} 1.3.6.1.4.1.248.32.18.1.5.81.11.1.1.2
hmStatusLanInterfaceBundlingPrpInterfacesEntryCnterrora OBJECT-TYPE
    SYNTAX     Integer32 (0..2147483647)
    MAX-ACCESS read-only
    STATUS     current
    DESCRIPTION
            "-- empty --"
    ::= { hmStatusLanInterfaceBundlingPrpInterfacesEntry 2 }

-- {COLUMN} 1.3.6.1.4.1.248.32.18.1.5.81.11.1.1.3
hmStatusLanInterfaceBundlingPrpInterfacesEntryCnterrorb OBJECT-TYPE
    SYNTAX     Integer32 (0..2147483647)
    MAX-ACCESS read-only
    STATUS     current
    DESCRIPTION
            "-- empty --"
    ::= { hmStatusLanInterfaceBundlingPrpInterfacesEntry 3 }

-- {COLUMN} 1.3.6.1.4.1.248.32.18.1.5.81.11.1.1.4
hmStatusLanInterfaceBundlingPrpInterfacesEntryCntreceiveda OBJECT-TYPE
    SYNTAX     Integer32 (0..2147483647)
    MAX-ACCESS read-only
    STATUS     current
    DESCRIPTION
            "-- empty --"
    ::= { hmStatusLanInterfaceBundlingPrpInterfacesEntry 4 }

-- {COLUMN} 1.3.6.1.4.1.248.32.18.1.5.81.11.1.1.5
hmStatusLanInterfaceBundlingPrpInterfacesEntryCntreceivedb OBJECT-TYPE
    SYNTAX     Integer32 (0..2147483647)
    MAX-ACCESS read-only
    STATUS     current
    DESCRIPTION
            "-- empty --"
    ::= { hmStatusLanInterfaceBundlingPrpInterfacesEntry 5 }

-- {COLUMN} 1.3.6.1.4.1.248.32.18.1.5.81.11.1.1.6
hmStatusLanInterfaceBundlingPrpInterfacesEntryCnterrwronglana OBJECT-TYPE
    SYNTAX     Integer32 (0..2147483647)
    MAX-ACCESS read-only
    STATUS     current
    DESCRIPTION
            "-- empty --"
    ::= { hmStatusLanInterfaceBundlingPrpInterfacesEntry 6 }

-- {COLUMN} 1.3.6.1.4.1.248.32.18.1.5.81.11.1.1.7
hmStatusLanInterfaceBundlingPrpInterfacesEntryCnterrwronglanb OBJECT-TYPE
    SYNTAX     Integer32 (0..2147483647)
    MAX-ACCESS read-only
    STATUS     current
    DESCRIPTION
            "-- empty --"
    ::= { hmStatusLanInterfaceBundlingPrpInterfacesEntry 7 }

-- {COLUMN} 1.3.6.1.4.1.248.32.18.1.5.81.11.1.1.8
hmStatusLanInterfaceBundlingPrpInterfacesEntryActivea OBJECT-TYPE
    SYNTAX     INTEGER {
                  eNo (0),
                  eYes (1)
            }
    MAX-ACCESS read-only
    STATUS     current
    DESCRIPTION
            "-- empty --"
    ::= { hmStatusLanInterfaceBundlingPrpInterfacesEntry 8 }

-- {COLUMN} 1.3.6.1.4.1.248.32.18.1.5.81.11.1.1.9
hmStatusLanInterfaceBundlingPrpInterfacesEntryActiveb OBJECT-TYPE
    SYNTAX     INTEGER {
                  eNo (0),
                  eYes (1)
            }
    MAX-ACCESS read-only
    STATUS     current
    DESCRIPTION
            "-- empty --"
    ::= { hmStatusLanInterfaceBundlingPrpInterfacesEntry 9 }

-- {COLUMN} 1.3.6.1.4.1.248.32.18.1.5.81.11.1.1.10
hmStatusLanInterfaceBundlingPrpInterfacesEntryCntuniquea OBJECT-TYPE
    SYNTAX     Integer32 (0..2147483647)
    MAX-ACCESS read-only
    STATUS     current
    DESCRIPTION
            "-- empty --"
    ::= { hmStatusLanInterfaceBundlingPrpInterfacesEntry 10 }

-- {COLUMN} 1.3.6.1.4.1.248.32.18.1.5.81.11.1.1.11
hmStatusLanInterfaceBundlingPrpInterfacesEntryCntuniqueb OBJECT-TYPE
    SYNTAX     Integer32 (0..2147483647)
    MAX-ACCESS read-only
    STATUS     current
    DESCRIPTION
            "-- empty --"
    ::= { hmStatusLanInterfaceBundlingPrpInterfacesEntry 11 }

-- {COLUMN} 1.3.6.1.4.1.248.32.18.1.5.81.11.1.1.12
hmStatusLanInterfaceBundlingPrpInterfacesEntryCntduplicatea OBJECT-TYPE
    SYNTAX     Integer32 (0..2147483647)
    MAX-ACCESS read-only
    STATUS     current
    DESCRIPTION
            "-- empty --"
    ::= { hmStatusLanInterfaceBundlingPrpInterfacesEntry 12 }

-- {COLUMN} 1.3.6.1.4.1.248.32.18.1.5.81.11.1.1.13
hmStatusLanInterfaceBundlingPrpInterfacesEntryCntduplicateb OBJECT-TYPE
    SYNTAX     Integer32 (0..2147483647)
    MAX-ACCESS read-only
    STATUS     current
    DESCRIPTION
            "-- empty --"
    ::= { hmStatusLanInterfaceBundlingPrpInterfacesEntry 13 }

-- {COLUMN} 1.3.6.1.4.1.248.32.18.1.5.81.11.1.1.14
hmStatusLanInterfaceBundlingPrpInterfacesEntryCntmultia OBJECT-TYPE
    SYNTAX     Integer32 (0..2147483647)
    MAX-ACCESS read-only
    STATUS     current
    DESCRIPTION
            "-- empty --"
    ::= { hmStatusLanInterfaceBundlingPrpInterfacesEntry 14 }

-- {COLUMN} 1.3.6.1.4.1.248.32.18.1.5.81.11.1.1.15
hmStatusLanInterfaceBundlingPrpInterfacesEntryCntmultib OBJECT-TYPE
    SYNTAX     Integer32 (0..2147483647)
    MAX-ACCESS read-only
    STATUS     current
    DESCRIPTION
            "-- empty --"
    ::= { hmStatusLanInterfaceBundlingPrpInterfacesEntry 15 }

-- {TABLE} 1.3.6.1.4.1.248.32.18.1.5.81.11.2
hmStatusLanInterfaceBundlingPrpNodeTableTable OBJECT-TYPE
    SYNTAX     SEQUENCE OF HmStatusLanInterfaceBundlingPrpNodeTableEntry
    MAX-ACCESS not-accessible
    STATUS     current
    DESCRIPTION
            "-- empty --"
    ::= { hmStatusLanInterfaceBundlingPrp 2 }

-- {ROW} 1.3.6.1.4.1.248.32.18.1.5.81.11.2.1
hmStatusLanInterfaceBundlingPrpNodeTableEntry OBJECT-TYPE
    SYNTAX     HmStatusLanInterfaceBundlingPrpNodeTableEntry
    MAX-ACCESS not-accessible
    STATUS     current
    DESCRIPTION
            ""
    INDEX {
            hmStatusLanInterfaceBundlingPrpNodeTableEntryInterface,
            hmStatusLanInterfaceBundlingPrpNodeTableEntryMacAddress
          }
    ::= { hmStatusLanInterfaceBundlingPrpNodeTableTable 1 }

HmStatusLanInterfaceBundlingPrpNodeTableEntry ::= SEQUENCE {
            hmStatusLanInterfaceBundlingPrpNodeTableEntryInterface DisplayString,
            hmStatusLanInterfaceBundlingPrpNodeTableEntryMacAddress MacAddress,
            hmStatusLanInterfaceBundlingPrpNodeTableEntryType INTEGER,
            hmStatusLanInterfaceBundlingPrpNodeTableEntryDuplicateMode INTEGER,
            hmStatusLanInterfaceBundlingPrpNodeTableEntryTimelastseena Integer32,
            hmStatusLanInterfaceBundlingPrpNodeTableEntryTimelastseenb Integer32,
            hmStatusLanInterfaceBundlingPrpNodeTableEntryCntreceiveda Integer32,
            hmStatusLanInterfaceBundlingPrpNodeTableEntryCntreceivedb Integer32,
            hmStatusLanInterfaceBundlingPrpNodeTableEntryCnterrwronglana Integer32,
            hmStatusLanInterfaceBundlingPrpNodeTableEntryCnterrwronglanb Integer32,
            hmStatusLanInterfaceBundlingPrpNodeTableEntryNumEntries Integer32
    }

-- {COLUMN} 1.3.6.1.4.1.248.32.18.1.5.81.11.2.1.1
hmStatusLanInterfaceBundlingPrpNodeTableEntryInterface OBJECT-TYPE
    SYNTAX     DisplayString (SIZE(0..255))
    MAX-ACCESS read-only
    STATUS     current
    DESCRIPTION
            "-- empty --"
    ::= { hmStatusLanInterfaceBundlingPrpNodeTableEntry 1 }

-- {COLUMN} 1.3.6.1.4.1.248.32.18.1.5.81.11.2.1.2
hmStatusLanInterfaceBundlingPrpNodeTableEntryMacAddress OBJECT-TYPE
    SYNTAX     MacAddress
    MAX-ACCESS read-only
    STATUS     current
    DESCRIPTION
            "-- empty --"
    ::= { hmStatusLanInterfaceBundlingPrpNodeTableEntry 2 }

-- {COLUMN} 1.3.6.1.4.1.248.32.18.1.5.81.11.2.1.3
hmStatusLanInterfaceBundlingPrpNodeTableEntryType OBJECT-TYPE
    SYNTAX     INTEGER {
                  eUnknown (0),
                  eSana (1),
                  eSanb (2),
                  eSanab (3),
                  eDanp (4),
                  eVdanp (5),
                  eRedboxp (6)
            }
    MAX-ACCESS read-only
    STATUS     current
    DESCRIPTION
            "-- empty --"
    ::= { hmStatusLanInterfaceBundlingPrpNodeTableEntry 3 }

-- {COLUMN} 1.3.6.1.4.1.248.32.18.1.5.81.11.2.1.4
hmStatusLanInterfaceBundlingPrpNodeTableEntryDuplicateMode OBJECT-TYPE
    SYNTAX     INTEGER {
                  eNone (0),
                  eAccept (1),
                  eDiscard (2)
            }
    MAX-ACCESS read-only
    STATUS     current
    DESCRIPTION
            "-- empty --"
    ::= { hmStatusLanInterfaceBundlingPrpNodeTableEntry 4 }

-- {COLUMN} 1.3.6.1.4.1.248.32.18.1.5.81.11.2.1.5
hmStatusLanInterfaceBundlingPrpNodeTableEntryTimelastseena OBJECT-TYPE
    SYNTAX     Integer32 (0..2147483647)
    MAX-ACCESS read-only
    STATUS     current
    DESCRIPTION
            "-- empty --"
    ::= { hmStatusLanInterfaceBundlingPrpNodeTableEntry 5 }

-- {COLUMN} 1.3.6.1.4.1.248.32.18.1.5.81.11.2.1.6
hmStatusLanInterfaceBundlingPrpNodeTableEntryTimelastseenb OBJECT-TYPE
    SYNTAX     Integer32 (0..2147483647)
    MAX-ACCESS read-only
    STATUS     current
    DESCRIPTION
            "-- empty --"
    ::= { hmStatusLanInterfaceBundlingPrpNodeTableEntry 6 }

-- {COLUMN} 1.3.6.1.4.1.248.32.18.1.5.81.11.2.1.7
hmStatusLanInterfaceBundlingPrpNodeTableEntryCntreceiveda OBJECT-TYPE
    SYNTAX     Integer32 (0..2147483647)
    MAX-ACCESS read-only
    STATUS     current
    DESCRIPTION
            "-- empty --"
    ::= { hmStatusLanInterfaceBundlingPrpNodeTableEntry 7 }

-- {COLUMN} 1.3.6.1.4.1.248.32.18.1.5.81.11.2.1.8
hmStatusLanInterfaceBundlingPrpNodeTableEntryCntreceivedb OBJECT-TYPE
    SYNTAX     Integer32 (0..2147483647)
    MAX-ACCESS read-only
    STATUS     current
    DESCRIPTION
            "-- empty --"
    ::= { hmStatusLanInterfaceBundlingPrpNodeTableEntry 8 }

-- {COLUMN} 1.3.6.1.4.1.248.32.18.1.5.81.11.2.1.9
hmStatusLanInterfaceBundlingPrpNodeTableEntryCnterrwronglana OBJECT-TYPE
    SYNTAX     Integer32 (0..2147483647)
    MAX-ACCESS read-only
    STATUS     current
    DESCRIPTION
            "-- empty --"
    ::= { hmStatusLanInterfaceBundlingPrpNodeTableEntry 9 }

-- {COLUMN} 1.3.6.1.4.1.248.32.18.1.5.81.11.2.1.10
hmStatusLanInterfaceBundlingPrpNodeTableEntryCnterrwronglanb OBJECT-TYPE
    SYNTAX     Integer32 (0..2147483647)
    MAX-ACCESS read-only
    STATUS     current
    DESCRIPTION
            "-- empty --"
    ::= { hmStatusLanInterfaceBundlingPrpNodeTableEntry 10 }

-- {COLUMN} 1.3.6.1.4.1.248.32.18.1.5.81.11.2.1.11
hmStatusLanInterfaceBundlingPrpNodeTableEntryNumEntries OBJECT-TYPE
    SYNTAX     Integer32 (0..2147483647)
    MAX-ACCESS read-only
    STATUS     current
    DESCRIPTION
            "-- empty --"
    ::= { hmStatusLanInterfaceBundlingPrpNodeTableEntry 11 }

-- {TABLE} 1.3.6.1.4.1.248.32.18.1.5.81.11.3
hmStatusLanInterfaceBundlingPrpProxyNodeTableTable OBJECT-TYPE
    SYNTAX     SEQUENCE OF HmStatusLanInterfaceBundlingPrpProxyNodeTableEntry
    MAX-ACCESS not-accessible
    STATUS     current
    DESCRIPTION
            "-- empty --"
    ::= { hmStatusLanInterfaceBundlingPrp 3 }

-- {ROW} 1.3.6.1.4.1.248.32.18.1.5.81.11.3.1
hmStatusLanInterfaceBundlingPrpProxyNodeTableEntry OBJECT-TYPE
    SYNTAX     HmStatusLanInterfaceBundlingPrpProxyNodeTableEntry
    MAX-ACCESS not-accessible
    STATUS     current
    DESCRIPTION
            ""
    INDEX {
            hmStatusLanInterfaceBundlingPrpProxyNodeTableEntryInterface,
            hmStatusLanInterfaceBundlingPrpProxyNodeTableEntryMacAddress
          }
    ::= { hmStatusLanInterfaceBundlingPrpProxyNodeTableTable 1 }

HmStatusLanInterfaceBundlingPrpProxyNodeTableEntry ::= SEQUENCE {
            hmStatusLanInterfaceBundlingPrpProxyNodeTableEntryInterface DisplayString,
            hmStatusLanInterfaceBundlingPrpProxyNodeTableEntryMacAddress MacAddress,
            hmStatusLanInterfaceBundlingPrpProxyNodeTableEntryTimelastseen Integer32,
            hmStatusLanInterfaceBundlingPrpProxyNodeTableEntryCntreceived Integer32,
            hmStatusLanInterfaceBundlingPrpProxyNodeTableEntryTxseqnum Integer32
    }

-- {COLUMN} 1.3.6.1.4.1.248.32.18.1.5.81.11.3.1.1
hmStatusLanInterfaceBundlingPrpProxyNodeTableEntryInterface OBJECT-TYPE
    SYNTAX     DisplayString (SIZE(0..255))
    MAX-ACCESS read-only
    STATUS     current
    DESCRIPTION
            "-- empty --"
    ::= { hmStatusLanInterfaceBundlingPrpProxyNodeTableEntry 1 }

-- {COLUMN} 1.3.6.1.4.1.248.32.18.1.5.81.11.3.1.2
hmStatusLanInterfaceBundlingPrpProxyNodeTableEntryMacAddress OBJECT-TYPE
    SYNTAX     MacAddress
    MAX-ACCESS read-only
    STATUS     current
    DESCRIPTION
            "-- empty --"
    ::= { hmStatusLanInterfaceBundlingPrpProxyNodeTableEntry 2 }

-- {COLUMN} 1.3.6.1.4.1.248.32.18.1.5.81.11.3.1.3
hmStatusLanInterfaceBundlingPrpProxyNodeTableEntryTimelastseen OBJECT-TYPE
    SYNTAX     Integer32 (0..2147483647)
    MAX-ACCESS read-only
    STATUS     current
    DESCRIPTION
            "-- empty --"
    ::= { hmStatusLanInterfaceBundlingPrpProxyNodeTableEntry 3 }

-- {COLUMN} 1.3.6.1.4.1.248.32.18.1.5.81.11.3.1.4
hmStatusLanInterfaceBundlingPrpProxyNodeTableEntryCntreceived OBJECT-TYPE
    SYNTAX     Integer32 (0..2147483647)
    MAX-ACCESS read-only
    STATUS     current
    DESCRIPTION
            "-- empty --"
    ::= { hmStatusLanInterfaceBundlingPrpProxyNodeTableEntry 4 }

-- {COLUMN} 1.3.6.1.4.1.248.32.18.1.5.81.11.3.1.5
hmStatusLanInterfaceBundlingPrpProxyNodeTableEntryTxseqnum OBJECT-TYPE
    SYNTAX     Integer32 (0..65535)
    MAX-ACCESS read-only
    STATUS     current
    DESCRIPTION
            "-- empty --"
    ::= { hmStatusLanInterfaceBundlingPrpProxyNodeTableEntry 5 }

-- {SCALAR} 1.3.6.1.4.1.248.32.18.1.5.81.11.99
hmStatusLanInterfaceBundlingPrpDeleteValues OBJECT-TYPE
    SYNTAX     DisplayString
    MAX-ACCESS read-write
    STATUS     current
    DESCRIPTION
            "-- empty --"
    ::= { hmStatusLanInterfaceBundlingPrp 99 }

-- {SCALAR} 1.3.6.1.4.1.248.32.18.1.5.81.99
hmStatusLanInterfaceBundlingDeleteValues OBJECT-TYPE
    SYNTAX     DisplayString
    MAX-ACCESS read-write
    STATUS     current
    DESCRIPTION
            "-- empty --"
    ::= { hmStatusLanInterfaceBundling 99 }

-- {TABLE} 1.3.6.1.4.1.248.32.18.1.5.90
hmStatusLanStationTableTable OBJECT-TYPE
    SYNTAX     SEQUENCE OF HmStatusLanStationTableEntry
    MAX-ACCESS not-accessible
    STATUS     current
    DESCRIPTION
            "-- empty --"
    ::= { hmStatusLan 90 }

-- {ROW} 1.3.6.1.4.1.248.32.18.1.5.90.1
hmStatusLanStationTableEntry OBJECT-TYPE
    SYNTAX     HmStatusLanStationTableEntry
    MAX-ACCESS not-accessible
    STATUS     current
    DESCRIPTION
            ""
    INDEX {
            hmStatusLanStationTableEntryInterface,
            hmStatusLanStationTableEntryMacAddress
          }
    ::= { hmStatusLanStationTableTable 1 }

HmStatusLanStationTableEntry ::= SEQUENCE {
            hmStatusLanStationTableEntryMacAddress MacAddress,
            hmStatusLanStationTableEntryInterface INTEGER,
            hmStatusLanStationTableEntryTxLimit Integer32,
            hmStatusLanStationTableEntryRxLimit Integer32,
            hmStatusLanStationTableEntryVlanId Integer32,
            hmStatusLanStationTableEntryOrigVlanId Integer32,
            hmStatusLanStationTableEntryAuthenticated INTEGER
    }

-- {COLUMN} 1.3.6.1.4.1.248.32.18.1.5.90.1.1
hmStatusLanStationTableEntryMacAddress OBJECT-TYPE
    SYNTAX     MacAddress
    MAX-ACCESS read-only
    STATUS     current
    DESCRIPTION
            "-- empty --"
    ::= { hmStatusLanStationTableEntry 1 }

-- {COLUMN} 1.3.6.1.4.1.248.32.18.1.5.90.1.2
hmStatusLanStationTableEntryInterface OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eAny (65535)
            }
    MAX-ACCESS read-only
    STATUS     current
    DESCRIPTION
            "-- empty --"
    ::= { hmStatusLanStationTableEntry 2 }

-- {COLUMN} 1.3.6.1.4.1.248.32.18.1.5.90.1.3
hmStatusLanStationTableEntryTxLimit OBJECT-TYPE
    SYNTAX     Integer32 (0..2147483647)
    MAX-ACCESS read-only
    STATUS     current
    DESCRIPTION
            "-- empty --"
    ::= { hmStatusLanStationTableEntry 3 }

-- {COLUMN} 1.3.6.1.4.1.248.32.18.1.5.90.1.4
hmStatusLanStationTableEntryRxLimit OBJECT-TYPE
    SYNTAX     Integer32 (0..2147483647)
    MAX-ACCESS read-only
    STATUS     current
    DESCRIPTION
            "-- empty --"
    ::= { hmStatusLanStationTableEntry 4 }

-- {COLUMN} 1.3.6.1.4.1.248.32.18.1.5.90.1.5
hmStatusLanStationTableEntryVlanId OBJECT-TYPE
    SYNTAX     Integer32 (0..65535)
    MAX-ACCESS read-only
    STATUS     current
    DESCRIPTION
            "-- empty --"
    ::= { hmStatusLanStationTableEntry 5 }

-- {COLUMN} 1.3.6.1.4.1.248.32.18.1.5.90.1.6
hmStatusLanStationTableEntryOrigVlanId OBJECT-TYPE
    SYNTAX     Integer32 (0..65535)
    MAX-ACCESS read-only
    STATUS     current
    DESCRIPTION
            "-- empty --"
    ::= { hmStatusLanStationTableEntry 6 }

-- {COLUMN} 1.3.6.1.4.1.248.32.18.1.5.90.1.7
hmStatusLanStationTableEntryAuthenticated OBJECT-TYPE
    SYNTAX     INTEGER {
                  eNo (0),
                  eYes (1)
            }
    MAX-ACCESS read-only
    STATUS     current
    DESCRIPTION
            "-- empty --"
    ::= { hmStatusLanStationTableEntry 7 }

-- {NODE} 1.3.6.1.4.1.248.32.18.1.6
hmStatusPpp OBJECT IDENTIFIER ::= { hmStatus 6 }

-- {TABLE} 1.3.6.1.4.1.248.32.18.1.6.1
hmStatusPppPppPhasesTable OBJECT-TYPE
    SYNTAX     SEQUENCE OF HmStatusPppPppPhasesEntry
    MAX-ACCESS not-accessible
    STATUS     current
    DESCRIPTION
            "-- empty --"
    ::= { hmStatusPpp 1 }

-- {ROW} 1.3.6.1.4.1.248.32.18.1.6.1.1
hmStatusPppPppPhasesEntry OBJECT-TYPE
    SYNTAX     HmStatusPppPppPhasesEntry
    MAX-ACCESS not-accessible
    STATUS     current
    DESCRIPTION
            ""
    INDEX {
            hmStatusPppPppPhasesEntryIfc
          }
    ::= { hmStatusPppPppPhasesTable 1 }

HmStatusPppPppPhasesEntry ::= SEQUENCE {
            hmStatusPppPppPhasesEntryIfc INTEGER,
            hmStatusPppPppPhasesEntryPhaseTo INTEGER,
            hmStatusPppPppPhasesEntryLcp INTEGER,
            hmStatusPppPppPhasesEntryIpcp INTEGER,
            hmStatusPppPppPhasesEntryCcp INTEGER,
            hmStatusPppPppPhasesEntryIpv6cp INTEGER
    }

-- {COLUMN} 1.3.6.1.4.1.248.32.18.1.6.1.1.1
hmStatusPppPppPhasesEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusPppPppPhasesEntry 1 }

-- {COLUMN} 1.3.6.1.4.1.248.32.18.1.6.1.1.2
hmStatusPppPppPhasesEntryPhaseTo OBJECT-TYPE
    SYNTAX     INTEGER {
                  eDead (1),
                  eEstablish (2),
                  eTerminate (3),
                  eAuthenticate (4),
                  eCallback (5),
                  eNetwork (6)
            }
    MAX-ACCESS read-only
    STATUS     current
    DESCRIPTION
            "-- empty --"
    ::= { hmStatusPppPppPhasesEntry 2 }

-- {COLUMN} 1.3.6.1.4.1.248.32.18.1.6.1.1.3
hmStatusPppPppPhasesEntryLcp OBJECT-TYPE
    SYNTAX     INTEGER {
                  eInitial (1),
                  eStartng (2),
                  eClosed (3),
                  eStopped (4),
                  eClosing (5),
                  eStoppng (6),
                  eReqsent (7),
                  eAckrcvd (8),
                  eAcksent (9),
                  eOpened (10)
            }
    MAX-ACCESS read-only
    STATUS     current
    DESCRIPTION
            "-- empty --"
    ::= { hmStatusPppPppPhasesEntry 3 }

-- {COLUMN} 1.3.6.1.4.1.248.32.18.1.6.1.1.4
hmStatusPppPppPhasesEntryIpcp OBJECT-TYPE
    SYNTAX     INTEGER {
                  eInitial (1),
                  eStartng (2),
                  eClosed (3),
                  eStopped (4),
                  eClosing (5),
                  eStoppng (6),
                  eReqsent (7),
                  eAckrcvd (8),
                  eAcksent (9),
                  eOpened (10)
            }
    MAX-ACCESS read-only
    STATUS     current
    DESCRIPTION
            "-- empty --"
    ::= { hmStatusPppPppPhasesEntry 4 }

-- {COLUMN} 1.3.6.1.4.1.248.32.18.1.6.1.1.6
hmStatusPppPppPhasesEntryCcp OBJECT-TYPE
    SYNTAX     INTEGER {
                  eInitial (1),
                  eStartng (2),
                  eClosed (3),
                  eStopped (4),
                  eClosing (5),
                  eStoppng (6),
                  eReqsent (7),
                  eAckrcvd (8),
                  eAcksent (9),
                  eOpened (10)
            }
    MAX-ACCESS read-only
    STATUS     current
    DESCRIPTION
            "-- empty --"
    ::= { hmStatusPppPppPhasesEntry 6 }

-- {COLUMN} 1.3.6.1.4.1.248.32.18.1.6.1.1.8
hmStatusPppPppPhasesEntryIpv6cp OBJECT-TYPE
    SYNTAX     INTEGER {
                  eInitial (1),
                  eStartng (2),
                  eClosed (3),
                  eStopped (4),
                  eClosing (5),
                  eStoppng (6),
                  eReqsent (7),
                  eAckrcvd (8),
                  eAcksent (9),
                  eOpened (10)
            }
    MAX-ACCESS read-only
    STATUS     current
    DESCRIPTION
            "-- empty --"
    ::= { hmStatusPppPppPhasesEntry 8 }

-- {NODE} 1.3.6.1.4.1.248.32.18.1.6.2
hmStatusPppLcp OBJECT IDENTIFIER ::= { hmStatusPpp 2 }

-- {SCALAR} 1.3.6.1.4.1.248.32.18.1.6.2.1
hmStatusPppLcpRxErrors OBJECT-TYPE
    SYNTAX     Counter32
    MAX-ACCESS read-only
    STATUS     current
    DESCRIPTION
            "-- empty --"
    ::= { hmStatusPppLcp 1 }

-- {SCALAR} 1.3.6.1.4.1.248.32.18.1.6.2.2
hmStatusPppLcpRxDiscarded OBJECT-TYPE
    SYNTAX     Counter32
    MAX-ACCESS read-only
    STATUS     current
    DESCRIPTION
            "-- empty --"
    ::= { hmStatusPppLcp 2 }

-- {SCALAR} 1.3.6.1.4.1.248.32.18.1.6.2.3
hmStatusPppLcpRxConfigRequest OBJECT-TYPE
    SYNTAX     Counter32
    MAX-ACCESS read-only
    STATUS     current
    DESCRIPTION
            "-- empty --"
    ::= { hmStatusPppLcp 3 }

-- {SCALAR} 1.3.6.1.4.1.248.32.18.1.6.2.4
hmStatusPppLcpRxConfigAck OBJECT-TYPE
    SYNTAX     Counter32
    MAX-ACCESS read-only
    STATUS     current
    DESCRIPTION
            "-- empty --"
    ::= { hmStatusPppLcp 4 }

-- {SCALAR} 1.3.6.1.4.1.248.32.18.1.6.2.5
hmStatusPppLcpRxConfigNak OBJECT-TYPE
    SYNTAX     Counter32
    MAX-ACCESS read-only
    STATUS     current
    DESCRIPTION
            "-- empty --"
    ::= { hmStatusPppLcp 5 }

-- {SCALAR} 1.3.6.1.4.1.248.32.18.1.6.2.6
hmStatusPppLcpRxConfigReject OBJECT-TYPE
    SYNTAX     Counter32
    MAX-ACCESS read-only
    STATUS     current
    DESCRIPTION
            "-- empty --"
    ::= { hmStatusPppLcp 6 }

-- {SCALAR} 1.3.6.1.4.1.248.32.18.1.6.2.7
hmStatusPppLcpRxTerminateRequest OBJECT-TYPE
    SYNTAX     Counter32
    MAX-ACCESS read-only
    STATUS     current
    DESCRIPTION
            "-- empty --"
    ::= { hmStatusPppLcp 7 }

-- {SCALAR} 1.3.6.1.4.1.248.32.18.1.6.2.8
hmStatusPppLcpRxTerminateAck OBJECT-TYPE
    SYNTAX     Counter32
    MAX-ACCESS read-only
    STATUS     current
    DESCRIPTION
            "-- empty --"
    ::= { hmStatusPppLcp 8 }

-- {SCALAR} 1.3.6.1.4.1.248.32.18.1.6.2.9
hmStatusPppLcpRxCodeReject OBJECT-TYPE
    SYNTAX     Counter32
    MAX-ACCESS read-only
    STATUS     current
    DESCRIPTION
            "-- empty --"
    ::= { hmStatusPppLcp 9 }

-- {SCALAR} 1.3.6.1.4.1.248.32.18.1.6.2.10
hmStatusPppLcpRxProtocolReject OBJECT-TYPE
    SYNTAX     Counter32
    MAX-ACCESS read-only
    STATUS     current
    DESCRIPTION
            "-- empty --"
    ::= { hmStatusPppLcp 10 }

-- {SCALAR} 1.3.6.1.4.1.248.32.18.1.6.2.11
hmStatusPppLcpRxEchoRequest OBJECT-TYPE
    SYNTAX     Counter32
    MAX-ACCESS read-only
    STATUS     current
    DESCRIPTION
            "-- empty --"
    ::= { hmStatusPppLcp 11 }

-- {SCALAR} 1.3.6.1.4.1.248.32.18.1.6.2.12
hmStatusPppLcpRxEchoReply OBJECT-TYPE
    SYNTAX     Counter32
    MAX-ACCESS read-only
    STATUS     current
    DESCRIPTION
            "-- empty --"
    ::= { hmStatusPppLcp 12 }

-- {SCALAR} 1.3.6.1.4.1.248.32.18.1.6.2.13
hmStatusPppLcpRxDiscardRequest OBJECT-TYPE
    SYNTAX     Counter32
    MAX-ACCESS read-only
    STATUS     current
    DESCRIPTION
            "-- empty --"
    ::= { hmStatusPppLcp 13 }

-- {SCALAR} 1.3.6.1.4.1.248.32.18.1.6.2.14
hmStatusPppLcpTxConfigRequest OBJECT-TYPE
    SYNTAX     Counter32
    MAX-ACCESS read-only
    STATUS     current
    DESCRIPTION
            "-- empty --"
    ::= { hmStatusPppLcp 14 }

-- {SCALAR} 1.3.6.1.4.1.248.32.18.1.6.2.15
hmStatusPppLcpTxConfigAck OBJECT-TYPE
    SYNTAX     Counter32
    MAX-ACCESS read-only
    STATUS     current
    DESCRIPTION
            "-- empty --"
    ::= { hmStatusPppLcp 15 }

-- {SCALAR} 1.3.6.1.4.1.248.32.18.1.6.2.16
hmStatusPppLcpTxConfigNak OBJECT-TYPE
    SYNTAX     Counter32
    MAX-ACCESS read-only
    STATUS     current
    DESCRIPTION
            "-- empty --"
    ::= { hmStatusPppLcp 16 }

-- {SCALAR} 1.3.6.1.4.1.248.32.18.1.6.2.17
hmStatusPppLcpTxConfigReject OBJECT-TYPE
    SYNTAX     Counter32
    MAX-ACCESS read-only
    STATUS     current
    DESCRIPTION
            "-- empty --"
    ::= { hmStatusPppLcp 17 }

-- {SCALAR} 1.3.6.1.4.1.248.32.18.1.6.2.18
hmStatusPppLcpTxTerminateRequest OBJECT-TYPE
    SYNTAX     Counter32
    MAX-ACCESS read-only
    STATUS     current
    DESCRIPTION
            "-- empty --"
    ::= { hmStatusPppLcp 18 }

-- {SCALAR} 1.3.6.1.4.1.248.32.18.1.6.2.19
hmStatusPppLcpTxTerminateAck OBJECT-TYPE
    SYNTAX     Counter32
    MAX-ACCESS read-only
    STATUS     current
    DESCRIPTION
            "-- empty --"
    ::= { hmStatusPppLcp 19 }

-- {SCALAR} 1.3.6.1.4.1.248.32.18.1.6.2.20
hmStatusPppLcpTxCodeReject OBJECT-TYPE
    SYNTAX     Counter32
    MAX-ACCESS read-only
    STATUS     current
    DESCRIPTION
            "-- empty --"
    ::= { hmStatusPppLcp 20 }

-- {SCALAR} 1.3.6.1.4.1.248.32.18.1.6.2.21
hmStatusPppLcpTxProtocolReject OBJECT-TYPE
    SYNTAX     Counter32
    MAX-ACCESS read-only
    STATUS     current
    DESCRIPTION
            "-- empty --"
    ::= { hmStatusPppLcp 21 }

-- {SCALAR} 1.3.6.1.4.1.248.32.18.1.6.2.22
hmStatusPppLcpTxEchoRequest OBJECT-TYPE
    SYNTAX     Counter32
    MAX-ACCESS read-only
    STATUS     current
    DESCRIPTION
            "-- empty --"
    ::= { hmStatusPppLcp 22 }

-- {SCALAR} 1.3.6.1.4.1.248.32.18.1.6.2.23
hmStatusPppLcpTxEchoReply OBJECT-TYPE
    SYNTAX     Counter32
    MAX-ACCESS read-only
    STATUS     current
    DESCRIPTION
            "-- empty --"
    ::= { hmStatusPppLcp 23 }

-- {SCALAR} 1.3.6.1.4.1.248.32.18.1.6.2.24
hmStatusPppLcpTxDiscardRequest OBJECT-TYPE
    SYNTAX     Counter32
    MAX-ACCESS read-only
    STATUS     current
    DESCRIPTION
            "-- empty --"
    ::= { hmStatusPppLcp 24 }

-- {SCALAR} 1.3.6.1.4.1.248.32.18.1.6.2.25
hmStatusPppLcpDeleteValues OBJECT-TYPE
    SYNTAX     DisplayString
    MAX-ACCESS read-write
    STATUS     current
    DESCRIPTION
            "-- empty --"
    ::= { hmStatusPppLcp 25 }

-- {NODE} 1.3.6.1.4.1.248.32.18.1.6.3
hmStatusPppPap OBJECT IDENTIFIER ::= { hmStatusPpp 3 }

-- {SCALAR} 1.3.6.1.4.1.248.32.18.1.6.3.1
hmStatusPppPapRxDiscarded OBJECT-TYPE
    SYNTAX     Counter32
    MAX-ACCESS read-only
    STATUS     current
    DESCRIPTION
            "-- empty --"
    ::= { hmStatusPppPap 1 }

-- {SCALAR} 1.3.6.1.4.1.248.32.18.1.6.3.2
hmStatusPppPapRxRequest OBJECT-TYPE
    SYNTAX     Counter32
    MAX-ACCESS read-only
    STATUS     current
    DESCRIPTION
            "-- empty --"
    ::= { hmStatusPppPap 2 }

-- {SCALAR} 1.3.6.1.4.1.248.32.18.1.6.3.3
hmStatusPppPapRxSuccess OBJECT-TYPE
    SYNTAX     Counter32
    MAX-ACCESS read-only
    STATUS     current
    DESCRIPTION
            "-- empty --"
    ::= { hmStatusPppPap 3 }

-- {SCALAR} 1.3.6.1.4.1.248.32.18.1.6.3.4
hmStatusPppPapRxFailure OBJECT-TYPE
    SYNTAX     Counter32
    MAX-ACCESS read-only
    STATUS     current
    DESCRIPTION
            "-- empty --"
    ::= { hmStatusPppPap 4 }

-- {SCALAR} 1.3.6.1.4.1.248.32.18.1.6.3.5
hmStatusPppPapTxRetry OBJECT-TYPE
    SYNTAX     Counter32
    MAX-ACCESS read-only
    STATUS     current
    DESCRIPTION
            "-- empty --"
    ::= { hmStatusPppPap 5 }

-- {SCALAR} 1.3.6.1.4.1.248.32.18.1.6.3.6
hmStatusPppPapTxRequest OBJECT-TYPE
    SYNTAX     Counter32
    MAX-ACCESS read-only
    STATUS     current
    DESCRIPTION
            "-- empty --"
    ::= { hmStatusPppPap 6 }

-- {SCALAR} 1.3.6.1.4.1.248.32.18.1.6.3.7
hmStatusPppPapTxSuccess OBJECT-TYPE
    SYNTAX     Counter32
    MAX-ACCESS read-only
    STATUS     current
    DESCRIPTION
            "-- empty --"
    ::= { hmStatusPppPap 7 }

-- {SCALAR} 1.3.6.1.4.1.248.32.18.1.6.3.8
hmStatusPppPapTxFailure OBJECT-TYPE
    SYNTAX     Counter32
    MAX-ACCESS read-only
    STATUS     current
    DESCRIPTION
            "-- empty --"
    ::= { hmStatusPppPap 8 }

-- {SCALAR} 1.3.6.1.4.1.248.32.18.1.6.3.9
hmStatusPppPapDeleteValues OBJECT-TYPE
    SYNTAX     DisplayString
    MAX-ACCESS read-write
    STATUS     current
    DESCRIPTION
            "-- empty --"
    ::= { hmStatusPppPap 9 }

-- {NODE} 1.3.6.1.4.1.248.32.18.1.6.4
hmStatusPppChap OBJECT IDENTIFIER ::= { hmStatusPpp 4 }

-- {SCALAR} 1.3.6.1.4.1.248.32.18.1.6.4.1
hmStatusPppChapRxDiscarded OBJECT-TYPE
    SYNTAX     Counter32
    MAX-ACCESS read-only
    STATUS     current
    DESCRIPTION
            "-- empty --"
    ::= { hmStatusPppChap 1 }

-- {SCALAR} 1.3.6.1.4.1.248.32.18.1.6.4.2
hmStatusPppChapRxChallenge OBJECT-TYPE
    SYNTAX     Counter32
    MAX-ACCESS read-only
    STATUS     current
    DESCRIPTION
            "-- empty --"
    ::= { hmStatusPppChap 2 }

-- {SCALAR} 1.3.6.1.4.1.248.32.18.1.6.4.3
hmStatusPppChapRxResponse OBJECT-TYPE
    SYNTAX     Counter32
    MAX-ACCESS read-only
    STATUS     current
    DESCRIPTION
            "-- empty --"
    ::= { hmStatusPppChap 3 }

-- {SCALAR} 1.3.6.1.4.1.248.32.18.1.6.4.4
hmStatusPppChapRxSuccess OBJECT-TYPE
    SYNTAX     Counter32
    MAX-ACCESS read-only
    STATUS     current
    DESCRIPTION
            "-- empty --"
    ::= { hmStatusPppChap 4 }

-- {SCALAR} 1.3.6.1.4.1.248.32.18.1.6.4.5
hmStatusPppChapRxFailure OBJECT-TYPE
    SYNTAX     Counter32
    MAX-ACCESS read-only
    STATUS     current
    DESCRIPTION
            "-- empty --"
    ::= { hmStatusPppChap 5 }

-- {SCALAR} 1.3.6.1.4.1.248.32.18.1.6.4.6
hmStatusPppChapTxRetry OBJECT-TYPE
    SYNTAX     Counter32
    MAX-ACCESS read-only
    STATUS     current
    DESCRIPTION
            "-- empty --"
    ::= { hmStatusPppChap 6 }

-- {SCALAR} 1.3.6.1.4.1.248.32.18.1.6.4.7
hmStatusPppChapTxChallenge OBJECT-TYPE
    SYNTAX     Counter32
    MAX-ACCESS read-only
    STATUS     current
    DESCRIPTION
            "-- empty --"
    ::= { hmStatusPppChap 7 }

-- {SCALAR} 1.3.6.1.4.1.248.32.18.1.6.4.8
hmStatusPppChapTxResponse OBJECT-TYPE
    SYNTAX     Counter32
    MAX-ACCESS read-only
    STATUS     current
    DESCRIPTION
            "-- empty --"
    ::= { hmStatusPppChap 8 }

-- {SCALAR} 1.3.6.1.4.1.248.32.18.1.6.4.9
hmStatusPppChapTxSuccess OBJECT-TYPE
    SYNTAX     Counter32
    MAX-ACCESS read-only
    STATUS     current
    DESCRIPTION
            "-- empty --"
    ::= { hmStatusPppChap 9 }

-- {SCALAR} 1.3.6.1.4.1.248.32.18.1.6.4.10
hmStatusPppChapTxFailure OBJECT-TYPE
    SYNTAX     Counter32
    MAX-ACCESS read-only
    STATUS     current
    DESCRIPTION
            "-- empty --"
    ::= { hmStatusPppChap 10 }

-- {SCALAR} 1.3.6.1.4.1.248.32.18.1.6.4.11
hmStatusPppChapDeleteValues OBJECT-TYPE
    SYNTAX     DisplayString
    MAX-ACCESS read-write
    STATUS     current
    DESCRIPTION
            "-- empty --"
    ::= { hmStatusPppChap 11 }

-- {NODE} 1.3.6.1.4.1.248.32.18.1.6.6
hmStatusPppIpcp OBJECT IDENTIFIER ::= { hmStatusPpp 6 }

-- {SCALAR} 1.3.6.1.4.1.248.32.18.1.6.6.1
hmStatusPppIpcpRxDiscarded OBJECT-TYPE
    SYNTAX     Counter32
    MAX-ACCESS read-only
    STATUS     current
    DESCRIPTION
            "-- empty --"
    ::= { hmStatusPppIpcp 1 }

-- {SCALAR} 1.3.6.1.4.1.248.32.18.1.6.6.2
hmStatusPppIpcpRxConfigRequest OBJECT-TYPE
    SYNTAX     Counter32
    MAX-ACCESS read-only
    STATUS     current
    DESCRIPTION
            "-- empty --"
    ::= { hmStatusPppIpcp 2 }

-- {SCALAR} 1.3.6.1.4.1.248.32.18.1.6.6.3
hmStatusPppIpcpRxConfigAck OBJECT-TYPE
    SYNTAX     Counter32
    MAX-ACCESS read-only
    STATUS     current
    DESCRIPTION
            "-- empty --"
    ::= { hmStatusPppIpcp 3 }

-- {SCALAR} 1.3.6.1.4.1.248.32.18.1.6.6.4
hmStatusPppIpcpRxConfigNak OBJECT-TYPE
    SYNTAX     Counter32
    MAX-ACCESS read-only
    STATUS     current
    DESCRIPTION
            "-- empty --"
    ::= { hmStatusPppIpcp 4 }

-- {SCALAR} 1.3.6.1.4.1.248.32.18.1.6.6.5
hmStatusPppIpcpRxConfigReject OBJECT-TYPE
    SYNTAX     Counter32
    MAX-ACCESS read-only
    STATUS     current
    DESCRIPTION
            "-- empty --"
    ::= { hmStatusPppIpcp 5 }

-- {SCALAR} 1.3.6.1.4.1.248.32.18.1.6.6.6
hmStatusPppIpcpRxTerminateRequest OBJECT-TYPE
    SYNTAX     Counter32
    MAX-ACCESS read-only
    STATUS     current
    DESCRIPTION
            "-- empty --"
    ::= { hmStatusPppIpcp 6 }

-- {SCALAR} 1.3.6.1.4.1.248.32.18.1.6.6.7
hmStatusPppIpcpRxTerminateAck OBJECT-TYPE
    SYNTAX     Counter32
    MAX-ACCESS read-only
    STATUS     current
    DESCRIPTION
            "-- empty --"
    ::= { hmStatusPppIpcp 7 }

-- {SCALAR} 1.3.6.1.4.1.248.32.18.1.6.6.8
hmStatusPppIpcpRxCodeReject OBJECT-TYPE
    SYNTAX     Counter32
    MAX-ACCESS read-only
    STATUS     current
    DESCRIPTION
            "-- empty --"
    ::= { hmStatusPppIpcp 8 }

-- {SCALAR} 1.3.6.1.4.1.248.32.18.1.6.6.9
hmStatusPppIpcpTxConfigRequest OBJECT-TYPE
    SYNTAX     Counter32
    MAX-ACCESS read-only
    STATUS     current
    DESCRIPTION
            "-- empty --"
    ::= { hmStatusPppIpcp 9 }

-- {SCALAR} 1.3.6.1.4.1.248.32.18.1.6.6.10
hmStatusPppIpcpTxConfigAck OBJECT-TYPE
    SYNTAX     Counter32
    MAX-ACCESS read-only
    STATUS     current
    DESCRIPTION
            "-- empty --"
    ::= { hmStatusPppIpcp 10 }

-- {SCALAR} 1.3.6.1.4.1.248.32.18.1.6.6.11
hmStatusPppIpcpTxConfigNak OBJECT-TYPE
    SYNTAX     Counter32
    MAX-ACCESS read-only
    STATUS     current
    DESCRIPTION
            "-- empty --"
    ::= { hmStatusPppIpcp 11 }

-- {SCALAR} 1.3.6.1.4.1.248.32.18.1.6.6.12
hmStatusPppIpcpTxConfigReject OBJECT-TYPE
    SYNTAX     Counter32
    MAX-ACCESS read-only
    STATUS     current
    DESCRIPTION
            "-- empty --"
    ::= { hmStatusPppIpcp 12 }

-- {SCALAR} 1.3.6.1.4.1.248.32.18.1.6.6.13
hmStatusPppIpcpTxTerminateRequest OBJECT-TYPE
    SYNTAX     Counter32
    MAX-ACCESS read-only
    STATUS     current
    DESCRIPTION
            "-- empty --"
    ::= { hmStatusPppIpcp 13 }

-- {SCALAR} 1.3.6.1.4.1.248.32.18.1.6.6.14
hmStatusPppIpcpTxTerminateAck OBJECT-TYPE
    SYNTAX     Counter32
    MAX-ACCESS read-only
    STATUS     current
    DESCRIPTION
            "-- empty --"
    ::= { hmStatusPppIpcp 14 }

-- {SCALAR} 1.3.6.1.4.1.248.32.18.1.6.6.15
hmStatusPppIpcpTxCodeReject OBJECT-TYPE
    SYNTAX     Counter32
    MAX-ACCESS read-only
    STATUS     current
    DESCRIPTION
            "-- empty --"
    ::= { hmStatusPppIpcp 15 }

-- {SCALAR} 1.3.6.1.4.1.248.32.18.1.6.6.16
hmStatusPppIpcpDeleteValues OBJECT-TYPE
    SYNTAX     DisplayString
    MAX-ACCESS read-write
    STATUS     current
    DESCRIPTION
            "-- empty --"
    ::= { hmStatusPppIpcp 16 }

-- {NODE} 1.3.6.1.4.1.248.32.18.1.6.8
hmStatusPppRxOptions OBJECT IDENTIFIER ::= { hmStatusPpp 8 }

-- {TABLE} 1.3.6.1.4.1.248.32.18.1.6.8.1
hmStatusPppRxOptionsLcpTable OBJECT-TYPE
    SYNTAX     SEQUENCE OF HmStatusPppRxOptionsLcpEntry
    MAX-ACCESS not-accessible
    STATUS     current
    DESCRIPTION
            "-- empty --"
    ::= { hmStatusPppRxOptions 1 }

-- {ROW} 1.3.6.1.4.1.248.32.18.1.6.8.1.1
hmStatusPppRxOptionsLcpEntry OBJECT-TYPE
    SYNTAX     HmStatusPppRxOptionsLcpEntry
    MAX-ACCESS not-accessible
    STATUS     current
    DESCRIPTION
            ""
    INDEX {
            hmStatusPppRxOptionsLcpEntryIfc
          }
    ::= { hmStatusPppRxOptionsLcpTable 1 }

HmStatusPppRxOptionsLcpEntry ::= SEQUENCE {
            hmStatusPppRxOptionsLcpEntryIfc INTEGER,
            hmStatusPppRxOptionsLcpEntryMru Integer32,
            hmStatusPppRxOptionsLcpEntryAuthentRequest INTEGER,
            hmStatusPppRxOptionsLcpEntryMagicNum DisplayString
    }

-- {COLUMN} 1.3.6.1.4.1.248.32.18.1.6.8.1.1.1
hmStatusPppRxOptionsLcpEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusPppRxOptionsLcpEntry 1 }

-- {COLUMN} 1.3.6.1.4.1.248.32.18.1.6.8.1.1.2
hmStatusPppRxOptionsLcpEntryMru OBJECT-TYPE
    SYNTAX     Integer32 (0..65535)
    MAX-ACCESS read-only
    STATUS     current
    DESCRIPTION
            "-- empty --"
    ::= { hmStatusPppRxOptionsLcpEntry 2 }

-- {COLUMN} 1.3.6.1.4.1.248.32.18.1.6.8.1.1.4
hmStatusPppRxOptionsLcpEntryAuthentRequest OBJECT-TYPE
    SYNTAX     INTEGER {
                  eNone (0),
                  ePap (4),
                  eChap (8),
                  eMsChap (16),
                  eMsChapv2 (32)
            }
    MAX-ACCESS read-only
    STATUS     current
    DESCRIPTION
            "-- empty --"
    ::= { hmStatusPppRxOptionsLcpEntry 4 }

-- {COLUMN} 1.3.6.1.4.1.248.32.18.1.6.8.1.1.6
hmStatusPppRxOptionsLcpEntryMagicNum OBJECT-TYPE
    SYNTAX     DisplayString (SIZE(0..8))
    MAX-ACCESS read-only
    STATUS     current
    DESCRIPTION
            "-- empty --"
    ::= { hmStatusPppRxOptionsLcpEntry 6 }

-- {TABLE} 1.3.6.1.4.1.248.32.18.1.6.8.3
hmStatusPppRxOptionsIpcpTable OBJECT-TYPE
    SYNTAX     SEQUENCE OF HmStatusPppRxOptionsIpcpEntry
    MAX-ACCESS not-accessible
    STATUS     current
    DESCRIPTION
            "-- empty --"
    ::= { hmStatusPppRxOptions 3 }

-- {ROW} 1.3.6.1.4.1.248.32.18.1.6.8.3.1
hmStatusPppRxOptionsIpcpEntry OBJECT-TYPE
    SYNTAX     HmStatusPppRxOptionsIpcpEntry
    MAX-ACCESS not-accessible
    STATUS     current
    DESCRIPTION
            ""
    INDEX {
            hmStatusPppRxOptionsIpcpEntryIfc
          }
    ::= { hmStatusPppRxOptionsIpcpTable 1 }

HmStatusPppRxOptionsIpcpEntry ::= SEQUENCE {
            hmStatusPppRxOptionsIpcpEntryIfc INTEGER,
            hmStatusPppRxOptionsIpcpEntryIpAddress IpAddress,
            hmStatusPppRxOptionsIpcpEntryDnsDefault IpAddress,
            hmStatusPppRxOptionsIpcpEntryNbnsDefault IpAddress,
            hmStatusPppRxOptionsIpcpEntryDnsBackup IpAddress,
            hmStatusPppRxOptionsIpcpEntryNbnsBackup IpAddress
    }

-- {COLUMN} 1.3.6.1.4.1.248.32.18.1.6.8.3.1.1
hmStatusPppRxOptionsIpcpEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusPppRxOptionsIpcpEntry 1 }

-- {COLUMN} 1.3.6.1.4.1.248.32.18.1.6.8.3.1.2
hmStatusPppRxOptionsIpcpEntryIpAddress OBJECT-TYPE
    SYNTAX     IpAddress
    MAX-ACCESS read-only
    STATUS     current
    DESCRIPTION
            "-- empty --"
    ::= { hmStatusPppRxOptionsIpcpEntry 2 }

-- {COLUMN} 1.3.6.1.4.1.248.32.18.1.6.8.3.1.3
hmStatusPppRxOptionsIpcpEntryDnsDefault OBJECT-TYPE
    SYNTAX     IpAddress
    MAX-ACCESS read-only
    STATUS     current
    DESCRIPTION
            "-- empty --"
    ::= { hmStatusPppRxOptionsIpcpEntry 3 }

-- {COLUMN} 1.3.6.1.4.1.248.32.18.1.6.8.3.1.4
hmStatusPppRxOptionsIpcpEntryNbnsDefault OBJECT-TYPE
    SYNTAX     IpAddress
    MAX-ACCESS read-only
    STATUS     current
    DESCRIPTION
            "-- empty --"
    ::= { hmStatusPppRxOptionsIpcpEntry 4 }

-- {COLUMN} 1.3.6.1.4.1.248.32.18.1.6.8.3.1.5
hmStatusPppRxOptionsIpcpEntryDnsBackup OBJECT-TYPE
    SYNTAX     IpAddress
    MAX-ACCESS read-only
    STATUS     current
    DESCRIPTION
            "-- empty --"
    ::= { hmStatusPppRxOptionsIpcpEntry 5 }

-- {COLUMN} 1.3.6.1.4.1.248.32.18.1.6.8.3.1.6
hmStatusPppRxOptionsIpcpEntryNbnsBackup OBJECT-TYPE
    SYNTAX     IpAddress
    MAX-ACCESS read-only
    STATUS     current
    DESCRIPTION
            "-- empty --"
    ::= { hmStatusPppRxOptionsIpcpEntry 6 }

-- {TABLE} 1.3.6.1.4.1.248.32.18.1.6.8.4
hmStatusPppRxOptionsIpv6cpTable OBJECT-TYPE
    SYNTAX     SEQUENCE OF HmStatusPppRxOptionsIpv6cpEntry
    MAX-ACCESS not-accessible
    STATUS     current
    DESCRIPTION
            "-- empty --"
    ::= { hmStatusPppRxOptions 4 }

-- {ROW} 1.3.6.1.4.1.248.32.18.1.6.8.4.1
hmStatusPppRxOptionsIpv6cpEntry OBJECT-TYPE
    SYNTAX     HmStatusPppRxOptionsIpv6cpEntry
    MAX-ACCESS not-accessible
    STATUS     current
    DESCRIPTION
            ""
    INDEX {
            hmStatusPppRxOptionsIpv6cpEntryIfc
          }
    ::= { hmStatusPppRxOptionsIpv6cpTable 1 }

HmStatusPppRxOptionsIpv6cpEntry ::= SEQUENCE {
            hmStatusPppRxOptionsIpv6cpEntryIfc INTEGER,
            hmStatusPppRxOptionsIpv6cpEntryIdentifier Integer32
    }

-- {COLUMN} 1.3.6.1.4.1.248.32.18.1.6.8.4.1.1
hmStatusPppRxOptionsIpv6cpEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusPppRxOptionsIpv6cpEntry 1 }

-- {COLUMN} 1.3.6.1.4.1.248.32.18.1.6.8.4.1.2
hmStatusPppRxOptionsIpv6cpEntryIdentifier OBJECT-TYPE
    SYNTAX     Integer32 (0..2147483647)
    MAX-ACCESS read-only
    STATUS     current
    DESCRIPTION
            "-- empty --"
    ::= { hmStatusPppRxOptionsIpv6cpEntry 2 }

-- {NODE} 1.3.6.1.4.1.248.32.18.1.6.9
hmStatusPppTxOptions OBJECT IDENTIFIER ::= { hmStatusPpp 9 }

-- {TABLE} 1.3.6.1.4.1.248.32.18.1.6.9.1
hmStatusPppTxOptionsLcpTable OBJECT-TYPE
    SYNTAX     SEQUENCE OF HmStatusPppTxOptionsLcpEntry
    MAX-ACCESS not-accessible
    STATUS     current
    DESCRIPTION
            "-- empty --"
    ::= { hmStatusPppTxOptions 1 }

-- {ROW} 1.3.6.1.4.1.248.32.18.1.6.9.1.1
hmStatusPppTxOptionsLcpEntry OBJECT-TYPE
    SYNTAX     HmStatusPppTxOptionsLcpEntry
    MAX-ACCESS not-accessible
    STATUS     current
    DESCRIPTION
            ""
    INDEX {
            hmStatusPppTxOptionsLcpEntryIfc
          }
    ::= { hmStatusPppTxOptionsLcpTable 1 }

HmStatusPppTxOptionsLcpEntry ::= SEQUENCE {
            hmStatusPppTxOptionsLcpEntryIfc INTEGER,
            hmStatusPppTxOptionsLcpEntryMru Integer32,
            hmStatusPppTxOptionsLcpEntryAuthentRequest INTEGER,
            hmStatusPppTxOptionsLcpEntryMagicNum DisplayString
    }

-- {COLUMN} 1.3.6.1.4.1.248.32.18.1.6.9.1.1.1
hmStatusPppTxOptionsLcpEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusPppTxOptionsLcpEntry 1 }

-- {COLUMN} 1.3.6.1.4.1.248.32.18.1.6.9.1.1.2
hmStatusPppTxOptionsLcpEntryMru OBJECT-TYPE
    SYNTAX     Integer32 (0..65535)
    MAX-ACCESS read-only
    STATUS     current
    DESCRIPTION
            "-- empty --"
    ::= { hmStatusPppTxOptionsLcpEntry 2 }

-- {COLUMN} 1.3.6.1.4.1.248.32.18.1.6.9.1.1.4
hmStatusPppTxOptionsLcpEntryAuthentRequest OBJECT-TYPE
    SYNTAX     INTEGER {
                  eNone (0),
                  ePap (4),
                  eChap (8),
                  eMsChap (16),
                  eMsChapv2 (32)
            }
    MAX-ACCESS read-only
    STATUS     current
    DESCRIPTION
            "-- empty --"
    ::= { hmStatusPppTxOptionsLcpEntry 4 }

-- {COLUMN} 1.3.6.1.4.1.248.32.18.1.6.9.1.1.6
hmStatusPppTxOptionsLcpEntryMagicNum OBJECT-TYPE
    SYNTAX     DisplayString (SIZE(0..8))
    MAX-ACCESS read-only
    STATUS     current
    DESCRIPTION
            "-- empty --"
    ::= { hmStatusPppTxOptionsLcpEntry 6 }

-- {TABLE} 1.3.6.1.4.1.248.32.18.1.6.9.3
hmStatusPppTxOptionsIpcpTable OBJECT-TYPE
    SYNTAX     SEQUENCE OF HmStatusPppTxOptionsIpcpEntry
    MAX-ACCESS not-accessible
    STATUS     current
    DESCRIPTION
            "-- empty --"
    ::= { hmStatusPppTxOptions 3 }

-- {ROW} 1.3.6.1.4.1.248.32.18.1.6.9.3.1
hmStatusPppTxOptionsIpcpEntry OBJECT-TYPE
    SYNTAX     HmStatusPppTxOptionsIpcpEntry
    MAX-ACCESS not-accessible
    STATUS     current
    DESCRIPTION
            ""
    INDEX {
            hmStatusPppTxOptionsIpcpEntryIfc
          }
    ::= { hmStatusPppTxOptionsIpcpTable 1 }

HmStatusPppTxOptionsIpcpEntry ::= SEQUENCE {
            hmStatusPppTxOptionsIpcpEntryIfc INTEGER,
            hmStatusPppTxOptionsIpcpEntryIpAddress IpAddress,
            hmStatusPppTxOptionsIpcpEntryDnsDefault IpAddress,
            hmStatusPppTxOptionsIpcpEntryNbnsDefault IpAddress,
            hmStatusPppTxOptionsIpcpEntryDnsBackup IpAddress,
            hmStatusPppTxOptionsIpcpEntryNbnsBackup IpAddress
    }

-- {COLUMN} 1.3.6.1.4.1.248.32.18.1.6.9.3.1.1
hmStatusPppTxOptionsIpcpEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusPppTxOptionsIpcpEntry 1 }

-- {COLUMN} 1.3.6.1.4.1.248.32.18.1.6.9.3.1.2
hmStatusPppTxOptionsIpcpEntryIpAddress OBJECT-TYPE
    SYNTAX     IpAddress
    MAX-ACCESS read-only
    STATUS     current
    DESCRIPTION
            "-- empty --"
    ::= { hmStatusPppTxOptionsIpcpEntry 2 }

-- {COLUMN} 1.3.6.1.4.1.248.32.18.1.6.9.3.1.3
hmStatusPppTxOptionsIpcpEntryDnsDefault OBJECT-TYPE
    SYNTAX     IpAddress
    MAX-ACCESS read-only
    STATUS     current
    DESCRIPTION
            "-- empty --"
    ::= { hmStatusPppTxOptionsIpcpEntry 3 }

-- {COLUMN} 1.3.6.1.4.1.248.32.18.1.6.9.3.1.4
hmStatusPppTxOptionsIpcpEntryNbnsDefault OBJECT-TYPE
    SYNTAX     IpAddress
    MAX-ACCESS read-only
    STATUS     current
    DESCRIPTION
            "-- empty --"
    ::= { hmStatusPppTxOptionsIpcpEntry 4 }

-- {COLUMN} 1.3.6.1.4.1.248.32.18.1.6.9.3.1.5
hmStatusPppTxOptionsIpcpEntryDnsBackup OBJECT-TYPE
    SYNTAX     IpAddress
    MAX-ACCESS read-only
    STATUS     current
    DESCRIPTION
            "-- empty --"
    ::= { hmStatusPppTxOptionsIpcpEntry 5 }

-- {COLUMN} 1.3.6.1.4.1.248.32.18.1.6.9.3.1.6
hmStatusPppTxOptionsIpcpEntryNbnsBackup OBJECT-TYPE
    SYNTAX     IpAddress
    MAX-ACCESS read-only
    STATUS     current
    DESCRIPTION
            "-- empty --"
    ::= { hmStatusPppTxOptionsIpcpEntry 6 }

-- {TABLE} 1.3.6.1.4.1.248.32.18.1.6.9.4
hmStatusPppTxOptionsIpv6cpTable OBJECT-TYPE
    SYNTAX     SEQUENCE OF HmStatusPppTxOptionsIpv6cpEntry
    MAX-ACCESS not-accessible
    STATUS     current
    DESCRIPTION
            "-- empty --"
    ::= { hmStatusPppTxOptions 4 }

-- {ROW} 1.3.6.1.4.1.248.32.18.1.6.9.4.1
hmStatusPppTxOptionsIpv6cpEntry OBJECT-TYPE
    SYNTAX     HmStatusPppTxOptionsIpv6cpEntry
    MAX-ACCESS not-accessible
    STATUS     current
    DESCRIPTION
            ""
    INDEX {
            hmStatusPppTxOptionsIpv6cpEntryIfc
          }
    ::= { hmStatusPppTxOptionsIpv6cpTable 1 }

HmStatusPppTxOptionsIpv6cpEntry ::= SEQUENCE {
            hmStatusPppTxOptionsIpv6cpEntryIfc INTEGER,
            hmStatusPppTxOptionsIpv6cpEntryIdentifier Integer32
    }

-- {COLUMN} 1.3.6.1.4.1.248.32.18.1.6.9.4.1.1
hmStatusPppTxOptionsIpv6cpEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusPppTxOptionsIpv6cpEntry 1 }

-- {COLUMN} 1.3.6.1.4.1.248.32.18.1.6.9.4.1.2
hmStatusPppTxOptionsIpv6cpEntryIdentifier OBJECT-TYPE
    SYNTAX     Integer32 (0..2147483647)
    MAX-ACCESS read-only
    STATUS     current
    DESCRIPTION
            "-- empty --"
    ::= { hmStatusPppTxOptionsIpv6cpEntry 2 }

-- {NODE} 1.3.6.1.4.1.248.32.18.1.6.10
hmStatusPppCcp OBJECT IDENTIFIER ::= { hmStatusPpp 10 }

-- {SCALAR} 1.3.6.1.4.1.248.32.18.1.6.10.1
hmStatusPppCcpRxDiscarded OBJECT-TYPE
    SYNTAX     Counter32
    MAX-ACCESS read-only
    STATUS     current
    DESCRIPTION
            "-- empty --"
    ::= { hmStatusPppCcp 1 }

-- {SCALAR} 1.3.6.1.4.1.248.32.18.1.6.10.2
hmStatusPppCcpRxConfigRequest OBJECT-TYPE
    SYNTAX     Counter32
    MAX-ACCESS read-only
    STATUS     current
    DESCRIPTION
            "-- empty --"
    ::= { hmStatusPppCcp 2 }

-- {SCALAR} 1.3.6.1.4.1.248.32.18.1.6.10.3
hmStatusPppCcpRxConfigAck OBJECT-TYPE
    SYNTAX     Counter32
    MAX-ACCESS read-only
    STATUS     current
    DESCRIPTION
            "-- empty --"
    ::= { hmStatusPppCcp 3 }

-- {SCALAR} 1.3.6.1.4.1.248.32.18.1.6.10.4
hmStatusPppCcpRxConfigNak OBJECT-TYPE
    SYNTAX     Counter32
    MAX-ACCESS read-only
    STATUS     current
    DESCRIPTION
            "-- empty --"
    ::= { hmStatusPppCcp 4 }

-- {SCALAR} 1.3.6.1.4.1.248.32.18.1.6.10.5
hmStatusPppCcpRxConfigReject OBJECT-TYPE
    SYNTAX     Counter32
    MAX-ACCESS read-only
    STATUS     current
    DESCRIPTION
            "-- empty --"
    ::= { hmStatusPppCcp 5 }

-- {SCALAR} 1.3.6.1.4.1.248.32.18.1.6.10.6
hmStatusPppCcpRxTerminateRequest OBJECT-TYPE
    SYNTAX     Counter32
    MAX-ACCESS read-only
    STATUS     current
    DESCRIPTION
            "-- empty --"
    ::= { hmStatusPppCcp 6 }

-- {SCALAR} 1.3.6.1.4.1.248.32.18.1.6.10.7
hmStatusPppCcpRxTerminateAck OBJECT-TYPE
    SYNTAX     Counter32
    MAX-ACCESS read-only
    STATUS     current
    DESCRIPTION
            "-- empty --"
    ::= { hmStatusPppCcp 7 }

-- {SCALAR} 1.3.6.1.4.1.248.32.18.1.6.10.8
hmStatusPppCcpRxCodeReject OBJECT-TYPE
    SYNTAX     Counter32
    MAX-ACCESS read-only
    STATUS     current
    DESCRIPTION
            "-- empty --"
    ::= { hmStatusPppCcp 8 }

-- {SCALAR} 1.3.6.1.4.1.248.32.18.1.6.10.9
hmStatusPppCcpRxResetRequest OBJECT-TYPE
    SYNTAX     Counter32
    MAX-ACCESS read-only
    STATUS     current
    DESCRIPTION
            "-- empty --"
    ::= { hmStatusPppCcp 9 }

-- {SCALAR} 1.3.6.1.4.1.248.32.18.1.6.10.10
hmStatusPppCcpRxResetAck OBJECT-TYPE
    SYNTAX     Counter32
    MAX-ACCESS read-only
    STATUS     current
    DESCRIPTION
            "-- empty --"
    ::= { hmStatusPppCcp 10 }

-- {SCALAR} 1.3.6.1.4.1.248.32.18.1.6.10.11
hmStatusPppCcpTxConfigRequest OBJECT-TYPE
    SYNTAX     Counter32
    MAX-ACCESS read-only
    STATUS     current
    DESCRIPTION
            "-- empty --"
    ::= { hmStatusPppCcp 11 }

-- {SCALAR} 1.3.6.1.4.1.248.32.18.1.6.10.12
hmStatusPppCcpTxConfigAck OBJECT-TYPE
    SYNTAX     Counter32
    MAX-ACCESS read-only
    STATUS     current
    DESCRIPTION
            "-- empty --"
    ::= { hmStatusPppCcp 12 }

-- {SCALAR} 1.3.6.1.4.1.248.32.18.1.6.10.13
hmStatusPppCcpTxConfigNak OBJECT-TYPE
    SYNTAX     Counter32
    MAX-ACCESS read-only
    STATUS     current
    DESCRIPTION
            "-- empty --"
    ::= { hmStatusPppCcp 13 }

-- {SCALAR} 1.3.6.1.4.1.248.32.18.1.6.10.14
hmStatusPppCcpTxConfigReject OBJECT-TYPE
    SYNTAX     Counter32
    MAX-ACCESS read-only
    STATUS     current
    DESCRIPTION
            "-- empty --"
    ::= { hmStatusPppCcp 14 }

-- {SCALAR} 1.3.6.1.4.1.248.32.18.1.6.10.15
hmStatusPppCcpTxTerminateRequest OBJECT-TYPE
    SYNTAX     Counter32
    MAX-ACCESS read-only
    STATUS     current
    DESCRIPTION
            "-- empty --"
    ::= { hmStatusPppCcp 15 }

-- {SCALAR} 1.3.6.1.4.1.248.32.18.1.6.10.16
hmStatusPppCcpTxTerminateAck OBJECT-TYPE
    SYNTAX     Counter32
    MAX-ACCESS read-only
    STATUS     current
    DESCRIPTION
            "-- empty --"
    ::= { hmStatusPppCcp 16 }

-- {SCALAR} 1.3.6.1.4.1.248.32.18.1.6.10.17
hmStatusPppCcpTxCodeReject OBJECT-TYPE
    SYNTAX     Counter32
    MAX-ACCESS read-only
    STATUS     current
    DESCRIPTION
            "-- empty --"
    ::= { hmStatusPppCcp 17 }

-- {SCALAR} 1.3.6.1.4.1.248.32.18.1.6.10.19
hmStatusPppCcpTxResetRequest OBJECT-TYPE
    SYNTAX     Counter32
    MAX-ACCESS read-only
    STATUS     current
    DESCRIPTION
            "-- empty --"
    ::= { hmStatusPppCcp 19 }

-- {SCALAR} 1.3.6.1.4.1.248.32.18.1.6.10.20
hmStatusPppCcpTxResetAck OBJECT-TYPE
    SYNTAX     Counter32
    MAX-ACCESS read-only
    STATUS     current
    DESCRIPTION
            "-- empty --"
    ::= { hmStatusPppCcp 20 }

-- {SCALAR} 1.3.6.1.4.1.248.32.18.1.6.10.21
hmStatusPppCcpDeleteValues OBJECT-TYPE
    SYNTAX     DisplayString
    MAX-ACCESS read-write
    STATUS     current
    DESCRIPTION
            "-- empty --"
    ::= { hmStatusPppCcp 21 }

-- {SCALAR} 1.3.6.1.4.1.248.32.18.1.6.10.22
hmStatusPppCcpCompressionErrors OBJECT-TYPE
    SYNTAX     Counter32
    MAX-ACCESS read-only
    STATUS     current
    DESCRIPTION
            "-- empty --"
    ::= { hmStatusPppCcp 22 }

-- {SCALAR} 1.3.6.1.4.1.248.32.18.1.6.13
hmStatusPppDeleteValues OBJECT-TYPE
    SYNTAX     DisplayString
    MAX-ACCESS read-write
    STATUS     current
    DESCRIPTION
            "-- empty --"
    ::= { hmStatusPpp 13 }

-- {NODE} 1.3.6.1.4.1.248.32.18.1.6.14
hmStatusPppIpv6cp OBJECT IDENTIFIER ::= { hmStatusPpp 14 }

-- {SCALAR} 1.3.6.1.4.1.248.32.18.1.6.14.1
hmStatusPppIpv6cpRxDiscarded OBJECT-TYPE
    SYNTAX     Counter32
    MAX-ACCESS read-only
    STATUS     current
    DESCRIPTION
            "-- empty --"
    ::= { hmStatusPppIpv6cp 1 }

-- {SCALAR} 1.3.6.1.4.1.248.32.18.1.6.14.2
hmStatusPppIpv6cpRxConfigRequest OBJECT-TYPE
    SYNTAX     Counter32
    MAX-ACCESS read-only
    STATUS     current
    DESCRIPTION
            "-- empty --"
    ::= { hmStatusPppIpv6cp 2 }

-- {SCALAR} 1.3.6.1.4.1.248.32.18.1.6.14.3
hmStatusPppIpv6cpRxConfigAck OBJECT-TYPE
    SYNTAX     Counter32
    MAX-ACCESS read-only
    STATUS     current
    DESCRIPTION
            "-- empty --"
    ::= { hmStatusPppIpv6cp 3 }

-- {SCALAR} 1.3.6.1.4.1.248.32.18.1.6.14.4
hmStatusPppIpv6cpRxConfigNak OBJECT-TYPE
    SYNTAX     Counter32
    MAX-ACCESS read-only
    STATUS     current
    DESCRIPTION
            "-- empty --"
    ::= { hmStatusPppIpv6cp 4 }

-- {SCALAR} 1.3.6.1.4.1.248.32.18.1.6.14.5
hmStatusPppIpv6cpRxConfigReject OBJECT-TYPE
    SYNTAX     Counter32
    MAX-ACCESS read-only
    STATUS     current
    DESCRIPTION
            "-- empty --"
    ::= { hmStatusPppIpv6cp 5 }

-- {SCALAR} 1.3.6.1.4.1.248.32.18.1.6.14.6
hmStatusPppIpv6cpRxTerminateRequest OBJECT-TYPE
    SYNTAX     Counter32
    MAX-ACCESS read-only
    STATUS     current
    DESCRIPTION
            "-- empty --"
    ::= { hmStatusPppIpv6cp 6 }

-- {SCALAR} 1.3.6.1.4.1.248.32.18.1.6.14.7
hmStatusPppIpv6cpRxTerminateAck OBJECT-TYPE
    SYNTAX     Counter32
    MAX-ACCESS read-only
    STATUS     current
    DESCRIPTION
            "-- empty --"
    ::= { hmStatusPppIpv6cp 7 }

-- {SCALAR} 1.3.6.1.4.1.248.32.18.1.6.14.8
hmStatusPppIpv6cpRxCodeReject OBJECT-TYPE
    SYNTAX     Counter32
    MAX-ACCESS read-only
    STATUS     current
    DESCRIPTION
            "-- empty --"
    ::= { hmStatusPppIpv6cp 8 }

-- {SCALAR} 1.3.6.1.4.1.248.32.18.1.6.14.9
hmStatusPppIpv6cpTxConfigRequest OBJECT-TYPE
    SYNTAX     Counter32
    MAX-ACCESS read-only
    STATUS     current
    DESCRIPTION
            "-- empty --"
    ::= { hmStatusPppIpv6cp 9 }

-- {SCALAR} 1.3.6.1.4.1.248.32.18.1.6.14.10
hmStatusPppIpv6cpTxConfigAck OBJECT-TYPE
    SYNTAX     Counter32
    MAX-ACCESS read-only
    STATUS     current
    DESCRIPTION
            "-- empty --"
    ::= { hmStatusPppIpv6cp 10 }

-- {SCALAR} 1.3.6.1.4.1.248.32.18.1.6.14.11
hmStatusPppIpv6cpTxConfigNak OBJECT-TYPE
    SYNTAX     Counter32
    MAX-ACCESS read-only
    STATUS     current
    DESCRIPTION
            "-- empty --"
    ::= { hmStatusPppIpv6cp 11 }

-- {SCALAR} 1.3.6.1.4.1.248.32.18.1.6.14.12
hmStatusPppIpv6cpTxConfigReject OBJECT-TYPE
    SYNTAX     Counter32
    MAX-ACCESS read-only
    STATUS     current
    DESCRIPTION
            "-- empty --"
    ::= { hmStatusPppIpv6cp 12 }

-- {SCALAR} 1.3.6.1.4.1.248.32.18.1.6.14.13
hmStatusPppIpv6cpTxTerminateRequest OBJECT-TYPE
    SYNTAX     Counter32
    MAX-ACCESS read-only
    STATUS     current
    DESCRIPTION
            "-- empty --"
    ::= { hmStatusPppIpv6cp 13 }

-- {SCALAR} 1.3.6.1.4.1.248.32.18.1.6.14.14
hmStatusPppIpv6cpTxTerminateAck OBJECT-TYPE
    SYNTAX     Counter32
    MAX-ACCESS read-only
    STATUS     current
    DESCRIPTION
            "-- empty --"
    ::= { hmStatusPppIpv6cp 14 }

-- {SCALAR} 1.3.6.1.4.1.248.32.18.1.6.14.15
hmStatusPppIpv6cpTxCodeReject OBJECT-TYPE
    SYNTAX     Counter32
    MAX-ACCESS read-only
    STATUS     current
    DESCRIPTION
            "-- empty --"
    ::= { hmStatusPppIpv6cp 15 }

-- {SCALAR} 1.3.6.1.4.1.248.32.18.1.6.14.16
hmStatusPppIpv6cpDeleteValues OBJECT-TYPE
    SYNTAX     DisplayString
    MAX-ACCESS read-write
    STATUS     current
    DESCRIPTION
            "-- empty --"
    ::= { hmStatusPppIpv6cp 16 }

-- {NODE} 1.3.6.1.4.1.248.32.18.1.9
hmStatusTcpIp OBJECT IDENTIFIER ::= { hmStatus 9 }

-- {NODE} 1.3.6.1.4.1.248.32.18.1.9.1
hmStatusTcpIpArp OBJECT IDENTIFIER ::= { hmStatusTcpIp 1 }

-- {SCALAR} 1.3.6.1.4.1.248.32.18.1.9.1.1
hmStatusTcpIpArpLanRx OBJECT-TYPE
    SYNTAX     Counter32
    MAX-ACCESS read-only
    STATUS     current
    DESCRIPTION
            "-- empty --"
    ::= { hmStatusTcpIpArp 1 }

-- {SCALAR} 1.3.6.1.4.1.248.32.18.1.9.1.2
hmStatusTcpIpArpLanTx OBJECT-TYPE
    SYNTAX     Counter32
    MAX-ACCESS read-only
    STATUS     current
    DESCRIPTION
            "-- empty --"
    ::= { hmStatusTcpIpArp 2 }

-- {SCALAR} 1.3.6.1.4.1.248.32.18.1.9.1.3
hmStatusTcpIpArpLanErrors OBJECT-TYPE
    SYNTAX     Counter32
    MAX-ACCESS read-only
    STATUS     current
    DESCRIPTION
            "-- empty --"
    ::= { hmStatusTcpIpArp 3 }

-- {SCALAR} 1.3.6.1.4.1.248.32.18.1.9.1.4
hmStatusTcpIpArpWanRx OBJECT-TYPE
    SYNTAX     Counter32
    MAX-ACCESS read-only
    STATUS     current
    DESCRIPTION
            "-- empty --"
    ::= { hmStatusTcpIpArp 4 }

-- {SCALAR} 1.3.6.1.4.1.248.32.18.1.9.1.5
hmStatusTcpIpArpWanTx OBJECT-TYPE
    SYNTAX     Counter32
    MAX-ACCESS read-only
    STATUS     current
    DESCRIPTION
            "-- empty --"
    ::= { hmStatusTcpIpArp 5 }

-- {SCALAR} 1.3.6.1.4.1.248.32.18.1.9.1.6
hmStatusTcpIpArpWanErrors OBJECT-TYPE
    SYNTAX     Counter32
    MAX-ACCESS read-only
    STATUS     current
    DESCRIPTION
            "-- empty --"
    ::= { hmStatusTcpIpArp 6 }

-- {TABLE} 1.3.6.1.4.1.248.32.18.1.9.1.7
hmStatusTcpIpArpTableArpTable OBJECT-TYPE
    SYNTAX     SEQUENCE OF HmStatusTcpIpArpTableArpEntry
    MAX-ACCESS not-accessible
    STATUS     current
    DESCRIPTION
            "-- empty --"
    ::= { hmStatusTcpIpArp 7 }

-- {ROW} 1.3.6.1.4.1.248.32.18.1.9.1.7.1
hmStatusTcpIpArpTableArpEntry OBJECT-TYPE
    SYNTAX     HmStatusTcpIpArpTableArpEntry
    MAX-ACCESS not-accessible
    STATUS     current
    DESCRIPTION
            ""
    INDEX {
            hmStatusTcpIpArpTableArpEntryIpAddress
          }
    ::= { hmStatusTcpIpArpTableArpTable 1 }

HmStatusTcpIpArpTableArpEntry ::= SEQUENCE {
            hmStatusTcpIpArpTableArpEntryIpAddress IpAddress,
            hmStatusTcpIpArpTableArpEntryMacAddress MacAddress,
            hmStatusTcpIpArpTableArpEntryLastAccess Integer32,
            hmStatusTcpIpArpTableArpEntryEthernetPort INTEGER,
            hmStatusTcpIpArpTableArpEntryPeer DisplayString,
            hmStatusTcpIpArpTableArpEntryVlanId Integer32,
            hmStatusTcpIpArpTableArpEntryConnect INTEGER
    }

-- {COLUMN} 1.3.6.1.4.1.248.32.18.1.9.1.7.1.1
hmStatusTcpIpArpTableArpEntryIpAddress OBJECT-TYPE
    SYNTAX     IpAddress
    MAX-ACCESS read-only
    STATUS     current
    DESCRIPTION
            "-- empty --"
    ::= { hmStatusTcpIpArpTableArpEntry 1 }

-- {COLUMN} 1.3.6.1.4.1.248.32.18.1.9.1.7.1.2
hmStatusTcpIpArpTableArpEntryMacAddress OBJECT-TYPE
    SYNTAX     MacAddress
    MAX-ACCESS read-only
    STATUS     current
    DESCRIPTION
            "-- empty --"
    ::= { hmStatusTcpIpArpTableArpEntry 2 }

-- {COLUMN} 1.3.6.1.4.1.248.32.18.1.9.1.7.1.3
hmStatusTcpIpArpTableArpEntryLastAccess OBJECT-TYPE
    SYNTAX     Integer32 (0..2147483647)
    MAX-ACCESS read-only
    STATUS     current
    DESCRIPTION
            "-- empty --"
    ::= { hmStatusTcpIpArpTableArpEntry 3 }

-- {COLUMN} 1.3.6.1.4.1.248.32.18.1.9.1.7.1.5
hmStatusTcpIpArpTableArpEntryEthernetPort OBJECT-TYPE
    SYNTAX     INTEGER {
                  eEth1 (2),
                  eEth2 (3),
                  eEth3 (4),
                  eEth4 (5)
            }
    MAX-ACCESS read-only
    STATUS     current
    DESCRIPTION
            "-- empty --"
    ::= { hmStatusTcpIpArpTableArpEntry 5 }

-- {COLUMN} 1.3.6.1.4.1.248.32.18.1.9.1.7.1.6
hmStatusTcpIpArpTableArpEntryPeer OBJECT-TYPE
    SYNTAX     DisplayString (SIZE(0..255))
    MAX-ACCESS read-only
    STATUS     current
    DESCRIPTION
            "-- empty --"
    ::= { hmStatusTcpIpArpTableArpEntry 6 }

-- {COLUMN} 1.3.6.1.4.1.248.32.18.1.9.1.7.1.7
hmStatusTcpIpArpTableArpEntryVlanId OBJECT-TYPE
    SYNTAX     Integer32 (0..65535)
    MAX-ACCESS read-only
    STATUS     current
    DESCRIPTION
            "-- empty --"
    ::= { hmStatusTcpIpArpTableArpEntry 7 }

-- {COLUMN} 1.3.6.1.4.1.248.32.18.1.9.1.7.1.8
hmStatusTcpIpArpTableArpEntryConnect OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eWan (32768)
            }
    MAX-ACCESS read-only
    STATUS     current
    DESCRIPTION
            "-- empty --"
    ::= { hmStatusTcpIpArpTableArpEntry 8 }

-- {SCALAR} 1.3.6.1.4.1.248.32.18.1.9.1.8
hmStatusTcpIpArpDeleteValues OBJECT-TYPE
    SYNTAX     DisplayString
    MAX-ACCESS read-write
    STATUS     current
    DESCRIPTION
            "-- empty --"
    ::= { hmStatusTcpIpArp 8 }

-- {SCALAR} 1.3.6.1.4.1.248.32.18.1.9.1.10
hmStatusTcpIpArpLanProxyRules OBJECT-TYPE
    SYNTAX     Integer32 (0..2147483647)
    MAX-ACCESS read-only
    STATUS     current
    DESCRIPTION
            "-- empty --"
    ::= { hmStatusTcpIpArp 10 }

-- {NODE} 1.3.6.1.4.1.248.32.18.1.9.2
hmStatusTcpIpIp OBJECT IDENTIFIER ::= { hmStatusTcpIp 2 }

-- {SCALAR} 1.3.6.1.4.1.248.32.18.1.9.2.1
hmStatusTcpIpIpLanRx OBJECT-TYPE
    SYNTAX     Counter32
    MAX-ACCESS read-only
    STATUS     current
    DESCRIPTION
            "-- empty --"
    ::= { hmStatusTcpIpIp 1 }

-- {SCALAR} 1.3.6.1.4.1.248.32.18.1.9.2.2
hmStatusTcpIpIpLanTx OBJECT-TYPE
    SYNTAX     Counter32
    MAX-ACCESS read-only
    STATUS     current
    DESCRIPTION
            "-- empty --"
    ::= { hmStatusTcpIpIp 2 }

-- {SCALAR} 1.3.6.1.4.1.248.32.18.1.9.2.3
hmStatusTcpIpIpLanChecksumErrors OBJECT-TYPE
    SYNTAX     Counter32
    MAX-ACCESS read-only
    STATUS     current
    DESCRIPTION
            "-- empty --"
    ::= { hmStatusTcpIpIp 3 }

-- {SCALAR} 1.3.6.1.4.1.248.32.18.1.9.2.4
hmStatusTcpIpIpLanServiceErrors OBJECT-TYPE
    SYNTAX     Counter32
    MAX-ACCESS read-only
    STATUS     current
    DESCRIPTION
            "-- empty --"
    ::= { hmStatusTcpIpIp 4 }

-- {SCALAR} 1.3.6.1.4.1.248.32.18.1.9.2.5
hmStatusTcpIpIpWanRx OBJECT-TYPE
    SYNTAX     Counter32
    MAX-ACCESS read-only
    STATUS     current
    DESCRIPTION
            "-- empty --"
    ::= { hmStatusTcpIpIp 5 }

-- {SCALAR} 1.3.6.1.4.1.248.32.18.1.9.2.6
hmStatusTcpIpIpWanTx OBJECT-TYPE
    SYNTAX     Counter32
    MAX-ACCESS read-only
    STATUS     current
    DESCRIPTION
            "-- empty --"
    ::= { hmStatusTcpIpIp 6 }

-- {SCALAR} 1.3.6.1.4.1.248.32.18.1.9.2.7
hmStatusTcpIpIpWanChecksumErrors OBJECT-TYPE
    SYNTAX     Counter32
    MAX-ACCESS read-only
    STATUS     current
    DESCRIPTION
            "-- empty --"
    ::= { hmStatusTcpIpIp 7 }

-- {SCALAR} 1.3.6.1.4.1.248.32.18.1.9.2.8
hmStatusTcpIpIpWanServiceErrors OBJECT-TYPE
    SYNTAX     Counter32
    MAX-ACCESS read-only
    STATUS     current
    DESCRIPTION
            "-- empty --"
    ::= { hmStatusTcpIpIp 8 }

-- {SCALAR} 1.3.6.1.4.1.248.32.18.1.9.2.9
hmStatusTcpIpIpWanRxDisconnect OBJECT-TYPE
    SYNTAX     Counter32
    MAX-ACCESS read-only
    STATUS     current
    DESCRIPTION
            "-- empty --"
    ::= { hmStatusTcpIpIp 9 }

-- {SCALAR} 1.3.6.1.4.1.248.32.18.1.9.2.10
hmStatusTcpIpIpLanFragmentationErrors OBJECT-TYPE
    SYNTAX     Counter32
    MAX-ACCESS read-only
    STATUS     current
    DESCRIPTION
            "-- empty --"
    ::= { hmStatusTcpIpIp 10 }

-- {SCALAR} 1.3.6.1.4.1.248.32.18.1.9.2.11
hmStatusTcpIpIpWanFragmentationErrors OBJECT-TYPE
    SYNTAX     Counter32
    MAX-ACCESS read-only
    STATUS     current
    DESCRIPTION
            "-- empty --"
    ::= { hmStatusTcpIpIp 11 }

-- {SCALAR} 1.3.6.1.4.1.248.32.18.1.9.2.12
hmStatusTcpIpIpDeleteValues OBJECT-TYPE
    SYNTAX     DisplayString
    MAX-ACCESS read-write
    STATUS     current
    DESCRIPTION
            "-- empty --"
    ::= { hmStatusTcpIpIp 12 }

-- {SCALAR} 1.3.6.1.4.1.248.32.18.1.9.2.13
hmStatusTcpIpIpLanFragmentations OBJECT-TYPE
    SYNTAX     Counter32
    MAX-ACCESS read-only
    STATUS     current
    DESCRIPTION
            "-- empty --"
    ::= { hmStatusTcpIpIp 13 }

-- {SCALAR} 1.3.6.1.4.1.248.32.18.1.9.2.14
hmStatusTcpIpIpLanFragmentationsForced OBJECT-TYPE
    SYNTAX     Counter32
    MAX-ACCESS read-only
    STATUS     current
    DESCRIPTION
            "-- empty --"
    ::= { hmStatusTcpIpIp 14 }

-- {SCALAR} 1.3.6.1.4.1.248.32.18.1.9.2.15
hmStatusTcpIpIpWanFragmentations OBJECT-TYPE
    SYNTAX     Counter32
    MAX-ACCESS read-only
    STATUS     current
    DESCRIPTION
            "-- empty --"
    ::= { hmStatusTcpIpIp 15 }

-- {SCALAR} 1.3.6.1.4.1.248.32.18.1.9.2.16
hmStatusTcpIpIpWanFragmentationsForced OBJECT-TYPE
    SYNTAX     Counter32
    MAX-ACCESS read-only
    STATUS     current
    DESCRIPTION
            "-- empty --"
    ::= { hmStatusTcpIpIp 16 }

-- {SCALAR} 1.3.6.1.4.1.248.32.18.1.9.2.17
hmStatusTcpIpIpLoopError OBJECT-TYPE
    SYNTAX     Counter32
    MAX-ACCESS read-only
    STATUS     current
    DESCRIPTION
            "-- empty --"
    ::= { hmStatusTcpIpIp 17 }

-- {NODE} 1.3.6.1.4.1.248.32.18.1.9.3
hmStatusTcpIpIcmp OBJECT IDENTIFIER ::= { hmStatusTcpIp 3 }

-- {SCALAR} 1.3.6.1.4.1.248.32.18.1.9.3.1
hmStatusTcpIpIcmpLanRx OBJECT-TYPE
    SYNTAX     Counter32
    MAX-ACCESS read-only
    STATUS     current
    DESCRIPTION
            "-- empty --"
    ::= { hmStatusTcpIpIcmp 1 }

-- {SCALAR} 1.3.6.1.4.1.248.32.18.1.9.3.2
hmStatusTcpIpIcmpLanTx OBJECT-TYPE
    SYNTAX     Counter32
    MAX-ACCESS read-only
    STATUS     current
    DESCRIPTION
            "-- empty --"
    ::= { hmStatusTcpIpIcmp 2 }

-- {SCALAR} 1.3.6.1.4.1.248.32.18.1.9.3.3
hmStatusTcpIpIcmpLanChecksumErrors OBJECT-TYPE
    SYNTAX     Counter32
    MAX-ACCESS read-only
    STATUS     current
    DESCRIPTION
            "-- empty --"
    ::= { hmStatusTcpIpIcmp 3 }

-- {SCALAR} 1.3.6.1.4.1.248.32.18.1.9.3.4
hmStatusTcpIpIcmpLanServiceErrors OBJECT-TYPE
    SYNTAX     Counter32
    MAX-ACCESS read-only
    STATUS     current
    DESCRIPTION
            "-- empty --"
    ::= { hmStatusTcpIpIcmp 4 }

-- {SCALAR} 1.3.6.1.4.1.248.32.18.1.9.3.5
hmStatusTcpIpIcmpWanRx OBJECT-TYPE
    SYNTAX     Counter32
    MAX-ACCESS read-only
    STATUS     current
    DESCRIPTION
            "-- empty --"
    ::= { hmStatusTcpIpIcmp 5 }

-- {SCALAR} 1.3.6.1.4.1.248.32.18.1.9.3.6
hmStatusTcpIpIcmpWanTx OBJECT-TYPE
    SYNTAX     Counter32
    MAX-ACCESS read-only
    STATUS     current
    DESCRIPTION
            "-- empty --"
    ::= { hmStatusTcpIpIcmp 6 }

-- {SCALAR} 1.3.6.1.4.1.248.32.18.1.9.3.7
hmStatusTcpIpIcmpWanChecksumErrors OBJECT-TYPE
    SYNTAX     Counter32
    MAX-ACCESS read-only
    STATUS     current
    DESCRIPTION
            "-- empty --"
    ::= { hmStatusTcpIpIcmp 7 }

-- {SCALAR} 1.3.6.1.4.1.248.32.18.1.9.3.8
hmStatusTcpIpIcmpWanServiceErrors OBJECT-TYPE
    SYNTAX     Counter32
    MAX-ACCESS read-only
    STATUS     current
    DESCRIPTION
            "-- empty --"
    ::= { hmStatusTcpIpIcmp 8 }

-- {SCALAR} 1.3.6.1.4.1.248.32.18.1.9.3.9
hmStatusTcpIpIcmpDeleteValues OBJECT-TYPE
    SYNTAX     DisplayString
    MAX-ACCESS read-write
    STATUS     current
    DESCRIPTION
            "-- empty --"
    ::= { hmStatusTcpIpIcmp 9 }

-- {NODE} 1.3.6.1.4.1.248.32.18.1.9.4
hmStatusTcpIpTftp OBJECT IDENTIFIER ::= { hmStatusTcpIp 4 }

-- {SCALAR} 1.3.6.1.4.1.248.32.18.1.9.4.1
hmStatusTcpIpTftpLanRx OBJECT-TYPE
    SYNTAX     Counter32
    MAX-ACCESS read-only
    STATUS     current
    DESCRIPTION
            "-- empty --"
    ::= { hmStatusTcpIpTftp 1 }

-- {SCALAR} 1.3.6.1.4.1.248.32.18.1.9.4.2
hmStatusTcpIpTftpLanRxReadRequest OBJECT-TYPE
    SYNTAX     Counter32
    MAX-ACCESS read-only
    STATUS     current
    DESCRIPTION
            "-- empty --"
    ::= { hmStatusTcpIpTftp 2 }

-- {SCALAR} 1.3.6.1.4.1.248.32.18.1.9.4.3
hmStatusTcpIpTftpLanRxWriteRequest OBJECT-TYPE
    SYNTAX     Counter32
    MAX-ACCESS read-only
    STATUS     current
    DESCRIPTION
            "-- empty --"
    ::= { hmStatusTcpIpTftp 3 }

-- {SCALAR} 1.3.6.1.4.1.248.32.18.1.9.4.4
hmStatusTcpIpTftpLanRxData OBJECT-TYPE
    SYNTAX     Counter32
    MAX-ACCESS read-only
    STATUS     current
    DESCRIPTION
            "-- empty --"
    ::= { hmStatusTcpIpTftp 4 }

-- {SCALAR} 1.3.6.1.4.1.248.32.18.1.9.4.5
hmStatusTcpIpTftpLanRxAck OBJECT-TYPE
    SYNTAX     Counter32
    MAX-ACCESS read-only
    STATUS     current
    DESCRIPTION
            "-- empty --"
    ::= { hmStatusTcpIpTftp 5 }

-- {SCALAR} 1.3.6.1.4.1.248.32.18.1.9.4.6
hmStatusTcpIpTftpLanRxOptionAck OBJECT-TYPE
    SYNTAX     Counter32
    MAX-ACCESS read-only
    STATUS     current
    DESCRIPTION
            "-- empty --"
    ::= { hmStatusTcpIpTftp 6 }

-- {SCALAR} 1.3.6.1.4.1.248.32.18.1.9.4.7
hmStatusTcpIpTftpLanRxErrors OBJECT-TYPE
    SYNTAX     Counter32
    MAX-ACCESS read-only
    STATUS     current
    DESCRIPTION
            "-- empty --"
    ::= { hmStatusTcpIpTftp 7 }

-- {SCALAR} 1.3.6.1.4.1.248.32.18.1.9.4.8
hmStatusTcpIpTftpLanRxBadPackets OBJECT-TYPE
    SYNTAX     Counter32
    MAX-ACCESS read-only
    STATUS     current
    DESCRIPTION
            "-- empty --"
    ::= { hmStatusTcpIpTftp 8 }

-- {SCALAR} 1.3.6.1.4.1.248.32.18.1.9.4.9
hmStatusTcpIpTftpLanTx OBJECT-TYPE
    SYNTAX     Counter32
    MAX-ACCESS read-only
    STATUS     current
    DESCRIPTION
            "-- empty --"
    ::= { hmStatusTcpIpTftp 9 }

-- {SCALAR} 1.3.6.1.4.1.248.32.18.1.9.4.10
hmStatusTcpIpTftpLanTxData OBJECT-TYPE
    SYNTAX     Counter32
    MAX-ACCESS read-only
    STATUS     current
    DESCRIPTION
            "-- empty --"
    ::= { hmStatusTcpIpTftp 10 }

-- {SCALAR} 1.3.6.1.4.1.248.32.18.1.9.4.11
hmStatusTcpIpTftpLanTxAck OBJECT-TYPE
    SYNTAX     Counter32
    MAX-ACCESS read-only
    STATUS     current
    DESCRIPTION
            "-- empty --"
    ::= { hmStatusTcpIpTftp 11 }

-- {SCALAR} 1.3.6.1.4.1.248.32.18.1.9.4.12
hmStatusTcpIpTftpLanTxOptionAck OBJECT-TYPE
    SYNTAX     Counter32
    MAX-ACCESS read-only
    STATUS     current
    DESCRIPTION
            "-- empty --"
    ::= { hmStatusTcpIpTftp 12 }

-- {SCALAR} 1.3.6.1.4.1.248.32.18.1.9.4.13
hmStatusTcpIpTftpLanTxErrors OBJECT-TYPE
    SYNTAX     Counter32
    MAX-ACCESS read-only
    STATUS     current
    DESCRIPTION
            "-- empty --"
    ::= { hmStatusTcpIpTftp 13 }

-- {SCALAR} 1.3.6.1.4.1.248.32.18.1.9.4.14
hmStatusTcpIpTftpLanTxRepeats OBJECT-TYPE
    SYNTAX     Counter32
    MAX-ACCESS read-only
    STATUS     current
    DESCRIPTION
            "-- empty --"
    ::= { hmStatusTcpIpTftp 14 }

-- {SCALAR} 1.3.6.1.4.1.248.32.18.1.9.4.15
hmStatusTcpIpTftpLanConnections OBJECT-TYPE
    SYNTAX     Counter32
    MAX-ACCESS read-only
    STATUS     current
    DESCRIPTION
            "-- empty --"
    ::= { hmStatusTcpIpTftp 15 }

-- {SCALAR} 1.3.6.1.4.1.248.32.18.1.9.4.16
hmStatusTcpIpTftpWanRx OBJECT-TYPE
    SYNTAX     Counter32
    MAX-ACCESS read-only
    STATUS     current
    DESCRIPTION
            "-- empty --"
    ::= { hmStatusTcpIpTftp 16 }

-- {SCALAR} 1.3.6.1.4.1.248.32.18.1.9.4.17
hmStatusTcpIpTftpWanRxReadRequest OBJECT-TYPE
    SYNTAX     Counter32
    MAX-ACCESS read-only
    STATUS     current
    DESCRIPTION
            "-- empty --"
    ::= { hmStatusTcpIpTftp 17 }

-- {SCALAR} 1.3.6.1.4.1.248.32.18.1.9.4.18
hmStatusTcpIpTftpWanRxWriteRequest OBJECT-TYPE
    SYNTAX     Counter32
    MAX-ACCESS read-only
    STATUS     current
    DESCRIPTION
            "-- empty --"
    ::= { hmStatusTcpIpTftp 18 }

-- {SCALAR} 1.3.6.1.4.1.248.32.18.1.9.4.19
hmStatusTcpIpTftpWanRxData OBJECT-TYPE
    SYNTAX     Counter32
    MAX-ACCESS read-only
    STATUS     current
    DESCRIPTION
            "-- empty --"
    ::= { hmStatusTcpIpTftp 19 }

-- {SCALAR} 1.3.6.1.4.1.248.32.18.1.9.4.20
hmStatusTcpIpTftpWanRxAck OBJECT-TYPE
    SYNTAX     Counter32
    MAX-ACCESS read-only
    STATUS     current
    DESCRIPTION
            "-- empty --"
    ::= { hmStatusTcpIpTftp 20 }

-- {SCALAR} 1.3.6.1.4.1.248.32.18.1.9.4.21
hmStatusTcpIpTftpWanRxOptionAck OBJECT-TYPE
    SYNTAX     Counter32
    MAX-ACCESS read-only
    STATUS     current
    DESCRIPTION
            "-- empty --"
    ::= { hmStatusTcpIpTftp 21 }

-- {SCALAR} 1.3.6.1.4.1.248.32.18.1.9.4.22
hmStatusTcpIpTftpWanRxErrors OBJECT-TYPE
    SYNTAX     Counter32
    MAX-ACCESS read-only
    STATUS     current
    DESCRIPTION
            "-- empty --"
    ::= { hmStatusTcpIpTftp 22 }

-- {SCALAR} 1.3.6.1.4.1.248.32.18.1.9.4.23
hmStatusTcpIpTftpWanRxBadPackets OBJECT-TYPE
    SYNTAX     Counter32
    MAX-ACCESS read-only
    STATUS     current
    DESCRIPTION
            "-- empty --"
    ::= { hmStatusTcpIpTftp 23 }

-- {SCALAR} 1.3.6.1.4.1.248.32.18.1.9.4.24
hmStatusTcpIpTftpWanTx OBJECT-TYPE
    SYNTAX     Counter32
    MAX-ACCESS read-only
    STATUS     current
    DESCRIPTION
            "-- empty --"
    ::= { hmStatusTcpIpTftp 24 }

-- {SCALAR} 1.3.6.1.4.1.248.32.18.1.9.4.25
hmStatusTcpIpTftpWanTxData OBJECT-TYPE
    SYNTAX     Counter32
    MAX-ACCESS read-only
    STATUS     current
    DESCRIPTION
            "-- empty --"
    ::= { hmStatusTcpIpTftp 25 }

-- {SCALAR} 1.3.6.1.4.1.248.32.18.1.9.4.26
hmStatusTcpIpTftpWanTxAck OBJECT-TYPE
    SYNTAX     Counter32
    MAX-ACCESS read-only
    STATUS     current
    DESCRIPTION
            "-- empty --"
    ::= { hmStatusTcpIpTftp 26 }

-- {SCALAR} 1.3.6.1.4.1.248.32.18.1.9.4.27
hmStatusTcpIpTftpWanTxOptionAck OBJECT-TYPE
    SYNTAX     Counter32
    MAX-ACCESS read-only
    STATUS     current
    DESCRIPTION
            "-- empty --"
    ::= { hmStatusTcpIpTftp 27 }

-- {SCALAR} 1.3.6.1.4.1.248.32.18.1.9.4.28
hmStatusTcpIpTftpWanTxErrors OBJECT-TYPE
    SYNTAX     Counter32
    MAX-ACCESS read-only
    STATUS     current
    DESCRIPTION
            "-- empty --"
    ::= { hmStatusTcpIpTftp 28 }

-- {SCALAR} 1.3.6.1.4.1.248.32.18.1.9.4.29
hmStatusTcpIpTftpWanTxRepeats OBJECT-TYPE
    SYNTAX     Counter32
    MAX-ACCESS read-only
    STATUS     current
    DESCRIPTION
            "-- empty --"
    ::= { hmStatusTcpIpTftp 29 }

-- {SCALAR} 1.3.6.1.4.1.248.32.18.1.9.4.30
hmStatusTcpIpTftpWanConnections OBJECT-TYPE
    SYNTAX     Counter32
    MAX-ACCESS read-only
    STATUS     current
    DESCRIPTION
            "-- empty --"
    ::= { hmStatusTcpIpTftp 30 }

-- {SCALAR} 1.3.6.1.4.1.248.32.18.1.9.4.31
hmStatusTcpIpTftpDeleteValues OBJECT-TYPE
    SYNTAX     DisplayString
    MAX-ACCESS read-write
    STATUS     current
    DESCRIPTION
            "-- empty --"
    ::= { hmStatusTcpIpTftp 31 }

-- {NODE} 1.3.6.1.4.1.248.32.18.1.9.5
hmStatusTcpIpTcp OBJECT IDENTIFIER ::= { hmStatusTcpIp 5 }

-- {SCALAR} 1.3.6.1.4.1.248.32.18.1.9.5.1
hmStatusTcpIpTcpLanRx OBJECT-TYPE
    SYNTAX     Counter32
    MAX-ACCESS read-only
    STATUS     current
    DESCRIPTION
            "-- empty --"
    ::= { hmStatusTcpIpTcp 1 }

-- {SCALAR} 1.3.6.1.4.1.248.32.18.1.9.5.2
hmStatusTcpIpTcpLanTx OBJECT-TYPE
    SYNTAX     Counter32
    MAX-ACCESS read-only
    STATUS     current
    DESCRIPTION
            "-- empty --"
    ::= { hmStatusTcpIpTcp 2 }

-- {SCALAR} 1.3.6.1.4.1.248.32.18.1.9.5.3
hmStatusTcpIpTcpLanTxRepeats OBJECT-TYPE
    SYNTAX     Counter32
    MAX-ACCESS read-only
    STATUS     current
    DESCRIPTION
            "-- empty --"
    ::= { hmStatusTcpIpTcp 3 }

-- {SCALAR} 1.3.6.1.4.1.248.32.18.1.9.5.4
hmStatusTcpIpTcpLanChecksumErrors OBJECT-TYPE
    SYNTAX     Counter32
    MAX-ACCESS read-only
    STATUS     current
    DESCRIPTION
            "-- empty --"
    ::= { hmStatusTcpIpTcp 4 }

-- {SCALAR} 1.3.6.1.4.1.248.32.18.1.9.5.5
hmStatusTcpIpTcpLanServiceErrors OBJECT-TYPE
    SYNTAX     Counter32
    MAX-ACCESS read-only
    STATUS     current
    DESCRIPTION
            "-- empty --"
    ::= { hmStatusTcpIpTcp 5 }

-- {SCALAR} 1.3.6.1.4.1.248.32.18.1.9.5.6
hmStatusTcpIpTcpLanConnections OBJECT-TYPE
    SYNTAX     Counter32
    MAX-ACCESS read-only
    STATUS     current
    DESCRIPTION
            "-- empty --"
    ::= { hmStatusTcpIpTcp 6 }

-- {SCALAR} 1.3.6.1.4.1.248.32.18.1.9.5.7
hmStatusTcpIpTcpWanRx OBJECT-TYPE
    SYNTAX     Counter32
    MAX-ACCESS read-only
    STATUS     current
    DESCRIPTION
            "-- empty --"
    ::= { hmStatusTcpIpTcp 7 }

-- {SCALAR} 1.3.6.1.4.1.248.32.18.1.9.5.8
hmStatusTcpIpTcpWanTx OBJECT-TYPE
    SYNTAX     Counter32
    MAX-ACCESS read-only
    STATUS     current
    DESCRIPTION
            "-- empty --"
    ::= { hmStatusTcpIpTcp 8 }

-- {SCALAR} 1.3.6.1.4.1.248.32.18.1.9.5.9
hmStatusTcpIpTcpWanTxRepeats OBJECT-TYPE
    SYNTAX     Counter32
    MAX-ACCESS read-only
    STATUS     current
    DESCRIPTION
            "-- empty --"
    ::= { hmStatusTcpIpTcp 9 }

-- {SCALAR} 1.3.6.1.4.1.248.32.18.1.9.5.10
hmStatusTcpIpTcpWanChecksumErrors OBJECT-TYPE
    SYNTAX     Counter32
    MAX-ACCESS read-only
    STATUS     current
    DESCRIPTION
            "-- empty --"
    ::= { hmStatusTcpIpTcp 10 }

-- {SCALAR} 1.3.6.1.4.1.248.32.18.1.9.5.11
hmStatusTcpIpTcpWanServiceErrors OBJECT-TYPE
    SYNTAX     Counter32
    MAX-ACCESS read-only
    STATUS     current
    DESCRIPTION
            "-- empty --"
    ::= { hmStatusTcpIpTcp 11 }

-- {SCALAR} 1.3.6.1.4.1.248.32.18.1.9.5.12
hmStatusTcpIpTcpWanConnections OBJECT-TYPE
    SYNTAX     Counter32
    MAX-ACCESS read-only
    STATUS     current
    DESCRIPTION
            "-- empty --"
    ::= { hmStatusTcpIpTcp 12 }

-- {SCALAR} 1.3.6.1.4.1.248.32.18.1.9.5.13
hmStatusTcpIpTcpDeleteValues OBJECT-TYPE
    SYNTAX     DisplayString
    MAX-ACCESS read-write
    STATUS     current
    DESCRIPTION
            "-- empty --"
    ::= { hmStatusTcpIpTcp 13 }

-- {NODE} 1.3.6.1.4.1.248.32.18.1.9.6
hmStatusTcpIpDhcp OBJECT IDENTIFIER ::= { hmStatusTcpIp 6 }

-- {SCALAR} 1.3.6.1.4.1.248.32.18.1.9.6.1
hmStatusTcpIpDhcpLanRx OBJECT-TYPE
    SYNTAX     Counter32
    MAX-ACCESS read-only
    STATUS     current
    DESCRIPTION
            "-- empty --"
    ::= { hmStatusTcpIpDhcp 1 }

-- {SCALAR} 1.3.6.1.4.1.248.32.18.1.9.6.2
hmStatusTcpIpDhcpLanTx OBJECT-TYPE
    SYNTAX     Counter32
    MAX-ACCESS read-only
    STATUS     current
    DESCRIPTION
            "-- empty --"
    ::= { hmStatusTcpIpDhcp 2 }

-- {SCALAR} 1.3.6.1.4.1.248.32.18.1.9.6.3
hmStatusTcpIpDhcpWanRx OBJECT-TYPE
    SYNTAX     Counter32
    MAX-ACCESS read-only
    STATUS     current
    DESCRIPTION
            "-- empty --"
    ::= { hmStatusTcpIpDhcp 3 }

-- {SCALAR} 1.3.6.1.4.1.248.32.18.1.9.6.4
hmStatusTcpIpDhcpDiscard OBJECT-TYPE
    SYNTAX     Counter32
    MAX-ACCESS read-only
    STATUS     current
    DESCRIPTION
            "-- empty --"
    ::= { hmStatusTcpIpDhcp 4 }

-- {SCALAR} 1.3.6.1.4.1.248.32.18.1.9.6.5
hmStatusTcpIpDhcpRxDiscover OBJECT-TYPE
    SYNTAX     Counter32
    MAX-ACCESS read-only
    STATUS     current
    DESCRIPTION
            "-- empty --"
    ::= { hmStatusTcpIpDhcp 5 }

-- {SCALAR} 1.3.6.1.4.1.248.32.18.1.9.6.6
hmStatusTcpIpDhcpRxRequest OBJECT-TYPE
    SYNTAX     Counter32
    MAX-ACCESS read-only
    STATUS     current
    DESCRIPTION
            "-- empty --"
    ::= { hmStatusTcpIpDhcp 6 }

-- {SCALAR} 1.3.6.1.4.1.248.32.18.1.9.6.7
hmStatusTcpIpDhcpRxDecline OBJECT-TYPE
    SYNTAX     Counter32
    MAX-ACCESS read-only
    STATUS     current
    DESCRIPTION
            "-- empty --"
    ::= { hmStatusTcpIpDhcp 7 }

-- {SCALAR} 1.3.6.1.4.1.248.32.18.1.9.6.8
hmStatusTcpIpDhcpRxInform OBJECT-TYPE
    SYNTAX     Counter32
    MAX-ACCESS read-only
    STATUS     current
    DESCRIPTION
            "-- empty --"
    ::= { hmStatusTcpIpDhcp 8 }

-- {SCALAR} 1.3.6.1.4.1.248.32.18.1.9.6.9
hmStatusTcpIpDhcpRxRelease OBJECT-TYPE
    SYNTAX     Counter32
    MAX-ACCESS read-only
    STATUS     current
    DESCRIPTION
            "-- empty --"
    ::= { hmStatusTcpIpDhcp 9 }

-- {SCALAR} 1.3.6.1.4.1.248.32.18.1.9.6.10
hmStatusTcpIpDhcpTxOffer OBJECT-TYPE
    SYNTAX     Counter32
    MAX-ACCESS read-only
    STATUS     current
    DESCRIPTION
            "-- empty --"
    ::= { hmStatusTcpIpDhcp 10 }

-- {SCALAR} 1.3.6.1.4.1.248.32.18.1.9.6.11
hmStatusTcpIpDhcpTxAck OBJECT-TYPE
    SYNTAX     Counter32
    MAX-ACCESS read-only
    STATUS     current
    DESCRIPTION
            "-- empty --"
    ::= { hmStatusTcpIpDhcp 11 }

-- {SCALAR} 1.3.6.1.4.1.248.32.18.1.9.6.12
hmStatusTcpIpDhcpTxNak OBJECT-TYPE
    SYNTAX     Counter32
    MAX-ACCESS read-only
    STATUS     current
    DESCRIPTION
            "-- empty --"
    ::= { hmStatusTcpIpDhcp 12 }

-- {SCALAR} 1.3.6.1.4.1.248.32.18.1.9.6.13
hmStatusTcpIpDhcpServerError OBJECT-TYPE
    SYNTAX     Counter32
    MAX-ACCESS read-only
    STATUS     current
    DESCRIPTION
            "-- empty --"
    ::= { hmStatusTcpIpDhcp 13 }

-- {SCALAR} 1.3.6.1.4.1.248.32.18.1.9.6.14
hmStatusTcpIpDhcpAssigned OBJECT-TYPE
    SYNTAX     Integer32 (0..2147483647)
    MAX-ACCESS read-only
    STATUS     current
    DESCRIPTION
            "-- empty --"
    ::= { hmStatusTcpIpDhcp 14 }

-- {SCALAR} 1.3.6.1.4.1.248.32.18.1.9.6.15
hmStatusTcpIpDhcpMacConflicts OBJECT-TYPE
    SYNTAX     Counter32
    MAX-ACCESS read-only
    STATUS     current
    DESCRIPTION
            "-- empty --"
    ::= { hmStatusTcpIpDhcp 15 }

-- {TABLE} 1.3.6.1.4.1.248.32.18.1.9.6.16
hmStatusTcpIpDhcpDhcpTableTable OBJECT-TYPE
    SYNTAX     SEQUENCE OF HmStatusTcpIpDhcpDhcpTableEntry
    MAX-ACCESS not-accessible
    STATUS     current
    DESCRIPTION
            "-- empty --"
    ::= { hmStatusTcpIpDhcp 16 }

-- {ROW} 1.3.6.1.4.1.248.32.18.1.9.6.16.1
hmStatusTcpIpDhcpDhcpTableEntry OBJECT-TYPE
    SYNTAX     HmStatusTcpIpDhcpDhcpTableEntry
    MAX-ACCESS not-accessible
    STATUS     current
    DESCRIPTION
            ""
    INDEX {
            hmStatusTcpIpDhcpDhcpTableEntryIpAddress,
            hmStatusTcpIpDhcpDhcpTableEntryNetworkName
          }
    ::= { hmStatusTcpIpDhcpDhcpTableTable 1 }

HmStatusTcpIpDhcpDhcpTableEntry ::= SEQUENCE {
            hmStatusTcpIpDhcpDhcpTableEntryIpAddress IpAddress,
            hmStatusTcpIpDhcpDhcpTableEntryMacAddress DisplayString,
            hmStatusTcpIpDhcpDhcpTableEntryTimeout Integer32,
            hmStatusTcpIpDhcpDhcpTableEntryHostname DisplayString,
            hmStatusTcpIpDhcpDhcpTableEntryType BITS,
            hmStatusTcpIpDhcpDhcpTableEntryEthernetPort INTEGER,
            hmStatusTcpIpDhcpDhcpTableEntryVlanId Integer32,
            hmStatusTcpIpDhcpDhcpTableEntryNetworkName DisplayString,
            hmStatusTcpIpDhcpDhcpTableEntryLanIfc INTEGER,
            hmStatusTcpIpDhcpDhcpTableEntryAssignment DisplayString,
            hmStatusTcpIpDhcpDhcpTableEntryAssignmentNumeric Gauge32
    }

-- {COLUMN} 1.3.6.1.4.1.248.32.18.1.9.6.16.1.1
hmStatusTcpIpDhcpDhcpTableEntryIpAddress OBJECT-TYPE
    SYNTAX     IpAddress
    MAX-ACCESS read-only
    STATUS     current
    DESCRIPTION
            "-- empty --"
    ::= { hmStatusTcpIpDhcpDhcpTableEntry 1 }

-- {COLUMN} 1.3.6.1.4.1.248.32.18.1.9.6.16.1.2
hmStatusTcpIpDhcpDhcpTableEntryMacAddress OBJECT-TYPE
    SYNTAX     DisplayString (SIZE(0..12))
    MAX-ACCESS read-only
    STATUS     current
    DESCRIPTION
            "-- empty --"
    ::= { hmStatusTcpIpDhcpDhcpTableEntry 2 }

-- {COLUMN} 1.3.6.1.4.1.248.32.18.1.9.6.16.1.3
hmStatusTcpIpDhcpDhcpTableEntryTimeout OBJECT-TYPE
    SYNTAX     Integer32 (0..2147483647)
    MAX-ACCESS read-only
    STATUS     current
    DESCRIPTION
            "-- empty --"
    ::= { hmStatusTcpIpDhcpDhcpTableEntry 3 }

-- {COLUMN} 1.3.6.1.4.1.248.32.18.1.9.6.16.1.4
hmStatusTcpIpDhcpDhcpTableEntryHostname OBJECT-TYPE
    SYNTAX     DisplayString (SIZE(0..65))
    MAX-ACCESS read-only
    STATUS     current
    DESCRIPTION
            "-- empty --"
    ::= { hmStatusTcpIpDhcpDhcpTableEntry 4 }

-- {COLUMN} 1.3.6.1.4.1.248.32.18.1.9.6.16.1.5
hmStatusTcpIpDhcpDhcpTableEntryType OBJECT-TYPE
    SYNTAX     BITS {
                  eRelay (4),
                  eCache (8),
                  eBootp (10),
                  eDyn (11),
                  eStat (12),
                  eUnkn (13),
                  enewreq (14),
                  enew (15)
            }
    MAX-ACCESS read-only
    STATUS     current
    DESCRIPTION
            "-- empty --"
    ::= { hmStatusTcpIpDhcpDhcpTableEntry 5 }

-- {COLUMN} 1.3.6.1.4.1.248.32.18.1.9.6.16.1.7
hmStatusTcpIpDhcpDhcpTableEntryEthernetPort OBJECT-TYPE
    SYNTAX     INTEGER {
                  eEth1 (2),
                  eEth2 (3),
                  eEth3 (4),
                  eEth4 (5)
            }
    MAX-ACCESS read-only
    STATUS     current
    DESCRIPTION
            "-- empty --"
    ::= { hmStatusTcpIpDhcpDhcpTableEntry 7 }

-- {COLUMN} 1.3.6.1.4.1.248.32.18.1.9.6.16.1.8
hmStatusTcpIpDhcpDhcpTableEntryVlanId OBJECT-TYPE
    SYNTAX     Integer32 (0..65535)
    MAX-ACCESS read-only
    STATUS     current
    DESCRIPTION
            "-- empty --"
    ::= { hmStatusTcpIpDhcpDhcpTableEntry 8 }

-- {COLUMN} 1.3.6.1.4.1.248.32.18.1.9.6.16.1.9
hmStatusTcpIpDhcpDhcpTableEntryNetworkName OBJECT-TYPE
    SYNTAX     DisplayString (SIZE(0..17))
    MAX-ACCESS read-only
    STATUS     current
    DESCRIPTION
            "-- empty --"
    ::= { hmStatusTcpIpDhcpDhcpTableEntry 9 }

-- {COLUMN} 1.3.6.1.4.1.248.32.18.1.9.6.16.1.10
hmStatusTcpIpDhcpDhcpTableEntryLanIfc OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eAny (65535)
            }
    MAX-ACCESS read-only
    STATUS     current
    DESCRIPTION
            "-- empty --"
    ::= { hmStatusTcpIpDhcpDhcpTableEntry 10 }

-- {COLUMN} 1.3.6.1.4.1.248.32.18.1.9.6.16.1.11
hmStatusTcpIpDhcpDhcpTableEntryAssignment OBJECT-TYPE
    SYNTAX     DisplayString (SIZE(0..21))
    MAX-ACCESS read-only
    STATUS     current
    DESCRIPTION
            "-- empty --"
    ::= { hmStatusTcpIpDhcpDhcpTableEntry 11 }

-- {COLUMN} 1.3.6.1.4.1.248.32.18.1.9.6.16.1.12
hmStatusTcpIpDhcpDhcpTableEntryAssignmentNumeric OBJECT-TYPE
    SYNTAX     Gauge32
    MAX-ACCESS read-only
    STATUS     current
    DESCRIPTION
            "-- empty --"
    ::= { hmStatusTcpIpDhcpDhcpTableEntry 12 }

-- {SCALAR} 1.3.6.1.4.1.248.32.18.1.9.6.18
hmStatusTcpIpDhcpDeleteValues OBJECT-TYPE
    SYNTAX     DisplayString
    MAX-ACCESS read-write
    STATUS     current
    DESCRIPTION
            "-- empty --"
    ::= { hmStatusTcpIpDhcp 18 }

-- {SCALAR} 1.3.6.1.4.1.248.32.18.1.9.6.19
hmStatusTcpIpDhcpWanTx OBJECT-TYPE
    SYNTAX     Counter32
    MAX-ACCESS read-only
    STATUS     current
    DESCRIPTION
            "-- empty --"
    ::= { hmStatusTcpIpDhcp 19 }

-- {TABLE} 1.3.6.1.4.1.248.32.18.1.9.6.20
hmStatusTcpIpDhcpNetworkListTable OBJECT-TYPE
    SYNTAX     SEQUENCE OF HmStatusTcpIpDhcpNetworkListEntry
    MAX-ACCESS not-accessible
    STATUS     current
    DESCRIPTION
            "-- empty --"
    ::= { hmStatusTcpIpDhcp 20 }

-- {ROW} 1.3.6.1.4.1.248.32.18.1.9.6.20.1
hmStatusTcpIpDhcpNetworkListEntry OBJECT-TYPE
    SYNTAX     HmStatusTcpIpDhcpNetworkListEntry
    MAX-ACCESS not-accessible
    STATUS     current
    DESCRIPTION
            ""
    INDEX {
            hmStatusTcpIpDhcpNetworkListEntryNetworkName
          }
    ::= { hmStatusTcpIpDhcpNetworkListTable 1 }

HmStatusTcpIpDhcpNetworkListEntry ::= SEQUENCE {
            hmStatusTcpIpDhcpNetworkListEntryNetworkName DisplayString,
            hmStatusTcpIpDhcpNetworkListEntryStartAddressPool IpAddress,
            hmStatusTcpIpDhcpNetworkListEntryEndAddressPool IpAddress,
            hmStatusTcpIpDhcpNetworkListEntryNetmask IpAddress,
            hmStatusTcpIpDhcpNetworkListEntryBroadcastAddress IpAddress,
            hmStatusTcpIpDhcpNetworkListEntryGatewayAddress IpAddress,
            hmStatusTcpIpDhcpNetworkListEntryDnsDefault IpAddress,
            hmStatusTcpIpDhcpNetworkListEntryDnsBackup IpAddress,
            hmStatusTcpIpDhcpNetworkListEntryNbnsDefault IpAddress,
            hmStatusTcpIpDhcpNetworkListEntryNbnsBackup IpAddress,
            hmStatusTcpIpDhcpNetworkListEntryServerFlags DisplayString,
            hmStatusTcpIpDhcpNetworkListEntryBroadcastBit INTEGER,
            hmStatusTcpIpDhcpNetworkListEntryServerId IpAddress,
            hmStatusTcpIpDhcpNetworkListEntryVlanId Integer32,
            hmStatusTcpIpDhcpNetworkListEntryMasterServer IpAddress,
            hmStatusTcpIpDhcpNetworkListEntryCache INTEGER,
            hmStatusTcpIpDhcpNetworkListEntryAdaption INTEGER,
            hmStatusTcpIpDhcpNetworkListEntryCluster INTEGER,
            hmStatusTcpIpDhcpNetworkListEntry2ndMasterServer IpAddress,
            hmStatusTcpIpDhcpNetworkListEntry3rdMasterServer IpAddress,
            hmStatusTcpIpDhcpNetworkListEntry4thMasterServer IpAddress,
            hmStatusTcpIpDhcpNetworkListEntryLanIfc INTEGER
    }

-- {COLUMN} 1.3.6.1.4.1.248.32.18.1.9.6.20.1.1
hmStatusTcpIpDhcpNetworkListEntryNetworkName OBJECT-TYPE
    SYNTAX     DisplayString (SIZE(0..16))
    MAX-ACCESS read-only
    STATUS     current
    DESCRIPTION
            "-- empty --"
    ::= { hmStatusTcpIpDhcpNetworkListEntry 1 }

-- {COLUMN} 1.3.6.1.4.1.248.32.18.1.9.6.20.1.2
hmStatusTcpIpDhcpNetworkListEntryStartAddressPool OBJECT-TYPE
    SYNTAX     IpAddress
    MAX-ACCESS read-only
    STATUS     current
    DESCRIPTION
            "-- empty --"
    ::= { hmStatusTcpIpDhcpNetworkListEntry 2 }

-- {COLUMN} 1.3.6.1.4.1.248.32.18.1.9.6.20.1.3
hmStatusTcpIpDhcpNetworkListEntryEndAddressPool OBJECT-TYPE
    SYNTAX     IpAddress
    MAX-ACCESS read-only
    STATUS     current
    DESCRIPTION
            "-- empty --"
    ::= { hmStatusTcpIpDhcpNetworkListEntry 3 }

-- {COLUMN} 1.3.6.1.4.1.248.32.18.1.9.6.20.1.4
hmStatusTcpIpDhcpNetworkListEntryNetmask OBJECT-TYPE
    SYNTAX     IpAddress
    MAX-ACCESS read-only
    STATUS     current
    DESCRIPTION
            "-- empty --"
    ::= { hmStatusTcpIpDhcpNetworkListEntry 4 }

-- {COLUMN} 1.3.6.1.4.1.248.32.18.1.9.6.20.1.5
hmStatusTcpIpDhcpNetworkListEntryBroadcastAddress OBJECT-TYPE
    SYNTAX     IpAddress
    MAX-ACCESS read-only
    STATUS     current
    DESCRIPTION
            "-- empty --"
    ::= { hmStatusTcpIpDhcpNetworkListEntry 5 }

-- {COLUMN} 1.3.6.1.4.1.248.32.18.1.9.6.20.1.6
hmStatusTcpIpDhcpNetworkListEntryGatewayAddress OBJECT-TYPE
    SYNTAX     IpAddress
    MAX-ACCESS read-only
    STATUS     current
    DESCRIPTION
            "-- empty --"
    ::= { hmStatusTcpIpDhcpNetworkListEntry 6 }

-- {COLUMN} 1.3.6.1.4.1.248.32.18.1.9.6.20.1.7
hmStatusTcpIpDhcpNetworkListEntryDnsDefault OBJECT-TYPE
    SYNTAX     IpAddress
    MAX-ACCESS read-only
    STATUS     current
    DESCRIPTION
            "-- empty --"
    ::= { hmStatusTcpIpDhcpNetworkListEntry 7 }

-- {COLUMN} 1.3.6.1.4.1.248.32.18.1.9.6.20.1.8
hmStatusTcpIpDhcpNetworkListEntryDnsBackup OBJECT-TYPE
    SYNTAX     IpAddress
    MAX-ACCESS read-only
    STATUS     current
    DESCRIPTION
            "-- empty --"
    ::= { hmStatusTcpIpDhcpNetworkListEntry 8 }

-- {COLUMN} 1.3.6.1.4.1.248.32.18.1.9.6.20.1.9
hmStatusTcpIpDhcpNetworkListEntryNbnsDefault OBJECT-TYPE
    SYNTAX     IpAddress
    MAX-ACCESS read-only
    STATUS     current
    DESCRIPTION
            "-- empty --"
    ::= { hmStatusTcpIpDhcpNetworkListEntry 9 }

-- {COLUMN} 1.3.6.1.4.1.248.32.18.1.9.6.20.1.10
hmStatusTcpIpDhcpNetworkListEntryNbnsBackup OBJECT-TYPE
    SYNTAX     IpAddress
    MAX-ACCESS read-only
    STATUS     current
    DESCRIPTION
            "-- empty --"
    ::= { hmStatusTcpIpDhcpNetworkListEntry 10 }

-- {COLUMN} 1.3.6.1.4.1.248.32.18.1.9.6.20.1.11
hmStatusTcpIpDhcpNetworkListEntryServerFlags OBJECT-TYPE
    SYNTAX     DisplayString (SIZE(0..255))
    MAX-ACCESS read-only
    STATUS     current
    DESCRIPTION
            "-- empty --"
    ::= { hmStatusTcpIpDhcpNetworkListEntry 11 }

-- {COLUMN} 1.3.6.1.4.1.248.32.18.1.9.6.20.1.13
hmStatusTcpIpDhcpNetworkListEntryBroadcastBit OBJECT-TYPE
    SYNTAX     INTEGER {
                  eNo (0),
                  eYes (1)
            }
    MAX-ACCESS read-only
    STATUS     current
    DESCRIPTION
            "-- empty --"
    ::= { hmStatusTcpIpDhcpNetworkListEntry 13 }

-- {COLUMN} 1.3.6.1.4.1.248.32.18.1.9.6.20.1.14
hmStatusTcpIpDhcpNetworkListEntryServerId OBJECT-TYPE
    SYNTAX     IpAddress
    MAX-ACCESS read-only
    STATUS     current
    DESCRIPTION
            "-- empty --"
    ::= { hmStatusTcpIpDhcpNetworkListEntry 14 }

-- {COLUMN} 1.3.6.1.4.1.248.32.18.1.9.6.20.1.16
hmStatusTcpIpDhcpNetworkListEntryVlanId OBJECT-TYPE
    SYNTAX     Integer32 (0..65535)
    MAX-ACCESS read-only
    STATUS     current
    DESCRIPTION
            "-- empty --"
    ::= { hmStatusTcpIpDhcpNetworkListEntry 16 }

-- {COLUMN} 1.3.6.1.4.1.248.32.18.1.9.6.20.1.17
hmStatusTcpIpDhcpNetworkListEntryMasterServer OBJECT-TYPE
    SYNTAX     IpAddress
    MAX-ACCESS read-only
    STATUS     current
    DESCRIPTION
            "-- empty --"
    ::= { hmStatusTcpIpDhcpNetworkListEntry 17 }

-- {COLUMN} 1.3.6.1.4.1.248.32.18.1.9.6.20.1.18
hmStatusTcpIpDhcpNetworkListEntryCache OBJECT-TYPE
    SYNTAX     INTEGER {
                  eNo (0),
                  eYes (1)
            }
    MAX-ACCESS read-only
    STATUS     current
    DESCRIPTION
            "-- empty --"
    ::= { hmStatusTcpIpDhcpNetworkListEntry 18 }

-- {COLUMN} 1.3.6.1.4.1.248.32.18.1.9.6.20.1.19
hmStatusTcpIpDhcpNetworkListEntryAdaption OBJECT-TYPE
    SYNTAX     INTEGER {
                  eNo (0),
                  eYes (1)
            }
    MAX-ACCESS read-only
    STATUS     current
    DESCRIPTION
            "-- empty --"
    ::= { hmStatusTcpIpDhcpNetworkListEntry 19 }

-- {COLUMN} 1.3.6.1.4.1.248.32.18.1.9.6.20.1.20
hmStatusTcpIpDhcpNetworkListEntryCluster OBJECT-TYPE
    SYNTAX     INTEGER {
                  eNo (0),
                  eYes (1)
            }
    MAX-ACCESS read-only
    STATUS     current
    DESCRIPTION
            "-- empty --"
    ::= { hmStatusTcpIpDhcpNetworkListEntry 20 }

-- {COLUMN} 1.3.6.1.4.1.248.32.18.1.9.6.20.1.21
hmStatusTcpIpDhcpNetworkListEntry2ndMasterServer OBJECT-TYPE
    SYNTAX     IpAddress
    MAX-ACCESS read-only
    STATUS     current
    DESCRIPTION
            "-- empty --"
    ::= { hmStatusTcpIpDhcpNetworkListEntry 21 }

-- {COLUMN} 1.3.6.1.4.1.248.32.18.1.9.6.20.1.22
hmStatusTcpIpDhcpNetworkListEntry3rdMasterServer OBJECT-TYPE
    SYNTAX     IpAddress
    MAX-ACCESS read-only
    STATUS     current
    DESCRIPTION
            "-- empty --"
    ::= { hmStatusTcpIpDhcpNetworkListEntry 22 }

-- {COLUMN} 1.3.6.1.4.1.248.32.18.1.9.6.20.1.23
hmStatusTcpIpDhcpNetworkListEntry4thMasterServer OBJECT-TYPE
    SYNTAX     IpAddress
    MAX-ACCESS read-only
    STATUS     current
    DESCRIPTION
            "-- empty --"
    ::= { hmStatusTcpIpDhcpNetworkListEntry 23 }

-- {COLUMN} 1.3.6.1.4.1.248.32.18.1.9.6.20.1.24
hmStatusTcpIpDhcpNetworkListEntryLanIfc OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eAny (65535)
            }
    MAX-ACCESS read-only
    STATUS     current
    DESCRIPTION
            "-- empty --"
    ::= { hmStatusTcpIpDhcpNetworkListEntry 24 }

-- {SCALAR} 1.3.6.1.4.1.248.32.18.1.9.7
hmStatusTcpIpDeleteValues OBJECT-TYPE
    SYNTAX     DisplayString
    MAX-ACCESS read-write
    STATUS     current
    DESCRIPTION
            "-- empty --"
    ::= { hmStatusTcpIp 7 }

-- {NODE} 1.3.6.1.4.1.248.32.18.1.9.8
hmStatusTcpIpNetbios OBJECT IDENTIFIER ::= { hmStatusTcpIp 8 }

-- {SCALAR} 1.3.6.1.4.1.248.32.18.1.9.8.1
hmStatusTcpIpNetbiosLanRx OBJECT-TYPE
    SYNTAX     Counter32
    MAX-ACCESS read-only
    STATUS     current
    DESCRIPTION
            "-- empty --"
    ::= { hmStatusTcpIpNetbios 1 }

-- {SCALAR} 1.3.6.1.4.1.248.32.18.1.9.8.2
hmStatusTcpIpNetbiosLanTx OBJECT-TYPE
    SYNTAX     Counter32
    MAX-ACCESS read-only
    STATUS     current
    DESCRIPTION
            "-- empty --"
    ::= { hmStatusTcpIpNetbios 2 }

-- {SCALAR} 1.3.6.1.4.1.248.32.18.1.9.8.3
hmStatusTcpIpNetbiosWanRx OBJECT-TYPE
    SYNTAX     Counter32
    MAX-ACCESS read-only
    STATUS     current
    DESCRIPTION
            "-- empty --"
    ::= { hmStatusTcpIpNetbios 3 }

-- {SCALAR} 1.3.6.1.4.1.248.32.18.1.9.8.4
hmStatusTcpIpNetbiosWanTx OBJECT-TYPE
    SYNTAX     Counter32
    MAX-ACCESS read-only
    STATUS     current
    DESCRIPTION
            "-- empty --"
    ::= { hmStatusTcpIpNetbios 4 }

-- {SCALAR} 1.3.6.1.4.1.248.32.18.1.9.8.5
hmStatusTcpIpNetbiosRegisters OBJECT-TYPE
    SYNTAX     Counter32
    MAX-ACCESS read-only
    STATUS     current
    DESCRIPTION
            "-- empty --"
    ::= { hmStatusTcpIpNetbios 5 }

-- {SCALAR} 1.3.6.1.4.1.248.32.18.1.9.8.6
hmStatusTcpIpNetbiosConflicts OBJECT-TYPE
    SYNTAX     Counter32
    MAX-ACCESS read-only
    STATUS     current
    DESCRIPTION
            "-- empty --"
    ::= { hmStatusTcpIpNetbios 6 }

-- {SCALAR} 1.3.6.1.4.1.248.32.18.1.9.8.7
hmStatusTcpIpNetbiosReleases OBJECT-TYPE
    SYNTAX     Counter32
    MAX-ACCESS read-only
    STATUS     current
    DESCRIPTION
            "-- empty --"
    ::= { hmStatusTcpIpNetbios 7 }

-- {SCALAR} 1.3.6.1.4.1.248.32.18.1.9.8.8
hmStatusTcpIpNetbiosRefreshs OBJECT-TYPE
    SYNTAX     Counter32
    MAX-ACCESS read-only
    STATUS     current
    DESCRIPTION
            "-- empty --"
    ::= { hmStatusTcpIpNetbios 8 }

-- {SCALAR} 1.3.6.1.4.1.248.32.18.1.9.8.9
hmStatusTcpIpNetbiosTimeouts OBJECT-TYPE
    SYNTAX     Counter32
    MAX-ACCESS read-only
    STATUS     current
    DESCRIPTION
            "-- empty --"
    ::= { hmStatusTcpIpNetbios 9 }

-- {SCALAR} 1.3.6.1.4.1.248.32.18.1.9.8.10
hmStatusTcpIpNetbiosHosts OBJECT-TYPE
    SYNTAX     Integer32 (0..2147483647)
    MAX-ACCESS read-only
    STATUS     current
    DESCRIPTION
            "-- empty --"
    ::= { hmStatusTcpIpNetbios 10 }

-- {SCALAR} 1.3.6.1.4.1.248.32.18.1.9.8.11
hmStatusTcpIpNetbiosGroups OBJECT-TYPE
    SYNTAX     Integer32 (0..2147483647)
    MAX-ACCESS read-only
    STATUS     current
    DESCRIPTION
            "-- empty --"
    ::= { hmStatusTcpIpNetbios 11 }

-- {SCALAR} 1.3.6.1.4.1.248.32.18.1.9.8.12
hmStatusTcpIpNetbiosBNodes OBJECT-TYPE
    SYNTAX     Integer32 (0..2147483647)
    MAX-ACCESS read-only
    STATUS     current
    DESCRIPTION
            "-- empty --"
    ::= { hmStatusTcpIpNetbios 12 }

-- {SCALAR} 1.3.6.1.4.1.248.32.18.1.9.8.13
hmStatusTcpIpNetbiosPNodes OBJECT-TYPE
    SYNTAX     Integer32 (0..2147483647)
    MAX-ACCESS read-only
    STATUS     current
    DESCRIPTION
            "-- empty --"
    ::= { hmStatusTcpIpNetbios 13 }

-- {SCALAR} 1.3.6.1.4.1.248.32.18.1.9.8.14
hmStatusTcpIpNetbiosMNodes OBJECT-TYPE
    SYNTAX     Integer32 (0..2147483647)
    MAX-ACCESS read-only
    STATUS     current
    DESCRIPTION
            "-- empty --"
    ::= { hmStatusTcpIpNetbios 14 }

-- {SCALAR} 1.3.6.1.4.1.248.32.18.1.9.8.15
hmStatusTcpIpNetbiosWNodes OBJECT-TYPE
    SYNTAX     Integer32 (0..2147483647)
    MAX-ACCESS read-only
    STATUS     current
    DESCRIPTION
            "-- empty --"
    ::= { hmStatusTcpIpNetbios 15 }

-- {TABLE} 1.3.6.1.4.1.248.32.18.1.9.8.16
hmStatusTcpIpNetbiosPeersTable OBJECT-TYPE
    SYNTAX     SEQUENCE OF HmStatusTcpIpNetbiosPeersEntry
    MAX-ACCESS not-accessible
    STATUS     current
    DESCRIPTION
            "-- empty --"
    ::= { hmStatusTcpIpNetbios 16 }

-- {ROW} 1.3.6.1.4.1.248.32.18.1.9.8.16.1
hmStatusTcpIpNetbiosPeersEntry OBJECT-TYPE
    SYNTAX     HmStatusTcpIpNetbiosPeersEntry
    MAX-ACCESS not-accessible
    STATUS     current
    DESCRIPTION
            ""
    INDEX {
            hmStatusTcpIpNetbiosPeersEntryName
          }
    ::= { hmStatusTcpIpNetbiosPeersTable 1 }

HmStatusTcpIpNetbiosPeersEntry ::= SEQUENCE {
            hmStatusTcpIpNetbiosPeersEntryName DisplayString,
            hmStatusTcpIpNetbiosPeersEntryType INTEGER,
            hmStatusTcpIpNetbiosPeersEntryBackoff Integer32,
            hmStatusTcpIpNetbiosPeersEntryTime Integer32
    }

-- {COLUMN} 1.3.6.1.4.1.248.32.18.1.9.8.16.1.1
hmStatusTcpIpNetbiosPeersEntryName OBJECT-TYPE
    SYNTAX     DisplayString (SIZE(0..16))
    MAX-ACCESS read-only
    STATUS     current
    DESCRIPTION
            "-- empty --"
    ::= { hmStatusTcpIpNetbiosPeersEntry 1 }

-- {COLUMN} 1.3.6.1.4.1.248.32.18.1.9.8.16.1.2
hmStatusTcpIpNetbiosPeersEntryType OBJECT-TYPE
    SYNTAX     INTEGER {
                  eRouter (0),
                  eWorkstation (1)
            }
    MAX-ACCESS read-only
    STATUS     current
    DESCRIPTION
            "-- empty --"
    ::= { hmStatusTcpIpNetbiosPeersEntry 2 }

-- {COLUMN} 1.3.6.1.4.1.248.32.18.1.9.8.16.1.3
hmStatusTcpIpNetbiosPeersEntryBackoff OBJECT-TYPE
    SYNTAX     Integer32 (0..255)
    MAX-ACCESS read-only
    STATUS     current
    DESCRIPTION
            "-- empty --"
    ::= { hmStatusTcpIpNetbiosPeersEntry 3 }

-- {COLUMN} 1.3.6.1.4.1.248.32.18.1.9.8.16.1.4
hmStatusTcpIpNetbiosPeersEntryTime OBJECT-TYPE
    SYNTAX     Integer32 (0..65535)
    MAX-ACCESS read-only
    STATUS     current
    DESCRIPTION
            "-- empty --"
    ::= { hmStatusTcpIpNetbiosPeersEntry 4 }

-- {SCALAR} 1.3.6.1.4.1.248.32.18.1.9.8.17
hmStatusTcpIpNetbiosDeleteValues OBJECT-TYPE
    SYNTAX     DisplayString
    MAX-ACCESS read-write
    STATUS     current
    DESCRIPTION
            "-- empty --"
    ::= { hmStatusTcpIpNetbios 17 }

-- {TABLE} 1.3.6.1.4.1.248.32.18.1.9.8.18
hmStatusTcpIpNetbiosNetworksTable OBJECT-TYPE
    SYNTAX     SEQUENCE OF HmStatusTcpIpNetbiosNetworksEntry
    MAX-ACCESS not-accessible
    STATUS     current
    DESCRIPTION
            "-- empty --"
    ::= { hmStatusTcpIpNetbios 18 }

-- {ROW} 1.3.6.1.4.1.248.32.18.1.9.8.18.1
hmStatusTcpIpNetbiosNetworksEntry OBJECT-TYPE
    SYNTAX     HmStatusTcpIpNetbiosNetworksEntry
    MAX-ACCESS not-accessible
    STATUS     current
    DESCRIPTION
            ""
    INDEX {
            hmStatusTcpIpNetbiosNetworksEntryNetworkName
          }
    ::= { hmStatusTcpIpNetbiosNetworksTable 1 }

HmStatusTcpIpNetbiosNetworksEntry ::= SEQUENCE {
            hmStatusTcpIpNetbiosNetworksEntryNetworkName DisplayString,
            hmStatusTcpIpNetbiosNetworksEntryNtDomain DisplayString,
            hmStatusTcpIpNetbiosNetworksEntryRtgTag Integer32,
            hmStatusTcpIpNetbiosNetworksEntryVlanId Integer32,
            hmStatusTcpIpNetbiosNetworksEntryInterface INTEGER
    }

-- {COLUMN} 1.3.6.1.4.1.248.32.18.1.9.8.18.1.1
hmStatusTcpIpNetbiosNetworksEntryNetworkName OBJECT-TYPE
    SYNTAX     DisplayString (SIZE(0..16))
    MAX-ACCESS read-only
    STATUS     current
    DESCRIPTION
            "-- empty --"
    ::= { hmStatusTcpIpNetbiosNetworksEntry 1 }

-- {COLUMN} 1.3.6.1.4.1.248.32.18.1.9.8.18.1.2
hmStatusTcpIpNetbiosNetworksEntryNtDomain OBJECT-TYPE
    SYNTAX     DisplayString (SIZE(0..15))
    MAX-ACCESS read-only
    STATUS     current
    DESCRIPTION
            "-- empty --"
    ::= { hmStatusTcpIpNetbiosNetworksEntry 2 }

-- {COLUMN} 1.3.6.1.4.1.248.32.18.1.9.8.18.1.3
hmStatusTcpIpNetbiosNetworksEntryRtgTag OBJECT-TYPE
    SYNTAX     Integer32 (0..65535)
    MAX-ACCESS read-only
    STATUS     current
    DESCRIPTION
            "-- empty --"
    ::= { hmStatusTcpIpNetbiosNetworksEntry 3 }

-- {COLUMN} 1.3.6.1.4.1.248.32.18.1.9.8.18.1.5
hmStatusTcpIpNetbiosNetworksEntryVlanId OBJECT-TYPE
    SYNTAX     Integer32 (0..65535)
    MAX-ACCESS read-only
    STATUS     current
    DESCRIPTION
            "-- empty --"
    ::= { hmStatusTcpIpNetbiosNetworksEntry 5 }

-- {COLUMN} 1.3.6.1.4.1.248.32.18.1.9.8.18.1.7
hmStatusTcpIpNetbiosNetworksEntryInterface OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eAny (65535)
            }
    MAX-ACCESS read-only
    STATUS     current
    DESCRIPTION
            "-- empty --"
    ::= { hmStatusTcpIpNetbiosNetworksEntry 7 }

-- {TABLE} 1.3.6.1.4.1.248.32.18.1.9.8.19
hmStatusTcpIpNetbiosGroupListTable OBJECT-TYPE
    SYNTAX     SEQUENCE OF HmStatusTcpIpNetbiosGroupListEntry
    MAX-ACCESS not-accessible
    STATUS     current
    DESCRIPTION
            "-- empty --"
    ::= { hmStatusTcpIpNetbios 19 }

-- {ROW} 1.3.6.1.4.1.248.32.18.1.9.8.19.1
hmStatusTcpIpNetbiosGroupListEntry OBJECT-TYPE
    SYNTAX     HmStatusTcpIpNetbiosGroupListEntry
    MAX-ACCESS not-accessible
    STATUS     current
    DESCRIPTION
            ""
    INDEX {
            hmStatusTcpIpNetbiosGroupListEntryGroupDomain,
            hmStatusTcpIpNetbiosGroupListEntryType,
            hmStatusTcpIpNetbiosGroupListEntryIpAddress,
            hmStatusTcpIpNetbiosGroupListEntryRtgTag
          }
    ::= { hmStatusTcpIpNetbiosGroupListTable 1 }

HmStatusTcpIpNetbiosGroupListEntry ::= SEQUENCE {
            hmStatusTcpIpNetbiosGroupListEntryGroupDomain DisplayString,
            hmStatusTcpIpNetbiosGroupListEntryType DisplayString,
            hmStatusTcpIpNetbiosGroupListEntryIpAddress IpAddress,
            hmStatusTcpIpNetbiosGroupListEntryPeer DisplayString,
            hmStatusTcpIpNetbiosGroupListEntryTimeout Integer32,
            hmStatusTcpIpNetbiosGroupListEntryFlags DisplayString,
            hmStatusTcpIpNetbiosGroupListEntryNetworkName DisplayString,
            hmStatusTcpIpNetbiosGroupListEntryRtgTag Integer32
    }

-- {COLUMN} 1.3.6.1.4.1.248.32.18.1.9.8.19.1.1
hmStatusTcpIpNetbiosGroupListEntryGroupDomain OBJECT-TYPE
    SYNTAX     DisplayString (SIZE(0..15))
    MAX-ACCESS read-only
    STATUS     current
    DESCRIPTION
            "-- empty --"
    ::= { hmStatusTcpIpNetbiosGroupListEntry 1 }

-- {COLUMN} 1.3.6.1.4.1.248.32.18.1.9.8.19.1.2
hmStatusTcpIpNetbiosGroupListEntryType OBJECT-TYPE
    SYNTAX     DisplayString (SIZE(0..1))
    MAX-ACCESS read-only
    STATUS     current
    DESCRIPTION
            "-- empty --"
    ::= { hmStatusTcpIpNetbiosGroupListEntry 2 }

-- {COLUMN} 1.3.6.1.4.1.248.32.18.1.9.8.19.1.3
hmStatusTcpIpNetbiosGroupListEntryIpAddress OBJECT-TYPE
    SYNTAX     IpAddress
    MAX-ACCESS read-only
    STATUS     current
    DESCRIPTION
            "-- empty --"
    ::= { hmStatusTcpIpNetbiosGroupListEntry 3 }

-- {COLUMN} 1.3.6.1.4.1.248.32.18.1.9.8.19.1.4
hmStatusTcpIpNetbiosGroupListEntryPeer OBJECT-TYPE
    SYNTAX     DisplayString (SIZE(0..16))
    MAX-ACCESS read-only
    STATUS     current
    DESCRIPTION
            "-- empty --"
    ::= { hmStatusTcpIpNetbiosGroupListEntry 4 }

-- {COLUMN} 1.3.6.1.4.1.248.32.18.1.9.8.19.1.5
hmStatusTcpIpNetbiosGroupListEntryTimeout OBJECT-TYPE
    SYNTAX     Integer32 (0..2147483647)
    MAX-ACCESS read-only
    STATUS     current
    DESCRIPTION
            "-- empty --"
    ::= { hmStatusTcpIpNetbiosGroupListEntry 5 }

-- {COLUMN} 1.3.6.1.4.1.248.32.18.1.9.8.19.1.6
hmStatusTcpIpNetbiosGroupListEntryFlags OBJECT-TYPE
    SYNTAX     DisplayString (SIZE(0..2))
    MAX-ACCESS read-only
    STATUS     current
    DESCRIPTION
            "-- empty --"
    ::= { hmStatusTcpIpNetbiosGroupListEntry 6 }

-- {COLUMN} 1.3.6.1.4.1.248.32.18.1.9.8.19.1.7
hmStatusTcpIpNetbiosGroupListEntryNetworkName OBJECT-TYPE
    SYNTAX     DisplayString (SIZE(0..16))
    MAX-ACCESS read-only
    STATUS     current
    DESCRIPTION
            "-- empty --"
    ::= { hmStatusTcpIpNetbiosGroupListEntry 7 }

-- {COLUMN} 1.3.6.1.4.1.248.32.18.1.9.8.19.1.8
hmStatusTcpIpNetbiosGroupListEntryRtgTag OBJECT-TYPE
    SYNTAX     Integer32 (0..65535)
    MAX-ACCESS read-only
    STATUS     current
    DESCRIPTION
            "-- empty --"
    ::= { hmStatusTcpIpNetbiosGroupListEntry 8 }

-- {TABLE} 1.3.6.1.4.1.248.32.18.1.9.8.20
hmStatusTcpIpNetbiosHostListTable OBJECT-TYPE
    SYNTAX     SEQUENCE OF HmStatusTcpIpNetbiosHostListEntry
    MAX-ACCESS not-accessible
    STATUS     current
    DESCRIPTION
            "-- empty --"
    ::= { hmStatusTcpIpNetbios 20 }

-- {ROW} 1.3.6.1.4.1.248.32.18.1.9.8.20.1
hmStatusTcpIpNetbiosHostListEntry OBJECT-TYPE
    SYNTAX     HmStatusTcpIpNetbiosHostListEntry
    MAX-ACCESS not-accessible
    STATUS     current
    DESCRIPTION
            ""
    INDEX {
            hmStatusTcpIpNetbiosHostListEntryName,
            hmStatusTcpIpNetbiosHostListEntryType,
            hmStatusTcpIpNetbiosHostListEntryIpAddress,
            hmStatusTcpIpNetbiosHostListEntryRtgTag
          }
    ::= { hmStatusTcpIpNetbiosHostListTable 1 }

HmStatusTcpIpNetbiosHostListEntry ::= SEQUENCE {
            hmStatusTcpIpNetbiosHostListEntryName DisplayString,
            hmStatusTcpIpNetbiosHostListEntryType DisplayString,
            hmStatusTcpIpNetbiosHostListEntryIpAddress IpAddress,
            hmStatusTcpIpNetbiosHostListEntryPeer DisplayString,
            hmStatusTcpIpNetbiosHostListEntryTimeout Integer32,
            hmStatusTcpIpNetbiosHostListEntryFlags DisplayString,
            hmStatusTcpIpNetbiosHostListEntryNetworkName DisplayString,
            hmStatusTcpIpNetbiosHostListEntryRtgTag Integer32
    }

-- {COLUMN} 1.3.6.1.4.1.248.32.18.1.9.8.20.1.1
hmStatusTcpIpNetbiosHostListEntryName OBJECT-TYPE
    SYNTAX     DisplayString (SIZE(0..15))
    MAX-ACCESS read-only
    STATUS     current
    DESCRIPTION
            "-- empty --"
    ::= { hmStatusTcpIpNetbiosHostListEntry 1 }

-- {COLUMN} 1.3.6.1.4.1.248.32.18.1.9.8.20.1.2
hmStatusTcpIpNetbiosHostListEntryType OBJECT-TYPE
    SYNTAX     DisplayString (SIZE(0..1))
    MAX-ACCESS read-only
    STATUS     current
    DESCRIPTION
            "-- empty --"
    ::= { hmStatusTcpIpNetbiosHostListEntry 2 }

-- {COLUMN} 1.3.6.1.4.1.248.32.18.1.9.8.20.1.3
hmStatusTcpIpNetbiosHostListEntryIpAddress OBJECT-TYPE
    SYNTAX     IpAddress
    MAX-ACCESS read-only
    STATUS     current
    DESCRIPTION
            "-- empty --"
    ::= { hmStatusTcpIpNetbiosHostListEntry 3 }

-- {COLUMN} 1.3.6.1.4.1.248.32.18.1.9.8.20.1.4
hmStatusTcpIpNetbiosHostListEntryPeer OBJECT-TYPE
    SYNTAX     DisplayString (SIZE(0..16))
    MAX-ACCESS read-only
    STATUS     current
    DESCRIPTION
            "-- empty --"
    ::= { hmStatusTcpIpNetbiosHostListEntry 4 }

-- {COLUMN} 1.3.6.1.4.1.248.32.18.1.9.8.20.1.5
hmStatusTcpIpNetbiosHostListEntryTimeout OBJECT-TYPE
    SYNTAX     Integer32 (0..2147483647)
    MAX-ACCESS read-only
    STATUS     current
    DESCRIPTION
            "-- empty --"
    ::= { hmStatusTcpIpNetbiosHostListEntry 5 }

-- {COLUMN} 1.3.6.1.4.1.248.32.18.1.9.8.20.1.6
hmStatusTcpIpNetbiosHostListEntryFlags OBJECT-TYPE
    SYNTAX     DisplayString (SIZE(0..2))
    MAX-ACCESS read-only
    STATUS     current
    DESCRIPTION
            "-- empty --"
    ::= { hmStatusTcpIpNetbiosHostListEntry 6 }

-- {COLUMN} 1.3.6.1.4.1.248.32.18.1.9.8.20.1.7
hmStatusTcpIpNetbiosHostListEntryNetworkName OBJECT-TYPE
    SYNTAX     DisplayString (SIZE(0..16))
    MAX-ACCESS read-only
    STATUS     current
    DESCRIPTION
            "-- empty --"
    ::= { hmStatusTcpIpNetbiosHostListEntry 7 }

-- {COLUMN} 1.3.6.1.4.1.248.32.18.1.9.8.20.1.8
hmStatusTcpIpNetbiosHostListEntryRtgTag OBJECT-TYPE
    SYNTAX     Integer32 (0..65535)
    MAX-ACCESS read-only
    STATUS     current
    DESCRIPTION
            "-- empty --"
    ::= { hmStatusTcpIpNetbiosHostListEntry 8 }

-- {TABLE} 1.3.6.1.4.1.248.32.18.1.9.8.21
hmStatusTcpIpNetbiosServerListTable OBJECT-TYPE
    SYNTAX     SEQUENCE OF HmStatusTcpIpNetbiosServerListEntry
    MAX-ACCESS not-accessible
    STATUS     current
    DESCRIPTION
            "-- empty --"
    ::= { hmStatusTcpIpNetbios 21 }

-- {ROW} 1.3.6.1.4.1.248.32.18.1.9.8.21.1
hmStatusTcpIpNetbiosServerListEntry OBJECT-TYPE
    SYNTAX     HmStatusTcpIpNetbiosServerListEntry
    MAX-ACCESS not-accessible
    STATUS     current
    DESCRIPTION
            ""
    INDEX {
            hmStatusTcpIpNetbiosServerListEntryHost,
            hmStatusTcpIpNetbiosServerListEntryGroupDomain,
            hmStatusTcpIpNetbiosServerListEntryIpAddress,
            hmStatusTcpIpNetbiosServerListEntryRtgTag
          }
    ::= { hmStatusTcpIpNetbiosServerListTable 1 }

HmStatusTcpIpNetbiosServerListEntry ::= SEQUENCE {
            hmStatusTcpIpNetbiosServerListEntryHost DisplayString,
            hmStatusTcpIpNetbiosServerListEntryGroupDomain DisplayString,
            hmStatusTcpIpNetbiosServerListEntryIpAddress DisplayString,
            hmStatusTcpIpNetbiosServerListEntryOsVer DisplayString,
            hmStatusTcpIpNetbiosServerListEntrySmbVer DisplayString,
            hmStatusTcpIpNetbiosServerListEntryServerTyp DisplayString,
            hmStatusTcpIpNetbiosServerListEntryPeer DisplayString,
            hmStatusTcpIpNetbiosServerListEntryTimeout Integer32,
            hmStatusTcpIpNetbiosServerListEntryFlags DisplayString,
            hmStatusTcpIpNetbiosServerListEntryNetworkName DisplayString,
            hmStatusTcpIpNetbiosServerListEntryRtgTag Integer32
    }

-- {COLUMN} 1.3.6.1.4.1.248.32.18.1.9.8.21.1.1
hmStatusTcpIpNetbiosServerListEntryHost OBJECT-TYPE
    SYNTAX     DisplayString (SIZE(0..15))
    MAX-ACCESS read-only
    STATUS     current
    DESCRIPTION
            "-- empty --"
    ::= { hmStatusTcpIpNetbiosServerListEntry 1 }

-- {COLUMN} 1.3.6.1.4.1.248.32.18.1.9.8.21.1.2
hmStatusTcpIpNetbiosServerListEntryGroupDomain OBJECT-TYPE
    SYNTAX     DisplayString (SIZE(0..16))
    MAX-ACCESS read-only
    STATUS     current
    DESCRIPTION
            "-- empty --"
    ::= { hmStatusTcpIpNetbiosServerListEntry 2 }

-- {COLUMN} 1.3.6.1.4.1.248.32.18.1.9.8.21.1.4
hmStatusTcpIpNetbiosServerListEntryIpAddress OBJECT-TYPE
    SYNTAX     DisplayString (SIZE(0..15))
    MAX-ACCESS read-only
    STATUS     current
    DESCRIPTION
            "-- empty --"
    ::= { hmStatusTcpIpNetbiosServerListEntry 4 }

-- {COLUMN} 1.3.6.1.4.1.248.32.18.1.9.8.21.1.5
hmStatusTcpIpNetbiosServerListEntryOsVer OBJECT-TYPE
    SYNTAX     DisplayString (SIZE(0..2))
    MAX-ACCESS read-only
    STATUS     current
    DESCRIPTION
            "-- empty --"
    ::= { hmStatusTcpIpNetbiosServerListEntry 5 }

-- {COLUMN} 1.3.6.1.4.1.248.32.18.1.9.8.21.1.6
hmStatusTcpIpNetbiosServerListEntrySmbVer OBJECT-TYPE
    SYNTAX     DisplayString (SIZE(0..2))
    MAX-ACCESS read-only
    STATUS     current
    DESCRIPTION
            "-- empty --"
    ::= { hmStatusTcpIpNetbiosServerListEntry 6 }

-- {COLUMN} 1.3.6.1.4.1.248.32.18.1.9.8.21.1.7
hmStatusTcpIpNetbiosServerListEntryServerTyp OBJECT-TYPE
    SYNTAX     DisplayString (SIZE(0..4))
    MAX-ACCESS read-only
    STATUS     current
    DESCRIPTION
            "-- empty --"
    ::= { hmStatusTcpIpNetbiosServerListEntry 7 }

-- {COLUMN} 1.3.6.1.4.1.248.32.18.1.9.8.21.1.8
hmStatusTcpIpNetbiosServerListEntryPeer OBJECT-TYPE
    SYNTAX     DisplayString (SIZE(0..16))
    MAX-ACCESS read-only
    STATUS     current
    DESCRIPTION
            "-- empty --"
    ::= { hmStatusTcpIpNetbiosServerListEntry 8 }

-- {COLUMN} 1.3.6.1.4.1.248.32.18.1.9.8.21.1.9
hmStatusTcpIpNetbiosServerListEntryTimeout OBJECT-TYPE
    SYNTAX     Integer32 (0..2147483647)
    MAX-ACCESS read-only
    STATUS     current
    DESCRIPTION
            "-- empty --"
    ::= { hmStatusTcpIpNetbiosServerListEntry 9 }

-- {COLUMN} 1.3.6.1.4.1.248.32.18.1.9.8.21.1.10
hmStatusTcpIpNetbiosServerListEntryFlags OBJECT-TYPE
    SYNTAX     DisplayString (SIZE(0..2))
    MAX-ACCESS read-only
    STATUS     current
    DESCRIPTION
            "-- empty --"
    ::= { hmStatusTcpIpNetbiosServerListEntry 10 }

-- {COLUMN} 1.3.6.1.4.1.248.32.18.1.9.8.21.1.11
hmStatusTcpIpNetbiosServerListEntryNetworkName OBJECT-TYPE
    SYNTAX     DisplayString (SIZE(0..16))
    MAX-ACCESS read-only
    STATUS     current
    DESCRIPTION
            "-- empty --"
    ::= { hmStatusTcpIpNetbiosServerListEntry 11 }

-- {COLUMN} 1.3.6.1.4.1.248.32.18.1.9.8.21.1.12
hmStatusTcpIpNetbiosServerListEntryRtgTag OBJECT-TYPE
    SYNTAX     Integer32 (0..65535)
    MAX-ACCESS read-only
    STATUS     current
    DESCRIPTION
            "-- empty --"
    ::= { hmStatusTcpIpNetbiosServerListEntry 12 }

-- {TABLE} 1.3.6.1.4.1.248.32.18.1.9.8.22
hmStatusTcpIpNetbiosBrowserListTable OBJECT-TYPE
    SYNTAX     SEQUENCE OF HmStatusTcpIpNetbiosBrowserListEntry
    MAX-ACCESS not-accessible
    STATUS     current
    DESCRIPTION
            "-- empty --"
    ::= { hmStatusTcpIpNetbios 22 }

-- {ROW} 1.3.6.1.4.1.248.32.18.1.9.8.22.1
hmStatusTcpIpNetbiosBrowserListEntry OBJECT-TYPE
    SYNTAX     HmStatusTcpIpNetbiosBrowserListEntry
    MAX-ACCESS not-accessible
    STATUS     current
    DESCRIPTION
            ""
    INDEX {
            hmStatusTcpIpNetbiosBrowserListEntryBrowser,
            hmStatusTcpIpNetbiosBrowserListEntryGroupDomain,
            hmStatusTcpIpNetbiosBrowserListEntryIpAddress,
            hmStatusTcpIpNetbiosBrowserListEntryRtgTag
          }
    ::= { hmStatusTcpIpNetbiosBrowserListTable 1 }

HmStatusTcpIpNetbiosBrowserListEntry ::= SEQUENCE {
            hmStatusTcpIpNetbiosBrowserListEntryBrowser DisplayString,
            hmStatusTcpIpNetbiosBrowserListEntryGroupDomain DisplayString,
            hmStatusTcpIpNetbiosBrowserListEntryIpAddress DisplayString,
            hmStatusTcpIpNetbiosBrowserListEntryOsVer DisplayString,
            hmStatusTcpIpNetbiosBrowserListEntryServerTyp DisplayString,
            hmStatusTcpIpNetbiosBrowserListEntryPeer DisplayString,
            hmStatusTcpIpNetbiosBrowserListEntryTimeout Integer32,
            hmStatusTcpIpNetbiosBrowserListEntryFlags DisplayString,
            hmStatusTcpIpNetbiosBrowserListEntryNetworkName DisplayString,
            hmStatusTcpIpNetbiosBrowserListEntryRtgTag Integer32
    }

-- {COLUMN} 1.3.6.1.4.1.248.32.18.1.9.8.22.1.1
hmStatusTcpIpNetbiosBrowserListEntryBrowser OBJECT-TYPE
    SYNTAX     DisplayString (SIZE(0..15))
    MAX-ACCESS read-only
    STATUS     current
    DESCRIPTION
            "-- empty --"
    ::= { hmStatusTcpIpNetbiosBrowserListEntry 1 }

-- {COLUMN} 1.3.6.1.4.1.248.32.18.1.9.8.22.1.2
hmStatusTcpIpNetbiosBrowserListEntryGroupDomain OBJECT-TYPE
    SYNTAX     DisplayString (SIZE(0..16))
    MAX-ACCESS read-only
    STATUS     current
    DESCRIPTION
            "-- empty --"
    ::= { hmStatusTcpIpNetbiosBrowserListEntry 2 }

-- {COLUMN} 1.3.6.1.4.1.248.32.18.1.9.8.22.1.4
hmStatusTcpIpNetbiosBrowserListEntryIpAddress OBJECT-TYPE
    SYNTAX     DisplayString (SIZE(0..15))
    MAX-ACCESS read-only
    STATUS     current
    DESCRIPTION
            "-- empty --"
    ::= { hmStatusTcpIpNetbiosBrowserListEntry 4 }

-- {COLUMN} 1.3.6.1.4.1.248.32.18.1.9.8.22.1.5
hmStatusTcpIpNetbiosBrowserListEntryOsVer OBJECT-TYPE
    SYNTAX     DisplayString (SIZE(0..2))
    MAX-ACCESS read-only
    STATUS     current
    DESCRIPTION
            "-- empty --"
    ::= { hmStatusTcpIpNetbiosBrowserListEntry 5 }

-- {COLUMN} 1.3.6.1.4.1.248.32.18.1.9.8.22.1.7
hmStatusTcpIpNetbiosBrowserListEntryServerTyp OBJECT-TYPE
    SYNTAX     DisplayString (SIZE(0..4))
    MAX-ACCESS read-only
    STATUS     current
    DESCRIPTION
            "-- empty --"
    ::= { hmStatusTcpIpNetbiosBrowserListEntry 7 }

-- {COLUMN} 1.3.6.1.4.1.248.32.18.1.9.8.22.1.8
hmStatusTcpIpNetbiosBrowserListEntryPeer OBJECT-TYPE
    SYNTAX     DisplayString (SIZE(0..16))
    MAX-ACCESS read-only
    STATUS     current
    DESCRIPTION
            "-- empty --"
    ::= { hmStatusTcpIpNetbiosBrowserListEntry 8 }

-- {COLUMN} 1.3.6.1.4.1.248.32.18.1.9.8.22.1.9
hmStatusTcpIpNetbiosBrowserListEntryTimeout OBJECT-TYPE
    SYNTAX     Integer32 (0..2147483647)
    MAX-ACCESS read-only
    STATUS     current
    DESCRIPTION
            "-- empty --"
    ::= { hmStatusTcpIpNetbiosBrowserListEntry 9 }

-- {COLUMN} 1.3.6.1.4.1.248.32.18.1.9.8.22.1.10
hmStatusTcpIpNetbiosBrowserListEntryFlags OBJECT-TYPE
    SYNTAX     DisplayString (SIZE(0..2))
    MAX-ACCESS read-only
    STATUS     current
    DESCRIPTION
            "-- empty --"
    ::= { hmStatusTcpIpNetbiosBrowserListEntry 10 }

-- {COLUMN} 1.3.6.1.4.1.248.32.18.1.9.8.22.1.11
hmStatusTcpIpNetbiosBrowserListEntryNetworkName OBJECT-TYPE
    SYNTAX     DisplayString (SIZE(0..16))
    MAX-ACCESS read-only
    STATUS     current
    DESCRIPTION
            "-- empty --"
    ::= { hmStatusTcpIpNetbiosBrowserListEntry 11 }

-- {COLUMN} 1.3.6.1.4.1.248.32.18.1.9.8.22.1.12
hmStatusTcpIpNetbiosBrowserListEntryRtgTag OBJECT-TYPE
    SYNTAX     Integer32 (0..65535)
    MAX-ACCESS read-only
    STATUS     current
    DESCRIPTION
            "-- empty --"
    ::= { hmStatusTcpIpNetbiosBrowserListEntry 12 }

-- {NODE} 1.3.6.1.4.1.248.32.18.1.9.9
hmStatusTcpIpDns OBJECT IDENTIFIER ::= { hmStatusTcpIp 9 }

-- {SCALAR} 1.3.6.1.4.1.248.32.18.1.9.9.1
hmStatusTcpIpDnsLanRx OBJECT-TYPE
    SYNTAX     Counter32
    MAX-ACCESS read-only
    STATUS     current
    DESCRIPTION
            "-- empty --"
    ::= { hmStatusTcpIpDns 1 }

-- {SCALAR} 1.3.6.1.4.1.248.32.18.1.9.9.2
hmStatusTcpIpDnsLanTx OBJECT-TYPE
    SYNTAX     Counter32
    MAX-ACCESS read-only
    STATUS     current
    DESCRIPTION
            "-- empty --"
    ::= { hmStatusTcpIpDns 2 }

-- {SCALAR} 1.3.6.1.4.1.248.32.18.1.9.9.3
hmStatusTcpIpDnsWanRx OBJECT-TYPE
    SYNTAX     Counter32
    MAX-ACCESS read-only
    STATUS     current
    DESCRIPTION
            "-- empty --"
    ::= { hmStatusTcpIpDns 3 }

-- {SCALAR} 1.3.6.1.4.1.248.32.18.1.9.9.4
hmStatusTcpIpDnsWanTx OBJECT-TYPE
    SYNTAX     Counter32
    MAX-ACCESS read-only
    STATUS     current
    DESCRIPTION
            "-- empty --"
    ::= { hmStatusTcpIpDns 4 }

-- {SCALAR} 1.3.6.1.4.1.248.32.18.1.9.9.5
hmStatusTcpIpDnsForwarded OBJECT-TYPE
    SYNTAX     Counter32
    MAX-ACCESS read-only
    STATUS     current
    DESCRIPTION
            "-- empty --"
    ::= { hmStatusTcpIpDns 5 }

-- {SCALAR} 1.3.6.1.4.1.248.32.18.1.9.9.6
hmStatusTcpIpDnsErrors OBJECT-TYPE
    SYNTAX     Counter32
    MAX-ACCESS read-only
    STATUS     current
    DESCRIPTION
            "-- empty --"
    ::= { hmStatusTcpIpDns 6 }

-- {SCALAR} 1.3.6.1.4.1.248.32.18.1.9.9.7
hmStatusTcpIpDnsDnsAccess OBJECT-TYPE
    SYNTAX     Counter32
    MAX-ACCESS read-only
    STATUS     current
    DESCRIPTION
            "-- empty --"
    ::= { hmStatusTcpIpDns 7 }

-- {SCALAR} 1.3.6.1.4.1.248.32.18.1.9.9.8
hmStatusTcpIpDnsDhcpAccess OBJECT-TYPE
    SYNTAX     Counter32
    MAX-ACCESS read-only
    STATUS     current
    DESCRIPTION
            "-- empty --"
    ::= { hmStatusTcpIpDns 8 }

-- {SCALAR} 1.3.6.1.4.1.248.32.18.1.9.9.9
hmStatusTcpIpDnsNetbiosAccess OBJECT-TYPE
    SYNTAX     Counter32
    MAX-ACCESS read-only
    STATUS     current
    DESCRIPTION
            "-- empty --"
    ::= { hmStatusTcpIpDns 9 }

-- {SCALAR} 1.3.6.1.4.1.248.32.18.1.9.9.10
hmStatusTcpIpDnsFilter OBJECT-TYPE
    SYNTAX     Counter32
    MAX-ACCESS read-only
    STATUS     current
    DESCRIPTION
            "-- empty --"
    ::= { hmStatusTcpIpDns 10 }

-- {TABLE} 1.3.6.1.4.1.248.32.18.1.9.9.11
hmStatusTcpIpDnsHitListTable OBJECT-TYPE
    SYNTAX     SEQUENCE OF HmStatusTcpIpDnsHitListEntry
    MAX-ACCESS not-accessible
    STATUS     current
    DESCRIPTION
            "-- empty --"
    ::= { hmStatusTcpIpDns 11 }

-- {ROW} 1.3.6.1.4.1.248.32.18.1.9.9.11.1
hmStatusTcpIpDnsHitListEntry OBJECT-TYPE
    SYNTAX     HmStatusTcpIpDnsHitListEntry
    MAX-ACCESS not-accessible
    STATUS     current
    DESCRIPTION
            ""
    INDEX {
            hmStatusTcpIpDnsHitListEntryDomain
          }
    ::= { hmStatusTcpIpDnsHitListTable 1 }

HmStatusTcpIpDnsHitListEntry ::= SEQUENCE {
            hmStatusTcpIpDnsHitListEntryDomain DisplayString,
            hmStatusTcpIpDnsHitListEntryRequests Integer32,
            hmStatusTcpIpDnsHitListEntryTime DisplayString,
            hmStatusTcpIpDnsHitListEntryIpAddress IpAddress,
            hmStatusTcpIpDnsHitListEntryIpv6Address DisplayString
    }

-- {COLUMN} 1.3.6.1.4.1.248.32.18.1.9.9.11.1.1
hmStatusTcpIpDnsHitListEntryDomain OBJECT-TYPE
    SYNTAX     DisplayString (SIZE(0..64))
    MAX-ACCESS read-only
    STATUS     current
    DESCRIPTION
            "-- empty --"
    ::= { hmStatusTcpIpDnsHitListEntry 1 }

-- {COLUMN} 1.3.6.1.4.1.248.32.18.1.9.9.11.1.2
hmStatusTcpIpDnsHitListEntryRequests OBJECT-TYPE
    SYNTAX     Integer32 (0..2147483647)
    MAX-ACCESS read-only
    STATUS     current
    DESCRIPTION
            "-- empty --"
    ::= { hmStatusTcpIpDnsHitListEntry 2 }

-- {COLUMN} 1.3.6.1.4.1.248.32.18.1.9.9.11.1.3
hmStatusTcpIpDnsHitListEntryTime OBJECT-TYPE
    SYNTAX     DisplayString (SIZE(0..20))
    MAX-ACCESS read-only
    STATUS     current
    DESCRIPTION
            "-- empty --"
    ::= { hmStatusTcpIpDnsHitListEntry 3 }

-- {COLUMN} 1.3.6.1.4.1.248.32.18.1.9.9.11.1.4
hmStatusTcpIpDnsHitListEntryIpAddress OBJECT-TYPE
    SYNTAX     IpAddress
    MAX-ACCESS read-only
    STATUS     current
    DESCRIPTION
            "-- empty --"
    ::= { hmStatusTcpIpDnsHitListEntry 4 }

-- {COLUMN} 1.3.6.1.4.1.248.32.18.1.9.9.11.1.5
hmStatusTcpIpDnsHitListEntryIpv6Address OBJECT-TYPE
    SYNTAX     DisplayString (SIZE(0..255))
    MAX-ACCESS read-only
    STATUS     current
    DESCRIPTION
            "-- empty --"
    ::= { hmStatusTcpIpDnsHitListEntry 5 }

-- {SCALAR} 1.3.6.1.4.1.248.32.18.1.9.9.12
hmStatusTcpIpDnsDeleteValues OBJECT-TYPE
    SYNTAX     DisplayString
    MAX-ACCESS read-write
    STATUS     current
    DESCRIPTION
            "-- empty --"
    ::= { hmStatusTcpIpDns 12 }

-- {NODE} 1.3.6.1.4.1.248.32.18.1.9.10
hmStatusTcpIpHttp OBJECT IDENTIFIER ::= { hmStatusTcpIp 10 }

-- {SCALAR} 1.3.6.1.4.1.248.32.18.1.9.10.1
hmStatusTcpIpHttpHttpAccesses OBJECT-TYPE
    SYNTAX     Counter32
    MAX-ACCESS read-only
    STATUS     current
    DESCRIPTION
            "-- empty --"
    ::= { hmStatusTcpIpHttp 1 }

-- {SCALAR} 1.3.6.1.4.1.248.32.18.1.9.10.2
hmStatusTcpIpHttpHttpNotfoundErrors OBJECT-TYPE
    SYNTAX     Counter32
    MAX-ACCESS read-only
    STATUS     current
    DESCRIPTION
            "-- empty --"
    ::= { hmStatusTcpIpHttp 2 }

-- {SCALAR} 1.3.6.1.4.1.248.32.18.1.9.10.3
hmStatusTcpIpHttpHttpAuthenticationErrors OBJECT-TYPE
    SYNTAX     Counter32
    MAX-ACCESS read-only
    STATUS     current
    DESCRIPTION
            "-- empty --"
    ::= { hmStatusTcpIpHttp 3 }

-- {SCALAR} 1.3.6.1.4.1.248.32.18.1.9.10.4
hmStatusTcpIpHttpHttpProtocolErrors OBJECT-TYPE
    SYNTAX     Counter32
    MAX-ACCESS read-only
    STATUS     current
    DESCRIPTION
            "-- empty --"
    ::= { hmStatusTcpIpHttp 4 }

-- {SCALAR} 1.3.6.1.4.1.248.32.18.1.9.10.5
hmStatusTcpIpHttpDeleteValues OBJECT-TYPE
    SYNTAX     DisplayString
    MAX-ACCESS read-write
    STATUS     current
    DESCRIPTION
            "-- empty --"
    ::= { hmStatusTcpIpHttp 5 }

-- {SCALAR} 1.3.6.1.4.1.248.32.18.1.9.10.6
hmStatusTcpIpHttpHttpsAccesses OBJECT-TYPE
    SYNTAX     Counter32
    MAX-ACCESS read-only
    STATUS     current
    DESCRIPTION
            "-- empty --"
    ::= { hmStatusTcpIpHttp 6 }

-- {TABLE} 1.3.6.1.4.1.248.32.18.1.9.10.7
hmStatusTcpIpHttpAgentListTable OBJECT-TYPE
    SYNTAX     SEQUENCE OF HmStatusTcpIpHttpAgentListEntry
    MAX-ACCESS not-accessible
    STATUS     current
    DESCRIPTION
            "-- empty --"
    ::= { hmStatusTcpIpHttp 7 }

-- {ROW} 1.3.6.1.4.1.248.32.18.1.9.10.7.1
hmStatusTcpIpHttpAgentListEntry OBJECT-TYPE
    SYNTAX     HmStatusTcpIpHttpAgentListEntry
    MAX-ACCESS not-accessible
    STATUS     current
    DESCRIPTION
            ""
    INDEX {
            hmStatusTcpIpHttpAgentListEntryAgentName
          }
    ::= { hmStatusTcpIpHttpAgentListTable 1 }

HmStatusTcpIpHttpAgentListEntry ::= SEQUENCE {
            hmStatusTcpIpHttpAgentListEntryAgentName DisplayString,
            hmStatusTcpIpHttpAgentListEntryAccesses Integer32
    }

-- {COLUMN} 1.3.6.1.4.1.248.32.18.1.9.10.7.1.1
hmStatusTcpIpHttpAgentListEntryAgentName OBJECT-TYPE
    SYNTAX     DisplayString (SIZE(0..67))
    MAX-ACCESS read-only
    STATUS     current
    DESCRIPTION
            "-- empty --"
    ::= { hmStatusTcpIpHttpAgentListEntry 1 }

-- {COLUMN} 1.3.6.1.4.1.248.32.18.1.9.10.7.1.2
hmStatusTcpIpHttpAgentListEntryAccesses OBJECT-TYPE
    SYNTAX     Integer32 (0..2147483647)
    MAX-ACCESS read-only
    STATUS     current
    DESCRIPTION
            "-- empty --"
    ::= { hmStatusTcpIpHttpAgentListEntry 2 }

-- {TABLE} 1.3.6.1.4.1.248.32.18.1.9.10.8
hmStatusTcpIpHttpActiveTunnelsTable OBJECT-TYPE
    SYNTAX     SEQUENCE OF HmStatusTcpIpHttpActiveTunnelsEntry
    MAX-ACCESS not-accessible
    STATUS     current
    DESCRIPTION
            "-- empty --"
    ::= { hmStatusTcpIpHttp 8 }

-- {ROW} 1.3.6.1.4.1.248.32.18.1.9.10.8.1
hmStatusTcpIpHttpActiveTunnelsEntry OBJECT-TYPE
    SYNTAX     HmStatusTcpIpHttpActiveTunnelsEntry
    MAX-ACCESS not-accessible
    STATUS     current
    DESCRIPTION
            ""
    INDEX {
            hmStatusTcpIpHttpActiveTunnelsEntryIndex
          }
    ::= { hmStatusTcpIpHttpActiveTunnelsTable 1 }

HmStatusTcpIpHttpActiveTunnelsEntry ::= SEQUENCE {
            hmStatusTcpIpHttpActiveTunnelsEntryIndex Integer32,
            hmStatusTcpIpHttpActiveTunnelsEntryRemoteAddress IpAddress,
            hmStatusTcpIpHttpActiveTunnelsEntryRemotePort Integer32,
            hmStatusTcpIpHttpActiveTunnelsEntryLocalHost DisplayString,
            hmStatusTcpIpHttpActiveTunnelsEntryLocalPort Integer32,
            hmStatusTcpIpHttpActiveTunnelsEntryIdleTime Integer32,
            hmStatusTcpIpHttpActiveTunnelsEntryLocalRtgTag Integer32,
            hmStatusTcpIpHttpActiveTunnelsEntryNumConnections Integer32,
            hmStatusTcpIpHttpActiveTunnelsEntryState INTEGER
    }

-- {COLUMN} 1.3.6.1.4.1.248.32.18.1.9.10.8.1.1
hmStatusTcpIpHttpActiveTunnelsEntryIndex OBJECT-TYPE
    SYNTAX     Integer32 (0..2147483647)
    MAX-ACCESS read-only
    STATUS     current
    DESCRIPTION
            "-- empty --"
    ::= { hmStatusTcpIpHttpActiveTunnelsEntry 1 }

-- {COLUMN} 1.3.6.1.4.1.248.32.18.1.9.10.8.1.2
hmStatusTcpIpHttpActiveTunnelsEntryRemoteAddress OBJECT-TYPE
    SYNTAX     IpAddress
    MAX-ACCESS read-only
    STATUS     current
    DESCRIPTION
            "-- empty --"
    ::= { hmStatusTcpIpHttpActiveTunnelsEntry 2 }

-- {COLUMN} 1.3.6.1.4.1.248.32.18.1.9.10.8.1.3
hmStatusTcpIpHttpActiveTunnelsEntryRemotePort OBJECT-TYPE
    SYNTAX     Integer32 (0..65535)
    MAX-ACCESS read-only
    STATUS     current
    DESCRIPTION
            "-- empty --"
    ::= { hmStatusTcpIpHttpActiveTunnelsEntry 3 }

-- {COLUMN} 1.3.6.1.4.1.248.32.18.1.9.10.8.1.4
hmStatusTcpIpHttpActiveTunnelsEntryLocalHost OBJECT-TYPE
    SYNTAX     DisplayString (SIZE(0..48))
    MAX-ACCESS read-only
    STATUS     current
    DESCRIPTION
            "-- empty --"
    ::= { hmStatusTcpIpHttpActiveTunnelsEntry 4 }

-- {COLUMN} 1.3.6.1.4.1.248.32.18.1.9.10.8.1.5
hmStatusTcpIpHttpActiveTunnelsEntryLocalPort OBJECT-TYPE
    SYNTAX     Integer32 (0..65535)
    MAX-ACCESS read-only
    STATUS     current
    DESCRIPTION
            "-- empty --"
    ::= { hmStatusTcpIpHttpActiveTunnelsEntry 5 }

-- {COLUMN} 1.3.6.1.4.1.248.32.18.1.9.10.8.1.6
hmStatusTcpIpHttpActiveTunnelsEntryIdleTime OBJECT-TYPE
    SYNTAX     Integer32 (0..2147483647)
    MAX-ACCESS read-only
    STATUS     current
    DESCRIPTION
            "-- empty --"
    ::= { hmStatusTcpIpHttpActiveTunnelsEntry 6 }

-- {COLUMN} 1.3.6.1.4.1.248.32.18.1.9.10.8.1.7
hmStatusTcpIpHttpActiveTunnelsEntryLocalRtgTag OBJECT-TYPE
    SYNTAX     Integer32 (0..65535)
    MAX-ACCESS read-only
    STATUS     current
    DESCRIPTION
            "-- empty --"
    ::= { hmStatusTcpIpHttpActiveTunnelsEntry 7 }

-- {COLUMN} 1.3.6.1.4.1.248.32.18.1.9.10.8.1.8
hmStatusTcpIpHttpActiveTunnelsEntryNumConnections OBJECT-TYPE
    SYNTAX     Integer32 (0..2147483647)
    MAX-ACCESS read-only
    STATUS     current
    DESCRIPTION
            "-- empty --"
    ::= { hmStatusTcpIpHttpActiveTunnelsEntry 8 }

-- {COLUMN} 1.3.6.1.4.1.248.32.18.1.9.10.8.1.9
hmStatusTcpIpHttpActiveTunnelsEntryState OBJECT-TYPE
    SYNTAX     INTEGER {
                  eActive (0),
                  eClosing (1)
            }
    MAX-ACCESS read-only
    STATUS     current
    DESCRIPTION
            "-- empty --"
    ::= { hmStatusTcpIpHttpActiveTunnelsEntry 9 }

-- {SCALAR} 1.3.6.1.4.1.248.32.18.1.9.10.15
hmStatusTcpIpHttpMaxHttpJobCount OBJECT-TYPE
    SYNTAX     Integer32 (0..2147483647)
    MAX-ACCESS read-only
    STATUS     current
    DESCRIPTION
            "-- empty --"
    ::= { hmStatusTcpIpHttp 15 }

-- {SCALAR} 1.3.6.1.4.1.248.32.18.1.9.10.16
hmStatusTcpIpHttpJobCount OBJECT-TYPE
    SYNTAX     Integer32 (0..2147483647)
    MAX-ACCESS read-only
    STATUS     current
    DESCRIPTION
            "-- empty --"
    ::= { hmStatusTcpIpHttp 16 }

-- {SCALAR} 1.3.6.1.4.1.248.32.18.1.9.10.17
hmStatusTcpIpHttpIdleJobs OBJECT-TYPE
    SYNTAX     Integer32 (0..2147483647)
    MAX-ACCESS read-only
    STATUS     current
    DESCRIPTION
            "-- empty --"
    ::= { hmStatusTcpIpHttp 17 }

-- {NODE} 1.3.6.1.4.1.248.32.18.1.9.11
hmStatusTcpIpSyslog OBJECT IDENTIFIER ::= { hmStatusTcpIp 11 }

-- {TABLE} 1.3.6.1.4.1.248.32.18.1.9.11.11
hmStatusTcpIpSyslogLastMessagesTable OBJECT-TYPE
    SYNTAX     SEQUENCE OF HmStatusTcpIpSyslogLastMessagesEntry
    MAX-ACCESS not-accessible
    STATUS     current
    DESCRIPTION
            "-- empty --"
    ::= { hmStatusTcpIpSyslog 11 }

-- {ROW} 1.3.6.1.4.1.248.32.18.1.9.11.11.1
hmStatusTcpIpSyslogLastMessagesEntry OBJECT-TYPE
    SYNTAX     HmStatusTcpIpSyslogLastMessagesEntry
    MAX-ACCESS not-accessible
    STATUS     current
    DESCRIPTION
            ""
    INDEX {
            hmStatusTcpIpSyslogLastMessagesEntryIdx
          }
    ::= { hmStatusTcpIpSyslogLastMessagesTable 1 }

HmStatusTcpIpSyslogLastMessagesEntry ::= SEQUENCE {
            hmStatusTcpIpSyslogLastMessagesEntryIdx Integer32,
            hmStatusTcpIpSyslogLastMessagesEntryTime DisplayString,
            hmStatusTcpIpSyslogLastMessagesEntrySource INTEGER,
            hmStatusTcpIpSyslogLastMessagesEntryLevel INTEGER,
            hmStatusTcpIpSyslogLastMessagesEntryMessage DisplayString
    }

-- {COLUMN} 1.3.6.1.4.1.248.32.18.1.9.11.11.1.1
hmStatusTcpIpSyslogLastMessagesEntryIdx OBJECT-TYPE
    SYNTAX     Integer32 (0..2147483647)
    MAX-ACCESS read-only
    STATUS     current
    DESCRIPTION
            "-- empty --"
    ::= { hmStatusTcpIpSyslogLastMessagesEntry 1 }

-- {COLUMN} 1.3.6.1.4.1.248.32.18.1.9.11.11.1.2
hmStatusTcpIpSyslogLastMessagesEntryTime OBJECT-TYPE
    SYNTAX     DisplayString (SIZE(0..255))
    MAX-ACCESS read-only
    STATUS     current
    DESCRIPTION
            "-- empty --"
    ::= { hmStatusTcpIpSyslogLastMessagesEntry 2 }

-- {COLUMN} 1.3.6.1.4.1.248.32.18.1.9.11.11.1.3
hmStatusTcpIpSyslogLastMessagesEntrySource OBJECT-TYPE
    SYNTAX     INTEGER {
                  eKern (0),
                  eUser (1),
                  eMail (2),
                  eDaemon (3),
                  eAuth (4),
                  eSyslog (5),
                  eLpr (6),
                  eNews (7),
                  eUucp (8),
                  eCron (9),
                  eAuthpriv (10),
                  eLocal0 (16),
                  eLocal1 (17),
                  eLocal2 (18),
                  eLocal3 (19),
                  eLocal4 (20),
                  eLocal5 (21),
                  eLocal6 (22),
                  eLocal7 (23)
            }
    MAX-ACCESS read-only
    STATUS     current
    DESCRIPTION
            "-- empty --"
    ::= { hmStatusTcpIpSyslogLastMessagesEntry 3 }

-- {COLUMN} 1.3.6.1.4.1.248.32.18.1.9.11.11.1.4
hmStatusTcpIpSyslogLastMessagesEntryLevel OBJECT-TYPE
    SYNTAX     INTEGER {
                  eEmergency (0),
                  eAlarm (1),
                  eCritical (2),
                  eError (3),
                  eWarning (4),
                  eNotice (5),
                  eInfo (6),
                  eDebug (7)
            }
    MAX-ACCESS read-only
    STATUS     current
    DESCRIPTION
            "-- empty --"
    ::= { hmStatusTcpIpSyslogLastMessagesEntry 4 }

-- {COLUMN} 1.3.6.1.4.1.248.32.18.1.9.11.11.1.5
hmStatusTcpIpSyslogLastMessagesEntryMessage OBJECT-TYPE
    SYNTAX     DisplayString (SIZE(0..255))
    MAX-ACCESS read-only
    STATUS     current
    DESCRIPTION
            "-- empty --"
    ::= { hmStatusTcpIpSyslogLastMessagesEntry 5 }

-- {SCALAR} 1.3.6.1.4.1.248.32.18.1.9.11.12
hmStatusTcpIpSyslogSyslogCritical OBJECT-TYPE
    SYNTAX     INTEGER {
                  eNo (0),
                  eYes (1)
            }
    MAX-ACCESS read-only
    STATUS     current
    DESCRIPTION
            "-- empty --"
    ::= { hmStatusTcpIpSyslog 12 }

-- {SCALAR} 1.3.6.1.4.1.248.32.18.1.9.11.99
hmStatusTcpIpSyslogDeleteValues OBJECT-TYPE
    SYNTAX     DisplayString
    MAX-ACCESS read-write
    STATUS     current
    DESCRIPTION
            "-- empty --"
    ::= { hmStatusTcpIpSyslog 99 }

-- {NODE} 1.3.6.1.4.1.248.32.18.1.9.12
hmStatusTcpIpRadiuss OBJECT IDENTIFIER ::= { hmStatusTcpIp 12 }

-- {NODE} 1.3.6.1.4.1.248.32.18.1.9.12.1
hmStatusTcpIpRadiussAccess OBJECT IDENTIFIER ::= { hmStatusTcpIpRadiuss 1 }

-- {SCALAR} 1.3.6.1.4.1.248.32.18.1.9.12.1.5
hmStatusTcpIpRadiussAccessTotalAccessRequests OBJECT-TYPE
    SYNTAX     Counter32
    MAX-ACCESS read-only
    STATUS     current
    DESCRIPTION
            "-- empty --"
    ::= { hmStatusTcpIpRadiussAccess 5 }

-- {SCALAR} 1.3.6.1.4.1.248.32.18.1.9.12.1.6
hmStatusTcpIpRadiussAccessTotalInvalidAccessRequests OBJECT-TYPE
    SYNTAX     Counter32
    MAX-ACCESS read-only
    STATUS     current
    DESCRIPTION
            "-- empty --"
    ::= { hmStatusTcpIpRadiussAccess 6 }

-- {SCALAR} 1.3.6.1.4.1.248.32.18.1.9.12.1.7
hmStatusTcpIpRadiussAccessTotalDuplicateAccessRequests OBJECT-TYPE
    SYNTAX     Counter32
    MAX-ACCESS read-only
    STATUS     current
    DESCRIPTION
            "-- empty --"
    ::= { hmStatusTcpIpRadiussAccess 7 }

-- {SCALAR} 1.3.6.1.4.1.248.32.18.1.9.12.1.8
hmStatusTcpIpRadiussAccessTotalAccessAccepts OBJECT-TYPE
    SYNTAX     Counter32
    MAX-ACCESS read-only
    STATUS     current
    DESCRIPTION
            "-- empty --"
    ::= { hmStatusTcpIpRadiussAccess 8 }

-- {SCALAR} 1.3.6.1.4.1.248.32.18.1.9.12.1.9
hmStatusTcpIpRadiussAccessTotalAccessRejects OBJECT-TYPE
    SYNTAX     Counter32
    MAX-ACCESS read-only
    STATUS     current
    DESCRIPTION
            "-- empty --"
    ::= { hmStatusTcpIpRadiussAccess 9 }

-- {SCALAR} 1.3.6.1.4.1.248.32.18.1.9.12.1.10
hmStatusTcpIpRadiussAccessTotalAccessChallenges OBJECT-TYPE
    SYNTAX     Counter32
    MAX-ACCESS read-only
    STATUS     current
    DESCRIPTION
            "-- empty --"
    ::= { hmStatusTcpIpRadiussAccess 10 }

-- {SCALAR} 1.3.6.1.4.1.248.32.18.1.9.12.1.11
hmStatusTcpIpRadiussAccessTotalMalformedAccessRequests OBJECT-TYPE
    SYNTAX     Counter32
    MAX-ACCESS read-only
    STATUS     current
    DESCRIPTION
            "-- empty --"
    ::= { hmStatusTcpIpRadiussAccess 11 }

-- {SCALAR} 1.3.6.1.4.1.248.32.18.1.9.12.1.12
hmStatusTcpIpRadiussAccessTotalAccessBadAuthenticator OBJECT-TYPE
    SYNTAX     Counter32
    MAX-ACCESS read-only
    STATUS     current
    DESCRIPTION
            "-- empty --"
    ::= { hmStatusTcpIpRadiussAccess 12 }

-- {SCALAR} 1.3.6.1.4.1.248.32.18.1.9.12.1.13
hmStatusTcpIpRadiussAccessTotalAccessDropped OBJECT-TYPE
    SYNTAX     Counter32
    MAX-ACCESS read-only
    STATUS     current
    DESCRIPTION
            "-- empty --"
    ::= { hmStatusTcpIpRadiussAccess 13 }

-- {SCALAR} 1.3.6.1.4.1.248.32.18.1.9.12.1.14
hmStatusTcpIpRadiussAccessTotalAccessUnknownType OBJECT-TYPE
    SYNTAX     Counter32
    MAX-ACCESS read-only
    STATUS     current
    DESCRIPTION
            "-- empty --"
    ::= { hmStatusTcpIpRadiussAccess 14 }

-- {TABLE} 1.3.6.1.4.1.248.32.18.1.9.12.1.15
hmStatusTcpIpRadiussAccessClientsTable OBJECT-TYPE
    SYNTAX     SEQUENCE OF HmStatusTcpIpRadiussAccessClientsEntry
    MAX-ACCESS not-accessible
    STATUS     current
    DESCRIPTION
            "-- empty --"
    ::= { hmStatusTcpIpRadiussAccess 15 }

-- {ROW} 1.3.6.1.4.1.248.32.18.1.9.12.1.15.1
hmStatusTcpIpRadiussAccessClientsEntry OBJECT-TYPE
    SYNTAX     HmStatusTcpIpRadiussAccessClientsEntry
    MAX-ACCESS not-accessible
    STATUS     current
    DESCRIPTION
            ""
    INDEX {
            hmStatusTcpIpRadiussAccessClientsEntryIpAddress
          }
    ::= { hmStatusTcpIpRadiussAccessClientsTable 1 }

HmStatusTcpIpRadiussAccessClientsEntry ::= SEQUENCE {
            hmStatusTcpIpRadiussAccessClientsEntryIpAddress IpAddress,
            hmStatusTcpIpRadiussAccessClientsEntryAccessRequests Counter32,
            hmStatusTcpIpRadiussAccessClientsEntryDuplicateRequests Counter32,
            hmStatusTcpIpRadiussAccessClientsEntryAccessAccepts Counter32,
            hmStatusTcpIpRadiussAccessClientsEntryAccessRejects Counter32,
            hmStatusTcpIpRadiussAccessClientsEntryAccessChallenges Counter32,
            hmStatusTcpIpRadiussAccessClientsEntryMalfAccReq Counter32,
            hmStatusTcpIpRadiussAccessClientsEntryBadAuthenticator Counter32,
            hmStatusTcpIpRadiussAccessClientsEntryDropped Counter32,
            hmStatusTcpIpRadiussAccessClientsEntryUnknownType Counter32,
            hmStatusTcpIpRadiussAccessClientsEntryLastRequest Integer32,
            hmStatusTcpIpRadiussAccessClientsEntryNasIdent DisplayString,
            hmStatusTcpIpRadiussAccessClientsEntryStatusRequests Counter32,
            hmStatusTcpIpRadiussAccessClientsEntryStatusResponses Counter32,
            hmStatusTcpIpRadiussAccessClientsEntryLastStatusRequest Integer32
    }

-- {COLUMN} 1.3.6.1.4.1.248.32.18.1.9.12.1.15.1.1
hmStatusTcpIpRadiussAccessClientsEntryIpAddress OBJECT-TYPE
    SYNTAX     IpAddress
    MAX-ACCESS read-only
    STATUS     current
    DESCRIPTION
            "-- empty --"
    ::= { hmStatusTcpIpRadiussAccessClientsEntry 1 }

-- {COLUMN} 1.3.6.1.4.1.248.32.18.1.9.12.1.15.1.4
hmStatusTcpIpRadiussAccessClientsEntryAccessRequests OBJECT-TYPE
    SYNTAX     Counter32
    MAX-ACCESS read-only
    STATUS     current
    DESCRIPTION
            "-- empty --"
    ::= { hmStatusTcpIpRadiussAccessClientsEntry 4 }

-- {COLUMN} 1.3.6.1.4.1.248.32.18.1.9.12.1.15.1.5
hmStatusTcpIpRadiussAccessClientsEntryDuplicateRequests OBJECT-TYPE
    SYNTAX     Counter32
    MAX-ACCESS read-only
    STATUS     current
    DESCRIPTION
            "-- empty --"
    ::= { hmStatusTcpIpRadiussAccessClientsEntry 5 }

-- {COLUMN} 1.3.6.1.4.1.248.32.18.1.9.12.1.15.1.6
hmStatusTcpIpRadiussAccessClientsEntryAccessAccepts OBJECT-TYPE
    SYNTAX     Counter32
    MAX-ACCESS read-only
    STATUS     current
    DESCRIPTION
            "-- empty --"
    ::= { hmStatusTcpIpRadiussAccessClientsEntry 6 }

-- {COLUMN} 1.3.6.1.4.1.248.32.18.1.9.12.1.15.1.7
hmStatusTcpIpRadiussAccessClientsEntryAccessRejects OBJECT-TYPE
    SYNTAX     Counter32
    MAX-ACCESS read-only
    STATUS     current
    DESCRIPTION
            "-- empty --"
    ::= { hmStatusTcpIpRadiussAccessClientsEntry 7 }

-- {COLUMN} 1.3.6.1.4.1.248.32.18.1.9.12.1.15.1.8
hmStatusTcpIpRadiussAccessClientsEntryAccessChallenges OBJECT-TYPE
    SYNTAX     Counter32
    MAX-ACCESS read-only
    STATUS     current
    DESCRIPTION
            "-- empty --"
    ::= { hmStatusTcpIpRadiussAccessClientsEntry 8 }

-- {COLUMN} 1.3.6.1.4.1.248.32.18.1.9.12.1.15.1.9
hmStatusTcpIpRadiussAccessClientsEntryMalfAccReq OBJECT-TYPE
    SYNTAX     Counter32
    MAX-ACCESS read-only
    STATUS     current
    DESCRIPTION
            ""
    ::= { hmStatusTcpIpRadiussAccessClientsEntry 9 }

-- {COLUMN} 1.3.6.1.4.1.248.32.18.1.9.12.1.15.1.10
hmStatusTcpIpRadiussAccessClientsEntryBadAuthenticator OBJECT-TYPE
    SYNTAX     Counter32
    MAX-ACCESS read-only
    STATUS     current
    DESCRIPTION
            "-- empty --"
    ::= { hmStatusTcpIpRadiussAccessClientsEntry 10 }

-- {COLUMN} 1.3.6.1.4.1.248.32.18.1.9.12.1.15.1.11
hmStatusTcpIpRadiussAccessClientsEntryDropped OBJECT-TYPE
    SYNTAX     Counter32
    MAX-ACCESS read-only
    STATUS     current
    DESCRIPTION
            "-- empty --"
    ::= { hmStatusTcpIpRadiussAccessClientsEntry 11 }

-- {COLUMN} 1.3.6.1.4.1.248.32.18.1.9.12.1.15.1.12
hmStatusTcpIpRadiussAccessClientsEntryUnknownType OBJECT-TYPE
    SYNTAX     Counter32
    MAX-ACCESS read-only
    STATUS     current
    DESCRIPTION
            "-- empty --"
    ::= { hmStatusTcpIpRadiussAccessClientsEntry 12 }

-- {COLUMN} 1.3.6.1.4.1.248.32.18.1.9.12.1.15.1.13
hmStatusTcpIpRadiussAccessClientsEntryLastRequest OBJECT-TYPE
    SYNTAX     Integer32 (0..2147483647)
    MAX-ACCESS read-only
    STATUS     current
    DESCRIPTION
            "-- empty --"
    ::= { hmStatusTcpIpRadiussAccessClientsEntry 13 }

-- {COLUMN} 1.3.6.1.4.1.248.32.18.1.9.12.1.15.1.14
hmStatusTcpIpRadiussAccessClientsEntryNasIdent OBJECT-TYPE
    SYNTAX     DisplayString (SIZE(0..64))
    MAX-ACCESS read-only
    STATUS     current
    DESCRIPTION
            "-- empty --"
    ::= { hmStatusTcpIpRadiussAccessClientsEntry 14 }

-- {COLUMN} 1.3.6.1.4.1.248.32.18.1.9.12.1.15.1.30
hmStatusTcpIpRadiussAccessClientsEntryStatusRequests OBJECT-TYPE
    SYNTAX     Counter32
    MAX-ACCESS read-only
    STATUS     current
    DESCRIPTION
            "-- empty --"
    ::= { hmStatusTcpIpRadiussAccessClientsEntry 30 }

-- {COLUMN} 1.3.6.1.4.1.248.32.18.1.9.12.1.15.1.31
hmStatusTcpIpRadiussAccessClientsEntryStatusResponses OBJECT-TYPE
    SYNTAX     Counter32
    MAX-ACCESS read-only
    STATUS     current
    DESCRIPTION
            "-- empty --"
    ::= { hmStatusTcpIpRadiussAccessClientsEntry 31 }

-- {COLUMN} 1.3.6.1.4.1.248.32.18.1.9.12.1.15.1.32
hmStatusTcpIpRadiussAccessClientsEntryLastStatusRequest OBJECT-TYPE
    SYNTAX     Integer32 (0..2147483647)
    MAX-ACCESS read-only
    STATUS     current
    DESCRIPTION
            "-- empty --"
    ::= { hmStatusTcpIpRadiussAccessClientsEntry 32 }

-- {TABLE} 1.3.6.1.4.1.248.32.18.1.9.12.1.20
hmStatusTcpIpRadiussAccessIpv6ClientsTable OBJECT-TYPE
    SYNTAX     SEQUENCE OF HmStatusTcpIpRadiussAccessIpv6ClientsEntry
    MAX-ACCESS not-accessible
    STATUS     current
    DESCRIPTION
            "-- empty --"
    ::= { hmStatusTcpIpRadiussAccess 20 }

-- {ROW} 1.3.6.1.4.1.248.32.18.1.9.12.1.20.1
hmStatusTcpIpRadiussAccessIpv6ClientsEntry OBJECT-TYPE
    SYNTAX     HmStatusTcpIpRadiussAccessIpv6ClientsEntry
    MAX-ACCESS not-accessible
    STATUS     current
    DESCRIPTION
            ""
    INDEX {
            hmStatusTcpIpRadiussAccessIpv6ClientsEntryIpAddress
          }
    ::= { hmStatusTcpIpRadiussAccessIpv6ClientsTable 1 }

HmStatusTcpIpRadiussAccessIpv6ClientsEntry ::= SEQUENCE {
            hmStatusTcpIpRadiussAccessIpv6ClientsEntryIpAddress IpAddress,
            hmStatusTcpIpRadiussAccessIpv6ClientsEntryAccessRequests Counter32,
            hmStatusTcpIpRadiussAccessIpv6ClientsEntryDuplicateRequests Counter32,
            hmStatusTcpIpRadiussAccessIpv6ClientsEntryAccessAccepts Counter32,
            hmStatusTcpIpRadiussAccessIpv6ClientsEntryAccessRejects Counter32,
            hmStatusTcpIpRadiussAccessIpv6ClientsEntryAccessChallenges Counter32,
            hmStatusTcpIpRadiussAccessIpv6ClientsEntryMalfAccReq Counter32,
            hmStatusTcpIpRadiussAccessIpv6ClientsEntryBadAuthenticator Counter32,
            hmStatusTcpIpRadiussAccessIpv6ClientsEntryDropped Counter32,
            hmStatusTcpIpRadiussAccessIpv6ClientsEntryUnknownType Counter32,
            hmStatusTcpIpRadiussAccessIpv6ClientsEntryLastRequest Integer32,
            hmStatusTcpIpRadiussAccessIpv6ClientsEntryNasIdent DisplayString,
            hmStatusTcpIpRadiussAccessIpv6ClientsEntryStatusRequests Counter32,
            hmStatusTcpIpRadiussAccessIpv6ClientsEntryStatusResponses Counter32,
            hmStatusTcpIpRadiussAccessIpv6ClientsEntryLastStatusRequest Integer32
    }

-- {COLUMN} 1.3.6.1.4.1.248.32.18.1.9.12.1.20.1.1
hmStatusTcpIpRadiussAccessIpv6ClientsEntryIpAddress OBJECT-TYPE
    SYNTAX     IpAddress
    MAX-ACCESS read-only
    STATUS     current
    DESCRIPTION
            "-- empty --"
    ::= { hmStatusTcpIpRadiussAccessIpv6ClientsEntry 1 }

-- {COLUMN} 1.3.6.1.4.1.248.32.18.1.9.12.1.20.1.4
hmStatusTcpIpRadiussAccessIpv6ClientsEntryAccessRequests OBJECT-TYPE
    SYNTAX     Counter32
    MAX-ACCESS read-only
    STATUS     current
    DESCRIPTION
            "-- empty --"
    ::= { hmStatusTcpIpRadiussAccessIpv6ClientsEntry 4 }

-- {COLUMN} 1.3.6.1.4.1.248.32.18.1.9.12.1.20.1.5
hmStatusTcpIpRadiussAccessIpv6ClientsEntryDuplicateRequests OBJECT-TYPE
    SYNTAX     Counter32
    MAX-ACCESS read-only
    STATUS     current
    DESCRIPTION
            "-- empty --"
    ::= { hmStatusTcpIpRadiussAccessIpv6ClientsEntry 5 }

-- {COLUMN} 1.3.6.1.4.1.248.32.18.1.9.12.1.20.1.6
hmStatusTcpIpRadiussAccessIpv6ClientsEntryAccessAccepts OBJECT-TYPE
    SYNTAX     Counter32
    MAX-ACCESS read-only
    STATUS     current
    DESCRIPTION
            "-- empty --"
    ::= { hmStatusTcpIpRadiussAccessIpv6ClientsEntry 6 }

-- {COLUMN} 1.3.6.1.4.1.248.32.18.1.9.12.1.20.1.7
hmStatusTcpIpRadiussAccessIpv6ClientsEntryAccessRejects OBJECT-TYPE
    SYNTAX     Counter32
    MAX-ACCESS read-only
    STATUS     current
    DESCRIPTION
            "-- empty --"
    ::= { hmStatusTcpIpRadiussAccessIpv6ClientsEntry 7 }

-- {COLUMN} 1.3.6.1.4.1.248.32.18.1.9.12.1.20.1.8
hmStatusTcpIpRadiussAccessIpv6ClientsEntryAccessChallenges OBJECT-TYPE
    SYNTAX     Counter32
    MAX-ACCESS read-only
    STATUS     current
    DESCRIPTION
            "-- empty --"
    ::= { hmStatusTcpIpRadiussAccessIpv6ClientsEntry 8 }

-- {COLUMN} 1.3.6.1.4.1.248.32.18.1.9.12.1.20.1.9
hmStatusTcpIpRadiussAccessIpv6ClientsEntryMalfAccReq OBJECT-TYPE
    SYNTAX     Counter32
    MAX-ACCESS read-only
    STATUS     current
    DESCRIPTION
            ""
    ::= { hmStatusTcpIpRadiussAccessIpv6ClientsEntry 9 }

-- {COLUMN} 1.3.6.1.4.1.248.32.18.1.9.12.1.20.1.10
hmStatusTcpIpRadiussAccessIpv6ClientsEntryBadAuthenticator OBJECT-TYPE
    SYNTAX     Counter32
    MAX-ACCESS read-only
    STATUS     current
    DESCRIPTION
            "-- empty --"
    ::= { hmStatusTcpIpRadiussAccessIpv6ClientsEntry 10 }

-- {COLUMN} 1.3.6.1.4.1.248.32.18.1.9.12.1.20.1.11
hmStatusTcpIpRadiussAccessIpv6ClientsEntryDropped OBJECT-TYPE
    SYNTAX     Counter32
    MAX-ACCESS read-only
    STATUS     current
    DESCRIPTION
            "-- empty --"
    ::= { hmStatusTcpIpRadiussAccessIpv6ClientsEntry 11 }

-- {COLUMN} 1.3.6.1.4.1.248.32.18.1.9.12.1.20.1.12
hmStatusTcpIpRadiussAccessIpv6ClientsEntryUnknownType OBJECT-TYPE
    SYNTAX     Counter32
    MAX-ACCESS read-only
    STATUS     current
    DESCRIPTION
            "-- empty --"
    ::= { hmStatusTcpIpRadiussAccessIpv6ClientsEntry 12 }

-- {COLUMN} 1.3.6.1.4.1.248.32.18.1.9.12.1.20.1.13
hmStatusTcpIpRadiussAccessIpv6ClientsEntryLastRequest OBJECT-TYPE
    SYNTAX     Integer32 (0..2147483647)
    MAX-ACCESS read-only
    STATUS     current
    DESCRIPTION
            "-- empty --"
    ::= { hmStatusTcpIpRadiussAccessIpv6ClientsEntry 13 }

-- {COLUMN} 1.3.6.1.4.1.248.32.18.1.9.12.1.20.1.14
hmStatusTcpIpRadiussAccessIpv6ClientsEntryNasIdent OBJECT-TYPE
    SYNTAX     DisplayString (SIZE(0..64))
    MAX-ACCESS read-only
    STATUS     current
    DESCRIPTION
            "-- empty --"
    ::= { hmStatusTcpIpRadiussAccessIpv6ClientsEntry 14 }

-- {COLUMN} 1.3.6.1.4.1.248.32.18.1.9.12.1.20.1.30
hmStatusTcpIpRadiussAccessIpv6ClientsEntryStatusRequests OBJECT-TYPE
    SYNTAX     Counter32
    MAX-ACCESS read-only
    STATUS     current
    DESCRIPTION
            "-- empty --"
    ::= { hmStatusTcpIpRadiussAccessIpv6ClientsEntry 30 }

-- {COLUMN} 1.3.6.1.4.1.248.32.18.1.9.12.1.20.1.31
hmStatusTcpIpRadiussAccessIpv6ClientsEntryStatusResponses OBJECT-TYPE
    SYNTAX     Counter32
    MAX-ACCESS read-only
    STATUS     current
    DESCRIPTION
            "-- empty --"
    ::= { hmStatusTcpIpRadiussAccessIpv6ClientsEntry 31 }

-- {COLUMN} 1.3.6.1.4.1.248.32.18.1.9.12.1.20.1.32
hmStatusTcpIpRadiussAccessIpv6ClientsEntryLastStatusRequest OBJECT-TYPE
    SYNTAX     Integer32 (0..2147483647)
    MAX-ACCESS read-only
    STATUS     current
    DESCRIPTION
            "-- empty --"
    ::= { hmStatusTcpIpRadiussAccessIpv6ClientsEntry 32 }

-- {SCALAR} 1.3.6.1.4.1.248.32.18.1.9.12.1.30
hmStatusTcpIpRadiussAccessTotalStatusRequests OBJECT-TYPE
    SYNTAX     Counter32
    MAX-ACCESS read-only
    STATUS     current
    DESCRIPTION
            "-- empty --"
    ::= { hmStatusTcpIpRadiussAccess 30 }

-- {SCALAR} 1.3.6.1.4.1.248.32.18.1.9.12.1.31
hmStatusTcpIpRadiussAccessTotalStatusResponses OBJECT-TYPE
    SYNTAX     Counter32
    MAX-ACCESS read-only
    STATUS     current
    DESCRIPTION
            "-- empty --"
    ::= { hmStatusTcpIpRadiussAccess 31 }

-- {SCALAR} 1.3.6.1.4.1.248.32.18.1.9.12.1.100
hmStatusTcpIpRadiussAccessDeleteValues OBJECT-TYPE
    SYNTAX     DisplayString
    MAX-ACCESS read-write
    STATUS     current
    DESCRIPTION
            "-- empty --"
    ::= { hmStatusTcpIpRadiussAccess 100 }

-- {NODE} 1.3.6.1.4.1.248.32.18.1.9.12.2
hmStatusTcpIpRadiussAccnt OBJECT IDENTIFIER ::= { hmStatusTcpIpRadiuss 2 }

-- {SCALAR} 1.3.6.1.4.1.248.32.18.1.9.12.2.5
hmStatusTcpIpRadiussAccntTotalAccountRequests OBJECT-TYPE
    SYNTAX     Counter32
    MAX-ACCESS read-only
    STATUS     current
    DESCRIPTION
            "-- empty --"
    ::= { hmStatusTcpIpRadiussAccnt 5 }

-- {SCALAR} 1.3.6.1.4.1.248.32.18.1.9.12.2.6
hmStatusTcpIpRadiussAccntTotalInvalidAccountRequests OBJECT-TYPE
    SYNTAX     Counter32
    MAX-ACCESS read-only
    STATUS     current
    DESCRIPTION
            "-- empty --"
    ::= { hmStatusTcpIpRadiussAccnt 6 }

-- {SCALAR} 1.3.6.1.4.1.248.32.18.1.9.12.2.7
hmStatusTcpIpRadiussAccntTotalDuplicateAccountRequests OBJECT-TYPE
    SYNTAX     Counter32
    MAX-ACCESS read-only
    STATUS     current
    DESCRIPTION
            "-- empty --"
    ::= { hmStatusTcpIpRadiussAccnt 7 }

-- {SCALAR} 1.3.6.1.4.1.248.32.18.1.9.12.2.8
hmStatusTcpIpRadiussAccntTotalAccountResponses OBJECT-TYPE
    SYNTAX     Counter32
    MAX-ACCESS read-only
    STATUS     current
    DESCRIPTION
            "-- empty --"
    ::= { hmStatusTcpIpRadiussAccnt 8 }

-- {SCALAR} 1.3.6.1.4.1.248.32.18.1.9.12.2.9
hmStatusTcpIpRadiussAccntTotalMalformedAccountRequests OBJECT-TYPE
    SYNTAX     Counter32
    MAX-ACCESS read-only
    STATUS     current
    DESCRIPTION
            "-- empty --"
    ::= { hmStatusTcpIpRadiussAccnt 9 }

-- {SCALAR} 1.3.6.1.4.1.248.32.18.1.9.12.2.10
hmStatusTcpIpRadiussAccntTotalAccountBadAuthenticator OBJECT-TYPE
    SYNTAX     Counter32
    MAX-ACCESS read-only
    STATUS     current
    DESCRIPTION
            "-- empty --"
    ::= { hmStatusTcpIpRadiussAccnt 10 }

-- {SCALAR} 1.3.6.1.4.1.248.32.18.1.9.12.2.11
hmStatusTcpIpRadiussAccntTotalAccountDropped OBJECT-TYPE
    SYNTAX     Counter32
    MAX-ACCESS read-only
    STATUS     current
    DESCRIPTION
            "-- empty --"
    ::= { hmStatusTcpIpRadiussAccnt 11 }

-- {SCALAR} 1.3.6.1.4.1.248.32.18.1.9.12.2.12
hmStatusTcpIpRadiussAccntTotalAccountNorecord OBJECT-TYPE
    SYNTAX     Counter32
    MAX-ACCESS read-only
    STATUS     current
    DESCRIPTION
            "-- empty --"
    ::= { hmStatusTcpIpRadiussAccnt 12 }

-- {SCALAR} 1.3.6.1.4.1.248.32.18.1.9.12.2.13
hmStatusTcpIpRadiussAccntTotalAccountUnknownType OBJECT-TYPE
    SYNTAX     Counter32
    MAX-ACCESS read-only
    STATUS     current
    DESCRIPTION
            "-- empty --"
    ::= { hmStatusTcpIpRadiussAccnt 13 }

-- {TABLE} 1.3.6.1.4.1.248.32.18.1.9.12.2.15
hmStatusTcpIpRadiussAccntClientsTable OBJECT-TYPE
    SYNTAX     SEQUENCE OF HmStatusTcpIpRadiussAccntClientsEntry
    MAX-ACCESS not-accessible
    STATUS     current
    DESCRIPTION
            "-- empty --"
    ::= { hmStatusTcpIpRadiussAccnt 15 }

-- {ROW} 1.3.6.1.4.1.248.32.18.1.9.12.2.15.1
hmStatusTcpIpRadiussAccntClientsEntry OBJECT-TYPE
    SYNTAX     HmStatusTcpIpRadiussAccntClientsEntry
    MAX-ACCESS not-accessible
    STATUS     current
    DESCRIPTION
            ""
    INDEX {
            hmStatusTcpIpRadiussAccntClientsEntryIpAddress
          }
    ::= { hmStatusTcpIpRadiussAccntClientsTable 1 }

HmStatusTcpIpRadiussAccntClientsEntry ::= SEQUENCE {
            hmStatusTcpIpRadiussAccntClientsEntryIpAddress IpAddress,
            hmStatusTcpIpRadiussAccntClientsEntryAccountRequests Counter32,
            hmStatusTcpIpRadiussAccntClientsEntryDuplicateRequests Counter32,
            hmStatusTcpIpRadiussAccntClientsEntryAccountResponses Counter32,
            hmStatusTcpIpRadiussAccntClientsEntryAccountNorecords Counter32,
            hmStatusTcpIpRadiussAccntClientsEntryMalfAccReq Counter32,
            hmStatusTcpIpRadiussAccntClientsEntryBadAuthenticator Counter32,
            hmStatusTcpIpRadiussAccntClientsEntryDropped Counter32,
            hmStatusTcpIpRadiussAccntClientsEntryUnknownType Counter32,
            hmStatusTcpIpRadiussAccntClientsEntryLastRequest Integer32,
            hmStatusTcpIpRadiussAccntClientsEntryNasIdent DisplayString,
            hmStatusTcpIpRadiussAccntClientsEntryStatusRequests Counter32,
            hmStatusTcpIpRadiussAccntClientsEntryStatusResponses Counter32,
            hmStatusTcpIpRadiussAccntClientsEntryLastStatusRequest Integer32
    }

-- {COLUMN} 1.3.6.1.4.1.248.32.18.1.9.12.2.15.1.1
hmStatusTcpIpRadiussAccntClientsEntryIpAddress OBJECT-TYPE
    SYNTAX     IpAddress
    MAX-ACCESS read-only
    STATUS     current
    DESCRIPTION
            "-- empty --"
    ::= { hmStatusTcpIpRadiussAccntClientsEntry 1 }

-- {COLUMN} 1.3.6.1.4.1.248.32.18.1.9.12.2.15.1.4
hmStatusTcpIpRadiussAccntClientsEntryAccountRequests OBJECT-TYPE
    SYNTAX     Counter32
    MAX-ACCESS read-only
    STATUS     current
    DESCRIPTION
            "-- empty --"
    ::= { hmStatusTcpIpRadiussAccntClientsEntry 4 }

-- {COLUMN} 1.3.6.1.4.1.248.32.18.1.9.12.2.15.1.5
hmStatusTcpIpRadiussAccntClientsEntryDuplicateRequests OBJECT-TYPE
    SYNTAX     Counter32
    MAX-ACCESS read-only
    STATUS     current
    DESCRIPTION
            "-- empty --"
    ::= { hmStatusTcpIpRadiussAccntClientsEntry 5 }

-- {COLUMN} 1.3.6.1.4.1.248.32.18.1.9.12.2.15.1.6
hmStatusTcpIpRadiussAccntClientsEntryAccountResponses OBJECT-TYPE
    SYNTAX     Counter32
    MAX-ACCESS read-only
    STATUS     current
    DESCRIPTION
            "-- empty --"
    ::= { hmStatusTcpIpRadiussAccntClientsEntry 6 }

-- {COLUMN} 1.3.6.1.4.1.248.32.18.1.9.12.2.15.1.7
hmStatusTcpIpRadiussAccntClientsEntryAccountNorecords OBJECT-TYPE
    SYNTAX     Counter32
    MAX-ACCESS read-only
    STATUS     current
    DESCRIPTION
            "-- empty --"
    ::= { hmStatusTcpIpRadiussAccntClientsEntry 7 }

-- {COLUMN} 1.3.6.1.4.1.248.32.18.1.9.12.2.15.1.9
hmStatusTcpIpRadiussAccntClientsEntryMalfAccReq OBJECT-TYPE
    SYNTAX     Counter32
    MAX-ACCESS read-only
    STATUS     current
    DESCRIPTION
            ""
    ::= { hmStatusTcpIpRadiussAccntClientsEntry 9 }

-- {COLUMN} 1.3.6.1.4.1.248.32.18.1.9.12.2.15.1.10
hmStatusTcpIpRadiussAccntClientsEntryBadAuthenticator OBJECT-TYPE
    SYNTAX     Counter32
    MAX-ACCESS read-only
    STATUS     current
    DESCRIPTION
            "-- empty --"
    ::= { hmStatusTcpIpRadiussAccntClientsEntry 10 }

-- {COLUMN} 1.3.6.1.4.1.248.32.18.1.9.12.2.15.1.11
hmStatusTcpIpRadiussAccntClientsEntryDropped OBJECT-TYPE
    SYNTAX     Counter32
    MAX-ACCESS read-only
    STATUS     current
    DESCRIPTION
            "-- empty --"
    ::= { hmStatusTcpIpRadiussAccntClientsEntry 11 }

-- {COLUMN} 1.3.6.1.4.1.248.32.18.1.9.12.2.15.1.12
hmStatusTcpIpRadiussAccntClientsEntryUnknownType OBJECT-TYPE
    SYNTAX     Counter32
    MAX-ACCESS read-only
    STATUS     current
    DESCRIPTION
            "-- empty --"
    ::= { hmStatusTcpIpRadiussAccntClientsEntry 12 }

-- {COLUMN} 1.3.6.1.4.1.248.32.18.1.9.12.2.15.1.13
hmStatusTcpIpRadiussAccntClientsEntryLastRequest OBJECT-TYPE
    SYNTAX     Integer32 (0..2147483647)
    MAX-ACCESS read-only
    STATUS     current
    DESCRIPTION
            "-- empty --"
    ::= { hmStatusTcpIpRadiussAccntClientsEntry 13 }

-- {COLUMN} 1.3.6.1.4.1.248.32.18.1.9.12.2.15.1.14
hmStatusTcpIpRadiussAccntClientsEntryNasIdent OBJECT-TYPE
    SYNTAX     DisplayString (SIZE(0..64))
    MAX-ACCESS read-only
    STATUS     current
    DESCRIPTION
            "-- empty --"
    ::= { hmStatusTcpIpRadiussAccntClientsEntry 14 }

-- {COLUMN} 1.3.6.1.4.1.248.32.18.1.9.12.2.15.1.30
hmStatusTcpIpRadiussAccntClientsEntryStatusRequests OBJECT-TYPE
    SYNTAX     Counter32
    MAX-ACCESS read-only
    STATUS     current
    DESCRIPTION
            "-- empty --"
    ::= { hmStatusTcpIpRadiussAccntClientsEntry 30 }

-- {COLUMN} 1.3.6.1.4.1.248.32.18.1.9.12.2.15.1.31
hmStatusTcpIpRadiussAccntClientsEntryStatusResponses OBJECT-TYPE
    SYNTAX     Counter32
    MAX-ACCESS read-only
    STATUS     current
    DESCRIPTION
            "-- empty --"
    ::= { hmStatusTcpIpRadiussAccntClientsEntry 31 }

-- {COLUMN} 1.3.6.1.4.1.248.32.18.1.9.12.2.15.1.32
hmStatusTcpIpRadiussAccntClientsEntryLastStatusRequest OBJECT-TYPE
    SYNTAX     Integer32 (0..2147483647)
    MAX-ACCESS read-only
    STATUS     current
    DESCRIPTION
            "-- empty --"
    ::= { hmStatusTcpIpRadiussAccntClientsEntry 32 }

-- {TABLE} 1.3.6.1.4.1.248.32.18.1.9.12.2.16
hmStatusTcpIpRadiussAccntActAccntSessTable OBJECT-TYPE
    SYNTAX     SEQUENCE OF HmStatusTcpIpRadiussAccntActAccntSessEntry
    MAX-ACCESS not-accessible
    STATUS     current
    DESCRIPTION
            ""
    ::= { hmStatusTcpIpRadiussAccnt 16 }

-- {ROW} 1.3.6.1.4.1.248.32.18.1.9.12.2.16.1
hmStatusTcpIpRadiussAccntActAccntSessEntry OBJECT-TYPE
    SYNTAX     HmStatusTcpIpRadiussAccntActAccntSessEntry
    MAX-ACCESS not-accessible
    STATUS     current
    DESCRIPTION
            ""
    INDEX {
            hmStatusTcpIpRadiussAccntActAccntSessEntryIndex
          }
    ::= { hmStatusTcpIpRadiussAccntActAccntSessTable 1 }

HmStatusTcpIpRadiussAccntActAccntSessEntry ::= SEQUENCE {
            hmStatusTcpIpRadiussAccntActAccntSessEntryIndex Integer32,
            hmStatusTcpIpRadiussAccntActAccntSessEntryNasIpAddress IpAddress,
            hmStatusTcpIpRadiussAccntActAccntSessEntryNasIdent DisplayString,
            hmStatusTcpIpRadiussAccntActAccntSessEntrySessionId DisplayString,
            hmStatusTcpIpRadiussAccntActAccntSessEntryUserName DisplayString,
            hmStatusTcpIpRadiussAccntActAccntSessEntrySessionTime Integer32,
            hmStatusTcpIpRadiussAccntActAccntSessEntryInputPackets Counter32,
            hmStatusTcpIpRadiussAccntActAccntSessEntryOutputPackets Counter32,
            hmStatusTcpIpRadiussAccntActAccntSessEntryInputOctets Counter64,
            hmStatusTcpIpRadiussAccntActAccntSessEntryOutputOctets Counter64,
            hmStatusTcpIpRadiussAccntActAccntSessEntryIpAddress IpAddress,
            hmStatusTcpIpRadiussAccntActAccntSessEntryStartTime DisplayString,
            hmStatusTcpIpRadiussAccntActAccntSessEntryLastUpdate Integer32,
            hmStatusTcpIpRadiussAccntActAccntSessEntryUpdateDelta Integer32,
            hmStatusTcpIpRadiussAccntActAccntSessEntryNasPortType INTEGER,
            hmStatusTcpIpRadiussAccntActAccntSessEntryNasPortId Integer32,
            hmStatusTcpIpRadiussAccntActAccntSessEntryCalledStationId DisplayString,
            hmStatusTcpIpRadiussAccntActAccntSessEntryCallingStationId DisplayString,
            hmStatusTcpIpRadiussAccntActAccntSessEntryNasIpv6Address IpAddress
    }

-- {COLUMN} 1.3.6.1.4.1.248.32.18.1.9.12.2.16.1.1
hmStatusTcpIpRadiussAccntActAccntSessEntryIndex OBJECT-TYPE
    SYNTAX     Integer32 (0..2147483647)
    MAX-ACCESS read-only
    STATUS     current
    DESCRIPTION
            "-- empty --"
    ::= { hmStatusTcpIpRadiussAccntActAccntSessEntry 1 }

-- {COLUMN} 1.3.6.1.4.1.248.32.18.1.9.12.2.16.1.2
hmStatusTcpIpRadiussAccntActAccntSessEntryNasIpAddress OBJECT-TYPE
    SYNTAX     IpAddress
    MAX-ACCESS read-only
    STATUS     current
    DESCRIPTION
            "-- empty --"
    ::= { hmStatusTcpIpRadiussAccntActAccntSessEntry 2 }

-- {COLUMN} 1.3.6.1.4.1.248.32.18.1.9.12.2.16.1.3
hmStatusTcpIpRadiussAccntActAccntSessEntryNasIdent OBJECT-TYPE
    SYNTAX     DisplayString (SIZE(0..64))
    MAX-ACCESS read-only
    STATUS     current
    DESCRIPTION
            "-- empty --"
    ::= { hmStatusTcpIpRadiussAccntActAccntSessEntry 3 }

-- {COLUMN} 1.3.6.1.4.1.248.32.18.1.9.12.2.16.1.4
hmStatusTcpIpRadiussAccntActAccntSessEntrySessionId OBJECT-TYPE
    SYNTAX     DisplayString (SIZE(0..128))
    MAX-ACCESS read-only
    STATUS     current
    DESCRIPTION
            "-- empty --"
    ::= { hmStatusTcpIpRadiussAccntActAccntSessEntry 4 }

-- {COLUMN} 1.3.6.1.4.1.248.32.18.1.9.12.2.16.1.5
hmStatusTcpIpRadiussAccntActAccntSessEntryUserName OBJECT-TYPE
    SYNTAX     DisplayString (SIZE(0..48))
    MAX-ACCESS read-only
    STATUS     current
    DESCRIPTION
            "-- empty --"
    ::= { hmStatusTcpIpRadiussAccntActAccntSessEntry 5 }

-- {COLUMN} 1.3.6.1.4.1.248.32.18.1.9.12.2.16.1.6
hmStatusTcpIpRadiussAccntActAccntSessEntrySessionTime OBJECT-TYPE
    SYNTAX     Integer32 (0..2147483647)
    MAX-ACCESS read-only
    STATUS     current
    DESCRIPTION
            "-- empty --"
    ::= { hmStatusTcpIpRadiussAccntActAccntSessEntry 6 }

-- {COLUMN} 1.3.6.1.4.1.248.32.18.1.9.12.2.16.1.7
hmStatusTcpIpRadiussAccntActAccntSessEntryInputPackets OBJECT-TYPE
    SYNTAX     Counter32
    MAX-ACCESS read-only
    STATUS     current
    DESCRIPTION
            "-- empty --"
    ::= { hmStatusTcpIpRadiussAccntActAccntSessEntry 7 }

-- {COLUMN} 1.3.6.1.4.1.248.32.18.1.9.12.2.16.1.8
hmStatusTcpIpRadiussAccntActAccntSessEntryOutputPackets OBJECT-TYPE
    SYNTAX     Counter32
    MAX-ACCESS read-only
    STATUS     current
    DESCRIPTION
            "-- empty --"
    ::= { hmStatusTcpIpRadiussAccntActAccntSessEntry 8 }

-- {COLUMN} 1.3.6.1.4.1.248.32.18.1.9.12.2.16.1.9
hmStatusTcpIpRadiussAccntActAccntSessEntryInputOctets OBJECT-TYPE
    SYNTAX     Counter64
    MAX-ACCESS read-only
    STATUS     current
    DESCRIPTION
            "-- empty --"
    ::= { hmStatusTcpIpRadiussAccntActAccntSessEntry 9 }

-- {COLUMN} 1.3.6.1.4.1.248.32.18.1.9.12.2.16.1.10
hmStatusTcpIpRadiussAccntActAccntSessEntryOutputOctets OBJECT-TYPE
    SYNTAX     Counter64
    MAX-ACCESS read-only
    STATUS     current
    DESCRIPTION
            "-- empty --"
    ::= { hmStatusTcpIpRadiussAccntActAccntSessEntry 10 }

-- {COLUMN} 1.3.6.1.4.1.248.32.18.1.9.12.2.16.1.11
hmStatusTcpIpRadiussAccntActAccntSessEntryIpAddress OBJECT-TYPE
    SYNTAX     IpAddress
    MAX-ACCESS read-only
    STATUS     current
    DESCRIPTION
            "-- empty --"
    ::= { hmStatusTcpIpRadiussAccntActAccntSessEntry 11 }

-- {COLUMN} 1.3.6.1.4.1.248.32.18.1.9.12.2.16.1.12
hmStatusTcpIpRadiussAccntActAccntSessEntryStartTime OBJECT-TYPE
    SYNTAX     DisplayString (SIZE(0..19))
    MAX-ACCESS read-only
    STATUS     current
    DESCRIPTION
            "-- empty --"
    ::= { hmStatusTcpIpRadiussAccntActAccntSessEntry 12 }

-- {COLUMN} 1.3.6.1.4.1.248.32.18.1.9.12.2.16.1.15
hmStatusTcpIpRadiussAccntActAccntSessEntryLastUpdate OBJECT-TYPE
    SYNTAX     Integer32 (0..2147483647)
    MAX-ACCESS read-only
    STATUS     current
    DESCRIPTION
            "-- empty --"
    ::= { hmStatusTcpIpRadiussAccntActAccntSessEntry 15 }

-- {COLUMN} 1.3.6.1.4.1.248.32.18.1.9.12.2.16.1.16
hmStatusTcpIpRadiussAccntActAccntSessEntryUpdateDelta OBJECT-TYPE
    SYNTAX     Integer32 (0..2147483647)
    MAX-ACCESS read-only
    STATUS     current
    DESCRIPTION
            "-- empty --"
    ::= { hmStatusTcpIpRadiussAccntActAccntSessEntry 16 }

-- {COLUMN} 1.3.6.1.4.1.248.32.18.1.9.12.2.16.1.17
hmStatusTcpIpRadiussAccntActAccntSessEntryNasPortType OBJECT-TYPE
    SYNTAX     INTEGER {
                  eUnknown (-1),
                  eAsync (0),
                  eSync (1),
                  eIsdnSync (2),
                  eV120 (3),
                  eV110 (4),
                  eVirtual (5),
                  ePiafs (6),
                  eHdlcClearChannel (7),
                  eX25 (8),
                  eX75 (9),
                  eG3Fax (10),
                  eSdsl (11),
                  eAdslCap (12),
                  eAdslDmt (13),
                  eIdsl (14),
                  eEthernet (15),
                  eXdsl (16),
                  eCable (17),
                  eWirelessOther (18),
                  eWireless80211 (19),
                  eTokenRing (20),
                  eFddi (21),
                  eWirelessCdma2000 (22),
                  eWirelessUmts (23),
                  eWireless1xEv (24),
                  eIapp (25),
                  eFttp (26),
                  eWireless80216 (27),
                  eWireless80220 (28),
                  eWireless80222 (29),
                  ePppoa (30),
                  ePppoeoa (31),
                  ePppoeoe (32),
                  ePppoeovlan (33),
                  ePppoeoqinq (34),
                  eXpon (35)
            }
    MAX-ACCESS read-only
    STATUS     current
    DESCRIPTION
            "-- empty --"
    ::= { hmStatusTcpIpRadiussAccntActAccntSessEntry 17 }

-- {COLUMN} 1.3.6.1.4.1.248.32.18.1.9.12.2.16.1.18
hmStatusTcpIpRadiussAccntActAccntSessEntryNasPortId OBJECT-TYPE
    SYNTAX     Integer32 (0..2147483647)
    MAX-ACCESS read-only
    STATUS     current
    DESCRIPTION
            "-- empty --"
    ::= { hmStatusTcpIpRadiussAccntActAccntSessEntry 18 }

-- {COLUMN} 1.3.6.1.4.1.248.32.18.1.9.12.2.16.1.19
hmStatusTcpIpRadiussAccntActAccntSessEntryCalledStationId OBJECT-TYPE
    SYNTAX     DisplayString (SIZE(0..48))
    MAX-ACCESS read-only
    STATUS     current
    DESCRIPTION
            "-- empty --"
    ::= { hmStatusTcpIpRadiussAccntActAccntSessEntry 19 }

-- {COLUMN} 1.3.6.1.4.1.248.32.18.1.9.12.2.16.1.20
hmStatusTcpIpRadiussAccntActAccntSessEntryCallingStationId OBJECT-TYPE
    SYNTAX     DisplayString (SIZE(0..48))
    MAX-ACCESS read-only
    STATUS     current
    DESCRIPTION
            "-- empty --"
    ::= { hmStatusTcpIpRadiussAccntActAccntSessEntry 20 }

-- {COLUMN} 1.3.6.1.4.1.248.32.18.1.9.12.2.16.1.21
hmStatusTcpIpRadiussAccntActAccntSessEntryNasIpv6Address OBJECT-TYPE
    SYNTAX     IpAddress
    MAX-ACCESS read-only
    STATUS     current
    DESCRIPTION
            "-- empty --"
    ::= { hmStatusTcpIpRadiussAccntActAccntSessEntry 21 }

-- {TABLE} 1.3.6.1.4.1.248.32.18.1.9.12.2.17
hmStatusTcpIpRadiussAccntComplAccntSessTable OBJECT-TYPE
    SYNTAX     SEQUENCE OF HmStatusTcpIpRadiussAccntComplAccntSessEntry
    MAX-ACCESS not-accessible
    STATUS     current
    DESCRIPTION
            ""
    ::= { hmStatusTcpIpRadiussAccnt 17 }

-- {ROW} 1.3.6.1.4.1.248.32.18.1.9.12.2.17.1
hmStatusTcpIpRadiussAccntComplAccntSessEntry OBJECT-TYPE
    SYNTAX     HmStatusTcpIpRadiussAccntComplAccntSessEntry
    MAX-ACCESS not-accessible
    STATUS     current
    DESCRIPTION
            ""
    INDEX {
            hmStatusTcpIpRadiussAccntComplAccntSessEntryIndex
          }
    ::= { hmStatusTcpIpRadiussAccntComplAccntSessTable 1 }

HmStatusTcpIpRadiussAccntComplAccntSessEntry ::= SEQUENCE {
            hmStatusTcpIpRadiussAccntComplAccntSessEntryIndex Integer32,
            hmStatusTcpIpRadiussAccntComplAccntSessEntryNasIpAddress IpAddress,
            hmStatusTcpIpRadiussAccntComplAccntSessEntryNasIdent DisplayString,
            hmStatusTcpIpRadiussAccntComplAccntSessEntrySessionId DisplayString,
            hmStatusTcpIpRadiussAccntComplAccntSessEntryUserName DisplayString,
            hmStatusTcpIpRadiussAccntComplAccntSessEntrySessionTime Integer32,
            hmStatusTcpIpRadiussAccntComplAccntSessEntryInputPackets Counter32,
            hmStatusTcpIpRadiussAccntComplAccntSessEntryOutputPackets Counter32,
            hmStatusTcpIpRadiussAccntComplAccntSessEntryInputOctets Counter64,
            hmStatusTcpIpRadiussAccntComplAccntSessEntryOutputOctets Counter64,
            hmStatusTcpIpRadiussAccntComplAccntSessEntryIpAddress IpAddress,
            hmStatusTcpIpRadiussAccntComplAccntSessEntryStartTime DisplayString,
            hmStatusTcpIpRadiussAccntComplAccntSessEntryStopTime DisplayString,
            hmStatusTcpIpRadiussAccntComplAccntSessEntryTerminateCause INTEGER,
            hmStatusTcpIpRadiussAccntComplAccntSessEntryNasPortType INTEGER,
            hmStatusTcpIpRadiussAccntComplAccntSessEntryNasPortId Integer32,
            hmStatusTcpIpRadiussAccntComplAccntSessEntryCalledStationId DisplayString,
            hmStatusTcpIpRadiussAccntComplAccntSessEntryCallingStationId DisplayString,
            hmStatusTcpIpRadiussAccntComplAccntSessEntryNasIpv6Address IpAddress
    }

-- {COLUMN} 1.3.6.1.4.1.248.32.18.1.9.12.2.17.1.1
hmStatusTcpIpRadiussAccntComplAccntSessEntryIndex OBJECT-TYPE
    SYNTAX     Integer32 (0..2147483647)
    MAX-ACCESS read-only
    STATUS     current
    DESCRIPTION
            "-- empty --"
    ::= { hmStatusTcpIpRadiussAccntComplAccntSessEntry 1 }

-- {COLUMN} 1.3.6.1.4.1.248.32.18.1.9.12.2.17.1.2
hmStatusTcpIpRadiussAccntComplAccntSessEntryNasIpAddress OBJECT-TYPE
    SYNTAX     IpAddress
    MAX-ACCESS read-only
    STATUS     current
    DESCRIPTION
            "-- empty --"
    ::= { hmStatusTcpIpRadiussAccntComplAccntSessEntry 2 }

-- {COLUMN} 1.3.6.1.4.1.248.32.18.1.9.12.2.17.1.3
hmStatusTcpIpRadiussAccntComplAccntSessEntryNasIdent OBJECT-TYPE
    SYNTAX     DisplayString (SIZE(0..64))
    MAX-ACCESS read-only
    STATUS     current
    DESCRIPTION
            "-- empty --"
    ::= { hmStatusTcpIpRadiussAccntComplAccntSessEntry 3 }

-- {COLUMN} 1.3.6.1.4.1.248.32.18.1.9.12.2.17.1.4
hmStatusTcpIpRadiussAccntComplAccntSessEntrySessionId OBJECT-TYPE
    SYNTAX     DisplayString (SIZE(0..128))
    MAX-ACCESS read-only
    STATUS     current
    DESCRIPTION
            "-- empty --"
    ::= { hmStatusTcpIpRadiussAccntComplAccntSessEntry 4 }

-- {COLUMN} 1.3.6.1.4.1.248.32.18.1.9.12.2.17.1.5
hmStatusTcpIpRadiussAccntComplAccntSessEntryUserName OBJECT-TYPE
    SYNTAX     DisplayString (SIZE(0..48))
    MAX-ACCESS read-only
    STATUS     current
    DESCRIPTION
            "-- empty --"
    ::= { hmStatusTcpIpRadiussAccntComplAccntSessEntry 5 }

-- {COLUMN} 1.3.6.1.4.1.248.32.18.1.9.12.2.17.1.6
hmStatusTcpIpRadiussAccntComplAccntSessEntrySessionTime OBJECT-TYPE
    SYNTAX     Integer32 (0..2147483647)
    MAX-ACCESS read-only
    STATUS     current
    DESCRIPTION
            "-- empty --"
    ::= { hmStatusTcpIpRadiussAccntComplAccntSessEntry 6 }

-- {COLUMN} 1.3.6.1.4.1.248.32.18.1.9.12.2.17.1.7
hmStatusTcpIpRadiussAccntComplAccntSessEntryInputPackets OBJECT-TYPE
    SYNTAX     Counter32
    MAX-ACCESS read-only
    STATUS     current
    DESCRIPTION
            "-- empty --"
    ::= { hmStatusTcpIpRadiussAccntComplAccntSessEntry 7 }

-- {COLUMN} 1.3.6.1.4.1.248.32.18.1.9.12.2.17.1.8
hmStatusTcpIpRadiussAccntComplAccntSessEntryOutputPackets OBJECT-TYPE
    SYNTAX     Counter32
    MAX-ACCESS read-only
    STATUS     current
    DESCRIPTION
            "-- empty --"
    ::= { hmStatusTcpIpRadiussAccntComplAccntSessEntry 8 }

-- {COLUMN} 1.3.6.1.4.1.248.32.18.1.9.12.2.17.1.9
hmStatusTcpIpRadiussAccntComplAccntSessEntryInputOctets OBJECT-TYPE
    SYNTAX     Counter64
    MAX-ACCESS read-only
    STATUS     current
    DESCRIPTION
            "-- empty --"
    ::= { hmStatusTcpIpRadiussAccntComplAccntSessEntry 9 }

-- {COLUMN} 1.3.6.1.4.1.248.32.18.1.9.12.2.17.1.10
hmStatusTcpIpRadiussAccntComplAccntSessEntryOutputOctets OBJECT-TYPE
    SYNTAX     Counter64
    MAX-ACCESS read-only
    STATUS     current
    DESCRIPTION
            "-- empty --"
    ::= { hmStatusTcpIpRadiussAccntComplAccntSessEntry 10 }

-- {COLUMN} 1.3.6.1.4.1.248.32.18.1.9.12.2.17.1.11
hmStatusTcpIpRadiussAccntComplAccntSessEntryIpAddress OBJECT-TYPE
    SYNTAX     IpAddress
    MAX-ACCESS read-only
    STATUS     current
    DESCRIPTION
            "-- empty --"
    ::= { hmStatusTcpIpRadiussAccntComplAccntSessEntry 11 }

-- {COLUMN} 1.3.6.1.4.1.248.32.18.1.9.12.2.17.1.12
hmStatusTcpIpRadiussAccntComplAccntSessEntryStartTime OBJECT-TYPE
    SYNTAX     DisplayString (SIZE(0..19))
    MAX-ACCESS read-only
    STATUS     current
    DESCRIPTION
            "-- empty --"
    ::= { hmStatusTcpIpRadiussAccntComplAccntSessEntry 12 }

-- {COLUMN} 1.3.6.1.4.1.248.32.18.1.9.12.2.17.1.13
hmStatusTcpIpRadiussAccntComplAccntSessEntryStopTime OBJECT-TYPE
    SYNTAX     DisplayString (SIZE(0..19))
    MAX-ACCESS read-only
    STATUS     current
    DESCRIPTION
            "-- empty --"
    ::= { hmStatusTcpIpRadiussAccntComplAccntSessEntry 13 }

-- {COLUMN} 1.3.6.1.4.1.248.32.18.1.9.12.2.17.1.14
hmStatusTcpIpRadiussAccntComplAccntSessEntryTerminateCause OBJECT-TYPE
    SYNTAX     INTEGER {
                  eUserRequest (1),
                  eLostCarrier (2),
                  eLostService (3),
                  eIdleTimeout (4),
                  eSessionTimeout (5),
                  eAdminReset (6),
                  eAdminReboot (7),
                  ePortError (8),
                  eNasError (9),
                  eNasRequest (10),
                  eNasReboot (11),
                  ePortUnneeded (12),
                  ePortPreempted (13),
                  ePortSuspended (14),
                  eServiceUnavailable (15),
                  eCallback (16),
                  eUserError (17),
                  eHostRequest (18),
                  eSupplicantRestart (19),
                  eReauthenticationFailure (20),
                  ePortReinit (21),
                  ePortAdminDisabled (22)
            }
    MAX-ACCESS read-only
    STATUS     current
    DESCRIPTION
            "-- empty --"
    ::= { hmStatusTcpIpRadiussAccntComplAccntSessEntry 14 }

-- {COLUMN} 1.3.6.1.4.1.248.32.18.1.9.12.2.17.1.17
hmStatusTcpIpRadiussAccntComplAccntSessEntryNasPortType OBJECT-TYPE
    SYNTAX     INTEGER {
                  eUnknown (-1),
                  eAsync (0),
                  eSync (1),
                  eIsdnSync (2),
                  eV120 (3),
                  eV110 (4),
                  eVirtual (5),
                  ePiafs (6),
                  eHdlcClearChannel (7),
                  eX25 (8),
                  eX75 (9),
                  eG3Fax (10),
                  eSdsl (11),
                  eAdslCap (12),
                  eAdslDmt (13),
                  eIdsl (14),
                  eEthernet (15),
                  eXdsl (16),
                  eCable (17),
                  eWirelessOther (18),
                  eWireless80211 (19),
                  eTokenRing (20),
                  eFddi (21),
                  eWirelessCdma2000 (22),
                  eWirelessUmts (23),
                  eWireless1xEv (24),
                  eIapp (25),
                  eFttp (26),
                  eWireless80216 (27),
                  eWireless80220 (28),
                  eWireless80222 (29),
                  ePppoa (30),
                  ePppoeoa (31),
                  ePppoeoe (32),
                  ePppoeovlan (33),
                  ePppoeoqinq (34),
                  eXpon (35)
            }
    MAX-ACCESS read-only
    STATUS     current
    DESCRIPTION
            "-- empty --"
    ::= { hmStatusTcpIpRadiussAccntComplAccntSessEntry 17 }

-- {COLUMN} 1.3.6.1.4.1.248.32.18.1.9.12.2.17.1.18
hmStatusTcpIpRadiussAccntComplAccntSessEntryNasPortId OBJECT-TYPE
    SYNTAX     Integer32 (0..2147483647)
    MAX-ACCESS read-only
    STATUS     current
    DESCRIPTION
            "-- empty --"
    ::= { hmStatusTcpIpRadiussAccntComplAccntSessEntry 18 }

-- {COLUMN} 1.3.6.1.4.1.248.32.18.1.9.12.2.17.1.19
hmStatusTcpIpRadiussAccntComplAccntSessEntryCalledStationId OBJECT-TYPE
    SYNTAX     DisplayString (SIZE(0..48))
    MAX-ACCESS read-only
    STATUS     current
    DESCRIPTION
            "-- empty --"
    ::= { hmStatusTcpIpRadiussAccntComplAccntSessEntry 19 }

-- {COLUMN} 1.3.6.1.4.1.248.32.18.1.9.12.2.17.1.20
hmStatusTcpIpRadiussAccntComplAccntSessEntryCallingStationId OBJECT-TYPE
    SYNTAX     DisplayString (SIZE(0..48))
    MAX-ACCESS read-only
    STATUS     current
    DESCRIPTION
            "-- empty --"
    ::= { hmStatusTcpIpRadiussAccntComplAccntSessEntry 20 }

-- {COLUMN} 1.3.6.1.4.1.248.32.18.1.9.12.2.17.1.21
hmStatusTcpIpRadiussAccntComplAccntSessEntryNasIpv6Address OBJECT-TYPE
    SYNTAX     IpAddress
    MAX-ACCESS read-only
    STATUS     current
    DESCRIPTION
            "-- empty --"
    ::= { hmStatusTcpIpRadiussAccntComplAccntSessEntry 21 }

-- {TABLE} 1.3.6.1.4.1.248.32.18.1.9.12.2.18
hmStatusTcpIpRadiussAccntAccountingTotalTable OBJECT-TYPE
    SYNTAX     SEQUENCE OF HmStatusTcpIpRadiussAccntAccountingTotalEntry
    MAX-ACCESS not-accessible
    STATUS     current
    DESCRIPTION
            "-- empty --"
    ::= { hmStatusTcpIpRadiussAccnt 18 }

-- {ROW} 1.3.6.1.4.1.248.32.18.1.9.12.2.18.1
hmStatusTcpIpRadiussAccntAccountingTotalEntry OBJECT-TYPE
    SYNTAX     HmStatusTcpIpRadiussAccntAccountingTotalEntry
    MAX-ACCESS not-accessible
    STATUS     current
    DESCRIPTION
            ""
    INDEX {
            hmStatusTcpIpRadiussAccntAccountingTotalEntryUserName
          }
    ::= { hmStatusTcpIpRadiussAccntAccountingTotalTable 1 }

HmStatusTcpIpRadiussAccntAccountingTotalEntry ::= SEQUENCE {
            hmStatusTcpIpRadiussAccntAccountingTotalEntryUserName DisplayString,
            hmStatusTcpIpRadiussAccntAccountingTotalEntryTime Integer32,
            hmStatusTcpIpRadiussAccntAccountingTotalEntryInputPackets Integer32,
            hmStatusTcpIpRadiussAccntAccountingTotalEntryOutputPackets Integer32,
            hmStatusTcpIpRadiussAccntAccountingTotalEntryInputOctets Integer32,
            hmStatusTcpIpRadiussAccntAccountingTotalEntryOutputOctets Integer32,
            hmStatusTcpIpRadiussAccntAccountingTotalEntryFirstLogin DisplayString
    }

-- {COLUMN} 1.3.6.1.4.1.248.32.18.1.9.12.2.18.1.1
hmStatusTcpIpRadiussAccntAccountingTotalEntryUserName OBJECT-TYPE
    SYNTAX     DisplayString (SIZE(0..48))
    MAX-ACCESS read-only
    STATUS     current
    DESCRIPTION
            "-- empty --"
    ::= { hmStatusTcpIpRadiussAccntAccountingTotalEntry 1 }

-- {COLUMN} 1.3.6.1.4.1.248.32.18.1.9.12.2.18.1.2
hmStatusTcpIpRadiussAccntAccountingTotalEntryTime OBJECT-TYPE
    SYNTAX     Integer32 (0..2147483647)
    MAX-ACCESS read-only
    STATUS     current
    DESCRIPTION
            "-- empty --"
    ::= { hmStatusTcpIpRadiussAccntAccountingTotalEntry 2 }

-- {COLUMN} 1.3.6.1.4.1.248.32.18.1.9.12.2.18.1.3
hmStatusTcpIpRadiussAccntAccountingTotalEntryInputPackets OBJECT-TYPE
    SYNTAX     Integer32 (0..2147483647)
    MAX-ACCESS read-only
    STATUS     current
    DESCRIPTION
            "-- empty --"
    ::= { hmStatusTcpIpRadiussAccntAccountingTotalEntry 3 }

-- {COLUMN} 1.3.6.1.4.1.248.32.18.1.9.12.2.18.1.4
hmStatusTcpIpRadiussAccntAccountingTotalEntryOutputPackets OBJECT-TYPE
    SYNTAX     Integer32 (0..2147483647)
    MAX-ACCESS read-only
    STATUS     current
    DESCRIPTION
            "-- empty --"
    ::= { hmStatusTcpIpRadiussAccntAccountingTotalEntry 4 }

-- {COLUMN} 1.3.6.1.4.1.248.32.18.1.9.12.2.18.1.5
hmStatusTcpIpRadiussAccntAccountingTotalEntryInputOctets OBJECT-TYPE
    SYNTAX     Integer32 (0..2147483647)
    MAX-ACCESS read-only
    STATUS     current
    DESCRIPTION
            "-- empty --"
    ::= { hmStatusTcpIpRadiussAccntAccountingTotalEntry 5 }

-- {COLUMN} 1.3.6.1.4.1.248.32.18.1.9.12.2.18.1.6
hmStatusTcpIpRadiussAccntAccountingTotalEntryOutputOctets OBJECT-TYPE
    SYNTAX     Integer32 (0..2147483647)
    MAX-ACCESS read-only
    STATUS     current
    DESCRIPTION
            "-- empty --"
    ::= { hmStatusTcpIpRadiussAccntAccountingTotalEntry 6 }

-- {COLUMN} 1.3.6.1.4.1.248.32.18.1.9.12.2.18.1.7
hmStatusTcpIpRadiussAccntAccountingTotalEntryFirstLogin OBJECT-TYPE
    SYNTAX     DisplayString (SIZE(0..21))
    MAX-ACCESS read-only
    STATUS     current
    DESCRIPTION
            "-- empty --"
    ::= { hmStatusTcpIpRadiussAccntAccountingTotalEntry 7 }

-- {SCALAR} 1.3.6.1.4.1.248.32.18.1.9.12.2.19
hmStatusTcpIpRadiussAccntDeleteAccountingTotal OBJECT-TYPE
    SYNTAX     DisplayString
    MAX-ACCESS read-write
    STATUS     current
    DESCRIPTION
            "-- empty --"
    ::= { hmStatusTcpIpRadiussAccnt 19 }

-- {TABLE} 1.3.6.1.4.1.248.32.18.1.9.12.2.20
hmStatusTcpIpRadiussAccntIpv6ClientsTable OBJECT-TYPE
    SYNTAX     SEQUENCE OF HmStatusTcpIpRadiussAccntIpv6ClientsEntry
    MAX-ACCESS not-accessible
    STATUS     current
    DESCRIPTION
            "-- empty --"
    ::= { hmStatusTcpIpRadiussAccnt 20 }

-- {ROW} 1.3.6.1.4.1.248.32.18.1.9.12.2.20.1
hmStatusTcpIpRadiussAccntIpv6ClientsEntry OBJECT-TYPE
    SYNTAX     HmStatusTcpIpRadiussAccntIpv6ClientsEntry
    MAX-ACCESS not-accessible
    STATUS     current
    DESCRIPTION
            ""
    INDEX {
            hmStatusTcpIpRadiussAccntIpv6ClientsEntryIpAddress
          }
    ::= { hmStatusTcpIpRadiussAccntIpv6ClientsTable 1 }

HmStatusTcpIpRadiussAccntIpv6ClientsEntry ::= SEQUENCE {
            hmStatusTcpIpRadiussAccntIpv6ClientsEntryIpAddress IpAddress,
            hmStatusTcpIpRadiussAccntIpv6ClientsEntryAccountRequests Counter32,
            hmStatusTcpIpRadiussAccntIpv6ClientsEntryDuplicateRequests Counter32,
            hmStatusTcpIpRadiussAccntIpv6ClientsEntryAccountResponses Counter32,
            hmStatusTcpIpRadiussAccntIpv6ClientsEntryAccountNorecords Counter32,
            hmStatusTcpIpRadiussAccntIpv6ClientsEntryMalfAccReq Counter32,
            hmStatusTcpIpRadiussAccntIpv6ClientsEntryBadAuthenticator Counter32,
            hmStatusTcpIpRadiussAccntIpv6ClientsEntryDropped Counter32,
            hmStatusTcpIpRadiussAccntIpv6ClientsEntryUnknownType Counter32,
            hmStatusTcpIpRadiussAccntIpv6ClientsEntryLastRequest Integer32,
            hmStatusTcpIpRadiussAccntIpv6ClientsEntryNasIdent DisplayString,
            hmStatusTcpIpRadiussAccntIpv6ClientsEntryStatusRequests Counter32,
            hmStatusTcpIpRadiussAccntIpv6ClientsEntryStatusResponses Counter32,
            hmStatusTcpIpRadiussAccntIpv6ClientsEntryLastStatusRequest Integer32
    }

-- {COLUMN} 1.3.6.1.4.1.248.32.18.1.9.12.2.20.1.1
hmStatusTcpIpRadiussAccntIpv6ClientsEntryIpAddress OBJECT-TYPE
    SYNTAX     IpAddress
    MAX-ACCESS read-only
    STATUS     current
    DESCRIPTION
            "-- empty --"
    ::= { hmStatusTcpIpRadiussAccntIpv6ClientsEntry 1 }

-- {COLUMN} 1.3.6.1.4.1.248.32.18.1.9.12.2.20.1.4
hmStatusTcpIpRadiussAccntIpv6ClientsEntryAccountRequests OBJECT-TYPE
    SYNTAX     Counter32
    MAX-ACCESS read-only
    STATUS     current
    DESCRIPTION
            "-- empty --"
    ::= { hmStatusTcpIpRadiussAccntIpv6ClientsEntry 4 }

-- {COLUMN} 1.3.6.1.4.1.248.32.18.1.9.12.2.20.1.5
hmStatusTcpIpRadiussAccntIpv6ClientsEntryDuplicateRequests OBJECT-TYPE
    SYNTAX     Counter32
    MAX-ACCESS read-only
    STATUS     current
    DESCRIPTION
            "-- empty --"
    ::= { hmStatusTcpIpRadiussAccntIpv6ClientsEntry 5 }

-- {COLUMN} 1.3.6.1.4.1.248.32.18.1.9.12.2.20.1.6
hmStatusTcpIpRadiussAccntIpv6ClientsEntryAccountResponses OBJECT-TYPE
    SYNTAX     Counter32
    MAX-ACCESS read-only
    STATUS     current
    DESCRIPTION
            "-- empty --"
    ::= { hmStatusTcpIpRadiussAccntIpv6ClientsEntry 6 }

-- {COLUMN} 1.3.6.1.4.1.248.32.18.1.9.12.2.20.1.7
hmStatusTcpIpRadiussAccntIpv6ClientsEntryAccountNorecords OBJECT-TYPE
    SYNTAX     Counter32
    MAX-ACCESS read-only
    STATUS     current
    DESCRIPTION
            "-- empty --"
    ::= { hmStatusTcpIpRadiussAccntIpv6ClientsEntry 7 }

-- {COLUMN} 1.3.6.1.4.1.248.32.18.1.9.12.2.20.1.9
hmStatusTcpIpRadiussAccntIpv6ClientsEntryMalfAccReq OBJECT-TYPE
    SYNTAX     Counter32
    MAX-ACCESS read-only
    STATUS     current
    DESCRIPTION
            ""
    ::= { hmStatusTcpIpRadiussAccntIpv6ClientsEntry 9 }

-- {COLUMN} 1.3.6.1.4.1.248.32.18.1.9.12.2.20.1.10
hmStatusTcpIpRadiussAccntIpv6ClientsEntryBadAuthenticator OBJECT-TYPE
    SYNTAX     Counter32
    MAX-ACCESS read-only
    STATUS     current
    DESCRIPTION
            "-- empty --"
    ::= { hmStatusTcpIpRadiussAccntIpv6ClientsEntry 10 }

-- {COLUMN} 1.3.6.1.4.1.248.32.18.1.9.12.2.20.1.11
hmStatusTcpIpRadiussAccntIpv6ClientsEntryDropped OBJECT-TYPE
    SYNTAX     Counter32
    MAX-ACCESS read-only
    STATUS     current
    DESCRIPTION
            "-- empty --"
    ::= { hmStatusTcpIpRadiussAccntIpv6ClientsEntry 11 }

-- {COLUMN} 1.3.6.1.4.1.248.32.18.1.9.12.2.20.1.12
hmStatusTcpIpRadiussAccntIpv6ClientsEntryUnknownType OBJECT-TYPE
    SYNTAX     Counter32
    MAX-ACCESS read-only
    STATUS     current
    DESCRIPTION
            "-- empty --"
    ::= { hmStatusTcpIpRadiussAccntIpv6ClientsEntry 12 }

-- {COLUMN} 1.3.6.1.4.1.248.32.18.1.9.12.2.20.1.13
hmStatusTcpIpRadiussAccntIpv6ClientsEntryLastRequest OBJECT-TYPE
    SYNTAX     Integer32 (0..2147483647)
    MAX-ACCESS read-only
    STATUS     current
    DESCRIPTION
            "-- empty --"
    ::= { hmStatusTcpIpRadiussAccntIpv6ClientsEntry 13 }

-- {COLUMN} 1.3.6.1.4.1.248.32.18.1.9.12.2.20.1.14
hmStatusTcpIpRadiussAccntIpv6ClientsEntryNasIdent OBJECT-TYPE
    SYNTAX     DisplayString (SIZE(0..64))
    MAX-ACCESS read-only
    STATUS     current
    DESCRIPTION
            "-- empty --"
    ::= { hmStatusTcpIpRadiussAccntIpv6ClientsEntry 14 }

-- {COLUMN} 1.3.6.1.4.1.248.32.18.1.9.12.2.20.1.30
hmStatusTcpIpRadiussAccntIpv6ClientsEntryStatusRequests OBJECT-TYPE
    SYNTAX     Counter32
    MAX-ACCESS read-only
    STATUS     current
    DESCRIPTION
            "-- empty --"
    ::= { hmStatusTcpIpRadiussAccntIpv6ClientsEntry 30 }

-- {COLUMN} 1.3.6.1.4.1.248.32.18.1.9.12.2.20.1.31
hmStatusTcpIpRadiussAccntIpv6ClientsEntryStatusResponses OBJECT-TYPE
    SYNTAX     Counter32
    MAX-ACCESS read-only
    STATUS     current
    DESCRIPTION
            "-- empty --"
    ::= { hmStatusTcpIpRadiussAccntIpv6ClientsEntry 31 }

-- {COLUMN} 1.3.6.1.4.1.248.32.18.1.9.12.2.20.1.32
hmStatusTcpIpRadiussAccntIpv6ClientsEntryLastStatusRequest OBJECT-TYPE
    SYNTAX     Integer32 (0..2147483647)
    MAX-ACCESS read-only
    STATUS     current
    DESCRIPTION
            "-- empty --"
    ::= { hmStatusTcpIpRadiussAccntIpv6ClientsEntry 32 }

-- {SCALAR} 1.3.6.1.4.1.248.32.18.1.9.12.2.30
hmStatusTcpIpRadiussAccntTotalStatusRequests OBJECT-TYPE
    SYNTAX     Counter32
    MAX-ACCESS read-only
    STATUS     current
    DESCRIPTION
            "-- empty --"
    ::= { hmStatusTcpIpRadiussAccnt 30 }

-- {SCALAR} 1.3.6.1.4.1.248.32.18.1.9.12.2.31
hmStatusTcpIpRadiussAccntTotalStatusResponses OBJECT-TYPE
    SYNTAX     Counter32
    MAX-ACCESS read-only
    STATUS     current
    DESCRIPTION
            "-- empty --"
    ::= { hmStatusTcpIpRadiussAccnt 31 }

-- {SCALAR} 1.3.6.1.4.1.248.32.18.1.9.12.2.100
hmStatusTcpIpRadiussAccntDeleteValues OBJECT-TYPE
    SYNTAX     DisplayString
    MAX-ACCESS read-write
    STATUS     current
    DESCRIPTION
            "-- empty --"
    ::= { hmStatusTcpIpRadiussAccnt 100 }

-- {TABLE} 1.3.6.1.4.1.248.32.18.1.9.12.10
hmStatusTcpIpRadiussLogTableTable OBJECT-TYPE
    SYNTAX     SEQUENCE OF HmStatusTcpIpRadiussLogTableEntry
    MAX-ACCESS not-accessible
    STATUS     current
    DESCRIPTION
            "-- empty --"
    ::= { hmStatusTcpIpRadiuss 10 }

-- {ROW} 1.3.6.1.4.1.248.32.18.1.9.12.10.1
hmStatusTcpIpRadiussLogTableEntry OBJECT-TYPE
    SYNTAX     HmStatusTcpIpRadiussLogTableEntry
    MAX-ACCESS not-accessible
    STATUS     current
    DESCRIPTION
            ""
    INDEX {
            hmStatusTcpIpRadiussLogTableEntryIndex
          }
    ::= { hmStatusTcpIpRadiussLogTableTable 1 }

HmStatusTcpIpRadiussLogTableEntry ::= SEQUENCE {
            hmStatusTcpIpRadiussLogTableEntryIndex Integer32,
            hmStatusTcpIpRadiussLogTableEntryTime DisplayString,
            hmStatusTcpIpRadiussLogTableEntryEvent DisplayString
    }

-- {COLUMN} 1.3.6.1.4.1.248.32.18.1.9.12.10.1.1
hmStatusTcpIpRadiussLogTableEntryIndex OBJECT-TYPE
    SYNTAX     Integer32 (0..2147483647)
    MAX-ACCESS read-only
    STATUS     current
    DESCRIPTION
            "-- empty --"
    ::= { hmStatusTcpIpRadiussLogTableEntry 1 }

-- {COLUMN} 1.3.6.1.4.1.248.32.18.1.9.12.10.1.2
hmStatusTcpIpRadiussLogTableEntryTime OBJECT-TYPE
    SYNTAX     DisplayString (SIZE(0..21))
    MAX-ACCESS read-only
    STATUS     current
    DESCRIPTION
            "-- empty --"
    ::= { hmStatusTcpIpRadiussLogTableEntry 2 }

-- {COLUMN} 1.3.6.1.4.1.248.32.18.1.9.12.10.1.3
hmStatusTcpIpRadiussLogTableEntryEvent OBJECT-TYPE
    SYNTAX     DisplayString (SIZE(0..128))
    MAX-ACCESS read-only
    STATUS     current
    DESCRIPTION
            "-- empty --"
    ::= { hmStatusTcpIpRadiussLogTableEntry 3 }

-- {SCALAR} 1.3.6.1.4.1.248.32.18.1.9.12.100
hmStatusTcpIpRadiussDeleteValues OBJECT-TYPE
    SYNTAX     DisplayString
    MAX-ACCESS read-write
    STATUS     current
    DESCRIPTION
            "-- empty --"
    ::= { hmStatusTcpIpRadiuss 100 }

-- {NODE} 1.3.6.1.4.1.248.32.18.1.9.13
hmStatusTcpIpRadiusc OBJECT IDENTIFIER ::= { hmStatusTcpIp 13 }

-- {SCALAR} 1.3.6.1.4.1.248.32.18.1.9.13.1
hmStatusTcpIpRadiuscInvalAuthAddrResp OBJECT-TYPE
    SYNTAX     Counter32
    MAX-ACCESS read-only
    STATUS     current
    DESCRIPTION
            ""
    ::= { hmStatusTcpIpRadiusc 1 }

-- {TABLE} 1.3.6.1.4.1.248.32.18.1.9.13.2
hmStatusTcpIpRadiuscAuthServTable OBJECT-TYPE
    SYNTAX     SEQUENCE OF HmStatusTcpIpRadiuscAuthServEntry
    MAX-ACCESS not-accessible
    STATUS     current
    DESCRIPTION
            ""
    ::= { hmStatusTcpIpRadiusc 2 }

-- {ROW} 1.3.6.1.4.1.248.32.18.1.9.13.2.1
hmStatusTcpIpRadiuscAuthServEntry OBJECT-TYPE
    SYNTAX     HmStatusTcpIpRadiuscAuthServEntry
    MAX-ACCESS not-accessible
    STATUS     current
    DESCRIPTION
            ""
    INDEX {
            hmStatusTcpIpRadiuscAuthServEntryIpAddr,
            hmStatusTcpIpRadiuscAuthServEntryPort
          }
    ::= { hmStatusTcpIpRadiuscAuthServTable 1 }

HmStatusTcpIpRadiuscAuthServEntry ::= SEQUENCE {
            hmStatusTcpIpRadiuscAuthServEntryIpAddr IpAddress,
            hmStatusTcpIpRadiuscAuthServEntryPort Integer32,
            hmStatusTcpIpRadiuscAuthServEntryLastRequest Integer32,
            hmStatusTcpIpRadiuscAuthServEntryRoundTripTime Counter32,
            hmStatusTcpIpRadiuscAuthServEntryAccReq Counter32,
            hmStatusTcpIpRadiuscAuthServEntryAccRetrs Counter32,
            hmStatusTcpIpRadiuscAuthServEntryAccAccepts Counter32,
            hmStatusTcpIpRadiuscAuthServEntryAccRej Counter32,
            hmStatusTcpIpRadiuscAuthServEntryAccChallenges Counter32,
            hmStatusTcpIpRadiuscAuthServEntryMalfAccResp Counter32,
            hmStatusTcpIpRadiuscAuthServEntryBadAuth Counter32,
            hmStatusTcpIpRadiuscAuthServEntryPendReq Counter32,
            hmStatusTcpIpRadiuscAuthServEntryTimeouts Counter32,
            hmStatusTcpIpRadiuscAuthServEntryUnknownTypes Counter32,
            hmStatusTcpIpRadiuscAuthServEntryDropped Counter32
    }

-- {COLUMN} 1.3.6.1.4.1.248.32.18.1.9.13.2.1.1
hmStatusTcpIpRadiuscAuthServEntryIpAddr OBJECT-TYPE
    SYNTAX     IpAddress
    MAX-ACCESS read-only
    STATUS     current
    DESCRIPTION
            ""
    ::= { hmStatusTcpIpRadiuscAuthServEntry 1 }

-- {COLUMN} 1.3.6.1.4.1.248.32.18.1.9.13.2.1.2
hmStatusTcpIpRadiuscAuthServEntryPort OBJECT-TYPE
    SYNTAX     Integer32 (0..65535)
    MAX-ACCESS read-only
    STATUS     current
    DESCRIPTION
            ""
    ::= { hmStatusTcpIpRadiuscAuthServEntry 2 }

-- {COLUMN} 1.3.6.1.4.1.248.32.18.1.9.13.2.1.3
hmStatusTcpIpRadiuscAuthServEntryLastRequest OBJECT-TYPE
    SYNTAX     Integer32 (0..2147483647)
    MAX-ACCESS read-only
    STATUS     current
    DESCRIPTION
            ""
    ::= { hmStatusTcpIpRadiuscAuthServEntry 3 }

-- {COLUMN} 1.3.6.1.4.1.248.32.18.1.9.13.2.1.4
hmStatusTcpIpRadiuscAuthServEntryRoundTripTime OBJECT-TYPE
    SYNTAX     Counter32
    MAX-ACCESS read-only
    STATUS     current
    DESCRIPTION
            ""
    ::= { hmStatusTcpIpRadiuscAuthServEntry 4 }

-- {COLUMN} 1.3.6.1.4.1.248.32.18.1.9.13.2.1.5
hmStatusTcpIpRadiuscAuthServEntryAccReq OBJECT-TYPE
    SYNTAX     Counter32
    MAX-ACCESS read-only
    STATUS     current
    DESCRIPTION
            ""
    ::= { hmStatusTcpIpRadiuscAuthServEntry 5 }

-- {COLUMN} 1.3.6.1.4.1.248.32.18.1.9.13.2.1.6
hmStatusTcpIpRadiuscAuthServEntryAccRetrs OBJECT-TYPE
    SYNTAX     Counter32
    MAX-ACCESS read-only
    STATUS     current
    DESCRIPTION
            ""
    ::= { hmStatusTcpIpRadiuscAuthServEntry 6 }

-- {COLUMN} 1.3.6.1.4.1.248.32.18.1.9.13.2.1.7
hmStatusTcpIpRadiuscAuthServEntryAccAccepts OBJECT-TYPE
    SYNTAX     Counter32
    MAX-ACCESS read-only
    STATUS     current
    DESCRIPTION
            ""
    ::= { hmStatusTcpIpRadiuscAuthServEntry 7 }

-- {COLUMN} 1.3.6.1.4.1.248.32.18.1.9.13.2.1.8
hmStatusTcpIpRadiuscAuthServEntryAccRej OBJECT-TYPE
    SYNTAX     Counter32
    MAX-ACCESS read-only
    STATUS     current
    DESCRIPTION
            ""
    ::= { hmStatusTcpIpRadiuscAuthServEntry 8 }

-- {COLUMN} 1.3.6.1.4.1.248.32.18.1.9.13.2.1.9
hmStatusTcpIpRadiuscAuthServEntryAccChallenges OBJECT-TYPE
    SYNTAX     Counter32
    MAX-ACCESS read-only
    STATUS     current
    DESCRIPTION
            ""
    ::= { hmStatusTcpIpRadiuscAuthServEntry 9 }

-- {COLUMN} 1.3.6.1.4.1.248.32.18.1.9.13.2.1.10
hmStatusTcpIpRadiuscAuthServEntryMalfAccResp OBJECT-TYPE
    SYNTAX     Counter32
    MAX-ACCESS read-only
    STATUS     current
    DESCRIPTION
            ""
    ::= { hmStatusTcpIpRadiuscAuthServEntry 10 }

-- {COLUMN} 1.3.6.1.4.1.248.32.18.1.9.13.2.1.11
hmStatusTcpIpRadiuscAuthServEntryBadAuth OBJECT-TYPE
    SYNTAX     Counter32
    MAX-ACCESS read-only
    STATUS     current
    DESCRIPTION
            ""
    ::= { hmStatusTcpIpRadiuscAuthServEntry 11 }

-- {COLUMN} 1.3.6.1.4.1.248.32.18.1.9.13.2.1.12
hmStatusTcpIpRadiuscAuthServEntryPendReq OBJECT-TYPE
    SYNTAX     Counter32
    MAX-ACCESS read-only
    STATUS     current
    DESCRIPTION
            ""
    ::= { hmStatusTcpIpRadiuscAuthServEntry 12 }

-- {COLUMN} 1.3.6.1.4.1.248.32.18.1.9.13.2.1.13
hmStatusTcpIpRadiuscAuthServEntryTimeouts OBJECT-TYPE
    SYNTAX     Counter32
    MAX-ACCESS read-only
    STATUS     current
    DESCRIPTION
            ""
    ::= { hmStatusTcpIpRadiuscAuthServEntry 13 }

-- {COLUMN} 1.3.6.1.4.1.248.32.18.1.9.13.2.1.14
hmStatusTcpIpRadiuscAuthServEntryUnknownTypes OBJECT-TYPE
    SYNTAX     Counter32
    MAX-ACCESS read-only
    STATUS     current
    DESCRIPTION
            ""
    ::= { hmStatusTcpIpRadiuscAuthServEntry 14 }

-- {COLUMN} 1.3.6.1.4.1.248.32.18.1.9.13.2.1.15
hmStatusTcpIpRadiuscAuthServEntryDropped OBJECT-TYPE
    SYNTAX     Counter32
    MAX-ACCESS read-only
    STATUS     current
    DESCRIPTION
            ""
    ::= { hmStatusTcpIpRadiuscAuthServEntry 15 }

-- {TABLE} 1.3.6.1.4.1.248.32.18.1.9.13.3
hmStatusTcpIpRadiuscIpv6AuthenticationServersTable OBJECT-TYPE
    SYNTAX     SEQUENCE OF HmStatusTcpIpRadiuscIpv6AuthenticationServersEntry
    MAX-ACCESS not-accessible
    STATUS     current
    DESCRIPTION
            "-- empty --"
    ::= { hmStatusTcpIpRadiusc 3 }

-- {ROW} 1.3.6.1.4.1.248.32.18.1.9.13.3.1
hmStatusTcpIpRadiuscIpv6AuthenticationServersEntry OBJECT-TYPE
    SYNTAX     HmStatusTcpIpRadiuscIpv6AuthenticationServersEntry
    MAX-ACCESS not-accessible
    STATUS     current
    DESCRIPTION
            ""
    INDEX {
            hmStatusTcpIpRadiuscIpv6AuthenticationServersEntryIpAddr,
            hmStatusTcpIpRadiuscIpv6AuthenticationServersEntryPort
          }
    ::= { hmStatusTcpIpRadiuscIpv6AuthenticationServersTable 1 }

HmStatusTcpIpRadiuscIpv6AuthenticationServersEntry ::= SEQUENCE {
            hmStatusTcpIpRadiuscIpv6AuthenticationServersEntryIpAddr IpAddress,
            hmStatusTcpIpRadiuscIpv6AuthenticationServersEntryPort Integer32,
            hmStatusTcpIpRadiuscIpv6AuthenticationServersEntryLastRequest Integer32,
            hmStatusTcpIpRadiuscIpv6AuthenticationServersEntryRoundTripTime Counter32,
            hmStatusTcpIpRadiuscIpv6AuthenticationServersEntryAccReq Counter32,
            hmStatusTcpIpRadiuscIpv6AuthenticationServersEntryAccRetrs Counter32,
            hmStatusTcpIpRadiuscIpv6AuthenticationServersEntryAccAccepts Counter32,
            hmStatusTcpIpRadiuscIpv6AuthenticationServersEntryAccRej Counter32,
            hmStatusTcpIpRadiuscIpv6AuthenticationServersEntryAccChallenges Counter32,
            hmStatusTcpIpRadiuscIpv6AuthenticationServersEntryMalfAccResp Counter32,
            hmStatusTcpIpRadiuscIpv6AuthenticationServersEntryBadAuth Counter32,
            hmStatusTcpIpRadiuscIpv6AuthenticationServersEntryPendReq Counter32,
            hmStatusTcpIpRadiuscIpv6AuthenticationServersEntryTimeouts Counter32,
            hmStatusTcpIpRadiuscIpv6AuthenticationServersEntryUnknownTypes Counter32,
            hmStatusTcpIpRadiuscIpv6AuthenticationServersEntryDropped Counter32
    }

-- {COLUMN} 1.3.6.1.4.1.248.32.18.1.9.13.3.1.1
hmStatusTcpIpRadiuscIpv6AuthenticationServersEntryIpAddr OBJECT-TYPE
    SYNTAX     IpAddress
    MAX-ACCESS read-only
    STATUS     current
    DESCRIPTION
            ""
    ::= { hmStatusTcpIpRadiuscIpv6AuthenticationServersEntry 1 }

-- {COLUMN} 1.3.6.1.4.1.248.32.18.1.9.13.3.1.2
hmStatusTcpIpRadiuscIpv6AuthenticationServersEntryPort OBJECT-TYPE
    SYNTAX     Integer32 (0..65535)
    MAX-ACCESS read-only
    STATUS     current
    DESCRIPTION
            ""
    ::= { hmStatusTcpIpRadiuscIpv6AuthenticationServersEntry 2 }

-- {COLUMN} 1.3.6.1.4.1.248.32.18.1.9.13.3.1.3
hmStatusTcpIpRadiuscIpv6AuthenticationServersEntryLastRequest OBJECT-TYPE
    SYNTAX     Integer32 (0..2147483647)
    MAX-ACCESS read-only
    STATUS     current
    DESCRIPTION
            ""
    ::= { hmStatusTcpIpRadiuscIpv6AuthenticationServersEntry 3 }

-- {COLUMN} 1.3.6.1.4.1.248.32.18.1.9.13.3.1.4
hmStatusTcpIpRadiuscIpv6AuthenticationServersEntryRoundTripTime OBJECT-TYPE
    SYNTAX     Counter32
    MAX-ACCESS read-only
    STATUS     current
    DESCRIPTION
            ""
    ::= { hmStatusTcpIpRadiuscIpv6AuthenticationServersEntry 4 }

-- {COLUMN} 1.3.6.1.4.1.248.32.18.1.9.13.3.1.5
hmStatusTcpIpRadiuscIpv6AuthenticationServersEntryAccReq OBJECT-TYPE
    SYNTAX     Counter32
    MAX-ACCESS read-only
    STATUS     current
    DESCRIPTION
            ""
    ::= { hmStatusTcpIpRadiuscIpv6AuthenticationServersEntry 5 }

-- {COLUMN} 1.3.6.1.4.1.248.32.18.1.9.13.3.1.6
hmStatusTcpIpRadiuscIpv6AuthenticationServersEntryAccRetrs OBJECT-TYPE
    SYNTAX     Counter32
    MAX-ACCESS read-only
    STATUS     current
    DESCRIPTION
            ""
    ::= { hmStatusTcpIpRadiuscIpv6AuthenticationServersEntry 6 }

-- {COLUMN} 1.3.6.1.4.1.248.32.18.1.9.13.3.1.7
hmStatusTcpIpRadiuscIpv6AuthenticationServersEntryAccAccepts OBJECT-TYPE
    SYNTAX     Counter32
    MAX-ACCESS read-only
    STATUS     current
    DESCRIPTION
            ""
    ::= { hmStatusTcpIpRadiuscIpv6AuthenticationServersEntry 7 }

-- {COLUMN} 1.3.6.1.4.1.248.32.18.1.9.13.3.1.8
hmStatusTcpIpRadiuscIpv6AuthenticationServersEntryAccRej OBJECT-TYPE
    SYNTAX     Counter32
    MAX-ACCESS read-only
    STATUS     current
    DESCRIPTION
            ""
    ::= { hmStatusTcpIpRadiuscIpv6AuthenticationServersEntry 8 }

-- {COLUMN} 1.3.6.1.4.1.248.32.18.1.9.13.3.1.9
hmStatusTcpIpRadiuscIpv6AuthenticationServersEntryAccChallenges OBJECT-TYPE
    SYNTAX     Counter32
    MAX-ACCESS read-only
    STATUS     current
    DESCRIPTION
            ""
    ::= { hmStatusTcpIpRadiuscIpv6AuthenticationServersEntry 9 }

-- {COLUMN} 1.3.6.1.4.1.248.32.18.1.9.13.3.1.10
hmStatusTcpIpRadiuscIpv6AuthenticationServersEntryMalfAccResp OBJECT-TYPE
    SYNTAX     Counter32
    MAX-ACCESS read-only
    STATUS     current
    DESCRIPTION
            ""
    ::= { hmStatusTcpIpRadiuscIpv6AuthenticationServersEntry 10 }

-- {COLUMN} 1.3.6.1.4.1.248.32.18.1.9.13.3.1.11
hmStatusTcpIpRadiuscIpv6AuthenticationServersEntryBadAuth OBJECT-TYPE
    SYNTAX     Counter32
    MAX-ACCESS read-only
    STATUS     current
    DESCRIPTION
            ""
    ::= { hmStatusTcpIpRadiuscIpv6AuthenticationServersEntry 11 }

-- {COLUMN} 1.3.6.1.4.1.248.32.18.1.9.13.3.1.12
hmStatusTcpIpRadiuscIpv6AuthenticationServersEntryPendReq OBJECT-TYPE
    SYNTAX     Counter32
    MAX-ACCESS read-only
    STATUS     current
    DESCRIPTION
            ""
    ::= { hmStatusTcpIpRadiuscIpv6AuthenticationServersEntry 12 }

-- {COLUMN} 1.3.6.1.4.1.248.32.18.1.9.13.3.1.13
hmStatusTcpIpRadiuscIpv6AuthenticationServersEntryTimeouts OBJECT-TYPE
    SYNTAX     Counter32
    MAX-ACCESS read-only
    STATUS     current
    DESCRIPTION
            ""
    ::= { hmStatusTcpIpRadiuscIpv6AuthenticationServersEntry 13 }

-- {COLUMN} 1.3.6.1.4.1.248.32.18.1.9.13.3.1.14
hmStatusTcpIpRadiuscIpv6AuthenticationServersEntryUnknownTypes OBJECT-TYPE
    SYNTAX     Counter32
    MAX-ACCESS read-only
    STATUS     current
    DESCRIPTION
            ""
    ::= { hmStatusTcpIpRadiuscIpv6AuthenticationServersEntry 14 }

-- {COLUMN} 1.3.6.1.4.1.248.32.18.1.9.13.3.1.15
hmStatusTcpIpRadiuscIpv6AuthenticationServersEntryDropped OBJECT-TYPE
    SYNTAX     Counter32
    MAX-ACCESS read-only
    STATUS     current
    DESCRIPTION
            ""
    ::= { hmStatusTcpIpRadiuscIpv6AuthenticationServersEntry 15 }

-- {SCALAR} 1.3.6.1.4.1.248.32.18.1.9.13.11
hmStatusTcpIpRadiuscInvalAccntAddrResp OBJECT-TYPE
    SYNTAX     Counter32
    MAX-ACCESS read-only
    STATUS     current
    DESCRIPTION
            ""
    ::= { hmStatusTcpIpRadiusc 11 }

-- {TABLE} 1.3.6.1.4.1.248.32.18.1.9.13.12
hmStatusTcpIpRadiuscAccntServTable OBJECT-TYPE
    SYNTAX     SEQUENCE OF HmStatusTcpIpRadiuscAccntServEntry
    MAX-ACCESS not-accessible
    STATUS     current
    DESCRIPTION
            ""
    ::= { hmStatusTcpIpRadiusc 12 }

-- {ROW} 1.3.6.1.4.1.248.32.18.1.9.13.12.1
hmStatusTcpIpRadiuscAccntServEntry OBJECT-TYPE
    SYNTAX     HmStatusTcpIpRadiuscAccntServEntry
    MAX-ACCESS not-accessible
    STATUS     current
    DESCRIPTION
            ""
    INDEX {
            hmStatusTcpIpRadiuscAccntServEntryIpAddr,
            hmStatusTcpIpRadiuscAccntServEntryPort
          }
    ::= { hmStatusTcpIpRadiuscAccntServTable 1 }

HmStatusTcpIpRadiuscAccntServEntry ::= SEQUENCE {
            hmStatusTcpIpRadiuscAccntServEntryIpAddr IpAddress,
            hmStatusTcpIpRadiuscAccntServEntryPort Integer32,
            hmStatusTcpIpRadiuscAccntServEntryLastRequest Integer32,
            hmStatusTcpIpRadiuscAccntServEntryRoundTripTime Counter32,
            hmStatusTcpIpRadiuscAccntServEntryAccntReq Counter32,
            hmStatusTcpIpRadiuscAccntServEntryAccntRetrans Counter32,
            hmStatusTcpIpRadiuscAccntServEntryAccntResp Counter32,
            hmStatusTcpIpRadiuscAccntServEntryMalfAccntResp Counter32,
            hmStatusTcpIpRadiuscAccntServEntryBadAuth Counter32,
            hmStatusTcpIpRadiuscAccntServEntryPendReq Counter32,
            hmStatusTcpIpRadiuscAccntServEntryTimeouts Counter32,
            hmStatusTcpIpRadiuscAccntServEntryUnknownTypes Counter32,
            hmStatusTcpIpRadiuscAccntServEntryDropped Counter32
    }

-- {COLUMN} 1.3.6.1.4.1.248.32.18.1.9.13.12.1.1
hmStatusTcpIpRadiuscAccntServEntryIpAddr OBJECT-TYPE
    SYNTAX     IpAddress
    MAX-ACCESS read-only
    STATUS     current
    DESCRIPTION
            ""
    ::= { hmStatusTcpIpRadiuscAccntServEntry 1 }

-- {COLUMN} 1.3.6.1.4.1.248.32.18.1.9.13.12.1.2
hmStatusTcpIpRadiuscAccntServEntryPort OBJECT-TYPE
    SYNTAX     Integer32 (0..65535)
    MAX-ACCESS read-only
    STATUS     current
    DESCRIPTION
            ""
    ::= { hmStatusTcpIpRadiuscAccntServEntry 2 }

-- {COLUMN} 1.3.6.1.4.1.248.32.18.1.9.13.12.1.3
hmStatusTcpIpRadiuscAccntServEntryLastRequest OBJECT-TYPE
    SYNTAX     Integer32 (0..2147483647)
    MAX-ACCESS read-only
    STATUS     current
    DESCRIPTION
            ""
    ::= { hmStatusTcpIpRadiuscAccntServEntry 3 }

-- {COLUMN} 1.3.6.1.4.1.248.32.18.1.9.13.12.1.4
hmStatusTcpIpRadiuscAccntServEntryRoundTripTime OBJECT-TYPE
    SYNTAX     Counter32
    MAX-ACCESS read-only
    STATUS     current
    DESCRIPTION
            ""
    ::= { hmStatusTcpIpRadiuscAccntServEntry 4 }

-- {COLUMN} 1.3.6.1.4.1.248.32.18.1.9.13.12.1.5
hmStatusTcpIpRadiuscAccntServEntryAccntReq OBJECT-TYPE
    SYNTAX     Counter32
    MAX-ACCESS read-only
    STATUS     current
    DESCRIPTION
            ""
    ::= { hmStatusTcpIpRadiuscAccntServEntry 5 }

-- {COLUMN} 1.3.6.1.4.1.248.32.18.1.9.13.12.1.6
hmStatusTcpIpRadiuscAccntServEntryAccntRetrans OBJECT-TYPE
    SYNTAX     Counter32
    MAX-ACCESS read-only
    STATUS     current
    DESCRIPTION
            ""
    ::= { hmStatusTcpIpRadiuscAccntServEntry 6 }

-- {COLUMN} 1.3.6.1.4.1.248.32.18.1.9.13.12.1.7
hmStatusTcpIpRadiuscAccntServEntryAccntResp OBJECT-TYPE
    SYNTAX     Counter32
    MAX-ACCESS read-only
    STATUS     current
    DESCRIPTION
            ""
    ::= { hmStatusTcpIpRadiuscAccntServEntry 7 }

-- {COLUMN} 1.3.6.1.4.1.248.32.18.1.9.13.12.1.8
hmStatusTcpIpRadiuscAccntServEntryMalfAccntResp OBJECT-TYPE
    SYNTAX     Counter32
    MAX-ACCESS read-only
    STATUS     current
    DESCRIPTION
            ""
    ::= { hmStatusTcpIpRadiuscAccntServEntry 8 }

-- {COLUMN} 1.3.6.1.4.1.248.32.18.1.9.13.12.1.9
hmStatusTcpIpRadiuscAccntServEntryBadAuth OBJECT-TYPE
    SYNTAX     Counter32
    MAX-ACCESS read-only
    STATUS     current
    DESCRIPTION
            ""
    ::= { hmStatusTcpIpRadiuscAccntServEntry 9 }

-- {COLUMN} 1.3.6.1.4.1.248.32.18.1.9.13.12.1.10
hmStatusTcpIpRadiuscAccntServEntryPendReq OBJECT-TYPE
    SYNTAX     Counter32
    MAX-ACCESS read-only
    STATUS     current
    DESCRIPTION
            ""
    ::= { hmStatusTcpIpRadiuscAccntServEntry 10 }

-- {COLUMN} 1.3.6.1.4.1.248.32.18.1.9.13.12.1.11
hmStatusTcpIpRadiuscAccntServEntryTimeouts OBJECT-TYPE
    SYNTAX     Counter32
    MAX-ACCESS read-only
    STATUS     current
    DESCRIPTION
            ""
    ::= { hmStatusTcpIpRadiuscAccntServEntry 11 }

-- {COLUMN} 1.3.6.1.4.1.248.32.18.1.9.13.12.1.12
hmStatusTcpIpRadiuscAccntServEntryUnknownTypes OBJECT-TYPE
    SYNTAX     Counter32
    MAX-ACCESS read-only
    STATUS     current
    DESCRIPTION
            ""
    ::= { hmStatusTcpIpRadiuscAccntServEntry 12 }

-- {COLUMN} 1.3.6.1.4.1.248.32.18.1.9.13.12.1.13
hmStatusTcpIpRadiuscAccntServEntryDropped OBJECT-TYPE
    SYNTAX     Counter32
    MAX-ACCESS read-only
    STATUS     current
    DESCRIPTION
            ""
    ::= { hmStatusTcpIpRadiuscAccntServEntry 13 }

-- {TABLE} 1.3.6.1.4.1.248.32.18.1.9.13.13
hmStatusTcpIpRadiuscIpv6AccountingServersTable OBJECT-TYPE
    SYNTAX     SEQUENCE OF HmStatusTcpIpRadiuscIpv6AccountingServersEntry
    MAX-ACCESS not-accessible
    STATUS     current
    DESCRIPTION
            "-- empty --"
    ::= { hmStatusTcpIpRadiusc 13 }

-- {ROW} 1.3.6.1.4.1.248.32.18.1.9.13.13.1
hmStatusTcpIpRadiuscIpv6AccountingServersEntry OBJECT-TYPE
    SYNTAX     HmStatusTcpIpRadiuscIpv6AccountingServersEntry
    MAX-ACCESS not-accessible
    STATUS     current
    DESCRIPTION
            ""
    INDEX {
            hmStatusTcpIpRadiuscIpv6AccountingServersEntryIpAddr,
            hmStatusTcpIpRadiuscIpv6AccountingServersEntryPort
          }
    ::= { hmStatusTcpIpRadiuscIpv6AccountingServersTable 1 }

HmStatusTcpIpRadiuscIpv6AccountingServersEntry ::= SEQUENCE {
            hmStatusTcpIpRadiuscIpv6AccountingServersEntryIpAddr IpAddress,
            hmStatusTcpIpRadiuscIpv6AccountingServersEntryPort Integer32,
            hmStatusTcpIpRadiuscIpv6AccountingServersEntryLastRequest Integer32,
            hmStatusTcpIpRadiuscIpv6AccountingServersEntryRoundTripTime Counter32,
            hmStatusTcpIpRadiuscIpv6AccountingServersEntryAccntReq Counter32,
            hmStatusTcpIpRadiuscIpv6AccountingServersEntryAccntRetrans Counter32,
            hmStatusTcpIpRadiuscIpv6AccountingServersEntryAccntResp Counter32,
            hmStatusTcpIpRadiuscIpv6AccountingServersEntryMalfAccntResp Counter32,
            hmStatusTcpIpRadiuscIpv6AccountingServersEntryBadAuth Counter32,
            hmStatusTcpIpRadiuscIpv6AccountingServersEntryPendReq Counter32,
            hmStatusTcpIpRadiuscIpv6AccountingServersEntryTimeouts Counter32,
            hmStatusTcpIpRadiuscIpv6AccountingServersEntryUnknownTypes Counter32,
            hmStatusTcpIpRadiuscIpv6AccountingServersEntryDropped Counter32
    }

-- {COLUMN} 1.3.6.1.4.1.248.32.18.1.9.13.13.1.1
hmStatusTcpIpRadiuscIpv6AccountingServersEntryIpAddr OBJECT-TYPE
    SYNTAX     IpAddress
    MAX-ACCESS read-only
    STATUS     current
    DESCRIPTION
            ""
    ::= { hmStatusTcpIpRadiuscIpv6AccountingServersEntry 1 }

-- {COLUMN} 1.3.6.1.4.1.248.32.18.1.9.13.13.1.2
hmStatusTcpIpRadiuscIpv6AccountingServersEntryPort OBJECT-TYPE
    SYNTAX     Integer32 (0..65535)
    MAX-ACCESS read-only
    STATUS     current
    DESCRIPTION
            ""
    ::= { hmStatusTcpIpRadiuscIpv6AccountingServersEntry 2 }

-- {COLUMN} 1.3.6.1.4.1.248.32.18.1.9.13.13.1.3
hmStatusTcpIpRadiuscIpv6AccountingServersEntryLastRequest OBJECT-TYPE
    SYNTAX     Integer32 (0..2147483647)
    MAX-ACCESS read-only
    STATUS     current
    DESCRIPTION
            ""
    ::= { hmStatusTcpIpRadiuscIpv6AccountingServersEntry 3 }

-- {COLUMN} 1.3.6.1.4.1.248.32.18.1.9.13.13.1.4
hmStatusTcpIpRadiuscIpv6AccountingServersEntryRoundTripTime OBJECT-TYPE
    SYNTAX     Counter32
    MAX-ACCESS read-only
    STATUS     current
    DESCRIPTION
            ""
    ::= { hmStatusTcpIpRadiuscIpv6AccountingServersEntry 4 }

-- {COLUMN} 1.3.6.1.4.1.248.32.18.1.9.13.13.1.5
hmStatusTcpIpRadiuscIpv6AccountingServersEntryAccntReq OBJECT-TYPE
    SYNTAX     Counter32
    MAX-ACCESS read-only
    STATUS     current
    DESCRIPTION
            ""
    ::= { hmStatusTcpIpRadiuscIpv6AccountingServersEntry 5 }

-- {COLUMN} 1.3.6.1.4.1.248.32.18.1.9.13.13.1.6
hmStatusTcpIpRadiuscIpv6AccountingServersEntryAccntRetrans OBJECT-TYPE
    SYNTAX     Counter32
    MAX-ACCESS read-only
    STATUS     current
    DESCRIPTION
            ""
    ::= { hmStatusTcpIpRadiuscIpv6AccountingServersEntry 6 }

-- {COLUMN} 1.3.6.1.4.1.248.32.18.1.9.13.13.1.7
hmStatusTcpIpRadiuscIpv6AccountingServersEntryAccntResp OBJECT-TYPE
    SYNTAX     Counter32
    MAX-ACCESS read-only
    STATUS     current
    DESCRIPTION
            ""
    ::= { hmStatusTcpIpRadiuscIpv6AccountingServersEntry 7 }

-- {COLUMN} 1.3.6.1.4.1.248.32.18.1.9.13.13.1.8
hmStatusTcpIpRadiuscIpv6AccountingServersEntryMalfAccntResp OBJECT-TYPE
    SYNTAX     Counter32
    MAX-ACCESS read-only
    STATUS     current
    DESCRIPTION
            ""
    ::= { hmStatusTcpIpRadiuscIpv6AccountingServersEntry 8 }

-- {COLUMN} 1.3.6.1.4.1.248.32.18.1.9.13.13.1.9
hmStatusTcpIpRadiuscIpv6AccountingServersEntryBadAuth OBJECT-TYPE
    SYNTAX     Counter32
    MAX-ACCESS read-only
    STATUS     current
    DESCRIPTION
            ""
    ::= { hmStatusTcpIpRadiuscIpv6AccountingServersEntry 9 }

-- {COLUMN} 1.3.6.1.4.1.248.32.18.1.9.13.13.1.10
hmStatusTcpIpRadiuscIpv6AccountingServersEntryPendReq OBJECT-TYPE
    SYNTAX     Counter32
    MAX-ACCESS read-only
    STATUS     current
    DESCRIPTION
            ""
    ::= { hmStatusTcpIpRadiuscIpv6AccountingServersEntry 10 }

-- {COLUMN} 1.3.6.1.4.1.248.32.18.1.9.13.13.1.11
hmStatusTcpIpRadiuscIpv6AccountingServersEntryTimeouts OBJECT-TYPE
    SYNTAX     Counter32
    MAX-ACCESS read-only
    STATUS     current
    DESCRIPTION
            ""
    ::= { hmStatusTcpIpRadiuscIpv6AccountingServersEntry 11 }

-- {COLUMN} 1.3.6.1.4.1.248.32.18.1.9.13.13.1.12
hmStatusTcpIpRadiuscIpv6AccountingServersEntryUnknownTypes OBJECT-TYPE
    SYNTAX     Counter32
    MAX-ACCESS read-only
    STATUS     current
    DESCRIPTION
            ""
    ::= { hmStatusTcpIpRadiuscIpv6AccountingServersEntry 12 }

-- {COLUMN} 1.3.6.1.4.1.248.32.18.1.9.13.13.1.13
hmStatusTcpIpRadiuscIpv6AccountingServersEntryDropped OBJECT-TYPE
    SYNTAX     Counter32
    MAX-ACCESS read-only
    STATUS     current
    DESCRIPTION
            ""
    ::= { hmStatusTcpIpRadiuscIpv6AccountingServersEntry 13 }

-- {SCALAR} 1.3.6.1.4.1.248.32.18.1.9.13.100
hmStatusTcpIpRadiuscDeleteValues OBJECT-TYPE
    SYNTAX     DisplayString
    MAX-ACCESS read-write
    STATUS     current
    DESCRIPTION
            "-- empty --"
    ::= { hmStatusTcpIpRadiusc 100 }

-- {TABLE} 1.3.6.1.4.1.248.32.18.1.9.20
hmStatusTcpIpNetworkListTable OBJECT-TYPE
    SYNTAX     SEQUENCE OF HmStatusTcpIpNetworkListEntry
    MAX-ACCESS not-accessible
    STATUS     current
    DESCRIPTION
            "-- empty --"
    ::= { hmStatusTcpIp 20 }

-- {ROW} 1.3.6.1.4.1.248.32.18.1.9.20.1
hmStatusTcpIpNetworkListEntry OBJECT-TYPE
    SYNTAX     HmStatusTcpIpNetworkListEntry
    MAX-ACCESS not-accessible
    STATUS     current
    DESCRIPTION
            ""
    INDEX {
            hmStatusTcpIpNetworkListEntryNetworkName
          }
    ::= { hmStatusTcpIpNetworkListTable 1 }

HmStatusTcpIpNetworkListEntry ::= SEQUENCE {
            hmStatusTcpIpNetworkListEntryNetworkName DisplayString,
            hmStatusTcpIpNetworkListEntryIpAddress IpAddress,
            hmStatusTcpIpNetworkListEntryIpNetmask IpAddress,
            hmStatusTcpIpNetworkListEntryVlanId Integer32,
            hmStatusTcpIpNetworkListEntryInterface INTEGER,
            hmStatusTcpIpNetworkListEntrySrcCheck INTEGER,
            hmStatusTcpIpNetworkListEntryType INTEGER,
            hmStatusTcpIpNetworkListEntryRtgTag Integer32
    }

-- {COLUMN} 1.3.6.1.4.1.248.32.18.1.9.20.1.1
hmStatusTcpIpNetworkListEntryNetworkName OBJECT-TYPE
    SYNTAX     DisplayString (SIZE(0..17))
    MAX-ACCESS read-only
    STATUS     current
    DESCRIPTION
            "-- empty --"
    ::= { hmStatusTcpIpNetworkListEntry 1 }

-- {COLUMN} 1.3.6.1.4.1.248.32.18.1.9.20.1.2
hmStatusTcpIpNetworkListEntryIpAddress OBJECT-TYPE
    SYNTAX     IpAddress
    MAX-ACCESS read-only
    STATUS     current
    DESCRIPTION
            "-- empty --"
    ::= { hmStatusTcpIpNetworkListEntry 2 }

-- {COLUMN} 1.3.6.1.4.1.248.32.18.1.9.20.1.3
hmStatusTcpIpNetworkListEntryIpNetmask OBJECT-TYPE
    SYNTAX     IpAddress
    MAX-ACCESS read-only
    STATUS     current
    DESCRIPTION
            "-- empty --"
    ::= { hmStatusTcpIpNetworkListEntry 3 }

-- {COLUMN} 1.3.6.1.4.1.248.32.18.1.9.20.1.4
hmStatusTcpIpNetworkListEntryVlanId OBJECT-TYPE
    SYNTAX     Integer32 (0..65535)
    MAX-ACCESS read-only
    STATUS     current
    DESCRIPTION
            "-- empty --"
    ::= { hmStatusTcpIpNetworkListEntry 4 }

-- {COLUMN} 1.3.6.1.4.1.248.32.18.1.9.20.1.5
hmStatusTcpIpNetworkListEntryInterface OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eAny (65535)
            }
    MAX-ACCESS read-only
    STATUS     current
    DESCRIPTION
            "-- empty --"
    ::= { hmStatusTcpIpNetworkListEntry 5 }

-- {COLUMN} 1.3.6.1.4.1.248.32.18.1.9.20.1.6
hmStatusTcpIpNetworkListEntrySrcCheck OBJECT-TYPE
    SYNTAX     INTEGER {
                  eLoose (0),
                  eStrict (1)
            }
    MAX-ACCESS read-only
    STATUS     current
    DESCRIPTION
            "-- empty --"
    ::= { hmStatusTcpIpNetworkListEntry 6 }

-- {COLUMN} 1.3.6.1.4.1.248.32.18.1.9.20.1.7
hmStatusTcpIpNetworkListEntryType OBJECT-TYPE
    SYNTAX     INTEGER {
                  eDisabled (0),
                  eIntranet (1),
                  eDmz (2)
            }
    MAX-ACCESS read-only
    STATUS     current
    DESCRIPTION
            "-- empty --"
    ::= { hmStatusTcpIpNetworkListEntry 7 }

-- {COLUMN} 1.3.6.1.4.1.248.32.18.1.9.20.1.8
hmStatusTcpIpNetworkListEntryRtgTag OBJECT-TYPE
    SYNTAX     Integer32 (0..65535)
    MAX-ACCESS read-only
    STATUS     current
    DESCRIPTION
            "-- empty --"
    ::= { hmStatusTcpIpNetworkListEntry 8 }

-- {NODE} 1.3.6.1.4.1.248.32.18.1.10
hmStatusIpRouter OBJECT IDENTIFIER ::= { hmStatus 10 }

-- {SCALAR} 1.3.6.1.4.1.248.32.18.1.10.1
hmStatusIpRouterLanRx OBJECT-TYPE
    SYNTAX     Counter32
    MAX-ACCESS read-only
    STATUS     current
    DESCRIPTION
            "-- empty --"
    ::= { hmStatusIpRouter 1 }

-- {SCALAR} 1.3.6.1.4.1.248.32.18.1.10.2
hmStatusIpRouterLanTx OBJECT-TYPE
    SYNTAX     Counter32
    MAX-ACCESS read-only
    STATUS     current
    DESCRIPTION
            "-- empty --"
    ::= { hmStatusIpRouter 2 }

-- {SCALAR} 1.3.6.1.4.1.248.32.18.1.10.3
hmStatusIpRouterLanLocalRoutings OBJECT-TYPE
    SYNTAX     Counter32
    MAX-ACCESS read-only
    STATUS     current
    DESCRIPTION
            "-- empty --"
    ::= { hmStatusIpRouter 3 }

-- {SCALAR} 1.3.6.1.4.1.248.32.18.1.10.4
hmStatusIpRouterLanNetworkErrors OBJECT-TYPE
    SYNTAX     Counter32
    MAX-ACCESS read-only
    STATUS     current
    DESCRIPTION
            "-- empty --"
    ::= { hmStatusIpRouter 4 }

-- {SCALAR} 1.3.6.1.4.1.248.32.18.1.10.5
hmStatusIpRouterLanRoutingErrors OBJECT-TYPE
    SYNTAX     Counter32
    MAX-ACCESS read-only
    STATUS     current
    DESCRIPTION
            "-- empty --"
    ::= { hmStatusIpRouter 5 }

-- {SCALAR} 1.3.6.1.4.1.248.32.18.1.10.6
hmStatusIpRouterLanTtlErrors OBJECT-TYPE
    SYNTAX     Counter32
    MAX-ACCESS read-only
    STATUS     current
    DESCRIPTION
            "-- empty --"
    ::= { hmStatusIpRouter 6 }

-- {SCALAR} 1.3.6.1.4.1.248.32.18.1.10.7
hmStatusIpRouterLanFilters OBJECT-TYPE
    SYNTAX     Counter32
    MAX-ACCESS read-only
    STATUS     current
    DESCRIPTION
            "-- empty --"
    ::= { hmStatusIpRouter 7 }

-- {SCALAR} 1.3.6.1.4.1.248.32.18.1.10.8
hmStatusIpRouterLanDiscards OBJECT-TYPE
    SYNTAX     Counter32
    MAX-ACCESS read-only
    STATUS     current
    DESCRIPTION
            "-- empty --"
    ::= { hmStatusIpRouter 8 }

-- {SCALAR} 1.3.6.1.4.1.248.32.18.1.10.9
hmStatusIpRouterWanRx OBJECT-TYPE
    SYNTAX     Counter32
    MAX-ACCESS read-only
    STATUS     current
    DESCRIPTION
            "-- empty --"
    ::= { hmStatusIpRouter 9 }

-- {SCALAR} 1.3.6.1.4.1.248.32.18.1.10.10
hmStatusIpRouterWanTx OBJECT-TYPE
    SYNTAX     Counter32
    MAX-ACCESS read-only
    STATUS     current
    DESCRIPTION
            "-- empty --"
    ::= { hmStatusIpRouter 10 }

-- {SCALAR} 1.3.6.1.4.1.248.32.18.1.10.11
hmStatusIpRouterWanNetworkErrors OBJECT-TYPE
    SYNTAX     Counter32
    MAX-ACCESS read-only
    STATUS     current
    DESCRIPTION
            "-- empty --"
    ::= { hmStatusIpRouter 11 }

-- {SCALAR} 1.3.6.1.4.1.248.32.18.1.10.12
hmStatusIpRouterWanTtlErrors OBJECT-TYPE
    SYNTAX     Counter32
    MAX-ACCESS read-only
    STATUS     current
    DESCRIPTION
            "-- empty --"
    ::= { hmStatusIpRouter 12 }

-- {SCALAR} 1.3.6.1.4.1.248.32.18.1.10.13
hmStatusIpRouterWanFilters OBJECT-TYPE
    SYNTAX     Counter32
    MAX-ACCESS read-only
    STATUS     current
    DESCRIPTION
            "-- empty --"
    ::= { hmStatusIpRouter 13 }

-- {SCALAR} 1.3.6.1.4.1.248.32.18.1.10.14
hmStatusIpRouterWanDiscards OBJECT-TYPE
    SYNTAX     Counter32
    MAX-ACCESS read-only
    STATUS     current
    DESCRIPTION
            "-- empty --"
    ::= { hmStatusIpRouter 14 }

-- {SCALAR} 1.3.6.1.4.1.248.32.18.1.10.15
hmStatusIpRouterWanTypeErrors OBJECT-TYPE
    SYNTAX     Counter32
    MAX-ACCESS read-only
    STATUS     current
    DESCRIPTION
            "-- empty --"
    ::= { hmStatusIpRouter 15 }

-- {SCALAR} 1.3.6.1.4.1.248.32.18.1.10.16
hmStatusIpRouterArpErrors OBJECT-TYPE
    SYNTAX     Counter32
    MAX-ACCESS read-only
    STATUS     current
    DESCRIPTION
            "-- empty --"
    ::= { hmStatusIpRouter 16 }

-- {TABLE} 1.3.6.1.4.1.248.32.18.1.10.17
hmStatusIpRouterEstablishTableTable OBJECT-TYPE
    SYNTAX     SEQUENCE OF HmStatusIpRouterEstablishTableEntry
    MAX-ACCESS not-accessible
    STATUS     current
    DESCRIPTION
            "-- empty --"
    ::= { hmStatusIpRouter 17 }

-- {ROW} 1.3.6.1.4.1.248.32.18.1.10.17.1
hmStatusIpRouterEstablishTableEntry OBJECT-TYPE
    SYNTAX     HmStatusIpRouterEstablishTableEntry
    MAX-ACCESS not-accessible
    STATUS     current
    DESCRIPTION
            ""
    INDEX {
            hmStatusIpRouterEstablishTableEntryTime,
            hmStatusIpRouterEstablishTableEntryCounter
          }
    ::= { hmStatusIpRouterEstablishTableTable 1 }

HmStatusIpRouterEstablishTableEntry ::= SEQUENCE {
            hmStatusIpRouterEstablishTableEntryTime DisplayString,
            hmStatusIpRouterEstablishTableEntryDestAddress IpAddress,
            hmStatusIpRouterEstablishTableEntrySrcAddress IpAddress,
            hmStatusIpRouterEstablishTableEntryProt INTEGER,
            hmStatusIpRouterEstablishTableEntryDPortFrom Integer32,
            hmStatusIpRouterEstablishTableEntrySourcePort Integer32,
            hmStatusIpRouterEstablishTableEntryCounter Integer32
    }

-- {COLUMN} 1.3.6.1.4.1.248.32.18.1.10.17.1.1
hmStatusIpRouterEstablishTableEntryTime OBJECT-TYPE
    SYNTAX     DisplayString (SIZE(0..19))
    MAX-ACCESS read-only
    STATUS     current
    DESCRIPTION
            "-- empty --"
    ::= { hmStatusIpRouterEstablishTableEntry 1 }

-- {COLUMN} 1.3.6.1.4.1.248.32.18.1.10.17.1.2
hmStatusIpRouterEstablishTableEntryDestAddress OBJECT-TYPE
    SYNTAX     IpAddress
    MAX-ACCESS read-only
    STATUS     current
    DESCRIPTION
            "-- empty --"
    ::= { hmStatusIpRouterEstablishTableEntry 2 }

-- {COLUMN} 1.3.6.1.4.1.248.32.18.1.10.17.1.3
hmStatusIpRouterEstablishTableEntrySrcAddress OBJECT-TYPE
    SYNTAX     IpAddress
    MAX-ACCESS read-only
    STATUS     current
    DESCRIPTION
            "-- empty --"
    ::= { hmStatusIpRouterEstablishTableEntry 3 }

-- {COLUMN} 1.3.6.1.4.1.248.32.18.1.10.17.1.4
hmStatusIpRouterEstablishTableEntryProt OBJECT-TYPE
    SYNTAX     INTEGER {
                  eIcmp (1),
                  eIgmp (2),
                  eGgt (3),
                  eIpip (4),
                  eTcp (6),
                  eEgp (8),
                  eUdp (17),
                  eGre (47),
                  eEsp (50),
                  eAh (51),
                  eCftp (62),
                  eIpcomp (108),
                  eVrrp (112),
                  eSrp (119)
            }
    MAX-ACCESS read-only
    STATUS     current
    DESCRIPTION
            "-- empty --"
    ::= { hmStatusIpRouterEstablishTableEntry 4 }

-- {COLUMN} 1.3.6.1.4.1.248.32.18.1.10.17.1.5
hmStatusIpRouterEstablishTableEntryDPortFrom OBJECT-TYPE
    SYNTAX     Integer32 (0..65535)
    MAX-ACCESS read-only
    STATUS     current
    DESCRIPTION
            "-- empty --"
    ::= { hmStatusIpRouterEstablishTableEntry 5 }

-- {COLUMN} 1.3.6.1.4.1.248.32.18.1.10.17.1.6
hmStatusIpRouterEstablishTableEntrySourcePort OBJECT-TYPE
    SYNTAX     Integer32 (0..65535)
    MAX-ACCESS read-only
    STATUS     current
    DESCRIPTION
            "-- empty --"
    ::= { hmStatusIpRouterEstablishTableEntry 6 }

-- {COLUMN} 1.3.6.1.4.1.248.32.18.1.10.17.1.7
hmStatusIpRouterEstablishTableEntryCounter OBJECT-TYPE
    SYNTAX     Integer32 (0..2147483647)
    MAX-ACCESS read-only
    STATUS     current
    DESCRIPTION
            "-- empty --"
    ::= { hmStatusIpRouterEstablishTableEntry 7 }

-- {TABLE} 1.3.6.1.4.1.248.32.18.1.10.18
hmStatusIpRouterProtocolTableTable OBJECT-TYPE
    SYNTAX     SEQUENCE OF HmStatusIpRouterProtocolTableEntry
    MAX-ACCESS not-accessible
    STATUS     current
    DESCRIPTION
            "-- empty --"
    ::= { hmStatusIpRouter 18 }

-- {ROW} 1.3.6.1.4.1.248.32.18.1.10.18.1
hmStatusIpRouterProtocolTableEntry OBJECT-TYPE
    SYNTAX     HmStatusIpRouterProtocolTableEntry
    MAX-ACCESS not-accessible
    STATUS     current
    DESCRIPTION
            ""
    INDEX {
            hmStatusIpRouterProtocolTableEntryProt
          }
    ::= { hmStatusIpRouterProtocolTableTable 1 }

HmStatusIpRouterProtocolTableEntry ::= SEQUENCE {
            hmStatusIpRouterProtocolTableEntryProt INTEGER,
            hmStatusIpRouterProtocolTableEntryLanTx Counter32,
            hmStatusIpRouterProtocolTableEntryWanTx Counter32
    }

-- {COLUMN} 1.3.6.1.4.1.248.32.18.1.10.18.1.1
hmStatusIpRouterProtocolTableEntryProt OBJECT-TYPE
    SYNTAX     INTEGER {
                  eIcmp (1),
                  eIgmp (2),
                  eGgt (3),
                  eIpip (4),
                  eTcp (6),
                  eEgp (8),
                  eUdp (17),
                  eGre (47),
                  eEsp (50),
                  eAh (51),
                  eCftp (62),
                  eIpcomp (108),
                  eVrrp (112),
                  eSrp (119)
            }
    MAX-ACCESS read-only
    STATUS     current
    DESCRIPTION
            "-- empty --"
    ::= { hmStatusIpRouterProtocolTableEntry 1 }

-- {COLUMN} 1.3.6.1.4.1.248.32.18.1.10.18.1.2
hmStatusIpRouterProtocolTableEntryLanTx OBJECT-TYPE
    SYNTAX     Counter32
    MAX-ACCESS read-only
    STATUS     current
    DESCRIPTION
            "-- empty --"
    ::= { hmStatusIpRouterProtocolTableEntry 2 }

-- {COLUMN} 1.3.6.1.4.1.248.32.18.1.10.18.1.3
hmStatusIpRouterProtocolTableEntryWanTx OBJECT-TYPE
    SYNTAX     Counter32
    MAX-ACCESS read-only
    STATUS     current
    DESCRIPTION
            "-- empty --"
    ::= { hmStatusIpRouterProtocolTableEntry 3 }

-- {NODE} 1.3.6.1.4.1.248.32.18.1.10.19
hmStatusIpRouterRip OBJECT IDENTIFIER ::= { hmStatusIpRouter 19 }

-- {SCALAR} 1.3.6.1.4.1.248.32.18.1.10.19.1
hmStatusIpRouterRipRx OBJECT-TYPE
    SYNTAX     Counter32
    MAX-ACCESS read-only
    STATUS     current
    DESCRIPTION
            "-- empty --"
    ::= { hmStatusIpRouterRip 1 }

-- {SCALAR} 1.3.6.1.4.1.248.32.18.1.10.19.2
hmStatusIpRouterRipRequests OBJECT-TYPE
    SYNTAX     Counter32
    MAX-ACCESS read-only
    STATUS     current
    DESCRIPTION
            "-- empty --"
    ::= { hmStatusIpRouterRip 2 }

-- {SCALAR} 1.3.6.1.4.1.248.32.18.1.10.19.3
hmStatusIpRouterRipResponse OBJECT-TYPE
    SYNTAX     Counter32
    MAX-ACCESS read-only
    STATUS     current
    DESCRIPTION
            "-- empty --"
    ::= { hmStatusIpRouterRip 3 }

-- {SCALAR} 1.3.6.1.4.1.248.32.18.1.10.19.4
hmStatusIpRouterRipDiscards OBJECT-TYPE
    SYNTAX     Counter32
    MAX-ACCESS read-only
    STATUS     current
    DESCRIPTION
            "-- empty --"
    ::= { hmStatusIpRouterRip 4 }

-- {SCALAR} 1.3.6.1.4.1.248.32.18.1.10.19.5
hmStatusIpRouterRipErrors OBJECT-TYPE
    SYNTAX     Counter32
    MAX-ACCESS read-only
    STATUS     current
    DESCRIPTION
            "-- empty --"
    ::= { hmStatusIpRouterRip 5 }

-- {SCALAR} 1.3.6.1.4.1.248.32.18.1.10.19.6
hmStatusIpRouterRipEntryErrors OBJECT-TYPE
    SYNTAX     Counter32
    MAX-ACCESS read-only
    STATUS     current
    DESCRIPTION
            "-- empty --"
    ::= { hmStatusIpRouterRip 6 }

-- {SCALAR} 1.3.6.1.4.1.248.32.18.1.10.19.7
hmStatusIpRouterRipTx OBJECT-TYPE
    SYNTAX     Counter32
    MAX-ACCESS read-only
    STATUS     current
    DESCRIPTION
            "-- empty --"
    ::= { hmStatusIpRouterRip 7 }

-- {TABLE} 1.3.6.1.4.1.248.32.18.1.10.19.8
hmStatusIpRouterRipBestRoutesTable OBJECT-TYPE
    SYNTAX     SEQUENCE OF HmStatusIpRouterRipBestRoutesEntry
    MAX-ACCESS not-accessible
    STATUS     current
    DESCRIPTION
            "-- empty --"
    ::= { hmStatusIpRouterRip 8 }

-- {ROW} 1.3.6.1.4.1.248.32.18.1.10.19.8.1
hmStatusIpRouterRipBestRoutesEntry OBJECT-TYPE
    SYNTAX     HmStatusIpRouterRipBestRoutesEntry
    MAX-ACCESS not-accessible
    STATUS     current
    DESCRIPTION
            ""
    INDEX {
            hmStatusIpRouterRipBestRoutesEntryIpAddress,
            hmStatusIpRouterRipBestRoutesEntryIpNetmask,
            hmStatusIpRouterRipBestRoutesEntryRtgTag,
            hmStatusIpRouterRipBestRoutesEntryGateway
          }
    ::= { hmStatusIpRouterRipBestRoutesTable 1 }

HmStatusIpRouterRipBestRoutesEntry ::= SEQUENCE {
            hmStatusIpRouterRipBestRoutesEntryIpAddress IpAddress,
            hmStatusIpRouterRipBestRoutesEntryIpNetmask IpAddress,
            hmStatusIpRouterRipBestRoutesEntryTime Integer32,
            hmStatusIpRouterRipBestRoutesEntryDistance Integer32,
            hmStatusIpRouterRipBestRoutesEntryGateway IpAddress,
            hmStatusIpRouterRipBestRoutesEntryRtgTag Integer32,
            hmStatusIpRouterRipBestRoutesEntryPeer DisplayString,
            hmStatusIpRouterRipBestRoutesEntryVlanId Integer32,
            hmStatusIpRouterRipBestRoutesEntryNetworkName DisplayString,
            hmStatusIpRouterRipBestRoutesEntryPort INTEGER
    }

-- {COLUMN} 1.3.6.1.4.1.248.32.18.1.10.19.8.1.1
hmStatusIpRouterRipBestRoutesEntryIpAddress OBJECT-TYPE
    SYNTAX     IpAddress
    MAX-ACCESS read-only
    STATUS     current
    DESCRIPTION
            "-- empty --"
    ::= { hmStatusIpRouterRipBestRoutesEntry 1 }

-- {COLUMN} 1.3.6.1.4.1.248.32.18.1.10.19.8.1.2
hmStatusIpRouterRipBestRoutesEntryIpNetmask OBJECT-TYPE
    SYNTAX     IpAddress
    MAX-ACCESS read-only
    STATUS     current
    DESCRIPTION
            "-- empty --"
    ::= { hmStatusIpRouterRipBestRoutesEntry 2 }

-- {COLUMN} 1.3.6.1.4.1.248.32.18.1.10.19.8.1.3
hmStatusIpRouterRipBestRoutesEntryTime OBJECT-TYPE
    SYNTAX     Integer32 (0..65535)
    MAX-ACCESS read-only
    STATUS     current
    DESCRIPTION
            "-- empty --"
    ::= { hmStatusIpRouterRipBestRoutesEntry 3 }

-- {COLUMN} 1.3.6.1.4.1.248.32.18.1.10.19.8.1.4
hmStatusIpRouterRipBestRoutesEntryDistance OBJECT-TYPE
    SYNTAX     Integer32 (0..65535)
    MAX-ACCESS read-only
    STATUS     current
    DESCRIPTION
            "-- empty --"
    ::= { hmStatusIpRouterRipBestRoutesEntry 4 }

-- {COLUMN} 1.3.6.1.4.1.248.32.18.1.10.19.8.1.5
hmStatusIpRouterRipBestRoutesEntryGateway OBJECT-TYPE
    SYNTAX     IpAddress
    MAX-ACCESS read-only
    STATUS     current
    DESCRIPTION
            "-- empty --"
    ::= { hmStatusIpRouterRipBestRoutesEntry 5 }

-- {COLUMN} 1.3.6.1.4.1.248.32.18.1.10.19.8.1.6
hmStatusIpRouterRipBestRoutesEntryRtgTag OBJECT-TYPE
    SYNTAX     Integer32 (0..65535)
    MAX-ACCESS read-only
    STATUS     current
    DESCRIPTION
            "-- empty --"
    ::= { hmStatusIpRouterRipBestRoutesEntry 6 }

-- {COLUMN} 1.3.6.1.4.1.248.32.18.1.10.19.8.1.8
hmStatusIpRouterRipBestRoutesEntryPeer OBJECT-TYPE
    SYNTAX     DisplayString (SIZE(0..255))
    MAX-ACCESS read-only
    STATUS     current
    DESCRIPTION
            "-- empty --"
    ::= { hmStatusIpRouterRipBestRoutesEntry 8 }

-- {COLUMN} 1.3.6.1.4.1.248.32.18.1.10.19.8.1.10
hmStatusIpRouterRipBestRoutesEntryVlanId OBJECT-TYPE
    SYNTAX     Integer32 (0..65535)
    MAX-ACCESS read-only
    STATUS     current
    DESCRIPTION
            "-- empty --"
    ::= { hmStatusIpRouterRipBestRoutesEntry 10 }

-- {COLUMN} 1.3.6.1.4.1.248.32.18.1.10.19.8.1.11
hmStatusIpRouterRipBestRoutesEntryNetworkName OBJECT-TYPE
    SYNTAX     DisplayString (SIZE(0..255))
    MAX-ACCESS read-only
    STATUS     current
    DESCRIPTION
            "-- empty --"
    ::= { hmStatusIpRouterRipBestRoutesEntry 11 }

-- {COLUMN} 1.3.6.1.4.1.248.32.18.1.10.19.8.1.12
hmStatusIpRouterRipBestRoutesEntryPort OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eAny (65535)
            }
    MAX-ACCESS read-only
    STATUS     current
    DESCRIPTION
            "-- empty --"
    ::= { hmStatusIpRouterRipBestRoutesEntry 12 }

-- {SCALAR} 1.3.6.1.4.1.248.32.18.1.10.19.9
hmStatusIpRouterRipDeleteValues OBJECT-TYPE
    SYNTAX     DisplayString
    MAX-ACCESS read-write
    STATUS     current
    DESCRIPTION
            "-- empty --"
    ::= { hmStatusIpRouterRip 9 }

-- {TABLE} 1.3.6.1.4.1.248.32.18.1.10.19.10
hmStatusIpRouterRipLanSitesTable OBJECT-TYPE
    SYNTAX     SEQUENCE OF HmStatusIpRouterRipLanSitesEntry
    MAX-ACCESS not-accessible
    STATUS     current
    DESCRIPTION
            "-- empty --"
    ::= { hmStatusIpRouterRip 10 }

-- {ROW} 1.3.6.1.4.1.248.32.18.1.10.19.10.1
hmStatusIpRouterRipLanSitesEntry OBJECT-TYPE
    SYNTAX     HmStatusIpRouterRipLanSitesEntry
    MAX-ACCESS not-accessible
    STATUS     current
    DESCRIPTION
            ""
    INDEX {
            hmStatusIpRouterRipLanSitesEntryNetworkName
          }
    ::= { hmStatusIpRouterRipLanSitesTable 1 }

HmStatusIpRouterRipLanSitesEntry ::= SEQUENCE {
            hmStatusIpRouterRipLanSitesEntryNetworkName DisplayString,
            hmStatusIpRouterRipLanSitesEntryRipType INTEGER,
            hmStatusIpRouterRipLanSitesEntryRipAccept INTEGER,
            hmStatusIpRouterRipLanSitesEntryPropagate INTEGER,
            hmStatusIpRouterRipLanSitesEntryDftRtgTag Integer32,
            hmStatusIpRouterRipLanSitesEntryRtgTagList DisplayString,
            hmStatusIpRouterRipLanSitesEntryVlanId Integer32,
            hmStatusIpRouterRipLanSitesEntryPoisonedReverse INTEGER,
            hmStatusIpRouterRipLanSitesEntryRxFilter DisplayString,
            hmStatusIpRouterRipLanSitesEntryTxFilter DisplayString,
            hmStatusIpRouterRipLanSitesEntryRipSend INTEGER,
            hmStatusIpRouterRipLanSitesEntryPort INTEGER
    }

-- {COLUMN} 1.3.6.1.4.1.248.32.18.1.10.19.10.1.1
hmStatusIpRouterRipLanSitesEntryNetworkName OBJECT-TYPE
    SYNTAX     DisplayString (SIZE(0..16))
    MAX-ACCESS read-only
    STATUS     current
    DESCRIPTION
            "-- empty --"
    ::= { hmStatusIpRouterRipLanSitesEntry 1 }

-- {COLUMN} 1.3.6.1.4.1.248.32.18.1.10.19.10.1.2
hmStatusIpRouterRipLanSitesEntryRipType OBJECT-TYPE
    SYNTAX     INTEGER {
                  eOff (0),
                  eRip1 (1),
                  eR1Comp (2),
                  eRip2 (3)
            }
    MAX-ACCESS read-only
    STATUS     current
    DESCRIPTION
            "-- empty --"
    ::= { hmStatusIpRouterRipLanSitesEntry 2 }

-- {COLUMN} 1.3.6.1.4.1.248.32.18.1.10.19.10.1.3
hmStatusIpRouterRipLanSitesEntryRipAccept OBJECT-TYPE
    SYNTAX     INTEGER {
                  eNo (0),
                  eYes (1)
            }
    MAX-ACCESS read-only
    STATUS     current
    DESCRIPTION
            "-- empty --"
    ::= { hmStatusIpRouterRipLanSitesEntry 3 }

-- {COLUMN} 1.3.6.1.4.1.248.32.18.1.10.19.10.1.4
hmStatusIpRouterRipLanSitesEntryPropagate OBJECT-TYPE
    SYNTAX     INTEGER {
                  eNo (0),
                  eYes (1)
            }
    MAX-ACCESS read-only
    STATUS     current
    DESCRIPTION
            "-- empty --"
    ::= { hmStatusIpRouterRipLanSitesEntry 4 }

-- {COLUMN} 1.3.6.1.4.1.248.32.18.1.10.19.10.1.5
hmStatusIpRouterRipLanSitesEntryDftRtgTag OBJECT-TYPE
    SYNTAX     Integer32 (0..65535)
    MAX-ACCESS read-only
    STATUS     current
    DESCRIPTION
            "-- empty --"
    ::= { hmStatusIpRouterRipLanSitesEntry 5 }

-- {COLUMN} 1.3.6.1.4.1.248.32.18.1.10.19.10.1.6
hmStatusIpRouterRipLanSitesEntryRtgTagList OBJECT-TYPE
    SYNTAX     DisplayString (SIZE(0..33))
    MAX-ACCESS read-only
    STATUS     current
    DESCRIPTION
            "-- empty --"
    ::= { hmStatusIpRouterRipLanSitesEntry 6 }

-- {COLUMN} 1.3.6.1.4.1.248.32.18.1.10.19.10.1.8
hmStatusIpRouterRipLanSitesEntryVlanId OBJECT-TYPE
    SYNTAX     Integer32 (0..65535)
    MAX-ACCESS read-only
    STATUS     current
    DESCRIPTION
            "-- empty --"
    ::= { hmStatusIpRouterRipLanSitesEntry 8 }

-- {COLUMN} 1.3.6.1.4.1.248.32.18.1.10.19.10.1.9
hmStatusIpRouterRipLanSitesEntryPoisonedReverse OBJECT-TYPE
    SYNTAX     INTEGER {
                  eNo (0),
                  eYes (1)
            }
    MAX-ACCESS read-only
    STATUS     current
    DESCRIPTION
            "-- empty --"
    ::= { hmStatusIpRouterRipLanSitesEntry 9 }

-- {COLUMN} 1.3.6.1.4.1.248.32.18.1.10.19.10.1.10
hmStatusIpRouterRipLanSitesEntryRxFilter OBJECT-TYPE
    SYNTAX     DisplayString (SIZE(0..16))
    MAX-ACCESS read-only
    STATUS     current
    DESCRIPTION
            "-- empty --"
    ::= { hmStatusIpRouterRipLanSitesEntry 10 }

-- {COLUMN} 1.3.6.1.4.1.248.32.18.1.10.19.10.1.11
hmStatusIpRouterRipLanSitesEntryTxFilter OBJECT-TYPE
    SYNTAX     DisplayString (SIZE(0..16))
    MAX-ACCESS read-only
    STATUS     current
    DESCRIPTION
            "-- empty --"
    ::= { hmStatusIpRouterRipLanSitesEntry 11 }

-- {COLUMN} 1.3.6.1.4.1.248.32.18.1.10.19.10.1.12
hmStatusIpRouterRipLanSitesEntryRipSend OBJECT-TYPE
    SYNTAX     INTEGER {
                  eNo (0),
                  eYes (1)
            }
    MAX-ACCESS read-only
    STATUS     current
    DESCRIPTION
            "-- empty --"
    ::= { hmStatusIpRouterRipLanSitesEntry 12 }

-- {COLUMN} 1.3.6.1.4.1.248.32.18.1.10.19.10.1.31
hmStatusIpRouterRipLanSitesEntryPort OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eAny (65535)
            }
    MAX-ACCESS read-only
    STATUS     current
    DESCRIPTION
            "-- empty --"
    ::= { hmStatusIpRouterRipLanSitesEntry 31 }

-- {TABLE} 1.3.6.1.4.1.248.32.18.1.10.19.11
hmStatusIpRouterRipWanSitesTable OBJECT-TYPE
    SYNTAX     SEQUENCE OF HmStatusIpRouterRipWanSitesEntry
    MAX-ACCESS not-accessible
    STATUS     current
    DESCRIPTION
            "-- empty --"
    ::= { hmStatusIpRouterRip 11 }

-- {ROW} 1.3.6.1.4.1.248.32.18.1.10.19.11.1
hmStatusIpRouterRipWanSitesEntry OBJECT-TYPE
    SYNTAX     HmStatusIpRouterRipWanSitesEntry
    MAX-ACCESS not-accessible
    STATUS     current
    DESCRIPTION
            ""
    INDEX {
            hmStatusIpRouterRipWanSitesEntryPeer
          }
    ::= { hmStatusIpRouterRipWanSitesTable 1 }

HmStatusIpRouterRipWanSitesEntry ::= SEQUENCE {
            hmStatusIpRouterRipWanSitesEntryPeer DisplayString,
            hmStatusIpRouterRipWanSitesEntryRipType INTEGER,
            hmStatusIpRouterRipWanSitesEntryRipAccept INTEGER,
            hmStatusIpRouterRipWanSitesEntryMasquerade INTEGER,
            hmStatusIpRouterRipWanSitesEntryDftRtgTag Integer32,
            hmStatusIpRouterRipWanSitesEntryRtgTagList DisplayString,
            hmStatusIpRouterRipWanSitesEntryPoisonedReverse INTEGER,
            hmStatusIpRouterRipWanSitesEntryRfc2091 INTEGER,
            hmStatusIpRouterRipWanSitesEntryGateway IpAddress,
            hmStatusIpRouterRipWanSitesEntryRxFilter DisplayString,
            hmStatusIpRouterRipWanSitesEntryTxFilter DisplayString,
            hmStatusIpRouterRipWanSitesEntryRipSend INTEGER
    }

-- {COLUMN} 1.3.6.1.4.1.248.32.18.1.10.19.11.1.1
hmStatusIpRouterRipWanSitesEntryPeer OBJECT-TYPE
    SYNTAX     DisplayString (SIZE(0..16))
    MAX-ACCESS read-only
    STATUS     current
    DESCRIPTION
            "-- empty --"
    ::= { hmStatusIpRouterRipWanSitesEntry 1 }

-- {COLUMN} 1.3.6.1.4.1.248.32.18.1.10.19.11.1.2
hmStatusIpRouterRipWanSitesEntryRipType OBJECT-TYPE
    SYNTAX     INTEGER {
                  eOff (0),
                  eRip1 (1),
                  eR1Comp (2),
                  eRip2 (3)
            }
    MAX-ACCESS read-only
    STATUS     current
    DESCRIPTION
            "-- empty --"
    ::= { hmStatusIpRouterRipWanSitesEntry 2 }

-- {COLUMN} 1.3.6.1.4.1.248.32.18.1.10.19.11.1.3
hmStatusIpRouterRipWanSitesEntryRipAccept OBJECT-TYPE
    SYNTAX     INTEGER {
                  eNo (0),
                  eYes (1)
            }
    MAX-ACCESS read-only
    STATUS     current
    DESCRIPTION
            "-- empty --"
    ::= { hmStatusIpRouterRipWanSitesEntry 3 }

-- {COLUMN} 1.3.6.1.4.1.248.32.18.1.10.19.11.1.4
hmStatusIpRouterRipWanSitesEntryMasquerade OBJECT-TYPE
    SYNTAX     INTEGER {
                  eAuto (0),
                  eOn (1),
                  eIntranet (2)
            }
    MAX-ACCESS read-only
    STATUS     current
    DESCRIPTION
            "-- empty --"
    ::= { hmStatusIpRouterRipWanSitesEntry 4 }

-- {COLUMN} 1.3.6.1.4.1.248.32.18.1.10.19.11.1.5
hmStatusIpRouterRipWanSitesEntryDftRtgTag OBJECT-TYPE
    SYNTAX     Integer32 (0..65535)
    MAX-ACCESS read-only
    STATUS     current
    DESCRIPTION
            "-- empty --"
    ::= { hmStatusIpRouterRipWanSitesEntry 5 }

-- {COLUMN} 1.3.6.1.4.1.248.32.18.1.10.19.11.1.6
hmStatusIpRouterRipWanSitesEntryRtgTagList OBJECT-TYPE
    SYNTAX     DisplayString (SIZE(0..33))
    MAX-ACCESS read-only
    STATUS     current
    DESCRIPTION
            "-- empty --"
    ::= { hmStatusIpRouterRipWanSitesEntry 6 }

-- {COLUMN} 1.3.6.1.4.1.248.32.18.1.10.19.11.1.7
hmStatusIpRouterRipWanSitesEntryPoisonedReverse OBJECT-TYPE
    SYNTAX     INTEGER {
                  eNo (0),
                  eYes (1)
            }
    MAX-ACCESS read-only
    STATUS     current
    DESCRIPTION
            "-- empty --"
    ::= { hmStatusIpRouterRipWanSitesEntry 7 }

-- {COLUMN} 1.3.6.1.4.1.248.32.18.1.10.19.11.1.8
hmStatusIpRouterRipWanSitesEntryRfc2091 OBJECT-TYPE
    SYNTAX     INTEGER {
                  eNo (0),
                  eYes (1)
            }
    MAX-ACCESS read-only
    STATUS     current
    DESCRIPTION
            "-- empty --"
    ::= { hmStatusIpRouterRipWanSitesEntry 8 }

-- {COLUMN} 1.3.6.1.4.1.248.32.18.1.10.19.11.1.9
hmStatusIpRouterRipWanSitesEntryGateway OBJECT-TYPE
    SYNTAX     IpAddress
    MAX-ACCESS read-only
    STATUS     current
    DESCRIPTION
            "-- empty --"
    ::= { hmStatusIpRouterRipWanSitesEntry 9 }

-- {COLUMN} 1.3.6.1.4.1.248.32.18.1.10.19.11.1.10
hmStatusIpRouterRipWanSitesEntryRxFilter OBJECT-TYPE
    SYNTAX     DisplayString (SIZE(0..16))
    MAX-ACCESS read-only
    STATUS     current
    DESCRIPTION
            "-- empty --"
    ::= { hmStatusIpRouterRipWanSitesEntry 10 }

-- {COLUMN} 1.3.6.1.4.1.248.32.18.1.10.19.11.1.11
hmStatusIpRouterRipWanSitesEntryTxFilter OBJECT-TYPE
    SYNTAX     DisplayString (SIZE(0..16))
    MAX-ACCESS read-only
    STATUS     current
    DESCRIPTION
            "-- empty --"
    ::= { hmStatusIpRouterRipWanSitesEntry 11 }

-- {COLUMN} 1.3.6.1.4.1.248.32.18.1.10.19.11.1.12
hmStatusIpRouterRipWanSitesEntryRipSend OBJECT-TYPE
    SYNTAX     INTEGER {
                  eNo (0),
                  eYes (1)
            }
    MAX-ACCESS read-only
    STATUS     current
    DESCRIPTION
            "-- empty --"
    ::= { hmStatusIpRouterRipWanSitesEntry 12 }

-- {TABLE} 1.3.6.1.4.1.248.32.18.1.10.19.12
hmStatusIpRouterRipVrrpSitesTable OBJECT-TYPE
    SYNTAX     SEQUENCE OF HmStatusIpRouterRipVrrpSitesEntry
    MAX-ACCESS not-accessible
    STATUS     current
    DESCRIPTION
            "-- empty --"
    ::= { hmStatusIpRouterRip 12 }

-- {ROW} 1.3.6.1.4.1.248.32.18.1.10.19.12.1
hmStatusIpRouterRipVrrpSitesEntry OBJECT-TYPE
    SYNTAX     HmStatusIpRouterRipVrrpSitesEntry
    MAX-ACCESS not-accessible
    STATUS     current
    DESCRIPTION
            ""
    INDEX {
            hmStatusIpRouterRipVrrpSitesEntryNetworkName,
            hmStatusIpRouterRipVrrpSitesEntryRouterId
          }
    ::= { hmStatusIpRouterRipVrrpSitesTable 1 }

HmStatusIpRouterRipVrrpSitesEntry ::= SEQUENCE {
            hmStatusIpRouterRipVrrpSitesEntryNetworkName DisplayString,
            hmStatusIpRouterRipVrrpSitesEntryRipType INTEGER,
            hmStatusIpRouterRipVrrpSitesEntryRouterId Integer32
    }

-- {COLUMN} 1.3.6.1.4.1.248.32.18.1.10.19.12.1.1
hmStatusIpRouterRipVrrpSitesEntryNetworkName OBJECT-TYPE
    SYNTAX     DisplayString (SIZE(0..16))
    MAX-ACCESS read-only
    STATUS     current
    DESCRIPTION
            "-- empty --"
    ::= { hmStatusIpRouterRipVrrpSitesEntry 1 }

-- {COLUMN} 1.3.6.1.4.1.248.32.18.1.10.19.12.1.2
hmStatusIpRouterRipVrrpSitesEntryRipType OBJECT-TYPE
    SYNTAX     INTEGER {
                  eOff (0),
                  eRip1 (1),
                  eR1Comp (2),
                  eRip2 (3)
            }
    MAX-ACCESS read-only
    STATUS     current
    DESCRIPTION
            "-- empty --"
    ::= { hmStatusIpRouterRipVrrpSitesEntry 2 }

-- {COLUMN} 1.3.6.1.4.1.248.32.18.1.10.19.12.1.3
hmStatusIpRouterRipVrrpSitesEntryRouterId OBJECT-TYPE
    SYNTAX     Integer32 (0..255)
    MAX-ACCESS read-only
    STATUS     current
    DESCRIPTION
            "-- empty --"
    ::= { hmStatusIpRouterRipVrrpSitesEntry 3 }

-- {TABLE} 1.3.6.1.4.1.248.32.18.1.10.19.13
hmStatusIpRouterRipDynLanSitesTable OBJECT-TYPE
    SYNTAX     SEQUENCE OF HmStatusIpRouterRipDynLanSitesEntry
    MAX-ACCESS not-accessible
    STATUS     current
    DESCRIPTION
            "-- empty --"
    ::= { hmStatusIpRouterRip 13 }

-- {ROW} 1.3.6.1.4.1.248.32.18.1.10.19.13.1
hmStatusIpRouterRipDynLanSitesEntry OBJECT-TYPE
    SYNTAX     HmStatusIpRouterRipDynLanSitesEntry
    MAX-ACCESS not-accessible
    STATUS     current
    DESCRIPTION
            ""
    INDEX {
            hmStatusIpRouterRipDynLanSitesEntryGateway
          }
    ::= { hmStatusIpRouterRipDynLanSitesTable 1 }

HmStatusIpRouterRipDynLanSitesEntry ::= SEQUENCE {
            hmStatusIpRouterRipDynLanSitesEntryGateway DisplayString,
            hmStatusIpRouterRipDynLanSitesEntryRipType INTEGER,
            hmStatusIpRouterRipDynLanSitesEntryRipAccept INTEGER,
            hmStatusIpRouterRipDynLanSitesEntryPoisonedReverse INTEGER,
            hmStatusIpRouterRipDynLanSitesEntryDftRtgTag Integer32,
            hmStatusIpRouterRipDynLanSitesEntryRtgTagList DisplayString,
            hmStatusIpRouterRipDynLanSitesEntryVlanId Integer32,
            hmStatusIpRouterRipDynLanSitesEntryRxFilter DisplayString,
            hmStatusIpRouterRipDynLanSitesEntryTxFilter DisplayString,
            hmStatusIpRouterRipDynLanSitesEntryRipSend INTEGER,
            hmStatusIpRouterRipDynLanSitesEntryPort INTEGER
    }

-- {COLUMN} 1.3.6.1.4.1.248.32.18.1.10.19.13.1.1
hmStatusIpRouterRipDynLanSitesEntryGateway OBJECT-TYPE
    SYNTAX     DisplayString (SIZE(0..16))
    MAX-ACCESS read-only
    STATUS     current
    DESCRIPTION
            "-- empty --"
    ::= { hmStatusIpRouterRipDynLanSitesEntry 1 }

-- {COLUMN} 1.3.6.1.4.1.248.32.18.1.10.19.13.1.2
hmStatusIpRouterRipDynLanSitesEntryRipType OBJECT-TYPE
    SYNTAX     INTEGER {
                  eOff (0),
                  eRip1 (1),
                  eR1Comp (2),
                  eRip2 (3)
            }
    MAX-ACCESS read-only
    STATUS     current
    DESCRIPTION
            "-- empty --"
    ::= { hmStatusIpRouterRipDynLanSitesEntry 2 }

-- {COLUMN} 1.3.6.1.4.1.248.32.18.1.10.19.13.1.3
hmStatusIpRouterRipDynLanSitesEntryRipAccept OBJECT-TYPE
    SYNTAX     INTEGER {
                  eNo (0),
                  eYes (1)
            }
    MAX-ACCESS read-only
    STATUS     current
    DESCRIPTION
            "-- empty --"
    ::= { hmStatusIpRouterRipDynLanSitesEntry 3 }

-- {COLUMN} 1.3.6.1.4.1.248.32.18.1.10.19.13.1.4
hmStatusIpRouterRipDynLanSitesEntryPoisonedReverse OBJECT-TYPE
    SYNTAX     INTEGER {
                  eNo (0),
                  eYes (1)
            }
    MAX-ACCESS read-only
    STATUS     current
    DESCRIPTION
            "-- empty --"
    ::= { hmStatusIpRouterRipDynLanSitesEntry 4 }

-- {COLUMN} 1.3.6.1.4.1.248.32.18.1.10.19.13.1.5
hmStatusIpRouterRipDynLanSitesEntryDftRtgTag OBJECT-TYPE
    SYNTAX     Integer32 (0..65535)
    MAX-ACCESS read-only
    STATUS     current
    DESCRIPTION
            "-- empty --"
    ::= { hmStatusIpRouterRipDynLanSitesEntry 5 }

-- {COLUMN} 1.3.6.1.4.1.248.32.18.1.10.19.13.1.6
hmStatusIpRouterRipDynLanSitesEntryRtgTagList OBJECT-TYPE
    SYNTAX     DisplayString (SIZE(0..33))
    MAX-ACCESS read-only
    STATUS     current
    DESCRIPTION
            "-- empty --"
    ::= { hmStatusIpRouterRipDynLanSitesEntry 6 }

-- {COLUMN} 1.3.6.1.4.1.248.32.18.1.10.19.13.1.8
hmStatusIpRouterRipDynLanSitesEntryVlanId OBJECT-TYPE
    SYNTAX     Integer32 (0..65535)
    MAX-ACCESS read-only
    STATUS     current
    DESCRIPTION
            "-- empty --"
    ::= { hmStatusIpRouterRipDynLanSitesEntry 8 }

-- {COLUMN} 1.3.6.1.4.1.248.32.18.1.10.19.13.1.10
hmStatusIpRouterRipDynLanSitesEntryRxFilter OBJECT-TYPE
    SYNTAX     DisplayString (SIZE(0..16))
    MAX-ACCESS read-only
    STATUS     current
    DESCRIPTION
            "-- empty --"
    ::= { hmStatusIpRouterRipDynLanSitesEntry 10 }

-- {COLUMN} 1.3.6.1.4.1.248.32.18.1.10.19.13.1.11
hmStatusIpRouterRipDynLanSitesEntryTxFilter OBJECT-TYPE
    SYNTAX     DisplayString (SIZE(0..16))
    MAX-ACCESS read-only
    STATUS     current
    DESCRIPTION
            "-- empty --"
    ::= { hmStatusIpRouterRipDynLanSitesEntry 11 }

-- {COLUMN} 1.3.6.1.4.1.248.32.18.1.10.19.13.1.12
hmStatusIpRouterRipDynLanSitesEntryRipSend OBJECT-TYPE
    SYNTAX     INTEGER {
                  eNo (0),
                  eYes (1)
            }
    MAX-ACCESS read-only
    STATUS     current
    DESCRIPTION
            "-- empty --"
    ::= { hmStatusIpRouterRipDynLanSitesEntry 12 }

-- {COLUMN} 1.3.6.1.4.1.248.32.18.1.10.19.13.1.31
hmStatusIpRouterRipDynLanSitesEntryPort OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eAny (65535)
            }
    MAX-ACCESS read-only
    STATUS     current
    DESCRIPTION
            "-- empty --"
    ::= { hmStatusIpRouterRipDynLanSitesEntry 31 }

-- {TABLE} 1.3.6.1.4.1.248.32.18.1.10.19.14
hmStatusIpRouterRipDynWanSitesTable OBJECT-TYPE
    SYNTAX     SEQUENCE OF HmStatusIpRouterRipDynWanSitesEntry
    MAX-ACCESS not-accessible
    STATUS     current
    DESCRIPTION
            "-- empty --"
    ::= { hmStatusIpRouterRip 14 }

-- {ROW} 1.3.6.1.4.1.248.32.18.1.10.19.14.1
hmStatusIpRouterRipDynWanSitesEntry OBJECT-TYPE
    SYNTAX     HmStatusIpRouterRipDynWanSitesEntry
    MAX-ACCESS not-accessible
    STATUS     current
    DESCRIPTION
            ""
    INDEX {
            hmStatusIpRouterRipDynWanSitesEntryPeer
          }
    ::= { hmStatusIpRouterRipDynWanSitesTable 1 }

HmStatusIpRouterRipDynWanSitesEntry ::= SEQUENCE {
            hmStatusIpRouterRipDynWanSitesEntryPeer DisplayString,
            hmStatusIpRouterRipDynWanSitesEntryRipType INTEGER,
            hmStatusIpRouterRipDynWanSitesEntryRipAccept INTEGER,
            hmStatusIpRouterRipDynWanSitesEntryMasquerade INTEGER,
            hmStatusIpRouterRipDynWanSitesEntryDftRtgTag Integer32,
            hmStatusIpRouterRipDynWanSitesEntryRtgTagList DisplayString,
            hmStatusIpRouterRipDynWanSitesEntryPoisonedReverse INTEGER,
            hmStatusIpRouterRipDynWanSitesEntryRfc2091 INTEGER,
            hmStatusIpRouterRipDynWanSitesEntryGateway IpAddress,
            hmStatusIpRouterRipDynWanSitesEntryRxFilter DisplayString,
            hmStatusIpRouterRipDynWanSitesEntryTxFilter DisplayString,
            hmStatusIpRouterRipDynWanSitesEntryRipSend INTEGER
    }

-- {COLUMN} 1.3.6.1.4.1.248.32.18.1.10.19.14.1.1
hmStatusIpRouterRipDynWanSitesEntryPeer OBJECT-TYPE
    SYNTAX     DisplayString (SIZE(0..16))
    MAX-ACCESS read-only
    STATUS     current
    DESCRIPTION
            "-- empty --"
    ::= { hmStatusIpRouterRipDynWanSitesEntry 1 }

-- {COLUMN} 1.3.6.1.4.1.248.32.18.1.10.19.14.1.2
hmStatusIpRouterRipDynWanSitesEntryRipType OBJECT-TYPE
    SYNTAX     INTEGER {
                  eOff (0),
                  eRip1 (1),
                  eR1Comp (2),
                  eRip2 (3)
            }
    MAX-ACCESS read-only
    STATUS     current
    DESCRIPTION
            "-- empty --"
    ::= { hmStatusIpRouterRipDynWanSitesEntry 2 }

-- {COLUMN} 1.3.6.1.4.1.248.32.18.1.10.19.14.1.3
hmStatusIpRouterRipDynWanSitesEntryRipAccept OBJECT-TYPE
    SYNTAX     INTEGER {
                  eNo (0),
                  eYes (1)
            }
    MAX-ACCESS read-only
    STATUS     current
    DESCRIPTION
            "-- empty --"
    ::= { hmStatusIpRouterRipDynWanSitesEntry 3 }

-- {COLUMN} 1.3.6.1.4.1.248.32.18.1.10.19.14.1.4
hmStatusIpRouterRipDynWanSitesEntryMasquerade OBJECT-TYPE
    SYNTAX     INTEGER {
                  eAuto (0),
                  eOn (1),
                  eIntranet (2)
            }
    MAX-ACCESS read-only
    STATUS     current
    DESCRIPTION
            "-- empty --"
    ::= { hmStatusIpRouterRipDynWanSitesEntry 4 }

-- {COLUMN} 1.3.6.1.4.1.248.32.18.1.10.19.14.1.5
hmStatusIpRouterRipDynWanSitesEntryDftRtgTag OBJECT-TYPE
    SYNTAX     Integer32 (0..65535)
    MAX-ACCESS read-only
    STATUS     current
    DESCRIPTION
            "-- empty --"
    ::= { hmStatusIpRouterRipDynWanSitesEntry 5 }

-- {COLUMN} 1.3.6.1.4.1.248.32.18.1.10.19.14.1.6
hmStatusIpRouterRipDynWanSitesEntryRtgTagList OBJECT-TYPE
    SYNTAX     DisplayString (SIZE(0..33))
    MAX-ACCESS read-only
    STATUS     current
    DESCRIPTION
            "-- empty --"
    ::= { hmStatusIpRouterRipDynWanSitesEntry 6 }

-- {COLUMN} 1.3.6.1.4.1.248.32.18.1.10.19.14.1.7
hmStatusIpRouterRipDynWanSitesEntryPoisonedReverse OBJECT-TYPE
    SYNTAX     INTEGER {
                  eNo (0),
                  eYes (1)
            }
    MAX-ACCESS read-only
    STATUS     current
    DESCRIPTION
            "-- empty --"
    ::= { hmStatusIpRouterRipDynWanSitesEntry 7 }

-- {COLUMN} 1.3.6.1.4.1.248.32.18.1.10.19.14.1.8
hmStatusIpRouterRipDynWanSitesEntryRfc2091 OBJECT-TYPE
    SYNTAX     INTEGER {
                  eNo (0),
                  eYes (1)
            }
    MAX-ACCESS read-only
    STATUS     current
    DESCRIPTION
            "-- empty --"
    ::= { hmStatusIpRouterRipDynWanSitesEntry 8 }

-- {COLUMN} 1.3.6.1.4.1.248.32.18.1.10.19.14.1.9
hmStatusIpRouterRipDynWanSitesEntryGateway OBJECT-TYPE
    SYNTAX     IpAddress
    MAX-ACCESS read-only
    STATUS     current
    DESCRIPTION
            "-- empty --"
    ::= { hmStatusIpRouterRipDynWanSitesEntry 9 }

-- {COLUMN} 1.3.6.1.4.1.248.32.18.1.10.19.14.1.10
hmStatusIpRouterRipDynWanSitesEntryRxFilter OBJECT-TYPE
    SYNTAX     DisplayString (SIZE(0..16))
    MAX-ACCESS read-only
    STATUS     current
    DESCRIPTION
            "-- empty --"
    ::= { hmStatusIpRouterRipDynWanSitesEntry 10 }

-- {COLUMN} 1.3.6.1.4.1.248.32.18.1.10.19.14.1.11
hmStatusIpRouterRipDynWanSitesEntryTxFilter OBJECT-TYPE
    SYNTAX     DisplayString (SIZE(0..16))
    MAX-ACCESS read-only
    STATUS     current
    DESCRIPTION
            "-- empty --"
    ::= { hmStatusIpRouterRipDynWanSitesEntry 11 }

-- {COLUMN} 1.3.6.1.4.1.248.32.18.1.10.19.14.1.12
hmStatusIpRouterRipDynWanSitesEntryRipSend OBJECT-TYPE
    SYNTAX     INTEGER {
                  eNo (0),
                  eYes (1)
            }
    MAX-ACCESS read-only
    STATUS     current
    DESCRIPTION
            "-- empty --"
    ::= { hmStatusIpRouterRipDynWanSitesEntry 12 }

-- {TABLE} 1.3.6.1.4.1.248.32.18.1.10.19.15
hmStatusIpRouterRipFilterTable OBJECT-TYPE
    SYNTAX     SEQUENCE OF HmStatusIpRouterRipFilterEntry
    MAX-ACCESS not-accessible
    STATUS     current
    DESCRIPTION
            "-- empty --"
    ::= { hmStatusIpRouterRip 15 }

-- {ROW} 1.3.6.1.4.1.248.32.18.1.10.19.15.1
hmStatusIpRouterRipFilterEntry OBJECT-TYPE
    SYNTAX     HmStatusIpRouterRipFilterEntry
    MAX-ACCESS not-accessible
    STATUS     current
    DESCRIPTION
            ""
    INDEX {
            hmStatusIpRouterRipFilterEntryIdx
          }
    ::= { hmStatusIpRouterRipFilterTable 1 }

HmStatusIpRouterRipFilterEntry ::= SEQUENCE {
            hmStatusIpRouterRipFilterEntryIdx Integer32,
            hmStatusIpRouterRipFilterEntryType INTEGER,
            hmStatusIpRouterRipFilterEntryName DisplayString,
            hmStatusIpRouterRipFilterEntryIpAddress IpAddress,
            hmStatusIpRouterRipFilterEntryIpNetmask IpAddress
    }

-- {COLUMN} 1.3.6.1.4.1.248.32.18.1.10.19.15.1.1
hmStatusIpRouterRipFilterEntryIdx OBJECT-TYPE
    SYNTAX     Integer32 (0..65535)
    MAX-ACCESS read-only
    STATUS     current
    DESCRIPTION
            "-- empty --"
    ::= { hmStatusIpRouterRipFilterEntry 1 }

-- {COLUMN} 1.3.6.1.4.1.248.32.18.1.10.19.15.1.2
hmStatusIpRouterRipFilterEntryType OBJECT-TYPE
    SYNTAX     INTEGER {
                  eUnknown (0),
                  ePositive (1),
                  eNegative (2)
            }
    MAX-ACCESS read-only
    STATUS     current
    DESCRIPTION
            "-- empty --"
    ::= { hmStatusIpRouterRipFilterEntry 2 }

-- {COLUMN} 1.3.6.1.4.1.248.32.18.1.10.19.15.1.3
hmStatusIpRouterRipFilterEntryName OBJECT-TYPE
    SYNTAX     DisplayString (SIZE(0..255))
    MAX-ACCESS read-only
    STATUS     current
    DESCRIPTION
            "-- empty --"
    ::= { hmStatusIpRouterRipFilterEntry 3 }

-- {COLUMN} 1.3.6.1.4.1.248.32.18.1.10.19.15.1.4
hmStatusIpRouterRipFilterEntryIpAddress OBJECT-TYPE
    SYNTAX     IpAddress
    MAX-ACCESS read-only
    STATUS     current
    DESCRIPTION
            "-- empty --"
    ::= { hmStatusIpRouterRipFilterEntry 4 }

-- {COLUMN} 1.3.6.1.4.1.248.32.18.1.10.19.15.1.5
hmStatusIpRouterRipFilterEntryIpNetmask OBJECT-TYPE
    SYNTAX     IpAddress
    MAX-ACCESS read-only
    STATUS     current
    DESCRIPTION
            "-- empty --"
    ::= { hmStatusIpRouterRipFilterEntry 5 }

-- {TABLE} 1.3.6.1.4.1.248.32.18.1.10.19.16
hmStatusIpRouterRipWildcardSitesTable OBJECT-TYPE
    SYNTAX     SEQUENCE OF HmStatusIpRouterRipWildcardSitesEntry
    MAX-ACCESS not-accessible
    STATUS     current
    DESCRIPTION
            "-- empty --"
    ::= { hmStatusIpRouterRip 16 }

-- {ROW} 1.3.6.1.4.1.248.32.18.1.10.19.16.1
hmStatusIpRouterRipWildcardSitesEntry OBJECT-TYPE
    SYNTAX     HmStatusIpRouterRipWildcardSitesEntry
    MAX-ACCESS not-accessible
    STATUS     current
    DESCRIPTION
            ""
    INDEX {
            hmStatusIpRouterRipWildcardSitesEntryPeer
          }
    ::= { hmStatusIpRouterRipWildcardSitesTable 1 }

HmStatusIpRouterRipWildcardSitesEntry ::= SEQUENCE {
            hmStatusIpRouterRipWildcardSitesEntryPeer DisplayString,
            hmStatusIpRouterRipWildcardSitesEntryRipType INTEGER,
            hmStatusIpRouterRipWildcardSitesEntryRipAccept INTEGER,
            hmStatusIpRouterRipWildcardSitesEntryMasquerade INTEGER,
            hmStatusIpRouterRipWildcardSitesEntryDftRtgTag Integer32,
            hmStatusIpRouterRipWildcardSitesEntryRtgTagList DisplayString,
            hmStatusIpRouterRipWildcardSitesEntryPoisonedReverse INTEGER,
            hmStatusIpRouterRipWildcardSitesEntryRfc2091 INTEGER,
            hmStatusIpRouterRipWildcardSitesEntryGateway IpAddress,
            hmStatusIpRouterRipWildcardSitesEntryRxFilter DisplayString,
            hmStatusIpRouterRipWildcardSitesEntryTxFilter DisplayString,
            hmStatusIpRouterRipWildcardSitesEntryRipSend INTEGER
    }

-- {COLUMN} 1.3.6.1.4.1.248.32.18.1.10.19.16.1.1
hmStatusIpRouterRipWildcardSitesEntryPeer OBJECT-TYPE
    SYNTAX     DisplayString (SIZE(0..16))
    MAX-ACCESS read-only
    STATUS     current
    DESCRIPTION
            "-- empty --"
    ::= { hmStatusIpRouterRipWildcardSitesEntry 1 }

-- {COLUMN} 1.3.6.1.4.1.248.32.18.1.10.19.16.1.2
hmStatusIpRouterRipWildcardSitesEntryRipType OBJECT-TYPE
    SYNTAX     INTEGER {
                  eOff (0),
                  eRip1 (1),
                  eR1Comp (2),
                  eRip2 (3)
            }
    MAX-ACCESS read-only
    STATUS     current
    DESCRIPTION
            "-- empty --"
    ::= { hmStatusIpRouterRipWildcardSitesEntry 2 }

-- {COLUMN} 1.3.6.1.4.1.248.32.18.1.10.19.16.1.3
hmStatusIpRouterRipWildcardSitesEntryRipAccept OBJECT-TYPE
    SYNTAX     INTEGER {
                  eNo (0),
                  eYes (1)
            }
    MAX-ACCESS read-only
    STATUS     current
    DESCRIPTION
            "-- empty --"
    ::= { hmStatusIpRouterRipWildcardSitesEntry 3 }

-- {COLUMN} 1.3.6.1.4.1.248.32.18.1.10.19.16.1.4
hmStatusIpRouterRipWildcardSitesEntryMasquerade OBJECT-TYPE
    SYNTAX     INTEGER {
                  eAuto (0),
                  eOn (1),
                  eIntranet (2)
            }
    MAX-ACCESS read-only
    STATUS     current
    DESCRIPTION
            "-- empty --"
    ::= { hmStatusIpRouterRipWildcardSitesEntry 4 }

-- {COLUMN} 1.3.6.1.4.1.248.32.18.1.10.19.16.1.5
hmStatusIpRouterRipWildcardSitesEntryDftRtgTag OBJECT-TYPE
    SYNTAX     Integer32 (0..65535)
    MAX-ACCESS read-only
    STATUS     current
    DESCRIPTION
            "-- empty --"
    ::= { hmStatusIpRouterRipWildcardSitesEntry 5 }

-- {COLUMN} 1.3.6.1.4.1.248.32.18.1.10.19.16.1.6
hmStatusIpRouterRipWildcardSitesEntryRtgTagList OBJECT-TYPE
    SYNTAX     DisplayString (SIZE(0..33))
    MAX-ACCESS read-only
    STATUS     current
    DESCRIPTION
            "-- empty --"
    ::= { hmStatusIpRouterRipWildcardSitesEntry 6 }

-- {COLUMN} 1.3.6.1.4.1.248.32.18.1.10.19.16.1.7
hmStatusIpRouterRipWildcardSitesEntryPoisonedReverse OBJECT-TYPE
    SYNTAX     INTEGER {
                  eNo (0),
                  eYes (1)
            }
    MAX-ACCESS read-only
    STATUS     current
    DESCRIPTION
            "-- empty --"
    ::= { hmStatusIpRouterRipWildcardSitesEntry 7 }

-- {COLUMN} 1.3.6.1.4.1.248.32.18.1.10.19.16.1.8
hmStatusIpRouterRipWildcardSitesEntryRfc2091 OBJECT-TYPE
    SYNTAX     INTEGER {
                  eNo (0),
                  eYes (1)
            }
    MAX-ACCESS read-only
    STATUS     current
    DESCRIPTION
            "-- empty --"
    ::= { hmStatusIpRouterRipWildcardSitesEntry 8 }

-- {COLUMN} 1.3.6.1.4.1.248.32.18.1.10.19.16.1.9
hmStatusIpRouterRipWildcardSitesEntryGateway OBJECT-TYPE
    SYNTAX     IpAddress
    MAX-ACCESS read-only
    STATUS     current
    DESCRIPTION
            "-- empty --"
    ::= { hmStatusIpRouterRipWildcardSitesEntry 9 }

-- {COLUMN} 1.3.6.1.4.1.248.32.18.1.10.19.16.1.10
hmStatusIpRouterRipWildcardSitesEntryRxFilter OBJECT-TYPE
    SYNTAX     DisplayString (SIZE(0..16))
    MAX-ACCESS read-only
    STATUS     current
    DESCRIPTION
            "-- empty --"
    ::= { hmStatusIpRouterRipWildcardSitesEntry 10 }

-- {COLUMN} 1.3.6.1.4.1.248.32.18.1.10.19.16.1.11
hmStatusIpRouterRipWildcardSitesEntryTxFilter OBJECT-TYPE
    SYNTAX     DisplayString (SIZE(0..16))
    MAX-ACCESS read-only
    STATUS     current
    DESCRIPTION
            "-- empty --"
    ::= { hmStatusIpRouterRipWildcardSitesEntry 11 }

-- {COLUMN} 1.3.6.1.4.1.248.32.18.1.10.19.16.1.12
hmStatusIpRouterRipWildcardSitesEntryRipSend OBJECT-TYPE
    SYNTAX     INTEGER {
                  eNo (0),
                  eYes (1)
            }
    MAX-ACCESS read-only
    STATUS     current
    DESCRIPTION
            "-- empty --"
    ::= { hmStatusIpRouterRipWildcardSitesEntry 12 }

-- {TABLE} 1.3.6.1.4.1.248.32.18.1.10.19.20
hmStatusIpRouterRipAllRoutesTable OBJECT-TYPE
    SYNTAX     SEQUENCE OF HmStatusIpRouterRipAllRoutesEntry
    MAX-ACCESS not-accessible
    STATUS     current
    DESCRIPTION
            "-- empty --"
    ::= { hmStatusIpRouterRip 20 }

-- {ROW} 1.3.6.1.4.1.248.32.18.1.10.19.20.1
hmStatusIpRouterRipAllRoutesEntry OBJECT-TYPE
    SYNTAX     HmStatusIpRouterRipAllRoutesEntry
    MAX-ACCESS not-accessible
    STATUS     current
    DESCRIPTION
            ""
    INDEX {
            hmStatusIpRouterRipAllRoutesEntryIpAddress,
            hmStatusIpRouterRipAllRoutesEntryIpNetmask,
            hmStatusIpRouterRipAllRoutesEntryRtgTag,
            hmStatusIpRouterRipAllRoutesEntryGateway
          }
    ::= { hmStatusIpRouterRipAllRoutesTable 1 }

HmStatusIpRouterRipAllRoutesEntry ::= SEQUENCE {
            hmStatusIpRouterRipAllRoutesEntryIpAddress IpAddress,
            hmStatusIpRouterRipAllRoutesEntryIpNetmask IpAddress,
            hmStatusIpRouterRipAllRoutesEntryTime Integer32,
            hmStatusIpRouterRipAllRoutesEntryDistance Integer32,
            hmStatusIpRouterRipAllRoutesEntryGateway IpAddress,
            hmStatusIpRouterRipAllRoutesEntryRtgTag Integer32,
            hmStatusIpRouterRipAllRoutesEntryPeer DisplayString,
            hmStatusIpRouterRipAllRoutesEntryVlanId Integer32,
            hmStatusIpRouterRipAllRoutesEntryNetworkName DisplayString,
            hmStatusIpRouterRipAllRoutesEntryPort INTEGER
    }

-- {COLUMN} 1.3.6.1.4.1.248.32.18.1.10.19.20.1.1
hmStatusIpRouterRipAllRoutesEntryIpAddress OBJECT-TYPE
    SYNTAX     IpAddress
    MAX-ACCESS read-only
    STATUS     current
    DESCRIPTION
            "-- empty --"
    ::= { hmStatusIpRouterRipAllRoutesEntry 1 }

-- {COLUMN} 1.3.6.1.4.1.248.32.18.1.10.19.20.1.2
hmStatusIpRouterRipAllRoutesEntryIpNetmask OBJECT-TYPE
    SYNTAX     IpAddress
    MAX-ACCESS read-only
    STATUS     current
    DESCRIPTION
            "-- empty --"
    ::= { hmStatusIpRouterRipAllRoutesEntry 2 }

-- {COLUMN} 1.3.6.1.4.1.248.32.18.1.10.19.20.1.3
hmStatusIpRouterRipAllRoutesEntryTime OBJECT-TYPE
    SYNTAX     Integer32 (0..65535)
    MAX-ACCESS read-only
    STATUS     current
    DESCRIPTION
            "-- empty --"
    ::= { hmStatusIpRouterRipAllRoutesEntry 3 }

-- {COLUMN} 1.3.6.1.4.1.248.32.18.1.10.19.20.1.4
hmStatusIpRouterRipAllRoutesEntryDistance OBJECT-TYPE
    SYNTAX     Integer32 (0..65535)
    MAX-ACCESS read-only
    STATUS     current
    DESCRIPTION
            "-- empty --"
    ::= { hmStatusIpRouterRipAllRoutesEntry 4 }

-- {COLUMN} 1.3.6.1.4.1.248.32.18.1.10.19.20.1.5
hmStatusIpRouterRipAllRoutesEntryGateway OBJECT-TYPE
    SYNTAX     IpAddress
    MAX-ACCESS read-only
    STATUS     current
    DESCRIPTION
            "-- empty --"
    ::= { hmStatusIpRouterRipAllRoutesEntry 5 }

-- {COLUMN} 1.3.6.1.4.1.248.32.18.1.10.19.20.1.6
hmStatusIpRouterRipAllRoutesEntryRtgTag OBJECT-TYPE
    SYNTAX     Integer32 (0..65535)
    MAX-ACCESS read-only
    STATUS     current
    DESCRIPTION
            "-- empty --"
    ::= { hmStatusIpRouterRipAllRoutesEntry 6 }

-- {COLUMN} 1.3.6.1.4.1.248.32.18.1.10.19.20.1.8
hmStatusIpRouterRipAllRoutesEntryPeer OBJECT-TYPE
    SYNTAX     DisplayString (SIZE(0..255))
    MAX-ACCESS read-only
    STATUS     current
    DESCRIPTION
            "-- empty --"
    ::= { hmStatusIpRouterRipAllRoutesEntry 8 }

-- {COLUMN} 1.3.6.1.4.1.248.32.18.1.10.19.20.1.10
hmStatusIpRouterRipAllRoutesEntryVlanId OBJECT-TYPE
    SYNTAX     Integer32 (0..65535)
    MAX-ACCESS read-only
    STATUS     current
    DESCRIPTION
            "-- empty --"
    ::= { hmStatusIpRouterRipAllRoutesEntry 10 }

-- {COLUMN} 1.3.6.1.4.1.248.32.18.1.10.19.20.1.11
hmStatusIpRouterRipAllRoutesEntryNetworkName OBJECT-TYPE
    SYNTAX     DisplayString (SIZE(0..255))
    MAX-ACCESS read-only
    STATUS     current
    DESCRIPTION
            "-- empty --"
    ::= { hmStatusIpRouterRipAllRoutesEntry 11 }

-- {COLUMN} 1.3.6.1.4.1.248.32.18.1.10.19.20.1.12
hmStatusIpRouterRipAllRoutesEntryPort OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eAny (65535)
            }
    MAX-ACCESS read-only
    STATUS     current
    DESCRIPTION
            "-- empty --"
    ::= { hmStatusIpRouterRipAllRoutesEntry 12 }

-- {SCALAR} 1.3.6.1.4.1.248.32.18.1.10.20
hmStatusIpRouterDeleteValues OBJECT-TYPE
    SYNTAX     DisplayString
    MAX-ACCESS read-write
    STATUS     current
    DESCRIPTION
            "-- empty --"
    ::= { hmStatusIpRouter 20 }

-- {TABLE} 1.3.6.1.4.1.248.32.18.1.10.21
hmStatusIpRouterServiceTableTable OBJECT-TYPE
    SYNTAX     SEQUENCE OF HmStatusIpRouterServiceTableEntry
    MAX-ACCESS not-accessible
    STATUS     current
    DESCRIPTION
            "-- empty --"
    ::= { hmStatusIpRouter 21 }

-- {ROW} 1.3.6.1.4.1.248.32.18.1.10.21.1
hmStatusIpRouterServiceTableEntry OBJECT-TYPE
    SYNTAX     HmStatusIpRouterServiceTableEntry
    MAX-ACCESS not-accessible
    STATUS     current
    DESCRIPTION
            ""
    INDEX {
            hmStatusIpRouterServiceTableEntryService
          }
    ::= { hmStatusIpRouterServiceTableTable 1 }

HmStatusIpRouterServiceTableEntry ::= SEQUENCE {
            hmStatusIpRouterServiceTableEntryService INTEGER,
            hmStatusIpRouterServiceTableEntryPacketRx Counter32,
            hmStatusIpRouterServiceTableEntryPacketTx Counter32,
            hmStatusIpRouterServiceTableEntryPacketRel DisplayString,
            hmStatusIpRouterServiceTableEntryKbytesRx Counter32,
            hmStatusIpRouterServiceTableEntryKbytesTx Counter32,
            hmStatusIpRouterServiceTableEntryKbytesRel DisplayString
    }

-- {COLUMN} 1.3.6.1.4.1.248.32.18.1.10.21.1.1
hmStatusIpRouterServiceTableEntryService OBJECT-TYPE
    SYNTAX     INTEGER {
                  eIcmp (1),
                  eFtp (2),
                  eHttp (3),
                  eSmtp (4),
                  eDns (5),
                  eTelnet (6),
                  eTftp (7),
                  eDhcp (8),
                  ePop3 (9),
                  eNetbios (10),
                  eImap2 (11),
                  eNews (12),
                  eIrc (13),
                  eSnmp (14),
                  eOther (15),
                  eTotal (16)
            }
    MAX-ACCESS read-only
    STATUS     current
    DESCRIPTION
            "-- empty --"
    ::= { hmStatusIpRouterServiceTableEntry 1 }

-- {COLUMN} 1.3.6.1.4.1.248.32.18.1.10.21.1.2
hmStatusIpRouterServiceTableEntryPacketRx OBJECT-TYPE
    SYNTAX     Counter32
    MAX-ACCESS read-only
    STATUS     current
    DESCRIPTION
            "-- empty --"
    ::= { hmStatusIpRouterServiceTableEntry 2 }

-- {COLUMN} 1.3.6.1.4.1.248.32.18.1.10.21.1.3
hmStatusIpRouterServiceTableEntryPacketTx OBJECT-TYPE
    SYNTAX     Counter32
    MAX-ACCESS read-only
    STATUS     current
    DESCRIPTION
            "-- empty --"
    ::= { hmStatusIpRouterServiceTableEntry 3 }

-- {COLUMN} 1.3.6.1.4.1.248.32.18.1.10.21.1.4
hmStatusIpRouterServiceTableEntryPacketRel OBJECT-TYPE
    SYNTAX     DisplayString (SIZE(0..255))
    MAX-ACCESS read-only
    STATUS     current
    DESCRIPTION
            "-- empty --"
    ::= { hmStatusIpRouterServiceTableEntry 4 }

-- {COLUMN} 1.3.6.1.4.1.248.32.18.1.10.21.1.5
hmStatusIpRouterServiceTableEntryKbytesRx OBJECT-TYPE
    SYNTAX     Counter32
    MAX-ACCESS read-only
    STATUS     current
    DESCRIPTION
            "-- empty --"
    ::= { hmStatusIpRouterServiceTableEntry 5 }

-- {COLUMN} 1.3.6.1.4.1.248.32.18.1.10.21.1.6
hmStatusIpRouterServiceTableEntryKbytesTx OBJECT-TYPE
    SYNTAX     Counter32
    MAX-ACCESS read-only
    STATUS     current
    DESCRIPTION
            "-- empty --"
    ::= { hmStatusIpRouterServiceTableEntry 6 }

-- {COLUMN} 1.3.6.1.4.1.248.32.18.1.10.21.1.7
hmStatusIpRouterServiceTableEntryKbytesRel OBJECT-TYPE
    SYNTAX     DisplayString (SIZE(0..255))
    MAX-ACCESS read-only
    STATUS     current
    DESCRIPTION
            "-- empty --"
    ::= { hmStatusIpRouterServiceTableEntry 7 }

-- {TABLE} 1.3.6.1.4.1.248.32.18.1.10.22
hmStatusIpRouterFilterListTable OBJECT-TYPE
    SYNTAX     SEQUENCE OF HmStatusIpRouterFilterListEntry
    MAX-ACCESS not-accessible
    STATUS     current
    DESCRIPTION
            "-- empty --"
    ::= { hmStatusIpRouter 22 }

-- {ROW} 1.3.6.1.4.1.248.32.18.1.10.22.1
hmStatusIpRouterFilterListEntry OBJECT-TYPE
    SYNTAX     HmStatusIpRouterFilterListEntry
    MAX-ACCESS not-accessible
    STATUS     current
    DESCRIPTION
            ""
    INDEX {
            hmStatusIpRouterFilterListEntryIdx
          }
    ::= { hmStatusIpRouterFilterListTable 1 }

HmStatusIpRouterFilterListEntry ::= SEQUENCE {
            hmStatusIpRouterFilterListEntryIdx Integer32,
            hmStatusIpRouterFilterListEntryProt Integer32,
            hmStatusIpRouterFilterListEntrySrcAddress IpAddress,
            hmStatusIpRouterFilterListEntrySrcNetmask IpAddress,
            hmStatusIpRouterFilterListEntrySSt Integer32,
            hmStatusIpRouterFilterListEntrySEnd Integer32,
            hmStatusIpRouterFilterListEntryDstAddress IpAddress,
            hmStatusIpRouterFilterListEntryDstNetmask IpAddress,
            hmStatusIpRouterFilterListEntryDSt Integer32,
            hmStatusIpRouterFilterListEntryDEnd Integer32,
            hmStatusIpRouterFilterListEntryAction DisplayString,
            hmStatusIpRouterFilterListEntrySrcMac DisplayString,
            hmStatusIpRouterFilterListEntryDstMac DisplayString,
            hmStatusIpRouterFilterListEntryLinked INTEGER,
            hmStatusIpRouterFilterListEntryPrio Integer32,
            hmStatusIpRouterFilterListEntryRtgTag Integer32,
            hmStatusIpRouterFilterListEntrySrcTag Integer32
    }

-- {COLUMN} 1.3.6.1.4.1.248.32.18.1.10.22.1.1
hmStatusIpRouterFilterListEntryIdx OBJECT-TYPE
    SYNTAX     Integer32 (0..2147483647)
    MAX-ACCESS read-only
    STATUS     current
    DESCRIPTION
            "-- empty --"
    ::= { hmStatusIpRouterFilterListEntry 1 }

-- {COLUMN} 1.3.6.1.4.1.248.32.18.1.10.22.1.2
hmStatusIpRouterFilterListEntryProt OBJECT-TYPE
    SYNTAX     Integer32 (0..255)
    MAX-ACCESS read-only
    STATUS     current
    DESCRIPTION
            "-- empty --"
    ::= { hmStatusIpRouterFilterListEntry 2 }

-- {COLUMN} 1.3.6.1.4.1.248.32.18.1.10.22.1.3
hmStatusIpRouterFilterListEntrySrcAddress OBJECT-TYPE
    SYNTAX     IpAddress
    MAX-ACCESS read-only
    STATUS     current
    DESCRIPTION
            "-- empty --"
    ::= { hmStatusIpRouterFilterListEntry 3 }

-- {COLUMN} 1.3.6.1.4.1.248.32.18.1.10.22.1.4
hmStatusIpRouterFilterListEntrySrcNetmask OBJECT-TYPE
    SYNTAX     IpAddress
    MAX-ACCESS read-only
    STATUS     current
    DESCRIPTION
            "-- empty --"
    ::= { hmStatusIpRouterFilterListEntry 4 }

-- {COLUMN} 1.3.6.1.4.1.248.32.18.1.10.22.1.5
hmStatusIpRouterFilterListEntrySSt OBJECT-TYPE
    SYNTAX     Integer32 (0..65535)
    MAX-ACCESS read-only
    STATUS     current
    DESCRIPTION
            "-- empty --"
    ::= { hmStatusIpRouterFilterListEntry 5 }

-- {COLUMN} 1.3.6.1.4.1.248.32.18.1.10.22.1.6
hmStatusIpRouterFilterListEntrySEnd OBJECT-TYPE
    SYNTAX     Integer32 (0..65535)
    MAX-ACCESS read-only
    STATUS     current
    DESCRIPTION
            "-- empty --"
    ::= { hmStatusIpRouterFilterListEntry 6 }

-- {COLUMN} 1.3.6.1.4.1.248.32.18.1.10.22.1.7
hmStatusIpRouterFilterListEntryDstAddress OBJECT-TYPE
    SYNTAX     IpAddress
    MAX-ACCESS read-only
    STATUS     current
    DESCRIPTION
            "-- empty --"
    ::= { hmStatusIpRouterFilterListEntry 7 }

-- {COLUMN} 1.3.6.1.4.1.248.32.18.1.10.22.1.8
hmStatusIpRouterFilterListEntryDstNetmask OBJECT-TYPE
    SYNTAX     IpAddress
    MAX-ACCESS read-only
    STATUS     current
    DESCRIPTION
            "-- empty --"
    ::= { hmStatusIpRouterFilterListEntry 8 }

-- {COLUMN} 1.3.6.1.4.1.248.32.18.1.10.22.1.9
hmStatusIpRouterFilterListEntryDSt OBJECT-TYPE
    SYNTAX     Integer32 (0..65535)
    MAX-ACCESS read-only
    STATUS     current
    DESCRIPTION
            "-- empty --"
    ::= { hmStatusIpRouterFilterListEntry 9 }

-- {COLUMN} 1.3.6.1.4.1.248.32.18.1.10.22.1.10
hmStatusIpRouterFilterListEntryDEnd OBJECT-TYPE
    SYNTAX     Integer32 (0..65535)
    MAX-ACCESS read-only
    STATUS     current
    DESCRIPTION
            "-- empty --"
    ::= { hmStatusIpRouterFilterListEntry 10 }

-- {COLUMN} 1.3.6.1.4.1.248.32.18.1.10.22.1.11
hmStatusIpRouterFilterListEntryAction OBJECT-TYPE
    SYNTAX     DisplayString (SIZE(0..255))
    MAX-ACCESS read-only
    STATUS     current
    DESCRIPTION
            "-- empty --"
    ::= { hmStatusIpRouterFilterListEntry 11 }

-- {COLUMN} 1.3.6.1.4.1.248.32.18.1.10.22.1.13
hmStatusIpRouterFilterListEntrySrcMac OBJECT-TYPE
    SYNTAX     DisplayString (SIZE(0..255))
    MAX-ACCESS read-only
    STATUS     current
    DESCRIPTION
            "-- empty --"
    ::= { hmStatusIpRouterFilterListEntry 13 }

-- {COLUMN} 1.3.6.1.4.1.248.32.18.1.10.22.1.14
hmStatusIpRouterFilterListEntryDstMac OBJECT-TYPE
    SYNTAX     DisplayString (SIZE(0..255))
    MAX-ACCESS read-only
    STATUS     current
    DESCRIPTION
            "-- empty --"
    ::= { hmStatusIpRouterFilterListEntry 14 }

-- {COLUMN} 1.3.6.1.4.1.248.32.18.1.10.22.1.15
hmStatusIpRouterFilterListEntryLinked OBJECT-TYPE
    SYNTAX     INTEGER {
                  eNo (0),
                  eYes (1)
            }
    MAX-ACCESS read-only
    STATUS     current
    DESCRIPTION
            "-- empty --"
    ::= { hmStatusIpRouterFilterListEntry 15 }

-- {COLUMN} 1.3.6.1.4.1.248.32.18.1.10.22.1.16
hmStatusIpRouterFilterListEntryPrio OBJECT-TYPE
    SYNTAX     Integer32 (0..65535)
    MAX-ACCESS read-only
    STATUS     current
    DESCRIPTION
            "-- empty --"
    ::= { hmStatusIpRouterFilterListEntry 16 }

-- {COLUMN} 1.3.6.1.4.1.248.32.18.1.10.22.1.17
hmStatusIpRouterFilterListEntryRtgTag OBJECT-TYPE
    SYNTAX     Integer32 (0..65535)
    MAX-ACCESS read-only
    STATUS     current
    DESCRIPTION
            "-- empty --"
    ::= { hmStatusIpRouterFilterListEntry 17 }

-- {COLUMN} 1.3.6.1.4.1.248.32.18.1.10.22.1.18
hmStatusIpRouterFilterListEntrySrcTag OBJECT-TYPE
    SYNTAX     Integer32 (0..65535)
    MAX-ACCESS read-only
    STATUS     current
    DESCRIPTION
            "-- empty --"
    ::= { hmStatusIpRouterFilterListEntry 18 }

-- {TABLE} 1.3.6.1.4.1.248.32.18.1.10.23
hmStatusIpRouterConnectionListTable OBJECT-TYPE
    SYNTAX     SEQUENCE OF HmStatusIpRouterConnectionListEntry
    MAX-ACCESS not-accessible
    STATUS     current
    DESCRIPTION
            "-- empty --"
    ::= { hmStatusIpRouter 23 }

-- {ROW} 1.3.6.1.4.1.248.32.18.1.10.23.1
hmStatusIpRouterConnectionListEntry OBJECT-TYPE
    SYNTAX     HmStatusIpRouterConnectionListEntry
    MAX-ACCESS not-accessible
    STATUS     current
    DESCRIPTION
            ""
    INDEX {
            hmStatusIpRouterConnectionListEntrySrcAddress,
            hmStatusIpRouterConnectionListEntryDstAddress,
            hmStatusIpRouterConnectionListEntryProt,
            hmStatusIpRouterConnectionListEntrySrcPort,
            hmStatusIpRouterConnectionListEntryDstPort
          }
    ::= { hmStatusIpRouterConnectionListTable 1 }

HmStatusIpRouterConnectionListEntry ::= SEQUENCE {
            hmStatusIpRouterConnectionListEntrySrcAddress IpAddress,
            hmStatusIpRouterConnectionListEntryDstAddress IpAddress,
            hmStatusIpRouterConnectionListEntryProt Integer32,
            hmStatusIpRouterConnectionListEntrySrcPort Integer32,
            hmStatusIpRouterConnectionListEntryDstPort Integer32,
            hmStatusIpRouterConnectionListEntryTimeout Integer32,
            hmStatusIpRouterConnectionListEntryFlags Integer32,
            hmStatusIpRouterConnectionListEntryFilterRule DisplayString,
            hmStatusIpRouterConnectionListEntrySrcRoute DisplayString,
            hmStatusIpRouterConnectionListEntryDestRoute DisplayString,
            hmStatusIpRouterConnectionListEntryRtgTag Integer32
    }

-- {COLUMN} 1.3.6.1.4.1.248.32.18.1.10.23.1.1
hmStatusIpRouterConnectionListEntrySrcAddress OBJECT-TYPE
    SYNTAX     IpAddress
    MAX-ACCESS read-only
    STATUS     current
    DESCRIPTION
            "-- empty --"
    ::= { hmStatusIpRouterConnectionListEntry 1 }

-- {COLUMN} 1.3.6.1.4.1.248.32.18.1.10.23.1.2
hmStatusIpRouterConnectionListEntryDstAddress OBJECT-TYPE
    SYNTAX     IpAddress
    MAX-ACCESS read-only
    STATUS     current
    DESCRIPTION
            "-- empty --"
    ::= { hmStatusIpRouterConnectionListEntry 2 }

-- {COLUMN} 1.3.6.1.4.1.248.32.18.1.10.23.1.3
hmStatusIpRouterConnectionListEntryProt OBJECT-TYPE
    SYNTAX     Integer32 (0..255)
    MAX-ACCESS read-only
    STATUS     current
    DESCRIPTION
            "-- empty --"
    ::= { hmStatusIpRouterConnectionListEntry 3 }

-- {COLUMN} 1.3.6.1.4.1.248.32.18.1.10.23.1.4
hmStatusIpRouterConnectionListEntrySrcPort OBJECT-TYPE
    SYNTAX     Integer32 (0..65535)
    MAX-ACCESS read-only
    STATUS     current
    DESCRIPTION
            "-- empty --"
    ::= { hmStatusIpRouterConnectionListEntry 4 }

-- {COLUMN} 1.3.6.1.4.1.248.32.18.1.10.23.1.5
hmStatusIpRouterConnectionListEntryDstPort OBJECT-TYPE
    SYNTAX     Integer32 (0..65535)
    MAX-ACCESS read-only
    STATUS     current
    DESCRIPTION
            "-- empty --"
    ::= { hmStatusIpRouterConnectionListEntry 5 }

-- {COLUMN} 1.3.6.1.4.1.248.32.18.1.10.23.1.6
hmStatusIpRouterConnectionListEntryTimeout OBJECT-TYPE
    SYNTAX     Integer32 (0..65535)
    MAX-ACCESS read-only
    STATUS     current
    DESCRIPTION
            "-- empty --"
    ::= { hmStatusIpRouterConnectionListEntry 6 }

-- {COLUMN} 1.3.6.1.4.1.248.32.18.1.10.23.1.7
hmStatusIpRouterConnectionListEntryFlags OBJECT-TYPE
    SYNTAX     Integer32 (0..2147483647)
    MAX-ACCESS read-only
    STATUS     current
    DESCRIPTION
            "-- empty --"
    ::= { hmStatusIpRouterConnectionListEntry 7 }

-- {COLUMN} 1.3.6.1.4.1.248.32.18.1.10.23.1.8
hmStatusIpRouterConnectionListEntryFilterRule OBJECT-TYPE
    SYNTAX     DisplayString (SIZE(0..255))
    MAX-ACCESS read-only
    STATUS     current
    DESCRIPTION
            "-- empty --"
    ::= { hmStatusIpRouterConnectionListEntry 8 }

-- {COLUMN} 1.3.6.1.4.1.248.32.18.1.10.23.1.9
hmStatusIpRouterConnectionListEntrySrcRoute OBJECT-TYPE
    SYNTAX     DisplayString (SIZE(0..255))
    MAX-ACCESS read-only
    STATUS     current
    DESCRIPTION
            "-- empty --"
    ::= { hmStatusIpRouterConnectionListEntry 9 }

-- {COLUMN} 1.3.6.1.4.1.248.32.18.1.10.23.1.10
hmStatusIpRouterConnectionListEntryDestRoute OBJECT-TYPE
    SYNTAX     DisplayString (SIZE(0..255))
    MAX-ACCESS read-only
    STATUS     current
    DESCRIPTION
            "-- empty --"
    ::= { hmStatusIpRouterConnectionListEntry 10 }

-- {COLUMN} 1.3.6.1.4.1.248.32.18.1.10.23.1.11
hmStatusIpRouterConnectionListEntryRtgTag OBJECT-TYPE
    SYNTAX     Integer32 (0..65535)
    MAX-ACCESS read-only
    STATUS     current
    DESCRIPTION
            "-- empty --"
    ::= { hmStatusIpRouterConnectionListEntry 11 }

-- {TABLE} 1.3.6.1.4.1.248.32.18.1.10.24
hmStatusIpRouterHostBlockListTable OBJECT-TYPE
    SYNTAX     SEQUENCE OF HmStatusIpRouterHostBlockListEntry
    MAX-ACCESS not-accessible
    STATUS     current
    DESCRIPTION
            "-- empty --"
    ::= { hmStatusIpRouter 24 }

-- {ROW} 1.3.6.1.4.1.248.32.18.1.10.24.1
hmStatusIpRouterHostBlockListEntry OBJECT-TYPE
    SYNTAX     HmStatusIpRouterHostBlockListEntry
    MAX-ACCESS not-accessible
    STATUS     current
    DESCRIPTION
            ""
    INDEX {
            hmStatusIpRouterHostBlockListEntrySrcAddress
          }
    ::= { hmStatusIpRouterHostBlockListTable 1 }

HmStatusIpRouterHostBlockListEntry ::= SEQUENCE {
            hmStatusIpRouterHostBlockListEntrySrcAddress IpAddress,
            hmStatusIpRouterHostBlockListEntryTimeout Integer32,
            hmStatusIpRouterHostBlockListEntryFilterRule DisplayString
    }

-- {COLUMN} 1.3.6.1.4.1.248.32.18.1.10.24.1.1
hmStatusIpRouterHostBlockListEntrySrcAddress OBJECT-TYPE
    SYNTAX     IpAddress
    MAX-ACCESS read-only
    STATUS     current
    DESCRIPTION
            "-- empty --"
    ::= { hmStatusIpRouterHostBlockListEntry 1 }

-- {COLUMN} 1.3.6.1.4.1.248.32.18.1.10.24.1.2
hmStatusIpRouterHostBlockListEntryTimeout OBJECT-TYPE
    SYNTAX     Integer32 (0..2147483647)
    MAX-ACCESS read-only
    STATUS     current
    DESCRIPTION
            "-- empty --"
    ::= { hmStatusIpRouterHostBlockListEntry 2 }

-- {COLUMN} 1.3.6.1.4.1.248.32.18.1.10.24.1.3
hmStatusIpRouterHostBlockListEntryFilterRule OBJECT-TYPE
    SYNTAX     DisplayString (SIZE(0..255))
    MAX-ACCESS read-only
    STATUS     current
    DESCRIPTION
            "-- empty --"
    ::= { hmStatusIpRouterHostBlockListEntry 3 }

-- {TABLE} 1.3.6.1.4.1.248.32.18.1.10.25
hmStatusIpRouterPortBlockListTable OBJECT-TYPE
    SYNTAX     SEQUENCE OF HmStatusIpRouterPortBlockListEntry
    MAX-ACCESS not-accessible
    STATUS     current
    DESCRIPTION
            "-- empty --"
    ::= { hmStatusIpRouter 25 }

-- {ROW} 1.3.6.1.4.1.248.32.18.1.10.25.1
hmStatusIpRouterPortBlockListEntry OBJECT-TYPE
    SYNTAX     HmStatusIpRouterPortBlockListEntry
    MAX-ACCESS not-accessible
    STATUS     current
    DESCRIPTION
            ""
    INDEX {
            hmStatusIpRouterPortBlockListEntryDstAddress
          }
    ::= { hmStatusIpRouterPortBlockListTable 1 }

HmStatusIpRouterPortBlockListEntry ::= SEQUENCE {
            hmStatusIpRouterPortBlockListEntryDstAddress IpAddress,
            hmStatusIpRouterPortBlockListEntryProt Integer32,
            hmStatusIpRouterPortBlockListEntryDstPort Integer32,
            hmStatusIpRouterPortBlockListEntryTimeout Integer32,
            hmStatusIpRouterPortBlockListEntryFilterRule DisplayString
    }

-- {COLUMN} 1.3.6.1.4.1.248.32.18.1.10.25.1.1
hmStatusIpRouterPortBlockListEntryDstAddress OBJECT-TYPE
    SYNTAX     IpAddress
    MAX-ACCESS read-only
    STATUS     current
    DESCRIPTION
            "-- empty --"
    ::= { hmStatusIpRouterPortBlockListEntry 1 }

-- {COLUMN} 1.3.6.1.4.1.248.32.18.1.10.25.1.2
hmStatusIpRouterPortBlockListEntryProt OBJECT-TYPE
    SYNTAX     Integer32 (0..65535)
    MAX-ACCESS read-only
    STATUS     current
    DESCRIPTION
            "-- empty --"
    ::= { hmStatusIpRouterPortBlockListEntry 2 }

-- {COLUMN} 1.3.6.1.4.1.248.32.18.1.10.25.1.3
hmStatusIpRouterPortBlockListEntryDstPort OBJECT-TYPE
    SYNTAX     Integer32 (0..65535)
    MAX-ACCESS read-only
    STATUS     current
    DESCRIPTION
            "-- empty --"
    ::= { hmStatusIpRouterPortBlockListEntry 3 }

-- {COLUMN} 1.3.6.1.4.1.248.32.18.1.10.25.1.4
hmStatusIpRouterPortBlockListEntryTimeout OBJECT-TYPE
    SYNTAX     Integer32 (0..2147483647)
    MAX-ACCESS read-only
    STATUS     current
    DESCRIPTION
            "-- empty --"
    ::= { hmStatusIpRouterPortBlockListEntry 4 }

-- {COLUMN} 1.3.6.1.4.1.248.32.18.1.10.25.1.5
hmStatusIpRouterPortBlockListEntryFilterRule OBJECT-TYPE
    SYNTAX     DisplayString (SIZE(0..255))
    MAX-ACCESS read-only
    STATUS     current
    DESCRIPTION
            "-- empty --"
    ::= { hmStatusIpRouterPortBlockListEntry 5 }

-- {TABLE} 1.3.6.1.4.1.248.32.18.1.10.26
hmStatusIpRouterLogTableTable OBJECT-TYPE
    SYNTAX     SEQUENCE OF HmStatusIpRouterLogTableEntry
    MAX-ACCESS not-accessible
    STATUS     current
    DESCRIPTION
            "-- empty --"
    ::= { hmStatusIpRouter 26 }

-- {ROW} 1.3.6.1.4.1.248.32.18.1.10.26.1
hmStatusIpRouterLogTableEntry OBJECT-TYPE
    SYNTAX     HmStatusIpRouterLogTableEntry
    MAX-ACCESS not-accessible
    STATUS     current
    DESCRIPTION
            ""
    INDEX {
            hmStatusIpRouterLogTableEntryIdx
          }
    ::= { hmStatusIpRouterLogTableTable 1 }

HmStatusIpRouterLogTableEntry ::= SEQUENCE {
            hmStatusIpRouterLogTableEntryIdx Integer32,
            hmStatusIpRouterLogTableEntrySystemTime DisplayString,
            hmStatusIpRouterLogTableEntrySrcAddress IpAddress,
            hmStatusIpRouterLogTableEntryDstAddress IpAddress,
            hmStatusIpRouterLogTableEntryProt Integer32,
            hmStatusIpRouterLogTableEntrySrcPort Integer32,
            hmStatusIpRouterLogTableEntryDstPort Integer32,
            hmStatusIpRouterLogTableEntryFilterRule DisplayString,
            hmStatusIpRouterLogTableEntryLimit Integer32,
            hmStatusIpRouterLogTableEntryThreshold Integer32,
            hmStatusIpRouterLogTableEntryAction Integer32
    }

-- {COLUMN} 1.3.6.1.4.1.248.32.18.1.10.26.1.1
hmStatusIpRouterLogTableEntryIdx OBJECT-TYPE
    SYNTAX     Integer32 (0..65535)
    MAX-ACCESS read-only
    STATUS     current
    DESCRIPTION
            "-- empty --"
    ::= { hmStatusIpRouterLogTableEntry 1 }

-- {COLUMN} 1.3.6.1.4.1.248.32.18.1.10.26.1.2
hmStatusIpRouterLogTableEntrySystemTime OBJECT-TYPE
    SYNTAX     DisplayString (SIZE(0..19))
    MAX-ACCESS read-only
    STATUS     current
    DESCRIPTION
            "-- empty --"
    ::= { hmStatusIpRouterLogTableEntry 2 }

-- {COLUMN} 1.3.6.1.4.1.248.32.18.1.10.26.1.3
hmStatusIpRouterLogTableEntrySrcAddress OBJECT-TYPE
    SYNTAX     IpAddress
    MAX-ACCESS read-only
    STATUS     current
    DESCRIPTION
            "-- empty --"
    ::= { hmStatusIpRouterLogTableEntry 3 }

-- {COLUMN} 1.3.6.1.4.1.248.32.18.1.10.26.1.4
hmStatusIpRouterLogTableEntryDstAddress OBJECT-TYPE
    SYNTAX     IpAddress
    MAX-ACCESS read-only
    STATUS     current
    DESCRIPTION
            "-- empty --"
    ::= { hmStatusIpRouterLogTableEntry 4 }

-- {COLUMN} 1.3.6.1.4.1.248.32.18.1.10.26.1.5
hmStatusIpRouterLogTableEntryProt OBJECT-TYPE
    SYNTAX     Integer32 (0..255)
    MAX-ACCESS read-only
    STATUS     current
    DESCRIPTION
            "-- empty --"
    ::= { hmStatusIpRouterLogTableEntry 5 }

-- {COLUMN} 1.3.6.1.4.1.248.32.18.1.10.26.1.6
hmStatusIpRouterLogTableEntrySrcPort OBJECT-TYPE
    SYNTAX     Integer32 (0..65535)
    MAX-ACCESS read-only
    STATUS     current
    DESCRIPTION
            "-- empty --"
    ::= { hmStatusIpRouterLogTableEntry 6 }

-- {COLUMN} 1.3.6.1.4.1.248.32.18.1.10.26.1.7
hmStatusIpRouterLogTableEntryDstPort OBJECT-TYPE
    SYNTAX     Integer32 (0..65535)
    MAX-ACCESS read-only
    STATUS     current
    DESCRIPTION
            "-- empty --"
    ::= { hmStatusIpRouterLogTableEntry 7 }

-- {COLUMN} 1.3.6.1.4.1.248.32.18.1.10.26.1.8
hmStatusIpRouterLogTableEntryFilterRule OBJECT-TYPE
    SYNTAX     DisplayString (SIZE(0..32))
    MAX-ACCESS read-only
    STATUS     current
    DESCRIPTION
            "-- empty --"
    ::= { hmStatusIpRouterLogTableEntry 8 }

-- {COLUMN} 1.3.6.1.4.1.248.32.18.1.10.26.1.9
hmStatusIpRouterLogTableEntryLimit OBJECT-TYPE
    SYNTAX     Integer32 (0..2147483647)
    MAX-ACCESS read-only
    STATUS     current
    DESCRIPTION
            "-- empty --"
    ::= { hmStatusIpRouterLogTableEntry 9 }

-- {COLUMN} 1.3.6.1.4.1.248.32.18.1.10.26.1.10
hmStatusIpRouterLogTableEntryThreshold OBJECT-TYPE
    SYNTAX     Integer32 (0..2147483647)
    MAX-ACCESS read-only
    STATUS     current
    DESCRIPTION
            "-- empty --"
    ::= { hmStatusIpRouterLogTableEntry 10 }

-- {COLUMN} 1.3.6.1.4.1.248.32.18.1.10.26.1.11
hmStatusIpRouterLogTableEntryAction OBJECT-TYPE
    SYNTAX     Integer32 (0..2147483647)
    MAX-ACCESS read-only
    STATUS     current
    DESCRIPTION
            "-- empty --"
    ::= { hmStatusIpRouterLogTableEntry 11 }

-- {TABLE} 1.3.6.1.4.1.248.32.18.1.10.27
hmStatusIpRouterHoConnListTable OBJECT-TYPE
    SYNTAX     SEQUENCE OF HmStatusIpRouterHoConnListEntry
    MAX-ACCESS not-accessible
    STATUS     current
    DESCRIPTION
            "-- empty --"
    ::= { hmStatusIpRouter 27 }

-- {ROW} 1.3.6.1.4.1.248.32.18.1.10.27.1
hmStatusIpRouterHoConnListEntry OBJECT-TYPE
    SYNTAX     HmStatusIpRouterHoConnListEntry
    MAX-ACCESS not-accessible
    STATUS     current
    DESCRIPTION
            ""
    INDEX {
            hmStatusIpRouterHoConnListEntryDstAddress
          }
    ::= { hmStatusIpRouterHoConnListTable 1 }

HmStatusIpRouterHoConnListEntry ::= SEQUENCE {
            hmStatusIpRouterHoConnListEntryDstAddress IpAddress,
            hmStatusIpRouterHoConnListEntryNumHoConn Integer32,
            hmStatusIpRouterHoConnListEntryTimeout Integer32
    }

-- {COLUMN} 1.3.6.1.4.1.248.32.18.1.10.27.1.1
hmStatusIpRouterHoConnListEntryDstAddress OBJECT-TYPE
    SYNTAX     IpAddress
    MAX-ACCESS read-only
    STATUS     current
    DESCRIPTION
            "-- empty --"
    ::= { hmStatusIpRouterHoConnListEntry 1 }

-- {COLUMN} 1.3.6.1.4.1.248.32.18.1.10.27.1.2
hmStatusIpRouterHoConnListEntryNumHoConn OBJECT-TYPE
    SYNTAX     Integer32 (0..2147483647)
    MAX-ACCESS read-only
    STATUS     current
    DESCRIPTION
            "-- empty --"
    ::= { hmStatusIpRouterHoConnListEntry 2 }

-- {COLUMN} 1.3.6.1.4.1.248.32.18.1.10.27.1.3
hmStatusIpRouterHoConnListEntryTimeout OBJECT-TYPE
    SYNTAX     Integer32 (0..65535)
    MAX-ACCESS read-only
    STATUS     current
    DESCRIPTION
            "-- empty --"
    ::= { hmStatusIpRouterHoConnListEntry 3 }

-- {TABLE} 1.3.6.1.4.1.248.32.18.1.10.28
hmStatusIpRouterQosTable OBJECT-TYPE
    SYNTAX     SEQUENCE OF HmStatusIpRouterQosEntry
    MAX-ACCESS not-accessible
    STATUS     current
    DESCRIPTION
            "-- empty --"
    ::= { hmStatusIpRouter 28 }

-- {ROW} 1.3.6.1.4.1.248.32.18.1.10.28.1
hmStatusIpRouterQosEntry OBJECT-TYPE
    SYNTAX     HmStatusIpRouterQosEntry
    MAX-ACCESS not-accessible
    STATUS     current
    DESCRIPTION
            ""
    INDEX {
            hmStatusIpRouterQosEntryIfc
          }
    ::= { hmStatusIpRouterQosTable 1 }

HmStatusIpRouterQosEntry ::= SEQUENCE {
            hmStatusIpRouterQosEntryIfc INTEGER,
            hmStatusIpRouterQosEntryPeer DisplayString,
            hmStatusIpRouterQosEntryDownstreamRate Integer32,
            hmStatusIpRouterQosEntryRxReserved Integer32,
            hmStatusIpRouterQosEntryRxBlocksPending Integer32,
            hmStatusIpRouterQosEntryFragmentSize Integer32,
            hmStatusIpRouterQosEntryPmtuSize Integer32,
            hmStatusIpRouterQosEntryUpstreamRate Integer32,
            hmStatusIpRouterQosEntryTxReserved Integer32,
            hmStatusIpRouterQosEntryTxBlocksPending Integer32,
            hmStatusIpRouterQosEntryRxRequested Integer32,
            hmStatusIpRouterQosEntryTxRequested Integer32,
            hmStatusIpRouterQosEntryTxFavoured Integer32
    }

-- {COLUMN} 1.3.6.1.4.1.248.32.18.1.10.28.1.1
hmStatusIpRouterQosEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusIpRouterQosEntry 1 }

-- {COLUMN} 1.3.6.1.4.1.248.32.18.1.10.28.1.2
hmStatusIpRouterQosEntryPeer OBJECT-TYPE
    SYNTAX     DisplayString (SIZE(0..16))
    MAX-ACCESS read-only
    STATUS     current
    DESCRIPTION
            "-- empty --"
    ::= { hmStatusIpRouterQosEntry 2 }

-- {COLUMN} 1.3.6.1.4.1.248.32.18.1.10.28.1.3
hmStatusIpRouterQosEntryDownstreamRate OBJECT-TYPE
    SYNTAX     Integer32 (0..2147483647)
    MAX-ACCESS read-only
    STATUS     current
    DESCRIPTION
            "-- empty --"
    ::= { hmStatusIpRouterQosEntry 3 }

-- {COLUMN} 1.3.6.1.4.1.248.32.18.1.10.28.1.4
hmStatusIpRouterQosEntryRxReserved OBJECT-TYPE
    SYNTAX     Integer32 (0..2147483647)
    MAX-ACCESS read-only
    STATUS     current
    DESCRIPTION
            "-- empty --"
    ::= { hmStatusIpRouterQosEntry 4 }

-- {COLUMN} 1.3.6.1.4.1.248.32.18.1.10.28.1.5
hmStatusIpRouterQosEntryRxBlocksPending OBJECT-TYPE
    SYNTAX     Integer32 (0..65535)
    MAX-ACCESS read-only
    STATUS     current
    DESCRIPTION
            "-- empty --"
    ::= { hmStatusIpRouterQosEntry 5 }

-- {COLUMN} 1.3.6.1.4.1.248.32.18.1.10.28.1.6
hmStatusIpRouterQosEntryFragmentSize OBJECT-TYPE
    SYNTAX     Integer32 (0..65535)
    MAX-ACCESS read-only
    STATUS     current
    DESCRIPTION
            "-- empty --"
    ::= { hmStatusIpRouterQosEntry 6 }

-- {COLUMN} 1.3.6.1.4.1.248.32.18.1.10.28.1.7
hmStatusIpRouterQosEntryPmtuSize OBJECT-TYPE
    SYNTAX     Integer32 (0..65535)
    MAX-ACCESS read-only
    STATUS     current
    DESCRIPTION
            "-- empty --"
    ::= { hmStatusIpRouterQosEntry 7 }

-- {COLUMN} 1.3.6.1.4.1.248.32.18.1.10.28.1.8
hmStatusIpRouterQosEntryUpstreamRate OBJECT-TYPE
    SYNTAX     Integer32 (0..2147483647)
    MAX-ACCESS read-only
    STATUS     current
    DESCRIPTION
            "-- empty --"
    ::= { hmStatusIpRouterQosEntry 8 }

-- {COLUMN} 1.3.6.1.4.1.248.32.18.1.10.28.1.9
hmStatusIpRouterQosEntryTxReserved OBJECT-TYPE
    SYNTAX     Integer32 (0..2147483647)
    MAX-ACCESS read-only
    STATUS     current
    DESCRIPTION
            "-- empty --"
    ::= { hmStatusIpRouterQosEntry 9 }

-- {COLUMN} 1.3.6.1.4.1.248.32.18.1.10.28.1.10
hmStatusIpRouterQosEntryTxBlocksPending OBJECT-TYPE
    SYNTAX     Integer32 (0..65535)
    MAX-ACCESS read-only
    STATUS     current
    DESCRIPTION
            "-- empty --"
    ::= { hmStatusIpRouterQosEntry 10 }

-- {COLUMN} 1.3.6.1.4.1.248.32.18.1.10.28.1.11
hmStatusIpRouterQosEntryRxRequested OBJECT-TYPE
    SYNTAX     Integer32 (0..2147483647)
    MAX-ACCESS read-only
    STATUS     current
    DESCRIPTION
            "-- empty --"
    ::= { hmStatusIpRouterQosEntry 11 }

-- {COLUMN} 1.3.6.1.4.1.248.32.18.1.10.28.1.12
hmStatusIpRouterQosEntryTxRequested OBJECT-TYPE
    SYNTAX     Integer32 (0..2147483647)
    MAX-ACCESS read-only
    STATUS     current
    DESCRIPTION
            "-- empty --"
    ::= { hmStatusIpRouterQosEntry 12 }

-- {COLUMN} 1.3.6.1.4.1.248.32.18.1.10.28.1.13
hmStatusIpRouterQosEntryTxFavoured OBJECT-TYPE
    SYNTAX     Integer32 (0..2147483647)
    MAX-ACCESS read-only
    STATUS     current
    DESCRIPTION
            "-- empty --"
    ::= { hmStatusIpRouterQosEntry 13 }

-- {TABLE} 1.3.6.1.4.1.248.32.18.1.10.29
hmStatusIpRouterOpenPortListTable OBJECT-TYPE
    SYNTAX     SEQUENCE OF HmStatusIpRouterOpenPortListEntry
    MAX-ACCESS not-accessible
    STATUS     current
    DESCRIPTION
            "-- empty --"
    ::= { hmStatusIpRouter 29 }

-- {ROW} 1.3.6.1.4.1.248.32.18.1.10.29.1
hmStatusIpRouterOpenPortListEntry OBJECT-TYPE
    SYNTAX     HmStatusIpRouterOpenPortListEntry
    MAX-ACCESS not-accessible
    STATUS     current
    DESCRIPTION
            ""
    INDEX {
            hmStatusIpRouterOpenPortListEntrySrcAddress,
            hmStatusIpRouterOpenPortListEntryDstAddress,
            hmStatusIpRouterOpenPortListEntryProt,
            hmStatusIpRouterOpenPortListEntryDstPort
          }
    ::= { hmStatusIpRouterOpenPortListTable 1 }

HmStatusIpRouterOpenPortListEntry ::= SEQUENCE {
            hmStatusIpRouterOpenPortListEntrySrcAddress IpAddress,
            hmStatusIpRouterOpenPortListEntryDstAddress IpAddress,
            hmStatusIpRouterOpenPortListEntryProt Integer32,
            hmStatusIpRouterOpenPortListEntryDstPort Integer32,
            hmStatusIpRouterOpenPortListEntryTimeout Integer32,
            hmStatusIpRouterOpenPortListEntryFilterRule DisplayString,
            hmStatusIpRouterOpenPortListEntrySrcRoute DisplayString
    }

-- {COLUMN} 1.3.6.1.4.1.248.32.18.1.10.29.1.1
hmStatusIpRouterOpenPortListEntrySrcAddress OBJECT-TYPE
    SYNTAX     IpAddress
    MAX-ACCESS read-only
    STATUS     current
    DESCRIPTION
            "-- empty --"
    ::= { hmStatusIpRouterOpenPortListEntry 1 }

-- {COLUMN} 1.3.6.1.4.1.248.32.18.1.10.29.1.2
hmStatusIpRouterOpenPortListEntryDstAddress OBJECT-TYPE
    SYNTAX     IpAddress
    MAX-ACCESS read-only
    STATUS     current
    DESCRIPTION
            "-- empty --"
    ::= { hmStatusIpRouterOpenPortListEntry 2 }

-- {COLUMN} 1.3.6.1.4.1.248.32.18.1.10.29.1.3
hmStatusIpRouterOpenPortListEntryProt OBJECT-TYPE
    SYNTAX     Integer32 (0..255)
    MAX-ACCESS read-only
    STATUS     current
    DESCRIPTION
            "-- empty --"
    ::= { hmStatusIpRouterOpenPortListEntry 3 }

-- {COLUMN} 1.3.6.1.4.1.248.32.18.1.10.29.1.5
hmStatusIpRouterOpenPortListEntryDstPort OBJECT-TYPE
    SYNTAX     Integer32 (0..65535)
    MAX-ACCESS read-only
    STATUS     current
    DESCRIPTION
            "-- empty --"
    ::= { hmStatusIpRouterOpenPortListEntry 5 }

-- {COLUMN} 1.3.6.1.4.1.248.32.18.1.10.29.1.6
hmStatusIpRouterOpenPortListEntryTimeout OBJECT-TYPE
    SYNTAX     Integer32 (0..65535)
    MAX-ACCESS read-only
    STATUS     current
    DESCRIPTION
            "-- empty --"
    ::= { hmStatusIpRouterOpenPortListEntry 6 }

-- {COLUMN} 1.3.6.1.4.1.248.32.18.1.10.29.1.8
hmStatusIpRouterOpenPortListEntryFilterRule OBJECT-TYPE
    SYNTAX     DisplayString (SIZE(0..255))
    MAX-ACCESS read-only
    STATUS     current
    DESCRIPTION
            "-- empty --"
    ::= { hmStatusIpRouterOpenPortListEntry 8 }

-- {COLUMN} 1.3.6.1.4.1.248.32.18.1.10.29.1.9
hmStatusIpRouterOpenPortListEntrySrcRoute OBJECT-TYPE
    SYNTAX     DisplayString (SIZE(0..255))
    MAX-ACCESS read-only
    STATUS     current
    DESCRIPTION
            "-- empty --"
    ::= { hmStatusIpRouterOpenPortListEntry 9 }

-- {TABLE} 1.3.6.1.4.1.248.32.18.1.10.30
hmStatusIpRouterActIpRoutingTabTable OBJECT-TYPE
    SYNTAX     SEQUENCE OF HmStatusIpRouterActIpRoutingTabEntry
    MAX-ACCESS not-accessible
    STATUS     current
    DESCRIPTION
            "-- empty --"
    ::= { hmStatusIpRouter 30 }

-- {ROW} 1.3.6.1.4.1.248.32.18.1.10.30.1
hmStatusIpRouterActIpRoutingTabEntry OBJECT-TYPE
    SYNTAX     HmStatusIpRouterActIpRoutingTabEntry
    MAX-ACCESS not-accessible
    STATUS     current
    DESCRIPTION
            ""
    INDEX {
            hmStatusIpRouterActIpRoutingTabEntryIpAddress,
            hmStatusIpRouterActIpRoutingTabEntryIpNetmask,
            hmStatusIpRouterActIpRoutingTabEntryRtgTag
          }
    ::= { hmStatusIpRouterActIpRoutingTabTable 1 }

HmStatusIpRouterActIpRoutingTabEntry ::= SEQUENCE {
            hmStatusIpRouterActIpRoutingTabEntryIpAddress IpAddress,
            hmStatusIpRouterActIpRoutingTabEntryIpNetmask IpAddress,
            hmStatusIpRouterActIpRoutingTabEntryRtgTag Integer32,
            hmStatusIpRouterActIpRoutingTabEntryGateway IpAddress,
            hmStatusIpRouterActIpRoutingTabEntryPeer DisplayString,
            hmStatusIpRouterActIpRoutingTabEntryDistance Integer32,
            hmStatusIpRouterActIpRoutingTabEntryMasquerade INTEGER,
            hmStatusIpRouterActIpRoutingTabEntryType INTEGER
    }

-- {COLUMN} 1.3.6.1.4.1.248.32.18.1.10.30.1.1
hmStatusIpRouterActIpRoutingTabEntryIpAddress OBJECT-TYPE
    SYNTAX     IpAddress
    MAX-ACCESS read-only
    STATUS     current
    DESCRIPTION
            "-- empty --"
    ::= { hmStatusIpRouterActIpRoutingTabEntry 1 }

-- {COLUMN} 1.3.6.1.4.1.248.32.18.1.10.30.1.2
hmStatusIpRouterActIpRoutingTabEntryIpNetmask OBJECT-TYPE
    SYNTAX     IpAddress
    MAX-ACCESS read-only
    STATUS     current
    DESCRIPTION
            "-- empty --"
    ::= { hmStatusIpRouterActIpRoutingTabEntry 2 }

-- {COLUMN} 1.3.6.1.4.1.248.32.18.1.10.30.1.3
hmStatusIpRouterActIpRoutingTabEntryRtgTag OBJECT-TYPE
    SYNTAX     Integer32 (0..65535)
    MAX-ACCESS read-only
    STATUS     current
    DESCRIPTION
            "-- empty --"
    ::= { hmStatusIpRouterActIpRoutingTabEntry 3 }

-- {COLUMN} 1.3.6.1.4.1.248.32.18.1.10.30.1.4
hmStatusIpRouterActIpRoutingTabEntryGateway OBJECT-TYPE
    SYNTAX     IpAddress
    MAX-ACCESS read-only
    STATUS     current
    DESCRIPTION
            "-- empty --"
    ::= { hmStatusIpRouterActIpRoutingTabEntry 4 }

-- {COLUMN} 1.3.6.1.4.1.248.32.18.1.10.30.1.5
hmStatusIpRouterActIpRoutingTabEntryPeer OBJECT-TYPE
    SYNTAX     DisplayString (SIZE(0..255))
    MAX-ACCESS read-only
    STATUS     current
    DESCRIPTION
            "-- empty --"
    ::= { hmStatusIpRouterActIpRoutingTabEntry 5 }

-- {COLUMN} 1.3.6.1.4.1.248.32.18.1.10.30.1.6
hmStatusIpRouterActIpRoutingTabEntryDistance OBJECT-TYPE
    SYNTAX     Integer32 (0..255)
    MAX-ACCESS read-only
    STATUS     current
    DESCRIPTION
            "-- empty --"
    ::= { hmStatusIpRouterActIpRoutingTabEntry 6 }

-- {COLUMN} 1.3.6.1.4.1.248.32.18.1.10.30.1.7
hmStatusIpRouterActIpRoutingTabEntryMasquerade OBJECT-TYPE
    SYNTAX     INTEGER {
                  eNo (0),
                  eOn (1),
                  eIntranet (2),
                  eUnknown (255)
            }
    MAX-ACCESS read-only
    STATUS     current
    DESCRIPTION
            "-- empty --"
    ::= { hmStatusIpRouterActIpRoutingTabEntry 7 }

-- {COLUMN} 1.3.6.1.4.1.248.32.18.1.10.30.1.8
hmStatusIpRouterActIpRoutingTabEntryType OBJECT-TYPE
    SYNTAX     INTEGER {
                  eUnknown (0),
                  eStatic (1),
                  eRip (2),
                  eVpn (3),
                  eCapwap (4),
                  eRas (5),
                  eIntranet (6),
                  eDmz (7),
                  eDisabled (8)
            }
    MAX-ACCESS read-only
    STATUS     current
    DESCRIPTION
            "-- empty --"
    ::= { hmStatusIpRouterActIpRoutingTabEntry 8 }

-- {SCALAR} 1.3.6.1.4.1.248.32.18.1.10.31
hmStatusIpRouterL4Errors OBJECT-TYPE
    SYNTAX     Counter32
    MAX-ACCESS read-only
    STATUS     current
    DESCRIPTION
            "-- empty --"
    ::= { hmStatusIpRouter 31 }

-- {NODE} 1.3.6.1.4.1.248.32.18.1.10.32
hmStatusIpRouterLoadBalancer OBJECT IDENTIFIER ::= { hmStatusIpRouter 32 }

-- {SCALAR} 1.3.6.1.4.1.248.32.18.1.10.32.1
hmStatusIpRouterLoadBalancerOperating OBJECT-TYPE
    SYNTAX     INTEGER {
                  eNo (0),
                  eYes (1)
            }
    MAX-ACCESS read-only
    STATUS     current
    DESCRIPTION
            "-- empty --"
    ::= { hmStatusIpRouterLoadBalancer 1 }

-- {TABLE} 1.3.6.1.4.1.248.32.18.1.10.32.2
hmStatusIpRouterLoadBalancerConnectionsTable OBJECT-TYPE
    SYNTAX     SEQUENCE OF HmStatusIpRouterLoadBalancerConnectionsEntry
    MAX-ACCESS not-accessible
    STATUS     current
    DESCRIPTION
            "-- empty --"
    ::= { hmStatusIpRouterLoadBalancer 2 }

-- {ROW} 1.3.6.1.4.1.248.32.18.1.10.32.2.1
hmStatusIpRouterLoadBalancerConnectionsEntry OBJECT-TYPE
    SYNTAX     HmStatusIpRouterLoadBalancerConnectionsEntry
    MAX-ACCESS not-accessible
    STATUS     current
    DESCRIPTION
            ""
    INDEX {
            hmStatusIpRouterLoadBalancerConnectionsEntryPeer,
            hmStatusIpRouterLoadBalancerConnectionsEntryBundlePeer
          }
    ::= { hmStatusIpRouterLoadBalancerConnectionsTable 1 }

HmStatusIpRouterLoadBalancerConnectionsEntry ::= SEQUENCE {
            hmStatusIpRouterLoadBalancerConnectionsEntryPeer DisplayString,
            hmStatusIpRouterLoadBalancerConnectionsEntryBundlePeer DisplayString,
            hmStatusIpRouterLoadBalancerConnectionsEntryState INTEGER,
            hmStatusIpRouterLoadBalancerConnectionsEntryTcpIpSessions Integer32,
            hmStatusIpRouterLoadBalancerConnectionsEntryPptpSessions Integer32,
            hmStatusIpRouterLoadBalancerConnectionsEntryVpnSessions Integer32
    }

-- {COLUMN} 1.3.6.1.4.1.248.32.18.1.10.32.2.1.1
hmStatusIpRouterLoadBalancerConnectionsEntryPeer OBJECT-TYPE
    SYNTAX     DisplayString (SIZE(0..16))
    MAX-ACCESS read-only
    STATUS     current
    DESCRIPTION
            "-- empty --"
    ::= { hmStatusIpRouterLoadBalancerConnectionsEntry 1 }

-- {COLUMN} 1.3.6.1.4.1.248.32.18.1.10.32.2.1.2
hmStatusIpRouterLoadBalancerConnectionsEntryBundlePeer OBJECT-TYPE
    SYNTAX     DisplayString (SIZE(0..16))
    MAX-ACCESS read-only
    STATUS     current
    DESCRIPTION
            "-- empty --"
    ::= { hmStatusIpRouterLoadBalancerConnectionsEntry 2 }

-- {COLUMN} 1.3.6.1.4.1.248.32.18.1.10.32.2.1.3
hmStatusIpRouterLoadBalancerConnectionsEntryState OBJECT-TYPE
    SYNTAX     INTEGER {
                  eReady (2),
                  eConnection (7),
                  eDisconnecting (8)
            }
    MAX-ACCESS read-only
    STATUS     current
    DESCRIPTION
            "-- empty --"
    ::= { hmStatusIpRouterLoadBalancerConnectionsEntry 3 }

-- {COLUMN} 1.3.6.1.4.1.248.32.18.1.10.32.2.1.4
hmStatusIpRouterLoadBalancerConnectionsEntryTcpIpSessions OBJECT-TYPE
    SYNTAX     Integer32 (0..2147483647)
    MAX-ACCESS read-only
    STATUS     current
    DESCRIPTION
            "-- empty --"
    ::= { hmStatusIpRouterLoadBalancerConnectionsEntry 4 }

-- {COLUMN} 1.3.6.1.4.1.248.32.18.1.10.32.2.1.5
hmStatusIpRouterLoadBalancerConnectionsEntryPptpSessions OBJECT-TYPE
    SYNTAX     Integer32 (0..2147483647)
    MAX-ACCESS read-only
    STATUS     current
    DESCRIPTION
            "-- empty --"
    ::= { hmStatusIpRouterLoadBalancerConnectionsEntry 5 }

-- {COLUMN} 1.3.6.1.4.1.248.32.18.1.10.32.2.1.6
hmStatusIpRouterLoadBalancerConnectionsEntryVpnSessions OBJECT-TYPE
    SYNTAX     Integer32 (0..2147483647)
    MAX-ACCESS read-only
    STATUS     current
    DESCRIPTION
            "-- empty --"
    ::= { hmStatusIpRouterLoadBalancerConnectionsEntry 6 }

-- {SCALAR} 1.3.6.1.4.1.248.32.18.1.10.32.3
hmStatusIpRouterLoadBalancerClientBinding OBJECT-TYPE
    SYNTAX     Integer32 (0..2147483647)
    MAX-ACCESS read-only
    STATUS     current
    DESCRIPTION
            "-- empty --"
    ::= { hmStatusIpRouterLoadBalancer 3 }

-- {NODE} 1.3.6.1.4.1.248.32.18.1.10.33
hmStatusIpRouterVrrp OBJECT IDENTIFIER ::= { hmStatusIpRouter 33 }

-- {SCALAR} 1.3.6.1.4.1.248.32.18.1.10.33.1
hmStatusIpRouterVrrpRx OBJECT-TYPE
    SYNTAX     Counter32
    MAX-ACCESS read-only
    STATUS     current
    DESCRIPTION
            "-- empty --"
    ::= { hmStatusIpRouterVrrp 1 }

-- {SCALAR} 1.3.6.1.4.1.248.32.18.1.10.33.2
hmStatusIpRouterVrrpTx OBJECT-TYPE
    SYNTAX     Counter32
    MAX-ACCESS read-only
    STATUS     current
    DESCRIPTION
            "-- empty --"
    ::= { hmStatusIpRouterVrrp 2 }

-- {SCALAR} 1.3.6.1.4.1.248.32.18.1.10.33.3
hmStatusIpRouterVrrpError OBJECT-TYPE
    SYNTAX     Counter32
    MAX-ACCESS read-only
    STATUS     current
    DESCRIPTION
            "-- empty --"
    ::= { hmStatusIpRouterVrrp 3 }

-- {SCALAR} 1.3.6.1.4.1.248.32.18.1.10.33.4
hmStatusIpRouterVrrpDrop OBJECT-TYPE
    SYNTAX     Counter32
    MAX-ACCESS read-only
    STATUS     current
    DESCRIPTION
            "-- empty --"
    ::= { hmStatusIpRouterVrrp 4 }

-- {SCALAR} 1.3.6.1.4.1.248.32.18.1.10.33.5
hmStatusIpRouterVrrpOperating OBJECT-TYPE
    SYNTAX     INTEGER {
                  eNo (0),
                  eYes (1)
            }
    MAX-ACCESS read-only
    STATUS     current
    DESCRIPTION
            "-- empty --"
    ::= { hmStatusIpRouterVrrp 5 }

-- {SCALAR} 1.3.6.1.4.1.248.32.18.1.10.33.6
hmStatusIpRouterVrrpInternalServices OBJECT-TYPE
    SYNTAX     INTEGER {
                  eNo (0),
                  eYes (1)
            }
    MAX-ACCESS read-only
    STATUS     current
    DESCRIPTION
            "-- empty --"
    ::= { hmStatusIpRouterVrrp 6 }

-- {SCALAR} 1.3.6.1.4.1.248.32.18.1.10.33.7
hmStatusIpRouterVrrpQueueErrors OBJECT-TYPE
    SYNTAX     Counter32
    MAX-ACCESS read-only
    STATUS     current
    DESCRIPTION
            "-- empty --"
    ::= { hmStatusIpRouterVrrp 7 }

-- {TABLE} 1.3.6.1.4.1.248.32.18.1.10.33.10
hmStatusIpRouterVrrpVirtualRouterTable OBJECT-TYPE
    SYNTAX     SEQUENCE OF HmStatusIpRouterVrrpVirtualRouterEntry
    MAX-ACCESS not-accessible
    STATUS     current
    DESCRIPTION
            "-- empty --"
    ::= { hmStatusIpRouterVrrp 10 }

-- {ROW} 1.3.6.1.4.1.248.32.18.1.10.33.10.1
hmStatusIpRouterVrrpVirtualRouterEntry OBJECT-TYPE
    SYNTAX     HmStatusIpRouterVrrpVirtualRouterEntry
    MAX-ACCESS not-accessible
    STATUS     current
    DESCRIPTION
            ""
    INDEX {
            hmStatusIpRouterVrrpVirtualRouterEntryRouterId
          }
    ::= { hmStatusIpRouterVrrpVirtualRouterTable 1 }

HmStatusIpRouterVrrpVirtualRouterEntry ::= SEQUENCE {
            hmStatusIpRouterVrrpVirtualRouterEntryRouterId Integer32,
            hmStatusIpRouterVrrpVirtualRouterEntryVirtAddress IpAddress,
            hmStatusIpRouterVrrpVirtualRouterEntryPrio Integer32,
            hmStatusIpRouterVrrpVirtualRouterEntryBPrio Integer32,
            hmStatusIpRouterVrrpVirtualRouterEntryPeer DisplayString,
            hmStatusIpRouterVrrpVirtualRouterEntryState INTEGER,
            hmStatusIpRouterVrrpVirtualRouterEntryBackup INTEGER,
            hmStatusIpRouterVrrpVirtualRouterEntryMaster IpAddress,
            hmStatusIpRouterVrrpVirtualRouterEntryVlanId Integer32,
            hmStatusIpRouterVrrpVirtualRouterEntryNetworkName DisplayString,
            hmStatusIpRouterVrrpVirtualRouterEntryPort INTEGER
    }

-- {COLUMN} 1.3.6.1.4.1.248.32.18.1.10.33.10.1.1
hmStatusIpRouterVrrpVirtualRouterEntryRouterId OBJECT-TYPE
    SYNTAX     Integer32 (0..255)
    MAX-ACCESS read-only
    STATUS     current
    DESCRIPTION
            "-- empty --"
    ::= { hmStatusIpRouterVrrpVirtualRouterEntry 1 }

-- {COLUMN} 1.3.6.1.4.1.248.32.18.1.10.33.10.1.2
hmStatusIpRouterVrrpVirtualRouterEntryVirtAddress OBJECT-TYPE
    SYNTAX     IpAddress
    MAX-ACCESS read-only
    STATUS     current
    DESCRIPTION
            "-- empty --"
    ::= { hmStatusIpRouterVrrpVirtualRouterEntry 2 }

-- {COLUMN} 1.3.6.1.4.1.248.32.18.1.10.33.10.1.3
hmStatusIpRouterVrrpVirtualRouterEntryPrio OBJECT-TYPE
    SYNTAX     Integer32 (0..255)
    MAX-ACCESS read-only
    STATUS     current
    DESCRIPTION
            "-- empty --"
    ::= { hmStatusIpRouterVrrpVirtualRouterEntry 3 }

-- {COLUMN} 1.3.6.1.4.1.248.32.18.1.10.33.10.1.4
hmStatusIpRouterVrrpVirtualRouterEntryBPrio OBJECT-TYPE
    SYNTAX     Integer32 (0..255)
    MAX-ACCESS read-only
    STATUS     current
    DESCRIPTION
            "-- empty --"
    ::= { hmStatusIpRouterVrrpVirtualRouterEntry 4 }

-- {COLUMN} 1.3.6.1.4.1.248.32.18.1.10.33.10.1.5
hmStatusIpRouterVrrpVirtualRouterEntryPeer OBJECT-TYPE
    SYNTAX     DisplayString (SIZE(0..16))
    MAX-ACCESS read-only
    STATUS     current
    DESCRIPTION
            "-- empty --"
    ::= { hmStatusIpRouterVrrpVirtualRouterEntry 5 }

-- {COLUMN} 1.3.6.1.4.1.248.32.18.1.10.33.10.1.6
hmStatusIpRouterVrrpVirtualRouterEntryState OBJECT-TYPE
    SYNTAX     INTEGER {
                  eInit (0),
                  eListen (1),
                  eStandby (2),
                  eMaster (3),
                  eDown (4),
                  eReconnect (5)
            }
    MAX-ACCESS read-only
    STATUS     current
    DESCRIPTION
            "-- empty --"
    ::= { hmStatusIpRouterVrrpVirtualRouterEntry 6 }

-- {COLUMN} 1.3.6.1.4.1.248.32.18.1.10.33.10.1.7
hmStatusIpRouterVrrpVirtualRouterEntryBackup OBJECT-TYPE
    SYNTAX     INTEGER {
                  eNo (0),
                  eYes (1)
            }
    MAX-ACCESS read-only
    STATUS     current
    DESCRIPTION
            "-- empty --"
    ::= { hmStatusIpRouterVrrpVirtualRouterEntry 7 }

-- {COLUMN} 1.3.6.1.4.1.248.32.18.1.10.33.10.1.8
hmStatusIpRouterVrrpVirtualRouterEntryMaster OBJECT-TYPE
    SYNTAX     IpAddress
    MAX-ACCESS read-only
    STATUS     current
    DESCRIPTION
            "-- empty --"
    ::= { hmStatusIpRouterVrrpVirtualRouterEntry 8 }

-- {COLUMN} 1.3.6.1.4.1.248.32.18.1.10.33.10.1.10
hmStatusIpRouterVrrpVirtualRouterEntryVlanId OBJECT-TYPE
    SYNTAX     Integer32 (0..65535)
    MAX-ACCESS read-only
    STATUS     current
    DESCRIPTION
            "-- empty --"
    ::= { hmStatusIpRouterVrrpVirtualRouterEntry 10 }

-- {COLUMN} 1.3.6.1.4.1.248.32.18.1.10.33.10.1.11
hmStatusIpRouterVrrpVirtualRouterEntryNetworkName OBJECT-TYPE
    SYNTAX     DisplayString (SIZE(0..16))
    MAX-ACCESS read-only
    STATUS     current
    DESCRIPTION
            "-- empty --"
    ::= { hmStatusIpRouterVrrpVirtualRouterEntry 11 }

-- {COLUMN} 1.3.6.1.4.1.248.32.18.1.10.33.10.1.12
hmStatusIpRouterVrrpVirtualRouterEntryPort OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eAny (65535)
            }
    MAX-ACCESS read-only
    STATUS     current
    DESCRIPTION
            "-- empty --"
    ::= { hmStatusIpRouterVrrpVirtualRouterEntry 12 }

-- {TABLE} 1.3.6.1.4.1.248.32.18.1.10.33.11
hmStatusIpRouterVrrpMacListTable OBJECT-TYPE
    SYNTAX     SEQUENCE OF HmStatusIpRouterVrrpMacListEntry
    MAX-ACCESS not-accessible
    STATUS     current
    DESCRIPTION
            "-- empty --"
    ::= { hmStatusIpRouterVrrp 11 }

-- {ROW} 1.3.6.1.4.1.248.32.18.1.10.33.11.1
hmStatusIpRouterVrrpMacListEntry OBJECT-TYPE
    SYNTAX     HmStatusIpRouterVrrpMacListEntry
    MAX-ACCESS not-accessible
    STATUS     current
    DESCRIPTION
            ""
    INDEX {
            hmStatusIpRouterVrrpMacListEntryVirtAddress
          }
    ::= { hmStatusIpRouterVrrpMacListTable 1 }

HmStatusIpRouterVrrpMacListEntry ::= SEQUENCE {
            hmStatusIpRouterVrrpMacListEntryVirtAddress IpAddress,
            hmStatusIpRouterVrrpMacListEntryMacAddress MacAddress,
            hmStatusIpRouterVrrpMacListEntryRouterId Integer32
    }

-- {COLUMN} 1.3.6.1.4.1.248.32.18.1.10.33.11.1.1
hmStatusIpRouterVrrpMacListEntryVirtAddress OBJECT-TYPE
    SYNTAX     IpAddress
    MAX-ACCESS read-only
    STATUS     current
    DESCRIPTION
            "-- empty --"
    ::= { hmStatusIpRouterVrrpMacListEntry 1 }

-- {COLUMN} 1.3.6.1.4.1.248.32.18.1.10.33.11.1.2
hmStatusIpRouterVrrpMacListEntryMacAddress OBJECT-TYPE
    SYNTAX     MacAddress
    MAX-ACCESS read-only
    STATUS     current
    DESCRIPTION
            "-- empty --"
    ::= { hmStatusIpRouterVrrpMacListEntry 2 }

-- {COLUMN} 1.3.6.1.4.1.248.32.18.1.10.33.11.1.3
hmStatusIpRouterVrrpMacListEntryRouterId OBJECT-TYPE
    SYNTAX     Integer32 (0..255)
    MAX-ACCESS read-only
    STATUS     current
    DESCRIPTION
            "-- empty --"
    ::= { hmStatusIpRouterVrrpMacListEntry 3 }

-- {TABLE} 1.3.6.1.4.1.248.32.18.1.10.33.12
hmStatusIpRouterVrrpEventLogTable OBJECT-TYPE
    SYNTAX     SEQUENCE OF HmStatusIpRouterVrrpEventLogEntry
    MAX-ACCESS not-accessible
    STATUS     current
    DESCRIPTION
            "-- empty --"
    ::= { hmStatusIpRouterVrrp 12 }

-- {ROW} 1.3.6.1.4.1.248.32.18.1.10.33.12.1
hmStatusIpRouterVrrpEventLogEntry OBJECT-TYPE
    SYNTAX     HmStatusIpRouterVrrpEventLogEntry
    MAX-ACCESS not-accessible
    STATUS     current
    DESCRIPTION
            ""
    INDEX {
            hmStatusIpRouterVrrpEventLogEntryIdx
          }
    ::= { hmStatusIpRouterVrrpEventLogTable 1 }

HmStatusIpRouterVrrpEventLogEntry ::= SEQUENCE {
            hmStatusIpRouterVrrpEventLogEntryIdx Integer32,
            hmStatusIpRouterVrrpEventLogEntrySystemTime DisplayString,
            hmStatusIpRouterVrrpEventLogEntrySrcAddress IpAddress,
            hmStatusIpRouterVrrpEventLogEntryVrid Integer32,
            hmStatusIpRouterVrrpEventLogEntryEvent INTEGER,
            hmStatusIpRouterVrrpEventLogEntryInfo DisplayString
    }

-- {COLUMN} 1.3.6.1.4.1.248.32.18.1.10.33.12.1.1
hmStatusIpRouterVrrpEventLogEntryIdx OBJECT-TYPE
    SYNTAX     Integer32 (0..65535)
    MAX-ACCESS read-only
    STATUS     current
    DESCRIPTION
            "-- empty --"
    ::= { hmStatusIpRouterVrrpEventLogEntry 1 }

-- {COLUMN} 1.3.6.1.4.1.248.32.18.1.10.33.12.1.2
hmStatusIpRouterVrrpEventLogEntrySystemTime OBJECT-TYPE
    SYNTAX     DisplayString (SIZE(0..19))
    MAX-ACCESS read-only
    STATUS     current
    DESCRIPTION
            "-- empty --"
    ::= { hmStatusIpRouterVrrpEventLogEntry 2 }

-- {COLUMN} 1.3.6.1.4.1.248.32.18.1.10.33.12.1.3
hmStatusIpRouterVrrpEventLogEntrySrcAddress OBJECT-TYPE
    SYNTAX     IpAddress
    MAX-ACCESS read-only
    STATUS     current
    DESCRIPTION
            "-- empty --"
    ::= { hmStatusIpRouterVrrpEventLogEntry 3 }

-- {COLUMN} 1.3.6.1.4.1.248.32.18.1.10.33.12.1.4
hmStatusIpRouterVrrpEventLogEntryVrid OBJECT-TYPE
    SYNTAX     Integer32 (0..255)
    MAX-ACCESS read-only
    STATUS     current
    DESCRIPTION
            "-- empty --"
    ::= { hmStatusIpRouterVrrpEventLogEntry 4 }

-- {COLUMN} 1.3.6.1.4.1.248.32.18.1.10.33.12.1.5
hmStatusIpRouterVrrpEventLogEntryEvent OBJECT-TYPE
    SYNTAX     INTEGER {
                  eInvalidTtl (1),
                  eInvalidVersion (2),
                  eBadNumberOfVirtualAddresses (3),
                  eBadAuthenticationType (4),
                  eBadAdvertisementInterval (5),
                  eInvalidVrid (6),
                  eInvalidRouterAddress (7),
                  eInvalidPriority (8),
                  eVirtualRouterStopped (9),
                  eVirtualRouterStarted (10),
                  eLinkUp (11),
                  eLinkDown (12),
                  eNewMaster (13),
                  eBackupStarted (14),
                  eBackupEnded (15)
            }
    MAX-ACCESS read-only
    STATUS     current
    DESCRIPTION
            "-- empty --"
    ::= { hmStatusIpRouterVrrpEventLogEntry 5 }

-- {COLUMN} 1.3.6.1.4.1.248.32.18.1.10.33.12.1.6
hmStatusIpRouterVrrpEventLogEntryInfo OBJECT-TYPE
    SYNTAX     DisplayString (SIZE(0..255))
    MAX-ACCESS read-only
    STATUS     current
    DESCRIPTION
            "-- empty --"
    ::= { hmStatusIpRouterVrrpEventLogEntry 6 }

-- {SCALAR} 1.3.6.1.4.1.248.32.18.1.10.33.20
hmStatusIpRouterVrrpDeleteValues OBJECT-TYPE
    SYNTAX     DisplayString
    MAX-ACCESS read-write
    STATUS     current
    DESCRIPTION
            "-- empty --"
    ::= { hmStatusIpRouterVrrp 20 }

-- {SCALAR} 1.3.6.1.4.1.248.32.18.1.10.34
hmStatusIpRouterRules OBJECT-TYPE
    SYNTAX     Integer32 (0..2147483647)
    MAX-ACCESS read-only
    STATUS     current
    DESCRIPTION
            "-- empty --"
    ::= { hmStatusIpRouter 34 }

-- {SCALAR} 1.3.6.1.4.1.248.32.18.1.10.35
hmStatusIpRouterFilter OBJECT-TYPE
    SYNTAX     Integer32 (0..2147483647)
    MAX-ACCESS read-only
    STATUS     current
    DESCRIPTION
            "-- empty --"
    ::= { hmStatusIpRouter 35 }

-- {NODE} 1.3.6.1.4.1.248.32.18.1.11
hmStatusConfig OBJECT IDENTIFIER ::= { hmStatus 11 }

-- {SCALAR} 1.3.6.1.4.1.248.32.18.1.11.1
hmStatusConfigLanActiveConnections OBJECT-TYPE
    SYNTAX     Integer32 (0..65535)
    MAX-ACCESS read-only
    STATUS     current
    DESCRIPTION
            "-- empty --"
    ::= { hmStatusConfig 1 }

-- {SCALAR} 1.3.6.1.4.1.248.32.18.1.11.2
hmStatusConfigLanTotalConnections OBJECT-TYPE
    SYNTAX     Counter32
    MAX-ACCESS read-only
    STATUS     current
    DESCRIPTION
            "-- empty --"
    ::= { hmStatusConfig 2 }

-- {SCALAR} 1.3.6.1.4.1.248.32.18.1.11.3
hmStatusConfigWanActiveConnections OBJECT-TYPE
    SYNTAX     Integer32 (0..65535)
    MAX-ACCESS read-only
    STATUS     current
    DESCRIPTION
            "-- empty --"
    ::= { hmStatusConfig 3 }

-- {SCALAR} 1.3.6.1.4.1.248.32.18.1.11.4
hmStatusConfigWanTotalConnections OBJECT-TYPE
    SYNTAX     Counter32
    MAX-ACCESS read-only
    STATUS     current
    DESCRIPTION
            "-- empty --"
    ::= { hmStatusConfig 4 }

-- {SCALAR} 1.3.6.1.4.1.248.32.18.1.11.5
hmStatusConfigOutbandActiveConnections OBJECT-TYPE
    SYNTAX     Integer32 (0..65535)
    MAX-ACCESS read-only
    STATUS     current
    DESCRIPTION
            "-- empty --"
    ::= { hmStatusConfig 5 }

-- {SCALAR} 1.3.6.1.4.1.248.32.18.1.11.6
hmStatusConfigOutbandTotalConnections OBJECT-TYPE
    SYNTAX     Counter32
    MAX-ACCESS read-only
    STATUS     current
    DESCRIPTION
            "-- empty --"
    ::= { hmStatusConfig 6 }

-- {SCALAR} 1.3.6.1.4.1.248.32.18.1.11.7
hmStatusConfigOutbandBitrate OBJECT-TYPE
    SYNTAX     Integer32 (0..2147483647)
    MAX-ACCESS read-only
    STATUS     current
    DESCRIPTION
            "-- empty --"
    ::= { hmStatusConfig 7 }

-- {SCALAR} 1.3.6.1.4.1.248.32.18.1.11.8
hmStatusConfigLoginErrors OBJECT-TYPE
    SYNTAX     Counter32
    MAX-ACCESS read-only
    STATUS     current
    DESCRIPTION
            "-- empty --"
    ::= { hmStatusConfig 8 }

-- {SCALAR} 1.3.6.1.4.1.248.32.18.1.11.9
hmStatusConfigLoginLocks OBJECT-TYPE
    SYNTAX     Counter32
    MAX-ACCESS read-only
    STATUS     current
    DESCRIPTION
            "-- empty --"
    ::= { hmStatusConfig 9 }

-- {SCALAR} 1.3.6.1.4.1.248.32.18.1.11.10
hmStatusConfigLoginRejects OBJECT-TYPE
    SYNTAX     Counter32
    MAX-ACCESS read-only
    STATUS     current
    DESCRIPTION
            "-- empty --"
    ::= { hmStatusConfig 10 }

-- {SCALAR} 1.3.6.1.4.1.248.32.18.1.11.11
hmStatusConfigDeleteValues OBJECT-TYPE
    SYNTAX     DisplayString
    MAX-ACCESS read-write
    STATUS     current
    DESCRIPTION
            "-- empty --"
    ::= { hmStatusConfig 11 }

-- {TABLE} 1.3.6.1.4.1.248.32.18.1.11.12
hmStatusConfigEventLogTable OBJECT-TYPE
    SYNTAX     SEQUENCE OF HmStatusConfigEventLogEntry
    MAX-ACCESS not-accessible
    STATUS     current
    DESCRIPTION
            "-- empty --"
    ::= { hmStatusConfig 12 }

-- {ROW} 1.3.6.1.4.1.248.32.18.1.11.12.1
hmStatusConfigEventLogEntry OBJECT-TYPE
    SYNTAX     HmStatusConfigEventLogEntry
    MAX-ACCESS not-accessible
    STATUS     current
    DESCRIPTION
            ""
    INDEX {
            hmStatusConfigEventLogEntryIdx
          }
    ::= { hmStatusConfigEventLogTable 1 }

HmStatusConfigEventLogEntry ::= SEQUENCE {
            hmStatusConfigEventLogEntryIdx Integer32,
            hmStatusConfigEventLogEntryEvent INTEGER,
            hmStatusConfigEventLogEntryAccess INTEGER,
            hmStatusConfigEventLogEntryIpAddress IpAddress,
            hmStatusConfigEventLogEntryInfo1 DisplayString,
            hmStatusConfigEventLogEntryInfo2 DisplayString,
            hmStatusConfigEventLogEntrySystemTime DisplayString,
            hmStatusConfigEventLogEntryIpAddressNew DisplayString,
            hmStatusConfigEventLogEntryInfo3 DisplayString
    }

-- {COLUMN} 1.3.6.1.4.1.248.32.18.1.11.12.1.1
hmStatusConfigEventLogEntryIdx OBJECT-TYPE
    SYNTAX     Integer32 (0..255)
    MAX-ACCESS read-only
    STATUS     current
    DESCRIPTION
            "-- empty --"
    ::= { hmStatusConfigEventLogEntry 1 }

-- {COLUMN} 1.3.6.1.4.1.248.32.18.1.11.12.1.2
hmStatusConfigEventLogEntryEvent OBJECT-TYPE
    SYNTAX     INTEGER {
                  eFwUplStart (4),
                  eUplsucc (5),
                  eUplfailto (6),
                  eUplfailincl (7),
                  eUplfailbaddev (8),
                  eLogin (9),
                  eLogout (10),
                  eCnfuplstart (11),
                  eCnfdnlstart (12),
                  eCnfdnlsucc (13),
                  eErrlogin (29),
                  eScrptuplstart (79),
                  eScrptdnlstart (80),
                  eLoginBlocked (87),
                  eUplinvversion (7000),
                  eUplfileexists (7001)
            }
    MAX-ACCESS read-only
    STATUS     current
    DESCRIPTION
            "-- empty --"
    ::= { hmStatusConfigEventLogEntry 2 }

-- {COLUMN} 1.3.6.1.4.1.248.32.18.1.11.12.1.3
hmStatusConfigEventLogEntryAccess OBJECT-TYPE
    SYNTAX     INTEGER {
                  eOutband (0),
                  eTelnet (1),
                  eTftp (2),
                  eHttp (3),
                  eSnmp (4),
                  eHttps (5),
                  eTelnetSsl (6),
                  eSsh (7),
                  eLl2m (8),
                  ePpp (254),
                  eUnknown (255)
            }
    MAX-ACCESS read-only
    STATUS     current
    DESCRIPTION
            "-- empty --"
    ::= { hmStatusConfigEventLogEntry 3 }

-- {COLUMN} 1.3.6.1.4.1.248.32.18.1.11.12.1.4
hmStatusConfigEventLogEntryIpAddress OBJECT-TYPE
    SYNTAX     IpAddress
    MAX-ACCESS read-only
    STATUS     obsolete
    DESCRIPTION
            "-- empty --"
    ::= { hmStatusConfigEventLogEntry 4 }

-- {COLUMN} 1.3.6.1.4.1.248.32.18.1.11.12.1.5
hmStatusConfigEventLogEntryInfo1 OBJECT-TYPE
    SYNTAX     DisplayString (SIZE(0..32))
    MAX-ACCESS read-only
    STATUS     current
    DESCRIPTION
            "-- empty --"
    ::= { hmStatusConfigEventLogEntry 5 }

-- {COLUMN} 1.3.6.1.4.1.248.32.18.1.11.12.1.6
hmStatusConfigEventLogEntryInfo2 OBJECT-TYPE
    SYNTAX     DisplayString (SIZE(0..64))
    MAX-ACCESS read-only
    STATUS     current
    DESCRIPTION
            "-- empty --"
    ::= { hmStatusConfigEventLogEntry 6 }

-- {COLUMN} 1.3.6.1.4.1.248.32.18.1.11.12.1.7
hmStatusConfigEventLogEntrySystemTime OBJECT-TYPE
    SYNTAX     DisplayString (SIZE(0..19))
    MAX-ACCESS read-only
    STATUS     current
    DESCRIPTION
            "-- empty --"
    ::= { hmStatusConfigEventLogEntry 7 }

-- {COLUMN} 1.3.6.1.4.1.248.32.18.1.11.12.1.8
hmStatusConfigEventLogEntryIpAddressNew OBJECT-TYPE
    SYNTAX     DisplayString (SIZE(0..255))
    MAX-ACCESS read-only
    STATUS     current
    DESCRIPTION
            "-- empty --"
    ::= { hmStatusConfigEventLogEntry 8 }

-- {COLUMN} 1.3.6.1.4.1.248.32.18.1.11.12.1.9
hmStatusConfigEventLogEntryInfo3 OBJECT-TYPE
    SYNTAX     DisplayString (SIZE(0..128))
    MAX-ACCESS read-only
    STATUS     current
    DESCRIPTION
            "-- empty --"
    ::= { hmStatusConfigEventLogEntry 9 }

-- {SCALAR} 1.3.6.1.4.1.248.32.18.1.11.13
hmStatusConfigStartScan OBJECT-TYPE
    SYNTAX     DisplayString
    MAX-ACCESS read-write
    STATUS     current
    DESCRIPTION
            "-- empty --"
    ::= { hmStatusConfig 13 }

-- {TABLE} 1.3.6.1.4.1.248.32.18.1.11.14
hmStatusConfigScanResultsTable OBJECT-TYPE
    SYNTAX     SEQUENCE OF HmStatusConfigScanResultsEntry
    MAX-ACCESS not-accessible
    STATUS     current
    DESCRIPTION
            "-- empty --"
    ::= { hmStatusConfig 14 }

-- {ROW} 1.3.6.1.4.1.248.32.18.1.11.14.1
hmStatusConfigScanResultsEntry OBJECT-TYPE
    SYNTAX     HmStatusConfigScanResultsEntry
    MAX-ACCESS not-accessible
    STATUS     current
    DESCRIPTION
            ""
    INDEX {
            hmStatusConfigScanResultsEntryIpAddress,
            hmStatusConfigScanResultsEntryRtgTag
          }
    ::= { hmStatusConfigScanResultsTable 1 }

HmStatusConfigScanResultsEntry ::= SEQUENCE {
            hmStatusConfigScanResultsEntryIpAddress IpAddress,
            hmStatusConfigScanResultsEntryName DisplayString,
            hmStatusConfigScanResultsEntryDeviceType DisplayString,
            hmStatusConfigScanResultsEntryVersion DisplayString,
            hmStatusConfigScanResultsEntryState INTEGER,
            hmStatusConfigScanResultsEntryCapiPort Integer32,
            hmStatusConfigScanResultsEntryHttpPort Integer32,
            hmStatusConfigScanResultsEntryHttpsPort Integer32,
            hmStatusConfigScanResultsEntryRtgTag Integer32
    }

-- {COLUMN} 1.3.6.1.4.1.248.32.18.1.11.14.1.1
hmStatusConfigScanResultsEntryIpAddress OBJECT-TYPE
    SYNTAX     IpAddress
    MAX-ACCESS read-only
    STATUS     current
    DESCRIPTION
            "-- empty --"
    ::= { hmStatusConfigScanResultsEntry 1 }

-- {COLUMN} 1.3.6.1.4.1.248.32.18.1.11.14.1.2
hmStatusConfigScanResultsEntryName OBJECT-TYPE
    SYNTAX     DisplayString (SIZE(0..65))
    MAX-ACCESS read-only
    STATUS     current
    DESCRIPTION
            "-- empty --"
    ::= { hmStatusConfigScanResultsEntry 2 }

-- {COLUMN} 1.3.6.1.4.1.248.32.18.1.11.14.1.3
hmStatusConfigScanResultsEntryDeviceType OBJECT-TYPE
    SYNTAX     DisplayString (SIZE(0..64))
    MAX-ACCESS read-only
    STATUS     current
    DESCRIPTION
            "-- empty --"
    ::= { hmStatusConfigScanResultsEntry 3 }

-- {COLUMN} 1.3.6.1.4.1.248.32.18.1.11.14.1.4
hmStatusConfigScanResultsEntryVersion OBJECT-TYPE
    SYNTAX     DisplayString (SIZE(0..30))
    MAX-ACCESS read-only
    STATUS     current
    DESCRIPTION
            "-- empty --"
    ::= { hmStatusConfigScanResultsEntry 4 }

-- {COLUMN} 1.3.6.1.4.1.248.32.18.1.11.14.1.5
hmStatusConfigScanResultsEntryState OBJECT-TYPE
    SYNTAX     INTEGER {
                  eScanning (0),
                  eReady (1),
                  eError (2)
            }
    MAX-ACCESS read-only
    STATUS     current
    DESCRIPTION
            "-- empty --"
    ::= { hmStatusConfigScanResultsEntry 5 }

-- {COLUMN} 1.3.6.1.4.1.248.32.18.1.11.14.1.6
hmStatusConfigScanResultsEntryCapiPort OBJECT-TYPE
    SYNTAX     Integer32 (0..65535)
    MAX-ACCESS read-only
    STATUS     current
    DESCRIPTION
            "-- empty --"
    ::= { hmStatusConfigScanResultsEntry 6 }

-- {COLUMN} 1.3.6.1.4.1.248.32.18.1.11.14.1.7
hmStatusConfigScanResultsEntryHttpPort OBJECT-TYPE
    SYNTAX     Integer32 (0..65535)
    MAX-ACCESS read-only
    STATUS     current
    DESCRIPTION
            "-- empty --"
    ::= { hmStatusConfigScanResultsEntry 7 }

-- {COLUMN} 1.3.6.1.4.1.248.32.18.1.11.14.1.8
hmStatusConfigScanResultsEntryHttpsPort OBJECT-TYPE
    SYNTAX     Integer32 (0..65535)
    MAX-ACCESS read-only
    STATUS     current
    DESCRIPTION
            "-- empty --"
    ::= { hmStatusConfigScanResultsEntry 8 }

-- {COLUMN} 1.3.6.1.4.1.248.32.18.1.11.14.1.9
hmStatusConfigScanResultsEntryRtgTag OBJECT-TYPE
    SYNTAX     Integer32 (0..65535)
    MAX-ACCESS read-only
    STATUS     current
    DESCRIPTION
            "-- empty --"
    ::= { hmStatusConfigScanResultsEntry 9 }

-- {TABLE} 1.3.6.1.4.1.248.32.18.1.11.16
hmStatusConfigFeaturesTable OBJECT-TYPE
    SYNTAX     SEQUENCE OF HmStatusConfigFeaturesEntry
    MAX-ACCESS not-accessible
    STATUS     current
    DESCRIPTION
            "-- empty --"
    ::= { hmStatusConfig 16 }

-- {ROW} 1.3.6.1.4.1.248.32.18.1.11.16.1
hmStatusConfigFeaturesEntry OBJECT-TYPE
    SYNTAX     HmStatusConfigFeaturesEntry
    MAX-ACCESS not-accessible
    STATUS     current
    DESCRIPTION
            ""
    INDEX {
            hmStatusConfigFeaturesEntryFeature,
            hmStatusConfigFeaturesEntryIndex
          }
    ::= { hmStatusConfigFeaturesTable 1 }

HmStatusConfigFeaturesEntry ::= SEQUENCE {
            hmStatusConfigFeaturesEntryFeature INTEGER,
            hmStatusConfigFeaturesEntryExpires DisplayString,
            hmStatusConfigFeaturesEntryExpire Gauge32,
            hmStatusConfigFeaturesEntryState INTEGER,
            hmStatusConfigFeaturesEntryIndex Integer32,
            hmStatusConfigFeaturesEntryCount Integer32
    }

-- {COLUMN} 1.3.6.1.4.1.248.32.18.1.11.16.1.1
hmStatusConfigFeaturesEntryFeature OBJECT-TYPE
    SYNTAX     INTEGER {
                  eIpx (1),
                  eLanBridge (2),
                  eLancapi (3),
                  eLeasedLine (4),
                  eSwitchedLine (5),
                  eDslInterface (6),
                  eFax (7),
                  eModem (8),
                  eVpn5 (9),
                  eVpn25 (10),
                  eCommonCriteria (11),
                  eProductionOk (12),
                  eVpn100 (13),
                  eWlc4025100 (14),
                  eWlanPointToPoint (15),
                  ePublicSpot (16),
                  eVpn200 (17),
                  eVpn500 (18),
                  eVpn1000 (19),
                  eHermes1Wpa (20),
                  eVpn3 (21),
                  eUmts (22),
                  eDynamicVpn (23),
                  eWlan5ghz (24),
                  eWlanNoEncryption (25),
                  eVoipAdvanced32 (26),
                  eAllIp (27),
                  eWlanFccRestrictions (28),
                  eWlc402550 (29),
                  eWlc400612 (30),
                  eVoipAdvanced8 (31),
                  eContentfilterAdditive (36),
                  eWlcPublicSpot (37),
                  eWlanMonitorMode (38),
                  eWlanNo5ghz (39),
                  eWlcApUpgrade (40),
                  eWlanDfs3 (41),
                  eInProduction (42),
                  eNetioServer (43),
                  eLanWlanBridge (44),
                  eEthernetIp (45),
                  eProfinet (46),
                  eWlanFilteredAveraging (47),
                  eVpn50 (48),
                  eWlcApBasic (49),
                  ePms (50),
                  ePrp (53),
                  eAllIpAdditive (55),
                  eClustering (56)
            }
    MAX-ACCESS read-only
    STATUS     current
    DESCRIPTION
            "-- empty --"
    ::= { hmStatusConfigFeaturesEntry 1 }

-- {COLUMN} 1.3.6.1.4.1.248.32.18.1.11.16.1.2
hmStatusConfigFeaturesEntryExpires OBJECT-TYPE
    SYNTAX     DisplayString (SIZE(0..255))
    MAX-ACCESS read-only
    STATUS     current
    DESCRIPTION
            "-- empty --"
    ::= { hmStatusConfigFeaturesEntry 2 }

-- {COLUMN} 1.3.6.1.4.1.248.32.18.1.11.16.1.3
hmStatusConfigFeaturesEntryExpire OBJECT-TYPE
    SYNTAX     Gauge32
    MAX-ACCESS read-only
    STATUS     current
    DESCRIPTION
            "-- empty --"
    ::= { hmStatusConfigFeaturesEntry 3 }

-- {COLUMN} 1.3.6.1.4.1.248.32.18.1.11.16.1.4
hmStatusConfigFeaturesEntryState OBJECT-TYPE
    SYNTAX     INTEGER {
                  eLocked (0),
                  eActive (1),
                  eHidden (2),
                  eExpired (3),
                  eUnused (4)
            }
    MAX-ACCESS read-only
    STATUS     current
    DESCRIPTION
            "-- empty --"
    ::= { hmStatusConfigFeaturesEntry 4 }

-- {COLUMN} 1.3.6.1.4.1.248.32.18.1.11.16.1.5
hmStatusConfigFeaturesEntryIndex OBJECT-TYPE
    SYNTAX     Integer32 (0..2147483647)
    MAX-ACCESS read-only
    STATUS     current
    DESCRIPTION
            "-- empty --"
    ::= { hmStatusConfigFeaturesEntry 5 }

-- {COLUMN} 1.3.6.1.4.1.248.32.18.1.11.16.1.6
hmStatusConfigFeaturesEntryCount OBJECT-TYPE
    SYNTAX     Integer32 (0..2147483647)
    MAX-ACCESS read-only
    STATUS     current
    DESCRIPTION
            "-- empty --"
    ::= { hmStatusConfigFeaturesEntry 6 }

-- {SCALAR} 1.3.6.1.4.1.248.32.18.1.11.20
hmStatusConfigConfigDateNew OBJECT-TYPE
    SYNTAX     Counter32
    MAX-ACCESS read-only
    STATUS     current
    DESCRIPTION
            ""
    ::= { hmStatusConfig 20 }

-- {SCALAR} 1.3.6.1.4.1.248.32.18.1.11.21
hmStatusConfigConfigHash OBJECT-TYPE
    SYNTAX     OCTET STRING
    MAX-ACCESS read-only
    STATUS     current
    DESCRIPTION
            "-- empty --"
    ::= { hmStatusConfig 21 }

-- {SCALAR} 1.3.6.1.4.1.248.32.18.1.11.22
hmStatusConfigConfigVersion OBJECT-TYPE
    SYNTAX     Integer32 (0..2147483647)
    MAX-ACCESS read-only
    STATUS     current
    DESCRIPTION
            "-- empty --"
    ::= { hmStatusConfig 22 }

-- {TABLE} 1.3.6.1.4.1.248.32.18.1.11.23
hmStatusConfigScriptLogTable OBJECT-TYPE
    SYNTAX     SEQUENCE OF HmStatusConfigScriptLogEntry
    MAX-ACCESS not-accessible
    STATUS     current
    DESCRIPTION
            "-- empty --"
    ::= { hmStatusConfig 23 }

-- {ROW} 1.3.6.1.4.1.248.32.18.1.11.23.1
hmStatusConfigScriptLogEntry OBJECT-TYPE
    SYNTAX     HmStatusConfigScriptLogEntry
    MAX-ACCESS not-accessible
    STATUS     current
    DESCRIPTION
            ""
    INDEX {
            hmStatusConfigScriptLogEntryIndex
          }
    ::= { hmStatusConfigScriptLogTable 1 }

HmStatusConfigScriptLogEntry ::= SEQUENCE {
            hmStatusConfigScriptLogEntryIndex Integer32,
            hmStatusConfigScriptLogEntryTime DisplayString,
            hmStatusConfigScriptLogEntryComment DisplayString,
            hmStatusConfigScriptLogEntrySuccessful INTEGER,
            hmStatusConfigScriptLogEntryErrorLine Integer32
    }

-- {COLUMN} 1.3.6.1.4.1.248.32.18.1.11.23.1.1
hmStatusConfigScriptLogEntryIndex OBJECT-TYPE
    SYNTAX     Integer32 (0..2147483647)
    MAX-ACCESS read-only
    STATUS     current
    DESCRIPTION
            "-- empty --"
    ::= { hmStatusConfigScriptLogEntry 1 }

-- {COLUMN} 1.3.6.1.4.1.248.32.18.1.11.23.1.2
hmStatusConfigScriptLogEntryTime OBJECT-TYPE
    SYNTAX     DisplayString (SIZE(0..19))
    MAX-ACCESS read-only
    STATUS     current
    DESCRIPTION
            "-- empty --"
    ::= { hmStatusConfigScriptLogEntry 2 }

-- {COLUMN} 1.3.6.1.4.1.248.32.18.1.11.23.1.3
hmStatusConfigScriptLogEntryComment OBJECT-TYPE
    SYNTAX     DisplayString (SIZE(0..80))
    MAX-ACCESS read-only
    STATUS     current
    DESCRIPTION
            "-- empty --"
    ::= { hmStatusConfigScriptLogEntry 3 }

-- {COLUMN} 1.3.6.1.4.1.248.32.18.1.11.23.1.4
hmStatusConfigScriptLogEntrySuccessful OBJECT-TYPE
    SYNTAX     INTEGER {
                  eNo (0),
                  eYes (1)
            }
    MAX-ACCESS read-only
    STATUS     current
    DESCRIPTION
            "-- empty --"
    ::= { hmStatusConfigScriptLogEntry 4 }

-- {COLUMN} 1.3.6.1.4.1.248.32.18.1.11.23.1.5
hmStatusConfigScriptLogEntryErrorLine OBJECT-TYPE
    SYNTAX     Integer32 (0..2147483647)
    MAX-ACCESS read-only
    STATUS     current
    DESCRIPTION
            "-- empty --"
    ::= { hmStatusConfigScriptLogEntry 5 }

-- {NODE} 1.3.6.1.4.1.248.32.18.1.11.51
hmStatusConfigSync OBJECT IDENTIFIER ::= { hmStatusConfig 51 }

-- {SCALAR} 1.3.6.1.4.1.248.32.18.1.11.51.1
hmStatusConfigSyncState OBJECT-TYPE
    SYNTAX     INTEGER {
                  eOff (0),
                  eTcpListenFailure (2),
                  eNotYetLaunched (3),
                  eIncompatibleFirmware (4),
                  eIncompatibleMenuNodes (5),
                  eWrongOwnAddress (6),
                  eNoSnapshot (7),
                  eTimeUnknown (8),
                  eOk (9)
            }
    MAX-ACCESS read-only
    STATUS     current
    DESCRIPTION
            "-- empty --"
    ::= { hmStatusConfigSync 1 }

-- {NODE} 1.3.6.1.4.1.248.32.18.1.11.51.2
hmStatusConfigSyncNewCluster OBJECT IDENTIFIER ::= { hmStatusConfigSync 2 }

-- {SCALAR} 1.3.6.1.4.1.248.32.18.1.11.51.2.1
hmStatusConfigSyncNewClusterName OBJECT-TYPE
    SYNTAX     DisplayString (SIZE(0..254))
    MAX-ACCESS read-only
    STATUS     current
    DESCRIPTION
            "-- empty --"
    ::= { hmStatusConfigSyncNewCluster 1 }

-- {TABLE} 1.3.6.1.4.1.248.32.18.1.11.51.2.2
hmStatusConfigSyncNewClusterGroupMembersTable OBJECT-TYPE
    SYNTAX     SEQUENCE OF HmStatusConfigSyncNewClusterGroupMembersEntry
    MAX-ACCESS not-accessible
    STATUS     current
    DESCRIPTION
            "-- empty --"
    ::= { hmStatusConfigSyncNewCluster 2 }

-- {ROW} 1.3.6.1.4.1.248.32.18.1.11.51.2.2.1
hmStatusConfigSyncNewClusterGroupMembersEntry OBJECT-TYPE
    SYNTAX     HmStatusConfigSyncNewClusterGroupMembersEntry
    MAX-ACCESS not-accessible
    STATUS     current
    DESCRIPTION
            ""
    INDEX {
            hmStatusConfigSyncNewClusterGroupMembersEntryIdx
          }
    ::= { hmStatusConfigSyncNewClusterGroupMembersTable 1 }

HmStatusConfigSyncNewClusterGroupMembersEntry ::= SEQUENCE {
            hmStatusConfigSyncNewClusterGroupMembersEntryIdx Integer32,
            hmStatusConfigSyncNewClusterGroupMembersEntryId Integer32,
            hmStatusConfigSyncNewClusterGroupMembersEntryAddress DisplayString,
            hmStatusConfigSyncNewClusterGroupMembersEntryThisDevice INTEGER
    }

-- {COLUMN} 1.3.6.1.4.1.248.32.18.1.11.51.2.2.1.1
hmStatusConfigSyncNewClusterGroupMembersEntryIdx OBJECT-TYPE
    SYNTAX     Integer32 (0..65535)
    MAX-ACCESS read-only
    STATUS     current
    DESCRIPTION
            "-- empty --"
    ::= { hmStatusConfigSyncNewClusterGroupMembersEntry 1 }

-- {COLUMN} 1.3.6.1.4.1.248.32.18.1.11.51.2.2.1.2
hmStatusConfigSyncNewClusterGroupMembersEntryId OBJECT-TYPE
    SYNTAX     Integer32 (0..65535)
    MAX-ACCESS read-only
    STATUS     current
    DESCRIPTION
            "-- empty --"
    ::= { hmStatusConfigSyncNewClusterGroupMembersEntry 2 }

-- {COLUMN} 1.3.6.1.4.1.248.32.18.1.11.51.2.2.1.3
hmStatusConfigSyncNewClusterGroupMembersEntryAddress OBJECT-TYPE
    SYNTAX     DisplayString (SIZE(0..63))
    MAX-ACCESS read-only
    STATUS     current
    DESCRIPTION
            "-- empty --"
    ::= { hmStatusConfigSyncNewClusterGroupMembersEntry 3 }

-- {COLUMN} 1.3.6.1.4.1.248.32.18.1.11.51.2.2.1.4
hmStatusConfigSyncNewClusterGroupMembersEntryThisDevice OBJECT-TYPE
    SYNTAX     INTEGER {
                  eNo (0),
                  eYes (1)
            }
    MAX-ACCESS read-only
    STATUS     current
    DESCRIPTION
            "-- empty --"
    ::= { hmStatusConfigSyncNewClusterGroupMembersEntry 4 }

-- {TABLE} 1.3.6.1.4.1.248.32.18.1.11.51.2.3
hmStatusConfigSyncNewClusterMenuNodesTable OBJECT-TYPE
    SYNTAX     SEQUENCE OF HmStatusConfigSyncNewClusterMenuNodesEntry
    MAX-ACCESS not-accessible
    STATUS     current
    DESCRIPTION
            "-- empty --"
    ::= { hmStatusConfigSyncNewCluster 3 }

-- {ROW} 1.3.6.1.4.1.248.32.18.1.11.51.2.3.1
hmStatusConfigSyncNewClusterMenuNodesEntry OBJECT-TYPE
    SYNTAX     HmStatusConfigSyncNewClusterMenuNodesEntry
    MAX-ACCESS not-accessible
    STATUS     current
    DESCRIPTION
            ""
    INDEX {
            hmStatusConfigSyncNewClusterMenuNodesEntryIdx
          }
    ::= { hmStatusConfigSyncNewClusterMenuNodesTable 1 }

HmStatusConfigSyncNewClusterMenuNodesEntry ::= SEQUENCE {
            hmStatusConfigSyncNewClusterMenuNodesEntryIdx Integer32,
            hmStatusConfigSyncNewClusterMenuNodesEntryId Integer32,
            hmStatusConfigSyncNewClusterMenuNodesEntryPath DisplayString,
            hmStatusConfigSyncNewClusterMenuNodesEntrySnmpOid DisplayString,
            hmStatusConfigSyncNewClusterMenuNodesEntryIndexColumns DisplayString
    }

-- {COLUMN} 1.3.6.1.4.1.248.32.18.1.11.51.2.3.1.1
hmStatusConfigSyncNewClusterMenuNodesEntryIdx OBJECT-TYPE
    SYNTAX     Integer32 (0..2147483647)
    MAX-ACCESS read-only
    STATUS     current
    DESCRIPTION
            "-- empty --"
    ::= { hmStatusConfigSyncNewClusterMenuNodesEntry 1 }

-- {COLUMN} 1.3.6.1.4.1.248.32.18.1.11.51.2.3.1.2
hmStatusConfigSyncNewClusterMenuNodesEntryId OBJECT-TYPE
    SYNTAX     Integer32 (0..2147483647)
    MAX-ACCESS read-only
    STATUS     current
    DESCRIPTION
            "-- empty --"
    ::= { hmStatusConfigSyncNewClusterMenuNodesEntry 2 }

-- {COLUMN} 1.3.6.1.4.1.248.32.18.1.11.51.2.3.1.3
hmStatusConfigSyncNewClusterMenuNodesEntryPath OBJECT-TYPE
    SYNTAX     DisplayString (SIZE(0..127))
    MAX-ACCESS read-only
    STATUS     current
    DESCRIPTION
            "-- empty --"
    ::= { hmStatusConfigSyncNewClusterMenuNodesEntry 3 }

-- {COLUMN} 1.3.6.1.4.1.248.32.18.1.11.51.2.3.1.4
hmStatusConfigSyncNewClusterMenuNodesEntrySnmpOid OBJECT-TYPE
    SYNTAX     DisplayString (SIZE(0..63))
    MAX-ACCESS read-only
    STATUS     current
    DESCRIPTION
            "-- empty --"
    ::= { hmStatusConfigSyncNewClusterMenuNodesEntry 4 }

-- {COLUMN} 1.3.6.1.4.1.248.32.18.1.11.51.2.3.1.5
hmStatusConfigSyncNewClusterMenuNodesEntryIndexColumns OBJECT-TYPE
    SYNTAX     DisplayString (SIZE(0..127))
    MAX-ACCESS read-only
    STATUS     current
    DESCRIPTION
            "-- empty --"
    ::= { hmStatusConfigSyncNewClusterMenuNodesEntry 5 }

-- {TABLE} 1.3.6.1.4.1.248.32.18.1.11.51.2.4
hmStatusConfigSyncNewClusterIgnoredRowsTable OBJECT-TYPE
    SYNTAX     SEQUENCE OF HmStatusConfigSyncNewClusterIgnoredRowsEntry
    MAX-ACCESS not-accessible
    STATUS     current
    DESCRIPTION
            "-- empty --"
    ::= { hmStatusConfigSyncNewCluster 4 }

-- {ROW} 1.3.6.1.4.1.248.32.18.1.11.51.2.4.1
hmStatusConfigSyncNewClusterIgnoredRowsEntry OBJECT-TYPE
    SYNTAX     HmStatusConfigSyncNewClusterIgnoredRowsEntry
    MAX-ACCESS not-accessible
    STATUS     current
    DESCRIPTION
            ""
    INDEX {
            hmStatusConfigSyncNewClusterIgnoredRowsEntryIdx
          }
    ::= { hmStatusConfigSyncNewClusterIgnoredRowsTable 1 }

HmStatusConfigSyncNewClusterIgnoredRowsEntry ::= SEQUENCE {
            hmStatusConfigSyncNewClusterIgnoredRowsEntryIdx Integer32,
            hmStatusConfigSyncNewClusterIgnoredRowsEntryId Integer32,
            hmStatusConfigSyncNewClusterIgnoredRowsEntryPath DisplayString,
            hmStatusConfigSyncNewClusterIgnoredRowsEntrySnmpOid DisplayString,
            hmStatusConfigSyncNewClusterIgnoredRowsEntryRowIndex DisplayString
    }

-- {COLUMN} 1.3.6.1.4.1.248.32.18.1.11.51.2.4.1.1
hmStatusConfigSyncNewClusterIgnoredRowsEntryIdx OBJECT-TYPE
    SYNTAX     Integer32 (0..2147483647)
    MAX-ACCESS read-only
    STATUS     current
    DESCRIPTION
            "-- empty --"
    ::= { hmStatusConfigSyncNewClusterIgnoredRowsEntry 1 }

-- {COLUMN} 1.3.6.1.4.1.248.32.18.1.11.51.2.4.1.2
hmStatusConfigSyncNewClusterIgnoredRowsEntryId OBJECT-TYPE
    SYNTAX     Integer32 (0..2147483647)
    MAX-ACCESS read-only
    STATUS     current
    DESCRIPTION
            "-- empty --"
    ::= { hmStatusConfigSyncNewClusterIgnoredRowsEntry 2 }

-- {COLUMN} 1.3.6.1.4.1.248.32.18.1.11.51.2.4.1.3
hmStatusConfigSyncNewClusterIgnoredRowsEntryPath OBJECT-TYPE
    SYNTAX     DisplayString (SIZE(0..127))
    MAX-ACCESS read-only
    STATUS     current
    DESCRIPTION
            "-- empty --"
    ::= { hmStatusConfigSyncNewClusterIgnoredRowsEntry 3 }

-- {COLUMN} 1.3.6.1.4.1.248.32.18.1.11.51.2.4.1.4
hmStatusConfigSyncNewClusterIgnoredRowsEntrySnmpOid OBJECT-TYPE
    SYNTAX     DisplayString (SIZE(0..63))
    MAX-ACCESS read-only
    STATUS     current
    DESCRIPTION
            "-- empty --"
    ::= { hmStatusConfigSyncNewClusterIgnoredRowsEntry 4 }

-- {COLUMN} 1.3.6.1.4.1.248.32.18.1.11.51.2.4.1.5
hmStatusConfigSyncNewClusterIgnoredRowsEntryRowIndex OBJECT-TYPE
    SYNTAX     DisplayString (SIZE(0..127))
    MAX-ACCESS read-only
    STATUS     current
    DESCRIPTION
            "-- empty --"
    ::= { hmStatusConfigSyncNewClusterIgnoredRowsEntry 5 }

-- {SCALAR} 1.3.6.1.4.1.248.32.18.1.11.51.2.5
hmStatusConfigSyncNewClusterState OBJECT-TYPE
    SYNTAX     INTEGER {
                  eOff (0),
                  eInvalid (1),
                  eNotRunning (2),
                  eRunning (3),
                  eChanged (4)
            }
    MAX-ACCESS read-only
    STATUS     current
    DESCRIPTION
            "-- empty --"
    ::= { hmStatusConfigSyncNewCluster 5 }

-- {SCALAR} 1.3.6.1.4.1.248.32.18.1.11.51.2.6
hmStatusConfigSyncNewClusterInfo OBJECT-TYPE
    SYNTAX     DisplayString (SIZE(0..254))
    MAX-ACCESS read-only
    STATUS     current
    DESCRIPTION
            "-- empty --"
    ::= { hmStatusConfigSyncNewCluster 6 }

-- {SCALAR} 1.3.6.1.4.1.248.32.18.1.11.51.2.7
hmStatusConfigSyncNewClusterLaunch OBJECT-TYPE
    SYNTAX     DisplayString
    MAX-ACCESS read-write
    STATUS     current
    DESCRIPTION
            "-- empty --"
    ::= { hmStatusConfigSyncNewCluster 7 }

-- {SCALAR} 1.3.6.1.4.1.248.32.18.1.11.51.3
hmStatusConfigSyncClusterTime OBJECT-TYPE
    SYNTAX     DisplayString
    MAX-ACCESS read-only
    STATUS     current
    DESCRIPTION
            "-- empty --"
    ::= { hmStatusConfigSync 3 }

-- {NODE} 1.3.6.1.4.1.248.32.18.1.11.51.4
hmStatusConfigSyncLocalConfig OBJECT IDENTIFIER ::= { hmStatusConfigSync 4 }

-- {TABLE} 1.3.6.1.4.1.248.32.18.1.11.51.4.1
hmStatusConfigSyncLocalConfigDetectedTable OBJECT-TYPE
    SYNTAX     SEQUENCE OF HmStatusConfigSyncLocalConfigDetectedEntry
    MAX-ACCESS not-accessible
    STATUS     current
    DESCRIPTION
            ""
    ::= { hmStatusConfigSyncLocalConfig 1 }

-- {ROW} 1.3.6.1.4.1.248.32.18.1.11.51.4.1.1
hmStatusConfigSyncLocalConfigDetectedEntry OBJECT-TYPE
    SYNTAX     HmStatusConfigSyncLocalConfigDetectedEntry
    MAX-ACCESS not-accessible
    STATUS     current
    DESCRIPTION
            ""
    INDEX {
            hmStatusConfigSyncLocalConfigDetectedEntryIdx
          }
    ::= { hmStatusConfigSyncLocalConfigDetectedTable 1 }

HmStatusConfigSyncLocalConfigDetectedEntry ::= SEQUENCE {
            hmStatusConfigSyncLocalConfigDetectedEntryIdx Integer32,
            hmStatusConfigSyncLocalConfigDetectedEntryDetectedAt DisplayString,
            hmStatusConfigSyncLocalConfigDetectedEntryDetectedAtNumerical Counter32,
            hmStatusConfigSyncLocalConfigDetectedEntryPath DisplayString,
            hmStatusConfigSyncLocalConfigDetectedEntryType INTEGER,
            hmStatusConfigSyncLocalConfigDetectedEntryValue DisplayString
    }

-- {COLUMN} 1.3.6.1.4.1.248.32.18.1.11.51.4.1.1.1
hmStatusConfigSyncLocalConfigDetectedEntryIdx OBJECT-TYPE
    SYNTAX     Integer32 (0..2147483647)
    MAX-ACCESS read-only
    STATUS     current
    DESCRIPTION
            "-- empty --"
    ::= { hmStatusConfigSyncLocalConfigDetectedEntry 1 }

-- {COLUMN} 1.3.6.1.4.1.248.32.18.1.11.51.4.1.1.2
hmStatusConfigSyncLocalConfigDetectedEntryDetectedAt OBJECT-TYPE
    SYNTAX     DisplayString (SIZE(0..255))
    MAX-ACCESS read-only
    STATUS     current
    DESCRIPTION
            "-- empty --"
    ::= { hmStatusConfigSyncLocalConfigDetectedEntry 2 }

-- {COLUMN} 1.3.6.1.4.1.248.32.18.1.11.51.4.1.1.3
hmStatusConfigSyncLocalConfigDetectedEntryDetectedAtNumerical OBJECT-TYPE
    SYNTAX     Counter32
    MAX-ACCESS read-only
    STATUS     current
    DESCRIPTION
            "-- empty --"
    ::= { hmStatusConfigSyncLocalConfigDetectedEntry 3 }

-- {COLUMN} 1.3.6.1.4.1.248.32.18.1.11.51.4.1.1.4
hmStatusConfigSyncLocalConfigDetectedEntryPath OBJECT-TYPE
    SYNTAX     DisplayString (SIZE(0..255))
    MAX-ACCESS read-only
    STATUS     current
    DESCRIPTION
            "-- empty --"
    ::= { hmStatusConfigSyncLocalConfigDetectedEntry 4 }

-- {COLUMN} 1.3.6.1.4.1.248.32.18.1.11.51.4.1.1.5
hmStatusConfigSyncLocalConfigDetectedEntryType OBJECT-TYPE
    SYNTAX     INTEGER {
                  eSetScalar (1),
                  eSetRow (2),
                  eDeleteRow (3)
            }
    MAX-ACCESS read-only
    STATUS     current
    DESCRIPTION
            "-- empty --"
    ::= { hmStatusConfigSyncLocalConfigDetectedEntry 5 }

-- {COLUMN} 1.3.6.1.4.1.248.32.18.1.11.51.4.1.1.6
hmStatusConfigSyncLocalConfigDetectedEntryValue OBJECT-TYPE
    SYNTAX     DisplayString (SIZE(0..255))
    MAX-ACCESS read-only
    STATUS     current
    DESCRIPTION
            "-- empty --"
    ::= { hmStatusConfigSyncLocalConfigDetectedEntry 6 }

-- {TABLE} 1.3.6.1.4.1.248.32.18.1.11.51.4.2
hmStatusConfigSyncLocalConfigAppliedTable OBJECT-TYPE
    SYNTAX     SEQUENCE OF HmStatusConfigSyncLocalConfigAppliedEntry
    MAX-ACCESS not-accessible
    STATUS     current
    DESCRIPTION
            ""
    ::= { hmStatusConfigSyncLocalConfig 2 }

-- {ROW} 1.3.6.1.4.1.248.32.18.1.11.51.4.2.1
hmStatusConfigSyncLocalConfigAppliedEntry OBJECT-TYPE
    SYNTAX     HmStatusConfigSyncLocalConfigAppliedEntry
    MAX-ACCESS not-accessible
    STATUS     current
    DESCRIPTION
            ""
    INDEX {
            hmStatusConfigSyncLocalConfigAppliedEntryIdx
          }
    ::= { hmStatusConfigSyncLocalConfigAppliedTable 1 }

HmStatusConfigSyncLocalConfigAppliedEntry ::= SEQUENCE {
            hmStatusConfigSyncLocalConfigAppliedEntryIdx Integer32,
            hmStatusConfigSyncLocalConfigAppliedEntryAppliedAt DisplayString,
            hmStatusConfigSyncLocalConfigAppliedEntryAppliedAtNumerical Counter32,
            hmStatusConfigSyncLocalConfigAppliedEntryPath DisplayString,
            hmStatusConfigSyncLocalConfigAppliedEntryType INTEGER,
            hmStatusConfigSyncLocalConfigAppliedEntryValue DisplayString,
            hmStatusConfigSyncLocalConfigAppliedEntryResult INTEGER
    }

-- {COLUMN} 1.3.6.1.4.1.248.32.18.1.11.51.4.2.1.1
hmStatusConfigSyncLocalConfigAppliedEntryIdx OBJECT-TYPE
    SYNTAX     Integer32 (0..2147483647)
    MAX-ACCESS read-only
    STATUS     current
    DESCRIPTION
            "-- empty --"
    ::= { hmStatusConfigSyncLocalConfigAppliedEntry 1 }

-- {COLUMN} 1.3.6.1.4.1.248.32.18.1.11.51.4.2.1.2
hmStatusConfigSyncLocalConfigAppliedEntryAppliedAt OBJECT-TYPE
    SYNTAX     DisplayString (SIZE(0..255))
    MAX-ACCESS read-only
    STATUS     current
    DESCRIPTION
            "-- empty --"
    ::= { hmStatusConfigSyncLocalConfigAppliedEntry 2 }

-- {COLUMN} 1.3.6.1.4.1.248.32.18.1.11.51.4.2.1.3
hmStatusConfigSyncLocalConfigAppliedEntryAppliedAtNumerical OBJECT-TYPE
    SYNTAX     Counter32
    MAX-ACCESS read-only
    STATUS     current
    DESCRIPTION
            "-- empty --"
    ::= { hmStatusConfigSyncLocalConfigAppliedEntry 3 }

-- {COLUMN} 1.3.6.1.4.1.248.32.18.1.11.51.4.2.1.4
hmStatusConfigSyncLocalConfigAppliedEntryPath OBJECT-TYPE
    SYNTAX     DisplayString (SIZE(0..255))
    MAX-ACCESS read-only
    STATUS     current
    DESCRIPTION
            "-- empty --"
    ::= { hmStatusConfigSyncLocalConfigAppliedEntry 4 }

-- {COLUMN} 1.3.6.1.4.1.248.32.18.1.11.51.4.2.1.5
hmStatusConfigSyncLocalConfigAppliedEntryType OBJECT-TYPE
    SYNTAX     INTEGER {
                  eSetScalar (1),
                  eSetRow (2),
                  eDeleteRow (3)
            }
    MAX-ACCESS read-only
    STATUS     current
    DESCRIPTION
            "-- empty --"
    ::= { hmStatusConfigSyncLocalConfigAppliedEntry 5 }

-- {COLUMN} 1.3.6.1.4.1.248.32.18.1.11.51.4.2.1.6
hmStatusConfigSyncLocalConfigAppliedEntryValue OBJECT-TYPE
    SYNTAX     DisplayString (SIZE(0..255))
    MAX-ACCESS read-only
    STATUS     current
    DESCRIPTION
            "-- empty --"
    ::= { hmStatusConfigSyncLocalConfigAppliedEntry 6 }

-- {COLUMN} 1.3.6.1.4.1.248.32.18.1.11.51.4.2.1.7
hmStatusConfigSyncLocalConfigAppliedEntryResult OBJECT-TYPE
    SYNTAX     INTEGER {
                  eOk (0),
                  eOkMsgSent (1),
                  eOkClose (2),
                  eOkAbort (3),
                  eOkMore (4),
                  eOkStarted (5),
                  eNoLogin (16),
                  eSyntaxError (32),
                  eNoPath (48),
                  ePathUnresolvable (64),
                  ePathAmbiguous (80),
                  eNoMenuStack (96),
                  eNotSettable (112),
                  eValueInvalid (128),
                  eReadOnlyConn (144),
                  eActionFailed (160),
                  eTableIsFull (176),
                  eWasIgnored (192),
                  eWrongPassword (208),
                  ePathNameEmpty (224),
                  eEndOfLine (240)
            }
    MAX-ACCESS read-only
    STATUS     current
    DESCRIPTION
            "-- empty --"
    ::= { hmStatusConfigSyncLocalConfigAppliedEntry 7 }

-- {NODE} 1.3.6.1.4.1.248.32.18.1.11.51.5
hmStatusConfigSyncRunningCluster OBJECT IDENTIFIER ::= { hmStatusConfigSync 5 }

-- {SCALAR} 1.3.6.1.4.1.248.32.18.1.11.51.5.1
hmStatusConfigSyncRunningClusterId OBJECT-TYPE
    SYNTAX     DisplayString (SIZE(0..8))
    MAX-ACCESS read-only
    STATUS     current
    DESCRIPTION
            "-- empty --"
    ::= { hmStatusConfigSyncRunningCluster 1 }

-- {SCALAR} 1.3.6.1.4.1.248.32.18.1.11.51.5.2
hmStatusConfigSyncRunningClusterName OBJECT-TYPE
    SYNTAX     DisplayString (SIZE(0..254))
    MAX-ACCESS read-only
    STATUS     current
    DESCRIPTION
            "-- empty --"
    ::= { hmStatusConfigSyncRunningCluster 2 }

-- {TABLE} 1.3.6.1.4.1.248.32.18.1.11.51.5.3
hmStatusConfigSyncRunningClusterGroupMembersTable OBJECT-TYPE
    SYNTAX     SEQUENCE OF HmStatusConfigSyncRunningClusterGroupMembersEntry
    MAX-ACCESS not-accessible
    STATUS     current
    DESCRIPTION
            "-- empty --"
    ::= { hmStatusConfigSyncRunningCluster 3 }

-- {ROW} 1.3.6.1.4.1.248.32.18.1.11.51.5.3.1
hmStatusConfigSyncRunningClusterGroupMembersEntry OBJECT-TYPE
    SYNTAX     HmStatusConfigSyncRunningClusterGroupMembersEntry
    MAX-ACCESS not-accessible
    STATUS     current
    DESCRIPTION
            ""
    INDEX {
            hmStatusConfigSyncRunningClusterGroupMembersEntryIdx
          }
    ::= { hmStatusConfigSyncRunningClusterGroupMembersTable 1 }

HmStatusConfigSyncRunningClusterGroupMembersEntry ::= SEQUENCE {
            hmStatusConfigSyncRunningClusterGroupMembersEntryIdx Integer32,
            hmStatusConfigSyncRunningClusterGroupMembersEntryId Integer32,
            hmStatusConfigSyncRunningClusterGroupMembersEntryAddress DisplayString,
            hmStatusConfigSyncRunningClusterGroupMembersEntryThisDevice INTEGER
    }

-- {COLUMN} 1.3.6.1.4.1.248.32.18.1.11.51.5.3.1.1
hmStatusConfigSyncRunningClusterGroupMembersEntryIdx OBJECT-TYPE
    SYNTAX     Integer32 (0..65535)
    MAX-ACCESS read-only
    STATUS     current
    DESCRIPTION
            "-- empty --"
    ::= { hmStatusConfigSyncRunningClusterGroupMembersEntry 1 }

-- {COLUMN} 1.3.6.1.4.1.248.32.18.1.11.51.5.3.1.2
hmStatusConfigSyncRunningClusterGroupMembersEntryId OBJECT-TYPE
    SYNTAX     Integer32 (0..65535)
    MAX-ACCESS read-only
    STATUS     current
    DESCRIPTION
            "-- empty --"
    ::= { hmStatusConfigSyncRunningClusterGroupMembersEntry 2 }

-- {COLUMN} 1.3.6.1.4.1.248.32.18.1.11.51.5.3.1.3
hmStatusConfigSyncRunningClusterGroupMembersEntryAddress OBJECT-TYPE
    SYNTAX     DisplayString (SIZE(0..63))
    MAX-ACCESS read-only
    STATUS     current
    DESCRIPTION
            "-- empty --"
    ::= { hmStatusConfigSyncRunningClusterGroupMembersEntry 3 }

-- {COLUMN} 1.3.6.1.4.1.248.32.18.1.11.51.5.3.1.4
hmStatusConfigSyncRunningClusterGroupMembersEntryThisDevice OBJECT-TYPE
    SYNTAX     INTEGER {
                  eNo (0),
                  eYes (1)
            }
    MAX-ACCESS read-only
    STATUS     current
    DESCRIPTION
            "-- empty --"
    ::= { hmStatusConfigSyncRunningClusterGroupMembersEntry 4 }

-- {TABLE} 1.3.6.1.4.1.248.32.18.1.11.51.5.4
hmStatusConfigSyncRunningClusterMenuNodesTable OBJECT-TYPE
    SYNTAX     SEQUENCE OF HmStatusConfigSyncRunningClusterMenuNodesEntry
    MAX-ACCESS not-accessible
    STATUS     current
    DESCRIPTION
            "-- empty --"
    ::= { hmStatusConfigSyncRunningCluster 4 }

-- {ROW} 1.3.6.1.4.1.248.32.18.1.11.51.5.4.1
hmStatusConfigSyncRunningClusterMenuNodesEntry OBJECT-TYPE
    SYNTAX     HmStatusConfigSyncRunningClusterMenuNodesEntry
    MAX-ACCESS not-accessible
    STATUS     current
    DESCRIPTION
            ""
    INDEX {
            hmStatusConfigSyncRunningClusterMenuNodesEntryIdx
          }
    ::= { hmStatusConfigSyncRunningClusterMenuNodesTable 1 }

HmStatusConfigSyncRunningClusterMenuNodesEntry ::= SEQUENCE {
            hmStatusConfigSyncRunningClusterMenuNodesEntryIdx Integer32,
            hmStatusConfigSyncRunningClusterMenuNodesEntryId Integer32,
            hmStatusConfigSyncRunningClusterMenuNodesEntryPath DisplayString,
            hmStatusConfigSyncRunningClusterMenuNodesEntrySnmpOid DisplayString,
            hmStatusConfigSyncRunningClusterMenuNodesEntryIndexColumns DisplayString
    }

-- {COLUMN} 1.3.6.1.4.1.248.32.18.1.11.51.5.4.1.1
hmStatusConfigSyncRunningClusterMenuNodesEntryIdx OBJECT-TYPE
    SYNTAX     Integer32 (0..2147483647)
    MAX-ACCESS read-only
    STATUS     current
    DESCRIPTION
            "-- empty --"
    ::= { hmStatusConfigSyncRunningClusterMenuNodesEntry 1 }

-- {COLUMN} 1.3.6.1.4.1.248.32.18.1.11.51.5.4.1.2
hmStatusConfigSyncRunningClusterMenuNodesEntryId OBJECT-TYPE
    SYNTAX     Integer32 (0..2147483647)
    MAX-ACCESS read-only
    STATUS     current
    DESCRIPTION
            "-- empty --"
    ::= { hmStatusConfigSyncRunningClusterMenuNodesEntry 2 }

-- {COLUMN} 1.3.6.1.4.1.248.32.18.1.11.51.5.4.1.3
hmStatusConfigSyncRunningClusterMenuNodesEntryPath OBJECT-TYPE
    SYNTAX     DisplayString (SIZE(0..127))
    MAX-ACCESS read-only
    STATUS     current
    DESCRIPTION
            "-- empty --"
    ::= { hmStatusConfigSyncRunningClusterMenuNodesEntry 3 }

-- {COLUMN} 1.3.6.1.4.1.248.32.18.1.11.51.5.4.1.4
hmStatusConfigSyncRunningClusterMenuNodesEntrySnmpOid OBJECT-TYPE
    SYNTAX     DisplayString (SIZE(0..63))
    MAX-ACCESS read-only
    STATUS     current
    DESCRIPTION
            "-- empty --"
    ::= { hmStatusConfigSyncRunningClusterMenuNodesEntry 4 }

-- {COLUMN} 1.3.6.1.4.1.248.32.18.1.11.51.5.4.1.5
hmStatusConfigSyncRunningClusterMenuNodesEntryIndexColumns OBJECT-TYPE
    SYNTAX     DisplayString (SIZE(0..127))
    MAX-ACCESS read-only
    STATUS     current
    DESCRIPTION
            "-- empty --"
    ::= { hmStatusConfigSyncRunningClusterMenuNodesEntry 5 }

-- {TABLE} 1.3.6.1.4.1.248.32.18.1.11.51.5.5
hmStatusConfigSyncRunningClusterIgnoredRowsTable OBJECT-TYPE
    SYNTAX     SEQUENCE OF HmStatusConfigSyncRunningClusterIgnoredRowsEntry
    MAX-ACCESS not-accessible
    STATUS     current
    DESCRIPTION
            "-- empty --"
    ::= { hmStatusConfigSyncRunningCluster 5 }

-- {ROW} 1.3.6.1.4.1.248.32.18.1.11.51.5.5.1
hmStatusConfigSyncRunningClusterIgnoredRowsEntry OBJECT-TYPE
    SYNTAX     HmStatusConfigSyncRunningClusterIgnoredRowsEntry
    MAX-ACCESS not-accessible
    STATUS     current
    DESCRIPTION
            ""
    INDEX {
            hmStatusConfigSyncRunningClusterIgnoredRowsEntryIdx
          }
    ::= { hmStatusConfigSyncRunningClusterIgnoredRowsTable 1 }

HmStatusConfigSyncRunningClusterIgnoredRowsEntry ::= SEQUENCE {
            hmStatusConfigSyncRunningClusterIgnoredRowsEntryIdx Integer32,
            hmStatusConfigSyncRunningClusterIgnoredRowsEntryId Integer32,
            hmStatusConfigSyncRunningClusterIgnoredRowsEntryPath DisplayString,
            hmStatusConfigSyncRunningClusterIgnoredRowsEntrySnmpOid DisplayString,
            hmStatusConfigSyncRunningClusterIgnoredRowsEntryRowIndex DisplayString
    }

-- {COLUMN} 1.3.6.1.4.1.248.32.18.1.11.51.5.5.1.1
hmStatusConfigSyncRunningClusterIgnoredRowsEntryIdx OBJECT-TYPE
    SYNTAX     Integer32 (0..2147483647)
    MAX-ACCESS read-only
    STATUS     current
    DESCRIPTION
            "-- empty --"
    ::= { hmStatusConfigSyncRunningClusterIgnoredRowsEntry 1 }

-- {COLUMN} 1.3.6.1.4.1.248.32.18.1.11.51.5.5.1.2
hmStatusConfigSyncRunningClusterIgnoredRowsEntryId OBJECT-TYPE
    SYNTAX     Integer32 (0..2147483647)
    MAX-ACCESS read-only
    STATUS     current
    DESCRIPTION
            "-- empty --"
    ::= { hmStatusConfigSyncRunningClusterIgnoredRowsEntry 2 }

-- {COLUMN} 1.3.6.1.4.1.248.32.18.1.11.51.5.5.1.3
hmStatusConfigSyncRunningClusterIgnoredRowsEntryPath OBJECT-TYPE
    SYNTAX     DisplayString (SIZE(0..127))
    MAX-ACCESS read-only
    STATUS     current
    DESCRIPTION
            "-- empty --"
    ::= { hmStatusConfigSyncRunningClusterIgnoredRowsEntry 3 }

-- {COLUMN} 1.3.6.1.4.1.248.32.18.1.11.51.5.5.1.4
hmStatusConfigSyncRunningClusterIgnoredRowsEntrySnmpOid OBJECT-TYPE
    SYNTAX     DisplayString (SIZE(0..63))
    MAX-ACCESS read-only
    STATUS     current
    DESCRIPTION
            "-- empty --"
    ::= { hmStatusConfigSyncRunningClusterIgnoredRowsEntry 4 }

-- {COLUMN} 1.3.6.1.4.1.248.32.18.1.11.51.5.5.1.5
hmStatusConfigSyncRunningClusterIgnoredRowsEntryRowIndex OBJECT-TYPE
    SYNTAX     DisplayString (SIZE(0..127))
    MAX-ACCESS read-only
    STATUS     current
    DESCRIPTION
            "-- empty --"
    ::= { hmStatusConfigSyncRunningClusterIgnoredRowsEntry 5 }

-- {NODE} 1.3.6.1.4.1.248.32.18.1.11.51.6
hmStatusConfigSyncConfigHistory OBJECT IDENTIFIER ::= { hmStatusConfigSync 6 }

-- {SCALAR} 1.3.6.1.4.1.248.32.18.1.11.51.6.1
hmStatusConfigSyncConfigHistorySnapshotReceivedAt OBJECT-TYPE
    SYNTAX     Counter32
    MAX-ACCESS read-only
    STATUS     current
    DESCRIPTION
            "-- empty --"
    ::= { hmStatusConfigSyncConfigHistory 1 }

-- {SCALAR} 1.3.6.1.4.1.248.32.18.1.11.51.6.2
hmStatusConfigSyncConfigHistorySnapshotTimestamp OBJECT-TYPE
    SYNTAX     DisplayString (SIZE(0..8))
    MAX-ACCESS read-only
    STATUS     current
    DESCRIPTION
            "-- empty --"
    ::= { hmStatusConfigSyncConfigHistory 2 }

-- {TABLE} 1.3.6.1.4.1.248.32.18.1.11.51.6.3
hmStatusConfigSyncConfigHistorySnapshotTable OBJECT-TYPE
    SYNTAX     SEQUENCE OF HmStatusConfigSyncConfigHistorySnapshotEntry
    MAX-ACCESS not-accessible
    STATUS     current
    DESCRIPTION
            "-- empty --"
    ::= { hmStatusConfigSyncConfigHistory 3 }

-- {ROW} 1.3.6.1.4.1.248.32.18.1.11.51.6.3.1
hmStatusConfigSyncConfigHistorySnapshotEntry OBJECT-TYPE
    SYNTAX     HmStatusConfigSyncConfigHistorySnapshotEntry
    MAX-ACCESS not-accessible
    STATUS     current
    DESCRIPTION
            ""
    INDEX {
            hmStatusConfigSyncConfigHistorySnapshotEntryIdx
          }
    ::= { hmStatusConfigSyncConfigHistorySnapshotTable 1 }

HmStatusConfigSyncConfigHistorySnapshotEntry ::= SEQUENCE {
            hmStatusConfigSyncConfigHistorySnapshotEntryIdx Integer32,
            hmStatusConfigSyncConfigHistorySnapshotEntryPath DisplayString,
            hmStatusConfigSyncConfigHistorySnapshotEntryValue DisplayString
    }

-- {COLUMN} 1.3.6.1.4.1.248.32.18.1.11.51.6.3.1.1
hmStatusConfigSyncConfigHistorySnapshotEntryIdx OBJECT-TYPE
    SYNTAX     Integer32 (0..2147483647)
    MAX-ACCESS read-only
    STATUS     current
    DESCRIPTION
            "-- empty --"
    ::= { hmStatusConfigSyncConfigHistorySnapshotEntry 1 }

-- {COLUMN} 1.3.6.1.4.1.248.32.18.1.11.51.6.3.1.2
hmStatusConfigSyncConfigHistorySnapshotEntryPath OBJECT-TYPE
    SYNTAX     DisplayString (SIZE(0..127))
    MAX-ACCESS read-only
    STATUS     current
    DESCRIPTION
            "-- empty --"
    ::= { hmStatusConfigSyncConfigHistorySnapshotEntry 2 }

-- {COLUMN} 1.3.6.1.4.1.248.32.18.1.11.51.6.3.1.3
hmStatusConfigSyncConfigHistorySnapshotEntryValue OBJECT-TYPE
    SYNTAX     DisplayString (SIZE(0..254))
    MAX-ACCESS read-only
    STATUS     current
    DESCRIPTION
            "-- empty --"
    ::= { hmStatusConfigSyncConfigHistorySnapshotEntry 3 }

-- {SCALAR} 1.3.6.1.4.1.248.32.18.1.11.51.6.4
hmStatusConfigSyncConfigHistoryModifications OBJECT-TYPE
    SYNTAX     Integer32 (0..2147483647)
    MAX-ACCESS read-only
    STATUS     current
    DESCRIPTION
            "-- empty --"
    ::= { hmStatusConfigSyncConfigHistory 4 }

-- {SCALAR} 1.3.6.1.4.1.248.32.18.1.11.51.6.5
hmStatusConfigSyncConfigHistoryRenewSnapshot OBJECT-TYPE
    SYNTAX     DisplayString
    MAX-ACCESS read-write
    STATUS     current
    DESCRIPTION
            "-- empty --"
    ::= { hmStatusConfigSyncConfigHistory 5 }

-- {TABLE} 1.3.6.1.4.1.248.32.18.1.11.51.7
hmStatusConfigSyncReplicasTable OBJECT-TYPE
    SYNTAX     SEQUENCE OF HmStatusConfigSyncReplicasEntry
    MAX-ACCESS not-accessible
    STATUS     current
    DESCRIPTION
            "-- empty --"
    ::= { hmStatusConfigSync 7 }

-- {ROW} 1.3.6.1.4.1.248.32.18.1.11.51.7.1
hmStatusConfigSyncReplicasEntry OBJECT-TYPE
    SYNTAX     HmStatusConfigSyncReplicasEntry
    MAX-ACCESS not-accessible
    STATUS     current
    DESCRIPTION
            ""
    INDEX {
            hmStatusConfigSyncReplicasEntryIdx
          }
    ::= { hmStatusConfigSyncReplicasTable 1 }

HmStatusConfigSyncReplicasEntry ::= SEQUENCE {
            hmStatusConfigSyncReplicasEntryIdx Integer32,
            hmStatusConfigSyncReplicasEntryId Integer32,
            hmStatusConfigSyncReplicasEntryAddress DisplayString,
            hmStatusConfigSyncReplicasEntryResolvedAddress DisplayString,
            hmStatusConfigSyncReplicasEntryConnectionState INTEGER,
            hmStatusConfigSyncReplicasEntryState INTEGER,
            hmStatusConfigSyncReplicasEntryClusterTime Integer32,
            hmStatusConfigSyncReplicasEntryLastMessageReceivedAt DisplayString,
            hmStatusConfigSyncReplicasEntryLastMessageReceivedAtNumerical Counter32,
            hmStatusConfigSyncReplicasEntryLastUpdateReceivedAt DisplayString,
            hmStatusConfigSyncReplicasEntryLastUpdateReceivedAtNumerical Counter32,
            hmStatusConfigSyncReplicasEntryLastMessageSentAt DisplayString,
            hmStatusConfigSyncReplicasEntryLastMessageSentAtNumerical Counter32
    }

-- {COLUMN} 1.3.6.1.4.1.248.32.18.1.11.51.7.1.1
hmStatusConfigSyncReplicasEntryIdx OBJECT-TYPE
    SYNTAX     Integer32 (0..65535)
    MAX-ACCESS read-only
    STATUS     current
    DESCRIPTION
            "-- empty --"
    ::= { hmStatusConfigSyncReplicasEntry 1 }

-- {COLUMN} 1.3.6.1.4.1.248.32.18.1.11.51.7.1.2
hmStatusConfigSyncReplicasEntryId OBJECT-TYPE
    SYNTAX     Integer32 (0..65535)
    MAX-ACCESS read-only
    STATUS     current
    DESCRIPTION
            "-- empty --"
    ::= { hmStatusConfigSyncReplicasEntry 2 }

-- {COLUMN} 1.3.6.1.4.1.248.32.18.1.11.51.7.1.3
hmStatusConfigSyncReplicasEntryAddress OBJECT-TYPE
    SYNTAX     DisplayString (SIZE(0..255))
    MAX-ACCESS read-only
    STATUS     current
    DESCRIPTION
            "-- empty --"
    ::= { hmStatusConfigSyncReplicasEntry 3 }

-- {COLUMN} 1.3.6.1.4.1.248.32.18.1.11.51.7.1.4
hmStatusConfigSyncReplicasEntryResolvedAddress OBJECT-TYPE
    SYNTAX     DisplayString (SIZE(0..255))
    MAX-ACCESS read-only
    STATUS     current
    DESCRIPTION
            "-- empty --"
    ::= { hmStatusConfigSyncReplicasEntry 4 }

-- {COLUMN} 1.3.6.1.4.1.248.32.18.1.11.51.7.1.5
hmStatusConfigSyncReplicasEntryConnectionState OBJECT-TYPE
    SYNTAX     INTEGER {
                  eNotConnected (0),
                  eDnsLookup (1),
                  eConnecting (2),
                  eOk (3),
                  eDnsLookupFailure (4),
                  eTcpConnectFailure (5),
                  eTlsConnectFailure (6),
                  eClosedByReplica (7),
                  eIncompatibleFirmware (8),
                  eTransferError (9)
            }
    MAX-ACCESS read-only
    STATUS     current
    DESCRIPTION
            "-- empty --"
    ::= { hmStatusConfigSyncReplicasEntry 5 }

-- {COLUMN} 1.3.6.1.4.1.248.32.18.1.11.51.7.1.6
hmStatusConfigSyncReplicasEntryState OBJECT-TYPE
    SYNTAX     INTEGER {
                  eUnknown (0),
                  eMissingMessages (1),
                  eMissingUpdates (2),
                  eOldCluster (3),
                  eNewCluster (4),
                  eNoSnapshot (5),
                  eTimeUnknown (6),
                  eOk (7)
            }
    MAX-ACCESS read-only
    STATUS     current
    DESCRIPTION
            "-- empty --"
    ::= { hmStatusConfigSyncReplicasEntry 6 }

-- {COLUMN} 1.3.6.1.4.1.248.32.18.1.11.51.7.1.7
hmStatusConfigSyncReplicasEntryClusterTime OBJECT-TYPE
    SYNTAX     Integer32 (0..2147483647)
    MAX-ACCESS read-only
    STATUS     current
    DESCRIPTION
            "-- empty --"
    ::= { hmStatusConfigSyncReplicasEntry 7 }

-- {COLUMN} 1.3.6.1.4.1.248.32.18.1.11.51.7.1.8
hmStatusConfigSyncReplicasEntryLastMessageReceivedAt OBJECT-TYPE
    SYNTAX     DisplayString (SIZE(0..255))
    MAX-ACCESS read-only
    STATUS     current
    DESCRIPTION
            "-- empty --"
    ::= { hmStatusConfigSyncReplicasEntry 8 }

-- {COLUMN} 1.3.6.1.4.1.248.32.18.1.11.51.7.1.9
hmStatusConfigSyncReplicasEntryLastMessageReceivedAtNumerical OBJECT-TYPE
    SYNTAX     Counter32
    MAX-ACCESS read-only
    STATUS     current
    DESCRIPTION
            "-- empty --"
    ::= { hmStatusConfigSyncReplicasEntry 9 }

-- {COLUMN} 1.3.6.1.4.1.248.32.18.1.11.51.7.1.10
hmStatusConfigSyncReplicasEntryLastUpdateReceivedAt OBJECT-TYPE
    SYNTAX     DisplayString (SIZE(0..255))
    MAX-ACCESS read-only
    STATUS     current
    DESCRIPTION
            "-- empty --"
    ::= { hmStatusConfigSyncReplicasEntry 10 }

-- {COLUMN} 1.3.6.1.4.1.248.32.18.1.11.51.7.1.11
hmStatusConfigSyncReplicasEntryLastUpdateReceivedAtNumerical OBJECT-TYPE
    SYNTAX     Counter32
    MAX-ACCESS read-only
    STATUS     current
    DESCRIPTION
            "-- empty --"
    ::= { hmStatusConfigSyncReplicasEntry 11 }

-- {COLUMN} 1.3.6.1.4.1.248.32.18.1.11.51.7.1.12
hmStatusConfigSyncReplicasEntryLastMessageSentAt OBJECT-TYPE
    SYNTAX     DisplayString (SIZE(0..255))
    MAX-ACCESS read-only
    STATUS     current
    DESCRIPTION
            "-- empty --"
    ::= { hmStatusConfigSyncReplicasEntry 12 }

-- {COLUMN} 1.3.6.1.4.1.248.32.18.1.11.51.7.1.13
hmStatusConfigSyncReplicasEntryLastMessageSentAtNumerical OBJECT-TYPE
    SYNTAX     Counter32
    MAX-ACCESS read-only
    STATUS     current
    DESCRIPTION
            "-- empty --"
    ::= { hmStatusConfigSyncReplicasEntry 13 }

-- {NODE} 1.3.6.1.4.1.248.32.18.1.11.65
hmStatusConfigLl2m OBJECT IDENTIFIER ::= { hmStatusConfig 65 }

-- {SCALAR} 1.3.6.1.4.1.248.32.18.1.11.65.1
hmStatusConfigLl2mRxPackets OBJECT-TYPE
    SYNTAX     Integer32 (0..2147483647)
    MAX-ACCESS read-only
    STATUS     current
    DESCRIPTION
            "-- empty --"
    ::= { hmStatusConfigLl2m 1 }

-- {SCALAR} 1.3.6.1.4.1.248.32.18.1.11.65.2
hmStatusConfigLl2mRxBroadcastPackets OBJECT-TYPE
    SYNTAX     Integer32 (0..2147483647)
    MAX-ACCESS read-only
    STATUS     current
    DESCRIPTION
            "-- empty --"
    ::= { hmStatusConfigLl2m 2 }

-- {SCALAR} 1.3.6.1.4.1.248.32.18.1.11.65.3
hmStatusConfigLl2mRxMulticastPackets OBJECT-TYPE
    SYNTAX     Integer32 (0..2147483647)
    MAX-ACCESS read-only
    STATUS     current
    DESCRIPTION
            "-- empty --"
    ::= { hmStatusConfigLl2m 3 }

-- {SCALAR} 1.3.6.1.4.1.248.32.18.1.11.65.4
hmStatusConfigLl2mRxUnicastPackets OBJECT-TYPE
    SYNTAX     Integer32 (0..2147483647)
    MAX-ACCESS read-only
    STATUS     current
    DESCRIPTION
            "-- empty --"
    ::= { hmStatusConfigLl2m 4 }

-- {SCALAR} 1.3.6.1.4.1.248.32.18.1.11.65.5
hmStatusConfigLl2mRxDiscard OBJECT-TYPE
    SYNTAX     Integer32 (0..2147483647)
    MAX-ACCESS read-only
    STATUS     current
    DESCRIPTION
            "-- empty --"
    ::= { hmStatusConfigLl2m 5 }

-- {SCALAR} 1.3.6.1.4.1.248.32.18.1.11.65.6
hmStatusConfigLl2mRxMalformed OBJECT-TYPE
    SYNTAX     Integer32 (0..2147483647)
    MAX-ACCESS read-only
    STATUS     current
    DESCRIPTION
            "-- empty --"
    ::= { hmStatusConfigLl2m 6 }

-- {NODE} 1.3.6.1.4.1.248.32.18.1.11.65.20
hmStatusConfigLl2mServer OBJECT IDENTIFIER ::= { hmStatusConfigLl2m 20 }

-- {SCALAR} 1.3.6.1.4.1.248.32.18.1.11.65.20.1
hmStatusConfigLl2mServerRxPackets OBJECT-TYPE
    SYNTAX     Integer32 (0..2147483647)
    MAX-ACCESS read-only
    STATUS     current
    DESCRIPTION
            "-- empty --"
    ::= { hmStatusConfigLl2mServer 1 }

-- {SCALAR} 1.3.6.1.4.1.248.32.18.1.11.65.20.2
hmStatusConfigLl2mServerRxBroadcastPackets OBJECT-TYPE
    SYNTAX     Integer32 (0..2147483647)
    MAX-ACCESS read-only
    STATUS     current
    DESCRIPTION
            "-- empty --"
    ::= { hmStatusConfigLl2mServer 2 }

-- {SCALAR} 1.3.6.1.4.1.248.32.18.1.11.65.20.3
hmStatusConfigLl2mServerRxMulticastPackets OBJECT-TYPE
    SYNTAX     Integer32 (0..2147483647)
    MAX-ACCESS read-only
    STATUS     current
    DESCRIPTION
            "-- empty --"
    ::= { hmStatusConfigLl2mServer 3 }

-- {SCALAR} 1.3.6.1.4.1.248.32.18.1.11.65.20.4
hmStatusConfigLl2mServerRxUnicastPackets OBJECT-TYPE
    SYNTAX     Integer32 (0..2147483647)
    MAX-ACCESS read-only
    STATUS     current
    DESCRIPTION
            "-- empty --"
    ::= { hmStatusConfigLl2mServer 4 }

-- {SCALAR} 1.3.6.1.4.1.248.32.18.1.11.65.20.5
hmStatusConfigLl2mServerRxDiscard OBJECT-TYPE
    SYNTAX     Integer32 (0..2147483647)
    MAX-ACCESS read-only
    STATUS     current
    DESCRIPTION
            "-- empty --"
    ::= { hmStatusConfigLl2mServer 5 }

-- {SCALAR} 1.3.6.1.4.1.248.32.18.1.11.65.20.99
hmStatusConfigLl2mServerDeleteValues OBJECT-TYPE
    SYNTAX     DisplayString
    MAX-ACCESS read-write
    STATUS     current
    DESCRIPTION
            "-- empty --"
    ::= { hmStatusConfigLl2mServer 99 }

-- {NODE} 1.3.6.1.4.1.248.32.18.1.11.65.30
hmStatusConfigLl2mClient OBJECT IDENTIFIER ::= { hmStatusConfigLl2m 30 }

-- {SCALAR} 1.3.6.1.4.1.248.32.18.1.11.65.30.1
hmStatusConfigLl2mClientRxPackets OBJECT-TYPE
    SYNTAX     Integer32 (0..2147483647)
    MAX-ACCESS read-only
    STATUS     current
    DESCRIPTION
            "-- empty --"
    ::= { hmStatusConfigLl2mClient 1 }

-- {SCALAR} 1.3.6.1.4.1.248.32.18.1.11.65.30.2
hmStatusConfigLl2mClientRxBroadcastPackets OBJECT-TYPE
    SYNTAX     Integer32 (0..2147483647)
    MAX-ACCESS read-only
    STATUS     current
    DESCRIPTION
            "-- empty --"
    ::= { hmStatusConfigLl2mClient 2 }

-- {SCALAR} 1.3.6.1.4.1.248.32.18.1.11.65.30.3
hmStatusConfigLl2mClientRxMulticastPackets OBJECT-TYPE
    SYNTAX     Integer32 (0..2147483647)
    MAX-ACCESS read-only
    STATUS     current
    DESCRIPTION
            "-- empty --"
    ::= { hmStatusConfigLl2mClient 3 }

-- {SCALAR} 1.3.6.1.4.1.248.32.18.1.11.65.30.4
hmStatusConfigLl2mClientRxUnicastPackets OBJECT-TYPE
    SYNTAX     Integer32 (0..2147483647)
    MAX-ACCESS read-only
    STATUS     current
    DESCRIPTION
            "-- empty --"
    ::= { hmStatusConfigLl2mClient 4 }

-- {SCALAR} 1.3.6.1.4.1.248.32.18.1.11.65.30.5
hmStatusConfigLl2mClientRxDiscard OBJECT-TYPE
    SYNTAX     Integer32 (0..2147483647)
    MAX-ACCESS read-only
    STATUS     current
    DESCRIPTION
            "-- empty --"
    ::= { hmStatusConfigLl2mClient 5 }

-- {SCALAR} 1.3.6.1.4.1.248.32.18.1.11.65.30.99
hmStatusConfigLl2mClientDeleteValues OBJECT-TYPE
    SYNTAX     DisplayString
    MAX-ACCESS read-write
    STATUS     current
    DESCRIPTION
            "-- empty --"
    ::= { hmStatusConfigLl2mClient 99 }

-- {SCALAR} 1.3.6.1.4.1.248.32.18.1.11.65.99
hmStatusConfigLl2mDeleteValues OBJECT-TYPE
    SYNTAX     DisplayString
    MAX-ACCESS read-write
    STATUS     current
    DESCRIPTION
            "-- empty --"
    ::= { hmStatusConfigLl2m 99 }

-- {NODE} 1.3.6.1.4.1.248.32.18.1.11.70
hmStatusConfigDownloadStatus OBJECT IDENTIFIER ::= { hmStatusConfig 70 }

-- {SCALAR} 1.3.6.1.4.1.248.32.18.1.11.70.1
hmStatusConfigDownloadStatusFirmwareSuccesses OBJECT-TYPE
    SYNTAX     Integer32 (0..2147483647)
    MAX-ACCESS read-only
    STATUS     current
    DESCRIPTION
            "-- empty --"
    ::= { hmStatusConfigDownloadStatus 1 }

-- {SCALAR} 1.3.6.1.4.1.248.32.18.1.11.70.2
hmStatusConfigDownloadStatusFirmwareFailures OBJECT-TYPE
    SYNTAX     Integer32 (0..2147483647)
    MAX-ACCESS read-only
    STATUS     current
    DESCRIPTION
            "-- empty --"
    ::= { hmStatusConfigDownloadStatus 2 }

-- {SCALAR} 1.3.6.1.4.1.248.32.18.1.11.70.3
hmStatusConfigDownloadStatusConfigurationSuccesses OBJECT-TYPE
    SYNTAX     Integer32 (0..2147483647)
    MAX-ACCESS read-only
    STATUS     current
    DESCRIPTION
            "-- empty --"
    ::= { hmStatusConfigDownloadStatus 3 }

-- {SCALAR} 1.3.6.1.4.1.248.32.18.1.11.70.4
hmStatusConfigDownloadStatusConfigurationFailures OBJECT-TYPE
    SYNTAX     Integer32 (0..2147483647)
    MAX-ACCESS read-only
    STATUS     current
    DESCRIPTION
            "-- empty --"
    ::= { hmStatusConfigDownloadStatus 4 }

-- {SCALAR} 1.3.6.1.4.1.248.32.18.1.11.70.5
hmStatusConfigDownloadStatusScriptSuccesses OBJECT-TYPE
    SYNTAX     Integer32 (0..2147483647)
    MAX-ACCESS read-only
    STATUS     current
    DESCRIPTION
            "-- empty --"
    ::= { hmStatusConfigDownloadStatus 5 }

-- {SCALAR} 1.3.6.1.4.1.248.32.18.1.11.70.6
hmStatusConfigDownloadStatusScriptFailures OBJECT-TYPE
    SYNTAX     Integer32 (0..2147483647)
    MAX-ACCESS read-only
    STATUS     current
    DESCRIPTION
            "-- empty --"
    ::= { hmStatusConfigDownloadStatus 6 }

-- {SCALAR} 1.3.6.1.4.1.248.32.18.1.11.70.7
hmStatusConfigDownloadStatusFileSuccesses OBJECT-TYPE
    SYNTAX     Integer32 (0..2147483647)
    MAX-ACCESS read-only
    STATUS     current
    DESCRIPTION
            "-- empty --"
    ::= { hmStatusConfigDownloadStatus 7 }

-- {SCALAR} 1.3.6.1.4.1.248.32.18.1.11.70.8
hmStatusConfigDownloadStatusFileFailures OBJECT-TYPE
    SYNTAX     Integer32 (0..2147483647)
    MAX-ACCESS read-only
    STATUS     current
    DESCRIPTION
            "-- empty --"
    ::= { hmStatusConfigDownloadStatus 8 }

-- {TABLE} 1.3.6.1.4.1.248.32.18.1.11.70.20
hmStatusConfigDownloadStatusLastOperationsTable OBJECT-TYPE
    SYNTAX     SEQUENCE OF HmStatusConfigDownloadStatusLastOperationsEntry
    MAX-ACCESS not-accessible
    STATUS     current
    DESCRIPTION
            "-- empty --"
    ::= { hmStatusConfigDownloadStatus 20 }

-- {ROW} 1.3.6.1.4.1.248.32.18.1.11.70.20.1
hmStatusConfigDownloadStatusLastOperationsEntry OBJECT-TYPE
    SYNTAX     HmStatusConfigDownloadStatusLastOperationsEntry
    MAX-ACCESS not-accessible
    STATUS     current
    DESCRIPTION
            ""
    INDEX {
            hmStatusConfigDownloadStatusLastOperationsEntryIndex
          }
    ::= { hmStatusConfigDownloadStatusLastOperationsTable 1 }

HmStatusConfigDownloadStatusLastOperationsEntry ::= SEQUENCE {
            hmStatusConfigDownloadStatusLastOperationsEntryIndex Integer32,
            hmStatusConfigDownloadStatusLastOperationsEntryIdentifier Integer32,
            hmStatusConfigDownloadStatusLastOperationsEntryType INTEGER,
            hmStatusConfigDownloadStatusLastOperationsEntryUrl DisplayString,
            hmStatusConfigDownloadStatusLastOperationsEntryStatus INTEGER,
            hmStatusConfigDownloadStatusLastOperationsEntryFailureReason DisplayString
    }

-- {COLUMN} 1.3.6.1.4.1.248.32.18.1.11.70.20.1.1
hmStatusConfigDownloadStatusLastOperationsEntryIndex OBJECT-TYPE
    SYNTAX     Integer32 (0..2147483647)
    MAX-ACCESS read-only
    STATUS     current
    DESCRIPTION
            "-- empty --"
    ::= { hmStatusConfigDownloadStatusLastOperationsEntry 1 }

-- {COLUMN} 1.3.6.1.4.1.248.32.18.1.11.70.20.1.2
hmStatusConfigDownloadStatusLastOperationsEntryIdentifier OBJECT-TYPE
    SYNTAX     Integer32 (0..2147483647)
    MAX-ACCESS read-only
    STATUS     current
    DESCRIPTION
            "-- empty --"
    ::= { hmStatusConfigDownloadStatusLastOperationsEntry 2 }

-- {COLUMN} 1.3.6.1.4.1.248.32.18.1.11.70.20.1.3
hmStatusConfigDownloadStatusLastOperationsEntryType OBJECT-TYPE
    SYNTAX     INTEGER {
                  eConfiguration (0),
                  eFirmware (1),
                  eScript (2),
                  eFile (3)
            }
    MAX-ACCESS read-only
    STATUS     current
    DESCRIPTION
            "-- empty --"
    ::= { hmStatusConfigDownloadStatusLastOperationsEntry 3 }

-- {COLUMN} 1.3.6.1.4.1.248.32.18.1.11.70.20.1.4
hmStatusConfigDownloadStatusLastOperationsEntryUrl OBJECT-TYPE
    SYNTAX     DisplayString (SIZE(0..252))
    MAX-ACCESS read-only
    STATUS     current
    DESCRIPTION
            "-- empty --"
    ::= { hmStatusConfigDownloadStatusLastOperationsEntry 4 }

-- {COLUMN} 1.3.6.1.4.1.248.32.18.1.11.70.20.1.5
hmStatusConfigDownloadStatusLastOperationsEntryStatus OBJECT-TYPE
    SYNTAX     INTEGER {
                  eIdle (0),
                  ePending (1),
                  eSuccess (2),
                  eFailure (3),
                  eUnknown (4)
            }
    MAX-ACCESS read-only
    STATUS     current
    DESCRIPTION
            "-- empty --"
    ::= { hmStatusConfigDownloadStatusLastOperationsEntry 5 }

-- {COLUMN} 1.3.6.1.4.1.248.32.18.1.11.70.20.1.6
hmStatusConfigDownloadStatusLastOperationsEntryFailureReason OBJECT-TYPE
    SYNTAX     DisplayString (SIZE(0..100))
    MAX-ACCESS read-only
    STATUS     current
    DESCRIPTION
            "-- empty --"
    ::= { hmStatusConfigDownloadStatusLastOperationsEntry 6 }

-- {SCALAR} 1.3.6.1.4.1.248.32.18.1.11.70.99
hmStatusConfigDownloadStatusDeleteValues OBJECT-TYPE
    SYNTAX     DisplayString
    MAX-ACCESS read-write
    STATUS     current
    DESCRIPTION
            "-- empty --"
    ::= { hmStatusConfigDownloadStatus 99 }

-- {SCALAR} 1.3.6.1.4.1.248.32.18.1.11.248
hmStatusConfigDefaultPasswordActive OBJECT-TYPE
    SYNTAX     INTEGER {
                  eNo (0),
                  eYes (1)
            }
    MAX-ACCESS read-only
    STATUS     current
    DESCRIPTION
            "-- empty --"
    ::= { hmStatusConfig 248 }

-- {NODE} 1.3.6.1.4.1.248.32.18.1.12
hmStatusQueue OBJECT IDENTIFIER ::= { hmStatus 12 }

-- {SCALAR} 1.3.6.1.4.1.248.32.18.1.12.1
hmStatusQueueLanHeapPackets OBJECT-TYPE
    SYNTAX     Integer32 (0..2147483647)
    MAX-ACCESS read-only
    STATUS     current
    DESCRIPTION
            "-- empty --"
    ::= { hmStatusQueue 1 }

-- {SCALAR} 1.3.6.1.4.1.248.32.18.1.12.2
hmStatusQueueQueuePackets OBJECT-TYPE
    SYNTAX     Integer32 (0..2147483647)
    MAX-ACCESS read-only
    STATUS     current
    DESCRIPTION
            "LAN Queue Packets"
    ::= { hmStatusQueue 2 }

-- {SCALAR} 1.3.6.1.4.1.248.32.18.1.12.3
hmStatusQueueWanHeapPackets OBJECT-TYPE
    SYNTAX     Integer32 (0..2147483647)
    MAX-ACCESS read-only
    STATUS     current
    DESCRIPTION
            "-- empty --"
    ::= { hmStatusQueue 3 }

-- {SCALAR} 1.3.6.1.4.1.248.32.18.1.12.4
hmStatusQueueWanQueuePackets OBJECT-TYPE
    SYNTAX     Integer32 (0..2147483647)
    MAX-ACCESS read-only
    STATUS     current
    DESCRIPTION
            "-- empty --"
    ::= { hmStatusQueue 4 }

-- {SCALAR} 1.3.6.1.4.1.248.32.18.1.12.7
hmStatusQueueArpQueryQueuePackets OBJECT-TYPE
    SYNTAX     Integer32 (0..2147483647)
    MAX-ACCESS read-only
    STATUS     current
    DESCRIPTION
            "-- empty --"
    ::= { hmStatusQueue 7 }

-- {SCALAR} 1.3.6.1.4.1.248.32.18.1.12.8
hmStatusQueueArpQueuePackets OBJECT-TYPE
    SYNTAX     Integer32 (0..2147483647)
    MAX-ACCESS read-only
    STATUS     current
    DESCRIPTION
            "-- empty --"
    ::= { hmStatusQueue 8 }

-- {SCALAR} 1.3.6.1.4.1.248.32.18.1.12.9
hmStatusQueueIpQueuePackets OBJECT-TYPE
    SYNTAX     Integer32 (0..2147483647)
    MAX-ACCESS read-only
    STATUS     current
    DESCRIPTION
            "-- empty --"
    ::= { hmStatusQueue 9 }

-- {SCALAR} 1.3.6.1.4.1.248.32.18.1.12.10
hmStatusQueueIpUrgentQueuePackets OBJECT-TYPE
    SYNTAX     Integer32 (0..2147483647)
    MAX-ACCESS read-only
    STATUS     current
    DESCRIPTION
            "-- empty --"
    ::= { hmStatusQueue 10 }

-- {SCALAR} 1.3.6.1.4.1.248.32.18.1.12.11
hmStatusQueueIcmpQueuePackets OBJECT-TYPE
    SYNTAX     Integer32 (0..2147483647)
    MAX-ACCESS read-only
    STATUS     current
    DESCRIPTION
            "-- empty --"
    ::= { hmStatusQueue 11 }

-- {SCALAR} 1.3.6.1.4.1.248.32.18.1.12.12
hmStatusQueueTcpQueuePackets OBJECT-TYPE
    SYNTAX     Integer32 (0..2147483647)
    MAX-ACCESS read-only
    STATUS     current
    DESCRIPTION
            "-- empty --"
    ::= { hmStatusQueue 12 }

-- {SCALAR} 1.3.6.1.4.1.248.32.18.1.12.13
hmStatusQueueTftpServerQueuePackets OBJECT-TYPE
    SYNTAX     Integer32 (0..2147483647)
    MAX-ACCESS read-only
    STATUS     current
    DESCRIPTION
            "-- empty --"
    ::= { hmStatusQueue 13 }

-- {SCALAR} 1.3.6.1.4.1.248.32.18.1.12.14
hmStatusQueueSnmpQueuePackets OBJECT-TYPE
    SYNTAX     Integer32 (0..2147483647)
    MAX-ACCESS read-only
    STATUS     current
    DESCRIPTION
            "-- empty --"
    ::= { hmStatusQueue 14 }

-- {SCALAR} 1.3.6.1.4.1.248.32.18.1.12.22
hmStatusQueueProtHeapPackets OBJECT-TYPE
    SYNTAX     Integer32 (0..2147483647)
    MAX-ACCESS read-only
    STATUS     current
    DESCRIPTION
            "-- empty --"
    ::= { hmStatusQueue 22 }

-- {SCALAR} 1.3.6.1.4.1.248.32.18.1.12.27
hmStatusQueueDhcpServerQueuePackets OBJECT-TYPE
    SYNTAX     Integer32 (0..2147483647)
    MAX-ACCESS read-only
    STATUS     current
    DESCRIPTION
            "-- empty --"
    ::= { hmStatusQueue 27 }

-- {SCALAR} 1.3.6.1.4.1.248.32.18.1.12.28
hmStatusQueueDhcpClientQueuePackets OBJECT-TYPE
    SYNTAX     Integer32 (0..2147483647)
    MAX-ACCESS read-only
    STATUS     current
    DESCRIPTION
            "-- empty --"
    ::= { hmStatusQueue 28 }

-- {SCALAR} 1.3.6.1.4.1.248.32.18.1.12.29
hmStatusQueueIprRipQueuePackets OBJECT-TYPE
    SYNTAX     Integer32 (0..2147483647)
    MAX-ACCESS read-only
    STATUS     current
    DESCRIPTION
            "-- empty --"
    ::= { hmStatusQueue 29 }

-- {SCALAR} 1.3.6.1.4.1.248.32.18.1.12.30
hmStatusQueueDnsTxQueuePackets OBJECT-TYPE
    SYNTAX     Integer32 (0..2147483647)
    MAX-ACCESS read-only
    STATUS     current
    DESCRIPTION
            "-- empty --"
    ::= { hmStatusQueue 30 }

-- {SCALAR} 1.3.6.1.4.1.248.32.18.1.12.31
hmStatusQueueDnsRxQueuePackets OBJECT-TYPE
    SYNTAX     Integer32 (0..2147483647)
    MAX-ACCESS read-only
    STATUS     current
    DESCRIPTION
            "-- empty --"
    ::= { hmStatusQueue 31 }

-- {SCALAR} 1.3.6.1.4.1.248.32.18.1.12.40
hmStatusQueueWlanManagementHeapPackets OBJECT-TYPE
    SYNTAX     Integer32 (0..2147483647)
    MAX-ACCESS read-only
    STATUS     current
    DESCRIPTION
            "-- empty --"
    ::= { hmStatusQueue 40 }

-- {TABLE} 1.3.6.1.4.1.248.32.18.1.13
hmStatusConnectionTable OBJECT-TYPE
    SYNTAX     SEQUENCE OF HmStatusConnectionEntry
    MAX-ACCESS not-accessible
    STATUS     current
    DESCRIPTION
            "-- empty --"
    ::= { hmStatus 13 }

-- {ROW} 1.3.6.1.4.1.248.32.18.1.13.1
hmStatusConnectionEntry OBJECT-TYPE
    SYNTAX     HmStatusConnectionEntry
    MAX-ACCESS not-accessible
    STATUS     current
    DESCRIPTION
            ""
    INDEX {
            hmStatusConnectionEntryIfc
          }
    ::= { hmStatusConnectionTable 1 }

HmStatusConnectionEntry ::= SEQUENCE {
            hmStatusConnectionEntryIfc INTEGER,
            hmStatusConnectionEntryConnections Integer32,
            hmStatusConnectionEntryActive Integer32,
            hmStatusConnectionEntryPassive Integer32,
            hmStatusConnectionEntryErrors Integer32,
            hmStatusConnectionEntryConTime DisplayString,
            hmStatusConnectionEntryCharge Integer32
    }

-- {COLUMN} 1.3.6.1.4.1.248.32.18.1.13.1.1
hmStatusConnectionEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusConnectionEntry 1 }

-- {COLUMN} 1.3.6.1.4.1.248.32.18.1.13.1.2
hmStatusConnectionEntryConnections OBJECT-TYPE
    SYNTAX     Integer32 (0..2147483647)
    MAX-ACCESS read-only
    STATUS     current
    DESCRIPTION
            "-- empty --"
    ::= { hmStatusConnectionEntry 2 }

-- {COLUMN} 1.3.6.1.4.1.248.32.18.1.13.1.3
hmStatusConnectionEntryActive OBJECT-TYPE
    SYNTAX     Integer32 (0..2147483647)
    MAX-ACCESS read-only
    STATUS     current
    DESCRIPTION
            "-- empty --"
    ::= { hmStatusConnectionEntry 3 }

-- {COLUMN} 1.3.6.1.4.1.248.32.18.1.13.1.4
hmStatusConnectionEntryPassive OBJECT-TYPE
    SYNTAX     Integer32 (0..2147483647)
    MAX-ACCESS read-only
    STATUS     current
    DESCRIPTION
            "-- empty --"
    ::= { hmStatusConnectionEntry 4 }

-- {COLUMN} 1.3.6.1.4.1.248.32.18.1.13.1.5
hmStatusConnectionEntryErrors OBJECT-TYPE
    SYNTAX     Integer32 (0..2147483647)
    MAX-ACCESS read-only
    STATUS     current
    DESCRIPTION
            "-- empty --"
    ::= { hmStatusConnectionEntry 5 }

-- {COLUMN} 1.3.6.1.4.1.248.32.18.1.13.1.6
hmStatusConnectionEntryConTime OBJECT-TYPE
    SYNTAX     DisplayString (SIZE(0..255))
    MAX-ACCESS read-only
    STATUS     current
    DESCRIPTION
            "-- empty --"
    ::= { hmStatusConnectionEntry 6 }

-- {COLUMN} 1.3.6.1.4.1.248.32.18.1.13.1.7
hmStatusConnectionEntryCharge OBJECT-TYPE
    SYNTAX     Integer32 (0..2147483647)
    MAX-ACCESS read-only
    STATUS     current
    DESCRIPTION
            "-- empty --"
    ::= { hmStatusConnectionEntry 7 }

-- {TABLE} 1.3.6.1.4.1.248.32.18.1.14
hmStatusInfoConnectionTable OBJECT-TYPE
    SYNTAX     SEQUENCE OF HmStatusInfoConnectionEntry
    MAX-ACCESS not-accessible
    STATUS     current
    DESCRIPTION
            "-- empty --"
    ::= { hmStatus 14 }

-- {ROW} 1.3.6.1.4.1.248.32.18.1.14.1
hmStatusInfoConnectionEntry OBJECT-TYPE
    SYNTAX     HmStatusInfoConnectionEntry
    MAX-ACCESS not-accessible
    STATUS     current
    DESCRIPTION
            ""
    INDEX {
            hmStatusInfoConnectionEntryIfc
          }
    ::= { hmStatusInfoConnectionTable 1 }

HmStatusInfoConnectionEntry ::= SEQUENCE {
            hmStatusInfoConnectionEntryIfc INTEGER,
            hmStatusInfoConnectionEntryStatus DisplayString,
            hmStatusInfoConnectionEntryMode INTEGER,
            hmStatusInfoConnectionEntryDialupRemote DisplayString,
            hmStatusInfoConnectionEntryPeer DisplayString,
            hmStatusInfoConnectionEntryB1Dt Integer32,
            hmStatusInfoConnectionEntryB2Dt Integer32
    }

-- {COLUMN} 1.3.6.1.4.1.248.32.18.1.14.1.1
hmStatusInfoConnectionEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusInfoConnectionEntry 1 }

-- {COLUMN} 1.3.6.1.4.1.248.32.18.1.14.1.2
hmStatusInfoConnectionEntryStatus OBJECT-TYPE
    SYNTAX     DisplayString (SIZE(0..16))
    MAX-ACCESS read-only
    STATUS     current
    DESCRIPTION
            "-- empty --"
    ::= { hmStatusInfoConnectionEntry 2 }

-- {COLUMN} 1.3.6.1.4.1.248.32.18.1.14.1.3
hmStatusInfoConnectionEntryMode OBJECT-TYPE
    SYNTAX     INTEGER {
                  eUnknown (0),
                  eActive (4),
                  ePassive (5),
                  eCallback (9)
            }
    MAX-ACCESS read-only
    STATUS     current
    DESCRIPTION
            "-- empty --"
    ::= { hmStatusInfoConnectionEntry 3 }

-- {COLUMN} 1.3.6.1.4.1.248.32.18.1.14.1.4
hmStatusInfoConnectionEntryDialupRemote OBJECT-TYPE
    SYNTAX     DisplayString (SIZE(0..20))
    MAX-ACCESS read-only
    STATUS     current
    DESCRIPTION
            "-- empty --"
    ::= { hmStatusInfoConnectionEntry 4 }

-- {COLUMN} 1.3.6.1.4.1.248.32.18.1.14.1.5
hmStatusInfoConnectionEntryPeer OBJECT-TYPE
    SYNTAX     DisplayString (SIZE(0..16))
    MAX-ACCESS read-only
    STATUS     current
    DESCRIPTION
            "-- empty --"
    ::= { hmStatusInfoConnectionEntry 5 }

-- {COLUMN} 1.3.6.1.4.1.248.32.18.1.14.1.6
hmStatusInfoConnectionEntryB1Dt OBJECT-TYPE
    SYNTAX     Integer32 (0..65535)
    MAX-ACCESS read-only
    STATUS     current
    DESCRIPTION
            "-- empty --"
    ::= { hmStatusInfoConnectionEntry 6 }

-- {COLUMN} 1.3.6.1.4.1.248.32.18.1.14.1.7
hmStatusInfoConnectionEntryB2Dt OBJECT-TYPE
    SYNTAX     Integer32 (0..65535)
    MAX-ACCESS read-only
    STATUS     current
    DESCRIPTION
            "-- empty --"
    ::= { hmStatusInfoConnectionEntry 7 }

-- {TABLE} 1.3.6.1.4.1.248.32.18.1.15
hmStatusLayerConnectionTable OBJECT-TYPE
    SYNTAX     SEQUENCE OF HmStatusLayerConnectionEntry
    MAX-ACCESS not-accessible
    STATUS     current
    DESCRIPTION
            "-- empty --"
    ::= { hmStatus 15 }

-- {ROW} 1.3.6.1.4.1.248.32.18.1.15.1
hmStatusLayerConnectionEntry OBJECT-TYPE
    SYNTAX     HmStatusLayerConnectionEntry
    MAX-ACCESS not-accessible
    STATUS     current
    DESCRIPTION
            ""
    INDEX {
            hmStatusLayerConnectionEntryIfc
          }
    ::= { hmStatusLayerConnectionTable 1 }

HmStatusLayerConnectionEntry ::= SEQUENCE {
            hmStatusLayerConnectionEntryIfc INTEGER,
            hmStatusLayerConnectionEntryWanLayer DisplayString,
            hmStatusLayerConnectionEntryEncaps INTEGER,
            hmStatusLayerConnectionEntryLay3 INTEGER,
            hmStatusLayerConnectionEntryLay2 INTEGER,
            hmStatusLayerConnectionEntryL2Opt INTEGER,
            hmStatusLayerConnectionEntryLay1 INTEGER,
            hmStatusLayerConnectionEntryL1Parameter INTEGER
    }

-- {COLUMN} 1.3.6.1.4.1.248.32.18.1.15.1.1
hmStatusLayerConnectionEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusLayerConnectionEntry 1 }

-- {COLUMN} 1.3.6.1.4.1.248.32.18.1.15.1.2
hmStatusLayerConnectionEntryWanLayer OBJECT-TYPE
    SYNTAX     DisplayString (SIZE(0..9))
    MAX-ACCESS read-only
    STATUS     current
    DESCRIPTION
            "-- empty --"
    ::= { hmStatusLayerConnectionEntry 2 }

-- {COLUMN} 1.3.6.1.4.1.248.32.18.1.15.1.3
hmStatusLayerConnectionEntryEncaps OBJECT-TYPE
    SYNTAX     INTEGER {
                  eEther (0),
                  eTrans (255)
            }
    MAX-ACCESS read-only
    STATUS     current
    DESCRIPTION
            "-- empty --"
    ::= { hmStatusLayerConnectionEntry 3 }

-- {COLUMN} 1.3.6.1.4.1.248.32.18.1.15.1.4
hmStatusLayerConnectionEntryLay3 OBJECT-TYPE
    SYNTAX     INTEGER {
                  ePpp (4),
                  eAppp (5),
                  eScppp (6),
                  eScappp (7),
                  eSctrans (8),
                  eDhcp (9),
                  eTRANS (255)
            }
    MAX-ACCESS read-only
    STATUS     current
    DESCRIPTION
            "-- empty --"
    ::= { hmStatusLayerConnectionEntry 4 }

-- {COLUMN} 1.3.6.1.4.1.248.32.18.1.15.1.5
hmStatusLayerConnectionEntryLay2 OBJECT-TYPE
    SYNTAX     INTEGER {
                  eX75lapb (0),
                  eTrans (1),
                  ePppoe (5),
                  eSscop (6)
            }
    MAX-ACCESS read-only
    STATUS     current
    DESCRIPTION
            "-- empty --"
    ::= { hmStatusLayerConnectionEntry 5 }

-- {COLUMN} 1.3.6.1.4.1.248.32.18.1.15.1.6
hmStatusLayerConnectionEntryL2Opt OBJECT-TYPE
    SYNTAX     INTEGER {
                  eCompr (0),
                  eBundle (1),
                  eBndPlusCmpr (2),
                  eNone (255)
            }
    MAX-ACCESS read-only
    STATUS     current
    DESCRIPTION
            "-- empty --"
    ::= { hmStatusLayerConnectionEntry 6 }

-- {COLUMN} 1.3.6.1.4.1.248.32.18.1.15.1.7
hmStatusLayerConnectionEntryLay1 OBJECT-TYPE
    SYNTAX     INTEGER {
                  eHdlc64k (0),
                  eHdlc56k (1),
                  eAdsl (2),
                  eEth (4),
                  eModem (5),
                  eSerial (6)
            }
    MAX-ACCESS read-only
    STATUS     current
    DESCRIPTION
            "-- empty --"
    ::= { hmStatusLayerConnectionEntry 7 }

-- {COLUMN} 1.3.6.1.4.1.248.32.18.1.15.1.8
hmStatusLayerConnectionEntryL1Parameter OBJECT-TYPE
    SYNTAX     INTEGER {
                  eNone (0),
                  eV21300 (1),
                  eV23600 (2),
                  eV231200 (3),
                  eV221200 (4),
                  eV22bis2400 (5),
                  eV32qam4800 (6),
                  eV32qam9600 (7),
                  eV32bis7200 (8),
                  eV32tcm9600 (9),
                  eV32bis12000 (10),
                  eV32bis14400 (11),
                  eV342400 (12),
                  eV344800 (13),
                  eV347200 (14),
                  eV349600 (15),
                  eV3412000 (16),
                  eV3414400 (17),
                  eV3416800 (18),
                  eV3419200 (19),
                  eV3421600 (20),
                  eV3424000 (21),
                  eV3426400 (22),
                  eV3428800 (23),
                  eV3431200 (24),
                  eV3433600 (25),
                  eV9028000 (26),
                  eV9029333 (27),
                  eV9030667 (28),
                  eV9032000 (29),
                  eV9033333 (30),
                  eV9034667 (31),
                  eV9036000 (32),
                  eV9037333 (33),
                  eV9038667 (34),
                  eV9040000 (35),
                  eV9041333 (36),
                  eV9042667 (37),
                  eV9044000 (38),
                  eV9045333 (39),
                  eV9046667 (40),
                  eV9048000 (41),
                  eV9049333 (42),
                  eV9050667 (43),
                  eV9052000 (44),
                  eV9053333 (45),
                  eV9054667 (46),
                  eV9056000 (47)
            }
    MAX-ACCESS read-only
    STATUS     current
    DESCRIPTION
            "-- empty --"
    ::= { hmStatusLayerConnectionEntry 8 }

-- {TABLE} 1.3.6.1.4.1.248.32.18.1.16
hmStatusCallInformationTable OBJECT-TYPE
    SYNTAX     SEQUENCE OF HmStatusCallInformationEntry
    MAX-ACCESS not-accessible
    STATUS     current
    DESCRIPTION
            "-- empty --"
    ::= { hmStatus 16 }

-- {ROW} 1.3.6.1.4.1.248.32.18.1.16.1
hmStatusCallInformationEntry OBJECT-TYPE
    SYNTAX     HmStatusCallInformationEntry
    MAX-ACCESS not-accessible
    STATUS     current
    DESCRIPTION
            ""
    INDEX {
            hmStatusCallInformationEntrySystemTime,
            hmStatusCallInformationEntryCounter
          }
    ::= { hmStatusCallInformationTable 1 }

HmStatusCallInformationEntry ::= SEQUENCE {
            hmStatusCallInformationEntrySystemTime Gauge32,
            hmStatusCallInformationEntryIfc INTEGER,
            hmStatusCallInformationEntryClipCaller DisplayString,
            hmStatusCallInformationEntryDialCaller DisplayString,
            hmStatusCallInformationEntryCapab INTEGER,
            hmStatusCallInformationEntryBChan Integer32,
            hmStatusCallInformationEntryCounter Integer32
    }

-- {COLUMN} 1.3.6.1.4.1.248.32.18.1.16.1.1
hmStatusCallInformationEntrySystemTime OBJECT-TYPE
    SYNTAX     Gauge32
    MAX-ACCESS read-only
    STATUS     current
    DESCRIPTION
            "-- empty --"
    ::= { hmStatusCallInformationEntry 1 }

-- {COLUMN} 1.3.6.1.4.1.248.32.18.1.16.1.2
hmStatusCallInformationEntryIfc OBJECT-TYPE
    SYNTAX     INTEGER {
                  eModem (513),
                  eDsl1 (2049),
                  eDsl2 (2050),
                  eDsl3 (2051),
                  eDsl4 (2052)
            }
    MAX-ACCESS read-only
    STATUS     current
    DESCRIPTION
            "-- empty --"
    ::= { hmStatusCallInformationEntry 2 }

-- {COLUMN} 1.3.6.1.4.1.248.32.18.1.16.1.3
hmStatusCallInformationEntryClipCaller OBJECT-TYPE
    SYNTAX     DisplayString (SIZE(0..20))
    MAX-ACCESS read-only
    STATUS     current
    DESCRIPTION
            "-- empty --"
    ::= { hmStatusCallInformationEntry 3 }

-- {COLUMN} 1.3.6.1.4.1.248.32.18.1.16.1.4
hmStatusCallInformationEntryDialCaller OBJECT-TYPE
    SYNTAX     DisplayString (SIZE(0..20))
    MAX-ACCESS read-only
    STATUS     current
    DESCRIPTION
            "-- empty --"
    ::= { hmStatusCallInformationEntry 4 }

-- {COLUMN} 1.3.6.1.4.1.248.32.18.1.16.1.5
hmStatusCallInformationEntryCapab OBJECT-TYPE
    SYNTAX     INTEGER {
                  eHdlc64k (0),
                  eHdlc56k (1),
                  eV1109k6 (3),
                  eModem (5),
                  eA31khz (13),
                  eSpeech (14),
                  eFaxG23 (15),
                  eV11019k2 (67),
                  eV11038k4 (131),
                  eUnknown (255)
            }
    MAX-ACCESS read-only
    STATUS     current
    DESCRIPTION
            "-- empty --"
    ::= { hmStatusCallInformationEntry 5 }

-- {COLUMN} 1.3.6.1.4.1.248.32.18.1.16.1.6
hmStatusCallInformationEntryBChan OBJECT-TYPE
    SYNTAX     Integer32 (0..65535)
    MAX-ACCESS read-only
    STATUS     current
    DESCRIPTION
            "-- empty --"
    ::= { hmStatusCallInformationEntry 6 }

-- {COLUMN} 1.3.6.1.4.1.248.32.18.1.16.1.7
hmStatusCallInformationEntryCounter OBJECT-TYPE
    SYNTAX     Integer32 (0..2147483647)
    MAX-ACCESS read-only
    STATUS     current
    DESCRIPTION
            "-- empty --"
    ::= { hmStatusCallInformationEntry 7 }

-- {TABLE} 1.3.6.1.4.1.248.32.18.1.17
hmStatusRemoteConnectionsTable OBJECT-TYPE
    SYNTAX     SEQUENCE OF HmStatusRemoteConnectionsEntry
    MAX-ACCESS not-accessible
    STATUS     current
    DESCRIPTION
            "-- empty --"
    ::= { hmStatus 17 }

-- {ROW} 1.3.6.1.4.1.248.32.18.1.17.1
hmStatusRemoteConnectionsEntry OBJECT-TYPE
    SYNTAX     HmStatusRemoteConnectionsEntry
    MAX-ACCESS not-accessible
    STATUS     current
    DESCRIPTION
            ""
    INDEX {
            hmStatusRemoteConnectionsEntryConnStart,
            hmStatusRemoteConnectionsEntryCounter
          }
    ::= { hmStatusRemoteConnectionsTable 1 }

HmStatusRemoteConnectionsEntry ::= SEQUENCE {
            hmStatusRemoteConnectionsEntryConnStart DisplayString,
            hmStatusRemoteConnectionsEntryRemoteId DisplayString,
            hmStatusRemoteConnectionsEntryMode INTEGER,
            hmStatusRemoteConnectionsEntryIfc INTEGER,
            hmStatusRemoteConnectionsEntryConnTime DisplayString,
            hmStatusRemoteConnectionsEntryCharge Integer32,
            hmStatusRemoteConnectionsEntryCounter Integer32
    }

-- {COLUMN} 1.3.6.1.4.1.248.32.18.1.17.1.1
hmStatusRemoteConnectionsEntryConnStart OBJECT-TYPE
    SYNTAX     DisplayString (SIZE(0..19))
    MAX-ACCESS read-only
    STATUS     current
    DESCRIPTION
            "-- empty --"
    ::= { hmStatusRemoteConnectionsEntry 1 }

-- {COLUMN} 1.3.6.1.4.1.248.32.18.1.17.1.2
hmStatusRemoteConnectionsEntryRemoteId OBJECT-TYPE
    SYNTAX     DisplayString (SIZE(0..16))
    MAX-ACCESS read-only
    STATUS     current
    DESCRIPTION
            "-- empty --"
    ::= { hmStatusRemoteConnectionsEntry 2 }

-- {COLUMN} 1.3.6.1.4.1.248.32.18.1.17.1.3
hmStatusRemoteConnectionsEntryMode OBJECT-TYPE
    SYNTAX     INTEGER {
                  eUnknown (0),
                  eActive (4),
                  ePassive (5),
                  eCallback (9)
            }
    MAX-ACCESS read-only
    STATUS     current
    DESCRIPTION
            "-- empty --"
    ::= { hmStatusRemoteConnectionsEntry 3 }

-- {COLUMN} 1.3.6.1.4.1.248.32.18.1.17.1.4
hmStatusRemoteConnectionsEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusRemoteConnectionsEntry 4 }

-- {COLUMN} 1.3.6.1.4.1.248.32.18.1.17.1.5
hmStatusRemoteConnectionsEntryConnTime OBJECT-TYPE
    SYNTAX     DisplayString (SIZE(0..255))
    MAX-ACCESS read-only
    STATUS     current
    DESCRIPTION
            "-- empty --"
    ::= { hmStatusRemoteConnectionsEntry 5 }

-- {COLUMN} 1.3.6.1.4.1.248.32.18.1.17.1.6
hmStatusRemoteConnectionsEntryCharge OBJECT-TYPE
    SYNTAX     Integer32 (0..2147483647)
    MAX-ACCESS read-only
    STATUS     current
    DESCRIPTION
            "-- empty --"
    ::= { hmStatusRemoteConnectionsEntry 6 }

-- {COLUMN} 1.3.6.1.4.1.248.32.18.1.17.1.8
hmStatusRemoteConnectionsEntryCounter OBJECT-TYPE
    SYNTAX     Integer32 (0..2147483647)
    MAX-ACCESS read-only
    STATUS     current
    DESCRIPTION
            "-- empty --"
    ::= { hmStatusRemoteConnectionsEntry 8 }

-- {SCALAR} 1.3.6.1.4.1.248.32.18.1.18
hmStatusCurrentTime OBJECT-TYPE
    SYNTAX     DisplayString
    MAX-ACCESS read-only
    STATUS     current
    DESCRIPTION
            "-- empty --"
    ::= { hmStatus 18 }

-- {NODE} 1.3.6.1.4.1.248.32.18.1.21
hmStatusTime OBJECT IDENTIFIER ::= { hmStatus 21 }

-- {SCALAR} 1.3.6.1.4.1.248.32.18.1.21.1
hmStatusTimeCurrentTime OBJECT-TYPE
    SYNTAX     DisplayString
    MAX-ACCESS read-only
    STATUS     current
    DESCRIPTION
            "-- empty --"
    ::= { hmStatusTime 1 }

-- {SCALAR} 1.3.6.1.4.1.248.32.18.1.21.2
hmStatusTimeSource OBJECT-TYPE
    SYNTAX     INTEGER {
                  eNo (0),
                  eManual (1),
                  eLan (3),
                  eRam (4),
                  eLanconfig (8),
                  eNtp (9),
                  eCapwap (10),
                  eRtc (11)
            }
    MAX-ACCESS read-only
    STATUS     current
    DESCRIPTION
            "-- empty --"
    ::= { hmStatusTime 2 }

-- {SCALAR} 1.3.6.1.4.1.248.32.18.1.21.3
hmStatusTimeSetCount OBJECT-TYPE
    SYNTAX     Counter32
    MAX-ACCESS read-only
    STATUS     current
    DESCRIPTION
            "-- empty --"
    ::= { hmStatusTime 3 }

-- {SCALAR} 1.3.6.1.4.1.248.32.18.1.21.10
hmStatusTimeTimezone OBJECT-TYPE
    SYNTAX     INTEGER {
                  e0 (0),
                  eplus1 (1),
                  eplus2 (2),
                  eplus3 (3),
                  eplus4 (4),
                  eplus5 (5),
                  eplus6 (6),
                  eplus7 (7),
                  eplus8 (8),
                  eplus9 (9),
                  eplus10 (10),
                  eplus11 (11),
                  eplus12 (12),
                  eplus13 (13),
                  eplus14 (14),
                  eminus12 (244),
                  eminus11 (245),
                  eminus10 (246),
                  eminus9 (247),
                  eminus8 (248),
                  eminus7 (249),
                  eminus6 (250),
                  eminus5 (251),
                  eminus4 (252),
                  eminus3 (253),
                  eminus2 (254),
                  eminus1 (255)
            }
    MAX-ACCESS read-only
    STATUS     current
    DESCRIPTION
            "-- empty --"
    ::= { hmStatusTime 10 }

-- {SCALAR} 1.3.6.1.4.1.248.32.18.1.21.11
hmStatusTimeDaylightSavingTime OBJECT-TYPE
    SYNTAX     INTEGER {
                  eNo (0),
                  eYes (1),
                  eEuropeEu (2),
                  eRussia (3),
                  eUsa (4),
                  eUserDefined (255)
            }
    MAX-ACCESS read-only
    STATUS     current
    DESCRIPTION
            "-- empty --"
    ::= { hmStatusTime 11 }

-- {TABLE} 1.3.6.1.4.1.248.32.18.1.21.12
hmStatusTimeDstClockChangesTable OBJECT-TYPE
    SYNTAX     SEQUENCE OF HmStatusTimeDstClockChangesEntry
    MAX-ACCESS not-accessible
    STATUS     current
    DESCRIPTION
            "-- empty --"
    ::= { hmStatusTime 12 }

-- {ROW} 1.3.6.1.4.1.248.32.18.1.21.12.1
hmStatusTimeDstClockChangesEntry OBJECT-TYPE
    SYNTAX     HmStatusTimeDstClockChangesEntry
    MAX-ACCESS not-accessible
    STATUS     current
    DESCRIPTION
            ""
    INDEX {
            hmStatusTimeDstClockChangesEntryEvent
          }
    ::= { hmStatusTimeDstClockChangesTable 1 }

HmStatusTimeDstClockChangesEntry ::= SEQUENCE {
            hmStatusTimeDstClockChangesEntryEvent INTEGER,
            hmStatusTimeDstClockChangesEntryIndex INTEGER,
            hmStatusTimeDstClockChangesEntryDay INTEGER,
            hmStatusTimeDstClockChangesEntryMonth INTEGER,
            hmStatusTimeDstClockChangesEntryHour Integer32,
            hmStatusTimeDstClockChangesEntryMinute Integer32,
            hmStatusTimeDstClockChangesEntryTimeType INTEGER
    }

-- {COLUMN} 1.3.6.1.4.1.248.32.18.1.21.12.1.1
hmStatusTimeDstClockChangesEntryEvent OBJECT-TYPE
    SYNTAX     INTEGER {
                  eStart (1),
                  eEnd (2)
            }
    MAX-ACCESS read-only
    STATUS     current
    DESCRIPTION
            "-- empty --"
    ::= { hmStatusTimeDstClockChangesEntry 1 }

-- {COLUMN} 1.3.6.1.4.1.248.32.18.1.21.12.1.2
hmStatusTimeDstClockChangesEntryIndex OBJECT-TYPE
    SYNTAX     INTEGER {
                  eFirst (1),
                  eSecond (2),
                  eThird (3),
                  eFourth (4),
                  e4Last (252),
                  e3Last (253),
                  e2Last (254),
                  eLast (255)
            }
    MAX-ACCESS read-only
    STATUS     current
    DESCRIPTION
            "-- empty --"
    ::= { hmStatusTimeDstClockChangesEntry 2 }

-- {COLUMN} 1.3.6.1.4.1.248.32.18.1.21.12.1.3
hmStatusTimeDstClockChangesEntryDay OBJECT-TYPE
    SYNTAX     INTEGER {
                  eSunday (0),
                  eMonday (1),
                  eTuesday (2),
                  eWednesday (3),
                  eThursday (4),
                  eFriday (5),
                  eSaturday (6)
            }
    MAX-ACCESS read-only
    STATUS     current
    DESCRIPTION
            "-- empty --"
    ::= { hmStatusTimeDstClockChangesEntry 3 }

-- {COLUMN} 1.3.6.1.4.1.248.32.18.1.21.12.1.4
hmStatusTimeDstClockChangesEntryMonth OBJECT-TYPE
    SYNTAX     INTEGER {
                  eJanuary (1),
                  eFebruary (2),
                  eMarch (3),
                  eApril (4),
                  eMay (5),
                  eJune (6),
                  eJuly (7),
                  eAugust (8),
                  eSeptember (9),
                  eOctober (10),
                  eNovember (11),
                  eDecember (12)
            }
    MAX-ACCESS read-only
    STATUS     current
    DESCRIPTION
            "-- empty --"
    ::= { hmStatusTimeDstClockChangesEntry 4 }

-- {COLUMN} 1.3.6.1.4.1.248.32.18.1.21.12.1.5
hmStatusTimeDstClockChangesEntryHour OBJECT-TYPE
    SYNTAX     Integer32 (0..255)
    MAX-ACCESS read-only
    STATUS     current
    DESCRIPTION
            "-- empty --"
    ::= { hmStatusTimeDstClockChangesEntry 5 }

-- {COLUMN} 1.3.6.1.4.1.248.32.18.1.21.12.1.6
hmStatusTimeDstClockChangesEntryMinute OBJECT-TYPE
    SYNTAX     Integer32 (0..255)
    MAX-ACCESS read-only
    STATUS     current
    DESCRIPTION
            "-- empty --"
    ::= { hmStatusTimeDstClockChangesEntry 6 }

-- {COLUMN} 1.3.6.1.4.1.248.32.18.1.21.12.1.7
hmStatusTimeDstClockChangesEntryTimeType OBJECT-TYPE
    SYNTAX     INTEGER {
                  eLst (0),
                  eUtc (1)
            }
    MAX-ACCESS read-only
    STATUS     current
    DESCRIPTION
            "-- empty --"
    ::= { hmStatusTimeDstClockChangesEntry 7 }

-- {SCALAR} 1.3.6.1.4.1.248.32.18.1.21.14
hmStatusTimeSntpClientStatus OBJECT-TYPE
    SYNTAX     INTEGER
      {
        eNotSynchronized (2),
        eSynchronized (5),
        eDisabled (1),
        e0 (0), -- plus 2 hours
        eplus3 (3), -- plus 3 hours
        eplus4 (4), -- plus 5 hours
        eplus6 (6), -- plus 6 hours
        eplus7 (7), -- plus 7 hours
        eplus8 (8), -- plus 8 hours
        eplus9 (9), -- plus 9 hours
        eplus10 (10), -- plus 10 hours
        eplus11 (11), -- plus 11 hours
        eplus12 (12), -- plus 12 hours
        eplus13 (13), -- plus 13 hours
        eplus14 (14), -- plus 14 hours
        eminus1 (255), -- minus 1 hour
        eminus2 (254), -- minus 2 hours
        eminus3 (253), -- minus 3 hours
        eminus4 (252), -- minus 4 hours
        eminus5 (251), -- minus 5 hours
        eminus6 (250), -- minus 6 hours
        eminus7 (249), -- minus 7 hours
        eminus8 (248), -- minus 8 hours
        eminus9 (247), -- minus 9 hours
        eminus10 (246), -- minus 10 hours
        eminus11 (245), -- minus 11 hours
        eminus12 (244) -- minus 12 hours
      }
    MAX-ACCESS read-only
    STATUS     current
    DESCRIPTION
        "-- empty --"
    ::= { hmStatusTime 14 }


-- {NODE} 1.3.6.1.4.1.248.32.18.1.22
hmStatusLcr OBJECT IDENTIFIER ::= { hmStatus 22 }

-- {SCALAR} 1.3.6.1.4.1.248.32.18.1.22.1
hmStatusLcrTotalCalls OBJECT-TYPE
    SYNTAX     Counter32
    MAX-ACCESS read-only
    STATUS     current
    DESCRIPTION
            "-- empty --"
    ::= { hmStatusLcr 1 }

-- {SCALAR} 1.3.6.1.4.1.248.32.18.1.22.2
hmStatusLcrFoundEvents OBJECT-TYPE
    SYNTAX     Counter32
    MAX-ACCESS read-only
    STATUS     current
    DESCRIPTION
            "-- empty --"
    ::= { hmStatusLcr 2 }

-- {SCALAR} 1.3.6.1.4.1.248.32.18.1.22.3
hmStatusLcrNotfoundErrors OBJECT-TYPE
    SYNTAX     Counter32
    MAX-ACCESS read-only
    STATUS     current
    DESCRIPTION
            "-- empty --"
    ::= { hmStatusLcr 3 }

-- {SCALAR} 1.3.6.1.4.1.248.32.18.1.22.4
hmStatusLcrMissingtimeErrors OBJECT-TYPE
    SYNTAX     Counter32
    MAX-ACCESS read-only
    STATUS     current
    DESCRIPTION
            "-- empty --"
    ::= { hmStatusLcr 4 }

-- {TABLE} 1.3.6.1.4.1.248.32.18.1.22.6
hmStatusLcrProviderTable OBJECT-TYPE
    SYNTAX     SEQUENCE OF HmStatusLcrProviderEntry
    MAX-ACCESS not-accessible
    STATUS     current
    DESCRIPTION
            "-- empty --"
    ::= { hmStatusLcr 6 }

-- {ROW} 1.3.6.1.4.1.248.32.18.1.22.6.1
hmStatusLcrProviderEntry OBJECT-TYPE
    SYNTAX     HmStatusLcrProviderEntry
    MAX-ACCESS not-accessible
    STATUS     current
    DESCRIPTION
            ""
    INDEX {
            hmStatusLcrProviderEntryProvider
          }
    ::= { hmStatusLcrProviderTable 1 }

HmStatusLcrProviderEntry ::= SEQUENCE {
            hmStatusLcrProviderEntryProvider DisplayString,
            hmStatusLcrProviderEntryFailures Integer32,
            hmStatusLcrProviderEntrySuccesses Integer32
    }

-- {COLUMN} 1.3.6.1.4.1.248.32.18.1.22.6.1.1
hmStatusLcrProviderEntryProvider OBJECT-TYPE
    SYNTAX     DisplayString (SIZE(0..10))
    MAX-ACCESS read-only
    STATUS     current
    DESCRIPTION
            "-- empty --"
    ::= { hmStatusLcrProviderEntry 1 }

-- {COLUMN} 1.3.6.1.4.1.248.32.18.1.22.6.1.2
hmStatusLcrProviderEntryFailures OBJECT-TYPE
    SYNTAX     Integer32 (0..2147483647)
    MAX-ACCESS read-only
    STATUS     current
    DESCRIPTION
            "-- empty --"
    ::= { hmStatusLcrProviderEntry 2 }

-- {COLUMN} 1.3.6.1.4.1.248.32.18.1.22.6.1.3
hmStatusLcrProviderEntrySuccesses OBJECT-TYPE
    SYNTAX     Integer32 (0..2147483647)
    MAX-ACCESS read-only
    STATUS     current
    DESCRIPTION
            "-- empty --"
    ::= { hmStatusLcrProviderEntry 3 }

-- {SCALAR} 1.3.6.1.4.1.248.32.18.1.22.7
hmStatusLcrDeleteValues OBJECT-TYPE
    SYNTAX     DisplayString
    MAX-ACCESS read-write
    STATUS     current
    DESCRIPTION
            "-- empty --"
    ::= { hmStatusLcr 7 }

-- {NODE} 1.3.6.1.4.1.248.32.18.1.22.31
hmStatusLcrPppoe OBJECT IDENTIFIER ::= { hmStatusLcr 31 }

-- {SCALAR} 1.3.6.1.4.1.248.32.18.1.22.31.1
hmStatusLcrPppoeTxPadi OBJECT-TYPE
    SYNTAX     Integer32 (0..2147483647)
    MAX-ACCESS read-only
    STATUS     current
    DESCRIPTION
            "-- empty --"
    ::= { hmStatusLcrPppoe 1 }

-- {SCALAR} 1.3.6.1.4.1.248.32.18.1.22.31.2
hmStatusLcrPppoeRxPado OBJECT-TYPE
    SYNTAX     Integer32 (0..2147483647)
    MAX-ACCESS read-only
    STATUS     current
    DESCRIPTION
            "-- empty --"
    ::= { hmStatusLcrPppoe 2 }

-- {SCALAR} 1.3.6.1.4.1.248.32.18.1.22.31.3
hmStatusLcrPppoeTxPadr OBJECT-TYPE
    SYNTAX     Integer32 (0..2147483647)
    MAX-ACCESS read-only
    STATUS     current
    DESCRIPTION
            "-- empty --"
    ::= { hmStatusLcrPppoe 3 }

-- {SCALAR} 1.3.6.1.4.1.248.32.18.1.22.31.4
hmStatusLcrPppoeRxPads OBJECT-TYPE
    SYNTAX     Integer32 (0..2147483647)
    MAX-ACCESS read-only
    STATUS     current
    DESCRIPTION
            "-- empty --"
    ::= { hmStatusLcrPppoe 4 }

-- {SCALAR} 1.3.6.1.4.1.248.32.18.1.22.31.5
hmStatusLcrPppoeTxPadt OBJECT-TYPE
    SYNTAX     Integer32 (0..2147483647)
    MAX-ACCESS read-only
    STATUS     current
    DESCRIPTION
            "-- empty --"
    ::= { hmStatusLcrPppoe 5 }

-- {SCALAR} 1.3.6.1.4.1.248.32.18.1.22.31.6
hmStatusLcrPppoeRxPadt OBJECT-TYPE
    SYNTAX     Integer32 (0..2147483647)
    MAX-ACCESS read-only
    STATUS     current
    DESCRIPTION
            "-- empty --"
    ::= { hmStatusLcrPppoe 6 }

-- {SCALAR} 1.3.6.1.4.1.248.32.18.1.22.31.7
hmStatusLcrPppoeTxProtocol OBJECT-TYPE
    SYNTAX     Integer32 (0..2147483647)
    MAX-ACCESS read-only
    STATUS     current
    DESCRIPTION
            "-- empty --"
    ::= { hmStatusLcrPppoe 7 }

-- {SCALAR} 1.3.6.1.4.1.248.32.18.1.22.31.8
hmStatusLcrPppoeRxProtocol OBJECT-TYPE
    SYNTAX     Integer32 (0..2147483647)
    MAX-ACCESS read-only
    STATUS     current
    DESCRIPTION
            "-- empty --"
    ::= { hmStatusLcrPppoe 8 }

-- {SCALAR} 1.3.6.1.4.1.248.32.18.1.22.31.9
hmStatusLcrPppoeTxData OBJECT-TYPE
    SYNTAX     Integer32 (0..2147483647)
    MAX-ACCESS read-only
    STATUS     current
    DESCRIPTION
            "-- empty --"
    ::= { hmStatusLcrPppoe 9 }

-- {SCALAR} 1.3.6.1.4.1.248.32.18.1.22.31.10
hmStatusLcrPppoeRxData OBJECT-TYPE
    SYNTAX     Integer32 (0..2147483647)
    MAX-ACCESS read-only
    STATUS     current
    DESCRIPTION
            "-- empty --"
    ::= { hmStatusLcrPppoe 10 }

-- {SCALAR} 1.3.6.1.4.1.248.32.18.1.22.31.11
hmStatusLcrPppoeRxBad OBJECT-TYPE
    SYNTAX     Integer32 (0..2147483647)
    MAX-ACCESS read-only
    STATUS     current
    DESCRIPTION
            "-- empty --"
    ::= { hmStatusLcrPppoe 11 }

-- {SCALAR} 1.3.6.1.4.1.248.32.18.1.22.31.12
hmStatusLcrPppoeAcName OBJECT-TYPE
    SYNTAX     DisplayString (SIZE(0..63))
    MAX-ACCESS read-only
    STATUS     current
    DESCRIPTION
            "-- empty --"
    ::= { hmStatusLcrPppoe 12 }

-- {SCALAR} 1.3.6.1.4.1.248.32.18.1.22.31.13
hmStatusLcrPppoeService OBJECT-TYPE
    SYNTAX     DisplayString (SIZE(0..63))
    MAX-ACCESS read-only
    STATUS     current
    DESCRIPTION
            "-- empty --"
    ::= { hmStatusLcrPppoe 13 }

-- {SCALAR} 1.3.6.1.4.1.248.32.18.1.22.31.30
hmStatusLcrPppoeDeleteValues OBJECT-TYPE
    SYNTAX     DisplayString
    MAX-ACCESS read-write
    STATUS     current
    DESCRIPTION
            "-- empty --"
    ::= { hmStatusLcrPppoe 30 }

-- {NODE} 1.3.6.1.4.1.248.32.18.1.24
hmStatusCharging OBJECT IDENTIFIER ::= { hmStatus 24 }

-- {SCALAR} 1.3.6.1.4.1.248.32.18.1.24.1
hmStatusChargingSpareDslBroadbandMinutes OBJECT-TYPE
    SYNTAX     Integer32 (0..2147483647)
    MAX-ACCESS read-only
    STATUS     current
    DESCRIPTION
            "-- empty --"
    ::= { hmStatusCharging 1 }

-- {TABLE} 1.3.6.1.4.1.248.32.18.1.24.2
hmStatusChargingTimeTableTable OBJECT-TYPE
    SYNTAX     SEQUENCE OF HmStatusChargingTimeTableEntry
    MAX-ACCESS not-accessible
    STATUS     current
    DESCRIPTION
            "-- empty --"
    ::= { hmStatusCharging 2 }

-- {ROW} 1.3.6.1.4.1.248.32.18.1.24.2.1
hmStatusChargingTimeTableEntry OBJECT-TYPE
    SYNTAX     HmStatusChargingTimeTableEntry
    MAX-ACCESS not-accessible
    STATUS     current
    DESCRIPTION
            ""
    INDEX {
            hmStatusChargingTimeTableEntryIfc
          }
    ::= { hmStatusChargingTimeTableTable 1 }

HmStatusChargingTimeTableEntry ::= SEQUENCE {
            hmStatusChargingTimeTableEntryIfc INTEGER,
            hmStatusChargingTimeTableEntryBudgetMinutes Integer32,
            hmStatusChargingTimeTableEntrySpareMinutes Integer32,
            hmStatusChargingTimeTableEntryMinutesActive Integer32,
            hmStatusChargingTimeTableEntryMinutesPassive Integer32
    }

-- {COLUMN} 1.3.6.1.4.1.248.32.18.1.24.2.1.1
hmStatusChargingTimeTableEntryIfc OBJECT-TYPE
    SYNTAX     INTEGER {
                  eRouterDslBroadband (1),
                  eRouterSerial (2),
                  eLancapi (3),
                  eAb1 (4),
                  eAb2 (5),
                  eAb3 (6),
                  eAb4 (7),
                  eTimeModul (255)
            }
    MAX-ACCESS read-only
    STATUS     current
    DESCRIPTION
            "-- empty --"
    ::= { hmStatusChargingTimeTableEntry 1 }

-- {COLUMN} 1.3.6.1.4.1.248.32.18.1.24.2.1.2
hmStatusChargingTimeTableEntryBudgetMinutes OBJECT-TYPE
    SYNTAX     Integer32 (0..2147483647)
    MAX-ACCESS read-only
    STATUS     current
    DESCRIPTION
            "-- empty --"
    ::= { hmStatusChargingTimeTableEntry 2 }

-- {COLUMN} 1.3.6.1.4.1.248.32.18.1.24.2.1.3
hmStatusChargingTimeTableEntrySpareMinutes OBJECT-TYPE
    SYNTAX     Integer32 (0..2147483647)
    MAX-ACCESS read-only
    STATUS     current
    DESCRIPTION
            "-- empty --"
    ::= { hmStatusChargingTimeTableEntry 3 }

-- {COLUMN} 1.3.6.1.4.1.248.32.18.1.24.2.1.4
hmStatusChargingTimeTableEntryMinutesActive OBJECT-TYPE
    SYNTAX     Integer32 (0..2147483647)
    MAX-ACCESS read-only
    STATUS     current
    DESCRIPTION
            "-- empty --"
    ::= { hmStatusChargingTimeTableEntry 4 }

-- {COLUMN} 1.3.6.1.4.1.248.32.18.1.24.2.1.5
hmStatusChargingTimeTableEntryMinutesPassive OBJECT-TYPE
    SYNTAX     Integer32 (0..2147483647)
    MAX-ACCESS read-only
    STATUS     current
    DESCRIPTION
            "-- empty --"
    ::= { hmStatusChargingTimeTableEntry 5 }

-- {SCALAR} 1.3.6.1.4.1.248.32.18.1.24.3
hmStatusChargingDeleteValues OBJECT-TYPE
    SYNTAX     DisplayString
    MAX-ACCESS read-write
    STATUS     current
    DESCRIPTION
            "-- empty --"
    ::= { hmStatusCharging 3 }

-- {SCALAR} 1.3.6.1.4.1.248.32.18.1.24.6
hmStatusChargingSpareDaysPerPeriod OBJECT-TYPE
    SYNTAX     Integer32 (0..65535)
    MAX-ACCESS read-only
    STATUS     current
    DESCRIPTION
            "-- empty --"
    ::= { hmStatusCharging 6 }

-- {SCALAR} 1.3.6.1.4.1.248.32.18.1.24.9
hmStatusChargingRouterDslBroadbandMinutesActive OBJECT-TYPE
    SYNTAX     Integer32 (0..2147483647)
    MAX-ACCESS read-only
    STATUS     current
    DESCRIPTION
            "-- empty --"
    ::= { hmStatusCharging 9 }

-- {SCALAR} 1.3.6.1.4.1.248.32.18.1.24.10
hmStatusChargingSpareDialupMinutes OBJECT-TYPE
    SYNTAX     Integer32 (0..2147483647)
    MAX-ACCESS read-only
    STATUS     current
    DESCRIPTION
            "-- empty --"
    ::= { hmStatusCharging 10 }

-- {SCALAR} 1.3.6.1.4.1.248.32.18.1.24.11
hmStatusChargingDialupMinutesActive OBJECT-TYPE
    SYNTAX     Integer32 (0..2147483647)
    MAX-ACCESS read-only
    STATUS     current
    DESCRIPTION
            "-- empty --"
    ::= { hmStatusCharging 11 }

-- {NODE} 1.3.6.1.4.1.248.32.18.1.24.31
hmStatusChargingPppoe OBJECT IDENTIFIER ::= { hmStatusCharging 31 }

-- {SCALAR} 1.3.6.1.4.1.248.32.18.1.24.31.1
hmStatusChargingPppoeTxPadi OBJECT-TYPE
    SYNTAX     Integer32 (0..2147483647)
    MAX-ACCESS read-only
    STATUS     current
    DESCRIPTION
            "-- empty --"
    ::= { hmStatusChargingPppoe 1 }

-- {SCALAR} 1.3.6.1.4.1.248.32.18.1.24.31.2
hmStatusChargingPppoeRxPado OBJECT-TYPE
    SYNTAX     Integer32 (0..2147483647)
    MAX-ACCESS read-only
    STATUS     current
    DESCRIPTION
            "-- empty --"
    ::= { hmStatusChargingPppoe 2 }

-- {SCALAR} 1.3.6.1.4.1.248.32.18.1.24.31.3
hmStatusChargingPppoeTxPadr OBJECT-TYPE
    SYNTAX     Integer32 (0..2147483647)
    MAX-ACCESS read-only
    STATUS     current
    DESCRIPTION
            "-- empty --"
    ::= { hmStatusChargingPppoe 3 }

-- {SCALAR} 1.3.6.1.4.1.248.32.18.1.24.31.4
hmStatusChargingPppoeRxPads OBJECT-TYPE
    SYNTAX     Integer32 (0..2147483647)
    MAX-ACCESS read-only
    STATUS     current
    DESCRIPTION
            "-- empty --"
    ::= { hmStatusChargingPppoe 4 }

-- {SCALAR} 1.3.6.1.4.1.248.32.18.1.24.31.5
hmStatusChargingPppoeTxPadt OBJECT-TYPE
    SYNTAX     Integer32 (0..2147483647)
    MAX-ACCESS read-only
    STATUS     current
    DESCRIPTION
            "-- empty --"
    ::= { hmStatusChargingPppoe 5 }

-- {SCALAR} 1.3.6.1.4.1.248.32.18.1.24.31.6
hmStatusChargingPppoeRxPadt OBJECT-TYPE
    SYNTAX     Integer32 (0..2147483647)
    MAX-ACCESS read-only
    STATUS     current
    DESCRIPTION
            "-- empty --"
    ::= { hmStatusChargingPppoe 6 }

-- {SCALAR} 1.3.6.1.4.1.248.32.18.1.24.31.7
hmStatusChargingPppoeTxProtocol OBJECT-TYPE
    SYNTAX     Integer32 (0..2147483647)
    MAX-ACCESS read-only
    STATUS     current
    DESCRIPTION
            "-- empty --"
    ::= { hmStatusChargingPppoe 7 }

-- {SCALAR} 1.3.6.1.4.1.248.32.18.1.24.31.8
hmStatusChargingPppoeRxProtocol OBJECT-TYPE
    SYNTAX     Integer32 (0..2147483647)
    MAX-ACCESS read-only
    STATUS     current
    DESCRIPTION
            "-- empty --"
    ::= { hmStatusChargingPppoe 8 }

-- {SCALAR} 1.3.6.1.4.1.248.32.18.1.24.31.9
hmStatusChargingPppoeTxData OBJECT-TYPE
    SYNTAX     Integer32 (0..2147483647)
    MAX-ACCESS read-only
    STATUS     current
    DESCRIPTION
            "-- empty --"
    ::= { hmStatusChargingPppoe 9 }

-- {SCALAR} 1.3.6.1.4.1.248.32.18.1.24.31.10
hmStatusChargingPppoeRxData OBJECT-TYPE
    SYNTAX     Integer32 (0..2147483647)
    MAX-ACCESS read-only
    STATUS     current
    DESCRIPTION
            "-- empty --"
    ::= { hmStatusChargingPppoe 10 }

-- {SCALAR} 1.3.6.1.4.1.248.32.18.1.24.31.11
hmStatusChargingPppoeRxBad OBJECT-TYPE
    SYNTAX     Integer32 (0..2147483647)
    MAX-ACCESS read-only
    STATUS     current
    DESCRIPTION
            "-- empty --"
    ::= { hmStatusChargingPppoe 11 }

-- {SCALAR} 1.3.6.1.4.1.248.32.18.1.24.31.12
hmStatusChargingPppoeAcName OBJECT-TYPE
    SYNTAX     DisplayString (SIZE(0..63))
    MAX-ACCESS read-only
    STATUS     current
    DESCRIPTION
            "-- empty --"
    ::= { hmStatusChargingPppoe 12 }

-- {SCALAR} 1.3.6.1.4.1.248.32.18.1.24.31.13
hmStatusChargingPppoeService OBJECT-TYPE
    SYNTAX     DisplayString (SIZE(0..63))
    MAX-ACCESS read-only
    STATUS     current
    DESCRIPTION
            "-- empty --"
    ::= { hmStatusChargingPppoe 13 }

-- {SCALAR} 1.3.6.1.4.1.248.32.18.1.24.31.30
hmStatusChargingPppoeDeleteValues OBJECT-TYPE
    SYNTAX     DisplayString
    MAX-ACCESS read-write
    STATUS     current
    DESCRIPTION
            "-- empty --"
    ::= { hmStatusChargingPppoe 30 }

-- {NODE} 1.3.6.1.4.1.248.32.18.1.26
hmStatusVpn OBJECT IDENTIFIER ::= { hmStatus 26 }

-- {SCALAR} 1.3.6.1.4.1.248.32.18.1.26.1
hmStatusVpnPeers OBJECT-TYPE
    SYNTAX     Integer32 (0..2147483647)
    MAX-ACCESS read-only
    STATUS     current
    DESCRIPTION
            "-- empty --"
    ::= { hmStatusVpn 1 }

-- {SCALAR} 1.3.6.1.4.1.248.32.18.1.26.2
hmStatusVpnRules OBJECT-TYPE
    SYNTAX     Integer32 (0..2147483647)
    MAX-ACCESS read-only
    STATUS     current
    DESCRIPTION
            "-- empty --"
    ::= { hmStatusVpn 2 }

-- {SCALAR} 1.3.6.1.4.1.248.32.18.1.26.4
hmStatusVpnTunnel OBJECT-TYPE
    SYNTAX     Integer32 (0..2147483647)
    MAX-ACCESS read-only
    STATUS     current
    DESCRIPTION
            "-- empty --"
    ::= { hmStatusVpn 4 }

-- {SCALAR} 1.3.6.1.4.1.248.32.18.1.26.5
hmStatusVpnIkeSas OBJECT-TYPE
    SYNTAX     Integer32 (0..2147483647)
    MAX-ACCESS read-only
    STATUS     current
    DESCRIPTION
            "-- empty --"
    ::= { hmStatusVpn 5 }

-- {SCALAR} 1.3.6.1.4.1.248.32.18.1.26.6
hmStatusVpnEspSas OBJECT-TYPE
    SYNTAX     Integer32 (0..2147483647)
    MAX-ACCESS read-only
    STATUS     current
    DESCRIPTION
            "-- empty --"
    ::= { hmStatusVpn 6 }

-- {SCALAR} 1.3.6.1.4.1.248.32.18.1.26.7
hmStatusVpnAhSas OBJECT-TYPE
    SYNTAX     Integer32 (0..2147483647)
    MAX-ACCESS read-only
    STATUS     current
    DESCRIPTION
            "-- empty --"
    ::= { hmStatusVpn 7 }

-- {TABLE} 1.3.6.1.4.1.248.32.18.1.26.8
hmStatusVpnIkeTable OBJECT-TYPE
    SYNTAX     SEQUENCE OF HmStatusVpnIkeEntry
    MAX-ACCESS not-accessible
    STATUS     current
    DESCRIPTION
            "-- empty --"
    ::= { hmStatusVpn 8 }

-- {ROW} 1.3.6.1.4.1.248.32.18.1.26.8.1
hmStatusVpnIkeEntry OBJECT-TYPE
    SYNTAX     HmStatusVpnIkeEntry
    MAX-ACCESS not-accessible
    STATUS     current
    DESCRIPTION
            ""
    INDEX {
            hmStatusVpnIkeEntryIdx
          }
    ::= { hmStatusVpnIkeTable 1 }

HmStatusVpnIkeEntry ::= SEQUENCE {
            hmStatusVpnIkeEntryIdx DisplayString,
            hmStatusVpnIkeEntryPeer DisplayString,
            hmStatusVpnIkeEntryDestAddress IpAddress,
            hmStatusVpnIkeEntrySrcAddress IpAddress,
            hmStatusVpnIkeEntryCryptAlg DisplayString,
            hmStatusVpnIkeEntryHashAlg DisplayString,
            hmStatusVpnIkeEntryAge Integer32,
            hmStatusVpnIkeEntryInitiator DisplayString,
            hmStatusVpnIkeEntrySoftSec Integer32,
            hmStatusVpnIkeEntryMaxSec Integer32,
            hmStatusVpnIkeEntryKbyte Integer32,
            hmStatusVpnIkeEntrySoftKbyte Integer32,
            hmStatusVpnIkeEntryMaxKbyte Integer32,
            hmStatusVpnIkeEntryIkeAuthMode INTEGER,
            hmStatusVpnIkeEntryDstPort Integer32,
            hmStatusVpnIkeEntrySrcPort Integer32,
            hmStatusVpnIkeEntryDestAddressNew DisplayString,
            hmStatusVpnIkeEntrySrcAddressNew DisplayString
    }

-- {COLUMN} 1.3.6.1.4.1.248.32.18.1.26.8.1.1
hmStatusVpnIkeEntryIdx OBJECT-TYPE
    SYNTAX     DisplayString (SIZE(0..255))
    MAX-ACCESS read-only
    STATUS     current
    DESCRIPTION
            "-- empty --"
    ::= { hmStatusVpnIkeEntry 1 }

-- {COLUMN} 1.3.6.1.4.1.248.32.18.1.26.8.1.2
hmStatusVpnIkeEntryPeer OBJECT-TYPE
    SYNTAX     DisplayString (SIZE(0..15))
    MAX-ACCESS read-only
    STATUS     current
    DESCRIPTION
            "-- empty --"
    ::= { hmStatusVpnIkeEntry 2 }

-- {COLUMN} 1.3.6.1.4.1.248.32.18.1.26.8.1.3
hmStatusVpnIkeEntryDestAddress OBJECT-TYPE
    SYNTAX     IpAddress
    MAX-ACCESS read-only
    STATUS     current
    DESCRIPTION
            "-- empty --"
    ::= { hmStatusVpnIkeEntry 3 }

-- {COLUMN} 1.3.6.1.4.1.248.32.18.1.26.8.1.4
hmStatusVpnIkeEntrySrcAddress OBJECT-TYPE
    SYNTAX     IpAddress
    MAX-ACCESS read-only
    STATUS     current
    DESCRIPTION
            "-- empty --"
    ::= { hmStatusVpnIkeEntry 4 }

-- {COLUMN} 1.3.6.1.4.1.248.32.18.1.26.8.1.5
hmStatusVpnIkeEntryCryptAlg OBJECT-TYPE
    SYNTAX     DisplayString (SIZE(0..12))
    MAX-ACCESS read-only
    STATUS     current
    DESCRIPTION
            "-- empty --"
    ::= { hmStatusVpnIkeEntry 5 }

-- {COLUMN} 1.3.6.1.4.1.248.32.18.1.26.8.1.6
hmStatusVpnIkeEntryHashAlg OBJECT-TYPE
    SYNTAX     DisplayString (SIZE(0..12))
    MAX-ACCESS read-only
    STATUS     current
    DESCRIPTION
            "-- empty --"
    ::= { hmStatusVpnIkeEntry 6 }

-- {COLUMN} 1.3.6.1.4.1.248.32.18.1.26.8.1.8
hmStatusVpnIkeEntryAge OBJECT-TYPE
    SYNTAX     Integer32 (0..2147483647)
    MAX-ACCESS read-only
    STATUS     current
    DESCRIPTION
            "-- empty --"
    ::= { hmStatusVpnIkeEntry 8 }

-- {COLUMN} 1.3.6.1.4.1.248.32.18.1.26.8.1.9
hmStatusVpnIkeEntryInitiator OBJECT-TYPE
    SYNTAX     DisplayString (SIZE(0..3))
    MAX-ACCESS read-only
    STATUS     current
    DESCRIPTION
            "-- empty --"
    ::= { hmStatusVpnIkeEntry 9 }

-- {COLUMN} 1.3.6.1.4.1.248.32.18.1.26.8.1.10
hmStatusVpnIkeEntrySoftSec OBJECT-TYPE
    SYNTAX     Integer32 (0..2147483647)
    MAX-ACCESS read-only
    STATUS     current
    DESCRIPTION
            "-- empty --"
    ::= { hmStatusVpnIkeEntry 10 }

-- {COLUMN} 1.3.6.1.4.1.248.32.18.1.26.8.1.11
hmStatusVpnIkeEntryMaxSec OBJECT-TYPE
    SYNTAX     Integer32 (0..2147483647)
    MAX-ACCESS read-only
    STATUS     current
    DESCRIPTION
            "-- empty --"
    ::= { hmStatusVpnIkeEntry 11 }

-- {COLUMN} 1.3.6.1.4.1.248.32.18.1.26.8.1.12
hmStatusVpnIkeEntryKbyte OBJECT-TYPE
    SYNTAX     Integer32 (0..2147483647)
    MAX-ACCESS read-only
    STATUS     current
    DESCRIPTION
            "-- empty --"
    ::= { hmStatusVpnIkeEntry 12 }

-- {COLUMN} 1.3.6.1.4.1.248.32.18.1.26.8.1.13
hmStatusVpnIkeEntrySoftKbyte OBJECT-TYPE
    SYNTAX     Integer32 (0..2147483647)
    MAX-ACCESS read-only
    STATUS     current
    DESCRIPTION
            "-- empty --"
    ::= { hmStatusVpnIkeEntry 13 }

-- {COLUMN} 1.3.6.1.4.1.248.32.18.1.26.8.1.14
hmStatusVpnIkeEntryMaxKbyte OBJECT-TYPE
    SYNTAX     Integer32 (0..2147483647)
    MAX-ACCESS read-only
    STATUS     current
    DESCRIPTION
            "-- empty --"
    ::= { hmStatusVpnIkeEntry 14 }

-- {COLUMN} 1.3.6.1.4.1.248.32.18.1.26.8.1.15
hmStatusVpnIkeEntryIkeAuthMode OBJECT-TYPE
    SYNTAX     INTEGER {
                  eNo (0),
                  ePreShared (1),
                  eDss (2),
                  eRsaSig (3),
                  eRsaEnc (4),
                  eRsaEncRev (5),
                  eElGamalEnc (6),
                  eElGamalEncRev (7),
                  eEcdsaSig (8),
                  ePreSharedInitXauth (65001),
                  ePreSharedRespXauth (65002),
                  eDssInitXauth (65003),
                  eDssRespXauth (65004),
                  eRsaInitXauth (65005),
                  eRsaRespXauth (65006)
            }
    MAX-ACCESS read-only
    STATUS     current
    DESCRIPTION
            "-- empty --"
    ::= { hmStatusVpnIkeEntry 15 }

-- {COLUMN} 1.3.6.1.4.1.248.32.18.1.26.8.1.16
hmStatusVpnIkeEntryDstPort OBJECT-TYPE
    SYNTAX     Integer32 (0..65535)
    MAX-ACCESS read-only
    STATUS     current
    DESCRIPTION
            "-- empty --"
    ::= { hmStatusVpnIkeEntry 16 }

-- {COLUMN} 1.3.6.1.4.1.248.32.18.1.26.8.1.17
hmStatusVpnIkeEntrySrcPort OBJECT-TYPE
    SYNTAX     Integer32 (0..65535)
    MAX-ACCESS read-only
    STATUS     current
    DESCRIPTION
            "-- empty --"
    ::= { hmStatusVpnIkeEntry 17 }

-- {COLUMN} 1.3.6.1.4.1.248.32.18.1.26.8.1.18
hmStatusVpnIkeEntryDestAddressNew OBJECT-TYPE
    SYNTAX     DisplayString (SIZE(0..39))
    MAX-ACCESS read-only
    STATUS     current
    DESCRIPTION
            ""
    ::= { hmStatusVpnIkeEntry 18 }

-- {COLUMN} 1.3.6.1.4.1.248.32.18.1.26.8.1.19
hmStatusVpnIkeEntrySrcAddressNew OBJECT-TYPE
    SYNTAX     DisplayString (SIZE(0..39))
    MAX-ACCESS read-only
    STATUS     current
    DESCRIPTION
            ""
    ::= { hmStatusVpnIkeEntry 19 }

-- {TABLE} 1.3.6.1.4.1.248.32.18.1.26.9
hmStatusVpnEspTable OBJECT-TYPE
    SYNTAX     SEQUENCE OF HmStatusVpnEspEntry
    MAX-ACCESS not-accessible
    STATUS     current
    DESCRIPTION
            "-- empty --"
    ::= { hmStatusVpn 9 }

-- {ROW} 1.3.6.1.4.1.248.32.18.1.26.9.1
hmStatusVpnEspEntry OBJECT-TYPE
    SYNTAX     HmStatusVpnEspEntry
    MAX-ACCESS not-accessible
    STATUS     current
    DESCRIPTION
            ""
    INDEX {
            hmStatusVpnEspEntryIdx
          }
    ::= { hmStatusVpnEspTable 1 }

HmStatusVpnEspEntry ::= SEQUENCE {
            hmStatusVpnEspEntryIdx DisplayString,
            hmStatusVpnEspEntryPeer DisplayString,
            hmStatusVpnEspEntryDestAddress IpAddress,
            hmStatusVpnEspEntrySrcAddress IpAddress,
            hmStatusVpnEspEntryMode DisplayString,
            hmStatusVpnEspEntryCryptAlg DisplayString,
            hmStatusVpnEspEntryHashAlg DisplayString,
            hmStatusVpnEspEntrySpi DisplayString,
            hmStatusVpnEspEntryAge Integer32,
            hmStatusVpnEspEntrySoftSec Integer32,
            hmStatusVpnEspEntryMaxSec Integer32,
            hmStatusVpnEspEntryKbyte Integer32,
            hmStatusVpnEspEntrySoftKbyte Integer32,
            hmStatusVpnEspEntryMaxKbyte Integer32,
            hmStatusVpnEspEntryDestAddressNew DisplayString,
            hmStatusVpnEspEntrySrcAddressNew DisplayString
    }

-- {COLUMN} 1.3.6.1.4.1.248.32.18.1.26.9.1.1
hmStatusVpnEspEntryIdx OBJECT-TYPE
    SYNTAX     DisplayString (SIZE(0..255))
    MAX-ACCESS read-only
    STATUS     current
    DESCRIPTION
            "-- empty --"
    ::= { hmStatusVpnEspEntry 1 }

-- {COLUMN} 1.3.6.1.4.1.248.32.18.1.26.9.1.2
hmStatusVpnEspEntryPeer OBJECT-TYPE
    SYNTAX     DisplayString (SIZE(0..15))
    MAX-ACCESS read-only
    STATUS     current
    DESCRIPTION
            "-- empty --"
    ::= { hmStatusVpnEspEntry 2 }

-- {COLUMN} 1.3.6.1.4.1.248.32.18.1.26.9.1.3
hmStatusVpnEspEntryDestAddress OBJECT-TYPE
    SYNTAX     IpAddress
    MAX-ACCESS read-only
    STATUS     current
    DESCRIPTION
            "-- empty --"
    ::= { hmStatusVpnEspEntry 3 }

-- {COLUMN} 1.3.6.1.4.1.248.32.18.1.26.9.1.4
hmStatusVpnEspEntrySrcAddress OBJECT-TYPE
    SYNTAX     IpAddress
    MAX-ACCESS read-only
    STATUS     current
    DESCRIPTION
            "-- empty --"
    ::= { hmStatusVpnEspEntry 4 }

-- {COLUMN} 1.3.6.1.4.1.248.32.18.1.26.9.1.5
hmStatusVpnEspEntryMode OBJECT-TYPE
    SYNTAX     DisplayString (SIZE(0..2))
    MAX-ACCESS read-only
    STATUS     current
    DESCRIPTION
            "-- empty --"
    ::= { hmStatusVpnEspEntry 5 }

-- {COLUMN} 1.3.6.1.4.1.248.32.18.1.26.9.1.6
hmStatusVpnEspEntryCryptAlg OBJECT-TYPE
    SYNTAX     DisplayString (SIZE(0..12))
    MAX-ACCESS read-only
    STATUS     current
    DESCRIPTION
            "-- empty --"
    ::= { hmStatusVpnEspEntry 6 }

-- {COLUMN} 1.3.6.1.4.1.248.32.18.1.26.9.1.7
hmStatusVpnEspEntryHashAlg OBJECT-TYPE
    SYNTAX     DisplayString (SIZE(0..12))
    MAX-ACCESS read-only
    STATUS     current
    DESCRIPTION
            "-- empty --"
    ::= { hmStatusVpnEspEntry 7 }

-- {COLUMN} 1.3.6.1.4.1.248.32.18.1.26.9.1.9
hmStatusVpnEspEntrySpi OBJECT-TYPE
    SYNTAX     DisplayString (SIZE(0..15))
    MAX-ACCESS read-only
    STATUS     current
    DESCRIPTION
            "-- empty --"
    ::= { hmStatusVpnEspEntry 9 }

-- {COLUMN} 1.3.6.1.4.1.248.32.18.1.26.9.1.10
hmStatusVpnEspEntryAge OBJECT-TYPE
    SYNTAX     Integer32 (0..2147483647)
    MAX-ACCESS read-only
    STATUS     current
    DESCRIPTION
            "-- empty --"
    ::= { hmStatusVpnEspEntry 10 }

-- {COLUMN} 1.3.6.1.4.1.248.32.18.1.26.9.1.11
hmStatusVpnEspEntrySoftSec OBJECT-TYPE
    SYNTAX     Integer32 (0..2147483647)
    MAX-ACCESS read-only
    STATUS     current
    DESCRIPTION
            "-- empty --"
    ::= { hmStatusVpnEspEntry 11 }

-- {COLUMN} 1.3.6.1.4.1.248.32.18.1.26.9.1.12
hmStatusVpnEspEntryMaxSec OBJECT-TYPE
    SYNTAX     Integer32 (0..2147483647)
    MAX-ACCESS read-only
    STATUS     current
    DESCRIPTION
            "-- empty --"
    ::= { hmStatusVpnEspEntry 12 }

-- {COLUMN} 1.3.6.1.4.1.248.32.18.1.26.9.1.13
hmStatusVpnEspEntryKbyte OBJECT-TYPE
    SYNTAX     Integer32 (0..2147483647)
    MAX-ACCESS read-only
    STATUS     current
    DESCRIPTION
            "-- empty --"
    ::= { hmStatusVpnEspEntry 13 }

-- {COLUMN} 1.3.6.1.4.1.248.32.18.1.26.9.1.14
hmStatusVpnEspEntrySoftKbyte OBJECT-TYPE
    SYNTAX     Integer32 (0..2147483647)
    MAX-ACCESS read-only
    STATUS     current
    DESCRIPTION
            "-- empty --"
    ::= { hmStatusVpnEspEntry 14 }

-- {COLUMN} 1.3.6.1.4.1.248.32.18.1.26.9.1.15
hmStatusVpnEspEntryMaxKbyte OBJECT-TYPE
    SYNTAX     Integer32 (0..2147483647)
    MAX-ACCESS read-only
    STATUS     current
    DESCRIPTION
            "-- empty --"
    ::= { hmStatusVpnEspEntry 15 }

-- {COLUMN} 1.3.6.1.4.1.248.32.18.1.26.9.1.16
hmStatusVpnEspEntryDestAddressNew OBJECT-TYPE
    SYNTAX     DisplayString (SIZE(0..39))
    MAX-ACCESS read-only
    STATUS     current
    DESCRIPTION
            ""
    ::= { hmStatusVpnEspEntry 16 }

-- {COLUMN} 1.3.6.1.4.1.248.32.18.1.26.9.1.17
hmStatusVpnEspEntrySrcAddressNew OBJECT-TYPE
    SYNTAX     DisplayString (SIZE(0..39))
    MAX-ACCESS read-only
    STATUS     current
    DESCRIPTION
            ""
    ::= { hmStatusVpnEspEntry 17 }

-- {TABLE} 1.3.6.1.4.1.248.32.18.1.26.10
hmStatusVpnAhTable OBJECT-TYPE
    SYNTAX     SEQUENCE OF HmStatusVpnAhEntry
    MAX-ACCESS not-accessible
    STATUS     current
    DESCRIPTION
            "-- empty --"
    ::= { hmStatusVpn 10 }

-- {ROW} 1.3.6.1.4.1.248.32.18.1.26.10.1
hmStatusVpnAhEntry OBJECT-TYPE
    SYNTAX     HmStatusVpnAhEntry
    MAX-ACCESS not-accessible
    STATUS     current
    DESCRIPTION
            ""
    INDEX {
            hmStatusVpnAhEntryIdx
          }
    ::= { hmStatusVpnAhTable 1 }

HmStatusVpnAhEntry ::= SEQUENCE {
            hmStatusVpnAhEntryIdx DisplayString,
            hmStatusVpnAhEntryPeer DisplayString,
            hmStatusVpnAhEntryDestAddress IpAddress,
            hmStatusVpnAhEntrySrcAddress IpAddress,
            hmStatusVpnAhEntryMode DisplayString,
            hmStatusVpnAhEntryCryptAlg DisplayString,
            hmStatusVpnAhEntryHashAlg DisplayString,
            hmStatusVpnAhEntrySpi DisplayString,
            hmStatusVpnAhEntryAge Integer32,
            hmStatusVpnAhEntrySoftSec Integer32,
            hmStatusVpnAhEntryMaxSec Integer32,
            hmStatusVpnAhEntryKbyte Integer32,
            hmStatusVpnAhEntrySoftKbyte Integer32,
            hmStatusVpnAhEntryMaxKbyte Integer32,
            hmStatusVpnAhEntryDestAddressNew DisplayString,
            hmStatusVpnAhEntrySrcAddressNew DisplayString
    }

-- {COLUMN} 1.3.6.1.4.1.248.32.18.1.26.10.1.1
hmStatusVpnAhEntryIdx OBJECT-TYPE
    SYNTAX     DisplayString (SIZE(0..255))
    MAX-ACCESS read-only
    STATUS     current
    DESCRIPTION
            "-- empty --"
    ::= { hmStatusVpnAhEntry 1 }

-- {COLUMN} 1.3.6.1.4.1.248.32.18.1.26.10.1.2
hmStatusVpnAhEntryPeer OBJECT-TYPE
    SYNTAX     DisplayString (SIZE(0..15))
    MAX-ACCESS read-only
    STATUS     current
    DESCRIPTION
            "-- empty --"
    ::= { hmStatusVpnAhEntry 2 }

-- {COLUMN} 1.3.6.1.4.1.248.32.18.1.26.10.1.3
hmStatusVpnAhEntryDestAddress OBJECT-TYPE
    SYNTAX     IpAddress
    MAX-ACCESS read-only
    STATUS     current
    DESCRIPTION
            "-- empty --"
    ::= { hmStatusVpnAhEntry 3 }

-- {COLUMN} 1.3.6.1.4.1.248.32.18.1.26.10.1.4
hmStatusVpnAhEntrySrcAddress OBJECT-TYPE
    SYNTAX     IpAddress
    MAX-ACCESS read-only
    STATUS     current
    DESCRIPTION
            "-- empty --"
    ::= { hmStatusVpnAhEntry 4 }

-- {COLUMN} 1.3.6.1.4.1.248.32.18.1.26.10.1.5
hmStatusVpnAhEntryMode OBJECT-TYPE
    SYNTAX     DisplayString (SIZE(0..2))
    MAX-ACCESS read-only
    STATUS     current
    DESCRIPTION
            "-- empty --"
    ::= { hmStatusVpnAhEntry 5 }

-- {COLUMN} 1.3.6.1.4.1.248.32.18.1.26.10.1.6
hmStatusVpnAhEntryCryptAlg OBJECT-TYPE
    SYNTAX     DisplayString (SIZE(0..12))
    MAX-ACCESS read-only
    STATUS     current
    DESCRIPTION
            "-- empty --"
    ::= { hmStatusVpnAhEntry 6 }

-- {COLUMN} 1.3.6.1.4.1.248.32.18.1.26.10.1.7
hmStatusVpnAhEntryHashAlg OBJECT-TYPE
    SYNTAX     DisplayString (SIZE(0..12))
    MAX-ACCESS read-only
    STATUS     current
    DESCRIPTION
            "-- empty --"
    ::= { hmStatusVpnAhEntry 7 }

-- {COLUMN} 1.3.6.1.4.1.248.32.18.1.26.10.1.9
hmStatusVpnAhEntrySpi OBJECT-TYPE
    SYNTAX     DisplayString (SIZE(0..15))
    MAX-ACCESS read-only
    STATUS     current
    DESCRIPTION
            "-- empty --"
    ::= { hmStatusVpnAhEntry 9 }

-- {COLUMN} 1.3.6.1.4.1.248.32.18.1.26.10.1.10
hmStatusVpnAhEntryAge OBJECT-TYPE
    SYNTAX     Integer32 (0..2147483647)
    MAX-ACCESS read-only
    STATUS     current
    DESCRIPTION
            "-- empty --"
    ::= { hmStatusVpnAhEntry 10 }

-- {COLUMN} 1.3.6.1.4.1.248.32.18.1.26.10.1.11
hmStatusVpnAhEntrySoftSec OBJECT-TYPE
    SYNTAX     Integer32 (0..2147483647)
    MAX-ACCESS read-only
    STATUS     current
    DESCRIPTION
            "-- empty --"
    ::= { hmStatusVpnAhEntry 11 }

-- {COLUMN} 1.3.6.1.4.1.248.32.18.1.26.10.1.12
hmStatusVpnAhEntryMaxSec OBJECT-TYPE
    SYNTAX     Integer32 (0..2147483647)
    MAX-ACCESS read-only
    STATUS     current
    DESCRIPTION
            "-- empty --"
    ::= { hmStatusVpnAhEntry 12 }

-- {COLUMN} 1.3.6.1.4.1.248.32.18.1.26.10.1.13
hmStatusVpnAhEntryKbyte OBJECT-TYPE
    SYNTAX     Integer32 (0..2147483647)
    MAX-ACCESS read-only
    STATUS     current
    DESCRIPTION
            "-- empty --"
    ::= { hmStatusVpnAhEntry 13 }

-- {COLUMN} 1.3.6.1.4.1.248.32.18.1.26.10.1.14
hmStatusVpnAhEntrySoftKbyte OBJECT-TYPE
    SYNTAX     Integer32 (0..2147483647)
    MAX-ACCESS read-only
    STATUS     current
    DESCRIPTION
            "-- empty --"
    ::= { hmStatusVpnAhEntry 14 }

-- {COLUMN} 1.3.6.1.4.1.248.32.18.1.26.10.1.15
hmStatusVpnAhEntryMaxKbyte OBJECT-TYPE
    SYNTAX     Integer32 (0..2147483647)
    MAX-ACCESS read-only
    STATUS     current
    DESCRIPTION
            "-- empty --"
    ::= { hmStatusVpnAhEntry 15 }

-- {COLUMN} 1.3.6.1.4.1.248.32.18.1.26.10.1.16
hmStatusVpnAhEntryDestAddressNew OBJECT-TYPE
    SYNTAX     DisplayString (SIZE(0..39))
    MAX-ACCESS read-only
    STATUS     current
    DESCRIPTION
            ""
    ::= { hmStatusVpnAhEntry 16 }

-- {COLUMN} 1.3.6.1.4.1.248.32.18.1.26.10.1.17
hmStatusVpnAhEntrySrcAddressNew OBJECT-TYPE
    SYNTAX     DisplayString (SIZE(0..39))
    MAX-ACCESS read-only
    STATUS     current
    DESCRIPTION
            ""
    ::= { hmStatusVpnAhEntry 17 }

-- {SCALAR} 1.3.6.1.4.1.248.32.18.1.26.12
hmStatusVpnDeleteValues OBJECT-TYPE
    SYNTAX     DisplayString
    MAX-ACCESS read-write
    STATUS     current
    DESCRIPTION
            "-- empty --"
    ::= { hmStatusVpn 12 }

-- {SCALAR} 1.3.6.1.4.1.248.32.18.1.26.13
hmStatusVpnIpcompSas OBJECT-TYPE
    SYNTAX     Integer32 (0..2147483647)
    MAX-ACCESS read-only
    STATUS     current
    DESCRIPTION
            "-- empty --"
    ::= { hmStatusVpn 13 }

-- {TABLE} 1.3.6.1.4.1.248.32.18.1.26.14
hmStatusVpnIpcompTable OBJECT-TYPE
    SYNTAX     SEQUENCE OF HmStatusVpnIpcompEntry
    MAX-ACCESS not-accessible
    STATUS     current
    DESCRIPTION
            "-- empty --"
    ::= { hmStatusVpn 14 }

-- {ROW} 1.3.6.1.4.1.248.32.18.1.26.14.1
hmStatusVpnIpcompEntry OBJECT-TYPE
    SYNTAX     HmStatusVpnIpcompEntry
    MAX-ACCESS not-accessible
    STATUS     current
    DESCRIPTION
            ""
    INDEX {
            hmStatusVpnIpcompEntryIdx
          }
    ::= { hmStatusVpnIpcompTable 1 }

HmStatusVpnIpcompEntry ::= SEQUENCE {
            hmStatusVpnIpcompEntryIdx DisplayString,
            hmStatusVpnIpcompEntryPeer DisplayString,
            hmStatusVpnIpcompEntryDestAddress IpAddress,
            hmStatusVpnIpcompEntrySrcAddress IpAddress,
            hmStatusVpnIpcompEntryMode DisplayString,
            hmStatusVpnIpcompEntryCryptAlg DisplayString,
            hmStatusVpnIpcompEntryHashAlg DisplayString,
            hmStatusVpnIpcompEntrySpi DisplayString,
            hmStatusVpnIpcompEntryAge Integer32,
            hmStatusVpnIpcompEntrySoftSec Integer32,
            hmStatusVpnIpcompEntryMaxSec Integer32,
            hmStatusVpnIpcompEntryKbyte Integer32,
            hmStatusVpnIpcompEntrySoftKbyte Integer32,
            hmStatusVpnIpcompEntryMaxKbyte Integer32,
            hmStatusVpnIpcompEntryDestAddressNew DisplayString,
            hmStatusVpnIpcompEntrySrcAddressNew DisplayString
    }

-- {COLUMN} 1.3.6.1.4.1.248.32.18.1.26.14.1.1
hmStatusVpnIpcompEntryIdx OBJECT-TYPE
    SYNTAX     DisplayString (SIZE(0..255))
    MAX-ACCESS read-only
    STATUS     current
    DESCRIPTION
            "-- empty --"
    ::= { hmStatusVpnIpcompEntry 1 }

-- {COLUMN} 1.3.6.1.4.1.248.32.18.1.26.14.1.2
hmStatusVpnIpcompEntryPeer OBJECT-TYPE
    SYNTAX     DisplayString (SIZE(0..15))
    MAX-ACCESS read-only
    STATUS     current
    DESCRIPTION
            "-- empty --"
    ::= { hmStatusVpnIpcompEntry 2 }

-- {COLUMN} 1.3.6.1.4.1.248.32.18.1.26.14.1.3
hmStatusVpnIpcompEntryDestAddress OBJECT-TYPE
    SYNTAX     IpAddress
    MAX-ACCESS read-only
    STATUS     current
    DESCRIPTION
            "-- empty --"
    ::= { hmStatusVpnIpcompEntry 3 }

-- {COLUMN} 1.3.6.1.4.1.248.32.18.1.26.14.1.4
hmStatusVpnIpcompEntrySrcAddress OBJECT-TYPE
    SYNTAX     IpAddress
    MAX-ACCESS read-only
    STATUS     current
    DESCRIPTION
            "-- empty --"
    ::= { hmStatusVpnIpcompEntry 4 }

-- {COLUMN} 1.3.6.1.4.1.248.32.18.1.26.14.1.5
hmStatusVpnIpcompEntryMode OBJECT-TYPE
    SYNTAX     DisplayString (SIZE(0..2))
    MAX-ACCESS read-only
    STATUS     current
    DESCRIPTION
            "-- empty --"
    ::= { hmStatusVpnIpcompEntry 5 }

-- {COLUMN} 1.3.6.1.4.1.248.32.18.1.26.14.1.6
hmStatusVpnIpcompEntryCryptAlg OBJECT-TYPE
    SYNTAX     DisplayString (SIZE(0..12))
    MAX-ACCESS read-only
    STATUS     current
    DESCRIPTION
            "-- empty --"
    ::= { hmStatusVpnIpcompEntry 6 }

-- {COLUMN} 1.3.6.1.4.1.248.32.18.1.26.14.1.7
hmStatusVpnIpcompEntryHashAlg OBJECT-TYPE
    SYNTAX     DisplayString (SIZE(0..12))
    MAX-ACCESS read-only
    STATUS     current
    DESCRIPTION
            "-- empty --"
    ::= { hmStatusVpnIpcompEntry 7 }

-- {COLUMN} 1.3.6.1.4.1.248.32.18.1.26.14.1.9
hmStatusVpnIpcompEntrySpi OBJECT-TYPE
    SYNTAX     DisplayString (SIZE(0..15))
    MAX-ACCESS read-only
    STATUS     current
    DESCRIPTION
            "-- empty --"
    ::= { hmStatusVpnIpcompEntry 9 }

-- {COLUMN} 1.3.6.1.4.1.248.32.18.1.26.14.1.10
hmStatusVpnIpcompEntryAge OBJECT-TYPE
    SYNTAX     Integer32 (0..2147483647)
    MAX-ACCESS read-only
    STATUS     current
    DESCRIPTION
            "-- empty --"
    ::= { hmStatusVpnIpcompEntry 10 }

-- {COLUMN} 1.3.6.1.4.1.248.32.18.1.26.14.1.11
hmStatusVpnIpcompEntrySoftSec OBJECT-TYPE
    SYNTAX     Integer32 (0..2147483647)
    MAX-ACCESS read-only
    STATUS     current
    DESCRIPTION
            "-- empty --"
    ::= { hmStatusVpnIpcompEntry 11 }

-- {COLUMN} 1.3.6.1.4.1.248.32.18.1.26.14.1.12
hmStatusVpnIpcompEntryMaxSec OBJECT-TYPE
    SYNTAX     Integer32 (0..2147483647)
    MAX-ACCESS read-only
    STATUS     current
    DESCRIPTION
            "-- empty --"
    ::= { hmStatusVpnIpcompEntry 12 }

-- {COLUMN} 1.3.6.1.4.1.248.32.18.1.26.14.1.13
hmStatusVpnIpcompEntryKbyte OBJECT-TYPE
    SYNTAX     Integer32 (0..2147483647)
    MAX-ACCESS read-only
    STATUS     current
    DESCRIPTION
            "-- empty --"
    ::= { hmStatusVpnIpcompEntry 13 }

-- {COLUMN} 1.3.6.1.4.1.248.32.18.1.26.14.1.14
hmStatusVpnIpcompEntrySoftKbyte OBJECT-TYPE
    SYNTAX     Integer32 (0..2147483647)
    MAX-ACCESS read-only
    STATUS     current
    DESCRIPTION
            "-- empty --"
    ::= { hmStatusVpnIpcompEntry 14 }

-- {COLUMN} 1.3.6.1.4.1.248.32.18.1.26.14.1.15
hmStatusVpnIpcompEntryMaxKbyte OBJECT-TYPE
    SYNTAX     Integer32 (0..2147483647)
    MAX-ACCESS read-only
    STATUS     current
    DESCRIPTION
            "-- empty --"
    ::= { hmStatusVpnIpcompEntry 15 }

-- {COLUMN} 1.3.6.1.4.1.248.32.18.1.26.14.1.16
hmStatusVpnIpcompEntryDestAddressNew OBJECT-TYPE
    SYNTAX     DisplayString (SIZE(0..39))
    MAX-ACCESS read-only
    STATUS     current
    DESCRIPTION
            ""
    ::= { hmStatusVpnIpcompEntry 16 }

-- {COLUMN} 1.3.6.1.4.1.248.32.18.1.26.14.1.17
hmStatusVpnIpcompEntrySrcAddressNew OBJECT-TYPE
    SYNTAX     DisplayString (SIZE(0..39))
    MAX-ACCESS read-only
    STATUS     current
    DESCRIPTION
            ""
    ::= { hmStatusVpnIpcompEntry 17 }

-- {TABLE} 1.3.6.1.4.1.248.32.18.1.26.17
hmStatusVpnConnectionsTable OBJECT-TYPE
    SYNTAX     SEQUENCE OF HmStatusVpnConnectionsEntry
    MAX-ACCESS not-accessible
    STATUS     current
    DESCRIPTION
            "-- empty --"
    ::= { hmStatusVpn 17 }

-- {ROW} 1.3.6.1.4.1.248.32.18.1.26.17.1
hmStatusVpnConnectionsEntry OBJECT-TYPE
    SYNTAX     HmStatusVpnConnectionsEntry
    MAX-ACCESS not-accessible
    STATUS     current
    DESCRIPTION
            ""
    INDEX {
            hmStatusVpnConnectionsEntryPeer
          }
    ::= { hmStatusVpnConnectionsTable 1 }

HmStatusVpnConnectionsEntry ::= SEQUENCE {
            hmStatusVpnConnectionsEntryPeer DisplayString,
            hmStatusVpnConnectionsEntryPhysConn DisplayString,
            hmStatusVpnConnectionsEntryRemoteGw IpAddress,
            hmStatusVpnConnectionsEntryCryptAlg DisplayString,
            hmStatusVpnConnectionsEntryCryptLength Integer32,
            hmStatusVpnConnectionsEntryHashAlg DisplayString,
            hmStatusVpnConnectionsEntryHashLength Integer32,
            hmStatusVpnConnectionsEntryHmacAlg DisplayString,
            hmStatusVpnConnectionsEntryHmacLength Integer32,
            hmStatusVpnConnectionsEntryComprAlg DisplayString,
            hmStatusVpnConnectionsEntryState INTEGER,
            hmStatusVpnConnectionsEntryMode INTEGER,
            hmStatusVpnConnectionsEntryShTime Integer32,
            hmStatusVpnConnectionsEntryB1Dt Integer32,
            hmStatusVpnConnectionsEntryLastError INTEGER,
            hmStatusVpnConnectionsEntryClientSn INTEGER,
            hmStatusVpnConnectionsEntryNatDetection INTEGER,
            hmStatusVpnConnectionsEntryConnTime Gauge32,
            hmStatusVpnConnectionsEntrySslEncaps INTEGER,
            hmStatusVpnConnectionsEntryRemoteGwNew DisplayString
    }

-- {COLUMN} 1.3.6.1.4.1.248.32.18.1.26.17.1.1
hmStatusVpnConnectionsEntryPeer OBJECT-TYPE
    SYNTAX     DisplayString (SIZE(0..16))
    MAX-ACCESS read-only
    STATUS     current
    DESCRIPTION
            "-- empty --"
    ::= { hmStatusVpnConnectionsEntry 1 }

-- {COLUMN} 1.3.6.1.4.1.248.32.18.1.26.17.1.2
hmStatusVpnConnectionsEntryPhysConn OBJECT-TYPE
    SYNTAX     DisplayString (SIZE(0..16))
    MAX-ACCESS read-only
    STATUS     current
    DESCRIPTION
            "-- empty --"
    ::= { hmStatusVpnConnectionsEntry 2 }

-- {COLUMN} 1.3.6.1.4.1.248.32.18.1.26.17.1.3
hmStatusVpnConnectionsEntryRemoteGw OBJECT-TYPE
    SYNTAX     IpAddress
    MAX-ACCESS read-only
    STATUS     obsolete
    DESCRIPTION
            "-- empty --"
    ::= { hmStatusVpnConnectionsEntry 3 }

-- {COLUMN} 1.3.6.1.4.1.248.32.18.1.26.17.1.4
hmStatusVpnConnectionsEntryCryptAlg OBJECT-TYPE
    SYNTAX     DisplayString (SIZE(0..14))
    MAX-ACCESS read-only
    STATUS     current
    DESCRIPTION
            "-- empty --"
    ::= { hmStatusVpnConnectionsEntry 4 }

-- {COLUMN} 1.3.6.1.4.1.248.32.18.1.26.17.1.5
hmStatusVpnConnectionsEntryCryptLength OBJECT-TYPE
    SYNTAX     Integer32 (0..65535)
    MAX-ACCESS read-only
    STATUS     current
    DESCRIPTION
            "-- empty --"
    ::= { hmStatusVpnConnectionsEntry 5 }

-- {COLUMN} 1.3.6.1.4.1.248.32.18.1.26.17.1.6
hmStatusVpnConnectionsEntryHashAlg OBJECT-TYPE
    SYNTAX     DisplayString (SIZE(0..14))
    MAX-ACCESS read-only
    STATUS     current
    DESCRIPTION
            "-- empty --"
    ::= { hmStatusVpnConnectionsEntry 6 }

-- {COLUMN} 1.3.6.1.4.1.248.32.18.1.26.17.1.7
hmStatusVpnConnectionsEntryHashLength OBJECT-TYPE
    SYNTAX     Integer32 (0..65535)
    MAX-ACCESS read-only
    STATUS     current
    DESCRIPTION
            "-- empty --"
    ::= { hmStatusVpnConnectionsEntry 7 }

-- {COLUMN} 1.3.6.1.4.1.248.32.18.1.26.17.1.8
hmStatusVpnConnectionsEntryHmacAlg OBJECT-TYPE
    SYNTAX     DisplayString (SIZE(0..14))
    MAX-ACCESS read-only
    STATUS     current
    DESCRIPTION
            "-- empty --"
    ::= { hmStatusVpnConnectionsEntry 8 }

-- {COLUMN} 1.3.6.1.4.1.248.32.18.1.26.17.1.9
hmStatusVpnConnectionsEntryHmacLength OBJECT-TYPE
    SYNTAX     Integer32 (0..65535)
    MAX-ACCESS read-only
    STATUS     current
    DESCRIPTION
            "-- empty --"
    ::= { hmStatusVpnConnectionsEntry 9 }

-- {COLUMN} 1.3.6.1.4.1.248.32.18.1.26.17.1.10
hmStatusVpnConnectionsEntryComprAlg OBJECT-TYPE
    SYNTAX     DisplayString (SIZE(0..14))
    MAX-ACCESS read-only
    STATUS     current
    DESCRIPTION
            "-- empty --"
    ::= { hmStatusVpnConnectionsEntry 10 }

-- {COLUMN} 1.3.6.1.4.1.248.32.18.1.26.17.1.11
hmStatusVpnConnectionsEntryState OBJECT-TYPE
    SYNTAX     INTEGER {
                  eInit (0),
                  eSetupWan (1),
                  eReady (2),
                  eWaitForCb (3),
                  eDial (4),
                  eIncomingCall (5),
                  eProtocol (6),
                  eConnection (7),
                  eDisconnecting (8),
                  eCallBack (9),
                  eBundleConnect (10),
                  eProtocol2 (11),
                  eReserved (12),
                  eBundle (13)
            }
    MAX-ACCESS read-only
    STATUS     current
    DESCRIPTION
            "-- empty --"
    ::= { hmStatusVpnConnectionsEntry 11 }

-- {COLUMN} 1.3.6.1.4.1.248.32.18.1.26.17.1.12
hmStatusVpnConnectionsEntryMode OBJECT-TYPE
    SYNTAX     INTEGER {
                  ePassive (0),
                  eActive (128)
            }
    MAX-ACCESS read-only
    STATUS     current
    DESCRIPTION
            "-- empty --"
    ::= { hmStatusVpnConnectionsEntry 12 }

-- {COLUMN} 1.3.6.1.4.1.248.32.18.1.26.17.1.13
hmStatusVpnConnectionsEntryShTime OBJECT-TYPE
    SYNTAX     Integer32 (0..65535)
    MAX-ACCESS read-only
    STATUS     current
    DESCRIPTION
            "-- empty --"
    ::= { hmStatusVpnConnectionsEntry 13 }

-- {COLUMN} 1.3.6.1.4.1.248.32.18.1.26.17.1.14
hmStatusVpnConnectionsEntryB1Dt OBJECT-TYPE
    SYNTAX     Integer32 (0..65535)
    MAX-ACCESS read-only
    STATUS     current
    DESCRIPTION
            "-- empty --"
    ::= { hmStatusVpnConnectionsEntry 14 }

-- {COLUMN} 1.3.6.1.4.1.248.32.18.1.26.17.1.16
hmStatusVpnConnectionsEntryLastError OBJECT-TYPE
    SYNTAX     INTEGER {
                  eNone (0),
                  eIcmpConnError (275),
                  eIfcILicenseExceeded (4353),
                  eIfcINoChannelAvailable (4354),
                  eIfcINoRouteToRemoteGateway (4355),
                  eIfcINoPppTableEntryMatched (4356),
                  eIfcIConnectionTimeoutDynamic (4357),
                  eIfcIConnectionTimeoutIkeIpsec (4358),
                  eIfcINoPollTableEntryMatched (4360),
                  eIfcINameResolutionFailed (4361),
                  eIfcINegotiatorChargeLocked (4369),
                  eIfcINegotiatorTimeLocked (4370),
                  eIfcINegotiatorNoDialNumber (4371),
                  eIfcINegotiatorNoRemote (4372),
                  eIfcINegotiatorRemoteBlocked (4373),
                  eIfcINegotiatorNoMulticonnect (4374),
                  eIfcINegotiatorLineError (4375),
                  eIfcIPhysicalChargeLocked (4385),
                  eIfcIPhysicalTimeLocked (4386),
                  eIfcIPhysicalNoDialNumber (4387),
                  eIfcIPhysicalNoRemote (4388),
                  eIfcIPhysicalNoServerAddress (4389),
                  eIfcIPhysicalRemoteLocked (4390),
                  eIfcIPhysicalNoMulticonnect (4391),
                  eIfcIConnectionLimitReached (4393),
                  eIfcRLicenseExceeded (4609),
                  eIfcRNoChannelAvailable (4610),
                  eIfcRNoRouteToRemoteGateway (4611),
                  eIfcRNoPppTableEntryMatched (4612),
                  eIfcRConnectionTimeoutDynamic (4613),
                  eIfcRConnectionTimeoutIkeIpsec (4614),
                  eIfcRConnectionLimitReached (4649),
                  eIfcXLinePollingFailed (4871),
                  eIfcXGwInsideRemoteNetwork (4874),
                  eIfcXPhysicalLineError (4904),
                  eIkeINoProposalMatched (8451),
                  eIkeIIkeKeyMismatch (8458),
                  eIkeIDpdTimeout (8461),
                  eIkeIUnableToGetIssuerCert (8462),
                  eIkeIUnableToGetCrl (8463),
                  eIkeIUnableToDecryptCertSignature (8464),
                  eIkeIUnableToDecryptCrlSignature (8465),
                  eIkeIUnableToDecodeIssuerPublicKey (8466),
                  eIkeICertSignatureFailure (8467),
                  eIkeICrlSignatureFailure (8468),
                  eIkeICertNotYetValid (8469),
                  eIkeICertHasExpired (8470),
                  eIkeICrlNotYetValid (8471),
                  eIkeICrlHasExpired (8472),
                  eIkeIErrorInCertNotBeforeField (8473),
                  eIkeIErrorInCertNotAfterField (8474),
                  eIkeIErrorInCrlLastUpdateField (8475),
                  eIkeIErrorInCrlNextUpdateField (8476),
                  eIkeIOutOfMem (8477),
                  eIkeIDepthZeroSelfSignedCert (8478),
                  eIkeISelfSignedCertInChain (8479),
                  eIkeIUnableToGetIssuerCertLocally (8480),
                  eIkeIUnableToVerifyLeafSignature (8481),
                  eIkeICertChainTooLong (8482),
                  eIkeICertRevoked (8483),
                  eIkeIInvalidCa (8484),
                  eIkeIPathLengthExceeded (8485),
                  eIkeIInvalidPurpose (8486),
                  eIkeICertUntrusted (8487),
                  eIkeICertRejected (8488),
                  eIkeISubjectIssuerMismatch (8489),
                  eIkeIAkidSkidMismatch (8490),
                  eIkeIAkidIssuerSerialMismatch (8491),
                  eIkeIKeyusageNoCertsign (8492),
                  eIkeIUnableToGetCrlIssuer (8493),
                  eIkeIUnhandledCriticalExtension (8494),
                  eIkeIKeyusageNoCrlSign (8495),
                  eIkeIUnhandledCriticalCrlExtension (8496),
                  eIkeICrlHasExceededExceedance (8497),
                  eIkeIApplicationVerification (8498),
                  eIkeICertRevokedUnspecified (8499),
                  eIkeICertRevokedKeyCompromise (8500),
                  eIkeICertRevokedCaCompromise (8501),
                  eIkeICertRevokedAffiliationChanged (8502),
                  eIkeICertRevokedSuperseded (8503),
                  eIkeICertRevokedCessationOfOperation (8504),
                  eIkeICertRevokedCertificateHold (8505),
                  eIkeICertRevokedRemoveFromCrl (8506),
                  eIkeICertRevokedPrivilegeWithdrawn (8507),
                  eIkeICertRevokedAACompromise (8508),
                  eIkeICertRevokedUnknownReason (8509),
                  eIkeIOutOfMemory (8702),
                  eIkeIGeneralFailure (8703),
                  eIkeRLicenseExceeded (8705),
                  eIkeRExchangeTypeMismatch (8706),
                  eIkeRNoProposalMatched (8707),
                  eIkeRIkeGroupMismatch (8708),
                  eIkeRLifeTypeUnsupported (8709),
                  eIkeRLifeDurationMismatch (8710),
                  eIkeRIdTypeUnsupported (8711),
                  eIkeRIdTypeMismatch (8712),
                  eIkeRNoRuleMatchedId (8713),
                  eIkeRIkeKeyMismatch (8714),
                  eIkeRLicenseDemosnExceeded (8715),
                  eIkeRLicenseSnExceeded (8716),
                  eIkeRDpdTimeout (8717),
                  eIkeRUnableToGetIssuerCert (8718),
                  eIkeRUnableToGetCrl (8719),
                  eIkeRUnableToDecryptCertSignature (8720),
                  eIkeRUnableToDecryptCrlSignature (8721),
                  eIkeRUnableToDecodeIssuerPublicKey (8722),
                  eIkeRCertSignatureFailure (8723),
                  eIkeRCrlSignatureFailure (8724),
                  eIkeRCertNotYetValid (8725),
                  eIkeRCertHasExpired (8726),
                  eIkeRCrlNotYetValid (8727),
                  eIkeRCrlHasExpired (8728),
                  eIkeRErrorInCertNotBeforeField (8729),
                  eIkeRErrorInCertNotAfterField (8730),
                  eIkeRErrorInCrlLastUpdateField (8731),
                  eIkeRErrorInCrlNextUpdateField (8732),
                  eIkeROutOfMem (8733),
                  eIkeRDepthZeroSelfSignedCert (8734),
                  eIkeRSelfSignedCertInChain (8735),
                  eIkeRUnableToGetIssuerCertLocally (8736),
                  eIkeRUnableToVerifyLeafSignature (8737),
                  eIkeRCertChainTooLong (8738),
                  eIkeRCertRevoked (8739),
                  eIkeRInvalidCa (8740),
                  eIkeRPathLengthExceeded (8741),
                  eIkeRInvalidPurpose (8742),
                  eIkeRCertUntrusted (8743),
                  eIkeRCertRejected (8744),
                  eIkeRSubjectIssuerMismatch (8745),
                  eIkeRAkidSkidMismatch (8746),
                  eIkeRAkidIssuerSerialMismatch (8747),
                  eIkeRKeyusageNoCertsign (8748),
                  eIkeRUnableToGetCrlIssuer (8749),
                  eIkeRUnhandledCriticalExtension (8750),
                  eIkeRKeyusageNoCrlSign (8751),
                  eIkeRUnhandledCriticalCrlExtension (8752),
                  eIkeRCrlHasExceededExceedance (8753),
                  eIkeRApplicationVerification (8754),
                  eIkeRCertRevokedUnspecified (8755),
                  eIkeRCertRevokedKeyCompromise (8756),
                  eIkeRCertRevokedCaCompromise (8757),
                  eIkeRCertRevokedAffiliationChanged (8758),
                  eIkeRCertRevokedSuperseded (8759),
                  eIkeRCertRevokedCessationOfOperation (8760),
                  eIkeRCertRevokedCertificateHold (8761),
                  eIkeRCertRevokedRemoveFromCrl (8762),
                  eIkeRCertRevokedPrivilegeWithdrawn (8763),
                  eIkeRCertRevokedAACompromise (8764),
                  eIkeRCertRevokedUnknownReason (8765),
                  eIkeRConnLimitReached (8784),
                  eIkeROutOfMemory (8958),
                  eIkeRGeneralFailure (8959),
                  eIpsecINoProposalMatched (12546),
                  eIpsecRNoRuleMatchedIds (12801),
                  eIpsecRNoProposalMatched (12802),
                  eIpsecRPfsGroupMismatch (12803),
                  eRemoteDisconnected (17153),
                  eManualDisconnect (17154),
                  eShortholdExpired (17155),
                  ePhysicalDisconnected (17156),
                  eInvalidPhysicalChannel (17157),
                  eDynamicVpnReconnect (17158),
                  eConfigurationChanged (17159),
                  eRemovedFromConfig (17160)
            }
    MAX-ACCESS read-write
    STATUS     current
    DESCRIPTION
            "-- empty --"
    ::= { hmStatusVpnConnectionsEntry 16 }

-- {COLUMN} 1.3.6.1.4.1.248.32.18.1.26.17.1.17
hmStatusVpnConnectionsEntryClientSn OBJECT-TYPE
    SYNTAX     INTEGER {
                  eNotAvailable (-1),
                  eDemoVersion (0)
            }
    MAX-ACCESS read-only
    STATUS     current
    DESCRIPTION
            "-- empty --"
    ::= { hmStatusVpnConnectionsEntry 17 }

-- {COLUMN} 1.3.6.1.4.1.248.32.18.1.26.17.1.18
hmStatusVpnConnectionsEntryNatDetection OBJECT-TYPE
    SYNTAX     INTEGER {
                  eNoNat (0),
                  eNatLocal (1),
                  eNatRemote (2),
                  eNatBoth (3)
            }
    MAX-ACCESS read-only
    STATUS     current
    DESCRIPTION
            "-- empty --"
    ::= { hmStatusVpnConnectionsEntry 18 }

-- {COLUMN} 1.3.6.1.4.1.248.32.18.1.26.17.1.19
hmStatusVpnConnectionsEntryConnTime OBJECT-TYPE
    SYNTAX     Gauge32
    MAX-ACCESS read-only
    STATUS     current
    DESCRIPTION
            "-- empty --"
    ::= { hmStatusVpnConnectionsEntry 19 }

-- {COLUMN} 1.3.6.1.4.1.248.32.18.1.26.17.1.20
hmStatusVpnConnectionsEntrySslEncaps OBJECT-TYPE
    SYNTAX     INTEGER {
                  eNo (0),
                  eYes (1)
            }
    MAX-ACCESS read-only
    STATUS     current
    DESCRIPTION
            "-- empty --"
    ::= { hmStatusVpnConnectionsEntry 20 }

-- {COLUMN} 1.3.6.1.4.1.248.32.18.1.26.17.1.21
hmStatusVpnConnectionsEntryRemoteGwNew OBJECT-TYPE
    SYNTAX     DisplayString (SIZE(0..39))
    MAX-ACCESS read-only
    STATUS     current
    DESCRIPTION
            ""
    ::= { hmStatusVpnConnectionsEntry 21 }

-- {SCALAR} 1.3.6.1.4.1.248.32.18.1.26.20
hmStatusVpnRxPackets OBJECT-TYPE
    SYNTAX     Counter32
    MAX-ACCESS read-only
    STATUS     current
    DESCRIPTION
            "-- empty --"
    ::= { hmStatusVpn 20 }

-- {SCALAR} 1.3.6.1.4.1.248.32.18.1.26.21
hmStatusVpnTxPackets OBJECT-TYPE
    SYNTAX     Counter32
    MAX-ACCESS read-only
    STATUS     current
    DESCRIPTION
            "-- empty --"
    ::= { hmStatusVpn 21 }

-- {SCALAR} 1.3.6.1.4.1.248.32.18.1.26.22
hmStatusVpnTxDropped OBJECT-TYPE
    SYNTAX     Counter32
    MAX-ACCESS read-only
    STATUS     current
    DESCRIPTION
            "-- empty --"
    ::= { hmStatusVpn 22 }

-- {SCALAR} 1.3.6.1.4.1.248.32.18.1.26.23
hmStatusVpnRxErrors OBJECT-TYPE
    SYNTAX     Counter32
    MAX-ACCESS read-only
    STATUS     current
    DESCRIPTION
            "-- empty --"
    ::= { hmStatusVpn 23 }

-- {SCALAR} 1.3.6.1.4.1.248.32.18.1.26.25
hmStatusVpnTxInvalid OBJECT-TYPE
    SYNTAX     Counter64
    MAX-ACCESS read-only
    STATUS     current
    DESCRIPTION
            "-- empty --"
    ::= { hmStatusVpn 25 }

-- {SCALAR} 1.3.6.1.4.1.248.32.18.1.26.26
hmStatusVpnTxNoSa OBJECT-TYPE
    SYNTAX     Counter64
    MAX-ACCESS read-only
    STATUS     current
    DESCRIPTION
            "-- empty --"
    ::= { hmStatusVpn 26 }

-- {SCALAR} 1.3.6.1.4.1.248.32.18.1.26.27
hmStatusVpnTxNoPolicy OBJECT-TYPE
    SYNTAX     Counter64
    MAX-ACCESS read-only
    STATUS     current
    DESCRIPTION
            "-- empty --"
    ::= { hmStatusVpn 27 }

-- {SCALAR} 1.3.6.1.4.1.248.32.18.1.26.28
hmStatusVpnRxEspAuthFail OBJECT-TYPE
    SYNTAX     Counter64
    MAX-ACCESS read-only
    STATUS     current
    DESCRIPTION
            "-- empty --"
    ::= { hmStatusVpn 28 }

-- {SCALAR} 1.3.6.1.4.1.248.32.18.1.26.29
hmStatusVpnRxAhAuthFail OBJECT-TYPE
    SYNTAX     Counter64
    MAX-ACCESS read-only
    STATUS     current
    DESCRIPTION
            "-- empty --"
    ::= { hmStatusVpn 29 }

-- {SCALAR} 1.3.6.1.4.1.248.32.18.1.26.30
hmStatusVpnRxIpcompFail OBJECT-TYPE
    SYNTAX     Counter64
    MAX-ACCESS read-only
    STATUS     current
    DESCRIPTION
            "-- empty --"
    ::= { hmStatusVpn 30 }

-- {SCALAR} 1.3.6.1.4.1.248.32.18.1.26.31
hmStatusVpnRxEspReplay OBJECT-TYPE
    SYNTAX     Counter64
    MAX-ACCESS read-only
    STATUS     current
    DESCRIPTION
            "-- empty --"
    ::= { hmStatusVpn 31 }

-- {SCALAR} 1.3.6.1.4.1.248.32.18.1.26.32
hmStatusVpnRxAhReplay OBJECT-TYPE
    SYNTAX     Counter64
    MAX-ACCESS read-only
    STATUS     current
    DESCRIPTION
            "-- empty --"
    ::= { hmStatusVpn 32 }

-- {SCALAR} 1.3.6.1.4.1.248.32.18.1.26.33
hmStatusVpnRxBadSpi OBJECT-TYPE
    SYNTAX     Counter64
    MAX-ACCESS read-only
    STATUS     current
    DESCRIPTION
            "-- empty --"
    ::= { hmStatusVpn 33 }

-- {SCALAR} 1.3.6.1.4.1.248.32.18.1.26.34
hmStatusVpnRxInvalid OBJECT-TYPE
    SYNTAX     Counter64
    MAX-ACCESS read-only
    STATUS     current
    DESCRIPTION
            "-- empty --"
    ::= { hmStatusVpn 34 }

-- {SCALAR} 1.3.6.1.4.1.248.32.18.1.26.35
hmStatusVpnRxNoSa OBJECT-TYPE
    SYNTAX     Counter64
    MAX-ACCESS read-only
    STATUS     current
    DESCRIPTION
            "-- empty --"
    ::= { hmStatusVpn 35 }

-- {SCALAR} 1.3.6.1.4.1.248.32.18.1.26.36
hmStatusVpnQueueError OBJECT-TYPE
    SYNTAX     Counter64
    MAX-ACCESS read-only
    STATUS     current
    DESCRIPTION
            "-- empty --"
    ::= { hmStatusVpn 36 }

-- {NODE} 1.3.6.1.4.1.248.32.18.1.26.37
hmStatusVpnDhGroups OBJECT IDENTIFIER ::= { hmStatusVpn 37 }

-- {TABLE} 1.3.6.1.4.1.248.32.18.1.26.37.5
hmStatusVpnDhGroupsPrecalculationTable OBJECT-TYPE
    SYNTAX     SEQUENCE OF HmStatusVpnDhGroupsPrecalculationEntry
    MAX-ACCESS not-accessible
    STATUS     current
    DESCRIPTION
            "-- empty --"
    ::= { hmStatusVpnDhGroups 5 }

-- {ROW} 1.3.6.1.4.1.248.32.18.1.26.37.5.1
hmStatusVpnDhGroupsPrecalculationEntry OBJECT-TYPE
    SYNTAX     HmStatusVpnDhGroupsPrecalculationEntry
    MAX-ACCESS not-accessible
    STATUS     current
    DESCRIPTION
            ""
    INDEX {
            hmStatusVpnDhGroupsPrecalculationEntryDhGroup
          }
    ::= { hmStatusVpnDhGroupsPrecalculationTable 1 }

HmStatusVpnDhGroupsPrecalculationEntry ::= SEQUENCE {
            hmStatusVpnDhGroupsPrecalculationEntryDhGroup Integer32,
            hmStatusVpnDhGroupsPrecalculationEntryRuleDependentTarget Integer32,
            hmStatusVpnDhGroupsPrecalculationEntryConfiguredTarget Integer32,
            hmStatusVpnDhGroupsPrecalculationEntryActualTarget Integer32,
            hmStatusVpnDhGroupsPrecalculationEntryCurrentStock Integer32
    }

-- {COLUMN} 1.3.6.1.4.1.248.32.18.1.26.37.5.1.1
hmStatusVpnDhGroupsPrecalculationEntryDhGroup OBJECT-TYPE
    SYNTAX     Integer32 (0..2147483647)
    MAX-ACCESS read-only
    STATUS     current
    DESCRIPTION
            "-- empty --"
    ::= { hmStatusVpnDhGroupsPrecalculationEntry 1 }

-- {COLUMN} 1.3.6.1.4.1.248.32.18.1.26.37.5.1.2
hmStatusVpnDhGroupsPrecalculationEntryRuleDependentTarget OBJECT-TYPE
    SYNTAX     Integer32 (0..2147483647)
    MAX-ACCESS read-only
    STATUS     current
    DESCRIPTION
            "-- empty --"
    ::= { hmStatusVpnDhGroupsPrecalculationEntry 2 }

-- {COLUMN} 1.3.6.1.4.1.248.32.18.1.26.37.5.1.3
hmStatusVpnDhGroupsPrecalculationEntryConfiguredTarget OBJECT-TYPE
    SYNTAX     Integer32 (0..2147483647)
    MAX-ACCESS read-only
    STATUS     current
    DESCRIPTION
            "-- empty --"
    ::= { hmStatusVpnDhGroupsPrecalculationEntry 3 }

-- {COLUMN} 1.3.6.1.4.1.248.32.18.1.26.37.5.1.4
hmStatusVpnDhGroupsPrecalculationEntryActualTarget OBJECT-TYPE
    SYNTAX     Integer32 (0..2147483647)
    MAX-ACCESS read-only
    STATUS     current
    DESCRIPTION
            "-- empty --"
    ::= { hmStatusVpnDhGroupsPrecalculationEntry 4 }

-- {COLUMN} 1.3.6.1.4.1.248.32.18.1.26.37.5.1.5
hmStatusVpnDhGroupsPrecalculationEntryCurrentStock OBJECT-TYPE
    SYNTAX     Integer32 (0..2147483647)
    MAX-ACCESS read-only
    STATUS     current
    DESCRIPTION
            "-- empty --"
    ::= { hmStatusVpnDhGroupsPrecalculationEntry 5 }

-- {SCALAR} 1.3.6.1.4.1.248.32.18.1.26.38
hmStatusVpnDeleteConnErrors OBJECT-TYPE
    SYNTAX     DisplayString
    MAX-ACCESS read-write
    STATUS     current
    DESCRIPTION
            "-- empty --"
    ::= { hmStatusVpn 38 }

-- {NODE} 1.3.6.1.4.1.248.32.18.1.27
hmStatusPptp OBJECT IDENTIFIER ::= { hmStatus 27 }

-- {SCALAR} 1.3.6.1.4.1.248.32.18.1.27.1
hmStatusPptpRxPackets OBJECT-TYPE
    SYNTAX     Counter32
    MAX-ACCESS read-only
    STATUS     current
    DESCRIPTION
            "-- empty --"
    ::= { hmStatusPptp 1 }

-- {SCALAR} 1.3.6.1.4.1.248.32.18.1.27.2
hmStatusPptpTxPackets OBJECT-TYPE
    SYNTAX     Counter32
    MAX-ACCESS read-only
    STATUS     current
    DESCRIPTION
            "-- empty --"
    ::= { hmStatusPptp 2 }

-- {SCALAR} 1.3.6.1.4.1.248.32.18.1.27.3
hmStatusPptpEchoRetries OBJECT-TYPE
    SYNTAX     Counter32
    MAX-ACCESS read-only
    STATUS     current
    DESCRIPTION
            "-- empty --"
    ::= { hmStatusPptp 3 }

-- {SCALAR} 1.3.6.1.4.1.248.32.18.1.27.4
hmStatusPptpAckTimeouts OBJECT-TYPE
    SYNTAX     Counter32
    MAX-ACCESS read-only
    STATUS     current
    DESCRIPTION
            "-- empty --"
    ::= { hmStatusPptp 4 }

-- {SCALAR} 1.3.6.1.4.1.248.32.18.1.27.5
hmStatusPptpDroppedPackets OBJECT-TYPE
    SYNTAX     Counter32
    MAX-ACCESS read-only
    STATUS     current
    DESCRIPTION
            "-- empty --"
    ::= { hmStatusPptp 5 }

-- {SCALAR} 1.3.6.1.4.1.248.32.18.1.27.6
hmStatusPptpRxErrors OBJECT-TYPE
    SYNTAX     Counter32
    MAX-ACCESS read-only
    STATUS     current
    DESCRIPTION
            "-- empty --"
    ::= { hmStatusPptp 6 }

-- {SCALAR} 1.3.6.1.4.1.248.32.18.1.27.7
hmStatusPptpTcpErrors OBJECT-TYPE
    SYNTAX     Counter32
    MAX-ACCESS read-only
    STATUS     current
    DESCRIPTION
            "-- empty --"
    ::= { hmStatusPptp 7 }

-- {SCALAR} 1.3.6.1.4.1.248.32.18.1.27.8
hmStatusPptpCallErrors OBJECT-TYPE
    SYNTAX     Counter32
    MAX-ACCESS read-only
    STATUS     current
    DESCRIPTION
            "-- empty --"
    ::= { hmStatusPptp 8 }

-- {TABLE} 1.3.6.1.4.1.248.32.18.1.27.9
hmStatusPptpConnectionsTable OBJECT-TYPE
    SYNTAX     SEQUENCE OF HmStatusPptpConnectionsEntry
    MAX-ACCESS not-accessible
    STATUS     current
    DESCRIPTION
            "-- empty --"
    ::= { hmStatusPptp 9 }

-- {ROW} 1.3.6.1.4.1.248.32.18.1.27.9.1
hmStatusPptpConnectionsEntry OBJECT-TYPE
    SYNTAX     HmStatusPptpConnectionsEntry
    MAX-ACCESS not-accessible
    STATUS     current
    DESCRIPTION
            ""
    INDEX {
            hmStatusPptpConnectionsEntryChannel
          }
    ::= { hmStatusPptpConnectionsTable 1 }

HmStatusPptpConnectionsEntry ::= SEQUENCE {
            hmStatusPptpConnectionsEntryChannel DisplayString,
            hmStatusPptpConnectionsEntryState INTEGER,
            hmStatusPptpConnectionsEntryMode INTEGER,
            hmStatusPptpConnectionsEntryShTime Integer32,
            hmStatusPptpConnectionsEntryPhysConnection DisplayString,
            hmStatusPptpConnectionsEntryPeerAddress IpAddress,
            hmStatusPptpConnectionsEntryIpAddress IpAddress,
            hmStatusPptpConnectionsEntryDnsDefault IpAddress,
            hmStatusPptpConnectionsEntryNbnsDefault IpAddress,
            hmStatusPptpConnectionsEntryLastError INTEGER,
            hmStatusPptpConnectionsEntryDnsBackup IpAddress,
            hmStatusPptpConnectionsEntryNbnsBackup IpAddress,
            hmStatusPptpConnectionsEntryConnTime Gauge32,
            hmStatusPptpConnectionsEntryGateway IpAddress,
            hmStatusPptpConnectionsEntryEncryption INTEGER
    }

-- {COLUMN} 1.3.6.1.4.1.248.32.18.1.27.9.1.1
hmStatusPptpConnectionsEntryChannel OBJECT-TYPE
    SYNTAX     DisplayString (SIZE(0..16))
    MAX-ACCESS read-only
    STATUS     current
    DESCRIPTION
            "-- empty --"
    ::= { hmStatusPptpConnectionsEntry 1 }

-- {COLUMN} 1.3.6.1.4.1.248.32.18.1.27.9.1.3
hmStatusPptpConnectionsEntryState OBJECT-TYPE
    SYNTAX     INTEGER {
                  eInit (0),
                  eSetupWan (1),
                  eReady (2),
                  eWaitForCb (3),
                  eDial (4),
                  eIncomingCall (5),
                  eProtocol (6),
                  eConnection (7),
                  eDisconnecting (8),
                  eCallBack (9),
                  eBundleConnect (10),
                  eProtocol2 (11),
                  eReserved (12),
                  eBundle (13)
            }
    MAX-ACCESS read-only
    STATUS     current
    DESCRIPTION
            "-- empty --"
    ::= { hmStatusPptpConnectionsEntry 3 }

-- {COLUMN} 1.3.6.1.4.1.248.32.18.1.27.9.1.4
hmStatusPptpConnectionsEntryMode OBJECT-TYPE
    SYNTAX     INTEGER {
                  ePassive (0),
                  eActive (128)
            }
    MAX-ACCESS read-only
    STATUS     current
    DESCRIPTION
            "-- empty --"
    ::= { hmStatusPptpConnectionsEntry 4 }

-- {COLUMN} 1.3.6.1.4.1.248.32.18.1.27.9.1.5
hmStatusPptpConnectionsEntryShTime OBJECT-TYPE
    SYNTAX     Integer32 (0..65535)
    MAX-ACCESS read-only
    STATUS     current
    DESCRIPTION
            "-- empty --"
    ::= { hmStatusPptpConnectionsEntry 5 }

-- {COLUMN} 1.3.6.1.4.1.248.32.18.1.27.9.1.6
hmStatusPptpConnectionsEntryPhysConnection OBJECT-TYPE
    SYNTAX     DisplayString (SIZE(0..16))
    MAX-ACCESS read-only
    STATUS     current
    DESCRIPTION
            "-- empty --"
    ::= { hmStatusPptpConnectionsEntry 6 }

-- {COLUMN} 1.3.6.1.4.1.248.32.18.1.27.9.1.7
hmStatusPptpConnectionsEntryPeerAddress OBJECT-TYPE
    SYNTAX     IpAddress
    MAX-ACCESS read-only
    STATUS     current
    DESCRIPTION
            "-- empty --"
    ::= { hmStatusPptpConnectionsEntry 7 }

-- {COLUMN} 1.3.6.1.4.1.248.32.18.1.27.9.1.8
hmStatusPptpConnectionsEntryIpAddress OBJECT-TYPE
    SYNTAX     IpAddress
    MAX-ACCESS read-only
    STATUS     current
    DESCRIPTION
            "-- empty --"
    ::= { hmStatusPptpConnectionsEntry 8 }

-- {COLUMN} 1.3.6.1.4.1.248.32.18.1.27.9.1.9
hmStatusPptpConnectionsEntryDnsDefault OBJECT-TYPE
    SYNTAX     IpAddress
    MAX-ACCESS read-only
    STATUS     current
    DESCRIPTION
            "-- empty --"
    ::= { hmStatusPptpConnectionsEntry 9 }

-- {COLUMN} 1.3.6.1.4.1.248.32.18.1.27.9.1.10
hmStatusPptpConnectionsEntryNbnsDefault OBJECT-TYPE
    SYNTAX     IpAddress
    MAX-ACCESS read-only
    STATUS     current
    DESCRIPTION
            "-- empty --"
    ::= { hmStatusPptpConnectionsEntry 10 }

-- {COLUMN} 1.3.6.1.4.1.248.32.18.1.27.9.1.11
hmStatusPptpConnectionsEntryLastError OBJECT-TYPE
    SYNTAX     INTEGER {
                  eNone (0),
                  eRemoteDoubled (267),
                  eIcmpConnError (275),
                  eDhcpTimeout (277),
                  ePptpNoResponse (278),
                  eVpnNoResponse (279),
                  eArpNoResponse (280),
                  ePptpNoChannel (513),
                  ePptpBadFormat (514),
                  ePptpBadValue (515),
                  ePptpNoRessource (516),
                  ePptpBadCallId (517),
                  ePptpGenError (518),
                  ePptpNoAddress (519),
                  ePptpDnsResolvError (520),
                  ePptpTcpConnError (521),
                  eRemoteDisconnected (17153),
                  eManualDisconnect (17154),
                  eShortholdExpired (17155),
                  ePhysicalDisconnected (17156),
                  eInvalidPhysicalChannel (17157),
                  eDynamicVpnReconnect (17158),
                  eConfigurationChanged (17159),
                  eRemovedFromConfig (17160),
                  eLcpRejected (32768),
                  eAuthError (32769),
                  eAuthRejected (32770),
                  eLcpConnError (32771),
                  ePapRejected (32784),
                  ePapRxTimeout (32785),
                  ePapTxTimeout (32786),
                  eWrongPapReq (32787),
                  ePapNakReceived (32788),
                  eUnknPapPeer (32789),
                  eChapRejected (32800),
                  eChapRxTimeout (32801),
                  eChapTxTimeout (32802),
                  eWrongChapResp (32803),
                  eChapFailRecvd (32804),
                  eUnknChapPeer (32805),
                  eIpxcpRejected (32816),
                  eWrongIpxcpNet (32817),
                  eIpxcpNetReject (32818),
                  eIpxcpRouteUnkn (32819),
                  eIpcpRejected (32832),
                  eCcpRejected (32848),
                  eNoNcpAvailable (33008)
            }
    MAX-ACCESS read-write
    STATUS     current
    DESCRIPTION
            "-- empty --"
    ::= { hmStatusPptpConnectionsEntry 11 }

-- {COLUMN} 1.3.6.1.4.1.248.32.18.1.27.9.1.12
hmStatusPptpConnectionsEntryDnsBackup OBJECT-TYPE
    SYNTAX     IpAddress
    MAX-ACCESS read-only
    STATUS     current
    DESCRIPTION
            "-- empty --"
    ::= { hmStatusPptpConnectionsEntry 12 }

-- {COLUMN} 1.3.6.1.4.1.248.32.18.1.27.9.1.13
hmStatusPptpConnectionsEntryNbnsBackup OBJECT-TYPE
    SYNTAX     IpAddress
    MAX-ACCESS read-only
    STATUS     current
    DESCRIPTION
            "-- empty --"
    ::= { hmStatusPptpConnectionsEntry 13 }

-- {COLUMN} 1.3.6.1.4.1.248.32.18.1.27.9.1.14
hmStatusPptpConnectionsEntryConnTime OBJECT-TYPE
    SYNTAX     Gauge32
    MAX-ACCESS read-only
    STATUS     current
    DESCRIPTION
            "-- empty --"
    ::= { hmStatusPptpConnectionsEntry 14 }

-- {COLUMN} 1.3.6.1.4.1.248.32.18.1.27.9.1.15
hmStatusPptpConnectionsEntryGateway OBJECT-TYPE
    SYNTAX     IpAddress
    MAX-ACCESS read-only
    STATUS     current
    DESCRIPTION
            "-- empty --"
    ::= { hmStatusPptpConnectionsEntry 15 }

-- {COLUMN} 1.3.6.1.4.1.248.32.18.1.27.9.1.16
hmStatusPptpConnectionsEntryEncryption OBJECT-TYPE
    SYNTAX     INTEGER {
                  eOff (0),
                  e128Bits (64),
                  e56Bits (192),
                  e40Bits (224)
            }
    MAX-ACCESS read-only
    STATUS     current
    DESCRIPTION
            "-- empty --"
    ::= { hmStatusPptpConnectionsEntry 16 }

-- {SCALAR} 1.3.6.1.4.1.248.32.18.1.27.10
hmStatusPptpTunnel OBJECT-TYPE
    SYNTAX     Integer32 (0..2147483647)
    MAX-ACCESS read-only
    STATUS     current
    DESCRIPTION
            "-- empty --"
    ::= { hmStatusPptp 10 }

-- {SCALAR} 1.3.6.1.4.1.248.32.18.1.27.11
hmStatusPptpDeleteValues OBJECT-TYPE
    SYNTAX     DisplayString
    MAX-ACCESS read-write
    STATUS     current
    DESCRIPTION
            "-- empty --"
    ::= { hmStatusPptp 11 }

-- {SCALAR} 1.3.6.1.4.1.248.32.18.1.27.12
hmStatusPptpFlowControlQueue OBJECT-TYPE
    SYNTAX     Integer32 (0..2147483647)
    MAX-ACCESS read-only
    STATUS     current
    DESCRIPTION
            "-- empty --"
    ::= { hmStatusPptp 12 }

-- {SCALAR} 1.3.6.1.4.1.248.32.18.1.27.13
hmStatusPptpEncryptedTunnel OBJECT-TYPE
    SYNTAX     Integer32 (0..2147483647)
    MAX-ACCESS read-only
    STATUS     current
    DESCRIPTION
            "-- empty --"
    ::= { hmStatusPptp 13 }

-- {NODE} 1.3.6.1.4.1.248.32.18.1.28
hmStatusPppoe OBJECT IDENTIFIER ::= { hmStatus 28 }

-- {SCALAR} 1.3.6.1.4.1.248.32.18.1.28.1
hmStatusPppoeTxPadi OBJECT-TYPE
    SYNTAX     Integer32 (0..2147483647)
    MAX-ACCESS read-only
    STATUS     current
    DESCRIPTION
            "-- empty --"
    ::= { hmStatusPppoe 1 }

-- {SCALAR} 1.3.6.1.4.1.248.32.18.1.28.2
hmStatusPppoeRxPado OBJECT-TYPE
    SYNTAX     Integer32 (0..2147483647)
    MAX-ACCESS read-only
    STATUS     current
    DESCRIPTION
            "-- empty --"
    ::= { hmStatusPppoe 2 }

-- {SCALAR} 1.3.6.1.4.1.248.32.18.1.28.3
hmStatusPppoeTxPadr OBJECT-TYPE
    SYNTAX     Integer32 (0..2147483647)
    MAX-ACCESS read-only
    STATUS     current
    DESCRIPTION
            "-- empty --"
    ::= { hmStatusPppoe 3 }

-- {SCALAR} 1.3.6.1.4.1.248.32.18.1.28.4
hmStatusPppoeRxPads OBJECT-TYPE
    SYNTAX     Integer32 (0..2147483647)
    MAX-ACCESS read-only
    STATUS     current
    DESCRIPTION
            "-- empty --"
    ::= { hmStatusPppoe 4 }

-- {SCALAR} 1.3.6.1.4.1.248.32.18.1.28.5
hmStatusPppoeTxPadt OBJECT-TYPE
    SYNTAX     Integer32 (0..2147483647)
    MAX-ACCESS read-only
    STATUS     current
    DESCRIPTION
            "-- empty --"
    ::= { hmStatusPppoe 5 }

-- {SCALAR} 1.3.6.1.4.1.248.32.18.1.28.6
hmStatusPppoeRxPadt OBJECT-TYPE
    SYNTAX     Integer32 (0..2147483647)
    MAX-ACCESS read-only
    STATUS     current
    DESCRIPTION
            "-- empty --"
    ::= { hmStatusPppoe 6 }

-- {SCALAR} 1.3.6.1.4.1.248.32.18.1.28.7
hmStatusPppoeTxProtocol OBJECT-TYPE
    SYNTAX     Integer32 (0..2147483647)
    MAX-ACCESS read-only
    STATUS     current
    DESCRIPTION
            "-- empty --"
    ::= { hmStatusPppoe 7 }

-- {SCALAR} 1.3.6.1.4.1.248.32.18.1.28.8
hmStatusPppoeRxProtocol OBJECT-TYPE
    SYNTAX     Integer32 (0..2147483647)
    MAX-ACCESS read-only
    STATUS     current
    DESCRIPTION
            "-- empty --"
    ::= { hmStatusPppoe 8 }

-- {SCALAR} 1.3.6.1.4.1.248.32.18.1.28.9
hmStatusPppoeTxData OBJECT-TYPE
    SYNTAX     Integer32 (0..2147483647)
    MAX-ACCESS read-only
    STATUS     current
    DESCRIPTION
            "-- empty --"
    ::= { hmStatusPppoe 9 }

-- {SCALAR} 1.3.6.1.4.1.248.32.18.1.28.10
hmStatusPppoeRxData OBJECT-TYPE
    SYNTAX     Integer32 (0..2147483647)
    MAX-ACCESS read-only
    STATUS     current
    DESCRIPTION
            "-- empty --"
    ::= { hmStatusPppoe 10 }

-- {SCALAR} 1.3.6.1.4.1.248.32.18.1.28.11
hmStatusPppoeRxBad OBJECT-TYPE
    SYNTAX     Integer32 (0..2147483647)
    MAX-ACCESS read-only
    STATUS     current
    DESCRIPTION
            "-- empty --"
    ::= { hmStatusPppoe 11 }

-- {SCALAR} 1.3.6.1.4.1.248.32.18.1.28.12
hmStatusPppoeAcName OBJECT-TYPE
    SYNTAX     DisplayString (SIZE(0..63))
    MAX-ACCESS read-only
    STATUS     current
    DESCRIPTION
            "-- empty --"
    ::= { hmStatusPppoe 12 }

-- {SCALAR} 1.3.6.1.4.1.248.32.18.1.28.13
hmStatusPppoeService OBJECT-TYPE
    SYNTAX     DisplayString (SIZE(0..63))
    MAX-ACCESS read-only
    STATUS     current
    DESCRIPTION
            "-- empty --"
    ::= { hmStatusPppoe 13 }

-- {SCALAR} 1.3.6.1.4.1.248.32.18.1.28.30
hmStatusPppoeDeleteValues OBJECT-TYPE
    SYNTAX     DisplayString
    MAX-ACCESS read-write
    STATUS     current
    DESCRIPTION
            "-- empty --"
    ::= { hmStatusPppoe 30 }

-- {NODE} 1.3.6.1.4.1.248.32.18.1.31
hmStatusLanBridge OBJECT IDENTIFIER ::= { hmStatus 31 }

-- {TABLE} 1.3.6.1.4.1.248.32.18.1.31.1
hmStatusLanBridgeAddressTableTable OBJECT-TYPE
    SYNTAX     SEQUENCE OF HmStatusLanBridgeAddressTableEntry
    MAX-ACCESS not-accessible
    STATUS     current
    DESCRIPTION
            "-- empty --"
    ::= { hmStatusLanBridge 1 }

-- {ROW} 1.3.6.1.4.1.248.32.18.1.31.1.1
hmStatusLanBridgeAddressTableEntry OBJECT-TYPE
    SYNTAX     HmStatusLanBridgeAddressTableEntry
    MAX-ACCESS not-accessible
    STATUS     current
    DESCRIPTION
            ""
    INDEX {
            hmStatusLanBridgeAddressTableEntryIndex
          }
    ::= { hmStatusLanBridgeAddressTableTable 1 }

HmStatusLanBridgeAddressTableEntry ::= SEQUENCE {
            hmStatusLanBridgeAddressTableEntryIndex Integer32,
            hmStatusLanBridgeAddressTableEntryAge Integer32,
            hmStatusLanBridgeAddressTableEntryMacAddress MacAddress,
            hmStatusLanBridgeAddressTableEntryEthernetPort INTEGER,
            hmStatusLanBridgeAddressTableEntryBrgAddr MacAddress,
            hmStatusLanBridgeAddressTableEntryVlanId Integer32,
            hmStatusLanBridgeAddressTableEntryBridgeGroup INTEGER,
            hmStatusLanBridgeAddressTableEntryPort DisplayString
    }

-- {COLUMN} 1.3.6.1.4.1.248.32.18.1.31.1.1.1
hmStatusLanBridgeAddressTableEntryIndex OBJECT-TYPE
    SYNTAX     Integer32 (0..2147483647)
    MAX-ACCESS read-only
    STATUS     current
    DESCRIPTION
            "-- empty --"
    ::= { hmStatusLanBridgeAddressTableEntry 1 }

-- {COLUMN} 1.3.6.1.4.1.248.32.18.1.31.1.1.2
hmStatusLanBridgeAddressTableEntryAge OBJECT-TYPE
    SYNTAX     Integer32 (0..65535)
    MAX-ACCESS read-only
    STATUS     current
    DESCRIPTION
            "-- empty --"
    ::= { hmStatusLanBridgeAddressTableEntry 2 }

-- {COLUMN} 1.3.6.1.4.1.248.32.18.1.31.1.1.3
hmStatusLanBridgeAddressTableEntryMacAddress OBJECT-TYPE
    SYNTAX     MacAddress
    MAX-ACCESS read-only
    STATUS     current
    DESCRIPTION
            "-- empty --"
    ::= { hmStatusLanBridgeAddressTableEntry 3 }

-- {COLUMN} 1.3.6.1.4.1.248.32.18.1.31.1.1.5
hmStatusLanBridgeAddressTableEntryEthernetPort OBJECT-TYPE
    SYNTAX     INTEGER {
                  eEth1 (2),
                  eEth2 (3),
                  eEth3 (4),
                  eEth4 (5)
            }
    MAX-ACCESS read-only
    STATUS     current
    DESCRIPTION
            "-- empty --"
    ::= { hmStatusLanBridgeAddressTableEntry 5 }

-- {COLUMN} 1.3.6.1.4.1.248.32.18.1.31.1.1.6
hmStatusLanBridgeAddressTableEntryBrgAddr OBJECT-TYPE
    SYNTAX     MacAddress
    MAX-ACCESS read-only
    STATUS     current
    DESCRIPTION
            "-- empty --"
    ::= { hmStatusLanBridgeAddressTableEntry 6 }

-- {COLUMN} 1.3.6.1.4.1.248.32.18.1.31.1.1.7
hmStatusLanBridgeAddressTableEntryVlanId OBJECT-TYPE
    SYNTAX     Integer32 (0..65535)
    MAX-ACCESS read-only
    STATUS     current
    DESCRIPTION
            "-- empty --"
    ::= { hmStatusLanBridgeAddressTableEntry 7 }

-- {COLUMN} 1.3.6.1.4.1.248.32.18.1.31.1.1.8
hmStatusLanBridgeAddressTableEntryBridgeGroup OBJECT-TYPE
    SYNTAX     INTEGER {
                  eBrg1 (0),
                  eBrg2 (1),
                  eBrg3 (2),
                  eBrg4 (3),
                  eBrg5 (4),
                  eBrg6 (5),
                  eBrg7 (6),
                  eBrg8 (7),
                  eNone (255)
            }
    MAX-ACCESS read-only
    STATUS     current
    DESCRIPTION
            "-- empty --"
    ::= { hmStatusLanBridgeAddressTableEntry 8 }

-- {COLUMN} 1.3.6.1.4.1.248.32.18.1.31.1.1.9
hmStatusLanBridgeAddressTableEntryPort OBJECT-TYPE
    SYNTAX     DisplayString (SIZE(0..255))
    MAX-ACCESS read-only
    STATUS     current
    DESCRIPTION
            "-- empty --"
    ::= { hmStatusLanBridgeAddressTableEntry 9 }

-- {SCALAR} 1.3.6.1.4.1.248.32.18.1.31.8
hmStatusLanBridgeIsolatedMode OBJECT-TYPE
    SYNTAX     INTEGER {
                  eNo (0),
                  eYes (1)
            }
    MAX-ACCESS read-only
    STATUS     current
    DESCRIPTION
            "-- empty --"
    ::= { hmStatusLanBridge 8 }

-- {TABLE} 1.3.6.1.4.1.248.32.18.1.31.9
hmStatusLanBridgeConnectionTableTable OBJECT-TYPE
    SYNTAX     SEQUENCE OF HmStatusLanBridgeConnectionTableEntry
    MAX-ACCESS not-accessible
    STATUS     current
    DESCRIPTION
            "-- empty --"
    ::= { hmStatusLanBridge 9 }

-- {ROW} 1.3.6.1.4.1.248.32.18.1.31.9.1
hmStatusLanBridgeConnectionTableEntry OBJECT-TYPE
    SYNTAX     HmStatusLanBridgeConnectionTableEntry
    MAX-ACCESS not-accessible
    STATUS     current
    DESCRIPTION
            ""
    INDEX {
            hmStatusLanBridgeConnectionTableEntryIndex
          }
    ::= { hmStatusLanBridgeConnectionTableTable 1 }

HmStatusLanBridgeConnectionTableEntry ::= SEQUENCE {
            hmStatusLanBridgeConnectionTableEntryIndex Integer32,
            hmStatusLanBridgeConnectionTableEntryProtocol DisplayString,
            hmStatusLanBridgeConnectionTableEntrySubProtocol Integer32,
            hmStatusLanBridgeConnectionTableEntrySourceAddress IpAddress,
            hmStatusLanBridgeConnectionTableEntrySourcePort Integer32,
            hmStatusLanBridgeConnectionTableEntryDestPort Integer32,
            hmStatusLanBridgeConnectionTableEntryDestAddress IpAddress,
            hmStatusLanBridgeConnectionTableEntryDestMac DisplayString,
            hmStatusLanBridgeConnectionTableEntryAge Integer32,
            hmStatusLanBridgeConnectionTableEntryInterface INTEGER,
            hmStatusLanBridgeConnectionTableEntryName DisplayString
    }

-- {COLUMN} 1.3.6.1.4.1.248.32.18.1.31.9.1.1
hmStatusLanBridgeConnectionTableEntryIndex OBJECT-TYPE
    SYNTAX     Integer32 (0..2147483647)
    MAX-ACCESS read-only
    STATUS     current
    DESCRIPTION
            "-- empty --"
    ::= { hmStatusLanBridgeConnectionTableEntry 1 }

-- {COLUMN} 1.3.6.1.4.1.248.32.18.1.31.9.1.3
hmStatusLanBridgeConnectionTableEntryProtocol OBJECT-TYPE
    SYNTAX     DisplayString (SIZE(0..4))
    MAX-ACCESS read-only
    STATUS     current
    DESCRIPTION
            "-- empty --"
    ::= { hmStatusLanBridgeConnectionTableEntry 3 }

-- {COLUMN} 1.3.6.1.4.1.248.32.18.1.31.9.1.4
hmStatusLanBridgeConnectionTableEntrySubProtocol OBJECT-TYPE
    SYNTAX     Integer32 (0..65535)
    MAX-ACCESS read-only
    STATUS     current
    DESCRIPTION
            "-- empty --"
    ::= { hmStatusLanBridgeConnectionTableEntry 4 }

-- {COLUMN} 1.3.6.1.4.1.248.32.18.1.31.9.1.5
hmStatusLanBridgeConnectionTableEntrySourceAddress OBJECT-TYPE
    SYNTAX     IpAddress
    MAX-ACCESS read-only
    STATUS     current
    DESCRIPTION
            "-- empty --"
    ::= { hmStatusLanBridgeConnectionTableEntry 5 }

-- {COLUMN} 1.3.6.1.4.1.248.32.18.1.31.9.1.6
hmStatusLanBridgeConnectionTableEntrySourcePort OBJECT-TYPE
    SYNTAX     Integer32 (0..65535)
    MAX-ACCESS read-only
    STATUS     current
    DESCRIPTION
            "-- empty --"
    ::= { hmStatusLanBridgeConnectionTableEntry 6 }

-- {COLUMN} 1.3.6.1.4.1.248.32.18.1.31.9.1.7
hmStatusLanBridgeConnectionTableEntryDestPort OBJECT-TYPE
    SYNTAX     Integer32 (0..65535)
    MAX-ACCESS read-only
    STATUS     current
    DESCRIPTION
            "-- empty --"
    ::= { hmStatusLanBridgeConnectionTableEntry 7 }

-- {COLUMN} 1.3.6.1.4.1.248.32.18.1.31.9.1.8
hmStatusLanBridgeConnectionTableEntryDestAddress OBJECT-TYPE
    SYNTAX     IpAddress
    MAX-ACCESS read-only
    STATUS     current
    DESCRIPTION
            "-- empty --"
    ::= { hmStatusLanBridgeConnectionTableEntry 8 }

-- {COLUMN} 1.3.6.1.4.1.248.32.18.1.31.9.1.9
hmStatusLanBridgeConnectionTableEntryDestMac OBJECT-TYPE
    SYNTAX     DisplayString (SIZE(0..12))
    MAX-ACCESS read-only
    STATUS     current
    DESCRIPTION
            "-- empty --"
    ::= { hmStatusLanBridgeConnectionTableEntry 9 }

-- {COLUMN} 1.3.6.1.4.1.248.32.18.1.31.9.1.10
hmStatusLanBridgeConnectionTableEntryAge OBJECT-TYPE
    SYNTAX     Integer32 (0..2147483647)
    MAX-ACCESS read-only
    STATUS     current
    DESCRIPTION
            "-- empty --"
    ::= { hmStatusLanBridgeConnectionTableEntry 10 }

-- {COLUMN} 1.3.6.1.4.1.248.32.18.1.31.9.1.11
hmStatusLanBridgeConnectionTableEntryInterface OBJECT-TYPE
    SYNTAX     INTEGER {
                  eLan1 (256),
                  eLan2 (257),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eAny (65535)
            }
    MAX-ACCESS read-only
    STATUS     current
    DESCRIPTION
            "-- empty --"
    ::= { hmStatusLanBridgeConnectionTableEntry 11 }

-- {COLUMN} 1.3.6.1.4.1.248.32.18.1.31.9.1.12
hmStatusLanBridgeConnectionTableEntryName OBJECT-TYPE
    SYNTAX     DisplayString (SIZE(0..15))
    MAX-ACCESS read-only
    STATUS     current
    DESCRIPTION
            "-- empty --"
    ::= { hmStatusLanBridgeConnectionTableEntry 12 }

-- {TABLE} 1.3.6.1.4.1.248.32.18.1.31.10
hmStatusLanBridgeDhcpTableTable OBJECT-TYPE
    SYNTAX     SEQUENCE OF HmStatusLanBridgeDhcpTableEntry
    MAX-ACCESS not-accessible
    STATUS     current
    DESCRIPTION
            "-- empty --"
    ::= { hmStatusLanBridge 10 }

-- {ROW} 1.3.6.1.4.1.248.32.18.1.31.10.1
hmStatusLanBridgeDhcpTableEntry OBJECT-TYPE
    SYNTAX     HmStatusLanBridgeDhcpTableEntry
    MAX-ACCESS not-accessible
    STATUS     current
    DESCRIPTION
            ""
    INDEX {
            hmStatusLanBridgeDhcpTableEntryMacAddress
          }
    ::= { hmStatusLanBridgeDhcpTableTable 1 }

HmStatusLanBridgeDhcpTableEntry ::= SEQUENCE {
            hmStatusLanBridgeDhcpTableEntryMacAddress MacAddress,
            hmStatusLanBridgeDhcpTableEntryIpAddress IpAddress,
            hmStatusLanBridgeDhcpTableEntryLastUpdate Integer32,
            hmStatusLanBridgeDhcpTableEntryPort DisplayString,
            hmStatusLanBridgeDhcpTableEntrySrcPort DisplayString
    }

-- {COLUMN} 1.3.6.1.4.1.248.32.18.1.31.10.1.1
hmStatusLanBridgeDhcpTableEntryMacAddress OBJECT-TYPE
    SYNTAX     MacAddress
    MAX-ACCESS read-only
    STATUS     current
    DESCRIPTION
            "-- empty --"
    ::= { hmStatusLanBridgeDhcpTableEntry 1 }

-- {COLUMN} 1.3.6.1.4.1.248.32.18.1.31.10.1.4
hmStatusLanBridgeDhcpTableEntryIpAddress OBJECT-TYPE
    SYNTAX     IpAddress
    MAX-ACCESS read-only
    STATUS     current
    DESCRIPTION
            "-- empty --"
    ::= { hmStatusLanBridgeDhcpTableEntry 4 }

-- {COLUMN} 1.3.6.1.4.1.248.32.18.1.31.10.1.5
hmStatusLanBridgeDhcpTableEntryLastUpdate OBJECT-TYPE
    SYNTAX     Integer32 (0..2147483647)
    MAX-ACCESS read-only
    STATUS     current
    DESCRIPTION
            "-- empty --"
    ::= { hmStatusLanBridgeDhcpTableEntry 5 }

-- {COLUMN} 1.3.6.1.4.1.248.32.18.1.31.10.1.6
hmStatusLanBridgeDhcpTableEntryPort OBJECT-TYPE
    SYNTAX     DisplayString (SIZE(0..255))
    MAX-ACCESS read-only
    STATUS     current
    DESCRIPTION
            "-- empty --"
    ::= { hmStatusLanBridgeDhcpTableEntry 6 }

-- {COLUMN} 1.3.6.1.4.1.248.32.18.1.31.10.1.7
hmStatusLanBridgeDhcpTableEntrySrcPort OBJECT-TYPE
    SYNTAX     DisplayString (SIZE(0..255))
    MAX-ACCESS read-only
    STATUS     current
    DESCRIPTION
            "-- empty --"
    ::= { hmStatusLanBridgeDhcpTableEntry 7 }

-- {TABLE} 1.3.6.1.4.1.248.32.18.1.31.11
hmStatusLanBridgePortDataTable OBJECT-TYPE
    SYNTAX     SEQUENCE OF HmStatusLanBridgePortDataEntry
    MAX-ACCESS not-accessible
    STATUS     current
    DESCRIPTION
            "-- empty --"
    ::= { hmStatusLanBridge 11 }

-- {ROW} 1.3.6.1.4.1.248.32.18.1.31.11.1
hmStatusLanBridgePortDataEntry OBJECT-TYPE
    SYNTAX     HmStatusLanBridgePortDataEntry
    MAX-ACCESS not-accessible
    STATUS     current
    DESCRIPTION
            ""
    INDEX {
            hmStatusLanBridgePortDataEntryPort
          }
    ::= { hmStatusLanBridgePortDataTable 1 }

HmStatusLanBridgePortDataEntry ::= SEQUENCE {
            hmStatusLanBridgePortDataEntryPort DisplayString,
            hmStatusLanBridgePortDataEntryPointToPointPort INTEGER,
            hmStatusLanBridgePortDataEntryOperatingState INTEGER,
            hmStatusLanBridgePortDataEntryBridgeGroup INTEGER,
            hmStatusLanBridgePortDataEntryInPackets Integer32,
            hmStatusLanBridgePortDataEntryOutPackets Integer32,
            hmStatusLanBridgePortDataEntryInDiscards Integer32,
            hmStatusLanBridgePortDataEntryPrivateMode INTEGER
    }

-- {COLUMN} 1.3.6.1.4.1.248.32.18.1.31.11.1.1
hmStatusLanBridgePortDataEntryPort OBJECT-TYPE
    SYNTAX     DisplayString (SIZE(0..255))
    MAX-ACCESS read-only
    STATUS     current
    DESCRIPTION
            "-- empty --"
    ::= { hmStatusLanBridgePortDataEntry 1 }

-- {COLUMN} 1.3.6.1.4.1.248.32.18.1.31.11.1.2
hmStatusLanBridgePortDataEntryPointToPointPort OBJECT-TYPE
    SYNTAX     INTEGER {
                  eNo (0),
                  eYes (1)
            }
    MAX-ACCESS read-only
    STATUS     current
    DESCRIPTION
            "-- empty --"
    ::= { hmStatusLanBridgePortDataEntry 2 }

-- {COLUMN} 1.3.6.1.4.1.248.32.18.1.31.11.1.3
hmStatusLanBridgePortDataEntryOperatingState OBJECT-TYPE
    SYNTAX     INTEGER {
                  eUp (1),
                  eDown (2),
                  eTesting (3),
                  eUnknown (4),
                  eDormant (5),
                  eNotPresent (6),
                  eLowerLayerDown (7)
            }
    MAX-ACCESS read-only
    STATUS     current
    DESCRIPTION
            "-- empty --"
    ::= { hmStatusLanBridgePortDataEntry 3 }

-- {COLUMN} 1.3.6.1.4.1.248.32.18.1.31.11.1.5
hmStatusLanBridgePortDataEntryBridgeGroup OBJECT-TYPE
    SYNTAX     INTEGER {
                  eBrg1 (0),
                  eBrg2 (1),
                  eBrg3 (2),
                  eBrg4 (3),
                  eBrg5 (4),
                  eBrg6 (5),
                  eBrg7 (6),
                  eBrg8 (7),
                  eNone (255)
            }
    MAX-ACCESS read-only
    STATUS     current
    DESCRIPTION
            "-- empty --"
    ::= { hmStatusLanBridgePortDataEntry 5 }

-- {COLUMN} 1.3.6.1.4.1.248.32.18.1.31.11.1.6
hmStatusLanBridgePortDataEntryInPackets OBJECT-TYPE
    SYNTAX     Integer32 (0..2147483647)
    MAX-ACCESS read-only
    STATUS     current
    DESCRIPTION
            "-- empty --"
    ::= { hmStatusLanBridgePortDataEntry 6 }

-- {COLUMN} 1.3.6.1.4.1.248.32.18.1.31.11.1.7
hmStatusLanBridgePortDataEntryOutPackets OBJECT-TYPE
    SYNTAX     Integer32 (0..2147483647)
    MAX-ACCESS read-only
    STATUS     current
    DESCRIPTION
            "-- empty --"
    ::= { hmStatusLanBridgePortDataEntry 7 }

-- {COLUMN} 1.3.6.1.4.1.248.32.18.1.31.11.1.8
hmStatusLanBridgePortDataEntryInDiscards OBJECT-TYPE
    SYNTAX     Integer32 (0..2147483647)
    MAX-ACCESS read-only
    STATUS     current
    DESCRIPTION
            "-- empty --"
    ::= { hmStatusLanBridgePortDataEntry 8 }

-- {COLUMN} 1.3.6.1.4.1.248.32.18.1.31.11.1.9
hmStatusLanBridgePortDataEntryPrivateMode OBJECT-TYPE
    SYNTAX     INTEGER {
                  eNo (0),
                  eYes (1)
            }
    MAX-ACCESS read-only
    STATUS     current
    DESCRIPTION
            "-- empty --"
    ::= { hmStatusLanBridgePortDataEntry 9 }

-- {NODE} 1.3.6.1.4.1.248.32.18.1.31.20
hmStatusLanBridgeSpanningTree OBJECT IDENTIFIER ::= { hmStatusLanBridge 20 }

-- {SCALAR} 1.3.6.1.4.1.248.32.18.1.31.20.1
hmStatusLanBridgeSpanningTreeOperating OBJECT-TYPE
    SYNTAX     INTEGER {
                  eNo (0),
                  eYes (1)
            }
    MAX-ACCESS read-only
    STATUS     current
    DESCRIPTION
            "-- empty --"
    ::= { hmStatusLanBridgeSpanningTree 1 }

-- {SCALAR} 1.3.6.1.4.1.248.32.18.1.31.20.2
hmStatusLanBridgeSpanningTreeBridgeId OBJECT-TYPE
    SYNTAX     DisplayString (SIZE(0..20))
    MAX-ACCESS read-only
    STATUS     current
    DESCRIPTION
            "-- empty --"
    ::= { hmStatusLanBridgeSpanningTree 2 }

-- {SCALAR} 1.3.6.1.4.1.248.32.18.1.31.20.3
hmStatusLanBridgeSpanningTreeRootBridge OBJECT-TYPE
    SYNTAX     DisplayString (SIZE(0..20))
    MAX-ACCESS read-only
    STATUS     current
    DESCRIPTION
            "-- empty --"
    ::= { hmStatusLanBridgeSpanningTree 3 }

-- {SCALAR} 1.3.6.1.4.1.248.32.18.1.31.20.5
hmStatusLanBridgeSpanningTreeRootPathCost OBJECT-TYPE
    SYNTAX     Integer32 (0..2147483647)
    MAX-ACCESS read-only
    STATUS     current
    DESCRIPTION
            "-- empty --"
    ::= { hmStatusLanBridgeSpanningTree 5 }

-- {TABLE} 1.3.6.1.4.1.248.32.18.1.31.20.6
hmStatusLanBridgeSpanningTreePortTableTable OBJECT-TYPE
    SYNTAX     SEQUENCE OF HmStatusLanBridgeSpanningTreePortTableEntry
    MAX-ACCESS not-accessible
    STATUS     current
    DESCRIPTION
            "-- empty --"
    ::= { hmStatusLanBridgeSpanningTree 6 }

-- {ROW} 1.3.6.1.4.1.248.32.18.1.31.20.6.1
hmStatusLanBridgeSpanningTreePortTableEntry OBJECT-TYPE
    SYNTAX     HmStatusLanBridgeSpanningTreePortTableEntry
    MAX-ACCESS not-accessible
    STATUS     current
    DESCRIPTION
            ""
    INDEX {
            hmStatusLanBridgeSpanningTreePortTableEntryDescription
          }
    ::= { hmStatusLanBridgeSpanningTreePortTableTable 1 }

HmStatusLanBridgeSpanningTreePortTableEntry ::= SEQUENCE {
            hmStatusLanBridgeSpanningTreePortTableEntryDescription DisplayString,
            hmStatusLanBridgeSpanningTreePortTableEntryPriority Integer32,
            hmStatusLanBridgeSpanningTreePortTableEntryState INTEGER,
            hmStatusLanBridgeSpanningTreePortTableEntryRoot DisplayString,
            hmStatusLanBridgeSpanningTreePortTableEntryBridge DisplayString,
            hmStatusLanBridgeSpanningTreePortTableEntryPathCost Integer32
    }

-- {COLUMN} 1.3.6.1.4.1.248.32.18.1.31.20.6.1.1
hmStatusLanBridgeSpanningTreePortTableEntryDescription OBJECT-TYPE
    SYNTAX     DisplayString (SIZE(0..18))
    MAX-ACCESS read-only
    STATUS     current
    DESCRIPTION
            "-- empty --"
    ::= { hmStatusLanBridgeSpanningTreePortTableEntry 1 }

-- {COLUMN} 1.3.6.1.4.1.248.32.18.1.31.20.6.1.2
hmStatusLanBridgeSpanningTreePortTableEntryPriority OBJECT-TYPE
    SYNTAX     Integer32 (0..255)
    MAX-ACCESS read-only
    STATUS     current
    DESCRIPTION
            "-- empty --"
    ::= { hmStatusLanBridgeSpanningTreePortTableEntry 2 }

-- {COLUMN} 1.3.6.1.4.1.248.32.18.1.31.20.6.1.3
hmStatusLanBridgeSpanningTreePortTableEntryState OBJECT-TYPE
    SYNTAX     INTEGER {
                  eDisabled (0),
                  eListening (1),
                  eLearning (2),
                  eForwarding (3),
                  eBlocking (4)
            }
    MAX-ACCESS read-only
    STATUS     current
    DESCRIPTION
            "-- empty --"
    ::= { hmStatusLanBridgeSpanningTreePortTableEntry 3 }

-- {COLUMN} 1.3.6.1.4.1.248.32.18.1.31.20.6.1.4
hmStatusLanBridgeSpanningTreePortTableEntryRoot OBJECT-TYPE
    SYNTAX     DisplayString (SIZE(0..16))
    MAX-ACCESS read-only
    STATUS     current
    DESCRIPTION
            "-- empty --"
    ::= { hmStatusLanBridgeSpanningTreePortTableEntry 4 }

-- {COLUMN} 1.3.6.1.4.1.248.32.18.1.31.20.6.1.5
hmStatusLanBridgeSpanningTreePortTableEntryBridge OBJECT-TYPE
    SYNTAX     DisplayString (SIZE(0..16))
    MAX-ACCESS read-only
    STATUS     current
    DESCRIPTION
            "-- empty --"
    ::= { hmStatusLanBridgeSpanningTreePortTableEntry 5 }

-- {COLUMN} 1.3.6.1.4.1.248.32.18.1.31.20.6.1.6
hmStatusLanBridgeSpanningTreePortTableEntryPathCost OBJECT-TYPE
    SYNTAX     Integer32 (0..2147483647)
    MAX-ACCESS read-only
    STATUS     current
    DESCRIPTION
            "-- empty --"
    ::= { hmStatusLanBridgeSpanningTreePortTableEntry 6 }

-- {SCALAR} 1.3.6.1.4.1.248.32.18.1.31.20.7
hmStatusLanBridgeSpanningTreeProtocolVersion OBJECT-TYPE
    SYNTAX     INTEGER {
                  eClassic (0),
                  eRapid (1)
            }
    MAX-ACCESS read-only
    STATUS     current
    DESCRIPTION
            "-- empty --"
    ::= { hmStatusLanBridgeSpanningTree 7 }

-- {SCALAR} 1.3.6.1.4.1.248.32.18.1.31.20.8
hmStatusLanBridgeSpanningTreePathCostComputation OBJECT-TYPE
    SYNTAX     INTEGER {
                  eClassic (0),
                  eRapid (1)
            }
    MAX-ACCESS read-only
    STATUS     current
    DESCRIPTION
            "-- empty --"
    ::= { hmStatusLanBridgeSpanningTree 8 }

-- {SCALAR} 1.3.6.1.4.1.248.32.18.1.31.20.9
hmStatusLanBridgeSpanningTreeBridgePriority OBJECT-TYPE
    SYNTAX     Integer32 (0..65535)
    MAX-ACCESS read-only
    STATUS     current
    DESCRIPTION
            "-- empty --"
    ::= { hmStatusLanBridgeSpanningTree 9 }

-- {TABLE} 1.3.6.1.4.1.248.32.18.1.31.20.10
hmStatusLanBridgeSpanningTreeRstpPortTableTable OBJECT-TYPE
    SYNTAX     SEQUENCE OF HmStatusLanBridgeSpanningTreeRstpPortTableEntry
    MAX-ACCESS not-accessible
    STATUS     current
    DESCRIPTION
            "-- empty --"
    ::= { hmStatusLanBridgeSpanningTree 10 }

-- {ROW} 1.3.6.1.4.1.248.32.18.1.31.20.10.1
hmStatusLanBridgeSpanningTreeRstpPortTableEntry OBJECT-TYPE
    SYNTAX     HmStatusLanBridgeSpanningTreeRstpPortTableEntry
    MAX-ACCESS not-accessible
    STATUS     current
    DESCRIPTION
            ""
    INDEX {
            hmStatusLanBridgeSpanningTreeRstpPortTableEntryDescription
          }
    ::= { hmStatusLanBridgeSpanningTreeRstpPortTableTable 1 }

HmStatusLanBridgeSpanningTreeRstpPortTableEntry ::= SEQUENCE {
            hmStatusLanBridgeSpanningTreeRstpPortTableEntryDescription DisplayString,
            hmStatusLanBridgeSpanningTreeRstpPortTableEntryRole INTEGER,
            hmStatusLanBridgeSpanningTreeRstpPortTableEntryLearning INTEGER,
            hmStatusLanBridgeSpanningTreeRstpPortTableEntryForwarding INTEGER,
            hmStatusLanBridgeSpanningTreeRstpPortTableEntryEdgePort INTEGER,
            hmStatusLanBridgeSpanningTreeRstpPortTableEntryProtocolVersion INTEGER,
            hmStatusLanBridgeSpanningTreeRstpPortTableEntryPathCost Integer32
    }

-- {COLUMN} 1.3.6.1.4.1.248.32.18.1.31.20.10.1.1
hmStatusLanBridgeSpanningTreeRstpPortTableEntryDescription OBJECT-TYPE
    SYNTAX     DisplayString (SIZE(0..255))
    MAX-ACCESS read-only
    STATUS     current
    DESCRIPTION
            "-- empty --"
    ::= { hmStatusLanBridgeSpanningTreeRstpPortTableEntry 1 }

-- {COLUMN} 1.3.6.1.4.1.248.32.18.1.31.20.10.1.2
hmStatusLanBridgeSpanningTreeRstpPortTableEntryRole OBJECT-TYPE
    SYNTAX     INTEGER {
                  eRoot (0),
                  eDesignated (1),
                  eAlternate (2),
                  eBackup (3),
                  eDisabled (4)
            }
    MAX-ACCESS read-only
    STATUS     current
    DESCRIPTION
            "-- empty --"
    ::= { hmStatusLanBridgeSpanningTreeRstpPortTableEntry 2 }

-- {COLUMN} 1.3.6.1.4.1.248.32.18.1.31.20.10.1.3
hmStatusLanBridgeSpanningTreeRstpPortTableEntryLearning OBJECT-TYPE
    SYNTAX     INTEGER {
                  eNo (0),
                  eYes (1)
            }
    MAX-ACCESS read-only
    STATUS     current
    DESCRIPTION
            "-- empty --"
    ::= { hmStatusLanBridgeSpanningTreeRstpPortTableEntry 3 }

-- {COLUMN} 1.3.6.1.4.1.248.32.18.1.31.20.10.1.4
hmStatusLanBridgeSpanningTreeRstpPortTableEntryForwarding OBJECT-TYPE
    SYNTAX     INTEGER {
                  eNo (0),
                  eYes (1)
            }
    MAX-ACCESS read-only
    STATUS     current
    DESCRIPTION
            "-- empty --"
    ::= { hmStatusLanBridgeSpanningTreeRstpPortTableEntry 4 }

-- {COLUMN} 1.3.6.1.4.1.248.32.18.1.31.20.10.1.5
hmStatusLanBridgeSpanningTreeRstpPortTableEntryEdgePort OBJECT-TYPE
    SYNTAX     INTEGER {
                  eNo (0),
                  eYes (1)
            }
    MAX-ACCESS read-only
    STATUS     current
    DESCRIPTION
            "-- empty --"
    ::= { hmStatusLanBridgeSpanningTreeRstpPortTableEntry 5 }

-- {COLUMN} 1.3.6.1.4.1.248.32.18.1.31.20.10.1.6
hmStatusLanBridgeSpanningTreeRstpPortTableEntryProtocolVersion OBJECT-TYPE
    SYNTAX     INTEGER {
                  eClassic (0),
                  eRapid (1)
            }
    MAX-ACCESS read-only
    STATUS     current
    DESCRIPTION
            "-- empty --"
    ::= { hmStatusLanBridgeSpanningTreeRstpPortTableEntry 6 }

-- {COLUMN} 1.3.6.1.4.1.248.32.18.1.31.20.10.1.7
hmStatusLanBridgeSpanningTreeRstpPortTableEntryPathCost OBJECT-TYPE
    SYNTAX     Integer32 (0..2147483647)
    MAX-ACCESS read-only
    STATUS     current
    DESCRIPTION
            "-- empty --"
    ::= { hmStatusLanBridgeSpanningTreeRstpPortTableEntry 7 }

-- {SCALAR} 1.3.6.1.4.1.248.32.18.1.31.20.11
hmStatusLanBridgeSpanningTreeRootPort OBJECT-TYPE
    SYNTAX     DisplayString
    MAX-ACCESS read-only
    STATUS     current
    DESCRIPTION
            "-- empty --"
    ::= { hmStatusLanBridgeSpanningTree 11 }

-- {TABLE} 1.3.6.1.4.1.248.32.18.1.31.20.12
hmStatusLanBridgeSpanningTreeLogTableTable OBJECT-TYPE
    SYNTAX     SEQUENCE OF HmStatusLanBridgeSpanningTreeLogTableEntry
    MAX-ACCESS not-accessible
    STATUS     current
    DESCRIPTION
            "-- empty --"
    ::= { hmStatusLanBridgeSpanningTree 12 }

-- {ROW} 1.3.6.1.4.1.248.32.18.1.31.20.12.1
hmStatusLanBridgeSpanningTreeLogTableEntry OBJECT-TYPE
    SYNTAX     HmStatusLanBridgeSpanningTreeLogTableEntry
    MAX-ACCESS not-accessible
    STATUS     current
    DESCRIPTION
            ""
    INDEX {
            hmStatusLanBridgeSpanningTreeLogTableEntryIndex
          }
    ::= { hmStatusLanBridgeSpanningTreeLogTableTable 1 }

HmStatusLanBridgeSpanningTreeLogTableEntry ::= SEQUENCE {
            hmStatusLanBridgeSpanningTreeLogTableEntryIndex Integer32,
            hmStatusLanBridgeSpanningTreeLogTableEntryTime DisplayString,
            hmStatusLanBridgeSpanningTreeLogTableEntryEvent DisplayString
    }

-- {COLUMN} 1.3.6.1.4.1.248.32.18.1.31.20.12.1.1
hmStatusLanBridgeSpanningTreeLogTableEntryIndex OBJECT-TYPE
    SYNTAX     Integer32 (0..2147483647)
    MAX-ACCESS read-only
    STATUS     current
    DESCRIPTION
            "-- empty --"
    ::= { hmStatusLanBridgeSpanningTreeLogTableEntry 1 }

-- {COLUMN} 1.3.6.1.4.1.248.32.18.1.31.20.12.1.2
hmStatusLanBridgeSpanningTreeLogTableEntryTime OBJECT-TYPE
    SYNTAX     DisplayString (SIZE(0..19))
    MAX-ACCESS read-only
    STATUS     current
    DESCRIPTION
            "-- empty --"
    ::= { hmStatusLanBridgeSpanningTreeLogTableEntry 2 }

-- {COLUMN} 1.3.6.1.4.1.248.32.18.1.31.20.12.1.3
hmStatusLanBridgeSpanningTreeLogTableEntryEvent OBJECT-TYPE
    SYNTAX     DisplayString (SIZE(0..69))
    MAX-ACCESS read-only
    STATUS     current
    DESCRIPTION
            "-- empty --"
    ::= { hmStatusLanBridgeSpanningTreeLogTableEntry 3 }

-- {NODE} 1.3.6.1.4.1.248.32.18.1.31.30
hmStatusLanBridgeIgmpSnooping OBJECT IDENTIFIER ::= { hmStatusLanBridge 30 }

-- {SCALAR} 1.3.6.1.4.1.248.32.18.1.31.30.1
hmStatusLanBridgeIgmpSnoopingOperating OBJECT-TYPE
    SYNTAX     INTEGER {
                  eNo (0),
                  eYes (1),
                  eAuto (2)
            }
    MAX-ACCESS read-only
    STATUS     current
    DESCRIPTION
            "-- empty --"
    ::= { hmStatusLanBridgeIgmpSnooping 1 }

-- {TABLE} 1.3.6.1.4.1.248.32.18.1.31.30.2
hmStatusLanBridgeIgmpSnoopingPortStatusTable OBJECT-TYPE
    SYNTAX     SEQUENCE OF HmStatusLanBridgeIgmpSnoopingPortStatusEntry
    MAX-ACCESS not-accessible
    STATUS     current
    DESCRIPTION
            "-- empty --"
    ::= { hmStatusLanBridgeIgmpSnooping 2 }

-- {ROW} 1.3.6.1.4.1.248.32.18.1.31.30.2.1
hmStatusLanBridgeIgmpSnoopingPortStatusEntry OBJECT-TYPE
    SYNTAX     HmStatusLanBridgeIgmpSnoopingPortStatusEntry
    MAX-ACCESS not-accessible
    STATUS     current
    DESCRIPTION
            ""
    INDEX {
            hmStatusLanBridgeIgmpSnoopingPortStatusEntryPort
          }
    ::= { hmStatusLanBridgeIgmpSnoopingPortStatusTable 1 }

HmStatusLanBridgeIgmpSnoopingPortStatusEntry ::= SEQUENCE {
            hmStatusLanBridgeIgmpSnoopingPortStatusEntryPort DisplayString,
            hmStatusLanBridgeIgmpSnoopingPortStatusEntryRouterPort INTEGER,
            hmStatusLanBridgeIgmpSnoopingPortStatusEntryIpv4Packets Counter32,
            hmStatusLanBridgeIgmpSnoopingPortStatusEntryDataPackets Counter32,
            hmStatusLanBridgeIgmpSnoopingPortStatusEntryControlPackets Counter32,
            hmStatusLanBridgeIgmpSnoopingPortStatusEntryBadPackets Counter32
    }

-- {COLUMN} 1.3.6.1.4.1.248.32.18.1.31.30.2.1.1
hmStatusLanBridgeIgmpSnoopingPortStatusEntryPort OBJECT-TYPE
    SYNTAX     DisplayString (SIZE(0..18))
    MAX-ACCESS read-only
    STATUS     current
    DESCRIPTION
            "-- empty --"
    ::= { hmStatusLanBridgeIgmpSnoopingPortStatusEntry 1 }

-- {COLUMN} 1.3.6.1.4.1.248.32.18.1.31.30.2.1.2
hmStatusLanBridgeIgmpSnoopingPortStatusEntryRouterPort OBJECT-TYPE
    SYNTAX     INTEGER {
                  eNo (0),
                  eAuto (1),
                  eYes (2)
            }
    MAX-ACCESS read-only
    STATUS     current
    DESCRIPTION
            "-- empty --"
    ::= { hmStatusLanBridgeIgmpSnoopingPortStatusEntry 2 }

-- {COLUMN} 1.3.6.1.4.1.248.32.18.1.31.30.2.1.10
hmStatusLanBridgeIgmpSnoopingPortStatusEntryIpv4Packets OBJECT-TYPE
    SYNTAX     Counter32
    MAX-ACCESS read-only
    STATUS     current
    DESCRIPTION
            "-- empty --"
    ::= { hmStatusLanBridgeIgmpSnoopingPortStatusEntry 10 }

-- {COLUMN} 1.3.6.1.4.1.248.32.18.1.31.30.2.1.12
hmStatusLanBridgeIgmpSnoopingPortStatusEntryDataPackets OBJECT-TYPE
    SYNTAX     Counter32
    MAX-ACCESS read-only
    STATUS     current
    DESCRIPTION
            "-- empty --"
    ::= { hmStatusLanBridgeIgmpSnoopingPortStatusEntry 12 }

-- {COLUMN} 1.3.6.1.4.1.248.32.18.1.31.30.2.1.13
hmStatusLanBridgeIgmpSnoopingPortStatusEntryControlPackets OBJECT-TYPE
    SYNTAX     Counter32
    MAX-ACCESS read-only
    STATUS     current
    DESCRIPTION
            "-- empty --"
    ::= { hmStatusLanBridgeIgmpSnoopingPortStatusEntry 13 }

-- {COLUMN} 1.3.6.1.4.1.248.32.18.1.31.30.2.1.14
hmStatusLanBridgeIgmpSnoopingPortStatusEntryBadPackets OBJECT-TYPE
    SYNTAX     Counter32
    MAX-ACCESS read-only
    STATUS     current
    DESCRIPTION
            "-- empty --"
    ::= { hmStatusLanBridgeIgmpSnoopingPortStatusEntry 14 }

-- {TABLE} 1.3.6.1.4.1.248.32.18.1.31.30.3
hmStatusLanBridgeIgmpSnoopingGroupsTable OBJECT-TYPE
    SYNTAX     SEQUENCE OF HmStatusLanBridgeIgmpSnoopingGroupsEntry
    MAX-ACCESS not-accessible
    STATUS     current
    DESCRIPTION
            "-- empty --"
    ::= { hmStatusLanBridgeIgmpSnooping 3 }

-- {ROW} 1.3.6.1.4.1.248.32.18.1.31.30.3.1
hmStatusLanBridgeIgmpSnoopingGroupsEntry OBJECT-TYPE
    SYNTAX     HmStatusLanBridgeIgmpSnoopingGroupsEntry
    MAX-ACCESS not-accessible
    STATUS     current
    DESCRIPTION
            ""
    INDEX {
            hmStatusLanBridgeIgmpSnoopingGroupsEntryAddress,
            hmStatusLanBridgeIgmpSnoopingGroupsEntryVlanId
          }
    ::= { hmStatusLanBridgeIgmpSnoopingGroupsTable 1 }

HmStatusLanBridgeIgmpSnoopingGroupsEntry ::= SEQUENCE {
            hmStatusLanBridgeIgmpSnoopingGroupsEntryAddress IpAddress,
            hmStatusLanBridgeIgmpSnoopingGroupsEntryDynamicMembers DisplayString,
            hmStatusLanBridgeIgmpSnoopingGroupsEntryStaticMembers DisplayString,
            hmStatusLanBridgeIgmpSnoopingGroupsEntryVlanId Integer32,
            hmStatusLanBridgeIgmpSnoopingGroupsEntryAllowLearning INTEGER
    }

-- {COLUMN} 1.3.6.1.4.1.248.32.18.1.31.30.3.1.1
hmStatusLanBridgeIgmpSnoopingGroupsEntryAddress OBJECT-TYPE
    SYNTAX     IpAddress
    MAX-ACCESS read-only
    STATUS     current
    DESCRIPTION
            "-- empty --"
    ::= { hmStatusLanBridgeIgmpSnoopingGroupsEntry 1 }

-- {COLUMN} 1.3.6.1.4.1.248.32.18.1.31.30.3.1.2
hmStatusLanBridgeIgmpSnoopingGroupsEntryDynamicMembers OBJECT-TYPE
    SYNTAX     DisplayString (SIZE(0..255))
    MAX-ACCESS read-only
    STATUS     current
    DESCRIPTION
            "-- empty --"
    ::= { hmStatusLanBridgeIgmpSnoopingGroupsEntry 2 }

-- {COLUMN} 1.3.6.1.4.1.248.32.18.1.31.30.3.1.3
hmStatusLanBridgeIgmpSnoopingGroupsEntryStaticMembers OBJECT-TYPE
    SYNTAX     DisplayString (SIZE(0..255))
    MAX-ACCESS read-only
    STATUS     current
    DESCRIPTION
            "-- empty --"
    ::= { hmStatusLanBridgeIgmpSnoopingGroupsEntry 3 }

-- {COLUMN} 1.3.6.1.4.1.248.32.18.1.31.30.3.1.4
hmStatusLanBridgeIgmpSnoopingGroupsEntryVlanId OBJECT-TYPE
    SYNTAX     Integer32 (0..65535)
    MAX-ACCESS read-only
    STATUS     current
    DESCRIPTION
            "-- empty --"
    ::= { hmStatusLanBridgeIgmpSnoopingGroupsEntry 4 }

-- {COLUMN} 1.3.6.1.4.1.248.32.18.1.31.30.3.1.5
hmStatusLanBridgeIgmpSnoopingGroupsEntryAllowLearning OBJECT-TYPE
    SYNTAX     INTEGER {
                  eYes (0),
                  eNo (1)
            }
    MAX-ACCESS read-only
    STATUS     current
    DESCRIPTION
            "-- empty --"
    ::= { hmStatusLanBridgeIgmpSnoopingGroupsEntry 5 }

-- {TABLE} 1.3.6.1.4.1.248.32.18.1.31.30.4
hmStatusLanBridgeIgmpSnoopingSimulatedQueriersTable OBJECT-TYPE
    SYNTAX     SEQUENCE OF HmStatusLanBridgeIgmpSnoopingSimulatedQueriersEntry
    MAX-ACCESS not-accessible
    STATUS     current
    DESCRIPTION
            "-- empty --"
    ::= { hmStatusLanBridgeIgmpSnooping 4 }

-- {ROW} 1.3.6.1.4.1.248.32.18.1.31.30.4.1
hmStatusLanBridgeIgmpSnoopingSimulatedQueriersEntry OBJECT-TYPE
    SYNTAX     HmStatusLanBridgeIgmpSnoopingSimulatedQueriersEntry
    MAX-ACCESS not-accessible
    STATUS     current
    DESCRIPTION
            ""
    INDEX {
            hmStatusLanBridgeIgmpSnoopingSimulatedQueriersEntryName
          }
    ::= { hmStatusLanBridgeIgmpSnoopingSimulatedQueriersTable 1 }

HmStatusLanBridgeIgmpSnoopingSimulatedQueriersEntry ::= SEQUENCE {
            hmStatusLanBridgeIgmpSnoopingSimulatedQueriersEntryName DisplayString,
            hmStatusLanBridgeIgmpSnoopingSimulatedQueriersEntryBridgeGroup INTEGER,
            hmStatusLanBridgeIgmpSnoopingSimulatedQueriersEntryVlanId Integer32,
            hmStatusLanBridgeIgmpSnoopingSimulatedQueriersEntryStatus INTEGER
    }

-- {COLUMN} 1.3.6.1.4.1.248.32.18.1.31.30.4.1.1
hmStatusLanBridgeIgmpSnoopingSimulatedQueriersEntryName OBJECT-TYPE
    SYNTAX     DisplayString (SIZE(0..255))
    MAX-ACCESS read-only
    STATUS     current
    DESCRIPTION
            "-- empty --"
    ::= { hmStatusLanBridgeIgmpSnoopingSimulatedQueriersEntry 1 }

-- {COLUMN} 1.3.6.1.4.1.248.32.18.1.31.30.4.1.3
hmStatusLanBridgeIgmpSnoopingSimulatedQueriersEntryBridgeGroup OBJECT-TYPE
    SYNTAX     INTEGER {
                  eBrg1 (0),
                  eBrg2 (1),
                  eBrg3 (2),
                  eBrg4 (3),
                  eBrg5 (4),
                  eBrg6 (5),
                  eBrg7 (6),
                  eBrg8 (7),
                  eNone (255)
            }
    MAX-ACCESS read-only
    STATUS     current
    DESCRIPTION
            "-- empty --"
    ::= { hmStatusLanBridgeIgmpSnoopingSimulatedQueriersEntry 3 }

-- {COLUMN} 1.3.6.1.4.1.248.32.18.1.31.30.4.1.4
hmStatusLanBridgeIgmpSnoopingSimulatedQueriersEntryVlanId OBJECT-TYPE
    SYNTAX     Integer32 (0..65535)
    MAX-ACCESS read-only
    STATUS     current
    DESCRIPTION
            "-- empty --"
    ::= { hmStatusLanBridgeIgmpSnoopingSimulatedQueriersEntry 4 }

-- {COLUMN} 1.3.6.1.4.1.248.32.18.1.31.30.4.1.5
hmStatusLanBridgeIgmpSnoopingSimulatedQueriersEntryStatus OBJECT-TYPE
    SYNTAX     INTEGER {
                  eInitial (0),
                  eQuerier (1),
                  eNonQuerier (2)
            }
    MAX-ACCESS read-only
    STATUS     current
    DESCRIPTION
            "-- empty --"
    ::= { hmStatusLanBridgeIgmpSnoopingSimulatedQueriersEntry 5 }

-- {SCALAR} 1.3.6.1.4.1.248.32.18.1.31.30.5
hmStatusLanBridgeIgmpSnoopingFilterActive OBJECT-TYPE
    SYNTAX     INTEGER {
                  eNo (0),
                  eYes (1)
            }
    MAX-ACCESS read-only
    STATUS     current
    DESCRIPTION
            "-- empty --"
    ::= { hmStatusLanBridgeIgmpSnooping 5 }

-- {SCALAR} 1.3.6.1.4.1.248.32.18.1.31.30.10
hmStatusLanBridgeIgmpSnoopingIpv4Packets OBJECT-TYPE
    SYNTAX     Counter32
    MAX-ACCESS read-only
    STATUS     current
    DESCRIPTION
            "-- empty --"
    ::= { hmStatusLanBridgeIgmpSnooping 10 }

-- {SCALAR} 1.3.6.1.4.1.248.32.18.1.31.30.12
hmStatusLanBridgeIgmpSnoopingDataPackets OBJECT-TYPE
    SYNTAX     Counter32
    MAX-ACCESS read-only
    STATUS     current
    DESCRIPTION
            "-- empty --"
    ::= { hmStatusLanBridgeIgmpSnooping 12 }

-- {SCALAR} 1.3.6.1.4.1.248.32.18.1.31.30.13
hmStatusLanBridgeIgmpSnoopingControlPackets OBJECT-TYPE
    SYNTAX     Counter32
    MAX-ACCESS read-only
    STATUS     current
    DESCRIPTION
            "-- empty --"
    ::= { hmStatusLanBridgeIgmpSnooping 13 }

-- {SCALAR} 1.3.6.1.4.1.248.32.18.1.31.30.14
hmStatusLanBridgeIgmpSnoopingBadPackets OBJECT-TYPE
    SYNTAX     Counter32
    MAX-ACCESS read-only
    STATUS     current
    DESCRIPTION
            "-- empty --"
    ::= { hmStatusLanBridgeIgmpSnooping 14 }

-- {SCALAR} 1.3.6.1.4.1.248.32.18.1.31.30.99
hmStatusLanBridgeIgmpSnoopingDeleteValues OBJECT-TYPE
    SYNTAX     DisplayString
    MAX-ACCESS read-write
    STATUS     current
    DESCRIPTION
            "-- empty --"
    ::= { hmStatusLanBridgeIgmpSnooping 99 }

-- {SCALAR} 1.3.6.1.4.1.248.32.18.1.31.99
hmStatusLanBridgeDeleteValues OBJECT-TYPE
    SYNTAX     DisplayString
    MAX-ACCESS read-write
    STATUS     current
    DESCRIPTION
            "-- empty --"
    ::= { hmStatusLanBridge 99 }

-- {NODE} 1.3.6.1.4.1.248.32.18.1.31.248
hmStatusLanBridgeL2Firewall OBJECT IDENTIFIER ::= { hmStatusLanBridge 248 }

-- {TABLE} 1.3.6.1.4.1.248.32.18.1.31.248.1
hmStatusLanBridgeL2FirewallLogTableTable OBJECT-TYPE
    SYNTAX     SEQUENCE OF HmStatusLanBridgeL2FirewallLogTableEntry
    MAX-ACCESS not-accessible
    STATUS     current
    DESCRIPTION
            "-- empty --"
    ::= { hmStatusLanBridgeL2Firewall 1 }

-- {ROW} 1.3.6.1.4.1.248.32.18.1.31.248.1.1
hmStatusLanBridgeL2FirewallLogTableEntry OBJECT-TYPE
    SYNTAX     HmStatusLanBridgeL2FirewallLogTableEntry
    MAX-ACCESS not-accessible
    STATUS     current
    DESCRIPTION
            ""
    INDEX {
            hmStatusLanBridgeL2FirewallLogTableEntryIdx
          }
    ::= { hmStatusLanBridgeL2FirewallLogTableTable 1 }

HmStatusLanBridgeL2FirewallLogTableEntry ::= SEQUENCE {
            hmStatusLanBridgeL2FirewallLogTableEntryIdx Integer32,
            hmStatusLanBridgeL2FirewallLogTableEntrySystemTime DisplayString,
            hmStatusLanBridgeL2FirewallLogTableEntrySrcAddress DisplayString,
            hmStatusLanBridgeL2FirewallLogTableEntryDstAddress DisplayString,
            hmStatusLanBridgeL2FirewallLogTableEntryProtocol DisplayString,
            hmStatusLanBridgeL2FirewallLogTableEntrySrcPort DisplayString,
            hmStatusLanBridgeL2FirewallLogTableEntryDstPort DisplayString,
            hmStatusLanBridgeL2FirewallLogTableEntryRuleIndex Integer32,
            hmStatusLanBridgeL2FirewallLogTableEntryAction DisplayString
    }

-- {COLUMN} 1.3.6.1.4.1.248.32.18.1.31.248.1.1.1
hmStatusLanBridgeL2FirewallLogTableEntryIdx OBJECT-TYPE
    SYNTAX     Integer32 (0..65535)
    MAX-ACCESS read-only
    STATUS     current
    DESCRIPTION
            "-- empty --"
    ::= { hmStatusLanBridgeL2FirewallLogTableEntry 1 }

-- {COLUMN} 1.3.6.1.4.1.248.32.18.1.31.248.1.1.2
hmStatusLanBridgeL2FirewallLogTableEntrySystemTime OBJECT-TYPE
    SYNTAX     DisplayString (SIZE(0..19))
    MAX-ACCESS read-only
    STATUS     current
    DESCRIPTION
            "-- empty --"
    ::= { hmStatusLanBridgeL2FirewallLogTableEntry 2 }

-- {COLUMN} 1.3.6.1.4.1.248.32.18.1.31.248.1.1.3
hmStatusLanBridgeL2FirewallLogTableEntrySrcAddress OBJECT-TYPE
    SYNTAX     DisplayString (SIZE(0..255))
    MAX-ACCESS read-only
    STATUS     current
    DESCRIPTION
            "-- empty --"
    ::= { hmStatusLanBridgeL2FirewallLogTableEntry 3 }

-- {COLUMN} 1.3.6.1.4.1.248.32.18.1.31.248.1.1.4
hmStatusLanBridgeL2FirewallLogTableEntryDstAddress OBJECT-TYPE
    SYNTAX     DisplayString (SIZE(0..255))
    MAX-ACCESS read-only
    STATUS     current
    DESCRIPTION
            "-- empty --"
    ::= { hmStatusLanBridgeL2FirewallLogTableEntry 4 }

-- {COLUMN} 1.3.6.1.4.1.248.32.18.1.31.248.1.1.5
hmStatusLanBridgeL2FirewallLogTableEntryProtocol OBJECT-TYPE
    SYNTAX     DisplayString (SIZE(0..255))
    MAX-ACCESS read-only
    STATUS     current
    DESCRIPTION
            "-- empty --"
    ::= { hmStatusLanBridgeL2FirewallLogTableEntry 5 }

-- {COLUMN} 1.3.6.1.4.1.248.32.18.1.31.248.1.1.6
hmStatusLanBridgeL2FirewallLogTableEntrySrcPort OBJECT-TYPE
    SYNTAX     DisplayString (SIZE(0..255))
    MAX-ACCESS read-only
    STATUS     current
    DESCRIPTION
            "-- empty --"
    ::= { hmStatusLanBridgeL2FirewallLogTableEntry 6 }

-- {COLUMN} 1.3.6.1.4.1.248.32.18.1.31.248.1.1.7
hmStatusLanBridgeL2FirewallLogTableEntryDstPort OBJECT-TYPE
    SYNTAX     DisplayString (SIZE(0..255))
    MAX-ACCESS read-only
    STATUS     current
    DESCRIPTION
            "-- empty --"
    ::= { hmStatusLanBridgeL2FirewallLogTableEntry 7 }

-- {COLUMN} 1.3.6.1.4.1.248.32.18.1.31.248.1.1.8
hmStatusLanBridgeL2FirewallLogTableEntryRuleIndex OBJECT-TYPE
    SYNTAX     Integer32 (0..65535)
    MAX-ACCESS read-only
    STATUS     current
    DESCRIPTION
            "-- empty --"
    ::= { hmStatusLanBridgeL2FirewallLogTableEntry 8 }

-- {COLUMN} 1.3.6.1.4.1.248.32.18.1.31.248.1.1.9
hmStatusLanBridgeL2FirewallLogTableEntryAction OBJECT-TYPE
    SYNTAX     DisplayString (SIZE(0..255))
    MAX-ACCESS read-only
    STATUS     current
    DESCRIPTION
            "-- empty --"
    ::= { hmStatusLanBridgeL2FirewallLogTableEntry 9 }

-- {NODE} 1.3.6.1.4.1.248.32.18.1.31.248.2
hmStatusLanBridgeL2FirewallStatistics OBJECT IDENTIFIER ::= { hmStatusLanBridgeL2Firewall 2 }

-- {SCALAR} 1.3.6.1.4.1.248.32.18.1.31.248.2.1
hmStatusLanBridgeL2FirewallStatisticsTotalPacketsProcessed OBJECT-TYPE
    SYNTAX     Counter64
    MAX-ACCESS read-only
    STATUS     current
    DESCRIPTION
            "-- empty --"
    ::= { hmStatusLanBridgeL2FirewallStatistics 1 }

-- {SCALAR} 1.3.6.1.4.1.248.32.18.1.31.248.2.2
hmStatusLanBridgeL2FirewallStatisticsTotalPacketsProcessedSize OBJECT-TYPE
    SYNTAX     Counter64
    MAX-ACCESS read-only
    STATUS     current
    DESCRIPTION
            "-- empty --"
    ::= { hmStatusLanBridgeL2FirewallStatistics 2 }

-- {SCALAR} 1.3.6.1.4.1.248.32.18.1.31.248.2.3
hmStatusLanBridgeL2FirewallStatisticsTotalPacketsRejected OBJECT-TYPE
    SYNTAX     Counter64
    MAX-ACCESS read-only
    STATUS     current
    DESCRIPTION
            "-- empty --"
    ::= { hmStatusLanBridgeL2FirewallStatistics 3 }

-- {SCALAR} 1.3.6.1.4.1.248.32.18.1.31.248.2.4
hmStatusLanBridgeL2FirewallStatisticsTotalPacketsRejectedSize OBJECT-TYPE
    SYNTAX     Counter64
    MAX-ACCESS read-only
    STATUS     current
    DESCRIPTION
            "-- empty --"
    ::= { hmStatusLanBridgeL2FirewallStatistics 4 }

-- {SCALAR} 1.3.6.1.4.1.248.32.18.1.31.248.2.10
hmStatusLanBridgeL2FirewallStatisticsRulesTable OBJECT-TYPE
    SYNTAX     Integer32 (0..2147483647)
    MAX-ACCESS read-only
    STATUS     current
    DESCRIPTION
            "-- empty --"
    ::= { hmStatusLanBridgeL2FirewallStatistics 10 }

-- {SCALAR} 1.3.6.1.4.1.248.32.18.1.31.248.3
hmStatusLanBridgeL2FirewallOpenConnections OBJECT-TYPE
    SYNTAX     Integer32 (0..2147483647)
    MAX-ACCESS read-only
    STATUS     current
    DESCRIPTION
            "-- empty --"
    ::= { hmStatusLanBridgeL2Firewall 3 }

-- {NODE} 1.3.6.1.4.1.248.32.18.1.32
hmStatusDhcpClient OBJECT IDENTIFIER ::= { hmStatus 32 }

-- {TABLE} 1.3.6.1.4.1.248.32.18.1.32.20
hmStatusDhcpClientWanIpListTable OBJECT-TYPE
    SYNTAX     SEQUENCE OF HmStatusDhcpClientWanIpListEntry
    MAX-ACCESS not-accessible
    STATUS     current
    DESCRIPTION
            "-- empty --"
    ::= { hmStatusDhcpClient 20 }

-- {ROW} 1.3.6.1.4.1.248.32.18.1.32.20.1
hmStatusDhcpClientWanIpListEntry OBJECT-TYPE
    SYNTAX     HmStatusDhcpClientWanIpListEntry
    MAX-ACCESS not-accessible
    STATUS     current
    DESCRIPTION
            ""
    INDEX {
            hmStatusDhcpClientWanIpListEntryIfc
          }
    ::= { hmStatusDhcpClientWanIpListTable 1 }

HmStatusDhcpClientWanIpListEntry ::= SEQUENCE {
            hmStatusDhcpClientWanIpListEntryIfc INTEGER,
            hmStatusDhcpClientWanIpListEntryIpAddress IpAddress,
            hmStatusDhcpClientWanIpListEntryIpNetmask IpAddress,
            hmStatusDhcpClientWanIpListEntryGateway IpAddress,
            hmStatusDhcpClientWanIpListEntryDnsDefault IpAddress,
            hmStatusDhcpClientWanIpListEntryDnsBackup IpAddress,
            hmStatusDhcpClientWanIpListEntryNbnsDefault IpAddress,
            hmStatusDhcpClientWanIpListEntryNbnsBackup IpAddress,
            hmStatusDhcpClientWanIpListEntryDhcpServer IpAddress,
            hmStatusDhcpClientWanIpListEntryDomain DisplayString
    }

-- {COLUMN} 1.3.6.1.4.1.248.32.18.1.32.20.1.1
hmStatusDhcpClientWanIpListEntryIfc OBJECT-TYPE
    SYNTAX     INTEGER {
                  eModem (513),
                  eDslCh1 (2049),
                  eDslCh2 (2050),
                  eDslCh3 (2051),
                  eDslCh4 (2052),
                  eDslCh5 (2053),
                  eDslCh6 (2054),
                  eDslCh7 (2055),
                  eDslCh8 (2056)
            }
    MAX-ACCESS read-only
    STATUS     current
    DESCRIPTION
            "-- empty --"
    ::= { hmStatusDhcpClientWanIpListEntry 1 }

-- {COLUMN} 1.3.6.1.4.1.248.32.18.1.32.20.1.2
hmStatusDhcpClientWanIpListEntryIpAddress OBJECT-TYPE
    SYNTAX     IpAddress
    MAX-ACCESS read-only
    STATUS     current
    DESCRIPTION
            "-- empty --"
    ::= { hmStatusDhcpClientWanIpListEntry 2 }

-- {COLUMN} 1.3.6.1.4.1.248.32.18.1.32.20.1.3
hmStatusDhcpClientWanIpListEntryIpNetmask OBJECT-TYPE
    SYNTAX     IpAddress
    MAX-ACCESS read-only
    STATUS     current
    DESCRIPTION
            "-- empty --"
    ::= { hmStatusDhcpClientWanIpListEntry 3 }

-- {COLUMN} 1.3.6.1.4.1.248.32.18.1.32.20.1.4
hmStatusDhcpClientWanIpListEntryGateway OBJECT-TYPE
    SYNTAX     IpAddress
    MAX-ACCESS read-only
    STATUS     current
    DESCRIPTION
            "-- empty --"
    ::= { hmStatusDhcpClientWanIpListEntry 4 }

-- {COLUMN} 1.3.6.1.4.1.248.32.18.1.32.20.1.5
hmStatusDhcpClientWanIpListEntryDnsDefault OBJECT-TYPE
    SYNTAX     IpAddress
    MAX-ACCESS read-only
    STATUS     current
    DESCRIPTION
            "-- empty --"
    ::= { hmStatusDhcpClientWanIpListEntry 5 }

-- {COLUMN} 1.3.6.1.4.1.248.32.18.1.32.20.1.6
hmStatusDhcpClientWanIpListEntryDnsBackup OBJECT-TYPE
    SYNTAX     IpAddress
    MAX-ACCESS read-only
    STATUS     current
    DESCRIPTION
            "-- empty --"
    ::= { hmStatusDhcpClientWanIpListEntry 6 }

-- {COLUMN} 1.3.6.1.4.1.248.32.18.1.32.20.1.7
hmStatusDhcpClientWanIpListEntryNbnsDefault OBJECT-TYPE
    SYNTAX     IpAddress
    MAX-ACCESS read-only
    STATUS     current
    DESCRIPTION
            "-- empty --"
    ::= { hmStatusDhcpClientWanIpListEntry 7 }

-- {COLUMN} 1.3.6.1.4.1.248.32.18.1.32.20.1.8
hmStatusDhcpClientWanIpListEntryNbnsBackup OBJECT-TYPE
    SYNTAX     IpAddress
    MAX-ACCESS read-only
    STATUS     current
    DESCRIPTION
            "-- empty --"
    ::= { hmStatusDhcpClientWanIpListEntry 8 }

-- {COLUMN} 1.3.6.1.4.1.248.32.18.1.32.20.1.9
hmStatusDhcpClientWanIpListEntryDhcpServer OBJECT-TYPE
    SYNTAX     IpAddress
    MAX-ACCESS read-only
    STATUS     current
    DESCRIPTION
            "-- empty --"
    ::= { hmStatusDhcpClientWanIpListEntry 9 }

-- {COLUMN} 1.3.6.1.4.1.248.32.18.1.32.20.1.10
hmStatusDhcpClientWanIpListEntryDomain OBJECT-TYPE
    SYNTAX     DisplayString (SIZE(0..255))
    MAX-ACCESS read-only
    STATUS     current
    DESCRIPTION
            "-- empty --"
    ::= { hmStatusDhcpClientWanIpListEntry 10 }

-- {TABLE} 1.3.6.1.4.1.248.32.18.1.32.21
hmStatusDhcpClientLanIpListTable OBJECT-TYPE
    SYNTAX     SEQUENCE OF HmStatusDhcpClientLanIpListEntry
    MAX-ACCESS not-accessible
    STATUS     current
    DESCRIPTION
            "-- empty --"
    ::= { hmStatusDhcpClient 21 }

-- {ROW} 1.3.6.1.4.1.248.32.18.1.32.21.1
hmStatusDhcpClientLanIpListEntry OBJECT-TYPE
    SYNTAX     HmStatusDhcpClientLanIpListEntry
    MAX-ACCESS not-accessible
    STATUS     current
    DESCRIPTION
            ""
    INDEX {
            hmStatusDhcpClientLanIpListEntryIfc
          }
    ::= { hmStatusDhcpClientLanIpListTable 1 }

HmStatusDhcpClientLanIpListEntry ::= SEQUENCE {
            hmStatusDhcpClientLanIpListEntryIfc DisplayString,
            hmStatusDhcpClientLanIpListEntryIpAddress IpAddress,
            hmStatusDhcpClientLanIpListEntryIpNetmask IpAddress,
            hmStatusDhcpClientLanIpListEntryGateway IpAddress,
            hmStatusDhcpClientLanIpListEntryDnsDefault IpAddress,
            hmStatusDhcpClientLanIpListEntryDnsBackup IpAddress,
            hmStatusDhcpClientLanIpListEntryNbnsDefault IpAddress,
            hmStatusDhcpClientLanIpListEntryNbnsBackup IpAddress,
            hmStatusDhcpClientLanIpListEntryDhcpServer IpAddress,
            hmStatusDhcpClientLanIpListEntryDomain DisplayString
    }

-- {COLUMN} 1.3.6.1.4.1.248.32.18.1.32.21.1.1
hmStatusDhcpClientLanIpListEntryIfc OBJECT-TYPE
    SYNTAX     DisplayString (SIZE(0..16))
    MAX-ACCESS read-only
    STATUS     current
    DESCRIPTION
            "-- empty --"
    ::= { hmStatusDhcpClientLanIpListEntry 1 }

-- {COLUMN} 1.3.6.1.4.1.248.32.18.1.32.21.1.2
hmStatusDhcpClientLanIpListEntryIpAddress OBJECT-TYPE
    SYNTAX     IpAddress
    MAX-ACCESS read-only
    STATUS     current
    DESCRIPTION
            "-- empty --"
    ::= { hmStatusDhcpClientLanIpListEntry 2 }

-- {COLUMN} 1.3.6.1.4.1.248.32.18.1.32.21.1.3
hmStatusDhcpClientLanIpListEntryIpNetmask OBJECT-TYPE
    SYNTAX     IpAddress
    MAX-ACCESS read-only
    STATUS     current
    DESCRIPTION
            "-- empty --"
    ::= { hmStatusDhcpClientLanIpListEntry 3 }

-- {COLUMN} 1.3.6.1.4.1.248.32.18.1.32.21.1.4
hmStatusDhcpClientLanIpListEntryGateway OBJECT-TYPE
    SYNTAX     IpAddress
    MAX-ACCESS read-only
    STATUS     current
    DESCRIPTION
            "-- empty --"
    ::= { hmStatusDhcpClientLanIpListEntry 4 }

-- {COLUMN} 1.3.6.1.4.1.248.32.18.1.32.21.1.5
hmStatusDhcpClientLanIpListEntryDnsDefault OBJECT-TYPE
    SYNTAX     IpAddress
    MAX-ACCESS read-only
    STATUS     current
    DESCRIPTION
            "-- empty --"
    ::= { hmStatusDhcpClientLanIpListEntry 5 }

-- {COLUMN} 1.3.6.1.4.1.248.32.18.1.32.21.1.6
hmStatusDhcpClientLanIpListEntryDnsBackup OBJECT-TYPE
    SYNTAX     IpAddress
    MAX-ACCESS read-only
    STATUS     current
    DESCRIPTION
            "-- empty --"
    ::= { hmStatusDhcpClientLanIpListEntry 6 }

-- {COLUMN} 1.3.6.1.4.1.248.32.18.1.32.21.1.7
hmStatusDhcpClientLanIpListEntryNbnsDefault OBJECT-TYPE
    SYNTAX     IpAddress
    MAX-ACCESS read-only
    STATUS     current
    DESCRIPTION
            "-- empty --"
    ::= { hmStatusDhcpClientLanIpListEntry 7 }

-- {COLUMN} 1.3.6.1.4.1.248.32.18.1.32.21.1.8
hmStatusDhcpClientLanIpListEntryNbnsBackup OBJECT-TYPE
    SYNTAX     IpAddress
    MAX-ACCESS read-only
    STATUS     current
    DESCRIPTION
            "-- empty --"
    ::= { hmStatusDhcpClientLanIpListEntry 8 }

-- {COLUMN} 1.3.6.1.4.1.248.32.18.1.32.21.1.9
hmStatusDhcpClientLanIpListEntryDhcpServer OBJECT-TYPE
    SYNTAX     IpAddress
    MAX-ACCESS read-only
    STATUS     current
    DESCRIPTION
            "-- empty --"
    ::= { hmStatusDhcpClientLanIpListEntry 9 }

-- {COLUMN} 1.3.6.1.4.1.248.32.18.1.32.21.1.10
hmStatusDhcpClientLanIpListEntryDomain OBJECT-TYPE
    SYNTAX     DisplayString (SIZE(0..255))
    MAX-ACCESS read-only
    STATUS     current
    DESCRIPTION
            "-- empty --"
    ::= { hmStatusDhcpClientLanIpListEntry 10 }

-- {NODE} 1.3.6.1.4.1.248.32.18.1.35
hmStatusSnmp OBJECT IDENTIFIER ::= { hmStatus 35 }

-- {TABLE} 1.3.6.1.4.1.248.32.18.1.35.1
hmStatusSnmpEventTable OBJECT-TYPE
    SYNTAX     SEQUENCE OF HmStatusSnmpEventEntry
    MAX-ACCESS not-accessible
    STATUS     current
    DESCRIPTION
            "-- empty --"
    ::= { hmStatusSnmp 1 }

-- {ROW} 1.3.6.1.4.1.248.32.18.1.35.1.1
hmStatusSnmpEventEntry OBJECT-TYPE
    SYNTAX     HmStatusSnmpEventEntry
    MAX-ACCESS not-accessible
    STATUS     current
    DESCRIPTION
            ""
    INDEX {
            hmStatusSnmpEventEntryTrapName,
            hmStatusSnmpEventEntryVendorName
          }
    ::= { hmStatusSnmpEventTable 1 }

HmStatusSnmpEventEntry ::= SEQUENCE {
            hmStatusSnmpEventEntryTrapName INTEGER,
            hmStatusSnmpEventEntryVendorName INTEGER,
            hmStatusSnmpEventEntryCount Integer32
    }

-- {COLUMN} 1.3.6.1.4.1.248.32.18.1.35.1.1.1
hmStatusSnmpEventEntryTrapName OBJECT-TYPE
    SYNTAX     INTEGER {
                  eWarmBoot (1),
                  eLinkDown (2),
                  eLinkUp (3),
                  eAuthFail (4),
                  eEPGNloss (5),
                  eEnterprise (6),
                  eColdBoot (255)
            }
    MAX-ACCESS read-only
    STATUS     current
    DESCRIPTION
            "-- empty --"
    ::= { hmStatusSnmpEventEntry 1 }

-- {COLUMN} 1.3.6.1.4.1.248.32.18.1.35.1.1.2
hmStatusSnmpEventEntryVendorName OBJECT-TYPE
    SYNTAX     INTEGER {
                  eNone (0),
                  eStatChan (1),
                  eFwUplStart (4),
                  eUplsucc (5),
                  eUplfailto (6),
                  eUplfailincl (7),
                  eUplfailbaddev (8),
                  eLogin (9),
                  eLogout (10),
                  eCnfuplstart (11),
                  eCnfdnlstart (12),
                  eCnfdnlsucc (13),
                  eBssscan (14),
                  eBssstart (15),
                  eBssjoin (16),
                  eAuthstation (17),
                  eDeauthstation (18),
                  eAssstation (19),
                  eReassstation (20),
                  eDisassstation (21),
                  eAssrej (22),
                  eCardhung (25),
                  eIpfwflt (26),
                  eVpnconn (27),
                  ePptpconn (28),
                  eErrlogin (29),
                  eKeyhandshakeTimeout (33),
                  eSupervision (35),
                  eLdblconn (38),
                  ePppoesconn (39),
                  eVrrp (41),
                  eExceirp (42),
                  eIdleTimeout (46),
                  eAdminDeassoc (47),
                  eWlanovertemp (48),
                  eWlanovertempend (49),
                  eWlanundertemp (50),
                  eWlanundertempend (51),
                  eMacchkfail (52),
                  eRoamed (53),
                  eConnected (54),
                  eClLostconn (55),
                  eClAuthfail (56),
                  eClAssocfail (57),
                  eClConnected (58),
                  eCl8021xFail (59),
                  eCaStatChg (61),
                  eNewPendReq (62),
                  eMissingAp (63),
                  eActiveAp (64),
                  eNewAp (65),
                  eStations (66),
                  eNetworks (67),
                  eNetworkcounts (68),
                  eApCounter (69),
                  eCertTabMod (73),
                  ePendListMod (74),
                  eNextdoorAp (75),
                  eWlcTunnels (76),
                  eLicensemgtexpire (77),
                  eScrptuplstart (79),
                  eScrptdnlstart (80),
                  eIpv6fwflt (81),
                  eWwanStates (82),
                  eDS-Lite (83),
                  eL2TP-Endpoints (85),
                  eL2TP-Connections (86),
                  eLoginBlocked (87),
                  eSpgtreePortstatchg (1000),
                  eSpgtreeRstpstatchg (1001),
                  eSpgtreeRootportchg (1002),
                  eHttpTunnelOpen (2000),
                  eHttpTunnelClose (2001),
                  eLanauthuseradd (3000),
                  eLanauthuserdel (3001),
                  eLanauthsessionstart (3002),
                  eLanauthsessionend (3003),
                  eTempmonovertemp (4000),
                  eTempmonnoovertemp (4001),
                  eTempmonundertemp (4002),
                  eTempmonnoundertemp (4003),
                  eLanOvertempThrottle (5002),
                  eLanOvertempThrottleEnd (5003),
                  eLanOvertempThrottleRecommend (5004),
                  eEthPortDownshift (5101),
                  eWlanConfadaptRadiochannel (6100),
                  eWlanConfadaptRadiomode (6101),
                  eWlanConfadaptBasicRate (6102),
                  eWlanConfadaptEapolRate (6103),
                  eWlanConfadaptEncryption (6104),
                  eWlanAlarmP2pSignal (6200),
                  eWlanAlarmP2pTxtotretries (6201),
                  eWlanAlarmP2pTxerrors (6202),
                  eWlanAlarmNetwSignal (6203),
                  eWlanAlarmNetwTxtotretries (6204),
                  eWlanAlarmNetwTxerrors (6205),
                  eWlanAlarmClientSignal (6206),
                  eWlanAlarmClientTxtotretries (6207),
                  eWlanAlarmClientTxerrors (6208),
                  eWlanDfsAllblocked (6300),
                  eUplinvversion (7000),
                  eUplfileexists (7001),
                  eIdsTrapEvent (10000),
                  eL2fwflt (10001),
                  eWlanLinkStatusLogUpdated (10100),
                  ePsustate (10101)
            }
    MAX-ACCESS read-only
    STATUS     current
    DESCRIPTION
            "-- empty --"
    ::= { hmStatusSnmpEventEntry 2 }

-- {COLUMN} 1.3.6.1.4.1.248.32.18.1.35.1.1.3
hmStatusSnmpEventEntryCount OBJECT-TYPE
    SYNTAX     Integer32 (0..2147483647)
    MAX-ACCESS read-only
    STATUS     current
    DESCRIPTION
            "-- empty --"
    ::= { hmStatusSnmpEventEntry 3 }

-- {SCALAR} 1.3.6.1.4.1.248.32.18.1.35.2
hmStatusSnmpRejectedRequests OBJECT-TYPE
    SYNTAX     Integer32 (0..2147483647)
    MAX-ACCESS read-only
    STATUS     current
    DESCRIPTION
            "-- empty --"
    ::= { hmStatusSnmp 2 }

-- {SCALAR} 1.3.6.1.4.1.248.32.18.1.35.3
hmStatusSnmpQueueBlockErrors OBJECT-TYPE
    SYNTAX     Integer32 (0..2147483647)
    MAX-ACCESS read-only
    STATUS     current
    DESCRIPTION
            "-- empty --"
    ::= { hmStatusSnmp 3 }

-- {SCALAR} 1.3.6.1.4.1.248.32.18.1.35.4
hmStatusSnmpDroppedPackets OBJECT-TYPE
    SYNTAX     Integer32 (0..2147483647)
    MAX-ACCESS read-only
    STATUS     current
    DESCRIPTION
            "-- empty --"
    ::= { hmStatusSnmp 4 }

-- {SCALAR} 1.3.6.1.4.1.248.32.18.1.35.5
hmStatusSnmpPublicComment1 OBJECT-TYPE
    SYNTAX     DisplayString (SIZE(0..255))
    MAX-ACCESS read-only
    STATUS     current
    DESCRIPTION
            "-- empty --"
    ::= { hmStatusSnmp 5 }

-- {SCALAR} 1.3.6.1.4.1.248.32.18.1.35.7
hmStatusSnmpPublicComment3 OBJECT-TYPE
    SYNTAX     DisplayString (SIZE(0..255))
    MAX-ACCESS read-only
    STATUS     current
    DESCRIPTION
            "-- empty --"
    ::= { hmStatusSnmp 7 }

-- {SCALAR} 1.3.6.1.4.1.248.32.18.1.35.8
hmStatusSnmpPublicComment4 OBJECT-TYPE
    SYNTAX     DisplayString (SIZE(0..255))
    MAX-ACCESS read-only
    STATUS     current
    DESCRIPTION
            "-- empty --"
    ::= { hmStatusSnmp 8 }

-- {SCALAR} 1.3.6.1.4.1.248.32.18.1.35.9
hmStatusSnmpPublicComment2 OBJECT-TYPE
    SYNTAX     DisplayString (SIZE(0..255))
    MAX-ACCESS read-only
    STATUS     current
    DESCRIPTION
            "-- empty --"
    ::= { hmStatusSnmp 9 }

-- {NODE} 1.3.6.1.4.1.248.32.18.1.43
hmStatusMail OBJECT IDENTIFIER ::= { hmStatus 43 }

-- {SCALAR} 1.3.6.1.4.1.248.32.18.1.43.1
hmStatusMailBufferedMails OBJECT-TYPE
    SYNTAX     Integer32 (0..65535)
    MAX-ACCESS read-only
    STATUS     current
    DESCRIPTION
            "-- empty --"
    ::= { hmStatusMail 1 }

-- {SCALAR} 1.3.6.1.4.1.248.32.18.1.43.2
hmStatusMailSentMails OBJECT-TYPE
    SYNTAX     Counter32
    MAX-ACCESS read-only
    STATUS     current
    DESCRIPTION
            "-- empty --"
    ::= { hmStatusMail 2 }

-- {SCALAR} 1.3.6.1.4.1.248.32.18.1.43.3
hmStatusMailDiscardedMails OBJECT-TYPE
    SYNTAX     Counter32
    MAX-ACCESS read-only
    STATUS     current
    DESCRIPTION
            "-- empty --"
    ::= { hmStatusMail 3 }

-- {SCALAR} 1.3.6.1.4.1.248.32.18.1.43.4
hmStatusMailClearBuffer OBJECT-TYPE
    SYNTAX     DisplayString
    MAX-ACCESS read-write
    STATUS     current
    DESCRIPTION
            "-- empty --"
    ::= { hmStatusMail 4 }

-- {SCALAR} 1.3.6.1.4.1.248.32.18.1.43.5
hmStatusMailDeleteStatistics OBJECT-TYPE
    SYNTAX     DisplayString
    MAX-ACCESS read-write
    STATUS     current
    DESCRIPTION
            "-- empty --"
    ::= { hmStatusMail 5 }

-- {NODE} 1.3.6.1.4.1.248.32.18.1.44
hmStatusPublicSpot OBJECT IDENTIFIER ::= { hmStatus 44 }

-- {TABLE} 1.3.6.1.4.1.248.32.18.1.44.1
hmStatusPublicSpotStationTableTable OBJECT-TYPE
    SYNTAX     SEQUENCE OF HmStatusPublicSpotStationTableEntry
    MAX-ACCESS not-accessible
    STATUS     current
    DESCRIPTION
            "-- empty --"
    ::= { hmStatusPublicSpot 1 }

-- {ROW} 1.3.6.1.4.1.248.32.18.1.44.1.1
hmStatusPublicSpotStationTableEntry OBJECT-TYPE
    SYNTAX     HmStatusPublicSpotStationTableEntry
    MAX-ACCESS not-accessible
    STATUS     current
    DESCRIPTION
            ""
    INDEX {
            hmStatusPublicSpotStationTableEntryMacAddress
          }
    ::= { hmStatusPublicSpotStationTableTable 1 }

HmStatusPublicSpotStationTableEntry ::= SEQUENCE {
            hmStatusPublicSpotStationTableEntryMacAddress DisplayString,
            hmStatusPublicSpotStationTableEntryIpAddress DisplayString,
            hmStatusPublicSpotStationTableEntryName DisplayString,
            hmStatusPublicSpotStationTableEntryProvider DisplayString,
            hmStatusPublicSpotStationTableEntryTxBytes Integer32,
            hmStatusPublicSpotStationTableEntryRxBytes Integer32,
            hmStatusPublicSpotStationTableEntryTxPackets Integer32,
            hmStatusPublicSpotStationTableEntryRxPackets Integer32,
            hmStatusPublicSpotStationTableEntryLoginTime Integer32,
            hmStatusPublicSpotStationTableEntryState INTEGER,
            hmStatusPublicSpotStationTableEntrySessionId Integer32,
            hmStatusPublicSpotStationTableEntrySecExpire Integer32,
            hmStatusPublicSpotStationTableEntryVolExpire Integer32,
            hmStatusPublicSpotStationTableEntryAccCycle Integer32,
            hmStatusPublicSpotStationTableEntryIdleTimeout Integer32,
            hmStatusPublicSpotStationTableEntryTxLimit Integer32,
            hmStatusPublicSpotStationTableEntryRxLimit Integer32,
            hmStatusPublicSpotStationTableEntryPort DisplayString,
            hmStatusPublicSpotStationTableEntryOrigHost DisplayString,
            hmStatusPublicSpotStationTableEntryVlanId Integer32,
            hmStatusPublicSpotStationTableEntryVolExpireMbytes Integer32,
            hmStatusPublicSpotStationTableEntryTxBytesNew Counter64,
            hmStatusPublicSpotStationTableEntryRxBytesNew Counter64,
            hmStatusPublicSpotStationTableEntryCircuitId DisplayString
    }

-- {COLUMN} 1.3.6.1.4.1.248.32.18.1.44.1.1.1
hmStatusPublicSpotStationTableEntryMacAddress OBJECT-TYPE
    SYNTAX     DisplayString (SIZE(0..12))
    MAX-ACCESS read-only
    STATUS     current
    DESCRIPTION
            "-- empty --"
    ::= { hmStatusPublicSpotStationTableEntry 1 }

-- {COLUMN} 1.3.6.1.4.1.248.32.18.1.44.1.1.2
hmStatusPublicSpotStationTableEntryIpAddress OBJECT-TYPE
    SYNTAX     DisplayString (SIZE(0..15))
    MAX-ACCESS read-only
    STATUS     current
    DESCRIPTION
            "-- empty --"
    ::= { hmStatusPublicSpotStationTableEntry 2 }

-- {COLUMN} 1.3.6.1.4.1.248.32.18.1.44.1.1.3
hmStatusPublicSpotStationTableEntryName OBJECT-TYPE
    SYNTAX     DisplayString (SIZE(0..64))
    MAX-ACCESS read-only
    STATUS     current
    DESCRIPTION
            "-- empty --"
    ::= { hmStatusPublicSpotStationTableEntry 3 }

-- {COLUMN} 1.3.6.1.4.1.248.32.18.1.44.1.1.4
hmStatusPublicSpotStationTableEntryProvider OBJECT-TYPE
    SYNTAX     DisplayString (SIZE(0..16))
    MAX-ACCESS read-only
    STATUS     current
    DESCRIPTION
            "-- empty --"
    ::= { hmStatusPublicSpotStationTableEntry 4 }

-- {COLUMN} 1.3.6.1.4.1.248.32.18.1.44.1.1.5
hmStatusPublicSpotStationTableEntryTxBytes OBJECT-TYPE
    SYNTAX     Integer32 (0..2147483647)
    MAX-ACCESS read-only
    STATUS     current
    DESCRIPTION
            "-- empty --"
    ::= { hmStatusPublicSpotStationTableEntry 5 }

-- {COLUMN} 1.3.6.1.4.1.248.32.18.1.44.1.1.6
hmStatusPublicSpotStationTableEntryRxBytes OBJECT-TYPE
    SYNTAX     Integer32 (0..2147483647)
    MAX-ACCESS read-only
    STATUS     current
    DESCRIPTION
            "-- empty --"
    ::= { hmStatusPublicSpotStationTableEntry 6 }

-- {COLUMN} 1.3.6.1.4.1.248.32.18.1.44.1.1.7
hmStatusPublicSpotStationTableEntryTxPackets OBJECT-TYPE
    SYNTAX     Integer32 (0..2147483647)
    MAX-ACCESS read-only
    STATUS     current
    DESCRIPTION
            "-- empty --"
    ::= { hmStatusPublicSpotStationTableEntry 7 }

-- {COLUMN} 1.3.6.1.4.1.248.32.18.1.44.1.1.8
hmStatusPublicSpotStationTableEntryRxPackets OBJECT-TYPE
    SYNTAX     Integer32 (0..2147483647)
    MAX-ACCESS read-only
    STATUS     current
    DESCRIPTION
            "-- empty --"
    ::= { hmStatusPublicSpotStationTableEntry 8 }

-- {COLUMN} 1.3.6.1.4.1.248.32.18.1.44.1.1.9
hmStatusPublicSpotStationTableEntryLoginTime OBJECT-TYPE
    SYNTAX     Integer32 (0..2147483647)
    MAX-ACCESS read-only
    STATUS     current
    DESCRIPTION
            "-- empty --"
    ::= { hmStatusPublicSpotStationTableEntry 9 }

-- {COLUMN} 1.3.6.1.4.1.248.32.18.1.44.1.1.10
hmStatusPublicSpotStationTableEntryState OBJECT-TYPE
    SYNTAX     INTEGER {
                  eUnauthenticated (0),
                  eAuthenticated (1),
                  eDeceased (2),
                  eAdvertisement (4)
            }
    MAX-ACCESS read-only
    STATUS     current
    DESCRIPTION
            "-- empty --"
    ::= { hmStatusPublicSpotStationTableEntry 10 }

-- {COLUMN} 1.3.6.1.4.1.248.32.18.1.44.1.1.11
hmStatusPublicSpotStationTableEntrySessionId OBJECT-TYPE
    SYNTAX     Integer32 (0..2147483647)
    MAX-ACCESS read-only
    STATUS     current
    DESCRIPTION
            "-- empty --"
    ::= { hmStatusPublicSpotStationTableEntry 11 }

-- {COLUMN} 1.3.6.1.4.1.248.32.18.1.44.1.1.12
hmStatusPublicSpotStationTableEntrySecExpire OBJECT-TYPE
    SYNTAX     Integer32 (0..2147483647)
    MAX-ACCESS read-only
    STATUS     current
    DESCRIPTION
            "-- empty --"
    ::= { hmStatusPublicSpotStationTableEntry 12 }

-- {COLUMN} 1.3.6.1.4.1.248.32.18.1.44.1.1.13
hmStatusPublicSpotStationTableEntryVolExpire OBJECT-TYPE
    SYNTAX     Integer32 (0..2147483647)
    MAX-ACCESS read-only
    STATUS     current
    DESCRIPTION
            "-- empty --"
    ::= { hmStatusPublicSpotStationTableEntry 13 }

-- {COLUMN} 1.3.6.1.4.1.248.32.18.1.44.1.1.14
hmStatusPublicSpotStationTableEntryAccCycle OBJECT-TYPE
    SYNTAX     Integer32 (0..2147483647)
    MAX-ACCESS read-only
    STATUS     current
    DESCRIPTION
            "-- empty --"
    ::= { hmStatusPublicSpotStationTableEntry 14 }

-- {COLUMN} 1.3.6.1.4.1.248.32.18.1.44.1.1.16
hmStatusPublicSpotStationTableEntryIdleTimeout OBJECT-TYPE
    SYNTAX     Integer32 (0..2147483647)
    MAX-ACCESS read-only
    STATUS     current
    DESCRIPTION
            "-- empty --"
    ::= { hmStatusPublicSpotStationTableEntry 16 }

-- {COLUMN} 1.3.6.1.4.1.248.32.18.1.44.1.1.17
hmStatusPublicSpotStationTableEntryTxLimit OBJECT-TYPE
    SYNTAX     Integer32 (0..2147483647)
    MAX-ACCESS read-only
    STATUS     current
    DESCRIPTION
            "-- empty --"
    ::= { hmStatusPublicSpotStationTableEntry 17 }

-- {COLUMN} 1.3.6.1.4.1.248.32.18.1.44.1.1.18
hmStatusPublicSpotStationTableEntryRxLimit OBJECT-TYPE
    SYNTAX     Integer32 (0..2147483647)
    MAX-ACCESS read-only
    STATUS     current
    DESCRIPTION
            "-- empty --"
    ::= { hmStatusPublicSpotStationTableEntry 18 }

-- {COLUMN} 1.3.6.1.4.1.248.32.18.1.44.1.1.19
hmStatusPublicSpotStationTableEntryPort OBJECT-TYPE
    SYNTAX     DisplayString (SIZE(0..18))
    MAX-ACCESS read-only
    STATUS     current
    DESCRIPTION
            "-- empty --"
    ::= { hmStatusPublicSpotStationTableEntry 19 }

-- {COLUMN} 1.3.6.1.4.1.248.32.18.1.44.1.1.20
hmStatusPublicSpotStationTableEntryOrigHost OBJECT-TYPE
    SYNTAX     DisplayString (SIZE(0..255))
    MAX-ACCESS read-only
    STATUS     current
    DESCRIPTION
            "-- empty --"
    ::= { hmStatusPublicSpotStationTableEntry 20 }

-- {COLUMN} 1.3.6.1.4.1.248.32.18.1.44.1.1.21
hmStatusPublicSpotStationTableEntryVlanId OBJECT-TYPE
    SYNTAX     Integer32 (0..65535)
    MAX-ACCESS read-only
    STATUS     current
    DESCRIPTION
            "-- empty --"
    ::= { hmStatusPublicSpotStationTableEntry 21 }

-- {COLUMN} 1.3.6.1.4.1.248.32.18.1.44.1.1.22
hmStatusPublicSpotStationTableEntryVolExpireMbytes OBJECT-TYPE
    SYNTAX     Integer32 (0..2147483647)
    MAX-ACCESS read-only
    STATUS     current
    DESCRIPTION
            "-- empty --"
    ::= { hmStatusPublicSpotStationTableEntry 22 }

-- {COLUMN} 1.3.6.1.4.1.248.32.18.1.44.1.1.23
hmStatusPublicSpotStationTableEntryTxBytesNew OBJECT-TYPE
    SYNTAX     Counter64
    MAX-ACCESS read-only
    STATUS     current
    DESCRIPTION
            "Amount of data sent to the client"
    ::= { hmStatusPublicSpotStationTableEntry 23 }

-- {COLUMN} 1.3.6.1.4.1.248.32.18.1.44.1.1.24
hmStatusPublicSpotStationTableEntryRxBytesNew OBJECT-TYPE
    SYNTAX     Counter64
    MAX-ACCESS read-only
    STATUS     current
    DESCRIPTION
            "Amount of data received from the client"
    ::= { hmStatusPublicSpotStationTableEntry 24 }

-- {COLUMN} 1.3.6.1.4.1.248.32.18.1.44.1.1.25
hmStatusPublicSpotStationTableEntryCircuitId OBJECT-TYPE
    SYNTAX     DisplayString (SIZE(0..64))
    MAX-ACCESS read-only
    STATUS     current
    DESCRIPTION
            "-- empty --"
    ::= { hmStatusPublicSpotStationTableEntry 25 }

-- {SCALAR} 1.3.6.1.4.1.248.32.18.1.44.2
hmStatusPublicSpotDeleteStation OBJECT-TYPE
    SYNTAX     DisplayString
    MAX-ACCESS read-write
    STATUS     current
    DESCRIPTION
            "-- empty --"
    ::= { hmStatusPublicSpot 2 }

-- {SCALAR} 1.3.6.1.4.1.248.32.18.1.44.3
hmStatusPublicSpotCleanupTable OBJECT-TYPE
    SYNTAX     DisplayString
    MAX-ACCESS read-write
    STATUS     current
    DESCRIPTION
            "-- empty --"
    ::= { hmStatusPublicSpot 3 }

-- {SCALAR} 1.3.6.1.4.1.248.32.18.1.44.4
hmStatusPublicSpotDeleteValues OBJECT-TYPE
    SYNTAX     DisplayString
    MAX-ACCESS read-write
    STATUS     current
    DESCRIPTION
            "-- empty --"
    ::= { hmStatusPublicSpot 4 }

-- {SCALAR} 1.3.6.1.4.1.248.32.18.1.44.5
hmStatusPublicSpotDisconnectUser OBJECT-TYPE
    SYNTAX     DisplayString
    MAX-ACCESS read-write
    STATUS     current
    DESCRIPTION
            "-- empty --"
    ::= { hmStatusPublicSpot 5 }

-- {TABLE} 1.3.6.1.4.1.248.32.18.1.44.6
hmStatusPublicSpotLogTableTable OBJECT-TYPE
    SYNTAX     SEQUENCE OF HmStatusPublicSpotLogTableEntry
    MAX-ACCESS not-accessible
    STATUS     current
    DESCRIPTION
            "-- empty --"
    ::= { hmStatusPublicSpot 6 }

-- {ROW} 1.3.6.1.4.1.248.32.18.1.44.6.1
hmStatusPublicSpotLogTableEntry OBJECT-TYPE
    SYNTAX     HmStatusPublicSpotLogTableEntry
    MAX-ACCESS not-accessible
    STATUS     current
    DESCRIPTION
            ""
    INDEX {
            hmStatusPublicSpotLogTableEntryIndex
          }
    ::= { hmStatusPublicSpotLogTableTable 1 }

HmStatusPublicSpotLogTableEntry ::= SEQUENCE {
            hmStatusPublicSpotLogTableEntryIndex Integer32,
            hmStatusPublicSpotLogTableEntryTime DisplayString,
            hmStatusPublicSpotLogTableEntryEvent DisplayString
    }

-- {COLUMN} 1.3.6.1.4.1.248.32.18.1.44.6.1.1
hmStatusPublicSpotLogTableEntryIndex OBJECT-TYPE
    SYNTAX     Integer32 (0..2147483647)
    MAX-ACCESS read-only
    STATUS     current
    DESCRIPTION
            "-- empty --"
    ::= { hmStatusPublicSpotLogTableEntry 1 }

-- {COLUMN} 1.3.6.1.4.1.248.32.18.1.44.6.1.2
hmStatusPublicSpotLogTableEntryTime OBJECT-TYPE
    SYNTAX     DisplayString (SIZE(0..21))
    MAX-ACCESS read-only
    STATUS     current
    DESCRIPTION
            "-- empty --"
    ::= { hmStatusPublicSpotLogTableEntry 2 }

-- {COLUMN} 1.3.6.1.4.1.248.32.18.1.44.6.1.3
hmStatusPublicSpotLogTableEntryEvent OBJECT-TYPE
    SYNTAX     DisplayString (SIZE(0..252))
    MAX-ACCESS read-only
    STATUS     current
    DESCRIPTION
            "-- empty --"
    ::= { hmStatusPublicSpotLogTableEntry 3 }

-- {TABLE} 1.3.6.1.4.1.248.32.18.1.44.7
hmStatusPublicSpotRadiusMacCheckCacheTable OBJECT-TYPE
    SYNTAX     SEQUENCE OF HmStatusPublicSpotRadiusMacCheckCacheEntry
    MAX-ACCESS not-accessible
    STATUS     current
    DESCRIPTION
            "-- empty --"
    ::= { hmStatusPublicSpot 7 }

-- {ROW} 1.3.6.1.4.1.248.32.18.1.44.7.1
hmStatusPublicSpotRadiusMacCheckCacheEntry OBJECT-TYPE
    SYNTAX     HmStatusPublicSpotRadiusMacCheckCacheEntry
    MAX-ACCESS not-accessible
    STATUS     current
    DESCRIPTION
            ""
    INDEX {
            hmStatusPublicSpotRadiusMacCheckCacheEntryMacAddress
          }
    ::= { hmStatusPublicSpotRadiusMacCheckCacheTable 1 }

HmStatusPublicSpotRadiusMacCheckCacheEntry ::= SEQUENCE {
            hmStatusPublicSpotRadiusMacCheckCacheEntryMacAddress MacAddress,
            hmStatusPublicSpotRadiusMacCheckCacheEntryState INTEGER,
            hmStatusPublicSpotRadiusMacCheckCacheEntryAge Integer32,
            hmStatusPublicSpotRadiusMacCheckCacheEntryResponseAge Integer32
    }

-- {COLUMN} 1.3.6.1.4.1.248.32.18.1.44.7.1.1
hmStatusPublicSpotRadiusMacCheckCacheEntryMacAddress OBJECT-TYPE
    SYNTAX     MacAddress
    MAX-ACCESS read-only
    STATUS     current
    DESCRIPTION
            "-- empty --"
    ::= { hmStatusPublicSpotRadiusMacCheckCacheEntry 1 }

-- {COLUMN} 1.3.6.1.4.1.248.32.18.1.44.7.1.2
hmStatusPublicSpotRadiusMacCheckCacheEntryState OBJECT-TYPE
    SYNTAX     INTEGER {
                  ePending (1),
                  eReject (2),
                  eAccept (3)
            }
    MAX-ACCESS read-only
    STATUS     current
    DESCRIPTION
            "-- empty --"
    ::= { hmStatusPublicSpotRadiusMacCheckCacheEntry 2 }

-- {COLUMN} 1.3.6.1.4.1.248.32.18.1.44.7.1.3
hmStatusPublicSpotRadiusMacCheckCacheEntryAge OBJECT-TYPE
    SYNTAX     Integer32 (0..2147483647)
    MAX-ACCESS read-only
    STATUS     current
    DESCRIPTION
            "-- empty --"
    ::= { hmStatusPublicSpotRadiusMacCheckCacheEntry 3 }

-- {COLUMN} 1.3.6.1.4.1.248.32.18.1.44.7.1.4
hmStatusPublicSpotRadiusMacCheckCacheEntryResponseAge OBJECT-TYPE
    SYNTAX     Integer32 (0..2147483647)
    MAX-ACCESS read-only
    STATUS     current
    DESCRIPTION
            "-- empty --"
    ::= { hmStatusPublicSpotRadiusMacCheckCacheEntry 4 }

-- {NODE} 1.3.6.1.4.1.248.32.18.1.44.8
hmStatusPublicSpotAutoReLogin OBJECT IDENTIFIER ::= { hmStatusPublicSpot 8 }

-- {TABLE} 1.3.6.1.4.1.248.32.18.1.44.8.1
hmStatusPublicSpotAutoReLoginStationTableTable OBJECT-TYPE
    SYNTAX     SEQUENCE OF HmStatusPublicSpotAutoReLoginStationTableEntry
    MAX-ACCESS not-accessible
    STATUS     current
    DESCRIPTION
            "-- empty --"
    ::= { hmStatusPublicSpotAutoReLogin 1 }

-- {ROW} 1.3.6.1.4.1.248.32.18.1.44.8.1.1
hmStatusPublicSpotAutoReLoginStationTableEntry OBJECT-TYPE
    SYNTAX     HmStatusPublicSpotAutoReLoginStationTableEntry
    MAX-ACCESS not-accessible
    STATUS     current
    DESCRIPTION
            ""
    INDEX {
            hmStatusPublicSpotAutoReLoginStationTableEntryMacAddress
          }
    ::= { hmStatusPublicSpotAutoReLoginStationTableTable 1 }

HmStatusPublicSpotAutoReLoginStationTableEntry ::= SEQUENCE {
            hmStatusPublicSpotAutoReLoginStationTableEntryMacAddress MacAddress,
            hmStatusPublicSpotAutoReLoginStationTableEntryIpAddress DisplayString,
            hmStatusPublicSpotAutoReLoginStationTableEntryUserName DisplayString,
            hmStatusPublicSpotAutoReLoginStationTableEntryExistTimeout Integer32
    }

-- {COLUMN} 1.3.6.1.4.1.248.32.18.1.44.8.1.1.1
hmStatusPublicSpotAutoReLoginStationTableEntryMacAddress OBJECT-TYPE
    SYNTAX     MacAddress
    MAX-ACCESS read-only
    STATUS     current
    DESCRIPTION
            "-- empty --"
    ::= { hmStatusPublicSpotAutoReLoginStationTableEntry 1 }

-- {COLUMN} 1.3.6.1.4.1.248.32.18.1.44.8.1.1.2
hmStatusPublicSpotAutoReLoginStationTableEntryIpAddress OBJECT-TYPE
    SYNTAX     DisplayString (SIZE(0..15))
    MAX-ACCESS read-only
    STATUS     current
    DESCRIPTION
            "-- empty --"
    ::= { hmStatusPublicSpotAutoReLoginStationTableEntry 2 }

-- {COLUMN} 1.3.6.1.4.1.248.32.18.1.44.8.1.1.3
hmStatusPublicSpotAutoReLoginStationTableEntryUserName OBJECT-TYPE
    SYNTAX     DisplayString (SIZE(0..64))
    MAX-ACCESS read-only
    STATUS     current
    DESCRIPTION
            "-- empty --"
    ::= { hmStatusPublicSpotAutoReLoginStationTableEntry 3 }

-- {COLUMN} 1.3.6.1.4.1.248.32.18.1.44.8.1.1.4
hmStatusPublicSpotAutoReLoginStationTableEntryExistTimeout OBJECT-TYPE
    SYNTAX     Integer32 (0..2147483647)
    MAX-ACCESS read-only
    STATUS     current
    DESCRIPTION
            "-- empty --"
    ::= { hmStatusPublicSpotAutoReLoginStationTableEntry 4 }

-- {SCALAR} 1.3.6.1.4.1.248.32.18.1.44.9
hmStatusPublicSpotFlushTemplateCache OBJECT-TYPE
    SYNTAX     DisplayString
    MAX-ACCESS read-write
    STATUS     current
    DESCRIPTION
            "-- empty --"
    ::= { hmStatusPublicSpot 9 }

-- {NODE} 1.3.6.1.4.1.248.32.18.1.44.10
hmStatusPublicSpotAdvertisement OBJECT IDENTIFIER ::= { hmStatusPublicSpot 10 }

-- {TABLE} 1.3.6.1.4.1.248.32.18.1.44.10.1
hmStatusPublicSpotAdvertisementFreeNetworksTable OBJECT-TYPE
    SYNTAX     SEQUENCE OF HmStatusPublicSpotAdvertisementFreeNetworksEntry
    MAX-ACCESS not-accessible
    STATUS     current
    DESCRIPTION
            "-- empty --"
    ::= { hmStatusPublicSpotAdvertisement 1 }

-- {ROW} 1.3.6.1.4.1.248.32.18.1.44.10.1.1
hmStatusPublicSpotAdvertisementFreeNetworksEntry OBJECT-TYPE
    SYNTAX     HmStatusPublicSpotAdvertisementFreeNetworksEntry
    MAX-ACCESS not-accessible
    STATUS     current
    DESCRIPTION
            ""
    INDEX {
            hmStatusPublicSpotAdvertisementFreeNetworksEntryHostName
          }
    ::= { hmStatusPublicSpotAdvertisementFreeNetworksTable 1 }

HmStatusPublicSpotAdvertisementFreeNetworksEntry ::= SEQUENCE {
            hmStatusPublicSpotAdvertisementFreeNetworksEntryHostName IpAddress,
            hmStatusPublicSpotAdvertisementFreeNetworksEntryMask IpAddress
    }

-- {COLUMN} 1.3.6.1.4.1.248.32.18.1.44.10.1.1.1
hmStatusPublicSpotAdvertisementFreeNetworksEntryHostName OBJECT-TYPE
    SYNTAX     IpAddress
    MAX-ACCESS read-only
    STATUS     current
    DESCRIPTION
            "-- empty --"
    ::= { hmStatusPublicSpotAdvertisementFreeNetworksEntry 1 }

-- {COLUMN} 1.3.6.1.4.1.248.32.18.1.44.10.1.1.2
hmStatusPublicSpotAdvertisementFreeNetworksEntryMask OBJECT-TYPE
    SYNTAX     IpAddress
    MAX-ACCESS read-only
    STATUS     current
    DESCRIPTION
            "-- empty --"
    ::= { hmStatusPublicSpotAdvertisementFreeNetworksEntry 2 }

-- {TABLE} 1.3.6.1.4.1.248.32.18.1.44.10.2
hmStatusPublicSpotAdvertisementFreeHostsTable OBJECT-TYPE
    SYNTAX     SEQUENCE OF HmStatusPublicSpotAdvertisementFreeHostsEntry
    MAX-ACCESS not-accessible
    STATUS     current
    DESCRIPTION
            "-- empty --"
    ::= { hmStatusPublicSpotAdvertisement 2 }

-- {ROW} 1.3.6.1.4.1.248.32.18.1.44.10.2.1
hmStatusPublicSpotAdvertisementFreeHostsEntry OBJECT-TYPE
    SYNTAX     HmStatusPublicSpotAdvertisementFreeHostsEntry
    MAX-ACCESS not-accessible
    STATUS     current
    DESCRIPTION
            ""
    INDEX {
            hmStatusPublicSpotAdvertisementFreeHostsEntryAddress,
            hmStatusPublicSpotAdvertisementFreeHostsEntryHostName,
            hmStatusPublicSpotAdvertisementFreeHostsEntrySource
          }
    ::= { hmStatusPublicSpotAdvertisementFreeHostsTable 1 }

HmStatusPublicSpotAdvertisementFreeHostsEntry ::= SEQUENCE {
            hmStatusPublicSpotAdvertisementFreeHostsEntryAddress IpAddress,
            hmStatusPublicSpotAdvertisementFreeHostsEntryHostName DisplayString,
            hmStatusPublicSpotAdvertisementFreeHostsEntrySource INTEGER,
            hmStatusPublicSpotAdvertisementFreeHostsEntryTtl Integer32,
            hmStatusPublicSpotAdvertisementFreeHostsEntryAge Integer32
    }

-- {COLUMN} 1.3.6.1.4.1.248.32.18.1.44.10.2.1.1
hmStatusPublicSpotAdvertisementFreeHostsEntryAddress OBJECT-TYPE
    SYNTAX     IpAddress
    MAX-ACCESS read-only
    STATUS     current
    DESCRIPTION
            "-- empty --"
    ::= { hmStatusPublicSpotAdvertisementFreeHostsEntry 1 }

-- {COLUMN} 1.3.6.1.4.1.248.32.18.1.44.10.2.1.2
hmStatusPublicSpotAdvertisementFreeHostsEntryHostName OBJECT-TYPE
    SYNTAX     DisplayString (SIZE(0..64))
    MAX-ACCESS read-only
    STATUS     current
    DESCRIPTION
            "-- empty --"
    ::= { hmStatusPublicSpotAdvertisementFreeHostsEntry 2 }

-- {COLUMN} 1.3.6.1.4.1.248.32.18.1.44.10.2.1.3
hmStatusPublicSpotAdvertisementFreeHostsEntrySource OBJECT-TYPE
    SYNTAX     INTEGER {
                  eNone (0),
                  eDynamic (1),
                  eStatic (2)
            }
    MAX-ACCESS read-only
    STATUS     current
    DESCRIPTION
            "-- empty --"
    ::= { hmStatusPublicSpotAdvertisementFreeHostsEntry 3 }

-- {COLUMN} 1.3.6.1.4.1.248.32.18.1.44.10.2.1.4
hmStatusPublicSpotAdvertisementFreeHostsEntryTtl OBJECT-TYPE
    SYNTAX     Integer32 (0..2147483647)
    MAX-ACCESS read-only
    STATUS     current
    DESCRIPTION
            "-- empty --"
    ::= { hmStatusPublicSpotAdvertisementFreeHostsEntry 4 }

-- {COLUMN} 1.3.6.1.4.1.248.32.18.1.44.10.2.1.5
hmStatusPublicSpotAdvertisementFreeHostsEntryAge OBJECT-TYPE
    SYNTAX     Integer32 (0..2147483647)
    MAX-ACCESS read-only
    STATUS     current
    DESCRIPTION
            "-- empty --"
    ::= { hmStatusPublicSpotAdvertisementFreeHostsEntry 5 }

-- {SCALAR} 1.3.6.1.4.1.248.32.18.1.44.11
hmStatusPublicSpotMaxNbUsers OBJECT-TYPE
    SYNTAX     Integer32 (0..2147483647)
    MAX-ACCESS read-only
    STATUS     current
    DESCRIPTION
            "-- empty --"
    ::= { hmStatusPublicSpot 11 }

-- {SCALAR} 1.3.6.1.4.1.248.32.18.1.44.12
hmStatusPublicSpotPbspotAuthenticatedUsers OBJECT-TYPE
    SYNTAX     Integer32 (0..2147483647)
    MAX-ACCESS read-only
    STATUS     current
    DESCRIPTION
            "-- empty --"
    ::= { hmStatusPublicSpot 12 }

-- {SCALAR} 1.3.6.1.4.1.248.32.18.1.44.14
hmStatusPublicSpotPbspotNbVoucher OBJECT-TYPE
    SYNTAX     Integer32 (0..2147483647)
    MAX-ACCESS read-only
    STATUS     current
    DESCRIPTION
            "-- empty --"
    ::= { hmStatusPublicSpot 14 }

-- {TABLE} 1.3.6.1.4.1.248.32.18.1.44.31
hmStatusPublicSpotFreeNetsTable OBJECT-TYPE
    SYNTAX     SEQUENCE OF HmStatusPublicSpotFreeNetsEntry
    MAX-ACCESS not-accessible
    STATUS     current
    DESCRIPTION
            ""
    ::= { hmStatusPublicSpot 31 }

-- {ROW} 1.3.6.1.4.1.248.32.18.1.44.31.1
hmStatusPublicSpotFreeNetsEntry OBJECT-TYPE
    SYNTAX     HmStatusPublicSpotFreeNetsEntry
    MAX-ACCESS not-accessible
    STATUS     current
    DESCRIPTION
            ""
    INDEX {
            hmStatusPublicSpotFreeNetsEntryAddress
          }
    ::= { hmStatusPublicSpotFreeNetsTable 1 }

HmStatusPublicSpotFreeNetsEntry ::= SEQUENCE {
            hmStatusPublicSpotFreeNetsEntryAddress IpAddress,
            hmStatusPublicSpotFreeNetsEntryMask IpAddress,
            hmStatusPublicSpotFreeNetsEntryVlans DisplayString
    }

-- {COLUMN} 1.3.6.1.4.1.248.32.18.1.44.31.1.1
hmStatusPublicSpotFreeNetsEntryAddress OBJECT-TYPE
    SYNTAX     IpAddress
    MAX-ACCESS read-only
    STATUS     current
    DESCRIPTION
            "-- empty --"
    ::= { hmStatusPublicSpotFreeNetsEntry 1 }

-- {COLUMN} 1.3.6.1.4.1.248.32.18.1.44.31.1.2
hmStatusPublicSpotFreeNetsEntryMask OBJECT-TYPE
    SYNTAX     IpAddress
    MAX-ACCESS read-only
    STATUS     current
    DESCRIPTION
            "-- empty --"
    ::= { hmStatusPublicSpotFreeNetsEntry 2 }

-- {COLUMN} 1.3.6.1.4.1.248.32.18.1.44.31.1.3
hmStatusPublicSpotFreeNetsEntryVlans OBJECT-TYPE
    SYNTAX     DisplayString (SIZE(0..254))
    MAX-ACCESS read-only
    STATUS     current
    DESCRIPTION
            "-- empty --"
    ::= { hmStatusPublicSpotFreeNetsEntry 3 }

-- {TABLE} 1.3.6.1.4.1.248.32.18.1.44.32
hmStatusPublicSpotFreeHostsTable OBJECT-TYPE
    SYNTAX     SEQUENCE OF HmStatusPublicSpotFreeHostsEntry
    MAX-ACCESS not-accessible
    STATUS     current
    DESCRIPTION
            "-- empty --"
    ::= { hmStatusPublicSpot 32 }

-- {ROW} 1.3.6.1.4.1.248.32.18.1.44.32.1
hmStatusPublicSpotFreeHostsEntry OBJECT-TYPE
    SYNTAX     HmStatusPublicSpotFreeHostsEntry
    MAX-ACCESS not-accessible
    STATUS     current
    DESCRIPTION
            ""
    INDEX {
            hmStatusPublicSpotFreeHostsEntryAddress,
            hmStatusPublicSpotFreeHostsEntryHostName,
            hmStatusPublicSpotFreeHostsEntrySource
          }
    ::= { hmStatusPublicSpotFreeHostsTable 1 }

HmStatusPublicSpotFreeHostsEntry ::= SEQUENCE {
            hmStatusPublicSpotFreeHostsEntryAddress IpAddress,
            hmStatusPublicSpotFreeHostsEntryHostName DisplayString,
            hmStatusPublicSpotFreeHostsEntrySource INTEGER,
            hmStatusPublicSpotFreeHostsEntryTtl Integer32,
            hmStatusPublicSpotFreeHostsEntryAge Integer32,
            hmStatusPublicSpotFreeHostsEntryVlans DisplayString
    }

-- {COLUMN} 1.3.6.1.4.1.248.32.18.1.44.32.1.1
hmStatusPublicSpotFreeHostsEntryAddress OBJECT-TYPE
    SYNTAX     IpAddress
    MAX-ACCESS read-only
    STATUS     current
    DESCRIPTION
            "-- empty --"
    ::= { hmStatusPublicSpotFreeHostsEntry 1 }

-- {COLUMN} 1.3.6.1.4.1.248.32.18.1.44.32.1.2
hmStatusPublicSpotFreeHostsEntryHostName OBJECT-TYPE
    SYNTAX     DisplayString (SIZE(0..64))
    MAX-ACCESS read-only
    STATUS     current
    DESCRIPTION
            "-- empty --"
    ::= { hmStatusPublicSpotFreeHostsEntry 2 }

-- {COLUMN} 1.3.6.1.4.1.248.32.18.1.44.32.1.3
hmStatusPublicSpotFreeHostsEntrySource OBJECT-TYPE
    SYNTAX     INTEGER {
                  eNone (0),
                  eDynamic (1),
                  eStatic (2)
            }
    MAX-ACCESS read-only
    STATUS     current
    DESCRIPTION
            "-- empty --"
    ::= { hmStatusPublicSpotFreeHostsEntry 3 }

-- {COLUMN} 1.3.6.1.4.1.248.32.18.1.44.32.1.4
hmStatusPublicSpotFreeHostsEntryTtl OBJECT-TYPE
    SYNTAX     Integer32 (0..2147483647)
    MAX-ACCESS read-only
    STATUS     current
    DESCRIPTION
            "-- empty --"
    ::= { hmStatusPublicSpotFreeHostsEntry 4 }

-- {COLUMN} 1.3.6.1.4.1.248.32.18.1.44.32.1.5
hmStatusPublicSpotFreeHostsEntryAge OBJECT-TYPE
    SYNTAX     Integer32 (0..2147483647)
    MAX-ACCESS read-only
    STATUS     current
    DESCRIPTION
            "-- empty --"
    ::= { hmStatusPublicSpotFreeHostsEntry 5 }

-- {COLUMN} 1.3.6.1.4.1.248.32.18.1.44.32.1.6
hmStatusPublicSpotFreeHostsEntryVlans OBJECT-TYPE
    SYNTAX     DisplayString (SIZE(0..254))
    MAX-ACCESS read-only
    STATUS     current
    DESCRIPTION
            "-- empty --"
    ::= { hmStatusPublicSpotFreeHostsEntry 6 }

-- {NODE} 1.3.6.1.4.1.248.32.18.1.46
hmStatusIeee8021x OBJECT IDENTIFIER ::= { hmStatus 46 }

-- {TABLE} 1.3.6.1.4.1.248.32.18.1.46.1
hmStatusIeee8021xStationTableTable OBJECT-TYPE
    SYNTAX     SEQUENCE OF HmStatusIeee8021xStationTableEntry
    MAX-ACCESS not-accessible
    STATUS     current
    DESCRIPTION
            "-- empty --"
    ::= { hmStatusIeee8021x 1 }

-- {ROW} 1.3.6.1.4.1.248.32.18.1.46.1.1
hmStatusIeee8021xStationTableEntry OBJECT-TYPE
    SYNTAX     HmStatusIeee8021xStationTableEntry
    MAX-ACCESS not-accessible
    STATUS     current
    DESCRIPTION
            ""
    INDEX {
            hmStatusIeee8021xStationTableEntryMacAddress
          }
    ::= { hmStatusIeee8021xStationTableTable 1 }

HmStatusIeee8021xStationTableEntry ::= SEQUENCE {
            hmStatusIeee8021xStationTableEntryMacAddress DisplayString,
            hmStatusIeee8021xStationTableEntryAuthIfc DisplayString,
            hmStatusIeee8021xStationTableEntrySessionId DisplayString,
            hmStatusIeee8021xStationTableEntryPortMode INTEGER,
            hmStatusIeee8021xStationTableEntryPortStatus INTEGER,
            hmStatusIeee8021xStationTableEntryUserName DisplayString,
            hmStatusIeee8021xStationTableEntryReplyMsg DisplayString,
            hmStatusIeee8021xStationTableEntryCommIfc DisplayString
    }

-- {COLUMN} 1.3.6.1.4.1.248.32.18.1.46.1.1.1
hmStatusIeee8021xStationTableEntryMacAddress OBJECT-TYPE
    SYNTAX     DisplayString (SIZE(0..12))
    MAX-ACCESS read-only
    STATUS     current
    DESCRIPTION
            "-- empty --"
    ::= { hmStatusIeee8021xStationTableEntry 1 }

-- {COLUMN} 1.3.6.1.4.1.248.32.18.1.46.1.1.2
hmStatusIeee8021xStationTableEntryAuthIfc OBJECT-TYPE
    SYNTAX     DisplayString (SIZE(0..255))
    MAX-ACCESS read-only
    STATUS     current
    DESCRIPTION
            "-- empty --"
    ::= { hmStatusIeee8021xStationTableEntry 2 }

-- {COLUMN} 1.3.6.1.4.1.248.32.18.1.46.1.1.3
hmStatusIeee8021xStationTableEntrySessionId OBJECT-TYPE
    SYNTAX     DisplayString (SIZE(0..8))
    MAX-ACCESS read-only
    STATUS     current
    DESCRIPTION
            "-- empty --"
    ::= { hmStatusIeee8021xStationTableEntry 3 }

-- {COLUMN} 1.3.6.1.4.1.248.32.18.1.46.1.1.4
hmStatusIeee8021xStationTableEntryPortMode OBJECT-TYPE
    SYNTAX     INTEGER {
                  eForceUnauth (0),
                  eForceAuth (1),
                  eAuto (2)
            }
    MAX-ACCESS read-only
    STATUS     current
    DESCRIPTION
            "-- empty --"
    ::= { hmStatusIeee8021xStationTableEntry 4 }

-- {COLUMN} 1.3.6.1.4.1.248.32.18.1.46.1.1.5
hmStatusIeee8021xStationTableEntryPortStatus OBJECT-TYPE
    SYNTAX     INTEGER {
                  eUnauthorized (0),
                  eAuthorized (1)
            }
    MAX-ACCESS read-only
    STATUS     current
    DESCRIPTION
            "-- empty --"
    ::= { hmStatusIeee8021xStationTableEntry 5 }

-- {COLUMN} 1.3.6.1.4.1.248.32.18.1.46.1.1.6
hmStatusIeee8021xStationTableEntryUserName OBJECT-TYPE
    SYNTAX     DisplayString (SIZE(0..255))
    MAX-ACCESS read-only
    STATUS     current
    DESCRIPTION
            "-- empty --"
    ::= { hmStatusIeee8021xStationTableEntry 6 }

-- {COLUMN} 1.3.6.1.4.1.248.32.18.1.46.1.1.7
hmStatusIeee8021xStationTableEntryReplyMsg OBJECT-TYPE
    SYNTAX     DisplayString (SIZE(0..255))
    MAX-ACCESS read-only
    STATUS     current
    DESCRIPTION
            "-- empty --"
    ::= { hmStatusIeee8021xStationTableEntry 7 }

-- {COLUMN} 1.3.6.1.4.1.248.32.18.1.46.1.1.8
hmStatusIeee8021xStationTableEntryCommIfc OBJECT-TYPE
    SYNTAX     DisplayString (SIZE(0..255))
    MAX-ACCESS read-only
    STATUS     current
    DESCRIPTION
            "-- empty --"
    ::= { hmStatusIeee8021xStationTableEntry 8 }

-- {SCALAR} 1.3.6.1.4.1.248.32.18.1.46.2
hmStatusIeee8021xForceReauth OBJECT-TYPE
    SYNTAX     DisplayString
    MAX-ACCESS read-write
    STATUS     current
    DESCRIPTION
            "-- empty --"
    ::= { hmStatusIeee8021x 2 }

-- {TABLE} 1.3.6.1.4.1.248.32.18.1.46.3
hmStatusIeee8021xPortsTable OBJECT-TYPE
    SYNTAX     SEQUENCE OF HmStatusIeee8021xPortsEntry
    MAX-ACCESS not-accessible
    STATUS     current
    DESCRIPTION
            "-- empty --"
    ::= { hmStatusIeee8021x 3 }

-- {ROW} 1.3.6.1.4.1.248.32.18.1.46.3.1
hmStatusIeee8021xPortsEntry OBJECT-TYPE
    SYNTAX     HmStatusIeee8021xPortsEntry
    MAX-ACCESS not-accessible
    STATUS     current
    DESCRIPTION
            ""
    INDEX {
            hmStatusIeee8021xPortsEntryPort
          }
    ::= { hmStatusIeee8021xPortsTable 1 }

HmStatusIeee8021xPortsEntry ::= SEQUENCE {
            hmStatusIeee8021xPortsEntryPort DisplayString,
            hmStatusIeee8021xPortsEntryNumAccept Counter32,
            hmStatusIeee8021xPortsEntryNumReject Counter32,
            hmStatusIeee8021xPortsEntryNumReauthmaxReached Counter32
    }

-- {COLUMN} 1.3.6.1.4.1.248.32.18.1.46.3.1.1
hmStatusIeee8021xPortsEntryPort OBJECT-TYPE
    SYNTAX     DisplayString (SIZE(0..18))
    MAX-ACCESS read-only
    STATUS     current
    DESCRIPTION
            "-- empty --"
    ::= { hmStatusIeee8021xPortsEntry 1 }

-- {COLUMN} 1.3.6.1.4.1.248.32.18.1.46.3.1.2
hmStatusIeee8021xPortsEntryNumAccept OBJECT-TYPE
    SYNTAX     Counter32
    MAX-ACCESS read-only
    STATUS     current
    DESCRIPTION
            "-- empty --"
    ::= { hmStatusIeee8021xPortsEntry 2 }

-- {COLUMN} 1.3.6.1.4.1.248.32.18.1.46.3.1.3
hmStatusIeee8021xPortsEntryNumReject OBJECT-TYPE
    SYNTAX     Counter32
    MAX-ACCESS read-only
    STATUS     current
    DESCRIPTION
            "-- empty --"
    ::= { hmStatusIeee8021xPortsEntry 3 }

-- {COLUMN} 1.3.6.1.4.1.248.32.18.1.46.3.1.4
hmStatusIeee8021xPortsEntryNumReauthmaxReached OBJECT-TYPE
    SYNTAX     Counter32
    MAX-ACCESS read-only
    STATUS     current
    DESCRIPTION
            "-- empty --"
    ::= { hmStatusIeee8021xPortsEntry 4 }

-- {SCALAR} 1.3.6.1.4.1.248.32.18.1.46.99
hmStatusIeee8021xDeleteValues OBJECT-TYPE
    SYNTAX     DisplayString
    MAX-ACCESS read-write
    STATUS     current
    DESCRIPTION
            "-- empty --"
    ::= { hmStatusIeee8021x 99 }

-- {NODE} 1.3.6.1.4.1.248.32.18.1.47
hmStatusHardwareInfo OBJECT IDENTIFIER ::= { hmStatus 47 }

-- {SCALAR} 1.3.6.1.4.1.248.32.18.1.47.1
hmStatusHardwareInfoCpuType OBJECT-TYPE
    SYNTAX     DisplayString (SIZE(0..39))
    MAX-ACCESS read-only
    STATUS     current
    DESCRIPTION
            "-- empty --"
    ::= { hmStatusHardwareInfo 1 }

-- {SCALAR} 1.3.6.1.4.1.248.32.18.1.47.2
hmStatusHardwareInfoCpuClockMhz OBJECT-TYPE
    SYNTAX     Integer32 (0..2147483647)
    MAX-ACCESS read-only
    STATUS     current
    DESCRIPTION
            "-- empty --"
    ::= { hmStatusHardwareInfo 2 }

-- {SCALAR} 1.3.6.1.4.1.248.32.18.1.47.3
hmStatusHardwareInfoCpuLoadPercent OBJECT-TYPE
    SYNTAX     Integer32 (0..255)
    MAX-ACCESS read-only
    STATUS     current
    DESCRIPTION
            "-- empty --"
    ::= { hmStatusHardwareInfo 3 }

-- {SCALAR} 1.3.6.1.4.1.248.32.18.1.47.4
hmStatusHardwareInfoTotalMemoryKbytes OBJECT-TYPE
    SYNTAX     Integer32 (0..2147483647)
    MAX-ACCESS read-only
    STATUS     current
    DESCRIPTION
            "-- empty --"
    ::= { hmStatusHardwareInfo 4 }

-- {SCALAR} 1.3.6.1.4.1.248.32.18.1.47.5
hmStatusHardwareInfoFreeMemoryKbytes OBJECT-TYPE
    SYNTAX     Integer32 (0..2147483647)
    MAX-ACCESS read-only
    STATUS     current
    DESCRIPTION
            "-- empty --"
    ::= { hmStatusHardwareInfo 5 }

-- {SCALAR} 1.3.6.1.4.1.248.32.18.1.47.6
hmStatusHardwareInfoModelNumber OBJECT-TYPE
    SYNTAX     DisplayString (SIZE(0..64))
    MAX-ACCESS read-only
    STATUS     current
    DESCRIPTION
            "-- empty --"
    ::= { hmStatusHardwareInfo 6 }

-- {SCALAR} 1.3.6.1.4.1.248.32.18.1.47.7
hmStatusHardwareInfoSerialNumber OBJECT-TYPE
    SYNTAX     DisplayString (SIZE(0..18))
    MAX-ACCESS read-only
    STATUS     current
    DESCRIPTION
            "-- empty --"
    ::= { hmStatusHardwareInfo 7 }

-- {SCALAR} 1.3.6.1.4.1.248.32.18.1.47.8
hmStatusHardwareInfoBoardRevision OBJECT-TYPE
    SYNTAX     DisplayString (SIZE(0..1))
    MAX-ACCESS read-only
    STATUS     current
    DESCRIPTION
            "-- empty --"
    ::= { hmStatusHardwareInfo 8 }

-- {SCALAR} 1.3.6.1.4.1.248.32.18.1.47.9
hmStatusHardwareInfoSwVersion OBJECT-TYPE
    SYNTAX     DisplayString (SIZE(0..39))
    MAX-ACCESS read-only
    STATUS     current
    DESCRIPTION
            "-- empty --"
    ::= { hmStatusHardwareInfo 9 }

-- {SCALAR} 1.3.6.1.4.1.248.32.18.1.47.10
hmStatusHardwareInfoProductVariant OBJECT-TYPE
    SYNTAX     INTEGER {
               bat54-rail(1),
               bat54-rail-fcc(2),
               bat54-rail-japan(3),
               bat54-f(4),
               bat54-f-fcc(5),
               bat54-f-x2(6),
               bat54-f-x2-fcc(7),
               bat54-rail-client(17),
               bat54-rail-client-fcc(18),
               bat54-rail-client-japan(19),
               bat54-f-client(20),
               bat54-f-client-fcc(21),
               bat54-f-client-x2(22),
               bat54-f-client-x2-fcc(23),
               bat300-rail(33),
               bat300-rail-fcc(34),
               bat300-rail-japan(35),
               bat300-f(36),
               bat300-f-fcc(37),
               bat300-f-x2(38),
               bat300-f-x2-fcc(39),
               bat54-rail-plus(65),
               bat54-rail-plus-fcc(66),
               bat54-rail-plus-japan(67),
               bat54-f-plus(68),
               bat54-f-plus-fcc(69),
               bat54-f-x2-plus(70),
               bat54-f-x2-plus-fcc(71),
               bat54-f-single(72),
               bat54-f-single-fcc(73),
               bat54-f-x2-single(74),
               bat54-f-x2-single-fcc(75),
               bat54-rail-single(76),
               bat54-rail-single-fcc(77),
               bat54-rail-client-plus(81),
               bat54-rail-client-plus-fcc(82),
               bat54-rail-client-plus-japan(83),
               bat54-f-client-plus(84),
               bat54-f-client-plus-ffc(85),
               bat54-f-x2-client-plus(86),
               bat54-f-x2-client-plus-ffc(87),
               bat54-f-single-plus(100),
               bat54-f-single-plus-fcc(101),
               bat54-f-x2-single-plus(102),
               bat54-f-x2-single-plus-fcc(103)            }
    MAX-ACCESS read-only
    STATUS     current
    DESCRIPTION
            "-- empty --"
    ::= { hmStatusHardwareInfo 10 }

-- {SCALAR} 1.3.6.1.4.1.248.32.18.1.47.11
hmStatusHardwareInfoSecurityEngine OBJECT-TYPE
    SYNTAX     INTEGER {
                  eNo (0),
                  eYes (1)
            }
    MAX-ACCESS read-only
    STATUS     current
    DESCRIPTION
            "-- empty --"
    ::= { hmStatusHardwareInfo 11 }

-- {SCALAR} 1.3.6.1.4.1.248.32.18.1.47.12
hmStatusHardwareInfoCpuLoad1sPercent OBJECT-TYPE
    SYNTAX     Integer32 (0..255)
    MAX-ACCESS read-only
    STATUS     current
    DESCRIPTION
            "-- empty --"
    ::= { hmStatusHardwareInfo 12 }

-- {SCALAR} 1.3.6.1.4.1.248.32.18.1.47.13
hmStatusHardwareInfoCpuLoad5sPercent OBJECT-TYPE
    SYNTAX     Integer32 (0..255)
    MAX-ACCESS read-only
    STATUS     current
    DESCRIPTION
            "-- empty --"
    ::= { hmStatusHardwareInfo 13 }

-- {SCALAR} 1.3.6.1.4.1.248.32.18.1.47.14
hmStatusHardwareInfoCpuLoad60sPercent OBJECT-TYPE
    SYNTAX     Integer32 (0..255)
    MAX-ACCESS read-only
    STATUS     current
    DESCRIPTION
            "-- empty --"
    ::= { hmStatusHardwareInfo 14 }

-- {SCALAR} 1.3.6.1.4.1.248.32.18.1.47.15
hmStatusHardwareInfoCpuLoad300sPercent OBJECT-TYPE
    SYNTAX     Integer32 (0..255)
    MAX-ACCESS read-only
    STATUS     current
    DESCRIPTION
            "-- empty --"
    ::= { hmStatusHardwareInfo 15 }

-- {NODE} 1.3.6.1.4.1.248.32.18.1.47.16
hmStatusHardwareInfoSecUnit OBJECT IDENTIFIER ::= { hmStatusHardwareInfo 16 }

-- {TABLE} 1.3.6.1.4.1.248.32.18.1.47.16.1
hmStatusHardwareInfoSecUnitChannelStateTable OBJECT-TYPE
    SYNTAX     SEQUENCE OF HmStatusHardwareInfoSecUnitChannelStateEntry
    MAX-ACCESS not-accessible
    STATUS     current
    DESCRIPTION
            "-- empty --"
    ::= { hmStatusHardwareInfoSecUnit 1 }

-- {ROW} 1.3.6.1.4.1.248.32.18.1.47.16.1.1
hmStatusHardwareInfoSecUnitChannelStateEntry OBJECT-TYPE
    SYNTAX     HmStatusHardwareInfoSecUnitChannelStateEntry
    MAX-ACCESS not-accessible
    STATUS     current
    DESCRIPTION
            ""
    INDEX {
            hmStatusHardwareInfoSecUnitChannelStateEntryChan
          }
    ::= { hmStatusHardwareInfoSecUnitChannelStateTable 1 }

HmStatusHardwareInfoSecUnitChannelStateEntry ::= SEQUENCE {
            hmStatusHardwareInfoSecUnitChannelStateEntryChan Integer32,
            hmStatusHardwareInfoSecUnitChannelStateEntryDone Integer32,
            hmStatusHardwareInfoSecUnitChannelStateEntryErrirq Integer32,
            hmStatusHardwareInfoSecUnitChannelStateEntryOverrun Integer32,
            hmStatusHardwareInfoSecUnitChannelStateEntryDoubleFetch Integer32,
            hmStatusHardwareInfoSecUnitChannelStateEntrySingleFetch Integer32,
            hmStatusHardwareInfoSecUnitChannelStateEntryMasterTranferError Integer32,
            hmStatusHardwareInfoSecUnitChannelStateEntryScatGathDLen Integer32,
            hmStatusHardwareInfoSecUnitChannelStateEntryFetchpointerZero Integer32,
            hmStatusHardwareInfoSecUnitChannelStateEntryIllegalHeader Integer32,
            hmStatusHardwareInfoSecUnitChannelStateEntryIllegalAssign Integer32,
            hmStatusHardwareInfoSecUnitChannelStateEntryExeunit Integer32,
            hmStatusHardwareInfoSecUnitChannelStateEntryGatherBound Integer32,
            hmStatusHardwareInfoSecUnitChannelStateEntryGatherLen Integer32,
            hmStatusHardwareInfoSecUnitChannelStateEntryScatterBound Integer32,
            hmStatusHardwareInfoSecUnitChannelStateEntryScatterLen Integer32,
            hmStatusHardwareInfoSecUnitChannelStateEntryOther Integer32,
            hmStatusHardwareInfoSecUnitChannelStateEntryChannelReset Integer32,
            hmStatusHardwareInfoSecUnitChannelStateEntryQueue Integer32
    }

-- {COLUMN} 1.3.6.1.4.1.248.32.18.1.47.16.1.1.1
hmStatusHardwareInfoSecUnitChannelStateEntryChan OBJECT-TYPE
    SYNTAX     Integer32 (-2147483648..2147483647)
    MAX-ACCESS read-only
    STATUS     current
    DESCRIPTION
            ""
    ::= { hmStatusHardwareInfoSecUnitChannelStateEntry 1 }

-- {COLUMN} 1.3.6.1.4.1.248.32.18.1.47.16.1.1.2
hmStatusHardwareInfoSecUnitChannelStateEntryDone OBJECT-TYPE
    SYNTAX     Integer32 (-2147483648..2147483647)
    MAX-ACCESS read-only
    STATUS     current
    DESCRIPTION
            "-- empty --"
    ::= { hmStatusHardwareInfoSecUnitChannelStateEntry 2 }

-- {COLUMN} 1.3.6.1.4.1.248.32.18.1.47.16.1.1.3
hmStatusHardwareInfoSecUnitChannelStateEntryErrirq OBJECT-TYPE
    SYNTAX     Integer32 (-2147483648..2147483647)
    MAX-ACCESS read-only
    STATUS     current
    DESCRIPTION
            "-- empty --"
    ::= { hmStatusHardwareInfoSecUnitChannelStateEntry 3 }

-- {COLUMN} 1.3.6.1.4.1.248.32.18.1.47.16.1.1.4
hmStatusHardwareInfoSecUnitChannelStateEntryOverrun OBJECT-TYPE
    SYNTAX     Integer32 (-2147483648..2147483647)
    MAX-ACCESS read-only
    STATUS     current
    DESCRIPTION
            "-- empty --"
    ::= { hmStatusHardwareInfoSecUnitChannelStateEntry 4 }

-- {COLUMN} 1.3.6.1.4.1.248.32.18.1.47.16.1.1.5
hmStatusHardwareInfoSecUnitChannelStateEntryDoubleFetch OBJECT-TYPE
    SYNTAX     Integer32 (-2147483648..2147483647)
    MAX-ACCESS read-only
    STATUS     current
    DESCRIPTION
            "-- empty --"
    ::= { hmStatusHardwareInfoSecUnitChannelStateEntry 5 }

-- {COLUMN} 1.3.6.1.4.1.248.32.18.1.47.16.1.1.6
hmStatusHardwareInfoSecUnitChannelStateEntrySingleFetch OBJECT-TYPE
    SYNTAX     Integer32 (-2147483648..2147483647)
    MAX-ACCESS read-only
    STATUS     current
    DESCRIPTION
            "-- empty --"
    ::= { hmStatusHardwareInfoSecUnitChannelStateEntry 6 }

-- {COLUMN} 1.3.6.1.4.1.248.32.18.1.47.16.1.1.7
hmStatusHardwareInfoSecUnitChannelStateEntryMasterTranferError OBJECT-TYPE
    SYNTAX     Integer32 (-2147483648..2147483647)
    MAX-ACCESS read-only
    STATUS     current
    DESCRIPTION
            "-- empty --"
    ::= { hmStatusHardwareInfoSecUnitChannelStateEntry 7 }

-- {COLUMN} 1.3.6.1.4.1.248.32.18.1.47.16.1.1.8
hmStatusHardwareInfoSecUnitChannelStateEntryScatGathDLen OBJECT-TYPE
    SYNTAX     Integer32 (-2147483648..2147483647)
    MAX-ACCESS read-only
    STATUS     current
    DESCRIPTION
            ""
    ::= { hmStatusHardwareInfoSecUnitChannelStateEntry 8 }

-- {COLUMN} 1.3.6.1.4.1.248.32.18.1.47.16.1.1.9
hmStatusHardwareInfoSecUnitChannelStateEntryFetchpointerZero OBJECT-TYPE
    SYNTAX     Integer32 (-2147483648..2147483647)
    MAX-ACCESS read-only
    STATUS     current
    DESCRIPTION
            "-- empty --"
    ::= { hmStatusHardwareInfoSecUnitChannelStateEntry 9 }

-- {COLUMN} 1.3.6.1.4.1.248.32.18.1.47.16.1.1.10
hmStatusHardwareInfoSecUnitChannelStateEntryIllegalHeader OBJECT-TYPE
    SYNTAX     Integer32 (-2147483648..2147483647)
    MAX-ACCESS read-only
    STATUS     current
    DESCRIPTION
            "-- empty --"
    ::= { hmStatusHardwareInfoSecUnitChannelStateEntry 10 }

-- {COLUMN} 1.3.6.1.4.1.248.32.18.1.47.16.1.1.11
hmStatusHardwareInfoSecUnitChannelStateEntryIllegalAssign OBJECT-TYPE
    SYNTAX     Integer32 (-2147483648..2147483647)
    MAX-ACCESS read-only
    STATUS     current
    DESCRIPTION
            "-- empty --"
    ::= { hmStatusHardwareInfoSecUnitChannelStateEntry 11 }

-- {COLUMN} 1.3.6.1.4.1.248.32.18.1.47.16.1.1.12
hmStatusHardwareInfoSecUnitChannelStateEntryExeunit OBJECT-TYPE
    SYNTAX     Integer32 (-2147483648..2147483647)
    MAX-ACCESS read-only
    STATUS     current
    DESCRIPTION
            "-- empty --"
    ::= { hmStatusHardwareInfoSecUnitChannelStateEntry 12 }

-- {COLUMN} 1.3.6.1.4.1.248.32.18.1.47.16.1.1.13
hmStatusHardwareInfoSecUnitChannelStateEntryGatherBound OBJECT-TYPE
    SYNTAX     Integer32 (-2147483648..2147483647)
    MAX-ACCESS read-only
    STATUS     current
    DESCRIPTION
            "-- empty --"
    ::= { hmStatusHardwareInfoSecUnitChannelStateEntry 13 }

-- {COLUMN} 1.3.6.1.4.1.248.32.18.1.47.16.1.1.14
hmStatusHardwareInfoSecUnitChannelStateEntryGatherLen OBJECT-TYPE
    SYNTAX     Integer32 (-2147483648..2147483647)
    MAX-ACCESS read-only
    STATUS     current
    DESCRIPTION
            "-- empty --"
    ::= { hmStatusHardwareInfoSecUnitChannelStateEntry 14 }

-- {COLUMN} 1.3.6.1.4.1.248.32.18.1.47.16.1.1.15
hmStatusHardwareInfoSecUnitChannelStateEntryScatterBound OBJECT-TYPE
    SYNTAX     Integer32 (-2147483648..2147483647)
    MAX-ACCESS read-only
    STATUS     current
    DESCRIPTION
            "-- empty --"
    ::= { hmStatusHardwareInfoSecUnitChannelStateEntry 15 }

-- {COLUMN} 1.3.6.1.4.1.248.32.18.1.47.16.1.1.16
hmStatusHardwareInfoSecUnitChannelStateEntryScatterLen OBJECT-TYPE
    SYNTAX     Integer32 (-2147483648..2147483647)
    MAX-ACCESS read-only
    STATUS     current
    DESCRIPTION
            "-- empty --"
    ::= { hmStatusHardwareInfoSecUnitChannelStateEntry 16 }

-- {COLUMN} 1.3.6.1.4.1.248.32.18.1.47.16.1.1.17
hmStatusHardwareInfoSecUnitChannelStateEntryOther OBJECT-TYPE
    SYNTAX     Integer32 (-2147483648..2147483647)
    MAX-ACCESS read-only
    STATUS     current
    DESCRIPTION
            "-- empty --"
    ::= { hmStatusHardwareInfoSecUnitChannelStateEntry 17 }

-- {COLUMN} 1.3.6.1.4.1.248.32.18.1.47.16.1.1.18
hmStatusHardwareInfoSecUnitChannelStateEntryChannelReset OBJECT-TYPE
    SYNTAX     Integer32 (-2147483648..2147483647)
    MAX-ACCESS read-only
    STATUS     current
    DESCRIPTION
            "-- empty --"
    ::= { hmStatusHardwareInfoSecUnitChannelStateEntry 18 }

-- {COLUMN} 1.3.6.1.4.1.248.32.18.1.47.16.1.1.19
hmStatusHardwareInfoSecUnitChannelStateEntryQueue OBJECT-TYPE
    SYNTAX     Integer32 (-2147483648..2147483647)
    MAX-ACCESS read-only
    STATUS     current
    DESCRIPTION
            "-- empty --"
    ::= { hmStatusHardwareInfoSecUnitChannelStateEntry 19 }

-- {SCALAR} 1.3.6.1.4.1.248.32.18.1.47.16.2
hmStatusHardwareInfoSecUnitDeleteValues OBJECT-TYPE
    SYNTAX     DisplayString
    MAX-ACCESS read-write
    STATUS     current
    DESCRIPTION
            "-- empty --"
    ::= { hmStatusHardwareInfoSecUnit 2 }

-- {SCALAR} 1.3.6.1.4.1.248.32.18.1.47.16.3
hmStatusHardwareInfoSecUnitTestRandomNumbers OBJECT-TYPE
    SYNTAX     DisplayString
    MAX-ACCESS read-write
    STATUS     current
    DESCRIPTION
            "-- empty --"
    ::= { hmStatusHardwareInfoSecUnit 3 }

-- {TABLE} 1.3.6.1.4.1.248.32.18.1.47.16.10
hmStatusHardwareInfoSecUnitLogTableTable OBJECT-TYPE
    SYNTAX     SEQUENCE OF HmStatusHardwareInfoSecUnitLogTableEntry
    MAX-ACCESS not-accessible
    STATUS     current
    DESCRIPTION
            "-- empty --"
    ::= { hmStatusHardwareInfoSecUnit 10 }

-- {ROW} 1.3.6.1.4.1.248.32.18.1.47.16.10.1
hmStatusHardwareInfoSecUnitLogTableEntry OBJECT-TYPE
    SYNTAX     HmStatusHardwareInfoSecUnitLogTableEntry
    MAX-ACCESS not-accessible
    STATUS     current
    DESCRIPTION
            ""
    INDEX {
            hmStatusHardwareInfoSecUnitLogTableEntryIndex
          }
    ::= { hmStatusHardwareInfoSecUnitLogTableTable 1 }

HmStatusHardwareInfoSecUnitLogTableEntry ::= SEQUENCE {
            hmStatusHardwareInfoSecUnitLogTableEntryIndex Integer32,
            hmStatusHardwareInfoSecUnitLogTableEntryTime DisplayString,
            hmStatusHardwareInfoSecUnitLogTableEntryChan Integer32,
            hmStatusHardwareInfoSecUnitLogTableEntryType INTEGER,
            hmStatusHardwareInfoSecUnitLogTableEntryExecutionUnit1 INTEGER,
            hmStatusHardwareInfoSecUnitLogTableEntryExecutionUnit1Isr DisplayString,
            hmStatusHardwareInfoSecUnitLogTableEntryExecutionUnit2 INTEGER,
            hmStatusHardwareInfoSecUnitLogTableEntryExecutionUnit2Isr DisplayString,
            hmStatusHardwareInfoSecUnitLogTableEntryDescriptor DisplayString
    }

-- {COLUMN} 1.3.6.1.4.1.248.32.18.1.47.16.10.1.1
hmStatusHardwareInfoSecUnitLogTableEntryIndex OBJECT-TYPE
    SYNTAX     Integer32 (0..2147483647)
    MAX-ACCESS read-only
    STATUS     current
    DESCRIPTION
            "-- empty --"
    ::= { hmStatusHardwareInfoSecUnitLogTableEntry 1 }

-- {COLUMN} 1.3.6.1.4.1.248.32.18.1.47.16.10.1.2
hmStatusHardwareInfoSecUnitLogTableEntryTime OBJECT-TYPE
    SYNTAX     DisplayString (SIZE(0..19))
    MAX-ACCESS read-only
    STATUS     current
    DESCRIPTION
            "-- empty --"
    ::= { hmStatusHardwareInfoSecUnitLogTableEntry 2 }

-- {COLUMN} 1.3.6.1.4.1.248.32.18.1.47.16.10.1.3
hmStatusHardwareInfoSecUnitLogTableEntryChan OBJECT-TYPE
    SYNTAX     Integer32 (0..2147483647)
    MAX-ACCESS read-only
    STATUS     current
    DESCRIPTION
            ""
    ::= { hmStatusHardwareInfoSecUnitLogTableEntry 3 }

-- {COLUMN} 1.3.6.1.4.1.248.32.18.1.47.16.10.1.4
hmStatusHardwareInfoSecUnitLogTableEntryType OBJECT-TYPE
    SYNTAX     INTEGER {
                  eUnknown (0),
                  eDoubleFetchFifoWriteOverflow (1),
                  eSingleFetchFifoWriteOverflow (2),
                  eMasterDataTransferError (3),
                  eScatterGatherDataLengthZero (4),
                  eFetchPointerZero (5),
                  eIllegalDescriptorHeader (6),
                  eInvalidEuAssignment (7),
                  eEuError (8),
                  eGatherBoundaryError (9),
                  eGatherReturnLengthError (10),
                  eScatterBoundaryError (11),
                  eScatterReturnLengthError (12),
                  eOverflow (13)
            }
    MAX-ACCESS read-only
    STATUS     current
    DESCRIPTION
            "-- empty --"
    ::= { hmStatusHardwareInfoSecUnitLogTableEntry 4 }

-- {COLUMN} 1.3.6.1.4.1.248.32.18.1.47.16.10.1.5
hmStatusHardwareInfoSecUnitLogTableEntryExecutionUnit1 OBJECT-TYPE
    SYNTAX     INTEGER {
                  eNotSet (0),
                  eAfeu (1),
                  eDeu (2),
                  eMdeua (3),
                  eRng (4),
                  ePkeu (5),
                  eAesu (6),
                  eKeu (7),
                  eMdeub (11)
            }
    MAX-ACCESS read-only
    STATUS     current
    DESCRIPTION
            "-- empty --"
    ::= { hmStatusHardwareInfoSecUnitLogTableEntry 5 }

-- {COLUMN} 1.3.6.1.4.1.248.32.18.1.47.16.10.1.6
hmStatusHardwareInfoSecUnitLogTableEntryExecutionUnit1Isr OBJECT-TYPE
    SYNTAX     DisplayString (SIZE(0..21))
    MAX-ACCESS read-only
    STATUS     current
    DESCRIPTION
            "-- empty --"
    ::= { hmStatusHardwareInfoSecUnitLogTableEntry 6 }

-- {COLUMN} 1.3.6.1.4.1.248.32.18.1.47.16.10.1.7
hmStatusHardwareInfoSecUnitLogTableEntryExecutionUnit2 OBJECT-TYPE
    SYNTAX     INTEGER {
                  eNotSet (0),
                  eAfeu (1),
                  eDeu (2),
                  eMdeua (3),
                  eRng (4),
                  ePkeu (5),
                  eAesu (6),
                  eKeu (7),
                  eMdeub (11)
            }
    MAX-ACCESS read-only
    STATUS     current
    DESCRIPTION
            "-- empty --"
    ::= { hmStatusHardwareInfoSecUnitLogTableEntry 7 }

-- {COLUMN} 1.3.6.1.4.1.248.32.18.1.47.16.10.1.8
hmStatusHardwareInfoSecUnitLogTableEntryExecutionUnit2Isr OBJECT-TYPE
    SYNTAX     DisplayString (SIZE(0..21))
    MAX-ACCESS read-only
    STATUS     current
    DESCRIPTION
            "-- empty --"
    ::= { hmStatusHardwareInfoSecUnitLogTableEntry 8 }

-- {COLUMN} 1.3.6.1.4.1.248.32.18.1.47.16.10.1.9
hmStatusHardwareInfoSecUnitLogTableEntryDescriptor OBJECT-TYPE
    SYNTAX     DisplayString (SIZE(0..145))
    MAX-ACCESS read-only
    STATUS     current
    DESCRIPTION
            "-- empty --"
    ::= { hmStatusHardwareInfoSecUnitLogTableEntry 9 }

-- {SCALAR} 1.3.6.1.4.1.248.32.18.1.47.20
hmStatusHardwareInfoTemperatureDegrees OBJECT-TYPE
    SYNTAX     Integer32 (-32768..32767)
    MAX-ACCESS read-only
    STATUS     current
    DESCRIPTION
            "-- empty --"
    ::= { hmStatusHardwareInfo 20 }

-- {TABLE} 1.3.6.1.4.1.248.32.18.1.47.30
hmStatusHardwareInfoPciDeviceListTable OBJECT-TYPE
    SYNTAX     SEQUENCE OF HmStatusHardwareInfoPciDeviceListEntry
    MAX-ACCESS not-accessible
    STATUS     current
    DESCRIPTION
            "-- empty --"
    ::= { hmStatusHardwareInfo 30 }

-- {ROW} 1.3.6.1.4.1.248.32.18.1.47.30.1
hmStatusHardwareInfoPciDeviceListEntry OBJECT-TYPE
    SYNTAX     HmStatusHardwareInfoPciDeviceListEntry
    MAX-ACCESS not-accessible
    STATUS     current
    DESCRIPTION
            ""
    INDEX {
            hmStatusHardwareInfoPciDeviceListEntryHostBridge,
            hmStatusHardwareInfoPciDeviceListEntryBus,
            hmStatusHardwareInfoPciDeviceListEntryDevice,
            hmStatusHardwareInfoPciDeviceListEntryFunction
          }
    ::= { hmStatusHardwareInfoPciDeviceListTable 1 }

HmStatusHardwareInfoPciDeviceListEntry ::= SEQUENCE {
            hmStatusHardwareInfoPciDeviceListEntryHostBridge Integer32,
            hmStatusHardwareInfoPciDeviceListEntryBus Integer32,
            hmStatusHardwareInfoPciDeviceListEntryDevice Integer32,
            hmStatusHardwareInfoPciDeviceListEntryFunction Integer32,
            hmStatusHardwareInfoPciDeviceListEntryDeviceId DisplayString,
            hmStatusHardwareInfoPciDeviceListEntrySubsystemId DisplayString,
            hmStatusHardwareInfoPciDeviceListEntryClass INTEGER,
            hmStatusHardwareInfoPciDeviceListEntryType INTEGER,
            hmStatusHardwareInfoPciDeviceListEntryInterruptCount Counter64
    }

-- {COLUMN} 1.3.6.1.4.1.248.32.18.1.47.30.1.1
hmStatusHardwareInfoPciDeviceListEntryHostBridge OBJECT-TYPE
    SYNTAX     Integer32 (0..2147483647)
    MAX-ACCESS read-only
    STATUS     current
    DESCRIPTION
            "-- empty --"
    ::= { hmStatusHardwareInfoPciDeviceListEntry 1 }

-- {COLUMN} 1.3.6.1.4.1.248.32.18.1.47.30.1.2
hmStatusHardwareInfoPciDeviceListEntryBus OBJECT-TYPE
    SYNTAX     Integer32 (0..2147483647)
    MAX-ACCESS read-only
    STATUS     current
    DESCRIPTION
            "-- empty --"
    ::= { hmStatusHardwareInfoPciDeviceListEntry 2 }

-- {COLUMN} 1.3.6.1.4.1.248.32.18.1.47.30.1.3
hmStatusHardwareInfoPciDeviceListEntryDevice OBJECT-TYPE
    SYNTAX     Integer32 (0..2147483647)
    MAX-ACCESS read-only
    STATUS     current
    DESCRIPTION
            "-- empty --"
    ::= { hmStatusHardwareInfoPciDeviceListEntry 3 }

-- {COLUMN} 1.3.6.1.4.1.248.32.18.1.47.30.1.4
hmStatusHardwareInfoPciDeviceListEntryFunction OBJECT-TYPE
    SYNTAX     Integer32 (0..2147483647)
    MAX-ACCESS read-only
    STATUS     current
    DESCRIPTION
            "-- empty --"
    ::= { hmStatusHardwareInfoPciDeviceListEntry 4 }

-- {COLUMN} 1.3.6.1.4.1.248.32.18.1.47.30.1.5
hmStatusHardwareInfoPciDeviceListEntryDeviceId OBJECT-TYPE
    SYNTAX     DisplayString (SIZE(0..255))
    MAX-ACCESS read-only
    STATUS     current
    DESCRIPTION
            "-- empty --"
    ::= { hmStatusHardwareInfoPciDeviceListEntry 5 }

-- {COLUMN} 1.3.6.1.4.1.248.32.18.1.47.30.1.6
hmStatusHardwareInfoPciDeviceListEntrySubsystemId OBJECT-TYPE
    SYNTAX     DisplayString (SIZE(0..255))
    MAX-ACCESS read-only
    STATUS     current
    DESCRIPTION
            "-- empty --"
    ::= { hmStatusHardwareInfoPciDeviceListEntry 6 }

-- {COLUMN} 1.3.6.1.4.1.248.32.18.1.47.30.1.7
hmStatusHardwareInfoPciDeviceListEntryClass OBJECT-TYPE
    SYNTAX     INTEGER {
                  eEthernet (131072),
                  eTokenRing (131328),
                  eNetwork (163840),
                  eAudio (262400),
                  eIsaBridge (393472),
                  ePciBridge (394240),
                  ePciBridgeSubtractive (394241),
                  eCardbusBridge (395008),
                  eUart16550 (458754),
                  eUart16950 (458758),
                  eCommunication (491520),
                  ePowerpc (729088),
                  eOhci1394 (786448),
                  eUsbUhci (787200),
                  eUsbOhci (787216),
                  eUsbEhci (787232)
            }
    MAX-ACCESS read-only
    STATUS     current
    DESCRIPTION
            "-- empty --"
    ::= { hmStatusHardwareInfoPciDeviceListEntry 7 }

-- {COLUMN} 1.3.6.1.4.1.248.32.18.1.47.30.1.8
hmStatusHardwareInfoPciDeviceListEntryType OBJECT-TYPE
    SYNTAX     INTEGER {
                  ePci (0),
                  ePcie (1)
            }
    MAX-ACCESS read-only
    STATUS     current
    DESCRIPTION
            "-- empty --"
    ::= { hmStatusHardwareInfoPciDeviceListEntry 8 }

-- {COLUMN} 1.3.6.1.4.1.248.32.18.1.47.30.1.9
hmStatusHardwareInfoPciDeviceListEntryInterruptCount OBJECT-TYPE
    SYNTAX     Counter64
    MAX-ACCESS read-only
    STATUS     current
    DESCRIPTION
            "-- empty --"
    ::= { hmStatusHardwareInfoPciDeviceListEntry 9 }

-- {TABLE} 1.3.6.1.4.1.248.32.18.1.47.32
hmStatusHardwareInfoAdvErrorReportingLogTable OBJECT-TYPE
    SYNTAX     SEQUENCE OF HmStatusHardwareInfoAdvErrorReportingLogEntry
    MAX-ACCESS not-accessible
    STATUS     current
    DESCRIPTION
            "-- empty --"
    ::= { hmStatusHardwareInfo 32 }

-- {ROW} 1.3.6.1.4.1.248.32.18.1.47.32.1
hmStatusHardwareInfoAdvErrorReportingLogEntry OBJECT-TYPE
    SYNTAX     HmStatusHardwareInfoAdvErrorReportingLogEntry
    MAX-ACCESS not-accessible
    STATUS     current
    DESCRIPTION
            ""
    INDEX {
            hmStatusHardwareInfoAdvErrorReportingLogEntryIndex
          }
    ::= { hmStatusHardwareInfoAdvErrorReportingLogTable 1 }

HmStatusHardwareInfoAdvErrorReportingLogEntry ::= SEQUENCE {
            hmStatusHardwareInfoAdvErrorReportingLogEntryIndex Integer32,
            hmStatusHardwareInfoAdvErrorReportingLogEntryTime DisplayString,
            hmStatusHardwareInfoAdvErrorReportingLogEntrySeverity INTEGER,
            hmStatusHardwareInfoAdvErrorReportingLogEntryMultiple INTEGER,
            hmStatusHardwareInfoAdvErrorReportingLogEntrySource Integer32,
            hmStatusHardwareInfoAdvErrorReportingLogEntryLayer INTEGER,
            hmStatusHardwareInfoAdvErrorReportingLogEntryEvent DisplayString
    }

-- {COLUMN} 1.3.6.1.4.1.248.32.18.1.47.32.1.1
hmStatusHardwareInfoAdvErrorReportingLogEntryIndex OBJECT-TYPE
    SYNTAX     Integer32 (0..2147483647)
    MAX-ACCESS read-only
    STATUS     current
    DESCRIPTION
            "-- empty --"
    ::= { hmStatusHardwareInfoAdvErrorReportingLogEntry 1 }

-- {COLUMN} 1.3.6.1.4.1.248.32.18.1.47.32.1.2
hmStatusHardwareInfoAdvErrorReportingLogEntryTime OBJECT-TYPE
    SYNTAX     DisplayString (SIZE(0..19))
    MAX-ACCESS read-only
    STATUS     current
    DESCRIPTION
            "-- empty --"
    ::= { hmStatusHardwareInfoAdvErrorReportingLogEntry 2 }

-- {COLUMN} 1.3.6.1.4.1.248.32.18.1.47.32.1.3
hmStatusHardwareInfoAdvErrorReportingLogEntrySeverity OBJECT-TYPE
    SYNTAX     INTEGER {
                  eCorrectable (0),
                  eUncorrectableNonFatal (1),
                  eUncorrectableFatal (2)
            }
    MAX-ACCESS read-only
    STATUS     current
    DESCRIPTION
            "-- empty --"
    ::= { hmStatusHardwareInfoAdvErrorReportingLogEntry 3 }

-- {COLUMN} 1.3.6.1.4.1.248.32.18.1.47.32.1.4
hmStatusHardwareInfoAdvErrorReportingLogEntryMultiple OBJECT-TYPE
    SYNTAX     INTEGER {
                  eNo (0),
                  eYes (1)
            }
    MAX-ACCESS read-only
    STATUS     current
    DESCRIPTION
            "-- empty --"
    ::= { hmStatusHardwareInfoAdvErrorReportingLogEntry 4 }

-- {COLUMN} 1.3.6.1.4.1.248.32.18.1.47.32.1.5
hmStatusHardwareInfoAdvErrorReportingLogEntrySource OBJECT-TYPE
    SYNTAX     Integer32 (0..65535)
    MAX-ACCESS read-only
    STATUS     current
    DESCRIPTION
            "-- empty --"
    ::= { hmStatusHardwareInfoAdvErrorReportingLogEntry 5 }

-- {COLUMN} 1.3.6.1.4.1.248.32.18.1.47.32.1.6
hmStatusHardwareInfoAdvErrorReportingLogEntryLayer OBJECT-TYPE
    SYNTAX     INTEGER {
                  eUnknown (0),
                  ePhysical (1),
                  eDataLink (2),
                  eTransaction (3)
            }
    MAX-ACCESS read-only
    STATUS     current
    DESCRIPTION
            "-- empty --"
    ::= { hmStatusHardwareInfoAdvErrorReportingLogEntry 6 }

-- {COLUMN} 1.3.6.1.4.1.248.32.18.1.47.32.1.7
hmStatusHardwareInfoAdvErrorReportingLogEntryEvent OBJECT-TYPE
    SYNTAX     DisplayString (SIZE(0..251))
    MAX-ACCESS read-only
    STATUS     current
    DESCRIPTION
            "-- empty --"
    ::= { hmStatusHardwareInfoAdvErrorReportingLogEntry 7 }

-- {SCALAR} 1.3.6.1.4.1.248.32.18.1.47.36
hmStatusHardwareInfoPcieCorrErrors OBJECT-TYPE
    SYNTAX     Integer32 (0..2147483647)
    MAX-ACCESS read-only
    STATUS     current
    DESCRIPTION
            "-- empty --"
    ::= { hmStatusHardwareInfo 36 }

-- {SCALAR} 1.3.6.1.4.1.248.32.18.1.47.37
hmStatusHardwareInfoPcieUncorrErrors OBJECT-TYPE
    SYNTAX     Integer32 (0..2147483647)
    MAX-ACCESS read-only
    STATUS     current
    DESCRIPTION
            "-- empty --"
    ::= { hmStatusHardwareInfo 37 }

-- {SCALAR} 1.3.6.1.4.1.248.32.18.1.47.38
hmStatusHardwareInfoPcieLinkResets OBJECT-TYPE
    SYNTAX     Integer32 (0..2147483647)
    MAX-ACCESS read-only
    STATUS     current
    DESCRIPTION
            "-- empty --"
    ::= { hmStatusHardwareInfo 38 }

-- {SCALAR} 1.3.6.1.4.1.248.32.18.1.47.39
hmStatusHardwareInfoExtendedName OBJECT-TYPE
    SYNTAX     DisplayString (SIZE(0..127))
    MAX-ACCESS read-only
    STATUS     current
    DESCRIPTION
            "-- empty --"
    ::= { hmStatusHardwareInfo 39 }

-- {SCALAR} 1.3.6.1.4.1.248.32.18.1.47.40
hmStatusHardwareInfoModLevel OBJECT-TYPE
    SYNTAX     DisplayString (SIZE(0..32))
    MAX-ACCESS read-only
    STATUS     current
    DESCRIPTION
            "-- empty --"
    ::= { hmStatusHardwareInfo 40 }

-- {SCALAR} 1.3.6.1.4.1.248.32.18.1.47.41
hmStatusHardwareInfoProductionDate OBJECT-TYPE
    SYNTAX     DisplayString (SIZE(0..10))
    MAX-ACCESS read-only
    STATUS     current
    DESCRIPTION
            "-- empty --"
    ::= { hmStatusHardwareInfo 41 }

-- {TABLE} 1.3.6.1.4.1.248.32.18.1.47.42
hmStatusHardwareInfoEccErrorReportingTable OBJECT-TYPE
    SYNTAX     SEQUENCE OF HmStatusHardwareInfoEccErrorReportingEntry
    MAX-ACCESS not-accessible
    STATUS     current
    DESCRIPTION
            "-- empty --"
    ::= { hmStatusHardwareInfo 42 }

-- {ROW} 1.3.6.1.4.1.248.32.18.1.47.42.1
hmStatusHardwareInfoEccErrorReportingEntry OBJECT-TYPE
    SYNTAX     HmStatusHardwareInfoEccErrorReportingEntry
    MAX-ACCESS not-accessible
    STATUS     current
    DESCRIPTION
            ""
    INDEX {
            hmStatusHardwareInfoEccErrorReportingEntryIndex
          }
    ::= { hmStatusHardwareInfoEccErrorReportingTable 1 }

HmStatusHardwareInfoEccErrorReportingEntry ::= SEQUENCE {
            hmStatusHardwareInfoEccErrorReportingEntryIndex Integer32,
            hmStatusHardwareInfoEccErrorReportingEntryTime DisplayString,
            hmStatusHardwareInfoEccErrorReportingEntryEvent DisplayString
    }

-- {COLUMN} 1.3.6.1.4.1.248.32.18.1.47.42.1.1
hmStatusHardwareInfoEccErrorReportingEntryIndex OBJECT-TYPE
    SYNTAX     Integer32 (0..2147483647)
    MAX-ACCESS read-only
    STATUS     current
    DESCRIPTION
            "-- empty --"
    ::= { hmStatusHardwareInfoEccErrorReportingEntry 1 }

-- {COLUMN} 1.3.6.1.4.1.248.32.18.1.47.42.1.2
hmStatusHardwareInfoEccErrorReportingEntryTime OBJECT-TYPE
    SYNTAX     DisplayString (SIZE(0..19))
    MAX-ACCESS read-only
    STATUS     current
    DESCRIPTION
            "-- empty --"
    ::= { hmStatusHardwareInfoEccErrorReportingEntry 2 }

-- {COLUMN} 1.3.6.1.4.1.248.32.18.1.47.42.1.3
hmStatusHardwareInfoEccErrorReportingEntryEvent OBJECT-TYPE
    SYNTAX     DisplayString (SIZE(0..251))
    MAX-ACCESS read-only
    STATUS     current
    DESCRIPTION
            "-- empty --"
    ::= { hmStatusHardwareInfoEccErrorReportingEntry 3 }

-- {SCALAR} 1.3.6.1.4.1.248.32.18.1.47.43
hmStatusHardwareInfoProductCode OBJECT-TYPE
    SYNTAX     DisplayString (SIZE(0..42))
    MAX-ACCESS read-only
    STATUS     current
    DESCRIPTION
            "-- empty --"
    ::= { hmStatusHardwareInfo 43 }

-- {SCALAR} 1.3.6.1.4.1.248.32.18.1.47.44
hmStatusHardwareInfoPldVersion OBJECT-TYPE
    SYNTAX     DisplayString (SIZE(0..7))
    MAX-ACCESS read-only
    STATUS     current
    DESCRIPTION
            "-- empty --"
    ::= { hmStatusHardwareInfo 44 }

-- {SCALAR} 1.3.6.1.4.1.248.32.18.1.47.45
hmStatusHardwareInfoResetButtonState OBJECT-TYPE
    SYNTAX     INTEGER {
                  eInactive (0),
                  eActive (1)
            }
    MAX-ACCESS read-only
    STATUS     current
    DESCRIPTION
            "-- empty --"
    ::= { hmStatusHardwareInfo 45 }

-- {TABLE} 1.3.6.1.4.1.248.32.18.1.47.248
hmStatusHardwareInfoPowerSuppliesTable OBJECT-TYPE
    SYNTAX     SEQUENCE OF HmStatusHardwareInfoPowerSuppliesEntry
    MAX-ACCESS not-accessible
    STATUS     current
    DESCRIPTION
            "-- empty --"
    ::= { hmStatusHardwareInfo 248 }

-- {ROW} 1.3.6.1.4.1.248.32.18.1.47.248.1
hmStatusHardwareInfoPowerSuppliesEntry OBJECT-TYPE
    SYNTAX     HmStatusHardwareInfoPowerSuppliesEntry
    MAX-ACCESS not-accessible
    STATUS     current
    DESCRIPTION
            ""
    INDEX {
            hmStatusHardwareInfoPowerSuppliesEntryPowerSupply
          }
    ::= { hmStatusHardwareInfoPowerSuppliesTable 1 }

HmStatusHardwareInfoPowerSuppliesEntry ::= SEQUENCE {
            hmStatusHardwareInfoPowerSuppliesEntryPowerSupply DisplayString,
            hmStatusHardwareInfoPowerSuppliesEntryStatus DisplayString
    }

-- {COLUMN} 1.3.6.1.4.1.248.32.18.1.47.248.1.1
hmStatusHardwareInfoPowerSuppliesEntryPowerSupply OBJECT-TYPE
    SYNTAX     DisplayString (SIZE(0..4))
    MAX-ACCESS read-only
    STATUS     current
    DESCRIPTION
            "-- empty --"
    ::= { hmStatusHardwareInfoPowerSuppliesEntry 1 }

-- {COLUMN} 1.3.6.1.4.1.248.32.18.1.47.248.1.2
hmStatusHardwareInfoPowerSuppliesEntryStatus OBJECT-TYPE
    SYNTAX     DisplayString (SIZE(0..255))
    MAX-ACCESS read-only
    STATUS     current
    DESCRIPTION
            "-- empty --"
    ::= { hmStatusHardwareInfoPowerSuppliesEntry 2 }

-- {TABLE} 1.3.6.1.4.1.248.32.18.1.48
hmStatusChannelTable OBJECT-TYPE
    SYNTAX     SEQUENCE OF HmStatusChannelEntry
    MAX-ACCESS not-accessible
    STATUS     current
    DESCRIPTION
            "-- empty --"
    ::= { hmStatus 48 }

-- {ROW} 1.3.6.1.4.1.248.32.18.1.48.1
hmStatusChannelEntry OBJECT-TYPE
    SYNTAX     HmStatusChannelEntry
    MAX-ACCESS not-accessible
    STATUS     current
    DESCRIPTION
            ""
    INDEX {
            hmStatusChannelEntryChan
          }
    ::= { hmStatusChannelTable 1 }

HmStatusChannelEntry ::= SEQUENCE {
            hmStatusChannelEntryChan INTEGER,
            hmStatusChannelEntryPlci Integer32,
            hmStatusChannelEntryBus Integer32,
            hmStatusChannelEntryState Integer32,
            hmStatusChannelEntryApp INTEGER,
            hmStatusChannelEntryMode INTEGER,
            hmStatusChannelEntryCause Integer32,
            hmStatusChannelEntryNumber DisplayString,
            hmStatusChannelEntryCharge Integer32,
            hmStatusChannelEntryExtra DisplayString,
            hmStatusChannelEntryConnTime Integer32,
            hmStatusChannelEntryConnStart Integer32,
            hmStatusChannelEntryIsdnDisplay DisplayString,
            hmStatusChannelEntryPhChan Integer32,
            hmStatusChannelEntryPptpConns Integer32,
            hmStatusChannelEntryVpnConns Integer32,
            hmStatusChannelEntrySubaddress Integer32
    }

-- {COLUMN} 1.3.6.1.4.1.248.32.18.1.48.1.1
hmStatusChannelEntryChan OBJECT-TYPE
    SYNTAX     INTEGER {
                  eDslErr (257),
                  eDslCh1 (258),
                  eDslCh2 (259),
                  eDslCh3 (260),
                  eDslCh4 (261),
                  eDslCh5 (262),
                  eDslCh6 (263),
                  eDslCh7 (264),
                  eDslCh8 (265),
                  eExtErr (1281),
                  eExt (1282)
            }
    MAX-ACCESS read-only
    STATUS     current
    DESCRIPTION
            "-- empty --"
    ::= { hmStatusChannelEntry 1 }

-- {COLUMN} 1.3.6.1.4.1.248.32.18.1.48.1.2
hmStatusChannelEntryPlci OBJECT-TYPE
    SYNTAX     Integer32 (0..2147483647)
    MAX-ACCESS read-only
    STATUS     current
    DESCRIPTION
            "-- empty --"
    ::= { hmStatusChannelEntry 2 }

-- {COLUMN} 1.3.6.1.4.1.248.32.18.1.48.1.3
hmStatusChannelEntryBus OBJECT-TYPE
    SYNTAX     Integer32 (0..2147483647)
    MAX-ACCESS read-only
    STATUS     current
    DESCRIPTION
            "-- empty --"
    ::= { hmStatusChannelEntry 3 }

-- {COLUMN} 1.3.6.1.4.1.248.32.18.1.48.1.4
hmStatusChannelEntryState OBJECT-TYPE
    SYNTAX     Integer32 (0..2147483647)
    MAX-ACCESS read-only
    STATUS     current
    DESCRIPTION
            "-- empty --"
    ::= { hmStatusChannelEntry 4 }

-- {COLUMN} 1.3.6.1.4.1.248.32.18.1.48.1.5
hmStatusChannelEntryApp OBJECT-TYPE
    SYNTAX     INTEGER {
                  eNone (0),
                  eRouter (1),
                  eCapi (2),
                  eAB (3),
                  eTimeModule (255)
            }
    MAX-ACCESS read-only
    STATUS     current
    DESCRIPTION
            "-- empty --"
    ::= { hmStatusChannelEntry 5 }

-- {COLUMN} 1.3.6.1.4.1.248.32.18.1.48.1.6
hmStatusChannelEntryMode OBJECT-TYPE
    SYNTAX     INTEGER {
                  eUnk (0),
                  eAct (1),
                  ePas (2),
                  ePerm (3)
            }
    MAX-ACCESS read-only
    STATUS     current
    DESCRIPTION
            "-- empty --"
    ::= { hmStatusChannelEntry 6 }

-- {COLUMN} 1.3.6.1.4.1.248.32.18.1.48.1.7
hmStatusChannelEntryCause OBJECT-TYPE
    SYNTAX     Integer32 (0..65535)
    MAX-ACCESS read-write
    STATUS     current
    DESCRIPTION
            "-- empty --"
    ::= { hmStatusChannelEntry 7 }

-- {COLUMN} 1.3.6.1.4.1.248.32.18.1.48.1.8
hmStatusChannelEntryNumber OBJECT-TYPE
    SYNTAX     DisplayString (SIZE(0..40))
    MAX-ACCESS read-only
    STATUS     current
    DESCRIPTION
            "-- empty --"
    ::= { hmStatusChannelEntry 8 }

-- {COLUMN} 1.3.6.1.4.1.248.32.18.1.48.1.10
hmStatusChannelEntryCharge OBJECT-TYPE
    SYNTAX     Integer32 (0..2147483647)
    MAX-ACCESS read-only
    STATUS     current
    DESCRIPTION
            "-- empty --"
    ::= { hmStatusChannelEntry 10 }

-- {COLUMN} 1.3.6.1.4.1.248.32.18.1.48.1.11
hmStatusChannelEntryExtra OBJECT-TYPE
    SYNTAX     DisplayString (SIZE(0..16))
    MAX-ACCESS read-only
    STATUS     current
    DESCRIPTION
            "-- empty --"
    ::= { hmStatusChannelEntry 11 }

-- {COLUMN} 1.3.6.1.4.1.248.32.18.1.48.1.12
hmStatusChannelEntryConnTime OBJECT-TYPE
    SYNTAX     Integer32 (0..2147483647)
    MAX-ACCESS read-only
    STATUS     current
    DESCRIPTION
            "-- empty --"
    ::= { hmStatusChannelEntry 12 }

-- {COLUMN} 1.3.6.1.4.1.248.32.18.1.48.1.13
hmStatusChannelEntryConnStart OBJECT-TYPE
    SYNTAX     Integer32 (0..2147483647)
    MAX-ACCESS read-only
    STATUS     current
    DESCRIPTION
            "-- empty --"
    ::= { hmStatusChannelEntry 13 }

-- {COLUMN} 1.3.6.1.4.1.248.32.18.1.48.1.14
hmStatusChannelEntryIsdnDisplay OBJECT-TYPE
    SYNTAX     DisplayString (SIZE(0..34))
    MAX-ACCESS read-only
    STATUS     current
    DESCRIPTION
            "-- empty --"
    ::= { hmStatusChannelEntry 14 }

-- {COLUMN} 1.3.6.1.4.1.248.32.18.1.48.1.15
hmStatusChannelEntryPhChan OBJECT-TYPE
    SYNTAX     Integer32 (0..2147483647)
    MAX-ACCESS read-only
    STATUS     current
    DESCRIPTION
            "-- empty --"
    ::= { hmStatusChannelEntry 15 }

-- {COLUMN} 1.3.6.1.4.1.248.32.18.1.48.1.16
hmStatusChannelEntryPptpConns OBJECT-TYPE
    SYNTAX     Integer32 (0..2147483647)
    MAX-ACCESS read-only
    STATUS     current
    DESCRIPTION
            "-- empty --"
    ::= { hmStatusChannelEntry 16 }

-- {COLUMN} 1.3.6.1.4.1.248.32.18.1.48.1.17
hmStatusChannelEntryVpnConns OBJECT-TYPE
    SYNTAX     Integer32 (0..2147483647)
    MAX-ACCESS read-only
    STATUS     current
    DESCRIPTION
            "-- empty --"
    ::= { hmStatusChannelEntry 17 }

-- {COLUMN} 1.3.6.1.4.1.248.32.18.1.48.1.18
hmStatusChannelEntrySubaddress OBJECT-TYPE
    SYNTAX     Integer32 (0..2147483647)
    MAX-ACCESS read-only
    STATUS     current
    DESCRIPTION
            "-- empty --"
    ::= { hmStatusChannelEntry 18 }

-- {NODE} 1.3.6.1.4.1.248.32.18.1.49
hmStatusModemMobile OBJECT IDENTIFIER ::= { hmStatus 49 }

-- {SCALAR} 1.3.6.1.4.1.248.32.18.1.49.1
hmStatusModemMobileModemInfo OBJECT-TYPE
    SYNTAX     DisplayString (SIZE(0..255))
    MAX-ACCESS read-only
    STATUS     current
    DESCRIPTION
            "-- empty --"
    ::= { hmStatusModemMobile 1 }

-- {SCALAR} 1.3.6.1.4.1.248.32.18.1.49.2
hmStatusModemMobileConnectInfo OBJECT-TYPE
    SYNTAX     DisplayString (SIZE(0..63))
    MAX-ACCESS read-only
    STATUS     current
    DESCRIPTION
            "-- empty --"
    ::= { hmStatusModemMobile 2 }

-- {SCALAR} 1.3.6.1.4.1.248.32.18.1.49.3
hmStatusModemMobileState OBJECT-TYPE
    SYNTAX     INTEGER {
                  eDeactivated (0),
                  eDeviceDetection (1),
                  eReset (2),
                  eInitializing (3),
                  eModemId (4),
                  eReady (5),
                  eConnecting (6),
                  ePassConnecting (7),
                  eDataMode (8),
                  eNetworkScan (9),
                  eSetPin (10),
                  ePinInvalid (11),
                  eUnexpectedResponse (12),
                  ePukRequired (13),
                  eNetwork (14),
                  eWaitForDevice (15),
                  ePinMissing (16),
                  eHwPoll (18)
            }
    MAX-ACCESS read-only
    STATUS     current
    DESCRIPTION
            "-- empty --"
    ::= { hmStatusModemMobile 3 }

-- {SCALAR} 1.3.6.1.4.1.248.32.18.1.49.4
hmStatusModemMobileOperating OBJECT-TYPE
    SYNTAX     INTEGER {
                  eNo (0),
                  eModem (1),
                  eWwan (2)
            }
    MAX-ACCESS read-only
    STATUS     current
    DESCRIPTION
            "-- empty --"
    ::= { hmStatusModemMobile 4 }

-- {SCALAR} 1.3.6.1.4.1.248.32.18.1.49.5
hmStatusModemMobileDataRate OBJECT-TYPE
    SYNTAX     Integer32 (0..2147483647)
    MAX-ACCESS read-only
    STATUS     current
    DESCRIPTION
            "-- empty --"
    ::= { hmStatusModemMobile 5 }

-- {SCALAR} 1.3.6.1.4.1.248.32.18.1.49.6
hmStatusModemMobileSignalDbm OBJECT-TYPE
    SYNTAX     Integer32 (-2147483648..2147483647)
    MAX-ACCESS read-only
    STATUS     current
    DESCRIPTION
            "-- empty --"
    ::= { hmStatusModemMobile 6 }

-- {SCALAR} 1.3.6.1.4.1.248.32.18.1.49.7
hmStatusModemMobileRegistration OBJECT-TYPE
    SYNTAX     INTEGER {
                  eNoNetwork (0),
                  eHomeNetwork (1),
                  eSearching (2),
                  eDenied (3),
                  eUnknown (4),
                  eRoaming (5),
                  eNoNetworkDenied (128),
                  eSearchingDenied (130),
                  eRegistrationDenied (131),
                  eUnknownDenied (132)
            }
    MAX-ACCESS read-only
    STATUS     current
    DESCRIPTION
            "-- empty --"
    ::= { hmStatusModemMobile 7 }

-- {SCALAR} 1.3.6.1.4.1.248.32.18.1.49.8
hmStatusModemMobileNetwork OBJECT-TYPE
    SYNTAX     DisplayString (SIZE(0..16))
    MAX-ACCESS read-only
    STATUS     current
    DESCRIPTION
            "-- empty --"
    ::= { hmStatusModemMobile 8 }

-- {TABLE} 1.3.6.1.4.1.248.32.18.1.49.9
hmStatusModemMobileNetworkListTable OBJECT-TYPE
    SYNTAX     SEQUENCE OF HmStatusModemMobileNetworkListEntry
    MAX-ACCESS not-accessible
    STATUS     current
    DESCRIPTION
            "-- empty --"
    ::= { hmStatusModemMobile 9 }

-- {ROW} 1.3.6.1.4.1.248.32.18.1.49.9.1
hmStatusModemMobileNetworkListEntry OBJECT-TYPE
    SYNTAX     HmStatusModemMobileNetworkListEntry
    MAX-ACCESS not-accessible
    STATUS     current
    DESCRIPTION
            ""
    INDEX {
            hmStatusModemMobileNetworkListEntryNetwork
          }
    ::= { hmStatusModemMobileNetworkListTable 1 }

HmStatusModemMobileNetworkListEntry ::= SEQUENCE {
            hmStatusModemMobileNetworkListEntryNetwork DisplayString,
            hmStatusModemMobileNetworkListEntryState INTEGER,
            hmStatusModemMobileNetworkListEntryMode BITS,
            hmStatusModemMobileNetworkListEntryNumeric Integer32
    }

-- {COLUMN} 1.3.6.1.4.1.248.32.18.1.49.9.1.1
hmStatusModemMobileNetworkListEntryNetwork OBJECT-TYPE
    SYNTAX     DisplayString (SIZE(0..16))
    MAX-ACCESS read-only
    STATUS     current
    DESCRIPTION
            "-- empty --"
    ::= { hmStatusModemMobileNetworkListEntry 1 }

-- {COLUMN} 1.3.6.1.4.1.248.32.18.1.49.9.1.2
hmStatusModemMobileNetworkListEntryState OBJECT-TYPE
    SYNTAX     INTEGER {
                  eUnknown (1),
                  eAvailable (2),
                  eCurrent (3),
                  eForbidden (4)
            }
    MAX-ACCESS read-only
    STATUS     current
    DESCRIPTION
            "-- empty --"
    ::= { hmStatusModemMobileNetworkListEntry 2 }

-- {COLUMN} 1.3.6.1.4.1.248.32.18.1.49.9.1.3
hmStatusModemMobileNetworkListEntryMode OBJECT-TYPE
    SYNTAX     BITS {
                  eUnknown (0),
                  eLte (29),
                  eUmts (30),
                  eGprs (31)
            }
    MAX-ACCESS read-only
    STATUS     current
    DESCRIPTION
            "-- empty --"
    ::= { hmStatusModemMobileNetworkListEntry 3 }

-- {COLUMN} 1.3.6.1.4.1.248.32.18.1.49.9.1.4
hmStatusModemMobileNetworkListEntryNumeric OBJECT-TYPE
    SYNTAX     Integer32 (0..2147483647)
    MAX-ACCESS read-only
    STATUS     current
    DESCRIPTION
            "-- empty --"
    ::= { hmStatusModemMobileNetworkListEntry 4 }

-- {SCALAR} 1.3.6.1.4.1.248.32.18.1.49.10
hmStatusModemMobileScanNetworks OBJECT-TYPE
    SYNTAX     DisplayString
    MAX-ACCESS read-write
    STATUS     current
    DESCRIPTION
            "-- empty --"
    ::= { hmStatusModemMobile 10 }

-- {SCALAR} 1.3.6.1.4.1.248.32.18.1.49.11
hmStatusModemMobileInputPuk OBJECT-TYPE
    SYNTAX     DisplayString
    MAX-ACCESS read-write
    STATUS     current
    DESCRIPTION
            "-- empty --"
    ::= { hmStatusModemMobile 11 }

-- {SCALAR} 1.3.6.1.4.1.248.32.18.1.49.12
hmStatusModemMobileMode OBJECT-TYPE
    SYNTAX     INTEGER {
                  eUnknown (0),
                  eUmts (1),
                  eGprs (2),
                  eGsm (3),
                  eEdge (4),
                  eHsdpa (5),
                  eHsupa (6),
                  eHspaPlus (7),
                  eLte (8),
                  eHspa (9)
            }
    MAX-ACCESS read-only
    STATUS     current
    DESCRIPTION
            "-- empty --"
    ::= { hmStatusModemMobile 12 }

-- {SCALAR} 1.3.6.1.4.1.248.32.18.1.49.13
hmStatusModemMobilePort OBJECT-TYPE
    SYNTAX     INTEGER {
                  eNone (0),
                  eOutband (1),
                  eUsb (2)
            }
    MAX-ACCESS read-only
    STATUS     current
    DESCRIPTION
            "-- empty --"
    ::= { hmStatusModemMobile 13 }

-- {SCALAR} 1.3.6.1.4.1.248.32.18.1.49.14
hmStatusModemMobileDroppedTxPackets OBJECT-TYPE
    SYNTAX     Integer32 (0..2147483647)
    MAX-ACCESS read-only
    STATUS     current
    DESCRIPTION
            "-- empty --"
    ::= { hmStatusModemMobile 14 }

-- {SCALAR} 1.3.6.1.4.1.248.32.18.1.49.15
hmStatusModemMobileHardwareResets OBJECT-TYPE
    SYNTAX     Integer32 (0..2147483647)
    MAX-ACCESS read-only
    STATUS     current
    DESCRIPTION
            "-- empty --"
    ::= { hmStatusModemMobile 15 }

-- {TABLE} 1.3.6.1.4.1.248.32.18.1.49.16
hmStatusModemMobileHistoryTable OBJECT-TYPE
    SYNTAX     SEQUENCE OF HmStatusModemMobileHistoryEntry
    MAX-ACCESS not-accessible
    STATUS     current
    DESCRIPTION
            "-- empty --"
    ::= { hmStatusModemMobile 16 }

-- {ROW} 1.3.6.1.4.1.248.32.18.1.49.16.1
hmStatusModemMobileHistoryEntry OBJECT-TYPE
    SYNTAX     HmStatusModemMobileHistoryEntry
    MAX-ACCESS not-accessible
    STATUS     current
    DESCRIPTION
            ""
    INDEX {
            hmStatusModemMobileHistoryEntryIndex
          }
    ::= { hmStatusModemMobileHistoryTable 1 }

HmStatusModemMobileHistoryEntry ::= SEQUENCE {
            hmStatusModemMobileHistoryEntryIndex Integer32,
            hmStatusModemMobileHistoryEntryTimestamp Gauge32,
            hmStatusModemMobileHistoryEntrySignalDbm Integer32,
            hmStatusModemMobileHistoryEntryNetwork DisplayString,
            hmStatusModemMobileHistoryEntryMode INTEGER,
            hmStatusModemMobileHistoryEntryRegistration INTEGER
    }

-- {COLUMN} 1.3.6.1.4.1.248.32.18.1.49.16.1.1
hmStatusModemMobileHistoryEntryIndex OBJECT-TYPE
    SYNTAX     Integer32 (0..2147483647)
    MAX-ACCESS read-only
    STATUS     current
    DESCRIPTION
            "-- empty --"
    ::= { hmStatusModemMobileHistoryEntry 1 }

-- {COLUMN} 1.3.6.1.4.1.248.32.18.1.49.16.1.2
hmStatusModemMobileHistoryEntryTimestamp OBJECT-TYPE
    SYNTAX     Gauge32
    MAX-ACCESS read-only
    STATUS     current
    DESCRIPTION
            "-- empty --"
    ::= { hmStatusModemMobileHistoryEntry 2 }

-- {COLUMN} 1.3.6.1.4.1.248.32.18.1.49.16.1.3
hmStatusModemMobileHistoryEntrySignalDbm OBJECT-TYPE
    SYNTAX     Integer32 (-2147483648..2147483647)
    MAX-ACCESS read-only
    STATUS     current
    DESCRIPTION
            "-- empty --"
    ::= { hmStatusModemMobileHistoryEntry 3 }

-- {COLUMN} 1.3.6.1.4.1.248.32.18.1.49.16.1.4
hmStatusModemMobileHistoryEntryNetwork OBJECT-TYPE
    SYNTAX     DisplayString (SIZE(0..1))
    MAX-ACCESS read-only
    STATUS     current
    DESCRIPTION
            "-- empty --"
    ::= { hmStatusModemMobileHistoryEntry 4 }

-- {COLUMN} 1.3.6.1.4.1.248.32.18.1.49.16.1.5
hmStatusModemMobileHistoryEntryMode OBJECT-TYPE
    SYNTAX     INTEGER {
                  eUnknown (0),
                  eUmts (1),
                  eGprs (2),
                  eGsm (3),
                  eEdge (4),
                  eHsdpa (5),
                  eHsupa (6),
                  eHspaPlus (7),
                  eLte (8),
                  eHspa (9)
            }
    MAX-ACCESS read-only
    STATUS     current
    DESCRIPTION
            "-- empty --"
    ::= { hmStatusModemMobileHistoryEntry 5 }

-- {COLUMN} 1.3.6.1.4.1.248.32.18.1.49.16.1.6
hmStatusModemMobileHistoryEntryRegistration OBJECT-TYPE
    SYNTAX     INTEGER {
                  eNoNetwork (0),
                  eHomeNetwork (1),
                  eSearching (2),
                  eDenied (3),
                  eUnknown (4),
                  eRoaming (5),
                  eNoNetworkDenied (128),
                  eSearchingDenied (130),
                  eRegistrationDenied (131),
                  eUnknownDenied (132)
            }
    MAX-ACCESS read-only
    STATUS     current
    DESCRIPTION
            "-- empty --"
    ::= { hmStatusModemMobileHistoryEntry 6 }

-- {SCALAR} 1.3.6.1.4.1.248.32.18.1.49.17
hmStatusModemMobileTemperatureStatus OBJECT-TYPE
    SYNTAX     INTEGER {
                  eUnknown (0),
                  eNormal (1),
                  eLow (2),
                  eHigh (3),
                  eLowCritical (5),
                  eHighCritical (6)
            }
    MAX-ACCESS read-only
    STATUS     current
    DESCRIPTION
            "-- empty --"
    ::= { hmStatusModemMobile 17 }

-- {SCALAR} 1.3.6.1.4.1.248.32.18.1.49.18
hmStatusModemMobileTemperatureDegc OBJECT-TYPE
    SYNTAX     Integer32 (0..255)
    MAX-ACCESS read-only
    STATUS     current
    DESCRIPTION
            "-- empty --"
    ::= { hmStatusModemMobile 18 }

-- {SCALAR} 1.3.6.1.4.1.248.32.18.1.49.19
hmStatusModemMobileSupplyVoltageStatus OBJECT-TYPE
    SYNTAX     INTEGER {
                  eUnknown (0),
                  eNormal (1),
                  eLow (2),
                  eHigh (3),
                  eLowCritical (5),
                  eHighCritical (6)
            }
    MAX-ACCESS read-only
    STATUS     current
    DESCRIPTION
            "-- empty --"
    ::= { hmStatusModemMobile 19 }

-- {SCALAR} 1.3.6.1.4.1.248.32.18.1.49.20
hmStatusModemMobileSupplyVoltageMv OBJECT-TYPE
    SYNTAX     Integer32 (0..65535)
    MAX-ACCESS read-only
    STATUS     current
    DESCRIPTION
            "-- empty --"
    ::= { hmStatusModemMobile 20 }

-- {SCALAR} 1.3.6.1.4.1.248.32.18.1.49.21
hmStatusModemMobilePinStatus OBJECT-TYPE
    SYNTAX     DisplayString (SIZE(0..47))
    MAX-ACCESS read-only
    STATUS     current
    DESCRIPTION
            "-- empty --"
    ::= { hmStatusModemMobile 21 }

-- {SCALAR} 1.3.6.1.4.1.248.32.18.1.49.22
hmStatusModemMobileRxTimeouts OBJECT-TYPE
    SYNTAX     Integer32 (0..2147483647)
    MAX-ACCESS read-only
    STATUS     current
    DESCRIPTION
            "-- empty --"
    ::= { hmStatusModemMobile 22 }

-- {SCALAR} 1.3.6.1.4.1.248.32.18.1.49.23
hmStatusModemMobileSimIdIccid OBJECT-TYPE
    SYNTAX     DisplayString (SIZE(0..22))
    MAX-ACCESS read-only
    STATUS     current
    DESCRIPTION
            "-- empty --"
    ::= { hmStatusModemMobile 23 }

-- {SCALAR} 1.3.6.1.4.1.248.32.18.1.49.25
hmStatusModemMobileFallbackTo2g OBJECT-TYPE
    SYNTAX     INTEGER {
                  eNo (0),
                  eYes (1)
            }
    MAX-ACCESS read-only
    STATUS     current
    DESCRIPTION
            "-- empty --"
    ::= { hmStatusModemMobile 25 }

-- {SCALAR} 1.3.6.1.4.1.248.32.18.1.49.26
hmStatusModemMobileMobileCountryCode OBJECT-TYPE
    SYNTAX     INTEGER {
                  eUnknown (0),
                  eDe (262)
            }
    MAX-ACCESS read-only
    STATUS     current
    DESCRIPTION
            "-- empty --"
    ::= { hmStatusModemMobile 26 }

-- {SCALAR} 1.3.6.1.4.1.248.32.18.1.49.27
hmStatusModemMobileMobileNetworkCode OBJECT-TYPE
    SYNTAX     Integer32 (0..2147483647)
    MAX-ACCESS read-only
    STATUS     current
    DESCRIPTION
            "-- empty --"
    ::= { hmStatusModemMobile 27 }

-- {SCALAR} 1.3.6.1.4.1.248.32.18.1.49.28
hmStatusModemMobileCellId OBJECT-TYPE
    SYNTAX     Integer32 (0..2147483647)
    MAX-ACCESS read-only
    STATUS     current
    DESCRIPTION
            "-- empty --"
    ::= { hmStatusModemMobile 28 }

-- {SCALAR} 1.3.6.1.4.1.248.32.18.1.49.29
hmStatusModemMobileLocalAreaCode OBJECT-TYPE
    SYNTAX     Integer32 (0..2147483647)
    MAX-ACCESS read-only
    STATUS     current
    DESCRIPTION
            "-- empty --"
    ::= { hmStatusModemMobile 29 }

-- {SCALAR} 1.3.6.1.4.1.248.32.18.1.49.30
hmStatusModemMobileRelease OBJECT-TYPE
    SYNTAX     Integer32 (0..2147483647)
    MAX-ACCESS read-only
    STATUS     current
    DESCRIPTION
            "-- empty --"
    ::= { hmStatusModemMobile 30 }

-- {SCALAR} 1.3.6.1.4.1.248.32.18.1.49.31
hmStatusModemMobileMaxDownstreamRateKbS OBJECT-TYPE
    SYNTAX     Integer32 (0..2147483647)
    MAX-ACCESS read-only
    STATUS     current
    DESCRIPTION
            "-- empty --"
    ::= { hmStatusModemMobile 31 }

-- {SCALAR} 1.3.6.1.4.1.248.32.18.1.49.32
hmStatusModemMobileMaxUpstreamRateKbS OBJECT-TYPE
    SYNTAX     Integer32 (0..2147483647)
    MAX-ACCESS read-only
    STATUS     current
    DESCRIPTION
            "-- empty --"
    ::= { hmStatusModemMobile 32 }

-- {SCALAR} 1.3.6.1.4.1.248.32.18.1.49.33
hmStatusModemMobileMobileBand OBJECT-TYPE
    SYNTAX     DisplayString (SIZE(0..15))
    MAX-ACCESS read-only
    STATUS     current
    DESCRIPTION
            "-- empty --"
    ::= { hmStatusModemMobile 33 }

-- {SCALAR} 1.3.6.1.4.1.248.32.18.1.49.34
hmStatusModemMobileMobileBandwidthMhz OBJECT-TYPE
    SYNTAX     Integer32 (0..2147483647)
    MAX-ACCESS read-only
    STATUS     current
    DESCRIPTION
            "-- empty --"
    ::= { hmStatusModemMobile 34 }

-- {SCALAR} 1.3.6.1.4.1.248.32.18.1.49.35
hmStatusModemMobileMobileTxChannel OBJECT-TYPE
    SYNTAX     Integer32 (0..2147483647)
    MAX-ACCESS read-only
    STATUS     current
    DESCRIPTION
            "-- empty --"
    ::= { hmStatusModemMobile 35 }

-- {SCALAR} 1.3.6.1.4.1.248.32.18.1.49.36
hmStatusModemMobileMobileRxChannel OBJECT-TYPE
    SYNTAX     Integer32 (0..2147483647)
    MAX-ACCESS read-only
    STATUS     current
    DESCRIPTION
            "-- empty --"
    ::= { hmStatusModemMobile 36 }

-- {SCALAR} 1.3.6.1.4.1.248.32.18.1.49.37
hmStatusModemMobileImei OBJECT-TYPE
    SYNTAX     DisplayString (SIZE(0..15))
    MAX-ACCESS read-only
    STATUS     current
    DESCRIPTION
            "-- empty --"
    ::= { hmStatusModemMobile 37 }

-- {SCALAR} 1.3.6.1.4.1.248.32.18.1.49.39
hmStatusModemMobileImsi OBJECT-TYPE
    SYNTAX     DisplayString (SIZE(0..15))
    MAX-ACCESS read-only
    STATUS     current
    DESCRIPTION
            "-- empty --"
    ::= { hmStatusModemMobile 39 }

-- {SCALAR} 1.3.6.1.4.1.248.32.18.1.49.40
hmStatusModemMobilePhoneNumber OBJECT-TYPE
    SYNTAX     DisplayString (SIZE(0..31))
    MAX-ACCESS read-only
    STATUS     current
    DESCRIPTION
            "-- empty --"
    ::= { hmStatusModemMobile 40 }

-- {SCALAR} 1.3.6.1.4.1.248.32.18.1.49.41
hmStatusModemMobileSetApn OBJECT-TYPE
    SYNTAX     DisplayString (SIZE(0..63))
    MAX-ACCESS read-only
    STATUS     current
    DESCRIPTION
            "-- empty --"
    ::= { hmStatusModemMobile 41 }

-- {SCALAR} 1.3.6.1.4.1.248.32.18.1.49.42
hmStatusModemMobilePinChange OBJECT-TYPE
    SYNTAX     DisplayString
    MAX-ACCESS read-write
    STATUS     current
    DESCRIPTION
            "-- empty --"
    ::= { hmStatusModemMobile 42 }

-- {SCALAR} 1.3.6.1.4.1.248.32.18.1.49.46
hmStatusModemMobileNetworkselection OBJECT-TYPE
    SYNTAX     INTEGER {
                  eAuto (0),
                  eManual (1),
                  eUnknown (3)
            }
    MAX-ACCESS read-only
    STATUS     current
    DESCRIPTION
            "-- empty --"
    ::= { hmStatusModemMobile 46 }

-- {NODE} 1.3.6.1.4.1.248.32.18.1.50
hmStatusFileSystem OBJECT IDENTIFIER ::= { hmStatus 50 }

-- {TABLE} 1.3.6.1.4.1.248.32.18.1.50.1
hmStatusFileSystemContentsTable OBJECT-TYPE
    SYNTAX     SEQUENCE OF HmStatusFileSystemContentsEntry
    MAX-ACCESS not-accessible
    STATUS     current
    DESCRIPTION
            "-- empty --"
    ::= { hmStatusFileSystem 1 }

-- {ROW} 1.3.6.1.4.1.248.32.18.1.50.1.1
hmStatusFileSystemContentsEntry OBJECT-TYPE
    SYNTAX     HmStatusFileSystemContentsEntry
    MAX-ACCESS not-accessible
    STATUS     current
    DESCRIPTION
            ""
    INDEX {
            hmStatusFileSystemContentsEntryName
          }
    ::= { hmStatusFileSystemContentsTable 1 }

HmStatusFileSystemContentsEntry ::= SEQUENCE {
            hmStatusFileSystemContentsEntryName DisplayString,
            hmStatusFileSystemContentsEntrySize Integer32
    }

-- {COLUMN} 1.3.6.1.4.1.248.32.18.1.50.1.1.1
hmStatusFileSystemContentsEntryName OBJECT-TYPE
    SYNTAX     DisplayString (SIZE(0..255))
    MAX-ACCESS read-only
    STATUS     current
    DESCRIPTION
            "-- empty --"
    ::= { hmStatusFileSystemContentsEntry 1 }

-- {COLUMN} 1.3.6.1.4.1.248.32.18.1.50.1.1.2
hmStatusFileSystemContentsEntrySize OBJECT-TYPE
    SYNTAX     Integer32 (0..2147483647)
    MAX-ACCESS read-only
    STATUS     current
    DESCRIPTION
            "-- empty --"
    ::= { hmStatusFileSystemContentsEntry 2 }

-- {TABLE} 1.3.6.1.4.1.248.32.18.1.50.2
hmStatusFileSystemVolumesTable OBJECT-TYPE
    SYNTAX     SEQUENCE OF HmStatusFileSystemVolumesEntry
    MAX-ACCESS not-accessible
    STATUS     current
    DESCRIPTION
            "-- empty --"
    ::= { hmStatusFileSystem 2 }

-- {ROW} 1.3.6.1.4.1.248.32.18.1.50.2.1
hmStatusFileSystemVolumesEntry OBJECT-TYPE
    SYNTAX     HmStatusFileSystemVolumesEntry
    MAX-ACCESS not-accessible
    STATUS     current
    DESCRIPTION
            ""
    INDEX {
            hmStatusFileSystemVolumesEntryId
          }
    ::= { hmStatusFileSystemVolumesTable 1 }

HmStatusFileSystemVolumesEntry ::= SEQUENCE {
            hmStatusFileSystemVolumesEntryId DisplayString,
            hmStatusFileSystemVolumesEntryMountpoints DisplayString,
            hmStatusFileSystemVolumesEntryFilesystem DisplayString,
            hmStatusFileSystemVolumesEntryUnmountable Integer32,
            hmStatusFileSystemVolumesEntryFree DisplayString,
            hmStatusFileSystemVolumesEntrySize DisplayString,
            hmStatusFileSystemVolumesEntryFb Integer32,
            hmStatusFileSystemVolumesEntrySb Integer32
    }

-- {COLUMN} 1.3.6.1.4.1.248.32.18.1.50.2.1.1
hmStatusFileSystemVolumesEntryId OBJECT-TYPE
    SYNTAX     DisplayString (SIZE(0..255))
    MAX-ACCESS read-only
    STATUS     current
    DESCRIPTION
            "-- empty --"
    ::= { hmStatusFileSystemVolumesEntry 1 }

-- {COLUMN} 1.3.6.1.4.1.248.32.18.1.50.2.1.2
hmStatusFileSystemVolumesEntryMountpoints OBJECT-TYPE
    SYNTAX     DisplayString (SIZE(0..255))
    MAX-ACCESS read-only
    STATUS     current
    DESCRIPTION
            "-- empty --"
    ::= { hmStatusFileSystemVolumesEntry 2 }

-- {COLUMN} 1.3.6.1.4.1.248.32.18.1.50.2.1.3
hmStatusFileSystemVolumesEntryFilesystem OBJECT-TYPE
    SYNTAX     DisplayString (SIZE(0..255))
    MAX-ACCESS read-only
    STATUS     current
    DESCRIPTION
            "-- empty --"
    ::= { hmStatusFileSystemVolumesEntry 3 }

-- {COLUMN} 1.3.6.1.4.1.248.32.18.1.50.2.1.4
hmStatusFileSystemVolumesEntryUnmountable OBJECT-TYPE
    SYNTAX     Integer32 (0..255)
    MAX-ACCESS read-only
    STATUS     current
    DESCRIPTION
            "-- empty --"
    ::= { hmStatusFileSystemVolumesEntry 4 }

-- {COLUMN} 1.3.6.1.4.1.248.32.18.1.50.2.1.5
hmStatusFileSystemVolumesEntryFree OBJECT-TYPE
    SYNTAX     DisplayString (SIZE(0..255))
    MAX-ACCESS read-only
    STATUS     current
    DESCRIPTION
            "-- empty --"
    ::= { hmStatusFileSystemVolumesEntry 5 }

-- {COLUMN} 1.3.6.1.4.1.248.32.18.1.50.2.1.6
hmStatusFileSystemVolumesEntrySize OBJECT-TYPE
    SYNTAX     DisplayString (SIZE(0..255))
    MAX-ACCESS read-only
    STATUS     current
    DESCRIPTION
            "-- empty --"
    ::= { hmStatusFileSystemVolumesEntry 6 }

-- {COLUMN} 1.3.6.1.4.1.248.32.18.1.50.2.1.7
hmStatusFileSystemVolumesEntryFb OBJECT-TYPE
    SYNTAX     Integer32 (0..2147483647)
    MAX-ACCESS read-only
    STATUS     current
    DESCRIPTION
            "-- empty --"
    ::= { hmStatusFileSystemVolumesEntry 7 }

-- {COLUMN} 1.3.6.1.4.1.248.32.18.1.50.2.1.8
hmStatusFileSystemVolumesEntrySb OBJECT-TYPE
    SYNTAX     Integer32 (0..2147483647)
    MAX-ACCESS read-only
    STATUS     current
    DESCRIPTION
            "-- empty --"
    ::= { hmStatusFileSystemVolumesEntry 8 }

-- {SCALAR} 1.3.6.1.4.1.248.32.18.1.50.3
hmStatusFileSystemUnmount OBJECT-TYPE
    SYNTAX     DisplayString
    MAX-ACCESS read-write
    STATUS     current
    DESCRIPTION
            "-- empty --"
    ::= { hmStatusFileSystem 3 }

-- {SCALAR} 1.3.6.1.4.1.248.32.18.1.50.4
hmStatusFileSystemSecureErase OBJECT-TYPE
    SYNTAX     DisplayString
    MAX-ACCESS read-write
    STATUS     current
    DESCRIPTION
            "-- empty --"
    ::= { hmStatusFileSystem 4 }

-- {NODE} 1.3.6.1.4.1.248.32.18.1.51
hmStatusEthernetPorts OBJECT IDENTIFIER ::= { hmStatus 51 }

-- {TABLE} 1.3.6.1.4.1.248.32.18.1.51.1
hmStatusEthernetPortsPortsTable OBJECT-TYPE
    SYNTAX     SEQUENCE OF HmStatusEthernetPortsPortsEntry
    MAX-ACCESS not-accessible
    STATUS     current
    DESCRIPTION
            "-- empty --"
    ::= { hmStatusEthernetPorts 1 }

-- {ROW} 1.3.6.1.4.1.248.32.18.1.51.1.1
hmStatusEthernetPortsPortsEntry OBJECT-TYPE
    SYNTAX     HmStatusEthernetPortsPortsEntry
    MAX-ACCESS not-accessible
    STATUS     current
    DESCRIPTION
            ""
    INDEX {
            hmStatusEthernetPortsPortsEntryPort
          }
    ::= { hmStatusEthernetPortsPortsTable 1 }

HmStatusEthernetPortsPortsEntry ::= SEQUENCE {
            hmStatusEthernetPortsPortsEntryPort INTEGER,
            hmStatusEthernetPortsPortsEntryLinkActive INTEGER,
            hmStatusEthernetPortsPortsEntryConnector INTEGER,
            hmStatusEthernetPortsPortsEntryMdiMode INTEGER,
            hmStatusEthernetPortsPortsEntryAssignment INTEGER,
            hmStatusEthernetPortsPortsEntryFlowControl INTEGER,
            hmStatusEthernetPortsPortsEntryPrivateMode INTEGER,
            hmStatusEthernetPortsPortsEntryAutoNegotiation INTEGER,
            hmStatusEthernetPortsPortsEntryDownshift INTEGER,
            hmStatusEthernetPortsPortsEntryClockRole INTEGER,
            hmStatusEthernetPortsPortsEntryRemoteFault INTEGER
    }

-- {COLUMN} 1.3.6.1.4.1.248.32.18.1.51.1.1.1
hmStatusEthernetPortsPortsEntryPort OBJECT-TYPE
    SYNTAX     INTEGER {
                  eEth1 (2),
                  eEth2 (3),
                  eEth3 (4),
                  eEth4 (5)
            }
    MAX-ACCESS read-only
    STATUS     current
    DESCRIPTION
            "-- empty --"
    ::= { hmStatusEthernetPortsPortsEntry 1 }

-- {COLUMN} 1.3.6.1.4.1.248.32.18.1.51.1.1.3
hmStatusEthernetPortsPortsEntryLinkActive OBJECT-TYPE
    SYNTAX     INTEGER {
                  eNo (0),
                  eYes (1)
            }
    MAX-ACCESS read-only
    STATUS     current
    DESCRIPTION
            "-- empty --"
    ::= { hmStatusEthernetPortsPortsEntry 3 }

-- {COLUMN} 1.3.6.1.4.1.248.32.18.1.51.1.1.4
hmStatusEthernetPortsPortsEntryConnector OBJECT-TYPE
    SYNTAX     INTEGER {
                  eNone (0),
                  e10bT (1),
                  eFd10bTx (2),
                  e100bTx (3),
                  eFd100bTx (4),
                  eFd1000bTx (6),
                  e10b2 (33),
                  e10b5 (34),
                  eFd1000bF (70),
                  ePowerDown (255)
            }
    MAX-ACCESS read-only
    STATUS     current
    DESCRIPTION
            "-- empty --"
    ::= { hmStatusEthernetPortsPortsEntry 4 }

-- {COLUMN} 1.3.6.1.4.1.248.32.18.1.51.1.1.6
hmStatusEthernetPortsPortsEntryMdiMode OBJECT-TYPE
    SYNTAX     INTEGER {
                  eUnknown (0),
                  eMdi (1),
                  eMdix (2),
                  eNotApplicable (3)
            }
    MAX-ACCESS read-only
    STATUS     current
    DESCRIPTION
            "-- empty --"
    ::= { hmStatusEthernetPortsPortsEntry 6 }

-- {COLUMN} 1.3.6.1.4.1.248.32.18.1.51.1.1.7
hmStatusEthernetPortsPortsEntryAssignment OBJECT-TYPE
    SYNTAX     INTEGER {
                  eLan1 (0),
                  eLan2 (1),
                  eLan3 (2),
                  eLan4 (3),
                  eDsl1 (512),
                  eDsl2 (513),
                  eDsl3 (514),
                  eDsl4 (515),
                  eIdle (65533),
                  ePowerDown (65535)
            }
    MAX-ACCESS read-only
    STATUS     current
    DESCRIPTION
            "-- empty --"
    ::= { hmStatusEthernetPortsPortsEntry 7 }

-- {COLUMN} 1.3.6.1.4.1.248.32.18.1.51.1.1.8
hmStatusEthernetPortsPortsEntryFlowControl OBJECT-TYPE
    SYNTAX     INTEGER {
                  eNo (0),
                  eYes (1),
                  eTxOnly (3),
                  eRxOnly (4)
            }
    MAX-ACCESS read-only
    STATUS     current
    DESCRIPTION
            "-- empty --"
    ::= { hmStatusEthernetPortsPortsEntry 8 }

-- {COLUMN} 1.3.6.1.4.1.248.32.18.1.51.1.1.9
hmStatusEthernetPortsPortsEntryPrivateMode OBJECT-TYPE
    SYNTAX     INTEGER {
                  eYes (1)
            }
    MAX-ACCESS read-only
    STATUS     current
    DESCRIPTION
            "-- empty --"
    ::= { hmStatusEthernetPortsPortsEntry 9 }

-- {COLUMN} 1.3.6.1.4.1.248.32.18.1.51.1.1.10
hmStatusEthernetPortsPortsEntryAutoNegotiation OBJECT-TYPE
    SYNTAX     INTEGER {
                  ePending (0),
                  eCompleted (1),
                  eDisabled (2),
                  eNotAvailable (3)
            }
    MAX-ACCESS read-only
    STATUS     current
    DESCRIPTION
            "-- empty --"
    ::= { hmStatusEthernetPortsPortsEntry 10 }

-- {COLUMN} 1.3.6.1.4.1.248.32.18.1.51.1.1.11
hmStatusEthernetPortsPortsEntryDownshift OBJECT-TYPE
    SYNTAX     INTEGER {
                  eNo (0),
                  eYes (1)
            }
    MAX-ACCESS read-only
    STATUS     current
    DESCRIPTION
            "-- empty --"
    ::= { hmStatusEthernetPortsPortsEntry 11 }

-- {COLUMN} 1.3.6.1.4.1.248.32.18.1.51.1.1.12
hmStatusEthernetPortsPortsEntryClockRole OBJECT-TYPE
    SYNTAX     INTEGER {
                  eNone (0),
                  eMaster (1),
                  eSlave (2),
                  eFault (3)
            }
    MAX-ACCESS read-only
    STATUS     current
    DESCRIPTION
            "-- empty --"
    ::= { hmStatusEthernetPortsPortsEntry 12 }

-- {COLUMN} 1.3.6.1.4.1.248.32.18.1.51.1.1.14
hmStatusEthernetPortsPortsEntryRemoteFault OBJECT-TYPE
    SYNTAX     INTEGER {
                  eNo (0),
                  eYes (1)
            }
    MAX-ACCESS read-only
    STATUS     current
    DESCRIPTION
            "-- empty --"
    ::= { hmStatusEthernetPortsPortsEntry 14 }

-- {SCALAR} 1.3.6.1.4.1.248.32.18.1.51.2
hmStatusEthernetPortsCableTest OBJECT-TYPE
    SYNTAX     DisplayString
    MAX-ACCESS read-write
    STATUS     current
    DESCRIPTION
            "-- empty --"
    ::= { hmStatusEthernetPorts 2 }

-- {TABLE} 1.3.6.1.4.1.248.32.18.1.51.3
hmStatusEthernetPortsCableTestResultsTable OBJECT-TYPE
    SYNTAX     SEQUENCE OF HmStatusEthernetPortsCableTestResultsEntry
    MAX-ACCESS not-accessible
    STATUS     current
    DESCRIPTION
            "-- empty --"
    ::= { hmStatusEthernetPorts 3 }

-- {ROW} 1.3.6.1.4.1.248.32.18.1.51.3.1
hmStatusEthernetPortsCableTestResultsEntry OBJECT-TYPE
    SYNTAX     HmStatusEthernetPortsCableTestResultsEntry
    MAX-ACCESS not-accessible
    STATUS     current
    DESCRIPTION
            ""
    INDEX {
            hmStatusEthernetPortsCableTestResultsEntryIfc
          }
    ::= { hmStatusEthernetPortsCableTestResultsTable 1 }

HmStatusEthernetPortsCableTestResultsEntry ::= SEQUENCE {
            hmStatusEthernetPortsCableTestResultsEntryIfc INTEGER,
            hmStatusEthernetPortsCableTestResultsEntryMdi0Status INTEGER,
            hmStatusEthernetPortsCableTestResultsEntryMdi0Distance DisplayString,
            hmStatusEthernetPortsCableTestResultsEntryMdi1Status INTEGER,
            hmStatusEthernetPortsCableTestResultsEntryMdi1Distance DisplayString,
            hmStatusEthernetPortsCableTestResultsEntryMdi2Status INTEGER,
            hmStatusEthernetPortsCableTestResultsEntryMdi2Distance DisplayString,
            hmStatusEthernetPortsCableTestResultsEntryMdi3Status INTEGER,
            hmStatusEthernetPortsCableTestResultsEntryMdi3Distance DisplayString
    }

-- {COLUMN} 1.3.6.1.4.1.248.32.18.1.51.3.1.1
hmStatusEthernetPortsCableTestResultsEntryIfc OBJECT-TYPE
    SYNTAX     INTEGER {
                  eEth1 (2),
                  eEth2 (3),
                  eEth3 (4),
                  eEth4 (5)
            }
    MAX-ACCESS read-only
    STATUS     current
    DESCRIPTION
            "-- empty --"
    ::= { hmStatusEthernetPortsCableTestResultsEntry 1 }

-- {COLUMN} 1.3.6.1.4.1.248.32.18.1.51.3.1.6
hmStatusEthernetPortsCableTestResultsEntryMdi0Status OBJECT-TYPE
    SYNTAX     INTEGER {
                  eUnknown (0),
                  eOk (1),
                  eOpen (2),
                  eShort (3),
                  eImpedanceFault (4),
                  eFail (5),
                  eBusy (6),
                  eLinkUp (7)
            }
    MAX-ACCESS read-only
    STATUS     current
    DESCRIPTION
            "-- empty --"
    ::= { hmStatusEthernetPortsCableTestResultsEntry 6 }

-- {COLUMN} 1.3.6.1.4.1.248.32.18.1.51.3.1.7
hmStatusEthernetPortsCableTestResultsEntryMdi0Distance OBJECT-TYPE
    SYNTAX     DisplayString (SIZE(0..10))
    MAX-ACCESS read-only
    STATUS     current
    DESCRIPTION
            "-- empty --"
    ::= { hmStatusEthernetPortsCableTestResultsEntry 7 }

-- {COLUMN} 1.3.6.1.4.1.248.32.18.1.51.3.1.8
hmStatusEthernetPortsCableTestResultsEntryMdi1Status OBJECT-TYPE
    SYNTAX     INTEGER {
                  eUnknown (0),
                  eOk (1),
                  eOpen (2),
                  eShort (3),
                  eImpedanceFault (4),
                  eFail (5),
                  eBusy (6),
                  eLinkUp (7)
            }
    MAX-ACCESS read-only
    STATUS     current
    DESCRIPTION
            "-- empty --"
    ::= { hmStatusEthernetPortsCableTestResultsEntry 8 }

-- {COLUMN} 1.3.6.1.4.1.248.32.18.1.51.3.1.9
hmStatusEthernetPortsCableTestResultsEntryMdi1Distance OBJECT-TYPE
    SYNTAX     DisplayString (SIZE(0..10))
    MAX-ACCESS read-only
    STATUS     current
    DESCRIPTION
            "-- empty --"
    ::= { hmStatusEthernetPortsCableTestResultsEntry 9 }

-- {COLUMN} 1.3.6.1.4.1.248.32.18.1.51.3.1.10
hmStatusEthernetPortsCableTestResultsEntryMdi2Status OBJECT-TYPE
    SYNTAX     INTEGER {
                  eUnknown (0),
                  eOk (1),
                  eOpen (2),
                  eShort (3),
                  eImpedanceFault (4),
                  eFail (5),
                  eBusy (6),
                  eLinkUp (7)
            }
    MAX-ACCESS read-only
    STATUS     current
    DESCRIPTION
            "-- empty --"
    ::= { hmStatusEthernetPortsCableTestResultsEntry 10 }

-- {COLUMN} 1.3.6.1.4.1.248.32.18.1.51.3.1.11
hmStatusEthernetPortsCableTestResultsEntryMdi2Distance OBJECT-TYPE
    SYNTAX     DisplayString (SIZE(0..10))
    MAX-ACCESS read-only
    STATUS     current
    DESCRIPTION
            "-- empty --"
    ::= { hmStatusEthernetPortsCableTestResultsEntry 11 }

-- {COLUMN} 1.3.6.1.4.1.248.32.18.1.51.3.1.12
hmStatusEthernetPortsCableTestResultsEntryMdi3Status OBJECT-TYPE
    SYNTAX     INTEGER {
                  eUnknown (0),
                  eOk (1),
                  eOpen (2),
                  eShort (3),
                  eImpedanceFault (4),
                  eFail (5),
                  eBusy (6),
                  eLinkUp (7)
            }
    MAX-ACCESS read-only
    STATUS     current
    DESCRIPTION
            "-- empty --"
    ::= { hmStatusEthernetPortsCableTestResultsEntry 12 }

-- {COLUMN} 1.3.6.1.4.1.248.32.18.1.51.3.1.13
hmStatusEthernetPortsCableTestResultsEntryMdi3Distance OBJECT-TYPE
    SYNTAX     DisplayString (SIZE(0..10))
    MAX-ACCESS read-only
    STATUS     current
    DESCRIPTION
            "-- empty --"
    ::= { hmStatusEthernetPortsCableTestResultsEntry 13 }

-- {TABLE} 1.3.6.1.4.1.248.32.18.1.51.4
hmStatusEthernetPortsErrorsTable OBJECT-TYPE
    SYNTAX     SEQUENCE OF HmStatusEthernetPortsErrorsEntry
    MAX-ACCESS not-accessible
    STATUS     current
    DESCRIPTION
            "-- empty --"
    ::= { hmStatusEthernetPorts 4 }

-- {ROW} 1.3.6.1.4.1.248.32.18.1.51.4.1
hmStatusEthernetPortsErrorsEntry OBJECT-TYPE
    SYNTAX     HmStatusEthernetPortsErrorsEntry
    MAX-ACCESS not-accessible
    STATUS     current
    DESCRIPTION
            ""
    INDEX {
            hmStatusEthernetPortsErrorsEntryIfc
          }
    ::= { hmStatusEthernetPortsErrorsTable 1 }

HmStatusEthernetPortsErrorsEntry ::= SEQUENCE {
            hmStatusEthernetPortsErrorsEntryIfc INTEGER,
            hmStatusEthernetPortsErrorsEntryRxErrors Counter32,
            hmStatusEthernetPortsErrorsEntryTxErrors Counter32,
            hmStatusEthernetPortsErrorsEntryStackErrors Counter32,
            hmStatusEthernetPortsErrorsEntryNicErrors Counter32,
            hmStatusEthernetPortsErrorsEntryQueueErrors Counter32,
            hmStatusEthernetPortsErrorsEntryRxCrcErrors Counter32,
            hmStatusEthernetPortsErrorsEntryCollisions Counter32,
            hmStatusEthernetPortsErrorsEntrySingleCollisions Counter32,
            hmStatusEthernetPortsErrorsEntryMultipleCollisions Counter32,
            hmStatusEthernetPortsErrorsEntryLateCollisions Counter32,
            hmStatusEthernetPortsErrorsEntryExcessiveCollisions Counter32,
            hmStatusEthernetPortsErrorsEntryRxAlignErrors Counter32,
            hmStatusEthernetPortsErrorsEntryRxTooShort Counter32,
            hmStatusEthernetPortsErrorsEntryRxTooLong Counter32,
            hmStatusEthernetPortsErrorsEntryTxCarrier Counter32,
            hmStatusEthernetPortsErrorsEntryTxDeferred Counter32,
            hmStatusEthernetPortsErrorsEntryRxPhyErrors Counter32,
            hmStatusEthernetPortsErrorsEntryRxFifoOverflow Counter32,
            hmStatusEthernetPortsErrorsEntryTxDiscarded Counter32,
            hmStatusEthernetPortsErrorsEntryRxDscrUnderflow Counter32
    }

-- {COLUMN} 1.3.6.1.4.1.248.32.18.1.51.4.1.1
hmStatusEthernetPortsErrorsEntryIfc OBJECT-TYPE
    SYNTAX     INTEGER {
                  eEth1 (2),
                  eEth2 (3),
                  eEth3 (4),
                  eEth4 (5)
            }
    MAX-ACCESS read-only
    STATUS     current
    DESCRIPTION
            "-- empty --"
    ::= { hmStatusEthernetPortsErrorsEntry 1 }

-- {COLUMN} 1.3.6.1.4.1.248.32.18.1.51.4.1.2
hmStatusEthernetPortsErrorsEntryRxErrors OBJECT-TYPE
    SYNTAX     Counter32
    MAX-ACCESS read-only
    STATUS     current
    DESCRIPTION
            "-- empty --"
    ::= { hmStatusEthernetPortsErrorsEntry 2 }

-- {COLUMN} 1.3.6.1.4.1.248.32.18.1.51.4.1.3
hmStatusEthernetPortsErrorsEntryTxErrors OBJECT-TYPE
    SYNTAX     Counter32
    MAX-ACCESS read-only
    STATUS     current
    DESCRIPTION
            "-- empty --"
    ::= { hmStatusEthernetPortsErrorsEntry 3 }

-- {COLUMN} 1.3.6.1.4.1.248.32.18.1.51.4.1.4
hmStatusEthernetPortsErrorsEntryStackErrors OBJECT-TYPE
    SYNTAX     Counter32
    MAX-ACCESS read-only
    STATUS     current
    DESCRIPTION
            "-- empty --"
    ::= { hmStatusEthernetPortsErrorsEntry 4 }

-- {COLUMN} 1.3.6.1.4.1.248.32.18.1.51.4.1.5
hmStatusEthernetPortsErrorsEntryNicErrors OBJECT-TYPE
    SYNTAX     Counter32
    MAX-ACCESS read-only
    STATUS     current
    DESCRIPTION
            "-- empty --"
    ::= { hmStatusEthernetPortsErrorsEntry 5 }

-- {COLUMN} 1.3.6.1.4.1.248.32.18.1.51.4.1.6
hmStatusEthernetPortsErrorsEntryQueueErrors OBJECT-TYPE
    SYNTAX     Counter32
    MAX-ACCESS read-only
    STATUS     current
    DESCRIPTION
            "-- empty --"
    ::= { hmStatusEthernetPortsErrorsEntry 6 }

-- {COLUMN} 1.3.6.1.4.1.248.32.18.1.51.4.1.7
hmStatusEthernetPortsErrorsEntryRxCrcErrors OBJECT-TYPE
    SYNTAX     Counter32
    MAX-ACCESS read-only
    STATUS     current
    DESCRIPTION
            "-- empty --"
    ::= { hmStatusEthernetPortsErrorsEntry 7 }

-- {COLUMN} 1.3.6.1.4.1.248.32.18.1.51.4.1.8
hmStatusEthernetPortsErrorsEntryCollisions OBJECT-TYPE
    SYNTAX     Counter32
    MAX-ACCESS read-only
    STATUS     current
    DESCRIPTION
            "-- empty --"
    ::= { hmStatusEthernetPortsErrorsEntry 8 }

-- {COLUMN} 1.3.6.1.4.1.248.32.18.1.51.4.1.9
hmStatusEthernetPortsErrorsEntrySingleCollisions OBJECT-TYPE
    SYNTAX     Counter32
    MAX-ACCESS read-only
    STATUS     current
    DESCRIPTION
            "-- empty --"
    ::= { hmStatusEthernetPortsErrorsEntry 9 }

-- {COLUMN} 1.3.6.1.4.1.248.32.18.1.51.4.1.10
hmStatusEthernetPortsErrorsEntryMultipleCollisions OBJECT-TYPE
    SYNTAX     Counter32
    MAX-ACCESS read-only
    STATUS     current
    DESCRIPTION
            "-- empty --"
    ::= { hmStatusEthernetPortsErrorsEntry 10 }

-- {COLUMN} 1.3.6.1.4.1.248.32.18.1.51.4.1.11
hmStatusEthernetPortsErrorsEntryLateCollisions OBJECT-TYPE
    SYNTAX     Counter32
    MAX-ACCESS read-only
    STATUS     current
    DESCRIPTION
            "-- empty --"
    ::= { hmStatusEthernetPortsErrorsEntry 11 }

-- {COLUMN} 1.3.6.1.4.1.248.32.18.1.51.4.1.12
hmStatusEthernetPortsErrorsEntryExcessiveCollisions OBJECT-TYPE
    SYNTAX     Counter32
    MAX-ACCESS read-only
    STATUS     current
    DESCRIPTION
            "-- empty --"
    ::= { hmStatusEthernetPortsErrorsEntry 12 }

-- {COLUMN} 1.3.6.1.4.1.248.32.18.1.51.4.1.13
hmStatusEthernetPortsErrorsEntryRxAlignErrors OBJECT-TYPE
    SYNTAX     Counter32
    MAX-ACCESS read-only
    STATUS     current
    DESCRIPTION
            "-- empty --"
    ::= { hmStatusEthernetPortsErrorsEntry 13 }

-- {COLUMN} 1.3.6.1.4.1.248.32.18.1.51.4.1.14
hmStatusEthernetPortsErrorsEntryRxTooShort OBJECT-TYPE
    SYNTAX     Counter32
    MAX-ACCESS read-only
    STATUS     current
    DESCRIPTION
            "-- empty --"
    ::= { hmStatusEthernetPortsErrorsEntry 14 }

-- {COLUMN} 1.3.6.1.4.1.248.32.18.1.51.4.1.15
hmStatusEthernetPortsErrorsEntryRxTooLong OBJECT-TYPE
    SYNTAX     Counter32
    MAX-ACCESS read-only
    STATUS     current
    DESCRIPTION
            "-- empty --"
    ::= { hmStatusEthernetPortsErrorsEntry 15 }

-- {COLUMN} 1.3.6.1.4.1.248.32.18.1.51.4.1.16
hmStatusEthernetPortsErrorsEntryTxCarrier OBJECT-TYPE
    SYNTAX     Counter32
    MAX-ACCESS read-only
    STATUS     current
    DESCRIPTION
            "-- empty --"
    ::= { hmStatusEthernetPortsErrorsEntry 16 }

-- {COLUMN} 1.3.6.1.4.1.248.32.18.1.51.4.1.17
hmStatusEthernetPortsErrorsEntryTxDeferred OBJECT-TYPE
    SYNTAX     Counter32
    MAX-ACCESS read-only
    STATUS     current
    DESCRIPTION
            "-- empty --"
    ::= { hmStatusEthernetPortsErrorsEntry 17 }

-- {COLUMN} 1.3.6.1.4.1.248.32.18.1.51.4.1.18
hmStatusEthernetPortsErrorsEntryRxPhyErrors OBJECT-TYPE
    SYNTAX     Counter32
    MAX-ACCESS read-only
    STATUS     current
    DESCRIPTION
            "-- empty --"
    ::= { hmStatusEthernetPortsErrorsEntry 18 }

-- {COLUMN} 1.3.6.1.4.1.248.32.18.1.51.4.1.19
hmStatusEthernetPortsErrorsEntryRxFifoOverflow OBJECT-TYPE
    SYNTAX     Counter32
    MAX-ACCESS read-only
    STATUS     current
    DESCRIPTION
            "-- empty --"
    ::= { hmStatusEthernetPortsErrorsEntry 19 }

-- {COLUMN} 1.3.6.1.4.1.248.32.18.1.51.4.1.20
hmStatusEthernetPortsErrorsEntryTxDiscarded OBJECT-TYPE
    SYNTAX     Counter32
    MAX-ACCESS read-only
    STATUS     current
    DESCRIPTION
            "-- empty --"
    ::= { hmStatusEthernetPortsErrorsEntry 20 }

-- {COLUMN} 1.3.6.1.4.1.248.32.18.1.51.4.1.21
hmStatusEthernetPortsErrorsEntryRxDscrUnderflow OBJECT-TYPE
    SYNTAX     Counter32
    MAX-ACCESS read-only
    STATUS     current
    DESCRIPTION
            "-- empty --"
    ::= { hmStatusEthernetPortsErrorsEntry 21 }

-- {TABLE} 1.3.6.1.4.1.248.32.18.1.51.11
hmStatusEthernetPortsSfpPortsTable OBJECT-TYPE
    SYNTAX     SEQUENCE OF HmStatusEthernetPortsSfpPortsEntry
    MAX-ACCESS not-accessible
    STATUS     current
    DESCRIPTION
            "-- empty --"
    ::= { hmStatusEthernetPorts 11 }

-- {ROW} 1.3.6.1.4.1.248.32.18.1.51.11.1
hmStatusEthernetPortsSfpPortsEntry OBJECT-TYPE
    SYNTAX     HmStatusEthernetPortsSfpPortsEntry
    MAX-ACCESS not-accessible
    STATUS     current
    DESCRIPTION
            ""
    INDEX {
            hmStatusEthernetPortsSfpPortsEntryPort
          }
    ::= { hmStatusEthernetPortsSfpPortsTable 1 }

HmStatusEthernetPortsSfpPortsEntry ::= SEQUENCE {
            hmStatusEthernetPortsSfpPortsEntryPort INTEGER,
            hmStatusEthernetPortsSfpPortsEntryVendor DisplayString,
            hmStatusEthernetPortsSfpPortsEntryPartNo DisplayString,
            hmStatusEthernetPortsSfpPortsEntryRevision DisplayString,
            hmStatusEthernetPortsSfpPortsEntrySerialNo DisplayString,
            hmStatusEthernetPortsSfpPortsEntryStatus INTEGER,
            hmStatusEthernetPortsSfpPortsEntryMedium BITS,
            hmStatusEthernetPortsSfpPortsEntryWavelength Integer32,
            hmStatusEthernetPortsSfpPortsEntryDate DisplayString,
            hmStatusEthernetPortsSfpPortsEntryConnector INTEGER,
            hmStatusEthernetPortsSfpPortsEntryTemperature Integer32,
            hmStatusEthernetPortsSfpPortsEntrySupplyVoltage Integer32,
            hmStatusEthernetPortsSfpPortsEntryTxBias Integer32,
            hmStatusEthernetPortsSfpPortsEntryTxPower Integer32,
            hmStatusEthernetPortsSfpPortsEntryRxPower Integer32,
            hmStatusEthernetPortsSfpPortsEntryMonitoring INTEGER
    }

-- {COLUMN} 1.3.6.1.4.1.248.32.18.1.51.11.1.1
hmStatusEthernetPortsSfpPortsEntryPort OBJECT-TYPE
    SYNTAX     INTEGER {
                  eEth1 (2),
                  eEth2 (3)
            }
    MAX-ACCESS read-only
    STATUS     current
    DESCRIPTION
            "-- empty --"
    ::= { hmStatusEthernetPortsSfpPortsEntry 1 }

-- {COLUMN} 1.3.6.1.4.1.248.32.18.1.51.11.1.2
hmStatusEthernetPortsSfpPortsEntryVendor OBJECT-TYPE
    SYNTAX     DisplayString (SIZE(0..255))
    MAX-ACCESS read-only
    STATUS     current
    DESCRIPTION
            "-- empty --"
    ::= { hmStatusEthernetPortsSfpPortsEntry 2 }

-- {COLUMN} 1.3.6.1.4.1.248.32.18.1.51.11.1.3
hmStatusEthernetPortsSfpPortsEntryPartNo OBJECT-TYPE
    SYNTAX     DisplayString (SIZE(0..255))
    MAX-ACCESS read-only
    STATUS     current
    DESCRIPTION
            "-- empty --"
    ::= { hmStatusEthernetPortsSfpPortsEntry 3 }

-- {COLUMN} 1.3.6.1.4.1.248.32.18.1.51.11.1.4
hmStatusEthernetPortsSfpPortsEntryRevision OBJECT-TYPE
    SYNTAX     DisplayString (SIZE(0..255))
    MAX-ACCESS read-only
    STATUS     current
    DESCRIPTION
            "-- empty --"
    ::= { hmStatusEthernetPortsSfpPortsEntry 4 }

-- {COLUMN} 1.3.6.1.4.1.248.32.18.1.51.11.1.5
hmStatusEthernetPortsSfpPortsEntrySerialNo OBJECT-TYPE
    SYNTAX     DisplayString (SIZE(0..255))
    MAX-ACCESS read-only
    STATUS     current
    DESCRIPTION
            "-- empty --"
    ::= { hmStatusEthernetPortsSfpPortsEntry 5 }

-- {COLUMN} 1.3.6.1.4.1.248.32.18.1.51.11.1.6
hmStatusEthernetPortsSfpPortsEntryStatus OBJECT-TYPE
    SYNTAX     INTEGER {
                  eNotPresent (0),
                  eOk (1),
                  eChksumError (2),
                  eUnsupported (3),
                  eTxFault (4)
            }
    MAX-ACCESS read-only
    STATUS     current
    DESCRIPTION
            "-- empty --"
    ::= { hmStatusEthernetPortsSfpPortsEntry 6 }

-- {COLUMN} 1.3.6.1.4.1.248.32.18.1.51.11.1.7
hmStatusEthernetPortsSfpPortsEntryMedium OBJECT-TYPE
    SYNTAX     BITS {
                  eNone (0),
                  e1000baseBx10 (1),
                  e100baseFx (2),
                  e100baseLx (3),
                  e1000baseT (4),
                  e1000baseCx (5),
                  e1000baseLx (6),
                  e1000baseSx (7)
            }
    MAX-ACCESS read-only
    STATUS     current
    DESCRIPTION
            "-- empty --"
    ::= { hmStatusEthernetPortsSfpPortsEntry 7 }

-- {COLUMN} 1.3.6.1.4.1.248.32.18.1.51.11.1.8
hmStatusEthernetPortsSfpPortsEntryWavelength OBJECT-TYPE
    SYNTAX     Integer32 (0..65535)
    MAX-ACCESS read-only
    STATUS     current
    DESCRIPTION
            "-- empty --"
    ::= { hmStatusEthernetPortsSfpPortsEntry 8 }

-- {COLUMN} 1.3.6.1.4.1.248.32.18.1.51.11.1.9
hmStatusEthernetPortsSfpPortsEntryDate OBJECT-TYPE
    SYNTAX     DisplayString (SIZE(0..255))
    MAX-ACCESS read-only
    STATUS     current
    DESCRIPTION
            "-- empty --"
    ::= { hmStatusEthernetPortsSfpPortsEntry 9 }

-- {COLUMN} 1.3.6.1.4.1.248.32.18.1.51.11.1.10
hmStatusEthernetPortsSfpPortsEntryConnector OBJECT-TYPE
    SYNTAX     INTEGER {
                  eUnknown (0),
                  eSc (2),
                  eLc (7),
                  eSg (10),
                  eRj45 (34)
            }
    MAX-ACCESS read-only
    STATUS     current
    DESCRIPTION
            "-- empty --"
    ::= { hmStatusEthernetPortsSfpPortsEntry 10 }

-- {COLUMN} 1.3.6.1.4.1.248.32.18.1.51.11.1.11
hmStatusEthernetPortsSfpPortsEntryTemperature OBJECT-TYPE
    SYNTAX     Integer32 (-32768..32767)
    MAX-ACCESS read-only
    STATUS     current
    DESCRIPTION
            "-- empty --"
    ::= { hmStatusEthernetPortsSfpPortsEntry 11 }

-- {COLUMN} 1.3.6.1.4.1.248.32.18.1.51.11.1.12
hmStatusEthernetPortsSfpPortsEntrySupplyVoltage OBJECT-TYPE
    SYNTAX     Integer32 (0..65535)
    MAX-ACCESS read-only
    STATUS     current
    DESCRIPTION
            "-- empty --"
    ::= { hmStatusEthernetPortsSfpPortsEntry 12 }

-- {COLUMN} 1.3.6.1.4.1.248.32.18.1.51.11.1.13
hmStatusEthernetPortsSfpPortsEntryTxBias OBJECT-TYPE
    SYNTAX     Integer32 (0..65535)
    MAX-ACCESS read-only
    STATUS     current
    DESCRIPTION
            "-- empty --"
    ::= { hmStatusEthernetPortsSfpPortsEntry 13 }

-- {COLUMN} 1.3.6.1.4.1.248.32.18.1.51.11.1.14
hmStatusEthernetPortsSfpPortsEntryTxPower OBJECT-TYPE
    SYNTAX     Integer32 (0..65535)
    MAX-ACCESS read-only
    STATUS     current
    DESCRIPTION
            "-- empty --"
    ::= { hmStatusEthernetPortsSfpPortsEntry 14 }

-- {COLUMN} 1.3.6.1.4.1.248.32.18.1.51.11.1.15
hmStatusEthernetPortsSfpPortsEntryRxPower OBJECT-TYPE
    SYNTAX     Integer32 (0..65535)
    MAX-ACCESS read-only
    STATUS     current
    DESCRIPTION
            "-- empty --"
    ::= { hmStatusEthernetPortsSfpPortsEntry 15 }

-- {COLUMN} 1.3.6.1.4.1.248.32.18.1.51.11.1.16
hmStatusEthernetPortsSfpPortsEntryMonitoring OBJECT-TYPE
    SYNTAX     INTEGER {
                  eNo (0),
                  eYes (1)
            }
    MAX-ACCESS read-only
    STATUS     current
    DESCRIPTION
            "-- empty --"
    ::= { hmStatusEthernetPortsSfpPortsEntry 16 }

-- {SCALAR} 1.3.6.1.4.1.248.32.18.1.51.99
hmStatusEthernetPortsDeleteValues OBJECT-TYPE
    SYNTAX     DisplayString
    MAX-ACCESS read-write
    STATUS     current
    DESCRIPTION
            "-- empty --"
    ::= { hmStatusEthernetPorts 99 }

-- {NODE} 1.3.6.1.4.1.248.32.18.1.52
hmStatusPppoeServer OBJECT IDENTIFIER ::= { hmStatus 52 }

-- {SCALAR} 1.3.6.1.4.1.248.32.18.1.52.1
hmStatusPppoeServerRxPackets OBJECT-TYPE
    SYNTAX     Counter32
    MAX-ACCESS read-only
    STATUS     current
    DESCRIPTION
            "-- empty --"
    ::= { hmStatusPppoeServer 1 }

-- {SCALAR} 1.3.6.1.4.1.248.32.18.1.52.2
hmStatusPppoeServerTxPackets OBJECT-TYPE
    SYNTAX     Counter32
    MAX-ACCESS read-only
    STATUS     current
    DESCRIPTION
            "-- empty --"
    ::= { hmStatusPppoeServer 2 }

-- {SCALAR} 1.3.6.1.4.1.248.32.18.1.52.5
hmStatusPppoeServerDroppedPackets OBJECT-TYPE
    SYNTAX     Counter32
    MAX-ACCESS read-only
    STATUS     current
    DESCRIPTION
            "-- empty --"
    ::= { hmStatusPppoeServer 5 }

-- {SCALAR} 1.3.6.1.4.1.248.32.18.1.52.6
hmStatusPppoeServerRxErrors OBJECT-TYPE
    SYNTAX     Counter32
    MAX-ACCESS read-only
    STATUS     current
    DESCRIPTION
            "-- empty --"
    ::= { hmStatusPppoeServer 6 }

-- {SCALAR} 1.3.6.1.4.1.248.32.18.1.52.8
hmStatusPppoeServerSessionErrors OBJECT-TYPE
    SYNTAX     Counter32
    MAX-ACCESS read-only
    STATUS     current
    DESCRIPTION
            "-- empty --"
    ::= { hmStatusPppoeServer 8 }

-- {TABLE} 1.3.6.1.4.1.248.32.18.1.52.9
hmStatusPppoeServerConnectionsTable OBJECT-TYPE
    SYNTAX     SEQUENCE OF HmStatusPppoeServerConnectionsEntry
    MAX-ACCESS not-accessible
    STATUS     current
    DESCRIPTION
            "-- empty --"
    ::= { hmStatusPppoeServer 9 }

-- {ROW} 1.3.6.1.4.1.248.32.18.1.52.9.1
hmStatusPppoeServerConnectionsEntry OBJECT-TYPE
    SYNTAX     HmStatusPppoeServerConnectionsEntry
    MAX-ACCESS not-accessible
    STATUS     current
    DESCRIPTION
            ""
    INDEX {
            hmStatusPppoeServerConnectionsEntryChannel,
            hmStatusPppoeServerConnectionsEntryMacAddress
          }
    ::= { hmStatusPppoeServerConnectionsTable 1 }

HmStatusPppoeServerConnectionsEntry ::= SEQUENCE {
            hmStatusPppoeServerConnectionsEntryChannel DisplayString,
            hmStatusPppoeServerConnectionsEntryMacAddress DisplayString,
            hmStatusPppoeServerConnectionsEntryState INTEGER,
            hmStatusPppoeServerConnectionsEntryLastError INTEGER,
            hmStatusPppoeServerConnectionsEntryShTime Integer32,
            hmStatusPppoeServerConnectionsEntryPeerAddress IpAddress,
            hmStatusPppoeServerConnectionsEntryConnTime Gauge32
    }

-- {COLUMN} 1.3.6.1.4.1.248.32.18.1.52.9.1.1
hmStatusPppoeServerConnectionsEntryChannel OBJECT-TYPE
    SYNTAX     DisplayString (SIZE(0..16))
    MAX-ACCESS read-only
    STATUS     current
    DESCRIPTION
            "-- empty --"
    ::= { hmStatusPppoeServerConnectionsEntry 1 }

-- {COLUMN} 1.3.6.1.4.1.248.32.18.1.52.9.1.2
hmStatusPppoeServerConnectionsEntryMacAddress OBJECT-TYPE
    SYNTAX     DisplayString (SIZE(0..12))
    MAX-ACCESS read-only
    STATUS     current
    DESCRIPTION
            "-- empty --"
    ::= { hmStatusPppoeServerConnectionsEntry 2 }

-- {COLUMN} 1.3.6.1.4.1.248.32.18.1.52.9.1.3
hmStatusPppoeServerConnectionsEntryState OBJECT-TYPE
    SYNTAX     INTEGER {
                  eInit (0),
                  eSetupWan (1),
                  eReady (2),
                  eWaitForCb (3),
                  eDial (4),
                  eIncomingCall (5),
                  eProtocol (6),
                  eConnection (7),
                  eDisconnecting (8),
                  eCallBack (9),
                  eBundleConnect (10),
                  eProtocol2 (11),
                  eReserved (12),
                  eBundle (13)
            }
    MAX-ACCESS read-only
    STATUS     current
    DESCRIPTION
            "-- empty --"
    ::= { hmStatusPppoeServerConnectionsEntry 3 }

-- {COLUMN} 1.3.6.1.4.1.248.32.18.1.52.9.1.4
hmStatusPppoeServerConnectionsEntryLastError OBJECT-TYPE
    SYNTAX     INTEGER {
                  eNone (0),
                  eRemoteDoubled (267),
                  eIcmpConnError (275),
                  eDhcpTimeout (277),
                  ePptpNoResponse (278),
                  eVpnNoResponse (279),
                  eArpNoResponse (280),
                  ePptpNoChannel (513),
                  ePptpBadFormat (514),
                  ePptpBadValue (515),
                  ePptpNoRessource (516),
                  ePptpBadCallId (517),
                  ePptpGenError (518),
                  eRemoteDisconnected (17153),
                  eManualDisconnect (17154),
                  eShortholdExpired (17155),
                  ePhysicalDisconnected (17156),
                  eInvalidPhysicalChannel (17157),
                  eDynamicVpnReconnect (17158),
                  eConfigurationChanged (17159),
                  eRemovedFromConfig (17160),
                  eLcpRejected (32768),
                  eAuthError (32769),
                  eAuthRejected (32770),
                  eLcpConnError (32771),
                  ePapRejected (32784),
                  ePapRxTimeout (32785),
                  ePapTxTimeout (32786),
                  eWrongPapReq (32787),
                  ePapNakReceived (32788),
                  eUnknPapPeer (32789),
                  eChapRejected (32800),
                  eChapRxTimeout (32801),
                  eChapTxTimeout (32802),
                  eWrongChapResp (32803),
                  eChapFailRecvd (32804),
                  eUnknChapPeer (32805),
                  eIpxcpRejected (32816),
                  eWrongIpxcpNet (32817),
                  eIpxcpNetReject (32818),
                  eIpxcpRouteUnkn (32819),
                  eIpcpRejected (32832),
                  eCcpRejected (32848),
                  eNoNcpAvailable (33008)
            }
    MAX-ACCESS read-write
    STATUS     current
    DESCRIPTION
            "-- empty --"
    ::= { hmStatusPppoeServerConnectionsEntry 4 }

-- {COLUMN} 1.3.6.1.4.1.248.32.18.1.52.9.1.5
hmStatusPppoeServerConnectionsEntryShTime OBJECT-TYPE
    SYNTAX     Integer32 (0..65535)
    MAX-ACCESS read-only
    STATUS     current
    DESCRIPTION
            "-- empty --"
    ::= { hmStatusPppoeServerConnectionsEntry 5 }

-- {COLUMN} 1.3.6.1.4.1.248.32.18.1.52.9.1.6
hmStatusPppoeServerConnectionsEntryPeerAddress OBJECT-TYPE
    SYNTAX     IpAddress
    MAX-ACCESS read-only
    STATUS     current
    DESCRIPTION
            "-- empty --"
    ::= { hmStatusPppoeServerConnectionsEntry 6 }

-- {COLUMN} 1.3.6.1.4.1.248.32.18.1.52.9.1.7
hmStatusPppoeServerConnectionsEntryConnTime OBJECT-TYPE
    SYNTAX     Gauge32
    MAX-ACCESS read-only
    STATUS     current
    DESCRIPTION
            "-- empty --"
    ::= { hmStatusPppoeServerConnectionsEntry 7 }

-- {SCALAR} 1.3.6.1.4.1.248.32.18.1.52.10
hmStatusPppoeServerNumConnections OBJECT-TYPE
    SYNTAX     Integer32 (0..2147483647)
    MAX-ACCESS read-only
    STATUS     current
    DESCRIPTION
            "-- empty --"
    ::= { hmStatusPppoeServer 10 }

-- {SCALAR} 1.3.6.1.4.1.248.32.18.1.52.11
hmStatusPppoeServerDeleteValues OBJECT-TYPE
    SYNTAX     DisplayString
    MAX-ACCESS read-write
    STATUS     current
    DESCRIPTION
            "-- empty --"
    ::= { hmStatusPppoeServer 11 }

-- {NODE} 1.3.6.1.4.1.248.32.18.1.54
hmStatusUsb OBJECT IDENTIFIER ::= { hmStatus 54 }

-- {TABLE} 1.3.6.1.4.1.248.32.18.1.54.1
hmStatusUsbDevicesTable OBJECT-TYPE
    SYNTAX     SEQUENCE OF HmStatusUsbDevicesEntry
    MAX-ACCESS not-accessible
    STATUS     current
    DESCRIPTION
            "-- empty --"
    ::= { hmStatusUsb 1 }

-- {ROW} 1.3.6.1.4.1.248.32.18.1.54.1.1
hmStatusUsbDevicesEntry OBJECT-TYPE
    SYNTAX     HmStatusUsbDevicesEntry
    MAX-ACCESS not-accessible
    STATUS     current
    DESCRIPTION
            ""
    INDEX {
            hmStatusUsbDevicesEntryBus,
            hmStatusUsbDevicesEntryAddress
          }
    ::= { hmStatusUsbDevicesTable 1 }

HmStatusUsbDevicesEntry ::= SEQUENCE {
            hmStatusUsbDevicesEntryBus DisplayString,
            hmStatusUsbDevicesEntryAddress Integer32,
            hmStatusUsbDevicesEntryVendor DisplayString,
            hmStatusUsbDevicesEntryVendorId Integer32,
            hmStatusUsbDevicesEntryProduct DisplayString,
            hmStatusUsbDevicesEntryProductId Integer32,
            hmStatusUsbDevicesEntryDepth Integer32,
            hmStatusUsbDevicesEntrySpeed Integer32,
            hmStatusUsbDevicesEntryInterfaces Integer32,
            hmStatusUsbDevicesEntryPower Integer32,
            hmStatusUsbDevicesEntryDriver DisplayString,
            hmStatusUsbDevicesEntryParent DisplayString
    }

-- {COLUMN} 1.3.6.1.4.1.248.32.18.1.54.1.1.1
hmStatusUsbDevicesEntryBus OBJECT-TYPE
    SYNTAX     DisplayString (SIZE(0..255))
    MAX-ACCESS read-only
    STATUS     current
    DESCRIPTION
            "-- empty --"
    ::= { hmStatusUsbDevicesEntry 1 }

-- {COLUMN} 1.3.6.1.4.1.248.32.18.1.54.1.1.2
hmStatusUsbDevicesEntryAddress OBJECT-TYPE
    SYNTAX     Integer32 (0..255)
    MAX-ACCESS read-only
    STATUS     current
    DESCRIPTION
            "-- empty --"
    ::= { hmStatusUsbDevicesEntry 2 }

-- {COLUMN} 1.3.6.1.4.1.248.32.18.1.54.1.1.3
hmStatusUsbDevicesEntryVendor OBJECT-TYPE
    SYNTAX     DisplayString (SIZE(0..255))
    MAX-ACCESS read-only
    STATUS     current
    DESCRIPTION
            "-- empty --"
    ::= { hmStatusUsbDevicesEntry 3 }

-- {COLUMN} 1.3.6.1.4.1.248.32.18.1.54.1.1.4
hmStatusUsbDevicesEntryVendorId OBJECT-TYPE
    SYNTAX     Integer32 (0..65535)
    MAX-ACCESS read-only
    STATUS     current
    DESCRIPTION
            "-- empty --"
    ::= { hmStatusUsbDevicesEntry 4 }

-- {COLUMN} 1.3.6.1.4.1.248.32.18.1.54.1.1.5
hmStatusUsbDevicesEntryProduct OBJECT-TYPE
    SYNTAX     DisplayString (SIZE(0..255))
    MAX-ACCESS read-only
    STATUS     current
    DESCRIPTION
            "-- empty --"
    ::= { hmStatusUsbDevicesEntry 5 }

-- {COLUMN} 1.3.6.1.4.1.248.32.18.1.54.1.1.6
hmStatusUsbDevicesEntryProductId OBJECT-TYPE
    SYNTAX     Integer32 (0..65535)
    MAX-ACCESS read-only
    STATUS     current
    DESCRIPTION
            "-- empty --"
    ::= { hmStatusUsbDevicesEntry 6 }

-- {COLUMN} 1.3.6.1.4.1.248.32.18.1.54.1.1.8
hmStatusUsbDevicesEntryDepth OBJECT-TYPE
    SYNTAX     Integer32 (0..255)
    MAX-ACCESS read-only
    STATUS     current
    DESCRIPTION
            "-- empty --"
    ::= { hmStatusUsbDevicesEntry 8 }

-- {COLUMN} 1.3.6.1.4.1.248.32.18.1.54.1.1.9
hmStatusUsbDevicesEntrySpeed OBJECT-TYPE
    SYNTAX     Integer32 (0..255)
    MAX-ACCESS read-only
    STATUS     current
    DESCRIPTION
            "-- empty --"
    ::= { hmStatusUsbDevicesEntry 9 }

-- {COLUMN} 1.3.6.1.4.1.248.32.18.1.54.1.1.10
hmStatusUsbDevicesEntryInterfaces OBJECT-TYPE
    SYNTAX     Integer32 (0..255)
    MAX-ACCESS read-only
    STATUS     current
    DESCRIPTION
            "-- empty --"
    ::= { hmStatusUsbDevicesEntry 10 }

-- {COLUMN} 1.3.6.1.4.1.248.32.18.1.54.1.1.11
hmStatusUsbDevicesEntryPower OBJECT-TYPE
    SYNTAX     Integer32 (0..2147483647)
    MAX-ACCESS read-only
    STATUS     current
    DESCRIPTION
            "-- empty --"
    ::= { hmStatusUsbDevicesEntry 11 }

-- {COLUMN} 1.3.6.1.4.1.248.32.18.1.54.1.1.12
hmStatusUsbDevicesEntryDriver OBJECT-TYPE
    SYNTAX     DisplayString (SIZE(0..255))
    MAX-ACCESS read-only
    STATUS     current
    DESCRIPTION
            "-- empty --"
    ::= { hmStatusUsbDevicesEntry 12 }

-- {COLUMN} 1.3.6.1.4.1.248.32.18.1.54.1.1.13
hmStatusUsbDevicesEntryParent OBJECT-TYPE
    SYNTAX     DisplayString (SIZE(0..255))
    MAX-ACCESS read-only
    STATUS     current
    DESCRIPTION
            "-- empty --"
    ::= { hmStatusUsbDevicesEntry 13 }

-- {SCALAR} 1.3.6.1.4.1.248.32.18.1.54.2
hmStatusUsbReinit OBJECT-TYPE
    SYNTAX     DisplayString
    MAX-ACCESS read-write
    STATUS     current
    DESCRIPTION
            "-- empty --"
    ::= { hmStatusUsb 2 }

-- {TABLE} 1.3.6.1.4.1.248.32.18.1.54.3
hmStatusUsbStatisticsTable OBJECT-TYPE
    SYNTAX     SEQUENCE OF HmStatusUsbStatisticsEntry
    MAX-ACCESS not-accessible
    STATUS     current
    DESCRIPTION
            "-- empty --"
    ::= { hmStatusUsb 3 }

-- {ROW} 1.3.6.1.4.1.248.32.18.1.54.3.1
hmStatusUsbStatisticsEntry OBJECT-TYPE
    SYNTAX     HmStatusUsbStatisticsEntry
    MAX-ACCESS not-accessible
    STATUS     current
    DESCRIPTION
            ""
    INDEX {
            hmStatusUsbStatisticsEntryBus
          }
    ::= { hmStatusUsbStatisticsTable 1 }

HmStatusUsbStatisticsEntry ::= SEQUENCE {
            hmStatusUsbStatisticsEntryBus DisplayString,
            hmStatusUsbStatisticsEntryProduct DisplayString,
            hmStatusUsbStatisticsEntryTransactions Integer32,
            hmStatusUsbStatisticsEntryInRetransmissions Integer32,
            hmStatusUsbStatisticsEntryInBabbles Integer32,
            hmStatusUsbStatisticsEntryInBufferErrors Integer32,
            hmStatusUsbStatisticsEntryOutRetransmissions Integer32,
            hmStatusUsbStatisticsEntryOutBabbles Integer32,
            hmStatusUsbStatisticsEntryOutBufferErrors Integer32
    }

-- {COLUMN} 1.3.6.1.4.1.248.32.18.1.54.3.1.1
hmStatusUsbStatisticsEntryBus OBJECT-TYPE
    SYNTAX     DisplayString (SIZE(0..255))
    MAX-ACCESS read-only
    STATUS     current
    DESCRIPTION
            "-- empty --"
    ::= { hmStatusUsbStatisticsEntry 1 }

-- {COLUMN} 1.3.6.1.4.1.248.32.18.1.54.3.1.2
hmStatusUsbStatisticsEntryProduct OBJECT-TYPE
    SYNTAX     DisplayString (SIZE(0..255))
    MAX-ACCESS read-only
    STATUS     current
    DESCRIPTION
            "-- empty --"
    ::= { hmStatusUsbStatisticsEntry 2 }

-- {COLUMN} 1.3.6.1.4.1.248.32.18.1.54.3.1.3
hmStatusUsbStatisticsEntryTransactions OBJECT-TYPE
    SYNTAX     Integer32 (-2147483648..2147483647)
    MAX-ACCESS read-only
    STATUS     current
    DESCRIPTION
            "-- empty --"
    ::= { hmStatusUsbStatisticsEntry 3 }

-- {COLUMN} 1.3.6.1.4.1.248.32.18.1.54.3.1.10
hmStatusUsbStatisticsEntryInRetransmissions OBJECT-TYPE
    SYNTAX     Integer32 (-2147483648..2147483647)
    MAX-ACCESS read-only
    STATUS     current
    DESCRIPTION
            "-- empty --"
    ::= { hmStatusUsbStatisticsEntry 10 }

-- {COLUMN} 1.3.6.1.4.1.248.32.18.1.54.3.1.11
hmStatusUsbStatisticsEntryInBabbles OBJECT-TYPE
    SYNTAX     Integer32 (-2147483648..2147483647)
    MAX-ACCESS read-only
    STATUS     current
    DESCRIPTION
            "-- empty --"
    ::= { hmStatusUsbStatisticsEntry 11 }

-- {COLUMN} 1.3.6.1.4.1.248.32.18.1.54.3.1.12
hmStatusUsbStatisticsEntryInBufferErrors OBJECT-TYPE
    SYNTAX     Integer32 (-2147483648..2147483647)
    MAX-ACCESS read-only
    STATUS     current
    DESCRIPTION
            "-- empty --"
    ::= { hmStatusUsbStatisticsEntry 12 }

-- {COLUMN} 1.3.6.1.4.1.248.32.18.1.54.3.1.20
hmStatusUsbStatisticsEntryOutRetransmissions OBJECT-TYPE
    SYNTAX     Integer32 (-2147483648..2147483647)
    MAX-ACCESS read-only
    STATUS     current
    DESCRIPTION
            "-- empty --"
    ::= { hmStatusUsbStatisticsEntry 20 }

-- {COLUMN} 1.3.6.1.4.1.248.32.18.1.54.3.1.21
hmStatusUsbStatisticsEntryOutBabbles OBJECT-TYPE
    SYNTAX     Integer32 (-2147483648..2147483647)
    MAX-ACCESS read-only
    STATUS     current
    DESCRIPTION
            "-- empty --"
    ::= { hmStatusUsbStatisticsEntry 21 }

-- {COLUMN} 1.3.6.1.4.1.248.32.18.1.54.3.1.22
hmStatusUsbStatisticsEntryOutBufferErrors OBJECT-TYPE
    SYNTAX     Integer32 (-2147483648..2147483647)
    MAX-ACCESS read-only
    STATUS     current
    DESCRIPTION
            "-- empty --"
    ::= { hmStatusUsbStatisticsEntry 22 }

-- {SCALAR} 1.3.6.1.4.1.248.32.18.1.54.4
hmStatusUsbClearStatistics OBJECT-TYPE
    SYNTAX     DisplayString
    MAX-ACCESS read-write
    STATUS     current
    DESCRIPTION
            "-- empty --"
    ::= { hmStatusUsb 4 }

-- {SCALAR} 1.3.6.1.4.1.248.32.18.1.54.5
hmStatusUsbQueryHubStatus OBJECT-TYPE
    SYNTAX     DisplayString
    MAX-ACCESS read-write
    STATUS     current
    DESCRIPTION
            "-- empty --"
    ::= { hmStatusUsb 5 }

-- {NODE} 1.3.6.1.4.1.248.32.18.1.56
hmStatusAccounting OBJECT IDENTIFIER ::= { hmStatus 56 }

-- {TABLE} 1.3.6.1.4.1.248.32.18.1.56.1
hmStatusAccountingCurrentUserTable OBJECT-TYPE
    SYNTAX     SEQUENCE OF HmStatusAccountingCurrentUserEntry
    MAX-ACCESS not-accessible
    STATUS     current
    DESCRIPTION
            "-- empty --"
    ::= { hmStatusAccounting 1 }

-- {ROW} 1.3.6.1.4.1.248.32.18.1.56.1.1
hmStatusAccountingCurrentUserEntry OBJECT-TYPE
    SYNTAX     HmStatusAccountingCurrentUserEntry
    MAX-ACCESS not-accessible
    STATUS     current
    DESCRIPTION
            ""
    INDEX {
            hmStatusAccountingCurrentUserEntryUsername,
            hmStatusAccountingCurrentUserEntryMacAddress,
            hmStatusAccountingCurrentUserEntryPeer,
            hmStatusAccountingCurrentUserEntryConnType
          }
    ::= { hmStatusAccountingCurrentUserTable 1 }

HmStatusAccountingCurrentUserEntry ::= SEQUENCE {
            hmStatusAccountingCurrentUserEntryUsername DisplayString,
            hmStatusAccountingCurrentUserEntryMacAddress DisplayString,
            hmStatusAccountingCurrentUserEntryPeer DisplayString,
            hmStatusAccountingCurrentUserEntryConnType INTEGER,
            hmStatusAccountingCurrentUserEntryRxKbytes Integer32,
            hmStatusAccountingCurrentUserEntryTxKbytes Integer32,
            hmStatusAccountingCurrentUserEntryTotalTime Gauge32,
            hmStatusAccountingCurrentUserEntryConnections Integer32
    }

-- {COLUMN} 1.3.6.1.4.1.248.32.18.1.56.1.1.1
hmStatusAccountingCurrentUserEntryUsername OBJECT-TYPE
    SYNTAX     DisplayString (SIZE(0..28))
    MAX-ACCESS read-only
    STATUS     current
    DESCRIPTION
            "-- empty --"
    ::= { hmStatusAccountingCurrentUserEntry 1 }

-- {COLUMN} 1.3.6.1.4.1.248.32.18.1.56.1.1.2
hmStatusAccountingCurrentUserEntryMacAddress OBJECT-TYPE
    SYNTAX     DisplayString (SIZE(0..255))
    MAX-ACCESS read-only
    STATUS     current
    DESCRIPTION
            "-- empty --"
    ::= { hmStatusAccountingCurrentUserEntry 2 }

-- {COLUMN} 1.3.6.1.4.1.248.32.18.1.56.1.1.3
hmStatusAccountingCurrentUserEntryPeer OBJECT-TYPE
    SYNTAX     DisplayString (SIZE(0..16))
    MAX-ACCESS read-only
    STATUS     current
    DESCRIPTION
            "-- empty --"
    ::= { hmStatusAccountingCurrentUserEntry 3 }

-- {COLUMN} 1.3.6.1.4.1.248.32.18.1.56.1.1.4
hmStatusAccountingCurrentUserEntryConnType OBJECT-TYPE
    SYNTAX     INTEGER {
                  eUnknown (0),
                  eDialUp (1),
                  eLeasedLine (2),
                  eDslLine (4),
                  eVpnConn (7),
                  ePptpConn (8),
                  eL2tpConn (9),
                  eDsLiteConn (10),
                  eGreConn (11)
            }
    MAX-ACCESS read-only
    STATUS     current
    DESCRIPTION
            "-- empty --"
    ::= { hmStatusAccountingCurrentUserEntry 4 }

-- {COLUMN} 1.3.6.1.4.1.248.32.18.1.56.1.1.5
hmStatusAccountingCurrentUserEntryRxKbytes OBJECT-TYPE
    SYNTAX     Integer32 (0..2147483647)
    MAX-ACCESS read-only
    STATUS     current
    DESCRIPTION
            "-- empty --"
    ::= { hmStatusAccountingCurrentUserEntry 5 }

-- {COLUMN} 1.3.6.1.4.1.248.32.18.1.56.1.1.6
hmStatusAccountingCurrentUserEntryTxKbytes OBJECT-TYPE
    SYNTAX     Integer32 (0..2147483647)
    MAX-ACCESS read-only
    STATUS     current
    DESCRIPTION
            "-- empty --"
    ::= { hmStatusAccountingCurrentUserEntry 6 }

-- {COLUMN} 1.3.6.1.4.1.248.32.18.1.56.1.1.8
hmStatusAccountingCurrentUserEntryTotalTime OBJECT-TYPE
    SYNTAX     Gauge32
    MAX-ACCESS read-only
    STATUS     current
    DESCRIPTION
            "-- empty --"
    ::= { hmStatusAccountingCurrentUserEntry 8 }

-- {COLUMN} 1.3.6.1.4.1.248.32.18.1.56.1.1.9
hmStatusAccountingCurrentUserEntryConnections OBJECT-TYPE
    SYNTAX     Integer32 (0..2147483647)
    MAX-ACCESS read-only
    STATUS     current
    DESCRIPTION
            "-- empty --"
    ::= { hmStatusAccountingCurrentUserEntry 9 }

-- {TABLE} 1.3.6.1.4.1.248.32.18.1.56.2
hmStatusAccountingAccountingListTable OBJECT-TYPE
    SYNTAX     SEQUENCE OF HmStatusAccountingAccountingListEntry
    MAX-ACCESS not-accessible
    STATUS     current
    DESCRIPTION
            "-- empty --"
    ::= { hmStatusAccounting 2 }

-- {ROW} 1.3.6.1.4.1.248.32.18.1.56.2.1
hmStatusAccountingAccountingListEntry OBJECT-TYPE
    SYNTAX     HmStatusAccountingAccountingListEntry
    MAX-ACCESS not-accessible
    STATUS     current
    DESCRIPTION
            ""
    INDEX {
            hmStatusAccountingAccountingListEntryUsername,
            hmStatusAccountingAccountingListEntryMacAddress,
            hmStatusAccountingAccountingListEntryPeer,
            hmStatusAccountingAccountingListEntryConnType
          }
    ::= { hmStatusAccountingAccountingListTable 1 }

HmStatusAccountingAccountingListEntry ::= SEQUENCE {
            hmStatusAccountingAccountingListEntryUsername DisplayString,
            hmStatusAccountingAccountingListEntryMacAddress DisplayString,
            hmStatusAccountingAccountingListEntryPeer DisplayString,
            hmStatusAccountingAccountingListEntryConnType INTEGER,
            hmStatusAccountingAccountingListEntryRxKbytes Integer32,
            hmStatusAccountingAccountingListEntryTxKbytes Integer32,
            hmStatusAccountingAccountingListEntryTotalTime Gauge32,
            hmStatusAccountingAccountingListEntryConnections Integer32
    }

-- {COLUMN} 1.3.6.1.4.1.248.32.18.1.56.2.1.1
hmStatusAccountingAccountingListEntryUsername OBJECT-TYPE
    SYNTAX     DisplayString (SIZE(0..28))
    MAX-ACCESS read-only
    STATUS     current
    DESCRIPTION
            "-- empty --"
    ::= { hmStatusAccountingAccountingListEntry 1 }

-- {COLUMN} 1.3.6.1.4.1.248.32.18.1.56.2.1.2
hmStatusAccountingAccountingListEntryMacAddress OBJECT-TYPE
    SYNTAX     DisplayString (SIZE(0..255))
    MAX-ACCESS read-only
    STATUS     current
    DESCRIPTION
            "-- empty --"
    ::= { hmStatusAccountingAccountingListEntry 2 }

-- {COLUMN} 1.3.6.1.4.1.248.32.18.1.56.2.1.3
hmStatusAccountingAccountingListEntryPeer OBJECT-TYPE
    SYNTAX     DisplayString (SIZE(0..16))
    MAX-ACCESS read-only
    STATUS     current
    DESCRIPTION
            "-- empty --"
    ::= { hmStatusAccountingAccountingListEntry 3 }

-- {COLUMN} 1.3.6.1.4.1.248.32.18.1.56.2.1.4
hmStatusAccountingAccountingListEntryConnType OBJECT-TYPE
    SYNTAX     INTEGER {
                  eUnknown (0),
                  eDialUp (1),
                  eLeasedLine (2),
                  eDslLine (4),
                  eVpnConn (7),
                  ePptpConn (8),
                  eL2tpConn (9),
                  eDsLiteConn (10),
                  eGreConn (11)
            }
    MAX-ACCESS read-only
    STATUS     current
    DESCRIPTION
            "-- empty --"
    ::= { hmStatusAccountingAccountingListEntry 4 }

-- {COLUMN} 1.3.6.1.4.1.248.32.18.1.56.2.1.5
hmStatusAccountingAccountingListEntryRxKbytes OBJECT-TYPE
    SYNTAX     Integer32 (0..2147483647)
    MAX-ACCESS read-only
    STATUS     current
    DESCRIPTION
            "-- empty --"
    ::= { hmStatusAccountingAccountingListEntry 5 }

-- {COLUMN} 1.3.6.1.4.1.248.32.18.1.56.2.1.6
hmStatusAccountingAccountingListEntryTxKbytes OBJECT-TYPE
    SYNTAX     Integer32 (0..2147483647)
    MAX-ACCESS read-only
    STATUS     current
    DESCRIPTION
            "-- empty --"
    ::= { hmStatusAccountingAccountingListEntry 6 }

-- {COLUMN} 1.3.6.1.4.1.248.32.18.1.56.2.1.8
hmStatusAccountingAccountingListEntryTotalTime OBJECT-TYPE
    SYNTAX     Gauge32
    MAX-ACCESS read-only
    STATUS     current
    DESCRIPTION
            "-- empty --"
    ::= { hmStatusAccountingAccountingListEntry 8 }

-- {COLUMN} 1.3.6.1.4.1.248.32.18.1.56.2.1.9
hmStatusAccountingAccountingListEntryConnections OBJECT-TYPE
    SYNTAX     Integer32 (0..2147483647)
    MAX-ACCESS read-only
    STATUS     current
    DESCRIPTION
            "-- empty --"
    ::= { hmStatusAccountingAccountingListEntry 9 }

-- {TABLE} 1.3.6.1.4.1.248.32.18.1.56.3
hmStatusAccountingLastSnapshotTable OBJECT-TYPE
    SYNTAX     SEQUENCE OF HmStatusAccountingLastSnapshotEntry
    MAX-ACCESS not-accessible
    STATUS     current
    DESCRIPTION
            "-- empty --"
    ::= { hmStatusAccounting 3 }

-- {ROW} 1.3.6.1.4.1.248.32.18.1.56.3.1
hmStatusAccountingLastSnapshotEntry OBJECT-TYPE
    SYNTAX     HmStatusAccountingLastSnapshotEntry
    MAX-ACCESS not-accessible
    STATUS     current
    DESCRIPTION
            ""
    INDEX {
            hmStatusAccountingLastSnapshotEntryUsername,
            hmStatusAccountingLastSnapshotEntryMacAddress,
            hmStatusAccountingLastSnapshotEntryPeer,
            hmStatusAccountingLastSnapshotEntryConnType
          }
    ::= { hmStatusAccountingLastSnapshotTable 1 }

HmStatusAccountingLastSnapshotEntry ::= SEQUENCE {
            hmStatusAccountingLastSnapshotEntryUsername DisplayString,
            hmStatusAccountingLastSnapshotEntryMacAddress DisplayString,
            hmStatusAccountingLastSnapshotEntryPeer DisplayString,
            hmStatusAccountingLastSnapshotEntryConnType INTEGER,
            hmStatusAccountingLastSnapshotEntryRxKbytes Integer32,
            hmStatusAccountingLastSnapshotEntryTxKbytes Integer32,
            hmStatusAccountingLastSnapshotEntryTotalTime Gauge32,
            hmStatusAccountingLastSnapshotEntryConnections Integer32
    }

-- {COLUMN} 1.3.6.1.4.1.248.32.18.1.56.3.1.1
hmStatusAccountingLastSnapshotEntryUsername OBJECT-TYPE
    SYNTAX     DisplayString (SIZE(0..28))
    MAX-ACCESS read-only
    STATUS     current
    DESCRIPTION
            "-- empty --"
    ::= { hmStatusAccountingLastSnapshotEntry 1 }

-- {COLUMN} 1.3.6.1.4.1.248.32.18.1.56.3.1.2
hmStatusAccountingLastSnapshotEntryMacAddress OBJECT-TYPE
    SYNTAX     DisplayString (SIZE(0..255))
    MAX-ACCESS read-only
    STATUS     current
    DESCRIPTION
            "-- empty --"
    ::= { hmStatusAccountingLastSnapshotEntry 2 }

-- {COLUMN} 1.3.6.1.4.1.248.32.18.1.56.3.1.3
hmStatusAccountingLastSnapshotEntryPeer OBJECT-TYPE
    SYNTAX     DisplayString (SIZE(0..16))
    MAX-ACCESS read-only
    STATUS     current
    DESCRIPTION
            "-- empty --"
    ::= { hmStatusAccountingLastSnapshotEntry 3 }

-- {COLUMN} 1.3.6.1.4.1.248.32.18.1.56.3.1.4
hmStatusAccountingLastSnapshotEntryConnType OBJECT-TYPE
    SYNTAX     INTEGER {
                  eUnknown (0),
                  eDialUp (1),
                  eLeasedLine (2),
                  eDslLine (4),
                  eVpnConn (7),
                  ePptpConn (8),
                  eL2tpConn (9),
                  eDsLiteConn (10),
                  eGreConn (11)
            }
    MAX-ACCESS read-only
    STATUS     current
    DESCRIPTION
            "-- empty --"
    ::= { hmStatusAccountingLastSnapshotEntry 4 }

-- {COLUMN} 1.3.6.1.4.1.248.32.18.1.56.3.1.5
hmStatusAccountingLastSnapshotEntryRxKbytes OBJECT-TYPE
    SYNTAX     Integer32 (0..2147483647)
    MAX-ACCESS read-only
    STATUS     current
    DESCRIPTION
            "-- empty --"
    ::= { hmStatusAccountingLastSnapshotEntry 5 }

-- {COLUMN} 1.3.6.1.4.1.248.32.18.1.56.3.1.6
hmStatusAccountingLastSnapshotEntryTxKbytes OBJECT-TYPE
    SYNTAX     Integer32 (0..2147483647)
    MAX-ACCESS read-only
    STATUS     current
    DESCRIPTION
            "-- empty --"
    ::= { hmStatusAccountingLastSnapshotEntry 6 }

-- {COLUMN} 1.3.6.1.4.1.248.32.18.1.56.3.1.8
hmStatusAccountingLastSnapshotEntryTotalTime OBJECT-TYPE
    SYNTAX     Gauge32
    MAX-ACCESS read-only
    STATUS     current
    DESCRIPTION
            "-- empty --"
    ::= { hmStatusAccountingLastSnapshotEntry 8 }

-- {COLUMN} 1.3.6.1.4.1.248.32.18.1.56.3.1.9
hmStatusAccountingLastSnapshotEntryConnections OBJECT-TYPE
    SYNTAX     Integer32 (0..2147483647)
    MAX-ACCESS read-only
    STATUS     current
    DESCRIPTION
            "-- empty --"
    ::= { hmStatusAccountingLastSnapshotEntry 9 }

-- {SCALAR} 1.3.6.1.4.1.248.32.18.1.56.4
hmStatusAccountingDeleteValues OBJECT-TYPE
    SYNTAX     DisplayString
    MAX-ACCESS read-write
    STATUS     current
    DESCRIPTION
            "-- empty --"
    ::= { hmStatusAccounting 4 }

-- {TABLE} 1.3.6.1.4.1.248.32.18.1.56.5
hmStatusAccountingTimeLastSnapshotTable OBJECT-TYPE
    SYNTAX     SEQUENCE OF HmStatusAccountingTimeLastSnapshotEntry
    MAX-ACCESS not-accessible
    STATUS     current
    DESCRIPTION
            "-- empty --"
    ::= { hmStatusAccounting 5 }

-- {ROW} 1.3.6.1.4.1.248.32.18.1.56.5.1
hmStatusAccountingTimeLastSnapshotEntry OBJECT-TYPE
    SYNTAX     HmStatusAccountingTimeLastSnapshotEntry
    MAX-ACCESS not-accessible
    STATUS     current
    DESCRIPTION
            ""
    INDEX {
            hmStatusAccountingTimeLastSnapshotEntrySystemTime
          }
    ::= { hmStatusAccountingTimeLastSnapshotTable 1 }

HmStatusAccountingTimeLastSnapshotEntry ::= SEQUENCE {
            hmStatusAccountingTimeLastSnapshotEntrySystemTime Counter32
    }

-- {COLUMN} 1.3.6.1.4.1.248.32.18.1.56.5.1.1
hmStatusAccountingTimeLastSnapshotEntrySystemTime OBJECT-TYPE
    SYNTAX     Counter32
    MAX-ACCESS read-only
    STATUS     current
    DESCRIPTION
            "-- empty --"
    ::= { hmStatusAccountingTimeLastSnapshotEntry 1 }

-- {NODE} 1.3.6.1.4.1.248.32.18.1.59
hmStatusWtpMngmt OBJECT IDENTIFIER ::= { hmStatus 59 }

-- {TABLE} 1.3.6.1.4.1.248.32.18.1.59.1
hmStatusWtpMngmtApConnectionsTable OBJECT-TYPE
    SYNTAX     SEQUENCE OF HmStatusWtpMngmtApConnectionsEntry
    MAX-ACCESS not-accessible
    STATUS     current
    DESCRIPTION
            "-- empty --"
    ::= { hmStatusWtpMngmt 1 }

-- {ROW} 1.3.6.1.4.1.248.32.18.1.59.1.1
hmStatusWtpMngmtApConnectionsEntry OBJECT-TYPE
    SYNTAX     HmStatusWtpMngmtApConnectionsEntry
    MAX-ACCESS not-accessible
    STATUS     current
    DESCRIPTION
            ""
    INDEX {
            hmStatusWtpMngmtApConnectionsEntryConnId
          }
    ::= { hmStatusWtpMngmtApConnectionsTable 1 }

HmStatusWtpMngmtApConnectionsEntry ::= SEQUENCE {
            hmStatusWtpMngmtApConnectionsEntryConnId Integer32,
            hmStatusWtpMngmtApConnectionsEntryIpAddress IpAddress,
            hmStatusWtpMngmtApConnectionsEntryPort Integer32,
            hmStatusWtpMngmtApConnectionsEntryResptime Integer32,
            hmStatusWtpMngmtApConnectionsEntryName DisplayString,
            hmStatusWtpMngmtApConnectionsEntryState INTEGER,
            hmStatusWtpMngmtApConnectionsEntryResult INTEGER,
            hmStatusWtpMngmtApConnectionsEntryPriority INTEGER,
            hmStatusWtpMngmtApConnectionsEntryUtilisation DisplayString,
            hmStatusWtpMngmtApConnectionsEntryFirmwareVersion DisplayString,
            hmStatusWtpMngmtApConnectionsEntryPmtu Integer32,
            hmStatusWtpMngmtApConnectionsEntryDscpForControlPackets INTEGER,
            hmStatusWtpMngmtApConnectionsEntryDscpForDataPackets INTEGER,
            hmStatusWtpMngmtApConnectionsEntryPreference Integer32,
            hmStatusWtpMngmtApConnectionsEntryCpuLoad300sPercent DisplayString
    }

-- {COLUMN} 1.3.6.1.4.1.248.32.18.1.59.1.1.1
hmStatusWtpMngmtApConnectionsEntryConnId OBJECT-TYPE
    SYNTAX     Integer32 (0..2147483647)
    MAX-ACCESS read-only
    STATUS     current
    DESCRIPTION
            "-- empty --"
    ::= { hmStatusWtpMngmtApConnectionsEntry 1 }

-- {COLUMN} 1.3.6.1.4.1.248.32.18.1.59.1.1.2
hmStatusWtpMngmtApConnectionsEntryIpAddress OBJECT-TYPE
    SYNTAX     IpAddress
    MAX-ACCESS read-only
    STATUS     current
    DESCRIPTION
            "-- empty --"
    ::= { hmStatusWtpMngmtApConnectionsEntry 2 }

-- {COLUMN} 1.3.6.1.4.1.248.32.18.1.59.1.1.3
hmStatusWtpMngmtApConnectionsEntryPort OBJECT-TYPE
    SYNTAX     Integer32 (0..65535)
    MAX-ACCESS read-only
    STATUS     current
    DESCRIPTION
            "-- empty --"
    ::= { hmStatusWtpMngmtApConnectionsEntry 3 }

-- {COLUMN} 1.3.6.1.4.1.248.32.18.1.59.1.1.4
hmStatusWtpMngmtApConnectionsEntryResptime OBJECT-TYPE
    SYNTAX     Integer32 (0..2147483647)
    MAX-ACCESS read-only
    STATUS     current
    DESCRIPTION
            "-- empty --"
    ::= { hmStatusWtpMngmtApConnectionsEntry 4 }

-- {COLUMN} 1.3.6.1.4.1.248.32.18.1.59.1.1.5
hmStatusWtpMngmtApConnectionsEntryName OBJECT-TYPE
    SYNTAX     DisplayString (SIZE(0..31))
    MAX-ACCESS read-only
    STATUS     current
    DESCRIPTION
            "-- empty --"
    ::= { hmStatusWtpMngmtApConnectionsEntry 5 }

-- {COLUMN} 1.3.6.1.4.1.248.32.18.1.59.1.1.6
hmStatusWtpMngmtApConnectionsEntryState OBJECT-TYPE
    SYNTAX     INTEGER {
                  eUnknown (0),
                  eIdle (5),
                  eDiscovery (10),
                  eDtlsSetup (15),
                  eJoin (20),
                  eConfigure (25),
                  eImageData (30),
                  eReset (35),
                  eDtlsTeardown (40),
                  eSulking (45),
                  eRun (100)
            }
    MAX-ACCESS read-only
    STATUS     current
    DESCRIPTION
            "-- empty --"
    ::= { hmStatusWtpMngmtApConnectionsEntry 6 }

-- {COLUMN} 1.3.6.1.4.1.248.32.18.1.59.1.1.7
hmStatusWtpMngmtApConnectionsEntryResult OBJECT-TYPE
    SYNTAX     INTEGER {
                  eSuccess (0),
                  eFailure (1),
                  eSuccessNat (2),
                  eJoinFailUnspecified (3),
                  eJoinFailResourceDepletion (4),
                  eJoinFailUnknwnSrc (5),
                  eJoinFailIncorrectData (6),
                  eJoinFailSessionIdInUse (7),
                  eJoinFailWtpNotSupported (8),
                  eJoinFailBindingNotSupp (9),
                  eResetFailUnableToReset (10),
                  eResetFailFirmwWriteErr (11),
                  eConfigurationErrorServProvAnyhow (12),
                  eConfigurationErrorServNotProv (13),
                  eImageDataErrorChecksum (14),
                  eImageDataErrorLength (15),
                  eImageDataErrorOther (16),
                  eImageDataErrorAlrPresent (17),
                  eMessageUnexpectedInvalid (18),
                  eMessageUnexpectedUnrecognized (19),
                  eFailMissingMandMsgElem (20),
                  eFailUnrecognizedMsgElem (21),
                  eUnsupportedLoaderVersion (300),
                  eUnsupportedFirmwareVersion (301),
                  eUnknown (302),
                  eJoinFailAlreadyConnected (303)
            }
    MAX-ACCESS read-only
    STATUS     current
    DESCRIPTION
            "-- empty --"
    ::= { hmStatusWtpMngmtApConnectionsEntry 7 }

-- {COLUMN} 1.3.6.1.4.1.248.32.18.1.59.1.1.8
hmStatusWtpMngmtApConnectionsEntryPriority OBJECT-TYPE
    SYNTAX     INTEGER {
                  eUnspec (0),
                  ePrimary (1),
                  eSecondary (2)
            }
    MAX-ACCESS read-only
    STATUS     current
    DESCRIPTION
            "-- empty --"
    ::= { hmStatusWtpMngmtApConnectionsEntry 8 }

-- {COLUMN} 1.3.6.1.4.1.248.32.18.1.59.1.1.9
hmStatusWtpMngmtApConnectionsEntryUtilisation OBJECT-TYPE
    SYNTAX     DisplayString (SIZE(0..6))
    MAX-ACCESS read-only
    STATUS     current
    DESCRIPTION
            "-- empty --"
    ::= { hmStatusWtpMngmtApConnectionsEntry 9 }

-- {COLUMN} 1.3.6.1.4.1.248.32.18.1.59.1.1.10
hmStatusWtpMngmtApConnectionsEntryFirmwareVersion OBJECT-TYPE
    SYNTAX     DisplayString (SIZE(0..31))
    MAX-ACCESS read-only
    STATUS     current
    DESCRIPTION
            "-- empty --"
    ::= { hmStatusWtpMngmtApConnectionsEntry 10 }

-- {COLUMN} 1.3.6.1.4.1.248.32.18.1.59.1.1.11
hmStatusWtpMngmtApConnectionsEntryPmtu OBJECT-TYPE
    SYNTAX     Integer32 (0..2147483647)
    MAX-ACCESS read-only
    STATUS     current
    DESCRIPTION
            "-- empty --"
    ::= { hmStatusWtpMngmtApConnectionsEntry 11 }

-- {COLUMN} 1.3.6.1.4.1.248.32.18.1.59.1.1.12
hmStatusWtpMngmtApConnectionsEntryDscpForControlPackets OBJECT-TYPE
    SYNTAX     INTEGER {
                  eBestEffort (0),
                  eAssuredForwarding11 (40),
                  eAssuredForwarding12 (48),
                  eAssuredForwarding13 (56),
                  eAssuredForwarding21 (72),
                  eAssuredForwarding22 (80),
                  eAssuredForwarding23 (88),
                  eAssuredForwarding31 (104),
                  eAssuredForwarding32 (112),
                  eAssuredForwarding33 (120),
                  eAssuredForwarding41 (136),
                  eAssuredForwarding42 (144),
                  eAssuredForwarding43 (152),
                  eExpeditedForwarding (184)
            }
    MAX-ACCESS read-only
    STATUS     current
    DESCRIPTION
            "-- empty --"
    ::= { hmStatusWtpMngmtApConnectionsEntry 12 }

-- {COLUMN} 1.3.6.1.4.1.248.32.18.1.59.1.1.13
hmStatusWtpMngmtApConnectionsEntryDscpForDataPackets OBJECT-TYPE
    SYNTAX     INTEGER {
                  eBestEffort (0),
                  eAssuredForwarding11 (40),
                  eAssuredForwarding12 (48),
                  eAssuredForwarding13 (56),
                  eAssuredForwarding21 (72),
                  eAssuredForwarding22 (80),
                  eAssuredForwarding23 (88),
                  eAssuredForwarding31 (104),
                  eAssuredForwarding32 (112),
                  eAssuredForwarding33 (120),
                  eAssuredForwarding41 (136),
                  eAssuredForwarding42 (144),
                  eAssuredForwarding43 (152),
                  eExpeditedForwarding (184)
            }
    MAX-ACCESS read-only
    STATUS     current
    DESCRIPTION
            "-- empty --"
    ::= { hmStatusWtpMngmtApConnectionsEntry 13 }

-- {COLUMN} 1.3.6.1.4.1.248.32.18.1.59.1.1.14
hmStatusWtpMngmtApConnectionsEntryPreference OBJECT-TYPE
    SYNTAX     Integer32 (0..255)
    MAX-ACCESS read-only
    STATUS     current
    DESCRIPTION
            "-- empty --"
    ::= { hmStatusWtpMngmtApConnectionsEntry 14 }

-- {COLUMN} 1.3.6.1.4.1.248.32.18.1.59.1.1.15
hmStatusWtpMngmtApConnectionsEntryCpuLoad300sPercent OBJECT-TYPE
    SYNTAX     DisplayString (SIZE(0..7))
    MAX-ACCESS read-only
    STATUS     current
    DESCRIPTION
            "-- empty --"
    ::= { hmStatusWtpMngmtApConnectionsEntry 15 }

-- {TABLE} 1.3.6.1.4.1.248.32.18.1.59.99
hmStatusWtpMngmtGlobalconfigTable OBJECT-TYPE
    SYNTAX     SEQUENCE OF HmStatusWtpMngmtGlobalconfigEntry
    MAX-ACCESS not-accessible
    STATUS     current
    DESCRIPTION
            "-- empty --"
    ::= { hmStatusWtpMngmt 99 }

-- {ROW} 1.3.6.1.4.1.248.32.18.1.59.99.1
hmStatusWtpMngmtGlobalconfigEntry OBJECT-TYPE
    SYNTAX     HmStatusWtpMngmtGlobalconfigEntry
    MAX-ACCESS not-accessible
    STATUS     current
    DESCRIPTION
            ""
    INDEX {
            hmStatusWtpMngmtGlobalconfigEntryVersion
          }
    ::= { hmStatusWtpMngmtGlobalconfigTable 1 }

HmStatusWtpMngmtGlobalconfigEntry ::= SEQUENCE {
            hmStatusWtpMngmtGlobalconfigEntryVersion Integer32,
            hmStatusWtpMngmtGlobalconfigEntryIpAddress IpAddress,
            hmStatusWtpMngmtGlobalconfigEntryNetMask IpAddress,
            hmStatusWtpMngmtGlobalconfigEntryGateway IpAddress,
            hmStatusWtpMngmtGlobalconfigEntryDns1 IpAddress,
            hmStatusWtpMngmtGlobalconfigEntryDns2 IpAddress,
            hmStatusWtpMngmtGlobalconfigEntryMgmtVlanid Integer32,
            hmStatusWtpMngmtGlobalconfigEntryMgmtVlantrunk Integer32,
            hmStatusWtpMngmtGlobalconfigEntryDnsSuffix DisplayString
    }

-- {COLUMN} 1.3.6.1.4.1.248.32.18.1.59.99.1.1
hmStatusWtpMngmtGlobalconfigEntryVersion OBJECT-TYPE
    SYNTAX     Integer32 (0..2147483647)
    MAX-ACCESS read-only
    STATUS     current
    DESCRIPTION
            "-- empty --"
    ::= { hmStatusWtpMngmtGlobalconfigEntry 1 }

-- {COLUMN} 1.3.6.1.4.1.248.32.18.1.59.99.1.2
hmStatusWtpMngmtGlobalconfigEntryIpAddress OBJECT-TYPE
    SYNTAX     IpAddress
    MAX-ACCESS read-only
    STATUS     current
    DESCRIPTION
            "-- empty --"
    ::= { hmStatusWtpMngmtGlobalconfigEntry 2 }

-- {COLUMN} 1.3.6.1.4.1.248.32.18.1.59.99.1.3
hmStatusWtpMngmtGlobalconfigEntryNetMask OBJECT-TYPE
    SYNTAX     IpAddress
    MAX-ACCESS read-only
    STATUS     current
    DESCRIPTION
            "-- empty --"
    ::= { hmStatusWtpMngmtGlobalconfigEntry 3 }

-- {COLUMN} 1.3.6.1.4.1.248.32.18.1.59.99.1.4
hmStatusWtpMngmtGlobalconfigEntryGateway OBJECT-TYPE
    SYNTAX     IpAddress
    MAX-ACCESS read-only
    STATUS     current
    DESCRIPTION
            "-- empty --"
    ::= { hmStatusWtpMngmtGlobalconfigEntry 4 }

-- {COLUMN} 1.3.6.1.4.1.248.32.18.1.59.99.1.5
hmStatusWtpMngmtGlobalconfigEntryDns1 OBJECT-TYPE
    SYNTAX     IpAddress
    MAX-ACCESS read-only
    STATUS     current
    DESCRIPTION
            "-- empty --"
    ::= { hmStatusWtpMngmtGlobalconfigEntry 5 }

-- {COLUMN} 1.3.6.1.4.1.248.32.18.1.59.99.1.6
hmStatusWtpMngmtGlobalconfigEntryDns2 OBJECT-TYPE
    SYNTAX     IpAddress
    MAX-ACCESS read-only
    STATUS     current
    DESCRIPTION
            "-- empty --"
    ::= { hmStatusWtpMngmtGlobalconfigEntry 6 }

-- {COLUMN} 1.3.6.1.4.1.248.32.18.1.59.99.1.8
hmStatusWtpMngmtGlobalconfigEntryMgmtVlanid OBJECT-TYPE
    SYNTAX     Integer32 (0..65535)
    MAX-ACCESS read-only
    STATUS     current
    DESCRIPTION
            "-- empty --"
    ::= { hmStatusWtpMngmtGlobalconfigEntry 8 }

-- {COLUMN} 1.3.6.1.4.1.248.32.18.1.59.99.1.9
hmStatusWtpMngmtGlobalconfigEntryMgmtVlantrunk OBJECT-TYPE
    SYNTAX     Integer32 (0..65535)
    MAX-ACCESS read-only
    STATUS     current
    DESCRIPTION
            "-- empty --"
    ::= { hmStatusWtpMngmtGlobalconfigEntry 9 }

-- {COLUMN} 1.3.6.1.4.1.248.32.18.1.59.99.1.14
hmStatusWtpMngmtGlobalconfigEntryDnsSuffix OBJECT-TYPE
    SYNTAX     DisplayString (SIZE(0..63))
    MAX-ACCESS read-only
    STATUS     current
    DESCRIPTION
            "-- empty --"
    ::= { hmStatusWtpMngmtGlobalconfigEntry 14 }

-- {TABLE} 1.3.6.1.4.1.248.32.18.1.59.100
hmStatusWtpMngmtLastWlcTable OBJECT-TYPE
    SYNTAX     SEQUENCE OF HmStatusWtpMngmtLastWlcEntry
    MAX-ACCESS not-accessible
    STATUS     current
    DESCRIPTION
            "-- empty --"
    ::= { hmStatusWtpMngmt 100 }

-- {ROW} 1.3.6.1.4.1.248.32.18.1.59.100.1
hmStatusWtpMngmtLastWlcEntry OBJECT-TYPE
    SYNTAX     HmStatusWtpMngmtLastWlcEntry
    MAX-ACCESS not-accessible
    STATUS     current
    DESCRIPTION
            ""
    INDEX {
            hmStatusWtpMngmtLastWlcEntryIpAddress
          }
    ::= { hmStatusWtpMngmtLastWlcTable 1 }

HmStatusWtpMngmtLastWlcEntry ::= SEQUENCE {
            hmStatusWtpMngmtLastWlcEntryIpAddress IpAddress,
            hmStatusWtpMngmtLastWlcEntryPort Integer32,
            hmStatusWtpMngmtLastWlcEntryName DisplayString,
            hmStatusWtpMngmtLastWlcEntryRoutetag Integer32,
            hmStatusWtpMngmtLastWlcEntryType Integer32,
            hmStatusWtpMngmtLastWlcEntryMgmtVlanId Integer32
    }

-- {COLUMN} 1.3.6.1.4.1.248.32.18.1.59.100.1.1
hmStatusWtpMngmtLastWlcEntryIpAddress OBJECT-TYPE
    SYNTAX     IpAddress
    MAX-ACCESS read-only
    STATUS     current
    DESCRIPTION
            "-- empty --"
    ::= { hmStatusWtpMngmtLastWlcEntry 1 }

-- {COLUMN} 1.3.6.1.4.1.248.32.18.1.59.100.1.2
hmStatusWtpMngmtLastWlcEntryPort OBJECT-TYPE
    SYNTAX     Integer32 (0..65535)
    MAX-ACCESS read-only
    STATUS     current
    DESCRIPTION
            "-- empty --"
    ::= { hmStatusWtpMngmtLastWlcEntry 2 }

-- {COLUMN} 1.3.6.1.4.1.248.32.18.1.59.100.1.3
hmStatusWtpMngmtLastWlcEntryName OBJECT-TYPE
    SYNTAX     DisplayString (SIZE(0..31))
    MAX-ACCESS read-only
    STATUS     current
    DESCRIPTION
            "-- empty --"
    ::= { hmStatusWtpMngmtLastWlcEntry 3 }

-- {COLUMN} 1.3.6.1.4.1.248.32.18.1.59.100.1.4
hmStatusWtpMngmtLastWlcEntryRoutetag OBJECT-TYPE
    SYNTAX     Integer32 (0..65535)
    MAX-ACCESS read-only
    STATUS     current
    DESCRIPTION
            "-- empty --"
    ::= { hmStatusWtpMngmtLastWlcEntry 4 }

-- {COLUMN} 1.3.6.1.4.1.248.32.18.1.59.100.1.5
hmStatusWtpMngmtLastWlcEntryType OBJECT-TYPE
    SYNTAX     Integer32 (0..255)
    MAX-ACCESS read-only
    STATUS     current
    DESCRIPTION
            "-- empty --"
    ::= { hmStatusWtpMngmtLastWlcEntry 5 }

-- {COLUMN} 1.3.6.1.4.1.248.32.18.1.59.100.1.6
hmStatusWtpMngmtLastWlcEntryMgmtVlanId OBJECT-TYPE
    SYNTAX     Integer32 (0..65535)
    MAX-ACCESS read-only
    STATUS     current
    DESCRIPTION
            "-- empty --"
    ::= { hmStatusWtpMngmtLastWlcEntry 6 }

-- {TABLE} 1.3.6.1.4.1.248.32.18.1.59.101
hmStatusWtpMngmtRadioprofilsTable OBJECT-TYPE
    SYNTAX     SEQUENCE OF HmStatusWtpMngmtRadioprofilsEntry
    MAX-ACCESS not-accessible
    STATUS     current
    DESCRIPTION
            ""
    ::= { hmStatusWtpMngmt 101 }

-- {ROW} 1.3.6.1.4.1.248.32.18.1.59.101.1
hmStatusWtpMngmtRadioprofilsEntry OBJECT-TYPE
    SYNTAX     HmStatusWtpMngmtRadioprofilsEntry
    MAX-ACCESS not-accessible
    STATUS     current
    DESCRIPTION
            ""
    INDEX {
            hmStatusWtpMngmtRadioprofilsEntryName
          }
    ::= { hmStatusWtpMngmtRadioprofilsTable 1 }

HmStatusWtpMngmtRadioprofilsEntry ::= SEQUENCE {
            hmStatusWtpMngmtRadioprofilsEntryName DisplayString,
            hmStatusWtpMngmtRadioprofilsEntryCountry INTEGER,
            hmStatusWtpMngmtRadioprofilsEntry24ghzMode INTEGER,
            hmStatusWtpMngmtRadioprofilsEntry5ghzMode INTEGER,
            hmStatusWtpMngmtRadioprofilsEntrySubbands INTEGER,
            hmStatusWtpMngmtRadioprofilsEntryQos INTEGER,
            hmStatusWtpMngmtRadioprofilsEntryDtimPeriod Integer32,
            hmStatusWtpMngmtRadioprofilsEntryBackgroundScan Integer32,
            hmStatusWtpMngmtRadioprofilsEntryAntennaGain Integer32,
            hmStatusWtpMngmtRadioprofilsEntryTxPowerReduction Integer32,
            hmStatusWtpMngmtRadioprofilsEntryMgmtVLANId Integer32,
            hmStatusWtpMngmtRadioprofilsEntryMgmtVlanTrunk Integer32,
            hmStatusWtpMngmtRadioprofilsEntryIndoorOnlyOperation INTEGER,
            hmStatusWtpMngmtRadioprofilsEntryMgmtVLANIdnew Integer32,
            hmStatusWtpMngmtRadioprofilsEntryReportSeenClients INTEGER,
            hmStatusWtpMngmtRadioprofilsEntryClientSteering INTEGER,
            hmStatusWtpMngmtRadioprofilsEntryPreferredBand INTEGER,
            hmStatusWtpMngmtRadioprofilsEntryPrReqAgeO Integer32
    }

-- {COLUMN} 1.3.6.1.4.1.248.32.18.1.59.101.1.1
hmStatusWtpMngmtRadioprofilsEntryName OBJECT-TYPE
    SYNTAX     DisplayString (SIZE(0..31))
    MAX-ACCESS read-only
    STATUS     current
    DESCRIPTION
            "-- empty --"
    ::= { hmStatusWtpMngmtRadioprofilsEntry 1 }

-- {COLUMN} 1.3.6.1.4.1.248.32.18.1.59.101.1.4
hmStatusWtpMngmtRadioprofilsEntryCountry OBJECT-TYPE
    SYNTAX     INTEGER {
                  eDefault (0),
                  eAlbania (8),
                  eAlgeria (12),
                  eArgentina (32),
                  eAustralia (36),
                  eAustria (40),
                  eBahrain (48),
                  eBangladesh (50),
                  eBelgium (56),
                  eBosniaHerzegovina (70),
                  eBrazil (76),
                  eBruneiDarussalam (96),
                  eBulgaria (100),
                  eBelarus (112),
                  eCanada (124),
                  eChile (152),
                  eChina (156),
                  eTaiwan (158),
                  eColombia (170),
                  eCostaRica (188),
                  eCroatia (191),
                  eCyprus (196),
                  eCzech (203),
                  eDenmark (208),
                  eEcuador (218),
                  eEstonia (233),
                  eFinland (246),
                  eFrance (250),
                  eGermany (276),
                  eGhana (288),
                  eGreece (300),
                  eGuatemala (320),
                  eHonduras (340),
                  eHongKong (344),
                  eHungary (348),
                  eIceland (352),
                  eIndia (356),
                  eIndonesia (360),
                  eIreland (372),
                  eIsrael (376),
                  eItaly (380),
                  eJapan (392),
                  eJordan (400),
                  eSouthKorea (410),
                  eKuwait (414),
                  eLebanon (422),
                  eLatvia (428),
                  eLiechtenstein (438),
                  eLithuania (440),
                  eLuxembourg (442),
                  eMacau (446),
                  eMalaysia (458),
                  eMalta (470),
                  eMexico (484),
                  eMoldavia (498),
                  eMorocco (504),
                  eOman (512),
                  eNetherlands (528),
                  eNewZealand (554),
                  eNicaragua (558),
                  eNorway (578),
                  ePakistan (586),
                  ePanama (591),
                  eParaguay (600),
                  ePeru (604),
                  ePhilippines (608),
                  ePoland (616),
                  ePortugal (620),
                  ePuertoRico (630),
                  eQatar (634),
                  eRomania (642),
                  eRussia (643),
                  eSaudiArabia (682),
                  eSingapore (702),
                  eSlovak (703),
                  eSlovenia (705),
                  eSouthAfrica (710),
                  eSpain (724),
                  eSweden (752),
                  eSwitzerland (756),
                  eThailand (764),
                  eUnitedArabEmirates (784),
                  eTunisia (788),
                  eTurkey (792),
                  eUganda (800),
                  eUkraine (804),
                  eMacedonia (807),
                  eEgypt (818),
                  eUnitedKingdom (826),
                  eTanzania (834),
                  eUnitedStatesFcc (840),
                  eUruguay (858),
                  eVenezuela (862),
                  eEurope (998),
                  eEgalistan (999)
            }
    MAX-ACCESS read-only
    STATUS     current
    DESCRIPTION
            "-- empty --"
    ::= { hmStatusWtpMngmtRadioprofilsEntry 4 }

-- {COLUMN} 1.3.6.1.4.1.248.32.18.1.59.101.1.6
hmStatusWtpMngmtRadioprofilsEntry24ghzMode OBJECT-TYPE
    SYNTAX     INTEGER {
                  e11bgMixed (0),
                  e11gOnly (1),
                  e11bOnly (2),
                  e11bgnMixed (4),
                  e11gnMixed (5),
                  eGreenfield (6),
                  eAuto (255)
            }
    MAX-ACCESS read-only
    STATUS     current
    DESCRIPTION
            "-- empty --"
    ::= { hmStatusWtpMngmtRadioprofilsEntry 6 }

-- {COLUMN} 1.3.6.1.4.1.248.32.18.1.59.101.1.7
hmStatusWtpMngmtRadioprofilsEntry5ghzMode OBJECT-TYPE
    SYNTAX     INTEGER {
                  eNormal (0),
                  e11anMixed (4),
                  eGreenfield (5),
                  eAuto (255)
            }
    MAX-ACCESS read-only
    STATUS     current
    DESCRIPTION
            "-- empty --"
    ::= { hmStatusWtpMngmtRadioprofilsEntry 7 }

-- {COLUMN} 1.3.6.1.4.1.248.32.18.1.59.101.1.8
hmStatusWtpMngmtRadioprofilsEntrySubbands OBJECT-TYPE
    SYNTAX     INTEGER {
                  eBand1Plus2Plus3 (0),
                  eBand1 (1),
                  eBand2 (2),
                  eBand3 (3),
                  eBand1Plus2 (4),
                  eBand1Plus3 (5),
                  eBand2Plus3 (6)
            }
    MAX-ACCESS read-only
    STATUS     current
    DESCRIPTION
            "-- empty --"
    ::= { hmStatusWtpMngmtRadioprofilsEntry 8 }

-- {COLUMN} 1.3.6.1.4.1.248.32.18.1.59.101.1.9
hmStatusWtpMngmtRadioprofilsEntryQos OBJECT-TYPE
    SYNTAX     INTEGER {
                  eNo (0),
                  eYes (1)
            }
    MAX-ACCESS read-only
    STATUS     current
    DESCRIPTION
            "-- empty --"
    ::= { hmStatusWtpMngmtRadioprofilsEntry 9 }

-- {COLUMN} 1.3.6.1.4.1.248.32.18.1.59.101.1.10
hmStatusWtpMngmtRadioprofilsEntryDtimPeriod OBJECT-TYPE
    SYNTAX     Integer32 (0..255)
    MAX-ACCESS read-only
    STATUS     current
    DESCRIPTION
            "-- empty --"
    ::= { hmStatusWtpMngmtRadioprofilsEntry 10 }

-- {COLUMN} 1.3.6.1.4.1.248.32.18.1.59.101.1.11
hmStatusWtpMngmtRadioprofilsEntryBackgroundScan OBJECT-TYPE
    SYNTAX     Integer32 (0..2147483647)
    MAX-ACCESS read-only
    STATUS     current
    DESCRIPTION
            "-- empty --"
    ::= { hmStatusWtpMngmtRadioprofilsEntry 11 }

-- {COLUMN} 1.3.6.1.4.1.248.32.18.1.59.101.1.12
hmStatusWtpMngmtRadioprofilsEntryAntennaGain OBJECT-TYPE
    SYNTAX     Integer32 (-128..127)
    MAX-ACCESS read-only
    STATUS     current
    DESCRIPTION
            "-- empty --"
    ::= { hmStatusWtpMngmtRadioprofilsEntry 12 }

-- {COLUMN} 1.3.6.1.4.1.248.32.18.1.59.101.1.13
hmStatusWtpMngmtRadioprofilsEntryTxPowerReduction OBJECT-TYPE
    SYNTAX     Integer32 (0..255)
    MAX-ACCESS read-only
    STATUS     current
    DESCRIPTION
            "-- empty --"
    ::= { hmStatusWtpMngmtRadioprofilsEntry 13 }

-- {COLUMN} 1.3.6.1.4.1.248.32.18.1.59.101.1.14
hmStatusWtpMngmtRadioprofilsEntryMgmtVLANId OBJECT-TYPE
    SYNTAX     Integer32 (0..65535)
    MAX-ACCESS read-only
    STATUS     obsolete
    DESCRIPTION
            ""
    ::= { hmStatusWtpMngmtRadioprofilsEntry 14 }

-- {COLUMN} 1.3.6.1.4.1.248.32.18.1.59.101.1.15
hmStatusWtpMngmtRadioprofilsEntryMgmtVlanTrunk OBJECT-TYPE
    SYNTAX     Integer32 (0..65535)
    MAX-ACCESS read-only
    STATUS     current
    DESCRIPTION
            "-- empty --"
    ::= { hmStatusWtpMngmtRadioprofilsEntry 15 }

-- {COLUMN} 1.3.6.1.4.1.248.32.18.1.59.101.1.16
hmStatusWtpMngmtRadioprofilsEntryIndoorOnlyOperation OBJECT-TYPE
    SYNTAX     INTEGER {
                  eNo (0),
                  eYes (1)
            }
    MAX-ACCESS read-only
    STATUS     current
    DESCRIPTION
            "-- empty --"
    ::= { hmStatusWtpMngmtRadioprofilsEntry 16 }

-- {COLUMN} 1.3.6.1.4.1.248.32.18.1.59.101.1.19
hmStatusWtpMngmtRadioprofilsEntryMgmtVLANIdnew OBJECT-TYPE
    SYNTAX     Integer32 (0..65535)
    MAX-ACCESS read-only
    STATUS     current
    DESCRIPTION
            ""
    ::= { hmStatusWtpMngmtRadioprofilsEntry 19 }

-- {COLUMN} 1.3.6.1.4.1.248.32.18.1.59.101.1.20
hmStatusWtpMngmtRadioprofilsEntryReportSeenClients OBJECT-TYPE
    SYNTAX     INTEGER {
                  eNo (0),
                  eYes (1)
            }
    MAX-ACCESS read-only
    STATUS     current
    DESCRIPTION
            "-- empty --"
    ::= { hmStatusWtpMngmtRadioprofilsEntry 20 }

-- {COLUMN} 1.3.6.1.4.1.248.32.18.1.59.101.1.21
hmStatusWtpMngmtRadioprofilsEntryClientSteering OBJECT-TYPE
    SYNTAX     INTEGER {
                  eOff (0),
                  eYes (1),
                  eOn (2)
            }
    MAX-ACCESS read-only
    STATUS     current
    DESCRIPTION
            "-- empty --"
    ::= { hmStatusWtpMngmtRadioprofilsEntry 21 }

-- {COLUMN} 1.3.6.1.4.1.248.32.18.1.59.101.1.22
hmStatusWtpMngmtRadioprofilsEntryPreferredBand OBJECT-TYPE
    SYNTAX     INTEGER {
                  e24ghz (1),
                  e5ghz (2)
            }
    MAX-ACCESS read-only
    STATUS     current
    DESCRIPTION
            "-- empty --"
    ::= { hmStatusWtpMngmtRadioprofilsEntry 22 }

-- {COLUMN} 1.3.6.1.4.1.248.32.18.1.59.101.1.23
hmStatusWtpMngmtRadioprofilsEntryPrReqAgeO OBJECT-TYPE
    SYNTAX     Integer32 (0..2147483647)
    MAX-ACCESS read-only
    STATUS     current
    DESCRIPTION
            ""
    ::= { hmStatusWtpMngmtRadioprofilsEntry 23 }

-- {TABLE} 1.3.6.1.4.1.248.32.18.1.59.102
hmStatusWtpMngmtRadioModeTable OBJECT-TYPE
    SYNTAX     SEQUENCE OF HmStatusWtpMngmtRadioModeEntry
    MAX-ACCESS not-accessible
    STATUS     current
    DESCRIPTION
            "-- empty --"
    ::= { hmStatusWtpMngmt 102 }

-- {ROW} 1.3.6.1.4.1.248.32.18.1.59.102.1
hmStatusWtpMngmtRadioModeEntry OBJECT-TYPE
    SYNTAX     HmStatusWtpMngmtRadioModeEntry
    MAX-ACCESS not-accessible
    STATUS     current
    DESCRIPTION
            ""
    INDEX {
            hmStatusWtpMngmtRadioModeEntryIndex
          }
    ::= { hmStatusWtpMngmtRadioModeTable 1 }

HmStatusWtpMngmtRadioModeEntry ::= SEQUENCE {
            hmStatusWtpMngmtRadioModeEntryIndex Integer32,
            hmStatusWtpMngmtRadioModeEntryRadioMode INTEGER,
            hmStatusWtpMngmtRadioModeEntryOperating INTEGER,
            hmStatusWtpMngmtRadioModeEntryChannelList DisplayString,
            hmStatusWtpMngmtRadioModeEntryRadioChannel INTEGER,
            hmStatusWtpMngmtRadioModeEntryAllow40mhz INTEGER,
            hmStatusWtpMngmtRadioModeEntryAntennaMask INTEGER,
            hmStatusWtpMngmtRadioModeEntryAntennaGain Integer32,
            hmStatusWtpMngmtRadioModeEntryTxPowerReduction Integer32,
            hmStatusWtpMngmtRadioModeEntryMaxChannelBandwidth INTEGER
    }

-- {COLUMN} 1.3.6.1.4.1.248.32.18.1.59.102.1.1
hmStatusWtpMngmtRadioModeEntryIndex OBJECT-TYPE
    SYNTAX     Integer32 (0..255)
    MAX-ACCESS read-only
    STATUS     current
    DESCRIPTION
            "-- empty --"
    ::= { hmStatusWtpMngmtRadioModeEntry 1 }

-- {COLUMN} 1.3.6.1.4.1.248.32.18.1.59.102.1.2
hmStatusWtpMngmtRadioModeEntryRadioMode OBJECT-TYPE
    SYNTAX     INTEGER {
                  eDefault (0),
                  e24ghz (1),
                  e5ghz (2),
                  eOff (3),
                  eAuto (255)
            }
    MAX-ACCESS read-only
    STATUS     current
    DESCRIPTION
            "-- empty --"
    ::= { hmStatusWtpMngmtRadioModeEntry 2 }

-- {COLUMN} 1.3.6.1.4.1.248.32.18.1.59.102.1.3
hmStatusWtpMngmtRadioModeEntryOperating OBJECT-TYPE
    SYNTAX     INTEGER {
                  eYes (0),
                  eNo (1)
            }
    MAX-ACCESS read-only
    STATUS     current
    DESCRIPTION
            "-- empty --"
    ::= { hmStatusWtpMngmtRadioModeEntry 3 }

-- {COLUMN} 1.3.6.1.4.1.248.32.18.1.59.102.1.4
hmStatusWtpMngmtRadioModeEntryChannelList OBJECT-TYPE
    SYNTAX     DisplayString (SIZE(0..48))
    MAX-ACCESS read-only
    STATUS     current
    DESCRIPTION
            "-- empty --"
    ::= { hmStatusWtpMngmtRadioModeEntry 4 }

-- {COLUMN} 1.3.6.1.4.1.248.32.18.1.59.102.1.5
hmStatusWtpMngmtRadioModeEntryRadioChannel OBJECT-TYPE
    SYNTAX     INTEGER {
                  eAuto (0)
            }
    MAX-ACCESS read-only
    STATUS     current
    DESCRIPTION
            "-- empty --"
    ::= { hmStatusWtpMngmtRadioModeEntry 5 }

-- {COLUMN} 1.3.6.1.4.1.248.32.18.1.59.102.1.6
hmStatusWtpMngmtRadioModeEntryAllow40mhz OBJECT-TYPE
    SYNTAX     INTEGER {
                  eAuto (0),
                  eNo (1)
            }
    MAX-ACCESS read-only
    STATUS     current
    DESCRIPTION
            "-- empty --"
    ::= { hmStatusWtpMngmtRadioModeEntry 6 }

-- {COLUMN} 1.3.6.1.4.1.248.32.18.1.59.102.1.7
hmStatusWtpMngmtRadioModeEntryAntennaMask OBJECT-TYPE
    SYNTAX     INTEGER {
                  eAuto (0),
                  eAntenna1 (1),
                  eAntenna1Plus2 (3),
                  eAntenna1Plus3 (5),
                  eAntenna1Plus2Plus3 (7)
            }
    MAX-ACCESS read-only
    STATUS     current
    DESCRIPTION
            "-- empty --"
    ::= { hmStatusWtpMngmtRadioModeEntry 7 }

-- {COLUMN} 1.3.6.1.4.1.248.32.18.1.59.102.1.8
hmStatusWtpMngmtRadioModeEntryAntennaGain OBJECT-TYPE
    SYNTAX     Integer32 (-128..127)
    MAX-ACCESS read-only
    STATUS     current
    DESCRIPTION
            "-- empty --"
    ::= { hmStatusWtpMngmtRadioModeEntry 8 }

-- {COLUMN} 1.3.6.1.4.1.248.32.18.1.59.102.1.9
hmStatusWtpMngmtRadioModeEntryTxPowerReduction OBJECT-TYPE
    SYNTAX     Integer32 (0..255)
    MAX-ACCESS read-only
    STATUS     current
    DESCRIPTION
            "-- empty --"
    ::= { hmStatusWtpMngmtRadioModeEntry 9 }

-- {COLUMN} 1.3.6.1.4.1.248.32.18.1.59.102.1.10
hmStatusWtpMngmtRadioModeEntryMaxChannelBandwidth OBJECT-TYPE
    SYNTAX     INTEGER {
                  e20mhz (0),
                  e40mhz (1),
                  eAuto (255)
            }
    MAX-ACCESS read-only
    STATUS     current
    DESCRIPTION
            "-- empty --"
    ::= { hmStatusWtpMngmtRadioModeEntry 10 }

-- {TABLE} 1.3.6.1.4.1.248.32.18.1.59.103
hmStatusWtpMngmtNetwprofilsTable OBJECT-TYPE
    SYNTAX     SEQUENCE OF HmStatusWtpMngmtNetwprofilsEntry
    MAX-ACCESS not-accessible
    STATUS     current
    DESCRIPTION
            "network profiles"
    ::= { hmStatusWtpMngmt 103 }

-- {ROW} 1.3.6.1.4.1.248.32.18.1.59.103.1
hmStatusWtpMngmtNetwprofilsEntry OBJECT-TYPE
    SYNTAX     HmStatusWtpMngmtNetwprofilsEntry
    MAX-ACCESS not-accessible
    STATUS     current
    DESCRIPTION
            ""
    INDEX {
            hmStatusWtpMngmtNetwprofilsEntryName
          }
    ::= { hmStatusWtpMngmtNetwprofilsTable 1 }

HmStatusWtpMngmtNetwprofilsEntry ::= SEQUENCE {
            hmStatusWtpMngmtNetwprofilsEntryName DisplayString,
            hmStatusWtpMngmtNetwprofilsEntryOperating INTEGER,
            hmStatusWtpMngmtNetwprofilsEntryVlanId Integer32,
            hmStatusWtpMngmtNetwprofilsEntryEncryption INTEGER,
            hmStatusWtpMngmtNetwprofilsEntryWpa1SessionKeytypes INTEGER,
            hmStatusWtpMngmtNetwprofilsEntryWpaVersion INTEGER,
            hmStatusWtpMngmtNetwprofilsEntryKey DisplayString,
            hmStatusWtpMngmtNetwprofilsEntryRadioBand INTEGER,
            hmStatusWtpMngmtNetwprofilsEntryContinuation Integer32,
            hmStatusWtpMngmtNetwprofilsEntryMinTxRate INTEGER,
            hmStatusWtpMngmtNetwprofilsEntryMaxTxRate INTEGER,
            hmStatusWtpMngmtNetwprofilsEntryBasicRate INTEGER,
            hmStatusWtpMngmtNetwprofilsEntry11bPreamble INTEGER,
            hmStatusWtpMngmtNetwprofilsEntryMacFilter INTEGER,
            hmStatusWtpMngmtNetwprofilsEntryClBrgSupport INTEGER,
            hmStatusWtpMngmtNetwprofilsEntryMaxStations Integer32,
            hmStatusWtpMngmtNetwprofilsEntrySsidBroadcast INTEGER,
            hmStatusWtpMngmtNetwprofilsEntryVlanTrunk Integer32,
            hmStatusWtpMngmtNetwprofilsEntrySsid DisplayString,
            hmStatusWtpMngmtNetwprofilsEntryMinHtMcs INTEGER,
            hmStatusWtpMngmtNetwprofilsEntryMaxHtMcs INTEGER,
            hmStatusWtpMngmtNetwprofilsEntryShortGuardInterval INTEGER,
            hmStatusWtpMngmtNetwprofilsEntryMaxSpatialStreams INTEGER,
            hmStatusWtpMngmtNetwprofilsEntrySendAggregates INTEGER,
            hmStatusWtpMngmtNetwprofilsEntryWpa2SessionKeytypes INTEGER,
            hmStatusWtpMngmtNetwprofilsEntryRadiusAccounting INTEGER,
            hmStatusWtpMngmtNetwprofilsEntryVlanMode INTEGER,
            hmStatusWtpMngmtNetwprofilsEntryConnectSsidTo INTEGER,
            hmStatusWtpMngmtNetwprofilsEntryInterStationTraffic INTEGER,
            hmStatusWtpMngmtNetwprofilsEntryVlanIdnew Integer32,
            hmStatusWtpMngmtNetwprofilsEntryRadiusProfile DisplayString,
            hmStatusWtpMngmtNetwprofilsEntryStbcActivated INTEGER,
            hmStatusWtpMngmtNetwprofilsEntryLdpcActivated INTEGER,
            hmStatusWtpMngmtNetwprofilsEntryMinClientStrength Integer32,
            hmStatusWtpMngmtNetwprofilsEntryIeee80211uNetworkProfile DisplayString,
            hmStatusWtpMngmtNetwprofilsEntryOkc INTEGER,
            hmStatusWtpMngmtNetwprofilsEntryWpa2KeyManagement BITS,
            hmStatusWtpMngmtNetwprofilsEntryApsd INTEGER,
            hmStatusWtpMngmtNetwprofilsEntryProtMgmtFrames INTEGER,
            hmStatusWtpMngmtNetwprofilsEntryTxLimit Integer32,
            hmStatusWtpMngmtNetwprofilsEntryRxLimit Integer32,
            hmStatusWtpMngmtNetwprofilsEntryLbsTracking INTEGER,
            hmStatusWtpMngmtNetwprofilsEntryLbsTrackingList DisplayString,
            hmStatusWtpMngmtNetwprofilsEntryClBrgRoamingSupport INTEGER
    }

-- {COLUMN} 1.3.6.1.4.1.248.32.18.1.59.103.1.1
hmStatusWtpMngmtNetwprofilsEntryName OBJECT-TYPE
    SYNTAX     DisplayString (SIZE(0..31))
    MAX-ACCESS read-only
    STATUS     current
    DESCRIPTION
            "-- empty --"
    ::= { hmStatusWtpMngmtNetwprofilsEntry 1 }

-- {COLUMN} 1.3.6.1.4.1.248.32.18.1.59.103.1.4
hmStatusWtpMngmtNetwprofilsEntryOperating OBJECT-TYPE
    SYNTAX     INTEGER {
                  eYes (0),
                  eNo (1)
            }
    MAX-ACCESS read-only
    STATUS     current
    DESCRIPTION
            "-- empty --"
    ::= { hmStatusWtpMngmtNetwprofilsEntry 4 }

-- {COLUMN} 1.3.6.1.4.1.248.32.18.1.59.103.1.5
hmStatusWtpMngmtNetwprofilsEntryVlanId OBJECT-TYPE
    SYNTAX     Integer32 (0..65535)
    MAX-ACCESS read-only
    STATUS     obsolete
    DESCRIPTION
            ""
    ::= { hmStatusWtpMngmtNetwprofilsEntry 5 }

-- {COLUMN} 1.3.6.1.4.1.248.32.18.1.59.103.1.6
hmStatusWtpMngmtNetwprofilsEntryEncryption OBJECT-TYPE
    SYNTAX     INTEGER {
                  e80211iWpaPsk (0),
                  e80211iWpa8021x (1),
                  eWep104Bits (2),
                  eWep40Bits (3),
                  eWep104Bits8021x (4),
                  eWep40Bits8021x (5),
                  eNone (6)
            }
    MAX-ACCESS read-only
    STATUS     current
    DESCRIPTION
            "-- empty --"
    ::= { hmStatusWtpMngmtNetwprofilsEntry 6 }

-- {COLUMN} 1.3.6.1.4.1.248.32.18.1.59.103.1.7
hmStatusWtpMngmtNetwprofilsEntryWpa1SessionKeytypes OBJECT-TYPE
    SYNTAX     INTEGER {
                  eTkipAes (0),
                  eAes (1),
                  eTkip (2)
            }
    MAX-ACCESS read-only
    STATUS     current
    DESCRIPTION
            "-- empty --"
    ::= { hmStatusWtpMngmtNetwprofilsEntry 7 }

-- {COLUMN} 1.3.6.1.4.1.248.32.18.1.59.103.1.8
hmStatusWtpMngmtNetwprofilsEntryWpaVersion OBJECT-TYPE
    SYNTAX     INTEGER {
                  eWpa12 (0),
                  eWpa1 (1),
                  eWpa2 (2)
            }
    MAX-ACCESS read-only
    STATUS     current
    DESCRIPTION
            "-- empty --"
    ::= { hmStatusWtpMngmtNetwprofilsEntry 8 }

-- {COLUMN} 1.3.6.1.4.1.248.32.18.1.59.103.1.9
hmStatusWtpMngmtNetwprofilsEntryKey OBJECT-TYPE
    SYNTAX     DisplayString (SIZE(0..63))
    MAX-ACCESS read-only
    STATUS     current
    DESCRIPTION
            "-- empty --"
    ::= { hmStatusWtpMngmtNetwprofilsEntry 9 }

-- {COLUMN} 1.3.6.1.4.1.248.32.18.1.59.103.1.10
hmStatusWtpMngmtNetwprofilsEntryRadioBand OBJECT-TYPE
    SYNTAX     INTEGER {
                  e24ghz5ghz (0),
                  e24ghz (1),
                  e5ghz (2)
            }
    MAX-ACCESS read-only
    STATUS     current
    DESCRIPTION
            "-- empty --"
    ::= { hmStatusWtpMngmtNetwprofilsEntry 10 }

-- {COLUMN} 1.3.6.1.4.1.248.32.18.1.59.103.1.11
hmStatusWtpMngmtNetwprofilsEntryContinuation OBJECT-TYPE
    SYNTAX     Integer32 (0..65535)
    MAX-ACCESS read-only
    STATUS     current
    DESCRIPTION
            ""
    ::= { hmStatusWtpMngmtNetwprofilsEntry 11 }

-- {COLUMN} 1.3.6.1.4.1.248.32.18.1.59.103.1.12
hmStatusWtpMngmtNetwprofilsEntryMinTxRate OBJECT-TYPE
    SYNTAX     INTEGER {
                  eAuto (0),
                  e1M (1),
                  e2M (2),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-only
    STATUS     current
    DESCRIPTION
            "-- empty --"
    ::= { hmStatusWtpMngmtNetwprofilsEntry 12 }

-- {COLUMN} 1.3.6.1.4.1.248.32.18.1.59.103.1.13
hmStatusWtpMngmtNetwprofilsEntryMaxTxRate OBJECT-TYPE
    SYNTAX     INTEGER {
                  eAuto (0),
                  e1M (1),
                  e2M (2),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-only
    STATUS     current
    DESCRIPTION
            "-- empty --"
    ::= { hmStatusWtpMngmtNetwprofilsEntry 13 }

-- {COLUMN} 1.3.6.1.4.1.248.32.18.1.59.103.1.14
hmStatusWtpMngmtNetwprofilsEntryBasicRate OBJECT-TYPE
    SYNTAX     INTEGER {
                  e2M (0),
                  e1M (1),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-only
    STATUS     current
    DESCRIPTION
            "-- empty --"
    ::= { hmStatusWtpMngmtNetwprofilsEntry 14 }

-- {COLUMN} 1.3.6.1.4.1.248.32.18.1.59.103.1.15
hmStatusWtpMngmtNetwprofilsEntry11bPreamble OBJECT-TYPE
    SYNTAX     INTEGER {
                  eAuto (0),
                  eLong (1)
            }
    MAX-ACCESS read-only
    STATUS     current
    DESCRIPTION
            "-- empty --"
    ::= { hmStatusWtpMngmtNetwprofilsEntry 15 }

-- {COLUMN} 1.3.6.1.4.1.248.32.18.1.59.103.1.16
hmStatusWtpMngmtNetwprofilsEntryMacFilter OBJECT-TYPE
    SYNTAX     INTEGER {
                  eNo (0),
                  eYes (1)
            }
    MAX-ACCESS read-only
    STATUS     current
    DESCRIPTION
            "-- empty --"
    ::= { hmStatusWtpMngmtNetwprofilsEntry 16 }

-- {COLUMN} 1.3.6.1.4.1.248.32.18.1.59.103.1.17
hmStatusWtpMngmtNetwprofilsEntryClBrgSupport OBJECT-TYPE
    SYNTAX     INTEGER {
                  eNo (0),
                  eYes (1),
                  eExclusive (2)
            }
    MAX-ACCESS read-only
    STATUS     current
    DESCRIPTION
            "-- empty --"
    ::= { hmStatusWtpMngmtNetwprofilsEntry 17 }

-- {COLUMN} 1.3.6.1.4.1.248.32.18.1.59.103.1.18
hmStatusWtpMngmtNetwprofilsEntryMaxStations OBJECT-TYPE
    SYNTAX     Integer32 (0..65535)
    MAX-ACCESS read-only
    STATUS     current
    DESCRIPTION
            "-- empty --"
    ::= { hmStatusWtpMngmtNetwprofilsEntry 18 }

-- {COLUMN} 1.3.6.1.4.1.248.32.18.1.59.103.1.19
hmStatusWtpMngmtNetwprofilsEntrySsidBroadcast OBJECT-TYPE
    SYNTAX     INTEGER {
                  eYes (0),
                  eNo (1),
                  eTightened (2)
            }
    MAX-ACCESS read-only
    STATUS     current
    DESCRIPTION
            "-- empty --"
    ::= { hmStatusWtpMngmtNetwprofilsEntry 19 }

-- {COLUMN} 1.3.6.1.4.1.248.32.18.1.59.103.1.20
hmStatusWtpMngmtNetwprofilsEntryVlanTrunk OBJECT-TYPE
    SYNTAX     Integer32 (0..65535)
    MAX-ACCESS read-only
    STATUS     current
    DESCRIPTION
            "-- empty --"
    ::= { hmStatusWtpMngmtNetwprofilsEntry 20 }

-- {COLUMN} 1.3.6.1.4.1.248.32.18.1.59.103.1.21
hmStatusWtpMngmtNetwprofilsEntrySsid OBJECT-TYPE
    SYNTAX     DisplayString (SIZE(0..32))
    MAX-ACCESS read-only
    STATUS     current
    DESCRIPTION
            "-- empty --"
    ::= { hmStatusWtpMngmtNetwprofilsEntry 21 }

-- {COLUMN} 1.3.6.1.4.1.248.32.18.1.59.103.1.22
hmStatusWtpMngmtNetwprofilsEntryMinHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-only
    STATUS     current
    DESCRIPTION
            "-- empty --"
    ::= { hmStatusWtpMngmtNetwprofilsEntry 22 }

-- {COLUMN} 1.3.6.1.4.1.248.32.18.1.59.103.1.23
hmStatusWtpMngmtNetwprofilsEntryMaxHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-only
    STATUS     current
    DESCRIPTION
            "-- empty --"
    ::= { hmStatusWtpMngmtNetwprofilsEntry 23 }

-- {COLUMN} 1.3.6.1.4.1.248.32.18.1.59.103.1.24
hmStatusWtpMngmtNetwprofilsEntryShortGuardInterval OBJECT-TYPE
    SYNTAX     INTEGER {
                  eAuto (0),
                  eNo (1)
            }
    MAX-ACCESS read-only
    STATUS     current
    DESCRIPTION
            "-- empty --"
    ::= { hmStatusWtpMngmtNetwprofilsEntry 24 }

-- {COLUMN} 1.3.6.1.4.1.248.32.18.1.59.103.1.25
hmStatusWtpMngmtNetwprofilsEntryMaxSpatialStreams OBJECT-TYPE
    SYNTAX     INTEGER {
                  eAuto (0),
                  eOne (1),
                  eTwo (2)
            }
    MAX-ACCESS read-only
    STATUS     current
    DESCRIPTION
            "-- empty --"
    ::= { hmStatusWtpMngmtNetwprofilsEntry 25 }

-- {COLUMN} 1.3.6.1.4.1.248.32.18.1.59.103.1.26
hmStatusWtpMngmtNetwprofilsEntrySendAggregates OBJECT-TYPE
    SYNTAX     INTEGER {
                  eNo (0),
                  eYes (1)
            }
    MAX-ACCESS read-only
    STATUS     current
    DESCRIPTION
            "-- empty --"
    ::= { hmStatusWtpMngmtNetwprofilsEntry 26 }

-- {COLUMN} 1.3.6.1.4.1.248.32.18.1.59.103.1.27
hmStatusWtpMngmtNetwprofilsEntryWpa2SessionKeytypes OBJECT-TYPE
    SYNTAX     INTEGER {
                  eTkipAes (0),
                  eAes (1),
                  eTkip (2)
            }
    MAX-ACCESS read-only
    STATUS     current
    DESCRIPTION
            "-- empty --"
    ::= { hmStatusWtpMngmtNetwprofilsEntry 27 }

-- {COLUMN} 1.3.6.1.4.1.248.32.18.1.59.103.1.28
hmStatusWtpMngmtNetwprofilsEntryRadiusAccounting OBJECT-TYPE
    SYNTAX     INTEGER {
                  eNo (0),
                  eYes (1)
            }
    MAX-ACCESS read-only
    STATUS     current
    DESCRIPTION
            "-- empty --"
    ::= { hmStatusWtpMngmtNetwprofilsEntry 28 }

-- {COLUMN} 1.3.6.1.4.1.248.32.18.1.59.103.1.30
hmStatusWtpMngmtNetwprofilsEntryVlanMode OBJECT-TYPE
    SYNTAX     INTEGER {
                  eUntagged (0),
                  eTagged (1)
            }
    MAX-ACCESS read-only
    STATUS     current
    DESCRIPTION
            "-- empty --"
    ::= { hmStatusWtpMngmtNetwprofilsEntry 30 }

-- {COLUMN} 1.3.6.1.4.1.248.32.18.1.59.103.1.32
hmStatusWtpMngmtNetwprofilsEntryConnectSsidTo OBJECT-TYPE
    SYNTAX     INTEGER {
                  eLan (0),
                  eWlcTunnel1 (1),
                  eWlcTunnel2 (2),
                  eWlcTunnel3 (3),
                  eWlcTunnel4 (4),
                  eWlcTunnel5 (5),
                  eWlcTunnel6 (6),
                  eWlcTunnel7 (7),
                  eWlcTunnel8 (8),
                  eWlcTunnel9 (9),
                  eWlcTunnel10 (10),
                  eWlcTunnel11 (11),
                  eWlcTunnel12 (12),
                  eWlcTunnel13 (13),
                  eWlcTunnel14 (14),
                  eWlcTunnel15 (15),
                  eWlcTunnel16 (16),
                  eWlcTunnel17 (17),
                  eWlcTunnel18 (18),
                  eWlcTunnel19 (19),
                  eWlcTunnel20 (20),
                  eWlcTunnel21 (21),
                  eWlcTunnel22 (22),
                  eWlcTunnel23 (23),
                  eWlcTunnel24 (24),
                  eWlcTunnel25 (25),
                  eWlcTunnel26 (26),
                  eWlcTunnel27 (27),
                  eWlcTunnel28 (28),
                  eWlcTunnel29 (29),
                  eWlcTunnel30 (30),
                  eWlcTunnel31 (31),
                  eWlcTunnel32 (32),
                  eWlcTunnelAutowds (33)
            }
    MAX-ACCESS read-only
    STATUS     current
    DESCRIPTION
            "-- empty --"
    ::= { hmStatusWtpMngmtNetwprofilsEntry 32 }

-- {COLUMN} 1.3.6.1.4.1.248.32.18.1.59.103.1.33
hmStatusWtpMngmtNetwprofilsEntryInterStationTraffic OBJECT-TYPE
    SYNTAX     INTEGER {
                  eNo (0),
                  eYes (1)
            }
    MAX-ACCESS read-only
    STATUS     current
    DESCRIPTION
            "-- empty --"
    ::= { hmStatusWtpMngmtNetwprofilsEntry 33 }

-- {COLUMN} 1.3.6.1.4.1.248.32.18.1.59.103.1.34
hmStatusWtpMngmtNetwprofilsEntryVlanIdnew OBJECT-TYPE
    SYNTAX     Integer32 (0..65535)
    MAX-ACCESS read-only
    STATUS     current
    DESCRIPTION
            ""
    ::= { hmStatusWtpMngmtNetwprofilsEntry 34 }

-- {COLUMN} 1.3.6.1.4.1.248.32.18.1.59.103.1.35
hmStatusWtpMngmtNetwprofilsEntryRadiusProfile OBJECT-TYPE
    SYNTAX     DisplayString (SIZE(0..16))
    MAX-ACCESS read-only
    STATUS     current
    DESCRIPTION
            "-- empty --"
    ::= { hmStatusWtpMngmtNetwprofilsEntry 35 }

-- {COLUMN} 1.3.6.1.4.1.248.32.18.1.59.103.1.36
hmStatusWtpMngmtNetwprofilsEntryStbcActivated OBJECT-TYPE
    SYNTAX     INTEGER {
                  eNo (0),
                  eYes (1)
            }
    MAX-ACCESS read-only
    STATUS     current
    DESCRIPTION
            "-- empty --"
    ::= { hmStatusWtpMngmtNetwprofilsEntry 36 }

-- {COLUMN} 1.3.6.1.4.1.248.32.18.1.59.103.1.37
hmStatusWtpMngmtNetwprofilsEntryLdpcActivated OBJECT-TYPE
    SYNTAX     INTEGER {
                  eNo (0),
                  eYes (1)
            }
    MAX-ACCESS read-only
    STATUS     current
    DESCRIPTION
            "-- empty --"
    ::= { hmStatusWtpMngmtNetwprofilsEntry 37 }

-- {COLUMN} 1.3.6.1.4.1.248.32.18.1.59.103.1.38
hmStatusWtpMngmtNetwprofilsEntryMinClientStrength OBJECT-TYPE
    SYNTAX     Integer32 (0..255)
    MAX-ACCESS read-only
    STATUS     current
    DESCRIPTION
            "-- empty --"
    ::= { hmStatusWtpMngmtNetwprofilsEntry 38 }

-- {COLUMN} 1.3.6.1.4.1.248.32.18.1.59.103.1.39
hmStatusWtpMngmtNetwprofilsEntryIeee80211uNetworkProfile OBJECT-TYPE
    SYNTAX     DisplayString (SIZE(0..32))
    MAX-ACCESS read-only
    STATUS     current
    DESCRIPTION
            "-- empty --"
    ::= { hmStatusWtpMngmtNetwprofilsEntry 39 }

-- {COLUMN} 1.3.6.1.4.1.248.32.18.1.59.103.1.40
hmStatusWtpMngmtNetwprofilsEntryOkc OBJECT-TYPE
    SYNTAX     INTEGER {
                  eNo (0),
                  eYes (1)
            }
    MAX-ACCESS read-only
    STATUS     current
    DESCRIPTION
            "-- empty --"
    ::= { hmStatusWtpMngmtNetwprofilsEntry 40 }

-- {COLUMN} 1.3.6.1.4.1.248.32.18.1.59.103.1.41
hmStatusWtpMngmtNetwprofilsEntryWpa2KeyManagement OBJECT-TYPE
    SYNTAX     BITS {
                  eSha256 (5),
                  eFastRoaming (6),
                  eStandard (7)
            }
    MAX-ACCESS read-only
    STATUS     current
    DESCRIPTION
            "-- empty --"
    ::= { hmStatusWtpMngmtNetwprofilsEntry 41 }

-- {COLUMN} 1.3.6.1.4.1.248.32.18.1.59.103.1.42
hmStatusWtpMngmtNetwprofilsEntryApsd OBJECT-TYPE
    SYNTAX     INTEGER {
                  eNo (0),
                  eYes (1)
            }
    MAX-ACCESS read-only
    STATUS     current
    DESCRIPTION
            "-- empty --"
    ::= { hmStatusWtpMngmtNetwprofilsEntry 42 }

-- {COLUMN} 1.3.6.1.4.1.248.32.18.1.59.103.1.43
hmStatusWtpMngmtNetwprofilsEntryProtMgmtFrames OBJECT-TYPE
    SYNTAX     INTEGER {
                  eNo (0),
                  eOptional (1),
                  eMandatory (2)
            }
    MAX-ACCESS read-only
    STATUS     current
    DESCRIPTION
            "-- empty --"
    ::= { hmStatusWtpMngmtNetwprofilsEntry 43 }

-- {COLUMN} 1.3.6.1.4.1.248.32.18.1.59.103.1.44
hmStatusWtpMngmtNetwprofilsEntryTxLimit OBJECT-TYPE
    SYNTAX     Integer32 (0..2147483647)
    MAX-ACCESS read-only
    STATUS     current
    DESCRIPTION
            "-- empty --"
    ::= { hmStatusWtpMngmtNetwprofilsEntry 44 }

-- {COLUMN} 1.3.6.1.4.1.248.32.18.1.59.103.1.45
hmStatusWtpMngmtNetwprofilsEntryRxLimit OBJECT-TYPE
    SYNTAX     Integer32 (0..2147483647)
    MAX-ACCESS read-only
    STATUS     current
    DESCRIPTION
            "-- empty --"
    ::= { hmStatusWtpMngmtNetwprofilsEntry 45 }

-- {COLUMN} 1.3.6.1.4.1.248.32.18.1.59.103.1.46
hmStatusWtpMngmtNetwprofilsEntryLbsTracking OBJECT-TYPE
    SYNTAX     INTEGER {
                  eNo (0),
                  eYes (1)
            }
    MAX-ACCESS read-only
    STATUS     current
    DESCRIPTION
            "-- empty --"
    ::= { hmStatusWtpMngmtNetwprofilsEntry 46 }

-- {COLUMN} 1.3.6.1.4.1.248.32.18.1.59.103.1.47
hmStatusWtpMngmtNetwprofilsEntryLbsTrackingList OBJECT-TYPE
    SYNTAX     DisplayString (SIZE(0..32))
    MAX-ACCESS read-only
    STATUS     current
    DESCRIPTION
            "-- empty --"
    ::= { hmStatusWtpMngmtNetwprofilsEntry 47 }

-- {COLUMN} 1.3.6.1.4.1.248.32.18.1.59.103.1.48
hmStatusWtpMngmtNetwprofilsEntryClBrgRoamingSupport OBJECT-TYPE
    SYNTAX     INTEGER {
                  eNo (0),
                  eYes (1)
            }
    MAX-ACCESS read-only
    STATUS     current
    DESCRIPTION
            "-- empty --"
    ::= { hmStatusWtpMngmtNetwprofilsEntry 48 }

-- {TABLE} 1.3.6.1.4.1.248.32.18.1.59.104
hmStatusWtpMngmtApBridgeInterfacesTable OBJECT-TYPE
    SYNTAX     SEQUENCE OF HmStatusWtpMngmtApBridgeInterfacesEntry
    MAX-ACCESS not-accessible
    STATUS     current
    DESCRIPTION
            "-- empty --"
    ::= { hmStatusWtpMngmt 104 }

-- {ROW} 1.3.6.1.4.1.248.32.18.1.59.104.1
hmStatusWtpMngmtApBridgeInterfacesEntry OBJECT-TYPE
    SYNTAX     HmStatusWtpMngmtApBridgeInterfacesEntry
    MAX-ACCESS not-accessible
    STATUS     current
    DESCRIPTION
            ""
    INDEX {
            hmStatusWtpMngmtApBridgeInterfacesEntryBridgeInterface
          }
    ::= { hmStatusWtpMngmtApBridgeInterfacesTable 1 }

HmStatusWtpMngmtApBridgeInterfacesEntry ::= SEQUENCE {
            hmStatusWtpMngmtApBridgeInterfacesEntryBridgeInterface INTEGER,
            hmStatusWtpMngmtApBridgeInterfacesEntryRegisteredConnections Integer32,
            hmStatusWtpMngmtApBridgeInterfacesEntryRecvUnicasts Integer32,
            hmStatusWtpMngmtApBridgeInterfacesEntryRecvMulticasts Integer32,
            hmStatusWtpMngmtApBridgeInterfacesEntryRecvBroadcasts Integer32,
            hmStatusWtpMngmtApBridgeInterfacesEntryTransUnicastPackets Integer32,
            hmStatusWtpMngmtApBridgeInterfacesEntryTransMultiBroadPckts Integer32,
            hmStatusWtpMngmtApBridgeInterfacesEntryDroppedPackets Integer32
    }

-- {COLUMN} 1.3.6.1.4.1.248.32.18.1.59.104.1.1
hmStatusWtpMngmtApBridgeInterfacesEntryBridgeInterface OBJECT-TYPE
    SYNTAX     INTEGER {
                  eLan (0),
                  eWlcTunnel1 (1),
                  eWlcTunnel2 (2),
                  eWlcTunnel3 (3),
                  eWlcTunnel4 (4),
                  eWlcTunnel5 (5),
                  eWlcTunnel6 (6),
                  eWlcTunnel7 (7),
                  eWlcTunnel8 (8),
                  eWlcTunnel9 (9),
                  eWlcTunnel10 (10),
                  eWlcTunnel11 (11),
                  eWlcTunnel12 (12),
                  eWlcTunnel13 (13),
                  eWlcTunnel14 (14),
                  eWlcTunnel15 (15),
                  eWlcTunnel16 (16),
                  eWlcTunnel17 (17),
                  eWlcTunnel18 (18),
                  eWlcTunnel19 (19),
                  eWlcTunnel20 (20),
                  eWlcTunnel21 (21),
                  eWlcTunnel22 (22),
                  eWlcTunnel23 (23),
                  eWlcTunnel24 (24),
                  eWlcTunnel25 (25),
                  eWlcTunnel26 (26),
                  eWlcTunnel27 (27),
                  eWlcTunnel28 (28),
                  eWlcTunnel29 (29),
                  eWlcTunnel30 (30),
                  eWlcTunnel31 (31),
                  eWlcTunnel32 (32),
                  eWlcTunnelAutowds (33)
            }
    MAX-ACCESS read-only
    STATUS     current
    DESCRIPTION
            "-- empty --"
    ::= { hmStatusWtpMngmtApBridgeInterfacesEntry 1 }

-- {COLUMN} 1.3.6.1.4.1.248.32.18.1.59.104.1.2
hmStatusWtpMngmtApBridgeInterfacesEntryRegisteredConnections OBJECT-TYPE
    SYNTAX     Integer32 (0..2147483647)
    MAX-ACCESS read-only
    STATUS     current
    DESCRIPTION
            "-- empty --"
    ::= { hmStatusWtpMngmtApBridgeInterfacesEntry 2 }

-- {COLUMN} 1.3.6.1.4.1.248.32.18.1.59.104.1.3
hmStatusWtpMngmtApBridgeInterfacesEntryRecvUnicasts OBJECT-TYPE
    SYNTAX     Integer32 (0..2147483647)
    MAX-ACCESS read-only
    STATUS     current
    DESCRIPTION
            "-- empty --"
    ::= { hmStatusWtpMngmtApBridgeInterfacesEntry 3 }

-- {COLUMN} 1.3.6.1.4.1.248.32.18.1.59.104.1.4
hmStatusWtpMngmtApBridgeInterfacesEntryRecvMulticasts OBJECT-TYPE
    SYNTAX     Integer32 (0..2147483647)
    MAX-ACCESS read-only
    STATUS     current
    DESCRIPTION
            "-- empty --"
    ::= { hmStatusWtpMngmtApBridgeInterfacesEntry 4 }

-- {COLUMN} 1.3.6.1.4.1.248.32.18.1.59.104.1.5
hmStatusWtpMngmtApBridgeInterfacesEntryRecvBroadcasts OBJECT-TYPE
    SYNTAX     Integer32 (0..2147483647)
    MAX-ACCESS read-only
    STATUS     current
    DESCRIPTION
            "-- empty --"
    ::= { hmStatusWtpMngmtApBridgeInterfacesEntry 5 }

-- {COLUMN} 1.3.6.1.4.1.248.32.18.1.59.104.1.6
hmStatusWtpMngmtApBridgeInterfacesEntryTransUnicastPackets OBJECT-TYPE
    SYNTAX     Integer32 (0..2147483647)
    MAX-ACCESS read-only
    STATUS     current
    DESCRIPTION
            "-- empty --"
    ::= { hmStatusWtpMngmtApBridgeInterfacesEntry 6 }

-- {COLUMN} 1.3.6.1.4.1.248.32.18.1.59.104.1.7
hmStatusWtpMngmtApBridgeInterfacesEntryTransMultiBroadPckts OBJECT-TYPE
    SYNTAX     Integer32 (0..2147483647)
    MAX-ACCESS read-only
    STATUS     current
    DESCRIPTION
            ""
    ::= { hmStatusWtpMngmtApBridgeInterfacesEntry 7 }

-- {COLUMN} 1.3.6.1.4.1.248.32.18.1.59.104.1.8
hmStatusWtpMngmtApBridgeInterfacesEntryDroppedPackets OBJECT-TYPE
    SYNTAX     Integer32 (0..2147483647)
    MAX-ACCESS read-only
    STATUS     current
    DESCRIPTION
            "-- empty --"
    ::= { hmStatusWtpMngmtApBridgeInterfacesEntry 8 }

-- {TABLE} 1.3.6.1.4.1.248.32.18.1.59.105
hmStatusWtpMngmtRadiusServerProfilesTable OBJECT-TYPE
    SYNTAX     SEQUENCE OF HmStatusWtpMngmtRadiusServerProfilesEntry
    MAX-ACCESS not-accessible
    STATUS     current
    DESCRIPTION
            "-- empty --"
    ::= { hmStatusWtpMngmt 105 }

-- {ROW} 1.3.6.1.4.1.248.32.18.1.59.105.1
hmStatusWtpMngmtRadiusServerProfilesEntry OBJECT-TYPE
    SYNTAX     HmStatusWtpMngmtRadiusServerProfilesEntry
    MAX-ACCESS not-accessible
    STATUS     current
    DESCRIPTION
            ""
    INDEX {
            hmStatusWtpMngmtRadiusServerProfilesEntryName
          }
    ::= { hmStatusWtpMngmtRadiusServerProfilesTable 1 }

HmStatusWtpMngmtRadiusServerProfilesEntry ::= SEQUENCE {
            hmStatusWtpMngmtRadiusServerProfilesEntryName DisplayString,
            hmStatusWtpMngmtRadiusServerProfilesEntryAccountIp IpAddress,
            hmStatusWtpMngmtRadiusServerProfilesEntryAccountPort Integer32,
            hmStatusWtpMngmtRadiusServerProfilesEntryAccountSecret DisplayString,
            hmStatusWtpMngmtRadiusServerProfilesEntryAccountLoopback DisplayString,
            hmStatusWtpMngmtRadiusServerProfilesEntryAccountProtocol INTEGER,
            hmStatusWtpMngmtRadiusServerProfilesEntryAccessIp IpAddress,
            hmStatusWtpMngmtRadiusServerProfilesEntryAccessPort Integer32,
            hmStatusWtpMngmtRadiusServerProfilesEntryAccessSecret DisplayString,
            hmStatusWtpMngmtRadiusServerProfilesEntryAccessLoopback DisplayString,
            hmStatusWtpMngmtRadiusServerProfilesEntryAccessProtocol INTEGER,
            hmStatusWtpMngmtRadiusServerProfilesEntryBackup DisplayString
    }

-- {COLUMN} 1.3.6.1.4.1.248.32.18.1.59.105.1.1
hmStatusWtpMngmtRadiusServerProfilesEntryName OBJECT-TYPE
    SYNTAX     DisplayString (SIZE(0..16))
    MAX-ACCESS read-only
    STATUS     current
    DESCRIPTION
            "-- empty --"
    ::= { hmStatusWtpMngmtRadiusServerProfilesEntry 1 }

-- {COLUMN} 1.3.6.1.4.1.248.32.18.1.59.105.1.2
hmStatusWtpMngmtRadiusServerProfilesEntryAccountIp OBJECT-TYPE
    SYNTAX     IpAddress
    MAX-ACCESS read-only
    STATUS     current
    DESCRIPTION
            "-- empty --"
    ::= { hmStatusWtpMngmtRadiusServerProfilesEntry 2 }

-- {COLUMN} 1.3.6.1.4.1.248.32.18.1.59.105.1.3
hmStatusWtpMngmtRadiusServerProfilesEntryAccountPort OBJECT-TYPE
    SYNTAX     Integer32 (0..65535)
    MAX-ACCESS read-only
    STATUS     current
    DESCRIPTION
            "-- empty --"
    ::= { hmStatusWtpMngmtRadiusServerProfilesEntry 3 }

-- {COLUMN} 1.3.6.1.4.1.248.32.18.1.59.105.1.4
hmStatusWtpMngmtRadiusServerProfilesEntryAccountSecret OBJECT-TYPE
    SYNTAX     DisplayString (SIZE(0..64))
    MAX-ACCESS read-only
    STATUS     current
    DESCRIPTION
            "-- empty --"
    ::= { hmStatusWtpMngmtRadiusServerProfilesEntry 4 }

-- {COLUMN} 1.3.6.1.4.1.248.32.18.1.59.105.1.5
hmStatusWtpMngmtRadiusServerProfilesEntryAccountLoopback OBJECT-TYPE
    SYNTAX     DisplayString (SIZE(0..16))
    MAX-ACCESS read-only
    STATUS     current
    DESCRIPTION
            "-- empty --"
    ::= { hmStatusWtpMngmtRadiusServerProfilesEntry 5 }

-- {COLUMN} 1.3.6.1.4.1.248.32.18.1.59.105.1.6
hmStatusWtpMngmtRadiusServerProfilesEntryAccountProtocol OBJECT-TYPE
    SYNTAX     INTEGER {
                  eRadius (0),
                  eRadsec (1)
            }
    MAX-ACCESS read-only
    STATUS     current
    DESCRIPTION
            "-- empty --"
    ::= { hmStatusWtpMngmtRadiusServerProfilesEntry 6 }

-- {COLUMN} 1.3.6.1.4.1.248.32.18.1.59.105.1.7
hmStatusWtpMngmtRadiusServerProfilesEntryAccessIp OBJECT-TYPE
    SYNTAX     IpAddress
    MAX-ACCESS read-only
    STATUS     current
    DESCRIPTION
            "-- empty --"
    ::= { hmStatusWtpMngmtRadiusServerProfilesEntry 7 }

-- {COLUMN} 1.3.6.1.4.1.248.32.18.1.59.105.1.8
hmStatusWtpMngmtRadiusServerProfilesEntryAccessPort OBJECT-TYPE
    SYNTAX     Integer32 (0..65535)
    MAX-ACCESS read-only
    STATUS     current
    DESCRIPTION
            "-- empty --"
    ::= { hmStatusWtpMngmtRadiusServerProfilesEntry 8 }

-- {COLUMN} 1.3.6.1.4.1.248.32.18.1.59.105.1.9
hmStatusWtpMngmtRadiusServerProfilesEntryAccessSecret OBJECT-TYPE
    SYNTAX     DisplayString (SIZE(0..64))
    MAX-ACCESS read-only
    STATUS     current
    DESCRIPTION
            "-- empty --"
    ::= { hmStatusWtpMngmtRadiusServerProfilesEntry 9 }

-- {COLUMN} 1.3.6.1.4.1.248.32.18.1.59.105.1.10
hmStatusWtpMngmtRadiusServerProfilesEntryAccessLoopback OBJECT-TYPE
    SYNTAX     DisplayString (SIZE(0..16))
    MAX-ACCESS read-only
    STATUS     current
    DESCRIPTION
            "-- empty --"
    ::= { hmStatusWtpMngmtRadiusServerProfilesEntry 10 }

-- {COLUMN} 1.3.6.1.4.1.248.32.18.1.59.105.1.11
hmStatusWtpMngmtRadiusServerProfilesEntryAccessProtocol OBJECT-TYPE
    SYNTAX     INTEGER {
                  eRadius (0),
                  eRadsec (1)
            }
    MAX-ACCESS read-only
    STATUS     current
    DESCRIPTION
            "-- empty --"
    ::= { hmStatusWtpMngmtRadiusServerProfilesEntry 11 }

-- {COLUMN} 1.3.6.1.4.1.248.32.18.1.59.105.1.12
hmStatusWtpMngmtRadiusServerProfilesEntryBackup OBJECT-TYPE
    SYNTAX     DisplayString (SIZE(0..16))
    MAX-ACCESS read-only
    STATUS     current
    DESCRIPTION
            "-- empty --"
    ::= { hmStatusWtpMngmtRadiusServerProfilesEntry 12 }

-- {TABLE} 1.3.6.1.4.1.248.32.18.1.59.106
hmStatusWtpMngmtAutowdsProfileTable OBJECT-TYPE
    SYNTAX     SEQUENCE OF HmStatusWtpMngmtAutowdsProfileEntry
    MAX-ACCESS not-accessible
    STATUS     current
    DESCRIPTION
            "-- empty --"
    ::= { hmStatusWtpMngmt 106 }

-- {ROW} 1.3.6.1.4.1.248.32.18.1.59.106.1
hmStatusWtpMngmtAutowdsProfileEntry OBJECT-TYPE
    SYNTAX     HmStatusWtpMngmtAutowdsProfileEntry
    MAX-ACCESS not-accessible
    STATUS     current
    DESCRIPTION
            ""
    INDEX {
            hmStatusWtpMngmtAutowdsProfileEntryName
          }
    ::= { hmStatusWtpMngmtAutowdsProfileTable 1 }

HmStatusWtpMngmtAutowdsProfileEntry ::= SEQUENCE {
            hmStatusWtpMngmtAutowdsProfileEntryName DisplayString,
            hmStatusWtpMngmtAutowdsProfileEntrySsid DisplayString,
            hmStatusWtpMngmtAutowdsProfileEntryKey DisplayString,
            hmStatusWtpMngmtAutowdsProfileEntryNetNumber Integer32,
            hmStatusWtpMngmtAutowdsProfileEntryEnabled INTEGER,
            hmStatusWtpMngmtAutowdsProfileEntryAllowExprInt INTEGER,
            hmStatusWtpMngmtAutowdsProfileEntryTimeTillPreconfScan Integer32,
            hmStatusWtpMngmtAutowdsProfileEntryTimeTillExpressScan Integer32,
            hmStatusWtpMngmtAutowdsProfileEntryInterfacePairing INTEGER
    }

-- {COLUMN} 1.3.6.1.4.1.248.32.18.1.59.106.1.1
hmStatusWtpMngmtAutowdsProfileEntryName OBJECT-TYPE
    SYNTAX     DisplayString (SIZE(0..31))
    MAX-ACCESS read-only
    STATUS     current
    DESCRIPTION
            "-- empty --"
    ::= { hmStatusWtpMngmtAutowdsProfileEntry 1 }

-- {COLUMN} 1.3.6.1.4.1.248.32.18.1.59.106.1.3
hmStatusWtpMngmtAutowdsProfileEntrySsid OBJECT-TYPE
    SYNTAX     DisplayString (SIZE(0..32))
    MAX-ACCESS read-only
    STATUS     current
    DESCRIPTION
            "-- empty --"
    ::= { hmStatusWtpMngmtAutowdsProfileEntry 3 }

-- {COLUMN} 1.3.6.1.4.1.248.32.18.1.59.106.1.4
hmStatusWtpMngmtAutowdsProfileEntryKey OBJECT-TYPE
    SYNTAX     DisplayString (SIZE(0..63))
    MAX-ACCESS read-only
    STATUS     current
    DESCRIPTION
            "-- empty --"
    ::= { hmStatusWtpMngmtAutowdsProfileEntry 4 }

-- {COLUMN} 1.3.6.1.4.1.248.32.18.1.59.106.1.5
hmStatusWtpMngmtAutowdsProfileEntryNetNumber OBJECT-TYPE
    SYNTAX     Integer32 (0..255)
    MAX-ACCESS read-only
    STATUS     current
    DESCRIPTION
            "-- empty --"
    ::= { hmStatusWtpMngmtAutowdsProfileEntry 5 }

-- {COLUMN} 1.3.6.1.4.1.248.32.18.1.59.106.1.6
hmStatusWtpMngmtAutowdsProfileEntryEnabled OBJECT-TYPE
    SYNTAX     INTEGER {
                  eNo (0),
                  eYes (1)
            }
    MAX-ACCESS read-only
    STATUS     current
    DESCRIPTION
            "-- empty --"
    ::= { hmStatusWtpMngmtAutowdsProfileEntry 6 }

-- {COLUMN} 1.3.6.1.4.1.248.32.18.1.59.106.1.7
hmStatusWtpMngmtAutowdsProfileEntryAllowExprInt OBJECT-TYPE
    SYNTAX     INTEGER {
                  eNo (0),
                  eYes (1)
            }
    MAX-ACCESS read-only
    STATUS     current
    DESCRIPTION
            "Allow-Express-Integration"
    ::= { hmStatusWtpMngmtAutowdsProfileEntry 7 }

-- {COLUMN} 1.3.6.1.4.1.248.32.18.1.59.106.1.15
hmStatusWtpMngmtAutowdsProfileEntryTimeTillPreconfScan OBJECT-TYPE
    SYNTAX     Integer32 (0..2147483647)
    MAX-ACCESS read-only
    STATUS     current
    DESCRIPTION
            "-- empty --"
    ::= { hmStatusWtpMngmtAutowdsProfileEntry 15 }

-- {COLUMN} 1.3.6.1.4.1.248.32.18.1.59.106.1.16
hmStatusWtpMngmtAutowdsProfileEntryTimeTillExpressScan OBJECT-TYPE
    SYNTAX     Integer32 (0..2147483647)
    MAX-ACCESS read-only
    STATUS     current
    DESCRIPTION
            "-- empty --"
    ::= { hmStatusWtpMngmtAutowdsProfileEntry 16 }

-- {COLUMN} 1.3.6.1.4.1.248.32.18.1.59.106.1.17
hmStatusWtpMngmtAutowdsProfileEntryInterfacePairing OBJECT-TYPE
    SYNTAX     INTEGER {
                  eAutomatic (0),
                  eStrict (1),
                  eMixed (2)
            }
    MAX-ACCESS read-only
    STATUS     current
    DESCRIPTION
            "-- empty --"
    ::= { hmStatusWtpMngmtAutowdsProfileEntry 17 }

-- {TABLE} 1.3.6.1.4.1.248.32.18.1.59.107
hmStatusWtpMngmtAutowdsTopologyTable OBJECT-TYPE
    SYNTAX     SEQUENCE OF HmStatusWtpMngmtAutowdsTopologyEntry
    MAX-ACCESS not-accessible
    STATUS     current
    DESCRIPTION
            "-- empty --"
    ::= { hmStatusWtpMngmt 107 }

-- {ROW} 1.3.6.1.4.1.248.32.18.1.59.107.1
hmStatusWtpMngmtAutowdsTopologyEntry OBJECT-TYPE
    SYNTAX     HmStatusWtpMngmtAutowdsTopologyEntry
    MAX-ACCESS not-accessible
    STATUS     current
    DESCRIPTION
            ""
    INDEX {
            hmStatusWtpMngmtAutowdsTopologyEntryAutowdsProfile,
            hmStatusWtpMngmtAutowdsTopologyEntryPriority,
            hmStatusWtpMngmtAutowdsTopologyEntrySlaveApName,
            hmStatusWtpMngmtAutowdsTopologyEntrySlaveApWlanIfc,
            hmStatusWtpMngmtAutowdsTopologyEntrySlaveApWlanMac
          }
    ::= { hmStatusWtpMngmtAutowdsTopologyTable 1 }

HmStatusWtpMngmtAutowdsTopologyEntry ::= SEQUENCE {
            hmStatusWtpMngmtAutowdsTopologyEntryAutowdsProfile DisplayString,
            hmStatusWtpMngmtAutowdsTopologyEntryPriority Integer32,
            hmStatusWtpMngmtAutowdsTopologyEntrySlaveApName DisplayString,
            hmStatusWtpMngmtAutowdsTopologyEntrySlaveApWlanIfc INTEGER,
            hmStatusWtpMngmtAutowdsTopologyEntrySlaveApWlanMac DisplayString,
            hmStatusWtpMngmtAutowdsTopologyEntryMasterApName DisplayString,
            hmStatusWtpMngmtAutowdsTopologyEntryMasterApWlanIfc INTEGER,
            hmStatusWtpMngmtAutowdsTopologyEntryMasterApWlanMac DisplayString,
            hmStatusWtpMngmtAutowdsTopologyEntryKey DisplayString,
            hmStatusWtpMngmtAutowdsTopologyEntryEnabled INTEGER,
            hmStatusWtpMngmtAutowdsTopologyEntrySlaveTxLimit Integer32,
            hmStatusWtpMngmtAutowdsTopologyEntryMasterTxLimit Integer32,
            hmStatusWtpMngmtAutowdsTopologyEntryLinkLossTimeout Integer32,
            hmStatusWtpMngmtAutowdsTopologyEntryContinuation Integer32,
            hmStatusWtpMngmtAutowdsTopologyEntryGenerated INTEGER,
            hmStatusWtpMngmtAutowdsTopologyEntryP2pIndex Integer32,
            hmStatusWtpMngmtAutowdsTopologyEntryP2pRole INTEGER
    }

-- {COLUMN} 1.3.6.1.4.1.248.32.18.1.59.107.1.1
hmStatusWtpMngmtAutowdsTopologyEntryAutowdsProfile OBJECT-TYPE
    SYNTAX     DisplayString (SIZE(0..31))
    MAX-ACCESS read-only
    STATUS     current
    DESCRIPTION
            "-- empty --"
    ::= { hmStatusWtpMngmtAutowdsTopologyEntry 1 }

-- {COLUMN} 1.3.6.1.4.1.248.32.18.1.59.107.1.2
hmStatusWtpMngmtAutowdsTopologyEntryPriority OBJECT-TYPE
    SYNTAX     Integer32 (0..65535)
    MAX-ACCESS read-only
    STATUS     current
    DESCRIPTION
            "-- empty --"
    ::= { hmStatusWtpMngmtAutowdsTopologyEntry 2 }

-- {COLUMN} 1.3.6.1.4.1.248.32.18.1.59.107.1.3
hmStatusWtpMngmtAutowdsTopologyEntrySlaveApName OBJECT-TYPE
    SYNTAX     DisplayString (SIZE(0..16))
    MAX-ACCESS read-only
    STATUS     current
    DESCRIPTION
            "-- empty --"
    ::= { hmStatusWtpMngmtAutowdsTopologyEntry 3 }

-- {COLUMN} 1.3.6.1.4.1.248.32.18.1.59.107.1.4
hmStatusWtpMngmtAutowdsTopologyEntrySlaveApWlanIfc OBJECT-TYPE
    SYNTAX     INTEGER {
                  eWlan1 (1),
                  eWlan2 (2)
            }
    MAX-ACCESS read-only
    STATUS     current
    DESCRIPTION
            "-- empty --"
    ::= { hmStatusWtpMngmtAutowdsTopologyEntry 4 }

-- {COLUMN} 1.3.6.1.4.1.248.32.18.1.59.107.1.5
hmStatusWtpMngmtAutowdsTopologyEntrySlaveApWlanMac OBJECT-TYPE
    SYNTAX     DisplayString (SIZE(0..12))
    MAX-ACCESS read-only
    STATUS     current
    DESCRIPTION
            "-- empty --"
    ::= { hmStatusWtpMngmtAutowdsTopologyEntry 5 }

-- {COLUMN} 1.3.6.1.4.1.248.32.18.1.59.107.1.6
hmStatusWtpMngmtAutowdsTopologyEntryMasterApName OBJECT-TYPE
    SYNTAX     DisplayString (SIZE(0..16))
    MAX-ACCESS read-only
    STATUS     current
    DESCRIPTION
            "-- empty --"
    ::= { hmStatusWtpMngmtAutowdsTopologyEntry 6 }

-- {COLUMN} 1.3.6.1.4.1.248.32.18.1.59.107.1.7
hmStatusWtpMngmtAutowdsTopologyEntryMasterApWlanIfc OBJECT-TYPE
    SYNTAX     INTEGER {
                  eWlan1 (1),
                  eWlan2 (2)
            }
    MAX-ACCESS read-only
    STATUS     current
    DESCRIPTION
            "-- empty --"
    ::= { hmStatusWtpMngmtAutowdsTopologyEntry 7 }

-- {COLUMN} 1.3.6.1.4.1.248.32.18.1.59.107.1.8
hmStatusWtpMngmtAutowdsTopologyEntryMasterApWlanMac OBJECT-TYPE
    SYNTAX     DisplayString (SIZE(0..12))
    MAX-ACCESS read-only
    STATUS     current
    DESCRIPTION
            "-- empty --"
    ::= { hmStatusWtpMngmtAutowdsTopologyEntry 8 }

-- {COLUMN} 1.3.6.1.4.1.248.32.18.1.59.107.1.9
hmStatusWtpMngmtAutowdsTopologyEntryKey OBJECT-TYPE
    SYNTAX     DisplayString (SIZE(0..63))
    MAX-ACCESS read-only
    STATUS     current
    DESCRIPTION
            "-- empty --"
    ::= { hmStatusWtpMngmtAutowdsTopologyEntry 9 }

-- {COLUMN} 1.3.6.1.4.1.248.32.18.1.59.107.1.10
hmStatusWtpMngmtAutowdsTopologyEntryEnabled OBJECT-TYPE
    SYNTAX     INTEGER {
                  eNo (0),
                  eYes (1)
            }
    MAX-ACCESS read-only
    STATUS     current
    DESCRIPTION
            "-- empty --"
    ::= { hmStatusWtpMngmtAutowdsTopologyEntry 10 }

-- {COLUMN} 1.3.6.1.4.1.248.32.18.1.59.107.1.12
hmStatusWtpMngmtAutowdsTopologyEntrySlaveTxLimit OBJECT-TYPE
    SYNTAX     Integer32 (0..2147483647)
    MAX-ACCESS read-only
    STATUS     current
    DESCRIPTION
            "-- empty --"
    ::= { hmStatusWtpMngmtAutowdsTopologyEntry 12 }

-- {COLUMN} 1.3.6.1.4.1.248.32.18.1.59.107.1.13
hmStatusWtpMngmtAutowdsTopologyEntryMasterTxLimit OBJECT-TYPE
    SYNTAX     Integer32 (0..2147483647)
    MAX-ACCESS read-only
    STATUS     current
    DESCRIPTION
            "-- empty --"
    ::= { hmStatusWtpMngmtAutowdsTopologyEntry 13 }

-- {COLUMN} 1.3.6.1.4.1.248.32.18.1.59.107.1.14
hmStatusWtpMngmtAutowdsTopologyEntryLinkLossTimeout OBJECT-TYPE
    SYNTAX     Integer32 (0..2147483647)
    MAX-ACCESS read-only
    STATUS     current
    DESCRIPTION
            "-- empty --"
    ::= { hmStatusWtpMngmtAutowdsTopologyEntry 14 }

-- {COLUMN} 1.3.6.1.4.1.248.32.18.1.59.107.1.16
hmStatusWtpMngmtAutowdsTopologyEntryContinuation OBJECT-TYPE
    SYNTAX     Integer32 (0..65535)
    MAX-ACCESS read-only
    STATUS     current
    DESCRIPTION
            ""
    ::= { hmStatusWtpMngmtAutowdsTopologyEntry 16 }

-- {COLUMN} 1.3.6.1.4.1.248.32.18.1.59.107.1.17
hmStatusWtpMngmtAutowdsTopologyEntryGenerated OBJECT-TYPE
    SYNTAX     INTEGER {
                  eNo (0),
                  eYes (1)
            }
    MAX-ACCESS read-only
    STATUS     current
    DESCRIPTION
            "-- empty --"
    ::= { hmStatusWtpMngmtAutowdsTopologyEntry 17 }

-- {COLUMN} 1.3.6.1.4.1.248.32.18.1.59.107.1.19
hmStatusWtpMngmtAutowdsTopologyEntryP2pIndex OBJECT-TYPE
    SYNTAX     Integer32 (0..65535)
    MAX-ACCESS read-only
    STATUS     current
    DESCRIPTION
            "-- empty --"
    ::= { hmStatusWtpMngmtAutowdsTopologyEntry 19 }

-- {COLUMN} 1.3.6.1.4.1.248.32.18.1.59.107.1.20
hmStatusWtpMngmtAutowdsTopologyEntryP2pRole OBJECT-TYPE
    SYNTAX     INTEGER {
                  eNone (0),
                  eSlave (1),
                  eMaster (2)
            }
    MAX-ACCESS read-only
    STATUS     current
    DESCRIPTION
            "-- empty --"
    ::= { hmStatusWtpMngmtAutowdsTopologyEntry 20 }

-- {NODE} 1.3.6.1.4.1.248.32.18.1.59.109
hmStatusWtpMngmtAutowdsOperation OBJECT IDENTIFIER ::= { hmStatusWtpMngmt 109 }

-- {SCALAR} 1.3.6.1.4.1.248.32.18.1.59.109.1
hmStatusWtpMngmtAutowdsOperationActiveScanMode OBJECT-TYPE
    SYNTAX     INTEGER {
                  eNone (0),
                  eExpress (1),
                  ePreconfigured (2)
            }
    MAX-ACCESS read-only
    STATUS     current
    DESCRIPTION
            "-- empty --"
    ::= { hmStatusWtpMngmtAutowdsOperation 1 }

-- {SCALAR} 1.3.6.1.4.1.248.32.18.1.59.109.2
hmStatusWtpMngmtAutowdsOperationCapwapUp OBJECT-TYPE
    SYNTAX     INTEGER {
                  eNo (0),
                  eYes (1)
            }
    MAX-ACCESS read-only
    STATUS     current
    DESCRIPTION
            "-- empty --"
    ::= { hmStatusWtpMngmtAutowdsOperation 2 }

-- {SCALAR} 1.3.6.1.4.1.248.32.18.1.59.109.3
hmStatusWtpMngmtAutowdsOperationCapwapUpAgainAfterConfig OBJECT-TYPE
    SYNTAX     INTEGER {
                  eNo (0),
                  eYes (1)
            }
    MAX-ACCESS read-only
    STATUS     current
    DESCRIPTION
            "-- empty --"
    ::= { hmStatusWtpMngmtAutowdsOperation 3 }

-- {SCALAR} 1.3.6.1.4.1.248.32.18.1.59.109.4
hmStatusWtpMngmtAutowdsOperationAutowdsFallbackTimer OBJECT-TYPE
    SYNTAX     Integer32 (0..2147483647)
    MAX-ACCESS read-only
    STATUS     current
    DESCRIPTION
            "-- empty --"
    ::= { hmStatusWtpMngmtAutowdsOperation 4 }

-- {SCALAR} 1.3.6.1.4.1.248.32.18.1.59.109.5
hmStatusWtpMngmtAutowdsOperationAutowdsFallbForceDeassocTimer OBJECT-TYPE
    SYNTAX     Integer32 (0..2147483647)
    MAX-ACCESS read-only
    STATUS     current
    DESCRIPTION
            ""
    ::= { hmStatusWtpMngmtAutowdsOperation 5 }

-- {SCALAR} 1.3.6.1.4.1.248.32.18.1.59.109.6
hmStatusWtpMngmtAutowdsOperationCapwapContinuationTimer OBJECT-TYPE
    SYNTAX     Integer32 (0..2147483647)
    MAX-ACCESS read-only
    STATUS     current
    DESCRIPTION
            "-- empty --"
    ::= { hmStatusWtpMngmtAutowdsOperation 6 }

-- {SCALAR} 1.3.6.1.4.1.248.32.18.1.59.109.7
hmStatusWtpMngmtAutowdsOperationCapwapSilentTimer OBJECT-TYPE
    SYNTAX     Integer32 (0..2147483647)
    MAX-ACCESS read-only
    STATUS     current
    DESCRIPTION
            "-- empty --"
    ::= { hmStatusWtpMngmtAutowdsOperation 7 }

-- {TABLE} 1.3.6.1.4.1.248.32.18.1.59.110
hmStatusWtpMngmtLedProfilesTable OBJECT-TYPE
    SYNTAX     SEQUENCE OF HmStatusWtpMngmtLedProfilesEntry
    MAX-ACCESS not-accessible
    STATUS     current
    DESCRIPTION
            "-- empty --"
    ::= { hmStatusWtpMngmt 110 }

-- {ROW} 1.3.6.1.4.1.248.32.18.1.59.110.1
hmStatusWtpMngmtLedProfilesEntry OBJECT-TYPE
    SYNTAX     HmStatusWtpMngmtLedProfilesEntry
    MAX-ACCESS not-accessible
    STATUS     current
    DESCRIPTION
            ""
    INDEX {
            hmStatusWtpMngmtLedProfilesEntryName
          }
    ::= { hmStatusWtpMngmtLedProfilesTable 1 }

HmStatusWtpMngmtLedProfilesEntry ::= SEQUENCE {
            hmStatusWtpMngmtLedProfilesEntryName DisplayString,
            hmStatusWtpMngmtLedProfilesEntryLedMode INTEGER,
            hmStatusWtpMngmtLedProfilesEntryLedOffSeconds Integer32
    }

-- {COLUMN} 1.3.6.1.4.1.248.32.18.1.59.110.1.1
hmStatusWtpMngmtLedProfilesEntryName OBJECT-TYPE
    SYNTAX     DisplayString (SIZE(0..31))
    MAX-ACCESS read-only
    STATUS     current
    DESCRIPTION
            "-- empty --"
    ::= { hmStatusWtpMngmtLedProfilesEntry 1 }

-- {COLUMN} 1.3.6.1.4.1.248.32.18.1.59.110.1.4
hmStatusWtpMngmtLedProfilesEntryLedMode OBJECT-TYPE
    SYNTAX     INTEGER {
                  eOn (0),
                  eOff (1),
                  eTimedOff (2)
            }
    MAX-ACCESS read-only
    STATUS     current
    DESCRIPTION
            "-- empty --"
    ::= { hmStatusWtpMngmtLedProfilesEntry 4 }

-- {COLUMN} 1.3.6.1.4.1.248.32.18.1.59.110.1.5
hmStatusWtpMngmtLedProfilesEntryLedOffSeconds OBJECT-TYPE
    SYNTAX     Integer32 (0..2147483647)
    MAX-ACCESS read-only
    STATUS     current
    DESCRIPTION
            "-- empty --"
    ::= { hmStatusWtpMngmtLedProfilesEntry 5 }

-- {TABLE} 1.3.6.1.4.1.248.32.18.1.59.120
hmStatusWtpMngmtLogTableTable OBJECT-TYPE
    SYNTAX     SEQUENCE OF HmStatusWtpMngmtLogTableEntry
    MAX-ACCESS not-accessible
    STATUS     current
    DESCRIPTION
            "-- empty --"
    ::= { hmStatusWtpMngmt 120 }

-- {ROW} 1.3.6.1.4.1.248.32.18.1.59.120.1
hmStatusWtpMngmtLogTableEntry OBJECT-TYPE
    SYNTAX     HmStatusWtpMngmtLogTableEntry
    MAX-ACCESS not-accessible
    STATUS     current
    DESCRIPTION
            ""
    INDEX {
            hmStatusWtpMngmtLogTableEntryIndex
          }
    ::= { hmStatusWtpMngmtLogTableTable 1 }

HmStatusWtpMngmtLogTableEntry ::= SEQUENCE {
            hmStatusWtpMngmtLogTableEntryIndex Integer32,
            hmStatusWtpMngmtLogTableEntryTime DisplayString,
            hmStatusWtpMngmtLogTableEntryEvent DisplayString
    }

-- {COLUMN} 1.3.6.1.4.1.248.32.18.1.59.120.1.1
hmStatusWtpMngmtLogTableEntryIndex OBJECT-TYPE
    SYNTAX     Integer32 (0..2147483647)
    MAX-ACCESS read-only
    STATUS     current
    DESCRIPTION
            "-- empty --"
    ::= { hmStatusWtpMngmtLogTableEntry 1 }

-- {COLUMN} 1.3.6.1.4.1.248.32.18.1.59.120.1.2
hmStatusWtpMngmtLogTableEntryTime OBJECT-TYPE
    SYNTAX     DisplayString (SIZE(0..19))
    MAX-ACCESS read-only
    STATUS     current
    DESCRIPTION
            "-- empty --"
    ::= { hmStatusWtpMngmtLogTableEntry 2 }

-- {COLUMN} 1.3.6.1.4.1.248.32.18.1.59.120.1.6
hmStatusWtpMngmtLogTableEntryEvent OBJECT-TYPE
    SYNTAX     DisplayString (SIZE(0..80))
    MAX-ACCESS read-only
    STATUS     current
    DESCRIPTION
            "-- empty --"
    ::= { hmStatusWtpMngmtLogTableEntry 6 }

-- {TABLE} 1.3.6.1.4.1.248.32.18.1.59.248
hmStatusWtpMngmtWIdsTable OBJECT-TYPE
    SYNTAX     SEQUENCE OF HmStatusWtpMngmtWIdsEntry
    MAX-ACCESS not-accessible
    STATUS     current
    DESCRIPTION
            ""
    ::= { hmStatusWtpMngmt 248 }

-- {ROW} 1.3.6.1.4.1.248.32.18.1.59.248.1
hmStatusWtpMngmtWIdsEntry OBJECT-TYPE
    SYNTAX     HmStatusWtpMngmtWIdsEntry
    MAX-ACCESS not-accessible
    STATUS     current
    DESCRIPTION
            ""
    INDEX {
            hmStatusWtpMngmtWIdsEntryName
          }
    ::= { hmStatusWtpMngmtWIdsTable 1 }

HmStatusWtpMngmtWIdsEntry ::= SEQUENCE {
            hmStatusWtpMngmtWIdsEntryName DisplayString,
            hmStatusWtpMngmtWIdsEntryOperating INTEGER,
            hmStatusWtpMngmtWIdsEntryEAPOLStartCtrLim Integer32,
            hmStatusWtpMngmtWIdsEntryEAPOLStartCtrInt Integer32,
            hmStatusWtpMngmtWIdsEntryProbeBroadCtrLim Integer32,
            hmStatusWtpMngmtWIdsEntryProbeBroadCtrInt Integer32,
            hmStatusWtpMngmtWIdsEntryDeauthBroadCtrLimt Integer32,
            hmStatusWtpMngmtWIdsEntryDeauthBroadCtrInt Integer32,
            hmStatusWtpMngmtWIdsEntryDeauthCtrLim Integer32,
            hmStatusWtpMngmtWIdsEntryDeauthCtrInt Integer32,
            hmStatusWtpMngmtWIdsEntryAssocReqCtrLim Integer32,
            hmStatusWtpMngmtWIdsEntryAssocReqCtrInt Integer32,
            hmStatusWtpMngmtWIdsEntryReAssocReqCtrLim Integer32,
            hmStatusWtpMngmtWIdsEntryReAssocReqCtrInt Integer32,
            hmStatusWtpMngmtWIdsEntryAuthCtrLim Integer32,
            hmStatusWtpMngmtWIdsEntryAuthCtrInt Integer32,
            hmStatusWtpMngmtWIdsEntryDisAssocCtrLim Integer32,
            hmStatusWtpMngmtWIdsEntryDisAssocCtrInt Integer32,
            hmStatusWtpMngmtWIdsEntryIdsOperational INTEGER,
            hmStatusWtpMngmtWIdsEntrySyslogOperational INTEGER,
            hmStatusWtpMngmtWIdsEntrySNMPTrapsOperational INTEGER,
            hmStatusWtpMngmtWIdsEntryEMail INTEGER,
            hmStatusWtpMngmtWIdsEntryEMailReceiver DisplayString,
            hmStatusWtpMngmtWIdsEntryEMailAggregateInterval Integer32,
            hmStatusWtpMngmtWIdsEntryBlockAckOutOfWindowCtrLim Integer32,
            hmStatusWtpMngmtWIdsEntryBlockAckOutOfWindowCtrInt Integer32,
            hmStatusWtpMngmtWIdsEntryBlockAckAfterDelBACtrLim Integer32,
            hmStatusWtpMngmtWIdsEntryBlockAckAfterDelBACtrInt Integer32,
            hmStatusWtpMngmtWIdsEntryNullDataFloodCtrLim Integer32,
            hmStatusWtpMngmtWIdsEntryNullDataFloodCtrInt Integer32,
            hmStatusWtpMngmtWIdsEntryNullDataPSOverflowCtrLim Integer32,
            hmStatusWtpMngmtWIdsEntryNullDataPSOverflowCtrInt Integer32,
            hmStatusWtpMngmtWIdsEntryPSPollTIMInterval Integer32,
            hmStatusWtpMngmtWIdsEntryPSPollTIMIntervalCtrLim Integer32,
            hmStatusWtpMngmtWIdsEntryPSPollTIMIntervalCtrInt Integer32,
            hmStatusWtpMngmtWIdsEntrySMPSMulStreamCtrLim Integer32,
            hmStatusWtpMngmtWIdsEntrySMPSMulStreamCtrInt Integer32,
            hmStatusWtpMngmtWIdsEntrySMPSSingleStreamCtrLim Integer32,
            hmStatusWtpMngmtWIdsEntrySMPSSingleStreamCtrInt Integer32,
            hmStatusWtpMngmtWIdsEntryDisAssocBroadCtrLim Integer32,
            hmStatusWtpMngmtWIdsEntryDisAssocBroadCtrInt Integer32,
            hmStatusWtpMngmtWIdsEntryIntruderIdentification INTEGER,
            hmStatusWtpMngmtWIdsEntryTimeoutIntruderActivity Integer32,
            hmStatusWtpMngmtWIdsEntryWhiteListId Integer32,
            hmStatusWtpMngmtWIdsEntryStoreIntruderDhcpRequests INTEGER
    }

-- {COLUMN} 1.3.6.1.4.1.248.32.18.1.59.248.1.1
hmStatusWtpMngmtWIdsEntryName OBJECT-TYPE
    SYNTAX     DisplayString (SIZE(0..31))
    MAX-ACCESS read-only
    STATUS     current
    DESCRIPTION
            "-- empty --"
    ::= { hmStatusWtpMngmtWIdsEntry 1 }

-- {COLUMN} 1.3.6.1.4.1.248.32.18.1.59.248.1.2
hmStatusWtpMngmtWIdsEntryOperating OBJECT-TYPE
    SYNTAX     INTEGER {
                  eNo (0),
                  eYes (1)
            }
    MAX-ACCESS read-only
    STATUS     current
    DESCRIPTION
            "-- empty --"
    ::= { hmStatusWtpMngmtWIdsEntry 2 }

-- {COLUMN} 1.3.6.1.4.1.248.32.18.1.59.248.1.3
hmStatusWtpMngmtWIdsEntryEAPOLStartCtrLim OBJECT-TYPE
    SYNTAX     Integer32 (0..2147483647)
    MAX-ACCESS read-only
    STATUS     current
    DESCRIPTION
            ""
    ::= { hmStatusWtpMngmtWIdsEntry 3 }

-- {COLUMN} 1.3.6.1.4.1.248.32.18.1.59.248.1.4
hmStatusWtpMngmtWIdsEntryEAPOLStartCtrInt OBJECT-TYPE
    SYNTAX     Integer32 (0..2147483647)
    MAX-ACCESS read-only
    STATUS     current
    DESCRIPTION
            ""
    ::= { hmStatusWtpMngmtWIdsEntry 4 }

-- {COLUMN} 1.3.6.1.4.1.248.32.18.1.59.248.1.5
hmStatusWtpMngmtWIdsEntryProbeBroadCtrLim OBJECT-TYPE
    SYNTAX     Integer32 (0..2147483647)
    MAX-ACCESS read-only
    STATUS     current
    DESCRIPTION
            ""
    ::= { hmStatusWtpMngmtWIdsEntry 5 }

-- {COLUMN} 1.3.6.1.4.1.248.32.18.1.59.248.1.6
hmStatusWtpMngmtWIdsEntryProbeBroadCtrInt OBJECT-TYPE
    SYNTAX     Integer32 (0..2147483647)
    MAX-ACCESS read-only
    STATUS     current
    DESCRIPTION
            ""
    ::= { hmStatusWtpMngmtWIdsEntry 6 }

-- {COLUMN} 1.3.6.1.4.1.248.32.18.1.59.248.1.7
hmStatusWtpMngmtWIdsEntryDeauthBroadCtrLimt OBJECT-TYPE
    SYNTAX     Integer32 (0..2147483647)
    MAX-ACCESS read-only
    STATUS     current
    DESCRIPTION
            ""
    ::= { hmStatusWtpMngmtWIdsEntry 7 }

-- {COLUMN} 1.3.6.1.4.1.248.32.18.1.59.248.1.8
hmStatusWtpMngmtWIdsEntryDeauthBroadCtrInt OBJECT-TYPE
    SYNTAX     Integer32 (0..2147483647)
    MAX-ACCESS read-only
    STATUS     current
    DESCRIPTION
            ""
    ::= { hmStatusWtpMngmtWIdsEntry 8 }

-- {COLUMN} 1.3.6.1.4.1.248.32.18.1.59.248.1.9
hmStatusWtpMngmtWIdsEntryDeauthCtrLim OBJECT-TYPE
    SYNTAX     Integer32 (0..2147483647)
    MAX-ACCESS read-only
    STATUS     current
    DESCRIPTION
            ""
    ::= { hmStatusWtpMngmtWIdsEntry 9 }

-- {COLUMN} 1.3.6.1.4.1.248.32.18.1.59.248.1.10
hmStatusWtpMngmtWIdsEntryDeauthCtrInt OBJECT-TYPE
    SYNTAX     Integer32 (0..2147483647)
    MAX-ACCESS read-only
    STATUS     current
    DESCRIPTION
            ""
    ::= { hmStatusWtpMngmtWIdsEntry 10 }

-- {COLUMN} 1.3.6.1.4.1.248.32.18.1.59.248.1.11
hmStatusWtpMngmtWIdsEntryAssocReqCtrLim OBJECT-TYPE
    SYNTAX     Integer32 (0..2147483647)
    MAX-ACCESS read-only
    STATUS     current
    DESCRIPTION
            ""
    ::= { hmStatusWtpMngmtWIdsEntry 11 }

-- {COLUMN} 1.3.6.1.4.1.248.32.18.1.59.248.1.12
hmStatusWtpMngmtWIdsEntryAssocReqCtrInt OBJECT-TYPE
    SYNTAX     Integer32 (0..2147483647)
    MAX-ACCESS read-only
    STATUS     current
    DESCRIPTION
            ""
    ::= { hmStatusWtpMngmtWIdsEntry 12 }

-- {COLUMN} 1.3.6.1.4.1.248.32.18.1.59.248.1.13
hmStatusWtpMngmtWIdsEntryReAssocReqCtrLim OBJECT-TYPE
    SYNTAX     Integer32 (0..2147483647)
    MAX-ACCESS read-only
    STATUS     current
    DESCRIPTION
            ""
    ::= { hmStatusWtpMngmtWIdsEntry 13 }

-- {COLUMN} 1.3.6.1.4.1.248.32.18.1.59.248.1.14
hmStatusWtpMngmtWIdsEntryReAssocReqCtrInt OBJECT-TYPE
    SYNTAX     Integer32 (0..2147483647)
    MAX-ACCESS read-only
    STATUS     current
    DESCRIPTION
            ""
    ::= { hmStatusWtpMngmtWIdsEntry 14 }

-- {COLUMN} 1.3.6.1.4.1.248.32.18.1.59.248.1.15
hmStatusWtpMngmtWIdsEntryAuthCtrLim OBJECT-TYPE
    SYNTAX     Integer32 (0..2147483647)
    MAX-ACCESS read-only
    STATUS     current
    DESCRIPTION
            ""
    ::= { hmStatusWtpMngmtWIdsEntry 15 }

-- {COLUMN} 1.3.6.1.4.1.248.32.18.1.59.248.1.16
hmStatusWtpMngmtWIdsEntryAuthCtrInt OBJECT-TYPE
    SYNTAX     Integer32 (0..2147483647)
    MAX-ACCESS read-only
    STATUS     current
    DESCRIPTION
            ""
    ::= { hmStatusWtpMngmtWIdsEntry 16 }

-- {COLUMN} 1.3.6.1.4.1.248.32.18.1.59.248.1.17
hmStatusWtpMngmtWIdsEntryDisAssocCtrLim OBJECT-TYPE
    SYNTAX     Integer32 (0..2147483647)
    MAX-ACCESS read-only
    STATUS     current
    DESCRIPTION
            ""
    ::= { hmStatusWtpMngmtWIdsEntry 17 }

-- {COLUMN} 1.3.6.1.4.1.248.32.18.1.59.248.1.18
hmStatusWtpMngmtWIdsEntryDisAssocCtrInt OBJECT-TYPE
    SYNTAX     Integer32 (0..2147483647)
    MAX-ACCESS read-only
    STATUS     current
    DESCRIPTION
            ""
    ::= { hmStatusWtpMngmtWIdsEntry 18 }

-- {COLUMN} 1.3.6.1.4.1.248.32.18.1.59.248.1.19
hmStatusWtpMngmtWIdsEntryIdsOperational OBJECT-TYPE
    SYNTAX     INTEGER {
                  eNo (0),
                  eYes (1)
            }
    MAX-ACCESS read-only
    STATUS     current
    DESCRIPTION
            ""
    ::= { hmStatusWtpMngmtWIdsEntry 19 }

-- {COLUMN} 1.3.6.1.4.1.248.32.18.1.59.248.1.20
hmStatusWtpMngmtWIdsEntrySyslogOperational OBJECT-TYPE
    SYNTAX     INTEGER {
                  eNo (0),
                  eYes (1)
            }
    MAX-ACCESS read-only
    STATUS     current
    DESCRIPTION
            ""
    ::= { hmStatusWtpMngmtWIdsEntry 20 }

-- {COLUMN} 1.3.6.1.4.1.248.32.18.1.59.248.1.21
hmStatusWtpMngmtWIdsEntrySNMPTrapsOperational OBJECT-TYPE
    SYNTAX     INTEGER {
                  eNo (0),
                  eYes (1)
            }
    MAX-ACCESS read-only
    STATUS     current
    DESCRIPTION
            ""
    ::= { hmStatusWtpMngmtWIdsEntry 21 }

-- {COLUMN} 1.3.6.1.4.1.248.32.18.1.59.248.1.22
hmStatusWtpMngmtWIdsEntryEMail OBJECT-TYPE
    SYNTAX     INTEGER {
                  eNo (0),
                  eYes (1)
            }
    MAX-ACCESS read-only
    STATUS     current
    DESCRIPTION
            "-- empty --"
    ::= { hmStatusWtpMngmtWIdsEntry 22 }

-- {COLUMN} 1.3.6.1.4.1.248.32.18.1.59.248.1.23
hmStatusWtpMngmtWIdsEntryEMailReceiver OBJECT-TYPE
    SYNTAX     DisplayString (SIZE(0..64))
    MAX-ACCESS read-only
    STATUS     current
    DESCRIPTION
            "-- empty --"
    ::= { hmStatusWtpMngmtWIdsEntry 23 }

-- {COLUMN} 1.3.6.1.4.1.248.32.18.1.59.248.1.24
hmStatusWtpMngmtWIdsEntryEMailAggregateInterval OBJECT-TYPE
    SYNTAX     Integer32 (0..2147483647)
    MAX-ACCESS read-only
    STATUS     current
    DESCRIPTION
            ""
    ::= { hmStatusWtpMngmtWIdsEntry 24 }

-- {COLUMN} 1.3.6.1.4.1.248.32.18.1.59.248.1.26
hmStatusWtpMngmtWIdsEntryBlockAckOutOfWindowCtrLim OBJECT-TYPE
    SYNTAX     Integer32 (0..2147483647)
    MAX-ACCESS read-only
    STATUS     current
    DESCRIPTION
            ""
    ::= { hmStatusWtpMngmtWIdsEntry 26 }

-- {COLUMN} 1.3.6.1.4.1.248.32.18.1.59.248.1.27
hmStatusWtpMngmtWIdsEntryBlockAckOutOfWindowCtrInt OBJECT-TYPE
    SYNTAX     Integer32 (0..2147483647)
    MAX-ACCESS read-only
    STATUS     current
    DESCRIPTION
            ""
    ::= { hmStatusWtpMngmtWIdsEntry 27 }

-- {COLUMN} 1.3.6.1.4.1.248.32.18.1.59.248.1.28
hmStatusWtpMngmtWIdsEntryBlockAckAfterDelBACtrLim OBJECT-TYPE
    SYNTAX     Integer32 (0..2147483647)
    MAX-ACCESS read-only
    STATUS     current
    DESCRIPTION
            ""
    ::= { hmStatusWtpMngmtWIdsEntry 28 }

-- {COLUMN} 1.3.6.1.4.1.248.32.18.1.59.248.1.29
hmStatusWtpMngmtWIdsEntryBlockAckAfterDelBACtrInt OBJECT-TYPE
    SYNTAX     Integer32 (0..2147483647)
    MAX-ACCESS read-only
    STATUS     current
    DESCRIPTION
            ""
    ::= { hmStatusWtpMngmtWIdsEntry 29 }

-- {COLUMN} 1.3.6.1.4.1.248.32.18.1.59.248.1.31
hmStatusWtpMngmtWIdsEntryNullDataFloodCtrLim OBJECT-TYPE
    SYNTAX     Integer32 (0..2147483647)
    MAX-ACCESS read-only
    STATUS     current
    DESCRIPTION
            ""
    ::= { hmStatusWtpMngmtWIdsEntry 31 }

-- {COLUMN} 1.3.6.1.4.1.248.32.18.1.59.248.1.32
hmStatusWtpMngmtWIdsEntryNullDataFloodCtrInt OBJECT-TYPE
    SYNTAX     Integer32 (0..2147483647)
    MAX-ACCESS read-only
    STATUS     current
    DESCRIPTION
            ""
    ::= { hmStatusWtpMngmtWIdsEntry 32 }

-- {COLUMN} 1.3.6.1.4.1.248.32.18.1.59.248.1.34
hmStatusWtpMngmtWIdsEntryNullDataPSOverflowCtrLim OBJECT-TYPE
    SYNTAX     Integer32 (0..2147483647)
    MAX-ACCESS read-only
    STATUS     current
    DESCRIPTION
            ""
    ::= { hmStatusWtpMngmtWIdsEntry 34 }

-- {COLUMN} 1.3.6.1.4.1.248.32.18.1.59.248.1.35
hmStatusWtpMngmtWIdsEntryNullDataPSOverflowCtrInt OBJECT-TYPE
    SYNTAX     Integer32 (0..2147483647)
    MAX-ACCESS read-only
    STATUS     current
    DESCRIPTION
            ""
    ::= { hmStatusWtpMngmtWIdsEntry 35 }

-- {COLUMN} 1.3.6.1.4.1.248.32.18.1.59.248.1.37
hmStatusWtpMngmtWIdsEntryPSPollTIMInterval OBJECT-TYPE
    SYNTAX     Integer32 (0..2147483647)
    MAX-ACCESS read-only
    STATUS     current
    DESCRIPTION
            ""
    ::= { hmStatusWtpMngmtWIdsEntry 37 }

-- {COLUMN} 1.3.6.1.4.1.248.32.18.1.59.248.1.38
hmStatusWtpMngmtWIdsEntryPSPollTIMIntervalCtrLim OBJECT-TYPE
    SYNTAX     Integer32 (0..2147483647)
    MAX-ACCESS read-only
    STATUS     current
    DESCRIPTION
            ""
    ::= { hmStatusWtpMngmtWIdsEntry 38 }

-- {COLUMN} 1.3.6.1.4.1.248.32.18.1.59.248.1.39
hmStatusWtpMngmtWIdsEntryPSPollTIMIntervalCtrInt OBJECT-TYPE
    SYNTAX     Integer32 (0..2147483647)
    MAX-ACCESS read-only
    STATUS     current
    DESCRIPTION
            ""
    ::= { hmStatusWtpMngmtWIdsEntry 39 }

-- {COLUMN} 1.3.6.1.4.1.248.32.18.1.59.248.1.41
hmStatusWtpMngmtWIdsEntrySMPSMulStreamCtrLim OBJECT-TYPE
    SYNTAX     Integer32 (0..2147483647)
    MAX-ACCESS read-only
    STATUS     current
    DESCRIPTION
            ""
    ::= { hmStatusWtpMngmtWIdsEntry 41 }

-- {COLUMN} 1.3.6.1.4.1.248.32.18.1.59.248.1.42
hmStatusWtpMngmtWIdsEntrySMPSMulStreamCtrInt OBJECT-TYPE
    SYNTAX     Integer32 (0..2147483647)
    MAX-ACCESS read-only
    STATUS     current
    DESCRIPTION
            ""
    ::= { hmStatusWtpMngmtWIdsEntry 42 }

-- {COLUMN} 1.3.6.1.4.1.248.32.18.1.59.248.1.43
hmStatusWtpMngmtWIdsEntrySMPSSingleStreamCtrLim OBJECT-TYPE
    SYNTAX     Integer32 (0..2147483647)
    MAX-ACCESS read-only
    STATUS     current
    DESCRIPTION
            ""
    ::= { hmStatusWtpMngmtWIdsEntry 43 }

-- {COLUMN} 1.3.6.1.4.1.248.32.18.1.59.248.1.44
hmStatusWtpMngmtWIdsEntrySMPSSingleStreamCtrInt OBJECT-TYPE
    SYNTAX     Integer32 (0..2147483647)
    MAX-ACCESS read-only
    STATUS     current
    DESCRIPTION
            ""
    ::= { hmStatusWtpMngmtWIdsEntry 44 }

-- {COLUMN} 1.3.6.1.4.1.248.32.18.1.59.248.1.45
hmStatusWtpMngmtWIdsEntryDisAssocBroadCtrLim OBJECT-TYPE
    SYNTAX     Integer32 (0..2147483647)
    MAX-ACCESS read-only
    STATUS     current
    DESCRIPTION
            ""
    ::= { hmStatusWtpMngmtWIdsEntry 45 }

-- {COLUMN} 1.3.6.1.4.1.248.32.18.1.59.248.1.46
hmStatusWtpMngmtWIdsEntryDisAssocBroadCtrInt OBJECT-TYPE
    SYNTAX     Integer32 (0..2147483647)
    MAX-ACCESS read-only
    STATUS     current
    DESCRIPTION
            ""
    ::= { hmStatusWtpMngmtWIdsEntry 46 }

-- {COLUMN} 1.3.6.1.4.1.248.32.18.1.59.248.1.52
hmStatusWtpMngmtWIdsEntryIntruderIdentification OBJECT-TYPE
    SYNTAX     INTEGER {
                  eNo (0),
                  eYes (1)
            }
    MAX-ACCESS read-only
    STATUS     current
    DESCRIPTION
            "-- empty --"
    ::= { hmStatusWtpMngmtWIdsEntry 52 }

-- {COLUMN} 1.3.6.1.4.1.248.32.18.1.59.248.1.53
hmStatusWtpMngmtWIdsEntryTimeoutIntruderActivity OBJECT-TYPE
    SYNTAX     Integer32 (0..2147483647)
    MAX-ACCESS read-only
    STATUS     current
    DESCRIPTION
            "-- empty --"
    ::= { hmStatusWtpMngmtWIdsEntry 53 }

-- {COLUMN} 1.3.6.1.4.1.248.32.18.1.59.248.1.54
hmStatusWtpMngmtWIdsEntryWhiteListId OBJECT-TYPE
    SYNTAX     Integer32 (0..255)
    MAX-ACCESS read-only
    STATUS     current
    DESCRIPTION
            "-- empty --"
    ::= { hmStatusWtpMngmtWIdsEntry 54 }

-- {COLUMN} 1.3.6.1.4.1.248.32.18.1.59.248.1.55
hmStatusWtpMngmtWIdsEntryStoreIntruderDhcpRequests OBJECT-TYPE
    SYNTAX     INTEGER {
                  eNo (0),
                  eYes (1)
            }
    MAX-ACCESS read-only
    STATUS     current
    DESCRIPTION
            "-- empty --"
    ::= { hmStatusWtpMngmtWIdsEntry 55 }

-- {NODE} 1.3.6.1.4.1.248.32.18.1.60
hmStatusLldp OBJECT IDENTIFIER ::= { hmStatus 60 }

-- {SCALAR} 1.3.6.1.4.1.248.32.18.1.60.1
hmStatusLldpRemoteTablesLastChange OBJECT-TYPE
    SYNTAX     DisplayString (SIZE(0..21))
    MAX-ACCESS read-only
    STATUS     current
    DESCRIPTION
            "-- empty --"
    ::= { hmStatusLldp 1 }

-- {SCALAR} 1.3.6.1.4.1.248.32.18.1.60.2
hmStatusLldpRemoteTablesInserts OBJECT-TYPE
    SYNTAX     Counter32
    MAX-ACCESS read-only
    STATUS     current
    DESCRIPTION
            "-- empty --"
    ::= { hmStatusLldp 2 }

-- {SCALAR} 1.3.6.1.4.1.248.32.18.1.60.3
hmStatusLldpRemoteTablesDeletes OBJECT-TYPE
    SYNTAX     Counter32
    MAX-ACCESS read-only
    STATUS     current
    DESCRIPTION
            "-- empty --"
    ::= { hmStatusLldp 3 }

-- {SCALAR} 1.3.6.1.4.1.248.32.18.1.60.4
hmStatusLldpRemoteTablesDrops OBJECT-TYPE
    SYNTAX     Counter32
    MAX-ACCESS read-only
    STATUS     current
    DESCRIPTION
            "-- empty --"
    ::= { hmStatusLldp 4 }

-- {SCALAR} 1.3.6.1.4.1.248.32.18.1.60.5
hmStatusLldpRemoteTablesAgeouts OBJECT-TYPE
    SYNTAX     Counter32
    MAX-ACCESS read-only
    STATUS     current
    DESCRIPTION
            "-- empty --"
    ::= { hmStatusLldp 5 }

-- {TABLE} 1.3.6.1.4.1.248.32.18.1.60.7
hmStatusLldpPortsTable OBJECT-TYPE
    SYNTAX     SEQUENCE OF HmStatusLldpPortsEntry
    MAX-ACCESS not-accessible
    STATUS     current
    DESCRIPTION
            "-- empty --"
    ::= { hmStatusLldp 7 }

-- {ROW} 1.3.6.1.4.1.248.32.18.1.60.7.1
hmStatusLldpPortsEntry OBJECT-TYPE
    SYNTAX     HmStatusLldpPortsEntry
    MAX-ACCESS not-accessible
    STATUS     current
    DESCRIPTION
            ""
    INDEX {
            hmStatusLldpPortsEntryName
          }
    ::= { hmStatusLldpPortsTable 1 }

HmStatusLldpPortsEntry ::= SEQUENCE {
            hmStatusLldpPortsEntryName DisplayString,
            hmStatusLldpPortsEntryTxFrames Counter32,
            hmStatusLldpPortsEntryRxFrames Counter32,
            hmStatusLldpPortsEntryFramesDiscarded Counter32,
            hmStatusLldpPortsEntryFramesErrors Counter32,
            hmStatusLldpPortsEntryTlvsDiscarded Counter32,
            hmStatusLldpPortsEntryTlvsUnrecognized Counter32,
            hmStatusLldpPortsEntryAgeouts Counter32,
            hmStatusLldpPortsEntryTotalEntries Gauge32,
            hmStatusLldpPortsEntryFdbTotalEntries Gauge32,
            hmStatusLldpPortsEntryLldpEntries Gauge32,
            hmStatusLldpPortsEntryOtherEntries Gauge32
    }

-- {COLUMN} 1.3.6.1.4.1.248.32.18.1.60.7.1.1
hmStatusLldpPortsEntryName OBJECT-TYPE
    SYNTAX     DisplayString (SIZE(0..255))
    MAX-ACCESS read-only
    STATUS     current
    DESCRIPTION
            "-- empty --"
    ::= { hmStatusLldpPortsEntry 1 }

-- {COLUMN} 1.3.6.1.4.1.248.32.18.1.60.7.1.2
hmStatusLldpPortsEntryTxFrames OBJECT-TYPE
    SYNTAX     Counter32
    MAX-ACCESS read-only
    STATUS     current
    DESCRIPTION
            "-- empty --"
    ::= { hmStatusLldpPortsEntry 2 }

-- {COLUMN} 1.3.6.1.4.1.248.32.18.1.60.7.1.3
hmStatusLldpPortsEntryRxFrames OBJECT-TYPE
    SYNTAX     Counter32
    MAX-ACCESS read-only
    STATUS     current
    DESCRIPTION
            "-- empty --"
    ::= { hmStatusLldpPortsEntry 3 }

-- {COLUMN} 1.3.6.1.4.1.248.32.18.1.60.7.1.4
hmStatusLldpPortsEntryFramesDiscarded OBJECT-TYPE
    SYNTAX     Counter32
    MAX-ACCESS read-only
    STATUS     current
    DESCRIPTION
            "-- empty --"
    ::= { hmStatusLldpPortsEntry 4 }

-- {COLUMN} 1.3.6.1.4.1.248.32.18.1.60.7.1.5
hmStatusLldpPortsEntryFramesErrors OBJECT-TYPE
    SYNTAX     Counter32
    MAX-ACCESS read-only
    STATUS     current
    DESCRIPTION
            "-- empty --"
    ::= { hmStatusLldpPortsEntry 5 }

-- {COLUMN} 1.3.6.1.4.1.248.32.18.1.60.7.1.6
hmStatusLldpPortsEntryTlvsDiscarded OBJECT-TYPE
    SYNTAX     Counter32
    MAX-ACCESS read-only
    STATUS     current
    DESCRIPTION
            "-- empty --"
    ::= { hmStatusLldpPortsEntry 6 }

-- {COLUMN} 1.3.6.1.4.1.248.32.18.1.60.7.1.7
hmStatusLldpPortsEntryTlvsUnrecognized OBJECT-TYPE
    SYNTAX     Counter32
    MAX-ACCESS read-only
    STATUS     current
    DESCRIPTION
            "-- empty --"
    ::= { hmStatusLldpPortsEntry 7 }

-- {COLUMN} 1.3.6.1.4.1.248.32.18.1.60.7.1.8
hmStatusLldpPortsEntryAgeouts OBJECT-TYPE
    SYNTAX     Counter32
    MAX-ACCESS read-only
    STATUS     current
    DESCRIPTION
            "-- empty --"
    ::= { hmStatusLldpPortsEntry 8 }

-- {COLUMN} 1.3.6.1.4.1.248.32.18.1.60.7.1.9
hmStatusLldpPortsEntryTotalEntries OBJECT-TYPE
    SYNTAX     Gauge32
    MAX-ACCESS read-only
    STATUS     current
    DESCRIPTION
            "-- empty --"
    ::= { hmStatusLldpPortsEntry 9 }

-- {COLUMN} 1.3.6.1.4.1.248.32.18.1.60.7.1.10
hmStatusLldpPortsEntryFdbTotalEntries OBJECT-TYPE
    SYNTAX     Gauge32
    MAX-ACCESS read-only
    STATUS     current
    DESCRIPTION
            "-- empty --"
    ::= { hmStatusLldpPortsEntry 10 }

-- {COLUMN} 1.3.6.1.4.1.248.32.18.1.60.7.1.11
hmStatusLldpPortsEntryLldpEntries OBJECT-TYPE
    SYNTAX     Gauge32
    MAX-ACCESS read-only
    STATUS     current
    DESCRIPTION
            "-- empty --"
    ::= { hmStatusLldpPortsEntry 11 }

-- {COLUMN} 1.3.6.1.4.1.248.32.18.1.60.7.1.12
hmStatusLldpPortsEntryOtherEntries OBJECT-TYPE
    SYNTAX     Gauge32
    MAX-ACCESS read-only
    STATUS     current
    DESCRIPTION
            "-- empty --"
    ::= { hmStatusLldpPortsEntry 12 }

-- {TABLE} 1.3.6.1.4.1.248.32.18.1.60.8
hmStatusLldpRemoteTableTable OBJECT-TYPE
    SYNTAX     SEQUENCE OF HmStatusLldpRemoteTableEntry
    MAX-ACCESS not-accessible
    STATUS     current
    DESCRIPTION
            "-- empty --"
    ::= { hmStatusLldp 8 }

-- {ROW} 1.3.6.1.4.1.248.32.18.1.60.8.1
hmStatusLldpRemoteTableEntry OBJECT-TYPE
    SYNTAX     HmStatusLldpRemoteTableEntry
    MAX-ACCESS not-accessible
    STATUS     current
    DESCRIPTION
            ""
    INDEX {
            hmStatusLldpRemoteTableEntryIndex
          }
    ::= { hmStatusLldpRemoteTableTable 1 }

HmStatusLldpRemoteTableEntry ::= SEQUENCE {
            hmStatusLldpRemoteTableEntryIndex Integer32,
            hmStatusLldpRemoteTableEntryLastUpdate DisplayString,
            hmStatusLldpRemoteTableEntryChassisIdType INTEGER,
            hmStatusLldpRemoteTableEntryChassisId DisplayString,
            hmStatusLldpRemoteTableEntryPortIdType INTEGER,
            hmStatusLldpRemoteTableEntryPortId DisplayString,
            hmStatusLldpRemoteTableEntryTtl Integer32,
            hmStatusLldpRemoteTableEntryTtlRemaining Integer32,
            hmStatusLldpRemoteTableEntryPortDescriptor DisplayString,
            hmStatusLldpRemoteTableEntrySystemName DisplayString,
            hmStatusLldpRemoteTableEntrySystemDescriptor DisplayString,
            hmStatusLldpRemoteTableEntryCapabilitiesSupported BITS,
            hmStatusLldpRemoteTableEntryCapabilitiesEnabled BITS,
            hmStatusLldpRemoteTableEntryPortVlanId Integer32,
            hmStatusLldpRemoteTableEntrySource INTEGER,
            hmStatusLldpRemoteTableEntryPort DisplayString
    }

-- {COLUMN} 1.3.6.1.4.1.248.32.18.1.60.8.1.1
hmStatusLldpRemoteTableEntryIndex OBJECT-TYPE
    SYNTAX     Integer32 (0..2147483647)
    MAX-ACCESS read-only
    STATUS     current
    DESCRIPTION
            "-- empty --"
    ::= { hmStatusLldpRemoteTableEntry 1 }

-- {COLUMN} 1.3.6.1.4.1.248.32.18.1.60.8.1.2
hmStatusLldpRemoteTableEntryLastUpdate OBJECT-TYPE
    SYNTAX     DisplayString (SIZE(0..19))
    MAX-ACCESS read-only
    STATUS     current
    DESCRIPTION
            "-- empty --"
    ::= { hmStatusLldpRemoteTableEntry 2 }

-- {COLUMN} 1.3.6.1.4.1.248.32.18.1.60.8.1.4
hmStatusLldpRemoteTableEntryChassisIdType OBJECT-TYPE
    SYNTAX     INTEGER {
                  eChassisComponent (1),
                  eInterfaceAlias (2),
                  ePortComponent (3),
                  eMacAddress (4),
                  eNetworkAddress (5),
                  eInterfaceName (6),
                  eLocallyAssigned (7)
            }
    MAX-ACCESS read-only
    STATUS     current
    DESCRIPTION
            "-- empty --"
    ::= { hmStatusLldpRemoteTableEntry 4 }

-- {COLUMN} 1.3.6.1.4.1.248.32.18.1.60.8.1.5
hmStatusLldpRemoteTableEntryChassisId OBJECT-TYPE
    SYNTAX     DisplayString (SIZE(0..255))
    MAX-ACCESS read-only
    STATUS     current
    DESCRIPTION
            "-- empty --"
    ::= { hmStatusLldpRemoteTableEntry 5 }

-- {COLUMN} 1.3.6.1.4.1.248.32.18.1.60.8.1.6
hmStatusLldpRemoteTableEntryPortIdType OBJECT-TYPE
    SYNTAX     INTEGER {
                  eInterfaceAlias (1),
                  ePortComponent (2),
                  eMacAddress (3),
                  eNetworkAddress (4),
                  eInterfaceName (5),
                  eCircuitId (6),
                  eLocallyAssigned (7)
            }
    MAX-ACCESS read-only
    STATUS     current
    DESCRIPTION
            "-- empty --"
    ::= { hmStatusLldpRemoteTableEntry 6 }

-- {COLUMN} 1.3.6.1.4.1.248.32.18.1.60.8.1.7
hmStatusLldpRemoteTableEntryPortId OBJECT-TYPE
    SYNTAX     DisplayString (SIZE(0..255))
    MAX-ACCESS read-only
    STATUS     current
    DESCRIPTION
            "-- empty --"
    ::= { hmStatusLldpRemoteTableEntry 7 }

-- {COLUMN} 1.3.6.1.4.1.248.32.18.1.60.8.1.8
hmStatusLldpRemoteTableEntryTtl OBJECT-TYPE
    SYNTAX     Integer32 (0..65535)
    MAX-ACCESS read-only
    STATUS     current
    DESCRIPTION
            "-- empty --"
    ::= { hmStatusLldpRemoteTableEntry 8 }

-- {COLUMN} 1.3.6.1.4.1.248.32.18.1.60.8.1.9
hmStatusLldpRemoteTableEntryTtlRemaining OBJECT-TYPE
    SYNTAX     Integer32 (0..65535)
    MAX-ACCESS read-only
    STATUS     current
    DESCRIPTION
            "-- empty --"
    ::= { hmStatusLldpRemoteTableEntry 9 }

-- {COLUMN} 1.3.6.1.4.1.248.32.18.1.60.8.1.10
hmStatusLldpRemoteTableEntryPortDescriptor OBJECT-TYPE
    SYNTAX     DisplayString (SIZE(0..255))
    MAX-ACCESS read-only
    STATUS     current
    DESCRIPTION
            "-- empty --"
    ::= { hmStatusLldpRemoteTableEntry 10 }

-- {COLUMN} 1.3.6.1.4.1.248.32.18.1.60.8.1.11
hmStatusLldpRemoteTableEntrySystemName OBJECT-TYPE
    SYNTAX     DisplayString (SIZE(0..255))
    MAX-ACCESS read-only
    STATUS     current
    DESCRIPTION
            "-- empty --"
    ::= { hmStatusLldpRemoteTableEntry 11 }

-- {COLUMN} 1.3.6.1.4.1.248.32.18.1.60.8.1.12
hmStatusLldpRemoteTableEntrySystemDescriptor OBJECT-TYPE
    SYNTAX     DisplayString (SIZE(0..255))
    MAX-ACCESS read-only
    STATUS     current
    DESCRIPTION
            "-- empty --"
    ::= { hmStatusLldpRemoteTableEntry 12 }

-- {COLUMN} 1.3.6.1.4.1.248.32.18.1.60.8.1.13
hmStatusLldpRemoteTableEntryCapabilitiesSupported OBJECT-TYPE
    SYNTAX     BITS {
                  eStationOnly (0),
                  eDocsisCable (1),
                  eTelephone (2),
                  eRouter (3),
                  eWlanAp (4),
                  eBridge (5),
                  eRepeater (6),
                  eOther (7)
            }
    MAX-ACCESS read-only
    STATUS     current
    DESCRIPTION
            "-- empty --"
    ::= { hmStatusLldpRemoteTableEntry 13 }

-- {COLUMN} 1.3.6.1.4.1.248.32.18.1.60.8.1.14
hmStatusLldpRemoteTableEntryCapabilitiesEnabled OBJECT-TYPE
    SYNTAX     BITS {
                  eStationOnly (0),
                  eDocsisCable (1),
                  eTelephone (2),
                  eRouter (3),
                  eWlanAp (4),
                  eBridge (5),
                  eRepeater (6),
                  eOther (7)
            }
    MAX-ACCESS read-only
    STATUS     current
    DESCRIPTION
            "-- empty --"
    ::= { hmStatusLldpRemoteTableEntry 14 }

-- {COLUMN} 1.3.6.1.4.1.248.32.18.1.60.8.1.15
hmStatusLldpRemoteTableEntryPortVlanId OBJECT-TYPE
    SYNTAX     Integer32 (0..65535)
    MAX-ACCESS read-only
    STATUS     current
    DESCRIPTION
            "-- empty --"
    ::= { hmStatusLldpRemoteTableEntry 15 }

-- {COLUMN} 1.3.6.1.4.1.248.32.18.1.60.8.1.16
hmStatusLldpRemoteTableEntrySource OBJECT-TYPE
    SYNTAX     INTEGER {
                  eLldp (1),
                  eCdp (2),
                  eWlan (3),
                  eFdb (4)
            }
    MAX-ACCESS read-only
    STATUS     current
    DESCRIPTION
            "-- empty --"
    ::= { hmStatusLldpRemoteTableEntry 16 }

-- {COLUMN} 1.3.6.1.4.1.248.32.18.1.60.8.1.17
hmStatusLldpRemoteTableEntryPort OBJECT-TYPE
    SYNTAX     DisplayString (SIZE(0..255))
    MAX-ACCESS read-only
    STATUS     current
    DESCRIPTION
            "-- empty --"
    ::= { hmStatusLldpRemoteTableEntry 17 }

-- {TABLE} 1.3.6.1.4.1.248.32.18.1.60.9
hmStatusLldpRemoteManagementAddressesTable OBJECT-TYPE
    SYNTAX     SEQUENCE OF HmStatusLldpRemoteManagementAddressesEntry
    MAX-ACCESS not-accessible
    STATUS     current
    DESCRIPTION
            "-- empty --"
    ::= { hmStatusLldp 9 }

-- {ROW} 1.3.6.1.4.1.248.32.18.1.60.9.1
hmStatusLldpRemoteManagementAddressesEntry OBJECT-TYPE
    SYNTAX     HmStatusLldpRemoteManagementAddressesEntry
    MAX-ACCESS not-accessible
    STATUS     current
    DESCRIPTION
            ""
    INDEX {
            hmStatusLldpRemoteManagementAddressesEntryIndex,
            hmStatusLldpRemoteManagementAddressesEntryAddressType,
            hmStatusLldpRemoteManagementAddressesEntryAddress
          }
    ::= { hmStatusLldpRemoteManagementAddressesTable 1 }

HmStatusLldpRemoteManagementAddressesEntry ::= SEQUENCE {
            hmStatusLldpRemoteManagementAddressesEntryIndex Integer32,
            hmStatusLldpRemoteManagementAddressesEntryAddressType INTEGER,
            hmStatusLldpRemoteManagementAddressesEntryAddress DisplayString,
            hmStatusLldpRemoteManagementAddressesEntryIfcSubtype INTEGER,
            hmStatusLldpRemoteManagementAddressesEntryIfcId Integer32
    }

-- {COLUMN} 1.3.6.1.4.1.248.32.18.1.60.9.1.1
hmStatusLldpRemoteManagementAddressesEntryIndex OBJECT-TYPE
    SYNTAX     Integer32 (0..2147483647)
    MAX-ACCESS read-only
    STATUS     current
    DESCRIPTION
            "-- empty --"
    ::= { hmStatusLldpRemoteManagementAddressesEntry 1 }

-- {COLUMN} 1.3.6.1.4.1.248.32.18.1.60.9.1.2
hmStatusLldpRemoteManagementAddressesEntryAddressType OBJECT-TYPE
    SYNTAX     INTEGER {
                  eIpv4 (1),
                  eIpv6 (2),
                  e802 (6),
                  eIpx (11)
            }
    MAX-ACCESS read-only
    STATUS     current
    DESCRIPTION
            "-- empty --"
    ::= { hmStatusLldpRemoteManagementAddressesEntry 2 }

-- {COLUMN} 1.3.6.1.4.1.248.32.18.1.60.9.1.3
hmStatusLldpRemoteManagementAddressesEntryAddress OBJECT-TYPE
    SYNTAX     DisplayString (SIZE(0..255))
    MAX-ACCESS read-only
    STATUS     current
    DESCRIPTION
            "-- empty --"
    ::= { hmStatusLldpRemoteManagementAddressesEntry 3 }

-- {COLUMN} 1.3.6.1.4.1.248.32.18.1.60.9.1.4
hmStatusLldpRemoteManagementAddressesEntryIfcSubtype OBJECT-TYPE
    SYNTAX     INTEGER {
                  eUnknown (1),
                  eIfindex (2),
                  eSystemPortNum (3)
            }
    MAX-ACCESS read-only
    STATUS     current
    DESCRIPTION
            "-- empty --"
    ::= { hmStatusLldpRemoteManagementAddressesEntry 4 }

-- {COLUMN} 1.3.6.1.4.1.248.32.18.1.60.9.1.5
hmStatusLldpRemoteManagementAddressesEntryIfcId OBJECT-TYPE
    SYNTAX     Integer32 (0..2147483647)
    MAX-ACCESS read-only
    STATUS     current
    DESCRIPTION
            "-- empty --"
    ::= { hmStatusLldpRemoteManagementAddressesEntry 5 }

-- {TABLE} 1.3.6.1.4.1.248.32.18.1.60.10
hmStatusLldpRemote8023TableTable OBJECT-TYPE
    SYNTAX     SEQUENCE OF HmStatusLldpRemote8023TableEntry
    MAX-ACCESS not-accessible
    STATUS     current
    DESCRIPTION
            "-- empty --"
    ::= { hmStatusLldp 10 }

-- {ROW} 1.3.6.1.4.1.248.32.18.1.60.10.1
hmStatusLldpRemote8023TableEntry OBJECT-TYPE
    SYNTAX     HmStatusLldpRemote8023TableEntry
    MAX-ACCESS not-accessible
    STATUS     current
    DESCRIPTION
            ""
    INDEX {
            hmStatusLldpRemote8023TableEntryIndex
          }
    ::= { hmStatusLldpRemote8023TableTable 1 }

HmStatusLldpRemote8023TableEntry ::= SEQUENCE {
            hmStatusLldpRemote8023TableEntryIndex Integer32,
            hmStatusLldpRemote8023TableEntryAutoNegotiationSupported INTEGER,
            hmStatusLldpRemote8023TableEntryAutoNegotiationEnabled INTEGER,
            hmStatusLldpRemote8023TableEntryAutoNegotiationCapabilities BITS,
            hmStatusLldpRemote8023TableEntryMauOperationalType INTEGER,
            hmStatusLldpRemote8023TableEntryPortPowerType INTEGER,
            hmStatusLldpRemote8023TableEntryPsePowerSupport INTEGER,
            hmStatusLldpRemote8023TableEntryPsePowerEnabled INTEGER,
            hmStatusLldpRemote8023TableEntryPsePowerPairControl INTEGER,
            hmStatusLldpRemote8023TableEntryPsePowerPair INTEGER,
            hmStatusLldpRemote8023TableEntryPowerClass INTEGER,
            hmStatusLldpRemote8023TableEntryAggregationCapable INTEGER,
            hmStatusLldpRemote8023TableEntryAggregationEnabled INTEGER,
            hmStatusLldpRemote8023TableEntryAggregationPortId Integer32,
            hmStatusLldpRemote8023TableEntryMaxFrameSize Integer32
    }

-- {COLUMN} 1.3.6.1.4.1.248.32.18.1.60.10.1.1
hmStatusLldpRemote8023TableEntryIndex OBJECT-TYPE
    SYNTAX     Integer32 (0..2147483647)
    MAX-ACCESS read-only
    STATUS     current
    DESCRIPTION
            "-- empty --"
    ::= { hmStatusLldpRemote8023TableEntry 1 }

-- {COLUMN} 1.3.6.1.4.1.248.32.18.1.60.10.1.2
hmStatusLldpRemote8023TableEntryAutoNegotiationSupported OBJECT-TYPE
    SYNTAX     INTEGER {
                  eNo (0),
                  eYes (1)
            }
    MAX-ACCESS read-only
    STATUS     current
    DESCRIPTION
            "-- empty --"
    ::= { hmStatusLldpRemote8023TableEntry 2 }

-- {COLUMN} 1.3.6.1.4.1.248.32.18.1.60.10.1.3
hmStatusLldpRemote8023TableEntryAutoNegotiationEnabled OBJECT-TYPE
    SYNTAX     INTEGER {
                  eNo (0),
                  eYes (1)
            }
    MAX-ACCESS read-only
    STATUS     current
    DESCRIPTION
            "-- empty --"
    ::= { hmStatusLldpRemote8023TableEntry 3 }

-- {COLUMN} 1.3.6.1.4.1.248.32.18.1.60.10.1.4
hmStatusLldpRemote8023TableEntryAutoNegotiationCapabilities OBJECT-TYPE
    SYNTAX     BITS {
                  eOther (0),
                  e10baset (1),
                  e10basetFd (2),
                  e100baset4 (3),
                  e100basetx (4),
                  e100basetxFd (5),
                  e100baset2 (6),
                  e100baset2Fd (7),
                  ePause (8),
                  eAsymmetricPause (9),
                  eSymmetricPause (10),
                  eAsymmetricSymmetricPause (11),
                  e1000basex (12),
                  e1000basexFd (13),
                  e1000baset (14),
                  e1000basetFd (15)
            }
    MAX-ACCESS read-only
    STATUS     current
    DESCRIPTION
            "-- empty --"
    ::= { hmStatusLldpRemote8023TableEntry 4 }

-- {COLUMN} 1.3.6.1.4.1.248.32.18.1.60.10.1.5
hmStatusLldpRemote8023TableEntryMauOperationalType OBJECT-TYPE
    SYNTAX     INTEGER {
                  eUnknown (0),
                  e10baseaui (1),
                  e10base2 (4),
                  e10basetHd (10),
                  e10basetFd (11),
                  e100basetxHd (15),
                  e100basetxFd (16),
                  e1000basexHd (21),
                  e1000basexFd (22),
                  e1000baselxHd (23),
                  e1000baselxFd (24),
                  e1000basesxHd (25),
                  e1000basesxFd (26),
                  e1000basetxFd (30),
                  e1000basebx10d (44),
                  e1000basebx10u (45)
            }
    MAX-ACCESS read-only
    STATUS     current
    DESCRIPTION
            "-- empty --"
    ::= { hmStatusLldpRemote8023TableEntry 5 }

-- {COLUMN} 1.3.6.1.4.1.248.32.18.1.60.10.1.6
hmStatusLldpRemote8023TableEntryPortPowerType OBJECT-TYPE
    SYNTAX     INTEGER {
                  eNone (0),
                  ePse (1),
                  ePd (2)
            }
    MAX-ACCESS read-only
    STATUS     current
    DESCRIPTION
            "-- empty --"
    ::= { hmStatusLldpRemote8023TableEntry 6 }

-- {COLUMN} 1.3.6.1.4.1.248.32.18.1.60.10.1.7
hmStatusLldpRemote8023TableEntryPsePowerSupport OBJECT-TYPE
    SYNTAX     INTEGER {
                  eNo (0),
                  eYes (1)
            }
    MAX-ACCESS read-only
    STATUS     current
    DESCRIPTION
            "-- empty --"
    ::= { hmStatusLldpRemote8023TableEntry 7 }

-- {COLUMN} 1.3.6.1.4.1.248.32.18.1.60.10.1.8
hmStatusLldpRemote8023TableEntryPsePowerEnabled OBJECT-TYPE
    SYNTAX     INTEGER {
                  eNo (0),
                  eYes (1)
            }
    MAX-ACCESS read-only
    STATUS     current
    DESCRIPTION
            "-- empty --"
    ::= { hmStatusLldpRemote8023TableEntry 8 }

-- {COLUMN} 1.3.6.1.4.1.248.32.18.1.60.10.1.9
hmStatusLldpRemote8023TableEntryPsePowerPairControl OBJECT-TYPE
    SYNTAX     INTEGER {
                  eNo (0),
                  eYes (1)
            }
    MAX-ACCESS read-only
    STATUS     current
    DESCRIPTION
            "-- empty --"
    ::= { hmStatusLldpRemote8023TableEntry 9 }

-- {COLUMN} 1.3.6.1.4.1.248.32.18.1.60.10.1.10
hmStatusLldpRemote8023TableEntryPsePowerPair OBJECT-TYPE
    SYNTAX     INTEGER {
                  eNone (0),
                  eSignal (1),
                  eSpare (2)
            }
    MAX-ACCESS read-only
    STATUS     current
    DESCRIPTION
            "-- empty --"
    ::= { hmStatusLldpRemote8023TableEntry 10 }

-- {COLUMN} 1.3.6.1.4.1.248.32.18.1.60.10.1.11
hmStatusLldpRemote8023TableEntryPowerClass OBJECT-TYPE
    SYNTAX     INTEGER {
                  eNone (0),
                  eClass0 (1),
                  eClass1 (2),
                  eClass2 (3),
                  eClass3 (4),
                  eClass4 (5)
            }
    MAX-ACCESS read-only
    STATUS     current
    DESCRIPTION
            "-- empty --"
    ::= { hmStatusLldpRemote8023TableEntry 11 }

-- {COLUMN} 1.3.6.1.4.1.248.32.18.1.60.10.1.12
hmStatusLldpRemote8023TableEntryAggregationCapable OBJECT-TYPE
    SYNTAX     INTEGER {
                  eNo (0),
                  eYes (1)
            }
    MAX-ACCESS read-only
    STATUS     current
    DESCRIPTION
            "-- empty --"
    ::= { hmStatusLldpRemote8023TableEntry 12 }

-- {COLUMN} 1.3.6.1.4.1.248.32.18.1.60.10.1.13
hmStatusLldpRemote8023TableEntryAggregationEnabled OBJECT-TYPE
    SYNTAX     INTEGER {
                  eNo (0),
                  eYes (1)
            }
    MAX-ACCESS read-only
    STATUS     current
    DESCRIPTION
            "-- empty --"
    ::= { hmStatusLldpRemote8023TableEntry 13 }

-- {COLUMN} 1.3.6.1.4.1.248.32.18.1.60.10.1.14
hmStatusLldpRemote8023TableEntryAggregationPortId OBJECT-TYPE
    SYNTAX     Integer32 (0..2147483647)
    MAX-ACCESS read-only
    STATUS     current
    DESCRIPTION
            "-- empty --"
    ::= { hmStatusLldpRemote8023TableEntry 14 }

-- {COLUMN} 1.3.6.1.4.1.248.32.18.1.60.10.1.15
hmStatusLldpRemote8023TableEntryMaxFrameSize OBJECT-TYPE
    SYNTAX     Integer32 (0..65535)
    MAX-ACCESS read-only
    STATUS     current
    DESCRIPTION
            "-- empty --"
    ::= { hmStatusLldpRemote8023TableEntry 15 }

-- {TABLE} 1.3.6.1.4.1.248.32.18.1.60.11
hmStatusLldpRemote8021ProtoVlansTable OBJECT-TYPE
    SYNTAX     SEQUENCE OF HmStatusLldpRemote8021ProtoVlansEntry
    MAX-ACCESS not-accessible
    STATUS     current
    DESCRIPTION
            "-- empty --"
    ::= { hmStatusLldp 11 }

-- {ROW} 1.3.6.1.4.1.248.32.18.1.60.11.1
hmStatusLldpRemote8021ProtoVlansEntry OBJECT-TYPE
    SYNTAX     HmStatusLldpRemote8021ProtoVlansEntry
    MAX-ACCESS not-accessible
    STATUS     current
    DESCRIPTION
            ""
    INDEX {
            hmStatusLldpRemote8021ProtoVlansEntryIndex,
            hmStatusLldpRemote8021ProtoVlansEntryVlanId
          }
    ::= { hmStatusLldpRemote8021ProtoVlansTable 1 }

HmStatusLldpRemote8021ProtoVlansEntry ::= SEQUENCE {
            hmStatusLldpRemote8021ProtoVlansEntryIndex Integer32,
            hmStatusLldpRemote8021ProtoVlansEntryVlanId Integer32,
            hmStatusLldpRemote8021ProtoVlansEntrySupported INTEGER,
            hmStatusLldpRemote8021ProtoVlansEntryEnabled INTEGER
    }

-- {COLUMN} 1.3.6.1.4.1.248.32.18.1.60.11.1.1
hmStatusLldpRemote8021ProtoVlansEntryIndex OBJECT-TYPE
    SYNTAX     Integer32 (0..2147483647)
    MAX-ACCESS read-only
    STATUS     current
    DESCRIPTION
            "-- empty --"
    ::= { hmStatusLldpRemote8021ProtoVlansEntry 1 }

-- {COLUMN} 1.3.6.1.4.1.248.32.18.1.60.11.1.2
hmStatusLldpRemote8021ProtoVlansEntryVlanId OBJECT-TYPE
    SYNTAX     Integer32 (0..65535)
    MAX-ACCESS read-only
    STATUS     current
    DESCRIPTION
            "-- empty --"
    ::= { hmStatusLldpRemote8021ProtoVlansEntry 2 }

-- {COLUMN} 1.3.6.1.4.1.248.32.18.1.60.11.1.3
hmStatusLldpRemote8021ProtoVlansEntrySupported OBJECT-TYPE
    SYNTAX     INTEGER {
                  eNo (0),
                  eYes (1)
            }
    MAX-ACCESS read-only
    STATUS     current
    DESCRIPTION
            "-- empty --"
    ::= { hmStatusLldpRemote8021ProtoVlansEntry 3 }

-- {COLUMN} 1.3.6.1.4.1.248.32.18.1.60.11.1.4
hmStatusLldpRemote8021ProtoVlansEntryEnabled OBJECT-TYPE
    SYNTAX     INTEGER {
                  eNo (0),
                  eYes (1)
            }
    MAX-ACCESS read-only
    STATUS     current
    DESCRIPTION
            "-- empty --"
    ::= { hmStatusLldpRemote8021ProtoVlansEntry 4 }

-- {TABLE} 1.3.6.1.4.1.248.32.18.1.60.12
hmStatusLldpRemote8021VlanNamesTable OBJECT-TYPE
    SYNTAX     SEQUENCE OF HmStatusLldpRemote8021VlanNamesEntry
    MAX-ACCESS not-accessible
    STATUS     current
    DESCRIPTION
            "-- empty --"
    ::= { hmStatusLldp 12 }

-- {ROW} 1.3.6.1.4.1.248.32.18.1.60.12.1
hmStatusLldpRemote8021VlanNamesEntry OBJECT-TYPE
    SYNTAX     HmStatusLldpRemote8021VlanNamesEntry
    MAX-ACCESS not-accessible
    STATUS     current
    DESCRIPTION
            ""
    INDEX {
            hmStatusLldpRemote8021VlanNamesEntryIndex,
            hmStatusLldpRemote8021VlanNamesEntryVlanId
          }
    ::= { hmStatusLldpRemote8021VlanNamesTable 1 }

HmStatusLldpRemote8021VlanNamesEntry ::= SEQUENCE {
            hmStatusLldpRemote8021VlanNamesEntryIndex Integer32,
            hmStatusLldpRemote8021VlanNamesEntryVlanId Integer32,
            hmStatusLldpRemote8021VlanNamesEntryName DisplayString
    }

-- {COLUMN} 1.3.6.1.4.1.248.32.18.1.60.12.1.1
hmStatusLldpRemote8021VlanNamesEntryIndex OBJECT-TYPE
    SYNTAX     Integer32 (0..2147483647)
    MAX-ACCESS read-only
    STATUS     current
    DESCRIPTION
            "-- empty --"
    ::= { hmStatusLldpRemote8021VlanNamesEntry 1 }

-- {COLUMN} 1.3.6.1.4.1.248.32.18.1.60.12.1.2
hmStatusLldpRemote8021VlanNamesEntryVlanId OBJECT-TYPE
    SYNTAX     Integer32 (0..65535)
    MAX-ACCESS read-only
    STATUS     current
    DESCRIPTION
            "-- empty --"
    ::= { hmStatusLldpRemote8021VlanNamesEntry 2 }

-- {COLUMN} 1.3.6.1.4.1.248.32.18.1.60.12.1.3
hmStatusLldpRemote8021VlanNamesEntryName OBJECT-TYPE
    SYNTAX     DisplayString (SIZE(0..32))
    MAX-ACCESS read-only
    STATUS     current
    DESCRIPTION
            "-- empty --"
    ::= { hmStatusLldpRemote8021VlanNamesEntry 3 }

-- {TABLE} 1.3.6.1.4.1.248.32.18.1.60.13
hmStatusLldpRemote8021ProtocolIdsTable OBJECT-TYPE
    SYNTAX     SEQUENCE OF HmStatusLldpRemote8021ProtocolIdsEntry
    MAX-ACCESS not-accessible
    STATUS     current
    DESCRIPTION
            "-- empty --"
    ::= { hmStatusLldp 13 }

-- {ROW} 1.3.6.1.4.1.248.32.18.1.60.13.1
hmStatusLldpRemote8021ProtocolIdsEntry OBJECT-TYPE
    SYNTAX     HmStatusLldpRemote8021ProtocolIdsEntry
    MAX-ACCESS not-accessible
    STATUS     current
    DESCRIPTION
            ""
    INDEX {
            hmStatusLldpRemote8021ProtocolIdsEntryIndex,
            hmStatusLldpRemote8021ProtocolIdsEntryProtocol
          }
    ::= { hmStatusLldpRemote8021ProtocolIdsTable 1 }

HmStatusLldpRemote8021ProtocolIdsEntry ::= SEQUENCE {
            hmStatusLldpRemote8021ProtocolIdsEntryIndex Integer32,
            hmStatusLldpRemote8021ProtocolIdsEntryProtocol DisplayString
    }

-- {COLUMN} 1.3.6.1.4.1.248.32.18.1.60.13.1.1
hmStatusLldpRemote8021ProtocolIdsEntryIndex OBJECT-TYPE
    SYNTAX     Integer32 (0..2147483647)
    MAX-ACCESS read-only
    STATUS     current
    DESCRIPTION
            "-- empty --"
    ::= { hmStatusLldpRemote8021ProtocolIdsEntry 1 }

-- {COLUMN} 1.3.6.1.4.1.248.32.18.1.60.13.1.3
hmStatusLldpRemote8021ProtocolIdsEntryProtocol OBJECT-TYPE
    SYNTAX     DisplayString (SIZE(0..255))
    MAX-ACCESS read-only
    STATUS     current
    DESCRIPTION
            "-- empty --"
    ::= { hmStatusLldpRemote8021ProtocolIdsEntry 3 }

-- {TABLE} 1.3.6.1.4.1.248.32.18.1.60.14
hmStatusLldpRemoteUnknownTlvsTable OBJECT-TYPE
    SYNTAX     SEQUENCE OF HmStatusLldpRemoteUnknownTlvsEntry
    MAX-ACCESS not-accessible
    STATUS     current
    DESCRIPTION
            "-- empty --"
    ::= { hmStatusLldp 14 }

-- {ROW} 1.3.6.1.4.1.248.32.18.1.60.14.1
hmStatusLldpRemoteUnknownTlvsEntry OBJECT-TYPE
    SYNTAX     HmStatusLldpRemoteUnknownTlvsEntry
    MAX-ACCESS not-accessible
    STATUS     current
    DESCRIPTION
            ""
    INDEX {
            hmStatusLldpRemoteUnknownTlvsEntryIndex,
            hmStatusLldpRemoteUnknownTlvsEntryType
          }
    ::= { hmStatusLldpRemoteUnknownTlvsTable 1 }

HmStatusLldpRemoteUnknownTlvsEntry ::= SEQUENCE {
            hmStatusLldpRemoteUnknownTlvsEntryIndex Integer32,
            hmStatusLldpRemoteUnknownTlvsEntryType Integer32,
            hmStatusLldpRemoteUnknownTlvsEntryData DisplayString
    }

-- {COLUMN} 1.3.6.1.4.1.248.32.18.1.60.14.1.1
hmStatusLldpRemoteUnknownTlvsEntryIndex OBJECT-TYPE
    SYNTAX     Integer32 (0..2147483647)
    MAX-ACCESS read-only
    STATUS     current
    DESCRIPTION
            "-- empty --"
    ::= { hmStatusLldpRemoteUnknownTlvsEntry 1 }

-- {COLUMN} 1.3.6.1.4.1.248.32.18.1.60.14.1.2
hmStatusLldpRemoteUnknownTlvsEntryType OBJECT-TYPE
    SYNTAX     Integer32 (0..255)
    MAX-ACCESS read-only
    STATUS     current
    DESCRIPTION
            "-- empty --"
    ::= { hmStatusLldpRemoteUnknownTlvsEntry 2 }

-- {COLUMN} 1.3.6.1.4.1.248.32.18.1.60.14.1.3
hmStatusLldpRemoteUnknownTlvsEntryData OBJECT-TYPE
    SYNTAX     DisplayString (SIZE(0..255))
    MAX-ACCESS read-only
    STATUS     current
    DESCRIPTION
            "-- empty --"
    ::= { hmStatusLldpRemoteUnknownTlvsEntry 3 }

-- {TABLE} 1.3.6.1.4.1.248.32.18.1.60.15
hmStatusLldpRemoteOrgDefaultInfosTable OBJECT-TYPE
    SYNTAX     SEQUENCE OF HmStatusLldpRemoteOrgDefaultInfosEntry
    MAX-ACCESS not-accessible
    STATUS     current
    DESCRIPTION
            "-- empty --"
    ::= { hmStatusLldp 15 }

-- {ROW} 1.3.6.1.4.1.248.32.18.1.60.15.1
hmStatusLldpRemoteOrgDefaultInfosEntry OBJECT-TYPE
    SYNTAX     HmStatusLldpRemoteOrgDefaultInfosEntry
    MAX-ACCESS not-accessible
    STATUS     current
    DESCRIPTION
            ""
    INDEX {
            hmStatusLldpRemoteOrgDefaultInfosEntryIndex,
            hmStatusLldpRemoteOrgDefaultInfosEntryOid,
            hmStatusLldpRemoteOrgDefaultInfosEntrySubtype,
            hmStatusLldpRemoteOrgDefaultInfosEntryTlvIndex
          }
    ::= { hmStatusLldpRemoteOrgDefaultInfosTable 1 }

HmStatusLldpRemoteOrgDefaultInfosEntry ::= SEQUENCE {
            hmStatusLldpRemoteOrgDefaultInfosEntryIndex Integer32,
            hmStatusLldpRemoteOrgDefaultInfosEntryOid Integer32,
            hmStatusLldpRemoteOrgDefaultInfosEntrySubtype Integer32,
            hmStatusLldpRemoteOrgDefaultInfosEntryTlvIndex Integer32,
            hmStatusLldpRemoteOrgDefaultInfosEntryData DisplayString
    }

-- {COLUMN} 1.3.6.1.4.1.248.32.18.1.60.15.1.1
hmStatusLldpRemoteOrgDefaultInfosEntryIndex OBJECT-TYPE
    SYNTAX     Integer32 (0..2147483647)
    MAX-ACCESS read-only
    STATUS     current
    DESCRIPTION
            "-- empty --"
    ::= { hmStatusLldpRemoteOrgDefaultInfosEntry 1 }

-- {COLUMN} 1.3.6.1.4.1.248.32.18.1.60.15.1.2
hmStatusLldpRemoteOrgDefaultInfosEntryOid OBJECT-TYPE
    SYNTAX     Integer32 (0..2147483647)
    MAX-ACCESS read-only
    STATUS     current
    DESCRIPTION
            "-- empty --"
    ::= { hmStatusLldpRemoteOrgDefaultInfosEntry 2 }

-- {COLUMN} 1.3.6.1.4.1.248.32.18.1.60.15.1.3
hmStatusLldpRemoteOrgDefaultInfosEntrySubtype OBJECT-TYPE
    SYNTAX     Integer32 (0..255)
    MAX-ACCESS read-only
    STATUS     current
    DESCRIPTION
            "-- empty --"
    ::= { hmStatusLldpRemoteOrgDefaultInfosEntry 3 }

-- {COLUMN} 1.3.6.1.4.1.248.32.18.1.60.15.1.4
hmStatusLldpRemoteOrgDefaultInfosEntryTlvIndex OBJECT-TYPE
    SYNTAX     Integer32 (0..2147483647)
    MAX-ACCESS read-only
    STATUS     current
    DESCRIPTION
            "-- empty --"
    ::= { hmStatusLldpRemoteOrgDefaultInfosEntry 4 }

-- {COLUMN} 1.3.6.1.4.1.248.32.18.1.60.15.1.5
hmStatusLldpRemoteOrgDefaultInfosEntryData OBJECT-TYPE
    SYNTAX     DisplayString (SIZE(0..255))
    MAX-ACCESS read-only
    STATUS     current
    DESCRIPTION
            "-- empty --"
    ::= { hmStatusLldpRemoteOrgDefaultInfosEntry 5 }

-- {TABLE} 1.3.6.1.4.1.248.32.18.1.60.16
hmStatusLldpRemote80211TableTable OBJECT-TYPE
    SYNTAX     SEQUENCE OF HmStatusLldpRemote80211TableEntry
    MAX-ACCESS not-accessible
    STATUS     current
    DESCRIPTION
            "-- empty --"
    ::= { hmStatusLldp 16 }

-- {ROW} 1.3.6.1.4.1.248.32.18.1.60.16.1
hmStatusLldpRemote80211TableEntry OBJECT-TYPE
    SYNTAX     HmStatusLldpRemote80211TableEntry
    MAX-ACCESS not-accessible
    STATUS     current
    DESCRIPTION
            ""
    INDEX {
            hmStatusLldpRemote80211TableEntryIndex
          }
    ::= { hmStatusLldpRemote80211TableTable 1 }

HmStatusLldpRemote80211TableEntry ::= SEQUENCE {
            hmStatusLldpRemote80211TableEntryIndex Integer32,
            hmStatusLldpRemote80211TableEntrySsid DisplayString,
            hmStatusLldpRemote80211TableEntryRadioChannel Integer32,
            hmStatusLldpRemote80211TableEntryPhyType INTEGER
    }

-- {COLUMN} 1.3.6.1.4.1.248.32.18.1.60.16.1.1
hmStatusLldpRemote80211TableEntryIndex OBJECT-TYPE
    SYNTAX     Integer32 (0..2147483647)
    MAX-ACCESS read-only
    STATUS     current
    DESCRIPTION
            "-- empty --"
    ::= { hmStatusLldpRemote80211TableEntry 1 }

-- {COLUMN} 1.3.6.1.4.1.248.32.18.1.60.16.1.3
hmStatusLldpRemote80211TableEntrySsid OBJECT-TYPE
    SYNTAX     DisplayString (SIZE(0..32))
    MAX-ACCESS read-only
    STATUS     current
    DESCRIPTION
            "-- empty --"
    ::= { hmStatusLldpRemote80211TableEntry 3 }

-- {COLUMN} 1.3.6.1.4.1.248.32.18.1.60.16.1.4
hmStatusLldpRemote80211TableEntryRadioChannel OBJECT-TYPE
    SYNTAX     Integer32 (0..255)
    MAX-ACCESS read-only
    STATUS     current
    DESCRIPTION
            "-- empty --"
    ::= { hmStatusLldpRemote80211TableEntry 4 }

-- {COLUMN} 1.3.6.1.4.1.248.32.18.1.60.16.1.5
hmStatusLldpRemote80211TableEntryPhyType OBJECT-TYPE
    SYNTAX     INTEGER {
                  eFhss (1),
                  eDsss (2),
                  eInfrared (3),
                  eOfdm (4),
                  eHrDsss (5),
                  eErp (6),
                  eHt (7),
                  eVht (9),
                  ePbcc (254)
            }
    MAX-ACCESS read-only
    STATUS     current
    DESCRIPTION
            "-- empty --"
    ::= { hmStatusLldpRemote80211TableEntry 5 }

-- {NODE} 1.3.6.1.4.1.248.32.18.1.61
hmStatusCerts OBJECT IDENTIFIER ::= { hmStatus 61 }

-- {NODE} 1.3.6.1.4.1.248.32.18.1.61.1
hmStatusCertsScepClnt OBJECT IDENTIFIER ::= { hmStatusCerts 1 }

-- {TABLE} 1.3.6.1.4.1.248.32.18.1.61.1.4
hmStatusCertsScepClntCasTable OBJECT-TYPE
    SYNTAX     SEQUENCE OF HmStatusCertsScepClntCasEntry
    MAX-ACCESS not-accessible
    STATUS     current
    DESCRIPTION
            "-- empty --"
    ::= { hmStatusCertsScepClnt 4 }

-- {ROW} 1.3.6.1.4.1.248.32.18.1.61.1.4.1
hmStatusCertsScepClntCasEntry OBJECT-TYPE
    SYNTAX     HmStatusCertsScepClntCasEntry
    MAX-ACCESS not-accessible
    STATUS     current
    DESCRIPTION
            ""
    INDEX {
            hmStatusCertsScepClntCasEntryIdx
          }
    ::= { hmStatusCertsScepClntCasTable 1 }

HmStatusCertsScepClntCasEntry ::= SEQUENCE {
            hmStatusCertsScepClntCasEntryIdx Integer32,
            hmStatusCertsScepClntCasEntryName DisplayString,
            hmStatusCertsScepClntCasEntryExpires DisplayString,
            hmStatusCertsScepClntCasEntryIssued DisplayString,
            hmStatusCertsScepClntCasEntryKeyUsage DisplayString,
            hmStatusCertsScepClntCasEntryIssuer DisplayString,
            hmStatusCertsScepClntCasEntrySubject DisplayString,
            hmStatusCertsScepClntCasEntryStatus DisplayString,
            hmStatusCertsScepClntCasEntryIkeCertificate DisplayString,
            hmStatusCertsScepClntCasEntryMd5Fingerprint DisplayString,
            hmStatusCertsScepClntCasEntrySha1Fingerprint DisplayString,
            hmStatusCertsScepClntCasEntryExpSnmp Counter32,
            hmStatusCertsScepClntCasEntryIssSnmp Counter32
    }

-- {COLUMN} 1.3.6.1.4.1.248.32.18.1.61.1.4.1.1
hmStatusCertsScepClntCasEntryIdx OBJECT-TYPE
    SYNTAX     Integer32 (0..2147483647)
    MAX-ACCESS read-only
    STATUS     current
    DESCRIPTION
            "-- empty --"
    ::= { hmStatusCertsScepClntCasEntry 1 }

-- {COLUMN} 1.3.6.1.4.1.248.32.18.1.61.1.4.1.2
hmStatusCertsScepClntCasEntryName OBJECT-TYPE
    SYNTAX     DisplayString (SIZE(0..255))
    MAX-ACCESS read-only
    STATUS     current
    DESCRIPTION
            "-- empty --"
    ::= { hmStatusCertsScepClntCasEntry 2 }

-- {COLUMN} 1.3.6.1.4.1.248.32.18.1.61.1.4.1.3
hmStatusCertsScepClntCasEntryExpires OBJECT-TYPE
    SYNTAX     DisplayString (SIZE(0..255))
    MAX-ACCESS read-only
    STATUS     current
    DESCRIPTION
            "-- empty --"
    ::= { hmStatusCertsScepClntCasEntry 3 }

-- {COLUMN} 1.3.6.1.4.1.248.32.18.1.61.1.4.1.4
hmStatusCertsScepClntCasEntryIssued OBJECT-TYPE
    SYNTAX     DisplayString (SIZE(0..255))
    MAX-ACCESS read-only
    STATUS     current
    DESCRIPTION
            "-- empty --"
    ::= { hmStatusCertsScepClntCasEntry 4 }

-- {COLUMN} 1.3.6.1.4.1.248.32.18.1.61.1.4.1.5
hmStatusCertsScepClntCasEntryKeyUsage OBJECT-TYPE
    SYNTAX     DisplayString (SIZE(0..255))
    MAX-ACCESS read-only
    STATUS     current
    DESCRIPTION
            "-- empty --"
    ::= { hmStatusCertsScepClntCasEntry 5 }

-- {COLUMN} 1.3.6.1.4.1.248.32.18.1.61.1.4.1.6
hmStatusCertsScepClntCasEntryIssuer OBJECT-TYPE
    SYNTAX     DisplayString (SIZE(0..255))
    MAX-ACCESS read-only
    STATUS     current
    DESCRIPTION
            "-- empty --"
    ::= { hmStatusCertsScepClntCasEntry 6 }

-- {COLUMN} 1.3.6.1.4.1.248.32.18.1.61.1.4.1.7
hmStatusCertsScepClntCasEntrySubject OBJECT-TYPE
    SYNTAX     DisplayString (SIZE(0..255))
    MAX-ACCESS read-only
    STATUS     current
    DESCRIPTION
            "-- empty --"
    ::= { hmStatusCertsScepClntCasEntry 7 }

-- {COLUMN} 1.3.6.1.4.1.248.32.18.1.61.1.4.1.8
hmStatusCertsScepClntCasEntryStatus OBJECT-TYPE
    SYNTAX     DisplayString (SIZE(0..255))
    MAX-ACCESS read-only
    STATUS     current
    DESCRIPTION
            "-- empty --"
    ::= { hmStatusCertsScepClntCasEntry 8 }

-- {COLUMN} 1.3.6.1.4.1.248.32.18.1.61.1.4.1.9
hmStatusCertsScepClntCasEntryIkeCertificate OBJECT-TYPE
    SYNTAX     DisplayString (SIZE(0..255))
    MAX-ACCESS read-only
    STATUS     current
    DESCRIPTION
            "-- empty --"
    ::= { hmStatusCertsScepClntCasEntry 9 }

-- {COLUMN} 1.3.6.1.4.1.248.32.18.1.61.1.4.1.10
hmStatusCertsScepClntCasEntryMd5Fingerprint OBJECT-TYPE
    SYNTAX     DisplayString (SIZE(0..255))
    MAX-ACCESS read-only
    STATUS     current
    DESCRIPTION
            "-- empty --"
    ::= { hmStatusCertsScepClntCasEntry 10 }

-- {COLUMN} 1.3.6.1.4.1.248.32.18.1.61.1.4.1.11
hmStatusCertsScepClntCasEntrySha1Fingerprint OBJECT-TYPE
    SYNTAX     DisplayString (SIZE(0..255))
    MAX-ACCESS read-only
    STATUS     current
    DESCRIPTION
            "-- empty --"
    ::= { hmStatusCertsScepClntCasEntry 11 }

-- {COLUMN} 1.3.6.1.4.1.248.32.18.1.61.1.4.1.12
hmStatusCertsScepClntCasEntryExpSnmp OBJECT-TYPE
    SYNTAX     Counter32
    MAX-ACCESS read-only
    STATUS     current
    DESCRIPTION
            "-- empty --"
    ::= { hmStatusCertsScepClntCasEntry 12 }

-- {COLUMN} 1.3.6.1.4.1.248.32.18.1.61.1.4.1.13
hmStatusCertsScepClntCasEntryIssSnmp OBJECT-TYPE
    SYNTAX     Counter32
    MAX-ACCESS read-only
    STATUS     current
    DESCRIPTION
            "-- empty --"
    ::= { hmStatusCertsScepClntCasEntry 13 }

-- {TABLE} 1.3.6.1.4.1.248.32.18.1.61.1.5
hmStatusCertsScepClntRasTable OBJECT-TYPE
    SYNTAX     SEQUENCE OF HmStatusCertsScepClntRasEntry
    MAX-ACCESS not-accessible
    STATUS     current
    DESCRIPTION
            "-- empty --"
    ::= { hmStatusCertsScepClnt 5 }

-- {ROW} 1.3.6.1.4.1.248.32.18.1.61.1.5.1
hmStatusCertsScepClntRasEntry OBJECT-TYPE
    SYNTAX     HmStatusCertsScepClntRasEntry
    MAX-ACCESS not-accessible
    STATUS     current
    DESCRIPTION
            ""
    INDEX {
            hmStatusCertsScepClntRasEntryIdx
          }
    ::= { hmStatusCertsScepClntRasTable 1 }

HmStatusCertsScepClntRasEntry ::= SEQUENCE {
            hmStatusCertsScepClntRasEntryIdx Integer32,
            hmStatusCertsScepClntRasEntryName DisplayString,
            hmStatusCertsScepClntRasEntryExpires DisplayString,
            hmStatusCertsScepClntRasEntryIssued DisplayString,
            hmStatusCertsScepClntRasEntryKeyUsage DisplayString,
            hmStatusCertsScepClntRasEntryIssuer DisplayString,
            hmStatusCertsScepClntRasEntrySubject DisplayString,
            hmStatusCertsScepClntRasEntryStatus DisplayString,
            hmStatusCertsScepClntRasEntryExpSnmp Counter32,
            hmStatusCertsScepClntRasEntryIssSnmp Counter32
    }

-- {COLUMN} 1.3.6.1.4.1.248.32.18.1.61.1.5.1.1
hmStatusCertsScepClntRasEntryIdx OBJECT-TYPE
    SYNTAX     Integer32 (0..2147483647)
    MAX-ACCESS read-only
    STATUS     current
    DESCRIPTION
            "-- empty --"
    ::= { hmStatusCertsScepClntRasEntry 1 }

-- {COLUMN} 1.3.6.1.4.1.248.32.18.1.61.1.5.1.2
hmStatusCertsScepClntRasEntryName OBJECT-TYPE
    SYNTAX     DisplayString (SIZE(0..255))
    MAX-ACCESS read-only
    STATUS     current
    DESCRIPTION
            "-- empty --"
    ::= { hmStatusCertsScepClntRasEntry 2 }

-- {COLUMN} 1.3.6.1.4.1.248.32.18.1.61.1.5.1.3
hmStatusCertsScepClntRasEntryExpires OBJECT-TYPE
    SYNTAX     DisplayString (SIZE(0..255))
    MAX-ACCESS read-only
    STATUS     current
    DESCRIPTION
            "-- empty --"
    ::= { hmStatusCertsScepClntRasEntry 3 }

-- {COLUMN} 1.3.6.1.4.1.248.32.18.1.61.1.5.1.4
hmStatusCertsScepClntRasEntryIssued OBJECT-TYPE
    SYNTAX     DisplayString (SIZE(0..255))
    MAX-ACCESS read-only
    STATUS     current
    DESCRIPTION
            "-- empty --"
    ::= { hmStatusCertsScepClntRasEntry 4 }

-- {COLUMN} 1.3.6.1.4.1.248.32.18.1.61.1.5.1.5
hmStatusCertsScepClntRasEntryKeyUsage OBJECT-TYPE
    SYNTAX     DisplayString (SIZE(0..255))
    MAX-ACCESS read-only
    STATUS     current
    DESCRIPTION
            "-- empty --"
    ::= { hmStatusCertsScepClntRasEntry 5 }

-- {COLUMN} 1.3.6.1.4.1.248.32.18.1.61.1.5.1.6
hmStatusCertsScepClntRasEntryIssuer OBJECT-TYPE
    SYNTAX     DisplayString (SIZE(0..255))
    MAX-ACCESS read-only
    STATUS     current
    DESCRIPTION
            "-- empty --"
    ::= { hmStatusCertsScepClntRasEntry 6 }

-- {COLUMN} 1.3.6.1.4.1.248.32.18.1.61.1.5.1.7
hmStatusCertsScepClntRasEntrySubject OBJECT-TYPE
    SYNTAX     DisplayString (SIZE(0..255))
    MAX-ACCESS read-only
    STATUS     current
    DESCRIPTION
            "-- empty --"
    ::= { hmStatusCertsScepClntRasEntry 7 }

-- {COLUMN} 1.3.6.1.4.1.248.32.18.1.61.1.5.1.8
hmStatusCertsScepClntRasEntryStatus OBJECT-TYPE
    SYNTAX     DisplayString (SIZE(0..255))
    MAX-ACCESS read-only
    STATUS     current
    DESCRIPTION
            "-- empty --"
    ::= { hmStatusCertsScepClntRasEntry 8 }

-- {COLUMN} 1.3.6.1.4.1.248.32.18.1.61.1.5.1.9
hmStatusCertsScepClntRasEntryExpSnmp OBJECT-TYPE
    SYNTAX     Counter32
    MAX-ACCESS read-only
    STATUS     current
    DESCRIPTION
            "-- empty --"
    ::= { hmStatusCertsScepClntRasEntry 9 }

-- {COLUMN} 1.3.6.1.4.1.248.32.18.1.61.1.5.1.10
hmStatusCertsScepClntRasEntryIssSnmp OBJECT-TYPE
    SYNTAX     Counter32
    MAX-ACCESS read-only
    STATUS     current
    DESCRIPTION
            "-- empty --"
    ::= { hmStatusCertsScepClntRasEntry 10 }

-- {TABLE} 1.3.6.1.4.1.248.32.18.1.61.1.6
hmStatusCertsScepClntCertsTable OBJECT-TYPE
    SYNTAX     SEQUENCE OF HmStatusCertsScepClntCertsEntry
    MAX-ACCESS not-accessible
    STATUS     current
    DESCRIPTION
            "-- empty --"
    ::= { hmStatusCertsScepClnt 6 }

-- {ROW} 1.3.6.1.4.1.248.32.18.1.61.1.6.1
hmStatusCertsScepClntCertsEntry OBJECT-TYPE
    SYNTAX     HmStatusCertsScepClntCertsEntry
    MAX-ACCESS not-accessible
    STATUS     current
    DESCRIPTION
            ""
    INDEX {
            hmStatusCertsScepClntCertsEntryIdx
          }
    ::= { hmStatusCertsScepClntCertsTable 1 }

HmStatusCertsScepClntCertsEntry ::= SEQUENCE {
            hmStatusCertsScepClntCertsEntryIdx Integer32,
            hmStatusCertsScepClntCertsEntryName DisplayString,
            hmStatusCertsScepClntCertsEntryExpires DisplayString,
            hmStatusCertsScepClntCertsEntryIssued DisplayString,
            hmStatusCertsScepClntCertsEntryKeyUsage DisplayString,
            hmStatusCertsScepClntCertsEntrySubjectaltname DisplayString,
            hmStatusCertsScepClntCertsEntryIssuer DisplayString,
            hmStatusCertsScepClntCertsEntrySubject DisplayString,
            hmStatusCertsScepClntCertsEntryStatus DisplayString,
            hmStatusCertsScepClntCertsEntryExpSnmp Counter32,
            hmStatusCertsScepClntCertsEntryIssSnmp Counter32,
            hmStatusCertsScepClntCertsEntryExtendedKeyusage DisplayString,
            hmStatusCertsScepClntCertsEntryFilename DisplayString
    }

-- {COLUMN} 1.3.6.1.4.1.248.32.18.1.61.1.6.1.1
hmStatusCertsScepClntCertsEntryIdx OBJECT-TYPE
    SYNTAX     Integer32 (0..2147483647)
    MAX-ACCESS read-only
    STATUS     current
    DESCRIPTION
            "-- empty --"
    ::= { hmStatusCertsScepClntCertsEntry 1 }

-- {COLUMN} 1.3.6.1.4.1.248.32.18.1.61.1.6.1.2
hmStatusCertsScepClntCertsEntryName OBJECT-TYPE
    SYNTAX     DisplayString (SIZE(0..255))
    MAX-ACCESS read-only
    STATUS     current
    DESCRIPTION
            "-- empty --"
    ::= { hmStatusCertsScepClntCertsEntry 2 }

-- {COLUMN} 1.3.6.1.4.1.248.32.18.1.61.1.6.1.3
hmStatusCertsScepClntCertsEntryExpires OBJECT-TYPE
    SYNTAX     DisplayString (SIZE(0..255))
    MAX-ACCESS read-only
    STATUS     current
    DESCRIPTION
            "-- empty --"
    ::= { hmStatusCertsScepClntCertsEntry 3 }

-- {COLUMN} 1.3.6.1.4.1.248.32.18.1.61.1.6.1.4
hmStatusCertsScepClntCertsEntryIssued OBJECT-TYPE
    SYNTAX     DisplayString (SIZE(0..255))
    MAX-ACCESS read-only
    STATUS     current
    DESCRIPTION
            "-- empty --"
    ::= { hmStatusCertsScepClntCertsEntry 4 }

-- {COLUMN} 1.3.6.1.4.1.248.32.18.1.61.1.6.1.5
hmStatusCertsScepClntCertsEntryKeyUsage OBJECT-TYPE
    SYNTAX     DisplayString (SIZE(0..255))
    MAX-ACCESS read-only
    STATUS     current
    DESCRIPTION
            "-- empty --"
    ::= { hmStatusCertsScepClntCertsEntry 5 }

-- {COLUMN} 1.3.6.1.4.1.248.32.18.1.61.1.6.1.6
hmStatusCertsScepClntCertsEntrySubjectaltname OBJECT-TYPE
    SYNTAX     DisplayString (SIZE(0..255))
    MAX-ACCESS read-only
    STATUS     current
    DESCRIPTION
            "-- empty --"
    ::= { hmStatusCertsScepClntCertsEntry 6 }

-- {COLUMN} 1.3.6.1.4.1.248.32.18.1.61.1.6.1.7
hmStatusCertsScepClntCertsEntryIssuer OBJECT-TYPE
    SYNTAX     DisplayString (SIZE(0..255))
    MAX-ACCESS read-only
    STATUS     current
    DESCRIPTION
            "-- empty --"
    ::= { hmStatusCertsScepClntCertsEntry 7 }

-- {COLUMN} 1.3.6.1.4.1.248.32.18.1.61.1.6.1.8
hmStatusCertsScepClntCertsEntrySubject OBJECT-TYPE
    SYNTAX     DisplayString (SIZE(0..255))
    MAX-ACCESS read-only
    STATUS     current
    DESCRIPTION
            "-- empty --"
    ::= { hmStatusCertsScepClntCertsEntry 8 }

-- {COLUMN} 1.3.6.1.4.1.248.32.18.1.61.1.6.1.9
hmStatusCertsScepClntCertsEntryStatus OBJECT-TYPE
    SYNTAX     DisplayString (SIZE(0..255))
    MAX-ACCESS read-only
    STATUS     current
    DESCRIPTION
            "-- empty --"
    ::= { hmStatusCertsScepClntCertsEntry 9 }

-- {COLUMN} 1.3.6.1.4.1.248.32.18.1.61.1.6.1.10
hmStatusCertsScepClntCertsEntryExpSnmp OBJECT-TYPE
    SYNTAX     Counter32
    MAX-ACCESS read-only
    STATUS     current
    DESCRIPTION
            "-- empty --"
    ::= { hmStatusCertsScepClntCertsEntry 10 }

-- {COLUMN} 1.3.6.1.4.1.248.32.18.1.61.1.6.1.11
hmStatusCertsScepClntCertsEntryIssSnmp OBJECT-TYPE
    SYNTAX     Counter32
    MAX-ACCESS read-only
    STATUS     current
    DESCRIPTION
            "-- empty --"
    ::= { hmStatusCertsScepClntCertsEntry 11 }

-- {COLUMN} 1.3.6.1.4.1.248.32.18.1.61.1.6.1.12
hmStatusCertsScepClntCertsEntryExtendedKeyusage OBJECT-TYPE
    SYNTAX     DisplayString (SIZE(0..255))
    MAX-ACCESS read-only
    STATUS     current
    DESCRIPTION
            "-- empty --"
    ::= { hmStatusCertsScepClntCertsEntry 12 }

-- {COLUMN} 1.3.6.1.4.1.248.32.18.1.61.1.6.1.13
hmStatusCertsScepClntCertsEntryFilename OBJECT-TYPE
    SYNTAX     DisplayString (SIZE(0..255))
    MAX-ACCESS read-only
    STATUS     current
    DESCRIPTION
            "-- empty --"
    ::= { hmStatusCertsScepClntCertsEntry 13 }

-- {SCALAR} 1.3.6.1.4.1.248.32.18.1.61.1.8
hmStatusCertsScepClntScepClientState OBJECT-TYPE
    SYNTAX     DisplayString
    MAX-ACCESS read-only
    STATUS     current
    DESCRIPTION
            "-- empty --"
    ::= { hmStatusCertsScepClnt 8 }

-- {NODE} 1.3.6.1.4.1.248.32.18.1.61.2
hmStatusCertsScepCa OBJECT IDENTIFIER ::= { hmStatusCerts 2 }

-- {NODE} 1.3.6.1.4.1.248.32.18.1.61.2.1
hmStatusCertsScepCaCerts OBJECT IDENTIFIER ::= { hmStatusCertsScepCa 1 }

-- {TABLE} 1.3.6.1.4.1.248.32.18.1.61.2.1.1
hmStatusCertsScepCaCertsCertsStatusTabTable OBJECT-TYPE
    SYNTAX     SEQUENCE OF HmStatusCertsScepCaCertsCertsStatusTabEntry
    MAX-ACCESS not-accessible
    STATUS     current
    DESCRIPTION
            "certificates status table"
    ::= { hmStatusCertsScepCaCerts 1 }

-- {ROW} 1.3.6.1.4.1.248.32.18.1.61.2.1.1.1
hmStatusCertsScepCaCertsCertsStatusTabEntry OBJECT-TYPE
    SYNTAX     HmStatusCertsScepCaCertsCertsStatusTabEntry
    MAX-ACCESS not-accessible
    STATUS     current
    DESCRIPTION
            ""
    INDEX {
            hmStatusCertsScepCaCertsCertsStatusTabEntryIndex
          }
    ::= { hmStatusCertsScepCaCertsCertsStatusTabTable 1 }

HmStatusCertsScepCaCertsCertsStatusTabEntry ::= SEQUENCE {
            hmStatusCertsScepCaCertsCertsStatusTabEntryIndex Integer32,
            hmStatusCertsScepCaCertsCertsStatusTabEntrySerialnumber DisplayString,
            hmStatusCertsScepCaCertsCertsStatusTabEntryStatus DisplayString,
            hmStatusCertsScepCaCertsCertsStatusTabEntryCreationDate DisplayString,
            hmStatusCertsScepCaCertsCertsStatusTabEntryEndTime DisplayString,
            hmStatusCertsScepCaCertsCertsStatusTabEntryRevTime DisplayString,
            hmStatusCertsScepCaCertsCertsStatusTabEntryRevReas DisplayString,
            hmStatusCertsScepCaCertsCertsStatusTabEntryMacAddress DisplayString,
            hmStatusCertsScepCaCertsCertsStatusTabEntryDn DisplayString,
            hmStatusCertsScepCaCertsCertsStatusTabEntryProfileName DisplayString
    }

-- {COLUMN} 1.3.6.1.4.1.248.32.18.1.61.2.1.1.1.1
hmStatusCertsScepCaCertsCertsStatusTabEntryIndex OBJECT-TYPE
    SYNTAX     Integer32 (0..2147483647)
    MAX-ACCESS read-only
    STATUS     current
    DESCRIPTION
            "-- empty --"
    ::= { hmStatusCertsScepCaCertsCertsStatusTabEntry 1 }

-- {COLUMN} 1.3.6.1.4.1.248.32.18.1.61.2.1.1.1.2
hmStatusCertsScepCaCertsCertsStatusTabEntrySerialnumber OBJECT-TYPE
    SYNTAX     DisplayString (SIZE(0..255))
    MAX-ACCESS read-only
    STATUS     current
    DESCRIPTION
            "-- empty --"
    ::= { hmStatusCertsScepCaCertsCertsStatusTabEntry 2 }

-- {COLUMN} 1.3.6.1.4.1.248.32.18.1.61.2.1.1.1.3
hmStatusCertsScepCaCertsCertsStatusTabEntryStatus OBJECT-TYPE
    SYNTAX     DisplayString (SIZE(0..255))
    MAX-ACCESS read-only
    STATUS     current
    DESCRIPTION
            "-- empty --"
    ::= { hmStatusCertsScepCaCertsCertsStatusTabEntry 3 }

-- {COLUMN} 1.3.6.1.4.1.248.32.18.1.61.2.1.1.1.4
hmStatusCertsScepCaCertsCertsStatusTabEntryCreationDate OBJECT-TYPE
    SYNTAX     DisplayString (SIZE(0..255))
    MAX-ACCESS read-only
    STATUS     current
    DESCRIPTION
            "-- empty --"
    ::= { hmStatusCertsScepCaCertsCertsStatusTabEntry 4 }

-- {COLUMN} 1.3.6.1.4.1.248.32.18.1.61.2.1.1.1.5
hmStatusCertsScepCaCertsCertsStatusTabEntryEndTime OBJECT-TYPE
    SYNTAX     DisplayString (SIZE(0..255))
    MAX-ACCESS read-only
    STATUS     current
    DESCRIPTION
            "ending time"
    ::= { hmStatusCertsScepCaCertsCertsStatusTabEntry 5 }

-- {COLUMN} 1.3.6.1.4.1.248.32.18.1.61.2.1.1.1.6
hmStatusCertsScepCaCertsCertsStatusTabEntryRevTime OBJECT-TYPE
    SYNTAX     DisplayString (SIZE(0..255))
    MAX-ACCESS read-only
    STATUS     current
    DESCRIPTION
            "revocation time"
    ::= { hmStatusCertsScepCaCertsCertsStatusTabEntry 6 }

-- {COLUMN} 1.3.6.1.4.1.248.32.18.1.61.2.1.1.1.7
hmStatusCertsScepCaCertsCertsStatusTabEntryRevReas OBJECT-TYPE
    SYNTAX     DisplayString (SIZE(0..255))
    MAX-ACCESS read-only
    STATUS     current
    DESCRIPTION
            "revoke reason"
    ::= { hmStatusCertsScepCaCertsCertsStatusTabEntry 7 }

-- {COLUMN} 1.3.6.1.4.1.248.32.18.1.61.2.1.1.1.8
hmStatusCertsScepCaCertsCertsStatusTabEntryMacAddress OBJECT-TYPE
    SYNTAX     DisplayString (SIZE(0..255))
    MAX-ACCESS read-only
    STATUS     current
    DESCRIPTION
            "-- empty --"
    ::= { hmStatusCertsScepCaCertsCertsStatusTabEntry 8 }

-- {COLUMN} 1.3.6.1.4.1.248.32.18.1.61.2.1.1.1.9
hmStatusCertsScepCaCertsCertsStatusTabEntryDn OBJECT-TYPE
    SYNTAX     DisplayString (SIZE(0..255))
    MAX-ACCESS read-only
    STATUS     current
    DESCRIPTION
            "-- empty --"
    ::= { hmStatusCertsScepCaCertsCertsStatusTabEntry 9 }

-- {COLUMN} 1.3.6.1.4.1.248.32.18.1.61.2.1.1.1.10
hmStatusCertsScepCaCertsCertsStatusTabEntryProfileName OBJECT-TYPE
    SYNTAX     DisplayString (SIZE(0..255))
    MAX-ACCESS read-only
    STATUS     current
    DESCRIPTION
            "-- empty --"
    ::= { hmStatusCertsScepCaCertsCertsStatusTabEntry 10 }

-- {SCALAR} 1.3.6.1.4.1.248.32.18.1.61.2.1.2
hmStatusCertsScepCaCertsRevokeCertificate OBJECT-TYPE
    SYNTAX     DisplayString
    MAX-ACCESS read-write
    STATUS     current
    DESCRIPTION
            "-- empty --"
    ::= { hmStatusCertsScepCaCerts 2 }

-- {SCALAR} 1.3.6.1.4.1.248.32.18.1.61.2.1.3
hmStatusCertsScepCaCertsSetCertificateOnHold OBJECT-TYPE
    SYNTAX     DisplayString
    MAX-ACCESS read-write
    STATUS     current
    DESCRIPTION
            "-- empty --"
    ::= { hmStatusCertsScepCaCerts 3 }

-- {SCALAR} 1.3.6.1.4.1.248.32.18.1.61.2.1.4
hmStatusCertsScepCaCertsDeclCertsValid OBJECT-TYPE
    SYNTAX     DisplayString
    MAX-ACCESS read-write
    STATUS     current
    DESCRIPTION
            "declare certificates as valid again"
    ::= { hmStatusCertsScepCaCerts 4 }

-- {NODE} 1.3.6.1.4.1.248.32.18.1.61.2.2
hmStatusCertsScepCaRequests OBJECT IDENTIFIER ::= { hmStatusCertsScepCa 2 }

-- {TABLE} 1.3.6.1.4.1.248.32.18.1.61.2.2.1
hmStatusCertsScepCaRequestsPendReqTable OBJECT-TYPE
    SYNTAX     SEQUENCE OF HmStatusCertsScepCaRequestsPendReqEntry
    MAX-ACCESS not-accessible
    STATUS     current
    DESCRIPTION
            "pending requests"
    ::= { hmStatusCertsScepCaRequests 1 }

-- {ROW} 1.3.6.1.4.1.248.32.18.1.61.2.2.1.1
hmStatusCertsScepCaRequestsPendReqEntry OBJECT-TYPE
    SYNTAX     HmStatusCertsScepCaRequestsPendReqEntry
    MAX-ACCESS not-accessible
    STATUS     current
    DESCRIPTION
            ""
    INDEX {
            hmStatusCertsScepCaRequestsPendReqEntryIndex
          }
    ::= { hmStatusCertsScepCaRequestsPendReqTable 1 }

HmStatusCertsScepCaRequestsPendReqEntry ::= SEQUENCE {
            hmStatusCertsScepCaRequestsPendReqEntryIndex Integer32,
            hmStatusCertsScepCaRequestsPendReqEntryTransactionId DisplayString,
            hmStatusCertsScepCaRequestsPendReqEntryMacAddress DisplayString,
            hmStatusCertsScepCaRequestsPendReqEntryIpAddress IpAddress,
            hmStatusCertsScepCaRequestsPendReqEntryPkiStatus DisplayString,
            hmStatusCertsScepCaRequestsPendReqEntryReason INTEGER,
            hmStatusCertsScepCaRequestsPendReqEntryRequestFingerprint DisplayString,
            hmStatusCertsScepCaRequestsPendReqEntryDn DisplayString,
            hmStatusCertsScepCaRequestsPendReqEntryReceiveDate DisplayString
    }

-- {COLUMN} 1.3.6.1.4.1.248.32.18.1.61.2.2.1.1.1
hmStatusCertsScepCaRequestsPendReqEntryIndex OBJECT-TYPE
    SYNTAX     Integer32 (0..65535)
    MAX-ACCESS read-only
    STATUS     current
    DESCRIPTION
            "-- empty --"
    ::= { hmStatusCertsScepCaRequestsPendReqEntry 1 }

-- {COLUMN} 1.3.6.1.4.1.248.32.18.1.61.2.2.1.1.2
hmStatusCertsScepCaRequestsPendReqEntryTransactionId OBJECT-TYPE
    SYNTAX     DisplayString (SIZE(0..32))
    MAX-ACCESS read-only
    STATUS     current
    DESCRIPTION
            "-- empty --"
    ::= { hmStatusCertsScepCaRequestsPendReqEntry 2 }

-- {COLUMN} 1.3.6.1.4.1.248.32.18.1.61.2.2.1.1.3
hmStatusCertsScepCaRequestsPendReqEntryMacAddress OBJECT-TYPE
    SYNTAX     DisplayString (SIZE(0..12))
    MAX-ACCESS read-only
    STATUS     current
    DESCRIPTION
            "-- empty --"
    ::= { hmStatusCertsScepCaRequestsPendReqEntry 3 }

-- {COLUMN} 1.3.6.1.4.1.248.32.18.1.61.2.2.1.1.4
hmStatusCertsScepCaRequestsPendReqEntryIpAddress OBJECT-TYPE
    SYNTAX     IpAddress
    MAX-ACCESS read-only
    STATUS     current
    DESCRIPTION
            "-- empty --"
    ::= { hmStatusCertsScepCaRequestsPendReqEntry 4 }

-- {COLUMN} 1.3.6.1.4.1.248.32.18.1.61.2.2.1.1.5
hmStatusCertsScepCaRequestsPendReqEntryPkiStatus OBJECT-TYPE
    SYNTAX     DisplayString (SIZE(0..7))
    MAX-ACCESS read-only
    STATUS     current
    DESCRIPTION
            "-- empty --"
    ::= { hmStatusCertsScepCaRequestsPendReqEntry 5 }

-- {COLUMN} 1.3.6.1.4.1.248.32.18.1.61.2.2.1.1.6
hmStatusCertsScepCaRequestsPendReqEntryReason OBJECT-TYPE
    SYNTAX     INTEGER {
                  eUnknownReason (0),
                  eManuallyDeclined (1),
                  eManuallyGranted (2),
                  eAutoapproveNotAllowed (3),
                  eClientCertificateIsNotValid (4),
                  eClientCertificateIsNotOldEnoughForRenewal (5),
                  eClientRequestContainsNoChallengePassword (6),
                  eNoGeneralChallengePasswordAvailableForClients (7),
                  eRequestContainsBrokenChallengePasswordAttribute (8),
                  eChallengePasswordDoesNotMatch (9),
                  eInternalProcessingError (10),
                  eRequestSignatureVerificationFailed (11),
                  eNoCertificateRequestAvailable (12),
                  eRequestSubjectNameDoesNotMatchCertificateSubjectName (13),
                  eMaximalSizeOfCertificateListReached (14)
            }
    MAX-ACCESS read-only
    STATUS     current
    DESCRIPTION
            "-- empty --"
    ::= { hmStatusCertsScepCaRequestsPendReqEntry 6 }

-- {COLUMN} 1.3.6.1.4.1.248.32.18.1.61.2.2.1.1.7
hmStatusCertsScepCaRequestsPendReqEntryRequestFingerprint OBJECT-TYPE
    SYNTAX     DisplayString (SIZE(0..128))
    MAX-ACCESS read-only
    STATUS     current
    DESCRIPTION
            "-- empty --"
    ::= { hmStatusCertsScepCaRequestsPendReqEntry 7 }

-- {COLUMN} 1.3.6.1.4.1.248.32.18.1.61.2.2.1.1.8
hmStatusCertsScepCaRequestsPendReqEntryDn OBJECT-TYPE
    SYNTAX     DisplayString (SIZE(0..251))
    MAX-ACCESS read-only
    STATUS     current
    DESCRIPTION
            "-- empty --"
    ::= { hmStatusCertsScepCaRequestsPendReqEntry 8 }

-- {COLUMN} 1.3.6.1.4.1.248.32.18.1.61.2.2.1.1.9
hmStatusCertsScepCaRequestsPendReqEntryReceiveDate OBJECT-TYPE
    SYNTAX     DisplayString (SIZE(0..63))
    MAX-ACCESS read-only
    STATUS     current
    DESCRIPTION
            "-- empty --"
    ::= { hmStatusCertsScepCaRequestsPendReqEntry 9 }

-- {SCALAR} 1.3.6.1.4.1.248.32.18.1.61.2.2.2
hmStatusCertsScepCaRequestsIssueCertificate OBJECT-TYPE
    SYNTAX     DisplayString
    MAX-ACCESS read-write
    STATUS     current
    DESCRIPTION
            "-- empty --"
    ::= { hmStatusCertsScepCaRequests 2 }

-- {SCALAR} 1.3.6.1.4.1.248.32.18.1.61.2.2.3
hmStatusCertsScepCaRequestsGrantAllCertificates OBJECT-TYPE
    SYNTAX     DisplayString
    MAX-ACCESS read-write
    STATUS     current
    DESCRIPTION
            "-- empty --"
    ::= { hmStatusCertsScepCaRequests 3 }

-- {SCALAR} 1.3.6.1.4.1.248.32.18.1.61.2.2.4
hmStatusCertsScepCaRequestsDeclineRequest OBJECT-TYPE
    SYNTAX     DisplayString
    MAX-ACCESS read-write
    STATUS     current
    DESCRIPTION
            "-- empty --"
    ::= { hmStatusCertsScepCaRequests 4 }

-- {SCALAR} 1.3.6.1.4.1.248.32.18.1.61.2.2.5
hmStatusCertsScepCaRequestsDenyAllRequests OBJECT-TYPE
    SYNTAX     DisplayString
    MAX-ACCESS read-write
    STATUS     current
    DESCRIPTION
            "-- empty --"
    ::= { hmStatusCertsScepCaRequests 5 }

-- {SCALAR} 1.3.6.1.4.1.248.32.18.1.61.2.2.6
hmStatusCertsScepCaRequestsDeletePendingRequest OBJECT-TYPE
    SYNTAX     DisplayString
    MAX-ACCESS read-write
    STATUS     current
    DESCRIPTION
            "-- empty --"
    ::= { hmStatusCertsScepCaRequests 6 }

-- {SCALAR} 1.3.6.1.4.1.248.32.18.1.61.2.2.7
hmStatusCertsScepCaRequestsDeleteAllPendingRequests OBJECT-TYPE
    SYNTAX     DisplayString
    MAX-ACCESS read-write
    STATUS     current
    DESCRIPTION
            "-- empty --"
    ::= { hmStatusCertsScepCaRequests 7 }

-- {NODE} 1.3.6.1.4.1.248.32.18.1.61.2.3
hmStatusCertsScepCaCaStatus OBJECT IDENTIFIER ::= { hmStatusCertsScepCa 3 }

-- {SCALAR} 1.3.6.1.4.1.248.32.18.1.61.2.3.1
hmStatusCertsScepCaCaStatusCaStatus OBJECT-TYPE
    SYNTAX     INTEGER {
                  eDisabled (0),
                  eActive (1),
                  eInitializing (2),
                  eInitializationError (3)
            }
    MAX-ACCESS read-only
    STATUS     current
    DESCRIPTION
            "-- empty --"
    ::= { hmStatusCertsScepCaCaStatus 1 }

-- {SCALAR} 1.3.6.1.4.1.248.32.18.1.61.2.3.2
hmStatusCertsScepCaCaStatusError OBJECT-TYPE
    SYNTAX     INTEGER {
                  eNoError (0),
                  eNoValidCadn (1),
                  eNoValidRadn (2),
                  eNoValidKeyUsageForCaCertificate (3),
                  eNoValidKeyUsageForRaCertificate (4),
                  eNoUtcAvailable (6),
                  eConfiguredKeyLengthDoesNotMatchSavedKeys (7),
                  eNoGeneralChallengePasswordSet (8),
                  eValidityPeriodForCaRaIsZero (9),
                  eValidityPeriodForClientsIsZero (10),
                  eCouldNotCreateNewCaRaCertificates (11),
                  eCaRaCertificatesAreNotValid (12),
                  eSavedKeysDoNotMatchCertificates (13),
                  eRaCertKeyUsageMismatch (14),
                  eCaCertKeyUsageMismatch (15),
                  eCaCertDigestMismatch (16),
                  eRaCertDigestMismatch (17),
                  eCadnDoesNotMatchCertificate (18),
                  eRadnDoesNotMatchCertificate (19),
                  eNoMemoryAvailable (20),
                  eRandomPoolNotSeeded (21),
                  eMaximalSizeOfCertificateListReached (23),
                  eValidityPeriodForClientsIsTooLong (24),
                  eConfigCheckLimitReached (25)
            }
    MAX-ACCESS read-only
    STATUS     current
    DESCRIPTION
            "-- empty --"
    ::= { hmStatusCertsScepCaCaStatus 2 }

-- {SCALAR} 1.3.6.1.4.1.248.32.18.1.61.2.3.3
hmStatusCertsScepCaCaStatusAdditonalErrorInformation OBJECT-TYPE
    SYNTAX     DisplayString
    MAX-ACCESS read-only
    STATUS     current
    DESCRIPTION
            "-- empty --"
    ::= { hmStatusCertsScepCaCaStatus 3 }

-- {SCALAR} 1.3.6.1.4.1.248.32.18.1.61.2.3.4
hmStatusCertsScepCaCaStatusFingerprintAlgorithm OBJECT-TYPE
    SYNTAX     INTEGER {
                  eMd5 (0),
                  eSha1 (1),
                  eSha2256 (2),
                  eSha2384 (3),
                  eSha2512 (4)
            }
    MAX-ACCESS read-only
    STATUS     current
    DESCRIPTION
            "-- empty --"
    ::= { hmStatusCertsScepCaCaStatus 4 }

-- {SCALAR} 1.3.6.1.4.1.248.32.18.1.61.2.3.5
hmStatusCertsScepCaCaStatusCaCertificateFingerprint OBJECT-TYPE
    SYNTAX     DisplayString
    MAX-ACCESS read-only
    STATUS     current
    DESCRIPTION
            "-- empty --"
    ::= { hmStatusCertsScepCaCaStatus 5 }

-- {SCALAR} 1.3.6.1.4.1.248.32.18.1.61.2.3.6
hmStatusCertsScepCaCaStatusRaCertificateFingerprint OBJECT-TYPE
    SYNTAX     DisplayString
    MAX-ACCESS read-only
    STATUS     current
    DESCRIPTION
            "-- empty --"
    ::= { hmStatusCertsScepCaCaStatus 6 }

-- {TABLE} 1.3.6.1.4.1.248.32.18.1.61.2.3.7
hmStatusCertsScepCaCaStatusLogTableTable OBJECT-TYPE
    SYNTAX     SEQUENCE OF HmStatusCertsScepCaCaStatusLogTableEntry
    MAX-ACCESS not-accessible
    STATUS     current
    DESCRIPTION
            "-- empty --"
    ::= { hmStatusCertsScepCaCaStatus 7 }

-- {ROW} 1.3.6.1.4.1.248.32.18.1.61.2.3.7.1
hmStatusCertsScepCaCaStatusLogTableEntry OBJECT-TYPE
    SYNTAX     HmStatusCertsScepCaCaStatusLogTableEntry
    MAX-ACCESS not-accessible
    STATUS     current
    DESCRIPTION
            ""
    INDEX {
            hmStatusCertsScepCaCaStatusLogTableEntryIndex
          }
    ::= { hmStatusCertsScepCaCaStatusLogTableTable 1 }

HmStatusCertsScepCaCaStatusLogTableEntry ::= SEQUENCE {
            hmStatusCertsScepCaCaStatusLogTableEntryIndex Integer32,
            hmStatusCertsScepCaCaStatusLogTableEntryTime DisplayString,
            hmStatusCertsScepCaCaStatusLogTableEntryEvent DisplayString
    }

-- {COLUMN} 1.3.6.1.4.1.248.32.18.1.61.2.3.7.1.1
hmStatusCertsScepCaCaStatusLogTableEntryIndex OBJECT-TYPE
    SYNTAX     Integer32 (0..2147483647)
    MAX-ACCESS read-only
    STATUS     current
    DESCRIPTION
            "-- empty --"
    ::= { hmStatusCertsScepCaCaStatusLogTableEntry 1 }

-- {COLUMN} 1.3.6.1.4.1.248.32.18.1.61.2.3.7.1.2
hmStatusCertsScepCaCaStatusLogTableEntryTime OBJECT-TYPE
    SYNTAX     DisplayString (SIZE(0..19))
    MAX-ACCESS read-only
    STATUS     current
    DESCRIPTION
            "-- empty --"
    ::= { hmStatusCertsScepCaCaStatusLogTableEntry 2 }

-- {COLUMN} 1.3.6.1.4.1.248.32.18.1.61.2.3.7.1.6
hmStatusCertsScepCaCaStatusLogTableEntryEvent OBJECT-TYPE
    SYNTAX     DisplayString (SIZE(0..80))
    MAX-ACCESS read-only
    STATUS     current
    DESCRIPTION
            "-- empty --"
    ::= { hmStatusCertsScepCaCaStatusLogTableEntry 6 }

-- {NODE} 1.3.6.1.4.1.248.32.18.1.61.2.4
hmStatusCertsScepCaWebIfc OBJECT IDENTIFIER ::= { hmStatusCertsScepCa 4 }

-- {TABLE} 1.3.6.1.4.1.248.32.18.1.61.2.4.1
hmStatusCertsScepCaWebIfcProfilesTable OBJECT-TYPE
    SYNTAX     SEQUENCE OF HmStatusCertsScepCaWebIfcProfilesEntry
    MAX-ACCESS not-accessible
    STATUS     current
    DESCRIPTION
            "-- empty --"
    ::= { hmStatusCertsScepCaWebIfc 1 }

-- {ROW} 1.3.6.1.4.1.248.32.18.1.61.2.4.1.1
hmStatusCertsScepCaWebIfcProfilesEntry OBJECT-TYPE
    SYNTAX     HmStatusCertsScepCaWebIfcProfilesEntry
    MAX-ACCESS not-accessible
    STATUS     current
    DESCRIPTION
            ""
    INDEX {
            hmStatusCertsScepCaWebIfcProfilesEntryProfileName,
            hmStatusCertsScepCaWebIfcProfilesEntryTemplate
          }
    ::= { hmStatusCertsScepCaWebIfcProfilesTable 1 }

HmStatusCertsScepCaWebIfcProfilesEntry ::= SEQUENCE {
            hmStatusCertsScepCaWebIfcProfilesEntryProfileName DisplayString,
            hmStatusCertsScepCaWebIfcProfilesEntryKeyUsage DisplayString,
            hmStatusCertsScepCaWebIfcProfilesEntryExtendedKeyUsage DisplayString,
            hmStatusCertsScepCaWebIfcProfilesEntryRsaKeyLength INTEGER,
            hmStatusCertsScepCaWebIfcProfilesEntryValidityPeriod Integer32,
            hmStatusCertsScepCaWebIfcProfilesEntryCa INTEGER,
            hmStatusCertsScepCaWebIfcProfilesEntryPassword DisplayString,
            hmStatusCertsScepCaWebIfcProfilesEntryCountryName DisplayString,
            hmStatusCertsScepCaWebIfcProfilesEntryLocalityName DisplayString,
            hmStatusCertsScepCaWebIfcProfilesEntryOrganizationName DisplayString,
            hmStatusCertsScepCaWebIfcProfilesEntryOrganizationUnitName DisplayString,
            hmStatusCertsScepCaWebIfcProfilesEntryStateOrProvince DisplayString,
            hmStatusCertsScepCaWebIfcProfilesEntryEMail DisplayString,
            hmStatusCertsScepCaWebIfcProfilesEntrySurname DisplayString,
            hmStatusCertsScepCaWebIfcProfilesEntrySerialNumber DisplayString,
            hmStatusCertsScepCaWebIfcProfilesEntryPostalCode DisplayString,
            hmStatusCertsScepCaWebIfcProfilesEntryTemplate DisplayString,
            hmStatusCertsScepCaWebIfcProfilesEntrySubjectAlternativeName DisplayString
    }

-- {COLUMN} 1.3.6.1.4.1.248.32.18.1.61.2.4.1.1.1
hmStatusCertsScepCaWebIfcProfilesEntryProfileName OBJECT-TYPE
    SYNTAX     DisplayString (SIZE(0..32))
    MAX-ACCESS read-only
    STATUS     current
    DESCRIPTION
            "-- empty --"
    ::= { hmStatusCertsScepCaWebIfcProfilesEntry 1 }

-- {COLUMN} 1.3.6.1.4.1.248.32.18.1.61.2.4.1.1.2
hmStatusCertsScepCaWebIfcProfilesEntryKeyUsage OBJECT-TYPE
    SYNTAX     DisplayString (SIZE(0..251))
    MAX-ACCESS read-only
    STATUS     current
    DESCRIPTION
            "-- empty --"
    ::= { hmStatusCertsScepCaWebIfcProfilesEntry 2 }

-- {COLUMN} 1.3.6.1.4.1.248.32.18.1.61.2.4.1.1.3
hmStatusCertsScepCaWebIfcProfilesEntryExtendedKeyUsage OBJECT-TYPE
    SYNTAX     DisplayString (SIZE(0..251))
    MAX-ACCESS read-only
    STATUS     current
    DESCRIPTION
            "-- empty --"
    ::= { hmStatusCertsScepCaWebIfcProfilesEntry 3 }

-- {COLUMN} 1.3.6.1.4.1.248.32.18.1.61.2.4.1.1.4
hmStatusCertsScepCaWebIfcProfilesEntryRsaKeyLength OBJECT-TYPE
    SYNTAX     INTEGER {
                  e1024 (1024),
                  e2048 (2048),
                  e3072 (3072),
                  e4096 (4096),
                  e8192 (8192)
            }
    MAX-ACCESS read-only
    STATUS     current
    DESCRIPTION
            "-- empty --"
    ::= { hmStatusCertsScepCaWebIfcProfilesEntry 4 }

-- {COLUMN} 1.3.6.1.4.1.248.32.18.1.61.2.4.1.1.5
hmStatusCertsScepCaWebIfcProfilesEntryValidityPeriod OBJECT-TYPE
    SYNTAX     Integer32 (0..2147483647)
    MAX-ACCESS read-only
    STATUS     current
    DESCRIPTION
            "-- empty --"
    ::= { hmStatusCertsScepCaWebIfcProfilesEntry 5 }

-- {COLUMN} 1.3.6.1.4.1.248.32.18.1.61.2.4.1.1.6
hmStatusCertsScepCaWebIfcProfilesEntryCa OBJECT-TYPE
    SYNTAX     INTEGER {
                  eNo (0),
                  eYes (1)
            }
    MAX-ACCESS read-only
    STATUS     current
    DESCRIPTION
            "-- empty --"
    ::= { hmStatusCertsScepCaWebIfcProfilesEntry 6 }

-- {COLUMN} 1.3.6.1.4.1.248.32.18.1.61.2.4.1.1.7
hmStatusCertsScepCaWebIfcProfilesEntryPassword OBJECT-TYPE
    SYNTAX     DisplayString (SIZE(0..32))
    MAX-ACCESS read-only
    STATUS     current
    DESCRIPTION
            "-- empty --"
    ::= { hmStatusCertsScepCaWebIfcProfilesEntry 7 }

-- {COLUMN} 1.3.6.1.4.1.248.32.18.1.61.2.4.1.1.8
hmStatusCertsScepCaWebIfcProfilesEntryCountryName OBJECT-TYPE
    SYNTAX     DisplayString (SIZE(0..2))
    MAX-ACCESS read-only
    STATUS     current
    DESCRIPTION
            "-- empty --"
    ::= { hmStatusCertsScepCaWebIfcProfilesEntry 8 }

-- {COLUMN} 1.3.6.1.4.1.248.32.18.1.61.2.4.1.1.9
hmStatusCertsScepCaWebIfcProfilesEntryLocalityName OBJECT-TYPE
    SYNTAX     DisplayString (SIZE(0..32))
    MAX-ACCESS read-only
    STATUS     current
    DESCRIPTION
            "-- empty --"
    ::= { hmStatusCertsScepCaWebIfcProfilesEntry 9 }

-- {COLUMN} 1.3.6.1.4.1.248.32.18.1.61.2.4.1.1.10
hmStatusCertsScepCaWebIfcProfilesEntryOrganizationName OBJECT-TYPE
    SYNTAX     DisplayString (SIZE(0..32))
    MAX-ACCESS read-only
    STATUS     current
    DESCRIPTION
            "-- empty --"
    ::= { hmStatusCertsScepCaWebIfcProfilesEntry 10 }

-- {COLUMN} 1.3.6.1.4.1.248.32.18.1.61.2.4.1.1.11
hmStatusCertsScepCaWebIfcProfilesEntryOrganizationUnitName OBJECT-TYPE
    SYNTAX     DisplayString (SIZE(0..32))
    MAX-ACCESS read-only
    STATUS     current
    DESCRIPTION
            "-- empty --"
    ::= { hmStatusCertsScepCaWebIfcProfilesEntry 11 }

-- {COLUMN} 1.3.6.1.4.1.248.32.18.1.61.2.4.1.1.12
hmStatusCertsScepCaWebIfcProfilesEntryStateOrProvince OBJECT-TYPE
    SYNTAX     DisplayString (SIZE(0..32))
    MAX-ACCESS read-only
    STATUS     current
    DESCRIPTION
            "-- empty --"
    ::= { hmStatusCertsScepCaWebIfcProfilesEntry 12 }

-- {COLUMN} 1.3.6.1.4.1.248.32.18.1.61.2.4.1.1.13
hmStatusCertsScepCaWebIfcProfilesEntryEMail OBJECT-TYPE
    SYNTAX     DisplayString (SIZE(0..64))
    MAX-ACCESS read-only
    STATUS     current
    DESCRIPTION
            "-- empty --"
    ::= { hmStatusCertsScepCaWebIfcProfilesEntry 13 }

-- {COLUMN} 1.3.6.1.4.1.248.32.18.1.61.2.4.1.1.14
hmStatusCertsScepCaWebIfcProfilesEntrySurname OBJECT-TYPE
    SYNTAX     DisplayString (SIZE(0..32))
    MAX-ACCESS read-only
    STATUS     current
    DESCRIPTION
            "-- empty --"
    ::= { hmStatusCertsScepCaWebIfcProfilesEntry 14 }

-- {COLUMN} 1.3.6.1.4.1.248.32.18.1.61.2.4.1.1.15
hmStatusCertsScepCaWebIfcProfilesEntrySerialNumber OBJECT-TYPE
    SYNTAX     DisplayString (SIZE(0..32))
    MAX-ACCESS read-only
    STATUS     current
    DESCRIPTION
            "-- empty --"
    ::= { hmStatusCertsScepCaWebIfcProfilesEntry 15 }

-- {COLUMN} 1.3.6.1.4.1.248.32.18.1.61.2.4.1.1.16
hmStatusCertsScepCaWebIfcProfilesEntryPostalCode OBJECT-TYPE
    SYNTAX     DisplayString (SIZE(0..25))
    MAX-ACCESS read-only
    STATUS     current
    DESCRIPTION
            "-- empty --"
    ::= { hmStatusCertsScepCaWebIfcProfilesEntry 16 }

-- {COLUMN} 1.3.6.1.4.1.248.32.18.1.61.2.4.1.1.17
hmStatusCertsScepCaWebIfcProfilesEntryTemplate OBJECT-TYPE
    SYNTAX     DisplayString (SIZE(0..31))
    MAX-ACCESS read-only
    STATUS     current
    DESCRIPTION
            "-- empty --"
    ::= { hmStatusCertsScepCaWebIfcProfilesEntry 17 }

-- {COLUMN} 1.3.6.1.4.1.248.32.18.1.61.2.4.1.1.18
hmStatusCertsScepCaWebIfcProfilesEntrySubjectAlternativeName OBJECT-TYPE
    SYNTAX     DisplayString (SIZE(0..254))
    MAX-ACCESS read-only
    STATUS     current
    DESCRIPTION
            "-- empty --"
    ::= { hmStatusCertsScepCaWebIfcProfilesEntry 18 }

-- {TABLE} 1.3.6.1.4.1.248.32.18.1.61.2.4.2
hmStatusCertsScepCaWebIfcTemplateTable OBJECT-TYPE
    SYNTAX     SEQUENCE OF HmStatusCertsScepCaWebIfcTemplateEntry
    MAX-ACCESS not-accessible
    STATUS     current
    DESCRIPTION
            "-- empty --"
    ::= { hmStatusCertsScepCaWebIfc 2 }

-- {ROW} 1.3.6.1.4.1.248.32.18.1.61.2.4.2.1
hmStatusCertsScepCaWebIfcTemplateEntry OBJECT-TYPE
    SYNTAX     HmStatusCertsScepCaWebIfcTemplateEntry
    MAX-ACCESS not-accessible
    STATUS     current
    DESCRIPTION
            ""
    INDEX {
            hmStatusCertsScepCaWebIfcTemplateEntryName
          }
    ::= { hmStatusCertsScepCaWebIfcTemplateTable 1 }

HmStatusCertsScepCaWebIfcTemplateEntry ::= SEQUENCE {
            hmStatusCertsScepCaWebIfcTemplateEntryName DisplayString,
            hmStatusCertsScepCaWebIfcTemplateEntryKeyUsage INTEGER,
            hmStatusCertsScepCaWebIfcTemplateEntryExtendedKeyUsage INTEGER,
            hmStatusCertsScepCaWebIfcTemplateEntryRsaKeyLength INTEGER,
            hmStatusCertsScepCaWebIfcTemplateEntryValidityPeriod INTEGER,
            hmStatusCertsScepCaWebIfcTemplateEntryCa INTEGER,
            hmStatusCertsScepCaWebIfcTemplateEntryPassword Integer32,
            hmStatusCertsScepCaWebIfcTemplateEntryCountryName INTEGER,
            hmStatusCertsScepCaWebIfcTemplateEntryLocalityName INTEGER,
            hmStatusCertsScepCaWebIfcTemplateEntryOrganizationName INTEGER,
            hmStatusCertsScepCaWebIfcTemplateEntryOrganizationUnitName INTEGER,
            hmStatusCertsScepCaWebIfcTemplateEntryStateOrProvince INTEGER,
            hmStatusCertsScepCaWebIfcTemplateEntryEMail INTEGER,
            hmStatusCertsScepCaWebIfcTemplateEntrySurname INTEGER,
            hmStatusCertsScepCaWebIfcTemplateEntrySerialNumber INTEGER,
            hmStatusCertsScepCaWebIfcTemplateEntryPostalCode INTEGER,
            hmStatusCertsScepCaWebIfcTemplateEntrySubjectAlternativeName INTEGER
    }

-- {COLUMN} 1.3.6.1.4.1.248.32.18.1.61.2.4.2.1.1
hmStatusCertsScepCaWebIfcTemplateEntryName OBJECT-TYPE
    SYNTAX     DisplayString (SIZE(0..31))
    MAX-ACCESS read-only
    STATUS     current
    DESCRIPTION
            "-- empty --"
    ::= { hmStatusCertsScepCaWebIfcTemplateEntry 1 }

-- {COLUMN} 1.3.6.1.4.1.248.32.18.1.61.2.4.2.1.2
hmStatusCertsScepCaWebIfcTemplateEntryKeyUsage OBJECT-TYPE
    SYNTAX     INTEGER {
                  eNo (0),
                  eYes (1),
                  eMandatory (2),
                  eFixed (3)
            }
    MAX-ACCESS read-only
    STATUS     current
    DESCRIPTION
            "-- empty --"
    ::= { hmStatusCertsScepCaWebIfcTemplateEntry 2 }

-- {COLUMN} 1.3.6.1.4.1.248.32.18.1.61.2.4.2.1.3
hmStatusCertsScepCaWebIfcTemplateEntryExtendedKeyUsage OBJECT-TYPE
    SYNTAX     INTEGER {
                  eNo (0),
                  eYes (1),
                  eMandatory (2),
                  eFixed (3)
            }
    MAX-ACCESS read-only
    STATUS     current
    DESCRIPTION
            "-- empty --"
    ::= { hmStatusCertsScepCaWebIfcTemplateEntry 3 }

-- {COLUMN} 1.3.6.1.4.1.248.32.18.1.61.2.4.2.1.4
hmStatusCertsScepCaWebIfcTemplateEntryRsaKeyLength OBJECT-TYPE
    SYNTAX     INTEGER {
                  eNo (0),
                  eYes (1),
                  eMandatory (2),
                  eFixed (3)
            }
    MAX-ACCESS read-only
    STATUS     current
    DESCRIPTION
            "-- empty --"
    ::= { hmStatusCertsScepCaWebIfcTemplateEntry 4 }

-- {COLUMN} 1.3.6.1.4.1.248.32.18.1.61.2.4.2.1.5
hmStatusCertsScepCaWebIfcTemplateEntryValidityPeriod OBJECT-TYPE
    SYNTAX     INTEGER {
                  eNo (0),
                  eYes (1),
                  eMandatory (2),
                  eFixed (3)
            }
    MAX-ACCESS read-only
    STATUS     current
    DESCRIPTION
            "-- empty --"
    ::= { hmStatusCertsScepCaWebIfcTemplateEntry 5 }

-- {COLUMN} 1.3.6.1.4.1.248.32.18.1.61.2.4.2.1.6
hmStatusCertsScepCaWebIfcTemplateEntryCa OBJECT-TYPE
    SYNTAX     INTEGER {
                  eNo (0),
                  eYes (1),
                  eMandatory (2),
                  eFixed (3)
            }
    MAX-ACCESS read-only
    STATUS     current
    DESCRIPTION
            "-- empty --"
    ::= { hmStatusCertsScepCaWebIfcTemplateEntry 6 }

-- {COLUMN} 1.3.6.1.4.1.248.32.18.1.61.2.4.2.1.7
hmStatusCertsScepCaWebIfcTemplateEntryPassword OBJECT-TYPE
    SYNTAX     Integer32 (0..255)
    MAX-ACCESS read-only
    STATUS     current
    DESCRIPTION
            "-- empty --"
    ::= { hmStatusCertsScepCaWebIfcTemplateEntry 7 }

-- {COLUMN} 1.3.6.1.4.1.248.32.18.1.61.2.4.2.1.8
hmStatusCertsScepCaWebIfcTemplateEntryCountryName OBJECT-TYPE
    SYNTAX     INTEGER {
                  eNo (0),
                  eYes (1),
                  eMandatory (2),
                  eFixed (3)
            }
    MAX-ACCESS read-only
    STATUS     current
    DESCRIPTION
            "-- empty --"
    ::= { hmStatusCertsScepCaWebIfcTemplateEntry 8 }

-- {COLUMN} 1.3.6.1.4.1.248.32.18.1.61.2.4.2.1.9
hmStatusCertsScepCaWebIfcTemplateEntryLocalityName OBJECT-TYPE
    SYNTAX     INTEGER {
                  eNo (0),
                  eYes (1),
                  eMandatory (2),
                  eFixed (3)
            }
    MAX-ACCESS read-only
    STATUS     current
    DESCRIPTION
            "-- empty --"
    ::= { hmStatusCertsScepCaWebIfcTemplateEntry 9 }

-- {COLUMN} 1.3.6.1.4.1.248.32.18.1.61.2.4.2.1.10
hmStatusCertsScepCaWebIfcTemplateEntryOrganizationName OBJECT-TYPE
    SYNTAX     INTEGER {
                  eNo (0),
                  eYes (1),
                  eMandatory (2),
                  eFixed (3)
            }
    MAX-ACCESS read-only
    STATUS     current
    DESCRIPTION
            "-- empty --"
    ::= { hmStatusCertsScepCaWebIfcTemplateEntry 10 }

-- {COLUMN} 1.3.6.1.4.1.248.32.18.1.61.2.4.2.1.11
hmStatusCertsScepCaWebIfcTemplateEntryOrganizationUnitName OBJECT-TYPE
    SYNTAX     INTEGER {
                  eNo (0),
                  eYes (1),
                  eMandatory (2),
                  eFixed (3)
            }
    MAX-ACCESS read-only
    STATUS     current
    DESCRIPTION
            "-- empty --"
    ::= { hmStatusCertsScepCaWebIfcTemplateEntry 11 }

-- {COLUMN} 1.3.6.1.4.1.248.32.18.1.61.2.4.2.1.12
hmStatusCertsScepCaWebIfcTemplateEntryStateOrProvince OBJECT-TYPE
    SYNTAX     INTEGER {
                  eNo (0),
                  eYes (1),
                  eMandatory (2),
                  eFixed (3)
            }
    MAX-ACCESS read-only
    STATUS     current
    DESCRIPTION
            "-- empty --"
    ::= { hmStatusCertsScepCaWebIfcTemplateEntry 12 }

-- {COLUMN} 1.3.6.1.4.1.248.32.18.1.61.2.4.2.1.13
hmStatusCertsScepCaWebIfcTemplateEntryEMail OBJECT-TYPE
    SYNTAX     INTEGER {
                  eNo (0),
                  eYes (1),
                  eMandatory (2),
                  eFixed (3)
            }
    MAX-ACCESS read-only
    STATUS     current
    DESCRIPTION
            "-- empty --"
    ::= { hmStatusCertsScepCaWebIfcTemplateEntry 13 }

-- {COLUMN} 1.3.6.1.4.1.248.32.18.1.61.2.4.2.1.14
hmStatusCertsScepCaWebIfcTemplateEntrySurname OBJECT-TYPE
    SYNTAX     INTEGER {
                  eNo (0),
                  eYes (1),
                  eMandatory (2),
                  eFixed (3)
            }
    MAX-ACCESS read-only
    STATUS     current
    DESCRIPTION
            "-- empty --"
    ::= { hmStatusCertsScepCaWebIfcTemplateEntry 14 }

-- {COLUMN} 1.3.6.1.4.1.248.32.18.1.61.2.4.2.1.15
hmStatusCertsScepCaWebIfcTemplateEntrySerialNumber OBJECT-TYPE
    SYNTAX     INTEGER {
                  eNo (0),
                  eYes (1),
                  eMandatory (2),
                  eFixed (3)
            }
    MAX-ACCESS read-only
    STATUS     current
    DESCRIPTION
            "-- empty --"
    ::= { hmStatusCertsScepCaWebIfcTemplateEntry 15 }

-- {COLUMN} 1.3.6.1.4.1.248.32.18.1.61.2.4.2.1.16
hmStatusCertsScepCaWebIfcTemplateEntryPostalCode OBJECT-TYPE
    SYNTAX     INTEGER {
                  eNo (0),
                  eYes (1),
                  eMandatory (2),
                  eFixed (3)
            }
    MAX-ACCESS read-only
    STATUS     current
    DESCRIPTION
            "-- empty --"
    ::= { hmStatusCertsScepCaWebIfcTemplateEntry 16 }

-- {COLUMN} 1.3.6.1.4.1.248.32.18.1.61.2.4.2.1.17
hmStatusCertsScepCaWebIfcTemplateEntrySubjectAlternativeName OBJECT-TYPE
    SYNTAX     INTEGER {
                  eNo (0),
                  eYes (1),
                  eMandatory (2),
                  eFixed (3)
            }
    MAX-ACCESS read-only
    STATUS     current
    DESCRIPTION
            "-- empty --"
    ::= { hmStatusCertsScepCaWebIfcTemplateEntry 17 }

-- {NODE} 1.3.6.1.4.1.248.32.18.1.61.3
hmStatusCertsCrls OBJECT IDENTIFIER ::= { hmStatusCerts 3 }

-- {SCALAR} 1.3.6.1.4.1.248.32.18.1.61.3.1
hmStatusCertsCrlsNumcrls OBJECT-TYPE
    SYNTAX     Integer32 (0..2147483647)
    MAX-ACCESS read-only
    STATUS     current
    DESCRIPTION
            "-- empty --"
    ::= { hmStatusCertsCrls 1 }

-- {TABLE} 1.3.6.1.4.1.248.32.18.1.61.3.2
hmStatusCertsCrlsCrlsTable OBJECT-TYPE
    SYNTAX     SEQUENCE OF HmStatusCertsCrlsCrlsEntry
    MAX-ACCESS not-accessible
    STATUS     current
    DESCRIPTION
            "-- empty --"
    ::= { hmStatusCertsCrls 2 }

-- {ROW} 1.3.6.1.4.1.248.32.18.1.61.3.2.1
hmStatusCertsCrlsCrlsEntry OBJECT-TYPE
    SYNTAX     HmStatusCertsCrlsCrlsEntry
    MAX-ACCESS not-accessible
    STATUS     current
    DESCRIPTION
            ""
    INDEX {
            hmStatusCertsCrlsCrlsEntryIdx
          }
    ::= { hmStatusCertsCrlsCrlsTable 1 }

HmStatusCertsCrlsCrlsEntry ::= SEQUENCE {
            hmStatusCertsCrlsCrlsEntryIdx Integer32,
            hmStatusCertsCrlsCrlsEntryExpires DisplayString,
            hmStatusCertsCrlsCrlsEntryIssued DisplayString,
            hmStatusCertsCrlsCrlsEntryIssuer DisplayString,
            hmStatusCertsCrlsCrlsEntryDistributionPoint DisplayString,
            hmStatusCertsCrlsCrlsEntryStatSnmp Integer32,
            hmStatusCertsCrlsCrlsEntryExpSnmp Counter32,
            hmStatusCertsCrlsCrlsEntryIssSnmp Counter32,
            hmStatusCertsCrlsCrlsEntryStatus DisplayString
    }

-- {COLUMN} 1.3.6.1.4.1.248.32.18.1.61.3.2.1.1
hmStatusCertsCrlsCrlsEntryIdx OBJECT-TYPE
    SYNTAX     Integer32 (0..2147483647)
    MAX-ACCESS read-only
    STATUS     current
    DESCRIPTION
            "-- empty --"
    ::= { hmStatusCertsCrlsCrlsEntry 1 }

-- {COLUMN} 1.3.6.1.4.1.248.32.18.1.61.3.2.1.2
hmStatusCertsCrlsCrlsEntryExpires OBJECT-TYPE
    SYNTAX     DisplayString (SIZE(0..255))
    MAX-ACCESS read-only
    STATUS     current
    DESCRIPTION
            "-- empty --"
    ::= { hmStatusCertsCrlsCrlsEntry 2 }

-- {COLUMN} 1.3.6.1.4.1.248.32.18.1.61.3.2.1.3
hmStatusCertsCrlsCrlsEntryIssued OBJECT-TYPE
    SYNTAX     DisplayString (SIZE(0..255))
    MAX-ACCESS read-only
    STATUS     current
    DESCRIPTION
            "-- empty --"
    ::= { hmStatusCertsCrlsCrlsEntry 3 }

-- {COLUMN} 1.3.6.1.4.1.248.32.18.1.61.3.2.1.4
hmStatusCertsCrlsCrlsEntryIssuer OBJECT-TYPE
    SYNTAX     DisplayString (SIZE(0..255))
    MAX-ACCESS read-only
    STATUS     current
    DESCRIPTION
            "-- empty --"
    ::= { hmStatusCertsCrlsCrlsEntry 4 }

-- {COLUMN} 1.3.6.1.4.1.248.32.18.1.61.3.2.1.5
hmStatusCertsCrlsCrlsEntryDistributionPoint OBJECT-TYPE
    SYNTAX     DisplayString (SIZE(0..255))
    MAX-ACCESS read-only
    STATUS     current
    DESCRIPTION
            "-- empty --"
    ::= { hmStatusCertsCrlsCrlsEntry 5 }

-- {COLUMN} 1.3.6.1.4.1.248.32.18.1.61.3.2.1.6
hmStatusCertsCrlsCrlsEntryStatSnmp OBJECT-TYPE
    SYNTAX     Integer32 (0..2147483647)
    MAX-ACCESS read-only
    STATUS     current
    DESCRIPTION
            "-- empty --"
    ::= { hmStatusCertsCrlsCrlsEntry 6 }

-- {COLUMN} 1.3.6.1.4.1.248.32.18.1.61.3.2.1.7
hmStatusCertsCrlsCrlsEntryExpSnmp OBJECT-TYPE
    SYNTAX     Counter32
    MAX-ACCESS read-only
    STATUS     current
    DESCRIPTION
            "-- empty --"
    ::= { hmStatusCertsCrlsCrlsEntry 7 }

-- {COLUMN} 1.3.6.1.4.1.248.32.18.1.61.3.2.1.8
hmStatusCertsCrlsCrlsEntryIssSnmp OBJECT-TYPE
    SYNTAX     Counter32
    MAX-ACCESS read-only
    STATUS     current
    DESCRIPTION
            "-- empty --"
    ::= { hmStatusCertsCrlsCrlsEntry 8 }

-- {COLUMN} 1.3.6.1.4.1.248.32.18.1.61.3.2.1.9
hmStatusCertsCrlsCrlsEntryStatus OBJECT-TYPE
    SYNTAX     DisplayString (SIZE(0..255))
    MAX-ACCESS read-only
    STATUS     current
    DESCRIPTION
            "-- empty --"
    ::= { hmStatusCertsCrlsCrlsEntry 9 }

-- {TABLE} 1.3.6.1.4.1.248.32.18.1.61.4
hmStatusCertsDeviceCertificatesTable OBJECT-TYPE
    SYNTAX     SEQUENCE OF HmStatusCertsDeviceCertificatesEntry
    MAX-ACCESS not-accessible
    STATUS     current
    DESCRIPTION
            "-- empty --"
    ::= { hmStatusCerts 4 }

-- {ROW} 1.3.6.1.4.1.248.32.18.1.61.4.1
hmStatusCertsDeviceCertificatesEntry OBJECT-TYPE
    SYNTAX     HmStatusCertsDeviceCertificatesEntry
    MAX-ACCESS not-accessible
    STATUS     current
    DESCRIPTION
            ""
    INDEX {
            hmStatusCertsDeviceCertificatesEntryFilename
          }
    ::= { hmStatusCertsDeviceCertificatesTable 1 }

HmStatusCertsDeviceCertificatesEntry ::= SEQUENCE {
            hmStatusCertsDeviceCertificatesEntryFilename DisplayString,
            hmStatusCertsDeviceCertificatesEntryAvailable INTEGER,
            hmStatusCertsDeviceCertificatesEntryExpires DisplayString,
            hmStatusCertsDeviceCertificatesEntryIssued DisplayString,
            hmStatusCertsDeviceCertificatesEntryKeyUsage DisplayString,
            hmStatusCertsDeviceCertificatesEntrySubjectaltname DisplayString,
            hmStatusCertsDeviceCertificatesEntryIssuer DisplayString,
            hmStatusCertsDeviceCertificatesEntrySubject DisplayString,
            hmStatusCertsDeviceCertificatesEntryApplication DisplayString,
            hmStatusCertsDeviceCertificatesEntryExtendedKeyusage DisplayString
    }

-- {COLUMN} 1.3.6.1.4.1.248.32.18.1.61.4.1.1
hmStatusCertsDeviceCertificatesEntryFilename OBJECT-TYPE
    SYNTAX     DisplayString (SIZE(0..255))
    MAX-ACCESS read-only
    STATUS     current
    DESCRIPTION
            "-- empty --"
    ::= { hmStatusCertsDeviceCertificatesEntry 1 }

-- {COLUMN} 1.3.6.1.4.1.248.32.18.1.61.4.1.2
hmStatusCertsDeviceCertificatesEntryAvailable OBJECT-TYPE
    SYNTAX     INTEGER {
                  eNo (0),
                  eYes (1)
            }
    MAX-ACCESS read-only
    STATUS     current
    DESCRIPTION
            "-- empty --"
    ::= { hmStatusCertsDeviceCertificatesEntry 2 }

-- {COLUMN} 1.3.6.1.4.1.248.32.18.1.61.4.1.3
hmStatusCertsDeviceCertificatesEntryExpires OBJECT-TYPE
    SYNTAX     DisplayString (SIZE(0..20))
    MAX-ACCESS read-only
    STATUS     current
    DESCRIPTION
            "-- empty --"
    ::= { hmStatusCertsDeviceCertificatesEntry 3 }

-- {COLUMN} 1.3.6.1.4.1.248.32.18.1.61.4.1.4
hmStatusCertsDeviceCertificatesEntryIssued OBJECT-TYPE
    SYNTAX     DisplayString (SIZE(0..20))
    MAX-ACCESS read-only
    STATUS     current
    DESCRIPTION
            "-- empty --"
    ::= { hmStatusCertsDeviceCertificatesEntry 4 }

-- {COLUMN} 1.3.6.1.4.1.248.32.18.1.61.4.1.5
hmStatusCertsDeviceCertificatesEntryKeyUsage OBJECT-TYPE
    SYNTAX     DisplayString (SIZE(0..251))
    MAX-ACCESS read-only
    STATUS     current
    DESCRIPTION
            "-- empty --"
    ::= { hmStatusCertsDeviceCertificatesEntry 5 }

-- {COLUMN} 1.3.6.1.4.1.248.32.18.1.61.4.1.6
hmStatusCertsDeviceCertificatesEntrySubjectaltname OBJECT-TYPE
    SYNTAX     DisplayString (SIZE(0..251))
    MAX-ACCESS read-only
    STATUS     current
    DESCRIPTION
            "-- empty --"
    ::= { hmStatusCertsDeviceCertificatesEntry 6 }

-- {COLUMN} 1.3.6.1.4.1.248.32.18.1.61.4.1.7
hmStatusCertsDeviceCertificatesEntryIssuer OBJECT-TYPE
    SYNTAX     DisplayString (SIZE(0..251))
    MAX-ACCESS read-only
    STATUS     current
    DESCRIPTION
            "-- empty --"
    ::= { hmStatusCertsDeviceCertificatesEntry 7 }

-- {COLUMN} 1.3.6.1.4.1.248.32.18.1.61.4.1.8
hmStatusCertsDeviceCertificatesEntrySubject OBJECT-TYPE
    SYNTAX     DisplayString (SIZE(0..251))
    MAX-ACCESS read-only
    STATUS     current
    DESCRIPTION
            "-- empty --"
    ::= { hmStatusCertsDeviceCertificatesEntry 8 }

-- {COLUMN} 1.3.6.1.4.1.248.32.18.1.61.4.1.9
hmStatusCertsDeviceCertificatesEntryApplication OBJECT-TYPE
    SYNTAX     DisplayString (SIZE(0..15))
    MAX-ACCESS read-only
    STATUS     current
    DESCRIPTION
            "-- empty --"
    ::= { hmStatusCertsDeviceCertificatesEntry 9 }

-- {COLUMN} 1.3.6.1.4.1.248.32.18.1.61.4.1.12
hmStatusCertsDeviceCertificatesEntryExtendedKeyusage OBJECT-TYPE
    SYNTAX     DisplayString (SIZE(0..251))
    MAX-ACCESS read-only
    STATUS     current
    DESCRIPTION
            "-- empty --"
    ::= { hmStatusCertsDeviceCertificatesEntry 12 }

-- {NODE} 1.3.6.1.4.1.248.32.18.1.61.6
hmStatusCertsOcspClient OBJECT IDENTIFIER ::= { hmStatusCerts 6 }

-- {TABLE} 1.3.6.1.4.1.248.32.18.1.61.6.1
hmStatusCertsOcspClientCaStatusTableTable OBJECT-TYPE
    SYNTAX     SEQUENCE OF HmStatusCertsOcspClientCaStatusTableEntry
    MAX-ACCESS not-accessible
    STATUS     current
    DESCRIPTION
            "-- empty --"
    ::= { hmStatusCertsOcspClient 1 }

-- {ROW} 1.3.6.1.4.1.248.32.18.1.61.6.1.1
hmStatusCertsOcspClientCaStatusTableEntry OBJECT-TYPE
    SYNTAX     HmStatusCertsOcspClientCaStatusTableEntry
    MAX-ACCESS not-accessible
    STATUS     current
    DESCRIPTION
            ""
    INDEX {
            hmStatusCertsOcspClientCaStatusTableEntryProfileName
          }
    ::= { hmStatusCertsOcspClientCaStatusTableTable 1 }

HmStatusCertsOcspClientCaStatusTableEntry ::= SEQUENCE {
            hmStatusCertsOcspClientCaStatusTableEntryProfileName DisplayString,
            hmStatusCertsOcspClientCaStatusTableEntryRequests Integer32,
            hmStatusCertsOcspClientCaStatusTableEntryResponses Integer32,
            hmStatusCertsOcspClientCaStatusTableEntryGoodResponses Integer32,
            hmStatusCertsOcspClientCaStatusTableEntryRevokeResponses Integer32,
            hmStatusCertsOcspClientCaStatusTableEntryUnknownResponses Integer32,
            hmStatusCertsOcspClientCaStatusTableEntrySuccessfulResponses Integer32,
            hmStatusCertsOcspClientCaStatusTableEntryErrorResponses Integer32,
            hmStatusCertsOcspClientCaStatusTableEntryMalformedRequests Integer32,
            hmStatusCertsOcspClientCaStatusTableEntryIntErrorResponses Integer32,
            hmStatusCertsOcspClientCaStatusTableEntryTryLaterResponses Integer32,
            hmStatusCertsOcspClientCaStatusTableEntrySignRequiredResponses Integer32,
            hmStatusCertsOcspClientCaStatusTableEntryUnauthorizedResponses Integer32,
            hmStatusCertsOcspClientCaStatusTableEntrySignerVerifyFailures Integer32,
            hmStatusCertsOcspClientCaStatusTableEntryCertTimedOuts Integer32,
            hmStatusCertsOcspClientCaStatusTableEntryGenericErrors Integer32,
            hmStatusCertsOcspClientCaStatusTableEntryTransportErrors Integer32
    }

-- {COLUMN} 1.3.6.1.4.1.248.32.18.1.61.6.1.1.1
hmStatusCertsOcspClientCaStatusTableEntryProfileName OBJECT-TYPE
    SYNTAX     DisplayString (SIZE(0..32))
    MAX-ACCESS read-only
    STATUS     current
    DESCRIPTION
            "-- empty --"
    ::= { hmStatusCertsOcspClientCaStatusTableEntry 1 }

-- {COLUMN} 1.3.6.1.4.1.248.32.18.1.61.6.1.1.2
hmStatusCertsOcspClientCaStatusTableEntryRequests OBJECT-TYPE
    SYNTAX     Integer32 (0..2147483647)
    MAX-ACCESS read-only
    STATUS     current
    DESCRIPTION
            "-- empty --"
    ::= { hmStatusCertsOcspClientCaStatusTableEntry 2 }

-- {COLUMN} 1.3.6.1.4.1.248.32.18.1.61.6.1.1.3
hmStatusCertsOcspClientCaStatusTableEntryResponses OBJECT-TYPE
    SYNTAX     Integer32 (0..2147483647)
    MAX-ACCESS read-only
    STATUS     current
    DESCRIPTION
            "-- empty --"
    ::= { hmStatusCertsOcspClientCaStatusTableEntry 3 }

-- {COLUMN} 1.3.6.1.4.1.248.32.18.1.61.6.1.1.4
hmStatusCertsOcspClientCaStatusTableEntryGoodResponses OBJECT-TYPE
    SYNTAX     Integer32 (0..2147483647)
    MAX-ACCESS read-only
    STATUS     current
    DESCRIPTION
            "-- empty --"
    ::= { hmStatusCertsOcspClientCaStatusTableEntry 4 }

-- {COLUMN} 1.3.6.1.4.1.248.32.18.1.61.6.1.1.5
hmStatusCertsOcspClientCaStatusTableEntryRevokeResponses OBJECT-TYPE
    SYNTAX     Integer32 (0..2147483647)
    MAX-ACCESS read-only
    STATUS     current
    DESCRIPTION
            "-- empty --"
    ::= { hmStatusCertsOcspClientCaStatusTableEntry 5 }

-- {COLUMN} 1.3.6.1.4.1.248.32.18.1.61.6.1.1.6
hmStatusCertsOcspClientCaStatusTableEntryUnknownResponses OBJECT-TYPE
    SYNTAX     Integer32 (0..2147483647)
    MAX-ACCESS read-only
    STATUS     current
    DESCRIPTION
            "-- empty --"
    ::= { hmStatusCertsOcspClientCaStatusTableEntry 6 }

-- {COLUMN} 1.3.6.1.4.1.248.32.18.1.61.6.1.1.7
hmStatusCertsOcspClientCaStatusTableEntrySuccessfulResponses OBJECT-TYPE
    SYNTAX     Integer32 (0..2147483647)
    MAX-ACCESS read-only
    STATUS     current
    DESCRIPTION
            "-- empty --"
    ::= { hmStatusCertsOcspClientCaStatusTableEntry 7 }

-- {COLUMN} 1.3.6.1.4.1.248.32.18.1.61.6.1.1.8
hmStatusCertsOcspClientCaStatusTableEntryErrorResponses OBJECT-TYPE
    SYNTAX     Integer32 (0..2147483647)
    MAX-ACCESS read-only
    STATUS     current
    DESCRIPTION
            "-- empty --"
    ::= { hmStatusCertsOcspClientCaStatusTableEntry 8 }

-- {COLUMN} 1.3.6.1.4.1.248.32.18.1.61.6.1.1.9
hmStatusCertsOcspClientCaStatusTableEntryMalformedRequests OBJECT-TYPE
    SYNTAX     Integer32 (0..2147483647)
    MAX-ACCESS read-only
    STATUS     current
    DESCRIPTION
            "-- empty --"
    ::= { hmStatusCertsOcspClientCaStatusTableEntry 9 }

-- {COLUMN} 1.3.6.1.4.1.248.32.18.1.61.6.1.1.10
hmStatusCertsOcspClientCaStatusTableEntryIntErrorResponses OBJECT-TYPE
    SYNTAX     Integer32 (0..2147483647)
    MAX-ACCESS read-only
    STATUS     current
    DESCRIPTION
            "-- empty --"
    ::= { hmStatusCertsOcspClientCaStatusTableEntry 10 }

-- {COLUMN} 1.3.6.1.4.1.248.32.18.1.61.6.1.1.11
hmStatusCertsOcspClientCaStatusTableEntryTryLaterResponses OBJECT-TYPE
    SYNTAX     Integer32 (0..2147483647)
    MAX-ACCESS read-only
    STATUS     current
    DESCRIPTION
            "-- empty --"
    ::= { hmStatusCertsOcspClientCaStatusTableEntry 11 }

-- {COLUMN} 1.3.6.1.4.1.248.32.18.1.61.6.1.1.12
hmStatusCertsOcspClientCaStatusTableEntrySignRequiredResponses OBJECT-TYPE
    SYNTAX     Integer32 (0..2147483647)
    MAX-ACCESS read-only
    STATUS     current
    DESCRIPTION
            "-- empty --"
    ::= { hmStatusCertsOcspClientCaStatusTableEntry 12 }

-- {COLUMN} 1.3.6.1.4.1.248.32.18.1.61.6.1.1.13
hmStatusCertsOcspClientCaStatusTableEntryUnauthorizedResponses OBJECT-TYPE
    SYNTAX     Integer32 (0..2147483647)
    MAX-ACCESS read-only
    STATUS     current
    DESCRIPTION
            "-- empty --"
    ::= { hmStatusCertsOcspClientCaStatusTableEntry 13 }

-- {COLUMN} 1.3.6.1.4.1.248.32.18.1.61.6.1.1.14
hmStatusCertsOcspClientCaStatusTableEntrySignerVerifyFailures OBJECT-TYPE
    SYNTAX     Integer32 (0..2147483647)
    MAX-ACCESS read-only
    STATUS     current
    DESCRIPTION
            "-- empty --"
    ::= { hmStatusCertsOcspClientCaStatusTableEntry 14 }

-- {COLUMN} 1.3.6.1.4.1.248.32.18.1.61.6.1.1.15
hmStatusCertsOcspClientCaStatusTableEntryCertTimedOuts OBJECT-TYPE
    SYNTAX     Integer32 (0..2147483647)
    MAX-ACCESS read-only
    STATUS     current
    DESCRIPTION
            "-- empty --"
    ::= { hmStatusCertsOcspClientCaStatusTableEntry 15 }

-- {COLUMN} 1.3.6.1.4.1.248.32.18.1.61.6.1.1.16
hmStatusCertsOcspClientCaStatusTableEntryGenericErrors OBJECT-TYPE
    SYNTAX     Integer32 (0..2147483647)
    MAX-ACCESS read-only
    STATUS     current
    DESCRIPTION
            "-- empty --"
    ::= { hmStatusCertsOcspClientCaStatusTableEntry 16 }

-- {COLUMN} 1.3.6.1.4.1.248.32.18.1.61.6.1.1.17
hmStatusCertsOcspClientCaStatusTableEntryTransportErrors OBJECT-TYPE
    SYNTAX     Integer32 (0..2147483647)
    MAX-ACCESS read-only
    STATUS     current
    DESCRIPTION
            "-- empty --"
    ::= { hmStatusCertsOcspClientCaStatusTableEntry 17 }

-- {NODE} 1.3.6.1.4.1.248.32.18.1.62
hmStatusVlan OBJECT IDENTIFIER ::= { hmStatus 62 }

-- {TABLE} 1.3.6.1.4.1.248.32.18.1.62.1
hmStatusVlanNetworksTable OBJECT-TYPE
    SYNTAX     SEQUENCE OF HmStatusVlanNetworksEntry
    MAX-ACCESS not-accessible
    STATUS     current
    DESCRIPTION
            "-- empty --"
    ::= { hmStatusVlan 1 }

-- {ROW} 1.3.6.1.4.1.248.32.18.1.62.1.1
hmStatusVlanNetworksEntry OBJECT-TYPE
    SYNTAX     HmStatusVlanNetworksEntry
    MAX-ACCESS not-accessible
    STATUS     current
    DESCRIPTION
            ""
    INDEX {
            hmStatusVlanNetworksEntryVlanId
          }
    ::= { hmStatusVlanNetworksTable 1 }

HmStatusVlanNetworksEntry ::= SEQUENCE {
            hmStatusVlanNetworksEntryVlanId Integer32,
            hmStatusVlanNetworksEntryPorts DisplayString
    }

-- {COLUMN} 1.3.6.1.4.1.248.32.18.1.62.1.1.1
hmStatusVlanNetworksEntryVlanId OBJECT-TYPE
    SYNTAX     Integer32 (0..65535)
    MAX-ACCESS read-only
    STATUS     current
    DESCRIPTION
            "-- empty --"
    ::= { hmStatusVlanNetworksEntry 1 }

-- {COLUMN} 1.3.6.1.4.1.248.32.18.1.62.1.1.4
hmStatusVlanNetworksEntryPorts OBJECT-TYPE
    SYNTAX     DisplayString (SIZE(0..255))
    MAX-ACCESS read-only
    STATUS     current
    DESCRIPTION
            "-- empty --"
    ::= { hmStatusVlanNetworksEntry 4 }

-- {TABLE} 1.3.6.1.4.1.248.32.18.1.62.2
hmStatusVlanPortTableTable OBJECT-TYPE
    SYNTAX     SEQUENCE OF HmStatusVlanPortTableEntry
    MAX-ACCESS not-accessible
    STATUS     current
    DESCRIPTION
            "-- empty --"
    ::= { hmStatusVlan 2 }

-- {ROW} 1.3.6.1.4.1.248.32.18.1.62.2.1
hmStatusVlanPortTableEntry OBJECT-TYPE
    SYNTAX     HmStatusVlanPortTableEntry
    MAX-ACCESS not-accessible
    STATUS     current
    DESCRIPTION
            ""
    INDEX {
            hmStatusVlanPortTableEntryPort
          }
    ::= { hmStatusVlanPortTableTable 1 }

HmStatusVlanPortTableEntry ::= SEQUENCE {
            hmStatusVlanPortTableEntryPort DisplayString,
            hmStatusVlanPortTableEntryAllowAllVlans INTEGER,
            hmStatusVlanPortTableEntryPortVlanId Integer32,
            hmStatusVlanPortTableEntryTaggingMode INTEGER
    }

-- {COLUMN} 1.3.6.1.4.1.248.32.18.1.62.2.1.1
hmStatusVlanPortTableEntryPort OBJECT-TYPE
    SYNTAX     DisplayString (SIZE(0..255))
    MAX-ACCESS read-only
    STATUS     current
    DESCRIPTION
            "-- empty --"
    ::= { hmStatusVlanPortTableEntry 1 }

-- {COLUMN} 1.3.6.1.4.1.248.32.18.1.62.2.1.4
hmStatusVlanPortTableEntryAllowAllVlans OBJECT-TYPE
    SYNTAX     INTEGER {
                  eNo (0),
                  eYes (1)
            }
    MAX-ACCESS read-only
    STATUS     current
    DESCRIPTION
            "-- empty --"
    ::= { hmStatusVlanPortTableEntry 4 }

-- {COLUMN} 1.3.6.1.4.1.248.32.18.1.62.2.1.5
hmStatusVlanPortTableEntryPortVlanId OBJECT-TYPE
    SYNTAX     Integer32 (0..65535)
    MAX-ACCESS read-only
    STATUS     current
    DESCRIPTION
            "-- empty --"
    ::= { hmStatusVlanPortTableEntry 5 }

-- {COLUMN} 1.3.6.1.4.1.248.32.18.1.62.2.1.6
hmStatusVlanPortTableEntryTaggingMode OBJECT-TYPE
    SYNTAX     INTEGER {
                  eIngressMixed (0),
                  eNever (1),
                  eMixed (2),
                  eAlways (3)
            }
    MAX-ACCESS read-only
    STATUS     current
    DESCRIPTION
            "-- empty --"
    ::= { hmStatusVlanPortTableEntry 6 }

-- {SCALAR} 1.3.6.1.4.1.248.32.18.1.62.4
hmStatusVlanOperating OBJECT-TYPE
    SYNTAX     INTEGER {
                  eNo (0),
                  eYes (1)
            }
    MAX-ACCESS read-only
    STATUS     current
    DESCRIPTION
            "-- empty --"
    ::= { hmStatusVlan 4 }

-- {NODE} 1.3.6.1.4.1.248.32.18.1.66
hmStatusHidiscovery OBJECT IDENTIFIER ::= { hmStatus 66 }

-- {SCALAR} 1.3.6.1.4.1.248.32.18.1.66.1
hmStatusHidiscoveryRxUnicastPackets OBJECT-TYPE
    SYNTAX     Integer32 (0..2147483647)
    MAX-ACCESS read-only
    STATUS     current
    DESCRIPTION
            "-- empty --"
    ::= { hmStatusHidiscovery 1 }

-- {SCALAR} 1.3.6.1.4.1.248.32.18.1.66.2
hmStatusHidiscoveryRxMulticastPackets OBJECT-TYPE
    SYNTAX     Integer32 (0..2147483647)
    MAX-ACCESS read-only
    STATUS     current
    DESCRIPTION
            "-- empty --"
    ::= { hmStatusHidiscovery 2 }

-- {SCALAR} 1.3.6.1.4.1.248.32.18.1.66.3
hmStatusHidiscoveryTxPackets OBJECT-TYPE
    SYNTAX     Integer32 (0..2147483647)
    MAX-ACCESS read-only
    STATUS     current
    DESCRIPTION
            "-- empty --"
    ::= { hmStatusHidiscovery 3 }

-- {SCALAR} 1.3.6.1.4.1.248.32.18.1.66.99
hmStatusHidiscoveryDeleteValues OBJECT-TYPE
    SYNTAX     DisplayString
    MAX-ACCESS read-write
    STATUS     current
    DESCRIPTION
            "-- empty --"
    ::= { hmStatusHidiscovery 99 }

-- {NODE} 1.3.6.1.4.1.248.32.18.1.67
hmStatusComPorts OBJECT IDENTIFIER ::= { hmStatus 67 }

-- {TABLE} 1.3.6.1.4.1.248.32.18.1.67.1
hmStatusComPortsDevTable OBJECT-TYPE
    SYNTAX     SEQUENCE OF HmStatusComPortsDevEntry
    MAX-ACCESS not-accessible
    STATUS     current
    DESCRIPTION
            ""
    ::= { hmStatusComPorts 1 }

-- {ROW} 1.3.6.1.4.1.248.32.18.1.67.1.1
hmStatusComPortsDevEntry OBJECT-TYPE
    SYNTAX     HmStatusComPortsDevEntry
    MAX-ACCESS not-accessible
    STATUS     current
    DESCRIPTION
            ""
    INDEX {
            hmStatusComPortsDevEntryIndex
          }
    ::= { hmStatusComPortsDevTable 1 }

HmStatusComPortsDevEntry ::= SEQUENCE {
            hmStatusComPortsDevEntryIndex Integer32,
            hmStatusComPortsDevEntryDeviceType INTEGER,
            hmStatusComPortsDevEntryBus INTEGER,
            hmStatusComPortsDevEntryDevice Integer32,
            hmStatusComPortsDevEntryVendor Integer32,
            hmStatusComPortsDevEntryUsbDriver INTEGER,
            hmStatusComPortsDevEntryState INTEGER,
            hmStatusComPortsDevEntryFirmwareVersion DisplayString,
            hmStatusComPortsDevEntryServ INTEGER,
            hmStatusComPortsDevEntryFullName DisplayString
    }

-- {COLUMN} 1.3.6.1.4.1.248.32.18.1.67.1.1.1
hmStatusComPortsDevEntryIndex OBJECT-TYPE
    SYNTAX     Integer32 (0..2147483647)
    MAX-ACCESS read-only
    STATUS     current
    DESCRIPTION
            "-- empty --"
    ::= { hmStatusComPortsDevEntry 1 }

-- {COLUMN} 1.3.6.1.4.1.248.32.18.1.67.1.1.2
hmStatusComPortsDevEntryDeviceType OBJECT-TYPE
    SYNTAX     INTEGER {
                  eOutband (1),
                  eOutbandModem (2),
                  eOptionIcon (17),
                  eHuaweiE612E630E1750 (21),
                  e4gSystemsUxs1 (23),
                  eNovatelMerlinMc950d (26),
                  eSierraAircard875u (30),
                  eHuaweiE172E220E870 (31),
                  eBelkinF5u103 (33),
                  eProlific2303 (34),
                  eFtdi8u232am (35),
                  eSierraCompass885 (39),
                  eSierraAircard501 (46),
                  eHuaweiK4505 (49),
                  eHuaweiK3765 (51),
                  eSierraDirectIp (53),
                  eHuaweiE182 (54),
                  eHuaweiE1750 (57),
                  eNokiaCs19 (59),
                  eHuaweiE398 (60),
                  eHuaweiE1550 (61),
                  eHuaweiE352 (64)
            }
    MAX-ACCESS read-only
    STATUS     current
    DESCRIPTION
            "-- empty --"
    ::= { hmStatusComPortsDevEntry 2 }

-- {COLUMN} 1.3.6.1.4.1.248.32.18.1.67.1.1.3
hmStatusComPortsDevEntryBus OBJECT-TYPE
    SYNTAX     INTEGER {
                  eOutband (1),
                  eCardbus (2),
                  eUsb (3),
                  eVirtual (4)
            }
    MAX-ACCESS read-only
    STATUS     current
    DESCRIPTION
            "-- empty --"
    ::= { hmStatusComPortsDevEntry 3 }

-- {COLUMN} 1.3.6.1.4.1.248.32.18.1.67.1.1.4
hmStatusComPortsDevEntryDevice OBJECT-TYPE
    SYNTAX     Integer32 (0..65535)
    MAX-ACCESS read-only
    STATUS     current
    DESCRIPTION
            "-- empty --"
    ::= { hmStatusComPortsDevEntry 4 }

-- {COLUMN} 1.3.6.1.4.1.248.32.18.1.67.1.1.5
hmStatusComPortsDevEntryVendor OBJECT-TYPE
    SYNTAX     Integer32 (0..65535)
    MAX-ACCESS read-only
    STATUS     current
    DESCRIPTION
            "-- empty --"
    ::= { hmStatusComPortsDevEntry 5 }

-- {COLUMN} 1.3.6.1.4.1.248.32.18.1.67.1.1.11
hmStatusComPortsDevEntryUsbDriver OBJECT-TYPE
    SYNTAX     INTEGER {
                  eNone (0),
                  eUbsa (1),
                  eUchcom (2),
                  eUftdi (3),
                  eUgensa (4),
                  eUhmodem (5),
                  eUkyopon (6),
                  eUplcom (7),
                  eUslsa (8),
                  eUcdcacm (10)
            }
    MAX-ACCESS read-only
    STATUS     current
    DESCRIPTION
            "-- empty --"
    ::= { hmStatusComPortsDevEntry 11 }

-- {COLUMN} 1.3.6.1.4.1.248.32.18.1.67.1.1.13
hmStatusComPortsDevEntryState OBJECT-TYPE
    SYNTAX     INTEGER {
                  eUnknown (0),
                  eInitialize (1),
                  eWaitForFirmware (2),
                  eReady (3),
                  eInUse (4),
                  eExclusive (5),
                  eInitialize2 (6),
                  eResetting (7)
            }
    MAX-ACCESS read-only
    STATUS     current
    DESCRIPTION
            "-- empty --"
    ::= { hmStatusComPortsDevEntry 13 }

-- {COLUMN} 1.3.6.1.4.1.248.32.18.1.67.1.1.14
hmStatusComPortsDevEntryFirmwareVersion OBJECT-TYPE
    SYNTAX     DisplayString (SIZE(0..63))
    MAX-ACCESS read-only
    STATUS     current
    DESCRIPTION
            "-- empty --"
    ::= { hmStatusComPortsDevEntry 14 }

-- {COLUMN} 1.3.6.1.4.1.248.32.18.1.67.1.1.15
hmStatusComPortsDevEntryServ OBJECT-TYPE
    SYNTAX     INTEGER {
                  eWan (1),
                  eCOMPortServ (2)
            }
    MAX-ACCESS read-only
    STATUS     current
    DESCRIPTION
            ""
    ::= { hmStatusComPortsDevEntry 15 }

-- {COLUMN} 1.3.6.1.4.1.248.32.18.1.67.1.1.99
hmStatusComPortsDevEntryFullName OBJECT-TYPE
    SYNTAX     DisplayString (SIZE(0..31))
    MAX-ACCESS read-only
    STATUS     current
    DESCRIPTION
            "-- empty --"
    ::= { hmStatusComPortsDevEntry 99 }

-- {NODE} 1.3.6.1.4.1.248.32.18.1.67.2
hmStatusComPortsComPortServer OBJECT IDENTIFIER ::= { hmStatusComPorts 2 }

-- {TABLE} 1.3.6.1.4.1.248.32.18.1.67.2.1
hmStatusComPortsComPortServerNetworkStatusTable OBJECT-TYPE
    SYNTAX     SEQUENCE OF HmStatusComPortsComPortServerNetworkStatusEntry
    MAX-ACCESS not-accessible
    STATUS     current
    DESCRIPTION
            "-- empty --"
    ::= { hmStatusComPortsComPortServer 1 }

-- {ROW} 1.3.6.1.4.1.248.32.18.1.67.2.1.1
hmStatusComPortsComPortServerNetworkStatusEntry OBJECT-TYPE
    SYNTAX     HmStatusComPortsComPortServerNetworkStatusEntry
    MAX-ACCESS not-accessible
    STATUS     current
    DESCRIPTION
            ""
    INDEX {
            hmStatusComPortsComPortServerNetworkStatusEntryDeviceType,
            hmStatusComPortsComPortServerNetworkStatusEntryPortNumber
          }
    ::= { hmStatusComPortsComPortServerNetworkStatusTable 1 }

HmStatusComPortsComPortServerNetworkStatusEntry ::= SEQUENCE {
            hmStatusComPortsComPortServerNetworkStatusEntryDeviceType INTEGER,
            hmStatusComPortsComPortServerNetworkStatusEntryPortNumber Integer32,
            hmStatusComPortsComPortServerNetworkStatusEntryConnectionStatus INTEGER,
            hmStatusComPortsComPortServerNetworkStatusEntryLastError INTEGER,
            hmStatusComPortsComPortServerNetworkStatusEntryRemoteAddress IpAddress,
            hmStatusComPortsComPortServerNetworkStatusEntryLocalPort Integer32,
            hmStatusComPortsComPortServerNetworkStatusEntryRemotePort Integer32,
            hmStatusComPortsComPortServerNetworkStatusEntryRemoteIpv6Addr IpAddress,
            hmStatusComPortsComPortServerNetworkStatusEntryFullName DisplayString
    }

-- {COLUMN} 1.3.6.1.4.1.248.32.18.1.67.2.1.1.1
hmStatusComPortsComPortServerNetworkStatusEntryDeviceType OBJECT-TYPE
    SYNTAX     INTEGER {
                  eOutband (1),
                  eBelkinF5u103 (33),
                  eProlific2303 (34),
                  eFtdi8u232am (35)
            }
    MAX-ACCESS read-only
    STATUS     current
    DESCRIPTION
            "-- empty --"
    ::= { hmStatusComPortsComPortServerNetworkStatusEntry 1 }

-- {COLUMN} 1.3.6.1.4.1.248.32.18.1.67.2.1.1.2
hmStatusComPortsComPortServerNetworkStatusEntryPortNumber OBJECT-TYPE
    SYNTAX     Integer32 (0..255)
    MAX-ACCESS read-only
    STATUS     current
    DESCRIPTION
            "-- empty --"
    ::= { hmStatusComPortsComPortServerNetworkStatusEntry 2 }

-- {COLUMN} 1.3.6.1.4.1.248.32.18.1.67.2.1.1.4
hmStatusComPortsComPortServerNetworkStatusEntryConnectionStatus OBJECT-TYPE
    SYNTAX     INTEGER {
                  eIdle (0),
                  eListening (1),
                  eConnecting (2),
                  eConnected (3),
                  eNotListening (4),
                  eConErrBackoff (5)
            }
    MAX-ACCESS read-only
    STATUS     current
    DESCRIPTION
            "-- empty --"
    ::= { hmStatusComPortsComPortServerNetworkStatusEntry 4 }

-- {COLUMN} 1.3.6.1.4.1.248.32.18.1.67.2.1.1.5
hmStatusComPortsComPortServerNetworkStatusEntryLastError OBJECT-TYPE
    SYNTAX     INTEGER {
                  eNone (0),
                  eDnsError (1),
                  eTCPConnErr (2),
                  eRemDisc (3)
            }
    MAX-ACCESS read-only
    STATUS     current
    DESCRIPTION
            "-- empty --"
    ::= { hmStatusComPortsComPortServerNetworkStatusEntry 5 }

-- {COLUMN} 1.3.6.1.4.1.248.32.18.1.67.2.1.1.6
hmStatusComPortsComPortServerNetworkStatusEntryRemoteAddress OBJECT-TYPE
    SYNTAX     IpAddress
    MAX-ACCESS read-only
    STATUS     current
    DESCRIPTION
            "-- empty --"
    ::= { hmStatusComPortsComPortServerNetworkStatusEntry 6 }

-- {COLUMN} 1.3.6.1.4.1.248.32.18.1.67.2.1.1.7
hmStatusComPortsComPortServerNetworkStatusEntryLocalPort OBJECT-TYPE
    SYNTAX     Integer32 (0..65535)
    MAX-ACCESS read-only
    STATUS     current
    DESCRIPTION
            "-- empty --"
    ::= { hmStatusComPortsComPortServerNetworkStatusEntry 7 }

-- {COLUMN} 1.3.6.1.4.1.248.32.18.1.67.2.1.1.8
hmStatusComPortsComPortServerNetworkStatusEntryRemotePort OBJECT-TYPE
    SYNTAX     Integer32 (0..65535)
    MAX-ACCESS read-only
    STATUS     current
    DESCRIPTION
            "-- empty --"
    ::= { hmStatusComPortsComPortServerNetworkStatusEntry 8 }

-- {COLUMN} 1.3.6.1.4.1.248.32.18.1.67.2.1.1.10
hmStatusComPortsComPortServerNetworkStatusEntryRemoteIpv6Addr OBJECT-TYPE
    SYNTAX     IpAddress
    MAX-ACCESS read-only
    STATUS     current
    DESCRIPTION
            ""
    ::= { hmStatusComPortsComPortServerNetworkStatusEntry 10 }

-- {COLUMN} 1.3.6.1.4.1.248.32.18.1.67.2.1.1.99
hmStatusComPortsComPortServerNetworkStatusEntryFullName OBJECT-TYPE
    SYNTAX     DisplayString (SIZE(0..255))
    MAX-ACCESS read-only
    STATUS     current
    DESCRIPTION
            "-- empty --"
    ::= { hmStatusComPortsComPortServerNetworkStatusEntry 99 }

-- {TABLE} 1.3.6.1.4.1.248.32.18.1.67.2.2
hmStatusComPortsComPortServerComPortStatusTable OBJECT-TYPE
    SYNTAX     SEQUENCE OF HmStatusComPortsComPortServerComPortStatusEntry
    MAX-ACCESS not-accessible
    STATUS     current
    DESCRIPTION
            "-- empty --"
    ::= { hmStatusComPortsComPortServer 2 }

-- {ROW} 1.3.6.1.4.1.248.32.18.1.67.2.2.1
hmStatusComPortsComPortServerComPortStatusEntry OBJECT-TYPE
    SYNTAX     HmStatusComPortsComPortServerComPortStatusEntry
    MAX-ACCESS not-accessible
    STATUS     current
    DESCRIPTION
            ""
    INDEX {
            hmStatusComPortsComPortServerComPortStatusEntryDeviceType,
            hmStatusComPortsComPortServerComPortStatusEntryPortNumber
          }
    ::= { hmStatusComPortsComPortServerComPortStatusTable 1 }

HmStatusComPortsComPortServerComPortStatusEntry ::= SEQUENCE {
            hmStatusComPortsComPortServerComPortStatusEntryDeviceType INTEGER,
            hmStatusComPortsComPortServerComPortStatusEntryPortNumber Integer32,
            hmStatusComPortsComPortServerComPortStatusEntryInterfaceStatus INTEGER,
            hmStatusComPortsComPortServerComPortStatusEntryBitRate INTEGER,
            hmStatusComPortsComPortServerComPortStatusEntryDataBits INTEGER,
            hmStatusComPortsComPortServerComPortStatusEntryParity INTEGER,
            hmStatusComPortsComPortServerComPortStatusEntryStopBits INTEGER,
            hmStatusComPortsComPortServerComPortStatusEntryHandshake INTEGER,
            hmStatusComPortsComPortServerComPortStatusEntryFullName DisplayString
    }

-- {COLUMN} 1.3.6.1.4.1.248.32.18.1.67.2.2.1.1
hmStatusComPortsComPortServerComPortStatusEntryDeviceType OBJECT-TYPE
    SYNTAX     INTEGER {
                  eOutband (1),
                  eBelkinF5u103 (33),
                  eProlific2303 (34),
                  eFtdi8u232am (35)
            }
    MAX-ACCESS read-only
    STATUS     current
    DESCRIPTION
            "-- empty --"
    ::= { hmStatusComPortsComPortServerComPortStatusEntry 1 }

-- {COLUMN} 1.3.6.1.4.1.248.32.18.1.67.2.2.1.2
hmStatusComPortsComPortServerComPortStatusEntryPortNumber OBJECT-TYPE
    SYNTAX     Integer32 (0..255)
    MAX-ACCESS read-only
    STATUS     current
    DESCRIPTION
            "-- empty --"
    ::= { hmStatusComPortsComPortServerComPortStatusEntry 2 }

-- {COLUMN} 1.3.6.1.4.1.248.32.18.1.67.2.2.1.4
hmStatusComPortsComPortServerComPortStatusEntryInterfaceStatus OBJECT-TYPE
    SYNTAX     INTEGER {
                  eNotPresent (0),
                  eNotReady (1),
                  eReady (2)
            }
    MAX-ACCESS read-only
    STATUS     current
    DESCRIPTION
            "-- empty --"
    ::= { hmStatusComPortsComPortServerComPortStatusEntry 4 }

-- {COLUMN} 1.3.6.1.4.1.248.32.18.1.67.2.2.1.5
hmStatusComPortsComPortServerComPortStatusEntryBitRate OBJECT-TYPE
    SYNTAX     INTEGER {
                  e110 (110),
                  e300 (300),
                  e600 (600),
                  e1200 (1200),
                  e2400 (2400),
                  e4800 (4800),
                  e9600 (9600),
                  e19200 (19200),
                  e38400 (38400),
                  e57600 (57600),
                  e115200 (115200),
                  e125000 (125000),
                  e230400 (230400)
            }
    MAX-ACCESS read-only
    STATUS     current
    DESCRIPTION
            "-- empty --"
    ::= { hmStatusComPortsComPortServerComPortStatusEntry 5 }

-- {COLUMN} 1.3.6.1.4.1.248.32.18.1.67.2.2.1.6
hmStatusComPortsComPortServerComPortStatusEntryDataBits OBJECT-TYPE
    SYNTAX     INTEGER {
                  e7 (7),
                  e8 (8)
            }
    MAX-ACCESS read-only
    STATUS     current
    DESCRIPTION
            "-- empty --"
    ::= { hmStatusComPortsComPortServerComPortStatusEntry 6 }

-- {COLUMN} 1.3.6.1.4.1.248.32.18.1.67.2.2.1.7
hmStatusComPortsComPortServerComPortStatusEntryParity OBJECT-TYPE
    SYNTAX     INTEGER {
                  eNone (1),
                  eOdd (2),
                  eEven (3)
            }
    MAX-ACCESS read-only
    STATUS     current
    DESCRIPTION
            "-- empty --"
    ::= { hmStatusComPortsComPortServerComPortStatusEntry 7 }

-- {COLUMN} 1.3.6.1.4.1.248.32.18.1.67.2.2.1.8
hmStatusComPortsComPortServerComPortStatusEntryStopBits OBJECT-TYPE
    SYNTAX     INTEGER {
                  e1 (1),
                  e2 (2)
            }
    MAX-ACCESS read-only
    STATUS     current
    DESCRIPTION
            "-- empty --"
    ::= { hmStatusComPortsComPortServerComPortStatusEntry 8 }

-- {COLUMN} 1.3.6.1.4.1.248.32.18.1.67.2.2.1.9
hmStatusComPortsComPortServerComPortStatusEntryHandshake OBJECT-TYPE
    SYNTAX     INTEGER {
                  eNone (0),
                  eRtsCts (1)
            }
    MAX-ACCESS read-only
    STATUS     current
    DESCRIPTION
            "-- empty --"
    ::= { hmStatusComPortsComPortServerComPortStatusEntry 9 }

-- {COLUMN} 1.3.6.1.4.1.248.32.18.1.67.2.2.1.99
hmStatusComPortsComPortServerComPortStatusEntryFullName OBJECT-TYPE
    SYNTAX     DisplayString (SIZE(0..255))
    MAX-ACCESS read-only
    STATUS     current
    DESCRIPTION
            "-- empty --"
    ::= { hmStatusComPortsComPortServerComPortStatusEntry 99 }

-- {TABLE} 1.3.6.1.4.1.248.32.18.1.67.2.3
hmStatusComPortsComPortServerByteCountersTable OBJECT-TYPE
    SYNTAX     SEQUENCE OF HmStatusComPortsComPortServerByteCountersEntry
    MAX-ACCESS not-accessible
    STATUS     current
    DESCRIPTION
            "-- empty --"
    ::= { hmStatusComPortsComPortServer 3 }

-- {ROW} 1.3.6.1.4.1.248.32.18.1.67.2.3.1
hmStatusComPortsComPortServerByteCountersEntry OBJECT-TYPE
    SYNTAX     HmStatusComPortsComPortServerByteCountersEntry
    MAX-ACCESS not-accessible
    STATUS     current
    DESCRIPTION
            ""
    INDEX {
            hmStatusComPortsComPortServerByteCountersEntryDeviceType,
            hmStatusComPortsComPortServerByteCountersEntryPortNumber
          }
    ::= { hmStatusComPortsComPortServerByteCountersTable 1 }

HmStatusComPortsComPortServerByteCountersEntry ::= SEQUENCE {
            hmStatusComPortsComPortServerByteCountersEntryDeviceType INTEGER,
            hmStatusComPortsComPortServerByteCountersEntryPortNumber Integer32,
            hmStatusComPortsComPortServerByteCountersEntrySerialTx Integer32,
            hmStatusComPortsComPortServerByteCountersEntrySerialRx Integer32,
            hmStatusComPortsComPortServerByteCountersEntryNetworkTx Integer32,
            hmStatusComPortsComPortServerByteCountersEntryNetworkRx Integer32,
            hmStatusComPortsComPortServerByteCountersEntryFullName DisplayString
    }

-- {COLUMN} 1.3.6.1.4.1.248.32.18.1.67.2.3.1.1
hmStatusComPortsComPortServerByteCountersEntryDeviceType OBJECT-TYPE
    SYNTAX     INTEGER {
                  eOutband (1),
                  eBelkinF5u103 (33),
                  eProlific2303 (34),
                  eFtdi8u232am (35)
            }
    MAX-ACCESS read-only
    STATUS     current
    DESCRIPTION
            "-- empty --"
    ::= { hmStatusComPortsComPortServerByteCountersEntry 1 }

-- {COLUMN} 1.3.6.1.4.1.248.32.18.1.67.2.3.1.2
hmStatusComPortsComPortServerByteCountersEntryPortNumber OBJECT-TYPE
    SYNTAX     Integer32 (0..255)
    MAX-ACCESS read-only
    STATUS     current
    DESCRIPTION
            "-- empty --"
    ::= { hmStatusComPortsComPortServerByteCountersEntry 2 }

-- {COLUMN} 1.3.6.1.4.1.248.32.18.1.67.2.3.1.4
hmStatusComPortsComPortServerByteCountersEntrySerialTx OBJECT-TYPE
    SYNTAX     Integer32 (0..2147483647)
    MAX-ACCESS read-only
    STATUS     current
    DESCRIPTION
            "-- empty --"
    ::= { hmStatusComPortsComPortServerByteCountersEntry 4 }

-- {COLUMN} 1.3.6.1.4.1.248.32.18.1.67.2.3.1.5
hmStatusComPortsComPortServerByteCountersEntrySerialRx OBJECT-TYPE
    SYNTAX     Integer32 (0..2147483647)
    MAX-ACCESS read-only
    STATUS     current
    DESCRIPTION
            "-- empty --"
    ::= { hmStatusComPortsComPortServerByteCountersEntry 5 }

-- {COLUMN} 1.3.6.1.4.1.248.32.18.1.67.2.3.1.6
hmStatusComPortsComPortServerByteCountersEntryNetworkTx OBJECT-TYPE
    SYNTAX     Integer32 (0..2147483647)
    MAX-ACCESS read-only
    STATUS     current
    DESCRIPTION
            "-- empty --"
    ::= { hmStatusComPortsComPortServerByteCountersEntry 6 }

-- {COLUMN} 1.3.6.1.4.1.248.32.18.1.67.2.3.1.7
hmStatusComPortsComPortServerByteCountersEntryNetworkRx OBJECT-TYPE
    SYNTAX     Integer32 (0..2147483647)
    MAX-ACCESS read-only
    STATUS     current
    DESCRIPTION
            "-- empty --"
    ::= { hmStatusComPortsComPortServerByteCountersEntry 7 }

-- {COLUMN} 1.3.6.1.4.1.248.32.18.1.67.2.3.1.99
hmStatusComPortsComPortServerByteCountersEntryFullName OBJECT-TYPE
    SYNTAX     DisplayString (SIZE(0..255))
    MAX-ACCESS read-only
    STATUS     current
    DESCRIPTION
            "-- empty --"
    ::= { hmStatusComPortsComPortServerByteCountersEntry 99 }

-- {TABLE} 1.3.6.1.4.1.248.32.18.1.67.2.4
hmStatusComPortsComPortServerComPortErrorsTable OBJECT-TYPE
    SYNTAX     SEQUENCE OF HmStatusComPortsComPortServerComPortErrorsEntry
    MAX-ACCESS not-accessible
    STATUS     current
    DESCRIPTION
            "-- empty --"
    ::= { hmStatusComPortsComPortServer 4 }

-- {ROW} 1.3.6.1.4.1.248.32.18.1.67.2.4.1
hmStatusComPortsComPortServerComPortErrorsEntry OBJECT-TYPE
    SYNTAX     HmStatusComPortsComPortServerComPortErrorsEntry
    MAX-ACCESS not-accessible
    STATUS     current
    DESCRIPTION
            ""
    INDEX {
            hmStatusComPortsComPortServerComPortErrorsEntryDeviceType,
            hmStatusComPortsComPortServerComPortErrorsEntryPortNumber
          }
    ::= { hmStatusComPortsComPortServerComPortErrorsTable 1 }

HmStatusComPortsComPortServerComPortErrorsEntry ::= SEQUENCE {
            hmStatusComPortsComPortServerComPortErrorsEntryDeviceType INTEGER,
            hmStatusComPortsComPortServerComPortErrorsEntryPortNumber Integer32,
            hmStatusComPortsComPortServerComPortErrorsEntryParityErrors Integer32,
            hmStatusComPortsComPortServerComPortErrorsEntryFramingErrors Integer32,
            hmStatusComPortsComPortServerComPortErrorsEntryRxLostErrors Integer32,
            hmStatusComPortsComPortServerComPortErrorsEntryFullName DisplayString
    }

-- {COLUMN} 1.3.6.1.4.1.248.32.18.1.67.2.4.1.1
hmStatusComPortsComPortServerComPortErrorsEntryDeviceType OBJECT-TYPE
    SYNTAX     INTEGER {
                  eOutband (1),
                  eBelkinF5u103 (33),
                  eProlific2303 (34),
                  eFtdi8u232am (35)
            }
    MAX-ACCESS read-only
    STATUS     current
    DESCRIPTION
            "-- empty --"
    ::= { hmStatusComPortsComPortServerComPortErrorsEntry 1 }

-- {COLUMN} 1.3.6.1.4.1.248.32.18.1.67.2.4.1.2
hmStatusComPortsComPortServerComPortErrorsEntryPortNumber OBJECT-TYPE
    SYNTAX     Integer32 (0..255)
    MAX-ACCESS read-only
    STATUS     current
    DESCRIPTION
            "-- empty --"
    ::= { hmStatusComPortsComPortServerComPortErrorsEntry 2 }

-- {COLUMN} 1.3.6.1.4.1.248.32.18.1.67.2.4.1.4
hmStatusComPortsComPortServerComPortErrorsEntryParityErrors OBJECT-TYPE
    SYNTAX     Integer32 (0..2147483647)
    MAX-ACCESS read-only
    STATUS     current
    DESCRIPTION
            "-- empty --"
    ::= { hmStatusComPortsComPortServerComPortErrorsEntry 4 }

-- {COLUMN} 1.3.6.1.4.1.248.32.18.1.67.2.4.1.5
hmStatusComPortsComPortServerComPortErrorsEntryFramingErrors OBJECT-TYPE
    SYNTAX     Integer32 (0..2147483647)
    MAX-ACCESS read-only
    STATUS     current
    DESCRIPTION
            "-- empty --"
    ::= { hmStatusComPortsComPortServerComPortErrorsEntry 5 }

-- {COLUMN} 1.3.6.1.4.1.248.32.18.1.67.2.4.1.6
hmStatusComPortsComPortServerComPortErrorsEntryRxLostErrors OBJECT-TYPE
    SYNTAX     Integer32 (0..2147483647)
    MAX-ACCESS read-only
    STATUS     current
    DESCRIPTION
            "-- empty --"
    ::= { hmStatusComPortsComPortServerComPortErrorsEntry 6 }

-- {COLUMN} 1.3.6.1.4.1.248.32.18.1.67.2.4.1.99
hmStatusComPortsComPortServerComPortErrorsEntryFullName OBJECT-TYPE
    SYNTAX     DisplayString (SIZE(0..255))
    MAX-ACCESS read-only
    STATUS     current
    DESCRIPTION
            "-- empty --"
    ::= { hmStatusComPortsComPortServerComPortErrorsEntry 99 }

-- {TABLE} 1.3.6.1.4.1.248.32.18.1.67.2.5
hmStatusComPortsComPortServerConnTable OBJECT-TYPE
    SYNTAX     SEQUENCE OF HmStatusComPortsComPortServerConnEntry
    MAX-ACCESS not-accessible
    STATUS     current
    DESCRIPTION
            ""
    ::= { hmStatusComPortsComPortServer 5 }

-- {ROW} 1.3.6.1.4.1.248.32.18.1.67.2.5.1
hmStatusComPortsComPortServerConnEntry OBJECT-TYPE
    SYNTAX     HmStatusComPortsComPortServerConnEntry
    MAX-ACCESS not-accessible
    STATUS     current
    DESCRIPTION
            ""
    INDEX {
            hmStatusComPortsComPortServerConnEntryDeviceType,
            hmStatusComPortsComPortServerConnEntryPortNumber
          }
    ::= { hmStatusComPortsComPortServerConnTable 1 }

HmStatusComPortsComPortServerConnEntry ::= SEQUENCE {
            hmStatusComPortsComPortServerConnEntryDeviceType INTEGER,
            hmStatusComPortsComPortServerConnEntryPortNumber Integer32,
            hmStatusComPortsComPortServerConnEntryServGrant Integer32,
            hmStatusComPortsComPortServerConnEntryServRej Integer32,
            hmStatusComPortsComPortServerConnEntryClntSucc Integer32,
            hmStatusComPortsComPortServerConnEntryClntDnsErr Integer32,
            hmStatusComPortsComPortServerConnEntryClntTcpErr Integer32,
            hmStatusComPortsComPortServerConnEntryClntRemDisc Integer32,
            hmStatusComPortsComPortServerConnEntryFullName DisplayString
    }

-- {COLUMN} 1.3.6.1.4.1.248.32.18.1.67.2.5.1.1
hmStatusComPortsComPortServerConnEntryDeviceType OBJECT-TYPE
    SYNTAX     INTEGER {
                  eOutband (1),
                  eBelkinF5u103 (33),
                  eProlific2303 (34),
                  eFtdi8u232am (35)
            }
    MAX-ACCESS read-only
    STATUS     current
    DESCRIPTION
            "-- empty --"
    ::= { hmStatusComPortsComPortServerConnEntry 1 }

-- {COLUMN} 1.3.6.1.4.1.248.32.18.1.67.2.5.1.2
hmStatusComPortsComPortServerConnEntryPortNumber OBJECT-TYPE
    SYNTAX     Integer32 (0..255)
    MAX-ACCESS read-only
    STATUS     current
    DESCRIPTION
            "-- empty --"
    ::= { hmStatusComPortsComPortServerConnEntry 2 }

-- {COLUMN} 1.3.6.1.4.1.248.32.18.1.67.2.5.1.4
hmStatusComPortsComPortServerConnEntryServGrant OBJECT-TYPE
    SYNTAX     Integer32 (0..2147483647)
    MAX-ACCESS read-only
    STATUS     current
    DESCRIPTION
            ""
    ::= { hmStatusComPortsComPortServerConnEntry 4 }

-- {COLUMN} 1.3.6.1.4.1.248.32.18.1.67.2.5.1.5
hmStatusComPortsComPortServerConnEntryServRej OBJECT-TYPE
    SYNTAX     Integer32 (0..2147483647)
    MAX-ACCESS read-only
    STATUS     current
    DESCRIPTION
            ""
    ::= { hmStatusComPortsComPortServerConnEntry 5 }

-- {COLUMN} 1.3.6.1.4.1.248.32.18.1.67.2.5.1.6
hmStatusComPortsComPortServerConnEntryClntSucc OBJECT-TYPE
    SYNTAX     Integer32 (0..2147483647)
    MAX-ACCESS read-only
    STATUS     current
    DESCRIPTION
            ""
    ::= { hmStatusComPortsComPortServerConnEntry 6 }

-- {COLUMN} 1.3.6.1.4.1.248.32.18.1.67.2.5.1.7
hmStatusComPortsComPortServerConnEntryClntDnsErr OBJECT-TYPE
    SYNTAX     Integer32 (0..2147483647)
    MAX-ACCESS read-only
    STATUS     current
    DESCRIPTION
            ""
    ::= { hmStatusComPortsComPortServerConnEntry 7 }

-- {COLUMN} 1.3.6.1.4.1.248.32.18.1.67.2.5.1.8
hmStatusComPortsComPortServerConnEntryClntTcpErr OBJECT-TYPE
    SYNTAX     Integer32 (0..2147483647)
    MAX-ACCESS read-only
    STATUS     current
    DESCRIPTION
            ""
    ::= { hmStatusComPortsComPortServerConnEntry 8 }

-- {COLUMN} 1.3.6.1.4.1.248.32.18.1.67.2.5.1.9
hmStatusComPortsComPortServerConnEntryClntRemDisc OBJECT-TYPE
    SYNTAX     Integer32 (0..2147483647)
    MAX-ACCESS read-only
    STATUS     current
    DESCRIPTION
            ""
    ::= { hmStatusComPortsComPortServerConnEntry 9 }

-- {COLUMN} 1.3.6.1.4.1.248.32.18.1.67.2.5.1.99
hmStatusComPortsComPortServerConnEntryFullName OBJECT-TYPE
    SYNTAX     DisplayString (SIZE(0..255))
    MAX-ACCESS read-only
    STATUS     current
    DESCRIPTION
            "-- empty --"
    ::= { hmStatusComPortsComPortServerConnEntry 99 }

-- {SCALAR} 1.3.6.1.4.1.248.32.18.1.67.2.99
hmStatusComPortsComPortServerDeleteValues OBJECT-TYPE
    SYNTAX     DisplayString
    MAX-ACCESS read-write
    STATUS     current
    DESCRIPTION
            "-- empty --"
    ::= { hmStatusComPortsComPortServer 99 }

-- {NODE} 1.3.6.1.4.1.248.32.18.1.68
hmStatusBlockDevices OBJECT IDENTIFIER ::= { hmStatus 68 }

-- {TABLE} 1.3.6.1.4.1.248.32.18.1.68.1
hmStatusBlockDevicesDeviceListTable OBJECT-TYPE
    SYNTAX     SEQUENCE OF HmStatusBlockDevicesDeviceListEntry
    MAX-ACCESS not-accessible
    STATUS     current
    DESCRIPTION
            "-- empty --"
    ::= { hmStatusBlockDevices 1 }

-- {ROW} 1.3.6.1.4.1.248.32.18.1.68.1.1
hmStatusBlockDevicesDeviceListEntry OBJECT-TYPE
    SYNTAX     HmStatusBlockDevicesDeviceListEntry
    MAX-ACCESS not-accessible
    STATUS     current
    DESCRIPTION
            ""
    INDEX {
            hmStatusBlockDevicesDeviceListEntryId,
            hmStatusBlockDevicesDeviceListEntryPartition
          }
    ::= { hmStatusBlockDevicesDeviceListTable 1 }

HmStatusBlockDevicesDeviceListEntry ::= SEQUENCE {
            hmStatusBlockDevicesDeviceListEntryId Integer32,
            hmStatusBlockDevicesDeviceListEntryType DisplayString,
            hmStatusBlockDevicesDeviceListEntryBlocksize Integer32,
            hmStatusBlockDevicesDeviceListEntryBlockcount Integer32,
            hmStatusBlockDevicesDeviceListEntryPartition Integer32,
            hmStatusBlockDevicesDeviceListEntryFirstBlock Integer32
    }

-- {COLUMN} 1.3.6.1.4.1.248.32.18.1.68.1.1.1
hmStatusBlockDevicesDeviceListEntryId OBJECT-TYPE
    SYNTAX     Integer32 (0..2147483647)
    MAX-ACCESS read-only
    STATUS     current
    DESCRIPTION
            "-- empty --"
    ::= { hmStatusBlockDevicesDeviceListEntry 1 }

-- {COLUMN} 1.3.6.1.4.1.248.32.18.1.68.1.1.2
hmStatusBlockDevicesDeviceListEntryType OBJECT-TYPE
    SYNTAX     DisplayString (SIZE(0..255))
    MAX-ACCESS read-only
    STATUS     current
    DESCRIPTION
            "-- empty --"
    ::= { hmStatusBlockDevicesDeviceListEntry 2 }

-- {COLUMN} 1.3.6.1.4.1.248.32.18.1.68.1.1.3
hmStatusBlockDevicesDeviceListEntryBlocksize OBJECT-TYPE
    SYNTAX     Integer32 (0..2147483647)
    MAX-ACCESS read-only
    STATUS     current
    DESCRIPTION
            "-- empty --"
    ::= { hmStatusBlockDevicesDeviceListEntry 3 }

-- {COLUMN} 1.3.6.1.4.1.248.32.18.1.68.1.1.4
hmStatusBlockDevicesDeviceListEntryBlockcount OBJECT-TYPE
    SYNTAX     Integer32 (0..2147483647)
    MAX-ACCESS read-only
    STATUS     current
    DESCRIPTION
            "-- empty --"
    ::= { hmStatusBlockDevicesDeviceListEntry 4 }

-- {COLUMN} 1.3.6.1.4.1.248.32.18.1.68.1.1.5
hmStatusBlockDevicesDeviceListEntryPartition OBJECT-TYPE
    SYNTAX     Integer32 (0..2147483647)
    MAX-ACCESS read-only
    STATUS     current
    DESCRIPTION
            "-- empty --"
    ::= { hmStatusBlockDevicesDeviceListEntry 5 }

-- {COLUMN} 1.3.6.1.4.1.248.32.18.1.68.1.1.6
hmStatusBlockDevicesDeviceListEntryFirstBlock OBJECT-TYPE
    SYNTAX     Integer32 (0..2147483647)
    MAX-ACCESS read-only
    STATUS     current
    DESCRIPTION
            "-- empty --"
    ::= { hmStatusBlockDevicesDeviceListEntry 6 }

-- {NODE} 1.3.6.1.4.1.248.32.18.1.69
hmStatusTacacsPlus OBJECT IDENTIFIER ::= { hmStatus 69 }

-- {SCALAR} 1.3.6.1.4.1.248.32.18.1.69.1
hmStatusTacacsPlusAuthenticationErrors OBJECT-TYPE
    SYNTAX     Counter32
    MAX-ACCESS read-only
    STATUS     current
    DESCRIPTION
            "-- empty --"
    ::= { hmStatusTacacsPlus 1 }

-- {SCALAR} 1.3.6.1.4.1.248.32.18.1.69.2
hmStatusTacacsPlusAuthorisationErrors OBJECT-TYPE
    SYNTAX     Counter32
    MAX-ACCESS read-only
    STATUS     current
    DESCRIPTION
            "-- empty --"
    ::= { hmStatusTacacsPlus 2 }

-- {SCALAR} 1.3.6.1.4.1.248.32.18.1.69.3
hmStatusTacacsPlusDeleteValues OBJECT-TYPE
    SYNTAX     DisplayString
    MAX-ACCESS read-write
    STATUS     current
    DESCRIPTION
            "-- empty --"
    ::= { hmStatusTacacsPlus 3 }

-- {NODE} 1.3.6.1.4.1.248.32.18.1.70
hmStatusTemperatureMonitor OBJECT IDENTIFIER ::= { hmStatus 70 }

-- {TABLE} 1.3.6.1.4.1.248.32.18.1.70.1
hmStatusTemperatureMonitorExtremesTable OBJECT-TYPE
    SYNTAX     SEQUENCE OF HmStatusTemperatureMonitorExtremesEntry
    MAX-ACCESS not-accessible
    STATUS     current
    DESCRIPTION
            "-- empty --"
    ::= { hmStatusTemperatureMonitor 1 }

-- {ROW} 1.3.6.1.4.1.248.32.18.1.70.1.1
hmStatusTemperatureMonitorExtremesEntry OBJECT-TYPE
    SYNTAX     HmStatusTemperatureMonitorExtremesEntry
    MAX-ACCESS not-accessible
    STATUS     current
    DESCRIPTION
            ""
    INDEX {
            hmStatusTemperatureMonitorExtremesEntryType
          }
    ::= { hmStatusTemperatureMonitorExtremesTable 1 }

HmStatusTemperatureMonitorExtremesEntry ::= SEQUENCE {
            hmStatusTemperatureMonitorExtremesEntryType INTEGER,
            hmStatusTemperatureMonitorExtremesEntryValue Integer32,
            hmStatusTemperatureMonitorExtremesEntryTime DisplayString
    }

-- {COLUMN} 1.3.6.1.4.1.248.32.18.1.70.1.1.1
hmStatusTemperatureMonitorExtremesEntryType OBJECT-TYPE
    SYNTAX     INTEGER {
                  eMinimum1 (1),
                  eMaximum1 (2),
                  eMinimum2 (257),
                  eMaximum2 (258),
                  eMinimum3 (513),
                  eMaximum3 (514),
                  eMinimum4 (769),
                  eMaximum4 (770),
                  eMinimum5 (1025),
                  eMaximum5 (1026),
                  eMinimum6 (1281),
                  eMaximum6 (1282),
                  eMinimum7 (1537),
                  eMaximum7 (1538),
                  eMinimum8 (1793),
                  eMaximum8 (1794)
            }
    MAX-ACCESS read-only
    STATUS     current
    DESCRIPTION
            "-- empty --"
    ::= { hmStatusTemperatureMonitorExtremesEntry 1 }

-- {COLUMN} 1.3.6.1.4.1.248.32.18.1.70.1.1.2
hmStatusTemperatureMonitorExtremesEntryValue OBJECT-TYPE
    SYNTAX     Integer32 (-32768..32767)
    MAX-ACCESS read-only
    STATUS     current
    DESCRIPTION
            "-- empty --"
    ::= { hmStatusTemperatureMonitorExtremesEntry 2 }

-- {COLUMN} 1.3.6.1.4.1.248.32.18.1.70.1.1.3
hmStatusTemperatureMonitorExtremesEntryTime OBJECT-TYPE
    SYNTAX     DisplayString (SIZE(0..255))
    MAX-ACCESS read-only
    STATUS     current
    DESCRIPTION
            "-- empty --"
    ::= { hmStatusTemperatureMonitorExtremesEntry 3 }

-- {NODE} 1.3.6.1.4.1.248.32.18.1.72
hmStatusDsl OBJECT IDENTIFIER ::= { hmStatus 72 }

-- {TABLE} 1.3.6.1.4.1.248.32.18.1.72.1
hmStatusDslInterfacesTable OBJECT-TYPE
    SYNTAX     SEQUENCE OF HmStatusDslInterfacesEntry
    MAX-ACCESS not-accessible
    STATUS     current
    DESCRIPTION
            "-- empty --"
    ::= { hmStatusDsl 1 }

-- {ROW} 1.3.6.1.4.1.248.32.18.1.72.1.1
hmStatusDslInterfacesEntry OBJECT-TYPE
    SYNTAX     HmStatusDslInterfacesEntry
    MAX-ACCESS not-accessible
    STATUS     current
    DESCRIPTION
            ""
    INDEX {
            hmStatusDslInterfacesEntryIfc
          }
    ::= { hmStatusDslInterfacesTable 1 }

HmStatusDslInterfacesEntry ::= SEQUENCE {
            hmStatusDslInterfacesEntryIfc DisplayString,
            hmStatusDslInterfacesEntryLinkActive INTEGER
    }

-- {COLUMN} 1.3.6.1.4.1.248.32.18.1.72.1.1.1
hmStatusDslInterfacesEntryIfc OBJECT-TYPE
    SYNTAX     DisplayString (SIZE(0..255))
    MAX-ACCESS read-only
    STATUS     current
    DESCRIPTION
            "-- empty --"
    ::= { hmStatusDslInterfacesEntry 1 }

-- {COLUMN} 1.3.6.1.4.1.248.32.18.1.72.1.1.3
hmStatusDslInterfacesEntryLinkActive OBJECT-TYPE
    SYNTAX     INTEGER {
                  eNo (0),
                  eYes (1)
            }
    MAX-ACCESS read-only
    STATUS     current
    DESCRIPTION
            "-- empty --"
    ::= { hmStatusDslInterfacesEntry 3 }

-- {TABLE} 1.3.6.1.4.1.248.32.18.1.72.2
hmStatusDslByteTransportTable OBJECT-TYPE
    SYNTAX     SEQUENCE OF HmStatusDslByteTransportEntry
    MAX-ACCESS not-accessible
    STATUS     current
    DESCRIPTION
            "-- empty --"
    ::= { hmStatusDsl 2 }

-- {ROW} 1.3.6.1.4.1.248.32.18.1.72.2.1
hmStatusDslByteTransportEntry OBJECT-TYPE
    SYNTAX     HmStatusDslByteTransportEntry
    MAX-ACCESS not-accessible
    STATUS     current
    DESCRIPTION
            ""
    INDEX {
            hmStatusDslByteTransportEntryIfc
          }
    ::= { hmStatusDslByteTransportTable 1 }

HmStatusDslByteTransportEntry ::= SEQUENCE {
            hmStatusDslByteTransportEntryIfc DisplayString,
            hmStatusDslByteTransportEntryTxBytes Counter64,
            hmStatusDslByteTransportEntryRxBytes Counter64
    }

-- {COLUMN} 1.3.6.1.4.1.248.32.18.1.72.2.1.1
hmStatusDslByteTransportEntryIfc OBJECT-TYPE
    SYNTAX     DisplayString (SIZE(0..255))
    MAX-ACCESS read-only
    STATUS     current
    DESCRIPTION
            "-- empty --"
    ::= { hmStatusDslByteTransportEntry 1 }

-- {COLUMN} 1.3.6.1.4.1.248.32.18.1.72.2.1.2
hmStatusDslByteTransportEntryTxBytes OBJECT-TYPE
    SYNTAX     Counter64
    MAX-ACCESS read-only
    STATUS     current
    DESCRIPTION
            "-- empty --"
    ::= { hmStatusDslByteTransportEntry 2 }

-- {COLUMN} 1.3.6.1.4.1.248.32.18.1.72.2.1.3
hmStatusDslByteTransportEntryRxBytes OBJECT-TYPE
    SYNTAX     Counter64
    MAX-ACCESS read-only
    STATUS     current
    DESCRIPTION
            "-- empty --"
    ::= { hmStatusDslByteTransportEntry 3 }

-- {TABLE} 1.3.6.1.4.1.248.32.18.1.72.3
hmStatusDslPacketTransportTable OBJECT-TYPE
    SYNTAX     SEQUENCE OF HmStatusDslPacketTransportEntry
    MAX-ACCESS not-accessible
    STATUS     current
    DESCRIPTION
            "-- empty --"
    ::= { hmStatusDsl 3 }

-- {ROW} 1.3.6.1.4.1.248.32.18.1.72.3.1
hmStatusDslPacketTransportEntry OBJECT-TYPE
    SYNTAX     HmStatusDslPacketTransportEntry
    MAX-ACCESS not-accessible
    STATUS     current
    DESCRIPTION
            ""
    INDEX {
            hmStatusDslPacketTransportEntryIfc
          }
    ::= { hmStatusDslPacketTransportTable 1 }

HmStatusDslPacketTransportEntry ::= SEQUENCE {
            hmStatusDslPacketTransportEntryIfc DisplayString,
            hmStatusDslPacketTransportEntryRxPackets Counter32,
            hmStatusDslPacketTransportEntryTxPackets Counter32,
            hmStatusDslPacketTransportEntryRxBroadcasts Counter32,
            hmStatusDslPacketTransportEntryRxMulticasts Counter32,
            hmStatusDslPacketTransportEntryRxUnicasts Counter32,
            hmStatusDslPacketTransportEntryTxBroadcasts Counter32,
            hmStatusDslPacketTransportEntryTxMulticasts Counter32,
            hmStatusDslPacketTransportEntryTxUnicasts Counter32
    }

-- {COLUMN} 1.3.6.1.4.1.248.32.18.1.72.3.1.1
hmStatusDslPacketTransportEntryIfc OBJECT-TYPE
    SYNTAX     DisplayString (SIZE(0..255))
    MAX-ACCESS read-only
    STATUS     current
    DESCRIPTION
            "-- empty --"
    ::= { hmStatusDslPacketTransportEntry 1 }

-- {COLUMN} 1.3.6.1.4.1.248.32.18.1.72.3.1.2
hmStatusDslPacketTransportEntryRxPackets OBJECT-TYPE
    SYNTAX     Counter32
    MAX-ACCESS read-only
    STATUS     current
    DESCRIPTION
            "-- empty --"
    ::= { hmStatusDslPacketTransportEntry 2 }

-- {COLUMN} 1.3.6.1.4.1.248.32.18.1.72.3.1.3
hmStatusDslPacketTransportEntryTxPackets OBJECT-TYPE
    SYNTAX     Counter32
    MAX-ACCESS read-only
    STATUS     current
    DESCRIPTION
            "-- empty --"
    ::= { hmStatusDslPacketTransportEntry 3 }

-- {COLUMN} 1.3.6.1.4.1.248.32.18.1.72.3.1.4
hmStatusDslPacketTransportEntryRxBroadcasts OBJECT-TYPE
    SYNTAX     Counter32
    MAX-ACCESS read-only
    STATUS     current
    DESCRIPTION
            "-- empty --"
    ::= { hmStatusDslPacketTransportEntry 4 }

-- {COLUMN} 1.3.6.1.4.1.248.32.18.1.72.3.1.5
hmStatusDslPacketTransportEntryRxMulticasts OBJECT-TYPE
    SYNTAX     Counter32
    MAX-ACCESS read-only
    STATUS     current
    DESCRIPTION
            "-- empty --"
    ::= { hmStatusDslPacketTransportEntry 5 }

-- {COLUMN} 1.3.6.1.4.1.248.32.18.1.72.3.1.6
hmStatusDslPacketTransportEntryRxUnicasts OBJECT-TYPE
    SYNTAX     Counter32
    MAX-ACCESS read-only
    STATUS     current
    DESCRIPTION
            "-- empty --"
    ::= { hmStatusDslPacketTransportEntry 6 }

-- {COLUMN} 1.3.6.1.4.1.248.32.18.1.72.3.1.7
hmStatusDslPacketTransportEntryTxBroadcasts OBJECT-TYPE
    SYNTAX     Counter32
    MAX-ACCESS read-only
    STATUS     current
    DESCRIPTION
            "-- empty --"
    ::= { hmStatusDslPacketTransportEntry 7 }

-- {COLUMN} 1.3.6.1.4.1.248.32.18.1.72.3.1.8
hmStatusDslPacketTransportEntryTxMulticasts OBJECT-TYPE
    SYNTAX     Counter32
    MAX-ACCESS read-only
    STATUS     current
    DESCRIPTION
            "-- empty --"
    ::= { hmStatusDslPacketTransportEntry 8 }

-- {COLUMN} 1.3.6.1.4.1.248.32.18.1.72.3.1.9
hmStatusDslPacketTransportEntryTxUnicasts OBJECT-TYPE
    SYNTAX     Counter32
    MAX-ACCESS read-only
    STATUS     current
    DESCRIPTION
            "-- empty --"
    ::= { hmStatusDslPacketTransportEntry 9 }

-- {TABLE} 1.3.6.1.4.1.248.32.18.1.72.4
hmStatusDslErrorsTable OBJECT-TYPE
    SYNTAX     SEQUENCE OF HmStatusDslErrorsEntry
    MAX-ACCESS not-accessible
    STATUS     current
    DESCRIPTION
            "-- empty --"
    ::= { hmStatusDsl 4 }

-- {ROW} 1.3.6.1.4.1.248.32.18.1.72.4.1
hmStatusDslErrorsEntry OBJECT-TYPE
    SYNTAX     HmStatusDslErrorsEntry
    MAX-ACCESS not-accessible
    STATUS     current
    DESCRIPTION
            ""
    INDEX {
            hmStatusDslErrorsEntryIfc
          }
    ::= { hmStatusDslErrorsTable 1 }

HmStatusDslErrorsEntry ::= SEQUENCE {
            hmStatusDslErrorsEntryIfc DisplayString,
            hmStatusDslErrorsEntryRxErrors Counter32,
            hmStatusDslErrorsEntryTxErrors Counter32,
            hmStatusDslErrorsEntryStackErrors Counter32,
            hmStatusDslErrorsEntryNicErrors Counter32,
            hmStatusDslErrorsEntryQueueErrors Counter32,
            hmStatusDslErrorsEntryRxCrcErrors Counter32,
            hmStatusDslErrorsEntryCollisions Counter32,
            hmStatusDslErrorsEntrySingleCollisions Counter32,
            hmStatusDslErrorsEntryMultipleCollisions Counter32,
            hmStatusDslErrorsEntryLateCollisions Counter32,
            hmStatusDslErrorsEntryExcessiveCollisions Counter32,
            hmStatusDslErrorsEntryRxAlignErrors Counter32,
            hmStatusDslErrorsEntryRxTooShort Counter32,
            hmStatusDslErrorsEntryRxTooLong Counter32,
            hmStatusDslErrorsEntryTxCarrier Counter32,
            hmStatusDslErrorsEntryTxDeferred Counter32
    }

-- {COLUMN} 1.3.6.1.4.1.248.32.18.1.72.4.1.1
hmStatusDslErrorsEntryIfc OBJECT-TYPE
    SYNTAX     DisplayString (SIZE(0..255))
    MAX-ACCESS read-only
    STATUS     current
    DESCRIPTION
            "-- empty --"
    ::= { hmStatusDslErrorsEntry 1 }

-- {COLUMN} 1.3.6.1.4.1.248.32.18.1.72.4.1.2
hmStatusDslErrorsEntryRxErrors OBJECT-TYPE
    SYNTAX     Counter32
    MAX-ACCESS read-only
    STATUS     current
    DESCRIPTION
            "-- empty --"
    ::= { hmStatusDslErrorsEntry 2 }

-- {COLUMN} 1.3.6.1.4.1.248.32.18.1.72.4.1.3
hmStatusDslErrorsEntryTxErrors OBJECT-TYPE
    SYNTAX     Counter32
    MAX-ACCESS read-only
    STATUS     current
    DESCRIPTION
            "-- empty --"
    ::= { hmStatusDslErrorsEntry 3 }

-- {COLUMN} 1.3.6.1.4.1.248.32.18.1.72.4.1.4
hmStatusDslErrorsEntryStackErrors OBJECT-TYPE
    SYNTAX     Counter32
    MAX-ACCESS read-only
    STATUS     current
    DESCRIPTION
            "-- empty --"
    ::= { hmStatusDslErrorsEntry 4 }

-- {COLUMN} 1.3.6.1.4.1.248.32.18.1.72.4.1.5
hmStatusDslErrorsEntryNicErrors OBJECT-TYPE
    SYNTAX     Counter32
    MAX-ACCESS read-only
    STATUS     current
    DESCRIPTION
            "-- empty --"
    ::= { hmStatusDslErrorsEntry 5 }

-- {COLUMN} 1.3.6.1.4.1.248.32.18.1.72.4.1.6
hmStatusDslErrorsEntryQueueErrors OBJECT-TYPE
    SYNTAX     Counter32
    MAX-ACCESS read-only
    STATUS     current
    DESCRIPTION
            "-- empty --"
    ::= { hmStatusDslErrorsEntry 6 }

-- {COLUMN} 1.3.6.1.4.1.248.32.18.1.72.4.1.7
hmStatusDslErrorsEntryRxCrcErrors OBJECT-TYPE
    SYNTAX     Counter32
    MAX-ACCESS read-only
    STATUS     current
    DESCRIPTION
            "-- empty --"
    ::= { hmStatusDslErrorsEntry 7 }

-- {COLUMN} 1.3.6.1.4.1.248.32.18.1.72.4.1.8
hmStatusDslErrorsEntryCollisions OBJECT-TYPE
    SYNTAX     Counter32
    MAX-ACCESS read-only
    STATUS     current
    DESCRIPTION
            "-- empty --"
    ::= { hmStatusDslErrorsEntry 8 }

-- {COLUMN} 1.3.6.1.4.1.248.32.18.1.72.4.1.9
hmStatusDslErrorsEntrySingleCollisions OBJECT-TYPE
    SYNTAX     Counter32
    MAX-ACCESS read-only
    STATUS     current
    DESCRIPTION
            "-- empty --"
    ::= { hmStatusDslErrorsEntry 9 }

-- {COLUMN} 1.3.6.1.4.1.248.32.18.1.72.4.1.10
hmStatusDslErrorsEntryMultipleCollisions OBJECT-TYPE
    SYNTAX     Counter32
    MAX-ACCESS read-only
    STATUS     current
    DESCRIPTION
            "-- empty --"
    ::= { hmStatusDslErrorsEntry 10 }

-- {COLUMN} 1.3.6.1.4.1.248.32.18.1.72.4.1.11
hmStatusDslErrorsEntryLateCollisions OBJECT-TYPE
    SYNTAX     Counter32
    MAX-ACCESS read-only
    STATUS     current
    DESCRIPTION
            "-- empty --"
    ::= { hmStatusDslErrorsEntry 11 }

-- {COLUMN} 1.3.6.1.4.1.248.32.18.1.72.4.1.12
hmStatusDslErrorsEntryExcessiveCollisions OBJECT-TYPE
    SYNTAX     Counter32
    MAX-ACCESS read-only
    STATUS     current
    DESCRIPTION
            "-- empty --"
    ::= { hmStatusDslErrorsEntry 12 }

-- {COLUMN} 1.3.6.1.4.1.248.32.18.1.72.4.1.13
hmStatusDslErrorsEntryRxAlignErrors OBJECT-TYPE
    SYNTAX     Counter32
    MAX-ACCESS read-only
    STATUS     current
    DESCRIPTION
            "-- empty --"
    ::= { hmStatusDslErrorsEntry 13 }

-- {COLUMN} 1.3.6.1.4.1.248.32.18.1.72.4.1.14
hmStatusDslErrorsEntryRxTooShort OBJECT-TYPE
    SYNTAX     Counter32
    MAX-ACCESS read-only
    STATUS     current
    DESCRIPTION
            "-- empty --"
    ::= { hmStatusDslErrorsEntry 14 }

-- {COLUMN} 1.3.6.1.4.1.248.32.18.1.72.4.1.15
hmStatusDslErrorsEntryRxTooLong OBJECT-TYPE
    SYNTAX     Counter32
    MAX-ACCESS read-only
    STATUS     current
    DESCRIPTION
            "-- empty --"
    ::= { hmStatusDslErrorsEntry 15 }

-- {COLUMN} 1.3.6.1.4.1.248.32.18.1.72.4.1.16
hmStatusDslErrorsEntryTxCarrier OBJECT-TYPE
    SYNTAX     Counter32
    MAX-ACCESS read-only
    STATUS     current
    DESCRIPTION
            "-- empty --"
    ::= { hmStatusDslErrorsEntry 16 }

-- {COLUMN} 1.3.6.1.4.1.248.32.18.1.72.4.1.17
hmStatusDslErrorsEntryTxDeferred OBJECT-TYPE
    SYNTAX     Counter32
    MAX-ACCESS read-only
    STATUS     current
    DESCRIPTION
            "-- empty --"
    ::= { hmStatusDslErrorsEntry 17 }

-- {SCALAR} 1.3.6.1.4.1.248.32.18.1.72.30
hmStatusDslDeleteValues OBJECT-TYPE
    SYNTAX     DisplayString
    MAX-ACCESS read-write
    STATUS     current
    DESCRIPTION
            "-- empty --"
    ::= { hmStatusDsl 30 }

-- {NODE} 1.3.6.1.4.1.248.32.18.1.73
hmStatusWlanMngmt OBJECT IDENTIFIER ::= { hmStatus 73 }

-- {SCALAR} 1.3.6.1.4.1.248.32.18.1.73.1
hmStatusWlanMngmtControllerState OBJECT-TYPE
    SYNTAX     INTEGER {
                  eUnknown (0),
                  eInitScepClient (1),
                  eCertReqSent (2),
                  eReady (3),
                  eTimeNotSet (4),
                  eNoRandom (5),
                  eSubcaInitScep (6),
                  eDisabled (7)
            }
    MAX-ACCESS read-only
    STATUS     current
    DESCRIPTION
            "-- empty --"
    ::= { hmStatusWlanMngmt 1 }

-- {NODE} 1.3.6.1.4.1.248.32.18.1.73.2
hmStatusWlanMngmtApConf OBJECT IDENTIFIER ::= { hmStatusWlanMngmt 2 }

-- {TABLE} 1.3.6.1.4.1.248.32.18.1.73.2.1
hmStatusWlanMngmtApConfNetwprofilsTable OBJECT-TYPE
    SYNTAX     SEQUENCE OF HmStatusWlanMngmtApConfNetwprofilsEntry
    MAX-ACCESS not-accessible
    STATUS     current
    DESCRIPTION
            "network profiles"
    ::= { hmStatusWlanMngmtApConf 1 }

-- {ROW} 1.3.6.1.4.1.248.32.18.1.73.2.1.1
hmStatusWlanMngmtApConfNetwprofilsEntry OBJECT-TYPE
    SYNTAX     HmStatusWlanMngmtApConfNetwprofilsEntry
    MAX-ACCESS not-accessible
    STATUS     current
    DESCRIPTION
            ""
    INDEX {
            hmStatusWlanMngmtApConfNetwprofilsEntryName
          }
    ::= { hmStatusWlanMngmtApConfNetwprofilsTable 1 }

HmStatusWlanMngmtApConfNetwprofilsEntry ::= SEQUENCE {
            hmStatusWlanMngmtApConfNetwprofilsEntryName DisplayString,
            hmStatusWlanMngmtApConfNetwprofilsEntryOperating INTEGER,
            hmStatusWlanMngmtApConfNetwprofilsEntryVlanId Integer32,
            hmStatusWlanMngmtApConfNetwprofilsEntryEncryption INTEGER,
            hmStatusWlanMngmtApConfNetwprofilsEntryWpa1SessionKeytypes INTEGER,
            hmStatusWlanMngmtApConfNetwprofilsEntryWpaVersion INTEGER,
            hmStatusWlanMngmtApConfNetwprofilsEntryKey DisplayString,
            hmStatusWlanMngmtApConfNetwprofilsEntryRadioBand INTEGER,
            hmStatusWlanMngmtApConfNetwprofilsEntryContinuation Integer32,
            hmStatusWlanMngmtApConfNetwprofilsEntryMinTxRate INTEGER,
            hmStatusWlanMngmtApConfNetwprofilsEntryMaxTxRate INTEGER,
            hmStatusWlanMngmtApConfNetwprofilsEntryBasicRate INTEGER,
            hmStatusWlanMngmtApConfNetwprofilsEntry11bPreamble INTEGER,
            hmStatusWlanMngmtApConfNetwprofilsEntryMacFilter INTEGER,
            hmStatusWlanMngmtApConfNetwprofilsEntryClBrgSupport INTEGER,
            hmStatusWlanMngmtApConfNetwprofilsEntryMaxStations Integer32,
            hmStatusWlanMngmtApConfNetwprofilsEntrySsidBroadcast INTEGER,
            hmStatusWlanMngmtApConfNetwprofilsEntrySsid DisplayString,
            hmStatusWlanMngmtApConfNetwprofilsEntryMinHtMcs INTEGER,
            hmStatusWlanMngmtApConfNetwprofilsEntryMaxHtMcs INTEGER,
            hmStatusWlanMngmtApConfNetwprofilsEntryShortGuardInterval INTEGER,
            hmStatusWlanMngmtApConfNetwprofilsEntryMaxSpatialStreams INTEGER,
            hmStatusWlanMngmtApConfNetwprofilsEntrySendAggregates INTEGER,
            hmStatusWlanMngmtApConfNetwprofilsEntryWpa2SessionKeytypes INTEGER,
            hmStatusWlanMngmtApConfNetwprofilsEntryRadiusAccounting INTEGER,
            hmStatusWlanMngmtApConfNetwprofilsEntryVlanMode INTEGER,
            hmStatusWlanMngmtApConfNetwprofilsEntryConnectSsidTo INTEGER,
            hmStatusWlanMngmtApConfNetwprofilsEntryInterStationTraffic INTEGER,
            hmStatusWlanMngmtApConfNetwprofilsEntryVlanIdnew Integer32,
            hmStatusWlanMngmtApConfNetwprofilsEntryRadiusProfile DisplayString,
            hmStatusWlanMngmtApConfNetwprofilsEntryStbcActivated INTEGER,
            hmStatusWlanMngmtApConfNetwprofilsEntryLdpcActivated INTEGER,
            hmStatusWlanMngmtApConfNetwprofilsEntryMinClientStrength Integer32,
            hmStatusWlanMngmtApConfNetwprofilsEntryIeee80211uNetworkProfile DisplayString,
            hmStatusWlanMngmtApConfNetwprofilsEntryOkc INTEGER,
            hmStatusWlanMngmtApConfNetwprofilsEntryWpa2KeyManagement BITS,
            hmStatusWlanMngmtApConfNetwprofilsEntryApsd INTEGER,
            hmStatusWlanMngmtApConfNetwprofilsEntryProtMgmtFrames INTEGER,
            hmStatusWlanMngmtApConfNetwprofilsEntryTxLimit Integer32,
            hmStatusWlanMngmtApConfNetwprofilsEntryRxLimit Integer32,
            hmStatusWlanMngmtApConfNetwprofilsEntryLbsTracking INTEGER,
            hmStatusWlanMngmtApConfNetwprofilsEntryLbsTrackingList DisplayString,
            hmStatusWlanMngmtApConfNetwprofilsEntryClBrgRoamingSupport INTEGER
    }

-- {COLUMN} 1.3.6.1.4.1.248.32.18.1.73.2.1.1.1
hmStatusWlanMngmtApConfNetwprofilsEntryName OBJECT-TYPE
    SYNTAX     DisplayString (SIZE(0..31))
    MAX-ACCESS read-only
    STATUS     current
    DESCRIPTION
            "-- empty --"
    ::= { hmStatusWlanMngmtApConfNetwprofilsEntry 1 }

-- {COLUMN} 1.3.6.1.4.1.248.32.18.1.73.2.1.1.4
hmStatusWlanMngmtApConfNetwprofilsEntryOperating OBJECT-TYPE
    SYNTAX     INTEGER {
                  eYes (0),
                  eNo (1)
            }
    MAX-ACCESS read-only
    STATUS     current
    DESCRIPTION
            "-- empty --"
    ::= { hmStatusWlanMngmtApConfNetwprofilsEntry 4 }

-- {COLUMN} 1.3.6.1.4.1.248.32.18.1.73.2.1.1.5
hmStatusWlanMngmtApConfNetwprofilsEntryVlanId OBJECT-TYPE
    SYNTAX     Integer32 (0..65535)
    MAX-ACCESS read-only
    STATUS     obsolete
    DESCRIPTION
            ""
    ::= { hmStatusWlanMngmtApConfNetwprofilsEntry 5 }

-- {COLUMN} 1.3.6.1.4.1.248.32.18.1.73.2.1.1.6
hmStatusWlanMngmtApConfNetwprofilsEntryEncryption OBJECT-TYPE
    SYNTAX     INTEGER {
                  e80211iWpaPsk (0),
                  e80211iWpa8021x (1),
                  eWep104Bits (2),
                  eWep40Bits (3),
                  eWep104Bits8021x (4),
                  eWep40Bits8021x (5),
                  eNone (6)
            }
    MAX-ACCESS read-only
    STATUS     current
    DESCRIPTION
            "-- empty --"
    ::= { hmStatusWlanMngmtApConfNetwprofilsEntry 6 }

-- {COLUMN} 1.3.6.1.4.1.248.32.18.1.73.2.1.1.7
hmStatusWlanMngmtApConfNetwprofilsEntryWpa1SessionKeytypes OBJECT-TYPE
    SYNTAX     INTEGER {
                  eTkipAes (0),
                  eAes (1),
                  eTkip (2)
            }
    MAX-ACCESS read-only
    STATUS     current
    DESCRIPTION
            "-- empty --"
    ::= { hmStatusWlanMngmtApConfNetwprofilsEntry 7 }

-- {COLUMN} 1.3.6.1.4.1.248.32.18.1.73.2.1.1.8
hmStatusWlanMngmtApConfNetwprofilsEntryWpaVersion OBJECT-TYPE
    SYNTAX     INTEGER {
                  eWpa12 (0),
                  eWpa1 (1),
                  eWpa2 (2)
            }
    MAX-ACCESS read-only
    STATUS     current
    DESCRIPTION
            "-- empty --"
    ::= { hmStatusWlanMngmtApConfNetwprofilsEntry 8 }

-- {COLUMN} 1.3.6.1.4.1.248.32.18.1.73.2.1.1.9
hmStatusWlanMngmtApConfNetwprofilsEntryKey OBJECT-TYPE
    SYNTAX     DisplayString (SIZE(0..63))
    MAX-ACCESS read-only
    STATUS     current
    DESCRIPTION
            "-- empty --"
    ::= { hmStatusWlanMngmtApConfNetwprofilsEntry 9 }

-- {COLUMN} 1.3.6.1.4.1.248.32.18.1.73.2.1.1.10
hmStatusWlanMngmtApConfNetwprofilsEntryRadioBand OBJECT-TYPE
    SYNTAX     INTEGER {
                  e24ghz5ghz (0),
                  e24ghz (1),
                  e5ghz (2)
            }
    MAX-ACCESS read-only
    STATUS     current
    DESCRIPTION
            "-- empty --"
    ::= { hmStatusWlanMngmtApConfNetwprofilsEntry 10 }

-- {COLUMN} 1.3.6.1.4.1.248.32.18.1.73.2.1.1.11
hmStatusWlanMngmtApConfNetwprofilsEntryContinuation OBJECT-TYPE
    SYNTAX     Integer32 (0..65535)
    MAX-ACCESS read-only
    STATUS     current
    DESCRIPTION
            ""
    ::= { hmStatusWlanMngmtApConfNetwprofilsEntry 11 }

-- {COLUMN} 1.3.6.1.4.1.248.32.18.1.73.2.1.1.12
hmStatusWlanMngmtApConfNetwprofilsEntryMinTxRate OBJECT-TYPE
    SYNTAX     INTEGER {
                  eAuto (0),
                  e1M (1),
                  e2M (2),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-only
    STATUS     current
    DESCRIPTION
            "-- empty --"
    ::= { hmStatusWlanMngmtApConfNetwprofilsEntry 12 }

-- {COLUMN} 1.3.6.1.4.1.248.32.18.1.73.2.1.1.13
hmStatusWlanMngmtApConfNetwprofilsEntryMaxTxRate OBJECT-TYPE
    SYNTAX     INTEGER {
                  eAuto (0),
                  e1M (1),
                  e2M (2),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-only
    STATUS     current
    DESCRIPTION
            "-- empty --"
    ::= { hmStatusWlanMngmtApConfNetwprofilsEntry 13 }

-- {COLUMN} 1.3.6.1.4.1.248.32.18.1.73.2.1.1.14
hmStatusWlanMngmtApConfNetwprofilsEntryBasicRate OBJECT-TYPE
    SYNTAX     INTEGER {
                  e2M (0),
                  e1M (1),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-only
    STATUS     current
    DESCRIPTION
            "-- empty --"
    ::= { hmStatusWlanMngmtApConfNetwprofilsEntry 14 }

-- {COLUMN} 1.3.6.1.4.1.248.32.18.1.73.2.1.1.15
hmStatusWlanMngmtApConfNetwprofilsEntry11bPreamble OBJECT-TYPE
    SYNTAX     INTEGER {
                  eAuto (0),
                  eLong (1)
            }
    MAX-ACCESS read-only
    STATUS     current
    DESCRIPTION
            "-- empty --"
    ::= { hmStatusWlanMngmtApConfNetwprofilsEntry 15 }

-- {COLUMN} 1.3.6.1.4.1.248.32.18.1.73.2.1.1.16
hmStatusWlanMngmtApConfNetwprofilsEntryMacFilter OBJECT-TYPE
    SYNTAX     INTEGER {
                  eNo (0),
                  eYes (1)
            }
    MAX-ACCESS read-only
    STATUS     current
    DESCRIPTION
            "-- empty --"
    ::= { hmStatusWlanMngmtApConfNetwprofilsEntry 16 }

-- {COLUMN} 1.3.6.1.4.1.248.32.18.1.73.2.1.1.17
hmStatusWlanMngmtApConfNetwprofilsEntryClBrgSupport OBJECT-TYPE
    SYNTAX     INTEGER {
                  eNo (0),
                  eYes (1),
                  eExclusive (2)
            }
    MAX-ACCESS read-only
    STATUS     current
    DESCRIPTION
            "-- empty --"
    ::= { hmStatusWlanMngmtApConfNetwprofilsEntry 17 }

-- {COLUMN} 1.3.6.1.4.1.248.32.18.1.73.2.1.1.18
hmStatusWlanMngmtApConfNetwprofilsEntryMaxStations OBJECT-TYPE
    SYNTAX     Integer32 (0..65535)
    MAX-ACCESS read-only
    STATUS     current
    DESCRIPTION
            "-- empty --"
    ::= { hmStatusWlanMngmtApConfNetwprofilsEntry 18 }

-- {COLUMN} 1.3.6.1.4.1.248.32.18.1.73.2.1.1.19
hmStatusWlanMngmtApConfNetwprofilsEntrySsidBroadcast OBJECT-TYPE
    SYNTAX     INTEGER {
                  eYes (0),
                  eNo (1),
                  eTightened (2)
            }
    MAX-ACCESS read-only
    STATUS     current
    DESCRIPTION
            "-- empty --"
    ::= { hmStatusWlanMngmtApConfNetwprofilsEntry 19 }

-- {COLUMN} 1.3.6.1.4.1.248.32.18.1.73.2.1.1.21
hmStatusWlanMngmtApConfNetwprofilsEntrySsid OBJECT-TYPE
    SYNTAX     DisplayString (SIZE(0..32))
    MAX-ACCESS read-only
    STATUS     current
    DESCRIPTION
            "-- empty --"
    ::= { hmStatusWlanMngmtApConfNetwprofilsEntry 21 }

-- {COLUMN} 1.3.6.1.4.1.248.32.18.1.73.2.1.1.22
hmStatusWlanMngmtApConfNetwprofilsEntryMinHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-only
    STATUS     current
    DESCRIPTION
            "-- empty --"
    ::= { hmStatusWlanMngmtApConfNetwprofilsEntry 22 }

-- {COLUMN} 1.3.6.1.4.1.248.32.18.1.73.2.1.1.23
hmStatusWlanMngmtApConfNetwprofilsEntryMaxHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-only
    STATUS     current
    DESCRIPTION
            "-- empty --"
    ::= { hmStatusWlanMngmtApConfNetwprofilsEntry 23 }

-- {COLUMN} 1.3.6.1.4.1.248.32.18.1.73.2.1.1.24
hmStatusWlanMngmtApConfNetwprofilsEntryShortGuardInterval OBJECT-TYPE
    SYNTAX     INTEGER {
                  eAuto (0),
                  eNo (1)
            }
    MAX-ACCESS read-only
    STATUS     current
    DESCRIPTION
            "-- empty --"
    ::= { hmStatusWlanMngmtApConfNetwprofilsEntry 24 }

-- {COLUMN} 1.3.6.1.4.1.248.32.18.1.73.2.1.1.25
hmStatusWlanMngmtApConfNetwprofilsEntryMaxSpatialStreams OBJECT-TYPE
    SYNTAX     INTEGER {
                  eAuto (0),
                  eOne (1),
                  eTwo (2)
            }
    MAX-ACCESS read-only
    STATUS     current
    DESCRIPTION
            "-- empty --"
    ::= { hmStatusWlanMngmtApConfNetwprofilsEntry 25 }

-- {COLUMN} 1.3.6.1.4.1.248.32.18.1.73.2.1.1.26
hmStatusWlanMngmtApConfNetwprofilsEntrySendAggregates OBJECT-TYPE
    SYNTAX     INTEGER {
                  eNo (0),
                  eYes (1)
            }
    MAX-ACCESS read-only
    STATUS     current
    DESCRIPTION
            "-- empty --"
    ::= { hmStatusWlanMngmtApConfNetwprofilsEntry 26 }

-- {COLUMN} 1.3.6.1.4.1.248.32.18.1.73.2.1.1.27
hmStatusWlanMngmtApConfNetwprofilsEntryWpa2SessionKeytypes OBJECT-TYPE
    SYNTAX     INTEGER {
                  eTkipAes (0),
                  eAes (1),
                  eTkip (2)
            }
    MAX-ACCESS read-only
    STATUS     current
    DESCRIPTION
            "-- empty --"
    ::= { hmStatusWlanMngmtApConfNetwprofilsEntry 27 }

-- {COLUMN} 1.3.6.1.4.1.248.32.18.1.73.2.1.1.28
hmStatusWlanMngmtApConfNetwprofilsEntryRadiusAccounting OBJECT-TYPE
    SYNTAX     INTEGER {
                  eNo (0),
                  eYes (1)
            }
    MAX-ACCESS read-only
    STATUS     current
    DESCRIPTION
            "-- empty --"
    ::= { hmStatusWlanMngmtApConfNetwprofilsEntry 28 }

-- {COLUMN} 1.3.6.1.4.1.248.32.18.1.73.2.1.1.30
hmStatusWlanMngmtApConfNetwprofilsEntryVlanMode OBJECT-TYPE
    SYNTAX     INTEGER {
                  eUntagged (0),
                  eTagged (1)
            }
    MAX-ACCESS read-only
    STATUS     current
    DESCRIPTION
            "-- empty --"
    ::= { hmStatusWlanMngmtApConfNetwprofilsEntry 30 }

-- {COLUMN} 1.3.6.1.4.1.248.32.18.1.73.2.1.1.32
hmStatusWlanMngmtApConfNetwprofilsEntryConnectSsidTo OBJECT-TYPE
    SYNTAX     INTEGER {
                  eLan (0),
                  eWlcTunnel1 (1),
                  eWlcTunnel2 (2),
                  eWlcTunnel3 (3),
                  eWlcTunnel4 (4),
                  eWlcTunnel5 (5),
                  eWlcTunnel6 (6),
                  eWlcTunnel7 (7),
                  eWlcTunnel8 (8),
                  eWlcTunnel9 (9),
                  eWlcTunnel10 (10),
                  eWlcTunnel11 (11),
                  eWlcTunnel12 (12),
                  eWlcTunnel13 (13),
                  eWlcTunnel14 (14),
                  eWlcTunnel15 (15),
                  eWlcTunnel16 (16),
                  eWlcTunnel17 (17),
                  eWlcTunnel18 (18),
                  eWlcTunnel19 (19),
                  eWlcTunnel20 (20),
                  eWlcTunnel21 (21),
                  eWlcTunnel22 (22),
                  eWlcTunnel23 (23),
                  eWlcTunnel24 (24),
                  eWlcTunnel25 (25),
                  eWlcTunnel26 (26),
                  eWlcTunnel27 (27),
                  eWlcTunnel28 (28),
                  eWlcTunnel29 (29),
                  eWlcTunnel30 (30),
                  eWlcTunnel31 (31),
                  eWlcTunnel32 (32),
                  eWlcTunnelAutowds (33)
            }
    MAX-ACCESS read-only
    STATUS     current
    DESCRIPTION
            "-- empty --"
    ::= { hmStatusWlanMngmtApConfNetwprofilsEntry 32 }

-- {COLUMN} 1.3.6.1.4.1.248.32.18.1.73.2.1.1.33
hmStatusWlanMngmtApConfNetwprofilsEntryInterStationTraffic OBJECT-TYPE
    SYNTAX     INTEGER {
                  eNo (0),
                  eYes (1)
            }
    MAX-ACCESS read-only
    STATUS     current
    DESCRIPTION
            "-- empty --"
    ::= { hmStatusWlanMngmtApConfNetwprofilsEntry 33 }

-- {COLUMN} 1.3.6.1.4.1.248.32.18.1.73.2.1.1.34
hmStatusWlanMngmtApConfNetwprofilsEntryVlanIdnew OBJECT-TYPE
    SYNTAX     Integer32 (0..65535)
    MAX-ACCESS read-only
    STATUS     current
    DESCRIPTION
            ""
    ::= { hmStatusWlanMngmtApConfNetwprofilsEntry 34 }

-- {COLUMN} 1.3.6.1.4.1.248.32.18.1.73.2.1.1.35
hmStatusWlanMngmtApConfNetwprofilsEntryRadiusProfile OBJECT-TYPE
    SYNTAX     DisplayString (SIZE(0..16))
    MAX-ACCESS read-only
    STATUS     current
    DESCRIPTION
            "-- empty --"
    ::= { hmStatusWlanMngmtApConfNetwprofilsEntry 35 }

-- {COLUMN} 1.3.6.1.4.1.248.32.18.1.73.2.1.1.36
hmStatusWlanMngmtApConfNetwprofilsEntryStbcActivated OBJECT-TYPE
    SYNTAX     INTEGER {
                  eNo (0),
                  eYes (1)
            }
    MAX-ACCESS read-only
    STATUS     current
    DESCRIPTION
            "-- empty --"
    ::= { hmStatusWlanMngmtApConfNetwprofilsEntry 36 }

-- {COLUMN} 1.3.6.1.4.1.248.32.18.1.73.2.1.1.37
hmStatusWlanMngmtApConfNetwprofilsEntryLdpcActivated OBJECT-TYPE
    SYNTAX     INTEGER {
                  eNo (0),
                  eYes (1)
            }
    MAX-ACCESS read-only
    STATUS     current
    DESCRIPTION
            "-- empty --"
    ::= { hmStatusWlanMngmtApConfNetwprofilsEntry 37 }

-- {COLUMN} 1.3.6.1.4.1.248.32.18.1.73.2.1.1.38
hmStatusWlanMngmtApConfNetwprofilsEntryMinClientStrength OBJECT-TYPE
    SYNTAX     Integer32 (0..255)
    MAX-ACCESS read-only
    STATUS     current
    DESCRIPTION
            "-- empty --"
    ::= { hmStatusWlanMngmtApConfNetwprofilsEntry 38 }

-- {COLUMN} 1.3.6.1.4.1.248.32.18.1.73.2.1.1.39
hmStatusWlanMngmtApConfNetwprofilsEntryIeee80211uNetworkProfile OBJECT-TYPE
    SYNTAX     DisplayString (SIZE(0..32))
    MAX-ACCESS read-only
    STATUS     current
    DESCRIPTION
            "-- empty --"
    ::= { hmStatusWlanMngmtApConfNetwprofilsEntry 39 }

-- {COLUMN} 1.3.6.1.4.1.248.32.18.1.73.2.1.1.40
hmStatusWlanMngmtApConfNetwprofilsEntryOkc OBJECT-TYPE
    SYNTAX     INTEGER {
                  eNo (0),
                  eYes (1)
            }
    MAX-ACCESS read-only
    STATUS     current
    DESCRIPTION
            "-- empty --"
    ::= { hmStatusWlanMngmtApConfNetwprofilsEntry 40 }

-- {COLUMN} 1.3.6.1.4.1.248.32.18.1.73.2.1.1.41
hmStatusWlanMngmtApConfNetwprofilsEntryWpa2KeyManagement OBJECT-TYPE
    SYNTAX     BITS {
                  eSha256 (5),
                  eFastRoaming (6),
                  eStandard (7)
            }
    MAX-ACCESS read-only
    STATUS     current
    DESCRIPTION
            "-- empty --"
    ::= { hmStatusWlanMngmtApConfNetwprofilsEntry 41 }

-- {COLUMN} 1.3.6.1.4.1.248.32.18.1.73.2.1.1.42
hmStatusWlanMngmtApConfNetwprofilsEntryApsd OBJECT-TYPE
    SYNTAX     INTEGER {
                  eNo (0),
                  eYes (1)
            }
    MAX-ACCESS read-only
    STATUS     current
    DESCRIPTION
            "-- empty --"
    ::= { hmStatusWlanMngmtApConfNetwprofilsEntry 42 }

-- {COLUMN} 1.3.6.1.4.1.248.32.18.1.73.2.1.1.43
hmStatusWlanMngmtApConfNetwprofilsEntryProtMgmtFrames OBJECT-TYPE
    SYNTAX     INTEGER {
                  eNo (0),
                  eOptional (1),
                  eMandatory (2)
            }
    MAX-ACCESS read-only
    STATUS     current
    DESCRIPTION
            "-- empty --"
    ::= { hmStatusWlanMngmtApConfNetwprofilsEntry 43 }

-- {COLUMN} 1.3.6.1.4.1.248.32.18.1.73.2.1.1.44
hmStatusWlanMngmtApConfNetwprofilsEntryTxLimit OBJECT-TYPE
    SYNTAX     Integer32 (0..2147483647)
    MAX-ACCESS read-only
    STATUS     current
    DESCRIPTION
            "-- empty --"
    ::= { hmStatusWlanMngmtApConfNetwprofilsEntry 44 }

-- {COLUMN} 1.3.6.1.4.1.248.32.18.1.73.2.1.1.45
hmStatusWlanMngmtApConfNetwprofilsEntryRxLimit OBJECT-TYPE
    SYNTAX     Integer32 (0..2147483647)
    MAX-ACCESS read-only
    STATUS     current
    DESCRIPTION
            "-- empty --"
    ::= { hmStatusWlanMngmtApConfNetwprofilsEntry 45 }

-- {COLUMN} 1.3.6.1.4.1.248.32.18.1.73.2.1.1.46
hmStatusWlanMngmtApConfNetwprofilsEntryLbsTracking OBJECT-TYPE
    SYNTAX     INTEGER {
                  eNo (0),
                  eYes (1)
            }
    MAX-ACCESS read-only
    STATUS     current
    DESCRIPTION
            "-- empty --"
    ::= { hmStatusWlanMngmtApConfNetwprofilsEntry 46 }

-- {COLUMN} 1.3.6.1.4.1.248.32.18.1.73.2.1.1.47
hmStatusWlanMngmtApConfNetwprofilsEntryLbsTrackingList OBJECT-TYPE
    SYNTAX     DisplayString (SIZE(0..32))
    MAX-ACCESS read-only
    STATUS     current
    DESCRIPTION
            "-- empty --"
    ::= { hmStatusWlanMngmtApConfNetwprofilsEntry 47 }

-- {COLUMN} 1.3.6.1.4.1.248.32.18.1.73.2.1.1.48
hmStatusWlanMngmtApConfNetwprofilsEntryClBrgRoamingSupport OBJECT-TYPE
    SYNTAX     INTEGER {
                  eNo (0),
                  eYes (1)
            }
    MAX-ACCESS read-only
    STATUS     current
    DESCRIPTION
            "-- empty --"
    ::= { hmStatusWlanMngmtApConfNetwprofilsEntry 48 }

-- {TABLE} 1.3.6.1.4.1.248.32.18.1.73.2.2
hmStatusWlanMngmtApConfRadioprofilsTable OBJECT-TYPE
    SYNTAX     SEQUENCE OF HmStatusWlanMngmtApConfRadioprofilsEntry
    MAX-ACCESS not-accessible
    STATUS     current
    DESCRIPTION
            ""
    ::= { hmStatusWlanMngmtApConf 2 }

-- {ROW} 1.3.6.1.4.1.248.32.18.1.73.2.2.1
hmStatusWlanMngmtApConfRadioprofilsEntry OBJECT-TYPE
    SYNTAX     HmStatusWlanMngmtApConfRadioprofilsEntry
    MAX-ACCESS not-accessible
    STATUS     current
    DESCRIPTION
            ""
    INDEX {
            hmStatusWlanMngmtApConfRadioprofilsEntryName
          }
    ::= { hmStatusWlanMngmtApConfRadioprofilsTable 1 }

HmStatusWlanMngmtApConfRadioprofilsEntry ::= SEQUENCE {
            hmStatusWlanMngmtApConfRadioprofilsEntryName DisplayString,
            hmStatusWlanMngmtApConfRadioprofilsEntryCountry INTEGER,
            hmStatusWlanMngmtApConfRadioprofilsEntryChannelList DisplayString,
            hmStatusWlanMngmtApConfRadioprofilsEntry24ghzMode INTEGER,
            hmStatusWlanMngmtApConfRadioprofilsEntry5ghzMode INTEGER,
            hmStatusWlanMngmtApConfRadioprofilsEntrySubbands INTEGER,
            hmStatusWlanMngmtApConfRadioprofilsEntryQos INTEGER,
            hmStatusWlanMngmtApConfRadioprofilsEntryDtimPeriod Integer32,
            hmStatusWlanMngmtApConfRadioprofilsEntryBackgroundScan Integer32,
            hmStatusWlanMngmtApConfRadioprofilsEntryAntennaGain Integer32,
            hmStatusWlanMngmtApConfRadioprofilsEntryTxPowerReduction Integer32,
            hmStatusWlanMngmtApConfRadioprofilsEntryMgmtVLANId Integer32,
            hmStatusWlanMngmtApConfRadioprofilsEntryIndoorOnlyOperation INTEGER,
            hmStatusWlanMngmtApConfRadioprofilsEntryActVlanModOfMngdAps INTEGER,
            hmStatusWlanMngmtApConfRadioprofilsEntryMgmtVlanMode INTEGER,
            hmStatusWlanMngmtApConfRadioprofilsEntryMgmtVLANIdnew Integer32,
            hmStatusWlanMngmtApConfRadioprofilsEntryReportSeenClients INTEGER,
            hmStatusWlanMngmtApConfRadioprofilsEntryClientSteering INTEGER,
            hmStatusWlanMngmtApConfRadioprofilsEntryPreferredBand INTEGER,
            hmStatusWlanMngmtApConfRadioprofilsEntryPrReqAgeO Integer32
    }

-- {COLUMN} 1.3.6.1.4.1.248.32.18.1.73.2.2.1.1
hmStatusWlanMngmtApConfRadioprofilsEntryName OBJECT-TYPE
    SYNTAX     DisplayString (SIZE(0..31))
    MAX-ACCESS read-only
    STATUS     current
    DESCRIPTION
            "-- empty --"
    ::= { hmStatusWlanMngmtApConfRadioprofilsEntry 1 }

-- {COLUMN} 1.3.6.1.4.1.248.32.18.1.73.2.2.1.4
hmStatusWlanMngmtApConfRadioprofilsEntryCountry OBJECT-TYPE
    SYNTAX     INTEGER {
                  eDefault (0),
                  eAlbania (8),
                  eAlgeria (12),
                  eArgentina (32),
                  eAustralia (36),
                  eAustria (40),
                  eBahrain (48),
                  eBangladesh (50),
                  eBelgium (56),
                  eBosniaHerzegovina (70),
                  eBrazil (76),
                  eBruneiDarussalam (96),
                  eBulgaria (100),
                  eBelarus (112),
                  eCanada (124),
                  eChile (152),
                  eChina (156),
                  eTaiwan (158),
                  eColombia (170),
                  eCostaRica (188),
                  eCroatia (191),
                  eCyprus (196),
                  eCzech (203),
                  eDenmark (208),
                  eEcuador (218),
                  eEstonia (233),
                  eFinland (246),
                  eFrance (250),
                  eGermany (276),
                  eGhana (288),
                  eGreece (300),
                  eGuatemala (320),
                  eHonduras (340),
                  eHongKong (344),
                  eHungary (348),
                  eIceland (352),
                  eIndia (356),
                  eIndonesia (360),
                  eIreland (372),
                  eIsrael (376),
                  eItaly (380),
                  eJapan (392),
                  eJordan (400),
                  eSouthKorea (410),
                  eKuwait (414),
                  eLebanon (422),
                  eLatvia (428),
                  eLiechtenstein (438),
                  eLithuania (440),
                  eLuxembourg (442),
                  eMacau (446),
                  eMalaysia (458),
                  eMalta (470),
                  eMexico (484),
                  eMoldavia (498),
                  eMorocco (504),
                  eOman (512),
                  eNetherlands (528),
                  eNewZealand (554),
                  eNicaragua (558),
                  eNorway (578),
                  ePakistan (586),
                  ePanama (591),
                  eParaguay (600),
                  ePeru (604),
                  ePhilippines (608),
                  ePoland (616),
                  ePortugal (620),
                  ePuertoRico (630),
                  eQatar (634),
                  eRomania (642),
                  eRussia (643),
                  eSaudiArabia (682),
                  eSingapore (702),
                  eSlovak (703),
                  eSlovenia (705),
                  eSouthAfrica (710),
                  eSpain (724),
                  eSweden (752),
                  eSwitzerland (756),
                  eThailand (764),
                  eUnitedArabEmirates (784),
                  eTunisia (788),
                  eTurkey (792),
                  eUganda (800),
                  eUkraine (804),
                  eMacedonia (807),
                  eEgypt (818),
                  eUnitedKingdom (826),
                  eTanzania (834),
                  eUnitedStatesFcc (840),
                  eUruguay (858),
                  eVenezuela (862),
                  eEurope (998),
                  eEgalistan (999)
            }
    MAX-ACCESS read-only
    STATUS     current
    DESCRIPTION
            "-- empty --"
    ::= { hmStatusWlanMngmtApConfRadioprofilsEntry 4 }

-- {COLUMN} 1.3.6.1.4.1.248.32.18.1.73.2.2.1.5
hmStatusWlanMngmtApConfRadioprofilsEntryChannelList OBJECT-TYPE
    SYNTAX     DisplayString (SIZE(0..48))
    MAX-ACCESS read-only
    STATUS     current
    DESCRIPTION
            "-- empty --"
    ::= { hmStatusWlanMngmtApConfRadioprofilsEntry 5 }

-- {COLUMN} 1.3.6.1.4.1.248.32.18.1.73.2.2.1.6
hmStatusWlanMngmtApConfRadioprofilsEntry24ghzMode OBJECT-TYPE
    SYNTAX     INTEGER {
                  e11bgMixed (0),
                  e11gOnly (1),
                  e11bOnly (2),
                  e108mbps (3),
                  e11bgnMixed (4),
                  e11gnMixed (5),
                  eGreenfield (6),
                  eAuto (255)
            }
    MAX-ACCESS read-only
    STATUS     current
    DESCRIPTION
            "-- empty --"
    ::= { hmStatusWlanMngmtApConfRadioprofilsEntry 6 }

-- {COLUMN} 1.3.6.1.4.1.248.32.18.1.73.2.2.1.7
hmStatusWlanMngmtApConfRadioprofilsEntry5ghzMode OBJECT-TYPE
    SYNTAX     INTEGER {
                  eNormal (0),
                  e108mbps (3),
                  e11anMixed (4),
                  eGreenfield (5),
                  e11anacMixed (6),
                  e11nacMixed (7),
                  e11acOnly (8),
                  eAuto (255)
            }
    MAX-ACCESS read-only
    STATUS     current
    DESCRIPTION
            "-- empty --"
    ::= { hmStatusWlanMngmtApConfRadioprofilsEntry 7 }

-- {COLUMN} 1.3.6.1.4.1.248.32.18.1.73.2.2.1.8
hmStatusWlanMngmtApConfRadioprofilsEntrySubbands OBJECT-TYPE
    SYNTAX     INTEGER {
                  eBand1Plus2Plus3 (0),
                  eBand1 (1),
                  eBand2 (2),
                  eBand3 (3),
                  eBand1Plus2 (4),
                  eBand1Plus3 (5),
                  eBand2Plus3 (6)
            }
    MAX-ACCESS read-only
    STATUS     current
    DESCRIPTION
            "-- empty --"
    ::= { hmStatusWlanMngmtApConfRadioprofilsEntry 8 }

-- {COLUMN} 1.3.6.1.4.1.248.32.18.1.73.2.2.1.9
hmStatusWlanMngmtApConfRadioprofilsEntryQos OBJECT-TYPE
    SYNTAX     INTEGER {
                  eNo (0),
                  eYes (1)
            }
    MAX-ACCESS read-only
    STATUS     current
    DESCRIPTION
            "-- empty --"
    ::= { hmStatusWlanMngmtApConfRadioprofilsEntry 9 }

-- {COLUMN} 1.3.6.1.4.1.248.32.18.1.73.2.2.1.10
hmStatusWlanMngmtApConfRadioprofilsEntryDtimPeriod OBJECT-TYPE
    SYNTAX     Integer32 (0..255)
    MAX-ACCESS read-only
    STATUS     current
    DESCRIPTION
            "-- empty --"
    ::= { hmStatusWlanMngmtApConfRadioprofilsEntry 10 }

-- {COLUMN} 1.3.6.1.4.1.248.32.18.1.73.2.2.1.11
hmStatusWlanMngmtApConfRadioprofilsEntryBackgroundScan OBJECT-TYPE
    SYNTAX     Integer32 (0..2147483647)
    MAX-ACCESS read-only
    STATUS     current
    DESCRIPTION
            "-- empty --"
    ::= { hmStatusWlanMngmtApConfRadioprofilsEntry 11 }

-- {COLUMN} 1.3.6.1.4.1.248.32.18.1.73.2.2.1.12
hmStatusWlanMngmtApConfRadioprofilsEntryAntennaGain OBJECT-TYPE
    SYNTAX     Integer32 (-128..127)
    MAX-ACCESS read-only
    STATUS     current
    DESCRIPTION
            "-- empty --"
    ::= { hmStatusWlanMngmtApConfRadioprofilsEntry 12 }

-- {COLUMN} 1.3.6.1.4.1.248.32.18.1.73.2.2.1.13
hmStatusWlanMngmtApConfRadioprofilsEntryTxPowerReduction OBJECT-TYPE
    SYNTAX     Integer32 (0..255)
    MAX-ACCESS read-only
    STATUS     current
    DESCRIPTION
            "-- empty --"
    ::= { hmStatusWlanMngmtApConfRadioprofilsEntry 13 }

-- {COLUMN} 1.3.6.1.4.1.248.32.18.1.73.2.2.1.14
hmStatusWlanMngmtApConfRadioprofilsEntryMgmtVLANId OBJECT-TYPE
    SYNTAX     Integer32 (0..65535)
    MAX-ACCESS read-only
    STATUS     obsolete
    DESCRIPTION
            ""
    ::= { hmStatusWlanMngmtApConfRadioprofilsEntry 14 }

-- {COLUMN} 1.3.6.1.4.1.248.32.18.1.73.2.2.1.16
hmStatusWlanMngmtApConfRadioprofilsEntryIndoorOnlyOperation OBJECT-TYPE
    SYNTAX     INTEGER {
                  eNo (0),
                  eYes (1)
            }
    MAX-ACCESS read-only
    STATUS     current
    DESCRIPTION
            "-- empty --"
    ::= { hmStatusWlanMngmtApConfRadioprofilsEntry 16 }

-- {COLUMN} 1.3.6.1.4.1.248.32.18.1.73.2.2.1.17
hmStatusWlanMngmtApConfRadioprofilsEntryActVlanModOfMngdAps OBJECT-TYPE
    SYNTAX     INTEGER {
                  eNo (0),
                  eYes (1)
            }
    MAX-ACCESS read-only
    STATUS     current
    DESCRIPTION
            ""
    ::= { hmStatusWlanMngmtApConfRadioprofilsEntry 17 }

-- {COLUMN} 1.3.6.1.4.1.248.32.18.1.73.2.2.1.18
hmStatusWlanMngmtApConfRadioprofilsEntryMgmtVlanMode OBJECT-TYPE
    SYNTAX     INTEGER {
                  eUntagged (0),
                  eTagged (1)
            }
    MAX-ACCESS read-only
    STATUS     current
    DESCRIPTION
            "-- empty --"
    ::= { hmStatusWlanMngmtApConfRadioprofilsEntry 18 }

-- {COLUMN} 1.3.6.1.4.1.248.32.18.1.73.2.2.1.19
hmStatusWlanMngmtApConfRadioprofilsEntryMgmtVLANIdnew OBJECT-TYPE
    SYNTAX     Integer32 (0..65535)
    MAX-ACCESS read-only
    STATUS     current
    DESCRIPTION
            ""
    ::= { hmStatusWlanMngmtApConfRadioprofilsEntry 19 }

-- {COLUMN} 1.3.6.1.4.1.248.32.18.1.73.2.2.1.20
hmStatusWlanMngmtApConfRadioprofilsEntryReportSeenClients OBJECT-TYPE
    SYNTAX     INTEGER {
                  eNo (0),
                  eYes (1)
            }
    MAX-ACCESS read-only
    STATUS     current
    DESCRIPTION
            "-- empty --"
    ::= { hmStatusWlanMngmtApConfRadioprofilsEntry 20 }

-- {COLUMN} 1.3.6.1.4.1.248.32.18.1.73.2.2.1.21
hmStatusWlanMngmtApConfRadioprofilsEntryClientSteering OBJECT-TYPE
    SYNTAX     INTEGER {
                  eOff (0),
                  eYes (1),
                  eOn (2)
            }
    MAX-ACCESS read-only
    STATUS     current
    DESCRIPTION
            "-- empty --"
    ::= { hmStatusWlanMngmtApConfRadioprofilsEntry 21 }

-- {COLUMN} 1.3.6.1.4.1.248.32.18.1.73.2.2.1.22
hmStatusWlanMngmtApConfRadioprofilsEntryPreferredBand OBJECT-TYPE
    SYNTAX     INTEGER {
                  e24ghz (1),
                  e5ghz (2)
            }
    MAX-ACCESS read-only
    STATUS     current
    DESCRIPTION
            "-- empty --"
    ::= { hmStatusWlanMngmtApConfRadioprofilsEntry 22 }

-- {COLUMN} 1.3.6.1.4.1.248.32.18.1.73.2.2.1.23
hmStatusWlanMngmtApConfRadioprofilsEntryPrReqAgeO OBJECT-TYPE
    SYNTAX     Integer32 (0..2147483647)
    MAX-ACCESS read-only
    STATUS     current
    DESCRIPTION
            ""
    ::= { hmStatusWlanMngmtApConfRadioprofilsEntry 23 }

-- {TABLE} 1.3.6.1.4.1.248.32.18.1.73.2.3
hmStatusWlanMngmtApConfCommonprofilsTable OBJECT-TYPE
    SYNTAX     SEQUENCE OF HmStatusWlanMngmtApConfCommonprofilsEntry
    MAX-ACCESS not-accessible
    STATUS     current
    DESCRIPTION
            ""
    ::= { hmStatusWlanMngmtApConf 3 }

-- {ROW} 1.3.6.1.4.1.248.32.18.1.73.2.3.1
hmStatusWlanMngmtApConfCommonprofilsEntry OBJECT-TYPE
    SYNTAX     HmStatusWlanMngmtApConfCommonprofilsEntry
    MAX-ACCESS not-accessible
    STATUS     current
    DESCRIPTION
            ""
    INDEX {
            hmStatusWlanMngmtApConfCommonprofilsEntryName
          }
    ::= { hmStatusWlanMngmtApConfCommonprofilsTable 1 }

HmStatusWlanMngmtApConfCommonprofilsEntry ::= SEQUENCE {
            hmStatusWlanMngmtApConfCommonprofilsEntryName DisplayString,
            hmStatusWlanMngmtApConfCommonprofilsEntryNetw DisplayString,
            hmStatusWlanMngmtApConfCommonprofilsEntryApParams DisplayString,
            hmStatusWlanMngmtApConfCommonprofilsEntryContr DisplayString,
            hmStatusWlanMngmtApConfCommonprofilsEntryIeee80211uGeneral DisplayString,
            hmStatusWlanMngmtApConfCommonprofilsEntryConfigurationDelay Integer32,
            hmStatusWlanMngmtApConfCommonprofilsEntryLedProfile DisplayString,
            hmStatusWlanMngmtApConfCommonprofilsEntryLbsGeneralProfile DisplayString,
            hmStatusWlanMngmtApConfCommonprofilsEntryWirelessEpaperProfile DisplayString,
            hmStatusWlanMngmtApConfCommonprofilsEntryWIds DisplayString
    }

-- {COLUMN} 1.3.6.1.4.1.248.32.18.1.73.2.3.1.1
hmStatusWlanMngmtApConfCommonprofilsEntryName OBJECT-TYPE
    SYNTAX     DisplayString (SIZE(0..31))
    MAX-ACCESS read-only
    STATUS     current
    DESCRIPTION
            "-- empty --"
    ::= { hmStatusWlanMngmtApConfCommonprofilsEntry 1 }

-- {COLUMN} 1.3.6.1.4.1.248.32.18.1.73.2.3.1.2
hmStatusWlanMngmtApConfCommonprofilsEntryNetw OBJECT-TYPE
    SYNTAX     DisplayString (SIZE(0..251))
    MAX-ACCESS read-only
    STATUS     current
    DESCRIPTION
            ""
    ::= { hmStatusWlanMngmtApConfCommonprofilsEntry 2 }

-- {COLUMN} 1.3.6.1.4.1.248.32.18.1.73.2.3.1.3
hmStatusWlanMngmtApConfCommonprofilsEntryApParams OBJECT-TYPE
    SYNTAX     DisplayString (SIZE(0..31))
    MAX-ACCESS read-only
    STATUS     current
    DESCRIPTION
            ""
    ::= { hmStatusWlanMngmtApConfCommonprofilsEntry 3 }

-- {COLUMN} 1.3.6.1.4.1.248.32.18.1.73.2.3.1.4
hmStatusWlanMngmtApConfCommonprofilsEntryContr OBJECT-TYPE
    SYNTAX     DisplayString (SIZE(0..159))
    MAX-ACCESS read-only
    STATUS     current
    DESCRIPTION
            ""
    ::= { hmStatusWlanMngmtApConfCommonprofilsEntry 4 }

-- {COLUMN} 1.3.6.1.4.1.248.32.18.1.73.2.3.1.6
hmStatusWlanMngmtApConfCommonprofilsEntryIeee80211uGeneral OBJECT-TYPE
    SYNTAX     DisplayString (SIZE(0..32))
    MAX-ACCESS read-only
    STATUS     current
    DESCRIPTION
            "-- empty --"
    ::= { hmStatusWlanMngmtApConfCommonprofilsEntry 6 }

-- {COLUMN} 1.3.6.1.4.1.248.32.18.1.73.2.3.1.7
hmStatusWlanMngmtApConfCommonprofilsEntryConfigurationDelay OBJECT-TYPE
    SYNTAX     Integer32 (0..2147483647)
    MAX-ACCESS read-only
    STATUS     current
    DESCRIPTION
            "-- empty --"
    ::= { hmStatusWlanMngmtApConfCommonprofilsEntry 7 }

-- {COLUMN} 1.3.6.1.4.1.248.32.18.1.73.2.3.1.8
hmStatusWlanMngmtApConfCommonprofilsEntryLedProfile OBJECT-TYPE
    SYNTAX     DisplayString (SIZE(0..31))
    MAX-ACCESS read-only
    STATUS     current
    DESCRIPTION
            "-- empty --"
    ::= { hmStatusWlanMngmtApConfCommonprofilsEntry 8 }

-- {COLUMN} 1.3.6.1.4.1.248.32.18.1.73.2.3.1.9
hmStatusWlanMngmtApConfCommonprofilsEntryLbsGeneralProfile OBJECT-TYPE
    SYNTAX     DisplayString (SIZE(0..32))
    MAX-ACCESS read-only
    STATUS     current
    DESCRIPTION
            "-- empty --"
    ::= { hmStatusWlanMngmtApConfCommonprofilsEntry 9 }

-- {COLUMN} 1.3.6.1.4.1.248.32.18.1.73.2.3.1.10
hmStatusWlanMngmtApConfCommonprofilsEntryWirelessEpaperProfile OBJECT-TYPE
    SYNTAX     DisplayString (SIZE(0..31))
    MAX-ACCESS read-only
    STATUS     current
    DESCRIPTION
            "-- empty --"
    ::= { hmStatusWlanMngmtApConfCommonprofilsEntry 10 }

-- {COLUMN} 1.3.6.1.4.1.248.32.18.1.73.2.3.1.248
hmStatusWlanMngmtApConfCommonprofilsEntryWIds OBJECT-TYPE
    SYNTAX     DisplayString (SIZE(0..32))
    MAX-ACCESS read-only
    STATUS     current
    DESCRIPTION
            ""
    ::= { hmStatusWlanMngmtApConfCommonprofilsEntry 248 }

-- {TABLE} 1.3.6.1.4.1.248.32.18.1.73.2.4
hmStatusWlanMngmtApConfApsTable OBJECT-TYPE
    SYNTAX     SEQUENCE OF HmStatusWlanMngmtApConfApsEntry
    MAX-ACCESS not-accessible
    STATUS     current
    DESCRIPTION
            "accesspoints"
    ::= { hmStatusWlanMngmtApConf 4 }

-- {ROW} 1.3.6.1.4.1.248.32.18.1.73.2.4.1
hmStatusWlanMngmtApConfApsEntry OBJECT-TYPE
    SYNTAX     HmStatusWlanMngmtApConfApsEntry
    MAX-ACCESS not-accessible
    STATUS     current
    DESCRIPTION
            ""
    INDEX {
            hmStatusWlanMngmtApConfApsEntryMacAddress
          }
    ::= { hmStatusWlanMngmtApConfApsTable 1 }

HmStatusWlanMngmtApConfApsEntry ::= SEQUENCE {
            hmStatusWlanMngmtApConfApsEntryMacAddress DisplayString,
            hmStatusWlanMngmtApConfApsEntryName DisplayString,
            hmStatusWlanMngmtApConfApsEntryLocation DisplayString,
            hmStatusWlanMngmtApConfApsEntryProfile DisplayString,
            hmStatusWlanMngmtApConfApsEntryDeviceParameters DisplayString,
            hmStatusWlanMngmtApConfApsEntryEncryption INTEGER,
            hmStatusWlanMngmtApConfApsEntryWlanModule1 INTEGER,
            hmStatusWlanMngmtApConfApsEntryWlanModule2 INTEGER,
            hmStatusWlanMngmtApConfApsEntryModule1ChannelList DisplayString,
            hmStatusWlanMngmtApConfApsEntryModule2ChannelList DisplayString,
            hmStatusWlanMngmtApConfApsEntryOperating INTEGER,
            hmStatusWlanMngmtApConfApsEntryIpAddress IpAddress,
            hmStatusWlanMngmtApConfApsEntryNetmask IpAddress,
            hmStatusWlanMngmtApConfApsEntryGateway IpAddress,
            hmStatusWlanMngmtApConfApsEntryAllow40mhz INTEGER,
            hmStatusWlanMngmtApConfApsEntryAntennaMask INTEGER,
            hmStatusWlanMngmtApConfApsEntryApIntranet DisplayString,
            hmStatusWlanMngmtApConfApsEntryManageFirmware INTEGER,
            hmStatusWlanMngmtApConfApsEntryMngmtFwAddInfo INTEGER,
            hmStatusWlanMngmtApConfApsEntryModule1AntGain DisplayString,
            hmStatusWlanMngmtApConfApsEntryModule2AntGain DisplayString,
            hmStatusWlanMngmtApConfApsEntryModule1TxReduct DisplayString,
            hmStatusWlanMngmtApConfApsEntryModule2TxReduct DisplayString,
            hmStatusWlanMngmtApConfApsEntryGroup DisplayString,
            hmStatusWlanMngmtApConfApsEntryModule2MaxChannelBandwidth INTEGER,
            hmStatusWlanMngmtApConfApsEntryModule1MaxChannelBandwidth INTEGER,
            hmStatusWlanMngmtApConfApsEntryClientSteeringProfile DisplayString,
            hmStatusWlanMngmtApConfApsEntryLbsDeviceLocationProfile DisplayString,
            hmStatusWlanMngmtApConfApsEntryWirelessEpaperChannel INTEGER,
            hmStatusWlanMngmtApConfApsEntryIbeaconProfile DisplayString,
            hmStatusWlanMngmtApConfApsEntryIbeaconChannel BITS,
            hmStatusWlanMngmtApConfApsEntryMinor Integer32,
            hmStatusWlanMngmtApConfApsEntryIbeaconTransmitPower INTEGER
    }

-- {COLUMN} 1.3.6.1.4.1.248.32.18.1.73.2.4.1.1
hmStatusWlanMngmtApConfApsEntryMacAddress OBJECT-TYPE
    SYNTAX     DisplayString (SIZE(0..12))
    MAX-ACCESS read-only
    STATUS     current
    DESCRIPTION
            "-- empty --"
    ::= { hmStatusWlanMngmtApConfApsEntry 1 }

-- {COLUMN} 1.3.6.1.4.1.248.32.18.1.73.2.4.1.2
hmStatusWlanMngmtApConfApsEntryName OBJECT-TYPE
    SYNTAX     DisplayString (SIZE(0..16))
    MAX-ACCESS read-only
    STATUS     current
    DESCRIPTION
            "-- empty --"
    ::= { hmStatusWlanMngmtApConfApsEntry 2 }

-- {COLUMN} 1.3.6.1.4.1.248.32.18.1.73.2.4.1.3
hmStatusWlanMngmtApConfApsEntryLocation OBJECT-TYPE
    SYNTAX     DisplayString (SIZE(0..251))
    MAX-ACCESS read-only
    STATUS     current
    DESCRIPTION
            "-- empty --"
    ::= { hmStatusWlanMngmtApConfApsEntry 3 }

-- {COLUMN} 1.3.6.1.4.1.248.32.18.1.73.2.4.1.4
hmStatusWlanMngmtApConfApsEntryProfile OBJECT-TYPE
    SYNTAX     DisplayString (SIZE(0..31))
    MAX-ACCESS read-only
    STATUS     current
    DESCRIPTION
            "-- empty --"
    ::= { hmStatusWlanMngmtApConfApsEntry 4 }

-- {COLUMN} 1.3.6.1.4.1.248.32.18.1.73.2.4.1.5
hmStatusWlanMngmtApConfApsEntryDeviceParameters OBJECT-TYPE
    SYNTAX     DisplayString (SIZE(0..31))
    MAX-ACCESS read-only
    STATUS     current
    DESCRIPTION
            "-- empty --"
    ::= { hmStatusWlanMngmtApConfApsEntry 5 }

-- {COLUMN} 1.3.6.1.4.1.248.32.18.1.73.2.4.1.6
hmStatusWlanMngmtApConfApsEntryEncryption OBJECT-TYPE
    SYNTAX     INTEGER {
                  eDefault (0),
                  eDtls (1),
                  eNo (2)
            }
    MAX-ACCESS read-only
    STATUS     current
    DESCRIPTION
            "encryption setting for control connection"
    ::= { hmStatusWlanMngmtApConfApsEntry 6 }

-- {COLUMN} 1.3.6.1.4.1.248.32.18.1.73.2.4.1.7
hmStatusWlanMngmtApConfApsEntryWlanModule1 OBJECT-TYPE
    SYNTAX     INTEGER {
                  eDefault (0),
                  e24ghz (1),
                  e5ghz (2),
                  eOff (3),
                  eAuto (255)
            }
    MAX-ACCESS read-only
    STATUS     current
    DESCRIPTION
            "-- empty --"
    ::= { hmStatusWlanMngmtApConfApsEntry 7 }

-- {COLUMN} 1.3.6.1.4.1.248.32.18.1.73.2.4.1.8
hmStatusWlanMngmtApConfApsEntryWlanModule2 OBJECT-TYPE
    SYNTAX     INTEGER {
                  eDefault (0),
                  e24ghz (1),
                  e5ghz (2),
                  eOff (3),
                  eAuto (255)
            }
    MAX-ACCESS read-only
    STATUS     current
    DESCRIPTION
            "-- empty --"
    ::= { hmStatusWlanMngmtApConfApsEntry 8 }

-- {COLUMN} 1.3.6.1.4.1.248.32.18.1.73.2.4.1.9
hmStatusWlanMngmtApConfApsEntryModule1ChannelList OBJECT-TYPE
    SYNTAX     DisplayString (SIZE(0..48))
    MAX-ACCESS read-only
    STATUS     current
    DESCRIPTION
            "-- empty --"
    ::= { hmStatusWlanMngmtApConfApsEntry 9 }

-- {COLUMN} 1.3.6.1.4.1.248.32.18.1.73.2.4.1.10
hmStatusWlanMngmtApConfApsEntryModule2ChannelList OBJECT-TYPE
    SYNTAX     DisplayString (SIZE(0..48))
    MAX-ACCESS read-only
    STATUS     current
    DESCRIPTION
            "-- empty --"
    ::= { hmStatusWlanMngmtApConfApsEntry 10 }

-- {COLUMN} 1.3.6.1.4.1.248.32.18.1.73.2.4.1.11
hmStatusWlanMngmtApConfApsEntryOperating OBJECT-TYPE
    SYNTAX     INTEGER {
                  eYes (0),
                  eNo (1)
            }
    MAX-ACCESS read-only
    STATUS     current
    DESCRIPTION
            "-- empty --"
    ::= { hmStatusWlanMngmtApConfApsEntry 11 }

-- {COLUMN} 1.3.6.1.4.1.248.32.18.1.73.2.4.1.12
hmStatusWlanMngmtApConfApsEntryIpAddress OBJECT-TYPE
    SYNTAX     IpAddress
    MAX-ACCESS read-only
    STATUS     current
    DESCRIPTION
            "-- empty --"
    ::= { hmStatusWlanMngmtApConfApsEntry 12 }

-- {COLUMN} 1.3.6.1.4.1.248.32.18.1.73.2.4.1.13
hmStatusWlanMngmtApConfApsEntryNetmask OBJECT-TYPE
    SYNTAX     IpAddress
    MAX-ACCESS read-only
    STATUS     current
    DESCRIPTION
            "-- empty --"
    ::= { hmStatusWlanMngmtApConfApsEntry 13 }

-- {COLUMN} 1.3.6.1.4.1.248.32.18.1.73.2.4.1.14
hmStatusWlanMngmtApConfApsEntryGateway OBJECT-TYPE
    SYNTAX     IpAddress
    MAX-ACCESS read-only
    STATUS     current
    DESCRIPTION
            "-- empty --"
    ::= { hmStatusWlanMngmtApConfApsEntry 14 }

-- {COLUMN} 1.3.6.1.4.1.248.32.18.1.73.2.4.1.15
hmStatusWlanMngmtApConfApsEntryAllow40mhz OBJECT-TYPE
    SYNTAX     INTEGER {
                  eAuto (0),
                  eNo (1)
            }
    MAX-ACCESS read-only
    STATUS     current
    DESCRIPTION
            "-- empty --"
    ::= { hmStatusWlanMngmtApConfApsEntry 15 }

-- {COLUMN} 1.3.6.1.4.1.248.32.18.1.73.2.4.1.16
hmStatusWlanMngmtApConfApsEntryAntennaMask OBJECT-TYPE
    SYNTAX     INTEGER {
                  eAuto (0),
                  eAntenna1 (1),
                  eAntenna1Plus2 (3),
                  eAntenna1Plus3 (5),
                  eAntenna1Plus2Plus3 (7)
            }
    MAX-ACCESS read-only
    STATUS     current
    DESCRIPTION
            "-- empty --"
    ::= { hmStatusWlanMngmtApConfApsEntry 16 }

-- {COLUMN} 1.3.6.1.4.1.248.32.18.1.73.2.4.1.17
hmStatusWlanMngmtApConfApsEntryApIntranet OBJECT-TYPE
    SYNTAX     DisplayString (SIZE(0..31))
    MAX-ACCESS read-only
    STATUS     current
    DESCRIPTION
            "-- empty --"
    ::= { hmStatusWlanMngmtApConfApsEntry 17 }

-- {COLUMN} 1.3.6.1.4.1.248.32.18.1.73.2.4.1.18
hmStatusWlanMngmtApConfApsEntryManageFirmware OBJECT-TYPE
    SYNTAX     INTEGER {
                  eYes (0),
                  eNo (1)
            }
    MAX-ACCESS read-only
    STATUS     current
    DESCRIPTION
            "-- empty --"
    ::= { hmStatusWlanMngmtApConfApsEntry 18 }

-- {COLUMN} 1.3.6.1.4.1.248.32.18.1.73.2.4.1.19
hmStatusWlanMngmtApConfApsEntryMngmtFwAddInfo OBJECT-TYPE
    SYNTAX     INTEGER {
                  eDisabledDueToErrorDuringUpdate (1),
                  eDisabledByManualUpload (2)
            }
    MAX-ACCESS read-only
    STATUS     current
    DESCRIPTION
            ""
    ::= { hmStatusWlanMngmtApConfApsEntry 19 }

-- {COLUMN} 1.3.6.1.4.1.248.32.18.1.73.2.4.1.20
hmStatusWlanMngmtApConfApsEntryModule1AntGain OBJECT-TYPE
    SYNTAX     DisplayString (SIZE(0..4))
    MAX-ACCESS read-only
    STATUS     current
    DESCRIPTION
            "-- empty --"
    ::= { hmStatusWlanMngmtApConfApsEntry 20 }

-- {COLUMN} 1.3.6.1.4.1.248.32.18.1.73.2.4.1.21
hmStatusWlanMngmtApConfApsEntryModule2AntGain OBJECT-TYPE
    SYNTAX     DisplayString (SIZE(0..4))
    MAX-ACCESS read-only
    STATUS     current
    DESCRIPTION
            "-- empty --"
    ::= { hmStatusWlanMngmtApConfApsEntry 21 }

-- {COLUMN} 1.3.6.1.4.1.248.32.18.1.73.2.4.1.22
hmStatusWlanMngmtApConfApsEntryModule1TxReduct OBJECT-TYPE
    SYNTAX     DisplayString (SIZE(0..3))
    MAX-ACCESS read-only
    STATUS     current
    DESCRIPTION
            "-- empty --"
    ::= { hmStatusWlanMngmtApConfApsEntry 22 }

-- {COLUMN} 1.3.6.1.4.1.248.32.18.1.73.2.4.1.23
hmStatusWlanMngmtApConfApsEntryModule2TxReduct OBJECT-TYPE
    SYNTAX     DisplayString (SIZE(0..3))
    MAX-ACCESS read-only
    STATUS     current
    DESCRIPTION
            "-- empty --"
    ::= { hmStatusWlanMngmtApConfApsEntry 23 }

-- {COLUMN} 1.3.6.1.4.1.248.32.18.1.73.2.4.1.24
hmStatusWlanMngmtApConfApsEntryGroup OBJECT-TYPE
    SYNTAX     DisplayString (SIZE(0..251))
    MAX-ACCESS read-only
    STATUS     current
    DESCRIPTION
            "-- empty --"
    ::= { hmStatusWlanMngmtApConfApsEntry 24 }

-- {COLUMN} 1.3.6.1.4.1.248.32.18.1.73.2.4.1.25
hmStatusWlanMngmtApConfApsEntryModule2MaxChannelBandwidth OBJECT-TYPE
    SYNTAX     INTEGER {
                  e20mhz (0),
                  e40mhz (1),
                  e80mhz (2),
                  eAuto (255)
            }
    MAX-ACCESS read-only
    STATUS     current
    DESCRIPTION
            "-- empty --"
    ::= { hmStatusWlanMngmtApConfApsEntry 25 }

-- {COLUMN} 1.3.6.1.4.1.248.32.18.1.73.2.4.1.26
hmStatusWlanMngmtApConfApsEntryModule1MaxChannelBandwidth OBJECT-TYPE
    SYNTAX     INTEGER {
                  e20mhz (0),
                  e40mhz (1),
                  e80mhz (2),
                  eAuto (255)
            }
    MAX-ACCESS read-only
    STATUS     current
    DESCRIPTION
            "-- empty --"
    ::= { hmStatusWlanMngmtApConfApsEntry 26 }

-- {COLUMN} 1.3.6.1.4.1.248.32.18.1.73.2.4.1.27
hmStatusWlanMngmtApConfApsEntryClientSteeringProfile OBJECT-TYPE
    SYNTAX     DisplayString (SIZE(0..31))
    MAX-ACCESS read-only
    STATUS     current
    DESCRIPTION
            "-- empty --"
    ::= { hmStatusWlanMngmtApConfApsEntry 27 }

-- {COLUMN} 1.3.6.1.4.1.248.32.18.1.73.2.4.1.28
hmStatusWlanMngmtApConfApsEntryLbsDeviceLocationProfile OBJECT-TYPE
    SYNTAX     DisplayString (SIZE(0..32))
    MAX-ACCESS read-only
    STATUS     current
    DESCRIPTION
            "-- empty --"
    ::= { hmStatusWlanMngmtApConfApsEntry 28 }

-- {COLUMN} 1.3.6.1.4.1.248.32.18.1.73.2.4.1.29
hmStatusWlanMngmtApConfApsEntryWirelessEpaperChannel OBJECT-TYPE
    SYNTAX     INTEGER {
                  e2404mhz (0),
                  e2410mhz (1),
                  e2422mhz (2),
                  e2425mhz (3),
                  e2442mhz (4),
                  e2450mhz (5),
                  e2462mhz (6),
                  e2470mhz (7),
                  e2474mhz (8),
                  e2477mhz (9),
                  e2480mhz (10),
                  eAuto (255)
            }
    MAX-ACCESS read-only
    STATUS     current
    DESCRIPTION
            "-- empty --"
    ::= { hmStatusWlanMngmtApConfApsEntry 29 }

-- {COLUMN} 1.3.6.1.4.1.248.32.18.1.73.2.4.1.30
hmStatusWlanMngmtApConfApsEntryIbeaconProfile OBJECT-TYPE
    SYNTAX     DisplayString (SIZE(0..31))
    MAX-ACCESS read-only
    STATUS     current
    DESCRIPTION
            "-- empty --"
    ::= { hmStatusWlanMngmtApConfApsEntry 30 }

-- {COLUMN} 1.3.6.1.4.1.248.32.18.1.73.2.4.1.31
hmStatusWlanMngmtApConfApsEntryIbeaconChannel OBJECT-TYPE
    SYNTAX     BITS {
                  e2480mhz (5),
                  e2426mhz (6),
                  e2402mhz (7)
            }
    MAX-ACCESS read-only
    STATUS     current
    DESCRIPTION
            "-- empty --"
    ::= { hmStatusWlanMngmtApConfApsEntry 31 }

-- {COLUMN} 1.3.6.1.4.1.248.32.18.1.73.2.4.1.32
hmStatusWlanMngmtApConfApsEntryMinor OBJECT-TYPE
    SYNTAX     Integer32 (0..65535)
    MAX-ACCESS read-only
    STATUS     current
    DESCRIPTION
            "-- empty --"
    ::= { hmStatusWlanMngmtApConfApsEntry 32 }

-- {COLUMN} 1.3.6.1.4.1.248.32.18.1.73.2.4.1.33
hmStatusWlanMngmtApConfApsEntryIbeaconTransmitPower OBJECT-TYPE
    SYNTAX     INTEGER {
                  eLow (0),
                  eMedium (1),
                  eHigh (2)
            }
    MAX-ACCESS read-only
    STATUS     current
    DESCRIPTION
            "-- empty --"
    ::= { hmStatusWlanMngmtApConfApsEntry 33 }

-- {TABLE} 1.3.6.1.4.1.248.32.18.1.73.2.5
hmStatusWlanMngmtApConfNetwProfErrorsTable OBJECT-TYPE
    SYNTAX     SEQUENCE OF HmStatusWlanMngmtApConfNetwProfErrorsEntry
    MAX-ACCESS not-accessible
    STATUS     current
    DESCRIPTION
            "-- empty --"
    ::= { hmStatusWlanMngmtApConf 5 }

-- {ROW} 1.3.6.1.4.1.248.32.18.1.73.2.5.1
hmStatusWlanMngmtApConfNetwProfErrorsEntry OBJECT-TYPE
    SYNTAX     HmStatusWlanMngmtApConfNetwProfErrorsEntry
    MAX-ACCESS not-accessible
    STATUS     current
    DESCRIPTION
            ""
    INDEX {
            hmStatusWlanMngmtApConfNetwProfErrorsEntryIndex
          }
    ::= { hmStatusWlanMngmtApConfNetwProfErrorsTable 1 }

HmStatusWlanMngmtApConfNetwProfErrorsEntry ::= SEQUENCE {
            hmStatusWlanMngmtApConfNetwProfErrorsEntryIndex Integer32,
            hmStatusWlanMngmtApConfNetwProfErrorsEntryName DisplayString,
            hmStatusWlanMngmtApConfNetwProfErrorsEntryError INTEGER
    }

-- {COLUMN} 1.3.6.1.4.1.248.32.18.1.73.2.5.1.1
hmStatusWlanMngmtApConfNetwProfErrorsEntryIndex OBJECT-TYPE
    SYNTAX     Integer32 (0..2147483647)
    MAX-ACCESS read-only
    STATUS     current
    DESCRIPTION
            "-- empty --"
    ::= { hmStatusWlanMngmtApConfNetwProfErrorsEntry 1 }

-- {COLUMN} 1.3.6.1.4.1.248.32.18.1.73.2.5.1.2
hmStatusWlanMngmtApConfNetwProfErrorsEntryName OBJECT-TYPE
    SYNTAX     DisplayString (SIZE(0..31))
    MAX-ACCESS read-only
    STATUS     current
    DESCRIPTION
            "-- empty --"
    ::= { hmStatusWlanMngmtApConfNetwProfErrorsEntry 2 }

-- {COLUMN} 1.3.6.1.4.1.248.32.18.1.73.2.5.1.3
hmStatusWlanMngmtApConfNetwProfErrorsEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eAutowdsProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20)
            }
    MAX-ACCESS read-only
    STATUS     current
    DESCRIPTION
            "-- empty --"
    ::= { hmStatusWlanMngmtApConfNetwProfErrorsEntry 3 }

-- {TABLE} 1.3.6.1.4.1.248.32.18.1.73.2.6
hmStatusWlanMngmtApConfRadioProfErrorsTable OBJECT-TYPE
    SYNTAX     SEQUENCE OF HmStatusWlanMngmtApConfRadioProfErrorsEntry
    MAX-ACCESS not-accessible
    STATUS     current
    DESCRIPTION
            "-- empty --"
    ::= { hmStatusWlanMngmtApConf 6 }

-- {ROW} 1.3.6.1.4.1.248.32.18.1.73.2.6.1
hmStatusWlanMngmtApConfRadioProfErrorsEntry OBJECT-TYPE
    SYNTAX     HmStatusWlanMngmtApConfRadioProfErrorsEntry
    MAX-ACCESS not-accessible
    STATUS     current
    DESCRIPTION
            ""
    INDEX {
            hmStatusWlanMngmtApConfRadioProfErrorsEntryIndex
          }
    ::= { hmStatusWlanMngmtApConfRadioProfErrorsTable 1 }

HmStatusWlanMngmtApConfRadioProfErrorsEntry ::= SEQUENCE {
            hmStatusWlanMngmtApConfRadioProfErrorsEntryIndex Integer32,
            hmStatusWlanMngmtApConfRadioProfErrorsEntryName DisplayString,
            hmStatusWlanMngmtApConfRadioProfErrorsEntryError INTEGER
    }

-- {COLUMN} 1.3.6.1.4.1.248.32.18.1.73.2.6.1.1
hmStatusWlanMngmtApConfRadioProfErrorsEntryIndex OBJECT-TYPE
    SYNTAX     Integer32 (0..2147483647)
    MAX-ACCESS read-only
    STATUS     current
    DESCRIPTION
            "-- empty --"
    ::= { hmStatusWlanMngmtApConfRadioProfErrorsEntry 1 }

-- {COLUMN} 1.3.6.1.4.1.248.32.18.1.73.2.6.1.2
hmStatusWlanMngmtApConfRadioProfErrorsEntryName OBJECT-TYPE
    SYNTAX     DisplayString (SIZE(0..31))
    MAX-ACCESS read-only
    STATUS     current
    DESCRIPTION
            "-- empty --"
    ::= { hmStatusWlanMngmtApConfRadioProfErrorsEntry 2 }

-- {COLUMN} 1.3.6.1.4.1.248.32.18.1.73.2.6.1.3
hmStatusWlanMngmtApConfRadioProfErrorsEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eAutowdsProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20)
            }
    MAX-ACCESS read-only
    STATUS     current
    DESCRIPTION
            "-- empty --"
    ::= { hmStatusWlanMngmtApConfRadioProfErrorsEntry 3 }

-- {TABLE} 1.3.6.1.4.1.248.32.18.1.73.2.7
hmStatusWlanMngmtApConfCommProfErrorsTable OBJECT-TYPE
    SYNTAX     SEQUENCE OF HmStatusWlanMngmtApConfCommProfErrorsEntry
    MAX-ACCESS not-accessible
    STATUS     current
    DESCRIPTION
            "-- empty --"
    ::= { hmStatusWlanMngmtApConf 7 }

-- {ROW} 1.3.6.1.4.1.248.32.18.1.73.2.7.1
hmStatusWlanMngmtApConfCommProfErrorsEntry OBJECT-TYPE
    SYNTAX     HmStatusWlanMngmtApConfCommProfErrorsEntry
    MAX-ACCESS not-accessible
    STATUS     current
    DESCRIPTION
            ""
    INDEX {
            hmStatusWlanMngmtApConfCommProfErrorsEntryIndex
          }
    ::= { hmStatusWlanMngmtApConfCommProfErrorsTable 1 }

HmStatusWlanMngmtApConfCommProfErrorsEntry ::= SEQUENCE {
            hmStatusWlanMngmtApConfCommProfErrorsEntryIndex Integer32,
            hmStatusWlanMngmtApConfCommProfErrorsEntryName DisplayString,
            hmStatusWlanMngmtApConfCommProfErrorsEntryError INTEGER,
            hmStatusWlanMngmtApConfCommProfErrorsEntryNetworkApParameters DisplayString
    }

-- {COLUMN} 1.3.6.1.4.1.248.32.18.1.73.2.7.1.1
hmStatusWlanMngmtApConfCommProfErrorsEntryIndex OBJECT-TYPE
    SYNTAX     Integer32 (0..2147483647)
    MAX-ACCESS read-only
    STATUS     current
    DESCRIPTION
            "-- empty --"
    ::= { hmStatusWlanMngmtApConfCommProfErrorsEntry 1 }

-- {COLUMN} 1.3.6.1.4.1.248.32.18.1.73.2.7.1.2
hmStatusWlanMngmtApConfCommProfErrorsEntryName OBJECT-TYPE
    SYNTAX     DisplayString (SIZE(0..31))
    MAX-ACCESS read-only
    STATUS     current
    DESCRIPTION
            "-- empty --"
    ::= { hmStatusWlanMngmtApConfCommProfErrorsEntry 2 }

-- {COLUMN} 1.3.6.1.4.1.248.32.18.1.73.2.7.1.3
hmStatusWlanMngmtApConfCommProfErrorsEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eAutowdsProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20)
            }
    MAX-ACCESS read-only
    STATUS     current
    DESCRIPTION
            "-- empty --"
    ::= { hmStatusWlanMngmtApConfCommProfErrorsEntry 3 }

-- {COLUMN} 1.3.6.1.4.1.248.32.18.1.73.2.7.1.4
hmStatusWlanMngmtApConfCommProfErrorsEntryNetworkApParameters OBJECT-TYPE
    SYNTAX     DisplayString (SIZE(0..31))
    MAX-ACCESS read-only
    STATUS     current
    DESCRIPTION
            "-- empty --"
    ::= { hmStatusWlanMngmtApConfCommProfErrorsEntry 4 }

-- {TABLE} 1.3.6.1.4.1.248.32.18.1.73.2.8
hmStatusWlanMngmtApConfApConfErrorsTable OBJECT-TYPE
    SYNTAX     SEQUENCE OF HmStatusWlanMngmtApConfApConfErrorsEntry
    MAX-ACCESS not-accessible
    STATUS     current
    DESCRIPTION
            "-- empty --"
    ::= { hmStatusWlanMngmtApConf 8 }

-- {ROW} 1.3.6.1.4.1.248.32.18.1.73.2.8.1
hmStatusWlanMngmtApConfApConfErrorsEntry OBJECT-TYPE
    SYNTAX     HmStatusWlanMngmtApConfApConfErrorsEntry
    MAX-ACCESS not-accessible
    STATUS     current
    DESCRIPTION
            ""
    INDEX {
            hmStatusWlanMngmtApConfApConfErrorsEntryIndex
          }
    ::= { hmStatusWlanMngmtApConfApConfErrorsTable 1 }

HmStatusWlanMngmtApConfApConfErrorsEntry ::= SEQUENCE {
            hmStatusWlanMngmtApConfApConfErrorsEntryIndex Integer32,
            hmStatusWlanMngmtApConfApConfErrorsEntryName DisplayString,
            hmStatusWlanMngmtApConfApConfErrorsEntryError INTEGER,
            hmStatusWlanMngmtApConfApConfErrorsEntryProfile DisplayString,
            hmStatusWlanMngmtApConfApConfErrorsEntryMacAddress DisplayString,
            hmStatusWlanMngmtApConfApConfErrorsEntryGroup DisplayString,
            hmStatusWlanMngmtApConfApConfErrorsEntryErrorMessage DisplayString
    }

-- {COLUMN} 1.3.6.1.4.1.248.32.18.1.73.2.8.1.1
hmStatusWlanMngmtApConfApConfErrorsEntryIndex OBJECT-TYPE
    SYNTAX     Integer32 (0..2147483647)
    MAX-ACCESS read-only
    STATUS     current
    DESCRIPTION
            "-- empty --"
    ::= { hmStatusWlanMngmtApConfApConfErrorsEntry 1 }

-- {COLUMN} 1.3.6.1.4.1.248.32.18.1.73.2.8.1.2
hmStatusWlanMngmtApConfApConfErrorsEntryName OBJECT-TYPE
    SYNTAX     DisplayString (SIZE(0..31))
    MAX-ACCESS read-only
    STATUS     current
    DESCRIPTION
            "-- empty --"
    ::= { hmStatusWlanMngmtApConfApConfErrorsEntry 2 }

-- {COLUMN} 1.3.6.1.4.1.248.32.18.1.73.2.8.1.3
hmStatusWlanMngmtApConfApConfErrorsEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eAutowdsProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20)
            }
    MAX-ACCESS read-only
    STATUS     current
    DESCRIPTION
            "-- empty --"
    ::= { hmStatusWlanMngmtApConfApConfErrorsEntry 3 }

-- {COLUMN} 1.3.6.1.4.1.248.32.18.1.73.2.8.1.4
hmStatusWlanMngmtApConfApConfErrorsEntryProfile OBJECT-TYPE
    SYNTAX     DisplayString (SIZE(0..31))
    MAX-ACCESS read-only
    STATUS     current
    DESCRIPTION
            "-- empty --"
    ::= { hmStatusWlanMngmtApConfApConfErrorsEntry 4 }

-- {COLUMN} 1.3.6.1.4.1.248.32.18.1.73.2.8.1.5
hmStatusWlanMngmtApConfApConfErrorsEntryMacAddress OBJECT-TYPE
    SYNTAX     DisplayString (SIZE(0..12))
    MAX-ACCESS read-only
    STATUS     current
    DESCRIPTION
            "-- empty --"
    ::= { hmStatusWlanMngmtApConfApConfErrorsEntry 5 }

-- {COLUMN} 1.3.6.1.4.1.248.32.18.1.73.2.8.1.6
hmStatusWlanMngmtApConfApConfErrorsEntryGroup OBJECT-TYPE
    SYNTAX     DisplayString (SIZE(0..31))
    MAX-ACCESS read-only
    STATUS     current
    DESCRIPTION
            "-- empty --"
    ::= { hmStatusWlanMngmtApConfApConfErrorsEntry 6 }

-- {COLUMN} 1.3.6.1.4.1.248.32.18.1.73.2.8.1.7
hmStatusWlanMngmtApConfApConfErrorsEntryErrorMessage OBJECT-TYPE
    SYNTAX     DisplayString (SIZE(0..127))
    MAX-ACCESS read-only
    STATUS     current
    DESCRIPTION
            "-- empty --"
    ::= { hmStatusWlanMngmtApConfApConfErrorsEntry 7 }

-- {TABLE} 1.3.6.1.4.1.248.32.18.1.73.2.9
hmStatusWlanMngmtApConfApIntranetsTable OBJECT-TYPE
    SYNTAX     SEQUENCE OF HmStatusWlanMngmtApConfApIntranetsEntry
    MAX-ACCESS not-accessible
    STATUS     current
    DESCRIPTION
            "-- empty --"
    ::= { hmStatusWlanMngmtApConf 9 }

-- {ROW} 1.3.6.1.4.1.248.32.18.1.73.2.9.1
hmStatusWlanMngmtApConfApIntranetsEntry OBJECT-TYPE
    SYNTAX     HmStatusWlanMngmtApConfApIntranetsEntry
    MAX-ACCESS not-accessible
    STATUS     current
    DESCRIPTION
            ""
    INDEX {
            hmStatusWlanMngmtApConfApIntranetsEntryName
          }
    ::= { hmStatusWlanMngmtApConfApIntranetsTable 1 }

HmStatusWlanMngmtApConfApIntranetsEntry ::= SEQUENCE {
            hmStatusWlanMngmtApConfApIntranetsEntryName DisplayString,
            hmStatusWlanMngmtApConfApIntranetsEntryParentName DisplayString,
            hmStatusWlanMngmtApConfApIntranetsEntryLocVal DisplayString,
            hmStatusWlanMngmtApConfApIntranetsEntryDomainName DisplayString,
            hmStatusWlanMngmtApConfApIntranetsEntryNetmask IpAddress,
            hmStatusWlanMngmtApConfApIntranetsEntryGateway IpAddress,
            hmStatusWlanMngmtApConfApIntranetsEntryPrimaryDnsSrv IpAddress,
            hmStatusWlanMngmtApConfApIntranetsEntrySecondaryDnsSrv IpAddress,
            hmStatusWlanMngmtApConfApIntranetsEntryIpv4ConfigPoolStart DisplayString,
            hmStatusWlanMngmtApConfApIntranetsEntryIpv4ConfigPoolEnd DisplayString
    }

-- {COLUMN} 1.3.6.1.4.1.248.32.18.1.73.2.9.1.1
hmStatusWlanMngmtApConfApIntranetsEntryName OBJECT-TYPE
    SYNTAX     DisplayString (SIZE(0..31))
    MAX-ACCESS read-only
    STATUS     current
    DESCRIPTION
            "-- empty --"
    ::= { hmStatusWlanMngmtApConfApIntranetsEntry 1 }

-- {COLUMN} 1.3.6.1.4.1.248.32.18.1.73.2.9.1.2
hmStatusWlanMngmtApConfApIntranetsEntryParentName OBJECT-TYPE
    SYNTAX     DisplayString (SIZE(0..31))
    MAX-ACCESS read-only
    STATUS     current
    DESCRIPTION
            ""
    ::= { hmStatusWlanMngmtApConfApIntranetsEntry 2 }

-- {COLUMN} 1.3.6.1.4.1.248.32.18.1.73.2.9.1.3
hmStatusWlanMngmtApConfApIntranetsEntryLocVal OBJECT-TYPE
    SYNTAX     DisplayString (SIZE(0..2))
    MAX-ACCESS read-only
    STATUS     current
    DESCRIPTION
            "local values"
    ::= { hmStatusWlanMngmtApConfApIntranetsEntry 3 }

-- {COLUMN} 1.3.6.1.4.1.248.32.18.1.73.2.9.1.4
hmStatusWlanMngmtApConfApIntranetsEntryDomainName OBJECT-TYPE
    SYNTAX     DisplayString (SIZE(0..63))
    MAX-ACCESS read-only
    STATUS     current
    DESCRIPTION
            "-- empty --"
    ::= { hmStatusWlanMngmtApConfApIntranetsEntry 4 }

-- {COLUMN} 1.3.6.1.4.1.248.32.18.1.73.2.9.1.5
hmStatusWlanMngmtApConfApIntranetsEntryNetmask OBJECT-TYPE
    SYNTAX     IpAddress
    MAX-ACCESS read-only
    STATUS     current
    DESCRIPTION
            "-- empty --"
    ::= { hmStatusWlanMngmtApConfApIntranetsEntry 5 }

-- {COLUMN} 1.3.6.1.4.1.248.32.18.1.73.2.9.1.6
hmStatusWlanMngmtApConfApIntranetsEntryGateway OBJECT-TYPE
    SYNTAX     IpAddress
    MAX-ACCESS read-only
    STATUS     current
    DESCRIPTION
            "-- empty --"
    ::= { hmStatusWlanMngmtApConfApIntranetsEntry 6 }

-- {COLUMN} 1.3.6.1.4.1.248.32.18.1.73.2.9.1.7
hmStatusWlanMngmtApConfApIntranetsEntryPrimaryDnsSrv OBJECT-TYPE
    SYNTAX     IpAddress
    MAX-ACCESS read-only
    STATUS     current
    DESCRIPTION
            "-- empty --"
    ::= { hmStatusWlanMngmtApConfApIntranetsEntry 7 }

-- {COLUMN} 1.3.6.1.4.1.248.32.18.1.73.2.9.1.8
hmStatusWlanMngmtApConfApIntranetsEntrySecondaryDnsSrv OBJECT-TYPE
    SYNTAX     IpAddress
    MAX-ACCESS read-only
    STATUS     current
    DESCRIPTION
            "-- empty --"
    ::= { hmStatusWlanMngmtApConfApIntranetsEntry 8 }

-- {COLUMN} 1.3.6.1.4.1.248.32.18.1.73.2.9.1.9
hmStatusWlanMngmtApConfApIntranetsEntryIpv4ConfigPoolStart OBJECT-TYPE
    SYNTAX     DisplayString (SIZE(0..15))
    MAX-ACCESS read-only
    STATUS     current
    DESCRIPTION
            "-- empty --"
    ::= { hmStatusWlanMngmtApConfApIntranetsEntry 9 }

-- {COLUMN} 1.3.6.1.4.1.248.32.18.1.73.2.9.1.10
hmStatusWlanMngmtApConfApIntranetsEntryIpv4ConfigPoolEnd OBJECT-TYPE
    SYNTAX     DisplayString (SIZE(0..15))
    MAX-ACCESS read-only
    STATUS     current
    DESCRIPTION
            "-- empty --"
    ::= { hmStatusWlanMngmtApConfApIntranetsEntry 10 }

-- {TABLE} 1.3.6.1.4.1.248.32.18.1.73.2.10
hmStatusWlanMngmtApConfApIntranetErrorsTable OBJECT-TYPE
    SYNTAX     SEQUENCE OF HmStatusWlanMngmtApConfApIntranetErrorsEntry
    MAX-ACCESS not-accessible
    STATUS     current
    DESCRIPTION
            "-- empty --"
    ::= { hmStatusWlanMngmtApConf 10 }

-- {ROW} 1.3.6.1.4.1.248.32.18.1.73.2.10.1
hmStatusWlanMngmtApConfApIntranetErrorsEntry OBJECT-TYPE
    SYNTAX     HmStatusWlanMngmtApConfApIntranetErrorsEntry
    MAX-ACCESS not-accessible
    STATUS     current
    DESCRIPTION
            ""
    INDEX {
            hmStatusWlanMngmtApConfApIntranetErrorsEntryIndex
          }
    ::= { hmStatusWlanMngmtApConfApIntranetErrorsTable 1 }

HmStatusWlanMngmtApConfApIntranetErrorsEntry ::= SEQUENCE {
            hmStatusWlanMngmtApConfApIntranetErrorsEntryIndex Integer32,
            hmStatusWlanMngmtApConfApIntranetErrorsEntryName DisplayString,
            hmStatusWlanMngmtApConfApIntranetErrorsEntryError INTEGER
    }

-- {COLUMN} 1.3.6.1.4.1.248.32.18.1.73.2.10.1.1
hmStatusWlanMngmtApConfApIntranetErrorsEntryIndex OBJECT-TYPE
    SYNTAX     Integer32 (0..2147483647)
    MAX-ACCESS read-only
    STATUS     current
    DESCRIPTION
            "-- empty --"
    ::= { hmStatusWlanMngmtApConfApIntranetErrorsEntry 1 }

-- {COLUMN} 1.3.6.1.4.1.248.32.18.1.73.2.10.1.2
hmStatusWlanMngmtApConfApIntranetErrorsEntryName OBJECT-TYPE
    SYNTAX     DisplayString (SIZE(0..31))
    MAX-ACCESS read-only
    STATUS     current
    DESCRIPTION
            "-- empty --"
    ::= { hmStatusWlanMngmtApConfApIntranetErrorsEntry 2 }

-- {COLUMN} 1.3.6.1.4.1.248.32.18.1.73.2.10.1.3
hmStatusWlanMngmtApConfApIntranetErrorsEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eAutowdsProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20)
            }
    MAX-ACCESS read-only
    STATUS     current
    DESCRIPTION
            "-- empty --"
    ::= { hmStatusWlanMngmtApConfApIntranetErrorsEntry 3 }

-- {TABLE} 1.3.6.1.4.1.248.32.18.1.73.2.11
hmStatusWlanMngmtApConfAutowdsProfilesTable OBJECT-TYPE
    SYNTAX     SEQUENCE OF HmStatusWlanMngmtApConfAutowdsProfilesEntry
    MAX-ACCESS not-accessible
    STATUS     current
    DESCRIPTION
            "-- empty --"
    ::= { hmStatusWlanMngmtApConf 11 }

-- {ROW} 1.3.6.1.4.1.248.32.18.1.73.2.11.1
hmStatusWlanMngmtApConfAutowdsProfilesEntry OBJECT-TYPE
    SYNTAX     HmStatusWlanMngmtApConfAutowdsProfilesEntry
    MAX-ACCESS not-accessible
    STATUS     current
    DESCRIPTION
            ""
    INDEX {
            hmStatusWlanMngmtApConfAutowdsProfilesEntryName
          }
    ::= { hmStatusWlanMngmtApConfAutowdsProfilesTable 1 }

HmStatusWlanMngmtApConfAutowdsProfilesEntry ::= SEQUENCE {
            hmStatusWlanMngmtApConfAutowdsProfilesEntryName DisplayString,
            hmStatusWlanMngmtApConfAutowdsProfilesEntryCommonprofile DisplayString,
            hmStatusWlanMngmtApConfAutowdsProfilesEntrySsid DisplayString,
            hmStatusWlanMngmtApConfAutowdsProfilesEntryKey DisplayString,
            hmStatusWlanMngmtApConfAutowdsProfilesEntryEnabled INTEGER,
            hmStatusWlanMngmtApConfAutowdsProfilesEntryAllowExprInt INTEGER,
            hmStatusWlanMngmtApConfAutowdsProfilesEntryTopologyManagement INTEGER,
            hmStatusWlanMngmtApConfAutowdsProfilesEntrySlaveTxLimit Integer32,
            hmStatusWlanMngmtApConfAutowdsProfilesEntryMasterTxLimit Integer32,
            hmStatusWlanMngmtApConfAutowdsProfilesEntryLinkLossTimeout Integer32,
            hmStatusWlanMngmtApConfAutowdsProfilesEntryContinuation Integer32,
            hmStatusWlanMngmtApConfAutowdsProfilesEntryTimeTillPreconfScan Integer32,
            hmStatusWlanMngmtApConfAutowdsProfilesEntryTimeTillExpressScan Integer32,
            hmStatusWlanMngmtApConfAutowdsProfilesEntryInterfacePairing INTEGER,
            hmStatusWlanMngmtApConfAutowdsProfilesEntryRadioBand INTEGER,
            hmStatusWlanMngmtApConfAutowdsProfilesEntrySsidBroadcast INTEGER
    }

-- {COLUMN} 1.3.6.1.4.1.248.32.18.1.73.2.11.1.1
hmStatusWlanMngmtApConfAutowdsProfilesEntryName OBJECT-TYPE
    SYNTAX     DisplayString (SIZE(0..31))
    MAX-ACCESS read-only
    STATUS     current
    DESCRIPTION
            "-- empty --"
    ::= { hmStatusWlanMngmtApConfAutowdsProfilesEntry 1 }

-- {COLUMN} 1.3.6.1.4.1.248.32.18.1.73.2.11.1.2
hmStatusWlanMngmtApConfAutowdsProfilesEntryCommonprofile OBJECT-TYPE
    SYNTAX     DisplayString (SIZE(0..31))
    MAX-ACCESS read-only
    STATUS     current
    DESCRIPTION
            "-- empty --"
    ::= { hmStatusWlanMngmtApConfAutowdsProfilesEntry 2 }

-- {COLUMN} 1.3.6.1.4.1.248.32.18.1.73.2.11.1.3
hmStatusWlanMngmtApConfAutowdsProfilesEntrySsid OBJECT-TYPE
    SYNTAX     DisplayString (SIZE(0..32))
    MAX-ACCESS read-only
    STATUS     current
    DESCRIPTION
            "-- empty --"
    ::= { hmStatusWlanMngmtApConfAutowdsProfilesEntry 3 }

-- {COLUMN} 1.3.6.1.4.1.248.32.18.1.73.2.11.1.4
hmStatusWlanMngmtApConfAutowdsProfilesEntryKey OBJECT-TYPE
    SYNTAX     DisplayString (SIZE(0..63))
    MAX-ACCESS read-only
    STATUS     current
    DESCRIPTION
            "-- empty --"
    ::= { hmStatusWlanMngmtApConfAutowdsProfilesEntry 4 }

-- {COLUMN} 1.3.6.1.4.1.248.32.18.1.73.2.11.1.6
hmStatusWlanMngmtApConfAutowdsProfilesEntryEnabled OBJECT-TYPE
    SYNTAX     INTEGER {
                  eNo (0),
                  eYes (1)
            }
    MAX-ACCESS read-only
    STATUS     current
    DESCRIPTION
            "-- empty --"
    ::= { hmStatusWlanMngmtApConfAutowdsProfilesEntry 6 }

-- {COLUMN} 1.3.6.1.4.1.248.32.18.1.73.2.11.1.7
hmStatusWlanMngmtApConfAutowdsProfilesEntryAllowExprInt OBJECT-TYPE
    SYNTAX     INTEGER {
                  eNo (0),
                  eYes (1)
            }
    MAX-ACCESS read-only
    STATUS     current
    DESCRIPTION
            "Allow-Express-Integration"
    ::= { hmStatusWlanMngmtApConfAutowdsProfilesEntry 7 }

-- {COLUMN} 1.3.6.1.4.1.248.32.18.1.73.2.11.1.8
hmStatusWlanMngmtApConfAutowdsProfilesEntryTopologyManagement OBJECT-TYPE
    SYNTAX     INTEGER {
                  eAutomatic (0),
                  eSemiAutomatic (1),
                  eManual (2)
            }
    MAX-ACCESS read-only
    STATUS     current
    DESCRIPTION
            "-- empty --"
    ::= { hmStatusWlanMngmtApConfAutowdsProfilesEntry 8 }

-- {COLUMN} 1.3.6.1.4.1.248.32.18.1.73.2.11.1.10
hmStatusWlanMngmtApConfAutowdsProfilesEntrySlaveTxLimit OBJECT-TYPE
    SYNTAX     Integer32 (0..2147483647)
    MAX-ACCESS read-only
    STATUS     current
    DESCRIPTION
            "-- empty --"
    ::= { hmStatusWlanMngmtApConfAutowdsProfilesEntry 10 }

-- {COLUMN} 1.3.6.1.4.1.248.32.18.1.73.2.11.1.11
hmStatusWlanMngmtApConfAutowdsProfilesEntryMasterTxLimit OBJECT-TYPE
    SYNTAX     Integer32 (0..2147483647)
    MAX-ACCESS read-only
    STATUS     current
    DESCRIPTION
            "-- empty --"
    ::= { hmStatusWlanMngmtApConfAutowdsProfilesEntry 11 }

-- {COLUMN} 1.3.6.1.4.1.248.32.18.1.73.2.11.1.12
hmStatusWlanMngmtApConfAutowdsProfilesEntryLinkLossTimeout OBJECT-TYPE
    SYNTAX     Integer32 (0..2147483647)
    MAX-ACCESS read-only
    STATUS     current
    DESCRIPTION
            "-- empty --"
    ::= { hmStatusWlanMngmtApConfAutowdsProfilesEntry 12 }

-- {COLUMN} 1.3.6.1.4.1.248.32.18.1.73.2.11.1.14
hmStatusWlanMngmtApConfAutowdsProfilesEntryContinuation OBJECT-TYPE
    SYNTAX     Integer32 (0..65535)
    MAX-ACCESS read-only
    STATUS     current
    DESCRIPTION
            ""
    ::= { hmStatusWlanMngmtApConfAutowdsProfilesEntry 14 }

-- {COLUMN} 1.3.6.1.4.1.248.32.18.1.73.2.11.1.15
hmStatusWlanMngmtApConfAutowdsProfilesEntryTimeTillPreconfScan OBJECT-TYPE
    SYNTAX     Integer32 (0..2147483647)
    MAX-ACCESS read-only
    STATUS     current
    DESCRIPTION
            "-- empty --"
    ::= { hmStatusWlanMngmtApConfAutowdsProfilesEntry 15 }

-- {COLUMN} 1.3.6.1.4.1.248.32.18.1.73.2.11.1.16
hmStatusWlanMngmtApConfAutowdsProfilesEntryTimeTillExpressScan OBJECT-TYPE
    SYNTAX     Integer32 (0..2147483647)
    MAX-ACCESS read-only
    STATUS     current
    DESCRIPTION
            "-- empty --"
    ::= { hmStatusWlanMngmtApConfAutowdsProfilesEntry 16 }

-- {COLUMN} 1.3.6.1.4.1.248.32.18.1.73.2.11.1.17
hmStatusWlanMngmtApConfAutowdsProfilesEntryInterfacePairing OBJECT-TYPE
    SYNTAX     INTEGER {
                  eAutomatic (0),
                  eStrict (1),
                  eMixed (2)
            }
    MAX-ACCESS read-only
    STATUS     current
    DESCRIPTION
            "-- empty --"
    ::= { hmStatusWlanMngmtApConfAutowdsProfilesEntry 17 }

-- {COLUMN} 1.3.6.1.4.1.248.32.18.1.73.2.11.1.19
hmStatusWlanMngmtApConfAutowdsProfilesEntryRadioBand OBJECT-TYPE
    SYNTAX     INTEGER {
                  e24ghz5ghz (0),
                  e24ghz (1),
                  e5ghz (2)
            }
    MAX-ACCESS read-only
    STATUS     current
    DESCRIPTION
            "-- empty --"
    ::= { hmStatusWlanMngmtApConfAutowdsProfilesEntry 19 }

-- {COLUMN} 1.3.6.1.4.1.248.32.18.1.73.2.11.1.20
hmStatusWlanMngmtApConfAutowdsProfilesEntrySsidBroadcast OBJECT-TYPE
    SYNTAX     INTEGER {
                  eNo (0),
                  eYes (1)
            }
    MAX-ACCESS read-only
    STATUS     current
    DESCRIPTION
            "-- empty --"
    ::= { hmStatusWlanMngmtApConfAutowdsProfilesEntry 20 }

-- {TABLE} 1.3.6.1.4.1.248.32.18.1.73.2.12
hmStatusWlanMngmtApConfAutowdsTopologyTable OBJECT-TYPE
    SYNTAX     SEQUENCE OF HmStatusWlanMngmtApConfAutowdsTopologyEntry
    MAX-ACCESS not-accessible
    STATUS     current
    DESCRIPTION
            "-- empty --"
    ::= { hmStatusWlanMngmtApConf 12 }

-- {ROW} 1.3.6.1.4.1.248.32.18.1.73.2.12.1
hmStatusWlanMngmtApConfAutowdsTopologyEntry OBJECT-TYPE
    SYNTAX     HmStatusWlanMngmtApConfAutowdsTopologyEntry
    MAX-ACCESS not-accessible
    STATUS     current
    DESCRIPTION
            ""
    INDEX {
            hmStatusWlanMngmtApConfAutowdsTopologyEntryAutowdsProfile,
            hmStatusWlanMngmtApConfAutowdsTopologyEntryPriority,
            hmStatusWlanMngmtApConfAutowdsTopologyEntrySlaveApName,
            hmStatusWlanMngmtApConfAutowdsTopologyEntrySlaveApWlanIfc,
            hmStatusWlanMngmtApConfAutowdsTopologyEntrySlaveApWlanMac
          }
    ::= { hmStatusWlanMngmtApConfAutowdsTopologyTable 1 }

HmStatusWlanMngmtApConfAutowdsTopologyEntry ::= SEQUENCE {
            hmStatusWlanMngmtApConfAutowdsTopologyEntryAutowdsProfile DisplayString,
            hmStatusWlanMngmtApConfAutowdsTopologyEntryPriority Integer32,
            hmStatusWlanMngmtApConfAutowdsTopologyEntrySlaveApName DisplayString,
            hmStatusWlanMngmtApConfAutowdsTopologyEntrySlaveApWlanIfc INTEGER,
            hmStatusWlanMngmtApConfAutowdsTopologyEntrySlaveApWlanMac DisplayString,
            hmStatusWlanMngmtApConfAutowdsTopologyEntryMasterApName DisplayString,
            hmStatusWlanMngmtApConfAutowdsTopologyEntryMasterApWlanIfc INTEGER,
            hmStatusWlanMngmtApConfAutowdsTopologyEntryMasterApWlanMac DisplayString,
            hmStatusWlanMngmtApConfAutowdsTopologyEntryKey DisplayString,
            hmStatusWlanMngmtApConfAutowdsTopologyEntryEnabled INTEGER,
            hmStatusWlanMngmtApConfAutowdsTopologyEntrySlaveTxLimit Integer32,
            hmStatusWlanMngmtApConfAutowdsTopologyEntryMasterTxLimit Integer32,
            hmStatusWlanMngmtApConfAutowdsTopologyEntryLinkLossTimeout Integer32,
            hmStatusWlanMngmtApConfAutowdsTopologyEntryContinuation Integer32,
            hmStatusWlanMngmtApConfAutowdsTopologyEntryGenerated INTEGER,
            hmStatusWlanMngmtApConfAutowdsTopologyEntryState INTEGER
    }

-- {COLUMN} 1.3.6.1.4.1.248.32.18.1.73.2.12.1.1
hmStatusWlanMngmtApConfAutowdsTopologyEntryAutowdsProfile OBJECT-TYPE
    SYNTAX     DisplayString (SIZE(0..31))
    MAX-ACCESS read-only
    STATUS     current
    DESCRIPTION
            "-- empty --"
    ::= { hmStatusWlanMngmtApConfAutowdsTopologyEntry 1 }

-- {COLUMN} 1.3.6.1.4.1.248.32.18.1.73.2.12.1.2
hmStatusWlanMngmtApConfAutowdsTopologyEntryPriority OBJECT-TYPE
    SYNTAX     Integer32 (0..65535)
    MAX-ACCESS read-only
    STATUS     current
    DESCRIPTION
            "-- empty --"
    ::= { hmStatusWlanMngmtApConfAutowdsTopologyEntry 2 }

-- {COLUMN} 1.3.6.1.4.1.248.32.18.1.73.2.12.1.3
hmStatusWlanMngmtApConfAutowdsTopologyEntrySlaveApName OBJECT-TYPE
    SYNTAX     DisplayString (SIZE(0..16))
    MAX-ACCESS read-only
    STATUS     current
    DESCRIPTION
            "-- empty --"
    ::= { hmStatusWlanMngmtApConfAutowdsTopologyEntry 3 }

-- {COLUMN} 1.3.6.1.4.1.248.32.18.1.73.2.12.1.4
hmStatusWlanMngmtApConfAutowdsTopologyEntrySlaveApWlanIfc OBJECT-TYPE
    SYNTAX     INTEGER {
                  eWlan1 (1),
                  eWlan2 (2)
            }
    MAX-ACCESS read-only
    STATUS     current
    DESCRIPTION
            "-- empty --"
    ::= { hmStatusWlanMngmtApConfAutowdsTopologyEntry 4 }

-- {COLUMN} 1.3.6.1.4.1.248.32.18.1.73.2.12.1.5
hmStatusWlanMngmtApConfAutowdsTopologyEntrySlaveApWlanMac OBJECT-TYPE
    SYNTAX     DisplayString (SIZE(0..12))
    MAX-ACCESS read-only
    STATUS     current
    DESCRIPTION
            "-- empty --"
    ::= { hmStatusWlanMngmtApConfAutowdsTopologyEntry 5 }

-- {COLUMN} 1.3.6.1.4.1.248.32.18.1.73.2.12.1.6
hmStatusWlanMngmtApConfAutowdsTopologyEntryMasterApName OBJECT-TYPE
    SYNTAX     DisplayString (SIZE(0..16))
    MAX-ACCESS read-only
    STATUS     current
    DESCRIPTION
            "-- empty --"
    ::= { hmStatusWlanMngmtApConfAutowdsTopologyEntry 6 }

-- {COLUMN} 1.3.6.1.4.1.248.32.18.1.73.2.12.1.7
hmStatusWlanMngmtApConfAutowdsTopologyEntryMasterApWlanIfc OBJECT-TYPE
    SYNTAX     INTEGER {
                  eWlan1 (1),
                  eWlan2 (2)
            }
    MAX-ACCESS read-only
    STATUS     current
    DESCRIPTION
            "-- empty --"
    ::= { hmStatusWlanMngmtApConfAutowdsTopologyEntry 7 }

-- {COLUMN} 1.3.6.1.4.1.248.32.18.1.73.2.12.1.8
hmStatusWlanMngmtApConfAutowdsTopologyEntryMasterApWlanMac OBJECT-TYPE
    SYNTAX     DisplayString (SIZE(0..12))
    MAX-ACCESS read-only
    STATUS     current
    DESCRIPTION
            "-- empty --"
    ::= { hmStatusWlanMngmtApConfAutowdsTopologyEntry 8 }

-- {COLUMN} 1.3.6.1.4.1.248.32.18.1.73.2.12.1.9
hmStatusWlanMngmtApConfAutowdsTopologyEntryKey OBJECT-TYPE
    SYNTAX     DisplayString (SIZE(0..63))
    MAX-ACCESS read-only
    STATUS     current
    DESCRIPTION
            "-- empty --"
    ::= { hmStatusWlanMngmtApConfAutowdsTopologyEntry 9 }

-- {COLUMN} 1.3.6.1.4.1.248.32.18.1.73.2.12.1.10
hmStatusWlanMngmtApConfAutowdsTopologyEntryEnabled OBJECT-TYPE
    SYNTAX     INTEGER {
                  eNo (0),
                  eYes (1)
            }
    MAX-ACCESS read-only
    STATUS     current
    DESCRIPTION
            "-- empty --"
    ::= { hmStatusWlanMngmtApConfAutowdsTopologyEntry 10 }

-- {COLUMN} 1.3.6.1.4.1.248.32.18.1.73.2.12.1.12
hmStatusWlanMngmtApConfAutowdsTopologyEntrySlaveTxLimit OBJECT-TYPE
    SYNTAX     Integer32 (0..2147483647)
    MAX-ACCESS read-only
    STATUS     current
    DESCRIPTION
            "-- empty --"
    ::= { hmStatusWlanMngmtApConfAutowdsTopologyEntry 12 }

-- {COLUMN} 1.3.6.1.4.1.248.32.18.1.73.2.12.1.13
hmStatusWlanMngmtApConfAutowdsTopologyEntryMasterTxLimit OBJECT-TYPE
    SYNTAX     Integer32 (0..2147483647)
    MAX-ACCESS read-only
    STATUS     current
    DESCRIPTION
            "-- empty --"
    ::= { hmStatusWlanMngmtApConfAutowdsTopologyEntry 13 }

-- {COLUMN} 1.3.6.1.4.1.248.32.18.1.73.2.12.1.14
hmStatusWlanMngmtApConfAutowdsTopologyEntryLinkLossTimeout OBJECT-TYPE
    SYNTAX     Integer32 (0..2147483647)
    MAX-ACCESS read-only
    STATUS     current
    DESCRIPTION
            "-- empty --"
    ::= { hmStatusWlanMngmtApConfAutowdsTopologyEntry 14 }

-- {COLUMN} 1.3.6.1.4.1.248.32.18.1.73.2.12.1.16
hmStatusWlanMngmtApConfAutowdsTopologyEntryContinuation OBJECT-TYPE
    SYNTAX     Integer32 (0..65535)
    MAX-ACCESS read-only
    STATUS     current
    DESCRIPTION
            ""
    ::= { hmStatusWlanMngmtApConfAutowdsTopologyEntry 16 }

-- {COLUMN} 1.3.6.1.4.1.248.32.18.1.73.2.12.1.17
hmStatusWlanMngmtApConfAutowdsTopologyEntryGenerated OBJECT-TYPE
    SYNTAX     INTEGER {
                  eNo (0),
                  eYes (1)
            }
    MAX-ACCESS read-only
    STATUS     current
    DESCRIPTION
            "-- empty --"
    ::= { hmStatusWlanMngmtApConfAutowdsTopologyEntry 17 }

-- {COLUMN} 1.3.6.1.4.1.248.32.18.1.73.2.12.1.18
hmStatusWlanMngmtApConfAutowdsTopologyEntryState OBJECT-TYPE
    SYNTAX     INTEGER {
                  eNone (0),
                  eActive (1),
                  eInactive (2)
            }
    MAX-ACCESS read-only
    STATUS     current
    DESCRIPTION
            "-- empty --"
    ::= { hmStatusWlanMngmtApConfAutowdsTopologyEntry 18 }

-- {TABLE} 1.3.6.1.4.1.248.32.18.1.73.2.13
hmStatusWlanMngmtApConfAutowdsAutoTopologyTable OBJECT-TYPE
    SYNTAX     SEQUENCE OF HmStatusWlanMngmtApConfAutowdsAutoTopologyEntry
    MAX-ACCESS not-accessible
    STATUS     current
    DESCRIPTION
            "-- empty --"
    ::= { hmStatusWlanMngmtApConf 13 }

-- {ROW} 1.3.6.1.4.1.248.32.18.1.73.2.13.1
hmStatusWlanMngmtApConfAutowdsAutoTopologyEntry OBJECT-TYPE
    SYNTAX     HmStatusWlanMngmtApConfAutowdsAutoTopologyEntry
    MAX-ACCESS not-accessible
    STATUS     current
    DESCRIPTION
            ""
    INDEX {
            hmStatusWlanMngmtApConfAutowdsAutoTopologyEntryAutowdsProfile,
            hmStatusWlanMngmtApConfAutowdsAutoTopologyEntryPriority,
            hmStatusWlanMngmtApConfAutowdsAutoTopologyEntrySlaveApName,
            hmStatusWlanMngmtApConfAutowdsAutoTopologyEntrySlaveApWlanIfc,
            hmStatusWlanMngmtApConfAutowdsAutoTopologyEntrySlaveApWlanMac
          }
    ::= { hmStatusWlanMngmtApConfAutowdsAutoTopologyTable 1 }

HmStatusWlanMngmtApConfAutowdsAutoTopologyEntry ::= SEQUENCE {
            hmStatusWlanMngmtApConfAutowdsAutoTopologyEntryAutowdsProfile DisplayString,
            hmStatusWlanMngmtApConfAutowdsAutoTopologyEntryPriority Integer32,
            hmStatusWlanMngmtApConfAutowdsAutoTopologyEntrySlaveApName DisplayString,
            hmStatusWlanMngmtApConfAutowdsAutoTopologyEntrySlaveApWlanIfc INTEGER,
            hmStatusWlanMngmtApConfAutowdsAutoTopologyEntrySlaveApWlanMac DisplayString,
            hmStatusWlanMngmtApConfAutowdsAutoTopologyEntryMasterApName DisplayString,
            hmStatusWlanMngmtApConfAutowdsAutoTopologyEntryMasterApWlanIfc INTEGER,
            hmStatusWlanMngmtApConfAutowdsAutoTopologyEntryMasterApWlanMac DisplayString,
            hmStatusWlanMngmtApConfAutowdsAutoTopologyEntryKey DisplayString,
            hmStatusWlanMngmtApConfAutowdsAutoTopologyEntryEnabled INTEGER,
            hmStatusWlanMngmtApConfAutowdsAutoTopologyEntrySlaveTxLimit Integer32,
            hmStatusWlanMngmtApConfAutowdsAutoTopologyEntryMasterTxLimit Integer32,
            hmStatusWlanMngmtApConfAutowdsAutoTopologyEntryLinkLossTimeout Integer32,
            hmStatusWlanMngmtApConfAutowdsAutoTopologyEntryContinuation Integer32,
            hmStatusWlanMngmtApConfAutowdsAutoTopologyEntryGenerated INTEGER,
            hmStatusWlanMngmtApConfAutowdsAutoTopologyEntryState INTEGER
    }

-- {COLUMN} 1.3.6.1.4.1.248.32.18.1.73.2.13.1.1
hmStatusWlanMngmtApConfAutowdsAutoTopologyEntryAutowdsProfile OBJECT-TYPE
    SYNTAX     DisplayString (SIZE(0..31))
    MAX-ACCESS read-only
    STATUS     current
    DESCRIPTION
            "-- empty --"
    ::= { hmStatusWlanMngmtApConfAutowdsAutoTopologyEntry 1 }

-- {COLUMN} 1.3.6.1.4.1.248.32.18.1.73.2.13.1.2
hmStatusWlanMngmtApConfAutowdsAutoTopologyEntryPriority OBJECT-TYPE
    SYNTAX     Integer32 (0..65535)
    MAX-ACCESS read-only
    STATUS     current
    DESCRIPTION
            "-- empty --"
    ::= { hmStatusWlanMngmtApConfAutowdsAutoTopologyEntry 2 }

-- {COLUMN} 1.3.6.1.4.1.248.32.18.1.73.2.13.1.3
hmStatusWlanMngmtApConfAutowdsAutoTopologyEntrySlaveApName OBJECT-TYPE
    SYNTAX     DisplayString (SIZE(0..16))
    MAX-ACCESS read-only
    STATUS     current
    DESCRIPTION
            "-- empty --"
    ::= { hmStatusWlanMngmtApConfAutowdsAutoTopologyEntry 3 }

-- {COLUMN} 1.3.6.1.4.1.248.32.18.1.73.2.13.1.4
hmStatusWlanMngmtApConfAutowdsAutoTopologyEntrySlaveApWlanIfc OBJECT-TYPE
    SYNTAX     INTEGER {
                  eWlan1 (1),
                  eWlan2 (2)
            }
    MAX-ACCESS read-only
    STATUS     current
    DESCRIPTION
            "-- empty --"
    ::= { hmStatusWlanMngmtApConfAutowdsAutoTopologyEntry 4 }

-- {COLUMN} 1.3.6.1.4.1.248.32.18.1.73.2.13.1.5
hmStatusWlanMngmtApConfAutowdsAutoTopologyEntrySlaveApWlanMac OBJECT-TYPE
    SYNTAX     DisplayString (SIZE(0..12))
    MAX-ACCESS read-only
    STATUS     current
    DESCRIPTION
            "-- empty --"
    ::= { hmStatusWlanMngmtApConfAutowdsAutoTopologyEntry 5 }

-- {COLUMN} 1.3.6.1.4.1.248.32.18.1.73.2.13.1.6
hmStatusWlanMngmtApConfAutowdsAutoTopologyEntryMasterApName OBJECT-TYPE
    SYNTAX     DisplayString (SIZE(0..16))
    MAX-ACCESS read-only
    STATUS     current
    DESCRIPTION
            "-- empty --"
    ::= { hmStatusWlanMngmtApConfAutowdsAutoTopologyEntry 6 }

-- {COLUMN} 1.3.6.1.4.1.248.32.18.1.73.2.13.1.7
hmStatusWlanMngmtApConfAutowdsAutoTopologyEntryMasterApWlanIfc OBJECT-TYPE
    SYNTAX     INTEGER {
                  eWlan1 (1),
                  eWlan2 (2)
            }
    MAX-ACCESS read-only
    STATUS     current
    DESCRIPTION
            "-- empty --"
    ::= { hmStatusWlanMngmtApConfAutowdsAutoTopologyEntry 7 }

-- {COLUMN} 1.3.6.1.4.1.248.32.18.1.73.2.13.1.8
hmStatusWlanMngmtApConfAutowdsAutoTopologyEntryMasterApWlanMac OBJECT-TYPE
    SYNTAX     DisplayString (SIZE(0..12))
    MAX-ACCESS read-only
    STATUS     current
    DESCRIPTION
            "-- empty --"
    ::= { hmStatusWlanMngmtApConfAutowdsAutoTopologyEntry 8 }

-- {COLUMN} 1.3.6.1.4.1.248.32.18.1.73.2.13.1.9
hmStatusWlanMngmtApConfAutowdsAutoTopologyEntryKey OBJECT-TYPE
    SYNTAX     DisplayString (SIZE(0..63))
    MAX-ACCESS read-only
    STATUS     current
    DESCRIPTION
            "-- empty --"
    ::= { hmStatusWlanMngmtApConfAutowdsAutoTopologyEntry 9 }

-- {COLUMN} 1.3.6.1.4.1.248.32.18.1.73.2.13.1.10
hmStatusWlanMngmtApConfAutowdsAutoTopologyEntryEnabled OBJECT-TYPE
    SYNTAX     INTEGER {
                  eNo (0),
                  eYes (1)
            }
    MAX-ACCESS read-only
    STATUS     current
    DESCRIPTION
            "-- empty --"
    ::= { hmStatusWlanMngmtApConfAutowdsAutoTopologyEntry 10 }

-- {COLUMN} 1.3.6.1.4.1.248.32.18.1.73.2.13.1.12
hmStatusWlanMngmtApConfAutowdsAutoTopologyEntrySlaveTxLimit OBJECT-TYPE
    SYNTAX     Integer32 (0..2147483647)
    MAX-ACCESS read-only
    STATUS     current
    DESCRIPTION
            "-- empty --"
    ::= { hmStatusWlanMngmtApConfAutowdsAutoTopologyEntry 12 }

-- {COLUMN} 1.3.6.1.4.1.248.32.18.1.73.2.13.1.13
hmStatusWlanMngmtApConfAutowdsAutoTopologyEntryMasterTxLimit OBJECT-TYPE
    SYNTAX     Integer32 (0..2147483647)
    MAX-ACCESS read-only
    STATUS     current
    DESCRIPTION
            "-- empty --"
    ::= { hmStatusWlanMngmtApConfAutowdsAutoTopologyEntry 13 }

-- {COLUMN} 1.3.6.1.4.1.248.32.18.1.73.2.13.1.14
hmStatusWlanMngmtApConfAutowdsAutoTopologyEntryLinkLossTimeout OBJECT-TYPE
    SYNTAX     Integer32 (0..2147483647)
    MAX-ACCESS read-only
    STATUS     current
    DESCRIPTION
            "-- empty --"
    ::= { hmStatusWlanMngmtApConfAutowdsAutoTopologyEntry 14 }

-- {COLUMN} 1.3.6.1.4.1.248.32.18.1.73.2.13.1.16
hmStatusWlanMngmtApConfAutowdsAutoTopologyEntryContinuation OBJECT-TYPE
    SYNTAX     Integer32 (0..65535)
    MAX-ACCESS read-only
    STATUS     current
    DESCRIPTION
            ""
    ::= { hmStatusWlanMngmtApConfAutowdsAutoTopologyEntry 16 }

-- {COLUMN} 1.3.6.1.4.1.248.32.18.1.73.2.13.1.17
hmStatusWlanMngmtApConfAutowdsAutoTopologyEntryGenerated OBJECT-TYPE
    SYNTAX     INTEGER {
                  eNo (0),
                  eYes (1)
            }
    MAX-ACCESS read-only
    STATUS     current
    DESCRIPTION
            "-- empty --"
    ::= { hmStatusWlanMngmtApConfAutowdsAutoTopologyEntry 17 }

-- {COLUMN} 1.3.6.1.4.1.248.32.18.1.73.2.13.1.18
hmStatusWlanMngmtApConfAutowdsAutoTopologyEntryState OBJECT-TYPE
    SYNTAX     INTEGER {
                  eNone (0),
                  eActive (1),
                  eInactive (2)
            }
    MAX-ACCESS read-only
    STATUS     current
    DESCRIPTION
            "-- empty --"
    ::= { hmStatusWlanMngmtApConfAutowdsAutoTopologyEntry 18 }

-- {TABLE} 1.3.6.1.4.1.248.32.18.1.73.2.14
hmStatusWlanMngmtApConfAutowdsProfErrorsTable OBJECT-TYPE
    SYNTAX     SEQUENCE OF HmStatusWlanMngmtApConfAutowdsProfErrorsEntry
    MAX-ACCESS not-accessible
    STATUS     current
    DESCRIPTION
            "-- empty --"
    ::= { hmStatusWlanMngmtApConf 14 }

-- {ROW} 1.3.6.1.4.1.248.32.18.1.73.2.14.1
hmStatusWlanMngmtApConfAutowdsProfErrorsEntry OBJECT-TYPE
    SYNTAX     HmStatusWlanMngmtApConfAutowdsProfErrorsEntry
    MAX-ACCESS not-accessible
    STATUS     current
    DESCRIPTION
            ""
    INDEX {
            hmStatusWlanMngmtApConfAutowdsProfErrorsEntryIndex
          }
    ::= { hmStatusWlanMngmtApConfAutowdsProfErrorsTable 1 }

HmStatusWlanMngmtApConfAutowdsProfErrorsEntry ::= SEQUENCE {
            hmStatusWlanMngmtApConfAutowdsProfErrorsEntryIndex Integer32,
            hmStatusWlanMngmtApConfAutowdsProfErrorsEntryName DisplayString,
            hmStatusWlanMngmtApConfAutowdsProfErrorsEntryError INTEGER,
            hmStatusWlanMngmtApConfAutowdsProfErrorsEntryNetworkApParameters DisplayString
    }

-- {COLUMN} 1.3.6.1.4.1.248.32.18.1.73.2.14.1.1
hmStatusWlanMngmtApConfAutowdsProfErrorsEntryIndex OBJECT-TYPE
    SYNTAX     Integer32 (0..2147483647)
    MAX-ACCESS read-only
    STATUS     current
    DESCRIPTION
            "-- empty --"
    ::= { hmStatusWlanMngmtApConfAutowdsProfErrorsEntry 1 }

-- {COLUMN} 1.3.6.1.4.1.248.32.18.1.73.2.14.1.2
hmStatusWlanMngmtApConfAutowdsProfErrorsEntryName OBJECT-TYPE
    SYNTAX     DisplayString (SIZE(0..31))
    MAX-ACCESS read-only
    STATUS     current
    DESCRIPTION
            "-- empty --"
    ::= { hmStatusWlanMngmtApConfAutowdsProfErrorsEntry 2 }

-- {COLUMN} 1.3.6.1.4.1.248.32.18.1.73.2.14.1.3
hmStatusWlanMngmtApConfAutowdsProfErrorsEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eAutowdsProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20)
            }
    MAX-ACCESS read-only
    STATUS     current
    DESCRIPTION
            "-- empty --"
    ::= { hmStatusWlanMngmtApConfAutowdsProfErrorsEntry 3 }

-- {COLUMN} 1.3.6.1.4.1.248.32.18.1.73.2.14.1.4
hmStatusWlanMngmtApConfAutowdsProfErrorsEntryNetworkApParameters OBJECT-TYPE
    SYNTAX     DisplayString (SIZE(0..31))
    MAX-ACCESS read-only
    STATUS     current
    DESCRIPTION
            "-- empty --"
    ::= { hmStatusWlanMngmtApConfAutowdsProfErrorsEntry 4 }

-- {TABLE} 1.3.6.1.4.1.248.32.18.1.73.2.15
hmStatusWlanMngmtApConfAutowdsTopoErrorsTable OBJECT-TYPE
    SYNTAX     SEQUENCE OF HmStatusWlanMngmtApConfAutowdsTopoErrorsEntry
    MAX-ACCESS not-accessible
    STATUS     current
    DESCRIPTION
            "-- empty --"
    ::= { hmStatusWlanMngmtApConf 15 }

-- {ROW} 1.3.6.1.4.1.248.32.18.1.73.2.15.1
hmStatusWlanMngmtApConfAutowdsTopoErrorsEntry OBJECT-TYPE
    SYNTAX     HmStatusWlanMngmtApConfAutowdsTopoErrorsEntry
    MAX-ACCESS not-accessible
    STATUS     current
    DESCRIPTION
            ""
    INDEX {
            hmStatusWlanMngmtApConfAutowdsTopoErrorsEntryIndex,
            hmStatusWlanMngmtApConfAutowdsTopoErrorsEntryPriority,
            hmStatusWlanMngmtApConfAutowdsTopoErrorsEntrySlaveApName,
            hmStatusWlanMngmtApConfAutowdsTopoErrorsEntrySlaveApWlanIfc
          }
    ::= { hmStatusWlanMngmtApConfAutowdsTopoErrorsTable 1 }

HmStatusWlanMngmtApConfAutowdsTopoErrorsEntry ::= SEQUENCE {
            hmStatusWlanMngmtApConfAutowdsTopoErrorsEntryIndex Integer32,
            hmStatusWlanMngmtApConfAutowdsTopoErrorsEntryAutowdsProfile DisplayString,
            hmStatusWlanMngmtApConfAutowdsTopoErrorsEntryPriority Integer32,
            hmStatusWlanMngmtApConfAutowdsTopoErrorsEntrySlaveApName DisplayString,
            hmStatusWlanMngmtApConfAutowdsTopoErrorsEntrySlaveApWlanIfc INTEGER,
            hmStatusWlanMngmtApConfAutowdsTopoErrorsEntrySlaveApWlanMac DisplayString,
            hmStatusWlanMngmtApConfAutowdsTopoErrorsEntryMasterApName DisplayString,
            hmStatusWlanMngmtApConfAutowdsTopoErrorsEntryMasterApWlanIfc INTEGER,
            hmStatusWlanMngmtApConfAutowdsTopoErrorsEntryMasterApWlanMac DisplayString,
            hmStatusWlanMngmtApConfAutowdsTopoErrorsEntryError INTEGER
    }

-- {COLUMN} 1.3.6.1.4.1.248.32.18.1.73.2.15.1.1
hmStatusWlanMngmtApConfAutowdsTopoErrorsEntryIndex OBJECT-TYPE
    SYNTAX     Integer32 (0..2147483647)
    MAX-ACCESS read-only
    STATUS     current
    DESCRIPTION
            "-- empty --"
    ::= { hmStatusWlanMngmtApConfAutowdsTopoErrorsEntry 1 }

-- {COLUMN} 1.3.6.1.4.1.248.32.18.1.73.2.15.1.2
hmStatusWlanMngmtApConfAutowdsTopoErrorsEntryAutowdsProfile OBJECT-TYPE
    SYNTAX     DisplayString (SIZE(0..31))
    MAX-ACCESS read-only
    STATUS     current
    DESCRIPTION
            "-- empty --"
    ::= { hmStatusWlanMngmtApConfAutowdsTopoErrorsEntry 2 }

-- {COLUMN} 1.3.6.1.4.1.248.32.18.1.73.2.15.1.3
hmStatusWlanMngmtApConfAutowdsTopoErrorsEntryPriority OBJECT-TYPE
    SYNTAX     Integer32 (0..65535)
    MAX-ACCESS read-only
    STATUS     current
    DESCRIPTION
            "-- empty --"
    ::= { hmStatusWlanMngmtApConfAutowdsTopoErrorsEntry 3 }

-- {COLUMN} 1.3.6.1.4.1.248.32.18.1.73.2.15.1.4
hmStatusWlanMngmtApConfAutowdsTopoErrorsEntrySlaveApName OBJECT-TYPE
    SYNTAX     DisplayString (SIZE(0..16))
    MAX-ACCESS read-only
    STATUS     current
    DESCRIPTION
            "-- empty --"
    ::= { hmStatusWlanMngmtApConfAutowdsTopoErrorsEntry 4 }

-- {COLUMN} 1.3.6.1.4.1.248.32.18.1.73.2.15.1.5
hmStatusWlanMngmtApConfAutowdsTopoErrorsEntrySlaveApWlanIfc OBJECT-TYPE
    SYNTAX     INTEGER {
                  eWlan1 (1),
                  eWlan2 (2)
            }
    MAX-ACCESS read-only
    STATUS     current
    DESCRIPTION
            "-- empty --"
    ::= { hmStatusWlanMngmtApConfAutowdsTopoErrorsEntry 5 }

-- {COLUMN} 1.3.6.1.4.1.248.32.18.1.73.2.15.1.6
hmStatusWlanMngmtApConfAutowdsTopoErrorsEntrySlaveApWlanMac OBJECT-TYPE
    SYNTAX     DisplayString (SIZE(0..12))
    MAX-ACCESS read-only
    STATUS     current
    DESCRIPTION
            "-- empty --"
    ::= { hmStatusWlanMngmtApConfAutowdsTopoErrorsEntry 6 }

-- {COLUMN} 1.3.6.1.4.1.248.32.18.1.73.2.15.1.7
hmStatusWlanMngmtApConfAutowdsTopoErrorsEntryMasterApName OBJECT-TYPE
    SYNTAX     DisplayString (SIZE(0..16))
    MAX-ACCESS read-only
    STATUS     current
    DESCRIPTION
            "-- empty --"
    ::= { hmStatusWlanMngmtApConfAutowdsTopoErrorsEntry 7 }

-- {COLUMN} 1.3.6.1.4.1.248.32.18.1.73.2.15.1.8
hmStatusWlanMngmtApConfAutowdsTopoErrorsEntryMasterApWlanIfc OBJECT-TYPE
    SYNTAX     INTEGER {
                  eWlan1 (1),
                  eWlan2 (2)
            }
    MAX-ACCESS read-only
    STATUS     current
    DESCRIPTION
            "-- empty --"
    ::= { hmStatusWlanMngmtApConfAutowdsTopoErrorsEntry 8 }

-- {COLUMN} 1.3.6.1.4.1.248.32.18.1.73.2.15.1.9
hmStatusWlanMngmtApConfAutowdsTopoErrorsEntryMasterApWlanMac OBJECT-TYPE
    SYNTAX     DisplayString (SIZE(0..12))
    MAX-ACCESS read-only
    STATUS     current
    DESCRIPTION
            "-- empty --"
    ::= { hmStatusWlanMngmtApConfAutowdsTopoErrorsEntry 9 }

-- {COLUMN} 1.3.6.1.4.1.248.32.18.1.73.2.15.1.10
hmStatusWlanMngmtApConfAutowdsTopoErrorsEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eAutowdsProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20)
            }
    MAX-ACCESS read-only
    STATUS     current
    DESCRIPTION
            "-- empty --"
    ::= { hmStatusWlanMngmtApConfAutowdsTopoErrorsEntry 10 }

-- {NODE} 1.3.6.1.4.1.248.32.18.1.73.2.17
hmStatusWlanMngmtApConf11u OBJECT IDENTIFIER ::= { hmStatusWlanMngmtApConf 17 }

-- {TABLE} 1.3.6.1.4.1.248.32.18.1.73.2.17.1
hmStatusWlanMngmtApConf11u11u-NwTable OBJECT-TYPE
    SYNTAX     SEQUENCE OF HmStatusWlanMngmtApConf11u11u-NwEntry
    MAX-ACCESS not-accessible
    STATUS     current
    DESCRIPTION
            "IEEE802.11u-Networks"
    ::= { hmStatusWlanMngmtApConf11u 1 }

-- {ROW} 1.3.6.1.4.1.248.32.18.1.73.2.17.1.1
hmStatusWlanMngmtApConf11u11u-NwEntry OBJECT-TYPE
    SYNTAX     HmStatusWlanMngmtApConf11u11u-NwEntry
    MAX-ACCESS not-accessible
    STATUS     current
    DESCRIPTION
            ""
    INDEX {
            hmStatusWlanMngmtApConf11u11u-NwEntryName
          }
    ::= { hmStatusWlanMngmtApConf11u11u-NwTable 1 }

HmStatusWlanMngmtApConf11u11u-NwEntry ::= SEQUENCE {
            hmStatusWlanMngmtApConf11u11u-NwEntryName DisplayString,
            hmStatusWlanMngmtApConf11u11u-NwEntryOper INTEGER,
            hmStatusWlanMngmtApConf11u11u-NwEntryHs20 INTEGER,
            hmStatusWlanMngmtApConf11u11u-NwEntryInet INTEGER,
            hmStatusWlanMngmtApConf11u11u-NwEntryNwType INTEGER,
            hmStatusWlanMngmtApConf11u11u-NwEntryAsra INTEGER,
            hmStatusWlanMngmtApConf11u11u-NwEntryHESSIDT INTEGER,
            hmStatusWlanMngmtApConf11u11u-NwEntryHESSIDM MacAddress,
            hmStatusWlanMngmtApConf11u11u-NwEntryANQP-Prof DisplayString,
            hmStatusWlanMngmtApConf11u11u-NwEntryHs20-Prof DisplayString
    }

-- {COLUMN} 1.3.6.1.4.1.248.32.18.1.73.2.17.1.1.1
hmStatusWlanMngmtApConf11u11u-NwEntryName OBJECT-TYPE
    SYNTAX     DisplayString (SIZE(0..32))
    MAX-ACCESS read-only
    STATUS     current
    DESCRIPTION
            "-- empty --"
    ::= { hmStatusWlanMngmtApConf11u11u-NwEntry 1 }

-- {COLUMN} 1.3.6.1.4.1.248.32.18.1.73.2.17.1.1.2
hmStatusWlanMngmtApConf11u11u-NwEntryOper OBJECT-TYPE
    SYNTAX     INTEGER {
                  eNo (0),
                  eYes (1)
            }
    MAX-ACCESS read-only
    STATUS     current
    DESCRIPTION
            "Operating"
    ::= { hmStatusWlanMngmtApConf11u11u-NwEntry 2 }

-- {COLUMN} 1.3.6.1.4.1.248.32.18.1.73.2.17.1.1.3
hmStatusWlanMngmtApConf11u11u-NwEntryHs20 OBJECT-TYPE
    SYNTAX     INTEGER {
                  eNo (0),
                  eYes (1)
            }
    MAX-ACCESS read-only
    STATUS     current
    DESCRIPTION
            "Hotspot2.0"
    ::= { hmStatusWlanMngmtApConf11u11u-NwEntry 3 }

-- {COLUMN} 1.3.6.1.4.1.248.32.18.1.73.2.17.1.1.4
hmStatusWlanMngmtApConf11u11u-NwEntryInet OBJECT-TYPE
    SYNTAX     INTEGER {
                  eNo (0),
                  eYes (1)
            }
    MAX-ACCESS read-only
    STATUS     current
    DESCRIPTION
            "Internet"
    ::= { hmStatusWlanMngmtApConf11u11u-NwEntry 4 }

-- {COLUMN} 1.3.6.1.4.1.248.32.18.1.73.2.17.1.1.5
hmStatusWlanMngmtApConf11u11u-NwEntryNwType OBJECT-TYPE
    SYNTAX     INTEGER {
                  ePrivate (0),
                  ePrivateGuestacc (1),
                  ePublicCharge (2),
                  ePublicFree (3),
                  ePersonalDev (4),
                  eEmergency (5),
                  eExperimental (14),
                  eWildcard (15)
            }
    MAX-ACCESS read-only
    STATUS     current
    DESCRIPTION
            "Network-Type"
    ::= { hmStatusWlanMngmtApConf11u11u-NwEntry 5 }

-- {COLUMN} 1.3.6.1.4.1.248.32.18.1.73.2.17.1.1.6
hmStatusWlanMngmtApConf11u11u-NwEntryAsra OBJECT-TYPE
    SYNTAX     INTEGER {
                  eNo (0),
                  eYes (1)
            }
    MAX-ACCESS read-only
    STATUS     current
    DESCRIPTION
            "Asra"
    ::= { hmStatusWlanMngmtApConf11u11u-NwEntry 6 }

-- {COLUMN} 1.3.6.1.4.1.248.32.18.1.73.2.17.1.1.7
hmStatusWlanMngmtApConf11u11u-NwEntryHESSIDT OBJECT-TYPE
    SYNTAX     INTEGER {
                  eAuto (0),
                  eUser (1),
                  eNone (2)
            }
    MAX-ACCESS read-only
    STATUS     current
    DESCRIPTION
            "HESSID-Type"
    ::= { hmStatusWlanMngmtApConf11u11u-NwEntry 7 }

-- {COLUMN} 1.3.6.1.4.1.248.32.18.1.73.2.17.1.1.8
hmStatusWlanMngmtApConf11u11u-NwEntryHESSIDM OBJECT-TYPE
    SYNTAX     MacAddress
    MAX-ACCESS read-only
    STATUS     current
    DESCRIPTION
            "HESSID-MAC"
    ::= { hmStatusWlanMngmtApConf11u11u-NwEntry 8 }

-- {COLUMN} 1.3.6.1.4.1.248.32.18.1.73.2.17.1.1.10
hmStatusWlanMngmtApConf11u11u-NwEntryANQP-Prof OBJECT-TYPE
    SYNTAX     DisplayString (SIZE(0..32))
    MAX-ACCESS read-only
    STATUS     current
    DESCRIPTION
            "ANQP-Profile"
    ::= { hmStatusWlanMngmtApConf11u11u-NwEntry 10 }

-- {COLUMN} 1.3.6.1.4.1.248.32.18.1.73.2.17.1.1.12
hmStatusWlanMngmtApConf11u11u-NwEntryHs20-Prof OBJECT-TYPE
    SYNTAX     DisplayString (SIZE(0..32))
    MAX-ACCESS read-only
    STATUS     current
    DESCRIPTION
            "HS20-Profile"
    ::= { hmStatusWlanMngmtApConf11u11u-NwEntry 12 }

-- {TABLE} 1.3.6.1.4.1.248.32.18.1.73.2.17.2
hmStatusWlanMngmtApConf11uANQP-ProfsTable OBJECT-TYPE
    SYNTAX     SEQUENCE OF HmStatusWlanMngmtApConf11uANQP-ProfsEntry
    MAX-ACCESS not-accessible
    STATUS     current
    DESCRIPTION
            "ANQP-Profiles"
    ::= { hmStatusWlanMngmtApConf11u 2 }

-- {ROW} 1.3.6.1.4.1.248.32.18.1.73.2.17.2.1
hmStatusWlanMngmtApConf11uANQP-ProfsEntry OBJECT-TYPE
    SYNTAX     HmStatusWlanMngmtApConf11uANQP-ProfsEntry
    MAX-ACCESS not-accessible
    STATUS     current
    DESCRIPTION
            ""
    INDEX {
            hmStatusWlanMngmtApConf11uANQP-ProfsEntryName
          }
    ::= { hmStatusWlanMngmtApConf11uANQP-ProfsTable 1 }

HmStatusWlanMngmtApConf11uANQP-ProfsEntry ::= SEQUENCE {
            hmStatusWlanMngmtApConf11uANQP-ProfsEntryName DisplayString,
            hmStatusWlanMngmtApConf11uANQP-ProfsEntryIncOUI DisplayString,
            hmStatusWlanMngmtApConf11uANQP-ProfsEntryAddOUI DisplayString,
            hmStatusWlanMngmtApConf11uANQP-ProfsEntryDomainList DisplayString,
            hmStatusWlanMngmtApConf11uANQP-ProfsEntryNaiRealmList DisplayString,
            hmStatusWlanMngmtApConf11uANQP-ProfsEntryCellularList DisplayString,
            hmStatusWlanMngmtApConf11uANQP-ProfsEntryNetList DisplayString
    }

-- {COLUMN} 1.3.6.1.4.1.248.32.18.1.73.2.17.2.1.1
hmStatusWlanMngmtApConf11uANQP-ProfsEntryName OBJECT-TYPE
    SYNTAX     DisplayString (SIZE(0..32))
    MAX-ACCESS read-only
    STATUS     current
    DESCRIPTION
            "-- empty --"
    ::= { hmStatusWlanMngmtApConf11uANQP-ProfsEntry 1 }

-- {COLUMN} 1.3.6.1.4.1.248.32.18.1.73.2.17.2.1.2
hmStatusWlanMngmtApConf11uANQP-ProfsEntryIncOUI OBJECT-TYPE
    SYNTAX     DisplayString (SIZE(0..65))
    MAX-ACCESS read-only
    STATUS     current
    DESCRIPTION
            "Include-in-Beacon-OUI"
    ::= { hmStatusWlanMngmtApConf11uANQP-ProfsEntry 2 }

-- {COLUMN} 1.3.6.1.4.1.248.32.18.1.73.2.17.2.1.3
hmStatusWlanMngmtApConf11uANQP-ProfsEntryAddOUI OBJECT-TYPE
    SYNTAX     DisplayString (SIZE(0..65))
    MAX-ACCESS read-only
    STATUS     current
    DESCRIPTION
            "Additional-OUI"
    ::= { hmStatusWlanMngmtApConf11uANQP-ProfsEntry 3 }

-- {COLUMN} 1.3.6.1.4.1.248.32.18.1.73.2.17.2.1.4
hmStatusWlanMngmtApConf11uANQP-ProfsEntryDomainList OBJECT-TYPE
    SYNTAX     DisplayString (SIZE(0..65))
    MAX-ACCESS read-only
    STATUS     current
    DESCRIPTION
            "-- empty --"
    ::= { hmStatusWlanMngmtApConf11uANQP-ProfsEntry 4 }

-- {COLUMN} 1.3.6.1.4.1.248.32.18.1.73.2.17.2.1.5
hmStatusWlanMngmtApConf11uANQP-ProfsEntryNaiRealmList OBJECT-TYPE
    SYNTAX     DisplayString (SIZE(0..65))
    MAX-ACCESS read-only
    STATUS     current
    DESCRIPTION
            "-- empty --"
    ::= { hmStatusWlanMngmtApConf11uANQP-ProfsEntry 5 }

-- {COLUMN} 1.3.6.1.4.1.248.32.18.1.73.2.17.2.1.6
hmStatusWlanMngmtApConf11uANQP-ProfsEntryCellularList OBJECT-TYPE
    SYNTAX     DisplayString (SIZE(0..65))
    MAX-ACCESS read-only
    STATUS     current
    DESCRIPTION
            "-- empty --"
    ::= { hmStatusWlanMngmtApConf11uANQP-ProfsEntry 6 }

-- {COLUMN} 1.3.6.1.4.1.248.32.18.1.73.2.17.2.1.7
hmStatusWlanMngmtApConf11uANQP-ProfsEntryNetList OBJECT-TYPE
    SYNTAX     DisplayString (SIZE(0..65))
    MAX-ACCESS read-only
    STATUS     current
    DESCRIPTION
            "Network-Auth-Type-List"
    ::= { hmStatusWlanMngmtApConf11uANQP-ProfsEntry 7 }

-- {TABLE} 1.3.6.1.4.1.248.32.18.1.73.2.17.3
hmStatusWlanMngmtApConf11uHs20-ProfsTable OBJECT-TYPE
    SYNTAX     SEQUENCE OF HmStatusWlanMngmtApConf11uHs20-ProfsEntry
    MAX-ACCESS not-accessible
    STATUS     current
    DESCRIPTION
            "Hotspot2.0-Profiles"
    ::= { hmStatusWlanMngmtApConf11u 3 }

-- {ROW} 1.3.6.1.4.1.248.32.18.1.73.2.17.3.1
hmStatusWlanMngmtApConf11uHs20-ProfsEntry OBJECT-TYPE
    SYNTAX     HmStatusWlanMngmtApConf11uHs20-ProfsEntry
    MAX-ACCESS not-accessible
    STATUS     current
    DESCRIPTION
            ""
    INDEX {
            hmStatusWlanMngmtApConf11uHs20-ProfsEntryName
          }
    ::= { hmStatusWlanMngmtApConf11uHs20-ProfsTable 1 }

HmStatusWlanMngmtApConf11uHs20-ProfsEntry ::= SEQUENCE {
            hmStatusWlanMngmtApConf11uHs20-ProfsEntryName DisplayString,
            hmStatusWlanMngmtApConf11uHs20-ProfsEntryOperatorName DisplayString,
            hmStatusWlanMngmtApConf11uHs20-ProfsEntryConnCaps DisplayString,
            hmStatusWlanMngmtApConf11uHs20-ProfsEntryOpClass DisplayString
    }

-- {COLUMN} 1.3.6.1.4.1.248.32.18.1.73.2.17.3.1.1
hmStatusWlanMngmtApConf11uHs20-ProfsEntryName OBJECT-TYPE
    SYNTAX     DisplayString (SIZE(0..32))
    MAX-ACCESS read-only
    STATUS     current
    DESCRIPTION
            "-- empty --"
    ::= { hmStatusWlanMngmtApConf11uHs20-ProfsEntry 1 }

-- {COLUMN} 1.3.6.1.4.1.248.32.18.1.73.2.17.3.1.2
hmStatusWlanMngmtApConf11uHs20-ProfsEntryOperatorName OBJECT-TYPE
    SYNTAX     DisplayString (SIZE(0..65))
    MAX-ACCESS read-only
    STATUS     current
    DESCRIPTION
            "-- empty --"
    ::= { hmStatusWlanMngmtApConf11uHs20-ProfsEntry 2 }

-- {COLUMN} 1.3.6.1.4.1.248.32.18.1.73.2.17.3.1.3
hmStatusWlanMngmtApConf11uHs20-ProfsEntryConnCaps OBJECT-TYPE
    SYNTAX     DisplayString (SIZE(0..250))
    MAX-ACCESS read-only
    STATUS     current
    DESCRIPTION
            "Connection-Capabilities"
    ::= { hmStatusWlanMngmtApConf11uHs20-ProfsEntry 3 }

-- {COLUMN} 1.3.6.1.4.1.248.32.18.1.73.2.17.3.1.4
hmStatusWlanMngmtApConf11uHs20-ProfsEntryOpClass OBJECT-TYPE
    SYNTAX     DisplayString (SIZE(0..32))
    MAX-ACCESS read-only
    STATUS     current
    DESCRIPTION
            "Operating-Class"
    ::= { hmStatusWlanMngmtApConf11uHs20-ProfsEntry 4 }

-- {TABLE} 1.3.6.1.4.1.248.32.18.1.73.2.17.4
hmStatusWlanMngmtApConf11uNetAuthTable OBJECT-TYPE
    SYNTAX     SEQUENCE OF HmStatusWlanMngmtApConf11uNetAuthEntry
    MAX-ACCESS not-accessible
    STATUS     current
    DESCRIPTION
            "Network-Authentication-Type"
    ::= { hmStatusWlanMngmtApConf11u 4 }

-- {ROW} 1.3.6.1.4.1.248.32.18.1.73.2.17.4.1
hmStatusWlanMngmtApConf11uNetAuthEntry OBJECT-TYPE
    SYNTAX     HmStatusWlanMngmtApConf11uNetAuthEntry
    MAX-ACCESS not-accessible
    STATUS     current
    DESCRIPTION
            ""
    INDEX {
            hmStatusWlanMngmtApConf11uNetAuthEntryName
          }
    ::= { hmStatusWlanMngmtApConf11uNetAuthTable 1 }

HmStatusWlanMngmtApConf11uNetAuthEntry ::= SEQUENCE {
            hmStatusWlanMngmtApConf11uNetAuthEntryName DisplayString,
            hmStatusWlanMngmtApConf11uNetAuthEntryNetType INTEGER,
            hmStatusWlanMngmtApConf11uNetAuthEntryReUrl DisplayString
    }

-- {COLUMN} 1.3.6.1.4.1.248.32.18.1.73.2.17.4.1.1
hmStatusWlanMngmtApConf11uNetAuthEntryName OBJECT-TYPE
    SYNTAX     DisplayString (SIZE(0..32))
    MAX-ACCESS read-only
    STATUS     current
    DESCRIPTION
            "-- empty --"
    ::= { hmStatusWlanMngmtApConf11uNetAuthEntry 1 }

-- {COLUMN} 1.3.6.1.4.1.248.32.18.1.73.2.17.4.1.2
hmStatusWlanMngmtApConf11uNetAuthEntryNetType OBJECT-TYPE
    SYNTAX     INTEGER {
                  eAcceptTermsCond (0),
                  eOnlineEnrollment (1),
                  eHttpRedirection (2),
                  eDnsRedirection (3)
            }
    MAX-ACCESS read-only
    STATUS     current
    DESCRIPTION
            "Network-Auth-Type"
    ::= { hmStatusWlanMngmtApConf11uNetAuthEntry 2 }

-- {COLUMN} 1.3.6.1.4.1.248.32.18.1.73.2.17.4.1.3
hmStatusWlanMngmtApConf11uNetAuthEntryReUrl OBJECT-TYPE
    SYNTAX     DisplayString (SIZE(0..65))
    MAX-ACCESS read-only
    STATUS     current
    DESCRIPTION
            "Redirect-URL"
    ::= { hmStatusWlanMngmtApConf11uNetAuthEntry 3 }

-- {TABLE} 1.3.6.1.4.1.248.32.18.1.73.2.17.5
hmStatusWlanMngmtApConf11uCellListTable OBJECT-TYPE
    SYNTAX     SEQUENCE OF HmStatusWlanMngmtApConf11uCellListEntry
    MAX-ACCESS not-accessible
    STATUS     current
    DESCRIPTION
            "Cellular-Network-Information-List"
    ::= { hmStatusWlanMngmtApConf11u 5 }

-- {ROW} 1.3.6.1.4.1.248.32.18.1.73.2.17.5.1
hmStatusWlanMngmtApConf11uCellListEntry OBJECT-TYPE
    SYNTAX     HmStatusWlanMngmtApConf11uCellListEntry
    MAX-ACCESS not-accessible
    STATUS     current
    DESCRIPTION
            ""
    INDEX {
            hmStatusWlanMngmtApConf11uCellListEntryName
          }
    ::= { hmStatusWlanMngmtApConf11uCellListTable 1 }

HmStatusWlanMngmtApConf11uCellListEntry ::= SEQUENCE {
            hmStatusWlanMngmtApConf11uCellListEntryName DisplayString,
            hmStatusWlanMngmtApConf11uCellListEntryCountry DisplayString,
            hmStatusWlanMngmtApConf11uCellListEntryNetwork DisplayString
    }

-- {COLUMN} 1.3.6.1.4.1.248.32.18.1.73.2.17.5.1.1
hmStatusWlanMngmtApConf11uCellListEntryName OBJECT-TYPE
    SYNTAX     DisplayString (SIZE(0..32))
    MAX-ACCESS read-only
    STATUS     current
    DESCRIPTION
            "-- empty --"
    ::= { hmStatusWlanMngmtApConf11uCellListEntry 1 }

-- {COLUMN} 1.3.6.1.4.1.248.32.18.1.73.2.17.5.1.2
hmStatusWlanMngmtApConf11uCellListEntryCountry OBJECT-TYPE
    SYNTAX     DisplayString (SIZE(0..3))
    MAX-ACCESS read-only
    STATUS     current
    DESCRIPTION
            "Country-Code"
    ::= { hmStatusWlanMngmtApConf11uCellListEntry 2 }

-- {COLUMN} 1.3.6.1.4.1.248.32.18.1.73.2.17.5.1.3
hmStatusWlanMngmtApConf11uCellListEntryNetwork OBJECT-TYPE
    SYNTAX     DisplayString (SIZE(0..3))
    MAX-ACCESS read-only
    STATUS     current
    DESCRIPTION
            "Network-Code"
    ::= { hmStatusWlanMngmtApConf11uCellListEntry 3 }

-- {TABLE} 1.3.6.1.4.1.248.32.18.1.73.2.17.6
hmStatusWlanMngmtApConf11uVenueNameTable OBJECT-TYPE
    SYNTAX     SEQUENCE OF HmStatusWlanMngmtApConf11uVenueNameEntry
    MAX-ACCESS not-accessible
    STATUS     current
    DESCRIPTION
            "-- empty --"
    ::= { hmStatusWlanMngmtApConf11u 6 }

-- {ROW} 1.3.6.1.4.1.248.32.18.1.73.2.17.6.1
hmStatusWlanMngmtApConf11uVenueNameEntry OBJECT-TYPE
    SYNTAX     HmStatusWlanMngmtApConf11uVenueNameEntry
    MAX-ACCESS not-accessible
    STATUS     current
    DESCRIPTION
            ""
    INDEX {
            hmStatusWlanMngmtApConf11uVenueNameEntryName,
            hmStatusWlanMngmtApConf11uVenueNameEntryLanguage
          }
    ::= { hmStatusWlanMngmtApConf11uVenueNameTable 1 }

HmStatusWlanMngmtApConf11uVenueNameEntry ::= SEQUENCE {
            hmStatusWlanMngmtApConf11uVenueNameEntryName DisplayString,
            hmStatusWlanMngmtApConf11uVenueNameEntryLanguage INTEGER,
            hmStatusWlanMngmtApConf11uVenueNameEntryVenueName DisplayString
    }

-- {COLUMN} 1.3.6.1.4.1.248.32.18.1.73.2.17.6.1.1
hmStatusWlanMngmtApConf11uVenueNameEntryName OBJECT-TYPE
    SYNTAX     DisplayString (SIZE(0..32))
    MAX-ACCESS read-only
    STATUS     current
    DESCRIPTION
            "-- empty --"
    ::= { hmStatusWlanMngmtApConf11uVenueNameEntry 1 }

-- {COLUMN} 1.3.6.1.4.1.248.32.18.1.73.2.17.6.1.2
hmStatusWlanMngmtApConf11uVenueNameEntryLanguage OBJECT-TYPE
    SYNTAX     INTEGER {
                  eNone (0),
                  eEnglish (1),
                  eGerman (2),
                  eChinese (3),
                  eSpanish (4),
                  eFrench (5),
                  eItalian (6),
                  eRussian (7),
                  eDutch (8),
                  eTurkish (9),
                  ePortuguese (10),
                  ePolish (11),
                  eCzech (12),
                  eArabic (13)
            }
    MAX-ACCESS read-only
    STATUS     current
    DESCRIPTION
            "-- empty --"
    ::= { hmStatusWlanMngmtApConf11uVenueNameEntry 2 }

-- {COLUMN} 1.3.6.1.4.1.248.32.18.1.73.2.17.6.1.3
hmStatusWlanMngmtApConf11uVenueNameEntryVenueName OBJECT-TYPE
    SYNTAX     DisplayString (SIZE(0..65))
    MAX-ACCESS read-only
    STATUS     current
    DESCRIPTION
            "-- empty --"
    ::= { hmStatusWlanMngmtApConf11uVenueNameEntry 3 }

-- {TABLE} 1.3.6.1.4.1.248.32.18.1.73.2.17.7
hmStatusWlanMngmtApConf11uNAIsTable OBJECT-TYPE
    SYNTAX     SEQUENCE OF HmStatusWlanMngmtApConf11uNAIsEntry
    MAX-ACCESS not-accessible
    STATUS     current
    DESCRIPTION
            "NAI-Realms"
    ::= { hmStatusWlanMngmtApConf11u 7 }

-- {ROW} 1.3.6.1.4.1.248.32.18.1.73.2.17.7.1
hmStatusWlanMngmtApConf11uNAIsEntry OBJECT-TYPE
    SYNTAX     HmStatusWlanMngmtApConf11uNAIsEntry
    MAX-ACCESS not-accessible
    STATUS     current
    DESCRIPTION
            ""
    INDEX {
            hmStatusWlanMngmtApConf11uNAIsEntryName
          }
    ::= { hmStatusWlanMngmtApConf11uNAIsTable 1 }

HmStatusWlanMngmtApConf11uNAIsEntry ::= SEQUENCE {
            hmStatusWlanMngmtApConf11uNAIsEntryName DisplayString,
            hmStatusWlanMngmtApConf11uNAIsEntryNaiRealm DisplayString,
            hmStatusWlanMngmtApConf11uNAIsEntryEapMethod INTEGER,
            hmStatusWlanMngmtApConf11uNAIsEntryAuthPar DisplayString
    }

-- {COLUMN} 1.3.6.1.4.1.248.32.18.1.73.2.17.7.1.1
hmStatusWlanMngmtApConf11uNAIsEntryName OBJECT-TYPE
    SYNTAX     DisplayString (SIZE(0..32))
    MAX-ACCESS read-only
    STATUS     current
    DESCRIPTION
            "-- empty --"
    ::= { hmStatusWlanMngmtApConf11uNAIsEntry 1 }

-- {COLUMN} 1.3.6.1.4.1.248.32.18.1.73.2.17.7.1.2
hmStatusWlanMngmtApConf11uNAIsEntryNaiRealm OBJECT-TYPE
    SYNTAX     DisplayString (SIZE(0..32))
    MAX-ACCESS read-only
    STATUS     current
    DESCRIPTION
            "-- empty --"
    ::= { hmStatusWlanMngmtApConf11uNAIsEntry 2 }

-- {COLUMN} 1.3.6.1.4.1.248.32.18.1.73.2.17.7.1.3
hmStatusWlanMngmtApConf11uNAIsEntryEapMethod OBJECT-TYPE
    SYNTAX     INTEGER {
                  eNone (0),
                  eEapTls (13),
                  eEapSim (18),
                  eEapTtls (21),
                  eEapAka (23)
            }
    MAX-ACCESS read-only
    STATUS     current
    DESCRIPTION
            "-- empty --"
    ::= { hmStatusWlanMngmtApConf11uNAIsEntry 3 }

-- {COLUMN} 1.3.6.1.4.1.248.32.18.1.73.2.17.7.1.4
hmStatusWlanMngmtApConf11uNAIsEntryAuthPar OBJECT-TYPE
    SYNTAX     DisplayString (SIZE(0..65))
    MAX-ACCESS read-only
    STATUS     current
    DESCRIPTION
            "Auth-Parameter-List"
    ::= { hmStatusWlanMngmtApConf11uNAIsEntry 4 }

-- {TABLE} 1.3.6.1.4.1.248.32.18.1.73.2.17.8
hmStatusWlanMngmtApConf11uOperatorListTable OBJECT-TYPE
    SYNTAX     SEQUENCE OF HmStatusWlanMngmtApConf11uOperatorListEntry
    MAX-ACCESS not-accessible
    STATUS     current
    DESCRIPTION
            "-- empty --"
    ::= { hmStatusWlanMngmtApConf11u 8 }

-- {ROW} 1.3.6.1.4.1.248.32.18.1.73.2.17.8.1
hmStatusWlanMngmtApConf11uOperatorListEntry OBJECT-TYPE
    SYNTAX     HmStatusWlanMngmtApConf11uOperatorListEntry
    MAX-ACCESS not-accessible
    STATUS     current
    DESCRIPTION
            ""
    INDEX {
            hmStatusWlanMngmtApConf11uOperatorListEntryName,
            hmStatusWlanMngmtApConf11uOperatorListEntryLanguage
          }
    ::= { hmStatusWlanMngmtApConf11uOperatorListTable 1 }

HmStatusWlanMngmtApConf11uOperatorListEntry ::= SEQUENCE {
            hmStatusWlanMngmtApConf11uOperatorListEntryName DisplayString,
            hmStatusWlanMngmtApConf11uOperatorListEntryLanguage INTEGER,
            hmStatusWlanMngmtApConf11uOperatorListEntryOperatorName DisplayString
    }

-- {COLUMN} 1.3.6.1.4.1.248.32.18.1.73.2.17.8.1.1
hmStatusWlanMngmtApConf11uOperatorListEntryName OBJECT-TYPE
    SYNTAX     DisplayString (SIZE(0..32))
    MAX-ACCESS read-only
    STATUS     current
    DESCRIPTION
            "-- empty --"
    ::= { hmStatusWlanMngmtApConf11uOperatorListEntry 1 }

-- {COLUMN} 1.3.6.1.4.1.248.32.18.1.73.2.17.8.1.2
hmStatusWlanMngmtApConf11uOperatorListEntryLanguage OBJECT-TYPE
    SYNTAX     INTEGER {
                  eNone (0),
                  eEnglish (1),
                  eGerman (2),
                  eChinese (3),
                  eSpanish (4),
                  eFrench (5),
                  eItalian (6),
                  eRussian (7),
                  eDutch (8),
                  eTurkish (9),
                  ePortuguese (10),
                  ePolish (11),
                  eCzech (12),
                  eArabic (13)
            }
    MAX-ACCESS read-only
    STATUS     current
    DESCRIPTION
            "-- empty --"
    ::= { hmStatusWlanMngmtApConf11uOperatorListEntry 2 }

-- {COLUMN} 1.3.6.1.4.1.248.32.18.1.73.2.17.8.1.3
hmStatusWlanMngmtApConf11uOperatorListEntryOperatorName OBJECT-TYPE
    SYNTAX     DisplayString (SIZE(0..65))
    MAX-ACCESS read-only
    STATUS     current
    DESCRIPTION
            "-- empty --"
    ::= { hmStatusWlanMngmtApConf11uOperatorListEntry 3 }

-- {TABLE} 1.3.6.1.4.1.248.32.18.1.73.2.17.9
hmStatusWlanMngmtApConf11uGeneralTable OBJECT-TYPE
    SYNTAX     SEQUENCE OF HmStatusWlanMngmtApConf11uGeneralEntry
    MAX-ACCESS not-accessible
    STATUS     current
    DESCRIPTION
            "-- empty --"
    ::= { hmStatusWlanMngmtApConf11u 9 }

-- {ROW} 1.3.6.1.4.1.248.32.18.1.73.2.17.9.1
hmStatusWlanMngmtApConf11uGeneralEntry OBJECT-TYPE
    SYNTAX     HmStatusWlanMngmtApConf11uGeneralEntry
    MAX-ACCESS not-accessible
    STATUS     current
    DESCRIPTION
            ""
    INDEX {
            hmStatusWlanMngmtApConf11uGeneralEntryName
          }
    ::= { hmStatusWlanMngmtApConf11uGeneralTable 1 }

HmStatusWlanMngmtApConf11uGeneralEntry ::= SEQUENCE {
            hmStatusWlanMngmtApConf11uGeneralEntryName DisplayString,
            hmStatusWlanMngmtApConf11uGeneralEntryLinkStatus INTEGER,
            hmStatusWlanMngmtApConf11uGeneralEntryDownlinkSpeed Integer32,
            hmStatusWlanMngmtApConf11uGeneralEntryUplinkSpeed Integer32,
            hmStatusWlanMngmtApConf11uGeneralEntryIpv4AddrType INTEGER,
            hmStatusWlanMngmtApConf11uGeneralEntryIpv6AddrType INTEGER,
            hmStatusWlanMngmtApConf11uGeneralEntryVenueGroup INTEGER,
            hmStatusWlanMngmtApConf11uGeneralEntryVenueType Integer32,
            hmStatusWlanMngmtApConf11uGeneralEntryVenueName DisplayString
    }

-- {COLUMN} 1.3.6.1.4.1.248.32.18.1.73.2.17.9.1.1
hmStatusWlanMngmtApConf11uGeneralEntryName OBJECT-TYPE
    SYNTAX     DisplayString (SIZE(0..32))
    MAX-ACCESS read-only
    STATUS     current
    DESCRIPTION
            "-- empty --"
    ::= { hmStatusWlanMngmtApConf11uGeneralEntry 1 }

-- {COLUMN} 1.3.6.1.4.1.248.32.18.1.73.2.17.9.1.2
hmStatusWlanMngmtApConf11uGeneralEntryLinkStatus OBJECT-TYPE
    SYNTAX     INTEGER {
                  eAuto (0),
                  eLinkUp (1),
                  eLinkDown (2),
                  eLinkTest (3)
            }
    MAX-ACCESS read-only
    STATUS     current
    DESCRIPTION
            "-- empty --"
    ::= { hmStatusWlanMngmtApConf11uGeneralEntry 2 }

-- {COLUMN} 1.3.6.1.4.1.248.32.18.1.73.2.17.9.1.3
hmStatusWlanMngmtApConf11uGeneralEntryDownlinkSpeed OBJECT-TYPE
    SYNTAX     Integer32 (0..2147483647)
    MAX-ACCESS read-only
    STATUS     current
    DESCRIPTION
            "-- empty --"
    ::= { hmStatusWlanMngmtApConf11uGeneralEntry 3 }

-- {COLUMN} 1.3.6.1.4.1.248.32.18.1.73.2.17.9.1.4
hmStatusWlanMngmtApConf11uGeneralEntryUplinkSpeed OBJECT-TYPE
    SYNTAX     Integer32 (0..2147483647)
    MAX-ACCESS read-only
    STATUS     current
    DESCRIPTION
            "-- empty --"
    ::= { hmStatusWlanMngmtApConf11uGeneralEntry 4 }

-- {COLUMN} 1.3.6.1.4.1.248.32.18.1.73.2.17.9.1.5
hmStatusWlanMngmtApConf11uGeneralEntryIpv4AddrType OBJECT-TYPE
    SYNTAX     INTEGER {
                  eNotAvailable (0),
                  ePublicAddrAvailable (1),
                  ePortRestrAddrAvail (2),
                  eSingleNatPrivAddrAvail (3),
                  eDoubleNatPrivAddrAvail (4),
                  ePortRestrSingleNatAddrAvail (5),
                  ePortRestrDoubleNatAddrAvail (6),
                  eAvailabilityNotKnown (7)
            }
    MAX-ACCESS read-only
    STATUS     current
    DESCRIPTION
            "-- empty --"
    ::= { hmStatusWlanMngmtApConf11uGeneralEntry 5 }

-- {COLUMN} 1.3.6.1.4.1.248.32.18.1.73.2.17.9.1.6
hmStatusWlanMngmtApConf11uGeneralEntryIpv6AddrType OBJECT-TYPE
    SYNTAX     INTEGER {
                  eNotAvailable (0),
                  eAvailable (1),
                  eAvailabilityNotKnown (2)
            }
    MAX-ACCESS read-only
    STATUS     current
    DESCRIPTION
            "-- empty --"
    ::= { hmStatusWlanMngmtApConf11uGeneralEntry 6 }

-- {COLUMN} 1.3.6.1.4.1.248.32.18.1.73.2.17.9.1.7
hmStatusWlanMngmtApConf11uGeneralEntryVenueGroup OBJECT-TYPE
    SYNTAX     INTEGER {
                  eUnspecified (0),
                  eAssembly (1),
                  eBusiness (2),
                  eEducational (3),
                  eFactoryAndIndustrial (4),
                  eInstitutional (5),
                  eMercantile (6),
                  eResindential (7),
                  eStorage (8),
                  eUtilityAndMiscellaneous (9),
                  eVehicular (10),
                  eOutdoor (11)
            }
    MAX-ACCESS read-only
    STATUS     current
    DESCRIPTION
            "-- empty --"
    ::= { hmStatusWlanMngmtApConf11uGeneralEntry 7 }

-- {COLUMN} 1.3.6.1.4.1.248.32.18.1.73.2.17.9.1.8
hmStatusWlanMngmtApConf11uGeneralEntryVenueType OBJECT-TYPE
    SYNTAX     Integer32 (0..255)
    MAX-ACCESS read-only
    STATUS     current
    DESCRIPTION
            "-- empty --"
    ::= { hmStatusWlanMngmtApConf11uGeneralEntry 8 }

-- {COLUMN} 1.3.6.1.4.1.248.32.18.1.73.2.17.9.1.9
hmStatusWlanMngmtApConf11uGeneralEntryVenueName OBJECT-TYPE
    SYNTAX     DisplayString (SIZE(0..32))
    MAX-ACCESS read-only
    STATUS     current
    DESCRIPTION
            "-- empty --"
    ::= { hmStatusWlanMngmtApConf11uGeneralEntry 9 }

-- {TABLE} 1.3.6.1.4.1.248.32.18.1.73.2.19
hmStatusWlanMngmtApConfGroupsTable OBJECT-TYPE
    SYNTAX     SEQUENCE OF HmStatusWlanMngmtApConfGroupsEntry
    MAX-ACCESS not-accessible
    STATUS     current
    DESCRIPTION
            "-- empty --"
    ::= { hmStatusWlanMngmtApConf 19 }

-- {ROW} 1.3.6.1.4.1.248.32.18.1.73.2.19.1
hmStatusWlanMngmtApConfGroupsEntry OBJECT-TYPE
    SYNTAX     HmStatusWlanMngmtApConfGroupsEntry
    MAX-ACCESS not-accessible
    STATUS     current
    DESCRIPTION
            ""
    INDEX {
            hmStatusWlanMngmtApConfGroupsEntryName
          }
    ::= { hmStatusWlanMngmtApConfGroupsTable 1 }

HmStatusWlanMngmtApConfGroupsEntry ::= SEQUENCE {
            hmStatusWlanMngmtApConfGroupsEntryName DisplayString,
            hmStatusWlanMngmtApConfGroupsEntryProfile DisplayString,
            hmStatusWlanMngmtApConfGroupsEntryApIntranet DisplayString,
            hmStatusWlanMngmtApConfGroupsEntryIpv4ReferencePoolStart DisplayString,
            hmStatusWlanMngmtApConfGroupsEntryIpv4ReferencePoolEnd DisplayString,
            hmStatusWlanMngmtApConfGroupsEntryClientSteeringProfile DisplayString,
            hmStatusWlanMngmtApConfGroupsEntryIbeaconProfile DisplayString
    }

-- {COLUMN} 1.3.6.1.4.1.248.32.18.1.73.2.19.1.1
hmStatusWlanMngmtApConfGroupsEntryName OBJECT-TYPE
    SYNTAX     DisplayString (SIZE(0..31))
    MAX-ACCESS read-only
    STATUS     current
    DESCRIPTION
            "-- empty --"
    ::= { hmStatusWlanMngmtApConfGroupsEntry 1 }

-- {COLUMN} 1.3.6.1.4.1.248.32.18.1.73.2.19.1.2
hmStatusWlanMngmtApConfGroupsEntryProfile OBJECT-TYPE
    SYNTAX     DisplayString (SIZE(0..31))
    MAX-ACCESS read-only
    STATUS     current
    DESCRIPTION
            "-- empty --"
    ::= { hmStatusWlanMngmtApConfGroupsEntry 2 }

-- {COLUMN} 1.3.6.1.4.1.248.32.18.1.73.2.19.1.3
hmStatusWlanMngmtApConfGroupsEntryApIntranet OBJECT-TYPE
    SYNTAX     DisplayString (SIZE(0..31))
    MAX-ACCESS read-only
    STATUS     current
    DESCRIPTION
            "-- empty --"
    ::= { hmStatusWlanMngmtApConfGroupsEntry 3 }

-- {COLUMN} 1.3.6.1.4.1.248.32.18.1.73.2.19.1.4
hmStatusWlanMngmtApConfGroupsEntryIpv4ReferencePoolStart OBJECT-TYPE
    SYNTAX     DisplayString (SIZE(0..15))
    MAX-ACCESS read-only
    STATUS     current
    DESCRIPTION
            "-- empty --"
    ::= { hmStatusWlanMngmtApConfGroupsEntry 4 }

-- {COLUMN} 1.3.6.1.4.1.248.32.18.1.73.2.19.1.5
hmStatusWlanMngmtApConfGroupsEntryIpv4ReferencePoolEnd OBJECT-TYPE
    SYNTAX     DisplayString (SIZE(0..15))
    MAX-ACCESS read-only
    STATUS     current
    DESCRIPTION
            "-- empty --"
    ::= { hmStatusWlanMngmtApConfGroupsEntry 5 }

-- {COLUMN} 1.3.6.1.4.1.248.32.18.1.73.2.19.1.6
hmStatusWlanMngmtApConfGroupsEntryClientSteeringProfile OBJECT-TYPE
    SYNTAX     DisplayString (SIZE(0..31))
    MAX-ACCESS read-only
    STATUS     current
    DESCRIPTION
            "-- empty --"
    ::= { hmStatusWlanMngmtApConfGroupsEntry 6 }

-- {COLUMN} 1.3.6.1.4.1.248.32.18.1.73.2.19.1.7
hmStatusWlanMngmtApConfGroupsEntryIbeaconProfile OBJECT-TYPE
    SYNTAX     DisplayString (SIZE(0..31))
    MAX-ACCESS read-only
    STATUS     current
    DESCRIPTION
            "-- empty --"
    ::= { hmStatusWlanMngmtApConfGroupsEntry 7 }

-- {TABLE} 1.3.6.1.4.1.248.32.18.1.73.2.20
hmStatusWlanMngmtApConfGroupsConfigErrorsTable OBJECT-TYPE
    SYNTAX     SEQUENCE OF HmStatusWlanMngmtApConfGroupsConfigErrorsEntry
    MAX-ACCESS not-accessible
    STATUS     current
    DESCRIPTION
            "-- empty --"
    ::= { hmStatusWlanMngmtApConf 20 }

-- {ROW} 1.3.6.1.4.1.248.32.18.1.73.2.20.1
hmStatusWlanMngmtApConfGroupsConfigErrorsEntry OBJECT-TYPE
    SYNTAX     HmStatusWlanMngmtApConfGroupsConfigErrorsEntry
    MAX-ACCESS not-accessible
    STATUS     current
    DESCRIPTION
            ""
    INDEX {
            hmStatusWlanMngmtApConfGroupsConfigErrorsEntryIndex
          }
    ::= { hmStatusWlanMngmtApConfGroupsConfigErrorsTable 1 }

HmStatusWlanMngmtApConfGroupsConfigErrorsEntry ::= SEQUENCE {
            hmStatusWlanMngmtApConfGroupsConfigErrorsEntryIndex Integer32,
            hmStatusWlanMngmtApConfGroupsConfigErrorsEntryGroup DisplayString,
            hmStatusWlanMngmtApConfGroupsConfigErrorsEntryError INTEGER
    }

-- {COLUMN} 1.3.6.1.4.1.248.32.18.1.73.2.20.1.1
hmStatusWlanMngmtApConfGroupsConfigErrorsEntryIndex OBJECT-TYPE
    SYNTAX     Integer32 (0..2147483647)
    MAX-ACCESS read-only
    STATUS     current
    DESCRIPTION
            "-- empty --"
    ::= { hmStatusWlanMngmtApConfGroupsConfigErrorsEntry 1 }

-- {COLUMN} 1.3.6.1.4.1.248.32.18.1.73.2.20.1.2
hmStatusWlanMngmtApConfGroupsConfigErrorsEntryGroup OBJECT-TYPE
    SYNTAX     DisplayString (SIZE(0..31))
    MAX-ACCESS read-only
    STATUS     current
    DESCRIPTION
            "-- empty --"
    ::= { hmStatusWlanMngmtApConfGroupsConfigErrorsEntry 2 }

-- {COLUMN} 1.3.6.1.4.1.248.32.18.1.73.2.20.1.3
hmStatusWlanMngmtApConfGroupsConfigErrorsEntryError OBJECT-TYPE
    SYNTAX     INTEGER {
                  eIntranetNotFound (1),
                  eProfileNotFound (2),
                  eGroupNotFound (3)
            }
    MAX-ACCESS read-only
    STATUS     current
    DESCRIPTION
            "-- empty --"
    ::= { hmStatusWlanMngmtApConfGroupsConfigErrorsEntry 3 }

-- {TABLE} 1.3.6.1.4.1.248.32.18.1.73.2.21
hmStatusWlanMngmtApConfTagGroupsTable OBJECT-TYPE
    SYNTAX     SEQUENCE OF HmStatusWlanMngmtApConfTagGroupsEntry
    MAX-ACCESS not-accessible
    STATUS     current
    DESCRIPTION
            "-- empty --"
    ::= { hmStatusWlanMngmtApConf 21 }

-- {ROW} 1.3.6.1.4.1.248.32.18.1.73.2.21.1
hmStatusWlanMngmtApConfTagGroupsEntry OBJECT-TYPE
    SYNTAX     HmStatusWlanMngmtApConfTagGroupsEntry
    MAX-ACCESS not-accessible
    STATUS     current
    DESCRIPTION
            ""
    INDEX {
            hmStatusWlanMngmtApConfTagGroupsEntryName
          }
    ::= { hmStatusWlanMngmtApConfTagGroupsTable 1 }

HmStatusWlanMngmtApConfTagGroupsEntry ::= SEQUENCE {
            hmStatusWlanMngmtApConfTagGroupsEntryName DisplayString
    }

-- {COLUMN} 1.3.6.1.4.1.248.32.18.1.73.2.21.1.1
hmStatusWlanMngmtApConfTagGroupsEntryName OBJECT-TYPE
    SYNTAX     DisplayString (SIZE(0..31))
    MAX-ACCESS read-only
    STATUS     current
    DESCRIPTION
            "-- empty --"
    ::= { hmStatusWlanMngmtApConfTagGroupsEntry 1 }

-- {TABLE} 1.3.6.1.4.1.248.32.18.1.73.2.22
hmStatusWlanMngmtApConfLedProfErrorsTable OBJECT-TYPE
    SYNTAX     SEQUENCE OF HmStatusWlanMngmtApConfLedProfErrorsEntry
    MAX-ACCESS not-accessible
    STATUS     current
    DESCRIPTION
            "-- empty --"
    ::= { hmStatusWlanMngmtApConf 22 }

-- {ROW} 1.3.6.1.4.1.248.32.18.1.73.2.22.1
hmStatusWlanMngmtApConfLedProfErrorsEntry OBJECT-TYPE
    SYNTAX     HmStatusWlanMngmtApConfLedProfErrorsEntry
    MAX-ACCESS not-accessible
    STATUS     current
    DESCRIPTION
            ""
    INDEX {
            hmStatusWlanMngmtApConfLedProfErrorsEntryIndex
          }
    ::= { hmStatusWlanMngmtApConfLedProfErrorsTable 1 }

HmStatusWlanMngmtApConfLedProfErrorsEntry ::= SEQUENCE {
            hmStatusWlanMngmtApConfLedProfErrorsEntryIndex Integer32,
            hmStatusWlanMngmtApConfLedProfErrorsEntryName DisplayString,
            hmStatusWlanMngmtApConfLedProfErrorsEntryError INTEGER
    }

-- {COLUMN} 1.3.6.1.4.1.248.32.18.1.73.2.22.1.1
hmStatusWlanMngmtApConfLedProfErrorsEntryIndex OBJECT-TYPE
    SYNTAX     Integer32 (0..2147483647)
    MAX-ACCESS read-only
    STATUS     current
    DESCRIPTION
            "-- empty --"
    ::= { hmStatusWlanMngmtApConfLedProfErrorsEntry 1 }

-- {COLUMN} 1.3.6.1.4.1.248.32.18.1.73.2.22.1.2
hmStatusWlanMngmtApConfLedProfErrorsEntryName OBJECT-TYPE
    SYNTAX     DisplayString (SIZE(0..31))
    MAX-ACCESS read-only
    STATUS     current
    DESCRIPTION
            "-- empty --"
    ::= { hmStatusWlanMngmtApConfLedProfErrorsEntry 2 }

-- {COLUMN} 1.3.6.1.4.1.248.32.18.1.73.2.22.1.3
hmStatusWlanMngmtApConfLedProfErrorsEntryError OBJECT-TYPE
    SYNTAX     INTEGER {
                  eNone (0),
                  eInheritanceError (1),
                  eNoProfile (2),
                  eProfileNotFound (3),
                  eNoMemory (4),
                  eSsidMissing (5),
                  eNetworkNotFound (6),
                  eApParametersNotFound (7),
                  eApIntranetNotFound (8),
                  eRadiusProfileNotFound (9),
                  eAutowdsProfileNotFound (10),
                  eMasterEqualToSlave (11),
                  eNoProfileEitherGroupFound (12),
                  eInfoProfileWinsGroup (13),
                  eGroupWrongDefined (14),
                  eSsidWlcTunnelMissing (15),
                  eSsidInterStationTrafficAllowed (16),
                  eTooManyNetworksForAutowds (17),
                  eReportedByAp (18),
                  eWirelessEpaperProfileNotFound (19),
                  eLedProfileNotFound (20)
            }
    MAX-ACCESS read-only
    STATUS     current
    DESCRIPTION
            "-- empty --"
    ::= { hmStatusWlanMngmtApConfLedProfErrorsEntry 3 }

-- {TABLE} 1.3.6.1.4.1.248.32.18.1.73.2.23
hmStatusWlanMngmtApConfLedProfilesTable OBJECT-TYPE
    SYNTAX     SEQUENCE OF HmStatusWlanMngmtApConfLedProfilesEntry
    MAX-ACCESS not-accessible
    STATUS     current
    DESCRIPTION
            "-- empty --"
    ::= { hmStatusWlanMngmtApConf 23 }

-- {ROW} 1.3.6.1.4.1.248.32.18.1.73.2.23.1
hmStatusWlanMngmtApConfLedProfilesEntry OBJECT-TYPE
    SYNTAX     HmStatusWlanMngmtApConfLedProfilesEntry
    MAX-ACCESS not-accessible
    STATUS     current
    DESCRIPTION
            ""
    INDEX {
            hmStatusWlanMngmtApConfLedProfilesEntryName
          }
    ::= { hmStatusWlanMngmtApConfLedProfilesTable 1 }

HmStatusWlanMngmtApConfLedProfilesEntry ::= SEQUENCE {
            hmStatusWlanMngmtApConfLedProfilesEntryName DisplayString,
            hmStatusWlanMngmtApConfLedProfilesEntryLedMode INTEGER,
            hmStatusWlanMngmtApConfLedProfilesEntryLedOffSeconds Integer32
    }

-- {COLUMN} 1.3.6.1.4.1.248.32.18.1.73.2.23.1.1
hmStatusWlanMngmtApConfLedProfilesEntryName OBJECT-TYPE
    SYNTAX     DisplayString (SIZE(0..31))
    MAX-ACCESS read-only
    STATUS     current
    DESCRIPTION
            "-- empty --"
    ::= { hmStatusWlanMngmtApConfLedProfilesEntry 1 }

-- {COLUMN} 1.3.6.1.4.1.248.32.18.1.73.2.23.1.4
hmStatusWlanMngmtApConfLedProfilesEntryLedMode OBJECT-TYPE
    SYNTAX     INTEGER {
                  eOn (0),
                  eOff (1),
                  eTimedOff (2)
            }
    MAX-ACCESS read-only
    STATUS     current
    DESCRIPTION
            "-- empty --"
    ::= { hmStatusWlanMngmtApConfLedProfilesEntry 4 }

-- {COLUMN} 1.3.6.1.4.1.248.32.18.1.73.2.23.1.5
hmStatusWlanMngmtApConfLedProfilesEntryLedOffSeconds OBJECT-TYPE
    SYNTAX     Integer32 (0..2147483647)
    MAX-ACCESS read-only
    STATUS     current
    DESCRIPTION
            "-- empty --"
    ::= { hmStatusWlanMngmtApConfLedProfilesEntry 5 }

-- {NODE} 1.3.6.1.4.1.248.32.18.1.73.2.24
hmStatusWlanMngmtApConfLbs OBJECT IDENTIFIER ::= { hmStatusWlanMngmtApConf 24 }

-- {TABLE} 1.3.6.1.4.1.248.32.18.1.73.2.24.1
hmStatusWlanMngmtApConfLbsGeneralTable OBJECT-TYPE
    SYNTAX     SEQUENCE OF HmStatusWlanMngmtApConfLbsGeneralEntry
    MAX-ACCESS not-accessible
    STATUS     current
    DESCRIPTION
            "-- empty --"
    ::= { hmStatusWlanMngmtApConfLbs 1 }

-- {ROW} 1.3.6.1.4.1.248.32.18.1.73.2.24.1.1
hmStatusWlanMngmtApConfLbsGeneralEntry OBJECT-TYPE
    SYNTAX     HmStatusWlanMngmtApConfLbsGeneralEntry
    MAX-ACCESS not-accessible
    STATUS     current
    DESCRIPTION
            ""
    INDEX {
            hmStatusWlanMngmtApConfLbsGeneralEntryName
          }
    ::= { hmStatusWlanMngmtApConfLbsGeneralTable 1 }

HmStatusWlanMngmtApConfLbsGeneralEntry ::= SEQUENCE {
            hmStatusWlanMngmtApConfLbsGeneralEntryName DisplayString,
            hmStatusWlanMngmtApConfLbsGeneralEntryOperating INTEGER,
            hmStatusWlanMngmtApConfLbsGeneralEntryUseTlsConnection INTEGER,
            hmStatusWlanMngmtApConfLbsGeneralEntryLbsServerAddress DisplayString,
            hmStatusWlanMngmtApConfLbsGeneralEntryLbsServerPort Integer32
    }

-- {COLUMN} 1.3.6.1.4.1.248.32.18.1.73.2.24.1.1.1
hmStatusWlanMngmtApConfLbsGeneralEntryName OBJECT-TYPE
    SYNTAX     DisplayString (SIZE(0..31))
    MAX-ACCESS read-only
    STATUS     current
    DESCRIPTION
            "-- empty --"
    ::= { hmStatusWlanMngmtApConfLbsGeneralEntry 1 }

-- {COLUMN} 1.3.6.1.4.1.248.32.18.1.73.2.24.1.1.2
hmStatusWlanMngmtApConfLbsGeneralEntryOperating OBJECT-TYPE
    SYNTAX     INTEGER {
                  eNo (0),
                  eYes (1)
            }
    MAX-ACCESS read-only
    STATUS     current
    DESCRIPTION
            "-- empty --"
    ::= { hmStatusWlanMngmtApConfLbsGeneralEntry 2 }

-- {COLUMN} 1.3.6.1.4.1.248.32.18.1.73.2.24.1.1.3
hmStatusWlanMngmtApConfLbsGeneralEntryUseTlsConnection OBJECT-TYPE
    SYNTAX     INTEGER {
                  eNo (0),
                  eYes (1)
            }
    MAX-ACCESS read-only
    STATUS     current
    DESCRIPTION
            "-- empty --"
    ::= { hmStatusWlanMngmtApConfLbsGeneralEntry 3 }

-- {COLUMN} 1.3.6.1.4.1.248.32.18.1.73.2.24.1.1.4
hmStatusWlanMngmtApConfLbsGeneralEntryLbsServerAddress OBJECT-TYPE
    SYNTAX     DisplayString (SIZE(0..64))
    MAX-ACCESS read-only
    STATUS     current
    DESCRIPTION
            "-- empty --"
    ::= { hmStatusWlanMngmtApConfLbsGeneralEntry 4 }

-- {COLUMN} 1.3.6.1.4.1.248.32.18.1.73.2.24.1.1.5
hmStatusWlanMngmtApConfLbsGeneralEntryLbsServerPort OBJECT-TYPE
    SYNTAX     Integer32 (0..65535)
    MAX-ACCESS read-only
    STATUS     current
    DESCRIPTION
            "-- empty --"
    ::= { hmStatusWlanMngmtApConfLbsGeneralEntry 5 }

-- {TABLE} 1.3.6.1.4.1.248.32.18.1.73.2.24.2
hmStatusWlanMngmtApConfLbsDevLocTable OBJECT-TYPE
    SYNTAX     SEQUENCE OF HmStatusWlanMngmtApConfLbsDevLocEntry
    MAX-ACCESS not-accessible
    STATUS     current
    DESCRIPTION
            ""
    ::= { hmStatusWlanMngmtApConfLbs 2 }

-- {ROW} 1.3.6.1.4.1.248.32.18.1.73.2.24.2.1
hmStatusWlanMngmtApConfLbsDevLocEntry OBJECT-TYPE
    SYNTAX     HmStatusWlanMngmtApConfLbsDevLocEntry
    MAX-ACCESS not-accessible
    STATUS     current
    DESCRIPTION
            ""
    INDEX {
            hmStatusWlanMngmtApConfLbsDevLocEntryName
          }
    ::= { hmStatusWlanMngmtApConfLbsDevLocTable 1 }

HmStatusWlanMngmtApConfLbsDevLocEntry ::= SEQUENCE {
            hmStatusWlanMngmtApConfLbsDevLocEntryName DisplayString,
            hmStatusWlanMngmtApConfLbsDevLocEntryFloor Integer32,
            hmStatusWlanMngmtApConfLbsDevLocEntryHeight Integer32,
            hmStatusWlanMngmtApConfLbsDevLocEntryLatDeg Integer32,
            hmStatusWlanMngmtApConfLbsDevLocEntryLatMin Integer32,
            hmStatusWlanMngmtApConfLbsDevLocEntryLatSec Integer32,
            hmStatusWlanMngmtApConfLbsDevLocEntryLatHemi INTEGER,
            hmStatusWlanMngmtApConfLbsDevLocEntryLongDeg Integer32,
            hmStatusWlanMngmtApConfLbsDevLocEntryLongMin Integer32,
            hmStatusWlanMngmtApConfLbsDevLocEntryLongSec Integer32,
            hmStatusWlanMngmtApConfLbsDevLocEntryLongHemi INTEGER,
            hmStatusWlanMngmtApConfLbsDevLocEntryDescription DisplayString
    }

-- {COLUMN} 1.3.6.1.4.1.248.32.18.1.73.2.24.2.1.1
hmStatusWlanMngmtApConfLbsDevLocEntryName OBJECT-TYPE
    SYNTAX     DisplayString (SIZE(0..31))
    MAX-ACCESS read-only
    STATUS     current
    DESCRIPTION
            "-- empty --"
    ::= { hmStatusWlanMngmtApConfLbsDevLocEntry 1 }

-- {COLUMN} 1.3.6.1.4.1.248.32.18.1.73.2.24.2.1.2
hmStatusWlanMngmtApConfLbsDevLocEntryFloor OBJECT-TYPE
    SYNTAX     Integer32 (-32768..32767)
    MAX-ACCESS read-only
    STATUS     current
    DESCRIPTION
            "-- empty --"
    ::= { hmStatusWlanMngmtApConfLbsDevLocEntry 2 }

-- {COLUMN} 1.3.6.1.4.1.248.32.18.1.73.2.24.2.1.3
hmStatusWlanMngmtApConfLbsDevLocEntryHeight OBJECT-TYPE
    SYNTAX     Integer32 (-32768..32767)
    MAX-ACCESS read-only
    STATUS     current
    DESCRIPTION
            "-- empty --"
    ::= { hmStatusWlanMngmtApConfLbsDevLocEntry 3 }

-- {COLUMN} 1.3.6.1.4.1.248.32.18.1.73.2.24.2.1.4
hmStatusWlanMngmtApConfLbsDevLocEntryLatDeg OBJECT-TYPE
    SYNTAX     Integer32 (0..255)
    MAX-ACCESS read-only
    STATUS     current
    DESCRIPTION
            ""
    ::= { hmStatusWlanMngmtApConfLbsDevLocEntry 4 }

-- {COLUMN} 1.3.6.1.4.1.248.32.18.1.73.2.24.2.1.5
hmStatusWlanMngmtApConfLbsDevLocEntryLatMin OBJECT-TYPE
    SYNTAX     Integer32 (0..255)
    MAX-ACCESS read-only
    STATUS     current
    DESCRIPTION
            ""
    ::= { hmStatusWlanMngmtApConfLbsDevLocEntry 5 }

-- {COLUMN} 1.3.6.1.4.1.248.32.18.1.73.2.24.2.1.6
hmStatusWlanMngmtApConfLbsDevLocEntryLatSec OBJECT-TYPE
    SYNTAX     Integer32 (0..2147483647)
    MAX-ACCESS read-only
    STATUS     current
    DESCRIPTION
            ""
    ::= { hmStatusWlanMngmtApConfLbsDevLocEntry 6 }

-- {COLUMN} 1.3.6.1.4.1.248.32.18.1.73.2.24.2.1.7
hmStatusWlanMngmtApConfLbsDevLocEntryLatHemi OBJECT-TYPE
    SYNTAX     INTEGER {
                  eN (0),
                  eS (1)
            }
    MAX-ACCESS read-only
    STATUS     current
    DESCRIPTION
            ""
    ::= { hmStatusWlanMngmtApConfLbsDevLocEntry 7 }

-- {COLUMN} 1.3.6.1.4.1.248.32.18.1.73.2.24.2.1.8
hmStatusWlanMngmtApConfLbsDevLocEntryLongDeg OBJECT-TYPE
    SYNTAX     Integer32 (0..255)
    MAX-ACCESS read-only
    STATUS     current
    DESCRIPTION
            ""
    ::= { hmStatusWlanMngmtApConfLbsDevLocEntry 8 }

-- {COLUMN} 1.3.6.1.4.1.248.32.18.1.73.2.24.2.1.9
hmStatusWlanMngmtApConfLbsDevLocEntryLongMin OBJECT-TYPE
    SYNTAX     Integer32 (0..255)
    MAX-ACCESS read-only
    STATUS     current
    DESCRIPTION
            ""
    ::= { hmStatusWlanMngmtApConfLbsDevLocEntry 9 }

-- {COLUMN} 1.3.6.1.4.1.248.32.18.1.73.2.24.2.1.10
hmStatusWlanMngmtApConfLbsDevLocEntryLongSec OBJECT-TYPE
    SYNTAX     Integer32 (0..2147483647)
    MAX-ACCESS read-only
    STATUS     current
    DESCRIPTION
            ""
    ::= { hmStatusWlanMngmtApConfLbsDevLocEntry 10 }

-- {COLUMN} 1.3.6.1.4.1.248.32.18.1.73.2.24.2.1.11
hmStatusWlanMngmtApConfLbsDevLocEntryLongHemi OBJECT-TYPE
    SYNTAX     INTEGER {
                  eE (0),
                  eW (1)
            }
    MAX-ACCESS read-only
    STATUS     current
    DESCRIPTION
            ""
    ::= { hmStatusWlanMngmtApConfLbsDevLocEntry 11 }

-- {COLUMN} 1.3.6.1.4.1.248.32.18.1.73.2.24.2.1.12
hmStatusWlanMngmtApConfLbsDevLocEntryDescription OBJECT-TYPE
    SYNTAX     DisplayString (SIZE(0..31))
    MAX-ACCESS read-only
    STATUS     current
    DESCRIPTION
            "-- empty --"
    ::= { hmStatusWlanMngmtApConfLbsDevLocEntry 12 }

-- {TABLE} 1.3.6.1.4.1.248.32.18.1.73.2.25
hmStatusWlanMngmtApConfWirelessEpaperProfileTable OBJECT-TYPE
    SYNTAX     SEQUENCE OF HmStatusWlanMngmtApConfWirelessEpaperProfileEntry
    MAX-ACCESS not-accessible
    STATUS     current
    DESCRIPTION
            "-- empty --"
    ::= { hmStatusWlanMngmtApConf 25 }

-- {ROW} 1.3.6.1.4.1.248.32.18.1.73.2.25.1
hmStatusWlanMngmtApConfWirelessEpaperProfileEntry OBJECT-TYPE
    SYNTAX     HmStatusWlanMngmtApConfWirelessEpaperProfileEntry
    MAX-ACCESS not-accessible
    STATUS     current
    DESCRIPTION
            ""
    INDEX {
            hmStatusWlanMngmtApConfWirelessEpaperProfileEntryName
          }
    ::= { hmStatusWlanMngmtApConfWirelessEpaperProfileTable 1 }

HmStatusWlanMngmtApConfWirelessEpaperProfileEntry ::= SEQUENCE {
            hmStatusWlanMngmtApConfWirelessEpaperProfileEntryName DisplayString,
            hmStatusWlanMngmtApConfWirelessEpaperProfileEntryOperating INTEGER,
            hmStatusWlanMngmtApConfWirelessEpaperProfileEntryPort Integer32
    }

-- {COLUMN} 1.3.6.1.4.1.248.32.18.1.73.2.25.1.1
hmStatusWlanMngmtApConfWirelessEpaperProfileEntryName OBJECT-TYPE
    SYNTAX     DisplayString (SIZE(0..31))
    MAX-ACCESS read-write
    STATUS     current
    DESCRIPTION
            "-- empty --"
    ::= { hmStatusWlanMngmtApConfWirelessEpaperProfileEntry 1 }

-- {COLUMN} 1.3.6.1.4.1.248.32.18.1.73.2.25.1.2
hmStatusWlanMngmtApConfWirelessEpaperProfileEntryOperating OBJECT-TYPE
    SYNTAX     INTEGER {
                  eNo (0),
                  eYes (1)
            }
    MAX-ACCESS read-write
    STATUS     current
    DESCRIPTION
            "-- empty --"
    ::= { hmStatusWlanMngmtApConfWirelessEpaperProfileEntry 2 }

-- {COLUMN} 1.3.6.1.4.1.248.32.18.1.73.2.25.1.3
hmStatusWlanMngmtApConfWirelessEpaperProfileEntryPort OBJECT-TYPE
    SYNTAX     Integer32 (0..65535)
    MAX-ACCESS read-write
    STATUS     current
    DESCRIPTION
            "-- empty --"
    ::= { hmStatusWlanMngmtApConfWirelessEpaperProfileEntry 3 }

-- {TABLE} 1.3.6.1.4.1.248.32.18.1.73.2.26
hmStatusWlanMngmtApConfIbeaconProfileTable OBJECT-TYPE
    SYNTAX     SEQUENCE OF HmStatusWlanMngmtApConfIbeaconProfileEntry
    MAX-ACCESS not-accessible
    STATUS     current
    DESCRIPTION
            "-- empty --"
    ::= { hmStatusWlanMngmtApConf 26 }

-- {ROW} 1.3.6.1.4.1.248.32.18.1.73.2.26.1
hmStatusWlanMngmtApConfIbeaconProfileEntry OBJECT-TYPE
    SYNTAX     HmStatusWlanMngmtApConfIbeaconProfileEntry
    MAX-ACCESS not-accessible
    STATUS     current
    DESCRIPTION
            ""
    INDEX {
            hmStatusWlanMngmtApConfIbeaconProfileEntryName
          }
    ::= { hmStatusWlanMngmtApConfIbeaconProfileTable 1 }

HmStatusWlanMngmtApConfIbeaconProfileEntry ::= SEQUENCE {
            hmStatusWlanMngmtApConfIbeaconProfileEntryName DisplayString,
            hmStatusWlanMngmtApConfIbeaconProfileEntryOperating INTEGER,
            hmStatusWlanMngmtApConfIbeaconProfileEntryMajor Integer32,
            hmStatusWlanMngmtApConfIbeaconProfileEntryUuid DisplayString
    }

-- {COLUMN} 1.3.6.1.4.1.248.32.18.1.73.2.26.1.1
hmStatusWlanMngmtApConfIbeaconProfileEntryName OBJECT-TYPE
    SYNTAX     DisplayString (SIZE(0..31))
    MAX-ACCESS read-write
    STATUS     current
    DESCRIPTION
            "-- empty --"
    ::= { hmStatusWlanMngmtApConfIbeaconProfileEntry 1 }

-- {COLUMN} 1.3.6.1.4.1.248.32.18.1.73.2.26.1.2
hmStatusWlanMngmtApConfIbeaconProfileEntryOperating OBJECT-TYPE
    SYNTAX     INTEGER {
                  eNo (0),
                  eYes (1)
            }
    MAX-ACCESS read-write
    STATUS     current
    DESCRIPTION
            "-- empty --"
    ::= { hmStatusWlanMngmtApConfIbeaconProfileEntry 2 }

-- {COLUMN} 1.3.6.1.4.1.248.32.18.1.73.2.26.1.3
hmStatusWlanMngmtApConfIbeaconProfileEntryMajor OBJECT-TYPE
    SYNTAX     Integer32 (0..65535)
    MAX-ACCESS read-write
    STATUS     current
    DESCRIPTION
            "-- empty --"
    ::= { hmStatusWlanMngmtApConfIbeaconProfileEntry 3 }

-- {COLUMN} 1.3.6.1.4.1.248.32.18.1.73.2.26.1.4
hmStatusWlanMngmtApConfIbeaconProfileEntryUuid OBJECT-TYPE
    SYNTAX     DisplayString (SIZE(0..36))
    MAX-ACCESS read-write
    STATUS     current
    DESCRIPTION
            "-- empty --"
    ::= { hmStatusWlanMngmtApConfIbeaconProfileEntry 4 }

-- {SCALAR} 1.3.6.1.4.1.248.32.18.1.73.3
hmStatusWlanMngmtNumberOfApConnections OBJECT-TYPE
    SYNTAX     Integer32 (0..2147483647)
    MAX-ACCESS read-only
    STATUS     current
    DESCRIPTION
            "-- empty --"
    ::= { hmStatusWlanMngmt 3 }

-- {TABLE} 1.3.6.1.4.1.248.32.18.1.73.4
hmStatusWlanMngmtApConnectionsTable OBJECT-TYPE
    SYNTAX     SEQUENCE OF HmStatusWlanMngmtApConnectionsEntry
    MAX-ACCESS not-accessible
    STATUS     current
    DESCRIPTION
            "-- empty --"
    ::= { hmStatusWlanMngmt 4 }

-- {ROW} 1.3.6.1.4.1.248.32.18.1.73.4.1
hmStatusWlanMngmtApConnectionsEntry OBJECT-TYPE
    SYNTAX     HmStatusWlanMngmtApConnectionsEntry
    MAX-ACCESS not-accessible
    STATUS     current
    DESCRIPTION
            ""
    INDEX {
            hmStatusWlanMngmtApConnectionsEntryJob
          }
    ::= { hmStatusWlanMngmtApConnectionsTable 1 }

HmStatusWlanMngmtApConnectionsEntry ::= SEQUENCE {
            hmStatusWlanMngmtApConnectionsEntryJob Integer32,
            hmStatusWlanMngmtApConnectionsEntryJobId DisplayString,
            hmStatusWlanMngmtApConnectionsEntryApLanMac MacAddress,
            hmStatusWlanMngmtApConnectionsEntryIpAddress IpAddress,
            hmStatusWlanMngmtApConnectionsEntryAuthorized INTEGER,
            hmStatusWlanMngmtApConnectionsEntryState INTEGER,
            hmStatusWlanMngmtApConnectionsEntryConfiguration INTEGER,
            hmStatusWlanMngmtApConnectionsEntryEncrypted INTEGER,
            hmStatusWlanMngmtApConnectionsEntryPmtu Integer32,
            hmStatusWlanMngmtApConnectionsEntryDscpForControlPackets INTEGER,
            hmStatusWlanMngmtApConnectionsEntryDscpForDataPackets INTEGER
    }

-- {COLUMN} 1.3.6.1.4.1.248.32.18.1.73.4.1.1
hmStatusWlanMngmtApConnectionsEntryJob OBJECT-TYPE
    SYNTAX     Integer32 (0..2147483647)
    MAX-ACCESS read-only
    STATUS     current
    DESCRIPTION
            "-- empty --"
    ::= { hmStatusWlanMngmtApConnectionsEntry 1 }

-- {COLUMN} 1.3.6.1.4.1.248.32.18.1.73.4.1.2
hmStatusWlanMngmtApConnectionsEntryJobId OBJECT-TYPE
    SYNTAX     DisplayString (SIZE(0..2))
    MAX-ACCESS read-only
    STATUS     current
    DESCRIPTION
            "-- empty --"
    ::= { hmStatusWlanMngmtApConnectionsEntry 2 }

-- {COLUMN} 1.3.6.1.4.1.248.32.18.1.73.4.1.3
hmStatusWlanMngmtApConnectionsEntryApLanMac OBJECT-TYPE
    SYNTAX     MacAddress
    MAX-ACCESS read-only
    STATUS     current
    DESCRIPTION
            "-- empty --"
    ::= { hmStatusWlanMngmtApConnectionsEntry 3 }

-- {COLUMN} 1.3.6.1.4.1.248.32.18.1.73.4.1.4
hmStatusWlanMngmtApConnectionsEntryIpAddress OBJECT-TYPE
    SYNTAX     IpAddress
    MAX-ACCESS read-only
    STATUS     current
    DESCRIPTION
            "-- empty --"
    ::= { hmStatusWlanMngmtApConnectionsEntry 4 }

-- {COLUMN} 1.3.6.1.4.1.248.32.18.1.73.4.1.5
hmStatusWlanMngmtApConnectionsEntryAuthorized OBJECT-TYPE
    SYNTAX     INTEGER {
                  eUnknown (0),
                  eYes (1),
                  eNo (2)
            }
    MAX-ACCESS read-only
    STATUS     current
    DESCRIPTION
            "-- empty --"
    ::= { hmStatusWlanMngmtApConnectionsEntry 5 }

-- {COLUMN} 1.3.6.1.4.1.248.32.18.1.73.4.1.6
hmStatusWlanMngmtApConnectionsEntryState OBJECT-TYPE
    SYNTAX     INTEGER {
                  eUnknown (0),
                  eIdle (5),
                  eDiscovery (10),
                  eDtlsSetup (15),
                  eJoin (20),
                  eConfigure (25),
                  eImageData (30),
                  eReset (35),
                  eDtlsTeardown (40),
                  eSulking (45),
                  eRun (100)
            }
    MAX-ACCESS read-only
    STATUS     current
    DESCRIPTION
            "-- empty --"
    ::= { hmStatusWlanMngmtApConnectionsEntry 6 }

-- {COLUMN} 1.3.6.1.4.1.248.32.18.1.73.4.1.7
hmStatusWlanMngmtApConnectionsEntryConfiguration OBJECT-TYPE
    SYNTAX     INTEGER {
                  eNo (0),
                  eYes (1),
                  eDefault (2)
            }
    MAX-ACCESS read-only
    STATUS     current
    DESCRIPTION
            "-- empty --"
    ::= { hmStatusWlanMngmtApConnectionsEntry 7 }

-- {COLUMN} 1.3.6.1.4.1.248.32.18.1.73.4.1.8
hmStatusWlanMngmtApConnectionsEntryEncrypted OBJECT-TYPE
    SYNTAX     INTEGER {
                  eNo (0),
                  eYes (1)
            }
    MAX-ACCESS read-only
    STATUS     current
    DESCRIPTION
            "-- empty --"
    ::= { hmStatusWlanMngmtApConnectionsEntry 8 }

-- {COLUMN} 1.3.6.1.4.1.248.32.18.1.73.4.1.9
hmStatusWlanMngmtApConnectionsEntryPmtu OBJECT-TYPE
    SYNTAX     Integer32 (0..2147483647)
    MAX-ACCESS read-only
    STATUS     current
    DESCRIPTION
            "-- empty --"
    ::= { hmStatusWlanMngmtApConnectionsEntry 9 }

-- {COLUMN} 1.3.6.1.4.1.248.32.18.1.73.4.1.10
hmStatusWlanMngmtApConnectionsEntryDscpForControlPackets OBJECT-TYPE
    SYNTAX     INTEGER {
                  eBestEffort (0),
                  eAssuredForwarding11 (40),
                  eAssuredForwarding12 (48),
                  eAssuredForwarding13 (56),
                  eAssuredForwarding21 (72),
                  eAssuredForwarding22 (80),
                  eAssuredForwarding23 (88),
                  eAssuredForwarding31 (104),
                  eAssuredForwarding32 (112),
                  eAssuredForwarding33 (120),
                  eAssuredForwarding41 (136),
                  eAssuredForwarding42 (144),
                  eAssuredForwarding43 (152),
                  eExpeditedForwarding (184)
            }
    MAX-ACCESS read-only
    STATUS     current
    DESCRIPTION
            "-- empty --"
    ::= { hmStatusWlanMngmtApConnectionsEntry 10 }

-- {COLUMN} 1.3.6.1.4.1.248.32.18.1.73.4.1.11
hmStatusWlanMngmtApConnectionsEntryDscpForDataPackets OBJECT-TYPE
    SYNTAX     INTEGER {
                  eBestEffort (0),
                  eAssuredForwarding11 (40),
                  eAssuredForwarding12 (48),
                  eAssuredForwarding13 (56),
                  eAssuredForwarding21 (72),
                  eAssuredForwarding22 (80),
                  eAssuredForwarding23 (88),
                  eAssuredForwarding31 (104),
                  eAssuredForwarding32 (112),
                  eAssuredForwarding33 (120),
                  eAssuredForwarding41 (136),
                  eAssuredForwarding42 (144),
                  eAssuredForwarding43 (152),
                  eExpeditedForwarding (184)
            }
    MAX-ACCESS read-only
    STATUS     current
    DESCRIPTION
            "-- empty --"
    ::= { hmStatusWlanMngmtApConnectionsEntry 11 }

-- {SCALAR} 1.3.6.1.4.1.248.32.18.1.73.5
hmStatusWlanMngmtExpectedAp OBJECT-TYPE
    SYNTAX     Integer32 (0..2147483647)
    MAX-ACCESS read-only
    STATUS     current
    DESCRIPTION
            "-- empty --"
    ::= { hmStatusWlanMngmt 5 }

-- {SCALAR} 1.3.6.1.4.1.248.32.18.1.73.6
hmStatusWlanMngmtConnectedExpectedAp OBJECT-TYPE
    SYNTAX     Integer32 (0..2147483647)
    MAX-ACCESS read-only
    STATUS     current
    DESCRIPTION
            "-- empty --"
    ::= { hmStatusWlanMngmt 6 }

-- {SCALAR} 1.3.6.1.4.1.248.32.18.1.73.7
hmStatusWlanMngmtConnectedManagedAp OBJECT-TYPE
    SYNTAX     Integer32 (0..2147483647)
    MAX-ACCESS read-only
    STATUS     current
    DESCRIPTION
            "-- empty --"
    ::= { hmStatusWlanMngmt 7 }

-- {SCALAR} 1.3.6.1.4.1.248.32.18.1.73.8
hmStatusWlanMngmtConnectedNewAp OBJECT-TYPE
    SYNTAX     Integer32 (0..2147483647)
    MAX-ACCESS read-only
    STATUS     current
    DESCRIPTION
            "-- empty --"
    ::= { hmStatusWlanMngmt 8 }

-- {NODE} 1.3.6.1.4.1.248.32.18.1.73.9
hmStatusWlanMngmtApStatus OBJECT IDENTIFIER ::= { hmStatusWlanMngmt 9 }

-- {TABLE} 1.3.6.1.4.1.248.32.18.1.73.9.1
hmStatusWlanMngmtApStatusMissingApTable OBJECT-TYPE
    SYNTAX     SEQUENCE OF HmStatusWlanMngmtApStatusMissingApEntry
    MAX-ACCESS not-accessible
    STATUS     current
    DESCRIPTION
            "-- empty --"
    ::= { hmStatusWlanMngmtApStatus 1 }

-- {ROW} 1.3.6.1.4.1.248.32.18.1.73.9.1.1
hmStatusWlanMngmtApStatusMissingApEntry OBJECT-TYPE
    SYNTAX     HmStatusWlanMngmtApStatusMissingApEntry
    MAX-ACCESS not-accessible
    STATUS     current
    DESCRIPTION
            ""
    INDEX {
            hmStatusWlanMngmtApStatusMissingApEntryApLanMac
          }
    ::= { hmStatusWlanMngmtApStatusMissingApTable 1 }

HmStatusWlanMngmtApStatusMissingApEntry ::= SEQUENCE {
            hmStatusWlanMngmtApStatusMissingApEntryApLanMac MacAddress,
            hmStatusWlanMngmtApStatusMissingApEntryIpAddress IpAddress,
            hmStatusWlanMngmtApStatusMissingApEntryName DisplayString,
            hmStatusWlanMngmtApStatusMissingApEntryLocation DisplayString,
            hmStatusWlanMngmtApStatusMissingApEntryValid INTEGER,
            hmStatusWlanMngmtApStatusMissingApEntryModule DisplayString,
            hmStatusWlanMngmtApStatusMissingApEntryGroups DisplayString
    }

-- {COLUMN} 1.3.6.1.4.1.248.32.18.1.73.9.1.1.1
hmStatusWlanMngmtApStatusMissingApEntryApLanMac OBJECT-TYPE
    SYNTAX     MacAddress
    MAX-ACCESS read-only
    STATUS     current
    DESCRIPTION
            "-- empty --"
    ::= { hmStatusWlanMngmtApStatusMissingApEntry 1 }

-- {COLUMN} 1.3.6.1.4.1.248.32.18.1.73.9.1.1.2
hmStatusWlanMngmtApStatusMissingApEntryIpAddress OBJECT-TYPE
    SYNTAX     IpAddress
    MAX-ACCESS read-only
    STATUS     current
    DESCRIPTION
            "-- empty --"
    ::= { hmStatusWlanMngmtApStatusMissingApEntry 2 }

-- {COLUMN} 1.3.6.1.4.1.248.32.18.1.73.9.1.1.3
hmStatusWlanMngmtApStatusMissingApEntryName OBJECT-TYPE
    SYNTAX     DisplayString (SIZE(0..82))
    MAX-ACCESS read-only
    STATUS     current
    DESCRIPTION
            "-- empty --"
    ::= { hmStatusWlanMngmtApStatusMissingApEntry 3 }

-- {COLUMN} 1.3.6.1.4.1.248.32.18.1.73.9.1.1.4
hmStatusWlanMngmtApStatusMissingApEntryLocation OBJECT-TYPE
    SYNTAX     DisplayString (SIZE(0..251))
    MAX-ACCESS read-only
    STATUS     current
    DESCRIPTION
            "-- empty --"
    ::= { hmStatusWlanMngmtApStatusMissingApEntry 4 }

-- {COLUMN} 1.3.6.1.4.1.248.32.18.1.73.9.1.1.5
hmStatusWlanMngmtApStatusMissingApEntryValid OBJECT-TYPE
    SYNTAX     INTEGER {
                  eNo (0),
                  eYes (1)
            }
    MAX-ACCESS read-only
    STATUS     current
    DESCRIPTION
            "-- empty --"
    ::= { hmStatusWlanMngmtApStatusMissingApEntry 5 }

-- {COLUMN} 1.3.6.1.4.1.248.32.18.1.73.9.1.1.21
hmStatusWlanMngmtApStatusMissingApEntryModule OBJECT-TYPE
    SYNTAX     DisplayString (SIZE(0..64))
    MAX-ACCESS read-only
    STATUS     current
    DESCRIPTION
            "-- empty --"
    ::= { hmStatusWlanMngmtApStatusMissingApEntry 21 }

-- {COLUMN} 1.3.6.1.4.1.248.32.18.1.73.9.1.1.31
hmStatusWlanMngmtApStatusMissingApEntryGroups OBJECT-TYPE
    SYNTAX     DisplayString (SIZE(0..251))
    MAX-ACCESS read-only
    STATUS     current
    DESCRIPTION
            "-- empty --"
    ::= { hmStatusWlanMngmtApStatusMissingApEntry 31 }

-- {TABLE} 1.3.6.1.4.1.248.32.18.1.73.9.2
hmStatusWlanMngmtApStatusActiveRadiosTable OBJECT-TYPE
    SYNTAX     SEQUENCE OF HmStatusWlanMngmtApStatusActiveRadiosEntry
    MAX-ACCESS not-accessible
    STATUS     current
    DESCRIPTION
            "-- empty --"
    ::= { hmStatusWlanMngmtApStatus 2 }

-- {ROW} 1.3.6.1.4.1.248.32.18.1.73.9.2.1
hmStatusWlanMngmtApStatusActiveRadiosEntry OBJECT-TYPE
    SYNTAX     HmStatusWlanMngmtApStatusActiveRadiosEntry
    MAX-ACCESS not-accessible
    STATUS     current
    DESCRIPTION
            ""
    INDEX {
            hmStatusWlanMngmtApStatusActiveRadiosEntryApLanMac,
            hmStatusWlanMngmtApStatusActiveRadiosEntryIfc
          }
    ::= { hmStatusWlanMngmtApStatusActiveRadiosTable 1 }

HmStatusWlanMngmtApStatusActiveRadiosEntry ::= SEQUENCE {
            hmStatusWlanMngmtApStatusActiveRadiosEntryApLanMac MacAddress,
            hmStatusWlanMngmtApStatusActiveRadiosEntryIpAddress IpAddress,
            hmStatusWlanMngmtApStatusActiveRadiosEntryName DisplayString,
            hmStatusWlanMngmtApStatusActiveRadiosEntryLocation DisplayString,
            hmStatusWlanMngmtApStatusActiveRadiosEntryValid INTEGER,
            hmStatusWlanMngmtApStatusActiveRadiosEntryApWlanMac MacAddress,
            hmStatusWlanMngmtApStatusActiveRadiosEntryIfc INTEGER,
            hmStatusWlanMngmtApStatusActiveRadiosEntryRadioBand Integer32,
            hmStatusWlanMngmtApStatusActiveRadiosEntryRadioChannel Integer32,
            hmStatusWlanMngmtApStatusActiveRadiosEntryClientCount Integer32,
            hmStatusWlanMngmtApStatusActiveRadiosEntryBackgroundScan Integer32,
            hmStatusWlanMngmtApStatusActiveRadiosEntryCardId DisplayString,
            hmStatusWlanMngmtApStatusActiveRadiosEntryCardFirmwareVersion DisplayString,
            hmStatusWlanMngmtApStatusActiveRadiosEntryCardSerialNumber DisplayString,
            hmStatusWlanMngmtApStatusActiveRadiosEntryOperating INTEGER,
            hmStatusWlanMngmtApStatusActiveRadiosEntryTransmitPower DisplayString,
            hmStatusWlanMngmtApStatusActiveRadiosEntryEirp DisplayString,
            hmStatusWlanMngmtApStatusActiveRadiosEntryExcEirp Integer32,
            hmStatusWlanMngmtApStatusActiveRadiosEntryInternal INTEGER,
            hmStatusWlanMngmtApStatusActiveRadiosEntryRadios Integer32,
            hmStatusWlanMngmtApStatusActiveRadiosEntryModule DisplayString,
            hmStatusWlanMngmtApStatusActiveRadiosEntrySerialNumber DisplayString,
            hmStatusWlanMngmtApStatusActiveRadiosEntryVersion DisplayString,
            hmStatusWlanMngmtApStatusActiveRadiosEntryCardState INTEGER,
            hmStatusWlanMngmtApStatusActiveRadiosEntryRadioFldOpt INTEGER,
            hmStatusWlanMngmtApStatusActiveRadiosEntryMinimalModemLoad Integer32,
            hmStatusWlanMngmtApStatusActiveRadiosEntryMaximalModemLoad Integer32,
            hmStatusWlanMngmtApStatusActiveRadiosEntryAverageModemLoad Integer32,
            hmStatusWlanMngmtApStatusActiveRadiosEntryApConnection INTEGER,
            hmStatusWlanMngmtApStatusActiveRadiosEntryGroups DisplayString
    }

-- {COLUMN} 1.3.6.1.4.1.248.32.18.1.73.9.2.1.1
hmStatusWlanMngmtApStatusActiveRadiosEntryApLanMac OBJECT-TYPE
    SYNTAX     MacAddress
    MAX-ACCESS read-only
    STATUS     current
    DESCRIPTION
            "-- empty --"
    ::= { hmStatusWlanMngmtApStatusActiveRadiosEntry 1 }

-- {COLUMN} 1.3.6.1.4.1.248.32.18.1.73.9.2.1.2
hmStatusWlanMngmtApStatusActiveRadiosEntryIpAddress OBJECT-TYPE
    SYNTAX     IpAddress
    MAX-ACCESS read-only
    STATUS     current
    DESCRIPTION
            "-- empty --"
    ::= { hmStatusWlanMngmtApStatusActiveRadiosEntry 2 }

-- {COLUMN} 1.3.6.1.4.1.248.32.18.1.73.9.2.1.3
hmStatusWlanMngmtApStatusActiveRadiosEntryName OBJECT-TYPE
    SYNTAX     DisplayString (SIZE(0..82))
    MAX-ACCESS read-only
    STATUS     current
    DESCRIPTION
            "-- empty --"
    ::= { hmStatusWlanMngmtApStatusActiveRadiosEntry 3 }

-- {COLUMN} 1.3.6.1.4.1.248.32.18.1.73.9.2.1.4
hmStatusWlanMngmtApStatusActiveRadiosEntryLocation OBJECT-TYPE
    SYNTAX     DisplayString (SIZE(0..251))
    MAX-ACCESS read-only
    STATUS     current
    DESCRIPTION
            "-- empty --"
    ::= { hmStatusWlanMngmtApStatusActiveRadiosEntry 4 }

-- {COLUMN} 1.3.6.1.4.1.248.32.18.1.73.9.2.1.5
hmStatusWlanMngmtApStatusActiveRadiosEntryValid OBJECT-TYPE
    SYNTAX     INTEGER {
                  eNo (0),
                  eYes (1)
            }
    MAX-ACCESS read-only
    STATUS     current
    DESCRIPTION
            "-- empty --"
    ::= { hmStatusWlanMngmtApStatusActiveRadiosEntry 5 }

-- {COLUMN} 1.3.6.1.4.1.248.32.18.1.73.9.2.1.6
hmStatusWlanMngmtApStatusActiveRadiosEntryApWlanMac OBJECT-TYPE
    SYNTAX     MacAddress
    MAX-ACCESS read-only
    STATUS     current
    DESCRIPTION
            "-- empty --"
    ::= { hmStatusWlanMngmtApStatusActiveRadiosEntry 6 }

-- {COLUMN} 1.3.6.1.4.1.248.32.18.1.73.9.2.1.7
hmStatusWlanMngmtApStatusActiveRadiosEntryIfc OBJECT-TYPE
    SYNTAX     INTEGER {
                  eWlan1 (0),
                  eWlan2 (1),
                  eWlan3 (2),
                  eWlan4 (3)
            }
    MAX-ACCESS read-only
    STATUS     current
    DESCRIPTION
            "-- empty --"
    ::= { hmStatusWlanMngmtApStatusActiveRadiosEntry 7 }

-- {COLUMN} 1.3.6.1.4.1.248.32.18.1.73.9.2.1.8
hmStatusWlanMngmtApStatusActiveRadiosEntryRadioBand OBJECT-TYPE
    SYNTAX     Integer32 (0..255)
    MAX-ACCESS read-only
    STATUS     current
    DESCRIPTION
            "-- empty --"
    ::= { hmStatusWlanMngmtApStatusActiveRadiosEntry 8 }

-- {COLUMN} 1.3.6.1.4.1.248.32.18.1.73.9.2.1.9
hmStatusWlanMngmtApStatusActiveRadiosEntryRadioChannel OBJECT-TYPE
    SYNTAX     Integer32 (0..255)
    MAX-ACCESS read-only
    STATUS     current
    DESCRIPTION
            "-- empty --"
    ::= { hmStatusWlanMngmtApStatusActiveRadiosEntry 9 }

-- {COLUMN} 1.3.6.1.4.1.248.32.18.1.73.9.2.1.10
hmStatusWlanMngmtApStatusActiveRadiosEntryClientCount OBJECT-TYPE
    SYNTAX     Integer32 (0..65535)
    MAX-ACCESS read-only
    STATUS     current
    DESCRIPTION
            "-- empty --"
    ::= { hmStatusWlanMngmtApStatusActiveRadiosEntry 10 }

-- {COLUMN} 1.3.6.1.4.1.248.32.18.1.73.9.2.1.11
hmStatusWlanMngmtApStatusActiveRadiosEntryBackgroundScan OBJECT-TYPE
    SYNTAX     Integer32 (0..2147483647)
    MAX-ACCESS read-only
    STATUS     current
    DESCRIPTION
            "-- empty --"
    ::= { hmStatusWlanMngmtApStatusActiveRadiosEntry 11 }

-- {COLUMN} 1.3.6.1.4.1.248.32.18.1.73.9.2.1.12
hmStatusWlanMngmtApStatusActiveRadiosEntryCardId OBJECT-TYPE
    SYNTAX     DisplayString (SIZE(0..90))
    MAX-ACCESS read-only
    STATUS     current
    DESCRIPTION
            "-- empty --"
    ::= { hmStatusWlanMngmtApStatusActiveRadiosEntry 12 }

-- {COLUMN} 1.3.6.1.4.1.248.32.18.1.73.9.2.1.13
hmStatusWlanMngmtApStatusActiveRadiosEntryCardFirmwareVersion OBJECT-TYPE
    SYNTAX     DisplayString (SIZE(0..32))
    MAX-ACCESS read-only
    STATUS     current
    DESCRIPTION
            "-- empty --"
    ::= { hmStatusWlanMngmtApStatusActiveRadiosEntry 13 }

-- {COLUMN} 1.3.6.1.4.1.248.32.18.1.73.9.2.1.14
hmStatusWlanMngmtApStatusActiveRadiosEntryCardSerialNumber OBJECT-TYPE
    SYNTAX     DisplayString (SIZE(0..32))
    MAX-ACCESS read-only
    STATUS     current
    DESCRIPTION
            "-- empty --"
    ::= { hmStatusWlanMngmtApStatusActiveRadiosEntry 14 }

-- {COLUMN} 1.3.6.1.4.1.248.32.18.1.73.9.2.1.15
hmStatusWlanMngmtApStatusActiveRadiosEntryOperating OBJECT-TYPE
    SYNTAX     INTEGER {
                  eNo (0),
                  eYes (1)
            }
    MAX-ACCESS read-only
    STATUS     current
    DESCRIPTION
            "-- empty --"
    ::= { hmStatusWlanMngmtApStatusActiveRadiosEntry 15 }

-- {COLUMN} 1.3.6.1.4.1.248.32.18.1.73.9.2.1.16
hmStatusWlanMngmtApStatusActiveRadiosEntryTransmitPower OBJECT-TYPE
    SYNTAX     DisplayString (SIZE(0..255))
    MAX-ACCESS read-only
    STATUS     current
    DESCRIPTION
            "-- empty --"
    ::= { hmStatusWlanMngmtApStatusActiveRadiosEntry 16 }

-- {COLUMN} 1.3.6.1.4.1.248.32.18.1.73.9.2.1.17
hmStatusWlanMngmtApStatusActiveRadiosEntryEirp OBJECT-TYPE
    SYNTAX     DisplayString (SIZE(0..255))
    MAX-ACCESS read-only
    STATUS     current
    DESCRIPTION
            "-- empty --"
    ::= { hmStatusWlanMngmtApStatusActiveRadiosEntry 17 }

-- {COLUMN} 1.3.6.1.4.1.248.32.18.1.73.9.2.1.18
hmStatusWlanMngmtApStatusActiveRadiosEntryExcEirp OBJECT-TYPE
    SYNTAX     Integer32 (0..255)
    MAX-ACCESS read-only
    STATUS     current
    DESCRIPTION
            "-- empty --"
    ::= { hmStatusWlanMngmtApStatusActiveRadiosEntry 18 }

-- {COLUMN} 1.3.6.1.4.1.248.32.18.1.73.9.2.1.19
hmStatusWlanMngmtApStatusActiveRadiosEntryInternal OBJECT-TYPE
    SYNTAX     INTEGER {
                  eNo (0),
                  eYes (1)
            }
    MAX-ACCESS read-only
    STATUS     current
    DESCRIPTION
            "-- empty --"
    ::= { hmStatusWlanMngmtApStatusActiveRadiosEntry 19 }

-- {COLUMN} 1.3.6.1.4.1.248.32.18.1.73.9.2.1.20
hmStatusWlanMngmtApStatusActiveRadiosEntryRadios OBJECT-TYPE
    SYNTAX     Integer32 (0..255)
    MAX-ACCESS read-only
    STATUS     current
    DESCRIPTION
            "-- empty --"
    ::= { hmStatusWlanMngmtApStatusActiveRadiosEntry 20 }

-- {COLUMN} 1.3.6.1.4.1.248.32.18.1.73.9.2.1.21
hmStatusWlanMngmtApStatusActiveRadiosEntryModule OBJECT-TYPE
    SYNTAX     DisplayString (SIZE(0..64))
    MAX-ACCESS read-only
    STATUS     current
    DESCRIPTION
            "-- empty --"
    ::= { hmStatusWlanMngmtApStatusActiveRadiosEntry 21 }

-- {COLUMN} 1.3.6.1.4.1.248.32.18.1.73.9.2.1.22
hmStatusWlanMngmtApStatusActiveRadiosEntrySerialNumber OBJECT-TYPE
    SYNTAX     DisplayString (SIZE(0..18))
    MAX-ACCESS read-only
    STATUS     current
    DESCRIPTION
            "-- empty --"
    ::= { hmStatusWlanMngmtApStatusActiveRadiosEntry 22 }

-- {COLUMN} 1.3.6.1.4.1.248.32.18.1.73.9.2.1.23
hmStatusWlanMngmtApStatusActiveRadiosEntryVersion OBJECT-TYPE
    SYNTAX     DisplayString (SIZE(0..25))
    MAX-ACCESS read-only
    STATUS     current
    DESCRIPTION
            "-- empty --"
    ::= { hmStatusWlanMngmtApStatusActiveRadiosEntry 23 }

-- {COLUMN} 1.3.6.1.4.1.248.32.18.1.73.9.2.1.24
hmStatusWlanMngmtApStatusActiveRadiosEntryCardState OBJECT-TYPE
    SYNTAX     INTEGER {
                  eNormal (0),
                  eFailure (1),
                  eInitalizing (2),
                  eNoCard (4)
            }
    MAX-ACCESS read-only
    STATUS     current
    DESCRIPTION
            "-- empty --"
    ::= { hmStatusWlanMngmtApStatusActiveRadiosEntry 24 }

-- {COLUMN} 1.3.6.1.4.1.248.32.18.1.73.9.2.1.25
hmStatusWlanMngmtApStatusActiveRadiosEntryRadioFldOpt OBJECT-TYPE
    SYNTAX     INTEGER {
                  eInactive (0),
                  eWaiting (1),
                  eScanning (2)
            }
    MAX-ACCESS read-only
    STATUS     current
    DESCRIPTION
            "radio field optimization"
    ::= { hmStatusWlanMngmtApStatusActiveRadiosEntry 25 }

-- {COLUMN} 1.3.6.1.4.1.248.32.18.1.73.9.2.1.26
hmStatusWlanMngmtApStatusActiveRadiosEntryMinimalModemLoad OBJECT-TYPE
    SYNTAX     Integer32 (0..2147483647)
    MAX-ACCESS read-only
    STATUS     current
    DESCRIPTION
            "-- empty --"
    ::= { hmStatusWlanMngmtApStatusActiveRadiosEntry 26 }

-- {COLUMN} 1.3.6.1.4.1.248.32.18.1.73.9.2.1.27
hmStatusWlanMngmtApStatusActiveRadiosEntryMaximalModemLoad OBJECT-TYPE
    SYNTAX     Integer32 (0..2147483647)
    MAX-ACCESS read-only
    STATUS     current
    DESCRIPTION
            "-- empty --"
    ::= { hmStatusWlanMngmtApStatusActiveRadiosEntry 27 }

-- {COLUMN} 1.3.6.1.4.1.248.32.18.1.73.9.2.1.28
hmStatusWlanMngmtApStatusActiveRadiosEntryAverageModemLoad OBJECT-TYPE
    SYNTAX     Integer32 (0..2147483647)
    MAX-ACCESS read-only
    STATUS     current
    DESCRIPTION
            "-- empty --"
    ::= { hmStatusWlanMngmtApStatusActiveRadiosEntry 28 }

-- {COLUMN} 1.3.6.1.4.1.248.32.18.1.73.9.2.1.29
hmStatusWlanMngmtApStatusActiveRadiosEntryApConnection OBJECT-TYPE
    SYNTAX     INTEGER {
                  eLan (0),
                  eWlanClient (1),
                  eWlanAutowds (2)
            }
    MAX-ACCESS read-only
    STATUS     current
    DESCRIPTION
            "-- empty --"
    ::= { hmStatusWlanMngmtApStatusActiveRadiosEntry 29 }

-- {COLUMN} 1.3.6.1.4.1.248.32.18.1.73.9.2.1.31
hmStatusWlanMngmtApStatusActiveRadiosEntryGroups OBJECT-TYPE
    SYNTAX     DisplayString (SIZE(0..251))
    MAX-ACCESS read-only
    STATUS     current
    DESCRIPTION
            "-- empty --"
    ::= { hmStatusWlanMngmtApStatusActiveRadiosEntry 31 }

-- {TABLE} 1.3.6.1.4.1.248.32.18.1.73.9.3
hmStatusWlanMngmtApStatusNewApTable OBJECT-TYPE
    SYNTAX     SEQUENCE OF HmStatusWlanMngmtApStatusNewApEntry
    MAX-ACCESS not-accessible
    STATUS     current
    DESCRIPTION
            "-- empty --"
    ::= { hmStatusWlanMngmtApStatus 3 }

-- {ROW} 1.3.6.1.4.1.248.32.18.1.73.9.3.1
hmStatusWlanMngmtApStatusNewApEntry OBJECT-TYPE
    SYNTAX     HmStatusWlanMngmtApStatusNewApEntry
    MAX-ACCESS not-accessible
    STATUS     current
    DESCRIPTION
            ""
    INDEX {
            hmStatusWlanMngmtApStatusNewApEntryApLanMac
          }
    ::= { hmStatusWlanMngmtApStatusNewApTable 1 }

HmStatusWlanMngmtApStatusNewApEntry ::= SEQUENCE {
            hmStatusWlanMngmtApStatusNewApEntryApLanMac MacAddress,
            hmStatusWlanMngmtApStatusNewApEntryIpAddress IpAddress,
            hmStatusWlanMngmtApStatusNewApEntryName DisplayString,
            hmStatusWlanMngmtApStatusNewApEntryLocation DisplayString,
            hmStatusWlanMngmtApStatusNewApEntryValid INTEGER,
            hmStatusWlanMngmtApStatusNewApEntryConfiguration INTEGER,
            hmStatusWlanMngmtApStatusNewApEntryAutowdsIntegration INTEGER,
            hmStatusWlanMngmtApStatusNewApEntryGroups DisplayString,
            hmStatusWlanMngmtApStatusNewApEntryCertificateState INTEGER
    }

-- {COLUMN} 1.3.6.1.4.1.248.32.18.1.73.9.3.1.1
hmStatusWlanMngmtApStatusNewApEntryApLanMac OBJECT-TYPE
    SYNTAX     MacAddress
    MAX-ACCESS read-only
    STATUS     current
    DESCRIPTION
            "-- empty --"
    ::= { hmStatusWlanMngmtApStatusNewApEntry 1 }

-- {COLUMN} 1.3.6.1.4.1.248.32.18.1.73.9.3.1.2
hmStatusWlanMngmtApStatusNewApEntryIpAddress OBJECT-TYPE
    SYNTAX     IpAddress
    MAX-ACCESS read-only
    STATUS     current
    DESCRIPTION
            "-- empty --"
    ::= { hmStatusWlanMngmtApStatusNewApEntry 2 }

-- {COLUMN} 1.3.6.1.4.1.248.32.18.1.73.9.3.1.3
hmStatusWlanMngmtApStatusNewApEntryName OBJECT-TYPE
    SYNTAX     DisplayString (SIZE(0..82))
    MAX-ACCESS read-only
    STATUS     current
    DESCRIPTION
            "-- empty --"
    ::= { hmStatusWlanMngmtApStatusNewApEntry 3 }

-- {COLUMN} 1.3.6.1.4.1.248.32.18.1.73.9.3.1.4
hmStatusWlanMngmtApStatusNewApEntryLocation OBJECT-TYPE
    SYNTAX     DisplayString (SIZE(0..251))
    MAX-ACCESS read-only
    STATUS     current
    DESCRIPTION
            "-- empty --"
    ::= { hmStatusWlanMngmtApStatusNewApEntry 4 }

-- {COLUMN} 1.3.6.1.4.1.248.32.18.1.73.9.3.1.5
hmStatusWlanMngmtApStatusNewApEntryValid OBJECT-TYPE
    SYNTAX     INTEGER {
                  eNo (0),
                  eYes (1)
            }
    MAX-ACCESS read-only
    STATUS     current
    DESCRIPTION
            "-- empty --"
    ::= { hmStatusWlanMngmtApStatusNewApEntry 5 }

-- {COLUMN} 1.3.6.1.4.1.248.32.18.1.73.9.3.1.6
hmStatusWlanMngmtApStatusNewApEntryConfiguration OBJECT-TYPE
    SYNTAX     INTEGER {
                  eNo (0),
                  eYes (1)
            }
    MAX-ACCESS read-only
    STATUS     current
    DESCRIPTION
            "-- empty --"
    ::= { hmStatusWlanMngmtApStatusNewApEntry 6 }

-- {COLUMN} 1.3.6.1.4.1.248.32.18.1.73.9.3.1.7
hmStatusWlanMngmtApStatusNewApEntryAutowdsIntegration OBJECT-TYPE
    SYNTAX     INTEGER {
                  eNone (0),
                  eExpress (1),
                  ePreconfigured (2)
            }
    MAX-ACCESS read-only
    STATUS     current
    DESCRIPTION
            "-- empty --"
    ::= { hmStatusWlanMngmtApStatusNewApEntry 7 }

-- {COLUMN} 1.3.6.1.4.1.248.32.18.1.73.9.3.1.8
hmStatusWlanMngmtApStatusNewApEntryGroups OBJECT-TYPE
    SYNTAX     DisplayString (SIZE(0..251))
    MAX-ACCESS read-only
    STATUS     current
    DESCRIPTION
            "-- empty --"
    ::= { hmStatusWlanMngmtApStatusNewApEntry 8 }

-- {COLUMN} 1.3.6.1.4.1.248.32.18.1.73.9.3.1.9
hmStatusWlanMngmtApStatusNewApEntryCertificateState OBJECT-TYPE
    SYNTAX     INTEGER {
                  eUnknown (0),
                  eMissing (1),
                  eExpired (2),
                  eIncompatible (3),
                  eNotYetValid (4),
                  eValid (5)
            }
    MAX-ACCESS read-only
    STATUS     current
    DESCRIPTION
            "-- empty --"
    ::= { hmStatusWlanMngmtApStatusNewApEntry 9 }

-- {TABLE} 1.3.6.1.4.1.248.32.18.1.73.9.4
hmStatusWlanMngmtApStatusNextdoorApTable OBJECT-TYPE
    SYNTAX     SEQUENCE OF HmStatusWlanMngmtApStatusNextdoorApEntry
    MAX-ACCESS not-accessible
    STATUS     current
    DESCRIPTION
            "-- empty --"
    ::= { hmStatusWlanMngmtApStatus 4 }

-- {ROW} 1.3.6.1.4.1.248.32.18.1.73.9.4.1
hmStatusWlanMngmtApStatusNextdoorApEntry OBJECT-TYPE
    SYNTAX     HmStatusWlanMngmtApStatusNextdoorApEntry
    MAX-ACCESS not-accessible
    STATUS     current
    DESCRIPTION
            ""
    INDEX {
            hmStatusWlanMngmtApStatusNextdoorApEntryApLanMac
          }
    ::= { hmStatusWlanMngmtApStatusNextdoorApTable 1 }

HmStatusWlanMngmtApStatusNextdoorApEntry ::= SEQUENCE {
            hmStatusWlanMngmtApStatusNextdoorApEntryApLanMac MacAddress,
            hmStatusWlanMngmtApStatusNextdoorApEntryIpAddress IpAddress,
            hmStatusWlanMngmtApStatusNextdoorApEntryName DisplayString,
            hmStatusWlanMngmtApStatusNextdoorApEntryLocation DisplayString,
            hmStatusWlanMngmtApStatusNextdoorApEntryValid INTEGER,
            hmStatusWlanMngmtApStatusNextdoorApEntryWlcName DisplayString,
            hmStatusWlanMngmtApStatusNextdoorApEntryWlcLanMac MacAddress,
            hmStatusWlanMngmtApStatusNextdoorApEntryGroups DisplayString
    }

-- {COLUMN} 1.3.6.1.4.1.248.32.18.1.73.9.4.1.1
hmStatusWlanMngmtApStatusNextdoorApEntryApLanMac OBJECT-TYPE
    SYNTAX     MacAddress
    MAX-ACCESS read-only
    STATUS     current
    DESCRIPTION
            "-- empty --"
    ::= { hmStatusWlanMngmtApStatusNextdoorApEntry 1 }

-- {COLUMN} 1.3.6.1.4.1.248.32.18.1.73.9.4.1.2
hmStatusWlanMngmtApStatusNextdoorApEntryIpAddress OBJECT-TYPE
    SYNTAX     IpAddress
    MAX-ACCESS read-only
    STATUS     current
    DESCRIPTION
            "-- empty --"
    ::= { hmStatusWlanMngmtApStatusNextdoorApEntry 2 }

-- {COLUMN} 1.3.6.1.4.1.248.32.18.1.73.9.4.1.3
hmStatusWlanMngmtApStatusNextdoorApEntryName OBJECT-TYPE
    SYNTAX     DisplayString (SIZE(0..82))
    MAX-ACCESS read-only
    STATUS     current
    DESCRIPTION
            "-- empty --"
    ::= { hmStatusWlanMngmtApStatusNextdoorApEntry 3 }

-- {COLUMN} 1.3.6.1.4.1.248.32.18.1.73.9.4.1.4
hmStatusWlanMngmtApStatusNextdoorApEntryLocation OBJECT-TYPE
    SYNTAX     DisplayString (SIZE(0..251))
    MAX-ACCESS read-only
    STATUS     current
    DESCRIPTION
            "-- empty --"
    ::= { hmStatusWlanMngmtApStatusNextdoorApEntry 4 }

-- {COLUMN} 1.3.6.1.4.1.248.32.18.1.73.9.4.1.5
hmStatusWlanMngmtApStatusNextdoorApEntryValid OBJECT-TYPE
    SYNTAX     INTEGER {
                  eNo (0),
                  eYes (1)
            }
    MAX-ACCESS read-only
    STATUS     current
    DESCRIPTION
            "-- empty --"
    ::= { hmStatusWlanMngmtApStatusNextdoorApEntry 5 }

-- {COLUMN} 1.3.6.1.4.1.248.32.18.1.73.9.4.1.6
hmStatusWlanMngmtApStatusNextdoorApEntryWlcName OBJECT-TYPE
    SYNTAX     DisplayString (SIZE(0..82))
    MAX-ACCESS read-only
    STATUS     current
    DESCRIPTION
            "-- empty --"
    ::= { hmStatusWlanMngmtApStatusNextdoorApEntry 6 }

-- {COLUMN} 1.3.6.1.4.1.248.32.18.1.73.9.4.1.7
hmStatusWlanMngmtApStatusNextdoorApEntryWlcLanMac OBJECT-TYPE
    SYNTAX     MacAddress
    MAX-ACCESS read-only
    STATUS     current
    DESCRIPTION
            "-- empty --"
    ::= { hmStatusWlanMngmtApStatusNextdoorApEntry 7 }

-- {COLUMN} 1.3.6.1.4.1.248.32.18.1.73.9.4.1.31
hmStatusWlanMngmtApStatusNextdoorApEntryGroups OBJECT-TYPE
    SYNTAX     DisplayString (SIZE(0..251))
    MAX-ACCESS read-only
    STATUS     current
    DESCRIPTION
            "-- empty --"
    ::= { hmStatusWlanMngmtApStatusNextdoorApEntry 31 }

-- {SCALAR} 1.3.6.1.4.1.248.32.18.1.73.10
hmStatusWlanMngmtAcceptAp OBJECT-TYPE
    SYNTAX     DisplayString
    MAX-ACCESS read-write
    STATUS     current
    DESCRIPTION
            "-- empty --"
    ::= { hmStatusWlanMngmt 10 }

-- {SCALAR} 1.3.6.1.4.1.248.32.18.1.73.11
hmStatusWlanMngmtDisconnectAp OBJECT-TYPE
    SYNTAX     DisplayString
    MAX-ACCESS read-write
    STATUS     current
    DESCRIPTION
            "-- empty --"
    ::= { hmStatusWlanMngmt 11 }

-- {NODE} 1.3.6.1.4.1.248.32.18.1.73.20
hmStatusWlanMngmtCentralFwMngmt OBJECT IDENTIFIER ::= { hmStatusWlanMngmt 20 }

-- {TABLE} 1.3.6.1.4.1.248.32.18.1.73.20.12
hmStatusWlanMngmtCentralFwMngmtAvailFwTable OBJECT-TYPE
    SYNTAX     SEQUENCE OF HmStatusWlanMngmtCentralFwMngmtAvailFwEntry
    MAX-ACCESS not-accessible
    STATUS     current
    DESCRIPTION
            "available firmwares"
    ::= { hmStatusWlanMngmtCentralFwMngmt 12 }

-- {ROW} 1.3.6.1.4.1.248.32.18.1.73.20.12.1
hmStatusWlanMngmtCentralFwMngmtAvailFwEntry OBJECT-TYPE
    SYNTAX     HmStatusWlanMngmtCentralFwMngmtAvailFwEntry
    MAX-ACCESS not-accessible
    STATUS     current
    DESCRIPTION
            ""
    INDEX {
            hmStatusWlanMngmtCentralFwMngmtAvailFwEntryIndex
          }
    ::= { hmStatusWlanMngmtCentralFwMngmtAvailFwTable 1 }

HmStatusWlanMngmtCentralFwMngmtAvailFwEntry ::= SEQUENCE {
            hmStatusWlanMngmtCentralFwMngmtAvailFwEntryIndex Integer32,
            hmStatusWlanMngmtCentralFwMngmtAvailFwEntryDevice DisplayString,
            hmStatusWlanMngmtCentralFwMngmtAvailFwEntryVersion DisplayString,
            hmStatusWlanMngmtCentralFwMngmtAvailFwEntryDate DisplayString,
            hmStatusWlanMngmtCentralFwMngmtAvailFwEntryDescription DisplayString,
            hmStatusWlanMngmtCentralFwMngmtAvailFwEntryFileType INTEGER,
            hmStatusWlanMngmtCentralFwMngmtAvailFwEntryFilesize Integer32,
            hmStatusWlanMngmtCentralFwMngmtAvailFwEntryLoaded INTEGER,
            hmStatusWlanMngmtCentralFwMngmtAvailFwEntryRunningUpdates Integer32,
            hmStatusWlanMngmtCentralFwMngmtAvailFwEntryCompatibilityId Integer32
    }

-- {COLUMN} 1.3.6.1.4.1.248.32.18.1.73.20.12.1.1
hmStatusWlanMngmtCentralFwMngmtAvailFwEntryIndex OBJECT-TYPE
    SYNTAX     Integer32 (0..2147483647)
    MAX-ACCESS read-only
    STATUS     current
    DESCRIPTION
            "-- empty --"
    ::= { hmStatusWlanMngmtCentralFwMngmtAvailFwEntry 1 }

-- {COLUMN} 1.3.6.1.4.1.248.32.18.1.73.20.12.1.2
hmStatusWlanMngmtCentralFwMngmtAvailFwEntryDevice OBJECT-TYPE
    SYNTAX     DisplayString (SIZE(0..255))
    MAX-ACCESS read-only
    STATUS     current
    DESCRIPTION
            "-- empty --"
    ::= { hmStatusWlanMngmtCentralFwMngmtAvailFwEntry 2 }

-- {COLUMN} 1.3.6.1.4.1.248.32.18.1.73.20.12.1.3
hmStatusWlanMngmtCentralFwMngmtAvailFwEntryVersion OBJECT-TYPE
    SYNTAX     DisplayString (SIZE(0..255))
    MAX-ACCESS read-only
    STATUS     current
    DESCRIPTION
            "-- empty --"
    ::= { hmStatusWlanMngmtCentralFwMngmtAvailFwEntry 3 }

-- {COLUMN} 1.3.6.1.4.1.248.32.18.1.73.20.12.1.4
hmStatusWlanMngmtCentralFwMngmtAvailFwEntryDate OBJECT-TYPE
    SYNTAX     DisplayString (SIZE(0..255))
    MAX-ACCESS read-only
    STATUS     current
    DESCRIPTION
            "-- empty --"
    ::= { hmStatusWlanMngmtCentralFwMngmtAvailFwEntry 4 }

-- {COLUMN} 1.3.6.1.4.1.248.32.18.1.73.20.12.1.5
hmStatusWlanMngmtCentralFwMngmtAvailFwEntryDescription OBJECT-TYPE
    SYNTAX     DisplayString (SIZE(0..255))
    MAX-ACCESS read-only
    STATUS     current
    DESCRIPTION
            "-- empty --"
    ::= { hmStatusWlanMngmtCentralFwMngmtAvailFwEntry 5 }

-- {COLUMN} 1.3.6.1.4.1.248.32.18.1.73.20.12.1.6
hmStatusWlanMngmtCentralFwMngmtAvailFwEntryFileType OBJECT-TYPE
    SYNTAX     INTEGER {
                  eUnknown (0),
                  eFirmware (1),
                  eLoader (2),
                  eOemFile (3),
                  eConverter (4),
                  eMiniFirmware (5)
            }
    MAX-ACCESS read-only
    STATUS     current
    DESCRIPTION
            "-- empty --"
    ::= { hmStatusWlanMngmtCentralFwMngmtAvailFwEntry 6 }

-- {COLUMN} 1.3.6.1.4.1.248.32.18.1.73.20.12.1.7
hmStatusWlanMngmtCentralFwMngmtAvailFwEntryFilesize OBJECT-TYPE
    SYNTAX     Integer32 (0..2147483647)
    MAX-ACCESS read-only
    STATUS     current
    DESCRIPTION
            "-- empty --"
    ::= { hmStatusWlanMngmtCentralFwMngmtAvailFwEntry 7 }

-- {COLUMN} 1.3.6.1.4.1.248.32.18.1.73.20.12.1.8
hmStatusWlanMngmtCentralFwMngmtAvailFwEntryLoaded OBJECT-TYPE
    SYNTAX     INTEGER {
                  eNo (0),
                  eYes (1)
            }
    MAX-ACCESS read-only
    STATUS     current
    DESCRIPTION
            "-- empty --"
    ::= { hmStatusWlanMngmtCentralFwMngmtAvailFwEntry 8 }

-- {COLUMN} 1.3.6.1.4.1.248.32.18.1.73.20.12.1.9
hmStatusWlanMngmtCentralFwMngmtAvailFwEntryRunningUpdates OBJECT-TYPE
    SYNTAX     Integer32 (0..2147483647)
    MAX-ACCESS read-only
    STATUS     current
    DESCRIPTION
            "-- empty --"
    ::= { hmStatusWlanMngmtCentralFwMngmtAvailFwEntry 9 }

-- {COLUMN} 1.3.6.1.4.1.248.32.18.1.73.20.12.1.10
hmStatusWlanMngmtCentralFwMngmtAvailFwEntryCompatibilityId OBJECT-TYPE
    SYNTAX     Integer32 (0..65535)
    MAX-ACCESS read-only
    STATUS     current
    DESCRIPTION
            "-- empty --"
    ::= { hmStatusWlanMngmtCentralFwMngmtAvailFwEntry 10 }

-- {TABLE} 1.3.6.1.4.1.248.32.18.1.73.20.13
hmStatusWlanMngmtCentralFwMngmtAvailableScriptsTable OBJECT-TYPE
    SYNTAX     SEQUENCE OF HmStatusWlanMngmtCentralFwMngmtAvailableScriptsEntry
    MAX-ACCESS not-accessible
    STATUS     current
    DESCRIPTION
            "-- empty --"
    ::= { hmStatusWlanMngmtCentralFwMngmt 13 }

-- {ROW} 1.3.6.1.4.1.248.32.18.1.73.20.13.1
hmStatusWlanMngmtCentralFwMngmtAvailableScriptsEntry OBJECT-TYPE
    SYNTAX     HmStatusWlanMngmtCentralFwMngmtAvailableScriptsEntry
    MAX-ACCESS not-accessible
    STATUS     current
    DESCRIPTION
            ""
    INDEX {
            hmStatusWlanMngmtCentralFwMngmtAvailableScriptsEntryIndex
          }
    ::= { hmStatusWlanMngmtCentralFwMngmtAvailableScriptsTable 1 }

HmStatusWlanMngmtCentralFwMngmtAvailableScriptsEntry ::= SEQUENCE {
            hmStatusWlanMngmtCentralFwMngmtAvailableScriptsEntryIndex Integer32,
            hmStatusWlanMngmtCentralFwMngmtAvailableScriptsEntryName DisplayString,
            hmStatusWlanMngmtCentralFwMngmtAvailableScriptsEntryFilesize Integer32,
            hmStatusWlanMngmtCentralFwMngmtAvailableScriptsEntryCommentary DisplayString,
            hmStatusWlanMngmtCentralFwMngmtAvailableScriptsEntryRunTransm Integer32
    }

-- {COLUMN} 1.3.6.1.4.1.248.32.18.1.73.20.13.1.1
hmStatusWlanMngmtCentralFwMngmtAvailableScriptsEntryIndex OBJECT-TYPE
    SYNTAX     Integer32 (0..2147483647)
    MAX-ACCESS read-only
    STATUS     current
    DESCRIPTION
            "-- empty --"
    ::= { hmStatusWlanMngmtCentralFwMngmtAvailableScriptsEntry 1 }

-- {COLUMN} 1.3.6.1.4.1.248.32.18.1.73.20.13.1.2
hmStatusWlanMngmtCentralFwMngmtAvailableScriptsEntryName OBJECT-TYPE
    SYNTAX     DisplayString (SIZE(0..255))
    MAX-ACCESS read-only
    STATUS     current
    DESCRIPTION
            "-- empty --"
    ::= { hmStatusWlanMngmtCentralFwMngmtAvailableScriptsEntry 2 }

-- {COLUMN} 1.3.6.1.4.1.248.32.18.1.73.20.13.1.3
hmStatusWlanMngmtCentralFwMngmtAvailableScriptsEntryFilesize OBJECT-TYPE
    SYNTAX     Integer32 (0..2147483647)
    MAX-ACCESS read-only
    STATUS     current
    DESCRIPTION
            "-- empty --"
    ::= { hmStatusWlanMngmtCentralFwMngmtAvailableScriptsEntry 3 }

-- {COLUMN} 1.3.6.1.4.1.248.32.18.1.73.20.13.1.4
hmStatusWlanMngmtCentralFwMngmtAvailableScriptsEntryCommentary OBJECT-TYPE
    SYNTAX     DisplayString (SIZE(0..255))
    MAX-ACCESS read-only
    STATUS     current
    DESCRIPTION
            "-- empty --"
    ::= { hmStatusWlanMngmtCentralFwMngmtAvailableScriptsEntry 4 }

-- {COLUMN} 1.3.6.1.4.1.248.32.18.1.73.20.13.1.5
hmStatusWlanMngmtCentralFwMngmtAvailableScriptsEntryRunTransm OBJECT-TYPE
    SYNTAX     Integer32 (0..2147483647)
    MAX-ACCESS read-only
    STATUS     current
    DESCRIPTION
            "running transmissions"
    ::= { hmStatusWlanMngmtCentralFwMngmtAvailableScriptsEntry 5 }

-- {SCALAR} 1.3.6.1.4.1.248.32.18.1.73.20.14
hmStatusWlanMngmtCentralFwMngmtFetchJobStatus OBJECT-TYPE
    SYNTAX     INTEGER {
                  eIdle (0),
                  eBadUrl (1),
                  eHttpTimeOut (2),
                  eNoMemory (3),
                  eValidUrlFound (4),
                  eHttpError (5),
                  eDownloadIsRunning (6),
                  eFetchJobIsBusy (7),
                  eReceivedFileTooBig (8),
                  eBroken (9),
                  eInvalidFilesize (10),
                  eConnError (11),
                  eTooSlow (12),
                  eReadFailed (13),
                  eConnectionError (14),
                  eDnsError (15),
                  eProtocolError (16)
            }
    MAX-ACCESS read-only
    STATUS     current
    DESCRIPTION
            "-- empty --"
    ::= { hmStatusWlanMngmtCentralFwMngmt 14 }

-- {SCALAR} 1.3.6.1.4.1.248.32.18.1.73.20.15
hmStatusWlanMngmtCentralFwMngmtLoadedFirmwares OBJECT-TYPE
    SYNTAX     Integer32 (0..2147483647)
    MAX-ACCESS read-only
    STATUS     current
    DESCRIPTION
            "-- empty --"
    ::= { hmStatusWlanMngmtCentralFwMngmt 15 }

-- {SCALAR} 1.3.6.1.4.1.248.32.18.1.73.20.16
hmStatusWlanMngmtCentralFwMngmtUsedMemory OBJECT-TYPE
    SYNTAX     Integer32 (0..2147483647)
    MAX-ACCESS read-only
    STATUS     current
    DESCRIPTION
            "-- empty --"
    ::= { hmStatusWlanMngmtCentralFwMngmt 16 }

-- {SCALAR} 1.3.6.1.4.1.248.32.18.1.73.20.17
hmStatusWlanMngmtCentralFwMngmtUpdFwScriptInfo OBJECT-TYPE
    SYNTAX     DisplayString
    MAX-ACCESS read-write
    STATUS     current
    DESCRIPTION
            "update firmware and script information"
    ::= { hmStatusWlanMngmtCentralFwMngmt 17 }

-- {SCALAR} 1.3.6.1.4.1.248.32.18.1.73.20.18
hmStatusWlanMngmtCentralFwMngmtRebootUpdatedAps OBJECT-TYPE
    SYNTAX     DisplayString
    MAX-ACCESS read-write
    STATUS     current
    DESCRIPTION
            "-- empty --"
    ::= { hmStatusWlanMngmtCentralFwMngmt 18 }

-- {SCALAR} 1.3.6.1.4.1.248.32.18.1.73.32
hmStatusWlanMngmtLicenseCount OBJECT-TYPE
    SYNTAX     Integer32 (0..2147483647)
    MAX-ACCESS read-only
    STATUS     current
    DESCRIPTION
            "-- empty --"
    ::= { hmStatusWlanMngmt 32 }

-- {SCALAR} 1.3.6.1.4.1.248.32.18.1.73.33
hmStatusWlanMngmtLicenseLimit OBJECT-TYPE
    SYNTAX     Integer32 (0..2147483647)
    MAX-ACCESS read-only
    STATUS     current
    DESCRIPTION
            "-- empty --"
    ::= { hmStatusWlanMngmt 33 }

-- {SCALAR} 1.3.6.1.4.1.248.32.18.1.73.34
hmStatusWlanMngmtQueueBlockErrors OBJECT-TYPE
    SYNTAX     Integer32 (0..2147483647)
    MAX-ACCESS read-only
    STATUS     current
    DESCRIPTION
            "-- empty --"
    ::= { hmStatusWlanMngmt 34 }

-- {SCALAR} 1.3.6.1.4.1.248.32.18.1.73.35
hmStatusWlanMngmtClientCount OBJECT-TYPE
    SYNTAX     Integer32 (0..2147483647)
    MAX-ACCESS read-only
    STATUS     current
    DESCRIPTION
            "-- empty --"
    ::= { hmStatusWlanMngmt 35 }

-- {TABLE} 1.3.6.1.4.1.248.32.18.1.73.36
hmStatusWlanMngmtWlcBridgeInterfacesTable OBJECT-TYPE
    SYNTAX     SEQUENCE OF HmStatusWlanMngmtWlcBridgeInterfacesEntry
    MAX-ACCESS not-accessible
    STATUS     current
    DESCRIPTION
            "-- empty --"
    ::= { hmStatusWlanMngmt 36 }

-- {ROW} 1.3.6.1.4.1.248.32.18.1.73.36.1
hmStatusWlanMngmtWlcBridgeInterfacesEntry OBJECT-TYPE
    SYNTAX     HmStatusWlanMngmtWlcBridgeInterfacesEntry
    MAX-ACCESS not-accessible
    STATUS     current
    DESCRIPTION
            ""
    INDEX {
            hmStatusWlanMngmtWlcBridgeInterfacesEntryBridgeInterface
          }
    ::= { hmStatusWlanMngmtWlcBridgeInterfacesTable 1 }

HmStatusWlanMngmtWlcBridgeInterfacesEntry ::= SEQUENCE {
            hmStatusWlanMngmtWlcBridgeInterfacesEntryBridgeInterface INTEGER,
            hmStatusWlanMngmtWlcBridgeInterfacesEntryRegisteredConnections Integer32,
            hmStatusWlanMngmtWlcBridgeInterfacesEntryRecvUnicasts Integer32,
            hmStatusWlanMngmtWlcBridgeInterfacesEntryRecvMulticasts Integer32,
            hmStatusWlanMngmtWlcBridgeInterfacesEntryRecvBroadcasts Integer32,
            hmStatusWlanMngmtWlcBridgeInterfacesEntryTransUnicastPackets Integer32,
            hmStatusWlanMngmtWlcBridgeInterfacesEntryTransMultiBroadPckts Integer32,
            hmStatusWlanMngmtWlcBridgeInterfacesEntryDroppedPackets Integer32,
            hmStatusWlanMngmtWlcBridgeInterfacesEntryUnicastConnections Integer32
    }

-- {COLUMN} 1.3.6.1.4.1.248.32.18.1.73.36.1.1
hmStatusWlanMngmtWlcBridgeInterfacesEntryBridgeInterface OBJECT-TYPE
    SYNTAX     INTEGER {
                  eLan (0),
                  eWlcTunnel1 (1),
                  eWlcTunnel2 (2),
                  eWlcTunnel3 (3),
                  eWlcTunnel4 (4),
                  eWlcTunnel5 (5),
                  eWlcTunnel6 (6),
                  eWlcTunnel7 (7),
                  eWlcTunnel8 (8),
                  eWlcTunnel9 (9),
                  eWlcTunnel10 (10),
                  eWlcTunnel11 (11),
                  eWlcTunnel12 (12),
                  eWlcTunnel13 (13),
                  eWlcTunnel14 (14),
                  eWlcTunnel15 (15),
                  eWlcTunnel16 (16),
                  eWlcTunnel17 (17),
                  eWlcTunnel18 (18),
                  eWlcTunnel19 (19),
                  eWlcTunnel20 (20),
                  eWlcTunnel21 (21),
                  eWlcTunnel22 (22),
                  eWlcTunnel23 (23),
                  eWlcTunnel24 (24),
                  eWlcTunnel25 (25),
                  eWlcTunnel26 (26),
                  eWlcTunnel27 (27),
                  eWlcTunnel28 (28),
                  eWlcTunnel29 (29),
                  eWlcTunnel30 (30),
                  eWlcTunnel31 (31),
                  eWlcTunnel32 (32),
                  eWlcTunnelAutowds (33)
            }
    MAX-ACCESS read-only
    STATUS     current
    DESCRIPTION
            "-- empty --"
    ::= { hmStatusWlanMngmtWlcBridgeInterfacesEntry 1 }

-- {COLUMN} 1.3.6.1.4.1.248.32.18.1.73.36.1.2
hmStatusWlanMngmtWlcBridgeInterfacesEntryRegisteredConnections OBJECT-TYPE
    SYNTAX     Integer32 (0..2147483647)
    MAX-ACCESS read-only
    STATUS     current
    DESCRIPTION
            "-- empty --"
    ::= { hmStatusWlanMngmtWlcBridgeInterfacesEntry 2 }

-- {COLUMN} 1.3.6.1.4.1.248.32.18.1.73.36.1.3
hmStatusWlanMngmtWlcBridgeInterfacesEntryRecvUnicasts OBJECT-TYPE
    SYNTAX     Integer32 (0..2147483647)
    MAX-ACCESS read-only
    STATUS     current
    DESCRIPTION
            "-- empty --"
    ::= { hmStatusWlanMngmtWlcBridgeInterfacesEntry 3 }

-- {COLUMN} 1.3.6.1.4.1.248.32.18.1.73.36.1.4
hmStatusWlanMngmtWlcBridgeInterfacesEntryRecvMulticasts OBJECT-TYPE
    SYNTAX     Integer32 (0..2147483647)
    MAX-ACCESS read-only
    STATUS     current
    DESCRIPTION
            "-- empty --"
    ::= { hmStatusWlanMngmtWlcBridgeInterfacesEntry 4 }

-- {COLUMN} 1.3.6.1.4.1.248.32.18.1.73.36.1.5
hmStatusWlanMngmtWlcBridgeInterfacesEntryRecvBroadcasts OBJECT-TYPE
    SYNTAX     Integer32 (0..2147483647)
    MAX-ACCESS read-only
    STATUS     current
    DESCRIPTION
            "-- empty --"
    ::= { hmStatusWlanMngmtWlcBridgeInterfacesEntry 5 }

-- {COLUMN} 1.3.6.1.4.1.248.32.18.1.73.36.1.6
hmStatusWlanMngmtWlcBridgeInterfacesEntryTransUnicastPackets OBJECT-TYPE
    SYNTAX     Integer32 (0..2147483647)
    MAX-ACCESS read-only
    STATUS     current
    DESCRIPTION
            "-- empty --"
    ::= { hmStatusWlanMngmtWlcBridgeInterfacesEntry 6 }

-- {COLUMN} 1.3.6.1.4.1.248.32.18.1.73.36.1.7
hmStatusWlanMngmtWlcBridgeInterfacesEntryTransMultiBroadPckts OBJECT-TYPE
    SYNTAX     Integer32 (0..2147483647)
    MAX-ACCESS read-only
    STATUS     current
    DESCRIPTION
            ""
    ::= { hmStatusWlanMngmtWlcBridgeInterfacesEntry 7 }

-- {COLUMN} 1.3.6.1.4.1.248.32.18.1.73.36.1.8
hmStatusWlanMngmtWlcBridgeInterfacesEntryDroppedPackets OBJECT-TYPE
    SYNTAX     Integer32 (0..2147483647)
    MAX-ACCESS read-only
    STATUS     current
    DESCRIPTION
            "-- empty --"
    ::= { hmStatusWlanMngmtWlcBridgeInterfacesEntry 8 }

-- {COLUMN} 1.3.6.1.4.1.248.32.18.1.73.36.1.9
hmStatusWlanMngmtWlcBridgeInterfacesEntryUnicastConnections OBJECT-TYPE
    SYNTAX     Integer32 (0..2147483647)
    MAX-ACCESS read-only
    STATUS     current
    DESCRIPTION
            "-- empty --"
    ::= { hmStatusWlanMngmtWlcBridgeInterfacesEntry 9 }

-- {SCALAR} 1.3.6.1.4.1.248.32.18.1.73.37
hmStatusWlanMngmtPreference OBJECT-TYPE
    SYNTAX     Integer32 (0..255)
    MAX-ACCESS read-only
    STATUS     current
    DESCRIPTION
            "-- empty --"
    ::= { hmStatusWlanMngmt 37 }

-- {NODE} 1.3.6.1.4.1.248.32.18.1.73.40
hmStatusWlanMngmtWlcTunnels OBJECT IDENTIFIER ::= { hmStatusWlanMngmt 40 }

-- {SCALAR} 1.3.6.1.4.1.248.32.18.1.73.40.2
hmStatusWlanMngmtWlcTunnelsWlcDataTunnelActive OBJECT-TYPE
    SYNTAX     INTEGER {
                  eNo (0),
                  eYes (1)
            }
    MAX-ACCESS read-only
    STATUS     current
    DESCRIPTION
            "-- empty --"
    ::= { hmStatusWlanMngmtWlcTunnels 2 }

-- {SCALAR} 1.3.6.1.4.1.248.32.18.1.73.40.4
hmStatusWlanMngmtWlcTunnelsNumberOfWlcConn OBJECT-TYPE
    SYNTAX     Integer32 (0..2147483647)
    MAX-ACCESS read-only
    STATUS     current
    DESCRIPTION
            "-- empty --"
    ::= { hmStatusWlanMngmtWlcTunnels 4 }

-- {SCALAR} 1.3.6.1.4.1.248.32.18.1.73.40.5
hmStatusWlanMngmtWlcTunnelsActiveConnections OBJECT-TYPE
    SYNTAX     Integer32 (0..2147483647)
    MAX-ACCESS read-only
    STATUS     current
    DESCRIPTION
            "-- empty --"
    ::= { hmStatusWlanMngmtWlcTunnels 5 }

-- {TABLE} 1.3.6.1.4.1.248.32.18.1.73.40.6
hmStatusWlanMngmtWlcTunnelsWlcConnectionsTable OBJECT-TYPE
    SYNTAX     SEQUENCE OF HmStatusWlanMngmtWlcTunnelsWlcConnectionsEntry
    MAX-ACCESS not-accessible
    STATUS     current
    DESCRIPTION
            "-- empty --"
    ::= { hmStatusWlanMngmtWlcTunnels 6 }

-- {ROW} 1.3.6.1.4.1.248.32.18.1.73.40.6.1
hmStatusWlanMngmtWlcTunnelsWlcConnectionsEntry OBJECT-TYPE
    SYNTAX     HmStatusWlanMngmtWlcTunnelsWlcConnectionsEntry
    MAX-ACCESS not-accessible
    STATUS     current
    DESCRIPTION
            ""
    INDEX {
            hmStatusWlanMngmtWlcTunnelsWlcConnectionsEntryConnId
          }
    ::= { hmStatusWlanMngmtWlcTunnelsWlcConnectionsTable 1 }

HmStatusWlanMngmtWlcTunnelsWlcConnectionsEntry ::= SEQUENCE {
            hmStatusWlanMngmtWlcTunnelsWlcConnectionsEntryConnId Integer32,
            hmStatusWlanMngmtWlcTunnelsWlcConnectionsEntryIpAddress IpAddress,
            hmStatusWlanMngmtWlcTunnelsWlcConnectionsEntryPort Integer32,
            hmStatusWlanMngmtWlcTunnelsWlcConnectionsEntryResult INTEGER,
            hmStatusWlanMngmtWlcTunnelsWlcConnectionsEntryName DisplayString,
            hmStatusWlanMngmtWlcTunnelsWlcConnectionsEntryState INTEGER,
            hmStatusWlanMngmtWlcTunnelsWlcConnectionsEntryValid INTEGER,
            hmStatusWlanMngmtWlcTunnelsWlcConnectionsEntryMacAddress Integer32,
            hmStatusWlanMngmtWlcTunnelsWlcConnectionsEntryFirmwareVersion DisplayString,
            hmStatusWlanMngmtWlcTunnelsWlcConnectionsEntryPmtu Integer32
    }

-- {COLUMN} 1.3.6.1.4.1.248.32.18.1.73.40.6.1.1
hmStatusWlanMngmtWlcTunnelsWlcConnectionsEntryConnId OBJECT-TYPE
    SYNTAX     Integer32 (0..2147483647)
    MAX-ACCESS read-only
    STATUS     current
    DESCRIPTION
            "-- empty --"
    ::= { hmStatusWlanMngmtWlcTunnelsWlcConnectionsEntry 1 }

-- {COLUMN} 1.3.6.1.4.1.248.32.18.1.73.40.6.1.2
hmStatusWlanMngmtWlcTunnelsWlcConnectionsEntryIpAddress OBJECT-TYPE
    SYNTAX     IpAddress
    MAX-ACCESS read-only
    STATUS     current
    DESCRIPTION
            "-- empty --"
    ::= { hmStatusWlanMngmtWlcTunnelsWlcConnectionsEntry 2 }

-- {COLUMN} 1.3.6.1.4.1.248.32.18.1.73.40.6.1.3
hmStatusWlanMngmtWlcTunnelsWlcConnectionsEntryPort OBJECT-TYPE
    SYNTAX     Integer32 (0..65535)
    MAX-ACCESS read-only
    STATUS     current
    DESCRIPTION
            "-- empty --"
    ::= { hmStatusWlanMngmtWlcTunnelsWlcConnectionsEntry 3 }

-- {COLUMN} 1.3.6.1.4.1.248.32.18.1.73.40.6.1.4
hmStatusWlanMngmtWlcTunnelsWlcConnectionsEntryResult OBJECT-TYPE
    SYNTAX     INTEGER {
                  eSuccess (0),
                  eFailure (1),
                  eSuccessNat (2),
                  eJoinFailUnspecified (3),
                  eJoinFailResourceDepletion (4),
                  eJoinFailUnknwnSrc (5),
                  eJoinFailIncorrectData (6),
                  eJoinFailSessionIdInUse (7),
                  eJoinFailWtpNotSupported (8),
                  eJoinFailBindingNotSupp (9),
                  eResetFailUnableToReset (10),
                  eResetFailFirmwWriteErr (11),
                  eConfigurationErrorServProvAnyhow (12),
                  eConfigurationErrorServNotProv (13),
                  eImageDataErrorChecksum (14),
                  eImageDataErrorLength (15),
                  eImageDataErrorOther (16),
                  eImageDataErrorAlrPresent (17),
                  eMessageUnexpectedInvalid (18),
                  eMessageUnexpectedUnrecognized (19),
                  eFailMissingMandMsgElem (20),
                  eFailUnrecognizedMsgElem (21),
                  eUnsupportedLoaderVersion (300),
                  eUnsupportedFirmwareVersion (301),
                  eUnknown (302),
                  eJoinFailAlreadyConnected (303)
            }
    MAX-ACCESS read-only
    STATUS     current
    DESCRIPTION
            "-- empty --"
    ::= { hmStatusWlanMngmtWlcTunnelsWlcConnectionsEntry 4 }

-- {COLUMN} 1.3.6.1.4.1.248.32.18.1.73.40.6.1.5
hmStatusWlanMngmtWlcTunnelsWlcConnectionsEntryName OBJECT-TYPE
    SYNTAX     DisplayString (SIZE(0..31))
    MAX-ACCESS read-only
    STATUS     current
    DESCRIPTION
            "-- empty --"
    ::= { hmStatusWlanMngmtWlcTunnelsWlcConnectionsEntry 5 }

-- {COLUMN} 1.3.6.1.4.1.248.32.18.1.73.40.6.1.6
hmStatusWlanMngmtWlcTunnelsWlcConnectionsEntryState OBJECT-TYPE
    SYNTAX     INTEGER {
                  eUnknown (0),
                  eIdle (5),
                  eDiscovery (10),
                  eDtlsSetup (15),
                  eJoin (20),
                  eConfigure (25),
                  eImageData (30),
                  eReset (35),
                  eDtlsTeardown (40),
                  eSulking (45),
                  eRun (100)
            }
    MAX-ACCESS read-only
    STATUS     current
    DESCRIPTION
            "-- empty --"
    ::= { hmStatusWlanMngmtWlcTunnelsWlcConnectionsEntry 6 }

-- {COLUMN} 1.3.6.1.4.1.248.32.18.1.73.40.6.1.7
hmStatusWlanMngmtWlcTunnelsWlcConnectionsEntryValid OBJECT-TYPE
    SYNTAX     INTEGER {
                  eNo (0),
                  eYes (1)
            }
    MAX-ACCESS read-only
    STATUS     current
    DESCRIPTION
            "-- empty --"
    ::= { hmStatusWlanMngmtWlcTunnelsWlcConnectionsEntry 7 }

-- {COLUMN} 1.3.6.1.4.1.248.32.18.1.73.40.6.1.8
hmStatusWlanMngmtWlcTunnelsWlcConnectionsEntryMacAddress OBJECT-TYPE
    SYNTAX     Integer32 (0..2147483647)
    MAX-ACCESS read-only
    STATUS     current
    DESCRIPTION
            "-- empty --"
    ::= { hmStatusWlanMngmtWlcTunnelsWlcConnectionsEntry 8 }

-- {COLUMN} 1.3.6.1.4.1.248.32.18.1.73.40.6.1.9
hmStatusWlanMngmtWlcTunnelsWlcConnectionsEntryFirmwareVersion OBJECT-TYPE
    SYNTAX     DisplayString (SIZE(0..31))
    MAX-ACCESS read-only
    STATUS     current
    DESCRIPTION
            "-- empty --"
    ::= { hmStatusWlanMngmtWlcTunnelsWlcConnectionsEntry 9 }

-- {COLUMN} 1.3.6.1.4.1.248.32.18.1.73.40.6.1.10
hmStatusWlanMngmtWlcTunnelsWlcConnectionsEntryPmtu OBJECT-TYPE
    SYNTAX     Integer32 (0..2147483647)
    MAX-ACCESS read-only
    STATUS     current
    DESCRIPTION
            "-- empty --"
    ::= { hmStatusWlanMngmtWlcTunnelsWlcConnectionsEntry 10 }

-- {TABLE} 1.3.6.1.4.1.248.32.18.1.73.40.7
hmStatusWlanMngmtWlcTunnelsWlcDiscoveryTable OBJECT-TYPE
    SYNTAX     SEQUENCE OF HmStatusWlanMngmtWlcTunnelsWlcDiscoveryEntry
    MAX-ACCESS not-accessible
    STATUS     current
    DESCRIPTION
            "-- empty --"
    ::= { hmStatusWlanMngmtWlcTunnels 7 }

-- {ROW} 1.3.6.1.4.1.248.32.18.1.73.40.7.1
hmStatusWlanMngmtWlcTunnelsWlcDiscoveryEntry OBJECT-TYPE
    SYNTAX     HmStatusWlanMngmtWlcTunnelsWlcDiscoveryEntry
    MAX-ACCESS not-accessible
    STATUS     current
    DESCRIPTION
            ""
    INDEX {
            hmStatusWlanMngmtWlcTunnelsWlcDiscoveryEntryNetwork
          }
    ::= { hmStatusWlanMngmtWlcTunnelsWlcDiscoveryTable 1 }

HmStatusWlanMngmtWlcTunnelsWlcDiscoveryEntry ::= SEQUENCE {
            hmStatusWlanMngmtWlcTunnelsWlcDiscoveryEntryNetwork DisplayString,
            hmStatusWlanMngmtWlcTunnelsWlcDiscoveryEntryActive INTEGER,
            hmStatusWlanMngmtWlcTunnelsWlcDiscoveryEntryPort Integer32
    }

-- {COLUMN} 1.3.6.1.4.1.248.32.18.1.73.40.7.1.1
hmStatusWlanMngmtWlcTunnelsWlcDiscoveryEntryNetwork OBJECT-TYPE
    SYNTAX     DisplayString (SIZE(0..16))
    MAX-ACCESS read-only
    STATUS     current
    DESCRIPTION
            "-- empty --"
    ::= { hmStatusWlanMngmtWlcTunnelsWlcDiscoveryEntry 1 }

-- {COLUMN} 1.3.6.1.4.1.248.32.18.1.73.40.7.1.2
hmStatusWlanMngmtWlcTunnelsWlcDiscoveryEntryActive OBJECT-TYPE
    SYNTAX     INTEGER {
                  eNo (0),
                  eYes (1)
            }
    MAX-ACCESS read-only
    STATUS     current
    DESCRIPTION
            "-- empty --"
    ::= { hmStatusWlanMngmtWlcTunnelsWlcDiscoveryEntry 2 }

-- {COLUMN} 1.3.6.1.4.1.248.32.18.1.73.40.7.1.3
hmStatusWlanMngmtWlcTunnelsWlcDiscoveryEntryPort OBJECT-TYPE
    SYNTAX     Integer32 (0..65535)
    MAX-ACCESS read-only
    STATUS     current
    DESCRIPTION
            "-- empty --"
    ::= { hmStatusWlanMngmtWlcTunnelsWlcDiscoveryEntry 3 }

-- {SCALAR} 1.3.6.1.4.1.248.32.18.1.73.40.8
hmStatusWlanMngmtWlcTunnelsWlcTunnelActive OBJECT-TYPE
    SYNTAX     INTEGER {
                  eNo (0),
                  eYes (1)
            }
    MAX-ACCESS read-only
    STATUS     current
    DESCRIPTION
            "-- empty --"
    ::= { hmStatusWlanMngmtWlcTunnels 8 }

-- {SCALAR} 1.3.6.1.4.1.248.32.18.1.73.41
hmStatusWlanMngmtNextdoorAp OBJECT-TYPE
    SYNTAX     Integer32 (0..2147483647)
    MAX-ACCESS read-only
    STATUS     current
    DESCRIPTION
            "-- empty --"
    ::= { hmStatusWlanMngmt 41 }

-- {SCALAR} 1.3.6.1.4.1.248.32.18.1.73.50
hmStatusWlanMngmtWtpCount OBJECT-TYPE
    SYNTAX     Integer32 (0..2147483647)
    MAX-ACCESS read-only
    STATUS     current
    DESCRIPTION
            "-- empty --"
    ::= { hmStatusWlanMngmt 50 }

-- {SCALAR} 1.3.6.1.4.1.248.32.18.1.73.51
hmStatusWlanMngmtClientCount24ghz OBJECT-TYPE
    SYNTAX     Integer32 (0..2147483647)
    MAX-ACCESS read-only
    STATUS     current
    DESCRIPTION
            "-- empty --"
    ::= { hmStatusWlanMngmt 51 }

-- {SCALAR} 1.3.6.1.4.1.248.32.18.1.73.52
hmStatusWlanMngmtClientCount5ghz OBJECT-TYPE
    SYNTAX     Integer32 (0..2147483647)
    MAX-ACCESS read-only
    STATUS     current
    DESCRIPTION
            "-- empty --"
    ::= { hmStatusWlanMngmt 52 }

-- {TABLE} 1.3.6.1.4.1.248.32.18.1.73.100
hmStatusWlanMngmtStationTableTable OBJECT-TYPE
    SYNTAX     SEQUENCE OF HmStatusWlanMngmtStationTableEntry
    MAX-ACCESS not-accessible
    STATUS     current
    DESCRIPTION
            "-- empty --"
    ::= { hmStatusWlanMngmt 100 }

-- {ROW} 1.3.6.1.4.1.248.32.18.1.73.100.1
hmStatusWlanMngmtStationTableEntry OBJECT-TYPE
    SYNTAX     HmStatusWlanMngmtStationTableEntry
    MAX-ACCESS not-accessible
    STATUS     current
    DESCRIPTION
            ""
    INDEX {
            hmStatusWlanMngmtStationTableEntryClientMac,
            hmStatusWlanMngmtStationTableEntryApWlanMac
          }
    ::= { hmStatusWlanMngmtStationTableTable 1 }

HmStatusWlanMngmtStationTableEntry ::= SEQUENCE {
            hmStatusWlanMngmtStationTableEntryClientMac MacAddress,
            hmStatusWlanMngmtStationTableEntryApWlanMac MacAddress,
            hmStatusWlanMngmtStationTableEntryIdentification DisplayString,
            hmStatusWlanMngmtStationTableEntryTrap Integer32,
            hmStatusWlanMngmtStationTableEntryPhySignal Integer32,
            hmStatusWlanMngmtStationTableEntryTxRate INTEGER,
            hmStatusWlanMngmtStationTableEntryRxRate INTEGER,
            hmStatusWlanMngmtStationTableEntryNetworkName DisplayString,
            hmStatusWlanMngmtStationTableEntryKeyType INTEGER,
            hmStatusWlanMngmtStationTableEntryWpaVersion INTEGER,
            hmStatusWlanMngmtStationTableEntryState INTEGER,
            hmStatusWlanMngmtStationTableEntryLastError INTEGER,
            hmStatusWlanMngmtStationTableEntryIpAddress IpAddress,
            hmStatusWlanMngmtStationTableEntryInterface INTEGER,
            hmStatusWlanMngmtStationTableEntryThroughput Integer32,
            hmStatusWlanMngmtStationTableEntryCompression Integer32,
            hmStatusWlanMngmtStationTableEntryApLanMac MacAddress,
            hmStatusWlanMngmtStationTableEntryApName DisplayString,
            hmStatusWlanMngmtStationTableEntryValid INTEGER,
            hmStatusWlanMngmtStationTableEntryEffTxRate Integer32,
            hmStatusWlanMngmtStationTableEntryEffRxRate Integer32,
            hmStatusWlanMngmtStationTableEntryBssid MacAddress,
            hmStatusWlanMngmtStationTableEntryClientSteering INTEGER,
            hmStatusWlanMngmtStationTableEntryOperationMode INTEGER,
            hmStatusWlanMngmtStationTableEntryFastRoaming INTEGER,
            hmStatusWlanMngmtStationTableEntryUserName DisplayString,
            hmStatusWlanMngmtStationTableEntryRadioBand INTEGER,
            hmStatusWlanMngmtStationTableEntryRadioChannel Integer32
    }

-- {COLUMN} 1.3.6.1.4.1.248.32.18.1.73.100.1.1
hmStatusWlanMngmtStationTableEntryClientMac OBJECT-TYPE
    SYNTAX     MacAddress
    MAX-ACCESS read-only
    STATUS     current
    DESCRIPTION
            "-- empty --"
    ::= { hmStatusWlanMngmtStationTableEntry 1 }

-- {COLUMN} 1.3.6.1.4.1.248.32.18.1.73.100.1.2
hmStatusWlanMngmtStationTableEntryApWlanMac OBJECT-TYPE
    SYNTAX     MacAddress
    MAX-ACCESS read-only
    STATUS     current
    DESCRIPTION
            "-- empty --"
    ::= { hmStatusWlanMngmtStationTableEntry 2 }

-- {COLUMN} 1.3.6.1.4.1.248.32.18.1.73.100.1.3
hmStatusWlanMngmtStationTableEntryIdentification OBJECT-TYPE
    SYNTAX     DisplayString (SIZE(0..24))
    MAX-ACCESS read-only
    STATUS     current
    DESCRIPTION
            "-- empty --"
    ::= { hmStatusWlanMngmtStationTableEntry 3 }

-- {COLUMN} 1.3.6.1.4.1.248.32.18.1.73.100.1.4
hmStatusWlanMngmtStationTableEntryTrap OBJECT-TYPE
    SYNTAX     Integer32 (0..65535)
    MAX-ACCESS read-only
    STATUS     current
    DESCRIPTION
            "-- empty --"
    ::= { hmStatusWlanMngmtStationTableEntry 4 }

-- {COLUMN} 1.3.6.1.4.1.248.32.18.1.73.100.1.5
hmStatusWlanMngmtStationTableEntryPhySignal OBJECT-TYPE
    SYNTAX     Integer32 (0..65535)
    MAX-ACCESS read-only
    STATUS     current
    DESCRIPTION
            "-- empty --"
    ::= { hmStatusWlanMngmtStationTableEntry 5 }

-- {COLUMN} 1.3.6.1.4.1.248.32.18.1.73.100.1.6
hmStatusWlanMngmtStationTableEntryTxRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eXR0M5 (16),
                  eXR1M (17),
                  eXR2M (18),
                  eXR3M (19),
                  eT12M (20),
                  eT18M (21),
                  eT24M (22),
                  eT36M (23),
                  eT48M (24),
                  eT72M (25),
                  eT96M (26),
                  eT108M (27),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            "-- empty --"
    ::= { hmStatusWlanMngmtStationTableEntry 6 }

-- {COLUMN} 1.3.6.1.4.1.248.32.18.1.73.100.1.7
hmStatusWlanMngmtStationTableEntryRxRate OBJECT-TYPE
    SYNTAX     INTEGER {
                  eUnknown (0),
                  e1M (1),
                  e2M (2),
                  e5M (3),
                  e5M5 (4),
                  e8M (5),
                  e11M (6),
                  e6M (8),
                  e9M (9),
                  e12M (10),
                  e18M (11),
                  e24M (12),
                  e36M (13),
                  e48M (14),
                  e54M (15),
                  eXR0M5 (16),
                  eXR1M (17),
                  eXR2M (18),
                  eXR3M (19),
                  eT12M (20),
                  eT18M (21),
                  eT24M (22),
                  eT36M (23),
                  eT48M (24),
                  eT72M (25),
                  eT96M (26),
                  eT108M (27),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51),
                  eVHT1S6M5 (105),
                  eVHT1S13M (106),
                  eVHT1S19M5 (107),
                  eVHT1S26M (108),
                  eVHT1S39M (109),
                  eVHT1S52M (110),
                  eVHT1S58M5 (111),
                  eVHT1S65M (112),
                  eVHT1S78M (113),
                  eVHT1S86M7 (114),
                  eVHT2S13M (115),
                  eVHT2S26M (116),
                  eVHT2S39M (117),
                  eVHT2S52M (118),
                  eVHT2S78M (119),
                  eVHT2S104M (120),
                  eVHT2S117M (121),
                  eVHT2S130M (122),
                  eVHT2S156M (123),
                  eVHT2S173M3 (124),
                  eVHT3S19M5 (125),
                  eVHT3S39M (126),
                  eVHT3S58M5 (127),
                  eVHT3S78M (128),
                  eVHT3S117M (129),
                  eVHT3S156M (130),
                  eVHT3S175M5 (131),
                  eVHT3S195M (132),
                  eVHT3S234M (133),
                  eVHT3S260M (134),
                  eVHT4S26M (135),
                  eVHT4S52M (136),
                  eVHT4S78M (137),
                  eVHT4S104M (138),
                  eVHT4S156M (139),
                  eVHT4S208M (140),
                  eVHT4S234M (141),
                  eVHT4S260M (142),
                  eVHT4S312M (143),
                  eVHT4S346M7 (144)
            }
    MAX-ACCESS read-only
    STATUS     current
    DESCRIPTION
            "-- empty --"
    ::= { hmStatusWlanMngmtStationTableEntry 7 }

-- {COLUMN} 1.3.6.1.4.1.248.32.18.1.73.100.1.8
hmStatusWlanMngmtStationTableEntryNetworkName OBJECT-TYPE
    SYNTAX     DisplayString (SIZE(0..31))
    MAX-ACCESS read-only
    STATUS     current
    DESCRIPTION
            "-- empty --"
    ::= { hmStatusWlanMngmtStationTableEntry 8 }

-- {COLUMN} 1.3.6.1.4.1.248.32.18.1.73.100.1.9
hmStatusWlanMngmtStationTableEntryKeyType OBJECT-TYPE
    SYNTAX     INTEGER {
                  eNone (0),
                  eUnknown (1),
                  eWep40Bits (5),
                  eWep104Bits (13),
                  eWep128Bits (16),
                  eTkip (64),
                  eAesOcb (65),
                  eAesCcm (66),
                  eBip (68)
            }
    MAX-ACCESS read-only
    STATUS     current
    DESCRIPTION
            "-- empty --"
    ::= { hmStatusWlanMngmtStationTableEntry 9 }

-- {COLUMN} 1.3.6.1.4.1.248.32.18.1.73.100.1.10
hmStatusWlanMngmtStationTableEntryWpaVersion OBJECT-TYPE
    SYNTAX     INTEGER {
                  eNone (0),
                  eWpa1 (1),
                  eWpa2 (2)
            }
    MAX-ACCESS read-only
    STATUS     current
    DESCRIPTION
            "-- empty --"
    ::= { hmStatusWlanMngmtStationTableEntry 10 }

-- {COLUMN} 1.3.6.1.4.1.248.32.18.1.73.100.1.11
hmStatusWlanMngmtStationTableEntryState OBJECT-TYPE
    SYNTAX     INTEGER {
                  eNone (0),
                  eAdhoc (1),
                  eAuthenticated (2),
                  eConnected (3),
                  eMacCheck (4),
                  eKeyHandshake (8),
                  eAssociated (9),
                  e1xNegotiation (10),
                  eWpsNegotiation (11)
            }
    MAX-ACCESS read-only
    STATUS     current
    DESCRIPTION
            "-- empty --"
    ::= { hmStatusWlanMngmtStationTableEntry 11 }

-- {COLUMN} 1.3.6.1.4.1.248.32.18.1.73.100.1.12
hmStatusWlanMngmtStationTableEntryLastError OBJECT-TYPE
    SYNTAX     INTEGER {
                  eNone (0),
                  eAuthSuccess (1),
                  eDeauth (2),
                  eAssocSuccess (3),
                  eReassocSuccess (4),
                  eDisassoc (5),
                  eRadiusSuccess (6),
                  eAuthReject (7),
                  eAssocReject (8),
                  eKeyhandshakeSuccess (9),
                  eKeyhandshakeTimeout (10),
                  eKeyhandshakeFailure (11),
                  eRadiusReject (12),
                  eSupervision (13),
                  e8021xSuccess (14),
                  e8021xFailure (15),
                  eIdleTimeout (16),
                  eAdminDeassoc (17),
                  eRoamed (18)
            }
    MAX-ACCESS read-only
    STATUS     current
    DESCRIPTION
            "-- empty --"
    ::= { hmStatusWlanMngmtStationTableEntry 12 }

-- {COLUMN} 1.3.6.1.4.1.248.32.18.1.73.100.1.13
hmStatusWlanMngmtStationTableEntryIpAddress OBJECT-TYPE
    SYNTAX     IpAddress
    MAX-ACCESS read-only
    STATUS     current
    DESCRIPTION
            "-- empty --"
    ::= { hmStatusWlanMngmtStationTableEntry 13 }

-- {COLUMN} 1.3.6.1.4.1.248.32.18.1.73.100.1.14
hmStatusWlanMngmtStationTableEntryInterface OBJECT-TYPE
    SYNTAX     INTEGER {
                  eWlan1 (0),
                  eWlan2 (1),
                  eWlan3 (2),
                  eWlan4 (3)
            }
    MAX-ACCESS read-only
    STATUS     current
    DESCRIPTION
            "-- empty --"
    ::= { hmStatusWlanMngmtStationTableEntry 14 }

-- {COLUMN} 1.3.6.1.4.1.248.32.18.1.73.100.1.15
hmStatusWlanMngmtStationTableEntryThroughput OBJECT-TYPE
    SYNTAX     Integer32 (0..2147483647)
    MAX-ACCESS read-only
    STATUS     current
    DESCRIPTION
            "-- empty --"
    ::= { hmStatusWlanMngmtStationTableEntry 15 }

-- {COLUMN} 1.3.6.1.4.1.248.32.18.1.73.100.1.16
hmStatusWlanMngmtStationTableEntryCompression OBJECT-TYPE
    SYNTAX     Integer32 (0..255)
    MAX-ACCESS read-only
    STATUS     current
    DESCRIPTION
            "-- empty --"
    ::= { hmStatusWlanMngmtStationTableEntry 16 }

-- {COLUMN} 1.3.6.1.4.1.248.32.18.1.73.100.1.17
hmStatusWlanMngmtStationTableEntryApLanMac OBJECT-TYPE
    SYNTAX     MacAddress
    MAX-ACCESS read-only
    STATUS     current
    DESCRIPTION
            "-- empty --"
    ::= { hmStatusWlanMngmtStationTableEntry 17 }

-- {COLUMN} 1.3.6.1.4.1.248.32.18.1.73.100.1.18
hmStatusWlanMngmtStationTableEntryApName OBJECT-TYPE
    SYNTAX     DisplayString (SIZE(0..16))
    MAX-ACCESS read-only
    STATUS     current
    DESCRIPTION
            "-- empty --"
    ::= { hmStatusWlanMngmtStationTableEntry 18 }

-- {COLUMN} 1.3.6.1.4.1.248.32.18.1.73.100.1.19
hmStatusWlanMngmtStationTableEntryValid OBJECT-TYPE
    SYNTAX     INTEGER {
                  eNo (0),
                  eYes (1)
            }
    MAX-ACCESS read-only
    STATUS     current
    DESCRIPTION
            "-- empty --"
    ::= { hmStatusWlanMngmtStationTableEntry 19 }

-- {COLUMN} 1.3.6.1.4.1.248.32.18.1.73.100.1.20
hmStatusWlanMngmtStationTableEntryEffTxRate OBJECT-TYPE
    SYNTAX     Integer32 (0..65535)
    MAX-ACCESS read-only
    STATUS     current
    DESCRIPTION
            "-- empty --"
    ::= { hmStatusWlanMngmtStationTableEntry 20 }

-- {COLUMN} 1.3.6.1.4.1.248.32.18.1.73.100.1.21
hmStatusWlanMngmtStationTableEntryEffRxRate OBJECT-TYPE
    SYNTAX     Integer32 (0..65535)
    MAX-ACCESS read-only
    STATUS     current
    DESCRIPTION
            "-- empty --"
    ::= { hmStatusWlanMngmtStationTableEntry 21 }

-- {COLUMN} 1.3.6.1.4.1.248.32.18.1.73.100.1.22
hmStatusWlanMngmtStationTableEntryBssid OBJECT-TYPE
    SYNTAX     MacAddress
    MAX-ACCESS read-only
    STATUS     current
    DESCRIPTION
            "-- empty --"
    ::= { hmStatusWlanMngmtStationTableEntry 22 }

-- {COLUMN} 1.3.6.1.4.1.248.32.18.1.73.100.1.23
hmStatusWlanMngmtStationTableEntryClientSteering OBJECT-TYPE
    SYNTAX     INTEGER {
                  ePending (0),
                  eClientSteeringOk (1),
                  eUnsteerable (2),
                  eNoInfo (3)
            }
    MAX-ACCESS read-only
    STATUS     current
    DESCRIPTION
            "-- empty --"
    ::= { hmStatusWlanMngmtStationTableEntry 23 }

-- {COLUMN} 1.3.6.1.4.1.248.32.18.1.73.100.1.24
hmStatusWlanMngmtStationTableEntryOperationMode OBJECT-TYPE
    SYNTAX     INTEGER {
                  eUnknown (0),
                  e11b (1),
                  e11g (2),
                  e11a (3),
                  e11n (4),
                  e11ac (5)
            }
    MAX-ACCESS read-only
    STATUS     current
    DESCRIPTION
            "-- empty --"
    ::= { hmStatusWlanMngmtStationTableEntry 24 }

-- {COLUMN} 1.3.6.1.4.1.248.32.18.1.73.100.1.25
hmStatusWlanMngmtStationTableEntryFastRoaming OBJECT-TYPE
    SYNTAX     INTEGER {
                  eNo (0),
                  eYes (1)
            }
    MAX-ACCESS read-only
    STATUS     current
    DESCRIPTION
            "-- empty --"
    ::= { hmStatusWlanMngmtStationTableEntry 25 }

-- {COLUMN} 1.3.6.1.4.1.248.32.18.1.73.100.1.26
hmStatusWlanMngmtStationTableEntryUserName OBJECT-TYPE
    SYNTAX     DisplayString (SIZE(0..20))
    MAX-ACCESS read-only
    STATUS     current
    DESCRIPTION
            "-- empty --"
    ::= { hmStatusWlanMngmtStationTableEntry 26 }

-- {COLUMN} 1.3.6.1.4.1.248.32.18.1.73.100.1.27
hmStatusWlanMngmtStationTableEntryRadioBand OBJECT-TYPE
    SYNTAX     INTEGER {
                  eUnknown (0),
                  e24ghz (1),
                  e5ghz (2)
            }
    MAX-ACCESS read-only
    STATUS     current
    DESCRIPTION
            "-- empty --"
    ::= { hmStatusWlanMngmtStationTableEntry 27 }

-- {COLUMN} 1.3.6.1.4.1.248.32.18.1.73.100.1.28
hmStatusWlanMngmtStationTableEntryRadioChannel OBJECT-TYPE
    SYNTAX     Integer32 (0..65535)
    MAX-ACCESS read-only
    STATUS     current
    DESCRIPTION
            "-- empty --"
    ::= { hmStatusWlanMngmtStationTableEntry 28 }

-- {TABLE} 1.3.6.1.4.1.248.32.18.1.73.101
hmStatusWlanMngmtNetworksTable OBJECT-TYPE
    SYNTAX     SEQUENCE OF HmStatusWlanMngmtNetworksEntry
    MAX-ACCESS not-accessible
    STATUS     current
    DESCRIPTION
            "-- empty --"
    ::= { hmStatusWlanMngmt 101 }

-- {ROW} 1.3.6.1.4.1.248.32.18.1.73.101.1
hmStatusWlanMngmtNetworksEntry OBJECT-TYPE
    SYNTAX     HmStatusWlanMngmtNetworksEntry
    MAX-ACCESS not-accessible
    STATUS     current
    DESCRIPTION
            ""
    INDEX {
            hmStatusWlanMngmtNetworksEntryBssid
          }
    ::= { hmStatusWlanMngmtNetworksTable 1 }

HmStatusWlanMngmtNetworksEntry ::= SEQUENCE {
            hmStatusWlanMngmtNetworksEntryBssid MacAddress,
            hmStatusWlanMngmtNetworksEntryApLanMac MacAddress,
            hmStatusWlanMngmtNetworksEntryApWlanMac MacAddress,
            hmStatusWlanMngmtNetworksEntryApName DisplayString,
            hmStatusWlanMngmtNetworksEntryInterface INTEGER,
            hmStatusWlanMngmtNetworksEntryNetNumber Integer32,
            hmStatusWlanMngmtNetworksEntryName DisplayString,
            hmStatusWlanMngmtNetworksEntryClientCount Integer32,
            hmStatusWlanMngmtNetworksEntryValid INTEGER
    }

-- {COLUMN} 1.3.6.1.4.1.248.32.18.1.73.101.1.1
hmStatusWlanMngmtNetworksEntryBssid OBJECT-TYPE
    SYNTAX     MacAddress
    MAX-ACCESS read-only
    STATUS     current
    DESCRIPTION
            "-- empty --"
    ::= { hmStatusWlanMngmtNetworksEntry 1 }

-- {COLUMN} 1.3.6.1.4.1.248.32.18.1.73.101.1.2
hmStatusWlanMngmtNetworksEntryApLanMac OBJECT-TYPE
    SYNTAX     MacAddress
    MAX-ACCESS read-only
    STATUS     current
    DESCRIPTION
            "-- empty --"
    ::= { hmStatusWlanMngmtNetworksEntry 2 }

-- {COLUMN} 1.3.6.1.4.1.248.32.18.1.73.101.1.3
hmStatusWlanMngmtNetworksEntryApWlanMac OBJECT-TYPE
    SYNTAX     MacAddress
    MAX-ACCESS read-only
    STATUS     current
    DESCRIPTION
            "-- empty --"
    ::= { hmStatusWlanMngmtNetworksEntry 3 }

-- {COLUMN} 1.3.6.1.4.1.248.32.18.1.73.101.1.4
hmStatusWlanMngmtNetworksEntryApName OBJECT-TYPE
    SYNTAX     DisplayString (SIZE(0..16))
    MAX-ACCESS read-only
    STATUS     current
    DESCRIPTION
            "-- empty --"
    ::= { hmStatusWlanMngmtNetworksEntry 4 }

-- {COLUMN} 1.3.6.1.4.1.248.32.18.1.73.101.1.5
hmStatusWlanMngmtNetworksEntryInterface OBJECT-TYPE
    SYNTAX     INTEGER {
                  eWlan1 (0),
                  eWlan2 (1),
                  eWlan3 (2),
                  eWlan4 (3)
            }
    MAX-ACCESS read-only
    STATUS     current
    DESCRIPTION
            "-- empty --"
    ::= { hmStatusWlanMngmtNetworksEntry 5 }

-- {COLUMN} 1.3.6.1.4.1.248.32.18.1.73.101.1.6
hmStatusWlanMngmtNetworksEntryNetNumber OBJECT-TYPE
    SYNTAX     Integer32 (0..255)
    MAX-ACCESS read-only
    STATUS     current
    DESCRIPTION
            "-- empty --"
    ::= { hmStatusWlanMngmtNetworksEntry 6 }

-- {COLUMN} 1.3.6.1.4.1.248.32.18.1.73.101.1.7
hmStatusWlanMngmtNetworksEntryName OBJECT-TYPE
    SYNTAX     DisplayString (SIZE(0..31))
    MAX-ACCESS read-only
    STATUS     current
    DESCRIPTION
            "-- empty --"
    ::= { hmStatusWlanMngmtNetworksEntry 7 }

-- {COLUMN} 1.3.6.1.4.1.248.32.18.1.73.101.1.8
hmStatusWlanMngmtNetworksEntryClientCount OBJECT-TYPE
    SYNTAX     Integer32 (0..2147483647)
    MAX-ACCESS read-only
    STATUS     current
    DESCRIPTION
            "-- empty --"
    ::= { hmStatusWlanMngmtNetworksEntry 8 }

-- {COLUMN} 1.3.6.1.4.1.248.32.18.1.73.101.1.9
hmStatusWlanMngmtNetworksEntryValid OBJECT-TYPE
    SYNTAX     INTEGER {
                  eNo (0),
                  eYes (1)
            }
    MAX-ACCESS read-only
    STATUS     current
    DESCRIPTION
            "-- empty --"
    ::= { hmStatusWlanMngmtNetworksEntry 9 }

-- {TABLE} 1.3.6.1.4.1.248.32.18.1.73.102
hmStatusWlanMngmtNetCountTable OBJECT-TYPE
    SYNTAX     SEQUENCE OF HmStatusWlanMngmtNetCountEntry
    MAX-ACCESS not-accessible
    STATUS     current
    DESCRIPTION
            "-- empty --"
    ::= { hmStatusWlanMngmt 102 }

-- {ROW} 1.3.6.1.4.1.248.32.18.1.73.102.1
hmStatusWlanMngmtNetCountEntry OBJECT-TYPE
    SYNTAX     HmStatusWlanMngmtNetCountEntry
    MAX-ACCESS not-accessible
    STATUS     current
    DESCRIPTION
            ""
    INDEX {
            hmStatusWlanMngmtNetCountEntryName
          }
    ::= { hmStatusWlanMngmtNetCountTable 1 }

HmStatusWlanMngmtNetCountEntry ::= SEQUENCE {
            hmStatusWlanMngmtNetCountEntryName DisplayString,
            hmStatusWlanMngmtNetCountEntryNumRadios Integer32,
            hmStatusWlanMngmtNetCountEntryNumStations Integer32,
            hmStatusWlanMngmtNetCountEntrySsid DisplayString,
            hmStatusWlanMngmtNetCountEntryBridgeInterface INTEGER
    }

-- {COLUMN} 1.3.6.1.4.1.248.32.18.1.73.102.1.1
hmStatusWlanMngmtNetCountEntryName OBJECT-TYPE
    SYNTAX     DisplayString (SIZE(0..31))
    MAX-ACCESS read-only
    STATUS     current
    DESCRIPTION
            "-- empty --"
    ::= { hmStatusWlanMngmtNetCountEntry 1 }

-- {COLUMN} 1.3.6.1.4.1.248.32.18.1.73.102.1.2
hmStatusWlanMngmtNetCountEntryNumRadios OBJECT-TYPE
    SYNTAX     Integer32 (0..2147483647)
    MAX-ACCESS read-only
    STATUS     current
    DESCRIPTION
            "-- empty --"
    ::= { hmStatusWlanMngmtNetCountEntry 2 }

-- {COLUMN} 1.3.6.1.4.1.248.32.18.1.73.102.1.3
hmStatusWlanMngmtNetCountEntryNumStations OBJECT-TYPE
    SYNTAX     Integer32 (0..2147483647)
    MAX-ACCESS read-only
    STATUS     current
    DESCRIPTION
            "-- empty --"
    ::= { hmStatusWlanMngmtNetCountEntry 3 }

-- {COLUMN} 1.3.6.1.4.1.248.32.18.1.73.102.1.4
hmStatusWlanMngmtNetCountEntrySsid OBJECT-TYPE
    SYNTAX     DisplayString (SIZE(0..32))
    MAX-ACCESS read-only
    STATUS     current
    DESCRIPTION
            "-- empty --"
    ::= { hmStatusWlanMngmtNetCountEntry 4 }

-- {COLUMN} 1.3.6.1.4.1.248.32.18.1.73.102.1.5
hmStatusWlanMngmtNetCountEntryBridgeInterface OBJECT-TYPE
    SYNTAX     INTEGER {
                  eLan (0),
                  eWlcTunnel1 (1),
                  eWlcTunnel2 (2),
                  eWlcTunnel3 (3),
                  eWlcTunnel4 (4),
                  eWlcTunnel5 (5),
                  eWlcTunnel6 (6),
                  eWlcTunnel7 (7),
                  eWlcTunnel8 (8),
                  eWlcTunnel9 (9),
                  eWlcTunnel10 (10),
                  eWlcTunnel11 (11),
                  eWlcTunnel12 (12),
                  eWlcTunnel13 (13),
                  eWlcTunnel14 (14),
                  eWlcTunnel15 (15),
                  eWlcTunnel16 (16),
                  eWlcTunnel17 (17),
                  eWlcTunnel18 (18),
                  eWlcTunnel19 (19),
                  eWlcTunnel20 (20),
                  eWlcTunnel21 (21),
                  eWlcTunnel22 (22),
                  eWlcTunnel23 (23),
                  eWlcTunnel24 (24),
                  eWlcTunnel25 (25),
                  eWlcTunnel26 (26),
                  eWlcTunnel27 (27),
                  eWlcTunnel28 (28),
                  eWlcTunnel29 (29),
                  eWlcTunnel30 (30),
                  eWlcTunnel31 (31),
                  eWlcTunnel32 (32),
                  eWlcTunnelAutowds (33)
            }
    MAX-ACCESS read-only
    STATUS     current
    DESCRIPTION
            "-- empty --"
    ::= { hmStatusWlanMngmtNetCountEntry 5 }

-- {TABLE} 1.3.6.1.4.1.248.32.18.1.73.120
hmStatusWlanMngmtScanResultsTable OBJECT-TYPE
    SYNTAX     SEQUENCE OF HmStatusWlanMngmtScanResultsEntry
    MAX-ACCESS not-accessible
    STATUS     current
    DESCRIPTION
            "-- empty --"
    ::= { hmStatusWlanMngmt 120 }

-- {ROW} 1.3.6.1.4.1.248.32.18.1.73.120.1
hmStatusWlanMngmtScanResultsEntry OBJECT-TYPE
    SYNTAX     HmStatusWlanMngmtScanResultsEntry
    MAX-ACCESS not-accessible
    STATUS     current
    DESCRIPTION
            ""
    INDEX {
            hmStatusWlanMngmtScanResultsEntryBssid
          }
    ::= { hmStatusWlanMngmtScanResultsTable 1 }

HmStatusWlanMngmtScanResultsEntry ::= SEQUENCE {
            hmStatusWlanMngmtScanResultsEntryBssid MacAddress,
            hmStatusWlanMngmtScanResultsEntryApName DisplayString,
            hmStatusWlanMngmtScanResultsEntryIpAddress IpAddress,
            hmStatusWlanMngmtScanResultsEntryApLanMac MacAddress,
            hmStatusWlanMngmtScanResultsEntryInterface INTEGER,
            hmStatusWlanMngmtScanResultsEntryNetworkName DisplayString,
            hmStatusWlanMngmtScanResultsEntryEncryption INTEGER,
            hmStatusWlanMngmtScanResultsEntryRadioBand INTEGER,
            hmStatusWlanMngmtScanResultsEntryRadioChannel Integer32,
            hmStatusWlanMngmtScanResultsEntry108mbpsMode Integer32,
            hmStatusWlanMngmtScanResultsEntryPhySignal Integer32,
            hmStatusWlanMngmtScanResultsEntryNoiseLevel Integer32,
            hmStatusWlanMngmtScanResultsEntryIdentification DisplayString,
            hmStatusWlanMngmtScanResultsEntryAge Integer32
    }

-- {COLUMN} 1.3.6.1.4.1.248.32.18.1.73.120.1.1
hmStatusWlanMngmtScanResultsEntryBssid OBJECT-TYPE
    SYNTAX     MacAddress
    MAX-ACCESS read-only
    STATUS     current
    DESCRIPTION
            "-- empty --"
    ::= { hmStatusWlanMngmtScanResultsEntry 1 }

-- {COLUMN} 1.3.6.1.4.1.248.32.18.1.73.120.1.2
hmStatusWlanMngmtScanResultsEntryApName OBJECT-TYPE
    SYNTAX     DisplayString (SIZE(0..16))
    MAX-ACCESS read-only
    STATUS     current
    DESCRIPTION
            "-- empty --"
    ::= { hmStatusWlanMngmtScanResultsEntry 2 }

-- {COLUMN} 1.3.6.1.4.1.248.32.18.1.73.120.1.3
hmStatusWlanMngmtScanResultsEntryIpAddress OBJECT-TYPE
    SYNTAX     IpAddress
    MAX-ACCESS read-only
    STATUS     current
    DESCRIPTION
            "-- empty --"
    ::= { hmStatusWlanMngmtScanResultsEntry 3 }

-- {COLUMN} 1.3.6.1.4.1.248.32.18.1.73.120.1.4
hmStatusWlanMngmtScanResultsEntryApLanMac OBJECT-TYPE
    SYNTAX     MacAddress
    MAX-ACCESS read-only
    STATUS     current
    DESCRIPTION
            "-- empty --"
    ::= { hmStatusWlanMngmtScanResultsEntry 4 }

-- {COLUMN} 1.3.6.1.4.1.248.32.18.1.73.120.1.5
hmStatusWlanMngmtScanResultsEntryInterface OBJECT-TYPE
    SYNTAX     INTEGER {
                  eWlan1 (0),
                  eWlan2 (1),
                  eWlan3 (2),
                  eWlan4 (3)
            }
    MAX-ACCESS read-only
    STATUS     current
    DESCRIPTION
            "-- empty --"
    ::= { hmStatusWlanMngmtScanResultsEntry 5 }

-- {COLUMN} 1.3.6.1.4.1.248.32.18.1.73.120.1.6
hmStatusWlanMngmtScanResultsEntryNetworkName OBJECT-TYPE
    SYNTAX     DisplayString (SIZE(0..31))
    MAX-ACCESS read-only
    STATUS     current
    DESCRIPTION
            "-- empty --"
    ::= { hmStatusWlanMngmtScanResultsEntry 6 }

-- {COLUMN} 1.3.6.1.4.1.248.32.18.1.73.120.1.7
hmStatusWlanMngmtScanResultsEntryEncryption OBJECT-TYPE
    SYNTAX     INTEGER {
                  eNone (0),
                  eWep (1),
                  eTkip (2),
                  eAes (3),
                  eAesPlusTkip (4)
            }
    MAX-ACCESS read-only
    STATUS     current
    DESCRIPTION
            "-- empty --"
    ::= { hmStatusWlanMngmtScanResultsEntry 7 }

-- {COLUMN} 1.3.6.1.4.1.248.32.18.1.73.120.1.8
hmStatusWlanMngmtScanResultsEntryRadioBand OBJECT-TYPE
    SYNTAX     INTEGER {
                  e24ghz5ghz (0),
                  e24ghz (1),
                  e5ghz (2)
            }
    MAX-ACCESS read-only
    STATUS     current
    DESCRIPTION
            "-- empty --"
    ::= { hmStatusWlanMngmtScanResultsEntry 8 }

-- {COLUMN} 1.3.6.1.4.1.248.32.18.1.73.120.1.9
hmStatusWlanMngmtScanResultsEntryRadioChannel OBJECT-TYPE
    SYNTAX     Integer32 (0..255)
    MAX-ACCESS read-only
    STATUS     current
    DESCRIPTION
            "-- empty --"
    ::= { hmStatusWlanMngmtScanResultsEntry 9 }

-- {COLUMN} 1.3.6.1.4.1.248.32.18.1.73.120.1.10
hmStatusWlanMngmtScanResultsEntry108mbpsMode OBJECT-TYPE
    SYNTAX     Integer32 (0..255)
    MAX-ACCESS read-only
    STATUS     current
    DESCRIPTION
            "-- empty --"
    ::= { hmStatusWlanMngmtScanResultsEntry 10 }

-- {COLUMN} 1.3.6.1.4.1.248.32.18.1.73.120.1.11
hmStatusWlanMngmtScanResultsEntryPhySignal OBJECT-TYPE
    SYNTAX     Integer32 (-32768..32767)
    MAX-ACCESS read-only
    STATUS     current
    DESCRIPTION
            "-- empty --"
    ::= { hmStatusWlanMngmtScanResultsEntry 11 }

-- {COLUMN} 1.3.6.1.4.1.248.32.18.1.73.120.1.12
hmStatusWlanMngmtScanResultsEntryNoiseLevel OBJECT-TYPE
    SYNTAX     Integer32 (-128..127)
    MAX-ACCESS read-only
    STATUS     current
    DESCRIPTION
            "-- empty --"
    ::= { hmStatusWlanMngmtScanResultsEntry 12 }

-- {COLUMN} 1.3.6.1.4.1.248.32.18.1.73.120.1.13
hmStatusWlanMngmtScanResultsEntryIdentification OBJECT-TYPE
    SYNTAX     DisplayString (SIZE(0..24))
    MAX-ACCESS read-only
    STATUS     current
    DESCRIPTION
            "-- empty --"
    ::= { hmStatusWlanMngmtScanResultsEntry 13 }

-- {COLUMN} 1.3.6.1.4.1.248.32.18.1.73.120.1.14
hmStatusWlanMngmtScanResultsEntryAge OBJECT-TYPE
    SYNTAX     Integer32 (0..2147483647)
    MAX-ACCESS read-only
    STATUS     current
    DESCRIPTION
            "-- empty --"
    ::= { hmStatusWlanMngmtScanResultsEntry 14 }

-- {TABLE} 1.3.6.1.4.1.248.32.18.1.73.121
hmStatusWlanMngmtSeenClientsTable OBJECT-TYPE
    SYNTAX     SEQUENCE OF HmStatusWlanMngmtSeenClientsEntry
    MAX-ACCESS not-accessible
    STATUS     current
    DESCRIPTION
            "-- empty --"
    ::= { hmStatusWlanMngmt 121 }

-- {ROW} 1.3.6.1.4.1.248.32.18.1.73.121.1
hmStatusWlanMngmtSeenClientsEntry OBJECT-TYPE
    SYNTAX     HmStatusWlanMngmtSeenClientsEntry
    MAX-ACCESS not-accessible
    STATUS     current
    DESCRIPTION
            ""
    INDEX {
            hmStatusWlanMngmtSeenClientsEntryClientMac,
            hmStatusWlanMngmtSeenClientsEntryApLanMac
          }
    ::= { hmStatusWlanMngmtSeenClientsTable 1 }

HmStatusWlanMngmtSeenClientsEntry ::= SEQUENCE {
            hmStatusWlanMngmtSeenClientsEntryClientMac MacAddress,
            hmStatusWlanMngmtSeenClientsEntryApName DisplayString,
            hmStatusWlanMngmtSeenClientsEntryIpAddress IpAddress,
            hmStatusWlanMngmtSeenClientsEntryApLanMac MacAddress,
            hmStatusWlanMngmtSeenClientsEntryInterface INTEGER,
            hmStatusWlanMngmtSeenClientsEntryRxPhySignal Integer32,
            hmStatusWlanMngmtSeenClientsEntryAge Integer32,
            hmStatusWlanMngmtSeenClientsEntryNetworkName DisplayString
    }

-- {COLUMN} 1.3.6.1.4.1.248.32.18.1.73.121.1.1
hmStatusWlanMngmtSeenClientsEntryClientMac OBJECT-TYPE
    SYNTAX     MacAddress
    MAX-ACCESS read-only
    STATUS     current
    DESCRIPTION
            "-- empty --"
    ::= { hmStatusWlanMngmtSeenClientsEntry 1 }

-- {COLUMN} 1.3.6.1.4.1.248.32.18.1.73.121.1.2
hmStatusWlanMngmtSeenClientsEntryApName OBJECT-TYPE
    SYNTAX     DisplayString (SIZE(0..16))
    MAX-ACCESS read-only
    STATUS     current
    DESCRIPTION
            "-- empty --"
    ::= { hmStatusWlanMngmtSeenClientsEntry 2 }

-- {COLUMN} 1.3.6.1.4.1.248.32.18.1.73.121.1.3
hmStatusWlanMngmtSeenClientsEntryIpAddress OBJECT-TYPE
    SYNTAX     IpAddress
    MAX-ACCESS read-only
    STATUS     current
    DESCRIPTION
            "-- empty --"
    ::= { hmStatusWlanMngmtSeenClientsEntry 3 }

-- {COLUMN} 1.3.6.1.4.1.248.32.18.1.73.121.1.4
hmStatusWlanMngmtSeenClientsEntryApLanMac OBJECT-TYPE
    SYNTAX     MacAddress
    MAX-ACCESS read-only
    STATUS     current
    DESCRIPTION
            "-- empty --"
    ::= { hmStatusWlanMngmtSeenClientsEntry 4 }

-- {COLUMN} 1.3.6.1.4.1.248.32.18.1.73.121.1.5
hmStatusWlanMngmtSeenClientsEntryInterface OBJECT-TYPE
    SYNTAX     INTEGER {
                  eWlan1 (0),
                  eWlan2 (1),
                  eWlan3 (2),
                  eWlan4 (3)
            }
    MAX-ACCESS read-only
    STATUS     current
    DESCRIPTION
            "-- empty --"
    ::= { hmStatusWlanMngmtSeenClientsEntry 5 }

-- {COLUMN} 1.3.6.1.4.1.248.32.18.1.73.121.1.6
hmStatusWlanMngmtSeenClientsEntryRxPhySignal OBJECT-TYPE
    SYNTAX     Integer32 (0..65535)
    MAX-ACCESS read-only
    STATUS     current
    DESCRIPTION
            "-- empty --"
    ::= { hmStatusWlanMngmtSeenClientsEntry 6 }

-- {COLUMN} 1.3.6.1.4.1.248.32.18.1.73.121.1.7
hmStatusWlanMngmtSeenClientsEntryAge OBJECT-TYPE
    SYNTAX     Integer32 (0..2147483647)
    MAX-ACCESS read-only
    STATUS     current
    DESCRIPTION
            "-- empty --"
    ::= { hmStatusWlanMngmtSeenClientsEntry 7 }

-- {COLUMN} 1.3.6.1.4.1.248.32.18.1.73.121.1.8
hmStatusWlanMngmtSeenClientsEntryNetworkName OBJECT-TYPE
    SYNTAX     DisplayString (SIZE(0..31))
    MAX-ACCESS read-only
    STATUS     current
    DESCRIPTION
            "-- empty --"
    ::= { hmStatusWlanMngmtSeenClientsEntry 8 }

-- {TABLE} 1.3.6.1.4.1.248.32.18.1.73.122
hmStatusWlanMngmtPmkCachingTable OBJECT-TYPE
    SYNTAX     SEQUENCE OF HmStatusWlanMngmtPmkCachingEntry
    MAX-ACCESS not-accessible
    STATUS     current
    DESCRIPTION
            "-- empty --"
    ::= { hmStatusWlanMngmt 122 }

-- {ROW} 1.3.6.1.4.1.248.32.18.1.73.122.1
hmStatusWlanMngmtPmkCachingEntry OBJECT-TYPE
    SYNTAX     HmStatusWlanMngmtPmkCachingEntry
    MAX-ACCESS not-accessible
    STATUS     current
    DESCRIPTION
            ""
    INDEX {
            hmStatusWlanMngmtPmkCachingEntrySupplicant
          }
    ::= { hmStatusWlanMngmtPmkCachingTable 1 }

HmStatusWlanMngmtPmkCachingEntry ::= SEQUENCE {
            hmStatusWlanMngmtPmkCachingEntrySupplicant MacAddress,
            hmStatusWlanMngmtPmkCachingEntrySsid DisplayString,
            hmStatusWlanMngmtPmkCachingEntryPmkValue OCTET STRING,
            hmStatusWlanMngmtPmkCachingEntryPmkLength Integer32,
            hmStatusWlanMngmtPmkCachingEntryLifetime Integer32,
            hmStatusWlanMngmtPmkCachingEntryVlanId Integer32,
            hmStatusWlanMngmtPmkCachingEntryUserName DisplayString,
            hmStatusWlanMngmtPmkCachingEntryStoreTime Integer32,
            hmStatusWlanMngmtPmkCachingEntryHeapNode Integer32
    }

-- {COLUMN} 1.3.6.1.4.1.248.32.18.1.73.122.1.1
hmStatusWlanMngmtPmkCachingEntrySupplicant OBJECT-TYPE
    SYNTAX     MacAddress
    MAX-ACCESS read-only
    STATUS     current
    DESCRIPTION
            "-- empty --"
    ::= { hmStatusWlanMngmtPmkCachingEntry 1 }

-- {COLUMN} 1.3.6.1.4.1.248.32.18.1.73.122.1.3
hmStatusWlanMngmtPmkCachingEntrySsid OBJECT-TYPE
    SYNTAX     DisplayString (SIZE(0..255))
    MAX-ACCESS read-only
    STATUS     current
    DESCRIPTION
            "-- empty --"
    ::= { hmStatusWlanMngmtPmkCachingEntry 3 }

-- {COLUMN} 1.3.6.1.4.1.248.32.18.1.73.122.1.4
hmStatusWlanMngmtPmkCachingEntryPmkValue OBJECT-TYPE
    SYNTAX     OCTET STRING
    MAX-ACCESS read-only
    STATUS     current
    DESCRIPTION
            "-- empty --"
    ::= { hmStatusWlanMngmtPmkCachingEntry 4 }

-- {COLUMN} 1.3.6.1.4.1.248.32.18.1.73.122.1.5
hmStatusWlanMngmtPmkCachingEntryPmkLength OBJECT-TYPE
    SYNTAX     Integer32 (0..255)
    MAX-ACCESS read-only
    STATUS     current
    DESCRIPTION
            "-- empty --"
    ::= { hmStatusWlanMngmtPmkCachingEntry 5 }

-- {COLUMN} 1.3.6.1.4.1.248.32.18.1.73.122.1.6
hmStatusWlanMngmtPmkCachingEntryLifetime OBJECT-TYPE
    SYNTAX     Integer32 (0..2147483647)
    MAX-ACCESS read-only
    STATUS     current
    DESCRIPTION
            "-- empty --"
    ::= { hmStatusWlanMngmtPmkCachingEntry 6 }

-- {COLUMN} 1.3.6.1.4.1.248.32.18.1.73.122.1.7
hmStatusWlanMngmtPmkCachingEntryVlanId OBJECT-TYPE
    SYNTAX     Integer32 (0..65535)
    MAX-ACCESS read-only
    STATUS     current
    DESCRIPTION
            "-- empty --"
    ::= { hmStatusWlanMngmtPmkCachingEntry 7 }

-- {COLUMN} 1.3.6.1.4.1.248.32.18.1.73.122.1.8
hmStatusWlanMngmtPmkCachingEntryUserName OBJECT-TYPE
    SYNTAX     DisplayString (SIZE(0..255))
    MAX-ACCESS read-only
    STATUS     current
    DESCRIPTION
            "-- empty --"
    ::= { hmStatusWlanMngmtPmkCachingEntry 8 }

-- {COLUMN} 1.3.6.1.4.1.248.32.18.1.73.122.1.9
hmStatusWlanMngmtPmkCachingEntryStoreTime OBJECT-TYPE
    SYNTAX     Integer32 (0..2147483647)
    MAX-ACCESS read-only
    STATUS     current
    DESCRIPTION
            "-- empty --"
    ::= { hmStatusWlanMngmtPmkCachingEntry 9 }

-- {COLUMN} 1.3.6.1.4.1.248.32.18.1.73.122.1.10
hmStatusWlanMngmtPmkCachingEntryHeapNode OBJECT-TYPE
    SYNTAX     Integer32 (0..2147483647)
    MAX-ACCESS read-only
    STATUS     current
    DESCRIPTION
            "-- empty --"
    ::= { hmStatusWlanMngmtPmkCachingEntry 10 }

-- {NODE} 1.3.6.1.4.1.248.32.18.1.73.123
hmStatusWlanMngmtClSte OBJECT IDENTIFIER ::= { hmStatusWlanMngmt 123 }

-- {SCALAR} 1.3.6.1.4.1.248.32.18.1.73.123.1
hmStatusWlanMngmtClSteOperating OBJECT-TYPE
    SYNTAX     INTEGER {
                  eNo (0),
                  eYes (1)
            }
    MAX-ACCESS read-only
    STATUS     current
    DESCRIPTION
            "-- empty --"
    ::= { hmStatusWlanMngmtClSte 1 }

-- {SCALAR} 1.3.6.1.4.1.248.32.18.1.73.123.2
hmStatusWlanMngmtClSteResetStatistics OBJECT-TYPE
    SYNTAX     DisplayString
    MAX-ACCESS read-write
    STATUS     current
    DESCRIPTION
            "-- empty --"
    ::= { hmStatusWlanMngmtClSte 2 }

-- {SCALAR} 1.3.6.1.4.1.248.32.18.1.73.123.3
hmStatusWlanMngmtClSteRateOfOptimizedConnections OBJECT-TYPE
    SYNTAX     Integer32 (0..2147483647)
    MAX-ACCESS read-only
    STATUS     current
    DESCRIPTION
            "-- empty --"
    ::= { hmStatusWlanMngmtClSte 3 }

-- {TABLE} 1.3.6.1.4.1.248.32.18.1.73.123.4
hmStatusWlanMngmtClSteClientInfoTable OBJECT-TYPE
    SYNTAX     SEQUENCE OF HmStatusWlanMngmtClSteClientInfoEntry
    MAX-ACCESS not-accessible
    STATUS     current
    DESCRIPTION
            "-- empty --"
    ::= { hmStatusWlanMngmtClSte 4 }

-- {ROW} 1.3.6.1.4.1.248.32.18.1.73.123.4.1
hmStatusWlanMngmtClSteClientInfoEntry OBJECT-TYPE
    SYNTAX     HmStatusWlanMngmtClSteClientInfoEntry
    MAX-ACCESS not-accessible
    STATUS     current
    DESCRIPTION
            ""
    INDEX {
            hmStatusWlanMngmtClSteClientInfoEntryClientMac
          }
    ::= { hmStatusWlanMngmtClSteClientInfoTable 1 }

HmStatusWlanMngmtClSteClientInfoEntry ::= SEQUENCE {
            hmStatusWlanMngmtClSteClientInfoEntryClientMac MacAddress,
            hmStatusWlanMngmtClSteClientInfoEntryApsGotOk Integer32,
            hmStatusWlanMngmtClSteClientInfoEntryState INTEGER,
            hmStatusWlanMngmtClSteClientInfoEntryOkCount Integer32,
            hmStatusWlanMngmtClSteClientInfoEntryNokCount Integer32,
            hmStatusWlanMngmtClSteClientInfoEntryAssociationTime Integer32,
            hmStatusWlanMngmtClSteClientInfoEntryRoamingTime Integer32
    }

-- {COLUMN} 1.3.6.1.4.1.248.32.18.1.73.123.4.1.1
hmStatusWlanMngmtClSteClientInfoEntryClientMac OBJECT-TYPE
    SYNTAX     MacAddress
    MAX-ACCESS read-only
    STATUS     current
    DESCRIPTION
            "-- empty --"
    ::= { hmStatusWlanMngmtClSteClientInfoEntry 1 }

-- {COLUMN} 1.3.6.1.4.1.248.32.18.1.73.123.4.1.4
hmStatusWlanMngmtClSteClientInfoEntryApsGotOk OBJECT-TYPE
    SYNTAX     Integer32 (0..2147483647)
    MAX-ACCESS read-only
    STATUS     current
    DESCRIPTION
            "-- empty --"
    ::= { hmStatusWlanMngmtClSteClientInfoEntry 4 }

-- {COLUMN} 1.3.6.1.4.1.248.32.18.1.73.123.4.1.5
hmStatusWlanMngmtClSteClientInfoEntryState OBJECT-TYPE
    SYNTAX     INTEGER {
                  ePending (0),
                  eClientSteeringOk (1),
                  eUnsteerable (2),
                  eNoInfo (3)
            }
    MAX-ACCESS read-only
    STATUS     current
    DESCRIPTION
            "-- empty --"
    ::= { hmStatusWlanMngmtClSteClientInfoEntry 5 }

-- {COLUMN} 1.3.6.1.4.1.248.32.18.1.73.123.4.1.6
hmStatusWlanMngmtClSteClientInfoEntryOkCount OBJECT-TYPE
    SYNTAX     Integer32 (0..2147483647)
    MAX-ACCESS read-only
    STATUS     current
    DESCRIPTION
            "-- empty --"
    ::= { hmStatusWlanMngmtClSteClientInfoEntry 6 }

-- {COLUMN} 1.3.6.1.4.1.248.32.18.1.73.123.4.1.7
hmStatusWlanMngmtClSteClientInfoEntryNokCount OBJECT-TYPE
    SYNTAX     Integer32 (0..2147483647)
    MAX-ACCESS read-only
    STATUS     current
    DESCRIPTION
            "-- empty --"
    ::= { hmStatusWlanMngmtClSteClientInfoEntry 7 }

-- {COLUMN} 1.3.6.1.4.1.248.32.18.1.73.123.4.1.8
hmStatusWlanMngmtClSteClientInfoEntryAssociationTime OBJECT-TYPE
    SYNTAX     Integer32 (0..2147483647)
    MAX-ACCESS read-only
    STATUS     current
    DESCRIPTION
            "-- empty --"
    ::= { hmStatusWlanMngmtClSteClientInfoEntry 8 }

-- {COLUMN} 1.3.6.1.4.1.248.32.18.1.73.123.4.1.9
hmStatusWlanMngmtClSteClientInfoEntryRoamingTime OBJECT-TYPE
    SYNTAX     Integer32 (0..2147483647)
    MAX-ACCESS read-only
    STATUS     current
    DESCRIPTION
            "-- empty --"
    ::= { hmStatusWlanMngmtClSteClientInfoEntry 9 }

-- {NODE} 1.3.6.1.4.1.248.32.18.1.73.123.7
hmStatusWlanMngmtClSteAvgStatAll OBJECT IDENTIFIER ::= { hmStatusWlanMngmtClSte 7 }

-- {SCALAR} 1.3.6.1.4.1.248.32.18.1.73.123.7.1
hmStatusWlanMngmtClSteAvgStatAllMedianAssociationDelay OBJECT-TYPE
    SYNTAX     Integer32 (0..2147483647)
    MAX-ACCESS read-only
    STATUS     current
    DESCRIPTION
            "-- empty --"
    ::= { hmStatusWlanMngmtClSteAvgStatAll 1 }

-- {SCALAR} 1.3.6.1.4.1.248.32.18.1.73.123.7.2
hmStatusWlanMngmtClSteAvgStatAllMedianRoamingDelay OBJECT-TYPE
    SYNTAX     Integer32 (0..2147483647)
    MAX-ACCESS read-only
    STATUS     current
    DESCRIPTION
            "-- empty --"
    ::= { hmStatusWlanMngmtClSteAvgStatAll 2 }

-- {SCALAR} 1.3.6.1.4.1.248.32.18.1.73.123.7.3
hmStatusWlanMngmtClSteAvgStatAllMinAssociationDelay OBJECT-TYPE
    SYNTAX     Integer32 (0..2147483647)
    MAX-ACCESS read-only
    STATUS     current
    DESCRIPTION
            "-- empty --"
    ::= { hmStatusWlanMngmtClSteAvgStatAll 3 }

-- {SCALAR} 1.3.6.1.4.1.248.32.18.1.73.123.7.4
hmStatusWlanMngmtClSteAvgStatAllMaxAssociationDelay OBJECT-TYPE
    SYNTAX     Integer32 (0..2147483647)
    MAX-ACCESS read-only
    STATUS     current
    DESCRIPTION
            "-- empty --"
    ::= { hmStatusWlanMngmtClSteAvgStatAll 4 }

-- {SCALAR} 1.3.6.1.4.1.248.32.18.1.73.123.7.5
hmStatusWlanMngmtClSteAvgStatAllNumberOfForcedRoamingEvents OBJECT-TYPE
    SYNTAX     Integer32 (0..2147483647)
    MAX-ACCESS read-only
    STATUS     current
    DESCRIPTION
            "-- empty --"
    ::= { hmStatusWlanMngmtClSteAvgStatAll 5 }

-- {SCALAR} 1.3.6.1.4.1.248.32.18.1.73.123.7.6
hmStatusWlanMngmtClSteAvgStatAllNumberOfUnsteerableAssociations OBJECT-TYPE
    SYNTAX     Integer32 (0..2147483647)
    MAX-ACCESS read-only
    STATUS     current
    DESCRIPTION
            "-- empty --"
    ::= { hmStatusWlanMngmtClSteAvgStatAll 6 }

-- {SCALAR} 1.3.6.1.4.1.248.32.18.1.73.123.7.7
hmStatusWlanMngmtClSteAvgStatAllAverageSignalStrength OBJECT-TYPE
    SYNTAX     Integer32 (0..2147483647)
    MAX-ACCESS read-only
    STATUS     current
    DESCRIPTION
            "-- empty --"
    ::= { hmStatusWlanMngmtClSteAvgStatAll 7 }

-- {SCALAR} 1.3.6.1.4.1.248.32.18.1.73.123.7.10
hmStatusWlanMngmtClSteAvgStatAllMinRoamingDelay OBJECT-TYPE
    SYNTAX     Integer32 (0..2147483647)
    MAX-ACCESS read-only
    STATUS     current
    DESCRIPTION
            "-- empty --"
    ::= { hmStatusWlanMngmtClSteAvgStatAll 10 }

-- {SCALAR} 1.3.6.1.4.1.248.32.18.1.73.123.7.11
hmStatusWlanMngmtClSteAvgStatAllMaxRoamingDelay OBJECT-TYPE
    SYNTAX     Integer32 (0..2147483647)
    MAX-ACCESS read-only
    STATUS     current
    DESCRIPTION
            "-- empty --"
    ::= { hmStatusWlanMngmtClSteAvgStatAll 11 }

-- {NODE} 1.3.6.1.4.1.248.32.18.1.73.123.8
hmStatusWlanMngmtClSteAvgStatFiv OBJECT IDENTIFIER ::= { hmStatusWlanMngmtClSte 8 }

-- {SCALAR} 1.3.6.1.4.1.248.32.18.1.73.123.8.1
hmStatusWlanMngmtClSteAvgStatFivMedianAssociationDelay OBJECT-TYPE
    SYNTAX     Integer32 (0..2147483647)
    MAX-ACCESS read-only
    STATUS     current
    DESCRIPTION
            "-- empty --"
    ::= { hmStatusWlanMngmtClSteAvgStatFiv 1 }

-- {SCALAR} 1.3.6.1.4.1.248.32.18.1.73.123.8.2
hmStatusWlanMngmtClSteAvgStatFivMedianRoamingDelay OBJECT-TYPE
    SYNTAX     Integer32 (0..2147483647)
    MAX-ACCESS read-only
    STATUS     current
    DESCRIPTION
            "-- empty --"
    ::= { hmStatusWlanMngmtClSteAvgStatFiv 2 }

-- {SCALAR} 1.3.6.1.4.1.248.32.18.1.73.123.8.3
hmStatusWlanMngmtClSteAvgStatFivMinAssociationDelay OBJECT-TYPE
    SYNTAX     Integer32 (0..2147483647)
    MAX-ACCESS read-only
    STATUS     current
    DESCRIPTION
            "-- empty --"
    ::= { hmStatusWlanMngmtClSteAvgStatFiv 3 }

-- {SCALAR} 1.3.6.1.4.1.248.32.18.1.73.123.8.4
hmStatusWlanMngmtClSteAvgStatFivMaxAssociationDelay OBJECT-TYPE
    SYNTAX     Integer32 (0..2147483647)
    MAX-ACCESS read-only
    STATUS     current
    DESCRIPTION
            "-- empty --"
    ::= { hmStatusWlanMngmtClSteAvgStatFiv 4 }

-- {SCALAR} 1.3.6.1.4.1.248.32.18.1.73.123.8.5
hmStatusWlanMngmtClSteAvgStatFivNumberOfForcedRoamingEvents OBJECT-TYPE
    SYNTAX     Integer32 (0..2147483647)
    MAX-ACCESS read-only
    STATUS     current
    DESCRIPTION
            "-- empty --"
    ::= { hmStatusWlanMngmtClSteAvgStatFiv 5 }

-- {SCALAR} 1.3.6.1.4.1.248.32.18.1.73.123.8.6
hmStatusWlanMngmtClSteAvgStatFivNumberOfUnsteerableAssociations OBJECT-TYPE
    SYNTAX     Integer32 (0..2147483647)
    MAX-ACCESS read-only
    STATUS     current
    DESCRIPTION
            "-- empty --"
    ::= { hmStatusWlanMngmtClSteAvgStatFiv 6 }

-- {SCALAR} 1.3.6.1.4.1.248.32.18.1.73.123.8.7
hmStatusWlanMngmtClSteAvgStatFivAverageSignalStrength OBJECT-TYPE
    SYNTAX     Integer32 (0..2147483647)
    MAX-ACCESS read-only
    STATUS     current
    DESCRIPTION
            "-- empty --"
    ::= { hmStatusWlanMngmtClSteAvgStatFiv 7 }

-- {SCALAR} 1.3.6.1.4.1.248.32.18.1.73.123.8.10
hmStatusWlanMngmtClSteAvgStatFivMinRoamingDelay OBJECT-TYPE
    SYNTAX     Integer32 (0..2147483647)
    MAX-ACCESS read-only
    STATUS     current
    DESCRIPTION
            "-- empty --"
    ::= { hmStatusWlanMngmtClSteAvgStatFiv 10 }

-- {SCALAR} 1.3.6.1.4.1.248.32.18.1.73.123.8.11
hmStatusWlanMngmtClSteAvgStatFivMaxRoamingDelay OBJECT-TYPE
    SYNTAX     Integer32 (0..2147483647)
    MAX-ACCESS read-only
    STATUS     current
    DESCRIPTION
            "-- empty --"
    ::= { hmStatusWlanMngmtClSteAvgStatFiv 11 }

-- {SCALAR} 1.3.6.1.4.1.248.32.18.1.73.123.9
hmStatusWlanMngmtClSteAcquireStatisticalData OBJECT-TYPE
    SYNTAX     INTEGER {
                  eNo (0),
                  eYes (1)
            }
    MAX-ACCESS read-only
    STATUS     current
    DESCRIPTION
            "-- empty --"
    ::= { hmStatusWlanMngmtClSte 9 }

-- {NODE} 1.3.6.1.4.1.248.32.18.1.73.248
hmStatusWlanMngmtWIds OBJECT IDENTIFIER ::= { hmStatusWlanMngmt 248 }

-- {TABLE} 1.3.6.1.4.1.248.32.18.1.73.248.1
hmStatusWlanMngmtWIdsEventTableTable OBJECT-TYPE
    SYNTAX     SEQUENCE OF HmStatusWlanMngmtWIdsEventTableEntry
    MAX-ACCESS not-accessible
    STATUS     current
    DESCRIPTION
            "-- empty --"
    ::= { hmStatusWlanMngmtWIds 1 }

-- {ROW} 1.3.6.1.4.1.248.32.18.1.73.248.1.1
hmStatusWlanMngmtWIdsEventTableEntry OBJECT-TYPE
    SYNTAX     HmStatusWlanMngmtWIdsEventTableEntry
    MAX-ACCESS not-accessible
    STATUS     current
    DESCRIPTION
            ""
    INDEX {
            hmStatusWlanMngmtWIdsEventTableEntryMacAddress,
            hmStatusWlanMngmtWIdsEventTableEntryEventType,
            hmStatusWlanMngmtWIdsEventTableEntryId
          }
    ::= { hmStatusWlanMngmtWIdsEventTableTable 1 }

HmStatusWlanMngmtWIdsEventTableEntry ::= SEQUENCE {
            hmStatusWlanMngmtWIdsEventTableEntryMacAddress MacAddress,
            hmStatusWlanMngmtWIdsEventTableEntryEventType INTEGER,
            hmStatusWlanMngmtWIdsEventTableEntryId Integer32,
            hmStatusWlanMngmtWIdsEventTableEntryEventTime DisplayString,
            hmStatusWlanMngmtWIdsEventTableEntryEventRate Integer32,
            hmStatusWlanMngmtWIdsEventTableEntryInterface INTEGER,
            hmStatusWlanMngmtWIdsEventTableEntryAttackerMac MacAddress
    }

-- {COLUMN} 1.3.6.1.4.1.248.32.18.1.73.248.1.1.1
hmStatusWlanMngmtWIdsEventTableEntryMacAddress OBJECT-TYPE
    SYNTAX     MacAddress
    MAX-ACCESS read-only
    STATUS     current
    DESCRIPTION
            "-- empty --"
    ::= { hmStatusWlanMngmtWIdsEventTableEntry 1 }

-- {COLUMN} 1.3.6.1.4.1.248.32.18.1.73.248.1.1.2
hmStatusWlanMngmtWIdsEventTableEntryEventType OBJECT-TYPE
    SYNTAX     INTEGER {
                  eEapolstart (1),
                  eProbebroad (2),
                  eDeauthenticatebroad (3),
                  eDeauthenticate (4),
                  eAssociatereq (5),
                  eReassociatereq (6),
                  eAuthenticate (7),
                  eDisassociate (8),
                  eGenericerror (9),
                  eBlockackAttack (10),
                  eDelba (11),
                  eNulldatadosattack (12),
                  eNulldatapsAttack (13),
                  ePsPollAttack (14),
                  eSmpsAttack (15),
                  eDisassociatebroad (17),
                  ePrematureeapolsuccess (18),
                  ePrematureeapolfailure (19)
            }
    MAX-ACCESS read-only
    STATUS     current
    DESCRIPTION
            "-- empty --"
    ::= { hmStatusWlanMngmtWIdsEventTableEntry 2 }

-- {COLUMN} 1.3.6.1.4.1.248.32.18.1.73.248.1.1.3
hmStatusWlanMngmtWIdsEventTableEntryId OBJECT-TYPE
    SYNTAX     Integer32 (0..2147483647)
    MAX-ACCESS read-only
    STATUS     current
    DESCRIPTION
            "-- empty --"
    ::= { hmStatusWlanMngmtWIdsEventTableEntry 3 }

-- {COLUMN} 1.3.6.1.4.1.248.32.18.1.73.248.1.1.4
hmStatusWlanMngmtWIdsEventTableEntryEventTime OBJECT-TYPE
    SYNTAX     DisplayString (SIZE(0..255))
    MAX-ACCESS read-only
    STATUS     current
    DESCRIPTION
            "-- empty --"
    ::= { hmStatusWlanMngmtWIdsEventTableEntry 4 }

-- {COLUMN} 1.3.6.1.4.1.248.32.18.1.73.248.1.1.5
hmStatusWlanMngmtWIdsEventTableEntryEventRate OBJECT-TYPE
    SYNTAX     Integer32 (0..2147483647)
    MAX-ACCESS read-only
    STATUS     current
    DESCRIPTION
            "-- empty --"
    ::= { hmStatusWlanMngmtWIdsEventTableEntry 5 }

-- {COLUMN} 1.3.6.1.4.1.248.32.18.1.73.248.1.1.6
hmStatusWlanMngmtWIdsEventTableEntryInterface OBJECT-TYPE
    SYNTAX     INTEGER {
                  eWlan1 (0),
                  eWlan2 (1),
                  eAny (2)
            }
    MAX-ACCESS read-only
    STATUS     current
    DESCRIPTION
            "-- empty --"
    ::= { hmStatusWlanMngmtWIdsEventTableEntry 6 }

-- {COLUMN} 1.3.6.1.4.1.248.32.18.1.73.248.1.1.7
hmStatusWlanMngmtWIdsEventTableEntryAttackerMac OBJECT-TYPE
    SYNTAX     MacAddress
    MAX-ACCESS read-only
    STATUS     current
    DESCRIPTION
            "-- empty --"
    ::= { hmStatusWlanMngmtWIdsEventTableEntry 7 }

-- {TABLE} 1.3.6.1.4.1.248.32.18.1.73.248.2
hmStatusWlanMngmtWIdsIntruderTableTable OBJECT-TYPE
    SYNTAX     SEQUENCE OF HmStatusWlanMngmtWIdsIntruderTableEntry
    MAX-ACCESS not-accessible
    STATUS     current
    DESCRIPTION
            "-- empty --"
    ::= { hmStatusWlanMngmtWIds 2 }

-- {ROW} 1.3.6.1.4.1.248.32.18.1.73.248.2.1
hmStatusWlanMngmtWIdsIntruderTableEntry OBJECT-TYPE
    SYNTAX     HmStatusWlanMngmtWIdsIntruderTableEntry
    MAX-ACCESS not-accessible
    STATUS     current
    DESCRIPTION
            ""
    INDEX {
            hmStatusWlanMngmtWIdsIntruderTableEntryMacAddress,
            hmStatusWlanMngmtWIdsIntruderTableEntryAttackType
          }
    ::= { hmStatusWlanMngmtWIdsIntruderTableTable 1 }

HmStatusWlanMngmtWIdsIntruderTableEntry ::= SEQUENCE {
            hmStatusWlanMngmtWIdsIntruderTableEntryMacAddress MacAddress,
            hmStatusWlanMngmtWIdsIntruderTableEntryAttackType INTEGER,
            hmStatusWlanMngmtWIdsIntruderTableEntryActive INTEGER,
            hmStatusWlanMngmtWIdsIntruderTableEntryRssi Integer32,
            hmStatusWlanMngmtWIdsIntruderTableEntryAttackRate Integer32,
            hmStatusWlanMngmtWIdsIntruderTableEntryKnownClient INTEGER
    }

-- {COLUMN} 1.3.6.1.4.1.248.32.18.1.73.248.2.1.1
hmStatusWlanMngmtWIdsIntruderTableEntryMacAddress OBJECT-TYPE
    SYNTAX     MacAddress
    MAX-ACCESS read-only
    STATUS     current
    DESCRIPTION
            "-- empty --"
    ::= { hmStatusWlanMngmtWIdsIntruderTableEntry 1 }

-- {COLUMN} 1.3.6.1.4.1.248.32.18.1.73.248.2.1.2
hmStatusWlanMngmtWIdsIntruderTableEntryAttackType OBJECT-TYPE
    SYNTAX     INTEGER {
                  eEapolstart (1),
                  eProbebroad (2),
                  eDeauthenticatebroad (3),
                  eDeauthenticate (4),
                  eAssociatereq (5),
                  eReassociatereq (6),
                  eAuthenticate (7),
                  eDisassociate (8),
                  eBlockackAttack (10),
                  eDelba (11),
                  eNulldatadosattack (12),
                  eNulldatapsAttack (13),
                  ePsPollAttack (14),
                  eSmpsAttack (15),
                  eDisassociatebroad (17),
                  eGenericerror (20)
            }
    MAX-ACCESS read-only
    STATUS     current
    DESCRIPTION
            "-- empty --"
    ::= { hmStatusWlanMngmtWIdsIntruderTableEntry 2 }

-- {COLUMN} 1.3.6.1.4.1.248.32.18.1.73.248.2.1.3
hmStatusWlanMngmtWIdsIntruderTableEntryActive OBJECT-TYPE
    SYNTAX     INTEGER {
                  eNo (0),
                  eYes (1)
            }
    MAX-ACCESS read-only
    STATUS     current
    DESCRIPTION
            "-- empty --"
    ::= { hmStatusWlanMngmtWIdsIntruderTableEntry 3 }

-- {COLUMN} 1.3.6.1.4.1.248.32.18.1.73.248.2.1.4
hmStatusWlanMngmtWIdsIntruderTableEntryRssi OBJECT-TYPE
    SYNTAX     Integer32 (0..65535)
    MAX-ACCESS read-only
    STATUS     current
    DESCRIPTION
            "-- empty --"
    ::= { hmStatusWlanMngmtWIdsIntruderTableEntry 4 }

-- {COLUMN} 1.3.6.1.4.1.248.32.18.1.73.248.2.1.5
hmStatusWlanMngmtWIdsIntruderTableEntryAttackRate OBJECT-TYPE
    SYNTAX     Integer32 (0..2147483647)
    MAX-ACCESS read-only
    STATUS     current
    DESCRIPTION
            "-- empty --"
    ::= { hmStatusWlanMngmtWIdsIntruderTableEntry 5 }

-- {COLUMN} 1.3.6.1.4.1.248.32.18.1.73.248.2.1.6
hmStatusWlanMngmtWIdsIntruderTableEntryKnownClient OBJECT-TYPE
    SYNTAX     INTEGER {
                  eNo (0),
                  eYes (1)
            }
    MAX-ACCESS read-only
    STATUS     current
    DESCRIPTION
            "-- empty --"
    ::= { hmStatusWlanMngmtWIdsIntruderTableEntry 6 }

-- {TABLE} 1.3.6.1.4.1.248.32.18.1.73.248.3
hmStatusWlanMngmtWIdsIntruderLocationTable OBJECT-TYPE
    SYNTAX     SEQUENCE OF HmStatusWlanMngmtWIdsIntruderLocationEntry
    MAX-ACCESS not-accessible
    STATUS     current
    DESCRIPTION
            "-- empty --"
    ::= { hmStatusWlanMngmtWIds 3 }

-- {ROW} 1.3.6.1.4.1.248.32.18.1.73.248.3.1
hmStatusWlanMngmtWIdsIntruderLocationEntry OBJECT-TYPE
    SYNTAX     HmStatusWlanMngmtWIdsIntruderLocationEntry
    MAX-ACCESS not-accessible
    STATUS     current
    DESCRIPTION
            ""
    INDEX {
            hmStatusWlanMngmtWIdsIntruderLocationEntryIntruderMac
          }
    ::= { hmStatusWlanMngmtWIdsIntruderLocationTable 1 }

HmStatusWlanMngmtWIdsIntruderLocationEntry ::= SEQUENCE {
            hmStatusWlanMngmtWIdsIntruderLocationEntryIntruderMac MacAddress,
            hmStatusWlanMngmtWIdsIntruderLocationEntrySeenBy MacAddress,
            hmStatusWlanMngmtWIdsIntruderLocationEntryRssi Integer32
    }

-- {COLUMN} 1.3.6.1.4.1.248.32.18.1.73.248.3.1.1
hmStatusWlanMngmtWIdsIntruderLocationEntryIntruderMac OBJECT-TYPE
    SYNTAX     MacAddress
    MAX-ACCESS read-only
    STATUS     current
    DESCRIPTION
            "-- empty --"
    ::= { hmStatusWlanMngmtWIdsIntruderLocationEntry 1 }

-- {COLUMN} 1.3.6.1.4.1.248.32.18.1.73.248.3.1.2
hmStatusWlanMngmtWIdsIntruderLocationEntrySeenBy OBJECT-TYPE
    SYNTAX     MacAddress
    MAX-ACCESS read-only
    STATUS     current
    DESCRIPTION
            "-- empty --"
    ::= { hmStatusWlanMngmtWIdsIntruderLocationEntry 2 }

-- {COLUMN} 1.3.6.1.4.1.248.32.18.1.73.248.3.1.3
hmStatusWlanMngmtWIdsIntruderLocationEntryRssi OBJECT-TYPE
    SYNTAX     Integer32 (0..65535)
    MAX-ACCESS read-only
    STATUS     current
    DESCRIPTION
            "-- empty --"
    ::= { hmStatusWlanMngmtWIdsIntruderLocationEntry 3 }

-- {NODE} 1.3.6.1.4.1.248.32.18.1.77
hmStatusIpv6 OBJECT IDENTIFIER ::= { hmStatus 77 }

-- {TABLE} 1.3.6.1.4.1.248.32.18.1.77.1
hmStatusIpv6AddressesTable OBJECT-TYPE
    SYNTAX     SEQUENCE OF HmStatusIpv6AddressesEntry
    MAX-ACCESS not-accessible
    STATUS     current
    DESCRIPTION
            "-- empty --"
    ::= { hmStatusIpv6 1 }

-- {ROW} 1.3.6.1.4.1.248.32.18.1.77.1.1
hmStatusIpv6AddressesEntry OBJECT-TYPE
    SYNTAX     HmStatusIpv6AddressesEntry
    MAX-ACCESS not-accessible
    STATUS     current
    DESCRIPTION
            ""
    INDEX {
            hmStatusIpv6AddressesEntryInterfaceName,
            hmStatusIpv6AddressesEntryIpv6Address
          }
    ::= { hmStatusIpv6AddressesTable 1 }

HmStatusIpv6AddressesEntry ::= SEQUENCE {
            hmStatusIpv6AddressesEntryInterfaceName DisplayString,
            hmStatusIpv6AddressesEntryIpv6Address DisplayString,
            hmStatusIpv6AddressesEntryStatus DisplayString,
            hmStatusIpv6AddressesEntryProperties DisplayString,
            hmStatusIpv6AddressesEntryAddressType DisplayString,
            hmStatusIpv6AddressesEntryInterfaceType INTEGER
    }

-- {COLUMN} 1.3.6.1.4.1.248.32.18.1.77.1.1.1
hmStatusIpv6AddressesEntryInterfaceName OBJECT-TYPE
    SYNTAX     DisplayString (SIZE(0..16))
    MAX-ACCESS read-only
    STATUS     current
    DESCRIPTION
            "-- empty --"
    ::= { hmStatusIpv6AddressesEntry 1 }

-- {COLUMN} 1.3.6.1.4.1.248.32.18.1.77.1.1.2
hmStatusIpv6AddressesEntryIpv6Address OBJECT-TYPE
    SYNTAX     DisplayString (SIZE(0..39))
    MAX-ACCESS read-only
    STATUS     current
    DESCRIPTION
            "-- empty --"
    ::= { hmStatusIpv6AddressesEntry 2 }

-- {COLUMN} 1.3.6.1.4.1.248.32.18.1.77.1.1.3
hmStatusIpv6AddressesEntryStatus OBJECT-TYPE
    SYNTAX     DisplayString (SIZE(0..10))
    MAX-ACCESS read-only
    STATUS     current
    DESCRIPTION
            "-- empty --"
    ::= { hmStatusIpv6AddressesEntry 3 }

-- {COLUMN} 1.3.6.1.4.1.248.32.18.1.77.1.1.4
hmStatusIpv6AddressesEntryProperties OBJECT-TYPE
    SYNTAX     DisplayString (SIZE(0..57))
    MAX-ACCESS read-only
    STATUS     current
    DESCRIPTION
            "-- empty --"
    ::= { hmStatusIpv6AddressesEntry 4 }

-- {COLUMN} 1.3.6.1.4.1.248.32.18.1.77.1.1.5
hmStatusIpv6AddressesEntryAddressType OBJECT-TYPE
    SYNTAX     DisplayString (SIZE(0..26))
    MAX-ACCESS read-only
    STATUS     current
    DESCRIPTION
            "-- empty --"
    ::= { hmStatusIpv6AddressesEntry 5 }

-- {COLUMN} 1.3.6.1.4.1.248.32.18.1.77.1.1.6
hmStatusIpv6AddressesEntryInterfaceType OBJECT-TYPE
    SYNTAX     INTEGER {
                  eLan (0),
                  eWan (1),
                  eLoopback (2)
            }
    MAX-ACCESS read-only
    STATUS     current
    DESCRIPTION
            "-- empty --"
    ::= { hmStatusIpv6AddressesEntry 6 }

-- {TABLE} 1.3.6.1.4.1.248.32.18.1.77.2
hmStatusIpv6PrefixTable OBJECT-TYPE
    SYNTAX     SEQUENCE OF HmStatusIpv6PrefixEntry
    MAX-ACCESS not-accessible
    STATUS     current
    DESCRIPTION
            "-- empty --"
    ::= { hmStatusIpv6 2 }

-- {ROW} 1.3.6.1.4.1.248.32.18.1.77.2.1
hmStatusIpv6PrefixEntry OBJECT-TYPE
    SYNTAX     HmStatusIpv6PrefixEntry
    MAX-ACCESS not-accessible
    STATUS     current
    DESCRIPTION
            ""
    INDEX {
            hmStatusIpv6PrefixEntryInterfaceName,
            hmStatusIpv6PrefixEntryPrefix
          }
    ::= { hmStatusIpv6PrefixTable 1 }

HmStatusIpv6PrefixEntry ::= SEQUENCE {
            hmStatusIpv6PrefixEntryInterfaceName DisplayString,
            hmStatusIpv6PrefixEntryPrefix DisplayString,
            hmStatusIpv6PrefixEntryStatus DisplayString,
            hmStatusIpv6PrefixEntryType DisplayString
    }

-- {COLUMN} 1.3.6.1.4.1.248.32.18.1.77.2.1.1
hmStatusIpv6PrefixEntryInterfaceName OBJECT-TYPE
    SYNTAX     DisplayString (SIZE(0..16))
    MAX-ACCESS read-only
    STATUS     current
    DESCRIPTION
            "-- empty --"
    ::= { hmStatusIpv6PrefixEntry 1 }

-- {COLUMN} 1.3.6.1.4.1.248.32.18.1.77.2.1.2
hmStatusIpv6PrefixEntryPrefix OBJECT-TYPE
    SYNTAX     DisplayString (SIZE(0..43))
    MAX-ACCESS read-only
    STATUS     current
    DESCRIPTION
            "-- empty --"
    ::= { hmStatusIpv6PrefixEntry 2 }

-- {COLUMN} 1.3.6.1.4.1.248.32.18.1.77.2.1.3
hmStatusIpv6PrefixEntryStatus OBJECT-TYPE
    SYNTAX     DisplayString (SIZE(0..10))
    MAX-ACCESS read-only
    STATUS     current
    DESCRIPTION
            "-- empty --"
    ::= { hmStatusIpv6PrefixEntry 3 }

-- {COLUMN} 1.3.6.1.4.1.248.32.18.1.77.2.1.4
hmStatusIpv6PrefixEntryType OBJECT-TYPE
    SYNTAX     DisplayString (SIZE(0..26))
    MAX-ACCESS read-only
    STATUS     current
    DESCRIPTION
            "-- empty --"
    ::= { hmStatusIpv6PrefixEntry 4 }

-- {NODE} 1.3.6.1.4.1.248.32.18.1.77.3
hmStatusIpv6Dhcpv6 OBJECT IDENTIFIER ::= { hmStatusIpv6 3 }

-- {NODE} 1.3.6.1.4.1.248.32.18.1.77.3.1
hmStatusIpv6Dhcpv6Server OBJECT IDENTIFIER ::= { hmStatusIpv6Dhcpv6 1 }

-- {TABLE} 1.3.6.1.4.1.248.32.18.1.77.3.1.1
hmStatusIpv6Dhcpv6ServerAddressBindTable OBJECT-TYPE
    SYNTAX     SEQUENCE OF HmStatusIpv6Dhcpv6ServerAddressBindEntry
    MAX-ACCESS not-accessible
    STATUS     current
    DESCRIPTION
            ""
    ::= { hmStatusIpv6Dhcpv6Server 1 }

-- {ROW} 1.3.6.1.4.1.248.32.18.1.77.3.1.1.1
hmStatusIpv6Dhcpv6ServerAddressBindEntry OBJECT-TYPE
    SYNTAX     HmStatusIpv6Dhcpv6ServerAddressBindEntry
    MAX-ACCESS not-accessible
    STATUS     current
    DESCRIPTION
            ""
    INDEX {
            hmStatusIpv6Dhcpv6ServerAddressBindEntryInterfaceNameOrRelay,
            hmStatusIpv6Dhcpv6ServerAddressBindEntryAddress
          }
    ::= { hmStatusIpv6Dhcpv6ServerAddressBindTable 1 }

HmStatusIpv6Dhcpv6ServerAddressBindEntry ::= SEQUENCE {
            hmStatusIpv6Dhcpv6ServerAddressBindEntryInterfaceNameOrRelay DisplayString,
            hmStatusIpv6Dhcpv6ServerAddressBindEntryAddress DisplayString,
            hmStatusIpv6Dhcpv6ServerAddressBindEntryPreferredUntilNumerical Counter32,
            hmStatusIpv6Dhcpv6ServerAddressBindEntryPreferredUntil DisplayString,
            hmStatusIpv6Dhcpv6ServerAddressBindEntryValidUntilNumerical Counter32,
            hmStatusIpv6Dhcpv6ServerAddressBindEntryValidUntil DisplayString,
            hmStatusIpv6Dhcpv6ServerAddressBindEntryClientId DisplayString,
            hmStatusIpv6Dhcpv6ServerAddressBindEntryIaId Integer32,
            hmStatusIpv6Dhcpv6ServerAddressBindEntryHostName DisplayString,
            hmStatusIpv6Dhcpv6ServerAddressBindEntryUpdatedAtNumerical Counter32,
            hmStatusIpv6Dhcpv6ServerAddressBindEntryUpdatedAt DisplayString
    }

-- {COLUMN} 1.3.6.1.4.1.248.32.18.1.77.3.1.1.1.1
hmStatusIpv6Dhcpv6ServerAddressBindEntryInterfaceNameOrRelay OBJECT-TYPE
    SYNTAX     DisplayString (SIZE(0..255))
    MAX-ACCESS read-only
    STATUS     current
    DESCRIPTION
            "-- empty --"
    ::= { hmStatusIpv6Dhcpv6ServerAddressBindEntry 1 }

-- {COLUMN} 1.3.6.1.4.1.248.32.18.1.77.3.1.1.1.2
hmStatusIpv6Dhcpv6ServerAddressBindEntryAddress OBJECT-TYPE
    SYNTAX     DisplayString (SIZE(0..255))
    MAX-ACCESS read-only
    STATUS     current
    DESCRIPTION
            "-- empty --"
    ::= { hmStatusIpv6Dhcpv6ServerAddressBindEntry 2 }

-- {COLUMN} 1.3.6.1.4.1.248.32.18.1.77.3.1.1.1.3
hmStatusIpv6Dhcpv6ServerAddressBindEntryPreferredUntilNumerical OBJECT-TYPE
    SYNTAX     Counter32
    MAX-ACCESS read-only
    STATUS     current
    DESCRIPTION
            "-- empty --"
    ::= { hmStatusIpv6Dhcpv6ServerAddressBindEntry 3 }

-- {COLUMN} 1.3.6.1.4.1.248.32.18.1.77.3.1.1.1.4
hmStatusIpv6Dhcpv6ServerAddressBindEntryPreferredUntil OBJECT-TYPE
    SYNTAX     DisplayString (SIZE(0..255))
    MAX-ACCESS read-only
    STATUS     current
    DESCRIPTION
            "-- empty --"
    ::= { hmStatusIpv6Dhcpv6ServerAddressBindEntry 4 }

-- {COLUMN} 1.3.6.1.4.1.248.32.18.1.77.3.1.1.1.5
hmStatusIpv6Dhcpv6ServerAddressBindEntryValidUntilNumerical OBJECT-TYPE
    SYNTAX     Counter32
    MAX-ACCESS read-only
    STATUS     current
    DESCRIPTION
            "-- empty --"
    ::= { hmStatusIpv6Dhcpv6ServerAddressBindEntry 5 }

-- {COLUMN} 1.3.6.1.4.1.248.32.18.1.77.3.1.1.1.6
hmStatusIpv6Dhcpv6ServerAddressBindEntryValidUntil OBJECT-TYPE
    SYNTAX     DisplayString (SIZE(0..255))
    MAX-ACCESS read-only
    STATUS     current
    DESCRIPTION
            "-- empty --"
    ::= { hmStatusIpv6Dhcpv6ServerAddressBindEntry 6 }

-- {COLUMN} 1.3.6.1.4.1.248.32.18.1.77.3.1.1.1.7
hmStatusIpv6Dhcpv6ServerAddressBindEntryClientId OBJECT-TYPE
    SYNTAX     DisplayString (SIZE(0..255))
    MAX-ACCESS read-only
    STATUS     current
    DESCRIPTION
            "-- empty --"
    ::= { hmStatusIpv6Dhcpv6ServerAddressBindEntry 7 }

-- {COLUMN} 1.3.6.1.4.1.248.32.18.1.77.3.1.1.1.8
hmStatusIpv6Dhcpv6ServerAddressBindEntryIaId OBJECT-TYPE
    SYNTAX     Integer32 (0..2147483647)
    MAX-ACCESS read-only
    STATUS     current
    DESCRIPTION
            "-- empty --"
    ::= { hmStatusIpv6Dhcpv6ServerAddressBindEntry 8 }

-- {COLUMN} 1.3.6.1.4.1.248.32.18.1.77.3.1.1.1.9
hmStatusIpv6Dhcpv6ServerAddressBindEntryHostName OBJECT-TYPE
    SYNTAX     DisplayString (SIZE(0..255))
    MAX-ACCESS read-only
    STATUS     current
    DESCRIPTION
            "-- empty --"
    ::= { hmStatusIpv6Dhcpv6ServerAddressBindEntry 9 }

-- {COLUMN} 1.3.6.1.4.1.248.32.18.1.77.3.1.1.1.10
hmStatusIpv6Dhcpv6ServerAddressBindEntryUpdatedAtNumerical OBJECT-TYPE
    SYNTAX     Counter32
    MAX-ACCESS read-only
    STATUS     current
    DESCRIPTION
            "-- empty --"
    ::= { hmStatusIpv6Dhcpv6ServerAddressBindEntry 10 }

-- {COLUMN} 1.3.6.1.4.1.248.32.18.1.77.3.1.1.1.11
hmStatusIpv6Dhcpv6ServerAddressBindEntryUpdatedAt OBJECT-TYPE
    SYNTAX     DisplayString (SIZE(0..255))
    MAX-ACCESS read-only
    STATUS     current
    DESCRIPTION
            "-- empty --"
    ::= { hmStatusIpv6Dhcpv6ServerAddressBindEntry 11 }

-- {TABLE} 1.3.6.1.4.1.248.32.18.1.77.3.1.2
hmStatusIpv6Dhcpv6ServerPdBindingsTable OBJECT-TYPE
    SYNTAX     SEQUENCE OF HmStatusIpv6Dhcpv6ServerPdBindingsEntry
    MAX-ACCESS not-accessible
    STATUS     current
    DESCRIPTION
            "-- empty --"
    ::= { hmStatusIpv6Dhcpv6Server 2 }

-- {ROW} 1.3.6.1.4.1.248.32.18.1.77.3.1.2.1
hmStatusIpv6Dhcpv6ServerPdBindingsEntry OBJECT-TYPE
    SYNTAX     HmStatusIpv6Dhcpv6ServerPdBindingsEntry
    MAX-ACCESS not-accessible
    STATUS     current
    DESCRIPTION
            ""
    INDEX {
            hmStatusIpv6Dhcpv6ServerPdBindingsEntryInterfaceNameOrRelay,
            hmStatusIpv6Dhcpv6ServerPdBindingsEntryPdPrefix
          }
    ::= { hmStatusIpv6Dhcpv6ServerPdBindingsTable 1 }

HmStatusIpv6Dhcpv6ServerPdBindingsEntry ::= SEQUENCE {
            hmStatusIpv6Dhcpv6ServerPdBindingsEntryInterfaceNameOrRelay DisplayString,
            hmStatusIpv6Dhcpv6ServerPdBindingsEntryPdPrefix DisplayString,
            hmStatusIpv6Dhcpv6ServerPdBindingsEntryPreferredUntilNumerical Counter32,
            hmStatusIpv6Dhcpv6ServerPdBindingsEntryPreferredUntil DisplayString,
            hmStatusIpv6Dhcpv6ServerPdBindingsEntryValidUntilNumerical Counter32,
            hmStatusIpv6Dhcpv6ServerPdBindingsEntryValidUntil DisplayString,
            hmStatusIpv6Dhcpv6ServerPdBindingsEntryClientId DisplayString,
            hmStatusIpv6Dhcpv6ServerPdBindingsEntryIaId Integer32,
            hmStatusIpv6Dhcpv6ServerPdBindingsEntryHostName DisplayString,
            hmStatusIpv6Dhcpv6ServerPdBindingsEntryUpdatedAtNumerical Counter32,
            hmStatusIpv6Dhcpv6ServerPdBindingsEntryUpdatedAt DisplayString
    }

-- {COLUMN} 1.3.6.1.4.1.248.32.18.1.77.3.1.2.1.1
hmStatusIpv6Dhcpv6ServerPdBindingsEntryInterfaceNameOrRelay OBJECT-TYPE
    SYNTAX     DisplayString (SIZE(0..255))
    MAX-ACCESS read-only
    STATUS     current
    DESCRIPTION
            "-- empty --"
    ::= { hmStatusIpv6Dhcpv6ServerPdBindingsEntry 1 }

-- {COLUMN} 1.3.6.1.4.1.248.32.18.1.77.3.1.2.1.2
hmStatusIpv6Dhcpv6ServerPdBindingsEntryPdPrefix OBJECT-TYPE
    SYNTAX     DisplayString (SIZE(0..255))
    MAX-ACCESS read-only
    STATUS     current
    DESCRIPTION
            "-- empty --"
    ::= { hmStatusIpv6Dhcpv6ServerPdBindingsEntry 2 }

-- {COLUMN} 1.3.6.1.4.1.248.32.18.1.77.3.1.2.1.3
hmStatusIpv6Dhcpv6ServerPdBindingsEntryPreferredUntilNumerical OBJECT-TYPE
    SYNTAX     Counter32
    MAX-ACCESS read-only
    STATUS     current
    DESCRIPTION
            "-- empty --"
    ::= { hmStatusIpv6Dhcpv6ServerPdBindingsEntry 3 }

-- {COLUMN} 1.3.6.1.4.1.248.32.18.1.77.3.1.2.1.4
hmStatusIpv6Dhcpv6ServerPdBindingsEntryPreferredUntil OBJECT-TYPE
    SYNTAX     DisplayString (SIZE(0..255))
    MAX-ACCESS read-only
    STATUS     current
    DESCRIPTION
            "-- empty --"
    ::= { hmStatusIpv6Dhcpv6ServerPdBindingsEntry 4 }

-- {COLUMN} 1.3.6.1.4.1.248.32.18.1.77.3.1.2.1.5
hmStatusIpv6Dhcpv6ServerPdBindingsEntryValidUntilNumerical OBJECT-TYPE
    SYNTAX     Counter32
    MAX-ACCESS read-only
    STATUS     current
    DESCRIPTION
            "-- empty --"
    ::= { hmStatusIpv6Dhcpv6ServerPdBindingsEntry 5 }

-- {COLUMN} 1.3.6.1.4.1.248.32.18.1.77.3.1.2.1.6
hmStatusIpv6Dhcpv6ServerPdBindingsEntryValidUntil OBJECT-TYPE
    SYNTAX     DisplayString (SIZE(0..255))
    MAX-ACCESS read-only
    STATUS     current
    DESCRIPTION
            "-- empty --"
    ::= { hmStatusIpv6Dhcpv6ServerPdBindingsEntry 6 }

-- {COLUMN} 1.3.6.1.4.1.248.32.18.1.77.3.1.2.1.7
hmStatusIpv6Dhcpv6ServerPdBindingsEntryClientId OBJECT-TYPE
    SYNTAX     DisplayString (SIZE(0..255))
    MAX-ACCESS read-only
    STATUS     current
    DESCRIPTION
            "-- empty --"
    ::= { hmStatusIpv6Dhcpv6ServerPdBindingsEntry 7 }

-- {COLUMN} 1.3.6.1.4.1.248.32.18.1.77.3.1.2.1.8
hmStatusIpv6Dhcpv6ServerPdBindingsEntryIaId OBJECT-TYPE
    SYNTAX     Integer32 (0..2147483647)
    MAX-ACCESS read-only
    STATUS     current
    DESCRIPTION
            "-- empty --"
    ::= { hmStatusIpv6Dhcpv6ServerPdBindingsEntry 8 }

-- {COLUMN} 1.3.6.1.4.1.248.32.18.1.77.3.1.2.1.9
hmStatusIpv6Dhcpv6ServerPdBindingsEntryHostName OBJECT-TYPE
    SYNTAX     DisplayString (SIZE(0..255))
    MAX-ACCESS read-only
    STATUS     current
    DESCRIPTION
            "-- empty --"
    ::= { hmStatusIpv6Dhcpv6ServerPdBindingsEntry 9 }

-- {COLUMN} 1.3.6.1.4.1.248.32.18.1.77.3.1.2.1.10
hmStatusIpv6Dhcpv6ServerPdBindingsEntryUpdatedAtNumerical OBJECT-TYPE
    SYNTAX     Counter32
    MAX-ACCESS read-only
    STATUS     current
    DESCRIPTION
            "-- empty --"
    ::= { hmStatusIpv6Dhcpv6ServerPdBindingsEntry 10 }

-- {COLUMN} 1.3.6.1.4.1.248.32.18.1.77.3.1.2.1.11
hmStatusIpv6Dhcpv6ServerPdBindingsEntryUpdatedAt OBJECT-TYPE
    SYNTAX     DisplayString (SIZE(0..255))
    MAX-ACCESS read-only
    STATUS     current
    DESCRIPTION
            "-- empty --"
    ::= { hmStatusIpv6Dhcpv6ServerPdBindingsEntry 11 }

-- {TABLE} 1.3.6.1.4.1.248.32.18.1.77.3.1.3
hmStatusIpv6Dhcpv6ServerDeclinedAddrTable OBJECT-TYPE
    SYNTAX     SEQUENCE OF HmStatusIpv6Dhcpv6ServerDeclinedAddrEntry
    MAX-ACCESS not-accessible
    STATUS     current
    DESCRIPTION
            ""
    ::= { hmStatusIpv6Dhcpv6Server 3 }

-- {ROW} 1.3.6.1.4.1.248.32.18.1.77.3.1.3.1
hmStatusIpv6Dhcpv6ServerDeclinedAddrEntry OBJECT-TYPE
    SYNTAX     HmStatusIpv6Dhcpv6ServerDeclinedAddrEntry
    MAX-ACCESS not-accessible
    STATUS     current
    DESCRIPTION
            ""
    INDEX {
            hmStatusIpv6Dhcpv6ServerDeclinedAddrEntryInterfaceNameOrRelay,
            hmStatusIpv6Dhcpv6ServerDeclinedAddrEntryAddress
          }
    ::= { hmStatusIpv6Dhcpv6ServerDeclinedAddrTable 1 }

HmStatusIpv6Dhcpv6ServerDeclinedAddrEntry ::= SEQUENCE {
            hmStatusIpv6Dhcpv6ServerDeclinedAddrEntryInterfaceNameOrRelay DisplayString,
            hmStatusIpv6Dhcpv6ServerDeclinedAddrEntryAddress DisplayString,
            hmStatusIpv6Dhcpv6ServerDeclinedAddrEntryDeclinedAtNumerical Counter32,
            hmStatusIpv6Dhcpv6ServerDeclinedAddrEntryDeclinedAt DisplayString,
            hmStatusIpv6Dhcpv6ServerDeclinedAddrEntryClientId DisplayString,
            hmStatusIpv6Dhcpv6ServerDeclinedAddrEntryIaId Integer32,
            hmStatusIpv6Dhcpv6ServerDeclinedAddrEntryHostName DisplayString
    }

-- {COLUMN} 1.3.6.1.4.1.248.32.18.1.77.3.1.3.1.1
hmStatusIpv6Dhcpv6ServerDeclinedAddrEntryInterfaceNameOrRelay OBJECT-TYPE
    SYNTAX     DisplayString (SIZE(0..255))
    MAX-ACCESS read-only
    STATUS     current
    DESCRIPTION
            "-- empty --"
    ::= { hmStatusIpv6Dhcpv6ServerDeclinedAddrEntry 1 }

-- {COLUMN} 1.3.6.1.4.1.248.32.18.1.77.3.1.3.1.2
hmStatusIpv6Dhcpv6ServerDeclinedAddrEntryAddress OBJECT-TYPE
    SYNTAX     DisplayString (SIZE(0..255))
    MAX-ACCESS read-only
    STATUS     current
    DESCRIPTION
            "-- empty --"
    ::= { hmStatusIpv6Dhcpv6ServerDeclinedAddrEntry 2 }

-- {COLUMN} 1.3.6.1.4.1.248.32.18.1.77.3.1.3.1.3
hmStatusIpv6Dhcpv6ServerDeclinedAddrEntryDeclinedAtNumerical OBJECT-TYPE
    SYNTAX     Counter32
    MAX-ACCESS read-only
    STATUS     current
    DESCRIPTION
            "-- empty --"
    ::= { hmStatusIpv6Dhcpv6ServerDeclinedAddrEntry 3 }

-- {COLUMN} 1.3.6.1.4.1.248.32.18.1.77.3.1.3.1.4
hmStatusIpv6Dhcpv6ServerDeclinedAddrEntryDeclinedAt OBJECT-TYPE
    SYNTAX     DisplayString (SIZE(0..255))
    MAX-ACCESS read-only
    STATUS     current
    DESCRIPTION
            "-- empty --"
    ::= { hmStatusIpv6Dhcpv6ServerDeclinedAddrEntry 4 }

-- {COLUMN} 1.3.6.1.4.1.248.32.18.1.77.3.1.3.1.5
hmStatusIpv6Dhcpv6ServerDeclinedAddrEntryClientId OBJECT-TYPE
    SYNTAX     DisplayString (SIZE(0..255))
    MAX-ACCESS read-only
    STATUS     current
    DESCRIPTION
            "-- empty --"
    ::= { hmStatusIpv6Dhcpv6ServerDeclinedAddrEntry 5 }

-- {COLUMN} 1.3.6.1.4.1.248.32.18.1.77.3.1.3.1.6
hmStatusIpv6Dhcpv6ServerDeclinedAddrEntryIaId OBJECT-TYPE
    SYNTAX     Integer32 (0..2147483647)
    MAX-ACCESS read-only
    STATUS     current
    DESCRIPTION
            "-- empty --"
    ::= { hmStatusIpv6Dhcpv6ServerDeclinedAddrEntry 6 }

-- {COLUMN} 1.3.6.1.4.1.248.32.18.1.77.3.1.3.1.9
hmStatusIpv6Dhcpv6ServerDeclinedAddrEntryHostName OBJECT-TYPE
    SYNTAX     DisplayString (SIZE(0..255))
    MAX-ACCESS read-only
    STATUS     current
    DESCRIPTION
            "-- empty --"
    ::= { hmStatusIpv6Dhcpv6ServerDeclinedAddrEntry 9 }

-- {TABLE} 1.3.6.1.4.1.248.32.18.1.77.3.1.4
hmStatusIpv6Dhcpv6ServerInterfaceStateTable OBJECT-TYPE
    SYNTAX     SEQUENCE OF HmStatusIpv6Dhcpv6ServerInterfaceStateEntry
    MAX-ACCESS not-accessible
    STATUS     current
    DESCRIPTION
            "-- empty --"
    ::= { hmStatusIpv6Dhcpv6Server 4 }

-- {ROW} 1.3.6.1.4.1.248.32.18.1.77.3.1.4.1
hmStatusIpv6Dhcpv6ServerInterfaceStateEntry OBJECT-TYPE
    SYNTAX     HmStatusIpv6Dhcpv6ServerInterfaceStateEntry
    MAX-ACCESS not-accessible
    STATUS     current
    DESCRIPTION
            ""
    INDEX {
            hmStatusIpv6Dhcpv6ServerInterfaceStateEntryInterfaceNameOrRelay
          }
    ::= { hmStatusIpv6Dhcpv6ServerInterfaceStateTable 1 }

HmStatusIpv6Dhcpv6ServerInterfaceStateEntry ::= SEQUENCE {
            hmStatusIpv6Dhcpv6ServerInterfaceStateEntryInterfaceNameOrRelay DisplayString,
            hmStatusIpv6Dhcpv6ServerInterfaceStateEntryOperating INTEGER,
            hmStatusIpv6Dhcpv6ServerInterfaceStateEntryMode INTEGER,
            hmStatusIpv6Dhcpv6ServerInterfaceStateEntryAssignPd INTEGER
    }

-- {COLUMN} 1.3.6.1.4.1.248.32.18.1.77.3.1.4.1.1
hmStatusIpv6Dhcpv6ServerInterfaceStateEntryInterfaceNameOrRelay OBJECT-TYPE
    SYNTAX     DisplayString (SIZE(0..255))
    MAX-ACCESS read-only
    STATUS     current
    DESCRIPTION
            "-- empty --"
    ::= { hmStatusIpv6Dhcpv6ServerInterfaceStateEntry 1 }

-- {COLUMN} 1.3.6.1.4.1.248.32.18.1.77.3.1.4.1.2
hmStatusIpv6Dhcpv6ServerInterfaceStateEntryOperating OBJECT-TYPE
    SYNTAX     INTEGER {
                  eNo (0),
                  eYes (1)
            }
    MAX-ACCESS read-only
    STATUS     current
    DESCRIPTION
            "-- empty --"
    ::= { hmStatusIpv6Dhcpv6ServerInterfaceStateEntry 2 }

-- {COLUMN} 1.3.6.1.4.1.248.32.18.1.77.3.1.4.1.3
hmStatusIpv6Dhcpv6ServerInterfaceStateEntryMode OBJECT-TYPE
    SYNTAX     INTEGER {
                  eStateless (0),
                  eStateful (1),
                  eStatic (2)
            }
    MAX-ACCESS read-only
    STATUS     current
    DESCRIPTION
            "-- empty --"
    ::= { hmStatusIpv6Dhcpv6ServerInterfaceStateEntry 3 }

-- {COLUMN} 1.3.6.1.4.1.248.32.18.1.77.3.1.4.1.4
hmStatusIpv6Dhcpv6ServerInterfaceStateEntryAssignPd OBJECT-TYPE
    SYNTAX     INTEGER {
                  eNo (0),
                  eYes (1)
            }
    MAX-ACCESS read-only
    STATUS     current
    DESCRIPTION
            "-- empty --"
    ::= { hmStatusIpv6Dhcpv6ServerInterfaceStateEntry 4 }

-- {SCALAR} 1.3.6.1.4.1.248.32.18.1.77.3.1.5
hmStatusIpv6Dhcpv6ServerServerId OBJECT-TYPE
    SYNTAX     DisplayString (SIZE(0..97))
    MAX-ACCESS read-only
    STATUS     current
    DESCRIPTION
            "-- empty --"
    ::= { hmStatusIpv6Dhcpv6Server 5 }

-- {TABLE} 1.3.6.1.4.1.248.32.18.1.77.3.1.6
hmStatusIpv6Dhcpv6ServerClientsTable OBJECT-TYPE
    SYNTAX     SEQUENCE OF HmStatusIpv6Dhcpv6ServerClientsEntry
    MAX-ACCESS not-accessible
    STATUS     current
    DESCRIPTION
            "-- empty --"
    ::= { hmStatusIpv6Dhcpv6Server 6 }

-- {ROW} 1.3.6.1.4.1.248.32.18.1.77.3.1.6.1
hmStatusIpv6Dhcpv6ServerClientsEntry OBJECT-TYPE
    SYNTAX     HmStatusIpv6Dhcpv6ServerClientsEntry
    MAX-ACCESS not-accessible
    STATUS     current
    DESCRIPTION
            ""
    INDEX {
            hmStatusIpv6Dhcpv6ServerClientsEntryClientId
          }
    ::= { hmStatusIpv6Dhcpv6ServerClientsTable 1 }

HmStatusIpv6Dhcpv6ServerClientsEntry ::= SEQUENCE {
            hmStatusIpv6Dhcpv6ServerClientsEntryClientId DisplayString,
            hmStatusIpv6Dhcpv6ServerClientsEntryHostName DisplayString,
            hmStatusIpv6Dhcpv6ServerClientsEntryReconfNegotiated INTEGER,
            hmStatusIpv6Dhcpv6ServerClientsEntryReconfNegotiatedAtNumerical Counter32,
            hmStatusIpv6Dhcpv6ServerClientsEntryReconfNegotiatedAt DisplayString,
            hmStatusIpv6Dhcpv6ServerClientsEntryReconfigure INTEGER
    }

-- {COLUMN} 1.3.6.1.4.1.248.32.18.1.77.3.1.6.1.1
hmStatusIpv6Dhcpv6ServerClientsEntryClientId OBJECT-TYPE
    SYNTAX     DisplayString (SIZE(0..255))
    MAX-ACCESS read-only
    STATUS     current
    DESCRIPTION
            "-- empty --"
    ::= { hmStatusIpv6Dhcpv6ServerClientsEntry 1 }

-- {COLUMN} 1.3.6.1.4.1.248.32.18.1.77.3.1.6.1.2
hmStatusIpv6Dhcpv6ServerClientsEntryHostName OBJECT-TYPE
    SYNTAX     DisplayString (SIZE(0..255))
    MAX-ACCESS read-only
    STATUS     current
    DESCRIPTION
            "-- empty --"
    ::= { hmStatusIpv6Dhcpv6ServerClientsEntry 2 }

-- {COLUMN} 1.3.6.1.4.1.248.32.18.1.77.3.1.6.1.3
hmStatusIpv6Dhcpv6ServerClientsEntryReconfNegotiated OBJECT-TYPE
    SYNTAX     INTEGER {
                  eNo (0),
                  eYes (1),
                  eNotEnoughRandom (2)
            }
    MAX-ACCESS read-only
    STATUS     current
    DESCRIPTION
            "-- empty --"
    ::= { hmStatusIpv6Dhcpv6ServerClientsEntry 3 }

-- {COLUMN} 1.3.6.1.4.1.248.32.18.1.77.3.1.6.1.4
hmStatusIpv6Dhcpv6ServerClientsEntryReconfNegotiatedAtNumerical OBJECT-TYPE
    SYNTAX     Counter32
    MAX-ACCESS read-only
    STATUS     current
    DESCRIPTION
            "-- empty --"
    ::= { hmStatusIpv6Dhcpv6ServerClientsEntry 4 }

-- {COLUMN} 1.3.6.1.4.1.248.32.18.1.77.3.1.6.1.5
hmStatusIpv6Dhcpv6ServerClientsEntryReconfNegotiatedAt OBJECT-TYPE
    SYNTAX     DisplayString (SIZE(0..255))
    MAX-ACCESS read-only
    STATUS     current
    DESCRIPTION
            "-- empty --"
    ::= { hmStatusIpv6Dhcpv6ServerClientsEntry 5 }

-- {COLUMN} 1.3.6.1.4.1.248.32.18.1.77.3.1.6.1.6
hmStatusIpv6Dhcpv6ServerClientsEntryReconfigure OBJECT-TYPE
    SYNTAX     INTEGER {
                  eOff (0),
                  eRunning (1),
                  eSucceeded (2),
                  eFailed (3)
            }
    MAX-ACCESS read-only
    STATUS     current
    DESCRIPTION
            "-- empty --"
    ::= { hmStatusIpv6Dhcpv6ServerClientsEntry 6 }

-- {SCALAR} 1.3.6.1.4.1.248.32.18.1.77.3.1.7
hmStatusIpv6Dhcpv6ServerReconfigure OBJECT-TYPE
    SYNTAX     DisplayString
    MAX-ACCESS read-write
    STATUS     current
    DESCRIPTION
            "-- empty --"
    ::= { hmStatusIpv6Dhcpv6Server 7 }

-- {SCALAR} 1.3.6.1.4.1.248.32.18.1.77.3.1.8
hmStatusIpv6Dhcpv6ServerRasInterfaces OBJECT-TYPE
    SYNTAX     Integer32 (0..2147483647)
    MAX-ACCESS read-only
    STATUS     current
    DESCRIPTION
            "-- empty --"
    ::= { hmStatusIpv6Dhcpv6Server 8 }

-- {NODE} 1.3.6.1.4.1.248.32.18.1.77.3.2
hmStatusIpv6Dhcpv6Client OBJECT IDENTIFIER ::= { hmStatusIpv6Dhcpv6 2 }

-- {TABLE} 1.3.6.1.4.1.248.32.18.1.77.3.2.1
hmStatusIpv6Dhcpv6ClientInterfaceListTable OBJECT-TYPE
    SYNTAX     SEQUENCE OF HmStatusIpv6Dhcpv6ClientInterfaceListEntry
    MAX-ACCESS not-accessible
    STATUS     current
    DESCRIPTION
            "-- empty --"
    ::= { hmStatusIpv6Dhcpv6Client 1 }

-- {ROW} 1.3.6.1.4.1.248.32.18.1.77.3.2.1.1
hmStatusIpv6Dhcpv6ClientInterfaceListEntry OBJECT-TYPE
    SYNTAX     HmStatusIpv6Dhcpv6ClientInterfaceListEntry
    MAX-ACCESS not-accessible
    STATUS     current
    DESCRIPTION
            ""
    INDEX {
            hmStatusIpv6Dhcpv6ClientInterfaceListEntryInterfaceName
          }
    ::= { hmStatusIpv6Dhcpv6ClientInterfaceListTable 1 }

HmStatusIpv6Dhcpv6ClientInterfaceListEntry ::= SEQUENCE {
            hmStatusIpv6Dhcpv6ClientInterfaceListEntryInterfaceName DisplayString,
            hmStatusIpv6Dhcpv6ClientInterfaceListEntryDnsDefault DisplayString,
            hmStatusIpv6Dhcpv6ClientInterfaceListEntryDnsBackup DisplayString,
            hmStatusIpv6Dhcpv6ClientInterfaceListEntryDomainList DisplayString,
            hmStatusIpv6Dhcpv6ClientInterfaceListEntryAftrNameForDsLite DisplayString
    }

-- {COLUMN} 1.3.6.1.4.1.248.32.18.1.77.3.2.1.1.1
hmStatusIpv6Dhcpv6ClientInterfaceListEntryInterfaceName OBJECT-TYPE
    SYNTAX     DisplayString (SIZE(0..255))
    MAX-ACCESS read-only
    STATUS     current
    DESCRIPTION
            "-- empty --"
    ::= { hmStatusIpv6Dhcpv6ClientInterfaceListEntry 1 }

-- {COLUMN} 1.3.6.1.4.1.248.32.18.1.77.3.2.1.1.2
hmStatusIpv6Dhcpv6ClientInterfaceListEntryDnsDefault OBJECT-TYPE
    SYNTAX     DisplayString (SIZE(0..255))
    MAX-ACCESS read-only
    STATUS     current
    DESCRIPTION
            "-- empty --"
    ::= { hmStatusIpv6Dhcpv6ClientInterfaceListEntry 2 }

-- {COLUMN} 1.3.6.1.4.1.248.32.18.1.77.3.2.1.1.3
hmStatusIpv6Dhcpv6ClientInterfaceListEntryDnsBackup OBJECT-TYPE
    SYNTAX     DisplayString (SIZE(0..255))
    MAX-ACCESS read-only
    STATUS     current
    DESCRIPTION
            "-- empty --"
    ::= { hmStatusIpv6Dhcpv6ClientInterfaceListEntry 3 }

-- {COLUMN} 1.3.6.1.4.1.248.32.18.1.77.3.2.1.1.4
hmStatusIpv6Dhcpv6ClientInterfaceListEntryDomainList OBJECT-TYPE
    SYNTAX     DisplayString (SIZE(0..255))
    MAX-ACCESS read-only
    STATUS     current
    DESCRIPTION
            "-- empty --"
    ::= { hmStatusIpv6Dhcpv6ClientInterfaceListEntry 4 }

-- {COLUMN} 1.3.6.1.4.1.248.32.18.1.77.3.2.1.1.5
hmStatusIpv6Dhcpv6ClientInterfaceListEntryAftrNameForDsLite OBJECT-TYPE
    SYNTAX     DisplayString (SIZE(0..255))
    MAX-ACCESS read-only
    STATUS     current
    DESCRIPTION
            "-- empty --"
    ::= { hmStatusIpv6Dhcpv6ClientInterfaceListEntry 5 }

-- {TABLE} 1.3.6.1.4.1.248.32.18.1.77.3.2.2
hmStatusIpv6Dhcpv6ClientAddressBindTable OBJECT-TYPE
    SYNTAX     SEQUENCE OF HmStatusIpv6Dhcpv6ClientAddressBindEntry
    MAX-ACCESS not-accessible
    STATUS     current
    DESCRIPTION
            ""
    ::= { hmStatusIpv6Dhcpv6Client 2 }

-- {ROW} 1.3.6.1.4.1.248.32.18.1.77.3.2.2.1
hmStatusIpv6Dhcpv6ClientAddressBindEntry OBJECT-TYPE
    SYNTAX     HmStatusIpv6Dhcpv6ClientAddressBindEntry
    MAX-ACCESS not-accessible
    STATUS     current
    DESCRIPTION
            ""
    INDEX {
            hmStatusIpv6Dhcpv6ClientAddressBindEntryInterfaceName,
            hmStatusIpv6Dhcpv6ClientAddressBindEntryAddress
          }
    ::= { hmStatusIpv6Dhcpv6ClientAddressBindTable 1 }

HmStatusIpv6Dhcpv6ClientAddressBindEntry ::= SEQUENCE {
            hmStatusIpv6Dhcpv6ClientAddressBindEntryInterfaceName DisplayString,
            hmStatusIpv6Dhcpv6ClientAddressBindEntryAddress DisplayString,
            hmStatusIpv6Dhcpv6ClientAddressBindEntryPreferredUntilNumerical Counter32,
            hmStatusIpv6Dhcpv6ClientAddressBindEntryPreferredUntil DisplayString,
            hmStatusIpv6Dhcpv6ClientAddressBindEntryValidUntilNumerical Counter32,
            hmStatusIpv6Dhcpv6ClientAddressBindEntryValidUntil DisplayString
    }

-- {COLUMN} 1.3.6.1.4.1.248.32.18.1.77.3.2.2.1.1
hmStatusIpv6Dhcpv6ClientAddressBindEntryInterfaceName OBJECT-TYPE
    SYNTAX     DisplayString (SIZE(0..255))
    MAX-ACCESS read-only
    STATUS     current
    DESCRIPTION
            "-- empty --"
    ::= { hmStatusIpv6Dhcpv6ClientAddressBindEntry 1 }

-- {COLUMN} 1.3.6.1.4.1.248.32.18.1.77.3.2.2.1.2
hmStatusIpv6Dhcpv6ClientAddressBindEntryAddress OBJECT-TYPE
    SYNTAX     DisplayString (SIZE(0..255))
    MAX-ACCESS read-only
    STATUS     current
    DESCRIPTION
            "-- empty --"
    ::= { hmStatusIpv6Dhcpv6ClientAddressBindEntry 2 }

-- {COLUMN} 1.3.6.1.4.1.248.32.18.1.77.3.2.2.1.3
hmStatusIpv6Dhcpv6ClientAddressBindEntryPreferredUntilNumerical OBJECT-TYPE
    SYNTAX     Counter32
    MAX-ACCESS read-only
    STATUS     current
    DESCRIPTION
            "-- empty --"
    ::= { hmStatusIpv6Dhcpv6ClientAddressBindEntry 3 }

-- {COLUMN} 1.3.6.1.4.1.248.32.18.1.77.3.2.2.1.4
hmStatusIpv6Dhcpv6ClientAddressBindEntryPreferredUntil OBJECT-TYPE
    SYNTAX     DisplayString (SIZE(0..255))
    MAX-ACCESS read-only
    STATUS     current
    DESCRIPTION
            "-- empty --"
    ::= { hmStatusIpv6Dhcpv6ClientAddressBindEntry 4 }

-- {COLUMN} 1.3.6.1.4.1.248.32.18.1.77.3.2.2.1.5
hmStatusIpv6Dhcpv6ClientAddressBindEntryValidUntilNumerical OBJECT-TYPE
    SYNTAX     Counter32
    MAX-ACCESS read-only
    STATUS     current
    DESCRIPTION
            "-- empty --"
    ::= { hmStatusIpv6Dhcpv6ClientAddressBindEntry 5 }

-- {COLUMN} 1.3.6.1.4.1.248.32.18.1.77.3.2.2.1.6
hmStatusIpv6Dhcpv6ClientAddressBindEntryValidUntil OBJECT-TYPE
    SYNTAX     DisplayString (SIZE(0..255))
    MAX-ACCESS read-only
    STATUS     current
    DESCRIPTION
            "-- empty --"
    ::= { hmStatusIpv6Dhcpv6ClientAddressBindEntry 6 }

-- {TABLE} 1.3.6.1.4.1.248.32.18.1.77.3.2.3
hmStatusIpv6Dhcpv6ClientPdBindingsTable OBJECT-TYPE
    SYNTAX     SEQUENCE OF HmStatusIpv6Dhcpv6ClientPdBindingsEntry
    MAX-ACCESS not-accessible
    STATUS     current
    DESCRIPTION
            "-- empty --"
    ::= { hmStatusIpv6Dhcpv6Client 3 }

-- {ROW} 1.3.6.1.4.1.248.32.18.1.77.3.2.3.1
hmStatusIpv6Dhcpv6ClientPdBindingsEntry OBJECT-TYPE
    SYNTAX     HmStatusIpv6Dhcpv6ClientPdBindingsEntry
    MAX-ACCESS not-accessible
    STATUS     current
    DESCRIPTION
            ""
    INDEX {
            hmStatusIpv6Dhcpv6ClientPdBindingsEntryInterfaceName,
            hmStatusIpv6Dhcpv6ClientPdBindingsEntryPdPrefix,
            hmStatusIpv6Dhcpv6ClientPdBindingsEntryExcludedPrefix
          }
    ::= { hmStatusIpv6Dhcpv6ClientPdBindingsTable 1 }

HmStatusIpv6Dhcpv6ClientPdBindingsEntry ::= SEQUENCE {
            hmStatusIpv6Dhcpv6ClientPdBindingsEntryInterfaceName DisplayString,
            hmStatusIpv6Dhcpv6ClientPdBindingsEntryPdPrefix DisplayString,
            hmStatusIpv6Dhcpv6ClientPdBindingsEntryPreferredUntilNumerical Counter32,
            hmStatusIpv6Dhcpv6ClientPdBindingsEntryPreferredUntil DisplayString,
            hmStatusIpv6Dhcpv6ClientPdBindingsEntryValidUntilNumerical Counter32,
            hmStatusIpv6Dhcpv6ClientPdBindingsEntryValidUntil DisplayString,
            hmStatusIpv6Dhcpv6ClientPdBindingsEntryExcludedPrefix DisplayString
    }

-- {COLUMN} 1.3.6.1.4.1.248.32.18.1.77.3.2.3.1.1
hmStatusIpv6Dhcpv6ClientPdBindingsEntryInterfaceName OBJECT-TYPE
    SYNTAX     DisplayString (SIZE(0..255))
    MAX-ACCESS read-only
    STATUS     current
    DESCRIPTION
            "-- empty --"
    ::= { hmStatusIpv6Dhcpv6ClientPdBindingsEntry 1 }

-- {COLUMN} 1.3.6.1.4.1.248.32.18.1.77.3.2.3.1.2
hmStatusIpv6Dhcpv6ClientPdBindingsEntryPdPrefix OBJECT-TYPE
    SYNTAX     DisplayString (SIZE(0..255))
    MAX-ACCESS read-only
    STATUS     current
    DESCRIPTION
            "-- empty --"
    ::= { hmStatusIpv6Dhcpv6ClientPdBindingsEntry 2 }

-- {COLUMN} 1.3.6.1.4.1.248.32.18.1.77.3.2.3.1.3
hmStatusIpv6Dhcpv6ClientPdBindingsEntryPreferredUntilNumerical OBJECT-TYPE
    SYNTAX     Counter32
    MAX-ACCESS read-only
    STATUS     current
    DESCRIPTION
            "-- empty --"
    ::= { hmStatusIpv6Dhcpv6ClientPdBindingsEntry 3 }

-- {COLUMN} 1.3.6.1.4.1.248.32.18.1.77.3.2.3.1.4
hmStatusIpv6Dhcpv6ClientPdBindingsEntryPreferredUntil OBJECT-TYPE
    SYNTAX     DisplayString (SIZE(0..255))
    MAX-ACCESS read-only
    STATUS     current
    DESCRIPTION
            "-- empty --"
    ::= { hmStatusIpv6Dhcpv6ClientPdBindingsEntry 4 }

-- {COLUMN} 1.3.6.1.4.1.248.32.18.1.77.3.2.3.1.5
hmStatusIpv6Dhcpv6ClientPdBindingsEntryValidUntilNumerical OBJECT-TYPE
    SYNTAX     Counter32
    MAX-ACCESS read-only
    STATUS     current
    DESCRIPTION
            "-- empty --"
    ::= { hmStatusIpv6Dhcpv6ClientPdBindingsEntry 5 }

-- {COLUMN} 1.3.6.1.4.1.248.32.18.1.77.3.2.3.1.6
hmStatusIpv6Dhcpv6ClientPdBindingsEntryValidUntil OBJECT-TYPE
    SYNTAX     DisplayString (SIZE(0..255))
    MAX-ACCESS read-only
    STATUS     current
    DESCRIPTION
            "-- empty --"
    ::= { hmStatusIpv6Dhcpv6ClientPdBindingsEntry 6 }

-- {COLUMN} 1.3.6.1.4.1.248.32.18.1.77.3.2.3.1.7
hmStatusIpv6Dhcpv6ClientPdBindingsEntryExcludedPrefix OBJECT-TYPE
    SYNTAX     DisplayString (SIZE(0..255))
    MAX-ACCESS read-only
    STATUS     current
    DESCRIPTION
            "-- empty --"
    ::= { hmStatusIpv6Dhcpv6ClientPdBindingsEntry 7 }

-- {TABLE} 1.3.6.1.4.1.248.32.18.1.77.3.2.4
hmStatusIpv6Dhcpv6ClientInterfaceStateTable OBJECT-TYPE
    SYNTAX     SEQUENCE OF HmStatusIpv6Dhcpv6ClientInterfaceStateEntry
    MAX-ACCESS not-accessible
    STATUS     current
    DESCRIPTION
            "-- empty --"
    ::= { hmStatusIpv6Dhcpv6Client 4 }

-- {ROW} 1.3.6.1.4.1.248.32.18.1.77.3.2.4.1
hmStatusIpv6Dhcpv6ClientInterfaceStateEntry OBJECT-TYPE
    SYNTAX     HmStatusIpv6Dhcpv6ClientInterfaceStateEntry
    MAX-ACCESS not-accessible
    STATUS     current
    DESCRIPTION
            ""
    INDEX {
            hmStatusIpv6Dhcpv6ClientInterfaceStateEntryInterfaceName
          }
    ::= { hmStatusIpv6Dhcpv6ClientInterfaceStateTable 1 }

HmStatusIpv6Dhcpv6ClientInterfaceStateEntry ::= SEQUENCE {
            hmStatusIpv6Dhcpv6ClientInterfaceStateEntryInterfaceName DisplayString,
            hmStatusIpv6Dhcpv6ClientInterfaceStateEntryMode INTEGER,
            hmStatusIpv6Dhcpv6ClientInterfaceStateEntryRequestPd INTEGER,
            hmStatusIpv6Dhcpv6ClientInterfaceStateEntryReconfNegotiated INTEGER
    }

-- {COLUMN} 1.3.6.1.4.1.248.32.18.1.77.3.2.4.1.1
hmStatusIpv6Dhcpv6ClientInterfaceStateEntryInterfaceName OBJECT-TYPE
    SYNTAX     DisplayString (SIZE(0..255))
    MAX-ACCESS read-only
    STATUS     current
    DESCRIPTION
            "-- empty --"
    ::= { hmStatusIpv6Dhcpv6ClientInterfaceStateEntry 1 }

-- {COLUMN} 1.3.6.1.4.1.248.32.18.1.77.3.2.4.1.2
hmStatusIpv6Dhcpv6ClientInterfaceStateEntryMode OBJECT-TYPE
    SYNTAX     INTEGER {
                  eStateless (0),
                  eStateful (1),
                  eStatic (2)
            }
    MAX-ACCESS read-only
    STATUS     current
    DESCRIPTION
            "-- empty --"
    ::= { hmStatusIpv6Dhcpv6ClientInterfaceStateEntry 2 }

-- {COLUMN} 1.3.6.1.4.1.248.32.18.1.77.3.2.4.1.3
hmStatusIpv6Dhcpv6ClientInterfaceStateEntryRequestPd OBJECT-TYPE
    SYNTAX     INTEGER {
                  eNo (0),
                  eYes (1)
            }
    MAX-ACCESS read-only
    STATUS     current
    DESCRIPTION
            "-- empty --"
    ::= { hmStatusIpv6Dhcpv6ClientInterfaceStateEntry 3 }

-- {COLUMN} 1.3.6.1.4.1.248.32.18.1.77.3.2.4.1.4
hmStatusIpv6Dhcpv6ClientInterfaceStateEntryReconfNegotiated OBJECT-TYPE
    SYNTAX     INTEGER {
                  eNo (0),
                  eYes (1)
            }
    MAX-ACCESS read-only
    STATUS     current
    DESCRIPTION
            "-- empty --"
    ::= { hmStatusIpv6Dhcpv6ClientInterfaceStateEntry 4 }

-- {SCALAR} 1.3.6.1.4.1.248.32.18.1.77.3.2.5
hmStatusIpv6Dhcpv6ClientRelease OBJECT-TYPE
    SYNTAX     DisplayString
    MAX-ACCESS read-write
    STATUS     current
    DESCRIPTION
            "-- empty --"
    ::= { hmStatusIpv6Dhcpv6Client 5 }

-- {SCALAR} 1.3.6.1.4.1.248.32.18.1.77.3.2.6
hmStatusIpv6Dhcpv6ClientClientId OBJECT-TYPE
    SYNTAX     DisplayString (SIZE(0..97))
    MAX-ACCESS read-only
    STATUS     current
    DESCRIPTION
            "-- empty --"
    ::= { hmStatusIpv6Dhcpv6Client 6 }

-- {NODE} 1.3.6.1.4.1.248.32.18.1.77.3.3
hmStatusIpv6Dhcpv6RelayAgent OBJECT IDENTIFIER ::= { hmStatusIpv6Dhcpv6 3 }

-- {SCALAR} 1.3.6.1.4.1.248.32.18.1.77.4
hmStatusIpv6Interfaces OBJECT-TYPE
    SYNTAX     Integer32 (0..2147483647)
    MAX-ACCESS read-only
    STATUS     current
    DESCRIPTION
            "-- empty --"
    ::= { hmStatusIpv6 4 }

-- {SCALAR} 1.3.6.1.4.1.248.32.18.1.77.5
hmStatusIpv6ActIpRoutingTab OBJECT-TYPE
    SYNTAX     Integer32 (0..2147483647)
    MAX-ACCESS read-only
    STATUS     current
    DESCRIPTION
            "-- empty --"
    ::= { hmStatusIpv6 5 }

-- {NODE} 1.3.6.1.4.1.248.32.18.1.77.6
hmStatusIpv6Network OBJECT IDENTIFIER ::= { hmStatusIpv6 6 }

-- {SCALAR} 1.3.6.1.4.1.248.32.18.1.77.6.1
hmStatusIpv6NetworkAddresses OBJECT-TYPE
    SYNTAX     Integer32 (0..2147483647)
    MAX-ACCESS read-only
    STATUS     current
    DESCRIPTION
            "-- empty --"
    ::= { hmStatusIpv6Network 1 }

-- {SCALAR} 1.3.6.1.4.1.248.32.18.1.77.6.2
hmStatusIpv6NetworkParameter OBJECT-TYPE
    SYNTAX     Integer32 (0..2147483647)
    MAX-ACCESS read-only
    STATUS     current
    DESCRIPTION
            "-- empty --"
    ::= { hmStatusIpv6Network 2 }

-- {NODE} 1.3.6.1.4.1.248.32.18.1.77.7
hmStatusIpv6RouterAdv OBJECT IDENTIFIER ::= { hmStatusIpv6 7 }

-- {SCALAR} 1.3.6.1.4.1.248.32.18.1.77.7.1
hmStatusIpv6RouterAdvInterfaceOptions OBJECT-TYPE
    SYNTAX     Integer32 (0..2147483647)
    MAX-ACCESS read-only
    STATUS     current
    DESCRIPTION
            "-- empty --"
    ::= { hmStatusIpv6RouterAdv 1 }

-- {SCALAR} 1.3.6.1.4.1.248.32.18.1.77.7.2
hmStatusIpv6RouterAdvPrefixOptions OBJECT-TYPE
    SYNTAX     Integer32 (0..2147483647)
    MAX-ACCESS read-only
    STATUS     current
    DESCRIPTION
            "-- empty --"
    ::= { hmStatusIpv6RouterAdv 2 }

-- {NODE} 1.3.6.1.4.1.248.32.18.1.77.8
hmStatusIpv6Tunnel OBJECT IDENTIFIER ::= { hmStatusIpv6 8 }

-- {SCALAR} 1.3.6.1.4.1.248.32.18.1.77.8.1
hmStatusIpv6Tunnel6in4 OBJECT-TYPE
    SYNTAX     Integer32 (0..2147483647)
    MAX-ACCESS read-only
    STATUS     current
    DESCRIPTION
            "-- empty --"
    ::= { hmStatusIpv6Tunnel 1 }

-- {SCALAR} 1.3.6.1.4.1.248.32.18.1.77.8.2
hmStatusIpv6Tunnel6rd OBJECT-TYPE
    SYNTAX     Integer32 (0..2147483647)
    MAX-ACCESS read-only
    STATUS     current
    DESCRIPTION
            "-- empty --"
    ::= { hmStatusIpv6Tunnel 2 }

-- {SCALAR} 1.3.6.1.4.1.248.32.18.1.77.8.3
hmStatusIpv6Tunnel6rdBorderRelay OBJECT-TYPE
    SYNTAX     Integer32 (0..2147483647)
    MAX-ACCESS read-only
    STATUS     current
    DESCRIPTION
            "-- empty --"
    ::= { hmStatusIpv6Tunnel 3 }

-- {SCALAR} 1.3.6.1.4.1.248.32.18.1.77.8.4
hmStatusIpv6Tunnel6to4 OBJECT-TYPE
    SYNTAX     Integer32 (0..2147483647)
    MAX-ACCESS read-only
    STATUS     current
    DESCRIPTION
            "-- empty --"
    ::= { hmStatusIpv6Tunnel 4 }

-- {NODE} 1.3.6.1.4.1.248.32.18.1.77.9
hmStatusIpv6Firewall OBJECT IDENTIFIER ::= { hmStatusIpv6 9 }

-- {TABLE} 1.3.6.1.4.1.248.32.18.1.77.9.1
hmStatusIpv6FirewallLogTableTable OBJECT-TYPE
    SYNTAX     SEQUENCE OF HmStatusIpv6FirewallLogTableEntry
    MAX-ACCESS not-accessible
    STATUS     current
    DESCRIPTION
            "-- empty --"
    ::= { hmStatusIpv6Firewall 1 }

-- {ROW} 1.3.6.1.4.1.248.32.18.1.77.9.1.1
hmStatusIpv6FirewallLogTableEntry OBJECT-TYPE
    SYNTAX     HmStatusIpv6FirewallLogTableEntry
    MAX-ACCESS not-accessible
    STATUS     current
    DESCRIPTION
            ""
    INDEX {
            hmStatusIpv6FirewallLogTableEntryIdx
          }
    ::= { hmStatusIpv6FirewallLogTableTable 1 }

HmStatusIpv6FirewallLogTableEntry ::= SEQUENCE {
            hmStatusIpv6FirewallLogTableEntryIdx Integer32,
            hmStatusIpv6FirewallLogTableEntrySystemTime DisplayString,
            hmStatusIpv6FirewallLogTableEntrySrcAddress DisplayString,
            hmStatusIpv6FirewallLogTableEntryDstAddress DisplayString,
            hmStatusIpv6FirewallLogTableEntryProt Integer32,
            hmStatusIpv6FirewallLogTableEntrySrcPort Integer32,
            hmStatusIpv6FirewallLogTableEntryDstPort Integer32,
            hmStatusIpv6FirewallLogTableEntryFilterRule DisplayString,
            hmStatusIpv6FirewallLogTableEntryLimit Integer32,
            hmStatusIpv6FirewallLogTableEntryThreshold Integer32,
            hmStatusIpv6FirewallLogTableEntryAction Integer32
    }

-- {COLUMN} 1.3.6.1.4.1.248.32.18.1.77.9.1.1.1
hmStatusIpv6FirewallLogTableEntryIdx OBJECT-TYPE
    SYNTAX     Integer32 (0..65535)
    MAX-ACCESS read-only
    STATUS     current
    DESCRIPTION
            "-- empty --"
    ::= { hmStatusIpv6FirewallLogTableEntry 1 }

-- {COLUMN} 1.3.6.1.4.1.248.32.18.1.77.9.1.1.2
hmStatusIpv6FirewallLogTableEntrySystemTime OBJECT-TYPE
    SYNTAX     DisplayString (SIZE(0..19))
    MAX-ACCESS read-only
    STATUS     current
    DESCRIPTION
            "-- empty --"
    ::= { hmStatusIpv6FirewallLogTableEntry 2 }

-- {COLUMN} 1.3.6.1.4.1.248.32.18.1.77.9.1.1.3
hmStatusIpv6FirewallLogTableEntrySrcAddress OBJECT-TYPE
    SYNTAX     DisplayString (SIZE(0..255))
    MAX-ACCESS read-only
    STATUS     current
    DESCRIPTION
            "-- empty --"
    ::= { hmStatusIpv6FirewallLogTableEntry 3 }

-- {COLUMN} 1.3.6.1.4.1.248.32.18.1.77.9.1.1.4
hmStatusIpv6FirewallLogTableEntryDstAddress OBJECT-TYPE
    SYNTAX     DisplayString (SIZE(0..255))
    MAX-ACCESS read-only
    STATUS     current
    DESCRIPTION
            "-- empty --"
    ::= { hmStatusIpv6FirewallLogTableEntry 4 }

-- {COLUMN} 1.3.6.1.4.1.248.32.18.1.77.9.1.1.5
hmStatusIpv6FirewallLogTableEntryProt OBJECT-TYPE
    SYNTAX     Integer32 (0..255)
    MAX-ACCESS read-only
    STATUS     current
    DESCRIPTION
            "-- empty --"
    ::= { hmStatusIpv6FirewallLogTableEntry 5 }

-- {COLUMN} 1.3.6.1.4.1.248.32.18.1.77.9.1.1.6
hmStatusIpv6FirewallLogTableEntrySrcPort OBJECT-TYPE
    SYNTAX     Integer32 (0..65535)
    MAX-ACCESS read-only
    STATUS     current
    DESCRIPTION
            "-- empty --"
    ::= { hmStatusIpv6FirewallLogTableEntry 6 }

-- {COLUMN} 1.3.6.1.4.1.248.32.18.1.77.9.1.1.7
hmStatusIpv6FirewallLogTableEntryDstPort OBJECT-TYPE
    SYNTAX     Integer32 (0..65535)
    MAX-ACCESS read-only
    STATUS     current
    DESCRIPTION
            "-- empty --"
    ::= { hmStatusIpv6FirewallLogTableEntry 7 }

-- {COLUMN} 1.3.6.1.4.1.248.32.18.1.77.9.1.1.8
hmStatusIpv6FirewallLogTableEntryFilterRule OBJECT-TYPE
    SYNTAX     DisplayString (SIZE(0..69))
    MAX-ACCESS read-only
    STATUS     current
    DESCRIPTION
            "-- empty --"
    ::= { hmStatusIpv6FirewallLogTableEntry 8 }

-- {COLUMN} 1.3.6.1.4.1.248.32.18.1.77.9.1.1.9
hmStatusIpv6FirewallLogTableEntryLimit OBJECT-TYPE
    SYNTAX     Integer32 (0..2147483647)
    MAX-ACCESS read-only
    STATUS     current
    DESCRIPTION
            "-- empty --"
    ::= { hmStatusIpv6FirewallLogTableEntry 9 }

-- {COLUMN} 1.3.6.1.4.1.248.32.18.1.77.9.1.1.10
hmStatusIpv6FirewallLogTableEntryThreshold OBJECT-TYPE
    SYNTAX     Integer32 (0..2147483647)
    MAX-ACCESS read-only
    STATUS     current
    DESCRIPTION
            "-- empty --"
    ::= { hmStatusIpv6FirewallLogTableEntry 10 }

-- {COLUMN} 1.3.6.1.4.1.248.32.18.1.77.9.1.1.11
hmStatusIpv6FirewallLogTableEntryAction OBJECT-TYPE
    SYNTAX     Integer32 (0..2147483647)
    MAX-ACCESS read-only
    STATUS     current
    DESCRIPTION
            "-- empty --"
    ::= { hmStatusIpv6FirewallLogTableEntry 11 }

-- {SCALAR} 1.3.6.1.4.1.248.32.18.1.77.9.2
hmStatusIpv6FirewallForwardingFilter OBJECT-TYPE
    SYNTAX     Integer32 (0..2147483647)
    MAX-ACCESS read-only
    STATUS     current
    DESCRIPTION
            "-- empty --"
    ::= { hmStatusIpv6Firewall 2 }

-- {SCALAR} 1.3.6.1.4.1.248.32.18.1.77.9.3
hmStatusIpv6FirewallInboundFilter OBJECT-TYPE
    SYNTAX     Integer32 (0..2147483647)
    MAX-ACCESS read-only
    STATUS     current
    DESCRIPTION
            "-- empty --"
    ::= { hmStatusIpv6Firewall 3 }

-- {SCALAR} 1.3.6.1.4.1.248.32.18.1.77.9.4
hmStatusIpv6FirewallForwardingSessions OBJECT-TYPE
    SYNTAX     Integer32 (0..2147483647)
    MAX-ACCESS read-only
    STATUS     current
    DESCRIPTION
            "-- empty --"
    ::= { hmStatusIpv6Firewall 4 }

-- {SCALAR} 1.3.6.1.4.1.248.32.18.1.77.9.5
hmStatusIpv6FirewallInboundSessions OBJECT-TYPE
    SYNTAX     Integer32 (0..2147483647)
    MAX-ACCESS read-only
    STATUS     current
    DESCRIPTION
            "-- empty --"
    ::= { hmStatusIpv6Firewall 5 }

-- {SCALAR} 1.3.6.1.4.1.248.32.18.1.77.9.6
hmStatusIpv6FirewallForwardingOpenPorts OBJECT-TYPE
    SYNTAX     Integer32 (0..2147483647)
    MAX-ACCESS read-only
    STATUS     current
    DESCRIPTION
            "-- empty --"
    ::= { hmStatusIpv6Firewall 6 }

-- {SCALAR} 1.3.6.1.4.1.248.32.18.1.77.9.7
hmStatusIpv6FirewallHostBlockList OBJECT-TYPE
    SYNTAX     Integer32 (0..2147483647)
    MAX-ACCESS read-only
    STATUS     current
    DESCRIPTION
            "-- empty --"
    ::= { hmStatusIpv6Firewall 7 }

-- {SCALAR} 1.3.6.1.4.1.248.32.18.1.77.9.8
hmStatusIpv6FirewallPortBlockList OBJECT-TYPE
    SYNTAX     Integer32 (0..2147483647)
    MAX-ACCESS read-only
    STATUS     current
    DESCRIPTION
            "-- empty --"
    ::= { hmStatusIpv6Firewall 8 }

-- {SCALAR} 1.3.6.1.4.1.248.32.18.1.77.9.9
hmStatusIpv6FirewallHalfOpenConnections OBJECT-TYPE
    SYNTAX     Integer32 (0..2147483647)
    MAX-ACCESS read-only
    STATUS     current
    DESCRIPTION
            "-- empty --"
    ::= { hmStatusIpv6Firewall 9 }

-- {NODE} 1.3.6.1.4.1.248.32.18.1.80
hmStatusRelays OBJECT IDENTIFIER ::= { hmStatus 80 }

-- {SCALAR} 1.3.6.1.4.1.248.32.18.1.80.1
hmStatusRelaysRelay1 OBJECT-TYPE
    SYNTAX     INTEGER {
                  eNo (0),
                  eYes (1)
            }
    MAX-ACCESS read-only
    STATUS     current
    DESCRIPTION
            "-- empty --"
    ::= { hmStatusRelays 1 }

-- {SCALAR} 1.3.6.1.4.1.248.32.18.1.80.2
hmStatusRelaysRelay2 OBJECT-TYPE
    SYNTAX     INTEGER {
                  eNo (0),
                  eYes (1)
            }
    MAX-ACCESS read-only
    STATUS     current
    DESCRIPTION
            "-- empty --"
    ::= { hmStatusRelays 2 }

-- {NODE} 1.3.6.1.4.1.248.32.18.1.81
hmStatusDsLite OBJECT IDENTIFIER ::= { hmStatus 81 }

-- {SCALAR} 1.3.6.1.4.1.248.32.18.1.81.1
hmStatusDsLiteRxPackets OBJECT-TYPE
    SYNTAX     Integer32 (0..2147483647)
    MAX-ACCESS read-only
    STATUS     current
    DESCRIPTION
            "-- empty --"
    ::= { hmStatusDsLite 1 }

-- {SCALAR} 1.3.6.1.4.1.248.32.18.1.81.2
hmStatusDsLiteTxPackets OBJECT-TYPE
    SYNTAX     Integer32 (0..2147483647)
    MAX-ACCESS read-only
    STATUS     current
    DESCRIPTION
            "-- empty --"
    ::= { hmStatusDsLite 2 }

-- {SCALAR} 1.3.6.1.4.1.248.32.18.1.81.3
hmStatusDsLiteQueueErrors OBJECT-TYPE
    SYNTAX     Integer32 (0..2147483647)
    MAX-ACCESS read-only
    STATUS     current
    DESCRIPTION
            "-- empty --"
    ::= { hmStatusDsLite 3 }

-- {TABLE} 1.3.6.1.4.1.248.32.18.1.81.4
hmStatusDsLiteConnectionsTable OBJECT-TYPE
    SYNTAX     SEQUENCE OF HmStatusDsLiteConnectionsEntry
    MAX-ACCESS not-accessible
    STATUS     current
    DESCRIPTION
            "-- empty --"
    ::= { hmStatusDsLite 4 }

-- {ROW} 1.3.6.1.4.1.248.32.18.1.81.4.1
hmStatusDsLiteConnectionsEntry OBJECT-TYPE
    SYNTAX     HmStatusDsLiteConnectionsEntry
    MAX-ACCESS not-accessible
    STATUS     current
    DESCRIPTION
            ""
    INDEX {
            hmStatusDsLiteConnectionsEntryPeer
          }
    ::= { hmStatusDsLiteConnectionsTable 1 }

HmStatusDsLiteConnectionsEntry ::= SEQUENCE {
            hmStatusDsLiteConnectionsEntryPeer DisplayString,
            hmStatusDsLiteConnectionsEntryState INTEGER,
            hmStatusDsLiteConnectionsEntryLastError INTEGER,
            hmStatusDsLiteConnectionsEntryIpv4Address IpAddress,
            hmStatusDsLiteConnectionsEntryPhysConn DisplayString,
            hmStatusDsLiteConnectionsEntryAftrName DisplayString,
            hmStatusDsLiteConnectionsEntryAftrIpv6Address DisplayString,
            hmStatusDsLiteConnectionsEntryConnTime Gauge32
    }

-- {COLUMN} 1.3.6.1.4.1.248.32.18.1.81.4.1.1
hmStatusDsLiteConnectionsEntryPeer OBJECT-TYPE
    SYNTAX     DisplayString (SIZE(0..16))
    MAX-ACCESS read-only
    STATUS     current
    DESCRIPTION
            "-- empty --"
    ::= { hmStatusDsLiteConnectionsEntry 1 }

-- {COLUMN} 1.3.6.1.4.1.248.32.18.1.81.4.1.2
hmStatusDsLiteConnectionsEntryState OBJECT-TYPE
    SYNTAX     INTEGER {
                  eInit (0),
                  eSetupWan (1),
                  eReady (2),
                  eWaitForCb (3),
                  eDial (4),
                  eIncomingCall (5),
                  eProtocol (6),
                  eConnection (7),
                  eDisconnecting (8),
                  eCallBack (9),
                  eBundleConnect (10),
                  eProtocol2 (11),
                  eReserved (12),
                  eBundle (13)
            }
    MAX-ACCESS read-only
    STATUS     current
    DESCRIPTION
            "-- empty --"
    ::= { hmStatusDsLiteConnectionsEntry 2 }

-- {COLUMN} 1.3.6.1.4.1.248.32.18.1.81.4.1.3
hmStatusDsLiteConnectionsEntryLastError OBJECT-TYPE
    SYNTAX     INTEGER {
                  eNone (0),
                  eIcmpConnError (275),
                  eDnsResolutionFailed (20481),
                  eNoRouteToGateway (20482),
                  eNoGatewayByDhcp (20483),
                  eInvalidGatewayAddress (20484),
                  eMultipleGatewayUsage (20485)
            }
    MAX-ACCESS read-write
    STATUS     current
    DESCRIPTION
            "-- empty --"
    ::= { hmStatusDsLiteConnectionsEntry 3 }

-- {COLUMN} 1.3.6.1.4.1.248.32.18.1.81.4.1.4
hmStatusDsLiteConnectionsEntryIpv4Address OBJECT-TYPE
    SYNTAX     IpAddress
    MAX-ACCESS read-only
    STATUS     current
    DESCRIPTION
            "-- empty --"
    ::= { hmStatusDsLiteConnectionsEntry 4 }

-- {COLUMN} 1.3.6.1.4.1.248.32.18.1.81.4.1.5
hmStatusDsLiteConnectionsEntryPhysConn OBJECT-TYPE
    SYNTAX     DisplayString (SIZE(0..16))
    MAX-ACCESS read-only
    STATUS     current
    DESCRIPTION
            "-- empty --"
    ::= { hmStatusDsLiteConnectionsEntry 5 }

-- {COLUMN} 1.3.6.1.4.1.248.32.18.1.81.4.1.6
hmStatusDsLiteConnectionsEntryAftrName OBJECT-TYPE
    SYNTAX     DisplayString (SIZE(0..64))
    MAX-ACCESS read-only
    STATUS     current
    DESCRIPTION
            "-- empty --"
    ::= { hmStatusDsLiteConnectionsEntry 6 }

-- {COLUMN} 1.3.6.1.4.1.248.32.18.1.81.4.1.7
hmStatusDsLiteConnectionsEntryAftrIpv6Address OBJECT-TYPE
    SYNTAX     DisplayString (SIZE(0..255))
    MAX-ACCESS read-only
    STATUS     current
    DESCRIPTION
            "-- empty --"
    ::= { hmStatusDsLiteConnectionsEntry 7 }

-- {COLUMN} 1.3.6.1.4.1.248.32.18.1.81.4.1.8
hmStatusDsLiteConnectionsEntryConnTime OBJECT-TYPE
    SYNTAX     Gauge32
    MAX-ACCESS read-only
    STATUS     current
    DESCRIPTION
            "-- empty --"
    ::= { hmStatusDsLiteConnectionsEntry 8 }

-- {SCALAR} 1.3.6.1.4.1.248.32.18.1.81.5
hmStatusDsLiteTunnel OBJECT-TYPE
    SYNTAX     Integer32 (0..2147483647)
    MAX-ACCESS read-only
    STATUS     current
    DESCRIPTION
            "-- empty --"
    ::= { hmStatusDsLite 5 }

-- {SCALAR} 1.3.6.1.4.1.248.32.18.1.81.6
hmStatusDsLiteDeleteValues OBJECT-TYPE
    SYNTAX     DisplayString
    MAX-ACCESS read-write
    STATUS     current
    DESCRIPTION
            "-- empty --"
    ::= { hmStatusDsLite 6 }

-- {NODE} 1.3.6.1.4.1.248.32.18.1.82
hmStatusCrypto OBJECT IDENTIFIER ::= { hmStatus 82 }

-- {NODE} 1.3.6.1.4.1.248.32.18.1.82.1
hmStatusCryptoRng OBJECT IDENTIFIER ::= { hmStatusCrypto 1 }

-- {SCALAR} 1.3.6.1.4.1.248.32.18.1.82.1.1
hmStatusCryptoRngState OBJECT-TYPE
    SYNTAX     INTEGER {
                  eNone (0),
                  eNotSeeded (1),
                  ePreSeeded (2),
                  eSeeded (3),
                  eNeedsReseed (4),
                  eError (5)
            }
    MAX-ACCESS read-only
    STATUS     current
    DESCRIPTION
            "-- empty --"
    ::= { hmStatusCryptoRng 1 }

-- {SCALAR} 1.3.6.1.4.1.248.32.18.1.82.1.2
hmStatusCryptoRngCounter OBJECT-TYPE
    SYNTAX     Integer32 (0..2147483647)
    MAX-ACCESS read-only
    STATUS     current
    DESCRIPTION
            "-- empty --"
    ::= { hmStatusCryptoRng 2 }

-- {SCALAR} 1.3.6.1.4.1.248.32.18.1.82.1.3
hmStatusCryptoRngPercent OBJECT-TYPE
    SYNTAX     Integer32 (0..65535)
    MAX-ACCESS read-only
    STATUS     current
    DESCRIPTION
            "-- empty --"
    ::= { hmStatusCryptoRng 3 }

-- {SCALAR} 1.3.6.1.4.1.248.32.18.1.82.1.4
hmStatusCryptoRngWriteInterval OBJECT-TYPE
    SYNTAX     Integer32 (0..2147483647)
    MAX-ACCESS read-only
    STATUS     current
    DESCRIPTION
            "-- empty --"
    ::= { hmStatusCryptoRng 4 }

-- {NODE} 1.3.6.1.4.1.248.32.18.1.84
hmStatusL2tp OBJECT IDENTIFIER ::= { hmStatus 84 }

-- {SCALAR} 1.3.6.1.4.1.248.32.18.1.84.1
hmStatusL2tpRxPackets OBJECT-TYPE
    SYNTAX     Integer32 (0..2147483647)
    MAX-ACCESS read-only
    STATUS     current
    DESCRIPTION
            "-- empty --"
    ::= { hmStatusL2tp 1 }

-- {SCALAR} 1.3.6.1.4.1.248.32.18.1.84.2
hmStatusL2tpTxPackets OBJECT-TYPE
    SYNTAX     Integer32 (0..2147483647)
    MAX-ACCESS read-only
    STATUS     current
    DESCRIPTION
            "-- empty --"
    ::= { hmStatusL2tp 2 }

-- {SCALAR} 1.3.6.1.4.1.248.32.18.1.84.3
hmStatusL2tpTxRetries OBJECT-TYPE
    SYNTAX     Integer32 (0..2147483647)
    MAX-ACCESS read-only
    STATUS     current
    DESCRIPTION
            "-- empty --"
    ::= { hmStatusL2tp 3 }

-- {SCALAR} 1.3.6.1.4.1.248.32.18.1.84.4
hmStatusL2tpCallErrors OBJECT-TYPE
    SYNTAX     Integer32 (0..2147483647)
    MAX-ACCESS read-only
    STATUS     current
    DESCRIPTION
            "-- empty --"
    ::= { hmStatusL2tp 4 }

-- {TABLE} 1.3.6.1.4.1.248.32.18.1.84.5
hmStatusL2tpEndpointsTable OBJECT-TYPE
    SYNTAX     SEQUENCE OF HmStatusL2tpEndpointsEntry
    MAX-ACCESS not-accessible
    STATUS     current
    DESCRIPTION
            "-- empty --"
    ::= { hmStatusL2tp 5 }

-- {ROW} 1.3.6.1.4.1.248.32.18.1.84.5.1
hmStatusL2tpEndpointsEntry OBJECT-TYPE
    SYNTAX     HmStatusL2tpEndpointsEntry
    MAX-ACCESS not-accessible
    STATUS     current
    DESCRIPTION
            ""
    INDEX {
            hmStatusL2tpEndpointsEntryL2tpEndpoint
          }
    ::= { hmStatusL2tpEndpointsTable 1 }

HmStatusL2tpEndpointsEntry ::= SEQUENCE {
            hmStatusL2tpEndpointsEntryL2tpEndpoint DisplayString,
            hmStatusL2tpEndpointsEntryState INTEGER,
            hmStatusL2tpEndpointsEntryLastError INTEGER,
            hmStatusL2tpEndpointsEntryMode INTEGER,
            hmStatusL2tpEndpointsEntryPhysConnection DisplayString,
            hmStatusL2tpEndpointsEntryGateway DisplayString,
            hmStatusL2tpEndpointsEntrySessions Integer32,
            hmStatusL2tpEndpointsEntryConnTime Gauge32,
            hmStatusL2tpEndpointsEntryEmbeddedErrorMessage DisplayString
    }

-- {COLUMN} 1.3.6.1.4.1.248.32.18.1.84.5.1.1
hmStatusL2tpEndpointsEntryL2tpEndpoint OBJECT-TYPE
    SYNTAX     DisplayString (SIZE(0..16))
    MAX-ACCESS read-only
    STATUS     current
    DESCRIPTION
            "-- empty --"
    ::= { hmStatusL2tpEndpointsEntry 1 }

-- {COLUMN} 1.3.6.1.4.1.248.32.18.1.84.5.1.2
hmStatusL2tpEndpointsEntryState OBJECT-TYPE
    SYNTAX     INTEGER {
                  eInvalid (-1),
                  eDestroying (0),
                  eIdle (1),
                  eWaitCtlReply (2),
                  eWaitCtlConn (3),
                  eWaitEstablish (4),
                  eEstablished (5),
                  eAuthenticating (6)
            }
    MAX-ACCESS read-only
    STATUS     current
    DESCRIPTION
            "-- empty --"
    ::= { hmStatusL2tpEndpointsEntry 2 }

-- {COLUMN} 1.3.6.1.4.1.248.32.18.1.84.5.1.3
hmStatusL2tpEndpointsEntryLastError OBJECT-TYPE
    SYNTAX     INTEGER {
                  eNone (0),
                  eDnsResolutionFailed (1),
                  eNoRouteToGateway (2),
                  eNoResponse (4),
                  eMessageTimeout (5),
                  eTunnelAlreadyExists (19),
                  eAuthorizationFailed (20),
                  eBadProtocolVersion (21),
                  eShuttingDown (22),
                  eStateMachineError (23),
                  eNoTunnelExists (33),
                  eInvalidLength (34),
                  eInvalidValue (35),
                  eNoRessources (36),
                  eInvalidSessionId (37),
                  eVendorSpecificError (38),
                  eTryAnother (39),
                  eUnknownMandatoryAttribute (40),
                  eUnknown (255)
            }
    MAX-ACCESS read-write
    STATUS     current
    DESCRIPTION
            "-- empty --"
    ::= { hmStatusL2tpEndpointsEntry 3 }

-- {COLUMN} 1.3.6.1.4.1.248.32.18.1.84.5.1.4
hmStatusL2tpEndpointsEntryMode OBJECT-TYPE
    SYNTAX     INTEGER {
                  eLac (0),
                  eLns (1)
            }
    MAX-ACCESS read-only
    STATUS     current
    DESCRIPTION
            "-- empty --"
    ::= { hmStatusL2tpEndpointsEntry 4 }

-- {COLUMN} 1.3.6.1.4.1.248.32.18.1.84.5.1.5
hmStatusL2tpEndpointsEntryPhysConnection OBJECT-TYPE
    SYNTAX     DisplayString (SIZE(0..16))
    MAX-ACCESS read-only
    STATUS     current
    DESCRIPTION
            "-- empty --"
    ::= { hmStatusL2tpEndpointsEntry 5 }

-- {COLUMN} 1.3.6.1.4.1.248.32.18.1.84.5.1.6
hmStatusL2tpEndpointsEntryGateway OBJECT-TYPE
    SYNTAX     DisplayString (SIZE(0..39))
    MAX-ACCESS read-only
    STATUS     current
    DESCRIPTION
            "-- empty --"
    ::= { hmStatusL2tpEndpointsEntry 6 }

-- {COLUMN} 1.3.6.1.4.1.248.32.18.1.84.5.1.7
hmStatusL2tpEndpointsEntrySessions OBJECT-TYPE
    SYNTAX     Integer32 (0..65535)
    MAX-ACCESS read-only
    STATUS     current
    DESCRIPTION
            "-- empty --"
    ::= { hmStatusL2tpEndpointsEntry 7 }

-- {COLUMN} 1.3.6.1.4.1.248.32.18.1.84.5.1.8
hmStatusL2tpEndpointsEntryConnTime OBJECT-TYPE
    SYNTAX     Gauge32
    MAX-ACCESS read-only
    STATUS     current
    DESCRIPTION
            "-- empty --"
    ::= { hmStatusL2tpEndpointsEntry 8 }

-- {COLUMN} 1.3.6.1.4.1.248.32.18.1.84.5.1.9
hmStatusL2tpEndpointsEntryEmbeddedErrorMessage OBJECT-TYPE
    SYNTAX     DisplayString (SIZE(0..32))
    MAX-ACCESS read-only
    STATUS     current
    DESCRIPTION
            "-- empty --"
    ::= { hmStatusL2tpEndpointsEntry 9 }

-- {SCALAR} 1.3.6.1.4.1.248.32.18.1.84.6
hmStatusL2tpNumEndpoints OBJECT-TYPE
    SYNTAX     Integer32 (0..2147483647)
    MAX-ACCESS read-only
    STATUS     current
    DESCRIPTION
            "-- empty --"
    ::= { hmStatusL2tp 6 }

-- {TABLE} 1.3.6.1.4.1.248.32.18.1.84.7
hmStatusL2tpConnectionsTable OBJECT-TYPE
    SYNTAX     SEQUENCE OF HmStatusL2tpConnectionsEntry
    MAX-ACCESS not-accessible
    STATUS     current
    DESCRIPTION
            "-- empty --"
    ::= { hmStatusL2tp 7 }

-- {ROW} 1.3.6.1.4.1.248.32.18.1.84.7.1
hmStatusL2tpConnectionsEntry OBJECT-TYPE
    SYNTAX     HmStatusL2tpConnectionsEntry
    MAX-ACCESS not-accessible
    STATUS     current
    DESCRIPTION
            ""
    INDEX {
            hmStatusL2tpConnectionsEntryPeer
          }
    ::= { hmStatusL2tpConnectionsTable 1 }

HmStatusL2tpConnectionsEntry ::= SEQUENCE {
            hmStatusL2tpConnectionsEntryPeer DisplayString,
            hmStatusL2tpConnectionsEntryState INTEGER,
            hmStatusL2tpConnectionsEntryLastError INTEGER,
            hmStatusL2tpConnectionsEntryMode INTEGER,
            hmStatusL2tpConnectionsEntryShTime Integer32,
            hmStatusL2tpConnectionsEntryL2tpEndpoint DisplayString,
            hmStatusL2tpConnectionsEntryPeerAddress IpAddress,
            hmStatusL2tpConnectionsEntryIpAddress IpAddress,
            hmStatusL2tpConnectionsEntryDnsDefault IpAddress,
            hmStatusL2tpConnectionsEntryDnsBackup IpAddress,
            hmStatusL2tpConnectionsEntryNbnsDefault IpAddress,
            hmStatusL2tpConnectionsEntryNbnsBackup IpAddress,
            hmStatusL2tpConnectionsEntryConnTime Gauge32
    }

-- {COLUMN} 1.3.6.1.4.1.248.32.18.1.84.7.1.1
hmStatusL2tpConnectionsEntryPeer OBJECT-TYPE
    SYNTAX     DisplayString (SIZE(0..16))
    MAX-ACCESS read-only
    STATUS     current
    DESCRIPTION
            "-- empty --"
    ::= { hmStatusL2tpConnectionsEntry 1 }

-- {COLUMN} 1.3.6.1.4.1.248.32.18.1.84.7.1.2
hmStatusL2tpConnectionsEntryState OBJECT-TYPE
    SYNTAX     INTEGER {
                  eInit (0),
                  eSetupWan (1),
                  eReady (2),
                  eWaitForCb (3),
                  eDial (4),
                  eIncomingCall (5),
                  eProtocol (6),
                  eConnection (7),
                  eDisconnecting (8),
                  eCallBack (9),
                  eBundleConnect (10),
                  eProtocol2 (11),
                  eReserved (12),
                  eBundle (13)
            }
    MAX-ACCESS read-only
    STATUS     current
    DESCRIPTION
            "-- empty --"
    ::= { hmStatusL2tpConnectionsEntry 2 }

-- {COLUMN} 1.3.6.1.4.1.248.32.18.1.84.7.1.3
hmStatusL2tpConnectionsEntryLastError OBJECT-TYPE
    SYNTAX     INTEGER {
                  eNone (0),
                  eRemoteDoubled (267),
                  eIcmpConnError (275),
                  eChargeLocked (283),
                  eRemoteDisconnected (17153),
                  eManualDisconnect (17154),
                  eShortholdExpired (17155),
                  ePhysicalDisconnected (17156),
                  eInvalidPhysicalChannel (17157),
                  eDynamicVpnReconnect (17158),
                  eConfigurationChanged (17159),
                  eRemovedFromConfig (17160),
                  eLcpRejected (32768),
                  eAuthError (32769),
                  eAuthRejected (32770),
                  eLcpConnError (32771),
                  ePapRejected (32784),
                  ePapRxTimeout (32785),
                  ePapTxTimeout (32786),
                  eWrongPapReq (32787),
                  ePapNakReceived (32788),
                  eUnknPapPeer (32789),
                  eChapRejected (32800),
                  eChapRxTimeout (32801),
                  eChapTxTimeout (32802),
                  eWrongChapResp (32803),
                  eChapFailRecvd (32804),
                  eUnknChapPeer (32805),
                  eIpcpRejected (32832),
                  eCcpRejected (32848),
                  eNoNcpAvailable (33008)
            }
    MAX-ACCESS read-write
    STATUS     current
    DESCRIPTION
            "-- empty --"
    ::= { hmStatusL2tpConnectionsEntry 3 }

-- {COLUMN} 1.3.6.1.4.1.248.32.18.1.84.7.1.4
hmStatusL2tpConnectionsEntryMode OBJECT-TYPE
    SYNTAX     INTEGER {
                  ePassive (0),
                  eActive (128)
            }
    MAX-ACCESS read-only
    STATUS     current
    DESCRIPTION
            "-- empty --"
    ::= { hmStatusL2tpConnectionsEntry 4 }

-- {COLUMN} 1.3.6.1.4.1.248.32.18.1.84.7.1.5
hmStatusL2tpConnectionsEntryShTime OBJECT-TYPE
    SYNTAX     Integer32 (0..65535)
    MAX-ACCESS read-only
    STATUS     current
    DESCRIPTION
            "-- empty --"
    ::= { hmStatusL2tpConnectionsEntry 5 }

-- {COLUMN} 1.3.6.1.4.1.248.32.18.1.84.7.1.6
hmStatusL2tpConnectionsEntryL2tpEndpoint OBJECT-TYPE
    SYNTAX     DisplayString (SIZE(0..16))
    MAX-ACCESS read-only
    STATUS     current
    DESCRIPTION
            "-- empty --"
    ::= { hmStatusL2tpConnectionsEntry 6 }

-- {COLUMN} 1.3.6.1.4.1.248.32.18.1.84.7.1.7
hmStatusL2tpConnectionsEntryPeerAddress OBJECT-TYPE
    SYNTAX     IpAddress
    MAX-ACCESS read-only
    STATUS     current
    DESCRIPTION
            "-- empty --"
    ::= { hmStatusL2tpConnectionsEntry 7 }

-- {COLUMN} 1.3.6.1.4.1.248.32.18.1.84.7.1.8
hmStatusL2tpConnectionsEntryIpAddress OBJECT-TYPE
    SYNTAX     IpAddress
    MAX-ACCESS read-only
    STATUS     current
    DESCRIPTION
            "-- empty --"
    ::= { hmStatusL2tpConnectionsEntry 8 }

-- {COLUMN} 1.3.6.1.4.1.248.32.18.1.84.7.1.9
hmStatusL2tpConnectionsEntryDnsDefault OBJECT-TYPE
    SYNTAX     IpAddress
    MAX-ACCESS read-only
    STATUS     current
    DESCRIPTION
            "-- empty --"
    ::= { hmStatusL2tpConnectionsEntry 9 }

-- {COLUMN} 1.3.6.1.4.1.248.32.18.1.84.7.1.10
hmStatusL2tpConnectionsEntryDnsBackup OBJECT-TYPE
    SYNTAX     IpAddress
    MAX-ACCESS read-only
    STATUS     current
    DESCRIPTION
            "-- empty --"
    ::= { hmStatusL2tpConnectionsEntry 10 }

-- {COLUMN} 1.3.6.1.4.1.248.32.18.1.84.7.1.11
hmStatusL2tpConnectionsEntryNbnsDefault OBJECT-TYPE
    SYNTAX     IpAddress
    MAX-ACCESS read-only
    STATUS     current
    DESCRIPTION
            "-- empty --"
    ::= { hmStatusL2tpConnectionsEntry 11 }

-- {COLUMN} 1.3.6.1.4.1.248.32.18.1.84.7.1.12
hmStatusL2tpConnectionsEntryNbnsBackup OBJECT-TYPE
    SYNTAX     IpAddress
    MAX-ACCESS read-only
    STATUS     current
    DESCRIPTION
            "-- empty --"
    ::= { hmStatusL2tpConnectionsEntry 12 }

-- {COLUMN} 1.3.6.1.4.1.248.32.18.1.84.7.1.13
hmStatusL2tpConnectionsEntryConnTime OBJECT-TYPE
    SYNTAX     Gauge32
    MAX-ACCESS read-only
    STATUS     current
    DESCRIPTION
            "-- empty --"
    ::= { hmStatusL2tpConnectionsEntry 13 }

-- {SCALAR} 1.3.6.1.4.1.248.32.18.1.84.8
hmStatusL2tpNumConnections OBJECT-TYPE
    SYNTAX     Integer32 (0..2147483647)
    MAX-ACCESS read-only
    STATUS     current
    DESCRIPTION
            "-- empty --"
    ::= { hmStatusL2tp 8 }

-- {SCALAR} 1.3.6.1.4.1.248.32.18.1.84.9
hmStatusL2tpDeleteValues OBJECT-TYPE
    SYNTAX     DisplayString
    MAX-ACCESS read-write
    STATUS     current
    DESCRIPTION
            "-- empty --"
    ::= { hmStatusL2tp 9 }

-- {TABLE} 1.3.6.1.4.1.248.32.18.1.86
hmStatusGreTunnelTable OBJECT-TYPE
    SYNTAX     SEQUENCE OF HmStatusGreTunnelEntry
    MAX-ACCESS not-accessible
    STATUS     current
    DESCRIPTION
            "-- empty --"
    ::= { hmStatus 86 }

-- {ROW} 1.3.6.1.4.1.248.32.18.1.86.1
hmStatusGreTunnelEntry OBJECT-TYPE
    SYNTAX     HmStatusGreTunnelEntry
    MAX-ACCESS not-accessible
    STATUS     current
    DESCRIPTION
            ""
    INDEX {
            hmStatusGreTunnelEntryPeer
          }
    ::= { hmStatusGreTunnelTable 1 }

HmStatusGreTunnelEntry ::= SEQUENCE {
            hmStatusGreTunnelEntryPeer DisplayString,
            hmStatusGreTunnelEntryIpAddress DisplayString,
            hmStatusGreTunnelEntryRtgTag Integer32,
            hmStatusGreTunnelEntryKeyPresent INTEGER,
            hmStatusGreTunnelEntryKeyValue Integer32,
            hmStatusGreTunnelEntryChecksum INTEGER,
            hmStatusGreTunnelEntrySequencing INTEGER,
            hmStatusGreTunnelEntryLoopbackAddress DisplayString
    }

-- {COLUMN} 1.3.6.1.4.1.248.32.18.1.86.1.1
hmStatusGreTunnelEntryPeer OBJECT-TYPE
    SYNTAX     DisplayString (SIZE(0..16))
    MAX-ACCESS read-only
    STATUS     current
    DESCRIPTION
            "-- empty --"
    ::= { hmStatusGreTunnelEntry 1 }

-- {COLUMN} 1.3.6.1.4.1.248.32.18.1.86.1.3
hmStatusGreTunnelEntryIpAddress OBJECT-TYPE
    SYNTAX     DisplayString (SIZE(0..64))
    MAX-ACCESS read-only
    STATUS     current
    DESCRIPTION
            "-- empty --"
    ::= { hmStatusGreTunnelEntry 3 }

-- {COLUMN} 1.3.6.1.4.1.248.32.18.1.86.1.4
hmStatusGreTunnelEntryRtgTag OBJECT-TYPE
    SYNTAX     Integer32 (0..2147483647)
    MAX-ACCESS read-only
    STATUS     current
    DESCRIPTION
            "-- empty --"
    ::= { hmStatusGreTunnelEntry 4 }

-- {COLUMN} 1.3.6.1.4.1.248.32.18.1.86.1.5
hmStatusGreTunnelEntryKeyPresent OBJECT-TYPE
    SYNTAX     INTEGER {
                  eNo (0),
                  eYes (1)
            }
    MAX-ACCESS read-only
    STATUS     current
    DESCRIPTION
            "-- empty --"
    ::= { hmStatusGreTunnelEntry 5 }

-- {COLUMN} 1.3.6.1.4.1.248.32.18.1.86.1.6
hmStatusGreTunnelEntryKeyValue OBJECT-TYPE
    SYNTAX     Integer32 (0..2147483647)
    MAX-ACCESS read-only
    STATUS     current
    DESCRIPTION
            "-- empty --"
    ::= { hmStatusGreTunnelEntry 6 }

-- {COLUMN} 1.3.6.1.4.1.248.32.18.1.86.1.7
hmStatusGreTunnelEntryChecksum OBJECT-TYPE
    SYNTAX     INTEGER {
                  eNo (0),
                  eYes (1)
            }
    MAX-ACCESS read-only
    STATUS     current
    DESCRIPTION
            "-- empty --"
    ::= { hmStatusGreTunnelEntry 7 }

-- {COLUMN} 1.3.6.1.4.1.248.32.18.1.86.1.8
hmStatusGreTunnelEntrySequencing OBJECT-TYPE
    SYNTAX     INTEGER {
                  eNo (0),
                  eYes (1)
            }
    MAX-ACCESS read-only
    STATUS     current
    DESCRIPTION
            "-- empty --"
    ::= { hmStatusGreTunnelEntry 8 }

-- {COLUMN} 1.3.6.1.4.1.248.32.18.1.86.1.9
hmStatusGreTunnelEntryLoopbackAddress OBJECT-TYPE
    SYNTAX     DisplayString (SIZE(0..16))
    MAX-ACCESS read-only
    STATUS     current
    DESCRIPTION
            "-- empty --"
    ::= { hmStatusGreTunnelEntry 9 }

-- {TABLE} 1.3.6.1.4.1.248.32.18.1.87
hmStatusEogreTunnelTable OBJECT-TYPE
    SYNTAX     SEQUENCE OF HmStatusEogreTunnelEntry
    MAX-ACCESS not-accessible
    STATUS     current
    DESCRIPTION
            "-- empty --"
    ::= { hmStatus 87 }

-- {ROW} 1.3.6.1.4.1.248.32.18.1.87.1
hmStatusEogreTunnelEntry OBJECT-TYPE
    SYNTAX     HmStatusEogreTunnelEntry
    MAX-ACCESS not-accessible
    STATUS     current
    DESCRIPTION
            ""
    INDEX {
            hmStatusEogreTunnelEntryPort
          }
    ::= { hmStatusEogreTunnelTable 1 }

HmStatusEogreTunnelEntry ::= SEQUENCE {
            hmStatusEogreTunnelEntryPort DisplayString,
            hmStatusEogreTunnelEntryActive INTEGER,
            hmStatusEogreTunnelEntryRemoteEndpointAddress DisplayString,
            hmStatusEogreTunnelEntryRtgTag Integer32,
            hmStatusEogreTunnelEntryKeyPresent INTEGER,
            hmStatusEogreTunnelEntryKeyValue Integer32,
            hmStatusEogreTunnelEntryChecksum INTEGER,
            hmStatusEogreTunnelEntrySequencing INTEGER,
            hmStatusEogreTunnelEntryLoopbackAddress DisplayString
    }

-- {COLUMN} 1.3.6.1.4.1.248.32.18.1.87.1.1
hmStatusEogreTunnelEntryPort OBJECT-TYPE
    SYNTAX     DisplayString (SIZE(0..15))
    MAX-ACCESS read-only
    STATUS     current
    DESCRIPTION
            "-- empty --"
    ::= { hmStatusEogreTunnelEntry 1 }

-- {COLUMN} 1.3.6.1.4.1.248.32.18.1.87.1.2
hmStatusEogreTunnelEntryActive OBJECT-TYPE
    SYNTAX     INTEGER {
                  eNo (0),
                  eYes (1)
            }
    MAX-ACCESS read-only
    STATUS     current
    DESCRIPTION
            "-- empty --"
    ::= { hmStatusEogreTunnelEntry 2 }

-- {COLUMN} 1.3.6.1.4.1.248.32.18.1.87.1.3
hmStatusEogreTunnelEntryRemoteEndpointAddress OBJECT-TYPE
    SYNTAX     DisplayString (SIZE(0..64))
    MAX-ACCESS read-only
    STATUS     current
    DESCRIPTION
            "-- empty --"
    ::= { hmStatusEogreTunnelEntry 3 }

-- {COLUMN} 1.3.6.1.4.1.248.32.18.1.87.1.4
hmStatusEogreTunnelEntryRtgTag OBJECT-TYPE
    SYNTAX     Integer32 (0..2147483647)
    MAX-ACCESS read-only
    STATUS     current
    DESCRIPTION
            "-- empty --"
    ::= { hmStatusEogreTunnelEntry 4 }

-- {COLUMN} 1.3.6.1.4.1.248.32.18.1.87.1.5
hmStatusEogreTunnelEntryKeyPresent OBJECT-TYPE
    SYNTAX     INTEGER {
                  eNo (0),
                  eYes (1)
            }
    MAX-ACCESS read-only
    STATUS     current
    DESCRIPTION
            "-- empty --"
    ::= { hmStatusEogreTunnelEntry 5 }

-- {COLUMN} 1.3.6.1.4.1.248.32.18.1.87.1.6
hmStatusEogreTunnelEntryKeyValue OBJECT-TYPE
    SYNTAX     Integer32 (0..2147483647)
    MAX-ACCESS read-only
    STATUS     current
    DESCRIPTION
            "-- empty --"
    ::= { hmStatusEogreTunnelEntry 6 }

-- {COLUMN} 1.3.6.1.4.1.248.32.18.1.87.1.7
hmStatusEogreTunnelEntryChecksum OBJECT-TYPE
    SYNTAX     INTEGER {
                  eNo (0),
                  eYes (1)
            }
    MAX-ACCESS read-only
    STATUS     current
    DESCRIPTION
            "-- empty --"
    ::= { hmStatusEogreTunnelEntry 7 }

-- {COLUMN} 1.3.6.1.4.1.248.32.18.1.87.1.8
hmStatusEogreTunnelEntrySequencing OBJECT-TYPE
    SYNTAX     INTEGER {
                  eNo (0),
                  eYes (1)
            }
    MAX-ACCESS read-only
    STATUS     current
    DESCRIPTION
            "-- empty --"
    ::= { hmStatusEogreTunnelEntry 8 }

-- {COLUMN} 1.3.6.1.4.1.248.32.18.1.87.1.9
hmStatusEogreTunnelEntryLoopbackAddress OBJECT-TYPE
    SYNTAX     DisplayString (SIZE(0..16))
    MAX-ACCESS read-only
    STATUS     current
    DESCRIPTION
            "-- empty --"
    ::= { hmStatusEogreTunnelEntry 9 }

-- {SCALAR} 1.3.6.1.4.1.248.32.18.1.100
hmStatusDeleteValues OBJECT-TYPE
    SYNTAX     DisplayString
    MAX-ACCESS read-write
    STATUS     current
    DESCRIPTION
            "-- empty --"
    ::= { hmStatus 100 }

-- {NODE} 1.3.6.1.4.1.248.32.18.2
hmSetup OBJECT IDENTIFIER ::= { bat54rail 2 }

-- {SCALAR} 1.3.6.1.4.1.248.32.18.2.1
hmSetupName OBJECT-TYPE
    SYNTAX     DisplayString (SIZE(0..64))
    MAX-ACCESS read-write
    STATUS     current
    DESCRIPTION
            "-- empty --"
    ::= { hmSetup 1 }

-- {NODE} 1.3.6.1.4.1.248.32.18.2.2
hmSetupWan OBJECT IDENTIFIER ::= { hmSetup 2 }

-- {TABLE} 1.3.6.1.4.1.248.32.18.2.2.2
hmSetupWanDialupPeersTable OBJECT-TYPE
    SYNTAX     SEQUENCE OF HmSetupWanDialupPeersEntry
    MAX-ACCESS not-accessible
    STATUS     current
    DESCRIPTION
            "-- empty --"
    ::= { hmSetupWan 2 }

-- {ROW} 1.3.6.1.4.1.248.32.18.2.2.2.1
hmSetupWanDialupPeersEntry OBJECT-TYPE
    SYNTAX     HmSetupWanDialupPeersEntry
    MAX-ACCESS not-accessible
    STATUS     current
    DESCRIPTION
            ""
    INDEX {
            hmSetupWanDialupPeersEntryPeer
          }
    ::= { hmSetupWanDialupPeersTable 1 }

HmSetupWanDialupPeersEntry ::= SEQUENCE {
            hmSetupWanDialupPeersEntryPeer DisplayString,
            hmSetupWanDialupPeersEntryDialupRemote DisplayString,
            hmSetupWanDialupPeersEntryB1Dt Integer32,
            hmSetupWanDialupPeersEntryB2Dt Integer32,
            hmSetupWanDialupPeersEntryWanLayer DisplayString,
            hmSetupWanDialupPeersEntryCallback INTEGER
    }

-- {COLUMN} 1.3.6.1.4.1.248.32.18.2.2.2.1.1
hmSetupWanDialupPeersEntryPeer OBJECT-TYPE
    SYNTAX     DisplayString (SIZE(0..16))
    MAX-ACCESS read-write
    STATUS     current
    DESCRIPTION
            "-- empty --"
    ::= { hmSetupWanDialupPeersEntry 1 }

-- {COLUMN} 1.3.6.1.4.1.248.32.18.2.2.2.1.2
hmSetupWanDialupPeersEntryDialupRemote OBJECT-TYPE
    SYNTAX     DisplayString (SIZE(0..31))
    MAX-ACCESS read-write
    STATUS     current
    DESCRIPTION
            "-- empty --"
    ::= { hmSetupWanDialupPeersEntry 2 }

-- {COLUMN} 1.3.6.1.4.1.248.32.18.2.2.2.1.3
hmSetupWanDialupPeersEntryB1Dt OBJECT-TYPE
    SYNTAX     Integer32 (0..65535)
    MAX-ACCESS read-write
    STATUS     current
    DESCRIPTION
            "-- empty --"
    ::= { hmSetupWanDialupPeersEntry 3 }

-- {COLUMN} 1.3.6.1.4.1.248.32.18.2.2.2.1.4
hmSetupWanDialupPeersEntryB2Dt OBJECT-TYPE
    SYNTAX     Integer32 (0..65535)
    MAX-ACCESS read-write
    STATUS     current
    DESCRIPTION
            "-- empty --"
    ::= { hmSetupWanDialupPeersEntry 4 }

-- {COLUMN} 1.3.6.1.4.1.248.32.18.2.2.2.1.5
hmSetupWanDialupPeersEntryWanLayer OBJECT-TYPE
    SYNTAX     DisplayString (SIZE(0..9))
    MAX-ACCESS read-write
    STATUS     current
    DESCRIPTION
            "-- empty --"
    ::= { hmSetupWanDialupPeersEntry 5 }

-- {COLUMN} 1.3.6.1.4.1.248.32.18.2.2.2.1.6
hmSetupWanDialupPeersEntryCallback OBJECT-TYPE
    SYNTAX     INTEGER {
                  eNo (0),
                  eAuto (1),
                  eLooser (2),
                  eName (5),
                  eFast (9)
            }
    MAX-ACCESS read-write
    STATUS     current
    DESCRIPTION
            "-- empty --"
    ::= { hmSetupWanDialupPeersEntry 6 }

-- {TABLE} 1.3.6.1.4.1.248.32.18.2.2.3
hmSetupWanRoundrobinTable OBJECT-TYPE
    SYNTAX     SEQUENCE OF HmSetupWanRoundrobinEntry
    MAX-ACCESS not-accessible
    STATUS     current
    DESCRIPTION
            "-- empty --"
    ::= { hmSetupWan 3 }

-- {ROW} 1.3.6.1.4.1.248.32.18.2.2.3.1
hmSetupWanRoundrobinEntry OBJECT-TYPE
    SYNTAX     HmSetupWanRoundrobinEntry
    MAX-ACCESS not-accessible
    STATUS     current
    DESCRIPTION
            ""
    INDEX {
            hmSetupWanRoundrobinEntryPeer
          }
    ::= { hmSetupWanRoundrobinTable 1 }

HmSetupWanRoundrobinEntry ::= SEQUENCE {
            hmSetupWanRoundrobinEntryPeer DisplayString,
            hmSetupWanRoundrobinEntryRoundRobin DisplayString,
            hmSetupWanRoundrobinEntryHead INTEGER
    }

-- {COLUMN} 1.3.6.1.4.1.248.32.18.2.2.3.1.1
hmSetupWanRoundrobinEntryPeer OBJECT-TYPE
    SYNTAX     DisplayString (SIZE(0..18))
    MAX-ACCESS read-write
    STATUS     current
    DESCRIPTION
            "-- empty --"
    ::= { hmSetupWanRoundrobinEntry 1 }

-- {COLUMN} 1.3.6.1.4.1.248.32.18.2.2.3.1.2
hmSetupWanRoundrobinEntryRoundRobin OBJECT-TYPE
    SYNTAX     DisplayString (SIZE(0..53))
    MAX-ACCESS read-write
    STATUS     current
    DESCRIPTION
            "-- empty --"
    ::= { hmSetupWanRoundrobinEntry 2 }

-- {COLUMN} 1.3.6.1.4.1.248.32.18.2.2.3.1.3
hmSetupWanRoundrobinEntryHead OBJECT-TYPE
    SYNTAX     INTEGER {
                  eLast (0),
                  eFirst (1)
            }
    MAX-ACCESS read-write
    STATUS     current
    DESCRIPTION
            "-- empty --"
    ::= { hmSetupWanRoundrobinEntry 3 }

-- {TABLE} 1.3.6.1.4.1.248.32.18.2.2.4
hmSetupWanLayerTable OBJECT-TYPE
    SYNTAX     SEQUENCE OF HmSetupWanLayerEntry
    MAX-ACCESS not-accessible
    STATUS     current
    DESCRIPTION
            "-- empty --"
    ::= { hmSetupWan 4 }

-- {ROW} 1.3.6.1.4.1.248.32.18.2.2.4.1
hmSetupWanLayerEntry OBJECT-TYPE
    SYNTAX     HmSetupWanLayerEntry
    MAX-ACCESS not-accessible
    STATUS     current
    DESCRIPTION
            ""
    INDEX {
            hmSetupWanLayerEntryWanLayer
          }
    ::= { hmSetupWanLayerTable 1 }

HmSetupWanLayerEntry ::= SEQUENCE {
            hmSetupWanLayerEntryWanLayer DisplayString,
            hmSetupWanLayerEntryEncaps INTEGER,
            hmSetupWanLayerEntryLay3 INTEGER,
            hmSetupWanLayerEntryLay2 INTEGER,
            hmSetupWanLayerEntryL2Opt INTEGER,
            hmSetupWanLayerEntryLay1 INTEGER
    }

-- {COLUMN} 1.3.6.1.4.1.248.32.18.2.2.4.1.1
hmSetupWanLayerEntryWanLayer OBJECT-TYPE
    SYNTAX     DisplayString (SIZE(0..9))
    MAX-ACCESS read-write
    STATUS     current
    DESCRIPTION
            "-- empty --"
    ::= { hmSetupWanLayerEntry 1 }

-- {COLUMN} 1.3.6.1.4.1.248.32.18.2.2.4.1.2
hmSetupWanLayerEntryEncaps OBJECT-TYPE
    SYNTAX     INTEGER {
                  eEther (0),
                  eTrans (255)
            }
    MAX-ACCESS read-write
    STATUS     current
    DESCRIPTION
            "-- empty --"
    ::= { hmSetupWanLayerEntry 2 }

-- {COLUMN} 1.3.6.1.4.1.248.32.18.2.2.4.1.3
hmSetupWanLayerEntryLay3 OBJECT-TYPE
    SYNTAX     INTEGER {
                  ePpp (4),
                  eAppp (5),
                  eScppp (6),
                  eScappp (7),
                  eSctrans (8),
                  eDhcp (9),
                  eTRANS (255)
            }
    MAX-ACCESS read-write
    STATUS     current
    DESCRIPTION
            "-- empty --"
    ::= { hmSetupWanLayerEntry 3 }

-- {COLUMN} 1.3.6.1.4.1.248.32.18.2.2.4.1.4
hmSetupWanLayerEntryLay2 OBJECT-TYPE
    SYNTAX     INTEGER {
                  eTrans (1),
                  ePppoe (5)
            }
    MAX-ACCESS read-write
    STATUS     current
    DESCRIPTION
            "-- empty --"
    ::= { hmSetupWanLayerEntry 4 }

-- {COLUMN} 1.3.6.1.4.1.248.32.18.2.2.4.1.5
hmSetupWanLayerEntryL2Opt OBJECT-TYPE
    SYNTAX     INTEGER {
                  eCompr (0),
                  eNone (255)
            }
    MAX-ACCESS read-write
    STATUS     current
    DESCRIPTION
            "-- empty --"
    ::= { hmSetupWanLayerEntry 5 }

-- {COLUMN} 1.3.6.1.4.1.248.32.18.2.2.4.1.6
hmSetupWanLayerEntryLay1 OBJECT-TYPE
    SYNTAX     INTEGER {
                  eEth (4),
                  eSerial (6)
            }
    MAX-ACCESS read-write
    STATUS     current
    DESCRIPTION
            "-- empty --"
    ::= { hmSetupWanLayerEntry 6 }

-- {TABLE} 1.3.6.1.4.1.248.32.18.2.2.5
hmSetupWanPppTable OBJECT-TYPE
    SYNTAX     SEQUENCE OF HmSetupWanPppEntry
    MAX-ACCESS not-accessible
    STATUS     current
    DESCRIPTION
            "-- empty --"
    ::= { hmSetupWan 5 }

-- {ROW} 1.3.6.1.4.1.248.32.18.2.2.5.1
hmSetupWanPppEntry OBJECT-TYPE
    SYNTAX     HmSetupWanPppEntry
    MAX-ACCESS not-accessible
    STATUS     current
    DESCRIPTION
            ""
    INDEX {
            hmSetupWanPppEntryPeer
          }
    ::= { hmSetupWanPppTable 1 }

HmSetupWanPppEntry ::= SEQUENCE {
            hmSetupWanPppEntryPeer DisplayString,
            hmSetupWanPppEntryAuthentRequest BITS,
            hmSetupWanPppEntryKey DisplayString,
            hmSetupWanPppEntryTime Integer32,
            hmSetupWanPppEntryTry Integer32,
            hmSetupWanPppEntryUsername DisplayString,
            hmSetupWanPppEntryConf Integer32,
            hmSetupWanPppEntryFail Integer32,
            hmSetupWanPppEntryTerm Integer32,
            hmSetupWanPppEntryRights BITS,
            hmSetupWanPppEntryAuthentResponse BITS
    }

-- {COLUMN} 1.3.6.1.4.1.248.32.18.2.2.5.1.1
hmSetupWanPppEntryPeer OBJECT-TYPE
    SYNTAX     DisplayString (SIZE(0..16))
    MAX-ACCESS read-write
    STATUS     current
    DESCRIPTION
            "-- empty --"
    ::= { hmSetupWanPppEntry 1 }

-- {COLUMN} 1.3.6.1.4.1.248.32.18.2.2.5.1.2
hmSetupWanPppEntryAuthentRequest OBJECT-TYPE
    SYNTAX     BITS {
                  eNone (0),
                  eMsChapv2 (2),
                  eMsChap (3),
                  eChap (4),
                  ePap (5)
            }
    MAX-ACCESS read-write
    STATUS     current
    DESCRIPTION
            "-- empty --"
    ::= { hmSetupWanPppEntry 2 }

-- {COLUMN} 1.3.6.1.4.1.248.32.18.2.2.5.1.3
hmSetupWanPppEntryKey OBJECT-TYPE
    SYNTAX     DisplayString (SIZE(0..32))
    MAX-ACCESS read-write
    STATUS     current
    DESCRIPTION
            "-- empty --"
    ::= { hmSetupWanPppEntry 3 }

-- {COLUMN} 1.3.6.1.4.1.248.32.18.2.2.5.1.4
hmSetupWanPppEntryTime OBJECT-TYPE
    SYNTAX     Integer32 (0..255)
    MAX-ACCESS read-write
    STATUS     current
    DESCRIPTION
            "-- empty --"
    ::= { hmSetupWanPppEntry 4 }

-- {COLUMN} 1.3.6.1.4.1.248.32.18.2.2.5.1.5
hmSetupWanPppEntryTry OBJECT-TYPE
    SYNTAX     Integer32 (0..255)
    MAX-ACCESS read-write
    STATUS     current
    DESCRIPTION
            "-- empty --"
    ::= { hmSetupWanPppEntry 5 }

-- {COLUMN} 1.3.6.1.4.1.248.32.18.2.2.5.1.6
hmSetupWanPppEntryUsername OBJECT-TYPE
    SYNTAX     DisplayString (SIZE(0..64))
    MAX-ACCESS read-write
    STATUS     current
    DESCRIPTION
            "-- empty --"
    ::= { hmSetupWanPppEntry 6 }

-- {COLUMN} 1.3.6.1.4.1.248.32.18.2.2.5.1.7
hmSetupWanPppEntryConf OBJECT-TYPE
    SYNTAX     Integer32 (0..255)
    MAX-ACCESS read-write
    STATUS     current
    DESCRIPTION
            "-- empty --"
    ::= { hmSetupWanPppEntry 7 }

-- {COLUMN} 1.3.6.1.4.1.248.32.18.2.2.5.1.8
hmSetupWanPppEntryFail OBJECT-TYPE
    SYNTAX     Integer32 (0..255)
    MAX-ACCESS read-write
    STATUS     current
    DESCRIPTION
            "-- empty --"
    ::= { hmSetupWanPppEntry 8 }

-- {COLUMN} 1.3.6.1.4.1.248.32.18.2.2.5.1.9
hmSetupWanPppEntryTerm OBJECT-TYPE
    SYNTAX     Integer32 (0..255)
    MAX-ACCESS read-write
    STATUS     current
    DESCRIPTION
            "-- empty --"
    ::= { hmSetupWanPppEntry 9 }

-- {COLUMN} 1.3.6.1.4.1.248.32.18.2.2.5.1.10
hmSetupWanPppEntryRights OBJECT-TYPE
    SYNTAX     BITS {
                  eNone (0),
                  eIpv6 (3),
                  eNbt (6),
                  eIp (7)
            }
    MAX-ACCESS read-write
    STATUS     current
    DESCRIPTION
            "-- empty --"
    ::= { hmSetupWanPppEntry 10 }

-- {COLUMN} 1.3.6.1.4.1.248.32.18.2.2.5.1.11
hmSetupWanPppEntryAuthentResponse OBJECT-TYPE
    SYNTAX     BITS {
                  eNone (0),
                  eMsChapv2 (2),
                  eMsChap (3),
                  eChap (4),
                  ePap (5)
            }
    MAX-ACCESS read-write
    STATUS     current
    DESCRIPTION
            "-- empty --"
    ::= { hmSetupWanPppEntry 11 }

-- {TABLE} 1.3.6.1.4.1.248.32.18.2.2.6
hmSetupWanIncomingCallingNumbersTable OBJECT-TYPE
    SYNTAX     SEQUENCE OF HmSetupWanIncomingCallingNumbersEntry
    MAX-ACCESS not-accessible
    STATUS     current
    DESCRIPTION
            "-- empty --"
    ::= { hmSetupWan 6 }

-- {ROW} 1.3.6.1.4.1.248.32.18.2.2.6.1
hmSetupWanIncomingCallingNumbersEntry OBJECT-TYPE
    SYNTAX     HmSetupWanIncomingCallingNumbersEntry
    MAX-ACCESS not-accessible
    STATUS     current
    DESCRIPTION
            ""
    INDEX {
            hmSetupWanIncomingCallingNumbersEntryDialupRemote
          }
    ::= { hmSetupWanIncomingCallingNumbersTable 1 }

HmSetupWanIncomingCallingNumbersEntry ::= SEQUENCE {
            hmSetupWanIncomingCallingNumbersEntryDialupRemote DisplayString,
            hmSetupWanIncomingCallingNumbersEntryPeer DisplayString
    }

-- {COLUMN} 1.3.6.1.4.1.248.32.18.2.2.6.1.1
hmSetupWanIncomingCallingNumbersEntryDialupRemote OBJECT-TYPE
    SYNTAX     DisplayString (SIZE(0..31))
    MAX-ACCESS read-write
    STATUS     current
    DESCRIPTION
            "-- empty --"
    ::= { hmSetupWanIncomingCallingNumbersEntry 1 }

-- {COLUMN} 1.3.6.1.4.1.248.32.18.2.2.6.1.2
hmSetupWanIncomingCallingNumbersEntryPeer OBJECT-TYPE
    SYNTAX     DisplayString (SIZE(0..16))
    MAX-ACCESS read-write
    STATUS     current
    DESCRIPTION
            "-- empty --"
    ::= { hmSetupWanIncomingCallingNumbersEntry 2 }

-- {SCALAR} 1.3.6.1.4.1.248.32.18.2.2.7
hmSetupWanDialPrefix OBJECT-TYPE
    SYNTAX     DisplayString (SIZE(0..8))
    MAX-ACCESS read-only
    STATUS     obsolete
    DESCRIPTION
            "-- empty --"
    ::= { hmSetupWan 7 }

-- {TABLE} 1.3.6.1.4.1.248.32.18.2.2.8
hmSetupWanScriptsTable OBJECT-TYPE
    SYNTAX     SEQUENCE OF HmSetupWanScriptsEntry
    MAX-ACCESS not-accessible
    STATUS     current
    DESCRIPTION
            "-- empty --"
    ::= { hmSetupWan 8 }

-- {ROW} 1.3.6.1.4.1.248.32.18.2.2.8.1
hmSetupWanScriptsEntry OBJECT-TYPE
    SYNTAX     HmSetupWanScriptsEntry
    MAX-ACCESS not-accessible
    STATUS     current
    DESCRIPTION
            ""
    INDEX {
            hmSetupWanScriptsEntryPeer
          }
    ::= { hmSetupWanScriptsTable 1 }

HmSetupWanScriptsEntry ::= SEQUENCE {
            hmSetupWanScriptsEntryPeer DisplayString,
            hmSetupWanScriptsEntryScript DisplayString
    }

-- {COLUMN} 1.3.6.1.4.1.248.32.18.2.2.8.1.1
hmSetupWanScriptsEntryPeer OBJECT-TYPE
    SYNTAX     DisplayString (SIZE(0..18))
    MAX-ACCESS read-write
    STATUS     current
    DESCRIPTION
            "-- empty --"
    ::= { hmSetupWanScriptsEntry 1 }

-- {COLUMN} 1.3.6.1.4.1.248.32.18.2.2.8.1.2
hmSetupWanScriptsEntryScript OBJECT-TYPE
    SYNTAX     DisplayString (SIZE(0..58))
    MAX-ACCESS read-write
    STATUS     current
    DESCRIPTION
            "-- empty --"
    ::= { hmSetupWanScriptsEntry 2 }

-- {SCALAR} 1.3.6.1.4.1.248.32.18.2.2.9
hmSetupWanProtect OBJECT-TYPE
    SYNTAX     INTEGER {
                  eNone (0),
                  eNumber (2),
                  eScreened (4)
            }
    MAX-ACCESS read-write
    STATUS     current
    DESCRIPTION
            "-- empty --"
    ::= { hmSetupWan 9 }

-- {SCALAR} 1.3.6.1.4.1.248.32.18.2.2.10
hmSetupWanCallbackAttempts OBJECT-TYPE
    SYNTAX     Integer32 (0..255)
    MAX-ACCESS read-write
    STATUS     current
    DESCRIPTION
            "-- empty --"
    ::= { hmSetupWan 10 }

-- {TABLE} 1.3.6.1.4.1.248.32.18.2.2.11
hmSetupWanRouterInterfaceTable OBJECT-TYPE
    SYNTAX     SEQUENCE OF HmSetupWanRouterInterfaceEntry
    MAX-ACCESS not-accessible
    STATUS     current
    DESCRIPTION
            "-- empty --"
    ::= { hmSetupWan 11 }

-- {ROW} 1.3.6.1.4.1.248.32.18.2.2.11.1
hmSetupWanRouterInterfaceEntry OBJECT-TYPE
    SYNTAX     HmSetupWanRouterInterfaceEntry
    MAX-ACCESS not-accessible
    STATUS     current
    DESCRIPTION
            ""
    INDEX {
            hmSetupWanRouterInterfaceEntryIfc
          }
    ::= { hmSetupWanRouterInterfaceTable 1 }

HmSetupWanRouterInterfaceEntry ::= SEQUENCE {
            hmSetupWanRouterInterfaceEntryIfc INTEGER,
            hmSetupWanRouterInterfaceEntryMsnEaz DisplayString,
            hmSetupWanRouterInterfaceEntryClip INTEGER,
            hmSetupWanRouterInterfaceEntryYc INTEGER,
            hmSetupWanRouterInterfaceEntryAcceptCalls INTEGER,
            hmSetupWanRouterInterfaceEntryTypeOfInterface Integer32
    }

-- {COLUMN} 1.3.6.1.4.1.248.32.18.2.2.11.1.1
hmSetupWanRouterInterfaceEntryIfc OBJECT-TYPE
    SYNTAX     INTEGER {
                  eModem (513),
                  eDsl1 (2049),
                  eDsl2 (2050),
                  eDsl3 (2051),
                  eDsl4 (2052)
            }
    MAX-ACCESS read-only
    STATUS     current
    DESCRIPTION
            "-- empty --"
    ::= { hmSetupWanRouterInterfaceEntry 1 }

-- {COLUMN} 1.3.6.1.4.1.248.32.18.2.2.11.1.2
hmSetupWanRouterInterfaceEntryMsnEaz OBJECT-TYPE
    SYNTAX     DisplayString (SIZE(0..30))
    MAX-ACCESS read-write
    STATUS     current
    DESCRIPTION
            "-- empty --"
    ::= { hmSetupWanRouterInterfaceEntry 2 }

-- {COLUMN} 1.3.6.1.4.1.248.32.18.2.2.11.1.3
hmSetupWanRouterInterfaceEntryClip OBJECT-TYPE
    SYNTAX     INTEGER {
                  eYes (0),
                  eNo (1)
            }
    MAX-ACCESS read-write
    STATUS     current
    DESCRIPTION
            "-- empty --"
    ::= { hmSetupWanRouterInterfaceEntry 3 }

-- {COLUMN} 1.3.6.1.4.1.248.32.18.2.2.11.1.8
hmSetupWanRouterInterfaceEntryYc OBJECT-TYPE
    SYNTAX     INTEGER {
                  eYes (0),
                  eNo (1)
            }
    MAX-ACCESS read-write
    STATUS     current
    DESCRIPTION
            "-- empty --"
    ::= { hmSetupWanRouterInterfaceEntry 8 }

-- {COLUMN} 1.3.6.1.4.1.248.32.18.2.2.11.1.9
hmSetupWanRouterInterfaceEntryAcceptCalls OBJECT-TYPE
    SYNTAX     INTEGER {
                  eAll (0),
                  eNone (128)
            }
    MAX-ACCESS read-write
    STATUS     current
    DESCRIPTION
            "-- empty --"
    ::= { hmSetupWanRouterInterfaceEntry 9 }

-- {COLUMN} 1.3.6.1.4.1.248.32.18.2.2.11.1.10
hmSetupWanRouterInterfaceEntryTypeOfInterface OBJECT-TYPE
    SYNTAX     Integer32 (0..2147483647)
    MAX-ACCESS read-only
    STATUS     current
    DESCRIPTION
            "-- empty --"
    ::= { hmSetupWanRouterInterfaceEntry 10 }

-- {NODE} 1.3.6.1.4.1.248.32.18.2.2.13
hmSetupWanManualDialing OBJECT IDENTIFIER ::= { hmSetupWan 13 }

-- {SCALAR} 1.3.6.1.4.1.248.32.18.2.2.13.1
hmSetupWanManualDialingConnect OBJECT-TYPE
    SYNTAX     DisplayString
    MAX-ACCESS read-write
    STATUS     current
    DESCRIPTION
            "-- empty --"
    ::= { hmSetupWanManualDialing 1 }

-- {SCALAR} 1.3.6.1.4.1.248.32.18.2.2.13.2
hmSetupWanManualDialingDisconnect OBJECT-TYPE
    SYNTAX     DisplayString
    MAX-ACCESS read-write
    STATUS     current
    DESCRIPTION
            "-- empty --"
    ::= { hmSetupWanManualDialing 2 }

-- {SCALAR} 1.3.6.1.4.1.248.32.18.2.2.18
hmSetupWanBackupDelaySeconds OBJECT-TYPE
    SYNTAX     Integer32 (0..65535)
    MAX-ACCESS read-write
    STATUS     current
    DESCRIPTION
            "-- empty --"
    ::= { hmSetupWan 18 }

-- {TABLE} 1.3.6.1.4.1.248.32.18.2.2.19
hmSetupWanDslBroadbandPeersTable OBJECT-TYPE
    SYNTAX     SEQUENCE OF HmSetupWanDslBroadbandPeersEntry
    MAX-ACCESS not-accessible
    STATUS     current
    DESCRIPTION
            "-- empty --"
    ::= { hmSetupWan 19 }

-- {ROW} 1.3.6.1.4.1.248.32.18.2.2.19.1
hmSetupWanDslBroadbandPeersEntry OBJECT-TYPE
    SYNTAX     HmSetupWanDslBroadbandPeersEntry
    MAX-ACCESS not-accessible
    STATUS     current
    DESCRIPTION
            ""
    INDEX {
            hmSetupWanDslBroadbandPeersEntryPeer
          }
    ::= { hmSetupWanDslBroadbandPeersTable 1 }

HmSetupWanDslBroadbandPeersEntry ::= SEQUENCE {
            hmSetupWanDslBroadbandPeersEntryPeer DisplayString,
            hmSetupWanDslBroadbandPeersEntryShTime Integer32,
            hmSetupWanDslBroadbandPeersEntryWanLayer DisplayString,
            hmSetupWanDslBroadbandPeersEntryAcName DisplayString,
            hmSetupWanDslBroadbandPeersEntryServicename DisplayString,
            hmSetupWanDslBroadbandPeersEntryUserDefMac MacAddress,
            hmSetupWanDslBroadbandPeersEntryDslIfcS DisplayString,
            hmSetupWanDslBroadbandPeersEntryMacType INTEGER,
            hmSetupWanDslBroadbandPeersEntryVlanId Integer32
    }

-- {COLUMN} 1.3.6.1.4.1.248.32.18.2.2.19.1.1
hmSetupWanDslBroadbandPeersEntryPeer OBJECT-TYPE
    SYNTAX     DisplayString (SIZE(0..16))
    MAX-ACCESS read-write
    STATUS     current
    DESCRIPTION
            "-- empty --"
    ::= { hmSetupWanDslBroadbandPeersEntry 1 }

-- {COLUMN} 1.3.6.1.4.1.248.32.18.2.2.19.1.3
hmSetupWanDslBroadbandPeersEntryShTime OBJECT-TYPE
    SYNTAX     Integer32 (0..65535)
    MAX-ACCESS read-write
    STATUS     current
    DESCRIPTION
            "-- empty --"
    ::= { hmSetupWanDslBroadbandPeersEntry 3 }

-- {COLUMN} 1.3.6.1.4.1.248.32.18.2.2.19.1.5
hmSetupWanDslBroadbandPeersEntryWanLayer OBJECT-TYPE
    SYNTAX     DisplayString (SIZE(0..9))
    MAX-ACCESS read-write
    STATUS     current
    DESCRIPTION
            "-- empty --"
    ::= { hmSetupWanDslBroadbandPeersEntry 5 }

-- {COLUMN} 1.3.6.1.4.1.248.32.18.2.2.19.1.9
hmSetupWanDslBroadbandPeersEntryAcName OBJECT-TYPE
    SYNTAX     DisplayString (SIZE(0..64))
    MAX-ACCESS read-write
    STATUS     current
    DESCRIPTION
            "-- empty --"
    ::= { hmSetupWanDslBroadbandPeersEntry 9 }

-- {COLUMN} 1.3.6.1.4.1.248.32.18.2.2.19.1.10
hmSetupWanDslBroadbandPeersEntryServicename OBJECT-TYPE
    SYNTAX     DisplayString (SIZE(0..32))
    MAX-ACCESS read-write
    STATUS     current
    DESCRIPTION
            "-- empty --"
    ::= { hmSetupWanDslBroadbandPeersEntry 10 }

-- {COLUMN} 1.3.6.1.4.1.248.32.18.2.2.19.1.13
hmSetupWanDslBroadbandPeersEntryUserDefMac OBJECT-TYPE
    SYNTAX     MacAddress
    MAX-ACCESS read-write
    STATUS     current
    DESCRIPTION
            "-- empty --"
    ::= { hmSetupWanDslBroadbandPeersEntry 13 }

-- {COLUMN} 1.3.6.1.4.1.248.32.18.2.2.19.1.14
hmSetupWanDslBroadbandPeersEntryDslIfcS OBJECT-TYPE
    SYNTAX     DisplayString (SIZE(0..8))
    MAX-ACCESS read-write
    STATUS     current
    DESCRIPTION
            "-- empty --"
    ::= { hmSetupWanDslBroadbandPeersEntry 14 }

-- {COLUMN} 1.3.6.1.4.1.248.32.18.2.2.19.1.15
hmSetupWanDslBroadbandPeersEntryMacType OBJECT-TYPE
    SYNTAX     INTEGER {
                  eLocal (0),
                  eGlobal (1),
                  eUserDef (2)
            }
    MAX-ACCESS read-write
    STATUS     current
    DESCRIPTION
            "-- empty --"
    ::= { hmSetupWanDslBroadbandPeersEntry 15 }

-- {COLUMN} 1.3.6.1.4.1.248.32.18.2.2.19.1.16
hmSetupWanDslBroadbandPeersEntryVlanId OBJECT-TYPE
    SYNTAX     Integer32 (0..65535)
    MAX-ACCESS read-write
    STATUS     current
    DESCRIPTION
            "-- empty --"
    ::= { hmSetupWanDslBroadbandPeersEntry 16 }

-- {TABLE} 1.3.6.1.4.1.248.32.18.2.2.20
hmSetupWanIpListTable OBJECT-TYPE
    SYNTAX     SEQUENCE OF HmSetupWanIpListEntry
    MAX-ACCESS not-accessible
    STATUS     current
    DESCRIPTION
            "-- empty --"
    ::= { hmSetupWan 20 }

-- {ROW} 1.3.6.1.4.1.248.32.18.2.2.20.1
hmSetupWanIpListEntry OBJECT-TYPE
    SYNTAX     HmSetupWanIpListEntry
    MAX-ACCESS not-accessible
    STATUS     current
    DESCRIPTION
            ""
    INDEX {
            hmSetupWanIpListEntryPeer
          }
    ::= { hmSetupWanIpListTable 1 }

HmSetupWanIpListEntry ::= SEQUENCE {
            hmSetupWanIpListEntryPeer DisplayString,
            hmSetupWanIpListEntryIpAddress IpAddress,
            hmSetupWanIpListEntryIpNetmask IpAddress,
            hmSetupWanIpListEntryGateway IpAddress,
            hmSetupWanIpListEntryDnsDefault IpAddress,
            hmSetupWanIpListEntryDnsBackup IpAddress,
            hmSetupWanIpListEntryNbnsDefault IpAddress,
            hmSetupWanIpListEntryNbnsBackup IpAddress,
            hmSetupWanIpListEntryMasqIpAddr IpAddress
    }

-- {COLUMN} 1.3.6.1.4.1.248.32.18.2.2.20.1.1
hmSetupWanIpListEntryPeer OBJECT-TYPE
    SYNTAX     DisplayString (SIZE(0..16))
    MAX-ACCESS read-write
    STATUS     current
    DESCRIPTION
            "-- empty --"
    ::= { hmSetupWanIpListEntry 1 }

-- {COLUMN} 1.3.6.1.4.1.248.32.18.2.2.20.1.2
hmSetupWanIpListEntryIpAddress OBJECT-TYPE
    SYNTAX     IpAddress
    MAX-ACCESS read-write
    STATUS     current
    DESCRIPTION
            "-- empty --"
    ::= { hmSetupWanIpListEntry 2 }

-- {COLUMN} 1.3.6.1.4.1.248.32.18.2.2.20.1.3
hmSetupWanIpListEntryIpNetmask OBJECT-TYPE
    SYNTAX     IpAddress
    MAX-ACCESS read-write
    STATUS     current
    DESCRIPTION
            "-- empty --"
    ::= { hmSetupWanIpListEntry 3 }

-- {COLUMN} 1.3.6.1.4.1.248.32.18.2.2.20.1.4
hmSetupWanIpListEntryGateway OBJECT-TYPE
    SYNTAX     IpAddress
    MAX-ACCESS read-write
    STATUS     current
    DESCRIPTION
            "-- empty --"
    ::= { hmSetupWanIpListEntry 4 }

-- {COLUMN} 1.3.6.1.4.1.248.32.18.2.2.20.1.5
hmSetupWanIpListEntryDnsDefault OBJECT-TYPE
    SYNTAX     IpAddress
    MAX-ACCESS read-write
    STATUS     current
    DESCRIPTION
            "-- empty --"
    ::= { hmSetupWanIpListEntry 5 }

-- {COLUMN} 1.3.6.1.4.1.248.32.18.2.2.20.1.6
hmSetupWanIpListEntryDnsBackup OBJECT-TYPE
    SYNTAX     IpAddress
    MAX-ACCESS read-write
    STATUS     current
    DESCRIPTION
            "-- empty --"
    ::= { hmSetupWanIpListEntry 6 }

-- {COLUMN} 1.3.6.1.4.1.248.32.18.2.2.20.1.7
hmSetupWanIpListEntryNbnsDefault OBJECT-TYPE
    SYNTAX     IpAddress
    MAX-ACCESS read-write
    STATUS     current
    DESCRIPTION
            "-- empty --"
    ::= { hmSetupWanIpListEntry 7 }

-- {COLUMN} 1.3.6.1.4.1.248.32.18.2.2.20.1.8
hmSetupWanIpListEntryNbnsBackup OBJECT-TYPE
    SYNTAX     IpAddress
    MAX-ACCESS read-write
    STATUS     current
    DESCRIPTION
            "-- empty --"
    ::= { hmSetupWanIpListEntry 8 }

-- {COLUMN} 1.3.6.1.4.1.248.32.18.2.2.20.1.9
hmSetupWanIpListEntryMasqIpAddr OBJECT-TYPE
    SYNTAX     IpAddress
    MAX-ACCESS read-write
    STATUS     current
    DESCRIPTION
            "-- empty --"
    ::= { hmSetupWanIpListEntry 9 }

-- {TABLE} 1.3.6.1.4.1.248.32.18.2.2.21
hmSetupWanPptpPeersTable OBJECT-TYPE
    SYNTAX     SEQUENCE OF HmSetupWanPptpPeersEntry
    MAX-ACCESS not-accessible
    STATUS     current
    DESCRIPTION
            "-- empty --"
    ::= { hmSetupWan 21 }

-- {ROW} 1.3.6.1.4.1.248.32.18.2.2.21.1
hmSetupWanPptpPeersEntry OBJECT-TYPE
    SYNTAX     HmSetupWanPptpPeersEntry
    MAX-ACCESS not-accessible
    STATUS     current
    DESCRIPTION
            ""
    INDEX {
            hmSetupWanPptpPeersEntryPeer
          }
    ::= { hmSetupWanPptpPeersTable 1 }

HmSetupWanPptpPeersEntry ::= SEQUENCE {
            hmSetupWanPptpPeersEntryPeer DisplayString,
            hmSetupWanPptpPeersEntryPort Integer32,
            hmSetupWanPptpPeersEntryShTime Integer32,
            hmSetupWanPptpPeersEntryRtgTag Integer32,
            hmSetupWanPptpPeersEntryIpAddress DisplayString,
            hmSetupWanPptpPeersEntryEncryption INTEGER
    }

-- {COLUMN} 1.3.6.1.4.1.248.32.18.2.2.21.1.1
hmSetupWanPptpPeersEntryPeer OBJECT-TYPE
    SYNTAX     DisplayString (SIZE(0..16))
    MAX-ACCESS read-write
    STATUS     current
    DESCRIPTION
            "-- empty --"
    ::= { hmSetupWanPptpPeersEntry 1 }

-- {COLUMN} 1.3.6.1.4.1.248.32.18.2.2.21.1.3
hmSetupWanPptpPeersEntryPort OBJECT-TYPE
    SYNTAX     Integer32 (0..65535)
    MAX-ACCESS read-write
    STATUS     current
    DESCRIPTION
            "-- empty --"
    ::= { hmSetupWanPptpPeersEntry 3 }

-- {COLUMN} 1.3.6.1.4.1.248.32.18.2.2.21.1.4
hmSetupWanPptpPeersEntryShTime OBJECT-TYPE
    SYNTAX     Integer32 (0..65535)
    MAX-ACCESS read-write
    STATUS     current
    DESCRIPTION
            "-- empty --"
    ::= { hmSetupWanPptpPeersEntry 4 }

-- {COLUMN} 1.3.6.1.4.1.248.32.18.2.2.21.1.5
hmSetupWanPptpPeersEntryRtgTag OBJECT-TYPE
    SYNTAX     Integer32 (0..65535)
    MAX-ACCESS read-write
    STATUS     current
    DESCRIPTION
            "-- empty --"
    ::= { hmSetupWanPptpPeersEntry 5 }

-- {COLUMN} 1.3.6.1.4.1.248.32.18.2.2.21.1.6
hmSetupWanPptpPeersEntryIpAddress OBJECT-TYPE
    SYNTAX     DisplayString (SIZE(0..63))
    MAX-ACCESS read-write
    STATUS     current
    DESCRIPTION
            "-- empty --"
    ::= { hmSetupWanPptpPeersEntry 6 }

-- {COLUMN} 1.3.6.1.4.1.248.32.18.2.2.21.1.7
hmSetupWanPptpPeersEntryEncryption OBJECT-TYPE
    SYNTAX     INTEGER {
                  eOff (0),
                  e128Bits (64),
                  e56Bits (192),
                  e40Bits (224)
            }
    MAX-ACCESS read-write
    STATUS     current
    DESCRIPTION
            "-- empty --"
    ::= { hmSetupWanPptpPeersEntry 7 }

-- {NODE} 1.3.6.1.4.1.248.32.18.2.2.22
hmSetupWanRadius OBJECT IDENTIFIER ::= { hmSetupWan 22 }

-- {SCALAR} 1.3.6.1.4.1.248.32.18.2.2.22.1
hmSetupWanRadiusOperating OBJECT-TYPE
    SYNTAX     INTEGER {
                  eNo (0),
                  eYes (1),
                  eExclusive (2)
            }
    MAX-ACCESS read-write
    STATUS     current
    DESCRIPTION
            "-- empty --"
    ::= { hmSetupWanRadius 1 }

-- {SCALAR} 1.3.6.1.4.1.248.32.18.2.2.22.2
hmSetupWanRadiusServerAddress OBJECT-TYPE
    SYNTAX     IpAddress
    MAX-ACCESS read-only
    STATUS     current
    DESCRIPTION
            "-- empty --"
    ::= { hmSetupWanRadius 2 }

-- {SCALAR} 1.3.6.1.4.1.248.32.18.2.2.22.3
hmSetupWanRadiusAuthPort OBJECT-TYPE
    SYNTAX     Integer32 (0..65535)
    MAX-ACCESS read-write
    STATUS     current
    DESCRIPTION
            "-- empty --"
    ::= { hmSetupWanRadius 3 }

-- {SCALAR} 1.3.6.1.4.1.248.32.18.2.2.22.4
hmSetupWanRadiusSecret OBJECT-TYPE
    SYNTAX     DisplayString (SIZE(0..64))
    MAX-ACCESS read-write
    STATUS     current
    DESCRIPTION
            "-- empty --"
    ::= { hmSetupWanRadius 4 }

-- {SCALAR} 1.3.6.1.4.1.248.32.18.2.2.22.5
hmSetupWanRadiusPppOperation OBJECT-TYPE
    SYNTAX     INTEGER {
                  eNo (0),
                  eYes (1),
                  eExclusive (2)
            }
    MAX-ACCESS read-write
    STATUS     current
    DESCRIPTION
            "-- empty --"
    ::= { hmSetupWanRadius 5 }

-- {SCALAR} 1.3.6.1.4.1.248.32.18.2.2.22.6
hmSetupWanRadiusClipOperation OBJECT-TYPE
    SYNTAX     INTEGER {
                  eNo (0),
                  eYes (1),
                  eExclusive (2)
            }
    MAX-ACCESS read-write
    STATUS     current
    DESCRIPTION
            "-- empty --"
    ::= { hmSetupWanRadius 6 }

-- {SCALAR} 1.3.6.1.4.1.248.32.18.2.2.22.7
hmSetupWanRadiusClipPassword OBJECT-TYPE
    SYNTAX     DisplayString (SIZE(0..64))
    MAX-ACCESS read-write
    STATUS     current
    DESCRIPTION
            "-- empty --"
    ::= { hmSetupWanRadius 7 }

-- {SCALAR} 1.3.6.1.4.1.248.32.18.2.2.22.8
hmSetupWanRadiusLoopbackAddr OBJECT-TYPE
    SYNTAX     DisplayString (SIZE(0..16))
    MAX-ACCESS read-write
    STATUS     current
    DESCRIPTION
            "-- empty --"
    ::= { hmSetupWanRadius 8 }

-- {SCALAR} 1.3.6.1.4.1.248.32.18.2.2.22.9
hmSetupWanRadiusProtocol OBJECT-TYPE
    SYNTAX     INTEGER {
                  eRadius (0),
                  eRadsec (1)
            }
    MAX-ACCESS read-write
    STATUS     current
    DESCRIPTION
            "-- empty --"
    ::= { hmSetupWanRadius 9 }

-- {SCALAR} 1.3.6.1.4.1.248.32.18.2.2.22.10
hmSetupWanRadiusAuthProtocols OBJECT-TYPE
    SYNTAX     BITS {
                  eNone (0),
                  eMsChapv2 (2),
                  eMsChap (3),
                  eChap (4),
                  ePap (5)
            }
    MAX-ACCESS read-write
    STATUS     current
    DESCRIPTION
            "-- empty --"
    ::= { hmSetupWanRadius 10 }

-- {SCALAR} 1.3.6.1.4.1.248.32.18.2.2.22.11
hmSetupWanRadiusServerHostname OBJECT-TYPE
    SYNTAX     DisplayString (SIZE(0..64))
    MAX-ACCESS read-write
    STATUS     current
    DESCRIPTION
            "-- empty --"
    ::= { hmSetupWanRadius 11 }

-- {SCALAR} 1.3.6.1.4.1.248.32.18.2.2.22.12
hmSetupWanRadiusAttributeValues OBJECT-TYPE
    SYNTAX     DisplayString (SIZE(0..251))
    MAX-ACCESS read-write
    STATUS     current
    DESCRIPTION
            "-- empty --"
    ::= { hmSetupWanRadius 12 }

-- {SCALAR} 1.3.6.1.4.1.248.32.18.2.2.22.20
hmSetupWanRadiusL2tpOperating OBJECT-TYPE
    SYNTAX     INTEGER {
                  eNo (0),
                  eYes (1),
                  eExclusive (2)
            }
    MAX-ACCESS read-write
    STATUS     current
    DESCRIPTION
            "-- empty --"
    ::= { hmSetupWanRadius 20 }

-- {SCALAR} 1.3.6.1.4.1.248.32.18.2.2.22.21
hmSetupWanRadiusL2tpServerHostname OBJECT-TYPE
    SYNTAX     DisplayString (SIZE(0..64))
    MAX-ACCESS read-write
    STATUS     current
    DESCRIPTION
            "-- empty --"
    ::= { hmSetupWanRadius 21 }

-- {SCALAR} 1.3.6.1.4.1.248.32.18.2.2.22.22
hmSetupWanRadiusL2tpAuthPort OBJECT-TYPE
    SYNTAX     Integer32 (0..65535)
    MAX-ACCESS read-write
    STATUS     current
    DESCRIPTION
            "-- empty --"
    ::= { hmSetupWanRadius 22 }

-- {SCALAR} 1.3.6.1.4.1.248.32.18.2.2.22.23
hmSetupWanRadiusL2tpLoopbackAddress OBJECT-TYPE
    SYNTAX     DisplayString (SIZE(0..16))
    MAX-ACCESS read-write
    STATUS     current
    DESCRIPTION
            "-- empty --"
    ::= { hmSetupWanRadius 23 }

-- {SCALAR} 1.3.6.1.4.1.248.32.18.2.2.22.24
hmSetupWanRadiusL2tpProtocol OBJECT-TYPE
    SYNTAX     INTEGER {
                  eRadius (0),
                  eRadsec (1)
            }
    MAX-ACCESS read-write
    STATUS     current
    DESCRIPTION
            "-- empty --"
    ::= { hmSetupWanRadius 24 }

-- {SCALAR} 1.3.6.1.4.1.248.32.18.2.2.22.25
hmSetupWanRadiusL2tpSecret OBJECT-TYPE
    SYNTAX     DisplayString (SIZE(0..64))
    MAX-ACCESS read-write
    STATUS     current
    DESCRIPTION
            "-- empty --"
    ::= { hmSetupWanRadius 25 }

-- {SCALAR} 1.3.6.1.4.1.248.32.18.2.2.22.26
hmSetupWanRadiusL2tpPassword OBJECT-TYPE
    SYNTAX     DisplayString (SIZE(0..64))
    MAX-ACCESS read-write
    STATUS     current
    DESCRIPTION
            "-- empty --"
    ::= { hmSetupWanRadius 26 }

-- {SCALAR} 1.3.6.1.4.1.248.32.18.2.2.22.27
hmSetupWanRadiusL2tpAttributeValues OBJECT-TYPE
    SYNTAX     DisplayString (SIZE(0..251))
    MAX-ACCESS read-write
    STATUS     current
    DESCRIPTION
            "-- empty --"
    ::= { hmSetupWanRadius 27 }

-- {TABLE} 1.3.6.1.4.1.248.32.18.2.2.23
hmSetupWanPollingTableTable OBJECT-TYPE
    SYNTAX     SEQUENCE OF HmSetupWanPollingTableEntry
    MAX-ACCESS not-accessible
    STATUS     current
    DESCRIPTION
            "-- empty --"
    ::= { hmSetupWan 23 }

-- {ROW} 1.3.6.1.4.1.248.32.18.2.2.23.1
hmSetupWanPollingTableEntry OBJECT-TYPE
    SYNTAX     HmSetupWanPollingTableEntry
    MAX-ACCESS not-accessible
    STATUS     current
    DESCRIPTION
            ""
    INDEX {
            hmSetupWanPollingTableEntryPeer
          }
    ::= { hmSetupWanPollingTableTable 1 }

HmSetupWanPollingTableEntry ::= SEQUENCE {
            hmSetupWanPollingTableEntryPeer DisplayString,
            hmSetupWanPollingTableEntryIpAddress1 IpAddress,
            hmSetupWanPollingTableEntryTime Integer32,
            hmSetupWanPollingTableEntryTry Integer32,
            hmSetupWanPollingTableEntryIpAddress2 IpAddress,
            hmSetupWanPollingTableEntryIpAddress3 IpAddress,
            hmSetupWanPollingTableEntryIpAddress4 IpAddress,
            hmSetupWanPollingTableEntryLoopbackAddr DisplayString,
            hmSetupWanPollingTableEntryType INTEGER
    }

-- {COLUMN} 1.3.6.1.4.1.248.32.18.2.2.23.1.1
hmSetupWanPollingTableEntryPeer OBJECT-TYPE
    SYNTAX     DisplayString (SIZE(0..16))
    MAX-ACCESS read-write
    STATUS     current
    DESCRIPTION
            "-- empty --"
    ::= { hmSetupWanPollingTableEntry 1 }

-- {COLUMN} 1.3.6.1.4.1.248.32.18.2.2.23.1.2
hmSetupWanPollingTableEntryIpAddress1 OBJECT-TYPE
    SYNTAX     IpAddress
    MAX-ACCESS read-write
    STATUS     current
    DESCRIPTION
            "-- empty --"
    ::= { hmSetupWanPollingTableEntry 2 }

-- {COLUMN} 1.3.6.1.4.1.248.32.18.2.2.23.1.3
hmSetupWanPollingTableEntryTime OBJECT-TYPE
    SYNTAX     Integer32 (0..65535)
    MAX-ACCESS read-write
    STATUS     current
    DESCRIPTION
            "-- empty --"
    ::= { hmSetupWanPollingTableEntry 3 }

-- {COLUMN} 1.3.6.1.4.1.248.32.18.2.2.23.1.4
hmSetupWanPollingTableEntryTry OBJECT-TYPE
    SYNTAX     Integer32 (0..255)
    MAX-ACCESS read-write
    STATUS     current
    DESCRIPTION
            "-- empty --"
    ::= { hmSetupWanPollingTableEntry 4 }

-- {COLUMN} 1.3.6.1.4.1.248.32.18.2.2.23.1.5
hmSetupWanPollingTableEntryIpAddress2 OBJECT-TYPE
    SYNTAX     IpAddress
    MAX-ACCESS read-write
    STATUS     current
    DESCRIPTION
            "-- empty --"
    ::= { hmSetupWanPollingTableEntry 5 }

-- {COLUMN} 1.3.6.1.4.1.248.32.18.2.2.23.1.6
hmSetupWanPollingTableEntryIpAddress3 OBJECT-TYPE
    SYNTAX     IpAddress
    MAX-ACCESS read-write
    STATUS     current
    DESCRIPTION
            "-- empty --"
    ::= { hmSetupWanPollingTableEntry 6 }

-- {COLUMN} 1.3.6.1.4.1.248.32.18.2.2.23.1.7
hmSetupWanPollingTableEntryIpAddress4 OBJECT-TYPE
    SYNTAX     IpAddress
    MAX-ACCESS read-write
    STATUS     current
    DESCRIPTION
            "-- empty --"
    ::= { hmSetupWanPollingTableEntry 7 }

-- {COLUMN} 1.3.6.1.4.1.248.32.18.2.2.23.1.8
hmSetupWanPollingTableEntryLoopbackAddr OBJECT-TYPE
    SYNTAX     DisplayString (SIZE(0..16))
    MAX-ACCESS read-write
    STATUS     current
    DESCRIPTION
            "-- empty --"
    ::= { hmSetupWanPollingTableEntry 8 }

-- {COLUMN} 1.3.6.1.4.1.248.32.18.2.2.23.1.9
hmSetupWanPollingTableEntryType OBJECT-TYPE
    SYNTAX     INTEGER {
                  eForced (0),
                  eAuto (1)
            }
    MAX-ACCESS read-write
    STATUS     current
    DESCRIPTION
            "-- empty --"
    ::= { hmSetupWanPollingTableEntry 9 }

-- {TABLE} 1.3.6.1.4.1.248.32.18.2.2.24
hmSetupWanBackupPeersTable OBJECT-TYPE
    SYNTAX     SEQUENCE OF HmSetupWanBackupPeersEntry
    MAX-ACCESS not-accessible
    STATUS     current
    DESCRIPTION
            "-- empty --"
    ::= { hmSetupWan 24 }

-- {ROW} 1.3.6.1.4.1.248.32.18.2.2.24.1
hmSetupWanBackupPeersEntry OBJECT-TYPE
    SYNTAX     HmSetupWanBackupPeersEntry
    MAX-ACCESS not-accessible
    STATUS     current
    DESCRIPTION
            ""
    INDEX {
            hmSetupWanBackupPeersEntryPeer
          }
    ::= { hmSetupWanBackupPeersTable 1 }

HmSetupWanBackupPeersEntry ::= SEQUENCE {
            hmSetupWanBackupPeersEntryPeer DisplayString,
            hmSetupWanBackupPeersEntryAlternativePeers DisplayString,
            hmSetupWanBackupPeersEntryHead INTEGER,
            hmSetupWanBackupPeersEntryFallbackMinutes Integer32
    }

-- {COLUMN} 1.3.6.1.4.1.248.32.18.2.2.24.1.1
hmSetupWanBackupPeersEntryPeer OBJECT-TYPE
    SYNTAX     DisplayString (SIZE(0..18))
    MAX-ACCESS read-write
    STATUS     current
    DESCRIPTION
            "-- empty --"
    ::= { hmSetupWanBackupPeersEntry 1 }

-- {COLUMN} 1.3.6.1.4.1.248.32.18.2.2.24.1.2
hmSetupWanBackupPeersEntryAlternativePeers OBJECT-TYPE
    SYNTAX     DisplayString (SIZE(0..53))
    MAX-ACCESS read-write
    STATUS     current
    DESCRIPTION
            "-- empty --"
    ::= { hmSetupWanBackupPeersEntry 2 }

-- {COLUMN} 1.3.6.1.4.1.248.32.18.2.2.24.1.3
hmSetupWanBackupPeersEntryHead OBJECT-TYPE
    SYNTAX     INTEGER {
                  eLast (0),
                  eFirst (1)
            }
    MAX-ACCESS read-write
    STATUS     current
    DESCRIPTION
            "-- empty --"
    ::= { hmSetupWanBackupPeersEntry 3 }

-- {COLUMN} 1.3.6.1.4.1.248.32.18.2.2.24.1.4
hmSetupWanBackupPeersEntryFallbackMinutes OBJECT-TYPE
    SYNTAX     Integer32 (0..65535)
    MAX-ACCESS read-write
    STATUS     current
    DESCRIPTION
            "-- empty --"
    ::= { hmSetupWanBackupPeersEntry 4 }

-- {TABLE} 1.3.6.1.4.1.248.32.18.2.2.25
hmSetupWanActionTableTable OBJECT-TYPE
    SYNTAX     SEQUENCE OF HmSetupWanActionTableEntry
    MAX-ACCESS not-accessible
    STATUS     current
    DESCRIPTION
            "-- empty --"
    ::= { hmSetupWan 25 }

-- {ROW} 1.3.6.1.4.1.248.32.18.2.2.25.1
hmSetupWanActionTableEntry OBJECT-TYPE
    SYNTAX     HmSetupWanActionTableEntry
    MAX-ACCESS not-accessible
    STATUS     current
    DESCRIPTION
            ""
    INDEX {
            hmSetupWanActionTableEntryIndex
          }
    ::= { hmSetupWanActionTableTable 1 }

HmSetupWanActionTableEntry ::= SEQUENCE {
            hmSetupWanActionTableEntryIndex Integer32,
            hmSetupWanActionTableEntryHostName DisplayString,
            hmSetupWanActionTableEntryPeer DisplayString,
            hmSetupWanActionTableEntryLockTime Integer32,
            hmSetupWanActionTableEntryCondition INTEGER,
            hmSetupWanActionTableEntryAction DisplayString,
            hmSetupWanActionTableEntryCheckFor DisplayString,
            hmSetupWanActionTableEntryActive INTEGER,
            hmSetupWanActionTableEntryOwner DisplayString,
            hmSetupWanActionTableEntryRoutingTag Integer32
    }

-- {COLUMN} 1.3.6.1.4.1.248.32.18.2.2.25.1.1
hmSetupWanActionTableEntryIndex OBJECT-TYPE
    SYNTAX     Integer32 (0..65535)
    MAX-ACCESS read-write
    STATUS     current
    DESCRIPTION
            "-- empty --"
    ::= { hmSetupWanActionTableEntry 1 }

-- {COLUMN} 1.3.6.1.4.1.248.32.18.2.2.25.1.2
hmSetupWanActionTableEntryHostName OBJECT-TYPE
    SYNTAX     DisplayString (SIZE(0..64))
    MAX-ACCESS read-write
    STATUS     current
    DESCRIPTION
            "-- empty --"
    ::= { hmSetupWanActionTableEntry 2 }

-- {COLUMN} 1.3.6.1.4.1.248.32.18.2.2.25.1.3
hmSetupWanActionTableEntryPeer OBJECT-TYPE
    SYNTAX     DisplayString (SIZE(0..16))
    MAX-ACCESS read-write
    STATUS     current
    DESCRIPTION
            "-- empty --"
    ::= { hmSetupWanActionTableEntry 3 }

-- {COLUMN} 1.3.6.1.4.1.248.32.18.2.2.25.1.4
hmSetupWanActionTableEntryLockTime OBJECT-TYPE
    SYNTAX     Integer32 (0..2147483647)
    MAX-ACCESS read-write
    STATUS     current
    DESCRIPTION
            "-- empty --"
    ::= { hmSetupWanActionTableEntry 4 }

-- {COLUMN} 1.3.6.1.4.1.248.32.18.2.2.25.1.5
hmSetupWanActionTableEntryCondition OBJECT-TYPE
    SYNTAX     INTEGER {
                  eEstablish (0),
                  eDisconnect (1),
                  eEnd (2),
                  eFailure (3),
                  eEstablishFailure (4),
                  eBudgetExhausted (5),
                  eBudgetReleased (6)
            }
    MAX-ACCESS read-write
    STATUS     current
    DESCRIPTION
            "-- empty --"
    ::= { hmSetupWanActionTableEntry 5 }

-- {COLUMN} 1.3.6.1.4.1.248.32.18.2.2.25.1.6
hmSetupWanActionTableEntryAction OBJECT-TYPE
    SYNTAX     DisplayString (SIZE(0..250))
    MAX-ACCESS read-write
    STATUS     current
    DESCRIPTION
            "-- empty --"
    ::= { hmSetupWanActionTableEntry 6 }

-- {COLUMN} 1.3.6.1.4.1.248.32.18.2.2.25.1.7
hmSetupWanActionTableEntryCheckFor OBJECT-TYPE
    SYNTAX     DisplayString (SIZE(0..50))
    MAX-ACCESS read-write
    STATUS     current
    DESCRIPTION
            "-- empty --"
    ::= { hmSetupWanActionTableEntry 7 }

-- {COLUMN} 1.3.6.1.4.1.248.32.18.2.2.25.1.8
hmSetupWanActionTableEntryActive OBJECT-TYPE
    SYNTAX     INTEGER {
                  eYes (0),
                  eNo (1)
            }
    MAX-ACCESS read-write
    STATUS     current
    DESCRIPTION
            "-- empty --"
    ::= { hmSetupWanActionTableEntry 8 }

-- {COLUMN} 1.3.6.1.4.1.248.32.18.2.2.25.1.9
hmSetupWanActionTableEntryOwner OBJECT-TYPE
    SYNTAX     DisplayString (SIZE(0..16))
    MAX-ACCESS read-write
    STATUS     current
    DESCRIPTION
            "-- empty --"
    ::= { hmSetupWanActionTableEntry 9 }

-- {COLUMN} 1.3.6.1.4.1.248.32.18.2.2.25.1.10
hmSetupWanActionTableEntryRoutingTag OBJECT-TYPE
    SYNTAX     Integer32 (0..65535)
    MAX-ACCESS read-write
    STATUS     current
    DESCRIPTION
            "-- empty --"
    ::= { hmSetupWanActionTableEntry 10 }

-- {TABLE} 1.3.6.1.4.1.248.32.18.2.2.26
hmSetupWanMtuListTable OBJECT-TYPE
    SYNTAX     SEQUENCE OF HmSetupWanMtuListEntry
    MAX-ACCESS not-accessible
    STATUS     current
    DESCRIPTION
            "-- empty --"
    ::= { hmSetupWan 26 }

-- {ROW} 1.3.6.1.4.1.248.32.18.2.2.26.1
hmSetupWanMtuListEntry OBJECT-TYPE
    SYNTAX     HmSetupWanMtuListEntry
    MAX-ACCESS not-accessible
    STATUS     current
    DESCRIPTION
            ""
    INDEX {
            hmSetupWanMtuListEntryPeer
          }
    ::= { hmSetupWanMtuListTable 1 }

HmSetupWanMtuListEntry ::= SEQUENCE {
            hmSetupWanMtuListEntryPeer DisplayString,
            hmSetupWanMtuListEntryMtu Integer32
    }

-- {COLUMN} 1.3.6.1.4.1.248.32.18.2.2.26.1.1
hmSetupWanMtuListEntryPeer OBJECT-TYPE
    SYNTAX     DisplayString (SIZE(0..16))
    MAX-ACCESS read-write
    STATUS     current
    DESCRIPTION
            "-- empty --"
    ::= { hmSetupWanMtuListEntry 1 }

-- {COLUMN} 1.3.6.1.4.1.248.32.18.2.2.26.1.2
hmSetupWanMtuListEntryMtu OBJECT-TYPE
    SYNTAX     Integer32 (0..65535)
    MAX-ACCESS read-write
    STATUS     current
    DESCRIPTION
            "-- empty --"
    ::= { hmSetupWanMtuListEntry 2 }

-- {TABLE} 1.3.6.1.4.1.248.32.18.2.2.30
hmSetupWanAdditionalPptpGatewaysTable OBJECT-TYPE
    SYNTAX     SEQUENCE OF HmSetupWanAdditionalPptpGatewaysEntry
    MAX-ACCESS not-accessible
    STATUS     current
    DESCRIPTION
            "-- empty --"
    ::= { hmSetupWan 30 }

-- {ROW} 1.3.6.1.4.1.248.32.18.2.2.30.1
hmSetupWanAdditionalPptpGatewaysEntry OBJECT-TYPE
    SYNTAX     HmSetupWanAdditionalPptpGatewaysEntry
    MAX-ACCESS not-accessible
    STATUS     current
    DESCRIPTION
            ""
    INDEX {
            hmSetupWanAdditionalPptpGatewaysEntryPeer
          }
    ::= { hmSetupWanAdditionalPptpGatewaysTable 1 }

HmSetupWanAdditionalPptpGatewaysEntry ::= SEQUENCE {
            hmSetupWanAdditionalPptpGatewaysEntryPeer DisplayString,
            hmSetupWanAdditionalPptpGatewaysEntryBeginWith INTEGER,
            hmSetupWanAdditionalPptpGatewaysEntryGateway1 DisplayString,
            hmSetupWanAdditionalPptpGatewaysEntryRtgTag1 Integer32,
            hmSetupWanAdditionalPptpGatewaysEntryGateway2 DisplayString,
            hmSetupWanAdditionalPptpGatewaysEntryRtgTag2 Integer32,
            hmSetupWanAdditionalPptpGatewaysEntryGateway3 DisplayString,
            hmSetupWanAdditionalPptpGatewaysEntryRtgTag3 Integer32,
            hmSetupWanAdditionalPptpGatewaysEntryGateway4 DisplayString,
            hmSetupWanAdditionalPptpGatewaysEntryRtgTag4 Integer32,
            hmSetupWanAdditionalPptpGatewaysEntryGateway5 DisplayString,
            hmSetupWanAdditionalPptpGatewaysEntryRtgTag5 Integer32,
            hmSetupWanAdditionalPptpGatewaysEntryGateway6 DisplayString,
            hmSetupWanAdditionalPptpGatewaysEntryRtgTag6 Integer32,
            hmSetupWanAdditionalPptpGatewaysEntryGateway7 DisplayString,
            hmSetupWanAdditionalPptpGatewaysEntryRtgTag7 Integer32,
            hmSetupWanAdditionalPptpGatewaysEntryGateway8 DisplayString,
            hmSetupWanAdditionalPptpGatewaysEntryRtgTag8 Integer32,
            hmSetupWanAdditionalPptpGatewaysEntryGateway9 DisplayString,
            hmSetupWanAdditionalPptpGatewaysEntryRtgTag9 Integer32,
            hmSetupWanAdditionalPptpGatewaysEntryGateway10 DisplayString,
            hmSetupWanAdditionalPptpGatewaysEntryRtgTag10 Integer32,
            hmSetupWanAdditionalPptpGatewaysEntryGateway11 DisplayString,
            hmSetupWanAdditionalPptpGatewaysEntryRtgTag11 Integer32,
            hmSetupWanAdditionalPptpGatewaysEntryGateway12 DisplayString,
            hmSetupWanAdditionalPptpGatewaysEntryRtgTag12 Integer32,
            hmSetupWanAdditionalPptpGatewaysEntryGateway13 DisplayString,
            hmSetupWanAdditionalPptpGatewaysEntryRtgTag13 Integer32,
            hmSetupWanAdditionalPptpGatewaysEntryGateway14 DisplayString,
            hmSetupWanAdditionalPptpGatewaysEntryRtgTag14 Integer32,
            hmSetupWanAdditionalPptpGatewaysEntryGateway15 DisplayString,
            hmSetupWanAdditionalPptpGatewaysEntryRtgTag15 Integer32,
            hmSetupWanAdditionalPptpGatewaysEntryGateway16 DisplayString,
            hmSetupWanAdditionalPptpGatewaysEntryRtgTag16 Integer32,
            hmSetupWanAdditionalPptpGatewaysEntryGateway17 DisplayString,
            hmSetupWanAdditionalPptpGatewaysEntryRtgTag17 Integer32,
            hmSetupWanAdditionalPptpGatewaysEntryGateway18 DisplayString,
            hmSetupWanAdditionalPptpGatewaysEntryRtgTag18 Integer32,
            hmSetupWanAdditionalPptpGatewaysEntryGateway19 DisplayString,
            hmSetupWanAdditionalPptpGatewaysEntryRtgTag19 Integer32,
            hmSetupWanAdditionalPptpGatewaysEntryGateway20 DisplayString,
            hmSetupWanAdditionalPptpGatewaysEntryRtgTag20 Integer32,
            hmSetupWanAdditionalPptpGatewaysEntryGateway21 DisplayString,
            hmSetupWanAdditionalPptpGatewaysEntryRtgTag21 Integer32,
            hmSetupWanAdditionalPptpGatewaysEntryGateway22 DisplayString,
            hmSetupWanAdditionalPptpGatewaysEntryRtgTag22 Integer32,
            hmSetupWanAdditionalPptpGatewaysEntryGateway23 DisplayString,
            hmSetupWanAdditionalPptpGatewaysEntryRtgTag23 Integer32,
            hmSetupWanAdditionalPptpGatewaysEntryGateway24 DisplayString,
            hmSetupWanAdditionalPptpGatewaysEntryRtgTag24 Integer32,
            hmSetupWanAdditionalPptpGatewaysEntryGateway25 DisplayString,
            hmSetupWanAdditionalPptpGatewaysEntryRtgTag25 Integer32,
            hmSetupWanAdditionalPptpGatewaysEntryGateway26 DisplayString,
            hmSetupWanAdditionalPptpGatewaysEntryRtgTag26 Integer32,
            hmSetupWanAdditionalPptpGatewaysEntryGateway27 DisplayString,
            hmSetupWanAdditionalPptpGatewaysEntryRtgTag27 Integer32,
            hmSetupWanAdditionalPptpGatewaysEntryGateway28 DisplayString,
            hmSetupWanAdditionalPptpGatewaysEntryRtgTag28 Integer32,
            hmSetupWanAdditionalPptpGatewaysEntryGateway29 DisplayString,
            hmSetupWanAdditionalPptpGatewaysEntryRtgTag29 Integer32,
            hmSetupWanAdditionalPptpGatewaysEntryGateway30 DisplayString,
            hmSetupWanAdditionalPptpGatewaysEntryRtgTag30 Integer32,
            hmSetupWanAdditionalPptpGatewaysEntryGateway31 DisplayString,
            hmSetupWanAdditionalPptpGatewaysEntryRtgTag31 Integer32,
            hmSetupWanAdditionalPptpGatewaysEntryGateway32 DisplayString,
            hmSetupWanAdditionalPptpGatewaysEntryRtgTag32 Integer32
    }

-- {COLUMN} 1.3.6.1.4.1.248.32.18.2.2.30.1.1
hmSetupWanAdditionalPptpGatewaysEntryPeer OBJECT-TYPE
    SYNTAX     DisplayString (SIZE(0..16))
    MAX-ACCESS read-write
    STATUS     current
    DESCRIPTION
            "-- empty --"
    ::= { hmSetupWanAdditionalPptpGatewaysEntry 1 }

-- {COLUMN} 1.3.6.1.4.1.248.32.18.2.2.30.1.2
hmSetupWanAdditionalPptpGatewaysEntryBeginWith OBJECT-TYPE
    SYNTAX     INTEGER {
                  eLastUsed (0),
                  eFirst (1),
                  eRandom (2)
            }
    MAX-ACCESS read-write
    STATUS     current
    DESCRIPTION
            "-- empty --"
    ::= { hmSetupWanAdditionalPptpGatewaysEntry 2 }

-- {COLUMN} 1.3.6.1.4.1.248.32.18.2.2.30.1.3
hmSetupWanAdditionalPptpGatewaysEntryGateway1 OBJECT-TYPE
    SYNTAX     DisplayString (SIZE(0..64))
    MAX-ACCESS read-write
    STATUS     current
    DESCRIPTION
            "-- empty --"
    ::= { hmSetupWanAdditionalPptpGatewaysEntry 3 }

-- {COLUMN} 1.3.6.1.4.1.248.32.18.2.2.30.1.4
hmSetupWanAdditionalPptpGatewaysEntryRtgTag1 OBJECT-TYPE
    SYNTAX     Integer32 (0..65535)
    MAX-ACCESS read-write
    STATUS     current
    DESCRIPTION
            "-- empty --"
    ::= { hmSetupWanAdditionalPptpGatewaysEntry 4 }

-- {COLUMN} 1.3.6.1.4.1.248.32.18.2.2.30.1.5
hmSetupWanAdditionalPptpGatewaysEntryGateway2 OBJECT-TYPE
    SYNTAX     DisplayString (SIZE(0..64))
    MAX-ACCESS read-write
    STATUS     current
    DESCRIPTION
            "-- empty --"
    ::= { hmSetupWanAdditionalPptpGatewaysEntry 5 }

-- {COLUMN} 1.3.6.1.4.1.248.32.18.2.2.30.1.6
hmSetupWanAdditionalPptpGatewaysEntryRtgTag2 OBJECT-TYPE
    SYNTAX     Integer32 (0..65535)
    MAX-ACCESS read-write
    STATUS     current
    DESCRIPTION
            "-- empty --"
    ::= { hmSetupWanAdditionalPptpGatewaysEntry 6 }

-- {COLUMN} 1.3.6.1.4.1.248.32.18.2.2.30.1.7
hmSetupWanAdditionalPptpGatewaysEntryGateway3 OBJECT-TYPE
    SYNTAX     DisplayString (SIZE(0..64))
    MAX-ACCESS read-write
    STATUS     current
    DESCRIPTION
            "-- empty --"
    ::= { hmSetupWanAdditionalPptpGatewaysEntry 7 }

-- {COLUMN} 1.3.6.1.4.1.248.32.18.2.2.30.1.8
hmSetupWanAdditionalPptpGatewaysEntryRtgTag3 OBJECT-TYPE
    SYNTAX     Integer32 (0..65535)
    MAX-ACCESS read-write
    STATUS     current
    DESCRIPTION
            "-- empty --"
    ::= { hmSetupWanAdditionalPptpGatewaysEntry 8 }

-- {COLUMN} 1.3.6.1.4.1.248.32.18.2.2.30.1.9
hmSetupWanAdditionalPptpGatewaysEntryGateway4 OBJECT-TYPE
    SYNTAX     DisplayString (SIZE(0..64))
    MAX-ACCESS read-write
    STATUS     current
    DESCRIPTION
            "-- empty --"
    ::= { hmSetupWanAdditionalPptpGatewaysEntry 9 }

-- {COLUMN} 1.3.6.1.4.1.248.32.18.2.2.30.1.10
hmSetupWanAdditionalPptpGatewaysEntryRtgTag4 OBJECT-TYPE
    SYNTAX     Integer32 (0..65535)
    MAX-ACCESS read-write
    STATUS     current
    DESCRIPTION
            "-- empty --"
    ::= { hmSetupWanAdditionalPptpGatewaysEntry 10 }

-- {COLUMN} 1.3.6.1.4.1.248.32.18.2.2.30.1.11
hmSetupWanAdditionalPptpGatewaysEntryGateway5 OBJECT-TYPE
    SYNTAX     DisplayString (SIZE(0..64))
    MAX-ACCESS read-write
    STATUS     current
    DESCRIPTION
            "-- empty --"
    ::= { hmSetupWanAdditionalPptpGatewaysEntry 11 }

-- {COLUMN} 1.3.6.1.4.1.248.32.18.2.2.30.1.12
hmSetupWanAdditionalPptpGatewaysEntryRtgTag5 OBJECT-TYPE
    SYNTAX     Integer32 (0..65535)
    MAX-ACCESS read-write
    STATUS     current
    DESCRIPTION
            "-- empty --"
    ::= { hmSetupWanAdditionalPptpGatewaysEntry 12 }

-- {COLUMN} 1.3.6.1.4.1.248.32.18.2.2.30.1.13
hmSetupWanAdditionalPptpGatewaysEntryGateway6 OBJECT-TYPE
    SYNTAX     DisplayString (SIZE(0..64))
    MAX-ACCESS read-write
    STATUS     current
    DESCRIPTION
            "-- empty --"
    ::= { hmSetupWanAdditionalPptpGatewaysEntry 13 }

-- {COLUMN} 1.3.6.1.4.1.248.32.18.2.2.30.1.14
hmSetupWanAdditionalPptpGatewaysEntryRtgTag6 OBJECT-TYPE
    SYNTAX     Integer32 (0..65535)
    MAX-ACCESS read-write
    STATUS     current
    DESCRIPTION
            "-- empty --"
    ::= { hmSetupWanAdditionalPptpGatewaysEntry 14 }

-- {COLUMN} 1.3.6.1.4.1.248.32.18.2.2.30.1.15
hmSetupWanAdditionalPptpGatewaysEntryGateway7 OBJECT-TYPE
    SYNTAX     DisplayString (SIZE(0..64))
    MAX-ACCESS read-write
    STATUS     current
    DESCRIPTION
            "-- empty --"
    ::= { hmSetupWanAdditionalPptpGatewaysEntry 15 }

-- {COLUMN} 1.3.6.1.4.1.248.32.18.2.2.30.1.16
hmSetupWanAdditionalPptpGatewaysEntryRtgTag7 OBJECT-TYPE
    SYNTAX     Integer32 (0..65535)
    MAX-ACCESS read-write
    STATUS     current
    DESCRIPTION
            "-- empty --"
    ::= { hmSetupWanAdditionalPptpGatewaysEntry 16 }

-- {COLUMN} 1.3.6.1.4.1.248.32.18.2.2.30.1.17
hmSetupWanAdditionalPptpGatewaysEntryGateway8 OBJECT-TYPE
    SYNTAX     DisplayString (SIZE(0..64))
    MAX-ACCESS read-write
    STATUS     current
    DESCRIPTION
            "-- empty --"
    ::= { hmSetupWanAdditionalPptpGatewaysEntry 17 }

-- {COLUMN} 1.3.6.1.4.1.248.32.18.2.2.30.1.18
hmSetupWanAdditionalPptpGatewaysEntryRtgTag8 OBJECT-TYPE
    SYNTAX     Integer32 (0..65535)
    MAX-ACCESS read-write
    STATUS     current
    DESCRIPTION
            "-- empty --"
    ::= { hmSetupWanAdditionalPptpGatewaysEntry 18 }

-- {COLUMN} 1.3.6.1.4.1.248.32.18.2.2.30.1.19
hmSetupWanAdditionalPptpGatewaysEntryGateway9 OBJECT-TYPE
    SYNTAX     DisplayString (SIZE(0..64))
    MAX-ACCESS read-write
    STATUS     current
    DESCRIPTION
            "-- empty --"
    ::= { hmSetupWanAdditionalPptpGatewaysEntry 19 }

-- {COLUMN} 1.3.6.1.4.1.248.32.18.2.2.30.1.20
hmSetupWanAdditionalPptpGatewaysEntryRtgTag9 OBJECT-TYPE
    SYNTAX     Integer32 (0..65535)
    MAX-ACCESS read-write
    STATUS     current
    DESCRIPTION
            "-- empty --"
    ::= { hmSetupWanAdditionalPptpGatewaysEntry 20 }

-- {COLUMN} 1.3.6.1.4.1.248.32.18.2.2.30.1.21
hmSetupWanAdditionalPptpGatewaysEntryGateway10 OBJECT-TYPE
    SYNTAX     DisplayString (SIZE(0..64))
    MAX-ACCESS read-write
    STATUS     current
    DESCRIPTION
            "-- empty --"
    ::= { hmSetupWanAdditionalPptpGatewaysEntry 21 }

-- {COLUMN} 1.3.6.1.4.1.248.32.18.2.2.30.1.22
hmSetupWanAdditionalPptpGatewaysEntryRtgTag10 OBJECT-TYPE
    SYNTAX     Integer32 (0..65535)
    MAX-ACCESS read-write
    STATUS     current
    DESCRIPTION
            "-- empty --"
    ::= { hmSetupWanAdditionalPptpGatewaysEntry 22 }

-- {COLUMN} 1.3.6.1.4.1.248.32.18.2.2.30.1.23
hmSetupWanAdditionalPptpGatewaysEntryGateway11 OBJECT-TYPE
    SYNTAX     DisplayString (SIZE(0..64))
    MAX-ACCESS read-write
    STATUS     current
    DESCRIPTION
            "-- empty --"
    ::= { hmSetupWanAdditionalPptpGatewaysEntry 23 }

-- {COLUMN} 1.3.6.1.4.1.248.32.18.2.2.30.1.24
hmSetupWanAdditionalPptpGatewaysEntryRtgTag11 OBJECT-TYPE
    SYNTAX     Integer32 (0..65535)
    MAX-ACCESS read-write
    STATUS     current
    DESCRIPTION
            "-- empty --"
    ::= { hmSetupWanAdditionalPptpGatewaysEntry 24 }

-- {COLUMN} 1.3.6.1.4.1.248.32.18.2.2.30.1.25
hmSetupWanAdditionalPptpGatewaysEntryGateway12 OBJECT-TYPE
    SYNTAX     DisplayString (SIZE(0..64))
    MAX-ACCESS read-write
    STATUS     current
    DESCRIPTION
            "-- empty --"
    ::= { hmSetupWanAdditionalPptpGatewaysEntry 25 }

-- {COLUMN} 1.3.6.1.4.1.248.32.18.2.2.30.1.26
hmSetupWanAdditionalPptpGatewaysEntryRtgTag12 OBJECT-TYPE
    SYNTAX     Integer32 (0..65535)
    MAX-ACCESS read-write
    STATUS     current
    DESCRIPTION
            "-- empty --"
    ::= { hmSetupWanAdditionalPptpGatewaysEntry 26 }

-- {COLUMN} 1.3.6.1.4.1.248.32.18.2.2.30.1.27
hmSetupWanAdditionalPptpGatewaysEntryGateway13 OBJECT-TYPE
    SYNTAX     DisplayString (SIZE(0..64))
    MAX-ACCESS read-write
    STATUS     current
    DESCRIPTION
            "-- empty --"
    ::= { hmSetupWanAdditionalPptpGatewaysEntry 27 }

-- {COLUMN} 1.3.6.1.4.1.248.32.18.2.2.30.1.28
hmSetupWanAdditionalPptpGatewaysEntryRtgTag13 OBJECT-TYPE
    SYNTAX     Integer32 (0..65535)
    MAX-ACCESS read-write
    STATUS     current
    DESCRIPTION
            "-- empty --"
    ::= { hmSetupWanAdditionalPptpGatewaysEntry 28 }

-- {COLUMN} 1.3.6.1.4.1.248.32.18.2.2.30.1.29
hmSetupWanAdditionalPptpGatewaysEntryGateway14 OBJECT-TYPE
    SYNTAX     DisplayString (SIZE(0..64))
    MAX-ACCESS read-write
    STATUS     current
    DESCRIPTION
            "-- empty --"
    ::= { hmSetupWanAdditionalPptpGatewaysEntry 29 }

-- {COLUMN} 1.3.6.1.4.1.248.32.18.2.2.30.1.30
hmSetupWanAdditionalPptpGatewaysEntryRtgTag14 OBJECT-TYPE
    SYNTAX     Integer32 (0..65535)
    MAX-ACCESS read-write
    STATUS     current
    DESCRIPTION
            "-- empty --"
    ::= { hmSetupWanAdditionalPptpGatewaysEntry 30 }

-- {COLUMN} 1.3.6.1.4.1.248.32.18.2.2.30.1.31
hmSetupWanAdditionalPptpGatewaysEntryGateway15 OBJECT-TYPE
    SYNTAX     DisplayString (SIZE(0..64))
    MAX-ACCESS read-write
    STATUS     current
    DESCRIPTION
            "-- empty --"
    ::= { hmSetupWanAdditionalPptpGatewaysEntry 31 }

-- {COLUMN} 1.3.6.1.4.1.248.32.18.2.2.30.1.32
hmSetupWanAdditionalPptpGatewaysEntryRtgTag15 OBJECT-TYPE
    SYNTAX     Integer32 (0..65535)
    MAX-ACCESS read-write
    STATUS     current
    DESCRIPTION
            "-- empty --"
    ::= { hmSetupWanAdditionalPptpGatewaysEntry 32 }

-- {COLUMN} 1.3.6.1.4.1.248.32.18.2.2.30.1.33
hmSetupWanAdditionalPptpGatewaysEntryGateway16 OBJECT-TYPE
    SYNTAX     DisplayString (SIZE(0..64))
    MAX-ACCESS read-write
    STATUS     current
    DESCRIPTION
            "-- empty --"
    ::= { hmSetupWanAdditionalPptpGatewaysEntry 33 }

-- {COLUMN} 1.3.6.1.4.1.248.32.18.2.2.30.1.34
hmSetupWanAdditionalPptpGatewaysEntryRtgTag16 OBJECT-TYPE
    SYNTAX     Integer32 (0..65535)
    MAX-ACCESS read-write
    STATUS     current
    DESCRIPTION
            "-- empty --"
    ::= { hmSetupWanAdditionalPptpGatewaysEntry 34 }

-- {COLUMN} 1.3.6.1.4.1.248.32.18.2.2.30.1.35
hmSetupWanAdditionalPptpGatewaysEntryGateway17 OBJECT-TYPE
    SYNTAX     DisplayString (SIZE(0..64))
    MAX-ACCESS read-write
    STATUS     current
    DESCRIPTION
            "-- empty --"
    ::= { hmSetupWanAdditionalPptpGatewaysEntry 35 }

-- {COLUMN} 1.3.6.1.4.1.248.32.18.2.2.30.1.36
hmSetupWanAdditionalPptpGatewaysEntryRtgTag17 OBJECT-TYPE
    SYNTAX     Integer32 (0..65535)
    MAX-ACCESS read-write
    STATUS     current
    DESCRIPTION
            "-- empty --"
    ::= { hmSetupWanAdditionalPptpGatewaysEntry 36 }

-- {COLUMN} 1.3.6.1.4.1.248.32.18.2.2.30.1.37
hmSetupWanAdditionalPptpGatewaysEntryGateway18 OBJECT-TYPE
    SYNTAX     DisplayString (SIZE(0..64))
    MAX-ACCESS read-write
    STATUS     current
    DESCRIPTION
            "-- empty --"
    ::= { hmSetupWanAdditionalPptpGatewaysEntry 37 }

-- {COLUMN} 1.3.6.1.4.1.248.32.18.2.2.30.1.38
hmSetupWanAdditionalPptpGatewaysEntryRtgTag18 OBJECT-TYPE
    SYNTAX     Integer32 (0..65535)
    MAX-ACCESS read-write
    STATUS     current
    DESCRIPTION
            "-- empty --"
    ::= { hmSetupWanAdditionalPptpGatewaysEntry 38 }

-- {COLUMN} 1.3.6.1.4.1.248.32.18.2.2.30.1.39
hmSetupWanAdditionalPptpGatewaysEntryGateway19 OBJECT-TYPE
    SYNTAX     DisplayString (SIZE(0..64))
    MAX-ACCESS read-write
    STATUS     current
    DESCRIPTION
            "-- empty --"
    ::= { hmSetupWanAdditionalPptpGatewaysEntry 39 }

-- {COLUMN} 1.3.6.1.4.1.248.32.18.2.2.30.1.40
hmSetupWanAdditionalPptpGatewaysEntryRtgTag19 OBJECT-TYPE
    SYNTAX     Integer32 (0..65535)
    MAX-ACCESS read-write
    STATUS     current
    DESCRIPTION
            "-- empty --"
    ::= { hmSetupWanAdditionalPptpGatewaysEntry 40 }

-- {COLUMN} 1.3.6.1.4.1.248.32.18.2.2.30.1.41
hmSetupWanAdditionalPptpGatewaysEntryGateway20 OBJECT-TYPE
    SYNTAX     DisplayString (SIZE(0..64))
    MAX-ACCESS read-write
    STATUS     current
    DESCRIPTION
            "-- empty --"
    ::= { hmSetupWanAdditionalPptpGatewaysEntry 41 }

-- {COLUMN} 1.3.6.1.4.1.248.32.18.2.2.30.1.42
hmSetupWanAdditionalPptpGatewaysEntryRtgTag20 OBJECT-TYPE
    SYNTAX     Integer32 (0..65535)
    MAX-ACCESS read-write
    STATUS     current
    DESCRIPTION
            "-- empty --"
    ::= { hmSetupWanAdditionalPptpGatewaysEntry 42 }

-- {COLUMN} 1.3.6.1.4.1.248.32.18.2.2.30.1.43
hmSetupWanAdditionalPptpGatewaysEntryGateway21 OBJECT-TYPE
    SYNTAX     DisplayString (SIZE(0..64))
    MAX-ACCESS read-write
    STATUS     current
    DESCRIPTION
            "-- empty --"
    ::= { hmSetupWanAdditionalPptpGatewaysEntry 43 }

-- {COLUMN} 1.3.6.1.4.1.248.32.18.2.2.30.1.44
hmSetupWanAdditionalPptpGatewaysEntryRtgTag21 OBJECT-TYPE
    SYNTAX     Integer32 (0..65535)
    MAX-ACCESS read-write
    STATUS     current
    DESCRIPTION
            "-- empty --"
    ::= { hmSetupWanAdditionalPptpGatewaysEntry 44 }

-- {COLUMN} 1.3.6.1.4.1.248.32.18.2.2.30.1.45
hmSetupWanAdditionalPptpGatewaysEntryGateway22 OBJECT-TYPE
    SYNTAX     DisplayString (SIZE(0..64))
    MAX-ACCESS read-write
    STATUS     current
    DESCRIPTION
            "-- empty --"
    ::= { hmSetupWanAdditionalPptpGatewaysEntry 45 }

-- {COLUMN} 1.3.6.1.4.1.248.32.18.2.2.30.1.46
hmSetupWanAdditionalPptpGatewaysEntryRtgTag22 OBJECT-TYPE
    SYNTAX     Integer32 (0..65535)
    MAX-ACCESS read-write
    STATUS     current
    DESCRIPTION
            "-- empty --"
    ::= { hmSetupWanAdditionalPptpGatewaysEntry 46 }

-- {COLUMN} 1.3.6.1.4.1.248.32.18.2.2.30.1.47
hmSetupWanAdditionalPptpGatewaysEntryGateway23 OBJECT-TYPE
    SYNTAX     DisplayString (SIZE(0..64))
    MAX-ACCESS read-write
    STATUS     current
    DESCRIPTION
            "-- empty --"
    ::= { hmSetupWanAdditionalPptpGatewaysEntry 47 }

-- {COLUMN} 1.3.6.1.4.1.248.32.18.2.2.30.1.48
hmSetupWanAdditionalPptpGatewaysEntryRtgTag23 OBJECT-TYPE
    SYNTAX     Integer32 (0..65535)
    MAX-ACCESS read-write
    STATUS     current
    DESCRIPTION
            "-- empty --"
    ::= { hmSetupWanAdditionalPptpGatewaysEntry 48 }

-- {COLUMN} 1.3.6.1.4.1.248.32.18.2.2.30.1.49
hmSetupWanAdditionalPptpGatewaysEntryGateway24 OBJECT-TYPE
    SYNTAX     DisplayString (SIZE(0..64))
    MAX-ACCESS read-write
    STATUS     current
    DESCRIPTION
            "-- empty --"
    ::= { hmSetupWanAdditionalPptpGatewaysEntry 49 }

-- {COLUMN} 1.3.6.1.4.1.248.32.18.2.2.30.1.50
hmSetupWanAdditionalPptpGatewaysEntryRtgTag24 OBJECT-TYPE
    SYNTAX     Integer32 (0..65535)
    MAX-ACCESS read-write
    STATUS     current
    DESCRIPTION
            "-- empty --"
    ::= { hmSetupWanAdditionalPptpGatewaysEntry 50 }

-- {COLUMN} 1.3.6.1.4.1.248.32.18.2.2.30.1.51
hmSetupWanAdditionalPptpGatewaysEntryGateway25 OBJECT-TYPE
    SYNTAX     DisplayString (SIZE(0..64))
    MAX-ACCESS read-write
    STATUS     current
    DESCRIPTION
            "-- empty --"
    ::= { hmSetupWanAdditionalPptpGatewaysEntry 51 }

-- {COLUMN} 1.3.6.1.4.1.248.32.18.2.2.30.1.52
hmSetupWanAdditionalPptpGatewaysEntryRtgTag25 OBJECT-TYPE
    SYNTAX     Integer32 (0..65535)
    MAX-ACCESS read-write
    STATUS     current
    DESCRIPTION
            "-- empty --"
    ::= { hmSetupWanAdditionalPptpGatewaysEntry 52 }

-- {COLUMN} 1.3.6.1.4.1.248.32.18.2.2.30.1.53
hmSetupWanAdditionalPptpGatewaysEntryGateway26 OBJECT-TYPE
    SYNTAX     DisplayString (SIZE(0..64))
    MAX-ACCESS read-write
    STATUS     current
    DESCRIPTION
            "-- empty --"
    ::= { hmSetupWanAdditionalPptpGatewaysEntry 53 }

-- {COLUMN} 1.3.6.1.4.1.248.32.18.2.2.30.1.54
hmSetupWanAdditionalPptpGatewaysEntryRtgTag26 OBJECT-TYPE
    SYNTAX     Integer32 (0..65535)
    MAX-ACCESS read-write
    STATUS     current
    DESCRIPTION
            "-- empty --"
    ::= { hmSetupWanAdditionalPptpGatewaysEntry 54 }

-- {COLUMN} 1.3.6.1.4.1.248.32.18.2.2.30.1.55
hmSetupWanAdditionalPptpGatewaysEntryGateway27 OBJECT-TYPE
    SYNTAX     DisplayString (SIZE(0..64))
    MAX-ACCESS read-write
    STATUS     current
    DESCRIPTION
            "-- empty --"
    ::= { hmSetupWanAdditionalPptpGatewaysEntry 55 }

-- {COLUMN} 1.3.6.1.4.1.248.32.18.2.2.30.1.56
hmSetupWanAdditionalPptpGatewaysEntryRtgTag27 OBJECT-TYPE
    SYNTAX     Integer32 (0..65535)
    MAX-ACCESS read-write
    STATUS     current
    DESCRIPTION
            "-- empty --"
    ::= { hmSetupWanAdditionalPptpGatewaysEntry 56 }

-- {COLUMN} 1.3.6.1.4.1.248.32.18.2.2.30.1.57
hmSetupWanAdditionalPptpGatewaysEntryGateway28 OBJECT-TYPE
    SYNTAX     DisplayString (SIZE(0..64))
    MAX-ACCESS read-write
    STATUS     current
    DESCRIPTION
            "-- empty --"
    ::= { hmSetupWanAdditionalPptpGatewaysEntry 57 }

-- {COLUMN} 1.3.6.1.4.1.248.32.18.2.2.30.1.58
hmSetupWanAdditionalPptpGatewaysEntryRtgTag28 OBJECT-TYPE
    SYNTAX     Integer32 (0..65535)
    MAX-ACCESS read-write
    STATUS     current
    DESCRIPTION
            "-- empty --"
    ::= { hmSetupWanAdditionalPptpGatewaysEntry 58 }

-- {COLUMN} 1.3.6.1.4.1.248.32.18.2.2.30.1.59
hmSetupWanAdditionalPptpGatewaysEntryGateway29 OBJECT-TYPE
    SYNTAX     DisplayString (SIZE(0..64))
    MAX-ACCESS read-write
    STATUS     current
    DESCRIPTION
            "-- empty --"
    ::= { hmSetupWanAdditionalPptpGatewaysEntry 59 }

-- {COLUMN} 1.3.6.1.4.1.248.32.18.2.2.30.1.60
hmSetupWanAdditionalPptpGatewaysEntryRtgTag29 OBJECT-TYPE
    SYNTAX     Integer32 (0..65535)
    MAX-ACCESS read-write
    STATUS     current
    DESCRIPTION
            "-- empty --"
    ::= { hmSetupWanAdditionalPptpGatewaysEntry 60 }

-- {COLUMN} 1.3.6.1.4.1.248.32.18.2.2.30.1.61
hmSetupWanAdditionalPptpGatewaysEntryGateway30 OBJECT-TYPE
    SYNTAX     DisplayString (SIZE(0..64))
    MAX-ACCESS read-write
    STATUS     current
    DESCRIPTION
            "-- empty --"
    ::= { hmSetupWanAdditionalPptpGatewaysEntry 61 }

-- {COLUMN} 1.3.6.1.4.1.248.32.18.2.2.30.1.62
hmSetupWanAdditionalPptpGatewaysEntryRtgTag30 OBJECT-TYPE
    SYNTAX     Integer32 (0..65535)
    MAX-ACCESS read-write
    STATUS     current
    DESCRIPTION
            "-- empty --"
    ::= { hmSetupWanAdditionalPptpGatewaysEntry 62 }

-- {COLUMN} 1.3.6.1.4.1.248.32.18.2.2.30.1.63
hmSetupWanAdditionalPptpGatewaysEntryGateway31 OBJECT-TYPE
    SYNTAX     DisplayString (SIZE(0..64))
    MAX-ACCESS read-write
    STATUS     current
    DESCRIPTION
            "-- empty --"
    ::= { hmSetupWanAdditionalPptpGatewaysEntry 63 }

-- {COLUMN} 1.3.6.1.4.1.248.32.18.2.2.30.1.64
hmSetupWanAdditionalPptpGatewaysEntryRtgTag31 OBJECT-TYPE
    SYNTAX     Integer32 (0..65535)
    MAX-ACCESS read-write
    STATUS     current
    DESCRIPTION
            "-- empty --"
    ::= { hmSetupWanAdditionalPptpGatewaysEntry 64 }

-- {COLUMN} 1.3.6.1.4.1.248.32.18.2.2.30.1.65
hmSetupWanAdditionalPptpGatewaysEntryGateway32 OBJECT-TYPE
    SYNTAX     DisplayString (SIZE(0..64))
    MAX-ACCESS read-write
    STATUS     current
    DESCRIPTION
            "-- empty --"
    ::= { hmSetupWanAdditionalPptpGatewaysEntry 65 }

-- {COLUMN} 1.3.6.1.4.1.248.32.18.2.2.30.1.66
hmSetupWanAdditionalPptpGatewaysEntryRtgTag32 OBJECT-TYPE
    SYNTAX     Integer32 (0..65535)
    MAX-ACCESS read-write
    STATUS     current
    DESCRIPTION
            "-- empty --"
    ::= { hmSetupWanAdditionalPptpGatewaysEntry 66 }

-- {SCALAR} 1.3.6.1.4.1.248.32.18.2.2.31
hmSetupWanPptpSourceCheck OBJECT-TYPE
    SYNTAX     INTEGER {
                  eAddress (0),
                  eTagPlusAddress (1)
            }
    MAX-ACCESS read-write
    STATUS     current
    DESCRIPTION
            "-- empty --"
    ::= { hmSetupWan 31 }

-- {TABLE} 1.3.6.1.4.1.248.32.18.2.2.35
hmSetupWanL2tpEndpointsTable OBJECT-TYPE
    SYNTAX     SEQUENCE OF HmSetupWanL2tpEndpointsEntry
    MAX-ACCESS not-accessible
    STATUS     current
    DESCRIPTION
            "-- empty --"
    ::= { hmSetupWan 35 }

-- {ROW} 1.3.6.1.4.1.248.32.18.2.2.35.1
hmSetupWanL2tpEndpointsEntry OBJECT-TYPE
    SYNTAX     HmSetupWanL2tpEndpointsEntry
    MAX-ACCESS not-accessible
    STATUS     current
    DESCRIPTION
            ""
    INDEX {
            hmSetupWanL2tpEndpointsEntryIdentifier
          }
    ::= { hmSetupWanL2tpEndpointsTable 1 }

HmSetupWanL2tpEndpointsEntry ::= SEQUENCE {
            hmSetupWanL2tpEndpointsEntryIdentifier DisplayString,
            hmSetupWanL2tpEndpointsEntryIpAddress DisplayString,
            hmSetupWanL2tpEndpointsEntryRtgTag Integer32,
            hmSetupWanL2tpEndpointsEntryPort Integer32,
            hmSetupWanL2tpEndpointsEntryPoll Integer32,
            hmSetupWanL2tpEndpointsEntryHostname DisplayString,
            hmSetupWanL2tpEndpointsEntryPassword DisplayString,
            hmSetupWanL2tpEndpointsEntryAuthPeer INTEGER,
            hmSetupWanL2tpEndpointsEntryHide INTEGER,
            hmSetupWanL2tpEndpointsEntryLoopbackAddress DisplayString
    }

-- {COLUMN} 1.3.6.1.4.1.248.32.18.2.2.35.1.1
hmSetupWanL2tpEndpointsEntryIdentifier OBJECT-TYPE
    SYNTAX     DisplayString (SIZE(0..16))
    MAX-ACCESS read-write
    STATUS     current
    DESCRIPTION
            "-- empty --"
    ::= { hmSetupWanL2tpEndpointsEntry 1 }

-- {COLUMN} 1.3.6.1.4.1.248.32.18.2.2.35.1.2
hmSetupWanL2tpEndpointsEntryIpAddress OBJECT-TYPE
    SYNTAX     DisplayString (SIZE(0..64))
    MAX-ACCESS read-write
    STATUS     current
    DESCRIPTION
            "-- empty --"
    ::= { hmSetupWanL2tpEndpointsEntry 2 }

-- {COLUMN} 1.3.6.1.4.1.248.32.18.2.2.35.1.3
hmSetupWanL2tpEndpointsEntryRtgTag OBJECT-TYPE
    SYNTAX     Integer32 (0..65535)
    MAX-ACCESS read-write
    STATUS     current
    DESCRIPTION
            "-- empty --"
    ::= { hmSetupWanL2tpEndpointsEntry 3 }

-- {COLUMN} 1.3.6.1.4.1.248.32.18.2.2.35.1.4
hmSetupWanL2tpEndpointsEntryPort OBJECT-TYPE
    SYNTAX     Integer32 (0..65535)
    MAX-ACCESS read-write
    STATUS     current
    DESCRIPTION
            "-- empty --"
    ::= { hmSetupWanL2tpEndpointsEntry 4 }

-- {COLUMN} 1.3.6.1.4.1.248.32.18.2.2.35.1.5
hmSetupWanL2tpEndpointsEntryPoll OBJECT-TYPE
    SYNTAX     Integer32 (0..65535)
    MAX-ACCESS read-write
    STATUS     current
    DESCRIPTION
            "-- empty --"
    ::= { hmSetupWanL2tpEndpointsEntry 5 }

-- {COLUMN} 1.3.6.1.4.1.248.32.18.2.2.35.1.6
hmSetupWanL2tpEndpointsEntryHostname OBJECT-TYPE
    SYNTAX     DisplayString (SIZE(0..64))
    MAX-ACCESS read-write
    STATUS     current
    DESCRIPTION
            "-- empty --"
    ::= { hmSetupWanL2tpEndpointsEntry 6 }

-- {COLUMN} 1.3.6.1.4.1.248.32.18.2.2.35.1.7
hmSetupWanL2tpEndpointsEntryPassword OBJECT-TYPE
    SYNTAX     DisplayString (SIZE(0..32))
    MAX-ACCESS read-write
    STATUS     current
    DESCRIPTION
            "-- empty --"
    ::= { hmSetupWanL2tpEndpointsEntry 7 }

-- {COLUMN} 1.3.6.1.4.1.248.32.18.2.2.35.1.8
hmSetupWanL2tpEndpointsEntryAuthPeer OBJECT-TYPE
    SYNTAX     INTEGER {
                  eNo (0),
                  eYes (1)
            }
    MAX-ACCESS read-write
    STATUS     current
    DESCRIPTION
            "-- empty --"
    ::= { hmSetupWanL2tpEndpointsEntry 8 }

-- {COLUMN} 1.3.6.1.4.1.248.32.18.2.2.35.1.9
hmSetupWanL2tpEndpointsEntryHide OBJECT-TYPE
    SYNTAX     INTEGER {
                  eNo (0),
                  eYes (1)
            }
    MAX-ACCESS read-write
    STATUS     current
    DESCRIPTION
            "-- empty --"
    ::= { hmSetupWanL2tpEndpointsEntry 9 }

-- {COLUMN} 1.3.6.1.4.1.248.32.18.2.2.35.1.10
hmSetupWanL2tpEndpointsEntryLoopbackAddress OBJECT-TYPE
    SYNTAX     DisplayString (SIZE(0..16))
    MAX-ACCESS read-write
    STATUS     current
    DESCRIPTION
            "-- empty --"
    ::= { hmSetupWanL2tpEndpointsEntry 10 }

-- {TABLE} 1.3.6.1.4.1.248.32.18.2.2.36
hmSetupWanL2tpAdditionalGatewaysTable OBJECT-TYPE
    SYNTAX     SEQUENCE OF HmSetupWanL2tpAdditionalGatewaysEntry
    MAX-ACCESS not-accessible
    STATUS     current
    DESCRIPTION
            "-- empty --"
    ::= { hmSetupWan 36 }

-- {ROW} 1.3.6.1.4.1.248.32.18.2.2.36.1
hmSetupWanL2tpAdditionalGatewaysEntry OBJECT-TYPE
    SYNTAX     HmSetupWanL2tpAdditionalGatewaysEntry
    MAX-ACCESS not-accessible
    STATUS     current
    DESCRIPTION
            ""
    INDEX {
            hmSetupWanL2tpAdditionalGatewaysEntryIdentifier
          }
    ::= { hmSetupWanL2tpAdditionalGatewaysTable 1 }

HmSetupWanL2tpAdditionalGatewaysEntry ::= SEQUENCE {
            hmSetupWanL2tpAdditionalGatewaysEntryIdentifier DisplayString,
            hmSetupWanL2tpAdditionalGatewaysEntryBeginWith INTEGER,
            hmSetupWanL2tpAdditionalGatewaysEntryGateway1 DisplayString,
            hmSetupWanL2tpAdditionalGatewaysEntryRtgTag1 Integer32,
            hmSetupWanL2tpAdditionalGatewaysEntryGateway2 DisplayString,
            hmSetupWanL2tpAdditionalGatewaysEntryRtgTag2 Integer32,
            hmSetupWanL2tpAdditionalGatewaysEntryGateway3 DisplayString,
            hmSetupWanL2tpAdditionalGatewaysEntryRtgTag3 Integer32,
            hmSetupWanL2tpAdditionalGatewaysEntryGateway4 DisplayString,
            hmSetupWanL2tpAdditionalGatewaysEntryRtgTag4 Integer32,
            hmSetupWanL2tpAdditionalGatewaysEntryGateway5 DisplayString,
            hmSetupWanL2tpAdditionalGatewaysEntryRtgTag5 Integer32,
            hmSetupWanL2tpAdditionalGatewaysEntryGateway6 DisplayString,
            hmSetupWanL2tpAdditionalGatewaysEntryRtgTag6 Integer32,
            hmSetupWanL2tpAdditionalGatewaysEntryGateway7 DisplayString,
            hmSetupWanL2tpAdditionalGatewaysEntryRtgTag7 Integer32,
            hmSetupWanL2tpAdditionalGatewaysEntryGateway8 DisplayString,
            hmSetupWanL2tpAdditionalGatewaysEntryRtgTag8 Integer32,
            hmSetupWanL2tpAdditionalGatewaysEntryGateway9 DisplayString,
            hmSetupWanL2tpAdditionalGatewaysEntryRtgTag9 Integer32,
            hmSetupWanL2tpAdditionalGatewaysEntryGateway10 DisplayString,
            hmSetupWanL2tpAdditionalGatewaysEntryRtgTag10 Integer32,
            hmSetupWanL2tpAdditionalGatewaysEntryGateway11 DisplayString,
            hmSetupWanL2tpAdditionalGatewaysEntryRtgTag11 Integer32,
            hmSetupWanL2tpAdditionalGatewaysEntryGateway12 DisplayString,
            hmSetupWanL2tpAdditionalGatewaysEntryRtgTag12 Integer32,
            hmSetupWanL2tpAdditionalGatewaysEntryGateway13 DisplayString,
            hmSetupWanL2tpAdditionalGatewaysEntryRtgTag13 Integer32,
            hmSetupWanL2tpAdditionalGatewaysEntryGateway14 DisplayString,
            hmSetupWanL2tpAdditionalGatewaysEntryRtgTag14 Integer32,
            hmSetupWanL2tpAdditionalGatewaysEntryGateway15 DisplayString,
            hmSetupWanL2tpAdditionalGatewaysEntryRtgTag15 Integer32,
            hmSetupWanL2tpAdditionalGatewaysEntryGateway16 DisplayString,
            hmSetupWanL2tpAdditionalGatewaysEntryRtgTag16 Integer32,
            hmSetupWanL2tpAdditionalGatewaysEntryGateway17 DisplayString,
            hmSetupWanL2tpAdditionalGatewaysEntryRtgTag17 Integer32,
            hmSetupWanL2tpAdditionalGatewaysEntryGateway18 DisplayString,
            hmSetupWanL2tpAdditionalGatewaysEntryRtgTag18 Integer32,
            hmSetupWanL2tpAdditionalGatewaysEntryGateway19 DisplayString,
            hmSetupWanL2tpAdditionalGatewaysEntryRtgTag19 Integer32,
            hmSetupWanL2tpAdditionalGatewaysEntryGateway20 DisplayString,
            hmSetupWanL2tpAdditionalGatewaysEntryRtgTag20 Integer32,
            hmSetupWanL2tpAdditionalGatewaysEntryGateway21 DisplayString,
            hmSetupWanL2tpAdditionalGatewaysEntryRtgTag21 Integer32,
            hmSetupWanL2tpAdditionalGatewaysEntryGateway22 DisplayString,
            hmSetupWanL2tpAdditionalGatewaysEntryRtgTag22 Integer32,
            hmSetupWanL2tpAdditionalGatewaysEntryGateway23 DisplayString,
            hmSetupWanL2tpAdditionalGatewaysEntryRtgTag23 Integer32,
            hmSetupWanL2tpAdditionalGatewaysEntryGateway24 DisplayString,
            hmSetupWanL2tpAdditionalGatewaysEntryRtgTag24 Integer32,
            hmSetupWanL2tpAdditionalGatewaysEntryGateway25 DisplayString,
            hmSetupWanL2tpAdditionalGatewaysEntryRtgTag25 Integer32,
            hmSetupWanL2tpAdditionalGatewaysEntryGateway26 DisplayString,
            hmSetupWanL2tpAdditionalGatewaysEntryRtgTag26 Integer32,
            hmSetupWanL2tpAdditionalGatewaysEntryGateway27 DisplayString,
            hmSetupWanL2tpAdditionalGatewaysEntryRtgTag27 Integer32,
            hmSetupWanL2tpAdditionalGatewaysEntryGateway28 DisplayString,
            hmSetupWanL2tpAdditionalGatewaysEntryRtgTag28 Integer32,
            hmSetupWanL2tpAdditionalGatewaysEntryGateway29 DisplayString,
            hmSetupWanL2tpAdditionalGatewaysEntryRtgTag29 Integer32,
            hmSetupWanL2tpAdditionalGatewaysEntryGateway30 DisplayString,
            hmSetupWanL2tpAdditionalGatewaysEntryRtgTag30 Integer32,
            hmSetupWanL2tpAdditionalGatewaysEntryGateway31 DisplayString,
            hmSetupWanL2tpAdditionalGatewaysEntryRtgTag31 Integer32,
            hmSetupWanL2tpAdditionalGatewaysEntryGateway32 DisplayString,
            hmSetupWanL2tpAdditionalGatewaysEntryRtgTag32 Integer32
    }

-- {COLUMN} 1.3.6.1.4.1.248.32.18.2.2.36.1.1
hmSetupWanL2tpAdditionalGatewaysEntryIdentifier OBJECT-TYPE
    SYNTAX     DisplayString (SIZE(0..16))
    MAX-ACCESS read-write
    STATUS     current
    DESCRIPTION
            "-- empty --"
    ::= { hmSetupWanL2tpAdditionalGatewaysEntry 1 }

-- {COLUMN} 1.3.6.1.4.1.248.32.18.2.2.36.1.2
hmSetupWanL2tpAdditionalGatewaysEntryBeginWith OBJECT-TYPE
    SYNTAX     INTEGER {
                  eLastUsed (0),
                  eFirst (1),
                  eRandom (2)
            }
    MAX-ACCESS read-write
    STATUS     current
    DESCRIPTION
            "-- empty --"
    ::= { hmSetupWanL2tpAdditionalGatewaysEntry 2 }

-- {COLUMN} 1.3.6.1.4.1.248.32.18.2.2.36.1.3
hmSetupWanL2tpAdditionalGatewaysEntryGateway1 OBJECT-TYPE
    SYNTAX     DisplayString (SIZE(0..64))
    MAX-ACCESS read-write
    STATUS     current
    DESCRIPTION
            "-- empty --"
    ::= { hmSetupWanL2tpAdditionalGatewaysEntry 3 }

-- {COLUMN} 1.3.6.1.4.1.248.32.18.2.2.36.1.4
hmSetupWanL2tpAdditionalGatewaysEntryRtgTag1 OBJECT-TYPE
    SYNTAX     Integer32 (0..65535)
    MAX-ACCESS read-write
    STATUS     current
    DESCRIPTION
            "-- empty --"
    ::= { hmSetupWanL2tpAdditionalGatewaysEntry 4 }

-- {COLUMN} 1.3.6.1.4.1.248.32.18.2.2.36.1.5
hmSetupWanL2tpAdditionalGatewaysEntryGateway2 OBJECT-TYPE
    SYNTAX     DisplayString (SIZE(0..64))
    MAX-ACCESS read-write
    STATUS     current
    DESCRIPTION
            "-- empty --"
    ::= { hmSetupWanL2tpAdditionalGatewaysEntry 5 }

-- {COLUMN} 1.3.6.1.4.1.248.32.18.2.2.36.1.6
hmSetupWanL2tpAdditionalGatewaysEntryRtgTag2 OBJECT-TYPE
    SYNTAX     Integer32 (0..65535)
    MAX-ACCESS read-write
    STATUS     current
    DESCRIPTION
            "-- empty --"
    ::= { hmSetupWanL2tpAdditionalGatewaysEntry 6 }

-- {COLUMN} 1.3.6.1.4.1.248.32.18.2.2.36.1.7
hmSetupWanL2tpAdditionalGatewaysEntryGateway3 OBJECT-TYPE
    SYNTAX     DisplayString (SIZE(0..64))
    MAX-ACCESS read-write
    STATUS     current
    DESCRIPTION
            "-- empty --"
    ::= { hmSetupWanL2tpAdditionalGatewaysEntry 7 }

-- {COLUMN} 1.3.6.1.4.1.248.32.18.2.2.36.1.8
hmSetupWanL2tpAdditionalGatewaysEntryRtgTag3 OBJECT-TYPE
    SYNTAX     Integer32 (0..65535)
    MAX-ACCESS read-write
    STATUS     current
    DESCRIPTION
            "-- empty --"
    ::= { hmSetupWanL2tpAdditionalGatewaysEntry 8 }

-- {COLUMN} 1.3.6.1.4.1.248.32.18.2.2.36.1.9
hmSetupWanL2tpAdditionalGatewaysEntryGateway4 OBJECT-TYPE
    SYNTAX     DisplayString (SIZE(0..64))
    MAX-ACCESS read-write
    STATUS     current
    DESCRIPTION
            "-- empty --"
    ::= { hmSetupWanL2tpAdditionalGatewaysEntry 9 }

-- {COLUMN} 1.3.6.1.4.1.248.32.18.2.2.36.1.10
hmSetupWanL2tpAdditionalGatewaysEntryRtgTag4 OBJECT-TYPE
    SYNTAX     Integer32 (0..65535)
    MAX-ACCESS read-write
    STATUS     current
    DESCRIPTION
            "-- empty --"
    ::= { hmSetupWanL2tpAdditionalGatewaysEntry 10 }

-- {COLUMN} 1.3.6.1.4.1.248.32.18.2.2.36.1.11
hmSetupWanL2tpAdditionalGatewaysEntryGateway5 OBJECT-TYPE
    SYNTAX     DisplayString (SIZE(0..64))
    MAX-ACCESS read-write
    STATUS     current
    DESCRIPTION
            "-- empty --"
    ::= { hmSetupWanL2tpAdditionalGatewaysEntry 11 }

-- {COLUMN} 1.3.6.1.4.1.248.32.18.2.2.36.1.12
hmSetupWanL2tpAdditionalGatewaysEntryRtgTag5 OBJECT-TYPE
    SYNTAX     Integer32 (0..65535)
    MAX-ACCESS read-write
    STATUS     current
    DESCRIPTION
            "-- empty --"
    ::= { hmSetupWanL2tpAdditionalGatewaysEntry 12 }

-- {COLUMN} 1.3.6.1.4.1.248.32.18.2.2.36.1.13
hmSetupWanL2tpAdditionalGatewaysEntryGateway6 OBJECT-TYPE
    SYNTAX     DisplayString (SIZE(0..64))
    MAX-ACCESS read-write
    STATUS     current
    DESCRIPTION
            "-- empty --"
    ::= { hmSetupWanL2tpAdditionalGatewaysEntry 13 }

-- {COLUMN} 1.3.6.1.4.1.248.32.18.2.2.36.1.14
hmSetupWanL2tpAdditionalGatewaysEntryRtgTag6 OBJECT-TYPE
    SYNTAX     Integer32 (0..65535)
    MAX-ACCESS read-write
    STATUS     current
    DESCRIPTION
            "-- empty --"
    ::= { hmSetupWanL2tpAdditionalGatewaysEntry 14 }

-- {COLUMN} 1.3.6.1.4.1.248.32.18.2.2.36.1.15
hmSetupWanL2tpAdditionalGatewaysEntryGateway7 OBJECT-TYPE
    SYNTAX     DisplayString (SIZE(0..64))
    MAX-ACCESS read-write
    STATUS     current
    DESCRIPTION
            "-- empty --"
    ::= { hmSetupWanL2tpAdditionalGatewaysEntry 15 }

-- {COLUMN} 1.3.6.1.4.1.248.32.18.2.2.36.1.16
hmSetupWanL2tpAdditionalGatewaysEntryRtgTag7 OBJECT-TYPE
    SYNTAX     Integer32 (0..65535)
    MAX-ACCESS read-write
    STATUS     current
    DESCRIPTION
            "-- empty --"
    ::= { hmSetupWanL2tpAdditionalGatewaysEntry 16 }

-- {COLUMN} 1.3.6.1.4.1.248.32.18.2.2.36.1.17
hmSetupWanL2tpAdditionalGatewaysEntryGateway8 OBJECT-TYPE
    SYNTAX     DisplayString (SIZE(0..64))
    MAX-ACCESS read-write
    STATUS     current
    DESCRIPTION
            "-- empty --"
    ::= { hmSetupWanL2tpAdditionalGatewaysEntry 17 }

-- {COLUMN} 1.3.6.1.4.1.248.32.18.2.2.36.1.18
hmSetupWanL2tpAdditionalGatewaysEntryRtgTag8 OBJECT-TYPE
    SYNTAX     Integer32 (0..65535)
    MAX-ACCESS read-write
    STATUS     current
    DESCRIPTION
            "-- empty --"
    ::= { hmSetupWanL2tpAdditionalGatewaysEntry 18 }

-- {COLUMN} 1.3.6.1.4.1.248.32.18.2.2.36.1.19
hmSetupWanL2tpAdditionalGatewaysEntryGateway9 OBJECT-TYPE
    SYNTAX     DisplayString (SIZE(0..64))
    MAX-ACCESS read-write
    STATUS     current
    DESCRIPTION
            "-- empty --"
    ::= { hmSetupWanL2tpAdditionalGatewaysEntry 19 }

-- {COLUMN} 1.3.6.1.4.1.248.32.18.2.2.36.1.20
hmSetupWanL2tpAdditionalGatewaysEntryRtgTag9 OBJECT-TYPE
    SYNTAX     Integer32 (0..65535)
    MAX-ACCESS read-write
    STATUS     current
    DESCRIPTION
            "-- empty --"
    ::= { hmSetupWanL2tpAdditionalGatewaysEntry 20 }

-- {COLUMN} 1.3.6.1.4.1.248.32.18.2.2.36.1.21
hmSetupWanL2tpAdditionalGatewaysEntryGateway10 OBJECT-TYPE
    SYNTAX     DisplayString (SIZE(0..64))
    MAX-ACCESS read-write
    STATUS     current
    DESCRIPTION
            "-- empty --"
    ::= { hmSetupWanL2tpAdditionalGatewaysEntry 21 }

-- {COLUMN} 1.3.6.1.4.1.248.32.18.2.2.36.1.22
hmSetupWanL2tpAdditionalGatewaysEntryRtgTag10 OBJECT-TYPE
    SYNTAX     Integer32 (0..65535)
    MAX-ACCESS read-write
    STATUS     current
    DESCRIPTION
            "-- empty --"
    ::= { hmSetupWanL2tpAdditionalGatewaysEntry 22 }

-- {COLUMN} 1.3.6.1.4.1.248.32.18.2.2.36.1.23
hmSetupWanL2tpAdditionalGatewaysEntryGateway11 OBJECT-TYPE
    SYNTAX     DisplayString (SIZE(0..64))
    MAX-ACCESS read-write
    STATUS     current
    DESCRIPTION
            "-- empty --"
    ::= { hmSetupWanL2tpAdditionalGatewaysEntry 23 }

-- {COLUMN} 1.3.6.1.4.1.248.32.18.2.2.36.1.24
hmSetupWanL2tpAdditionalGatewaysEntryRtgTag11 OBJECT-TYPE
    SYNTAX     Integer32 (0..65535)
    MAX-ACCESS read-write
    STATUS     current
    DESCRIPTION
            "-- empty --"
    ::= { hmSetupWanL2tpAdditionalGatewaysEntry 24 }

-- {COLUMN} 1.3.6.1.4.1.248.32.18.2.2.36.1.25
hmSetupWanL2tpAdditionalGatewaysEntryGateway12 OBJECT-TYPE
    SYNTAX     DisplayString (SIZE(0..64))
    MAX-ACCESS read-write
    STATUS     current
    DESCRIPTION
            "-- empty --"
    ::= { hmSetupWanL2tpAdditionalGatewaysEntry 25 }

-- {COLUMN} 1.3.6.1.4.1.248.32.18.2.2.36.1.26
hmSetupWanL2tpAdditionalGatewaysEntryRtgTag12 OBJECT-TYPE
    SYNTAX     Integer32 (0..65535)
    MAX-ACCESS read-write
    STATUS     current
    DESCRIPTION
            "-- empty --"
    ::= { hmSetupWanL2tpAdditionalGatewaysEntry 26 }

-- {COLUMN} 1.3.6.1.4.1.248.32.18.2.2.36.1.27
hmSetupWanL2tpAdditionalGatewaysEntryGateway13 OBJECT-TYPE
    SYNTAX     DisplayString (SIZE(0..64))
    MAX-ACCESS read-write
    STATUS     current
    DESCRIPTION
            "-- empty --"
    ::= { hmSetupWanL2tpAdditionalGatewaysEntry 27 }

-- {COLUMN} 1.3.6.1.4.1.248.32.18.2.2.36.1.28
hmSetupWanL2tpAdditionalGatewaysEntryRtgTag13 OBJECT-TYPE
    SYNTAX     Integer32 (0..65535)
    MAX-ACCESS read-write
    STATUS     current
    DESCRIPTION
            "-- empty --"
    ::= { hmSetupWanL2tpAdditionalGatewaysEntry 28 }

-- {COLUMN} 1.3.6.1.4.1.248.32.18.2.2.36.1.29
hmSetupWanL2tpAdditionalGatewaysEntryGateway14 OBJECT-TYPE
    SYNTAX     DisplayString (SIZE(0..64))
    MAX-ACCESS read-write
    STATUS     current
    DESCRIPTION
            "-- empty --"
    ::= { hmSetupWanL2tpAdditionalGatewaysEntry 29 }

-- {COLUMN} 1.3.6.1.4.1.248.32.18.2.2.36.1.30
hmSetupWanL2tpAdditionalGatewaysEntryRtgTag14 OBJECT-TYPE
    SYNTAX     Integer32 (0..65535)
    MAX-ACCESS read-write
    STATUS     current
    DESCRIPTION
            "-- empty --"
    ::= { hmSetupWanL2tpAdditionalGatewaysEntry 30 }

-- {COLUMN} 1.3.6.1.4.1.248.32.18.2.2.36.1.31
hmSetupWanL2tpAdditionalGatewaysEntryGateway15 OBJECT-TYPE
    SYNTAX     DisplayString (SIZE(0..64))
    MAX-ACCESS read-write
    STATUS     current
    DESCRIPTION
            "-- empty --"
    ::= { hmSetupWanL2tpAdditionalGatewaysEntry 31 }

-- {COLUMN} 1.3.6.1.4.1.248.32.18.2.2.36.1.32
hmSetupWanL2tpAdditionalGatewaysEntryRtgTag15 OBJECT-TYPE
    SYNTAX     Integer32 (0..65535)
    MAX-ACCESS read-write
    STATUS     current
    DESCRIPTION
            "-- empty --"
    ::= { hmSetupWanL2tpAdditionalGatewaysEntry 32 }

-- {COLUMN} 1.3.6.1.4.1.248.32.18.2.2.36.1.33
hmSetupWanL2tpAdditionalGatewaysEntryGateway16 OBJECT-TYPE
    SYNTAX     DisplayString (SIZE(0..64))
    MAX-ACCESS read-write
    STATUS     current
    DESCRIPTION
            "-- empty --"
    ::= { hmSetupWanL2tpAdditionalGatewaysEntry 33 }

-- {COLUMN} 1.3.6.1.4.1.248.32.18.2.2.36.1.34
hmSetupWanL2tpAdditionalGatewaysEntryRtgTag16 OBJECT-TYPE
    SYNTAX     Integer32 (0..65535)
    MAX-ACCESS read-write
    STATUS     current
    DESCRIPTION
            "-- empty --"
    ::= { hmSetupWanL2tpAdditionalGatewaysEntry 34 }

-- {COLUMN} 1.3.6.1.4.1.248.32.18.2.2.36.1.35
hmSetupWanL2tpAdditionalGatewaysEntryGateway17 OBJECT-TYPE
    SYNTAX     DisplayString (SIZE(0..64))
    MAX-ACCESS read-write
    STATUS     current
    DESCRIPTION
            "-- empty --"
    ::= { hmSetupWanL2tpAdditionalGatewaysEntry 35 }

-- {COLUMN} 1.3.6.1.4.1.248.32.18.2.2.36.1.36
hmSetupWanL2tpAdditionalGatewaysEntryRtgTag17 OBJECT-TYPE
    SYNTAX     Integer32 (0..65535)
    MAX-ACCESS read-write
    STATUS     current
    DESCRIPTION
            "-- empty --"
    ::= { hmSetupWanL2tpAdditionalGatewaysEntry 36 }

-- {COLUMN} 1.3.6.1.4.1.248.32.18.2.2.36.1.37
hmSetupWanL2tpAdditionalGatewaysEntryGateway18 OBJECT-TYPE
    SYNTAX     DisplayString (SIZE(0..64))
    MAX-ACCESS read-write
    STATUS     current
    DESCRIPTION
            "-- empty --"
    ::= { hmSetupWanL2tpAdditionalGatewaysEntry 37 }

-- {COLUMN} 1.3.6.1.4.1.248.32.18.2.2.36.1.38
hmSetupWanL2tpAdditionalGatewaysEntryRtgTag18 OBJECT-TYPE
    SYNTAX     Integer32 (0..65535)
    MAX-ACCESS read-write
    STATUS     current
    DESCRIPTION
            "-- empty --"
    ::= { hmSetupWanL2tpAdditionalGatewaysEntry 38 }

-- {COLUMN} 1.3.6.1.4.1.248.32.18.2.2.36.1.39
hmSetupWanL2tpAdditionalGatewaysEntryGateway19 OBJECT-TYPE
    SYNTAX     DisplayString (SIZE(0..64))
    MAX-ACCESS read-write
    STATUS     current
    DESCRIPTION
            "-- empty --"
    ::= { hmSetupWanL2tpAdditionalGatewaysEntry 39 }

-- {COLUMN} 1.3.6.1.4.1.248.32.18.2.2.36.1.40
hmSetupWanL2tpAdditionalGatewaysEntryRtgTag19 OBJECT-TYPE
    SYNTAX     Integer32 (0..65535)
    MAX-ACCESS read-write
    STATUS     current
    DESCRIPTION
            "-- empty --"
    ::= { hmSetupWanL2tpAdditionalGatewaysEntry 40 }

-- {COLUMN} 1.3.6.1.4.1.248.32.18.2.2.36.1.41
hmSetupWanL2tpAdditionalGatewaysEntryGateway20 OBJECT-TYPE
    SYNTAX     DisplayString (SIZE(0..64))
    MAX-ACCESS read-write
    STATUS     current
    DESCRIPTION
            "-- empty --"
    ::= { hmSetupWanL2tpAdditionalGatewaysEntry 41 }

-- {COLUMN} 1.3.6.1.4.1.248.32.18.2.2.36.1.42
hmSetupWanL2tpAdditionalGatewaysEntryRtgTag20 OBJECT-TYPE
    SYNTAX     Integer32 (0..65535)
    MAX-ACCESS read-write
    STATUS     current
    DESCRIPTION
            "-- empty --"
    ::= { hmSetupWanL2tpAdditionalGatewaysEntry 42 }

-- {COLUMN} 1.3.6.1.4.1.248.32.18.2.2.36.1.43
hmSetupWanL2tpAdditionalGatewaysEntryGateway21 OBJECT-TYPE
    SYNTAX     DisplayString (SIZE(0..64))
    MAX-ACCESS read-write
    STATUS     current
    DESCRIPTION
            "-- empty --"
    ::= { hmSetupWanL2tpAdditionalGatewaysEntry 43 }

-- {COLUMN} 1.3.6.1.4.1.248.32.18.2.2.36.1.44
hmSetupWanL2tpAdditionalGatewaysEntryRtgTag21 OBJECT-TYPE
    SYNTAX     Integer32 (0..65535)
    MAX-ACCESS read-write
    STATUS     current
    DESCRIPTION
            "-- empty --"
    ::= { hmSetupWanL2tpAdditionalGatewaysEntry 44 }

-- {COLUMN} 1.3.6.1.4.1.248.32.18.2.2.36.1.45
hmSetupWanL2tpAdditionalGatewaysEntryGateway22 OBJECT-TYPE
    SYNTAX     DisplayString (SIZE(0..64))
    MAX-ACCESS read-write
    STATUS     current
    DESCRIPTION
            "-- empty --"
    ::= { hmSetupWanL2tpAdditionalGatewaysEntry 45 }

-- {COLUMN} 1.3.6.1.4.1.248.32.18.2.2.36.1.46
hmSetupWanL2tpAdditionalGatewaysEntryRtgTag22 OBJECT-TYPE
    SYNTAX     Integer32 (0..65535)
    MAX-ACCESS read-write
    STATUS     current
    DESCRIPTION
            "-- empty --"
    ::= { hmSetupWanL2tpAdditionalGatewaysEntry 46 }

-- {COLUMN} 1.3.6.1.4.1.248.32.18.2.2.36.1.47
hmSetupWanL2tpAdditionalGatewaysEntryGateway23 OBJECT-TYPE
    SYNTAX     DisplayString (SIZE(0..64))
    MAX-ACCESS read-write
    STATUS     current
    DESCRIPTION
            "-- empty --"
    ::= { hmSetupWanL2tpAdditionalGatewaysEntry 47 }

-- {COLUMN} 1.3.6.1.4.1.248.32.18.2.2.36.1.48
hmSetupWanL2tpAdditionalGatewaysEntryRtgTag23 OBJECT-TYPE
    SYNTAX     Integer32 (0..65535)
    MAX-ACCESS read-write
    STATUS     current
    DESCRIPTION
            "-- empty --"
    ::= { hmSetupWanL2tpAdditionalGatewaysEntry 48 }

-- {COLUMN} 1.3.6.1.4.1.248.32.18.2.2.36.1.49
hmSetupWanL2tpAdditionalGatewaysEntryGateway24 OBJECT-TYPE
    SYNTAX     DisplayString (SIZE(0..64))
    MAX-ACCESS read-write
    STATUS     current
    DESCRIPTION
            "-- empty --"
    ::= { hmSetupWanL2tpAdditionalGatewaysEntry 49 }

-- {COLUMN} 1.3.6.1.4.1.248.32.18.2.2.36.1.50
hmSetupWanL2tpAdditionalGatewaysEntryRtgTag24 OBJECT-TYPE
    SYNTAX     Integer32 (0..65535)
    MAX-ACCESS read-write
    STATUS     current
    DESCRIPTION
            "-- empty --"
    ::= { hmSetupWanL2tpAdditionalGatewaysEntry 50 }

-- {COLUMN} 1.3.6.1.4.1.248.32.18.2.2.36.1.51
hmSetupWanL2tpAdditionalGatewaysEntryGateway25 OBJECT-TYPE
    SYNTAX     DisplayString (SIZE(0..64))
    MAX-ACCESS read-write
    STATUS     current
    DESCRIPTION
            "-- empty --"
    ::= { hmSetupWanL2tpAdditionalGatewaysEntry 51 }

-- {COLUMN} 1.3.6.1.4.1.248.32.18.2.2.36.1.52
hmSetupWanL2tpAdditionalGatewaysEntryRtgTag25 OBJECT-TYPE
    SYNTAX     Integer32 (0..65535)
    MAX-ACCESS read-write
    STATUS     current
    DESCRIPTION
            "-- empty --"
    ::= { hmSetupWanL2tpAdditionalGatewaysEntry 52 }

-- {COLUMN} 1.3.6.1.4.1.248.32.18.2.2.36.1.53
hmSetupWanL2tpAdditionalGatewaysEntryGateway26 OBJECT-TYPE
    SYNTAX     DisplayString (SIZE(0..64))
    MAX-ACCESS read-write
    STATUS     current
    DESCRIPTION
            "-- empty --"
    ::= { hmSetupWanL2tpAdditionalGatewaysEntry 53 }

-- {COLUMN} 1.3.6.1.4.1.248.32.18.2.2.36.1.54
hmSetupWanL2tpAdditionalGatewaysEntryRtgTag26 OBJECT-TYPE
    SYNTAX     Integer32 (0..65535)
    MAX-ACCESS read-write
    STATUS     current
    DESCRIPTION
            "-- empty --"
    ::= { hmSetupWanL2tpAdditionalGatewaysEntry 54 }

-- {COLUMN} 1.3.6.1.4.1.248.32.18.2.2.36.1.55
hmSetupWanL2tpAdditionalGatewaysEntryGateway27 OBJECT-TYPE
    SYNTAX     DisplayString (SIZE(0..64))
    MAX-ACCESS read-write
    STATUS     current
    DESCRIPTION
            "-- empty --"
    ::= { hmSetupWanL2tpAdditionalGatewaysEntry 55 }

-- {COLUMN} 1.3.6.1.4.1.248.32.18.2.2.36.1.56
hmSetupWanL2tpAdditionalGatewaysEntryRtgTag27 OBJECT-TYPE
    SYNTAX     Integer32 (0..65535)
    MAX-ACCESS read-write
    STATUS     current
    DESCRIPTION
            "-- empty --"
    ::= { hmSetupWanL2tpAdditionalGatewaysEntry 56 }

-- {COLUMN} 1.3.6.1.4.1.248.32.18.2.2.36.1.57
hmSetupWanL2tpAdditionalGatewaysEntryGateway28 OBJECT-TYPE
    SYNTAX     DisplayString (SIZE(0..64))
    MAX-ACCESS read-write
    STATUS     current
    DESCRIPTION
            "-- empty --"
    ::= { hmSetupWanL2tpAdditionalGatewaysEntry 57 }

-- {COLUMN} 1.3.6.1.4.1.248.32.18.2.2.36.1.58
hmSetupWanL2tpAdditionalGatewaysEntryRtgTag28 OBJECT-TYPE
    SYNTAX     Integer32 (0..65535)
    MAX-ACCESS read-write
    STATUS     current
    DESCRIPTION
            "-- empty --"
    ::= { hmSetupWanL2tpAdditionalGatewaysEntry 58 }

-- {COLUMN} 1.3.6.1.4.1.248.32.18.2.2.36.1.59
hmSetupWanL2tpAdditionalGatewaysEntryGateway29 OBJECT-TYPE
    SYNTAX     DisplayString (SIZE(0..64))
    MAX-ACCESS read-write
    STATUS     current
    DESCRIPTION
            "-- empty --"
    ::= { hmSetupWanL2tpAdditionalGatewaysEntry 59 }

-- {COLUMN} 1.3.6.1.4.1.248.32.18.2.2.36.1.60
hmSetupWanL2tpAdditionalGatewaysEntryRtgTag29 OBJECT-TYPE
    SYNTAX     Integer32 (0..65535)
    MAX-ACCESS read-write
    STATUS     current
    DESCRIPTION
            "-- empty --"
    ::= { hmSetupWanL2tpAdditionalGatewaysEntry 60 }

-- {COLUMN} 1.3.6.1.4.1.248.32.18.2.2.36.1.61
hmSetupWanL2tpAdditionalGatewaysEntryGateway30 OBJECT-TYPE
    SYNTAX     DisplayString (SIZE(0..64))
    MAX-ACCESS read-write
    STATUS     current
    DESCRIPTION
            "-- empty --"
    ::= { hmSetupWanL2tpAdditionalGatewaysEntry 61 }

-- {COLUMN} 1.3.6.1.4.1.248.32.18.2.2.36.1.62
hmSetupWanL2tpAdditionalGatewaysEntryRtgTag30 OBJECT-TYPE
    SYNTAX     Integer32 (0..65535)
    MAX-ACCESS read-write
    STATUS     current
    DESCRIPTION
            "-- empty --"
    ::= { hmSetupWanL2tpAdditionalGatewaysEntry 62 }

-- {COLUMN} 1.3.6.1.4.1.248.32.18.2.2.36.1.63
hmSetupWanL2tpAdditionalGatewaysEntryGateway31 OBJECT-TYPE
    SYNTAX     DisplayString (SIZE(0..64))
    MAX-ACCESS read-write
    STATUS     current
    DESCRIPTION
            "-- empty --"
    ::= { hmSetupWanL2tpAdditionalGatewaysEntry 63 }

-- {COLUMN} 1.3.6.1.4.1.248.32.18.2.2.36.1.64
hmSetupWanL2tpAdditionalGatewaysEntryRtgTag31 OBJECT-TYPE
    SYNTAX     Integer32 (0..65535)
    MAX-ACCESS read-write
    STATUS     current
    DESCRIPTION
            "-- empty --"
    ::= { hmSetupWanL2tpAdditionalGatewaysEntry 64 }

-- {COLUMN} 1.3.6.1.4.1.248.32.18.2.2.36.1.65
hmSetupWanL2tpAdditionalGatewaysEntryGateway32 OBJECT-TYPE
    SYNTAX     DisplayString (SIZE(0..64))
    MAX-ACCESS read-write
    STATUS     current
    DESCRIPTION
            "-- empty --"
    ::= { hmSetupWanL2tpAdditionalGatewaysEntry 65 }

-- {COLUMN} 1.3.6.1.4.1.248.32.18.2.2.36.1.66
hmSetupWanL2tpAdditionalGatewaysEntryRtgTag32 OBJECT-TYPE
    SYNTAX     Integer32 (0..65535)
    MAX-ACCESS read-write
    STATUS     current
    DESCRIPTION
            "-- empty --"
    ::= { hmSetupWanL2tpAdditionalGatewaysEntry 66 }

-- {TABLE} 1.3.6.1.4.1.248.32.18.2.2.37
hmSetupWanL2tpPeersTable OBJECT-TYPE
    SYNTAX     SEQUENCE OF HmSetupWanL2tpPeersEntry
    MAX-ACCESS not-accessible
    STATUS     current
    DESCRIPTION
            "-- empty --"
    ::= { hmSetupWan 37 }

-- {ROW} 1.3.6.1.4.1.248.32.18.2.2.37.1
hmSetupWanL2tpPeersEntry OBJECT-TYPE
    SYNTAX     HmSetupWanL2tpPeersEntry
    MAX-ACCESS not-accessible
    STATUS     current
    DESCRIPTION
            ""
    INDEX {
            hmSetupWanL2tpPeersEntryPeer
          }
    ::= { hmSetupWanL2tpPeersTable 1 }

HmSetupWanL2tpPeersEntry ::= SEQUENCE {
            hmSetupWanL2tpPeersEntryPeer DisplayString,
            hmSetupWanL2tpPeersEntryL2tpEndpoint DisplayString,
            hmSetupWanL2tpPeersEntryShTime Integer32
    }

-- {COLUMN} 1.3.6.1.4.1.248.32.18.2.2.37.1.1
hmSetupWanL2tpPeersEntryPeer OBJECT-TYPE
    SYNTAX     DisplayString (SIZE(0..16))
    MAX-ACCESS read-write
    STATUS     current
    DESCRIPTION
            "-- empty --"
    ::= { hmSetupWanL2tpPeersEntry 1 }

-- {COLUMN} 1.3.6.1.4.1.248.32.18.2.2.37.1.2
hmSetupWanL2tpPeersEntryL2tpEndpoint OBJECT-TYPE
    SYNTAX     DisplayString (SIZE(0..16))
    MAX-ACCESS read-write
    STATUS     current
    DESCRIPTION
            "-- empty --"
    ::= { hmSetupWanL2tpPeersEntry 2 }

-- {COLUMN} 1.3.6.1.4.1.248.32.18.2.2.37.1.3
hmSetupWanL2tpPeersEntryShTime OBJECT-TYPE
    SYNTAX     Integer32 (0..65535)
    MAX-ACCESS read-write
    STATUS     current
    DESCRIPTION
            "-- empty --"
    ::= { hmSetupWanL2tpPeersEntry 3 }

-- {SCALAR} 1.3.6.1.4.1.248.32.18.2.2.38
hmSetupWanL2tpSourceCheck OBJECT-TYPE
    SYNTAX     INTEGER {
                  eAddress (0),
                  eTagPlusAddress (1)
            }
    MAX-ACCESS read-write
    STATUS     current
    DESCRIPTION
            "-- empty --"
    ::= { hmSetupWan 38 }

-- {TABLE} 1.3.6.1.4.1.248.32.18.2.2.40
hmSetupWanDsLiteTunnelTable OBJECT-TYPE
    SYNTAX     SEQUENCE OF HmSetupWanDsLiteTunnelEntry
    MAX-ACCESS not-accessible
    STATUS     current
    DESCRIPTION
            "-- empty --"
    ::= { hmSetupWan 40 }

-- {ROW} 1.3.6.1.4.1.248.32.18.2.2.40.1
hmSetupWanDsLiteTunnelEntry OBJECT-TYPE
    SYNTAX     HmSetupWanDsLiteTunnelEntry
    MAX-ACCESS not-accessible
    STATUS     current
    DESCRIPTION
            ""
    INDEX {
            hmSetupWanDsLiteTunnelEntryName
          }
    ::= { hmSetupWanDsLiteTunnelTable 1 }

HmSetupWanDsLiteTunnelEntry ::= SEQUENCE {
            hmSetupWanDsLiteTunnelEntryName DisplayString,
            hmSetupWanDsLiteTunnelEntryGatewayAddress DisplayString,
            hmSetupWanDsLiteTunnelEntryRtgTag Integer32
    }

-- {COLUMN} 1.3.6.1.4.1.248.32.18.2.2.40.1.1
hmSetupWanDsLiteTunnelEntryName OBJECT-TYPE
    SYNTAX     DisplayString (SIZE(0..16))
    MAX-ACCESS read-write
    STATUS     current
    DESCRIPTION
            "-- empty --"
    ::= { hmSetupWanDsLiteTunnelEntry 1 }

-- {COLUMN} 1.3.6.1.4.1.248.32.18.2.2.40.1.2
hmSetupWanDsLiteTunnelEntryGatewayAddress OBJECT-TYPE
    SYNTAX     DisplayString (SIZE(0..64))
    MAX-ACCESS read-write
    STATUS     current
    DESCRIPTION
            "-- empty --"
    ::= { hmSetupWanDsLiteTunnelEntry 2 }

-- {COLUMN} 1.3.6.1.4.1.248.32.18.2.2.40.1.3
hmSetupWanDsLiteTunnelEntryRtgTag OBJECT-TYPE
    SYNTAX     Integer32 (0..65535)
    MAX-ACCESS read-write
    STATUS     current
    DESCRIPTION
            "-- empty --"
    ::= { hmSetupWanDsLiteTunnelEntry 3 }

-- {TABLE} 1.3.6.1.4.1.248.32.18.2.2.50
hmSetupWanEogreTunnelTable OBJECT-TYPE
    SYNTAX     SEQUENCE OF HmSetupWanEogreTunnelEntry
    MAX-ACCESS not-accessible
    STATUS     current
    DESCRIPTION
            "-- empty --"
    ::= { hmSetupWan 50 }

-- {ROW} 1.3.6.1.4.1.248.32.18.2.2.50.1
hmSetupWanEogreTunnelEntry OBJECT-TYPE
    SYNTAX     HmSetupWanEogreTunnelEntry
    MAX-ACCESS not-accessible
    STATUS     current
    DESCRIPTION
            ""
    INDEX {
            hmSetupWanEogreTunnelEntryPort
          }
    ::= { hmSetupWanEogreTunnelTable 1 }

HmSetupWanEogreTunnelEntry ::= SEQUENCE {
            hmSetupWanEogreTunnelEntryPort DisplayString,
            hmSetupWanEogreTunnelEntryActive INTEGER,
            hmSetupWanEogreTunnelEntryRemoteEndpointAddress DisplayString,
            hmSetupWanEogreTunnelEntryRtgTag Integer32,
            hmSetupWanEogreTunnelEntryKeyPresent INTEGER,
            hmSetupWanEogreTunnelEntryKeyValue Integer32,
            hmSetupWanEogreTunnelEntryChecksum INTEGER,
            hmSetupWanEogreTunnelEntrySequencing INTEGER,
            hmSetupWanEogreTunnelEntryLoopbackAddress DisplayString
    }

-- {COLUMN} 1.3.6.1.4.1.248.32.18.2.2.50.1.1
hmSetupWanEogreTunnelEntryPort OBJECT-TYPE
    SYNTAX     DisplayString (SIZE(0..15))
    MAX-ACCESS read-only
    STATUS     current
    DESCRIPTION
            "-- empty --"
    ::= { hmSetupWanEogreTunnelEntry 1 }

-- {COLUMN} 1.3.6.1.4.1.248.32.18.2.2.50.1.2
hmSetupWanEogreTunnelEntryActive OBJECT-TYPE
    SYNTAX     INTEGER {
                  eNo (0),
                  eYes (1)
            }
    MAX-ACCESS read-write
    STATUS     current
    DESCRIPTION
            "-- empty --"
    ::= { hmSetupWanEogreTunnelEntry 2 }

-- {COLUMN} 1.3.6.1.4.1.248.32.18.2.2.50.1.3
hmSetupWanEogreTunnelEntryRemoteEndpointAddress OBJECT-TYPE
    SYNTAX     DisplayString (SIZE(0..64))
    MAX-ACCESS read-write
    STATUS     current
    DESCRIPTION
            "-- empty --"
    ::= { hmSetupWanEogreTunnelEntry 3 }

-- {COLUMN} 1.3.6.1.4.1.248.32.18.2.2.50.1.4
hmSetupWanEogreTunnelEntryRtgTag OBJECT-TYPE
    SYNTAX     Integer32 (0..2147483647)
    MAX-ACCESS read-write
    STATUS     current
    DESCRIPTION
            "-- empty --"
    ::= { hmSetupWanEogreTunnelEntry 4 }

-- {COLUMN} 1.3.6.1.4.1.248.32.18.2.2.50.1.5
hmSetupWanEogreTunnelEntryKeyPresent OBJECT-TYPE
    SYNTAX     INTEGER {
                  eNo (0),
                  eYes (1)
            }
    MAX-ACCESS read-write
    STATUS     current
    DESCRIPTION
            "-- empty --"
    ::= { hmSetupWanEogreTunnelEntry 5 }

-- {COLUMN} 1.3.6.1.4.1.248.32.18.2.2.50.1.6
hmSetupWanEogreTunnelEntryKeyValue OBJECT-TYPE
    SYNTAX     Integer32 (0..2147483647)
    MAX-ACCESS read-write
    STATUS     current
    DESCRIPTION
            "-- empty --"
    ::= { hmSetupWanEogreTunnelEntry 6 }

-- {COLUMN} 1.3.6.1.4.1.248.32.18.2.2.50.1.7
hmSetupWanEogreTunnelEntryChecksum OBJECT-TYPE
    SYNTAX     INTEGER {
                  eNo (0),
                  eYes (1)
            }
    MAX-ACCESS read-write
    STATUS     current
    DESCRIPTION
            "-- empty --"
    ::= { hmSetupWanEogreTunnelEntry 7 }

-- {COLUMN} 1.3.6.1.4.1.248.32.18.2.2.50.1.8
hmSetupWanEogreTunnelEntrySequencing OBJECT-TYPE
    SYNTAX     INTEGER {
                  eNo (0),
                  eYes (1)
            }
    MAX-ACCESS read-write
    STATUS     current
    DESCRIPTION
            "-- empty --"
    ::= { hmSetupWanEogreTunnelEntry 8 }

-- {COLUMN} 1.3.6.1.4.1.248.32.18.2.2.50.1.9
hmSetupWanEogreTunnelEntryLoopbackAddress OBJECT-TYPE
    SYNTAX     DisplayString (SIZE(0..16))
    MAX-ACCESS read-write
    STATUS     current
    DESCRIPTION
            "-- empty --"
    ::= { hmSetupWanEogreTunnelEntry 9 }

-- {TABLE} 1.3.6.1.4.1.248.32.18.2.2.51
hmSetupWanGreTunnelTable OBJECT-TYPE
    SYNTAX     SEQUENCE OF HmSetupWanGreTunnelEntry
    MAX-ACCESS not-accessible
    STATUS     current
    DESCRIPTION
            "-- empty --"
    ::= { hmSetupWan 51 }

-- {ROW} 1.3.6.1.4.1.248.32.18.2.2.51.1
hmSetupWanGreTunnelEntry OBJECT-TYPE
    SYNTAX     HmSetupWanGreTunnelEntry
    MAX-ACCESS not-accessible
    STATUS     current
    DESCRIPTION
            ""
    INDEX {
            hmSetupWanGreTunnelEntryPeer
          }
    ::= { hmSetupWanGreTunnelTable 1 }

HmSetupWanGreTunnelEntry ::= SEQUENCE {
            hmSetupWanGreTunnelEntryPeer DisplayString,
            hmSetupWanGreTunnelEntryIpAddress DisplayString,
            hmSetupWanGreTunnelEntryRtgTag Integer32,
            hmSetupWanGreTunnelEntryKeyPresent INTEGER,
            hmSetupWanGreTunnelEntryKeyValue Integer32,
            hmSetupWanGreTunnelEntryChecksum INTEGER,
            hmSetupWanGreTunnelEntrySequencing INTEGER,
            hmSetupWanGreTunnelEntryLoopbackAddress DisplayString
    }

-- {COLUMN} 1.3.6.1.4.1.248.32.18.2.2.51.1.1
hmSetupWanGreTunnelEntryPeer OBJECT-TYPE
    SYNTAX     DisplayString (SIZE(0..16))
    MAX-ACCESS read-write
    STATUS     current
    DESCRIPTION
            "-- empty --"
    ::= { hmSetupWanGreTunnelEntry 1 }

-- {COLUMN} 1.3.6.1.4.1.248.32.18.2.2.51.1.3
hmSetupWanGreTunnelEntryIpAddress OBJECT-TYPE
    SYNTAX     DisplayString (SIZE(0..64))
    MAX-ACCESS read-write
    STATUS     current
    DESCRIPTION
            "-- empty --"
    ::= { hmSetupWanGreTunnelEntry 3 }

-- {COLUMN} 1.3.6.1.4.1.248.32.18.2.2.51.1.4
hmSetupWanGreTunnelEntryRtgTag OBJECT-TYPE
    SYNTAX     Integer32 (0..2147483647)
    MAX-ACCESS read-write
    STATUS     current
    DESCRIPTION
            "-- empty --"
    ::= { hmSetupWanGreTunnelEntry 4 }

-- {COLUMN} 1.3.6.1.4.1.248.32.18.2.2.51.1.5
hmSetupWanGreTunnelEntryKeyPresent OBJECT-TYPE
    SYNTAX     INTEGER {
                  eNo (0),
                  eYes (1)
            }
    MAX-ACCESS read-write
    STATUS     current
    DESCRIPTION
            "-- empty --"
    ::= { hmSetupWanGreTunnelEntry 5 }

-- {COLUMN} 1.3.6.1.4.1.248.32.18.2.2.51.1.6
hmSetupWanGreTunnelEntryKeyValue OBJECT-TYPE
    SYNTAX     Integer32 (0..2147483647)
    MAX-ACCESS read-write
    STATUS     current
    DESCRIPTION
            "-- empty --"
    ::= { hmSetupWanGreTunnelEntry 6 }

-- {COLUMN} 1.3.6.1.4.1.248.32.18.2.2.51.1.7
hmSetupWanGreTunnelEntryChecksum OBJECT-TYPE
    SYNTAX     INTEGER {
                  eNo (0),
                  eYes (1)
            }
    MAX-ACCESS read-write
    STATUS     current
    DESCRIPTION
            "-- empty --"
    ::= { hmSetupWanGreTunnelEntry 7 }

-- {COLUMN} 1.3.6.1.4.1.248.32.18.2.2.51.1.8
hmSetupWanGreTunnelEntrySequencing OBJECT-TYPE
    SYNTAX     INTEGER {
                  eNo (0),
                  eYes (1)
            }
    MAX-ACCESS read-write
    STATUS     current
    DESCRIPTION
            "-- empty --"
    ::= { hmSetupWanGreTunnelEntry 8 }

-- {COLUMN} 1.3.6.1.4.1.248.32.18.2.2.51.1.9
hmSetupWanGreTunnelEntryLoopbackAddress OBJECT-TYPE
    SYNTAX     DisplayString (SIZE(0..16))
    MAX-ACCESS read-write
    STATUS     current
    DESCRIPTION
            "-- empty --"
    ::= { hmSetupWanGreTunnelEntry 9 }

-- {NODE} 1.3.6.1.4.1.248.32.18.2.3
hmSetupCharges OBJECT IDENTIFIER ::= { hmSetup 3 }

-- {SCALAR} 1.3.6.1.4.1.248.32.18.2.3.2
hmSetupChargesDaysPerPeriod OBJECT-TYPE
    SYNTAX     Integer32 (0..65535)
    MAX-ACCESS read-write
    STATUS     current
    DESCRIPTION
            "-- empty --"
    ::= { hmSetupCharges 2 }

-- {TABLE} 1.3.6.1.4.1.248.32.18.2.3.7
hmSetupChargesTimeTableTable OBJECT-TYPE
    SYNTAX     SEQUENCE OF HmSetupChargesTimeTableEntry
    MAX-ACCESS not-accessible
    STATUS     current
    DESCRIPTION
            "-- empty --"
    ::= { hmSetupCharges 7 }

-- {ROW} 1.3.6.1.4.1.248.32.18.2.3.7.1
hmSetupChargesTimeTableEntry OBJECT-TYPE
    SYNTAX     HmSetupChargesTimeTableEntry
    MAX-ACCESS not-accessible
    STATUS     current
    DESCRIPTION
            ""
    INDEX {
            hmSetupChargesTimeTableEntryIfc
          }
    ::= { hmSetupChargesTimeTableTable 1 }

HmSetupChargesTimeTableEntry ::= SEQUENCE {
            hmSetupChargesTimeTableEntryIfc INTEGER,
            hmSetupChargesTimeTableEntryBudgetMinutes Integer32,
            hmSetupChargesTimeTableEntrySpareMinutes Integer32,
            hmSetupChargesTimeTableEntryMinutesActive Integer32,
            hmSetupChargesTimeTableEntryMinutesPassive Integer32
    }

-- {COLUMN} 1.3.6.1.4.1.248.32.18.2.3.7.1.1
hmSetupChargesTimeTableEntryIfc OBJECT-TYPE
    SYNTAX     INTEGER {
                  eRouterDslBroadband (1),
                  eRouterSerial (2),
                  eLancapi (3),
                  eAb1 (4),
                  eAb2 (5),
                  eAb3 (6),
                  eAb4 (7),
                  eTimeModul (255)
            }
    MAX-ACCESS read-only
    STATUS     current
    DESCRIPTION
            "-- empty --"
    ::= { hmSetupChargesTimeTableEntry 1 }

-- {COLUMN} 1.3.6.1.4.1.248.32.18.2.3.7.1.2
hmSetupChargesTimeTableEntryBudgetMinutes OBJECT-TYPE
    SYNTAX     Integer32 (0..2147483647)
    MAX-ACCESS read-only
    STATUS     current
    DESCRIPTION
            "-- empty --"
    ::= { hmSetupChargesTimeTableEntry 2 }

-- {COLUMN} 1.3.6.1.4.1.248.32.18.2.3.7.1.3
hmSetupChargesTimeTableEntrySpareMinutes OBJECT-TYPE
    SYNTAX     Integer32 (0..2147483647)
    MAX-ACCESS read-only
    STATUS     current
    DESCRIPTION
            "-- empty --"
    ::= { hmSetupChargesTimeTableEntry 3 }

-- {COLUMN} 1.3.6.1.4.1.248.32.18.2.3.7.1.4
hmSetupChargesTimeTableEntryMinutesActive OBJECT-TYPE
    SYNTAX     Integer32 (0..2147483647)
    MAX-ACCESS read-only
    STATUS     current
    DESCRIPTION
            "-- empty --"
    ::= { hmSetupChargesTimeTableEntry 4 }

-- {COLUMN} 1.3.6.1.4.1.248.32.18.2.3.7.1.5
hmSetupChargesTimeTableEntryMinutesPassive OBJECT-TYPE
    SYNTAX     Integer32 (0..2147483647)
    MAX-ACCESS read-only
    STATUS     current
    DESCRIPTION
            "-- empty --"
    ::= { hmSetupChargesTimeTableEntry 5 }

-- {SCALAR} 1.3.6.1.4.1.248.32.18.2.3.8
hmSetupChargesDslBroadbandMinutesBudget OBJECT-TYPE
    SYNTAX     Integer32 (0..2147483647)
    MAX-ACCESS read-write
    STATUS     current
    DESCRIPTION
            "-- empty --"
    ::= { hmSetupCharges 8 }

-- {SCALAR} 1.3.6.1.4.1.248.32.18.2.3.9
hmSetupChargesSpareDslBroadbandMinutes OBJECT-TYPE
    SYNTAX     Integer32 (0..2147483647)
    MAX-ACCESS read-only
    STATUS     current
    DESCRIPTION
            "-- empty --"
    ::= { hmSetupCharges 9 }

-- {SCALAR} 1.3.6.1.4.1.248.32.18.2.3.10
hmSetupChargesRouterDslBroadbandMinutesActive OBJECT-TYPE
    SYNTAX     Integer32 (0..2147483647)
    MAX-ACCESS read-only
    STATUS     current
    DESCRIPTION
            "-- empty --"
    ::= { hmSetupCharges 10 }

-- {SCALAR} 1.3.6.1.4.1.248.32.18.2.3.11
hmSetupChargesAdditionalDslBroadbandBudget OBJECT-TYPE
    SYNTAX     Integer32 (0..2147483647)
    MAX-ACCESS read-write
    STATUS     current
    DESCRIPTION
            "-- empty --"
    ::= { hmSetupCharges 11 }

-- {SCALAR} 1.3.6.1.4.1.248.32.18.2.3.12
hmSetupChargesActivateAdditionalBudget OBJECT-TYPE
    SYNTAX     DisplayString
    MAX-ACCESS read-write
    STATUS     current
    DESCRIPTION
            "-- empty --"
    ::= { hmSetupCharges 12 }

-- {SCALAR} 1.3.6.1.4.1.248.32.18.2.3.13
hmSetupChargesDialupMinutesBudget OBJECT-TYPE
    SYNTAX     Integer32 (0..2147483647)
    MAX-ACCESS read-write
    STATUS     current
    DESCRIPTION
            "-- empty --"
    ::= { hmSetupCharges 13 }

-- {SCALAR} 1.3.6.1.4.1.248.32.18.2.3.14
hmSetupChargesSpareDialupMinutes OBJECT-TYPE
    SYNTAX     Integer32 (0..2147483647)
    MAX-ACCESS read-only
    STATUS     current
    DESCRIPTION
            "-- empty --"
    ::= { hmSetupCharges 14 }

-- {SCALAR} 1.3.6.1.4.1.248.32.18.2.3.15
hmSetupChargesDialupMinutesActive OBJECT-TYPE
    SYNTAX     Integer32 (0..2147483647)
    MAX-ACCESS read-only
    STATUS     current
    DESCRIPTION
            "-- empty --"
    ::= { hmSetupCharges 15 }

-- {SCALAR} 1.3.6.1.4.1.248.32.18.2.3.16
hmSetupChargesResetBudgets OBJECT-TYPE
    SYNTAX     DisplayString
    MAX-ACCESS read-write
    STATUS     current
    DESCRIPTION
            "-- empty --"
    ::= { hmSetupCharges 16 }

-- {NODE} 1.3.6.1.4.1.248.32.18.2.4
hmSetupLan OBJECT IDENTIFIER ::= { hmSetup 4 }

-- {SCALAR} 1.3.6.1.4.1.248.32.18.2.4.2
hmSetupLanMacAddress OBJECT-TYPE
    SYNTAX     MacAddress
    MAX-ACCESS read-only
    STATUS     current
    DESCRIPTION
            "-- empty --"
    ::= { hmSetupLan 2 }

-- {SCALAR} 1.3.6.1.4.1.248.32.18.2.4.3
hmSetupLanSpareHeap OBJECT-TYPE
    SYNTAX     Integer32 (0..65535)
    MAX-ACCESS read-write
    STATUS     current
    DESCRIPTION
            "-- empty --"
    ::= { hmSetupLan 3 }

-- {SCALAR} 1.3.6.1.4.1.248.32.18.2.4.8
hmSetupLanTraceMac OBJECT-TYPE
    SYNTAX     MacAddress
    MAX-ACCESS read-write
    STATUS     current
    DESCRIPTION
            "-- empty --"
    ::= { hmSetupLan 8 }

-- {SCALAR} 1.3.6.1.4.1.248.32.18.2.4.9
hmSetupLanTraceLevel OBJECT-TYPE
    SYNTAX     Integer32 (0..255)
    MAX-ACCESS read-write
    STATUS     current
    DESCRIPTION
            "-- empty --"
    ::= { hmSetupLan 9 }

-- {NODE} 1.3.6.1.4.1.248.32.18.2.4.10
hmSetupLanIeee8021x OBJECT IDENTIFIER ::= { hmSetupLan 10 }

-- {TABLE} 1.3.6.1.4.1.248.32.18.2.4.10.1
hmSetupLanIeee8021xSupplicantIfcSetupTable OBJECT-TYPE
    SYNTAX     SEQUENCE OF HmSetupLanIeee8021xSupplicantIfcSetupEntry
    MAX-ACCESS not-accessible
    STATUS     current
    DESCRIPTION
            "-- empty --"
    ::= { hmSetupLanIeee8021x 1 }

-- {ROW} 1.3.6.1.4.1.248.32.18.2.4.10.1.1
hmSetupLanIeee8021xSupplicantIfcSetupEntry OBJECT-TYPE
    SYNTAX     HmSetupLanIeee8021xSupplicantIfcSetupEntry
    MAX-ACCESS not-accessible
    STATUS     current
    DESCRIPTION
            ""
    INDEX {
            hmSetupLanIeee8021xSupplicantIfcSetupEntryIfc
          }
    ::= { hmSetupLanIeee8021xSupplicantIfcSetupTable 1 }

HmSetupLanIeee8021xSupplicantIfcSetupEntry ::= SEQUENCE {
            hmSetupLanIeee8021xSupplicantIfcSetupEntryIfc INTEGER,
            hmSetupLanIeee8021xSupplicantIfcSetupEntryMethod INTEGER,
            hmSetupLanIeee8021xSupplicantIfcSetupEntryCredentials DisplayString
    }

-- {COLUMN} 1.3.6.1.4.1.248.32.18.2.4.10.1.1.1
hmSetupLanIeee8021xSupplicantIfcSetupEntryIfc OBJECT-TYPE
    SYNTAX     INTEGER {
                  eLan1 (1),
                  eLan2 (2)
            }
    MAX-ACCESS read-only
    STATUS     current
    DESCRIPTION
            "-- empty --"
    ::= { hmSetupLanIeee8021xSupplicantIfcSetupEntry 1 }

-- {COLUMN} 1.3.6.1.4.1.248.32.18.2.4.10.1.1.2
hmSetupLanIeee8021xSupplicantIfcSetupEntryMethod OBJECT-TYPE
    SYNTAX     INTEGER {
                  eNone (0),
                  eMd5 (1024),
                  eTls (3328),
                  eTtlsMd5 (5380),
                  eTtlsPap (5383),
                  eTtlsChap (5384),
                  eTtlsMschapv2 (5402),
                  eTtlsMschap (5567),
                  ePeapGtc (6406),
                  ePeapMschapv2 (6426)
            }
    MAX-ACCESS read-write
    STATUS     current
    DESCRIPTION
            "-- empty --"
    ::= { hmSetupLanIeee8021xSupplicantIfcSetupEntry 2 }

-- {COLUMN} 1.3.6.1.4.1.248.32.18.2.4.10.1.1.3
hmSetupLanIeee8021xSupplicantIfcSetupEntryCredentials OBJECT-TYPE
    SYNTAX     DisplayString (SIZE(0..64))
    MAX-ACCESS read-write
    STATUS     current
    DESCRIPTION
            "-- empty --"
    ::= { hmSetupLanIeee8021xSupplicantIfcSetupEntry 3 }

-- {TABLE} 1.3.6.1.4.1.248.32.18.2.4.10.2
hmSetupLanIeee8021xAuthenticatorIfcSetupTable OBJECT-TYPE
    SYNTAX     SEQUENCE OF HmSetupLanIeee8021xAuthenticatorIfcSetupEntry
    MAX-ACCESS not-accessible
    STATUS     current
    DESCRIPTION
            "-- empty --"
    ::= { hmSetupLanIeee8021x 2 }

-- {ROW} 1.3.6.1.4.1.248.32.18.2.4.10.2.1
hmSetupLanIeee8021xAuthenticatorIfcSetupEntry OBJECT-TYPE
    SYNTAX     HmSetupLanIeee8021xAuthenticatorIfcSetupEntry
    MAX-ACCESS not-accessible
    STATUS     current
    DESCRIPTION
            ""
    INDEX {
            hmSetupLanIeee8021xAuthenticatorIfcSetupEntryIfc
          }
    ::= { hmSetupLanIeee8021xAuthenticatorIfcSetupTable 1 }

HmSetupLanIeee8021xAuthenticatorIfcSetupEntry ::= SEQUENCE {
            hmSetupLanIeee8021xAuthenticatorIfcSetupEntryIfc INTEGER,
            hmSetupLanIeee8021xAuthenticatorIfcSetupEntryOperating INTEGER,
            hmSetupLanIeee8021xAuthenticatorIfcSetupEntryMode INTEGER,
            hmSetupLanIeee8021xAuthenticatorIfcSetupEntryRadiusServer DisplayString,
            hmSetupLanIeee8021xAuthenticatorIfcSetupEntryMacAuthBypass INTEGER
    }

-- {COLUMN} 1.3.6.1.4.1.248.32.18.2.4.10.2.1.1
hmSetupLanIeee8021xAuthenticatorIfcSetupEntryIfc OBJECT-TYPE
    SYNTAX     INTEGER {
                  eLan1 (1),
                  eLan2 (2)
            }
    MAX-ACCESS read-only
    STATUS     current
    DESCRIPTION
            "-- empty --"
    ::= { hmSetupLanIeee8021xAuthenticatorIfcSetupEntry 1 }

-- {COLUMN} 1.3.6.1.4.1.248.32.18.2.4.10.2.1.2
hmSetupLanIeee8021xAuthenticatorIfcSetupEntryOperating OBJECT-TYPE
    SYNTAX     INTEGER {
                  eNo (0),
                  eYes (1)
            }
    MAX-ACCESS read-write
    STATUS     current
    DESCRIPTION
            "-- empty --"
    ::= { hmSetupLanIeee8021xAuthenticatorIfcSetupEntry 2 }

-- {COLUMN} 1.3.6.1.4.1.248.32.18.2.4.10.2.1.3
hmSetupLanIeee8021xAuthenticatorIfcSetupEntryMode OBJECT-TYPE
    SYNTAX     INTEGER {
                  eSingleHost (0),
                  eMultipleHost (1),
                  eMultipleAuth (2)
            }
    MAX-ACCESS read-write
    STATUS     current
    DESCRIPTION
            "-- empty --"
    ::= { hmSetupLanIeee8021xAuthenticatorIfcSetupEntry 3 }

-- {COLUMN} 1.3.6.1.4.1.248.32.18.2.4.10.2.1.4
hmSetupLanIeee8021xAuthenticatorIfcSetupEntryRadiusServer OBJECT-TYPE
    SYNTAX     DisplayString (SIZE(0..16))
    MAX-ACCESS read-write
    STATUS     current
    DESCRIPTION
            "-- empty --"
    ::= { hmSetupLanIeee8021xAuthenticatorIfcSetupEntry 4 }

-- {COLUMN} 1.3.6.1.4.1.248.32.18.2.4.10.2.1.5
hmSetupLanIeee8021xAuthenticatorIfcSetupEntryMacAuthBypass OBJECT-TYPE
    SYNTAX     INTEGER {
                  eNo (0),
                  eYes (1)
            }
    MAX-ACCESS read-write
    STATUS     current
    DESCRIPTION
            "-- empty --"
    ::= { hmSetupLanIeee8021xAuthenticatorIfcSetupEntry 5 }

-- {SCALAR} 1.3.6.1.4.1.248.32.18.2.4.11
hmSetupLanLinkupReportDelayMs OBJECT-TYPE
    SYNTAX     Integer32 (0..2147483647)
    MAX-ACCESS read-write
    STATUS     current
    DESCRIPTION
            "-- empty --"
    ::= { hmSetupLan 11 }

-- {NODE} 1.3.6.1.4.1.248.32.18.2.4.13
hmSetupLanIfcBundl OBJECT IDENTIFIER ::= { hmSetupLan 13 }

-- {TABLE} 1.3.6.1.4.1.248.32.18.2.4.13.1
hmSetupLanIfcBundlInterfacesTable OBJECT-TYPE
    SYNTAX     SEQUENCE OF HmSetupLanIfcBundlInterfacesEntry
    MAX-ACCESS not-accessible
    STATUS     current
    DESCRIPTION
            "-- empty --"
    ::= { hmSetupLanIfcBundl 1 }

-- {ROW} 1.3.6.1.4.1.248.32.18.2.4.13.1.1
hmSetupLanIfcBundlInterfacesEntry OBJECT-TYPE
    SYNTAX     HmSetupLanIfcBundlInterfacesEntry
    MAX-ACCESS not-accessible
    STATUS     current
    DESCRIPTION
            ""
    INDEX {
            hmSetupLanIfcBundlInterfacesEntryInterface
          }
    ::= { hmSetupLanIfcBundlInterfacesTable 1 }

HmSetupLanIfcBundlInterfacesEntry ::= SEQUENCE {
            hmSetupLanIfcBundlInterfacesEntryInterface DisplayString,
            hmSetupLanIfcBundlInterfacesEntryOperating INTEGER,
            hmSetupLanIfcBundlInterfacesEntryProtocol INTEGER,
            hmSetupLanIfcBundlInterfacesEntryMacAddress MacAddress,
            hmSetupLanIfcBundlInterfacesEntryInterfaceA INTEGER,
            hmSetupLanIfcBundlInterfacesEntryInterfaceB INTEGER
    }

-- {COLUMN} 1.3.6.1.4.1.248.32.18.2.4.13.1.1.1
hmSetupLanIfcBundlInterfacesEntryInterface OBJECT-TYPE
    SYNTAX     DisplayString (SIZE(0..18))
    MAX-ACCESS read-only
    STATUS     current
    DESCRIPTION
            "-- empty --"
    ::= { hmSetupLanIfcBundlInterfacesEntry 1 }

-- {COLUMN} 1.3.6.1.4.1.248.32.18.2.4.13.1.1.2
hmSetupLanIfcBundlInterfacesEntryOperating OBJECT-TYPE
    SYNTAX     INTEGER {
                  eNo (0),
                  eYes (1)
            }
    MAX-ACCESS read-write
    STATUS     current
    DESCRIPTION
            "-- empty --"
    ::= { hmSetupLanIfcBundlInterfacesEntry 2 }

-- {COLUMN} 1.3.6.1.4.1.248.32.18.2.4.13.1.1.3
hmSetupLanIfcBundlInterfacesEntryProtocol OBJECT-TYPE
    SYNTAX     INTEGER {
                  ePrp (1)
            }
    MAX-ACCESS read-write
    STATUS     current
    DESCRIPTION
            "-- empty --"
    ::= { hmSetupLanIfcBundlInterfacesEntry 3 }

-- {COLUMN} 1.3.6.1.4.1.248.32.18.2.4.13.1.1.4
hmSetupLanIfcBundlInterfacesEntryMacAddress OBJECT-TYPE
    SYNTAX     MacAddress
    MAX-ACCESS read-write
    STATUS     current
    DESCRIPTION
            "-- empty --"
    ::= { hmSetupLanIfcBundlInterfacesEntry 4 }

-- {COLUMN} 1.3.6.1.4.1.248.32.18.2.4.13.1.1.5
hmSetupLanIfcBundlInterfacesEntryInterfaceA OBJECT-TYPE
    SYNTAX     INTEGER {
                  eLan1 (256),
                  eLan2 (257),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311)
            }
    MAX-ACCESS read-write
    STATUS     current
    DESCRIPTION
            "-- empty --"
    ::= { hmSetupLanIfcBundlInterfacesEntry 5 }

-- {COLUMN} 1.3.6.1.4.1.248.32.18.2.4.13.1.1.6
hmSetupLanIfcBundlInterfacesEntryInterfaceB OBJECT-TYPE
    SYNTAX     INTEGER {
                  eLan1 (256),
                  eLan2 (257),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311)
            }
    MAX-ACCESS read-write
    STATUS     current
    DESCRIPTION
            "-- empty --"
    ::= { hmSetupLanIfcBundlInterfacesEntry 6 }

-- {NODE} 1.3.6.1.4.1.248.32.18.2.4.13.11
hmSetupLanIfcBundlPrp OBJECT IDENTIFIER ::= { hmSetupLanIfcBundl 11 }

-- {TABLE} 1.3.6.1.4.1.248.32.18.2.4.13.11.1
hmSetupLanIfcBundlPrpInterfacesTable OBJECT-TYPE
    SYNTAX     SEQUENCE OF HmSetupLanIfcBundlPrpInterfacesEntry
    MAX-ACCESS not-accessible
    STATUS     current
    DESCRIPTION
            "-- empty --"
    ::= { hmSetupLanIfcBundlPrp 1 }

-- {ROW} 1.3.6.1.4.1.248.32.18.2.4.13.11.1.1
hmSetupLanIfcBundlPrpInterfacesEntry OBJECT-TYPE
    SYNTAX     HmSetupLanIfcBundlPrpInterfacesEntry
    MAX-ACCESS not-accessible
    STATUS     current
    DESCRIPTION
            ""
    INDEX {
            hmSetupLanIfcBundlPrpInterfacesEntryInterface
          }
    ::= { hmSetupLanIfcBundlPrpInterfacesTable 1 }

HmSetupLanIfcBundlPrpInterfacesEntry ::= SEQUENCE {
            hmSetupLanIfcBundlPrpInterfacesEntryInterface DisplayString,
            hmSetupLanIfcBundlPrpInterfacesEntryDuplicateAccept INTEGER,
            hmSetupLanIfcBundlPrpInterfacesEntryTransparentMode INTEGER,
            hmSetupLanIfcBundlPrpInterfacesEntryLifeCheckInterval Integer32,
            hmSetupLanIfcBundlPrpInterfacesEntryNodeForgetTime Integer32,
            hmSetupLanIfcBundlPrpInterfacesEntryEntryForgetTime Integer32,
            hmSetupLanIfcBundlPrpInterfacesEntryNodeRebootInterval Integer32,
            hmSetupLanIfcBundlPrpInterfacesEntryDupEliminationBufferSize Integer32,
            hmSetupLanIfcBundlPrpInterfacesEntrySendSupervisionFrames INTEGER,
            hmSetupLanIfcBundlPrpInterfacesEntryNodeName DisplayString,
            hmSetupLanIfcBundlPrpInterfacesEntryEvaluateSupFrames INTEGER,
            hmSetupLanIfcBundlPrpInterfacesEntryReorderingBufferEnable INTEGER,
            hmSetupLanIfcBundlPrpInterfacesEntryReorderingBufferMaxDelay Integer32,
            hmSetupLanIfcBundlPrpInterfacesEntryForcePrpTransmission INTEGER
    }

-- {COLUMN} 1.3.6.1.4.1.248.32.18.2.4.13.11.1.1.1
hmSetupLanIfcBundlPrpInterfacesEntryInterface OBJECT-TYPE
    SYNTAX     DisplayString (SIZE(0..18))
    MAX-ACCESS read-only
    STATUS     current
    DESCRIPTION
            "-- empty --"
    ::= { hmSetupLanIfcBundlPrpInterfacesEntry 1 }

-- {COLUMN} 1.3.6.1.4.1.248.32.18.2.4.13.11.1.1.2
hmSetupLanIfcBundlPrpInterfacesEntryDuplicateAccept OBJECT-TYPE
    SYNTAX     INTEGER {
                  eNo (0),
                  eYes (1)
            }
    MAX-ACCESS read-write
    STATUS     current
    DESCRIPTION
            "-- empty --"
    ::= { hmSetupLanIfcBundlPrpInterfacesEntry 2 }

-- {COLUMN} 1.3.6.1.4.1.248.32.18.2.4.13.11.1.1.3
hmSetupLanIfcBundlPrpInterfacesEntryTransparentMode OBJECT-TYPE
    SYNTAX     INTEGER {
                  eNo (0),
                  eYes (1)
            }
    MAX-ACCESS read-write
    STATUS     current
    DESCRIPTION
            "-- empty --"
    ::= { hmSetupLanIfcBundlPrpInterfacesEntry 3 }

-- {COLUMN} 1.3.6.1.4.1.248.32.18.2.4.13.11.1.1.4
hmSetupLanIfcBundlPrpInterfacesEntryLifeCheckInterval OBJECT-TYPE
    SYNTAX     Integer32 (0..2147483647)
    MAX-ACCESS read-write
    STATUS     current
    DESCRIPTION
            "-- empty --"
    ::= { hmSetupLanIfcBundlPrpInterfacesEntry 4 }

-- {COLUMN} 1.3.6.1.4.1.248.32.18.2.4.13.11.1.1.5
hmSetupLanIfcBundlPrpInterfacesEntryNodeForgetTime OBJECT-TYPE
    SYNTAX     Integer32 (0..2147483647)
    MAX-ACCESS read-write
    STATUS     current
    DESCRIPTION
            "-- empty --"
    ::= { hmSetupLanIfcBundlPrpInterfacesEntry 5 }

-- {COLUMN} 1.3.6.1.4.1.248.32.18.2.4.13.11.1.1.6
hmSetupLanIfcBundlPrpInterfacesEntryEntryForgetTime OBJECT-TYPE
    SYNTAX     Integer32 (0..2147483647)
    MAX-ACCESS read-write
    STATUS     current
    DESCRIPTION
            "-- empty --"
    ::= { hmSetupLanIfcBundlPrpInterfacesEntry 6 }

-- {COLUMN} 1.3.6.1.4.1.248.32.18.2.4.13.11.1.1.7
hmSetupLanIfcBundlPrpInterfacesEntryNodeRebootInterval OBJECT-TYPE
    SYNTAX     Integer32 (0..2147483647)
    MAX-ACCESS read-write
    STATUS     current
    DESCRIPTION
            "-- empty --"
    ::= { hmSetupLanIfcBundlPrpInterfacesEntry 7 }

-- {COLUMN} 1.3.6.1.4.1.248.32.18.2.4.13.11.1.1.8
hmSetupLanIfcBundlPrpInterfacesEntryDupEliminationBufferSize OBJECT-TYPE
    SYNTAX     Integer32 (0..2147483647)
    MAX-ACCESS read-write
    STATUS     current
    DESCRIPTION
            "-- empty --"
    ::= { hmSetupLanIfcBundlPrpInterfacesEntry 8 }

-- {COLUMN} 1.3.6.1.4.1.248.32.18.2.4.13.11.1.1.9
hmSetupLanIfcBundlPrpInterfacesEntrySendSupervisionFrames OBJECT-TYPE
    SYNTAX     INTEGER {
                  eNone (0),
                  eOwnMacOnly (1),
                  eAllNodes (2)
            }
    MAX-ACCESS read-write
    STATUS     current
    DESCRIPTION
            "-- empty --"
    ::= { hmSetupLanIfcBundlPrpInterfacesEntry 9 }

-- {COLUMN} 1.3.6.1.4.1.248.32.18.2.4.13.11.1.1.10
hmSetupLanIfcBundlPrpInterfacesEntryNodeName OBJECT-TYPE
    SYNTAX     DisplayString (SIZE(0..32))
    MAX-ACCESS read-write
    STATUS     current
    DESCRIPTION
            "-- empty --"
    ::= { hmSetupLanIfcBundlPrpInterfacesEntry 10 }

-- {COLUMN} 1.3.6.1.4.1.248.32.18.2.4.13.11.1.1.11
hmSetupLanIfcBundlPrpInterfacesEntryEvaluateSupFrames OBJECT-TYPE
    SYNTAX     INTEGER {
                  eNo (0),
                  eYes (1)
            }
    MAX-ACCESS read-write
    STATUS     current
    DESCRIPTION
            "-- empty --"
    ::= { hmSetupLanIfcBundlPrpInterfacesEntry 11 }

-- {COLUMN} 1.3.6.1.4.1.248.32.18.2.4.13.11.1.1.248
hmSetupLanIfcBundlPrpInterfacesEntryReorderingBufferEnable OBJECT-TYPE
    SYNTAX     INTEGER {
                  eNo (0),
                  eYes (1)
            }
    MAX-ACCESS read-write
    STATUS     current
    DESCRIPTION
            "-- empty --"
    ::= { hmSetupLanIfcBundlPrpInterfacesEntry 248 }

-- {COLUMN} 1.3.6.1.4.1.248.32.18.2.4.13.11.1.1.249
hmSetupLanIfcBundlPrpInterfacesEntryReorderingBufferMaxDelay OBJECT-TYPE
    SYNTAX     Integer32 (0..2147483647)
    MAX-ACCESS read-write
    STATUS     current
    DESCRIPTION
            "-- empty --"
    ::= { hmSetupLanIfcBundlPrpInterfacesEntry 249 }

-- {COLUMN} 1.3.6.1.4.1.248.32.18.2.4.13.11.1.1.250
hmSetupLanIfcBundlPrpInterfacesEntryForcePrpTransmission OBJECT-TYPE
    SYNTAX     INTEGER {
                  eNo (0),
                  eYes (1)
            }
    MAX-ACCESS read-write
    STATUS     current
    DESCRIPTION
            "-- empty --"
    ::= { hmSetupLanIfcBundlPrpInterfacesEntry 250 }

-- {NODE} 1.3.6.1.4.1.248.32.18.2.7
hmSetupTcpIp OBJECT IDENTIFIER ::= { hmSetup 7 }

-- {SCALAR} 1.3.6.1.4.1.248.32.18.2.7.1
hmSetupTcpIpOperating OBJECT-TYPE
    SYNTAX     INTEGER {
                  eNo (0),
                  eYes (1)
            }
    MAX-ACCESS read-write
    STATUS     current
    DESCRIPTION
            "-- empty --"
    ::= { hmSetupTcpIp 1 }

-- {TABLE} 1.3.6.1.4.1.248.32.18.2.7.6
hmSetupTcpIpAccessListTable OBJECT-TYPE
    SYNTAX     SEQUENCE OF HmSetupTcpIpAccessListEntry
    MAX-ACCESS not-accessible
    STATUS     current
    DESCRIPTION
            "-- empty --"
    ::= { hmSetupTcpIp 6 }

-- {ROW} 1.3.6.1.4.1.248.32.18.2.7.6.1
hmSetupTcpIpAccessListEntry OBJECT-TYPE
    SYNTAX     HmSetupTcpIpAccessListEntry
    MAX-ACCESS not-accessible
    STATUS     current
    DESCRIPTION
            ""
    INDEX {
            hmSetupTcpIpAccessListEntryIpAddress,
            hmSetupTcpIpAccessListEntryIpNetmask,
            hmSetupTcpIpAccessListEntryRtgTag
          }
    ::= { hmSetupTcpIpAccessListTable 1 }

HmSetupTcpIpAccessListEntry ::= SEQUENCE {
            hmSetupTcpIpAccessListEntryIpAddress IpAddress,
            hmSetupTcpIpAccessListEntryIpNetmask IpAddress,
            hmSetupTcpIpAccessListEntryRtgTag Integer32,
            hmSetupTcpIpAccessListEntryComment DisplayString
    }

-- {COLUMN} 1.3.6.1.4.1.248.32.18.2.7.6.1.1
hmSetupTcpIpAccessListEntryIpAddress OBJECT-TYPE
    SYNTAX     IpAddress
    MAX-ACCESS read-write
    STATUS     current
    DESCRIPTION
            "-- empty --"
    ::= { hmSetupTcpIpAccessListEntry 1 }

-- {COLUMN} 1.3.6.1.4.1.248.32.18.2.7.6.1.2
hmSetupTcpIpAccessListEntryIpNetmask OBJECT-TYPE
    SYNTAX     IpAddress
    MAX-ACCESS read-write
    STATUS     current
    DESCRIPTION
            "-- empty --"
    ::= { hmSetupTcpIpAccessListEntry 2 }

-- {COLUMN} 1.3.6.1.4.1.248.32.18.2.7.6.1.3
hmSetupTcpIpAccessListEntryRtgTag OBJECT-TYPE
    SYNTAX     Integer32 (0..65535)
    MAX-ACCESS read-write
    STATUS     current
    DESCRIPTION
            "-- empty --"
    ::= { hmSetupTcpIpAccessListEntry 3 }

-- {COLUMN} 1.3.6.1.4.1.248.32.18.2.7.6.1.4
hmSetupTcpIpAccessListEntryComment OBJECT-TYPE
    SYNTAX     DisplayString (SIZE(0..63))
    MAX-ACCESS read-write
    STATUS     current
    DESCRIPTION
            "-- empty --"
    ::= { hmSetupTcpIpAccessListEntry 4 }

-- {SCALAR} 1.3.6.1.4.1.248.32.18.2.7.7
hmSetupTcpIpDnsDefault OBJECT-TYPE
    SYNTAX     IpAddress
    MAX-ACCESS read-write
    STATUS     current
    DESCRIPTION
            "-- empty --"
    ::= { hmSetupTcpIp 7 }

-- {SCALAR} 1.3.6.1.4.1.248.32.18.2.7.8
hmSetupTcpIpDnsBackup OBJECT-TYPE
    SYNTAX     IpAddress
    MAX-ACCESS read-write
    STATUS     current
    DESCRIPTION
            "-- empty --"
    ::= { hmSetupTcpIp 8 }

-- {SCALAR} 1.3.6.1.4.1.248.32.18.2.7.9
hmSetupTcpIpNbnsDefault OBJECT-TYPE
    SYNTAX     IpAddress
    MAX-ACCESS read-write
    STATUS     current
    DESCRIPTION
            "-- empty --"
    ::= { hmSetupTcpIp 9 }

-- {SCALAR} 1.3.6.1.4.1.248.32.18.2.7.10
hmSetupTcpIpNbnsBackup OBJECT-TYPE
    SYNTAX     IpAddress
    MAX-ACCESS read-write
    STATUS     current
    DESCRIPTION
            "-- empty --"
    ::= { hmSetupTcpIp 10 }

-- {SCALAR} 1.3.6.1.4.1.248.32.18.2.7.11
hmSetupTcpIpArpAgingMinutes OBJECT-TYPE
    SYNTAX     Integer32 (0..255)
    MAX-ACCESS read-write
    STATUS     current
    DESCRIPTION
            "-- empty --"
    ::= { hmSetupTcpIp 11 }

-- {SCALAR} 1.3.6.1.4.1.248.32.18.2.7.12
hmSetupTcpIpTcpAgingMinutes OBJECT-TYPE
    SYNTAX     Integer32 (0..255)
    MAX-ACCESS read-write
    STATUS     current
    DESCRIPTION
            "-- empty --"
    ::= { hmSetupTcpIp 12 }

-- {SCALAR} 1.3.6.1.4.1.248.32.18.2.7.13
hmSetupTcpIpTcpMaxConn OBJECT-TYPE
    SYNTAX     Integer32 (0..255)
    MAX-ACCESS read-write
    STATUS     current
    DESCRIPTION
            "-- empty --"
    ::= { hmSetupTcpIp 13 }

-- {TABLE} 1.3.6.1.4.1.248.32.18.2.7.16
hmSetupTcpIpArpTableTable OBJECT-TYPE
    SYNTAX     SEQUENCE OF HmSetupTcpIpArpTableEntry
    MAX-ACCESS not-accessible
    STATUS     current
    DESCRIPTION
            "-- empty --"
    ::= { hmSetupTcpIp 16 }

-- {ROW} 1.3.6.1.4.1.248.32.18.2.7.16.1
hmSetupTcpIpArpTableEntry OBJECT-TYPE
    SYNTAX     HmSetupTcpIpArpTableEntry
    MAX-ACCESS not-accessible
    STATUS     current
    DESCRIPTION
            ""
    INDEX {
            hmSetupTcpIpArpTableEntryIpAddress
          }
    ::= { hmSetupTcpIpArpTableTable 1 }

HmSetupTcpIpArpTableEntry ::= SEQUENCE {
            hmSetupTcpIpArpTableEntryIpAddress IpAddress,
            hmSetupTcpIpArpTableEntryMacAddress MacAddress,
            hmSetupTcpIpArpTableEntryLastAccess Integer32,
            hmSetupTcpIpArpTableEntryEthernetPort INTEGER,
            hmSetupTcpIpArpTableEntryPeer DisplayString,
            hmSetupTcpIpArpTableEntryVlanId Integer32,
            hmSetupTcpIpArpTableEntryConnect INTEGER
    }

-- {COLUMN} 1.3.6.1.4.1.248.32.18.2.7.16.1.1
hmSetupTcpIpArpTableEntryIpAddress OBJECT-TYPE
    SYNTAX     IpAddress
    MAX-ACCESS read-only
    STATUS     current
    DESCRIPTION
            "-- empty --"
    ::= { hmSetupTcpIpArpTableEntry 1 }

-- {COLUMN} 1.3.6.1.4.1.248.32.18.2.7.16.1.2
hmSetupTcpIpArpTableEntryMacAddress OBJECT-TYPE
    SYNTAX     MacAddress
    MAX-ACCESS read-only
    STATUS     current
    DESCRIPTION
            "-- empty --"
    ::= { hmSetupTcpIpArpTableEntry 2 }

-- {COLUMN} 1.3.6.1.4.1.248.32.18.2.7.16.1.3
hmSetupTcpIpArpTableEntryLastAccess OBJECT-TYPE
    SYNTAX     Integer32 (0..2147483647)
    MAX-ACCESS read-only
    STATUS     current
    DESCRIPTION
            "-- empty --"
    ::= { hmSetupTcpIpArpTableEntry 3 }

-- {COLUMN} 1.3.6.1.4.1.248.32.18.2.7.16.1.5
hmSetupTcpIpArpTableEntryEthernetPort OBJECT-TYPE
    SYNTAX     INTEGER {
                  eEth1 (2),
                  eEth2 (3),
                  eEth3 (4),
                  eEth4 (5)
            }
    MAX-ACCESS read-only
    STATUS     current
    DESCRIPTION
            "-- empty --"
    ::= { hmSetupTcpIpArpTableEntry 5 }

-- {COLUMN} 1.3.6.1.4.1.248.32.18.2.7.16.1.6
hmSetupTcpIpArpTableEntryPeer OBJECT-TYPE
    SYNTAX     DisplayString (SIZE(0..255))
    MAX-ACCESS read-only
    STATUS     current
    DESCRIPTION
            "-- empty --"
    ::= { hmSetupTcpIpArpTableEntry 6 }

-- {COLUMN} 1.3.6.1.4.1.248.32.18.2.7.16.1.7
hmSetupTcpIpArpTableEntryVlanId OBJECT-TYPE
    SYNTAX     Integer32 (0..65535)
    MAX-ACCESS read-only
    STATUS     current
    DESCRIPTION
            "-- empty --"
    ::= { hmSetupTcpIpArpTableEntry 7 }

-- {COLUMN} 1.3.6.1.4.1.248.32.18.2.7.16.1.8
hmSetupTcpIpArpTableEntryConnect OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eWan (32768)
            }
    MAX-ACCESS read-only
    STATUS     current
    DESCRIPTION
            "-- empty --"
    ::= { hmSetupTcpIpArpTableEntry 8 }

-- {TABLE} 1.3.6.1.4.1.248.32.18.2.7.17
hmSetupTcpIpLoopbackListTable OBJECT-TYPE
    SYNTAX     SEQUENCE OF HmSetupTcpIpLoopbackListEntry
    MAX-ACCESS not-accessible
    STATUS     current
    DESCRIPTION
            "-- empty --"
    ::= { hmSetupTcpIp 17 }

-- {ROW} 1.3.6.1.4.1.248.32.18.2.7.17.1
hmSetupTcpIpLoopbackListEntry OBJECT-TYPE
    SYNTAX     HmSetupTcpIpLoopbackListEntry
    MAX-ACCESS not-accessible
    STATUS     current
    DESCRIPTION
            ""
    INDEX {
            hmSetupTcpIpLoopbackListEntryName
          }
    ::= { hmSetupTcpIpLoopbackListTable 1 }

HmSetupTcpIpLoopbackListEntry ::= SEQUENCE {
            hmSetupTcpIpLoopbackListEntryLoopbackAddr IpAddress,
            hmSetupTcpIpLoopbackListEntryName DisplayString,
            hmSetupTcpIpLoopbackListEntryRtgTag Integer32
    }

-- {COLUMN} 1.3.6.1.4.1.248.32.18.2.7.17.1.1
hmSetupTcpIpLoopbackListEntryLoopbackAddr OBJECT-TYPE
    SYNTAX     IpAddress
    MAX-ACCESS read-write
    STATUS     current
    DESCRIPTION
            "-- empty --"
    ::= { hmSetupTcpIpLoopbackListEntry 1 }

-- {COLUMN} 1.3.6.1.4.1.248.32.18.2.7.17.1.2
hmSetupTcpIpLoopbackListEntryName OBJECT-TYPE
    SYNTAX     DisplayString (SIZE(0..16))
    MAX-ACCESS read-write
    STATUS     current
    DESCRIPTION
            "-- empty --"
    ::= { hmSetupTcpIpLoopbackListEntry 2 }

-- {COLUMN} 1.3.6.1.4.1.248.32.18.2.7.17.1.3
hmSetupTcpIpLoopbackListEntryRtgTag OBJECT-TYPE
    SYNTAX     Integer32 (0..65535)
    MAX-ACCESS read-write
    STATUS     current
    DESCRIPTION
            "-- empty --"
    ::= { hmSetupTcpIpLoopbackListEntry 3 }

-- {SCALAR} 1.3.6.1.4.1.248.32.18.2.7.20
hmSetupTcpIpNonLocArpReplies OBJECT-TYPE
    SYNTAX     INTEGER {
                  eNo (0),
                  eYes (1)
            }
    MAX-ACCESS read-write
    STATUS     current
    DESCRIPTION
            "-- empty --"
    ::= { hmSetupTcpIp 20 }

-- {NODE} 1.3.6.1.4.1.248.32.18.2.7.21
hmSetupTcpIpAliveTest OBJECT IDENTIFIER ::= { hmSetupTcpIp 21 }

-- {SCALAR} 1.3.6.1.4.1.248.32.18.2.7.21.1
hmSetupTcpIpAliveTestTargetAddress OBJECT-TYPE
    SYNTAX     IpAddress
    MAX-ACCESS read-write
    STATUS     current
    DESCRIPTION
            "-- empty --"
    ::= { hmSetupTcpIpAliveTest 1 }

-- {SCALAR} 1.3.6.1.4.1.248.32.18.2.7.21.2
hmSetupTcpIpAliveTestTestInterval OBJECT-TYPE
    SYNTAX     Integer32 (0..2147483647)
    MAX-ACCESS read-write
    STATUS     current
    DESCRIPTION
            "-- empty --"
    ::= { hmSetupTcpIpAliveTest 2 }

-- {SCALAR} 1.3.6.1.4.1.248.32.18.2.7.21.3
hmSetupTcpIpAliveTestRetryCount OBJECT-TYPE
    SYNTAX     Integer32 (0..2147483647)
    MAX-ACCESS read-write
    STATUS     current
    DESCRIPTION
            "-- empty --"
    ::= { hmSetupTcpIpAliveTest 3 }

-- {SCALAR} 1.3.6.1.4.1.248.32.18.2.7.21.4
hmSetupTcpIpAliveTestRetryInterval OBJECT-TYPE
    SYNTAX     Integer32 (0..2147483647)
    MAX-ACCESS read-write
    STATUS     current
    DESCRIPTION
            "-- empty --"
    ::= { hmSetupTcpIpAliveTest 4 }

-- {SCALAR} 1.3.6.1.4.1.248.32.18.2.7.21.5
hmSetupTcpIpAliveTestFailLimit OBJECT-TYPE
    SYNTAX     Integer32 (0..2147483647)
    MAX-ACCESS read-write
    STATUS     current
    DESCRIPTION
            "-- empty --"
    ::= { hmSetupTcpIpAliveTest 5 }

-- {SCALAR} 1.3.6.1.4.1.248.32.18.2.7.21.6
hmSetupTcpIpAliveTestBootType OBJECT-TYPE
    SYNTAX     INTEGER {
                  eWarmBoot (0),
                  eColdBoot (1),
                  eAction (2)
            }
    MAX-ACCESS read-write
    STATUS     current
    DESCRIPTION
            "-- empty --"
    ::= { hmSetupTcpIpAliveTest 6 }

-- {SCALAR} 1.3.6.1.4.1.248.32.18.2.7.21.7
hmSetupTcpIpAliveTestAction OBJECT-TYPE
    SYNTAX     DisplayString (SIZE(0..251))
    MAX-ACCESS read-write
    STATUS     current
    DESCRIPTION
            "-- empty --"
    ::= { hmSetupTcpIpAliveTest 7 }

-- {SCALAR} 1.3.6.1.4.1.248.32.18.2.7.22
hmSetupTcpIpIcmpOnArpTimeout OBJECT-TYPE
    SYNTAX     INTEGER {
                  eNo (0),
                  eYes (1)
            }
    MAX-ACCESS read-write
    STATUS     current
    DESCRIPTION
            "-- empty --"
    ::= { hmSetupTcpIp 22 }

-- {TABLE} 1.3.6.1.4.1.248.32.18.2.7.30
hmSetupTcpIpNetworkListTable OBJECT-TYPE
    SYNTAX     SEQUENCE OF HmSetupTcpIpNetworkListEntry
    MAX-ACCESS not-accessible
    STATUS     current
    DESCRIPTION
            "-- empty --"
    ::= { hmSetupTcpIp 30 }

-- {ROW} 1.3.6.1.4.1.248.32.18.2.7.30.1
hmSetupTcpIpNetworkListEntry OBJECT-TYPE
    SYNTAX     HmSetupTcpIpNetworkListEntry
    MAX-ACCESS not-accessible
    STATUS     current
    DESCRIPTION
            ""
    INDEX {
            hmSetupTcpIpNetworkListEntryNetworkName
          }
    ::= { hmSetupTcpIpNetworkListTable 1 }

HmSetupTcpIpNetworkListEntry ::= SEQUENCE {
            hmSetupTcpIpNetworkListEntryNetworkName DisplayString,
            hmSetupTcpIpNetworkListEntryIpAddress IpAddress,
            hmSetupTcpIpNetworkListEntryIpNetmask IpAddress,
            hmSetupTcpIpNetworkListEntryVlanId Integer32,
            hmSetupTcpIpNetworkListEntryInterface INTEGER,
            hmSetupTcpIpNetworkListEntrySrcCheck INTEGER,
            hmSetupTcpIpNetworkListEntryType INTEGER,
            hmSetupTcpIpNetworkListEntryRtgTag Integer32,
            hmSetupTcpIpNetworkListEntryComment DisplayString
    }

-- {COLUMN} 1.3.6.1.4.1.248.32.18.2.7.30.1.1
hmSetupTcpIpNetworkListEntryNetworkName OBJECT-TYPE
    SYNTAX     DisplayString (SIZE(0..17))
    MAX-ACCESS read-write
    STATUS     current
    DESCRIPTION
            "-- empty --"
    ::= { hmSetupTcpIpNetworkListEntry 1 }

-- {COLUMN} 1.3.6.1.4.1.248.32.18.2.7.30.1.2
hmSetupTcpIpNetworkListEntryIpAddress OBJECT-TYPE
    SYNTAX     IpAddress
    MAX-ACCESS read-write
    STATUS     current
    DESCRIPTION
            "-- empty --"
    ::= { hmSetupTcpIpNetworkListEntry 2 }

-- {COLUMN} 1.3.6.1.4.1.248.32.18.2.7.30.1.3
hmSetupTcpIpNetworkListEntryIpNetmask OBJECT-TYPE
    SYNTAX     IpAddress
    MAX-ACCESS read-write
    STATUS     current
    DESCRIPTION
            "-- empty --"
    ::= { hmSetupTcpIpNetworkListEntry 3 }

-- {COLUMN} 1.3.6.1.4.1.248.32.18.2.7.30.1.4
hmSetupTcpIpNetworkListEntryVlanId OBJECT-TYPE
    SYNTAX     Integer32 (0..65535)
    MAX-ACCESS read-write
    STATUS     current
    DESCRIPTION
            "-- empty --"
    ::= { hmSetupTcpIpNetworkListEntry 4 }

-- {COLUMN} 1.3.6.1.4.1.248.32.18.2.7.30.1.5
hmSetupTcpIpNetworkListEntryInterface OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eAny (65535)
            }
    MAX-ACCESS read-write
    STATUS     current
    DESCRIPTION
            "-- empty --"
    ::= { hmSetupTcpIpNetworkListEntry 5 }

-- {COLUMN} 1.3.6.1.4.1.248.32.18.2.7.30.1.6
hmSetupTcpIpNetworkListEntrySrcCheck OBJECT-TYPE
    SYNTAX     INTEGER {
                  eLoose (0),
                  eStrict (1)
            }
    MAX-ACCESS read-write
    STATUS     current
    DESCRIPTION
            "-- empty --"
    ::= { hmSetupTcpIpNetworkListEntry 6 }

-- {COLUMN} 1.3.6.1.4.1.248.32.18.2.7.30.1.7
hmSetupTcpIpNetworkListEntryType OBJECT-TYPE
    SYNTAX     INTEGER {
                  eDisabled (0),
                  eIntranet (1),
                  eDmz (2)
            }
    MAX-ACCESS read-write
    STATUS     current
    DESCRIPTION
            "-- empty --"
    ::= { hmSetupTcpIpNetworkListEntry 7 }

-- {COLUMN} 1.3.6.1.4.1.248.32.18.2.7.30.1.8
hmSetupTcpIpNetworkListEntryRtgTag OBJECT-TYPE
    SYNTAX     Integer32 (0..65535)
    MAX-ACCESS read-write
    STATUS     current
    DESCRIPTION
            "-- empty --"
    ::= { hmSetupTcpIpNetworkListEntry 8 }

-- {COLUMN} 1.3.6.1.4.1.248.32.18.2.7.30.1.9
hmSetupTcpIpNetworkListEntryComment OBJECT-TYPE
    SYNTAX     DisplayString (SIZE(0..64))
    MAX-ACCESS read-write
    STATUS     current
    DESCRIPTION
            "-- empty --"
    ::= { hmSetupTcpIpNetworkListEntry 9 }

-- {NODE} 1.3.6.1.4.1.248.32.18.2.8
hmSetupIpRouter OBJECT IDENTIFIER ::= { hmSetup 8 }

-- {SCALAR} 1.3.6.1.4.1.248.32.18.2.8.1
hmSetupIpRouterOperating OBJECT-TYPE
    SYNTAX     INTEGER {
                  eNo (0),
                  eYes (1)
            }
    MAX-ACCESS read-write
    STATUS     current
    DESCRIPTION
            "-- empty --"
    ::= { hmSetupIpRouter 1 }

-- {TABLE} 1.3.6.1.4.1.248.32.18.2.8.2
hmSetupIpRouterIpRoutingTableTable OBJECT-TYPE
    SYNTAX     SEQUENCE OF HmSetupIpRouterIpRoutingTableEntry
    MAX-ACCESS not-accessible
    STATUS     current
    DESCRIPTION
            "-- empty --"
    ::= { hmSetupIpRouter 2 }

-- {ROW} 1.3.6.1.4.1.248.32.18.2.8.2.1
hmSetupIpRouterIpRoutingTableEntry OBJECT-TYPE
    SYNTAX     HmSetupIpRouterIpRoutingTableEntry
    MAX-ACCESS not-accessible
    STATUS     current
    DESCRIPTION
            ""
    INDEX {
            hmSetupIpRouterIpRoutingTableEntryIpAddress,
            hmSetupIpRouterIpRoutingTableEntryIpNetmask,
            hmSetupIpRouterIpRoutingTableEntryRtgTag
          }
    ::= { hmSetupIpRouterIpRoutingTableTable 1 }

HmSetupIpRouterIpRoutingTableEntry ::= SEQUENCE {
            hmSetupIpRouterIpRoutingTableEntryIpAddress IpAddress,
            hmSetupIpRouterIpRoutingTableEntryIpNetmask IpAddress,
            hmSetupIpRouterIpRoutingTableEntryPeerOrIp DisplayString,
            hmSetupIpRouterIpRoutingTableEntryDistance Integer32,
            hmSetupIpRouterIpRoutingTableEntryMasquerade INTEGER,
            hmSetupIpRouterIpRoutingTableEntryActive INTEGER,
            hmSetupIpRouterIpRoutingTableEntryComment DisplayString,
            hmSetupIpRouterIpRoutingTableEntryRtgTag Integer32
    }

-- {COLUMN} 1.3.6.1.4.1.248.32.18.2.8.2.1.1
hmSetupIpRouterIpRoutingTableEntryIpAddress OBJECT-TYPE
    SYNTAX     IpAddress
    MAX-ACCESS read-write
    STATUS     current
    DESCRIPTION
            "-- empty --"
    ::= { hmSetupIpRouterIpRoutingTableEntry 1 }

-- {COLUMN} 1.3.6.1.4.1.248.32.18.2.8.2.1.2
hmSetupIpRouterIpRoutingTableEntryIpNetmask OBJECT-TYPE
    SYNTAX     IpAddress
    MAX-ACCESS read-write
    STATUS     current
    DESCRIPTION
            "-- empty --"
    ::= { hmSetupIpRouterIpRoutingTableEntry 2 }

-- {COLUMN} 1.3.6.1.4.1.248.32.18.2.8.2.1.3
hmSetupIpRouterIpRoutingTableEntryPeerOrIp OBJECT-TYPE
    SYNTAX     DisplayString (SIZE(0..16))
    MAX-ACCESS read-write
    STATUS     current
    DESCRIPTION
            "-- empty --"
    ::= { hmSetupIpRouterIpRoutingTableEntry 3 }

-- {COLUMN} 1.3.6.1.4.1.248.32.18.2.8.2.1.4
hmSetupIpRouterIpRoutingTableEntryDistance OBJECT-TYPE
    SYNTAX     Integer32 (0..255)
    MAX-ACCESS read-write
    STATUS     current
    DESCRIPTION
            "-- empty --"
    ::= { hmSetupIpRouterIpRoutingTableEntry 4 }

-- {COLUMN} 1.3.6.1.4.1.248.32.18.2.8.2.1.5
hmSetupIpRouterIpRoutingTableEntryMasquerade OBJECT-TYPE
    SYNTAX     INTEGER {
                  eNo (0),
                  eOn (1),
                  eIntranet (2)
            }
    MAX-ACCESS read-write
    STATUS     current
    DESCRIPTION
            "-- empty --"
    ::= { hmSetupIpRouterIpRoutingTableEntry 5 }

-- {COLUMN} 1.3.6.1.4.1.248.32.18.2.8.2.1.6
hmSetupIpRouterIpRoutingTableEntryActive OBJECT-TYPE
    SYNTAX     INTEGER {
                  eYes (0),
                  eNo (1),
                  eSemi (2)
            }
    MAX-ACCESS read-write
    STATUS     current
    DESCRIPTION
            "-- empty --"
    ::= { hmSetupIpRouterIpRoutingTableEntry 6 }

-- {COLUMN} 1.3.6.1.4.1.248.32.18.2.8.2.1.7
hmSetupIpRouterIpRoutingTableEntryComment OBJECT-TYPE
    SYNTAX     DisplayString (SIZE(0..64))
    MAX-ACCESS read-write
    STATUS     current
    DESCRIPTION
            "-- empty --"
    ::= { hmSetupIpRouterIpRoutingTableEntry 7 }

-- {COLUMN} 1.3.6.1.4.1.248.32.18.2.8.2.1.8
hmSetupIpRouterIpRoutingTableEntryRtgTag OBJECT-TYPE
    SYNTAX     Integer32 (0..65535)
    MAX-ACCESS read-write
    STATUS     current
    DESCRIPTION
            "-- empty --"
    ::= { hmSetupIpRouterIpRoutingTableEntry 8 }

-- {SCALAR} 1.3.6.1.4.1.248.32.18.2.8.5
hmSetupIpRouterProxyArp OBJECT-TYPE
    SYNTAX     INTEGER {
                  eNo (0),
                  eYes (1)
            }
    MAX-ACCESS read-write
    STATUS     current
    DESCRIPTION
            "-- empty --"
    ::= { hmSetupIpRouter 5 }

-- {SCALAR} 1.3.6.1.4.1.248.32.18.2.8.6
hmSetupIpRouterSendIcmpRedirect OBJECT-TYPE
    SYNTAX     INTEGER {
                  eYes (0),
                  eNo (1)
            }
    MAX-ACCESS read-write
    STATUS     current
    DESCRIPTION
            "-- empty --"
    ::= { hmSetupIpRouter 6 }

-- {NODE} 1.3.6.1.4.1.248.32.18.2.8.7
hmSetupIpRouterRoutingMethod OBJECT IDENTIFIER ::= { hmSetupIpRouter 7 }

-- {SCALAR} 1.3.6.1.4.1.248.32.18.2.8.7.1
hmSetupIpRouterRoutingMethodRoutingMethod OBJECT-TYPE
    SYNTAX     INTEGER {
                  eNormal (0),
                  eTypeOfService (1),
                  eDiffserv (2)
            }
    MAX-ACCESS read-write
    STATUS     current
    DESCRIPTION
            "-- empty --"
    ::= { hmSetupIpRouterRoutingMethod 1 }

-- {SCALAR} 1.3.6.1.4.1.248.32.18.2.8.7.2
hmSetupIpRouterRoutingMethodIcmpRoutingMethod OBJECT-TYPE
    SYNTAX     INTEGER {
                  eNormal (0),
                  eReliable (1)
            }
    MAX-ACCESS read-write
    STATUS     current
    DESCRIPTION
            "-- empty --"
    ::= { hmSetupIpRouterRoutingMethod 2 }

-- {SCALAR} 1.3.6.1.4.1.248.32.18.2.8.7.3
hmSetupIpRouterRoutingMethodSynAckSpeedup OBJECT-TYPE
    SYNTAX     INTEGER {
                  eNo (0),
                  eYes (1)
            }
    MAX-ACCESS read-write
    STATUS     current
    DESCRIPTION
            "-- empty --"
    ::= { hmSetupIpRouterRoutingMethod 3 }

-- {SCALAR} 1.3.6.1.4.1.248.32.18.2.8.7.4
hmSetupIpRouterRoutingMethodL2L3Tagging OBJECT-TYPE
    SYNTAX     INTEGER {
                  eNo (0),
                  eYes (1),
                  eAuto (2)
            }
    MAX-ACCESS read-write
    STATUS     current
    DESCRIPTION
            "-- empty --"
    ::= { hmSetupIpRouterRoutingMethod 4 }

-- {SCALAR} 1.3.6.1.4.1.248.32.18.2.8.7.5
hmSetupIpRouterRoutingMethodL3L2Tagging OBJECT-TYPE
    SYNTAX     INTEGER {
                  eNo (0),
                  eYes (1)
            }
    MAX-ACCESS read-write
    STATUS     current
    DESCRIPTION
            "-- empty --"
    ::= { hmSetupIpRouterRoutingMethod 5 }

-- {SCALAR} 1.3.6.1.4.1.248.32.18.2.8.7.6
hmSetupIpRouterRoutingMethodRouteInternalServices OBJECT-TYPE
    SYNTAX     INTEGER {
                  eNo (0),
                  eYes (1)
            }
    MAX-ACCESS read-write
    STATUS     current
    DESCRIPTION
            "-- empty --"
    ::= { hmSetupIpRouterRoutingMethod 6 }

-- {NODE} 1.3.6.1.4.1.248.32.18.2.8.8
hmSetupIpRouterRip OBJECT IDENTIFIER ::= { hmSetupIpRouter 8 }

-- {SCALAR} 1.3.6.1.4.1.248.32.18.2.8.8.2
hmSetupIpRouterRipR1Mask OBJECT-TYPE
    SYNTAX     INTEGER {
                  eClass (0),
                  eAddress (1),
                  eClPlusAddr (2)
            }
    MAX-ACCESS read-write
    STATUS     current
    DESCRIPTION
            "-- empty --"
    ::= { hmSetupIpRouterRip 2 }

-- {TABLE} 1.3.6.1.4.1.248.32.18.2.8.8.4
hmSetupIpRouterRipWanSitesTable OBJECT-TYPE
    SYNTAX     SEQUENCE OF HmSetupIpRouterRipWanSitesEntry
    MAX-ACCESS not-accessible
    STATUS     current
    DESCRIPTION
            "-- empty --"
    ::= { hmSetupIpRouterRip 4 }

-- {ROW} 1.3.6.1.4.1.248.32.18.2.8.8.4.1
hmSetupIpRouterRipWanSitesEntry OBJECT-TYPE
    SYNTAX     HmSetupIpRouterRipWanSitesEntry
    MAX-ACCESS not-accessible
    STATUS     current
    DESCRIPTION
            ""
    INDEX {
            hmSetupIpRouterRipWanSitesEntryPeer
          }
    ::= { hmSetupIpRouterRipWanSitesTable 1 }

HmSetupIpRouterRipWanSitesEntry ::= SEQUENCE {
            hmSetupIpRouterRipWanSitesEntryPeer DisplayString,
            hmSetupIpRouterRipWanSitesEntryRipType INTEGER,
            hmSetupIpRouterRipWanSitesEntryRipAccept INTEGER,
            hmSetupIpRouterRipWanSitesEntryMasquerade INTEGER,
            hmSetupIpRouterRipWanSitesEntryDftRtgTag Integer32,
            hmSetupIpRouterRipWanSitesEntryRtgTagList DisplayString,
            hmSetupIpRouterRipWanSitesEntryPoisonedReverse INTEGER,
            hmSetupIpRouterRipWanSitesEntryRfc2091 INTEGER,
            hmSetupIpRouterRipWanSitesEntryGateway IpAddress,
            hmSetupIpRouterRipWanSitesEntryRxFilter DisplayString,
            hmSetupIpRouterRipWanSitesEntryTxFilter DisplayString,
            hmSetupIpRouterRipWanSitesEntryRipSend INTEGER,
            hmSetupIpRouterRipWanSitesEntryLoopbackAddress DisplayString
    }

-- {COLUMN} 1.3.6.1.4.1.248.32.18.2.8.8.4.1.1
hmSetupIpRouterRipWanSitesEntryPeer OBJECT-TYPE
    SYNTAX     DisplayString (SIZE(0..16))
    MAX-ACCESS read-write
    STATUS     current
    DESCRIPTION
            "-- empty --"
    ::= { hmSetupIpRouterRipWanSitesEntry 1 }

-- {COLUMN} 1.3.6.1.4.1.248.32.18.2.8.8.4.1.2
hmSetupIpRouterRipWanSitesEntryRipType OBJECT-TYPE
    SYNTAX     INTEGER {
                  eOff (0),
                  eRip1 (1),
                  eR1Comp (2),
                  eRip2 (3)
            }
    MAX-ACCESS read-write
    STATUS     current
    DESCRIPTION
            "-- empty --"
    ::= { hmSetupIpRouterRipWanSitesEntry 2 }

-- {COLUMN} 1.3.6.1.4.1.248.32.18.2.8.8.4.1.3
hmSetupIpRouterRipWanSitesEntryRipAccept OBJECT-TYPE
    SYNTAX     INTEGER {
                  eNo (0),
                  eYes (1)
            }
    MAX-ACCESS read-write
    STATUS     current
    DESCRIPTION
            "-- empty --"
    ::= { hmSetupIpRouterRipWanSitesEntry 3 }

-- {COLUMN} 1.3.6.1.4.1.248.32.18.2.8.8.4.1.4
hmSetupIpRouterRipWanSitesEntryMasquerade OBJECT-TYPE
    SYNTAX     INTEGER {
                  eAuto (0),
                  eOn (1),
                  eIntranet (2)
            }
    MAX-ACCESS read-write
    STATUS     current
    DESCRIPTION
            "-- empty --"
    ::= { hmSetupIpRouterRipWanSitesEntry 4 }

-- {COLUMN} 1.3.6.1.4.1.248.32.18.2.8.8.4.1.5
hmSetupIpRouterRipWanSitesEntryDftRtgTag OBJECT-TYPE
    SYNTAX     Integer32 (0..65535)
    MAX-ACCESS read-write
    STATUS     current
    DESCRIPTION
            "-- empty --"
    ::= { hmSetupIpRouterRipWanSitesEntry 5 }

-- {COLUMN} 1.3.6.1.4.1.248.32.18.2.8.8.4.1.6
hmSetupIpRouterRipWanSitesEntryRtgTagList OBJECT-TYPE
    SYNTAX     DisplayString (SIZE(0..33))
    MAX-ACCESS read-write
    STATUS     current
    DESCRIPTION
            "-- empty --"
    ::= { hmSetupIpRouterRipWanSitesEntry 6 }

-- {COLUMN} 1.3.6.1.4.1.248.32.18.2.8.8.4.1.7
hmSetupIpRouterRipWanSitesEntryPoisonedReverse OBJECT-TYPE
    SYNTAX     INTEGER {
                  eNo (0),
                  eYes (1)
            }
    MAX-ACCESS read-write
    STATUS     current
    DESCRIPTION
            "-- empty --"
    ::= { hmSetupIpRouterRipWanSitesEntry 7 }

-- {COLUMN} 1.3.6.1.4.1.248.32.18.2.8.8.4.1.8
hmSetupIpRouterRipWanSitesEntryRfc2091 OBJECT-TYPE
    SYNTAX     INTEGER {
                  eNo (0),
                  eYes (1)
            }
    MAX-ACCESS read-write
    STATUS     current
    DESCRIPTION
            "-- empty --"
    ::= { hmSetupIpRouterRipWanSitesEntry 8 }

-- {COLUMN} 1.3.6.1.4.1.248.32.18.2.8.8.4.1.9
hmSetupIpRouterRipWanSitesEntryGateway OBJECT-TYPE
    SYNTAX     IpAddress
    MAX-ACCESS read-write
    STATUS     current
    DESCRIPTION
            "-- empty --"
    ::= { hmSetupIpRouterRipWanSitesEntry 9 }

-- {COLUMN} 1.3.6.1.4.1.248.32.18.2.8.8.4.1.10
hmSetupIpRouterRipWanSitesEntryRxFilter OBJECT-TYPE
    SYNTAX     DisplayString (SIZE(0..16))
    MAX-ACCESS read-write
    STATUS     current
    DESCRIPTION
            "-- empty --"
    ::= { hmSetupIpRouterRipWanSitesEntry 10 }

-- {COLUMN} 1.3.6.1.4.1.248.32.18.2.8.8.4.1.11
hmSetupIpRouterRipWanSitesEntryTxFilter OBJECT-TYPE
    SYNTAX     DisplayString (SIZE(0..16))
    MAX-ACCESS read-write
    STATUS     current
    DESCRIPTION
            "-- empty --"
    ::= { hmSetupIpRouterRipWanSitesEntry 11 }

-- {COLUMN} 1.3.6.1.4.1.248.32.18.2.8.8.4.1.12
hmSetupIpRouterRipWanSitesEntryRipSend OBJECT-TYPE
    SYNTAX     INTEGER {
                  eNo (0),
                  eYes (1)
            }
    MAX-ACCESS read-write
    STATUS     current
    DESCRIPTION
            "-- empty --"
    ::= { hmSetupIpRouterRipWanSitesEntry 12 }

-- {COLUMN} 1.3.6.1.4.1.248.32.18.2.8.8.4.1.13
hmSetupIpRouterRipWanSitesEntryLoopbackAddress OBJECT-TYPE
    SYNTAX     DisplayString (SIZE(0..16))
    MAX-ACCESS read-write
    STATUS     current
    DESCRIPTION
            "-- empty --"
    ::= { hmSetupIpRouterRipWanSitesEntry 13 }

-- {TABLE} 1.3.6.1.4.1.248.32.18.2.8.8.5
hmSetupIpRouterRipLanSitesTable OBJECT-TYPE
    SYNTAX     SEQUENCE OF HmSetupIpRouterRipLanSitesEntry
    MAX-ACCESS not-accessible
    STATUS     current
    DESCRIPTION
            "-- empty --"
    ::= { hmSetupIpRouterRip 5 }

-- {ROW} 1.3.6.1.4.1.248.32.18.2.8.8.5.1
hmSetupIpRouterRipLanSitesEntry OBJECT-TYPE
    SYNTAX     HmSetupIpRouterRipLanSitesEntry
    MAX-ACCESS not-accessible
    STATUS     current
    DESCRIPTION
            ""
    INDEX {
            hmSetupIpRouterRipLanSitesEntryNetworkName
          }
    ::= { hmSetupIpRouterRipLanSitesTable 1 }

HmSetupIpRouterRipLanSitesEntry ::= SEQUENCE {
            hmSetupIpRouterRipLanSitesEntryNetworkName DisplayString,
            hmSetupIpRouterRipLanSitesEntryRipType INTEGER,
            hmSetupIpRouterRipLanSitesEntryRipAccept INTEGER,
            hmSetupIpRouterRipLanSitesEntryPropagate INTEGER,
            hmSetupIpRouterRipLanSitesEntryDftRtgTag Integer32,
            hmSetupIpRouterRipLanSitesEntryRtgTagList DisplayString,
            hmSetupIpRouterRipLanSitesEntryPoisonedReverse INTEGER,
            hmSetupIpRouterRipLanSitesEntryRxFilter DisplayString,
            hmSetupIpRouterRipLanSitesEntryTxFilter DisplayString,
            hmSetupIpRouterRipLanSitesEntryRipSend INTEGER
    }

-- {COLUMN} 1.3.6.1.4.1.248.32.18.2.8.8.5.1.1
hmSetupIpRouterRipLanSitesEntryNetworkName OBJECT-TYPE
    SYNTAX     DisplayString (SIZE(0..16))
    MAX-ACCESS read-write
    STATUS     current
    DESCRIPTION
            "-- empty --"
    ::= { hmSetupIpRouterRipLanSitesEntry 1 }

-- {COLUMN} 1.3.6.1.4.1.248.32.18.2.8.8.5.1.2
hmSetupIpRouterRipLanSitesEntryRipType OBJECT-TYPE
    SYNTAX     INTEGER {
                  eOff (0),
                  eRip1 (1),
                  eR1Comp (2),
                  eRip2 (3)
            }
    MAX-ACCESS read-write
    STATUS     current
    DESCRIPTION
            "-- empty --"
    ::= { hmSetupIpRouterRipLanSitesEntry 2 }

-- {COLUMN} 1.3.6.1.4.1.248.32.18.2.8.8.5.1.3
hmSetupIpRouterRipLanSitesEntryRipAccept OBJECT-TYPE
    SYNTAX     INTEGER {
                  eNo (0),
                  eYes (1)
            }
    MAX-ACCESS read-write
    STATUS     current
    DESCRIPTION
            "-- empty --"
    ::= { hmSetupIpRouterRipLanSitesEntry 3 }

-- {COLUMN} 1.3.6.1.4.1.248.32.18.2.8.8.5.1.4
hmSetupIpRouterRipLanSitesEntryPropagate OBJECT-TYPE
    SYNTAX     INTEGER {
                  eNo (0),
                  eYes (1)
            }
    MAX-ACCESS read-write
    STATUS     current
    DESCRIPTION
            "-- empty --"
    ::= { hmSetupIpRouterRipLanSitesEntry 4 }

-- {COLUMN} 1.3.6.1.4.1.248.32.18.2.8.8.5.1.5
hmSetupIpRouterRipLanSitesEntryDftRtgTag OBJECT-TYPE
    SYNTAX     Integer32 (0..65535)
    MAX-ACCESS read-write
    STATUS     current
    DESCRIPTION
            "-- empty --"
    ::= { hmSetupIpRouterRipLanSitesEntry 5 }

-- {COLUMN} 1.3.6.1.4.1.248.32.18.2.8.8.5.1.6
hmSetupIpRouterRipLanSitesEntryRtgTagList OBJECT-TYPE
    SYNTAX     DisplayString (SIZE(0..33))
    MAX-ACCESS read-write
    STATUS     current
    DESCRIPTION
            "-- empty --"
    ::= { hmSetupIpRouterRipLanSitesEntry 6 }

-- {COLUMN} 1.3.6.1.4.1.248.32.18.2.8.8.5.1.7
hmSetupIpRouterRipLanSitesEntryPoisonedReverse OBJECT-TYPE
    SYNTAX     INTEGER {
                  eNo (0),
                  eYes (1)
            }
    MAX-ACCESS read-write
    STATUS     current
    DESCRIPTION
            "-- empty --"
    ::= { hmSetupIpRouterRipLanSitesEntry 7 }

-- {COLUMN} 1.3.6.1.4.1.248.32.18.2.8.8.5.1.10
hmSetupIpRouterRipLanSitesEntryRxFilter OBJECT-TYPE
    SYNTAX     DisplayString (SIZE(0..16))
    MAX-ACCESS read-write
    STATUS     current
    DESCRIPTION
            "-- empty --"
    ::= { hmSetupIpRouterRipLanSitesEntry 10 }

-- {COLUMN} 1.3.6.1.4.1.248.32.18.2.8.8.5.1.11
hmSetupIpRouterRipLanSitesEntryTxFilter OBJECT-TYPE
    SYNTAX     DisplayString (SIZE(0..16))
    MAX-ACCESS read-write
    STATUS     current
    DESCRIPTION
            "-- empty --"
    ::= { hmSetupIpRouterRipLanSitesEntry 11 }

-- {COLUMN} 1.3.6.1.4.1.248.32.18.2.8.8.5.1.12
hmSetupIpRouterRipLanSitesEntryRipSend OBJECT-TYPE
    SYNTAX     INTEGER {
                  eNo (0),
                  eYes (1)
            }
    MAX-ACCESS read-write
    STATUS     current
    DESCRIPTION
            "-- empty --"
    ::= { hmSetupIpRouterRipLanSitesEntry 12 }

-- {NODE} 1.3.6.1.4.1.248.32.18.2.8.8.6
hmSetupIpRouterRipParameter OBJECT IDENTIFIER ::= { hmSetupIpRouterRip 6 }

-- {SCALAR} 1.3.6.1.4.1.248.32.18.2.8.8.6.1
hmSetupIpRouterRipParameterUpdate OBJECT-TYPE
    SYNTAX     Integer32 (0..255)
    MAX-ACCESS read-write
    STATUS     current
    DESCRIPTION
            "-- empty --"
    ::= { hmSetupIpRouterRipParameter 1 }

-- {SCALAR} 1.3.6.1.4.1.248.32.18.2.8.8.6.2
hmSetupIpRouterRipParameterHolddown OBJECT-TYPE
    SYNTAX     Integer32 (0..255)
    MAX-ACCESS read-write
    STATUS     current
    DESCRIPTION
            "-- empty --"
    ::= { hmSetupIpRouterRipParameter 2 }

-- {SCALAR} 1.3.6.1.4.1.248.32.18.2.8.8.6.3
hmSetupIpRouterRipParameterInvalidate OBJECT-TYPE
    SYNTAX     Integer32 (0..255)
    MAX-ACCESS read-write
    STATUS     current
    DESCRIPTION
            "-- empty --"
    ::= { hmSetupIpRouterRipParameter 3 }

-- {SCALAR} 1.3.6.1.4.1.248.32.18.2.8.8.6.4
hmSetupIpRouterRipParameterFlush OBJECT-TYPE
    SYNTAX     Integer32 (0..255)
    MAX-ACCESS read-write
    STATUS     current
    DESCRIPTION
            "-- empty --"
    ::= { hmSetupIpRouterRipParameter 4 }

-- {SCALAR} 1.3.6.1.4.1.248.32.18.2.8.8.6.5
hmSetupIpRouterRipParameterUpdDelay OBJECT-TYPE
    SYNTAX     Integer32 (0..255)
    MAX-ACCESS read-write
    STATUS     current
    DESCRIPTION
            "-- empty --"
    ::= { hmSetupIpRouterRipParameter 5 }

-- {SCALAR} 1.3.6.1.4.1.248.32.18.2.8.8.6.6
hmSetupIpRouterRipParameterMaxHopcount OBJECT-TYPE
    SYNTAX     Integer32 (0..255)
    MAX-ACCESS read-write
    STATUS     current
    DESCRIPTION
            "-- empty --"
    ::= { hmSetupIpRouterRipParameter 6 }

-- {SCALAR} 1.3.6.1.4.1.248.32.18.2.8.8.6.7
hmSetupIpRouterRipParameterRoutesPerFrame OBJECT-TYPE
    SYNTAX     Integer32 (0..255)
    MAX-ACCESS read-write
    STATUS     current
    DESCRIPTION
            "-- empty --"
    ::= { hmSetupIpRouterRipParameter 7 }

-- {SCALAR} 1.3.6.1.4.1.248.32.18.2.8.8.6.8
hmSetupIpRouterRipParameterInterPacketDelay OBJECT-TYPE
    SYNTAX     Integer32 (0..255)
    MAX-ACCESS read-write
    STATUS     current
    DESCRIPTION
            "-- empty --"
    ::= { hmSetupIpRouterRipParameter 8 }

-- {TABLE} 1.3.6.1.4.1.248.32.18.2.8.8.7
hmSetupIpRouterRipFilterTable OBJECT-TYPE
    SYNTAX     SEQUENCE OF HmSetupIpRouterRipFilterEntry
    MAX-ACCESS not-accessible
    STATUS     current
    DESCRIPTION
            "-- empty --"
    ::= { hmSetupIpRouterRip 7 }

-- {ROW} 1.3.6.1.4.1.248.32.18.2.8.8.7.1
hmSetupIpRouterRipFilterEntry OBJECT-TYPE
    SYNTAX     HmSetupIpRouterRipFilterEntry
    MAX-ACCESS not-accessible
    STATUS     current
    DESCRIPTION
            ""
    INDEX {
            hmSetupIpRouterRipFilterEntryName
          }
    ::= { hmSetupIpRouterRipFilterTable 1 }

HmSetupIpRouterRipFilterEntry ::= SEQUENCE {
            hmSetupIpRouterRipFilterEntryName DisplayString,
            hmSetupIpRouterRipFilterEntryFilter DisplayString
    }

-- {COLUMN} 1.3.6.1.4.1.248.32.18.2.8.8.7.1.1
hmSetupIpRouterRipFilterEntryName OBJECT-TYPE
    SYNTAX     DisplayString (SIZE(0..18))
    MAX-ACCESS read-write
    STATUS     current
    DESCRIPTION
            "-- empty --"
    ::= { hmSetupIpRouterRipFilterEntry 1 }

-- {COLUMN} 1.3.6.1.4.1.248.32.18.2.8.8.7.1.2
hmSetupIpRouterRipFilterEntryFilter OBJECT-TYPE
    SYNTAX     DisplayString (SIZE(0..64))
    MAX-ACCESS read-write
    STATUS     current
    DESCRIPTION
            "-- empty --"
    ::= { hmSetupIpRouterRipFilterEntry 2 }

-- {TABLE} 1.3.6.1.4.1.248.32.18.2.8.8.8
hmSetupIpRouterRipBestRoutesTable OBJECT-TYPE
    SYNTAX     SEQUENCE OF HmSetupIpRouterRipBestRoutesEntry
    MAX-ACCESS not-accessible
    STATUS     current
    DESCRIPTION
            "-- empty --"
    ::= { hmSetupIpRouterRip 8 }

-- {ROW} 1.3.6.1.4.1.248.32.18.2.8.8.8.1
hmSetupIpRouterRipBestRoutesEntry OBJECT-TYPE
    SYNTAX     HmSetupIpRouterRipBestRoutesEntry
    MAX-ACCESS not-accessible
    STATUS     current
    DESCRIPTION
            ""
    INDEX {
            hmSetupIpRouterRipBestRoutesEntryIpAddress,
            hmSetupIpRouterRipBestRoutesEntryIpNetmask,
            hmSetupIpRouterRipBestRoutesEntryRtgTag,
            hmSetupIpRouterRipBestRoutesEntryGateway
          }
    ::= { hmSetupIpRouterRipBestRoutesTable 1 }

HmSetupIpRouterRipBestRoutesEntry ::= SEQUENCE {
            hmSetupIpRouterRipBestRoutesEntryIpAddress IpAddress,
            hmSetupIpRouterRipBestRoutesEntryIpNetmask IpAddress,
            hmSetupIpRouterRipBestRoutesEntryTime Integer32,
            hmSetupIpRouterRipBestRoutesEntryDistance Integer32,
            hmSetupIpRouterRipBestRoutesEntryGateway IpAddress,
            hmSetupIpRouterRipBestRoutesEntryRtgTag Integer32,
            hmSetupIpRouterRipBestRoutesEntryPeer DisplayString,
            hmSetupIpRouterRipBestRoutesEntryVlanId Integer32,
            hmSetupIpRouterRipBestRoutesEntryNetworkName DisplayString,
            hmSetupIpRouterRipBestRoutesEntryPort INTEGER
    }

-- {COLUMN} 1.3.6.1.4.1.248.32.18.2.8.8.8.1.1
hmSetupIpRouterRipBestRoutesEntryIpAddress OBJECT-TYPE
    SYNTAX     IpAddress
    MAX-ACCESS read-only
    STATUS     current
    DESCRIPTION
            "-- empty --"
    ::= { hmSetupIpRouterRipBestRoutesEntry 1 }

-- {COLUMN} 1.3.6.1.4.1.248.32.18.2.8.8.8.1.2
hmSetupIpRouterRipBestRoutesEntryIpNetmask OBJECT-TYPE
    SYNTAX     IpAddress
    MAX-ACCESS read-only
    STATUS     current
    DESCRIPTION
            "-- empty --"
    ::= { hmSetupIpRouterRipBestRoutesEntry 2 }

-- {COLUMN} 1.3.6.1.4.1.248.32.18.2.8.8.8.1.3
hmSetupIpRouterRipBestRoutesEntryTime OBJECT-TYPE
    SYNTAX     Integer32 (0..65535)
    MAX-ACCESS read-only
    STATUS     current
    DESCRIPTION
            "-- empty --"
    ::= { hmSetupIpRouterRipBestRoutesEntry 3 }

-- {COLUMN} 1.3.6.1.4.1.248.32.18.2.8.8.8.1.4
hmSetupIpRouterRipBestRoutesEntryDistance OBJECT-TYPE
    SYNTAX     Integer32 (0..65535)
    MAX-ACCESS read-only
    STATUS     current
    DESCRIPTION
            "-- empty --"
    ::= { hmSetupIpRouterRipBestRoutesEntry 4 }

-- {COLUMN} 1.3.6.1.4.1.248.32.18.2.8.8.8.1.5
hmSetupIpRouterRipBestRoutesEntryGateway OBJECT-TYPE
    SYNTAX     IpAddress
    MAX-ACCESS read-only
    STATUS     current
    DESCRIPTION
            "-- empty --"
    ::= { hmSetupIpRouterRipBestRoutesEntry 5 }

-- {COLUMN} 1.3.6.1.4.1.248.32.18.2.8.8.8.1.6
hmSetupIpRouterRipBestRoutesEntryRtgTag OBJECT-TYPE
    SYNTAX     Integer32 (0..65535)
    MAX-ACCESS read-only
    STATUS     current
    DESCRIPTION
            "-- empty --"
    ::= { hmSetupIpRouterRipBestRoutesEntry 6 }

-- {COLUMN} 1.3.6.1.4.1.248.32.18.2.8.8.8.1.8
hmSetupIpRouterRipBestRoutesEntryPeer OBJECT-TYPE
    SYNTAX     DisplayString (SIZE(0..255))
    MAX-ACCESS read-only
    STATUS     current
    DESCRIPTION
            "-- empty --"
    ::= { hmSetupIpRouterRipBestRoutesEntry 8 }

-- {COLUMN} 1.3.6.1.4.1.248.32.18.2.8.8.8.1.10
hmSetupIpRouterRipBestRoutesEntryVlanId OBJECT-TYPE
    SYNTAX     Integer32 (0..65535)
    MAX-ACCESS read-only
    STATUS     current
    DESCRIPTION
            "-- empty --"
    ::= { hmSetupIpRouterRipBestRoutesEntry 10 }

-- {COLUMN} 1.3.6.1.4.1.248.32.18.2.8.8.8.1.11
hmSetupIpRouterRipBestRoutesEntryNetworkName OBJECT-TYPE
    SYNTAX     DisplayString (SIZE(0..255))
    MAX-ACCESS read-only
    STATUS     current
    DESCRIPTION
            "-- empty --"
    ::= { hmSetupIpRouterRipBestRoutesEntry 11 }

-- {COLUMN} 1.3.6.1.4.1.248.32.18.2.8.8.8.1.12
hmSetupIpRouterRipBestRoutesEntryPort OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eAny (65535)
            }
    MAX-ACCESS read-only
    STATUS     current
    DESCRIPTION
            "-- empty --"
    ::= { hmSetupIpRouterRipBestRoutesEntry 12 }

-- {TABLE} 1.3.6.1.4.1.248.32.18.2.8.8.9
hmSetupIpRouterRipAllRoutesTable OBJECT-TYPE
    SYNTAX     SEQUENCE OF HmSetupIpRouterRipAllRoutesEntry
    MAX-ACCESS not-accessible
    STATUS     current
    DESCRIPTION
            "-- empty --"
    ::= { hmSetupIpRouterRip 9 }

-- {ROW} 1.3.6.1.4.1.248.32.18.2.8.8.9.1
hmSetupIpRouterRipAllRoutesEntry OBJECT-TYPE
    SYNTAX     HmSetupIpRouterRipAllRoutesEntry
    MAX-ACCESS not-accessible
    STATUS     current
    DESCRIPTION
            ""
    INDEX {
            hmSetupIpRouterRipAllRoutesEntryIpAddress,
            hmSetupIpRouterRipAllRoutesEntryIpNetmask,
            hmSetupIpRouterRipAllRoutesEntryRtgTag,
            hmSetupIpRouterRipAllRoutesEntryGateway
          }
    ::= { hmSetupIpRouterRipAllRoutesTable 1 }

HmSetupIpRouterRipAllRoutesEntry ::= SEQUENCE {
            hmSetupIpRouterRipAllRoutesEntryIpAddress IpAddress,
            hmSetupIpRouterRipAllRoutesEntryIpNetmask IpAddress,
            hmSetupIpRouterRipAllRoutesEntryTime Integer32,
            hmSetupIpRouterRipAllRoutesEntryDistance Integer32,
            hmSetupIpRouterRipAllRoutesEntryGateway IpAddress,
            hmSetupIpRouterRipAllRoutesEntryRtgTag Integer32,
            hmSetupIpRouterRipAllRoutesEntryPeer DisplayString,
            hmSetupIpRouterRipAllRoutesEntryVlanId Integer32,
            hmSetupIpRouterRipAllRoutesEntryNetworkName DisplayString,
            hmSetupIpRouterRipAllRoutesEntryPort INTEGER
    }

-- {COLUMN} 1.3.6.1.4.1.248.32.18.2.8.8.9.1.1
hmSetupIpRouterRipAllRoutesEntryIpAddress OBJECT-TYPE
    SYNTAX     IpAddress
    MAX-ACCESS read-only
    STATUS     current
    DESCRIPTION
            "-- empty --"
    ::= { hmSetupIpRouterRipAllRoutesEntry 1 }

-- {COLUMN} 1.3.6.1.4.1.248.32.18.2.8.8.9.1.2
hmSetupIpRouterRipAllRoutesEntryIpNetmask OBJECT-TYPE
    SYNTAX     IpAddress
    MAX-ACCESS read-only
    STATUS     current
    DESCRIPTION
            "-- empty --"
    ::= { hmSetupIpRouterRipAllRoutesEntry 2 }

-- {COLUMN} 1.3.6.1.4.1.248.32.18.2.8.8.9.1.3
hmSetupIpRouterRipAllRoutesEntryTime OBJECT-TYPE
    SYNTAX     Integer32 (0..65535)
    MAX-ACCESS read-only
    STATUS     current
    DESCRIPTION
            "-- empty --"
    ::= { hmSetupIpRouterRipAllRoutesEntry 3 }

-- {COLUMN} 1.3.6.1.4.1.248.32.18.2.8.8.9.1.4
hmSetupIpRouterRipAllRoutesEntryDistance OBJECT-TYPE
    SYNTAX     Integer32 (0..65535)
    MAX-ACCESS read-only
    STATUS     current
    DESCRIPTION
            "-- empty --"
    ::= { hmSetupIpRouterRipAllRoutesEntry 4 }

-- {COLUMN} 1.3.6.1.4.1.248.32.18.2.8.8.9.1.5
hmSetupIpRouterRipAllRoutesEntryGateway OBJECT-TYPE
    SYNTAX     IpAddress
    MAX-ACCESS read-only
    STATUS     current
    DESCRIPTION
            "-- empty --"
    ::= { hmSetupIpRouterRipAllRoutesEntry 5 }

-- {COLUMN} 1.3.6.1.4.1.248.32.18.2.8.8.9.1.6
hmSetupIpRouterRipAllRoutesEntryRtgTag OBJECT-TYPE
    SYNTAX     Integer32 (0..65535)
    MAX-ACCESS read-only
    STATUS     current
    DESCRIPTION
            "-- empty --"
    ::= { hmSetupIpRouterRipAllRoutesEntry 6 }

-- {COLUMN} 1.3.6.1.4.1.248.32.18.2.8.8.9.1.8
hmSetupIpRouterRipAllRoutesEntryPeer OBJECT-TYPE
    SYNTAX     DisplayString (SIZE(0..255))
    MAX-ACCESS read-only
    STATUS     current
    DESCRIPTION
            "-- empty --"
    ::= { hmSetupIpRouterRipAllRoutesEntry 8 }

-- {COLUMN} 1.3.6.1.4.1.248.32.18.2.8.8.9.1.10
hmSetupIpRouterRipAllRoutesEntryVlanId OBJECT-TYPE
    SYNTAX     Integer32 (0..65535)
    MAX-ACCESS read-only
    STATUS     current
    DESCRIPTION
            "-- empty --"
    ::= { hmSetupIpRouterRipAllRoutesEntry 10 }

-- {COLUMN} 1.3.6.1.4.1.248.32.18.2.8.8.9.1.11
hmSetupIpRouterRipAllRoutesEntryNetworkName OBJECT-TYPE
    SYNTAX     DisplayString (SIZE(0..255))
    MAX-ACCESS read-only
    STATUS     current
    DESCRIPTION
            "-- empty --"
    ::= { hmSetupIpRouterRipAllRoutesEntry 11 }

-- {COLUMN} 1.3.6.1.4.1.248.32.18.2.8.8.9.1.12
hmSetupIpRouterRipAllRoutesEntryPort OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eAny (65535)
            }
    MAX-ACCESS read-only
    STATUS     current
    DESCRIPTION
            "-- empty --"
    ::= { hmSetupIpRouterRipAllRoutesEntry 12 }

-- {NODE} 1.3.6.1.4.1.248.32.18.2.8.9
hmSetupIpRouter1NNat OBJECT IDENTIFIER ::= { hmSetupIpRouter 9 }

-- {SCALAR} 1.3.6.1.4.1.248.32.18.2.8.9.1
hmSetupIpRouter1NNatTcpAgingSeconds OBJECT-TYPE
    SYNTAX     Integer32 (0..65535)
    MAX-ACCESS read-write
    STATUS     current
    DESCRIPTION
            "-- empty --"
    ::= { hmSetupIpRouter1NNat 1 }

-- {SCALAR} 1.3.6.1.4.1.248.32.18.2.8.9.2
hmSetupIpRouter1NNatUdpAgingSeconds OBJECT-TYPE
    SYNTAX     Integer32 (0..65535)
    MAX-ACCESS read-write
    STATUS     current
    DESCRIPTION
            "-- empty --"
    ::= { hmSetupIpRouter1NNat 2 }

-- {SCALAR} 1.3.6.1.4.1.248.32.18.2.8.9.3
hmSetupIpRouter1NNatIcmpAgingSeconds OBJECT-TYPE
    SYNTAX     Integer32 (0..65535)
    MAX-ACCESS read-write
    STATUS     current
    DESCRIPTION
            "-- empty --"
    ::= { hmSetupIpRouter1NNat 3 }

-- {TABLE} 1.3.6.1.4.1.248.32.18.2.8.9.4
hmSetupIpRouter1NNatServiceTableTable OBJECT-TYPE
    SYNTAX     SEQUENCE OF HmSetupIpRouter1NNatServiceTableEntry
    MAX-ACCESS not-accessible
    STATUS     current
    DESCRIPTION
            "-- empty --"
    ::= { hmSetupIpRouter1NNat 4 }

-- {ROW} 1.3.6.1.4.1.248.32.18.2.8.9.4.1
hmSetupIpRouter1NNatServiceTableEntry OBJECT-TYPE
    SYNTAX     HmSetupIpRouter1NNatServiceTableEntry
    MAX-ACCESS not-accessible
    STATUS     current
    DESCRIPTION
            ""
    INDEX {
            hmSetupIpRouter1NNatServiceTableEntryDPortFrom,
            hmSetupIpRouter1NNatServiceTableEntryDPortTo,
            hmSetupIpRouter1NNatServiceTableEntryProtocol,
            hmSetupIpRouter1NNatServiceTableEntryPeer,
            hmSetupIpRouter1NNatServiceTableEntryWanAddress
          }
    ::= { hmSetupIpRouter1NNatServiceTableTable 1 }

HmSetupIpRouter1NNatServiceTableEntry ::= SEQUENCE {
            hmSetupIpRouter1NNatServiceTableEntryDPortFrom Integer32,
            hmSetupIpRouter1NNatServiceTableEntryIntranetAddress IpAddress,
            hmSetupIpRouter1NNatServiceTableEntryDPortTo Integer32,
            hmSetupIpRouter1NNatServiceTableEntryMapPort Integer32,
            hmSetupIpRouter1NNatServiceTableEntryActive INTEGER,
            hmSetupIpRouter1NNatServiceTableEntryComment DisplayString,
            hmSetupIpRouter1NNatServiceTableEntryPeer DisplayString,
            hmSetupIpRouter1NNatServiceTableEntryProtocol INTEGER,
            hmSetupIpRouter1NNatServiceTableEntryWanAddress IpAddress
    }

-- {COLUMN} 1.3.6.1.4.1.248.32.18.2.8.9.4.1.1
hmSetupIpRouter1NNatServiceTableEntryDPortFrom OBJECT-TYPE
    SYNTAX     Integer32 (0..65535)
    MAX-ACCESS read-write
    STATUS     current
    DESCRIPTION
            "-- empty --"
    ::= { hmSetupIpRouter1NNatServiceTableEntry 1 }

-- {COLUMN} 1.3.6.1.4.1.248.32.18.2.8.9.4.1.2
hmSetupIpRouter1NNatServiceTableEntryIntranetAddress OBJECT-TYPE
    SYNTAX     IpAddress
    MAX-ACCESS read-write
    STATUS     current
    DESCRIPTION
            "-- empty --"
    ::= { hmSetupIpRouter1NNatServiceTableEntry 2 }

-- {COLUMN} 1.3.6.1.4.1.248.32.18.2.8.9.4.1.3
hmSetupIpRouter1NNatServiceTableEntryDPortTo OBJECT-TYPE
    SYNTAX     Integer32 (0..65535)
    MAX-ACCESS read-write
    STATUS     current
    DESCRIPTION
            "-- empty --"
    ::= { hmSetupIpRouter1NNatServiceTableEntry 3 }

-- {COLUMN} 1.3.6.1.4.1.248.32.18.2.8.9.4.1.4
hmSetupIpRouter1NNatServiceTableEntryMapPort OBJECT-TYPE
    SYNTAX     Integer32 (0..65535)
    MAX-ACCESS read-write
    STATUS     current
    DESCRIPTION
            "-- empty --"
    ::= { hmSetupIpRouter1NNatServiceTableEntry 4 }

-- {COLUMN} 1.3.6.1.4.1.248.32.18.2.8.9.4.1.5
hmSetupIpRouter1NNatServiceTableEntryActive OBJECT-TYPE
    SYNTAX     INTEGER {
                  eYes (0),
                  eNo (1)
            }
    MAX-ACCESS read-write
    STATUS     current
    DESCRIPTION
            "-- empty --"
    ::= { hmSetupIpRouter1NNatServiceTableEntry 5 }

-- {COLUMN} 1.3.6.1.4.1.248.32.18.2.8.9.4.1.6
hmSetupIpRouter1NNatServiceTableEntryComment OBJECT-TYPE
    SYNTAX     DisplayString (SIZE(0..64))
    MAX-ACCESS read-write
    STATUS     current
    DESCRIPTION
            "-- empty --"
    ::= { hmSetupIpRouter1NNatServiceTableEntry 6 }

-- {COLUMN} 1.3.6.1.4.1.248.32.18.2.8.9.4.1.7
hmSetupIpRouter1NNatServiceTableEntryPeer OBJECT-TYPE
    SYNTAX     DisplayString (SIZE(0..16))
    MAX-ACCESS read-write
    STATUS     current
    DESCRIPTION
            "-- empty --"
    ::= { hmSetupIpRouter1NNatServiceTableEntry 7 }

-- {COLUMN} 1.3.6.1.4.1.248.32.18.2.8.9.4.1.8
hmSetupIpRouter1NNatServiceTableEntryProtocol OBJECT-TYPE
    SYNTAX     INTEGER {
                  eTcpPlusUdp (0),
                  eTcp (1),
                  eUdp (2)
            }
    MAX-ACCESS read-write
    STATUS     current
    DESCRIPTION
            "-- empty --"
    ::= { hmSetupIpRouter1NNatServiceTableEntry 8 }

-- {COLUMN} 1.3.6.1.4.1.248.32.18.2.8.9.4.1.9
hmSetupIpRouter1NNatServiceTableEntryWanAddress OBJECT-TYPE
    SYNTAX     IpAddress
    MAX-ACCESS read-write
    STATUS     current
    DESCRIPTION
            "-- empty --"
    ::= { hmSetupIpRouter1NNatServiceTableEntry 9 }

-- {TABLE} 1.3.6.1.4.1.248.32.18.2.8.9.5
hmSetupIpRouter1NNatTable1NNatTable OBJECT-TYPE
    SYNTAX     SEQUENCE OF HmSetupIpRouter1NNatTable1NNatEntry
    MAX-ACCESS not-accessible
    STATUS     current
    DESCRIPTION
            "-- empty --"
    ::= { hmSetupIpRouter1NNat 5 }

-- {ROW} 1.3.6.1.4.1.248.32.18.2.8.9.5.1
hmSetupIpRouter1NNatTable1NNatEntry OBJECT-TYPE
    SYNTAX     HmSetupIpRouter1NNatTable1NNatEntry
    MAX-ACCESS not-accessible
    STATUS     current
    DESCRIPTION
            ""
    INDEX {
            hmSetupIpRouter1NNatTable1NNatEntryIntranetAddress
          }
    ::= { hmSetupIpRouter1NNatTable1NNatTable 1 }

HmSetupIpRouter1NNatTable1NNatEntry ::= SEQUENCE {
            hmSetupIpRouter1NNatTable1NNatEntryIntranetAddress IpAddress,
            hmSetupIpRouter1NNatTable1NNatEntrySourcePort Integer32,
            hmSetupIpRouter1NNatTable1NNatEntryProtocol INTEGER,
            hmSetupIpRouter1NNatTable1NNatEntryTimeout Integer32,
            hmSetupIpRouter1NNatTable1NNatEntryHandler DisplayString,
            hmSetupIpRouter1NNatTable1NNatEntryRemoteAddress IpAddress
    }

-- {COLUMN} 1.3.6.1.4.1.248.32.18.2.8.9.5.1.1
hmSetupIpRouter1NNatTable1NNatEntryIntranetAddress OBJECT-TYPE
    SYNTAX     IpAddress
    MAX-ACCESS read-only
    STATUS     current
    DESCRIPTION
            "-- empty --"
    ::= { hmSetupIpRouter1NNatTable1NNatEntry 1 }

-- {COLUMN} 1.3.6.1.4.1.248.32.18.2.8.9.5.1.2
hmSetupIpRouter1NNatTable1NNatEntrySourcePort OBJECT-TYPE
    SYNTAX     Integer32 (0..65535)
    MAX-ACCESS read-only
    STATUS     current
    DESCRIPTION
            "-- empty --"
    ::= { hmSetupIpRouter1NNatTable1NNatEntry 2 }

-- {COLUMN} 1.3.6.1.4.1.248.32.18.2.8.9.5.1.3
hmSetupIpRouter1NNatTable1NNatEntryProtocol OBJECT-TYPE
    SYNTAX     INTEGER {
                  eIcmp (1),
                  eTcp (6),
                  eUdp (17)
            }
    MAX-ACCESS read-only
    STATUS     current
    DESCRIPTION
            "-- empty --"
    ::= { hmSetupIpRouter1NNatTable1NNatEntry 3 }

-- {COLUMN} 1.3.6.1.4.1.248.32.18.2.8.9.5.1.4
hmSetupIpRouter1NNatTable1NNatEntryTimeout OBJECT-TYPE
    SYNTAX     Integer32 (0..65535)
    MAX-ACCESS read-only
    STATUS     current
    DESCRIPTION
            "-- empty --"
    ::= { hmSetupIpRouter1NNatTable1NNatEntry 4 }

-- {COLUMN} 1.3.6.1.4.1.248.32.18.2.8.9.5.1.5
hmSetupIpRouter1NNatTable1NNatEntryHandler OBJECT-TYPE
    SYNTAX     DisplayString (SIZE(0..255))
    MAX-ACCESS read-only
    STATUS     current
    DESCRIPTION
            "-- empty --"
    ::= { hmSetupIpRouter1NNatTable1NNatEntry 5 }

-- {COLUMN} 1.3.6.1.4.1.248.32.18.2.8.9.5.1.6
hmSetupIpRouter1NNatTable1NNatEntryRemoteAddress OBJECT-TYPE
    SYNTAX     IpAddress
    MAX-ACCESS read-only
    STATUS     current
    DESCRIPTION
            "-- empty --"
    ::= { hmSetupIpRouter1NNatTable1NNatEntry 6 }

-- {SCALAR} 1.3.6.1.4.1.248.32.18.2.8.9.6
hmSetupIpRouter1NNatFragments OBJECT-TYPE
    SYNTAX     INTEGER {
                  eFilter (0),
                  eRoute (1),
                  eReassemble (2)
            }
    MAX-ACCESS read-write
    STATUS     current
    DESCRIPTION
            "-- empty --"
    ::= { hmSetupIpRouter1NNat 6 }

-- {SCALAR} 1.3.6.1.4.1.248.32.18.2.8.9.7
hmSetupIpRouter1NNatFragmentAgingSeconds OBJECT-TYPE
    SYNTAX     Integer32 (0..255)
    MAX-ACCESS read-write
    STATUS     current
    DESCRIPTION
            "-- empty --"
    ::= { hmSetupIpRouter1NNat 7 }

-- {SCALAR} 1.3.6.1.4.1.248.32.18.2.8.9.8
hmSetupIpRouter1NNatIpsecAgingSeconds OBJECT-TYPE
    SYNTAX     Integer32 (0..65535)
    MAX-ACCESS read-write
    STATUS     current
    DESCRIPTION
            "-- empty --"
    ::= { hmSetupIpRouter1NNat 8 }

-- {TABLE} 1.3.6.1.4.1.248.32.18.2.8.9.9
hmSetupIpRouter1NNatIpsecTableTable OBJECT-TYPE
    SYNTAX     SEQUENCE OF HmSetupIpRouter1NNatIpsecTableEntry
    MAX-ACCESS not-accessible
    STATUS     current
    DESCRIPTION
            "-- empty --"
    ::= { hmSetupIpRouter1NNat 9 }

-- {ROW} 1.3.6.1.4.1.248.32.18.2.8.9.9.1
hmSetupIpRouter1NNatIpsecTableEntry OBJECT-TYPE
    SYNTAX     HmSetupIpRouter1NNatIpsecTableEntry
    MAX-ACCESS not-accessible
    STATUS     current
    DESCRIPTION
            ""
    INDEX {
            hmSetupIpRouter1NNatIpsecTableEntryRemoteAddress
          }
    ::= { hmSetupIpRouter1NNatIpsecTableTable 1 }

HmSetupIpRouter1NNatIpsecTableEntry ::= SEQUENCE {
            hmSetupIpRouter1NNatIpsecTableEntryRemoteAddress IpAddress,
            hmSetupIpRouter1NNatIpsecTableEntryLocalAddress IpAddress,
            hmSetupIpRouter1NNatIpsecTableEntryRcHi DisplayString,
            hmSetupIpRouter1NNatIpsecTableEntryRcLo DisplayString,
            hmSetupIpRouter1NNatIpsecTableEntryLcHi DisplayString,
            hmSetupIpRouter1NNatIpsecTableEntryLcLo DisplayString,
            hmSetupIpRouter1NNatIpsecTableEntryRemoteSpi DisplayString,
            hmSetupIpRouter1NNatIpsecTableEntryLocalSpi DisplayString,
            hmSetupIpRouter1NNatIpsecTableEntryTimeout Integer32,
            hmSetupIpRouter1NNatIpsecTableEntryFlags DisplayString,
            hmSetupIpRouter1NNatIpsecTableEntryCo Integer32,
            hmSetupIpRouter1NNatIpsecTableEntryNl Integer32,
            hmSetupIpRouter1NNatIpsecTableEntryNr Integer32,
            hmSetupIpRouter1NNatIpsecTableEntryDp Integer32
    }

-- {COLUMN} 1.3.6.1.4.1.248.32.18.2.8.9.9.1.1
hmSetupIpRouter1NNatIpsecTableEntryRemoteAddress OBJECT-TYPE
    SYNTAX     IpAddress
    MAX-ACCESS read-only
    STATUS     current
    DESCRIPTION
            "-- empty --"
    ::= { hmSetupIpRouter1NNatIpsecTableEntry 1 }

-- {COLUMN} 1.3.6.1.4.1.248.32.18.2.8.9.9.1.2
hmSetupIpRouter1NNatIpsecTableEntryLocalAddress OBJECT-TYPE
    SYNTAX     IpAddress
    MAX-ACCESS read-only
    STATUS     current
    DESCRIPTION
            "-- empty --"
    ::= { hmSetupIpRouter1NNatIpsecTableEntry 2 }

-- {COLUMN} 1.3.6.1.4.1.248.32.18.2.8.9.9.1.3
hmSetupIpRouter1NNatIpsecTableEntryRcHi OBJECT-TYPE
    SYNTAX     DisplayString (SIZE(0..8))
    MAX-ACCESS read-only
    STATUS     current
    DESCRIPTION
            "-- empty --"
    ::= { hmSetupIpRouter1NNatIpsecTableEntry 3 }

-- {COLUMN} 1.3.6.1.4.1.248.32.18.2.8.9.9.1.4
hmSetupIpRouter1NNatIpsecTableEntryRcLo OBJECT-TYPE
    SYNTAX     DisplayString (SIZE(0..8))
    MAX-ACCESS read-only
    STATUS     current
    DESCRIPTION
            "-- empty --"
    ::= { hmSetupIpRouter1NNatIpsecTableEntry 4 }

-- {COLUMN} 1.3.6.1.4.1.248.32.18.2.8.9.9.1.5
hmSetupIpRouter1NNatIpsecTableEntryLcHi OBJECT-TYPE
    SYNTAX     DisplayString (SIZE(0..8))
    MAX-ACCESS read-only
    STATUS     current
    DESCRIPTION
            "-- empty --"
    ::= { hmSetupIpRouter1NNatIpsecTableEntry 5 }

-- {COLUMN} 1.3.6.1.4.1.248.32.18.2.8.9.9.1.6
hmSetupIpRouter1NNatIpsecTableEntryLcLo OBJECT-TYPE
    SYNTAX     DisplayString (SIZE(0..8))
    MAX-ACCESS read-only
    STATUS     current
    DESCRIPTION
            "-- empty --"
    ::= { hmSetupIpRouter1NNatIpsecTableEntry 6 }

-- {COLUMN} 1.3.6.1.4.1.248.32.18.2.8.9.9.1.7
hmSetupIpRouter1NNatIpsecTableEntryRemoteSpi OBJECT-TYPE
    SYNTAX     DisplayString (SIZE(0..8))
    MAX-ACCESS read-only
    STATUS     current
    DESCRIPTION
            "-- empty --"
    ::= { hmSetupIpRouter1NNatIpsecTableEntry 7 }

-- {COLUMN} 1.3.6.1.4.1.248.32.18.2.8.9.9.1.8
hmSetupIpRouter1NNatIpsecTableEntryLocalSpi OBJECT-TYPE
    SYNTAX     DisplayString (SIZE(0..8))
    MAX-ACCESS read-only
    STATUS     current
    DESCRIPTION
            "-- empty --"
    ::= { hmSetupIpRouter1NNatIpsecTableEntry 8 }

-- {COLUMN} 1.3.6.1.4.1.248.32.18.2.8.9.9.1.9
hmSetupIpRouter1NNatIpsecTableEntryTimeout OBJECT-TYPE
    SYNTAX     Integer32 (0..2147483647)
    MAX-ACCESS read-only
    STATUS     current
    DESCRIPTION
            "-- empty --"
    ::= { hmSetupIpRouter1NNatIpsecTableEntry 9 }

-- {COLUMN} 1.3.6.1.4.1.248.32.18.2.8.9.9.1.10
hmSetupIpRouter1NNatIpsecTableEntryFlags OBJECT-TYPE
    SYNTAX     DisplayString (SIZE(0..4))
    MAX-ACCESS read-only
    STATUS     current
    DESCRIPTION
            "-- empty --"
    ::= { hmSetupIpRouter1NNatIpsecTableEntry 10 }

-- {COLUMN} 1.3.6.1.4.1.248.32.18.2.8.9.9.1.11
hmSetupIpRouter1NNatIpsecTableEntryCo OBJECT-TYPE
    SYNTAX     Integer32 (0..255)
    MAX-ACCESS read-only
    STATUS     current
    DESCRIPTION
            "-- empty --"
    ::= { hmSetupIpRouter1NNatIpsecTableEntry 11 }

-- {COLUMN} 1.3.6.1.4.1.248.32.18.2.8.9.9.1.12
hmSetupIpRouter1NNatIpsecTableEntryNl OBJECT-TYPE
    SYNTAX     Integer32 (0..255)
    MAX-ACCESS read-only
    STATUS     current
    DESCRIPTION
            "-- empty --"
    ::= { hmSetupIpRouter1NNatIpsecTableEntry 12 }

-- {COLUMN} 1.3.6.1.4.1.248.32.18.2.8.9.9.1.13
hmSetupIpRouter1NNatIpsecTableEntryNr OBJECT-TYPE
    SYNTAX     Integer32 (0..255)
    MAX-ACCESS read-only
    STATUS     current
    DESCRIPTION
            "-- empty --"
    ::= { hmSetupIpRouter1NNatIpsecTableEntry 13 }

-- {COLUMN} 1.3.6.1.4.1.248.32.18.2.8.9.9.1.14
hmSetupIpRouter1NNatIpsecTableEntryDp OBJECT-TYPE
    SYNTAX     Integer32 (0..255)
    MAX-ACCESS read-only
    STATUS     current
    DESCRIPTION
            "-- empty --"
    ::= { hmSetupIpRouter1NNatIpsecTableEntry 14 }

-- {SCALAR} 1.3.6.1.4.1.248.32.18.2.8.9.10
hmSetupIpRouter1NNatIdSpoofing OBJECT-TYPE
    SYNTAX     INTEGER {
                  eNo (0),
                  eYes (1)
            }
    MAX-ACCESS read-write
    STATUS     current
    DESCRIPTION
            "-- empty --"
    ::= { hmSetupIpRouter1NNat 10 }

-- {NODE} 1.3.6.1.4.1.248.32.18.2.8.10
hmSetupIpRouterFirewall OBJECT IDENTIFIER ::= { hmSetupIpRouter 10 }

-- {TABLE} 1.3.6.1.4.1.248.32.18.2.8.10.1
hmSetupIpRouterFirewallObjectsTable OBJECT-TYPE
    SYNTAX     SEQUENCE OF HmSetupIpRouterFirewallObjectsEntry
    MAX-ACCESS not-accessible
    STATUS     current
    DESCRIPTION
            "-- empty --"
    ::= { hmSetupIpRouterFirewall 1 }

-- {ROW} 1.3.6.1.4.1.248.32.18.2.8.10.1.1
hmSetupIpRouterFirewallObjectsEntry OBJECT-TYPE
    SYNTAX     HmSetupIpRouterFirewallObjectsEntry
    MAX-ACCESS not-accessible
    STATUS     current
    DESCRIPTION
            ""
    INDEX {
            hmSetupIpRouterFirewallObjectsEntryName
          }
    ::= { hmSetupIpRouterFirewallObjectsTable 1 }

HmSetupIpRouterFirewallObjectsEntry ::= SEQUENCE {
            hmSetupIpRouterFirewallObjectsEntryName DisplayString,
            hmSetupIpRouterFirewallObjectsEntryDescription DisplayString
    }

-- {COLUMN} 1.3.6.1.4.1.248.32.18.2.8.10.1.1.1
hmSetupIpRouterFirewallObjectsEntryName OBJECT-TYPE
    SYNTAX     DisplayString (SIZE(0..32))
    MAX-ACCESS read-write
    STATUS     current
    DESCRIPTION
            "-- empty --"
    ::= { hmSetupIpRouterFirewallObjectsEntry 1 }

-- {COLUMN} 1.3.6.1.4.1.248.32.18.2.8.10.1.1.2
hmSetupIpRouterFirewallObjectsEntryDescription OBJECT-TYPE
    SYNTAX     DisplayString (SIZE(0..64))
    MAX-ACCESS read-write
    STATUS     current
    DESCRIPTION
            "-- empty --"
    ::= { hmSetupIpRouterFirewallObjectsEntry 2 }

-- {TABLE} 1.3.6.1.4.1.248.32.18.2.8.10.2
hmSetupIpRouterFirewallRulesTable OBJECT-TYPE
    SYNTAX     SEQUENCE OF HmSetupIpRouterFirewallRulesEntry
    MAX-ACCESS not-accessible
    STATUS     current
    DESCRIPTION
            "-- empty --"
    ::= { hmSetupIpRouterFirewall 2 }

-- {ROW} 1.3.6.1.4.1.248.32.18.2.8.10.2.1
hmSetupIpRouterFirewallRulesEntry OBJECT-TYPE
    SYNTAX     HmSetupIpRouterFirewallRulesEntry
    MAX-ACCESS not-accessible
    STATUS     current
    DESCRIPTION
            ""
    INDEX {
            hmSetupIpRouterFirewallRulesEntryName
          }
    ::= { hmSetupIpRouterFirewallRulesTable 1 }

HmSetupIpRouterFirewallRulesEntry ::= SEQUENCE {
            hmSetupIpRouterFirewallRulesEntryName DisplayString,
            hmSetupIpRouterFirewallRulesEntryProt DisplayString,
            hmSetupIpRouterFirewallRulesEntrySource DisplayString,
            hmSetupIpRouterFirewallRulesEntryDestination DisplayString,
            hmSetupIpRouterFirewallRulesEntryAction DisplayString,
            hmSetupIpRouterFirewallRulesEntryLinked INTEGER,
            hmSetupIpRouterFirewallRulesEntryPrio Integer32,
            hmSetupIpRouterFirewallRulesEntryFirewallRule INTEGER,
            hmSetupIpRouterFirewallRulesEntryVpnRule INTEGER,
            hmSetupIpRouterFirewallRulesEntryStateful INTEGER,
            hmSetupIpRouterFirewallRulesEntryComment DisplayString,
            hmSetupIpRouterFirewallRulesEntryRtgTag Integer32,
            hmSetupIpRouterFirewallRulesEntrySrcTag Integer32
    }

-- {COLUMN} 1.3.6.1.4.1.248.32.18.2.8.10.2.1.1
hmSetupIpRouterFirewallRulesEntryName OBJECT-TYPE
    SYNTAX     DisplayString (SIZE(0..32))
    MAX-ACCESS read-write
    STATUS     current
    DESCRIPTION
            "-- empty --"
    ::= { hmSetupIpRouterFirewallRulesEntry 1 }

-- {COLUMN} 1.3.6.1.4.1.248.32.18.2.8.10.2.1.2
hmSetupIpRouterFirewallRulesEntryProt OBJECT-TYPE
    SYNTAX     DisplayString (SIZE(0..10))
    MAX-ACCESS read-write
    STATUS     current
    DESCRIPTION
            "-- empty --"
    ::= { hmSetupIpRouterFirewallRulesEntry 2 }

-- {COLUMN} 1.3.6.1.4.1.248.32.18.2.8.10.2.1.3
hmSetupIpRouterFirewallRulesEntrySource OBJECT-TYPE
    SYNTAX     DisplayString (SIZE(0..40))
    MAX-ACCESS read-write
    STATUS     current
    DESCRIPTION
            "-- empty --"
    ::= { hmSetupIpRouterFirewallRulesEntry 3 }

-- {COLUMN} 1.3.6.1.4.1.248.32.18.2.8.10.2.1.4
hmSetupIpRouterFirewallRulesEntryDestination OBJECT-TYPE
    SYNTAX     DisplayString (SIZE(0..40))
    MAX-ACCESS read-write
    STATUS     current
    DESCRIPTION
            "-- empty --"
    ::= { hmSetupIpRouterFirewallRulesEntry 4 }

-- {COLUMN} 1.3.6.1.4.1.248.32.18.2.8.10.2.1.7
hmSetupIpRouterFirewallRulesEntryAction OBJECT-TYPE
    SYNTAX     DisplayString (SIZE(0..40))
    MAX-ACCESS read-write
    STATUS     current
    DESCRIPTION
            "-- empty --"
    ::= { hmSetupIpRouterFirewallRulesEntry 7 }

-- {COLUMN} 1.3.6.1.4.1.248.32.18.2.8.10.2.1.8
hmSetupIpRouterFirewallRulesEntryLinked OBJECT-TYPE
    SYNTAX     INTEGER {
                  eNo (0),
                  eYes (1)
            }
    MAX-ACCESS read-write
    STATUS     current
    DESCRIPTION
            "-- empty --"
    ::= { hmSetupIpRouterFirewallRulesEntry 8 }

-- {COLUMN} 1.3.6.1.4.1.248.32.18.2.8.10.2.1.9
hmSetupIpRouterFirewallRulesEntryPrio OBJECT-TYPE
    SYNTAX     Integer32 (0..65535)
    MAX-ACCESS read-write
    STATUS     current
    DESCRIPTION
            "-- empty --"
    ::= { hmSetupIpRouterFirewallRulesEntry 9 }

-- {COLUMN} 1.3.6.1.4.1.248.32.18.2.8.10.2.1.10
hmSetupIpRouterFirewallRulesEntryFirewallRule OBJECT-TYPE
    SYNTAX     INTEGER {
                  eYes (0),
                  eNo (1)
            }
    MAX-ACCESS read-write
    STATUS     current
    DESCRIPTION
            "-- empty --"
    ::= { hmSetupIpRouterFirewallRulesEntry 10 }

-- {COLUMN} 1.3.6.1.4.1.248.32.18.2.8.10.2.1.11
hmSetupIpRouterFirewallRulesEntryVpnRule OBJECT-TYPE
    SYNTAX     INTEGER {
                  eNo (0),
                  eYes (1)
            }
    MAX-ACCESS read-write
    STATUS     current
    DESCRIPTION
            "-- empty --"
    ::= { hmSetupIpRouterFirewallRulesEntry 11 }

-- {COLUMN} 1.3.6.1.4.1.248.32.18.2.8.10.2.1.12
hmSetupIpRouterFirewallRulesEntryStateful OBJECT-TYPE
    SYNTAX     INTEGER {
                  eYes (0),
                  eNo (1)
            }
    MAX-ACCESS read-write
    STATUS     current
    DESCRIPTION
            "-- empty --"
    ::= { hmSetupIpRouterFirewallRulesEntry 12 }

-- {COLUMN} 1.3.6.1.4.1.248.32.18.2.8.10.2.1.13
hmSetupIpRouterFirewallRulesEntryComment OBJECT-TYPE
    SYNTAX     DisplayString (SIZE(0..64))
    MAX-ACCESS read-write
    STATUS     current
    DESCRIPTION
            "-- empty --"
    ::= { hmSetupIpRouterFirewallRulesEntry 13 }

-- {COLUMN} 1.3.6.1.4.1.248.32.18.2.8.10.2.1.14
hmSetupIpRouterFirewallRulesEntryRtgTag OBJECT-TYPE
    SYNTAX     Integer32 (0..65535)
    MAX-ACCESS read-write
    STATUS     current
    DESCRIPTION
            "-- empty --"
    ::= { hmSetupIpRouterFirewallRulesEntry 14 }

-- {COLUMN} 1.3.6.1.4.1.248.32.18.2.8.10.2.1.15
hmSetupIpRouterFirewallRulesEntrySrcTag OBJECT-TYPE
    SYNTAX     Integer32 (0..65535)
    MAX-ACCESS read-write
    STATUS     current
    DESCRIPTION
            "-- empty --"
    ::= { hmSetupIpRouterFirewallRulesEntry 15 }

-- {TABLE} 1.3.6.1.4.1.248.32.18.2.8.10.3
hmSetupIpRouterFirewallFilterListTable OBJECT-TYPE
    SYNTAX     SEQUENCE OF HmSetupIpRouterFirewallFilterListEntry
    MAX-ACCESS not-accessible
    STATUS     current
    DESCRIPTION
            "-- empty --"
    ::= { hmSetupIpRouterFirewall 3 }

-- {ROW} 1.3.6.1.4.1.248.32.18.2.8.10.3.1
hmSetupIpRouterFirewallFilterListEntry OBJECT-TYPE
    SYNTAX     HmSetupIpRouterFirewallFilterListEntry
    MAX-ACCESS not-accessible
    STATUS     current
    DESCRIPTION
            ""
    INDEX {
            hmSetupIpRouterFirewallFilterListEntryIdx
          }
    ::= { hmSetupIpRouterFirewallFilterListTable 1 }

HmSetupIpRouterFirewallFilterListEntry ::= SEQUENCE {
            hmSetupIpRouterFirewallFilterListEntryIdx Integer32,
            hmSetupIpRouterFirewallFilterListEntryProt Integer32,
            hmSetupIpRouterFirewallFilterListEntrySrcAddress IpAddress,
            hmSetupIpRouterFirewallFilterListEntrySrcNetmask IpAddress,
            hmSetupIpRouterFirewallFilterListEntrySSt Integer32,
            hmSetupIpRouterFirewallFilterListEntrySEnd Integer32,
            hmSetupIpRouterFirewallFilterListEntryDstAddress IpAddress,
            hmSetupIpRouterFirewallFilterListEntryDstNetmask IpAddress,
            hmSetupIpRouterFirewallFilterListEntryDSt Integer32,
            hmSetupIpRouterFirewallFilterListEntryDEnd Integer32,
            hmSetupIpRouterFirewallFilterListEntryAction DisplayString,
            hmSetupIpRouterFirewallFilterListEntrySrcMac DisplayString,
            hmSetupIpRouterFirewallFilterListEntryDstMac DisplayString,
            hmSetupIpRouterFirewallFilterListEntryLinked INTEGER,
            hmSetupIpRouterFirewallFilterListEntryPrio Integer32,
            hmSetupIpRouterFirewallFilterListEntryRtgTag Integer32,
            hmSetupIpRouterFirewallFilterListEntrySrcTag Integer32
    }

-- {COLUMN} 1.3.6.1.4.1.248.32.18.2.8.10.3.1.1
hmSetupIpRouterFirewallFilterListEntryIdx OBJECT-TYPE
    SYNTAX     Integer32 (0..2147483647)
    MAX-ACCESS read-only
    STATUS     current
    DESCRIPTION
            "-- empty --"
    ::= { hmSetupIpRouterFirewallFilterListEntry 1 }

-- {COLUMN} 1.3.6.1.4.1.248.32.18.2.8.10.3.1.2
hmSetupIpRouterFirewallFilterListEntryProt OBJECT-TYPE
    SYNTAX     Integer32 (0..255)
    MAX-ACCESS read-only
    STATUS     current
    DESCRIPTION
            "-- empty --"
    ::= { hmSetupIpRouterFirewallFilterListEntry 2 }

-- {COLUMN} 1.3.6.1.4.1.248.32.18.2.8.10.3.1.3
hmSetupIpRouterFirewallFilterListEntrySrcAddress OBJECT-TYPE
    SYNTAX     IpAddress
    MAX-ACCESS read-only
    STATUS     current
    DESCRIPTION
            "-- empty --"
    ::= { hmSetupIpRouterFirewallFilterListEntry 3 }

-- {COLUMN} 1.3.6.1.4.1.248.32.18.2.8.10.3.1.4
hmSetupIpRouterFirewallFilterListEntrySrcNetmask OBJECT-TYPE
    SYNTAX     IpAddress
    MAX-ACCESS read-only
    STATUS     current
    DESCRIPTION
            "-- empty --"
    ::= { hmSetupIpRouterFirewallFilterListEntry 4 }

-- {COLUMN} 1.3.6.1.4.1.248.32.18.2.8.10.3.1.5
hmSetupIpRouterFirewallFilterListEntrySSt OBJECT-TYPE
    SYNTAX     Integer32 (0..65535)
    MAX-ACCESS read-only
    STATUS     current
    DESCRIPTION
            "-- empty --"
    ::= { hmSetupIpRouterFirewallFilterListEntry 5 }

-- {COLUMN} 1.3.6.1.4.1.248.32.18.2.8.10.3.1.6
hmSetupIpRouterFirewallFilterListEntrySEnd OBJECT-TYPE
    SYNTAX     Integer32 (0..65535)
    MAX-ACCESS read-only
    STATUS     current
    DESCRIPTION
            "-- empty --"
    ::= { hmSetupIpRouterFirewallFilterListEntry 6 }

-- {COLUMN} 1.3.6.1.4.1.248.32.18.2.8.10.3.1.7
hmSetupIpRouterFirewallFilterListEntryDstAddress OBJECT-TYPE
    SYNTAX     IpAddress
    MAX-ACCESS read-only
    STATUS     current
    DESCRIPTION
            "-- empty --"
    ::= { hmSetupIpRouterFirewallFilterListEntry 7 }

-- {COLUMN} 1.3.6.1.4.1.248.32.18.2.8.10.3.1.8
hmSetupIpRouterFirewallFilterListEntryDstNetmask OBJECT-TYPE
    SYNTAX     IpAddress
    MAX-ACCESS read-only
    STATUS     current
    DESCRIPTION
            "-- empty --"
    ::= { hmSetupIpRouterFirewallFilterListEntry 8 }

-- {COLUMN} 1.3.6.1.4.1.248.32.18.2.8.10.3.1.9
hmSetupIpRouterFirewallFilterListEntryDSt OBJECT-TYPE
    SYNTAX     Integer32 (0..65535)
    MAX-ACCESS read-only
    STATUS     current
    DESCRIPTION
            "-- empty --"
    ::= { hmSetupIpRouterFirewallFilterListEntry 9 }

-- {COLUMN} 1.3.6.1.4.1.248.32.18.2.8.10.3.1.10
hmSetupIpRouterFirewallFilterListEntryDEnd OBJECT-TYPE
    SYNTAX     Integer32 (0..65535)
    MAX-ACCESS read-only
    STATUS     current
    DESCRIPTION
            "-- empty --"
    ::= { hmSetupIpRouterFirewallFilterListEntry 10 }

-- {COLUMN} 1.3.6.1.4.1.248.32.18.2.8.10.3.1.11
hmSetupIpRouterFirewallFilterListEntryAction OBJECT-TYPE
    SYNTAX     DisplayString (SIZE(0..255))
    MAX-ACCESS read-only
    STATUS     current
    DESCRIPTION
            "-- empty --"
    ::= { hmSetupIpRouterFirewallFilterListEntry 11 }

-- {COLUMN} 1.3.6.1.4.1.248.32.18.2.8.10.3.1.13
hmSetupIpRouterFirewallFilterListEntrySrcMac OBJECT-TYPE
    SYNTAX     DisplayString (SIZE(0..255))
    MAX-ACCESS read-only
    STATUS     current
    DESCRIPTION
            "-- empty --"
    ::= { hmSetupIpRouterFirewallFilterListEntry 13 }

-- {COLUMN} 1.3.6.1.4.1.248.32.18.2.8.10.3.1.14
hmSetupIpRouterFirewallFilterListEntryDstMac OBJECT-TYPE
    SYNTAX     DisplayString (SIZE(0..255))
    MAX-ACCESS read-only
    STATUS     current
    DESCRIPTION
            "-- empty --"
    ::= { hmSetupIpRouterFirewallFilterListEntry 14 }

-- {COLUMN} 1.3.6.1.4.1.248.32.18.2.8.10.3.1.15
hmSetupIpRouterFirewallFilterListEntryLinked OBJECT-TYPE
    SYNTAX     INTEGER {
                  eNo (0),
                  eYes (1)
            }
    MAX-ACCESS read-only
    STATUS     current
    DESCRIPTION
            "-- empty --"
    ::= { hmSetupIpRouterFirewallFilterListEntry 15 }

-- {COLUMN} 1.3.6.1.4.1.248.32.18.2.8.10.3.1.16
hmSetupIpRouterFirewallFilterListEntryPrio OBJECT-TYPE
    SYNTAX     Integer32 (0..65535)
    MAX-ACCESS read-only
    STATUS     current
    DESCRIPTION
            "-- empty --"
    ::= { hmSetupIpRouterFirewallFilterListEntry 16 }

-- {COLUMN} 1.3.6.1.4.1.248.32.18.2.8.10.3.1.17
hmSetupIpRouterFirewallFilterListEntryRtgTag OBJECT-TYPE
    SYNTAX     Integer32 (0..65535)
    MAX-ACCESS read-only
    STATUS     current
    DESCRIPTION
            "-- empty --"
    ::= { hmSetupIpRouterFirewallFilterListEntry 17 }

-- {COLUMN} 1.3.6.1.4.1.248.32.18.2.8.10.3.1.18
hmSetupIpRouterFirewallFilterListEntrySrcTag OBJECT-TYPE
    SYNTAX     Integer32 (0..65535)
    MAX-ACCESS read-only
    STATUS     current
    DESCRIPTION
            "-- empty --"
    ::= { hmSetupIpRouterFirewallFilterListEntry 18 }

-- {TABLE} 1.3.6.1.4.1.248.32.18.2.8.10.4
hmSetupIpRouterFirewallActionsTable OBJECT-TYPE
    SYNTAX     SEQUENCE OF HmSetupIpRouterFirewallActionsEntry
    MAX-ACCESS not-accessible
    STATUS     current
    DESCRIPTION
            "-- empty --"
    ::= { hmSetupIpRouterFirewall 4 }

-- {ROW} 1.3.6.1.4.1.248.32.18.2.8.10.4.1
hmSetupIpRouterFirewallActionsEntry OBJECT-TYPE
    SYNTAX     HmSetupIpRouterFirewallActionsEntry
    MAX-ACCESS not-accessible
    STATUS     current
    DESCRIPTION
            ""
    INDEX {
            hmSetupIpRouterFirewallActionsEntryName
          }
    ::= { hmSetupIpRouterFirewallActionsTable 1 }

HmSetupIpRouterFirewallActionsEntry ::= SEQUENCE {
            hmSetupIpRouterFirewallActionsEntryName DisplayString,
            hmSetupIpRouterFirewallActionsEntryDescription DisplayString
    }

-- {COLUMN} 1.3.6.1.4.1.248.32.18.2.8.10.4.1.1
hmSetupIpRouterFirewallActionsEntryName OBJECT-TYPE
    SYNTAX     DisplayString (SIZE(0..32))
    MAX-ACCESS read-write
    STATUS     current
    DESCRIPTION
            "-- empty --"
    ::= { hmSetupIpRouterFirewallActionsEntry 1 }

-- {COLUMN} 1.3.6.1.4.1.248.32.18.2.8.10.4.1.2
hmSetupIpRouterFirewallActionsEntryDescription OBJECT-TYPE
    SYNTAX     DisplayString (SIZE(0..64))
    MAX-ACCESS read-write
    STATUS     current
    DESCRIPTION
            "-- empty --"
    ::= { hmSetupIpRouterFirewallActionsEntry 2 }

-- {TABLE} 1.3.6.1.4.1.248.32.18.2.8.10.5
hmSetupIpRouterFirewallConnectionListTable OBJECT-TYPE
    SYNTAX     SEQUENCE OF HmSetupIpRouterFirewallConnectionListEntry
    MAX-ACCESS not-accessible
    STATUS     current
    DESCRIPTION
            "-- empty --"
    ::= { hmSetupIpRouterFirewall 5 }

-- {ROW} 1.3.6.1.4.1.248.32.18.2.8.10.5.1
hmSetupIpRouterFirewallConnectionListEntry OBJECT-TYPE
    SYNTAX     HmSetupIpRouterFirewallConnectionListEntry
    MAX-ACCESS not-accessible
    STATUS     current
    DESCRIPTION
            ""
    INDEX {
            hmSetupIpRouterFirewallConnectionListEntrySrcAddress,
            hmSetupIpRouterFirewallConnectionListEntryDstAddress,
            hmSetupIpRouterFirewallConnectionListEntryProt,
            hmSetupIpRouterFirewallConnectionListEntrySrcPort,
            hmSetupIpRouterFirewallConnectionListEntryDstPort
          }
    ::= { hmSetupIpRouterFirewallConnectionListTable 1 }

HmSetupIpRouterFirewallConnectionListEntry ::= SEQUENCE {
            hmSetupIpRouterFirewallConnectionListEntrySrcAddress IpAddress,
            hmSetupIpRouterFirewallConnectionListEntryDstAddress IpAddress,
            hmSetupIpRouterFirewallConnectionListEntryProt Integer32,
            hmSetupIpRouterFirewallConnectionListEntrySrcPort Integer32,
            hmSetupIpRouterFirewallConnectionListEntryDstPort Integer32,
            hmSetupIpRouterFirewallConnectionListEntryTimeout Integer32,
            hmSetupIpRouterFirewallConnectionListEntryFlags Integer32,
            hmSetupIpRouterFirewallConnectionListEntryFilterRule DisplayString,
            hmSetupIpRouterFirewallConnectionListEntrySrcRoute DisplayString,
            hmSetupIpRouterFirewallConnectionListEntryDestRoute DisplayString,
            hmSetupIpRouterFirewallConnectionListEntryRtgTag Integer32
    }

-- {COLUMN} 1.3.6.1.4.1.248.32.18.2.8.10.5.1.1
hmSetupIpRouterFirewallConnectionListEntrySrcAddress OBJECT-TYPE
    SYNTAX     IpAddress
    MAX-ACCESS read-only
    STATUS     current
    DESCRIPTION
            "-- empty --"
    ::= { hmSetupIpRouterFirewallConnectionListEntry 1 }

-- {COLUMN} 1.3.6.1.4.1.248.32.18.2.8.10.5.1.2
hmSetupIpRouterFirewallConnectionListEntryDstAddress OBJECT-TYPE
    SYNTAX     IpAddress
    MAX-ACCESS read-only
    STATUS     current
    DESCRIPTION
            "-- empty --"
    ::= { hmSetupIpRouterFirewallConnectionListEntry 2 }

-- {COLUMN} 1.3.6.1.4.1.248.32.18.2.8.10.5.1.3
hmSetupIpRouterFirewallConnectionListEntryProt OBJECT-TYPE
    SYNTAX     Integer32 (0..255)
    MAX-ACCESS read-only
    STATUS     current
    DESCRIPTION
            "-- empty --"
    ::= { hmSetupIpRouterFirewallConnectionListEntry 3 }

-- {COLUMN} 1.3.6.1.4.1.248.32.18.2.8.10.5.1.4
hmSetupIpRouterFirewallConnectionListEntrySrcPort OBJECT-TYPE
    SYNTAX     Integer32 (0..65535)
    MAX-ACCESS read-only
    STATUS     current
    DESCRIPTION
            "-- empty --"
    ::= { hmSetupIpRouterFirewallConnectionListEntry 4 }

-- {COLUMN} 1.3.6.1.4.1.248.32.18.2.8.10.5.1.5
hmSetupIpRouterFirewallConnectionListEntryDstPort OBJECT-TYPE
    SYNTAX     Integer32 (0..65535)
    MAX-ACCESS read-only
    STATUS     current
    DESCRIPTION
            "-- empty --"
    ::= { hmSetupIpRouterFirewallConnectionListEntry 5 }

-- {COLUMN} 1.3.6.1.4.1.248.32.18.2.8.10.5.1.6
hmSetupIpRouterFirewallConnectionListEntryTimeout OBJECT-TYPE
    SYNTAX     Integer32 (0..65535)
    MAX-ACCESS read-only
    STATUS     current
    DESCRIPTION
            "-- empty --"
    ::= { hmSetupIpRouterFirewallConnectionListEntry 6 }

-- {COLUMN} 1.3.6.1.4.1.248.32.18.2.8.10.5.1.7
hmSetupIpRouterFirewallConnectionListEntryFlags OBJECT-TYPE
    SYNTAX     Integer32 (0..2147483647)
    MAX-ACCESS read-only
    STATUS     current
    DESCRIPTION
            "-- empty --"
    ::= { hmSetupIpRouterFirewallConnectionListEntry 7 }

-- {COLUMN} 1.3.6.1.4.1.248.32.18.2.8.10.5.1.8
hmSetupIpRouterFirewallConnectionListEntryFilterRule OBJECT-TYPE
    SYNTAX     DisplayString (SIZE(0..255))
    MAX-ACCESS read-only
    STATUS     current
    DESCRIPTION
            "-- empty --"
    ::= { hmSetupIpRouterFirewallConnectionListEntry 8 }

-- {COLUMN} 1.3.6.1.4.1.248.32.18.2.8.10.5.1.9
hmSetupIpRouterFirewallConnectionListEntrySrcRoute OBJECT-TYPE
    SYNTAX     DisplayString (SIZE(0..255))
    MAX-ACCESS read-only
    STATUS     current
    DESCRIPTION
            "-- empty --"
    ::= { hmSetupIpRouterFirewallConnectionListEntry 9 }

-- {COLUMN} 1.3.6.1.4.1.248.32.18.2.8.10.5.1.10
hmSetupIpRouterFirewallConnectionListEntryDestRoute OBJECT-TYPE
    SYNTAX     DisplayString (SIZE(0..255))
    MAX-ACCESS read-only
    STATUS     current
    DESCRIPTION
            "-- empty --"
    ::= { hmSetupIpRouterFirewallConnectionListEntry 10 }

-- {COLUMN} 1.3.6.1.4.1.248.32.18.2.8.10.5.1.11
hmSetupIpRouterFirewallConnectionListEntryRtgTag OBJECT-TYPE
    SYNTAX     Integer32 (0..65535)
    MAX-ACCESS read-only
    STATUS     current
    DESCRIPTION
            "-- empty --"
    ::= { hmSetupIpRouterFirewallConnectionListEntry 11 }

-- {TABLE} 1.3.6.1.4.1.248.32.18.2.8.10.6
hmSetupIpRouterFirewallHostBlockListTable OBJECT-TYPE
    SYNTAX     SEQUENCE OF HmSetupIpRouterFirewallHostBlockListEntry
    MAX-ACCESS not-accessible
    STATUS     current
    DESCRIPTION
            "-- empty --"
    ::= { hmSetupIpRouterFirewall 6 }

-- {ROW} 1.3.6.1.4.1.248.32.18.2.8.10.6.1
hmSetupIpRouterFirewallHostBlockListEntry OBJECT-TYPE
    SYNTAX     HmSetupIpRouterFirewallHostBlockListEntry
    MAX-ACCESS not-accessible
    STATUS     current
    DESCRIPTION
            ""
    INDEX {
            hmSetupIpRouterFirewallHostBlockListEntrySrcAddress
          }
    ::= { hmSetupIpRouterFirewallHostBlockListTable 1 }

HmSetupIpRouterFirewallHostBlockListEntry ::= SEQUENCE {
            hmSetupIpRouterFirewallHostBlockListEntrySrcAddress IpAddress,
            hmSetupIpRouterFirewallHostBlockListEntryTimeout Integer32,
            hmSetupIpRouterFirewallHostBlockListEntryFilterRule DisplayString
    }

-- {COLUMN} 1.3.6.1.4.1.248.32.18.2.8.10.6.1.1
hmSetupIpRouterFirewallHostBlockListEntrySrcAddress OBJECT-TYPE
    SYNTAX     IpAddress
    MAX-ACCESS read-only
    STATUS     current
    DESCRIPTION
            "-- empty --"
    ::= { hmSetupIpRouterFirewallHostBlockListEntry 1 }

-- {COLUMN} 1.3.6.1.4.1.248.32.18.2.8.10.6.1.2
hmSetupIpRouterFirewallHostBlockListEntryTimeout OBJECT-TYPE
    SYNTAX     Integer32 (0..2147483647)
    MAX-ACCESS read-only
    STATUS     current
    DESCRIPTION
            "-- empty --"
    ::= { hmSetupIpRouterFirewallHostBlockListEntry 2 }

-- {COLUMN} 1.3.6.1.4.1.248.32.18.2.8.10.6.1.3
hmSetupIpRouterFirewallHostBlockListEntryFilterRule OBJECT-TYPE
    SYNTAX     DisplayString (SIZE(0..255))
    MAX-ACCESS read-only
    STATUS     current
    DESCRIPTION
            "-- empty --"
    ::= { hmSetupIpRouterFirewallHostBlockListEntry 3 }

-- {TABLE} 1.3.6.1.4.1.248.32.18.2.8.10.7
hmSetupIpRouterFirewallPortBlockListTable OBJECT-TYPE
    SYNTAX     SEQUENCE OF HmSetupIpRouterFirewallPortBlockListEntry
    MAX-ACCESS not-accessible
    STATUS     current
    DESCRIPTION
            "-- empty --"
    ::= { hmSetupIpRouterFirewall 7 }

-- {ROW} 1.3.6.1.4.1.248.32.18.2.8.10.7.1
hmSetupIpRouterFirewallPortBlockListEntry OBJECT-TYPE
    SYNTAX     HmSetupIpRouterFirewallPortBlockListEntry
    MAX-ACCESS not-accessible
    STATUS     current
    DESCRIPTION
            ""
    INDEX {
            hmSetupIpRouterFirewallPortBlockListEntryDstAddress
          }
    ::= { hmSetupIpRouterFirewallPortBlockListTable 1 }

HmSetupIpRouterFirewallPortBlockListEntry ::= SEQUENCE {
            hmSetupIpRouterFirewallPortBlockListEntryDstAddress IpAddress,
            hmSetupIpRouterFirewallPortBlockListEntryProt Integer32,
            hmSetupIpRouterFirewallPortBlockListEntryDstPort Integer32,
            hmSetupIpRouterFirewallPortBlockListEntryTimeout Integer32,
            hmSetupIpRouterFirewallPortBlockListEntryFilterRule DisplayString
    }

-- {COLUMN} 1.3.6.1.4.1.248.32.18.2.8.10.7.1.1
hmSetupIpRouterFirewallPortBlockListEntryDstAddress OBJECT-TYPE
    SYNTAX     IpAddress
    MAX-ACCESS read-only
    STATUS     current
    DESCRIPTION
            "-- empty --"
    ::= { hmSetupIpRouterFirewallPortBlockListEntry 1 }

-- {COLUMN} 1.3.6.1.4.1.248.32.18.2.8.10.7.1.2
hmSetupIpRouterFirewallPortBlockListEntryProt OBJECT-TYPE
    SYNTAX     Integer32 (0..65535)
    MAX-ACCESS read-only
    STATUS     current
    DESCRIPTION
            "-- empty --"
    ::= { hmSetupIpRouterFirewallPortBlockListEntry 2 }

-- {COLUMN} 1.3.6.1.4.1.248.32.18.2.8.10.7.1.3
hmSetupIpRouterFirewallPortBlockListEntryDstPort OBJECT-TYPE
    SYNTAX     Integer32 (0..65535)
    MAX-ACCESS read-only
    STATUS     current
    DESCRIPTION
            "-- empty --"
    ::= { hmSetupIpRouterFirewallPortBlockListEntry 3 }

-- {COLUMN} 1.3.6.1.4.1.248.32.18.2.8.10.7.1.4
hmSetupIpRouterFirewallPortBlockListEntryTimeout OBJECT-TYPE
    SYNTAX     Integer32 (0..2147483647)
    MAX-ACCESS read-only
    STATUS     current
    DESCRIPTION
            "-- empty --"
    ::= { hmSetupIpRouterFirewallPortBlockListEntry 4 }

-- {COLUMN} 1.3.6.1.4.1.248.32.18.2.8.10.7.1.5
hmSetupIpRouterFirewallPortBlockListEntryFilterRule OBJECT-TYPE
    SYNTAX     DisplayString (SIZE(0..255))
    MAX-ACCESS read-only
    STATUS     current
    DESCRIPTION
            "-- empty --"
    ::= { hmSetupIpRouterFirewallPortBlockListEntry 5 }

-- {SCALAR} 1.3.6.1.4.1.248.32.18.2.8.10.8
hmSetupIpRouterFirewallMaxHalfOpenConns OBJECT-TYPE
    SYNTAX     Integer32 (0..2147483647)
    MAX-ACCESS read-write
    STATUS     current
    DESCRIPTION
            "-- empty --"
    ::= { hmSetupIpRouterFirewall 8 }

-- {SCALAR} 1.3.6.1.4.1.248.32.18.2.8.10.9
hmSetupIpRouterFirewallDosAction OBJECT-TYPE
    SYNTAX     DisplayString (SIZE(0..29))
    MAX-ACCESS read-write
    STATUS     current
    DESCRIPTION
            "-- empty --"
    ::= { hmSetupIpRouterFirewall 9 }

-- {SCALAR} 1.3.6.1.4.1.248.32.18.2.8.10.10
hmSetupIpRouterFirewallAdminEmail OBJECT-TYPE
    SYNTAX     DisplayString (SIZE(0..255))
    MAX-ACCESS read-write
    STATUS     current
    DESCRIPTION
            "-- empty --"
    ::= { hmSetupIpRouterFirewall 10 }

-- {SCALAR} 1.3.6.1.4.1.248.32.18.2.8.10.11
hmSetupIpRouterFirewallOperating OBJECT-TYPE
    SYNTAX     INTEGER {
                  eNo (0),
                  eYes (1)
            }
    MAX-ACCESS read-write
    STATUS     current
    DESCRIPTION
            "-- empty --"
    ::= { hmSetupIpRouterFirewall 11 }

-- {SCALAR} 1.3.6.1.4.1.248.32.18.2.8.10.12
hmSetupIpRouterFirewallPortScanThreshold OBJECT-TYPE
    SYNTAX     Integer32 (0..2147483647)
    MAX-ACCESS read-write
    STATUS     current
    DESCRIPTION
            "-- empty --"
    ::= { hmSetupIpRouterFirewall 12 }

-- {SCALAR} 1.3.6.1.4.1.248.32.18.2.8.10.13
hmSetupIpRouterFirewallIdsAction OBJECT-TYPE
    SYNTAX     DisplayString (SIZE(0..29))
    MAX-ACCESS read-write
    STATUS     current
    DESCRIPTION
            "-- empty --"
    ::= { hmSetupIpRouterFirewall 13 }

-- {SCALAR} 1.3.6.1.4.1.248.32.18.2.8.10.14
hmSetupIpRouterFirewallPingBlock OBJECT-TYPE
    SYNTAX     INTEGER {
                  eOff (0),
                  eAlways (1),
                  eWan (2),
                  eDefaultRoute (3)
            }
    MAX-ACCESS read-write
    STATUS     current
    DESCRIPTION
            "-- empty --"
    ::= { hmSetupIpRouterFirewall 14 }

-- {SCALAR} 1.3.6.1.4.1.248.32.18.2.8.10.15
hmSetupIpRouterFirewallStealthMode OBJECT-TYPE
    SYNTAX     INTEGER {
                  eOff (0),
                  eAlways (1),
                  eWan (2),
                  eDefaultRoute (3)
            }
    MAX-ACCESS read-write
    STATUS     current
    DESCRIPTION
            "-- empty --"
    ::= { hmSetupIpRouterFirewall 15 }

-- {SCALAR} 1.3.6.1.4.1.248.32.18.2.8.10.16
hmSetupIpRouterFirewallAuthPort OBJECT-TYPE
    SYNTAX     INTEGER {
                  eClosed (0),
                  eStealth (1)
            }
    MAX-ACCESS read-write
    STATUS     current
    DESCRIPTION
            "-- empty --"
    ::= { hmSetupIpRouterFirewall 16 }

-- {SCALAR} 1.3.6.1.4.1.248.32.18.2.8.10.17
hmSetupIpRouterFirewallDenySessionRecover OBJECT-TYPE
    SYNTAX     INTEGER {
                  eOff (0),
                  eAlways (1),
                  eWan (2),
                  eDefaultRoute (3)
            }
    MAX-ACCESS read-write
    STATUS     current
    DESCRIPTION
            "-- empty --"
    ::= { hmSetupIpRouterFirewall 17 }

-- {TABLE} 1.3.6.1.4.1.248.32.18.2.8.10.19
hmSetupIpRouterFirewallOpenPortListTable OBJECT-TYPE
    SYNTAX     SEQUENCE OF HmSetupIpRouterFirewallOpenPortListEntry
    MAX-ACCESS not-accessible
    STATUS     current
    DESCRIPTION
            "-- empty --"
    ::= { hmSetupIpRouterFirewall 19 }

-- {ROW} 1.3.6.1.4.1.248.32.18.2.8.10.19.1
hmSetupIpRouterFirewallOpenPortListEntry OBJECT-TYPE
    SYNTAX     HmSetupIpRouterFirewallOpenPortListEntry
    MAX-ACCESS not-accessible
    STATUS     current
    DESCRIPTION
            ""
    INDEX {
            hmSetupIpRouterFirewallOpenPortListEntrySrcAddress,
            hmSetupIpRouterFirewallOpenPortListEntryDstAddress,
            hmSetupIpRouterFirewallOpenPortListEntryProt,
            hmSetupIpRouterFirewallOpenPortListEntryDstPort
          }
    ::= { hmSetupIpRouterFirewallOpenPortListTable 1 }

HmSetupIpRouterFirewallOpenPortListEntry ::= SEQUENCE {
            hmSetupIpRouterFirewallOpenPortListEntrySrcAddress IpAddress,
            hmSetupIpRouterFirewallOpenPortListEntryDstAddress IpAddress,
            hmSetupIpRouterFirewallOpenPortListEntryProt Integer32,
            hmSetupIpRouterFirewallOpenPortListEntryDstPort Integer32,
            hmSetupIpRouterFirewallOpenPortListEntryTimeout Integer32,
            hmSetupIpRouterFirewallOpenPortListEntryFilterRule DisplayString,
            hmSetupIpRouterFirewallOpenPortListEntrySrcRoute DisplayString
    }

-- {COLUMN} 1.3.6.1.4.1.248.32.18.2.8.10.19.1.1
hmSetupIpRouterFirewallOpenPortListEntrySrcAddress OBJECT-TYPE
    SYNTAX     IpAddress
    MAX-ACCESS read-only
    STATUS     current
    DESCRIPTION
            "-- empty --"
    ::= { hmSetupIpRouterFirewallOpenPortListEntry 1 }

-- {COLUMN} 1.3.6.1.4.1.248.32.18.2.8.10.19.1.2
hmSetupIpRouterFirewallOpenPortListEntryDstAddress OBJECT-TYPE
    SYNTAX     IpAddress
    MAX-ACCESS read-only
    STATUS     current
    DESCRIPTION
            "-- empty --"
    ::= { hmSetupIpRouterFirewallOpenPortListEntry 2 }

-- {COLUMN} 1.3.6.1.4.1.248.32.18.2.8.10.19.1.3
hmSetupIpRouterFirewallOpenPortListEntryProt OBJECT-TYPE
    SYNTAX     Integer32 (0..255)
    MAX-ACCESS read-only
    STATUS     current
    DESCRIPTION
            "-- empty --"
    ::= { hmSetupIpRouterFirewallOpenPortListEntry 3 }

-- {COLUMN} 1.3.6.1.4.1.248.32.18.2.8.10.19.1.5
hmSetupIpRouterFirewallOpenPortListEntryDstPort OBJECT-TYPE
    SYNTAX     Integer32 (0..65535)
    MAX-ACCESS read-only
    STATUS     current
    DESCRIPTION
            "-- empty --"
    ::= { hmSetupIpRouterFirewallOpenPortListEntry 5 }

-- {COLUMN} 1.3.6.1.4.1.248.32.18.2.8.10.19.1.6
hmSetupIpRouterFirewallOpenPortListEntryTimeout OBJECT-TYPE
    SYNTAX     Integer32 (0..65535)
    MAX-ACCESS read-only
    STATUS     current
    DESCRIPTION
            "-- empty --"
    ::= { hmSetupIpRouterFirewallOpenPortListEntry 6 }

-- {COLUMN} 1.3.6.1.4.1.248.32.18.2.8.10.19.1.8
hmSetupIpRouterFirewallOpenPortListEntryFilterRule OBJECT-TYPE
    SYNTAX     DisplayString (SIZE(0..255))
    MAX-ACCESS read-only
    STATUS     current
    DESCRIPTION
            "-- empty --"
    ::= { hmSetupIpRouterFirewallOpenPortListEntry 8 }

-- {COLUMN} 1.3.6.1.4.1.248.32.18.2.8.10.19.1.9
hmSetupIpRouterFirewallOpenPortListEntrySrcRoute OBJECT-TYPE
    SYNTAX     DisplayString (SIZE(0..255))
    MAX-ACCESS read-only
    STATUS     current
    DESCRIPTION
            "-- empty --"
    ::= { hmSetupIpRouterFirewallOpenPortListEntry 9 }

-- {NODE} 1.3.6.1.4.1.248.32.18.2.8.10.20
hmSetupIpRouterFirewallApplications OBJECT IDENTIFIER ::= { hmSetupIpRouterFirewall 20 }

-- {NODE} 1.3.6.1.4.1.248.32.18.2.8.10.20.1
hmSetupIpRouterFirewallApplicationsFtp OBJECT IDENTIFIER ::= { hmSetupIpRouterFirewallApplications 1 }

-- {SCALAR} 1.3.6.1.4.1.248.32.18.2.8.10.20.1.1
hmSetupIpRouterFirewallApplicationsFtpFtpBlock OBJECT-TYPE
    SYNTAX     INTEGER {
                  eOff (0),
                  eAlways (1),
                  eWan (2),
                  eDefaultRoute (3)
            }
    MAX-ACCESS read-write
    STATUS     current
    DESCRIPTION
            "-- empty --"
    ::= { hmSetupIpRouterFirewallApplicationsFtp 1 }

-- {SCALAR} 1.3.6.1.4.1.248.32.18.2.8.10.20.1.2
hmSetupIpRouterFirewallApplicationsFtpActiveFtpBlock OBJECT-TYPE
    SYNTAX     INTEGER {
                  eOff (0),
                  eAlways (1),
                  eWan (2),
                  eDefaultRoute (3)
            }
    MAX-ACCESS read-write
    STATUS     current
    DESCRIPTION
            "-- empty --"
    ::= { hmSetupIpRouterFirewallApplicationsFtp 2 }

-- {SCALAR} 1.3.6.1.4.1.248.32.18.2.8.10.20.1.3
hmSetupIpRouterFirewallApplicationsFtpMinPort OBJECT-TYPE
    SYNTAX     Integer32 (0..65535)
    MAX-ACCESS read-write
    STATUS     current
    DESCRIPTION
            "-- empty --"
    ::= { hmSetupIpRouterFirewallApplicationsFtp 3 }

-- {SCALAR} 1.3.6.1.4.1.248.32.18.2.8.10.20.1.4
hmSetupIpRouterFirewallApplicationsFtpCheckHostIp OBJECT-TYPE
    SYNTAX     INTEGER {
                  eOff (0),
                  eAlways (1),
                  eWan (2),
                  eDefaultRoute (3)
            }
    MAX-ACCESS read-write
    STATUS     current
    DESCRIPTION
            "-- empty --"
    ::= { hmSetupIpRouterFirewallApplicationsFtp 4 }

-- {SCALAR} 1.3.6.1.4.1.248.32.18.2.8.10.20.1.5
hmSetupIpRouterFirewallApplicationsFtpFxpBlock OBJECT-TYPE
    SYNTAX     INTEGER {
                  eOff (0),
                  eAlways (1),
                  eWan (2),
                  eDefaultRoute (3)
            }
    MAX-ACCESS read-write
    STATUS     current
    DESCRIPTION
            "-- empty --"
    ::= { hmSetupIpRouterFirewallApplicationsFtp 5 }

-- {NODE} 1.3.6.1.4.1.248.32.18.2.8.10.20.2
hmSetupIpRouterFirewallApplicationsIrc OBJECT IDENTIFIER ::= { hmSetupIpRouterFirewallApplications 2 }

-- {SCALAR} 1.3.6.1.4.1.248.32.18.2.8.10.20.2.1
hmSetupIpRouterFirewallApplicationsIrcIrcBlock OBJECT-TYPE
    SYNTAX     INTEGER {
                  eOff (0),
                  eAlways (1),
                  eWan (2),
                  eDefaultRoute (3)
            }
    MAX-ACCESS read-write
    STATUS     current
    DESCRIPTION
            "-- empty --"
    ::= { hmSetupIpRouterFirewallApplicationsIrc 1 }

-- {SCALAR} 1.3.6.1.4.1.248.32.18.2.8.10.20.2.2
hmSetupIpRouterFirewallApplicationsIrcDdcBlock OBJECT-TYPE
    SYNTAX     INTEGER {
                  eOff (0),
                  eAlways (1),
                  eWan (2),
                  eDefaultRoute (3)
            }
    MAX-ACCESS read-write
    STATUS     current
    DESCRIPTION
            "-- empty --"
    ::= { hmSetupIpRouterFirewallApplicationsIrc 2 }

-- {SCALAR} 1.3.6.1.4.1.248.32.18.2.8.10.20.2.3
hmSetupIpRouterFirewallApplicationsIrcMinPort OBJECT-TYPE
    SYNTAX     Integer32 (0..65535)
    MAX-ACCESS read-write
    STATUS     current
    DESCRIPTION
            "-- empty --"
    ::= { hmSetupIpRouterFirewallApplicationsIrc 3 }

-- {SCALAR} 1.3.6.1.4.1.248.32.18.2.8.10.20.2.4
hmSetupIpRouterFirewallApplicationsIrcCheckHostIp OBJECT-TYPE
    SYNTAX     INTEGER {
                  eOff (0),
                  eAlways (1),
                  eWan (2),
                  eDefaultRoute (3)
            }
    MAX-ACCESS read-write
    STATUS     current
    DESCRIPTION
            "-- empty --"
    ::= { hmSetupIpRouterFirewallApplicationsIrc 4 }

-- {SCALAR} 1.3.6.1.4.1.248.32.18.2.8.10.20.10
hmSetupIpRouterFirewallApplicationsApplAction OBJECT-TYPE
    SYNTAX     DisplayString (SIZE(0..29))
    MAX-ACCESS read-write
    STATUS     current
    DESCRIPTION
            "-- empty --"
    ::= { hmSetupIpRouterFirewallApplications 10 }

-- {SCALAR} 1.3.6.1.4.1.248.32.18.2.8.11
hmSetupIpRouterStartWanPool OBJECT-TYPE
    SYNTAX     IpAddress
    MAX-ACCESS read-write
    STATUS     current
    DESCRIPTION
            "-- empty --"
    ::= { hmSetupIpRouter 11 }

-- {SCALAR} 1.3.6.1.4.1.248.32.18.2.8.12
hmSetupIpRouterEndWanPool OBJECT-TYPE
    SYNTAX     IpAddress
    MAX-ACCESS read-write
    STATUS     current
    DESCRIPTION
            "-- empty --"
    ::= { hmSetupIpRouter 12 }

-- {TABLE} 1.3.6.1.4.1.248.32.18.2.8.13
hmSetupIpRouterDefaultTimeListTable OBJECT-TYPE
    SYNTAX     SEQUENCE OF HmSetupIpRouterDefaultTimeListEntry
    MAX-ACCESS not-accessible
    STATUS     current
    DESCRIPTION
            "-- empty --"
    ::= { hmSetupIpRouter 13 }

-- {ROW} 1.3.6.1.4.1.248.32.18.2.8.13.1
hmSetupIpRouterDefaultTimeListEntry OBJECT-TYPE
    SYNTAX     HmSetupIpRouterDefaultTimeListEntry
    MAX-ACCESS not-accessible
    STATUS     current
    DESCRIPTION
            ""
    INDEX {
            hmSetupIpRouterDefaultTimeListEntryIndex
          }
    ::= { hmSetupIpRouterDefaultTimeListTable 1 }

HmSetupIpRouterDefaultTimeListEntry ::= SEQUENCE {
            hmSetupIpRouterDefaultTimeListEntryIndex Integer32,
            hmSetupIpRouterDefaultTimeListEntryDays BITS,
            hmSetupIpRouterDefaultTimeListEntryStart DisplayString,
            hmSetupIpRouterDefaultTimeListEntryStop DisplayString,
            hmSetupIpRouterDefaultTimeListEntryPeer DisplayString
    }

-- {COLUMN} 1.3.6.1.4.1.248.32.18.2.8.13.1.1
hmSetupIpRouterDefaultTimeListEntryIndex OBJECT-TYPE
    SYNTAX     Integer32 (0..65535)
    MAX-ACCESS read-write
    STATUS     current
    DESCRIPTION
            "-- empty --"
    ::= { hmSetupIpRouterDefaultTimeListEntry 1 }

-- {COLUMN} 1.3.6.1.4.1.248.32.18.2.8.13.1.2
hmSetupIpRouterDefaultTimeListEntryDays OBJECT-TYPE
    SYNTAX     BITS {
                  eHoliday (0),
                  eSunday (1),
                  eSaturday (2),
                  eFriday (3),
                  eThursday (4),
                  eWednesday (5),
                  eTuesday (6),
                  eMonday (7)
            }
    MAX-ACCESS read-write
    STATUS     current
    DESCRIPTION
            "-- empty --"
    ::= { hmSetupIpRouterDefaultTimeListEntry 2 }

-- {COLUMN} 1.3.6.1.4.1.248.32.18.2.8.13.1.3
hmSetupIpRouterDefaultTimeListEntryStart OBJECT-TYPE
    SYNTAX     DisplayString (SIZE(0..5))
    MAX-ACCESS read-write
    STATUS     current
    DESCRIPTION
            "-- empty --"
    ::= { hmSetupIpRouterDefaultTimeListEntry 3 }

-- {COLUMN} 1.3.6.1.4.1.248.32.18.2.8.13.1.4
hmSetupIpRouterDefaultTimeListEntryStop OBJECT-TYPE
    SYNTAX     DisplayString (SIZE(0..5))
    MAX-ACCESS read-write
    STATUS     current
    DESCRIPTION
            "-- empty --"
    ::= { hmSetupIpRouterDefaultTimeListEntry 4 }

-- {COLUMN} 1.3.6.1.4.1.248.32.18.2.8.13.1.5
hmSetupIpRouterDefaultTimeListEntryPeer OBJECT-TYPE
    SYNTAX     DisplayString (SIZE(0..16))
    MAX-ACCESS read-write
    STATUS     current
    DESCRIPTION
            "-- empty --"
    ::= { hmSetupIpRouterDefaultTimeListEntry 5 }

-- {SCALAR} 1.3.6.1.4.1.248.32.18.2.8.14
hmSetupIpRouterUsageDefaultTimetable OBJECT-TYPE
    SYNTAX     INTEGER {
                  eNo (0),
                  eYes (1)
            }
    MAX-ACCESS read-write
    STATUS     current
    DESCRIPTION
            "-- empty --"
    ::= { hmSetupIpRouter 14 }

-- {TABLE} 1.3.6.1.4.1.248.32.18.2.8.19
hmSetupIpRouterNNNatTable OBJECT-TYPE
    SYNTAX     SEQUENCE OF HmSetupIpRouterNNNatEntry
    MAX-ACCESS not-accessible
    STATUS     current
    DESCRIPTION
            "-- empty --"
    ::= { hmSetupIpRouter 19 }

-- {ROW} 1.3.6.1.4.1.248.32.18.2.8.19.1
hmSetupIpRouterNNNatEntry OBJECT-TYPE
    SYNTAX     HmSetupIpRouterNNNatEntry
    MAX-ACCESS not-accessible
    STATUS     current
    DESCRIPTION
            ""
    INDEX {
            hmSetupIpRouterNNNatEntryIdx
          }
    ::= { hmSetupIpRouterNNNatTable 1 }

HmSetupIpRouterNNNatEntry ::= SEQUENCE {
            hmSetupIpRouterNNNatEntryIdx DisplayString,
            hmSetupIpRouterNNNatEntrySrcAddress IpAddress,
            hmSetupIpRouterNNNatEntrySrcMask IpAddress,
            hmSetupIpRouterNNNatEntryDstStation DisplayString,
            hmSetupIpRouterNNNatEntryMappedNetwork IpAddress
    }

-- {COLUMN} 1.3.6.1.4.1.248.32.18.2.8.19.1.1
hmSetupIpRouterNNNatEntryIdx OBJECT-TYPE
    SYNTAX     DisplayString (SIZE(0..4))
    MAX-ACCESS read-write
    STATUS     current
    DESCRIPTION
            "-- empty --"
    ::= { hmSetupIpRouterNNNatEntry 1 }

-- {COLUMN} 1.3.6.1.4.1.248.32.18.2.8.19.1.2
hmSetupIpRouterNNNatEntrySrcAddress OBJECT-TYPE
    SYNTAX     IpAddress
    MAX-ACCESS read-write
    STATUS     current
    DESCRIPTION
            "-- empty --"
    ::= { hmSetupIpRouterNNNatEntry 2 }

-- {COLUMN} 1.3.6.1.4.1.248.32.18.2.8.19.1.3
hmSetupIpRouterNNNatEntrySrcMask OBJECT-TYPE
    SYNTAX     IpAddress
    MAX-ACCESS read-write
    STATUS     current
    DESCRIPTION
            "-- empty --"
    ::= { hmSetupIpRouterNNNatEntry 3 }

-- {COLUMN} 1.3.6.1.4.1.248.32.18.2.8.19.1.4
hmSetupIpRouterNNNatEntryDstStation OBJECT-TYPE
    SYNTAX     DisplayString (SIZE(0..16))
    MAX-ACCESS read-write
    STATUS     current
    DESCRIPTION
            "-- empty --"
    ::= { hmSetupIpRouterNNNatEntry 4 }

-- {COLUMN} 1.3.6.1.4.1.248.32.18.2.8.19.1.5
hmSetupIpRouterNNNatEntryMappedNetwork OBJECT-TYPE
    SYNTAX     IpAddress
    MAX-ACCESS read-write
    STATUS     current
    DESCRIPTION
            "-- empty --"
    ::= { hmSetupIpRouterNNNatEntry 5 }

-- {NODE} 1.3.6.1.4.1.248.32.18.2.8.20
hmSetupIpRouterLoadBalancer OBJECT IDENTIFIER ::= { hmSetupIpRouter 20 }

-- {SCALAR} 1.3.6.1.4.1.248.32.18.2.8.20.1
hmSetupIpRouterLoadBalancerOperating OBJECT-TYPE
    SYNTAX     INTEGER {
                  eNo (0),
                  eYes (1)
            }
    MAX-ACCESS read-write
    STATUS     current
    DESCRIPTION
            "-- empty --"
    ::= { hmSetupIpRouterLoadBalancer 1 }

-- {TABLE} 1.3.6.1.4.1.248.32.18.2.8.20.2
hmSetupIpRouterLoadBalancerBundlePeersTable OBJECT-TYPE
    SYNTAX     SEQUENCE OF HmSetupIpRouterLoadBalancerBundlePeersEntry
    MAX-ACCESS not-accessible
    STATUS     current
    DESCRIPTION
            "-- empty --"
    ::= { hmSetupIpRouterLoadBalancer 2 }

-- {ROW} 1.3.6.1.4.1.248.32.18.2.8.20.2.1
hmSetupIpRouterLoadBalancerBundlePeersEntry OBJECT-TYPE
    SYNTAX     HmSetupIpRouterLoadBalancerBundlePeersEntry
    MAX-ACCESS not-accessible
    STATUS     current
    DESCRIPTION
            ""
    INDEX {
            hmSetupIpRouterLoadBalancerBundlePeersEntryPeer
          }
    ::= { hmSetupIpRouterLoadBalancerBundlePeersTable 1 }

HmSetupIpRouterLoadBalancerBundlePeersEntry ::= SEQUENCE {
            hmSetupIpRouterLoadBalancerBundlePeersEntryPeer DisplayString,
            hmSetupIpRouterLoadBalancerBundlePeersEntryBundlePeer1 DisplayString,
            hmSetupIpRouterLoadBalancerBundlePeersEntryBundlePeer2 DisplayString,
            hmSetupIpRouterLoadBalancerBundlePeersEntryBundlePeer3 DisplayString,
            hmSetupIpRouterLoadBalancerBundlePeersEntryBundlePeer4 DisplayString,
            hmSetupIpRouterLoadBalancerBundlePeersEntryClientBinding INTEGER
    }

-- {COLUMN} 1.3.6.1.4.1.248.32.18.2.8.20.2.1.1
hmSetupIpRouterLoadBalancerBundlePeersEntryPeer OBJECT-TYPE
    SYNTAX     DisplayString (SIZE(0..16))
    MAX-ACCESS read-write
    STATUS     current
    DESCRIPTION
            "-- empty --"
    ::= { hmSetupIpRouterLoadBalancerBundlePeersEntry 1 }

-- {COLUMN} 1.3.6.1.4.1.248.32.18.2.8.20.2.1.2
hmSetupIpRouterLoadBalancerBundlePeersEntryBundlePeer1 OBJECT-TYPE
    SYNTAX     DisplayString (SIZE(0..16))
    MAX-ACCESS read-write
    STATUS     current
    DESCRIPTION
            "-- empty --"
    ::= { hmSetupIpRouterLoadBalancerBundlePeersEntry 2 }

-- {COLUMN} 1.3.6.1.4.1.248.32.18.2.8.20.2.1.3
hmSetupIpRouterLoadBalancerBundlePeersEntryBundlePeer2 OBJECT-TYPE
    SYNTAX     DisplayString (SIZE(0..16))
    MAX-ACCESS read-write
    STATUS     current
    DESCRIPTION
            "-- empty --"
    ::= { hmSetupIpRouterLoadBalancerBundlePeersEntry 3 }

-- {COLUMN} 1.3.6.1.4.1.248.32.18.2.8.20.2.1.4
hmSetupIpRouterLoadBalancerBundlePeersEntryBundlePeer3 OBJECT-TYPE
    SYNTAX     DisplayString (SIZE(0..16))
    MAX-ACCESS read-write
    STATUS     current
    DESCRIPTION
            "-- empty --"
    ::= { hmSetupIpRouterLoadBalancerBundlePeersEntry 4 }

-- {COLUMN} 1.3.6.1.4.1.248.32.18.2.8.20.2.1.5
hmSetupIpRouterLoadBalancerBundlePeersEntryBundlePeer4 OBJECT-TYPE
    SYNTAX     DisplayString (SIZE(0..16))
    MAX-ACCESS read-write
    STATUS     current
    DESCRIPTION
            "-- empty --"
    ::= { hmSetupIpRouterLoadBalancerBundlePeersEntry 5 }

-- {COLUMN} 1.3.6.1.4.1.248.32.18.2.8.20.2.1.10
hmSetupIpRouterLoadBalancerBundlePeersEntryClientBinding OBJECT-TYPE
    SYNTAX     INTEGER {
                  eNo (0),
                  eYes (1)
            }
    MAX-ACCESS read-write
    STATUS     current
    DESCRIPTION
            "-- empty --"
    ::= { hmSetupIpRouterLoadBalancerBundlePeersEntry 10 }

-- {NODE} 1.3.6.1.4.1.248.32.18.2.8.20.3
hmSetupIpRouterLoadBalancerClientBinding OBJECT IDENTIFIER ::= { hmSetupIpRouterLoadBalancer 3 }

-- {TABLE} 1.3.6.1.4.1.248.32.18.2.8.20.3.1
hmSetupIpRouterLoadBalancerClientBindingProtocolsTable OBJECT-TYPE
    SYNTAX     SEQUENCE OF HmSetupIpRouterLoadBalancerClientBindingProtocolsEntry
    MAX-ACCESS not-accessible
    STATUS     current
    DESCRIPTION
            "-- empty --"
    ::= { hmSetupIpRouterLoadBalancerClientBinding 1 }

-- {ROW} 1.3.6.1.4.1.248.32.18.2.8.20.3.1.1
hmSetupIpRouterLoadBalancerClientBindingProtocolsEntry OBJECT-TYPE
    SYNTAX     HmSetupIpRouterLoadBalancerClientBindingProtocolsEntry
    MAX-ACCESS not-accessible
    STATUS     current
    DESCRIPTION
            ""
    INDEX {
            hmSetupIpRouterLoadBalancerClientBindingProtocolsEntryName
          }
    ::= { hmSetupIpRouterLoadBalancerClientBindingProtocolsTable 1 }

HmSetupIpRouterLoadBalancerClientBindingProtocolsEntry ::= SEQUENCE {
            hmSetupIpRouterLoadBalancerClientBindingProtocolsEntryName DisplayString,
            hmSetupIpRouterLoadBalancerClientBindingProtocolsEntryProtocol Integer32,
            hmSetupIpRouterLoadBalancerClientBindingProtocolsEntryPort Integer32,
            hmSetupIpRouterLoadBalancerClientBindingProtocolsEntryActive INTEGER
    }

-- {COLUMN} 1.3.6.1.4.1.248.32.18.2.8.20.3.1.1.1
hmSetupIpRouterLoadBalancerClientBindingProtocolsEntryName OBJECT-TYPE
    SYNTAX     DisplayString (SIZE(0..16))
    MAX-ACCESS read-write
    STATUS     current
    DESCRIPTION
            "-- empty --"
    ::= { hmSetupIpRouterLoadBalancerClientBindingProtocolsEntry 1 }

-- {COLUMN} 1.3.6.1.4.1.248.32.18.2.8.20.3.1.1.2
hmSetupIpRouterLoadBalancerClientBindingProtocolsEntryProtocol OBJECT-TYPE
    SYNTAX     Integer32 (0..255)
    MAX-ACCESS read-write
    STATUS     current
    DESCRIPTION
            "-- empty --"
    ::= { hmSetupIpRouterLoadBalancerClientBindingProtocolsEntry 2 }

-- {COLUMN} 1.3.6.1.4.1.248.32.18.2.8.20.3.1.1.3
hmSetupIpRouterLoadBalancerClientBindingProtocolsEntryPort OBJECT-TYPE
    SYNTAX     Integer32 (0..65535)
    MAX-ACCESS read-write
    STATUS     current
    DESCRIPTION
            "-- empty --"
    ::= { hmSetupIpRouterLoadBalancerClientBindingProtocolsEntry 3 }

-- {COLUMN} 1.3.6.1.4.1.248.32.18.2.8.20.3.1.1.4
hmSetupIpRouterLoadBalancerClientBindingProtocolsEntryActive OBJECT-TYPE
    SYNTAX     INTEGER {
                  eNo (0),
                  eYes (1)
            }
    MAX-ACCESS read-write
    STATUS     current
    DESCRIPTION
            "-- empty --"
    ::= { hmSetupIpRouterLoadBalancerClientBindingProtocolsEntry 4 }

-- {SCALAR} 1.3.6.1.4.1.248.32.18.2.8.20.3.2
hmSetupIpRouterLoadBalancerClientBindingBalanceSeconds OBJECT-TYPE
    SYNTAX     Integer32 (0..2147483647)
    MAX-ACCESS read-write
    STATUS     current
    DESCRIPTION
            "-- empty --"
    ::= { hmSetupIpRouterLoadBalancerClientBinding 2 }

-- {SCALAR} 1.3.6.1.4.1.248.32.18.2.8.20.3.3
hmSetupIpRouterLoadBalancerClientBindingBindingMinutes OBJECT-TYPE
    SYNTAX     Integer32 (0..2147483647)
    MAX-ACCESS read-write
    STATUS     current
    DESCRIPTION
            "-- empty --"
    ::= { hmSetupIpRouterLoadBalancerClientBinding 3 }

-- {NODE} 1.3.6.1.4.1.248.32.18.2.8.21
hmSetupIpRouterVrrp OBJECT IDENTIFIER ::= { hmSetupIpRouter 21 }

-- {SCALAR} 1.3.6.1.4.1.248.32.18.2.8.21.1
hmSetupIpRouterVrrpOperating OBJECT-TYPE
    SYNTAX     INTEGER {
                  eNo (0),
                  eYes (1)
            }
    MAX-ACCESS read-write
    STATUS     current
    DESCRIPTION
            "-- empty --"
    ::= { hmSetupIpRouterVrrp 1 }

-- {TABLE} 1.3.6.1.4.1.248.32.18.2.8.21.2
hmSetupIpRouterVrrpVrrpListTable OBJECT-TYPE
    SYNTAX     SEQUENCE OF HmSetupIpRouterVrrpVrrpListEntry
    MAX-ACCESS not-accessible
    STATUS     current
    DESCRIPTION
            "-- empty --"
    ::= { hmSetupIpRouterVrrp 2 }

-- {ROW} 1.3.6.1.4.1.248.32.18.2.8.21.2.1
hmSetupIpRouterVrrpVrrpListEntry OBJECT-TYPE
    SYNTAX     HmSetupIpRouterVrrpVrrpListEntry
    MAX-ACCESS not-accessible
    STATUS     current
    DESCRIPTION
            ""
    INDEX {
            hmSetupIpRouterVrrpVrrpListEntryRouterId
          }
    ::= { hmSetupIpRouterVrrpVrrpListTable 1 }

HmSetupIpRouterVrrpVrrpListEntry ::= SEQUENCE {
            hmSetupIpRouterVrrpVrrpListEntryRouterId Integer32,
            hmSetupIpRouterVrrpVrrpListEntryVirtAddress IpAddress,
            hmSetupIpRouterVrrpVrrpListEntryPrio Integer32,
            hmSetupIpRouterVrrpVrrpListEntryBPrio Integer32,
            hmSetupIpRouterVrrpVrrpListEntryPeer DisplayString,
            hmSetupIpRouterVrrpVrrpListEntryComment DisplayString
    }

-- {COLUMN} 1.3.6.1.4.1.248.32.18.2.8.21.2.1.1
hmSetupIpRouterVrrpVrrpListEntryRouterId OBJECT-TYPE
    SYNTAX     Integer32 (0..255)
    MAX-ACCESS read-write
    STATUS     current
    DESCRIPTION
            "-- empty --"
    ::= { hmSetupIpRouterVrrpVrrpListEntry 1 }

-- {COLUMN} 1.3.6.1.4.1.248.32.18.2.8.21.2.1.2
hmSetupIpRouterVrrpVrrpListEntryVirtAddress OBJECT-TYPE
    SYNTAX     IpAddress
    MAX-ACCESS read-write
    STATUS     current
    DESCRIPTION
            "-- empty --"
    ::= { hmSetupIpRouterVrrpVrrpListEntry 2 }

-- {COLUMN} 1.3.6.1.4.1.248.32.18.2.8.21.2.1.3
hmSetupIpRouterVrrpVrrpListEntryPrio OBJECT-TYPE
    SYNTAX     Integer32 (0..255)
    MAX-ACCESS read-write
    STATUS     current
    DESCRIPTION
            "-- empty --"
    ::= { hmSetupIpRouterVrrpVrrpListEntry 3 }

-- {COLUMN} 1.3.6.1.4.1.248.32.18.2.8.21.2.1.4
hmSetupIpRouterVrrpVrrpListEntryBPrio OBJECT-TYPE
    SYNTAX     Integer32 (0..255)
    MAX-ACCESS read-write
    STATUS     current
    DESCRIPTION
            "-- empty --"
    ::= { hmSetupIpRouterVrrpVrrpListEntry 4 }

-- {COLUMN} 1.3.6.1.4.1.248.32.18.2.8.21.2.1.5
hmSetupIpRouterVrrpVrrpListEntryPeer OBJECT-TYPE
    SYNTAX     DisplayString (SIZE(0..16))
    MAX-ACCESS read-write
    STATUS     current
    DESCRIPTION
            "-- empty --"
    ::= { hmSetupIpRouterVrrpVrrpListEntry 5 }

-- {COLUMN} 1.3.6.1.4.1.248.32.18.2.8.21.2.1.6
hmSetupIpRouterVrrpVrrpListEntryComment OBJECT-TYPE
    SYNTAX     DisplayString (SIZE(0..64))
    MAX-ACCESS read-write
    STATUS     current
    DESCRIPTION
            "-- empty --"
    ::= { hmSetupIpRouterVrrpVrrpListEntry 6 }

-- {SCALAR} 1.3.6.1.4.1.248.32.18.2.8.21.3
hmSetupIpRouterVrrpReconnectDelay OBJECT-TYPE
    SYNTAX     Integer32 (0..65535)
    MAX-ACCESS read-write
    STATUS     current
    DESCRIPTION
            "-- empty --"
    ::= { hmSetupIpRouterVrrp 3 }

-- {SCALAR} 1.3.6.1.4.1.248.32.18.2.8.21.4
hmSetupIpRouterVrrpAdvertIntervall OBJECT-TYPE
    SYNTAX     Integer32 (0..255)
    MAX-ACCESS read-write
    STATUS     current
    DESCRIPTION
            "-- empty --"
    ::= { hmSetupIpRouterVrrp 4 }

-- {SCALAR} 1.3.6.1.4.1.248.32.18.2.8.21.5
hmSetupIpRouterVrrpInternalServices OBJECT-TYPE
    SYNTAX     INTEGER {
                  eNo (0),
                  eYes (1)
            }
    MAX-ACCESS read-write
    STATUS     current
    DESCRIPTION
            "-- empty --"
    ::= { hmSetupIpRouterVrrp 5 }

-- {SCALAR} 1.3.6.1.4.1.248.32.18.2.8.22
hmSetupIpRouterWanTagCreation OBJECT-TYPE
    SYNTAX     INTEGER {
                  eManual (0),
                  eAuto (1)
            }
    MAX-ACCESS read-write
    STATUS     current
    DESCRIPTION
            "-- empty --"
    ::= { hmSetupIpRouter 22 }

-- {TABLE} 1.3.6.1.4.1.248.32.18.2.8.23
hmSetupIpRouterTagTableTable OBJECT-TYPE
    SYNTAX     SEQUENCE OF HmSetupIpRouterTagTableEntry
    MAX-ACCESS not-accessible
    STATUS     current
    DESCRIPTION
            "-- empty --"
    ::= { hmSetupIpRouter 23 }

-- {ROW} 1.3.6.1.4.1.248.32.18.2.8.23.1
hmSetupIpRouterTagTableEntry OBJECT-TYPE
    SYNTAX     HmSetupIpRouterTagTableEntry
    MAX-ACCESS not-accessible
    STATUS     current
    DESCRIPTION
            ""
    INDEX {
            hmSetupIpRouterTagTableEntryPeer
          }
    ::= { hmSetupIpRouterTagTableTable 1 }

HmSetupIpRouterTagTableEntry ::= SEQUENCE {
            hmSetupIpRouterTagTableEntryPeer DisplayString,
            hmSetupIpRouterTagTableEntryRtgTag Integer32,
            hmSetupIpRouterTagTableEntryStartWanPool IpAddress,
            hmSetupIpRouterTagTableEntryEndWanPool IpAddress,
            hmSetupIpRouterTagTableEntryDnsDefault IpAddress,
            hmSetupIpRouterTagTableEntryDnsBackup IpAddress,
            hmSetupIpRouterTagTableEntryNbnsDefault IpAddress,
            hmSetupIpRouterTagTableEntryNbnsBackup IpAddress
    }

-- {COLUMN} 1.3.6.1.4.1.248.32.18.2.8.23.1.1
hmSetupIpRouterTagTableEntryPeer OBJECT-TYPE
    SYNTAX     DisplayString (SIZE(0..16))
    MAX-ACCESS read-write
    STATUS     current
    DESCRIPTION
            "-- empty --"
    ::= { hmSetupIpRouterTagTableEntry 1 }

-- {COLUMN} 1.3.6.1.4.1.248.32.18.2.8.23.1.2
hmSetupIpRouterTagTableEntryRtgTag OBJECT-TYPE
    SYNTAX     Integer32 (0..65535)
    MAX-ACCESS read-write
    STATUS     current
    DESCRIPTION
            "-- empty --"
    ::= { hmSetupIpRouterTagTableEntry 2 }

-- {COLUMN} 1.3.6.1.4.1.248.32.18.2.8.23.1.3
hmSetupIpRouterTagTableEntryStartWanPool OBJECT-TYPE
    SYNTAX     IpAddress
    MAX-ACCESS read-write
    STATUS     current
    DESCRIPTION
            "-- empty --"
    ::= { hmSetupIpRouterTagTableEntry 3 }

-- {COLUMN} 1.3.6.1.4.1.248.32.18.2.8.23.1.4
hmSetupIpRouterTagTableEntryEndWanPool OBJECT-TYPE
    SYNTAX     IpAddress
    MAX-ACCESS read-write
    STATUS     current
    DESCRIPTION
            "-- empty --"
    ::= { hmSetupIpRouterTagTableEntry 4 }

-- {COLUMN} 1.3.6.1.4.1.248.32.18.2.8.23.1.5
hmSetupIpRouterTagTableEntryDnsDefault OBJECT-TYPE
    SYNTAX     IpAddress
    MAX-ACCESS read-write
    STATUS     current
    DESCRIPTION
            "-- empty --"
    ::= { hmSetupIpRouterTagTableEntry 5 }

-- {COLUMN} 1.3.6.1.4.1.248.32.18.2.8.23.1.6
hmSetupIpRouterTagTableEntryDnsBackup OBJECT-TYPE
    SYNTAX     IpAddress
    MAX-ACCESS read-write
    STATUS     current
    DESCRIPTION
            "-- empty --"
    ::= { hmSetupIpRouterTagTableEntry 6 }

-- {COLUMN} 1.3.6.1.4.1.248.32.18.2.8.23.1.7
hmSetupIpRouterTagTableEntryNbnsDefault OBJECT-TYPE
    SYNTAX     IpAddress
    MAX-ACCESS read-write
    STATUS     current
    DESCRIPTION
            "-- empty --"
    ::= { hmSetupIpRouterTagTableEntry 7 }

-- {COLUMN} 1.3.6.1.4.1.248.32.18.2.8.23.1.8
hmSetupIpRouterTagTableEntryNbnsBackup OBJECT-TYPE
    SYNTAX     IpAddress
    MAX-ACCESS read-write
    STATUS     current
    DESCRIPTION
            "-- empty --"
    ::= { hmSetupIpRouterTagTableEntry 8 }

-- {NODE} 1.3.6.1.4.1.248.32.18.2.9
hmSetupSnmp OBJECT IDENTIFIER ::= { hmSetup 9 }

-- {SCALAR} 1.3.6.1.4.1.248.32.18.2.9.1
hmSetupSnmpSendTraps OBJECT-TYPE
    SYNTAX     INTEGER {
                  eNo (0),
                  eYes (1)
            }
    MAX-ACCESS read-write
    STATUS     current
    DESCRIPTION
            "-- empty --"
    ::= { hmSetupSnmp 1 }

-- {TABLE} 1.3.6.1.4.1.248.32.18.2.9.2
hmSetupSnmpIpTrapsTable OBJECT-TYPE
    SYNTAX     SEQUENCE OF HmSetupSnmpIpTrapsEntry
    MAX-ACCESS not-accessible
    STATUS     current
    DESCRIPTION
            "-- empty --"
    ::= { hmSetupSnmp 2 }

-- {ROW} 1.3.6.1.4.1.248.32.18.2.9.2.1
hmSetupSnmpIpTrapsEntry OBJECT-TYPE
    SYNTAX     HmSetupSnmpIpTrapsEntry
    MAX-ACCESS not-accessible
    STATUS     current
    DESCRIPTION
            ""
    INDEX {
            hmSetupSnmpIpTrapsEntryTrapIp
          }
    ::= { hmSetupSnmpIpTrapsTable 1 }

-- setSnmpIpTrapsLoopbackV6 for backward compatibility (version < 7.0)
HmSetupSnmpIpTrapsEntry ::= SEQUENCE {
            hmSetupSnmpIpTrapsEntryTrapIp IpAddress,
                     setSnmpIpTrapsLoopbackV6 IpAddress,
            hmSetupSnmpIpTrapsEntryLoopbackAddr DisplayString,
            hmSetupSnmpIpTrapsEntryVersion INTEGER
    }

-- {COLUMN} 1.3.6.1.4.1.248.32.18.2.9.2.1.1
hmSetupSnmpIpTrapsEntryTrapIp OBJECT-TYPE
    SYNTAX     IpAddress
    MAX-ACCESS read-write
    STATUS     current
    DESCRIPTION
            "-- empty --"
    ::= { hmSetupSnmpIpTrapsEntry 1 }

setSnmpIpTrapsLoopbackV6 OBJECT-TYPE
                  SYNTAX IpAddress
                  MAX-ACCESS read-write
                  STATUS current
                  DESCRIPTION "Loopback-Addr. (for backward compatibility, only versions < 7.0 support it)"
                  ::= {  hmSetupSnmpIpTrapsEntry 2 }


-- {COLUMN} 1.3.6.1.4.1.248.32.18.2.9.2.1.3
hmSetupSnmpIpTrapsEntryLoopbackAddr OBJECT-TYPE
    SYNTAX     DisplayString (SIZE(0..16))
    MAX-ACCESS read-write
    STATUS     current
    DESCRIPTION
            "-- empty --"
    ::= { hmSetupSnmpIpTrapsEntry 3 }

-- {COLUMN} 1.3.6.1.4.1.248.32.18.2.9.2.1.4
hmSetupSnmpIpTrapsEntryVersion OBJECT-TYPE
    SYNTAX     INTEGER {
                  eSnmpv2 (0),
                  eSnmpv1 (1)
            }
    MAX-ACCESS read-write
    STATUS     current
    DESCRIPTION
            "-- empty --"
    ::= { hmSetupSnmpIpTrapsEntry 4 }

-- {COLUMN} 1.3.6.1.4.1.248.32.18.2.9.2.1.5
hmSetupSnmpIpTrapsEntryPort OBJECT-TYPE
    SYNTAX     Integer32 (0..65535)
    MAX-ACCESS read-write
    STATUS     current
    DESCRIPTION
            "-- empty --"
    ::= { hmSetupSnmpIpTrapsEntry 5 }

-- {SCALAR} 1.3.6.1.4.1.248.32.18.2.9.3
hmSetupSnmpAdministrator OBJECT-TYPE
    SYNTAX     DisplayString (SIZE(0..255))
    MAX-ACCESS read-write
    STATUS     current
    DESCRIPTION
            "-- empty --"
    ::= { hmSetupSnmp 3 }

-- {SCALAR} 1.3.6.1.4.1.248.32.18.2.9.4
hmSetupSnmpLocation OBJECT-TYPE
    SYNTAX     DisplayString (SIZE(0..255))
    MAX-ACCESS read-write
    STATUS     current
    DESCRIPTION
            "-- empty --"
    ::= { hmSetupSnmp 4 }

-- {SCALAR} 1.3.6.1.4.1.248.32.18.2.9.5
hmSetupSnmpRegisterMonitor OBJECT-TYPE
    SYNTAX     DisplayString
    MAX-ACCESS read-write
    STATUS     current
    DESCRIPTION
            "-- empty --"
    ::= { hmSetupSnmp 5 }

-- {SCALAR} 1.3.6.1.4.1.248.32.18.2.9.6
hmSetupSnmpDeleteMonitor OBJECT-TYPE
    SYNTAX     DisplayString
    MAX-ACCESS read-write
    STATUS     current
    DESCRIPTION
            "-- empty --"
    ::= { hmSetupSnmp 6 }

-- {TABLE} 1.3.6.1.4.1.248.32.18.2.9.7
hmSetupSnmpMonitorTableTable OBJECT-TYPE
    SYNTAX     SEQUENCE OF HmSetupSnmpMonitorTableEntry
    MAX-ACCESS not-accessible
    STATUS     current
    DESCRIPTION
            "-- empty --"
    ::= { hmSetupSnmp 7 }

-- {ROW} 1.3.6.1.4.1.248.32.18.2.9.7.1
hmSetupSnmpMonitorTableEntry OBJECT-TYPE
    SYNTAX     HmSetupSnmpMonitorTableEntry
    MAX-ACCESS not-accessible
    STATUS     current
    DESCRIPTION
            ""
    INDEX {
            hmSetupSnmpMonitorTableEntryIpAddress,
            hmSetupSnmpMonitorTableEntryPort
          }
    ::= { hmSetupSnmpMonitorTableTable 1 }

HmSetupSnmpMonitorTableEntry ::= SEQUENCE {
            hmSetupSnmpMonitorTableEntryIpAddress IpAddress,
            hmSetupSnmpMonitorTableEntryPort Integer32,
            hmSetupSnmpMonitorTableEntryTimeout Integer32,
            hmSetupSnmpMonitorTableEntryMacAddress DisplayString,
            hmSetupSnmpMonitorTableEntryPeer DisplayString,
            hmSetupSnmpMonitorTableEntryLoopbackAddr IpAddress,
            hmSetupSnmpMonitorTableEntryVlanId Integer32,
            hmSetupSnmpMonitorTableEntryLanIfc DisplayString,
            hmSetupSnmpMonitorTableEntryEthernetPort Integer32
    }

-- {COLUMN} 1.3.6.1.4.1.248.32.18.2.9.7.1.1
hmSetupSnmpMonitorTableEntryIpAddress OBJECT-TYPE
    SYNTAX     IpAddress
    MAX-ACCESS read-only
    STATUS     current
    DESCRIPTION
            "-- empty --"
    ::= { hmSetupSnmpMonitorTableEntry 1 }

-- {COLUMN} 1.3.6.1.4.1.248.32.18.2.9.7.1.2
hmSetupSnmpMonitorTableEntryPort OBJECT-TYPE
    SYNTAX     Integer32 (0..65535)
    MAX-ACCESS read-only
    STATUS     current
    DESCRIPTION
            "-- empty --"
    ::= { hmSetupSnmpMonitorTableEntry 2 }

-- {COLUMN} 1.3.6.1.4.1.248.32.18.2.9.7.1.3
hmSetupSnmpMonitorTableEntryTimeout OBJECT-TYPE
    SYNTAX     Integer32 (0..65535)
    MAX-ACCESS read-only
    STATUS     current
    DESCRIPTION
            "-- empty --"
    ::= { hmSetupSnmpMonitorTableEntry 3 }

-- {COLUMN} 1.3.6.1.4.1.248.32.18.2.9.7.1.4
hmSetupSnmpMonitorTableEntryMacAddress OBJECT-TYPE
    SYNTAX     DisplayString (SIZE(0..12))
    MAX-ACCESS read-only
    STATUS     current
    DESCRIPTION
            "-- empty --"
    ::= { hmSetupSnmpMonitorTableEntry 4 }

-- {COLUMN} 1.3.6.1.4.1.248.32.18.2.9.7.1.5
hmSetupSnmpMonitorTableEntryPeer OBJECT-TYPE
    SYNTAX     DisplayString (SIZE(0..16))
    MAX-ACCESS read-only
    STATUS     current
    DESCRIPTION
            "-- empty --"
    ::= { hmSetupSnmpMonitorTableEntry 5 }

-- {COLUMN} 1.3.6.1.4.1.248.32.18.2.9.7.1.6
hmSetupSnmpMonitorTableEntryLoopbackAddr OBJECT-TYPE
    SYNTAX     IpAddress
    MAX-ACCESS read-only
    STATUS     current
    DESCRIPTION
            "-- empty --"
    ::= { hmSetupSnmpMonitorTableEntry 6 }

-- {COLUMN} 1.3.6.1.4.1.248.32.18.2.9.7.1.7
hmSetupSnmpMonitorTableEntryVlanId OBJECT-TYPE
    SYNTAX     Integer32 (0..65535)
    MAX-ACCESS read-only
    STATUS     current
    DESCRIPTION
            "-- empty --"
    ::= { hmSetupSnmpMonitorTableEntry 7 }

-- {COLUMN} 1.3.6.1.4.1.248.32.18.2.9.7.1.8
hmSetupSnmpMonitorTableEntryLanIfc OBJECT-TYPE
    SYNTAX     DisplayString (SIZE(0..255))
    MAX-ACCESS read-only
    STATUS     current
    DESCRIPTION
            "-- empty --"
    ::= { hmSetupSnmpMonitorTableEntry 8 }

-- {COLUMN} 1.3.6.1.4.1.248.32.18.2.9.7.1.9
hmSetupSnmpMonitorTableEntryEthernetPort OBJECT-TYPE
    SYNTAX     Integer32 (0..255)
    MAX-ACCESS read-only
    STATUS     current
    DESCRIPTION
            "-- empty --"
    ::= { hmSetupSnmpMonitorTableEntry 9 }

-- {SCALAR} 1.3.6.1.4.1.248.32.18.2.9.10
hmSetupSnmpPasswordRequiredForSnmpReadAccess OBJECT-TYPE
    SYNTAX     INTEGER {
                  eNo (0),
                  eYes (1)
            }
    MAX-ACCESS read-write
    STATUS     current
    DESCRIPTION
            "-- empty --"
    ::= { hmSetupSnmp 10 }

-- {SCALAR} 1.3.6.1.4.1.248.32.18.2.9.11
hmSetupSnmpComment1 OBJECT-TYPE
    SYNTAX     DisplayString (SIZE(0..255))
    MAX-ACCESS read-write
    STATUS     current
    DESCRIPTION
            "-- empty --"
    ::= { hmSetupSnmp 11 }

-- {SCALAR} 1.3.6.1.4.1.248.32.18.2.9.12
hmSetupSnmpComment2 OBJECT-TYPE
    SYNTAX     DisplayString (SIZE(0..255))
    MAX-ACCESS read-write
    STATUS     current
    DESCRIPTION
            "-- empty --"
    ::= { hmSetupSnmp 12 }

-- {SCALAR} 1.3.6.1.4.1.248.32.18.2.9.13
hmSetupSnmpComment3 OBJECT-TYPE
    SYNTAX     DisplayString (SIZE(0..255))
    MAX-ACCESS read-write
    STATUS     current
    DESCRIPTION
            "-- empty --"
    ::= { hmSetupSnmp 13 }

-- {SCALAR} 1.3.6.1.4.1.248.32.18.2.9.14
hmSetupSnmpComment4 OBJECT-TYPE
    SYNTAX     DisplayString (SIZE(0..255))
    MAX-ACCESS read-write
    STATUS     current
    DESCRIPTION
            "-- empty --"
    ::= { hmSetupSnmp 14 }

-- {SCALAR} 1.3.6.1.4.1.248.32.18.2.9.15
hmSetupSnmpReadOnlyCommunity OBJECT-TYPE
    SYNTAX     DisplayString (SIZE(0..31))
    MAX-ACCESS read-write
    STATUS     current
    DESCRIPTION
            "-- empty --"
    ::= { hmSetupSnmp 15 }

-- {SCALAR} 1.3.6.1.4.1.248.32.18.2.9.16
hmSetupSnmpComment5 OBJECT-TYPE
    SYNTAX     DisplayString (SIZE(0..255))
    MAX-ACCESS read-write
    STATUS     current
    DESCRIPTION
            "-- empty --"
    ::= { hmSetupSnmp 16 }

-- {SCALAR} 1.3.6.1.4.1.248.32.18.2.9.17
hmSetupSnmpComment6 OBJECT-TYPE
    SYNTAX     DisplayString (SIZE(0..255))
    MAX-ACCESS read-write
    STATUS     current
    DESCRIPTION
            "-- empty --"
    ::= { hmSetupSnmp 17 }

-- {SCALAR} 1.3.6.1.4.1.248.32.18.2.9.18
hmSetupSnmpComment7 OBJECT-TYPE
    SYNTAX     DisplayString (SIZE(0..255))
    MAX-ACCESS read-write
    STATUS     current
    DESCRIPTION
            "-- empty --"
    ::= { hmSetupSnmp 18 }

-- {SCALAR} 1.3.6.1.4.1.248.32.18.2.9.19
hmSetupSnmpComment8 OBJECT-TYPE
    SYNTAX     DisplayString (SIZE(0..255))
    MAX-ACCESS read-write
    STATUS     current
    DESCRIPTION
            "-- empty --"
    ::= { hmSetupSnmp 19 }

-- {SCALAR} 1.3.6.1.4.1.248.32.18.2.9.20
hmSetupSnmpFullHostMib OBJECT-TYPE
    SYNTAX     INTEGER {
                  eNo (0),
                  eYes (1)
            }
    MAX-ACCESS read-write
    STATUS     current
    DESCRIPTION
            "-- empty --"
    ::= { hmSetupSnmp 20 }

-- {SCALAR} 1.3.6.1.4.1.248.32.18.2.9.21
hmSetupSnmpPort OBJECT-TYPE
    SYNTAX     Integer32 (0..65535)
    MAX-ACCESS read-write
    STATUS     current
    DESCRIPTION
            "-- empty --"
    ::= { hmSetupSnmp 21 }

-- {TABLE} 1.3.6.1.4.1.248.32.18.2.9.22
hmSetupSnmpReadOnlyCommunitiesTable OBJECT-TYPE
    SYNTAX     SEQUENCE OF HmSetupSnmpReadOnlyCommunitiesEntry
    MAX-ACCESS not-accessible
    STATUS     current
    DESCRIPTION
            "-- empty --"
    ::= { hmSetupSnmp 22 }

-- {ROW} 1.3.6.1.4.1.248.32.18.2.9.22.1
hmSetupSnmpReadOnlyCommunitiesEntry OBJECT-TYPE
    SYNTAX     HmSetupSnmpReadOnlyCommunitiesEntry
    MAX-ACCESS not-accessible
    STATUS     current
    DESCRIPTION
            ""
    INDEX {
            hmSetupSnmpReadOnlyCommunitiesEntryReadOnlyCommunity
          }
    ::= { hmSetupSnmpReadOnlyCommunitiesTable 1 }

HmSetupSnmpReadOnlyCommunitiesEntry ::= SEQUENCE {
            hmSetupSnmpReadOnlyCommunitiesEntryReadOnlyCommunity DisplayString
    }

-- {COLUMN} 1.3.6.1.4.1.248.32.18.2.9.22.1.1
hmSetupSnmpReadOnlyCommunitiesEntryReadOnlyCommunity OBJECT-TYPE
    SYNTAX     DisplayString (SIZE(0..31))
    MAX-ACCESS read-write
    STATUS     current
    DESCRIPTION
            "-- empty --"
    ::= { hmSetupSnmpReadOnlyCommunitiesEntry 1 }

-- {SCALAR} 1.3.6.1.4.1.248.32.18.2.9.23
hmSetupSnmpPublicComment1 OBJECT-TYPE
    SYNTAX     DisplayString (SIZE(0..255))
    MAX-ACCESS read-write
    STATUS     current
    DESCRIPTION
            "-- empty --"
    ::= { hmSetupSnmp 23 }

-- {SCALAR} 1.3.6.1.4.1.248.32.18.2.9.24
hmSetupSnmpPublicComment2 OBJECT-TYPE
    SYNTAX     DisplayString (SIZE(0..255))
    MAX-ACCESS read-write
    STATUS     current
    DESCRIPTION
            "-- empty --"
    ::= { hmSetupSnmp 24 }

-- {SCALAR} 1.3.6.1.4.1.248.32.18.2.9.25
hmSetupSnmpPublicComment3 OBJECT-TYPE
    SYNTAX     DisplayString (SIZE(0..255))
    MAX-ACCESS read-write
    STATUS     current
    DESCRIPTION
            "-- empty --"
    ::= { hmSetupSnmp 25 }

-- {SCALAR} 1.3.6.1.4.1.248.32.18.2.9.26
hmSetupSnmpPublicComment4 OBJECT-TYPE
    SYNTAX     DisplayString (SIZE(0..255))
    MAX-ACCESS read-write
    STATUS     current
    DESCRIPTION
            "-- empty --"
    ::= { hmSetupSnmp 26 }

-- {SCALAR} 1.3.6.1.4.1.248.32.18.2.9.37
hmSetupSnmpAdmittedProtocols OBJECT-TYPE
    SYNTAX     BITS {
                  eSnmpv3 (29),
                  eSnmpv2 (30),
                  eSnmpv1 (31)
            }
    MAX-ACCESS read-write
    STATUS     current
    DESCRIPTION
            "-- empty --"
    ::= { hmSetupSnmp 37 }

-- {SCALAR} 1.3.6.1.4.1.248.32.18.2.9.38
hmSetupSnmpAllowAdmins OBJECT-TYPE
    SYNTAX     INTEGER {
                  eNo (0),
                  eYes (1)
            }
    MAX-ACCESS read-write
    STATUS     current
    DESCRIPTION
            "-- empty --"
    ::= { hmSetupSnmp 38 }

-- {SCALAR} 1.3.6.1.4.1.248.32.18.2.9.39
hmSetupSnmpSnmpv3AdminAuthentication OBJECT-TYPE
    SYNTAX     INTEGER {
                  eHmacMd5 (2),
                  eHmacSha (3),
                  eHmacSha224 (4),
                  eHmacSha256 (5),
                  eHmacSha384 (6),
                  eHmacSha512 (7)
            }
    MAX-ACCESS read-only
    STATUS     current
    DESCRIPTION
            "-- empty --"
    ::= { hmSetupSnmp 39 }

-- {SCALAR} 1.3.6.1.4.1.248.32.18.2.9.40
hmSetupSnmpSnmpv3AdminPrivacy OBJECT-TYPE
    SYNTAX     INTEGER {
                  eDes (2),
                  eAes128 (4),
                  eAes192 (20),
                  eAes256 (21)
            }
    MAX-ACCESS read-only
    STATUS     current
    DESCRIPTION
            "-- empty --"
    ::= { hmSetupSnmp 40 }

-- {SCALAR} 1.3.6.1.4.1.248.32.18.2.9.41
hmSetupSnmpOperating OBJECT-TYPE
    SYNTAX     BITS {
                  eNo (0),
                  eYes (7)
            }
    MAX-ACCESS read-write
    STATUS     current
    DESCRIPTION
            "-- empty --"
    ::= { hmSetupSnmp 41 }

-- {NODE} 1.3.6.1.4.1.248.32.18.2.10
hmSetupDhcp OBJECT IDENTIFIER ::= { hmSetup 10 }

-- {SCALAR} 1.3.6.1.4.1.248.32.18.2.10.6
hmSetupDhcpMaxLeaseTimeMinutes OBJECT-TYPE
    SYNTAX     Integer32 (0..2147483647)
    MAX-ACCESS read-write
    STATUS     current
    DESCRIPTION
            "-- empty --"
    ::= { hmSetupDhcp 6 }

-- {SCALAR} 1.3.6.1.4.1.248.32.18.2.10.7
hmSetupDhcpDefaultLeaseTimeMinutes OBJECT-TYPE
    SYNTAX     Integer32 (0..2147483647)
    MAX-ACCESS read-write
    STATUS     current
    DESCRIPTION
            "-- empty --"
    ::= { hmSetupDhcp 7 }

-- {TABLE} 1.3.6.1.4.1.248.32.18.2.10.8
hmSetupDhcpDhcpTableTable OBJECT-TYPE
    SYNTAX     SEQUENCE OF HmSetupDhcpDhcpTableEntry
    MAX-ACCESS not-accessible
    STATUS     current
    DESCRIPTION
            "-- empty --"
    ::= { hmSetupDhcp 8 }

-- {ROW} 1.3.6.1.4.1.248.32.18.2.10.8.1
hmSetupDhcpDhcpTableEntry OBJECT-TYPE
    SYNTAX     HmSetupDhcpDhcpTableEntry
    MAX-ACCESS not-accessible
    STATUS     current
    DESCRIPTION
            ""
    INDEX {
            hmSetupDhcpDhcpTableEntryIpAddress,
            hmSetupDhcpDhcpTableEntryNetworkName
          }
    ::= { hmSetupDhcpDhcpTableTable 1 }

HmSetupDhcpDhcpTableEntry ::= SEQUENCE {
            hmSetupDhcpDhcpTableEntryIpAddress IpAddress,
            hmSetupDhcpDhcpTableEntryMacAddress DisplayString,
            hmSetupDhcpDhcpTableEntryTimeout Integer32,
            hmSetupDhcpDhcpTableEntryHostname DisplayString,
            hmSetupDhcpDhcpTableEntryType BITS,
            hmSetupDhcpDhcpTableEntryEthernetPort INTEGER,
            hmSetupDhcpDhcpTableEntryVlanId Integer32,
            hmSetupDhcpDhcpTableEntryNetworkName DisplayString,
            hmSetupDhcpDhcpTableEntryLanIfc INTEGER,
            hmSetupDhcpDhcpTableEntryAssignment DisplayString,
            hmSetupDhcpDhcpTableEntryAssignmentNumeric Gauge32
    }

-- {COLUMN} 1.3.6.1.4.1.248.32.18.2.10.8.1.1
hmSetupDhcpDhcpTableEntryIpAddress OBJECT-TYPE
    SYNTAX     IpAddress
    MAX-ACCESS read-only
    STATUS     current
    DESCRIPTION
            "-- empty --"
    ::= { hmSetupDhcpDhcpTableEntry 1 }

-- {COLUMN} 1.3.6.1.4.1.248.32.18.2.10.8.1.2
hmSetupDhcpDhcpTableEntryMacAddress OBJECT-TYPE
    SYNTAX     DisplayString (SIZE(0..12))
    MAX-ACCESS read-only
    STATUS     current
    DESCRIPTION
            "-- empty --"
    ::= { hmSetupDhcpDhcpTableEntry 2 }

-- {COLUMN} 1.3.6.1.4.1.248.32.18.2.10.8.1.3
hmSetupDhcpDhcpTableEntryTimeout OBJECT-TYPE
    SYNTAX     Integer32 (0..2147483647)
    MAX-ACCESS read-only
    STATUS     current
    DESCRIPTION
            "-- empty --"
    ::= { hmSetupDhcpDhcpTableEntry 3 }

-- {COLUMN} 1.3.6.1.4.1.248.32.18.2.10.8.1.4
hmSetupDhcpDhcpTableEntryHostname OBJECT-TYPE
    SYNTAX     DisplayString (SIZE(0..65))
    MAX-ACCESS read-only
    STATUS     current
    DESCRIPTION
            "-- empty --"
    ::= { hmSetupDhcpDhcpTableEntry 4 }

-- {COLUMN} 1.3.6.1.4.1.248.32.18.2.10.8.1.5
hmSetupDhcpDhcpTableEntryType OBJECT-TYPE
    SYNTAX     BITS {
                  eRelay (4),
                  eCache (8),
                  eBootp (10),
                  eDyn (11),
                  eStat (12),
                  eUnkn (13),
                  enewreq (14),
                  enew (15)
            }
    MAX-ACCESS read-only
    STATUS     current
    DESCRIPTION
            "-- empty --"
    ::= { hmSetupDhcpDhcpTableEntry 5 }

-- {COLUMN} 1.3.6.1.4.1.248.32.18.2.10.8.1.7
hmSetupDhcpDhcpTableEntryEthernetPort OBJECT-TYPE
    SYNTAX     INTEGER {
                  eEth1 (2),
                  eEth2 (3),
                  eEth3 (4),
                  eEth4 (5)
            }
    MAX-ACCESS read-only
    STATUS     current
    DESCRIPTION
            "-- empty --"
    ::= { hmSetupDhcpDhcpTableEntry 7 }

-- {COLUMN} 1.3.6.1.4.1.248.32.18.2.10.8.1.8
hmSetupDhcpDhcpTableEntryVlanId OBJECT-TYPE
    SYNTAX     Integer32 (0..65535)
    MAX-ACCESS read-only
    STATUS     current
    DESCRIPTION
            "-- empty --"
    ::= { hmSetupDhcpDhcpTableEntry 8 }

-- {COLUMN} 1.3.6.1.4.1.248.32.18.2.10.8.1.9
hmSetupDhcpDhcpTableEntryNetworkName OBJECT-TYPE
    SYNTAX     DisplayString (SIZE(0..17))
    MAX-ACCESS read-only
    STATUS     current
    DESCRIPTION
            "-- empty --"
    ::= { hmSetupDhcpDhcpTableEntry 9 }

-- {COLUMN} 1.3.6.1.4.1.248.32.18.2.10.8.1.10
hmSetupDhcpDhcpTableEntryLanIfc OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311),
                  eAny (65535)
            }
    MAX-ACCESS read-only
    STATUS     current
    DESCRIPTION
            "-- empty --"
    ::= { hmSetupDhcpDhcpTableEntry 10 }

-- {COLUMN} 1.3.6.1.4.1.248.32.18.2.10.8.1.11
hmSetupDhcpDhcpTableEntryAssignment OBJECT-TYPE
    SYNTAX     DisplayString (SIZE(0..21))
    MAX-ACCESS read-only
    STATUS     current
    DESCRIPTION
            "-- empty --"
    ::= { hmSetupDhcpDhcpTableEntry 11 }

-- {COLUMN} 1.3.6.1.4.1.248.32.18.2.10.8.1.12
hmSetupDhcpDhcpTableEntryAssignmentNumeric OBJECT-TYPE
    SYNTAX     Gauge32
    MAX-ACCESS read-only
    STATUS     current
    DESCRIPTION
            "-- empty --"
    ::= { hmSetupDhcpDhcpTableEntry 12 }

-- {TABLE} 1.3.6.1.4.1.248.32.18.2.10.9
hmSetupDhcpHostsTable OBJECT-TYPE
    SYNTAX     SEQUENCE OF HmSetupDhcpHostsEntry
    MAX-ACCESS not-accessible
    STATUS     current
    DESCRIPTION
            "-- empty --"
    ::= { hmSetupDhcp 9 }

-- {ROW} 1.3.6.1.4.1.248.32.18.2.10.9.1
hmSetupDhcpHostsEntry OBJECT-TYPE
    SYNTAX     HmSetupDhcpHostsEntry
    MAX-ACCESS not-accessible
    STATUS     current
    DESCRIPTION
            ""
    INDEX {
            hmSetupDhcpHostsEntryMacAddress,
            hmSetupDhcpHostsEntryNetworkName
          }
    ::= { hmSetupDhcpHostsTable 1 }

HmSetupDhcpHostsEntry ::= SEQUENCE {
            hmSetupDhcpHostsEntryMacAddress DisplayString,
            hmSetupDhcpHostsEntryIpAddress IpAddress,
            hmSetupDhcpHostsEntryHostname DisplayString,
            hmSetupDhcpHostsEntryImageAlias DisplayString,
            hmSetupDhcpHostsEntryNetworkName DisplayString
    }

-- {COLUMN} 1.3.6.1.4.1.248.32.18.2.10.9.1.1
hmSetupDhcpHostsEntryMacAddress OBJECT-TYPE
    SYNTAX     DisplayString (SIZE(0..12))
    MAX-ACCESS read-write
    STATUS     current
    DESCRIPTION
            "-- empty --"
    ::= { hmSetupDhcpHostsEntry 1 }

-- {COLUMN} 1.3.6.1.4.1.248.32.18.2.10.9.1.2
hmSetupDhcpHostsEntryIpAddress OBJECT-TYPE
    SYNTAX     IpAddress
    MAX-ACCESS read-write
    STATUS     current
    DESCRIPTION
            "-- empty --"
    ::= { hmSetupDhcpHostsEntry 2 }

-- {COLUMN} 1.3.6.1.4.1.248.32.18.2.10.9.1.3
hmSetupDhcpHostsEntryHostname OBJECT-TYPE
    SYNTAX     DisplayString (SIZE(0..30))
    MAX-ACCESS read-write
    STATUS     current
    DESCRIPTION
            "-- empty --"
    ::= { hmSetupDhcpHostsEntry 3 }

-- {COLUMN} 1.3.6.1.4.1.248.32.18.2.10.9.1.4
hmSetupDhcpHostsEntryImageAlias OBJECT-TYPE
    SYNTAX     DisplayString (SIZE(0..16))
    MAX-ACCESS read-write
    STATUS     current
    DESCRIPTION
            "-- empty --"
    ::= { hmSetupDhcpHostsEntry 4 }

-- {COLUMN} 1.3.6.1.4.1.248.32.18.2.10.9.1.5
hmSetupDhcpHostsEntryNetworkName OBJECT-TYPE
    SYNTAX     DisplayString (SIZE(0..16))
    MAX-ACCESS read-write
    STATUS     current
    DESCRIPTION
            "-- empty --"
    ::= { hmSetupDhcpHostsEntry 5 }

-- {TABLE} 1.3.6.1.4.1.248.32.18.2.10.10
hmSetupDhcpAliasListTable OBJECT-TYPE
    SYNTAX     SEQUENCE OF HmSetupDhcpAliasListEntry
    MAX-ACCESS not-accessible
    STATUS     current
    DESCRIPTION
            "-- empty --"
    ::= { hmSetupDhcp 10 }

-- {ROW} 1.3.6.1.4.1.248.32.18.2.10.10.1
hmSetupDhcpAliasListEntry OBJECT-TYPE
    SYNTAX     HmSetupDhcpAliasListEntry
    MAX-ACCESS not-accessible
    STATUS     current
    DESCRIPTION
            ""
    INDEX {
            hmSetupDhcpAliasListEntryImageAlias
          }
    ::= { hmSetupDhcpAliasListTable 1 }

HmSetupDhcpAliasListEntry ::= SEQUENCE {
            hmSetupDhcpAliasListEntryImageAlias DisplayString,
            hmSetupDhcpAliasListEntryImageFile DisplayString,
            hmSetupDhcpAliasListEntryImageServer IpAddress
    }

-- {COLUMN} 1.3.6.1.4.1.248.32.18.2.10.10.1.1
hmSetupDhcpAliasListEntryImageAlias OBJECT-TYPE
    SYNTAX     DisplayString (SIZE(0..16))
    MAX-ACCESS read-write
    STATUS     current
    DESCRIPTION
            "-- empty --"
    ::= { hmSetupDhcpAliasListEntry 1 }

-- {COLUMN} 1.3.6.1.4.1.248.32.18.2.10.10.1.2
hmSetupDhcpAliasListEntryImageFile OBJECT-TYPE
    SYNTAX     DisplayString (SIZE(0..60))
    MAX-ACCESS read-write
    STATUS     current
    DESCRIPTION
            "-- empty --"
    ::= { hmSetupDhcpAliasListEntry 2 }

-- {COLUMN} 1.3.6.1.4.1.248.32.18.2.10.10.1.3
hmSetupDhcpAliasListEntryImageServer OBJECT-TYPE
    SYNTAX     IpAddress
    MAX-ACCESS read-write
    STATUS     current
    DESCRIPTION
            "-- empty --"
    ::= { hmSetupDhcpAliasListEntry 3 }

-- {TABLE} 1.3.6.1.4.1.248.32.18.2.10.18
hmSetupDhcpPortsTable OBJECT-TYPE
    SYNTAX     SEQUENCE OF HmSetupDhcpPortsEntry
    MAX-ACCESS not-accessible
    STATUS     current
    DESCRIPTION
            "-- empty --"
    ::= { hmSetupDhcp 18 }

-- {ROW} 1.3.6.1.4.1.248.32.18.2.10.18.1
hmSetupDhcpPortsEntry OBJECT-TYPE
    SYNTAX     HmSetupDhcpPortsEntry
    MAX-ACCESS not-accessible
    STATUS     current
    DESCRIPTION
            ""
    INDEX {
            hmSetupDhcpPortsEntryPort
          }
    ::= { hmSetupDhcpPortsTable 1 }

HmSetupDhcpPortsEntry ::= SEQUENCE {
            hmSetupDhcpPortsEntryPort DisplayString,
            hmSetupDhcpPortsEntryEnableDhcp INTEGER
    }

-- {COLUMN} 1.3.6.1.4.1.248.32.18.2.10.18.1.2
hmSetupDhcpPortsEntryPort OBJECT-TYPE
    SYNTAX     DisplayString (SIZE(0..18))
    MAX-ACCESS read-only
    STATUS     current
    DESCRIPTION
            "-- empty --"
    ::= { hmSetupDhcpPortsEntry 2 }

-- {COLUMN} 1.3.6.1.4.1.248.32.18.2.10.18.1.3
hmSetupDhcpPortsEntryEnableDhcp OBJECT-TYPE
    SYNTAX     INTEGER {
                  eNo (0),
                  eYes (1)
            }
    MAX-ACCESS read-write
    STATUS     current
    DESCRIPTION
            "-- empty --"
    ::= { hmSetupDhcpPortsEntry 3 }

-- {SCALAR} 1.3.6.1.4.1.248.32.18.2.10.19
hmSetupDhcpUserClassIdentifer OBJECT-TYPE
    SYNTAX     DisplayString (SIZE(0..63))
    MAX-ACCESS read-write
    STATUS     current
    DESCRIPTION
            "-- empty --"
    ::= { hmSetupDhcp 19 }

-- {TABLE} 1.3.6.1.4.1.248.32.18.2.10.20
hmSetupDhcpNetworkListTable OBJECT-TYPE
    SYNTAX     SEQUENCE OF HmSetupDhcpNetworkListEntry
    MAX-ACCESS not-accessible
    STATUS     current
    DESCRIPTION
            "-- empty --"
    ::= { hmSetupDhcp 20 }

-- {ROW} 1.3.6.1.4.1.248.32.18.2.10.20.1
hmSetupDhcpNetworkListEntry OBJECT-TYPE
    SYNTAX     HmSetupDhcpNetworkListEntry
    MAX-ACCESS not-accessible
    STATUS     current
    DESCRIPTION
            ""
    INDEX {
            hmSetupDhcpNetworkListEntryNetworkName
          }
    ::= { hmSetupDhcpNetworkListTable 1 }

HmSetupDhcpNetworkListEntry ::= SEQUENCE {
            hmSetupDhcpNetworkListEntryNetworkName DisplayString,
            hmSetupDhcpNetworkListEntryStartAddressPool IpAddress,
            hmSetupDhcpNetworkListEntryEndAddressPool IpAddress,
            hmSetupDhcpNetworkListEntryNetmask IpAddress,
            hmSetupDhcpNetworkListEntryBroadcastAddress IpAddress,
            hmSetupDhcpNetworkListEntryGatewayAddress IpAddress,
            hmSetupDhcpNetworkListEntryDnsDefault IpAddress,
            hmSetupDhcpNetworkListEntryDnsBackup IpAddress,
            hmSetupDhcpNetworkListEntryNbnsDefault IpAddress,
            hmSetupDhcpNetworkListEntryNbnsBackup IpAddress,
            hmSetupDhcpNetworkListEntryOperating INTEGER,
            hmSetupDhcpNetworkListEntryBroadcastBit INTEGER,
            hmSetupDhcpNetworkListEntryMasterServer IpAddress,
            hmSetupDhcpNetworkListEntryCache INTEGER,
            hmSetupDhcpNetworkListEntryAdaption INTEGER,
            hmSetupDhcpNetworkListEntryCluster INTEGER,
            hmSetupDhcpNetworkListEntry2ndMasterServer IpAddress,
            hmSetupDhcpNetworkListEntry3rdMasterServer IpAddress,
            hmSetupDhcpNetworkListEntry4thMasterServer IpAddress
    }

-- {COLUMN} 1.3.6.1.4.1.248.32.18.2.10.20.1.1
hmSetupDhcpNetworkListEntryNetworkName OBJECT-TYPE
    SYNTAX     DisplayString (SIZE(0..16))
    MAX-ACCESS read-write
    STATUS     current
    DESCRIPTION
            "-- empty --"
    ::= { hmSetupDhcpNetworkListEntry 1 }

-- {COLUMN} 1.3.6.1.4.1.248.32.18.2.10.20.1.2
hmSetupDhcpNetworkListEntryStartAddressPool OBJECT-TYPE
    SYNTAX     IpAddress
    MAX-ACCESS read-write
    STATUS     current
    DESCRIPTION
            "-- empty --"
    ::= { hmSetupDhcpNetworkListEntry 2 }

-- {COLUMN} 1.3.6.1.4.1.248.32.18.2.10.20.1.3
hmSetupDhcpNetworkListEntryEndAddressPool OBJECT-TYPE
    SYNTAX     IpAddress
    MAX-ACCESS read-write
    STATUS     current
    DESCRIPTION
            "-- empty --"
    ::= { hmSetupDhcpNetworkListEntry 3 }

-- {COLUMN} 1.3.6.1.4.1.248.32.18.2.10.20.1.4
hmSetupDhcpNetworkListEntryNetmask OBJECT-TYPE
    SYNTAX     IpAddress
    MAX-ACCESS read-write
    STATUS     current
    DESCRIPTION
            "-- empty --"
    ::= { hmSetupDhcpNetworkListEntry 4 }

-- {COLUMN} 1.3.6.1.4.1.248.32.18.2.10.20.1.5
hmSetupDhcpNetworkListEntryBroadcastAddress OBJECT-TYPE
    SYNTAX     IpAddress
    MAX-ACCESS read-write
    STATUS     current
    DESCRIPTION
            "-- empty --"
    ::= { hmSetupDhcpNetworkListEntry 5 }

-- {COLUMN} 1.3.6.1.4.1.248.32.18.2.10.20.1.6
hmSetupDhcpNetworkListEntryGatewayAddress OBJECT-TYPE
    SYNTAX     IpAddress
    MAX-ACCESS read-write
    STATUS     current
    DESCRIPTION
            "-- empty --"
    ::= { hmSetupDhcpNetworkListEntry 6 }

-- {COLUMN} 1.3.6.1.4.1.248.32.18.2.10.20.1.7
hmSetupDhcpNetworkListEntryDnsDefault OBJECT-TYPE
    SYNTAX     IpAddress
    MAX-ACCESS read-write
    STATUS     current
    DESCRIPTION
            "-- empty --"
    ::= { hmSetupDhcpNetworkListEntry 7 }

-- {COLUMN} 1.3.6.1.4.1.248.32.18.2.10.20.1.8
hmSetupDhcpNetworkListEntryDnsBackup OBJECT-TYPE
    SYNTAX     IpAddress
    MAX-ACCESS read-write
    STATUS     current
    DESCRIPTION
            "-- empty --"
    ::= { hmSetupDhcpNetworkListEntry 8 }

-- {COLUMN} 1.3.6.1.4.1.248.32.18.2.10.20.1.9
hmSetupDhcpNetworkListEntryNbnsDefault OBJECT-TYPE
    SYNTAX     IpAddress
    MAX-ACCESS read-write
    STATUS     current
    DESCRIPTION
            "-- empty --"
    ::= { hmSetupDhcpNetworkListEntry 9 }

-- {COLUMN} 1.3.6.1.4.1.248.32.18.2.10.20.1.10
hmSetupDhcpNetworkListEntryNbnsBackup OBJECT-TYPE
    SYNTAX     IpAddress
    MAX-ACCESS read-write
    STATUS     current
    DESCRIPTION
            "-- empty --"
    ::= { hmSetupDhcpNetworkListEntry 10 }

-- {COLUMN} 1.3.6.1.4.1.248.32.18.2.10.20.1.11
hmSetupDhcpNetworkListEntryOperating OBJECT-TYPE
    SYNTAX     INTEGER {
                  eNo (0),
                  eYes (1),
                  eAuto (2),
                  eClient (4),
                  eRelay (16)
            }
    MAX-ACCESS read-write
    STATUS     current
    DESCRIPTION
            "-- empty --"
    ::= { hmSetupDhcpNetworkListEntry 11 }

-- {COLUMN} 1.3.6.1.4.1.248.32.18.2.10.20.1.12
hmSetupDhcpNetworkListEntryBroadcastBit OBJECT-TYPE
    SYNTAX     INTEGER {
                  eNo (0),
                  eYes (1)
            }
    MAX-ACCESS read-write
    STATUS     current
    DESCRIPTION
            "-- empty --"
    ::= { hmSetupDhcpNetworkListEntry 12 }

-- {COLUMN} 1.3.6.1.4.1.248.32.18.2.10.20.1.13
hmSetupDhcpNetworkListEntryMasterServer OBJECT-TYPE
    SYNTAX     IpAddress
    MAX-ACCESS read-write
    STATUS     current
    DESCRIPTION
            "-- empty --"
    ::= { hmSetupDhcpNetworkListEntry 13 }

-- {COLUMN} 1.3.6.1.4.1.248.32.18.2.10.20.1.14
hmSetupDhcpNetworkListEntryCache OBJECT-TYPE
    SYNTAX     INTEGER {
                  eNo (0),
                  eYes (1)
            }
    MAX-ACCESS read-write
    STATUS     current
    DESCRIPTION
            "-- empty --"
    ::= { hmSetupDhcpNetworkListEntry 14 }

-- {COLUMN} 1.3.6.1.4.1.248.32.18.2.10.20.1.15
hmSetupDhcpNetworkListEntryAdaption OBJECT-TYPE
    SYNTAX     INTEGER {
                  eNo (0),
                  eYes (1)
            }
    MAX-ACCESS read-write
    STATUS     current
    DESCRIPTION
            "-- empty --"
    ::= { hmSetupDhcpNetworkListEntry 15 }

-- {COLUMN} 1.3.6.1.4.1.248.32.18.2.10.20.1.16
hmSetupDhcpNetworkListEntryCluster OBJECT-TYPE
    SYNTAX     INTEGER {
                  eNo (0),
                  eYes (1)
            }
    MAX-ACCESS read-write
    STATUS     current
    DESCRIPTION
            "-- empty --"
    ::= { hmSetupDhcpNetworkListEntry 16 }

-- {COLUMN} 1.3.6.1.4.1.248.32.18.2.10.20.1.17
hmSetupDhcpNetworkListEntry2ndMasterServer OBJECT-TYPE
    SYNTAX     IpAddress
    MAX-ACCESS read-write
    STATUS     current
    DESCRIPTION
            "-- empty --"
    ::= { hmSetupDhcpNetworkListEntry 17 }

-- {COLUMN} 1.3.6.1.4.1.248.32.18.2.10.20.1.18
hmSetupDhcpNetworkListEntry3rdMasterServer OBJECT-TYPE
    SYNTAX     IpAddress
    MAX-ACCESS read-write
    STATUS     current
    DESCRIPTION
            "-- empty --"
    ::= { hmSetupDhcpNetworkListEntry 18 }

-- {COLUMN} 1.3.6.1.4.1.248.32.18.2.10.20.1.19
hmSetupDhcpNetworkListEntry4thMasterServer OBJECT-TYPE
    SYNTAX     IpAddress
    MAX-ACCESS read-write
    STATUS     current
    DESCRIPTION
            "-- empty --"
    ::= { hmSetupDhcpNetworkListEntry 19 }

-- {TABLE} 1.3.6.1.4.1.248.32.18.2.10.21
hmSetupDhcpAdditionalOptionsTable OBJECT-TYPE
    SYNTAX     SEQUENCE OF HmSetupDhcpAdditionalOptionsEntry
    MAX-ACCESS not-accessible
    STATUS     current
    DESCRIPTION
            "-- empty --"
    ::= { hmSetupDhcp 21 }

-- {ROW} 1.3.6.1.4.1.248.32.18.2.10.21.1
hmSetupDhcpAdditionalOptionsEntry OBJECT-TYPE
    SYNTAX     HmSetupDhcpAdditionalOptionsEntry
    MAX-ACCESS not-accessible
    STATUS     current
    DESCRIPTION
            ""
    INDEX {
            hmSetupDhcpAdditionalOptionsEntryOptionNumber,
            hmSetupDhcpAdditionalOptionsEntryNetworkName
          }
    ::= { hmSetupDhcpAdditionalOptionsTable 1 }

HmSetupDhcpAdditionalOptionsEntry ::= SEQUENCE {
            hmSetupDhcpAdditionalOptionsEntryOptionNumber Integer32,
            hmSetupDhcpAdditionalOptionsEntryNetworkName DisplayString,
            hmSetupDhcpAdditionalOptionsEntryOptionValue DisplayString,
            hmSetupDhcpAdditionalOptionsEntryOptionType INTEGER
    }

-- {COLUMN} 1.3.6.1.4.1.248.32.18.2.10.21.1.1
hmSetupDhcpAdditionalOptionsEntryOptionNumber OBJECT-TYPE
    SYNTAX     Integer32 (0..255)
    MAX-ACCESS read-write
    STATUS     current
    DESCRIPTION
            "-- empty --"
    ::= { hmSetupDhcpAdditionalOptionsEntry 1 }

-- {COLUMN} 1.3.6.1.4.1.248.32.18.2.10.21.1.2
hmSetupDhcpAdditionalOptionsEntryNetworkName OBJECT-TYPE
    SYNTAX     DisplayString (SIZE(0..16))
    MAX-ACCESS read-write
    STATUS     current
    DESCRIPTION
            "-- empty --"
    ::= { hmSetupDhcpAdditionalOptionsEntry 2 }

-- {COLUMN} 1.3.6.1.4.1.248.32.18.2.10.21.1.3
hmSetupDhcpAdditionalOptionsEntryOptionValue OBJECT-TYPE
    SYNTAX     DisplayString (SIZE(0..251))
    MAX-ACCESS read-write
    STATUS     current
    DESCRIPTION
            "-- empty --"
    ::= { hmSetupDhcpAdditionalOptionsEntry 3 }

-- {COLUMN} 1.3.6.1.4.1.248.32.18.2.10.21.1.4
hmSetupDhcpAdditionalOptionsEntryOptionType OBJECT-TYPE
    SYNTAX     INTEGER {
                  eString (0),
                  eInteger32 (1),
                  eIpAddress (2),
                  eInteger16 (3),
                  eInteger8 (4)
            }
    MAX-ACCESS read-write
    STATUS     current
    DESCRIPTION
            "-- empty --"
    ::= { hmSetupDhcpAdditionalOptionsEntry 4 }

-- {SCALAR} 1.3.6.1.4.1.248.32.18.2.10.22
hmSetupDhcpVendorClassIdentifer OBJECT-TYPE
    SYNTAX     DisplayString (SIZE(0..63))
    MAX-ACCESS read-write
    STATUS     current
    DESCRIPTION
            "-- empty --"
    ::= { hmSetupDhcp 22 }

-- {NODE} 1.3.6.1.4.1.248.32.18.2.11
hmSetupConfig OBJECT IDENTIFIER ::= { hmSetup 11 }

-- {SCALAR} 1.3.6.1.4.1.248.32.18.2.11.1
hmSetupConfigLan OBJECT-TYPE
    SYNTAX     Integer32 (0..255)
    MAX-ACCESS read-only
    STATUS     current
    DESCRIPTION
            "-- empty --"
    ::= { hmSetupConfig 1 }

-- {SCALAR} 1.3.6.1.4.1.248.32.18.2.11.2
hmSetupConfigWan OBJECT-TYPE
    SYNTAX     Integer32 (0..255)
    MAX-ACCESS read-only
    STATUS     current
    DESCRIPTION
            "-- empty --"
    ::= { hmSetupConfig 2 }

-- {SCALAR} 1.3.6.1.4.1.248.32.18.2.11.3
hmSetupConfigPasswordRequiredForSnmpReadAccess OBJECT-TYPE
    SYNTAX     INTEGER {
                  eNo (0),
                  eYes (1)
            }
    MAX-ACCESS read-write
    STATUS     current
    DESCRIPTION
            "-- empty --"
    ::= { hmSetupConfig 3 }

-- {SCALAR} 1.3.6.1.4.1.248.32.18.2.11.4
hmSetupConfigMaximumConnections OBJECT-TYPE
    SYNTAX     Integer32 (0..255)
    MAX-ACCESS read-write
    STATUS     current
    DESCRIPTION
            "-- empty --"
    ::= { hmSetupConfig 4 }

-- {SCALAR} 1.3.6.1.4.1.248.32.18.2.11.5
hmSetupConfigConfigAgingMinutes OBJECT-TYPE
    SYNTAX     Integer32 (0..255)
    MAX-ACCESS read-write
    STATUS     current
    DESCRIPTION
            "-- empty --"
    ::= { hmSetupConfig 5 }

-- {SCALAR} 1.3.6.1.4.1.248.32.18.2.11.6
hmSetupConfigLanguage OBJECT-TYPE
    SYNTAX     INTEGER {
                  eEnglish (1),
                  eDeutsch (2)
            }
    MAX-ACCESS read-write
    STATUS     current
    DESCRIPTION
            "-- empty --"
    ::= { hmSetupConfig 6 }

-- {SCALAR} 1.3.6.1.4.1.248.32.18.2.11.7
hmSetupConfigLoginErrors OBJECT-TYPE
    SYNTAX     Integer32 (0..255)
    MAX-ACCESS read-write
    STATUS     current
    DESCRIPTION
            "-- empty --"
    ::= { hmSetupConfig 7 }

-- {SCALAR} 1.3.6.1.4.1.248.32.18.2.11.8
hmSetupConfigLockMinutes OBJECT-TYPE
    SYNTAX     Integer32 (0..255)
    MAX-ACCESS read-write
    STATUS     current
    DESCRIPTION
            "-- empty --"
    ::= { hmSetupConfig 8 }

-- {SCALAR} 1.3.6.1.4.1.248.32.18.2.11.10
hmSetupConfigDisplayContrast OBJECT-TYPE
    SYNTAX     INTEGER {
                  eC8 (0),
                  eC7 (1),
                  eC6 (2),
                  eC5 (3),
                  eC4 (4),
                  eC3 (5),
                  eC2 (6),
                  eC1 (7)
            }
    MAX-ACCESS read-write
    STATUS     current
    DESCRIPTION
            "-- empty --"
    ::= { hmSetupConfig 10 }

-- {SCALAR} 1.3.6.1.4.1.248.32.18.2.11.11
hmSetupConfigWlanConfig OBJECT-TYPE
    SYNTAX     Integer32 (0..255)
    MAX-ACCESS read-only
    STATUS     current
    DESCRIPTION
            "-- empty --"
    ::= { hmSetupConfig 11 }

-- {SCALAR} 1.3.6.1.4.1.248.32.18.2.11.12
hmSetupConfigWlanAuthenticationPagesOnly OBJECT-TYPE
    SYNTAX     INTEGER {
                  eNo (0),
                  eYes (1)
            }
    MAX-ACCESS read-write
    STATUS     current
    DESCRIPTION
            "-- empty --"
    ::= { hmSetupConfig 12 }

-- {NODE} 1.3.6.1.4.1.248.32.18.2.11.13
hmSetupConfigTftpClient OBJECT IDENTIFIER ::= { hmSetupConfig 13 }

-- {SCALAR} 1.3.6.1.4.1.248.32.18.2.11.13.1
hmSetupConfigTftpClientConfigAddress OBJECT-TYPE
    SYNTAX     DisplayString (SIZE(0..31))
    MAX-ACCESS read-only
    STATUS     obsolete
    DESCRIPTION
            "-- empty --"
    ::= { hmSetupConfigTftpClient 1 }

-- {SCALAR} 1.3.6.1.4.1.248.32.18.2.11.13.2
hmSetupConfigTftpClientConfigFilename OBJECT-TYPE
    SYNTAX     DisplayString (SIZE(0..63))
    MAX-ACCESS read-only
    STATUS     obsolete
    DESCRIPTION
            "-- empty --"
    ::= { hmSetupConfigTftpClient 2 }

-- {SCALAR} 1.3.6.1.4.1.248.32.18.2.11.13.3
hmSetupConfigTftpClientFirmwareAddress OBJECT-TYPE
    SYNTAX     DisplayString (SIZE(0..31))
    MAX-ACCESS read-only
    STATUS     obsolete
    DESCRIPTION
            "-- empty --"
    ::= { hmSetupConfigTftpClient 3 }

-- {SCALAR} 1.3.6.1.4.1.248.32.18.2.11.13.4
hmSetupConfigTftpClientFirmwareFilename OBJECT-TYPE
    SYNTAX     DisplayString (SIZE(0..63))
    MAX-ACCESS read-only
    STATUS     obsolete
    DESCRIPTION
            "-- empty --"
    ::= { hmSetupConfigTftpClient 4 }

-- {SCALAR} 1.3.6.1.4.1.248.32.18.2.11.13.5
hmSetupConfigTftpClientBytesPerHashmark OBJECT-TYPE
    SYNTAX     Integer32 (0..2147483647)
    MAX-ACCESS read-only
    STATUS     obsolete
    DESCRIPTION
            "-- empty --"
    ::= { hmSetupConfigTftpClient 5 }

-- {SCALAR} 1.3.6.1.4.1.248.32.18.2.11.13.6
hmSetupConfigTftpClientScriptAddress OBJECT-TYPE
    SYNTAX     DisplayString (SIZE(0..31))
    MAX-ACCESS read-only
    STATUS     obsolete
    DESCRIPTION
            "-- empty --"
    ::= { hmSetupConfigTftpClient 6 }

-- {SCALAR} 1.3.6.1.4.1.248.32.18.2.11.13.7
hmSetupConfigTftpClientScriptFilename OBJECT-TYPE
    SYNTAX     DisplayString (SIZE(0..63))
    MAX-ACCESS read-only
    STATUS     obsolete
    DESCRIPTION
            "-- empty --"
    ::= { hmSetupConfigTftpClient 7 }

-- {TABLE} 1.3.6.1.4.1.248.32.18.2.11.15
hmSetupConfigAccessTableTable OBJECT-TYPE
    SYNTAX     SEQUENCE OF HmSetupConfigAccessTableEntry
    MAX-ACCESS not-accessible
    STATUS     current
    DESCRIPTION
            "-- empty --"
    ::= { hmSetupConfig 15 }

-- {ROW} 1.3.6.1.4.1.248.32.18.2.11.15.1
hmSetupConfigAccessTableEntry OBJECT-TYPE
    SYNTAX     HmSetupConfigAccessTableEntry
    MAX-ACCESS not-accessible
    STATUS     current
    DESCRIPTION
            ""
    INDEX {
            hmSetupConfigAccessTableEntryIfc
          }
    ::= { hmSetupConfigAccessTableTable 1 }

HmSetupConfigAccessTableEntry ::= SEQUENCE {
            hmSetupConfigAccessTableEntryIfc INTEGER,
            hmSetupConfigAccessTableEntryTelnet INTEGER,
            hmSetupConfigAccessTableEntryTftp INTEGER,
            hmSetupConfigAccessTableEntryHttp INTEGER,
            hmSetupConfigAccessTableEntrySnmp INTEGER,
            hmSetupConfigAccessTableEntryHttps INTEGER,
            hmSetupConfigAccessTableEntryTelnetSsl INTEGER,
            hmSetupConfigAccessTableEntrySsh INTEGER,
            hmSetupConfigAccessTableEntryConfigSync INTEGER
    }

-- {COLUMN} 1.3.6.1.4.1.248.32.18.2.11.15.1.1
hmSetupConfigAccessTableEntryIfc OBJECT-TYPE
    SYNTAX     INTEGER {
                  eLan (1),
                  eWan (2),
                  eWlan (3)
            }
    MAX-ACCESS read-only
    STATUS     current
    DESCRIPTION
            "-- empty --"
    ::= { hmSetupConfigAccessTableEntry 1 }

-- {COLUMN} 1.3.6.1.4.1.248.32.18.2.11.15.1.2
hmSetupConfigAccessTableEntryTelnet OBJECT-TYPE
    SYNTAX     INTEGER {
                  eNo (0),
                  eYes (1),
                  eRead (4),
                  eVpn (16)
            }
    MAX-ACCESS read-write
    STATUS     current
    DESCRIPTION
            "-- empty --"
    ::= { hmSetupConfigAccessTableEntry 2 }

-- {COLUMN} 1.3.6.1.4.1.248.32.18.2.11.15.1.3
hmSetupConfigAccessTableEntryTftp OBJECT-TYPE
    SYNTAX     INTEGER {
                  eNo (0),
                  eYes (1),
                  eRead (4),
                  eVpn (16)
            }
    MAX-ACCESS read-write
    STATUS     current
    DESCRIPTION
            "-- empty --"
    ::= { hmSetupConfigAccessTableEntry 3 }

-- {COLUMN} 1.3.6.1.4.1.248.32.18.2.11.15.1.4
hmSetupConfigAccessTableEntryHttp OBJECT-TYPE
    SYNTAX     INTEGER {
                  eNo (0),
                  eYes (1),
                  eRead (4),
                  eVpn (16)
            }
    MAX-ACCESS read-write
    STATUS     current
    DESCRIPTION
            "-- empty --"
    ::= { hmSetupConfigAccessTableEntry 4 }

-- {COLUMN} 1.3.6.1.4.1.248.32.18.2.11.15.1.5
hmSetupConfigAccessTableEntrySnmp OBJECT-TYPE
    SYNTAX     INTEGER {
                  eNo (0),
                  eYes (1),
                  eRead (4),
                  eVpn (16)
            }
    MAX-ACCESS read-write
    STATUS     current
    DESCRIPTION
            "-- empty --"
    ::= { hmSetupConfigAccessTableEntry 5 }

-- {COLUMN} 1.3.6.1.4.1.248.32.18.2.11.15.1.6
hmSetupConfigAccessTableEntryHttps OBJECT-TYPE
    SYNTAX     INTEGER {
                  eNo (0),
                  eYes (1),
                  eRead (4),
                  eVpn (16)
            }
    MAX-ACCESS read-write
    STATUS     current
    DESCRIPTION
            "-- empty --"
    ::= { hmSetupConfigAccessTableEntry 6 }

-- {COLUMN} 1.3.6.1.4.1.248.32.18.2.11.15.1.7
hmSetupConfigAccessTableEntryTelnetSsl OBJECT-TYPE
    SYNTAX     INTEGER {
                  eNo (0),
                  eYes (1),
                  eRead (4),
                  eVpn (16)
            }
    MAX-ACCESS read-write
    STATUS     current
    DESCRIPTION
            "-- empty --"
    ::= { hmSetupConfigAccessTableEntry 7 }

-- {COLUMN} 1.3.6.1.4.1.248.32.18.2.11.15.1.8
hmSetupConfigAccessTableEntrySsh OBJECT-TYPE
    SYNTAX     INTEGER {
                  eNo (0),
                  eYes (1),
                  eRead (4),
                  eVpn (16)
            }
    MAX-ACCESS read-write
    STATUS     current
    DESCRIPTION
            "-- empty --"
    ::= { hmSetupConfigAccessTableEntry 8 }

-- {COLUMN} 1.3.6.1.4.1.248.32.18.2.11.15.1.10
hmSetupConfigAccessTableEntryConfigSync OBJECT-TYPE
    SYNTAX     INTEGER {
                  eNo (0),
                  eYes (1),
                  eRead (4),
                  eVpn (16)
            }
    MAX-ACCESS read-write
    STATUS     current
    DESCRIPTION
            "-- empty --"
    ::= { hmSetupConfigAccessTableEntry 10 }

-- {SCALAR} 1.3.6.1.4.1.248.32.18.2.11.16
hmSetupConfigScreenHeight OBJECT-TYPE
    SYNTAX     Integer32 (0..65535)
    MAX-ACCESS read-write
    STATUS     current
    DESCRIPTION
            "-- empty --"
    ::= { hmSetupConfig 16 }

-- {SCALAR} 1.3.6.1.4.1.248.32.18.2.11.17
hmSetupConfigPrompt OBJECT-TYPE
    SYNTAX     DisplayString (SIZE(0..31))
    MAX-ACCESS read-write
    STATUS     current
    DESCRIPTION
            "-- empty --"
    ::= { hmSetupConfig 17 }

-- {SCALAR} 1.3.6.1.4.1.248.32.18.2.11.18
hmSetupConfigLedTest OBJECT-TYPE
    SYNTAX     INTEGER {
                  eOff (0),
                  eRed (1),
                  eGreen (2),
                  eOrange (3),
                  eNoTest (255)
            }
    MAX-ACCESS read-write
    STATUS     current
    DESCRIPTION
            "-- empty --"
    ::= { hmSetupConfig 18 }

-- {TABLE} 1.3.6.1.4.1.248.32.18.2.11.20
hmSetupConfigCronTableTable OBJECT-TYPE
    SYNTAX     SEQUENCE OF HmSetupConfigCronTableEntry
    MAX-ACCESS not-accessible
    STATUS     current
    DESCRIPTION
            "-- empty --"
    ::= { hmSetupConfig 20 }

-- {ROW} 1.3.6.1.4.1.248.32.18.2.11.20.1
hmSetupConfigCronTableEntry OBJECT-TYPE
    SYNTAX     HmSetupConfigCronTableEntry
    MAX-ACCESS not-accessible
    STATUS     current
    DESCRIPTION
            ""
    INDEX {
            hmSetupConfigCronTableEntryIndex
          }
    ::= { hmSetupConfigCronTableTable 1 }

HmSetupConfigCronTableEntry ::= SEQUENCE {
            hmSetupConfigCronTableEntryIndex Integer32,
            hmSetupConfigCronTableEntryMinute DisplayString,
            hmSetupConfigCronTableEntryHour DisplayString,
            hmSetupConfigCronTableEntryDayofweek DisplayString,
            hmSetupConfigCronTableEntryDay DisplayString,
            hmSetupConfigCronTableEntryMonth DisplayString,
            hmSetupConfigCronTableEntryCommand DisplayString,
            hmSetupConfigCronTableEntryBase INTEGER,
            hmSetupConfigCronTableEntryActive INTEGER,
            hmSetupConfigCronTableEntryOwner DisplayString,
            hmSetupConfigCronTableEntryVariation Integer32,
            hmSetupConfigCronTableEntryComment DisplayString
    }

-- {COLUMN} 1.3.6.1.4.1.248.32.18.2.11.20.1.1
hmSetupConfigCronTableEntryIndex OBJECT-TYPE
    SYNTAX     Integer32 (0..65535)
    MAX-ACCESS read-write
    STATUS     current
    DESCRIPTION
            "-- empty --"
    ::= { hmSetupConfigCronTableEntry 1 }

-- {COLUMN} 1.3.6.1.4.1.248.32.18.2.11.20.1.2
hmSetupConfigCronTableEntryMinute OBJECT-TYPE
    SYNTAX     DisplayString (SIZE(0..50))
    MAX-ACCESS read-write
    STATUS     current
    DESCRIPTION
            "-- empty --"
    ::= { hmSetupConfigCronTableEntry 2 }

-- {COLUMN} 1.3.6.1.4.1.248.32.18.2.11.20.1.3
hmSetupConfigCronTableEntryHour OBJECT-TYPE
    SYNTAX     DisplayString (SIZE(0..50))
    MAX-ACCESS read-write
    STATUS     current
    DESCRIPTION
            "-- empty --"
    ::= { hmSetupConfigCronTableEntry 3 }

-- {COLUMN} 1.3.6.1.4.1.248.32.18.2.11.20.1.4
hmSetupConfigCronTableEntryDayofweek OBJECT-TYPE
    SYNTAX     DisplayString (SIZE(0..50))
    MAX-ACCESS read-write
    STATUS     current
    DESCRIPTION
            "-- empty --"
    ::= { hmSetupConfigCronTableEntry 4 }

-- {COLUMN} 1.3.6.1.4.1.248.32.18.2.11.20.1.5
hmSetupConfigCronTableEntryDay OBJECT-TYPE
    SYNTAX     DisplayString (SIZE(0..50))
    MAX-ACCESS read-write
    STATUS     current
    DESCRIPTION
            "-- empty --"
    ::= { hmSetupConfigCronTableEntry 5 }

-- {COLUMN} 1.3.6.1.4.1.248.32.18.2.11.20.1.6
hmSetupConfigCronTableEntryMonth OBJECT-TYPE
    SYNTAX     DisplayString (SIZE(0..50))
    MAX-ACCESS read-write
    STATUS     current
    DESCRIPTION
            "-- empty --"
    ::= { hmSetupConfigCronTableEntry 6 }

-- {COLUMN} 1.3.6.1.4.1.248.32.18.2.11.20.1.7
hmSetupConfigCronTableEntryCommand OBJECT-TYPE
    SYNTAX     DisplayString (SIZE(0..252))
    MAX-ACCESS read-write
    STATUS     current
    DESCRIPTION
            "-- empty --"
    ::= { hmSetupConfigCronTableEntry 7 }

-- {COLUMN} 1.3.6.1.4.1.248.32.18.2.11.20.1.8
hmSetupConfigCronTableEntryBase OBJECT-TYPE
    SYNTAX     INTEGER {
                  eRealTime (0),
                  eOperationTime (1)
            }
    MAX-ACCESS read-write
    STATUS     current
    DESCRIPTION
            "-- empty --"
    ::= { hmSetupConfigCronTableEntry 8 }

-- {COLUMN} 1.3.6.1.4.1.248.32.18.2.11.20.1.9
hmSetupConfigCronTableEntryActive OBJECT-TYPE
    SYNTAX     INTEGER {
                  eYes (0),
                  eNo (1)
            }
    MAX-ACCESS read-write
    STATUS     current
    DESCRIPTION
            "-- empty --"
    ::= { hmSetupConfigCronTableEntry 9 }

-- {COLUMN} 1.3.6.1.4.1.248.32.18.2.11.20.1.10
hmSetupConfigCronTableEntryOwner OBJECT-TYPE
    SYNTAX     DisplayString (SIZE(0..16))
    MAX-ACCESS read-write
    STATUS     current
    DESCRIPTION
            "-- empty --"
    ::= { hmSetupConfigCronTableEntry 10 }

-- {COLUMN} 1.3.6.1.4.1.248.32.18.2.11.20.1.11
hmSetupConfigCronTableEntryVariation OBJECT-TYPE
    SYNTAX     Integer32 (0..65535)
    MAX-ACCESS read-write
    STATUS     current
    DESCRIPTION
            "-- empty --"
    ::= { hmSetupConfigCronTableEntry 11 }

-- {COLUMN} 1.3.6.1.4.1.248.32.18.2.11.20.1.12
hmSetupConfigCronTableEntryComment OBJECT-TYPE
    SYNTAX     DisplayString (SIZE(0..63))
    MAX-ACCESS read-write
    STATUS     current
    DESCRIPTION
            "-- empty --"
    ::= { hmSetupConfigCronTableEntry 12 }

-- {TABLE} 1.3.6.1.4.1.248.32.18.2.11.21
hmSetupConfigAdminsTable OBJECT-TYPE
    SYNTAX     SEQUENCE OF HmSetupConfigAdminsEntry
    MAX-ACCESS not-accessible
    STATUS     current
    DESCRIPTION
            "-- empty --"
    ::= { hmSetupConfig 21 }

-- {ROW} 1.3.6.1.4.1.248.32.18.2.11.21.1
hmSetupConfigAdminsEntry OBJECT-TYPE
    SYNTAX     HmSetupConfigAdminsEntry
    MAX-ACCESS not-accessible
    STATUS     current
    DESCRIPTION
            ""
    INDEX {
            hmSetupConfigAdminsEntryAdministrator
          }
    ::= { hmSetupConfigAdminsTable 1 }

HmSetupConfigAdminsEntry ::= SEQUENCE {
            hmSetupConfigAdminsEntryAdministrator DisplayString,
            hmSetupConfigAdminsEntryPassword DisplayString,
            hmSetupConfigAdminsEntryFunctionRights BITS,
            hmSetupConfigAdminsEntryActive INTEGER,
            hmSetupConfigAdminsEntryAccessRights INTEGER
    }

-- {COLUMN} 1.3.6.1.4.1.248.32.18.2.11.21.1.1
hmSetupConfigAdminsEntryAdministrator OBJECT-TYPE
    SYNTAX     DisplayString (SIZE(0..16))
    MAX-ACCESS read-write
    STATUS     current
    DESCRIPTION
            "-- empty --"
    ::= { hmSetupConfigAdminsEntry 1 }

-- {COLUMN} 1.3.6.1.4.1.248.32.18.2.11.21.1.2
hmSetupConfigAdminsEntryPassword OBJECT-TYPE
    SYNTAX     DisplayString (SIZE(0..16))
    MAX-ACCESS read-write
    STATUS     current
    DESCRIPTION
            "-- empty --"
    ::= { hmSetupConfigAdminsEntry 2 }

-- {COLUMN} 1.3.6.1.4.1.248.32.18.2.11.21.1.3
hmSetupConfigAdminsEntryFunctionRights OBJECT-TYPE
    SYNTAX     BITS {
                  eCaWebInterface (7),
                  ePublicSpotConfigurationWizard (10),
                  ePublicSpotUserManagementWizard (11),
                  ePublicSpotXmlInterface (12),
                  eSshCommand (14),
                  eWlcProfileWizard (15),
                  eDynamicDnsWizard (17),
                  eRolloutWizard (18),
                  eWlanWizard (19),
                  ePublicSpotWizard (20),
                  eWtpAssignmentWizard (21),
                  eWlanLinktest (23),
                  eDeviceSearch (24),
                  eTimeSetting (25),
                  eLanlanWizard (26),
                  eRasWizard (27),
                  eProviderSelection (28),
                  eInternetWizard (29),
                  eSecurityWizard (30),
                  eBasicWizard (31)
            }
    MAX-ACCESS read-write
    STATUS     current
    DESCRIPTION
            "-- empty --"
    ::= { hmSetupConfigAdminsEntry 3 }

-- {COLUMN} 1.3.6.1.4.1.248.32.18.2.11.21.1.4
hmSetupConfigAdminsEntryActive OBJECT-TYPE
    SYNTAX     INTEGER {
                  eYes (0),
                  eNo (1)
            }
    MAX-ACCESS read-write
    STATUS     current
    DESCRIPTION
            "-- empty --"
    ::= { hmSetupConfigAdminsEntry 4 }

-- {COLUMN} 1.3.6.1.4.1.248.32.18.2.11.21.1.5
hmSetupConfigAdminsEntryAccessRights OBJECT-TYPE
    SYNTAX     INTEGER {
                  eAdminNp (-129),
                  eSupervisor (-1),
                  eNone (0),
                  eAdminRoLimit (8388608),
                  eAdminRwLimit (8388864),
                  eAdminRo (16777216),
                  eAdminRw (16777472)
            }
    MAX-ACCESS read-write
    STATUS     current
    DESCRIPTION
            "-- empty --"
    ::= { hmSetupConfigAdminsEntry 5 }

-- {SCALAR} 1.3.6.1.4.1.248.32.18.2.11.23
hmSetupConfigTelnetPort OBJECT-TYPE
    SYNTAX     Integer32 (0..65535)
    MAX-ACCESS read-write
    STATUS     current
    DESCRIPTION
            "-- empty --"
    ::= { hmSetupConfig 23 }

-- {SCALAR} 1.3.6.1.4.1.248.32.18.2.11.24
hmSetupConfigTelnetSslPort OBJECT-TYPE
    SYNTAX     Integer32 (0..65535)
    MAX-ACCESS read-write
    STATUS     current
    DESCRIPTION
            "-- empty --"
    ::= { hmSetupConfig 24 }

-- {SCALAR} 1.3.6.1.4.1.248.32.18.2.11.25
hmSetupConfigSshPort OBJECT-TYPE
    SYNTAX     Integer32 (0..65535)
    MAX-ACCESS read-write
    STATUS     current
    DESCRIPTION
            "-- empty --"
    ::= { hmSetupConfig 25 }

-- {TABLE} 1.3.6.1.4.1.248.32.18.2.11.26
hmSetupConfigSshAuthenticationMethodsTable OBJECT-TYPE
    SYNTAX     SEQUENCE OF HmSetupConfigSshAuthenticationMethodsEntry
    MAX-ACCESS not-accessible
    STATUS     current
    DESCRIPTION
            "-- empty --"
    ::= { hmSetupConfig 26 }

-- {ROW} 1.3.6.1.4.1.248.32.18.2.11.26.1
hmSetupConfigSshAuthenticationMethodsEntry OBJECT-TYPE
    SYNTAX     HmSetupConfigSshAuthenticationMethodsEntry
    MAX-ACCESS not-accessible
    STATUS     current
    DESCRIPTION
            ""
    INDEX {
            hmSetupConfigSshAuthenticationMethodsEntryIfc
          }
    ::= { hmSetupConfigSshAuthenticationMethodsTable 1 }

HmSetupConfigSshAuthenticationMethodsEntry ::= SEQUENCE {
            hmSetupConfigSshAuthenticationMethodsEntryIfc INTEGER,
            hmSetupConfigSshAuthenticationMethodsEntryMethods INTEGER
    }

-- {COLUMN} 1.3.6.1.4.1.248.32.18.2.11.26.1.1
hmSetupConfigSshAuthenticationMethodsEntryIfc OBJECT-TYPE
    SYNTAX     INTEGER {
                  eLan (1),
                  eWan (2),
                  eWlan (3)
            }
    MAX-ACCESS read-only
    STATUS     current
    DESCRIPTION
            "-- empty --"
    ::= { hmSetupConfigSshAuthenticationMethodsEntry 1 }

-- {COLUMN} 1.3.6.1.4.1.248.32.18.2.11.26.1.2
hmSetupConfigSshAuthenticationMethodsEntryMethods OBJECT-TYPE
    SYNTAX     INTEGER {
                  ePublicKey (1),
                  ePassword (2),
                  ePasswordPlusPublicKey (3),
                  eKeyboardInteractive (4),
                  eKeyboardInteractivePlusPublicKey (5),
                  ePasswordPlusKeyboardInteractive (6),
                  eAll (255)
            }
    MAX-ACCESS read-write
    STATUS     current
    DESCRIPTION
            "-- empty --"
    ::= { hmSetupConfigSshAuthenticationMethodsEntry 2 }

-- {TABLE} 1.3.6.1.4.1.248.32.18.2.11.27
hmSetupConfigPredefAdminsTable OBJECT-TYPE
    SYNTAX     SEQUENCE OF HmSetupConfigPredefAdminsEntry
    MAX-ACCESS not-accessible
    STATUS     current
    DESCRIPTION
            "-- empty --"
    ::= { hmSetupConfig 27 }

-- {ROW} 1.3.6.1.4.1.248.32.18.2.11.27.1
hmSetupConfigPredefAdminsEntry OBJECT-TYPE
    SYNTAX     HmSetupConfigPredefAdminsEntry
    MAX-ACCESS not-accessible
    STATUS     current
    DESCRIPTION
            ""
    INDEX {
            hmSetupConfigPredefAdminsEntryName
          }
    ::= { hmSetupConfigPredefAdminsTable 1 }

HmSetupConfigPredefAdminsEntry ::= SEQUENCE {
            hmSetupConfigPredefAdminsEntryName DisplayString
    }

-- {COLUMN} 1.3.6.1.4.1.248.32.18.2.11.27.1.1
hmSetupConfigPredefAdminsEntryName OBJECT-TYPE
    SYNTAX     DisplayString (SIZE(0..15))
    MAX-ACCESS read-only
    STATUS     current
    DESCRIPTION
            "-- empty --"
    ::= { hmSetupConfigPredefAdminsEntry 1 }

-- {NODE} 1.3.6.1.4.1.248.32.18.2.11.28
hmSetupConfigSsh OBJECT IDENTIFIER ::= { hmSetupConfig 28 }

-- {SCALAR} 1.3.6.1.4.1.248.32.18.2.11.28.1
hmSetupConfigSshCipherAlgorithms OBJECT-TYPE
    SYNTAX     BITS {
                  eAes256Ctr (19),
                  eAes192Ctr (20),
                  eAes128Ctr (21),
                  eAes256Cbc (22),
                  eAes192Cbc (23),
                  eAes128Cbc (24),
                  eBlowfishCtr (25),
                  eBlowfishCbc (26),
                  eArcfour256 (27),
                  eArcfour128 (28),
                  eArcfour (29),
                  e3desCtr (30),
                  e3desCbc (31)
            }
    MAX-ACCESS read-write
    STATUS     current
    DESCRIPTION
            "-- empty --"
    ::= { hmSetupConfigSsh 1 }

-- {SCALAR} 1.3.6.1.4.1.248.32.18.2.11.28.2
hmSetupConfigSshMacAlgorithms OBJECT-TYPE
    SYNTAX     BITS {
                  eHmacSha2512 (24),
                  eHmacSha251296 (25),
                  eHmacSha2256 (26),
                  eHmacSha225696 (27),
                  eHmacSha1 (28),
                  eHmacSha196 (29),
                  eHmacMd5 (30),
                  eHmacMd596 (31)
            }
    MAX-ACCESS read-write
    STATUS     current
    DESCRIPTION
            "-- empty --"
    ::= { hmSetupConfigSsh 2 }

-- {SCALAR} 1.3.6.1.4.1.248.32.18.2.11.28.3
hmSetupConfigSshKeyExchangeAlgorithms OBJECT-TYPE
    SYNTAX     BITS {
                  eCurve25519Sha256 (26),
                  eEcdhSha2 (27),
                  eDiffieHellmanGroupExchangeSha256 (28),
                  eDiffieHellmanGroupExchangeSha1 (29),
                  eDiffieHellmanGroup14Sha1 (30),
                  eDiffieHellmanGroup1Sha1 (31)
            }
    MAX-ACCESS read-write
    STATUS     current
    DESCRIPTION
            "-- empty --"
    ::= { hmSetupConfigSsh 3 }

-- {SCALAR} 1.3.6.1.4.1.248.32.18.2.11.28.4
hmSetupConfigSshHostkeyAlgorithms OBJECT-TYPE
    SYNTAX     BITS {
                  eSshEd25519 (28),
                  eEcdsaSha2 (29),
                  eSshDss (30),
                  eSshRsa (31)
            }
    MAX-ACCESS read-write
    STATUS     current
    DESCRIPTION
            "-- empty --"
    ::= { hmSetupConfigSsh 4 }

-- {SCALAR} 1.3.6.1.4.1.248.32.18.2.11.28.5
hmSetupConfigSshMinHostkeyLength OBJECT-TYPE
    SYNTAX     Integer32 (0..65535)
    MAX-ACCESS read-write
    STATUS     current
    DESCRIPTION
            "-- empty --"
    ::= { hmSetupConfigSsh 5 }

-- {SCALAR} 1.3.6.1.4.1.248.32.18.2.11.28.6
hmSetupConfigSshMaxHostkeyLength OBJECT-TYPE
    SYNTAX     Integer32 (0..65535)
    MAX-ACCESS read-write
    STATUS     current
    DESCRIPTION
            "-- empty --"
    ::= { hmSetupConfigSsh 6 }

-- {SCALAR} 1.3.6.1.4.1.248.32.18.2.11.28.7
hmSetupConfigSshDhGroups OBJECT-TYPE
    SYNTAX     BITS {
                  eGroup16 (27),
                  eGroup15 (28),
                  eGroup14 (29),
                  eGroup5 (30),
                  eGroup1 (31)
            }
    MAX-ACCESS read-write
    STATUS     current
    DESCRIPTION
            "-- empty --"
    ::= { hmSetupConfigSsh 7 }

-- {SCALAR} 1.3.6.1.4.1.248.32.18.2.11.28.8
hmSetupConfigSshCompression OBJECT-TYPE
    SYNTAX     INTEGER {
                  eNo (0),
                  eYes (1)
            }
    MAX-ACCESS read-write
    STATUS     current
    DESCRIPTION
            "-- empty --"
    ::= { hmSetupConfigSsh 8 }

-- {SCALAR} 1.3.6.1.4.1.248.32.18.2.11.28.9
hmSetupConfigSshEllipticCurves OBJECT-TYPE
    SYNTAX     BITS {
                  eNistp521 (29),
                  eNistp384 (30),
                  eNistp256 (31)
            }
    MAX-ACCESS read-write
    STATUS     current
    DESCRIPTION
            "-- empty --"
    ::= { hmSetupConfigSsh 9 }

-- {NODE} 1.3.6.1.4.1.248.32.18.2.11.28.10
hmSetupConfigSshSftpServer OBJECT IDENTIFIER ::= { hmSetupConfigSsh 10 }

-- {SCALAR} 1.3.6.1.4.1.248.32.18.2.11.28.10.1
hmSetupConfigSshSftpServerOperating OBJECT-TYPE
    SYNTAX     INTEGER {
                  eNo (0),
                  eYes (1)
            }
    MAX-ACCESS read-write
    STATUS     current
    DESCRIPTION
            "-- empty --"
    ::= { hmSetupConfigSshSftpServer 1 }

-- {SCALAR} 1.3.6.1.4.1.248.32.18.2.11.28.11
hmSetupConfigSshKeepaliveInterval OBJECT-TYPE
    SYNTAX     Integer32 (0..2147483647)
    MAX-ACCESS read-write
    STATUS     current
    DESCRIPTION
            "-- empty --"
    ::= { hmSetupConfigSsh 11 }

-- {NODE} 1.3.6.1.4.1.248.32.18.2.11.29
hmSetupConfigTelnetSsl OBJECT IDENTIFIER ::= { hmSetupConfig 29 }

-- {SCALAR} 1.3.6.1.4.1.248.32.18.2.11.29.2
hmSetupConfigTelnetSslVersions OBJECT-TYPE
    SYNTAX     BITS {
                  eTlsv12 (28),
                  eTlsv11 (29),
                  eTlsv1 (30),
                  eSslv3 (31)
            }
    MAX-ACCESS read-write
    STATUS     current
    DESCRIPTION
            "-- empty --"
    ::= { hmSetupConfigTelnetSsl 2 }

-- {SCALAR} 1.3.6.1.4.1.248.32.18.2.11.29.3
hmSetupConfigTelnetSslKeyexAlgorithms OBJECT-TYPE
    SYNTAX     BITS {
                  eEcdhe (27),
                  eDhe (29),
                  eRsa (31)
            }
    MAX-ACCESS read-write
    STATUS     current
    DESCRIPTION
            "-- empty --"
    ::= { hmSetupConfigTelnetSsl 3 }

-- {SCALAR} 1.3.6.1.4.1.248.32.18.2.11.29.4
hmSetupConfigTelnetSslCryptoAlgorithms OBJECT-TYPE
    SYNTAX     BITS {
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { hmSetupConfigTelnetSsl 4 }

-- {SCALAR} 1.3.6.1.4.1.248.32.18.2.11.29.5
hmSetupConfigTelnetSslHashAlgorithms OBJECT-TYPE
    SYNTAX     BITS {
                  eSha2384 (26),
                  eSha2256 (27),
                  eSha1 (29),
                  eMd5 (30)
            }
    MAX-ACCESS read-write
    STATUS     current
    DESCRIPTION
            "-- empty --"
    ::= { hmSetupConfigTelnetSsl 5 }

-- {SCALAR} 1.3.6.1.4.1.248.32.18.2.11.29.6
hmSetupConfigTelnetSslPreferPfs OBJECT-TYPE
    SYNTAX     BITS {
                  eNo (0),
                  eYes (7)
            }
    MAX-ACCESS read-write
    STATUS     current
    DESCRIPTION
            "-- empty --"
    ::= { hmSetupConfigTelnetSsl 6 }

-- {SCALAR} 1.3.6.1.4.1.248.32.18.2.11.29.7
hmSetupConfigTelnetSslRenegotiations OBJECT-TYPE
    SYNTAX     INTEGER {
                  eForbidden (0),
                  eAllowed (1),
                  eIgnored (2)
            }
    MAX-ACCESS read-write
    STATUS     current
    DESCRIPTION
            "-- empty --"
    ::= { hmSetupConfigTelnetSsl 7 }

-- {SCALAR} 1.3.6.1.4.1.248.32.18.2.11.29.10
hmSetupConfigTelnetSslPortNew OBJECT-TYPE
    SYNTAX     Integer32 (0..65535)
    MAX-ACCESS read-write
    STATUS     current
    DESCRIPTION
            "TCP port device is listening on for Telnet/SSL"
    ::= { hmSetupConfigTelnetSsl 10 }

-- {SCALAR} 1.3.6.1.4.1.248.32.18.2.11.32
hmSetupConfigResetButton OBJECT-TYPE
    SYNTAX     INTEGER {
                  eIgnore (0),
                  eBootOnly (1),
                  eResetOrBoot (2)
            }
    MAX-ACCESS read-write
    STATUS     current
    DESCRIPTION
            "-- empty --"
    ::= { hmSetupConfig 32 }

-- {SCALAR} 1.3.6.1.4.1.248.32.18.2.11.33
hmSetupConfigOutbandAgingMinutes OBJECT-TYPE
    SYNTAX     Integer32 (0..255)
    MAX-ACCESS read-write
    STATUS     current
    DESCRIPTION
            "-- empty --"
    ::= { hmSetupConfig 33 }

-- {SCALAR} 1.3.6.1.4.1.248.32.18.2.11.34
hmSetupConfigTelnetOperating OBJECT-TYPE
    SYNTAX     INTEGER {
                  eNo (0),
                  eYes (1)
            }
    MAX-ACCESS read-write
    STATUS     current
    DESCRIPTION
            "-- empty --"
    ::= { hmSetupConfig 34 }

-- {NODE} 1.3.6.1.4.1.248.32.18.2.11.35
hmSetupConfigMonitortrace OBJECT IDENTIFIER ::= { hmSetupConfig 35 }

-- {SCALAR} 1.3.6.1.4.1.248.32.18.2.11.35.1
hmSetupConfigMonitortraceTracemask1 OBJECT-TYPE
    SYNTAX     Integer32 (0..2147483647)
    MAX-ACCESS read-only
    STATUS     current
    DESCRIPTION
            "-- empty --"
    ::= { hmSetupConfigMonitortrace 1 }

-- {SCALAR} 1.3.6.1.4.1.248.32.18.2.11.35.2
hmSetupConfigMonitortraceTracemask2 OBJECT-TYPE
    SYNTAX     Integer32 (0..2147483647)
    MAX-ACCESS read-only
    STATUS     current
    DESCRIPTION
            "-- empty --"
    ::= { hmSetupConfigMonitortrace 2 }

-- {SCALAR} 1.3.6.1.4.1.248.32.18.2.11.39
hmSetupConfigLicenseExpiryEmail OBJECT-TYPE
    SYNTAX     DisplayString (SIZE(0..63))
    MAX-ACCESS read-write
    STATUS     current
    DESCRIPTION
            "-- empty --"
    ::= { hmSetupConfig 39 }

-- {SCALAR} 1.3.6.1.4.1.248.32.18.2.11.40
hmSetupConfigCrashMessage OBJECT-TYPE
    SYNTAX     DisplayString (SIZE(0..32))
    MAX-ACCESS read-write
    STATUS     current
    DESCRIPTION
            "-- empty --"
    ::= { hmSetupConfig 40 }

-- {SCALAR} 1.3.6.1.4.1.248.32.18.2.11.41
hmSetupConfigAdminGender OBJECT-TYPE
    SYNTAX     INTEGER {
                  eUnknown (0),
                  eMale (1),
                  eFemale (2),
                  eGeek (3)
            }
    MAX-ACCESS read-write
    STATUS     current
    DESCRIPTION
            "-- empty --"
    ::= { hmSetupConfig 41 }

-- {SCALAR} 1.3.6.1.4.1.248.32.18.2.11.42
hmSetupConfigAssertAction OBJECT-TYPE
    SYNTAX     INTEGER {
                  eLogOnly (0),
                  eReboot (1)
            }
    MAX-ACCESS read-write
    STATUS     current
    DESCRIPTION
            "-- empty --"
    ::= { hmSetupConfig 42 }

-- {TABLE} 1.3.6.1.4.1.248.32.18.2.11.43
hmSetupConfigFunctionKeysTable OBJECT-TYPE
    SYNTAX     SEQUENCE OF HmSetupConfigFunctionKeysEntry
    MAX-ACCESS not-accessible
    STATUS     current
    DESCRIPTION
            "-- empty --"
    ::= { hmSetupConfig 43 }

-- {ROW} 1.3.6.1.4.1.248.32.18.2.11.43.1
hmSetupConfigFunctionKeysEntry OBJECT-TYPE
    SYNTAX     HmSetupConfigFunctionKeysEntry
    MAX-ACCESS not-accessible
    STATUS     current
    DESCRIPTION
            ""
    INDEX {
            hmSetupConfigFunctionKeysEntryKey
          }
    ::= { hmSetupConfigFunctionKeysTable 1 }

HmSetupConfigFunctionKeysEntry ::= SEQUENCE {
            hmSetupConfigFunctionKeysEntryKey INTEGER,
            hmSetupConfigFunctionKeysEntryMapping DisplayString
    }

-- {COLUMN} 1.3.6.1.4.1.248.32.18.2.11.43.1.1
hmSetupConfigFunctionKeysEntryKey OBJECT-TYPE
    SYNTAX     INTEGER {
                  eF1 (1),
                  eF2 (2),
                  eF3 (3),
                  eF4 (4),
                  eF5 (5),
                  eF6 (6),
                  eF7 (7),
                  eF8 (8),
                  eF9 (9),
                  eF10 (10),
                  eF11 (11),
                  eF12 (12)
            }
    MAX-ACCESS read-write
    STATUS     current
    DESCRIPTION
            "-- empty --"
    ::= { hmSetupConfigFunctionKeysEntry 1 }

-- {COLUMN} 1.3.6.1.4.1.248.32.18.2.11.43.1.2
hmSetupConfigFunctionKeysEntryMapping OBJECT-TYPE
    SYNTAX     DisplayString (SIZE(0..99))
    MAX-ACCESS read-write
    STATUS     current
    DESCRIPTION
            "-- empty --"
    ::= { hmSetupConfigFunctionKeysEntry 2 }

-- {SCALAR} 1.3.6.1.4.1.248.32.18.2.11.45
hmSetupConfigConfigDate OBJECT-TYPE
    SYNTAX     Counter32
    MAX-ACCESS read-only
    STATUS     current
    DESCRIPTION
            "-- empty --"
    ::= { hmSetupConfig 45 }

-- {NODE} 1.3.6.1.4.1.248.32.18.2.11.50
hmSetupConfigLl2m OBJECT IDENTIFIER ::= { hmSetupConfig 50 }

-- {SCALAR} 1.3.6.1.4.1.248.32.18.2.11.50.1
hmSetupConfigLl2mOperating OBJECT-TYPE
    SYNTAX     INTEGER {
                  eNo (0),
                  eYes (1)
            }
    MAX-ACCESS read-write
    STATUS     current
    DESCRIPTION
            "-- empty --"
    ::= { hmSetupConfigLl2m 1 }

-- {SCALAR} 1.3.6.1.4.1.248.32.18.2.11.50.2
hmSetupConfigLl2mTimeLimit OBJECT-TYPE
    SYNTAX     Integer32 (0..2147483647)
    MAX-ACCESS read-write
    STATUS     current
    DESCRIPTION
            "-- empty --"
    ::= { hmSetupConfigLl2m 2 }

-- {NODE} 1.3.6.1.4.1.248.32.18.2.11.51
hmSetupConfigSync OBJECT IDENTIFIER ::= { hmSetupConfig 51 }

-- {SCALAR} 1.3.6.1.4.1.248.32.18.2.11.51.1
hmSetupConfigSyncOperating OBJECT-TYPE
    SYNTAX     INTEGER {
                  eNo (0),
                  eYes (1)
            }
    MAX-ACCESS read-write
    STATUS     current
    DESCRIPTION
            "-- empty --"
    ::= { hmSetupConfigSync 1 }

-- {NODE} 1.3.6.1.4.1.248.32.18.2.11.51.2
hmSetupConfigSyncNewCluster OBJECT IDENTIFIER ::= { hmSetupConfigSync 2 }

-- {SCALAR} 1.3.6.1.4.1.248.32.18.2.11.51.2.1
hmSetupConfigSyncNewClusterName OBJECT-TYPE
    SYNTAX     DisplayString (SIZE(0..254))
    MAX-ACCESS read-write
    STATUS     current
    DESCRIPTION
            "-- empty --"
    ::= { hmSetupConfigSyncNewCluster 1 }

-- {TABLE} 1.3.6.1.4.1.248.32.18.2.11.51.2.2
hmSetupConfigSyncNewClusterGroupMembersTable OBJECT-TYPE
    SYNTAX     SEQUENCE OF HmSetupConfigSyncNewClusterGroupMembersEntry
    MAX-ACCESS not-accessible
    STATUS     current
    DESCRIPTION
            "-- empty --"
    ::= { hmSetupConfigSyncNewCluster 2 }

-- {ROW} 1.3.6.1.4.1.248.32.18.2.11.51.2.2.1
hmSetupConfigSyncNewClusterGroupMembersEntry OBJECT-TYPE
    SYNTAX     HmSetupConfigSyncNewClusterGroupMembersEntry
    MAX-ACCESS not-accessible
    STATUS     current
    DESCRIPTION
            ""
    INDEX {
            hmSetupConfigSyncNewClusterGroupMembersEntryIdx
          }
    ::= { hmSetupConfigSyncNewClusterGroupMembersTable 1 }

HmSetupConfigSyncNewClusterGroupMembersEntry ::= SEQUENCE {
            hmSetupConfigSyncNewClusterGroupMembersEntryIdx Integer32,
            hmSetupConfigSyncNewClusterGroupMembersEntryAddress DisplayString
    }

-- {COLUMN} 1.3.6.1.4.1.248.32.18.2.11.51.2.2.1.1
hmSetupConfigSyncNewClusterGroupMembersEntryIdx OBJECT-TYPE
    SYNTAX     Integer32 (0..65535)
    MAX-ACCESS read-write
    STATUS     current
    DESCRIPTION
            "-- empty --"
    ::= { hmSetupConfigSyncNewClusterGroupMembersEntry 1 }

-- {COLUMN} 1.3.6.1.4.1.248.32.18.2.11.51.2.2.1.2
hmSetupConfigSyncNewClusterGroupMembersEntryAddress OBJECT-TYPE
    SYNTAX     DisplayString (SIZE(0..63))
    MAX-ACCESS read-write
    STATUS     current
    DESCRIPTION
            "-- empty --"
    ::= { hmSetupConfigSyncNewClusterGroupMembersEntry 2 }

-- {TABLE} 1.3.6.1.4.1.248.32.18.2.11.51.2.3
hmSetupConfigSyncNewClusterMenuNodesTable OBJECT-TYPE
    SYNTAX     SEQUENCE OF HmSetupConfigSyncNewClusterMenuNodesEntry
    MAX-ACCESS not-accessible
    STATUS     current
    DESCRIPTION
            "-- empty --"
    ::= { hmSetupConfigSyncNewCluster 3 }

-- {ROW} 1.3.6.1.4.1.248.32.18.2.11.51.2.3.1
hmSetupConfigSyncNewClusterMenuNodesEntry OBJECT-TYPE
    SYNTAX     HmSetupConfigSyncNewClusterMenuNodesEntry
    MAX-ACCESS not-accessible
    STATUS     current
    DESCRIPTION
            ""
    INDEX {
            hmSetupConfigSyncNewClusterMenuNodesEntryIdx
          }
    ::= { hmSetupConfigSyncNewClusterMenuNodesTable 1 }

HmSetupConfigSyncNewClusterMenuNodesEntry ::= SEQUENCE {
            hmSetupConfigSyncNewClusterMenuNodesEntryIdx Integer32,
            hmSetupConfigSyncNewClusterMenuNodesEntryInclude INTEGER,
            hmSetupConfigSyncNewClusterMenuNodesEntryPath DisplayString,
            hmSetupConfigSyncNewClusterMenuNodesEntrySnmpOid DisplayString
    }

-- {COLUMN} 1.3.6.1.4.1.248.32.18.2.11.51.2.3.1.1
hmSetupConfigSyncNewClusterMenuNodesEntryIdx OBJECT-TYPE
    SYNTAX     Integer32 (0..65535)
    MAX-ACCESS read-write
    STATUS     current
    DESCRIPTION
            "-- empty --"
    ::= { hmSetupConfigSyncNewClusterMenuNodesEntry 1 }

-- {COLUMN} 1.3.6.1.4.1.248.32.18.2.11.51.2.3.1.2
hmSetupConfigSyncNewClusterMenuNodesEntryInclude OBJECT-TYPE
    SYNTAX     INTEGER {
                  eExclude (0),
                  eInclude (1)
            }
    MAX-ACCESS read-write
    STATUS     current
    DESCRIPTION
            "-- empty --"
    ::= { hmSetupConfigSyncNewClusterMenuNodesEntry 2 }

-- {COLUMN} 1.3.6.1.4.1.248.32.18.2.11.51.2.3.1.3
hmSetupConfigSyncNewClusterMenuNodesEntryPath OBJECT-TYPE
    SYNTAX     DisplayString (SIZE(0..127))
    MAX-ACCESS read-write
    STATUS     current
    DESCRIPTION
            "-- empty --"
    ::= { hmSetupConfigSyncNewClusterMenuNodesEntry 3 }

-- {COLUMN} 1.3.6.1.4.1.248.32.18.2.11.51.2.3.1.4
hmSetupConfigSyncNewClusterMenuNodesEntrySnmpOid OBJECT-TYPE
    SYNTAX     DisplayString (SIZE(0..63))
    MAX-ACCESS read-only
    STATUS     current
    DESCRIPTION
            "-- empty --"
    ::= { hmSetupConfigSyncNewClusterMenuNodesEntry 4 }

-- {TABLE} 1.3.6.1.4.1.248.32.18.2.11.51.2.4
hmSetupConfigSyncNewClusterIgnoredRowsTable OBJECT-TYPE
    SYNTAX     SEQUENCE OF HmSetupConfigSyncNewClusterIgnoredRowsEntry
    MAX-ACCESS not-accessible
    STATUS     current
    DESCRIPTION
            "-- empty --"
    ::= { hmSetupConfigSyncNewCluster 4 }

-- {ROW} 1.3.6.1.4.1.248.32.18.2.11.51.2.4.1
hmSetupConfigSyncNewClusterIgnoredRowsEntry OBJECT-TYPE
    SYNTAX     HmSetupConfigSyncNewClusterIgnoredRowsEntry
    MAX-ACCESS not-accessible
    STATUS     current
    DESCRIPTION
            ""
    INDEX {
            hmSetupConfigSyncNewClusterIgnoredRowsEntryIdx
          }
    ::= { hmSetupConfigSyncNewClusterIgnoredRowsTable 1 }

HmSetupConfigSyncNewClusterIgnoredRowsEntry ::= SEQUENCE {
            hmSetupConfigSyncNewClusterIgnoredRowsEntryIdx Integer32,
            hmSetupConfigSyncNewClusterIgnoredRowsEntryRowIndex DisplayString,
            hmSetupConfigSyncNewClusterIgnoredRowsEntryPath DisplayString,
            hmSetupConfigSyncNewClusterIgnoredRowsEntrySnmpOid DisplayString
    }

-- {COLUMN} 1.3.6.1.4.1.248.32.18.2.11.51.2.4.1.1
hmSetupConfigSyncNewClusterIgnoredRowsEntryIdx OBJECT-TYPE
    SYNTAX     Integer32 (0..65535)
    MAX-ACCESS read-write
    STATUS     current
    DESCRIPTION
            "-- empty --"
    ::= { hmSetupConfigSyncNewClusterIgnoredRowsEntry 1 }

-- {COLUMN} 1.3.6.1.4.1.248.32.18.2.11.51.2.4.1.2
hmSetupConfigSyncNewClusterIgnoredRowsEntryRowIndex OBJECT-TYPE
    SYNTAX     DisplayString (SIZE(0..127))
    MAX-ACCESS read-write
    STATUS     current
    DESCRIPTION
            "-- empty --"
    ::= { hmSetupConfigSyncNewClusterIgnoredRowsEntry 2 }

-- {COLUMN} 1.3.6.1.4.1.248.32.18.2.11.51.2.4.1.3
hmSetupConfigSyncNewClusterIgnoredRowsEntryPath OBJECT-TYPE
    SYNTAX     DisplayString (SIZE(0..127))
    MAX-ACCESS read-write
    STATUS     current
    DESCRIPTION
            "-- empty --"
    ::= { hmSetupConfigSyncNewClusterIgnoredRowsEntry 3 }

-- {COLUMN} 1.3.6.1.4.1.248.32.18.2.11.51.2.4.1.4
hmSetupConfigSyncNewClusterIgnoredRowsEntrySnmpOid OBJECT-TYPE
    SYNTAX     DisplayString (SIZE(0..63))
    MAX-ACCESS read-only
    STATUS     current
    DESCRIPTION
            "-- empty --"
    ::= { hmSetupConfigSyncNewClusterIgnoredRowsEntry 4 }

-- {SCALAR} 1.3.6.1.4.1.248.32.18.2.11.51.2.5
hmSetupConfigSyncNewClusterLaunch OBJECT-TYPE
    SYNTAX     DisplayString
    MAX-ACCESS read-write
    STATUS     current
    DESCRIPTION
            "-- empty --"
    ::= { hmSetupConfigSyncNewCluster 5 }

-- {NODE} 1.3.6.1.4.1.248.32.18.2.11.51.3
hmSetupConfigSyncTlsConnections OBJECT IDENTIFIER ::= { hmSetupConfigSync 3 }

-- {SCALAR} 1.3.6.1.4.1.248.32.18.2.11.51.3.1
hmSetupConfigSyncTlsConnectionsPort OBJECT-TYPE
    SYNTAX     Integer32 (0..65535)
    MAX-ACCESS read-write
    STATUS     current
    DESCRIPTION
            "-- empty --"
    ::= { hmSetupConfigSyncTlsConnections 1 }

-- {SCALAR} 1.3.6.1.4.1.248.32.18.2.11.51.3.2
hmSetupConfigSyncTlsConnectionsLoopbackAddress OBJECT-TYPE
    SYNTAX     DisplayString (SIZE(0..39))
    MAX-ACCESS read-write
    STATUS     current
    DESCRIPTION
            "-- empty --"
    ::= { hmSetupConfigSyncTlsConnections 2 }

-- {NODE} 1.3.6.1.4.1.248.32.18.2.11.51.4
hmSetupConfigSyncRenewSnapshot OBJECT IDENTIFIER ::= { hmSetupConfigSync 4 }

-- {SCALAR} 1.3.6.1.4.1.248.32.18.2.11.51.4.1
hmSetupConfigSyncRenewSnapshotModificationLimit OBJECT-TYPE
    SYNTAX     Integer32 (0..2147483647)
    MAX-ACCESS read-write
    STATUS     current
    DESCRIPTION
            "-- empty --"
    ::= { hmSetupConfigSyncRenewSnapshot 1 }

-- {SCALAR} 1.3.6.1.4.1.248.32.18.2.11.51.4.2
hmSetupConfigSyncRenewSnapshotKeptModifications OBJECT-TYPE
    SYNTAX     Integer32 (0..2147483647)
    MAX-ACCESS read-write
    STATUS     current
    DESCRIPTION
            "-- empty --"
    ::= { hmSetupConfigSyncRenewSnapshot 2 }

-- {SCALAR} 1.3.6.1.4.1.248.32.18.2.11.51.4.3
hmSetupConfigSyncRenewSnapshotRenewSnapshot OBJECT-TYPE
    SYNTAX     DisplayString
    MAX-ACCESS read-write
    STATUS     current
    DESCRIPTION
            "-- empty --"
    ::= { hmSetupConfigSyncRenewSnapshot 3 }

-- {NODE} 1.3.6.1.4.1.248.32.18.2.11.51.5
hmSetupConfigSyncLocalConfig OBJECT IDENTIFIER ::= { hmSetupConfigSync 5 }

-- {SCALAR} 1.3.6.1.4.1.248.32.18.2.11.51.5.1
hmSetupConfigSyncLocalConfigDetectedModificationsTabSize OBJECT-TYPE
    SYNTAX     Integer32 (0..2147483647)
    MAX-ACCESS read-write
    STATUS     current
    DESCRIPTION
            "-- empty --"
    ::= { hmSetupConfigSyncLocalConfig 1 }

-- {SCALAR} 1.3.6.1.4.1.248.32.18.2.11.51.5.2
hmSetupConfigSyncLocalConfigAppliedModificationsTabSize OBJECT-TYPE
    SYNTAX     Integer32 (0..2147483647)
    MAX-ACCESS read-write
    STATUS     current
    DESCRIPTION
            "-- empty --"
    ::= { hmSetupConfigSyncLocalConfig 2 }

-- {SCALAR} 1.3.6.1.4.1.248.32.18.2.11.60
hmSetupConfigCpuLoadInterval OBJECT-TYPE
    SYNTAX     INTEGER {
                  eT1s (1),
                  eT5s (5),
                  eT60s (60),
                  eT300s (300)
            }
    MAX-ACCESS read-write
    STATUS     current
    DESCRIPTION
            "-- empty --"
    ::= { hmSetupConfig 60 }

-- {SCALAR} 1.3.6.1.4.1.248.32.18.2.11.65
hmSetupConfigErrorAgingMinutes OBJECT-TYPE
    SYNTAX     Integer32 (0..255)
    MAX-ACCESS read-write
    STATUS     current
    DESCRIPTION
            "-- empty --"
    ::= { hmSetupConfig 65 }

-- {SCALAR} 1.3.6.1.4.1.248.32.18.2.11.73
hmSetupConfigSortMenu OBJECT-TYPE
    SYNTAX     INTEGER {
                  eNo (0),
                  eYes (1)
            }
    MAX-ACCESS read-write
    STATUS     current
    DESCRIPTION
            "-- empty --"
    ::= { hmSetupConfig 73 }

-- {SCALAR} 1.3.6.1.4.1.248.32.18.2.11.80
hmSetupConfigAuthentication OBJECT-TYPE
    SYNTAX     INTEGER {
                  eIntern (0),
                  eRadius (1),
                  eTacacsPlus (2)
            }
    MAX-ACCESS read-write
    STATUS     current
    DESCRIPTION
            "-- empty --"
    ::= { hmSetupConfig 80 }

-- {NODE} 1.3.6.1.4.1.248.32.18.2.11.81
hmSetupConfigRadius OBJECT IDENTIFIER ::= { hmSetupConfig 81 }

-- {TABLE} 1.3.6.1.4.1.248.32.18.2.11.81.1
hmSetupConfigRadiusServerTable OBJECT-TYPE
    SYNTAX     SEQUENCE OF HmSetupConfigRadiusServerEntry
    MAX-ACCESS not-accessible
    STATUS     current
    DESCRIPTION
            "-- empty --"
    ::= { hmSetupConfigRadius 1 }

-- {ROW} 1.3.6.1.4.1.248.32.18.2.11.81.1.1
hmSetupConfigRadiusServerEntry OBJECT-TYPE
    SYNTAX     HmSetupConfigRadiusServerEntry
    MAX-ACCESS not-accessible
    STATUS     current
    DESCRIPTION
            ""
    INDEX {
            hmSetupConfigRadiusServerEntryName
          }
    ::= { hmSetupConfigRadiusServerTable 1 }

HmSetupConfigRadiusServerEntry ::= SEQUENCE {
            hmSetupConfigRadiusServerEntryName DisplayString,
            hmSetupConfigRadiusServerEntryServer DisplayString,
            hmSetupConfigRadiusServerEntryPort Integer32,
            hmSetupConfigRadiusServerEntryProtocol INTEGER,
            hmSetupConfigRadiusServerEntryLoopbackAddress DisplayString,
            hmSetupConfigRadiusServerEntrySecret DisplayString,
            hmSetupConfigRadiusServerEntryBackup DisplayString,
            hmSetupConfigRadiusServerEntryCategory BITS,
            hmSetupConfigRadiusServerEntryAttributeValues DisplayString
    }

-- {COLUMN} 1.3.6.1.4.1.248.32.18.2.11.81.1.1.1
hmSetupConfigRadiusServerEntryName OBJECT-TYPE
    SYNTAX     DisplayString (SIZE(0..16))
    MAX-ACCESS read-write
    STATUS     current
    DESCRIPTION
            "-- empty --"
    ::= { hmSetupConfigRadiusServerEntry 1 }

-- {COLUMN} 1.3.6.1.4.1.248.32.18.2.11.81.1.1.2
hmSetupConfigRadiusServerEntryServer OBJECT-TYPE
    SYNTAX     DisplayString (SIZE(0..64))
    MAX-ACCESS read-write
    STATUS     current
    DESCRIPTION
            "-- empty --"
    ::= { hmSetupConfigRadiusServerEntry 2 }

-- {COLUMN} 1.3.6.1.4.1.248.32.18.2.11.81.1.1.3
hmSetupConfigRadiusServerEntryPort OBJECT-TYPE
    SYNTAX     Integer32 (0..65535)
    MAX-ACCESS read-write
    STATUS     current
    DESCRIPTION
            "-- empty --"
    ::= { hmSetupConfigRadiusServerEntry 3 }

-- {COLUMN} 1.3.6.1.4.1.248.32.18.2.11.81.1.1.4
hmSetupConfigRadiusServerEntryProtocol OBJECT-TYPE
    SYNTAX     INTEGER {
                  eRadius (0),
                  eRadsec (1)
            }
    MAX-ACCESS read-write
    STATUS     current
    DESCRIPTION
            "-- empty --"
    ::= { hmSetupConfigRadiusServerEntry 4 }

-- {COLUMN} 1.3.6.1.4.1.248.32.18.2.11.81.1.1.5
hmSetupConfigRadiusServerEntryLoopbackAddress OBJECT-TYPE
    SYNTAX     DisplayString (SIZE(0..16))
    MAX-ACCESS read-write
    STATUS     current
    DESCRIPTION
            "-- empty --"
    ::= { hmSetupConfigRadiusServerEntry 5 }

-- {COLUMN} 1.3.6.1.4.1.248.32.18.2.11.81.1.1.6
hmSetupConfigRadiusServerEntrySecret OBJECT-TYPE
    SYNTAX     DisplayString (SIZE(0..64))
    MAX-ACCESS read-write
    STATUS     current
    DESCRIPTION
            "-- empty --"
    ::= { hmSetupConfigRadiusServerEntry 6 }

-- {COLUMN} 1.3.6.1.4.1.248.32.18.2.11.81.1.1.7
hmSetupConfigRadiusServerEntryBackup OBJECT-TYPE
    SYNTAX     DisplayString (SIZE(0..16))
    MAX-ACCESS read-write
    STATUS     current
    DESCRIPTION
            "-- empty --"
    ::= { hmSetupConfigRadiusServerEntry 7 }

-- {COLUMN} 1.3.6.1.4.1.248.32.18.2.11.81.1.1.8
hmSetupConfigRadiusServerEntryCategory OBJECT-TYPE
    SYNTAX     BITS {
                  eAccounting (6),
                  eAuthentication (7)
            }
    MAX-ACCESS read-write
    STATUS     current
    DESCRIPTION
            "-- empty --"
    ::= { hmSetupConfigRadiusServerEntry 8 }

-- {COLUMN} 1.3.6.1.4.1.248.32.18.2.11.81.1.1.9
hmSetupConfigRadiusServerEntryAttributeValues OBJECT-TYPE
    SYNTAX     DisplayString (SIZE(0..251))
    MAX-ACCESS read-write
    STATUS     current
    DESCRIPTION
            "-- empty --"
    ::= { hmSetupConfigRadiusServerEntry 9 }

-- {SCALAR} 1.3.6.1.4.1.248.32.18.2.11.81.2
hmSetupConfigRadiusAccessRightsTransfer OBJECT-TYPE
    SYNTAX     INTEGER {
                  eVendorSpecific (0),
                  eMapped (1),
                  eShellPrivilege (2)
            }
    MAX-ACCESS read-write
    STATUS     current
    DESCRIPTION
            "-- empty --"
    ::= { hmSetupConfigRadius 2 }

-- {SCALAR} 1.3.6.1.4.1.248.32.18.2.11.81.3
hmSetupConfigRadiusAccounting OBJECT-TYPE
    SYNTAX     INTEGER {
                  eNo (0),
                  eYes (1)
            }
    MAX-ACCESS read-write
    STATUS     current
    DESCRIPTION
            "-- empty --"
    ::= { hmSetupConfigRadius 3 }

-- {SCALAR} 1.3.6.1.4.1.248.32.18.2.11.90
hmSetupConfigLedMode OBJECT-TYPE
    SYNTAX     INTEGER {
                  eOn (0),
                  eOff (1),
                  eTimedOff (2)
            }
    MAX-ACCESS read-write
    STATUS     current
    DESCRIPTION
            "-- empty --"
    ::= { hmSetupConfig 90 }

-- {SCALAR} 1.3.6.1.4.1.248.32.18.2.11.91
hmSetupConfigLedOffSeconds OBJECT-TYPE
    SYNTAX     Integer32 (0..2147483647)
    MAX-ACCESS read-write
    STATUS     current
    DESCRIPTION
            "-- empty --"
    ::= { hmSetupConfig 91 }

-- {NODE} 1.3.6.1.4.1.248.32.18.2.12
hmSetupWlan OBJECT IDENTIFIER ::= { hmSetup 12 }

-- {SCALAR} 1.3.6.1.4.1.248.32.18.2.12.3
hmSetupWlanSpareHeap OBJECT-TYPE
    SYNTAX     Integer32 (0..65535)
    MAX-ACCESS read-write
    STATUS     current
    DESCRIPTION
            "-- empty --"
    ::= { hmSetupWlan 3 }

-- {TABLE} 1.3.6.1.4.1.248.32.18.2.12.7
hmSetupWlanAccessListTable OBJECT-TYPE
    SYNTAX     SEQUENCE OF HmSetupWlanAccessListEntry
    MAX-ACCESS not-accessible
    STATUS     current
    DESCRIPTION
            "-- empty --"
    ::= { hmSetupWlan 7 }

-- {ROW} 1.3.6.1.4.1.248.32.18.2.12.7.1
hmSetupWlanAccessListEntry OBJECT-TYPE
    SYNTAX     HmSetupWlanAccessListEntry
    MAX-ACCESS not-accessible
    STATUS     current
    DESCRIPTION
            ""
    INDEX {
            hmSetupWlanAccessListEntryMacAddress
          }
    ::= { hmSetupWlanAccessListTable 1 }

HmSetupWlanAccessListEntry ::= SEQUENCE {
            hmSetupWlanAccessListEntryMacAddress MacAddress,
            hmSetupWlanAccessListEntryName DisplayString,
            hmSetupWlanAccessListEntryComment DisplayString,
            hmSetupWlanAccessListEntryWpaPassphrase DisplayString,
            hmSetupWlanAccessListEntryTxLimit Integer32,
            hmSetupWlanAccessListEntryRxLimit Integer32,
            hmSetupWlanAccessListEntryVlanId Integer32
    }

-- {COLUMN} 1.3.6.1.4.1.248.32.18.2.12.7.1.1
hmSetupWlanAccessListEntryMacAddress OBJECT-TYPE
    SYNTAX     MacAddress
    MAX-ACCESS read-write
    STATUS     current
    DESCRIPTION
            "-- empty --"
    ::= { hmSetupWlanAccessListEntry 1 }

-- {COLUMN} 1.3.6.1.4.1.248.32.18.2.12.7.1.2
hmSetupWlanAccessListEntryName OBJECT-TYPE
    SYNTAX     DisplayString (SIZE(0..32))
    MAX-ACCESS read-write
    STATUS     current
    DESCRIPTION
            "-- empty --"
    ::= { hmSetupWlanAccessListEntry 2 }

-- {COLUMN} 1.3.6.1.4.1.248.32.18.2.12.7.1.3
hmSetupWlanAccessListEntryComment OBJECT-TYPE
    SYNTAX     DisplayString (SIZE(0..30))
    MAX-ACCESS read-write
    STATUS     current
    DESCRIPTION
            "-- empty --"
    ::= { hmSetupWlanAccessListEntry 3 }

-- {COLUMN} 1.3.6.1.4.1.248.32.18.2.12.7.1.4
hmSetupWlanAccessListEntryWpaPassphrase OBJECT-TYPE
    SYNTAX     DisplayString (SIZE(0..63))
    MAX-ACCESS read-write
    STATUS     current
    DESCRIPTION
            "-- empty --"
    ::= { hmSetupWlanAccessListEntry 4 }

-- {COLUMN} 1.3.6.1.4.1.248.32.18.2.12.7.1.5
hmSetupWlanAccessListEntryTxLimit OBJECT-TYPE
    SYNTAX     Integer32 (0..2147483647)
    MAX-ACCESS read-write
    STATUS     current
    DESCRIPTION
            "-- empty --"
    ::= { hmSetupWlanAccessListEntry 5 }

-- {COLUMN} 1.3.6.1.4.1.248.32.18.2.12.7.1.6
hmSetupWlanAccessListEntryRxLimit OBJECT-TYPE
    SYNTAX     Integer32 (0..2147483647)
    MAX-ACCESS read-write
    STATUS     current
    DESCRIPTION
            "-- empty --"
    ::= { hmSetupWlanAccessListEntry 6 }

-- {COLUMN} 1.3.6.1.4.1.248.32.18.2.12.7.1.7
hmSetupWlanAccessListEntryVlanId OBJECT-TYPE
    SYNTAX     Integer32 (0..65535)
    MAX-ACCESS read-write
    STATUS     current
    DESCRIPTION
            "-- empty --"
    ::= { hmSetupWlanAccessListEntry 7 }

-- {SCALAR} 1.3.6.1.4.1.248.32.18.2.12.8
hmSetupWlanAccessMode OBJECT-TYPE
    SYNTAX     INTEGER {
                  eNegative (0),
                  ePositive (1)
            }
    MAX-ACCESS read-write
    STATUS     current
    DESCRIPTION
            "-- empty --"
    ::= { hmSetupWlan 8 }

-- {SCALAR} 1.3.6.1.4.1.248.32.18.2.12.12
hmSetupWlanIappProtocol OBJECT-TYPE
    SYNTAX     INTEGER {
                  eNo (0),
                  eYes (1)
            }
    MAX-ACCESS read-write
    STATUS     current
    DESCRIPTION
            "-- empty --"
    ::= { hmSetupWlan 12 }

-- {SCALAR} 1.3.6.1.4.1.248.32.18.2.12.13
hmSetupWlanIappAnnounceInterval OBJECT-TYPE
    SYNTAX     Integer32 (0..65535)
    MAX-ACCESS read-write
    STATUS     current
    DESCRIPTION
            "-- empty --"
    ::= { hmSetupWlan 13 }

-- {SCALAR} 1.3.6.1.4.1.248.32.18.2.12.14
hmSetupWlanIappHandoverTimeout OBJECT-TYPE
    SYNTAX     Integer32 (0..65535)
    MAX-ACCESS read-write
    STATUS     current
    DESCRIPTION
            "-- empty --"
    ::= { hmSetupWlan 14 }

-- {SCALAR} 1.3.6.1.4.1.248.32.18.2.12.26
hmSetupWlanInterSsidTraffic OBJECT-TYPE
    SYNTAX     INTEGER {
                  eLocallyOff (0),
                  eYes (1),
                  eGloballyOff (2)
            }
    MAX-ACCESS read-write
    STATUS     current
    DESCRIPTION
            "-- empty --"
    ::= { hmSetupWlan 26 }

-- {SCALAR} 1.3.6.1.4.1.248.32.18.2.12.27
hmSetupWlanSuperviseStations OBJECT-TYPE
    SYNTAX     INTEGER {
                  eNo (0),
                  eYes (1)
            }
    MAX-ACCESS read-write
    STATUS     current
    DESCRIPTION
            "-- empty --"
    ::= { hmSetupWlan 27 }

-- {NODE} 1.3.6.1.4.1.248.32.18.2.12.29
hmSetupWlanRadiusAccessCheck OBJECT IDENTIFIER ::= { hmSetupWlan 29 }

-- {SCALAR} 1.3.6.1.4.1.248.32.18.2.12.29.1
hmSetupWlanRadiusAccessCheckServerAddress OBJECT-TYPE
    SYNTAX     IpAddress
    MAX-ACCESS read-write
    STATUS     current
    DESCRIPTION
            "-- empty --"
    ::= { hmSetupWlanRadiusAccessCheck 1 }

-- {SCALAR} 1.3.6.1.4.1.248.32.18.2.12.29.2
hmSetupWlanRadiusAccessCheckAuthPort OBJECT-TYPE
    SYNTAX     Integer32 (0..65535)
    MAX-ACCESS read-write
    STATUS     current
    DESCRIPTION
            "-- empty --"
    ::= { hmSetupWlanRadiusAccessCheck 2 }

-- {SCALAR} 1.3.6.1.4.1.248.32.18.2.12.29.3
hmSetupWlanRadiusAccessCheckSecret OBJECT-TYPE
    SYNTAX     DisplayString (SIZE(0..64))
    MAX-ACCESS read-write
    STATUS     current
    DESCRIPTION
            "-- empty --"
    ::= { hmSetupWlanRadiusAccessCheck 3 }

-- {SCALAR} 1.3.6.1.4.1.248.32.18.2.12.29.4
hmSetupWlanRadiusAccessCheckBackupServerIpAddress OBJECT-TYPE
    SYNTAX     IpAddress
    MAX-ACCESS read-write
    STATUS     current
    DESCRIPTION
            "-- empty --"
    ::= { hmSetupWlanRadiusAccessCheck 4 }

-- {SCALAR} 1.3.6.1.4.1.248.32.18.2.12.29.5
hmSetupWlanRadiusAccessCheckBackupAuthPort OBJECT-TYPE
    SYNTAX     Integer32 (0..65535)
    MAX-ACCESS read-write
    STATUS     current
    DESCRIPTION
            "-- empty --"
    ::= { hmSetupWlanRadiusAccessCheck 5 }

-- {SCALAR} 1.3.6.1.4.1.248.32.18.2.12.29.6
hmSetupWlanRadiusAccessCheckBackupSecret OBJECT-TYPE
    SYNTAX     DisplayString (SIZE(0..64))
    MAX-ACCESS read-write
    STATUS     current
    DESCRIPTION
            "-- empty --"
    ::= { hmSetupWlanRadiusAccessCheck 6 }

-- {SCALAR} 1.3.6.1.4.1.248.32.18.2.12.29.7
hmSetupWlanRadiusAccessCheckResponseLifetime OBJECT-TYPE
    SYNTAX     Integer32 (0..2147483647)
    MAX-ACCESS read-write
    STATUS     current
    DESCRIPTION
            "-- empty --"
    ::= { hmSetupWlanRadiusAccessCheck 7 }

-- {SCALAR} 1.3.6.1.4.1.248.32.18.2.12.29.8
hmSetupWlanRadiusAccessCheckPasswordSource OBJECT-TYPE
    SYNTAX     INTEGER {
                  eSecret (0),
                  eMacAddress (1)
            }
    MAX-ACCESS read-write
    STATUS     current
    DESCRIPTION
            "-- empty --"
    ::= { hmSetupWlanRadiusAccessCheck 8 }

-- {SCALAR} 1.3.6.1.4.1.248.32.18.2.12.29.9
hmSetupWlanRadiusAccessCheckRecheckCycle OBJECT-TYPE
    SYNTAX     Integer32 (0..2147483647)
    MAX-ACCESS read-write
    STATUS     current
    DESCRIPTION
            "-- empty --"
    ::= { hmSetupWlanRadiusAccessCheck 9 }

-- {SCALAR} 1.3.6.1.4.1.248.32.18.2.12.29.10
hmSetupWlanRadiusAccessCheckProvideServerDatabase OBJECT-TYPE
    SYNTAX     INTEGER {
                  eNo (0),
                  eYes (1)
            }
    MAX-ACCESS read-write
    STATUS     current
    DESCRIPTION
            "-- empty --"
    ::= { hmSetupWlanRadiusAccessCheck 10 }

-- {SCALAR} 1.3.6.1.4.1.248.32.18.2.12.29.11
hmSetupWlanRadiusAccessCheckLoopbackAddress OBJECT-TYPE
    SYNTAX     DisplayString (SIZE(0..16))
    MAX-ACCESS read-write
    STATUS     current
    DESCRIPTION
            "-- empty --"
    ::= { hmSetupWlanRadiusAccessCheck 11 }

-- {SCALAR} 1.3.6.1.4.1.248.32.18.2.12.29.12
hmSetupWlanRadiusAccessCheckBackupLoopbackAddress OBJECT-TYPE
    SYNTAX     DisplayString (SIZE(0..16))
    MAX-ACCESS read-write
    STATUS     current
    DESCRIPTION
            "-- empty --"
    ::= { hmSetupWlanRadiusAccessCheck 12 }

-- {SCALAR} 1.3.6.1.4.1.248.32.18.2.12.29.13
hmSetupWlanRadiusAccessCheckProtocol OBJECT-TYPE
    SYNTAX     INTEGER {
                  eRadius (0),
                  eRadsec (1)
            }
    MAX-ACCESS read-write
    STATUS     current
    DESCRIPTION
            "-- empty --"
    ::= { hmSetupWlanRadiusAccessCheck 13 }

-- {SCALAR} 1.3.6.1.4.1.248.32.18.2.12.29.14
hmSetupWlanRadiusAccessCheckBackupProtocol OBJECT-TYPE
    SYNTAX     INTEGER {
                  eRadius (0),
                  eRadsec (1)
            }
    MAX-ACCESS read-write
    STATUS     current
    DESCRIPTION
            "-- empty --"
    ::= { hmSetupWlanRadiusAccessCheck 14 }

-- {SCALAR} 1.3.6.1.4.1.248.32.18.2.12.29.15
hmSetupWlanRadiusAccessCheckForceRecheck OBJECT-TYPE
    SYNTAX     DisplayString
    MAX-ACCESS read-write
    STATUS     current
    DESCRIPTION
            "-- empty --"
    ::= { hmSetupWlanRadiusAccessCheck 15 }

-- {SCALAR} 1.3.6.1.4.1.248.32.18.2.12.29.16
hmSetupWlanRadiusAccessCheckServerHostname OBJECT-TYPE
    SYNTAX     DisplayString (SIZE(0..64))
    MAX-ACCESS read-write
    STATUS     current
    DESCRIPTION
            "-- empty --"
    ::= { hmSetupWlanRadiusAccessCheck 16 }

-- {SCALAR} 1.3.6.1.4.1.248.32.18.2.12.29.17
hmSetupWlanRadiusAccessCheckBackupServerHostname OBJECT-TYPE
    SYNTAX     DisplayString (SIZE(0..64))
    MAX-ACCESS read-write
    STATUS     current
    DESCRIPTION
            "-- empty --"
    ::= { hmSetupWlanRadiusAccessCheck 17 }

-- {SCALAR} 1.3.6.1.4.1.248.32.18.2.12.29.18
hmSetupWlanRadiusAccessCheckAttributeValues OBJECT-TYPE
    SYNTAX     DisplayString (SIZE(0..251))
    MAX-ACCESS read-write
    STATUS     current
    DESCRIPTION
            "-- empty --"
    ::= { hmSetupWlanRadiusAccessCheck 18 }

-- {SCALAR} 1.3.6.1.4.1.248.32.18.2.12.29.19
hmSetupWlanRadiusAccessCheckBackupAttributeValues OBJECT-TYPE
    SYNTAX     DisplayString (SIZE(0..251))
    MAX-ACCESS read-write
    STATUS     current
    DESCRIPTION
            "-- empty --"
    ::= { hmSetupWlanRadiusAccessCheck 19 }

-- {SCALAR} 1.3.6.1.4.1.248.32.18.2.12.36
hmSetupWlanCountry OBJECT-TYPE
    SYNTAX     INTEGER {
                  eUnknown (0),
                  eAlbania (8),
                  eAlgeria (12),
                  eArgentina (32),
                  eAustralia (36),
                  eAustria (40),
                  eBahrain (48),
                  eBangladesh (50),
                  eBelgium (56),
                  eBosniaHerzegovina (70),
                  eBrazil (76),
                  eBruneiDarussalam (96),
                  eBulgaria (100),
                  eBelarus (112),
                  eCanada (124),
                  eChile (152),
                  eChina (156),
                  eTaiwan (158),
                  eColombia (170),
                  eCostaRica (188),
                  eCroatia (191),
                  eCyprus (196),
                  eCzech (203),
                  eDenmark (208),
                  eEcuador (218),
                  eEstonia (233),
                  eFinland (246),
                  eFrance (250),
                  eGermany (276),
                  eGhana (288),
                  eGreece (300),
                  eGuatemala (320),
                  eHonduras (340),
                  eHongKong (344),
                  eHungary (348),
                  eIceland (352),
                  eIndia (356),
                  eIndonesia (360),
                  eIreland (372),
                  eIsrael (376),
                  eItaly (380),
                  eJapan (392),
                  eJordan (400),
                  eSouthKorea (410),
                  eKuwait (414),
                  eLebanon (422),
                  eLatvia (428),
                  eLiechtenstein (438),
                  eLithuania (440),
                  eLuxembourg (442),
                  eMacau (446),
                  eMalaysia (458),
                  eMalta (470),
                  eMexico (484),
                  eMoldavia (498),
                  eMorocco (504),
                  eOman (512),
                  eNetherlands (528),
                  eNewZealand (554),
                  eNicaragua (558),
                  eNorway (578),
                  ePakistan (586),
                  ePanama (591),
                  eParaguay (600),
                  ePeru (604),
                  ePhilippines (608),
                  ePoland (616),
                  ePortugal (620),
                  ePuertoRico (630),
                  eQatar (634),
                  eRomania (642),
                  eRussia (643),
                  eSaudiArabia (682),
                  eSingapore (702),
                  eSlovak (703),
                  eSlovenia (705),
                  eSouthAfrica (710),
                  eSpain (724),
                  eSweden (752),
                  eSwitzerland (756),
                  eThailand (764),
                  eUnitedArabEmirates (784),
                  eTunisia (788),
                  eTurkey (792),
                  eUganda (800),
                  eUkraine (804),
                  eMacedonia (807),
                  eEgypt (818),
                  eUnitedKingdom (826),
                  eTanzania (834),
                  eUnitedStatesFcc (840),
                  eUruguay (858),
                  eVenezuela (862),
                  eEurope (998),
                  eEgalistan (999)
            }
    MAX-ACCESS read-write
    STATUS     current
    DESCRIPTION
            "-- empty --"
    ::= { hmSetupWlan 36 }

-- {SCALAR} 1.3.6.1.4.1.248.32.18.2.12.38
hmSetupWlanArpHandling OBJECT-TYPE
    SYNTAX     INTEGER {
                  eNo (0),
                  eYes (1)
            }
    MAX-ACCESS read-write
    STATUS     current
    DESCRIPTION
            "-- empty --"
    ::= { hmSetupWlan 38 }

-- {SCALAR} 1.3.6.1.4.1.248.32.18.2.12.41
hmSetupWlanMailAddress OBJECT-TYPE
    SYNTAX     DisplayString (SIZE(0..254))
    MAX-ACCESS read-write
    STATUS     current
    DESCRIPTION
            "-- empty --"
    ::= { hmSetupWlan 41 }

-- {SCALAR} 1.3.6.1.4.1.248.32.18.2.12.44
hmSetupWlanAllowIllegalAssociationWithoutAuthentication OBJECT-TYPE
    SYNTAX     INTEGER {
                  eNo (0),
                  eYes (1)
            }
    MAX-ACCESS read-write
    STATUS     current
    DESCRIPTION
            "-- empty --"
    ::= { hmSetupWlan 44 }

-- {NODE} 1.3.6.1.4.1.248.32.18.2.12.45
hmSetupWlanRadiusAccounting OBJECT IDENTIFIER ::= { hmSetupWlan 45 }

-- {SCALAR} 1.3.6.1.4.1.248.32.18.2.12.45.1
hmSetupWlanRadiusAccountingServerAddress OBJECT-TYPE
    SYNTAX     IpAddress
    MAX-ACCESS read-write
    STATUS     current
    DESCRIPTION
            "-- empty --"
    ::= { hmSetupWlanRadiusAccounting 1 }

-- {SCALAR} 1.3.6.1.4.1.248.32.18.2.12.45.2
hmSetupWlanRadiusAccountingAccntPort OBJECT-TYPE
    SYNTAX     Integer32 (0..65535)
    MAX-ACCESS read-write
    STATUS     current
    DESCRIPTION
            "-- empty --"
    ::= { hmSetupWlanRadiusAccounting 2 }

-- {SCALAR} 1.3.6.1.4.1.248.32.18.2.12.45.3
hmSetupWlanRadiusAccountingSecret OBJECT-TYPE
    SYNTAX     DisplayString (SIZE(0..64))
    MAX-ACCESS read-write
    STATUS     current
    DESCRIPTION
            "-- empty --"
    ::= { hmSetupWlanRadiusAccounting 3 }

-- {SCALAR} 1.3.6.1.4.1.248.32.18.2.12.45.4
hmSetupWlanRadiusAccountingBackupServerIpAddress OBJECT-TYPE
    SYNTAX     IpAddress
    MAX-ACCESS read-write
    STATUS     current
    DESCRIPTION
            "-- empty --"
    ::= { hmSetupWlanRadiusAccounting 4 }

-- {SCALAR} 1.3.6.1.4.1.248.32.18.2.12.45.5
hmSetupWlanRadiusAccountingBackupAccntPort OBJECT-TYPE
    SYNTAX     Integer32 (0..65535)
    MAX-ACCESS read-write
    STATUS     current
    DESCRIPTION
            "-- empty --"
    ::= { hmSetupWlanRadiusAccounting 5 }

-- {SCALAR} 1.3.6.1.4.1.248.32.18.2.12.45.6
hmSetupWlanRadiusAccountingBackupSecret OBJECT-TYPE
    SYNTAX     DisplayString (SIZE(0..64))
    MAX-ACCESS read-write
    STATUS     current
    DESCRIPTION
            "-- empty --"
    ::= { hmSetupWlanRadiusAccounting 6 }

-- {SCALAR} 1.3.6.1.4.1.248.32.18.2.12.45.7
hmSetupWlanRadiusAccountingClientBrgHandling OBJECT-TYPE
    SYNTAX     INTEGER {
                  eAllTraffic (0),
                  eBridgeTrafficOnly (1),
                  eClientTrafficOnly (2),
                  eSeparateAccounting (3)
            }
    MAX-ACCESS read-write
    STATUS     current
    DESCRIPTION
            "-- empty --"
    ::= { hmSetupWlanRadiusAccounting 7 }

-- {SCALAR} 1.3.6.1.4.1.248.32.18.2.12.45.8
hmSetupWlanRadiusAccountingInterimUpdatePeriod OBJECT-TYPE
    SYNTAX     Integer32 (0..2147483647)
    MAX-ACCESS read-write
    STATUS     current
    DESCRIPTION
            "-- empty --"
    ::= { hmSetupWlanRadiusAccounting 8 }

-- {SCALAR} 1.3.6.1.4.1.248.32.18.2.12.45.9
hmSetupWlanRadiusAccountingExcludedVlan OBJECT-TYPE
    SYNTAX     Integer32 (0..65535)
    MAX-ACCESS read-write
    STATUS     current
    DESCRIPTION
            "-- empty --"
    ::= { hmSetupWlanRadiusAccounting 9 }

-- {SCALAR} 1.3.6.1.4.1.248.32.18.2.12.45.10
hmSetupWlanRadiusAccountingLoopbackAddress OBJECT-TYPE
    SYNTAX     DisplayString (SIZE(0..16))
    MAX-ACCESS read-write
    STATUS     current
    DESCRIPTION
            "-- empty --"
    ::= { hmSetupWlanRadiusAccounting 10 }

-- {SCALAR} 1.3.6.1.4.1.248.32.18.2.12.45.11
hmSetupWlanRadiusAccountingBackupLoopbackAddress OBJECT-TYPE
    SYNTAX     DisplayString (SIZE(0..16))
    MAX-ACCESS read-write
    STATUS     current
    DESCRIPTION
            "-- empty --"
    ::= { hmSetupWlanRadiusAccounting 11 }

-- {SCALAR} 1.3.6.1.4.1.248.32.18.2.12.45.12
hmSetupWlanRadiusAccountingProtocol OBJECT-TYPE
    SYNTAX     INTEGER {
                  eRadius (0),
                  eRadsec (1)
            }
    MAX-ACCESS read-write
    STATUS     current
    DESCRIPTION
            "-- empty --"
    ::= { hmSetupWlanRadiusAccounting 12 }

-- {SCALAR} 1.3.6.1.4.1.248.32.18.2.12.45.13
hmSetupWlanRadiusAccountingBackupProtocol OBJECT-TYPE
    SYNTAX     INTEGER {
                  eRadius (0),
                  eRadsec (1)
            }
    MAX-ACCESS read-write
    STATUS     current
    DESCRIPTION
            "-- empty --"
    ::= { hmSetupWlanRadiusAccounting 13 }

-- {SCALAR} 1.3.6.1.4.1.248.32.18.2.12.45.14
hmSetupWlanRadiusAccountingRestartAccounting OBJECT-TYPE
    SYNTAX     DisplayString
    MAX-ACCESS read-write
    STATUS     current
    DESCRIPTION
            "-- empty --"
    ::= { hmSetupWlanRadiusAccounting 14 }

-- {TABLE} 1.3.6.1.4.1.248.32.18.2.12.45.17
hmSetupWlanRadiusAccountingServersTable OBJECT-TYPE
    SYNTAX     SEQUENCE OF HmSetupWlanRadiusAccountingServersEntry
    MAX-ACCESS not-accessible
    STATUS     current
    DESCRIPTION
            "-- empty --"
    ::= { hmSetupWlanRadiusAccounting 17 }

-- {ROW} 1.3.6.1.4.1.248.32.18.2.12.45.17.1
hmSetupWlanRadiusAccountingServersEntry OBJECT-TYPE
    SYNTAX     HmSetupWlanRadiusAccountingServersEntry
    MAX-ACCESS not-accessible
    STATUS     current
    DESCRIPTION
            ""
    INDEX {
            hmSetupWlanRadiusAccountingServersEntryName
          }
    ::= { hmSetupWlanRadiusAccountingServersTable 1 }

HmSetupWlanRadiusAccountingServersEntry ::= SEQUENCE {
            hmSetupWlanRadiusAccountingServersEntryName DisplayString,
            hmSetupWlanRadiusAccountingServersEntryPort Integer32,
            hmSetupWlanRadiusAccountingServersEntrySecret DisplayString,
            hmSetupWlanRadiusAccountingServersEntryLoopbackAddr DisplayString,
            hmSetupWlanRadiusAccountingServersEntryProtocol INTEGER,
            hmSetupWlanRadiusAccountingServersEntryBackup DisplayString,
            hmSetupWlanRadiusAccountingServersEntryHostName DisplayString,
            hmSetupWlanRadiusAccountingServersEntryAttributeValues DisplayString
    }

-- {COLUMN} 1.3.6.1.4.1.248.32.18.2.12.45.17.1.1
hmSetupWlanRadiusAccountingServersEntryName OBJECT-TYPE
    SYNTAX     DisplayString (SIZE(0..16))
    MAX-ACCESS read-write
    STATUS     current
    DESCRIPTION
            "-- empty --"
    ::= { hmSetupWlanRadiusAccountingServersEntry 1 }

-- {COLUMN} 1.3.6.1.4.1.248.32.18.2.12.45.17.1.3
hmSetupWlanRadiusAccountingServersEntryPort OBJECT-TYPE
    SYNTAX     Integer32 (0..65535)
    MAX-ACCESS read-write
    STATUS     current
    DESCRIPTION
            "-- empty --"
    ::= { hmSetupWlanRadiusAccountingServersEntry 3 }

-- {COLUMN} 1.3.6.1.4.1.248.32.18.2.12.45.17.1.4
hmSetupWlanRadiusAccountingServersEntrySecret OBJECT-TYPE
    SYNTAX     DisplayString (SIZE(0..64))
    MAX-ACCESS read-write
    STATUS     current
    DESCRIPTION
            "-- empty --"
    ::= { hmSetupWlanRadiusAccountingServersEntry 4 }

-- {COLUMN} 1.3.6.1.4.1.248.32.18.2.12.45.17.1.5
hmSetupWlanRadiusAccountingServersEntryLoopbackAddr OBJECT-TYPE
    SYNTAX     DisplayString (SIZE(0..16))
    MAX-ACCESS read-write
    STATUS     current
    DESCRIPTION
            "-- empty --"
    ::= { hmSetupWlanRadiusAccountingServersEntry 5 }

-- {COLUMN} 1.3.6.1.4.1.248.32.18.2.12.45.17.1.6
hmSetupWlanRadiusAccountingServersEntryProtocol OBJECT-TYPE
    SYNTAX     INTEGER {
                  eRadius (0),
                  eRadsec (1)
            }
    MAX-ACCESS read-write
    STATUS     current
    DESCRIPTION
            "-- empty --"
    ::= { hmSetupWlanRadiusAccountingServersEntry 6 }

-- {COLUMN} 1.3.6.1.4.1.248.32.18.2.12.45.17.1.7
hmSetupWlanRadiusAccountingServersEntryBackup OBJECT-TYPE
    SYNTAX     DisplayString (SIZE(0..16))
    MAX-ACCESS read-write
    STATUS     current
    DESCRIPTION
            "-- empty --"
    ::= { hmSetupWlanRadiusAccountingServersEntry 7 }

-- {COLUMN} 1.3.6.1.4.1.248.32.18.2.12.45.17.1.8
hmSetupWlanRadiusAccountingServersEntryHostName OBJECT-TYPE
    SYNTAX     DisplayString (SIZE(0..64))
    MAX-ACCESS read-write
    STATUS     current
    DESCRIPTION
            "-- empty --"
    ::= { hmSetupWlanRadiusAccountingServersEntry 8 }

-- {COLUMN} 1.3.6.1.4.1.248.32.18.2.12.45.17.1.9
hmSetupWlanRadiusAccountingServersEntryAttributeValues OBJECT-TYPE
    SYNTAX     DisplayString (SIZE(0..251))
    MAX-ACCESS read-write
    STATUS     current
    DESCRIPTION
            "-- empty --"
    ::= { hmSetupWlanRadiusAccountingServersEntry 9 }

-- {SCALAR} 1.3.6.1.4.1.248.32.18.2.12.46
hmSetupWlanIndoorOnlyOperation OBJECT-TYPE
    SYNTAX     INTEGER {
                  eNo (0),
                  eYes (1)
            }
    MAX-ACCESS read-write
    STATUS     current
    DESCRIPTION
            "-- empty --"
    ::= { hmSetupWlan 46 }

-- {SCALAR} 1.3.6.1.4.1.248.32.18.2.12.47
hmSetupWlanIdleTimeout OBJECT-TYPE
    SYNTAX     Integer32 (0..2147483647)
    MAX-ACCESS read-write
    STATUS     current
    DESCRIPTION
            "-- empty --"
    ::= { hmSetupWlan 47 }

-- {SCALAR} 1.3.6.1.4.1.248.32.18.2.12.48
hmSetupWlanUseFullChannelset OBJECT-TYPE
    SYNTAX     INTEGER {
                  eNo (0),
                  eYes (1)
            }
    MAX-ACCESS read-write
    STATUS     current
    DESCRIPTION
            "-- empty --"
    ::= { hmSetupWlan 48 }

-- {NODE} 1.3.6.1.4.1.248.32.18.2.12.50
hmSetupWlanSigAvrg OBJECT IDENTIFIER ::= { hmSetupWlan 50 }

-- {SCALAR} 1.3.6.1.4.1.248.32.18.2.12.50.1
hmSetupWlanSigAvrgMeth OBJECT-TYPE
    SYNTAX     INTEGER {
                  eStd (0)
            }
    MAX-ACCESS read-write
    STATUS     current
    DESCRIPTION
            ""
    ::= { hmSetupWlanSigAvrg 1 }

-- {NODE} 1.3.6.1.4.1.248.32.18.2.12.50.2
hmSetupWlanSigAvrgStdParams OBJECT IDENTIFIER ::= { hmSetupWlanSigAvrg 2 }

-- {SCALAR} 1.3.6.1.4.1.248.32.18.2.12.50.2.1
hmSetupWlanSigAvrgStdParamsFactor OBJECT-TYPE
    SYNTAX     Integer32 (0..255)
    MAX-ACCESS read-write
    STATUS     current
    DESCRIPTION
            ""
    ::= { hmSetupWlanSigAvrgStdParams 1 }

-- {NODE} 1.3.6.1.4.1.248.32.18.2.12.51
hmSetupWlanRateAdaption OBJECT IDENTIFIER ::= { hmSetupWlan 51 }

-- {SCALAR} 1.3.6.1.4.1.248.32.18.2.12.51.2
hmSetupWlanRateAdaptionInitialRate OBJECT-TYPE
    SYNTAX     INTEGER {
                  eMinimum (0),
                  eRssiDerived (1)
            }
    MAX-ACCESS read-write
    STATUS     current
    DESCRIPTION
            "-- empty --"
    ::= { hmSetupWlanRateAdaption 2 }

-- {SCALAR} 1.3.6.1.4.1.248.32.18.2.12.51.3
hmSetupWlanRateAdaptionMinstrelAveragingFactor OBJECT-TYPE
    SYNTAX     Integer32 (0..255)
    MAX-ACCESS read-write
    STATUS     current
    DESCRIPTION
            "-- empty --"
    ::= { hmSetupWlanRateAdaption 3 }

-- {SCALAR} 1.3.6.1.4.1.248.32.18.2.12.51.4
hmSetupWlanRateAdaptionStandardAveragingFactor OBJECT-TYPE
    SYNTAX     Integer32 (0..255)
    MAX-ACCESS read-write
    STATUS     current
    DESCRIPTION
            "-- empty --"
    ::= { hmSetupWlanRateAdaption 4 }

-- {SCALAR} 1.3.6.1.4.1.248.32.18.2.12.51.5
hmSetupWlanRateAdaptionMethod OBJECT-TYPE
    SYNTAX     INTEGER {
                  eStandard (0),
                  eMinstrel (1)
            }
    MAX-ACCESS read-write
    STATUS     current
    DESCRIPTION
            "-- empty --"
    ::= { hmSetupWlanRateAdaption 5 }

-- {SCALAR} 1.3.6.1.4.1.248.32.18.2.12.60
hmSetupWlanIappIpNetwork OBJECT-TYPE
    SYNTAX     DisplayString (SIZE(0..16))
    MAX-ACCESS read-write
    STATUS     current
    DESCRIPTION
            "-- empty --"
    ::= { hmSetupWlan 60 }

-- {TABLE} 1.3.6.1.4.1.248.32.18.2.12.70
hmSetupWlanVlanGroupkeyMappingTable OBJECT-TYPE
    SYNTAX     SEQUENCE OF HmSetupWlanVlanGroupkeyMappingEntry
    MAX-ACCESS not-accessible
    STATUS     current
    DESCRIPTION
            "-- empty --"
    ::= { hmSetupWlan 70 }

-- {ROW} 1.3.6.1.4.1.248.32.18.2.12.70.1
hmSetupWlanVlanGroupkeyMappingEntry OBJECT-TYPE
    SYNTAX     HmSetupWlanVlanGroupkeyMappingEntry
    MAX-ACCESS not-accessible
    STATUS     current
    DESCRIPTION
            ""
    INDEX {
            hmSetupWlanVlanGroupkeyMappingEntryNetwork,
            hmSetupWlanVlanGroupkeyMappingEntryVlanId
          }
    ::= { hmSetupWlanVlanGroupkeyMappingTable 1 }

HmSetupWlanVlanGroupkeyMappingEntry ::= SEQUENCE {
            hmSetupWlanVlanGroupkeyMappingEntryNetwork INTEGER,
            hmSetupWlanVlanGroupkeyMappingEntryVlanId Integer32,
            hmSetupWlanVlanGroupkeyMappingEntryGroupkeyIndex Integer32
    }

-- {COLUMN} 1.3.6.1.4.1.248.32.18.2.12.70.1.1
hmSetupWlanVlanGroupkeyMappingEntryNetwork OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan22 (32),
                  eWlan23 (33),
                  eWlan24 (34),
                  eWlan25 (35),
                  eWlan26 (36),
                  eWlan27 (37),
                  eWlan28 (38)
            }
    MAX-ACCESS read-write
    STATUS     current
    DESCRIPTION
            "-- empty --"
    ::= { hmSetupWlanVlanGroupkeyMappingEntry 1 }

-- {COLUMN} 1.3.6.1.4.1.248.32.18.2.12.70.1.2
hmSetupWlanVlanGroupkeyMappingEntryVlanId OBJECT-TYPE
    SYNTAX     Integer32 (0..65535)
    MAX-ACCESS read-write
    STATUS     current
    DESCRIPTION
            "-- empty --"
    ::= { hmSetupWlanVlanGroupkeyMappingEntry 2 }

-- {COLUMN} 1.3.6.1.4.1.248.32.18.2.12.70.1.3
hmSetupWlanVlanGroupkeyMappingEntryGroupkeyIndex OBJECT-TYPE
    SYNTAX     Integer32 (0..255)
    MAX-ACCESS read-write
    STATUS     current
    DESCRIPTION
            "-- empty --"
    ::= { hmSetupWlanVlanGroupkeyMappingEntry 3 }

-- {NODE} 1.3.6.1.4.1.248.32.18.2.12.80
hmSetupWlanDualRoaming OBJECT IDENTIFIER ::= { hmSetupWlan 80 }

-- {SCALAR} 1.3.6.1.4.1.248.32.18.2.12.80.1
hmSetupWlanDualRoamingGroup OBJECT-TYPE
    SYNTAX     INTEGER {
                  eOff (0),
                  eWlan1PlusWlan2 (3)
            }
    MAX-ACCESS read-write
    STATUS     current
    DESCRIPTION
            "-- empty --"
    ::= { hmSetupWlanDualRoaming 1 }

-- {SCALAR} 1.3.6.1.4.1.248.32.18.2.12.80.2
hmSetupWlanDualRoamingBlockTimeMs OBJECT-TYPE
    SYNTAX     Integer32 (0..2147483647)
    MAX-ACCESS read-write
    STATUS     current
    DESCRIPTION
            "-- empty --"
    ::= { hmSetupWlanDualRoaming 2 }

-- {NODE} 1.3.6.1.4.1.248.32.18.2.12.85
hmSetupWlanPmkCaching OBJECT IDENTIFIER ::= { hmSetupWlan 85 }

-- {SCALAR} 1.3.6.1.4.1.248.32.18.2.12.85.1
hmSetupWlanPmkCachingDefaultLifetime OBJECT-TYPE
    SYNTAX     Integer32 (0..2147483647)
    MAX-ACCESS read-write
    STATUS     current
    DESCRIPTION
            "-- empty --"
    ::= { hmSetupWlanPmkCaching 1 }

-- {NODE} 1.3.6.1.4.1.248.32.18.2.12.86
hmSetupWlanPacketCapture OBJECT IDENTIFIER ::= { hmSetupWlan 86 }

-- {SCALAR} 1.3.6.1.4.1.248.32.18.2.12.86.1
hmSetupWlanPacketCaptureWlanCaptureFormat OBJECT-TYPE
    SYNTAX     INTEGER {
                  ePlain (105),
                  ePrism (119),
                  eRadiotap (127),
                  eAvs (163),
                  ePpi (192)
            }
    MAX-ACCESS read-write
    STATUS     current
    DESCRIPTION
            "-- empty --"
    ::= { hmSetupWlanPacketCapture 1 }

-- {NODE} 1.3.6.1.4.1.248.32.18.2.12.87
hmSetupWlanBandSteering OBJECT IDENTIFIER ::= { hmSetupWlan 87 }

-- {SCALAR} 1.3.6.1.4.1.248.32.18.2.12.87.1
hmSetupWlanBandSteeringOperating OBJECT-TYPE
    SYNTAX     INTEGER {
                  eNo (0),
                  eYes (1)
            }
    MAX-ACCESS read-write
    STATUS     current
    DESCRIPTION
            "-- empty --"
    ::= { hmSetupWlanBandSteering 1 }

-- {SCALAR} 1.3.6.1.4.1.248.32.18.2.12.87.2
hmSetupWlanBandSteeringCriteria OBJECT-TYPE
    SYNTAX     INTEGER {
                  eRadioBand (1)
            }
    MAX-ACCESS read-write
    STATUS     current
    DESCRIPTION
            "-- empty --"
    ::= { hmSetupWlanBandSteering 2 }

-- {SCALAR} 1.3.6.1.4.1.248.32.18.2.12.87.3
hmSetupWlanBandSteeringPreferredBand OBJECT-TYPE
    SYNTAX     INTEGER {
                  e24ghz (1),
                  e5ghz (2)
            }
    MAX-ACCESS read-write
    STATUS     current
    DESCRIPTION
            "-- empty --"
    ::= { hmSetupWlanBandSteering 3 }

-- {SCALAR} 1.3.6.1.4.1.248.32.18.2.12.87.4
hmSetupWlanBandSteeringProberequestAgeoutSeconds OBJECT-TYPE
    SYNTAX     Integer32 (0..2147483647)
    MAX-ACCESS read-write
    STATUS     current
    DESCRIPTION
            "-- empty --"
    ::= { hmSetupWlanBandSteering 4 }

-- {SCALAR} 1.3.6.1.4.1.248.32.18.2.12.87.5
hmSetupWlanBandSteeringInitialBlocktimeSeconds OBJECT-TYPE
    SYNTAX     Integer32 (0..2147483647)
    MAX-ACCESS read-write
    STATUS     current
    DESCRIPTION
            "-- empty --"
    ::= { hmSetupWlanBandSteering 5 }

-- {NODE} 1.3.6.1.4.1.248.32.18.2.12.88
hmSetupWlanErrorMonitoring OBJECT IDENTIFIER ::= { hmSetupWlan 88 }

-- {SCALAR} 1.3.6.1.4.1.248.32.18.2.12.88.1
hmSetupWlanErrorMonitoringErrors OBJECT-TYPE
    SYNTAX     BITS {
                  eNone (0),
                  eStuckInterrupts (4),
                  eAgcCalibrateFailures (5),
                  eNicErrors (6),
                  eBusErrors (7)
            }
    MAX-ACCESS read-write
    STATUS     current
    DESCRIPTION
            "-- empty --"
    ::= { hmSetupWlanErrorMonitoring 1 }

-- {SCALAR} 1.3.6.1.4.1.248.32.18.2.12.88.2
hmSetupWlanErrorMonitoringTime OBJECT-TYPE
    SYNTAX     Integer32 (0..2147483647)
    MAX-ACCESS read-write
    STATUS     current
    DESCRIPTION
            "-- empty --"
    ::= { hmSetupWlanErrorMonitoring 2 }

-- {SCALAR} 1.3.6.1.4.1.248.32.18.2.12.88.3
hmSetupWlanErrorMonitoringBusErrorCount OBJECT-TYPE
    SYNTAX     Integer32 (0..2147483647)
    MAX-ACCESS read-write
    STATUS     current
    DESCRIPTION
            "-- empty --"
    ::= { hmSetupWlanErrorMonitoring 3 }

-- {SCALAR} 1.3.6.1.4.1.248.32.18.2.12.88.4
hmSetupWlanErrorMonitoringBootType OBJECT-TYPE
    SYNTAX     INTEGER {
                  eWarmBoot (0),
                  eColdBoot (1)
            }
    MAX-ACCESS read-write
    STATUS     current
    DESCRIPTION
            "-- empty --"
    ::= { hmSetupWlanErrorMonitoring 4 }

-- {SCALAR} 1.3.6.1.4.1.248.32.18.2.12.88.5
hmSetupWlanErrorMonitoringNicErrorCount OBJECT-TYPE
    SYNTAX     Integer32 (0..2147483647)
    MAX-ACCESS read-write
    STATUS     current
    DESCRIPTION
            "-- empty --"
    ::= { hmSetupWlanErrorMonitoring 5 }

-- {SCALAR} 1.3.6.1.4.1.248.32.18.2.12.88.6
hmSetupWlanErrorMonitoringAgcCalFailureCount OBJECT-TYPE
    SYNTAX     Integer32 (0..2147483647)
    MAX-ACCESS read-write
    STATUS     current
    DESCRIPTION
            "-- empty --"
    ::= { hmSetupWlanErrorMonitoring 6 }

-- {SCALAR} 1.3.6.1.4.1.248.32.18.2.12.88.7
hmSetupWlanErrorMonitoringStuckInterruptCount OBJECT-TYPE
    SYNTAX     Integer32 (0..2147483647)
    MAX-ACCESS read-write
    STATUS     current
    DESCRIPTION
            "-- empty --"
    ::= { hmSetupWlanErrorMonitoring 7 }

-- {TABLE} 1.3.6.1.4.1.248.32.18.2.12.89
hmSetupWlanAccessRulesTable OBJECT-TYPE
    SYNTAX     SEQUENCE OF HmSetupWlanAccessRulesEntry
    MAX-ACCESS not-accessible
    STATUS     current
    DESCRIPTION
            "-- empty --"
    ::= { hmSetupWlan 89 }

-- {ROW} 1.3.6.1.4.1.248.32.18.2.12.89.1
hmSetupWlanAccessRulesEntry OBJECT-TYPE
    SYNTAX     HmSetupWlanAccessRulesEntry
    MAX-ACCESS not-accessible
    STATUS     current
    DESCRIPTION
            ""
    INDEX {
            hmSetupWlanAccessRulesEntryMacAddressPattern,
            hmSetupWlanAccessRulesEntrySsidPattern
          }
    ::= { hmSetupWlanAccessRulesTable 1 }

HmSetupWlanAccessRulesEntry ::= SEQUENCE {
            hmSetupWlanAccessRulesEntryMacAddressPattern DisplayString,
            hmSetupWlanAccessRulesEntryName DisplayString,
            hmSetupWlanAccessRulesEntryComment DisplayString,
            hmSetupWlanAccessRulesEntryWpaPassphrase DisplayString,
            hmSetupWlanAccessRulesEntryTxLimit Integer32,
            hmSetupWlanAccessRulesEntryRxLimit Integer32,
            hmSetupWlanAccessRulesEntryVlanId Integer32,
            hmSetupWlanAccessRulesEntrySsidPattern DisplayString
    }

-- {COLUMN} 1.3.6.1.4.1.248.32.18.2.12.89.1.1
hmSetupWlanAccessRulesEntryMacAddressPattern OBJECT-TYPE
    SYNTAX     DisplayString (SIZE(0..20))
    MAX-ACCESS read-write
    STATUS     current
    DESCRIPTION
            "-- empty --"
    ::= { hmSetupWlanAccessRulesEntry 1 }

-- {COLUMN} 1.3.6.1.4.1.248.32.18.2.12.89.1.2
hmSetupWlanAccessRulesEntryName OBJECT-TYPE
    SYNTAX     DisplayString (SIZE(0..32))
    MAX-ACCESS read-write
    STATUS     current
    DESCRIPTION
            "-- empty --"
    ::= { hmSetupWlanAccessRulesEntry 2 }

-- {COLUMN} 1.3.6.1.4.1.248.32.18.2.12.89.1.3
hmSetupWlanAccessRulesEntryComment OBJECT-TYPE
    SYNTAX     DisplayString (SIZE(0..30))
    MAX-ACCESS read-write
    STATUS     current
    DESCRIPTION
            "-- empty --"
    ::= { hmSetupWlanAccessRulesEntry 3 }

-- {COLUMN} 1.3.6.1.4.1.248.32.18.2.12.89.1.4
hmSetupWlanAccessRulesEntryWpaPassphrase OBJECT-TYPE
    SYNTAX     DisplayString (SIZE(0..63))
    MAX-ACCESS read-write
    STATUS     current
    DESCRIPTION
            "-- empty --"
    ::= { hmSetupWlanAccessRulesEntry 4 }

-- {COLUMN} 1.3.6.1.4.1.248.32.18.2.12.89.1.5
hmSetupWlanAccessRulesEntryTxLimit OBJECT-TYPE
    SYNTAX     Integer32 (0..2147483647)
    MAX-ACCESS read-write
    STATUS     current
    DESCRIPTION
            "-- empty --"
    ::= { hmSetupWlanAccessRulesEntry 5 }

-- {COLUMN} 1.3.6.1.4.1.248.32.18.2.12.89.1.6
hmSetupWlanAccessRulesEntryRxLimit OBJECT-TYPE
    SYNTAX     Integer32 (0..2147483647)
    MAX-ACCESS read-write
    STATUS     current
    DESCRIPTION
            "-- empty --"
    ::= { hmSetupWlanAccessRulesEntry 6 }

-- {COLUMN} 1.3.6.1.4.1.248.32.18.2.12.89.1.7
hmSetupWlanAccessRulesEntryVlanId OBJECT-TYPE
    SYNTAX     Integer32 (0..65535)
    MAX-ACCESS read-write
    STATUS     current
    DESCRIPTION
            "-- empty --"
    ::= { hmSetupWlanAccessRulesEntry 7 }

-- {COLUMN} 1.3.6.1.4.1.248.32.18.2.12.89.1.8
hmSetupWlanAccessRulesEntrySsidPattern OBJECT-TYPE
    SYNTAX     DisplayString (SIZE(0..40))
    MAX-ACCESS read-write
    STATUS     current
    DESCRIPTION
            "-- empty --"
    ::= { hmSetupWlanAccessRulesEntry 8 }

-- {SCALAR} 1.3.6.1.4.1.248.32.18.2.12.100
hmSetupWlanCardReinitCycle OBJECT-TYPE
    SYNTAX     Integer32 (0..2147483647)
    MAX-ACCESS read-write
    STATUS     current
    DESCRIPTION
            "-- empty --"
    ::= { hmSetupWlan 100 }

-- {SCALAR} 1.3.6.1.4.1.248.32.18.2.12.101
hmSetupWlanNoiseCalibrationCycle OBJECT-TYPE
    SYNTAX     Integer32 (0..2147483647)
    MAX-ACCESS read-write
    STATUS     current
    DESCRIPTION
            "-- empty --"
    ::= { hmSetupWlan 101 }

-- {SCALAR} 1.3.6.1.4.1.248.32.18.2.12.103
hmSetupWlanTraceMac OBJECT-TYPE
    SYNTAX     MacAddress
    MAX-ACCESS read-write
    STATUS     current
    DESCRIPTION
            "-- empty --"
    ::= { hmSetupWlan 103 }

-- {SCALAR} 1.3.6.1.4.1.248.32.18.2.12.105
hmSetupWlanThermRecalCycle OBJECT-TYPE
    SYNTAX     Integer32 (0..2147483647)
    MAX-ACCESS read-write
    STATUS     current
    DESCRIPTION
            "-- empty --"
    ::= { hmSetupWlan 105 }

-- {TABLE} 1.3.6.1.4.1.248.32.18.2.12.107
hmSetupWlanRadarPatternThresholdsTable OBJECT-TYPE
    SYNTAX     SEQUENCE OF HmSetupWlanRadarPatternThresholdsEntry
    MAX-ACCESS not-accessible
    STATUS     current
    DESCRIPTION
            "-- empty --"
    ::= { hmSetupWlan 107 }

-- {ROW} 1.3.6.1.4.1.248.32.18.2.12.107.1
hmSetupWlanRadarPatternThresholdsEntry OBJECT-TYPE
    SYNTAX     HmSetupWlanRadarPatternThresholdsEntry
    MAX-ACCESS not-accessible
    STATUS     current
    DESCRIPTION
            ""
    INDEX {
            hmSetupWlanRadarPatternThresholdsEntryPatternPps
          }
    ::= { hmSetupWlanRadarPatternThresholdsTable 1 }

HmSetupWlanRadarPatternThresholdsEntry ::= SEQUENCE {
            hmSetupWlanRadarPatternThresholdsEntryPatternPps INTEGER,
            hmSetupWlanRadarPatternThresholdsEntryThreshold Integer32
    }

-- {COLUMN} 1.3.6.1.4.1.248.32.18.2.12.107.1.1
hmSetupWlanRadarPatternThresholdsEntryPatternPps OBJECT-TYPE
    SYNTAX     INTEGER {
                  eEn30189313200pps (200),
                  eEn30189313300pps (300),
                  eEn30189312330pps (330),
                  eEn30189313500pps (500),
                  eEn30189312700pps (700),
                  eEn30189313750pps (750),
                  eEn30189313800pps (800),
                  eEn301893131000pps (1000),
                  eEn301893131200pps (1200),
                  eEn301893131500pps (1500),
                  eEn301893131600pps (1600),
                  eEn301893121800pps (1800),
                  eEn301893132000pps (2000),
                  eEn301893132300pps (2300),
                  eEn301893133000pps (3000),
                  eEn301893133500pps (3500),
                  eEn301893134000pps (4000),
                  eEn302502200pps (262344),
                  eEn302502300pps (262444),
                  eEn302502500pps (262644),
                  eEn302502750pps (262894),
                  eEn302502800pps (262944),
                  eEn3025021000pps (263144),
                  eEn3025021200pps (263344),
                  eEn3025021500pps (263644),
                  eEn3025021600pps (263744),
                  eEn3025022000pps (264144),
                  eEn3025022300pps (264444),
                  eEn3025023000pps (265144),
                  eEn3025023500pps (265644),
                  eEn3025024000pps (266144),
                  eEn3025024500pps (266644)
            }
    MAX-ACCESS read-write
    STATUS     current
    DESCRIPTION
            "-- empty --"
    ::= { hmSetupWlanRadarPatternThresholdsEntry 1 }

-- {COLUMN} 1.3.6.1.4.1.248.32.18.2.12.107.1.2
hmSetupWlanRadarPatternThresholdsEntryThreshold OBJECT-TYPE
    SYNTAX     Integer32 (0..2147483647)
    MAX-ACCESS read-write
    STATUS     current
    DESCRIPTION
            "-- empty --"
    ::= { hmSetupWlanRadarPatternThresholdsEntry 2 }

-- {SCALAR} 1.3.6.1.4.1.248.32.18.2.12.108
hmSetupWlanRadarLoadThreshold OBJECT-TYPE
    SYNTAX     Integer32 (0..255)
    MAX-ACCESS read-write
    STATUS     current
    DESCRIPTION
            "-- empty --"
    ::= { hmSetupWlan 108 }

-- {TABLE} 1.3.6.1.4.1.248.32.18.2.12.109
hmSetupWlanNoiseOffsetsTable OBJECT-TYPE
    SYNTAX     SEQUENCE OF HmSetupWlanNoiseOffsetsEntry
    MAX-ACCESS not-accessible
    STATUS     current
    DESCRIPTION
            "-- empty --"
    ::= { hmSetupWlan 109 }

-- {ROW} 1.3.6.1.4.1.248.32.18.2.12.109.1
hmSetupWlanNoiseOffsetsEntry OBJECT-TYPE
    SYNTAX     HmSetupWlanNoiseOffsetsEntry
    MAX-ACCESS not-accessible
    STATUS     current
    DESCRIPTION
            ""
    INDEX {
            hmSetupWlanNoiseOffsetsEntryBand,
            hmSetupWlanNoiseOffsetsEntryChannel,
            hmSetupWlanNoiseOffsetsEntryInterface
          }
    ::= { hmSetupWlanNoiseOffsetsTable 1 }

HmSetupWlanNoiseOffsetsEntry ::= SEQUENCE {
            hmSetupWlanNoiseOffsetsEntryBand INTEGER,
            hmSetupWlanNoiseOffsetsEntryChannel Integer32,
            hmSetupWlanNoiseOffsetsEntryInterface INTEGER,
            hmSetupWlanNoiseOffsetsEntryValue Integer32
    }

-- {COLUMN} 1.3.6.1.4.1.248.32.18.2.12.109.1.1
hmSetupWlanNoiseOffsetsEntryBand OBJECT-TYPE
    SYNTAX     INTEGER {
                  e24ghz (1),
                  e5ghz (2)
            }
    MAX-ACCESS read-write
    STATUS     current
    DESCRIPTION
            "-- empty --"
    ::= { hmSetupWlanNoiseOffsetsEntry 1 }

-- {COLUMN} 1.3.6.1.4.1.248.32.18.2.12.109.1.2
hmSetupWlanNoiseOffsetsEntryChannel OBJECT-TYPE
    SYNTAX     Integer32 (0..65535)
    MAX-ACCESS read-write
    STATUS     current
    DESCRIPTION
            "-- empty --"
    ::= { hmSetupWlanNoiseOffsetsEntry 2 }

-- {COLUMN} 1.3.6.1.4.1.248.32.18.2.12.109.1.3
hmSetupWlanNoiseOffsetsEntryInterface OBJECT-TYPE
    SYNTAX     INTEGER {
                  eWlan1 (1),
                  eWlan2 (2)
            }
    MAX-ACCESS read-write
    STATUS     current
    DESCRIPTION
            "-- empty --"
    ::= { hmSetupWlanNoiseOffsetsEntry 3 }

-- {COLUMN} 1.3.6.1.4.1.248.32.18.2.12.109.1.4
hmSetupWlanNoiseOffsetsEntryValue OBJECT-TYPE
    SYNTAX     Integer32 (-128..127)
    MAX-ACCESS read-write
    STATUS     current
    DESCRIPTION
            "-- empty --"
    ::= { hmSetupWlanNoiseOffsetsEntry 4 }

-- {SCALAR} 1.3.6.1.4.1.248.32.18.2.12.110
hmSetupWlanTraceLevel OBJECT-TYPE
    SYNTAX     Integer32 (0..255)
    MAX-ACCESS read-write
    STATUS     current
    DESCRIPTION
            "-- empty --"
    ::= { hmSetupWlan 110 }

-- {NODE} 1.3.6.1.4.1.248.32.18.2.12.111
hmSetupWlanNoiseImmunity OBJECT IDENTIFIER ::= { hmSetupWlan 111 }

-- {SCALAR} 1.3.6.1.4.1.248.32.18.2.12.111.1
hmSetupWlanNoiseImmunityNoiseImmunityLevel OBJECT-TYPE
    SYNTAX     Integer32 (0..255)
    MAX-ACCESS read-write
    STATUS     current
    DESCRIPTION
            "-- empty --"
    ::= { hmSetupWlanNoiseImmunity 1 }

-- {SCALAR} 1.3.6.1.4.1.248.32.18.2.12.111.2
hmSetupWlanNoiseImmunityOfdmWeakSignalDetection OBJECT-TYPE
    SYNTAX     Integer32 (0..255)
    MAX-ACCESS read-write
    STATUS     current
    DESCRIPTION
            "-- empty --"
    ::= { hmSetupWlanNoiseImmunity 2 }

-- {SCALAR} 1.3.6.1.4.1.248.32.18.2.12.111.3
hmSetupWlanNoiseImmunityCckWeakSignalDetectionThreshold OBJECT-TYPE
    SYNTAX     Integer32 (0..255)
    MAX-ACCESS read-write
    STATUS     current
    DESCRIPTION
            "-- empty --"
    ::= { hmSetupWlanNoiseImmunity 3 }

-- {SCALAR} 1.3.6.1.4.1.248.32.18.2.12.111.4
hmSetupWlanNoiseImmunityFirStepLevel OBJECT-TYPE
    SYNTAX     Integer32 (0..255)
    MAX-ACCESS read-write
    STATUS     current
    DESCRIPTION
            "-- empty --"
    ::= { hmSetupWlanNoiseImmunity 4 }

-- {SCALAR} 1.3.6.1.4.1.248.32.18.2.12.111.5
hmSetupWlanNoiseImmunitySpuriousImmunityLevel OBJECT-TYPE
    SYNTAX     Integer32 (0..255)
    MAX-ACCESS read-write
    STATUS     current
    DESCRIPTION
            "-- empty --"
    ::= { hmSetupWlanNoiseImmunity 5 }

-- {SCALAR} 1.3.6.1.4.1.248.32.18.2.12.111.6
hmSetupWlanNoiseImmunityMrcCck OBJECT-TYPE
    SYNTAX     Integer32 (0..255)
    MAX-ACCESS read-write
    STATUS     current
    DESCRIPTION
            "-- empty --"
    ::= { hmSetupWlanNoiseImmunity 6 }

-- {SCALAR} 1.3.6.1.4.1.248.32.18.2.12.114
hmSetupWlanAggregateRetryLimit OBJECT-TYPE
    SYNTAX     Integer32 (0..255)
    MAX-ACCESS read-write
    STATUS     current
    DESCRIPTION
            "-- empty --"
    ::= { hmSetupWlan 114 }

-- {SCALAR} 1.3.6.1.4.1.248.32.18.2.12.115
hmSetupWlanOmitGlobalCryptoSequenceCheck OBJECT-TYPE
    SYNTAX     INTEGER {
                  eAuto (0),
                  eNo (1),
                  eYes (2)
            }
    MAX-ACCESS read-write
    STATUS     current
    DESCRIPTION
            "-- empty --"
    ::= { hmSetupWlan 115 }

-- {SCALAR} 1.3.6.1.4.1.248.32.18.2.12.116
hmSetupWlanTracePackets OBJECT-TYPE
    SYNTAX     BITS {
                  eAll (0),
                  eEapol (4),
                  eData (5),
                  eControl (6),
                  eManagement (7)
            }
    MAX-ACCESS read-write
    STATUS     current
    DESCRIPTION
            "-- empty --"
    ::= { hmSetupWlan 116 }

-- {SCALAR} 1.3.6.1.4.1.248.32.18.2.12.117
hmSetupWlanWpaHandshakeDelayMs OBJECT-TYPE
    SYNTAX     Integer32 (0..2147483647)
    MAX-ACCESS read-write
    STATUS     current
    DESCRIPTION
            "-- empty --"
    ::= { hmSetupWlan 117 }

-- {SCALAR} 1.3.6.1.4.1.248.32.18.2.12.118
hmSetupWlanWpaHandshakeTimeoutOverrideMs OBJECT-TYPE
    SYNTAX     Integer32 (0..2147483647)
    MAX-ACCESS read-write
    STATUS     current
    DESCRIPTION
            "-- empty --"
    ::= { hmSetupWlan 118 }

-- {SCALAR} 1.3.6.1.4.1.248.32.18.2.12.119
hmSetupWlanTraceBeacons OBJECT-TYPE
    SYNTAX     INTEGER {
                  eNo (0),
                  eYes (1)
            }
    MAX-ACCESS read-write
    STATUS     current
    DESCRIPTION
            "-- empty --"
    ::= { hmSetupWlan 119 }

-- {SCALAR} 1.3.6.1.4.1.248.32.18.2.12.120
hmSetupWlanRxAggregateFlushTimeoutMs OBJECT-TYPE
    SYNTAX     Integer32 (0..2147483647)
    MAX-ACCESS read-write
    STATUS     current
    DESCRIPTION
            "-- empty --"
    ::= { hmSetupWlan 120 }

-- {SCALAR} 1.3.6.1.4.1.248.32.18.2.12.121
hmSetupWlanHtFairness OBJECT-TYPE
    SYNTAX     INTEGER {
                  eNo (0),
                  eYes (1)
            }
    MAX-ACCESS read-write
    STATUS     current
    DESCRIPTION
            "-- empty --"
    ::= { hmSetupWlan 121 }

-- {SCALAR} 1.3.6.1.4.1.248.32.18.2.12.122
hmSetupWlanDfsTestmode OBJECT-TYPE
    SYNTAX     INTEGER {
                  eNo (0),
                  eYes (1)
            }
    MAX-ACCESS read-write
    STATUS     current
    DESCRIPTION
            "-- empty --"
    ::= { hmSetupWlan 122 }

-- {SCALAR} 1.3.6.1.4.1.248.32.18.2.12.124
hmSetupWlanTraceMgmtPackets OBJECT-TYPE
    SYNTAX     BITS {
                  eOther (2),
                  eBeacon (3),
                  eAction (4),
                  eProbe (5),
                  eAuthentication (6),
                  eAssociation (7)
            }
    MAX-ACCESS read-write
    STATUS     current
    DESCRIPTION
            "-- empty --"
    ::= { hmSetupWlan 124 }

-- {SCALAR} 1.3.6.1.4.1.248.32.18.2.12.125
hmSetupWlanTraceDataPackets OBJECT-TYPE
    SYNTAX     BITS {
                  eOther (5),
                  eNull (6),
                  eNormal (7)
            }
    MAX-ACCESS read-write
    STATUS     current
    DESCRIPTION
            "-- empty --"
    ::= { hmSetupWlan 125 }

-- {NODE} 1.3.6.1.4.1.248.32.18.2.12.130
hmSetupWlanDfs OBJECT IDENTIFIER ::= { hmSetupWlan 130 }

-- {SCALAR} 1.3.6.1.4.1.248.32.18.2.12.130.1
hmSetupWlanDfsUseFullChannelset OBJECT-TYPE
    SYNTAX     INTEGER {
                  eNo (0),
                  eYes (1)
            }
    MAX-ACCESS read-write
    STATUS     current
    DESCRIPTION
            "-- empty --"
    ::= { hmSetupWlanDfs 1 }

-- {SCALAR} 1.3.6.1.4.1.248.32.18.2.12.130.2
hmSetupWlanDfsRadarLoadThreshold OBJECT-TYPE
    SYNTAX     Integer32 (0..255)
    MAX-ACCESS read-write
    STATUS     current
    DESCRIPTION
            "-- empty --"
    ::= { hmSetupWlanDfs 2 }

-- {SCALAR} 1.3.6.1.4.1.248.32.18.2.12.130.3
hmSetupWlanDfsDirectChannelswitching OBJECT-TYPE
    SYNTAX     INTEGER {
                  eNo (0),
                  eYes (1)
            }
    MAX-ACCESS read-write
    STATUS     current
    DESCRIPTION
            "-- empty --"
    ::= { hmSetupWlanDfs 3 }

-- {SCALAR} 1.3.6.1.4.1.248.32.18.2.12.130.4
hmSetupWlanDfsDfsTestmode OBJECT-TYPE
    SYNTAX     INTEGER {
                  eNo (0),
                  eYes (1)
            }
    MAX-ACCESS read-write
    STATUS     current
    DESCRIPTION
            "-- empty --"
    ::= { hmSetupWlanDfs 4 }

-- {SCALAR} 1.3.6.1.4.1.248.32.18.2.12.130.5
hmSetupWlanDfsIgnoreCrcErrors OBJECT-TYPE
    SYNTAX     INTEGER {
                  eNo (0),
                  eYes (1)
            }
    MAX-ACCESS read-write
    STATUS     current
    DESCRIPTION
            "-- empty --"
    ::= { hmSetupWlanDfs 5 }

-- {SCALAR} 1.3.6.1.4.1.248.32.18.2.12.130.6
hmSetupWlanDfsTraceIgnoredPulses OBJECT-TYPE
    SYNTAX     INTEGER {
                  eNo (0),
                  eYes (1)
            }
    MAX-ACCESS read-write
    STATUS     current
    DESCRIPTION
            "-- empty --"
    ::= { hmSetupWlanDfs 6 }

-- {SCALAR} 1.3.6.1.4.1.248.32.18.2.12.130.7
hmSetupWlanDfsGoForHighestBandwidth OBJECT-TYPE
    SYNTAX     INTEGER {
                  eNo (0),
                  eYes (1)
            }
    MAX-ACCESS read-write
    STATUS     current
    DESCRIPTION
            "-- empty --"
    ::= { hmSetupWlanDfs 7 }

-- {SCALAR} 1.3.6.1.4.1.248.32.18.2.12.130.8
hmSetupWlanDfsPreferFastSwitch OBJECT-TYPE
    SYNTAX     INTEGER {
                  eNo (0),
                  eYes (1)
            }
    MAX-ACCESS read-write
    STATUS     current
    DESCRIPTION
            "-- empty --"
    ::= { hmSetupWlanDfs 8 }

-- {SCALAR} 1.3.6.1.4.1.248.32.18.2.12.130.9
hmSetupWlanDfsChannelChangeDelay OBJECT-TYPE
    SYNTAX     Integer32 (0..255)
    MAX-ACCESS read-write
    STATUS     current
    DESCRIPTION
            "-- empty --"
    ::= { hmSetupWlanDfs 9 }

-- {TABLE} 1.3.6.1.4.1.248.32.18.2.12.130.10
hmSetupWlanDfsRadarPatternThresholdsTable OBJECT-TYPE
    SYNTAX     SEQUENCE OF HmSetupWlanDfsRadarPatternThresholdsEntry
    MAX-ACCESS not-accessible
    STATUS     current
    DESCRIPTION
            "-- empty --"
    ::= { hmSetupWlanDfs 10 }

-- {ROW} 1.3.6.1.4.1.248.32.18.2.12.130.10.1
hmSetupWlanDfsRadarPatternThresholdsEntry OBJECT-TYPE
    SYNTAX     HmSetupWlanDfsRadarPatternThresholdsEntry
    MAX-ACCESS not-accessible
    STATUS     current
    DESCRIPTION
            ""
    INDEX {
            hmSetupWlanDfsRadarPatternThresholdsEntryPatternPps
          }
    ::= { hmSetupWlanDfsRadarPatternThresholdsTable 1 }

HmSetupWlanDfsRadarPatternThresholdsEntry ::= SEQUENCE {
            hmSetupWlanDfsRadarPatternThresholdsEntryPatternPps INTEGER,
            hmSetupWlanDfsRadarPatternThresholdsEntryThreshold Integer32
    }

-- {COLUMN} 1.3.6.1.4.1.248.32.18.2.12.130.10.1.1
hmSetupWlanDfsRadarPatternThresholdsEntryPatternPps OBJECT-TYPE
    SYNTAX     INTEGER {
                  eEn30189313200pps (200),
                  eEn30189313300pps (300),
                  eEn30189312330pps (330),
                  eEn30189313500pps (500),
                  eEn30189312700pps (700),
                  eEn30189313750pps (750),
                  eEn30189313800pps (800),
                  eEn301893131000pps (1000),
                  eEn301893131200pps (1200),
                  eEn301893131500pps (1500),
                  eEn301893131600pps (1600),
                  eEn301893121800pps (1800),
                  eEn301893132000pps (2000),
                  eEn301893132300pps (2300),
                  eEn301893133000pps (3000),
                  eEn301893133500pps (3500),
                  eEn301893134000pps (4000),
                  eEn302502200pps (262344),
                  eEn302502300pps (262444),
                  eEn302502500pps (262644),
                  eEn302502750pps (262894),
                  eEn302502800pps (262944),
                  eEn3025021000pps (263144),
                  eEn3025021200pps (263344),
                  eEn3025021500pps (263644),
                  eEn3025021600pps (263744),
                  eEn3025022000pps (264144),
                  eEn3025022300pps (264444),
                  eEn3025023000pps (265144),
                  eEn3025023500pps (265644),
                  eEn3025024000pps (266144),
                  eEn3025024500pps (266644)
            }
    MAX-ACCESS read-write
    STATUS     current
    DESCRIPTION
            "-- empty --"
    ::= { hmSetupWlanDfsRadarPatternThresholdsEntry 1 }

-- {COLUMN} 1.3.6.1.4.1.248.32.18.2.12.130.10.1.2
hmSetupWlanDfsRadarPatternThresholdsEntryThreshold OBJECT-TYPE
    SYNTAX     Integer32 (0..2147483647)
    MAX-ACCESS read-write
    STATUS     current
    DESCRIPTION
            "-- empty --"
    ::= { hmSetupWlanDfsRadarPatternThresholdsEntry 2 }

-- {SCALAR} 1.3.6.1.4.1.248.32.18.2.12.130.11
hmSetupWlanDfsMinInternalChannelDistance OBJECT-TYPE
    SYNTAX     Integer32 (0..255)
    MAX-ACCESS read-write
    STATUS     current
    DESCRIPTION
            "-- empty --"
    ::= { hmSetupWlanDfs 11 }

-- {NODE} 1.3.6.1.4.1.248.32.18.2.12.248
hmSetupWlanWirelessIds OBJECT IDENTIFIER ::= { hmSetupWlan 248 }

-- {SCALAR} 1.3.6.1.4.1.248.32.18.2.12.248.9
hmSetupWlanWirelessIdsIdsOperational OBJECT-TYPE
    SYNTAX     INTEGER {
                  eNo (0),
                  eYes (1)
            }
    MAX-ACCESS read-write
    STATUS     current
    DESCRIPTION
            ""
    ::= { hmSetupWlanWirelessIds 9 }

-- {SCALAR} 1.3.6.1.4.1.248.32.18.2.12.248.10
hmSetupWlanWirelessIdsSyslogOperational OBJECT-TYPE
    SYNTAX     INTEGER {
                  eNo (0),
                  eYes (1)
            }
    MAX-ACCESS read-write
    STATUS     current
    DESCRIPTION
            ""
    ::= { hmSetupWlanWirelessIds 10 }

-- {SCALAR} 1.3.6.1.4.1.248.32.18.2.12.248.11
hmSetupWlanWirelessIdsSNMPTrapsOperational OBJECT-TYPE
    SYNTAX     INTEGER {
                  eNo (0),
                  eYes (1)
            }
    MAX-ACCESS read-write
    STATUS     current
    DESCRIPTION
            ""
    ::= { hmSetupWlanWirelessIds 11 }

-- {SCALAR} 1.3.6.1.4.1.248.32.18.2.12.248.12
hmSetupWlanWirelessIdsEMail OBJECT-TYPE
    SYNTAX     INTEGER {
                  eNo (0),
                  eYes (1)
            }
    MAX-ACCESS read-write
    STATUS     current
    DESCRIPTION
            "-- empty --"
    ::= { hmSetupWlanWirelessIds 12 }

-- {SCALAR} 1.3.6.1.4.1.248.32.18.2.12.248.13
hmSetupWlanWirelessIdsEMailReceiver OBJECT-TYPE
    SYNTAX     DisplayString (SIZE(0..63))
    MAX-ACCESS read-write
    STATUS     current
    DESCRIPTION
            "-- empty --"
    ::= { hmSetupWlanWirelessIds 13 }

-- {SCALAR} 1.3.6.1.4.1.248.32.18.2.12.248.14
hmSetupWlanWirelessIdsEMailAggregateInterval OBJECT-TYPE
    SYNTAX     Integer32 (0..2147483647)
    MAX-ACCESS read-write
    STATUS     current
    DESCRIPTION
            ""
    ::= { hmSetupWlanWirelessIds 14 }

-- {SCALAR} 1.3.6.1.4.1.248.32.18.2.12.248.15
hmSetupWlanWirelessIdsEAPOLStartCounterTime OBJECT-TYPE
    SYNTAX     Integer32 (0..2147483647)
    MAX-ACCESS read-only
    STATUS     deprecated
    DESCRIPTION
            "This object is deprecated. Please use hmSetupWlanWirelessIdsSigEapolstartCtrInt instead."
    ::= { hmSetupWlanWirelessIds 15 }

-- {SCALAR} 1.3.6.1.4.1.248.32.18.2.12.248.16
hmSetupWlanWirelessIdsProbeBroadCounterTime OBJECT-TYPE
    SYNTAX     Integer32 (0..2147483647)
    MAX-ACCESS read-only
    STATUS     deprecated
    DESCRIPTION
            "This object is deprecated. Please use hmSetupWlanWirelessIdsSigProbeBroadCtrInt instead."
    ::= { hmSetupWlanWirelessIds 16 }

-- {SCALAR} 1.3.6.1.4.1.248.32.18.2.12.248.17
hmSetupWlanWirelessIdsDeauthenticateBroadCounterTime OBJECT-TYPE
    SYNTAX     Integer32 (0..2147483647)
    MAX-ACCESS read-only
    STATUS     deprecated
    DESCRIPTION
            "This object is deprecated. Please use hmSetupWlanWirelessIdsSigDeAuthBroadCtrInt instead."
    ::= { hmSetupWlanWirelessIds 17 }

-- {SCALAR} 1.3.6.1.4.1.248.32.18.2.12.248.18
hmSetupWlanWirelessIdsDeauthenticateCounterTime OBJECT-TYPE
    SYNTAX     Integer32 (0..2147483647)
    MAX-ACCESS read-only
    STATUS     deprecated
    DESCRIPTION
            "This object is deprecated. Please use hmSetupWlanWirelessIdsSigDeauthCtrInt instead."
    ::= { hmSetupWlanWirelessIds 18 }

-- {SCALAR} 1.3.6.1.4.1.248.32.18.2.12.248.19
hmSetupWlanWirelessIdsAssociateReqCounterTime OBJECT-TYPE
    SYNTAX     Integer32 (0..2147483647)
    MAX-ACCESS read-only
    STATUS     deprecated
    DESCRIPTION
            "This object is deprecated. Please use hmSetupWlanWirelessIdsSigAssocReqCtrInt instead."
    ::= { hmSetupWlanWirelessIds 19 }

-- {SCALAR} 1.3.6.1.4.1.248.32.18.2.12.248.20
hmSetupWlanWirelessIdsReAssociateReqCounterTime OBJECT-TYPE
    SYNTAX     Integer32 (0..2147483647)
    MAX-ACCESS read-only
    STATUS     deprecated
    DESCRIPTION
            "This object is deprecated. Please use hmSetupWlanWirelessIdsSigReAssocReqCtrInt instead."
    ::= { hmSetupWlanWirelessIds 20 }

-- {SCALAR} 1.3.6.1.4.1.248.32.18.2.12.248.21
hmSetupWlanWirelessIdsAuthenticateCounterTime OBJECT-TYPE
    SYNTAX     Integer32 (0..2147483647)
    MAX-ACCESS read-only
    STATUS     deprecated
    DESCRIPTION
            "This object is deprecated. Please use hmSetupWlanWirelessIdsSigAuthCtrInt instead."
    ::= { hmSetupWlanWirelessIds 21 }

-- {SCALAR} 1.3.6.1.4.1.248.32.18.2.12.248.22
hmSetupWlanWirelessIdsDisAssociateReqCounterTime OBJECT-TYPE
    SYNTAX     Integer32 (0..2147483647)
    MAX-ACCESS read-only
    STATUS     deprecated
    DESCRIPTION
            "This object is deprecated. Please use hmSetupWlanWirelessIdsSigDisAssocCtrInt instead."
    ::= { hmSetupWlanWirelessIds 22 }

-- {SCALAR} 1.3.6.1.4.1.248.32.18.2.12.248.43
hmSetupWlanWirelessIdsIntruderIdentification OBJECT-TYPE
    SYNTAX     INTEGER {
                  eNo (0),
                  eYes (1)
            }
    MAX-ACCESS read-write
    STATUS     current
    DESCRIPTION
            "-- empty --"
    ::= { hmSetupWlanWirelessIds 43 }

-- {SCALAR} 1.3.6.1.4.1.248.32.18.2.12.248.44
hmSetupWlanWirelessIdsTimeoutIntruderActivity OBJECT-TYPE
    SYNTAX     Integer32 (0..2147483647)
    MAX-ACCESS read-write
    STATUS     current
    DESCRIPTION
            "-- empty --"
    ::= { hmSetupWlanWirelessIds 44 }

-- {SCALAR} 1.3.6.1.4.1.248.32.18.2.12.248.45
hmSetupWlanWirelessIdsStoreIntruderDhcpRequests OBJECT-TYPE
    SYNTAX     INTEGER {
                  eNo (0),
                  eYes (1)
            }
    MAX-ACCESS read-write
    STATUS     current
    DESCRIPTION
            "-- empty --"
    ::= { hmSetupWlanWirelessIds 45 }

-- {NODE} 1.3.6.1.4.1.248.32.18.2.12.248.50
hmSetupWlanWirelessIdsSig OBJECT IDENTIFIER ::= { hmSetupWlanWirelessIds 50 }

-- {NODE} 1.3.6.1.4.1.248.32.18.2.12.248.50.1
hmSetupWlanWirelessIdsSigAssociatereqflood OBJECT IDENTIFIER ::= { hmSetupWlanWirelessIdsSig 1 }

-- {SCALAR} 1.3.6.1.4.1.248.32.18.2.12.248.50.1.1
hmSetupWlanWirelessIdsSigAssociatereqfloodCtrLim OBJECT-TYPE
    SYNTAX     Integer32 (0..2147483647)
    MAX-ACCESS read-write
    STATUS     current
    DESCRIPTION
            ""
    ::= { hmSetupWlanWirelessIdsSigAssociatereqflood 1 }

-- {SCALAR} 1.3.6.1.4.1.248.32.18.2.12.248.50.1.2
hmSetupWlanWirelessIdsSigAssociatereqfloodCtrInt OBJECT-TYPE
    SYNTAX     Integer32 (0..2147483647)
    MAX-ACCESS read-write
    STATUS     current
    DESCRIPTION
            ""
    ::= { hmSetupWlanWirelessIdsSigAssociatereqflood 2 }

-- {NODE} 1.3.6.1.4.1.248.32.18.2.12.248.50.2
hmSetupWlanWirelessIdsSigReassociatereqflood OBJECT IDENTIFIER ::= { hmSetupWlanWirelessIdsSig 2 }

-- {SCALAR} 1.3.6.1.4.1.248.32.18.2.12.248.50.2.1
hmSetupWlanWirelessIdsSigReassociatereqfloodCtrLim OBJECT-TYPE
    SYNTAX     Integer32 (0..2147483647)
    MAX-ACCESS read-write
    STATUS     current
    DESCRIPTION
            ""
    ::= { hmSetupWlanWirelessIdsSigReassociatereqflood 1 }

-- {SCALAR} 1.3.6.1.4.1.248.32.18.2.12.248.50.2.2
hmSetupWlanWirelessIdsSigReassociatereqfloodCtrInt OBJECT-TYPE
    SYNTAX     Integer32 (0..2147483647)
    MAX-ACCESS read-write
    STATUS     current
    DESCRIPTION
            ""
    ::= { hmSetupWlanWirelessIdsSigReassociatereqflood 2 }

-- {NODE} 1.3.6.1.4.1.248.32.18.2.12.248.50.3
hmSetupWlanWirelessIdsSigAuthenticatereqflood OBJECT IDENTIFIER ::= { hmSetupWlanWirelessIdsSig 3 }

-- {SCALAR} 1.3.6.1.4.1.248.32.18.2.12.248.50.3.1
hmSetupWlanWirelessIdsSigAuthenticatereqfloodCtrLim OBJECT-TYPE
    SYNTAX     Integer32 (0..2147483647)
    MAX-ACCESS read-write
    STATUS     current
    DESCRIPTION
            ""
    ::= { hmSetupWlanWirelessIdsSigAuthenticatereqflood 1 }

-- {SCALAR} 1.3.6.1.4.1.248.32.18.2.12.248.50.3.2
hmSetupWlanWirelessIdsSigAuthenticatereqfloodCtrInt OBJECT-TYPE
    SYNTAX     Integer32 (0..2147483647)
    MAX-ACCESS read-write
    STATUS     current
    DESCRIPTION
            ""
    ::= { hmSetupWlanWirelessIdsSigAuthenticatereqflood 2 }

-- {NODE} 1.3.6.1.4.1.248.32.18.2.12.248.50.4
hmSetupWlanWirelessIdsSigEapolstart OBJECT IDENTIFIER ::= { hmSetupWlanWirelessIdsSig 4 }

-- {SCALAR} 1.3.6.1.4.1.248.32.18.2.12.248.50.4.1
hmSetupWlanWirelessIdsSigEapolstartCtrLim OBJECT-TYPE
    SYNTAX     Integer32 (0..2147483647)
    MAX-ACCESS read-write
    STATUS     current
    DESCRIPTION
            ""
    ::= { hmSetupWlanWirelessIdsSigEapolstart 1 }

-- {SCALAR} 1.3.6.1.4.1.248.32.18.2.12.248.50.4.2
hmSetupWlanWirelessIdsSigEapolstartCtrInt OBJECT-TYPE
    SYNTAX     Integer32 (0..2147483647)
    MAX-ACCESS read-write
    STATUS     current
    DESCRIPTION
            ""
    ::= { hmSetupWlanWirelessIdsSigEapolstart 2 }

-- {NODE} 1.3.6.1.4.1.248.32.18.2.12.248.50.5
hmSetupWlanWirelessIdsSigProbebroadcast OBJECT IDENTIFIER ::= { hmSetupWlanWirelessIdsSig 5 }

-- {SCALAR} 1.3.6.1.4.1.248.32.18.2.12.248.50.5.1
hmSetupWlanWirelessIdsSigProbebroadcastCtrLim OBJECT-TYPE
    SYNTAX     Integer32 (0..2147483647)
    MAX-ACCESS read-write
    STATUS     current
    DESCRIPTION
            ""
    ::= { hmSetupWlanWirelessIdsSigProbebroadcast 1 }

-- {SCALAR} 1.3.6.1.4.1.248.32.18.2.12.248.50.5.2
hmSetupWlanWirelessIdsSigProbebroadcastCtrInt OBJECT-TYPE
    SYNTAX     Integer32 (0..2147483647)
    MAX-ACCESS read-write
    STATUS     current
    DESCRIPTION
            ""
    ::= { hmSetupWlanWirelessIdsSigProbebroadcast 2 }

-- {NODE} 1.3.6.1.4.1.248.32.18.2.12.248.50.6
hmSetupWlanWirelessIdsSigDisassociatebroadcast OBJECT IDENTIFIER ::= { hmSetupWlanWirelessIdsSig 6 }

-- {SCALAR} 1.3.6.1.4.1.248.32.18.2.12.248.50.6.1
hmSetupWlanWirelessIdsSigDisassociatebroadcastCtrLim OBJECT-TYPE
    SYNTAX     Integer32 (0..2147483647)
    MAX-ACCESS read-write
    STATUS     current
    DESCRIPTION
            ""
    ::= { hmSetupWlanWirelessIdsSigDisassociatebroadcast 1 }

-- {SCALAR} 1.3.6.1.4.1.248.32.18.2.12.248.50.6.2
hmSetupWlanWirelessIdsSigDisassociatebroadcastCtrInt OBJECT-TYPE
    SYNTAX     Integer32 (0..2147483647)
    MAX-ACCESS read-write
    STATUS     current
    DESCRIPTION
            ""
    ::= { hmSetupWlanWirelessIdsSigDisassociatebroadcast 2 }

-- {NODE} 1.3.6.1.4.1.248.32.18.2.12.248.50.7
hmSetupWlanWirelessIdsSigDeauthenticatebroadcast OBJECT IDENTIFIER ::= { hmSetupWlanWirelessIdsSig 7 }

-- {SCALAR} 1.3.6.1.4.1.248.32.18.2.12.248.50.7.1
hmSetupWlanWirelessIdsSigDeauthenticatebroadcastCtrLim OBJECT-TYPE
    SYNTAX     Integer32 (0..2147483647)
    MAX-ACCESS read-write
    STATUS     current
    DESCRIPTION
            ""
    ::= { hmSetupWlanWirelessIdsSigDeauthenticatebroadcast 1 }

-- {SCALAR} 1.3.6.1.4.1.248.32.18.2.12.248.50.7.2
hmSetupWlanWirelessIdsSigDeauthenticatebroadcastCtrInt OBJECT-TYPE
    SYNTAX     Integer32 (0..2147483647)
    MAX-ACCESS read-write
    STATUS     current
    DESCRIPTION
            ""
    ::= { hmSetupWlanWirelessIdsSigDeauthenticatebroadcast 2 }

-- {NODE} 1.3.6.1.4.1.248.32.18.2.12.248.50.8
hmSetupWlanWirelessIdsSigDisassociatereqflood OBJECT IDENTIFIER ::= { hmSetupWlanWirelessIdsSig 8 }

-- {SCALAR} 1.3.6.1.4.1.248.32.18.2.12.248.50.8.1
hmSetupWlanWirelessIdsSigDisassociatereqfloodCtrLim OBJECT-TYPE
    SYNTAX     Integer32 (0..2147483647)
    MAX-ACCESS read-write
    STATUS     current
    DESCRIPTION
            ""
    ::= { hmSetupWlanWirelessIdsSigDisassociatereqflood 1 }

-- {SCALAR} 1.3.6.1.4.1.248.32.18.2.12.248.50.8.2
hmSetupWlanWirelessIdsSigDisassociatereqfloodCtrInt OBJECT-TYPE
    SYNTAX     Integer32 (0..2147483647)
    MAX-ACCESS read-write
    STATUS     current
    DESCRIPTION
            ""
    ::= { hmSetupWlanWirelessIdsSigDisassociatereqflood 2 }

-- {NODE} 1.3.6.1.4.1.248.32.18.2.12.248.50.9
hmSetupWlanWirelessIdsSigBlockackoutofwindow OBJECT IDENTIFIER ::= { hmSetupWlanWirelessIdsSig 9 }

-- {SCALAR} 1.3.6.1.4.1.248.32.18.2.12.248.50.9.1
hmSetupWlanWirelessIdsSigBlockackoutofwindowCtrLim OBJECT-TYPE
    SYNTAX     Integer32 (0..2147483647)
    MAX-ACCESS read-write
    STATUS     current
    DESCRIPTION
            ""
    ::= { hmSetupWlanWirelessIdsSigBlockackoutofwindow 1 }

-- {SCALAR} 1.3.6.1.4.1.248.32.18.2.12.248.50.9.2
hmSetupWlanWirelessIdsSigBlockackoutofwindowCtrInt OBJECT-TYPE
    SYNTAX     Integer32 (0..2147483647)
    MAX-ACCESS read-write
    STATUS     current
    DESCRIPTION
            ""
    ::= { hmSetupWlanWirelessIdsSigBlockackoutofwindow 2 }

-- {NODE} 1.3.6.1.4.1.248.32.18.2.12.248.50.10
hmSetupWlanWirelessIdsSigBlockackafterdelba OBJECT IDENTIFIER ::= { hmSetupWlanWirelessIdsSig 10 }

-- {SCALAR} 1.3.6.1.4.1.248.32.18.2.12.248.50.10.1
hmSetupWlanWirelessIdsSigBlockackafterdelbaCtrLim OBJECT-TYPE
    SYNTAX     Integer32 (0..2147483647)
    MAX-ACCESS read-write
    STATUS     current
    DESCRIPTION
            ""
    ::= { hmSetupWlanWirelessIdsSigBlockackafterdelba 1 }

-- {SCALAR} 1.3.6.1.4.1.248.32.18.2.12.248.50.10.2
hmSetupWlanWirelessIdsSigBlockackafterdelbaCtrInt OBJECT-TYPE
    SYNTAX     Integer32 (0..2147483647)
    MAX-ACCESS read-write
    STATUS     current
    DESCRIPTION
            ""
    ::= { hmSetupWlanWirelessIdsSigBlockackafterdelba 2 }

-- {NODE} 1.3.6.1.4.1.248.32.18.2.12.248.50.11
hmSetupWlanWirelessIdsSigNulldataflood OBJECT IDENTIFIER ::= { hmSetupWlanWirelessIdsSig 11 }

-- {SCALAR} 1.3.6.1.4.1.248.32.18.2.12.248.50.11.1
hmSetupWlanWirelessIdsSigNulldatafloodCtrLim OBJECT-TYPE
    SYNTAX     Integer32 (0..2147483647)
    MAX-ACCESS read-write
    STATUS     current
    DESCRIPTION
            ""
    ::= { hmSetupWlanWirelessIdsSigNulldataflood 1 }

-- {SCALAR} 1.3.6.1.4.1.248.32.18.2.12.248.50.11.2
hmSetupWlanWirelessIdsSigNulldatafloodCtrInt OBJECT-TYPE
    SYNTAX     Integer32 (0..2147483647)
    MAX-ACCESS read-write
    STATUS     current
    DESCRIPTION
            ""
    ::= { hmSetupWlanWirelessIdsSigNulldataflood 2 }

-- {NODE} 1.3.6.1.4.1.248.32.18.2.12.248.50.12
hmSetupWlanWirelessIdsSigNullDataPSOv OBJECT IDENTIFIER ::= { hmSetupWlanWirelessIdsSig 12 }

-- {SCALAR} 1.3.6.1.4.1.248.32.18.2.12.248.50.12.1
hmSetupWlanWirelessIdsSigNullDataPSOvCtrLim OBJECT-TYPE
    SYNTAX     Integer32 (0..2147483647)
    MAX-ACCESS read-write
    STATUS     current
    DESCRIPTION
            ""
    ::= { hmSetupWlanWirelessIdsSigNullDataPSOv 1 }

-- {SCALAR} 1.3.6.1.4.1.248.32.18.2.12.248.50.12.2
hmSetupWlanWirelessIdsSigNullDataPSOvCtrInt OBJECT-TYPE
    SYNTAX     Integer32 (0..2147483647)
    MAX-ACCESS read-write
    STATUS     current
    DESCRIPTION
            ""
    ::= { hmSetupWlanWirelessIdsSigNullDataPSOv 2 }

-- {NODE} 1.3.6.1.4.1.248.32.18.2.12.248.50.13
hmSetupWlanWirelessIdsSigPspolltiminterval OBJECT IDENTIFIER ::= { hmSetupWlanWirelessIdsSig 13 }

-- {SCALAR} 1.3.6.1.4.1.248.32.18.2.12.248.50.13.1
hmSetupWlanWirelessIdsSigPspolltimintervalCtrLim OBJECT-TYPE
    SYNTAX     Integer32 (0..2147483647)
    MAX-ACCESS read-write
    STATUS     current
    DESCRIPTION
            ""
    ::= { hmSetupWlanWirelessIdsSigPspolltiminterval 1 }

-- {SCALAR} 1.3.6.1.4.1.248.32.18.2.12.248.50.13.2
hmSetupWlanWirelessIdsSigPspolltimintervalCtrInt OBJECT-TYPE
    SYNTAX     Integer32 (0..2147483647)
    MAX-ACCESS read-write
    STATUS     current
    DESCRIPTION
            ""
    ::= { hmSetupWlanWirelessIdsSigPspolltiminterval 2 }

-- {SCALAR} 1.3.6.1.4.1.248.32.18.2.12.248.50.13.3
hmSetupWlanWirelessIdsSigPspolltimintervalIntervalDiff OBJECT-TYPE
    SYNTAX     Integer32 (0..2147483647)
    MAX-ACCESS read-write
    STATUS     current
    DESCRIPTION
            "-- empty --"
    ::= { hmSetupWlanWirelessIdsSigPspolltiminterval 3 }

-- {NODE} 1.3.6.1.4.1.248.32.18.2.12.248.50.14
hmSetupWlanWirelessIdsSigSmpsmultistream OBJECT IDENTIFIER ::= { hmSetupWlanWirelessIdsSig 14 }

-- {SCALAR} 1.3.6.1.4.1.248.32.18.2.12.248.50.14.1
hmSetupWlanWirelessIdsSigSmpsmultistreamCtrLim OBJECT-TYPE
    SYNTAX     Integer32 (0..2147483647)
    MAX-ACCESS read-write
    STATUS     current
    DESCRIPTION
            ""
    ::= { hmSetupWlanWirelessIdsSigSmpsmultistream 1 }

-- {SCALAR} 1.3.6.1.4.1.248.32.18.2.12.248.50.14.2
hmSetupWlanWirelessIdsSigSmpsmultistreamCtrInt OBJECT-TYPE
    SYNTAX     Integer32 (0..2147483647)
    MAX-ACCESS read-write
    STATUS     current
    DESCRIPTION
            ""
    ::= { hmSetupWlanWirelessIdsSigSmpsmultistream 2 }

-- {NODE} 1.3.6.1.4.1.248.32.18.2.12.248.50.15
hmSetupWlanWirelessIdsSigDeauthenticatereqflood OBJECT IDENTIFIER ::= { hmSetupWlanWirelessIdsSig 15 }

-- {SCALAR} 1.3.6.1.4.1.248.32.18.2.12.248.50.15.1
hmSetupWlanWirelessIdsSigDeauthenticatereqfloodCtrLim OBJECT-TYPE
    SYNTAX     Integer32 (0..2147483647)
    MAX-ACCESS read-write
    STATUS     current
    DESCRIPTION
            ""
    ::= { hmSetupWlanWirelessIdsSigDeauthenticatereqflood 1 }

-- {SCALAR} 1.3.6.1.4.1.248.32.18.2.12.248.50.15.2
hmSetupWlanWirelessIdsSigDeauthenticatereqfloodCtrInt OBJECT-TYPE
    SYNTAX     Integer32 (0..2147483647)
    MAX-ACCESS read-write
    STATUS     current
    DESCRIPTION
            ""
    ::= { hmSetupWlanWirelessIdsSigDeauthenticatereqflood 2 }

-- {NODE} 1.3.6.1.4.1.248.32.18.2.12.248.50.18
hmSetupWlanWirelessIdsSigSmpssinglestream OBJECT IDENTIFIER ::= { hmSetupWlanWirelessIdsSig 18 }

-- {SCALAR} 1.3.6.1.4.1.248.32.18.2.12.248.50.18.1
hmSetupWlanWirelessIdsSigSmpssinglestreamCtrLim OBJECT-TYPE
    SYNTAX     Integer32 (0..2147483647)
    MAX-ACCESS read-write
    STATUS     current
    DESCRIPTION
            ""
    ::= { hmSetupWlanWirelessIdsSigSmpssinglestream 1 }

-- {SCALAR} 1.3.6.1.4.1.248.32.18.2.12.248.50.18.2
hmSetupWlanWirelessIdsSigSmpssinglestreamCtrInt OBJECT-TYPE
    SYNTAX     Integer32 (0..2147483647)
    MAX-ACCESS read-write
    STATUS     current
    DESCRIPTION
            ""
    ::= { hmSetupWlanWirelessIdsSigSmpssinglestream 2 }

-- {TABLE} 1.3.6.1.4.1.248.32.18.2.12.248.101
hmSetupWlanWirelessIdsWhiteListTable OBJECT-TYPE
    SYNTAX     SEQUENCE OF HmSetupWlanWirelessIdsWhiteListEntry
    MAX-ACCESS not-accessible
    STATUS     current
    DESCRIPTION
            ""
    ::= { hmSetupWlanWirelessIds 101 }

-- {ROW} 1.3.6.1.4.1.248.32.18.2.12.248.101.1
hmSetupWlanWirelessIdsWhiteListEntry OBJECT-TYPE
    SYNTAX     HmSetupWlanWirelessIdsWhiteListEntry
    MAX-ACCESS not-accessible
    STATUS     current
    DESCRIPTION
            ""
    INDEX {
            hmSetupWlanWirelessIdsWhiteListEntryStationId
          }
    ::= { hmSetupWlanWirelessIdsWhiteListTable 1 }

HmSetupWlanWirelessIdsWhiteListEntry ::= SEQUENCE {
            hmSetupWlanWirelessIdsWhiteListEntryStationId Integer32,
            hmSetupWlanWirelessIdsWhiteListEntryStationMac MacAddress
    }

-- {COLUMN} 1.3.6.1.4.1.248.32.18.2.12.248.101.1.1
hmSetupWlanWirelessIdsWhiteListEntryStationId OBJECT-TYPE
    SYNTAX     Integer32 (0..255)
    MAX-ACCESS read-write
    STATUS     current
    DESCRIPTION
            "-- empty --"
    ::= { hmSetupWlanWirelessIdsWhiteListEntry 1 }

-- {COLUMN} 1.3.6.1.4.1.248.32.18.2.12.248.101.1.2
hmSetupWlanWirelessIdsWhiteListEntryStationMac OBJECT-TYPE
    SYNTAX     MacAddress
    MAX-ACCESS read-write
    STATUS     current
    DESCRIPTION
            "-- empty --"
    ::= { hmSetupWlanWirelessIdsWhiteListEntry 2 }

-- {NODE} 1.3.6.1.4.1.248.32.18.2.12.249
hmSetupWlanWlanLinkStatusLog OBJECT IDENTIFIER ::= { hmSetupWlan 249 }

-- {SCALAR} 1.3.6.1.4.1.248.32.18.2.12.249.10
hmSetupWlanWlanLinkStatusLogActive OBJECT-TYPE
    SYNTAX     INTEGER {
                  eNo (0),
                  eYes (1)
            }
    MAX-ACCESS read-write
    STATUS     current
    DESCRIPTION
            "-- empty --"
    ::= { hmSetupWlanWlanLinkStatusLog 10 }

-- {SCALAR} 1.3.6.1.4.1.248.32.18.2.12.249.11
hmSetupWlanWlanLinkStatusLogSnmpTrapsActive OBJECT-TYPE
    SYNTAX     INTEGER {
                  eNo (0),
                  eYes (1)
            }
    MAX-ACCESS read-write
    STATUS     current
    DESCRIPTION
            "-- empty --"
    ::= { hmSetupWlanWlanLinkStatusLog 11 }

-- {SCALAR} 1.3.6.1.4.1.248.32.18.2.12.249.12
hmSetupWlanWlanLinkStatusLogSyslogActive OBJECT-TYPE
    SYNTAX     INTEGER {
                  eNo (0),
                  eYes (1)
            }
    MAX-ACCESS read-write
    STATUS     current
    DESCRIPTION
            "-- empty --"
    ::= { hmSetupWlanWlanLinkStatusLog 12 }

-- {SCALAR} 1.3.6.1.4.1.248.32.18.2.12.249.13
hmSetupWlanWlanLinkStatusLogUsbLoggingActive OBJECT-TYPE
    SYNTAX     INTEGER {
                  eNo (0),
                  eYes (1)
            }
    MAX-ACCESS read-write
    STATUS     current
    DESCRIPTION
            "-- empty --"
    ::= { hmSetupWlanWlanLinkStatusLog 13 }

-- {NODE} 1.3.6.1.4.1.248.32.18.2.12.249.14
hmSetupWlanWlanLinkStatusLogSamplingInterval OBJECT IDENTIFIER ::= { hmSetupWlanWlanLinkStatusLog 14 }

-- {SCALAR} 1.3.6.1.4.1.248.32.18.2.12.249.14.1
hmSetupWlanWlanLinkStatusLogSamplingIntervalMonths OBJECT-TYPE
    SYNTAX     Integer32 (0..255)
    MAX-ACCESS read-write
    STATUS     current
    DESCRIPTION
            "-- empty --"
    ::= { hmSetupWlanWlanLinkStatusLogSamplingInterval 1 }

-- {SCALAR} 1.3.6.1.4.1.248.32.18.2.12.249.14.2
hmSetupWlanWlanLinkStatusLogSamplingIntervalDays OBJECT-TYPE
    SYNTAX     Integer32 (0..255)
    MAX-ACCESS read-write
    STATUS     current
    DESCRIPTION
            "-- empty --"
    ::= { hmSetupWlanWlanLinkStatusLogSamplingInterval 2 }

-- {SCALAR} 1.3.6.1.4.1.248.32.18.2.12.249.14.3
hmSetupWlanWlanLinkStatusLogSamplingIntervalHours OBJECT-TYPE
    SYNTAX     Integer32 (0..255)
    MAX-ACCESS read-write
    STATUS     current
    DESCRIPTION
            "-- empty --"
    ::= { hmSetupWlanWlanLinkStatusLogSamplingInterval 3 }

-- {NODE} 1.3.6.1.4.1.248.32.18.2.12.249.15
hmSetupWlanWlanLinkStatusLogLinkAgeOutTime OBJECT IDENTIFIER ::= { hmSetupWlanWlanLinkStatusLog 15 }

-- {SCALAR} 1.3.6.1.4.1.248.32.18.2.12.249.15.1
hmSetupWlanWlanLinkStatusLogLinkAgeOutTimeMonths OBJECT-TYPE
    SYNTAX     Integer32 (0..255)
    MAX-ACCESS read-write
    STATUS     current
    DESCRIPTION
            "-- empty --"
    ::= { hmSetupWlanWlanLinkStatusLogLinkAgeOutTime 1 }

-- {SCALAR} 1.3.6.1.4.1.248.32.18.2.12.249.15.2
hmSetupWlanWlanLinkStatusLogLinkAgeOutTimeDays OBJECT-TYPE
    SYNTAX     Integer32 (0..255)
    MAX-ACCESS read-write
    STATUS     current
    DESCRIPTION
            "-- empty --"
    ::= { hmSetupWlanWlanLinkStatusLogLinkAgeOutTime 2 }

-- {SCALAR} 1.3.6.1.4.1.248.32.18.2.12.249.15.3
hmSetupWlanWlanLinkStatusLogLinkAgeOutTimeHours OBJECT-TYPE
    SYNTAX     Integer32 (0..255)
    MAX-ACCESS read-write
    STATUS     current
    DESCRIPTION
            "-- empty --"
    ::= { hmSetupWlanWlanLinkStatusLogLinkAgeOutTime 3 }

-- {SCALAR} 1.3.6.1.4.1.248.32.18.2.12.250
hmSetupWlanRoamingStatisticsTimeout OBJECT-TYPE
    SYNTAX     Gauge32
    MAX-ACCESS read-write
    STATUS     current
    DESCRIPTION
            "-- empty --"
    ::= { hmSetupWlan 250 }

-- {NODE} 1.3.6.1.4.1.248.32.18.2.12.251
hmSetupWlanPrioritizedChannelScan OBJECT IDENTIFIER ::= { hmSetupWlan 251 }

-- {SCALAR} 1.3.6.1.4.1.248.32.18.2.12.251.1
hmSetupWlanPrioritizedChannelScanMinimumRoamCount OBJECT-TYPE
    SYNTAX     Gauge32
    MAX-ACCESS read-write
    STATUS     current
    DESCRIPTION
            "-- empty --"
    ::= { hmSetupWlanPrioritizedChannelScan 1 }

-- {SCALAR} 1.3.6.1.4.1.248.32.18.2.12.251.2
hmSetupWlanPrioritizedChannelScanNormalScanCyclePeriod OBJECT-TYPE
    SYNTAX     Integer32 (0..255)
    MAX-ACCESS read-write
    STATUS     current
    DESCRIPTION
            "-- empty --"
    ::= { hmSetupWlanPrioritizedChannelScan 2 }

-- {NODE} 1.3.6.1.4.1.248.32.18.2.14
hmSetupTime OBJECT IDENTIFIER ::= { hmSetup 14 }

-- {SCALAR} 1.3.6.1.4.1.248.32.18.2.14.1
hmSetupTimeFetchMethod OBJECT-TYPE
    SYNTAX     INTEGER {
                  eNone (0),
                  eNtp (2)
            }
    MAX-ACCESS read-write
    STATUS     current
    DESCRIPTION
            "-- empty --"
    ::= { hmSetupTime 1 }

-- {SCALAR} 1.3.6.1.4.1.248.32.18.2.14.2
hmSetupTimeCurrentTime OBJECT-TYPE
    SYNTAX     DisplayString
    MAX-ACCESS read-only
    STATUS     current
    DESCRIPTION
            "-- empty --"
    ::= { hmSetupTime 2 }

-- {SCALAR} 1.3.6.1.4.1.248.32.18.2.14.7
hmSetupTimeUtcInSeconds OBJECT-TYPE
    SYNTAX     Counter32
    MAX-ACCESS read-only
    STATUS     current
    DESCRIPTION
            "-- empty --"
    ::= { hmSetupTime 7 }

-- {SCALAR} 1.3.6.1.4.1.248.32.18.2.14.10
hmSetupTimeTimezone OBJECT-TYPE
    SYNTAX     INTEGER {
                  e0 (0),
                  eplus1 (1),
                  eplus2 (2),
                  eplus3 (3),
                  eplus4 (4),
                  eplus5 (5),
                  eplus6 (6),
                  eplus7 (7),
                  eplus8 (8),
                  eplus9 (9),
                  eplus10 (10),
                  eplus11 (11),
                  eplus12 (12),
                  eplus13 (13),
                  eplus14 (14),
                  eminus12 (244),
                  eminus11 (245),
                  eminus10 (246),
                  eminus9 (247),
                  eminus8 (248),
                  eminus7 (249),
                  eminus6 (250),
                  eminus5 (251),
                  eminus4 (252),
                  eminus3 (253),
                  eminus2 (254),
                  eminus1 (255)
            }
    MAX-ACCESS read-write
    STATUS     current
    DESCRIPTION
            "-- empty --"
    ::= { hmSetupTime 10 }

-- {SCALAR} 1.3.6.1.4.1.248.32.18.2.14.11
hmSetupTimeDaylightSavingTime OBJECT-TYPE
    SYNTAX     INTEGER {
                  eNo (0),
                  eYes (1),
                  eEuropeEu (2),
                  eRussia (3),
                  eUsa (4),
                  eUserDefined (255)
            }
    MAX-ACCESS read-write
    STATUS     current
    DESCRIPTION
            "-- empty --"
    ::= { hmSetupTime 11 }

-- {TABLE} 1.3.6.1.4.1.248.32.18.2.14.12
hmSetupTimeDstClockChangesTable OBJECT-TYPE
    SYNTAX     SEQUENCE OF HmSetupTimeDstClockChangesEntry
    MAX-ACCESS not-accessible
    STATUS     current
    DESCRIPTION
            "-- empty --"
    ::= { hmSetupTime 12 }

-- {ROW} 1.3.6.1.4.1.248.32.18.2.14.12.1
hmSetupTimeDstClockChangesEntry OBJECT-TYPE
    SYNTAX     HmSetupTimeDstClockChangesEntry
    MAX-ACCESS not-accessible
    STATUS     current
    DESCRIPTION
            ""
    INDEX {
            hmSetupTimeDstClockChangesEntryEvent
          }
    ::= { hmSetupTimeDstClockChangesTable 1 }

HmSetupTimeDstClockChangesEntry ::= SEQUENCE {
            hmSetupTimeDstClockChangesEntryEvent INTEGER,
            hmSetupTimeDstClockChangesEntryIndex INTEGER,
            hmSetupTimeDstClockChangesEntryDay INTEGER,
            hmSetupTimeDstClockChangesEntryMonth INTEGER,
            hmSetupTimeDstClockChangesEntryHour Integer32,
            hmSetupTimeDstClockChangesEntryMinute Integer32,
            hmSetupTimeDstClockChangesEntryTimeType INTEGER
    }

-- {COLUMN} 1.3.6.1.4.1.248.32.18.2.14.12.1.1
hmSetupTimeDstClockChangesEntryEvent OBJECT-TYPE
    SYNTAX     INTEGER {
                  eStart (1),
                  eEnd (2)
            }
    MAX-ACCESS read-only
    STATUS     current
    DESCRIPTION
            "-- empty --"
    ::= { hmSetupTimeDstClockChangesEntry 1 }

-- {COLUMN} 1.3.6.1.4.1.248.32.18.2.14.12.1.2
hmSetupTimeDstClockChangesEntryIndex OBJECT-TYPE
    SYNTAX     INTEGER {
                  eFirst (1),
                  eSecond (2),
                  eThird (3),
                  eFourth (4),
                  e4Last (252),
                  e3Last (253),
                  e2Last (254),
                  eLast (255)
            }
    MAX-ACCESS read-write
    STATUS     current
    DESCRIPTION
            "-- empty --"
    ::= { hmSetupTimeDstClockChangesEntry 2 }

-- {COLUMN} 1.3.6.1.4.1.248.32.18.2.14.12.1.3
hmSetupTimeDstClockChangesEntryDay OBJECT-TYPE
    SYNTAX     INTEGER {
                  eSunday (0),
                  eMonday (1),
                  eTuesday (2),
                  eWednesday (3),
                  eThursday (4),
                  eFriday (5),
                  eSaturday (6)
            }
    MAX-ACCESS read-write
    STATUS     current
    DESCRIPTION
            "-- empty --"
    ::= { hmSetupTimeDstClockChangesEntry 3 }

-- {COLUMN} 1.3.6.1.4.1.248.32.18.2.14.12.1.4
hmSetupTimeDstClockChangesEntryMonth OBJECT-TYPE
    SYNTAX     INTEGER {
                  eJanuary (1),
                  eFebruary (2),
                  eMarch (3),
                  eApril (4),
                  eMay (5),
                  eJune (6),
                  eJuly (7),
                  eAugust (8),
                  eSeptember (9),
                  eOctober (10),
                  eNovember (11),
                  eDecember (12)
            }
    MAX-ACCESS read-write
    STATUS     current
    DESCRIPTION
            "-- empty --"
    ::= { hmSetupTimeDstClockChangesEntry 4 }

-- {COLUMN} 1.3.6.1.4.1.248.32.18.2.14.12.1.5
hmSetupTimeDstClockChangesEntryHour OBJECT-TYPE
    SYNTAX     Integer32 (0..255)
    MAX-ACCESS read-write
    STATUS     current
    DESCRIPTION
            "-- empty --"
    ::= { hmSetupTimeDstClockChangesEntry 5 }

-- {COLUMN} 1.3.6.1.4.1.248.32.18.2.14.12.1.6
hmSetupTimeDstClockChangesEntryMinute OBJECT-TYPE
    SYNTAX     Integer32 (0..255)
    MAX-ACCESS read-write
    STATUS     current
    DESCRIPTION
            "-- empty --"
    ::= { hmSetupTimeDstClockChangesEntry 6 }

-- {COLUMN} 1.3.6.1.4.1.248.32.18.2.14.12.1.7
hmSetupTimeDstClockChangesEntryTimeType OBJECT-TYPE
    SYNTAX     INTEGER {
                  eLst (0),
                  eUtc (1)
            }
    MAX-ACCESS read-write
    STATUS     current
    DESCRIPTION
            "-- empty --"
    ::= { hmSetupTimeDstClockChangesEntry 7 }

-- {SCALAR} 1.3.6.1.4.1.248.32.18.2.14.13
hmSetupTimeGetTime OBJECT-TYPE
    SYNTAX     DisplayString
    MAX-ACCESS read-write
    STATUS     current
    DESCRIPTION
            "-- empty --"
    ::= { hmSetupTime 13 }

-- {TABLE} 1.3.6.1.4.1.248.32.18.2.14.15
hmSetupTimeHolidaysTable OBJECT-TYPE
    SYNTAX     SEQUENCE OF HmSetupTimeHolidaysEntry
    MAX-ACCESS not-accessible
    STATUS     current
    DESCRIPTION
            "-- empty --"
    ::= { hmSetupTime 15 }

-- {ROW} 1.3.6.1.4.1.248.32.18.2.14.15.1
hmSetupTimeHolidaysEntry OBJECT-TYPE
    SYNTAX     HmSetupTimeHolidaysEntry
    MAX-ACCESS not-accessible
    STATUS     current
    DESCRIPTION
            ""
    INDEX {
            hmSetupTimeHolidaysEntryIndex
          }
    ::= { hmSetupTimeHolidaysTable 1 }

HmSetupTimeHolidaysEntry ::= SEQUENCE {
            hmSetupTimeHolidaysEntryIndex Integer32,
            hmSetupTimeHolidaysEntryDate DisplayString
    }

-- {COLUMN} 1.3.6.1.4.1.248.32.18.2.14.15.1.1
hmSetupTimeHolidaysEntryIndex OBJECT-TYPE
    SYNTAX     Integer32 (0..65535)
    MAX-ACCESS read-write
    STATUS     current
    DESCRIPTION
            "-- empty --"
    ::= { hmSetupTimeHolidaysEntry 1 }

-- {COLUMN} 1.3.6.1.4.1.248.32.18.2.14.15.1.2
hmSetupTimeHolidaysEntryDate OBJECT-TYPE
    SYNTAX     DisplayString (SIZE(0..13))
    MAX-ACCESS read-write
    STATUS     current
    DESCRIPTION
            "-- empty --"
    ::= { hmSetupTimeHolidaysEntry 2 }

-- {TABLE} 1.3.6.1.4.1.248.32.18.2.14.16
hmSetupTimeTimeframeTable OBJECT-TYPE
    SYNTAX     SEQUENCE OF HmSetupTimeTimeframeEntry
    MAX-ACCESS not-accessible
    STATUS     current
    DESCRIPTION
            "-- empty --"
    ::= { hmSetupTime 16 }

-- {ROW} 1.3.6.1.4.1.248.32.18.2.14.16.1
hmSetupTimeTimeframeEntry OBJECT-TYPE
    SYNTAX     HmSetupTimeTimeframeEntry
    MAX-ACCESS not-accessible
    STATUS     current
    DESCRIPTION
            ""
    INDEX {
            hmSetupTimeTimeframeEntryName,
            hmSetupTimeTimeframeEntryStart,
            hmSetupTimeTimeframeEntryStop,
            hmSetupTimeTimeframeEntryWeekdays
          }
    ::= { hmSetupTimeTimeframeTable 1 }

HmSetupTimeTimeframeEntry ::= SEQUENCE {
            hmSetupTimeTimeframeEntryName DisplayString,
            hmSetupTimeTimeframeEntryStart DisplayString,
            hmSetupTimeTimeframeEntryStop DisplayString,
            hmSetupTimeTimeframeEntryWeekdays BITS
    }

-- {COLUMN} 1.3.6.1.4.1.248.32.18.2.14.16.1.1
hmSetupTimeTimeframeEntryName OBJECT-TYPE
    SYNTAX     DisplayString (SIZE(0..31))
    MAX-ACCESS read-write
    STATUS     current
    DESCRIPTION
            "-- empty --"
    ::= { hmSetupTimeTimeframeEntry 1 }

-- {COLUMN} 1.3.6.1.4.1.248.32.18.2.14.16.1.2
hmSetupTimeTimeframeEntryStart OBJECT-TYPE
    SYNTAX     DisplayString (SIZE(0..5))
    MAX-ACCESS read-write
    STATUS     current
    DESCRIPTION
            "-- empty --"
    ::= { hmSetupTimeTimeframeEntry 2 }

-- {COLUMN} 1.3.6.1.4.1.248.32.18.2.14.16.1.3
hmSetupTimeTimeframeEntryStop OBJECT-TYPE
    SYNTAX     DisplayString (SIZE(0..5))
    MAX-ACCESS read-write
    STATUS     current
    DESCRIPTION
            "-- empty --"
    ::= { hmSetupTimeTimeframeEntry 3 }

-- {COLUMN} 1.3.6.1.4.1.248.32.18.2.14.16.1.4
hmSetupTimeTimeframeEntryWeekdays OBJECT-TYPE
    SYNTAX     BITS {
                  eHoliday (0),
                  eSaturday (1),
                  eFriday (2),
                  eThursday (3),
                  eWednesday (4),
                  eTuesday (5),
                  eMonday (6),
                  eSunday (7)
            }
    MAX-ACCESS read-write
    STATUS     current
    DESCRIPTION
            "-- empty --"
    ::= { hmSetupTimeTimeframeEntry 4 }

-- {NODE} 1.3.6.1.4.1.248.32.18.2.15
hmSetupLcr OBJECT IDENTIFIER ::= { hmSetup 15 }

-- {SCALAR} 1.3.6.1.4.1.248.32.18.2.15.1
hmSetupLcrRouterUsage OBJECT-TYPE
    SYNTAX     INTEGER {
                  eNo (0),
                  eYes (1)
            }
    MAX-ACCESS read-write
    STATUS     current
    DESCRIPTION
            "-- empty --"
    ::= { hmSetupLcr 1 }

-- {TABLE} 1.3.6.1.4.1.248.32.18.2.15.4
hmSetupLcrTimeListTable OBJECT-TYPE
    SYNTAX     SEQUENCE OF HmSetupLcrTimeListEntry
    MAX-ACCESS not-accessible
    STATUS     current
    DESCRIPTION
            "-- empty --"
    ::= { hmSetupLcr 4 }

-- {ROW} 1.3.6.1.4.1.248.32.18.2.15.4.1
hmSetupLcrTimeListEntry OBJECT-TYPE
    SYNTAX     HmSetupLcrTimeListEntry
    MAX-ACCESS not-accessible
    STATUS     current
    DESCRIPTION
            ""
    INDEX {
            hmSetupLcrTimeListEntryIndex
          }
    ::= { hmSetupLcrTimeListTable 1 }

HmSetupLcrTimeListEntry ::= SEQUENCE {
            hmSetupLcrTimeListEntryIndex Integer32,
            hmSetupLcrTimeListEntryPrefix DisplayString,
            hmSetupLcrTimeListEntryDays BITS,
            hmSetupLcrTimeListEntryStart DisplayString,
            hmSetupLcrTimeListEntryStop DisplayString,
            hmSetupLcrTimeListEntryNumberList DisplayString,
            hmSetupLcrTimeListEntryFallback INTEGER
    }

-- {COLUMN} 1.3.6.1.4.1.248.32.18.2.15.4.1.1
hmSetupLcrTimeListEntryIndex OBJECT-TYPE
    SYNTAX     Integer32 (0..65535)
    MAX-ACCESS read-write
    STATUS     current
    DESCRIPTION
            "-- empty --"
    ::= { hmSetupLcrTimeListEntry 1 }

-- {COLUMN} 1.3.6.1.4.1.248.32.18.2.15.4.1.2
hmSetupLcrTimeListEntryPrefix OBJECT-TYPE
    SYNTAX     DisplayString (SIZE(0..10))
    MAX-ACCESS read-write
    STATUS     current
    DESCRIPTION
            "-- empty --"
    ::= { hmSetupLcrTimeListEntry 2 }

-- {COLUMN} 1.3.6.1.4.1.248.32.18.2.15.4.1.3
hmSetupLcrTimeListEntryDays OBJECT-TYPE
    SYNTAX     BITS {
                  eHoliday (0),
                  eSunday (1),
                  eSaturday (2),
                  eFriday (3),
                  eThursday (4),
                  eWednesday (5),
                  eTuesday (6),
                  eMonday (7)
            }
    MAX-ACCESS read-write
    STATUS     current
    DESCRIPTION
            "-- empty --"
    ::= { hmSetupLcrTimeListEntry 3 }

-- {COLUMN} 1.3.6.1.4.1.248.32.18.2.15.4.1.4
hmSetupLcrTimeListEntryStart OBJECT-TYPE
    SYNTAX     DisplayString (SIZE(0..5))
    MAX-ACCESS read-write
    STATUS     current
    DESCRIPTION
            "-- empty --"
    ::= { hmSetupLcrTimeListEntry 4 }

-- {COLUMN} 1.3.6.1.4.1.248.32.18.2.15.4.1.5
hmSetupLcrTimeListEntryStop OBJECT-TYPE
    SYNTAX     DisplayString (SIZE(0..5))
    MAX-ACCESS read-write
    STATUS     current
    DESCRIPTION
            "-- empty --"
    ::= { hmSetupLcrTimeListEntry 5 }

-- {COLUMN} 1.3.6.1.4.1.248.32.18.2.15.4.1.6
hmSetupLcrTimeListEntryNumberList OBJECT-TYPE
    SYNTAX     DisplayString (SIZE(0..29))
    MAX-ACCESS read-write
    STATUS     current
    DESCRIPTION
            "-- empty --"
    ::= { hmSetupLcrTimeListEntry 6 }

-- {COLUMN} 1.3.6.1.4.1.248.32.18.2.15.4.1.7
hmSetupLcrTimeListEntryFallback OBJECT-TYPE
    SYNTAX     INTEGER {
                  eNo (0),
                  eYes (1)
            }
    MAX-ACCESS read-write
    STATUS     current
    DESCRIPTION
            "-- empty --"
    ::= { hmSetupLcrTimeListEntry 7 }

-- {NODE} 1.3.6.1.4.1.248.32.18.2.16
hmSetupNetbios OBJECT IDENTIFIER ::= { hmSetup 16 }

-- {SCALAR} 1.3.6.1.4.1.248.32.18.2.16.1
hmSetupNetbiosOperating OBJECT-TYPE
    SYNTAX     INTEGER {
                  eNo (0),
                  eYes (1)
            }
    MAX-ACCESS read-write
    STATUS     current
    DESCRIPTION
            "-- empty --"
    ::= { hmSetupNetbios 1 }

-- {SCALAR} 1.3.6.1.4.1.248.32.18.2.16.2
hmSetupNetbiosScopeId OBJECT-TYPE
    SYNTAX     DisplayString (SIZE(0..64))
    MAX-ACCESS read-write
    STATUS     current
    DESCRIPTION
            "-- empty --"
    ::= { hmSetupNetbios 2 }

-- {TABLE} 1.3.6.1.4.1.248.32.18.2.16.4
hmSetupNetbiosPeersTable OBJECT-TYPE
    SYNTAX     SEQUENCE OF HmSetupNetbiosPeersEntry
    MAX-ACCESS not-accessible
    STATUS     current
    DESCRIPTION
            "-- empty --"
    ::= { hmSetupNetbios 4 }

-- {ROW} 1.3.6.1.4.1.248.32.18.2.16.4.1
hmSetupNetbiosPeersEntry OBJECT-TYPE
    SYNTAX     HmSetupNetbiosPeersEntry
    MAX-ACCESS not-accessible
    STATUS     current
    DESCRIPTION
            ""
    INDEX {
            hmSetupNetbiosPeersEntryName
          }
    ::= { hmSetupNetbiosPeersTable 1 }

HmSetupNetbiosPeersEntry ::= SEQUENCE {
            hmSetupNetbiosPeersEntryName DisplayString,
            hmSetupNetbiosPeersEntryType INTEGER
    }

-- {COLUMN} 1.3.6.1.4.1.248.32.18.2.16.4.1.1
hmSetupNetbiosPeersEntryName OBJECT-TYPE
    SYNTAX     DisplayString (SIZE(0..16))
    MAX-ACCESS read-write
    STATUS     current
    DESCRIPTION
            "-- empty --"
    ::= { hmSetupNetbiosPeersEntry 1 }

-- {COLUMN} 1.3.6.1.4.1.248.32.18.2.16.4.1.3
hmSetupNetbiosPeersEntryType OBJECT-TYPE
    SYNTAX     INTEGER {
                  eRouter (0),
                  eWorkstation (1)
            }
    MAX-ACCESS read-write
    STATUS     current
    DESCRIPTION
            "-- empty --"
    ::= { hmSetupNetbiosPeersEntry 3 }

-- {TABLE} 1.3.6.1.4.1.248.32.18.2.16.5
hmSetupNetbiosGroupListTable OBJECT-TYPE
    SYNTAX     SEQUENCE OF HmSetupNetbiosGroupListEntry
    MAX-ACCESS not-accessible
    STATUS     current
    DESCRIPTION
            "-- empty --"
    ::= { hmSetupNetbios 5 }

-- {ROW} 1.3.6.1.4.1.248.32.18.2.16.5.1
hmSetupNetbiosGroupListEntry OBJECT-TYPE
    SYNTAX     HmSetupNetbiosGroupListEntry
    MAX-ACCESS not-accessible
    STATUS     current
    DESCRIPTION
            ""
    INDEX {
            hmSetupNetbiosGroupListEntryGroupDomain,
            hmSetupNetbiosGroupListEntryType,
            hmSetupNetbiosGroupListEntryIpAddress,
            hmSetupNetbiosGroupListEntryRtgTag
          }
    ::= { hmSetupNetbiosGroupListTable 1 }

HmSetupNetbiosGroupListEntry ::= SEQUENCE {
            hmSetupNetbiosGroupListEntryGroupDomain DisplayString,
            hmSetupNetbiosGroupListEntryType DisplayString,
            hmSetupNetbiosGroupListEntryIpAddress IpAddress,
            hmSetupNetbiosGroupListEntryPeer DisplayString,
            hmSetupNetbiosGroupListEntryTimeout Integer32,
            hmSetupNetbiosGroupListEntryFlags DisplayString,
            hmSetupNetbiosGroupListEntryNetworkName DisplayString,
            hmSetupNetbiosGroupListEntryRtgTag Integer32
    }

-- {COLUMN} 1.3.6.1.4.1.248.32.18.2.16.5.1.1
hmSetupNetbiosGroupListEntryGroupDomain OBJECT-TYPE
    SYNTAX     DisplayString (SIZE(0..15))
    MAX-ACCESS read-only
    STATUS     current
    DESCRIPTION
            "-- empty --"
    ::= { hmSetupNetbiosGroupListEntry 1 }

-- {COLUMN} 1.3.6.1.4.1.248.32.18.2.16.5.1.2
hmSetupNetbiosGroupListEntryType OBJECT-TYPE
    SYNTAX     DisplayString (SIZE(0..1))
    MAX-ACCESS read-only
    STATUS     current
    DESCRIPTION
            "-- empty --"
    ::= { hmSetupNetbiosGroupListEntry 2 }

-- {COLUMN} 1.3.6.1.4.1.248.32.18.2.16.5.1.3
hmSetupNetbiosGroupListEntryIpAddress OBJECT-TYPE
    SYNTAX     IpAddress
    MAX-ACCESS read-only
    STATUS     current
    DESCRIPTION
            "-- empty --"
    ::= { hmSetupNetbiosGroupListEntry 3 }

-- {COLUMN} 1.3.6.1.4.1.248.32.18.2.16.5.1.4
hmSetupNetbiosGroupListEntryPeer OBJECT-TYPE
    SYNTAX     DisplayString (SIZE(0..16))
    MAX-ACCESS read-only
    STATUS     current
    DESCRIPTION
            "-- empty --"
    ::= { hmSetupNetbiosGroupListEntry 4 }

-- {COLUMN} 1.3.6.1.4.1.248.32.18.2.16.5.1.5
hmSetupNetbiosGroupListEntryTimeout OBJECT-TYPE
    SYNTAX     Integer32 (0..2147483647)
    MAX-ACCESS read-only
    STATUS     current
    DESCRIPTION
            "-- empty --"
    ::= { hmSetupNetbiosGroupListEntry 5 }

-- {COLUMN} 1.3.6.1.4.1.248.32.18.2.16.5.1.6
hmSetupNetbiosGroupListEntryFlags OBJECT-TYPE
    SYNTAX     DisplayString (SIZE(0..2))
    MAX-ACCESS read-only
    STATUS     current
    DESCRIPTION
            "-- empty --"
    ::= { hmSetupNetbiosGroupListEntry 6 }

-- {COLUMN} 1.3.6.1.4.1.248.32.18.2.16.5.1.7
hmSetupNetbiosGroupListEntryNetworkName OBJECT-TYPE
    SYNTAX     DisplayString (SIZE(0..16))
    MAX-ACCESS read-only
    STATUS     current
    DESCRIPTION
            "-- empty --"
    ::= { hmSetupNetbiosGroupListEntry 7 }

-- {COLUMN} 1.3.6.1.4.1.248.32.18.2.16.5.1.8
hmSetupNetbiosGroupListEntryRtgTag OBJECT-TYPE
    SYNTAX     Integer32 (0..65535)
    MAX-ACCESS read-only
    STATUS     current
    DESCRIPTION
            "-- empty --"
    ::= { hmSetupNetbiosGroupListEntry 8 }

-- {TABLE} 1.3.6.1.4.1.248.32.18.2.16.6
hmSetupNetbiosHostListTable OBJECT-TYPE
    SYNTAX     SEQUENCE OF HmSetupNetbiosHostListEntry
    MAX-ACCESS not-accessible
    STATUS     current
    DESCRIPTION
            "-- empty --"
    ::= { hmSetupNetbios 6 }

-- {ROW} 1.3.6.1.4.1.248.32.18.2.16.6.1
hmSetupNetbiosHostListEntry OBJECT-TYPE
    SYNTAX     HmSetupNetbiosHostListEntry
    MAX-ACCESS not-accessible
    STATUS     current
    DESCRIPTION
            ""
    INDEX {
            hmSetupNetbiosHostListEntryName,
            hmSetupNetbiosHostListEntryType,
            hmSetupNetbiosHostListEntryIpAddress,
            hmSetupNetbiosHostListEntryRtgTag
          }
    ::= { hmSetupNetbiosHostListTable 1 }

HmSetupNetbiosHostListEntry ::= SEQUENCE {
            hmSetupNetbiosHostListEntryName DisplayString,
            hmSetupNetbiosHostListEntryType DisplayString,
            hmSetupNetbiosHostListEntryIpAddress IpAddress,
            hmSetupNetbiosHostListEntryPeer DisplayString,
            hmSetupNetbiosHostListEntryTimeout Integer32,
            hmSetupNetbiosHostListEntryFlags DisplayString,
            hmSetupNetbiosHostListEntryNetworkName DisplayString,
            hmSetupNetbiosHostListEntryRtgTag Integer32
    }

-- {COLUMN} 1.3.6.1.4.1.248.32.18.2.16.6.1.1
hmSetupNetbiosHostListEntryName OBJECT-TYPE
    SYNTAX     DisplayString (SIZE(0..15))
    MAX-ACCESS read-only
    STATUS     current
    DESCRIPTION
            "-- empty --"
    ::= { hmSetupNetbiosHostListEntry 1 }

-- {COLUMN} 1.3.6.1.4.1.248.32.18.2.16.6.1.2
hmSetupNetbiosHostListEntryType OBJECT-TYPE
    SYNTAX     DisplayString (SIZE(0..1))
    MAX-ACCESS read-only
    STATUS     current
    DESCRIPTION
            "-- empty --"
    ::= { hmSetupNetbiosHostListEntry 2 }

-- {COLUMN} 1.3.6.1.4.1.248.32.18.2.16.6.1.3
hmSetupNetbiosHostListEntryIpAddress OBJECT-TYPE
    SYNTAX     IpAddress
    MAX-ACCESS read-only
    STATUS     current
    DESCRIPTION
            "-- empty --"
    ::= { hmSetupNetbiosHostListEntry 3 }

-- {COLUMN} 1.3.6.1.4.1.248.32.18.2.16.6.1.4
hmSetupNetbiosHostListEntryPeer OBJECT-TYPE
    SYNTAX     DisplayString (SIZE(0..16))
    MAX-ACCESS read-only
    STATUS     current
    DESCRIPTION
            "-- empty --"
    ::= { hmSetupNetbiosHostListEntry 4 }

-- {COLUMN} 1.3.6.1.4.1.248.32.18.2.16.6.1.5
hmSetupNetbiosHostListEntryTimeout OBJECT-TYPE
    SYNTAX     Integer32 (0..2147483647)
    MAX-ACCESS read-only
    STATUS     current
    DESCRIPTION
            "-- empty --"
    ::= { hmSetupNetbiosHostListEntry 5 }

-- {COLUMN} 1.3.6.1.4.1.248.32.18.2.16.6.1.6
hmSetupNetbiosHostListEntryFlags OBJECT-TYPE
    SYNTAX     DisplayString (SIZE(0..2))
    MAX-ACCESS read-only
    STATUS     current
    DESCRIPTION
            "-- empty --"
    ::= { hmSetupNetbiosHostListEntry 6 }

-- {COLUMN} 1.3.6.1.4.1.248.32.18.2.16.6.1.7
hmSetupNetbiosHostListEntryNetworkName OBJECT-TYPE
    SYNTAX     DisplayString (SIZE(0..16))
    MAX-ACCESS read-only
    STATUS     current
    DESCRIPTION
            "-- empty --"
    ::= { hmSetupNetbiosHostListEntry 7 }

-- {COLUMN} 1.3.6.1.4.1.248.32.18.2.16.6.1.8
hmSetupNetbiosHostListEntryRtgTag OBJECT-TYPE
    SYNTAX     Integer32 (0..65535)
    MAX-ACCESS read-only
    STATUS     current
    DESCRIPTION
            "-- empty --"
    ::= { hmSetupNetbiosHostListEntry 8 }

-- {TABLE} 1.3.6.1.4.1.248.32.18.2.16.7
hmSetupNetbiosServerListTable OBJECT-TYPE
    SYNTAX     SEQUENCE OF HmSetupNetbiosServerListEntry
    MAX-ACCESS not-accessible
    STATUS     current
    DESCRIPTION
            "-- empty --"
    ::= { hmSetupNetbios 7 }

-- {ROW} 1.3.6.1.4.1.248.32.18.2.16.7.1
hmSetupNetbiosServerListEntry OBJECT-TYPE
    SYNTAX     HmSetupNetbiosServerListEntry
    MAX-ACCESS not-accessible
    STATUS     current
    DESCRIPTION
            ""
    INDEX {
            hmSetupNetbiosServerListEntryHost,
            hmSetupNetbiosServerListEntryGroupDomain,
            hmSetupNetbiosServerListEntryIpAddress,
            hmSetupNetbiosServerListEntryRtgTag
          }
    ::= { hmSetupNetbiosServerListTable 1 }

HmSetupNetbiosServerListEntry ::= SEQUENCE {
            hmSetupNetbiosServerListEntryHost DisplayString,
            hmSetupNetbiosServerListEntryGroupDomain DisplayString,
            hmSetupNetbiosServerListEntryIpAddress DisplayString,
            hmSetupNetbiosServerListEntryOsVer DisplayString,
            hmSetupNetbiosServerListEntrySmbVer DisplayString,
            hmSetupNetbiosServerListEntryServerTyp DisplayString,
            hmSetupNetbiosServerListEntryPeer DisplayString,
            hmSetupNetbiosServerListEntryTimeout Integer32,
            hmSetupNetbiosServerListEntryFlags DisplayString,
            hmSetupNetbiosServerListEntryNetworkName DisplayString,
            hmSetupNetbiosServerListEntryRtgTag Integer32
    }

-- {COLUMN} 1.3.6.1.4.1.248.32.18.2.16.7.1.1
hmSetupNetbiosServerListEntryHost OBJECT-TYPE
    SYNTAX     DisplayString (SIZE(0..15))
    MAX-ACCESS read-only
    STATUS     current
    DESCRIPTION
            "-- empty --"
    ::= { hmSetupNetbiosServerListEntry 1 }

-- {COLUMN} 1.3.6.1.4.1.248.32.18.2.16.7.1.2
hmSetupNetbiosServerListEntryGroupDomain OBJECT-TYPE
    SYNTAX     DisplayString (SIZE(0..16))
    MAX-ACCESS read-only
    STATUS     current
    DESCRIPTION
            "-- empty --"
    ::= { hmSetupNetbiosServerListEntry 2 }

-- {COLUMN} 1.3.6.1.4.1.248.32.18.2.16.7.1.4
hmSetupNetbiosServerListEntryIpAddress OBJECT-TYPE
    SYNTAX     DisplayString (SIZE(0..15))
    MAX-ACCESS read-only
    STATUS     current
    DESCRIPTION
            "-- empty --"
    ::= { hmSetupNetbiosServerListEntry 4 }

-- {COLUMN} 1.3.6.1.4.1.248.32.18.2.16.7.1.5
hmSetupNetbiosServerListEntryOsVer OBJECT-TYPE
    SYNTAX     DisplayString (SIZE(0..2))
    MAX-ACCESS read-only
    STATUS     current
    DESCRIPTION
            "-- empty --"
    ::= { hmSetupNetbiosServerListEntry 5 }

-- {COLUMN} 1.3.6.1.4.1.248.32.18.2.16.7.1.6
hmSetupNetbiosServerListEntrySmbVer OBJECT-TYPE
    SYNTAX     DisplayString (SIZE(0..2))
    MAX-ACCESS read-only
    STATUS     current
    DESCRIPTION
            "-- empty --"
    ::= { hmSetupNetbiosServerListEntry 6 }

-- {COLUMN} 1.3.6.1.4.1.248.32.18.2.16.7.1.7
hmSetupNetbiosServerListEntryServerTyp OBJECT-TYPE
    SYNTAX     DisplayString (SIZE(0..4))
    MAX-ACCESS read-only
    STATUS     current
    DESCRIPTION
            "-- empty --"
    ::= { hmSetupNetbiosServerListEntry 7 }

-- {COLUMN} 1.3.6.1.4.1.248.32.18.2.16.7.1.8
hmSetupNetbiosServerListEntryPeer OBJECT-TYPE
    SYNTAX     DisplayString (SIZE(0..16))
    MAX-ACCESS read-only
    STATUS     current
    DESCRIPTION
            "-- empty --"
    ::= { hmSetupNetbiosServerListEntry 8 }

-- {COLUMN} 1.3.6.1.4.1.248.32.18.2.16.7.1.9
hmSetupNetbiosServerListEntryTimeout OBJECT-TYPE
    SYNTAX     Integer32 (0..2147483647)
    MAX-ACCESS read-only
    STATUS     current
    DESCRIPTION
            "-- empty --"
    ::= { hmSetupNetbiosServerListEntry 9 }

-- {COLUMN} 1.3.6.1.4.1.248.32.18.2.16.7.1.10
hmSetupNetbiosServerListEntryFlags OBJECT-TYPE
    SYNTAX     DisplayString (SIZE(0..2))
    MAX-ACCESS read-only
    STATUS     current
    DESCRIPTION
            "-- empty --"
    ::= { hmSetupNetbiosServerListEntry 10 }

-- {COLUMN} 1.3.6.1.4.1.248.32.18.2.16.7.1.11
hmSetupNetbiosServerListEntryNetworkName OBJECT-TYPE
    SYNTAX     DisplayString (SIZE(0..16))
    MAX-ACCESS read-only
    STATUS     current
    DESCRIPTION
            "-- empty --"
    ::= { hmSetupNetbiosServerListEntry 11 }

-- {COLUMN} 1.3.6.1.4.1.248.32.18.2.16.7.1.12
hmSetupNetbiosServerListEntryRtgTag OBJECT-TYPE
    SYNTAX     Integer32 (0..65535)
    MAX-ACCESS read-only
    STATUS     current
    DESCRIPTION
            "-- empty --"
    ::= { hmSetupNetbiosServerListEntry 12 }

-- {SCALAR} 1.3.6.1.4.1.248.32.18.2.16.8
hmSetupNetbiosWatchdogs OBJECT-TYPE
    SYNTAX     INTEGER {
                  eRoute (0),
                  eSpoof (1)
            }
    MAX-ACCESS read-write
    STATUS     current
    DESCRIPTION
            "-- empty --"
    ::= { hmSetupNetbios 8 }

-- {SCALAR} 1.3.6.1.4.1.248.32.18.2.16.9
hmSetupNetbiosUpdate OBJECT-TYPE
    SYNTAX     INTEGER {
                  ePback (0),
                  eTrig (1),
                  eTime (2)
            }
    MAX-ACCESS read-write
    STATUS     current
    DESCRIPTION
            "-- empty --"
    ::= { hmSetupNetbios 9 }

-- {SCALAR} 1.3.6.1.4.1.248.32.18.2.16.10
hmSetupNetbiosWanUpdateMinutes OBJECT-TYPE
    SYNTAX     Integer32 (0..65535)
    MAX-ACCESS read-write
    STATUS     current
    DESCRIPTION
            "-- empty --"
    ::= { hmSetupNetbios 10 }

-- {SCALAR} 1.3.6.1.4.1.248.32.18.2.16.11
hmSetupNetbiosLeasetime OBJECT-TYPE
    SYNTAX     Integer32 (0..65535)
    MAX-ACCESS read-write
    STATUS     current
    DESCRIPTION
            "-- empty --"
    ::= { hmSetupNetbios 11 }

-- {TABLE} 1.3.6.1.4.1.248.32.18.2.16.12
hmSetupNetbiosNetworksTable OBJECT-TYPE
    SYNTAX     SEQUENCE OF HmSetupNetbiosNetworksEntry
    MAX-ACCESS not-accessible
    STATUS     current
    DESCRIPTION
            "-- empty --"
    ::= { hmSetupNetbios 12 }

-- {ROW} 1.3.6.1.4.1.248.32.18.2.16.12.1
hmSetupNetbiosNetworksEntry OBJECT-TYPE
    SYNTAX     HmSetupNetbiosNetworksEntry
    MAX-ACCESS not-accessible
    STATUS     current
    DESCRIPTION
            ""
    INDEX {
            hmSetupNetbiosNetworksEntryNetworkName
          }
    ::= { hmSetupNetbiosNetworksTable 1 }

HmSetupNetbiosNetworksEntry ::= SEQUENCE {
            hmSetupNetbiosNetworksEntryNetworkName DisplayString,
            hmSetupNetbiosNetworksEntryOperating INTEGER,
            hmSetupNetbiosNetworksEntryNtDomain DisplayString
    }

-- {COLUMN} 1.3.6.1.4.1.248.32.18.2.16.12.1.1
hmSetupNetbiosNetworksEntryNetworkName OBJECT-TYPE
    SYNTAX     DisplayString (SIZE(0..16))
    MAX-ACCESS read-write
    STATUS     current
    DESCRIPTION
            "-- empty --"
    ::= { hmSetupNetbiosNetworksEntry 1 }

-- {COLUMN} 1.3.6.1.4.1.248.32.18.2.16.12.1.2
hmSetupNetbiosNetworksEntryOperating OBJECT-TYPE
    SYNTAX     INTEGER {
                  eNo (0),
                  eYes (1)
            }
    MAX-ACCESS read-write
    STATUS     current
    DESCRIPTION
            "-- empty --"
    ::= { hmSetupNetbiosNetworksEntry 2 }

-- {COLUMN} 1.3.6.1.4.1.248.32.18.2.16.12.1.3
hmSetupNetbiosNetworksEntryNtDomain OBJECT-TYPE
    SYNTAX     DisplayString (SIZE(0..15))
    MAX-ACCESS read-write
    STATUS     current
    DESCRIPTION
            "-- empty --"
    ::= { hmSetupNetbiosNetworksEntry 3 }

-- {TABLE} 1.3.6.1.4.1.248.32.18.2.16.13
hmSetupNetbiosBrowserListTable OBJECT-TYPE
    SYNTAX     SEQUENCE OF HmSetupNetbiosBrowserListEntry
    MAX-ACCESS not-accessible
    STATUS     current
    DESCRIPTION
            "-- empty --"
    ::= { hmSetupNetbios 13 }

-- {ROW} 1.3.6.1.4.1.248.32.18.2.16.13.1
hmSetupNetbiosBrowserListEntry OBJECT-TYPE
    SYNTAX     HmSetupNetbiosBrowserListEntry
    MAX-ACCESS not-accessible
    STATUS     current
    DESCRIPTION
            ""
    INDEX {
            hmSetupNetbiosBrowserListEntryBrowser,
            hmSetupNetbiosBrowserListEntryGroupDomain,
            hmSetupNetbiosBrowserListEntryIpAddress,
            hmSetupNetbiosBrowserListEntryRtgTag
          }
    ::= { hmSetupNetbiosBrowserListTable 1 }

HmSetupNetbiosBrowserListEntry ::= SEQUENCE {
            hmSetupNetbiosBrowserListEntryBrowser DisplayString,
            hmSetupNetbiosBrowserListEntryGroupDomain DisplayString,
            hmSetupNetbiosBrowserListEntryIpAddress DisplayString,
            hmSetupNetbiosBrowserListEntryOsVer DisplayString,
            hmSetupNetbiosBrowserListEntryServerTyp DisplayString,
            hmSetupNetbiosBrowserListEntryPeer DisplayString,
            hmSetupNetbiosBrowserListEntryTimeout Integer32,
            hmSetupNetbiosBrowserListEntryFlags DisplayString,
            hmSetupNetbiosBrowserListEntryNetworkName DisplayString,
            hmSetupNetbiosBrowserListEntryRtgTag Integer32
    }

-- {COLUMN} 1.3.6.1.4.1.248.32.18.2.16.13.1.1
hmSetupNetbiosBrowserListEntryBrowser OBJECT-TYPE
    SYNTAX     DisplayString (SIZE(0..15))
    MAX-ACCESS read-only
    STATUS     current
    DESCRIPTION
            "-- empty --"
    ::= { hmSetupNetbiosBrowserListEntry 1 }

-- {COLUMN} 1.3.6.1.4.1.248.32.18.2.16.13.1.2
hmSetupNetbiosBrowserListEntryGroupDomain OBJECT-TYPE
    SYNTAX     DisplayString (SIZE(0..16))
    MAX-ACCESS read-only
    STATUS     current
    DESCRIPTION
            "-- empty --"
    ::= { hmSetupNetbiosBrowserListEntry 2 }

-- {COLUMN} 1.3.6.1.4.1.248.32.18.2.16.13.1.4
hmSetupNetbiosBrowserListEntryIpAddress OBJECT-TYPE
    SYNTAX     DisplayString (SIZE(0..15))
    MAX-ACCESS read-only
    STATUS     current
    DESCRIPTION
            "-- empty --"
    ::= { hmSetupNetbiosBrowserListEntry 4 }

-- {COLUMN} 1.3.6.1.4.1.248.32.18.2.16.13.1.5
hmSetupNetbiosBrowserListEntryOsVer OBJECT-TYPE
    SYNTAX     DisplayString (SIZE(0..2))
    MAX-ACCESS read-only
    STATUS     current
    DESCRIPTION
            "-- empty --"
    ::= { hmSetupNetbiosBrowserListEntry 5 }

-- {COLUMN} 1.3.6.1.4.1.248.32.18.2.16.13.1.7
hmSetupNetbiosBrowserListEntryServerTyp OBJECT-TYPE
    SYNTAX     DisplayString (SIZE(0..4))
    MAX-ACCESS read-only
    STATUS     current
    DESCRIPTION
            "-- empty --"
    ::= { hmSetupNetbiosBrowserListEntry 7 }

-- {COLUMN} 1.3.6.1.4.1.248.32.18.2.16.13.1.8
hmSetupNetbiosBrowserListEntryPeer OBJECT-TYPE
    SYNTAX     DisplayString (SIZE(0..16))
    MAX-ACCESS read-only
    STATUS     current
    DESCRIPTION
            "-- empty --"
    ::= { hmSetupNetbiosBrowserListEntry 8 }

-- {COLUMN} 1.3.6.1.4.1.248.32.18.2.16.13.1.9
hmSetupNetbiosBrowserListEntryTimeout OBJECT-TYPE
    SYNTAX     Integer32 (0..2147483647)
    MAX-ACCESS read-only
    STATUS     current
    DESCRIPTION
            "-- empty --"
    ::= { hmSetupNetbiosBrowserListEntry 9 }

-- {COLUMN} 1.3.6.1.4.1.248.32.18.2.16.13.1.10
hmSetupNetbiosBrowserListEntryFlags OBJECT-TYPE
    SYNTAX     DisplayString (SIZE(0..2))
    MAX-ACCESS read-only
    STATUS     current
    DESCRIPTION
            "-- empty --"
    ::= { hmSetupNetbiosBrowserListEntry 10 }

-- {COLUMN} 1.3.6.1.4.1.248.32.18.2.16.13.1.11
hmSetupNetbiosBrowserListEntryNetworkName OBJECT-TYPE
    SYNTAX     DisplayString (SIZE(0..16))
    MAX-ACCESS read-only
    STATUS     current
    DESCRIPTION
            "-- empty --"
    ::= { hmSetupNetbiosBrowserListEntry 11 }

-- {COLUMN} 1.3.6.1.4.1.248.32.18.2.16.13.1.12
hmSetupNetbiosBrowserListEntryRtgTag OBJECT-TYPE
    SYNTAX     Integer32 (0..65535)
    MAX-ACCESS read-only
    STATUS     current
    DESCRIPTION
            "-- empty --"
    ::= { hmSetupNetbiosBrowserListEntry 12 }

-- {SCALAR} 1.3.6.1.4.1.248.32.18.2.16.14
hmSetupNetbiosSupportBrowsing OBJECT-TYPE
    SYNTAX     INTEGER {
                  eNo (0),
                  eYes (1)
            }
    MAX-ACCESS read-write
    STATUS     current
    DESCRIPTION
            "-- empty --"
    ::= { hmSetupNetbios 14 }

-- {NODE} 1.3.6.1.4.1.248.32.18.2.17
hmSetupDns OBJECT IDENTIFIER ::= { hmSetup 17 }

-- {SCALAR} 1.3.6.1.4.1.248.32.18.2.17.1
hmSetupDnsOperating OBJECT-TYPE
    SYNTAX     INTEGER {
                  eNo (0),
                  eYes (1)
            }
    MAX-ACCESS read-write
    STATUS     current
    DESCRIPTION
            "-- empty --"
    ::= { hmSetupDns 1 }

-- {SCALAR} 1.3.6.1.4.1.248.32.18.2.17.2
hmSetupDnsDomain OBJECT-TYPE
    SYNTAX     DisplayString (SIZE(0..64))
    MAX-ACCESS read-write
    STATUS     current
    DESCRIPTION
            "-- empty --"
    ::= { hmSetupDns 2 }

-- {SCALAR} 1.3.6.1.4.1.248.32.18.2.17.3
hmSetupDnsDhcpUsage OBJECT-TYPE
    SYNTAX     INTEGER {
                  eNo (0),
                  eYes (1)
            }
    MAX-ACCESS read-write
    STATUS     current
    DESCRIPTION
            "-- empty --"
    ::= { hmSetupDns 3 }

-- {SCALAR} 1.3.6.1.4.1.248.32.18.2.17.4
hmSetupDnsNetbiosUsage OBJECT-TYPE
    SYNTAX     INTEGER {
                  eNo (0),
                  eYes (1)
            }
    MAX-ACCESS read-write
    STATUS     current
    DESCRIPTION
            "-- empty --"
    ::= { hmSetupDns 4 }

-- {TABLE} 1.3.6.1.4.1.248.32.18.2.17.5
hmSetupDnsDnsListTable OBJECT-TYPE
    SYNTAX     SEQUENCE OF HmSetupDnsDnsListEntry
    MAX-ACCESS not-accessible
    STATUS     current
    DESCRIPTION
            "-- empty --"
    ::= { hmSetupDns 5 }

-- {ROW} 1.3.6.1.4.1.248.32.18.2.17.5.1
hmSetupDnsDnsListEntry OBJECT-TYPE
    SYNTAX     HmSetupDnsDnsListEntry
    MAX-ACCESS not-accessible
    STATUS     current
    DESCRIPTION
            ""
    INDEX {
            hmSetupDnsDnsListEntryHostName,
            hmSetupDnsDnsListEntryRtgTag
          }
    ::= { hmSetupDnsDnsListTable 1 }

HmSetupDnsDnsListEntry ::= SEQUENCE {
            hmSetupDnsDnsListEntryHostName DisplayString,
            hmSetupDnsDnsListEntryIpAddress IpAddress,
            hmSetupDnsDnsListEntryIpv6Address DisplayString,
            hmSetupDnsDnsListEntryRtgTag Integer32
    }

-- {COLUMN} 1.3.6.1.4.1.248.32.18.2.17.5.1.1
hmSetupDnsDnsListEntryHostName OBJECT-TYPE
    SYNTAX     DisplayString (SIZE(0..64))
    MAX-ACCESS read-write
    STATUS     current
    DESCRIPTION
            "-- empty --"
    ::= { hmSetupDnsDnsListEntry 1 }

-- {COLUMN} 1.3.6.1.4.1.248.32.18.2.17.5.1.2
hmSetupDnsDnsListEntryIpAddress OBJECT-TYPE
    SYNTAX     IpAddress
    MAX-ACCESS read-write
    STATUS     current
    DESCRIPTION
            "-- empty --"
    ::= { hmSetupDnsDnsListEntry 2 }

-- {COLUMN} 1.3.6.1.4.1.248.32.18.2.17.5.1.3
hmSetupDnsDnsListEntryIpv6Address OBJECT-TYPE
    SYNTAX     DisplayString (SIZE(0..39))
    MAX-ACCESS read-write
    STATUS     current
    DESCRIPTION
            "-- empty --"
    ::= { hmSetupDnsDnsListEntry 3 }

-- {COLUMN} 1.3.6.1.4.1.248.32.18.2.17.5.1.4
hmSetupDnsDnsListEntryRtgTag OBJECT-TYPE
    SYNTAX     Integer32 (0..65535)
    MAX-ACCESS read-write
    STATUS     current
    DESCRIPTION
            "-- empty --"
    ::= { hmSetupDnsDnsListEntry 4 }

-- {TABLE} 1.3.6.1.4.1.248.32.18.2.17.6
hmSetupDnsFilterListTable OBJECT-TYPE
    SYNTAX     SEQUENCE OF HmSetupDnsFilterListEntry
    MAX-ACCESS not-accessible
    STATUS     current
    DESCRIPTION
            "-- empty --"
    ::= { hmSetupDns 6 }

-- {ROW} 1.3.6.1.4.1.248.32.18.2.17.6.1
hmSetupDnsFilterListEntry OBJECT-TYPE
    SYNTAX     HmSetupDnsFilterListEntry
    MAX-ACCESS not-accessible
    STATUS     current
    DESCRIPTION
            ""
    INDEX {
            hmSetupDnsFilterListEntryIdx
          }
    ::= { hmSetupDnsFilterListTable 1 }

HmSetupDnsFilterListEntry ::= SEQUENCE {
            hmSetupDnsFilterListEntryIdx DisplayString,
            hmSetupDnsFilterListEntryDomain DisplayString,
            hmSetupDnsFilterListEntryIpAddress IpAddress,
            hmSetupDnsFilterListEntryNetmask IpAddress,
            hmSetupDnsFilterListEntryIpv6Prefix DisplayString,
            hmSetupDnsFilterListEntryRtgTag Integer32
    }

-- {COLUMN} 1.3.6.1.4.1.248.32.18.2.17.6.1.1
hmSetupDnsFilterListEntryIdx OBJECT-TYPE
    SYNTAX     DisplayString (SIZE(0..4))
    MAX-ACCESS read-write
    STATUS     current
    DESCRIPTION
            "-- empty --"
    ::= { hmSetupDnsFilterListEntry 1 }

-- {COLUMN} 1.3.6.1.4.1.248.32.18.2.17.6.1.2
hmSetupDnsFilterListEntryDomain OBJECT-TYPE
    SYNTAX     DisplayString (SIZE(0..64))
    MAX-ACCESS read-write
    STATUS     current
    DESCRIPTION
            "-- empty --"
    ::= { hmSetupDnsFilterListEntry 2 }

-- {COLUMN} 1.3.6.1.4.1.248.32.18.2.17.6.1.3
hmSetupDnsFilterListEntryIpAddress OBJECT-TYPE
    SYNTAX     IpAddress
    MAX-ACCESS read-write
    STATUS     current
    DESCRIPTION
            "-- empty --"
    ::= { hmSetupDnsFilterListEntry 3 }

-- {COLUMN} 1.3.6.1.4.1.248.32.18.2.17.6.1.4
hmSetupDnsFilterListEntryNetmask OBJECT-TYPE
    SYNTAX     IpAddress
    MAX-ACCESS read-write
    STATUS     current
    DESCRIPTION
            "-- empty --"
    ::= { hmSetupDnsFilterListEntry 4 }

-- {COLUMN} 1.3.6.1.4.1.248.32.18.2.17.6.1.5
hmSetupDnsFilterListEntryIpv6Prefix OBJECT-TYPE
    SYNTAX     DisplayString (SIZE(0..43))
    MAX-ACCESS read-write
    STATUS     current
    DESCRIPTION
            "-- empty --"
    ::= { hmSetupDnsFilterListEntry 5 }

-- {COLUMN} 1.3.6.1.4.1.248.32.18.2.17.6.1.6
hmSetupDnsFilterListEntryRtgTag OBJECT-TYPE
    SYNTAX     Integer32 (0..65535)
    MAX-ACCESS read-write
    STATUS     current
    DESCRIPTION
            "-- empty --"
    ::= { hmSetupDnsFilterListEntry 6 }

-- {SCALAR} 1.3.6.1.4.1.248.32.18.2.17.7
hmSetupDnsLeasetime OBJECT-TYPE
    SYNTAX     Integer32 (0..65535)
    MAX-ACCESS read-write
    STATUS     current
    DESCRIPTION
            "-- empty --"
    ::= { hmSetupDns 7 }

-- {TABLE} 1.3.6.1.4.1.248.32.18.2.17.8
hmSetupDnsDynDnsListTable OBJECT-TYPE
    SYNTAX     SEQUENCE OF HmSetupDnsDynDnsListEntry
    MAX-ACCESS not-accessible
    STATUS     current
    DESCRIPTION
            "-- empty --"
    ::= { hmSetupDns 8 }

-- {ROW} 1.3.6.1.4.1.248.32.18.2.17.8.1
hmSetupDnsDynDnsListEntry OBJECT-TYPE
    SYNTAX     HmSetupDnsDynDnsListEntry
    MAX-ACCESS not-accessible
    STATUS     current
    DESCRIPTION
            ""
    INDEX {
            hmSetupDnsDynDnsListEntryHostName,
            hmSetupDnsDynDnsListEntryNetworkName
          }
    ::= { hmSetupDnsDynDnsListTable 1 }

HmSetupDnsDynDnsListEntry ::= SEQUENCE {
            hmSetupDnsDynDnsListEntryHostName DisplayString,
            hmSetupDnsDynDnsListEntryIpAddress IpAddress,
            hmSetupDnsDynDnsListEntryTimeout Integer32,
            hmSetupDnsDynDnsListEntryIpv6Address DisplayString,
            hmSetupDnsDynDnsListEntryNetworkName DisplayString
    }

-- {COLUMN} 1.3.6.1.4.1.248.32.18.2.17.8.1.1
hmSetupDnsDynDnsListEntryHostName OBJECT-TYPE
    SYNTAX     DisplayString (SIZE(0..64))
    MAX-ACCESS read-only
    STATUS     current
    DESCRIPTION
            "-- empty --"
    ::= { hmSetupDnsDynDnsListEntry 1 }

-- {COLUMN} 1.3.6.1.4.1.248.32.18.2.17.8.1.2
hmSetupDnsDynDnsListEntryIpAddress OBJECT-TYPE
    SYNTAX     IpAddress
    MAX-ACCESS read-only
    STATUS     current
    DESCRIPTION
            "-- empty --"
    ::= { hmSetupDnsDynDnsListEntry 2 }

-- {COLUMN} 1.3.6.1.4.1.248.32.18.2.17.8.1.3
hmSetupDnsDynDnsListEntryTimeout OBJECT-TYPE
    SYNTAX     Integer32 (0..2147483647)
    MAX-ACCESS read-only
    STATUS     current
    DESCRIPTION
            "-- empty --"
    ::= { hmSetupDnsDynDnsListEntry 3 }

-- {COLUMN} 1.3.6.1.4.1.248.32.18.2.17.8.1.4
hmSetupDnsDynDnsListEntryIpv6Address OBJECT-TYPE
    SYNTAX     DisplayString (SIZE(0..255))
    MAX-ACCESS read-only
    STATUS     current
    DESCRIPTION
            "-- empty --"
    ::= { hmSetupDnsDynDnsListEntry 4 }

-- {COLUMN} 1.3.6.1.4.1.248.32.18.2.17.8.1.5
hmSetupDnsDynDnsListEntryNetworkName OBJECT-TYPE
    SYNTAX     DisplayString (SIZE(0..16))
    MAX-ACCESS read-only
    STATUS     current
    DESCRIPTION
            "-- empty --"
    ::= { hmSetupDnsDynDnsListEntry 5 }

-- {TABLE} 1.3.6.1.4.1.248.32.18.2.17.9
hmSetupDnsDnsDestinationsTable OBJECT-TYPE
    SYNTAX     SEQUENCE OF HmSetupDnsDnsDestinationsEntry
    MAX-ACCESS not-accessible
    STATUS     current
    DESCRIPTION
            "-- empty --"
    ::= { hmSetupDns 9 }

-- {ROW} 1.3.6.1.4.1.248.32.18.2.17.9.1
hmSetupDnsDnsDestinationsEntry OBJECT-TYPE
    SYNTAX     HmSetupDnsDnsDestinationsEntry
    MAX-ACCESS not-accessible
    STATUS     current
    DESCRIPTION
            ""
    INDEX {
            hmSetupDnsDnsDestinationsEntryDomainName,
            hmSetupDnsDnsDestinationsEntryRtgTag
          }
    ::= { hmSetupDnsDnsDestinationsTable 1 }

HmSetupDnsDnsDestinationsEntry ::= SEQUENCE {
            hmSetupDnsDnsDestinationsEntryDomainName DisplayString,
            hmSetupDnsDnsDestinationsEntryDestination DisplayString,
            hmSetupDnsDnsDestinationsEntryRtgTag Integer32
    }

-- {COLUMN} 1.3.6.1.4.1.248.32.18.2.17.9.1.1
hmSetupDnsDnsDestinationsEntryDomainName OBJECT-TYPE
    SYNTAX     DisplayString (SIZE(0..64))
    MAX-ACCESS read-write
    STATUS     current
    DESCRIPTION
            "-- empty --"
    ::= { hmSetupDnsDnsDestinationsEntry 1 }

-- {COLUMN} 1.3.6.1.4.1.248.32.18.2.17.9.1.2
hmSetupDnsDnsDestinationsEntryDestination OBJECT-TYPE
    SYNTAX     DisplayString (SIZE(0..80))
    MAX-ACCESS read-write
    STATUS     current
    DESCRIPTION
            "-- empty --"
    ::= { hmSetupDnsDnsDestinationsEntry 2 }

-- {COLUMN} 1.3.6.1.4.1.248.32.18.2.17.9.1.3
hmSetupDnsDnsDestinationsEntryRtgTag OBJECT-TYPE
    SYNTAX     Integer32 (0..65535)
    MAX-ACCESS read-write
    STATUS     current
    DESCRIPTION
            "-- empty --"
    ::= { hmSetupDnsDnsDestinationsEntry 3 }

-- {TABLE} 1.3.6.1.4.1.248.32.18.2.17.10
hmSetupDnsServiceLocationListTable OBJECT-TYPE
    SYNTAX     SEQUENCE OF HmSetupDnsServiceLocationListEntry
    MAX-ACCESS not-accessible
    STATUS     current
    DESCRIPTION
            "-- empty --"
    ::= { hmSetupDns 10 }

-- {ROW} 1.3.6.1.4.1.248.32.18.2.17.10.1
hmSetupDnsServiceLocationListEntry OBJECT-TYPE
    SYNTAX     HmSetupDnsServiceLocationListEntry
    MAX-ACCESS not-accessible
    STATUS     current
    DESCRIPTION
            ""
    INDEX {
            hmSetupDnsServiceLocationListEntryServiceName,
            hmSetupDnsServiceLocationListEntryRtgTag
          }
    ::= { hmSetupDnsServiceLocationListTable 1 }

HmSetupDnsServiceLocationListEntry ::= SEQUENCE {
            hmSetupDnsServiceLocationListEntryServiceName DisplayString,
            hmSetupDnsServiceLocationListEntryHostName DisplayString,
            hmSetupDnsServiceLocationListEntryPort Integer32,
            hmSetupDnsServiceLocationListEntryRtgTag Integer32
    }

-- {COLUMN} 1.3.6.1.4.1.248.32.18.2.17.10.1.1
hmSetupDnsServiceLocationListEntryServiceName OBJECT-TYPE
    SYNTAX     DisplayString (SIZE(0..64))
    MAX-ACCESS read-write
    STATUS     current
    DESCRIPTION
            "-- empty --"
    ::= { hmSetupDnsServiceLocationListEntry 1 }

-- {COLUMN} 1.3.6.1.4.1.248.32.18.2.17.10.1.2
hmSetupDnsServiceLocationListEntryHostName OBJECT-TYPE
    SYNTAX     DisplayString (SIZE(0..64))
    MAX-ACCESS read-write
    STATUS     current
    DESCRIPTION
            "-- empty --"
    ::= { hmSetupDnsServiceLocationListEntry 2 }

-- {COLUMN} 1.3.6.1.4.1.248.32.18.2.17.10.1.3
hmSetupDnsServiceLocationListEntryPort OBJECT-TYPE
    SYNTAX     Integer32 (0..65535)
    MAX-ACCESS read-write
    STATUS     current
    DESCRIPTION
            "-- empty --"
    ::= { hmSetupDnsServiceLocationListEntry 3 }

-- {COLUMN} 1.3.6.1.4.1.248.32.18.2.17.10.1.4
hmSetupDnsServiceLocationListEntryRtgTag OBJECT-TYPE
    SYNTAX     Integer32 (0..65535)
    MAX-ACCESS read-write
    STATUS     current
    DESCRIPTION
            "-- empty --"
    ::= { hmSetupDnsServiceLocationListEntry 4 }

-- {TABLE} 1.3.6.1.4.1.248.32.18.2.17.11
hmSetupDnsDynamicSrvListTable OBJECT-TYPE
    SYNTAX     SEQUENCE OF HmSetupDnsDynamicSrvListEntry
    MAX-ACCESS not-accessible
    STATUS     current
    DESCRIPTION
            "-- empty --"
    ::= { hmSetupDns 11 }

-- {ROW} 1.3.6.1.4.1.248.32.18.2.17.11.1
hmSetupDnsDynamicSrvListEntry OBJECT-TYPE
    SYNTAX     HmSetupDnsDynamicSrvListEntry
    MAX-ACCESS not-accessible
    STATUS     current
    DESCRIPTION
            ""
    INDEX {
            hmSetupDnsDynamicSrvListEntryServiceName
          }
    ::= { hmSetupDnsDynamicSrvListTable 1 }

HmSetupDnsDynamicSrvListEntry ::= SEQUENCE {
            hmSetupDnsDynamicSrvListEntryServiceName DisplayString,
            hmSetupDnsDynamicSrvListEntryHostName DisplayString,
            hmSetupDnsDynamicSrvListEntryPort Integer32
    }

-- {COLUMN} 1.3.6.1.4.1.248.32.18.2.17.11.1.1
hmSetupDnsDynamicSrvListEntryServiceName OBJECT-TYPE
    SYNTAX     DisplayString (SIZE(0..64))
    MAX-ACCESS read-only
    STATUS     current
    DESCRIPTION
            "-- empty --"
    ::= { hmSetupDnsDynamicSrvListEntry 1 }

-- {COLUMN} 1.3.6.1.4.1.248.32.18.2.17.11.1.2
hmSetupDnsDynamicSrvListEntryHostName OBJECT-TYPE
    SYNTAX     DisplayString (SIZE(0..64))
    MAX-ACCESS read-only
    STATUS     current
    DESCRIPTION
            "-- empty --"
    ::= { hmSetupDnsDynamicSrvListEntry 2 }

-- {COLUMN} 1.3.6.1.4.1.248.32.18.2.17.11.1.3
hmSetupDnsDynamicSrvListEntryPort OBJECT-TYPE
    SYNTAX     Integer32 (0..65535)
    MAX-ACCESS read-only
    STATUS     current
    DESCRIPTION
            "-- empty --"
    ::= { hmSetupDnsDynamicSrvListEntry 3 }

-- {SCALAR} 1.3.6.1.4.1.248.32.18.2.17.12
hmSetupDnsResolveDomain OBJECT-TYPE
    SYNTAX     INTEGER {
                  eNo (0),
                  eYes (1)
            }
    MAX-ACCESS read-write
    STATUS     current
    DESCRIPTION
            "-- empty --"
    ::= { hmSetupDns 12 }

-- {TABLE} 1.3.6.1.4.1.248.32.18.2.17.13
hmSetupDnsSubDomainsTable OBJECT-TYPE
    SYNTAX     SEQUENCE OF HmSetupDnsSubDomainsEntry
    MAX-ACCESS not-accessible
    STATUS     current
    DESCRIPTION
            "-- empty --"
    ::= { hmSetupDns 13 }

-- {ROW} 1.3.6.1.4.1.248.32.18.2.17.13.1
hmSetupDnsSubDomainsEntry OBJECT-TYPE
    SYNTAX     HmSetupDnsSubDomainsEntry
    MAX-ACCESS not-accessible
    STATUS     current
    DESCRIPTION
            ""
    INDEX {
            hmSetupDnsSubDomainsEntryNetworkName
          }
    ::= { hmSetupDnsSubDomainsTable 1 }

HmSetupDnsSubDomainsEntry ::= SEQUENCE {
            hmSetupDnsSubDomainsEntryNetworkName DisplayString,
            hmSetupDnsSubDomainsEntrySubDomain DisplayString
    }

-- {COLUMN} 1.3.6.1.4.1.248.32.18.2.17.13.1.1
hmSetupDnsSubDomainsEntryNetworkName OBJECT-TYPE
    SYNTAX     DisplayString (SIZE(0..16))
    MAX-ACCESS read-write
    STATUS     current
    DESCRIPTION
            "-- empty --"
    ::= { hmSetupDnsSubDomainsEntry 1 }

-- {COLUMN} 1.3.6.1.4.1.248.32.18.2.17.13.1.2
hmSetupDnsSubDomainsEntrySubDomain OBJECT-TYPE
    SYNTAX     DisplayString (SIZE(0..64))
    MAX-ACCESS read-write
    STATUS     current
    DESCRIPTION
            "-- empty --"
    ::= { hmSetupDnsSubDomainsEntry 2 }

-- {SCALAR} 1.3.6.1.4.1.248.32.18.2.17.14
hmSetupDnsForwarder OBJECT-TYPE
    SYNTAX     INTEGER {
                  eNo (0),
                  eYes (1)
            }
    MAX-ACCESS read-write
    STATUS     current
    DESCRIPTION
            "-- empty --"
    ::= { hmSetupDns 14 }

-- {TABLE} 1.3.6.1.4.1.248.32.18.2.17.15
hmSetupDnsTagConfigurationTable OBJECT-TYPE
    SYNTAX     SEQUENCE OF HmSetupDnsTagConfigurationEntry
    MAX-ACCESS not-accessible
    STATUS     current
    DESCRIPTION
            "-- empty --"
    ::= { hmSetupDns 15 }

-- {ROW} 1.3.6.1.4.1.248.32.18.2.17.15.1
hmSetupDnsTagConfigurationEntry OBJECT-TYPE
    SYNTAX     HmSetupDnsTagConfigurationEntry
    MAX-ACCESS not-accessible
    STATUS     current
    DESCRIPTION
            ""
    INDEX {
            hmSetupDnsTagConfigurationEntryRtgTag
          }
    ::= { hmSetupDnsTagConfigurationTable 1 }

HmSetupDnsTagConfigurationEntry ::= SEQUENCE {
            hmSetupDnsTagConfigurationEntryRtgTag Integer32,
            hmSetupDnsTagConfigurationEntryOperating INTEGER,
            hmSetupDnsTagConfigurationEntryForwarder INTEGER,
            hmSetupDnsTagConfigurationEntryDhcpUsage INTEGER,
            hmSetupDnsTagConfigurationEntryNetbiosUsage INTEGER,
            hmSetupDnsTagConfigurationEntryResolveDomain INTEGER
    }

-- {COLUMN} 1.3.6.1.4.1.248.32.18.2.17.15.1.1
hmSetupDnsTagConfigurationEntryRtgTag OBJECT-TYPE
    SYNTAX     Integer32 (0..65535)
    MAX-ACCESS read-write
    STATUS     current
    DESCRIPTION
            "-- empty --"
    ::= { hmSetupDnsTagConfigurationEntry 1 }

-- {COLUMN} 1.3.6.1.4.1.248.32.18.2.17.15.1.2
hmSetupDnsTagConfigurationEntryOperating OBJECT-TYPE
    SYNTAX     INTEGER {
                  eNo (0),
                  eYes (1)
            }
    MAX-ACCESS read-write
    STATUS     current
    DESCRIPTION
            "-- empty --"
    ::= { hmSetupDnsTagConfigurationEntry 2 }

-- {COLUMN} 1.3.6.1.4.1.248.32.18.2.17.15.1.3
hmSetupDnsTagConfigurationEntryForwarder OBJECT-TYPE
    SYNTAX     INTEGER {
                  eNo (0),
                  eYes (1)
            }
    MAX-ACCESS read-write
    STATUS     current
    DESCRIPTION
            "-- empty --"
    ::= { hmSetupDnsTagConfigurationEntry 3 }

-- {COLUMN} 1.3.6.1.4.1.248.32.18.2.17.15.1.4
hmSetupDnsTagConfigurationEntryDhcpUsage OBJECT-TYPE
    SYNTAX     INTEGER {
                  eNo (0),
                  eYes (1)
            }
    MAX-ACCESS read-write
    STATUS     current
    DESCRIPTION
            "-- empty --"
    ::= { hmSetupDnsTagConfigurationEntry 4 }

-- {COLUMN} 1.3.6.1.4.1.248.32.18.2.17.15.1.5
hmSetupDnsTagConfigurationEntryNetbiosUsage OBJECT-TYPE
    SYNTAX     INTEGER {
                  eNo (0),
                  eYes (1)
            }
    MAX-ACCESS read-write
    STATUS     current
    DESCRIPTION
            "-- empty --"
    ::= { hmSetupDnsTagConfigurationEntry 5 }

-- {COLUMN} 1.3.6.1.4.1.248.32.18.2.17.15.1.6
hmSetupDnsTagConfigurationEntryResolveDomain OBJECT-TYPE
    SYNTAX     INTEGER {
                  eNo (0),
                  eYes (1)
            }
    MAX-ACCESS read-write
    STATUS     current
    DESCRIPTION
            "-- empty --"
    ::= { hmSetupDnsTagConfigurationEntry 6 }

-- {NODE} 1.3.6.1.4.1.248.32.18.2.18
hmSetupAccounting OBJECT IDENTIFIER ::= { hmSetup 18 }

-- {SCALAR} 1.3.6.1.4.1.248.32.18.2.18.1
hmSetupAccountingOperating OBJECT-TYPE
    SYNTAX     INTEGER {
                  eNo (0),
                  eYes (1)
            }
    MAX-ACCESS read-write
    STATUS     current
    DESCRIPTION
            "-- empty --"
    ::= { hmSetupAccounting 1 }

-- {SCALAR} 1.3.6.1.4.1.248.32.18.2.18.2
hmSetupAccountingSaveToFlashrom OBJECT-TYPE
    SYNTAX     INTEGER {
                  eNo (0),
                  eYes (1)
            }
    MAX-ACCESS read-write
    STATUS     current
    DESCRIPTION
            "-- empty --"
    ::= { hmSetupAccounting 2 }

-- {SCALAR} 1.3.6.1.4.1.248.32.18.2.18.3
hmSetupAccountingSortBy OBJECT-TYPE
    SYNTAX     INTEGER {
                  eTime (0),
                  eData (1)
            }
    MAX-ACCESS read-write
    STATUS     current
    DESCRIPTION
            "-- empty --"
    ::= { hmSetupAccounting 3 }

-- {TABLE} 1.3.6.1.4.1.248.32.18.2.18.4
hmSetupAccountingCurrentUserTable OBJECT-TYPE
    SYNTAX     SEQUENCE OF HmSetupAccountingCurrentUserEntry
    MAX-ACCESS not-accessible
    STATUS     current
    DESCRIPTION
            "-- empty --"
    ::= { hmSetupAccounting 4 }

-- {ROW} 1.3.6.1.4.1.248.32.18.2.18.4.1
hmSetupAccountingCurrentUserEntry OBJECT-TYPE
    SYNTAX     HmSetupAccountingCurrentUserEntry
    MAX-ACCESS not-accessible
    STATUS     current
    DESCRIPTION
            ""
    INDEX {
            hmSetupAccountingCurrentUserEntryUsername,
            hmSetupAccountingCurrentUserEntryMacAddress,
            hmSetupAccountingCurrentUserEntryPeer,
            hmSetupAccountingCurrentUserEntryConnType
          }
    ::= { hmSetupAccountingCurrentUserTable 1 }

HmSetupAccountingCurrentUserEntry ::= SEQUENCE {
            hmSetupAccountingCurrentUserEntryUsername DisplayString,
            hmSetupAccountingCurrentUserEntryMacAddress DisplayString,
            hmSetupAccountingCurrentUserEntryPeer DisplayString,
            hmSetupAccountingCurrentUserEntryConnType INTEGER,
            hmSetupAccountingCurrentUserEntryRxKbytes Integer32,
            hmSetupAccountingCurrentUserEntryTxKbytes Integer32,
            hmSetupAccountingCurrentUserEntryTotalTime Gauge32,
            hmSetupAccountingCurrentUserEntryConnections Integer32
    }

-- {COLUMN} 1.3.6.1.4.1.248.32.18.2.18.4.1.1
hmSetupAccountingCurrentUserEntryUsername OBJECT-TYPE
    SYNTAX     DisplayString (SIZE(0..28))
    MAX-ACCESS read-only
    STATUS     current
    DESCRIPTION
            "-- empty --"
    ::= { hmSetupAccountingCurrentUserEntry 1 }

-- {COLUMN} 1.3.6.1.4.1.248.32.18.2.18.4.1.2
hmSetupAccountingCurrentUserEntryMacAddress OBJECT-TYPE
    SYNTAX     DisplayString (SIZE(0..255))
    MAX-ACCESS read-only
    STATUS     current
    DESCRIPTION
            "-- empty --"
    ::= { hmSetupAccountingCurrentUserEntry 2 }

-- {COLUMN} 1.3.6.1.4.1.248.32.18.2.18.4.1.3
hmSetupAccountingCurrentUserEntryPeer OBJECT-TYPE
    SYNTAX     DisplayString (SIZE(0..16))
    MAX-ACCESS read-only
    STATUS     current
    DESCRIPTION
            "-- empty --"
    ::= { hmSetupAccountingCurrentUserEntry 3 }

-- {COLUMN} 1.3.6.1.4.1.248.32.18.2.18.4.1.4
hmSetupAccountingCurrentUserEntryConnType OBJECT-TYPE
    SYNTAX     INTEGER {
                  eUnknown (0),
                  eDialUp (1),
                  eLeasedLine (2),
                  eDslLine (4),
                  eVpnConn (7),
                  ePptpConn (8),
                  eL2tpConn (9),
                  eDsLiteConn (10),
                  eGreConn (11)
            }
    MAX-ACCESS read-only
    STATUS     current
    DESCRIPTION
            "-- empty --"
    ::= { hmSetupAccountingCurrentUserEntry 4 }

-- {COLUMN} 1.3.6.1.4.1.248.32.18.2.18.4.1.5
hmSetupAccountingCurrentUserEntryRxKbytes OBJECT-TYPE
    SYNTAX     Integer32 (0..2147483647)
    MAX-ACCESS read-only
    STATUS     current
    DESCRIPTION
            "-- empty --"
    ::= { hmSetupAccountingCurrentUserEntry 5 }

-- {COLUMN} 1.3.6.1.4.1.248.32.18.2.18.4.1.6
hmSetupAccountingCurrentUserEntryTxKbytes OBJECT-TYPE
    SYNTAX     Integer32 (0..2147483647)
    MAX-ACCESS read-only
    STATUS     current
    DESCRIPTION
            "-- empty --"
    ::= { hmSetupAccountingCurrentUserEntry 6 }

-- {COLUMN} 1.3.6.1.4.1.248.32.18.2.18.4.1.8
hmSetupAccountingCurrentUserEntryTotalTime OBJECT-TYPE
    SYNTAX     Gauge32
    MAX-ACCESS read-only
    STATUS     current
    DESCRIPTION
            "-- empty --"
    ::= { hmSetupAccountingCurrentUserEntry 8 }

-- {COLUMN} 1.3.6.1.4.1.248.32.18.2.18.4.1.9
hmSetupAccountingCurrentUserEntryConnections OBJECT-TYPE
    SYNTAX     Integer32 (0..2147483647)
    MAX-ACCESS read-only
    STATUS     current
    DESCRIPTION
            "-- empty --"
    ::= { hmSetupAccountingCurrentUserEntry 9 }

-- {TABLE} 1.3.6.1.4.1.248.32.18.2.18.5
hmSetupAccountingAccountingListTable OBJECT-TYPE
    SYNTAX     SEQUENCE OF HmSetupAccountingAccountingListEntry
    MAX-ACCESS not-accessible
    STATUS     current
    DESCRIPTION
            "-- empty --"
    ::= { hmSetupAccounting 5 }

-- {ROW} 1.3.6.1.4.1.248.32.18.2.18.5.1
hmSetupAccountingAccountingListEntry OBJECT-TYPE
    SYNTAX     HmSetupAccountingAccountingListEntry
    MAX-ACCESS not-accessible
    STATUS     current
    DESCRIPTION
            ""
    INDEX {
            hmSetupAccountingAccountingListEntryUsername,
            hmSetupAccountingAccountingListEntryMacAddress,
            hmSetupAccountingAccountingListEntryPeer,
            hmSetupAccountingAccountingListEntryConnType
          }
    ::= { hmSetupAccountingAccountingListTable 1 }

HmSetupAccountingAccountingListEntry ::= SEQUENCE {
            hmSetupAccountingAccountingListEntryUsername DisplayString,
            hmSetupAccountingAccountingListEntryMacAddress DisplayString,
            hmSetupAccountingAccountingListEntryPeer DisplayString,
            hmSetupAccountingAccountingListEntryConnType INTEGER,
            hmSetupAccountingAccountingListEntryRxKbytes Integer32,
            hmSetupAccountingAccountingListEntryTxKbytes Integer32,
            hmSetupAccountingAccountingListEntryTotalTime Gauge32,
            hmSetupAccountingAccountingListEntryConnections Integer32
    }

-- {COLUMN} 1.3.6.1.4.1.248.32.18.2.18.5.1.1
hmSetupAccountingAccountingListEntryUsername OBJECT-TYPE
    SYNTAX     DisplayString (SIZE(0..28))
    MAX-ACCESS read-only
    STATUS     current
    DESCRIPTION
            "-- empty --"
    ::= { hmSetupAccountingAccountingListEntry 1 }

-- {COLUMN} 1.3.6.1.4.1.248.32.18.2.18.5.1.2
hmSetupAccountingAccountingListEntryMacAddress OBJECT-TYPE
    SYNTAX     DisplayString (SIZE(0..255))
    MAX-ACCESS read-only
    STATUS     current
    DESCRIPTION
            "-- empty --"
    ::= { hmSetupAccountingAccountingListEntry 2 }

-- {COLUMN} 1.3.6.1.4.1.248.32.18.2.18.5.1.3
hmSetupAccountingAccountingListEntryPeer OBJECT-TYPE
    SYNTAX     DisplayString (SIZE(0..16))
    MAX-ACCESS read-only
    STATUS     current
    DESCRIPTION
            "-- empty --"
    ::= { hmSetupAccountingAccountingListEntry 3 }

-- {COLUMN} 1.3.6.1.4.1.248.32.18.2.18.5.1.4
hmSetupAccountingAccountingListEntryConnType OBJECT-TYPE
    SYNTAX     INTEGER {
                  eUnknown (0),
                  eDialUp (1),
                  eLeasedLine (2),
                  eDslLine (4),
                  eVpnConn (7),
                  ePptpConn (8),
                  eL2tpConn (9),
                  eDsLiteConn (10),
                  eGreConn (11)
            }
    MAX-ACCESS read-only
    STATUS     current
    DESCRIPTION
            "-- empty --"
    ::= { hmSetupAccountingAccountingListEntry 4 }

-- {COLUMN} 1.3.6.1.4.1.248.32.18.2.18.5.1.5
hmSetupAccountingAccountingListEntryRxKbytes OBJECT-TYPE
    SYNTAX     Integer32 (0..2147483647)
    MAX-ACCESS read-only
    STATUS     current
    DESCRIPTION
            "-- empty --"
    ::= { hmSetupAccountingAccountingListEntry 5 }

-- {COLUMN} 1.3.6.1.4.1.248.32.18.2.18.5.1.6
hmSetupAccountingAccountingListEntryTxKbytes OBJECT-TYPE
    SYNTAX     Integer32 (0..2147483647)
    MAX-ACCESS read-only
    STATUS     current
    DESCRIPTION
            "-- empty --"
    ::= { hmSetupAccountingAccountingListEntry 6 }

-- {COLUMN} 1.3.6.1.4.1.248.32.18.2.18.5.1.8
hmSetupAccountingAccountingListEntryTotalTime OBJECT-TYPE
    SYNTAX     Gauge32
    MAX-ACCESS read-only
    STATUS     current
    DESCRIPTION
            "-- empty --"
    ::= { hmSetupAccountingAccountingListEntry 8 }

-- {COLUMN} 1.3.6.1.4.1.248.32.18.2.18.5.1.9
hmSetupAccountingAccountingListEntryConnections OBJECT-TYPE
    SYNTAX     Integer32 (0..2147483647)
    MAX-ACCESS read-only
    STATUS     current
    DESCRIPTION
            "-- empty --"
    ::= { hmSetupAccountingAccountingListEntry 9 }

-- {SCALAR} 1.3.6.1.4.1.248.32.18.2.18.6
hmSetupAccountingDeleteAccountingList OBJECT-TYPE
    SYNTAX     DisplayString
    MAX-ACCESS read-write
    STATUS     current
    DESCRIPTION
            "-- empty --"
    ::= { hmSetupAccounting 6 }

-- {TABLE} 1.3.6.1.4.1.248.32.18.2.18.8
hmSetupAccountingTimeSnapshotTable OBJECT-TYPE
    SYNTAX     SEQUENCE OF HmSetupAccountingTimeSnapshotEntry
    MAX-ACCESS not-accessible
    STATUS     current
    DESCRIPTION
            "-- empty --"
    ::= { hmSetupAccounting 8 }

-- {ROW} 1.3.6.1.4.1.248.32.18.2.18.8.1
hmSetupAccountingTimeSnapshotEntry OBJECT-TYPE
    SYNTAX     HmSetupAccountingTimeSnapshotEntry
    MAX-ACCESS not-accessible
    STATUS     current
    DESCRIPTION
            ""
    INDEX {
            hmSetupAccountingTimeSnapshotEntryIndex
          }
    ::= { hmSetupAccountingTimeSnapshotTable 1 }

HmSetupAccountingTimeSnapshotEntry ::= SEQUENCE {
            hmSetupAccountingTimeSnapshotEntryIndex Integer32,
            hmSetupAccountingTimeSnapshotEntryActive INTEGER,
            hmSetupAccountingTimeSnapshotEntryType INTEGER,
            hmSetupAccountingTimeSnapshotEntryDay Integer32,
            hmSetupAccountingTimeSnapshotEntryDayofweek INTEGER,
            hmSetupAccountingTimeSnapshotEntryHour Integer32,
            hmSetupAccountingTimeSnapshotEntryMinute Integer32
    }

-- {COLUMN} 1.3.6.1.4.1.248.32.18.2.18.8.1.1
hmSetupAccountingTimeSnapshotEntryIndex OBJECT-TYPE
    SYNTAX     Integer32 (0..255)
    MAX-ACCESS read-only
    STATUS     current
    DESCRIPTION
            "-- empty --"
    ::= { hmSetupAccountingTimeSnapshotEntry 1 }

-- {COLUMN} 1.3.6.1.4.1.248.32.18.2.18.8.1.2
hmSetupAccountingTimeSnapshotEntryActive OBJECT-TYPE
    SYNTAX     INTEGER {
                  eNo (0),
                  eYes (1)
            }
    MAX-ACCESS read-write
    STATUS     current
    DESCRIPTION
            "-- empty --"
    ::= { hmSetupAccountingTimeSnapshotEntry 2 }

-- {COLUMN} 1.3.6.1.4.1.248.32.18.2.18.8.1.3
hmSetupAccountingTimeSnapshotEntryType OBJECT-TYPE
    SYNTAX     INTEGER {
                  eMonthly (0),
                  eWeekly (1),
                  eDaily (2)
            }
    MAX-ACCESS read-write
    STATUS     current
    DESCRIPTION
            "-- empty --"
    ::= { hmSetupAccountingTimeSnapshotEntry 3 }

-- {COLUMN} 1.3.6.1.4.1.248.32.18.2.18.8.1.4
hmSetupAccountingTimeSnapshotEntryDay OBJECT-TYPE
    SYNTAX     Integer32 (0..255)
    MAX-ACCESS read-write
    STATUS     current
    DESCRIPTION
            "-- empty --"
    ::= { hmSetupAccountingTimeSnapshotEntry 4 }

-- {COLUMN} 1.3.6.1.4.1.248.32.18.2.18.8.1.5
hmSetupAccountingTimeSnapshotEntryDayofweek OBJECT-TYPE
    SYNTAX     INTEGER {
                  eUnknown (0),
                  eSunday (1),
                  eMonday (2),
                  eTuesday (3),
                  eWednesday (4),
                  eThursday (5),
                  eFriday (6),
                  eSaturday (7)
            }
    MAX-ACCESS read-write
    STATUS     current
    DESCRIPTION
            "-- empty --"
    ::= { hmSetupAccountingTimeSnapshotEntry 5 }

-- {COLUMN} 1.3.6.1.4.1.248.32.18.2.18.8.1.6
hmSetupAccountingTimeSnapshotEntryHour OBJECT-TYPE
    SYNTAX     Integer32 (0..255)
    MAX-ACCESS read-write
    STATUS     current
    DESCRIPTION
            "-- empty --"
    ::= { hmSetupAccountingTimeSnapshotEntry 6 }

-- {COLUMN} 1.3.6.1.4.1.248.32.18.2.18.8.1.7
hmSetupAccountingTimeSnapshotEntryMinute OBJECT-TYPE
    SYNTAX     Integer32 (0..255)
    MAX-ACCESS read-write
    STATUS     current
    DESCRIPTION
            "-- empty --"
    ::= { hmSetupAccountingTimeSnapshotEntry 7 }

-- {TABLE} 1.3.6.1.4.1.248.32.18.2.18.9
hmSetupAccountingLastSnapshotTable OBJECT-TYPE
    SYNTAX     SEQUENCE OF HmSetupAccountingLastSnapshotEntry
    MAX-ACCESS not-accessible
    STATUS     current
    DESCRIPTION
            "-- empty --"
    ::= { hmSetupAccounting 9 }

-- {ROW} 1.3.6.1.4.1.248.32.18.2.18.9.1
hmSetupAccountingLastSnapshotEntry OBJECT-TYPE
    SYNTAX     HmSetupAccountingLastSnapshotEntry
    MAX-ACCESS not-accessible
    STATUS     current
    DESCRIPTION
            ""
    INDEX {
            hmSetupAccountingLastSnapshotEntryUsername,
            hmSetupAccountingLastSnapshotEntryMacAddress,
            hmSetupAccountingLastSnapshotEntryPeer,
            hmSetupAccountingLastSnapshotEntryConnType
          }
    ::= { hmSetupAccountingLastSnapshotTable 1 }

HmSetupAccountingLastSnapshotEntry ::= SEQUENCE {
            hmSetupAccountingLastSnapshotEntryUsername DisplayString,
            hmSetupAccountingLastSnapshotEntryMacAddress DisplayString,
            hmSetupAccountingLastSnapshotEntryPeer DisplayString,
            hmSetupAccountingLastSnapshotEntryConnType INTEGER,
            hmSetupAccountingLastSnapshotEntryRxKbytes Integer32,
            hmSetupAccountingLastSnapshotEntryTxKbytes Integer32,
            hmSetupAccountingLastSnapshotEntryTotalTime Gauge32,
            hmSetupAccountingLastSnapshotEntryConnections Integer32
    }

-- {COLUMN} 1.3.6.1.4.1.248.32.18.2.18.9.1.1
hmSetupAccountingLastSnapshotEntryUsername OBJECT-TYPE
    SYNTAX     DisplayString (SIZE(0..28))
    MAX-ACCESS read-only
    STATUS     current
    DESCRIPTION
            "-- empty --"
    ::= { hmSetupAccountingLastSnapshotEntry 1 }

-- {COLUMN} 1.3.6.1.4.1.248.32.18.2.18.9.1.2
hmSetupAccountingLastSnapshotEntryMacAddress OBJECT-TYPE
    SYNTAX     DisplayString (SIZE(0..255))
    MAX-ACCESS read-only
    STATUS     current
    DESCRIPTION
            "-- empty --"
    ::= { hmSetupAccountingLastSnapshotEntry 2 }

-- {COLUMN} 1.3.6.1.4.1.248.32.18.2.18.9.1.3
hmSetupAccountingLastSnapshotEntryPeer OBJECT-TYPE
    SYNTAX     DisplayString (SIZE(0..16))
    MAX-ACCESS read-only
    STATUS     current
    DESCRIPTION
            "-- empty --"
    ::= { hmSetupAccountingLastSnapshotEntry 3 }

-- {COLUMN} 1.3.6.1.4.1.248.32.18.2.18.9.1.4
hmSetupAccountingLastSnapshotEntryConnType OBJECT-TYPE
    SYNTAX     INTEGER {
                  eUnknown (0),
                  eDialUp (1),
                  eLeasedLine (2),
                  eDslLine (4),
                  eVpnConn (7),
                  ePptpConn (8),
                  eL2tpConn (9),
                  eDsLiteConn (10),
                  eGreConn (11)
            }
    MAX-ACCESS read-only
    STATUS     current
    DESCRIPTION
            "-- empty --"
    ::= { hmSetupAccountingLastSnapshotEntry 4 }

-- {COLUMN} 1.3.6.1.4.1.248.32.18.2.18.9.1.5
hmSetupAccountingLastSnapshotEntryRxKbytes OBJECT-TYPE
    SYNTAX     Integer32 (0..2147483647)
    MAX-ACCESS read-only
    STATUS     current
    DESCRIPTION
            "-- empty --"
    ::= { hmSetupAccountingLastSnapshotEntry 5 }

-- {COLUMN} 1.3.6.1.4.1.248.32.18.2.18.9.1.6
hmSetupAccountingLastSnapshotEntryTxKbytes OBJECT-TYPE
    SYNTAX     Integer32 (0..2147483647)
    MAX-ACCESS read-only
    STATUS     current
    DESCRIPTION
            "-- empty --"
    ::= { hmSetupAccountingLastSnapshotEntry 6 }

-- {COLUMN} 1.3.6.1.4.1.248.32.18.2.18.9.1.8
hmSetupAccountingLastSnapshotEntryTotalTime OBJECT-TYPE
    SYNTAX     Gauge32
    MAX-ACCESS read-only
    STATUS     current
    DESCRIPTION
            "-- empty --"
    ::= { hmSetupAccountingLastSnapshotEntry 8 }

-- {COLUMN} 1.3.6.1.4.1.248.32.18.2.18.9.1.9
hmSetupAccountingLastSnapshotEntryConnections OBJECT-TYPE
    SYNTAX     Integer32 (0..2147483647)
    MAX-ACCESS read-only
    STATUS     current
    DESCRIPTION
            "-- empty --"
    ::= { hmSetupAccountingLastSnapshotEntry 9 }

-- {SCALAR} 1.3.6.1.4.1.248.32.18.2.18.10
hmSetupAccountingDiscriminator OBJECT-TYPE
    SYNTAX     INTEGER {
                  eMacAddress (0),
                  eIpAddress (1)
            }
    MAX-ACCESS read-write
    STATUS     current
    DESCRIPTION
            "-- empty --"
    ::= { hmSetupAccounting 10 }

-- {NODE} 1.3.6.1.4.1.248.32.18.2.19
hmSetupVpn OBJECT IDENTIFIER ::= { hmSetup 19 }

-- {NODE} 1.3.6.1.4.1.248.32.18.2.19.3
hmSetupVpnIsakmp OBJECT IDENTIFIER ::= { hmSetupVpn 3 }

-- {TABLE} 1.3.6.1.4.1.248.32.18.2.19.3.4
hmSetupVpnIsakmpTimerTable OBJECT-TYPE
    SYNTAX     SEQUENCE OF HmSetupVpnIsakmpTimerEntry
    MAX-ACCESS not-accessible
    STATUS     current
    DESCRIPTION
            "-- empty --"
    ::= { hmSetupVpnIsakmp 4 }

-- {ROW} 1.3.6.1.4.1.248.32.18.2.19.3.4.1
hmSetupVpnIsakmpTimerEntry OBJECT-TYPE
    SYNTAX     HmSetupVpnIsakmpTimerEntry
    MAX-ACCESS not-accessible
    STATUS     current
    DESCRIPTION
            ""
    INDEX {
            hmSetupVpnIsakmpTimerEntryIdx
          }
    ::= { hmSetupVpnIsakmpTimerTable 1 }

HmSetupVpnIsakmpTimerEntry ::= SEQUENCE {
            hmSetupVpnIsakmpTimerEntryRetrLim Integer32,
            hmSetupVpnIsakmpTimerEntryRetrTim Integer32,
            hmSetupVpnIsakmpTimerEntryRetrTimUsec Integer32,
            hmSetupVpnIsakmpTimerEntryRetrTimMax Integer32,
            hmSetupVpnIsakmpTimerEntryExpTim Integer32,
            hmSetupVpnIsakmpTimerEntryIdx Integer32
    }

-- {COLUMN} 1.3.6.1.4.1.248.32.18.2.19.3.4.1.1
hmSetupVpnIsakmpTimerEntryRetrLim OBJECT-TYPE
    SYNTAX     Integer32 (0..65535)
    MAX-ACCESS read-write
    STATUS     current
    DESCRIPTION
            "-- empty --"
    ::= { hmSetupVpnIsakmpTimerEntry 1 }

-- {COLUMN} 1.3.6.1.4.1.248.32.18.2.19.3.4.1.2
hmSetupVpnIsakmpTimerEntryRetrTim OBJECT-TYPE
    SYNTAX     Integer32 (0..65535)
    MAX-ACCESS read-write
    STATUS     current
    DESCRIPTION
            "-- empty --"
    ::= { hmSetupVpnIsakmpTimerEntry 2 }

-- {COLUMN} 1.3.6.1.4.1.248.32.18.2.19.3.4.1.3
hmSetupVpnIsakmpTimerEntryRetrTimUsec OBJECT-TYPE
    SYNTAX     Integer32 (0..2147483647)
    MAX-ACCESS read-write
    STATUS     current
    DESCRIPTION
            "-- empty --"
    ::= { hmSetupVpnIsakmpTimerEntry 3 }

-- {COLUMN} 1.3.6.1.4.1.248.32.18.2.19.3.4.1.4
hmSetupVpnIsakmpTimerEntryRetrTimMax OBJECT-TYPE
    SYNTAX     Integer32 (0..65535)
    MAX-ACCESS read-write
    STATUS     current
    DESCRIPTION
            "-- empty --"
    ::= { hmSetupVpnIsakmpTimerEntry 4 }

-- {COLUMN} 1.3.6.1.4.1.248.32.18.2.19.3.4.1.5
hmSetupVpnIsakmpTimerEntryExpTim OBJECT-TYPE
    SYNTAX     Integer32 (0..65535)
    MAX-ACCESS read-write
    STATUS     current
    DESCRIPTION
            "-- empty --"
    ::= { hmSetupVpnIsakmpTimerEntry 5 }

-- {COLUMN} 1.3.6.1.4.1.248.32.18.2.19.3.4.1.6
hmSetupVpnIsakmpTimerEntryIdx OBJECT-TYPE
    SYNTAX     Integer32 (0..255)
    MAX-ACCESS read-only
    STATUS     current
    DESCRIPTION
            "-- empty --"
    ::= { hmSetupVpnIsakmpTimerEntry 6 }

-- {NODE} 1.3.6.1.4.1.248.32.18.2.19.3.29
hmSetupVpnIsakmpDhGroups OBJECT IDENTIFIER ::= { hmSetupVpnIsakmp 29 }

-- {SCALAR} 1.3.6.1.4.1.248.32.18.2.19.3.29.1
hmSetupVpnIsakmpDhGroupsPrecalculation OBJECT-TYPE
    SYNTAX     INTEGER {
                  eNo (0),
                  eYes (1)
            }
    MAX-ACCESS read-write
    STATUS     current
    DESCRIPTION
            "-- empty --"
    ::= { hmSetupVpnIsakmpDhGroups 1 }

-- {TABLE} 1.3.6.1.4.1.248.32.18.2.19.3.29.2
hmSetupVpnIsakmpDhGroupsGroupConfigTable OBJECT-TYPE
    SYNTAX     SEQUENCE OF HmSetupVpnIsakmpDhGroupsGroupConfigEntry
    MAX-ACCESS not-accessible
    STATUS     current
    DESCRIPTION
            "-- empty --"
    ::= { hmSetupVpnIsakmpDhGroups 2 }

-- {ROW} 1.3.6.1.4.1.248.32.18.2.19.3.29.2.1
hmSetupVpnIsakmpDhGroupsGroupConfigEntry OBJECT-TYPE
    SYNTAX     HmSetupVpnIsakmpDhGroupsGroupConfigEntry
    MAX-ACCESS not-accessible
    STATUS     current
    DESCRIPTION
            ""
    INDEX {
            hmSetupVpnIsakmpDhGroupsGroupConfigEntryDhGroup
          }
    ::= { hmSetupVpnIsakmpDhGroupsGroupConfigTable 1 }

HmSetupVpnIsakmpDhGroupsGroupConfigEntry ::= SEQUENCE {
            hmSetupVpnIsakmpDhGroupsGroupConfigEntryDhGroup Integer32,
            hmSetupVpnIsakmpDhGroupsGroupConfigEntryPrecalcTarget Integer32
    }

-- {COLUMN} 1.3.6.1.4.1.248.32.18.2.19.3.29.2.1.1
hmSetupVpnIsakmpDhGroupsGroupConfigEntryDhGroup OBJECT-TYPE
    SYNTAX     Integer32 (0..255)
    MAX-ACCESS read-only
    STATUS     current
    DESCRIPTION
            "-- empty --"
    ::= { hmSetupVpnIsakmpDhGroupsGroupConfigEntry 1 }

-- {COLUMN} 1.3.6.1.4.1.248.32.18.2.19.3.29.2.1.2
hmSetupVpnIsakmpDhGroupsGroupConfigEntryPrecalcTarget OBJECT-TYPE
    SYNTAX     Integer32 (0..2147483647)
    MAX-ACCESS read-write
    STATUS     current
    DESCRIPTION
            "-- empty --"
    ::= { hmSetupVpnIsakmpDhGroupsGroupConfigEntry 2 }

-- {NODE} 1.3.6.1.4.1.248.32.18.2.19.4
hmSetupVpnProposals OBJECT IDENTIFIER ::= { hmSetupVpn 4 }

-- {TABLE} 1.3.6.1.4.1.248.32.18.2.19.4.9
hmSetupVpnProposalsIkeProposalListsTable OBJECT-TYPE
    SYNTAX     SEQUENCE OF HmSetupVpnProposalsIkeProposalListsEntry
    MAX-ACCESS not-accessible
    STATUS     current
    DESCRIPTION
            "-- empty --"
    ::= { hmSetupVpnProposals 9 }

-- {ROW} 1.3.6.1.4.1.248.32.18.2.19.4.9.1
hmSetupVpnProposalsIkeProposalListsEntry OBJECT-TYPE
    SYNTAX     HmSetupVpnProposalsIkeProposalListsEntry
    MAX-ACCESS not-accessible
    STATUS     current
    DESCRIPTION
            ""
    INDEX {
            hmSetupVpnProposalsIkeProposalListsEntryIkeProposalLists
          }
    ::= { hmSetupVpnProposalsIkeProposalListsTable 1 }

HmSetupVpnProposalsIkeProposalListsEntry ::= SEQUENCE {
            hmSetupVpnProposalsIkeProposalListsEntryIkeProposalLists DisplayString,
            hmSetupVpnProposalsIkeProposalListsEntryIkeProposal1 DisplayString,
            hmSetupVpnProposalsIkeProposalListsEntryIkeProposal2 DisplayString,
            hmSetupVpnProposalsIkeProposalListsEntryIkeProposal3 DisplayString,
            hmSetupVpnProposalsIkeProposalListsEntryIkeProposal4 DisplayString,
            hmSetupVpnProposalsIkeProposalListsEntryIkeProposal5 DisplayString,
            hmSetupVpnProposalsIkeProposalListsEntryIkeProposal6 DisplayString,
            hmSetupVpnProposalsIkeProposalListsEntryIkeProposal7 DisplayString,
            hmSetupVpnProposalsIkeProposalListsEntryIkeProposal8 DisplayString
    }

-- {COLUMN} 1.3.6.1.4.1.248.32.18.2.19.4.9.1.1
hmSetupVpnProposalsIkeProposalListsEntryIkeProposalLists OBJECT-TYPE
    SYNTAX     DisplayString (SIZE(0..17))
    MAX-ACCESS read-write
    STATUS     current
    DESCRIPTION
            "-- empty --"
    ::= { hmSetupVpnProposalsIkeProposalListsEntry 1 }

-- {COLUMN} 1.3.6.1.4.1.248.32.18.2.19.4.9.1.2
hmSetupVpnProposalsIkeProposalListsEntryIkeProposal1 OBJECT-TYPE
    SYNTAX     DisplayString (SIZE(0..17))
    MAX-ACCESS read-write
    STATUS     current
    DESCRIPTION
            "-- empty --"
    ::= { hmSetupVpnProposalsIkeProposalListsEntry 2 }

-- {COLUMN} 1.3.6.1.4.1.248.32.18.2.19.4.9.1.3
hmSetupVpnProposalsIkeProposalListsEntryIkeProposal2 OBJECT-TYPE
    SYNTAX     DisplayString (SIZE(0..17))
    MAX-ACCESS read-write
    STATUS     current
    DESCRIPTION
            "-- empty --"
    ::= { hmSetupVpnProposalsIkeProposalListsEntry 3 }

-- {COLUMN} 1.3.6.1.4.1.248.32.18.2.19.4.9.1.4
hmSetupVpnProposalsIkeProposalListsEntryIkeProposal3 OBJECT-TYPE
    SYNTAX     DisplayString (SIZE(0..17))
    MAX-ACCESS read-write
    STATUS     current
    DESCRIPTION
            "-- empty --"
    ::= { hmSetupVpnProposalsIkeProposalListsEntry 4 }

-- {COLUMN} 1.3.6.1.4.1.248.32.18.2.19.4.9.1.5
hmSetupVpnProposalsIkeProposalListsEntryIkeProposal4 OBJECT-TYPE
    SYNTAX     DisplayString (SIZE(0..17))
    MAX-ACCESS read-write
    STATUS     current
    DESCRIPTION
            "-- empty --"
    ::= { hmSetupVpnProposalsIkeProposalListsEntry 5 }

-- {COLUMN} 1.3.6.1.4.1.248.32.18.2.19.4.9.1.6
hmSetupVpnProposalsIkeProposalListsEntryIkeProposal5 OBJECT-TYPE
    SYNTAX     DisplayString (SIZE(0..17))
    MAX-ACCESS read-write
    STATUS     current
    DESCRIPTION
            "-- empty --"
    ::= { hmSetupVpnProposalsIkeProposalListsEntry 6 }

-- {COLUMN} 1.3.6.1.4.1.248.32.18.2.19.4.9.1.7
hmSetupVpnProposalsIkeProposalListsEntryIkeProposal6 OBJECT-TYPE
    SYNTAX     DisplayString (SIZE(0..17))
    MAX-ACCESS read-write
    STATUS     current
    DESCRIPTION
            "-- empty --"
    ::= { hmSetupVpnProposalsIkeProposalListsEntry 7 }

-- {COLUMN} 1.3.6.1.4.1.248.32.18.2.19.4.9.1.8
hmSetupVpnProposalsIkeProposalListsEntryIkeProposal7 OBJECT-TYPE
    SYNTAX     DisplayString (SIZE(0..17))
    MAX-ACCESS read-write
    STATUS     current
    DESCRIPTION
            "-- empty --"
    ::= { hmSetupVpnProposalsIkeProposalListsEntry 8 }

-- {COLUMN} 1.3.6.1.4.1.248.32.18.2.19.4.9.1.9
hmSetupVpnProposalsIkeProposalListsEntryIkeProposal8 OBJECT-TYPE
    SYNTAX     DisplayString (SIZE(0..17))
    MAX-ACCESS read-write
    STATUS     current
    DESCRIPTION
            "-- empty --"
    ::= { hmSetupVpnProposalsIkeProposalListsEntry 9 }

-- {TABLE} 1.3.6.1.4.1.248.32.18.2.19.4.10
hmSetupVpnProposalsIpsecProposalListsTable OBJECT-TYPE
    SYNTAX     SEQUENCE OF HmSetupVpnProposalsIpsecProposalListsEntry
    MAX-ACCESS not-accessible
    STATUS     current
    DESCRIPTION
            "-- empty --"
    ::= { hmSetupVpnProposals 10 }

-- {ROW} 1.3.6.1.4.1.248.32.18.2.19.4.10.1
hmSetupVpnProposalsIpsecProposalListsEntry OBJECT-TYPE
    SYNTAX     HmSetupVpnProposalsIpsecProposalListsEntry
    MAX-ACCESS not-accessible
    STATUS     current
    DESCRIPTION
            ""
    INDEX {
            hmSetupVpnProposalsIpsecProposalListsEntryIpsecProposalLists
          }
    ::= { hmSetupVpnProposalsIpsecProposalListsTable 1 }

HmSetupVpnProposalsIpsecProposalListsEntry ::= SEQUENCE {
            hmSetupVpnProposalsIpsecProposalListsEntryIpsecProposalLists DisplayString,
            hmSetupVpnProposalsIpsecProposalListsEntryIpsecProposal1 DisplayString,
            hmSetupVpnProposalsIpsecProposalListsEntryIpsecProposal2 DisplayString,
            hmSetupVpnProposalsIpsecProposalListsEntryIpsecProposal3 DisplayString,
            hmSetupVpnProposalsIpsecProposalListsEntryIpsecProposal4 DisplayString,
            hmSetupVpnProposalsIpsecProposalListsEntryIpsecProposal5 DisplayString,
            hmSetupVpnProposalsIpsecProposalListsEntryIpsecProposal6 DisplayString,
            hmSetupVpnProposalsIpsecProposalListsEntryIpsecProposal7 DisplayString,
            hmSetupVpnProposalsIpsecProposalListsEntryIpsecProposal8 DisplayString
    }

-- {COLUMN} 1.3.6.1.4.1.248.32.18.2.19.4.10.1.1
hmSetupVpnProposalsIpsecProposalListsEntryIpsecProposalLists OBJECT-TYPE
    SYNTAX     DisplayString (SIZE(0..17))
    MAX-ACCESS read-write
    STATUS     current
    DESCRIPTION
            "-- empty --"
    ::= { hmSetupVpnProposalsIpsecProposalListsEntry 1 }

-- {COLUMN} 1.3.6.1.4.1.248.32.18.2.19.4.10.1.2
hmSetupVpnProposalsIpsecProposalListsEntryIpsecProposal1 OBJECT-TYPE
    SYNTAX     DisplayString (SIZE(0..17))
    MAX-ACCESS read-write
    STATUS     current
    DESCRIPTION
            "-- empty --"
    ::= { hmSetupVpnProposalsIpsecProposalListsEntry 2 }

-- {COLUMN} 1.3.6.1.4.1.248.32.18.2.19.4.10.1.3
hmSetupVpnProposalsIpsecProposalListsEntryIpsecProposal2 OBJECT-TYPE
    SYNTAX     DisplayString (SIZE(0..17))
    MAX-ACCESS read-write
    STATUS     current
    DESCRIPTION
            "-- empty --"
    ::= { hmSetupVpnProposalsIpsecProposalListsEntry 3 }

-- {COLUMN} 1.3.6.1.4.1.248.32.18.2.19.4.10.1.4
hmSetupVpnProposalsIpsecProposalListsEntryIpsecProposal3 OBJECT-TYPE
    SYNTAX     DisplayString (SIZE(0..17))
    MAX-ACCESS read-write
    STATUS     current
    DESCRIPTION
            "-- empty --"
    ::= { hmSetupVpnProposalsIpsecProposalListsEntry 4 }

-- {COLUMN} 1.3.6.1.4.1.248.32.18.2.19.4.10.1.5
hmSetupVpnProposalsIpsecProposalListsEntryIpsecProposal4 OBJECT-TYPE
    SYNTAX     DisplayString (SIZE(0..17))
    MAX-ACCESS read-write
    STATUS     current
    DESCRIPTION
            "-- empty --"
    ::= { hmSetupVpnProposalsIpsecProposalListsEntry 5 }

-- {COLUMN} 1.3.6.1.4.1.248.32.18.2.19.4.10.1.6
hmSetupVpnProposalsIpsecProposalListsEntryIpsecProposal5 OBJECT-TYPE
    SYNTAX     DisplayString (SIZE(0..17))
    MAX-ACCESS read-write
    STATUS     current
    DESCRIPTION
            "-- empty --"
    ::= { hmSetupVpnProposalsIpsecProposalListsEntry 6 }

-- {COLUMN} 1.3.6.1.4.1.248.32.18.2.19.4.10.1.7
hmSetupVpnProposalsIpsecProposalListsEntryIpsecProposal6 OBJECT-TYPE
    SYNTAX     DisplayString (SIZE(0..17))
    MAX-ACCESS read-write
    STATUS     current
    DESCRIPTION
            "-- empty --"
    ::= { hmSetupVpnProposalsIpsecProposalListsEntry 7 }

-- {COLUMN} 1.3.6.1.4.1.248.32.18.2.19.4.10.1.8
hmSetupVpnProposalsIpsecProposalListsEntryIpsecProposal7 OBJECT-TYPE
    SYNTAX     DisplayString (SIZE(0..17))
    MAX-ACCESS read-write
    STATUS     current
    DESCRIPTION
            "-- empty --"
    ::= { hmSetupVpnProposalsIpsecProposalListsEntry 8 }

-- {COLUMN} 1.3.6.1.4.1.248.32.18.2.19.4.10.1.9
hmSetupVpnProposalsIpsecProposalListsEntryIpsecProposal8 OBJECT-TYPE
    SYNTAX     DisplayString (SIZE(0..17))
    MAX-ACCESS read-write
    STATUS     current
    DESCRIPTION
            "-- empty --"
    ::= { hmSetupVpnProposalsIpsecProposalListsEntry 9 }

-- {TABLE} 1.3.6.1.4.1.248.32.18.2.19.4.11
hmSetupVpnProposalsIkeTable OBJECT-TYPE
    SYNTAX     SEQUENCE OF HmSetupVpnProposalsIkeEntry
    MAX-ACCESS not-accessible
    STATUS     current
    DESCRIPTION
            "-- empty --"
    ::= { hmSetupVpnProposals 11 }

-- {ROW} 1.3.6.1.4.1.248.32.18.2.19.4.11.1
hmSetupVpnProposalsIkeEntry OBJECT-TYPE
    SYNTAX     HmSetupVpnProposalsIkeEntry
    MAX-ACCESS not-accessible
    STATUS     current
    DESCRIPTION
            ""
    INDEX {
            hmSetupVpnProposalsIkeEntryName
          }
    ::= { hmSetupVpnProposalsIkeTable 1 }

HmSetupVpnProposalsIkeEntry ::= SEQUENCE {
            hmSetupVpnProposalsIkeEntryName DisplayString,
            hmSetupVpnProposalsIkeEntryIkeCryptAlg INTEGER,
            hmSetupVpnProposalsIkeEntryIkeCryptKeylen Integer32,
            hmSetupVpnProposalsIkeEntryIkeAuthAlg INTEGER,
            hmSetupVpnProposalsIkeEntryIkeAuthMode INTEGER,
            hmSetupVpnProposalsIkeEntryLifetimeSec Integer32,
            hmSetupVpnProposalsIkeEntryLifetimeKb Integer32
    }

-- {COLUMN} 1.3.6.1.4.1.248.32.18.2.19.4.11.1.1
hmSetupVpnProposalsIkeEntryName OBJECT-TYPE
    SYNTAX     DisplayString (SIZE(0..17))
    MAX-ACCESS read-write
    STATUS     current
    DESCRIPTION
            "-- empty --"
    ::= { hmSetupVpnProposalsIkeEntry 1 }

-- {COLUMN} 1.3.6.1.4.1.248.32.18.2.19.4.11.1.2
hmSetupVpnProposalsIkeEntryIkeCryptAlg OBJECT-TYPE
    SYNTAX     INTEGER {
                  eDesCbc (1),
                  eBlowfishCbc (3),
                  e3desCbc (5),
                  eCast128Cbc (6),
                  eAesCbc (7),
                  eNull (42)
            }
    MAX-ACCESS read-write
    STATUS     current
    DESCRIPTION
            "-- empty --"
    ::= { hmSetupVpnProposalsIkeEntry 2 }

-- {COLUMN} 1.3.6.1.4.1.248.32.18.2.19.4.11.1.3
hmSetupVpnProposalsIkeEntryIkeCryptKeylen OBJECT-TYPE
    SYNTAX     Integer32 (0..65535)
    MAX-ACCESS read-write
    STATUS     current
    DESCRIPTION
            "-- empty --"
    ::= { hmSetupVpnProposalsIkeEntry 3 }

-- {COLUMN} 1.3.6.1.4.1.248.32.18.2.19.4.11.1.4
hmSetupVpnProposalsIkeEntryIkeAuthAlg OBJECT-TYPE
    SYNTAX     INTEGER {
                  eMd5 (1),
                  eSha1 (2),
                  eSha2256 (4),
                  eSha2384 (5),
                  eSha2512 (6)
            }
    MAX-ACCESS read-write
    STATUS     current
    DESCRIPTION
            "-- empty --"
    ::= { hmSetupVpnProposalsIkeEntry 4 }

-- {COLUMN} 1.3.6.1.4.1.248.32.18.2.19.4.11.1.5
hmSetupVpnProposalsIkeEntryIkeAuthMode OBJECT-TYPE
    SYNTAX     INTEGER {
                  ePresharedKey (1),
                  eRsaSignature (3)
            }
    MAX-ACCESS read-write
    STATUS     current
    DESCRIPTION
            "-- empty --"
    ::= { hmSetupVpnProposalsIkeEntry 5 }

-- {COLUMN} 1.3.6.1.4.1.248.32.18.2.19.4.11.1.6
hmSetupVpnProposalsIkeEntryLifetimeSec OBJECT-TYPE
    SYNTAX     Integer32 (0..2147483647)
    MAX-ACCESS read-write
    STATUS     current
    DESCRIPTION
            "-- empty --"
    ::= { hmSetupVpnProposalsIkeEntry 6 }

-- {COLUMN} 1.3.6.1.4.1.248.32.18.2.19.4.11.1.7
hmSetupVpnProposalsIkeEntryLifetimeKb OBJECT-TYPE
    SYNTAX     Integer32 (0..2147483647)
    MAX-ACCESS read-write
    STATUS     current
    DESCRIPTION
            "-- empty --"
    ::= { hmSetupVpnProposalsIkeEntry 7 }

-- {TABLE} 1.3.6.1.4.1.248.32.18.2.19.4.12
hmSetupVpnProposalsIpsecTable OBJECT-TYPE
    SYNTAX     SEQUENCE OF HmSetupVpnProposalsIpsecEntry
    MAX-ACCESS not-accessible
    STATUS     current
    DESCRIPTION
            "-- empty --"
    ::= { hmSetupVpnProposals 12 }

-- {ROW} 1.3.6.1.4.1.248.32.18.2.19.4.12.1
hmSetupVpnProposalsIpsecEntry OBJECT-TYPE
    SYNTAX     HmSetupVpnProposalsIpsecEntry
    MAX-ACCESS not-accessible
    STATUS     current
    DESCRIPTION
            ""
    INDEX {
            hmSetupVpnProposalsIpsecEntryName
          }
    ::= { hmSetupVpnProposalsIpsecTable 1 }

HmSetupVpnProposalsIpsecEntry ::= SEQUENCE {
            hmSetupVpnProposalsIpsecEntryName DisplayString,
            hmSetupVpnProposalsIpsecEntryEncapsMode INTEGER,
            hmSetupVpnProposalsIpsecEntryEspCryptAlg INTEGER,
            hmSetupVpnProposalsIpsecEntryEspCryptKeylen Integer32,
            hmSetupVpnProposalsIpsecEntryEspAuthAlg INTEGER,
            hmSetupVpnProposalsIpsecEntryAhAuthAlg INTEGER,
            hmSetupVpnProposalsIpsecEntryIpcompAlg INTEGER,
            hmSetupVpnProposalsIpsecEntryLifetimeSec Integer32,
            hmSetupVpnProposalsIpsecEntryLifetimeKb Integer32
    }

-- {COLUMN} 1.3.6.1.4.1.248.32.18.2.19.4.12.1.1
hmSetupVpnProposalsIpsecEntryName OBJECT-TYPE
    SYNTAX     DisplayString (SIZE(0..17))
    MAX-ACCESS read-write
    STATUS     current
    DESCRIPTION
            "-- empty --"
    ::= { hmSetupVpnProposalsIpsecEntry 1 }

-- {COLUMN} 1.3.6.1.4.1.248.32.18.2.19.4.12.1.2
hmSetupVpnProposalsIpsecEntryEncapsMode OBJECT-TYPE
    SYNTAX     INTEGER {
                  eTunnel (1),
                  eTransport (2),
                  eMixedLcos4 (65001)
            }
    MAX-ACCESS read-write
    STATUS     current
    DESCRIPTION
            "-- empty --"
    ::= { hmSetupVpnProposalsIpsecEntry 2 }

-- {COLUMN} 1.3.6.1.4.1.248.32.18.2.19.4.12.1.3
hmSetupVpnProposalsIpsecEntryEspCryptAlg OBJECT-TYPE
    SYNTAX     INTEGER {
                  eNone (0),
                  eDesCbc (2),
                  e3desCbc (3),
                  eCast128Cbc (6),
                  eBlowfishCbc (7),
                  eNull (11),
                  eAesCbc (12)
            }
    MAX-ACCESS read-write
    STATUS     current
    DESCRIPTION
            "-- empty --"
    ::= { hmSetupVpnProposalsIpsecEntry 3 }

-- {COLUMN} 1.3.6.1.4.1.248.32.18.2.19.4.12.1.4
hmSetupVpnProposalsIpsecEntryEspCryptKeylen OBJECT-TYPE
    SYNTAX     Integer32 (0..65535)
    MAX-ACCESS read-write
    STATUS     current
    DESCRIPTION
            "-- empty --"
    ::= { hmSetupVpnProposalsIpsecEntry 4 }

-- {COLUMN} 1.3.6.1.4.1.248.32.18.2.19.4.12.1.5
hmSetupVpnProposalsIpsecEntryEspAuthAlg OBJECT-TYPE
    SYNTAX     INTEGER {
                  eNone (0),
                  eHmacMd5 (1),
                  eHmacSha1 (2),
                  eHmacSha2256 (5),
                  eHmacSha2384 (6),
                  eHmacSha2512 (7)
            }
    MAX-ACCESS read-write
    STATUS     current
    DESCRIPTION
            "-- empty --"
    ::= { hmSetupVpnProposalsIpsecEntry 5 }

-- {COLUMN} 1.3.6.1.4.1.248.32.18.2.19.4.12.1.6
hmSetupVpnProposalsIpsecEntryAhAuthAlg OBJECT-TYPE
    SYNTAX     INTEGER {
                  eNone (0),
                  eHmacMd5 (1),
                  eHmacSha1 (2),
                  eHmacSha2256 (5),
                  eHmacSha2384 (6),
                  eHmacSha2512 (7)
            }
    MAX-ACCESS read-write
    STATUS     current
    DESCRIPTION
            "-- empty --"
    ::= { hmSetupVpnProposalsIpsecEntry 6 }

-- {COLUMN} 1.3.6.1.4.1.248.32.18.2.19.4.12.1.7
hmSetupVpnProposalsIpsecEntryIpcompAlg OBJECT-TYPE
    SYNTAX     INTEGER {
                  eNone (0),
                  eDeflate (2),
                  eLzs (3)
            }
    MAX-ACCESS read-write
    STATUS     current
    DESCRIPTION
            "-- empty --"
    ::= { hmSetupVpnProposalsIpsecEntry 7 }

-- {COLUMN} 1.3.6.1.4.1.248.32.18.2.19.4.12.1.8
hmSetupVpnProposalsIpsecEntryLifetimeSec OBJECT-TYPE
    SYNTAX     Integer32 (0..2147483647)
    MAX-ACCESS read-write
    STATUS     current
    DESCRIPTION
            "-- empty --"
    ::= { hmSetupVpnProposalsIpsecEntry 8 }

-- {COLUMN} 1.3.6.1.4.1.248.32.18.2.19.4.12.1.9
hmSetupVpnProposalsIpsecEntryLifetimeKb OBJECT-TYPE
    SYNTAX     Integer32 (0..2147483647)
    MAX-ACCESS read-write
    STATUS     current
    DESCRIPTION
            "-- empty --"
    ::= { hmSetupVpnProposalsIpsecEntry 9 }

-- {NODE} 1.3.6.1.4.1.248.32.18.2.19.5
hmSetupVpnCertificatesAndKeys OBJECT IDENTIFIER ::= { hmSetupVpn 5 }

-- {TABLE} 1.3.6.1.4.1.248.32.18.2.19.5.3
hmSetupVpnCertificatesAndKeysIkeKeysTable OBJECT-TYPE
    SYNTAX     SEQUENCE OF HmSetupVpnCertificatesAndKeysIkeKeysEntry
    MAX-ACCESS not-accessible
    STATUS     current
    DESCRIPTION
            "-- empty --"
    ::= { hmSetupVpnCertificatesAndKeys 3 }

-- {ROW} 1.3.6.1.4.1.248.32.18.2.19.5.3.1
hmSetupVpnCertificatesAndKeysIkeKeysEntry OBJECT-TYPE
    SYNTAX     HmSetupVpnCertificatesAndKeysIkeKeysEntry
    MAX-ACCESS not-accessible
    STATUS     current
    DESCRIPTION
            ""
    INDEX {
            hmSetupVpnCertificatesAndKeysIkeKeysEntryName
          }
    ::= { hmSetupVpnCertificatesAndKeysIkeKeysTable 1 }

HmSetupVpnCertificatesAndKeysIkeKeysEntry ::= SEQUENCE {
            hmSetupVpnCertificatesAndKeysIkeKeysEntryName DisplayString,
            hmSetupVpnCertificatesAndKeysIkeKeysEntryRemoteIdentity DisplayString,
            hmSetupVpnCertificatesAndKeysIkeKeysEntrySharedSec DisplayString,
            hmSetupVpnCertificatesAndKeysIkeKeysEntrySharedSecFile DisplayString,
            hmSetupVpnCertificatesAndKeysIkeKeysEntryRemoteIdType INTEGER,
            hmSetupVpnCertificatesAndKeysIkeKeysEntryLocalIdType INTEGER,
            hmSetupVpnCertificatesAndKeysIkeKeysEntryLocalIdentity DisplayString
    }

-- {COLUMN} 1.3.6.1.4.1.248.32.18.2.19.5.3.1.1
hmSetupVpnCertificatesAndKeysIkeKeysEntryName OBJECT-TYPE
    SYNTAX     DisplayString (SIZE(0..16))
    MAX-ACCESS read-write
    STATUS     current
    DESCRIPTION
            "-- empty --"
    ::= { hmSetupVpnCertificatesAndKeysIkeKeysEntry 1 }

-- {COLUMN} 1.3.6.1.4.1.248.32.18.2.19.5.3.1.2
hmSetupVpnCertificatesAndKeysIkeKeysEntryRemoteIdentity OBJECT-TYPE
    SYNTAX     DisplayString (SIZE(0..254))
    MAX-ACCESS read-write
    STATUS     current
    DESCRIPTION
            "-- empty --"
    ::= { hmSetupVpnCertificatesAndKeysIkeKeysEntry 2 }

-- {COLUMN} 1.3.6.1.4.1.248.32.18.2.19.5.3.1.3
hmSetupVpnCertificatesAndKeysIkeKeysEntrySharedSec OBJECT-TYPE
    SYNTAX     DisplayString (SIZE(0..64))
    MAX-ACCESS read-write
    STATUS     current
    DESCRIPTION
            "-- empty --"
    ::= { hmSetupVpnCertificatesAndKeysIkeKeysEntry 3 }

-- {COLUMN} 1.3.6.1.4.1.248.32.18.2.19.5.3.1.4
hmSetupVpnCertificatesAndKeysIkeKeysEntrySharedSecFile OBJECT-TYPE
    SYNTAX     DisplayString (SIZE(0..20))
    MAX-ACCESS read-write
    STATUS     current
    DESCRIPTION
            "-- empty --"
    ::= { hmSetupVpnCertificatesAndKeysIkeKeysEntry 4 }

-- {COLUMN} 1.3.6.1.4.1.248.32.18.2.19.5.3.1.5
hmSetupVpnCertificatesAndKeysIkeKeysEntryRemoteIdType OBJECT-TYPE
    SYNTAX     INTEGER {
                  eNoIdentity (0),
                  eIpAddress (1),
                  eDomainName (2),
                  eEmailAddress (3),
                  eIpv6Address (5),
                  eDistinguishedName (9),
                  eKeyId (11)
            }
    MAX-ACCESS read-write
    STATUS     current
    DESCRIPTION
            "-- empty --"
    ::= { hmSetupVpnCertificatesAndKeysIkeKeysEntry 5 }

-- {COLUMN} 1.3.6.1.4.1.248.32.18.2.19.5.3.1.6
hmSetupVpnCertificatesAndKeysIkeKeysEntryLocalIdType OBJECT-TYPE
    SYNTAX     INTEGER {
                  eNoIdentity (0),
                  eIpAddress (1),
                  eDomainName (2),
                  eEmailAddress (3),
                  eIpv6Address (5),
                  eDistinguishedName (9),
                  eKeyId (11)
            }
    MAX-ACCESS read-write
    STATUS     current
    DESCRIPTION
            "-- empty --"
    ::= { hmSetupVpnCertificatesAndKeysIkeKeysEntry 6 }

-- {COLUMN} 1.3.6.1.4.1.248.32.18.2.19.5.3.1.7
hmSetupVpnCertificatesAndKeysIkeKeysEntryLocalIdentity OBJECT-TYPE
    SYNTAX     DisplayString (SIZE(0..254))
    MAX-ACCESS read-write
    STATUS     current
    DESCRIPTION
            "-- empty --"
    ::= { hmSetupVpnCertificatesAndKeysIkeKeysEntry 7 }

-- {TABLE} 1.3.6.1.4.1.248.32.18.2.19.7
hmSetupVpnLayerTable OBJECT-TYPE
    SYNTAX     SEQUENCE OF HmSetupVpnLayerEntry
    MAX-ACCESS not-accessible
    STATUS     current
    DESCRIPTION
            "-- empty --"
    ::= { hmSetupVpn 7 }

-- {ROW} 1.3.6.1.4.1.248.32.18.2.19.7.1
hmSetupVpnLayerEntry OBJECT-TYPE
    SYNTAX     HmSetupVpnLayerEntry
    MAX-ACCESS not-accessible
    STATUS     current
    DESCRIPTION
            ""
    INDEX {
            hmSetupVpnLayerEntryName
          }
    ::= { hmSetupVpnLayerTable 1 }

HmSetupVpnLayerEntry ::= SEQUENCE {
            hmSetupVpnLayerEntryName DisplayString,
            hmSetupVpnLayerEntryPfsGrp INTEGER,
            hmSetupVpnLayerEntryIkeGrp INTEGER,
            hmSetupVpnLayerEntryIkePropList DisplayString,
            hmSetupVpnLayerEntryIpsecPropList DisplayString,
            hmSetupVpnLayerEntryIkeKey DisplayString
    }

-- {COLUMN} 1.3.6.1.4.1.248.32.18.2.19.7.1.1
hmSetupVpnLayerEntryName OBJECT-TYPE
    SYNTAX     DisplayString (SIZE(0..16))
    MAX-ACCESS read-write
    STATUS     current
    DESCRIPTION
            "-- empty --"
    ::= { hmSetupVpnLayerEntry 1 }

-- {COLUMN} 1.3.6.1.4.1.248.32.18.2.19.7.1.3
hmSetupVpnLayerEntryPfsGrp OBJECT-TYPE
    SYNTAX     INTEGER {
                  e0 (0),
                  e1 (1),
                  e2 (2),
                  e5 (5),
                  e14 (14),
                  e15 (15),
                  e16 (16)
            }
    MAX-ACCESS read-write
    STATUS     current
    DESCRIPTION
            "-- empty --"
    ::= { hmSetupVpnLayerEntry 3 }

-- {COLUMN} 1.3.6.1.4.1.248.32.18.2.19.7.1.4
hmSetupVpnLayerEntryIkeGrp OBJECT-TYPE
    SYNTAX     INTEGER {
                  e1 (1),
                  e2 (2),
                  e5 (5),
                  e14 (14),
                  e15 (15),
                  e16 (16)
            }
    MAX-ACCESS read-write
    STATUS     current
    DESCRIPTION
            "-- empty --"
    ::= { hmSetupVpnLayerEntry 4 }

-- {COLUMN} 1.3.6.1.4.1.248.32.18.2.19.7.1.5
hmSetupVpnLayerEntryIkePropList OBJECT-TYPE
    SYNTAX     DisplayString (SIZE(0..17))
    MAX-ACCESS read-write
    STATUS     current
    DESCRIPTION
            "-- empty --"
    ::= { hmSetupVpnLayerEntry 5 }

-- {COLUMN} 1.3.6.1.4.1.248.32.18.2.19.7.1.6
hmSetupVpnLayerEntryIpsecPropList OBJECT-TYPE
    SYNTAX     DisplayString (SIZE(0..17))
    MAX-ACCESS read-write
    STATUS     current
    DESCRIPTION
            "-- empty --"
    ::= { hmSetupVpnLayerEntry 6 }

-- {COLUMN} 1.3.6.1.4.1.248.32.18.2.19.7.1.7
hmSetupVpnLayerEntryIkeKey OBJECT-TYPE
    SYNTAX     DisplayString (SIZE(0..16))
    MAX-ACCESS read-write
    STATUS     current
    DESCRIPTION
            "-- empty --"
    ::= { hmSetupVpnLayerEntry 7 }

-- {SCALAR} 1.3.6.1.4.1.248.32.18.2.19.8
hmSetupVpnOperating OBJECT-TYPE
    SYNTAX     INTEGER {
                  eNo (0),
                  eYes (1),
                  eExclusive (3)
            }
    MAX-ACCESS read-write
    STATUS     current
    DESCRIPTION
            "-- empty --"
    ::= { hmSetupVpn 8 }

-- {TABLE} 1.3.6.1.4.1.248.32.18.2.19.9
hmSetupVpnVpnPeersTable OBJECT-TYPE
    SYNTAX     SEQUENCE OF HmSetupVpnVpnPeersEntry
    MAX-ACCESS not-accessible
    STATUS     current
    DESCRIPTION
            "-- empty --"
    ::= { hmSetupVpn 9 }

-- {ROW} 1.3.6.1.4.1.248.32.18.2.19.9.1
hmSetupVpnVpnPeersEntry OBJECT-TYPE
    SYNTAX     HmSetupVpnVpnPeersEntry
    MAX-ACCESS not-accessible
    STATUS     current
    DESCRIPTION
            ""
    INDEX {
            hmSetupVpnVpnPeersEntryPeer
          }
    ::= { hmSetupVpnVpnPeersTable 1 }

HmSetupVpnVpnPeersEntry ::= SEQUENCE {
            hmSetupVpnVpnPeersEntryPeer DisplayString,
            hmSetupVpnVpnPeersEntryExtranetAddress IpAddress,
            hmSetupVpnVpnPeersEntryLayer DisplayString,
            hmSetupVpnVpnPeersEntryDynamic INTEGER,
            hmSetupVpnVpnPeersEntryShTime Integer32,
            hmSetupVpnVpnPeersEntryIkeExchange INTEGER,
            hmSetupVpnVpnPeersEntryRemoteGw DisplayString,
            hmSetupVpnVpnPeersEntryRuleCreation INTEGER,
            hmSetupVpnVpnPeersEntryDpdInactTimeout Integer32,
            hmSetupVpnVpnPeersEntryIkeCfg INTEGER,
            hmSetupVpnVpnPeersEntryXauth INTEGER,
            hmSetupVpnVpnPeersEntrySslEncaps INTEGER,
            hmSetupVpnVpnPeersEntryRtgTag Integer32,
            hmSetupVpnVpnPeersEntryOcspCheck INTEGER
    }

-- {COLUMN} 1.3.6.1.4.1.248.32.18.2.19.9.1.1
hmSetupVpnVpnPeersEntryPeer OBJECT-TYPE
    SYNTAX     DisplayString (SIZE(0..16))
    MAX-ACCESS read-write
    STATUS     current
    DESCRIPTION
            "-- empty --"
    ::= { hmSetupVpnVpnPeersEntry 1 }

-- {COLUMN} 1.3.6.1.4.1.248.32.18.2.19.9.1.2
hmSetupVpnVpnPeersEntryExtranetAddress OBJECT-TYPE
    SYNTAX     IpAddress
    MAX-ACCESS read-write
    STATUS     current
    DESCRIPTION
            "-- empty --"
    ::= { hmSetupVpnVpnPeersEntry 2 }

-- {COLUMN} 1.3.6.1.4.1.248.32.18.2.19.9.1.4
hmSetupVpnVpnPeersEntryLayer OBJECT-TYPE
    SYNTAX     DisplayString (SIZE(0..16))
    MAX-ACCESS read-write
    STATUS     current
    DESCRIPTION
            "-- empty --"
    ::= { hmSetupVpnVpnPeersEntry 4 }

-- {COLUMN} 1.3.6.1.4.1.248.32.18.2.19.9.1.5
hmSetupVpnVpnPeersEntryDynamic OBJECT-TYPE
    SYNTAX     INTEGER {
                  eNo (0),
                  eBChannel (1),
                  eIcmp (4),
                  eUdp (8)
            }
    MAX-ACCESS read-write
    STATUS     current
    DESCRIPTION
            "-- empty --"
    ::= { hmSetupVpnVpnPeersEntry 5 }

-- {COLUMN} 1.3.6.1.4.1.248.32.18.2.19.9.1.6
hmSetupVpnVpnPeersEntryShTime OBJECT-TYPE
    SYNTAX     Integer32 (0..65535)
    MAX-ACCESS read-write
    STATUS     current
    DESCRIPTION
            "-- empty --"
    ::= { hmSetupVpnVpnPeersEntry 6 }

-- {COLUMN} 1.3.6.1.4.1.248.32.18.2.19.9.1.7
hmSetupVpnVpnPeersEntryIkeExchange OBJECT-TYPE
    SYNTAX     INTEGER {
                  eMainMode (0),
                  eAggressiveMode (1)
            }
    MAX-ACCESS read-write
    STATUS     current
    DESCRIPTION
            "-- empty --"
    ::= { hmSetupVpnVpnPeersEntry 7 }

-- {COLUMN} 1.3.6.1.4.1.248.32.18.2.19.9.1.8
hmSetupVpnVpnPeersEntryRemoteGw OBJECT-TYPE
    SYNTAX     DisplayString (SIZE(0..63))
    MAX-ACCESS read-write
    STATUS     current
    DESCRIPTION
            "-- empty --"
    ::= { hmSetupVpnVpnPeersEntry 8 }

-- {COLUMN} 1.3.6.1.4.1.248.32.18.2.19.9.1.9
hmSetupVpnVpnPeersEntryRuleCreation OBJECT-TYPE
    SYNTAX     INTEGER {
                  eAuto (0),
                  eManually (1),
                  eOff (2)
            }
    MAX-ACCESS read-write
    STATUS     current
    DESCRIPTION
            "-- empty --"
    ::= { hmSetupVpnVpnPeersEntry 9 }

-- {COLUMN} 1.3.6.1.4.1.248.32.18.2.19.9.1.10
hmSetupVpnVpnPeersEntryDpdInactTimeout OBJECT-TYPE
    SYNTAX     Integer32 (0..2147483647)
    MAX-ACCESS read-write
    STATUS     current
    DESCRIPTION
            "-- empty --"
    ::= { hmSetupVpnVpnPeersEntry 10 }

-- {COLUMN} 1.3.6.1.4.1.248.32.18.2.19.9.1.11
hmSetupVpnVpnPeersEntryIkeCfg OBJECT-TYPE
    SYNTAX     INTEGER {
                  eOff (0),
                  eClient (1),
                  eServer (2)
            }
    MAX-ACCESS read-write
    STATUS     current
    DESCRIPTION
            "-- empty --"
    ::= { hmSetupVpnVpnPeersEntry 11 }

-- {COLUMN} 1.3.6.1.4.1.248.32.18.2.19.9.1.12
hmSetupVpnVpnPeersEntryXauth OBJECT-TYPE
    SYNTAX     INTEGER {
                  eOff (0),
                  eClient (1),
                  eServer (2)
            }
    MAX-ACCESS read-write
    STATUS     current
    DESCRIPTION
            "-- empty --"
    ::= { hmSetupVpnVpnPeersEntry 12 }

-- {COLUMN} 1.3.6.1.4.1.248.32.18.2.19.9.1.13
hmSetupVpnVpnPeersEntrySslEncaps OBJECT-TYPE
    SYNTAX     INTEGER {
                  eNo (0),
                  eYes (1)
            }
    MAX-ACCESS read-write
    STATUS     current
    DESCRIPTION
            "-- empty --"
    ::= { hmSetupVpnVpnPeersEntry 13 }

-- {COLUMN} 1.3.6.1.4.1.248.32.18.2.19.9.1.15
hmSetupVpnVpnPeersEntryRtgTag OBJECT-TYPE
    SYNTAX     Integer32 (0..65535)
    MAX-ACCESS read-write
    STATUS     current
    DESCRIPTION
            "-- empty --"
    ::= { hmSetupVpnVpnPeersEntry 15 }

-- {COLUMN} 1.3.6.1.4.1.248.32.18.2.19.9.1.16
hmSetupVpnVpnPeersEntryOcspCheck OBJECT-TYPE
    SYNTAX     INTEGER {
                  eNo (0),
                  eYes (1)
            }
    MAX-ACCESS read-write
    STATUS     current
    DESCRIPTION
            "-- empty --"
    ::= { hmSetupVpnVpnPeersEntry 16 }

-- {SCALAR} 1.3.6.1.4.1.248.32.18.2.19.10
hmSetupVpnAggrmodeProposalListDefault OBJECT-TYPE
    SYNTAX     DisplayString (SIZE(0..17))
    MAX-ACCESS read-write
    STATUS     current
    DESCRIPTION
            "-- empty --"
    ::= { hmSetupVpn 10 }

-- {SCALAR} 1.3.6.1.4.1.248.32.18.2.19.11
hmSetupVpnAggrmodeIkeGroupDefault OBJECT-TYPE
    SYNTAX     INTEGER {
                  e1 (1),
                  e2 (2),
                  e5 (5),
                  e14 (14),
                  e15 (15),
                  e16 (16)
            }
    MAX-ACCESS read-write
    STATUS     current
    DESCRIPTION
            "-- empty --"
    ::= { hmSetupVpn 11 }

-- {TABLE} 1.3.6.1.4.1.248.32.18.2.19.12
hmSetupVpnAdditionalGatewaysTable OBJECT-TYPE
    SYNTAX     SEQUENCE OF HmSetupVpnAdditionalGatewaysEntry
    MAX-ACCESS not-accessible
    STATUS     current
    DESCRIPTION
            "-- empty --"
    ::= { hmSetupVpn 12 }

-- {ROW} 1.3.6.1.4.1.248.32.18.2.19.12.1
hmSetupVpnAdditionalGatewaysEntry OBJECT-TYPE
    SYNTAX     HmSetupVpnAdditionalGatewaysEntry
    MAX-ACCESS not-accessible
    STATUS     current
    DESCRIPTION
            ""
    INDEX {
            hmSetupVpnAdditionalGatewaysEntryPeer
          }
    ::= { hmSetupVpnAdditionalGatewaysTable 1 }

HmSetupVpnAdditionalGatewaysEntry ::= SEQUENCE {
            hmSetupVpnAdditionalGatewaysEntryPeer DisplayString,
            hmSetupVpnAdditionalGatewaysEntryGateway1 DisplayString,
            hmSetupVpnAdditionalGatewaysEntryGateway2 DisplayString,
            hmSetupVpnAdditionalGatewaysEntryGateway3 DisplayString,
            hmSetupVpnAdditionalGatewaysEntryGateway4 DisplayString,
            hmSetupVpnAdditionalGatewaysEntryGateway5 DisplayString,
            hmSetupVpnAdditionalGatewaysEntryGateway6 DisplayString,
            hmSetupVpnAdditionalGatewaysEntryGateway7 DisplayString,
            hmSetupVpnAdditionalGatewaysEntryGateway8 DisplayString,
            hmSetupVpnAdditionalGatewaysEntryBeginWith INTEGER,
            hmSetupVpnAdditionalGatewaysEntryRtgTag1 Integer32,
            hmSetupVpnAdditionalGatewaysEntryRtgTag2 Integer32,
            hmSetupVpnAdditionalGatewaysEntryRtgTag3 Integer32,
            hmSetupVpnAdditionalGatewaysEntryRtgTag4 Integer32,
            hmSetupVpnAdditionalGatewaysEntryRtgTag5 Integer32,
            hmSetupVpnAdditionalGatewaysEntryRtgTag6 Integer32,
            hmSetupVpnAdditionalGatewaysEntryRtgTag7 Integer32,
            hmSetupVpnAdditionalGatewaysEntryRtgTag8 Integer32,
            hmSetupVpnAdditionalGatewaysEntryGateway9 DisplayString,
            hmSetupVpnAdditionalGatewaysEntryGateway10 DisplayString,
            hmSetupVpnAdditionalGatewaysEntryGateway11 DisplayString,
            hmSetupVpnAdditionalGatewaysEntryGateway12 DisplayString,
            hmSetupVpnAdditionalGatewaysEntryGateway13 DisplayString,
            hmSetupVpnAdditionalGatewaysEntryGateway14 DisplayString,
            hmSetupVpnAdditionalGatewaysEntryGateway15 DisplayString,
            hmSetupVpnAdditionalGatewaysEntryGateway16 DisplayString,
            hmSetupVpnAdditionalGatewaysEntryRtgTag9 Integer32,
            hmSetupVpnAdditionalGatewaysEntryRtgTag10 Integer32,
            hmSetupVpnAdditionalGatewaysEntryRtgTag11 Integer32,
            hmSetupVpnAdditionalGatewaysEntryRtgTag12 Integer32,
            hmSetupVpnAdditionalGatewaysEntryRtgTag13 Integer32,
            hmSetupVpnAdditionalGatewaysEntryRtgTag14 Integer32,
            hmSetupVpnAdditionalGatewaysEntryRtgTag15 Integer32,
            hmSetupVpnAdditionalGatewaysEntryRtgTag16 Integer32,
            hmSetupVpnAdditionalGatewaysEntryGateway17 DisplayString,
            hmSetupVpnAdditionalGatewaysEntryRtgTag17 Integer32,
            hmSetupVpnAdditionalGatewaysEntryGateway18 DisplayString,
            hmSetupVpnAdditionalGatewaysEntryRtgTag18 Integer32,
            hmSetupVpnAdditionalGatewaysEntryGateway19 DisplayString,
            hmSetupVpnAdditionalGatewaysEntryRtgTag19 Integer32,
            hmSetupVpnAdditionalGatewaysEntryGateway20 DisplayString,
            hmSetupVpnAdditionalGatewaysEntryRtgTag20 Integer32,
            hmSetupVpnAdditionalGatewaysEntryGateway21 DisplayString,
            hmSetupVpnAdditionalGatewaysEntryRtgTag21 Integer32,
            hmSetupVpnAdditionalGatewaysEntryGateway22 DisplayString,
            hmSetupVpnAdditionalGatewaysEntryRtgTag22 Integer32,
            hmSetupVpnAdditionalGatewaysEntryGateway23 DisplayString,
            hmSetupVpnAdditionalGatewaysEntryRtgTag23 Integer32,
            hmSetupVpnAdditionalGatewaysEntryGateway24 DisplayString,
            hmSetupVpnAdditionalGatewaysEntryRtgTag24 Integer32,
            hmSetupVpnAdditionalGatewaysEntryGateway25 DisplayString,
            hmSetupVpnAdditionalGatewaysEntryRtgTag25 Integer32,
            hmSetupVpnAdditionalGatewaysEntryGateway26 DisplayString,
            hmSetupVpnAdditionalGatewaysEntryRtgTag26 Integer32,
            hmSetupVpnAdditionalGatewaysEntryGateway27 DisplayString,
            hmSetupVpnAdditionalGatewaysEntryRtgTag27 Integer32,
            hmSetupVpnAdditionalGatewaysEntryGateway28 DisplayString,
            hmSetupVpnAdditionalGatewaysEntryRtgTag28 Integer32,
            hmSetupVpnAdditionalGatewaysEntryGateway29 DisplayString,
            hmSetupVpnAdditionalGatewaysEntryRtgTag29 Integer32,
            hmSetupVpnAdditionalGatewaysEntryGateway30 DisplayString,
            hmSetupVpnAdditionalGatewaysEntryRtgTag30 Integer32,
            hmSetupVpnAdditionalGatewaysEntryGateway31 DisplayString,
            hmSetupVpnAdditionalGatewaysEntryRtgTag31 Integer32,
            hmSetupVpnAdditionalGatewaysEntryGateway32 DisplayString,
            hmSetupVpnAdditionalGatewaysEntryRtgTag32 Integer32
    }

-- {COLUMN} 1.3.6.1.4.1.248.32.18.2.19.12.1.1
hmSetupVpnAdditionalGatewaysEntryPeer OBJECT-TYPE
    SYNTAX     DisplayString (SIZE(0..16))
    MAX-ACCESS read-write
    STATUS     current
    DESCRIPTION
            "-- empty --"
    ::= { hmSetupVpnAdditionalGatewaysEntry 1 }

-- {COLUMN} 1.3.6.1.4.1.248.32.18.2.19.12.1.2
hmSetupVpnAdditionalGatewaysEntryGateway1 OBJECT-TYPE
    SYNTAX     DisplayString (SIZE(0..64))
    MAX-ACCESS read-write
    STATUS     current
    DESCRIPTION
            "-- empty --"
    ::= { hmSetupVpnAdditionalGatewaysEntry 2 }

-- {COLUMN} 1.3.6.1.4.1.248.32.18.2.19.12.1.3
hmSetupVpnAdditionalGatewaysEntryGateway2 OBJECT-TYPE
    SYNTAX     DisplayString (SIZE(0..64))
    MAX-ACCESS read-write
    STATUS     current
    DESCRIPTION
            "-- empty --"
    ::= { hmSetupVpnAdditionalGatewaysEntry 3 }

-- {COLUMN} 1.3.6.1.4.1.248.32.18.2.19.12.1.4
hmSetupVpnAdditionalGatewaysEntryGateway3 OBJECT-TYPE
    SYNTAX     DisplayString (SIZE(0..64))
    MAX-ACCESS read-write
    STATUS     current
    DESCRIPTION
            "-- empty --"
    ::= { hmSetupVpnAdditionalGatewaysEntry 4 }

-- {COLUMN} 1.3.6.1.4.1.248.32.18.2.19.12.1.5
hmSetupVpnAdditionalGatewaysEntryGateway4 OBJECT-TYPE
    SYNTAX     DisplayString (SIZE(0..64))
    MAX-ACCESS read-write
    STATUS     current
    DESCRIPTION
            "-- empty --"
    ::= { hmSetupVpnAdditionalGatewaysEntry 5 }

-- {COLUMN} 1.3.6.1.4.1.248.32.18.2.19.12.1.6
hmSetupVpnAdditionalGatewaysEntryGateway5 OBJECT-TYPE
    SYNTAX     DisplayString (SIZE(0..64))
    MAX-ACCESS read-write
    STATUS     current
    DESCRIPTION
            "-- empty --"
    ::= { hmSetupVpnAdditionalGatewaysEntry 6 }

-- {COLUMN} 1.3.6.1.4.1.248.32.18.2.19.12.1.7
hmSetupVpnAdditionalGatewaysEntryGateway6 OBJECT-TYPE
    SYNTAX     DisplayString (SIZE(0..64))
    MAX-ACCESS read-write
    STATUS     current
    DESCRIPTION
            "-- empty --"
    ::= { hmSetupVpnAdditionalGatewaysEntry 7 }

-- {COLUMN} 1.3.6.1.4.1.248.32.18.2.19.12.1.8
hmSetupVpnAdditionalGatewaysEntryGateway7 OBJECT-TYPE
    SYNTAX     DisplayString (SIZE(0..64))
    MAX-ACCESS read-write
    STATUS     current
    DESCRIPTION
            "-- empty --"
    ::= { hmSetupVpnAdditionalGatewaysEntry 8 }

-- {COLUMN} 1.3.6.1.4.1.248.32.18.2.19.12.1.9
hmSetupVpnAdditionalGatewaysEntryGateway8 OBJECT-TYPE
    SYNTAX     DisplayString (SIZE(0..64))
    MAX-ACCESS read-write
    STATUS     current
    DESCRIPTION
            "-- empty --"
    ::= { hmSetupVpnAdditionalGatewaysEntry 9 }

-- {COLUMN} 1.3.6.1.4.1.248.32.18.2.19.12.1.10
hmSetupVpnAdditionalGatewaysEntryBeginWith OBJECT-TYPE
    SYNTAX     INTEGER {
                  eLastUsed (0),
                  eFirst (1),
                  eRandom (2)
            }
    MAX-ACCESS read-write
    STATUS     current
    DESCRIPTION
            "-- empty --"
    ::= { hmSetupVpnAdditionalGatewaysEntry 10 }

-- {COLUMN} 1.3.6.1.4.1.248.32.18.2.19.12.1.11
hmSetupVpnAdditionalGatewaysEntryRtgTag1 OBJECT-TYPE
    SYNTAX     Integer32 (0..65535)
    MAX-ACCESS read-write
    STATUS     current
    DESCRIPTION
            "-- empty --"
    ::= { hmSetupVpnAdditionalGatewaysEntry 11 }

-- {COLUMN} 1.3.6.1.4.1.248.32.18.2.19.12.1.12
hmSetupVpnAdditionalGatewaysEntryRtgTag2 OBJECT-TYPE
    SYNTAX     Integer32 (0..65535)
    MAX-ACCESS read-write
    STATUS     current
    DESCRIPTION
            "-- empty --"
    ::= { hmSetupVpnAdditionalGatewaysEntry 12 }

-- {COLUMN} 1.3.6.1.4.1.248.32.18.2.19.12.1.13
hmSetupVpnAdditionalGatewaysEntryRtgTag3 OBJECT-TYPE
    SYNTAX     Integer32 (0..65535)
    MAX-ACCESS read-write
    STATUS     current
    DESCRIPTION
            "-- empty --"
    ::= { hmSetupVpnAdditionalGatewaysEntry 13 }

-- {COLUMN} 1.3.6.1.4.1.248.32.18.2.19.12.1.14
hmSetupVpnAdditionalGatewaysEntryRtgTag4 OBJECT-TYPE
    SYNTAX     Integer32 (0..65535)
    MAX-ACCESS read-write
    STATUS     current
    DESCRIPTION
            "-- empty --"
    ::= { hmSetupVpnAdditionalGatewaysEntry 14 }

-- {COLUMN} 1.3.6.1.4.1.248.32.18.2.19.12.1.15
hmSetupVpnAdditionalGatewaysEntryRtgTag5 OBJECT-TYPE
    SYNTAX     Integer32 (0..65535)
    MAX-ACCESS read-write
    STATUS     current
    DESCRIPTION
            "-- empty --"
    ::= { hmSetupVpnAdditionalGatewaysEntry 15 }

-- {COLUMN} 1.3.6.1.4.1.248.32.18.2.19.12.1.16
hmSetupVpnAdditionalGatewaysEntryRtgTag6 OBJECT-TYPE
    SYNTAX     Integer32 (0..65535)
    MAX-ACCESS read-write
    STATUS     current
    DESCRIPTION
            "-- empty --"
    ::= { hmSetupVpnAdditionalGatewaysEntry 16 }

-- {COLUMN} 1.3.6.1.4.1.248.32.18.2.19.12.1.17
hmSetupVpnAdditionalGatewaysEntryRtgTag7 OBJECT-TYPE
    SYNTAX     Integer32 (0..65535)
    MAX-ACCESS read-write
    STATUS     current
    DESCRIPTION
            "-- empty --"
    ::= { hmSetupVpnAdditionalGatewaysEntry 17 }

-- {COLUMN} 1.3.6.1.4.1.248.32.18.2.19.12.1.18
hmSetupVpnAdditionalGatewaysEntryRtgTag8 OBJECT-TYPE
    SYNTAX     Integer32 (0..65535)
    MAX-ACCESS read-write
    STATUS     current
    DESCRIPTION
            "-- empty --"
    ::= { hmSetupVpnAdditionalGatewaysEntry 18 }

-- {COLUMN} 1.3.6.1.4.1.248.32.18.2.19.12.1.19
hmSetupVpnAdditionalGatewaysEntryGateway9 OBJECT-TYPE
    SYNTAX     DisplayString (SIZE(0..64))
    MAX-ACCESS read-write
    STATUS     current
    DESCRIPTION
            "-- empty --"
    ::= { hmSetupVpnAdditionalGatewaysEntry 19 }

-- {COLUMN} 1.3.6.1.4.1.248.32.18.2.19.12.1.20
hmSetupVpnAdditionalGatewaysEntryGateway10 OBJECT-TYPE
    SYNTAX     DisplayString (SIZE(0..64))
    MAX-ACCESS read-write
    STATUS     current
    DESCRIPTION
            "-- empty --"
    ::= { hmSetupVpnAdditionalGatewaysEntry 20 }

-- {COLUMN} 1.3.6.1.4.1.248.32.18.2.19.12.1.21
hmSetupVpnAdditionalGatewaysEntryGateway11 OBJECT-TYPE
    SYNTAX     DisplayString (SIZE(0..64))
    MAX-ACCESS read-write
    STATUS     current
    DESCRIPTION
            "-- empty --"
    ::= { hmSetupVpnAdditionalGatewaysEntry 21 }

-- {COLUMN} 1.3.6.1.4.1.248.32.18.2.19.12.1.22
hmSetupVpnAdditionalGatewaysEntryGateway12 OBJECT-TYPE
    SYNTAX     DisplayString (SIZE(0..64))
    MAX-ACCESS read-write
    STATUS     current
    DESCRIPTION
            "-- empty --"
    ::= { hmSetupVpnAdditionalGatewaysEntry 22 }

-- {COLUMN} 1.3.6.1.4.1.248.32.18.2.19.12.1.23
hmSetupVpnAdditionalGatewaysEntryGateway13 OBJECT-TYPE
    SYNTAX     DisplayString (SIZE(0..64))
    MAX-ACCESS read-write
    STATUS     current
    DESCRIPTION
            "-- empty --"
    ::= { hmSetupVpnAdditionalGatewaysEntry 23 }

-- {COLUMN} 1.3.6.1.4.1.248.32.18.2.19.12.1.24
hmSetupVpnAdditionalGatewaysEntryGateway14 OBJECT-TYPE
    SYNTAX     DisplayString (SIZE(0..64))
    MAX-ACCESS read-write
    STATUS     current
    DESCRIPTION
            "-- empty --"
    ::= { hmSetupVpnAdditionalGatewaysEntry 24 }

-- {COLUMN} 1.3.6.1.4.1.248.32.18.2.19.12.1.25
hmSetupVpnAdditionalGatewaysEntryGateway15 OBJECT-TYPE
    SYNTAX     DisplayString (SIZE(0..64))
    MAX-ACCESS read-write
    STATUS     current
    DESCRIPTION
            "-- empty --"
    ::= { hmSetupVpnAdditionalGatewaysEntry 25 }

-- {COLUMN} 1.3.6.1.4.1.248.32.18.2.19.12.1.26
hmSetupVpnAdditionalGatewaysEntryGateway16 OBJECT-TYPE
    SYNTAX     DisplayString (SIZE(0..64))
    MAX-ACCESS read-write
    STATUS     current
    DESCRIPTION
            "-- empty --"
    ::= { hmSetupVpnAdditionalGatewaysEntry 26 }

-- {COLUMN} 1.3.6.1.4.1.248.32.18.2.19.12.1.27
hmSetupVpnAdditionalGatewaysEntryRtgTag9 OBJECT-TYPE
    SYNTAX     Integer32 (0..65535)
    MAX-ACCESS read-write
    STATUS     current
    DESCRIPTION
            "-- empty --"
    ::= { hmSetupVpnAdditionalGatewaysEntry 27 }

-- {COLUMN} 1.3.6.1.4.1.248.32.18.2.19.12.1.28
hmSetupVpnAdditionalGatewaysEntryRtgTag10 OBJECT-TYPE
    SYNTAX     Integer32 (0..65535)
    MAX-ACCESS read-write
    STATUS     current
    DESCRIPTION
            "-- empty --"
    ::= { hmSetupVpnAdditionalGatewaysEntry 28 }

-- {COLUMN} 1.3.6.1.4.1.248.32.18.2.19.12.1.29
hmSetupVpnAdditionalGatewaysEntryRtgTag11 OBJECT-TYPE
    SYNTAX     Integer32 (0..65535)
    MAX-ACCESS read-write
    STATUS     current
    DESCRIPTION
            "-- empty --"
    ::= { hmSetupVpnAdditionalGatewaysEntry 29 }

-- {COLUMN} 1.3.6.1.4.1.248.32.18.2.19.12.1.30
hmSetupVpnAdditionalGatewaysEntryRtgTag12 OBJECT-TYPE
    SYNTAX     Integer32 (0..65535)
    MAX-ACCESS read-write
    STATUS     current
    DESCRIPTION
            "-- empty --"
    ::= { hmSetupVpnAdditionalGatewaysEntry 30 }

-- {COLUMN} 1.3.6.1.4.1.248.32.18.2.19.12.1.31
hmSetupVpnAdditionalGatewaysEntryRtgTag13 OBJECT-TYPE
    SYNTAX     Integer32 (0..65535)
    MAX-ACCESS read-write
    STATUS     current
    DESCRIPTION
            "-- empty --"
    ::= { hmSetupVpnAdditionalGatewaysEntry 31 }

-- {COLUMN} 1.3.6.1.4.1.248.32.18.2.19.12.1.32
hmSetupVpnAdditionalGatewaysEntryRtgTag14 OBJECT-TYPE
    SYNTAX     Integer32 (0..65535)
    MAX-ACCESS read-write
    STATUS     current
    DESCRIPTION
            "-- empty --"
    ::= { hmSetupVpnAdditionalGatewaysEntry 32 }

-- {COLUMN} 1.3.6.1.4.1.248.32.18.2.19.12.1.33
hmSetupVpnAdditionalGatewaysEntryRtgTag15 OBJECT-TYPE
    SYNTAX     Integer32 (0..65535)
    MAX-ACCESS read-write
    STATUS     current
    DESCRIPTION
            "-- empty --"
    ::= { hmSetupVpnAdditionalGatewaysEntry 33 }

-- {COLUMN} 1.3.6.1.4.1.248.32.18.2.19.12.1.34
hmSetupVpnAdditionalGatewaysEntryRtgTag16 OBJECT-TYPE
    SYNTAX     Integer32 (0..65535)
    MAX-ACCESS read-write
    STATUS     current
    DESCRIPTION
            "-- empty --"
    ::= { hmSetupVpnAdditionalGatewaysEntry 34 }

-- {COLUMN} 1.3.6.1.4.1.248.32.18.2.19.12.1.35
hmSetupVpnAdditionalGatewaysEntryGateway17 OBJECT-TYPE
    SYNTAX     DisplayString (SIZE(0..64))
    MAX-ACCESS read-write
    STATUS     current
    DESCRIPTION
            "-- empty --"
    ::= { hmSetupVpnAdditionalGatewaysEntry 35 }

-- {COLUMN} 1.3.6.1.4.1.248.32.18.2.19.12.1.36
hmSetupVpnAdditionalGatewaysEntryRtgTag17 OBJECT-TYPE
    SYNTAX     Integer32 (0..65535)
    MAX-ACCESS read-write
    STATUS     current
    DESCRIPTION
            "-- empty --"
    ::= { hmSetupVpnAdditionalGatewaysEntry 36 }

-- {COLUMN} 1.3.6.1.4.1.248.32.18.2.19.12.1.37
hmSetupVpnAdditionalGatewaysEntryGateway18 OBJECT-TYPE
    SYNTAX     DisplayString (SIZE(0..64))
    MAX-ACCESS read-write
    STATUS     current
    DESCRIPTION
            "-- empty --"
    ::= { hmSetupVpnAdditionalGatewaysEntry 37 }

-- {COLUMN} 1.3.6.1.4.1.248.32.18.2.19.12.1.38
hmSetupVpnAdditionalGatewaysEntryRtgTag18 OBJECT-TYPE
    SYNTAX     Integer32 (0..65535)
    MAX-ACCESS read-write
    STATUS     current
    DESCRIPTION
            "-- empty --"
    ::= { hmSetupVpnAdditionalGatewaysEntry 38 }

-- {COLUMN} 1.3.6.1.4.1.248.32.18.2.19.12.1.39
hmSetupVpnAdditionalGatewaysEntryGateway19 OBJECT-TYPE
    SYNTAX     DisplayString (SIZE(0..64))
    MAX-ACCESS read-write
    STATUS     current
    DESCRIPTION
            "-- empty --"
    ::= { hmSetupVpnAdditionalGatewaysEntry 39 }

-- {COLUMN} 1.3.6.1.4.1.248.32.18.2.19.12.1.40
hmSetupVpnAdditionalGatewaysEntryRtgTag19 OBJECT-TYPE
    SYNTAX     Integer32 (0..65535)
    MAX-ACCESS read-write
    STATUS     current
    DESCRIPTION
            "-- empty --"
    ::= { hmSetupVpnAdditionalGatewaysEntry 40 }

-- {COLUMN} 1.3.6.1.4.1.248.32.18.2.19.12.1.41
hmSetupVpnAdditionalGatewaysEntryGateway20 OBJECT-TYPE
    SYNTAX     DisplayString (SIZE(0..64))
    MAX-ACCESS read-write
    STATUS     current
    DESCRIPTION
            "-- empty --"
    ::= { hmSetupVpnAdditionalGatewaysEntry 41 }

-- {COLUMN} 1.3.6.1.4.1.248.32.18.2.19.12.1.42
hmSetupVpnAdditionalGatewaysEntryRtgTag20 OBJECT-TYPE
    SYNTAX     Integer32 (0..65535)
    MAX-ACCESS read-write
    STATUS     current
    DESCRIPTION
            "-- empty --"
    ::= { hmSetupVpnAdditionalGatewaysEntry 42 }

-- {COLUMN} 1.3.6.1.4.1.248.32.18.2.19.12.1.43
hmSetupVpnAdditionalGatewaysEntryGateway21 OBJECT-TYPE
    SYNTAX     DisplayString (SIZE(0..64))
    MAX-ACCESS read-write
    STATUS     current
    DESCRIPTION
            "-- empty --"
    ::= { hmSetupVpnAdditionalGatewaysEntry 43 }

-- {COLUMN} 1.3.6.1.4.1.248.32.18.2.19.12.1.44
hmSetupVpnAdditionalGatewaysEntryRtgTag21 OBJECT-TYPE
    SYNTAX     Integer32 (0..65535)
    MAX-ACCESS read-write
    STATUS     current
    DESCRIPTION
            "-- empty --"
    ::= { hmSetupVpnAdditionalGatewaysEntry 44 }

-- {COLUMN} 1.3.6.1.4.1.248.32.18.2.19.12.1.45
hmSetupVpnAdditionalGatewaysEntryGateway22 OBJECT-TYPE
    SYNTAX     DisplayString (SIZE(0..64))
    MAX-ACCESS read-write
    STATUS     current
    DESCRIPTION
            "-- empty --"
    ::= { hmSetupVpnAdditionalGatewaysEntry 45 }

-- {COLUMN} 1.3.6.1.4.1.248.32.18.2.19.12.1.46
hmSetupVpnAdditionalGatewaysEntryRtgTag22 OBJECT-TYPE
    SYNTAX     Integer32 (0..65535)
    MAX-ACCESS read-write
    STATUS     current
    DESCRIPTION
            "-- empty --"
    ::= { hmSetupVpnAdditionalGatewaysEntry 46 }

-- {COLUMN} 1.3.6.1.4.1.248.32.18.2.19.12.1.47
hmSetupVpnAdditionalGatewaysEntryGateway23 OBJECT-TYPE
    SYNTAX     DisplayString (SIZE(0..64))
    MAX-ACCESS read-write
    STATUS     current
    DESCRIPTION
            "-- empty --"
    ::= { hmSetupVpnAdditionalGatewaysEntry 47 }

-- {COLUMN} 1.3.6.1.4.1.248.32.18.2.19.12.1.48
hmSetupVpnAdditionalGatewaysEntryRtgTag23 OBJECT-TYPE
    SYNTAX     Integer32 (0..65535)
    MAX-ACCESS read-write
    STATUS     current
    DESCRIPTION
            "-- empty --"
    ::= { hmSetupVpnAdditionalGatewaysEntry 48 }

-- {COLUMN} 1.3.6.1.4.1.248.32.18.2.19.12.1.49
hmSetupVpnAdditionalGatewaysEntryGateway24 OBJECT-TYPE
    SYNTAX     DisplayString (SIZE(0..64))
    MAX-ACCESS read-write
    STATUS     current
    DESCRIPTION
            "-- empty --"
    ::= { hmSetupVpnAdditionalGatewaysEntry 49 }

-- {COLUMN} 1.3.6.1.4.1.248.32.18.2.19.12.1.50
hmSetupVpnAdditionalGatewaysEntryRtgTag24 OBJECT-TYPE
    SYNTAX     Integer32 (0..65535)
    MAX-ACCESS read-write
    STATUS     current
    DESCRIPTION
            "-- empty --"
    ::= { hmSetupVpnAdditionalGatewaysEntry 50 }

-- {COLUMN} 1.3.6.1.4.1.248.32.18.2.19.12.1.51
hmSetupVpnAdditionalGatewaysEntryGateway25 OBJECT-TYPE
    SYNTAX     DisplayString (SIZE(0..64))
    MAX-ACCESS read-write
    STATUS     current
    DESCRIPTION
            "-- empty --"
    ::= { hmSetupVpnAdditionalGatewaysEntry 51 }

-- {COLUMN} 1.3.6.1.4.1.248.32.18.2.19.12.1.52
hmSetupVpnAdditionalGatewaysEntryRtgTag25 OBJECT-TYPE
    SYNTAX     Integer32 (0..65535)
    MAX-ACCESS read-write
    STATUS     current
    DESCRIPTION
            "-- empty --"
    ::= { hmSetupVpnAdditionalGatewaysEntry 52 }

-- {COLUMN} 1.3.6.1.4.1.248.32.18.2.19.12.1.53
hmSetupVpnAdditionalGatewaysEntryGateway26 OBJECT-TYPE
    SYNTAX     DisplayString (SIZE(0..64))
    MAX-ACCESS read-write
    STATUS     current
    DESCRIPTION
            "-- empty --"
    ::= { hmSetupVpnAdditionalGatewaysEntry 53 }

-- {COLUMN} 1.3.6.1.4.1.248.32.18.2.19.12.1.54
hmSetupVpnAdditionalGatewaysEntryRtgTag26 OBJECT-TYPE
    SYNTAX     Integer32 (0..65535)
    MAX-ACCESS read-write
    STATUS     current
    DESCRIPTION
            "-- empty --"
    ::= { hmSetupVpnAdditionalGatewaysEntry 54 }

-- {COLUMN} 1.3.6.1.4.1.248.32.18.2.19.12.1.55
hmSetupVpnAdditionalGatewaysEntryGateway27 OBJECT-TYPE
    SYNTAX     DisplayString (SIZE(0..64))
    MAX-ACCESS read-write
    STATUS     current
    DESCRIPTION
            "-- empty --"
    ::= { hmSetupVpnAdditionalGatewaysEntry 55 }

-- {COLUMN} 1.3.6.1.4.1.248.32.18.2.19.12.1.56
hmSetupVpnAdditionalGatewaysEntryRtgTag27 OBJECT-TYPE
    SYNTAX     Integer32 (0..65535)
    MAX-ACCESS read-write
    STATUS     current
    DESCRIPTION
            "-- empty --"
    ::= { hmSetupVpnAdditionalGatewaysEntry 56 }

-- {COLUMN} 1.3.6.1.4.1.248.32.18.2.19.12.1.57
hmSetupVpnAdditionalGatewaysEntryGateway28 OBJECT-TYPE
    SYNTAX     DisplayString (SIZE(0..64))
    MAX-ACCESS read-write
    STATUS     current
    DESCRIPTION
            "-- empty --"
    ::= { hmSetupVpnAdditionalGatewaysEntry 57 }

-- {COLUMN} 1.3.6.1.4.1.248.32.18.2.19.12.1.58
hmSetupVpnAdditionalGatewaysEntryRtgTag28 OBJECT-TYPE
    SYNTAX     Integer32 (0..65535)
    MAX-ACCESS read-write
    STATUS     current
    DESCRIPTION
            "-- empty --"
    ::= { hmSetupVpnAdditionalGatewaysEntry 58 }

-- {COLUMN} 1.3.6.1.4.1.248.32.18.2.19.12.1.59
hmSetupVpnAdditionalGatewaysEntryGateway29 OBJECT-TYPE
    SYNTAX     DisplayString (SIZE(0..64))
    MAX-ACCESS read-write
    STATUS     current
    DESCRIPTION
            "-- empty --"
    ::= { hmSetupVpnAdditionalGatewaysEntry 59 }

-- {COLUMN} 1.3.6.1.4.1.248.32.18.2.19.12.1.60
hmSetupVpnAdditionalGatewaysEntryRtgTag29 OBJECT-TYPE
    SYNTAX     Integer32 (0..65535)
    MAX-ACCESS read-write
    STATUS     current
    DESCRIPTION
            "-- empty --"
    ::= { hmSetupVpnAdditionalGatewaysEntry 60 }

-- {COLUMN} 1.3.6.1.4.1.248.32.18.2.19.12.1.61
hmSetupVpnAdditionalGatewaysEntryGateway30 OBJECT-TYPE
    SYNTAX     DisplayString (SIZE(0..64))
    MAX-ACCESS read-write
    STATUS     current
    DESCRIPTION
            "-- empty --"
    ::= { hmSetupVpnAdditionalGatewaysEntry 61 }

-- {COLUMN} 1.3.6.1.4.1.248.32.18.2.19.12.1.62
hmSetupVpnAdditionalGatewaysEntryRtgTag30 OBJECT-TYPE
    SYNTAX     Integer32 (0..65535)
    MAX-ACCESS read-write
    STATUS     current
    DESCRIPTION
            "-- empty --"
    ::= { hmSetupVpnAdditionalGatewaysEntry 62 }

-- {COLUMN} 1.3.6.1.4.1.248.32.18.2.19.12.1.63
hmSetupVpnAdditionalGatewaysEntryGateway31 OBJECT-TYPE
    SYNTAX     DisplayString (SIZE(0..64))
    MAX-ACCESS read-write
    STATUS     current
    DESCRIPTION
            "-- empty --"
    ::= { hmSetupVpnAdditionalGatewaysEntry 63 }

-- {COLUMN} 1.3.6.1.4.1.248.32.18.2.19.12.1.64
hmSetupVpnAdditionalGatewaysEntryRtgTag31 OBJECT-TYPE
    SYNTAX     Integer32 (0..65535)
    MAX-ACCESS read-write
    STATUS     current
    DESCRIPTION
            "-- empty --"
    ::= { hmSetupVpnAdditionalGatewaysEntry 64 }

-- {COLUMN} 1.3.6.1.4.1.248.32.18.2.19.12.1.65
hmSetupVpnAdditionalGatewaysEntryGateway32 OBJECT-TYPE
    SYNTAX     DisplayString (SIZE(0..64))
    MAX-ACCESS read-write
    STATUS     current
    DESCRIPTION
            "-- empty --"
    ::= { hmSetupVpnAdditionalGatewaysEntry 65 }

-- {COLUMN} 1.3.6.1.4.1.248.32.18.2.19.12.1.66
hmSetupVpnAdditionalGatewaysEntryRtgTag32 OBJECT-TYPE
    SYNTAX     Integer32 (0..65535)
    MAX-ACCESS read-write
    STATUS     current
    DESCRIPTION
            "-- empty --"
    ::= { hmSetupVpnAdditionalGatewaysEntry 66 }

-- {SCALAR} 1.3.6.1.4.1.248.32.18.2.19.13
hmSetupVpnMainmodeProposalListDefault OBJECT-TYPE
    SYNTAX     DisplayString (SIZE(0..17))
    MAX-ACCESS read-write
    STATUS     current
    DESCRIPTION
            "-- empty --"
    ::= { hmSetupVpn 13 }

-- {SCALAR} 1.3.6.1.4.1.248.32.18.2.19.14
hmSetupVpnMainmodeIkeGroupDefault OBJECT-TYPE
    SYNTAX     INTEGER {
                  e1 (1),
                  e2 (2),
                  e5 (5),
                  e14 (14),
                  e15 (15),
                  e16 (16)
            }
    MAX-ACCESS read-write
    STATUS     current
    DESCRIPTION
            "-- empty --"
    ::= { hmSetupVpn 14 }

-- {SCALAR} 1.3.6.1.4.1.248.32.18.2.19.16
hmSetupVpnNatTOperating OBJECT-TYPE
    SYNTAX     INTEGER {
                  eNo (0),
                  eYes (1)
            }
    MAX-ACCESS read-write
    STATUS     current
    DESCRIPTION
            "-- empty --"
    ::= { hmSetupVpn 16 }

-- {SCALAR} 1.3.6.1.4.1.248.32.18.2.19.17
hmSetupVpnSimpleCertRasOperating OBJECT-TYPE
    SYNTAX     INTEGER {
                  eNo (0),
                  eYes (1)
            }
    MAX-ACCESS read-write
    STATUS     current
    DESCRIPTION
            "-- empty --"
    ::= { hmSetupVpn 17 }

-- {SCALAR} 1.3.6.1.4.1.248.32.18.2.19.19
hmSetupVpnQuickmodeProposalListDefault OBJECT-TYPE
    SYNTAX     DisplayString (SIZE(0..17))
    MAX-ACCESS read-write
    STATUS     current
    DESCRIPTION
            "-- empty --"
    ::= { hmSetupVpn 19 }

-- {SCALAR} 1.3.6.1.4.1.248.32.18.2.19.20
hmSetupVpnQuickmodePfsGroupDefault OBJECT-TYPE
    SYNTAX     INTEGER {
                  e0 (0),
                  e1 (1),
                  e2 (2),
                  e5 (5),
                  e14 (14),
                  e15 (15),
                  e16 (16)
            }
    MAX-ACCESS read-write
    STATUS     current
    DESCRIPTION
            "-- empty --"
    ::= { hmSetupVpn 20 }

-- {SCALAR} 1.3.6.1.4.1.248.32.18.2.19.21
hmSetupVpnQuickmodeShortholdTimeDefault OBJECT-TYPE
    SYNTAX     Integer32 (0..65535)
    MAX-ACCESS read-write
    STATUS     current
    DESCRIPTION
            "-- empty --"
    ::= { hmSetupVpn 21 }

-- {SCALAR} 1.3.6.1.4.1.248.32.18.2.19.22
hmSetupVpnAllowRemoteNetworkSelection OBJECT-TYPE
    SYNTAX     INTEGER {
                  eNo (0),
                  eYes (1)
            }
    MAX-ACCESS read-write
    STATUS     current
    DESCRIPTION
            "-- empty --"
    ::= { hmSetupVpn 22 }

-- {SCALAR} 1.3.6.1.4.1.248.32.18.2.19.23
hmSetupVpnEstablishSasCollectively OBJECT-TYPE
    SYNTAX     INTEGER {
                  eNo (0),
                  eYes (1),
                  eOnlyWithKeepalive (2)
            }
    MAX-ACCESS read-write
    STATUS     current
    DESCRIPTION
            "-- empty --"
    ::= { hmSetupVpn 23 }

-- {SCALAR} 1.3.6.1.4.1.248.32.18.2.19.24
hmSetupVpnMaxConcurrentConnections OBJECT-TYPE
    SYNTAX     Integer32 (0..2147483647)
    MAX-ACCESS read-write
    STATUS     current
    DESCRIPTION
            "-- empty --"
    ::= { hmSetupVpn 24 }

-- {SCALAR} 1.3.6.1.4.1.248.32.18.2.19.25
hmSetupVpnFlexibleIdComparison OBJECT-TYPE
    SYNTAX     INTEGER {
                  eNo (0),
                  eYes (1)
            }
    MAX-ACCESS read-write
    STATUS     current
    DESCRIPTION
            "-- empty --"
    ::= { hmSetupVpn 25 }

-- {SCALAR} 1.3.6.1.4.1.248.32.18.2.19.26
hmSetupVpnNatTPortForRekeying OBJECT-TYPE
    SYNTAX     INTEGER {
                  eNo (0),
                  eYes (1)
            }
    MAX-ACCESS read-write
    STATUS     current
    DESCRIPTION
            "-- empty --"
    ::= { hmSetupVpn 26 }

-- {SCALAR} 1.3.6.1.4.1.248.32.18.2.19.27
hmSetupVpnSslEncapsAllowed OBJECT-TYPE
    SYNTAX     INTEGER {
                  eNo (0),
                  eYes (1)
            }
    MAX-ACCESS read-write
    STATUS     current
    DESCRIPTION
            "-- empty --"
    ::= { hmSetupVpn 27 }

-- {SCALAR} 1.3.6.1.4.1.248.32.18.2.19.30
hmSetupVpnAntiReplayWindowSize OBJECT-TYPE
    SYNTAX     Integer32 (0..65535)
    MAX-ACCESS read-write
    STATUS     current
    DESCRIPTION
            "-- empty --"
    ::= { hmSetupVpn 30 }

-- {NODE} 1.3.6.1.4.1.248.32.18.2.19.64
hmSetupVpnOcspClient OBJECT IDENTIFIER ::= { hmSetupVpn 64 }

-- {SCALAR} 1.3.6.1.4.1.248.32.18.2.19.64.1
hmSetupVpnOcspClientActive OBJECT-TYPE
    SYNTAX     INTEGER {
                  eNo (0),
                  eYes (1)
            }
    MAX-ACCESS read-write
    STATUS     current
    DESCRIPTION
            "-- empty --"
    ::= { hmSetupVpnOcspClient 1 }

-- {NODE} 1.3.6.1.4.1.248.32.18.2.20
hmSetupLanBridge OBJECT IDENTIFIER ::= { hmSetup 20 }

-- {SCALAR} 1.3.6.1.4.1.248.32.18.2.20.1
hmSetupLanBridgeProtocolVersion OBJECT-TYPE
    SYNTAX     INTEGER {
                  eNo (0),
                  eYes (1)
            }
    MAX-ACCESS read-write
    STATUS     current
    DESCRIPTION
            "-- empty --"
    ::= { hmSetupLanBridge 1 }

-- {SCALAR} 1.3.6.1.4.1.248.32.18.2.20.2
hmSetupLanBridgeBridgePriority OBJECT-TYPE
    SYNTAX     Integer32 (0..65535)
    MAX-ACCESS read-write
    STATUS     current
    DESCRIPTION
            "-- empty --"
    ::= { hmSetupLanBridge 2 }

-- {TABLE} 1.3.6.1.4.1.248.32.18.2.20.4
hmSetupLanBridgeEncapsulationTableTable OBJECT-TYPE
    SYNTAX     SEQUENCE OF HmSetupLanBridgeEncapsulationTableEntry
    MAX-ACCESS not-accessible
    STATUS     current
    DESCRIPTION
            "-- empty --"
    ::= { hmSetupLanBridge 4 }

-- {ROW} 1.3.6.1.4.1.248.32.18.2.20.4.1
hmSetupLanBridgeEncapsulationTableEntry OBJECT-TYPE
    SYNTAX     HmSetupLanBridgeEncapsulationTableEntry
    MAX-ACCESS not-accessible
    STATUS     current
    DESCRIPTION
            ""
    INDEX {
            hmSetupLanBridgeEncapsulationTableEntryProtocol
          }
    ::= { hmSetupLanBridgeEncapsulationTableTable 1 }

HmSetupLanBridgeEncapsulationTableEntry ::= SEQUENCE {
            hmSetupLanBridgeEncapsulationTableEntryProtocol Integer32,
            hmSetupLanBridgeEncapsulationTableEntryEncapsulation INTEGER
    }

-- {COLUMN} 1.3.6.1.4.1.248.32.18.2.20.4.1.1
hmSetupLanBridgeEncapsulationTableEntryProtocol OBJECT-TYPE
    SYNTAX     Integer32 (0..65535)
    MAX-ACCESS read-write
    STATUS     current
    DESCRIPTION
            "-- empty --"
    ::= { hmSetupLanBridgeEncapsulationTableEntry 1 }

-- {COLUMN} 1.3.6.1.4.1.248.32.18.2.20.4.1.2
hmSetupLanBridgeEncapsulationTableEntryEncapsulation OBJECT-TYPE
    SYNTAX     INTEGER {
                  eEthIi (0),
                  eSnap (1)
            }
    MAX-ACCESS read-write
    STATUS     current
    DESCRIPTION
            "-- empty --"
    ::= { hmSetupLanBridgeEncapsulationTableEntry 2 }

-- {SCALAR} 1.3.6.1.4.1.248.32.18.2.20.5
hmSetupLanBridgeMaxAge OBJECT-TYPE
    SYNTAX     Integer32 (0..65535)
    MAX-ACCESS read-write
    STATUS     current
    DESCRIPTION
            "-- empty --"
    ::= { hmSetupLanBridge 5 }

-- {SCALAR} 1.3.6.1.4.1.248.32.18.2.20.6
hmSetupLanBridgeHelloTime OBJECT-TYPE
    SYNTAX     Integer32 (0..65535)
    MAX-ACCESS read-write
    STATUS     current
    DESCRIPTION
            "-- empty --"
    ::= { hmSetupLanBridge 6 }

-- {SCALAR} 1.3.6.1.4.1.248.32.18.2.20.7
hmSetupLanBridgeForwardDelay OBJECT-TYPE
    SYNTAX     Integer32 (0..65535)
    MAX-ACCESS read-write
    STATUS     current
    DESCRIPTION
            "-- empty --"
    ::= { hmSetupLanBridge 7 }

-- {SCALAR} 1.3.6.1.4.1.248.32.18.2.20.8
hmSetupLanBridgeIsolatedMode OBJECT-TYPE
    SYNTAX     INTEGER {
                  eNo (0),
                  eYes (1)
            }
    MAX-ACCESS read-write
    STATUS     current
    DESCRIPTION
            "-- empty --"
    ::= { hmSetupLanBridge 8 }

-- {TABLE} 1.3.6.1.4.1.248.32.18.2.20.10
hmSetupLanBridgeProtocolTableTable OBJECT-TYPE
    SYNTAX     SEQUENCE OF HmSetupLanBridgeProtocolTableEntry
    MAX-ACCESS not-accessible
    STATUS     current
    DESCRIPTION
            "-- empty --"
    ::= { hmSetupLanBridge 10 }

-- {ROW} 1.3.6.1.4.1.248.32.18.2.20.10.1
hmSetupLanBridgeProtocolTableEntry OBJECT-TYPE
    SYNTAX     HmSetupLanBridgeProtocolTableEntry
    MAX-ACCESS not-accessible
    STATUS     current
    DESCRIPTION
            ""
    INDEX {
            hmSetupLanBridgeProtocolTableEntryName
          }
    ::= { hmSetupLanBridgeProtocolTableTable 1 }

HmSetupLanBridgeProtocolTableEntry ::= SEQUENCE {
            hmSetupLanBridgeProtocolTableEntryName DisplayString,
            hmSetupLanBridgeProtocolTableEntryProtocol DisplayString,
            hmSetupLanBridgeProtocolTableEntrySubProtocol Integer32,
            hmSetupLanBridgeProtocolTableEntryPort Integer32,
            hmSetupLanBridgeProtocolTableEntryPortEnd Integer32,
            hmSetupLanBridgeProtocolTableEntryIfcList DisplayString,
            hmSetupLanBridgeProtocolTableEntryAction INTEGER,
            hmSetupLanBridgeProtocolTableEntryRedirectIpAddress IpAddress,
            hmSetupLanBridgeProtocolTableEntryDestMacAddr MacAddress,
            hmSetupLanBridgeProtocolTableEntryIpNetwork IpAddress,
            hmSetupLanBridgeProtocolTableEntryIpNetmask IpAddress,
            hmSetupLanBridgeProtocolTableEntryDhcpSrcMac INTEGER
    }

-- {COLUMN} 1.3.6.1.4.1.248.32.18.2.20.10.1.1
hmSetupLanBridgeProtocolTableEntryName OBJECT-TYPE
    SYNTAX     DisplayString (SIZE(0..15))
    MAX-ACCESS read-write
    STATUS     current
    DESCRIPTION
            "-- empty --"
    ::= { hmSetupLanBridgeProtocolTableEntry 1 }

-- {COLUMN} 1.3.6.1.4.1.248.32.18.2.20.10.1.2
hmSetupLanBridgeProtocolTableEntryProtocol OBJECT-TYPE
    SYNTAX     DisplayString (SIZE(0..4))
    MAX-ACCESS read-write
    STATUS     current
    DESCRIPTION
            "-- empty --"
    ::= { hmSetupLanBridgeProtocolTableEntry 2 }

-- {COLUMN} 1.3.6.1.4.1.248.32.18.2.20.10.1.3
hmSetupLanBridgeProtocolTableEntrySubProtocol OBJECT-TYPE
    SYNTAX     Integer32 (0..65535)
    MAX-ACCESS read-write
    STATUS     current
    DESCRIPTION
            "-- empty --"
    ::= { hmSetupLanBridgeProtocolTableEntry 3 }

-- {COLUMN} 1.3.6.1.4.1.248.32.18.2.20.10.1.4
hmSetupLanBridgeProtocolTableEntryPort OBJECT-TYPE
    SYNTAX     Integer32 (0..65535)
    MAX-ACCESS read-write
    STATUS     current
    DESCRIPTION
            "-- empty --"
    ::= { hmSetupLanBridgeProtocolTableEntry 4 }

-- {COLUMN} 1.3.6.1.4.1.248.32.18.2.20.10.1.5
hmSetupLanBridgeProtocolTableEntryPortEnd OBJECT-TYPE
    SYNTAX     Integer32 (0..65535)
    MAX-ACCESS read-write
    STATUS     current
    DESCRIPTION
            "-- empty --"
    ::= { hmSetupLanBridgeProtocolTableEntry 5 }

-- {COLUMN} 1.3.6.1.4.1.248.32.18.2.20.10.1.6
hmSetupLanBridgeProtocolTableEntryIfcList OBJECT-TYPE
    SYNTAX     DisplayString (SIZE(0..251))
    MAX-ACCESS read-write
    STATUS     current
    DESCRIPTION
            "-- empty --"
    ::= { hmSetupLanBridgeProtocolTableEntry 6 }

-- {COLUMN} 1.3.6.1.4.1.248.32.18.2.20.10.1.7
hmSetupLanBridgeProtocolTableEntryAction OBJECT-TYPE
    SYNTAX     INTEGER {
                  eDrop (0),
                  ePass (1),
                  eRedirect (2)
            }
    MAX-ACCESS read-write
    STATUS     current
    DESCRIPTION
            "-- empty --"
    ::= { hmSetupLanBridgeProtocolTableEntry 7 }

-- {COLUMN} 1.3.6.1.4.1.248.32.18.2.20.10.1.8
hmSetupLanBridgeProtocolTableEntryRedirectIpAddress OBJECT-TYPE
    SYNTAX     IpAddress
    MAX-ACCESS read-write
    STATUS     current
    DESCRIPTION
            "-- empty --"
    ::= { hmSetupLanBridgeProtocolTableEntry 8 }

-- {COLUMN} 1.3.6.1.4.1.248.32.18.2.20.10.1.9
hmSetupLanBridgeProtocolTableEntryDestMacAddr OBJECT-TYPE
    SYNTAX     MacAddress
    MAX-ACCESS read-write
    STATUS     current
    DESCRIPTION
            "-- empty --"
    ::= { hmSetupLanBridgeProtocolTableEntry 9 }

-- {COLUMN} 1.3.6.1.4.1.248.32.18.2.20.10.1.10
hmSetupLanBridgeProtocolTableEntryIpNetwork OBJECT-TYPE
    SYNTAX     IpAddress
    MAX-ACCESS read-write
    STATUS     current
    DESCRIPTION
            "-- empty --"
    ::= { hmSetupLanBridgeProtocolTableEntry 10 }

-- {COLUMN} 1.3.6.1.4.1.248.32.18.2.20.10.1.11
hmSetupLanBridgeProtocolTableEntryIpNetmask OBJECT-TYPE
    SYNTAX     IpAddress
    MAX-ACCESS read-write
    STATUS     current
    DESCRIPTION
            "-- empty --"
    ::= { hmSetupLanBridgeProtocolTableEntry 11 }

-- {COLUMN} 1.3.6.1.4.1.248.32.18.2.20.10.1.12
hmSetupLanBridgeProtocolTableEntryDhcpSrcMac OBJECT-TYPE
    SYNTAX     INTEGER {
                  eIrrelevant (0),
                  eNo (1),
                  eYes (2)
            }
    MAX-ACCESS read-write
    STATUS     current
    DESCRIPTION
            "-- empty --"
    ::= { hmSetupLanBridgeProtocolTableEntry 12 }

-- {TABLE} 1.3.6.1.4.1.248.32.18.2.20.11
hmSetupLanBridgePortDataTable OBJECT-TYPE
    SYNTAX     SEQUENCE OF HmSetupLanBridgePortDataEntry
    MAX-ACCESS not-accessible
    STATUS     current
    DESCRIPTION
            "-- empty --"
    ::= { hmSetupLanBridge 11 }

-- {ROW} 1.3.6.1.4.1.248.32.18.2.20.11.1
hmSetupLanBridgePortDataEntry OBJECT-TYPE
    SYNTAX     HmSetupLanBridgePortDataEntry
    MAX-ACCESS not-accessible
    STATUS     current
    DESCRIPTION
            ""
    INDEX {
            hmSetupLanBridgePortDataEntryPort
          }
    ::= { hmSetupLanBridgePortDataTable 1 }

HmSetupLanBridgePortDataEntry ::= SEQUENCE {
            hmSetupLanBridgePortDataEntryPort DisplayString,
            hmSetupLanBridgePortDataEntryActive INTEGER,
            hmSetupLanBridgePortDataEntryBridgeGroup INTEGER,
            hmSetupLanBridgePortDataEntryDhcpLimit Integer32,
            hmSetupLanBridgePortDataEntryPointToPointPort INTEGER,
            hmSetupLanBridgePortDataEntryPrivateMode INTEGER
    }

-- {COLUMN} 1.3.6.1.4.1.248.32.18.2.20.11.1.2
hmSetupLanBridgePortDataEntryPort OBJECT-TYPE
    SYNTAX     DisplayString (SIZE(0..18))
    MAX-ACCESS read-only
    STATUS     current
    DESCRIPTION
            "-- empty --"
    ::= { hmSetupLanBridgePortDataEntry 2 }

-- {COLUMN} 1.3.6.1.4.1.248.32.18.2.20.11.1.3
hmSetupLanBridgePortDataEntryActive OBJECT-TYPE
    SYNTAX     INTEGER {
                  eNo (0),
                  eYes (1)
            }
    MAX-ACCESS read-write
    STATUS     current
    DESCRIPTION
            "-- empty --"
    ::= { hmSetupLanBridgePortDataEntry 3 }

-- {COLUMN} 1.3.6.1.4.1.248.32.18.2.20.11.1.5
hmSetupLanBridgePortDataEntryBridgeGroup OBJECT-TYPE
    SYNTAX     INTEGER {
                  eBrg1 (0),
                  eBrg2 (1),
                  eBrg3 (2),
                  eBrg4 (3),
                  eBrg5 (4),
                  eBrg6 (5),
                  eBrg7 (6),
                  eBrg8 (7),
                  eNone (255)
            }
    MAX-ACCESS read-write
    STATUS     current
    DESCRIPTION
            "-- empty --"
    ::= { hmSetupLanBridgePortDataEntry 5 }

-- {COLUMN} 1.3.6.1.4.1.248.32.18.2.20.11.1.6
hmSetupLanBridgePortDataEntryDhcpLimit OBJECT-TYPE
    SYNTAX     Integer32 (0..255)
    MAX-ACCESS read-write
    STATUS     current
    DESCRIPTION
            "-- empty --"
    ::= { hmSetupLanBridgePortDataEntry 6 }

-- {COLUMN} 1.3.6.1.4.1.248.32.18.2.20.11.1.7
hmSetupLanBridgePortDataEntryPointToPointPort OBJECT-TYPE
    SYNTAX     INTEGER {
                  eAuto (0),
                  eForceTrue (1),
                  eForceFalse (2)
            }
    MAX-ACCESS read-write
    STATUS     current
    DESCRIPTION
            "-- empty --"
    ::= { hmSetupLanBridgePortDataEntry 7 }

-- {COLUMN} 1.3.6.1.4.1.248.32.18.2.20.11.1.9
hmSetupLanBridgePortDataEntryPrivateMode OBJECT-TYPE
    SYNTAX     INTEGER {
                  eNo (0),
                  eYes (1)
            }
    MAX-ACCESS read-write
    STATUS     current
    DESCRIPTION
            "-- empty --"
    ::= { hmSetupLanBridgePortDataEntry 9 }

-- {SCALAR} 1.3.6.1.4.1.248.32.18.2.20.12
hmSetupLanBridgeAgingTime OBJECT-TYPE
    SYNTAX     Integer32 (0..2147483647)
    MAX-ACCESS read-write
    STATUS     current
    DESCRIPTION
            "-- empty --"
    ::= { hmSetupLanBridge 12 }

-- {TABLE} 1.3.6.1.4.1.248.32.18.2.20.13
hmSetupLanBridgePriorityMappingTable OBJECT-TYPE
    SYNTAX     SEQUENCE OF HmSetupLanBridgePriorityMappingEntry
    MAX-ACCESS not-accessible
    STATUS     current
    DESCRIPTION
            "-- empty --"
    ::= { hmSetupLanBridge 13 }

-- {ROW} 1.3.6.1.4.1.248.32.18.2.20.13.1
hmSetupLanBridgePriorityMappingEntry OBJECT-TYPE
    SYNTAX     HmSetupLanBridgePriorityMappingEntry
    MAX-ACCESS not-accessible
    STATUS     current
    DESCRIPTION
            ""
    INDEX {
            hmSetupLanBridgePriorityMappingEntryName
          }
    ::= { hmSetupLanBridgePriorityMappingTable 1 }

HmSetupLanBridgePriorityMappingEntry ::= SEQUENCE {
            hmSetupLanBridgePriorityMappingEntryName DisplayString,
            hmSetupLanBridgePriorityMappingEntryDscpValue Integer32,
            hmSetupLanBridgePriorityMappingEntryPriority INTEGER
    }

-- {COLUMN} 1.3.6.1.4.1.248.32.18.2.20.13.1.1
hmSetupLanBridgePriorityMappingEntryName OBJECT-TYPE
    SYNTAX     DisplayString (SIZE(0..16))
    MAX-ACCESS read-write
    STATUS     current
    DESCRIPTION
            "-- empty --"
    ::= { hmSetupLanBridgePriorityMappingEntry 1 }

-- {COLUMN} 1.3.6.1.4.1.248.32.18.2.20.13.1.2
hmSetupLanBridgePriorityMappingEntryDscpValue OBJECT-TYPE
    SYNTAX     Integer32 (0..255)
    MAX-ACCESS read-write
    STATUS     current
    DESCRIPTION
            "-- empty --"
    ::= { hmSetupLanBridgePriorityMappingEntry 2 }

-- {COLUMN} 1.3.6.1.4.1.248.32.18.2.20.13.1.3
hmSetupLanBridgePriorityMappingEntryPriority OBJECT-TYPE
    SYNTAX     INTEGER {
                  eBestEffort (0),
                  eBackground (1),
                  eTwo (2),
                  eExcellentEffort (3),
                  eControlledLatency (4),
                  eVideo (5),
                  eVoice (6),
                  eNetworkControl (7)
            }
    MAX-ACCESS read-write
    STATUS     current
    DESCRIPTION
            "-- empty --"
    ::= { hmSetupLanBridgePriorityMappingEntry 3 }

-- {NODE} 1.3.6.1.4.1.248.32.18.2.20.20
hmSetupLanBridgeSpanningTree OBJECT IDENTIFIER ::= { hmSetupLanBridge 20 }

-- {SCALAR} 1.3.6.1.4.1.248.32.18.2.20.20.1
hmSetupLanBridgeSpanningTreeOperating OBJECT-TYPE
    SYNTAX     INTEGER {
                  eNo (0),
                  eYes (1)
            }
    MAX-ACCESS read-write
    STATUS     current
    DESCRIPTION
            "-- empty --"
    ::= { hmSetupLanBridgeSpanningTree 1 }

-- {SCALAR} 1.3.6.1.4.1.248.32.18.2.20.20.2
hmSetupLanBridgeSpanningTreeBridgePriority OBJECT-TYPE
    SYNTAX     Integer32 (0..65535)
    MAX-ACCESS read-write
    STATUS     current
    DESCRIPTION
            "-- empty --"
    ::= { hmSetupLanBridgeSpanningTree 2 }

-- {SCALAR} 1.3.6.1.4.1.248.32.18.2.20.20.5
hmSetupLanBridgeSpanningTreeMaxAge OBJECT-TYPE
    SYNTAX     Integer32 (0..65535)
    MAX-ACCESS read-write
    STATUS     current
    DESCRIPTION
            "-- empty --"
    ::= { hmSetupLanBridgeSpanningTree 5 }

-- {SCALAR} 1.3.6.1.4.1.248.32.18.2.20.20.6
hmSetupLanBridgeSpanningTreeHelloTime OBJECT-TYPE
    SYNTAX     Integer32 (0..65535)
    MAX-ACCESS read-write
    STATUS     current
    DESCRIPTION
            "-- empty --"
    ::= { hmSetupLanBridgeSpanningTree 6 }

-- {SCALAR} 1.3.6.1.4.1.248.32.18.2.20.20.7
hmSetupLanBridgeSpanningTreeForwardDelay OBJECT-TYPE
    SYNTAX     Integer32 (0..65535)
    MAX-ACCESS read-write
    STATUS     current
    DESCRIPTION
            "-- empty --"
    ::= { hmSetupLanBridgeSpanningTree 7 }

-- {TABLE} 1.3.6.1.4.1.248.32.18.2.20.20.11
hmSetupLanBridgeSpanningTreePortDataTable OBJECT-TYPE
    SYNTAX     SEQUENCE OF HmSetupLanBridgeSpanningTreePortDataEntry
    MAX-ACCESS not-accessible
    STATUS     current
    DESCRIPTION
            "-- empty --"
    ::= { hmSetupLanBridgeSpanningTree 11 }

-- {ROW} 1.3.6.1.4.1.248.32.18.2.20.20.11.1
hmSetupLanBridgeSpanningTreePortDataEntry OBJECT-TYPE
    SYNTAX     HmSetupLanBridgeSpanningTreePortDataEntry
    MAX-ACCESS not-accessible
    STATUS     current
    DESCRIPTION
            ""
    INDEX {
            hmSetupLanBridgeSpanningTreePortDataEntryPort
          }
    ::= { hmSetupLanBridgeSpanningTreePortDataTable 1 }

HmSetupLanBridgeSpanningTreePortDataEntry ::= SEQUENCE {
            hmSetupLanBridgeSpanningTreePortDataEntryPort DisplayString,
            hmSetupLanBridgeSpanningTreePortDataEntryPriority Integer32,
            hmSetupLanBridgeSpanningTreePortDataEntryEdgePort INTEGER,
            hmSetupLanBridgeSpanningTreePortDataEntryPathCostOverride Integer32
    }

-- {COLUMN} 1.3.6.1.4.1.248.32.18.2.20.20.11.1.2
hmSetupLanBridgeSpanningTreePortDataEntryPort OBJECT-TYPE
    SYNTAX     DisplayString (SIZE(0..18))
    MAX-ACCESS read-only
    STATUS     current
    DESCRIPTION
            "-- empty --"
    ::= { hmSetupLanBridgeSpanningTreePortDataEntry 2 }

-- {COLUMN} 1.3.6.1.4.1.248.32.18.2.20.20.11.1.4
hmSetupLanBridgeSpanningTreePortDataEntryPriority OBJECT-TYPE
    SYNTAX     Integer32 (0..255)
    MAX-ACCESS read-write
    STATUS     current
    DESCRIPTION
            "-- empty --"
    ::= { hmSetupLanBridgeSpanningTreePortDataEntry 4 }

-- {COLUMN} 1.3.6.1.4.1.248.32.18.2.20.20.11.1.6
hmSetupLanBridgeSpanningTreePortDataEntryEdgePort OBJECT-TYPE
    SYNTAX     INTEGER {
                  eNo (0),
                  eYes (1)
            }
    MAX-ACCESS read-write
    STATUS     current
    DESCRIPTION
            "-- empty --"
    ::= { hmSetupLanBridgeSpanningTreePortDataEntry 6 }

-- {COLUMN} 1.3.6.1.4.1.248.32.18.2.20.20.11.1.7
hmSetupLanBridgeSpanningTreePortDataEntryPathCostOverride OBJECT-TYPE
    SYNTAX     Integer32 (0..2147483647)
    MAX-ACCESS read-write
    STATUS     current
    DESCRIPTION
            "-- empty --"
    ::= { hmSetupLanBridgeSpanningTreePortDataEntry 7 }

-- {SCALAR} 1.3.6.1.4.1.248.32.18.2.20.20.12
hmSetupLanBridgeSpanningTreeProtocolVersion OBJECT-TYPE
    SYNTAX     INTEGER {
                  eClassic (0),
                  eRapid (1)
            }
    MAX-ACCESS read-write
    STATUS     current
    DESCRIPTION
            "-- empty --"
    ::= { hmSetupLanBridgeSpanningTree 12 }

-- {SCALAR} 1.3.6.1.4.1.248.32.18.2.20.20.13
hmSetupLanBridgeSpanningTreeTransmitHoldCount OBJECT-TYPE
    SYNTAX     Integer32 (0..255)
    MAX-ACCESS read-write
    STATUS     current
    DESCRIPTION
            "-- empty --"
    ::= { hmSetupLanBridgeSpanningTree 13 }

-- {SCALAR} 1.3.6.1.4.1.248.32.18.2.20.20.14
hmSetupLanBridgeSpanningTreePathCostComputation OBJECT-TYPE
    SYNTAX     INTEGER {
                  eClassic (0),
                  eRapid (1)
            }
    MAX-ACCESS read-write
    STATUS     current
    DESCRIPTION
            "-- empty --"
    ::= { hmSetupLanBridgeSpanningTree 14 }

-- {NODE} 1.3.6.1.4.1.248.32.18.2.20.30
hmSetupLanBridgeIgmpSnooping OBJECT IDENTIFIER ::= { hmSetupLanBridge 30 }

-- {SCALAR} 1.3.6.1.4.1.248.32.18.2.20.30.1
hmSetupLanBridgeIgmpSnoopingOperating OBJECT-TYPE
    SYNTAX     INTEGER {
                  eNo (0),
                  eYes (1),
                  eAuto (2)
            }
    MAX-ACCESS read-write
    STATUS     current
    DESCRIPTION
            "-- empty --"
    ::= { hmSetupLanBridgeIgmpSnooping 1 }

-- {TABLE} 1.3.6.1.4.1.248.32.18.2.20.30.2
hmSetupLanBridgeIgmpSnoopingPortSettingsTable OBJECT-TYPE
    SYNTAX     SEQUENCE OF HmSetupLanBridgeIgmpSnoopingPortSettingsEntry
    MAX-ACCESS not-accessible
    STATUS     current
    DESCRIPTION
            "-- empty --"
    ::= { hmSetupLanBridgeIgmpSnooping 2 }

-- {ROW} 1.3.6.1.4.1.248.32.18.2.20.30.2.1
hmSetupLanBridgeIgmpSnoopingPortSettingsEntry OBJECT-TYPE
    SYNTAX     HmSetupLanBridgeIgmpSnoopingPortSettingsEntry
    MAX-ACCESS not-accessible
    STATUS     current
    DESCRIPTION
            ""
    INDEX {
            hmSetupLanBridgeIgmpSnoopingPortSettingsEntryPort
          }
    ::= { hmSetupLanBridgeIgmpSnoopingPortSettingsTable 1 }

HmSetupLanBridgeIgmpSnoopingPortSettingsEntry ::= SEQUENCE {
            hmSetupLanBridgeIgmpSnoopingPortSettingsEntryPort DisplayString,
            hmSetupLanBridgeIgmpSnoopingPortSettingsEntryRouterPort INTEGER
    }

-- {COLUMN} 1.3.6.1.4.1.248.32.18.2.20.30.2.1.1
hmSetupLanBridgeIgmpSnoopingPortSettingsEntryPort OBJECT-TYPE
    SYNTAX     DisplayString (SIZE(0..18))
    MAX-ACCESS read-write
    STATUS     current
    DESCRIPTION
            "-- empty --"
    ::= { hmSetupLanBridgeIgmpSnoopingPortSettingsEntry 1 }

-- {COLUMN} 1.3.6.1.4.1.248.32.18.2.20.30.2.1.2
hmSetupLanBridgeIgmpSnoopingPortSettingsEntryRouterPort OBJECT-TYPE
    SYNTAX     INTEGER {
                  eNo (0),
                  eAuto (1),
                  eYes (2)
            }
    MAX-ACCESS read-write
    STATUS     current
    DESCRIPTION
            "-- empty --"
    ::= { hmSetupLanBridgeIgmpSnoopingPortSettingsEntry 2 }

-- {SCALAR} 1.3.6.1.4.1.248.32.18.2.20.30.3
hmSetupLanBridgeIgmpSnoopingUnregisteredDataPacketHandling OBJECT-TYPE
    SYNTAX     INTEGER {
                  eRouterPortsOnly (0),
                  eFlood (1),
                  eDiscard (2)
            }
    MAX-ACCESS read-write
    STATUS     current
    DESCRIPTION
            "-- empty --"
    ::= { hmSetupLanBridgeIgmpSnooping 3 }

-- {TABLE} 1.3.6.1.4.1.248.32.18.2.20.30.4
hmSetupLanBridgeIgmpSnoopingSimulatedQueriersTable OBJECT-TYPE
    SYNTAX     SEQUENCE OF HmSetupLanBridgeIgmpSnoopingSimulatedQueriersEntry
    MAX-ACCESS not-accessible
    STATUS     current
    DESCRIPTION
            "-- empty --"
    ::= { hmSetupLanBridgeIgmpSnooping 4 }

-- {ROW} 1.3.6.1.4.1.248.32.18.2.20.30.4.1
hmSetupLanBridgeIgmpSnoopingSimulatedQueriersEntry OBJECT-TYPE
    SYNTAX     HmSetupLanBridgeIgmpSnoopingSimulatedQueriersEntry
    MAX-ACCESS not-accessible
    STATUS     current
    DESCRIPTION
            ""
    INDEX {
            hmSetupLanBridgeIgmpSnoopingSimulatedQueriersEntryName
          }
    ::= { hmSetupLanBridgeIgmpSnoopingSimulatedQueriersTable 1 }

HmSetupLanBridgeIgmpSnoopingSimulatedQueriersEntry ::= SEQUENCE {
            hmSetupLanBridgeIgmpSnoopingSimulatedQueriersEntryName DisplayString,
            hmSetupLanBridgeIgmpSnoopingSimulatedQueriersEntryOperating INTEGER,
            hmSetupLanBridgeIgmpSnoopingSimulatedQueriersEntryBridgeGroup INTEGER,
            hmSetupLanBridgeIgmpSnoopingSimulatedQueriersEntryVlanId Integer32
    }

-- {COLUMN} 1.3.6.1.4.1.248.32.18.2.20.30.4.1.1
hmSetupLanBridgeIgmpSnoopingSimulatedQueriersEntryName OBJECT-TYPE
    SYNTAX     DisplayString (SIZE(0..8))
    MAX-ACCESS read-write
    STATUS     current
    DESCRIPTION
            "-- empty --"
    ::= { hmSetupLanBridgeIgmpSnoopingSimulatedQueriersEntry 1 }

-- {COLUMN} 1.3.6.1.4.1.248.32.18.2.20.30.4.1.2
hmSetupLanBridgeIgmpSnoopingSimulatedQueriersEntryOperating OBJECT-TYPE
    SYNTAX     INTEGER {
                  eNo (0),
                  eYes (1)
            }
    MAX-ACCESS read-write
    STATUS     current
    DESCRIPTION
            "-- empty --"
    ::= { hmSetupLanBridgeIgmpSnoopingSimulatedQueriersEntry 2 }

-- {COLUMN} 1.3.6.1.4.1.248.32.18.2.20.30.4.1.3
hmSetupLanBridgeIgmpSnoopingSimulatedQueriersEntryBridgeGroup OBJECT-TYPE
    SYNTAX     INTEGER {
                  eBrg1 (0),
                  eBrg2 (1),
                  eBrg3 (2),
                  eBrg4 (3),
                  eBrg5 (4),
                  eBrg6 (5),
                  eBrg7 (6),
                  eBrg8 (7),
                  eNone (255)
            }
    MAX-ACCESS read-write
    STATUS     current
    DESCRIPTION
            "-- empty --"
    ::= { hmSetupLanBridgeIgmpSnoopingSimulatedQueriersEntry 3 }

-- {COLUMN} 1.3.6.1.4.1.248.32.18.2.20.30.4.1.4
hmSetupLanBridgeIgmpSnoopingSimulatedQueriersEntryVlanId OBJECT-TYPE
    SYNTAX     Integer32 (0..65535)
    MAX-ACCESS read-write
    STATUS     current
    DESCRIPTION
            "-- empty --"
    ::= { hmSetupLanBridgeIgmpSnoopingSimulatedQueriersEntry 4 }

-- {SCALAR} 1.3.6.1.4.1.248.32.18.2.20.30.5
hmSetupLanBridgeIgmpSnoopingQueryInterval OBJECT-TYPE
    SYNTAX     Integer32 (0..2147483647)
    MAX-ACCESS read-write
    STATUS     current
    DESCRIPTION
            "-- empty --"
    ::= { hmSetupLanBridgeIgmpSnooping 5 }

-- {SCALAR} 1.3.6.1.4.1.248.32.18.2.20.30.6
hmSetupLanBridgeIgmpSnoopingQueryResponseInterval OBJECT-TYPE
    SYNTAX     Integer32 (0..2147483647)
    MAX-ACCESS read-write
    STATUS     current
    DESCRIPTION
            "-- empty --"
    ::= { hmSetupLanBridgeIgmpSnooping 6 }

-- {SCALAR} 1.3.6.1.4.1.248.32.18.2.20.30.7
hmSetupLanBridgeIgmpSnoopingRobustness OBJECT-TYPE
    SYNTAX     Integer32 (0..2147483647)
    MAX-ACCESS read-write
    STATUS     current
    DESCRIPTION
            "-- empty --"
    ::= { hmSetupLanBridgeIgmpSnooping 7 }

-- {TABLE} 1.3.6.1.4.1.248.32.18.2.20.30.8
hmSetupLanBridgeIgmpSnoopingStaticMembersTable OBJECT-TYPE
    SYNTAX     SEQUENCE OF HmSetupLanBridgeIgmpSnoopingStaticMembersEntry
    MAX-ACCESS not-accessible
    STATUS     current
    DESCRIPTION
            "-- empty --"
    ::= { hmSetupLanBridgeIgmpSnooping 8 }

-- {ROW} 1.3.6.1.4.1.248.32.18.2.20.30.8.1
hmSetupLanBridgeIgmpSnoopingStaticMembersEntry OBJECT-TYPE
    SYNTAX     HmSetupLanBridgeIgmpSnoopingStaticMembersEntry
    MAX-ACCESS not-accessible
    STATUS     current
    DESCRIPTION
            ""
    INDEX {
            hmSetupLanBridgeIgmpSnoopingStaticMembersEntryAddress,
            hmSetupLanBridgeIgmpSnoopingStaticMembersEntryVlanId
          }
    ::= { hmSetupLanBridgeIgmpSnoopingStaticMembersTable 1 }

HmSetupLanBridgeIgmpSnoopingStaticMembersEntry ::= SEQUENCE {
            hmSetupLanBridgeIgmpSnoopingStaticMembersEntryAddress IpAddress,
            hmSetupLanBridgeIgmpSnoopingStaticMembersEntryStaticMembers DisplayString,
            hmSetupLanBridgeIgmpSnoopingStaticMembersEntryVlanId Integer32,
            hmSetupLanBridgeIgmpSnoopingStaticMembersEntryAllowLearning INTEGER
    }

-- {COLUMN} 1.3.6.1.4.1.248.32.18.2.20.30.8.1.1
hmSetupLanBridgeIgmpSnoopingStaticMembersEntryAddress OBJECT-TYPE
    SYNTAX     IpAddress
    MAX-ACCESS read-write
    STATUS     current
    DESCRIPTION
            "-- empty --"
    ::= { hmSetupLanBridgeIgmpSnoopingStaticMembersEntry 1 }

-- {COLUMN} 1.3.6.1.4.1.248.32.18.2.20.30.8.1.2
hmSetupLanBridgeIgmpSnoopingStaticMembersEntryStaticMembers OBJECT-TYPE
    SYNTAX     DisplayString (SIZE(0..251))
    MAX-ACCESS read-write
    STATUS     current
    DESCRIPTION
            "-- empty --"
    ::= { hmSetupLanBridgeIgmpSnoopingStaticMembersEntry 2 }

-- {COLUMN} 1.3.6.1.4.1.248.32.18.2.20.30.8.1.3
hmSetupLanBridgeIgmpSnoopingStaticMembersEntryVlanId OBJECT-TYPE
    SYNTAX     Integer32 (0..65535)
    MAX-ACCESS read-write
    STATUS     current
    DESCRIPTION
            "-- empty --"
    ::= { hmSetupLanBridgeIgmpSnoopingStaticMembersEntry 3 }

-- {COLUMN} 1.3.6.1.4.1.248.32.18.2.20.30.8.1.4
hmSetupLanBridgeIgmpSnoopingStaticMembersEntryAllowLearning OBJECT-TYPE
    SYNTAX     INTEGER {
                  eYes (0),
                  eNo (1)
            }
    MAX-ACCESS read-write
    STATUS     current
    DESCRIPTION
            "-- empty --"
    ::= { hmSetupLanBridgeIgmpSnoopingStaticMembersEntry 4 }

-- {SCALAR} 1.3.6.1.4.1.248.32.18.2.20.30.9
hmSetupLanBridgeIgmpSnoopingAdvertiseInterval OBJECT-TYPE
    SYNTAX     Integer32 (0..255)
    MAX-ACCESS read-write
    STATUS     current
    DESCRIPTION
            "-- empty --"
    ::= { hmSetupLanBridgeIgmpSnooping 9 }

-- {TABLE} 1.3.6.1.4.1.248.32.18.2.20.40
hmSetupLanBridgeDhcpSnoopingTable OBJECT-TYPE
    SYNTAX     SEQUENCE OF HmSetupLanBridgeDhcpSnoopingEntry
    MAX-ACCESS not-accessible
    STATUS     current
    DESCRIPTION
            "-- empty --"
    ::= { hmSetupLanBridge 40 }

-- {ROW} 1.3.6.1.4.1.248.32.18.2.20.40.1
hmSetupLanBridgeDhcpSnoopingEntry OBJECT-TYPE
    SYNTAX     HmSetupLanBridgeDhcpSnoopingEntry
    MAX-ACCESS not-accessible
    STATUS     current
    DESCRIPTION
            ""
    INDEX {
            hmSetupLanBridgeDhcpSnoopingEntryPort
          }
    ::= { hmSetupLanBridgeDhcpSnoopingTable 1 }

HmSetupLanBridgeDhcpSnoopingEntry ::= SEQUENCE {
            hmSetupLanBridgeDhcpSnoopingEntryPort DisplayString,
            hmSetupLanBridgeDhcpSnoopingEntryAddAgentInfo INTEGER,
            hmSetupLanBridgeDhcpSnoopingEntryTreatExistingAgentInfo INTEGER,
            hmSetupLanBridgeDhcpSnoopingEntryRemoteId DisplayString,
            hmSetupLanBridgeDhcpSnoopingEntryCircuitId DisplayString
    }

-- {COLUMN} 1.3.6.1.4.1.248.32.18.2.20.40.1.1
hmSetupLanBridgeDhcpSnoopingEntryPort OBJECT-TYPE
    SYNTAX     DisplayString (SIZE(0..18))
    MAX-ACCESS read-only
    STATUS     current
    DESCRIPTION
            "-- empty --"
    ::= { hmSetupLanBridgeDhcpSnoopingEntry 1 }

-- {COLUMN} 1.3.6.1.4.1.248.32.18.2.20.40.1.2
hmSetupLanBridgeDhcpSnoopingEntryAddAgentInfo OBJECT-TYPE
    SYNTAX     INTEGER {
                  eNo (0),
                  eYes (1)
            }
    MAX-ACCESS read-write
    STATUS     current
    DESCRIPTION
            "-- empty --"
    ::= { hmSetupLanBridgeDhcpSnoopingEntry 2 }

-- {COLUMN} 1.3.6.1.4.1.248.32.18.2.20.40.1.3
hmSetupLanBridgeDhcpSnoopingEntryTreatExistingAgentInfo OBJECT-TYPE
    SYNTAX     INTEGER {
                  eKeep (0),
                  eReplace (1),
                  eDiscard (2)
            }
    MAX-ACCESS read-write
    STATUS     current
    DESCRIPTION
            "-- empty --"
    ::= { hmSetupLanBridgeDhcpSnoopingEntry 3 }

-- {COLUMN} 1.3.6.1.4.1.248.32.18.2.20.40.1.4
hmSetupLanBridgeDhcpSnoopingEntryRemoteId OBJECT-TYPE
    SYNTAX     DisplayString (SIZE(0..30))
    MAX-ACCESS read-write
    STATUS     current
    DESCRIPTION
            "-- empty --"
    ::= { hmSetupLanBridgeDhcpSnoopingEntry 4 }

-- {COLUMN} 1.3.6.1.4.1.248.32.18.2.20.40.1.5
hmSetupLanBridgeDhcpSnoopingEntryCircuitId OBJECT-TYPE
    SYNTAX     DisplayString (SIZE(0..30))
    MAX-ACCESS read-write
    STATUS     current
    DESCRIPTION
            "-- empty --"
    ::= { hmSetupLanBridgeDhcpSnoopingEntry 5 }

-- {TABLE} 1.3.6.1.4.1.248.32.18.2.20.41
hmSetupLanBridgeDhcpv6SnoopingTable OBJECT-TYPE
    SYNTAX     SEQUENCE OF HmSetupLanBridgeDhcpv6SnoopingEntry
    MAX-ACCESS not-accessible
    STATUS     current
    DESCRIPTION
            "-- empty --"
    ::= { hmSetupLanBridge 41 }

-- {ROW} 1.3.6.1.4.1.248.32.18.2.20.41.1
hmSetupLanBridgeDhcpv6SnoopingEntry OBJECT-TYPE
    SYNTAX     HmSetupLanBridgeDhcpv6SnoopingEntry
    MAX-ACCESS not-accessible
    STATUS     current
    DESCRIPTION
            ""
    INDEX {
            hmSetupLanBridgeDhcpv6SnoopingEntryPort
          }
    ::= { hmSetupLanBridgeDhcpv6SnoopingTable 1 }

HmSetupLanBridgeDhcpv6SnoopingEntry ::= SEQUENCE {
            hmSetupLanBridgeDhcpv6SnoopingEntryPort DisplayString,
            hmSetupLanBridgeDhcpv6SnoopingEntryOrientation INTEGER,
            hmSetupLanBridgeDhcpv6SnoopingEntryType INTEGER,
            hmSetupLanBridgeDhcpv6SnoopingEntryRemoteId DisplayString,
            hmSetupLanBridgeDhcpv6SnoopingEntryInterfaceId DisplayString,
            hmSetupLanBridgeDhcpv6SnoopingEntryServerAddress DisplayString
    }

-- {COLUMN} 1.3.6.1.4.1.248.32.18.2.20.41.1.1
hmSetupLanBridgeDhcpv6SnoopingEntryPort OBJECT-TYPE
    SYNTAX     DisplayString (SIZE(0..18))
    MAX-ACCESS read-only
    STATUS     current
    DESCRIPTION
            "-- empty --"
    ::= { hmSetupLanBridgeDhcpv6SnoopingEntry 1 }

-- {COLUMN} 1.3.6.1.4.1.248.32.18.2.20.41.1.2
hmSetupLanBridgeDhcpv6SnoopingEntryOrientation OBJECT-TYPE
    SYNTAX     INTEGER {
                  eNetworkFacing (0),
                  eClientFacing (1)
            }
    MAX-ACCESS read-write
    STATUS     current
    DESCRIPTION
            "-- empty --"
    ::= { hmSetupLanBridgeDhcpv6SnoopingEntry 2 }

-- {COLUMN} 1.3.6.1.4.1.248.32.18.2.20.41.1.3
hmSetupLanBridgeDhcpv6SnoopingEntryType OBJECT-TYPE
    SYNTAX     INTEGER {
                  eTrusted (0),
                  eUntrusted (1)
            }
    MAX-ACCESS read-write
    STATUS     current
    DESCRIPTION
            "-- empty --"
    ::= { hmSetupLanBridgeDhcpv6SnoopingEntry 3 }

-- {COLUMN} 1.3.6.1.4.1.248.32.18.2.20.41.1.4
hmSetupLanBridgeDhcpv6SnoopingEntryRemoteId OBJECT-TYPE
    SYNTAX     DisplayString (SIZE(0..30))
    MAX-ACCESS read-write
    STATUS     current
    DESCRIPTION
            "-- empty --"
    ::= { hmSetupLanBridgeDhcpv6SnoopingEntry 4 }

-- {COLUMN} 1.3.6.1.4.1.248.32.18.2.20.41.1.5
hmSetupLanBridgeDhcpv6SnoopingEntryInterfaceId OBJECT-TYPE
    SYNTAX     DisplayString (SIZE(0..30))
    MAX-ACCESS read-write
    STATUS     current
    DESCRIPTION
            "-- empty --"
    ::= { hmSetupLanBridgeDhcpv6SnoopingEntry 5 }

-- {COLUMN} 1.3.6.1.4.1.248.32.18.2.20.41.1.6
hmSetupLanBridgeDhcpv6SnoopingEntryServerAddress OBJECT-TYPE
    SYNTAX     DisplayString (SIZE(0..39))
    MAX-ACCESS read-write
    STATUS     current
    DESCRIPTION
            "-- empty --"
    ::= { hmSetupLanBridgeDhcpv6SnoopingEntry 6 }

-- {TABLE} 1.3.6.1.4.1.248.32.18.2.20.42
hmSetupLanBridgeRaSnoopingTable OBJECT-TYPE
    SYNTAX     SEQUENCE OF HmSetupLanBridgeRaSnoopingEntry
    MAX-ACCESS not-accessible
    STATUS     current
    DESCRIPTION
            "-- empty --"
    ::= { hmSetupLanBridge 42 }

-- {ROW} 1.3.6.1.4.1.248.32.18.2.20.42.1
hmSetupLanBridgeRaSnoopingEntry OBJECT-TYPE
    SYNTAX     HmSetupLanBridgeRaSnoopingEntry
    MAX-ACCESS not-accessible
    STATUS     current
    DESCRIPTION
            ""
    INDEX {
            hmSetupLanBridgeRaSnoopingEntryPort
          }
    ::= { hmSetupLanBridgeRaSnoopingTable 1 }

HmSetupLanBridgeRaSnoopingEntry ::= SEQUENCE {
            hmSetupLanBridgeRaSnoopingEntryPort DisplayString,
            hmSetupLanBridgeRaSnoopingEntryType INTEGER,
            hmSetupLanBridgeRaSnoopingEntryRouterAddress DisplayString
    }

-- {COLUMN} 1.3.6.1.4.1.248.32.18.2.20.42.1.1
hmSetupLanBridgeRaSnoopingEntryPort OBJECT-TYPE
    SYNTAX     DisplayString (SIZE(0..18))
    MAX-ACCESS read-only
    STATUS     current
    DESCRIPTION
            "-- empty --"
    ::= { hmSetupLanBridgeRaSnoopingEntry 1 }

-- {COLUMN} 1.3.6.1.4.1.248.32.18.2.20.42.1.3
hmSetupLanBridgeRaSnoopingEntryType OBJECT-TYPE
    SYNTAX     INTEGER {
                  eRouter (0),
                  eClient (1)
            }
    MAX-ACCESS read-write
    STATUS     current
    DESCRIPTION
            "-- empty --"
    ::= { hmSetupLanBridgeRaSnoopingEntry 3 }

-- {COLUMN} 1.3.6.1.4.1.248.32.18.2.20.42.1.4
hmSetupLanBridgeRaSnoopingEntryRouterAddress OBJECT-TYPE
    SYNTAX     DisplayString (SIZE(0..39))
    MAX-ACCESS read-write
    STATUS     current
    DESCRIPTION
            "-- empty --"
    ::= { hmSetupLanBridgeRaSnoopingEntry 4 }

-- {TABLE} 1.3.6.1.4.1.248.32.18.2.20.43
hmSetupLanBridgePppoeSnoopingTable OBJECT-TYPE
    SYNTAX     SEQUENCE OF HmSetupLanBridgePppoeSnoopingEntry
    MAX-ACCESS not-accessible
    STATUS     current
    DESCRIPTION
            "-- empty --"
    ::= { hmSetupLanBridge 43 }

-- {ROW} 1.3.6.1.4.1.248.32.18.2.20.43.1
hmSetupLanBridgePppoeSnoopingEntry OBJECT-TYPE
    SYNTAX     HmSetupLanBridgePppoeSnoopingEntry
    MAX-ACCESS not-accessible
    STATUS     current
    DESCRIPTION
            ""
    INDEX {
            hmSetupLanBridgePppoeSnoopingEntryPort
          }
    ::= { hmSetupLanBridgePppoeSnoopingTable 1 }

HmSetupLanBridgePppoeSnoopingEntry ::= SEQUENCE {
            hmSetupLanBridgePppoeSnoopingEntryPort DisplayString,
            hmSetupLanBridgePppoeSnoopingEntryAddAgentInfo INTEGER,
            hmSetupLanBridgePppoeSnoopingEntryRemoteId DisplayString,
            hmSetupLanBridgePppoeSnoopingEntryCircuitId DisplayString,
            hmSetupLanBridgePppoeSnoopingEntryDiscardServerPackets INTEGER
    }

-- {COLUMN} 1.3.6.1.4.1.248.32.18.2.20.43.1.1
hmSetupLanBridgePppoeSnoopingEntryPort OBJECT-TYPE
    SYNTAX     DisplayString (SIZE(0..18))
    MAX-ACCESS read-only
    STATUS     current
    DESCRIPTION
            "-- empty --"
    ::= { hmSetupLanBridgePppoeSnoopingEntry 1 }

-- {COLUMN} 1.3.6.1.4.1.248.32.18.2.20.43.1.2
hmSetupLanBridgePppoeSnoopingEntryAddAgentInfo OBJECT-TYPE
    SYNTAX     INTEGER {
                  eNo (0),
                  eYes (1)
            }
    MAX-ACCESS read-write
    STATUS     current
    DESCRIPTION
            "-- empty --"
    ::= { hmSetupLanBridgePppoeSnoopingEntry 2 }

-- {COLUMN} 1.3.6.1.4.1.248.32.18.2.20.43.1.3
hmSetupLanBridgePppoeSnoopingEntryRemoteId OBJECT-TYPE
    SYNTAX     DisplayString (SIZE(0..30))
    MAX-ACCESS read-write
    STATUS     current
    DESCRIPTION
            "-- empty --"
    ::= { hmSetupLanBridgePppoeSnoopingEntry 3 }

-- {COLUMN} 1.3.6.1.4.1.248.32.18.2.20.43.1.4
hmSetupLanBridgePppoeSnoopingEntryCircuitId OBJECT-TYPE
    SYNTAX     DisplayString (SIZE(0..30))
    MAX-ACCESS read-write
    STATUS     current
    DESCRIPTION
            "-- empty --"
    ::= { hmSetupLanBridgePppoeSnoopingEntry 4 }

-- {COLUMN} 1.3.6.1.4.1.248.32.18.2.20.43.1.5
hmSetupLanBridgePppoeSnoopingEntryDiscardServerPackets OBJECT-TYPE
    SYNTAX     INTEGER {
                  eNo (0),
                  eYes (1)
            }
    MAX-ACCESS read-write
    STATUS     current
    DESCRIPTION
            "-- empty --"
    ::= { hmSetupLanBridgePppoeSnoopingEntry 5 }

-- {NODE} 1.3.6.1.4.1.248.32.18.2.20.248
hmSetupLanBridgeL2Firewall OBJECT IDENTIFIER ::= { hmSetupLanBridge 248 }

-- {NODE} 1.3.6.1.4.1.248.32.18.2.20.248.1
hmSetupLanBridgeL2FirewallConfig OBJECT IDENTIFIER ::= { hmSetupLanBridgeL2Firewall 1 }

-- {SCALAR} 1.3.6.1.4.1.248.32.18.2.20.248.1.1
hmSetupLanBridgeL2FirewallConfigMaximumNumberOfRules OBJECT-TYPE
    SYNTAX     Integer32 (0..2147483647)
    MAX-ACCESS read-write
    STATUS     current
    DESCRIPTION
            "-- empty --"
    ::= { hmSetupLanBridgeL2FirewallConfig 1 }

-- {TABLE} 1.3.6.1.4.1.248.32.18.2.20.248.1.10
hmSetupLanBridgeL2FirewallConfigBridgeMappingTable OBJECT-TYPE
    SYNTAX     SEQUENCE OF HmSetupLanBridgeL2FirewallConfigBridgeMappingEntry
    MAX-ACCESS not-accessible
    STATUS     current
    DESCRIPTION
            "-- empty --"
    ::= { hmSetupLanBridgeL2FirewallConfig 10 }

-- {ROW} 1.3.6.1.4.1.248.32.18.2.20.248.1.10.1
hmSetupLanBridgeL2FirewallConfigBridgeMappingEntry OBJECT-TYPE
    SYNTAX     HmSetupLanBridgeL2FirewallConfigBridgeMappingEntry
    MAX-ACCESS not-accessible
    STATUS     current
    DESCRIPTION
            ""
    INDEX {
            hmSetupLanBridgeL2FirewallConfigBridgeMappingEntryBridgeIndex
          }
    ::= { hmSetupLanBridgeL2FirewallConfigBridgeMappingTable 1 }

HmSetupLanBridgeL2FirewallConfigBridgeMappingEntry ::= SEQUENCE {
            hmSetupLanBridgeL2FirewallConfigBridgeMappingEntryBridgeIndex INTEGER,
            hmSetupLanBridgeL2FirewallConfigBridgeMappingEntryEnable INTEGER,
            hmSetupLanBridgeL2FirewallConfigBridgeMappingEntryFilterMgmt INTEGER
    }

-- {COLUMN} 1.3.6.1.4.1.248.32.18.2.20.248.1.10.1.1
hmSetupLanBridgeL2FirewallConfigBridgeMappingEntryBridgeIndex OBJECT-TYPE
    SYNTAX     INTEGER {
                  eBrg1 (1),
                  eBrg2 (2),
                  eBrg3 (3),
                  eBrg4 (4),
                  eBrg5 (5),
                  eBrg6 (6),
                  eBrg7 (7),
                  eBrg8 (8)
            }
    MAX-ACCESS read-write
    STATUS     current
    DESCRIPTION
            "-- empty --"
    ::= { hmSetupLanBridgeL2FirewallConfigBridgeMappingEntry 1 }

-- {COLUMN} 1.3.6.1.4.1.248.32.18.2.20.248.1.10.1.2
hmSetupLanBridgeL2FirewallConfigBridgeMappingEntryEnable OBJECT-TYPE
    SYNTAX     INTEGER {
                  eNo (0),
                  eYes (1)
            }
    MAX-ACCESS read-write
    STATUS     current
    DESCRIPTION
            "-- empty --"
    ::= { hmSetupLanBridgeL2FirewallConfigBridgeMappingEntry 2 }

-- {COLUMN} 1.3.6.1.4.1.248.32.18.2.20.248.1.10.1.3
hmSetupLanBridgeL2FirewallConfigBridgeMappingEntryFilterMgmt OBJECT-TYPE
    SYNTAX     INTEGER {
                  eNo (0),
                  eYes (1)
            }
    MAX-ACCESS read-write
    STATUS     current
    DESCRIPTION
            "-- empty --"
    ::= { hmSetupLanBridgeL2FirewallConfigBridgeMappingEntry 3 }

-- {TABLE} 1.3.6.1.4.1.248.32.18.2.20.248.1.11
hmSetupLanBridgeL2FirewallConfigRuleTableTable OBJECT-TYPE
    SYNTAX     SEQUENCE OF HmSetupLanBridgeL2FirewallConfigRuleTableEntry
    MAX-ACCESS not-accessible
    STATUS     current
    DESCRIPTION
            "-- empty --"
    ::= { hmSetupLanBridgeL2FirewallConfig 11 }

-- {ROW} 1.3.6.1.4.1.248.32.18.2.20.248.1.11.1
hmSetupLanBridgeL2FirewallConfigRuleTableEntry OBJECT-TYPE
    SYNTAX     HmSetupLanBridgeL2FirewallConfigRuleTableEntry
    MAX-ACCESS not-accessible
    STATUS     current
    DESCRIPTION
            ""
    INDEX {
            hmSetupLanBridgeL2FirewallConfigRuleTableEntryRuleIndex
          }
    ::= { hmSetupLanBridgeL2FirewallConfigRuleTableTable 1 }

HmSetupLanBridgeL2FirewallConfigRuleTableEntry ::= SEQUENCE {
            hmSetupLanBridgeL2FirewallConfigRuleTableEntryRuleIndex Integer32,
            hmSetupLanBridgeL2FirewallConfigRuleTableEntrySourceAddress DisplayString,
            hmSetupLanBridgeL2FirewallConfigRuleTableEntrySourcePort Integer32,
            hmSetupLanBridgeL2FirewallConfigRuleTableEntryDestinationAddress DisplayString,
            hmSetupLanBridgeL2FirewallConfigRuleTableEntryDestinationPort Integer32,
            hmSetupLanBridgeL2FirewallConfigRuleTableEntryProtocol INTEGER,
            hmSetupLanBridgeL2FirewallConfigRuleTableEntryAdditionalParams DisplayString,
            hmSetupLanBridgeL2FirewallConfigRuleTableEntryAction INTEGER,
            hmSetupLanBridgeL2FirewallConfigRuleTableEntryLog INTEGER,
            hmSetupLanBridgeL2FirewallConfigRuleTableEntryTrap INTEGER,
            hmSetupLanBridgeL2FirewallConfigRuleTableEntryStatus INTEGER
    }

-- {COLUMN} 1.3.6.1.4.1.248.32.18.2.20.248.1.11.1.1
hmSetupLanBridgeL2FirewallConfigRuleTableEntryRuleIndex OBJECT-TYPE
    SYNTAX     Integer32 (0..65535)
    MAX-ACCESS read-write
    STATUS     current
    DESCRIPTION
            "-- empty --"
    ::= { hmSetupLanBridgeL2FirewallConfigRuleTableEntry 1 }

-- {COLUMN} 1.3.6.1.4.1.248.32.18.2.20.248.1.11.1.2
hmSetupLanBridgeL2FirewallConfigRuleTableEntrySourceAddress OBJECT-TYPE
    SYNTAX     DisplayString (SIZE(0..18))
    MAX-ACCESS read-write
    STATUS     current
    DESCRIPTION
            "-- empty --"
    ::= { hmSetupLanBridgeL2FirewallConfigRuleTableEntry 2 }

-- {COLUMN} 1.3.6.1.4.1.248.32.18.2.20.248.1.11.1.3
hmSetupLanBridgeL2FirewallConfigRuleTableEntrySourcePort OBJECT-TYPE
    SYNTAX     Integer32 (0..65535)
    MAX-ACCESS read-write
    STATUS     current
    DESCRIPTION
            "-- empty --"
    ::= { hmSetupLanBridgeL2FirewallConfigRuleTableEntry 3 }

-- {COLUMN} 1.3.6.1.4.1.248.32.18.2.20.248.1.11.1.4
hmSetupLanBridgeL2FirewallConfigRuleTableEntryDestinationAddress OBJECT-TYPE
    SYNTAX     DisplayString (SIZE(0..18))
    MAX-ACCESS read-write
    STATUS     current
    DESCRIPTION
            "-- empty --"
    ::= { hmSetupLanBridgeL2FirewallConfigRuleTableEntry 4 }

-- {COLUMN} 1.3.6.1.4.1.248.32.18.2.20.248.1.11.1.5
hmSetupLanBridgeL2FirewallConfigRuleTableEntryDestinationPort OBJECT-TYPE
    SYNTAX     Integer32 (0..65535)
    MAX-ACCESS read-write
    STATUS     current
    DESCRIPTION
            "-- empty --"
    ::= { hmSetupLanBridgeL2FirewallConfigRuleTableEntry 5 }

-- {COLUMN} 1.3.6.1.4.1.248.32.18.2.20.248.1.11.1.6
hmSetupLanBridgeL2FirewallConfigRuleTableEntryProtocol OBJECT-TYPE
    SYNTAX     INTEGER {
                  eAny (1),
                  eIcmp (2),
                  eTcp (3),
                  eUdp (4)
            }
    MAX-ACCESS read-write
    STATUS     current
    DESCRIPTION
            "-- empty --"
    ::= { hmSetupLanBridgeL2FirewallConfigRuleTableEntry 6 }

-- {COLUMN} 1.3.6.1.4.1.248.32.18.2.20.248.1.11.1.7
hmSetupLanBridgeL2FirewallConfigRuleTableEntryAdditionalParams OBJECT-TYPE
    SYNTAX     DisplayString (SIZE(0..50))
    MAX-ACCESS read-write
    STATUS     current
    DESCRIPTION
            "-- empty --"
    ::= { hmSetupLanBridgeL2FirewallConfigRuleTableEntry 7 }

-- {COLUMN} 1.3.6.1.4.1.248.32.18.2.20.248.1.11.1.8
hmSetupLanBridgeL2FirewallConfigRuleTableEntryAction OBJECT-TYPE
    SYNTAX     INTEGER {
                  eAccept (1),
                  eDrop (2),
                  eReject (3)
            }
    MAX-ACCESS read-write
    STATUS     current
    DESCRIPTION
            "-- empty --"
    ::= { hmSetupLanBridgeL2FirewallConfigRuleTableEntry 8 }

-- {COLUMN} 1.3.6.1.4.1.248.32.18.2.20.248.1.11.1.9
hmSetupLanBridgeL2FirewallConfigRuleTableEntryLog OBJECT-TYPE
    SYNTAX     INTEGER {
                  eNo (0),
                  eYes (1)
            }
    MAX-ACCESS read-write
    STATUS     current
    DESCRIPTION
            "-- empty --"
    ::= { hmSetupLanBridgeL2FirewallConfigRuleTableEntry 9 }

-- {COLUMN} 1.3.6.1.4.1.248.32.18.2.20.248.1.11.1.10
hmSetupLanBridgeL2FirewallConfigRuleTableEntryTrap OBJECT-TYPE
    SYNTAX     INTEGER {
                  eNo (0),
                  eYes (1)
            }
    MAX-ACCESS read-write
    STATUS     current
    DESCRIPTION
            "-- empty --"
    ::= { hmSetupLanBridgeL2FirewallConfigRuleTableEntry 10 }

-- {COLUMN} 1.3.6.1.4.1.248.32.18.2.20.248.1.11.1.11
hmSetupLanBridgeL2FirewallConfigRuleTableEntryStatus OBJECT-TYPE
    SYNTAX     INTEGER {
                  eActive (1),
                  eNotInService (2),
                  eNotReady (3),
                  eCreateAndGo (4),
                  eCreateAndWait (5),
                  eDestroy (6)
            }
    MAX-ACCESS read-write
    STATUS     current
    DESCRIPTION
            "-- empty --"
    ::= { hmSetupLanBridgeL2FirewallConfigRuleTableEntry 11 }

-- {TABLE} 1.3.6.1.4.1.248.32.18.2.20.248.1.12
hmSetupLanBridgeL2FirewallConfigRuleMappingTableTable OBJECT-TYPE
    SYNTAX     SEQUENCE OF HmSetupLanBridgeL2FirewallConfigRuleMappingTableEntry
    MAX-ACCESS not-accessible
    STATUS     current
    DESCRIPTION
            "-- empty --"
    ::= { hmSetupLanBridgeL2FirewallConfig 12 }

-- {ROW} 1.3.6.1.4.1.248.32.18.2.20.248.1.12.1
hmSetupLanBridgeL2FirewallConfigRuleMappingTableEntry OBJECT-TYPE
    SYNTAX     HmSetupLanBridgeL2FirewallConfigRuleMappingTableEntry
    MAX-ACCESS not-accessible
    STATUS     current
    DESCRIPTION
            ""
    INDEX {
            hmSetupLanBridgeL2FirewallConfigRuleMappingTableEntryRuleIndex,
            hmSetupLanBridgeL2FirewallConfigRuleMappingTableEntryAssocBridge
          }
    ::= { hmSetupLanBridgeL2FirewallConfigRuleMappingTableTable 1 }

HmSetupLanBridgeL2FirewallConfigRuleMappingTableEntry ::= SEQUENCE {
            hmSetupLanBridgeL2FirewallConfigRuleMappingTableEntryRuleIndex Integer32,
            hmSetupLanBridgeL2FirewallConfigRuleMappingTableEntryAssocBridge INTEGER,
            hmSetupLanBridgeL2FirewallConfigRuleMappingTableEntryPriority Integer32,
            hmSetupLanBridgeL2FirewallConfigRuleMappingTableEntryDirection INTEGER,
            hmSetupLanBridgeL2FirewallConfigRuleMappingTableEntryIfcIdx INTEGER,
            hmSetupLanBridgeL2FirewallConfigRuleMappingTableEntryStatus INTEGER
    }

-- {COLUMN} 1.3.6.1.4.1.248.32.18.2.20.248.1.12.1.1
hmSetupLanBridgeL2FirewallConfigRuleMappingTableEntryRuleIndex OBJECT-TYPE
    SYNTAX     Integer32 (0..65535)
    MAX-ACCESS read-write
    STATUS     current
    DESCRIPTION
            "-- empty --"
    ::= { hmSetupLanBridgeL2FirewallConfigRuleMappingTableEntry 1 }

-- {COLUMN} 1.3.6.1.4.1.248.32.18.2.20.248.1.12.1.2
hmSetupLanBridgeL2FirewallConfigRuleMappingTableEntryAssocBridge OBJECT-TYPE
    SYNTAX     INTEGER {
                  eBrg1 (1),
                  eBrg2 (2),
                  eBrg3 (3),
                  eBrg4 (4),
                  eBrg5 (5),
                  eBrg6 (6),
                  eBrg7 (7),
                  eBrg8 (8)
            }
    MAX-ACCESS read-write
    STATUS     current
    DESCRIPTION
            "-- empty --"
    ::= { hmSetupLanBridgeL2FirewallConfigRuleMappingTableEntry 2 }

-- {COLUMN} 1.3.6.1.4.1.248.32.18.2.20.248.1.12.1.3
hmSetupLanBridgeL2FirewallConfigRuleMappingTableEntryPriority OBJECT-TYPE
    SYNTAX     Integer32 (0..255)
    MAX-ACCESS read-write
    STATUS     current
    DESCRIPTION
            "-- empty --"
    ::= { hmSetupLanBridgeL2FirewallConfigRuleMappingTableEntry 3 }

-- {COLUMN} 1.3.6.1.4.1.248.32.18.2.20.248.1.12.1.4
hmSetupLanBridgeL2FirewallConfigRuleMappingTableEntryDirection OBJECT-TYPE
    SYNTAX     INTEGER {
                  eIngress (1),
                  eEgress (2),
                  eBoth (3)
            }
    MAX-ACCESS read-write
    STATUS     current
    DESCRIPTION
            "-- empty --"
    ::= { hmSetupLanBridgeL2FirewallConfigRuleMappingTableEntry 4 }

-- {COLUMN} 1.3.6.1.4.1.248.32.18.2.20.248.1.12.1.5
hmSetupLanBridgeL2FirewallConfigRuleMappingTableEntryIfcIdx OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311)
            }
    MAX-ACCESS read-write
    STATUS     current
    DESCRIPTION
            "-- empty --"
    ::= { hmSetupLanBridgeL2FirewallConfigRuleMappingTableEntry 5 }

-- {COLUMN} 1.3.6.1.4.1.248.32.18.2.20.248.1.12.1.6
hmSetupLanBridgeL2FirewallConfigRuleMappingTableEntryStatus OBJECT-TYPE
    SYNTAX     INTEGER {
                  eActive (1),
                  eNotInService (2),
                  eNotReady (3),
                  eCreateAndGo (4),
                  eCreateAndWait (5),
                  eDestroy (6)
            }
    MAX-ACCESS read-write
    STATUS     current
    DESCRIPTION
            "-- empty --"
    ::= { hmSetupLanBridgeL2FirewallConfigRuleMappingTableEntry 6 }

-- {NODE} 1.3.6.1.4.1.248.32.18.2.20.248.2
hmSetupLanBridgeL2FirewallAction OBJECT IDENTIFIER ::= { hmSetupLanBridgeL2Firewall 2 }

-- {SCALAR} 1.3.6.1.4.1.248.32.18.2.20.248.2.1
hmSetupLanBridgeL2FirewallActionResetStatistics OBJECT-TYPE
    SYNTAX     DisplayString
    MAX-ACCESS read-write
    STATUS     current
    DESCRIPTION
            "-- empty --"
    ::= { hmSetupLanBridgeL2FirewallAction 1 }

-- {SCALAR} 1.3.6.1.4.1.248.32.18.2.20.248.2.2
hmSetupLanBridgeL2FirewallActionFlushTables OBJECT-TYPE
    SYNTAX     DisplayString
    MAX-ACCESS read-write
    STATUS     current
    DESCRIPTION
            "-- empty --"
    ::= { hmSetupLanBridgeL2FirewallAction 2 }

-- {NODE} 1.3.6.1.4.1.248.32.18.2.21
hmSetupHttp OBJECT IDENTIFIER ::= { hmSetup 21 }

-- {SCALAR} 1.3.6.1.4.1.248.32.18.2.21.1
hmSetupHttpDocumentRoot OBJECT-TYPE
    SYNTAX     DisplayString (SIZE(0..99))
    MAX-ACCESS read-write
    STATUS     current
    DESCRIPTION
            "-- empty --"
    ::= { hmSetupHttp 1 }

-- {SCALAR} 1.3.6.1.4.1.248.32.18.2.21.2
hmSetupHttpUseCss OBJECT-TYPE
    SYNTAX     INTEGER {
                  eNo (0),
                  eYes (1)
            }
    MAX-ACCESS read-write
    STATUS     current
    DESCRIPTION
            "-- empty --"
    ::= { hmSetupHttp 2 }

-- {SCALAR} 1.3.6.1.4.1.248.32.18.2.21.3
hmSetupHttpFontFamily OBJECT-TYPE
    SYNTAX     DisplayString (SIZE(0..39))
    MAX-ACCESS read-write
    STATUS     current
    DESCRIPTION
            "-- empty --"
    ::= { hmSetupHttp 3 }

-- {SCALAR} 1.3.6.1.4.1.248.32.18.2.21.5
hmSetupHttpPageHeaders OBJECT-TYPE
    SYNTAX     INTEGER {
                  eImages (0),
                  eTexts (1)
            }
    MAX-ACCESS read-write
    STATUS     current
    DESCRIPTION
            "-- empty --"
    ::= { hmSetupHttp 5 }

-- {SCALAR} 1.3.6.1.4.1.248.32.18.2.21.6
hmSetupHttpErrorPageStyle OBJECT-TYPE
    SYNTAX     INTEGER {
                  eStandard (0),
                  eNifty (1)
            }
    MAX-ACCESS read-write
    STATUS     current
    DESCRIPTION
            "-- empty --"
    ::= { hmSetupHttp 6 }

-- {SCALAR} 1.3.6.1.4.1.248.32.18.2.21.7
hmSetupHttpPort OBJECT-TYPE
    SYNTAX     Integer32 (0..65535)
    MAX-ACCESS read-write
    STATUS     current
    DESCRIPTION
            "-- empty --"
    ::= { hmSetupHttp 7 }

-- {SCALAR} 1.3.6.1.4.1.248.32.18.2.21.8
hmSetupHttpSslPort OBJECT-TYPE
    SYNTAX     Integer32 (0..65535)
    MAX-ACCESS read-write
    STATUS     current
    DESCRIPTION
            "-- empty --"
    ::= { hmSetupHttp 8 }

-- {SCALAR} 1.3.6.1.4.1.248.32.18.2.21.9
hmSetupHttpMaxTunnelConnections OBJECT-TYPE
    SYNTAX     Integer32 (0..255)
    MAX-ACCESS read-write
    STATUS     current
    DESCRIPTION
            "-- empty --"
    ::= { hmSetupHttp 9 }

-- {SCALAR} 1.3.6.1.4.1.248.32.18.2.21.10
hmSetupHttpTunnelIdleTimeout OBJECT-TYPE
    SYNTAX     Integer32 (0..2147483647)
    MAX-ACCESS read-write
    STATUS     current
    DESCRIPTION
            "-- empty --"
    ::= { hmSetupHttp 10 }

-- {SCALAR} 1.3.6.1.4.1.248.32.18.2.21.11
hmSetupHttpSessionTimeout OBJECT-TYPE
    SYNTAX     Integer32 (0..2147483647)
    MAX-ACCESS read-write
    STATUS     current
    DESCRIPTION
            "-- empty --"
    ::= { hmSetupHttp 11 }

-- {SCALAR} 1.3.6.1.4.1.248.32.18.2.21.13
hmSetupHttpStandardDesign OBJECT-TYPE
    SYNTAX     INTEGER {
                  eNormalDesign (0),
                  eDesignForSmallResolutions (1),
                  eDesignWithHighContrast (2)
            }
    MAX-ACCESS read-write
    STATUS     current
    DESCRIPTION
            "-- empty --"
    ::= { hmSetupHttp 13 }

-- {TABLE} 1.3.6.1.4.1.248.32.18.2.21.14
hmSetupHttpShowDeviceInformationTable OBJECT-TYPE
    SYNTAX     SEQUENCE OF HmSetupHttpShowDeviceInformationEntry
    MAX-ACCESS not-accessible
    STATUS     current
    DESCRIPTION
            "-- empty --"
    ::= { hmSetupHttp 14 }

-- {ROW} 1.3.6.1.4.1.248.32.18.2.21.14.1
hmSetupHttpShowDeviceInformationEntry OBJECT-TYPE
    SYNTAX     HmSetupHttpShowDeviceInformationEntry
    MAX-ACCESS not-accessible
    STATUS     current
    DESCRIPTION
            ""
    INDEX {
            hmSetupHttpShowDeviceInformationEntryDeviceInformation
          }
    ::= { hmSetupHttpShowDeviceInformationTable 1 }

HmSetupHttpShowDeviceInformationEntry ::= SEQUENCE {
            hmSetupHttpShowDeviceInformationEntryDeviceInformation INTEGER,
            hmSetupHttpShowDeviceInformationEntryPosition Integer32
    }

-- {COLUMN} 1.3.6.1.4.1.248.32.18.2.21.14.1.1
hmSetupHttpShowDeviceInformationEntryDeviceInformation OBJECT-TYPE
    SYNTAX     INTEGER {
                  eCpu (1),
                  eMemory (2),
                  eWlan (3),
                  eP2pConnections (4),
                  eEthernetPorts (5),
                  eTroughputEthernet (6),
                  eUmtsModemInterface (7),
                  eRouter (8),
                  eFirewall (9),
                  eDhcp (10),
                  eDns (11),
                  eVpn (12),
                  eDSLDSLoL (15),
                  eScepCa (16),
                  eWlanController (17),
                  eTime (18),
                  eIpv4Addresses (19),
                  eOperatingTime (20),
                  eConnections (22),
                  eIpv6Addresses (23),
                  eIpv6Prefixes (24),
                  eDhcpv6Client (25),
                  eDhcpv6Server (26)
            }
    MAX-ACCESS read-write
    STATUS     current
    DESCRIPTION
            "-- empty --"
    ::= { hmSetupHttpShowDeviceInformationEntry 1 }

-- {COLUMN} 1.3.6.1.4.1.248.32.18.2.21.14.1.2
hmSetupHttpShowDeviceInformationEntryPosition OBJECT-TYPE
    SYNTAX     Integer32 (0..2147483647)
    MAX-ACCESS read-write
    STATUS     current
    DESCRIPTION
            "-- empty --"
    ::= { hmSetupHttpShowDeviceInformationEntry 2 }

-- {SCALAR} 1.3.6.1.4.1.248.32.18.2.21.15
hmSetupHttpHttpCompression OBJECT-TYPE
    SYNTAX     INTEGER {
                  eActivated (0),
                  eOnlyForWan (1),
                  eDeactivated (2)
            }
    MAX-ACCESS read-write
    STATUS     current
    DESCRIPTION
            "-- empty --"
    ::= { hmSetupHttp 15 }

-- {TABLE} 1.3.6.1.4.1.248.32.18.2.21.16
hmSetupHttpKeepServerPortsOpenTable OBJECT-TYPE
    SYNTAX     SEQUENCE OF HmSetupHttpKeepServerPortsOpenEntry
    MAX-ACCESS not-accessible
    STATUS     current
    DESCRIPTION
            "-- empty --"
    ::= { hmSetupHttp 16 }

-- {ROW} 1.3.6.1.4.1.248.32.18.2.21.16.1
hmSetupHttpKeepServerPortsOpenEntry OBJECT-TYPE
    SYNTAX     HmSetupHttpKeepServerPortsOpenEntry
    MAX-ACCESS not-accessible
    STATUS     current
    DESCRIPTION
            ""
    INDEX {
            hmSetupHttpKeepServerPortsOpenEntryIfc
          }
    ::= { hmSetupHttpKeepServerPortsOpenTable 1 }

HmSetupHttpKeepServerPortsOpenEntry ::= SEQUENCE {
            hmSetupHttpKeepServerPortsOpenEntryIfc INTEGER,
            hmSetupHttpKeepServerPortsOpenEntryKeepServerPortsOpen INTEGER
    }

-- {COLUMN} 1.3.6.1.4.1.248.32.18.2.21.16.1.1
hmSetupHttpKeepServerPortsOpenEntryIfc OBJECT-TYPE
    SYNTAX     INTEGER {
                  eLan (1),
                  eWan (2),
                  eWlan (4)
            }
    MAX-ACCESS read-only
    STATUS     current
    DESCRIPTION
            "-- empty --"
    ::= { hmSetupHttpKeepServerPortsOpenEntry 1 }

-- {COLUMN} 1.3.6.1.4.1.248.32.18.2.21.16.1.2
hmSetupHttpKeepServerPortsOpenEntryKeepServerPortsOpen OBJECT-TYPE
    SYNTAX     INTEGER {
                  eAutomatic (0),
                  eEnabled (1),
                  eDisabled (2)
            }
    MAX-ACCESS read-write
    STATUS     current
    DESCRIPTION
            "-- empty --"
    ::= { hmSetupHttpKeepServerPortsOpenEntry 2 }

-- {SCALAR} 1.3.6.1.4.1.248.32.18.2.21.17
hmSetupHttpUseUserProvidedCertificate OBJECT-TYPE
    SYNTAX     INTEGER {
                  eNo (0),
                  eYes (1)
            }
    MAX-ACCESS read-write
    STATUS     current
    DESCRIPTION
            "-- empty --"
    ::= { hmSetupHttp 17 }

-- {SCALAR} 1.3.6.1.4.1.248.32.18.2.21.18
hmSetupHttpSslVersions OBJECT-TYPE
    SYNTAX     BITS {
                  eTlsv12 (4),
                  eTlsv11 (5),
                  eTlsv1 (6),
                  eSslv3 (7)
            }
    MAX-ACCESS read-write
    STATUS     current
    DESCRIPTION
            "-- empty --"
    ::= { hmSetupHttp 18 }

-- {NODE} 1.3.6.1.4.1.248.32.18.2.21.20
hmSetupHttpRolloutWizard OBJECT IDENTIFIER ::= { hmSetupHttp 20 }

-- {SCALAR} 1.3.6.1.4.1.248.32.18.2.21.20.1
hmSetupHttpRolloutWizardOperating OBJECT-TYPE
    SYNTAX     INTEGER {
                  eNo (0),
                  eYes (1)
            }
    MAX-ACCESS read-write
    STATUS     current
    DESCRIPTION
            "-- empty --"
    ::= { hmSetupHttpRolloutWizard 1 }

-- {SCALAR} 1.3.6.1.4.1.248.32.18.2.21.20.2
hmSetupHttpRolloutWizardTitle OBJECT-TYPE
    SYNTAX     DisplayString (SIZE(0..50))
    MAX-ACCESS read-write
    STATUS     current
    DESCRIPTION
            "-- empty --"
    ::= { hmSetupHttpRolloutWizard 2 }

-- {TABLE} 1.3.6.1.4.1.248.32.18.2.21.20.3
hmSetupHttpRolloutWizardVariablesTable OBJECT-TYPE
    SYNTAX     SEQUENCE OF HmSetupHttpRolloutWizardVariablesEntry
    MAX-ACCESS not-accessible
    STATUS     current
    DESCRIPTION
            "-- empty --"
    ::= { hmSetupHttpRolloutWizard 3 }

-- {ROW} 1.3.6.1.4.1.248.32.18.2.21.20.3.1
hmSetupHttpRolloutWizardVariablesEntry OBJECT-TYPE
    SYNTAX     HmSetupHttpRolloutWizardVariablesEntry
    MAX-ACCESS not-accessible
    STATUS     current
    DESCRIPTION
            ""
    INDEX {
            hmSetupHttpRolloutWizardVariablesEntryIndex
          }
    ::= { hmSetupHttpRolloutWizardVariablesTable 1 }

HmSetupHttpRolloutWizardVariablesEntry ::= SEQUENCE {
            hmSetupHttpRolloutWizardVariablesEntryIndex Integer32,
            hmSetupHttpRolloutWizardVariablesEntryIdent DisplayString,
            hmSetupHttpRolloutWizardVariablesEntryTitle DisplayString,
            hmSetupHttpRolloutWizardVariablesEntryType INTEGER,
            hmSetupHttpRolloutWizardVariablesEntryMinValue Integer32,
            hmSetupHttpRolloutWizardVariablesEntryMaxValue Integer32,
            hmSetupHttpRolloutWizardVariablesEntryDefaultValue DisplayString
    }

-- {COLUMN} 1.3.6.1.4.1.248.32.18.2.21.20.3.1.1
hmSetupHttpRolloutWizardVariablesEntryIndex OBJECT-TYPE
    SYNTAX     Integer32 (0..2147483647)
    MAX-ACCESS read-write
    STATUS     current
    DESCRIPTION
            "-- empty --"
    ::= { hmSetupHttpRolloutWizardVariablesEntry 1 }

-- {COLUMN} 1.3.6.1.4.1.248.32.18.2.21.20.3.1.2
hmSetupHttpRolloutWizardVariablesEntryIdent OBJECT-TYPE
    SYNTAX     DisplayString (SIZE(0..16))
    MAX-ACCESS read-write
    STATUS     current
    DESCRIPTION
            "-- empty --"
    ::= { hmSetupHttpRolloutWizardVariablesEntry 2 }

-- {COLUMN} 1.3.6.1.4.1.248.32.18.2.21.20.3.1.3
hmSetupHttpRolloutWizardVariablesEntryTitle OBJECT-TYPE
    SYNTAX     DisplayString (SIZE(0..40))
    MAX-ACCESS read-write
    STATUS     current
    DESCRIPTION
            "-- empty --"
    ::= { hmSetupHttpRolloutWizardVariablesEntry 3 }

-- {COLUMN} 1.3.6.1.4.1.248.32.18.2.21.20.3.1.4
hmSetupHttpRolloutWizardVariablesEntryType OBJECT-TYPE
    SYNTAX     INTEGER {
                  eLabel (0),
                  eInteger (1),
                  eString (2),
                  ePassword (3),
                  eCheckmark (4)
            }
    MAX-ACCESS read-write
    STATUS     current
    DESCRIPTION
            "-- empty --"
    ::= { hmSetupHttpRolloutWizardVariablesEntry 4 }

-- {COLUMN} 1.3.6.1.4.1.248.32.18.2.21.20.3.1.5
hmSetupHttpRolloutWizardVariablesEntryMinValue OBJECT-TYPE
    SYNTAX     Integer32 (0..2147483647)
    MAX-ACCESS read-write
    STATUS     current
    DESCRIPTION
            "-- empty --"
    ::= { hmSetupHttpRolloutWizardVariablesEntry 5 }

-- {COLUMN} 1.3.6.1.4.1.248.32.18.2.21.20.3.1.6
hmSetupHttpRolloutWizardVariablesEntryMaxValue OBJECT-TYPE
    SYNTAX     Integer32 (0..2147483647)
    MAX-ACCESS read-write
    STATUS     current
    DESCRIPTION
            "-- empty --"
    ::= { hmSetupHttpRolloutWizardVariablesEntry 6 }

-- {COLUMN} 1.3.6.1.4.1.248.32.18.2.21.20.3.1.7
hmSetupHttpRolloutWizardVariablesEntryDefaultValue OBJECT-TYPE
    SYNTAX     DisplayString (SIZE(0..30))
    MAX-ACCESS read-write
    STATUS     current
    DESCRIPTION
            "-- empty --"
    ::= { hmSetupHttpRolloutWizardVariablesEntry 7 }

-- {TABLE} 1.3.6.1.4.1.248.32.18.2.21.20.4
hmSetupHttpRolloutWizardActionsTable OBJECT-TYPE
    SYNTAX     SEQUENCE OF HmSetupHttpRolloutWizardActionsEntry
    MAX-ACCESS not-accessible
    STATUS     current
    DESCRIPTION
            "-- empty --"
    ::= { hmSetupHttpRolloutWizard 4 }

-- {ROW} 1.3.6.1.4.1.248.32.18.2.21.20.4.1
hmSetupHttpRolloutWizardActionsEntry OBJECT-TYPE
    SYNTAX     HmSetupHttpRolloutWizardActionsEntry
    MAX-ACCESS not-accessible
    STATUS     current
    DESCRIPTION
            ""
    INDEX {
            hmSetupHttpRolloutWizardActionsEntryIndex
          }
    ::= { hmSetupHttpRolloutWizardActionsTable 1 }

HmSetupHttpRolloutWizardActionsEntry ::= SEQUENCE {
            hmSetupHttpRolloutWizardActionsEntryIndex Integer32,
            hmSetupHttpRolloutWizardActionsEntryAction DisplayString,
            hmSetupHttpRolloutWizardActionsEntryDescription DisplayString
    }

-- {COLUMN} 1.3.6.1.4.1.248.32.18.2.21.20.4.1.1
hmSetupHttpRolloutWizardActionsEntryIndex OBJECT-TYPE
    SYNTAX     Integer32 (0..2147483647)
    MAX-ACCESS read-write
    STATUS     current
    DESCRIPTION
            "-- empty --"
    ::= { hmSetupHttpRolloutWizardActionsEntry 1 }

-- {COLUMN} 1.3.6.1.4.1.248.32.18.2.21.20.4.1.2
hmSetupHttpRolloutWizardActionsEntryAction OBJECT-TYPE
    SYNTAX     DisplayString (SIZE(0..251))
    MAX-ACCESS read-write
    STATUS     current
    DESCRIPTION
            "-- empty --"
    ::= { hmSetupHttpRolloutWizardActionsEntry 2 }

-- {COLUMN} 1.3.6.1.4.1.248.32.18.2.21.20.4.1.3
hmSetupHttpRolloutWizardActionsEntryDescription OBJECT-TYPE
    SYNTAX     DisplayString (SIZE(0..251))
    MAX-ACCESS read-write
    STATUS     current
    DESCRIPTION
            "-- empty --"
    ::= { hmSetupHttpRolloutWizardActionsEntry 3 }

-- {SCALAR} 1.3.6.1.4.1.248.32.18.2.21.20.5
hmSetupHttpRolloutWizardRenumberVariables OBJECT-TYPE
    SYNTAX     DisplayString
    MAX-ACCESS read-write
    STATUS     current
    DESCRIPTION
            "-- empty --"
    ::= { hmSetupHttpRolloutWizard 5 }

-- {SCALAR} 1.3.6.1.4.1.248.32.18.2.21.20.6
hmSetupHttpRolloutWizardRenumberActions OBJECT-TYPE
    SYNTAX     DisplayString
    MAX-ACCESS read-write
    STATUS     current
    DESCRIPTION
            "-- empty --"
    ::= { hmSetupHttpRolloutWizard 6 }

-- {SCALAR} 1.3.6.1.4.1.248.32.18.2.21.20.7
hmSetupHttpRolloutWizardDisplayConnectionStatusFor OBJECT-TYPE
    SYNTAX     BITS {
                  eNothing (0),
                  eDsl (28),
                  eVpn (29)
            }
    MAX-ACCESS read-write
    STATUS     current
    DESCRIPTION
            "-- empty --"
    ::= { hmSetupHttpRolloutWizard 7 }

-- {SCALAR} 1.3.6.1.4.1.248.32.18.2.21.21
hmSetupHttpMaxHttpJobCount OBJECT-TYPE
    SYNTAX     Integer32 (0..2147483647)
    MAX-ACCESS read-write
    STATUS     current
    DESCRIPTION
            "-- empty --"
    ::= { hmSetupHttp 21 }

-- {NODE} 1.3.6.1.4.1.248.32.18.2.21.30
hmSetupHttpFileServer OBJECT IDENTIFIER ::= { hmSetupHttp 30 }

-- {SCALAR} 1.3.6.1.4.1.248.32.18.2.21.30.1
hmSetupHttpFileServerPublicSubdir OBJECT-TYPE
    SYNTAX     DisplayString (SIZE(0..64))
    MAX-ACCESS read-write
    STATUS     current
    DESCRIPTION
            "-- empty --"
    ::= { hmSetupHttpFileServer 1 }

-- {SCALAR} 1.3.6.1.4.1.248.32.18.2.21.30.2
hmSetupHttpFileServerOperating OBJECT-TYPE
    SYNTAX     INTEGER {
                  eNo (0),
                  eYes (1)
            }
    MAX-ACCESS read-write
    STATUS     current
    DESCRIPTION
            "-- empty --"
    ::= { hmSetupHttpFileServer 2 }

-- {NODE} 1.3.6.1.4.1.248.32.18.2.21.40
hmSetupHttpSslNew OBJECT IDENTIFIER ::= { hmSetupHttp 40 }

-- {SCALAR} 1.3.6.1.4.1.248.32.18.2.21.40.3
hmSetupHttpSslNewVersions OBJECT-TYPE
    SYNTAX     BITS {
                  eTlsv12 (28),
                  eTlsv11 (29),
                  eTlsv1 (30),
                  eSslv3 (31)
            }
    MAX-ACCESS read-write
    STATUS     current
    DESCRIPTION
            "-- empty --"
    ::= { hmSetupHttpSslNew 3 }

-- {SCALAR} 1.3.6.1.4.1.248.32.18.2.21.40.4
hmSetupHttpSslNewKeyexAlgorithms OBJECT-TYPE
    SYNTAX     BITS {
                  eEcdhe (27),
                  eDhe (29),
                  eRsa (31)
            }
    MAX-ACCESS read-write
    STATUS     current
    DESCRIPTION
            "-- empty --"
    ::= { hmSetupHttpSslNew 4 }

-- {SCALAR} 1.3.6.1.4.1.248.32.18.2.21.40.5
hmSetupHttpSslNewCryptoAlgorithms OBJECT-TYPE
    SYNTAX     BITS {
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { hmSetupHttpSslNew 5 }

-- {SCALAR} 1.3.6.1.4.1.248.32.18.2.21.40.6
hmSetupHttpSslNewHashAlgorithms OBJECT-TYPE
    SYNTAX     BITS {
                  eSha2384 (26),
                  eSha2256 (27),
                  eSha1 (29),
                  eMd5 (30)
            }
    MAX-ACCESS read-write
    STATUS     current
    DESCRIPTION
            "-- empty --"
    ::= { hmSetupHttpSslNew 6 }

-- {SCALAR} 1.3.6.1.4.1.248.32.18.2.21.40.7
hmSetupHttpSslNewPreferPfs OBJECT-TYPE
    SYNTAX     BITS {
                  eNo (0),
                  eYes (7)
            }
    MAX-ACCESS read-write
    STATUS     current
    DESCRIPTION
            "-- empty --"
    ::= { hmSetupHttpSslNew 7 }

-- {SCALAR} 1.3.6.1.4.1.248.32.18.2.21.40.8
hmSetupHttpSslNewRenegotiations OBJECT-TYPE
    SYNTAX     INTEGER {
                  eForbidden (0),
                  eAllowed (1),
                  eIgnored (2)
            }
    MAX-ACCESS read-write
    STATUS     current
    DESCRIPTION
            "-- empty --"
    ::= { hmSetupHttpSslNew 8 }

-- {SCALAR} 1.3.6.1.4.1.248.32.18.2.21.40.10
hmSetupHttpSslNewPortNew OBJECT-TYPE
    SYNTAX     Integer32 (0..65535)
    MAX-ACCESS read-write
    STATUS     current
    DESCRIPTION
            "TCP port device is listening on for HTTPS"
    ::= { hmSetupHttpSslNew 10 }

-- {SCALAR} 1.3.6.1.4.1.248.32.18.2.21.40.11
hmSetupHttpSslNewUseUserDefCert OBJECT-TYPE
    SYNTAX     INTEGER {
                  eNo (0),
                  eYes (1)
            }
    MAX-ACCESS read-write
    STATUS     current
    DESCRIPTION
            "use uploaded SSL certificate for HTTPS server"
    ::= { hmSetupHttpSslNew 11 }

-- {NODE} 1.3.6.1.4.1.248.32.18.2.22
hmSetupSyslog OBJECT IDENTIFIER ::= { hmSetup 22 }

-- {SCALAR} 1.3.6.1.4.1.248.32.18.2.22.1
hmSetupSyslogOperating OBJECT-TYPE
    SYNTAX     INTEGER {
                  eNo (0),
                  eYes (1)
            }
    MAX-ACCESS read-write
    STATUS     current
    DESCRIPTION
            "-- empty --"
    ::= { hmSetupSyslog 1 }

-- {TABLE} 1.3.6.1.4.1.248.32.18.2.22.2
hmSetupSyslogServerTable OBJECT-TYPE
    SYNTAX     SEQUENCE OF HmSetupSyslogServerEntry
    MAX-ACCESS not-accessible
    STATUS     current
    DESCRIPTION
            "-- empty --"
    ::= { hmSetupSyslog 2 }

-- {ROW} 1.3.6.1.4.1.248.32.18.2.22.2.1
hmSetupSyslogServerEntry OBJECT-TYPE
    SYNTAX     HmSetupSyslogServerEntry
    MAX-ACCESS not-accessible
    STATUS     current
    DESCRIPTION
            ""
    INDEX {
            hmSetupSyslogServerEntryIdx
          }
    ::= { hmSetupSyslogServerTable 1 }

HmSetupSyslogServerEntry ::= SEQUENCE {
            hmSetupSyslogServerEntryIdx DisplayString,
            hmSetupSyslogServerEntryIpAddress IpAddress,
            hmSetupSyslogServerEntrySource BITS,
            hmSetupSyslogServerEntryLevel BITS,
            hmSetupSyslogServerEntryLoopbackAddr DisplayString,
            hmSetupSyslogServerEntryIpAddressDns DisplayString,
            hmSetupSyslogServerEntryPort Integer32,
            hmSetupSyslogServerEntryProtocol INTEGER
    }

-- {COLUMN} 1.3.6.1.4.1.248.32.18.2.22.2.1.1
hmSetupSyslogServerEntryIdx OBJECT-TYPE
    SYNTAX     DisplayString (SIZE(0..4))
    MAX-ACCESS read-write
    STATUS     current
    DESCRIPTION
            "-- empty --"
    ::= { hmSetupSyslogServerEntry 1 }

-- {COLUMN} 1.3.6.1.4.1.248.32.18.2.22.2.1.2
hmSetupSyslogServerEntryIpAddress OBJECT-TYPE
    SYNTAX     IpAddress
    MAX-ACCESS read-write
    STATUS     current
    DESCRIPTION
            "-- empty --"
    ::= { hmSetupSyslogServerEntry 2 }

-- {COLUMN} 1.3.6.1.4.1.248.32.18.2.22.2.1.3
hmSetupSyslogServerEntrySource OBJECT-TYPE
    SYNTAX     BITS {
                  eRouter (0),
                  eAdministration (1),
                  eAccounting (2),
                  eConnections (3),
                  eConsoleLogin (4),
                  eSystemtime (5),
                  eLogin (6),
                  eSystem (7)
            }
    MAX-ACCESS read-write
    STATUS     current
    DESCRIPTION
            "-- empty --"
    ::= { hmSetupSyslogServerEntry 3 }

-- {COLUMN} 1.3.6.1.4.1.248.32.18.2.22.2.1.4
hmSetupSyslogServerEntryLevel OBJECT-TYPE
    SYNTAX     BITS {
                  eDebug (3),
                  eInfo (4),
                  eWarning (5),
                  eError (6),
                  eAlarm (7)
            }
    MAX-ACCESS read-write
    STATUS     current
    DESCRIPTION
            "-- empty --"
    ::= { hmSetupSyslogServerEntry 4 }

-- {COLUMN} 1.3.6.1.4.1.248.32.18.2.22.2.1.6
hmSetupSyslogServerEntryLoopbackAddr OBJECT-TYPE
    SYNTAX     DisplayString (SIZE(0..16))
    MAX-ACCESS read-write
    STATUS     current
    DESCRIPTION
            "-- empty --"
    ::= { hmSetupSyslogServerEntry 6 }

-- {COLUMN} 1.3.6.1.4.1.248.32.18.2.22.2.1.7
hmSetupSyslogServerEntryIpAddressDns OBJECT-TYPE
    SYNTAX     DisplayString (SIZE(0..64))
    MAX-ACCESS read-write
    STATUS     current
    DESCRIPTION
            ""
    ::= { hmSetupSyslogServerEntry 7 }

-- {COLUMN} 1.3.6.1.4.1.248.32.18.2.22.2.1.8
hmSetupSyslogServerEntryPort OBJECT-TYPE
    SYNTAX     Integer32 (0..65535)
    MAX-ACCESS read-write
    STATUS     current
    DESCRIPTION
            "-- empty --"
    ::= { hmSetupSyslogServerEntry 8 }

-- {COLUMN} 1.3.6.1.4.1.248.32.18.2.22.2.1.9
hmSetupSyslogServerEntryProtocol OBJECT-TYPE
    SYNTAX     INTEGER {
                  eUdp (0),
                  eTcp (1)
            }
    MAX-ACCESS read-write
    STATUS     current
    DESCRIPTION
            "-- empty --"
    ::= { hmSetupSyslogServerEntry 9 }

-- {TABLE} 1.3.6.1.4.1.248.32.18.2.22.3
hmSetupSyslogFacilityMapperTable OBJECT-TYPE
    SYNTAX     SEQUENCE OF HmSetupSyslogFacilityMapperEntry
    MAX-ACCESS not-accessible
    STATUS     current
    DESCRIPTION
            "-- empty --"
    ::= { hmSetupSyslog 3 }

-- {ROW} 1.3.6.1.4.1.248.32.18.2.22.3.1
hmSetupSyslogFacilityMapperEntry OBJECT-TYPE
    SYNTAX     HmSetupSyslogFacilityMapperEntry
    MAX-ACCESS not-accessible
    STATUS     current
    DESCRIPTION
            ""
    INDEX {
            hmSetupSyslogFacilityMapperEntrySource
          }
    ::= { hmSetupSyslogFacilityMapperTable 1 }

HmSetupSyslogFacilityMapperEntry ::= SEQUENCE {
            hmSetupSyslogFacilityMapperEntrySource INTEGER,
            hmSetupSyslogFacilityMapperEntryFacility INTEGER
    }

-- {COLUMN} 1.3.6.1.4.1.248.32.18.2.22.3.1.1
hmSetupSyslogFacilityMapperEntrySource OBJECT-TYPE
    SYNTAX     INTEGER {
                  eSystem (1),
                  eLogin (2),
                  eSystemtime (4),
                  eConsoleLogin (8),
                  eConnections (16),
                  eAccounting (32),
                  eAdministration (64),
                  eRouter (128)
            }
    MAX-ACCESS read-only
    STATUS     current
    DESCRIPTION
            "-- empty --"
    ::= { hmSetupSyslogFacilityMapperEntry 1 }

-- {COLUMN} 1.3.6.1.4.1.248.32.18.2.22.3.1.2
hmSetupSyslogFacilityMapperEntryFacility OBJECT-TYPE
    SYNTAX     INTEGER {
                  eKern (0),
                  eUser (1),
                  eMail (2),
                  eDaemon (3),
                  eAuth (4),
                  eSyslog (5),
                  eLpr (6),
                  eNews (7),
                  eUucp (8),
                  eCron (9),
                  eAuthpriv (10),
                  eLocal0 (16),
                  eLocal1 (17),
                  eLocal2 (18),
                  eLocal3 (19),
                  eLocal4 (20),
                  eLocal5 (21),
                  eLocal6 (22),
                  eLocal7 (23)
            }
    MAX-ACCESS read-write
    STATUS     current
    DESCRIPTION
            "-- empty --"
    ::= { hmSetupSyslogFacilityMapperEntry 2 }

-- {SCALAR} 1.3.6.1.4.1.248.32.18.2.22.4
hmSetupSyslogPort OBJECT-TYPE
    SYNTAX     Integer32 (0..65535)
    MAX-ACCESS read-write
    STATUS     current
    DESCRIPTION
            "-- empty --"
    ::= { hmSetupSyslog 4 }

-- {SCALAR} 1.3.6.1.4.1.248.32.18.2.22.5
hmSetupSyslogMessagesTableOrder OBJECT-TYPE
    SYNTAX     INTEGER {
                  eOldestOnTop (0),
                  eNewestOnTop (1)
            }
    MAX-ACCESS read-write
    STATUS     current
    DESCRIPTION
            "-- empty --"
    ::= { hmSetupSyslog 5 }

-- {SCALAR} 1.3.6.1.4.1.248.32.18.2.22.8
hmSetupSyslogLogCliChanges OBJECT-TYPE
    SYNTAX     INTEGER {
                  eNo (0),
                  eYes (1)
            }
    MAX-ACCESS read-write
    STATUS     current
    DESCRIPTION
            "-- empty --"
    ::= { hmSetupSyslog 8 }

-- {SCALAR} 1.3.6.1.4.1.248.32.18.2.22.9
hmSetupSyslogMaxMessageAgeHours OBJECT-TYPE
    SYNTAX     Integer32 (0..2147483647)
    MAX-ACCESS read-write
    STATUS     current
    DESCRIPTION
            "-- empty --"
    ::= { hmSetupSyslog 9 }

-- {SCALAR} 1.3.6.1.4.1.248.32.18.2.22.10
hmSetupSyslogRemoveOldMessages OBJECT-TYPE
    SYNTAX     INTEGER {
                  eNo (0),
                  eYes (1)
            }
    MAX-ACCESS read-write
    STATUS     current
    DESCRIPTION
            "-- empty --"
    ::= { hmSetupSyslog 10 }

-- {SCALAR} 1.3.6.1.4.1.248.32.18.2.22.11
hmSetupSyslogMaxAgeUnit OBJECT-TYPE
    SYNTAX     INTEGER {
                  eHour (0),
                  eDay (1),
                  eMonth (2)
            }
    MAX-ACCESS read-write
    STATUS     current
    DESCRIPTION
            "-- empty --"
    ::= { hmSetupSyslog 11 }

-- {SCALAR} 1.3.6.1.4.1.248.32.18.2.22.12
hmSetupSyslogCriticalPrio OBJECT-TYPE
    SYNTAX     INTEGER {
                  eEmergency (0),
                  eAlarm (1),
                  eCritical (2),
                  eError (3),
                  eWarning (4),
                  eNotice (5),
                  eInfo (6),
                  eDebug (7)
            }
    MAX-ACCESS read-write
    STATUS     current
    DESCRIPTION
            "-- empty --"
    ::= { hmSetupSyslog 12 }

-- {NODE} 1.3.6.1.4.1.248.32.18.2.23
hmSetupInterfaces OBJECT IDENTIFIER ::= { hmSetup 23 }

-- {TABLE} 1.3.6.1.4.1.248.32.18.2.23.4
hmSetupInterfacesDslTable OBJECT-TYPE
    SYNTAX     SEQUENCE OF HmSetupInterfacesDslEntry
    MAX-ACCESS not-accessible
    STATUS     current
    DESCRIPTION
            "-- empty --"
    ::= { hmSetupInterfaces 4 }

-- {ROW} 1.3.6.1.4.1.248.32.18.2.23.4.1
hmSetupInterfacesDslEntry OBJECT-TYPE
    SYNTAX     HmSetupInterfacesDslEntry
    MAX-ACCESS not-accessible
    STATUS     current
    DESCRIPTION
            ""
    INDEX {
            hmSetupInterfacesDslEntryIfc
          }
    ::= { hmSetupInterfacesDslTable 1 }

HmSetupInterfacesDslEntry ::= SEQUENCE {
            hmSetupInterfacesDslEntryIfc INTEGER,
            hmSetupInterfacesDslEntryOperating INTEGER,
            hmSetupInterfacesDslEntryTypeOfInterface Integer32,
            hmSetupInterfacesDslEntryUpstreamRate Integer32,
            hmSetupInterfacesDslEntryExtOverhead Integer32,
            hmSetupInterfacesDslEntryDownstreamRate Integer32
    }

-- {COLUMN} 1.3.6.1.4.1.248.32.18.2.23.4.1.1
hmSetupInterfacesDslEntryIfc OBJECT-TYPE
    SYNTAX     INTEGER {
                  eModem (513),
                  eDsl1 (2049),
                  eDsl2 (2050),
                  eDsl3 (2051),
                  eDsl4 (2052)
            }
    MAX-ACCESS read-only
    STATUS     current
    DESCRIPTION
            "-- empty --"
    ::= { hmSetupInterfacesDslEntry 1 }

-- {COLUMN} 1.3.6.1.4.1.248.32.18.2.23.4.1.2
hmSetupInterfacesDslEntryOperating OBJECT-TYPE
    SYNTAX     INTEGER {
                  eNo (0),
                  eYes (16)
            }
    MAX-ACCESS read-write
    STATUS     current
    DESCRIPTION
            "-- empty --"
    ::= { hmSetupInterfacesDslEntry 2 }

-- {COLUMN} 1.3.6.1.4.1.248.32.18.2.23.4.1.15
hmSetupInterfacesDslEntryTypeOfInterface OBJECT-TYPE
    SYNTAX     Integer32 (0..2147483647)
    MAX-ACCESS read-only
    STATUS     current
    DESCRIPTION
            "-- empty --"
    ::= { hmSetupInterfacesDslEntry 15 }

-- {COLUMN} 1.3.6.1.4.1.248.32.18.2.23.4.1.16
hmSetupInterfacesDslEntryUpstreamRate OBJECT-TYPE
    SYNTAX     Integer32 (0..2147483647)
    MAX-ACCESS read-write
    STATUS     current
    DESCRIPTION
            "-- empty --"
    ::= { hmSetupInterfacesDslEntry 16 }

-- {COLUMN} 1.3.6.1.4.1.248.32.18.2.23.4.1.17
hmSetupInterfacesDslEntryExtOverhead OBJECT-TYPE
    SYNTAX     Integer32 (0..2147483647)
    MAX-ACCESS read-write
    STATUS     current
    DESCRIPTION
            "-- empty --"
    ::= { hmSetupInterfacesDslEntry 17 }

-- {COLUMN} 1.3.6.1.4.1.248.32.18.2.23.4.1.18
hmSetupInterfacesDslEntryDownstreamRate OBJECT-TYPE
    SYNTAX     Integer32 (0..2147483647)
    MAX-ACCESS read-write
    STATUS     current
    DESCRIPTION
            "-- empty --"
    ::= { hmSetupInterfacesDslEntry 18 }

-- {TABLE} 1.3.6.1.4.1.248.32.18.2.23.7
hmSetupInterfacesModemMobileTable OBJECT-TYPE
    SYNTAX     SEQUENCE OF HmSetupInterfacesModemMobileEntry
    MAX-ACCESS not-accessible
    STATUS     current
    DESCRIPTION
            "-- empty --"
    ::= { hmSetupInterfaces 7 }

-- {ROW} 1.3.6.1.4.1.248.32.18.2.23.7.1
hmSetupInterfacesModemMobileEntry OBJECT-TYPE
    SYNTAX     HmSetupInterfacesModemMobileEntry
    MAX-ACCESS not-accessible
    STATUS     current
    DESCRIPTION
            ""
    INDEX {
            hmSetupInterfacesModemMobileEntryIfc
          }
    ::= { hmSetupInterfacesModemMobileTable 1 }

HmSetupInterfacesModemMobileEntry ::= SEQUENCE {
            hmSetupInterfacesModemMobileEntryIfc INTEGER,
            hmSetupInterfacesModemMobileEntryOperating INTEGER,
            hmSetupInterfacesModemMobileEntryTypeOfInterface Integer32,
            hmSetupInterfacesModemMobileEntryDataRate INTEGER,
            hmSetupInterfacesModemMobileEntryProfile DisplayString
    }

-- {COLUMN} 1.3.6.1.4.1.248.32.18.2.23.7.1.1
hmSetupInterfacesModemMobileEntryIfc OBJECT-TYPE
    SYNTAX     INTEGER {
                  eModem (513),
                  eDsl1 (2049),
                  eDsl2 (2050),
                  eDsl3 (2051),
                  eDsl4 (2052)
            }
    MAX-ACCESS read-only
    STATUS     current
    DESCRIPTION
            "-- empty --"
    ::= { hmSetupInterfacesModemMobileEntry 1 }

-- {COLUMN} 1.3.6.1.4.1.248.32.18.2.23.7.1.2
hmSetupInterfacesModemMobileEntryOperating OBJECT-TYPE
    SYNTAX     INTEGER {
                  eNo (0),
                  eModem (1),
                  eWwan (2)
            }
    MAX-ACCESS read-write
    STATUS     current
    DESCRIPTION
            "-- empty --"
    ::= { hmSetupInterfacesModemMobileEntry 2 }

-- {COLUMN} 1.3.6.1.4.1.248.32.18.2.23.7.1.15
hmSetupInterfacesModemMobileEntryTypeOfInterface OBJECT-TYPE
    SYNTAX     Integer32 (0..2147483647)
    MAX-ACCESS read-only
    STATUS     current
    DESCRIPTION
            "-- empty --"
    ::= { hmSetupInterfacesModemMobileEntry 15 }

-- {COLUMN} 1.3.6.1.4.1.248.32.18.2.23.7.1.21
hmSetupInterfacesModemMobileEntryDataRate OBJECT-TYPE
    SYNTAX     INTEGER {
                  e19200 (19200),
                  e38400 (38400),
                  e57600 (57600),
                  e115200 (115200)
            }
    MAX-ACCESS read-write
    STATUS     current
    DESCRIPTION
            "-- empty --"
    ::= { hmSetupInterfacesModemMobileEntry 21 }

-- {COLUMN} 1.3.6.1.4.1.248.32.18.2.23.7.1.22
hmSetupInterfacesModemMobileEntryProfile OBJECT-TYPE
    SYNTAX     DisplayString (SIZE(0..16))
    MAX-ACCESS read-write
    STATUS     current
    DESCRIPTION
            "-- empty --"
    ::= { hmSetupInterfacesModemMobileEntry 22 }

-- {NODE} 1.3.6.1.4.1.248.32.18.2.23.20
hmSetupInterfacesWlan OBJECT IDENTIFIER ::= { hmSetupInterfaces 20 }

-- {TABLE} 1.3.6.1.4.1.248.32.18.2.23.20.1
hmSetupInterfacesWlanNetworkTable OBJECT-TYPE
    SYNTAX     SEQUENCE OF HmSetupInterfacesWlanNetworkEntry
    MAX-ACCESS not-accessible
    STATUS     current
    DESCRIPTION
            "-- empty --"
    ::= { hmSetupInterfacesWlan 1 }

-- {ROW} 1.3.6.1.4.1.248.32.18.2.23.20.1.1
hmSetupInterfacesWlanNetworkEntry OBJECT-TYPE
    SYNTAX     HmSetupInterfacesWlanNetworkEntry
    MAX-ACCESS not-accessible
    STATUS     current
    DESCRIPTION
            ""
    INDEX {
            hmSetupInterfacesWlanNetworkEntryIfc
          }
    ::= { hmSetupInterfacesWlanNetworkTable 1 }

HmSetupInterfacesWlanNetworkEntry ::= SEQUENCE {
            hmSetupInterfacesWlanNetworkEntryIfc INTEGER,
            hmSetupInterfacesWlanNetworkEntryNetworkName DisplayString,
            hmSetupInterfacesWlanNetworkEntryClosedNetwork INTEGER,
            hmSetupInterfacesWlanNetworkEntryOperating INTEGER,
            hmSetupInterfacesWlanNetworkEntryMacFilter INTEGER,
            hmSetupInterfacesWlanNetworkEntryMaxStations Integer32,
            hmSetupInterfacesWlanNetworkEntryClBrgSupport INTEGER,
            hmSetupInterfacesWlanNetworkEntryRadiusAccounting INTEGER,
            hmSetupInterfacesWlanNetworkEntryInterStationTraffic INTEGER,
            hmSetupInterfacesWlanNetworkEntryApsd INTEGER,
            hmSetupInterfacesWlanNetworkEntryAironetExtensions INTEGER,
            hmSetupInterfacesWlanNetworkEntryMinClientStrength Integer32,
            hmSetupInterfacesWlanNetworkEntryIncludeUuid INTEGER,
            hmSetupInterfacesWlanNetworkEntryTransmitOnlyUnicasts INTEGER,
            hmSetupInterfacesWlanNetworkEntryTxLimit Integer32,
            hmSetupInterfacesWlanNetworkEntryRxLimit Integer32,
            hmSetupInterfacesWlanNetworkEntryAccountingServer DisplayString,
            hmSetupInterfacesWlanNetworkEntryPerClientTxLimit Integer32,
            hmSetupInterfacesWlanNetworkEntryPerClientRxLimit Integer32,
            hmSetupInterfacesWlanNetworkEntryClBrgRoamingSupport INTEGER
    }

-- {COLUMN} 1.3.6.1.4.1.248.32.18.2.23.20.1.1.1
hmSetupInterfacesWlanNetworkEntryIfc OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan22 (32),
                  eWlan23 (33),
                  eWlan24 (34),
                  eWlan25 (35),
                  eWlan26 (36),
                  eWlan27 (37),
                  eWlan28 (38)
            }
    MAX-ACCESS read-write
    STATUS     current
    DESCRIPTION
            "-- empty --"
    ::= { hmSetupInterfacesWlanNetworkEntry 1 }

-- {COLUMN} 1.3.6.1.4.1.248.32.18.2.23.20.1.1.2
hmSetupInterfacesWlanNetworkEntryNetworkName OBJECT-TYPE
    SYNTAX     DisplayString (SIZE(0..32))
    MAX-ACCESS read-write
    STATUS     current
    DESCRIPTION
            "-- empty --"
    ::= { hmSetupInterfacesWlanNetworkEntry 2 }

-- {COLUMN} 1.3.6.1.4.1.248.32.18.2.23.20.1.1.4
hmSetupInterfacesWlanNetworkEntryClosedNetwork OBJECT-TYPE
    SYNTAX     INTEGER {
                  eNo (0),
                  eYes (1),
                  eTightened (2)
            }
    MAX-ACCESS read-write
    STATUS     current
    DESCRIPTION
            "-- empty --"
    ::= { hmSetupInterfacesWlanNetworkEntry 4 }

-- {COLUMN} 1.3.6.1.4.1.248.32.18.2.23.20.1.1.8
hmSetupInterfacesWlanNetworkEntryOperating OBJECT-TYPE
    SYNTAX     INTEGER {
                  eYes (0),
                  eNo (1)
            }
    MAX-ACCESS read-write
    STATUS     current
    DESCRIPTION
            "-- empty --"
    ::= { hmSetupInterfacesWlanNetworkEntry 8 }

-- {COLUMN} 1.3.6.1.4.1.248.32.18.2.23.20.1.1.9
hmSetupInterfacesWlanNetworkEntryMacFilter OBJECT-TYPE
    SYNTAX     INTEGER {
                  eYes (0),
                  eNo (1),
                  eLocalOnly (2),
                  eRadiusOnly (3)
            }
    MAX-ACCESS read-write
    STATUS     current
    DESCRIPTION
            "-- empty --"
    ::= { hmSetupInterfacesWlanNetworkEntry 9 }

-- {COLUMN} 1.3.6.1.4.1.248.32.18.2.23.20.1.1.10
hmSetupInterfacesWlanNetworkEntryMaxStations OBJECT-TYPE
    SYNTAX     Integer32 (0..65535)
    MAX-ACCESS read-write
    STATUS     current
    DESCRIPTION
            "-- empty --"
    ::= { hmSetupInterfacesWlanNetworkEntry 10 }

-- {COLUMN} 1.3.6.1.4.1.248.32.18.2.23.20.1.1.11
hmSetupInterfacesWlanNetworkEntryClBrgSupport OBJECT-TYPE
    SYNTAX     INTEGER {
                  eNo (0),
                  eYes (1),
                  eExclusive (2)
            }
    MAX-ACCESS read-write
    STATUS     current
    DESCRIPTION
            "-- empty --"
    ::= { hmSetupInterfacesWlanNetworkEntry 11 }

-- {COLUMN} 1.3.6.1.4.1.248.32.18.2.23.20.1.1.12
hmSetupInterfacesWlanNetworkEntryRadiusAccounting OBJECT-TYPE
    SYNTAX     INTEGER {
                  eNo (0),
                  eYes (1)
            }
    MAX-ACCESS read-write
    STATUS     current
    DESCRIPTION
            "-- empty --"
    ::= { hmSetupInterfacesWlanNetworkEntry 12 }

-- {COLUMN} 1.3.6.1.4.1.248.32.18.2.23.20.1.1.13
hmSetupInterfacesWlanNetworkEntryInterStationTraffic OBJECT-TYPE
    SYNTAX     INTEGER {
                  eNo (0),
                  eYes (1)
            }
    MAX-ACCESS read-write
    STATUS     current
    DESCRIPTION
            "-- empty --"
    ::= { hmSetupInterfacesWlanNetworkEntry 13 }

-- {COLUMN} 1.3.6.1.4.1.248.32.18.2.23.20.1.1.14
hmSetupInterfacesWlanNetworkEntryApsd OBJECT-TYPE
    SYNTAX     INTEGER {
                  eNo (0),
                  eYes (1)
            }
    MAX-ACCESS read-write
    STATUS     current
    DESCRIPTION
            "-- empty --"
    ::= { hmSetupInterfacesWlanNetworkEntry 14 }

-- {COLUMN} 1.3.6.1.4.1.248.32.18.2.23.20.1.1.15
hmSetupInterfacesWlanNetworkEntryAironetExtensions OBJECT-TYPE
    SYNTAX     INTEGER {
                  eNo (0),
                  eYes (1)
            }
    MAX-ACCESS read-write
    STATUS     current
    DESCRIPTION
            "-- empty --"
    ::= { hmSetupInterfacesWlanNetworkEntry 15 }

-- {COLUMN} 1.3.6.1.4.1.248.32.18.2.23.20.1.1.16
hmSetupInterfacesWlanNetworkEntryMinClientStrength OBJECT-TYPE
    SYNTAX     Integer32 (0..255)
    MAX-ACCESS read-write
    STATUS     current
    DESCRIPTION
            "-- empty --"
    ::= { hmSetupInterfacesWlanNetworkEntry 16 }

-- {COLUMN} 1.3.6.1.4.1.248.32.18.2.23.20.1.1.17
hmSetupInterfacesWlanNetworkEntryIncludeUuid OBJECT-TYPE
    SYNTAX     INTEGER {
                  eNo (0),
                  eYes (1)
            }
    MAX-ACCESS read-write
    STATUS     current
    DESCRIPTION
            "-- empty --"
    ::= { hmSetupInterfacesWlanNetworkEntry 17 }

-- {COLUMN} 1.3.6.1.4.1.248.32.18.2.23.20.1.1.19
hmSetupInterfacesWlanNetworkEntryTransmitOnlyUnicasts OBJECT-TYPE
    SYNTAX     INTEGER {
                  eNo (0),
                  eYes (1)
            }
    MAX-ACCESS read-write
    STATUS     current
    DESCRIPTION
            "-- empty --"
    ::= { hmSetupInterfacesWlanNetworkEntry 19 }

-- {COLUMN} 1.3.6.1.4.1.248.32.18.2.23.20.1.1.20
hmSetupInterfacesWlanNetworkEntryTxLimit OBJECT-TYPE
    SYNTAX     Integer32 (0..2147483647)
    MAX-ACCESS read-write
    STATUS     current
    DESCRIPTION
            "-- empty --"
    ::= { hmSetupInterfacesWlanNetworkEntry 20 }

-- {COLUMN} 1.3.6.1.4.1.248.32.18.2.23.20.1.1.21
hmSetupInterfacesWlanNetworkEntryRxLimit OBJECT-TYPE
    SYNTAX     Integer32 (0..2147483647)
    MAX-ACCESS read-write
    STATUS     current
    DESCRIPTION
            "-- empty --"
    ::= { hmSetupInterfacesWlanNetworkEntry 21 }

-- {COLUMN} 1.3.6.1.4.1.248.32.18.2.23.20.1.1.22
hmSetupInterfacesWlanNetworkEntryAccountingServer OBJECT-TYPE
    SYNTAX     DisplayString (SIZE(0..16))
    MAX-ACCESS read-write
    STATUS     current
    DESCRIPTION
            "-- empty --"
    ::= { hmSetupInterfacesWlanNetworkEntry 22 }

-- {COLUMN} 1.3.6.1.4.1.248.32.18.2.23.20.1.1.25
hmSetupInterfacesWlanNetworkEntryPerClientTxLimit OBJECT-TYPE
    SYNTAX     Integer32 (0..2147483647)
    MAX-ACCESS read-write
    STATUS     current
    DESCRIPTION
            "-- empty --"
    ::= { hmSetupInterfacesWlanNetworkEntry 25 }

-- {COLUMN} 1.3.6.1.4.1.248.32.18.2.23.20.1.1.26
hmSetupInterfacesWlanNetworkEntryPerClientRxLimit OBJECT-TYPE
    SYNTAX     Integer32 (0..2147483647)
    MAX-ACCESS read-write
    STATUS     current
    DESCRIPTION
            "-- empty --"
    ::= { hmSetupInterfacesWlanNetworkEntry 26 }

-- {COLUMN} 1.3.6.1.4.1.248.32.18.2.23.20.1.1.248
hmSetupInterfacesWlanNetworkEntryClBrgRoamingSupport OBJECT-TYPE
    SYNTAX     INTEGER {
                  eNo (0),
                  eYes (1)
            }
    MAX-ACCESS read-write
    STATUS     current
    DESCRIPTION
            "-- empty --"
    ::= { hmSetupInterfacesWlanNetworkEntry 248 }

-- {TABLE} 1.3.6.1.4.1.248.32.18.2.23.20.2
hmSetupInterfacesWlanTransmissionTable OBJECT-TYPE
    SYNTAX     SEQUENCE OF HmSetupInterfacesWlanTransmissionEntry
    MAX-ACCESS not-accessible
    STATUS     current
    DESCRIPTION
            "-- empty --"
    ::= { hmSetupInterfacesWlan 2 }

-- {ROW} 1.3.6.1.4.1.248.32.18.2.23.20.2.1
hmSetupInterfacesWlanTransmissionEntry OBJECT-TYPE
    SYNTAX     HmSetupInterfacesWlanTransmissionEntry
    MAX-ACCESS not-accessible
    STATUS     current
    DESCRIPTION
            ""
    INDEX {
            hmSetupInterfacesWlanTransmissionEntryIfc
          }
    ::= { hmSetupInterfacesWlanTransmissionTable 1 }

HmSetupInterfacesWlanTransmissionEntry ::= SEQUENCE {
            hmSetupInterfacesWlanTransmissionEntryIfc INTEGER,
            hmSetupInterfacesWlanTransmissionEntryPacketSize Integer32,
            hmSetupInterfacesWlanTransmissionEntryMinTxRate INTEGER,
            hmSetupInterfacesWlanTransmissionEntryBasicRate INTEGER,
            hmSetupInterfacesWlanTransmissionEntryRtsThreshold Integer32,
            hmSetupInterfacesWlanTransmissionEntry11bPreamble INTEGER,
            hmSetupInterfacesWlanTransmissionEntryMaxTxRate INTEGER,
            hmSetupInterfacesWlanTransmissionEntryMinFragLen Integer32,
            hmSetupInterfacesWlanTransmissionEntrySoftRetries Integer32,
            hmSetupInterfacesWlanTransmissionEntryHardRetries Integer32,
            hmSetupInterfacesWlanTransmissionEntryShortGuardInterval INTEGER,
            hmSetupInterfacesWlanTransmissionEntryMaxSpatialStreams INTEGER,
            hmSetupInterfacesWlanTransmissionEntrySendAggregates INTEGER,
            hmSetupInterfacesWlanTransmissionEntryMinHtMcs INTEGER,
            hmSetupInterfacesWlanTransmissionEntryMaxHtMcs INTEGER,
            hmSetupInterfacesWlanTransmissionEntryMinSpatialStreams INTEGER,
            hmSetupInterfacesWlanTransmissionEntryEapolRate INTEGER,
            hmSetupInterfacesWlanTransmissionEntryMaxAggrPacketCount Integer32,
            hmSetupInterfacesWlanTransmissionEntryProberspRetries Integer32,
            hmSetupInterfacesWlanTransmissionEntryReceiveAggregates INTEGER,
            hmSetupInterfacesWlanTransmissionEntryUseStbc INTEGER,
            hmSetupInterfacesWlanTransmissionEntryUseLdpc INTEGER,
            hmSetupInterfacesWlanTransmissionEntryConvertToUnicast BITS
    }

-- {COLUMN} 1.3.6.1.4.1.248.32.18.2.23.20.2.1.1
hmSetupInterfacesWlanTransmissionEntryIfc OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan22 (32),
                  eWlan23 (33),
                  eWlan24 (34),
                  eWlan25 (35),
                  eWlan26 (36),
                  eWlan27 (37),
                  eWlan28 (38)
            }
    MAX-ACCESS read-write
    STATUS     current
    DESCRIPTION
            "-- empty --"
    ::= { hmSetupInterfacesWlanTransmissionEntry 1 }

-- {COLUMN} 1.3.6.1.4.1.248.32.18.2.23.20.2.1.2
hmSetupInterfacesWlanTransmissionEntryPacketSize OBJECT-TYPE
    SYNTAX     Integer32 (0..65535)
    MAX-ACCESS read-write
    STATUS     current
    DESCRIPTION
            "-- empty --"
    ::= { hmSetupInterfacesWlanTransmissionEntry 2 }

-- {COLUMN} 1.3.6.1.4.1.248.32.18.2.23.20.2.1.3
hmSetupInterfacesWlanTransmissionEntryMinTxRate OBJECT-TYPE
    SYNTAX     INTEGER {
                  eAuto (0),
                  e1M (1),
                  e2M (2),
                  e5M5 (4),
                  e11M (6),
                  e6M (8),
                  e9M (9),
                  e12M (10),
                  e18M (11),
                  e24M (12),
                  e36M (13),
                  e48M (14),
                  e54M (15)
            }
    MAX-ACCESS read-write
    STATUS     current
    DESCRIPTION
            "-- empty --"
    ::= { hmSetupInterfacesWlanTransmissionEntry 3 }

-- {COLUMN} 1.3.6.1.4.1.248.32.18.2.23.20.2.1.4
hmSetupInterfacesWlanTransmissionEntryBasicRate OBJECT-TYPE
    SYNTAX     INTEGER {
                  eAuto (0),
                  e1M (1),
                  e2M (2),
                  e5M5 (4),
                  e11M (6),
                  e6M (8),
                  e9M (9),
                  e12M (10),
                  e18M (11),
                  e24M (12),
                  e36M (13),
                  e48M (14),
                  e54M (15)
            }
    MAX-ACCESS read-write
    STATUS     current
    DESCRIPTION
            "-- empty --"
    ::= { hmSetupInterfacesWlanTransmissionEntry 4 }

-- {COLUMN} 1.3.6.1.4.1.248.32.18.2.23.20.2.1.6
hmSetupInterfacesWlanTransmissionEntryRtsThreshold OBJECT-TYPE
    SYNTAX     Integer32 (0..65535)
    MAX-ACCESS read-write
    STATUS     current
    DESCRIPTION
            "-- empty --"
    ::= { hmSetupInterfacesWlanTransmissionEntry 6 }

-- {COLUMN} 1.3.6.1.4.1.248.32.18.2.23.20.2.1.7
hmSetupInterfacesWlanTransmissionEntry11bPreamble OBJECT-TYPE
    SYNTAX     INTEGER {
                  eAuto (0),
                  eLong (1)
            }
    MAX-ACCESS read-write
    STATUS     current
    DESCRIPTION
            "-- empty --"
    ::= { hmSetupInterfacesWlanTransmissionEntry 7 }

-- {COLUMN} 1.3.6.1.4.1.248.32.18.2.23.20.2.1.9
hmSetupInterfacesWlanTransmissionEntryMaxTxRate OBJECT-TYPE
    SYNTAX     INTEGER {
                  eAuto (0),
                  e1M (1),
                  e2M (2),
                  e5M5 (4),
                  e11M (6),
                  e6M (8),
                  e9M (9),
                  e12M (10),
                  e18M (11),
                  e24M (12),
                  e36M (13),
                  e48M (14),
                  e54M (15)
            }
    MAX-ACCESS read-write
    STATUS     current
    DESCRIPTION
            "-- empty --"
    ::= { hmSetupInterfacesWlanTransmissionEntry 9 }

-- {COLUMN} 1.3.6.1.4.1.248.32.18.2.23.20.2.1.10
hmSetupInterfacesWlanTransmissionEntryMinFragLen OBJECT-TYPE
    SYNTAX     Integer32 (0..65535)
    MAX-ACCESS read-write
    STATUS     current
    DESCRIPTION
            "-- empty --"
    ::= { hmSetupInterfacesWlanTransmissionEntry 10 }

-- {COLUMN} 1.3.6.1.4.1.248.32.18.2.23.20.2.1.11
hmSetupInterfacesWlanTransmissionEntrySoftRetries OBJECT-TYPE
    SYNTAX     Integer32 (0..255)
    MAX-ACCESS read-write
    STATUS     current
    DESCRIPTION
            "-- empty --"
    ::= { hmSetupInterfacesWlanTransmissionEntry 11 }

-- {COLUMN} 1.3.6.1.4.1.248.32.18.2.23.20.2.1.12
hmSetupInterfacesWlanTransmissionEntryHardRetries OBJECT-TYPE
    SYNTAX     Integer32 (0..255)
    MAX-ACCESS read-write
    STATUS     current
    DESCRIPTION
            "-- empty --"
    ::= { hmSetupInterfacesWlanTransmissionEntry 12 }

-- {COLUMN} 1.3.6.1.4.1.248.32.18.2.23.20.2.1.13
hmSetupInterfacesWlanTransmissionEntryShortGuardInterval OBJECT-TYPE
    SYNTAX     INTEGER {
                  eAuto (0),
                  eNo (1)
            }
    MAX-ACCESS read-write
    STATUS     current
    DESCRIPTION
            "-- empty --"
    ::= { hmSetupInterfacesWlanTransmissionEntry 13 }

-- {COLUMN} 1.3.6.1.4.1.248.32.18.2.23.20.2.1.14
hmSetupInterfacesWlanTransmissionEntryMaxSpatialStreams OBJECT-TYPE
    SYNTAX     INTEGER {
                  eAuto (0),
                  eOne (1),
                  eTwo (2),
                  eThree (3)
            }
    MAX-ACCESS read-write
    STATUS     current
    DESCRIPTION
            "-- empty --"
    ::= { hmSetupInterfacesWlanTransmissionEntry 14 }

-- {COLUMN} 1.3.6.1.4.1.248.32.18.2.23.20.2.1.15
hmSetupInterfacesWlanTransmissionEntrySendAggregates OBJECT-TYPE
    SYNTAX     INTEGER {
                  eNo (0),
                  eYes (1)
            }
    MAX-ACCESS read-write
    STATUS     current
    DESCRIPTION
            "-- empty --"
    ::= { hmSetupInterfacesWlanTransmissionEntry 15 }

-- {COLUMN} 1.3.6.1.4.1.248.32.18.2.23.20.2.1.16
hmSetupInterfacesWlanTransmissionEntryMinHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-write
    STATUS     current
    DESCRIPTION
            "-- empty --"
    ::= { hmSetupInterfacesWlanTransmissionEntry 16 }

-- {COLUMN} 1.3.6.1.4.1.248.32.18.2.23.20.2.1.17
hmSetupInterfacesWlanTransmissionEntryMaxHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-write
    STATUS     current
    DESCRIPTION
            "-- empty --"
    ::= { hmSetupInterfacesWlanTransmissionEntry 17 }

-- {COLUMN} 1.3.6.1.4.1.248.32.18.2.23.20.2.1.18
hmSetupInterfacesWlanTransmissionEntryMinSpatialStreams OBJECT-TYPE
    SYNTAX     INTEGER {
                  eAuto (0),
                  eOne (1),
                  eTwo (2),
                  eThree (3)
            }
    MAX-ACCESS read-write
    STATUS     current
    DESCRIPTION
            "-- empty --"
    ::= { hmSetupInterfacesWlanTransmissionEntry 18 }

-- {COLUMN} 1.3.6.1.4.1.248.32.18.2.23.20.2.1.19
hmSetupInterfacesWlanTransmissionEntryEapolRate OBJECT-TYPE
    SYNTAX     INTEGER {
                  eLikeData (0),
                  e1M (1),
                  e2M (2),
                  e5M5 (4),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51)
            }
    MAX-ACCESS read-write
    STATUS     current
    DESCRIPTION
            "-- empty --"
    ::= { hmSetupInterfacesWlanTransmissionEntry 19 }

-- {COLUMN} 1.3.6.1.4.1.248.32.18.2.23.20.2.1.20
hmSetupInterfacesWlanTransmissionEntryMaxAggrPacketCount OBJECT-TYPE
    SYNTAX     Integer32 (0..255)
    MAX-ACCESS read-write
    STATUS     current
    DESCRIPTION
            "-- empty --"
    ::= { hmSetupInterfacesWlanTransmissionEntry 20 }

-- {COLUMN} 1.3.6.1.4.1.248.32.18.2.23.20.2.1.21
hmSetupInterfacesWlanTransmissionEntryProberspRetries OBJECT-TYPE
    SYNTAX     Integer32 (0..255)
    MAX-ACCESS read-write
    STATUS     current
    DESCRIPTION
            "-- empty --"
    ::= { hmSetupInterfacesWlanTransmissionEntry 21 }

-- {COLUMN} 1.3.6.1.4.1.248.32.18.2.23.20.2.1.22
hmSetupInterfacesWlanTransmissionEntryReceiveAggregates OBJECT-TYPE
    SYNTAX     INTEGER {
                  eNo (0),
                  eYes (1)
            }
    MAX-ACCESS read-write
    STATUS     current
    DESCRIPTION
            "-- empty --"
    ::= { hmSetupInterfacesWlanTransmissionEntry 22 }

-- {COLUMN} 1.3.6.1.4.1.248.32.18.2.23.20.2.1.23
hmSetupInterfacesWlanTransmissionEntryUseStbc OBJECT-TYPE
    SYNTAX     INTEGER {
                  eNo (0),
                  eYes (1)
            }
    MAX-ACCESS read-write
    STATUS     current
    DESCRIPTION
            "-- empty --"
    ::= { hmSetupInterfacesWlanTransmissionEntry 23 }

-- {COLUMN} 1.3.6.1.4.1.248.32.18.2.23.20.2.1.24
hmSetupInterfacesWlanTransmissionEntryUseLdpc OBJECT-TYPE
    SYNTAX     INTEGER {
                  eNo (0),
                  eYes (1)
            }
    MAX-ACCESS read-write
    STATUS     current
    DESCRIPTION
            "-- empty --"
    ::= { hmSetupInterfacesWlanTransmissionEntry 24 }

-- {COLUMN} 1.3.6.1.4.1.248.32.18.2.23.20.2.1.25
hmSetupInterfacesWlanTransmissionEntryConvertToUnicast OBJECT-TYPE
    SYNTAX     BITS {
                  eDhcp (31)
            }
    MAX-ACCESS read-write
    STATUS     current
    DESCRIPTION
            "-- empty --"
    ::= { hmSetupInterfacesWlanTransmissionEntry 25 }

-- {TABLE} 1.3.6.1.4.1.248.32.18.2.23.20.3
hmSetupInterfacesWlanEncryptionTable OBJECT-TYPE
    SYNTAX     SEQUENCE OF HmSetupInterfacesWlanEncryptionEntry
    MAX-ACCESS not-accessible
    STATUS     current
    DESCRIPTION
            "-- empty --"
    ::= { hmSetupInterfacesWlan 3 }

-- {ROW} 1.3.6.1.4.1.248.32.18.2.23.20.3.1
hmSetupInterfacesWlanEncryptionEntry OBJECT-TYPE
    SYNTAX     HmSetupInterfacesWlanEncryptionEntry
    MAX-ACCESS not-accessible
    STATUS     current
    DESCRIPTION
            ""
    INDEX {
            hmSetupInterfacesWlanEncryptionEntryIfc
          }
    ::= { hmSetupInterfacesWlanEncryptionTable 1 }

HmSetupInterfacesWlanEncryptionEntry ::= SEQUENCE {
            hmSetupInterfacesWlanEncryptionEntryIfc INTEGER,
            hmSetupInterfacesWlanEncryptionEntryEncryption INTEGER,
            hmSetupInterfacesWlanEncryptionEntryDefaultKey Integer32,
            hmSetupInterfacesWlanEncryptionEntryMethod INTEGER,
            hmSetupInterfacesWlanEncryptionEntryAuthentication INTEGER,
            hmSetupInterfacesWlanEncryptionEntryKey DisplayString,
            hmSetupInterfacesWlanEncryptionEntryWpaVersion INTEGER,
            hmSetupInterfacesWlanEncryptionEntryClientEapMethod INTEGER,
            hmSetupInterfacesWlanEncryptionEntryWpaRekeyingCycle Integer32,
            hmSetupInterfacesWlanEncryptionEntryWpa1SessionKeytypes INTEGER,
            hmSetupInterfacesWlanEncryptionEntryWpa2SessionKeytypes INTEGER,
            hmSetupInterfacesWlanEncryptionEntryProtMgmtFrames INTEGER,
            hmSetupInterfacesWlanEncryptionEntryPmkCaching INTEGER,
            hmSetupInterfacesWlanEncryptionEntryPreAuthentication INTEGER,
            hmSetupInterfacesWlanEncryptionEntryWpa2KeyManagement BITS,
            hmSetupInterfacesWlanEncryptionEntryOkc INTEGER
    }

-- {COLUMN} 1.3.6.1.4.1.248.32.18.2.23.20.3.1.1
hmSetupInterfacesWlanEncryptionEntryIfc OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan22 (32),
                  eWlan23 (33),
                  eWlan24 (34),
                  eWlan25 (35),
                  eWlan26 (36),
                  eWlan27 (37),
                  eWlan28 (38)
            }
    MAX-ACCESS read-write
    STATUS     current
    DESCRIPTION
            "-- empty --"
    ::= { hmSetupInterfacesWlanEncryptionEntry 1 }

-- {COLUMN} 1.3.6.1.4.1.248.32.18.2.23.20.3.1.2
hmSetupInterfacesWlanEncryptionEntryEncryption OBJECT-TYPE
    SYNTAX     INTEGER {
                  eNo (0),
                  eYes (2)
            }
    MAX-ACCESS read-write
    STATUS     current
    DESCRIPTION
            "-- empty --"
    ::= { hmSetupInterfacesWlanEncryptionEntry 2 }

-- {COLUMN} 1.3.6.1.4.1.248.32.18.2.23.20.3.1.3
hmSetupInterfacesWlanEncryptionEntryDefaultKey OBJECT-TYPE
    SYNTAX     Integer32 (0..255)
    MAX-ACCESS read-write
    STATUS     current
    DESCRIPTION
            "-- empty --"
    ::= { hmSetupInterfacesWlanEncryptionEntry 3 }

-- {COLUMN} 1.3.6.1.4.1.248.32.18.2.23.20.3.1.4
hmSetupInterfacesWlanEncryptionEntryMethod OBJECT-TYPE
    SYNTAX     INTEGER {
                  eWep40Bits (5),
                  eWep104Bits (13),
                  eWep128Bits (16),
                  e80211iWpaPsk (32),
                  e80211iWpa8021x (33),
                  eWep40Bits8021x (34),
                  eWep104Bits8021x (35),
                  eWep128Bits8021x (36)
            }
    MAX-ACCESS read-write
    STATUS     current
    DESCRIPTION
            "-- empty --"
    ::= { hmSetupInterfacesWlanEncryptionEntry 4 }

-- {COLUMN} 1.3.6.1.4.1.248.32.18.2.23.20.3.1.5
hmSetupInterfacesWlanEncryptionEntryAuthentication OBJECT-TYPE
    SYNTAX     INTEGER {
                  eOpenSystem (0),
                  eSharedKey (1)
            }
    MAX-ACCESS read-write
    STATUS     current
    DESCRIPTION
            "-- empty --"
    ::= { hmSetupInterfacesWlanEncryptionEntry 5 }

-- {COLUMN} 1.3.6.1.4.1.248.32.18.2.23.20.3.1.6
hmSetupInterfacesWlanEncryptionEntryKey OBJECT-TYPE
    SYNTAX     DisplayString (SIZE(0..63))
    MAX-ACCESS read-write
    STATUS     current
    DESCRIPTION
            "-- empty --"
    ::= { hmSetupInterfacesWlanEncryptionEntry 6 }

-- {COLUMN} 1.3.6.1.4.1.248.32.18.2.23.20.3.1.9
hmSetupInterfacesWlanEncryptionEntryWpaVersion OBJECT-TYPE
    SYNTAX     INTEGER {
                  eWpa1 (2),
                  eWpa2 (4),
                  eWpa12 (6)
            }
    MAX-ACCESS read-write
    STATUS     current
    DESCRIPTION
            "-- empty --"
    ::= { hmSetupInterfacesWlanEncryptionEntry 9 }

-- {COLUMN} 1.3.6.1.4.1.248.32.18.2.23.20.3.1.10
hmSetupInterfacesWlanEncryptionEntryClientEapMethod OBJECT-TYPE
    SYNTAX     INTEGER {
                  eTls (3328),
                  eTtlsMd5 (5380),
                  eTtlsPap (5383),
                  eTtlsChap (5384),
                  eTtlsMschapv2 (5402),
                  eTtlsMschap (5567),
                  ePeapGtc (6406),
                  ePeapMschapv2 (6426)
            }
    MAX-ACCESS read-write
    STATUS     current
    DESCRIPTION
            "-- empty --"
    ::= { hmSetupInterfacesWlanEncryptionEntry 10 }

-- {COLUMN} 1.3.6.1.4.1.248.32.18.2.23.20.3.1.11
hmSetupInterfacesWlanEncryptionEntryWpaRekeyingCycle OBJECT-TYPE
    SYNTAX     Integer32 (0..2147483647)
    MAX-ACCESS read-write
    STATUS     current
    DESCRIPTION
            "-- empty --"
    ::= { hmSetupInterfacesWlanEncryptionEntry 11 }

-- {COLUMN} 1.3.6.1.4.1.248.32.18.2.23.20.3.1.12
hmSetupInterfacesWlanEncryptionEntryWpa1SessionKeytypes OBJECT-TYPE
    SYNTAX     INTEGER {
                  eTkip (1),
                  eAes (2),
                  eTkipAes (3)
            }
    MAX-ACCESS read-write
    STATUS     current
    DESCRIPTION
            "-- empty --"
    ::= { hmSetupInterfacesWlanEncryptionEntry 12 }

-- {COLUMN} 1.3.6.1.4.1.248.32.18.2.23.20.3.1.13
hmSetupInterfacesWlanEncryptionEntryWpa2SessionKeytypes OBJECT-TYPE
    SYNTAX     INTEGER {
                  eTkip (1),
                  eAes (2),
                  eTkipAes (3)
            }
    MAX-ACCESS read-write
    STATUS     current
    DESCRIPTION
            "-- empty --"
    ::= { hmSetupInterfacesWlanEncryptionEntry 13 }

-- {COLUMN} 1.3.6.1.4.1.248.32.18.2.23.20.3.1.14
hmSetupInterfacesWlanEncryptionEntryProtMgmtFrames OBJECT-TYPE
    SYNTAX     INTEGER {
                  eNo (0),
                  eOptional (1),
                  eMandatory (2)
            }
    MAX-ACCESS read-write
    STATUS     current
    DESCRIPTION
            "-- empty --"
    ::= { hmSetupInterfacesWlanEncryptionEntry 14 }

-- {COLUMN} 1.3.6.1.4.1.248.32.18.2.23.20.3.1.15
hmSetupInterfacesWlanEncryptionEntryPmkCaching OBJECT-TYPE
    SYNTAX     INTEGER {
                  eNo (0),
                  eYes (1)
            }
    MAX-ACCESS read-write
    STATUS     current
    DESCRIPTION
            "-- empty --"
    ::= { hmSetupInterfacesWlanEncryptionEntry 15 }

-- {COLUMN} 1.3.6.1.4.1.248.32.18.2.23.20.3.1.16
hmSetupInterfacesWlanEncryptionEntryPreAuthentication OBJECT-TYPE
    SYNTAX     INTEGER {
                  eNo (0),
                  eYes (1)
            }
    MAX-ACCESS read-write
    STATUS     current
    DESCRIPTION
            "-- empty --"
    ::= { hmSetupInterfacesWlanEncryptionEntry 16 }

-- {COLUMN} 1.3.6.1.4.1.248.32.18.2.23.20.3.1.19
hmSetupInterfacesWlanEncryptionEntryWpa2KeyManagement OBJECT-TYPE
    SYNTAX     BITS {
                  eSha256 (5),
                  eFastRoaming (6),
                  eStandard (7)
            }
    MAX-ACCESS read-write
    STATUS     current
    DESCRIPTION
            "-- empty --"
    ::= { hmSetupInterfacesWlanEncryptionEntry 19 }

-- {COLUMN} 1.3.6.1.4.1.248.32.18.2.23.20.3.1.248
hmSetupInterfacesWlanEncryptionEntryOkc OBJECT-TYPE
    SYNTAX     INTEGER {
                  eNo (0),
                  eYes (1)
            }
    MAX-ACCESS read-write
    STATUS     current
    DESCRIPTION
            "-- empty --"
    ::= { hmSetupInterfacesWlanEncryptionEntry 248 }

-- {TABLE} 1.3.6.1.4.1.248.32.18.2.23.20.4
hmSetupInterfacesWlanGroupEncryptionKeysTable OBJECT-TYPE
    SYNTAX     SEQUENCE OF HmSetupInterfacesWlanGroupEncryptionKeysEntry
    MAX-ACCESS not-accessible
    STATUS     current
    DESCRIPTION
            "-- empty --"
    ::= { hmSetupInterfacesWlan 4 }

-- {ROW} 1.3.6.1.4.1.248.32.18.2.23.20.4.1
hmSetupInterfacesWlanGroupEncryptionKeysEntry OBJECT-TYPE
    SYNTAX     HmSetupInterfacesWlanGroupEncryptionKeysEntry
    MAX-ACCESS not-accessible
    STATUS     current
    DESCRIPTION
            ""
    INDEX {
            hmSetupInterfacesWlanGroupEncryptionKeysEntryIfc
          }
    ::= { hmSetupInterfacesWlanGroupEncryptionKeysTable 1 }

HmSetupInterfacesWlanGroupEncryptionKeysEntry ::= SEQUENCE {
            hmSetupInterfacesWlanGroupEncryptionKeysEntryIfc INTEGER,
            hmSetupInterfacesWlanGroupEncryptionKeysEntryKey2 DisplayString,
            hmSetupInterfacesWlanGroupEncryptionKeysEntryKey3 DisplayString,
            hmSetupInterfacesWlanGroupEncryptionKeysEntryKey4 DisplayString,
            hmSetupInterfacesWlanGroupEncryptionKeysEntryKeytype2 INTEGER,
            hmSetupInterfacesWlanGroupEncryptionKeysEntryKeytype3 INTEGER,
            hmSetupInterfacesWlanGroupEncryptionKeysEntryKeytype4 INTEGER
    }

-- {COLUMN} 1.3.6.1.4.1.248.32.18.2.23.20.4.1.1
hmSetupInterfacesWlanGroupEncryptionKeysEntryIfc OBJECT-TYPE
    SYNTAX     INTEGER {
                  eWlan1 (1),
                  eWlan2 (2)
            }
    MAX-ACCESS read-write
    STATUS     current
    DESCRIPTION
            "-- empty --"
    ::= { hmSetupInterfacesWlanGroupEncryptionKeysEntry 1 }

-- {COLUMN} 1.3.6.1.4.1.248.32.18.2.23.20.4.1.3
hmSetupInterfacesWlanGroupEncryptionKeysEntryKey2 OBJECT-TYPE
    SYNTAX     DisplayString (SIZE(0..63))
    MAX-ACCESS read-write
    STATUS     current
    DESCRIPTION
            "-- empty --"
    ::= { hmSetupInterfacesWlanGroupEncryptionKeysEntry 3 }

-- {COLUMN} 1.3.6.1.4.1.248.32.18.2.23.20.4.1.4
hmSetupInterfacesWlanGroupEncryptionKeysEntryKey3 OBJECT-TYPE
    SYNTAX     DisplayString (SIZE(0..63))
    MAX-ACCESS read-write
    STATUS     current
    DESCRIPTION
            "-- empty --"
    ::= { hmSetupInterfacesWlanGroupEncryptionKeysEntry 4 }

-- {COLUMN} 1.3.6.1.4.1.248.32.18.2.23.20.4.1.5
hmSetupInterfacesWlanGroupEncryptionKeysEntryKey4 OBJECT-TYPE
    SYNTAX     DisplayString (SIZE(0..63))
    MAX-ACCESS read-write
    STATUS     current
    DESCRIPTION
            "-- empty --"
    ::= { hmSetupInterfacesWlanGroupEncryptionKeysEntry 5 }

-- {COLUMN} 1.3.6.1.4.1.248.32.18.2.23.20.4.1.7
hmSetupInterfacesWlanGroupEncryptionKeysEntryKeytype2 OBJECT-TYPE
    SYNTAX     INTEGER {
                  eWep40Bits (5),
                  eWep104Bits (13),
                  eWep128Bits (16)
            }
    MAX-ACCESS read-write
    STATUS     current
    DESCRIPTION
            "-- empty --"
    ::= { hmSetupInterfacesWlanGroupEncryptionKeysEntry 7 }

-- {COLUMN} 1.3.6.1.4.1.248.32.18.2.23.20.4.1.8
hmSetupInterfacesWlanGroupEncryptionKeysEntryKeytype3 OBJECT-TYPE
    SYNTAX     INTEGER {
                  eWep40Bits (5),
                  eWep104Bits (13),
                  eWep128Bits (16)
            }
    MAX-ACCESS read-write
    STATUS     current
    DESCRIPTION
            "-- empty --"
    ::= { hmSetupInterfacesWlanGroupEncryptionKeysEntry 8 }

-- {COLUMN} 1.3.6.1.4.1.248.32.18.2.23.20.4.1.9
hmSetupInterfacesWlanGroupEncryptionKeysEntryKeytype4 OBJECT-TYPE
    SYNTAX     INTEGER {
                  eWep40Bits (5),
                  eWep104Bits (13),
                  eWep128Bits (16)
            }
    MAX-ACCESS read-write
    STATUS     current
    DESCRIPTION
            "-- empty --"
    ::= { hmSetupInterfacesWlanGroupEncryptionKeysEntry 9 }

-- {TABLE} 1.3.6.1.4.1.248.32.18.2.23.20.5
hmSetupInterfacesWlanIntpntSetTable OBJECT-TYPE
    SYNTAX     SEQUENCE OF HmSetupInterfacesWlanIntpntSetEntry
    MAX-ACCESS not-accessible
    STATUS     current
    DESCRIPTION
            ""
    ::= { hmSetupInterfacesWlan 5 }

-- {ROW} 1.3.6.1.4.1.248.32.18.2.23.20.5.1
hmSetupInterfacesWlanIntpntSetEntry OBJECT-TYPE
    SYNTAX     HmSetupInterfacesWlanIntpntSetEntry
    MAX-ACCESS not-accessible
    STATUS     current
    DESCRIPTION
            ""
    INDEX {
            hmSetupInterfacesWlanIntpntSetEntryIfc
          }
    ::= { hmSetupInterfacesWlanIntpntSetTable 1 }

HmSetupInterfacesWlanIntpntSetEntry ::= SEQUENCE {
            hmSetupInterfacesWlanIntpntSetEntryIfc INTEGER,
            hmSetupInterfacesWlanIntpntSetEntryEnable INTEGER,
            hmSetupInterfacesWlanIntpntSetEntryIsolatedMode INTEGER,
            hmSetupInterfacesWlanIntpntSetEntryChanSelScheme INTEGER,
            hmSetupInterfacesWlanIntpntSetEntryLinkLossTimeout Integer32,
            hmSetupInterfacesWlanIntpntSetEntryKeyHandshakeRole INTEGER,
            hmSetupInterfacesWlanIntpntSetEntryLocalName DisplayString,
            hmSetupInterfacesWlanIntpntSetEntryRemoteStatusReporting INTEGER,
            hmSetupInterfacesWlanIntpntSetEntryNetworkName DisplayString,
            hmSetupInterfacesWlanIntpntSetEntryC2cIdentifier DisplayString
    }

-- {COLUMN} 1.3.6.1.4.1.248.32.18.2.23.20.5.1.1
hmSetupInterfacesWlanIntpntSetEntryIfc OBJECT-TYPE
    SYNTAX     INTEGER {
                  eWlan1 (1),
                  eWlan2 (2)
            }
    MAX-ACCESS read-write
    STATUS     current
    DESCRIPTION
            "-- empty --"
    ::= { hmSetupInterfacesWlanIntpntSetEntry 1 }

-- {COLUMN} 1.3.6.1.4.1.248.32.18.2.23.20.5.1.2
hmSetupInterfacesWlanIntpntSetEntryEnable OBJECT-TYPE
    SYNTAX     INTEGER {
                  eNo (0),
                  eYes (1),
                  eExclusive (2)
            }
    MAX-ACCESS read-write
    STATUS     current
    DESCRIPTION
            "-- empty --"
    ::= { hmSetupInterfacesWlanIntpntSetEntry 2 }

-- {COLUMN} 1.3.6.1.4.1.248.32.18.2.23.20.5.1.9
hmSetupInterfacesWlanIntpntSetEntryIsolatedMode OBJECT-TYPE
    SYNTAX     INTEGER {
                  eNo (0),
                  eYes (1)
            }
    MAX-ACCESS read-write
    STATUS     current
    DESCRIPTION
            "-- empty --"
    ::= { hmSetupInterfacesWlanIntpntSetEntry 9 }

-- {COLUMN} 1.3.6.1.4.1.248.32.18.2.23.20.5.1.10
hmSetupInterfacesWlanIntpntSetEntryChanSelScheme OBJECT-TYPE
    SYNTAX     INTEGER {
                  eMaster (0),
                  eSlave (1)
            }
    MAX-ACCESS read-write
    STATUS     current
    DESCRIPTION
            ""
    ::= { hmSetupInterfacesWlanIntpntSetEntry 10 }

-- {COLUMN} 1.3.6.1.4.1.248.32.18.2.23.20.5.1.11
hmSetupInterfacesWlanIntpntSetEntryLinkLossTimeout OBJECT-TYPE
    SYNTAX     Integer32 (0..2147483647)
    MAX-ACCESS read-write
    STATUS     current
    DESCRIPTION
            "-- empty --"
    ::= { hmSetupInterfacesWlanIntpntSetEntry 11 }

-- {COLUMN} 1.3.6.1.4.1.248.32.18.2.23.20.5.1.12
hmSetupInterfacesWlanIntpntSetEntryKeyHandshakeRole OBJECT-TYPE
    SYNTAX     INTEGER {
                  eDefault (0),
                  eAuto (3)
            }
    MAX-ACCESS read-write
    STATUS     current
    DESCRIPTION
            "-- empty --"
    ::= { hmSetupInterfacesWlanIntpntSetEntry 12 }

-- {COLUMN} 1.3.6.1.4.1.248.32.18.2.23.20.5.1.13
hmSetupInterfacesWlanIntpntSetEntryLocalName OBJECT-TYPE
    SYNTAX     DisplayString (SIZE(0..24))
    MAX-ACCESS read-write
    STATUS     current
    DESCRIPTION
            "-- empty --"
    ::= { hmSetupInterfacesWlanIntpntSetEntry 13 }

-- {COLUMN} 1.3.6.1.4.1.248.32.18.2.23.20.5.1.14
hmSetupInterfacesWlanIntpntSetEntryRemoteStatusReporting OBJECT-TYPE
    SYNTAX     INTEGER {
                  eNo (0),
                  eYes (1)
            }
    MAX-ACCESS read-write
    STATUS     current
    DESCRIPTION
            "-- empty --"
    ::= { hmSetupInterfacesWlanIntpntSetEntry 14 }

-- {COLUMN} 1.3.6.1.4.1.248.32.18.2.23.20.5.1.15
hmSetupInterfacesWlanIntpntSetEntryNetworkName OBJECT-TYPE
    SYNTAX     DisplayString (SIZE(0..32))
    MAX-ACCESS read-write
    STATUS     current
    DESCRIPTION
            "-- empty --"
    ::= { hmSetupInterfacesWlanIntpntSetEntry 15 }

-- {COLUMN} 1.3.6.1.4.1.248.32.18.2.23.20.5.1.248
hmSetupInterfacesWlanIntpntSetEntryC2cIdentifier OBJECT-TYPE
    SYNTAX     DisplayString (SIZE(0..24))
    MAX-ACCESS read-write
    STATUS     current
    DESCRIPTION
            "-- empty --"
    ::= { hmSetupInterfacesWlanIntpntSetEntry 248 }

-- {TABLE} 1.3.6.1.4.1.248.32.18.2.23.20.6
hmSetupInterfacesWlanClientModesTable OBJECT-TYPE
    SYNTAX     SEQUENCE OF HmSetupInterfacesWlanClientModesEntry
    MAX-ACCESS not-accessible
    STATUS     current
    DESCRIPTION
            "-- empty --"
    ::= { hmSetupInterfacesWlan 6 }

-- {ROW} 1.3.6.1.4.1.248.32.18.2.23.20.6.1
hmSetupInterfacesWlanClientModesEntry OBJECT-TYPE
    SYNTAX     HmSetupInterfacesWlanClientModesEntry
    MAX-ACCESS not-accessible
    STATUS     current
    DESCRIPTION
            ""
    INDEX {
            hmSetupInterfacesWlanClientModesEntryIfc
          }
    ::= { hmSetupInterfacesWlanClientModesTable 1 }

HmSetupInterfacesWlanClientModesEntry ::= SEQUENCE {
            hmSetupInterfacesWlanClientModesEntryIfc INTEGER,
            hmSetupInterfacesWlanClientModesEntryConnectionKeepalive INTEGER,
            hmSetupInterfacesWlanClientModesEntryNetworkTypes INTEGER,
            hmSetupInterfacesWlanClientModesEntryScanBands INTEGER,
            hmSetupInterfacesWlanClientModesEntryPreferredBss MacAddress,
            hmSetupInterfacesWlanClientModesEntryAddressAdaption INTEGER,
            hmSetupInterfacesWlanClientModesEntryClBrgSupport INTEGER,
            hmSetupInterfacesWlanClientModesEntryTxLimit Integer32,
            hmSetupInterfacesWlanClientModesEntryRxLimit Integer32,
            hmSetupInterfacesWlanClientModesEntrySelectionPreference INTEGER,
            hmSetupInterfacesWlanClientModesEntrySendDeauthUpon BITS
    }

-- {COLUMN} 1.3.6.1.4.1.248.32.18.2.23.20.6.1.1
hmSetupInterfacesWlanClientModesEntryIfc OBJECT-TYPE
    SYNTAX     INTEGER {
                  eWlan1 (1),
                  eWlan2 (2)
            }
    MAX-ACCESS read-write
    STATUS     current
    DESCRIPTION
            "-- empty --"
    ::= { hmSetupInterfacesWlanClientModesEntry 1 }

-- {COLUMN} 1.3.6.1.4.1.248.32.18.2.23.20.6.1.3
hmSetupInterfacesWlanClientModesEntryConnectionKeepalive OBJECT-TYPE
    SYNTAX     INTEGER {
                  eNo (0),
                  eYes (1)
            }
    MAX-ACCESS read-write
    STATUS     current
    DESCRIPTION
            "-- empty --"
    ::= { hmSetupInterfacesWlanClientModesEntry 3 }

-- {COLUMN} 1.3.6.1.4.1.248.32.18.2.23.20.6.1.4
hmSetupInterfacesWlanClientModesEntryNetworkTypes OBJECT-TYPE
    SYNTAX     INTEGER {
                  eInfrastructure (4)
            }
    MAX-ACCESS read-write
    STATUS     current
    DESCRIPTION
            "-- empty --"
    ::= { hmSetupInterfacesWlanClientModesEntry 4 }

-- {COLUMN} 1.3.6.1.4.1.248.32.18.2.23.20.6.1.5
hmSetupInterfacesWlanClientModesEntryScanBands OBJECT-TYPE
    SYNTAX     INTEGER {
                  e24ghz (1),
                  e5ghz (2),
                  e24ghz5ghz (3)
            }
    MAX-ACCESS read-write
    STATUS     current
    DESCRIPTION
            "-- empty --"
    ::= { hmSetupInterfacesWlanClientModesEntry 5 }

-- {COLUMN} 1.3.6.1.4.1.248.32.18.2.23.20.6.1.6
hmSetupInterfacesWlanClientModesEntryPreferredBss OBJECT-TYPE
    SYNTAX     MacAddress
    MAX-ACCESS read-write
    STATUS     current
    DESCRIPTION
            "-- empty --"
    ::= { hmSetupInterfacesWlanClientModesEntry 6 }

-- {COLUMN} 1.3.6.1.4.1.248.32.18.2.23.20.6.1.7
hmSetupInterfacesWlanClientModesEntryAddressAdaption OBJECT-TYPE
    SYNTAX     INTEGER {
                  eNo (0),
                  eYes (1)
            }
    MAX-ACCESS read-write
    STATUS     current
    DESCRIPTION
            "-- empty --"
    ::= { hmSetupInterfacesWlanClientModesEntry 7 }

-- {COLUMN} 1.3.6.1.4.1.248.32.18.2.23.20.6.1.8
hmSetupInterfacesWlanClientModesEntryClBrgSupport OBJECT-TYPE
    SYNTAX     INTEGER {
                  eNo (0),
                  eYes (1)
            }
    MAX-ACCESS read-write
    STATUS     current
    DESCRIPTION
            "-- empty --"
    ::= { hmSetupInterfacesWlanClientModesEntry 8 }

-- {COLUMN} 1.3.6.1.4.1.248.32.18.2.23.20.6.1.9
hmSetupInterfacesWlanClientModesEntryTxLimit OBJECT-TYPE
    SYNTAX     Integer32 (0..2147483647)
    MAX-ACCESS read-write
    STATUS     current
    DESCRIPTION
            "-- empty --"
    ::= { hmSetupInterfacesWlanClientModesEntry 9 }

-- {COLUMN} 1.3.6.1.4.1.248.32.18.2.23.20.6.1.10
hmSetupInterfacesWlanClientModesEntryRxLimit OBJECT-TYPE
    SYNTAX     Integer32 (0..2147483647)
    MAX-ACCESS read-write
    STATUS     current
    DESCRIPTION
            "-- empty --"
    ::= { hmSetupInterfacesWlanClientModesEntry 10 }

-- {COLUMN} 1.3.6.1.4.1.248.32.18.2.23.20.6.1.12
hmSetupInterfacesWlanClientModesEntrySelectionPreference OBJECT-TYPE
    SYNTAX     INTEGER {
                  eSignalStrength (0),
                  eProfile (1)
            }
    MAX-ACCESS read-write
    STATUS     current
    DESCRIPTION
            "-- empty --"
    ::= { hmSetupInterfacesWlanClientModesEntry 12 }

-- {COLUMN} 1.3.6.1.4.1.248.32.18.2.23.20.6.1.13
hmSetupInterfacesWlanClientModesEntrySendDeauthUpon OBJECT-TYPE
    SYNTAX     BITS {
                  eNever (0),
                  eAddressChange (30),
                  eDeactivation (31)
            }
    MAX-ACCESS read-write
    STATUS     current
    DESCRIPTION
            "-- empty --"
    ::= { hmSetupInterfacesWlanClientModesEntry 13 }

-- {TABLE} 1.3.6.1.4.1.248.32.18.2.23.20.7
hmSetupInterfacesWlanOperationalTable OBJECT-TYPE
    SYNTAX     SEQUENCE OF HmSetupInterfacesWlanOperationalEntry
    MAX-ACCESS not-accessible
    STATUS     current
    DESCRIPTION
            "-- empty --"
    ::= { hmSetupInterfacesWlan 7 }

-- {ROW} 1.3.6.1.4.1.248.32.18.2.23.20.7.1
hmSetupInterfacesWlanOperationalEntry OBJECT-TYPE
    SYNTAX     HmSetupInterfacesWlanOperationalEntry
    MAX-ACCESS not-accessible
    STATUS     current
    DESCRIPTION
            ""
    INDEX {
            hmSetupInterfacesWlanOperationalEntryIfc
          }
    ::= { hmSetupInterfacesWlanOperationalTable 1 }

HmSetupInterfacesWlanOperationalEntry ::= SEQUENCE {
            hmSetupInterfacesWlanOperationalEntryIfc INTEGER,
            hmSetupInterfacesWlanOperationalEntryOperating INTEGER,
            hmSetupInterfacesWlanOperationalEntryOperationMode INTEGER,
            hmSetupInterfacesWlanOperationalEntryLinkLedFunction INTEGER,
            hmSetupInterfacesWlanOperationalEntryBrokenLinkDetection INTEGER,
            hmSetupInterfacesWlanOperationalEntryAssignment INTEGER
    }

-- {COLUMN} 1.3.6.1.4.1.248.32.18.2.23.20.7.1.1
hmSetupInterfacesWlanOperationalEntryIfc OBJECT-TYPE
    SYNTAX     INTEGER {
                  eWlan1 (1),
                  eWlan2 (2)
            }
    MAX-ACCESS read-write
    STATUS     current
    DESCRIPTION
            "-- empty --"
    ::= { hmSetupInterfacesWlanOperationalEntry 1 }

-- {COLUMN} 1.3.6.1.4.1.248.32.18.2.23.20.7.1.2
hmSetupInterfacesWlanOperationalEntryOperating OBJECT-TYPE
    SYNTAX     INTEGER {
                  eYes (0),
                  eNo (1)
            }
    MAX-ACCESS read-write
    STATUS     current
    DESCRIPTION
            "-- empty --"
    ::= { hmSetupInterfacesWlanOperationalEntry 2 }

-- {COLUMN} 1.3.6.1.4.1.248.32.18.2.23.20.7.1.3
hmSetupInterfacesWlanOperationalEntryOperationMode OBJECT-TYPE
    SYNTAX     INTEGER {
                  eStation (0),
                  eAccessPoint (1),
                  eManagedAp (4),
                  eProbe (5)
            }
    MAX-ACCESS read-write
    STATUS     current
    DESCRIPTION
            "hirschmann's description of operation mode"
    ::= { hmSetupInterfacesWlanOperationalEntry 3 }

-- {COLUMN} 1.3.6.1.4.1.248.32.18.2.23.20.7.1.4
hmSetupInterfacesWlanOperationalEntryLinkLedFunction OBJECT-TYPE
    SYNTAX     INTEGER {
                  eNormal (0),
                  eClientModeStrength (1),
                  eP2p1Strength (8),
                  eP2p2Strength (9),
                  eP2p3Strength (10),
                  eP2p4Strength (11),
                  eP2p5Strength (12),
                  eP2p6Strength (13),
                  eP2p7Strength (14),
                  eP2p8Strength (15),
                  eP2p9Strength (16),
                  eP2p10Strength (17),
                  eP2p11Strength (18),
                  eP2p12Strength (19),
                  eP2p13Strength (20),
                  eP2p14Strength (21),
                  eP2p15Strength (22),
                  eP2p16Strength (23)
            }
    MAX-ACCESS read-write
    STATUS     current
    DESCRIPTION
            "-- empty --"
    ::= { hmSetupInterfacesWlanOperationalEntry 4 }

-- {COLUMN} 1.3.6.1.4.1.248.32.18.2.23.20.7.1.5
hmSetupInterfacesWlanOperationalEntryBrokenLinkDetection OBJECT-TYPE
    SYNTAX     INTEGER {
                  eNo (0),
                  eLan1 (1),
                  eLan2 (2)
            }
    MAX-ACCESS read-write
    STATUS     current
    DESCRIPTION
            "-- empty --"
    ::= { hmSetupInterfacesWlanOperationalEntry 5 }

-- {COLUMN} 1.3.6.1.4.1.248.32.18.2.23.20.7.1.248
hmSetupInterfacesWlanOperationalEntryAssignment OBJECT-TYPE
    SYNTAX     INTEGER {
                  eWlan (0),
                  eDsl1 (1)
            }
    MAX-ACCESS read-write
    STATUS     current
    DESCRIPTION
            "-- empty --"
    ::= { hmSetupInterfacesWlanOperationalEntry 248 }

-- {TABLE} 1.3.6.1.4.1.248.32.18.2.23.20.8
hmSetupInterfacesWlanRadioSettingsTable OBJECT-TYPE
    SYNTAX     SEQUENCE OF HmSetupInterfacesWlanRadioSettingsEntry
    MAX-ACCESS not-accessible
    STATUS     current
    DESCRIPTION
            "-- empty --"
    ::= { hmSetupInterfacesWlan 8 }

-- {ROW} 1.3.6.1.4.1.248.32.18.2.23.20.8.1
hmSetupInterfacesWlanRadioSettingsEntry OBJECT-TYPE
    SYNTAX     HmSetupInterfacesWlanRadioSettingsEntry
    MAX-ACCESS not-accessible
    STATUS     current
    DESCRIPTION
            ""
    INDEX {
            hmSetupInterfacesWlanRadioSettingsEntryIfc
          }
    ::= { hmSetupInterfacesWlanRadioSettingsTable 1 }

HmSetupInterfacesWlanRadioSettingsEntry ::= SEQUENCE {
            hmSetupInterfacesWlanRadioSettingsEntryIfc INTEGER,
            hmSetupInterfacesWlanRadioSettingsEntryTxPowerReduction Integer32,
            hmSetupInterfacesWlanRadioSettingsEntry5ghzMode INTEGER,
            hmSetupInterfacesWlanRadioSettingsEntryMaximumDistance Integer32,
            hmSetupInterfacesWlanRadioSettingsEntryRadioBand INTEGER,
            hmSetupInterfacesWlanRadioSettingsEntrySubbands INTEGER,
            hmSetupInterfacesWlanRadioSettingsEntryRadioChannel Integer32,
            hmSetupInterfacesWlanRadioSettingsEntry24ghzMode INTEGER,
            hmSetupInterfacesWlanRadioSettingsEntryApDensity INTEGER,
            hmSetupInterfacesWlanRadioSettingsEntryAntennaGain Integer32,
            hmSetupInterfacesWlanRadioSettingsEntryChannelList DisplayString,
            hmSetupInterfacesWlanRadioSettingsEntryBackgroundScan Integer32,
            hmSetupInterfacesWlanRadioSettingsEntryDfsRescanHours DisplayString,
            hmSetupInterfacesWlanRadioSettingsEntryAllow40mhz INTEGER,
            hmSetupInterfacesWlanRadioSettingsEntryAntennaMask INTEGER,
            hmSetupInterfacesWlanRadioSettingsEntryBackgroundScanUnit INTEGER,
            hmSetupInterfacesWlanRadioSettingsEntryChannelPairing INTEGER,
            hmSetupInterfacesWlanRadioSettingsEntryPreferredDfsScheme INTEGER,
            hmSetupInterfacesWlanRadioSettingsEntryCacDuration Integer32,
            hmSetupInterfacesWlanRadioSettingsEntryForce40mhz INTEGER,
            hmSetupInterfacesWlanRadioSettingsEntryAdaptiveNoiseImmunity INTEGER,
            hmSetupInterfacesWlanRadioSettingsEntryMaxChannelBandwidth INTEGER,
            hmSetupInterfacesWlanRadioSettingsEntryAllowPhyRestarts INTEGER,
            hmSetupInterfacesWlanRadioSettingsEntryDfsRscFlClChan INTEGER,
            hmSetupInterfacesWlanRadioSettingsEntryDfsRescanNumChannels Integer32,
            hmSetupInterfacesWlanRadioSettingsEntryPreferred24Scheme INTEGER,
            hmSetupInterfacesWlanRadioSettingsEntryPassiveScanDuration Integer32
    }

-- {COLUMN} 1.3.6.1.4.1.248.32.18.2.23.20.8.1.1
hmSetupInterfacesWlanRadioSettingsEntryIfc OBJECT-TYPE
    SYNTAX     INTEGER {
                  eWlan1 (1),
                  eWlan2 (2)
            }
    MAX-ACCESS read-write
    STATUS     current
    DESCRIPTION
            "-- empty --"
    ::= { hmSetupInterfacesWlanRadioSettingsEntry 1 }

-- {COLUMN} 1.3.6.1.4.1.248.32.18.2.23.20.8.1.2
hmSetupInterfacesWlanRadioSettingsEntryTxPowerReduction OBJECT-TYPE
    SYNTAX     Integer32 (0..255)
    MAX-ACCESS read-write
    STATUS     current
    DESCRIPTION
            "-- empty --"
    ::= { hmSetupInterfacesWlanRadioSettingsEntry 2 }

-- {COLUMN} 1.3.6.1.4.1.248.32.18.2.23.20.8.1.3
hmSetupInterfacesWlanRadioSettingsEntry5ghzMode OBJECT-TYPE
    SYNTAX     INTEGER {
                  eNormal (0),
                  e11anMixed (3),
                  eGreenfield (4),
                  eAuto (255)
            }
    MAX-ACCESS read-write
    STATUS     current
    DESCRIPTION
            "-- empty --"
    ::= { hmSetupInterfacesWlanRadioSettingsEntry 3 }

-- {COLUMN} 1.3.6.1.4.1.248.32.18.2.23.20.8.1.4
hmSetupInterfacesWlanRadioSettingsEntryMaximumDistance OBJECT-TYPE
    SYNTAX     Integer32 (0..65535)
    MAX-ACCESS read-write
    STATUS     current
    DESCRIPTION
            "-- empty --"
    ::= { hmSetupInterfacesWlanRadioSettingsEntry 4 }

-- {COLUMN} 1.3.6.1.4.1.248.32.18.2.23.20.8.1.6
hmSetupInterfacesWlanRadioSettingsEntryRadioBand OBJECT-TYPE
    SYNTAX     INTEGER {
                  e24ghz (1),
                  e5ghz (2)
            }
    MAX-ACCESS read-write
    STATUS     current
    DESCRIPTION
            "-- empty --"
    ::= { hmSetupInterfacesWlanRadioSettingsEntry 6 }

-- {COLUMN} 1.3.6.1.4.1.248.32.18.2.23.20.8.1.7
hmSetupInterfacesWlanRadioSettingsEntrySubbands OBJECT-TYPE
    SYNTAX     INTEGER {
                  eBand1 (1),
                  eBand2 (2),
                  eBand1Plus2 (3),
                  eBand3 (4),
                  eBand1Plus3 (5),
                  eBand2Plus3 (6),
                  eBand1Plus2Plus3 (7)
            }
    MAX-ACCESS read-write
    STATUS     current
    DESCRIPTION
            "-- empty --"
    ::= { hmSetupInterfacesWlanRadioSettingsEntry 7 }

-- {COLUMN} 1.3.6.1.4.1.248.32.18.2.23.20.8.1.8
hmSetupInterfacesWlanRadioSettingsEntryRadioChannel OBJECT-TYPE
    SYNTAX     Integer32 (0..255)
    MAX-ACCESS read-write
    STATUS     current
    DESCRIPTION
            "-- empty --"
    ::= { hmSetupInterfacesWlanRadioSettingsEntry 8 }

-- {COLUMN} 1.3.6.1.4.1.248.32.18.2.23.20.8.1.9
hmSetupInterfacesWlanRadioSettingsEntry24ghzMode OBJECT-TYPE
    SYNTAX     INTEGER {
                  e11bgMixed (0),
                  e11gOnly (1),
                  e11bOnly (2),
                  e2mMixed (3),
                  e11bgnMixed (5),
                  e2m11bgnMixed (6),
                  e11gnMixed (7),
                  eGreenfield (8),
                  eAuto (255)
            }
    MAX-ACCESS read-write
    STATUS     current
    DESCRIPTION
            "-- empty --"
    ::= { hmSetupInterfacesWlanRadioSettingsEntry 9 }

-- {COLUMN} 1.3.6.1.4.1.248.32.18.2.23.20.8.1.10
hmSetupInterfacesWlanRadioSettingsEntryApDensity OBJECT-TYPE
    SYNTAX     INTEGER {
                  eOff (0),
                  eLow (1),
                  eMedium (2),
                  eHigh (3),
                  eMinicell (4),
                  eMicrocell (5)
            }
    MAX-ACCESS read-write
    STATUS     current
    DESCRIPTION
            "-- empty --"
    ::= { hmSetupInterfacesWlanRadioSettingsEntry 10 }

-- {COLUMN} 1.3.6.1.4.1.248.32.18.2.23.20.8.1.12
hmSetupInterfacesWlanRadioSettingsEntryAntennaGain OBJECT-TYPE
    SYNTAX     Integer32 (-128..127)
    MAX-ACCESS read-write
    STATUS     current
    DESCRIPTION
            "-- empty --"
    ::= { hmSetupInterfacesWlanRadioSettingsEntry 12 }

-- {COLUMN} 1.3.6.1.4.1.248.32.18.2.23.20.8.1.13
hmSetupInterfacesWlanRadioSettingsEntryChannelList OBJECT-TYPE
    SYNTAX     DisplayString (SIZE(0..48))
    MAX-ACCESS read-write
    STATUS     current
    DESCRIPTION
            "-- empty --"
    ::= { hmSetupInterfacesWlanRadioSettingsEntry 13 }

-- {COLUMN} 1.3.6.1.4.1.248.32.18.2.23.20.8.1.14
hmSetupInterfacesWlanRadioSettingsEntryBackgroundScan OBJECT-TYPE
    SYNTAX     Integer32 (0..2147483647)
    MAX-ACCESS read-write
    STATUS     current
    DESCRIPTION
            "-- empty --"
    ::= { hmSetupInterfacesWlanRadioSettingsEntry 14 }

-- {COLUMN} 1.3.6.1.4.1.248.32.18.2.23.20.8.1.15
hmSetupInterfacesWlanRadioSettingsEntryDfsRescanHours OBJECT-TYPE
    SYNTAX     DisplayString (SIZE(0..19))
    MAX-ACCESS read-write
    STATUS     current
    DESCRIPTION
            "-- empty --"
    ::= { hmSetupInterfacesWlanRadioSettingsEntry 15 }

-- {COLUMN} 1.3.6.1.4.1.248.32.18.2.23.20.8.1.16
hmSetupInterfacesWlanRadioSettingsEntryAllow40mhz OBJECT-TYPE
    SYNTAX     INTEGER {
                  eAuto (0),
                  eNo (1)
            }
    MAX-ACCESS read-write
    STATUS     current
    DESCRIPTION
            "-- empty --"
    ::= { hmSetupInterfacesWlanRadioSettingsEntry 16 }

-- {COLUMN} 1.3.6.1.4.1.248.32.18.2.23.20.8.1.17
hmSetupInterfacesWlanRadioSettingsEntryAntennaMask OBJECT-TYPE
    SYNTAX     INTEGER {
                  eAuto (0),
                  eAntenna1 (1),
                  eAntenna1Plus2 (3),
                  eAntenna1Plus2Plus3 (7)
            }
    MAX-ACCESS read-write
    STATUS     current
    DESCRIPTION
            "-- empty --"
    ::= { hmSetupInterfacesWlanRadioSettingsEntry 17 }

-- {COLUMN} 1.3.6.1.4.1.248.32.18.2.23.20.8.1.18
hmSetupInterfacesWlanRadioSettingsEntryBackgroundScanUnit OBJECT-TYPE
    SYNTAX     INTEGER {
                  eSeconds (0),
                  eMilliseconds (1),
                  eMicroseconds (2),
                  eMinutes (3),
                  eHours (4),
                  eDays (5),
                  eWeeks (6),
                  eFortnights (7)
            }
    MAX-ACCESS read-write
    STATUS     current
    DESCRIPTION
            "-- empty --"
    ::= { hmSetupInterfacesWlanRadioSettingsEntry 18 }

-- {COLUMN} 1.3.6.1.4.1.248.32.18.2.23.20.8.1.19
hmSetupInterfacesWlanRadioSettingsEntryChannelPairing OBJECT-TYPE
    SYNTAX     INTEGER {
                  e11nCompliant (0),
                  eLegacyTurboFriendly (1)
            }
    MAX-ACCESS read-write
    STATUS     current
    DESCRIPTION
            "-- empty --"
    ::= { hmSetupInterfacesWlanRadioSettingsEntry 19 }

-- {COLUMN} 1.3.6.1.4.1.248.32.18.2.23.20.8.1.20
hmSetupInterfacesWlanRadioSettingsEntryPreferredDfsScheme OBJECT-TYPE
    SYNTAX     INTEGER {
                  eEn301893V13 (2),
                  eEn301893V15 (32),
                  eEn301893V16 (64),
                  eEn301893V17Deprecated (128),
                  eEn301893V17 (256)
            }
    MAX-ACCESS read-write
    STATUS     current
    DESCRIPTION
            "-- empty --"
    ::= { hmSetupInterfacesWlanRadioSettingsEntry 20 }

-- {COLUMN} 1.3.6.1.4.1.248.32.18.2.23.20.8.1.21
hmSetupInterfacesWlanRadioSettingsEntryCacDuration OBJECT-TYPE
    SYNTAX     Integer32 (0..2147483647)
    MAX-ACCESS read-write
    STATUS     current
    DESCRIPTION
            "-- empty --"
    ::= { hmSetupInterfacesWlanRadioSettingsEntry 21 }

-- {COLUMN} 1.3.6.1.4.1.248.32.18.2.23.20.8.1.22
hmSetupInterfacesWlanRadioSettingsEntryForce40mhz OBJECT-TYPE
    SYNTAX     INTEGER {
                  eNo (0),
                  eYes (1)
            }
    MAX-ACCESS read-write
    STATUS     current
    DESCRIPTION
            "-- empty --"
    ::= { hmSetupInterfacesWlanRadioSettingsEntry 22 }

-- {COLUMN} 1.3.6.1.4.1.248.32.18.2.23.20.8.1.23
hmSetupInterfacesWlanRadioSettingsEntryAdaptiveNoiseImmunity OBJECT-TYPE
    SYNTAX     INTEGER {
                  eNo (0),
                  eYes (1)
            }
    MAX-ACCESS read-write
    STATUS     current
    DESCRIPTION
            "-- empty --"
    ::= { hmSetupInterfacesWlanRadioSettingsEntry 23 }

-- {COLUMN} 1.3.6.1.4.1.248.32.18.2.23.20.8.1.24
hmSetupInterfacesWlanRadioSettingsEntryMaxChannelBandwidth OBJECT-TYPE
    SYNTAX     INTEGER {
                  e20mhz (0),
                  e40mhz (1),
                  eAuto (255)
            }
    MAX-ACCESS read-write
    STATUS     current
    DESCRIPTION
            "-- empty --"
    ::= { hmSetupInterfacesWlanRadioSettingsEntry 24 }

-- {COLUMN} 1.3.6.1.4.1.248.32.18.2.23.20.8.1.25
hmSetupInterfacesWlanRadioSettingsEntryAllowPhyRestarts OBJECT-TYPE
    SYNTAX     INTEGER {
                  eNo (0),
                  eYes (1)
            }
    MAX-ACCESS read-write
    STATUS     current
    DESCRIPTION
            "-- empty --"
    ::= { hmSetupInterfacesWlanRadioSettingsEntry 25 }

-- {COLUMN} 1.3.6.1.4.1.248.32.18.2.23.20.8.1.26
hmSetupInterfacesWlanRadioSettingsEntryDfsRscFlClChan OBJECT-TYPE
    SYNTAX     INTEGER {
                  eNo (0),
                  eYes (1)
            }
    MAX-ACCESS read-write
    STATUS     current
    DESCRIPTION
            ""
    ::= { hmSetupInterfacesWlanRadioSettingsEntry 26 }

-- {COLUMN} 1.3.6.1.4.1.248.32.18.2.23.20.8.1.27
hmSetupInterfacesWlanRadioSettingsEntryDfsRescanNumChannels OBJECT-TYPE
    SYNTAX     Integer32 (0..2147483647)
    MAX-ACCESS read-write
    STATUS     current
    DESCRIPTION
            "-- empty --"
    ::= { hmSetupInterfacesWlanRadioSettingsEntry 27 }

-- {COLUMN} 1.3.6.1.4.1.248.32.18.2.23.20.8.1.28
hmSetupInterfacesWlanRadioSettingsEntryPreferred24Scheme OBJECT-TYPE
    SYNTAX     INTEGER {
                  eEn300328V17 (1),
                  eEn300328V18 (2)
            }
    MAX-ACCESS read-write
    STATUS     current
    DESCRIPTION
            "-- empty --"
    ::= { hmSetupInterfacesWlanRadioSettingsEntry 28 }

-- {COLUMN} 1.3.6.1.4.1.248.32.18.2.23.20.8.1.248
hmSetupInterfacesWlanRadioSettingsEntryPassiveScanDuration OBJECT-TYPE
    SYNTAX     Integer32 (0..2147483647)
    MAX-ACCESS read-write
    STATUS     current
    DESCRIPTION
            "-- empty --"
    ::= { hmSetupInterfacesWlanRadioSettingsEntry 248 }

-- {TABLE} 1.3.6.1.4.1.248.32.18.2.23.20.9
hmSetupInterfacesWlanPerformanceTable OBJECT-TYPE
    SYNTAX     SEQUENCE OF HmSetupInterfacesWlanPerformanceEntry
    MAX-ACCESS not-accessible
    STATUS     current
    DESCRIPTION
            "-- empty --"
    ::= { hmSetupInterfacesWlan 9 }

-- {ROW} 1.3.6.1.4.1.248.32.18.2.23.20.9.1
hmSetupInterfacesWlanPerformanceEntry OBJECT-TYPE
    SYNTAX     HmSetupInterfacesWlanPerformanceEntry
    MAX-ACCESS not-accessible
    STATUS     current
    DESCRIPTION
            ""
    INDEX {
            hmSetupInterfacesWlanPerformanceEntryIfc
          }
    ::= { hmSetupInterfacesWlanPerformanceTable 1 }

HmSetupInterfacesWlanPerformanceEntry ::= SEQUENCE {
            hmSetupInterfacesWlanPerformanceEntryIfc INTEGER,
            hmSetupInterfacesWlanPerformanceEntryTxBursting Integer32,
            hmSetupInterfacesWlanPerformanceEntryQos INTEGER
    }

-- {COLUMN} 1.3.6.1.4.1.248.32.18.2.23.20.9.1.1
hmSetupInterfacesWlanPerformanceEntryIfc OBJECT-TYPE
    SYNTAX     INTEGER {
                  eWlan1 (1),
                  eWlan2 (2)
            }
    MAX-ACCESS read-write
    STATUS     current
    DESCRIPTION
            "-- empty --"
    ::= { hmSetupInterfacesWlanPerformanceEntry 1 }

-- {COLUMN} 1.3.6.1.4.1.248.32.18.2.23.20.9.1.2
hmSetupInterfacesWlanPerformanceEntryTxBursting OBJECT-TYPE
    SYNTAX     Integer32 (0..65535)
    MAX-ACCESS read-write
    STATUS     current
    DESCRIPTION
            "-- empty --"
    ::= { hmSetupInterfacesWlanPerformanceEntry 2 }

-- {COLUMN} 1.3.6.1.4.1.248.32.18.2.23.20.9.1.5
hmSetupInterfacesWlanPerformanceEntryQos OBJECT-TYPE
    SYNTAX     INTEGER {
                  eNo (0),
                  eYes (1)
            }
    MAX-ACCESS read-write
    STATUS     current
    DESCRIPTION
            "-- empty --"
    ::= { hmSetupInterfacesWlanPerformanceEntry 5 }

-- {TABLE} 1.3.6.1.4.1.248.32.18.2.23.20.10
hmSetupInterfacesWlanBeaconingTable OBJECT-TYPE
    SYNTAX     SEQUENCE OF HmSetupInterfacesWlanBeaconingEntry
    MAX-ACCESS not-accessible
    STATUS     current
    DESCRIPTION
            "-- empty --"
    ::= { hmSetupInterfacesWlan 10 }

-- {ROW} 1.3.6.1.4.1.248.32.18.2.23.20.10.1
hmSetupInterfacesWlanBeaconingEntry OBJECT-TYPE
    SYNTAX     HmSetupInterfacesWlanBeaconingEntry
    MAX-ACCESS not-accessible
    STATUS     current
    DESCRIPTION
            ""
    INDEX {
            hmSetupInterfacesWlanBeaconingEntryIfc
          }
    ::= { hmSetupInterfacesWlanBeaconingTable 1 }

HmSetupInterfacesWlanBeaconingEntry ::= SEQUENCE {
            hmSetupInterfacesWlanBeaconingEntryIfc INTEGER,
            hmSetupInterfacesWlanBeaconingEntryBeaconPeriod Integer32,
            hmSetupInterfacesWlanBeaconingEntryDtimPeriod Integer32,
            hmSetupInterfacesWlanBeaconingEntryBeaconOrder INTEGER
    }

-- {COLUMN} 1.3.6.1.4.1.248.32.18.2.23.20.10.1.1
hmSetupInterfacesWlanBeaconingEntryIfc OBJECT-TYPE
    SYNTAX     INTEGER {
                  eWlan1 (1),
                  eWlan2 (2)
            }
    MAX-ACCESS read-write
    STATUS     current
    DESCRIPTION
            "-- empty --"
    ::= { hmSetupInterfacesWlanBeaconingEntry 1 }

-- {COLUMN} 1.3.6.1.4.1.248.32.18.2.23.20.10.1.2
hmSetupInterfacesWlanBeaconingEntryBeaconPeriod OBJECT-TYPE
    SYNTAX     Integer32 (0..65535)
    MAX-ACCESS read-write
    STATUS     current
    DESCRIPTION
            "-- empty --"
    ::= { hmSetupInterfacesWlanBeaconingEntry 2 }

-- {COLUMN} 1.3.6.1.4.1.248.32.18.2.23.20.10.1.3
hmSetupInterfacesWlanBeaconingEntryDtimPeriod OBJECT-TYPE
    SYNTAX     Integer32 (0..255)
    MAX-ACCESS read-write
    STATUS     current
    DESCRIPTION
            "-- empty --"
    ::= { hmSetupInterfacesWlanBeaconingEntry 3 }

-- {COLUMN} 1.3.6.1.4.1.248.32.18.2.23.20.10.1.4
hmSetupInterfacesWlanBeaconingEntryBeaconOrder OBJECT-TYPE
    SYNTAX     INTEGER {
                  eCyclic (0),
                  eStaggered (1),
                  eSimpleBurst (2)
            }
    MAX-ACCESS read-write
    STATUS     current
    DESCRIPTION
            "-- empty --"
    ::= { hmSetupInterfacesWlanBeaconingEntry 4 }

-- {TABLE} 1.3.6.1.4.1.248.32.18.2.23.20.11
hmSetupInterfacesWlanRoamingTable OBJECT-TYPE
    SYNTAX     SEQUENCE OF HmSetupInterfacesWlanRoamingEntry
    MAX-ACCESS not-accessible
    STATUS     current
    DESCRIPTION
            "-- empty --"
    ::= { hmSetupInterfacesWlan 11 }

-- {ROW} 1.3.6.1.4.1.248.32.18.2.23.20.11.1
hmSetupInterfacesWlanRoamingEntry OBJECT-TYPE
    SYNTAX     HmSetupInterfacesWlanRoamingEntry
    MAX-ACCESS not-accessible
    STATUS     current
    DESCRIPTION
            ""
    INDEX {
            hmSetupInterfacesWlanRoamingEntryIfc
          }
    ::= { hmSetupInterfacesWlanRoamingTable 1 }

HmSetupInterfacesWlanRoamingEntry ::= SEQUENCE {
            hmSetupInterfacesWlanRoamingEntryIfc INTEGER,
            hmSetupInterfacesWlanRoamingEntryBeaconMissThreshold Integer32,
            hmSetupInterfacesWlanRoamingEntryRoamingThreshold Integer32,
            hmSetupInterfacesWlanRoamingEntryNoRoamingThreshold Integer32,
            hmSetupInterfacesWlanRoamingEntryForceRoamingThreshold Integer32,
            hmSetupInterfacesWlanRoamingEntrySoftRoaming INTEGER,
            hmSetupInterfacesWlanRoamingEntryConnectThreshold Integer32,
            hmSetupInterfacesWlanRoamingEntryConnectHoldThreshold Integer32,
            hmSetupInterfacesWlanRoamingEntryMinConnectSignalLevel Integer32,
            hmSetupInterfacesWlanRoamingEntryMinConnectHoldSignalLevel Integer32,
            hmSetupInterfacesWlanRoamingEntryBlockTime Gauge32,
            hmSetupInterfacesWlanRoamingEntryPrioritizedChannelScan INTEGER
    }

-- {COLUMN} 1.3.6.1.4.1.248.32.18.2.23.20.11.1.1
hmSetupInterfacesWlanRoamingEntryIfc OBJECT-TYPE
    SYNTAX     INTEGER {
                  eWlan1 (1),
                  eWlan2 (2)
            }
    MAX-ACCESS read-write
    STATUS     current
    DESCRIPTION
            "-- empty --"
    ::= { hmSetupInterfacesWlanRoamingEntry 1 }

-- {COLUMN} 1.3.6.1.4.1.248.32.18.2.23.20.11.1.2
hmSetupInterfacesWlanRoamingEntryBeaconMissThreshold OBJECT-TYPE
    SYNTAX     Integer32 (0..255)
    MAX-ACCESS read-write
    STATUS     current
    DESCRIPTION
            "-- empty --"
    ::= { hmSetupInterfacesWlanRoamingEntry 2 }

-- {COLUMN} 1.3.6.1.4.1.248.32.18.2.23.20.11.1.3
hmSetupInterfacesWlanRoamingEntryRoamingThreshold OBJECT-TYPE
    SYNTAX     Integer32 (0..255)
    MAX-ACCESS read-write
    STATUS     current
    DESCRIPTION
            "-- empty --"
    ::= { hmSetupInterfacesWlanRoamingEntry 3 }

-- {COLUMN} 1.3.6.1.4.1.248.32.18.2.23.20.11.1.4
hmSetupInterfacesWlanRoamingEntryNoRoamingThreshold OBJECT-TYPE
    SYNTAX     Integer32 (0..255)
    MAX-ACCESS read-write
    STATUS     current
    DESCRIPTION
            "-- empty --"
    ::= { hmSetupInterfacesWlanRoamingEntry 4 }

-- {COLUMN} 1.3.6.1.4.1.248.32.18.2.23.20.11.1.5
hmSetupInterfacesWlanRoamingEntryForceRoamingThreshold OBJECT-TYPE
    SYNTAX     Integer32 (0..255)
    MAX-ACCESS read-write
    STATUS     current
    DESCRIPTION
            "-- empty --"
    ::= { hmSetupInterfacesWlanRoamingEntry 5 }

-- {COLUMN} 1.3.6.1.4.1.248.32.18.2.23.20.11.1.6
hmSetupInterfacesWlanRoamingEntrySoftRoaming OBJECT-TYPE
    SYNTAX     INTEGER {
                  eNo (0),
                  eYes (1)
            }
    MAX-ACCESS read-write
    STATUS     current
    DESCRIPTION
            "-- empty --"
    ::= { hmSetupInterfacesWlanRoamingEntry 6 }

-- {COLUMN} 1.3.6.1.4.1.248.32.18.2.23.20.11.1.7
hmSetupInterfacesWlanRoamingEntryConnectThreshold OBJECT-TYPE
    SYNTAX     Integer32 (0..255)
    MAX-ACCESS read-write
    STATUS     current
    DESCRIPTION
            "-- empty --"
    ::= { hmSetupInterfacesWlanRoamingEntry 7 }

-- {COLUMN} 1.3.6.1.4.1.248.32.18.2.23.20.11.1.8
hmSetupInterfacesWlanRoamingEntryConnectHoldThreshold OBJECT-TYPE
    SYNTAX     Integer32 (0..255)
    MAX-ACCESS read-write
    STATUS     current
    DESCRIPTION
            "-- empty --"
    ::= { hmSetupInterfacesWlanRoamingEntry 8 }

-- {COLUMN} 1.3.6.1.4.1.248.32.18.2.23.20.11.1.9
hmSetupInterfacesWlanRoamingEntryMinConnectSignalLevel OBJECT-TYPE
    SYNTAX     Integer32 (-128..127)
    MAX-ACCESS read-write
    STATUS     current
    DESCRIPTION
            "-- empty --"
    ::= { hmSetupInterfacesWlanRoamingEntry 9 }

-- {COLUMN} 1.3.6.1.4.1.248.32.18.2.23.20.11.1.10
hmSetupInterfacesWlanRoamingEntryMinConnectHoldSignalLevel OBJECT-TYPE
    SYNTAX     Integer32 (-128..127)
    MAX-ACCESS read-write
    STATUS     current
    DESCRIPTION
            "-- empty --"
    ::= { hmSetupInterfacesWlanRoamingEntry 10 }

-- {COLUMN} 1.3.6.1.4.1.248.32.18.2.23.20.11.1.11
hmSetupInterfacesWlanRoamingEntryBlockTime OBJECT-TYPE
    SYNTAX     Gauge32
    MAX-ACCESS read-write
    STATUS     current
    DESCRIPTION
            "-- empty --"
    ::= { hmSetupInterfacesWlanRoamingEntry 11 }

-- {COLUMN} 1.3.6.1.4.1.248.32.18.2.23.20.11.1.248
hmSetupInterfacesWlanRoamingEntryPrioritizedChannelScan OBJECT-TYPE
    SYNTAX     INTEGER {
                  eNo (0),
                  eYes (1)
            }
    MAX-ACCESS read-write
    STATUS     current
    DESCRIPTION
            "-- empty --"
    ::= { hmSetupInterfacesWlanRoamingEntry 248 }

-- {TABLE} 1.3.6.1.4.1.248.32.18.2.23.20.12
hmSetupInterfacesWlanIntpntPeersTable OBJECT-TYPE
    SYNTAX     SEQUENCE OF HmSetupInterfacesWlanIntpntPeersEntry
    MAX-ACCESS not-accessible
    STATUS     current
    DESCRIPTION
            ""
    ::= { hmSetupInterfacesWlan 12 }

-- {ROW} 1.3.6.1.4.1.248.32.18.2.23.20.12.1
hmSetupInterfacesWlanIntpntPeersEntry OBJECT-TYPE
    SYNTAX     HmSetupInterfacesWlanIntpntPeersEntry
    MAX-ACCESS not-accessible
    STATUS     current
    DESCRIPTION
            ""
    INDEX {
            hmSetupInterfacesWlanIntpntPeersEntryIfc
          }
    ::= { hmSetupInterfacesWlanIntpntPeersTable 1 }

HmSetupInterfacesWlanIntpntPeersEntry ::= SEQUENCE {
            hmSetupInterfacesWlanIntpntPeersEntryIfc INTEGER,
            hmSetupInterfacesWlanIntpntPeersEntryRecognizeBy INTEGER,
            hmSetupInterfacesWlanIntpntPeersEntryMacAddress MacAddress,
            hmSetupInterfacesWlanIntpntPeersEntryPeerName DisplayString,
            hmSetupInterfacesWlanIntpntPeersEntryOperating INTEGER,
            hmSetupInterfacesWlanIntpntPeersEntryTxLimit Integer32,
            hmSetupInterfacesWlanIntpntPeersEntryRxLimit Integer32,
            hmSetupInterfacesWlanIntpntPeersEntryKey DisplayString,
            hmSetupInterfacesWlanIntpntPeersEntryConnectThreshold Integer32,
            hmSetupInterfacesWlanIntpntPeersEntryConnectHoldThreshold Integer32,
            hmSetupInterfacesWlanIntpntPeersEntryC2cMode INTEGER
    }

-- {COLUMN} 1.3.6.1.4.1.248.32.18.2.23.20.12.1.1
hmSetupInterfacesWlanIntpntPeersEntryIfc OBJECT-TYPE
    SYNTAX     INTEGER {
                  eP2p11 (1),
                  eP2p12 (2),
                  eP2p13 (3),
                  eP2p14 (4),
                  eP2p15 (5),
                  eP2p16 (6),
                  eP2p21 (7),
                  eP2p22 (8),
                  eP2p23 (9),
                  eP2p24 (10),
                  eP2p25 (11),
                  eP2p26 (12),
                  eP2p17 (32),
                  eP2p18 (33),
                  eP2p19 (34),
                  eP2p110 (35),
                  eP2p111 (36),
                  eP2p112 (37),
                  eP2p113 (38),
                  eP2p114 (39),
                  eP2p115 (40),
                  eP2p116 (41),
                  eP2p27 (64),
                  eP2p28 (65),
                  eP2p29 (66),
                  eP2p210 (67),
                  eP2p211 (68),
                  eP2p212 (69),
                  eP2p213 (70),
                  eP2p214 (71),
                  eP2p215 (72),
                  eP2p216 (73)
            }
    MAX-ACCESS read-write
    STATUS     current
    DESCRIPTION
            "-- empty --"
    ::= { hmSetupInterfacesWlanIntpntPeersEntry 1 }

-- {COLUMN} 1.3.6.1.4.1.248.32.18.2.23.20.12.1.2
hmSetupInterfacesWlanIntpntPeersEntryRecognizeBy OBJECT-TYPE
    SYNTAX     INTEGER {
                  eMacAddress (0),
                  eName (1),
                  eSerialAutoconfig (2),
                  eC2cCoupling (3)
            }
    MAX-ACCESS read-write
    STATUS     current
    DESCRIPTION
            "-- empty --"
    ::= { hmSetupInterfacesWlanIntpntPeersEntry 2 }

-- {COLUMN} 1.3.6.1.4.1.248.32.18.2.23.20.12.1.3
hmSetupInterfacesWlanIntpntPeersEntryMacAddress OBJECT-TYPE
    SYNTAX     MacAddress
    MAX-ACCESS read-write
    STATUS     current
    DESCRIPTION
            "-- empty --"
    ::= { hmSetupInterfacesWlanIntpntPeersEntry 3 }

-- {COLUMN} 1.3.6.1.4.1.248.32.18.2.23.20.12.1.4
hmSetupInterfacesWlanIntpntPeersEntryPeerName OBJECT-TYPE
    SYNTAX     DisplayString (SIZE(0..24))
    MAX-ACCESS read-write
    STATUS     current
    DESCRIPTION
            "-- empty --"
    ::= { hmSetupInterfacesWlanIntpntPeersEntry 4 }

-- {COLUMN} 1.3.6.1.4.1.248.32.18.2.23.20.12.1.5
hmSetupInterfacesWlanIntpntPeersEntryOperating OBJECT-TYPE
    SYNTAX     INTEGER {
                  eNo (0),
                  eYes (1)
            }
    MAX-ACCESS read-write
    STATUS     current
    DESCRIPTION
            "-- empty --"
    ::= { hmSetupInterfacesWlanIntpntPeersEntry 5 }

-- {COLUMN} 1.3.6.1.4.1.248.32.18.2.23.20.12.1.6
hmSetupInterfacesWlanIntpntPeersEntryTxLimit OBJECT-TYPE
    SYNTAX     Integer32 (0..2147483647)
    MAX-ACCESS read-write
    STATUS     current
    DESCRIPTION
            "-- empty --"
    ::= { hmSetupInterfacesWlanIntpntPeersEntry 6 }

-- {COLUMN} 1.3.6.1.4.1.248.32.18.2.23.20.12.1.7
hmSetupInterfacesWlanIntpntPeersEntryRxLimit OBJECT-TYPE
    SYNTAX     Integer32 (0..2147483647)
    MAX-ACCESS read-write
    STATUS     current
    DESCRIPTION
            "-- empty --"
    ::= { hmSetupInterfacesWlanIntpntPeersEntry 7 }

-- {COLUMN} 1.3.6.1.4.1.248.32.18.2.23.20.12.1.8
hmSetupInterfacesWlanIntpntPeersEntryKey OBJECT-TYPE
    SYNTAX     DisplayString (SIZE(0..63))
    MAX-ACCESS read-write
    STATUS     current
    DESCRIPTION
            "-- empty --"
    ::= { hmSetupInterfacesWlanIntpntPeersEntry 8 }

-- {COLUMN} 1.3.6.1.4.1.248.32.18.2.23.20.12.1.9
hmSetupInterfacesWlanIntpntPeersEntryConnectThreshold OBJECT-TYPE
    SYNTAX     Integer32 (0..255)
    MAX-ACCESS read-write
    STATUS     current
    DESCRIPTION
            "-- empty --"
    ::= { hmSetupInterfacesWlanIntpntPeersEntry 9 }

-- {COLUMN} 1.3.6.1.4.1.248.32.18.2.23.20.12.1.10
hmSetupInterfacesWlanIntpntPeersEntryConnectHoldThreshold OBJECT-TYPE
    SYNTAX     Integer32 (0..255)
    MAX-ACCESS read-write
    STATUS     current
    DESCRIPTION
            "-- empty --"
    ::= { hmSetupInterfacesWlanIntpntPeersEntry 10 }

-- {COLUMN} 1.3.6.1.4.1.248.32.18.2.23.20.12.1.248
hmSetupInterfacesWlanIntpntPeersEntryC2cMode OBJECT-TYPE
    SYNTAX     INTEGER {
                  eAutomatic (0),
                  eManual (1)
            }
    MAX-ACCESS read-write
    STATUS     current
    DESCRIPTION
            "-- empty --"
    ::= { hmSetupInterfacesWlanIntpntPeersEntry 248 }

-- {TABLE} 1.3.6.1.4.1.248.32.18.2.23.20.13
hmSetupInterfacesWlanNetworkAlarmLimitsTable OBJECT-TYPE
    SYNTAX     SEQUENCE OF HmSetupInterfacesWlanNetworkAlarmLimitsEntry
    MAX-ACCESS not-accessible
    STATUS     current
    DESCRIPTION
            "-- empty --"
    ::= { hmSetupInterfacesWlan 13 }

-- {ROW} 1.3.6.1.4.1.248.32.18.2.23.20.13.1
hmSetupInterfacesWlanNetworkAlarmLimitsEntry OBJECT-TYPE
    SYNTAX     HmSetupInterfacesWlanNetworkAlarmLimitsEntry
    MAX-ACCESS not-accessible
    STATUS     current
    DESCRIPTION
            ""
    INDEX {
            hmSetupInterfacesWlanNetworkAlarmLimitsEntryIfc
          }
    ::= { hmSetupInterfacesWlanNetworkAlarmLimitsTable 1 }

HmSetupInterfacesWlanNetworkAlarmLimitsEntry ::= SEQUENCE {
            hmSetupInterfacesWlanNetworkAlarmLimitsEntryIfc INTEGER,
            hmSetupInterfacesWlanNetworkAlarmLimitsEntryPhySignal Integer32,
            hmSetupInterfacesWlanNetworkAlarmLimitsEntryTotalRetries Integer32,
            hmSetupInterfacesWlanNetworkAlarmLimitsEntryTxErrors Integer32
    }

-- {COLUMN} 1.3.6.1.4.1.248.32.18.2.23.20.13.1.1
hmSetupInterfacesWlanNetworkAlarmLimitsEntryIfc OBJECT-TYPE
    SYNTAX     INTEGER {
                  eWlan1 (1),
                  eWlan2 (2),
                  eWlan12 (16),
                  eWlan13 (17),
                  eWlan14 (18),
                  eWlan15 (19),
                  eWlan16 (20),
                  eWlan17 (21),
                  eWlan18 (22),
                  eWlan22 (32),
                  eWlan23 (33),
                  eWlan24 (34),
                  eWlan25 (35),
                  eWlan26 (36),
                  eWlan27 (37),
                  eWlan28 (38)
            }
    MAX-ACCESS read-write
    STATUS     current
    DESCRIPTION
            "-- empty --"
    ::= { hmSetupInterfacesWlanNetworkAlarmLimitsEntry 1 }

-- {COLUMN} 1.3.6.1.4.1.248.32.18.2.23.20.13.1.2
hmSetupInterfacesWlanNetworkAlarmLimitsEntryPhySignal OBJECT-TYPE
    SYNTAX     Integer32 (0..65535)
    MAX-ACCESS read-write
    STATUS     current
    DESCRIPTION
            "-- empty --"
    ::= { hmSetupInterfacesWlanNetworkAlarmLimitsEntry 2 }

-- {COLUMN} 1.3.6.1.4.1.248.32.18.2.23.20.13.1.3
hmSetupInterfacesWlanNetworkAlarmLimitsEntryTotalRetries OBJECT-TYPE
    SYNTAX     Integer32 (0..65535)
    MAX-ACCESS read-write
    STATUS     current
    DESCRIPTION
            "-- empty --"
    ::= { hmSetupInterfacesWlanNetworkAlarmLimitsEntry 3 }

-- {COLUMN} 1.3.6.1.4.1.248.32.18.2.23.20.13.1.4
hmSetupInterfacesWlanNetworkAlarmLimitsEntryTxErrors OBJECT-TYPE
    SYNTAX     Integer32 (0..65535)
    MAX-ACCESS read-write
    STATUS     current
    DESCRIPTION
            "-- empty --"
    ::= { hmSetupInterfacesWlanNetworkAlarmLimitsEntry 4 }

-- {TABLE} 1.3.6.1.4.1.248.32.18.2.23.20.14
hmSetupInterfacesWlanInterpointAlarmLimitsTable OBJECT-TYPE
    SYNTAX     SEQUENCE OF HmSetupInterfacesWlanInterpointAlarmLimitsEntry
    MAX-ACCESS not-accessible
    STATUS     current
    DESCRIPTION
            "-- empty --"
    ::= { hmSetupInterfacesWlan 14 }

-- {ROW} 1.3.6.1.4.1.248.32.18.2.23.20.14.1
hmSetupInterfacesWlanInterpointAlarmLimitsEntry OBJECT-TYPE
    SYNTAX     HmSetupInterfacesWlanInterpointAlarmLimitsEntry
    MAX-ACCESS not-accessible
    STATUS     current
    DESCRIPTION
            ""
    INDEX {
            hmSetupInterfacesWlanInterpointAlarmLimitsEntryIfc
          }
    ::= { hmSetupInterfacesWlanInterpointAlarmLimitsTable 1 }

HmSetupInterfacesWlanInterpointAlarmLimitsEntry ::= SEQUENCE {
            hmSetupInterfacesWlanInterpointAlarmLimitsEntryIfc INTEGER,
            hmSetupInterfacesWlanInterpointAlarmLimitsEntryPhySignal Integer32,
            hmSetupInterfacesWlanInterpointAlarmLimitsEntryTotalRetries Integer32,
            hmSetupInterfacesWlanInterpointAlarmLimitsEntryTxErrors Integer32
    }

-- {COLUMN} 1.3.6.1.4.1.248.32.18.2.23.20.14.1.1
hmSetupInterfacesWlanInterpointAlarmLimitsEntryIfc OBJECT-TYPE
    SYNTAX     INTEGER {
                  eP2p11 (1),
                  eP2p12 (2),
                  eP2p13 (3),
                  eP2p14 (4),
                  eP2p15 (5),
                  eP2p16 (6),
                  eP2p21 (7),
                  eP2p22 (8),
                  eP2p23 (9),
                  eP2p24 (10),
                  eP2p25 (11),
                  eP2p26 (12),
                  eP2p17 (32),
                  eP2p18 (33),
                  eP2p19 (34),
                  eP2p110 (35),
                  eP2p111 (36),
                  eP2p112 (37),
                  eP2p113 (38),
                  eP2p114 (39),
                  eP2p115 (40),
                  eP2p116 (41),
                  eP2p27 (64),
                  eP2p28 (65),
                  eP2p29 (66),
                  eP2p210 (67),
                  eP2p211 (68),
                  eP2p212 (69),
                  eP2p213 (70),
                  eP2p214 (71),
                  eP2p215 (72),
                  eP2p216 (73)
            }
    MAX-ACCESS read-write
    STATUS     current
    DESCRIPTION
            "-- empty --"
    ::= { hmSetupInterfacesWlanInterpointAlarmLimitsEntry 1 }

-- {COLUMN} 1.3.6.1.4.1.248.32.18.2.23.20.14.1.2
hmSetupInterfacesWlanInterpointAlarmLimitsEntryPhySignal OBJECT-TYPE
    SYNTAX     Integer32 (0..65535)
    MAX-ACCESS read-write
    STATUS     current
    DESCRIPTION
            "-- empty --"
    ::= { hmSetupInterfacesWlanInterpointAlarmLimitsEntry 2 }

-- {COLUMN} 1.3.6.1.4.1.248.32.18.2.23.20.14.1.3
hmSetupInterfacesWlanInterpointAlarmLimitsEntryTotalRetries OBJECT-TYPE
    SYNTAX     Integer32 (0..65535)
    MAX-ACCESS read-write
    STATUS     current
    DESCRIPTION
            "-- empty --"
    ::= { hmSetupInterfacesWlanInterpointAlarmLimitsEntry 3 }

-- {COLUMN} 1.3.6.1.4.1.248.32.18.2.23.20.14.1.4
hmSetupInterfacesWlanInterpointAlarmLimitsEntryTxErrors OBJECT-TYPE
    SYNTAX     Integer32 (0..65535)
    MAX-ACCESS read-write
    STATUS     current
    DESCRIPTION
            "-- empty --"
    ::= { hmSetupInterfacesWlanInterpointAlarmLimitsEntry 4 }

-- {TABLE} 1.3.6.1.4.1.248.32.18.2.23.20.15
hmSetupInterfacesWlanProbeSettingsTable OBJECT-TYPE
    SYNTAX     SEQUENCE OF HmSetupInterfacesWlanProbeSettingsEntry
    MAX-ACCESS not-accessible
    STATUS     current
    DESCRIPTION
            "-- empty --"
    ::= { hmSetupInterfacesWlan 15 }

-- {ROW} 1.3.6.1.4.1.248.32.18.2.23.20.15.1
hmSetupInterfacesWlanProbeSettingsEntry OBJECT-TYPE
    SYNTAX     HmSetupInterfacesWlanProbeSettingsEntry
    MAX-ACCESS not-accessible
    STATUS     current
    DESCRIPTION
            ""
    INDEX {
            hmSetupInterfacesWlanProbeSettingsEntryIfc
          }
    ::= { hmSetupInterfacesWlanProbeSettingsTable 1 }

HmSetupInterfacesWlanProbeSettingsEntry ::= SEQUENCE {
            hmSetupInterfacesWlanProbeSettingsEntryIfc INTEGER,
            hmSetupInterfacesWlanProbeSettingsEntryRadioBands INTEGER,
            hmSetupInterfacesWlanProbeSettingsEntrySubbands24ghz INTEGER,
            hmSetupInterfacesWlanProbeSettingsEntryChannelList24ghz DisplayString,
            hmSetupInterfacesWlanProbeSettingsEntrySubbands5ghz INTEGER,
            hmSetupInterfacesWlanProbeSettingsEntryChannelList5ghz DisplayString,
            hmSetupInterfacesWlanProbeSettingsEntryChannelDwellTime Integer32
    }

-- {COLUMN} 1.3.6.1.4.1.248.32.18.2.23.20.15.1.1
hmSetupInterfacesWlanProbeSettingsEntryIfc OBJECT-TYPE
    SYNTAX     INTEGER {
                  eWlan1 (1),
                  eWlan2 (2)
            }
    MAX-ACCESS read-write
    STATUS     current
    DESCRIPTION
            "-- empty --"
    ::= { hmSetupInterfacesWlanProbeSettingsEntry 1 }

-- {COLUMN} 1.3.6.1.4.1.248.32.18.2.23.20.15.1.2
hmSetupInterfacesWlanProbeSettingsEntryRadioBands OBJECT-TYPE
    SYNTAX     INTEGER {
                  e24ghz (1),
                  e5ghz (2),
                  e24ghz5ghz (3)
            }
    MAX-ACCESS read-write
    STATUS     current
    DESCRIPTION
            "-- empty --"
    ::= { hmSetupInterfacesWlanProbeSettingsEntry 2 }

-- {COLUMN} 1.3.6.1.4.1.248.32.18.2.23.20.15.1.3
hmSetupInterfacesWlanProbeSettingsEntrySubbands24ghz OBJECT-TYPE
    SYNTAX     INTEGER {
                  eBand1 (1),
                  eBand2 (2),
                  eBand1Plus2 (3),
                  eBand3 (4),
                  eBand1Plus3 (5),
                  eBand2Plus3 (6),
                  eBand1Plus2Plus3 (7)
            }
    MAX-ACCESS read-write
    STATUS     current
    DESCRIPTION
            "-- empty --"
    ::= { hmSetupInterfacesWlanProbeSettingsEntry 3 }

-- {COLUMN} 1.3.6.1.4.1.248.32.18.2.23.20.15.1.4
hmSetupInterfacesWlanProbeSettingsEntryChannelList24ghz OBJECT-TYPE
    SYNTAX     DisplayString (SIZE(0..48))
    MAX-ACCESS read-write
    STATUS     current
    DESCRIPTION
            "-- empty --"
    ::= { hmSetupInterfacesWlanProbeSettingsEntry 4 }

-- {COLUMN} 1.3.6.1.4.1.248.32.18.2.23.20.15.1.5
hmSetupInterfacesWlanProbeSettingsEntrySubbands5ghz OBJECT-TYPE
    SYNTAX     INTEGER {
                  eBand1 (1),
                  eBand2 (2),
                  eBand1Plus2 (3),
                  eBand3 (4),
                  eBand1Plus3 (5),
                  eBand2Plus3 (6),
                  eBand1Plus2Plus3 (7)
            }
    MAX-ACCESS read-write
    STATUS     current
    DESCRIPTION
            "-- empty --"
    ::= { hmSetupInterfacesWlanProbeSettingsEntry 5 }

-- {COLUMN} 1.3.6.1.4.1.248.32.18.2.23.20.15.1.6
hmSetupInterfacesWlanProbeSettingsEntryChannelList5ghz OBJECT-TYPE
    SYNTAX     DisplayString (SIZE(0..48))
    MAX-ACCESS read-write
    STATUS     current
    DESCRIPTION
            "-- empty --"
    ::= { hmSetupInterfacesWlanProbeSettingsEntry 6 }

-- {COLUMN} 1.3.6.1.4.1.248.32.18.2.23.20.15.1.7
hmSetupInterfacesWlanProbeSettingsEntryChannelDwellTime OBJECT-TYPE
    SYNTAX     Integer32 (0..2147483647)
    MAX-ACCESS read-write
    STATUS     current
    DESCRIPTION
            "-- empty --"
    ::= { hmSetupInterfacesWlanProbeSettingsEntry 7 }

-- {TABLE} 1.3.6.1.4.1.248.32.18.2.23.20.19
hmSetupInterfacesWlanIntptTrnsmisTable OBJECT-TYPE
    SYNTAX     SEQUENCE OF HmSetupInterfacesWlanIntptTrnsmisEntry
    MAX-ACCESS not-accessible
    STATUS     current
    DESCRIPTION
            ""
    ::= { hmSetupInterfacesWlan 19 }

-- {ROW} 1.3.6.1.4.1.248.32.18.2.23.20.19.1
hmSetupInterfacesWlanIntptTrnsmisEntry OBJECT-TYPE
    SYNTAX     HmSetupInterfacesWlanIntptTrnsmisEntry
    MAX-ACCESS not-accessible
    STATUS     current
    DESCRIPTION
            ""
    INDEX {
            hmSetupInterfacesWlanIntptTrnsmisEntryIfc
          }
    ::= { hmSetupInterfacesWlanIntptTrnsmisTable 1 }

HmSetupInterfacesWlanIntptTrnsmisEntry ::= SEQUENCE {
            hmSetupInterfacesWlanIntptTrnsmisEntryIfc INTEGER,
            hmSetupInterfacesWlanIntptTrnsmisEntryPacketSize Integer32,
            hmSetupInterfacesWlanIntptTrnsmisEntryMinTxRate INTEGER,
            hmSetupInterfacesWlanIntptTrnsmisEntryRtsThreshold Integer32,
            hmSetupInterfacesWlanIntptTrnsmisEntry11bPreamble INTEGER,
            hmSetupInterfacesWlanIntptTrnsmisEntryMaxTxRate INTEGER,
            hmSetupInterfacesWlanIntptTrnsmisEntryMinFragLen Integer32,
            hmSetupInterfacesWlanIntptTrnsmisEntrySoftRetries Integer32,
            hmSetupInterfacesWlanIntptTrnsmisEntryHardRetries Integer32,
            hmSetupInterfacesWlanIntptTrnsmisEntryShortGuardInterval INTEGER,
            hmSetupInterfacesWlanIntptTrnsmisEntryMaxSpatialStreams INTEGER,
            hmSetupInterfacesWlanIntptTrnsmisEntrySendAggregates INTEGER,
            hmSetupInterfacesWlanIntptTrnsmisEntryMinHtMcs INTEGER,
            hmSetupInterfacesWlanIntptTrnsmisEntryMaxHtMcs INTEGER,
            hmSetupInterfacesWlanIntptTrnsmisEntryMinSpatialStreams INTEGER,
            hmSetupInterfacesWlanIntptTrnsmisEntryEapolRate INTEGER,
            hmSetupInterfacesWlanIntptTrnsmisEntryMaxAggrPacketCount Integer32,
            hmSetupInterfacesWlanIntptTrnsmisEntryReceiveAggregates INTEGER,
            hmSetupInterfacesWlanIntptTrnsmisEntryUseStbc INTEGER,
            hmSetupInterfacesWlanIntptTrnsmisEntryUseLdpc INTEGER
    }

-- {COLUMN} 1.3.6.1.4.1.248.32.18.2.23.20.19.1.1
hmSetupInterfacesWlanIntptTrnsmisEntryIfc OBJECT-TYPE
    SYNTAX     INTEGER {
                  eP2p11 (1),
                  eP2p12 (2),
                  eP2p13 (3),
                  eP2p14 (4),
                  eP2p15 (5),
                  eP2p16 (6),
                  eP2p21 (7),
                  eP2p22 (8),
                  eP2p23 (9),
                  eP2p24 (10),
                  eP2p25 (11),
                  eP2p26 (12),
                  eP2p17 (32),
                  eP2p18 (33),
                  eP2p19 (34),
                  eP2p110 (35),
                  eP2p111 (36),
                  eP2p112 (37),
                  eP2p113 (38),
                  eP2p114 (39),
                  eP2p115 (40),
                  eP2p116 (41),
                  eP2p27 (64),
                  eP2p28 (65),
                  eP2p29 (66),
                  eP2p210 (67),
                  eP2p211 (68),
                  eP2p212 (69),
                  eP2p213 (70),
                  eP2p214 (71),
                  eP2p215 (72),
                  eP2p216 (73)
            }
    MAX-ACCESS read-write
    STATUS     current
    DESCRIPTION
            "-- empty --"
    ::= { hmSetupInterfacesWlanIntptTrnsmisEntry 1 }

-- {COLUMN} 1.3.6.1.4.1.248.32.18.2.23.20.19.1.2
hmSetupInterfacesWlanIntptTrnsmisEntryPacketSize OBJECT-TYPE
    SYNTAX     Integer32 (0..65535)
    MAX-ACCESS read-write
    STATUS     current
    DESCRIPTION
            "-- empty --"
    ::= { hmSetupInterfacesWlanIntptTrnsmisEntry 2 }

-- {COLUMN} 1.3.6.1.4.1.248.32.18.2.23.20.19.1.3
hmSetupInterfacesWlanIntptTrnsmisEntryMinTxRate OBJECT-TYPE
    SYNTAX     INTEGER {
                  eAuto (0),
                  e1M (1),
                  e2M (2),
                  e5M5 (4),
                  e11M (6),
                  e6M (8),
                  e9M (9),
                  e12M (10),
                  e18M (11),
                  e24M (12),
                  e36M (13),
                  e48M (14),
                  e54M (15)
            }
    MAX-ACCESS read-write
    STATUS     current
    DESCRIPTION
            "-- empty --"
    ::= { hmSetupInterfacesWlanIntptTrnsmisEntry 3 }

-- {COLUMN} 1.3.6.1.4.1.248.32.18.2.23.20.19.1.6
hmSetupInterfacesWlanIntptTrnsmisEntryRtsThreshold OBJECT-TYPE
    SYNTAX     Integer32 (0..65535)
    MAX-ACCESS read-write
    STATUS     current
    DESCRIPTION
            "-- empty --"
    ::= { hmSetupInterfacesWlanIntptTrnsmisEntry 6 }

-- {COLUMN} 1.3.6.1.4.1.248.32.18.2.23.20.19.1.7
hmSetupInterfacesWlanIntptTrnsmisEntry11bPreamble OBJECT-TYPE
    SYNTAX     INTEGER {
                  eAuto (0),
                  eLong (1)
            }
    MAX-ACCESS read-write
    STATUS     current
    DESCRIPTION
            "-- empty --"
    ::= { hmSetupInterfacesWlanIntptTrnsmisEntry 7 }

-- {COLUMN} 1.3.6.1.4.1.248.32.18.2.23.20.19.1.9
hmSetupInterfacesWlanIntptTrnsmisEntryMaxTxRate OBJECT-TYPE
    SYNTAX     INTEGER {
                  eAuto (0),
                  e1M (1),
                  e2M (2),
                  e5M5 (4),
                  e11M (6),
                  e6M (8),
                  e9M (9),
                  e12M (10),
                  e18M (11),
                  e24M (12),
                  e36M (13),
                  e48M (14),
                  e54M (15)
            }
    MAX-ACCESS read-write
    STATUS     current
    DESCRIPTION
            "-- empty --"
    ::= { hmSetupInterfacesWlanIntptTrnsmisEntry 9 }

-- {COLUMN} 1.3.6.1.4.1.248.32.18.2.23.20.19.1.10
hmSetupInterfacesWlanIntptTrnsmisEntryMinFragLen OBJECT-TYPE
    SYNTAX     Integer32 (0..65535)
    MAX-ACCESS read-write
    STATUS     current
    DESCRIPTION
            "-- empty --"
    ::= { hmSetupInterfacesWlanIntptTrnsmisEntry 10 }

-- {COLUMN} 1.3.6.1.4.1.248.32.18.2.23.20.19.1.11
hmSetupInterfacesWlanIntptTrnsmisEntrySoftRetries OBJECT-TYPE
    SYNTAX     Integer32 (0..255)
    MAX-ACCESS read-write
    STATUS     current
    DESCRIPTION
            "-- empty --"
    ::= { hmSetupInterfacesWlanIntptTrnsmisEntry 11 }

-- {COLUMN} 1.3.6.1.4.1.248.32.18.2.23.20.19.1.12
hmSetupInterfacesWlanIntptTrnsmisEntryHardRetries OBJECT-TYPE
    SYNTAX     Integer32 (0..255)
    MAX-ACCESS read-write
    STATUS     current
    DESCRIPTION
            "-- empty --"
    ::= { hmSetupInterfacesWlanIntptTrnsmisEntry 12 }

-- {COLUMN} 1.3.6.1.4.1.248.32.18.2.23.20.19.1.13
hmSetupInterfacesWlanIntptTrnsmisEntryShortGuardInterval OBJECT-TYPE
    SYNTAX     INTEGER {
                  eAuto (0),
                  eNo (1)
            }
    MAX-ACCESS read-write
    STATUS     current
    DESCRIPTION
            "-- empty --"
    ::= { hmSetupInterfacesWlanIntptTrnsmisEntry 13 }

-- {COLUMN} 1.3.6.1.4.1.248.32.18.2.23.20.19.1.14
hmSetupInterfacesWlanIntptTrnsmisEntryMaxSpatialStreams OBJECT-TYPE
    SYNTAX     INTEGER {
                  eAuto (0),
                  eOne (1),
                  eTwo (2),
                  eThree (3)
            }
    MAX-ACCESS read-write
    STATUS     current
    DESCRIPTION
            "-- empty --"
    ::= { hmSetupInterfacesWlanIntptTrnsmisEntry 14 }

-- {COLUMN} 1.3.6.1.4.1.248.32.18.2.23.20.19.1.15
hmSetupInterfacesWlanIntptTrnsmisEntrySendAggregates OBJECT-TYPE
    SYNTAX     INTEGER {
                  eNo (0),
                  eYes (1)
            }
    MAX-ACCESS read-write
    STATUS     current
    DESCRIPTION
            "-- empty --"
    ::= { hmSetupInterfacesWlanIntptTrnsmisEntry 15 }

-- {COLUMN} 1.3.6.1.4.1.248.32.18.2.23.20.19.1.16
hmSetupInterfacesWlanIntptTrnsmisEntryMinHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-write
    STATUS     current
    DESCRIPTION
            "-- empty --"
    ::= { hmSetupInterfacesWlanIntptTrnsmisEntry 16 }

-- {COLUMN} 1.3.6.1.4.1.248.32.18.2.23.20.19.1.17
hmSetupInterfacesWlanIntptTrnsmisEntryMaxHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-write
    STATUS     current
    DESCRIPTION
            "-- empty --"
    ::= { hmSetupInterfacesWlanIntptTrnsmisEntry 17 }

-- {COLUMN} 1.3.6.1.4.1.248.32.18.2.23.20.19.1.18
hmSetupInterfacesWlanIntptTrnsmisEntryMinSpatialStreams OBJECT-TYPE
    SYNTAX     INTEGER {
                  eAuto (0),
                  eOne (1),
                  eTwo (2),
                  eThree (3)
            }
    MAX-ACCESS read-write
    STATUS     current
    DESCRIPTION
            "-- empty --"
    ::= { hmSetupInterfacesWlanIntptTrnsmisEntry 18 }

-- {COLUMN} 1.3.6.1.4.1.248.32.18.2.23.20.19.1.19
hmSetupInterfacesWlanIntptTrnsmisEntryEapolRate OBJECT-TYPE
    SYNTAX     INTEGER {
                  eLikeData (0),
                  e1M (1),
                  e2M (2),
                  e5M5 (4),
                  e11M (6),
                  e6M (8),
                  e9M (9),
                  e12M (10),
                  e18M (11),
                  e24M (12),
                  e36M (13),
                  e48M (14),
                  e54M (15),
                  eHT1S6M5 (28),
                  eHT1S13M (29),
                  eHT1S19M5 (30),
                  eHT1S26M (31),
                  eHT1S39M (32),
                  eHT1S52M (33),
                  eHT1S58M5 (34),
                  eHT1S65M (35),
                  eHT2S13M (36),
                  eHT2S26M (37),
                  eHT2S39M (38),
                  eHT2S52M (39),
                  eHT2S78M (40),
                  eHT2S104M (41),
                  eHT2S117M (42),
                  eHT2S130M (43),
                  eHT3S19M5 (44),
                  eHT3S39M (45),
                  eHT3S58M5 (46),
                  eHT3S78M (47),
                  eHT3S117M (48),
                  eHT3S156M (49),
                  eHT3S175M5 (50),
                  eHT3S195M (51)
            }
    MAX-ACCESS read-write
    STATUS     current
    DESCRIPTION
            "-- empty --"
    ::= { hmSetupInterfacesWlanIntptTrnsmisEntry 19 }

-- {COLUMN} 1.3.6.1.4.1.248.32.18.2.23.20.19.1.20
hmSetupInterfacesWlanIntptTrnsmisEntryMaxAggrPacketCount OBJECT-TYPE
    SYNTAX     Integer32 (0..255)
    MAX-ACCESS read-write
    STATUS     current
    DESCRIPTION
            "-- empty --"
    ::= { hmSetupInterfacesWlanIntptTrnsmisEntry 20 }

-- {COLUMN} 1.3.6.1.4.1.248.32.18.2.23.20.19.1.22
hmSetupInterfacesWlanIntptTrnsmisEntryReceiveAggregates OBJECT-TYPE
    SYNTAX     INTEGER {
                  eNo (0),
                  eYes (1)
            }
    MAX-ACCESS read-write
    STATUS     current
    DESCRIPTION
            "-- empty --"
    ::= { hmSetupInterfacesWlanIntptTrnsmisEntry 22 }

-- {COLUMN} 1.3.6.1.4.1.248.32.18.2.23.20.19.1.23
hmSetupInterfacesWlanIntptTrnsmisEntryUseStbc OBJECT-TYPE
    SYNTAX     INTEGER {
                  eNo (0),
                  eYes (1)
            }
    MAX-ACCESS read-write
    STATUS     current
    DESCRIPTION
            "-- empty --"
    ::= { hmSetupInterfacesWlanIntptTrnsmisEntry 23 }

-- {COLUMN} 1.3.6.1.4.1.248.32.18.2.23.20.19.1.24
hmSetupInterfacesWlanIntptTrnsmisEntryUseLdpc OBJECT-TYPE
    SYNTAX     INTEGER {
                  eNo (0),
                  eYes (1)
            }
    MAX-ACCESS read-write
    STATUS     current
    DESCRIPTION
            "-- empty --"
    ::= { hmSetupInterfacesWlanIntptTrnsmisEntry 24 }

-- {TABLE} 1.3.6.1.4.1.248.32.18.2.23.20.20
hmSetupInterfacesWlanIntptEncTable OBJECT-TYPE
    SYNTAX     SEQUENCE OF HmSetupInterfacesWlanIntptEncEntry
    MAX-ACCESS not-accessible
    STATUS     current
    DESCRIPTION
            ""
    ::= { hmSetupInterfacesWlan 20 }

-- {ROW} 1.3.6.1.4.1.248.32.18.2.23.20.20.1
hmSetupInterfacesWlanIntptEncEntry OBJECT-TYPE
    SYNTAX     HmSetupInterfacesWlanIntptEncEntry
    MAX-ACCESS not-accessible
    STATUS     current
    DESCRIPTION
            ""
    INDEX {
            hmSetupInterfacesWlanIntptEncEntryIfc
          }
    ::= { hmSetupInterfacesWlanIntptEncTable 1 }

HmSetupInterfacesWlanIntptEncEntry ::= SEQUENCE {
            hmSetupInterfacesWlanIntptEncEntryIfc INTEGER,
            hmSetupInterfacesWlanIntptEncEntryEncryption INTEGER,
            hmSetupInterfacesWlanIntptEncEntryDefaultKey Integer32,
            hmSetupInterfacesWlanIntptEncEntryMethod INTEGER,
            hmSetupInterfacesWlanIntptEncEntryWpaVersion INTEGER,
            hmSetupInterfacesWlanIntptEncEntryWpaRekeyingCycle Integer32,
            hmSetupInterfacesWlanIntptEncEntryWpa1SessionKeytypes INTEGER,
            hmSetupInterfacesWlanIntptEncEntryWpa2SessionKeytypes INTEGER,
            hmSetupInterfacesWlanIntptEncEntryProtMgmtFrames INTEGER,
            hmSetupInterfacesWlanIntptEncEntryWpa2KeyManagement BITS
    }

-- {COLUMN} 1.3.6.1.4.1.248.32.18.2.23.20.20.1.1
hmSetupInterfacesWlanIntptEncEntryIfc OBJECT-TYPE
    SYNTAX     INTEGER {
                  eWlan1 (1),
                  eWlan2 (2)
            }
    MAX-ACCESS read-write
    STATUS     current
    DESCRIPTION
            "-- empty --"
    ::= { hmSetupInterfacesWlanIntptEncEntry 1 }

-- {COLUMN} 1.3.6.1.4.1.248.32.18.2.23.20.20.1.2
hmSetupInterfacesWlanIntptEncEntryEncryption OBJECT-TYPE
    SYNTAX     INTEGER {
                  eNo (0),
                  eYes (2)
            }
    MAX-ACCESS read-write
    STATUS     current
    DESCRIPTION
            "-- empty --"
    ::= { hmSetupInterfacesWlanIntptEncEntry 2 }

-- {COLUMN} 1.3.6.1.4.1.248.32.18.2.23.20.20.1.3
hmSetupInterfacesWlanIntptEncEntryDefaultKey OBJECT-TYPE
    SYNTAX     Integer32 (0..255)
    MAX-ACCESS read-write
    STATUS     current
    DESCRIPTION
            "-- empty --"
    ::= { hmSetupInterfacesWlanIntptEncEntry 3 }

-- {COLUMN} 1.3.6.1.4.1.248.32.18.2.23.20.20.1.4
hmSetupInterfacesWlanIntptEncEntryMethod OBJECT-TYPE
    SYNTAX     INTEGER {
                  eWep40Bits (5),
                  eWep104Bits (13),
                  eWep128Bits (16),
                  e80211iWpaPsk (32)
            }
    MAX-ACCESS read-write
    STATUS     current
    DESCRIPTION
            "-- empty --"
    ::= { hmSetupInterfacesWlanIntptEncEntry 4 }

-- {COLUMN} 1.3.6.1.4.1.248.32.18.2.23.20.20.1.9
hmSetupInterfacesWlanIntptEncEntryWpaVersion OBJECT-TYPE
    SYNTAX     INTEGER {
                  eWpa1 (2),
                  eWpa2 (4),
                  eWpa12 (6)
            }
    MAX-ACCESS read-write
    STATUS     current
    DESCRIPTION
            "-- empty --"
    ::= { hmSetupInterfacesWlanIntptEncEntry 9 }

-- {COLUMN} 1.3.6.1.4.1.248.32.18.2.23.20.20.1.11
hmSetupInterfacesWlanIntptEncEntryWpaRekeyingCycle OBJECT-TYPE
    SYNTAX     Integer32 (0..2147483647)
    MAX-ACCESS read-write
    STATUS     current
    DESCRIPTION
            "-- empty --"
    ::= { hmSetupInterfacesWlanIntptEncEntry 11 }

-- {COLUMN} 1.3.6.1.4.1.248.32.18.2.23.20.20.1.12
hmSetupInterfacesWlanIntptEncEntryWpa1SessionKeytypes OBJECT-TYPE
    SYNTAX     INTEGER {
                  eTkip (1),
                  eAes (2),
                  eTkipAes (3)
            }
    MAX-ACCESS read-write
    STATUS     current
    DESCRIPTION
            "-- empty --"
    ::= { hmSetupInterfacesWlanIntptEncEntry 12 }

-- {COLUMN} 1.3.6.1.4.1.248.32.18.2.23.20.20.1.13
hmSetupInterfacesWlanIntptEncEntryWpa2SessionKeytypes OBJECT-TYPE
    SYNTAX     INTEGER {
                  eTkip (1),
                  eAes (2),
                  eTkipAes (3)
            }
    MAX-ACCESS read-write
    STATUS     current
    DESCRIPTION
            "-- empty --"
    ::= { hmSetupInterfacesWlanIntptEncEntry 13 }

-- {COLUMN} 1.3.6.1.4.1.248.32.18.2.23.20.20.1.14
hmSetupInterfacesWlanIntptEncEntryProtMgmtFrames OBJECT-TYPE
    SYNTAX     INTEGER {
                  eNo (0),
                  eOptional (1),
                  eMandatory (2)
            }
    MAX-ACCESS read-write
    STATUS     current
    DESCRIPTION
            "-- empty --"
    ::= { hmSetupInterfacesWlanIntptEncEntry 14 }

-- {COLUMN} 1.3.6.1.4.1.248.32.18.2.23.20.20.1.19
hmSetupInterfacesWlanIntptEncEntryWpa2KeyManagement OBJECT-TYPE
    SYNTAX     BITS {
                  eSha256 (5),
                  eStandard (7)
            }
    MAX-ACCESS read-write
    STATUS     current
    DESCRIPTION
            "-- empty --"
    ::= { hmSetupInterfacesWlanIntptEncEntry 19 }

-- {SCALAR} 1.3.6.1.4.1.248.32.18.2.23.20.248
hmSetupInterfacesWlanStartc2c OBJECT-TYPE
    SYNTAX     DisplayString
    MAX-ACCESS read-write
    STATUS     current
    DESCRIPTION
            "-- empty --"
    ::= { hmSetupInterfacesWlan 248 }

-- {SCALAR} 1.3.6.1.4.1.248.32.18.2.23.20.249
hmSetupInterfacesWlanStopc2c OBJECT-TYPE
    SYNTAX     DisplayString
    MAX-ACCESS read-write
    STATUS     current
    DESCRIPTION
            "-- empty --"
    ::= { hmSetupInterfacesWlan 249 }

-- {TABLE} 1.3.6.1.4.1.248.32.18.2.23.21
hmSetupInterfacesLanInterfacesTable OBJECT-TYPE
    SYNTAX     SEQUENCE OF HmSetupInterfacesLanInterfacesEntry
    MAX-ACCESS not-accessible
    STATUS     current
    DESCRIPTION
            "-- empty --"
    ::= { hmSetupInterfaces 21 }

-- {ROW} 1.3.6.1.4.1.248.32.18.2.23.21.1
hmSetupInterfacesLanInterfacesEntry OBJECT-TYPE
    SYNTAX     HmSetupInterfacesLanInterfacesEntry
    MAX-ACCESS not-accessible
    STATUS     current
    DESCRIPTION
            ""
    INDEX {
            hmSetupInterfacesLanInterfacesEntryIfc
          }
    ::= { hmSetupInterfacesLanInterfacesTable 1 }

HmSetupInterfacesLanInterfacesEntry ::= SEQUENCE {
            hmSetupInterfacesLanInterfacesEntryIfc INTEGER,
            hmSetupInterfacesLanInterfacesEntryOperating INTEGER,
            hmSetupInterfacesLanInterfacesEntryTxLimit Integer32,
            hmSetupInterfacesLanInterfacesEntryRxLimit Integer32
    }

-- {COLUMN} 1.3.6.1.4.1.248.32.18.2.23.21.1.1
hmSetupInterfacesLanInterfacesEntryIfc OBJECT-TYPE
    SYNTAX     INTEGER {
                  eLan1 (1),
                  eLan2 (2),
                  eLan3 (3),
                  eLan4 (4)
            }
    MAX-ACCESS read-only
    STATUS     current
    DESCRIPTION
            "-- empty --"
    ::= { hmSetupInterfacesLanInterfacesEntry 1 }

-- {COLUMN} 1.3.6.1.4.1.248.32.18.2.23.21.1.7
hmSetupInterfacesLanInterfacesEntryOperating OBJECT-TYPE
    SYNTAX     INTEGER {
                  eYes (0),
                  eNo (1)
            }
    MAX-ACCESS read-write
    STATUS     current
    DESCRIPTION
            "-- empty --"
    ::= { hmSetupInterfacesLanInterfacesEntry 7 }

-- {COLUMN} 1.3.6.1.4.1.248.32.18.2.23.21.1.8
hmSetupInterfacesLanInterfacesEntryTxLimit OBJECT-TYPE
    SYNTAX     Integer32 (0..2147483647)
    MAX-ACCESS read-write
    STATUS     current
    DESCRIPTION
            "-- empty --"
    ::= { hmSetupInterfacesLanInterfacesEntry 8 }

-- {COLUMN} 1.3.6.1.4.1.248.32.18.2.23.21.1.9
hmSetupInterfacesLanInterfacesEntryRxLimit OBJECT-TYPE
    SYNTAX     Integer32 (0..2147483647)
    MAX-ACCESS read-write
    STATUS     current
    DESCRIPTION
            "-- empty --"
    ::= { hmSetupInterfacesLanInterfacesEntry 9 }

-- {TABLE} 1.3.6.1.4.1.248.32.18.2.23.30
hmSetupInterfacesEthernetPortsTable OBJECT-TYPE
    SYNTAX     SEQUENCE OF HmSetupInterfacesEthernetPortsEntry
    MAX-ACCESS not-accessible
    STATUS     current
    DESCRIPTION
            "-- empty --"
    ::= { hmSetupInterfaces 30 }

-- {ROW} 1.3.6.1.4.1.248.32.18.2.23.30.1
hmSetupInterfacesEthernetPortsEntry OBJECT-TYPE
    SYNTAX     HmSetupInterfacesEthernetPortsEntry
    MAX-ACCESS not-accessible
    STATUS     current
    DESCRIPTION
            ""
    INDEX {
            hmSetupInterfacesEthernetPortsEntryPort
          }
    ::= { hmSetupInterfacesEthernetPortsTable 1 }

HmSetupInterfacesEthernetPortsEntry ::= SEQUENCE {
            hmSetupInterfacesEthernetPortsEntryPort INTEGER,
            hmSetupInterfacesEthernetPortsEntryConnector INTEGER,
            hmSetupInterfacesEthernetPortsEntryPrivateMode INTEGER,
            hmSetupInterfacesEthernetPortsEntryAssignment INTEGER,
            hmSetupInterfacesEthernetPortsEntryMdiMode INTEGER,
            hmSetupInterfacesEthernetPortsEntryClockRole INTEGER,
            hmSetupInterfacesEthernetPortsEntryFlowControl INTEGER
    }

-- {COLUMN} 1.3.6.1.4.1.248.32.18.2.23.30.1.1
hmSetupInterfacesEthernetPortsEntryPort OBJECT-TYPE
    SYNTAX     INTEGER {
                  eEth1 (2),
                  eEth2 (3),
                  eEth3 (4),
                  eEth4 (5)
            }
    MAX-ACCESS read-only
    STATUS     current
    DESCRIPTION
            "-- empty --"
    ::= { hmSetupInterfacesEthernetPortsEntry 1 }

-- {COLUMN} 1.3.6.1.4.1.248.32.18.2.23.30.1.2
hmSetupInterfacesEthernetPortsEntryConnector OBJECT-TYPE
    SYNTAX     INTEGER {
                  eAuto (0),
                  e10bT (1),
                  eFd10bTx (2),
                  e100bTx (3),
                  eFd100bTx (4),
                  eAuto10 (5),
                  eFd1000bTx (6),
                  eAuto100 (7),
                  eFd1000bF (70)
            }
    MAX-ACCESS read-write
    STATUS     current
    DESCRIPTION
            "-- empty --"
    ::= { hmSetupInterfacesEthernetPortsEntry 2 }

-- {COLUMN} 1.3.6.1.4.1.248.32.18.2.23.30.1.3
hmSetupInterfacesEthernetPortsEntryPrivateMode OBJECT-TYPE
    SYNTAX     INTEGER {
                  eYes (1)
            }
    MAX-ACCESS read-write
    STATUS     current
    DESCRIPTION
            "-- empty --"
    ::= { hmSetupInterfacesEthernetPortsEntry 3 }

-- {COLUMN} 1.3.6.1.4.1.248.32.18.2.23.30.1.4
hmSetupInterfacesEthernetPortsEntryAssignment OBJECT-TYPE
    SYNTAX     INTEGER {
                  eLan1 (0),
                  eLan2 (1),
                  eLan3 (2),
                  eLan4 (3),
                  eDsl1 (512),
                  eDsl2 (513),
                  eDsl3 (514),
                  eDsl4 (515),
                  eIdle (65533),
                  ePowerDown (65535)
            }
    MAX-ACCESS read-write
    STATUS     current
    DESCRIPTION
            "-- empty --"
    ::= { hmSetupInterfacesEthernetPortsEntry 4 }

-- {COLUMN} 1.3.6.1.4.1.248.32.18.2.23.30.1.5
hmSetupInterfacesEthernetPortsEntryMdiMode OBJECT-TYPE
    SYNTAX     INTEGER {
                  eAuto (0),
                  eMdi (1),
                  eMdix (2)
            }
    MAX-ACCESS read-write
    STATUS     current
    DESCRIPTION
            "-- empty --"
    ::= { hmSetupInterfacesEthernetPortsEntry 5 }

-- {COLUMN} 1.3.6.1.4.1.248.32.18.2.23.30.1.6
hmSetupInterfacesEthernetPortsEntryClockRole OBJECT-TYPE
    SYNTAX     INTEGER {
                  eSlavePreferred (0),
                  eMaster (1),
                  eSlave (2),
                  eMasterPreferred (4)
            }
    MAX-ACCESS read-write
    STATUS     current
    DESCRIPTION
            "-- empty --"
    ::= { hmSetupInterfacesEthernetPortsEntry 6 }

-- {COLUMN} 1.3.6.1.4.1.248.32.18.2.23.30.1.9
hmSetupInterfacesEthernetPortsEntryFlowControl OBJECT-TYPE
    SYNTAX     INTEGER {
                  eAuto (0),
                  eOn (1),
                  eOff (2)
            }
    MAX-ACCESS read-write
    STATUS     current
    DESCRIPTION
            "-- empty --"
    ::= { hmSetupInterfacesEthernetPortsEntry 9 }

-- {NODE} 1.3.6.1.4.1.248.32.18.2.23.40
hmSetupInterfacesModem OBJECT IDENTIFIER ::= { hmSetupInterfaces 40 }

-- {SCALAR} 1.3.6.1.4.1.248.32.18.2.23.40.1
hmSetupInterfacesModemRingCount OBJECT-TYPE
    SYNTAX     Integer32 (0..255)
    MAX-ACCESS read-write
    STATUS     current
    DESCRIPTION
            "-- empty --"
    ::= { hmSetupInterfacesModem 1 }

-- {SCALAR} 1.3.6.1.4.1.248.32.18.2.23.40.2
hmSetupInterfacesModemEchoOffCommand OBJECT-TYPE
    SYNTAX     DisplayString (SIZE(0..9))
    MAX-ACCESS read-write
    STATUS     current
    DESCRIPTION
            "-- empty --"
    ::= { hmSetupInterfacesModem 2 }

-- {SCALAR} 1.3.6.1.4.1.248.32.18.2.23.40.3
hmSetupInterfacesModemResetCommand OBJECT-TYPE
    SYNTAX     DisplayString (SIZE(0..9))
    MAX-ACCESS read-write
    STATUS     current
    DESCRIPTION
            "-- empty --"
    ::= { hmSetupInterfacesModem 3 }

-- {SCALAR} 1.3.6.1.4.1.248.32.18.2.23.40.4
hmSetupInterfacesModemInitCommand OBJECT-TYPE
    SYNTAX     DisplayString (SIZE(0..63))
    MAX-ACCESS read-write
    STATUS     current
    DESCRIPTION
            "-- empty --"
    ::= { hmSetupInterfacesModem 4 }

-- {SCALAR} 1.3.6.1.4.1.248.32.18.2.23.40.5
hmSetupInterfacesModemDialCommand OBJECT-TYPE
    SYNTAX     DisplayString (SIZE(0..31))
    MAX-ACCESS read-write
    STATUS     current
    DESCRIPTION
            "-- empty --"
    ::= { hmSetupInterfacesModem 5 }

-- {SCALAR} 1.3.6.1.4.1.248.32.18.2.23.40.6
hmSetupInterfacesModemRequestId OBJECT-TYPE
    SYNTAX     DisplayString (SIZE(0..9))
    MAX-ACCESS read-write
    STATUS     current
    DESCRIPTION
            "-- empty --"
    ::= { hmSetupInterfacesModem 6 }

-- {SCALAR} 1.3.6.1.4.1.248.32.18.2.23.40.7
hmSetupInterfacesModemAnswerCommand OBJECT-TYPE
    SYNTAX     DisplayString (SIZE(0..9))
    MAX-ACCESS read-write
    STATUS     current
    DESCRIPTION
            "-- empty --"
    ::= { hmSetupInterfacesModem 7 }

-- {SCALAR} 1.3.6.1.4.1.248.32.18.2.23.40.8
hmSetupInterfacesModemDisconnectCommand OBJECT-TYPE
    SYNTAX     DisplayString (SIZE(0..9))
    MAX-ACCESS read-write
    STATUS     current
    DESCRIPTION
            "-- empty --"
    ::= { hmSetupInterfacesModem 8 }

-- {SCALAR} 1.3.6.1.4.1.248.32.18.2.23.40.9
hmSetupInterfacesModemEscapeSequence OBJECT-TYPE
    SYNTAX     DisplayString (SIZE(0..9))
    MAX-ACCESS read-write
    STATUS     current
    DESCRIPTION
            "-- empty --"
    ::= { hmSetupInterfacesModem 9 }

-- {SCALAR} 1.3.6.1.4.1.248.32.18.2.23.40.10
hmSetupInterfacesModemEscapePromtDelayMs OBJECT-TYPE
    SYNTAX     Integer32 (0..65535)
    MAX-ACCESS read-write
    STATUS     current
    DESCRIPTION
            "-- empty --"
    ::= { hmSetupInterfacesModem 10 }

-- {SCALAR} 1.3.6.1.4.1.248.32.18.2.23.40.11
hmSetupInterfacesModemInitDial OBJECT-TYPE
    SYNTAX     DisplayString (SIZE(0..63))
    MAX-ACCESS read-write
    STATUS     current
    DESCRIPTION
            "-- empty --"
    ::= { hmSetupInterfacesModem 11 }

-- {SCALAR} 1.3.6.1.4.1.248.32.18.2.23.40.12
hmSetupInterfacesModemInitAnswer OBJECT-TYPE
    SYNTAX     DisplayString (SIZE(0..63))
    MAX-ACCESS read-write
    STATUS     current
    DESCRIPTION
            "-- empty --"
    ::= { hmSetupInterfacesModem 12 }

-- {SCALAR} 1.3.6.1.4.1.248.32.18.2.23.40.13
hmSetupInterfacesModemCycletimeAtPollS OBJECT-TYPE
    SYNTAX     Integer32 (0..255)
    MAX-ACCESS read-write
    STATUS     current
    DESCRIPTION
            "-- empty --"
    ::= { hmSetupInterfacesModem 13 }

-- {SCALAR} 1.3.6.1.4.1.248.32.18.2.23.40.14
hmSetupInterfacesModemAtPollCount OBJECT-TYPE
    SYNTAX     Integer32 (0..255)
    MAX-ACCESS read-write
    STATUS     current
    DESCRIPTION
            "-- empty --"
    ::= { hmSetupInterfacesModem 14 }

-- {NODE} 1.3.6.1.4.1.248.32.18.2.23.41
hmSetupInterfacesMobile OBJECT IDENTIFIER ::= { hmSetupInterfaces 41 }

-- {TABLE} 1.3.6.1.4.1.248.32.18.2.23.41.1
hmSetupInterfacesMobileProfilesTable OBJECT-TYPE
    SYNTAX     SEQUENCE OF HmSetupInterfacesMobileProfilesEntry
    MAX-ACCESS not-accessible
    STATUS     current
    DESCRIPTION
            "-- empty --"
    ::= { hmSetupInterfacesMobile 1 }

-- {ROW} 1.3.6.1.4.1.248.32.18.2.23.41.1.1
hmSetupInterfacesMobileProfilesEntry OBJECT-TYPE
    SYNTAX     HmSetupInterfacesMobileProfilesEntry
    MAX-ACCESS not-accessible
    STATUS     current
    DESCRIPTION
            ""
    INDEX {
            hmSetupInterfacesMobileProfilesEntryProfile
          }
    ::= { hmSetupInterfacesMobileProfilesTable 1 }

HmSetupInterfacesMobileProfilesEntry ::= SEQUENCE {
            hmSetupInterfacesMobileProfilesEntryProfile DisplayString,
            hmSetupInterfacesMobileProfilesEntryPin DisplayString,
            hmSetupInterfacesMobileProfilesEntryApn DisplayString,
            hmSetupInterfacesMobileProfilesEntryNetwork DisplayString,
            hmSetupInterfacesMobileProfilesEntrySelect INTEGER,
            hmSetupInterfacesMobileProfilesEntryMode INTEGER,
            hmSetupInterfacesMobileProfilesEntryQosDownstreamDataRate Integer32,
            hmSetupInterfacesMobileProfilesEntryQosUpstreamDataRate Integer32,
            hmSetupInterfacesMobileProfilesEntryPdpType INTEGER,
            hmSetupInterfacesMobileProfilesEntryLteBands BITS,
            hmSetupInterfacesMobileProfilesEntryLteAttach INTEGER
    }

-- {COLUMN} 1.3.6.1.4.1.248.32.18.2.23.41.1.1.1
hmSetupInterfacesMobileProfilesEntryProfile OBJECT-TYPE
    SYNTAX     DisplayString (SIZE(0..16))
    MAX-ACCESS read-write
    STATUS     current
    DESCRIPTION
            "-- empty --"
    ::= { hmSetupInterfacesMobileProfilesEntry 1 }

-- {COLUMN} 1.3.6.1.4.1.248.32.18.2.23.41.1.1.2
hmSetupInterfacesMobileProfilesEntryPin OBJECT-TYPE
    SYNTAX     DisplayString (SIZE(0..6))
    MAX-ACCESS read-write
    STATUS     current
    DESCRIPTION
            "-- empty --"
    ::= { hmSetupInterfacesMobileProfilesEntry 2 }

-- {COLUMN} 1.3.6.1.4.1.248.32.18.2.23.41.1.1.3
hmSetupInterfacesMobileProfilesEntryApn OBJECT-TYPE
    SYNTAX     DisplayString (SIZE(0..47))
    MAX-ACCESS read-write
    STATUS     current
    DESCRIPTION
            "-- empty --"
    ::= { hmSetupInterfacesMobileProfilesEntry 3 }

-- {COLUMN} 1.3.6.1.4.1.248.32.18.2.23.41.1.1.4
hmSetupInterfacesMobileProfilesEntryNetwork OBJECT-TYPE
    SYNTAX     DisplayString (SIZE(0..16))
    MAX-ACCESS read-write
    STATUS     current
    DESCRIPTION
            "-- empty --"
    ::= { hmSetupInterfacesMobileProfilesEntry 4 }

-- {COLUMN} 1.3.6.1.4.1.248.32.18.2.23.41.1.1.5
hmSetupInterfacesMobileProfilesEntrySelect OBJECT-TYPE
    SYNTAX     INTEGER {
                  eAuto (0),
                  eManual (1),
                  eSAuto (2)
            }
    MAX-ACCESS read-write
    STATUS     current
    DESCRIPTION
            "-- empty --"
    ::= { hmSetupInterfacesMobileProfilesEntry 5 }

-- {COLUMN} 1.3.6.1.4.1.248.32.18.2.23.41.1.1.6
hmSetupInterfacesMobileProfilesEntryMode OBJECT-TYPE
    SYNTAX     INTEGER {
                  eAuto (0),
                  eUmts (1),
                  eGprs (2),
                  eLte (8),
                  eUmtsGprs (11)
            }
    MAX-ACCESS read-write
    STATUS     current
    DESCRIPTION
            "-- empty --"
    ::= { hmSetupInterfacesMobileProfilesEntry 6 }

-- {COLUMN} 1.3.6.1.4.1.248.32.18.2.23.41.1.1.7
hmSetupInterfacesMobileProfilesEntryQosDownstreamDataRate OBJECT-TYPE
    SYNTAX     Integer32 (0..2147483647)
    MAX-ACCESS read-write
    STATUS     current
    DESCRIPTION
            "-- empty --"
    ::= { hmSetupInterfacesMobileProfilesEntry 7 }

-- {COLUMN} 1.3.6.1.4.1.248.32.18.2.23.41.1.1.8
hmSetupInterfacesMobileProfilesEntryQosUpstreamDataRate OBJECT-TYPE
    SYNTAX     Integer32 (0..2147483647)
    MAX-ACCESS read-write
    STATUS     current
    DESCRIPTION
            "-- empty --"
    ::= { hmSetupInterfacesMobileProfilesEntry 8 }

-- {COLUMN} 1.3.6.1.4.1.248.32.18.2.23.41.1.1.9
hmSetupInterfacesMobileProfilesEntryPdpType OBJECT-TYPE
    SYNTAX     INTEGER {
                  eIpv4 (0),
                  eIpv6 (2),
                  eIpv4v6 (3)
            }
    MAX-ACCESS read-write
    STATUS     current
    DESCRIPTION
            "-- empty --"
    ::= { hmSetupInterfacesMobileProfilesEntry 9 }

-- {COLUMN} 1.3.6.1.4.1.248.32.18.2.23.41.1.1.10
hmSetupInterfacesMobileProfilesEntryLteBands OBJECT-TYPE
    SYNTAX     BITS {
                  eB20800 (26),
                  eB8900 (27),
                  eB72600 (28),
                  eB31800 (29),
                  eB12100 (30),
                  eAll (31)
            }
    MAX-ACCESS read-write
    STATUS     current
    DESCRIPTION
            "-- empty --"
    ::= { hmSetupInterfacesMobileProfilesEntry 10 }

-- {COLUMN} 1.3.6.1.4.1.248.32.18.2.23.41.1.1.11
hmSetupInterfacesMobileProfilesEntryLteAttach OBJECT-TYPE
    SYNTAX     INTEGER {
                  eImmediate (0),
                  eDelayed (1)
            }
    MAX-ACCESS read-write
    STATUS     current
    DESCRIPTION
            "-- empty --"
    ::= { hmSetupInterfacesMobileProfilesEntry 11 }

-- {SCALAR} 1.3.6.1.4.1.248.32.18.2.23.41.2
hmSetupInterfacesMobileScanNetworks OBJECT-TYPE
    SYNTAX     DisplayString
    MAX-ACCESS read-write
    STATUS     current
    DESCRIPTION
            "-- empty --"
    ::= { hmSetupInterfacesMobile 2 }

-- {SCALAR} 1.3.6.1.4.1.248.32.18.2.23.41.3
hmSetupInterfacesMobileInputPuk OBJECT-TYPE
    SYNTAX     DisplayString
    MAX-ACCESS read-write
    STATUS     current
    DESCRIPTION
            "-- empty --"
    ::= { hmSetupInterfacesMobile 3 }

-- {SCALAR} 1.3.6.1.4.1.248.32.18.2.23.41.6
hmSetupInterfacesMobileHistoryIntervalSec OBJECT-TYPE
    SYNTAX     Integer32 (0..2147483647)
    MAX-ACCESS read-write
    STATUS     current
    DESCRIPTION
            "-- empty --"
    ::= { hmSetupInterfacesMobile 6 }

-- {SCALAR} 1.3.6.1.4.1.248.32.18.2.23.41.7
hmSetupInterfacesMobileSyslogEnabled OBJECT-TYPE
    SYNTAX     INTEGER {
                  eNo (0),
                  eYes (1)
            }
    MAX-ACCESS read-write
    STATUS     current
    DESCRIPTION
            "-- empty --"
    ::= { hmSetupInterfacesMobile 7 }

-- {SCALAR} 1.3.6.1.4.1.248.32.18.2.23.41.9
hmSetupInterfacesMobileSignalCheckIntervallMin OBJECT-TYPE
    SYNTAX     Integer32 (0..2147483647)
    MAX-ACCESS read-write
    STATUS     current
    DESCRIPTION
            "-- empty --"
    ::= { hmSetupInterfacesMobile 9 }

-- {SCALAR} 1.3.6.1.4.1.248.32.18.2.23.41.10
hmSetupInterfacesMobileTreshold3gTo2gDb OBJECT-TYPE
    SYNTAX     Integer32 (-2147483648..2147483647)
    MAX-ACCESS read-write
    STATUS     current
    DESCRIPTION
            "-- empty --"
    ::= { hmSetupInterfacesMobile 10 }

-- {SCALAR} 1.3.6.1.4.1.248.32.18.2.23.41.11
hmSetupInterfacesMobileCheckWhileConnected OBJECT-TYPE
    SYNTAX     INTEGER {
                  eNo (0),
                  eYes (1)
            }
    MAX-ACCESS read-write
    STATUS     current
    DESCRIPTION
            "-- empty --"
    ::= { hmSetupInterfacesMobile 11 }

-- {SCALAR} 1.3.6.1.4.1.248.32.18.2.23.41.12
hmSetupInterfacesMobilePinChange OBJECT-TYPE
    SYNTAX     DisplayString
    MAX-ACCESS read-write
    STATUS     current
    DESCRIPTION
            "-- empty --"
    ::= { hmSetupInterfacesMobile 12 }

-- {NODE} 1.3.6.1.4.1.248.32.18.2.24
hmSetupPublicSpotModule OBJECT IDENTIFIER ::= { hmSetup 24 }

-- {SCALAR} 1.3.6.1.4.1.248.32.18.2.24.1
hmSetupPublicSpotModuleAuthenticationMode OBJECT-TYPE
    SYNTAX     INTEGER {
                  eNone (0),
                  eUserPlusPassword (1),
                  eMacPlusUserPlusPassword (2),
                  eEMail (3),
                  eEMail2sms (4),
                  eLoginViaAgreement (5)
            }
    MAX-ACCESS read-write
    STATUS     current
    DESCRIPTION
            "-- empty --"
    ::= { hmSetupPublicSpotModule 1 }

-- {TABLE} 1.3.6.1.4.1.248.32.18.2.24.2
hmSetupPublicSpotModuleUserTableTable OBJECT-TYPE
    SYNTAX     SEQUENCE OF HmSetupPublicSpotModuleUserTableEntry
    MAX-ACCESS not-accessible
    STATUS     current
    DESCRIPTION
            "-- empty --"
    ::= { hmSetupPublicSpotModule 2 }

-- {ROW} 1.3.6.1.4.1.248.32.18.2.24.2.1
hmSetupPublicSpotModuleUserTableEntry OBJECT-TYPE
    SYNTAX     HmSetupPublicSpotModuleUserTableEntry
    MAX-ACCESS not-accessible
    STATUS     current
    DESCRIPTION
            ""
    INDEX {
            hmSetupPublicSpotModuleUserTableEntryName
          }
    ::= { hmSetupPublicSpotModuleUserTableTable 1 }

HmSetupPublicSpotModuleUserTableEntry ::= SEQUENCE {
            hmSetupPublicSpotModuleUserTableEntryName DisplayString,
            hmSetupPublicSpotModuleUserTableEntryPassword DisplayString,
            hmSetupPublicSpotModuleUserTableEntryMacAddress MacAddress,
            hmSetupPublicSpotModuleUserTableEntryComment DisplayString,
            hmSetupPublicSpotModuleUserTableEntryProvider DisplayString,
            hmSetupPublicSpotModuleUserTableEntryExpiry DisplayString
    }

-- {COLUMN} 1.3.6.1.4.1.248.32.18.2.24.2.1.1
hmSetupPublicSpotModuleUserTableEntryName OBJECT-TYPE
    SYNTAX     DisplayString (SIZE(0..64))
    MAX-ACCESS read-write
    STATUS     current
    DESCRIPTION
            "-- empty --"
    ::= { hmSetupPublicSpotModuleUserTableEntry 1 }

-- {COLUMN} 1.3.6.1.4.1.248.32.18.2.24.2.1.2
hmSetupPublicSpotModuleUserTableEntryPassword OBJECT-TYPE
    SYNTAX     DisplayString (SIZE(0..16))
    MAX-ACCESS read-write
    STATUS     current
    DESCRIPTION
            "-- empty --"
    ::= { hmSetupPublicSpotModuleUserTableEntry 2 }

-- {COLUMN} 1.3.6.1.4.1.248.32.18.2.24.2.1.3
hmSetupPublicSpotModuleUserTableEntryMacAddress OBJECT-TYPE
    SYNTAX     MacAddress
    MAX-ACCESS read-write
    STATUS     current
    DESCRIPTION
            "-- empty --"
    ::= { hmSetupPublicSpotModuleUserTableEntry 3 }

-- {COLUMN} 1.3.6.1.4.1.248.32.18.2.24.2.1.4
hmSetupPublicSpotModuleUserTableEntryComment OBJECT-TYPE
    SYNTAX     DisplayString (SIZE(0..80))
    MAX-ACCESS read-write
    STATUS     current
    DESCRIPTION
            "-- empty --"
    ::= { hmSetupPublicSpotModuleUserTableEntry 4 }

-- {COLUMN} 1.3.6.1.4.1.248.32.18.2.24.2.1.5
hmSetupPublicSpotModuleUserTableEntryProvider OBJECT-TYPE
    SYNTAX     DisplayString (SIZE(0..16))
    MAX-ACCESS read-write
    STATUS     current
    DESCRIPTION
            "-- empty --"
    ::= { hmSetupPublicSpotModuleUserTableEntry 5 }

-- {COLUMN} 1.3.6.1.4.1.248.32.18.2.24.2.1.6
hmSetupPublicSpotModuleUserTableEntryExpiry OBJECT-TYPE
    SYNTAX     DisplayString (SIZE(0..21))
    MAX-ACCESS read-write
    STATUS     current
    DESCRIPTION
            "-- empty --"
    ::= { hmSetupPublicSpotModuleUserTableEntry 6 }

-- {TABLE} 1.3.6.1.4.1.248.32.18.2.24.3
hmSetupPublicSpotModuleProviderTableTable OBJECT-TYPE
    SYNTAX     SEQUENCE OF HmSetupPublicSpotModuleProviderTableEntry
    MAX-ACCESS not-accessible
    STATUS     current
    DESCRIPTION
            "-- empty --"
    ::= { hmSetupPublicSpotModule 3 }

-- {ROW} 1.3.6.1.4.1.248.32.18.2.24.3.1
hmSetupPublicSpotModuleProviderTableEntry OBJECT-TYPE
    SYNTAX     HmSetupPublicSpotModuleProviderTableEntry
    MAX-ACCESS not-accessible
    STATUS     current
    DESCRIPTION
            ""
    INDEX {
            hmSetupPublicSpotModuleProviderTableEntryProvider
          }
    ::= { hmSetupPublicSpotModuleProviderTableTable 1 }

HmSetupPublicSpotModuleProviderTableEntry ::= SEQUENCE {
            hmSetupPublicSpotModuleProviderTableEntryProvider DisplayString,
            hmSetupPublicSpotModuleProviderTableEntryAuthServerAddress IpAddress,
            hmSetupPublicSpotModuleProviderTableEntryAuthServerPort Integer32,
            hmSetupPublicSpotModuleProviderTableEntryAuthServerSecret DisplayString,
            hmSetupPublicSpotModuleProviderTableEntryAccServerAddress IpAddress,
            hmSetupPublicSpotModuleProviderTableEntryAccServerPort Integer32,
            hmSetupPublicSpotModuleProviderTableEntryAccServerSecret DisplayString,
            hmSetupPublicSpotModuleProviderTableEntryBackup DisplayString,
            hmSetupPublicSpotModuleProviderTableEntryAuthServerLoopbackAddr DisplayString,
            hmSetupPublicSpotModuleProviderTableEntryAccServerLoopbackAddr DisplayString,
            hmSetupPublicSpotModuleProviderTableEntryAuthServerProtocol INTEGER,
            hmSetupPublicSpotModuleProviderTableEntryAccServerProtocol INTEGER,
            hmSetupPublicSpotModuleProviderTableEntryAuthServerHostname DisplayString,
            hmSetupPublicSpotModuleProviderTableEntryAccServerHostname DisplayString,
            hmSetupPublicSpotModuleProviderTableEntryAuthAttributeValues DisplayString,
            hmSetupPublicSpotModuleProviderTableEntryAccAttributeValues DisplayString
    }

-- {COLUMN} 1.3.6.1.4.1.248.32.18.2.24.3.1.1
hmSetupPublicSpotModuleProviderTableEntryProvider OBJECT-TYPE
    SYNTAX     DisplayString (SIZE(0..16))
    MAX-ACCESS read-write
    STATUS     current
    DESCRIPTION
            "-- empty --"
    ::= { hmSetupPublicSpotModuleProviderTableEntry 1 }

-- {COLUMN} 1.3.6.1.4.1.248.32.18.2.24.3.1.2
hmSetupPublicSpotModuleProviderTableEntryAuthServerAddress OBJECT-TYPE
    SYNTAX     IpAddress
    MAX-ACCESS read-write
    STATUS     current
    DESCRIPTION
            "-- empty --"
    ::= { hmSetupPublicSpotModuleProviderTableEntry 2 }

-- {COLUMN} 1.3.6.1.4.1.248.32.18.2.24.3.1.3
hmSetupPublicSpotModuleProviderTableEntryAuthServerPort OBJECT-TYPE
    SYNTAX     Integer32 (0..65535)
    MAX-ACCESS read-write
    STATUS     current
    DESCRIPTION
            "-- empty --"
    ::= { hmSetupPublicSpotModuleProviderTableEntry 3 }

-- {COLUMN} 1.3.6.1.4.1.248.32.18.2.24.3.1.4
hmSetupPublicSpotModuleProviderTableEntryAuthServerSecret OBJECT-TYPE
    SYNTAX     DisplayString (SIZE(0..64))
    MAX-ACCESS read-write
    STATUS     current
    DESCRIPTION
            "-- empty --"
    ::= { hmSetupPublicSpotModuleProviderTableEntry 4 }

-- {COLUMN} 1.3.6.1.4.1.248.32.18.2.24.3.1.5
hmSetupPublicSpotModuleProviderTableEntryAccServerAddress OBJECT-TYPE
    SYNTAX     IpAddress
    MAX-ACCESS read-write
    STATUS     current
    DESCRIPTION
            "-- empty --"
    ::= { hmSetupPublicSpotModuleProviderTableEntry 5 }

-- {COLUMN} 1.3.6.1.4.1.248.32.18.2.24.3.1.6
hmSetupPublicSpotModuleProviderTableEntryAccServerPort OBJECT-TYPE
    SYNTAX     Integer32 (0..65535)
    MAX-ACCESS read-write
    STATUS     current
    DESCRIPTION
            "-- empty --"
    ::= { hmSetupPublicSpotModuleProviderTableEntry 6 }

-- {COLUMN} 1.3.6.1.4.1.248.32.18.2.24.3.1.7
hmSetupPublicSpotModuleProviderTableEntryAccServerSecret OBJECT-TYPE
    SYNTAX     DisplayString (SIZE(0..64))
    MAX-ACCESS read-write
    STATUS     current
    DESCRIPTION
            "-- empty --"
    ::= { hmSetupPublicSpotModuleProviderTableEntry 7 }

-- {COLUMN} 1.3.6.1.4.1.248.32.18.2.24.3.1.8
hmSetupPublicSpotModuleProviderTableEntryBackup OBJECT-TYPE
    SYNTAX     DisplayString (SIZE(0..16))
    MAX-ACCESS read-write
    STATUS     current
    DESCRIPTION
            "-- empty --"
    ::= { hmSetupPublicSpotModuleProviderTableEntry 8 }

-- {COLUMN} 1.3.6.1.4.1.248.32.18.2.24.3.1.9
hmSetupPublicSpotModuleProviderTableEntryAuthServerLoopbackAddr OBJECT-TYPE
    SYNTAX     DisplayString (SIZE(0..16))
    MAX-ACCESS read-write
    STATUS     current
    DESCRIPTION
            "-- empty --"
    ::= { hmSetupPublicSpotModuleProviderTableEntry 9 }

-- {COLUMN} 1.3.6.1.4.1.248.32.18.2.24.3.1.10
hmSetupPublicSpotModuleProviderTableEntryAccServerLoopbackAddr OBJECT-TYPE
    SYNTAX     DisplayString (SIZE(0..16))
    MAX-ACCESS read-write
    STATUS     current
    DESCRIPTION
            "-- empty --"
    ::= { hmSetupPublicSpotModuleProviderTableEntry 10 }

-- {COLUMN} 1.3.6.1.4.1.248.32.18.2.24.3.1.11
hmSetupPublicSpotModuleProviderTableEntryAuthServerProtocol OBJECT-TYPE
    SYNTAX     INTEGER {
                  eRadius (0),
                  eRadsec (1)
            }
    MAX-ACCESS read-write
    STATUS     current
    DESCRIPTION
            "-- empty --"
    ::= { hmSetupPublicSpotModuleProviderTableEntry 11 }

-- {COLUMN} 1.3.6.1.4.1.248.32.18.2.24.3.1.12
hmSetupPublicSpotModuleProviderTableEntryAccServerProtocol OBJECT-TYPE
    SYNTAX     INTEGER {
                  eRadius (0),
                  eRadsec (1)
            }
    MAX-ACCESS read-write
    STATUS     current
    DESCRIPTION
            "-- empty --"
    ::= { hmSetupPublicSpotModuleProviderTableEntry 12 }

-- {COLUMN} 1.3.6.1.4.1.248.32.18.2.24.3.1.13
hmSetupPublicSpotModuleProviderTableEntryAuthServerHostname OBJECT-TYPE
    SYNTAX     DisplayString (SIZE(0..64))
    MAX-ACCESS read-write
    STATUS     current
    DESCRIPTION
            "-- empty --"
    ::= { hmSetupPublicSpotModuleProviderTableEntry 13 }

-- {COLUMN} 1.3.6.1.4.1.248.32.18.2.24.3.1.14
hmSetupPublicSpotModuleProviderTableEntryAccServerHostname OBJECT-TYPE
    SYNTAX     DisplayString (SIZE(0..64))
    MAX-ACCESS read-write
    STATUS     current
    DESCRIPTION
            "-- empty --"
    ::= { hmSetupPublicSpotModuleProviderTableEntry 14 }

-- {COLUMN} 1.3.6.1.4.1.248.32.18.2.24.3.1.15
hmSetupPublicSpotModuleProviderTableEntryAuthAttributeValues OBJECT-TYPE
    SYNTAX     DisplayString (SIZE(0..251))
    MAX-ACCESS read-write
    STATUS     current
    DESCRIPTION
            "-- empty --"
    ::= { hmSetupPublicSpotModuleProviderTableEntry 15 }

-- {COLUMN} 1.3.6.1.4.1.248.32.18.2.24.3.1.16
hmSetupPublicSpotModuleProviderTableEntryAccAttributeValues OBJECT-TYPE
    SYNTAX     DisplayString (SIZE(0..251))
    MAX-ACCESS read-write
    STATUS     current
    DESCRIPTION
            "-- empty --"
    ::= { hmSetupPublicSpotModuleProviderTableEntry 16 }

-- {SCALAR} 1.3.6.1.4.1.248.32.18.2.24.5
hmSetupPublicSpotModuleTrafficLimitBytes OBJECT-TYPE
    SYNTAX     Integer32 (0..2147483647)
    MAX-ACCESS read-write
    STATUS     current
    DESCRIPTION
            "-- empty --"
    ::= { hmSetupPublicSpotModule 5 }

-- {SCALAR} 1.3.6.1.4.1.248.32.18.2.24.6
hmSetupPublicSpotModuleServerSubdir OBJECT-TYPE
    SYNTAX     DisplayString (SIZE(0..127))
    MAX-ACCESS read-write
    STATUS     current
    DESCRIPTION
            "-- empty --"
    ::= { hmSetupPublicSpotModule 6 }

-- {SCALAR} 1.3.6.1.4.1.248.32.18.2.24.7
hmSetupPublicSpotModuleAccountingCycle OBJECT-TYPE
    SYNTAX     Integer32 (0..2147483647)
    MAX-ACCESS read-write
    STATUS     current
    DESCRIPTION
            "-- empty --"
    ::= { hmSetupPublicSpotModule 7 }

-- {TABLE} 1.3.6.1.4.1.248.32.18.2.24.8
hmSetupPublicSpotModulePageTableTable OBJECT-TYPE
    SYNTAX     SEQUENCE OF HmSetupPublicSpotModulePageTableEntry
    MAX-ACCESS not-accessible
    STATUS     current
    DESCRIPTION
            "-- empty --"
    ::= { hmSetupPublicSpotModule 8 }

-- {ROW} 1.3.6.1.4.1.248.32.18.2.24.8.1
hmSetupPublicSpotModulePageTableEntry OBJECT-TYPE
    SYNTAX     HmSetupPublicSpotModulePageTableEntry
    MAX-ACCESS not-accessible
    STATUS     current
    DESCRIPTION
            ""
    INDEX {
            hmSetupPublicSpotModulePageTableEntryPage
          }
    ::= { hmSetupPublicSpotModulePageTableTable 1 }

HmSetupPublicSpotModulePageTableEntry ::= SEQUENCE {
            hmSetupPublicSpotModulePageTableEntryPage INTEGER,
            hmSetupPublicSpotModulePageTableEntryUrl DisplayString,
            hmSetupPublicSpotModulePageTableEntryFallback INTEGER,
            hmSetupPublicSpotModulePageTableEntryType INTEGER,
            hmSetupPublicSpotModulePageTableEntryLoopbackAddr DisplayString,
            hmSetupPublicSpotModulePageTableEntryTemplateCache INTEGER
    }

-- {COLUMN} 1.3.6.1.4.1.248.32.18.2.24.8.1.1
hmSetupPublicSpotModulePageTableEntryPage OBJECT-TYPE
    SYNTAX     INTEGER {
                  eWelcome (1),
                  eLogin (2),
                  eError (3),
                  eStart (4),
                  eStatus (5),
                  eLogoff (6),
                  eHelp (7),
                  eNoProxy (8),
                  eVoucher (9),
                  eGtc (10),
                  eRegistrationEMail (12),
                  eLoginEMail (13),
                  eRegistrationSms (14),
                  eLoginSms (15)
            }
    MAX-ACCESS read-only
    STATUS     current
    DESCRIPTION
            "-- empty --"
    ::= { hmSetupPublicSpotModulePageTableEntry 1 }

-- {COLUMN} 1.3.6.1.4.1.248.32.18.2.24.8.1.2
hmSetupPublicSpotModulePageTableEntryUrl OBJECT-TYPE
    SYNTAX     DisplayString (SIZE(0..251))
    MAX-ACCESS read-write
    STATUS     current
    DESCRIPTION
            "-- empty --"
    ::= { hmSetupPublicSpotModulePageTableEntry 2 }

-- {COLUMN} 1.3.6.1.4.1.248.32.18.2.24.8.1.3
hmSetupPublicSpotModulePageTableEntryFallback OBJECT-TYPE
    SYNTAX     INTEGER {
                  eNo (0),
                  eYes (1)
            }
    MAX-ACCESS read-write
    STATUS     current
    DESCRIPTION
            "-- empty --"
    ::= { hmSetupPublicSpotModulePageTableEntry 3 }

-- {COLUMN} 1.3.6.1.4.1.248.32.18.2.24.8.1.4
hmSetupPublicSpotModulePageTableEntryType OBJECT-TYPE
    SYNTAX     INTEGER {
                  eTemplate (0),
                  eRedirect (1)
            }
    MAX-ACCESS read-write
    STATUS     current
    DESCRIPTION
            "-- empty --"
    ::= { hmSetupPublicSpotModulePageTableEntry 4 }

-- {COLUMN} 1.3.6.1.4.1.248.32.18.2.24.8.1.5
hmSetupPublicSpotModulePageTableEntryLoopbackAddr OBJECT-TYPE
    SYNTAX     DisplayString (SIZE(0..16))
    MAX-ACCESS read-write
    STATUS     current
    DESCRIPTION
            "-- empty --"
    ::= { hmSetupPublicSpotModulePageTableEntry 5 }

-- {COLUMN} 1.3.6.1.4.1.248.32.18.2.24.8.1.6
hmSetupPublicSpotModulePageTableEntryTemplateCache OBJECT-TYPE
    SYNTAX     INTEGER {
                  eNo (0),
                  eYes (1)
            }
    MAX-ACCESS read-write
    STATUS     current
    DESCRIPTION
            "-- empty --"
    ::= { hmSetupPublicSpotModulePageTableEntry 6 }

-- {SCALAR} 1.3.6.1.4.1.248.32.18.2.24.9
hmSetupPublicSpotModuleRoamingSecret OBJECT-TYPE
    SYNTAX     DisplayString (SIZE(0..32))
    MAX-ACCESS read-write
    STATUS     current
    DESCRIPTION
            "-- empty --"
    ::= { hmSetupPublicSpotModule 9 }

-- {SCALAR} 1.3.6.1.4.1.248.32.18.2.24.12
hmSetupPublicSpotModuleCommunicationPort OBJECT-TYPE
    SYNTAX     Integer32 (0..65535)
    MAX-ACCESS read-write
    STATUS     current
    DESCRIPTION
            "-- empty --"
    ::= { hmSetupPublicSpotModule 12 }

-- {SCALAR} 1.3.6.1.4.1.248.32.18.2.24.14
hmSetupPublicSpotModuleIdleTimeout OBJECT-TYPE
    SYNTAX     Integer32 (0..2147483647)
    MAX-ACCESS read-write
    STATUS     current
    DESCRIPTION
            "-- empty --"
    ::= { hmSetupPublicSpotModule 14 }

-- {TABLE} 1.3.6.1.4.1.248.32.18.2.24.15
hmSetupPublicSpotModulePortTableTable OBJECT-TYPE
    SYNTAX     SEQUENCE OF HmSetupPublicSpotModulePortTableEntry
    MAX-ACCESS not-accessible
    STATUS     current
    DESCRIPTION
            "-- empty --"
    ::= { hmSetupPublicSpotModule 15 }

-- {ROW} 1.3.6.1.4.1.248.32.18.2.24.15.1
hmSetupPublicSpotModulePortTableEntry OBJECT-TYPE
    SYNTAX     HmSetupPublicSpotModulePortTableEntry
    MAX-ACCESS not-accessible
    STATUS     current
    DESCRIPTION
            ""
    INDEX {
            hmSetupPublicSpotModulePortTableEntryPort
          }
    ::= { hmSetupPublicSpotModulePortTableTable 1 }

HmSetupPublicSpotModulePortTableEntry ::= SEQUENCE {
            hmSetupPublicSpotModulePortTableEntryPort DisplayString,
            hmSetupPublicSpotModulePortTableEntryAuthenticationNecessary INTEGER
    }

-- {COLUMN} 1.3.6.1.4.1.248.32.18.2.24.15.1.2
hmSetupPublicSpotModulePortTableEntryPort OBJECT-TYPE
    SYNTAX     DisplayString (SIZE(0..18))
    MAX-ACCESS read-only
    STATUS     current
    DESCRIPTION
            "-- empty --"
    ::= { hmSetupPublicSpotModulePortTableEntry 2 }

-- {COLUMN} 1.3.6.1.4.1.248.32.18.2.24.15.1.3
hmSetupPublicSpotModulePortTableEntryAuthenticationNecessary OBJECT-TYPE
    SYNTAX     INTEGER {
                  eNo (0),
                  eYes (1)
            }
    MAX-ACCESS read-write
    STATUS     current
    DESCRIPTION
            "-- empty --"
    ::= { hmSetupPublicSpotModulePortTableEntry 3 }

-- {SCALAR} 1.3.6.1.4.1.248.32.18.2.24.16
hmSetupPublicSpotModuleAutoCleanupUserTable OBJECT-TYPE
    SYNTAX     INTEGER {
                  eNo (0),
                  eYes (1)
            }
    MAX-ACCESS read-write
    STATUS     current
    DESCRIPTION
            "-- empty --"
    ::= { hmSetupPublicSpotModule 16 }

-- {SCALAR} 1.3.6.1.4.1.248.32.18.2.24.17
hmSetupPublicSpotModuleProvideServerDatabase OBJECT-TYPE
    SYNTAX     INTEGER {
                  eNo (0),
                  eYes (1)
            }
    MAX-ACCESS read-write
    STATUS     current
    DESCRIPTION
            "-- empty --"
    ::= { hmSetupPublicSpotModule 17 }

-- {SCALAR} 1.3.6.1.4.1.248.32.18.2.24.18
hmSetupPublicSpotModuleDisallowMultipleLogin OBJECT-TYPE
    SYNTAX     INTEGER {
                  eNo (0),
                  eYes (1)
            }
    MAX-ACCESS read-write
    STATUS     current
    DESCRIPTION
            "-- empty --"
    ::= { hmSetupPublicSpotModule 18 }

-- {NODE} 1.3.6.1.4.1.248.32.18.2.24.19
hmSetupPublicSpotModuleAddUserWizard OBJECT IDENTIFIER ::= { hmSetupPublicSpotModule 19 }

-- {SCALAR} 1.3.6.1.4.1.248.32.18.2.24.19.2
hmSetupPublicSpotModuleAddUserWizardUsernamePattern OBJECT-TYPE
    SYNTAX     DisplayString (SIZE(0..19))
    MAX-ACCESS read-write
    STATUS     current
    DESCRIPTION
            "-- empty --"
    ::= { hmSetupPublicSpotModuleAddUserWizard 2 }

-- {SCALAR} 1.3.6.1.4.1.248.32.18.2.24.19.3
hmSetupPublicSpotModuleAddUserWizardPasswordLength OBJECT-TYPE
    SYNTAX     Integer32 (0..255)
    MAX-ACCESS read-write
    STATUS     current
    DESCRIPTION
            "-- empty --"
    ::= { hmSetupPublicSpotModuleAddUserWizard 3 }

-- {SCALAR} 1.3.6.1.4.1.248.32.18.2.24.19.4
hmSetupPublicSpotModuleAddUserWizardSsid OBJECT-TYPE
    SYNTAX     DisplayString (SIZE(0..32))
    MAX-ACCESS read-write
    STATUS     current
    DESCRIPTION
            "-- empty --"
    ::= { hmSetupPublicSpotModuleAddUserWizard 4 }

-- {TABLE} 1.3.6.1.4.1.248.32.18.2.24.19.5
hmSetupPublicSpotModuleAddUserWizardDefaultRuntimeTable OBJECT-TYPE
    SYNTAX     SEQUENCE OF HmSetupPublicSpotModuleAddUserWizardDefaultRuntimeEntry
    MAX-ACCESS not-accessible
    STATUS     current
    DESCRIPTION
            "-- empty --"
    ::= { hmSetupPublicSpotModuleAddUserWizard 5 }

-- {ROW} 1.3.6.1.4.1.248.32.18.2.24.19.5.1
hmSetupPublicSpotModuleAddUserWizardDefaultRuntimeEntry OBJECT-TYPE
    SYNTAX     HmSetupPublicSpotModuleAddUserWizardDefaultRuntimeEntry
    MAX-ACCESS not-accessible
    STATUS     current
    DESCRIPTION
            ""
    INDEX {
            hmSetupPublicSpotModuleAddUserWizardDefaultRuntimeEntryRuntime,
            hmSetupPublicSpotModuleAddUserWizardDefaultRuntimeEntryUnit
          }
    ::= { hmSetupPublicSpotModuleAddUserWizardDefaultRuntimeTable 1 }

HmSetupPublicSpotModuleAddUserWizardDefaultRuntimeEntry ::= SEQUENCE {
            hmSetupPublicSpotModuleAddUserWizardDefaultRuntimeEntryRuntime Integer32,
            hmSetupPublicSpotModuleAddUserWizardDefaultRuntimeEntryUnit INTEGER
    }

-- {COLUMN} 1.3.6.1.4.1.248.32.18.2.24.19.5.1.1
hmSetupPublicSpotModuleAddUserWizardDefaultRuntimeEntryRuntime OBJECT-TYPE
    SYNTAX     Integer32 (0..65535)
    MAX-ACCESS read-write
    STATUS     current
    DESCRIPTION
            "-- empty --"
    ::= { hmSetupPublicSpotModuleAddUserWizardDefaultRuntimeEntry 1 }

-- {COLUMN} 1.3.6.1.4.1.248.32.18.2.24.19.5.1.2
hmSetupPublicSpotModuleAddUserWizardDefaultRuntimeEntryUnit OBJECT-TYPE
    SYNTAX     INTEGER {
                  eHourS (0),
                  eDayS (1),
                  eMinuteS (2)
            }
    MAX-ACCESS read-write
    STATUS     current
    DESCRIPTION
            "-- empty --"
    ::= { hmSetupPublicSpotModuleAddUserWizardDefaultRuntimeEntry 2 }

-- {TABLE} 1.3.6.1.4.1.248.32.18.2.24.19.6
hmSetupPublicSpotModuleAddUserWizardCommentFieldsTable OBJECT-TYPE
    SYNTAX     SEQUENCE OF HmSetupPublicSpotModuleAddUserWizardCommentFieldsEntry
    MAX-ACCESS not-accessible
    STATUS     current
    DESCRIPTION
            "-- empty --"
    ::= { hmSetupPublicSpotModuleAddUserWizard 6 }

-- {ROW} 1.3.6.1.4.1.248.32.18.2.24.19.6.1
hmSetupPublicSpotModuleAddUserWizardCommentFieldsEntry OBJECT-TYPE
    SYNTAX     HmSetupPublicSpotModuleAddUserWizardCommentFieldsEntry
    MAX-ACCESS not-accessible
    STATUS     current
    DESCRIPTION
            ""
    INDEX {
            hmSetupPublicSpotModuleAddUserWizardCommentFieldsEntryFieldName
          }
    ::= { hmSetupPublicSpotModuleAddUserWizardCommentFieldsTable 1 }

HmSetupPublicSpotModuleAddUserWizardCommentFieldsEntry ::= SEQUENCE {
            hmSetupPublicSpotModuleAddUserWizardCommentFieldsEntryFieldName DisplayString
    }

-- {COLUMN} 1.3.6.1.4.1.248.32.18.2.24.19.6.1.1
hmSetupPublicSpotModuleAddUserWizardCommentFieldsEntryFieldName OBJECT-TYPE
    SYNTAX     DisplayString (SIZE(0..31))
    MAX-ACCESS read-write
    STATUS     current
    DESCRIPTION
            "-- empty --"
    ::= { hmSetupPublicSpotModuleAddUserWizardCommentFieldsEntry 1 }

-- {SCALAR} 1.3.6.1.4.1.248.32.18.2.24.19.7
hmSetupPublicSpotModuleAddUserWizardDefaultStartingTime OBJECT-TYPE
    SYNTAX     INTEGER {
                  eImmediately (1),
                  eFirstLogin (3)
            }
    MAX-ACCESS read-write
    STATUS     current
    DESCRIPTION
            "-- empty --"
    ::= { hmSetupPublicSpotModuleAddUserWizard 7 }

-- {SCALAR} 1.3.6.1.4.1.248.32.18.2.24.19.8
hmSetupPublicSpotModuleAddUserWizardPrintCommentsOnVoucher OBJECT-TYPE
    SYNTAX     INTEGER {
                  eNo (0),
                  eYes (1)
            }
    MAX-ACCESS read-write
    STATUS     current
    DESCRIPTION
            "-- empty --"
    ::= { hmSetupPublicSpotModuleAddUserWizard 8 }

-- {SCALAR} 1.3.6.1.4.1.248.32.18.2.24.19.9
hmSetupPublicSpotModuleAddUserWizardMaxVoucherValPeriod OBJECT-TYPE
    SYNTAX     Integer32 (0..2147483647)
    MAX-ACCESS read-write
    STATUS     current
    DESCRIPTION
            "Maximal voucher validate period"
    ::= { hmSetupPublicSpotModuleAddUserWizard 9 }

-- {SCALAR} 1.3.6.1.4.1.248.32.18.2.24.19.10
hmSetupPublicSpotModuleAddUserWizardAvailableExpiryMethods OBJECT-TYPE
    SYNTAX     INTEGER {
                  eAllMethods (0),
                  eCurrentTimeMethod (1),
                  eLoginTimeMethod (2)
            }
    MAX-ACCESS read-write
    STATUS     current
    DESCRIPTION
            "-- empty --"
    ::= { hmSetupPublicSpotModuleAddUserWizard 10 }

-- {TABLE} 1.3.6.1.4.1.248.32.18.2.24.19.11
hmSetupPublicSpotModuleAddUserWizardSsidTableTable OBJECT-TYPE
    SYNTAX     SEQUENCE OF HmSetupPublicSpotModuleAddUserWizardSsidTableEntry
    MAX-ACCESS not-accessible
    STATUS     current
    DESCRIPTION
            "-- empty --"
    ::= { hmSetupPublicSpotModuleAddUserWizard 11 }

-- {ROW} 1.3.6.1.4.1.248.32.18.2.24.19.11.1
hmSetupPublicSpotModuleAddUserWizardSsidTableEntry OBJECT-TYPE
    SYNTAX     HmSetupPublicSpotModuleAddUserWizardSsidTableEntry
    MAX-ACCESS not-accessible
    STATUS     current
    DESCRIPTION
            ""
    INDEX {
            hmSetupPublicSpotModuleAddUserWizardSsidTableEntryNetworkName
          }
    ::= { hmSetupPublicSpotModuleAddUserWizardSsidTableTable 1 }

HmSetupPublicSpotModuleAddUserWizardSsidTableEntry ::= SEQUENCE {
            hmSetupPublicSpotModuleAddUserWizardSsidTableEntryNetworkName DisplayString,
            hmSetupPublicSpotModuleAddUserWizardSsidTableEntryDefault INTEGER
    }

-- {COLUMN} 1.3.6.1.4.1.248.32.18.2.24.19.11.1.1
hmSetupPublicSpotModuleAddUserWizardSsidTableEntryNetworkName OBJECT-TYPE
    SYNTAX     DisplayString (SIZE(0..32))
    MAX-ACCESS read-write
    STATUS     current
    DESCRIPTION
            "-- empty --"
    ::= { hmSetupPublicSpotModuleAddUserWizardSsidTableEntry 1 }

-- {COLUMN} 1.3.6.1.4.1.248.32.18.2.24.19.11.1.2
hmSetupPublicSpotModuleAddUserWizardSsidTableEntryDefault OBJECT-TYPE
    SYNTAX     INTEGER {
                  eNo (0),
                  eYes (1)
            }
    MAX-ACCESS read-write
    STATUS     current
    DESCRIPTION
            "-- empty --"
    ::= { hmSetupPublicSpotModuleAddUserWizardSsidTableEntry 2 }

-- {SCALAR} 1.3.6.1.4.1.248.32.18.2.24.19.12
hmSetupPublicSpotModuleAddUserWizardUserNameCaseSensitive OBJECT-TYPE
    SYNTAX     INTEGER {
                  eNo (0),
                  eYes (1)
            }
    MAX-ACCESS read-write
    STATUS     current
    DESCRIPTION
            "-- empty --"
    ::= { hmSetupPublicSpotModuleAddUserWizard 12 }

-- {SCALAR} 1.3.6.1.4.1.248.32.18.2.24.19.13
hmSetupPublicSpotModuleAddUserWizardHideCaseSensitiveCheckbox OBJECT-TYPE
    SYNTAX     INTEGER {
                  eNo (0),
                  eYes (1)
            }
    MAX-ACCESS read-write
    STATUS     current
    DESCRIPTION
            "-- empty --"
    ::= { hmSetupPublicSpotModuleAddUserWizard 13 }

-- {TABLE} 1.3.6.1.4.1.248.32.18.2.24.19.14
hmSetupPublicSpotModuleAddUserWizardMaxConcLoginsTable OBJECT-TYPE
    SYNTAX     SEQUENCE OF HmSetupPublicSpotModuleAddUserWizardMaxConcLoginsEntry
    MAX-ACCESS not-accessible
    STATUS     current
    DESCRIPTION
            ""
    ::= { hmSetupPublicSpotModuleAddUserWizard 14 }

-- {ROW} 1.3.6.1.4.1.248.32.18.2.24.19.14.1
hmSetupPublicSpotModuleAddUserWizardMaxConcLoginsEntry OBJECT-TYPE
    SYNTAX     HmSetupPublicSpotModuleAddUserWizardMaxConcLoginsEntry
    MAX-ACCESS not-accessible
    STATUS     current
    DESCRIPTION
            ""
    INDEX {
            hmSetupPublicSpotModuleAddUserWizardMaxConcLoginsEntryValue
          }
    ::= { hmSetupPublicSpotModuleAddUserWizardMaxConcLoginsTable 1 }

HmSetupPublicSpotModuleAddUserWizardMaxConcLoginsEntry ::= SEQUENCE {
            hmSetupPublicSpotModuleAddUserWizardMaxConcLoginsEntryValue DisplayString
    }

-- {COLUMN} 1.3.6.1.4.1.248.32.18.2.24.19.14.1.1
hmSetupPublicSpotModuleAddUserWizardMaxConcLoginsEntryValue OBJECT-TYPE
    SYNTAX     DisplayString (SIZE(0..5))
    MAX-ACCESS read-write
    STATUS     current
    DESCRIPTION
            "-- empty --"
    ::= { hmSetupPublicSpotModuleAddUserWizardMaxConcLoginsEntry 1 }

-- {SCALAR} 1.3.6.1.4.1.248.32.18.2.24.19.15
hmSetupPublicSpotModuleAddUserWizardMultiLogin OBJECT-TYPE
    SYNTAX     INTEGER {
                  eNo (0),
                  eYes (1)
            }
    MAX-ACCESS read-write
    STATUS     current
    DESCRIPTION
            "-- empty --"
    ::= { hmSetupPublicSpotModuleAddUserWizard 15 }

-- {SCALAR} 1.3.6.1.4.1.248.32.18.2.24.19.16
hmSetupPublicSpotModuleAddUserWizardHideMultiLoginCheckbox OBJECT-TYPE
    SYNTAX     INTEGER {
                  eNo (0),
                  eYes (1)
            }
    MAX-ACCESS read-write
    STATUS     current
    DESCRIPTION
            "-- empty --"
    ::= { hmSetupPublicSpotModuleAddUserWizard 16 }

-- {TABLE} 1.3.6.1.4.1.248.32.18.2.24.19.17
hmSetupPublicSpotModuleAddUserWizardBWidthProTable OBJECT-TYPE
    SYNTAX     SEQUENCE OF HmSetupPublicSpotModuleAddUserWizardBWidthProEntry
    MAX-ACCESS not-accessible
    STATUS     current
    DESCRIPTION
            ""
    ::= { hmSetupPublicSpotModuleAddUserWizard 17 }

-- {ROW} 1.3.6.1.4.1.248.32.18.2.24.19.17.1
hmSetupPublicSpotModuleAddUserWizardBWidthProEntry OBJECT-TYPE
    SYNTAX     HmSetupPublicSpotModuleAddUserWizardBWidthProEntry
    MAX-ACCESS not-accessible
    STATUS     current
    DESCRIPTION
            ""
    INDEX {
            hmSetupPublicSpotModuleAddUserWizardBWidthProEntryProfileName
          }
    ::= { hmSetupPublicSpotModuleAddUserWizardBWidthProTable 1 }

HmSetupPublicSpotModuleAddUserWizardBWidthProEntry ::= SEQUENCE {
            hmSetupPublicSpotModuleAddUserWizardBWidthProEntryProfileName DisplayString,
            hmSetupPublicSpotModuleAddUserWizardBWidthProEntryTxBandwidth Integer32,
            hmSetupPublicSpotModuleAddUserWizardBWidthProEntryRxBandwidth Integer32
    }

-- {COLUMN} 1.3.6.1.4.1.248.32.18.2.24.19.17.1.1
hmSetupPublicSpotModuleAddUserWizardBWidthProEntryProfileName OBJECT-TYPE
    SYNTAX     DisplayString (SIZE(0..255))
    MAX-ACCESS read-write
    STATUS     current
    DESCRIPTION
            "-- empty --"
    ::= { hmSetupPublicSpotModuleAddUserWizardBWidthProEntry 1 }

-- {COLUMN} 1.3.6.1.4.1.248.32.18.2.24.19.17.1.2
hmSetupPublicSpotModuleAddUserWizardBWidthProEntryTxBandwidth OBJECT-TYPE
    SYNTAX     Integer32 (0..2147483647)
    MAX-ACCESS read-write
    STATUS     current
    DESCRIPTION
            "-- empty --"
    ::= { hmSetupPublicSpotModuleAddUserWizardBWidthProEntry 2 }

-- {COLUMN} 1.3.6.1.4.1.248.32.18.2.24.19.17.1.3
hmSetupPublicSpotModuleAddUserWizardBWidthProEntryRxBandwidth OBJECT-TYPE
    SYNTAX     Integer32 (0..2147483647)
    MAX-ACCESS read-write
    STATUS     current
    DESCRIPTION
            "-- empty --"
    ::= { hmSetupPublicSpotModuleAddUserWizardBWidthProEntry 3 }

-- {SCALAR} 1.3.6.1.4.1.248.32.18.2.24.19.18
hmSetupPublicSpotModuleAddUserWizardPasswordCharacterSet OBJECT-TYPE
    SYNTAX     INTEGER {
                  eCharactersPlusDigits (0),
                  eCharacters (1),
                  eDigits (2)
            }
    MAX-ACCESS read-write
    STATUS     current
    DESCRIPTION
            "-- empty --"
    ::= { hmSetupPublicSpotModuleAddUserWizard 18 }

-- {SCALAR} 1.3.6.1.4.1.248.32.18.2.24.19.19
hmSetupPublicSpotModuleAddUserWizardHideCsvExport OBJECT-TYPE
    SYNTAX     INTEGER {
                  eNo (0),
                  eYes (1)
            }
    MAX-ACCESS read-write
    STATUS     current
    DESCRIPTION
            "-- empty --"
    ::= { hmSetupPublicSpotModuleAddUserWizard 19 }

-- {SCALAR} 1.3.6.1.4.1.248.32.18.2.24.19.20
hmSetupPublicSpotModuleAddUserWizardHideUserManagementButton OBJECT-TYPE
    SYNTAX     INTEGER {
                  eNo (0),
                  eYes (1)
            }
    MAX-ACCESS read-write
    STATUS     current
    DESCRIPTION
            "-- empty --"
    ::= { hmSetupPublicSpotModuleAddUserWizard 20 }

-- {TABLE} 1.3.6.1.4.1.248.32.18.2.24.20
hmSetupPublicSpotModuleVlanTableTable OBJECT-TYPE
    SYNTAX     SEQUENCE OF HmSetupPublicSpotModuleVlanTableEntry
    MAX-ACCESS not-accessible
    STATUS     current
    DESCRIPTION
            "-- empty --"
    ::= { hmSetupPublicSpotModule 20 }

-- {ROW} 1.3.6.1.4.1.248.32.18.2.24.20.1
hmSetupPublicSpotModuleVlanTableEntry OBJECT-TYPE
    SYNTAX     HmSetupPublicSpotModuleVlanTableEntry
    MAX-ACCESS not-accessible
    STATUS     current
    DESCRIPTION
            ""
    INDEX {
            hmSetupPublicSpotModuleVlanTableEntryVlanId
          }
    ::= { hmSetupPublicSpotModuleVlanTableTable 1 }

HmSetupPublicSpotModuleVlanTableEntry ::= SEQUENCE {
            hmSetupPublicSpotModuleVlanTableEntryVlanId Integer32
    }

-- {COLUMN} 1.3.6.1.4.1.248.32.18.2.24.20.1.1
hmSetupPublicSpotModuleVlanTableEntryVlanId OBJECT-TYPE
    SYNTAX     Integer32 (0..65535)
    MAX-ACCESS read-write
    STATUS     current
    DESCRIPTION
            "-- empty --"
    ::= { hmSetupPublicSpotModuleVlanTableEntry 1 }

-- {SCALAR} 1.3.6.1.4.1.248.32.18.2.24.21
hmSetupPublicSpotModuleLoginPageType OBJECT-TYPE
    SYNTAX     INTEGER {
                  eHttps (0),
                  eHttp (1)
            }
    MAX-ACCESS read-write
    STATUS     current
    DESCRIPTION
            "-- empty --"
    ::= { hmSetupPublicSpotModule 21 }

-- {SCALAR} 1.3.6.1.4.1.248.32.18.2.24.22
hmSetupPublicSpotModuleDeviceHostname OBJECT-TYPE
    SYNTAX     DisplayString (SIZE(0..31))
    MAX-ACCESS read-write
    STATUS     current
    DESCRIPTION
            "-- empty --"
    ::= { hmSetupPublicSpotModule 22 }

-- {TABLE} 1.3.6.1.4.1.248.32.18.2.24.23
hmSetupPublicSpotModuleMacAddressTableTable OBJECT-TYPE
    SYNTAX     SEQUENCE OF HmSetupPublicSpotModuleMacAddressTableEntry
    MAX-ACCESS not-accessible
    STATUS     current
    DESCRIPTION
            "-- empty --"
    ::= { hmSetupPublicSpotModule 23 }

-- {ROW} 1.3.6.1.4.1.248.32.18.2.24.23.1
hmSetupPublicSpotModuleMacAddressTableEntry OBJECT-TYPE
    SYNTAX     HmSetupPublicSpotModuleMacAddressTableEntry
    MAX-ACCESS not-accessible
    STATUS     current
    DESCRIPTION
            ""
    INDEX {
            hmSetupPublicSpotModuleMacAddressTableEntryMacAddress
          }
    ::= { hmSetupPublicSpotModuleMacAddressTableTable 1 }

HmSetupPublicSpotModuleMacAddressTableEntry ::= SEQUENCE {
            hmSetupPublicSpotModuleMacAddressTableEntryMacAddress MacAddress,
            hmSetupPublicSpotModuleMacAddressTableEntryUserName DisplayString,
            hmSetupPublicSpotModuleMacAddressTableEntryProvider DisplayString
    }

-- {COLUMN} 1.3.6.1.4.1.248.32.18.2.24.23.1.1
hmSetupPublicSpotModuleMacAddressTableEntryMacAddress OBJECT-TYPE
    SYNTAX     MacAddress
    MAX-ACCESS read-write
    STATUS     current
    DESCRIPTION
            "-- empty --"
    ::= { hmSetupPublicSpotModuleMacAddressTableEntry 1 }

-- {COLUMN} 1.3.6.1.4.1.248.32.18.2.24.23.1.2
hmSetupPublicSpotModuleMacAddressTableEntryUserName OBJECT-TYPE
    SYNTAX     DisplayString (SIZE(0..64))
    MAX-ACCESS read-write
    STATUS     current
    DESCRIPTION
            "-- empty --"
    ::= { hmSetupPublicSpotModuleMacAddressTableEntry 2 }

-- {COLUMN} 1.3.6.1.4.1.248.32.18.2.24.23.1.3
hmSetupPublicSpotModuleMacAddressTableEntryProvider OBJECT-TYPE
    SYNTAX     DisplayString (SIZE(0..16))
    MAX-ACCESS read-write
    STATUS     current
    DESCRIPTION
            "-- empty --"
    ::= { hmSetupPublicSpotModuleMacAddressTableEntry 3 }

-- {SCALAR} 1.3.6.1.4.1.248.32.18.2.24.24
hmSetupPublicSpotModuleMacAddressCheckProvider OBJECT-TYPE
    SYNTAX     DisplayString (SIZE(0..16))
    MAX-ACCESS read-write
    STATUS     current
    DESCRIPTION
            "-- empty --"
    ::= { hmSetupPublicSpotModule 24 }

-- {SCALAR} 1.3.6.1.4.1.248.32.18.2.24.25
hmSetupPublicSpotModuleMacAddressCheckCacheTime OBJECT-TYPE
    SYNTAX     Integer32 (0..2147483647)
    MAX-ACCESS read-write
    STATUS     current
    DESCRIPTION
            "-- empty --"
    ::= { hmSetupPublicSpotModule 25 }

-- {SCALAR} 1.3.6.1.4.1.248.32.18.2.24.26
hmSetupPublicSpotModuleStationTableLimit OBJECT-TYPE
    SYNTAX     Integer32 (0..2147483647)
    MAX-ACCESS read-write
    STATUS     current
    DESCRIPTION
            "-- empty --"
    ::= { hmSetupPublicSpotModule 26 }

-- {SCALAR} 1.3.6.1.4.1.248.32.18.2.24.30
hmSetupPublicSpotModuleFreeServer OBJECT-TYPE
    SYNTAX     DisplayString (SIZE(0..64))
    MAX-ACCESS read-write
    STATUS     current
    DESCRIPTION
            "-- empty --"
    ::= { hmSetupPublicSpotModule 30 }

-- {TABLE} 1.3.6.1.4.1.248.32.18.2.24.31
hmSetupPublicSpotModuleFreeNetworksTable OBJECT-TYPE
    SYNTAX     SEQUENCE OF HmSetupPublicSpotModuleFreeNetworksEntry
    MAX-ACCESS not-accessible
    STATUS     current
    DESCRIPTION
            "-- empty --"
    ::= { hmSetupPublicSpotModule 31 }

-- {ROW} 1.3.6.1.4.1.248.32.18.2.24.31.1
hmSetupPublicSpotModuleFreeNetworksEntry OBJECT-TYPE
    SYNTAX     HmSetupPublicSpotModuleFreeNetworksEntry
    MAX-ACCESS not-accessible
    STATUS     current
    DESCRIPTION
            ""
    INDEX {
            hmSetupPublicSpotModuleFreeNetworksEntryHostName
          }
    ::= { hmSetupPublicSpotModuleFreeNetworksTable 1 }

HmSetupPublicSpotModuleFreeNetworksEntry ::= SEQUENCE {
            hmSetupPublicSpotModuleFreeNetworksEntryHostName DisplayString,
            hmSetupPublicSpotModuleFreeNetworksEntryMask IpAddress,
            hmSetupPublicSpotModuleFreeNetworksEntryVlans DisplayString
    }

-- {COLUMN} 1.3.6.1.4.1.248.32.18.2.24.31.1.1
hmSetupPublicSpotModuleFreeNetworksEntryHostName OBJECT-TYPE
    SYNTAX     DisplayString (SIZE(0..64))
    MAX-ACCESS read-write
    STATUS     current
    DESCRIPTION
            "-- empty --"
    ::= { hmSetupPublicSpotModuleFreeNetworksEntry 1 }

-- {COLUMN} 1.3.6.1.4.1.248.32.18.2.24.31.1.2
hmSetupPublicSpotModuleFreeNetworksEntryMask OBJECT-TYPE
    SYNTAX     IpAddress
    MAX-ACCESS read-write
    STATUS     current
    DESCRIPTION
            "-- empty --"
    ::= { hmSetupPublicSpotModuleFreeNetworksEntry 2 }

-- {COLUMN} 1.3.6.1.4.1.248.32.18.2.24.31.1.3
hmSetupPublicSpotModuleFreeNetworksEntryVlans OBJECT-TYPE
    SYNTAX     DisplayString (SIZE(0..254))
    MAX-ACCESS read-write
    STATUS     current
    DESCRIPTION
            "-- empty --"
    ::= { hmSetupPublicSpotModuleFreeNetworksEntry 3 }

-- {SCALAR} 1.3.6.1.4.1.248.32.18.2.24.32
hmSetupPublicSpotModuleFreeHostsMinimumTtl OBJECT-TYPE
    SYNTAX     Integer32 (0..2147483647)
    MAX-ACCESS read-write
    STATUS     current
    DESCRIPTION
            "-- empty --"
    ::= { hmSetupPublicSpotModule 32 }

-- {SCALAR} 1.3.6.1.4.1.248.32.18.2.24.33
hmSetupPublicSpotModuleLoginText OBJECT-TYPE
    SYNTAX     DisplayString (SIZE(0..254))
    MAX-ACCESS read-write
    STATUS     current
    DESCRIPTION
            "-- empty --"
    ::= { hmSetupPublicSpotModule 33 }

-- {SCALAR} 1.3.6.1.4.1.248.32.18.2.24.34
hmSetupPublicSpotModuleWanConnection OBJECT-TYPE
    SYNTAX     DisplayString (SIZE(0..16))
    MAX-ACCESS read-write
    STATUS     current
    DESCRIPTION
            "-- empty --"
    ::= { hmSetupPublicSpotModule 34 }

-- {SCALAR} 1.3.6.1.4.1.248.32.18.2.24.35
hmSetupPublicSpotModulePrintLogoAndHeaderboard OBJECT-TYPE
    SYNTAX     INTEGER {
                  eNo (0),
                  eYes (1)
            }
    MAX-ACCESS read-write
    STATUS     current
    DESCRIPTION
            "-- empty --"
    ::= { hmSetupPublicSpotModule 35 }

-- {SCALAR} 1.3.6.1.4.1.248.32.18.2.24.36
hmSetupPublicSpotModuleUserMustAcceptGtc OBJECT-TYPE
    SYNTAX     INTEGER {
                  eNo (0),
                  eYes (1)
            }
    MAX-ACCESS read-write
    STATUS     current
    DESCRIPTION
            "-- empty --"
    ::= { hmSetupPublicSpotModule 36 }

-- {SCALAR} 1.3.6.1.4.1.248.32.18.2.24.37
hmSetupPublicSpotModulePrintLogoutLink OBJECT-TYPE
    SYNTAX     INTEGER {
                  eNo (0),
                  eYes (1)
            }
    MAX-ACCESS read-write
    STATUS     current
    DESCRIPTION
            "-- empty --"
    ::= { hmSetupPublicSpotModule 37 }

-- {NODE} 1.3.6.1.4.1.248.32.18.2.24.40
hmSetupPublicSpotModuleXmlInterface OBJECT IDENTIFIER ::= { hmSetupPublicSpotModule 40 }

-- {SCALAR} 1.3.6.1.4.1.248.32.18.2.24.40.1
hmSetupPublicSpotModuleXmlInterfaceOperating OBJECT-TYPE
    SYNTAX     INTEGER {
                  eNo (0),
                  eYes (1)
            }
    MAX-ACCESS read-write
    STATUS     current
    DESCRIPTION
            "-- empty --"
    ::= { hmSetupPublicSpotModuleXmlInterface 1 }

-- {SCALAR} 1.3.6.1.4.1.248.32.18.2.24.40.2
hmSetupPublicSpotModuleXmlInterfaceRadiusAuthentication OBJECT-TYPE
    SYNTAX     INTEGER {
                  eNo (0),
                  eYes (1)
            }
    MAX-ACCESS read-write
    STATUS     current
    DESCRIPTION
            "-- empty --"
    ::= { hmSetupPublicSpotModuleXmlInterface 2 }

-- {NODE} 1.3.6.1.4.1.248.32.18.2.24.41
hmSetupPublicSpotModuleAuthMod OBJECT IDENTIFIER ::= { hmSetupPublicSpotModule 41 }

-- {NODE} 1.3.6.1.4.1.248.32.18.2.24.41.1
hmSetupPublicSpotModuleAuthModEmlAuth OBJECT IDENTIFIER ::= { hmSetupPublicSpotModuleAuthMod 1 }

-- {SCALAR} 1.3.6.1.4.1.248.32.18.2.24.41.1.1
hmSetupPublicSpotModuleAuthModEmlAuthLimitEMailsPerHour OBJECT-TYPE
    SYNTAX     Integer32 (0..65535)
    MAX-ACCESS read-write
    STATUS     current
    DESCRIPTION
            "-- empty --"
    ::= { hmSetupPublicSpotModuleAuthModEmlAuth 1 }

-- {SCALAR} 1.3.6.1.4.1.248.32.18.2.24.41.1.2
hmSetupPublicSpotModuleAuthModEmlAuthUserMustAcceptGtc OBJECT-TYPE
    SYNTAX     INTEGER {
                  eNo (0),
                  eYes (1)
            }
    MAX-ACCESS read-only
    STATUS     current
    DESCRIPTION
            "-- empty --"
    ::= { hmSetupPublicSpotModuleAuthModEmlAuth 2 }

-- {SCALAR} 1.3.6.1.4.1.248.32.18.2.24.41.1.3
hmSetupPublicSpotModuleAuthModEmlAuthSubject OBJECT-TYPE
    SYNTAX     DisplayString (SIZE(0..256))
    MAX-ACCESS read-write
    STATUS     current
    DESCRIPTION
            "-- empty --"
    ::= { hmSetupPublicSpotModuleAuthModEmlAuth 3 }

-- {SCALAR} 1.3.6.1.4.1.248.32.18.2.24.41.1.4
hmSetupPublicSpotModuleAuthModEmlAuthBody OBJECT-TYPE
    SYNTAX     DisplayString (SIZE(0..256))
    MAX-ACCESS read-write
    STATUS     current
    DESCRIPTION
            "-- empty --"
    ::= { hmSetupPublicSpotModuleAuthModEmlAuth 4 }

-- {SCALAR} 1.3.6.1.4.1.248.32.18.2.24.41.1.5
hmSetupPublicSpotModuleAuthModEmlAuthMaxRequestAttempts OBJECT-TYPE
    SYNTAX     Integer32 (0..65535)
    MAX-ACCESS read-write
    STATUS     current
    DESCRIPTION
            "-- empty --"
    ::= { hmSetupPublicSpotModuleAuthModEmlAuth 5 }

-- {SCALAR} 1.3.6.1.4.1.248.32.18.2.24.41.1.6
hmSetupPublicSpotModuleAuthModEmlAuthLocalEMailAddress OBJECT-TYPE
    SYNTAX     DisplayString (SIZE(0..150))
    MAX-ACCESS read-write
    STATUS     current
    DESCRIPTION
            "-- empty --"
    ::= { hmSetupPublicSpotModuleAuthModEmlAuth 6 }

-- {SCALAR} 1.3.6.1.4.1.248.32.18.2.24.41.1.7
hmSetupPublicSpotModuleAuthModEmlAuthRealName OBJECT-TYPE
    SYNTAX     DisplayString (SIZE(0..150))
    MAX-ACCESS read-write
    STATUS     current
    DESCRIPTION
            "-- empty --"
    ::= { hmSetupPublicSpotModuleAuthModEmlAuth 7 }

-- {SCALAR} 1.3.6.1.4.1.248.32.18.2.24.41.1.8
hmSetupPublicSpotModuleAuthModEmlAuthBlackWhiteDomainList OBJECT-TYPE
    SYNTAX     INTEGER {
                  eBlacklist (0),
                  eWhitelist (1)
            }
    MAX-ACCESS read-write
    STATUS     current
    DESCRIPTION
            "-- empty --"
    ::= { hmSetupPublicSpotModuleAuthModEmlAuth 8 }

-- {TABLE} 1.3.6.1.4.1.248.32.18.2.24.41.1.9
hmSetupPublicSpotModuleAuthModEmlAuthDomainListTable OBJECT-TYPE
    SYNTAX     SEQUENCE OF HmSetupPublicSpotModuleAuthModEmlAuthDomainListEntry
    MAX-ACCESS not-accessible
    STATUS     current
    DESCRIPTION
            "-- empty --"
    ::= { hmSetupPublicSpotModuleAuthModEmlAuth 9 }

-- {ROW} 1.3.6.1.4.1.248.32.18.2.24.41.1.9.1
hmSetupPublicSpotModuleAuthModEmlAuthDomainListEntry OBJECT-TYPE
    SYNTAX     HmSetupPublicSpotModuleAuthModEmlAuthDomainListEntry
    MAX-ACCESS not-accessible
    STATUS     current
    DESCRIPTION
            ""
    INDEX {
            hmSetupPublicSpotModuleAuthModEmlAuthDomainListEntryDomain
          }
    ::= { hmSetupPublicSpotModuleAuthModEmlAuthDomainListTable 1 }

HmSetupPublicSpotModuleAuthModEmlAuthDomainListEntry ::= SEQUENCE {
            hmSetupPublicSpotModuleAuthModEmlAuthDomainListEntryDomain DisplayString
    }

-- {COLUMN} 1.3.6.1.4.1.248.32.18.2.24.41.1.9.1.1
hmSetupPublicSpotModuleAuthModEmlAuthDomainListEntryDomain OBJECT-TYPE
    SYNTAX     DisplayString (SIZE(0..150))
    MAX-ACCESS read-write
    STATUS     current
    DESCRIPTION
            "-- empty --"
    ::= { hmSetupPublicSpotModuleAuthModEmlAuthDomainListEntry 1 }

-- {TABLE} 1.3.6.1.4.1.248.32.18.2.24.41.1.20
hmSetupPublicSpotModuleAuthModEmlAuthRealNameTable OBJECT-TYPE
    SYNTAX     SEQUENCE OF HmSetupPublicSpotModuleAuthModEmlAuthRealNameEntry
    MAX-ACCESS not-accessible
    STATUS     current
    DESCRIPTION
            "-- empty --"
    ::= { hmSetupPublicSpotModuleAuthModEmlAuth 20 }

-- {ROW} 1.3.6.1.4.1.248.32.18.2.24.41.1.20.1
hmSetupPublicSpotModuleAuthModEmlAuthRealNameEntry OBJECT-TYPE
    SYNTAX     HmSetupPublicSpotModuleAuthModEmlAuthRealNameEntry
    MAX-ACCESS not-accessible
    STATUS     current
    DESCRIPTION
            ""
    INDEX {
            hmSetupPublicSpotModuleAuthModEmlAuthRealNameEntryLanguage
          }
    ::= { hmSetupPublicSpotModuleAuthModEmlAuthRealNameTable 1 }

HmSetupPublicSpotModuleAuthModEmlAuthRealNameEntry ::= SEQUENCE {
            hmSetupPublicSpotModuleAuthModEmlAuthRealNameEntryLanguage INTEGER,
            hmSetupPublicSpotModuleAuthModEmlAuthRealNameEntryContent DisplayString
    }

-- {COLUMN} 1.3.6.1.4.1.248.32.18.2.24.41.1.20.1.1
hmSetupPublicSpotModuleAuthModEmlAuthRealNameEntryLanguage OBJECT-TYPE
    SYNTAX     INTEGER {
                  eGerman (1),
                  eEnglish (2),
                  eFrench (3),
                  eItalian (4),
                  eSpanish (5),
                  eDutch (6)
            }
    MAX-ACCESS read-only
    STATUS     current
    DESCRIPTION
            "-- empty --"
    ::= { hmSetupPublicSpotModuleAuthModEmlAuthRealNameEntry 1 }

-- {COLUMN} 1.3.6.1.4.1.248.32.18.2.24.41.1.20.1.2
hmSetupPublicSpotModuleAuthModEmlAuthRealNameEntryContent OBJECT-TYPE
    SYNTAX     DisplayString (SIZE(0..251))
    MAX-ACCESS read-write
    STATUS     current
    DESCRIPTION
            "-- empty --"
    ::= { hmSetupPublicSpotModuleAuthModEmlAuthRealNameEntry 2 }

-- {TABLE} 1.3.6.1.4.1.248.32.18.2.24.41.1.21
hmSetupPublicSpotModuleAuthModEmlAuthBodyTable OBJECT-TYPE
    SYNTAX     SEQUENCE OF HmSetupPublicSpotModuleAuthModEmlAuthBodyEntry
    MAX-ACCESS not-accessible
    STATUS     current
    DESCRIPTION
            "-- empty --"
    ::= { hmSetupPublicSpotModuleAuthModEmlAuth 21 }

-- {ROW} 1.3.6.1.4.1.248.32.18.2.24.41.1.21.1
hmSetupPublicSpotModuleAuthModEmlAuthBodyEntry OBJECT-TYPE
    SYNTAX     HmSetupPublicSpotModuleAuthModEmlAuthBodyEntry
    MAX-ACCESS not-accessible
    STATUS     current
    DESCRIPTION
            ""
    INDEX {
            hmSetupPublicSpotModuleAuthModEmlAuthBodyEntryLanguage
          }
    ::= { hmSetupPublicSpotModuleAuthModEmlAuthBodyTable 1 }

HmSetupPublicSpotModuleAuthModEmlAuthBodyEntry ::= SEQUENCE {
            hmSetupPublicSpotModuleAuthModEmlAuthBodyEntryLanguage INTEGER,
            hmSetupPublicSpotModuleAuthModEmlAuthBodyEntryContent DisplayString
    }

-- {COLUMN} 1.3.6.1.4.1.248.32.18.2.24.41.1.21.1.1
hmSetupPublicSpotModuleAuthModEmlAuthBodyEntryLanguage OBJECT-TYPE
    SYNTAX     INTEGER {
                  eGerman (1),
                  eEnglish (2),
                  eFrench (3),
                  eItalian (4),
                  eSpanish (5),
                  eDutch (6)
            }
    MAX-ACCESS read-only
    STATUS     current
    DESCRIPTION
            "-- empty --"
    ::= { hmSetupPublicSpotModuleAuthModEmlAuthBodyEntry 1 }

-- {COLUMN} 1.3.6.1.4.1.248.32.18.2.24.41.1.21.1.2
hmSetupPublicSpotModuleAuthModEmlAuthBodyEntryContent OBJECT-TYPE
    SYNTAX     DisplayString (SIZE(0..251))
    MAX-ACCESS read-write
    STATUS     current
    DESCRIPTION
            "-- empty --"
    ::= { hmSetupPublicSpotModuleAuthModEmlAuthBodyEntry 2 }

-- {TABLE} 1.3.6.1.4.1.248.32.18.2.24.41.1.22
hmSetupPublicSpotModuleAuthModEmlAuthSubjectTable OBJECT-TYPE
    SYNTAX     SEQUENCE OF HmSetupPublicSpotModuleAuthModEmlAuthSubjectEntry
    MAX-ACCESS not-accessible
    STATUS     current
    DESCRIPTION
            "-- empty --"
    ::= { hmSetupPublicSpotModuleAuthModEmlAuth 22 }

-- {ROW} 1.3.6.1.4.1.248.32.18.2.24.41.1.22.1
hmSetupPublicSpotModuleAuthModEmlAuthSubjectEntry OBJECT-TYPE
    SYNTAX     HmSetupPublicSpotModuleAuthModEmlAuthSubjectEntry
    MAX-ACCESS not-accessible
    STATUS     current
    DESCRIPTION
            ""
    INDEX {
            hmSetupPublicSpotModuleAuthModEmlAuthSubjectEntryLanguage
          }
    ::= { hmSetupPublicSpotModuleAuthModEmlAuthSubjectTable 1 }

HmSetupPublicSpotModuleAuthModEmlAuthSubjectEntry ::= SEQUENCE {
            hmSetupPublicSpotModuleAuthModEmlAuthSubjectEntryLanguage INTEGER,
            hmSetupPublicSpotModuleAuthModEmlAuthSubjectEntryContent DisplayString
    }

-- {COLUMN} 1.3.6.1.4.1.248.32.18.2.24.41.1.22.1.1
hmSetupPublicSpotModuleAuthModEmlAuthSubjectEntryLanguage OBJECT-TYPE
    SYNTAX     INTEGER {
                  eGerman (1),
                  eEnglish (2),
                  eFrench (3),
                  eItalian (4),
                  eSpanish (5),
                  eDutch (6)
            }
    MAX-ACCESS read-only
    STATUS     current
    DESCRIPTION
            "-- empty --"
    ::= { hmSetupPublicSpotModuleAuthModEmlAuthSubjectEntry 1 }

-- {COLUMN} 1.3.6.1.4.1.248.32.18.2.24.41.1.22.1.2
hmSetupPublicSpotModuleAuthModEmlAuthSubjectEntryContent OBJECT-TYPE
    SYNTAX     DisplayString (SIZE(0..251))
    MAX-ACCESS read-write
    STATUS     current
    DESCRIPTION
            "-- empty --"
    ::= { hmSetupPublicSpotModuleAuthModEmlAuthSubjectEntry 2 }

-- {NODE} 1.3.6.1.4.1.248.32.18.2.24.41.2
hmSetupPublicSpotModuleAuthModEmlSmsAuth OBJECT IDENTIFIER ::= { hmSetupPublicSpotModuleAuthMod 2 }

-- {SCALAR} 1.3.6.1.4.1.248.32.18.2.24.41.2.1
hmSetupPublicSpotModuleAuthModEmlSmsAuthLimitEMailsPerHour OBJECT-TYPE
    SYNTAX     Integer32 (0..65535)
    MAX-ACCESS read-write
    STATUS     current
    DESCRIPTION
            "-- empty --"
    ::= { hmSetupPublicSpotModuleAuthModEmlSmsAuth 1 }

-- {SCALAR} 1.3.6.1.4.1.248.32.18.2.24.41.2.2
hmSetupPublicSpotModuleAuthModEmlSmsAuthUserMustAcceptGtc OBJECT-TYPE
    SYNTAX     INTEGER {
                  eNo (0),
                  eYes (1)
            }
    MAX-ACCESS read-only
    STATUS     current
    DESCRIPTION
            "-- empty --"
    ::= { hmSetupPublicSpotModuleAuthModEmlSmsAuth 2 }

-- {SCALAR} 1.3.6.1.4.1.248.32.18.2.24.41.2.3
hmSetupPublicSpotModuleAuthModEmlSmsAuthSubject OBJECT-TYPE
    SYNTAX     DisplayString (SIZE(0..256))
    MAX-ACCESS read-write
    STATUS     current
    DESCRIPTION
            "-- empty --"
    ::= { hmSetupPublicSpotModuleAuthModEmlSmsAuth 3 }

-- {SCALAR} 1.3.6.1.4.1.248.32.18.2.24.41.2.4
hmSetupPublicSpotModuleAuthModEmlSmsAuthMaxRequestAttempts OBJECT-TYPE
    SYNTAX     Integer32 (0..65535)
    MAX-ACCESS read-write
    STATUS     current
    DESCRIPTION
            "-- empty --"
    ::= { hmSetupPublicSpotModuleAuthModEmlSmsAuth 4 }

-- {SCALAR} 1.3.6.1.4.1.248.32.18.2.24.41.2.5
hmSetupPublicSpotModuleAuthModEmlSmsAuthLocalEMailAddress OBJECT-TYPE
    SYNTAX     DisplayString (SIZE(0..150))
    MAX-ACCESS read-write
    STATUS     current
    DESCRIPTION
            "-- empty --"
    ::= { hmSetupPublicSpotModuleAuthModEmlSmsAuth 5 }

-- {SCALAR} 1.3.6.1.4.1.248.32.18.2.24.41.2.6
hmSetupPublicSpotModuleAuthModEmlSmsAuthRealName OBJECT-TYPE
    SYNTAX     DisplayString (SIZE(0..150))
    MAX-ACCESS read-write
    STATUS     current
    DESCRIPTION
            "-- empty --"
    ::= { hmSetupPublicSpotModuleAuthModEmlSmsAuth 6 }

-- {SCALAR} 1.3.6.1.4.1.248.32.18.2.24.41.2.12
hmSetupPublicSpotModuleAuthModEmlSmsAuthBody OBJECT-TYPE
    SYNTAX     DisplayString (SIZE(0..256))
    MAX-ACCESS read-write
    STATUS     current
    DESCRIPTION
            "-- empty --"
    ::= { hmSetupPublicSpotModuleAuthModEmlSmsAuth 12 }

-- {SCALAR} 1.3.6.1.4.1.248.32.18.2.24.41.2.13
hmSetupPublicSpotModuleAuthModEmlSmsAuthGatewayEMailAddress OBJECT-TYPE
    SYNTAX     DisplayString (SIZE(0..150))
    MAX-ACCESS read-write
    STATUS     current
    DESCRIPTION
            "-- empty --"
    ::= { hmSetupPublicSpotModuleAuthModEmlSmsAuth 13 }

-- {TABLE} 1.3.6.1.4.1.248.32.18.2.24.41.2.14
hmSetupPublicSpotModuleAuthModEmlSmsAuthAlldCtryCodsTable OBJECT-TYPE
    SYNTAX     SEQUENCE OF HmSetupPublicSpotModuleAuthModEmlSmsAuthAlldCtryCodsEntry
    MAX-ACCESS not-accessible
    STATUS     current
    DESCRIPTION
            ""
    ::= { hmSetupPublicSpotModuleAuthModEmlSmsAuth 14 }

-- {ROW} 1.3.6.1.4.1.248.32.18.2.24.41.2.14.1
hmSetupPublicSpotModuleAuthModEmlSmsAuthAlldCtryCodsEntry OBJECT-TYPE
    SYNTAX     HmSetupPublicSpotModuleAuthModEmlSmsAuthAlldCtryCodsEntry
    MAX-ACCESS not-accessible
    STATUS     current
    DESCRIPTION
            ""
    INDEX {
            hmSetupPublicSpotModuleAuthModEmlSmsAuthAlldCtryCodsEntryName
          }
    ::= { hmSetupPublicSpotModuleAuthModEmlSmsAuthAlldCtryCodsTable 1 }

HmSetupPublicSpotModuleAuthModEmlSmsAuthAlldCtryCodsEntry ::= SEQUENCE {
            hmSetupPublicSpotModuleAuthModEmlSmsAuthAlldCtryCodsEntryName DisplayString,
            hmSetupPublicSpotModuleAuthModEmlSmsAuthAlldCtryCodsEntryCode Integer32
    }

-- {COLUMN} 1.3.6.1.4.1.248.32.18.2.24.41.2.14.1.1
hmSetupPublicSpotModuleAuthModEmlSmsAuthAlldCtryCodsEntryName OBJECT-TYPE
    SYNTAX     DisplayString (SIZE(0..100))
    MAX-ACCESS read-write
    STATUS     current
    DESCRIPTION
            "-- empty --"
    ::= { hmSetupPublicSpotModuleAuthModEmlSmsAuthAlldCtryCodsEntry 1 }

-- {COLUMN} 1.3.6.1.4.1.248.32.18.2.24.41.2.14.1.2
hmSetupPublicSpotModuleAuthModEmlSmsAuthAlldCtryCodsEntryCode OBJECT-TYPE
    SYNTAX     Integer32 (0..65535)
    MAX-ACCESS read-write
    STATUS     current
    DESCRIPTION
            "-- empty --"
    ::= { hmSetupPublicSpotModuleAuthModEmlSmsAuthAlldCtryCodsEntry 2 }

-- {SCALAR} 1.3.6.1.4.1.248.32.18.2.24.41.2.15
hmSetupPublicSpotModuleAuthModEmlSmsAuthSendSms OBJECT-TYPE
    SYNTAX     INTEGER {
                  eSmsGateway (0),
                  eHttp2sms (1)
            }
    MAX-ACCESS read-write
    STATUS     current
    DESCRIPTION
            "-- empty --"
    ::= { hmSetupPublicSpotModuleAuthModEmlSmsAuth 15 }

-- {SCALAR} 1.3.6.1.4.1.248.32.18.2.24.41.2.16
hmSetupPublicSpotModuleAuthModEmlSmsAuthHttpUserName OBJECT-TYPE
    SYNTAX     DisplayString (SIZE(0..16))
    MAX-ACCESS read-write
    STATUS     current
    DESCRIPTION
            "-- empty --"
    ::= { hmSetupPublicSpotModuleAuthModEmlSmsAuth 16 }

-- {SCALAR} 1.3.6.1.4.1.248.32.18.2.24.41.2.17
hmSetupPublicSpotModuleAuthModEmlSmsAuthHttpPassword OBJECT-TYPE
    SYNTAX     DisplayString (SIZE(0..16))
    MAX-ACCESS read-write
    STATUS     current
    DESCRIPTION
            "-- empty --"
    ::= { hmSetupPublicSpotModuleAuthModEmlSmsAuth 17 }

-- {SCALAR} 1.3.6.1.4.1.248.32.18.2.24.41.2.18
hmSetupPublicSpotModuleAuthModEmlSmsAuthHttpGatewayAddress OBJECT-TYPE
    SYNTAX     DisplayString (SIZE(0..63))
    MAX-ACCESS read-write
    STATUS     current
    DESCRIPTION
            "-- empty --"
    ::= { hmSetupPublicSpotModuleAuthModEmlSmsAuth 18 }

-- {TABLE} 1.3.6.1.4.1.248.32.18.2.24.41.2.23
hmSetupPublicSpotModuleAuthModEmlSmsAuthRealNameTable OBJECT-TYPE
    SYNTAX     SEQUENCE OF HmSetupPublicSpotModuleAuthModEmlSmsAuthRealNameEntry
    MAX-ACCESS not-accessible
    STATUS     current
    DESCRIPTION
            "-- empty --"
    ::= { hmSetupPublicSpotModuleAuthModEmlSmsAuth 23 }

-- {ROW} 1.3.6.1.4.1.248.32.18.2.24.41.2.23.1
hmSetupPublicSpotModuleAuthModEmlSmsAuthRealNameEntry OBJECT-TYPE
    SYNTAX     HmSetupPublicSpotModuleAuthModEmlSmsAuthRealNameEntry
    MAX-ACCESS not-accessible
    STATUS     current
    DESCRIPTION
            ""
    INDEX {
            hmSetupPublicSpotModuleAuthModEmlSmsAuthRealNameEntryLanguage
          }
    ::= { hmSetupPublicSpotModuleAuthModEmlSmsAuthRealNameTable 1 }

HmSetupPublicSpotModuleAuthModEmlSmsAuthRealNameEntry ::= SEQUENCE {
            hmSetupPublicSpotModuleAuthModEmlSmsAuthRealNameEntryLanguage INTEGER,
            hmSetupPublicSpotModuleAuthModEmlSmsAuthRealNameEntryContent DisplayString
    }

-- {COLUMN} 1.3.6.1.4.1.248.32.18.2.24.41.2.23.1.1
hmSetupPublicSpotModuleAuthModEmlSmsAuthRealNameEntryLanguage OBJECT-TYPE
    SYNTAX     INTEGER {
                  eGerman (1),
                  eEnglish (2),
                  eFrench (3),
                  eItalian (4),
                  eSpanish (5),
                  eDutch (6)
            }
    MAX-ACCESS read-only
    STATUS     current
    DESCRIPTION
            "-- empty --"
    ::= { hmSetupPublicSpotModuleAuthModEmlSmsAuthRealNameEntry 1 }

-- {COLUMN} 1.3.6.1.4.1.248.32.18.2.24.41.2.23.1.2
hmSetupPublicSpotModuleAuthModEmlSmsAuthRealNameEntryContent OBJECT-TYPE
    SYNTAX     DisplayString (SIZE(0..251))
    MAX-ACCESS read-write
    STATUS     current
    DESCRIPTION
            "-- empty --"
    ::= { hmSetupPublicSpotModuleAuthModEmlSmsAuthRealNameEntry 2 }

-- {TABLE} 1.3.6.1.4.1.248.32.18.2.24.41.2.24
hmSetupPublicSpotModuleAuthModEmlSmsAuthBodyTable OBJECT-TYPE
    SYNTAX     SEQUENCE OF HmSetupPublicSpotModuleAuthModEmlSmsAuthBodyEntry
    MAX-ACCESS not-accessible
    STATUS     current
    DESCRIPTION
            "-- empty --"
    ::= { hmSetupPublicSpotModuleAuthModEmlSmsAuth 24 }

-- {ROW} 1.3.6.1.4.1.248.32.18.2.24.41.2.24.1
hmSetupPublicSpotModuleAuthModEmlSmsAuthBodyEntry OBJECT-TYPE
    SYNTAX     HmSetupPublicSpotModuleAuthModEmlSmsAuthBodyEntry
    MAX-ACCESS not-accessible
    STATUS     current
    DESCRIPTION
            ""
    INDEX {
            hmSetupPublicSpotModuleAuthModEmlSmsAuthBodyEntryLanguage
          }
    ::= { hmSetupPublicSpotModuleAuthModEmlSmsAuthBodyTable 1 }

HmSetupPublicSpotModuleAuthModEmlSmsAuthBodyEntry ::= SEQUENCE {
            hmSetupPublicSpotModuleAuthModEmlSmsAuthBodyEntryLanguage INTEGER,
            hmSetupPublicSpotModuleAuthModEmlSmsAuthBodyEntryContent DisplayString
    }

-- {COLUMN} 1.3.6.1.4.1.248.32.18.2.24.41.2.24.1.1
hmSetupPublicSpotModuleAuthModEmlSmsAuthBodyEntryLanguage OBJECT-TYPE
    SYNTAX     INTEGER {
                  eGerman (1),
                  eEnglish (2),
                  eFrench (3),
                  eItalian (4),
                  eSpanish (5),
                  eDutch (6)
            }
    MAX-ACCESS read-only
    STATUS     current
    DESCRIPTION
            "-- empty --"
    ::= { hmSetupPublicSpotModuleAuthModEmlSmsAuthBodyEntry 1 }

-- {COLUMN} 1.3.6.1.4.1.248.32.18.2.24.41.2.24.1.2
hmSetupPublicSpotModuleAuthModEmlSmsAuthBodyEntryContent OBJECT-TYPE
    SYNTAX     DisplayString (SIZE(0..251))
    MAX-ACCESS read-write
    STATUS     current
    DESCRIPTION
            "-- empty --"
    ::= { hmSetupPublicSpotModuleAuthModEmlSmsAuthBodyEntry 2 }

-- {TABLE} 1.3.6.1.4.1.248.32.18.2.24.41.2.25
hmSetupPublicSpotModuleAuthModEmlSmsAuthSubjectTable OBJECT-TYPE
    SYNTAX     SEQUENCE OF HmSetupPublicSpotModuleAuthModEmlSmsAuthSubjectEntry
    MAX-ACCESS not-accessible
    STATUS     current
    DESCRIPTION
            "-- empty --"
    ::= { hmSetupPublicSpotModuleAuthModEmlSmsAuth 25 }

-- {ROW} 1.3.6.1.4.1.248.32.18.2.24.41.2.25.1
hmSetupPublicSpotModuleAuthModEmlSmsAuthSubjectEntry OBJECT-TYPE
    SYNTAX     HmSetupPublicSpotModuleAuthModEmlSmsAuthSubjectEntry
    MAX-ACCESS not-accessible
    STATUS     current
    DESCRIPTION
            ""
    INDEX {
            hmSetupPublicSpotModuleAuthModEmlSmsAuthSubjectEntryLanguage
          }
    ::= { hmSetupPublicSpotModuleAuthModEmlSmsAuthSubjectTable 1 }

HmSetupPublicSpotModuleAuthModEmlSmsAuthSubjectEntry ::= SEQUENCE {
            hmSetupPublicSpotModuleAuthModEmlSmsAuthSubjectEntryLanguage INTEGER,
            hmSetupPublicSpotModuleAuthModEmlSmsAuthSubjectEntryContent DisplayString
    }

-- {COLUMN} 1.3.6.1.4.1.248.32.18.2.24.41.2.25.1.1
hmSetupPublicSpotModuleAuthModEmlSmsAuthSubjectEntryLanguage OBJECT-TYPE
    SYNTAX     INTEGER {
                  eGerman (1),
                  eEnglish (2),
                  eFrench (3),
                  eItalian (4),
                  eSpanish (5),
                  eDutch (6)
            }
    MAX-ACCESS read-only
    STATUS     current
    DESCRIPTION
            "-- empty --"
    ::= { hmSetupPublicSpotModuleAuthModEmlSmsAuthSubjectEntry 1 }

-- {COLUMN} 1.3.6.1.4.1.248.32.18.2.24.41.2.25.1.2
hmSetupPublicSpotModuleAuthModEmlSmsAuthSubjectEntryContent OBJECT-TYPE
    SYNTAX     DisplayString (SIZE(0..251))
    MAX-ACCESS read-write
    STATUS     current
    DESCRIPTION
            "-- empty --"
    ::= { hmSetupPublicSpotModuleAuthModEmlSmsAuthSubjectEntry 2 }

-- {NODE} 1.3.6.1.4.1.248.32.18.2.24.41.3
hmSetupPublicSpotModuleAuthModUserTemplate OBJECT IDENTIFIER ::= { hmSetupPublicSpotModuleAuthMod 3 }

-- {SCALAR} 1.3.6.1.4.1.248.32.18.2.24.41.3.2
hmSetupPublicSpotModuleAuthModUserTemplateComment OBJECT-TYPE
    SYNTAX     DisplayString (SIZE(0..251))
    MAX-ACCESS read-write
    STATUS     current
    DESCRIPTION
            "-- empty --"
    ::= { hmSetupPublicSpotModuleAuthModUserTemplate 2 }

-- {SCALAR} 1.3.6.1.4.1.248.32.18.2.24.41.3.3
hmSetupPublicSpotModuleAuthModUserTemplateVolumeBudget OBJECT-TYPE
    SYNTAX     Integer32 (0..2147483647)
    MAX-ACCESS read-write
    STATUS     current
    DESCRIPTION
            "-- empty --"
    ::= { hmSetupPublicSpotModuleAuthModUserTemplate 3 }

-- {SCALAR} 1.3.6.1.4.1.248.32.18.2.24.41.3.4
hmSetupPublicSpotModuleAuthModUserTemplateTimeBudget OBJECT-TYPE
    SYNTAX     Integer32 (0..2147483647)
    MAX-ACCESS read-write
    STATUS     current
    DESCRIPTION
            "-- empty --"
    ::= { hmSetupPublicSpotModuleAuthModUserTemplate 4 }

-- {SCALAR} 1.3.6.1.4.1.248.32.18.2.24.41.3.5
hmSetupPublicSpotModuleAuthModUserTemplateRelExpiry OBJECT-TYPE
    SYNTAX     Integer32 (0..2147483647)
    MAX-ACCESS read-write
    STATUS     current
    DESCRIPTION
            "-- empty --"
    ::= { hmSetupPublicSpotModuleAuthModUserTemplate 5 }

-- {SCALAR} 1.3.6.1.4.1.248.32.18.2.24.41.3.6
hmSetupPublicSpotModuleAuthModUserTemplateAbsExpiry OBJECT-TYPE
    SYNTAX     Integer32 (0..2147483647)
    MAX-ACCESS read-write
    STATUS     current
    DESCRIPTION
            "-- empty --"
    ::= { hmSetupPublicSpotModuleAuthModUserTemplate 6 }

-- {SCALAR} 1.3.6.1.4.1.248.32.18.2.24.41.3.7
hmSetupPublicSpotModuleAuthModUserTemplateExpiryType OBJECT-TYPE
    SYNTAX     BITS {
                  eNone (0),
                  eRelative (6),
                  eAbsolute (7)
            }
    MAX-ACCESS read-write
    STATUS     current
    DESCRIPTION
            "-- empty --"
    ::= { hmSetupPublicSpotModuleAuthModUserTemplate 7 }

-- {SCALAR} 1.3.6.1.4.1.248.32.18.2.24.41.3.8
hmSetupPublicSpotModuleAuthModUserTemplateMaxConcurrentLogins OBJECT-TYPE
    SYNTAX     Integer32 (0..2147483647)
    MAX-ACCESS read-write
    STATUS     current
    DESCRIPTION
            "-- empty --"
    ::= { hmSetupPublicSpotModuleAuthModUserTemplate 8 }

-- {SCALAR} 1.3.6.1.4.1.248.32.18.2.24.41.3.9
hmSetupPublicSpotModuleAuthModUserTemplateMultipleLogin OBJECT-TYPE
    SYNTAX     INTEGER {
                  eYes (0),
                  eNo (1)
            }
    MAX-ACCESS read-write
    STATUS     current
    DESCRIPTION
            "-- empty --"
    ::= { hmSetupPublicSpotModuleAuthModUserTemplate 9 }

-- {SCALAR} 1.3.6.1.4.1.248.32.18.2.24.41.3.10
hmSetupPublicSpotModuleAuthModUserTemplateTxLimit OBJECT-TYPE
    SYNTAX     Integer32 (0..2147483647)
    MAX-ACCESS read-write
    STATUS     current
    DESCRIPTION
            "-- empty --"
    ::= { hmSetupPublicSpotModuleAuthModUserTemplate 10 }

-- {SCALAR} 1.3.6.1.4.1.248.32.18.2.24.41.3.11
hmSetupPublicSpotModuleAuthModUserTemplateRxLimit OBJECT-TYPE
    SYNTAX     Integer32 (0..2147483647)
    MAX-ACCESS read-write
    STATUS     current
    DESCRIPTION
            "-- empty --"
    ::= { hmSetupPublicSpotModuleAuthModUserTemplate 11 }

-- {NODE} 1.3.6.1.4.1.248.32.18.2.24.41.4
hmSetupPublicSpotModuleAuthModNoAuth OBJECT IDENTIFIER ::= { hmSetupPublicSpotModuleAuthMod 4 }

-- {SCALAR} 1.3.6.1.4.1.248.32.18.2.24.41.4.1
hmSetupPublicSpotModuleAuthModNoAuthMaxRequestPerHour OBJECT-TYPE
    SYNTAX     Integer32 (0..65535)
    MAX-ACCESS read-write
    STATUS     current
    DESCRIPTION
            "-- empty --"
    ::= { hmSetupPublicSpotModuleAuthModNoAuth 1 }

-- {SCALAR} 1.3.6.1.4.1.248.32.18.2.24.41.4.2
hmSetupPublicSpotModuleAuthModNoAuthUserAccountsPerDay OBJECT-TYPE
    SYNTAX     Integer32 (0..65535)
    MAX-ACCESS read-write
    STATUS     current
    DESCRIPTION
            "-- empty --"
    ::= { hmSetupPublicSpotModuleAuthModNoAuth 2 }

-- {SCALAR} 1.3.6.1.4.1.248.32.18.2.24.41.4.3
hmSetupPublicSpotModuleAuthModNoAuthUsernamePrefix OBJECT-TYPE
    SYNTAX     DisplayString (SIZE(0..10))
    MAX-ACCESS read-write
    STATUS     current
    DESCRIPTION
            "-- empty --"
    ::= { hmSetupPublicSpotModuleAuthModNoAuth 3 }

-- {NODE} 1.3.6.1.4.1.248.32.18.2.24.42
hmSetupPublicSpotModuleWispr OBJECT IDENTIFIER ::= { hmSetupPublicSpotModule 42 }

-- {SCALAR} 1.3.6.1.4.1.248.32.18.2.24.42.1
hmSetupPublicSpotModuleWisprOperating OBJECT-TYPE
    SYNTAX     INTEGER {
                  eNo (0),
                  eYes (1)
            }
    MAX-ACCESS read-write
    STATUS     current
    DESCRIPTION
            "-- empty --"
    ::= { hmSetupPublicSpotModuleWispr 1 }

-- {SCALAR} 1.3.6.1.4.1.248.32.18.2.24.42.2
hmSetupPublicSpotModuleWisprLocationId OBJECT-TYPE
    SYNTAX     DisplayString (SIZE(0..255))
    MAX-ACCESS read-write
    STATUS     current
    DESCRIPTION
            "-- empty --"
    ::= { hmSetupPublicSpotModuleWispr 2 }

-- {SCALAR} 1.3.6.1.4.1.248.32.18.2.24.42.3
hmSetupPublicSpotModuleWisprOperatorName OBJECT-TYPE
    SYNTAX     DisplayString (SIZE(0..255))
    MAX-ACCESS read-write
    STATUS     current
    DESCRIPTION
            "-- empty --"
    ::= { hmSetupPublicSpotModuleWispr 3 }

-- {SCALAR} 1.3.6.1.4.1.248.32.18.2.24.42.4
hmSetupPublicSpotModuleWisprLocationName OBJECT-TYPE
    SYNTAX     DisplayString (SIZE(0..255))
    MAX-ACCESS read-write
    STATUS     current
    DESCRIPTION
            "-- empty --"
    ::= { hmSetupPublicSpotModuleWispr 4 }

-- {SCALAR} 1.3.6.1.4.1.248.32.18.2.24.42.5
hmSetupPublicSpotModuleWisprLoginUrl OBJECT-TYPE
    SYNTAX     DisplayString (SIZE(0..255))
    MAX-ACCESS read-write
    STATUS     current
    DESCRIPTION
            "-- empty --"
    ::= { hmSetupPublicSpotModuleWispr 5 }

-- {SCALAR} 1.3.6.1.4.1.248.32.18.2.24.42.6
hmSetupPublicSpotModuleWisprLogoffUrl OBJECT-TYPE
    SYNTAX     DisplayString (SIZE(0..255))
    MAX-ACCESS read-write
    STATUS     current
    DESCRIPTION
            "-- empty --"
    ::= { hmSetupPublicSpotModuleWispr 6 }

-- {SCALAR} 1.3.6.1.4.1.248.32.18.2.24.42.7
hmSetupPublicSpotModuleWisprAbortLoginUrl OBJECT-TYPE
    SYNTAX     DisplayString (SIZE(0..255))
    MAX-ACCESS read-write
    STATUS     current
    DESCRIPTION
            "-- empty --"
    ::= { hmSetupPublicSpotModuleWispr 7 }

-- {SCALAR} 1.3.6.1.4.1.248.32.18.2.24.42.8
hmSetupPublicSpotModuleWisprMaxAuthenFailure OBJECT-TYPE
    SYNTAX     Integer32 (0..65535)
    MAX-ACCESS read-write
    STATUS     current
    DESCRIPTION
            "-- empty --"
    ::= { hmSetupPublicSpotModuleWispr 8 }

-- {NODE} 1.3.6.1.4.1.248.32.18.2.24.43
hmSetupPublicSpotModuleAdvertisement OBJECT IDENTIFIER ::= { hmSetupPublicSpotModule 43 }

-- {SCALAR} 1.3.6.1.4.1.248.32.18.2.24.43.1
hmSetupPublicSpotModuleAdvertisementOperating OBJECT-TYPE
    SYNTAX     INTEGER {
                  eNo (0),
                  eYes (1)
            }
    MAX-ACCESS read-write
    STATUS     current
    DESCRIPTION
            "-- empty --"
    ::= { hmSetupPublicSpotModuleAdvertisement 1 }

-- {SCALAR} 1.3.6.1.4.1.248.32.18.2.24.43.2
hmSetupPublicSpotModuleAdvertisementInterval OBJECT-TYPE
    SYNTAX     Integer32 (0..65535)
    MAX-ACCESS read-write
    STATUS     current
    DESCRIPTION
            "-- empty --"
    ::= { hmSetupPublicSpotModuleAdvertisement 2 }

-- {TABLE} 1.3.6.1.4.1.248.32.18.2.24.43.3
hmSetupPublicSpotModuleAdvertisementUrlTable OBJECT-TYPE
    SYNTAX     SEQUENCE OF HmSetupPublicSpotModuleAdvertisementUrlEntry
    MAX-ACCESS not-accessible
    STATUS     current
    DESCRIPTION
            "-- empty --"
    ::= { hmSetupPublicSpotModuleAdvertisement 3 }

-- {ROW} 1.3.6.1.4.1.248.32.18.2.24.43.3.1
hmSetupPublicSpotModuleAdvertisementUrlEntry OBJECT-TYPE
    SYNTAX     HmSetupPublicSpotModuleAdvertisementUrlEntry
    MAX-ACCESS not-accessible
    STATUS     current
    DESCRIPTION
            ""
    INDEX {
            hmSetupPublicSpotModuleAdvertisementUrlEntryContent
          }
    ::= { hmSetupPublicSpotModuleAdvertisementUrlTable 1 }

HmSetupPublicSpotModuleAdvertisementUrlEntry ::= SEQUENCE {
            hmSetupPublicSpotModuleAdvertisementUrlEntryContent DisplayString
    }

-- {COLUMN} 1.3.6.1.4.1.248.32.18.2.24.43.3.1.1
hmSetupPublicSpotModuleAdvertisementUrlEntryContent OBJECT-TYPE
    SYNTAX     DisplayString (SIZE(0..150))
    MAX-ACCESS read-write
    STATUS     current
    DESCRIPTION
            "-- empty --"
    ::= { hmSetupPublicSpotModuleAdvertisementUrlEntry 1 }

-- {TABLE} 1.3.6.1.4.1.248.32.18.2.24.43.4
hmSetupPublicSpotModuleAdvertisementUsrAgtWhtLstTable OBJECT-TYPE
    SYNTAX     SEQUENCE OF HmSetupPublicSpotModuleAdvertisementUsrAgtWhtLstEntry
    MAX-ACCESS not-accessible
    STATUS     current
    DESCRIPTION
            ""
    ::= { hmSetupPublicSpotModuleAdvertisement 4 }

-- {ROW} 1.3.6.1.4.1.248.32.18.2.24.43.4.1
hmSetupPublicSpotModuleAdvertisementUsrAgtWhtLstEntry OBJECT-TYPE
    SYNTAX     HmSetupPublicSpotModuleAdvertisementUsrAgtWhtLstEntry
    MAX-ACCESS not-accessible
    STATUS     current
    DESCRIPTION
            ""
    INDEX {
            hmSetupPublicSpotModuleAdvertisementUsrAgtWhtLstEntryUserAgent
          }
    ::= { hmSetupPublicSpotModuleAdvertisementUsrAgtWhtLstTable 1 }

HmSetupPublicSpotModuleAdvertisementUsrAgtWhtLstEntry ::= SEQUENCE {
            hmSetupPublicSpotModuleAdvertisementUsrAgtWhtLstEntryUserAgent DisplayString
    }

-- {COLUMN} 1.3.6.1.4.1.248.32.18.2.24.43.4.1.1
hmSetupPublicSpotModuleAdvertisementUsrAgtWhtLstEntryUserAgent OBJECT-TYPE
    SYNTAX     DisplayString (SIZE(0..150))
    MAX-ACCESS read-write
    STATUS     current
    DESCRIPTION
            "-- empty --"
    ::= { hmSetupPublicSpotModuleAdvertisementUsrAgtWhtLstEntry 1 }

-- {SCALAR} 1.3.6.1.4.1.248.32.18.2.24.43.5
hmSetupPublicSpotModuleAdvertisementProcessWisprRedirectUrl OBJECT-TYPE
    SYNTAX     INTEGER {
                  eNo (0),
                  eYes (1)
            }
    MAX-ACCESS read-write
    STATUS     current
    DESCRIPTION
            "-- empty --"
    ::= { hmSetupPublicSpotModuleAdvertisement 5 }

-- {TABLE} 1.3.6.1.4.1.248.32.18.2.24.43.6
hmSetupPublicSpotModuleAdvertisementFreeNetworksTable OBJECT-TYPE
    SYNTAX     SEQUENCE OF HmSetupPublicSpotModuleAdvertisementFreeNetworksEntry
    MAX-ACCESS not-accessible
    STATUS     current
    DESCRIPTION
            "-- empty --"
    ::= { hmSetupPublicSpotModuleAdvertisement 6 }

-- {ROW} 1.3.6.1.4.1.248.32.18.2.24.43.6.1
hmSetupPublicSpotModuleAdvertisementFreeNetworksEntry OBJECT-TYPE
    SYNTAX     HmSetupPublicSpotModuleAdvertisementFreeNetworksEntry
    MAX-ACCESS not-accessible
    STATUS     current
    DESCRIPTION
            ""
    INDEX {
            hmSetupPublicSpotModuleAdvertisementFreeNetworksEntryHostName
          }
    ::= { hmSetupPublicSpotModuleAdvertisementFreeNetworksTable 1 }

HmSetupPublicSpotModuleAdvertisementFreeNetworksEntry ::= SEQUENCE {
            hmSetupPublicSpotModuleAdvertisementFreeNetworksEntryHostName DisplayString,
            hmSetupPublicSpotModuleAdvertisementFreeNetworksEntryMask IpAddress
    }

-- {COLUMN} 1.3.6.1.4.1.248.32.18.2.24.43.6.1.1
hmSetupPublicSpotModuleAdvertisementFreeNetworksEntryHostName OBJECT-TYPE
    SYNTAX     DisplayString (SIZE(0..64))
    MAX-ACCESS read-write
    STATUS     current
    DESCRIPTION
            "-- empty --"
    ::= { hmSetupPublicSpotModuleAdvertisementFreeNetworksEntry 1 }

-- {COLUMN} 1.3.6.1.4.1.248.32.18.2.24.43.6.1.2
hmSetupPublicSpotModuleAdvertisementFreeNetworksEntryMask OBJECT-TYPE
    SYNTAX     IpAddress
    MAX-ACCESS read-write
    STATUS     current
    DESCRIPTION
            "-- empty --"
    ::= { hmSetupPublicSpotModuleAdvertisementFreeNetworksEntry 2 }

-- {NODE} 1.3.6.1.4.1.248.32.18.2.24.44
hmSetupPublicSpotModuleManageUserWizard OBJECT IDENTIFIER ::= { hmSetupPublicSpotModule 44 }

-- {SCALAR} 1.3.6.1.4.1.248.32.18.2.24.44.10
hmSetupPublicSpotModuleManageUserWizardShowStatusInformation OBJECT-TYPE
    SYNTAX     INTEGER {
                  eNo (0),
                  eYes (1)
            }
    MAX-ACCESS read-write
    STATUS     current
    DESCRIPTION
            "-- empty --"
    ::= { hmSetupPublicSpotModuleManageUserWizard 10 }

-- {SCALAR} 1.3.6.1.4.1.248.32.18.2.24.44.11
hmSetupPublicSpotModuleManageUserWizardShowAllUserAdmIndep OBJECT-TYPE
    SYNTAX     INTEGER {
                  eNo (0),
                  eYes (1)
            }
    MAX-ACCESS read-write
    STATUS     current
    DESCRIPTION
            ""
    ::= { hmSetupPublicSpotModuleManageUserWizard 11 }

-- {SCALAR} 1.3.6.1.4.1.248.32.18.2.24.47
hmSetupPublicSpotModuleCheckOriginVlan OBJECT-TYPE
    SYNTAX     INTEGER {
                  eNo (0),
                  eYes (1)
            }
    MAX-ACCESS read-write
    STATUS     current
    DESCRIPTION
            "-- empty --"
    ::= { hmSetupPublicSpotModule 47 }

-- {TABLE} 1.3.6.1.4.1.248.32.18.2.24.48
hmSetupPublicSpotModuleCircuitIdsTable OBJECT-TYPE
    SYNTAX     SEQUENCE OF HmSetupPublicSpotModuleCircuitIdsEntry
    MAX-ACCESS not-accessible
    STATUS     current
    DESCRIPTION
            "-- empty --"
    ::= { hmSetupPublicSpotModule 48 }

-- {ROW} 1.3.6.1.4.1.248.32.18.2.24.48.1
hmSetupPublicSpotModuleCircuitIdsEntry OBJECT-TYPE
    SYNTAX     HmSetupPublicSpotModuleCircuitIdsEntry
    MAX-ACCESS not-accessible
    STATUS     current
    DESCRIPTION
            ""
    INDEX {
            hmSetupPublicSpotModuleCircuitIdsEntryAdministrator
          }
    ::= { hmSetupPublicSpotModuleCircuitIdsTable 1 }

HmSetupPublicSpotModuleCircuitIdsEntry ::= SEQUENCE {
            hmSetupPublicSpotModuleCircuitIdsEntryAdministrator DisplayString,
            hmSetupPublicSpotModuleCircuitIdsEntryCircuitId DisplayString
    }

-- {COLUMN} 1.3.6.1.4.1.248.32.18.2.24.48.1.1
hmSetupPublicSpotModuleCircuitIdsEntryAdministrator OBJECT-TYPE
    SYNTAX     DisplayString (SIZE(0..16))
    MAX-ACCESS read-write
    STATUS     current
    DESCRIPTION
            "-- empty --"
    ::= { hmSetupPublicSpotModuleCircuitIdsEntry 1 }

-- {COLUMN} 1.3.6.1.4.1.248.32.18.2.24.48.1.2
hmSetupPublicSpotModuleCircuitIdsEntryCircuitId OBJECT-TYPE
    SYNTAX     DisplayString (SIZE(0..64))
    MAX-ACCESS read-write
    STATUS     current
    DESCRIPTION
            "-- empty --"
    ::= { hmSetupPublicSpotModuleCircuitIdsEntry 2 }

-- {NODE} 1.3.6.1.4.1.248.32.18.2.24.50
hmSetupPublicSpotModuleAutoReLogin OBJECT IDENTIFIER ::= { hmSetupPublicSpotModule 50 }

-- {SCALAR} 1.3.6.1.4.1.248.32.18.2.24.50.1
hmSetupPublicSpotModuleAutoReLoginOperating OBJECT-TYPE
    SYNTAX     INTEGER {
                  eNo (0),
                  eYes (1)
            }
    MAX-ACCESS read-write
    STATUS     current
    DESCRIPTION
            "-- empty --"
    ::= { hmSetupPublicSpotModuleAutoReLogin 1 }

-- {SCALAR} 1.3.6.1.4.1.248.32.18.2.24.50.2
hmSetupPublicSpotModuleAutoReLoginStationTableLimit OBJECT-TYPE
    SYNTAX     Integer32 (0..2147483647)
    MAX-ACCESS read-write
    STATUS     current
    DESCRIPTION
            "-- empty --"
    ::= { hmSetupPublicSpotModuleAutoReLogin 2 }

-- {SCALAR} 1.3.6.1.4.1.248.32.18.2.24.50.3
hmSetupPublicSpotModuleAutoReLoginExistTimeout OBJECT-TYPE
    SYNTAX     Integer32 (0..2147483647)
    MAX-ACCESS read-write
    STATUS     current
    DESCRIPTION
            "-- empty --"
    ::= { hmSetupPublicSpotModuleAutoReLogin 3 }

-- {TABLE} 1.3.6.1.4.1.248.32.18.2.24.60
hmSetupPublicSpotModuleLoginTextTable OBJECT-TYPE
    SYNTAX     SEQUENCE OF HmSetupPublicSpotModuleLoginTextEntry
    MAX-ACCESS not-accessible
    STATUS     current
    DESCRIPTION
            "-- empty --"
    ::= { hmSetupPublicSpotModule 60 }

-- {ROW} 1.3.6.1.4.1.248.32.18.2.24.60.1
hmSetupPublicSpotModuleLoginTextEntry OBJECT-TYPE
    SYNTAX     HmSetupPublicSpotModuleLoginTextEntry
    MAX-ACCESS not-accessible
    STATUS     current
    DESCRIPTION
            ""
    INDEX {
            hmSetupPublicSpotModuleLoginTextEntryLanguage
          }
    ::= { hmSetupPublicSpotModuleLoginTextTable 1 }

HmSetupPublicSpotModuleLoginTextEntry ::= SEQUENCE {
            hmSetupPublicSpotModuleLoginTextEntryLanguage INTEGER,
            hmSetupPublicSpotModuleLoginTextEntryContent DisplayString
    }

-- {COLUMN} 1.3.6.1.4.1.248.32.18.2.24.60.1.1
hmSetupPublicSpotModuleLoginTextEntryLanguage OBJECT-TYPE
    SYNTAX     INTEGER {
                  eGerman (1),
                  eEnglish (2),
                  eFrench (3),
                  eItalian (4),
                  eSpanish (5),
                  eDutch (6)
            }
    MAX-ACCESS read-only
    STATUS     current
    DESCRIPTION
            "-- empty --"
    ::= { hmSetupPublicSpotModuleLoginTextEntry 1 }

-- {COLUMN} 1.3.6.1.4.1.248.32.18.2.24.60.1.2
hmSetupPublicSpotModuleLoginTextEntryContent OBJECT-TYPE
    SYNTAX     DisplayString (SIZE(0..251))
    MAX-ACCESS read-write
    STATUS     current
    DESCRIPTION
            "-- empty --"
    ::= { hmSetupPublicSpotModuleLoginTextEntry 2 }

-- {NODE} 1.3.6.1.4.1.248.32.18.2.25
hmSetupRadius OBJECT IDENTIFIER ::= { hmSetup 25 }

-- {SCALAR} 1.3.6.1.4.1.248.32.18.2.25.4
hmSetupRadiusAuthTimeout OBJECT-TYPE
    SYNTAX     Integer32 (0..65535)
    MAX-ACCESS read-write
    STATUS     current
    DESCRIPTION
            "-- empty --"
    ::= { hmSetupRadius 4 }

-- {SCALAR} 1.3.6.1.4.1.248.32.18.2.25.5
hmSetupRadiusAuthRetry OBJECT-TYPE
    SYNTAX     Integer32 (0..255)
    MAX-ACCESS read-write
    STATUS     current
    DESCRIPTION
            "-- empty --"
    ::= { hmSetupRadius 5 }

-- {SCALAR} 1.3.6.1.4.1.248.32.18.2.25.9
hmSetupRadiusBackupQueryStrategy OBJECT-TYPE
    SYNTAX     INTEGER {
                  eBlock (0),
                  eCyclic (1)
            }
    MAX-ACCESS read-write
    STATUS     current
    DESCRIPTION
            "-- empty --"
    ::= { hmSetupRadius 9 }

-- {NODE} 1.3.6.1.4.1.248.32.18.2.25.10
hmSetupRadiusServer OBJECT IDENTIFIER ::= { hmSetupRadius 10 }

-- {SCALAR} 1.3.6.1.4.1.248.32.18.2.25.10.1
hmSetupRadiusServerAuthentificationPort OBJECT-TYPE
    SYNTAX     Integer32 (0..65535)
    MAX-ACCESS read-write
    STATUS     current
    DESCRIPTION
            "-- empty --"
    ::= { hmSetupRadiusServer 1 }

-- {TABLE} 1.3.6.1.4.1.248.32.18.2.25.10.2
hmSetupRadiusServerClientsTable OBJECT-TYPE
    SYNTAX     SEQUENCE OF HmSetupRadiusServerClientsEntry
    MAX-ACCESS not-accessible
    STATUS     current
    DESCRIPTION
            "-- empty --"
    ::= { hmSetupRadiusServer 2 }

-- {ROW} 1.3.6.1.4.1.248.32.18.2.25.10.2.1
hmSetupRadiusServerClientsEntry OBJECT-TYPE
    SYNTAX     HmSetupRadiusServerClientsEntry
    MAX-ACCESS not-accessible
    STATUS     current
    DESCRIPTION
            ""
    INDEX {
            hmSetupRadiusServerClientsEntryIpNetwork,
            hmSetupRadiusServerClientsEntryIpNetmask
          }
    ::= { hmSetupRadiusServerClientsTable 1 }

HmSetupRadiusServerClientsEntry ::= SEQUENCE {
            hmSetupRadiusServerClientsEntryIpNetwork IpAddress,
            hmSetupRadiusServerClientsEntrySecret DisplayString,
            hmSetupRadiusServerClientsEntryIpNetmask IpAddress,
            hmSetupRadiusServerClientsEntryProtocols INTEGER,
            hmSetupRadiusServerClientsEntryComment DisplayString
    }

-- {COLUMN} 1.3.6.1.4.1.248.32.18.2.25.10.2.1.1
hmSetupRadiusServerClientsEntryIpNetwork OBJECT-TYPE
    SYNTAX     IpAddress
    MAX-ACCESS read-write
    STATUS     current
    DESCRIPTION
            "-- empty --"
    ::= { hmSetupRadiusServerClientsEntry 1 }

-- {COLUMN} 1.3.6.1.4.1.248.32.18.2.25.10.2.1.2
hmSetupRadiusServerClientsEntrySecret OBJECT-TYPE
    SYNTAX     DisplayString (SIZE(0..64))
    MAX-ACCESS read-write
    STATUS     current
    DESCRIPTION
            "-- empty --"
    ::= { hmSetupRadiusServerClientsEntry 2 }

-- {COLUMN} 1.3.6.1.4.1.248.32.18.2.25.10.2.1.3
hmSetupRadiusServerClientsEntryIpNetmask OBJECT-TYPE
    SYNTAX     IpAddress
    MAX-ACCESS read-write
    STATUS     current
    DESCRIPTION
            "-- empty --"
    ::= { hmSetupRadiusServerClientsEntry 3 }

-- {COLUMN} 1.3.6.1.4.1.248.32.18.2.25.10.2.1.4
hmSetupRadiusServerClientsEntryProtocols OBJECT-TYPE
    SYNTAX     INTEGER {
                  eRadius (0),
                  eRadsec (1),
                  eAll (255)
            }
    MAX-ACCESS read-write
    STATUS     current
    DESCRIPTION
            "-- empty --"
    ::= { hmSetupRadiusServerClientsEntry 4 }

-- {COLUMN} 1.3.6.1.4.1.248.32.18.2.25.10.2.1.5
hmSetupRadiusServerClientsEntryComment OBJECT-TYPE
    SYNTAX     DisplayString (SIZE(0..251))
    MAX-ACCESS read-write
    STATUS     current
    DESCRIPTION
            "-- empty --"
    ::= { hmSetupRadiusServerClientsEntry 5 }

-- {TABLE} 1.3.6.1.4.1.248.32.18.2.25.10.3
hmSetupRadiusServerForwardServersTable OBJECT-TYPE
    SYNTAX     SEQUENCE OF HmSetupRadiusServerForwardServersEntry
    MAX-ACCESS not-accessible
    STATUS     current
    DESCRIPTION
            "-- empty --"
    ::= { hmSetupRadiusServer 3 }

-- {ROW} 1.3.6.1.4.1.248.32.18.2.25.10.3.1
hmSetupRadiusServerForwardServersEntry OBJECT-TYPE
    SYNTAX     HmSetupRadiusServerForwardServersEntry
    MAX-ACCESS not-accessible
    STATUS     current
    DESCRIPTION
            ""
    INDEX {
            hmSetupRadiusServerForwardServersEntryRealm
          }
    ::= { hmSetupRadiusServerForwardServersTable 1 }

HmSetupRadiusServerForwardServersEntry ::= SEQUENCE {
            hmSetupRadiusServerForwardServersEntryRealm DisplayString,
            hmSetupRadiusServerForwardServersEntryIpAddress IpAddress,
            hmSetupRadiusServerForwardServersEntryPort Integer32,
            hmSetupRadiusServerForwardServersEntrySecret DisplayString,
            hmSetupRadiusServerForwardServersEntryBackup DisplayString,
            hmSetupRadiusServerForwardServersEntryLoopbackAddr DisplayString,
            hmSetupRadiusServerForwardServersEntryProtocol INTEGER,
            hmSetupRadiusServerForwardServersEntryAccntIpAddress IpAddress,
            hmSetupRadiusServerForwardServersEntryAccntPort Integer32,
            hmSetupRadiusServerForwardServersEntryAccntSecret DisplayString,
            hmSetupRadiusServerForwardServersEntryAccntLoopbackAddr DisplayString,
            hmSetupRadiusServerForwardServersEntryAccntProtocol INTEGER,
            hmSetupRadiusServerForwardServersEntryHostname DisplayString,
            hmSetupRadiusServerForwardServersEntryAccntHostname DisplayString,
            hmSetupRadiusServerForwardServersEntryAttributeValues DisplayString,
            hmSetupRadiusServerForwardServersEntryAccntAttributeValues DisplayString
    }

-- {COLUMN} 1.3.6.1.4.1.248.32.18.2.25.10.3.1.1
hmSetupRadiusServerForwardServersEntryRealm OBJECT-TYPE
    SYNTAX     DisplayString (SIZE(0..64))
    MAX-ACCESS read-write
    STATUS     current
    DESCRIPTION
            "-- empty --"
    ::= { hmSetupRadiusServerForwardServersEntry 1 }

-- {COLUMN} 1.3.6.1.4.1.248.32.18.2.25.10.3.1.2
hmSetupRadiusServerForwardServersEntryIpAddress OBJECT-TYPE
    SYNTAX     IpAddress
    MAX-ACCESS read-write
    STATUS     current
    DESCRIPTION
            "-- empty --"
    ::= { hmSetupRadiusServerForwardServersEntry 2 }

-- {COLUMN} 1.3.6.1.4.1.248.32.18.2.25.10.3.1.3
hmSetupRadiusServerForwardServersEntryPort OBJECT-TYPE
    SYNTAX     Integer32 (0..65535)
    MAX-ACCESS read-write
    STATUS     current
    DESCRIPTION
            "-- empty --"
    ::= { hmSetupRadiusServerForwardServersEntry 3 }

-- {COLUMN} 1.3.6.1.4.1.248.32.18.2.25.10.3.1.4
hmSetupRadiusServerForwardServersEntrySecret OBJECT-TYPE
    SYNTAX     DisplayString (SIZE(0..64))
    MAX-ACCESS read-write
    STATUS     current
    DESCRIPTION
            "-- empty --"
    ::= { hmSetupRadiusServerForwardServersEntry 4 }

-- {COLUMN} 1.3.6.1.4.1.248.32.18.2.25.10.3.1.5
hmSetupRadiusServerForwardServersEntryBackup OBJECT-TYPE
    SYNTAX     DisplayString (SIZE(0..64))
    MAX-ACCESS read-write
    STATUS     current
    DESCRIPTION
            "-- empty --"
    ::= { hmSetupRadiusServerForwardServersEntry 5 }

-- {COLUMN} 1.3.6.1.4.1.248.32.18.2.25.10.3.1.6
hmSetupRadiusServerForwardServersEntryLoopbackAddr OBJECT-TYPE
    SYNTAX     DisplayString (SIZE(0..16))
    MAX-ACCESS read-write
    STATUS     current
    DESCRIPTION
            "-- empty --"
    ::= { hmSetupRadiusServerForwardServersEntry 6 }

-- {COLUMN} 1.3.6.1.4.1.248.32.18.2.25.10.3.1.7
hmSetupRadiusServerForwardServersEntryProtocol OBJECT-TYPE
    SYNTAX     INTEGER {
                  eRadius (0),
                  eRadsec (1)
            }
    MAX-ACCESS read-write
    STATUS     current
    DESCRIPTION
            "-- empty --"
    ::= { hmSetupRadiusServerForwardServersEntry 7 }

-- {COLUMN} 1.3.6.1.4.1.248.32.18.2.25.10.3.1.8
hmSetupRadiusServerForwardServersEntryAccntIpAddress OBJECT-TYPE
    SYNTAX     IpAddress
    MAX-ACCESS read-write
    STATUS     current
    DESCRIPTION
            "-- empty --"
    ::= { hmSetupRadiusServerForwardServersEntry 8 }

-- {COLUMN} 1.3.6.1.4.1.248.32.18.2.25.10.3.1.9
hmSetupRadiusServerForwardServersEntryAccntPort OBJECT-TYPE
    SYNTAX     Integer32 (0..65535)
    MAX-ACCESS read-write
    STATUS     current
    DESCRIPTION
            "-- empty --"
    ::= { hmSetupRadiusServerForwardServersEntry 9 }

-- {COLUMN} 1.3.6.1.4.1.248.32.18.2.25.10.3.1.10
hmSetupRadiusServerForwardServersEntryAccntSecret OBJECT-TYPE
    SYNTAX     DisplayString (SIZE(0..64))
    MAX-ACCESS read-write
    STATUS     current
    DESCRIPTION
            "-- empty --"
    ::= { hmSetupRadiusServerForwardServersEntry 10 }

-- {COLUMN} 1.3.6.1.4.1.248.32.18.2.25.10.3.1.11
hmSetupRadiusServerForwardServersEntryAccntLoopbackAddr OBJECT-TYPE
    SYNTAX     DisplayString (SIZE(0..16))
    MAX-ACCESS read-write
    STATUS     current
    DESCRIPTION
            "-- empty --"
    ::= { hmSetupRadiusServerForwardServersEntry 11 }

-- {COLUMN} 1.3.6.1.4.1.248.32.18.2.25.10.3.1.12
hmSetupRadiusServerForwardServersEntryAccntProtocol OBJECT-TYPE
    SYNTAX     INTEGER {
                  eRadius (0),
                  eRadsec (1)
            }
    MAX-ACCESS read-write
    STATUS     current
    DESCRIPTION
            "-- empty --"
    ::= { hmSetupRadiusServerForwardServersEntry 12 }

-- {COLUMN} 1.3.6.1.4.1.248.32.18.2.25.10.3.1.13
hmSetupRadiusServerForwardServersEntryHostname OBJECT-TYPE
    SYNTAX     DisplayString (SIZE(0..64))
    MAX-ACCESS read-write
    STATUS     current
    DESCRIPTION
            "-- empty --"
    ::= { hmSetupRadiusServerForwardServersEntry 13 }

-- {COLUMN} 1.3.6.1.4.1.248.32.18.2.25.10.3.1.14
hmSetupRadiusServerForwardServersEntryAccntHostname OBJECT-TYPE
    SYNTAX     DisplayString (SIZE(0..64))
    MAX-ACCESS read-write
    STATUS     current
    DESCRIPTION
            "-- empty --"
    ::= { hmSetupRadiusServerForwardServersEntry 14 }

-- {COLUMN} 1.3.6.1.4.1.248.32.18.2.25.10.3.1.15
hmSetupRadiusServerForwardServersEntryAttributeValues OBJECT-TYPE
    SYNTAX     DisplayString (SIZE(0..251))
    MAX-ACCESS read-write
    STATUS     current
    DESCRIPTION
            "-- empty --"
    ::= { hmSetupRadiusServerForwardServersEntry 15 }

-- {COLUMN} 1.3.6.1.4.1.248.32.18.2.25.10.3.1.16
hmSetupRadiusServerForwardServersEntryAccntAttributeValues OBJECT-TYPE
    SYNTAX     DisplayString (SIZE(0..251))
    MAX-ACCESS read-write
    STATUS     current
    DESCRIPTION
            "-- empty --"
    ::= { hmSetupRadiusServerForwardServersEntry 16 }

-- {SCALAR} 1.3.6.1.4.1.248.32.18.2.25.10.5
hmSetupRadiusServerDefaultRealm OBJECT-TYPE
    SYNTAX     DisplayString (SIZE(0..64))
    MAX-ACCESS read-write
    STATUS     current
    DESCRIPTION
            "-- empty --"
    ::= { hmSetupRadiusServer 5 }

-- {SCALAR} 1.3.6.1.4.1.248.32.18.2.25.10.6
hmSetupRadiusServerEmptyRealm OBJECT-TYPE
    SYNTAX     DisplayString (SIZE(0..64))
    MAX-ACCESS read-write
    STATUS     current
    DESCRIPTION
            "-- empty --"
    ::= { hmSetupRadiusServer 6 }

-- {TABLE} 1.3.6.1.4.1.248.32.18.2.25.10.7
hmSetupRadiusServerUsersTable OBJECT-TYPE
    SYNTAX     SEQUENCE OF HmSetupRadiusServerUsersEntry
    MAX-ACCESS not-accessible
    STATUS     current
    DESCRIPTION
            "-- empty --"
    ::= { hmSetupRadiusServer 7 }

-- {ROW} 1.3.6.1.4.1.248.32.18.2.25.10.7.1
hmSetupRadiusServerUsersEntry OBJECT-TYPE
    SYNTAX     HmSetupRadiusServerUsersEntry
    MAX-ACCESS not-accessible
    STATUS     current
    DESCRIPTION
            ""
    INDEX {
            hmSetupRadiusServerUsersEntryUserName,
            hmSetupRadiusServerUsersEntryCallingStationIdMask,
            hmSetupRadiusServerUsersEntryCalledStationIdMask
          }
    ::= { hmSetupRadiusServerUsersTable 1 }

HmSetupRadiusServerUsersEntry ::= SEQUENCE {
            hmSetupRadiusServerUsersEntryUserName DisplayString,
            hmSetupRadiusServerUsersEntryPassword DisplayString,
            hmSetupRadiusServerUsersEntryLimitAuthMethods BITS,
            hmSetupRadiusServerUsersEntryVlanId Integer32,
            hmSetupRadiusServerUsersEntryCallingStationIdMask DisplayString,
            hmSetupRadiusServerUsersEntryCalledStationIdMask DisplayString,
            hmSetupRadiusServerUsersEntryTxLimit Integer32,
            hmSetupRadiusServerUsersEntryRxLimit Integer32,
            hmSetupRadiusServerUsersEntryMultipleLogin INTEGER,
            hmSetupRadiusServerUsersEntryAbsExpiry DisplayString,
            hmSetupRadiusServerUsersEntryTimeBudget Integer32,
            hmSetupRadiusServerUsersEntryVolumeBudget Integer32,
            hmSetupRadiusServerUsersEntryExpiryType BITS,
            hmSetupRadiusServerUsersEntryRelExpiry Integer32,
            hmSetupRadiusServerUsersEntryComment DisplayString,
            hmSetupRadiusServerUsersEntryServiceType INTEGER,
            hmSetupRadiusServerUsersEntryCaseSensitive INTEGER,
            hmSetupRadiusServerUsersEntryWpaPassphrase DisplayString,
            hmSetupRadiusServerUsersEntryMaxConcurrentLogins Integer32,
            hmSetupRadiusServerUsersEntryActive INTEGER,
            hmSetupRadiusServerUsersEntryShellPrivLevel Integer32,
            hmSetupRadiusServerUsersEntryVolumeBudgetMbytes Integer32
    }

-- {COLUMN} 1.3.6.1.4.1.248.32.18.2.25.10.7.1.1
hmSetupRadiusServerUsersEntryUserName OBJECT-TYPE
    SYNTAX     DisplayString (SIZE(0..48))
    MAX-ACCESS read-write
    STATUS     current
    DESCRIPTION
            "-- empty --"
    ::= { hmSetupRadiusServerUsersEntry 1 }

-- {COLUMN} 1.3.6.1.4.1.248.32.18.2.25.10.7.1.2
hmSetupRadiusServerUsersEntryPassword OBJECT-TYPE
    SYNTAX     DisplayString (SIZE(0..32))
    MAX-ACCESS read-write
    STATUS     current
    DESCRIPTION
            "-- empty --"
    ::= { hmSetupRadiusServerUsersEntry 2 }

-- {COLUMN} 1.3.6.1.4.1.248.32.18.2.25.10.7.1.3
hmSetupRadiusServerUsersEntryLimitAuthMethods OBJECT-TYPE
    SYNTAX     BITS {
                  eAll (0),
                  eEap (11),
                  eMschapv2 (12),
                  eMschap (13),
                  eChap (14),
                  ePap (15)
            }
    MAX-ACCESS read-write
    STATUS     current
    DESCRIPTION
            "-- empty --"
    ::= { hmSetupRadiusServerUsersEntry 3 }

-- {COLUMN} 1.3.6.1.4.1.248.32.18.2.25.10.7.1.4
hmSetupRadiusServerUsersEntryVlanId OBJECT-TYPE
    SYNTAX     Integer32 (0..65535)
    MAX-ACCESS read-write
    STATUS     current
    DESCRIPTION
            "-- empty --"
    ::= { hmSetupRadiusServerUsersEntry 4 }

-- {COLUMN} 1.3.6.1.4.1.248.32.18.2.25.10.7.1.5
hmSetupRadiusServerUsersEntryCallingStationIdMask OBJECT-TYPE
    SYNTAX     DisplayString (SIZE(0..64))
    MAX-ACCESS read-write
    STATUS     current
    DESCRIPTION
            "-- empty --"
    ::= { hmSetupRadiusServerUsersEntry 5 }

-- {COLUMN} 1.3.6.1.4.1.248.32.18.2.25.10.7.1.6
hmSetupRadiusServerUsersEntryCalledStationIdMask OBJECT-TYPE
    SYNTAX     DisplayString (SIZE(0..64))
    MAX-ACCESS read-write
    STATUS     current
    DESCRIPTION
            "-- empty --"
    ::= { hmSetupRadiusServerUsersEntry 6 }

-- {COLUMN} 1.3.6.1.4.1.248.32.18.2.25.10.7.1.7
hmSetupRadiusServerUsersEntryTxLimit OBJECT-TYPE
    SYNTAX     Integer32 (0..2147483647)
    MAX-ACCESS read-write
    STATUS     current
    DESCRIPTION
            "-- empty --"
    ::= { hmSetupRadiusServerUsersEntry 7 }

-- {COLUMN} 1.3.6.1.4.1.248.32.18.2.25.10.7.1.8
hmSetupRadiusServerUsersEntryRxLimit OBJECT-TYPE
    SYNTAX     Integer32 (0..2147483647)
    MAX-ACCESS read-write
    STATUS     current
    DESCRIPTION
            "-- empty --"
    ::= { hmSetupRadiusServerUsersEntry 8 }

-- {COLUMN} 1.3.6.1.4.1.248.32.18.2.25.10.7.1.9
hmSetupRadiusServerUsersEntryMultipleLogin OBJECT-TYPE
    SYNTAX     INTEGER {
                  eYes (0),
                  eNo (1)
            }
    MAX-ACCESS read-write
    STATUS     current
    DESCRIPTION
            "-- empty --"
    ::= { hmSetupRadiusServerUsersEntry 9 }

-- {COLUMN} 1.3.6.1.4.1.248.32.18.2.25.10.7.1.10
hmSetupRadiusServerUsersEntryAbsExpiry OBJECT-TYPE
    SYNTAX     DisplayString (SIZE(0..21))
    MAX-ACCESS read-write
    STATUS     current
    DESCRIPTION
            "-- empty --"
    ::= { hmSetupRadiusServerUsersEntry 10 }

-- {COLUMN} 1.3.6.1.4.1.248.32.18.2.25.10.7.1.11
hmSetupRadiusServerUsersEntryTimeBudget OBJECT-TYPE
    SYNTAX     Integer32 (0..2147483647)
    MAX-ACCESS read-write
    STATUS     current
    DESCRIPTION
            "-- empty --"
    ::= { hmSetupRadiusServerUsersEntry 11 }

-- {COLUMN} 1.3.6.1.4.1.248.32.18.2.25.10.7.1.12
hmSetupRadiusServerUsersEntryVolumeBudget OBJECT-TYPE
    SYNTAX     Integer32 (0..2147483647)
    MAX-ACCESS read-write
    STATUS     current
    DESCRIPTION
            "-- empty --"
    ::= { hmSetupRadiusServerUsersEntry 12 }

-- {COLUMN} 1.3.6.1.4.1.248.32.18.2.25.10.7.1.13
hmSetupRadiusServerUsersEntryExpiryType OBJECT-TYPE
    SYNTAX     BITS {
                  eNone (0),
                  eRelative (6),
                  eAbsolute (7)
            }
    MAX-ACCESS read-write
    STATUS     current
    DESCRIPTION
            "-- empty --"
    ::= { hmSetupRadiusServerUsersEntry 13 }

-- {COLUMN} 1.3.6.1.4.1.248.32.18.2.25.10.7.1.14
hmSetupRadiusServerUsersEntryRelExpiry OBJECT-TYPE
    SYNTAX     Integer32 (0..2147483647)
    MAX-ACCESS read-write
    STATUS     current
    DESCRIPTION
            "-- empty --"
    ::= { hmSetupRadiusServerUsersEntry 14 }

-- {COLUMN} 1.3.6.1.4.1.248.32.18.2.25.10.7.1.15
hmSetupRadiusServerUsersEntryComment OBJECT-TYPE
    SYNTAX     DisplayString (SIZE(0..251))
    MAX-ACCESS read-write
    STATUS     current
    DESCRIPTION
            "-- empty --"
    ::= { hmSetupRadiusServerUsersEntry 15 }

-- {COLUMN} 1.3.6.1.4.1.248.32.18.2.25.10.7.1.16
hmSetupRadiusServerUsersEntryServiceType OBJECT-TYPE
    SYNTAX     INTEGER {
                  eAny (0),
                  eLogin (1),
                  eFramed (2),
                  eCallbackLogin (3),
                  eCallbackFramed (4),
                  eOutbound (5),
                  eAdministrative (6),
                  eNasPrompt (7),
                  eAuthOnly (8),
                  eCallbackNasPrompt (9),
                  eCallCheck (10),
                  eCallbackAdministrative (11),
                  eVoice (12),
                  eFax (13),
                  eModemRelay (14),
                  eAuthorizeOnly (17),
                  eFramedManagement (18)
            }
    MAX-ACCESS read-write
    STATUS     current
    DESCRIPTION
            "-- empty --"
    ::= { hmSetupRadiusServerUsersEntry 16 }

-- {COLUMN} 1.3.6.1.4.1.248.32.18.2.25.10.7.1.17
hmSetupRadiusServerUsersEntryCaseSensitive OBJECT-TYPE
    SYNTAX     INTEGER {
                  eYes (0),
                  eNo (1)
            }
    MAX-ACCESS read-write
    STATUS     current
    DESCRIPTION
            "-- empty --"
    ::= { hmSetupRadiusServerUsersEntry 17 }

-- {COLUMN} 1.3.6.1.4.1.248.32.18.2.25.10.7.1.18
hmSetupRadiusServerUsersEntryWpaPassphrase OBJECT-TYPE
    SYNTAX     DisplayString (SIZE(0..63))
    MAX-ACCESS read-write
    STATUS     current
    DESCRIPTION
            "-- empty --"
    ::= { hmSetupRadiusServerUsersEntry 18 }

-- {COLUMN} 1.3.6.1.4.1.248.32.18.2.25.10.7.1.19
hmSetupRadiusServerUsersEntryMaxConcurrentLogins OBJECT-TYPE
    SYNTAX     Integer32 (0..2147483647)
    MAX-ACCESS read-write
    STATUS     current
    DESCRIPTION
            "-- empty --"
    ::= { hmSetupRadiusServerUsersEntry 19 }

-- {COLUMN} 1.3.6.1.4.1.248.32.18.2.25.10.7.1.20
hmSetupRadiusServerUsersEntryActive OBJECT-TYPE
    SYNTAX     INTEGER {
                  eNo (0),
                  eYes (1)
            }
    MAX-ACCESS read-write
    STATUS     current
    DESCRIPTION
            "-- empty --"
    ::= { hmSetupRadiusServerUsersEntry 20 }

-- {COLUMN} 1.3.6.1.4.1.248.32.18.2.25.10.7.1.21
hmSetupRadiusServerUsersEntryShellPrivLevel OBJECT-TYPE
    SYNTAX     Integer32 (0..2147483647)
    MAX-ACCESS read-write
    STATUS     current
    DESCRIPTION
            "-- empty --"
    ::= { hmSetupRadiusServerUsersEntry 21 }

-- {COLUMN} 1.3.6.1.4.1.248.32.18.2.25.10.7.1.22
hmSetupRadiusServerUsersEntryVolumeBudgetMbytes OBJECT-TYPE
    SYNTAX     Integer32 (0..2147483647)
    MAX-ACCESS read-write
    STATUS     current
    DESCRIPTION
            "-- empty --"
    ::= { hmSetupRadiusServerUsersEntry 22 }

-- {NODE} 1.3.6.1.4.1.248.32.18.2.25.10.10
hmSetupRadiusServerEap OBJECT IDENTIFIER ::= { hmSetupRadiusServer 10 }

-- {SCALAR} 1.3.6.1.4.1.248.32.18.2.25.10.10.1
hmSetupRadiusServerEapTunnelServer OBJECT-TYPE
    SYNTAX     DisplayString (SIZE(0..64))
    MAX-ACCESS read-write
    STATUS     current
    DESCRIPTION
            "-- empty --"
    ::= { hmSetupRadiusServerEap 1 }

-- {SCALAR} 1.3.6.1.4.1.248.32.18.2.25.10.10.2
hmSetupRadiusServerEapTlsCheckUsername OBJECT-TYPE
    SYNTAX     INTEGER {
                  eNo (0),
                  eYes (1)
            }
    MAX-ACCESS read-write
    STATUS     current
    DESCRIPTION
            "-- empty --"
    ::= { hmSetupRadiusServerEap 2 }

-- {SCALAR} 1.3.6.1.4.1.248.32.18.2.25.10.10.3
hmSetupRadiusServerEapReauthPeriod OBJECT-TYPE
    SYNTAX     Integer32 (0..2147483647)
    MAX-ACCESS read-write
    STATUS     current
    DESCRIPTION
            "-- empty --"
    ::= { hmSetupRadiusServerEap 3 }

-- {SCALAR} 1.3.6.1.4.1.248.32.18.2.25.10.10.4
hmSetupRadiusServerEapRetransmitTimeout OBJECT-TYPE
    SYNTAX     Integer32 (0..2147483647)
    MAX-ACCESS read-write
    STATUS     current
    DESCRIPTION
            "-- empty --"
    ::= { hmSetupRadiusServerEap 4 }

-- {SCALAR} 1.3.6.1.4.1.248.32.18.2.25.10.10.5
hmSetupRadiusServerEapTtlsDefaultTunnelMethod OBJECT-TYPE
    SYNTAX     INTEGER {
                  eNone (0),
                  eMd5 (4),
                  eGtc (6),
                  eMschapv2 (26)
            }
    MAX-ACCESS read-write
    STATUS     current
    DESCRIPTION
            "-- empty --"
    ::= { hmSetupRadiusServerEap 5 }

-- {SCALAR} 1.3.6.1.4.1.248.32.18.2.25.10.10.6
hmSetupRadiusServerEapPeapDefaultTunnelMethod OBJECT-TYPE
    SYNTAX     INTEGER {
                  eNone (0),
                  eMd5 (4),
                  eGtc (6),
                  eMschapv2 (26)
            }
    MAX-ACCESS read-write
    STATUS     current
    DESCRIPTION
            "-- empty --"
    ::= { hmSetupRadiusServerEap 6 }

-- {SCALAR} 1.3.6.1.4.1.248.32.18.2.25.10.10.7
hmSetupRadiusServerEapDefaultMethod OBJECT-TYPE
    SYNTAX     INTEGER {
                  eMd5 (4),
                  eGtc (6),
                  eTls (13),
                  eSim (18),
                  eTtls (21),
                  ePeap (25),
                  eMschapv2 (26)
            }
    MAX-ACCESS read-write
    STATUS     current
    DESCRIPTION
            "-- empty --"
    ::= { hmSetupRadiusServerEap 7 }

-- {SCALAR} 1.3.6.1.4.1.248.32.18.2.25.10.10.8
hmSetupRadiusServerEapDefaultMtu OBJECT-TYPE
    SYNTAX     Integer32 (0..65535)
    MAX-ACCESS read-write
    STATUS     current
    DESCRIPTION
            "-- empty --"
    ::= { hmSetupRadiusServerEap 8 }

-- {TABLE} 1.3.6.1.4.1.248.32.18.2.25.10.10.9
hmSetupRadiusServerEapAllowMethodsTable OBJECT-TYPE
    SYNTAX     SEQUENCE OF HmSetupRadiusServerEapAllowMethodsEntry
    MAX-ACCESS not-accessible
    STATUS     current
    DESCRIPTION
            "-- empty --"
    ::= { hmSetupRadiusServerEap 9 }

-- {ROW} 1.3.6.1.4.1.248.32.18.2.25.10.10.9.1
hmSetupRadiusServerEapAllowMethodsEntry OBJECT-TYPE
    SYNTAX     HmSetupRadiusServerEapAllowMethodsEntry
    MAX-ACCESS not-accessible
    STATUS     current
    DESCRIPTION
            ""
    INDEX {
            hmSetupRadiusServerEapAllowMethodsEntryMethod
          }
    ::= { hmSetupRadiusServerEapAllowMethodsTable 1 }

HmSetupRadiusServerEapAllowMethodsEntry ::= SEQUENCE {
            hmSetupRadiusServerEapAllowMethodsEntryMethod INTEGER,
            hmSetupRadiusServerEapAllowMethodsEntryAllow INTEGER
    }

-- {COLUMN} 1.3.6.1.4.1.248.32.18.2.25.10.10.9.1.1
hmSetupRadiusServerEapAllowMethodsEntryMethod OBJECT-TYPE
    SYNTAX     INTEGER {
                  eMd5 (4),
                  eGtc (6),
                  eTls (13),
                  eSim (18),
                  eTtls (21),
                  ePeap (25),
                  eMschapv2 (26)
            }
    MAX-ACCESS read-write
    STATUS     current
    DESCRIPTION
            "-- empty --"
    ::= { hmSetupRadiusServerEapAllowMethodsEntry 1 }

-- {COLUMN} 1.3.6.1.4.1.248.32.18.2.25.10.10.9.1.2
hmSetupRadiusServerEapAllowMethodsEntryAllow OBJECT-TYPE
    SYNTAX     INTEGER {
                  eOff (0),
                  eOn (1),
                  eInternalOnly (2)
            }
    MAX-ACCESS read-write
    STATUS     current
    DESCRIPTION
            "-- empty --"
    ::= { hmSetupRadiusServerEapAllowMethodsEntry 2 }

-- {SCALAR} 1.3.6.1.4.1.248.32.18.2.25.10.10.10
hmSetupRadiusServerEapMschapv2BackendServer OBJECT-TYPE
    SYNTAX     DisplayString (SIZE(0..64))
    MAX-ACCESS read-write
    STATUS     current
    DESCRIPTION
            "-- empty --"
    ::= { hmSetupRadiusServerEap 10 }

-- {NODE} 1.3.6.1.4.1.248.32.18.2.25.10.10.18
hmSetupRadiusServerEapEapSim OBJECT IDENTIFIER ::= { hmSetupRadiusServerEap 18 }

-- {TABLE} 1.3.6.1.4.1.248.32.18.2.25.10.10.18.1
hmSetupRadiusServerEapEapSimCardKeysTable OBJECT-TYPE
    SYNTAX     SEQUENCE OF HmSetupRadiusServerEapEapSimCardKeysEntry
    MAX-ACCESS not-accessible
    STATUS     current
    DESCRIPTION
            "-- empty --"
    ::= { hmSetupRadiusServerEapEapSim 1 }

-- {ROW} 1.3.6.1.4.1.248.32.18.2.25.10.10.18.1.1
hmSetupRadiusServerEapEapSimCardKeysEntry OBJECT-TYPE
    SYNTAX     HmSetupRadiusServerEapEapSimCardKeysEntry
    MAX-ACCESS not-accessible
    STATUS     current
    DESCRIPTION
            ""
    INDEX {
            hmSetupRadiusServerEapEapSimCardKeysEntryUserName,
            hmSetupRadiusServerEapEapSimCardKeysEntryCallingStationIdMask,
            hmSetupRadiusServerEapEapSimCardKeysEntryCalledStationIdMask
          }
    ::= { hmSetupRadiusServerEapEapSimCardKeysTable 1 }

HmSetupRadiusServerEapEapSimCardKeysEntry ::= SEQUENCE {
            hmSetupRadiusServerEapEapSimCardKeysEntryUserName DisplayString,
            hmSetupRadiusServerEapEapSimCardKeysEntryCallingStationIdMask DisplayString,
            hmSetupRadiusServerEapEapSimCardKeysEntryCalledStationIdMask DisplayString,
            hmSetupRadiusServerEapEapSimCardKeysEntryRand1 OCTET STRING,
            hmSetupRadiusServerEapEapSimCardKeysEntrySres1 OCTET STRING,
            hmSetupRadiusServerEapEapSimCardKeysEntryKc1 OCTET STRING,
            hmSetupRadiusServerEapEapSimCardKeysEntryRand2 OCTET STRING,
            hmSetupRadiusServerEapEapSimCardKeysEntrySres2 OCTET STRING,
            hmSetupRadiusServerEapEapSimCardKeysEntryKc2 OCTET STRING,
            hmSetupRadiusServerEapEapSimCardKeysEntryRand3 OCTET STRING,
            hmSetupRadiusServerEapEapSimCardKeysEntrySres3 OCTET STRING,
            hmSetupRadiusServerEapEapSimCardKeysEntryKc3 OCTET STRING
    }

-- {COLUMN} 1.3.6.1.4.1.248.32.18.2.25.10.10.18.1.1.1
hmSetupRadiusServerEapEapSimCardKeysEntryUserName OBJECT-TYPE
    SYNTAX     DisplayString (SIZE(0..48))
    MAX-ACCESS read-write
    STATUS     current
    DESCRIPTION
            "-- empty --"
    ::= { hmSetupRadiusServerEapEapSimCardKeysEntry 1 }

-- {COLUMN} 1.3.6.1.4.1.248.32.18.2.25.10.10.18.1.1.5
hmSetupRadiusServerEapEapSimCardKeysEntryCallingStationIdMask OBJECT-TYPE
    SYNTAX     DisplayString (SIZE(0..64))
    MAX-ACCESS read-write
    STATUS     current
    DESCRIPTION
            "-- empty --"
    ::= { hmSetupRadiusServerEapEapSimCardKeysEntry 5 }

-- {COLUMN} 1.3.6.1.4.1.248.32.18.2.25.10.10.18.1.1.6
hmSetupRadiusServerEapEapSimCardKeysEntryCalledStationIdMask OBJECT-TYPE
    SYNTAX     DisplayString (SIZE(0..64))
    MAX-ACCESS read-write
    STATUS     current
    DESCRIPTION
            "-- empty --"
    ::= { hmSetupRadiusServerEapEapSimCardKeysEntry 6 }

-- {COLUMN} 1.3.6.1.4.1.248.32.18.2.25.10.10.18.1.1.7
hmSetupRadiusServerEapEapSimCardKeysEntryRand1 OBJECT-TYPE
    SYNTAX     OCTET STRING
    MAX-ACCESS read-write
    STATUS     current
    DESCRIPTION
            "-- empty --"
    ::= { hmSetupRadiusServerEapEapSimCardKeysEntry 7 }

-- {COLUMN} 1.3.6.1.4.1.248.32.18.2.25.10.10.18.1.1.8
hmSetupRadiusServerEapEapSimCardKeysEntrySres1 OBJECT-TYPE
    SYNTAX     OCTET STRING
    MAX-ACCESS read-write
    STATUS     current
    DESCRIPTION
            "-- empty --"
    ::= { hmSetupRadiusServerEapEapSimCardKeysEntry 8 }

-- {COLUMN} 1.3.6.1.4.1.248.32.18.2.25.10.10.18.1.1.9
hmSetupRadiusServerEapEapSimCardKeysEntryKc1 OBJECT-TYPE
    SYNTAX     OCTET STRING
    MAX-ACCESS read-write
    STATUS     current
    DESCRIPTION
            "-- empty --"
    ::= { hmSetupRadiusServerEapEapSimCardKeysEntry 9 }

-- {COLUMN} 1.3.6.1.4.1.248.32.18.2.25.10.10.18.1.1.10
hmSetupRadiusServerEapEapSimCardKeysEntryRand2 OBJECT-TYPE
    SYNTAX     OCTET STRING
    MAX-ACCESS read-write
    STATUS     current
    DESCRIPTION
            "-- empty --"
    ::= { hmSetupRadiusServerEapEapSimCardKeysEntry 10 }

-- {COLUMN} 1.3.6.1.4.1.248.32.18.2.25.10.10.18.1.1.11
hmSetupRadiusServerEapEapSimCardKeysEntrySres2 OBJECT-TYPE
    SYNTAX     OCTET STRING
    MAX-ACCESS read-write
    STATUS     current
    DESCRIPTION
            "-- empty --"
    ::= { hmSetupRadiusServerEapEapSimCardKeysEntry 11 }

-- {COLUMN} 1.3.6.1.4.1.248.32.18.2.25.10.10.18.1.1.12
hmSetupRadiusServerEapEapSimCardKeysEntryKc2 OBJECT-TYPE
    SYNTAX     OCTET STRING
    MAX-ACCESS read-write
    STATUS     current
    DESCRIPTION
            "-- empty --"
    ::= { hmSetupRadiusServerEapEapSimCardKeysEntry 12 }

-- {COLUMN} 1.3.6.1.4.1.248.32.18.2.25.10.10.18.1.1.13
hmSetupRadiusServerEapEapSimCardKeysEntryRand3 OBJECT-TYPE
    SYNTAX     OCTET STRING
    MAX-ACCESS read-write
    STATUS     current
    DESCRIPTION
            "-- empty --"
    ::= { hmSetupRadiusServerEapEapSimCardKeysEntry 13 }

-- {COLUMN} 1.3.6.1.4.1.248.32.18.2.25.10.10.18.1.1.14
hmSetupRadiusServerEapEapSimCardKeysEntrySres3 OBJECT-TYPE
    SYNTAX     OCTET STRING
    MAX-ACCESS read-write
    STATUS     current
    DESCRIPTION
            "-- empty --"
    ::= { hmSetupRadiusServerEapEapSimCardKeysEntry 14 }

-- {COLUMN} 1.3.6.1.4.1.248.32.18.2.25.10.10.18.1.1.15
hmSetupRadiusServerEapEapSimCardKeysEntryKc3 OBJECT-TYPE
    SYNTAX     OCTET STRING
    MAX-ACCESS read-write
    STATUS     current
    DESCRIPTION
            "-- empty --"
    ::= { hmSetupRadiusServerEapEapSimCardKeysEntry 15 }

-- {NODE} 1.3.6.1.4.1.248.32.18.2.25.10.10.19
hmSetupRadiusServerEapEapTls OBJECT IDENTIFIER ::= { hmSetupRadiusServerEap 19 }

-- {SCALAR} 1.3.6.1.4.1.248.32.18.2.25.10.10.19.3
hmSetupRadiusServerEapEapTlsKeyexAlgorithms OBJECT-TYPE
    SYNTAX     BITS {
                  eEcdhe (27),
                  eDhe (29),
                  eRsa (31)
            }
    MAX-ACCESS read-write
    STATUS     current
    DESCRIPTION
            "-- empty --"
    ::= { hmSetupRadiusServerEapEapTls 3 }

-- {SCALAR} 1.3.6.1.4.1.248.32.18.2.25.10.10.19.4
hmSetupRadiusServerEapEapTlsCryptoAlgorithms OBJECT-TYPE
    SYNTAX     BITS {
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { hmSetupRadiusServerEapEapTls 4 }

-- {SCALAR} 1.3.6.1.4.1.248.32.18.2.25.10.10.19.5
hmSetupRadiusServerEapEapTlsHashAlgorithms OBJECT-TYPE
    SYNTAX     BITS {
                  eSha2384 (26),
                  eSha2256 (27),
                  eSha1 (29),
                  eMd5 (30)
            }
    MAX-ACCESS read-write
    STATUS     current
    DESCRIPTION
            "-- empty --"
    ::= { hmSetupRadiusServerEapEapTls 5 }

-- {SCALAR} 1.3.6.1.4.1.248.32.18.2.25.10.10.19.6
hmSetupRadiusServerEapEapTlsPreferPfs OBJECT-TYPE
    SYNTAX     BITS {
                  eNo (0),
                  eYes (7)
            }
    MAX-ACCESS read-write
    STATUS     current
    DESCRIPTION
            "-- empty --"
    ::= { hmSetupRadiusServerEapEapTls 6 }

-- {SCALAR} 1.3.6.1.4.1.248.32.18.2.25.10.10.19.10
hmSetupRadiusServerEapEapTlsCheckUsername OBJECT-TYPE
    SYNTAX     INTEGER {
                  eNo (0),
                  eYes (1)
            }
    MAX-ACCESS read-write
    STATUS     current
    DESCRIPTION
            "-- empty --"
    ::= { hmSetupRadiusServerEapEapTls 10 }

-- {SCALAR} 1.3.6.1.4.1.248.32.18.2.25.10.11
hmSetupRadiusServerAccountingPort OBJECT-TYPE
    SYNTAX     Integer32 (0..65535)
    MAX-ACCESS read-write
    STATUS     current
    DESCRIPTION
            "-- empty --"
    ::= { hmSetupRadiusServer 11 }

-- {SCALAR} 1.3.6.1.4.1.248.32.18.2.25.10.12
hmSetupRadiusServerAccountingInterimInterval OBJECT-TYPE
    SYNTAX     Integer32 (0..2147483647)
    MAX-ACCESS read-write
    STATUS     current
    DESCRIPTION
            "-- empty --"
    ::= { hmSetupRadiusServer 12 }

-- {SCALAR} 1.3.6.1.4.1.248.32.18.2.25.10.13
hmSetupRadiusServerRadsecPort OBJECT-TYPE
    SYNTAX     Integer32 (0..65535)
    MAX-ACCESS read-write
    STATUS     current
    DESCRIPTION
            "-- empty --"
    ::= { hmSetupRadiusServer 13 }

-- {SCALAR} 1.3.6.1.4.1.248.32.18.2.25.10.14
hmSetupRadiusServerAutoCleanupUserTable OBJECT-TYPE
    SYNTAX     INTEGER {
                  eNo (0),
                  eYes (1)
            }
    MAX-ACCESS read-write
    STATUS     current
    DESCRIPTION
            "-- empty --"
    ::= { hmSetupRadiusServer 14 }

-- {SCALAR} 1.3.6.1.4.1.248.32.18.2.25.10.15
hmSetupRadiusServerAllowStatusRequests OBJECT-TYPE
    SYNTAX     INTEGER {
                  eNo (0),
                  eYes (1)
            }
    MAX-ACCESS read-write
    STATUS     current
    DESCRIPTION
            "-- empty --"
    ::= { hmSetupRadiusServer 15 }

-- {TABLE} 1.3.6.1.4.1.248.32.18.2.25.10.16
hmSetupRadiusServerIpv6ClientsTable OBJECT-TYPE
    SYNTAX     SEQUENCE OF HmSetupRadiusServerIpv6ClientsEntry
    MAX-ACCESS not-accessible
    STATUS     current
    DESCRIPTION
            "-- empty --"
    ::= { hmSetupRadiusServer 16 }

-- {ROW} 1.3.6.1.4.1.248.32.18.2.25.10.16.1
hmSetupRadiusServerIpv6ClientsEntry OBJECT-TYPE
    SYNTAX     HmSetupRadiusServerIpv6ClientsEntry
    MAX-ACCESS not-accessible
    STATUS     current
    DESCRIPTION
            ""
    INDEX {
            hmSetupRadiusServerIpv6ClientsEntryAddressPrefixlength
          }
    ::= { hmSetupRadiusServerIpv6ClientsTable 1 }

HmSetupRadiusServerIpv6ClientsEntry ::= SEQUENCE {
            hmSetupRadiusServerIpv6ClientsEntryAddressPrefixlength DisplayString,
            hmSetupRadiusServerIpv6ClientsEntrySecret DisplayString,
            hmSetupRadiusServerIpv6ClientsEntryProtocols INTEGER,
            hmSetupRadiusServerIpv6ClientsEntryComment DisplayString
    }

-- {COLUMN} 1.3.6.1.4.1.248.32.18.2.25.10.16.1.1
hmSetupRadiusServerIpv6ClientsEntryAddressPrefixlength OBJECT-TYPE
    SYNTAX     DisplayString (SIZE(0..43))
    MAX-ACCESS read-write
    STATUS     current
    DESCRIPTION
            "-- empty --"
    ::= { hmSetupRadiusServerIpv6ClientsEntry 1 }

-- {COLUMN} 1.3.6.1.4.1.248.32.18.2.25.10.16.1.2
hmSetupRadiusServerIpv6ClientsEntrySecret OBJECT-TYPE
    SYNTAX     DisplayString (SIZE(0..64))
    MAX-ACCESS read-write
    STATUS     current
    DESCRIPTION
            "-- empty --"
    ::= { hmSetupRadiusServerIpv6ClientsEntry 2 }

-- {COLUMN} 1.3.6.1.4.1.248.32.18.2.25.10.16.1.4
hmSetupRadiusServerIpv6ClientsEntryProtocols OBJECT-TYPE
    SYNTAX     INTEGER {
                  eRadius (0),
                  eRadsec (1),
                  eAll (255)
            }
    MAX-ACCESS read-write
    STATUS     current
    DESCRIPTION
            "-- empty --"
    ::= { hmSetupRadiusServerIpv6ClientsEntry 4 }

-- {COLUMN} 1.3.6.1.4.1.248.32.18.2.25.10.16.1.5
hmSetupRadiusServerIpv6ClientsEntryComment OBJECT-TYPE
    SYNTAX     DisplayString (SIZE(0..251))
    MAX-ACCESS read-write
    STATUS     current
    DESCRIPTION
            "-- empty --"
    ::= { hmSetupRadiusServerIpv6ClientsEntry 5 }

-- {SCALAR} 1.3.6.1.4.1.248.32.18.2.25.10.17
hmSetupRadiusServerRealmTypes OBJECT-TYPE
    SYNTAX     BITS {
                  eMsCompauth (29),
                  eMsDomain (30),
                  eMailDomain (31)
            }
    MAX-ACCESS read-write
    STATUS     current
    DESCRIPTION
            "-- empty --"
    ::= { hmSetupRadiusServer 17 }

-- {SCALAR} 1.3.6.1.4.1.248.32.18.2.25.10.18
hmSetupRadiusServerAutoCleanupAccountingTotals OBJECT-TYPE
    SYNTAX     INTEGER {
                  eNo (0),
                  eYes (1)
            }
    MAX-ACCESS read-write
    STATUS     current
    DESCRIPTION
            "-- empty --"
    ::= { hmSetupRadiusServer 18 }

-- {NODE} 1.3.6.1.4.1.248.32.18.2.25.20
hmSetupRadiusRadsec OBJECT IDENTIFIER ::= { hmSetupRadius 20 }

-- {SCALAR} 1.3.6.1.4.1.248.32.18.2.25.20.1
hmSetupRadiusRadsecVersions OBJECT-TYPE
    SYNTAX     BITS {
                  eTlsv12 (28),
                  eTlsv11 (29),
                  eTlsv1 (30),
                  eSslv3 (31)
            }
    MAX-ACCESS read-write
    STATUS     current
    DESCRIPTION
            "-- empty --"
    ::= { hmSetupRadiusRadsec 1 }

-- {SCALAR} 1.3.6.1.4.1.248.32.18.2.25.20.2
hmSetupRadiusRadsecKeyexAlgorithms OBJECT-TYPE
    SYNTAX     BITS {
                  eEcdhe (27),
                  eDhe (29),
                  eRsa (31)
            }
    MAX-ACCESS read-write
    STATUS     current
    DESCRIPTION
            "-- empty --"
    ::= { hmSetupRadiusRadsec 2 }

-- {SCALAR} 1.3.6.1.4.1.248.32.18.2.25.20.3
hmSetupRadiusRadsecCryptoAlgorithms OBJECT-TYPE
    SYNTAX     BITS {
                  eAesgcm256 (20),
                  eAesgcm128 (21),
                  eAes256 (22),
                  eAes128 (23),
                  e3des (24),
                  eDes (25),
                  eDes40 (26),
                  eRc4128 (27),
                  eRc456 (28),
                  eRc440 (29)
            }
    MAX-ACCESS read-write
    STATUS     current
    DESCRIPTION
            "-- empty --"
    ::= { hmSetupRadiusRadsec 3 }

-- {SCALAR} 1.3.6.1.4.1.248.32.18.2.25.20.4
hmSetupRadiusRadsecHashAlgorithms OBJECT-TYPE
    SYNTAX     BITS {
                  eSha2384 (26),
                  eSha2256 (27),
                  eSha1 (29),
                  eMd5 (30)
            }
    MAX-ACCESS read-write
    STATUS     current
    DESCRIPTION
            "-- empty --"
    ::= { hmSetupRadiusRadsec 4 }

-- {SCALAR} 1.3.6.1.4.1.248.32.18.2.25.20.5
hmSetupRadiusRadsecPreferPfs OBJECT-TYPE
    SYNTAX     BITS {
                  eNo (0),
                  eYes (7)
            }
    MAX-ACCESS read-write
    STATUS     current
    DESCRIPTION
            "-- empty --"
    ::= { hmSetupRadiusRadsec 5 }

-- {SCALAR} 1.3.6.1.4.1.248.32.18.2.25.20.6
hmSetupRadiusRadsecRenegotiations OBJECT-TYPE
    SYNTAX     INTEGER {
                  eForbidden (0),
                  eAllowed (1),
                  eIgnored (2)
            }
    MAX-ACCESS read-write
    STATUS     current
    DESCRIPTION
            "-- empty --"
    ::= { hmSetupRadiusRadsec 6 }

-- {NODE} 1.3.6.1.4.1.248.32.18.2.26
hmSetupNtp OBJECT IDENTIFIER ::= { hmSetup 26 }

-- {SCALAR} 1.3.6.1.4.1.248.32.18.2.26.2
hmSetupNtpServerOperating OBJECT-TYPE
    SYNTAX     INTEGER {
                  eNo (0),
                  eYes (1)
            }
    MAX-ACCESS read-write
    STATUS     current
    DESCRIPTION
            "-- empty --"
    ::= { hmSetupNtp 2 }

-- {SCALAR} 1.3.6.1.4.1.248.32.18.2.26.3
hmSetupNtpBcMode OBJECT-TYPE
    SYNTAX     INTEGER {
                  eNo (0),
                  eYes (1)
            }
    MAX-ACCESS read-write
    STATUS     current
    DESCRIPTION
            "-- empty --"
    ::= { hmSetupNtp 3 }

-- {SCALAR} 1.3.6.1.4.1.248.32.18.2.26.4
hmSetupNtpBcInterval OBJECT-TYPE
    SYNTAX     Integer32 (0..65535)
    MAX-ACCESS read-write
    STATUS     current
    DESCRIPTION
            "-- empty --"
    ::= { hmSetupNtp 4 }

-- {SCALAR} 1.3.6.1.4.1.248.32.18.2.26.7
hmSetupNtpRqInterval OBJECT-TYPE
    SYNTAX     Integer32 (0..2147483647)
    MAX-ACCESS read-write
    STATUS     current
    DESCRIPTION
            "-- empty --"
    ::= { hmSetupNtp 7 }

-- {TABLE} 1.3.6.1.4.1.248.32.18.2.26.11
hmSetupNtpRqAddressTable OBJECT-TYPE
    SYNTAX     SEQUENCE OF HmSetupNtpRqAddressEntry
    MAX-ACCESS not-accessible
    STATUS     current
    DESCRIPTION
            "-- empty --"
    ::= { hmSetupNtp 11 }

-- {ROW} 1.3.6.1.4.1.248.32.18.2.26.11.1
hmSetupNtpRqAddressEntry OBJECT-TYPE
    SYNTAX     HmSetupNtpRqAddressEntry
    MAX-ACCESS not-accessible
    STATUS     current
    DESCRIPTION
            ""
    INDEX {
            hmSetupNtpRqAddressEntryRqAddress
          }
    ::= { hmSetupNtpRqAddressTable 1 }

HmSetupNtpRqAddressEntry ::= SEQUENCE {
            hmSetupNtpRqAddressEntryRqAddress DisplayString,
            hmSetupNtpRqAddressEntryLoopbackAddr DisplayString
    }

-- {COLUMN} 1.3.6.1.4.1.248.32.18.2.26.11.1.1
hmSetupNtpRqAddressEntryRqAddress OBJECT-TYPE
    SYNTAX     DisplayString (SIZE(0..31))
    MAX-ACCESS read-write
    STATUS     current
    DESCRIPTION
            "-- empty --"
    ::= { hmSetupNtpRqAddressEntry 1 }

-- {COLUMN} 1.3.6.1.4.1.248.32.18.2.26.11.1.2
hmSetupNtpRqAddressEntryLoopbackAddr OBJECT-TYPE
    SYNTAX     DisplayString (SIZE(0..16))
    MAX-ACCESS read-write
    STATUS     current
    DESCRIPTION
            "-- empty --"
    ::= { hmSetupNtpRqAddressEntry 2 }

-- {SCALAR} 1.3.6.1.4.1.248.32.18.2.26.12
hmSetupNtpRqTries OBJECT-TYPE
    SYNTAX     Integer32 (0..2147483647)
    MAX-ACCESS read-write
    STATUS     current
    DESCRIPTION
            "-- empty --"
    ::= { hmSetupNtp 12 }

-- {NODE} 1.3.6.1.4.1.248.32.18.2.27
hmSetupMail OBJECT IDENTIFIER ::= { hmSetup 27 }

-- {SCALAR} 1.3.6.1.4.1.248.32.18.2.27.1
hmSetupMailSmtpServer OBJECT-TYPE
    SYNTAX     DisplayString (SIZE(0..31))
    MAX-ACCESS read-write
    STATUS     current
    DESCRIPTION
            "-- empty --"
    ::= { hmSetupMail 1 }

-- {SCALAR} 1.3.6.1.4.1.248.32.18.2.27.2
hmSetupMailSmtpPort OBJECT-TYPE
    SYNTAX     Integer32 (0..65535)
    MAX-ACCESS read-write
    STATUS     current
    DESCRIPTION
            "-- empty --"
    ::= { hmSetupMail 2 }

-- {SCALAR} 1.3.6.1.4.1.248.32.18.2.27.3
hmSetupMailPop3Server OBJECT-TYPE
    SYNTAX     DisplayString (SIZE(0..31))
    MAX-ACCESS read-write
    STATUS     current
    DESCRIPTION
            "-- empty --"
    ::= { hmSetupMail 3 }

-- {SCALAR} 1.3.6.1.4.1.248.32.18.2.27.4
hmSetupMailPop3Port OBJECT-TYPE
    SYNTAX     Integer32 (0..65535)
    MAX-ACCESS read-write
    STATUS     current
    DESCRIPTION
            "-- empty --"
    ::= { hmSetupMail 4 }

-- {SCALAR} 1.3.6.1.4.1.248.32.18.2.27.5
hmSetupMailUserName OBJECT-TYPE
    SYNTAX     DisplayString (SIZE(0..63))
    MAX-ACCESS read-write
    STATUS     current
    DESCRIPTION
            "-- empty --"
    ::= { hmSetupMail 5 }

-- {SCALAR} 1.3.6.1.4.1.248.32.18.2.27.6
hmSetupMailPassword OBJECT-TYPE
    SYNTAX     DisplayString (SIZE(0..31))
    MAX-ACCESS read-write
    STATUS     current
    DESCRIPTION
            "-- empty --"
    ::= { hmSetupMail 6 }

-- {SCALAR} 1.3.6.1.4.1.248.32.18.2.27.7
hmSetupMailEMailSender OBJECT-TYPE
    SYNTAX     DisplayString (SIZE(0..63))
    MAX-ACCESS read-write
    STATUS     current
    DESCRIPTION
            "-- empty --"
    ::= { hmSetupMail 7 }

-- {SCALAR} 1.3.6.1.4.1.248.32.18.2.27.8
hmSetupMailSendAgainMin OBJECT-TYPE
    SYNTAX     Integer32 (0..65535)
    MAX-ACCESS read-write
    STATUS     current
    DESCRIPTION
            "-- empty --"
    ::= { hmSetupMail 8 }

-- {SCALAR} 1.3.6.1.4.1.248.32.18.2.27.9
hmSetupMailHoldTimeHrs OBJECT-TYPE
    SYNTAX     Integer32 (0..65535)
    MAX-ACCESS read-write
    STATUS     current
    DESCRIPTION
            "-- empty --"
    ::= { hmSetupMail 9 }

-- {SCALAR} 1.3.6.1.4.1.248.32.18.2.27.10
hmSetupMailBuffers OBJECT-TYPE
    SYNTAX     Integer32 (0..65535)
    MAX-ACCESS read-write
    STATUS     current
    DESCRIPTION
            "-- empty --"
    ::= { hmSetupMail 10 }

-- {SCALAR} 1.3.6.1.4.1.248.32.18.2.27.11
hmSetupMailLoopbackAddr OBJECT-TYPE
    SYNTAX     DisplayString (SIZE(0..16))
    MAX-ACCESS read-write
    STATUS     current
    DESCRIPTION
            "-- empty --"
    ::= { hmSetupMail 11 }

-- {SCALAR} 1.3.6.1.4.1.248.32.18.2.27.12
hmSetupMailSmtpUseTls OBJECT-TYPE
    SYNTAX     INTEGER {
                  eNo (0),
                  eYes (1),
                  ePreferred (2),
                  eRequired (3)
            }
    MAX-ACCESS read-write
    STATUS     current
    DESCRIPTION
            "-- empty --"
    ::= { hmSetupMail 12 }

-- {SCALAR} 1.3.6.1.4.1.248.32.18.2.27.13
hmSetupMailSmtpAuthentication OBJECT-TYPE
    SYNTAX     INTEGER {
                  eNone (0),
                  ePlainTextPreferred (1),
                  eEncrypted (2),
                  ePreferredEncrypted (3)
            }
    MAX-ACCESS read-write
    STATUS     current
    DESCRIPTION
            "-- empty --"
    ::= { hmSetupMail 13 }

-- {NODE} 1.3.6.1.4.1.248.32.18.2.30
hmSetupIeee8021x OBJECT IDENTIFIER ::= { hmSetup 30 }

-- {TABLE} 1.3.6.1.4.1.248.32.18.2.30.3
hmSetupIeee8021xRadiusServerTable OBJECT-TYPE
    SYNTAX     SEQUENCE OF HmSetupIeee8021xRadiusServerEntry
    MAX-ACCESS not-accessible
    STATUS     current
    DESCRIPTION
            "-- empty --"
    ::= { hmSetupIeee8021x 3 }

-- {ROW} 1.3.6.1.4.1.248.32.18.2.30.3.1
hmSetupIeee8021xRadiusServerEntry OBJECT-TYPE
    SYNTAX     HmSetupIeee8021xRadiusServerEntry
    MAX-ACCESS not-accessible
    STATUS     current
    DESCRIPTION
            ""
    INDEX {
            hmSetupIeee8021xRadiusServerEntryName
          }
    ::= { hmSetupIeee8021xRadiusServerTable 1 }

HmSetupIeee8021xRadiusServerEntry ::= SEQUENCE {
            hmSetupIeee8021xRadiusServerEntryName DisplayString,
            hmSetupIeee8021xRadiusServerEntryIpAddress IpAddress,
            hmSetupIeee8021xRadiusServerEntryPort Integer32,
            hmSetupIeee8021xRadiusServerEntrySecret DisplayString,
            hmSetupIeee8021xRadiusServerEntryBackup DisplayString,
            hmSetupIeee8021xRadiusServerEntryLoopbackAddr DisplayString,
            hmSetupIeee8021xRadiusServerEntryProtocol INTEGER,
            hmSetupIeee8021xRadiusServerEntryHostName DisplayString,
            hmSetupIeee8021xRadiusServerEntryAttributeValues DisplayString
    }

-- {COLUMN} 1.3.6.1.4.1.248.32.18.2.30.3.1.1
hmSetupIeee8021xRadiusServerEntryName OBJECT-TYPE
    SYNTAX     DisplayString (SIZE(0..16))
    MAX-ACCESS read-write
    STATUS     current
    DESCRIPTION
            "-- empty --"
    ::= { hmSetupIeee8021xRadiusServerEntry 1 }

-- {COLUMN} 1.3.6.1.4.1.248.32.18.2.30.3.1.2
hmSetupIeee8021xRadiusServerEntryIpAddress OBJECT-TYPE
    SYNTAX     IpAddress
    MAX-ACCESS read-write
    STATUS     current
    DESCRIPTION
            "-- empty --"
    ::= { hmSetupIeee8021xRadiusServerEntry 2 }

-- {COLUMN} 1.3.6.1.4.1.248.32.18.2.30.3.1.3
hmSetupIeee8021xRadiusServerEntryPort OBJECT-TYPE
    SYNTAX     Integer32 (0..65535)
    MAX-ACCESS read-write
    STATUS     current
    DESCRIPTION
            "-- empty --"
    ::= { hmSetupIeee8021xRadiusServerEntry 3 }

-- {COLUMN} 1.3.6.1.4.1.248.32.18.2.30.3.1.4
hmSetupIeee8021xRadiusServerEntrySecret OBJECT-TYPE
    SYNTAX     DisplayString (SIZE(0..64))
    MAX-ACCESS read-write
    STATUS     current
    DESCRIPTION
            "-- empty --"
    ::= { hmSetupIeee8021xRadiusServerEntry 4 }

-- {COLUMN} 1.3.6.1.4.1.248.32.18.2.30.3.1.5
hmSetupIeee8021xRadiusServerEntryBackup OBJECT-TYPE
    SYNTAX     DisplayString (SIZE(0..16))
    MAX-ACCESS read-write
    STATUS     current
    DESCRIPTION
            "-- empty --"
    ::= { hmSetupIeee8021xRadiusServerEntry 5 }

-- {COLUMN} 1.3.6.1.4.1.248.32.18.2.30.3.1.6
hmSetupIeee8021xRadiusServerEntryLoopbackAddr OBJECT-TYPE
    SYNTAX     DisplayString (SIZE(0..16))
    MAX-ACCESS read-write
    STATUS     current
    DESCRIPTION
            "-- empty --"
    ::= { hmSetupIeee8021xRadiusServerEntry 6 }

-- {COLUMN} 1.3.6.1.4.1.248.32.18.2.30.3.1.7
hmSetupIeee8021xRadiusServerEntryProtocol OBJECT-TYPE
    SYNTAX     INTEGER {
                  eRadius (0),
                  eRadsec (1)
            }
    MAX-ACCESS read-write
    STATUS     current
    DESCRIPTION
            "-- empty --"
    ::= { hmSetupIeee8021xRadiusServerEntry 7 }

-- {COLUMN} 1.3.6.1.4.1.248.32.18.2.30.3.1.8
hmSetupIeee8021xRadiusServerEntryHostName OBJECT-TYPE
    SYNTAX     DisplayString (SIZE(0..64))
    MAX-ACCESS read-write
    STATUS     current
    DESCRIPTION
            "-- empty --"
    ::= { hmSetupIeee8021xRadiusServerEntry 8 }

-- {COLUMN} 1.3.6.1.4.1.248.32.18.2.30.3.1.9
hmSetupIeee8021xRadiusServerEntryAttributeValues OBJECT-TYPE
    SYNTAX     DisplayString (SIZE(0..251))
    MAX-ACCESS read-write
    STATUS     current
    DESCRIPTION
            "-- empty --"
    ::= { hmSetupIeee8021xRadiusServerEntry 9 }

-- {TABLE} 1.3.6.1.4.1.248.32.18.2.30.4
hmSetupIeee8021xPortsTable OBJECT-TYPE
    SYNTAX     SEQUENCE OF HmSetupIeee8021xPortsEntry
    MAX-ACCESS not-accessible
    STATUS     current
    DESCRIPTION
            "-- empty --"
    ::= { hmSetupIeee8021x 4 }

-- {ROW} 1.3.6.1.4.1.248.32.18.2.30.4.1
hmSetupIeee8021xPortsEntry OBJECT-TYPE
    SYNTAX     HmSetupIeee8021xPortsEntry
    MAX-ACCESS not-accessible
    STATUS     current
    DESCRIPTION
            ""
    INDEX {
            hmSetupIeee8021xPortsEntryPort
          }
    ::= { hmSetupIeee8021xPortsTable 1 }

HmSetupIeee8021xPortsEntry ::= SEQUENCE {
            hmSetupIeee8021xPortsEntryPort DisplayString,
            hmSetupIeee8021xPortsEntryPortControl INTEGER,
            hmSetupIeee8021xPortsEntryReAuthMax Integer32,
            hmSetupIeee8021xPortsEntryMaxReq Integer32,
            hmSetupIeee8021xPortsEntryTxPeriod Integer32,
            hmSetupIeee8021xPortsEntrySuppTimeout Integer32,
            hmSetupIeee8021xPortsEntryServerTimeout Integer32,
            hmSetupIeee8021xPortsEntryQuietPeriod Integer32,
            hmSetupIeee8021xPortsEntryReAuthentication INTEGER,
            hmSetupIeee8021xPortsEntryReAuthInterval Integer32,
            hmSetupIeee8021xPortsEntryKeyTransmission INTEGER,
            hmSetupIeee8021xPortsEntryKeyTxInterval Integer32
    }

-- {COLUMN} 1.3.6.1.4.1.248.32.18.2.30.4.1.2
hmSetupIeee8021xPortsEntryPort OBJECT-TYPE
    SYNTAX     DisplayString (SIZE(0..18))
    MAX-ACCESS read-only
    STATUS     current
    DESCRIPTION
            "-- empty --"
    ::= { hmSetupIeee8021xPortsEntry 2 }

-- {COLUMN} 1.3.6.1.4.1.248.32.18.2.30.4.1.3
hmSetupIeee8021xPortsEntryPortControl OBJECT-TYPE
    SYNTAX     INTEGER {
                  eForceUnauth (0),
                  eForceAuth (1),
                  eAuto (2)
            }
    MAX-ACCESS read-write
    STATUS     current
    DESCRIPTION
            "-- empty --"
    ::= { hmSetupIeee8021xPortsEntry 3 }

-- {COLUMN} 1.3.6.1.4.1.248.32.18.2.30.4.1.4
hmSetupIeee8021xPortsEntryReAuthMax OBJECT-TYPE
    SYNTAX     Integer32 (0..255)
    MAX-ACCESS read-write
    STATUS     current
    DESCRIPTION
            "-- empty --"
    ::= { hmSetupIeee8021xPortsEntry 4 }

-- {COLUMN} 1.3.6.1.4.1.248.32.18.2.30.4.1.5
hmSetupIeee8021xPortsEntryMaxReq OBJECT-TYPE
    SYNTAX     Integer32 (0..255)
    MAX-ACCESS read-write
    STATUS     current
    DESCRIPTION
            "-- empty --"
    ::= { hmSetupIeee8021xPortsEntry 5 }

-- {COLUMN} 1.3.6.1.4.1.248.32.18.2.30.4.1.6
hmSetupIeee8021xPortsEntryTxPeriod OBJECT-TYPE
    SYNTAX     Integer32 (0..65535)
    MAX-ACCESS read-write
    STATUS     current
    DESCRIPTION
            "-- empty --"
    ::= { hmSetupIeee8021xPortsEntry 6 }

-- {COLUMN} 1.3.6.1.4.1.248.32.18.2.30.4.1.7
hmSetupIeee8021xPortsEntrySuppTimeout OBJECT-TYPE
    SYNTAX     Integer32 (0..65535)
    MAX-ACCESS read-write
    STATUS     current
    DESCRIPTION
            "-- empty --"
    ::= { hmSetupIeee8021xPortsEntry 7 }

-- {COLUMN} 1.3.6.1.4.1.248.32.18.2.30.4.1.8
hmSetupIeee8021xPortsEntryServerTimeout OBJECT-TYPE
    SYNTAX     Integer32 (0..65535)
    MAX-ACCESS read-write
    STATUS     current
    DESCRIPTION
            "-- empty --"
    ::= { hmSetupIeee8021xPortsEntry 8 }

-- {COLUMN} 1.3.6.1.4.1.248.32.18.2.30.4.1.9
hmSetupIeee8021xPortsEntryQuietPeriod OBJECT-TYPE
    SYNTAX     Integer32 (0..65535)
    MAX-ACCESS read-write
    STATUS     current
    DESCRIPTION
            "-- empty --"
    ::= { hmSetupIeee8021xPortsEntry 9 }

-- {COLUMN} 1.3.6.1.4.1.248.32.18.2.30.4.1.10
hmSetupIeee8021xPortsEntryReAuthentication OBJECT-TYPE
    SYNTAX     INTEGER {
                  eNo (0),
                  eYes (1)
            }
    MAX-ACCESS read-write
    STATUS     current
    DESCRIPTION
            "-- empty --"
    ::= { hmSetupIeee8021xPortsEntry 10 }

-- {COLUMN} 1.3.6.1.4.1.248.32.18.2.30.4.1.11
hmSetupIeee8021xPortsEntryReAuthInterval OBJECT-TYPE
    SYNTAX     Integer32 (0..65535)
    MAX-ACCESS read-write
    STATUS     current
    DESCRIPTION
            "-- empty --"
    ::= { hmSetupIeee8021xPortsEntry 11 }

-- {COLUMN} 1.3.6.1.4.1.248.32.18.2.30.4.1.12
hmSetupIeee8021xPortsEntryKeyTransmission OBJECT-TYPE
    SYNTAX     INTEGER {
                  eNo (0),
                  eYes (1)
            }
    MAX-ACCESS read-write
    STATUS     current
    DESCRIPTION
            "-- empty --"
    ::= { hmSetupIeee8021xPortsEntry 12 }

-- {COLUMN} 1.3.6.1.4.1.248.32.18.2.30.4.1.13
hmSetupIeee8021xPortsEntryKeyTxInterval OBJECT-TYPE
    SYNTAX     Integer32 (0..65535)
    MAX-ACCESS read-write
    STATUS     current
    DESCRIPTION
            "-- empty --"
    ::= { hmSetupIeee8021xPortsEntry 13 }

-- {NODE} 1.3.6.1.4.1.248.32.18.2.31
hmSetupPppoeServer OBJECT IDENTIFIER ::= { hmSetup 31 }

-- {SCALAR} 1.3.6.1.4.1.248.32.18.2.31.1
hmSetupPppoeServerOperating OBJECT-TYPE
    SYNTAX     INTEGER {
                  eNo (0),
                  eYes (1)
            }
    MAX-ACCESS read-write
    STATUS     current
    DESCRIPTION
            "-- empty --"
    ::= { hmSetupPppoeServer 1 }

-- {TABLE} 1.3.6.1.4.1.248.32.18.2.31.2
hmSetupPppoeServerNameListTable OBJECT-TYPE
    SYNTAX     SEQUENCE OF HmSetupPppoeServerNameListEntry
    MAX-ACCESS not-accessible
    STATUS     current
    DESCRIPTION
            "-- empty --"
    ::= { hmSetupPppoeServer 2 }

-- {ROW} 1.3.6.1.4.1.248.32.18.2.31.2.1
hmSetupPppoeServerNameListEntry OBJECT-TYPE
    SYNTAX     HmSetupPppoeServerNameListEntry
    MAX-ACCESS not-accessible
    STATUS     current
    DESCRIPTION
            ""
    INDEX {
            hmSetupPppoeServerNameListEntryPeer
          }
    ::= { hmSetupPppoeServerNameListTable 1 }

HmSetupPppoeServerNameListEntry ::= SEQUENCE {
            hmSetupPppoeServerNameListEntryPeer DisplayString,
            hmSetupPppoeServerNameListEntryShTime Integer32,
            hmSetupPppoeServerNameListEntryMacAddress DisplayString
    }

-- {COLUMN} 1.3.6.1.4.1.248.32.18.2.31.2.1.1
hmSetupPppoeServerNameListEntryPeer OBJECT-TYPE
    SYNTAX     DisplayString (SIZE(0..16))
    MAX-ACCESS read-write
    STATUS     current
    DESCRIPTION
            "-- empty --"
    ::= { hmSetupPppoeServerNameListEntry 1 }

-- {COLUMN} 1.3.6.1.4.1.248.32.18.2.31.2.1.2
hmSetupPppoeServerNameListEntryShTime OBJECT-TYPE
    SYNTAX     Integer32 (0..65535)
    MAX-ACCESS read-write
    STATUS     current
    DESCRIPTION
            "-- empty --"
    ::= { hmSetupPppoeServerNameListEntry 2 }

-- {COLUMN} 1.3.6.1.4.1.248.32.18.2.31.2.1.3
hmSetupPppoeServerNameListEntryMacAddress OBJECT-TYPE
    SYNTAX     DisplayString (SIZE(0..12))
    MAX-ACCESS read-write
    STATUS     current
    DESCRIPTION
            "-- empty --"
    ::= { hmSetupPppoeServerNameListEntry 3 }

-- {SCALAR} 1.3.6.1.4.1.248.32.18.2.31.3
hmSetupPppoeServerService OBJECT-TYPE
    SYNTAX     DisplayString (SIZE(0..32))
    MAX-ACCESS read-write
    STATUS     current
    DESCRIPTION
            "-- empty --"
    ::= { hmSetupPppoeServer 3 }

-- {SCALAR} 1.3.6.1.4.1.248.32.18.2.31.4
hmSetupPppoeServerSessionLimit OBJECT-TYPE
    SYNTAX     Integer32 (0..2147483647)
    MAX-ACCESS read-write
    STATUS     current
    DESCRIPTION
            "-- empty --"
    ::= { hmSetupPppoeServer 4 }

-- {TABLE} 1.3.6.1.4.1.248.32.18.2.31.5
hmSetupPppoeServerPortsTable OBJECT-TYPE
    SYNTAX     SEQUENCE OF HmSetupPppoeServerPortsEntry
    MAX-ACCESS not-accessible
    STATUS     current
    DESCRIPTION
            "-- empty --"
    ::= { hmSetupPppoeServer 5 }

-- {ROW} 1.3.6.1.4.1.248.32.18.2.31.5.1
hmSetupPppoeServerPortsEntry OBJECT-TYPE
    SYNTAX     HmSetupPppoeServerPortsEntry
    MAX-ACCESS not-accessible
    STATUS     current
    DESCRIPTION
            ""
    INDEX {
            hmSetupPppoeServerPortsEntryPort
          }
    ::= { hmSetupPppoeServerPortsTable 1 }

HmSetupPppoeServerPortsEntry ::= SEQUENCE {
            hmSetupPppoeServerPortsEntryPort DisplayString,
            hmSetupPppoeServerPortsEntryEnablePppoe INTEGER
    }

-- {COLUMN} 1.3.6.1.4.1.248.32.18.2.31.5.1.2
hmSetupPppoeServerPortsEntryPort OBJECT-TYPE
    SYNTAX     DisplayString (SIZE(0..18))
    MAX-ACCESS read-only
    STATUS     current
    DESCRIPTION
            "-- empty --"
    ::= { hmSetupPppoeServerPortsEntry 2 }

-- {COLUMN} 1.3.6.1.4.1.248.32.18.2.31.5.1.3
hmSetupPppoeServerPortsEntryEnablePppoe OBJECT-TYPE
    SYNTAX     INTEGER {
                  eNo (0),
                  eYes (1)
            }
    MAX-ACCESS read-write
    STATUS     current
    DESCRIPTION
            "-- empty --"
    ::= { hmSetupPppoeServerPortsEntry 3 }

-- {SCALAR} 1.3.6.1.4.1.248.32.18.2.31.6
hmSetupPppoeServerAcName OBJECT-TYPE
    SYNTAX     DisplayString (SIZE(0..32))
    MAX-ACCESS read-write
    STATUS     current
    DESCRIPTION
            "-- empty --"
    ::= { hmSetupPppoeServer 6 }

-- {NODE} 1.3.6.1.4.1.248.32.18.2.32
hmSetupVlan OBJECT IDENTIFIER ::= { hmSetup 32 }

-- {TABLE} 1.3.6.1.4.1.248.32.18.2.32.1
hmSetupVlanNetworksTable OBJECT-TYPE
    SYNTAX     SEQUENCE OF HmSetupVlanNetworksEntry
    MAX-ACCESS not-accessible
    STATUS     current
    DESCRIPTION
            "-- empty --"
    ::= { hmSetupVlan 1 }

-- {ROW} 1.3.6.1.4.1.248.32.18.2.32.1.1
hmSetupVlanNetworksEntry OBJECT-TYPE
    SYNTAX     HmSetupVlanNetworksEntry
    MAX-ACCESS not-accessible
    STATUS     current
    DESCRIPTION
            ""
    INDEX {
            hmSetupVlanNetworksEntryName
          }
    ::= { hmSetupVlanNetworksTable 1 }

HmSetupVlanNetworksEntry ::= SEQUENCE {
            hmSetupVlanNetworksEntryName DisplayString,
            hmSetupVlanNetworksEntryVlanId Integer32,
            hmSetupVlanNetworksEntryPorts DisplayString,
            hmSetupVlanNetworksEntryLldpTxTlvPpid DisplayString,
            hmSetupVlanNetworksEntryLldpTxTlvName DisplayString
    }

-- {COLUMN} 1.3.6.1.4.1.248.32.18.2.32.1.1.1
hmSetupVlanNetworksEntryName OBJECT-TYPE
    SYNTAX     DisplayString (SIZE(0..16))
    MAX-ACCESS read-write
    STATUS     current
    DESCRIPTION
            "-- empty --"
    ::= { hmSetupVlanNetworksEntry 1 }

-- {COLUMN} 1.3.6.1.4.1.248.32.18.2.32.1.1.2
hmSetupVlanNetworksEntryVlanId OBJECT-TYPE
    SYNTAX     Integer32 (0..65535)
    MAX-ACCESS read-write
    STATUS     current
    DESCRIPTION
            "-- empty --"
    ::= { hmSetupVlanNetworksEntry 2 }

-- {COLUMN} 1.3.6.1.4.1.248.32.18.2.32.1.1.4
hmSetupVlanNetworksEntryPorts OBJECT-TYPE
    SYNTAX     DisplayString (SIZE(0..251))
    MAX-ACCESS read-write
    STATUS     current
    DESCRIPTION
            "-- empty --"
    ::= { hmSetupVlanNetworksEntry 4 }

-- {COLUMN} 1.3.6.1.4.1.248.32.18.2.32.1.1.5
hmSetupVlanNetworksEntryLldpTxTlvPpid OBJECT-TYPE
    SYNTAX     DisplayString (SIZE(0..251))
    MAX-ACCESS read-write
    STATUS     current
    DESCRIPTION
            "-- empty --"
    ::= { hmSetupVlanNetworksEntry 5 }

-- {COLUMN} 1.3.6.1.4.1.248.32.18.2.32.1.1.6
hmSetupVlanNetworksEntryLldpTxTlvName OBJECT-TYPE
    SYNTAX     DisplayString (SIZE(0..251))
    MAX-ACCESS read-write
    STATUS     current
    DESCRIPTION
            "-- empty --"
    ::= { hmSetupVlanNetworksEntry 6 }

-- {TABLE} 1.3.6.1.4.1.248.32.18.2.32.2
hmSetupVlanPortTableTable OBJECT-TYPE
    SYNTAX     SEQUENCE OF HmSetupVlanPortTableEntry
    MAX-ACCESS not-accessible
    STATUS     current
    DESCRIPTION
            "-- empty --"
    ::= { hmSetupVlan 2 }

-- {ROW} 1.3.6.1.4.1.248.32.18.2.32.2.1
hmSetupVlanPortTableEntry OBJECT-TYPE
    SYNTAX     HmSetupVlanPortTableEntry
    MAX-ACCESS not-accessible
    STATUS     current
    DESCRIPTION
            ""
    INDEX {
            hmSetupVlanPortTableEntryPort
          }
    ::= { hmSetupVlanPortTableTable 1 }

HmSetupVlanPortTableEntry ::= SEQUENCE {
            hmSetupVlanPortTableEntryPort DisplayString,
            hmSetupVlanPortTableEntryAllowAllVlans INTEGER,
            hmSetupVlanPortTableEntryPortVlanId Integer32,
            hmSetupVlanPortTableEntryTaggingMode INTEGER,
            hmSetupVlanPortTableEntryTxLldpTlvPortVlan INTEGER
    }

-- {COLUMN} 1.3.6.1.4.1.248.32.18.2.32.2.1.1
hmSetupVlanPortTableEntryPort OBJECT-TYPE
    SYNTAX     DisplayString (SIZE(0..18))
    MAX-ACCESS read-only
    STATUS     current
    DESCRIPTION
            "-- empty --"
    ::= { hmSetupVlanPortTableEntry 1 }

-- {COLUMN} 1.3.6.1.4.1.248.32.18.2.32.2.1.4
hmSetupVlanPortTableEntryAllowAllVlans OBJECT-TYPE
    SYNTAX     INTEGER {
                  eNo (0),
                  eYes (1)
            }
    MAX-ACCESS read-write
    STATUS     current
    DESCRIPTION
            "-- empty --"
    ::= { hmSetupVlanPortTableEntry 4 }

-- {COLUMN} 1.3.6.1.4.1.248.32.18.2.32.2.1.5
hmSetupVlanPortTableEntryPortVlanId OBJECT-TYPE
    SYNTAX     Integer32 (0..65535)
    MAX-ACCESS read-write
    STATUS     current
    DESCRIPTION
            "-- empty --"
    ::= { hmSetupVlanPortTableEntry 5 }

-- {COLUMN} 1.3.6.1.4.1.248.32.18.2.32.2.1.6
hmSetupVlanPortTableEntryTaggingMode OBJECT-TYPE
    SYNTAX     INTEGER {
                  eIngressMixed (0),
                  eNever (1),
                  eMixed (2),
                  eAlways (3)
            }
    MAX-ACCESS read-write
    STATUS     current
    DESCRIPTION
            "-- empty --"
    ::= { hmSetupVlanPortTableEntry 6 }

-- {COLUMN} 1.3.6.1.4.1.248.32.18.2.32.2.1.7
hmSetupVlanPortTableEntryTxLldpTlvPortVlan OBJECT-TYPE
    SYNTAX     INTEGER {
                  eNo (0),
                  eYes (1)
            }
    MAX-ACCESS read-write
    STATUS     current
    DESCRIPTION
            "-- empty --"
    ::= { hmSetupVlanPortTableEntry 7 }

-- {SCALAR} 1.3.6.1.4.1.248.32.18.2.32.4
hmSetupVlanOperating OBJECT-TYPE
    SYNTAX     INTEGER {
                  eNo (0),
                  eYes (1)
            }
    MAX-ACCESS read-write
    STATUS     current
    DESCRIPTION
            "-- empty --"
    ::= { hmSetupVlan 4 }

-- {SCALAR} 1.3.6.1.4.1.248.32.18.2.32.5
hmSetupVlanTagValue OBJECT-TYPE
    SYNTAX     DisplayString (SIZE(0..4))
    MAX-ACCESS read-write
    STATUS     current
    DESCRIPTION
            "-- empty --"
    ::= { hmSetupVlan 5 }

-- {NODE} 1.3.6.1.4.1.248.32.18.2.34
hmSetupPrinter OBJECT IDENTIFIER ::= { hmSetup 34 }

-- {TABLE} 1.3.6.1.4.1.248.32.18.2.34.1
hmSetupPrinterPrinterTable OBJECT-TYPE
    SYNTAX     SEQUENCE OF HmSetupPrinterPrinterEntry
    MAX-ACCESS not-accessible
    STATUS     current
    DESCRIPTION
            "-- empty --"
    ::= { hmSetupPrinter 1 }

-- {ROW} 1.3.6.1.4.1.248.32.18.2.34.1.1
hmSetupPrinterPrinterEntry OBJECT-TYPE
    SYNTAX     HmSetupPrinterPrinterEntry
    MAX-ACCESS not-accessible
    STATUS     current
    DESCRIPTION
            ""
    INDEX {
            hmSetupPrinterPrinterEntryPrinter
          }
    ::= { hmSetupPrinterPrinterTable 1 }

HmSetupPrinterPrinterEntry ::= SEQUENCE {
            hmSetupPrinterPrinterEntryPrinter DisplayString,
            hmSetupPrinterPrinterEntryRawipPort Integer32,
            hmSetupPrinterPrinterEntryLpdPort Integer32,
            hmSetupPrinterPrinterEntryActiv INTEGER,
            hmSetupPrinterPrinterEntryBidirectional INTEGER,
            hmSetupPrinterPrinterEntryResetOnOpen INTEGER
    }

-- {COLUMN} 1.3.6.1.4.1.248.32.18.2.34.1.1.1
hmSetupPrinterPrinterEntryPrinter OBJECT-TYPE
    SYNTAX     DisplayString (SIZE(0..15))
    MAX-ACCESS read-write
    STATUS     current
    DESCRIPTION
            "-- empty --"
    ::= { hmSetupPrinterPrinterEntry 1 }

-- {COLUMN} 1.3.6.1.4.1.248.32.18.2.34.1.1.2
hmSetupPrinterPrinterEntryRawipPort OBJECT-TYPE
    SYNTAX     Integer32 (0..2147483647)
    MAX-ACCESS read-write
    STATUS     current
    DESCRIPTION
            "-- empty --"
    ::= { hmSetupPrinterPrinterEntry 2 }

-- {COLUMN} 1.3.6.1.4.1.248.32.18.2.34.1.1.3
hmSetupPrinterPrinterEntryLpdPort OBJECT-TYPE
    SYNTAX     Integer32 (0..2147483647)
    MAX-ACCESS read-write
    STATUS     current
    DESCRIPTION
            "-- empty --"
    ::= { hmSetupPrinterPrinterEntry 3 }

-- {COLUMN} 1.3.6.1.4.1.248.32.18.2.34.1.1.4
hmSetupPrinterPrinterEntryActiv OBJECT-TYPE
    SYNTAX     INTEGER {
                  eNo (0),
                  eYes (1)
            }
    MAX-ACCESS read-write
    STATUS     current
    DESCRIPTION
            "-- empty --"
    ::= { hmSetupPrinterPrinterEntry 4 }

-- {COLUMN} 1.3.6.1.4.1.248.32.18.2.34.1.1.5
hmSetupPrinterPrinterEntryBidirectional OBJECT-TYPE
    SYNTAX     INTEGER {
                  eNo (0),
                  eYes (1)
            }
    MAX-ACCESS read-write
    STATUS     current
    DESCRIPTION
            "-- empty --"
    ::= { hmSetupPrinterPrinterEntry 5 }

-- {COLUMN} 1.3.6.1.4.1.248.32.18.2.34.1.1.6
hmSetupPrinterPrinterEntryResetOnOpen OBJECT-TYPE
    SYNTAX     INTEGER {
                  eNo (0),
                  eYes (1)
            }
    MAX-ACCESS read-write
    STATUS     current
    DESCRIPTION
            "-- empty --"
    ::= { hmSetupPrinterPrinterEntry 6 }

-- {TABLE} 1.3.6.1.4.1.248.32.18.2.34.2
hmSetupPrinterAccessListTable OBJECT-TYPE
    SYNTAX     SEQUENCE OF HmSetupPrinterAccessListEntry
    MAX-ACCESS not-accessible
    STATUS     current
    DESCRIPTION
            "-- empty --"
    ::= { hmSetupPrinter 2 }

-- {ROW} 1.3.6.1.4.1.248.32.18.2.34.2.1
hmSetupPrinterAccessListEntry OBJECT-TYPE
    SYNTAX     HmSetupPrinterAccessListEntry
    MAX-ACCESS not-accessible
    STATUS     current
    DESCRIPTION
            ""
    INDEX {
            hmSetupPrinterAccessListEntryIpAddress,
            hmSetupPrinterAccessListEntryIpNetmask,
            hmSetupPrinterAccessListEntryRtgTag
          }
    ::= { hmSetupPrinterAccessListTable 1 }

HmSetupPrinterAccessListEntry ::= SEQUENCE {
            hmSetupPrinterAccessListEntryIpAddress IpAddress,
            hmSetupPrinterAccessListEntryIpNetmask IpAddress,
            hmSetupPrinterAccessListEntryRtgTag Integer32
    }

-- {COLUMN} 1.3.6.1.4.1.248.32.18.2.34.2.1.1
hmSetupPrinterAccessListEntryIpAddress OBJECT-TYPE
    SYNTAX     IpAddress
    MAX-ACCESS read-write
    STATUS     current
    DESCRIPTION
            "-- empty --"
    ::= { hmSetupPrinterAccessListEntry 1 }

-- {COLUMN} 1.3.6.1.4.1.248.32.18.2.34.2.1.2
hmSetupPrinterAccessListEntryIpNetmask OBJECT-TYPE
    SYNTAX     IpAddress
    MAX-ACCESS read-write
    STATUS     current
    DESCRIPTION
            "-- empty --"
    ::= { hmSetupPrinterAccessListEntry 2 }

-- {COLUMN} 1.3.6.1.4.1.248.32.18.2.34.2.1.3
hmSetupPrinterAccessListEntryRtgTag OBJECT-TYPE
    SYNTAX     Integer32 (0..65535)
    MAX-ACCESS read-write
    STATUS     current
    DESCRIPTION
            "-- empty --"
    ::= { hmSetupPrinterAccessListEntry 3 }

-- {NODE} 1.3.6.1.4.1.248.32.18.2.35
hmSetupEchoServer OBJECT IDENTIFIER ::= { hmSetup 35 }

-- {SCALAR} 1.3.6.1.4.1.248.32.18.2.35.1
hmSetupEchoServerOperating OBJECT-TYPE
    SYNTAX     INTEGER {
                  eNo (0),
                  eYes (1)
            }
    MAX-ACCESS read-write
    STATUS     current
    DESCRIPTION
            "-- empty --"
    ::= { hmSetupEchoServer 1 }

-- {TABLE} 1.3.6.1.4.1.248.32.18.2.35.2
hmSetupEchoServerAccessTableTable OBJECT-TYPE
    SYNTAX     SEQUENCE OF HmSetupEchoServerAccessTableEntry
    MAX-ACCESS not-accessible
    STATUS     current
    DESCRIPTION
            "-- empty --"
    ::= { hmSetupEchoServer 2 }

-- {ROW} 1.3.6.1.4.1.248.32.18.2.35.2.1
hmSetupEchoServerAccessTableEntry OBJECT-TYPE
    SYNTAX     HmSetupEchoServerAccessTableEntry
    MAX-ACCESS not-accessible
    STATUS     current
    DESCRIPTION
            ""
    INDEX {
            hmSetupEchoServerAccessTableEntryIpAddress,
            hmSetupEchoServerAccessTableEntryNetmask
          }
    ::= { hmSetupEchoServerAccessTableTable 1 }

HmSetupEchoServerAccessTableEntry ::= SEQUENCE {
            hmSetupEchoServerAccessTableEntryIpAddress IpAddress,
            hmSetupEchoServerAccessTableEntryNetmask IpAddress,
            hmSetupEchoServerAccessTableEntryProtokoll INTEGER,
            hmSetupEchoServerAccessTableEntryActive INTEGER,
            hmSetupEchoServerAccessTableEntryComment DisplayString
    }

-- {COLUMN} 1.3.6.1.4.1.248.32.18.2.35.2.1.1
hmSetupEchoServerAccessTableEntryIpAddress OBJECT-TYPE
    SYNTAX     IpAddress
    MAX-ACCESS read-write
    STATUS     current
    DESCRIPTION
            "-- empty --"
    ::= { hmSetupEchoServerAccessTableEntry 1 }

-- {COLUMN} 1.3.6.1.4.1.248.32.18.2.35.2.1.2
hmSetupEchoServerAccessTableEntryNetmask OBJECT-TYPE
    SYNTAX     IpAddress
    MAX-ACCESS read-write
    STATUS     current
    DESCRIPTION
            "-- empty --"
    ::= { hmSetupEchoServerAccessTableEntry 2 }

-- {COLUMN} 1.3.6.1.4.1.248.32.18.2.35.2.1.3
hmSetupEchoServerAccessTableEntryProtokoll OBJECT-TYPE
    SYNTAX     INTEGER {
                  eNone (0),
                  eTcp (1),
                  eUdp (2),
                  eTcpPlusUdp (3)
            }
    MAX-ACCESS read-write
    STATUS     current
    DESCRIPTION
            "-- empty --"
    ::= { hmSetupEchoServerAccessTableEntry 3 }

-- {COLUMN} 1.3.6.1.4.1.248.32.18.2.35.2.1.4
hmSetupEchoServerAccessTableEntryActive OBJECT-TYPE
    SYNTAX     INTEGER {
                  eYes (0),
                  eNo (1)
            }
    MAX-ACCESS read-write
    STATUS     current
    DESCRIPTION
            "-- empty --"
    ::= { hmSetupEchoServerAccessTableEntry 4 }

-- {COLUMN} 1.3.6.1.4.1.248.32.18.2.35.2.1.5
hmSetupEchoServerAccessTableEntryComment OBJECT-TYPE
    SYNTAX     DisplayString (SIZE(0..31))
    MAX-ACCESS read-write
    STATUS     current
    DESCRIPTION
            "-- empty --"
    ::= { hmSetupEchoServerAccessTableEntry 5 }

-- {SCALAR} 1.3.6.1.4.1.248.32.18.2.35.3
hmSetupEchoServerTcpTimeout OBJECT-TYPE
    SYNTAX     Integer32 (0..2147483647)
    MAX-ACCESS read-write
    STATUS     current
    DESCRIPTION
            "-- empty --"
    ::= { hmSetupEchoServer 3 }

-- {NODE} 1.3.6.1.4.1.248.32.18.2.36
hmSetupPerfmon OBJECT IDENTIFIER ::= { hmSetup 36 }

-- {TABLE} 1.3.6.1.4.1.248.32.18.2.36.2
hmSetupPerfmonRttmonadminTable OBJECT-TYPE
    SYNTAX     SEQUENCE OF HmSetupPerfmonRttmonadminEntry
    MAX-ACCESS not-accessible
    STATUS     current
    DESCRIPTION
            "-- empty --"
    ::= { hmSetupPerfmon 2 }

-- {ROW} 1.3.6.1.4.1.248.32.18.2.36.2.1
hmSetupPerfmonRttmonadminEntry OBJECT-TYPE
    SYNTAX     HmSetupPerfmonRttmonadminEntry
    MAX-ACCESS not-accessible
    STATUS     current
    DESCRIPTION
            ""
    INDEX {
            hmSetupPerfmonRttmonadminEntryIndex
          }
    ::= { hmSetupPerfmonRttmonadminTable 1 }

HmSetupPerfmonRttmonadminEntry ::= SEQUENCE {
            hmSetupPerfmonRttmonadminEntryIndex Integer32,
            hmSetupPerfmonRttmonadminEntryType INTEGER,
            hmSetupPerfmonRttmonadminEntryFrequency Integer32,
            hmSetupPerfmonRttmonadminEntryTimeout Integer32,
            hmSetupPerfmonRttmonadminEntryStatus INTEGER
    }

-- {COLUMN} 1.3.6.1.4.1.248.32.18.2.36.2.1.1
hmSetupPerfmonRttmonadminEntryIndex OBJECT-TYPE
    SYNTAX     Integer32 (0..2147483647)
    MAX-ACCESS read-write
    STATUS     current
    DESCRIPTION
            "-- empty --"
    ::= { hmSetupPerfmonRttmonadminEntry 1 }

-- {COLUMN} 1.3.6.1.4.1.248.32.18.2.36.2.1.4
hmSetupPerfmonRttmonadminEntryType OBJECT-TYPE
    SYNTAX     INTEGER {
                  eJitter (9)
            }
    MAX-ACCESS read-write
    STATUS     current
    DESCRIPTION
            "-- empty --"
    ::= { hmSetupPerfmonRttmonadminEntry 4 }

-- {COLUMN} 1.3.6.1.4.1.248.32.18.2.36.2.1.6
hmSetupPerfmonRttmonadminEntryFrequency OBJECT-TYPE
    SYNTAX     Integer32 (0..2147483647)
    MAX-ACCESS read-write
    STATUS     current
    DESCRIPTION
            "-- empty --"
    ::= { hmSetupPerfmonRttmonadminEntry 6 }

-- {COLUMN} 1.3.6.1.4.1.248.32.18.2.36.2.1.7
hmSetupPerfmonRttmonadminEntryTimeout OBJECT-TYPE
    SYNTAX     Integer32 (0..2147483647)
    MAX-ACCESS read-write
    STATUS     current
    DESCRIPTION
            "-- empty --"
    ::= { hmSetupPerfmonRttmonadminEntry 7 }

-- {COLUMN} 1.3.6.1.4.1.248.32.18.2.36.2.1.9
hmSetupPerfmonRttmonadminEntryStatus OBJECT-TYPE
    SYNTAX     INTEGER {
                  eActive (1),
                  eNotInService (2),
                  eNotReady (3),
                  eCreate (5),
                  eDestroy (6)
            }
    MAX-ACCESS read-write
    STATUS     current
    DESCRIPTION
            "-- empty --"
    ::= { hmSetupPerfmonRttmonadminEntry 9 }

-- {TABLE} 1.3.6.1.4.1.248.32.18.2.36.3
hmSetupPerfmonRttmonechoadminTable OBJECT-TYPE
    SYNTAX     SEQUENCE OF HmSetupPerfmonRttmonechoadminEntry
    MAX-ACCESS not-accessible
    STATUS     current
    DESCRIPTION
            "-- empty --"
    ::= { hmSetupPerfmon 3 }

-- {ROW} 1.3.6.1.4.1.248.32.18.2.36.3.1
hmSetupPerfmonRttmonechoadminEntry OBJECT-TYPE
    SYNTAX     HmSetupPerfmonRttmonechoadminEntry
    MAX-ACCESS not-accessible
    STATUS     current
    DESCRIPTION
            ""
    INDEX {
            hmSetupPerfmonRttmonechoadminEntryIndex
          }
    ::= { hmSetupPerfmonRttmonechoadminTable 1 }

HmSetupPerfmonRttmonechoadminEntry ::= SEQUENCE {
            hmSetupPerfmonRttmonechoadminEntryProtocol INTEGER,
            hmSetupPerfmonRttmonechoadminEntryDestinationAddress IpAddress,
            hmSetupPerfmonRttmonechoadminEntryPacketSize Integer32,
            hmSetupPerfmonRttmonechoadminEntryDestinationPort Integer32,
            hmSetupPerfmonRttmonechoadminEntryInterval Integer32,
            hmSetupPerfmonRttmonechoadminEntryPacketCount Integer32,
            hmSetupPerfmonRttmonechoadminEntryIndex Integer32
    }

-- {COLUMN} 1.3.6.1.4.1.248.32.18.2.36.3.1.1
hmSetupPerfmonRttmonechoadminEntryProtocol OBJECT-TYPE
    SYNTAX     INTEGER {
                  eEcho (3)
            }
    MAX-ACCESS read-write
    STATUS     current
    DESCRIPTION
            "-- empty --"
    ::= { hmSetupPerfmonRttmonechoadminEntry 1 }

-- {COLUMN} 1.3.6.1.4.1.248.32.18.2.36.3.1.2
hmSetupPerfmonRttmonechoadminEntryDestinationAddress OBJECT-TYPE
    SYNTAX     IpAddress
    MAX-ACCESS read-write
    STATUS     current
    DESCRIPTION
            "-- empty --"
    ::= { hmSetupPerfmonRttmonechoadminEntry 2 }

-- {COLUMN} 1.3.6.1.4.1.248.32.18.2.36.3.1.3
hmSetupPerfmonRttmonechoadminEntryPacketSize OBJECT-TYPE
    SYNTAX     Integer32 (0..65535)
    MAX-ACCESS read-write
    STATUS     current
    DESCRIPTION
            "-- empty --"
    ::= { hmSetupPerfmonRttmonechoadminEntry 3 }

-- {COLUMN} 1.3.6.1.4.1.248.32.18.2.36.3.1.5
hmSetupPerfmonRttmonechoadminEntryDestinationPort OBJECT-TYPE
    SYNTAX     Integer32 (0..65535)
    MAX-ACCESS read-write
    STATUS     current
    DESCRIPTION
            "-- empty --"
    ::= { hmSetupPerfmonRttmonechoadminEntry 5 }

-- {COLUMN} 1.3.6.1.4.1.248.32.18.2.36.3.1.17
hmSetupPerfmonRttmonechoadminEntryInterval OBJECT-TYPE
    SYNTAX     Integer32 (0..2147483647)
    MAX-ACCESS read-write
    STATUS     current
    DESCRIPTION
            "-- empty --"
    ::= { hmSetupPerfmonRttmonechoadminEntry 17 }

-- {COLUMN} 1.3.6.1.4.1.248.32.18.2.36.3.1.18
hmSetupPerfmonRttmonechoadminEntryPacketCount OBJECT-TYPE
    SYNTAX     Integer32 (0..2147483647)
    MAX-ACCESS read-write
    STATUS     current
    DESCRIPTION
            "-- empty --"
    ::= { hmSetupPerfmonRttmonechoadminEntry 18 }

-- {COLUMN} 1.3.6.1.4.1.248.32.18.2.36.3.1.255
hmSetupPerfmonRttmonechoadminEntryIndex OBJECT-TYPE
    SYNTAX     Integer32 (0..2147483647)
    MAX-ACCESS read-only
    STATUS     current
    DESCRIPTION
            "-- empty --"
    ::= { hmSetupPerfmonRttmonechoadminEntry 255 }

-- {TABLE} 1.3.6.1.4.1.248.32.18.2.36.4
hmSetupPerfmonRttmonstatisticsTable OBJECT-TYPE
    SYNTAX     SEQUENCE OF HmSetupPerfmonRttmonstatisticsEntry
    MAX-ACCESS not-accessible
    STATUS     current
    DESCRIPTION
            "-- empty --"
    ::= { hmSetupPerfmon 4 }

-- {ROW} 1.3.6.1.4.1.248.32.18.2.36.4.1
hmSetupPerfmonRttmonstatisticsEntry OBJECT-TYPE
    SYNTAX     HmSetupPerfmonRttmonstatisticsEntry
    MAX-ACCESS not-accessible
    STATUS     current
    DESCRIPTION
            ""
    INDEX {
            hmSetupPerfmonRttmonstatisticsEntryIndex
          }
    ::= { hmSetupPerfmonRttmonstatisticsTable 1 }

HmSetupPerfmonRttmonstatisticsEntry ::= SEQUENCE {
            hmSetupPerfmonRttmonstatisticsEntryCompletions Integer32,
            hmSetupPerfmonRttmonstatisticsEntryRttCount Integer32,
            hmSetupPerfmonRttmonstatisticsEntryRttSum Integer32,
            hmSetupPerfmonRttmonstatisticsEntryRttMin Integer32,
            hmSetupPerfmonRttmonstatisticsEntryRttMax Integer32,
            hmSetupPerfmonRttmonstatisticsEntryJitterMinPosSd Integer32,
            hmSetupPerfmonRttmonstatisticsEntryJitterMaxPosSd Integer32,
            hmSetupPerfmonRttmonstatisticsEntryJitterCountPosSd Integer32,
            hmSetupPerfmonRttmonstatisticsEntryJitterSumPosSd Integer32,
            hmSetupPerfmonRttmonstatisticsEntryJitterMinPosDs Integer32,
            hmSetupPerfmonRttmonstatisticsEntryJitterMaxPosDs Integer32,
            hmSetupPerfmonRttmonstatisticsEntryJitterCountPosDs Integer32,
            hmSetupPerfmonRttmonstatisticsEntryJitterSumPosDs Integer32,
            hmSetupPerfmonRttmonstatisticsEntryJitterMinNegSd Integer32,
            hmSetupPerfmonRttmonstatisticsEntryJitterMaxNegSd Integer32,
            hmSetupPerfmonRttmonstatisticsEntryJitterCountNegSd Integer32,
            hmSetupPerfmonRttmonstatisticsEntryJitterSumNegSd Integer32,
            hmSetupPerfmonRttmonstatisticsEntryJitterMinNegDs Integer32,
            hmSetupPerfmonRttmonstatisticsEntryJitterMaxNegDs Integer32,
            hmSetupPerfmonRttmonstatisticsEntryJitterCountNegDs Integer32,
            hmSetupPerfmonRttmonstatisticsEntryJitterSumNegDs Integer32,
            hmSetupPerfmonRttmonstatisticsEntryPacketLossSd Integer32,
            hmSetupPerfmonRttmonstatisticsEntryPacketLossDs Integer32,
            hmSetupPerfmonRttmonstatisticsEntryAverageJitter Integer32,
            hmSetupPerfmonRttmonstatisticsEntryAverageJitterSd Integer32,
            hmSetupPerfmonRttmonstatisticsEntryAverageJitterDs Integer32,
            hmSetupPerfmonRttmonstatisticsEntryIndex Integer32
    }

-- {COLUMN} 1.3.6.1.4.1.248.32.18.2.36.4.1.2
hmSetupPerfmonRttmonstatisticsEntryCompletions OBJECT-TYPE
    SYNTAX     Integer32 (0..2147483647)
    MAX-ACCESS read-only
    STATUS     current
    DESCRIPTION
            "-- empty --"
    ::= { hmSetupPerfmonRttmonstatisticsEntry 2 }

-- {COLUMN} 1.3.6.1.4.1.248.32.18.2.36.4.1.4
hmSetupPerfmonRttmonstatisticsEntryRttCount OBJECT-TYPE
    SYNTAX     Integer32 (0..2147483647)
    MAX-ACCESS read-only
    STATUS     current
    DESCRIPTION
            "-- empty --"
    ::= { hmSetupPerfmonRttmonstatisticsEntry 4 }

-- {COLUMN} 1.3.6.1.4.1.248.32.18.2.36.4.1.5
hmSetupPerfmonRttmonstatisticsEntryRttSum OBJECT-TYPE
    SYNTAX     Integer32 (0..2147483647)
    MAX-ACCESS read-only
    STATUS     current
    DESCRIPTION
            "-- empty --"
    ::= { hmSetupPerfmonRttmonstatisticsEntry 5 }

-- {COLUMN} 1.3.6.1.4.1.248.32.18.2.36.4.1.8
hmSetupPerfmonRttmonstatisticsEntryRttMin OBJECT-TYPE
    SYNTAX     Integer32 (0..2147483647)
    MAX-ACCESS read-only
    STATUS     current
    DESCRIPTION
            "-- empty --"
    ::= { hmSetupPerfmonRttmonstatisticsEntry 8 }

-- {COLUMN} 1.3.6.1.4.1.248.32.18.2.36.4.1.9
hmSetupPerfmonRttmonstatisticsEntryRttMax OBJECT-TYPE
    SYNTAX     Integer32 (0..2147483647)
    MAX-ACCESS read-only
    STATUS     current
    DESCRIPTION
            "-- empty --"
    ::= { hmSetupPerfmonRttmonstatisticsEntry 9 }

-- {COLUMN} 1.3.6.1.4.1.248.32.18.2.36.4.1.10
hmSetupPerfmonRttmonstatisticsEntryJitterMinPosSd OBJECT-TYPE
    SYNTAX     Integer32 (0..2147483647)
    MAX-ACCESS read-only
    STATUS     current
    DESCRIPTION
            "-- empty --"
    ::= { hmSetupPerfmonRttmonstatisticsEntry 10 }

-- {COLUMN} 1.3.6.1.4.1.248.32.18.2.36.4.1.11
hmSetupPerfmonRttmonstatisticsEntryJitterMaxPosSd OBJECT-TYPE
    SYNTAX     Integer32 (0..2147483647)
    MAX-ACCESS read-only
    STATUS     current
    DESCRIPTION
            "-- empty --"
    ::= { hmSetupPerfmonRttmonstatisticsEntry 11 }

-- {COLUMN} 1.3.6.1.4.1.248.32.18.2.36.4.1.12
hmSetupPerfmonRttmonstatisticsEntryJitterCountPosSd OBJECT-TYPE
    SYNTAX     Integer32 (0..2147483647)
    MAX-ACCESS read-only
    STATUS     current
    DESCRIPTION
            "-- empty --"
    ::= { hmSetupPerfmonRttmonstatisticsEntry 12 }

-- {COLUMN} 1.3.6.1.4.1.248.32.18.2.36.4.1.13
hmSetupPerfmonRttmonstatisticsEntryJitterSumPosSd OBJECT-TYPE
    SYNTAX     Integer32 (0..2147483647)
    MAX-ACCESS read-only
    STATUS     current
    DESCRIPTION
            "-- empty --"
    ::= { hmSetupPerfmonRttmonstatisticsEntry 13 }

-- {COLUMN} 1.3.6.1.4.1.248.32.18.2.36.4.1.16
hmSetupPerfmonRttmonstatisticsEntryJitterMinPosDs OBJECT-TYPE
    SYNTAX     Integer32 (0..2147483647)
    MAX-ACCESS read-only
    STATUS     current
    DESCRIPTION
            "-- empty --"
    ::= { hmSetupPerfmonRttmonstatisticsEntry 16 }

-- {COLUMN} 1.3.6.1.4.1.248.32.18.2.36.4.1.17
hmSetupPerfmonRttmonstatisticsEntryJitterMaxPosDs OBJECT-TYPE
    SYNTAX     Integer32 (0..2147483647)
    MAX-ACCESS read-only
    STATUS     current
    DESCRIPTION
            "-- empty --"
    ::= { hmSetupPerfmonRttmonstatisticsEntry 17 }

-- {COLUMN} 1.3.6.1.4.1.248.32.18.2.36.4.1.18
hmSetupPerfmonRttmonstatisticsEntryJitterCountPosDs OBJECT-TYPE
    SYNTAX     Integer32 (0..2147483647)
    MAX-ACCESS read-only
    STATUS     current
    DESCRIPTION
            "-- empty --"
    ::= { hmSetupPerfmonRttmonstatisticsEntry 18 }

-- {COLUMN} 1.3.6.1.4.1.248.32.18.2.36.4.1.19
hmSetupPerfmonRttmonstatisticsEntryJitterSumPosDs OBJECT-TYPE
    SYNTAX     Integer32 (0..2147483647)
    MAX-ACCESS read-only
    STATUS     current
    DESCRIPTION
            "-- empty --"
    ::= { hmSetupPerfmonRttmonstatisticsEntry 19 }

-- {COLUMN} 1.3.6.1.4.1.248.32.18.2.36.4.1.22
hmSetupPerfmonRttmonstatisticsEntryJitterMinNegSd OBJECT-TYPE
    SYNTAX     Integer32 (0..2147483647)
    MAX-ACCESS read-only
    STATUS     current
    DESCRIPTION
            "-- empty --"
    ::= { hmSetupPerfmonRttmonstatisticsEntry 22 }

-- {COLUMN} 1.3.6.1.4.1.248.32.18.2.36.4.1.23
hmSetupPerfmonRttmonstatisticsEntryJitterMaxNegSd OBJECT-TYPE
    SYNTAX     Integer32 (0..2147483647)
    MAX-ACCESS read-only
    STATUS     current
    DESCRIPTION
            "-- empty --"
    ::= { hmSetupPerfmonRttmonstatisticsEntry 23 }

-- {COLUMN} 1.3.6.1.4.1.248.32.18.2.36.4.1.24
hmSetupPerfmonRttmonstatisticsEntryJitterCountNegSd OBJECT-TYPE
    SYNTAX     Integer32 (0..2147483647)
    MAX-ACCESS read-only
    STATUS     current
    DESCRIPTION
            "-- empty --"
    ::= { hmSetupPerfmonRttmonstatisticsEntry 24 }

-- {COLUMN} 1.3.6.1.4.1.248.32.18.2.36.4.1.25
hmSetupPerfmonRttmonstatisticsEntryJitterSumNegSd OBJECT-TYPE
    SYNTAX     Integer32 (0..2147483647)
    MAX-ACCESS read-only
    STATUS     current
    DESCRIPTION
            "-- empty --"
    ::= { hmSetupPerfmonRttmonstatisticsEntry 25 }

-- {COLUMN} 1.3.6.1.4.1.248.32.18.2.36.4.1.28
hmSetupPerfmonRttmonstatisticsEntryJitterMinNegDs OBJECT-TYPE
    SYNTAX     Integer32 (0..2147483647)
    MAX-ACCESS read-only
    STATUS     current
    DESCRIPTION
            "-- empty --"
    ::= { hmSetupPerfmonRttmonstatisticsEntry 28 }

-- {COLUMN} 1.3.6.1.4.1.248.32.18.2.36.4.1.29
hmSetupPerfmonRttmonstatisticsEntryJitterMaxNegDs OBJECT-TYPE
    SYNTAX     Integer32 (0..2147483647)
    MAX-ACCESS read-only
    STATUS     current
    DESCRIPTION
            "-- empty --"
    ::= { hmSetupPerfmonRttmonstatisticsEntry 29 }

-- {COLUMN} 1.3.6.1.4.1.248.32.18.2.36.4.1.30
hmSetupPerfmonRttmonstatisticsEntryJitterCountNegDs OBJECT-TYPE
    SYNTAX     Integer32 (0..2147483647)
    MAX-ACCESS read-only
    STATUS     current
    DESCRIPTION
            "-- empty --"
    ::= { hmSetupPerfmonRttmonstatisticsEntry 30 }

-- {COLUMN} 1.3.6.1.4.1.248.32.18.2.36.4.1.31
hmSetupPerfmonRttmonstatisticsEntryJitterSumNegDs OBJECT-TYPE
    SYNTAX     Integer32 (0..2147483647)
    MAX-ACCESS read-only
    STATUS     current
    DESCRIPTION
            "-- empty --"
    ::= { hmSetupPerfmonRttmonstatisticsEntry 31 }

-- {COLUMN} 1.3.6.1.4.1.248.32.18.2.36.4.1.34
hmSetupPerfmonRttmonstatisticsEntryPacketLossSd OBJECT-TYPE
    SYNTAX     Integer32 (0..2147483647)
    MAX-ACCESS read-only
    STATUS     current
    DESCRIPTION
            "-- empty --"
    ::= { hmSetupPerfmonRttmonstatisticsEntry 34 }

-- {COLUMN} 1.3.6.1.4.1.248.32.18.2.36.4.1.35
hmSetupPerfmonRttmonstatisticsEntryPacketLossDs OBJECT-TYPE
    SYNTAX     Integer32 (0..2147483647)
    MAX-ACCESS read-only
    STATUS     current
    DESCRIPTION
            "-- empty --"
    ::= { hmSetupPerfmonRttmonstatisticsEntry 35 }

-- {COLUMN} 1.3.6.1.4.1.248.32.18.2.36.4.1.62
hmSetupPerfmonRttmonstatisticsEntryAverageJitter OBJECT-TYPE
    SYNTAX     Integer32 (0..2147483647)
    MAX-ACCESS read-only
    STATUS     current
    DESCRIPTION
            "-- empty --"
    ::= { hmSetupPerfmonRttmonstatisticsEntry 62 }

-- {COLUMN} 1.3.6.1.4.1.248.32.18.2.36.4.1.63
hmSetupPerfmonRttmonstatisticsEntryAverageJitterSd OBJECT-TYPE
    SYNTAX     Integer32 (0..2147483647)
    MAX-ACCESS read-only
    STATUS     current
    DESCRIPTION
            "-- empty --"
    ::= { hmSetupPerfmonRttmonstatisticsEntry 63 }

-- {COLUMN} 1.3.6.1.4.1.248.32.18.2.36.4.1.64
hmSetupPerfmonRttmonstatisticsEntryAverageJitterDs OBJECT-TYPE
    SYNTAX     Integer32 (0..2147483647)
    MAX-ACCESS read-only
    STATUS     current
    DESCRIPTION
            "-- empty --"
    ::= { hmSetupPerfmonRttmonstatisticsEntry 64 }

-- {COLUMN} 1.3.6.1.4.1.248.32.18.2.36.4.1.255
hmSetupPerfmonRttmonstatisticsEntryIndex OBJECT-TYPE
    SYNTAX     Integer32 (0..2147483647)
    MAX-ACCESS read-only
    STATUS     current
    DESCRIPTION
            "-- empty --"
    ::= { hmSetupPerfmonRttmonstatisticsEntry 255 }

-- {NODE} 1.3.6.1.4.1.248.32.18.2.37
hmSetupWlanMngmt OBJECT IDENTIFIER ::= { hmSetup 37 }

-- {NODE} 1.3.6.1.4.1.248.32.18.2.37.1
hmSetupWlanMngmtApConf OBJECT IDENTIFIER ::= { hmSetupWlanMngmt 1 }

-- {TABLE} 1.3.6.1.4.1.248.32.18.2.37.1.1
hmSetupWlanMngmtApConfNetwprofilsTable OBJECT-TYPE
    SYNTAX     SEQUENCE OF HmSetupWlanMngmtApConfNetwprofilsEntry
    MAX-ACCESS not-accessible
    STATUS     current
    DESCRIPTION
            "network profiles"
    ::= { hmSetupWlanMngmtApConf 1 }

-- {ROW} 1.3.6.1.4.1.248.32.18.2.37.1.1.1
hmSetupWlanMngmtApConfNetwprofilsEntry OBJECT-TYPE
    SYNTAX     HmSetupWlanMngmtApConfNetwprofilsEntry
    MAX-ACCESS not-accessible
    STATUS     current
    DESCRIPTION
            ""
    INDEX {
            hmSetupWlanMngmtApConfNetwprofilsEntryName
          }
    ::= { hmSetupWlanMngmtApConfNetwprofilsTable 1 }

HmSetupWlanMngmtApConfNetwprofilsEntry ::= SEQUENCE {
            hmSetupWlanMngmtApConfNetwprofilsEntryName DisplayString,
            hmSetupWlanMngmtApConfNetwprofilsEntryParentName DisplayString,
            hmSetupWlanMngmtApConfNetwprofilsEntryLocVal DisplayString,
            hmSetupWlanMngmtApConfNetwprofilsEntryOperating INTEGER,
            hmSetupWlanMngmtApConfNetwprofilsEntryVlanId Integer32,
            hmSetupWlanMngmtApConfNetwprofilsEntryEncryption INTEGER,
            hmSetupWlanMngmtApConfNetwprofilsEntryWpa1SessionKeytypes INTEGER,
            hmSetupWlanMngmtApConfNetwprofilsEntryWpaVersion INTEGER,
            hmSetupWlanMngmtApConfNetwprofilsEntryKey DisplayString,
            hmSetupWlanMngmtApConfNetwprofilsEntryRadioBand INTEGER,
            hmSetupWlanMngmtApConfNetwprofilsEntryContinuation Integer32,
            hmSetupWlanMngmtApConfNetwprofilsEntryMinTxRate INTEGER,
            hmSetupWlanMngmtApConfNetwprofilsEntryMaxTxRate INTEGER,
            hmSetupWlanMngmtApConfNetwprofilsEntryBasicRate INTEGER,
            hmSetupWlanMngmtApConfNetwprofilsEntry11bPreamble INTEGER,
            hmSetupWlanMngmtApConfNetwprofilsEntryMacFilter INTEGER,
            hmSetupWlanMngmtApConfNetwprofilsEntryClBrgSupport INTEGER,
            hmSetupWlanMngmtApConfNetwprofilsEntryMaxStations Integer32,
            hmSetupWlanMngmtApConfNetwprofilsEntrySsidBroadcast INTEGER,
            hmSetupWlanMngmtApConfNetwprofilsEntrySsid DisplayString,
            hmSetupWlanMngmtApConfNetwprofilsEntryMinHtMcs INTEGER,
            hmSetupWlanMngmtApConfNetwprofilsEntryMaxHtMcs INTEGER,
            hmSetupWlanMngmtApConfNetwprofilsEntryShortGuardInterval INTEGER,
            hmSetupWlanMngmtApConfNetwprofilsEntryMaxSpatialStreams INTEGER,
            hmSetupWlanMngmtApConfNetwprofilsEntrySendAggregates INTEGER,
            hmSetupWlanMngmtApConfNetwprofilsEntryWpa2SessionKeytypes INTEGER,
            hmSetupWlanMngmtApConfNetwprofilsEntryRadiusAccounting INTEGER,
            hmSetupWlanMngmtApConfNetwprofilsEntryVlanMode INTEGER,
            hmSetupWlanMngmtApConfNetwprofilsEntryConnectSsidTo INTEGER,
            hmSetupWlanMngmtApConfNetwprofilsEntryInterStationTraffic INTEGER,
            hmSetupWlanMngmtApConfNetwprofilsEntryVlanIdnew Integer32,
            hmSetupWlanMngmtApConfNetwprofilsEntryRadiusProfile DisplayString,
            hmSetupWlanMngmtApConfNetwprofilsEntryStbcActivated INTEGER,
            hmSetupWlanMngmtApConfNetwprofilsEntryLdpcActivated INTEGER,
            hmSetupWlanMngmtApConfNetwprofilsEntryMinClientStrength Integer32,
            hmSetupWlanMngmtApConfNetwprofilsEntryIeee80211uNetworkProfile DisplayString,
            hmSetupWlanMngmtApConfNetwprofilsEntryOkc INTEGER,
            hmSetupWlanMngmtApConfNetwprofilsEntryWpa2KeyManagement BITS,
            hmSetupWlanMngmtApConfNetwprofilsEntryApsd INTEGER,
            hmSetupWlanMngmtApConfNetwprofilsEntryProtMgmtFrames INTEGER,
            hmSetupWlanMngmtApConfNetwprofilsEntryTxLimit Integer32,
            hmSetupWlanMngmtApConfNetwprofilsEntryRxLimit Integer32,
            hmSetupWlanMngmtApConfNetwprofilsEntryLbsTracking INTEGER,
            hmSetupWlanMngmtApConfNetwprofilsEntryLbsTrackingList DisplayString,
            hmSetupWlanMngmtApConfNetwprofilsEntryClBrgRoamingSupport INTEGER
    }

-- {COLUMN} 1.3.6.1.4.1.248.32.18.2.37.1.1.1.1
hmSetupWlanMngmtApConfNetwprofilsEntryName OBJECT-TYPE
    SYNTAX     DisplayString (SIZE(0..31))
    MAX-ACCESS read-write
    STATUS     current
    DESCRIPTION
            "-- empty --"
    ::= { hmSetupWlanMngmtApConfNetwprofilsEntry 1 }

-- {COLUMN} 1.3.6.1.4.1.248.32.18.2.37.1.1.1.2
hmSetupWlanMngmtApConfNetwprofilsEntryParentName OBJECT-TYPE
    SYNTAX     DisplayString (SIZE(0..31))
    MAX-ACCESS read-write
    STATUS     current
    DESCRIPTION
            ""
    ::= { hmSetupWlanMngmtApConfNetwprofilsEntry 2 }

-- {COLUMN} 1.3.6.1.4.1.248.32.18.2.37.1.1.1.3
hmSetupWlanMngmtApConfNetwprofilsEntryLocVal OBJECT-TYPE
    SYNTAX     DisplayString (SIZE(0..12))
    MAX-ACCESS read-write
    STATUS     current
    DESCRIPTION
            "local values"
    ::= { hmSetupWlanMngmtApConfNetwprofilsEntry 3 }

-- {COLUMN} 1.3.6.1.4.1.248.32.18.2.37.1.1.1.4
hmSetupWlanMngmtApConfNetwprofilsEntryOperating OBJECT-TYPE
    SYNTAX     INTEGER {
                  eYes (0),
                  eNo (1)
            }
    MAX-ACCESS read-write
    STATUS     current
    DESCRIPTION
            "-- empty --"
    ::= { hmSetupWlanMngmtApConfNetwprofilsEntry 4 }

-- {COLUMN} 1.3.6.1.4.1.248.32.18.2.37.1.1.1.5
hmSetupWlanMngmtApConfNetwprofilsEntryVlanId OBJECT-TYPE
    SYNTAX     Integer32 (0..65535)
    MAX-ACCESS read-write
    STATUS     obsolete
    DESCRIPTION
            ""
    ::= { hmSetupWlanMngmtApConfNetwprofilsEntry 5 }

-- {COLUMN} 1.3.6.1.4.1.248.32.18.2.37.1.1.1.6
hmSetupWlanMngmtApConfNetwprofilsEntryEncryption OBJECT-TYPE
    SYNTAX     INTEGER {
                  e80211iWpaPsk (0),
                  e80211iWpa8021x (1),
                  eWep104Bits (2),
                  eWep40Bits (3),
                  eWep104Bits8021x (4),
                  eWep40Bits8021x (5),
                  eNone (6)
            }
    MAX-ACCESS read-write
    STATUS     current
    DESCRIPTION
            "-- empty --"
    ::= { hmSetupWlanMngmtApConfNetwprofilsEntry 6 }

-- {COLUMN} 1.3.6.1.4.1.248.32.18.2.37.1.1.1.7
hmSetupWlanMngmtApConfNetwprofilsEntryWpa1SessionKeytypes OBJECT-TYPE
    SYNTAX     INTEGER {
                  eTkipAes (0),
                  eAes (1),
                  eTkip (2)
            }
    MAX-ACCESS read-write
    STATUS     current
    DESCRIPTION
            "-- empty --"
    ::= { hmSetupWlanMngmtApConfNetwprofilsEntry 7 }

-- {COLUMN} 1.3.6.1.4.1.248.32.18.2.37.1.1.1.8
hmSetupWlanMngmtApConfNetwprofilsEntryWpaVersion OBJECT-TYPE
    SYNTAX     INTEGER {
                  eWpa12 (0),
                  eWpa1 (1),
                  eWpa2 (2)
            }
    MAX-ACCESS read-write
    STATUS     current
    DESCRIPTION
            "-- empty --"
    ::= { hmSetupWlanMngmtApConfNetwprofilsEntry 8 }

-- {COLUMN} 1.3.6.1.4.1.248.32.18.2.37.1.1.1.9
hmSetupWlanMngmtApConfNetwprofilsEntryKey OBJECT-TYPE
    SYNTAX     DisplayString (SIZE(0..63))
    MAX-ACCESS read-write
    STATUS     current
    DESCRIPTION
            "-- empty --"
    ::= { hmSetupWlanMngmtApConfNetwprofilsEntry 9 }

-- {COLUMN} 1.3.6.1.4.1.248.32.18.2.37.1.1.1.10
hmSetupWlanMngmtApConfNetwprofilsEntryRadioBand OBJECT-TYPE
    SYNTAX     INTEGER {
                  e24ghz5ghz (0),
                  e24ghz (1),
                  e5ghz (2)
            }
    MAX-ACCESS read-write
    STATUS     current
    DESCRIPTION
            "-- empty --"
    ::= { hmSetupWlanMngmtApConfNetwprofilsEntry 10 }

-- {COLUMN} 1.3.6.1.4.1.248.32.18.2.37.1.1.1.11
hmSetupWlanMngmtApConfNetwprofilsEntryContinuation OBJECT-TYPE
    SYNTAX     Integer32 (0..65535)
    MAX-ACCESS read-write
    STATUS     current
    DESCRIPTION
            ""
    ::= { hmSetupWlanMngmtApConfNetwprofilsEntry 11 }

-- {COLUMN} 1.3.6.1.4.1.248.32.18.2.37.1.1.1.12
hmSetupWlanMngmtApConfNetwprofilsEntryMinTxRate OBJECT-TYPE
    SYNTAX     INTEGER {
                  eAuto (0),
                  e1M (1),
                  e2M (2),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-write
    STATUS     current
    DESCRIPTION
            "-- empty --"
    ::= { hmSetupWlanMngmtApConfNetwprofilsEntry 12 }

-- {COLUMN} 1.3.6.1.4.1.248.32.18.2.37.1.1.1.13
hmSetupWlanMngmtApConfNetwprofilsEntryMaxTxRate OBJECT-TYPE
    SYNTAX     INTEGER {
                  eAuto (0),
                  e1M (1),
                  e2M (2),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-write
    STATUS     current
    DESCRIPTION
            "-- empty --"
    ::= { hmSetupWlanMngmtApConfNetwprofilsEntry 13 }

-- {COLUMN} 1.3.6.1.4.1.248.32.18.2.37.1.1.1.14
hmSetupWlanMngmtApConfNetwprofilsEntryBasicRate OBJECT-TYPE
    SYNTAX     INTEGER {
                  e2M (0),
                  e1M (1),
                  e5M5 (3),
                  e11M (4),
                  e6M (5),
                  e9M (6),
                  e12M (7),
                  e18M (8),
                  e24M (9),
                  e36M (10),
                  e48M (11),
                  e54M (12),
                  eT72M (13),
                  eT96M (14),
                  eT108M (15)
            }
    MAX-ACCESS read-write
    STATUS     current
    DESCRIPTION
            "-- empty --"
    ::= { hmSetupWlanMngmtApConfNetwprofilsEntry 14 }

-- {COLUMN} 1.3.6.1.4.1.248.32.18.2.37.1.1.1.15
hmSetupWlanMngmtApConfNetwprofilsEntry11bPreamble OBJECT-TYPE
    SYNTAX     INTEGER {
                  eAuto (0),
                  eLong (1)
            }
    MAX-ACCESS read-write
    STATUS     current
    DESCRIPTION
            "-- empty --"
    ::= { hmSetupWlanMngmtApConfNetwprofilsEntry 15 }

-- {COLUMN} 1.3.6.1.4.1.248.32.18.2.37.1.1.1.16
hmSetupWlanMngmtApConfNetwprofilsEntryMacFilter OBJECT-TYPE
    SYNTAX     INTEGER {
                  eNo (0),
                  eYes (1)
            }
    MAX-ACCESS read-write
    STATUS     current
    DESCRIPTION
            "-- empty --"
    ::= { hmSetupWlanMngmtApConfNetwprofilsEntry 16 }

-- {COLUMN} 1.3.6.1.4.1.248.32.18.2.37.1.1.1.17
hmSetupWlanMngmtApConfNetwprofilsEntryClBrgSupport OBJECT-TYPE
    SYNTAX     INTEGER {
                  eNo (0),
                  eYes (1),
                  eExclusive (2)
            }
    MAX-ACCESS read-write
    STATUS     current
    DESCRIPTION
            "-- empty --"
    ::= { hmSetupWlanMngmtApConfNetwprofilsEntry 17 }

-- {COLUMN} 1.3.6.1.4.1.248.32.18.2.37.1.1.1.18
hmSetupWlanMngmtApConfNetwprofilsEntryMaxStations OBJECT-TYPE
    SYNTAX     Integer32 (0..65535)
    MAX-ACCESS read-write
    STATUS     current
    DESCRIPTION
            "-- empty --"
    ::= { hmSetupWlanMngmtApConfNetwprofilsEntry 18 }

-- {COLUMN} 1.3.6.1.4.1.248.32.18.2.37.1.1.1.19
hmSetupWlanMngmtApConfNetwprofilsEntrySsidBroadcast OBJECT-TYPE
    SYNTAX     INTEGER {
                  eYes (0),
                  eNo (1),
                  eTightened (2)
            }
    MAX-ACCESS read-write
    STATUS     current
    DESCRIPTION
            "-- empty --"
    ::= { hmSetupWlanMngmtApConfNetwprofilsEntry 19 }

-- {COLUMN} 1.3.6.1.4.1.248.32.18.2.37.1.1.1.21
hmSetupWlanMngmtApConfNetwprofilsEntrySsid OBJECT-TYPE
    SYNTAX     DisplayString (SIZE(0..32))
    MAX-ACCESS read-write
    STATUS     current
    DESCRIPTION
            "-- empty --"
    ::= { hmSetupWlanMngmtApConfNetwprofilsEntry 21 }

-- {COLUMN} 1.3.6.1.4.1.248.32.18.2.37.1.1.1.22
hmSetupWlanMngmtApConfNetwprofilsEntryMinHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-write
    STATUS     current
    DESCRIPTION
            "-- empty --"
    ::= { hmSetupWlanMngmtApConfNetwprofilsEntry 22 }

-- {COLUMN} 1.3.6.1.4.1.248.32.18.2.37.1.1.1.23
hmSetupWlanMngmtApConfNetwprofilsEntryMaxHtMcs OBJECT-TYPE
    SYNTAX     INTEGER {
                  eAuto (0),
                  eMcs08 (1),
                  eMcs19 (2),
                  eMcs210 (3),
                  eMcs311 (4),
                  eMcs412 (5),
                  eMcs513 (6),
                  eMcs614 (7),
                  eMcs715 (8)
            }
    MAX-ACCESS read-write
    STATUS     current
    DESCRIPTION
            "-- empty --"
    ::= { hmSetupWlanMngmtApConfNetwprofilsEntry 23 }

-- {COLUMN} 1.3.6.1.4.1.248.32.18.2.37.1.1.1.24
hmSetupWlanMngmtApConfNetwprofilsEntryShortGuardInterval OBJECT-TYPE
    SYNTAX     INTEGER {
                  eAuto (0),
                  eNo (1)
            }
    MAX-ACCESS read-write
    STATUS     current
    DESCRIPTION
            "-- empty --"
    ::= { hmSetupWlanMngmtApConfNetwprofilsEntry 24 }

-- {COLUMN} 1.3.6.1.4.1.248.32.18.2.37.1.1.1.25
hmSetupWlanMngmtApConfNetwprofilsEntryMaxSpatialStreams OBJECT-TYPE
    SYNTAX     INTEGER {
                  eAuto (0),
                  eOne (1),
                  eTwo (2)
            }
    MAX-ACCESS read-write
    STATUS     current
    DESCRIPTION
            "-- empty --"
    ::= { hmSetupWlanMngmtApConfNetwprofilsEntry 25 }

-- {COLUMN} 1.3.6.1.4.1.248.32.18.2.37.1.1.1.26
hmSetupWlanMngmtApConfNetwprofilsEntrySendAggregates OBJECT-TYPE
    SYNTAX     INTEGER {
                  eNo (0),
                  eYes (1)
            }
    MAX-ACCESS read-write
    STATUS     current
    DESCRIPTION
            "-- empty --"
    ::= { hmSetupWlanMngmtApConfNetwprofilsEntry 26 }

-- {COLUMN} 1.3.6.1.4.1.248.32.18.2.37.1.1.1.27
hmSetupWlanMngmtApConfNetwprofilsEntryWpa2SessionKeytypes OBJECT-TYPE
    SYNTAX     INTEGER {
                  eTkipAes (0),
                  eAes (1),
                  eTkip (2)
            }
    MAX-ACCESS read-write
    STATUS     current
    DESCRIPTION
            "-- empty --"
    ::= { hmSetupWlanMngmtApConfNetwprofilsEntry 27 }

-- {COLUMN} 1.3.6.1.4.1.248.32.18.2.37.1.1.1.28
hmSetupWlanMngmtApConfNetwprofilsEntryRadiusAccounting OBJECT-TYPE
    SYNTAX     INTEGER {
                  eNo (0),
                  eYes (1)
            }
    MAX-ACCESS read-write
    STATUS     current
    DESCRIPTION
            "-- empty --"
    ::= { hmSetupWlanMngmtApConfNetwprofilsEntry 28 }

-- {COLUMN} 1.3.6.1.4.1.248.32.18.2.37.1.1.1.30
hmSetupWlanMngmtApConfNetwprofilsEntryVlanMode OBJECT-TYPE
    SYNTAX     INTEGER {
                  eUntagged (0),
                  eTagged (1)
            }
    MAX-ACCESS read-write
    STATUS     current
    DESCRIPTION
            "-- empty --"
    ::= { hmSetupWlanMngmtApConfNetwprofilsEntry 30 }

-- {COLUMN} 1.3.6.1.4.1.248.32.18.2.37.1.1.1.32
hmSetupWlanMngmtApConfNetwprofilsEntryConnectSsidTo OBJECT-TYPE
    SYNTAX     INTEGER {
                  eLan (0),
                  eWlcTunnel1 (1),
                  eWlcTunnel2 (2),
                  eWlcTunnel3 (3),
                  eWlcTunnel4 (4),
                  eWlcTunnel5 (5),
                  eWlcTunnel6 (6),
                  eWlcTunnel7 (7),
                  eWlcTunnel8 (8),
                  eWlcTunnel9 (9),
                  eWlcTunnel10 (10),
                  eWlcTunnel11 (11),
                  eWlcTunnel12 (12),
                  eWlcTunnel13 (13),
                  eWlcTunnel14 (14),
                  eWlcTunnel15 (15),
                  eWlcTunnel16 (16),
                  eWlcTunnel17 (17),
                  eWlcTunnel18 (18),
                  eWlcTunnel19 (19),
                  eWlcTunnel20 (20),
                  eWlcTunnel21 (21),
                  eWlcTunnel22 (22),
                  eWlcTunnel23 (23),
                  eWlcTunnel24 (24),
                  eWlcTunnel25 (25),
                  eWlcTunnel26 (26),
                  eWlcTunnel27 (27),
                  eWlcTunnel28 (28),
                  eWlcTunnel29 (29),
                  eWlcTunnel30 (30),
                  eWlcTunnel31 (31),
                  eWlcTunnel32 (32),
                  eWlcTunnelAutowds (33)
            }
    MAX-ACCESS read-write
    STATUS     current
    DESCRIPTION
            "-- empty --"
    ::= { hmSetupWlanMngmtApConfNetwprofilsEntry 32 }

-- {COLUMN} 1.3.6.1.4.1.248.32.18.2.37.1.1.1.33
hmSetupWlanMngmtApConfNetwprofilsEntryInterStationTraffic OBJECT-TYPE
    SYNTAX     INTEGER {
                  eNo (0),
                  eYes (1)
            }
    MAX-ACCESS read-write
    STATUS     current
    DESCRIPTION
            "-- empty --"
    ::= { hmSetupWlanMngmtApConfNetwprofilsEntry 33 }

-- {COLUMN} 1.3.6.1.4.1.248.32.18.2.37.1.1.1.34
hmSetupWlanMngmtApConfNetwprofilsEntryVlanIdnew OBJECT-TYPE
    SYNTAX     Integer32 (0..65535)
    MAX-ACCESS read-write
    STATUS     current
    DESCRIPTION
            ""
    ::= { hmSetupWlanMngmtApConfNetwprofilsEntry 34 }

-- {COLUMN} 1.3.6.1.4.1.248.32.18.2.37.1.1.1.35
hmSetupWlanMngmtApConfNetwprofilsEntryRadiusProfile OBJECT-TYPE
    SYNTAX     DisplayString (SIZE(0..16))
    MAX-ACCESS read-write
    STATUS     current
    DESCRIPTION
            "-- empty --"
    ::= { hmSetupWlanMngmtApConfNetwprofilsEntry 35 }

-- {COLUMN} 1.3.6.1.4.1.248.32.18.2.37.1.1.1.36
hmSetupWlanMngmtApConfNetwprofilsEntryStbcActivated OBJECT-TYPE
    SYNTAX     INTEGER {
                  eNo (0),
                  eYes (1)
            }
    MAX-ACCESS read-write
    STATUS     current
    DESCRIPTION
            "-- empty --"
    ::= { hmSetupWlanMngmtApConfNetwprofilsEntry 36 }

-- {COLUMN} 1.3.6.1.4.1.248.32.18.2.37.1.1.1.37
hmSetupWlanMngmtApConfNetwprofilsEntryLdpcActivated OBJECT-TYPE
    SYNTAX     INTEGER {
                  eNo (0),
                  eYes (1)
            }
    MAX-ACCESS read-write
    STATUS     current
    DESCRIPTION
            "-- empty --"
    ::= { hmSetupWlanMngmtApConfNetwprofilsEntry 37 }

-- {COLUMN} 1.3.6.1.4.1.248.32.18.2.37.1.1.1.38
hmSetupWlanMngmtApConfNetwprofilsEntryMinClientStrength OBJECT-TYPE
    SYNTAX     Integer32 (0..255)
    MAX-ACCESS read-write
    STATUS     current
    DESCRIPTION
            "-- empty --"
    ::= { hmSetupWlanMngmtApConfNetwprofilsEntry 38 }

-- {COLUMN} 1.3.6.1.4.1.248.32.18.2.37.1.1.1.39
hmSetupWlanMngmtApConfNetwprofilsEntryIeee80211uNetworkProfile OBJECT-TYPE
    SYNTAX     DisplayString (SIZE(0..32))
    MAX-ACCESS read-write
    STATUS     current
    DESCRIPTION
            "-- empty --"
    ::= { hmSetupWlanMngmtApConfNetwprofilsEntry 39 }

-- {COLUMN} 1.3.6.1.4.1.248.32.18.2.37.1.1.1.40
hmSetupWlanMngmtApConfNetwprofilsEntryOkc OBJECT-TYPE
    SYNTAX     INTEGER {
                  eNo (0),
                  eYes (1)
            }
    MAX-ACCESS read-write
    STATUS     current
    DESCRIPTION
            "-- empty --"
    ::= { hmSetupWlanMngmtApConfNetwprofilsEntry 40 }

-- {COLUMN} 1.3.6.1.4.1.248.32.18.2.37.1.1.1.41
hmSetupWlanMngmtApConfNetwprofilsEntryWpa2KeyManagement OBJECT-TYPE
    SYNTAX     BITS {
                  eSha256 (5),
                  eFastRoaming (6),
                  eStandard (7)
            }
    MAX-ACCESS read-write
    STATUS     current
    DESCRIPTION
            "-- empty --"
    ::= { hmSetupWlanMngmtApConfNetwprofilsEntry 41 }

-- {COLUMN} 1.3.6.1.4.1.248.32.18.2.37.1.1.1.42
hmSetupWlanMngmtApConfNetwprofilsEntryApsd OBJECT-TYPE
    SYNTAX     INTEGER {
                  eNo (0),
                  eYes (1)
            }
    MAX-ACCESS read-write
    STATUS     current
    DESCRIPTION
            "-- empty --"
    ::= { hmSetupWlanMngmtApConfNetwprofilsEntry 42 }

-- {COLUMN} 1.3.6.1.4.1.248.32.18.2.37.1.1.1.43
hmSetupWlanMngmtApConfNetwprofilsEntryProtMgmtFrames OBJECT-TYPE
    SYNTAX     INTEGER {
                  eNo (0),
                  eOptional (1),
                  eMandatory (2)
            }
    MAX-ACCESS read-write
    STATUS     current
    DESCRIPTION
            "-- empty --"
    ::= { hmSetupWlanMngmtApConfNetwprofilsEntry 43 }

-- {COLUMN} 1.3.6.1.4.1.248.32.18.2.37.1.1.1.44
hmSetupWlanMngmtApConfNetwprofilsEntryTxLimit OBJECT-TYPE
    SYNTAX     Integer32 (0..2147483647)
    MAX-ACCESS read-write
    STATUS     current
    DESCRIPTION
            "-- empty --"
    ::= { hmSetupWlanMngmtApConfNetwprofilsEntry 44 }

-- {COLUMN} 1.3.6.1.4.1.248.32.18.2.37.1.1.1.45
hmSetupWlanMngmtApConfNetwprofilsEntryRxLimit OBJECT-TYPE
    SYNTAX     Integer32 (0..2147483647)
    MAX-ACCESS read-write
    STATUS     current
    DESCRIPTION
            "-- empty --"
    ::= { hmSetupWlanMngmtApConfNetwprofilsEntry 45 }

-- {COLUMN} 1.3.6.1.4.1.248.32.18.2.37.1.1.1.46
hmSetupWlanMngmtApConfNetwprofilsEntryLbsTracking OBJECT-TYPE
    SYNTAX     INTEGER {
                  eNo (0),
                  eYes (1)
            }
    MAX-ACCESS read-write
    STATUS     current
    DESCRIPTION
            "-- empty --"
    ::= { hmSetupWlanMngmtApConfNetwprofilsEntry 46 }

-- {COLUMN} 1.3.6.1.4.1.248.32.18.2.37.1.1.1.47
hmSetupWlanMngmtApConfNetwprofilsEntryLbsTrackingList OBJECT-TYPE
    SYNTAX     DisplayString (SIZE(0..32))
    MAX-ACCESS read-write
    STATUS     current
    DESCRIPTION
            "-- empty --"
    ::= { hmSetupWlanMngmtApConfNetwprofilsEntry 47 }

-- {COLUMN} 1.3.6.1.4.1.248.32.18.2.37.1.1.1.48
hmSetupWlanMngmtApConfNetwprofilsEntryClBrgRoamingSupport OBJECT-TYPE
    SYNTAX     INTEGER {
                  eNo (0),
                  eYes (1)
            }
    MAX-ACCESS read-write
    STATUS     current
    DESCRIPTION
            "-- empty --"
    ::= { hmSetupWlanMngmtApConfNetwprofilsEntry 48 }

-- {TABLE} 1.3.6.1.4.1.248.32.18.2.37.1.2
hmSetupWlanMngmtApConfRadioprofilsTable OBJECT-TYPE
    SYNTAX     SEQUENCE OF HmSetupWlanMngmtApConfRadioprofilsEntry
    MAX-ACCESS not-accessible
    STATUS     current
    DESCRIPTION
            ""
    ::= { hmSetupWlanMngmtApConf 2 }

-- {ROW} 1.3.6.1.4.1.248.32.18.2.37.1.2.1
hmSetupWlanMngmtApConfRadioprofilsEntry OBJECT-TYPE
    SYNTAX     HmSetupWlanMngmtApConfRadioprofilsEntry
    MAX-ACCESS not-accessible
    STATUS     current
    DESCRIPTION
            ""
    INDEX {
            hmSetupWlanMngmtApConfRadioprofilsEntryName
          }
    ::= { hmSetupWlanMngmtApConfRadioprofilsTable 1 }

HmSetupWlanMngmtApConfRadioprofilsEntry ::= SEQUENCE {
            hmSetupWlanMngmtApConfRadioprofilsEntryName DisplayString,
            hmSetupWlanMngmtApConfRadioprofilsEntryParentName DisplayString,
            hmSetupWlanMngmtApConfRadioprofilsEntryLocVal DisplayString,
            hmSetupWlanMngmtApConfRadioprofilsEntryCountry INTEGER,
            hmSetupWlanMngmtApConfRadioprofilsEntryChannelList DisplayString,
            hmSetupWlanMngmtApConfRadioprofilsEntry24ghzMode INTEGER,
            hmSetupWlanMngmtApConfRadioprofilsEntry5ghzMode INTEGER,
            hmSetupWlanMngmtApConfRadioprofilsEntrySubbands INTEGER,
            hmSetupWlanMngmtApConfRadioprofilsEntryQos INTEGER,
            hmSetupWlanMngmtApConfRadioprofilsEntryDtimPeriod Integer32,
            hmSetupWlanMngmtApConfRadioprofilsEntryBackgroundScan Integer32,
            hmSetupWlanMngmtApConfRadioprofilsEntryAntennaGain Integer32,
            hmSetupWlanMngmtApConfRadioprofilsEntryTxPowerReduction Integer32,
            hmSetupWlanMngmtApConfRadioprofilsEntryMgmtVLANId Integer32,
            hmSetupWlanMngmtApConfRadioprofilsEntryIndoorOnlyOperation INTEGER,
            hmSetupWlanMngmtApConfRadioprofilsEntryActVlanModOfMngdAps INTEGER,
            hmSetupWlanMngmtApConfRadioprofilsEntryMgmtVlanMode INTEGER,
            hmSetupWlanMngmtApConfRadioprofilsEntryMgmtVLANIdnew Integer32,
            hmSetupWlanMngmtApConfRadioprofilsEntryReportSeenClients INTEGER,
            hmSetupWlanMngmtApConfRadioprofilsEntryClientSteering INTEGER,
            hmSetupWlanMngmtApConfRadioprofilsEntryPreferredBand INTEGER,
            hmSetupWlanMngmtApConfRadioprofilsEntryPrReqAgeO Integer32
    }

-- {COLUMN} 1.3.6.1.4.1.248.32.18.2.37.1.2.1.1
hmSetupWlanMngmtApConfRadioprofilsEntryName OBJECT-TYPE
    SYNTAX     DisplayString (SIZE(0..31))
    MAX-ACCESS read-write
    STATUS     current
    DESCRIPTION
            "-- empty --"
    ::= { hmSetupWlanMngmtApConfRadioprofilsEntry 1 }

-- {COLUMN} 1.3.6.1.4.1.248.32.18.2.37.1.2.1.2
hmSetupWlanMngmtApConfRadioprofilsEntryParentName OBJECT-TYPE
    SYNTAX     DisplayString (SIZE(0..31))
    MAX-ACCESS read-write
    STATUS     current
    DESCRIPTION
            ""
    ::= { hmSetupWlanMngmtApConfRadioprofilsEntry 2 }

-- {COLUMN} 1.3.6.1.4.1.248.32.18.2.37.1.2.1.3
hmSetupWlanMngmtApConfRadioprofilsEntryLocVal OBJECT-TYPE
    SYNTAX     DisplayString (SIZE(0..6))
    MAX-ACCESS read-write
    STATUS     current
    DESCRIPTION
            "local values"
    ::= { hmSetupWlanMngmtApConfRadioprofilsEntry 3 }

-- {COLUMN} 1.3.6.1.4.1.248.32.18.2.37.1.2.1.4
hmSetupWlanMngmtApConfRadioprofilsEntryCountry OBJECT-TYPE
    SYNTAX     INTEGER {
                  eDefault (0),
                  eAlbania (8),
                  eAlgeria (12),
                  eArgentina (32),
                  eAustralia (36),
                  eAustria (40),
                  eBahrain (48),
                  eBangladesh (50),
                  eBelgium (56),
                  eBosniaHerzegovina (70),
                  eBrazil (76),
                  eBruneiDarussalam (96),
                  eBulgaria (100),
                  eBelarus (112),
                  eCanada (124),
                  eChile (152),
                  eChina (156),
                  eTaiwan (158),
                  eColombia (170),
                  eCostaRica (188),
                  eCroatia (191),
                  eCyprus (196),
                  eCzech (203),
                  eDenmark (208),
                  eEcuador (218),
                  eEstonia (233),
                  eFinland (246),
                  eFrance (250),
                  eGermany (276),
                  eGhana (288),
                  eGreece (300),
                  eGuatemala (320),
                  eHonduras (340),
                  eHongKong (344),
                  eHungary (348),
                  eIceland (352),
                  eIndia (356),
                  eIndonesia (360),
                  eIreland (372),
                  eIsrael (376),
                  eItaly (380),
                  eJapan (392),
                  eJordan (400),
                  eSouthKorea (410),
                  eKuwait (414),
                  eLebanon (422),
                  eLatvia (428),
                  eLiechtenstein (438),
                  eLithuania (440),
                  eLuxembourg (442),
                  eMacau (446),
                  eMalaysia (458),
                  eMalta (470),
                  eMexico (484),
                  eMoldavia (498),
                  eMorocco (504),
                  eOman (512),
                  eNetherlands (528),
                  eNewZealand (554),
                  eNicaragua (558),
                  eNorway (578),
                  ePakistan (586),
                  ePanama (591),
                  eParaguay (600),
                  ePeru (604),
                  ePhilippines (608),
                  ePoland (616),
                  ePortugal (620),
                  ePuertoRico (630),
                  eQatar (634),
                  eRomania (642),
                  eRussia (643),
                  eSaudiArabia (682),
                  eSingapore (702),
                  eSlovak (703),
                  eSlovenia (705),
                  eSouthAfrica (710),
                  eSpain (724),
                  eSweden (752),
                  eSwitzerland (756),
                  eThailand (764),
                  eUnitedArabEmirates (784),
                  eTunisia (788),
                  eTurkey (792),
                  eUganda (800),
                  eUkraine (804),
                  eMacedonia (807),
                  eEgypt (818),
                  eUnitedKingdom (826),
                  eTanzania (834),
                  eUnitedStatesFcc (840),
                  eUruguay (858),
                  eVenezuela (862),
                  eEurope (998),
                  eEgalistan (999)
            }
    MAX-ACCESS read-write
    STATUS     current
    DESCRIPTION
            "-- empty --"
    ::= { hmSetupWlanMngmtApConfRadioprofilsEntry 4 }

-- {COLUMN} 1.3.6.1.4.1.248.32.18.2.37.1.2.1.5
hmSetupWlanMngmtApConfRadioprofilsEntryChannelList OBJECT-TYPE
    SYNTAX     DisplayString (SIZE(0..48))
    MAX-ACCESS read-write
    STATUS     current
    DESCRIPTION
            "-- empty --"
    ::= { hmSetupWlanMngmtApConfRadioprofilsEntry 5 }

-- {COLUMN} 1.3.6.1.4.1.248.32.18.2.37.1.2.1.6
hmSetupWlanMngmtApConfRadioprofilsEntry24ghzMode OBJECT-TYPE
    SYNTAX     INTEGER {
                  e11bgMixed (0),
                  e11gOnly (1),
                  e11bOnly (2),
                  e108mbps (3),
                  e11bgnMixed (4),
                  e11gnMixed (5),
                  eGreenfield (6),
                  eAuto (255)
            }
    MAX-ACCESS read-write
    STATUS     current
    DESCRIPTION
            "-- empty --"
    ::= { hmSetupWlanMngmtApConfRadioprofilsEntry 6 }

-- {COLUMN} 1.3.6.1.4.1.248.32.18.2.37.1.2.1.7
hmSetupWlanMngmtApConfRadioprofilsEntry5ghzMode OBJECT-TYPE
    SYNTAX     INTEGER {
                  eNormal (0),
                  e108mbps (3),
                  e11anMixed (4),
                  eGreenfield (5),
                  e11anacMixed (6),
                  e11nacMixed (7),
                  e11acOnly (8),
                  eAuto (255)
            }
    MAX-ACCESS read-write
    STATUS     current
    DESCRIPTION
            "-- empty --"
    ::= { hmSetupWlanMngmtApConfRadioprofilsEntry 7 }

-- {COLUMN} 1.3.6.1.4.1.248.32.18.2.37.1.2.1.8
hmSetupWlanMngmtApConfRadioprofilsEntrySubbands OBJECT-TYPE
    SYNTAX     INTEGER {
                  eBand1Plus2Plus3 (0),
                  eBand1 (1),
                  eBand2 (2),
                  eBand3 (3),
                  eBand1Plus2 (4),
                  eBand1Plus3 (5),
                  eBand2Plus3 (6)
            }
    MAX-ACCESS read-write
    STATUS     current
    DESCRIPTION
            "-- empty --"
    ::= { hmSetupWlanMngmtApConfRadioprofilsEntry 8 }

-- {COLUMN} 1.3.6.1.4.1.248.32.18.2.37.1.2.1.9
hmSetupWlanMngmtApConfRadioprofilsEntryQos OBJECT-TYPE
    SYNTAX     INTEGER {
                  eNo (0),
                  eYes (1)
            }
    MAX-ACCESS read-write
    STATUS     current
    DESCRIPTION
            "-- empty --"
    ::= { hmSetupWlanMngmtApConfRadioprofilsEntry 9 }

-- {COLUMN} 1.3.6.1.4.1.248.32.18.2.37.1.2.1.10
hmSetupWlanMngmtApConfRadioprofilsEntryDtimPeriod OBJECT-TYPE
    SYNTAX     Integer32 (0..255)
    MAX-ACCESS read-write
    STATUS     current
    DESCRIPTION
            "-- empty --"
    ::= { hmSetupWlanMngmtApConfRadioprofilsEntry 10 }

-- {COLUMN} 1.3.6.1.4.1.248.32.18.2.37.1.2.1.11
hmSetupWlanMngmtApConfRadioprofilsEntryBackgroundScan OBJECT-TYPE
    SYNTAX     Integer32 (0..2147483647)
    MAX-ACCESS read-write
    STATUS     current
    DESCRIPTION
            "-- empty --"
    ::= { hmSetupWlanMngmtApConfRadioprofilsEntry 11 }

-- {COLUMN} 1.3.6.1.4.1.248.32.18.2.37.1.2.1.12
hmSetupWlanMngmtApConfRadioprofilsEntryAntennaGain OBJECT-TYPE
    SYNTAX     Integer32 (-128..127)
    MAX-ACCESS read-write
    STATUS     current
    DESCRIPTION
            "-- empty --"
    ::= { hmSetupWlanMngmtApConfRadioprofilsEntry 12 }

-- {COLUMN} 1.3.6.1.4.1.248.32.18.2.37.1.2.1.13
hmSetupWlanMngmtApConfRadioprofilsEntryTxPowerReduction OBJECT-TYPE
    SYNTAX     Integer32 (0..255)
    MAX-ACCESS read-write
    STATUS     current
    DESCRIPTION
            "-- empty --"
    ::= { hmSetupWlanMngmtApConfRadioprofilsEntry 13 }

-- {COLUMN} 1.3.6.1.4.1.248.32.18.2.37.1.2.1.14
hmSetupWlanMngmtApConfRadioprofilsEntryMgmtVLANId OBJECT-TYPE
    SYNTAX     Integer32 (0..65535)
    MAX-ACCESS read-write
    STATUS     obsolete
    DESCRIPTION
            ""
    ::= { hmSetupWlanMngmtApConfRadioprofilsEntry 14 }

-- {COLUMN} 1.3.6.1.4.1.248.32.18.2.37.1.2.1.16
hmSetupWlanMngmtApConfRadioprofilsEntryIndoorOnlyOperation OBJECT-TYPE
    SYNTAX     INTEGER {
                  eNo (0),
                  eYes (1)
            }
    MAX-ACCESS read-write
    STATUS     current
    DESCRIPTION
            "-- empty --"
    ::= { hmSetupWlanMngmtApConfRadioprofilsEntry 16 }

-- {COLUMN} 1.3.6.1.4.1.248.32.18.2.37.1.2.1.17
hmSetupWlanMngmtApConfRadioprofilsEntryActVlanModOfMngdAps OBJECT-TYPE
    SYNTAX     INTEGER {
                  eNo (0),
                  eYes (1)
            }
    MAX-ACCESS read-write
    STATUS     current
    DESCRIPTION
            ""
    ::= { hmSetupWlanMngmtApConfRadioprofilsEntry 17 }

-- {COLUMN} 1.3.6.1.4.1.248.32.18.2.37.1.2.1.18
hmSetupWlanMngmtApConfRadioprofilsEntryMgmtVlanMode OBJECT-TYPE
    SYNTAX     INTEGER {
                  eUntagged (0),
                  eTagged (1)
            }
    MAX-ACCESS read-write
    STATUS     current
    DESCRIPTION
            "-- empty --"
    ::= { hmSetupWlanMngmtApConfRadioprofilsEntry 18 }

-- {COLUMN} 1.3.6.1.4.1.248.32.18.2.37.1.2.1.19
hmSetupWlanMngmtApConfRadioprofilsEntryMgmtVLANIdnew OBJECT-TYPE
    SYNTAX     Integer32 (0..65535)
    MAX-ACCESS read-write
    STATUS     current
    DESCRIPTION
            ""
    ::= { hmSetupWlanMngmtApConfRadioprofilsEntry 19 }

-- {COLUMN} 1.3.6.1.4.1.248.32.18.2.37.1.2.1.20
hmSetupWlanMngmtApConfRadioprofilsEntryReportSeenClients OBJECT-TYPE
    SYNTAX     INTEGER {
                  eNo (0),
                  eYes (1)
            }
    MAX-ACCESS read-write
    STATUS     current
    DESCRIPTION
            "-- empty --"
    ::= { hmSetupWlanMngmtApConfRadioprofilsEntry 20 }

-- {COLUMN} 1.3.6.1.4.1.248.32.18.2.37.1.2.1.21
hmSetupWlanMngmtApConfRadioprofilsEntryClientSteering OBJECT-TYPE
    SYNTAX     INTEGER {
                  eOff (0),
                  eYes (1),
                  eOn (2)
            }
    MAX-ACCESS read-write
    STATUS     current
    DESCRIPTION
            "-- empty --"
    ::= { hmSetupWlanMngmtApConfRadioprofilsEntry 21 }

-- {COLUMN} 1.3.6.1.4.1.248.32.18.2.37.1.2.1.22
hmSetupWlanMngmtApConfRadioprofilsEntryPreferredBand OBJECT-TYPE
    SYNTAX     INTEGER {
                  e24ghz (1),
                  e5ghz (2)
            }
    MAX-ACCESS read-write
    STATUS     current
    DESCRIPTION
            "-- empty --"
    ::= { hmSetupWlanMngmtApConfRadioprofilsEntry 22 }

-- {COLUMN} 1.3.6.1.4.1.248.32.18.2.37.1.2.1.23
hmSetupWlanMngmtApConfRadioprofilsEntryPrReqAgeO OBJECT-TYPE
    SYNTAX     Integer32 (0..2147483647)
    MAX-ACCESS read-write
    STATUS     current
    DESCRIPTION
            ""
    ::= { hmSetupWlanMngmtApConfRadioprofilsEntry 23 }

-- {TABLE} 1.3.6.1.4.1.248.32.18.2.37.1.3
hmSetupWlanMngmtApConfCommonprofilsTable OBJECT-TYPE
    SYNTAX     SEQUENCE OF HmSetupWlanMngmtApConfCommonprofilsEntry
    MAX-ACCESS not-accessible
    STATUS     current
    DESCRIPTION
            ""
    ::= { hmSetupWlanMngmtApConf 3 }

-- {ROW} 1.3.6.1.4.1.248.32.18.2.37.1.3.1
hmSetupWlanMngmtApConfCommonprofilsEntry OBJECT-TYPE
    SYNTAX     HmSetupWlanMngmtApConfCommonprofilsEntry
    MAX-ACCESS not-accessible
    STATUS     current
    DESCRIPTION
            ""
    INDEX {
            hmSetupWlanMngmtApConfCommonprofilsEntryName
          }
    ::= { hmSetupWlanMngmtApConfCommonprofilsTable 1 }

HmSetupWlanMngmtApConfCommonprofilsEntry ::= SEQUENCE {
            hmSetupWlanMngmtApConfCommonprofilsEntryName DisplayString,
            hmSetupWlanMngmtApConfCommonprofilsEntryNetw DisplayString,
            hmSetupWlanMngmtApConfCommonprofilsEntryApParams DisplayString,
            hmSetupWlanMngmtApConfCommonprofilsEntryContr DisplayString,
            hmSetupWlanMngmtApConfCommonprofilsEntryIeee80211uGeneral DisplayString,
            hmSetupWlanMngmtApConfCommonprofilsEntryConfigurationDelay Integer32,
            hmSetupWlanMngmtApConfCommonprofilsEntryLedProfile DisplayString,
            hmSetupWlanMngmtApConfCommonprofilsEntryLbsGeneralProfile DisplayString,
            hmSetupWlanMngmtApConfCommonprofilsEntryWirelessEpaperProfile DisplayString,
            hmSetupWlanMngmtApConfCommonprofilsEntryWIds DisplayString
    }

-- {COLUMN} 1.3.6.1.4.1.248.32.18.2.37.1.3.1.1
hmSetupWlanMngmtApConfCommonprofilsEntryName OBJECT-TYPE
    SYNTAX     DisplayString (SIZE(0..31))
    MAX-ACCESS read-write
    STATUS     current
    DESCRIPTION
            "-- empty --"
    ::= { hmSetupWlanMngmtApConfCommonprofilsEntry 1 }

-- {COLUMN} 1.3.6.1.4.1.248.32.18.2.37.1.3.1.2
hmSetupWlanMngmtApConfCommonprofilsEntryNetw OBJECT-TYPE
    SYNTAX     DisplayString (SIZE(0..251))
    MAX-ACCESS read-write
    STATUS     current
    DESCRIPTION
            ""
    ::= { hmSetupWlanMngmtApConfCommonprofilsEntry 2 }

-- {COLUMN} 1.3.6.1.4.1.248.32.18.2.37.1.3.1.3
hmSetupWlanMngmtApConfCommonprofilsEntryApParams OBJECT-TYPE
    SYNTAX     DisplayString (SIZE(0..31))
    MAX-ACCESS read-write
    STATUS     current
    DESCRIPTION
            ""
    ::= { hmSetupWlanMngmtApConfCommonprofilsEntry 3 }

-- {COLUMN} 1.3.6.1.4.1.248.32.18.2.37.1.3.1.4
hmSetupWlanMngmtApConfCommonprofilsEntryContr OBJECT-TYPE
    SYNTAX     DisplayString (SIZE(0..159))
    MAX-ACCESS read-write
    STATUS     current
    DESCRIPTION
            ""
    ::= { hmSetupWlanMngmtApConfCommonprofilsEntry 4 }

-- {COLUMN} 1.3.6.1.4.1.248.32.18.2.37.1.3.1.6
hmSetupWlanMngmtApConfCommonprofilsEntryIeee80211uGeneral OBJECT-TYPE
    SYNTAX     DisplayString (SIZE(0..32))
    MAX-ACCESS read-write
    STATUS     current
    DESCRIPTION
            "-- empty --"
    ::= { hmSetupWlanMngmtApConfCommonprofilsEntry 6 }

-- {COLUMN} 1.3.6.1.4.1.248.32.18.2.37.1.3.1.7
hmSetupWlanMngmtApConfCommonprofilsEntryConfigurationDelay OBJECT-TYPE
    SYNTAX     Integer32 (0..2147483647)
    MAX-ACCESS read-write
    STATUS     current
    DESCRIPTION
            "-- empty --"
    ::= { hmSetupWlanMngmtApConfCommonprofilsEntry 7 }

-- {COLUMN} 1.3.6.1.4.1.248.32.18.2.37.1.3.1.8
hmSetupWlanMngmtApConfCommonprofilsEntryLedProfile OBJECT-TYPE
    SYNTAX     DisplayString (SIZE(0..31))
    MAX-ACCESS read-write
    STATUS     current
    DESCRIPTION
            "-- empty --"
    ::= { hmSetupWlanMngmtApConfCommonprofilsEntry 8 }

-- {COLUMN} 1.3.6.1.4.1.248.32.18.2.37.1.3.1.9
hmSetupWlanMngmtApConfCommonprofilsEntryLbsGeneralProfile OBJECT-TYPE
    SYNTAX     DisplayString (SIZE(0..32))
    MAX-ACCESS read-write
    STATUS     current
    DESCRIPTION
            "-- empty --"
    ::= { hmSetupWlanMngmtApConfCommonprofilsEntry 9 }

-- {COLUMN} 1.3.6.1.4.1.248.32.18.2.37.1.3.1.10
hmSetupWlanMngmtApConfCommonprofilsEntryWirelessEpaperProfile OBJECT-TYPE
    SYNTAX     DisplayString (SIZE(0..31))
    MAX-ACCESS read-write
    STATUS     current
    DESCRIPTION
            "-- empty --"
    ::= { hmSetupWlanMngmtApConfCommonprofilsEntry 10 }

-- {COLUMN} 1.3.6.1.4.1.248.32.18.2.37.1.3.1.248
hmSetupWlanMngmtApConfCommonprofilsEntryWIds OBJECT-TYPE
    SYNTAX     DisplayString (SIZE(0..32))
    MAX-ACCESS read-write
    STATUS     current
    DESCRIPTION
            ""
    ::= { hmSetupWlanMngmtApConfCommonprofilsEntry 248 }

-- {TABLE} 1.3.6.1.4.1.248.32.18.2.37.1.4
hmSetupWlanMngmtApConfApsTable OBJECT-TYPE
    SYNTAX     SEQUENCE OF HmSetupWlanMngmtApConfApsEntry
    MAX-ACCESS not-accessible
    STATUS     current
    DESCRIPTION
            "accesspoints"
    ::= { hmSetupWlanMngmtApConf 4 }

-- {ROW} 1.3.6.1.4.1.248.32.18.2.37.1.4.1
hmSetupWlanMngmtApConfApsEntry OBJECT-TYPE
    SYNTAX     HmSetupWlanMngmtApConfApsEntry
    MAX-ACCESS not-accessible
    STATUS     current
    DESCRIPTION
            ""
    INDEX {
            hmSetupWlanMngmtApConfApsEntryMacAddress
          }
    ::= { hmSetupWlanMngmtApConfApsTable 1 }

HmSetupWlanMngmtApConfApsEntry ::= SEQUENCE {
            hmSetupWlanMngmtApConfApsEntryMacAddress DisplayString,
            hmSetupWlanMngmtApConfApsEntryName DisplayString,
            hmSetupWlanMngmtApConfApsEntryLocation DisplayString,
            hmSetupWlanMngmtApConfApsEntryProfile DisplayString,
            hmSetupWlanMngmtApConfApsEntryDeviceParameters DisplayString,
            hmSetupWlanMngmtApConfApsEntryEncryption INTEGER,
            hmSetupWlanMngmtApConfApsEntryWlanModule1 INTEGER,
            hmSetupWlanMngmtApConfApsEntryWlanModule2 INTEGER,
            hmSetupWlanMngmtApConfApsEntryModule1ChannelList DisplayString,
            hmSetupWlanMngmtApConfApsEntryModule2ChannelList DisplayString,
            hmSetupWlanMngmtApConfApsEntryOperating INTEGER,
            hmSetupWlanMngmtApConfApsEntryIpAddress IpAddress,
            hmSetupWlanMngmtApConfApsEntryNetmask IpAddress,
            hmSetupWlanMngmtApConfApsEntryGateway IpAddress,
            hmSetupWlanMngmtApConfApsEntryAllow40mhz INTEGER,
            hmSetupWlanMngmtApConfApsEntryAntennaMask INTEGER,
            hmSetupWlanMngmtApConfApsEntryApIntranet DisplayString,
            hmSetupWlanMngmtApConfApsEntryManageFirmware INTEGER,
            hmSetupWlanMngmtApConfApsEntryMngmtFwAddInfo INTEGER,
            hmSetupWlanMngmtApConfApsEntryModule1AntGain DisplayString,
            hmSetupWlanMngmtApConfApsEntryModule2AntGain DisplayString,
            hmSetupWlanMngmtApConfApsEntryModule1TxReduct DisplayString,
            hmSetupWlanMngmtApConfApsEntryModule2TxReduct DisplayString,
            hmSetupWlanMngmtApConfApsEntryGroup DisplayString,
            hmSetupWlanMngmtApConfApsEntryModule2MaxChannelBandwidth INTEGER,
            hmSetupWlanMngmtApConfApsEntryModule1MaxChannelBandwidth INTEGER,
            hmSetupWlanMngmtApConfApsEntryClientSteeringProfile DisplayString,
            hmSetupWlanMngmtApConfApsEntryLbsDeviceLocationProfile DisplayString,
            hmSetupWlanMngmtApConfApsEntryWirelessEpaperChannel INTEGER,
            hmSetupWlanMngmtApConfApsEntryIbeaconProfile DisplayString,
            hmSetupWlanMngmtApConfApsEntryIbeaconChannel BITS,
            hmSetupWlanMngmtApConfApsEntryMinor Integer32,
            hmSetupWlanMngmtApConfApsEntryIbeaconTransmitPower INTEGER
    }

-- {COLUMN} 1.3.6.1.4.1.248.32.18.2.37.1.4.1.1
hmSetupWlanMngmtApConfApsEntryMacAddress OBJECT-TYPE
    SYNTAX     DisplayString (SIZE(0..12))
    MAX-ACCESS read-write
    STATUS     current
    DESCRIPTION
            "-- empty --"
    ::= { hmSetupWlanMngmtApConfApsEntry 1 }

-- {COLUMN} 1.3.6.1.4.1.248.32.18.2.37.1.4.1.2
hmSetupWlanMngmtApConfApsEntryName OBJECT-TYPE
    SYNTAX     DisplayString (SIZE(0..16))
    MAX-ACCESS read-write
    STATUS     current
    DESCRIPTION
            "-- empty --"
    ::= { hmSetupWlanMngmtApConfApsEntry 2 }

-- {COLUMN} 1.3.6.1.4.1.248.32.18.2.37.1.4.1.3
hmSetupWlanMngmtApConfApsEntryLocation OBJECT-TYPE
    SYNTAX     DisplayString (SIZE(0..251))
    MAX-ACCESS read-write
    STATUS     current
    DESCRIPTION
            "-- empty --"
    ::= { hmSetupWlanMngmtApConfApsEntry 3 }

-- {COLUMN} 1.3.6.1.4.1.248.32.18.2.37.1.4.1.4
hmSetupWlanMngmtApConfApsEntryProfile OBJECT-TYPE
    SYNTAX     DisplayString (SIZE(0..31))
    MAX-ACCESS read-write
    STATUS     current
    DESCRIPTION
            "-- empty --"
    ::= { hmSetupWlanMngmtApConfApsEntry 4 }

-- {COLUMN} 1.3.6.1.4.1.248.32.18.2.37.1.4.1.5
hmSetupWlanMngmtApConfApsEntryDeviceParameters OBJECT-TYPE
    SYNTAX     DisplayString (SIZE(0..31))
    MAX-ACCESS read-write
    STATUS     current
    DESCRIPTION
            "-- empty --"
    ::= { hmSetupWlanMngmtApConfApsEntry 5 }

-- {COLUMN} 1.3.6.1.4.1.248.32.18.2.37.1.4.1.6
hmSetupWlanMngmtApConfApsEntryEncryption OBJECT-TYPE
    SYNTAX     INTEGER {
                  eDefault (0),
                  eDtls (1),
                  eNo (2)
            }
    MAX-ACCESS read-write
    STATUS     current
    DESCRIPTION
            "encryption setting for control connection"
    ::= { hmSetupWlanMngmtApConfApsEntry 6 }

-- {COLUMN} 1.3.6.1.4.1.248.32.18.2.37.1.4.1.7
hmSetupWlanMngmtApConfApsEntryWlanModule1 OBJECT-TYPE
    SYNTAX     INTEGER {
                  eDefault (0),
                  e24ghz (1),
                  e5ghz (2),
                  eOff (3),
                  eAuto (255)
            }
    MAX-ACCESS read-write
    STATUS     current
    DESCRIPTION
            "-- empty --"
    ::= { hmSetupWlanMngmtApConfApsEntry 7 }

-- {COLUMN} 1.3.6.1.4.1.248.32.18.2.37.1.4.1.8
hmSetupWlanMngmtApConfApsEntryWlanModule2 OBJECT-TYPE
    SYNTAX     INTEGER {
                  eDefault (0),
                  e24ghz (1),
                  e5ghz (2),
                  eOff (3),
                  eAuto (255)
            }
    MAX-ACCESS read-write
    STATUS     current
    DESCRIPTION
            "-- empty --"
    ::= { hmSetupWlanMngmtApConfApsEntry 8 }

-- {COLUMN} 1.3.6.1.4.1.248.32.18.2.37.1.4.1.9
hmSetupWlanMngmtApConfApsEntryModule1ChannelList OBJECT-TYPE
    SYNTAX     DisplayString (SIZE(0..48))
    MAX-ACCESS read-write
    STATUS     current
    DESCRIPTION
            "-- empty --"
    ::= { hmSetupWlanMngmtApConfApsEntry 9 }

-- {COLUMN} 1.3.6.1.4.1.248.32.18.2.37.1.4.1.10
hmSetupWlanMngmtApConfApsEntryModule2ChannelList OBJECT-TYPE
    SYNTAX     DisplayString (SIZE(0..48))
    MAX-ACCESS read-write
    STATUS     current
    DESCRIPTION
            "-- empty --"
    ::= { hmSetupWlanMngmtApConfApsEntry 10 }

-- {COLUMN} 1.3.6.1.4.1.248.32.18.2.37.1.4.1.11
hmSetupWlanMngmtApConfApsEntryOperating OBJECT-TYPE
    SYNTAX     INTEGER {
                  eYes (0),
                  eNo (1)
            }
    MAX-ACCESS read-write
    STATUS     current
    DESCRIPTION
            "-- empty --"
    ::= { hmSetupWlanMngmtApConfApsEntry 11 }

-- {COLUMN} 1.3.6.1.4.1.248.32.18.2.37.1.4.1.12
hmSetupWlanMngmtApConfApsEntryIpAddress OBJECT-TYPE
    SYNTAX     IpAddress
    MAX-ACCESS read-write
    STATUS     current
    DESCRIPTION
            "-- empty --"
    ::= { hmSetupWlanMngmtApConfApsEntry 12 }

-- {COLUMN} 1.3.6.1.4.1.248.32.18.2.37.1.4.1.13
hmSetupWlanMngmtApConfApsEntryNetmask OBJECT-TYPE
    SYNTAX     IpAddress
    MAX-ACCESS read-write
    STATUS     current
    DESCRIPTION
            "-- empty --"
    ::= { hmSetupWlanMngmtApConfApsEntry 13 }

-- {COLUMN} 1.3.6.1.4.1.248.32.18.2.37.1.4.1.14
hmSetupWlanMngmtApConfApsEntryGateway OBJECT-TYPE
    SYNTAX     IpAddress
    MAX-ACCESS read-write
    STATUS     current
    DESCRIPTION
            "-- empty --"
    ::= { hmSetupWlanMngmtApConfApsEntry 14 }

-- {COLUMN} 1.3.6.1.4.1.248.32.18.2.37.1.4.1.15
hmSetupWlanMngmtApConfApsEntryAllow40mhz OBJECT-TYPE
    SYNTAX     INTEGER {
                  eAuto (0),
                  eNo (1)
            }
    MAX-ACCESS read-write
    STATUS     current
    DESCRIPTION
            "-- empty --"
    ::= { hmSetupWlanMngmtApConfApsEntry 15 }

-- {COLUMN} 1.3.6.1.4.1.248.32.18.2.37.1.4.1.16
hmSetupWlanMngmtApConfApsEntryAntennaMask OBJECT-TYPE
    SYNTAX     INTEGER {
                  eAuto (0),
                  eAntenna1 (1),
                  eAntenna1Plus2 (3),
                  eAntenna1Plus3 (5),
                  eAntenna1Plus2Plus3 (7)
            }
    MAX-ACCESS read-write
    STATUS     current
    DESCRIPTION
            "-- empty --"
    ::= { hmSetupWlanMngmtApConfApsEntry 16 }

-- {COLUMN} 1.3.6.1.4.1.248.32.18.2.37.1.4.1.17
hmSetupWlanMngmtApConfApsEntryApIntranet OBJECT-TYPE
    SYNTAX     DisplayString (SIZE(0..31))
    MAX-ACCESS read-write
    STATUS     current
    DESCRIPTION
            "-- empty --"
    ::= { hmSetupWlanMngmtApConfApsEntry 17 }

-- {COLUMN} 1.3.6.1.4.1.248.32.18.2.37.1.4.1.18
hmSetupWlanMngmtApConfApsEntryManageFirmware OBJECT-TYPE
    SYNTAX     INTEGER {
                  eYes (0),
                  eNo (1)
            }
    MAX-ACCESS read-write
    STATUS     current
    DESCRIPTION
            "-- empty --"
    ::= { hmSetupWlanMngmtApConfApsEntry 18 }

-- {COLUMN} 1.3.6.1.4.1.248.32.18.2.37.1.4.1.19
hmSetupWlanMngmtApConfApsEntryMngmtFwAddInfo OBJECT-TYPE
    SYNTAX     INTEGER {
                  eDisabledDueToErrorDuringUpdate (1),
                  eDisabledByManualUpload (2)
            }
    MAX-ACCESS read-write
    STATUS     current
    DESCRIPTION
            ""
    ::= { hmSetupWlanMngmtApConfApsEntry 19 }

-- {COLUMN} 1.3.6.1.4.1.248.32.18.2.37.1.4.1.20
hmSetupWlanMngmtApConfApsEntryModule1AntGain OBJECT-TYPE
    SYNTAX     DisplayString (SIZE(0..4))
    MAX-ACCESS read-write
    STATUS     current
    DESCRIPTION
            "-- empty --"
    ::= { hmSetupWlanMngmtApConfApsEntry 20 }

-- {COLUMN} 1.3.6.1.4.1.248.32.18.2.37.1.4.1.21
hmSetupWlanMngmtApConfApsEntryModule2AntGain OBJECT-TYPE
    SYNTAX     DisplayString (SIZE(0..4))
    MAX-ACCESS read-write
    STATUS     current
    DESCRIPTION
            "-- empty --"
    ::= { hmSetupWlanMngmtApConfApsEntry 21 }

-- {COLUMN} 1.3.6.1.4.1.248.32.18.2.37.1.4.1.22
hmSetupWlanMngmtApConfApsEntryModule1TxReduct OBJECT-TYPE
    SYNTAX     DisplayString (SIZE(0..3))
    MAX-ACCESS read-write
    STATUS     current
    DESCRIPTION
            "-- empty --"
    ::= { hmSetupWlanMngmtApConfApsEntry 22 }

-- {COLUMN} 1.3.6.1.4.1.248.32.18.2.37.1.4.1.23
hmSetupWlanMngmtApConfApsEntryModule2TxReduct OBJECT-TYPE
    SYNTAX     DisplayString (SIZE(0..3))
    MAX-ACCESS read-write
    STATUS     current
    DESCRIPTION
            "-- empty --"
    ::= { hmSetupWlanMngmtApConfApsEntry 23 }

-- {COLUMN} 1.3.6.1.4.1.248.32.18.2.37.1.4.1.24
hmSetupWlanMngmtApConfApsEntryGroup OBJECT-TYPE
    SYNTAX     DisplayString (SIZE(0..251))
    MAX-ACCESS read-write
    STATUS     current
    DESCRIPTION
            "-- empty --"
    ::= { hmSetupWlanMngmtApConfApsEntry 24 }

-- {COLUMN} 1.3.6.1.4.1.248.32.18.2.37.1.4.1.25
hmSetupWlanMngmtApConfApsEntryModule2MaxChannelBandwidth OBJECT-TYPE
    SYNTAX     INTEGER {
                  e20mhz (0),
                  e40mhz (1),
                  e80mhz (2),
                  eAuto (255)
            }
    MAX-ACCESS read-write
    STATUS     current
    DESCRIPTION
            "-- empty --"
    ::= { hmSetupWlanMngmtApConfApsEntry 25 }

-- {COLUMN} 1.3.6.1.4.1.248.32.18.2.37.1.4.1.26
hmSetupWlanMngmtApConfApsEntryModule1MaxChannelBandwidth OBJECT-TYPE
    SYNTAX     INTEGER {
                  e20mhz (0),
                  e40mhz (1),
                  e80mhz (2),
                  eAuto (255)
            }
    MAX-ACCESS read-write
    STATUS     current
    DESCRIPTION
            "-- empty --"
    ::= { hmSetupWlanMngmtApConfApsEntry 26 }

-- {COLUMN} 1.3.6.1.4.1.248.32.18.2.37.1.4.1.27
hmSetupWlanMngmtApConfApsEntryClientSteeringProfile OBJECT-TYPE
    SYNTAX     DisplayString (SIZE(0..31))
    MAX-ACCESS read-write
    STATUS     current
    DESCRIPTION
            "-- empty --"
    ::= { hmSetupWlanMngmtApConfApsEntry 27 }

-- {COLUMN} 1.3.6.1.4.1.248.32.18.2.37.1.4.1.28
hmSetupWlanMngmtApConfApsEntryLbsDeviceLocationProfile OBJECT-TYPE
    SYNTAX     DisplayString (SIZE(0..32))
    MAX-ACCESS read-write
    STATUS     current
    DESCRIPTION
            "-- empty --"
    ::= { hmSetupWlanMngmtApConfApsEntry 28 }

-- {COLUMN} 1.3.6.1.4.1.248.32.18.2.37.1.4.1.29
hmSetupWlanMngmtApConfApsEntryWirelessEpaperChannel OBJECT-TYPE
    SYNTAX     INTEGER {
                  e2404mhz (0),
                  e2410mhz (1),
                  e2422mhz (2),
                  e2425mhz (3),
                  e2442mhz (4),
                  e2450mhz (5),
                  e2462mhz (6),
                  e2470mhz (7),
                  e2474mhz (8),
                  e2477mhz (9),
                  e2480mhz (10),
                  eAuto (255)
            }
    MAX-ACCESS read-write
    STATUS     current
    DESCRIPTION
            "-- empty --"
    ::= { hmSetupWlanMngmtApConfApsEntry 29 }

-- {COLUMN} 1.3.6.1.4.1.248.32.18.2.37.1.4.1.30
hmSetupWlanMngmtApConfApsEntryIbeaconProfile OBJECT-TYPE
    SYNTAX     DisplayString (SIZE(0..31))
    MAX-ACCESS read-write
    STATUS     current
    DESCRIPTION
            "-- empty --"
    ::= { hmSetupWlanMngmtApConfApsEntry 30 }

-- {COLUMN} 1.3.6.1.4.1.248.32.18.2.37.1.4.1.31
hmSetupWlanMngmtApConfApsEntryIbeaconChannel OBJECT-TYPE
    SYNTAX     BITS {
                  e2480mhz (5),
                  e2426mhz (6),
                  e2402mhz (7)
            }
    MAX-ACCESS read-write
    STATUS     current
    DESCRIPTION
            "-- empty --"
    ::= { hmSetupWlanMngmtApConfApsEntry 31 }

-- {COLUMN} 1.3.6.1.4.1.248.32.18.2.37.1.4.1.32
hmSetupWlanMngmtApConfApsEntryMinor OBJECT-TYPE
    SYNTAX     Integer32 (0..65535)
    MAX-ACCESS read-write
    STATUS     current
    DESCRIPTION
            "-- empty --"
    ::= { hmSetupWlanMngmtApConfApsEntry 32 }

-- {COLUMN} 1.3.6.1.4.1.248.32.18.2.37.1.4.1.33
hmSetupWlanMngmtApConfApsEntryIbeaconTransmitPower OBJECT-TYPE
    SYNTAX     INTEGER {
                  eLow (0),
                  eMedium (1),
                  eHigh (2)
            }
    MAX-ACCESS read-write
    STATUS     current
    DESCRIPTION
            "-- empty --"
    ::= { hmSetupWlanMngmtApConfApsEntry 33 }

-- {SCALAR} 1.3.6.1.4.1.248.32.18.2.37.1.5
hmSetupWlanMngmtApConfWlanModul1Default OBJECT-TYPE
    SYNTAX     INTEGER {
                  e24ghz (1),
                  e5ghz (2),
                  eOff (3),
                  eAuto (255)
            }
    MAX-ACCESS read-write
    STATUS     current
    DESCRIPTION
            "-- empty --"
    ::= { hmSetupWlanMngmtApConf 5 }

-- {SCALAR} 1.3.6.1.4.1.248.32.18.2.37.1.6
hmSetupWlanMngmtApConfWlanModul2Default OBJECT-TYPE
    SYNTAX     INTEGER {
                  e24ghz (1),
                  e5ghz (2),
                  eOff (3),
                  eAuto (255)
            }
    MAX-ACCESS read-write
    STATUS     current
    DESCRIPTION
            "-- empty --"
    ::= { hmSetupWlanMngmtApConf 6 }

-- {SCALAR} 1.3.6.1.4.1.248.32.18.2.37.1.7
hmSetupWlanMngmtApConfControlConnectionEncryptionDefault OBJECT-TYPE
    SYNTAX     INTEGER {
                  eDtls (1),
                  eNo (2)
            }
    MAX-ACCESS read-write
    STATUS     current
    DESCRIPTION
            "-- empty --"
    ::= { hmSetupWlanMngmtApConf 7 }

-- {SCALAR} 1.3.6.1.4.1.248.32.18.2.37.1.8
hmSetupWlanMngmtApConfCountryDefault OBJECT-TYPE
    SYNTAX     INTEGER {
                  eAlbania (8),
                  eAlgeria (12),
                  eArgentina (32),
                  eAustralia (36),
                  eAustria (40),
                  eBahrain (48),
                  eBangladesh (50),
                  eBelgium (56),
                  eBosniaHerzegovina (70),
                  eBrazil (76),
                  eBruneiDarussalam (96),
                  eBulgaria (100),
                  eBelarus (112),
                  eCanada (124),
                  eChile (152),
                  eChina (156),
                  eTaiwan (158),
                  eColombia (170),
                  eCostaRica (188),
                  eCroatia (191),
                  eCyprus (196),
                  eCzech (203),
                  eDenmark (208),
                  eEcuador (218),
                  eEstonia (233),
                  eFinland (246),
                  eFrance (250),
                  eGermany (276),
                  eGhana (288),
                  eGreece (300),
                  eGuatemala (320),
                  eHonduras (340),
                  eHongKong (344),
                  eHungary (348),
                  eIceland (352),
                  eIndia (356),
                  eIndonesia (360),
                  eIreland (372),
                  eIsrael (376),
                  eItaly (380),
                  eJapan (392),
                  eJordan (400),
                  eSouthKorea (410),
                  eKuwait (414),
                  eLebanon (422),
                  eLatvia (428),
                  eLiechtenstein (438),
                  eLithuania (440),
                  eLuxembourg (442),
                  eMacau (446),
                  eMalaysia (458),
                  eMalta (470),
                  eMexico (484),
                  eMoldavia (498),
                  eMorocco (504),
                  eOman (512),
                  eNetherlands (528),
                  eNewZealand (554),
                  eNicaragua (558),
                  eNorway (578),
                  ePakistan (586),
                  ePanama (591),
                  eParaguay (600),
                  ePeru (604),
                  ePhilippines (608),
                  ePoland (616),
                  ePortugal (620),
                  ePuertoRico (630),
                  eQatar (634),
                  eRomania (642),
                  eRussia (643),
                  eSaudiArabia (682),
                  eSingapore (702),
                  eSlovak (703),
                  eSlovenia (705),
                  eSouthAfrica (710),
                  eSpain (724),
                  eSweden (752),
                  eSwitzerland (756),
                  eThailand (764),
                  eUnitedArabEmirates (784),
                  eTunisia (788),
                  eTurkey (792),
                  eUganda (800),
                  eUkraine (804),
                  eMacedonia (807),
                  eEgypt (818),
                  eUnitedKingdom (826),
                  eTanzania (834),
                  eUnitedStatesFcc (840),
                  eUruguay (858),
                  eVenezuela (862),
                  eEurope (998),
                  eEgalistan (999)
            }
    MAX-ACCESS read-write
    STATUS     current
    DESCRIPTION
            "-- empty --"
    ::= { hmSetupWlanMngmtApConf 8 }

-- {TABLE} 1.3.6.1.4.1.248.32.18.2.37.1.9
hmSetupWlanMngmtApConfApIntranetsTable OBJECT-TYPE
    SYNTAX     SEQUENCE OF HmSetupWlanMngmtApConfApIntranetsEntry
    MAX-ACCESS not-accessible
    STATUS     current
    DESCRIPTION
            "-- empty --"
    ::= { hmSetupWlanMngmtApConf 9 }

-- {ROW} 1.3.6.1.4.1.248.32.18.2.37.1.9.1
hmSetupWlanMngmtApConfApIntranetsEntry OBJECT-TYPE
    SYNTAX     HmSetupWlanMngmtApConfApIntranetsEntry
    MAX-ACCESS not-accessible
    STATUS     current
    DESCRIPTION
            ""
    INDEX {
            hmSetupWlanMngmtApConfApIntranetsEntryName
          }
    ::= { hmSetupWlanMngmtApConfApIntranetsTable 1 }

HmSetupWlanMngmtApConfApIntranetsEntry ::= SEQUENCE {
            hmSetupWlanMngmtApConfApIntranetsEntryName DisplayString,
            hmSetupWlanMngmtApConfApIntranetsEntryParentName DisplayString,
            hmSetupWlanMngmtApConfApIntranetsEntryLocVal DisplayString,
            hmSetupWlanMngmtApConfApIntranetsEntryDomainName DisplayString,
            hmSetupWlanMngmtApConfApIntranetsEntryNetmask IpAddress,
            hmSetupWlanMngmtApConfApIntranetsEntryGateway IpAddress,
            hmSetupWlanMngmtApConfApIntranetsEntryPrimaryDnsSrv IpAddress,
            hmSetupWlanMngmtApConfApIntranetsEntrySecondaryDnsSrv IpAddress,
            hmSetupWlanMngmtApConfApIntranetsEntryIpv4ConfigPoolStart DisplayString,
            hmSetupWlanMngmtApConfApIntranetsEntryIpv4ConfigPoolEnd DisplayString
    }

-- {COLUMN} 1.3.6.1.4.1.248.32.18.2.37.1.9.1.1
hmSetupWlanMngmtApConfApIntranetsEntryName OBJECT-TYPE
    SYNTAX     DisplayString (SIZE(0..31))
    MAX-ACCESS read-write
    STATUS     current
    DESCRIPTION
            "-- empty --"
    ::= { hmSetupWlanMngmtApConfApIntranetsEntry 1 }

-- {COLUMN} 1.3.6.1.4.1.248.32.18.2.37.1.9.1.2
hmSetupWlanMngmtApConfApIntranetsEntryParentName OBJECT-TYPE
    SYNTAX     DisplayString (SIZE(0..31))
    MAX-ACCESS read-write
    STATUS     current
    DESCRIPTION
            ""
    ::= { hmSetupWlanMngmtApConfApIntranetsEntry 2 }

-- {COLUMN} 1.3.6.1.4.1.248.32.18.2.37.1.9.1.3
hmSetupWlanMngmtApConfApIntranetsEntryLocVal OBJECT-TYPE
    SYNTAX     DisplayString (SIZE(0..2))
    MAX-ACCESS read-write
    STATUS     current
    DESCRIPTION
            "local values"
    ::= { hmSetupWlanMngmtApConfApIntranetsEntry 3 }

-- {COLUMN} 1.3.6.1.4.1.248.32.18.2.37.1.9.1.4
hmSetupWlanMngmtApConfApIntranetsEntryDomainName OBJECT-TYPE
    SYNTAX     DisplayString (SIZE(0..63))
    MAX-ACCESS read-write
    STATUS     current
    DESCRIPTION
            "-- empty --"
    ::= { hmSetupWlanMngmtApConfApIntranetsEntry 4 }

-- {COLUMN} 1.3.6.1.4.1.248.32.18.2.37.1.9.1.5
hmSetupWlanMngmtApConfApIntranetsEntryNetmask OBJECT-TYPE
    SYNTAX     IpAddress
    MAX-ACCESS read-write
    STATUS     current
    DESCRIPTION
            "-- empty --"
    ::= { hmSetupWlanMngmtApConfApIntranetsEntry 5 }

-- {COLUMN} 1.3.6.1.4.1.248.32.18.2.37.1.9.1.6
hmSetupWlanMngmtApConfApIntranetsEntryGateway OBJECT-TYPE
    SYNTAX     IpAddress
    MAX-ACCESS read-write
    STATUS     current
    DESCRIPTION
            "-- empty --"
    ::= { hmSetupWlanMngmtApConfApIntranetsEntry 6 }

-- {COLUMN} 1.3.6.1.4.1.248.32.18.2.37.1.9.1.7
hmSetupWlanMngmtApConfApIntranetsEntryPrimaryDnsSrv OBJECT-TYPE
    SYNTAX     IpAddress
    MAX-ACCESS read-write
    STATUS     current
    DESCRIPTION
            "-- empty --"
    ::= { hmSetupWlanMngmtApConfApIntranetsEntry 7 }

-- {COLUMN} 1.3.6.1.4.1.248.32.18.2.37.1.9.1.8
hmSetupWlanMngmtApConfApIntranetsEntrySecondaryDnsSrv OBJECT-TYPE
    SYNTAX     IpAddress
    MAX-ACCESS read-write
    STATUS     current
    DESCRIPTION
            "-- empty --"
    ::= { hmSetupWlanMngmtApConfApIntranetsEntry 8 }

-- {COLUMN} 1.3.6.1.4.1.248.32.18.2.37.1.9.1.9
hmSetupWlanMngmtApConfApIntranetsEntryIpv4ConfigPoolStart OBJECT-TYPE
    SYNTAX     DisplayString (SIZE(0..15))
    MAX-ACCESS read-write
    STATUS     current
    DESCRIPTION
            "-- empty --"
    ::= { hmSetupWlanMngmtApConfApIntranetsEntry 9 }

-- {COLUMN} 1.3.6.1.4.1.248.32.18.2.37.1.9.1.10
hmSetupWlanMngmtApConfApIntranetsEntryIpv4ConfigPoolEnd OBJECT-TYPE
    SYNTAX     DisplayString (SIZE(0..15))
    MAX-ACCESS read-write
    STATUS     current
    DESCRIPTION
            "-- empty --"
    ::= { hmSetupWlanMngmtApConfApIntranetsEntry 10 }

-- {TABLE} 1.3.6.1.4.1.248.32.18.2.37.1.10
hmSetupWlanMngmtApConfPredefIntranetsTable OBJECT-TYPE
    SYNTAX     SEQUENCE OF HmSetupWlanMngmtApConfPredefIntranetsEntry
    MAX-ACCESS not-accessible
    STATUS     current
    DESCRIPTION
            "-- empty --"
    ::= { hmSetupWlanMngmtApConf 10 }

-- {ROW} 1.3.6.1.4.1.248.32.18.2.37.1.10.1
hmSetupWlanMngmtApConfPredefIntranetsEntry OBJECT-TYPE
    SYNTAX     HmSetupWlanMngmtApConfPredefIntranetsEntry
    MAX-ACCESS not-accessible
    STATUS     current
    DESCRIPTION
            ""
    INDEX {
            hmSetupWlanMngmtApConfPredefIntranetsEntryName
          }
    ::= { hmSetupWlanMngmtApConfPredefIntranetsTable 1 }

HmSetupWlanMngmtApConfPredefIntranetsEntry ::= SEQUENCE {
            hmSetupWlanMngmtApConfPredefIntranetsEntryName DisplayString
    }

-- {COLUMN} 1.3.6.1.4.1.248.32.18.2.37.1.10.1.1
hmSetupWlanMngmtApConfPredefIntranetsEntryName OBJECT-TYPE
    SYNTAX     DisplayString (SIZE(0..15))
    MAX-ACCESS read-only
    STATUS     current
    DESCRIPTION
            "-- empty --"
    ::= { hmSetupWlanMngmtApConfPredefIntranetsEntry 1 }

-- {SCALAR} 1.3.6.1.4.1.248.32.18.2.37.1.12
hmSetupWlanMngmtApConfDscpForControlPackets OBJECT-TYPE
    SYNTAX     INTEGER {
                  eBestEffort (0),
                  eAssuredForwarding11 (40),
                  eAssuredForwarding12 (48),
                  eAssuredForwarding13 (56),
                  eAssuredForwarding21 (72),
                  eAssuredForwarding22 (80),
                  eAssuredForwarding23 (88),
                  eAssuredForwarding31 (104),
                  eAssuredForwarding32 (112),
                  eAssuredForwarding33 (120),
                  eAssuredForwarding41 (136),
                  eAssuredForwarding42 (144),
                  eAssuredForwarding43 (152),
                  eExpeditedForwarding (184)
            }
    MAX-ACCESS read-write
    STATUS     current
    DESCRIPTION
            "-- empty --"
    ::= { hmSetupWlanMngmtApConf 12 }

-- {SCALAR} 1.3.6.1.4.1.248.32.18.2.37.1.13
hmSetupWlanMngmtApConfDscpForDataPackets OBJECT-TYPE
    SYNTAX     INTEGER {
                  eBestEffort (0),
                  eAssuredForwarding11 (40),
                  eAssuredForwarding12 (48),
                  eAssuredForwarding13 (56),
                  eAssuredForwarding21 (72),
                  eAssuredForwarding22 (80),
                  eAssuredForwarding23 (88),
                  eAssuredForwarding31 (104),
                  eAssuredForwarding32 (112),
                  eAssuredForwarding33 (120),
                  eAssuredForwarding41 (136),
                  eAssuredForwarding42 (144),
                  eAssuredForwarding43 (152),
                  eExpeditedForwarding (184)
            }
    MAX-ACCESS read-write
    STATUS     current
    DESCRIPTION
            "-- empty --"
    ::= { hmSetupWlanMngmtApConf 13 }

-- {TABLE} 1.3.6.1.4.1.248.32.18.2.37.1.14
hmSetupWlanMngmtApConfMulticastNetworksTable OBJECT-TYPE
    SYNTAX     SEQUENCE OF HmSetupWlanMngmtApConfMulticastNetworksEntry
    MAX-ACCESS not-accessible
    STATUS     current
    DESCRIPTION
            "-- empty --"
    ::= { hmSetupWlanMngmtApConf 14 }

-- {ROW} 1.3.6.1.4.1.248.32.18.2.37.1.14.1
hmSetupWlanMngmtApConfMulticastNetworksEntry OBJECT-TYPE
    SYNTAX     HmSetupWlanMngmtApConfMulticastNetworksEntry
    MAX-ACCESS not-accessible
    STATUS     current
    DESCRIPTION
            ""
    INDEX {
            hmSetupWlanMngmtApConfMulticastNetworksEntryBridgeInterface
          }
    ::= { hmSetupWlanMngmtApConfMulticastNetworksTable 1 }

HmSetupWlanMngmtApConfMulticastNetworksEntry ::= SEQUENCE {
            hmSetupWlanMngmtApConfMulticastNetworksEntryBridgeInterface INTEGER,
            hmSetupWlanMngmtApConfMulticastNetworksEntryActive INTEGER,
            hmSetupWlanMngmtApConfMulticastNetworksEntryMulticastAddress IpAddress,
            hmSetupWlanMngmtApConfMulticastNetworksEntryMulticastPort Integer32,
            hmSetupWlanMngmtApConfMulticastNetworksEntryLoopbackAddr DisplayString
    }

-- {COLUMN} 1.3.6.1.4.1.248.32.18.2.37.1.14.1.1
hmSetupWlanMngmtApConfMulticastNetworksEntryBridgeInterface OBJECT-TYPE
    SYNTAX     INTEGER {
                  eLan (0),
                  eWlcTunnel1 (1),
                  eWlcTunnel2 (2),
                  eWlcTunnel3 (3),
                  eWlcTunnel4 (4),
                  eWlcTunnel5 (5),
                  eWlcTunnel6 (6),
                  eWlcTunnel7 (7),
                  eWlcTunnel8 (8),
                  eWlcTunnel9 (9),
                  eWlcTunnel10 (10),
                  eWlcTunnel11 (11),
                  eWlcTunnel12 (12),
                  eWlcTunnel13 (13),
                  eWlcTunnel14 (14),
                  eWlcTunnel15 (15),
                  eWlcTunnel16 (16),
                  eWlcTunnel17 (17),
                  eWlcTunnel18 (18),
                  eWlcTunnel19 (19),
                  eWlcTunnel20 (20),
                  eWlcTunnel21 (21),
                  eWlcTunnel22 (22),
                  eWlcTunnel23 (23),
                  eWlcTunnel24 (24),
                  eWlcTunnel25 (25),
                  eWlcTunnel26 (26),
                  eWlcTunnel27 (27),
                  eWlcTunnel28 (28),
                  eWlcTunnel29 (29),
                  eWlcTunnel30 (30),
                  eWlcTunnel31 (31),
                  eWlcTunnel32 (32),
                  eWlcTunnelAutowds (33)
            }
    MAX-ACCESS read-only
    STATUS     current
    DESCRIPTION
            "-- empty --"
    ::= { hmSetupWlanMngmtApConfMulticastNetworksEntry 1 }

-- {COLUMN} 1.3.6.1.4.1.248.32.18.2.37.1.14.1.2
hmSetupWlanMngmtApConfMulticastNetworksEntryActive OBJECT-TYPE
    SYNTAX     INTEGER {
                  eNo (0),
                  eYes (1)
            }
    MAX-ACCESS read-write
    STATUS     current
    DESCRIPTION
            "-- empty --"
    ::= { hmSetupWlanMngmtApConfMulticastNetworksEntry 2 }

-- {COLUMN} 1.3.6.1.4.1.248.32.18.2.37.1.14.1.3
hmSetupWlanMngmtApConfMulticastNetworksEntryMulticastAddress OBJECT-TYPE
    SYNTAX     IpAddress
    MAX-ACCESS read-write
    STATUS     current
    DESCRIPTION
            "-- empty --"
    ::= { hmSetupWlanMngmtApConfMulticastNetworksEntry 3 }

-- {COLUMN} 1.3.6.1.4.1.248.32.18.2.37.1.14.1.4
hmSetupWlanMngmtApConfMulticastNetworksEntryMulticastPort OBJECT-TYPE
    SYNTAX     Integer32 (0..65535)
    MAX-ACCESS read-write
    STATUS     current
    DESCRIPTION
            "-- empty --"
    ::= { hmSetupWlanMngmtApConfMulticastNetworksEntry 4 }

-- {COLUMN} 1.3.6.1.4.1.248.32.18.2.37.1.14.1.5
hmSetupWlanMngmtApConfMulticastNetworksEntryLoopbackAddr OBJECT-TYPE
    SYNTAX     DisplayString (SIZE(0..16))
    MAX-ACCESS read-write
    STATUS     current
    DESCRIPTION
            "-- empty --"
    ::= { hmSetupWlanMngmtApConfMulticastNetworksEntry 5 }

-- {TABLE} 1.3.6.1.4.1.248.32.18.2.37.1.15
hmSetupWlanMngmtApConfAutowdsProfilesTable OBJECT-TYPE
    SYNTAX     SEQUENCE OF HmSetupWlanMngmtApConfAutowdsProfilesEntry
    MAX-ACCESS not-accessible
    STATUS     current
    DESCRIPTION
            "-- empty --"
    ::= { hmSetupWlanMngmtApConf 15 }

-- {ROW} 1.3.6.1.4.1.248.32.18.2.37.1.15.1
hmSetupWlanMngmtApConfAutowdsProfilesEntry OBJECT-TYPE
    SYNTAX     HmSetupWlanMngmtApConfAutowdsProfilesEntry
    MAX-ACCESS not-accessible
    STATUS     current
    DESCRIPTION
            ""
    INDEX {
            hmSetupWlanMngmtApConfAutowdsProfilesEntryName
          }
    ::= { hmSetupWlanMngmtApConfAutowdsProfilesTable 1 }

HmSetupWlanMngmtApConfAutowdsProfilesEntry ::= SEQUENCE {
            hmSetupWlanMngmtApConfAutowdsProfilesEntryName DisplayString,
            hmSetupWlanMngmtApConfAutowdsProfilesEntryCommonprofile DisplayString,
            hmSetupWlanMngmtApConfAutowdsProfilesEntrySsid DisplayString,
            hmSetupWlanMngmtApConfAutowdsProfilesEntryKey DisplayString,
            hmSetupWlanMngmtApConfAutowdsProfilesEntryEnabled INTEGER,
            hmSetupWlanMngmtApConfAutowdsProfilesEntryAllowExprInt INTEGER,
            hmSetupWlanMngmtApConfAutowdsProfilesEntryTopologyManagement INTEGER,
            hmSetupWlanMngmtApConfAutowdsProfilesEntrySlaveTxLimit Integer32,
            hmSetupWlanMngmtApConfAutowdsProfilesEntryMasterTxLimit Integer32,
            hmSetupWlanMngmtApConfAutowdsProfilesEntryLinkLossTimeout Integer32,
            hmSetupWlanMngmtApConfAutowdsProfilesEntryContinuation Integer32,
            hmSetupWlanMngmtApConfAutowdsProfilesEntryTimeTillPreconfScan Integer32,
            hmSetupWlanMngmtApConfAutowdsProfilesEntryTimeTillExpressScan Integer32,
            hmSetupWlanMngmtApConfAutowdsProfilesEntryInterfacePairing INTEGER,
            hmSetupWlanMngmtApConfAutowdsProfilesEntryRadioBand INTEGER,
            hmSetupWlanMngmtApConfAutowdsProfilesEntrySsidBroadcast INTEGER
    }

-- {COLUMN} 1.3.6.1.4.1.248.32.18.2.37.1.15.1.1
hmSetupWlanMngmtApConfAutowdsProfilesEntryName OBJECT-TYPE
    SYNTAX     DisplayString (SIZE(0..31))
    MAX-ACCESS read-only
    STATUS     current
    DESCRIPTION
            "-- empty --"
    ::= { hmSetupWlanMngmtApConfAutowdsProfilesEntry 1 }

-- {COLUMN} 1.3.6.1.4.1.248.32.18.2.37.1.15.1.2
hmSetupWlanMngmtApConfAutowdsProfilesEntryCommonprofile OBJECT-TYPE
    SYNTAX     DisplayString (SIZE(0..31))
    MAX-ACCESS read-write
    STATUS     current
    DESCRIPTION
            "-- empty --"
    ::= { hmSetupWlanMngmtApConfAutowdsProfilesEntry 2 }

-- {COLUMN} 1.3.6.1.4.1.248.32.18.2.37.1.15.1.3
hmSetupWlanMngmtApConfAutowdsProfilesEntrySsid OBJECT-TYPE
    SYNTAX     DisplayString (SIZE(0..32))
    MAX-ACCESS read-write
    STATUS     current
    DESCRIPTION
            "-- empty --"
    ::= { hmSetupWlanMngmtApConfAutowdsProfilesEntry 3 }

-- {COLUMN} 1.3.6.1.4.1.248.32.18.2.37.1.15.1.4
hmSetupWlanMngmtApConfAutowdsProfilesEntryKey OBJECT-TYPE
    SYNTAX     DisplayString (SIZE(0..63))
    MAX-ACCESS read-write
    STATUS     current
    DESCRIPTION
            "-- empty --"
    ::= { hmSetupWlanMngmtApConfAutowdsProfilesEntry 4 }

-- {COLUMN} 1.3.6.1.4.1.248.32.18.2.37.1.15.1.6
hmSetupWlanMngmtApConfAutowdsProfilesEntryEnabled OBJECT-TYPE
    SYNTAX     INTEGER {
                  eNo (0),
                  eYes (1)
            }
    MAX-ACCESS read-write
    STATUS     current
    DESCRIPTION
            "-- empty --"
    ::= { hmSetupWlanMngmtApConfAutowdsProfilesEntry 6 }

-- {COLUMN} 1.3.6.1.4.1.248.32.18.2.37.1.15.1.7
hmSetupWlanMngmtApConfAutowdsProfilesEntryAllowExprInt OBJECT-TYPE
    SYNTAX     INTEGER {
                  eNo (0),
                  eYes (1)
            }
    MAX-ACCESS read-write
    STATUS     current
    DESCRIPTION
            "Allow-Express-Integration"
    ::= { hmSetupWlanMngmtApConfAutowdsProfilesEntry 7 }

-- {COLUMN} 1.3.6.1.4.1.248.32.18.2.37.1.15.1.8
hmSetupWlanMngmtApConfAutowdsProfilesEntryTopologyManagement OBJECT-TYPE
    SYNTAX     INTEGER {
                  eAutomatic (0),
                  eSemiAutomatic (1),
                  eManual (2)
            }
    MAX-ACCESS read-write
    STATUS     current
    DESCRIPTION
            "-- empty --"
    ::= { hmSetupWlanMngmtApConfAutowdsProfilesEntry 8 }

-- {COLUMN} 1.3.6.1.4.1.248.32.18.2.37.1.15.1.10
hmSetupWlanMngmtApConfAutowdsProfilesEntrySlaveTxLimit OBJECT-TYPE
    SYNTAX     Integer32 (0..2147483647)
    MAX-ACCESS read-write
    STATUS     current
    DESCRIPTION
            "-- empty --"
    ::= { hmSetupWlanMngmtApConfAutowdsProfilesEntry 10 }

-- {COLUMN} 1.3.6.1.4.1.248.32.18.2.37.1.15.1.11
hmSetupWlanMngmtApConfAutowdsProfilesEntryMasterTxLimit OBJECT-TYPE
    SYNTAX     Integer32 (0..2147483647)
    MAX-ACCESS read-write
    STATUS     current
    DESCRIPTION
            "-- empty --"
    ::= { hmSetupWlanMngmtApConfAutowdsProfilesEntry 11 }

-- {COLUMN} 1.3.6.1.4.1.248.32.18.2.37.1.15.1.12
hmSetupWlanMngmtApConfAutowdsProfilesEntryLinkLossTimeout OBJECT-TYPE
    SYNTAX     Integer32 (0..2147483647)
    MAX-ACCESS read-write
    STATUS     current
    DESCRIPTION
            "-- empty --"
    ::= { hmSetupWlanMngmtApConfAutowdsProfilesEntry 12 }

-- {COLUMN} 1.3.6.1.4.1.248.32.18.2.37.1.15.1.14
hmSetupWlanMngmtApConfAutowdsProfilesEntryContinuation OBJECT-TYPE
    SYNTAX     Integer32 (0..65535)
    MAX-ACCESS read-write
    STATUS     current
    DESCRIPTION
            ""
    ::= { hmSetupWlanMngmtApConfAutowdsProfilesEntry 14 }

-- {COLUMN} 1.3.6.1.4.1.248.32.18.2.37.1.15.1.15
hmSetupWlanMngmtApConfAutowdsProfilesEntryTimeTillPreconfScan OBJECT-TYPE
    SYNTAX     Integer32 (0..2147483647)
    MAX-ACCESS read-write
    STATUS     current
    DESCRIPTION
            "-- empty --"
    ::= { hmSetupWlanMngmtApConfAutowdsProfilesEntry 15 }

-- {COLUMN} 1.3.6.1.4.1.248.32.18.2.37.1.15.1.16
hmSetupWlanMngmtApConfAutowdsProfilesEntryTimeTillExpressScan OBJECT-TYPE
    SYNTAX     Integer32 (0..2147483647)
    MAX-ACCESS read-write
    STATUS     current
    DESCRIPTION
            "-- empty --"
    ::= { hmSetupWlanMngmtApConfAutowdsProfilesEntry 16 }

-- {COLUMN} 1.3.6.1.4.1.248.32.18.2.37.1.15.1.17
hmSetupWlanMngmtApConfAutowdsProfilesEntryInterfacePairing OBJECT-TYPE
    SYNTAX     INTEGER {
                  eAutomatic (0),
                  eStrict (1),
                  eMixed (2)
            }
    MAX-ACCESS read-write
    STATUS     current
    DESCRIPTION
            "-- empty --"
    ::= { hmSetupWlanMngmtApConfAutowdsProfilesEntry 17 }

-- {COLUMN} 1.3.6.1.4.1.248.32.18.2.37.1.15.1.19
hmSetupWlanMngmtApConfAutowdsProfilesEntryRadioBand OBJECT-TYPE
    SYNTAX     INTEGER {
                  e24ghz5ghz (0),
                  e24ghz (1),
                  e5ghz (2)
            }
    MAX-ACCESS read-write
    STATUS     current
    DESCRIPTION
            "-- empty --"
    ::= { hmSetupWlanMngmtApConfAutowdsProfilesEntry 19 }

-- {COLUMN} 1.3.6.1.4.1.248.32.18.2.37.1.15.1.20
hmSetupWlanMngmtApConfAutowdsProfilesEntrySsidBroadcast OBJECT-TYPE
    SYNTAX     INTEGER {
                  eNo (0),
                  eYes (1)
            }
    MAX-ACCESS read-write
    STATUS     current
    DESCRIPTION
            "-- empty --"
    ::= { hmSetupWlanMngmtApConfAutowdsProfilesEntry 20 }

-- {TABLE} 1.3.6.1.4.1.248.32.18.2.37.1.16
hmSetupWlanMngmtApConfAutowdsTopologyTable OBJECT-TYPE
    SYNTAX     SEQUENCE OF HmSetupWlanMngmtApConfAutowdsTopologyEntry
    MAX-ACCESS not-accessible
    STATUS     current
    DESCRIPTION
            "-- empty --"
    ::= { hmSetupWlanMngmtApConf 16 }

-- {ROW} 1.3.6.1.4.1.248.32.18.2.37.1.16.1
hmSetupWlanMngmtApConfAutowdsTopologyEntry OBJECT-TYPE
    SYNTAX     HmSetupWlanMngmtApConfAutowdsTopologyEntry
    MAX-ACCESS not-accessible
    STATUS     current
    DESCRIPTION
            ""
    INDEX {
            hmSetupWlanMngmtApConfAutowdsTopologyEntryAutowdsProfile,
            hmSetupWlanMngmtApConfAutowdsTopologyEntryPriority,
            hmSetupWlanMngmtApConfAutowdsTopologyEntrySlaveApName,
            hmSetupWlanMngmtApConfAutowdsTopologyEntrySlaveApWlanIfc
          }
    ::= { hmSetupWlanMngmtApConfAutowdsTopologyTable 1 }

HmSetupWlanMngmtApConfAutowdsTopologyEntry ::= SEQUENCE {
            hmSetupWlanMngmtApConfAutowdsTopologyEntryAutowdsProfile DisplayString,
            hmSetupWlanMngmtApConfAutowdsTopologyEntryPriority Integer32,
            hmSetupWlanMngmtApConfAutowdsTopologyEntrySlaveApName DisplayString,
            hmSetupWlanMngmtApConfAutowdsTopologyEntrySlaveApWlanIfc INTEGER,
            hmSetupWlanMngmtApConfAutowdsTopologyEntryMasterApName DisplayString,
            hmSetupWlanMngmtApConfAutowdsTopologyEntryMasterApWlanIfc INTEGER,
            hmSetupWlanMngmtApConfAutowdsTopologyEntryKey DisplayString,
            hmSetupWlanMngmtApConfAutowdsTopologyEntryEnabled INTEGER,
            hmSetupWlanMngmtApConfAutowdsTopologyEntrySlaveTxLimit Integer32,
            hmSetupWlanMngmtApConfAutowdsTopologyEntryMasterTxLimit Integer32,
            hmSetupWlanMngmtApConfAutowdsTopologyEntryLinkLossTimeout Integer32,
            hmSetupWlanMngmtApConfAutowdsTopologyEntryContinuation Integer32
    }

-- {COLUMN} 1.3.6.1.4.1.248.32.18.2.37.1.16.1.1
hmSetupWlanMngmtApConfAutowdsTopologyEntryAutowdsProfile OBJECT-TYPE
    SYNTAX     DisplayString (SIZE(0..31))
    MAX-ACCESS read-write
    STATUS     current
    DESCRIPTION
            "-- empty --"
    ::= { hmSetupWlanMngmtApConfAutowdsTopologyEntry 1 }

-- {COLUMN} 1.3.6.1.4.1.248.32.18.2.37.1.16.1.2
hmSetupWlanMngmtApConfAutowdsTopologyEntryPriority OBJECT-TYPE
    SYNTAX     Integer32 (0..65535)
    MAX-ACCESS read-write
    STATUS     current
    DESCRIPTION
            "-- empty --"
    ::= { hmSetupWlanMngmtApConfAutowdsTopologyEntry 2 }

-- {COLUMN} 1.3.6.1.4.1.248.32.18.2.37.1.16.1.3
hmSetupWlanMngmtApConfAutowdsTopologyEntrySlaveApName OBJECT-TYPE
    SYNTAX     DisplayString (SIZE(0..16))
    MAX-ACCESS read-write
    STATUS     current
    DESCRIPTION
            "-- empty --"
    ::= { hmSetupWlanMngmtApConfAutowdsTopologyEntry 3 }

-- {COLUMN} 1.3.6.1.4.1.248.32.18.2.37.1.16.1.4
hmSetupWlanMngmtApConfAutowdsTopologyEntrySlaveApWlanIfc OBJECT-TYPE
    SYNTAX     INTEGER {
                  eWlan1 (1),
                  eWlan2 (2)
            }
    MAX-ACCESS read-write
    STATUS     current
    DESCRIPTION
            "-- empty --"
    ::= { hmSetupWlanMngmtApConfAutowdsTopologyEntry 4 }

-- {COLUMN} 1.3.6.1.4.1.248.32.18.2.37.1.16.1.6
hmSetupWlanMngmtApConfAutowdsTopologyEntryMasterApName OBJECT-TYPE
    SYNTAX     DisplayString (SIZE(0..16))
    MAX-ACCESS read-write
    STATUS     current
    DESCRIPTION
            "-- empty --"
    ::= { hmSetupWlanMngmtApConfAutowdsTopologyEntry 6 }

-- {COLUMN} 1.3.6.1.4.1.248.32.18.2.37.1.16.1.7
hmSetupWlanMngmtApConfAutowdsTopologyEntryMasterApWlanIfc OBJECT-TYPE
    SYNTAX     INTEGER {
                  eWlan1 (1),
                  eWlan2 (2)
            }
    MAX-ACCESS read-write
    STATUS     current
    DESCRIPTION
            "-- empty --"
    ::= { hmSetupWlanMngmtApConfAutowdsTopologyEntry 7 }

-- {COLUMN} 1.3.6.1.4.1.248.32.18.2.37.1.16.1.9
hmSetupWlanMngmtApConfAutowdsTopologyEntryKey OBJECT-TYPE
    SYNTAX     DisplayString (SIZE(0..63))
    MAX-ACCESS read-write
    STATUS     current
    DESCRIPTION
            "-- empty --"
    ::= { hmSetupWlanMngmtApConfAutowdsTopologyEntry 9 }

-- {COLUMN} 1.3.6.1.4.1.248.32.18.2.37.1.16.1.10
hmSetupWlanMngmtApConfAutowdsTopologyEntryEnabled OBJECT-TYPE
    SYNTAX     INTEGER {
                  eNo (0),
                  eYes (1)
            }
    MAX-ACCESS read-write
    STATUS     current
    DESCRIPTION
            "-- empty --"
    ::= { hmSetupWlanMngmtApConfAutowdsTopologyEntry 10 }

-- {COLUMN} 1.3.6.1.4.1.248.32.18.2.37.1.16.1.12
hmSetupWlanMngmtApConfAutowdsTopologyEntrySlaveTxLimit OBJECT-TYPE
    SYNTAX     Integer32 (0..2147483647)
    MAX-ACCESS read-write
    STATUS     current
    DESCRIPTION
            "-- empty --"
    ::= { hmSetupWlanMngmtApConfAutowdsTopologyEntry 12 }

-- {COLUMN} 1.3.6.1.4.1.248.32.18.2.37.1.16.1.13
hmSetupWlanMngmtApConfAutowdsTopologyEntryMasterTxLimit OBJECT-TYPE
    SYNTAX     Integer32 (0..2147483647)
    MAX-ACCESS read-write
    STATUS     current
    DESCRIPTION
            "-- empty --"
    ::= { hmSetupWlanMngmtApConfAutowdsTopologyEntry 13 }

-- {COLUMN} 1.3.6.1.4.1.248.32.18.2.37.1.16.1.14
hmSetupWlanMngmtApConfAutowdsTopologyEntryLinkLossTimeout OBJECT-TYPE
    SYNTAX     Integer32 (0..2147483647)
    MAX-ACCESS read-write
    STATUS     current
    DESCRIPTION
            "-- empty --"
    ::= { hmSetupWlanMngmtApConfAutowdsTopologyEntry 14 }

-- {COLUMN} 1.3.6.1.4.1.248.32.18.2.37.1.16.1.16
hmSetupWlanMngmtApConfAutowdsTopologyEntryContinuation OBJECT-TYPE
    SYNTAX     Integer32 (0..65535)
    MAX-ACCESS read-write
    STATUS     current
    DESCRIPTION
            ""
    ::= { hmSetupWlanMngmtApConfAutowdsTopologyEntry 16 }

-- {NODE} 1.3.6.1.4.1.248.32.18.2.37.1.17
hmSetupWlanMngmtApConf11u OBJECT IDENTIFIER ::= { hmSetupWlanMngmtApConf 17 }

-- {TABLE} 1.3.6.1.4.1.248.32.18.2.37.1.17.1
hmSetupWlanMngmtApConf11u11u-NwTable OBJECT-TYPE
    SYNTAX     SEQUENCE OF HmSetupWlanMngmtApConf11u11u-NwEntry
    MAX-ACCESS not-accessible
    STATUS     current
    DESCRIPTION
            "IEEE802.11u-Networks"
    ::= { hmSetupWlanMngmtApConf11u 1 }

-- {ROW} 1.3.6.1.4.1.248.32.18.2.37.1.17.1.1
hmSetupWlanMngmtApConf11u11u-NwEntry OBJECT-TYPE
    SYNTAX     HmSetupWlanMngmtApConf11u11u-NwEntry
    MAX-ACCESS not-accessible
    STATUS     current
    DESCRIPTION
            ""
    INDEX {
            hmSetupWlanMngmtApConf11u11u-NwEntryName
          }
    ::= { hmSetupWlanMngmtApConf11u11u-NwTable 1 }

HmSetupWlanMngmtApConf11u11u-NwEntry ::= SEQUENCE {
            hmSetupWlanMngmtApConf11u11u-NwEntryName DisplayString,
            hmSetupWlanMngmtApConf11u11u-NwEntryOper INTEGER,
            hmSetupWlanMngmtApConf11u11u-NwEntryHs20 INTEGER,
            hmSetupWlanMngmtApConf11u11u-NwEntryInet INTEGER,
            hmSetupWlanMngmtApConf11u11u-NwEntryNwType INTEGER,
            hmSetupWlanMngmtApConf11u11u-NwEntryAsra INTEGER,
            hmSetupWlanMngmtApConf11u11u-NwEntryHESSIDT INTEGER,
            hmSetupWlanMngmtApConf11u11u-NwEntryHESSIDM MacAddress,
            hmSetupWlanMngmtApConf11u11u-NwEntryANQP-Prof DisplayString,
            hmSetupWlanMngmtApConf11u11u-NwEntryHs20-Prof DisplayString
    }

-- {COLUMN} 1.3.6.1.4.1.248.32.18.2.37.1.17.1.1.1
hmSetupWlanMngmtApConf11u11u-NwEntryName OBJECT-TYPE
    SYNTAX     DisplayString (SIZE(0..32))
    MAX-ACCESS read-write
    STATUS     current
    DESCRIPTION
            "-- empty --"
    ::= { hmSetupWlanMngmtApConf11u11u-NwEntry 1 }

-- {COLUMN} 1.3.6.1.4.1.248.32.18.2.37.1.17.1.1.2
hmSetupWlanMngmtApConf11u11u-NwEntryOper OBJECT-TYPE
    SYNTAX     INTEGER {
                  eNo (0),
                  eYes (1)
            }
    MAX-ACCESS read-write
    STATUS     current
    DESCRIPTION
            "Operating"
    ::= { hmSetupWlanMngmtApConf11u11u-NwEntry 2 }

-- {COLUMN} 1.3.6.1.4.1.248.32.18.2.37.1.17.1.1.3
hmSetupWlanMngmtApConf11u11u-NwEntryHs20 OBJECT-TYPE
    SYNTAX     INTEGER {
                  eNo (0),
                  eYes (1)
            }
    MAX-ACCESS read-write
    STATUS     current
    DESCRIPTION
            "Hotspot2.0"
    ::= { hmSetupWlanMngmtApConf11u11u-NwEntry 3 }

-- {COLUMN} 1.3.6.1.4.1.248.32.18.2.37.1.17.1.1.4
hmSetupWlanMngmtApConf11u11u-NwEntryInet OBJECT-TYPE
    SYNTAX     INTEGER {
                  eNo (0),
                  eYes (1)
            }
    MAX-ACCESS read-write
    STATUS     current
    DESCRIPTION
            "Internet"
    ::= { hmSetupWlanMngmtApConf11u11u-NwEntry 4 }

-- {COLUMN} 1.3.6.1.4.1.248.32.18.2.37.1.17.1.1.5
hmSetupWlanMngmtApConf11u11u-NwEntryNwType OBJECT-TYPE
    SYNTAX     INTEGER {
                  ePrivate (0),
                  ePrivateGuestacc (1),
                  ePublicCharge (2),
                  ePublicFree (3),
                  ePersonalDev (4),
                  eEmergency (5),
                  eExperimental (14),
                  eWildcard (15)
            }
    MAX-ACCESS read-write
    STATUS     current
    DESCRIPTION
            "Network-Type"
    ::= { hmSetupWlanMngmtApConf11u11u-NwEntry 5 }

-- {COLUMN} 1.3.6.1.4.1.248.32.18.2.37.1.17.1.1.6
hmSetupWlanMngmtApConf11u11u-NwEntryAsra OBJECT-TYPE
    SYNTAX     INTEGER {
                  eNo (0),
                  eYes (1)
            }
    MAX-ACCESS read-write
    STATUS     current
    DESCRIPTION
            "Asra"
    ::= { hmSetupWlanMngmtApConf11u11u-NwEntry 6 }

-- {COLUMN} 1.3.6.1.4.1.248.32.18.2.37.1.17.1.1.7
hmSetupWlanMngmtApConf11u11u-NwEntryHESSIDT OBJECT-TYPE
    SYNTAX     INTEGER {
                  eAuto (0),
                  eUser (1),
                  eNone (2)
            }
    MAX-ACCESS read-write
    STATUS     current
    DESCRIPTION
            "HESSID-Type"
    ::= { hmSetupWlanMngmtApConf11u11u-NwEntry 7 }

-- {COLUMN} 1.3.6.1.4.1.248.32.18.2.37.1.17.1.1.8
hmSetupWlanMngmtApConf11u11u-NwEntryHESSIDM OBJECT-TYPE
    SYNTAX     MacAddress
    MAX-ACCESS read-write
    STATUS     current
    DESCRIPTION
            "HESSID-MAC"
    ::= { hmSetupWlanMngmtApConf11u11u-NwEntry 8 }

-- {COLUMN} 1.3.6.1.4.1.248.32.18.2.37.1.17.1.1.10
hmSetupWlanMngmtApConf11u11u-NwEntryANQP-Prof OBJECT-TYPE
    SYNTAX     DisplayString (SIZE(0..32))
    MAX-ACCESS read-write
    STATUS     current
    DESCRIPTION
            "ANQP-Profile"
    ::= { hmSetupWlanMngmtApConf11u11u-NwEntry 10 }

-- {COLUMN} 1.3.6.1.4.1.248.32.18.2.37.1.17.1.1.12
hmSetupWlanMngmtApConf11u11u-NwEntryHs20-Prof OBJECT-TYPE
    SYNTAX     DisplayString (SIZE(0..32))
    MAX-ACCESS read-write
    STATUS     current
    DESCRIPTION
            "HS20-Profile"
    ::= { hmSetupWlanMngmtApConf11u11u-NwEntry 12 }

-- {TABLE} 1.3.6.1.4.1.248.32.18.2.37.1.17.2
hmSetupWlanMngmtApConf11uANQP-ProfsTable OBJECT-TYPE
    SYNTAX     SEQUENCE OF HmSetupWlanMngmtApConf11uANQP-ProfsEntry
    MAX-ACCESS not-accessible
    STATUS     current
    DESCRIPTION
            "ANQP-Profiles"
    ::= { hmSetupWlanMngmtApConf11u 2 }

-- {ROW} 1.3.6.1.4.1.248.32.18.2.37.1.17.2.1
hmSetupWlanMngmtApConf11uANQP-ProfsEntry OBJECT-TYPE
    SYNTAX     HmSetupWlanMngmtApConf11uANQP-ProfsEntry
    MAX-ACCESS not-accessible
    STATUS     current
    DESCRIPTION
            ""
    INDEX {
            hmSetupWlanMngmtApConf11uANQP-ProfsEntryName
          }
    ::= { hmSetupWlanMngmtApConf11uANQP-ProfsTable 1 }

HmSetupWlanMngmtApConf11uANQP-ProfsEntry ::= SEQUENCE {
            hmSetupWlanMngmtApConf11uANQP-ProfsEntryName DisplayString,
            hmSetupWlanMngmtApConf11uANQP-ProfsEntryIncOUI DisplayString,
            hmSetupWlanMngmtApConf11uANQP-ProfsEntryAddOUI DisplayString,
            hmSetupWlanMngmtApConf11uANQP-ProfsEntryDomainList DisplayString,
            hmSetupWlanMngmtApConf11uANQP-ProfsEntryNaiRealmList DisplayString,
            hmSetupWlanMngmtApConf11uANQP-ProfsEntryCellularList DisplayString,
            hmSetupWlanMngmtApConf11uANQP-ProfsEntryNetList DisplayString
    }

-- {COLUMN} 1.3.6.1.4.1.248.32.18.2.37.1.17.2.1.1
hmSetupWlanMngmtApConf11uANQP-ProfsEntryName OBJECT-TYPE
    SYNTAX     DisplayString (SIZE(0..32))
    MAX-ACCESS read-write
    STATUS     current
    DESCRIPTION
            "-- empty --"
    ::= { hmSetupWlanMngmtApConf11uANQP-ProfsEntry 1 }

-- {COLUMN} 1.3.6.1.4.1.248.32.18.2.37.1.17.2.1.2
hmSetupWlanMngmtApConf11uANQP-ProfsEntryIncOUI OBJECT-TYPE
    SYNTAX     DisplayString (SIZE(0..65))
    MAX-ACCESS read-write
    STATUS     current
    DESCRIPTION
            "Include-in-Beacon-OUI"
    ::= { hmSetupWlanMngmtApConf11uANQP-ProfsEntry 2 }

-- {COLUMN} 1.3.6.1.4.1.248.32.18.2.37.1.17.2.1.3
hmSetupWlanMngmtApConf11uANQP-ProfsEntryAddOUI OBJECT-TYPE
    SYNTAX     DisplayString (SIZE(0..65))
    MAX-ACCESS read-write
    STATUS     current
    DESCRIPTION
            "Additional-OUI"
    ::= { hmSetupWlanMngmtApConf11uANQP-ProfsEntry 3 }

-- {COLUMN} 1.3.6.1.4.1.248.32.18.2.37.1.17.2.1.4
hmSetupWlanMngmtApConf11uANQP-ProfsEntryDomainList OBJECT-TYPE
    SYNTAX     DisplayString (SIZE(0..65))
    MAX-ACCESS read-write
    STATUS     current
    DESCRIPTION
            "-- empty --"
    ::= { hmSetupWlanMngmtApConf11uANQP-ProfsEntry 4 }

-- {COLUMN} 1.3.6.1.4.1.248.32.18.2.37.1.17.2.1.5
hmSetupWlanMngmtApConf11uANQP-ProfsEntryNaiRealmList OBJECT-TYPE
    SYNTAX     DisplayString (SIZE(0..65))
    MAX-ACCESS read-write
    STATUS     current
    DESCRIPTION
            "-- empty --"
    ::= { hmSetupWlanMngmtApConf11uANQP-ProfsEntry 5 }

-- {COLUMN} 1.3.6.1.4.1.248.32.18.2.37.1.17.2.1.6
hmSetupWlanMngmtApConf11uANQP-ProfsEntryCellularList OBJECT-TYPE
    SYNTAX     DisplayString (SIZE(0..65))
    MAX-ACCESS read-write
    STATUS     current
    DESCRIPTION
            "-- empty --"
    ::= { hmSetupWlanMngmtApConf11uANQP-ProfsEntry 6 }

-- {COLUMN} 1.3.6.1.4.1.248.32.18.2.37.1.17.2.1.7
hmSetupWlanMngmtApConf11uANQP-ProfsEntryNetList OBJECT-TYPE
    SYNTAX     DisplayString (SIZE(0..65))
    MAX-ACCESS read-write
    STATUS     current
    DESCRIPTION
            "Network-Auth-Type-List"
    ::= { hmSetupWlanMngmtApConf11uANQP-ProfsEntry 7 }

-- {TABLE} 1.3.6.1.4.1.248.32.18.2.37.1.17.3
hmSetupWlanMngmtApConf11uHs20-ProfsTable OBJECT-TYPE
    SYNTAX     SEQUENCE OF HmSetupWlanMngmtApConf11uHs20-ProfsEntry
    MAX-ACCESS not-accessible
    STATUS     current
    DESCRIPTION
            "Hotspot2.0-Profiles"
    ::= { hmSetupWlanMngmtApConf11u 3 }

-- {ROW} 1.3.6.1.4.1.248.32.18.2.37.1.17.3.1
hmSetupWlanMngmtApConf11uHs20-ProfsEntry OBJECT-TYPE
    SYNTAX     HmSetupWlanMngmtApConf11uHs20-ProfsEntry
    MAX-ACCESS not-accessible
    STATUS     current
    DESCRIPTION
            ""
    INDEX {
            hmSetupWlanMngmtApConf11uHs20-ProfsEntryName
          }
    ::= { hmSetupWlanMngmtApConf11uHs20-ProfsTable 1 }

HmSetupWlanMngmtApConf11uHs20-ProfsEntry ::= SEQUENCE {
            hmSetupWlanMngmtApConf11uHs20-ProfsEntryName DisplayString,
            hmSetupWlanMngmtApConf11uHs20-ProfsEntryOperatorName DisplayString,
            hmSetupWlanMngmtApConf11uHs20-ProfsEntryConnCaps DisplayString,
            hmSetupWlanMngmtApConf11uHs20-ProfsEntryOpClass DisplayString
    }

-- {COLUMN} 1.3.6.1.4.1.248.32.18.2.37.1.17.3.1.1
hmSetupWlanMngmtApConf11uHs20-ProfsEntryName OBJECT-TYPE
    SYNTAX     DisplayString (SIZE(0..32))
    MAX-ACCESS read-write
    STATUS     current
    DESCRIPTION
            "-- empty --"
    ::= { hmSetupWlanMngmtApConf11uHs20-ProfsEntry 1 }

-- {COLUMN} 1.3.6.1.4.1.248.32.18.2.37.1.17.3.1.2
hmSetupWlanMngmtApConf11uHs20-ProfsEntryOperatorName OBJECT-TYPE
    SYNTAX     DisplayString (SIZE(0..65))
    MAX-ACCESS read-write
    STATUS     current
    DESCRIPTION
            "-- empty --"
    ::= { hmSetupWlanMngmtApConf11uHs20-ProfsEntry 2 }

-- {COLUMN} 1.3.6.1.4.1.248.32.18.2.37.1.17.3.1.3
hmSetupWlanMngmtApConf11uHs20-ProfsEntryConnCaps OBJECT-TYPE
    SYNTAX     DisplayString (SIZE(0..250))
    MAX-ACCESS read-write
    STATUS     current
    DESCRIPTION
            "Connection-Capabilities"
    ::= { hmSetupWlanMngmtApConf11uHs20-ProfsEntry 3 }

-- {COLUMN} 1.3.6.1.4.1.248.32.18.2.37.1.17.3.1.4
hmSetupWlanMngmtApConf11uHs20-ProfsEntryOpClass OBJECT-TYPE
    SYNTAX     DisplayString (SIZE(0..32))
    MAX-ACCESS read-write
    STATUS     current
    DESCRIPTION
            "Operating-Class"
    ::= { hmSetupWlanMngmtApConf11uHs20-ProfsEntry 4 }

-- {TABLE} 1.3.6.1.4.1.248.32.18.2.37.1.17.4
hmSetupWlanMngmtApConf11uNetAuthTable OBJECT-TYPE
    SYNTAX     SEQUENCE OF HmSetupWlanMngmtApConf11uNetAuthEntry
    MAX-ACCESS not-accessible
    STATUS     current
    DESCRIPTION
            "Network-Authentication-Type"
    ::= { hmSetupWlanMngmtApConf11u 4 }

-- {ROW} 1.3.6.1.4.1.248.32.18.2.37.1.17.4.1
hmSetupWlanMngmtApConf11uNetAuthEntry OBJECT-TYPE
    SYNTAX     HmSetupWlanMngmtApConf11uNetAuthEntry
    MAX-ACCESS not-accessible
    STATUS     current
    DESCRIPTION
            ""
    INDEX {
            hmSetupWlanMngmtApConf11uNetAuthEntryName
          }
    ::= { hmSetupWlanMngmtApConf11uNetAuthTable 1 }

HmSetupWlanMngmtApConf11uNetAuthEntry ::= SEQUENCE {
            hmSetupWlanMngmtApConf11uNetAuthEntryName DisplayString,
            hmSetupWlanMngmtApConf11uNetAuthEntryNetType INTEGER,
            hmSetupWlanMngmtApConf11uNetAuthEntryReUrl DisplayString
    }

-- {COLUMN} 1.3.6.1.4.1.248.32.18.2.37.1.17.4.1.1
hmSetupWlanMngmtApConf11uNetAuthEntryName OBJECT-TYPE
    SYNTAX     DisplayString (SIZE(0..32))
    MAX-ACCESS read-write
    STATUS     current
    DESCRIPTION
            "-- empty --"
    ::= { hmSetupWlanMngmtApConf11uNetAuthEntry 1 }

-- {COLUMN} 1.3.6.1.4.1.248.32.18.2.37.1.17.4.1.2
hmSetupWlanMngmtApConf11uNetAuthEntryNetType OBJECT-TYPE
    SYNTAX     INTEGER {
                  eAcceptTermsCond (0),
                  eOnlineEnrollment (1),
                  eHttpRedirection (2),
                  eDnsRedirection (3)
            }
    MAX-ACCESS read-write
    STATUS     current
    DESCRIPTION
            "Network-Auth-Type"
    ::= { hmSetupWlanMngmtApConf11uNetAuthEntry 2 }

-- {COLUMN} 1.3.6.1.4.1.248.32.18.2.37.1.17.4.1.3
hmSetupWlanMngmtApConf11uNetAuthEntryReUrl OBJECT-TYPE
    SYNTAX     DisplayString (SIZE(0..65))
    MAX-ACCESS read-write
    STATUS     current
    DESCRIPTION
            "Redirect-URL"
    ::= { hmSetupWlanMngmtApConf11uNetAuthEntry 3 }

-- {TABLE} 1.3.6.1.4.1.248.32.18.2.37.1.17.5
hmSetupWlanMngmtApConf11uCellListTable OBJECT-TYPE
    SYNTAX     SEQUENCE OF HmSetupWlanMngmtApConf11uCellListEntry
    MAX-ACCESS not-accessible
    STATUS     current
    DESCRIPTION
            "Cellular-Network-Information-List"
    ::= { hmSetupWlanMngmtApConf11u 5 }

-- {ROW} 1.3.6.1.4.1.248.32.18.2.37.1.17.5.1
hmSetupWlanMngmtApConf11uCellListEntry OBJECT-TYPE
    SYNTAX     HmSetupWlanMngmtApConf11uCellListEntry
    MAX-ACCESS not-accessible
    STATUS     current
    DESCRIPTION
            ""
    INDEX {
            hmSetupWlanMngmtApConf11uCellListEntryName
          }
    ::= { hmSetupWlanMngmtApConf11uCellListTable 1 }

HmSetupWlanMngmtApConf11uCellListEntry ::= SEQUENCE {
            hmSetupWlanMngmtApConf11uCellListEntryName DisplayString,
            hmSetupWlanMngmtApConf11uCellListEntryCountry DisplayString,
            hmSetupWlanMngmtApConf11uCellListEntryNetwork DisplayString
    }

-- {COLUMN} 1.3.6.1.4.1.248.32.18.2.37.1.17.5.1.1
hmSetupWlanMngmtApConf11uCellListEntryName OBJECT-TYPE
    SYNTAX     DisplayString (SIZE(0..32))
    MAX-ACCESS read-write
    STATUS     current
    DESCRIPTION
            "-- empty --"
    ::= { hmSetupWlanMngmtApConf11uCellListEntry 1 }

-- {COLUMN} 1.3.6.1.4.1.248.32.18.2.37.1.17.5.1.2
hmSetupWlanMngmtApConf11uCellListEntryCountry OBJECT-TYPE
    SYNTAX     DisplayString (SIZE(0..3))
    MAX-ACCESS read-write
    STATUS     current
    DESCRIPTION
            "Country-Code"
    ::= { hmSetupWlanMngmtApConf11uCellListEntry 2 }

-- {COLUMN} 1.3.6.1.4.1.248.32.18.2.37.1.17.5.1.3
hmSetupWlanMngmtApConf11uCellListEntryNetwork OBJECT-TYPE
    SYNTAX     DisplayString (SIZE(0..3))
    MAX-ACCESS read-write
    STATUS     current
    DESCRIPTION
            "Network-Code"
    ::= { hmSetupWlanMngmtApConf11uCellListEntry 3 }

-- {TABLE} 1.3.6.1.4.1.248.32.18.2.37.1.17.6
hmSetupWlanMngmtApConf11uVenueNameTable OBJECT-TYPE
    SYNTAX     SEQUENCE OF HmSetupWlanMngmtApConf11uVenueNameEntry
    MAX-ACCESS not-accessible
    STATUS     current
    DESCRIPTION
            "-- empty --"
    ::= { hmSetupWlanMngmtApConf11u 6 }

-- {ROW} 1.3.6.1.4.1.248.32.18.2.37.1.17.6.1
hmSetupWlanMngmtApConf11uVenueNameEntry OBJECT-TYPE
    SYNTAX     HmSetupWlanMngmtApConf11uVenueNameEntry
    MAX-ACCESS not-accessible
    STATUS     current
    DESCRIPTION
            ""
    INDEX {
            hmSetupWlanMngmtApConf11uVenueNameEntryName,
            hmSetupWlanMngmtApConf11uVenueNameEntryLanguage
          }
    ::= { hmSetupWlanMngmtApConf11uVenueNameTable 1 }

HmSetupWlanMngmtApConf11uVenueNameEntry ::= SEQUENCE {
            hmSetupWlanMngmtApConf11uVenueNameEntryName DisplayString,
            hmSetupWlanMngmtApConf11uVenueNameEntryLanguage INTEGER,
            hmSetupWlanMngmtApConf11uVenueNameEntryVenueName DisplayString
    }

-- {COLUMN} 1.3.6.1.4.1.248.32.18.2.37.1.17.6.1.1
hmSetupWlanMngmtApConf11uVenueNameEntryName OBJECT-TYPE
    SYNTAX     DisplayString (SIZE(0..32))
    MAX-ACCESS read-write
    STATUS     current
    DESCRIPTION
            "-- empty --"
    ::= { hmSetupWlanMngmtApConf11uVenueNameEntry 1 }

-- {COLUMN} 1.3.6.1.4.1.248.32.18.2.37.1.17.6.1.2
hmSetupWlanMngmtApConf11uVenueNameEntryLanguage OBJECT-TYPE
    SYNTAX     INTEGER {
                  eNone (0),
                  eEnglish (1),
                  eGerman (2),
                  eChinese (3),
                  eSpanish (4),
                  eFrench (5),
                  eItalian (6),
                  eRussian (7),
                  eDutch (8),
                  eTurkish (9),
                  ePortuguese (10),
                  ePolish (11),
                  eCzech (12),
                  eArabic (13)
            }
    MAX-ACCESS read-write
    STATUS     current
    DESCRIPTION
            "-- empty --"
    ::= { hmSetupWlanMngmtApConf11uVenueNameEntry 2 }

-- {COLUMN} 1.3.6.1.4.1.248.32.18.2.37.1.17.6.1.3
hmSetupWlanMngmtApConf11uVenueNameEntryVenueName OBJECT-TYPE
    SYNTAX     DisplayString (SIZE(0..65))
    MAX-ACCESS read-write
    STATUS     current
    DESCRIPTION
            "-- empty --"
    ::= { hmSetupWlanMngmtApConf11uVenueNameEntry 3 }

-- {TABLE} 1.3.6.1.4.1.248.32.18.2.37.1.17.7
hmSetupWlanMngmtApConf11uNAIsTable OBJECT-TYPE
    SYNTAX     SEQUENCE OF HmSetupWlanMngmtApConf11uNAIsEntry
    MAX-ACCESS not-accessible
    STATUS     current
    DESCRIPTION
            "NAI-Realms"
    ::= { hmSetupWlanMngmtApConf11u 7 }

-- {ROW} 1.3.6.1.4.1.248.32.18.2.37.1.17.7.1
hmSetupWlanMngmtApConf11uNAIsEntry OBJECT-TYPE
    SYNTAX     HmSetupWlanMngmtApConf11uNAIsEntry
    MAX-ACCESS not-accessible
    STATUS     current
    DESCRIPTION
            ""
    INDEX {
            hmSetupWlanMngmtApConf11uNAIsEntryName
          }
    ::= { hmSetupWlanMngmtApConf11uNAIsTable 1 }

HmSetupWlanMngmtApConf11uNAIsEntry ::= SEQUENCE {
            hmSetupWlanMngmtApConf11uNAIsEntryName DisplayString,
            hmSetupWlanMngmtApConf11uNAIsEntryNaiRealm DisplayString,
            hmSetupWlanMngmtApConf11uNAIsEntryEapMethod INTEGER,
            hmSetupWlanMngmtApConf11uNAIsEntryAuthPar DisplayString
    }

-- {COLUMN} 1.3.6.1.4.1.248.32.18.2.37.1.17.7.1.1
hmSetupWlanMngmtApConf11uNAIsEntryName OBJECT-TYPE
    SYNTAX     DisplayString (SIZE(0..32))
    MAX-ACCESS read-write
    STATUS     current
    DESCRIPTION
            "-- empty --"
    ::= { hmSetupWlanMngmtApConf11uNAIsEntry 1 }

-- {COLUMN} 1.3.6.1.4.1.248.32.18.2.37.1.17.7.1.2
hmSetupWlanMngmtApConf11uNAIsEntryNaiRealm OBJECT-TYPE
    SYNTAX     DisplayString (SIZE(0..32))
    MAX-ACCESS read-write
    STATUS     current
    DESCRIPTION
            "-- empty --"
    ::= { hmSetupWlanMngmtApConf11uNAIsEntry 2 }

-- {COLUMN} 1.3.6.1.4.1.248.32.18.2.37.1.17.7.1.3
hmSetupWlanMngmtApConf11uNAIsEntryEapMethod OBJECT-TYPE
    SYNTAX     INTEGER {
                  eNone (0),
                  eEapTls (13),
                  eEapSim (18),
                  eEapTtls (21),
                  eEapAka (23)
            }
    MAX-ACCESS read-write
    STATUS     current
    DESCRIPTION
            "-- empty --"
    ::= { hmSetupWlanMngmtApConf11uNAIsEntry 3 }

-- {COLUMN} 1.3.6.1.4.1.248.32.18.2.37.1.17.7.1.4
hmSetupWlanMngmtApConf11uNAIsEntryAuthPar OBJECT-TYPE
    SYNTAX     DisplayString (SIZE(0..65))
    MAX-ACCESS read-write
    STATUS     current
    DESCRIPTION
            "Auth-Parameter-List"
    ::= { hmSetupWlanMngmtApConf11uNAIsEntry 4 }

-- {TABLE} 1.3.6.1.4.1.248.32.18.2.37.1.17.8
hmSetupWlanMngmtApConf11uOperatorListTable OBJECT-TYPE
    SYNTAX     SEQUENCE OF HmSetupWlanMngmtApConf11uOperatorListEntry
    MAX-ACCESS not-accessible
    STATUS     current
    DESCRIPTION
            "-- empty --"
    ::= { hmSetupWlanMngmtApConf11u 8 }

-- {ROW} 1.3.6.1.4.1.248.32.18.2.37.1.17.8.1
hmSetupWlanMngmtApConf11uOperatorListEntry OBJECT-TYPE
    SYNTAX     HmSetupWlanMngmtApConf11uOperatorListEntry
    MAX-ACCESS not-accessible
    STATUS     current
    DESCRIPTION
            ""
    INDEX {
            hmSetupWlanMngmtApConf11uOperatorListEntryName,
            hmSetupWlanMngmtApConf11uOperatorListEntryLanguage
          }
    ::= { hmSetupWlanMngmtApConf11uOperatorListTable 1 }

HmSetupWlanMngmtApConf11uOperatorListEntry ::= SEQUENCE {
            hmSetupWlanMngmtApConf11uOperatorListEntryName DisplayString,
            hmSetupWlanMngmtApConf11uOperatorListEntryLanguage INTEGER,
            hmSetupWlanMngmtApConf11uOperatorListEntryOperatorName DisplayString
    }

-- {COLUMN} 1.3.6.1.4.1.248.32.18.2.37.1.17.8.1.1
hmSetupWlanMngmtApConf11uOperatorListEntryName OBJECT-TYPE
    SYNTAX     DisplayString (SIZE(0..32))
    MAX-ACCESS read-write
    STATUS     current
    DESCRIPTION
            "-- empty --"
    ::= { hmSetupWlanMngmtApConf11uOperatorListEntry 1 }

-- {COLUMN} 1.3.6.1.4.1.248.32.18.2.37.1.17.8.1.2
hmSetupWlanMngmtApConf11uOperatorListEntryLanguage OBJECT-TYPE
    SYNTAX     INTEGER {
                  eNone (0),
                  eEnglish (1),
                  eGerman (2),
                  eChinese (3),
                  eSpanish (4),
                  eFrench (5),
                  eItalian (6),
                  eRussian (7),
                  eDutch (8),
                  eTurkish (9),
                  ePortuguese (10),
                  ePolish (11),
                  eCzech (12),
                  eArabic (13)
            }
    MAX-ACCESS read-write
    STATUS     current
    DESCRIPTION
            "-- empty --"
    ::= { hmSetupWlanMngmtApConf11uOperatorListEntry 2 }

-- {COLUMN} 1.3.6.1.4.1.248.32.18.2.37.1.17.8.1.3
hmSetupWlanMngmtApConf11uOperatorListEntryOperatorName OBJECT-TYPE
    SYNTAX     DisplayString (SIZE(0..65))
    MAX-ACCESS read-write
    STATUS     current
    DESCRIPTION
            "-- empty --"
    ::= { hmSetupWlanMngmtApConf11uOperatorListEntry 3 }

-- {TABLE} 1.3.6.1.4.1.248.32.18.2.37.1.17.9
hmSetupWlanMngmtApConf11uGeneralTable OBJECT-TYPE
    SYNTAX     SEQUENCE OF HmSetupWlanMngmtApConf11uGeneralEntry
    MAX-ACCESS not-accessible
    STATUS     current
    DESCRIPTION
            "-- empty --"
    ::= { hmSetupWlanMngmtApConf11u 9 }

-- {ROW} 1.3.6.1.4.1.248.32.18.2.37.1.17.9.1
hmSetupWlanMngmtApConf11uGeneralEntry OBJECT-TYPE
    SYNTAX     HmSetupWlanMngmtApConf11uGeneralEntry
    MAX-ACCESS not-accessible
    STATUS     current
    DESCRIPTION
            ""
    INDEX {
            hmSetupWlanMngmtApConf11uGeneralEntryName
          }
    ::= { hmSetupWlanMngmtApConf11uGeneralTable 1 }

HmSetupWlanMngmtApConf11uGeneralEntry ::= SEQUENCE {
            hmSetupWlanMngmtApConf11uGeneralEntryName DisplayString,
            hmSetupWlanMngmtApConf11uGeneralEntryLinkStatus INTEGER,
            hmSetupWlanMngmtApConf11uGeneralEntryDownlinkSpeed Integer32,
            hmSetupWlanMngmtApConf11uGeneralEntryUplinkSpeed Integer32,
            hmSetupWlanMngmtApConf11uGeneralEntryIpv4AddrType INTEGER,
            hmSetupWlanMngmtApConf11uGeneralEntryIpv6AddrType INTEGER,
            hmSetupWlanMngmtApConf11uGeneralEntryVenueGroup INTEGER,
            hmSetupWlanMngmtApConf11uGeneralEntryVenueType Integer32,
            hmSetupWlanMngmtApConf11uGeneralEntryVenueName DisplayString
    }

-- {COLUMN} 1.3.6.1.4.1.248.32.18.2.37.1.17.9.1.1
hmSetupWlanMngmtApConf11uGeneralEntryName OBJECT-TYPE
    SYNTAX     DisplayString (SIZE(0..32))
    MAX-ACCESS read-write
    STATUS     current
    DESCRIPTION
            "-- empty --"
    ::= { hmSetupWlanMngmtApConf11uGeneralEntry 1 }

-- {COLUMN} 1.3.6.1.4.1.248.32.18.2.37.1.17.9.1.2
hmSetupWlanMngmtApConf11uGeneralEntryLinkStatus OBJECT-TYPE
    SYNTAX     INTEGER {
                  eAuto (0),
                  eLinkUp (1),
                  eLinkDown (2),
                  eLinkTest (3)
            }
    MAX-ACCESS read-write
    STATUS     current
    DESCRIPTION
            "-- empty --"
    ::= { hmSetupWlanMngmtApConf11uGeneralEntry 2 }

-- {COLUMN} 1.3.6.1.4.1.248.32.18.2.37.1.17.9.1.3
hmSetupWlanMngmtApConf11uGeneralEntryDownlinkSpeed OBJECT-TYPE
    SYNTAX     Integer32 (0..2147483647)
    MAX-ACCESS read-write
    STATUS     current
    DESCRIPTION
            "-- empty --"
    ::= { hmSetupWlanMngmtApConf11uGeneralEntry 3 }

-- {COLUMN} 1.3.6.1.4.1.248.32.18.2.37.1.17.9.1.4
hmSetupWlanMngmtApConf11uGeneralEntryUplinkSpeed OBJECT-TYPE
    SYNTAX     Integer32 (0..2147483647)
    MAX-ACCESS read-write
    STATUS     current
    DESCRIPTION
            "-- empty --"
    ::= { hmSetupWlanMngmtApConf11uGeneralEntry 4 }

-- {COLUMN} 1.3.6.1.4.1.248.32.18.2.37.1.17.9.1.5
hmSetupWlanMngmtApConf11uGeneralEntryIpv4AddrType OBJECT-TYPE
    SYNTAX     INTEGER {
                  eNotAvailable (0),
                  ePublicAddrAvailable (1),
                  ePortRestrAddrAvail (2),
                  eSingleNatPrivAddrAvail (3),
                  eDoubleNatPrivAddrAvail (4),
                  ePortRestrSingleNatAddrAvail (5),
                  ePortRestrDoubleNatAddrAvail (6),
                  eAvailabilityNotKnown (7)
            }
    MAX-ACCESS read-write
    STATUS     current
    DESCRIPTION
            "-- empty --"
    ::= { hmSetupWlanMngmtApConf11uGeneralEntry 5 }

-- {COLUMN} 1.3.6.1.4.1.248.32.18.2.37.1.17.9.1.6
hmSetupWlanMngmtApConf11uGeneralEntryIpv6AddrType OBJECT-TYPE
    SYNTAX     INTEGER {
                  eNotAvailable (0),
                  eAvailable (1),
                  eAvailabilityNotKnown (2)
            }
    MAX-ACCESS read-write
    STATUS     current
    DESCRIPTION
            "-- empty --"
    ::= { hmSetupWlanMngmtApConf11uGeneralEntry 6 }

-- {COLUMN} 1.3.6.1.4.1.248.32.18.2.37.1.17.9.1.7
hmSetupWlanMngmtApConf11uGeneralEntryVenueGroup OBJECT-TYPE
    SYNTAX     INTEGER {
                  eUnspecified (0),
                  eAssembly (1),
                  eBusiness (2),
                  eEducational (3),
                  eFactoryAndIndustrial (4),
                  eInstitutional (5),
                  eMercantile (6),
                  eResindential (7),
                  eStorage (8),
                  eUtilityAndMiscellaneous (9),
                  eVehicular (10),
                  eOutdoor (11)
            }
    MAX-ACCESS read-write
    STATUS     current
    DESCRIPTION
            "-- empty --"
    ::= { hmSetupWlanMngmtApConf11uGeneralEntry 7 }

-- {COLUMN} 1.3.6.1.4.1.248.32.18.2.37.1.17.9.1.8
hmSetupWlanMngmtApConf11uGeneralEntryVenueType OBJECT-TYPE
    SYNTAX     Integer32 (0..255)
    MAX-ACCESS read-write
    STATUS     current
    DESCRIPTION
            "-- empty --"
    ::= { hmSetupWlanMngmtApConf11uGeneralEntry 8 }

-- {COLUMN} 1.3.6.1.4.1.248.32.18.2.37.1.17.9.1.9
hmSetupWlanMngmtApConf11uGeneralEntryVenueName OBJECT-TYPE
    SYNTAX     DisplayString (SIZE(0..32))
    MAX-ACCESS read-write
    STATUS     current
    DESCRIPTION
            "-- empty --"
    ::= { hmSetupWlanMngmtApConf11uGeneralEntry 9 }

-- {TABLE} 1.3.6.1.4.1.248.32.18.2.37.1.17.10
hmSetupWlanMngmtApConf11uAuthParameterTable OBJECT-TYPE
    SYNTAX     SEQUENCE OF HmSetupWlanMngmtApConf11uAuthParameterEntry
    MAX-ACCESS not-accessible
    STATUS     current
    DESCRIPTION
            "-- empty --"
    ::= { hmSetupWlanMngmtApConf11u 10 }

-- {ROW} 1.3.6.1.4.1.248.32.18.2.37.1.17.10.1
hmSetupWlanMngmtApConf11uAuthParameterEntry OBJECT-TYPE
    SYNTAX     HmSetupWlanMngmtApConf11uAuthParameterEntry
    MAX-ACCESS not-accessible
    STATUS     current
    DESCRIPTION
            ""
    INDEX {
            hmSetupWlanMngmtApConf11uAuthParameterEntryName
          }
    ::= { hmSetupWlanMngmtApConf11uAuthParameterTable 1 }

HmSetupWlanMngmtApConf11uAuthParameterEntry ::= SEQUENCE {
            hmSetupWlanMngmtApConf11uAuthParameterEntryName DisplayString
    }

-- {COLUMN} 1.3.6.1.4.1.248.32.18.2.37.1.17.10.1.1
hmSetupWlanMngmtApConf11uAuthParameterEntryName OBJECT-TYPE
    SYNTAX     DisplayString (SIZE(0..32))
    MAX-ACCESS read-only
    STATUS     current
    DESCRIPTION
            "-- empty --"
    ::= { hmSetupWlanMngmtApConf11uAuthParameterEntry 1 }

-- {TABLE} 1.3.6.1.4.1.248.32.18.2.37.1.17.11
hmSetupWlanMngmtApConf11uConnCapTable OBJECT-TYPE
    SYNTAX     SEQUENCE OF HmSetupWlanMngmtApConf11uConnCapEntry
    MAX-ACCESS not-accessible
    STATUS     current
    DESCRIPTION
            "Connection-Capability"
    ::= { hmSetupWlanMngmtApConf11u 11 }

-- {ROW} 1.3.6.1.4.1.248.32.18.2.37.1.17.11.1
hmSetupWlanMngmtApConf11uConnCapEntry OBJECT-TYPE
    SYNTAX     HmSetupWlanMngmtApConf11uConnCapEntry
    MAX-ACCESS not-accessible
    STATUS     current
    DESCRIPTION
            ""
    INDEX {
            hmSetupWlanMngmtApConf11uConnCapEntryName
          }
    ::= { hmSetupWlanMngmtApConf11uConnCapTable 1 }

HmSetupWlanMngmtApConf11uConnCapEntry ::= SEQUENCE {
            hmSetupWlanMngmtApConf11uConnCapEntryName DisplayString
    }

-- {COLUMN} 1.3.6.1.4.1.248.32.18.2.37.1.17.11.1.1
hmSetupWlanMngmtApConf11uConnCapEntryName OBJECT-TYPE
    SYNTAX     DisplayString (SIZE(0..32))
    MAX-ACCESS read-only
    STATUS     current
    DESCRIPTION
            "-- empty --"
    ::= { hmSetupWlanMngmtApConf11uConnCapEntry 1 }

-- {TABLE} 1.3.6.1.4.1.248.32.18.2.37.1.18
hmSetupWlanMngmtApConfGroupsTable OBJECT-TYPE
    SYNTAX     SEQUENCE OF HmSetupWlanMngmtApConfGroupsEntry
    MAX-ACCESS not-accessible
    STATUS     current
    DESCRIPTION
            "-- empty --"
    ::= { hmSetupWlanMngmtApConf 18 }

-- {ROW} 1.3.6.1.4.1.248.32.18.2.37.1.18.1
hmSetupWlanMngmtApConfGroupsEntry OBJECT-TYPE
    SYNTAX     HmSetupWlanMngmtApConfGroupsEntry
    MAX-ACCESS not-accessible
    STATUS     current
    DESCRIPTION
            ""
    INDEX {
            hmSetupWlanMngmtApConfGroupsEntryName
          }
    ::= { hmSetupWlanMngmtApConfGroupsTable 1 }

HmSetupWlanMngmtApConfGroupsEntry ::= SEQUENCE {
            hmSetupWlanMngmtApConfGroupsEntryName DisplayString,
            hmSetupWlanMngmtApConfGroupsEntryProfile DisplayString,
            hmSetupWlanMngmtApConfGroupsEntryApIntranet DisplayString,
            hmSetupWlanMngmtApConfGroupsEntryIpv4ReferencePoolStart DisplayString,
            hmSetupWlanMngmtApConfGroupsEntryIpv4ReferencePoolEnd DisplayString,
            hmSetupWlanMngmtApConfGroupsEntryClientSteeringProfile DisplayString,
            hmSetupWlanMngmtApConfGroupsEntryIbeaconProfile DisplayString
    }

-- {COLUMN} 1.3.6.1.4.1.248.32.18.2.37.1.18.1.1
hmSetupWlanMngmtApConfGroupsEntryName OBJECT-TYPE
    SYNTAX     DisplayString (SIZE(0..31))
    MAX-ACCESS read-write
    STATUS     current
    DESCRIPTION
            "-- empty --"
    ::= { hmSetupWlanMngmtApConfGroupsEntry 1 }

-- {COLUMN} 1.3.6.1.4.1.248.32.18.2.37.1.18.1.2
hmSetupWlanMngmtApConfGroupsEntryProfile OBJECT-TYPE
    SYNTAX     DisplayString (SIZE(0..31))
    MAX-ACCESS read-write
    STATUS     current
    DESCRIPTION
            "-- empty --"
    ::= { hmSetupWlanMngmtApConfGroupsEntry 2 }

-- {COLUMN} 1.3.6.1.4.1.248.32.18.2.37.1.18.1.3
hmSetupWlanMngmtApConfGroupsEntryApIntranet OBJECT-TYPE
    SYNTAX     DisplayString (SIZE(0..31))
    MAX-ACCESS read-write
    STATUS     current
    DESCRIPTION
            "-- empty --"
    ::= { hmSetupWlanMngmtApConfGroupsEntry 3 }

-- {COLUMN} 1.3.6.1.4.1.248.32.18.2.37.1.18.1.4
hmSetupWlanMngmtApConfGroupsEntryIpv4ReferencePoolStart OBJECT-TYPE
    SYNTAX     DisplayString (SIZE(0..15))
    MAX-ACCESS read-write
    STATUS     current
    DESCRIPTION
            "-- empty --"
    ::= { hmSetupWlanMngmtApConfGroupsEntry 4 }

-- {COLUMN} 1.3.6.1.4.1.248.32.18.2.37.1.18.1.5
hmSetupWlanMngmtApConfGroupsEntryIpv4ReferencePoolEnd OBJECT-TYPE
    SYNTAX     DisplayString (SIZE(0..15))
    MAX-ACCESS read-write
    STATUS     current
    DESCRIPTION
            "-- empty --"
    ::= { hmSetupWlanMngmtApConfGroupsEntry 5 }

-- {COLUMN} 1.3.6.1.4.1.248.32.18.2.37.1.18.1.6
hmSetupWlanMngmtApConfGroupsEntryClientSteeringProfile OBJECT-TYPE
    SYNTAX     DisplayString (SIZE(0..31))
    MAX-ACCESS read-write
    STATUS     current
    DESCRIPTION
            "-- empty --"
    ::= { hmSetupWlanMngmtApConfGroupsEntry 6 }

-- {COLUMN} 1.3.6.1.4.1.248.32.18.2.37.1.18.1.7
hmSetupWlanMngmtApConfGroupsEntryIbeaconProfile OBJECT-TYPE
    SYNTAX     DisplayString (SIZE(0..31))
    MAX-ACCESS read-write
    STATUS     current
    DESCRIPTION
            "-- empty --"
    ::= { hmSetupWlanMngmtApConfGroupsEntry 7 }

-- {TABLE} 1.3.6.1.4.1.248.32.18.2.37.1.20
hmSetupWlanMngmtApConfTagGroupsTable OBJECT-TYPE
    SYNTAX     SEQUENCE OF HmSetupWlanMngmtApConfTagGroupsEntry
    MAX-ACCESS not-accessible
    STATUS     current
    DESCRIPTION
            "-- empty --"
    ::= { hmSetupWlanMngmtApConf 20 }

-- {ROW} 1.3.6.1.4.1.248.32.18.2.37.1.20.1
hmSetupWlanMngmtApConfTagGroupsEntry OBJECT-TYPE
    SYNTAX     HmSetupWlanMngmtApConfTagGroupsEntry
    MAX-ACCESS not-accessible
    STATUS     current
    DESCRIPTION
            ""
    INDEX {
            hmSetupWlanMngmtApConfTagGroupsEntryName
          }
    ::= { hmSetupWlanMngmtApConfTagGroupsTable 1 }

HmSetupWlanMngmtApConfTagGroupsEntry ::= SEQUENCE {
            hmSetupWlanMngmtApConfTagGroupsEntryName DisplayString
    }

-- {COLUMN} 1.3.6.1.4.1.248.32.18.2.37.1.20.1.1
hmSetupWlanMngmtApConfTagGroupsEntryName OBJECT-TYPE
    SYNTAX     DisplayString (SIZE(0..31))
    MAX-ACCESS read-write
    STATUS     current
    DESCRIPTION
            "-- empty --"
    ::= { hmSetupWlanMngmtApConfTagGroupsEntry 1 }

-- {TABLE} 1.3.6.1.4.1.248.32.18.2.37.1.21
hmSetupWlanMngmtApConfLedProfilesTable OBJECT-TYPE
    SYNTAX     SEQUENCE OF HmSetupWlanMngmtApConfLedProfilesEntry
    MAX-ACCESS not-accessible
    STATUS     current
    DESCRIPTION
            "-- empty --"
    ::= { hmSetupWlanMngmtApConf 21 }

-- {ROW} 1.3.6.1.4.1.248.32.18.2.37.1.21.1
hmSetupWlanMngmtApConfLedProfilesEntry OBJECT-TYPE
    SYNTAX     HmSetupWlanMngmtApConfLedProfilesEntry
    MAX-ACCESS not-accessible
    STATUS     current
    DESCRIPTION
            ""
    INDEX {
            hmSetupWlanMngmtApConfLedProfilesEntryName
          }
    ::= { hmSetupWlanMngmtApConfLedProfilesTable 1 }

HmSetupWlanMngmtApConfLedProfilesEntry ::= SEQUENCE {
            hmSetupWlanMngmtApConfLedProfilesEntryName DisplayString,
            hmSetupWlanMngmtApConfLedProfilesEntryLedMode INTEGER,
            hmSetupWlanMngmtApConfLedProfilesEntryLedOffSeconds Integer32
    }

-- {COLUMN} 1.3.6.1.4.1.248.32.18.2.37.1.21.1.1
hmSetupWlanMngmtApConfLedProfilesEntryName OBJECT-TYPE
    SYNTAX     DisplayString (SIZE(0..31))
    MAX-ACCESS read-write
    STATUS     current
    DESCRIPTION
            "-- empty --"
    ::= { hmSetupWlanMngmtApConfLedProfilesEntry 1 }

-- {COLUMN} 1.3.6.1.4.1.248.32.18.2.37.1.21.1.4
hmSetupWlanMngmtApConfLedProfilesEntryLedMode OBJECT-TYPE
    SYNTAX     INTEGER {
                  eOn (0),
                  eOff (1),
                  eTimedOff (2)
            }
    MAX-ACCESS read-write
    STATUS     current
    DESCRIPTION
            "-- empty --"
    ::= { hmSetupWlanMngmtApConfLedProfilesEntry 4 }

-- {COLUMN} 1.3.6.1.4.1.248.32.18.2.37.1.21.1.5
hmSetupWlanMngmtApConfLedProfilesEntryLedOffSeconds OBJECT-TYPE
    SYNTAX     Integer32 (0..2147483647)
    MAX-ACCESS read-write
    STATUS     current
    DESCRIPTION
            "-- empty --"
    ::= { hmSetupWlanMngmtApConfLedProfilesEntry 5 }

-- {NODE} 1.3.6.1.4.1.248.32.18.2.37.1.22
hmSetupWlanMngmtApConfLbs OBJECT IDENTIFIER ::= { hmSetupWlanMngmtApConf 22 }

-- {TABLE} 1.3.6.1.4.1.248.32.18.2.37.1.22.1
hmSetupWlanMngmtApConfLbsGeneralTable OBJECT-TYPE
    SYNTAX     SEQUENCE OF HmSetupWlanMngmtApConfLbsGeneralEntry
    MAX-ACCESS not-accessible
    STATUS     current
    DESCRIPTION
            "-- empty --"
    ::= { hmSetupWlanMngmtApConfLbs 1 }

-- {ROW} 1.3.6.1.4.1.248.32.18.2.37.1.22.1.1
hmSetupWlanMngmtApConfLbsGeneralEntry OBJECT-TYPE
    SYNTAX     HmSetupWlanMngmtApConfLbsGeneralEntry
    MAX-ACCESS not-accessible
    STATUS     current
    DESCRIPTION
            ""
    INDEX {
            hmSetupWlanMngmtApConfLbsGeneralEntryName
          }
    ::= { hmSetupWlanMngmtApConfLbsGeneralTable 1 }

HmSetupWlanMngmtApConfLbsGeneralEntry ::= SEQUENCE {
            hmSetupWlanMngmtApConfLbsGeneralEntryName DisplayString,
            hmSetupWlanMngmtApConfLbsGeneralEntryOperating INTEGER,
            hmSetupWlanMngmtApConfLbsGeneralEntryUseTlsConnection INTEGER,
            hmSetupWlanMngmtApConfLbsGeneralEntryLbsServerAddress DisplayString,
            hmSetupWlanMngmtApConfLbsGeneralEntryLbsServerPort Integer32
    }

-- {COLUMN} 1.3.6.1.4.1.248.32.18.2.37.1.22.1.1.1
hmSetupWlanMngmtApConfLbsGeneralEntryName OBJECT-TYPE
    SYNTAX     DisplayString (SIZE(0..31))
    MAX-ACCESS read-write
    STATUS     current
    DESCRIPTION
            "-- empty --"
    ::= { hmSetupWlanMngmtApConfLbsGeneralEntry 1 }

-- {COLUMN} 1.3.6.1.4.1.248.32.18.2.37.1.22.1.1.2
hmSetupWlanMngmtApConfLbsGeneralEntryOperating OBJECT-TYPE
    SYNTAX     INTEGER {
                  eNo (0),
                  eYes (1)
            }
    MAX-ACCESS read-write
    STATUS     current
    DESCRIPTION
            "-- empty --"
    ::= { hmSetupWlanMngmtApConfLbsGeneralEntry 2 }

-- {COLUMN} 1.3.6.1.4.1.248.32.18.2.37.1.22.1.1.3
hmSetupWlanMngmtApConfLbsGeneralEntryUseTlsConnection OBJECT-TYPE
    SYNTAX     INTEGER {
                  eNo (0),
                  eYes (1)
            }
    MAX-ACCESS read-write
    STATUS     current
    DESCRIPTION
            "-- empty --"
    ::= { hmSetupWlanMngmtApConfLbsGeneralEntry 3 }

-- {COLUMN} 1.3.6.1.4.1.248.32.18.2.37.1.22.1.1.4
hmSetupWlanMngmtApConfLbsGeneralEntryLbsServerAddress OBJECT-TYPE
    SYNTAX     DisplayString (SIZE(0..64))
    MAX-ACCESS read-write
    STATUS     current
    DESCRIPTION
            "-- empty --"
    ::= { hmSetupWlanMngmtApConfLbsGeneralEntry 4 }

-- {COLUMN} 1.3.6.1.4.1.248.32.18.2.37.1.22.1.1.5
hmSetupWlanMngmtApConfLbsGeneralEntryLbsServerPort OBJECT-TYPE
    SYNTAX     Integer32 (0..65535)
    MAX-ACCESS read-write
    STATUS     current
    DESCRIPTION
            "-- empty --"
    ::= { hmSetupWlanMngmtApConfLbsGeneralEntry 5 }

-- {TABLE} 1.3.6.1.4.1.248.32.18.2.37.1.22.2
hmSetupWlanMngmtApConfLbsDevLocTable OBJECT-TYPE
    SYNTAX     SEQUENCE OF HmSetupWlanMngmtApConfLbsDevLocEntry
    MAX-ACCESS not-accessible
    STATUS     current
    DESCRIPTION
            ""
    ::= { hmSetupWlanMngmtApConfLbs 2 }

-- {ROW} 1.3.6.1.4.1.248.32.18.2.37.1.22.2.1
hmSetupWlanMngmtApConfLbsDevLocEntry OBJECT-TYPE
    SYNTAX     HmSetupWlanMngmtApConfLbsDevLocEntry
    MAX-ACCESS not-accessible
    STATUS     current
    DESCRIPTION
            ""
    INDEX {
            hmSetupWlanMngmtApConfLbsDevLocEntryName
          }
    ::= { hmSetupWlanMngmtApConfLbsDevLocTable 1 }

HmSetupWlanMngmtApConfLbsDevLocEntry ::= SEQUENCE {
            hmSetupWlanMngmtApConfLbsDevLocEntryName DisplayString,
            hmSetupWlanMngmtApConfLbsDevLocEntryFloor Integer32,
            hmSetupWlanMngmtApConfLbsDevLocEntryHeight Integer32,
            hmSetupWlanMngmtApConfLbsDevLocEntryLatDeg Integer32,
            hmSetupWlanMngmtApConfLbsDevLocEntryLatMin Integer32,
            hmSetupWlanMngmtApConfLbsDevLocEntryLatSec Integer32,
            hmSetupWlanMngmtApConfLbsDevLocEntryLatHemi INTEGER,
            hmSetupWlanMngmtApConfLbsDevLocEntryLongDeg Integer32,
            hmSetupWlanMngmtApConfLbsDevLocEntryLongMin Integer32,
            hmSetupWlanMngmtApConfLbsDevLocEntryLongSec Integer32,
            hmSetupWlanMngmtApConfLbsDevLocEntryLongHemi INTEGER,
            hmSetupWlanMngmtApConfLbsDevLocEntryDescription DisplayString
    }

-- {COLUMN} 1.3.6.1.4.1.248.32.18.2.37.1.22.2.1.1
hmSetupWlanMngmtApConfLbsDevLocEntryName OBJECT-TYPE
    SYNTAX     DisplayString (SIZE(0..31))
    MAX-ACCESS read-write
    STATUS     current
    DESCRIPTION
            "-- empty --"
    ::= { hmSetupWlanMngmtApConfLbsDevLocEntry 1 }

-- {COLUMN} 1.3.6.1.4.1.248.32.18.2.37.1.22.2.1.2
hmSetupWlanMngmtApConfLbsDevLocEntryFloor OBJECT-TYPE
    SYNTAX     Integer32 (-32768..32767)
    MAX-ACCESS read-write
    STATUS     current
    DESCRIPTION
            "-- empty --"
    ::= { hmSetupWlanMngmtApConfLbsDevLocEntry 2 }

-- {COLUMN} 1.3.6.1.4.1.248.32.18.2.37.1.22.2.1.3
hmSetupWlanMngmtApConfLbsDevLocEntryHeight OBJECT-TYPE
    SYNTAX     Integer32 (-32768..32767)
    MAX-ACCESS read-write
    STATUS     current
    DESCRIPTION
            "-- empty --"
    ::= { hmSetupWlanMngmtApConfLbsDevLocEntry 3 }

-- {COLUMN} 1.3.6.1.4.1.248.32.18.2.37.1.22.2.1.4
hmSetupWlanMngmtApConfLbsDevLocEntryLatDeg OBJECT-TYPE
    SYNTAX     Integer32 (0..255)
    MAX-ACCESS read-write
    STATUS     current
    DESCRIPTION
            ""
    ::= { hmSetupWlanMngmtApConfLbsDevLocEntry 4 }

-- {COLUMN} 1.3.6.1.4.1.248.32.18.2.37.1.22.2.1.5
hmSetupWlanMngmtApConfLbsDevLocEntryLatMin OBJECT-TYPE
    SYNTAX     Integer32 (0..255)
    MAX-ACCESS read-write
    STATUS     current
    DESCRIPTION
            ""
    ::= { hmSetupWlanMngmtApConfLbsDevLocEntry 5 }

-- {COLUMN} 1.3.6.1.4.1.248.32.18.2.37.1.22.2.1.6
hmSetupWlanMngmtApConfLbsDevLocEntryLatSec OBJECT-TYPE
    SYNTAX     Integer32 (0..2147483647)
    MAX-ACCESS read-write
    STATUS     current
    DESCRIPTION
            ""
    ::= { hmSetupWlanMngmtApConfLbsDevLocEntry 6 }

-- {COLUMN} 1.3.6.1.4.1.248.32.18.2.37.1.22.2.1.7
hmSetupWlanMngmtApConfLbsDevLocEntryLatHemi OBJECT-TYPE
    SYNTAX     INTEGER {
                  eN (0),
                  eS (1)
            }
    MAX-ACCESS read-write
    STATUS     current
    DESCRIPTION
            ""
    ::= { hmSetupWlanMngmtApConfLbsDevLocEntry 7 }

-- {COLUMN} 1.3.6.1.4.1.248.32.18.2.37.1.22.2.1.8
hmSetupWlanMngmtApConfLbsDevLocEntryLongDeg OBJECT-TYPE
    SYNTAX     Integer32 (0..255)
    MAX-ACCESS read-write
    STATUS     current
    DESCRIPTION
            ""
    ::= { hmSetupWlanMngmtApConfLbsDevLocEntry 8 }

-- {COLUMN} 1.3.6.1.4.1.248.32.18.2.37.1.22.2.1.9
hmSetupWlanMngmtApConfLbsDevLocEntryLongMin OBJECT-TYPE
    SYNTAX     Integer32 (0..255)
    MAX-ACCESS read-write
    STATUS     current
    DESCRIPTION
            ""
    ::= { hmSetupWlanMngmtApConfLbsDevLocEntry 9 }

-- {COLUMN} 1.3.6.1.4.1.248.32.18.2.37.1.22.2.1.10
hmSetupWlanMngmtApConfLbsDevLocEntryLongSec OBJECT-TYPE
    SYNTAX     Integer32 (0..2147483647)
    MAX-ACCESS read-write
    STATUS     current
    DESCRIPTION
            ""
    ::= { hmSetupWlanMngmtApConfLbsDevLocEntry 10 }

-- {COLUMN} 1.3.6.1.4.1.248.32.18.2.37.1.22.2.1.11
hmSetupWlanMngmtApConfLbsDevLocEntryLongHemi OBJECT-TYPE
    SYNTAX     INTEGER {
                  eE (0),
                  eW (1)
            }
    MAX-ACCESS read-write
    STATUS     current
    DESCRIPTION
            ""
    ::= { hmSetupWlanMngmtApConfLbsDevLocEntry 11 }

-- {COLUMN} 1.3.6.1.4.1.248.32.18.2.37.1.22.2.1.12
hmSetupWlanMngmtApConfLbsDevLocEntryDescription OBJECT-TYPE
    SYNTAX     DisplayString (SIZE(0..31))
    MAX-ACCESS read-write
    STATUS     current
    DESCRIPTION
            "-- empty --"
    ::= { hmSetupWlanMngmtApConfLbsDevLocEntry 12 }

-- {TABLE} 1.3.6.1.4.1.248.32.18.2.37.1.23
hmSetupWlanMngmtApConfWirelessEpaperProfileTable OBJECT-TYPE
    SYNTAX     SEQUENCE OF HmSetupWlanMngmtApConfWirelessEpaperProfileEntry
    MAX-ACCESS not-accessible
    STATUS     current
    DESCRIPTION
            "-- empty --"
    ::= { hmSetupWlanMngmtApConf 23 }

-- {ROW} 1.3.6.1.4.1.248.32.18.2.37.1.23.1
hmSetupWlanMngmtApConfWirelessEpaperProfileEntry OBJECT-TYPE
    SYNTAX     HmSetupWlanMngmtApConfWirelessEpaperProfileEntry
    MAX-ACCESS not-accessible
    STATUS     current
    DESCRIPTION
            ""
    INDEX {
            hmSetupWlanMngmtApConfWirelessEpaperProfileEntryName
          }
    ::= { hmSetupWlanMngmtApConfWirelessEpaperProfileTable 1 }

HmSetupWlanMngmtApConfWirelessEpaperProfileEntry ::= SEQUENCE {
            hmSetupWlanMngmtApConfWirelessEpaperProfileEntryName DisplayString,
            hmSetupWlanMngmtApConfWirelessEpaperProfileEntryOperating INTEGER,
            hmSetupWlanMngmtApConfWirelessEpaperProfileEntryPort Integer32
    }

-- {COLUMN} 1.3.6.1.4.1.248.32.18.2.37.1.23.1.1
hmSetupWlanMngmtApConfWirelessEpaperProfileEntryName OBJECT-TYPE
    SYNTAX     DisplayString (SIZE(0..31))
    MAX-ACCESS read-write
    STATUS     current
    DESCRIPTION
            "-- empty --"
    ::= { hmSetupWlanMngmtApConfWirelessEpaperProfileEntry 1 }

-- {COLUMN} 1.3.6.1.4.1.248.32.18.2.37.1.23.1.2
hmSetupWlanMngmtApConfWirelessEpaperProfileEntryOperating OBJECT-TYPE
    SYNTAX     INTEGER {
                  eNo (0),
                  eYes (1)
            }
    MAX-ACCESS read-write
    STATUS     current
    DESCRIPTION
            "-- empty --"
    ::= { hmSetupWlanMngmtApConfWirelessEpaperProfileEntry 2 }

-- {COLUMN} 1.3.6.1.4.1.248.32.18.2.37.1.23.1.3
hmSetupWlanMngmtApConfWirelessEpaperProfileEntryPort OBJECT-TYPE
    SYNTAX     Integer32 (0..65535)
    MAX-ACCESS read-write
    STATUS     current
    DESCRIPTION
            "-- empty --"
    ::= { hmSetupWlanMngmtApConfWirelessEpaperProfileEntry 3 }

-- {TABLE} 1.3.6.1.4.1.248.32.18.2.37.1.24
hmSetupWlanMngmtApConfIbeaconProfileTable OBJECT-TYPE
    SYNTAX     SEQUENCE OF HmSetupWlanMngmtApConfIbeaconProfileEntry
    MAX-ACCESS not-accessible
    STATUS     current
    DESCRIPTION
            "-- empty --"
    ::= { hmSetupWlanMngmtApConf 24 }

-- {ROW} 1.3.6.1.4.1.248.32.18.2.37.1.24.1
hmSetupWlanMngmtApConfIbeaconProfileEntry OBJECT-TYPE
    SYNTAX     HmSetupWlanMngmtApConfIbeaconProfileEntry
    MAX-ACCESS not-accessible
    STATUS     current
    DESCRIPTION
            ""
    INDEX {
            hmSetupWlanMngmtApConfIbeaconProfileEntryName
          }
    ::= { hmSetupWlanMngmtApConfIbeaconProfileTable 1 }

HmSetupWlanMngmtApConfIbeaconProfileEntry ::= SEQUENCE {
            hmSetupWlanMngmtApConfIbeaconProfileEntryName DisplayString,
            hmSetupWlanMngmtApConfIbeaconProfileEntryOperating INTEGER,
            hmSetupWlanMngmtApConfIbeaconProfileEntryMajor Integer32,
            hmSetupWlanMngmtApConfIbeaconProfileEntryUuid DisplayString
    }

-- {COLUMN} 1.3.6.1.4.1.248.32.18.2.37.1.24.1.1
hmSetupWlanMngmtApConfIbeaconProfileEntryName OBJECT-TYPE
    SYNTAX     DisplayString (SIZE(0..31))
    MAX-ACCESS read-write
    STATUS     current
    DESCRIPTION
            "-- empty --"
    ::= { hmSetupWlanMngmtApConfIbeaconProfileEntry 1 }

-- {COLUMN} 1.3.6.1.4.1.248.32.18.2.37.1.24.1.2
hmSetupWlanMngmtApConfIbeaconProfileEntryOperating OBJECT-TYPE
    SYNTAX     INTEGER {
                  eNo (0),
                  eYes (1)
            }
    MAX-ACCESS read-write
    STATUS     current
    DESCRIPTION
            "-- empty --"
    ::= { hmSetupWlanMngmtApConfIbeaconProfileEntry 2 }

-- {COLUMN} 1.3.6.1.4.1.248.32.18.2.37.1.24.1.3
hmSetupWlanMngmtApConfIbeaconProfileEntryMajor OBJECT-TYPE
    SYNTAX     Integer32 (0..65535)
    MAX-ACCESS read-write
    STATUS     current
    DESCRIPTION
            "-- empty --"
    ::= { hmSetupWlanMngmtApConfIbeaconProfileEntry 3 }

-- {COLUMN} 1.3.6.1.4.1.248.32.18.2.37.1.24.1.4
hmSetupWlanMngmtApConfIbeaconProfileEntryUuid OBJECT-TYPE
    SYNTAX     DisplayString (SIZE(0..36))
    MAX-ACCESS read-write
    STATUS     current
    DESCRIPTION
            "-- empty --"
    ::= { hmSetupWlanMngmtApConfIbeaconProfileEntry 4 }

-- {TABLE} 1.3.6.1.4.1.248.32.18.2.37.1.248
hmSetupWlanMngmtApConfWIdsTable OBJECT-TYPE
    SYNTAX     SEQUENCE OF HmSetupWlanMngmtApConfWIdsEntry
    MAX-ACCESS not-accessible
    STATUS     current
    DESCRIPTION
            ""
    ::= { hmSetupWlanMngmtApConf 248 }

-- {ROW} 1.3.6.1.4.1.248.32.18.2.37.1.248.1
hmSetupWlanMngmtApConfWIdsEntry OBJECT-TYPE
    SYNTAX     HmSetupWlanMngmtApConfWIdsEntry
    MAX-ACCESS not-accessible
    STATUS     current
    DESCRIPTION
            ""
    INDEX {
            hmSetupWlanMngmtApConfWIdsEntryName
          }
    ::= { hmSetupWlanMngmtApConfWIdsTable 1 }

HmSetupWlanMngmtApConfWIdsEntry ::= SEQUENCE {
            hmSetupWlanMngmtApConfWIdsEntryName DisplayString,
            hmSetupWlanMngmtApConfWIdsEntryOperating INTEGER,
            hmSetupWlanMngmtApConfWIdsEntryEAPOLStartCtrLim Integer32,
            hmSetupWlanMngmtApConfWIdsEntryEAPOLStartCtrInt Integer32,
            hmSetupWlanMngmtApConfWIdsEntryProbeBroadCtrLim Integer32,
            hmSetupWlanMngmtApConfWIdsEntryProbeBroadCtrInt Integer32,
            hmSetupWlanMngmtApConfWIdsEntryDeauthBroadCtrLimt Integer32,
            hmSetupWlanMngmtApConfWIdsEntryDeauthBroadCtrInt Integer32,
            hmSetupWlanMngmtApConfWIdsEntryDeauthCtrLim Integer32,
            hmSetupWlanMngmtApConfWIdsEntryDeauthCtrInt Integer32,
            hmSetupWlanMngmtApConfWIdsEntryAssocReqCtrLim Integer32,
            hmSetupWlanMngmtApConfWIdsEntryAssocReqCtrInt Integer32,
            hmSetupWlanMngmtApConfWIdsEntryReAssocReqCtrLim Integer32,
            hmSetupWlanMngmtApConfWIdsEntryReAssocReqCtrInt Integer32,
            hmSetupWlanMngmtApConfWIdsEntryAuthCtrLim Integer32,
            hmSetupWlanMngmtApConfWIdsEntryAuthCtrInt Integer32,
            hmSetupWlanMngmtApConfWIdsEntryDisAssocCtrLim Integer32,
            hmSetupWlanMngmtApConfWIdsEntryDisAssocCtrInt Integer32,
            hmSetupWlanMngmtApConfWIdsEntryIdsOperational INTEGER,
            hmSetupWlanMngmtApConfWIdsEntrySyslogOperational INTEGER,
            hmSetupWlanMngmtApConfWIdsEntrySNMPTrapsOperational INTEGER,
            hmSetupWlanMngmtApConfWIdsEntryEMail INTEGER,
            hmSetupWlanMngmtApConfWIdsEntryEMailReceiver DisplayString,
            hmSetupWlanMngmtApConfWIdsEntryEMailAggregateInterval Integer32,
            hmSetupWlanMngmtApConfWIdsEntryBlockAckOutOfWindowCtrLim Integer32,
            hmSetupWlanMngmtApConfWIdsEntryBlockAckOutOfWindowCtrInt Integer32,
            hmSetupWlanMngmtApConfWIdsEntryBlockAckAfterDelBACtrLim Integer32,
            hmSetupWlanMngmtApConfWIdsEntryBlockAckAfterDelBACtrInt Integer32,
            hmSetupWlanMngmtApConfWIdsEntryNullDataFloodCtrLim Integer32,
            hmSetupWlanMngmtApConfWIdsEntryNullDataFloodCtrInt Integer32,
            hmSetupWlanMngmtApConfWIdsEntryNullDataPSOverflowCtrLim Integer32,
            hmSetupWlanMngmtApConfWIdsEntryNullDataPSOverflowCtrInt Integer32,
            hmSetupWlanMngmtApConfWIdsEntryPSPollTIMInterval Integer32,
            hmSetupWlanMngmtApConfWIdsEntryPSPollTIMIntervalCtrLim Integer32,
            hmSetupWlanMngmtApConfWIdsEntryPSPollTIMIntervalCtrInt Integer32,
            hmSetupWlanMngmtApConfWIdsEntrySMPSMulStreamCtrLim Integer32,
            hmSetupWlanMngmtApConfWIdsEntrySMPSMulStreamCtrInt Integer32,
            hmSetupWlanMngmtApConfWIdsEntrySMPSSingleStreamCtrLim Integer32,
            hmSetupWlanMngmtApConfWIdsEntrySMPSSingleStreamCtrInt Integer32,
            hmSetupWlanMngmtApConfWIdsEntryDisAssocBroadCtrLim Integer32,
            hmSetupWlanMngmtApConfWIdsEntryDisAssocBroadCtrInt Integer32,
            hmSetupWlanMngmtApConfWIdsEntryIntruderIdentification INTEGER,
            hmSetupWlanMngmtApConfWIdsEntryTimeoutIntruderActivity Integer32,
            hmSetupWlanMngmtApConfWIdsEntryWhiteListId Integer32,
            hmSetupWlanMngmtApConfWIdsEntryStoreIntruderDhcpRequests INTEGER
    }

-- {COLUMN} 1.3.6.1.4.1.248.32.18.2.37.1.248.1.1
hmSetupWlanMngmtApConfWIdsEntryName OBJECT-TYPE
    SYNTAX     DisplayString (SIZE(0..31))
    MAX-ACCESS read-write
    STATUS     current
    DESCRIPTION
            "-- empty --"
    ::= { hmSetupWlanMngmtApConfWIdsEntry 1 }

-- {COLUMN} 1.3.6.1.4.1.248.32.18.2.37.1.248.1.2
hmSetupWlanMngmtApConfWIdsEntryOperating OBJECT-TYPE
    SYNTAX     INTEGER {
                  eNo (0),
                  eYes (1)
            }
    MAX-ACCESS read-write
    STATUS     current
    DESCRIPTION
            "-- empty --"
    ::= { hmSetupWlanMngmtApConfWIdsEntry 2 }

-- {COLUMN} 1.3.6.1.4.1.248.32.18.2.37.1.248.1.3
hmSetupWlanMngmtApConfWIdsEntryEAPOLStartCtrLim OBJECT-TYPE
    SYNTAX     Integer32 (0..2147483647)
    MAX-ACCESS read-write
    STATUS     current
    DESCRIPTION
            ""
    ::= { hmSetupWlanMngmtApConfWIdsEntry 3 }

-- {COLUMN} 1.3.6.1.4.1.248.32.18.2.37.1.248.1.4
hmSetupWlanMngmtApConfWIdsEntryEAPOLStartCtrInt OBJECT-TYPE
    SYNTAX     Integer32 (0..2147483647)
    MAX-ACCESS read-write
    STATUS     current
    DESCRIPTION
            ""
    ::= { hmSetupWlanMngmtApConfWIdsEntry 4 }

-- {COLUMN} 1.3.6.1.4.1.248.32.18.2.37.1.248.1.5
hmSetupWlanMngmtApConfWIdsEntryProbeBroadCtrLim OBJECT-TYPE
    SYNTAX     Integer32 (0..2147483647)
    MAX-ACCESS read-write
    STATUS     current
    DESCRIPTION
            ""
    ::= { hmSetupWlanMngmtApConfWIdsEntry 5 }

-- {COLUMN} 1.3.6.1.4.1.248.32.18.2.37.1.248.1.6
hmSetupWlanMngmtApConfWIdsEntryProbeBroadCtrInt OBJECT-TYPE
    SYNTAX     Integer32 (0..2147483647)
    MAX-ACCESS read-write
    STATUS     current
    DESCRIPTION
            ""
    ::= { hmSetupWlanMngmtApConfWIdsEntry 6 }

-- {COLUMN} 1.3.6.1.4.1.248.32.18.2.37.1.248.1.7
hmSetupWlanMngmtApConfWIdsEntryDeauthBroadCtrLimt OBJECT-TYPE
    SYNTAX     Integer32 (0..2147483647)
    MAX-ACCESS read-write
    STATUS     current
    DESCRIPTION
            ""
    ::= { hmSetupWlanMngmtApConfWIdsEntry 7 }

-- {COLUMN} 1.3.6.1.4.1.248.32.18.2.37.1.248.1.8
hmSetupWlanMngmtApConfWIdsEntryDeauthBroadCtrInt OBJECT-TYPE
    SYNTAX     Integer32 (0..2147483647)
    MAX-ACCESS read-write
    STATUS     current
    DESCRIPTION
            ""
    ::= { hmSetupWlanMngmtApConfWIdsEntry 8 }

-- {COLUMN} 1.3.6.1.4.1.248.32.18.2.37.1.248.1.9
hmSetupWlanMngmtApConfWIdsEntryDeauthCtrLim OBJECT-TYPE
    SYNTAX     Integer32 (0..2147483647)
    MAX-ACCESS read-write
    STATUS     current
    DESCRIPTION
            ""
    ::= { hmSetupWlanMngmtApConfWIdsEntry 9 }

-- {COLUMN} 1.3.6.1.4.1.248.32.18.2.37.1.248.1.10
hmSetupWlanMngmtApConfWIdsEntryDeauthCtrInt OBJECT-TYPE
    SYNTAX     Integer32 (0..2147483647)
    MAX-ACCESS read-write
    STATUS     current
    DESCRIPTION
            ""
    ::= { hmSetupWlanMngmtApConfWIdsEntry 10 }

-- {COLUMN} 1.3.6.1.4.1.248.32.18.2.37.1.248.1.11
hmSetupWlanMngmtApConfWIdsEntryAssocReqCtrLim OBJECT-TYPE
    SYNTAX     Integer32 (0..2147483647)
    MAX-ACCESS read-write
    STATUS     current
    DESCRIPTION
            ""
    ::= { hmSetupWlanMngmtApConfWIdsEntry 11 }

-- {COLUMN} 1.3.6.1.4.1.248.32.18.2.37.1.248.1.12
hmSetupWlanMngmtApConfWIdsEntryAssocReqCtrInt OBJECT-TYPE
    SYNTAX     Integer32 (0..2147483647)
    MAX-ACCESS read-write
    STATUS     current
    DESCRIPTION
            ""
    ::= { hmSetupWlanMngmtApConfWIdsEntry 12 }

-- {COLUMN} 1.3.6.1.4.1.248.32.18.2.37.1.248.1.13
hmSetupWlanMngmtApConfWIdsEntryReAssocReqCtrLim OBJECT-TYPE
    SYNTAX     Integer32 (0..2147483647)
    MAX-ACCESS read-write
    STATUS     current
    DESCRIPTION
            ""
    ::= { hmSetupWlanMngmtApConfWIdsEntry 13 }

-- {COLUMN} 1.3.6.1.4.1.248.32.18.2.37.1.248.1.14
hmSetupWlanMngmtApConfWIdsEntryReAssocReqCtrInt OBJECT-TYPE
    SYNTAX     Integer32 (0..2147483647)
    MAX-ACCESS read-write
    STATUS     current
    DESCRIPTION
            ""
    ::= { hmSetupWlanMngmtApConfWIdsEntry 14 }

-- {COLUMN} 1.3.6.1.4.1.248.32.18.2.37.1.248.1.15
hmSetupWlanMngmtApConfWIdsEntryAuthCtrLim OBJECT-TYPE
    SYNTAX     Integer32 (0..2147483647)
    MAX-ACCESS read-write
    STATUS     current
    DESCRIPTION
            ""
    ::= { hmSetupWlanMngmtApConfWIdsEntry 15 }

-- {COLUMN} 1.3.6.1.4.1.248.32.18.2.37.1.248.1.16
hmSetupWlanMngmtApConfWIdsEntryAuthCtrInt OBJECT-TYPE
    SYNTAX     Integer32 (0..2147483647)
    MAX-ACCESS read-write
    STATUS     current
    DESCRIPTION
            ""
    ::= { hmSetupWlanMngmtApConfWIdsEntry 16 }

-- {COLUMN} 1.3.6.1.4.1.248.32.18.2.37.1.248.1.17
hmSetupWlanMngmtApConfWIdsEntryDisAssocCtrLim OBJECT-TYPE
    SYNTAX     Integer32 (0..2147483647)
    MAX-ACCESS read-write
    STATUS     current
    DESCRIPTION
            ""
    ::= { hmSetupWlanMngmtApConfWIdsEntry 17 }

-- {COLUMN} 1.3.6.1.4.1.248.32.18.2.37.1.248.1.18
hmSetupWlanMngmtApConfWIdsEntryDisAssocCtrInt OBJECT-TYPE
    SYNTAX     Integer32 (0..2147483647)
    MAX-ACCESS read-write
    STATUS     current
    DESCRIPTION
            ""
    ::= { hmSetupWlanMngmtApConfWIdsEntry 18 }

-- {COLUMN} 1.3.6.1.4.1.248.32.18.2.37.1.248.1.19
hmSetupWlanMngmtApConfWIdsEntryIdsOperational OBJECT-TYPE
    SYNTAX     INTEGER {
                  eNo (0),
                  eYes (1)
            }
    MAX-ACCESS read-write
    STATUS     current
    DESCRIPTION
            ""
    ::= { hmSetupWlanMngmtApConfWIdsEntry 19 }

-- {COLUMN} 1.3.6.1.4.1.248.32.18.2.37.1.248.1.20
hmSetupWlanMngmtApConfWIdsEntrySyslogOperational OBJECT-TYPE
    SYNTAX     INTEGER {
                  eNo (0),
                  eYes (1)
            }
    MAX-ACCESS read-write
    STATUS     current
    DESCRIPTION
            ""
    ::= { hmSetupWlanMngmtApConfWIdsEntry 20 }

-- {COLUMN} 1.3.6.1.4.1.248.32.18.2.37.1.248.1.21
hmSetupWlanMngmtApConfWIdsEntrySNMPTrapsOperational OBJECT-TYPE
    SYNTAX     INTEGER {
                  eNo (0),
                  eYes (1)
            }
    MAX-ACCESS read-write
    STATUS     current
    DESCRIPTION
            ""
    ::= { hmSetupWlanMngmtApConfWIdsEntry 21 }

-- {COLUMN} 1.3.6.1.4.1.248.32.18.2.37.1.248.1.22
hmSetupWlanMngmtApConfWIdsEntryEMail OBJECT-TYPE
    SYNTAX     INTEGER {
                  eNo (0),
                  eYes (1)
            }
    MAX-ACCESS read-write
    STATUS     current
    DESCRIPTION
            "-- empty --"
    ::= { hmSetupWlanMngmtApConfWIdsEntry 22 }

-- {COLUMN} 1.3.6.1.4.1.248.32.18.2.37.1.248.1.23
hmSetupWlanMngmtApConfWIdsEntryEMailReceiver OBJECT-TYPE
    SYNTAX     DisplayString (SIZE(0..64))
    MAX-ACCESS read-write
    STATUS     current
    DESCRIPTION
            "-- empty --"
    ::= { hmSetupWlanMngmtApConfWIdsEntry 23 }

-- {COLUMN} 1.3.6.1.4.1.248.32.18.2.37.1.248.1.24
hmSetupWlanMngmtApConfWIdsEntryEMailAggregateInterval OBJECT-TYPE
    SYNTAX     Integer32 (0..2147483647)
    MAX-ACCESS read-write
    STATUS     current
    DESCRIPTION
            ""
    ::= { hmSetupWlanMngmtApConfWIdsEntry 24 }

-- {COLUMN} 1.3.6.1.4.1.248.32.18.2.37.1.248.1.26
hmSetupWlanMngmtApConfWIdsEntryBlockAckOutOfWindowCtrLim OBJECT-TYPE
    SYNTAX     Integer32 (0..2147483647)
    MAX-ACCESS read-write
    STATUS     current
    DESCRIPTION
            ""
    ::= { hmSetupWlanMngmtApConfWIdsEntry 26 }

-- {COLUMN} 1.3.6.1.4.1.248.32.18.2.37.1.248.1.27
hmSetupWlanMngmtApConfWIdsEntryBlockAckOutOfWindowCtrInt OBJECT-TYPE
    SYNTAX     Integer32 (0..2147483647)
    MAX-ACCESS read-write
    STATUS     current
    DESCRIPTION
            ""
    ::= { hmSetupWlanMngmtApConfWIdsEntry 27 }

-- {COLUMN} 1.3.6.1.4.1.248.32.18.2.37.1.248.1.28
hmSetupWlanMngmtApConfWIdsEntryBlockAckAfterDelBACtrLim OBJECT-TYPE
    SYNTAX     Integer32 (0..2147483647)
    MAX-ACCESS read-write
    STATUS     current
    DESCRIPTION
            ""
    ::= { hmSetupWlanMngmtApConfWIdsEntry 28 }

-- {COLUMN} 1.3.6.1.4.1.248.32.18.2.37.1.248.1.29
hmSetupWlanMngmtApConfWIdsEntryBlockAckAfterDelBACtrInt OBJECT-TYPE
    SYNTAX     Integer32 (0..2147483647)
    MAX-ACCESS read-write
    STATUS     current
    DESCRIPTION
            ""
    ::= { hmSetupWlanMngmtApConfWIdsEntry 29 }

-- {COLUMN} 1.3.6.1.4.1.248.32.18.2.37.1.248.1.31
hmSetupWlanMngmtApConfWIdsEntryNullDataFloodCtrLim OBJECT-TYPE
    SYNTAX     Integer32 (0..2147483647)
    MAX-ACCESS read-write
    STATUS     current
    DESCRIPTION
            ""
    ::= { hmSetupWlanMngmtApConfWIdsEntry 31 }

-- {COLUMN} 1.3.6.1.4.1.248.32.18.2.37.1.248.1.32
hmSetupWlanMngmtApConfWIdsEntryNullDataFloodCtrInt OBJECT-TYPE
    SYNTAX     Integer32 (0..2147483647)
    MAX-ACCESS read-write
    STATUS     current
    DESCRIPTION
            ""
    ::= { hmSetupWlanMngmtApConfWIdsEntry 32 }

-- {COLUMN} 1.3.6.1.4.1.248.32.18.2.37.1.248.1.34
hmSetupWlanMngmtApConfWIdsEntryNullDataPSOverflowCtrLim OBJECT-TYPE
    SYNTAX     Integer32 (0..2147483647)
    MAX-ACCESS read-write
    STATUS     current
    DESCRIPTION
            ""
    ::= { hmSetupWlanMngmtApConfWIdsEntry 34 }

-- {COLUMN} 1.3.6.1.4.1.248.32.18.2.37.1.248.1.35
hmSetupWlanMngmtApConfWIdsEntryNullDataPSOverflowCtrInt OBJECT-TYPE
    SYNTAX     Integer32 (0..2147483647)
    MAX-ACCESS read-write
    STATUS     current
    DESCRIPTION
            ""
    ::= { hmSetupWlanMngmtApConfWIdsEntry 35 }

-- {COLUMN} 1.3.6.1.4.1.248.32.18.2.37.1.248.1.37
hmSetupWlanMngmtApConfWIdsEntryPSPollTIMInterval OBJECT-TYPE
    SYNTAX     Integer32 (0..2147483647)
    MAX-ACCESS read-write
    STATUS     current
    DESCRIPTION
            ""
    ::= { hmSetupWlanMngmtApConfWIdsEntry 37 }

-- {COLUMN} 1.3.6.1.4.1.248.32.18.2.37.1.248.1.38
hmSetupWlanMngmtApConfWIdsEntryPSPollTIMIntervalCtrLim OBJECT-TYPE
    SYNTAX     Integer32 (0..2147483647)
    MAX-ACCESS read-write
    STATUS     current
    DESCRIPTION
            ""
    ::= { hmSetupWlanMngmtApConfWIdsEntry 38 }

-- {COLUMN} 1.3.6.1.4.1.248.32.18.2.37.1.248.1.39
hmSetupWlanMngmtApConfWIdsEntryPSPollTIMIntervalCtrInt OBJECT-TYPE
    SYNTAX     Integer32 (0..2147483647)
    MAX-ACCESS read-write
    STATUS     current
    DESCRIPTION
            ""
    ::= { hmSetupWlanMngmtApConfWIdsEntry 39 }

-- {COLUMN} 1.3.6.1.4.1.248.32.18.2.37.1.248.1.41
hmSetupWlanMngmtApConfWIdsEntrySMPSMulStreamCtrLim OBJECT-TYPE
    SYNTAX     Integer32 (0..2147483647)
    MAX-ACCESS read-write
    STATUS     current
    DESCRIPTION
            ""
    ::= { hmSetupWlanMngmtApConfWIdsEntry 41 }

-- {COLUMN} 1.3.6.1.4.1.248.32.18.2.37.1.248.1.42
hmSetupWlanMngmtApConfWIdsEntrySMPSMulStreamCtrInt OBJECT-TYPE
    SYNTAX     Integer32 (0..2147483647)
    MAX-ACCESS read-write
    STATUS     current
    DESCRIPTION
            ""
    ::= { hmSetupWlanMngmtApConfWIdsEntry 42 }

-- {COLUMN} 1.3.6.1.4.1.248.32.18.2.37.1.248.1.43
hmSetupWlanMngmtApConfWIdsEntrySMPSSingleStreamCtrLim OBJECT-TYPE
    SYNTAX     Integer32 (0..2147483647)
    MAX-ACCESS read-write
    STATUS     current
    DESCRIPTION
            ""
    ::= { hmSetupWlanMngmtApConfWIdsEntry 43 }

-- {COLUMN} 1.3.6.1.4.1.248.32.18.2.37.1.248.1.44
hmSetupWlanMngmtApConfWIdsEntrySMPSSingleStreamCtrInt OBJECT-TYPE
    SYNTAX     Integer32 (0..2147483647)
    MAX-ACCESS read-write
    STATUS     current
    DESCRIPTION
            ""
    ::= { hmSetupWlanMngmtApConfWIdsEntry 44 }

-- {COLUMN} 1.3.6.1.4.1.248.32.18.2.37.1.248.1.45
hmSetupWlanMngmtApConfWIdsEntryDisAssocBroadCtrLim OBJECT-TYPE
    SYNTAX     Integer32 (0..2147483647)
    MAX-ACCESS read-write
    STATUS     current
    DESCRIPTION
            ""
    ::= { hmSetupWlanMngmtApConfWIdsEntry 45 }

-- {COLUMN} 1.3.6.1.4.1.248.32.18.2.37.1.248.1.46
hmSetupWlanMngmtApConfWIdsEntryDisAssocBroadCtrInt OBJECT-TYPE
    SYNTAX     Integer32 (0..2147483647)
    MAX-ACCESS read-write
    STATUS     current
    DESCRIPTION
            ""
    ::= { hmSetupWlanMngmtApConfWIdsEntry 46 }

-- {COLUMN} 1.3.6.1.4.1.248.32.18.2.37.1.248.1.52
hmSetupWlanMngmtApConfWIdsEntryIntruderIdentification OBJECT-TYPE
    SYNTAX     INTEGER {
                  eNo (0),
                  eYes (1)
            }
    MAX-ACCESS read-write
    STATUS     current
    DESCRIPTION
            "-- empty --"
    ::= { hmSetupWlanMngmtApConfWIdsEntry 52 }

-- {COLUMN} 1.3.6.1.4.1.248.32.18.2.37.1.248.1.53
hmSetupWlanMngmtApConfWIdsEntryTimeoutIntruderActivity OBJECT-TYPE
    SYNTAX     Integer32 (0..2147483647)
    MAX-ACCESS read-write
    STATUS     current
    DESCRIPTION
            "-- empty --"
    ::= { hmSetupWlanMngmtApConfWIdsEntry 53 }

-- {COLUMN} 1.3.6.1.4.1.248.32.18.2.37.1.248.1.54
hmSetupWlanMngmtApConfWIdsEntryWhiteListId OBJECT-TYPE
    SYNTAX     Integer32 (0..255)
    MAX-ACCESS read-write
    STATUS     current
    DESCRIPTION
            "-- empty --"
    ::= { hmSetupWlanMngmtApConfWIdsEntry 54 }

-- {COLUMN} 1.3.6.1.4.1.248.32.18.2.37.1.248.1.55
hmSetupWlanMngmtApConfWIdsEntryStoreIntruderDhcpRequests OBJECT-TYPE
    SYNTAX     INTEGER {
                  eNo (0),
                  eYes (1)
            }
    MAX-ACCESS read-write
    STATUS     current
    DESCRIPTION
            "-- empty --"
    ::= { hmSetupWlanMngmtApConfWIdsEntry 55 }

-- {TABLE} 1.3.6.1.4.1.248.32.18.2.37.1.249
hmSetupWlanMngmtApConfWhiteListTable OBJECT-TYPE
    SYNTAX     SEQUENCE OF HmSetupWlanMngmtApConfWhiteListEntry
    MAX-ACCESS not-accessible
    STATUS     current
    DESCRIPTION
            ""
    ::= { hmSetupWlanMngmtApConf 249 }

-- {ROW} 1.3.6.1.4.1.248.32.18.2.37.1.249.1
hmSetupWlanMngmtApConfWhiteListEntry OBJECT-TYPE
    SYNTAX     HmSetupWlanMngmtApConfWhiteListEntry
    MAX-ACCESS not-accessible
    STATUS     current
    DESCRIPTION
            ""
    INDEX {
            hmSetupWlanMngmtApConfWhiteListEntryIndex
          }
    ::= { hmSetupWlanMngmtApConfWhiteListTable 1 }

HmSetupWlanMngmtApConfWhiteListEntry ::= SEQUENCE {
            hmSetupWlanMngmtApConfWhiteListEntryIndex Integer32,
            hmSetupWlanMngmtApConfWhiteListEntryWhiteListId Integer32,
            hmSetupWlanMngmtApConfWhiteListEntryStationMac MacAddress
    }

-- {COLUMN} 1.3.6.1.4.1.248.32.18.2.37.1.249.1.1
hmSetupWlanMngmtApConfWhiteListEntryIndex OBJECT-TYPE
    SYNTAX     Integer32 (0..255)
    MAX-ACCESS read-write
    STATUS     current
    DESCRIPTION
            "-- empty --"
    ::= { hmSetupWlanMngmtApConfWhiteListEntry 1 }

-- {COLUMN} 1.3.6.1.4.1.248.32.18.2.37.1.249.1.2
hmSetupWlanMngmtApConfWhiteListEntryWhiteListId OBJECT-TYPE
    SYNTAX     Integer32 (0..255)
    MAX-ACCESS read-write
    STATUS     current
    DESCRIPTION
            "-- empty --"
    ::= { hmSetupWlanMngmtApConfWhiteListEntry 2 }

-- {COLUMN} 1.3.6.1.4.1.248.32.18.2.37.1.249.1.3
hmSetupWlanMngmtApConfWhiteListEntryStationMac OBJECT-TYPE
    SYNTAX     MacAddress
    MAX-ACCESS read-write
    STATUS     current
    DESCRIPTION
            "-- empty --"
    ::= { hmSetupWlanMngmtApConfWhiteListEntry 3 }

-- {SCALAR} 1.3.6.1.4.1.248.32.18.2.37.5
hmSetupWlanMngmtCapwapPort OBJECT-TYPE
    SYNTAX     Integer32 (0..65535)
    MAX-ACCESS read-write
    STATUS     current
    DESCRIPTION
            "-- empty --"
    ::= { hmSetupWlanMngmt 5 }

-- {SCALAR} 1.3.6.1.4.1.248.32.18.2.37.6
hmSetupWlanMngmtAutoacceptAp OBJECT-TYPE
    SYNTAX     INTEGER {
                  eNo (0),
                  eYes (1)
            }
    MAX-ACCESS read-write
    STATUS     current
    DESCRIPTION
            "-- empty --"
    ::= { hmSetupWlanMngmt 6 }

-- {SCALAR} 1.3.6.1.4.1.248.32.18.2.37.7
hmSetupWlanMngmtAcceptAp OBJECT-TYPE
    SYNTAX     DisplayString
    MAX-ACCESS read-write
    STATUS     current
    DESCRIPTION
            "-- empty --"
    ::= { hmSetupWlanMngmt 7 }

-- {SCALAR} 1.3.6.1.4.1.248.32.18.2.37.8
hmSetupWlanMngmtProvideDefaultConfiguration OBJECT-TYPE
    SYNTAX     INTEGER {
                  eNo (0),
                  eYes (1)
            }
    MAX-ACCESS read-write
    STATUS     current
    DESCRIPTION
            "-- empty --"
    ::= { hmSetupWlanMngmt 8 }

-- {SCALAR} 1.3.6.1.4.1.248.32.18.2.37.9
hmSetupWlanMngmtDisconnectAp OBJECT-TYPE
    SYNTAX     DisplayString
    MAX-ACCESS read-write
    STATUS     current
    DESCRIPTION
            "-- empty --"
    ::= { hmSetupWlanMngmt 9 }

-- {NODE} 1.3.6.1.4.1.248.32.18.2.37.10
hmSetupWlanMngmtNotification OBJECT IDENTIFIER ::= { hmSetupWlanMngmt 10 }

-- {SCALAR} 1.3.6.1.4.1.248.32.18.2.37.10.1
hmSetupWlanMngmtNotificationEMail OBJECT-TYPE
    SYNTAX     INTEGER {
                  eNo (0),
                  eYes (1)
            }
    MAX-ACCESS read-write
    STATUS     current
    DESCRIPTION
            "-- empty --"
    ::= { hmSetupWlanMngmtNotification 1 }

-- {SCALAR} 1.3.6.1.4.1.248.32.18.2.37.10.2
hmSetupWlanMngmtNotificationSyslog OBJECT-TYPE
    SYNTAX     INTEGER {
                  eNo (0),
                  eYes (1)
            }
    MAX-ACCESS read-write
    STATUS     current
    DESCRIPTION
            "-- empty --"
    ::= { hmSetupWlanMngmtNotification 2 }

-- {SCALAR} 1.3.6.1.4.1.248.32.18.2.37.10.3
hmSetupWlanMngmtNotificationEMailReceiver OBJECT-TYPE
    SYNTAX     DisplayString (SIZE(0..63))
    MAX-ACCESS read-write
    STATUS     current
    DESCRIPTION
            "-- empty --"
    ::= { hmSetupWlanMngmtNotification 3 }

-- {TABLE} 1.3.6.1.4.1.248.32.18.2.37.10.4
hmSetupWlanMngmtNotificationAdvancedTable OBJECT-TYPE
    SYNTAX     SEQUENCE OF HmSetupWlanMngmtNotificationAdvancedEntry
    MAX-ACCESS not-accessible
    STATUS     current
    DESCRIPTION
            "-- empty --"
    ::= { hmSetupWlanMngmtNotification 4 }

-- {ROW} 1.3.6.1.4.1.248.32.18.2.37.10.4.1
hmSetupWlanMngmtNotificationAdvancedEntry OBJECT-TYPE
    SYNTAX     HmSetupWlanMngmtNotificationAdvancedEntry
    MAX-ACCESS not-accessible
    STATUS     current
    DESCRIPTION
            ""
    INDEX {
            hmSetupWlanMngmtNotificationAdvancedEntryName
          }
    ::= { hmSetupWlanMngmtNotificationAdvancedTable 1 }

HmSetupWlanMngmtNotificationAdvancedEntry ::= SEQUENCE {
            hmSetupWlanMngmtNotificationAdvancedEntryName INTEGER,
            hmSetupWlanMngmtNotificationAdvancedEntryActiveRadios INTEGER,
            hmSetupWlanMngmtNotificationAdvancedEntryMissingAp INTEGER,
            hmSetupWlanMngmtNotificationAdvancedEntryNewAp INTEGER
    }

-- {COLUMN} 1.3.6.1.4.1.248.32.18.2.37.10.4.1.1
hmSetupWlanMngmtNotificationAdvancedEntryName OBJECT-TYPE
    SYNTAX     INTEGER {
                  eEMail (1),
                  eSyslog (2)
            }
    MAX-ACCESS read-only
    STATUS     current
    DESCRIPTION
            "-- empty --"
    ::= { hmSetupWlanMngmtNotificationAdvancedEntry 1 }

-- {COLUMN} 1.3.6.1.4.1.248.32.18.2.37.10.4.1.2
hmSetupWlanMngmtNotificationAdvancedEntryActiveRadios OBJECT-TYPE
    SYNTAX     INTEGER {
                  eNo (0),
                  eYes (1)
            }
    MAX-ACCESS read-write
    STATUS     current
    DESCRIPTION
            "-- empty --"
    ::= { hmSetupWlanMngmtNotificationAdvancedEntry 2 }

-- {COLUMN} 1.3.6.1.4.1.248.32.18.2.37.10.4.1.3
hmSetupWlanMngmtNotificationAdvancedEntryMissingAp OBJECT-TYPE
    SYNTAX     INTEGER {
                  eNo (0),
                  eYes (1)
            }
    MAX-ACCESS read-write
    STATUS     current
    DESCRIPTION
            "-- empty --"
    ::= { hmSetupWlanMngmtNotificationAdvancedEntry 3 }

-- {COLUMN} 1.3.6.1.4.1.248.32.18.2.37.10.4.1.4
hmSetupWlanMngmtNotificationAdvancedEntryNewAp OBJECT-TYPE
    SYNTAX     INTEGER {
                  eNo (0),
                  eYes (1)
            }
    MAX-ACCESS read-write
    STATUS     current
    DESCRIPTION
            "-- empty --"
    ::= { hmSetupWlanMngmtNotificationAdvancedEntry 4 }

-- {SCALAR} 1.3.6.1.4.1.248.32.18.2.37.10.5
hmSetupWlanMngmtNotificationSendSnmpTrapForStationTableEvent OBJECT-TYPE
    SYNTAX     INTEGER {
                  eAddRemoveEntry (0),
                  eAllEvents (1)
            }
    MAX-ACCESS read-write
    STATUS     current
    DESCRIPTION
            "-- empty --"
    ::= { hmSetupWlanMngmtNotification 5 }

-- {TABLE} 1.3.6.1.4.1.248.32.18.2.37.17
hmSetupWlanMngmtRadiusServerTable OBJECT-TYPE
    SYNTAX     SEQUENCE OF HmSetupWlanMngmtRadiusServerEntry
    MAX-ACCESS not-accessible
    STATUS     current
    DESCRIPTION
            "-- empty --"
    ::= { hmSetupWlanMngmt 17 }

-- {ROW} 1.3.6.1.4.1.248.32.18.2.37.17.1
hmSetupWlanMngmtRadiusServerEntry OBJECT-TYPE
    SYNTAX     HmSetupWlanMngmtRadiusServerEntry
    MAX-ACCESS not-accessible
    STATUS     current
    DESCRIPTION
            ""
    INDEX {
            hmSetupWlanMngmtRadiusServerEntryType
          }
    ::= { hmSetupWlanMngmtRadiusServerTable 1 }

HmSetupWlanMngmtRadiusServerEntry ::= SEQUENCE {
            hmSetupWlanMngmtRadiusServerEntryType INTEGER,
            hmSetupWlanMngmtRadiusServerEntryIpAddress IpAddress,
            hmSetupWlanMngmtRadiusServerEntryPort Integer32,
            hmSetupWlanMngmtRadiusServerEntrySecret DisplayString
    }

-- {COLUMN} 1.3.6.1.4.1.248.32.18.2.37.17.1.1
hmSetupWlanMngmtRadiusServerEntryType OBJECT-TYPE
    SYNTAX     INTEGER {
                  eAccount (1),
                  eAccess (2),
                  eBackupAccount (3),
                  eBackupAccess (4)
            }
    MAX-ACCESS read-only
    STATUS     current
    DESCRIPTION
            "-- empty --"
    ::= { hmSetupWlanMngmtRadiusServerEntry 1 }

-- {COLUMN} 1.3.6.1.4.1.248.32.18.2.37.17.1.2
hmSetupWlanMngmtRadiusServerEntryIpAddress OBJECT-TYPE
    SYNTAX     IpAddress
    MAX-ACCESS read-write
    STATUS     current
    DESCRIPTION
            "-- empty --"
    ::= { hmSetupWlanMngmtRadiusServerEntry 2 }

-- {COLUMN} 1.3.6.1.4.1.248.32.18.2.37.17.1.3
hmSetupWlanMngmtRadiusServerEntryPort OBJECT-TYPE
    SYNTAX     Integer32 (0..65535)
    MAX-ACCESS read-write
    STATUS     current
    DESCRIPTION
            "-- empty --"
    ::= { hmSetupWlanMngmtRadiusServerEntry 3 }

-- {COLUMN} 1.3.6.1.4.1.248.32.18.2.37.17.1.4
hmSetupWlanMngmtRadiusServerEntrySecret OBJECT-TYPE
    SYNTAX     DisplayString (SIZE(0..64))
    MAX-ACCESS read-write
    STATUS     current
    DESCRIPTION
            "-- empty --"
    ::= { hmSetupWlanMngmtRadiusServerEntry 4 }

-- {SCALAR} 1.3.6.1.4.1.248.32.18.2.37.19
hmSetupWlanMngmtStartAutomaticRadioFieldOptimization OBJECT-TYPE
    SYNTAX     DisplayString
    MAX-ACCESS read-write
    STATUS     current
    DESCRIPTION
            "-- empty --"
    ::= { hmSetupWlanMngmt 19 }

-- {TABLE} 1.3.6.1.4.1.248.32.18.2.37.20
hmSetupWlanMngmtAccessListTable OBJECT-TYPE
    SYNTAX     SEQUENCE OF HmSetupWlanMngmtAccessListEntry
    MAX-ACCESS not-accessible
    STATUS     current
    DESCRIPTION
            "-- empty --"
    ::= { hmSetupWlanMngmt 20 }

-- {ROW} 1.3.6.1.4.1.248.32.18.2.37.20.1
hmSetupWlanMngmtAccessListEntry OBJECT-TYPE
    SYNTAX     HmSetupWlanMngmtAccessListEntry
    MAX-ACCESS not-accessible
    STATUS     current
    DESCRIPTION
            ""
    INDEX {
            hmSetupWlanMngmtAccessListEntryMacAddress
          }
    ::= { hmSetupWlanMngmtAccessListTable 1 }

HmSetupWlanMngmtAccessListEntry ::= SEQUENCE {
            hmSetupWlanMngmtAccessListEntryMacAddress MacAddress,
            hmSetupWlanMngmtAccessListEntryName DisplayString,
            hmSetupWlanMngmtAccessListEntryComment DisplayString,
            hmSetupWlanMngmtAccessListEntryWpaPassphrase DisplayString,
            hmSetupWlanMngmtAccessListEntryTxLimit Integer32,
            hmSetupWlanMngmtAccessListEntryRxLimit Integer32,
            hmSetupWlanMngmtAccessListEntryVlanId Integer32
    }

-- {COLUMN} 1.3.6.1.4.1.248.32.18.2.37.20.1.1
hmSetupWlanMngmtAccessListEntryMacAddress OBJECT-TYPE
    SYNTAX     MacAddress
    MAX-ACCESS read-write
    STATUS     current
    DESCRIPTION
            "-- empty --"
    ::= { hmSetupWlanMngmtAccessListEntry 1 }

-- {COLUMN} 1.3.6.1.4.1.248.32.18.2.37.20.1.2
hmSetupWlanMngmtAccessListEntryName OBJECT-TYPE
    SYNTAX     DisplayString (SIZE(0..32))
    MAX-ACCESS read-write
    STATUS     current
    DESCRIPTION
            "-- empty --"
    ::= { hmSetupWlanMngmtAccessListEntry 2 }

-- {COLUMN} 1.3.6.1.4.1.248.32.18.2.37.20.1.3
hmSetupWlanMngmtAccessListEntryComment OBJECT-TYPE
    SYNTAX     DisplayString (SIZE(0..30))
    MAX-ACCESS read-write
    STATUS     current
    DESCRIPTION
            "-- empty --"
    ::= { hmSetupWlanMngmtAccessListEntry 3 }

-- {COLUMN} 1.3.6.1.4.1.248.32.18.2.37.20.1.4
hmSetupWlanMngmtAccessListEntryWpaPassphrase OBJECT-TYPE
    SYNTAX     DisplayString (SIZE(0..63))
    MAX-ACCESS read-write
    STATUS     current
    DESCRIPTION
            "-- empty --"
    ::= { hmSetupWlanMngmtAccessListEntry 4 }

-- {COLUMN} 1.3.6.1.4.1.248.32.18.2.37.20.1.5
hmSetupWlanMngmtAccessListEntryTxLimit OBJECT-TYPE
    SYNTAX     Integer32 (0..2147483647)
    MAX-ACCESS read-write
    STATUS     current
    DESCRIPTION
            "-- empty --"
    ::= { hmSetupWlanMngmtAccessListEntry 5 }

-- {COLUMN} 1.3.6.1.4.1.248.32.18.2.37.20.1.6
hmSetupWlanMngmtAccessListEntryRxLimit OBJECT-TYPE
    SYNTAX     Integer32 (0..2147483647)
    MAX-ACCESS read-write
    STATUS     current
    DESCRIPTION
            "-- empty --"
    ::= { hmSetupWlanMngmtAccessListEntry 6 }

-- {COLUMN} 1.3.6.1.4.1.248.32.18.2.37.20.1.7
hmSetupWlanMngmtAccessListEntryVlanId OBJECT-TYPE
    SYNTAX     Integer32 (0..65535)
    MAX-ACCESS read-write
    STATUS     current
    DESCRIPTION
            "-- empty --"
    ::= { hmSetupWlanMngmtAccessListEntry 7 }

-- {TABLE} 1.3.6.1.4.1.248.32.18.2.37.21
hmSetupWlanMngmtAccessRulesTable OBJECT-TYPE
    SYNTAX     SEQUENCE OF HmSetupWlanMngmtAccessRulesEntry
    MAX-ACCESS not-accessible
    STATUS     current
    DESCRIPTION
            "-- empty --"
    ::= { hmSetupWlanMngmt 21 }

-- {ROW} 1.3.6.1.4.1.248.32.18.2.37.21.1
hmSetupWlanMngmtAccessRulesEntry OBJECT-TYPE
    SYNTAX     HmSetupWlanMngmtAccessRulesEntry
    MAX-ACCESS not-accessible
    STATUS     current
    DESCRIPTION
            ""
    INDEX {
            hmSetupWlanMngmtAccessRulesEntryMacAddressPattern,
            hmSetupWlanMngmtAccessRulesEntrySsidPattern
          }
    ::= { hmSetupWlanMngmtAccessRulesTable 1 }

HmSetupWlanMngmtAccessRulesEntry ::= SEQUENCE {
            hmSetupWlanMngmtAccessRulesEntryMacAddressPattern DisplayString,
            hmSetupWlanMngmtAccessRulesEntryName DisplayString,
            hmSetupWlanMngmtAccessRulesEntryComment DisplayString,
            hmSetupWlanMngmtAccessRulesEntryWpaPassphrase DisplayString,
            hmSetupWlanMngmtAccessRulesEntryTxLimit Integer32,
            hmSetupWlanMngmtAccessRulesEntryRxLimit Integer32,
            hmSetupWlanMngmtAccessRulesEntryVlanId Integer32,
            hmSetupWlanMngmtAccessRulesEntrySsidPattern DisplayString
    }

-- {COLUMN} 1.3.6.1.4.1.248.32.18.2.37.21.1.1
hmSetupWlanMngmtAccessRulesEntryMacAddressPattern OBJECT-TYPE
    SYNTAX     DisplayString (SIZE(0..20))
    MAX-ACCESS read-write
    STATUS     current
    DESCRIPTION
            "-- empty --"
    ::= { hmSetupWlanMngmtAccessRulesEntry 1 }

-- {COLUMN} 1.3.6.1.4.1.248.32.18.2.37.21.1.2
hmSetupWlanMngmtAccessRulesEntryName OBJECT-TYPE
    SYNTAX     DisplayString (SIZE(0..32))
    MAX-ACCESS read-write
    STATUS     current
    DESCRIPTION
            "-- empty --"
    ::= { hmSetupWlanMngmtAccessRulesEntry 2 }

-- {COLUMN} 1.3.6.1.4.1.248.32.18.2.37.21.1.3
hmSetupWlanMngmtAccessRulesEntryComment OBJECT-TYPE
    SYNTAX     DisplayString (SIZE(0..30))
    MAX-ACCESS read-write
    STATUS     current
    DESCRIPTION
            "-- empty --"
    ::= { hmSetupWlanMngmtAccessRulesEntry 3 }

-- {COLUMN} 1.3.6.1.4.1.248.32.18.2.37.21.1.4
hmSetupWlanMngmtAccessRulesEntryWpaPassphrase OBJECT-TYPE
    SYNTAX     DisplayString (SIZE(0..63))
    MAX-ACCESS read-write
    STATUS     current
    DESCRIPTION
            "-- empty --"
    ::= { hmSetupWlanMngmtAccessRulesEntry 4 }

-- {COLUMN} 1.3.6.1.4.1.248.32.18.2.37.21.1.5
hmSetupWlanMngmtAccessRulesEntryTxLimit OBJECT-TYPE
    SYNTAX     Integer32 (0..2147483647)
    MAX-ACCESS read-write
    STATUS     current
    DESCRIPTION
            "-- empty --"
    ::= { hmSetupWlanMngmtAccessRulesEntry 5 }

-- {COLUMN} 1.3.6.1.4.1.248.32.18.2.37.21.1.6
hmSetupWlanMngmtAccessRulesEntryRxLimit OBJECT-TYPE
    SYNTAX     Integer32 (0..2147483647)
    MAX-ACCESS read-write
    STATUS     current
    DESCRIPTION
            "-- empty --"
    ::= { hmSetupWlanMngmtAccessRulesEntry 6 }

-- {COLUMN} 1.3.6.1.4.1.248.32.18.2.37.21.1.7
hmSetupWlanMngmtAccessRulesEntryVlanId OBJECT-TYPE
    SYNTAX     Integer32 (0..65535)
    MAX-ACCESS read-write
    STATUS     current
    DESCRIPTION
            "-- empty --"
    ::= { hmSetupWlanMngmtAccessRulesEntry 7 }

-- {COLUMN} 1.3.6.1.4.1.248.32.18.2.37.21.1.8
hmSetupWlanMngmtAccessRulesEntrySsidPattern OBJECT-TYPE
    SYNTAX     DisplayString (SIZE(0..40))
    MAX-ACCESS read-write
    STATUS     current
    DESCRIPTION
            "-- empty --"
    ::= { hmSetupWlanMngmtAccessRulesEntry 8 }

-- {NODE} 1.3.6.1.4.1.248.32.18.2.37.27
hmSetupWlanMngmtCentralFwMngmt OBJECT IDENTIFIER ::= { hmSetupWlanMngmt 27 }

-- {SCALAR} 1.3.6.1.4.1.248.32.18.2.37.27.11
hmSetupWlanMngmtCentralFwMngmtFirmwareRepositoryUrl OBJECT-TYPE
    SYNTAX     DisplayString (SIZE(0..251))
    MAX-ACCESS read-write
    STATUS     current
    DESCRIPTION
            "-- empty --"
    ::= { hmSetupWlanMngmtCentralFwMngmt 11 }

-- {SCALAR} 1.3.6.1.4.1.248.32.18.2.37.27.12
hmSetupWlanMngmtCentralFwMngmtScriptRepositoryUrl OBJECT-TYPE
    SYNTAX     DisplayString (SIZE(0..251))
    MAX-ACCESS read-write
    STATUS     current
    DESCRIPTION
            "-- empty --"
    ::= { hmSetupWlanMngmtCentralFwMngmt 12 }

-- {SCALAR} 1.3.6.1.4.1.248.32.18.2.37.27.13
hmSetupWlanMngmtCentralFwMngmtUpdFwScriptInfo OBJECT-TYPE
    SYNTAX     DisplayString
    MAX-ACCESS read-write
    STATUS     current
    DESCRIPTION
            "update firmware and script information"
    ::= { hmSetupWlanMngmtCentralFwMngmt 13 }

-- {SCALAR} 1.3.6.1.4.1.248.32.18.2.37.27.14
hmSetupWlanMngmtCentralFwMngmtMaximumNumberOfLoadedFirmwares OBJECT-TYPE
    SYNTAX     Integer32 (0..255)
    MAX-ACCESS read-write
    STATUS     current
    DESCRIPTION
            "-- empty --"
    ::= { hmSetupWlanMngmtCentralFwMngmt 14 }

-- {TABLE} 1.3.6.1.4.1.248.32.18.2.37.27.15
hmSetupWlanMngmtCentralFwMngmtFwVersMngmtTable OBJECT-TYPE
    SYNTAX     SEQUENCE OF HmSetupWlanMngmtCentralFwMngmtFwVersMngmtEntry
    MAX-ACCESS not-accessible
    STATUS     current
    DESCRIPTION
            "firmware version management"
    ::= { hmSetupWlanMngmtCentralFwMngmt 15 }

-- {ROW} 1.3.6.1.4.1.248.32.18.2.37.27.15.1
hmSetupWlanMngmtCentralFwMngmtFwVersMngmtEntry OBJECT-TYPE
    SYNTAX     HmSetupWlanMngmtCentralFwMngmtFwVersMngmtEntry
    MAX-ACCESS not-accessible
    STATUS     current
    DESCRIPTION
            ""
    INDEX {
            hmSetupWlanMngmtCentralFwMngmtFwVersMngmtEntryDevice,
            hmSetupWlanMngmtCentralFwMngmtFwVersMngmtEntryMacAddress
          }
    ::= { hmSetupWlanMngmtCentralFwMngmtFwVersMngmtTable 1 }

HmSetupWlanMngmtCentralFwMngmtFwVersMngmtEntry ::= SEQUENCE {
            hmSetupWlanMngmtCentralFwMngmtFwVersMngmtEntryDevice INTEGER,
            hmSetupWlanMngmtCentralFwMngmtFwVersMngmtEntryMacAddress DisplayString,
            hmSetupWlanMngmtCentralFwMngmtFwVersMngmtEntryVersion DisplayString,
            hmSetupWlanMngmtCentralFwMngmtFwVersMngmtEntryDate DisplayString
    }

-- {COLUMN} 1.3.6.1.4.1.248.32.18.2.37.27.15.1.2
hmSetupWlanMngmtCentralFwMngmtFwVersMngmtEntryDevice OBJECT-TYPE
    SYNTAX     INTEGER {
                  eAllDevices (1),
                  eLancom1821WirelessAdslAnnA (2),
                  eLancom1821WirelessAdslAnnB (3),
                  eLANCOM1821plusWirelessADSLAnnA (5),
                  eLANCOM1821plusWirelessADSLAnnB (6),
                  eLancom1823VoipAnnexA (10),
                  eLancom1823VoipAnnexB (11),
                  eLancomIap54Wireless (12),
                  eLancomL54agWireless (13),
                  eLancom3850Umts (14),
                  eLancom3550Wireless (15),
                  eLancomOap54Wireless (16),
                  eLancomXap402 (19),
                  eLancomL54DualWireless (20),
                  eLancom1811WirelessDsl (21),
                  eLancomL310agnWireless (22),
                  eLancomL54gWireless (23),
                  eLancomXap402Fcc (24),
                  eLancomL305agnWireless (25),
                  eLancom3050Wireless (26),
                  eLancomOap310agnWireless (27),
                  eLancomOap541Wireless (28),
                  eLancom1811nWireless (29),
                  eLancomL315agnDualWireless (30),
                  eBAT54Rail (31),
                  eBAT54RailPlus (32),
                  eBAT300Rail (33),
                  eBAT300F (34),
                  eBAT300FX2 (35),
                  eBAT54F (36),
                  eBAT54FPlus (37),
                  eBAT54FX2 (38),
                  eBAT54FX2Plus (39),
                  eBAT54FSinglePlus (40),
                  eBAT54FX2SinglePlus (41),
                  eLancomL320agnWireless (42),
                  eLancomL321agnWireless (43),
                  eLancomL322agnDualWireless (44),
                  eBAT54RailSinglePlus (45),
                  eLancomOap321 (46),
                  eLancomIap321 (47),
                  eLancom1780ew3g (48),
                  eLancomIap3213g (49),
                  eLancomOap3213g (50),
                  eBAT-R (51),
                  eBAT-F (52),
                  eLancom1781ew (53),
                  eLancom1781aw (54),
                  eLancomOap382 (55),
                  eLancomL451agnWireless (57),
                  eLancomL452agnDualWireless (58),
                  eLancomL460agnDualWireless (59),
                  eLancomOap322 (60),
                  eLancom1780ew4g (61),
                  eLancomIap322 (62),
                  eLancomL1302acnDualWireless (63),
                  eLancomL1310acnDualWireless (64),
                  eLancomL151gnWireless (65),
                  eLancomL320agnWirelessR2 (66),
                  eLancomL321agnWirelessR2 (67),
                  eLancomL322agnDualWirelessR2 (68),
                  eLancomL322eWireless (69),
                  eLancomL151eWireless (70),
                  eLancom1781ewPlus (72),
                  eLancomL822acnDualWireless (73),
                  eLancomOap821 (75),
                  eLancomOap822 (76),
                  eLancomL330agnDualWireless (77),
                  eLancomOap830 (78),
                  eLancom1781vaw (79),
                  eLancom1783vaw (80)
            }
    MAX-ACCESS read-write
    STATUS     current
    DESCRIPTION
            "-- empty --"
    ::= { hmSetupWlanMngmtCentralFwMngmtFwVersMngmtEntry 2 }

-- {COLUMN} 1.3.6.1.4.1.248.32.18.2.37.27.15.1.3
hmSetupWlanMngmtCentralFwMngmtFwVersMngmtEntryMacAddress OBJECT-TYPE
    SYNTAX     DisplayString (SIZE(0..12))
    MAX-ACCESS read-write
    STATUS     current
    DESCRIPTION
            "-- empty --"
    ::= { hmSetupWlanMngmtCentralFwMngmtFwVersMngmtEntry 3 }

-- {COLUMN} 1.3.6.1.4.1.248.32.18.2.37.27.15.1.4
hmSetupWlanMngmtCentralFwMngmtFwVersMngmtEntryVersion OBJECT-TYPE
    SYNTAX     DisplayString (SIZE(0..4))
    MAX-ACCESS read-write
    STATUS     current
    DESCRIPTION
            "-- empty --"
    ::= { hmSetupWlanMngmtCentralFwMngmtFwVersMngmtEntry 4 }

-- {COLUMN} 1.3.6.1.4.1.248.32.18.2.37.27.15.1.5
hmSetupWlanMngmtCentralFwMngmtFwVersMngmtEntryDate OBJECT-TYPE
    SYNTAX     DisplayString (SIZE(0..8))
    MAX-ACCESS read-write
    STATUS     current
    DESCRIPTION
            "-- empty --"
    ::= { hmSetupWlanMngmtCentralFwMngmtFwVersMngmtEntry 5 }

-- {TABLE} 1.3.6.1.4.1.248.32.18.2.37.27.16
hmSetupWlanMngmtCentralFwMngmtScriptMngmtTable OBJECT-TYPE
    SYNTAX     SEQUENCE OF HmSetupWlanMngmtCentralFwMngmtScriptMngmtEntry
    MAX-ACCESS not-accessible
    STATUS     current
    DESCRIPTION
            "script management"
    ::= { hmSetupWlanMngmtCentralFwMngmt 16 }

-- {ROW} 1.3.6.1.4.1.248.32.18.2.37.27.16.1
hmSetupWlanMngmtCentralFwMngmtScriptMngmtEntry OBJECT-TYPE
    SYNTAX     HmSetupWlanMngmtCentralFwMngmtScriptMngmtEntry
    MAX-ACCESS not-accessible
    STATUS     current
    DESCRIPTION
            ""
    INDEX {
            hmSetupWlanMngmtCentralFwMngmtScriptMngmtEntryProfile
          }
    ::= { hmSetupWlanMngmtCentralFwMngmtScriptMngmtTable 1 }

HmSetupWlanMngmtCentralFwMngmtScriptMngmtEntry ::= SEQUENCE {
            hmSetupWlanMngmtCentralFwMngmtScriptMngmtEntryProfile DisplayString,
            hmSetupWlanMngmtCentralFwMngmtScriptMngmtEntryName DisplayString
    }

-- {COLUMN} 1.3.6.1.4.1.248.32.18.2.37.27.16.1.1
hmSetupWlanMngmtCentralFwMngmtScriptMngmtEntryProfile OBJECT-TYPE
    SYNTAX     DisplayString (SIZE(0..31))
    MAX-ACCESS read-write
    STATUS     current
    DESCRIPTION
            "-- empty --"
    ::= { hmSetupWlanMngmtCentralFwMngmtScriptMngmtEntry 1 }

-- {COLUMN} 1.3.6.1.4.1.248.32.18.2.37.27.16.1.2
hmSetupWlanMngmtCentralFwMngmtScriptMngmtEntryName OBJECT-TYPE
    SYNTAX     DisplayString (SIZE(0..63))
    MAX-ACCESS read-write
    STATUS     current
    DESCRIPTION
            "-- empty --"
    ::= { hmSetupWlanMngmtCentralFwMngmtScriptMngmtEntry 2 }

-- {SCALAR} 1.3.6.1.4.1.248.32.18.2.37.27.18
hmSetupWlanMngmtCentralFwMngmtRebootUpdatedAps OBJECT-TYPE
    SYNTAX     DisplayString
    MAX-ACCESS read-write
    STATUS     current
    DESCRIPTION
            "-- empty --"
    ::= { hmSetupWlanMngmtCentralFwMngmt 18 }

-- {SCALAR} 1.3.6.1.4.1.248.32.18.2.37.27.25
hmSetupWlanMngmtCentralFwMngmtFwLoopbkAddr OBJECT-TYPE
    SYNTAX     DisplayString (SIZE(0..16))
    MAX-ACCESS read-write
    STATUS     current
    DESCRIPTION
            "firmware loopback address"
    ::= { hmSetupWlanMngmtCentralFwMngmt 25 }

-- {SCALAR} 1.3.6.1.4.1.248.32.18.2.37.27.26
hmSetupWlanMngmtCentralFwMngmtScriptLoopbAddr OBJECT-TYPE
    SYNTAX     DisplayString (SIZE(0..16))
    MAX-ACCESS read-write
    STATUS     current
    DESCRIPTION
            "script loopback address"
    ::= { hmSetupWlanMngmtCentralFwMngmt 26 }

-- {SCALAR} 1.3.6.1.4.1.248.32.18.2.37.27.38
hmSetupWlanMngmtCentralFwMngmtMaxNumberOfConcurrentUpdates OBJECT-TYPE
    SYNTAX     Integer32 (0..255)
    MAX-ACCESS read-write
    STATUS     current
    DESCRIPTION
            "-- empty --"
    ::= { hmSetupWlanMngmtCentralFwMngmt 38 }

-- {SCALAR} 1.3.6.1.4.1.248.32.18.2.37.29
hmSetupWlanMngmtAllowWanConnections OBJECT-TYPE
    SYNTAX     INTEGER {
                  eNo (0),
                  eVpn (1),
                  eYes (2)
            }
    MAX-ACCESS read-write
    STATUS     current
    DESCRIPTION
            "-- empty --"
    ::= { hmSetupWlanMngmt 29 }

-- {SCALAR} 1.3.6.1.4.1.248.32.18.2.37.30
hmSetupWlanMngmtSyncWtpPassword OBJECT-TYPE
    SYNTAX     INTEGER {
                  eNo (0),
                  eYes (1)
            }
    MAX-ACCESS read-write
    STATUS     current
    DESCRIPTION
            "-- empty --"
    ::= { hmSetupWlanMngmt 30 }

-- {SCALAR} 1.3.6.1.4.1.248.32.18.2.37.31
hmSetupWlanMngmtIntervalForStatusTableCleanup OBJECT-TYPE
    SYNTAX     Integer32 (0..2147483647)
    MAX-ACCESS read-write
    STATUS     current
    DESCRIPTION
            "-- empty --"
    ::= { hmSetupWlanMngmt 31 }

-- {SCALAR} 1.3.6.1.4.1.248.32.18.2.37.32
hmSetupWlanMngmtLicenseCount OBJECT-TYPE
    SYNTAX     Integer32 (0..2147483647)
    MAX-ACCESS read-only
    STATUS     current
    DESCRIPTION
            "-- empty --"
    ::= { hmSetupWlanMngmt 32 }

-- {SCALAR} 1.3.6.1.4.1.248.32.18.2.37.33
hmSetupWlanMngmtLicenseLimit OBJECT-TYPE
    SYNTAX     Integer32 (0..2147483647)
    MAX-ACCESS read-only
    STATUS     current
    DESCRIPTION
            "-- empty --"
    ::= { hmSetupWlanMngmt 33 }

-- {NODE} 1.3.6.1.4.1.248.32.18.2.37.34
hmSetupWlanMngmtWlcTunnels OBJECT IDENTIFIER ::= { hmSetupWlanMngmt 34 }

-- {SCALAR} 1.3.6.1.4.1.248.32.18.2.37.34.2
hmSetupWlanMngmtWlcTunnelsWlcDataTunnelActive OBJECT-TYPE
    SYNTAX     INTEGER {
                  eNo (0),
                  eYes (1)
            }
    MAX-ACCESS read-write
    STATUS     current
    DESCRIPTION
            "-- empty --"
    ::= { hmSetupWlanMngmtWlcTunnels 2 }

-- {TABLE} 1.3.6.1.4.1.248.32.18.2.37.34.3
hmSetupWlanMngmtWlcTunnelsStaticWlcListTable OBJECT-TYPE
    SYNTAX     SEQUENCE OF HmSetupWlanMngmtWlcTunnelsStaticWlcListEntry
    MAX-ACCESS not-accessible
    STATUS     current
    DESCRIPTION
            "-- empty --"
    ::= { hmSetupWlanMngmtWlcTunnels 3 }

-- {ROW} 1.3.6.1.4.1.248.32.18.2.37.34.3.1
hmSetupWlanMngmtWlcTunnelsStaticWlcListEntry OBJECT-TYPE
    SYNTAX     HmSetupWlanMngmtWlcTunnelsStaticWlcListEntry
    MAX-ACCESS not-accessible
    STATUS     current
    DESCRIPTION
            ""
    INDEX {
            hmSetupWlanMngmtWlcTunnelsStaticWlcListEntryIpAddress
          }
    ::= { hmSetupWlanMngmtWlcTunnelsStaticWlcListTable 1 }

HmSetupWlanMngmtWlcTunnelsStaticWlcListEntry ::= SEQUENCE {
            hmSetupWlanMngmtWlcTunnelsStaticWlcListEntryIpAddress IpAddress,
            hmSetupWlanMngmtWlcTunnelsStaticWlcListEntryLoopbackAddr DisplayString,
            hmSetupWlanMngmtWlcTunnelsStaticWlcListEntryPort Integer32
    }

-- {COLUMN} 1.3.6.1.4.1.248.32.18.2.37.34.3.1.1
hmSetupWlanMngmtWlcTunnelsStaticWlcListEntryIpAddress OBJECT-TYPE
    SYNTAX     IpAddress
    MAX-ACCESS read-write
    STATUS     current
    DESCRIPTION
            "-- empty --"
    ::= { hmSetupWlanMngmtWlcTunnelsStaticWlcListEntry 1 }

-- {COLUMN} 1.3.6.1.4.1.248.32.18.2.37.34.3.1.2
hmSetupWlanMngmtWlcTunnelsStaticWlcListEntryLoopbackAddr OBJECT-TYPE
    SYNTAX     DisplayString (SIZE(0..16))
    MAX-ACCESS read-write
    STATUS     current
    DESCRIPTION
            "-- empty --"
    ::= { hmSetupWlanMngmtWlcTunnelsStaticWlcListEntry 2 }

-- {COLUMN} 1.3.6.1.4.1.248.32.18.2.37.34.3.1.3
hmSetupWlanMngmtWlcTunnelsStaticWlcListEntryPort OBJECT-TYPE
    SYNTAX     Integer32 (0..65535)
    MAX-ACCESS read-write
    STATUS     current
    DESCRIPTION
            "-- empty --"
    ::= { hmSetupWlanMngmtWlcTunnelsStaticWlcListEntry 3 }

-- {TABLE} 1.3.6.1.4.1.248.32.18.2.37.34.4
hmSetupWlanMngmtWlcTunnelsWlcDiscoveryTable OBJECT-TYPE
    SYNTAX     SEQUENCE OF HmSetupWlanMngmtWlcTunnelsWlcDiscoveryEntry
    MAX-ACCESS not-accessible
    STATUS     current
    DESCRIPTION
            "-- empty --"
    ::= { hmSetupWlanMngmtWlcTunnels 4 }

-- {ROW} 1.3.6.1.4.1.248.32.18.2.37.34.4.1
hmSetupWlanMngmtWlcTunnelsWlcDiscoveryEntry OBJECT-TYPE
    SYNTAX     HmSetupWlanMngmtWlcTunnelsWlcDiscoveryEntry
    MAX-ACCESS not-accessible
    STATUS     current
    DESCRIPTION
            ""
    INDEX {
            hmSetupWlanMngmtWlcTunnelsWlcDiscoveryEntryNetwork
          }
    ::= { hmSetupWlanMngmtWlcTunnelsWlcDiscoveryTable 1 }

HmSetupWlanMngmtWlcTunnelsWlcDiscoveryEntry ::= SEQUENCE {
            hmSetupWlanMngmtWlcTunnelsWlcDiscoveryEntryNetwork DisplayString,
            hmSetupWlanMngmtWlcTunnelsWlcDiscoveryEntryActive INTEGER,
            hmSetupWlanMngmtWlcTunnelsWlcDiscoveryEntryPort Integer32
    }

-- {COLUMN} 1.3.6.1.4.1.248.32.18.2.37.34.4.1.1
hmSetupWlanMngmtWlcTunnelsWlcDiscoveryEntryNetwork OBJECT-TYPE
    SYNTAX     DisplayString (SIZE(0..16))
    MAX-ACCESS read-write
    STATUS     current
    DESCRIPTION
            "-- empty --"
    ::= { hmSetupWlanMngmtWlcTunnelsWlcDiscoveryEntry 1 }

-- {COLUMN} 1.3.6.1.4.1.248.32.18.2.37.34.4.1.2
hmSetupWlanMngmtWlcTunnelsWlcDiscoveryEntryActive OBJECT-TYPE
    SYNTAX     INTEGER {
                  eNo (0),
                  eYes (1)
            }
    MAX-ACCESS read-write
    STATUS     current
    DESCRIPTION
            "-- empty --"
    ::= { hmSetupWlanMngmtWlcTunnelsWlcDiscoveryEntry 2 }

-- {COLUMN} 1.3.6.1.4.1.248.32.18.2.37.34.4.1.3
hmSetupWlanMngmtWlcTunnelsWlcDiscoveryEntryPort OBJECT-TYPE
    SYNTAX     Integer32 (0..65535)
    MAX-ACCESS read-write
    STATUS     current
    DESCRIPTION
            "-- empty --"
    ::= { hmSetupWlanMngmtWlcTunnelsWlcDiscoveryEntry 3 }

-- {SCALAR} 1.3.6.1.4.1.248.32.18.2.37.34.5
hmSetupWlanMngmtWlcTunnelsTriggerWlcRediscoveryOnWtps OBJECT-TYPE
    SYNTAX     DisplayString
    MAX-ACCESS read-write
    STATUS     current
    DESCRIPTION
            "-- empty --"
    ::= { hmSetupWlanMngmtWlcTunnels 5 }

-- {SCALAR} 1.3.6.1.4.1.248.32.18.2.37.34.6
hmSetupWlanMngmtWlcTunnelsWlcTunnelActive OBJECT-TYPE
    SYNTAX     INTEGER {
                  eNo (0),
                  eYes (1)
            }
    MAX-ACCESS read-write
    STATUS     current
    DESCRIPTION
            "-- empty --"
    ::= { hmSetupWlanMngmtWlcTunnels 6 }

-- {TABLE} 1.3.6.1.4.1.248.32.18.2.37.35
hmSetupWlanMngmtRadiusServerProfilesTable OBJECT-TYPE
    SYNTAX     SEQUENCE OF HmSetupWlanMngmtRadiusServerProfilesEntry
    MAX-ACCESS not-accessible
    STATUS     current
    DESCRIPTION
            "-- empty --"
    ::= { hmSetupWlanMngmt 35 }

-- {ROW} 1.3.6.1.4.1.248.32.18.2.37.35.1
hmSetupWlanMngmtRadiusServerProfilesEntry OBJECT-TYPE
    SYNTAX     HmSetupWlanMngmtRadiusServerProfilesEntry
    MAX-ACCESS not-accessible
    STATUS     current
    DESCRIPTION
            ""
    INDEX {
            hmSetupWlanMngmtRadiusServerProfilesEntryName
          }
    ::= { hmSetupWlanMngmtRadiusServerProfilesTable 1 }

HmSetupWlanMngmtRadiusServerProfilesEntry ::= SEQUENCE {
            hmSetupWlanMngmtRadiusServerProfilesEntryName DisplayString,
            hmSetupWlanMngmtRadiusServerProfilesEntryAccountIp IpAddress,
            hmSetupWlanMngmtRadiusServerProfilesEntryAccountPort Integer32,
            hmSetupWlanMngmtRadiusServerProfilesEntryAccountSecret DisplayString,
            hmSetupWlanMngmtRadiusServerProfilesEntryAccountLoopback DisplayString,
            hmSetupWlanMngmtRadiusServerProfilesEntryAccountProtocol INTEGER,
            hmSetupWlanMngmtRadiusServerProfilesEntryAccessIp IpAddress,
            hmSetupWlanMngmtRadiusServerProfilesEntryAccessPort Integer32,
            hmSetupWlanMngmtRadiusServerProfilesEntryAccessSecret DisplayString,
            hmSetupWlanMngmtRadiusServerProfilesEntryAccessLoopback DisplayString,
            hmSetupWlanMngmtRadiusServerProfilesEntryAccessProtocol INTEGER,
            hmSetupWlanMngmtRadiusServerProfilesEntryBackup DisplayString
    }

-- {COLUMN} 1.3.6.1.4.1.248.32.18.2.37.35.1.1
hmSetupWlanMngmtRadiusServerProfilesEntryName OBJECT-TYPE
    SYNTAX     DisplayString (SIZE(0..16))
    MAX-ACCESS read-write
    STATUS     current
    DESCRIPTION
            "-- empty --"
    ::= { hmSetupWlanMngmtRadiusServerProfilesEntry 1 }

-- {COLUMN} 1.3.6.1.4.1.248.32.18.2.37.35.1.2
hmSetupWlanMngmtRadiusServerProfilesEntryAccountIp OBJECT-TYPE
    SYNTAX     IpAddress
    MAX-ACCESS read-write
    STATUS     current
    DESCRIPTION
            "-- empty --"
    ::= { hmSetupWlanMngmtRadiusServerProfilesEntry 2 }

-- {COLUMN} 1.3.6.1.4.1.248.32.18.2.37.35.1.3
hmSetupWlanMngmtRadiusServerProfilesEntryAccountPort OBJECT-TYPE
    SYNTAX     Integer32 (0..65535)
    MAX-ACCESS read-write
    STATUS     current
    DESCRIPTION
            "-- empty --"
    ::= { hmSetupWlanMngmtRadiusServerProfilesEntry 3 }

-- {COLUMN} 1.3.6.1.4.1.248.32.18.2.37.35.1.4
hmSetupWlanMngmtRadiusServerProfilesEntryAccountSecret OBJECT-TYPE
    SYNTAX     DisplayString (SIZE(0..64))
    MAX-ACCESS read-write
    STATUS     current
    DESCRIPTION
            "-- empty --"
    ::= { hmSetupWlanMngmtRadiusServerProfilesEntry 4 }

-- {COLUMN} 1.3.6.1.4.1.248.32.18.2.37.35.1.5
hmSetupWlanMngmtRadiusServerProfilesEntryAccountLoopback OBJECT-TYPE
    SYNTAX     DisplayString (SIZE(0..16))
    MAX-ACCESS read-write
    STATUS     current
    DESCRIPTION
            "-- empty --"
    ::= { hmSetupWlanMngmtRadiusServerProfilesEntry 5 }

-- {COLUMN} 1.3.6.1.4.1.248.32.18.2.37.35.1.6
hmSetupWlanMngmtRadiusServerProfilesEntryAccountProtocol OBJECT-TYPE
    SYNTAX     INTEGER {
                  eRadius (0),
                  eRadsec (1)
            }
    MAX-ACCESS read-write
    STATUS     current
    DESCRIPTION
            "-- empty --"
    ::= { hmSetupWlanMngmtRadiusServerProfilesEntry 6 }

-- {COLUMN} 1.3.6.1.4.1.248.32.18.2.37.35.1.7
hmSetupWlanMngmtRadiusServerProfilesEntryAccessIp OBJECT-TYPE
    SYNTAX     IpAddress
    MAX-ACCESS read-write
    STATUS     current
    DESCRIPTION
            "-- empty --"
    ::= { hmSetupWlanMngmtRadiusServerProfilesEntry 7 }

-- {COLUMN} 1.3.6.1.4.1.248.32.18.2.37.35.1.8
hmSetupWlanMngmtRadiusServerProfilesEntryAccessPort OBJECT-TYPE
    SYNTAX     Integer32 (0..65535)
    MAX-ACCESS read-write
    STATUS     current
    DESCRIPTION
            "-- empty --"
    ::= { hmSetupWlanMngmtRadiusServerProfilesEntry 8 }

-- {COLUMN} 1.3.6.1.4.1.248.32.18.2.37.35.1.9
hmSetupWlanMngmtRadiusServerProfilesEntryAccessSecret OBJECT-TYPE
    SYNTAX     DisplayString (SIZE(0..64))
    MAX-ACCESS read-write
    STATUS     current
    DESCRIPTION
            "-- empty --"
    ::= { hmSetupWlanMngmtRadiusServerProfilesEntry 9 }

-- {COLUMN} 1.3.6.1.4.1.248.32.18.2.37.35.1.10
hmSetupWlanMngmtRadiusServerProfilesEntryAccessLoopback OBJECT-TYPE
    SYNTAX     DisplayString (SIZE(0..16))
    MAX-ACCESS read-write
    STATUS     current
    DESCRIPTION
            "-- empty --"
    ::= { hmSetupWlanMngmtRadiusServerProfilesEntry 10 }

-- {COLUMN} 1.3.6.1.4.1.248.32.18.2.37.35.1.11
hmSetupWlanMngmtRadiusServerProfilesEntryAccessProtocol OBJECT-TYPE
    SYNTAX     INTEGER {
                  eRadius (0),
                  eRadsec (1)
            }
    MAX-ACCESS read-write
    STATUS     current
    DESCRIPTION
            "-- empty --"
    ::= { hmSetupWlanMngmtRadiusServerProfilesEntry 11 }

-- {COLUMN} 1.3.6.1.4.1.248.32.18.2.37.35.1.12
hmSetupWlanMngmtRadiusServerProfilesEntryBackup OBJECT-TYPE
    SYNTAX     DisplayString (SIZE(0..16))
    MAX-ACCESS read-write
    STATUS     current
    DESCRIPTION
            "-- empty --"
    ::= { hmSetupWlanMngmtRadiusServerProfilesEntry 12 }

-- {SCALAR} 1.3.6.1.4.1.248.32.18.2.37.36
hmSetupWlanMngmtCapwapOperating OBJECT-TYPE
    SYNTAX     INTEGER {
                  eNo (0),
                  eYes (1)
            }
    MAX-ACCESS read-write
    STATUS     current
    DESCRIPTION
            "-- empty --"
    ::= { hmSetupWlanMngmt 36 }

-- {SCALAR} 1.3.6.1.4.1.248.32.18.2.37.37
hmSetupWlanMngmtPreference OBJECT-TYPE
    SYNTAX     Integer32 (0..255)
    MAX-ACCESS read-write
    STATUS     current
    DESCRIPTION
            "-- empty --"
    ::= { hmSetupWlanMngmt 37 }

-- {NODE} 1.3.6.1.4.1.248.32.18.2.37.40
hmSetupWlanMngmtClSte OBJECT IDENTIFIER ::= { hmSetupWlanMngmt 40 }

-- {SCALAR} 1.3.6.1.4.1.248.32.18.2.37.40.11
hmSetupWlanMngmtClSteTraceMac OBJECT-TYPE
    SYNTAX     MacAddress
    MAX-ACCESS read-write
    STATUS     current
    DESCRIPTION
            "-- empty --"
    ::= { hmSetupWlanMngmtClSte 11 }

-- {SCALAR} 1.3.6.1.4.1.248.32.18.2.37.40.17
hmSetupWlanMngmtClSteAcquireStatisticalData OBJECT-TYPE
    SYNTAX     INTEGER {
                  eNo (0),
                  eYes (1)
            }
    MAX-ACCESS read-write
    STATUS     current
    DESCRIPTION
            "-- empty --"
    ::= { hmSetupWlanMngmtClSte 17 }

-- {TABLE} 1.3.6.1.4.1.248.32.18.2.37.40.19
hmSetupWlanMngmtClSteProfilesTable OBJECT-TYPE
    SYNTAX     SEQUENCE OF HmSetupWlanMngmtClSteProfilesEntry
    MAX-ACCESS not-accessible
    STATUS     current
    DESCRIPTION
            "-- empty --"
    ::= { hmSetupWlanMngmtClSte 19 }

-- {ROW} 1.3.6.1.4.1.248.32.18.2.37.40.19.1
hmSetupWlanMngmtClSteProfilesEntry OBJECT-TYPE
    SYNTAX     HmSetupWlanMngmtClSteProfilesEntry
    MAX-ACCESS not-accessible
    STATUS     current
    DESCRIPTION
            ""
    INDEX {
            hmSetupWlanMngmtClSteProfilesEntryName
          }
    ::= { hmSetupWlanMngmtClSteProfilesTable 1 }

HmSetupWlanMngmtClSteProfilesEntry ::= SEQUENCE {
            hmSetupWlanMngmtClSteProfilesEntryName DisplayString,
            hmSetupWlanMngmtClSteProfilesEntryToleranceLevel Integer32,
            hmSetupWlanMngmtClSteProfilesEntrySignalStrengthWeighting Integer32,
            hmSetupWlanMngmtClSteProfilesEntryAssociatedClientsWeighting Integer32,
            hmSetupWlanMngmtClSteProfilesEntryFrequencyBandWeighting Integer32,
            hmSetupWlanMngmtClSteProfilesEntryPreferredBand INTEGER,
            hmSetupWlanMngmtClSteProfilesEntryDisassociationThreshold Integer32,
            hmSetupWlanMngmtClSteProfilesEntryTimeToDisassociation Integer32
    }

-- {COLUMN} 1.3.6.1.4.1.248.32.18.2.37.40.19.1.1
hmSetupWlanMngmtClSteProfilesEntryName OBJECT-TYPE
    SYNTAX     DisplayString (SIZE(0..31))
    MAX-ACCESS read-write
    STATUS     current
    DESCRIPTION
            "-- empty --"
    ::= { hmSetupWlanMngmtClSteProfilesEntry 1 }

-- {COLUMN} 1.3.6.1.4.1.248.32.18.2.37.40.19.1.2
hmSetupWlanMngmtClSteProfilesEntryToleranceLevel OBJECT-TYPE
    SYNTAX     Integer32 (0..255)
    MAX-ACCESS read-write
    STATUS     current
    DESCRIPTION
            "-- empty --"
    ::= { hmSetupWlanMngmtClSteProfilesEntry 2 }

-- {COLUMN} 1.3.6.1.4.1.248.32.18.2.37.40.19.1.4
hmSetupWlanMngmtClSteProfilesEntrySignalStrengthWeighting OBJECT-TYPE
    SYNTAX     Integer32 (0..2147483647)
    MAX-ACCESS read-write
    STATUS     current
    DESCRIPTION
            "-- empty --"
    ::= { hmSetupWlanMngmtClSteProfilesEntry 4 }

-- {COLUMN} 1.3.6.1.4.1.248.32.18.2.37.40.19.1.5
hmSetupWlanMngmtClSteProfilesEntryAssociatedClientsWeighting OBJECT-TYPE
    SYNTAX     Integer32 (0..2147483647)
    MAX-ACCESS read-write
    STATUS     current
    DESCRIPTION
            "-- empty --"
    ::= { hmSetupWlanMngmtClSteProfilesEntry 5 }

-- {COLUMN} 1.3.6.1.4.1.248.32.18.2.37.40.19.1.6
hmSetupWlanMngmtClSteProfilesEntryFrequencyBandWeighting OBJECT-TYPE
    SYNTAX     Integer32 (0..2147483647)
    MAX-ACCESS read-write
    STATUS     current
    DESCRIPTION
            "-- empty --"
    ::= { hmSetupWlanMngmtClSteProfilesEntry 6 }

-- {COLUMN} 1.3.6.1.4.1.248.32.18.2.37.40.19.1.9
hmSetupWlanMngmtClSteProfilesEntryPreferredBand OBJECT-TYPE
    SYNTAX     INTEGER {
                  e24ghz (1),
                  e5ghz (2)
            }
    MAX-ACCESS read-write
    STATUS     current
    DESCRIPTION
            "-- empty --"
    ::= { hmSetupWlanMngmtClSteProfilesEntry 9 }

-- {COLUMN} 1.3.6.1.4.1.248.32.18.2.37.40.19.1.10
hmSetupWlanMngmtClSteProfilesEntryDisassociationThreshold OBJECT-TYPE
    SYNTAX     Integer32 (0..255)
    MAX-ACCESS read-write
    STATUS     current
    DESCRIPTION
            "-- empty --"
    ::= { hmSetupWlanMngmtClSteProfilesEntry 10 }

-- {COLUMN} 1.3.6.1.4.1.248.32.18.2.37.40.19.1.11
hmSetupWlanMngmtClSteProfilesEntryTimeToDisassociation OBJECT-TYPE
    SYNTAX     Integer32 (0..255)
    MAX-ACCESS read-write
    STATUS     current
    DESCRIPTION
            "-- empty --"
    ::= { hmSetupWlanMngmtClSteProfilesEntry 11 }

-- {SCALAR} 1.3.6.1.4.1.248.32.18.2.37.40.20
hmSetupWlanMngmtClSteClientMacStatisticFilter OBJECT-TYPE
    SYNTAX     DisplayString (SIZE(0..251))
    MAX-ACCESS read-write
    STATUS     current
    DESCRIPTION
            "-- empty --"
    ::= { hmSetupWlanMngmtClSte 20 }

-- {NODE} 1.3.6.1.4.1.248.32.18.2.38
hmSetupLldp OBJECT IDENTIFIER ::= { hmSetup 38 }

-- {SCALAR} 1.3.6.1.4.1.248.32.18.2.38.1
hmSetupLldpMessageTxInterval OBJECT-TYPE
    SYNTAX     Integer32 (0..2147483647)
    MAX-ACCESS read-write
    STATUS     current
    DESCRIPTION
            "-- empty --"
    ::= { hmSetupLldp 1 }

-- {SCALAR} 1.3.6.1.4.1.248.32.18.2.38.2
hmSetupLldpMessageTxHoldMultiplier OBJECT-TYPE
    SYNTAX     Integer32 (0..2147483647)
    MAX-ACCESS read-write
    STATUS     current
    DESCRIPTION
            "-- empty --"
    ::= { hmSetupLldp 2 }

-- {SCALAR} 1.3.6.1.4.1.248.32.18.2.38.3
hmSetupLldpReinitDelay OBJECT-TYPE
    SYNTAX     Integer32 (0..2147483647)
    MAX-ACCESS read-write
    STATUS     current
    DESCRIPTION
            "-- empty --"
    ::= { hmSetupLldp 3 }

-- {SCALAR} 1.3.6.1.4.1.248.32.18.2.38.4
hmSetupLldpTxDelay OBJECT-TYPE
    SYNTAX     Integer32 (0..2147483647)
    MAX-ACCESS read-write
    STATUS     current
    DESCRIPTION
            "-- empty --"
    ::= { hmSetupLldp 4 }

-- {SCALAR} 1.3.6.1.4.1.248.32.18.2.38.5
hmSetupLldpNotificationInterval OBJECT-TYPE
    SYNTAX     Integer32 (0..2147483647)
    MAX-ACCESS read-write
    STATUS     current
    DESCRIPTION
            "-- empty --"
    ::= { hmSetupLldp 5 }

-- {TABLE} 1.3.6.1.4.1.248.32.18.2.38.6
hmSetupLldpPortsTable OBJECT-TYPE
    SYNTAX     SEQUENCE OF HmSetupLldpPortsEntry
    MAX-ACCESS not-accessible
    STATUS     current
    DESCRIPTION
            "-- empty --"
    ::= { hmSetupLldp 6 }

-- {ROW} 1.3.6.1.4.1.248.32.18.2.38.6.1
hmSetupLldpPortsEntry OBJECT-TYPE
    SYNTAX     HmSetupLldpPortsEntry
    MAX-ACCESS not-accessible
    STATUS     current
    DESCRIPTION
            ""
    INDEX {
            hmSetupLldpPortsEntryName
          }
    ::= { hmSetupLldpPortsTable 1 }

HmSetupLldpPortsEntry ::= SEQUENCE {
            hmSetupLldpPortsEntryName DisplayString,
            hmSetupLldpPortsEntryAdminStatus INTEGER,
            hmSetupLldpPortsEntryNotifications INTEGER,
            hmSetupLldpPortsEntryTlvs BITS,
            hmSetupLldpPortsEntryTlvs8023 BITS,
            hmSetupLldpPortsEntryMaxNeighbours Integer32,
            hmSetupLldpPortsEntryUpdateSource INTEGER,
            hmSetupLldpPortsEntryTlvsLcs BITS
    }

-- {COLUMN} 1.3.6.1.4.1.248.32.18.2.38.6.1.1
hmSetupLldpPortsEntryName OBJECT-TYPE
    SYNTAX     DisplayString (SIZE(0..18))
    MAX-ACCESS read-only
    STATUS     current
    DESCRIPTION
            "-- empty --"
    ::= { hmSetupLldpPortsEntry 1 }

-- {COLUMN} 1.3.6.1.4.1.248.32.18.2.38.6.1.2
hmSetupLldpPortsEntryAdminStatus OBJECT-TYPE
    SYNTAX     INTEGER {
                  eDisabled (0),
                  eTxOnly (1),
                  eRxOnly (2),
                  eRxTx (3)
            }
    MAX-ACCESS read-write
    STATUS     current
    DESCRIPTION
            "-- empty --"
    ::= { hmSetupLldpPortsEntry 2 }

-- {COLUMN} 1.3.6.1.4.1.248.32.18.2.38.6.1.3
hmSetupLldpPortsEntryNotifications OBJECT-TYPE
    SYNTAX     INTEGER {
                  eNo (0),
                  eYes (1)
            }
    MAX-ACCESS read-write
    STATUS     current
    DESCRIPTION
            "-- empty --"
    ::= { hmSetupLldpPortsEntry 3 }

-- {COLUMN} 1.3.6.1.4.1.248.32.18.2.38.6.1.4
hmSetupLldpPortsEntryTlvs OBJECT-TYPE
    SYNTAX     BITS {
                  ePortDescription (0),
                  eSysName (1),
                  eSysDescriptor (2),
                  eSysCaps (3),
                  eNone (7)
            }
    MAX-ACCESS read-write
    STATUS     current
    DESCRIPTION
            "-- empty --"
    ::= { hmSetupLldpPortsEntry 4 }

-- {COLUMN} 1.3.6.1.4.1.248.32.18.2.38.6.1.6
hmSetupLldpPortsEntryTlvs8023 OBJECT-TYPE
    SYNTAX     BITS {
                  ePhyConfigStatus (0),
                  ePowerViaMdi (1),
                  eLinkAggregation (2),
                  eMaxFrameSize (3),
                  eNone (7)
            }
    MAX-ACCESS read-write
    STATUS     current
    DESCRIPTION
            "-- empty --"
    ::= { hmSetupLldpPortsEntry 6 }

-- {COLUMN} 1.3.6.1.4.1.248.32.18.2.38.6.1.7
hmSetupLldpPortsEntryMaxNeighbours OBJECT-TYPE
    SYNTAX     Integer32 (0..65535)
    MAX-ACCESS read-write
    STATUS     current
    DESCRIPTION
            "-- empty --"
    ::= { hmSetupLldpPortsEntry 7 }

-- {COLUMN} 1.3.6.1.4.1.248.32.18.2.38.6.1.8
hmSetupLldpPortsEntryUpdateSource OBJECT-TYPE
    SYNTAX     INTEGER {
                  eLldpOnly (0),
                  eOtherOnly (1),
                  eBoth (2),
                  eAuto (3)
            }
    MAX-ACCESS read-write
    STATUS     current
    DESCRIPTION
            "-- empty --"
    ::= { hmSetupLldpPortsEntry 8 }

-- {COLUMN} 1.3.6.1.4.1.248.32.18.2.38.6.1.9
hmSetupLldpPortsEntryTlvsLcs OBJECT-TYPE
    SYNTAX     BITS {
                  eSsid (0),
                  eRadioChannel (1),
                  ePhyType (2),
                  eNone (7)
            }
    MAX-ACCESS read-write
    STATUS     current
    DESCRIPTION
            "-- empty --"
    ::= { hmSetupLldpPortsEntry 9 }

-- {TABLE} 1.3.6.1.4.1.248.32.18.2.38.7
hmSetupLldpManagementAddressesTable OBJECT-TYPE
    SYNTAX     SEQUENCE OF HmSetupLldpManagementAddressesEntry
    MAX-ACCESS not-accessible
    STATUS     current
    DESCRIPTION
            "-- empty --"
    ::= { hmSetupLldp 7 }

-- {ROW} 1.3.6.1.4.1.248.32.18.2.38.7.1
hmSetupLldpManagementAddressesEntry OBJECT-TYPE
    SYNTAX     HmSetupLldpManagementAddressesEntry
    MAX-ACCESS not-accessible
    STATUS     current
    DESCRIPTION
            ""
    INDEX {
            hmSetupLldpManagementAddressesEntryNetworkName
          }
    ::= { hmSetupLldpManagementAddressesTable 1 }

HmSetupLldpManagementAddressesEntry ::= SEQUENCE {
            hmSetupLldpManagementAddressesEntryNetworkName DisplayString,
            hmSetupLldpManagementAddressesEntryPortList DisplayString
    }

-- {COLUMN} 1.3.6.1.4.1.248.32.18.2.38.7.1.1
hmSetupLldpManagementAddressesEntryNetworkName OBJECT-TYPE
    SYNTAX     DisplayString (SIZE(0..16))
    MAX-ACCESS read-write
    STATUS     current
    DESCRIPTION
            "-- empty --"
    ::= { hmSetupLldpManagementAddressesEntry 1 }

-- {COLUMN} 1.3.6.1.4.1.248.32.18.2.38.7.1.2
hmSetupLldpManagementAddressesEntryPortList OBJECT-TYPE
    SYNTAX     DisplayString (SIZE(0..251))
    MAX-ACCESS read-write
    STATUS     current
    DESCRIPTION
            "-- empty --"
    ::= { hmSetupLldpManagementAddressesEntry 2 }

-- {TABLE} 1.3.6.1.4.1.248.32.18.2.38.8
hmSetupLldpProtocolsTable OBJECT-TYPE
    SYNTAX     SEQUENCE OF HmSetupLldpProtocolsEntry
    MAX-ACCESS not-accessible
    STATUS     current
    DESCRIPTION
            "-- empty --"
    ::= { hmSetupLldp 8 }

-- {ROW} 1.3.6.1.4.1.248.32.18.2.38.8.1
hmSetupLldpProtocolsEntry OBJECT-TYPE
    SYNTAX     HmSetupLldpProtocolsEntry
    MAX-ACCESS not-accessible
    STATUS     current
    DESCRIPTION
            ""
    INDEX {
            hmSetupLldpProtocolsEntryProtocol
          }
    ::= { hmSetupLldpProtocolsTable 1 }

HmSetupLldpProtocolsEntry ::= SEQUENCE {
            hmSetupLldpProtocolsEntryProtocol INTEGER,
            hmSetupLldpProtocolsEntryPortList DisplayString
    }

-- {COLUMN} 1.3.6.1.4.1.248.32.18.2.38.8.1.1
hmSetupLldpProtocolsEntryProtocol OBJECT-TYPE
    SYNTAX     INTEGER {
                  eSpanningTree (1),
                  eRapidSpanningTree (2)
            }
    MAX-ACCESS read-only
    STATUS     current
    DESCRIPTION
            "-- empty --"
    ::= { hmSetupLldpProtocolsEntry 1 }

-- {COLUMN} 1.3.6.1.4.1.248.32.18.2.38.8.1.2
hmSetupLldpProtocolsEntryPortList OBJECT-TYPE
    SYNTAX     DisplayString (SIZE(0..251))
    MAX-ACCESS read-write
    STATUS     current
    DESCRIPTION
            "-- empty --"
    ::= { hmSetupLldpProtocolsEntry 2 }

-- {SCALAR} 1.3.6.1.4.1.248.32.18.2.38.10
hmSetupLldpOperating OBJECT-TYPE
    SYNTAX     INTEGER {
                  eNo (0),
                  eYes (1)
            }
    MAX-ACCESS read-write
    STATUS     current
    DESCRIPTION
            "-- empty --"
    ::= { hmSetupLldp 10 }

-- {NODE} 1.3.6.1.4.1.248.32.18.2.39
hmSetupCerts OBJECT IDENTIFIER ::= { hmSetup 39 }

-- {NODE} 1.3.6.1.4.1.248.32.18.2.39.1
hmSetupCertsScepClnt OBJECT IDENTIFIER ::= { hmSetupCerts 1 }

-- {SCALAR} 1.3.6.1.4.1.248.32.18.2.39.1.1
hmSetupCertsScepClntScepOperating OBJECT-TYPE
    SYNTAX     INTEGER {
                  eNo (0),
                  eYes (1)
            }
    MAX-ACCESS read-write
    STATUS     current
    DESCRIPTION
            "-- empty --"
    ::= { hmSetupCertsScepClnt 1 }

-- {SCALAR} 1.3.6.1.4.1.248.32.18.2.39.1.2
hmSetupCertsScepClntDeviceCertificateUpdateBefore OBJECT-TYPE
    SYNTAX     Integer32 (0..2147483647)
    MAX-ACCESS read-write
    STATUS     current
    DESCRIPTION
            "-- empty --"
    ::= { hmSetupCertsScepClnt 2 }

-- {SCALAR} 1.3.6.1.4.1.248.32.18.2.39.1.3
hmSetupCertsScepClntCaCertificateUpdateBefore OBJECT-TYPE
    SYNTAX     Integer32 (0..2147483647)
    MAX-ACCESS read-write
    STATUS     current
    DESCRIPTION
            "-- empty --"
    ::= { hmSetupCertsScepClnt 3 }

-- {TABLE} 1.3.6.1.4.1.248.32.18.2.39.1.7
hmSetupCertsScepClntCertsTable OBJECT-TYPE
    SYNTAX     SEQUENCE OF HmSetupCertsScepClntCertsEntry
    MAX-ACCESS not-accessible
    STATUS     current
    DESCRIPTION
            ""
    ::= { hmSetupCertsScepClnt 7 }

-- {ROW} 1.3.6.1.4.1.248.32.18.2.39.1.7.1
hmSetupCertsScepClntCertsEntry OBJECT-TYPE
    SYNTAX     HmSetupCertsScepClntCertsEntry
    MAX-ACCESS not-accessible
    STATUS     current
    DESCRIPTION
            ""
    INDEX {
            hmSetupCertsScepClntCertsEntryName
          }
    ::= { hmSetupCertsScepClntCertsTable 1 }

HmSetupCertsScepClntCertsEntry ::= SEQUENCE {
            hmSetupCertsScepClntCertsEntryName DisplayString,
            hmSetupCertsScepClntCertsEntryCadn DisplayString,
            hmSetupCertsScepClntCertsEntrySubject DisplayString,
            hmSetupCertsScepClntCertsEntryChallengepwd DisplayString,
            hmSetupCertsScepClntCertsEntrySubjectaltname DisplayString,
            hmSetupCertsScepClntCertsEntryKeyusage DisplayString,
            hmSetupCertsScepClntCertsEntryDevCertKeyl Integer32,
            hmSetupCertsScepClntCertsEntryApplication INTEGER,
            hmSetupCertsScepClntCertsEntryExtendedKeyusage DisplayString
    }

-- {COLUMN} 1.3.6.1.4.1.248.32.18.2.39.1.7.1.1
hmSetupCertsScepClntCertsEntryName OBJECT-TYPE
    SYNTAX     DisplayString (SIZE(0..16))
    MAX-ACCESS read-write
    STATUS     current
    DESCRIPTION
            "-- empty --"
    ::= { hmSetupCertsScepClntCertsEntry 1 }

-- {COLUMN} 1.3.6.1.4.1.248.32.18.2.39.1.7.1.2
hmSetupCertsScepClntCertsEntryCadn OBJECT-TYPE
    SYNTAX     DisplayString (SIZE(0..251))
    MAX-ACCESS read-write
    STATUS     current
    DESCRIPTION
            "-- empty --"
    ::= { hmSetupCertsScepClntCertsEntry 2 }

-- {COLUMN} 1.3.6.1.4.1.248.32.18.2.39.1.7.1.3
hmSetupCertsScepClntCertsEntrySubject OBJECT-TYPE
    SYNTAX     DisplayString (SIZE(0..251))
    MAX-ACCESS read-write
    STATUS     current
    DESCRIPTION
            "-- empty --"
    ::= { hmSetupCertsScepClntCertsEntry 3 }

-- {COLUMN} 1.3.6.1.4.1.248.32.18.2.39.1.7.1.4
hmSetupCertsScepClntCertsEntryChallengepwd OBJECT-TYPE
    SYNTAX     DisplayString (SIZE(0..251))
    MAX-ACCESS read-write
    STATUS     current
    DESCRIPTION
            "-- empty --"
    ::= { hmSetupCertsScepClntCertsEntry 4 }

-- {COLUMN} 1.3.6.1.4.1.248.32.18.2.39.1.7.1.5
hmSetupCertsScepClntCertsEntrySubjectaltname OBJECT-TYPE
    SYNTAX     DisplayString (SIZE(0..251))
    MAX-ACCESS read-write
    STATUS     current
    DESCRIPTION
            "-- empty --"
    ::= { hmSetupCertsScepClntCertsEntry 5 }

-- {COLUMN} 1.3.6.1.4.1.248.32.18.2.39.1.7.1.6
hmSetupCertsScepClntCertsEntryKeyusage OBJECT-TYPE
    SYNTAX     DisplayString (SIZE(0..251))
    MAX-ACCESS read-write
    STATUS     current
    DESCRIPTION
            "-- empty --"
    ::= { hmSetupCertsScepClntCertsEntry 6 }

-- {COLUMN} 1.3.6.1.4.1.248.32.18.2.39.1.7.1.7
hmSetupCertsScepClntCertsEntryDevCertKeyl OBJECT-TYPE
    SYNTAX     Integer32 (0..2147483647)
    MAX-ACCESS read-write
    STATUS     current
    DESCRIPTION
            ""
    ::= { hmSetupCertsScepClntCertsEntry 7 }

-- {COLUMN} 1.3.6.1.4.1.248.32.18.2.39.1.7.1.8
hmSetupCertsScepClntCertsEntryApplication OBJECT-TYPE
    SYNTAX     INTEGER {
                  eUnconfigured (-1),
                  eVpn1 (0),
                  eWlanController (1),
                  eEapTls (3),
                  eVpn2 (5),
                  eVpn3 (6),
                  eVpn4 (7),
                  eVpn5 (8),
                  eVpn6 (9),
                  eVpn7 (10),
                  eVpn8 (11),
                  eVpn9 (12),
                  eDefault (13),
                  eCa (14),
                  eConfigsync (15)
            }
    MAX-ACCESS read-write
    STATUS     current
    DESCRIPTION
            "-- empty --"
    ::= { hmSetupCertsScepClntCertsEntry 8 }

-- {COLUMN} 1.3.6.1.4.1.248.32.18.2.39.1.7.1.9
hmSetupCertsScepClntCertsEntryExtendedKeyusage OBJECT-TYPE
    SYNTAX     DisplayString (SIZE(0..251))
    MAX-ACCESS read-write
    STATUS     current
    DESCRIPTION
            "-- empty --"
    ::= { hmSetupCertsScepClntCertsEntry 9 }

-- {SCALAR} 1.3.6.1.4.1.248.32.18.2.39.1.8
hmSetupCertsScepClntReinit OBJECT-TYPE
    SYNTAX     DisplayString
    MAX-ACCESS read-write
    STATUS     current
    DESCRIPTION
            "-- empty --"
    ::= { hmSetupCertsScepClnt 8 }

-- {SCALAR} 1.3.6.1.4.1.248.32.18.2.39.1.9
hmSetupCertsScepClntUpdate OBJECT-TYPE
    SYNTAX     DisplayString
    MAX-ACCESS read-write
    STATUS     current
    DESCRIPTION
            "-- empty --"
    ::= { hmSetupCertsScepClnt 9 }

-- {SCALAR} 1.3.6.1.4.1.248.32.18.2.39.1.10
hmSetupCertsScepClntClearScepFilesystem OBJECT-TYPE
    SYNTAX     DisplayString
    MAX-ACCESS read-write
    STATUS     current
    DESCRIPTION
            "-- empty --"
    ::= { hmSetupCertsScepClnt 10 }

-- {SCALAR} 1.3.6.1.4.1.248.32.18.2.39.1.11
hmSetupCertsScepClntRetryAfterErrorInterval OBJECT-TYPE
    SYNTAX     Integer32 (0..2147483647)
    MAX-ACCESS read-write
    STATUS     current
    DESCRIPTION
            "-- empty --"
    ::= { hmSetupCertsScepClnt 11 }

-- {SCALAR} 1.3.6.1.4.1.248.32.18.2.39.1.12
hmSetupCertsScepClntCheckPendingRequestsInterval OBJECT-TYPE
    SYNTAX     Integer32 (0..2147483647)
    MAX-ACCESS read-write
    STATUS     current
    DESCRIPTION
            "-- empty --"
    ::= { hmSetupCertsScepClnt 12 }

-- {SCALAR} 1.3.6.1.4.1.248.32.18.2.39.1.13
hmSetupCertsScepClntTraceLevel OBJECT-TYPE
    SYNTAX     INTEGER {
                  eOnlyErrors (3),
                  eReduced (6),
                  eAll (7)
            }
    MAX-ACCESS read-write
    STATUS     current
    DESCRIPTION
            "-- empty --"
    ::= { hmSetupCertsScepClnt 13 }

-- {TABLE} 1.3.6.1.4.1.248.32.18.2.39.1.14
hmSetupCertsScepClntCasTable OBJECT-TYPE
    SYNTAX     SEQUENCE OF HmSetupCertsScepClntCasEntry
    MAX-ACCESS not-accessible
    STATUS     current
    DESCRIPTION
            "-- empty --"
    ::= { hmSetupCertsScepClnt 14 }

-- {ROW} 1.3.6.1.4.1.248.32.18.2.39.1.14.1
hmSetupCertsScepClntCasEntry OBJECT-TYPE
    SYNTAX     HmSetupCertsScepClntCasEntry
    MAX-ACCESS not-accessible
    STATUS     current
    DESCRIPTION
            ""
    INDEX {
            hmSetupCertsScepClntCasEntryName
          }
    ::= { hmSetupCertsScepClntCasTable 1 }

HmSetupCertsScepClntCasEntry ::= SEQUENCE {
            hmSetupCertsScepClntCasEntryName DisplayString,
            hmSetupCertsScepClntCasEntryUrl DisplayString,
            hmSetupCertsScepClntCasEntryDn DisplayString,
            hmSetupCertsScepClntCasEntryEncAlg INTEGER,
            hmSetupCertsScepClntCasEntryIdentifier DisplayString,
            hmSetupCertsScepClntCasEntryCaSignatureAlgorithm INTEGER,
            hmSetupCertsScepClntCasEntryRaAutoapprove INTEGER,
            hmSetupCertsScepClntCasEntryCaFingerprintAlgorithm INTEGER,
            hmSetupCertsScepClntCasEntryCaFingerprint DisplayString,
            hmSetupCertsScepClntCasEntryLoopbackAddr DisplayString
    }

-- {COLUMN} 1.3.6.1.4.1.248.32.18.2.39.1.14.1.1
hmSetupCertsScepClntCasEntryName OBJECT-TYPE
    SYNTAX     DisplayString (SIZE(0..16))
    MAX-ACCESS read-write
    STATUS     current
    DESCRIPTION
            "-- empty --"
    ::= { hmSetupCertsScepClntCasEntry 1 }

-- {COLUMN} 1.3.6.1.4.1.248.32.18.2.39.1.14.1.2
hmSetupCertsScepClntCasEntryUrl OBJECT-TYPE
    SYNTAX     DisplayString (SIZE(0..251))
    MAX-ACCESS read-write
    STATUS     current
    DESCRIPTION
            "-- empty --"
    ::= { hmSetupCertsScepClntCasEntry 2 }

-- {COLUMN} 1.3.6.1.4.1.248.32.18.2.39.1.14.1.3
hmSetupCertsScepClntCasEntryDn OBJECT-TYPE
    SYNTAX     DisplayString (SIZE(0..251))
    MAX-ACCESS read-write
    STATUS     current
    DESCRIPTION
            "-- empty --"
    ::= { hmSetupCertsScepClntCasEntry 3 }

-- {COLUMN} 1.3.6.1.4.1.248.32.18.2.39.1.14.1.4
hmSetupCertsScepClntCasEntryEncAlg OBJECT-TYPE
    SYNTAX     INTEGER {
                  eDes (0),
                  e3des (1),
                  eBlowfish (2),
                  eAes128 (3),
                  eAes192 (4),
                  eAes256 (5)
            }
    MAX-ACCESS read-write
    STATUS     current
    DESCRIPTION
            "-- empty --"
    ::= { hmSetupCertsScepClntCasEntry 4 }

-- {COLUMN} 1.3.6.1.4.1.248.32.18.2.39.1.14.1.5
hmSetupCertsScepClntCasEntryIdentifier OBJECT-TYPE
    SYNTAX     DisplayString (SIZE(0..251))
    MAX-ACCESS read-write
    STATUS     current
    DESCRIPTION
            "-- empty --"
    ::= { hmSetupCertsScepClntCasEntry 5 }

-- {COLUMN} 1.3.6.1.4.1.248.32.18.2.39.1.14.1.6
hmSetupCertsScepClntCasEntryCaSignatureAlgorithm OBJECT-TYPE
    SYNTAX     INTEGER {
                  eMd5 (0),
                  eSha1 (1),
                  eSha2256 (2),
                  eSha2384 (3),
                  eSha2512 (4)
            }
    MAX-ACCESS read-write
    STATUS     current
    DESCRIPTION
            "-- empty --"
    ::= { hmSetupCertsScepClntCasEntry 6 }

-- {COLUMN} 1.3.6.1.4.1.248.32.18.2.39.1.14.1.7
hmSetupCertsScepClntCasEntryRaAutoapprove OBJECT-TYPE
    SYNTAX     INTEGER {
                  eNo (0),
                  eYes (1)
            }
    MAX-ACCESS read-write
    STATUS     current
    DESCRIPTION
            "-- empty --"
    ::= { hmSetupCertsScepClntCasEntry 7 }

-- {COLUMN} 1.3.6.1.4.1.248.32.18.2.39.1.14.1.8
hmSetupCertsScepClntCasEntryCaFingerprintAlgorithm OBJECT-TYPE
    SYNTAX     INTEGER {
                  eOff (0),
                  eSha1 (1),
                  eMd5 (2),
                  eSha2256 (3),
                  eSha2384 (4),
                  eSha2512 (5)
            }
    MAX-ACCESS read-write
    STATUS     current
    DESCRIPTION
            "-- empty --"
    ::= { hmSetupCertsScepClntCasEntry 8 }

-- {COLUMN} 1.3.6.1.4.1.248.32.18.2.39.1.14.1.9
hmSetupCertsScepClntCasEntryCaFingerprint OBJECT-TYPE
    SYNTAX     DisplayString (SIZE(0..59))
    MAX-ACCESS read-write
    STATUS     current
    DESCRIPTION
            "-- empty --"
    ::= { hmSetupCertsScepClntCasEntry 9 }

-- {COLUMN} 1.3.6.1.4.1.248.32.18.2.39.1.14.1.11
hmSetupCertsScepClntCasEntryLoopbackAddr OBJECT-TYPE
    SYNTAX     DisplayString (SIZE(0..16))
    MAX-ACCESS read-write
    STATUS     current
    DESCRIPTION
            "-- empty --"
    ::= { hmSetupCertsScepClntCasEntry 11 }

-- {NODE} 1.3.6.1.4.1.248.32.18.2.39.2
hmSetupCertsScepCa OBJECT IDENTIFIER ::= { hmSetupCerts 2 }

-- {SCALAR} 1.3.6.1.4.1.248.32.18.2.39.2.1
hmSetupCertsScepCaOperating OBJECT-TYPE
    SYNTAX     INTEGER {
                  eNo (0),
                  eYes (1)
            }
    MAX-ACCESS read-write
    STATUS     current
    DESCRIPTION
            "-- empty --"
    ::= { hmSetupCertsScepCa 1 }

-- {NODE} 1.3.6.1.4.1.248.32.18.2.39.2.2
hmSetupCertsScepCaCaCerts OBJECT IDENTIFIER ::= { hmSetupCertsScepCa 2 }

-- {SCALAR} 1.3.6.1.4.1.248.32.18.2.39.2.2.1
hmSetupCertsScepCaCaCertsCaDistingName OBJECT-TYPE
    SYNTAX     DisplayString (SIZE(0..251))
    MAX-ACCESS read-write
    STATUS     current
    DESCRIPTION
            "CA distinguished name"
    ::= { hmSetupCertsScepCaCaCerts 1 }

-- {SCALAR} 1.3.6.1.4.1.248.32.18.2.39.2.2.3
hmSetupCertsScepCaCaCertsAlternativeName OBJECT-TYPE
    SYNTAX     DisplayString (SIZE(0..251))
    MAX-ACCESS read-write
    STATUS     current
    DESCRIPTION
            "-- empty --"
    ::= { hmSetupCertsScepCaCaCerts 3 }

-- {SCALAR} 1.3.6.1.4.1.248.32.18.2.39.2.2.4
hmSetupCertsScepCaCaCertsRsaKeyLength OBJECT-TYPE
    SYNTAX     INTEGER {
                  e1024 (1024),
                  e2048 (2048),
                  e3072 (3072),
                  e4096 (4096),
                  e8192 (8192)
            }
    MAX-ACCESS read-write
    STATUS     current
    DESCRIPTION
            "-- empty --"
    ::= { hmSetupCertsScepCaCaCerts 4 }

-- {SCALAR} 1.3.6.1.4.1.248.32.18.2.39.2.2.5
hmSetupCertsScepCaCaCertsValidityPeriod OBJECT-TYPE
    SYNTAX     Integer32 (0..65535)
    MAX-ACCESS read-write
    STATUS     current
    DESCRIPTION
            "-- empty --"
    ::= { hmSetupCertsScepCaCaCerts 5 }

-- {SCALAR} 1.3.6.1.4.1.248.32.18.2.39.2.2.6
hmSetupCertsScepCaCaCertsUpdateCaCertificatesBeforeExpiration OBJECT-TYPE
    SYNTAX     Integer32 (0..65535)
    MAX-ACCESS read-write
    STATUS     current
    DESCRIPTION
            "-- empty --"
    ::= { hmSetupCertsScepCaCaCerts 6 }

-- {SCALAR} 1.3.6.1.4.1.248.32.18.2.39.2.2.8
hmSetupCertsScepCaCaCertsRaDistinguishedName OBJECT-TYPE
    SYNTAX     DisplayString (SIZE(0..251))
    MAX-ACCESS read-write
    STATUS     current
    DESCRIPTION
            "-- empty --"
    ::= { hmSetupCertsScepCaCaCerts 8 }

-- {SCALAR} 1.3.6.1.4.1.248.32.18.2.39.2.2.9
hmSetupCertsScepCaCaCertsCreateNewCaCertificates OBJECT-TYPE
    SYNTAX     DisplayString
    MAX-ACCESS read-write
    STATUS     current
    DESCRIPTION
            "-- empty --"
    ::= { hmSetupCertsScepCaCaCerts 9 }

-- {SCALAR} 1.3.6.1.4.1.248.32.18.2.39.2.2.10
hmSetupCertsScepCaCaCertsCreatePkcs12BackupFiles OBJECT-TYPE
    SYNTAX     DisplayString
    MAX-ACCESS read-write
    STATUS     current
    DESCRIPTION
            "-- empty --"
    ::= { hmSetupCertsScepCaCaCerts 10 }

-- {SCALAR} 1.3.6.1.4.1.248.32.18.2.39.2.2.11
hmSetupCertsScepCaCaCertsRestoreCertificatesFromBackup OBJECT-TYPE
    SYNTAX     DisplayString
    MAX-ACCESS read-write
    STATUS     current
    DESCRIPTION
            "-- empty --"
    ::= { hmSetupCertsScepCaCaCerts 11 }

-- {SCALAR} 1.3.6.1.4.1.248.32.18.2.39.2.3
hmSetupCertsScepCaEncryptionAlgorithm OBJECT-TYPE
    SYNTAX     INTEGER {
                  eDes (0),
                  e3des (1),
                  eBlowfish (2),
                  eAes128 (3),
                  eAes192 (4),
                  eAes256 (5)
            }
    MAX-ACCESS read-write
    STATUS     current
    DESCRIPTION
            "-- empty --"
    ::= { hmSetupCertsScepCa 3 }

-- {SCALAR} 1.3.6.1.4.1.248.32.18.2.39.2.4
hmSetupCertsScepCaRaAutoapprove OBJECT-TYPE
    SYNTAX     INTEGER {
                  eNo (0),
                  eYes (1)
            }
    MAX-ACCESS read-write
    STATUS     current
    DESCRIPTION
            "-- empty --"
    ::= { hmSetupCertsScepCa 4 }

-- {NODE} 1.3.6.1.4.1.248.32.18.2.39.2.5
hmSetupCertsScepCaClientCerts OBJECT IDENTIFIER ::= { hmSetupCertsScepCa 5 }

-- {SCALAR} 1.3.6.1.4.1.248.32.18.2.39.2.5.1
hmSetupCertsScepCaClientCertsValidityPeriod OBJECT-TYPE
    SYNTAX     Integer32 (0..65535)
    MAX-ACCESS read-write
    STATUS     current
    DESCRIPTION
            "-- empty --"
    ::= { hmSetupCertsScepCaClientCerts 1 }

-- {TABLE} 1.3.6.1.4.1.248.32.18.2.39.2.5.3
hmSetupCertsScepCaClientCertsChallPasswdsTable OBJECT-TYPE
    SYNTAX     SEQUENCE OF HmSetupCertsScepCaClientCertsChallPasswdsEntry
    MAX-ACCESS not-accessible
    STATUS     current
    DESCRIPTION
            "challange passwords"
    ::= { hmSetupCertsScepCaClientCerts 3 }

-- {ROW} 1.3.6.1.4.1.248.32.18.2.39.2.5.3.1
hmSetupCertsScepCaClientCertsChallPasswdsEntry OBJECT-TYPE
    SYNTAX     HmSetupCertsScepCaClientCertsChallPasswdsEntry
    MAX-ACCESS not-accessible
    STATUS     current
    DESCRIPTION
            ""
    INDEX {
            hmSetupCertsScepCaClientCertsChallPasswdsEntryIndex
          }
    ::= { hmSetupCertsScepCaClientCertsChallPasswdsTable 1 }

HmSetupCertsScepCaClientCertsChallPasswdsEntry ::= SEQUENCE {
            hmSetupCertsScepCaClientCertsChallPasswdsEntryIndex Integer32,
            hmSetupCertsScepCaClientCertsChallPasswdsEntrySubjDistngName DisplayString,
            hmSetupCertsScepCaClientCertsChallPasswdsEntryMacAddress DisplayString,
            hmSetupCertsScepCaClientCertsChallPasswdsEntryChallenge DisplayString,
            hmSetupCertsScepCaClientCertsChallPasswdsEntryValidity INTEGER
    }

-- {COLUMN} 1.3.6.1.4.1.248.32.18.2.39.2.5.3.1.1
hmSetupCertsScepCaClientCertsChallPasswdsEntryIndex OBJECT-TYPE
    SYNTAX     Integer32 (0..2147483647)
    MAX-ACCESS read-write
    STATUS     current
    DESCRIPTION
            "-- empty --"
    ::= { hmSetupCertsScepCaClientCertsChallPasswdsEntry 1 }

-- {COLUMN} 1.3.6.1.4.1.248.32.18.2.39.2.5.3.1.2
hmSetupCertsScepCaClientCertsChallPasswdsEntrySubjDistngName OBJECT-TYPE
    SYNTAX     DisplayString (SIZE(0..251))
    MAX-ACCESS read-write
    STATUS     current
    DESCRIPTION
            "subject distinguished name"
    ::= { hmSetupCertsScepCaClientCertsChallPasswdsEntry 2 }

-- {COLUMN} 1.3.6.1.4.1.248.32.18.2.39.2.5.3.1.3
hmSetupCertsScepCaClientCertsChallPasswdsEntryMacAddress OBJECT-TYPE
    SYNTAX     DisplayString (SIZE(0..12))
    MAX-ACCESS read-write
    STATUS     current
    DESCRIPTION
            "-- empty --"
    ::= { hmSetupCertsScepCaClientCertsChallPasswdsEntry 3 }

-- {COLUMN} 1.3.6.1.4.1.248.32.18.2.39.2.5.3.1.4
hmSetupCertsScepCaClientCertsChallPasswdsEntryChallenge OBJECT-TYPE
    SYNTAX     DisplayString (SIZE(0..16))
    MAX-ACCESS read-write
    STATUS     current
    DESCRIPTION
            "-- empty --"
    ::= { hmSetupCertsScepCaClientCertsChallPasswdsEntry 4 }

-- {COLUMN} 1.3.6.1.4.1.248.32.18.2.39.2.5.3.1.5
hmSetupCertsScepCaClientCertsChallPasswdsEntryValidity OBJECT-TYPE
    SYNTAX     INTEGER {
                  ePermanently (0),
                  eOneTime (1)
            }
    MAX-ACCESS read-write
    STATUS     current
    DESCRIPTION
            "-- empty --"
    ::= { hmSetupCertsScepCaClientCertsChallPasswdsEntry 5 }

-- {SCALAR} 1.3.6.1.4.1.248.32.18.2.39.2.5.4
hmSetupCertsScepCaClientCertsGeneralChallengePassword OBJECT-TYPE
    SYNTAX     DisplayString (SIZE(0..16))
    MAX-ACCESS read-write
    STATUS     current
    DESCRIPTION
            "-- empty --"
    ::= { hmSetupCertsScepCaClientCerts 4 }

-- {SCALAR} 1.3.6.1.4.1.248.32.18.2.39.2.6
hmSetupCertsScepCaSignatureAlgorithm OBJECT-TYPE
    SYNTAX     INTEGER {
                  eMd5 (0),
                  eSha1 (1),
                  eSha2256 (2),
                  eSha2384 (3),
                  eSha2512 (4)
            }
    MAX-ACCESS read-write
    STATUS     current
    DESCRIPTION
            "-- empty --"
    ::= { hmSetupCertsScepCa 6 }

-- {SCALAR} 1.3.6.1.4.1.248.32.18.2.39.2.7
hmSetupCertsScepCaFingerprintAlgorithm OBJECT-TYPE
    SYNTAX     INTEGER {
                  eMd5 (0),
                  eSha1 (1),
                  eSha2256 (2),
                  eSha2384 (3),
                  eSha2512 (4)
            }
    MAX-ACCESS read-write
    STATUS     current
    DESCRIPTION
            "-- empty --"
    ::= { hmSetupCertsScepCa 7 }

-- {NODE} 1.3.6.1.4.1.248.32.18.2.39.2.8
hmSetupCertsScepCaCertRevLists OBJECT IDENTIFIER ::= { hmSetupCertsScepCa 8 }

-- {SCALAR} 1.3.6.1.4.1.248.32.18.2.39.2.8.1
hmSetupCertsScepCaCertRevListsCrlUpdateInterval OBJECT-TYPE
    SYNTAX     Integer32 (0..2147483647)
    MAX-ACCESS read-write
    STATUS     current
    DESCRIPTION
            "-- empty --"
    ::= { hmSetupCertsScepCaCertRevLists 1 }

-- {SCALAR} 1.3.6.1.4.1.248.32.18.2.39.2.8.2
hmSetupCertsScepCaCertRevListsCrlDistributionPointHostname OBJECT-TYPE
    SYNTAX     DisplayString (SIZE(0..63))
    MAX-ACCESS read-write
    STATUS     current
    DESCRIPTION
            "-- empty --"
    ::= { hmSetupCertsScepCaCertRevLists 2 }

-- {SCALAR} 1.3.6.1.4.1.248.32.18.2.39.2.8.3
hmSetupCertsScepCaCertRevListsCreateNewCrl OBJECT-TYPE
    SYNTAX     DisplayString
    MAX-ACCESS read-write
    STATUS     current
    DESCRIPTION
            "-- empty --"
    ::= { hmSetupCertsScepCaCertRevLists 3 }

-- {SCALAR} 1.3.6.1.4.1.248.32.18.2.39.2.9
hmSetupCertsScepCaReinitialize OBJECT-TYPE
    SYNTAX     DisplayString
    MAX-ACCESS read-write
    STATUS     current
    DESCRIPTION
            "-- empty --"
    ::= { hmSetupCertsScepCa 9 }

-- {NODE} 1.3.6.1.4.1.248.32.18.2.39.2.10
hmSetupCertsScepCaLogging OBJECT IDENTIFIER ::= { hmSetupCertsScepCa 10 }

-- {SCALAR} 1.3.6.1.4.1.248.32.18.2.39.2.10.1
hmSetupCertsScepCaLoggingEMail OBJECT-TYPE
    SYNTAX     INTEGER {
                  eNo (0),
                  eYes (1)
            }
    MAX-ACCESS read-write
    STATUS     current
    DESCRIPTION
            "-- empty --"
    ::= { hmSetupCertsScepCaLogging 1 }

-- {SCALAR} 1.3.6.1.4.1.248.32.18.2.39.2.10.2
hmSetupCertsScepCaLoggingSyslog OBJECT-TYPE
    SYNTAX     INTEGER {
                  eNo (0),
                  eYes (1)
            }
    MAX-ACCESS read-write
    STATUS     current
    DESCRIPTION
            "-- empty --"
    ::= { hmSetupCertsScepCaLogging 2 }

-- {SCALAR} 1.3.6.1.4.1.248.32.18.2.39.2.10.3
hmSetupCertsScepCaLoggingEMailReceiver OBJECT-TYPE
    SYNTAX     DisplayString (SIZE(0..63))
    MAX-ACCESS read-write
    STATUS     current
    DESCRIPTION
            "-- empty --"
    ::= { hmSetupCertsScepCaLogging 3 }

-- {SCALAR} 1.3.6.1.4.1.248.32.18.2.39.2.10.4
hmSetupCertsScepCaLoggingSendBackupReminder OBJECT-TYPE
    SYNTAX     INTEGER {
                  eNo (0),
                  eYes (1)
            }
    MAX-ACCESS read-write
    STATUS     current
    DESCRIPTION
            "-- empty --"
    ::= { hmSetupCertsScepCaLogging 4 }

-- {SCALAR} 1.3.6.1.4.1.248.32.18.2.39.2.11
hmSetupCertsScepCaRootCa OBJECT-TYPE
    SYNTAX     INTEGER {
                  eNo (0),
                  eYes (1)
            }
    MAX-ACCESS read-write
    STATUS     current
    DESCRIPTION
            "-- empty --"
    ::= { hmSetupCertsScepCa 11 }

-- {SCALAR} 1.3.6.1.4.1.248.32.18.2.39.2.12
hmSetupCertsScepCaCaPathLength OBJECT-TYPE
    SYNTAX     Integer32 (0..65535)
    MAX-ACCESS read-write
    STATUS     current
    DESCRIPTION
            "-- empty --"
    ::= { hmSetupCertsScepCa 12 }

-- {NODE} 1.3.6.1.4.1.248.32.18.2.39.2.13
hmSetupCertsScepCaSubCa OBJECT IDENTIFIER ::= { hmSetupCertsScepCa 13 }

-- {SCALAR} 1.3.6.1.4.1.248.32.18.2.39.2.13.1
hmSetupCertsScepCaSubCaAutoGeneratedRequest OBJECT-TYPE
    SYNTAX     INTEGER {
                  eNo (0),
                  eYes (1)
            }
    MAX-ACCESS read-write
    STATUS     current
    DESCRIPTION
            "-- empty --"
    ::= { hmSetupCertsScepCaSubCa 1 }

-- {SCALAR} 1.3.6.1.4.1.248.32.18.2.39.2.13.2
hmSetupCertsScepCaSubCaCadn OBJECT-TYPE
    SYNTAX     DisplayString (SIZE(0..100))
    MAX-ACCESS read-write
    STATUS     current
    DESCRIPTION
            "-- empty --"
    ::= { hmSetupCertsScepCaSubCa 2 }

-- {SCALAR} 1.3.6.1.4.1.248.32.18.2.39.2.13.3
hmSetupCertsScepCaSubCaChallengePwd OBJECT-TYPE
    SYNTAX     DisplayString (SIZE(0..16))
    MAX-ACCESS read-write
    STATUS     current
    DESCRIPTION
            "-- empty --"
    ::= { hmSetupCertsScepCaSubCa 3 }

-- {SCALAR} 1.3.6.1.4.1.248.32.18.2.39.2.13.4
hmSetupCertsScepCaSubCaExtKeyUsage OBJECT-TYPE
    SYNTAX     DisplayString (SIZE(0..100))
    MAX-ACCESS read-write
    STATUS     current
    DESCRIPTION
            "-- empty --"
    ::= { hmSetupCertsScepCaSubCa 4 }

-- {SCALAR} 1.3.6.1.4.1.248.32.18.2.39.2.13.5
hmSetupCertsScepCaSubCaCertKeyUsage OBJECT-TYPE
    SYNTAX     DisplayString (SIZE(0..100))
    MAX-ACCESS read-write
    STATUS     current
    DESCRIPTION
            "-- empty --"
    ::= { hmSetupCertsScepCaSubCa 5 }

-- {SCALAR} 1.3.6.1.4.1.248.32.18.2.39.2.13.8
hmSetupCertsScepCaSubCaCaUrlAddress OBJECT-TYPE
    SYNTAX     DisplayString (SIZE(0..251))
    MAX-ACCESS read-write
    STATUS     current
    DESCRIPTION
            "-- empty --"
    ::= { hmSetupCertsScepCaSubCa 8 }

-- {SCALAR} 1.3.6.1.4.1.248.32.18.2.39.2.13.9
hmSetupCertsScepCaSubCaRestart OBJECT-TYPE
    SYNTAX     DisplayString
    MAX-ACCESS read-write
    STATUS     current
    DESCRIPTION
            "-- empty --"
    ::= { hmSetupCertsScepCaSubCa 9 }

-- {NODE} 1.3.6.1.4.1.248.32.18.2.39.2.14
hmSetupCertsScepCaWebIfc OBJECT IDENTIFIER ::= { hmSetupCertsScepCa 14 }

-- {TABLE} 1.3.6.1.4.1.248.32.18.2.39.2.14.1
hmSetupCertsScepCaWebIfcProfilesTable OBJECT-TYPE
    SYNTAX     SEQUENCE OF HmSetupCertsScepCaWebIfcProfilesEntry
    MAX-ACCESS not-accessible
    STATUS     current
    DESCRIPTION
            "-- empty --"
    ::= { hmSetupCertsScepCaWebIfc 1 }

-- {ROW} 1.3.6.1.4.1.248.32.18.2.39.2.14.1.1
hmSetupCertsScepCaWebIfcProfilesEntry OBJECT-TYPE
    SYNTAX     HmSetupCertsScepCaWebIfcProfilesEntry
    MAX-ACCESS not-accessible
    STATUS     current
    DESCRIPTION
            ""
    INDEX {
            hmSetupCertsScepCaWebIfcProfilesEntryProfileName,
            hmSetupCertsScepCaWebIfcProfilesEntryTemplate
          }
    ::= { hmSetupCertsScepCaWebIfcProfilesTable 1 }

HmSetupCertsScepCaWebIfcProfilesEntry ::= SEQUENCE {
            hmSetupCertsScepCaWebIfcProfilesEntryProfileName DisplayString,
            hmSetupCertsScepCaWebIfcProfilesEntryKeyUsage DisplayString,
            hmSetupCertsScepCaWebIfcProfilesEntryExtendedKeyUsage DisplayString,
            hmSetupCertsScepCaWebIfcProfilesEntryRsaKeyLength INTEGER,
            hmSetupCertsScepCaWebIfcProfilesEntryValidityPeriod Integer32,
            hmSetupCertsScepCaWebIfcProfilesEntryCa INTEGER,
            hmSetupCertsScepCaWebIfcProfilesEntryPassword DisplayString,
            hmSetupCertsScepCaWebIfcProfilesEntryCountryName DisplayString,
            hmSetupCertsScepCaWebIfcProfilesEntryLocalityName DisplayString,
            hmSetupCertsScepCaWebIfcProfilesEntryOrganizationName DisplayString,
            hmSetupCertsScepCaWebIfcProfilesEntryOrganizationUnitName DisplayString,
            hmSetupCertsScepCaWebIfcProfilesEntryStateOrProvince DisplayString,
            hmSetupCertsScepCaWebIfcProfilesEntryEMail DisplayString,
            hmSetupCertsScepCaWebIfcProfilesEntrySurname DisplayString,
            hmSetupCertsScepCaWebIfcProfilesEntrySerialNumber DisplayString,
            hmSetupCertsScepCaWebIfcProfilesEntryPostalCode DisplayString,
            hmSetupCertsScepCaWebIfcProfilesEntryTemplate DisplayString,
            hmSetupCertsScepCaWebIfcProfilesEntrySubjectAlternativeName DisplayString
    }

-- {COLUMN} 1.3.6.1.4.1.248.32.18.2.39.2.14.1.1.1
hmSetupCertsScepCaWebIfcProfilesEntryProfileName OBJECT-TYPE
    SYNTAX     DisplayString (SIZE(0..32))
    MAX-ACCESS read-write
    STATUS     current
    DESCRIPTION
            "-- empty --"
    ::= { hmSetupCertsScepCaWebIfcProfilesEntry 1 }

-- {COLUMN} 1.3.6.1.4.1.248.32.18.2.39.2.14.1.1.2
hmSetupCertsScepCaWebIfcProfilesEntryKeyUsage OBJECT-TYPE
    SYNTAX     DisplayString (SIZE(0..251))
    MAX-ACCESS read-write
    STATUS     current
    DESCRIPTION
            "-- empty --"
    ::= { hmSetupCertsScepCaWebIfcProfilesEntry 2 }

-- {COLUMN} 1.3.6.1.4.1.248.32.18.2.39.2.14.1.1.3
hmSetupCertsScepCaWebIfcProfilesEntryExtendedKeyUsage OBJECT-TYPE
    SYNTAX     DisplayString (SIZE(0..251))
    MAX-ACCESS read-write
    STATUS     current
    DESCRIPTION
            "-- empty --"
    ::= { hmSetupCertsScepCaWebIfcProfilesEntry 3 }

-- {COLUMN} 1.3.6.1.4.1.248.32.18.2.39.2.14.1.1.4
hmSetupCertsScepCaWebIfcProfilesEntryRsaKeyLength OBJECT-TYPE
    SYNTAX     INTEGER {
                  e1024 (1024),
                  e2048 (2048),
                  e3072 (3072),
                  e4096 (4096),
                  e8192 (8192)
            }
    MAX-ACCESS read-write
    STATUS     current
    DESCRIPTION
            "-- empty --"
    ::= { hmSetupCertsScepCaWebIfcProfilesEntry 4 }

-- {COLUMN} 1.3.6.1.4.1.248.32.18.2.39.2.14.1.1.5
hmSetupCertsScepCaWebIfcProfilesEntryValidityPeriod OBJECT-TYPE
    SYNTAX     Integer32 (0..2147483647)
    MAX-ACCESS read-write
    STATUS     current
    DESCRIPTION
            "-- empty --"
    ::= { hmSetupCertsScepCaWebIfcProfilesEntry 5 }

-- {COLUMN} 1.3.6.1.4.1.248.32.18.2.39.2.14.1.1.6
hmSetupCertsScepCaWebIfcProfilesEntryCa OBJECT-TYPE
    SYNTAX     INTEGER {
                  eNo (0),
                  eYes (1)
            }
    MAX-ACCESS read-write
    STATUS     current
    DESCRIPTION
            "-- empty --"
    ::= { hmSetupCertsScepCaWebIfcProfilesEntry 6 }

-- {COLUMN} 1.3.6.1.4.1.248.32.18.2.39.2.14.1.1.7
hmSetupCertsScepCaWebIfcProfilesEntryPassword OBJECT-TYPE
    SYNTAX     DisplayString (SIZE(0..32))
    MAX-ACCESS read-write
    STATUS     current
    DESCRIPTION
            "-- empty --"
    ::= { hmSetupCertsScepCaWebIfcProfilesEntry 7 }

-- {COLUMN} 1.3.6.1.4.1.248.32.18.2.39.2.14.1.1.8
hmSetupCertsScepCaWebIfcProfilesEntryCountryName OBJECT-TYPE
    SYNTAX     DisplayString (SIZE(0..2))
    MAX-ACCESS read-write
    STATUS     current
    DESCRIPTION
            "-- empty --"
    ::= { hmSetupCertsScepCaWebIfcProfilesEntry 8 }

-- {COLUMN} 1.3.6.1.4.1.248.32.18.2.39.2.14.1.1.9
hmSetupCertsScepCaWebIfcProfilesEntryLocalityName OBJECT-TYPE
    SYNTAX     DisplayString (SIZE(0..32))
    MAX-ACCESS read-write
    STATUS     current
    DESCRIPTION
            "-- empty --"
    ::= { hmSetupCertsScepCaWebIfcProfilesEntry 9 }

-- {COLUMN} 1.3.6.1.4.1.248.32.18.2.39.2.14.1.1.10
hmSetupCertsScepCaWebIfcProfilesEntryOrganizationName OBJECT-TYPE
    SYNTAX     DisplayString (SIZE(0..32))
    MAX-ACCESS read-write
    STATUS     current
    DESCRIPTION
            "-- empty --"
    ::= { hmSetupCertsScepCaWebIfcProfilesEntry 10 }

-- {COLUMN} 1.3.6.1.4.1.248.32.18.2.39.2.14.1.1.11
hmSetupCertsScepCaWebIfcProfilesEntryOrganizationUnitName OBJECT-TYPE
    SYNTAX     DisplayString (SIZE(0..32))
    MAX-ACCESS read-write
    STATUS     current
    DESCRIPTION
            "-- empty --"
    ::= { hmSetupCertsScepCaWebIfcProfilesEntry 11 }

-- {COLUMN} 1.3.6.1.4.1.248.32.18.2.39.2.14.1.1.12
hmSetupCertsScepCaWebIfcProfilesEntryStateOrProvince OBJECT-TYPE
    SYNTAX     DisplayString (SIZE(0..32))
    MAX-ACCESS read-write
    STATUS     current
    DESCRIPTION
            "-- empty --"
    ::= { hmSetupCertsScepCaWebIfcProfilesEntry 12 }

-- {COLUMN} 1.3.6.1.4.1.248.32.18.2.39.2.14.1.1.13
hmSetupCertsScepCaWebIfcProfilesEntryEMail OBJECT-TYPE
    SYNTAX     DisplayString (SIZE(0..64))
    MAX-ACCESS read-write
    STATUS     current
    DESCRIPTION
            "-- empty --"
    ::= { hmSetupCertsScepCaWebIfcProfilesEntry 13 }

-- {COLUMN} 1.3.6.1.4.1.248.32.18.2.39.2.14.1.1.14
hmSetupCertsScepCaWebIfcProfilesEntrySurname OBJECT-TYPE
    SYNTAX     DisplayString (SIZE(0..32))
    MAX-ACCESS read-write
    STATUS     current
    DESCRIPTION
            "-- empty --"
    ::= { hmSetupCertsScepCaWebIfcProfilesEntry 14 }

-- {COLUMN} 1.3.6.1.4.1.248.32.18.2.39.2.14.1.1.15
hmSetupCertsScepCaWebIfcProfilesEntrySerialNumber OBJECT-TYPE
    SYNTAX     DisplayString (SIZE(0..32))
    MAX-ACCESS read-write
    STATUS     current
    DESCRIPTION
            "-- empty --"
    ::= { hmSetupCertsScepCaWebIfcProfilesEntry 15 }

-- {COLUMN} 1.3.6.1.4.1.248.32.18.2.39.2.14.1.1.16
hmSetupCertsScepCaWebIfcProfilesEntryPostalCode OBJECT-TYPE
    SYNTAX     DisplayString (SIZE(0..25))
    MAX-ACCESS read-write
    STATUS     current
    DESCRIPTION
            "-- empty --"
    ::= { hmSetupCertsScepCaWebIfcProfilesEntry 16 }

-- {COLUMN} 1.3.6.1.4.1.248.32.18.2.39.2.14.1.1.17
hmSetupCertsScepCaWebIfcProfilesEntryTemplate OBJECT-TYPE
    SYNTAX     DisplayString (SIZE(0..31))
    MAX-ACCESS read-write
    STATUS     current
    DESCRIPTION
            "-- empty --"
    ::= { hmSetupCertsScepCaWebIfcProfilesEntry 17 }

-- {COLUMN} 1.3.6.1.4.1.248.32.18.2.39.2.14.1.1.18
hmSetupCertsScepCaWebIfcProfilesEntrySubjectAlternativeName OBJECT-TYPE
    SYNTAX     DisplayString (SIZE(0..254))
    MAX-ACCESS read-write
    STATUS     current
    DESCRIPTION
            "-- empty --"
    ::= { hmSetupCertsScepCaWebIfcProfilesEntry 18 }

-- {TABLE} 1.3.6.1.4.1.248.32.18.2.39.2.14.2
hmSetupCertsScepCaWebIfcTemplateTable OBJECT-TYPE
    SYNTAX     SEQUENCE OF HmSetupCertsScepCaWebIfcTemplateEntry
    MAX-ACCESS not-accessible
    STATUS     current
    DESCRIPTION
            "-- empty --"
    ::= { hmSetupCertsScepCaWebIfc 2 }

-- {ROW} 1.3.6.1.4.1.248.32.18.2.39.2.14.2.1
hmSetupCertsScepCaWebIfcTemplateEntry OBJECT-TYPE
    SYNTAX     HmSetupCertsScepCaWebIfcTemplateEntry
    MAX-ACCESS not-accessible
    STATUS     current
    DESCRIPTION
            ""
    INDEX {
            hmSetupCertsScepCaWebIfcTemplateEntryName
          }
    ::= { hmSetupCertsScepCaWebIfcTemplateTable 1 }

HmSetupCertsScepCaWebIfcTemplateEntry ::= SEQUENCE {
            hmSetupCertsScepCaWebIfcTemplateEntryName DisplayString,
            hmSetupCertsScepCaWebIfcTemplateEntryKeyUsage INTEGER,
            hmSetupCertsScepCaWebIfcTemplateEntryExtendedKeyUsage INTEGER,
            hmSetupCertsScepCaWebIfcTemplateEntryRsaKeyLength INTEGER,
            hmSetupCertsScepCaWebIfcTemplateEntryValidityPeriod INTEGER,
            hmSetupCertsScepCaWebIfcTemplateEntryCa INTEGER,
            hmSetupCertsScepCaWebIfcTemplateEntryPassword Integer32,
            hmSetupCertsScepCaWebIfcTemplateEntryCountryName INTEGER,
            hmSetupCertsScepCaWebIfcTemplateEntryLocalityName INTEGER,
            hmSetupCertsScepCaWebIfcTemplateEntryOrganizationName INTEGER,
            hmSetupCertsScepCaWebIfcTemplateEntryOrganizationUnitName INTEGER,
            hmSetupCertsScepCaWebIfcTemplateEntryStateOrProvince INTEGER,
            hmSetupCertsScepCaWebIfcTemplateEntryEMail INTEGER,
            hmSetupCertsScepCaWebIfcTemplateEntrySurname INTEGER,
            hmSetupCertsScepCaWebIfcTemplateEntrySerialNumber INTEGER,
            hmSetupCertsScepCaWebIfcTemplateEntryPostalCode INTEGER,
            hmSetupCertsScepCaWebIfcTemplateEntrySubjectAlternativeName INTEGER
    }

-- {COLUMN} 1.3.6.1.4.1.248.32.18.2.39.2.14.2.1.1
hmSetupCertsScepCaWebIfcTemplateEntryName OBJECT-TYPE
    SYNTAX     DisplayString (SIZE(0..31))
    MAX-ACCESS read-write
    STATUS     current
    DESCRIPTION
            "-- empty --"
    ::= { hmSetupCertsScepCaWebIfcTemplateEntry 1 }

-- {COLUMN} 1.3.6.1.4.1.248.32.18.2.39.2.14.2.1.2
hmSetupCertsScepCaWebIfcTemplateEntryKeyUsage OBJECT-TYPE
    SYNTAX     INTEGER {
                  eNo (0),
                  eYes (1),
                  eMandatory (2),
                  eFixed (3)
            }
    MAX-ACCESS read-write
    STATUS     current
    DESCRIPTION
            "-- empty --"
    ::= { hmSetupCertsScepCaWebIfcTemplateEntry 2 }

-- {COLUMN} 1.3.6.1.4.1.248.32.18.2.39.2.14.2.1.3
hmSetupCertsScepCaWebIfcTemplateEntryExtendedKeyUsage OBJECT-TYPE
    SYNTAX     INTEGER {
                  eNo (0),
                  eYes (1),
                  eMandatory (2),
                  eFixed (3)
            }
    MAX-ACCESS read-write
    STATUS     current
    DESCRIPTION
            "-- empty --"
    ::= { hmSetupCertsScepCaWebIfcTemplateEntry 3 }

-- {COLUMN} 1.3.6.1.4.1.248.32.18.2.39.2.14.2.1.4
hmSetupCertsScepCaWebIfcTemplateEntryRsaKeyLength OBJECT-TYPE
    SYNTAX     INTEGER {
                  eNo (0),
                  eYes (1),
                  eMandatory (2),
                  eFixed (3)
            }
    MAX-ACCESS read-write
    STATUS     current
    DESCRIPTION
            "-- empty --"
    ::= { hmSetupCertsScepCaWebIfcTemplateEntry 4 }

-- {COLUMN} 1.3.6.1.4.1.248.32.18.2.39.2.14.2.1.5
hmSetupCertsScepCaWebIfcTemplateEntryValidityPeriod OBJECT-TYPE
    SYNTAX     INTEGER {
                  eNo (0),
                  eYes (1),
                  eMandatory (2),
                  eFixed (3)
            }
    MAX-ACCESS read-write
    STATUS     current
    DESCRIPTION
            "-- empty --"
    ::= { hmSetupCertsScepCaWebIfcTemplateEntry 5 }

-- {COLUMN} 1.3.6.1.4.1.248.32.18.2.39.2.14.2.1.6
hmSetupCertsScepCaWebIfcTemplateEntryCa OBJECT-TYPE
    SYNTAX     INTEGER {
                  eNo (0),
                  eYes (1),
                  eMandatory (2),
                  eFixed (3)
            }
    MAX-ACCESS read-write
    STATUS     current
    DESCRIPTION
            "-- empty --"
    ::= { hmSetupCertsScepCaWebIfcTemplateEntry 6 }

-- {COLUMN} 1.3.6.1.4.1.248.32.18.2.39.2.14.2.1.7
hmSetupCertsScepCaWebIfcTemplateEntryPassword OBJECT-TYPE
    SYNTAX     Integer32 (0..255)
    MAX-ACCESS read-only
    STATUS     current
    DESCRIPTION
            "-- empty --"
    ::= { hmSetupCertsScepCaWebIfcTemplateEntry 7 }

-- {COLUMN} 1.3.6.1.4.1.248.32.18.2.39.2.14.2.1.8
hmSetupCertsScepCaWebIfcTemplateEntryCountryName OBJECT-TYPE
    SYNTAX     INTEGER {
                  eNo (0),
                  eYes (1),
                  eMandatory (2),
                  eFixed (3)
            }
    MAX-ACCESS read-write
    STATUS     current
    DESCRIPTION
            "-- empty --"
    ::= { hmSetupCertsScepCaWebIfcTemplateEntry 8 }

-- {COLUMN} 1.3.6.1.4.1.248.32.18.2.39.2.14.2.1.9
hmSetupCertsScepCaWebIfcTemplateEntryLocalityName OBJECT-TYPE
    SYNTAX     INTEGER {
                  eNo (0),
                  eYes (1),
                  eMandatory (2),
                  eFixed (3)
            }
    MAX-ACCESS read-write
    STATUS     current
    DESCRIPTION
            "-- empty --"
    ::= { hmSetupCertsScepCaWebIfcTemplateEntry 9 }

-- {COLUMN} 1.3.6.1.4.1.248.32.18.2.39.2.14.2.1.10
hmSetupCertsScepCaWebIfcTemplateEntryOrganizationName OBJECT-TYPE
    SYNTAX     INTEGER {
                  eNo (0),
                  eYes (1),
                  eMandatory (2),
                  eFixed (3)
            }
    MAX-ACCESS read-write
    STATUS     current
    DESCRIPTION
            "-- empty --"
    ::= { hmSetupCertsScepCaWebIfcTemplateEntry 10 }

-- {COLUMN} 1.3.6.1.4.1.248.32.18.2.39.2.14.2.1.11
hmSetupCertsScepCaWebIfcTemplateEntryOrganizationUnitName OBJECT-TYPE
    SYNTAX     INTEGER {
                  eNo (0),
                  eYes (1),
                  eMandatory (2),
                  eFixed (3)
            }
    MAX-ACCESS read-write
    STATUS     current
    DESCRIPTION
            "-- empty --"
    ::= { hmSetupCertsScepCaWebIfcTemplateEntry 11 }

-- {COLUMN} 1.3.6.1.4.1.248.32.18.2.39.2.14.2.1.12
hmSetupCertsScepCaWebIfcTemplateEntryStateOrProvince OBJECT-TYPE
    SYNTAX     INTEGER {
                  eNo (0),
                  eYes (1),
                  eMandatory (2),
                  eFixed (3)
            }
    MAX-ACCESS read-write
    STATUS     current
    DESCRIPTION
            "-- empty --"
    ::= { hmSetupCertsScepCaWebIfcTemplateEntry 12 }

-- {COLUMN} 1.3.6.1.4.1.248.32.18.2.39.2.14.2.1.13
hmSetupCertsScepCaWebIfcTemplateEntryEMail OBJECT-TYPE
    SYNTAX     INTEGER {
                  eNo (0),
                  eYes (1),
                  eMandatory (2),
                  eFixed (3)
            }
    MAX-ACCESS read-write
    STATUS     current
    DESCRIPTION
            "-- empty --"
    ::= { hmSetupCertsScepCaWebIfcTemplateEntry 13 }

-- {COLUMN} 1.3.6.1.4.1.248.32.18.2.39.2.14.2.1.14
hmSetupCertsScepCaWebIfcTemplateEntrySurname OBJECT-TYPE
    SYNTAX     INTEGER {
                  eNo (0),
                  eYes (1),
                  eMandatory (2),
                  eFixed (3)
            }
    MAX-ACCESS read-write
    STATUS     current
    DESCRIPTION
            "-- empty --"
    ::= { hmSetupCertsScepCaWebIfcTemplateEntry 14 }

-- {COLUMN} 1.3.6.1.4.1.248.32.18.2.39.2.14.2.1.15
hmSetupCertsScepCaWebIfcTemplateEntrySerialNumber OBJECT-TYPE
    SYNTAX     INTEGER {
                  eNo (0),
                  eYes (1),
                  eMandatory (2),
                  eFixed (3)
            }
    MAX-ACCESS read-write
    STATUS     current
    DESCRIPTION
            "-- empty --"
    ::= { hmSetupCertsScepCaWebIfcTemplateEntry 15 }

-- {COLUMN} 1.3.6.1.4.1.248.32.18.2.39.2.14.2.1.16
hmSetupCertsScepCaWebIfcTemplateEntryPostalCode OBJECT-TYPE
    SYNTAX     INTEGER {
                  eNo (0),
                  eYes (1),
                  eMandatory (2),
                  eFixed (3)
            }
    MAX-ACCESS read-write
    STATUS     current
    DESCRIPTION
            "-- empty --"
    ::= { hmSetupCertsScepCaWebIfcTemplateEntry 16 }

-- {COLUMN} 1.3.6.1.4.1.248.32.18.2.39.2.14.2.1.17
hmSetupCertsScepCaWebIfcTemplateEntrySubjectAlternativeName OBJECT-TYPE
    SYNTAX     INTEGER {
                  eNo (0),
                  eYes (1),
                  eMandatory (2),
                  eFixed (3)
            }
    MAX-ACCESS read-write
    STATUS     current
    DESCRIPTION
            "-- empty --"
    ::= { hmSetupCertsScepCaWebIfcTemplateEntry 17 }

-- {NODE} 1.3.6.1.4.1.248.32.18.2.39.3
hmSetupCertsCrls OBJECT IDENTIFIER ::= { hmSetupCerts 3 }

-- {SCALAR} 1.3.6.1.4.1.248.32.18.2.39.3.1
hmSetupCertsCrlsCrlOperating OBJECT-TYPE
    SYNTAX     INTEGER {
                  eNo (0),
                  eYes (1)
            }
    MAX-ACCESS read-write
    STATUS     current
    DESCRIPTION
            "-- empty --"
    ::= { hmSetupCertsCrls 1 }

-- {SCALAR} 1.3.6.1.4.1.248.32.18.2.39.3.4
hmSetupCertsCrlsUpdateBefore OBJECT-TYPE
    SYNTAX     Integer32 (0..2147483647)
    MAX-ACCESS read-write
    STATUS     current
    DESCRIPTION
            "-- empty --"
    ::= { hmSetupCertsCrls 4 }

-- {SCALAR} 1.3.6.1.4.1.248.32.18.2.39.3.5
hmSetupCertsCrlsPrefetchPeriod OBJECT-TYPE
    SYNTAX     Integer32 (0..2147483647)
    MAX-ACCESS read-write
    STATUS     current
    DESCRIPTION
            "-- empty --"
    ::= { hmSetupCertsCrls 5 }

-- {SCALAR} 1.3.6.1.4.1.248.32.18.2.39.3.6
hmSetupCertsCrlsValidityExceedance OBJECT-TYPE
    SYNTAX     Integer32 (0..2147483647)
    MAX-ACCESS read-write
    STATUS     current
    DESCRIPTION
            "-- empty --"
    ::= { hmSetupCertsCrls 6 }

-- {SCALAR} 1.3.6.1.4.1.248.32.18.2.39.3.7
hmSetupCertsCrlsRefreshCrlNow OBJECT-TYPE
    SYNTAX     DisplayString
    MAX-ACCESS read-write
    STATUS     current
    DESCRIPTION
            "-- empty --"
    ::= { hmSetupCertsCrls 7 }

-- {TABLE} 1.3.6.1.4.1.248.32.18.2.39.3.8
hmSetupCertsCrlsAlternativeUrlTableTable OBJECT-TYPE
    SYNTAX     SEQUENCE OF HmSetupCertsCrlsAlternativeUrlTableEntry
    MAX-ACCESS not-accessible
    STATUS     current
    DESCRIPTION
            "-- empty --"
    ::= { hmSetupCertsCrls 8 }

-- {ROW} 1.3.6.1.4.1.248.32.18.2.39.3.8.1
hmSetupCertsCrlsAlternativeUrlTableEntry OBJECT-TYPE
    SYNTAX     HmSetupCertsCrlsAlternativeUrlTableEntry
    MAX-ACCESS not-accessible
    STATUS     current
    DESCRIPTION
            ""
    INDEX {
            hmSetupCertsCrlsAlternativeUrlTableEntryAlternativeUrl
          }
    ::= { hmSetupCertsCrlsAlternativeUrlTableTable 1 }

HmSetupCertsCrlsAlternativeUrlTableEntry ::= SEQUENCE {
            hmSetupCertsCrlsAlternativeUrlTableEntryAlternativeUrl DisplayString
    }

-- {COLUMN} 1.3.6.1.4.1.248.32.18.2.39.3.8.1.1
hmSetupCertsCrlsAlternativeUrlTableEntryAlternativeUrl OBJECT-TYPE
    SYNTAX     DisplayString (SIZE(0..251))
    MAX-ACCESS read-write
    STATUS     current
    DESCRIPTION
            "-- empty --"
    ::= { hmSetupCertsCrlsAlternativeUrlTableEntry 1 }

-- {SCALAR} 1.3.6.1.4.1.248.32.18.2.39.3.9
hmSetupCertsCrlsLoopbackAddress OBJECT-TYPE
    SYNTAX     DisplayString (SIZE(0..16))
    MAX-ACCESS read-write
    STATUS     current
    DESCRIPTION
            "-- empty --"
    ::= { hmSetupCertsCrls 9 }

-- {NODE} 1.3.6.1.4.1.248.32.18.2.39.6
hmSetupCertsOcspClient OBJECT IDENTIFIER ::= { hmSetupCerts 6 }

-- {TABLE} 1.3.6.1.4.1.248.32.18.2.39.6.1
hmSetupCertsOcspClientCaProfileTableTable OBJECT-TYPE
    SYNTAX     SEQUENCE OF HmSetupCertsOcspClientCaProfileTableEntry
    MAX-ACCESS not-accessible
    STATUS     current
    DESCRIPTION
            "-- empty --"
    ::= { hmSetupCertsOcspClient 1 }

-- {ROW} 1.3.6.1.4.1.248.32.18.2.39.6.1.1
hmSetupCertsOcspClientCaProfileTableEntry OBJECT-TYPE
    SYNTAX     HmSetupCertsOcspClientCaProfileTableEntry
    MAX-ACCESS not-accessible
    STATUS     current
    DESCRIPTION
            ""
    INDEX {
            hmSetupCertsOcspClientCaProfileTableEntryProfileName
          }
    ::= { hmSetupCertsOcspClientCaProfileTableTable 1 }

HmSetupCertsOcspClientCaProfileTableEntry ::= SEQUENCE {
            hmSetupCertsOcspClientCaProfileTableEntryProfileName DisplayString,
            hmSetupCertsOcspClientCaProfileTableEntryCaDistinguishedName DisplayString,
            hmSetupCertsOcspClientCaProfileTableEntryPreferAia INTEGER,
            hmSetupCertsOcspClientCaProfileTableEntryResponderProfileName DisplayString,
            hmSetupCertsOcspClientCaProfileTableEntrySourceInterface DisplayString,
            hmSetupCertsOcspClientCaProfileTableEntryCertEvaluationMode INTEGER,
            hmSetupCertsOcspClientCaProfileTableEntrySyslogEvents INTEGER
    }

-- {COLUMN} 1.3.6.1.4.1.248.32.18.2.39.6.1.1.1
hmSetupCertsOcspClientCaProfileTableEntryProfileName OBJECT-TYPE
    SYNTAX     DisplayString (SIZE(0..32))
    MAX-ACCESS read-write
    STATUS     current
    DESCRIPTION
            "-- empty --"
    ::= { hmSetupCertsOcspClientCaProfileTableEntry 1 }

-- {COLUMN} 1.3.6.1.4.1.248.32.18.2.39.6.1.1.2
hmSetupCertsOcspClientCaProfileTableEntryCaDistinguishedName OBJECT-TYPE
    SYNTAX     DisplayString (SIZE(0..251))
    MAX-ACCESS read-write
    STATUS     current
    DESCRIPTION
            "-- empty --"
    ::= { hmSetupCertsOcspClientCaProfileTableEntry 2 }

-- {COLUMN} 1.3.6.1.4.1.248.32.18.2.39.6.1.1.3
hmSetupCertsOcspClientCaProfileTableEntryPreferAia OBJECT-TYPE
    SYNTAX     INTEGER {
                  eNo (0),
                  eYes (1)
            }
    MAX-ACCESS read-write
    STATUS     current
    DESCRIPTION
            "-- empty --"
    ::= { hmSetupCertsOcspClientCaProfileTableEntry 3 }

-- {COLUMN} 1.3.6.1.4.1.248.32.18.2.39.6.1.1.4
hmSetupCertsOcspClientCaProfileTableEntryResponderProfileName OBJECT-TYPE
    SYNTAX     DisplayString (SIZE(0..32))
    MAX-ACCESS read-write
    STATUS     current
    DESCRIPTION
            "-- empty --"
    ::= { hmSetupCertsOcspClientCaProfileTableEntry 4 }

-- {COLUMN} 1.3.6.1.4.1.248.32.18.2.39.6.1.1.5
hmSetupCertsOcspClientCaProfileTableEntrySourceInterface OBJECT-TYPE
    SYNTAX     DisplayString (SIZE(0..16))
    MAX-ACCESS read-write
    STATUS     current
    DESCRIPTION
            "-- empty --"
    ::= { hmSetupCertsOcspClientCaProfileTableEntry 5 }

-- {COLUMN} 1.3.6.1.4.1.248.32.18.2.39.6.1.1.6
hmSetupCertsOcspClientCaProfileTableEntryCertEvaluationMode OBJECT-TYPE
    SYNTAX     INTEGER {
                  eStrict (0),
                  eLoose (1)
            }
    MAX-ACCESS read-write
    STATUS     current
    DESCRIPTION
            "-- empty --"
    ::= { hmSetupCertsOcspClientCaProfileTableEntry 6 }

-- {COLUMN} 1.3.6.1.4.1.248.32.18.2.39.6.1.1.7
hmSetupCertsOcspClientCaProfileTableEntrySyslogEvents OBJECT-TYPE
    SYNTAX     INTEGER {
                  eNo (0),
                  eYes (1)
            }
    MAX-ACCESS read-write
    STATUS     current
    DESCRIPTION
            "-- empty --"
    ::= { hmSetupCertsOcspClientCaProfileTableEntry 7 }

-- {TABLE} 1.3.6.1.4.1.248.32.18.2.39.6.2
hmSetupCertsOcspClientResponderProfileTableTable OBJECT-TYPE
    SYNTAX     SEQUENCE OF HmSetupCertsOcspClientResponderProfileTableEntry
    MAX-ACCESS not-accessible
    STATUS     current
    DESCRIPTION
            "-- empty --"
    ::= { hmSetupCertsOcspClient 2 }

-- {ROW} 1.3.6.1.4.1.248.32.18.2.39.6.2.1
hmSetupCertsOcspClientResponderProfileTableEntry OBJECT-TYPE
    SYNTAX     HmSetupCertsOcspClientResponderProfileTableEntry
    MAX-ACCESS not-accessible
    STATUS     current
    DESCRIPTION
            ""
    INDEX {
            hmSetupCertsOcspClientResponderProfileTableEntryProfileName
          }
    ::= { hmSetupCertsOcspClientResponderProfileTableTable 1 }

HmSetupCertsOcspClientResponderProfileTableEntry ::= SEQUENCE {
            hmSetupCertsOcspClientResponderProfileTableEntryProfileName DisplayString,
            hmSetupCertsOcspClientResponderProfileTableEntryUrl DisplayString
    }

-- {COLUMN} 1.3.6.1.4.1.248.32.18.2.39.6.2.1.1
hmSetupCertsOcspClientResponderProfileTableEntryProfileName OBJECT-TYPE
    SYNTAX     DisplayString (SIZE(0..32))
    MAX-ACCESS read-write
    STATUS     current
    DESCRIPTION
            "-- empty --"
    ::= { hmSetupCertsOcspClientResponderProfileTableEntry 1 }

-- {COLUMN} 1.3.6.1.4.1.248.32.18.2.39.6.2.1.2
hmSetupCertsOcspClientResponderProfileTableEntryUrl OBJECT-TYPE
    SYNTAX     DisplayString (SIZE(0..251))
    MAX-ACCESS read-write
    STATUS     current
    DESCRIPTION
            "-- empty --"
    ::= { hmSetupCertsOcspClientResponderProfileTableEntry 2 }

-- {NODE} 1.3.6.1.4.1.248.32.18.2.51
hmSetupHidiscovery OBJECT IDENTIFIER ::= { hmSetup 51 }

-- {SCALAR} 1.3.6.1.4.1.248.32.18.2.51.1
hmSetupHidiscoveryServerOperating OBJECT-TYPE
    SYNTAX     INTEGER {
                  eEnabled (1),
                  eDisabled (2),
                  eReadOnly (3)
            }
    MAX-ACCESS read-write
    STATUS     current
    DESCRIPTION
            "-- empty --"
    ::= { hmSetupHidiscovery 1 }

-- {NODE} 1.3.6.1.4.1.248.32.18.2.52
hmSetupComPorts OBJECT IDENTIFIER ::= { hmSetup 52 }

-- {TABLE} 1.3.6.1.4.1.248.32.18.2.52.1
hmSetupComPortsDevTable OBJECT-TYPE
    SYNTAX     SEQUENCE OF HmSetupComPortsDevEntry
    MAX-ACCESS not-accessible
    STATUS     current
    DESCRIPTION
            ""
    ::= { hmSetupComPorts 1 }

-- {ROW} 1.3.6.1.4.1.248.32.18.2.52.1.1
hmSetupComPortsDevEntry OBJECT-TYPE
    SYNTAX     HmSetupComPortsDevEntry
    MAX-ACCESS not-accessible
    STATUS     current
    DESCRIPTION
            ""
    INDEX {
            hmSetupComPortsDevEntryDeviceType
          }
    ::= { hmSetupComPortsDevTable 1 }

HmSetupComPortsDevEntry ::= SEQUENCE {
            hmSetupComPortsDevEntryDeviceType INTEGER,
            hmSetupComPortsDevEntryServ INTEGER
    }

-- {COLUMN} 1.3.6.1.4.1.248.32.18.2.52.1.1.1
hmSetupComPortsDevEntryDeviceType OBJECT-TYPE
    SYNTAX     INTEGER {
                  eOutband (1),
                  eOptionIcon (17),
                  eHuaweiE612E630E1750 (21),
                  e4gSystemsUxs1 (23),
                  eNovatelMerlinMc950d (26),
                  eSierraAircard875u (30),
                  eHuaweiE172E220E870 (31),
                  eBelkinF5u103 (33),
                  eProlific2303 (34),
                  eFtdi8u232am (35),
                  eSierraCompass885 (39),
                  eSierraAircard501 (46),
                  eHuaweiK4505 (49),
                  eHuaweiK3765 (51),
                  eSierraDirectIp (53),
                  eHuaweiE182 (54),
                  eHuaweiE1750 (57),
                  eNokiaCs19 (59),
                  eHuaweiE398 (60),
                  eHuaweiE1550 (61),
                  eHuaweiE352 (64)
            }
    MAX-ACCESS read-write
    STATUS     current
    DESCRIPTION
            "-- empty --"
    ::= { hmSetupComPortsDevEntry 1 }

-- {COLUMN} 1.3.6.1.4.1.248.32.18.2.52.1.1.4
hmSetupComPortsDevEntryServ OBJECT-TYPE
    SYNTAX     INTEGER {
                  eWan (1),
                  eCOMPortServ (2)
            }
    MAX-ACCESS read-write
    STATUS     current
    DESCRIPTION
            ""
    ::= { hmSetupComPortsDevEntry 4 }

-- {NODE} 1.3.6.1.4.1.248.32.18.2.52.2
hmSetupComPortsCOMPortServ OBJECT IDENTIFIER ::= { hmSetupComPorts 2 }

-- {TABLE} 1.3.6.1.4.1.248.32.18.2.52.2.1
hmSetupComPortsCOMPortServOperTable OBJECT-TYPE
    SYNTAX     SEQUENCE OF HmSetupComPortsCOMPortServOperEntry
    MAX-ACCESS not-accessible
    STATUS     current
    DESCRIPTION
            ""
    ::= { hmSetupComPortsCOMPortServ 1 }

-- {ROW} 1.3.6.1.4.1.248.32.18.2.52.2.1.1
hmSetupComPortsCOMPortServOperEntry OBJECT-TYPE
    SYNTAX     HmSetupComPortsCOMPortServOperEntry
    MAX-ACCESS not-accessible
    STATUS     current
    DESCRIPTION
            ""
    INDEX {
            hmSetupComPortsCOMPortServOperEntryDeviceType,
            hmSetupComPortsCOMPortServOperEntryPortNumber
          }
    ::= { hmSetupComPortsCOMPortServOperTable 1 }

HmSetupComPortsCOMPortServOperEntry ::= SEQUENCE {
            hmSetupComPortsCOMPortServOperEntryDeviceType INTEGER,
            hmSetupComPortsCOMPortServOperEntryPortNumber Integer32,
            hmSetupComPortsCOMPortServOperEntryOperating INTEGER
    }

-- {COLUMN} 1.3.6.1.4.1.248.32.18.2.52.2.1.1.1
hmSetupComPortsCOMPortServOperEntryDeviceType OBJECT-TYPE
    SYNTAX     INTEGER {
                  eOutband (1),
                  eBelkinF5u103 (33),
                  eProlific2303 (34),
                  eFtdi8u232am (35)
            }
    MAX-ACCESS read-write
    STATUS     current
    DESCRIPTION
            "-- empty --"
    ::= { hmSetupComPortsCOMPortServOperEntry 1 }

-- {COLUMN} 1.3.6.1.4.1.248.32.18.2.52.2.1.1.2
hmSetupComPortsCOMPortServOperEntryPortNumber OBJECT-TYPE
    SYNTAX     Integer32 (0..255)
    MAX-ACCESS read-write
    STATUS     current
    DESCRIPTION
            "-- empty --"
    ::= { hmSetupComPortsCOMPortServOperEntry 2 }

-- {COLUMN} 1.3.6.1.4.1.248.32.18.2.52.2.1.1.4
hmSetupComPortsCOMPortServOperEntryOperating OBJECT-TYPE
    SYNTAX     INTEGER {
                  eNo (0),
                  eYes (1)
            }
    MAX-ACCESS read-write
    STATUS     current
    DESCRIPTION
            "-- empty --"
    ::= { hmSetupComPortsCOMPortServOperEntry 4 }

-- {TABLE} 1.3.6.1.4.1.248.32.18.2.52.2.2
hmSetupComPortsCOMPortServCOMPortSetTable OBJECT-TYPE
    SYNTAX     SEQUENCE OF HmSetupComPortsCOMPortServCOMPortSetEntry
    MAX-ACCESS not-accessible
    STATUS     current
    DESCRIPTION
            ""
    ::= { hmSetupComPortsCOMPortServ 2 }

-- {ROW} 1.3.6.1.4.1.248.32.18.2.52.2.2.1
hmSetupComPortsCOMPortServCOMPortSetEntry OBJECT-TYPE
    SYNTAX     HmSetupComPortsCOMPortServCOMPortSetEntry
    MAX-ACCESS not-accessible
    STATUS     current
    DESCRIPTION
            ""
    INDEX {
            hmSetupComPortsCOMPortServCOMPortSetEntryDeviceType,
            hmSetupComPortsCOMPortServCOMPortSetEntryPortNumber
          }
    ::= { hmSetupComPortsCOMPortServCOMPortSetTable 1 }

HmSetupComPortsCOMPortServCOMPortSetEntry ::= SEQUENCE {
            hmSetupComPortsCOMPortServCOMPortSetEntryDeviceType INTEGER,
            hmSetupComPortsCOMPortServCOMPortSetEntryPortNumber Integer32,
            hmSetupComPortsCOMPortServCOMPortSetEntryBitRate INTEGER,
            hmSetupComPortsCOMPortServCOMPortSetEntryDataBits INTEGER,
            hmSetupComPortsCOMPortServCOMPortSetEntryParity INTEGER,
            hmSetupComPortsCOMPortServCOMPortSetEntryStopBits INTEGER,
            hmSetupComPortsCOMPortServCOMPortSetEntryHandshake INTEGER,
            hmSetupComPortsCOMPortServCOMPortSetEntryReadyCondition INTEGER,
            hmSetupComPortsCOMPortServCOMPortSetEntryReadyDataTimeout Integer32
    }

-- {COLUMN} 1.3.6.1.4.1.248.32.18.2.52.2.2.1.1
hmSetupComPortsCOMPortServCOMPortSetEntryDeviceType OBJECT-TYPE
    SYNTAX     INTEGER {
                  eOutband (1),
                  eBelkinF5u103 (33),
                  eProlific2303 (34),
                  eFtdi8u232am (35)
            }
    MAX-ACCESS read-write
    STATUS     current
    DESCRIPTION
            "-- empty --"
    ::= { hmSetupComPortsCOMPortServCOMPortSetEntry 1 }

-- {COLUMN} 1.3.6.1.4.1.248.32.18.2.52.2.2.1.2
hmSetupComPortsCOMPortServCOMPortSetEntryPortNumber OBJECT-TYPE
    SYNTAX     Integer32 (0..255)
    MAX-ACCESS read-write
    STATUS     current
    DESCRIPTION
            "-- empty --"
    ::= { hmSetupComPortsCOMPortServCOMPortSetEntry 2 }

-- {COLUMN} 1.3.6.1.4.1.248.32.18.2.52.2.2.1.4
hmSetupComPortsCOMPortServCOMPortSetEntryBitRate OBJECT-TYPE
    SYNTAX     INTEGER {
                  e110 (110),
                  e300 (300),
                  e600 (600),
                  e1200 (1200),
                  e2400 (2400),
                  e4800 (4800),
                  e9600 (9600),
                  e19200 (19200),
                  e38400 (38400),
                  e57600 (57600),
                  e115200 (115200),
                  e125000 (125000),
                  e230400 (230400)
            }
    MAX-ACCESS read-write
    STATUS     current
    DESCRIPTION
            "-- empty --"
    ::= { hmSetupComPortsCOMPortServCOMPortSetEntry 4 }

-- {COLUMN} 1.3.6.1.4.1.248.32.18.2.52.2.2.1.5
hmSetupComPortsCOMPortServCOMPortSetEntryDataBits OBJECT-TYPE
    SYNTAX     INTEGER {
                  e7 (7),
                  e8 (8)
            }
    MAX-ACCESS read-write
    STATUS     current
    DESCRIPTION
            "-- empty --"
    ::= { hmSetupComPortsCOMPortServCOMPortSetEntry 5 }

-- {COLUMN} 1.3.6.1.4.1.248.32.18.2.52.2.2.1.6
hmSetupComPortsCOMPortServCOMPortSetEntryParity OBJECT-TYPE
    SYNTAX     INTEGER {
                  eNone (1),
                  eOdd (2),
                  eEven (3)
            }
    MAX-ACCESS read-write
    STATUS     current
    DESCRIPTION
            "-- empty --"
    ::= { hmSetupComPortsCOMPortServCOMPortSetEntry 6 }

-- {COLUMN} 1.3.6.1.4.1.248.32.18.2.52.2.2.1.7
hmSetupComPortsCOMPortServCOMPortSetEntryStopBits OBJECT-TYPE
    SYNTAX     INTEGER {
                  e1 (1),
                  e2 (2)
            }
    MAX-ACCESS read-write
    STATUS     current
    DESCRIPTION
            "-- empty --"
    ::= { hmSetupComPortsCOMPortServCOMPortSetEntry 7 }

-- {COLUMN} 1.3.6.1.4.1.248.32.18.2.52.2.2.1.8
hmSetupComPortsCOMPortServCOMPortSetEntryHandshake OBJECT-TYPE
    SYNTAX     INTEGER {
                  eNone (0),
                  eRtsCts (1)
            }
    MAX-ACCESS read-write
    STATUS     current
    DESCRIPTION
            "-- empty --"
    ::= { hmSetupComPortsCOMPortServCOMPortSetEntry 8 }

-- {COLUMN} 1.3.6.1.4.1.248.32.18.2.52.2.2.1.9
hmSetupComPortsCOMPortServCOMPortSetEntryReadyCondition OBJECT-TYPE
    SYNTAX     INTEGER {
                  eDtr (0),
                  eData (1)
            }
    MAX-ACCESS read-write
    STATUS     current
    DESCRIPTION
            "-- empty --"
    ::= { hmSetupComPortsCOMPortServCOMPortSetEntry 9 }

-- {COLUMN} 1.3.6.1.4.1.248.32.18.2.52.2.2.1.10
hmSetupComPortsCOMPortServCOMPortSetEntryReadyDataTimeout OBJECT-TYPE
    SYNTAX     Integer32 (0..2147483647)
    MAX-ACCESS read-write
    STATUS     current
    DESCRIPTION
            "-- empty --"
    ::= { hmSetupComPortsCOMPortServCOMPortSetEntry 10 }

-- {TABLE} 1.3.6.1.4.1.248.32.18.2.52.2.3
hmSetupComPortsCOMPortServNetwSetTable OBJECT-TYPE
    SYNTAX     SEQUENCE OF HmSetupComPortsCOMPortServNetwSetEntry
    MAX-ACCESS not-accessible
    STATUS     current
    DESCRIPTION
            ""
    ::= { hmSetupComPortsCOMPortServ 3 }

-- {ROW} 1.3.6.1.4.1.248.32.18.2.52.2.3.1
hmSetupComPortsCOMPortServNetwSetEntry OBJECT-TYPE
    SYNTAX     HmSetupComPortsCOMPortServNetwSetEntry
    MAX-ACCESS not-accessible
    STATUS     current
    DESCRIPTION
            ""
    INDEX {
            hmSetupComPortsCOMPortServNetwSetEntryDeviceType,
            hmSetupComPortsCOMPortServNetwSetEntryPortNumber
          }
    ::= { hmSetupComPortsCOMPortServNetwSetTable 1 }

HmSetupComPortsCOMPortServNetwSetEntry ::= SEQUENCE {
            hmSetupComPortsCOMPortServNetwSetEntryDeviceType INTEGER,
            hmSetupComPortsCOMPortServNetwSetEntryPortNumber Integer32,
            hmSetupComPortsCOMPortServNetwSetEntryTcpMode INTEGER,
            hmSetupComPortsCOMPortServNetwSetEntryListenPort Integer32,
            hmSetupComPortsCOMPortServNetwSetEntryConnectHostname DisplayString,
            hmSetupComPortsCOMPortServNetwSetEntryConnectPort Integer32,
            hmSetupComPortsCOMPortServNetwSetEntryLoopbackAddr DisplayString,
            hmSetupComPortsCOMPortServNetwSetEntryRfc2217Extensions INTEGER,
            hmSetupComPortsCOMPortServNetwSetEntryNewlineConversion INTEGER,
            hmSetupComPortsCOMPortServNetwSetEntryTcpRetransmitTimeout Integer32,
            hmSetupComPortsCOMPortServNetwSetEntryTcpRetryCount Integer32,
            hmSetupComPortsCOMPortServNetwSetEntryTcpKeepalive INTEGER,
            hmSetupComPortsCOMPortServNetwSetEntryTcpKeepaliveInterval Integer32,
            hmSetupComPortsCOMPortServNetwSetEntryBinaryMode INTEGER
    }

-- {COLUMN} 1.3.6.1.4.1.248.32.18.2.52.2.3.1.1
hmSetupComPortsCOMPortServNetwSetEntryDeviceType OBJECT-TYPE
    SYNTAX     INTEGER {
                  eOutband (1),
                  eBelkinF5u103 (33),
                  eProlific2303 (34),
                  eFtdi8u232am (35)
            }
    MAX-ACCESS read-write
    STATUS     current
    DESCRIPTION
            "-- empty --"
    ::= { hmSetupComPortsCOMPortServNetwSetEntry 1 }

-- {COLUMN} 1.3.6.1.4.1.248.32.18.2.52.2.3.1.2
hmSetupComPortsCOMPortServNetwSetEntryPortNumber OBJECT-TYPE
    SYNTAX     Integer32 (0..255)
    MAX-ACCESS read-write
    STATUS     current
    DESCRIPTION
            "-- empty --"
    ::= { hmSetupComPortsCOMPortServNetwSetEntry 2 }

-- {COLUMN} 1.3.6.1.4.1.248.32.18.2.52.2.3.1.4
hmSetupComPortsCOMPortServNetwSetEntryTcpMode OBJECT-TYPE
    SYNTAX     INTEGER {
                  eServer (0),
                  eClient (1)
            }
    MAX-ACCESS read-write
    STATUS     current
    DESCRIPTION
            "-- empty --"
    ::= { hmSetupComPortsCOMPortServNetwSetEntry 4 }

-- {COLUMN} 1.3.6.1.4.1.248.32.18.2.52.2.3.1.5
hmSetupComPortsCOMPortServNetwSetEntryListenPort OBJECT-TYPE
    SYNTAX     Integer32 (0..65535)
    MAX-ACCESS read-write
    STATUS     current
    DESCRIPTION
            "-- empty --"
    ::= { hmSetupComPortsCOMPortServNetwSetEntry 5 }

-- {COLUMN} 1.3.6.1.4.1.248.32.18.2.52.2.3.1.6
hmSetupComPortsCOMPortServNetwSetEntryConnectHostname OBJECT-TYPE
    SYNTAX     DisplayString (SIZE(0..48))
    MAX-ACCESS read-write
    STATUS     current
    DESCRIPTION
            "-- empty --"
    ::= { hmSetupComPortsCOMPortServNetwSetEntry 6 }

-- {COLUMN} 1.3.6.1.4.1.248.32.18.2.52.2.3.1.7
hmSetupComPortsCOMPortServNetwSetEntryConnectPort OBJECT-TYPE
    SYNTAX     Integer32 (0..65535)
    MAX-ACCESS read-write
    STATUS     current
    DESCRIPTION
            "-- empty --"
    ::= { hmSetupComPortsCOMPortServNetwSetEntry 7 }

-- {COLUMN} 1.3.6.1.4.1.248.32.18.2.52.2.3.1.8
hmSetupComPortsCOMPortServNetwSetEntryLoopbackAddr OBJECT-TYPE
    SYNTAX     DisplayString (SIZE(0..16))
    MAX-ACCESS read-write
    STATUS     current
    DESCRIPTION
            "-- empty --"
    ::= { hmSetupComPortsCOMPortServNetwSetEntry 8 }

-- {COLUMN} 1.3.6.1.4.1.248.32.18.2.52.2.3.1.9
hmSetupComPortsCOMPortServNetwSetEntryRfc2217Extensions OBJECT-TYPE
    SYNTAX     INTEGER {
                  eNo (0),
                  eYes (1)
            }
    MAX-ACCESS read-write
    STATUS     current
    DESCRIPTION
            "-- empty --"
    ::= { hmSetupComPortsCOMPortServNetwSetEntry 9 }

-- {COLUMN} 1.3.6.1.4.1.248.32.18.2.52.2.3.1.10
hmSetupComPortsCOMPortServNetwSetEntryNewlineConversion OBJECT-TYPE
    SYNTAX     INTEGER {
                  eCrlf (0),
                  eCr (1),
                  eLf (2)
            }
    MAX-ACCESS read-write
    STATUS     current
    DESCRIPTION
            "-- empty --"
    ::= { hmSetupComPortsCOMPortServNetwSetEntry 10 }

-- {COLUMN} 1.3.6.1.4.1.248.32.18.2.52.2.3.1.12
hmSetupComPortsCOMPortServNetwSetEntryTcpRetransmitTimeout OBJECT-TYPE
    SYNTAX     Integer32 (0..255)
    MAX-ACCESS read-write
    STATUS     current
    DESCRIPTION
            "-- empty --"
    ::= { hmSetupComPortsCOMPortServNetwSetEntry 12 }

-- {COLUMN} 1.3.6.1.4.1.248.32.18.2.52.2.3.1.13
hmSetupComPortsCOMPortServNetwSetEntryTcpRetryCount OBJECT-TYPE
    SYNTAX     Integer32 (0..255)
    MAX-ACCESS read-write
    STATUS     current
    DESCRIPTION
            "-- empty --"
    ::= { hmSetupComPortsCOMPortServNetwSetEntry 13 }

-- {COLUMN} 1.3.6.1.4.1.248.32.18.2.52.2.3.1.14
hmSetupComPortsCOMPortServNetwSetEntryTcpKeepalive OBJECT-TYPE
    SYNTAX     INTEGER {
                  eInactive (0),
                  eActive (1),
                  eProactive (2)
            }
    MAX-ACCESS read-write
    STATUS     current
    DESCRIPTION
            "-- empty --"
    ::= { hmSetupComPortsCOMPortServNetwSetEntry 14 }

-- {COLUMN} 1.3.6.1.4.1.248.32.18.2.52.2.3.1.15
hmSetupComPortsCOMPortServNetwSetEntryTcpKeepaliveInterval OBJECT-TYPE
    SYNTAX     Integer32 (0..2147483647)
    MAX-ACCESS read-write
    STATUS     current
    DESCRIPTION
            "-- empty --"
    ::= { hmSetupComPortsCOMPortServNetwSetEntry 15 }

-- {COLUMN} 1.3.6.1.4.1.248.32.18.2.52.2.3.1.16
hmSetupComPortsCOMPortServNetwSetEntryBinaryMode OBJECT-TYPE
    SYNTAX     INTEGER {
                  eAuto (0),
                  eYes (1),
                  eNo (2)
            }
    MAX-ACCESS read-write
    STATUS     current
    DESCRIPTION
            "-- empty --"
    ::= { hmSetupComPortsCOMPortServNetwSetEntry 16 }

-- {NODE} 1.3.6.1.4.1.248.32.18.2.52.3
hmSetupComPortsWan OBJECT IDENTIFIER ::= { hmSetupComPorts 3 }

-- {TABLE} 1.3.6.1.4.1.248.32.18.2.52.3.1
hmSetupComPortsWanDevTable OBJECT-TYPE
    SYNTAX     SEQUENCE OF HmSetupComPortsWanDevEntry
    MAX-ACCESS not-accessible
    STATUS     current
    DESCRIPTION
            ""
    ::= { hmSetupComPortsWan 1 }

-- {ROW} 1.3.6.1.4.1.248.32.18.2.52.3.1.1
hmSetupComPortsWanDevEntry OBJECT-TYPE
    SYNTAX     HmSetupComPortsWanDevEntry
    MAX-ACCESS not-accessible
    STATUS     current
    DESCRIPTION
            ""
    INDEX {
            hmSetupComPortsWanDevEntryDeviceType
          }
    ::= { hmSetupComPortsWanDevTable 1 }

HmSetupComPortsWanDevEntry ::= SEQUENCE {
            hmSetupComPortsWanDevEntryDeviceType INTEGER,
            hmSetupComPortsWanDevEntryOperating INTEGER
    }

-- {COLUMN} 1.3.6.1.4.1.248.32.18.2.52.3.1.1.1
hmSetupComPortsWanDevEntryDeviceType OBJECT-TYPE
    SYNTAX     INTEGER {
                  eOutbandModem (2),
                  eOptionIcon (17),
                  eHuaweiE612E630E1750 (21),
                  e4gSystemsUxs1 (23),
                  eNovatelMerlinMc950d (26),
                  eSierraAircard875u (30),
                  eHuaweiE172E220E870 (31),
                  eBelkinF5u103 (33),
                  eProlific2303 (34),
                  eFtdi8u232am (35),
                  eSierraCompass885 (39),
                  eSierraAircard501 (46),
                  eHuaweiK4505 (49),
                  eHuaweiK3765 (51),
                  eSierraDirectIp (53),
                  eHuaweiE182 (54),
                  eHuaweiE1750 (57),
                  eNokiaCs19 (59),
                  eHuaweiE398 (60),
                  eHuaweiE1550 (61),
                  eHuaweiE352 (64)
            }
    MAX-ACCESS read-write
    STATUS     current
    DESCRIPTION
            "-- empty --"
    ::= { hmSetupComPortsWanDevEntry 1 }

-- {COLUMN} 1.3.6.1.4.1.248.32.18.2.52.3.1.1.3
hmSetupComPortsWanDevEntryOperating OBJECT-TYPE
    SYNTAX     INTEGER {
                  eNo (0),
                  eYes (1)
            }
    MAX-ACCESS read-write
    STATUS     current
    DESCRIPTION
            "-- empty --"
    ::= { hmSetupComPortsWanDevEntry 3 }

-- {NODE} 1.3.6.1.4.1.248.32.18.2.52.4
hmSetupComPortsSerialConfig OBJECT IDENTIFIER ::= { hmSetupComPorts 4 }

-- {SCALAR} 1.3.6.1.4.1.248.32.18.2.52.4.1
hmSetupComPortsSerialConfigBitRate OBJECT-TYPE
    SYNTAX     INTEGER {
                  e1200 (1200),
                  e2400 (2400),
                  e4800 (4800),
                  e9600 (9600),
                  e19200 (19200),
                  e38400 (38400),
                  e57600 (57600),
                  e115200 (115200)
            }
    MAX-ACCESS read-write
    STATUS     current
    DESCRIPTION
            "-- empty --"
    ::= { hmSetupComPortsSerialConfig 1 }

-- {NODE} 1.3.6.1.4.1.248.32.18.2.53
hmSetupTemperatureMonitor OBJECT IDENTIFIER ::= { hmSetup 53 }

-- {SCALAR} 1.3.6.1.4.1.248.32.18.2.53.1
hmSetupTemperatureMonitorUpperLimitDegrees OBJECT-TYPE
    SYNTAX     Integer32 (-128..127)
    MAX-ACCESS read-write
    STATUS     current
    DESCRIPTION
            "-- empty --"
    ::= { hmSetupTemperatureMonitor 1 }

-- {SCALAR} 1.3.6.1.4.1.248.32.18.2.53.2
hmSetupTemperatureMonitorLowerLimitDegrees OBJECT-TYPE
    SYNTAX     Integer32 (-128..127)
    MAX-ACCESS read-write
    STATUS     current
    DESCRIPTION
            "-- empty --"
    ::= { hmSetupTemperatureMonitor 2 }

-- {NODE} 1.3.6.1.4.1.248.32.18.2.54
hmSetupTacacsPlus OBJECT IDENTIFIER ::= { hmSetup 54 }

-- {SCALAR} 1.3.6.1.4.1.248.32.18.2.54.1
hmSetupTacacsPlusAuthentication OBJECT-TYPE
    SYNTAX     INTEGER {
                  eDeactivated (0),
                  eActivated (1)
            }
    MAX-ACCESS read-only
    STATUS     current
    DESCRIPTION
            "-- empty --"
    ::= { hmSetupTacacsPlus 1 }

-- {SCALAR} 1.3.6.1.4.1.248.32.18.2.54.2
hmSetupTacacsPlusAuthorisation OBJECT-TYPE
    SYNTAX     INTEGER {
                  eDeactivated (0),
                  eActivated (1)
            }
    MAX-ACCESS read-write
    STATUS     current
    DESCRIPTION
            "-- empty --"
    ::= { hmSetupTacacsPlus 2 }

-- {SCALAR} 1.3.6.1.4.1.248.32.18.2.54.3
hmSetupTacacsPlusAccounting OBJECT-TYPE
    SYNTAX     INTEGER {
                  eDeactivated (0),
                  eActivated (1)
            }
    MAX-ACCESS read-write
    STATUS     current
    DESCRIPTION
            "-- empty --"
    ::= { hmSetupTacacsPlus 3 }

-- {SCALAR} 1.3.6.1.4.1.248.32.18.2.54.6
hmSetupTacacsPlusSharedSecret OBJECT-TYPE
    SYNTAX     DisplayString (SIZE(0..31))
    MAX-ACCESS read-write
    STATUS     current
    DESCRIPTION
            "-- empty --"
    ::= { hmSetupTacacsPlus 6 }

-- {SCALAR} 1.3.6.1.4.1.248.32.18.2.54.7
hmSetupTacacsPlusEncryption OBJECT-TYPE
    SYNTAX     INTEGER {
                  eDeactivated (0),
                  eActivated (1)
            }
    MAX-ACCESS read-write
    STATUS     current
    DESCRIPTION
            "-- empty --"
    ::= { hmSetupTacacsPlus 7 }

-- {TABLE} 1.3.6.1.4.1.248.32.18.2.54.9
hmSetupTacacsPlusServerTable OBJECT-TYPE
    SYNTAX     SEQUENCE OF HmSetupTacacsPlusServerEntry
    MAX-ACCESS not-accessible
    STATUS     current
    DESCRIPTION
            "-- empty --"
    ::= { hmSetupTacacsPlus 9 }

-- {ROW} 1.3.6.1.4.1.248.32.18.2.54.9.1
hmSetupTacacsPlusServerEntry OBJECT-TYPE
    SYNTAX     HmSetupTacacsPlusServerEntry
    MAX-ACCESS not-accessible
    STATUS     current
    DESCRIPTION
            ""
    INDEX {
            hmSetupTacacsPlusServerEntryServerAddress
          }
    ::= { hmSetupTacacsPlusServerTable 1 }

HmSetupTacacsPlusServerEntry ::= SEQUENCE {
            hmSetupTacacsPlusServerEntryServerAddress DisplayString,
            hmSetupTacacsPlusServerEntryLoopbackAddress DisplayString,
            hmSetupTacacsPlusServerEntryCompatibilityMode INTEGER
    }

-- {COLUMN} 1.3.6.1.4.1.248.32.18.2.54.9.1.1
hmSetupTacacsPlusServerEntryServerAddress OBJECT-TYPE
    SYNTAX     DisplayString (SIZE(0..31))
    MAX-ACCESS read-write
    STATUS     current
    DESCRIPTION
            "-- empty --"
    ::= { hmSetupTacacsPlusServerEntry 1 }

-- {COLUMN} 1.3.6.1.4.1.248.32.18.2.54.9.1.2
hmSetupTacacsPlusServerEntryLoopbackAddress OBJECT-TYPE
    SYNTAX     DisplayString (SIZE(0..16))
    MAX-ACCESS read-write
    STATUS     current
    DESCRIPTION
            "-- empty --"
    ::= { hmSetupTacacsPlusServerEntry 2 }

-- {COLUMN} 1.3.6.1.4.1.248.32.18.2.54.9.1.3
hmSetupTacacsPlusServerEntryCompatibilityMode OBJECT-TYPE
    SYNTAX     INTEGER {
                  eDeactivated (0),
                  eActivated (1)
            }
    MAX-ACCESS read-write
    STATUS     current
    DESCRIPTION
            "-- empty --"
    ::= { hmSetupTacacsPlusServerEntry 3 }

-- {SCALAR} 1.3.6.1.4.1.248.32.18.2.54.10
hmSetupTacacsPlusFallbackToLocalUsers OBJECT-TYPE
    SYNTAX     INTEGER {
                  eAllowed (0),
                  eProhibited (1)
            }
    MAX-ACCESS read-write
    STATUS     current
    DESCRIPTION
            "-- empty --"
    ::= { hmSetupTacacsPlus 10 }

-- {SCALAR} 1.3.6.1.4.1.248.32.18.2.54.11
hmSetupTacacsPlusSnmpGetRequestsAuthorisation OBJECT-TYPE
    SYNTAX     INTEGER {
                  eOnlyForSetupTree (0),
                  eAll (1),
                  eNone (2)
            }
    MAX-ACCESS read-write
    STATUS     current
    DESCRIPTION
            "-- empty --"
    ::= { hmSetupTacacsPlus 11 }

-- {SCALAR} 1.3.6.1.4.1.248.32.18.2.54.12
hmSetupTacacsPlusSnmpGetRequestsAccounting OBJECT-TYPE
    SYNTAX     INTEGER {
                  eOnlyForSetupTree (0),
                  eAll (1),
                  eNone (2)
            }
    MAX-ACCESS read-write
    STATUS     current
    DESCRIPTION
            "-- empty --"
    ::= { hmSetupTacacsPlus 12 }

-- {SCALAR} 1.3.6.1.4.1.248.32.18.2.54.13
hmSetupTacacsPlusBypassTacacsForCronScriptsActionTable OBJECT-TYPE
    SYNTAX     INTEGER {
                  eDeactivated (0),
                  eActivated (1)
            }
    MAX-ACCESS read-write
    STATUS     current
    DESCRIPTION
            "-- empty --"
    ::= { hmSetupTacacsPlus 13 }

-- {SCALAR} 1.3.6.1.4.1.248.32.18.2.54.14
hmSetupTacacsPlusIncludeValueIntoAuthorisationRequest OBJECT-TYPE
    SYNTAX     INTEGER {
                  eDeactivated (0),
                  eActivated (1)
            }
    MAX-ACCESS read-write
    STATUS     current
    DESCRIPTION
            "-- empty --"
    ::= { hmSetupTacacsPlus 14 }

-- {NODE} 1.3.6.1.4.1.248.32.18.2.56
hmSetupUsb OBJECT IDENTIFIER ::= { hmSetup 56 }

-- {SCALAR} 1.3.6.1.4.1.248.32.18.2.56.1
hmSetupUsbFirmwareAndLoader OBJECT-TYPE
    SYNTAX     INTEGER {
                  eInactive (1),
                  eIfUnconfigured (2),
                  eActive (3)
            }
    MAX-ACCESS read-only
    STATUS     deprecated
    DESCRIPTION
            "-- empty --"
    ::= { hmSetupUsb 1 }

-- {SCALAR} 1.3.6.1.4.1.248.32.18.2.56.2
hmSetupUsbConfigAndScript OBJECT-TYPE
    SYNTAX     INTEGER {
                  eInactive (1),
                  eIfUnconfigured (2),
                  eActive (3)
            }
    MAX-ACCESS read-only
    STATUS     deprecated
    DESCRIPTION
            "-- empty --"
    ::= { hmSetupUsb 2 }

-- {NODE} 1.3.6.1.4.1.248.32.18.2.59
hmSetupWtpMngmt OBJECT IDENTIFIER ::= { hmSetup 59 }

-- {TABLE} 1.3.6.1.4.1.248.32.18.2.59.1
hmSetupWtpMngmtStaticWlcConfTable OBJECT-TYPE
    SYNTAX     SEQUENCE OF HmSetupWtpMngmtStaticWlcConfEntry
    MAX-ACCESS not-accessible
    STATUS     current
    DESCRIPTION
            "static WLC configuration"
    ::= { hmSetupWtpMngmt 1 }

-- {ROW} 1.3.6.1.4.1.248.32.18.2.59.1.1
hmSetupWtpMngmtStaticWlcConfEntry OBJECT-TYPE
    SYNTAX     HmSetupWtpMngmtStaticWlcConfEntry
    MAX-ACCESS not-accessible
    STATUS     current
    DESCRIPTION
            ""
    INDEX {
            hmSetupWtpMngmtStaticWlcConfEntryIpAddress
          }
    ::= { hmSetupWtpMngmtStaticWlcConfTable 1 }

HmSetupWtpMngmtStaticWlcConfEntry ::= SEQUENCE {
            hmSetupWtpMngmtStaticWlcConfEntryIpAddress DisplayString,
            hmSetupWtpMngmtStaticWlcConfEntryPort Integer32,
            hmSetupWtpMngmtStaticWlcConfEntryLoopbackAddr DisplayString
    }

-- {COLUMN} 1.3.6.1.4.1.248.32.18.2.59.1.1.1
hmSetupWtpMngmtStaticWlcConfEntryIpAddress OBJECT-TYPE
    SYNTAX     DisplayString (SIZE(0..63))
    MAX-ACCESS read-write
    STATUS     current
    DESCRIPTION
            "-- empty --"
    ::= { hmSetupWtpMngmtStaticWlcConfEntry 1 }

-- {COLUMN} 1.3.6.1.4.1.248.32.18.2.59.1.1.2
hmSetupWtpMngmtStaticWlcConfEntryPort OBJECT-TYPE
    SYNTAX     Integer32 (0..65535)
    MAX-ACCESS read-write
    STATUS     current
    DESCRIPTION
            "-- empty --"
    ::= { hmSetupWtpMngmtStaticWlcConfEntry 2 }

-- {COLUMN} 1.3.6.1.4.1.248.32.18.2.59.1.1.3
hmSetupWtpMngmtStaticWlcConfEntryLoopbackAddr OBJECT-TYPE
    SYNTAX     DisplayString (SIZE(0..16))
    MAX-ACCESS read-write
    STATUS     current
    DESCRIPTION
            "-- empty --"
    ::= { hmSetupWtpMngmtStaticWlcConfEntry 3 }

-- {NODE} 1.3.6.1.4.1.248.32.18.2.59.3
hmSetupWtpMngmtCapwapTuning OBJECT IDENTIFIER ::= { hmSetupWtpMngmt 3 }

-- {SCALAR} 1.3.6.1.4.1.248.32.18.2.59.3.1
hmSetupWtpMngmtCapwapTuningEchoInterval OBJECT-TYPE
    SYNTAX     Integer32 (0..65535)
    MAX-ACCESS read-write
    STATUS     current
    DESCRIPTION
            "-- empty --"
    ::= { hmSetupWtpMngmtCapwapTuning 1 }

-- {SCALAR} 1.3.6.1.4.1.248.32.18.2.59.3.2
hmSetupWtpMngmtCapwapTuningRetransmitInterval OBJECT-TYPE
    SYNTAX     Integer32 (0..65535)
    MAX-ACCESS read-write
    STATUS     current
    DESCRIPTION
            "-- empty --"
    ::= { hmSetupWtpMngmtCapwapTuning 2 }

-- {SCALAR} 1.3.6.1.4.1.248.32.18.2.59.3.3
hmSetupWtpMngmtCapwapTuningDiscoveryInterval OBJECT-TYPE
    SYNTAX     Integer32 (0..65535)
    MAX-ACCESS read-write
    STATUS     current
    DESCRIPTION
            "-- empty --"
    ::= { hmSetupWtpMngmtCapwapTuning 3 }

-- {SCALAR} 1.3.6.1.4.1.248.32.18.2.59.3.4
hmSetupWtpMngmtCapwapTuningMaxDiscoveryInterval OBJECT-TYPE
    SYNTAX     Integer32 (0..65535)
    MAX-ACCESS read-write
    STATUS     current
    DESCRIPTION
            "-- empty --"
    ::= { hmSetupWtpMngmtCapwapTuning 4 }

-- {SCALAR} 1.3.6.1.4.1.248.32.18.2.59.3.5
hmSetupWtpMngmtCapwapTuningSilentInterval OBJECT-TYPE
    SYNTAX     Integer32 (0..65535)
    MAX-ACCESS read-write
    STATUS     current
    DESCRIPTION
            "-- empty --"
    ::= { hmSetupWtpMngmtCapwapTuning 5 }

-- {SCALAR} 1.3.6.1.4.1.248.32.18.2.59.3.6
hmSetupWtpMngmtCapwapTuningEnable OBJECT-TYPE
    SYNTAX     INTEGER {
                  eNo (0),
                  eYes (1)
            }
    MAX-ACCESS read-write
    STATUS     current
    DESCRIPTION
            "-- empty --"
    ::= { hmSetupWtpMngmtCapwapTuning 6 }

-- {NODE} 1.3.6.1.4.1.248.32.18.2.59.4
hmSetupWtpMngmtAutowds OBJECT IDENTIFIER ::= { hmSetupWtpMngmt 4 }

-- {SCALAR} 1.3.6.1.4.1.248.32.18.2.59.4.1
hmSetupWtpMngmtAutowdsOperation OBJECT-TYPE
    SYNTAX     INTEGER {
                  eNo (0),
                  eYes (1)
            }
    MAX-ACCESS read-write
    STATUS     current
    DESCRIPTION
            "-- empty --"
    ::= { hmSetupWtpMngmtAutowds 1 }

-- {SCALAR} 1.3.6.1.4.1.248.32.18.2.59.4.2
hmSetupWtpMngmtAutowdsPreconfSsid OBJECT-TYPE
    SYNTAX     DisplayString (SIZE(0..32))
    MAX-ACCESS read-write
    STATUS     current
    DESCRIPTION
            "-- empty --"
    ::= { hmSetupWtpMngmtAutowds 2 }

-- {SCALAR} 1.3.6.1.4.1.248.32.18.2.59.4.3
hmSetupWtpMngmtAutowdsPreconfKey OBJECT-TYPE
    SYNTAX     DisplayString (SIZE(0..63))
    MAX-ACCESS read-write
    STATUS     current
    DESCRIPTION
            "-- empty --"
    ::= { hmSetupWtpMngmtAutowds 3 }

-- {SCALAR} 1.3.6.1.4.1.248.32.18.2.59.4.4
hmSetupWtpMngmtAutowdsTimeTillPreconfScan OBJECT-TYPE
    SYNTAX     Integer32 (0..2147483647)
    MAX-ACCESS read-write
    STATUS     current
    DESCRIPTION
            "-- empty --"
    ::= { hmSetupWtpMngmtAutowds 4 }

-- {SCALAR} 1.3.6.1.4.1.248.32.18.2.59.4.5
hmSetupWtpMngmtAutowdsTimeTillExpressScan OBJECT-TYPE
    SYNTAX     Integer32 (0..2147483647)
    MAX-ACCESS read-write
    STATUS     current
    DESCRIPTION
            "-- empty --"
    ::= { hmSetupWtpMngmtAutowds 5 }

-- {SCALAR} 1.3.6.1.4.1.248.32.18.2.59.5
hmSetupWtpMngmtCapwapPort OBJECT-TYPE
    SYNTAX     Integer32 (0..65535)
    MAX-ACCESS read-write
    STATUS     current
    DESCRIPTION
            "-- empty --"
    ::= { hmSetupWtpMngmt 5 }

-- {SCALAR} 1.3.6.1.4.1.248.32.18.2.59.120
hmSetupWtpMngmtLogEntries OBJECT-TYPE
    SYNTAX     Integer32 (0..2147483647)
    MAX-ACCESS read-write
    STATUS     current
    DESCRIPTION
            "-- empty --"
    ::= { hmSetupWtpMngmt 120 }

-- {NODE} 1.3.6.1.4.1.248.32.18.2.60
hmSetupAutold OBJECT IDENTIFIER ::= { hmSetup 60 }

-- {NODE} 1.3.6.1.4.1.248.32.18.2.60.1
hmSetupAutoldNetwork OBJECT IDENTIFIER ::= { hmSetupAutold 1 }

-- {NODE} 1.3.6.1.4.1.248.32.18.2.60.1.1
hmSetupAutoldNetworkFirmware OBJECT IDENTIFIER ::= { hmSetupAutoldNetwork 1 }

-- {SCALAR} 1.3.6.1.4.1.248.32.18.2.60.1.1.1
hmSetupAutoldNetworkFirmwareCondition OBJECT-TYPE
    SYNTAX     INTEGER {
                  eUnconditionally (0),
                  eIfDifferent (1),
                  eIfNewer (2)
            }
    MAX-ACCESS read-write
    STATUS     current
    DESCRIPTION
            "-- empty --"
    ::= { hmSetupAutoldNetworkFirmware 1 }

-- {SCALAR} 1.3.6.1.4.1.248.32.18.2.60.1.1.2
hmSetupAutoldNetworkFirmwareUrl OBJECT-TYPE
    SYNTAX     DisplayString (SIZE(0..127))
    MAX-ACCESS read-write
    STATUS     current
    DESCRIPTION
            "-- empty --"
    ::= { hmSetupAutoldNetworkFirmware 2 }

-- {SCALAR} 1.3.6.1.4.1.248.32.18.2.60.1.1.3
hmSetupAutoldNetworkFirmwareMinimumVersion OBJECT-TYPE
    SYNTAX     DisplayString (SIZE(0..14))
    MAX-ACCESS read-write
    STATUS     current
    DESCRIPTION
            "-- empty --"
    ::= { hmSetupAutoldNetworkFirmware 3 }

-- {NODE} 1.3.6.1.4.1.248.32.18.2.60.1.2
hmSetupAutoldNetworkConfig OBJECT IDENTIFIER ::= { hmSetupAutoldNetwork 2 }

-- {SCALAR} 1.3.6.1.4.1.248.32.18.2.60.1.2.1
hmSetupAutoldNetworkConfigCondition OBJECT-TYPE
    SYNTAX     INTEGER {
                  eUnconditionally (0),
                  eIfDifferent (1)
            }
    MAX-ACCESS read-write
    STATUS     current
    DESCRIPTION
            "-- empty --"
    ::= { hmSetupAutoldNetworkConfig 1 }

-- {SCALAR} 1.3.6.1.4.1.248.32.18.2.60.1.2.2
hmSetupAutoldNetworkConfigUrl OBJECT-TYPE
    SYNTAX     DisplayString (SIZE(0..127))
    MAX-ACCESS read-write
    STATUS     current
    DESCRIPTION
            "-- empty --"
    ::= { hmSetupAutoldNetworkConfig 2 }

-- {NODE} 1.3.6.1.4.1.248.32.18.2.60.1.3
hmSetupAutoldNetworkScript OBJECT IDENTIFIER ::= { hmSetupAutoldNetwork 3 }

-- {SCALAR} 1.3.6.1.4.1.248.32.18.2.60.1.3.1
hmSetupAutoldNetworkScriptCondition OBJECT-TYPE
    SYNTAX     INTEGER {
                  eUnconditionally (0),
                  eIfDifferent (1)
            }
    MAX-ACCESS read-write
    STATUS     current
    DESCRIPTION
            "-- empty --"
    ::= { hmSetupAutoldNetworkScript 1 }

-- {SCALAR} 1.3.6.1.4.1.248.32.18.2.60.1.3.2
hmSetupAutoldNetworkScriptUrl OBJECT-TYPE
    SYNTAX     DisplayString (SIZE(0..127))
    MAX-ACCESS read-write
    STATUS     current
    DESCRIPTION
            "-- empty --"
    ::= { hmSetupAutoldNetworkScript 2 }

-- {NODE} 1.3.6.1.4.1.248.32.18.2.60.1.4
hmSetupAutoldNetworkTftpClient OBJECT IDENTIFIER ::= { hmSetupAutoldNetwork 4 }

-- {SCALAR} 1.3.6.1.4.1.248.32.18.2.60.1.4.1
hmSetupAutoldNetworkTftpClientBytesPerHashmark OBJECT-TYPE
    SYNTAX     Integer32 (0..2147483647)
    MAX-ACCESS read-write
    STATUS     obsolete
    DESCRIPTION
            "-- empty --"
    ::= { hmSetupAutoldNetworkTftpClient 1 }

-- {NODE} 1.3.6.1.4.1.248.32.18.2.60.3
hmSetupAutoldLicense OBJECT IDENTIFIER ::= { hmSetupAutold 3 }

-- {SCALAR} 1.3.6.1.4.1.248.32.18.2.60.3.1
hmSetupAutoldLicenseUrl OBJECT-TYPE
    SYNTAX     DisplayString (SIZE(0..127))
    MAX-ACCESS read-only
    STATUS     current
    DESCRIPTION
            "-- empty --"
    ::= { hmSetupAutoldLicense 1 }

-- {SCALAR} 1.3.6.1.4.1.248.32.18.2.60.3.2
hmSetupAutoldLicenseLoopbackAddress OBJECT-TYPE
    SYNTAX     DisplayString (SIZE(0..15))
    MAX-ACCESS read-only
    STATUS     current
    DESCRIPTION
            "-- empty --"
    ::= { hmSetupAutoldLicense 2 }

-- {SCALAR} 1.3.6.1.4.1.248.32.18.2.60.3.10
hmSetupAutoldLicenseCompany OBJECT-TYPE
    SYNTAX     DisplayString (SIZE(0..127))
    MAX-ACCESS read-only
    STATUS     current
    DESCRIPTION
            "-- empty --"
    ::= { hmSetupAutoldLicense 10 }

-- {SCALAR} 1.3.6.1.4.1.248.32.18.2.60.3.11
hmSetupAutoldLicenseLastName OBJECT-TYPE
    SYNTAX     DisplayString (SIZE(0..31))
    MAX-ACCESS read-only
    STATUS     current
    DESCRIPTION
            "-- empty --"
    ::= { hmSetupAutoldLicense 11 }

-- {SCALAR} 1.3.6.1.4.1.248.32.18.2.60.3.12
hmSetupAutoldLicenseFirstName OBJECT-TYPE
    SYNTAX     DisplayString (SIZE(0..31))
    MAX-ACCESS read-only
    STATUS     current
    DESCRIPTION
            "-- empty --"
    ::= { hmSetupAutoldLicense 12 }

-- {SCALAR} 1.3.6.1.4.1.248.32.18.2.60.3.13
hmSetupAutoldLicenseStreetAndNumber OBJECT-TYPE
    SYNTAX     DisplayString (SIZE(0..127))
    MAX-ACCESS read-only
    STATUS     current
    DESCRIPTION
            "-- empty --"
    ::= { hmSetupAutoldLicense 13 }

-- {SCALAR} 1.3.6.1.4.1.248.32.18.2.60.3.14
hmSetupAutoldLicensePostCode OBJECT-TYPE
    SYNTAX     DisplayString (SIZE(0..10))
    MAX-ACCESS read-only
    STATUS     current
    DESCRIPTION
            "-- empty --"
    ::= { hmSetupAutoldLicense 14 }

-- {SCALAR} 1.3.6.1.4.1.248.32.18.2.60.3.15
hmSetupAutoldLicenseCity OBJECT-TYPE
    SYNTAX     DisplayString (SIZE(0..63))
    MAX-ACCESS read-only
    STATUS     current
    DESCRIPTION
            "-- empty --"
    ::= { hmSetupAutoldLicense 15 }

-- {SCALAR} 1.3.6.1.4.1.248.32.18.2.60.3.16
hmSetupAutoldLicenseCountry OBJECT-TYPE
    SYNTAX     DisplayString (SIZE(0..63))
    MAX-ACCESS read-only
    STATUS     current
    DESCRIPTION
            "-- empty --"
    ::= { hmSetupAutoldLicense 16 }

-- {SCALAR} 1.3.6.1.4.1.248.32.18.2.60.3.17
hmSetupAutoldLicenseEmailAddress OBJECT-TYPE
    SYNTAX     DisplayString (SIZE(0..63))
    MAX-ACCESS read-only
    STATUS     current
    DESCRIPTION
            "-- empty --"
    ::= { hmSetupAutoldLicense 17 }

-- {NODE} 1.3.6.1.4.1.248.32.18.2.60.56
hmSetupAutoldUsb OBJECT IDENTIFIER ::= { hmSetupAutold 56 }

-- {SCALAR} 1.3.6.1.4.1.248.32.18.2.60.56.1
hmSetupAutoldUsbFirmwareAndLoader OBJECT-TYPE
    SYNTAX     INTEGER {
                  eInactive (1),
                  eIfUnconfigured (2),
                  eActive (3)
            }
    MAX-ACCESS read-write
    STATUS     current
    DESCRIPTION
            "-- empty --"
    ::= { hmSetupAutoldUsb 1 }

-- {SCALAR} 1.3.6.1.4.1.248.32.18.2.60.56.2
hmSetupAutoldUsbConfigAndScript OBJECT-TYPE
    SYNTAX     INTEGER {
                  eInactive (1),
                  eIfUnconfigured (2),
                  eActive (3)
            }
    MAX-ACCESS read-write
    STATUS     current
    DESCRIPTION
            "-- empty --"
    ::= { hmSetupAutoldUsb 2 }

-- {NODE} 1.3.6.1.4.1.248.32.18.2.63
hmSetupPacketCapture OBJECT IDENTIFIER ::= { hmSetup 63 }

-- {SCALAR} 1.3.6.1.4.1.248.32.18.2.63.1
hmSetupPacketCaptureLcoscapOperating OBJECT-TYPE
    SYNTAX     INTEGER {
                  eNo (0),
                  eYes (1)
            }
    MAX-ACCESS read-write
    STATUS     current
    DESCRIPTION
            "-- empty --"
    ::= { hmSetupPacketCapture 1 }

-- {SCALAR} 1.3.6.1.4.1.248.32.18.2.63.2
hmSetupPacketCaptureLcoscapPort OBJECT-TYPE
    SYNTAX     Integer32 (0..65535)
    MAX-ACCESS read-write
    STATUS     current
    DESCRIPTION
            "-- empty --"
    ::= { hmSetupPacketCapture 2 }

-- {SCALAR} 1.3.6.1.4.1.248.32.18.2.63.11
hmSetupPacketCaptureRpcapOperating OBJECT-TYPE
    SYNTAX     INTEGER {
                  eNo (0),
                  eYes (1)
            }
    MAX-ACCESS read-write
    STATUS     current
    DESCRIPTION
            "-- empty --"
    ::= { hmSetupPacketCapture 11 }

-- {SCALAR} 1.3.6.1.4.1.248.32.18.2.63.12
hmSetupPacketCaptureRpcapPort OBJECT-TYPE
    SYNTAX     Integer32 (0..65535)
    MAX-ACCESS read-write
    STATUS     current
    DESCRIPTION
            "-- empty --"
    ::= { hmSetupPacketCapture 12 }

-- {NODE} 1.3.6.1.4.1.248.32.18.2.70
hmSetupIpv6 OBJECT IDENTIFIER ::= { hmSetup 70 }

-- {NODE} 1.3.6.1.4.1.248.32.18.2.70.1
hmSetupIpv6Tunnel OBJECT IDENTIFIER ::= { hmSetupIpv6 1 }

-- {TABLE} 1.3.6.1.4.1.248.32.18.2.70.1.1
hmSetupIpv6Tunnel6in4Table OBJECT-TYPE
    SYNTAX     SEQUENCE OF HmSetupIpv6Tunnel6in4Entry
    MAX-ACCESS not-accessible
    STATUS     current
    DESCRIPTION
            "-- empty --"
    ::= { hmSetupIpv6Tunnel 1 }

-- {ROW} 1.3.6.1.4.1.248.32.18.2.70.1.1.1
hmSetupIpv6Tunnel6in4Entry OBJECT-TYPE
    SYNTAX     HmSetupIpv6Tunnel6in4Entry
    MAX-ACCESS not-accessible
    STATUS     current
    DESCRIPTION
            ""
    INDEX {
            hmSetupIpv6Tunnel6in4EntryPeerName
          }
    ::= { hmSetupIpv6Tunnel6in4Table 1 }

HmSetupIpv6Tunnel6in4Entry ::= SEQUENCE {
            hmSetupIpv6Tunnel6in4EntryPeerName DisplayString,
            hmSetupIpv6Tunnel6in4EntryRtgTag Integer32,
            hmSetupIpv6Tunnel6in4EntryGatewayAddress DisplayString,
            hmSetupIpv6Tunnel6in4EntryIpv4RtgTag Integer32,
            hmSetupIpv6Tunnel6in4EntryGatewayIpv6Address DisplayString,
            hmSetupIpv6Tunnel6in4EntryLocalIpv6Address DisplayString,
            hmSetupIpv6Tunnel6in4EntryRoutedIpv6Prefix DisplayString,
            hmSetupIpv6Tunnel6in4EntryFirewall INTEGER
    }

-- {COLUMN} 1.3.6.1.4.1.248.32.18.2.70.1.1.1.1
hmSetupIpv6Tunnel6in4EntryPeerName OBJECT-TYPE
    SYNTAX     DisplayString (SIZE(0..16))
    MAX-ACCESS read-write
    STATUS     current
    DESCRIPTION
            "-- empty --"
    ::= { hmSetupIpv6Tunnel6in4Entry 1 }

-- {COLUMN} 1.3.6.1.4.1.248.32.18.2.70.1.1.1.2
hmSetupIpv6Tunnel6in4EntryRtgTag OBJECT-TYPE
    SYNTAX     Integer32 (0..65535)
    MAX-ACCESS read-write
    STATUS     current
    DESCRIPTION
            "-- empty --"
    ::= { hmSetupIpv6Tunnel6in4Entry 2 }

-- {COLUMN} 1.3.6.1.4.1.248.32.18.2.70.1.1.1.3
hmSetupIpv6Tunnel6in4EntryGatewayAddress OBJECT-TYPE
    SYNTAX     DisplayString (SIZE(0..64))
    MAX-ACCESS read-write
    STATUS     current
    DESCRIPTION
            "-- empty --"
    ::= { hmSetupIpv6Tunnel6in4Entry 3 }

-- {COLUMN} 1.3.6.1.4.1.248.32.18.2.70.1.1.1.4
hmSetupIpv6Tunnel6in4EntryIpv4RtgTag OBJECT-TYPE
    SYNTAX     Integer32 (0..65535)
    MAX-ACCESS read-write
    STATUS     current
    DESCRIPTION
            "-- empty --"
    ::= { hmSetupIpv6Tunnel6in4Entry 4 }

-- {COLUMN} 1.3.6.1.4.1.248.32.18.2.70.1.1.1.5
hmSetupIpv6Tunnel6in4EntryGatewayIpv6Address OBJECT-TYPE
    SYNTAX     DisplayString (SIZE(0..43))
    MAX-ACCESS read-write
    STATUS     current
    DESCRIPTION
            "-- empty --"
    ::= { hmSetupIpv6Tunnel6in4Entry 5 }

-- {COLUMN} 1.3.6.1.4.1.248.32.18.2.70.1.1.1.6
hmSetupIpv6Tunnel6in4EntryLocalIpv6Address OBJECT-TYPE
    SYNTAX     DisplayString (SIZE(0..43))
    MAX-ACCESS read-write
    STATUS     current
    DESCRIPTION
            "-- empty --"
    ::= { hmSetupIpv6Tunnel6in4Entry 6 }

-- {COLUMN} 1.3.6.1.4.1.248.32.18.2.70.1.1.1.7
hmSetupIpv6Tunnel6in4EntryRoutedIpv6Prefix OBJECT-TYPE
    SYNTAX     DisplayString (SIZE(0..43))
    MAX-ACCESS read-write
    STATUS     current
    DESCRIPTION
            "-- empty --"
    ::= { hmSetupIpv6Tunnel6in4Entry 7 }

-- {COLUMN} 1.3.6.1.4.1.248.32.18.2.70.1.1.1.8
hmSetupIpv6Tunnel6in4EntryFirewall OBJECT-TYPE
    SYNTAX     INTEGER {
                  eYes (0),
                  eNo (1)
            }
    MAX-ACCESS read-write
    STATUS     current
    DESCRIPTION
            "-- empty --"
    ::= { hmSetupIpv6Tunnel6in4Entry 8 }

-- {TABLE} 1.3.6.1.4.1.248.32.18.2.70.1.2
hmSetupIpv6Tunnel6rdBorderRelayTable OBJECT-TYPE
    SYNTAX     SEQUENCE OF HmSetupIpv6Tunnel6rdBorderRelayEntry
    MAX-ACCESS not-accessible
    STATUS     current
    DESCRIPTION
            "-- empty --"
    ::= { hmSetupIpv6Tunnel 2 }

-- {ROW} 1.3.6.1.4.1.248.32.18.2.70.1.2.1
hmSetupIpv6Tunnel6rdBorderRelayEntry OBJECT-TYPE
    SYNTAX     HmSetupIpv6Tunnel6rdBorderRelayEntry
    MAX-ACCESS not-accessible
    STATUS     current
    DESCRIPTION
            ""
    INDEX {
            hmSetupIpv6Tunnel6rdBorderRelayEntryPeerName
          }
    ::= { hmSetupIpv6Tunnel6rdBorderRelayTable 1 }

HmSetupIpv6Tunnel6rdBorderRelayEntry ::= SEQUENCE {
            hmSetupIpv6Tunnel6rdBorderRelayEntryPeerName DisplayString,
            hmSetupIpv6Tunnel6rdBorderRelayEntryRtgTag Integer32,
            hmSetupIpv6Tunnel6rdBorderRelayEntryIpv4LoopbackAddress DisplayString,
            hmSetupIpv6Tunnel6rdBorderRelayEntry6rdPrefix DisplayString,
            hmSetupIpv6Tunnel6rdBorderRelayEntryIpv4MaskLength Integer32,
            hmSetupIpv6Tunnel6rdBorderRelayEntryDhcpv4Propagate INTEGER,
            hmSetupIpv6Tunnel6rdBorderRelayEntryFirewall INTEGER
    }

-- {COLUMN} 1.3.6.1.4.1.248.32.18.2.70.1.2.1.1
hmSetupIpv6Tunnel6rdBorderRelayEntryPeerName OBJECT-TYPE
    SYNTAX     DisplayString (SIZE(0..16))
    MAX-ACCESS read-write
    STATUS     current
    DESCRIPTION
            "-- empty --"
    ::= { hmSetupIpv6Tunnel6rdBorderRelayEntry 1 }

-- {COLUMN} 1.3.6.1.4.1.248.32.18.2.70.1.2.1.2
hmSetupIpv6Tunnel6rdBorderRelayEntryRtgTag OBJECT-TYPE
    SYNTAX     Integer32 (0..65535)
    MAX-ACCESS read-write
    STATUS     current
    DESCRIPTION
            "-- empty --"
    ::= { hmSetupIpv6Tunnel6rdBorderRelayEntry 2 }

-- {COLUMN} 1.3.6.1.4.1.248.32.18.2.70.1.2.1.3
hmSetupIpv6Tunnel6rdBorderRelayEntryIpv4LoopbackAddress OBJECT-TYPE
    SYNTAX     DisplayString (SIZE(0..21))
    MAX-ACCESS read-write
    STATUS     current
    DESCRIPTION
            "-- empty --"
    ::= { hmSetupIpv6Tunnel6rdBorderRelayEntry 3 }

-- {COLUMN} 1.3.6.1.4.1.248.32.18.2.70.1.2.1.4
hmSetupIpv6Tunnel6rdBorderRelayEntry6rdPrefix OBJECT-TYPE
    SYNTAX     DisplayString (SIZE(0..24))
    MAX-ACCESS read-write
    STATUS     current
    DESCRIPTION
            "-- empty --"
    ::= { hmSetupIpv6Tunnel6rdBorderRelayEntry 4 }

-- {COLUMN} 1.3.6.1.4.1.248.32.18.2.70.1.2.1.5
hmSetupIpv6Tunnel6rdBorderRelayEntryIpv4MaskLength OBJECT-TYPE
    SYNTAX     Integer32 (0..65535)
    MAX-ACCESS read-write
    STATUS     current
    DESCRIPTION
            "-- empty --"
    ::= { hmSetupIpv6Tunnel6rdBorderRelayEntry 5 }

-- {COLUMN} 1.3.6.1.4.1.248.32.18.2.70.1.2.1.6
hmSetupIpv6Tunnel6rdBorderRelayEntryDhcpv4Propagate OBJECT-TYPE
    SYNTAX     INTEGER {
                  eNo (0),
                  eYes (1)
            }
    MAX-ACCESS read-write
    STATUS     current
    DESCRIPTION
            "-- empty --"
    ::= { hmSetupIpv6Tunnel6rdBorderRelayEntry 6 }

-- {COLUMN} 1.3.6.1.4.1.248.32.18.2.70.1.2.1.7
hmSetupIpv6Tunnel6rdBorderRelayEntryFirewall OBJECT-TYPE
    SYNTAX     INTEGER {
                  eYes (0),
                  eNo (1)
            }
    MAX-ACCESS read-write
    STATUS     current
    DESCRIPTION
            "-- empty --"
    ::= { hmSetupIpv6Tunnel6rdBorderRelayEntry 7 }

-- {TABLE} 1.3.6.1.4.1.248.32.18.2.70.1.3
hmSetupIpv6Tunnel6rdTable OBJECT-TYPE
    SYNTAX     SEQUENCE OF HmSetupIpv6Tunnel6rdEntry
    MAX-ACCESS not-accessible
    STATUS     current
    DESCRIPTION
            "-- empty --"
    ::= { hmSetupIpv6Tunnel 3 }

-- {ROW} 1.3.6.1.4.1.248.32.18.2.70.1.3.1
hmSetupIpv6Tunnel6rdEntry OBJECT-TYPE
    SYNTAX     HmSetupIpv6Tunnel6rdEntry
    MAX-ACCESS not-accessible
    STATUS     current
    DESCRIPTION
            ""
    INDEX {
            hmSetupIpv6Tunnel6rdEntryPeerName
          }
    ::= { hmSetupIpv6Tunnel6rdTable 1 }

HmSetupIpv6Tunnel6rdEntry ::= SEQUENCE {
            hmSetupIpv6Tunnel6rdEntryPeerName DisplayString,
            hmSetupIpv6Tunnel6rdEntryRtgTag Integer32,
            hmSetupIpv6Tunnel6rdEntryBorderRelayAddress DisplayString,
            hmSetupIpv6Tunnel6rdEntryIpv4RtgTag Integer32,
            hmSetupIpv6Tunnel6rdEntry6rdPrefix DisplayString,
            hmSetupIpv6Tunnel6rdEntryIpv4MaskLength Integer32,
            hmSetupIpv6Tunnel6rdEntryFirewall INTEGER
    }

-- {COLUMN} 1.3.6.1.4.1.248.32.18.2.70.1.3.1.1
hmSetupIpv6Tunnel6rdEntryPeerName OBJECT-TYPE
    SYNTAX     DisplayString (SIZE(0..16))
    MAX-ACCESS read-write
    STATUS     current
    DESCRIPTION
            "-- empty --"
    ::= { hmSetupIpv6Tunnel6rdEntry 1 }

-- {COLUMN} 1.3.6.1.4.1.248.32.18.2.70.1.3.1.2
hmSetupIpv6Tunnel6rdEntryRtgTag OBJECT-TYPE
    SYNTAX     Integer32 (0..65535)
    MAX-ACCESS read-write
    STATUS     current
    DESCRIPTION
            "-- empty --"
    ::= { hmSetupIpv6Tunnel6rdEntry 2 }

-- {COLUMN} 1.3.6.1.4.1.248.32.18.2.70.1.3.1.3
hmSetupIpv6Tunnel6rdEntryBorderRelayAddress OBJECT-TYPE
    SYNTAX     DisplayString (SIZE(0..64))
    MAX-ACCESS read-write
    STATUS     current
    DESCRIPTION
            "-- empty --"
    ::= { hmSetupIpv6Tunnel6rdEntry 3 }

-- {COLUMN} 1.3.6.1.4.1.248.32.18.2.70.1.3.1.4
hmSetupIpv6Tunnel6rdEntryIpv4RtgTag OBJECT-TYPE
    SYNTAX     Integer32 (0..65535)
    MAX-ACCESS read-write
    STATUS     current
    DESCRIPTION
            "-- empty --"
    ::= { hmSetupIpv6Tunnel6rdEntry 4 }

-- {COLUMN} 1.3.6.1.4.1.248.32.18.2.70.1.3.1.5
hmSetupIpv6Tunnel6rdEntry6rdPrefix OBJECT-TYPE
    SYNTAX     DisplayString (SIZE(0..24))
    MAX-ACCESS read-write
    STATUS     current
    DESCRIPTION
            "-- empty --"
    ::= { hmSetupIpv6Tunnel6rdEntry 5 }

-- {COLUMN} 1.3.6.1.4.1.248.32.18.2.70.1.3.1.6
hmSetupIpv6Tunnel6rdEntryIpv4MaskLength OBJECT-TYPE
    SYNTAX     Integer32 (0..65535)
    MAX-ACCESS read-write
    STATUS     current
    DESCRIPTION
            "-- empty --"
    ::= { hmSetupIpv6Tunnel6rdEntry 6 }

-- {COLUMN} 1.3.6.1.4.1.248.32.18.2.70.1.3.1.7
hmSetupIpv6Tunnel6rdEntryFirewall OBJECT-TYPE
    SYNTAX     INTEGER {
                  eYes (0),
                  eNo (1)
            }
    MAX-ACCESS read-write
    STATUS     current
    DESCRIPTION
            "-- empty --"
    ::= { hmSetupIpv6Tunnel6rdEntry 7 }

-- {TABLE} 1.3.6.1.4.1.248.32.18.2.70.1.4
hmSetupIpv6Tunnel6to4Table OBJECT-TYPE
    SYNTAX     SEQUENCE OF HmSetupIpv6Tunnel6to4Entry
    MAX-ACCESS not-accessible
    STATUS     current
    DESCRIPTION
            "-- empty --"
    ::= { hmSetupIpv6Tunnel 4 }

-- {ROW} 1.3.6.1.4.1.248.32.18.2.70.1.4.1
hmSetupIpv6Tunnel6to4Entry OBJECT-TYPE
    SYNTAX     HmSetupIpv6Tunnel6to4Entry
    MAX-ACCESS not-accessible
    STATUS     current
    DESCRIPTION
            ""
    INDEX {
            hmSetupIpv6Tunnel6to4EntryPeerName
          }
    ::= { hmSetupIpv6Tunnel6to4Table 1 }

HmSetupIpv6Tunnel6to4Entry ::= SEQUENCE {
            hmSetupIpv6Tunnel6to4EntryPeerName DisplayString,
            hmSetupIpv6Tunnel6to4EntryRtgTag Integer32,
            hmSetupIpv6Tunnel6to4EntryGatewayAddress DisplayString,
            hmSetupIpv6Tunnel6to4EntryIpv4RtgTag Integer32,
            hmSetupIpv6Tunnel6to4EntryFirewall INTEGER
    }

-- {COLUMN} 1.3.6.1.4.1.248.32.18.2.70.1.4.1.1
hmSetupIpv6Tunnel6to4EntryPeerName OBJECT-TYPE
    SYNTAX     DisplayString (SIZE(0..16))
    MAX-ACCESS read-write
    STATUS     current
    DESCRIPTION
            "-- empty --"
    ::= { hmSetupIpv6Tunnel6to4Entry 1 }

-- {COLUMN} 1.3.6.1.4.1.248.32.18.2.70.1.4.1.2
hmSetupIpv6Tunnel6to4EntryRtgTag OBJECT-TYPE
    SYNTAX     Integer32 (0..65535)
    MAX-ACCESS read-write
    STATUS     current
    DESCRIPTION
            "-- empty --"
    ::= { hmSetupIpv6Tunnel6to4Entry 2 }

-- {COLUMN} 1.3.6.1.4.1.248.32.18.2.70.1.4.1.3
hmSetupIpv6Tunnel6to4EntryGatewayAddress OBJECT-TYPE
    SYNTAX     DisplayString (SIZE(0..64))
    MAX-ACCESS read-write
    STATUS     current
    DESCRIPTION
            "-- empty --"
    ::= { hmSetupIpv6Tunnel6to4Entry 3 }

-- {COLUMN} 1.3.6.1.4.1.248.32.18.2.70.1.4.1.4
hmSetupIpv6Tunnel6to4EntryIpv4RtgTag OBJECT-TYPE
    SYNTAX     Integer32 (0..65535)
    MAX-ACCESS read-write
    STATUS     current
    DESCRIPTION
            "-- empty --"
    ::= { hmSetupIpv6Tunnel6to4Entry 4 }

-- {COLUMN} 1.3.6.1.4.1.248.32.18.2.70.1.4.1.5
hmSetupIpv6Tunnel6to4EntryFirewall OBJECT-TYPE
    SYNTAX     INTEGER {
                  eYes (0),
                  eNo (1)
            }
    MAX-ACCESS read-write
    STATUS     current
    DESCRIPTION
            "-- empty --"
    ::= { hmSetupIpv6Tunnel6to4Entry 5 }

-- {NODE} 1.3.6.1.4.1.248.32.18.2.70.2
hmSetupIpv6RouterAdv OBJECT IDENTIFIER ::= { hmSetupIpv6 2 }

-- {TABLE} 1.3.6.1.4.1.248.32.18.2.70.2.1
hmSetupIpv6RouterAdvPrefixOptionsTable OBJECT-TYPE
    SYNTAX     SEQUENCE OF HmSetupIpv6RouterAdvPrefixOptionsEntry
    MAX-ACCESS not-accessible
    STATUS     current
    DESCRIPTION
            "-- empty --"
    ::= { hmSetupIpv6RouterAdv 1 }

-- {ROW} 1.3.6.1.4.1.248.32.18.2.70.2.1.1
hmSetupIpv6RouterAdvPrefixOptionsEntry OBJECT-TYPE
    SYNTAX     HmSetupIpv6RouterAdvPrefixOptionsEntry
    MAX-ACCESS not-accessible
    STATUS     current
    DESCRIPTION
            ""
    INDEX {
            hmSetupIpv6RouterAdvPrefixOptionsEntryInterfaceName,
            hmSetupIpv6RouterAdvPrefixOptionsEntryPrefix
          }
    ::= { hmSetupIpv6RouterAdvPrefixOptionsTable 1 }

HmSetupIpv6RouterAdvPrefixOptionsEntry ::= SEQUENCE {
            hmSetupIpv6RouterAdvPrefixOptionsEntryInterfaceName DisplayString,
            hmSetupIpv6RouterAdvPrefixOptionsEntryPrefix DisplayString,
            hmSetupIpv6RouterAdvPrefixOptionsEntrySubnetId DisplayString,
            hmSetupIpv6RouterAdvPrefixOptionsEntryAdvOnlink INTEGER,
            hmSetupIpv6RouterAdvPrefixOptionsEntryAdvAutonomous INTEGER,
            hmSetupIpv6RouterAdvPrefixOptionsEntryPdSource DisplayString,
            hmSetupIpv6RouterAdvPrefixOptionsEntryAdvPrefLifetime Integer32,
            hmSetupIpv6RouterAdvPrefixOptionsEntryAdvValidLifetime Integer32,
            hmSetupIpv6RouterAdvPrefixOptionsEntryDecrementlifetimes INTEGER
    }

-- {COLUMN} 1.3.6.1.4.1.248.32.18.2.70.2.1.1.1
hmSetupIpv6RouterAdvPrefixOptionsEntryInterfaceName OBJECT-TYPE
    SYNTAX     DisplayString (SIZE(0..16))
    MAX-ACCESS read-write
    STATUS     current
    DESCRIPTION
            "-- empty --"
    ::= { hmSetupIpv6RouterAdvPrefixOptionsEntry 1 }

-- {COLUMN} 1.3.6.1.4.1.248.32.18.2.70.2.1.1.2
hmSetupIpv6RouterAdvPrefixOptionsEntryPrefix OBJECT-TYPE
    SYNTAX     DisplayString (SIZE(0..43))
    MAX-ACCESS read-write
    STATUS     current
    DESCRIPTION
            "-- empty --"
    ::= { hmSetupIpv6RouterAdvPrefixOptionsEntry 2 }

-- {COLUMN} 1.3.6.1.4.1.248.32.18.2.70.2.1.1.3
hmSetupIpv6RouterAdvPrefixOptionsEntrySubnetId OBJECT-TYPE
    SYNTAX     DisplayString (SIZE(0..19))
    MAX-ACCESS read-write
    STATUS     current
    DESCRIPTION
            "-- empty --"
    ::= { hmSetupIpv6RouterAdvPrefixOptionsEntry 3 }

-- {COLUMN} 1.3.6.1.4.1.248.32.18.2.70.2.1.1.4
hmSetupIpv6RouterAdvPrefixOptionsEntryAdvOnlink OBJECT-TYPE
    SYNTAX     INTEGER {
                  eYes (0),
                  eNo (1)
            }
    MAX-ACCESS read-write
    STATUS     current
    DESCRIPTION
            "-- empty --"
    ::= { hmSetupIpv6RouterAdvPrefixOptionsEntry 4 }

-- {COLUMN} 1.3.6.1.4.1.248.32.18.2.70.2.1.1.5
hmSetupIpv6RouterAdvPrefixOptionsEntryAdvAutonomous OBJECT-TYPE
    SYNTAX     INTEGER {
                  eYes (0),
                  eNo (1)
            }
    MAX-ACCESS read-write
    STATUS     current
    DESCRIPTION
            "-- empty --"
    ::= { hmSetupIpv6RouterAdvPrefixOptionsEntry 5 }

-- {COLUMN} 1.3.6.1.4.1.248.32.18.2.70.2.1.1.6
hmSetupIpv6RouterAdvPrefixOptionsEntryPdSource OBJECT-TYPE
    SYNTAX     DisplayString (SIZE(0..16))
    MAX-ACCESS read-write
    STATUS     current
    DESCRIPTION
            "-- empty --"
    ::= { hmSetupIpv6RouterAdvPrefixOptionsEntry 6 }

-- {COLUMN} 1.3.6.1.4.1.248.32.18.2.70.2.1.1.7
hmSetupIpv6RouterAdvPrefixOptionsEntryAdvPrefLifetime OBJECT-TYPE
    SYNTAX     Integer32 (0..2147483647)
    MAX-ACCESS read-write
    STATUS     current
    DESCRIPTION
            "-- empty --"
    ::= { hmSetupIpv6RouterAdvPrefixOptionsEntry 7 }

-- {COLUMN} 1.3.6.1.4.1.248.32.18.2.70.2.1.1.8
hmSetupIpv6RouterAdvPrefixOptionsEntryAdvValidLifetime OBJECT-TYPE
    SYNTAX     Integer32 (0..2147483647)
    MAX-ACCESS read-write
    STATUS     current
    DESCRIPTION
            "-- empty --"
    ::= { hmSetupIpv6RouterAdvPrefixOptionsEntry 8 }

-- {COLUMN} 1.3.6.1.4.1.248.32.18.2.70.2.1.1.9
hmSetupIpv6RouterAdvPrefixOptionsEntryDecrementlifetimes OBJECT-TYPE
    SYNTAX     INTEGER {
                  eYes (0),
                  eNo (1)
            }
    MAX-ACCESS read-write
    STATUS     current
    DESCRIPTION
            "-- empty --"
    ::= { hmSetupIpv6RouterAdvPrefixOptionsEntry 9 }

-- {TABLE} 1.3.6.1.4.1.248.32.18.2.70.2.2
hmSetupIpv6RouterAdvInterfaceOptionsTable OBJECT-TYPE
    SYNTAX     SEQUENCE OF HmSetupIpv6RouterAdvInterfaceOptionsEntry
    MAX-ACCESS not-accessible
    STATUS     current
    DESCRIPTION
            "-- empty --"
    ::= { hmSetupIpv6RouterAdv 2 }

-- {ROW} 1.3.6.1.4.1.248.32.18.2.70.2.2.1
hmSetupIpv6RouterAdvInterfaceOptionsEntry OBJECT-TYPE
    SYNTAX     HmSetupIpv6RouterAdvInterfaceOptionsEntry
    MAX-ACCESS not-accessible
    STATUS     current
    DESCRIPTION
            ""
    INDEX {
            hmSetupIpv6RouterAdvInterfaceOptionsEntryInterfaceName
          }
    ::= { hmSetupIpv6RouterAdvInterfaceOptionsTable 1 }

HmSetupIpv6RouterAdvInterfaceOptionsEntry ::= SEQUENCE {
            hmSetupIpv6RouterAdvInterfaceOptionsEntryInterfaceName DisplayString,
            hmSetupIpv6RouterAdvInterfaceOptionsEntrySendAdverts INTEGER,
            hmSetupIpv6RouterAdvInterfaceOptionsEntryMinRtrInterval Integer32,
            hmSetupIpv6RouterAdvInterfaceOptionsEntryMaxRtrInterval Integer32,
            hmSetupIpv6RouterAdvInterfaceOptionsEntryManagedFlag INTEGER,
            hmSetupIpv6RouterAdvInterfaceOptionsEntryOtherConfigFlag INTEGER,
            hmSetupIpv6RouterAdvInterfaceOptionsEntryLinkMtu Integer32,
            hmSetupIpv6RouterAdvInterfaceOptionsEntryReachableTime Integer32,
            hmSetupIpv6RouterAdvInterfaceOptionsEntryCrtHopLimit Integer32,
            hmSetupIpv6RouterAdvInterfaceOptionsEntryDefaultLifetime Integer32,
            hmSetupIpv6RouterAdvInterfaceOptionsEntryDefaultRouterMode INTEGER,
            hmSetupIpv6RouterAdvInterfaceOptionsEntryRouterPreference INTEGER,
            hmSetupIpv6RouterAdvInterfaceOptionsEntryRtrTime Integer32
    }

-- {COLUMN} 1.3.6.1.4.1.248.32.18.2.70.2.2.1.1
hmSetupIpv6RouterAdvInterfaceOptionsEntryInterfaceName OBJECT-TYPE
    SYNTAX     DisplayString (SIZE(0..16))
    MAX-ACCESS read-write
    STATUS     current
    DESCRIPTION
            "-- empty --"
    ::= { hmSetupIpv6RouterAdvInterfaceOptionsEntry 1 }

-- {COLUMN} 1.3.6.1.4.1.248.32.18.2.70.2.2.1.2
hmSetupIpv6RouterAdvInterfaceOptionsEntrySendAdverts OBJECT-TYPE
    SYNTAX     INTEGER {
                  eYes (0),
                  eNo (1)
            }
    MAX-ACCESS read-write
    STATUS     current
    DESCRIPTION
            "-- empty --"
    ::= { hmSetupIpv6RouterAdvInterfaceOptionsEntry 2 }

-- {COLUMN} 1.3.6.1.4.1.248.32.18.2.70.2.2.1.3
hmSetupIpv6RouterAdvInterfaceOptionsEntryMinRtrInterval OBJECT-TYPE
    SYNTAX     Integer32 (0..2147483647)
    MAX-ACCESS read-write
    STATUS     current
    DESCRIPTION
            "-- empty --"
    ::= { hmSetupIpv6RouterAdvInterfaceOptionsEntry 3 }

-- {COLUMN} 1.3.6.1.4.1.248.32.18.2.70.2.2.1.4
hmSetupIpv6RouterAdvInterfaceOptionsEntryMaxRtrInterval OBJECT-TYPE
    SYNTAX     Integer32 (0..2147483647)
    MAX-ACCESS read-write
    STATUS     current
    DESCRIPTION
            "-- empty --"
    ::= { hmSetupIpv6RouterAdvInterfaceOptionsEntry 4 }

-- {COLUMN} 1.3.6.1.4.1.248.32.18.2.70.2.2.1.5
hmSetupIpv6RouterAdvInterfaceOptionsEntryManagedFlag OBJECT-TYPE
    SYNTAX     INTEGER {
                  eYes (0),
                  eNo (1)
            }
    MAX-ACCESS read-write
    STATUS     current
    DESCRIPTION
            "-- empty --"
    ::= { hmSetupIpv6RouterAdvInterfaceOptionsEntry 5 }

-- {COLUMN} 1.3.6.1.4.1.248.32.18.2.70.2.2.1.6
hmSetupIpv6RouterAdvInterfaceOptionsEntryOtherConfigFlag OBJECT-TYPE
    SYNTAX     INTEGER {
                  eYes (0),
                  eNo (1)
            }
    MAX-ACCESS read-write
    STATUS     current
    DESCRIPTION
            "-- empty --"
    ::= { hmSetupIpv6RouterAdvInterfaceOptionsEntry 6 }

-- {COLUMN} 1.3.6.1.4.1.248.32.18.2.70.2.2.1.7
hmSetupIpv6RouterAdvInterfaceOptionsEntryLinkMtu OBJECT-TYPE
    SYNTAX     Integer32 (0..2147483647)
    MAX-ACCESS read-write
    STATUS     current
    DESCRIPTION
            "-- empty --"
    ::= { hmSetupIpv6RouterAdvInterfaceOptionsEntry 7 }

-- {COLUMN} 1.3.6.1.4.1.248.32.18.2.70.2.2.1.8
hmSetupIpv6RouterAdvInterfaceOptionsEntryReachableTime OBJECT-TYPE
    SYNTAX     Integer32 (0..2147483647)
    MAX-ACCESS read-write
    STATUS     current
    DESCRIPTION
            "-- empty --"
    ::= { hmSetupIpv6RouterAdvInterfaceOptionsEntry 8 }

-- {COLUMN} 1.3.6.1.4.1.248.32.18.2.70.2.2.1.10
hmSetupIpv6RouterAdvInterfaceOptionsEntryCrtHopLimit OBJECT-TYPE
    SYNTAX     Integer32 (0..2147483647)
    MAX-ACCESS read-write
    STATUS     current
    DESCRIPTION
            "-- empty --"
    ::= { hmSetupIpv6RouterAdvInterfaceOptionsEntry 10 }

-- {COLUMN} 1.3.6.1.4.1.248.32.18.2.70.2.2.1.11
hmSetupIpv6RouterAdvInterfaceOptionsEntryDefaultLifetime OBJECT-TYPE
    SYNTAX     Integer32 (0..2147483647)
    MAX-ACCESS read-write
    STATUS     current
    DESCRIPTION
            "-- empty --"
    ::= { hmSetupIpv6RouterAdvInterfaceOptionsEntry 11 }

-- {COLUMN} 1.3.6.1.4.1.248.32.18.2.70.2.2.1.12
hmSetupIpv6RouterAdvInterfaceOptionsEntryDefaultRouterMode OBJECT-TYPE
    SYNTAX     INTEGER {
                  eAuto (0),
                  eAlways (1),
                  eNever (2)
            }
    MAX-ACCESS read-write
    STATUS     current
    DESCRIPTION
            "-- empty --"
    ::= { hmSetupIpv6RouterAdvInterfaceOptionsEntry 12 }

-- {COLUMN} 1.3.6.1.4.1.248.32.18.2.70.2.2.1.13
hmSetupIpv6RouterAdvInterfaceOptionsEntryRouterPreference OBJECT-TYPE
    SYNTAX     INTEGER {
                  eMedium (0),
                  eHigh (1),
                  eLow (2)
            }
    MAX-ACCESS read-write
    STATUS     current
    DESCRIPTION
            "-- empty --"
    ::= { hmSetupIpv6RouterAdvInterfaceOptionsEntry 13 }

-- {COLUMN} 1.3.6.1.4.1.248.32.18.2.70.2.2.1.14
hmSetupIpv6RouterAdvInterfaceOptionsEntryRtrTime OBJECT-TYPE
    SYNTAX     Integer32 (0..2147483647)
    MAX-ACCESS read-write
    STATUS     current
    DESCRIPTION
            "-- empty --"
    ::= { hmSetupIpv6RouterAdvInterfaceOptionsEntry 14 }

-- {TABLE} 1.3.6.1.4.1.248.32.18.2.70.2.3
hmSetupIpv6RouterAdvRouteOptionsTable OBJECT-TYPE
    SYNTAX     SEQUENCE OF HmSetupIpv6RouterAdvRouteOptionsEntry
    MAX-ACCESS not-accessible
    STATUS     current
    DESCRIPTION
            "-- empty --"
    ::= { hmSetupIpv6RouterAdv 3 }

-- {ROW} 1.3.6.1.4.1.248.32.18.2.70.2.3.1
hmSetupIpv6RouterAdvRouteOptionsEntry OBJECT-TYPE
    SYNTAX     HmSetupIpv6RouterAdvRouteOptionsEntry
    MAX-ACCESS not-accessible
    STATUS     current
    DESCRIPTION
            ""
    INDEX {
            hmSetupIpv6RouterAdvRouteOptionsEntryInterfaceName,
            hmSetupIpv6RouterAdvRouteOptionsEntryPrefix
          }
    ::= { hmSetupIpv6RouterAdvRouteOptionsTable 1 }

HmSetupIpv6RouterAdvRouteOptionsEntry ::= SEQUENCE {
            hmSetupIpv6RouterAdvRouteOptionsEntryInterfaceName DisplayString,
            hmSetupIpv6RouterAdvRouteOptionsEntryPrefix DisplayString,
            hmSetupIpv6RouterAdvRouteOptionsEntryRouteLifetime Integer32,
            hmSetupIpv6RouterAdvRouteOptionsEntryRoutePreference INTEGER
    }

-- {COLUMN} 1.3.6.1.4.1.248.32.18.2.70.2.3.1.1
hmSetupIpv6RouterAdvRouteOptionsEntryInterfaceName OBJECT-TYPE
    SYNTAX     DisplayString (SIZE(0..16))
    MAX-ACCESS read-write
    STATUS     current
    DESCRIPTION
            "-- empty --"
    ::= { hmSetupIpv6RouterAdvRouteOptionsEntry 1 }

-- {COLUMN} 1.3.6.1.4.1.248.32.18.2.70.2.3.1.2
hmSetupIpv6RouterAdvRouteOptionsEntryPrefix OBJECT-TYPE
    SYNTAX     DisplayString (SIZE(0..43))
    MAX-ACCESS read-write
    STATUS     current
    DESCRIPTION
            "-- empty --"
    ::= { hmSetupIpv6RouterAdvRouteOptionsEntry 2 }

-- {COLUMN} 1.3.6.1.4.1.248.32.18.2.70.2.3.1.3
hmSetupIpv6RouterAdvRouteOptionsEntryRouteLifetime OBJECT-TYPE
    SYNTAX     Integer32 (0..2147483647)
    MAX-ACCESS read-write
    STATUS     current
    DESCRIPTION
            "-- empty --"
    ::= { hmSetupIpv6RouterAdvRouteOptionsEntry 3 }

-- {COLUMN} 1.3.6.1.4.1.248.32.18.2.70.2.3.1.4
hmSetupIpv6RouterAdvRouteOptionsEntryRoutePreference OBJECT-TYPE
    SYNTAX     INTEGER {
                  eMedium (0),
                  eHigh (1),
                  eLow (2)
            }
    MAX-ACCESS read-write
    STATUS     current
    DESCRIPTION
            "-- empty --"
    ::= { hmSetupIpv6RouterAdvRouteOptionsEntry 4 }

-- {TABLE} 1.3.6.1.4.1.248.32.18.2.70.2.5
hmSetupIpv6RouterAdvRdnssOptionsTable OBJECT-TYPE
    SYNTAX     SEQUENCE OF HmSetupIpv6RouterAdvRdnssOptionsEntry
    MAX-ACCESS not-accessible
    STATUS     current
    DESCRIPTION
            "-- empty --"
    ::= { hmSetupIpv6RouterAdv 5 }

-- {ROW} 1.3.6.1.4.1.248.32.18.2.70.2.5.1
hmSetupIpv6RouterAdvRdnssOptionsEntry OBJECT-TYPE
    SYNTAX     HmSetupIpv6RouterAdvRdnssOptionsEntry
    MAX-ACCESS not-accessible
    STATUS     current
    DESCRIPTION
            ""
    INDEX {
            hmSetupIpv6RouterAdvRdnssOptionsEntryInterfaceName
          }
    ::= { hmSetupIpv6RouterAdvRdnssOptionsTable 1 }

HmSetupIpv6RouterAdvRdnssOptionsEntry ::= SEQUENCE {
            hmSetupIpv6RouterAdvRdnssOptionsEntryInterfaceName DisplayString,
            hmSetupIpv6RouterAdvRdnssOptionsEntryPrimaryDns DisplayString,
            hmSetupIpv6RouterAdvRdnssOptionsEntrySecondaryDns DisplayString,
            hmSetupIpv6RouterAdvRdnssOptionsEntryDnsSearchList BITS,
            hmSetupIpv6RouterAdvRdnssOptionsEntryLifetime Integer32
    }

-- {COLUMN} 1.3.6.1.4.1.248.32.18.2.70.2.5.1.1
hmSetupIpv6RouterAdvRdnssOptionsEntryInterfaceName OBJECT-TYPE
    SYNTAX     DisplayString (SIZE(0..16))
    MAX-ACCESS read-write
    STATUS     current
    DESCRIPTION
            "-- empty --"
    ::= { hmSetupIpv6RouterAdvRdnssOptionsEntry 1 }

-- {COLUMN} 1.3.6.1.4.1.248.32.18.2.70.2.5.1.2
hmSetupIpv6RouterAdvRdnssOptionsEntryPrimaryDns OBJECT-TYPE
    SYNTAX     DisplayString (SIZE(0..39))
    MAX-ACCESS read-write
    STATUS     current
    DESCRIPTION
            "-- empty --"
    ::= { hmSetupIpv6RouterAdvRdnssOptionsEntry 2 }

-- {COLUMN} 1.3.6.1.4.1.248.32.18.2.70.2.5.1.3
hmSetupIpv6RouterAdvRdnssOptionsEntrySecondaryDns OBJECT-TYPE
    SYNTAX     DisplayString (SIZE(0..39))
    MAX-ACCESS read-write
    STATUS     current
    DESCRIPTION
            "-- empty --"
    ::= { hmSetupIpv6RouterAdvRdnssOptionsEntry 3 }

-- {COLUMN} 1.3.6.1.4.1.248.32.18.2.70.2.5.1.4
hmSetupIpv6RouterAdvRdnssOptionsEntryDnsSearchList OBJECT-TYPE
    SYNTAX     BITS {
                  eNone (0),
                  eWan (6),
                  eInternal (7)
            }
    MAX-ACCESS read-write
    STATUS     current
    DESCRIPTION
            "-- empty --"
    ::= { hmSetupIpv6RouterAdvRdnssOptionsEntry 4 }

-- {COLUMN} 1.3.6.1.4.1.248.32.18.2.70.2.5.1.5
hmSetupIpv6RouterAdvRdnssOptionsEntryLifetime OBJECT-TYPE
    SYNTAX     Integer32 (0..2147483647)
    MAX-ACCESS read-write
    STATUS     current
    DESCRIPTION
            "-- empty --"
    ::= { hmSetupIpv6RouterAdvRdnssOptionsEntry 5 }

-- {TABLE} 1.3.6.1.4.1.248.32.18.2.70.2.6
hmSetupIpv6RouterAdvPrefixPoolsTable OBJECT-TYPE
    SYNTAX     SEQUENCE OF HmSetupIpv6RouterAdvPrefixPoolsEntry
    MAX-ACCESS not-accessible
    STATUS     current
    DESCRIPTION
            "-- empty --"
    ::= { hmSetupIpv6RouterAdv 6 }

-- {ROW} 1.3.6.1.4.1.248.32.18.2.70.2.6.1
hmSetupIpv6RouterAdvPrefixPoolsEntry OBJECT-TYPE
    SYNTAX     HmSetupIpv6RouterAdvPrefixPoolsEntry
    MAX-ACCESS not-accessible
    STATUS     current
    DESCRIPTION
            ""
    INDEX {
            hmSetupIpv6RouterAdvPrefixPoolsEntryInterfaceName,
            hmSetupIpv6RouterAdvPrefixPoolsEntryStartPrefixPool
          }
    ::= { hmSetupIpv6RouterAdvPrefixPoolsTable 1 }

HmSetupIpv6RouterAdvPrefixPoolsEntry ::= SEQUENCE {
            hmSetupIpv6RouterAdvPrefixPoolsEntryInterfaceName DisplayString,
            hmSetupIpv6RouterAdvPrefixPoolsEntryStartPrefixPool DisplayString,
            hmSetupIpv6RouterAdvPrefixPoolsEntryEndPrefixPool DisplayString,
            hmSetupIpv6RouterAdvPrefixPoolsEntryPrefixLength Integer32,
            hmSetupIpv6RouterAdvPrefixPoolsEntryAdvOnlink INTEGER,
            hmSetupIpv6RouterAdvPrefixPoolsEntryAdvAutonomous INTEGER,
            hmSetupIpv6RouterAdvPrefixPoolsEntryAdvPrefLifetime Integer32,
            hmSetupIpv6RouterAdvPrefixPoolsEntryAdvValidLifetime Integer32
    }

-- {COLUMN} 1.3.6.1.4.1.248.32.18.2.70.2.6.1.1
hmSetupIpv6RouterAdvPrefixPoolsEntryInterfaceName OBJECT-TYPE
    SYNTAX     DisplayString (SIZE(0..16))
    MAX-ACCESS read-write
    STATUS     current
    DESCRIPTION
            "-- empty --"
    ::= { hmSetupIpv6RouterAdvPrefixPoolsEntry 1 }

-- {COLUMN} 1.3.6.1.4.1.248.32.18.2.70.2.6.1.2
hmSetupIpv6RouterAdvPrefixPoolsEntryStartPrefixPool OBJECT-TYPE
    SYNTAX     DisplayString (SIZE(0..43))
    MAX-ACCESS read-write
    STATUS     current
    DESCRIPTION
            "-- empty --"
    ::= { hmSetupIpv6RouterAdvPrefixPoolsEntry 2 }

-- {COLUMN} 1.3.6.1.4.1.248.32.18.2.70.2.6.1.3
hmSetupIpv6RouterAdvPrefixPoolsEntryEndPrefixPool OBJECT-TYPE
    SYNTAX     DisplayString (SIZE(0..43))
    MAX-ACCESS read-write
    STATUS     current
    DESCRIPTION
            "-- empty --"
    ::= { hmSetupIpv6RouterAdvPrefixPoolsEntry 3 }

-- {COLUMN} 1.3.6.1.4.1.248.32.18.2.70.2.6.1.4
hmSetupIpv6RouterAdvPrefixPoolsEntryPrefixLength OBJECT-TYPE
    SYNTAX     Integer32 (0..255)
    MAX-ACCESS read-write
    STATUS     current
    DESCRIPTION
            "-- empty --"
    ::= { hmSetupIpv6RouterAdvPrefixPoolsEntry 4 }

-- {COLUMN} 1.3.6.1.4.1.248.32.18.2.70.2.6.1.5
hmSetupIpv6RouterAdvPrefixPoolsEntryAdvOnlink OBJECT-TYPE
    SYNTAX     INTEGER {
                  eYes (0),
                  eNo (1)
            }
    MAX-ACCESS read-write
    STATUS     current
    DESCRIPTION
            "-- empty --"
    ::= { hmSetupIpv6RouterAdvPrefixPoolsEntry 5 }

-- {COLUMN} 1.3.6.1.4.1.248.32.18.2.70.2.6.1.6
hmSetupIpv6RouterAdvPrefixPoolsEntryAdvAutonomous OBJECT-TYPE
    SYNTAX     INTEGER {
                  eYes (0),
                  eNo (1)
            }
    MAX-ACCESS read-write
    STATUS     current
    DESCRIPTION
            "-- empty --"
    ::= { hmSetupIpv6RouterAdvPrefixPoolsEntry 6 }

-- {COLUMN} 1.3.6.1.4.1.248.32.18.2.70.2.6.1.7
hmSetupIpv6RouterAdvPrefixPoolsEntryAdvPrefLifetime OBJECT-TYPE
    SYNTAX     Integer32 (0..2147483647)
    MAX-ACCESS read-write
    STATUS     current
    DESCRIPTION
            "-- empty --"
    ::= { hmSetupIpv6RouterAdvPrefixPoolsEntry 7 }

-- {COLUMN} 1.3.6.1.4.1.248.32.18.2.70.2.6.1.8
hmSetupIpv6RouterAdvPrefixPoolsEntryAdvValidLifetime OBJECT-TYPE
    SYNTAX     Integer32 (0..2147483647)
    MAX-ACCESS read-write
    STATUS     current
    DESCRIPTION
            "-- empty --"
    ::= { hmSetupIpv6RouterAdvPrefixPoolsEntry 8 }

-- {NODE} 1.3.6.1.4.1.248.32.18.2.70.3
hmSetupIpv6Dhcpv6 OBJECT IDENTIFIER ::= { hmSetupIpv6 3 }

-- {NODE} 1.3.6.1.4.1.248.32.18.2.70.3.1
hmSetupIpv6Dhcpv6Server OBJECT IDENTIFIER ::= { hmSetupIpv6Dhcpv6 1 }

-- {TABLE} 1.3.6.1.4.1.248.32.18.2.70.3.1.2
hmSetupIpv6Dhcpv6ServerAddressPoolsTable OBJECT-TYPE
    SYNTAX     SEQUENCE OF HmSetupIpv6Dhcpv6ServerAddressPoolsEntry
    MAX-ACCESS not-accessible
    STATUS     current
    DESCRIPTION
            "-- empty --"
    ::= { hmSetupIpv6Dhcpv6Server 2 }

-- {ROW} 1.3.6.1.4.1.248.32.18.2.70.3.1.2.1
hmSetupIpv6Dhcpv6ServerAddressPoolsEntry OBJECT-TYPE
    SYNTAX     HmSetupIpv6Dhcpv6ServerAddressPoolsEntry
    MAX-ACCESS not-accessible
    STATUS     current
    DESCRIPTION
            ""
    INDEX {
            hmSetupIpv6Dhcpv6ServerAddressPoolsEntryAddressPoolName,
            hmSetupIpv6Dhcpv6ServerAddressPoolsEntryStartAddressPool,
            hmSetupIpv6Dhcpv6ServerAddressPoolsEntryPdSource
          }
    ::= { hmSetupIpv6Dhcpv6ServerAddressPoolsTable 1 }

HmSetupIpv6Dhcpv6ServerAddressPoolsEntry ::= SEQUENCE {
            hmSetupIpv6Dhcpv6ServerAddressPoolsEntryAddressPoolName DisplayString,
            hmSetupIpv6Dhcpv6ServerAddressPoolsEntryStartAddressPool DisplayString,
            hmSetupIpv6Dhcpv6ServerAddressPoolsEntryEndAddressPool DisplayString,
            hmSetupIpv6Dhcpv6ServerAddressPoolsEntryPrefLifetime Integer32,
            hmSetupIpv6Dhcpv6ServerAddressPoolsEntryValidLifetime Integer32,
            hmSetupIpv6Dhcpv6ServerAddressPoolsEntryPdSource DisplayString
    }

-- {COLUMN} 1.3.6.1.4.1.248.32.18.2.70.3.1.2.1.1
hmSetupIpv6Dhcpv6ServerAddressPoolsEntryAddressPoolName OBJECT-TYPE
    SYNTAX     DisplayString (SIZE(0..31))
    MAX-ACCESS read-write
    STATUS     current
    DESCRIPTION
            "-- empty --"
    ::= { hmSetupIpv6Dhcpv6ServerAddressPoolsEntry 1 }

-- {COLUMN} 1.3.6.1.4.1.248.32.18.2.70.3.1.2.1.2
hmSetupIpv6Dhcpv6ServerAddressPoolsEntryStartAddressPool OBJECT-TYPE
    SYNTAX     DisplayString (SIZE(0..39))
    MAX-ACCESS read-write
    STATUS     current
    DESCRIPTION
            "-- empty --"
    ::= { hmSetupIpv6Dhcpv6ServerAddressPoolsEntry 2 }

-- {COLUMN} 1.3.6.1.4.1.248.32.18.2.70.3.1.2.1.3
hmSetupIpv6Dhcpv6ServerAddressPoolsEntryEndAddressPool OBJECT-TYPE
    SYNTAX     DisplayString (SIZE(0..39))
    MAX-ACCESS read-write
    STATUS     current
    DESCRIPTION
            "-- empty --"
    ::= { hmSetupIpv6Dhcpv6ServerAddressPoolsEntry 3 }

-- {COLUMN} 1.3.6.1.4.1.248.32.18.2.70.3.1.2.1.5
hmSetupIpv6Dhcpv6ServerAddressPoolsEntryPrefLifetime OBJECT-TYPE
    SYNTAX     Integer32 (0..2147483647)
    MAX-ACCESS read-write
    STATUS     current
    DESCRIPTION
            "-- empty --"
    ::= { hmSetupIpv6Dhcpv6ServerAddressPoolsEntry 5 }

-- {COLUMN} 1.3.6.1.4.1.248.32.18.2.70.3.1.2.1.6
hmSetupIpv6Dhcpv6ServerAddressPoolsEntryValidLifetime OBJECT-TYPE
    SYNTAX     Integer32 (0..2147483647)
    MAX-ACCESS read-write
    STATUS     current
    DESCRIPTION
            "-- empty --"
    ::= { hmSetupIpv6Dhcpv6ServerAddressPoolsEntry 6 }

-- {COLUMN} 1.3.6.1.4.1.248.32.18.2.70.3.1.2.1.7
hmSetupIpv6Dhcpv6ServerAddressPoolsEntryPdSource OBJECT-TYPE
    SYNTAX     DisplayString (SIZE(0..16))
    MAX-ACCESS read-write
    STATUS     current
    DESCRIPTION
            "-- empty --"
    ::= { hmSetupIpv6Dhcpv6ServerAddressPoolsEntry 7 }

-- {TABLE} 1.3.6.1.4.1.248.32.18.2.70.3.1.3
hmSetupIpv6Dhcpv6ServerPdPoolsTable OBJECT-TYPE
    SYNTAX     SEQUENCE OF HmSetupIpv6Dhcpv6ServerPdPoolsEntry
    MAX-ACCESS not-accessible
    STATUS     current
    DESCRIPTION
            "-- empty --"
    ::= { hmSetupIpv6Dhcpv6Server 3 }

-- {ROW} 1.3.6.1.4.1.248.32.18.2.70.3.1.3.1
hmSetupIpv6Dhcpv6ServerPdPoolsEntry OBJECT-TYPE
    SYNTAX     HmSetupIpv6Dhcpv6ServerPdPoolsEntry
    MAX-ACCESS not-accessible
    STATUS     current
    DESCRIPTION
            ""
    INDEX {
            hmSetupIpv6Dhcpv6ServerPdPoolsEntryPdPoolName,
            hmSetupIpv6Dhcpv6ServerPdPoolsEntryStartPdPool,
            hmSetupIpv6Dhcpv6ServerPdPoolsEntryPdSource
          }
    ::= { hmSetupIpv6Dhcpv6ServerPdPoolsTable 1 }

HmSetupIpv6Dhcpv6ServerPdPoolsEntry ::= SEQUENCE {
            hmSetupIpv6Dhcpv6ServerPdPoolsEntryPdPoolName DisplayString,
            hmSetupIpv6Dhcpv6ServerPdPoolsEntryStartPdPool DisplayString,
            hmSetupIpv6Dhcpv6ServerPdPoolsEntryEndPdPool DisplayString,
            hmSetupIpv6Dhcpv6ServerPdPoolsEntryPrefixLength Integer32,
            hmSetupIpv6Dhcpv6ServerPdPoolsEntryPrefLifetime Integer32,
            hmSetupIpv6Dhcpv6ServerPdPoolsEntryValidLifetime Integer32,
            hmSetupIpv6Dhcpv6ServerPdPoolsEntryPdSource DisplayString
    }

-- {COLUMN} 1.3.6.1.4.1.248.32.18.2.70.3.1.3.1.1
hmSetupIpv6Dhcpv6ServerPdPoolsEntryPdPoolName OBJECT-TYPE
    SYNTAX     DisplayString (SIZE(0..31))
    MAX-ACCESS read-write
    STATUS     current
    DESCRIPTION
            "-- empty --"
    ::= { hmSetupIpv6Dhcpv6ServerPdPoolsEntry 1 }

-- {COLUMN} 1.3.6.1.4.1.248.32.18.2.70.3.1.3.1.2
hmSetupIpv6Dhcpv6ServerPdPoolsEntryStartPdPool OBJECT-TYPE
    SYNTAX     DisplayString (SIZE(0..39))
    MAX-ACCESS read-write
    STATUS     current
    DESCRIPTION
            "-- empty --"
    ::= { hmSetupIpv6Dhcpv6ServerPdPoolsEntry 2 }

-- {COLUMN} 1.3.6.1.4.1.248.32.18.2.70.3.1.3.1.3
hmSetupIpv6Dhcpv6ServerPdPoolsEntryEndPdPool OBJECT-TYPE
    SYNTAX     DisplayString (SIZE(0..39))
    MAX-ACCESS read-write
    STATUS     current
    DESCRIPTION
            "-- empty --"
    ::= { hmSetupIpv6Dhcpv6ServerPdPoolsEntry 3 }

-- {COLUMN} 1.3.6.1.4.1.248.32.18.2.70.3.1.3.1.4
hmSetupIpv6Dhcpv6ServerPdPoolsEntryPrefixLength OBJECT-TYPE
    SYNTAX     Integer32 (0..255)
    MAX-ACCESS read-write
    STATUS     current
    DESCRIPTION
            "-- empty --"
    ::= { hmSetupIpv6Dhcpv6ServerPdPoolsEntry 4 }

-- {COLUMN} 1.3.6.1.4.1.248.32.18.2.70.3.1.3.1.5
hmSetupIpv6Dhcpv6ServerPdPoolsEntryPrefLifetime OBJECT-TYPE
    SYNTAX     Integer32 (0..2147483647)
    MAX-ACCESS read-write
    STATUS     current
    DESCRIPTION
            "-- empty --"
    ::= { hmSetupIpv6Dhcpv6ServerPdPoolsEntry 5 }

-- {COLUMN} 1.3.6.1.4.1.248.32.18.2.70.3.1.3.1.6
hmSetupIpv6Dhcpv6ServerPdPoolsEntryValidLifetime OBJECT-TYPE
    SYNTAX     Integer32 (0..2147483647)
    MAX-ACCESS read-write
    STATUS     current
    DESCRIPTION
            "-- empty --"
    ::= { hmSetupIpv6Dhcpv6ServerPdPoolsEntry 6 }

-- {COLUMN} 1.3.6.1.4.1.248.32.18.2.70.3.1.3.1.7
hmSetupIpv6Dhcpv6ServerPdPoolsEntryPdSource OBJECT-TYPE
    SYNTAX     DisplayString (SIZE(0..16))
    MAX-ACCESS read-write
    STATUS     current
    DESCRIPTION
            "-- empty --"
    ::= { hmSetupIpv6Dhcpv6ServerPdPoolsEntry 7 }

-- {TABLE} 1.3.6.1.4.1.248.32.18.2.70.3.1.4
hmSetupIpv6Dhcpv6ServerIfcListTable OBJECT-TYPE
    SYNTAX     SEQUENCE OF HmSetupIpv6Dhcpv6ServerIfcListEntry
    MAX-ACCESS not-accessible
    STATUS     current
    DESCRIPTION
            ""
    ::= { hmSetupIpv6Dhcpv6Server 4 }

-- {ROW} 1.3.6.1.4.1.248.32.18.2.70.3.1.4.1
hmSetupIpv6Dhcpv6ServerIfcListEntry OBJECT-TYPE
    SYNTAX     HmSetupIpv6Dhcpv6ServerIfcListEntry
    MAX-ACCESS not-accessible
    STATUS     current
    DESCRIPTION
            ""
    INDEX {
            hmSetupIpv6Dhcpv6ServerIfcListEntryInterfaceNameOrRelay
          }
    ::= { hmSetupIpv6Dhcpv6ServerIfcListTable 1 }

HmSetupIpv6Dhcpv6ServerIfcListEntry ::= SEQUENCE {
            hmSetupIpv6Dhcpv6ServerIfcListEntryInterfaceNameOrRelay DisplayString,
            hmSetupIpv6Dhcpv6ServerIfcListEntryOperating INTEGER,
            hmSetupIpv6Dhcpv6ServerIfcListEntryPrimaryDns DisplayString,
            hmSetupIpv6Dhcpv6ServerIfcListEntrySecondaryDns DisplayString,
            hmSetupIpv6Dhcpv6ServerIfcListEntryAddressPoolName DisplayString,
            hmSetupIpv6Dhcpv6ServerIfcListEntryPdPoolName DisplayString,
            hmSetupIpv6Dhcpv6ServerIfcListEntryRapidCommit INTEGER,
            hmSetupIpv6Dhcpv6ServerIfcListEntryPreference Integer32,
            hmSetupIpv6Dhcpv6ServerIfcListEntryRenewTime Integer32,
            hmSetupIpv6Dhcpv6ServerIfcListEntryRebindTime Integer32,
            hmSetupIpv6Dhcpv6ServerIfcListEntryUnicastAddress DisplayString,
            hmSetupIpv6Dhcpv6ServerIfcListEntryDnsSearchList BITS,
            hmSetupIpv6Dhcpv6ServerIfcListEntryReconfigure INTEGER
    }

-- {COLUMN} 1.3.6.1.4.1.248.32.18.2.70.3.1.4.1.1
hmSetupIpv6Dhcpv6ServerIfcListEntryInterfaceNameOrRelay OBJECT-TYPE
    SYNTAX     DisplayString (SIZE(0..39))
    MAX-ACCESS read-write
    STATUS     current
    DESCRIPTION
            "-- empty --"
    ::= { hmSetupIpv6Dhcpv6ServerIfcListEntry 1 }

-- {COLUMN} 1.3.6.1.4.1.248.32.18.2.70.3.1.4.1.2
hmSetupIpv6Dhcpv6ServerIfcListEntryOperating OBJECT-TYPE
    SYNTAX     INTEGER {
                  eNo (0),
                  eYes (1)
            }
    MAX-ACCESS read-write
    STATUS     current
    DESCRIPTION
            "-- empty --"
    ::= { hmSetupIpv6Dhcpv6ServerIfcListEntry 2 }

-- {COLUMN} 1.3.6.1.4.1.248.32.18.2.70.3.1.4.1.3
hmSetupIpv6Dhcpv6ServerIfcListEntryPrimaryDns OBJECT-TYPE
    SYNTAX     DisplayString (SIZE(0..39))
    MAX-ACCESS read-write
    STATUS     current
    DESCRIPTION
            "-- empty --"
    ::= { hmSetupIpv6Dhcpv6ServerIfcListEntry 3 }

-- {COLUMN} 1.3.6.1.4.1.248.32.18.2.70.3.1.4.1.4
hmSetupIpv6Dhcpv6ServerIfcListEntrySecondaryDns OBJECT-TYPE
    SYNTAX     DisplayString (SIZE(0..39))
    MAX-ACCESS read-write
    STATUS     current
    DESCRIPTION
            "-- empty --"
    ::= { hmSetupIpv6Dhcpv6ServerIfcListEntry 4 }

-- {COLUMN} 1.3.6.1.4.1.248.32.18.2.70.3.1.4.1.5
hmSetupIpv6Dhcpv6ServerIfcListEntryAddressPoolName OBJECT-TYPE
    SYNTAX     DisplayString (SIZE(0..31))
    MAX-ACCESS read-write
    STATUS     current
    DESCRIPTION
            "-- empty --"
    ::= { hmSetupIpv6Dhcpv6ServerIfcListEntry 5 }

-- {COLUMN} 1.3.6.1.4.1.248.32.18.2.70.3.1.4.1.6
hmSetupIpv6Dhcpv6ServerIfcListEntryPdPoolName OBJECT-TYPE
    SYNTAX     DisplayString (SIZE(0..31))
    MAX-ACCESS read-write
    STATUS     current
    DESCRIPTION
            "-- empty --"
    ::= { hmSetupIpv6Dhcpv6ServerIfcListEntry 6 }

-- {COLUMN} 1.3.6.1.4.1.248.32.18.2.70.3.1.4.1.7
hmSetupIpv6Dhcpv6ServerIfcListEntryRapidCommit OBJECT-TYPE
    SYNTAX     INTEGER {
                  eNo (0),
                  eYes (1)
            }
    MAX-ACCESS read-write
    STATUS     current
    DESCRIPTION
            "-- empty --"
    ::= { hmSetupIpv6Dhcpv6ServerIfcListEntry 7 }

-- {COLUMN} 1.3.6.1.4.1.248.32.18.2.70.3.1.4.1.8
hmSetupIpv6Dhcpv6ServerIfcListEntryPreference OBJECT-TYPE
    SYNTAX     Integer32 (0..255)
    MAX-ACCESS read-write
    STATUS     current
    DESCRIPTION
            "-- empty --"
    ::= { hmSetupIpv6Dhcpv6ServerIfcListEntry 8 }

-- {COLUMN} 1.3.6.1.4.1.248.32.18.2.70.3.1.4.1.9
hmSetupIpv6Dhcpv6ServerIfcListEntryRenewTime OBJECT-TYPE
    SYNTAX     Integer32 (0..2147483647)
    MAX-ACCESS read-write
    STATUS     current
    DESCRIPTION
            "-- empty --"
    ::= { hmSetupIpv6Dhcpv6ServerIfcListEntry 9 }

-- {COLUMN} 1.3.6.1.4.1.248.32.18.2.70.3.1.4.1.10
hmSetupIpv6Dhcpv6ServerIfcListEntryRebindTime OBJECT-TYPE
    SYNTAX     Integer32 (0..2147483647)
    MAX-ACCESS read-write
    STATUS     current
    DESCRIPTION
            "-- empty --"
    ::= { hmSetupIpv6Dhcpv6ServerIfcListEntry 10 }

-- {COLUMN} 1.3.6.1.4.1.248.32.18.2.70.3.1.4.1.11
hmSetupIpv6Dhcpv6ServerIfcListEntryUnicastAddress OBJECT-TYPE
    SYNTAX     DisplayString (SIZE(0..39))
    MAX-ACCESS read-write
    STATUS     current
    DESCRIPTION
            "-- empty --"
    ::= { hmSetupIpv6Dhcpv6ServerIfcListEntry 11 }

-- {COLUMN} 1.3.6.1.4.1.248.32.18.2.70.3.1.4.1.12
hmSetupIpv6Dhcpv6ServerIfcListEntryDnsSearchList OBJECT-TYPE
    SYNTAX     BITS {
                  eNone (0),
                  eWan (6),
                  eInternal (7)
            }
    MAX-ACCESS read-write
    STATUS     current
    DESCRIPTION
            "-- empty --"
    ::= { hmSetupIpv6Dhcpv6ServerIfcListEntry 12 }

-- {COLUMN} 1.3.6.1.4.1.248.32.18.2.70.3.1.4.1.13
hmSetupIpv6Dhcpv6ServerIfcListEntryReconfigure OBJECT-TYPE
    SYNTAX     INTEGER {
                  eOff (0),
                  eReject (1),
                  eAllow (2),
                  eRequire (3)
            }
    MAX-ACCESS read-write
    STATUS     current
    DESCRIPTION
            "-- empty --"
    ::= { hmSetupIpv6Dhcpv6ServerIfcListEntry 13 }

-- {SCALAR} 1.3.6.1.4.1.248.32.18.2.70.3.1.5
hmSetupIpv6Dhcpv6ServerLimitConfirmToClientsWithAddresses OBJECT-TYPE
    SYNTAX     INTEGER {
                  eNo (0),
                  eYes (1)
            }
    MAX-ACCESS read-write
    STATUS     current
    DESCRIPTION
            "-- empty --"
    ::= { hmSetupIpv6Dhcpv6Server 5 }

-- {TABLE} 1.3.6.1.4.1.248.32.18.2.70.3.1.6
hmSetupIpv6Dhcpv6ServerReservationsTable OBJECT-TYPE
    SYNTAX     SEQUENCE OF HmSetupIpv6Dhcpv6ServerReservationsEntry
    MAX-ACCESS not-accessible
    STATUS     current
    DESCRIPTION
            "-- empty --"
    ::= { hmSetupIpv6Dhcpv6Server 6 }

-- {ROW} 1.3.6.1.4.1.248.32.18.2.70.3.1.6.1
hmSetupIpv6Dhcpv6ServerReservationsEntry OBJECT-TYPE
    SYNTAX     HmSetupIpv6Dhcpv6ServerReservationsEntry
    MAX-ACCESS not-accessible
    STATUS     current
    DESCRIPTION
            ""
    INDEX {
            hmSetupIpv6Dhcpv6ServerReservationsEntryInterfaceNameOrRelay,
            hmSetupIpv6Dhcpv6ServerReservationsEntryAddressOrPdPrefix,
            hmSetupIpv6Dhcpv6ServerReservationsEntryPdSource
          }
    ::= { hmSetupIpv6Dhcpv6ServerReservationsTable 1 }

HmSetupIpv6Dhcpv6ServerReservationsEntry ::= SEQUENCE {
            hmSetupIpv6Dhcpv6ServerReservationsEntryInterfaceNameOrRelay DisplayString,
            hmSetupIpv6Dhcpv6ServerReservationsEntryAddressOrPdPrefix DisplayString,
            hmSetupIpv6Dhcpv6ServerReservationsEntryClientId DisplayString,
            hmSetupIpv6Dhcpv6ServerReservationsEntryPrefLifetime Integer32,
            hmSetupIpv6Dhcpv6ServerReservationsEntryValidLifetime Integer32,
            hmSetupIpv6Dhcpv6ServerReservationsEntryPdSource DisplayString
    }

-- {COLUMN} 1.3.6.1.4.1.248.32.18.2.70.3.1.6.1.1
hmSetupIpv6Dhcpv6ServerReservationsEntryInterfaceNameOrRelay OBJECT-TYPE
    SYNTAX     DisplayString (SIZE(0..39))
    MAX-ACCESS read-write
    STATUS     current
    DESCRIPTION
            "-- empty --"
    ::= { hmSetupIpv6Dhcpv6ServerReservationsEntry 1 }

-- {COLUMN} 1.3.6.1.4.1.248.32.18.2.70.3.1.6.1.2
hmSetupIpv6Dhcpv6ServerReservationsEntryAddressOrPdPrefix OBJECT-TYPE
    SYNTAX     DisplayString (SIZE(0..43))
    MAX-ACCESS read-write
    STATUS     current
    DESCRIPTION
            "-- empty --"
    ::= { hmSetupIpv6Dhcpv6ServerReservationsEntry 2 }

-- {COLUMN} 1.3.6.1.4.1.248.32.18.2.70.3.1.6.1.3
hmSetupIpv6Dhcpv6ServerReservationsEntryClientId OBJECT-TYPE
    SYNTAX     DisplayString (SIZE(0..96))
    MAX-ACCESS read-write
    STATUS     current
    DESCRIPTION
            "-- empty --"
    ::= { hmSetupIpv6Dhcpv6ServerReservationsEntry 3 }

-- {COLUMN} 1.3.6.1.4.1.248.32.18.2.70.3.1.6.1.5
hmSetupIpv6Dhcpv6ServerReservationsEntryPrefLifetime OBJECT-TYPE
    SYNTAX     Integer32 (0..2147483647)
    MAX-ACCESS read-write
    STATUS     current
    DESCRIPTION
            "-- empty --"
    ::= { hmSetupIpv6Dhcpv6ServerReservationsEntry 5 }

-- {COLUMN} 1.3.6.1.4.1.248.32.18.2.70.3.1.6.1.6
hmSetupIpv6Dhcpv6ServerReservationsEntryValidLifetime OBJECT-TYPE
    SYNTAX     Integer32 (0..2147483647)
    MAX-ACCESS read-write
    STATUS     current
    DESCRIPTION
            "-- empty --"
    ::= { hmSetupIpv6Dhcpv6ServerReservationsEntry 6 }

-- {COLUMN} 1.3.6.1.4.1.248.32.18.2.70.3.1.6.1.7
hmSetupIpv6Dhcpv6ServerReservationsEntryPdSource OBJECT-TYPE
    SYNTAX     DisplayString (SIZE(0..16))
    MAX-ACCESS read-write
    STATUS     current
    DESCRIPTION
            "-- empty --"
    ::= { hmSetupIpv6Dhcpv6ServerReservationsEntry 7 }

-- {SCALAR} 1.3.6.1.4.1.248.32.18.2.70.3.1.7
hmSetupIpv6Dhcpv6ServerCreateAddressRoutes OBJECT-TYPE
    SYNTAX     INTEGER {
                  eNo (0),
                  eYes (1)
            }
    MAX-ACCESS read-write
    STATUS     current
    DESCRIPTION
            "-- empty --"
    ::= { hmSetupIpv6Dhcpv6Server 7 }

-- {NODE} 1.3.6.1.4.1.248.32.18.2.70.3.2
hmSetupIpv6Dhcpv6Client OBJECT IDENTIFIER ::= { hmSetupIpv6Dhcpv6 2 }

-- {TABLE} 1.3.6.1.4.1.248.32.18.2.70.3.2.1
hmSetupIpv6Dhcpv6ClientInterfaceListTable OBJECT-TYPE
    SYNTAX     SEQUENCE OF HmSetupIpv6Dhcpv6ClientInterfaceListEntry
    MAX-ACCESS not-accessible
    STATUS     current
    DESCRIPTION
            "-- empty --"
    ::= { hmSetupIpv6Dhcpv6Client 1 }

-- {ROW} 1.3.6.1.4.1.248.32.18.2.70.3.2.1.1
hmSetupIpv6Dhcpv6ClientInterfaceListEntry OBJECT-TYPE
    SYNTAX     HmSetupIpv6Dhcpv6ClientInterfaceListEntry
    MAX-ACCESS not-accessible
    STATUS     current
    DESCRIPTION
            ""
    INDEX {
            hmSetupIpv6Dhcpv6ClientInterfaceListEntryInterfaceName
          }
    ::= { hmSetupIpv6Dhcpv6ClientInterfaceListTable 1 }

HmSetupIpv6Dhcpv6ClientInterfaceListEntry ::= SEQUENCE {
            hmSetupIpv6Dhcpv6ClientInterfaceListEntryInterfaceName DisplayString,
            hmSetupIpv6Dhcpv6ClientInterfaceListEntryOperating INTEGER,
            hmSetupIpv6Dhcpv6ClientInterfaceListEntryRequestDns INTEGER,
            hmSetupIpv6Dhcpv6ClientInterfaceListEntryRequestAddress INTEGER,
            hmSetupIpv6Dhcpv6ClientInterfaceListEntryRequestPd INTEGER,
            hmSetupIpv6Dhcpv6ClientInterfaceListEntryRapidCommit INTEGER,
            hmSetupIpv6Dhcpv6ClientInterfaceListEntrySendFqdn INTEGER,
            hmSetupIpv6Dhcpv6ClientInterfaceListEntryAcceptReconf INTEGER,
            hmSetupIpv6Dhcpv6ClientInterfaceListEntryRequestDomainList INTEGER
    }

-- {COLUMN} 1.3.6.1.4.1.248.32.18.2.70.3.2.1.1.1
hmSetupIpv6Dhcpv6ClientInterfaceListEntryInterfaceName OBJECT-TYPE
    SYNTAX     DisplayString (SIZE(0..16))
    MAX-ACCESS read-write
    STATUS     current
    DESCRIPTION
            "-- empty --"
    ::= { hmSetupIpv6Dhcpv6ClientInterfaceListEntry 1 }

-- {COLUMN} 1.3.6.1.4.1.248.32.18.2.70.3.2.1.1.2
hmSetupIpv6Dhcpv6ClientInterfaceListEntryOperating OBJECT-TYPE
    SYNTAX     INTEGER {
                  eNo (0),
                  eAutoconf (1),
                  eYes (2)
            }
    MAX-ACCESS read-write
    STATUS     current
    DESCRIPTION
            "-- empty --"
    ::= { hmSetupIpv6Dhcpv6ClientInterfaceListEntry 2 }

-- {COLUMN} 1.3.6.1.4.1.248.32.18.2.70.3.2.1.1.3
hmSetupIpv6Dhcpv6ClientInterfaceListEntryRequestDns OBJECT-TYPE
    SYNTAX     INTEGER {
                  eNo (0),
                  eYes (1)
            }
    MAX-ACCESS read-write
    STATUS     current
    DESCRIPTION
            "-- empty --"
    ::= { hmSetupIpv6Dhcpv6ClientInterfaceListEntry 3 }

-- {COLUMN} 1.3.6.1.4.1.248.32.18.2.70.3.2.1.1.4
hmSetupIpv6Dhcpv6ClientInterfaceListEntryRequestAddress OBJECT-TYPE
    SYNTAX     INTEGER {
                  eNo (0),
                  eYes (1)
            }
    MAX-ACCESS read-write
    STATUS     current
    DESCRIPTION
            "-- empty --"
    ::= { hmSetupIpv6Dhcpv6ClientInterfaceListEntry 4 }

-- {COLUMN} 1.3.6.1.4.1.248.32.18.2.70.3.2.1.1.5
hmSetupIpv6Dhcpv6ClientInterfaceListEntryRequestPd OBJECT-TYPE
    SYNTAX     INTEGER {
                  eNo (0),
                  eYes (1)
            }
    MAX-ACCESS read-write
    STATUS     current
    DESCRIPTION
            "-- empty --"
    ::= { hmSetupIpv6Dhcpv6ClientInterfaceListEntry 5 }

-- {COLUMN} 1.3.6.1.4.1.248.32.18.2.70.3.2.1.1.6
hmSetupIpv6Dhcpv6ClientInterfaceListEntryRapidCommit OBJECT-TYPE
    SYNTAX     INTEGER {
                  eNo (0),
                  eYes (1)
            }
    MAX-ACCESS read-write
    STATUS     current
    DESCRIPTION
            "-- empty --"
    ::= { hmSetupIpv6Dhcpv6ClientInterfaceListEntry 6 }

-- {COLUMN} 1.3.6.1.4.1.248.32.18.2.70.3.2.1.1.7
hmSetupIpv6Dhcpv6ClientInterfaceListEntrySendFqdn OBJECT-TYPE
    SYNTAX     INTEGER {
                  eNo (0),
                  eYes (1)
            }
    MAX-ACCESS read-write
    STATUS     current
    DESCRIPTION
            "-- empty --"
    ::= { hmSetupIpv6Dhcpv6ClientInterfaceListEntry 7 }

-- {COLUMN} 1.3.6.1.4.1.248.32.18.2.70.3.2.1.1.8
hmSetupIpv6Dhcpv6ClientInterfaceListEntryAcceptReconf OBJECT-TYPE
    SYNTAX     INTEGER {
                  eNo (0),
                  eYes (1)
            }
    MAX-ACCESS read-write
    STATUS     current
    DESCRIPTION
            "-- empty --"
    ::= { hmSetupIpv6Dhcpv6ClientInterfaceListEntry 8 }

-- {COLUMN} 1.3.6.1.4.1.248.32.18.2.70.3.2.1.1.9
hmSetupIpv6Dhcpv6ClientInterfaceListEntryRequestDomainList OBJECT-TYPE
    SYNTAX     INTEGER {
                  eNo (0),
                  eYes (1)
            }
    MAX-ACCESS read-write
    STATUS     current
    DESCRIPTION
            "-- empty --"
    ::= { hmSetupIpv6Dhcpv6ClientInterfaceListEntry 9 }

-- {SCALAR} 1.3.6.1.4.1.248.32.18.2.70.3.2.2
hmSetupIpv6Dhcpv6ClientUserClassIdentifer OBJECT-TYPE
    SYNTAX     DisplayString (SIZE(0..253))
    MAX-ACCESS read-write
    STATUS     current
    DESCRIPTION
            "-- empty --"
    ::= { hmSetupIpv6Dhcpv6Client 2 }

-- {SCALAR} 1.3.6.1.4.1.248.32.18.2.70.3.2.3
hmSetupIpv6Dhcpv6ClientVendorClassIdentifer OBJECT-TYPE
    SYNTAX     DisplayString (SIZE(0..253))
    MAX-ACCESS read-write
    STATUS     current
    DESCRIPTION
            "-- empty --"
    ::= { hmSetupIpv6Dhcpv6Client 3 }

-- {SCALAR} 1.3.6.1.4.1.248.32.18.2.70.3.2.4
hmSetupIpv6Dhcpv6ClientVendorClassNumber OBJECT-TYPE
    SYNTAX     Integer32 (0..2147483647)
    MAX-ACCESS read-write
    STATUS     current
    DESCRIPTION
            "-- empty --"
    ::= { hmSetupIpv6Dhcpv6Client 4 }

-- {NODE} 1.3.6.1.4.1.248.32.18.2.70.3.3
hmSetupIpv6Dhcpv6RelayAgent OBJECT IDENTIFIER ::= { hmSetupIpv6Dhcpv6 3 }

-- {TABLE} 1.3.6.1.4.1.248.32.18.2.70.3.3.1
hmSetupIpv6Dhcpv6RelayAgentInterfaceListTable OBJECT-TYPE
    SYNTAX     SEQUENCE OF HmSetupIpv6Dhcpv6RelayAgentInterfaceListEntry
    MAX-ACCESS not-accessible
    STATUS     current
    DESCRIPTION
            "-- empty --"
    ::= { hmSetupIpv6Dhcpv6RelayAgent 1 }

-- {ROW} 1.3.6.1.4.1.248.32.18.2.70.3.3.1.1
hmSetupIpv6Dhcpv6RelayAgentInterfaceListEntry OBJECT-TYPE
    SYNTAX     HmSetupIpv6Dhcpv6RelayAgentInterfaceListEntry
    MAX-ACCESS not-accessible
    STATUS     current
    DESCRIPTION
            ""
    INDEX {
            hmSetupIpv6Dhcpv6RelayAgentInterfaceListEntryInterfaceName
          }
    ::= { hmSetupIpv6Dhcpv6RelayAgentInterfaceListTable 1 }

HmSetupIpv6Dhcpv6RelayAgentInterfaceListEntry ::= SEQUENCE {
            hmSetupIpv6Dhcpv6RelayAgentInterfaceListEntryInterfaceName DisplayString,
            hmSetupIpv6Dhcpv6RelayAgentInterfaceListEntryOperating INTEGER,
            hmSetupIpv6Dhcpv6RelayAgentInterfaceListEntryInterfaceAddress DisplayString,
            hmSetupIpv6Dhcpv6RelayAgentInterfaceListEntryDestAddress DisplayString,
            hmSetupIpv6Dhcpv6RelayAgentInterfaceListEntryDestInterface DisplayString
    }

-- {COLUMN} 1.3.6.1.4.1.248.32.18.2.70.3.3.1.1.1
hmSetupIpv6Dhcpv6RelayAgentInterfaceListEntryInterfaceName OBJECT-TYPE
    SYNTAX     DisplayString (SIZE(0..16))
    MAX-ACCESS read-write
    STATUS     current
    DESCRIPTION
            "-- empty --"
    ::= { hmSetupIpv6Dhcpv6RelayAgentInterfaceListEntry 1 }

-- {COLUMN} 1.3.6.1.4.1.248.32.18.2.70.3.3.1.1.2
hmSetupIpv6Dhcpv6RelayAgentInterfaceListEntryOperating OBJECT-TYPE
    SYNTAX     INTEGER {
                  eNo (0),
                  eYes (1)
            }
    MAX-ACCESS read-write
    STATUS     current
    DESCRIPTION
            "-- empty --"
    ::= { hmSetupIpv6Dhcpv6RelayAgentInterfaceListEntry 2 }

-- {COLUMN} 1.3.6.1.4.1.248.32.18.2.70.3.3.1.1.3
hmSetupIpv6Dhcpv6RelayAgentInterfaceListEntryInterfaceAddress OBJECT-TYPE
    SYNTAX     DisplayString (SIZE(0..39))
    MAX-ACCESS read-write
    STATUS     current
    DESCRIPTION
            "-- empty --"
    ::= { hmSetupIpv6Dhcpv6RelayAgentInterfaceListEntry 3 }

-- {COLUMN} 1.3.6.1.4.1.248.32.18.2.70.3.3.1.1.4
hmSetupIpv6Dhcpv6RelayAgentInterfaceListEntryDestAddress OBJECT-TYPE
    SYNTAX     DisplayString (SIZE(0..39))
    MAX-ACCESS read-write
    STATUS     current
    DESCRIPTION
            "-- empty --"
    ::= { hmSetupIpv6Dhcpv6RelayAgentInterfaceListEntry 4 }

-- {COLUMN} 1.3.6.1.4.1.248.32.18.2.70.3.3.1.1.5
hmSetupIpv6Dhcpv6RelayAgentInterfaceListEntryDestInterface OBJECT-TYPE
    SYNTAX     DisplayString (SIZE(0..16))
    MAX-ACCESS read-write
    STATUS     current
    DESCRIPTION
            "-- empty --"
    ::= { hmSetupIpv6Dhcpv6RelayAgentInterfaceListEntry 5 }

-- {SCALAR} 1.3.6.1.4.1.248.32.18.2.70.3.3.2
hmSetupIpv6Dhcpv6RelayAgentCreateAddressRoutes OBJECT-TYPE
    SYNTAX     INTEGER {
                  eNo (0),
                  eYes (1)
            }
    MAX-ACCESS read-write
    STATUS     current
    DESCRIPTION
            "-- empty --"
    ::= { hmSetupIpv6Dhcpv6RelayAgent 2 }

-- {NODE} 1.3.6.1.4.1.248.32.18.2.70.4
hmSetupIpv6Network OBJECT IDENTIFIER ::= { hmSetupIpv6 4 }

-- {TABLE} 1.3.6.1.4.1.248.32.18.2.70.4.1
hmSetupIpv6NetworkAddressesTable OBJECT-TYPE
    SYNTAX     SEQUENCE OF HmSetupIpv6NetworkAddressesEntry
    MAX-ACCESS not-accessible
    STATUS     current
    DESCRIPTION
            "-- empty --"
    ::= { hmSetupIpv6Network 1 }

-- {ROW} 1.3.6.1.4.1.248.32.18.2.70.4.1.1
hmSetupIpv6NetworkAddressesEntry OBJECT-TYPE
    SYNTAX     HmSetupIpv6NetworkAddressesEntry
    MAX-ACCESS not-accessible
    STATUS     current
    DESCRIPTION
            ""
    INDEX {
            hmSetupIpv6NetworkAddressesEntryInterfaceName,
            hmSetupIpv6NetworkAddressesEntryIpv6AddressPrefixlength
          }
    ::= { hmSetupIpv6NetworkAddressesTable 1 }

HmSetupIpv6NetworkAddressesEntry ::= SEQUENCE {
            hmSetupIpv6NetworkAddressesEntryInterfaceName DisplayString,
            hmSetupIpv6NetworkAddressesEntryIpv6AddressPrefixlength DisplayString,
            hmSetupIpv6NetworkAddressesEntryAddressType INTEGER,
            hmSetupIpv6NetworkAddressesEntryNetworkGroup DisplayString,
            hmSetupIpv6NetworkAddressesEntryComment DisplayString
    }

-- {COLUMN} 1.3.6.1.4.1.248.32.18.2.70.4.1.1.1
hmSetupIpv6NetworkAddressesEntryInterfaceName OBJECT-TYPE
    SYNTAX     DisplayString (SIZE(0..16))
    MAX-ACCESS read-write
    STATUS     current
    DESCRIPTION
            "-- empty --"
    ::= { hmSetupIpv6NetworkAddressesEntry 1 }

-- {COLUMN} 1.3.6.1.4.1.248.32.18.2.70.4.1.1.2
hmSetupIpv6NetworkAddressesEntryIpv6AddressPrefixlength OBJECT-TYPE
    SYNTAX     DisplayString (SIZE(0..43))
    MAX-ACCESS read-write
    STATUS     current
    DESCRIPTION
            "-- empty --"
    ::= { hmSetupIpv6NetworkAddressesEntry 2 }

-- {COLUMN} 1.3.6.1.4.1.248.32.18.2.70.4.1.1.3
hmSetupIpv6NetworkAddressesEntryAddressType OBJECT-TYPE
    SYNTAX     INTEGER {
                  eUnicast (0),
                  eAnycast (1),
                  eEui64 (2)
            }
    MAX-ACCESS read-write
    STATUS     current
    DESCRIPTION
            "-- empty --"
    ::= { hmSetupIpv6NetworkAddressesEntry 3 }

-- {COLUMN} 1.3.6.1.4.1.248.32.18.2.70.4.1.1.4
hmSetupIpv6NetworkAddressesEntryNetworkGroup OBJECT-TYPE
    SYNTAX     DisplayString (SIZE(0..16))
    MAX-ACCESS read-write
    STATUS     current
    DESCRIPTION
            "-- empty --"
    ::= { hmSetupIpv6NetworkAddressesEntry 4 }

-- {COLUMN} 1.3.6.1.4.1.248.32.18.2.70.4.1.1.5
hmSetupIpv6NetworkAddressesEntryComment OBJECT-TYPE
    SYNTAX     DisplayString (SIZE(0..64))
    MAX-ACCESS read-write
    STATUS     current
    DESCRIPTION
            "-- empty --"
    ::= { hmSetupIpv6NetworkAddressesEntry 5 }

-- {TABLE} 1.3.6.1.4.1.248.32.18.2.70.4.2
hmSetupIpv6NetworkParameterTable OBJECT-TYPE
    SYNTAX     SEQUENCE OF HmSetupIpv6NetworkParameterEntry
    MAX-ACCESS not-accessible
    STATUS     current
    DESCRIPTION
            "-- empty --"
    ::= { hmSetupIpv6Network 2 }

-- {ROW} 1.3.6.1.4.1.248.32.18.2.70.4.2.1
hmSetupIpv6NetworkParameterEntry OBJECT-TYPE
    SYNTAX     HmSetupIpv6NetworkParameterEntry
    MAX-ACCESS not-accessible
    STATUS     current
    DESCRIPTION
            ""
    INDEX {
            hmSetupIpv6NetworkParameterEntryInterfaceName
          }
    ::= { hmSetupIpv6NetworkParameterTable 1 }

HmSetupIpv6NetworkParameterEntry ::= SEQUENCE {
            hmSetupIpv6NetworkParameterEntryInterfaceName DisplayString,
            hmSetupIpv6NetworkParameterEntryIpv6Gateway DisplayString,
            hmSetupIpv6NetworkParameterEntryPrimaryDns DisplayString,
            hmSetupIpv6NetworkParameterEntrySecondaryDns DisplayString
    }

-- {COLUMN} 1.3.6.1.4.1.248.32.18.2.70.4.2.1.1
hmSetupIpv6NetworkParameterEntryInterfaceName OBJECT-TYPE
    SYNTAX     DisplayString (SIZE(0..16))
    MAX-ACCESS read-write
    STATUS     current
    DESCRIPTION
            "-- empty --"
    ::= { hmSetupIpv6NetworkParameterEntry 1 }

-- {COLUMN} 1.3.6.1.4.1.248.32.18.2.70.4.2.1.2
hmSetupIpv6NetworkParameterEntryIpv6Gateway OBJECT-TYPE
    SYNTAX     DisplayString (SIZE(0..39))
    MAX-ACCESS read-write
    STATUS     current
    DESCRIPTION
            "-- empty --"
    ::= { hmSetupIpv6NetworkParameterEntry 2 }

-- {COLUMN} 1.3.6.1.4.1.248.32.18.2.70.4.2.1.3
hmSetupIpv6NetworkParameterEntryPrimaryDns OBJECT-TYPE
    SYNTAX     DisplayString (SIZE(0..39))
    MAX-ACCESS read-write
    STATUS     current
    DESCRIPTION
            "-- empty --"
    ::= { hmSetupIpv6NetworkParameterEntry 3 }

-- {COLUMN} 1.3.6.1.4.1.248.32.18.2.70.4.2.1.4
hmSetupIpv6NetworkParameterEntrySecondaryDns OBJECT-TYPE
    SYNTAX     DisplayString (SIZE(0..39))
    MAX-ACCESS read-write
    STATUS     current
    DESCRIPTION
            "-- empty --"
    ::= { hmSetupIpv6NetworkParameterEntry 4 }

-- {TABLE} 1.3.6.1.4.1.248.32.18.2.70.4.3
hmSetupIpv6NetworkLoopbackTable OBJECT-TYPE
    SYNTAX     SEQUENCE OF HmSetupIpv6NetworkLoopbackEntry
    MAX-ACCESS not-accessible
    STATUS     current
    DESCRIPTION
            "-- empty --"
    ::= { hmSetupIpv6Network 3 }

-- {ROW} 1.3.6.1.4.1.248.32.18.2.70.4.3.1
hmSetupIpv6NetworkLoopbackEntry OBJECT-TYPE
    SYNTAX     HmSetupIpv6NetworkLoopbackEntry
    MAX-ACCESS not-accessible
    STATUS     current
    DESCRIPTION
            ""
    INDEX {
            hmSetupIpv6NetworkLoopbackEntryName
          }
    ::= { hmSetupIpv6NetworkLoopbackTable 1 }

HmSetupIpv6NetworkLoopbackEntry ::= SEQUENCE {
            hmSetupIpv6NetworkLoopbackEntryName DisplayString,
            hmSetupIpv6NetworkLoopbackEntryIpv6LoopbackAddr DisplayString,
            hmSetupIpv6NetworkLoopbackEntryRtgTag Integer32,
            hmSetupIpv6NetworkLoopbackEntryComment DisplayString
    }

-- {COLUMN} 1.3.6.1.4.1.248.32.18.2.70.4.3.1.1
hmSetupIpv6NetworkLoopbackEntryName OBJECT-TYPE
    SYNTAX     DisplayString (SIZE(0..16))
    MAX-ACCESS read-write
    STATUS     current
    DESCRIPTION
            "-- empty --"
    ::= { hmSetupIpv6NetworkLoopbackEntry 1 }

-- {COLUMN} 1.3.6.1.4.1.248.32.18.2.70.4.3.1.2
hmSetupIpv6NetworkLoopbackEntryIpv6LoopbackAddr OBJECT-TYPE
    SYNTAX     DisplayString (SIZE(0..39))
    MAX-ACCESS read-write
    STATUS     current
    DESCRIPTION
            "-- empty --"
    ::= { hmSetupIpv6NetworkLoopbackEntry 2 }

-- {COLUMN} 1.3.6.1.4.1.248.32.18.2.70.4.3.1.3
hmSetupIpv6NetworkLoopbackEntryRtgTag OBJECT-TYPE
    SYNTAX     Integer32 (0..65535)
    MAX-ACCESS read-write
    STATUS     current
    DESCRIPTION
            "-- empty --"
    ::= { hmSetupIpv6NetworkLoopbackEntry 3 }

-- {COLUMN} 1.3.6.1.4.1.248.32.18.2.70.4.3.1.4
hmSetupIpv6NetworkLoopbackEntryComment OBJECT-TYPE
    SYNTAX     DisplayString (SIZE(0..64))
    MAX-ACCESS read-write
    STATUS     current
    DESCRIPTION
            "-- empty --"
    ::= { hmSetupIpv6NetworkLoopbackEntry 4 }

-- {NODE} 1.3.6.1.4.1.248.32.18.2.70.5
hmSetupIpv6Firewall OBJECT IDENTIFIER ::= { hmSetupIpv6 5 }

-- {SCALAR} 1.3.6.1.4.1.248.32.18.2.70.5.1
hmSetupIpv6FirewallOperating OBJECT-TYPE
    SYNTAX     INTEGER {
                  eNo (0),
                  eYes (1)
            }
    MAX-ACCESS read-write
    STATUS     current
    DESCRIPTION
            "-- empty --"
    ::= { hmSetupIpv6Firewall 1 }

-- {TABLE} 1.3.6.1.4.1.248.32.18.2.70.5.2
hmSetupIpv6FirewallForwardingRulesTable OBJECT-TYPE
    SYNTAX     SEQUENCE OF HmSetupIpv6FirewallForwardingRulesEntry
    MAX-ACCESS not-accessible
    STATUS     current
    DESCRIPTION
            "-- empty --"
    ::= { hmSetupIpv6Firewall 2 }

-- {ROW} 1.3.6.1.4.1.248.32.18.2.70.5.2.1
hmSetupIpv6FirewallForwardingRulesEntry OBJECT-TYPE
    SYNTAX     HmSetupIpv6FirewallForwardingRulesEntry
    MAX-ACCESS not-accessible
    STATUS     current
    DESCRIPTION
            ""
    INDEX {
            hmSetupIpv6FirewallForwardingRulesEntryName
          }
    ::= { hmSetupIpv6FirewallForwardingRulesTable 1 }

HmSetupIpv6FirewallForwardingRulesEntry ::= SEQUENCE {
            hmSetupIpv6FirewallForwardingRulesEntryName DisplayString,
            hmSetupIpv6FirewallForwardingRulesEntryFlags BITS,
            hmSetupIpv6FirewallForwardingRulesEntryPrio Integer32,
            hmSetupIpv6FirewallForwardingRulesEntryRtgTag Integer32,
            hmSetupIpv6FirewallForwardingRulesEntryAction DisplayString,
            hmSetupIpv6FirewallForwardingRulesEntryServices DisplayString,
            hmSetupIpv6FirewallForwardingRulesEntrySourceStations DisplayString,
            hmSetupIpv6FirewallForwardingRulesEntryDestinationStations DisplayString,
            hmSetupIpv6FirewallForwardingRulesEntryComment DisplayString,
            hmSetupIpv6FirewallForwardingRulesEntrySrcTag Integer32
    }

-- {COLUMN} 1.3.6.1.4.1.248.32.18.2.70.5.2.1.1
hmSetupIpv6FirewallForwardingRulesEntryName OBJECT-TYPE
    SYNTAX     DisplayString (SIZE(0..36))
    MAX-ACCESS read-write
    STATUS     current
    DESCRIPTION
            "-- empty --"
    ::= { hmSetupIpv6FirewallForwardingRulesEntry 1 }

-- {COLUMN} 1.3.6.1.4.1.248.32.18.2.70.5.2.1.2
hmSetupIpv6FirewallForwardingRulesEntryFlags OBJECT-TYPE
    SYNTAX     BITS {
                  eNone (0),
                  eStateless (4),
                  eLinked (5),
                  eDeactivated (7)
            }
    MAX-ACCESS read-write
    STATUS     current
    DESCRIPTION
            "-- empty --"
    ::= { hmSetupIpv6FirewallForwardingRulesEntry 2 }

-- {COLUMN} 1.3.6.1.4.1.248.32.18.2.70.5.2.1.3
hmSetupIpv6FirewallForwardingRulesEntryPrio OBJECT-TYPE
    SYNTAX     Integer32 (0..65535)
    MAX-ACCESS read-write
    STATUS     current
    DESCRIPTION
            "-- empty --"
    ::= { hmSetupIpv6FirewallForwardingRulesEntry 3 }

-- {COLUMN} 1.3.6.1.4.1.248.32.18.2.70.5.2.1.4
hmSetupIpv6FirewallForwardingRulesEntryRtgTag OBJECT-TYPE
    SYNTAX     Integer32 (0..65535)
    MAX-ACCESS read-write
    STATUS     current
    DESCRIPTION
            "-- empty --"
    ::= { hmSetupIpv6FirewallForwardingRulesEntry 4 }

-- {COLUMN} 1.3.6.1.4.1.248.32.18.2.70.5.2.1.5
hmSetupIpv6FirewallForwardingRulesEntryAction OBJECT-TYPE
    SYNTAX     DisplayString (SIZE(0..64))
    MAX-ACCESS read-write
    STATUS     current
    DESCRIPTION
            "-- empty --"
    ::= { hmSetupIpv6FirewallForwardingRulesEntry 5 }

-- {COLUMN} 1.3.6.1.4.1.248.32.18.2.70.5.2.1.7
hmSetupIpv6FirewallForwardingRulesEntryServices OBJECT-TYPE
    SYNTAX     DisplayString (SIZE(0..64))
    MAX-ACCESS read-write
    STATUS     current
    DESCRIPTION
            "-- empty --"
    ::= { hmSetupIpv6FirewallForwardingRulesEntry 7 }

-- {COLUMN} 1.3.6.1.4.1.248.32.18.2.70.5.2.1.8
hmSetupIpv6FirewallForwardingRulesEntrySourceStations OBJECT-TYPE
    SYNTAX     DisplayString (SIZE(0..64))
    MAX-ACCESS read-write
    STATUS     current
    DESCRIPTION
            "-- empty --"
    ::= { hmSetupIpv6FirewallForwardingRulesEntry 8 }

-- {COLUMN} 1.3.6.1.4.1.248.32.18.2.70.5.2.1.9
hmSetupIpv6FirewallForwardingRulesEntryDestinationStations OBJECT-TYPE
    SYNTAX     DisplayString (SIZE(0..64))
    MAX-ACCESS read-write
    STATUS     current
    DESCRIPTION
            "-- empty --"
    ::= { hmSetupIpv6FirewallForwardingRulesEntry 9 }

-- {COLUMN} 1.3.6.1.4.1.248.32.18.2.70.5.2.1.10
hmSetupIpv6FirewallForwardingRulesEntryComment OBJECT-TYPE
    SYNTAX     DisplayString (SIZE(0..64))
    MAX-ACCESS read-write
    STATUS     current
    DESCRIPTION
            "-- empty --"
    ::= { hmSetupIpv6FirewallForwardingRulesEntry 10 }

-- {COLUMN} 1.3.6.1.4.1.248.32.18.2.70.5.2.1.11
hmSetupIpv6FirewallForwardingRulesEntrySrcTag OBJECT-TYPE
    SYNTAX     Integer32 (0..65535)
    MAX-ACCESS read-write
    STATUS     current
    DESCRIPTION
            "-- empty --"
    ::= { hmSetupIpv6FirewallForwardingRulesEntry 11 }

-- {TABLE} 1.3.6.1.4.1.248.32.18.2.70.5.3
hmSetupIpv6FirewallActionListTable OBJECT-TYPE
    SYNTAX     SEQUENCE OF HmSetupIpv6FirewallActionListEntry
    MAX-ACCESS not-accessible
    STATUS     current
    DESCRIPTION
            "-- empty --"
    ::= { hmSetupIpv6Firewall 3 }

-- {ROW} 1.3.6.1.4.1.248.32.18.2.70.5.3.1
hmSetupIpv6FirewallActionListEntry OBJECT-TYPE
    SYNTAX     HmSetupIpv6FirewallActionListEntry
    MAX-ACCESS not-accessible
    STATUS     current
    DESCRIPTION
            ""
    INDEX {
            hmSetupIpv6FirewallActionListEntryName
          }
    ::= { hmSetupIpv6FirewallActionListTable 1 }

HmSetupIpv6FirewallActionListEntry ::= SEQUENCE {
            hmSetupIpv6FirewallActionListEntryName DisplayString,
            hmSetupIpv6FirewallActionListEntryDescription DisplayString
    }

-- {COLUMN} 1.3.6.1.4.1.248.32.18.2.70.5.3.1.1
hmSetupIpv6FirewallActionListEntryName OBJECT-TYPE
    SYNTAX     DisplayString (SIZE(0..36))
    MAX-ACCESS read-write
    STATUS     current
    DESCRIPTION
            "-- empty --"
    ::= { hmSetupIpv6FirewallActionListEntry 1 }

-- {COLUMN} 1.3.6.1.4.1.248.32.18.2.70.5.3.1.2
hmSetupIpv6FirewallActionListEntryDescription OBJECT-TYPE
    SYNTAX     DisplayString (SIZE(0..252))
    MAX-ACCESS read-write
    STATUS     current
    DESCRIPTION
            "-- empty --"
    ::= { hmSetupIpv6FirewallActionListEntry 2 }

-- {TABLE} 1.3.6.1.4.1.248.32.18.2.70.5.5
hmSetupIpv6FirewallStationListTable OBJECT-TYPE
    SYNTAX     SEQUENCE OF HmSetupIpv6FirewallStationListEntry
    MAX-ACCESS not-accessible
    STATUS     current
    DESCRIPTION
            "-- empty --"
    ::= { hmSetupIpv6Firewall 5 }

-- {ROW} 1.3.6.1.4.1.248.32.18.2.70.5.5.1
hmSetupIpv6FirewallStationListEntry OBJECT-TYPE
    SYNTAX     HmSetupIpv6FirewallStationListEntry
    MAX-ACCESS not-accessible
    STATUS     current
    DESCRIPTION
            ""
    INDEX {
            hmSetupIpv6FirewallStationListEntryName
          }
    ::= { hmSetupIpv6FirewallStationListTable 1 }

HmSetupIpv6FirewallStationListEntry ::= SEQUENCE {
            hmSetupIpv6FirewallStationListEntryName DisplayString,
            hmSetupIpv6FirewallStationListEntryDescription DisplayString
    }

-- {COLUMN} 1.3.6.1.4.1.248.32.18.2.70.5.5.1.1
hmSetupIpv6FirewallStationListEntryName OBJECT-TYPE
    SYNTAX     DisplayString (SIZE(0..36))
    MAX-ACCESS read-write
    STATUS     current
    DESCRIPTION
            "-- empty --"
    ::= { hmSetupIpv6FirewallStationListEntry 1 }

-- {COLUMN} 1.3.6.1.4.1.248.32.18.2.70.5.5.1.2
hmSetupIpv6FirewallStationListEntryDescription OBJECT-TYPE
    SYNTAX     DisplayString (SIZE(0..252))
    MAX-ACCESS read-write
    STATUS     current
    DESCRIPTION
            "-- empty --"
    ::= { hmSetupIpv6FirewallStationListEntry 2 }

-- {TABLE} 1.3.6.1.4.1.248.32.18.2.70.5.6
hmSetupIpv6FirewallServiceListTable OBJECT-TYPE
    SYNTAX     SEQUENCE OF HmSetupIpv6FirewallServiceListEntry
    MAX-ACCESS not-accessible
    STATUS     current
    DESCRIPTION
            "-- empty --"
    ::= { hmSetupIpv6Firewall 6 }

-- {ROW} 1.3.6.1.4.1.248.32.18.2.70.5.6.1
hmSetupIpv6FirewallServiceListEntry OBJECT-TYPE
    SYNTAX     HmSetupIpv6FirewallServiceListEntry
    MAX-ACCESS not-accessible
    STATUS     current
    DESCRIPTION
            ""
    INDEX {
            hmSetupIpv6FirewallServiceListEntryName
          }
    ::= { hmSetupIpv6FirewallServiceListTable 1 }

HmSetupIpv6FirewallServiceListEntry ::= SEQUENCE {
            hmSetupIpv6FirewallServiceListEntryName DisplayString,
            hmSetupIpv6FirewallServiceListEntryDescription DisplayString
    }

-- {COLUMN} 1.3.6.1.4.1.248.32.18.2.70.5.6.1.1
hmSetupIpv6FirewallServiceListEntryName OBJECT-TYPE
    SYNTAX     DisplayString (SIZE(0..36))
    MAX-ACCESS read-write
    STATUS     current
    DESCRIPTION
            "-- empty --"
    ::= { hmSetupIpv6FirewallServiceListEntry 1 }

-- {COLUMN} 1.3.6.1.4.1.248.32.18.2.70.5.6.1.2
hmSetupIpv6FirewallServiceListEntryDescription OBJECT-TYPE
    SYNTAX     DisplayString (SIZE(0..252))
    MAX-ACCESS read-write
    STATUS     current
    DESCRIPTION
            "-- empty --"
    ::= { hmSetupIpv6FirewallServiceListEntry 2 }

-- {TABLE} 1.3.6.1.4.1.248.32.18.2.70.5.7
hmSetupIpv6FirewallActionsTable OBJECT-TYPE
    SYNTAX     SEQUENCE OF HmSetupIpv6FirewallActionsEntry
    MAX-ACCESS not-accessible
    STATUS     current
    DESCRIPTION
            "-- empty --"
    ::= { hmSetupIpv6Firewall 7 }

-- {ROW} 1.3.6.1.4.1.248.32.18.2.70.5.7.1
hmSetupIpv6FirewallActionsEntry OBJECT-TYPE
    SYNTAX     HmSetupIpv6FirewallActionsEntry
    MAX-ACCESS not-accessible
    STATUS     current
    DESCRIPTION
            ""
    INDEX {
            hmSetupIpv6FirewallActionsEntryName
          }
    ::= { hmSetupIpv6FirewallActionsTable 1 }

HmSetupIpv6FirewallActionsEntry ::= SEQUENCE {
            hmSetupIpv6FirewallActionsEntryName DisplayString,
            hmSetupIpv6FirewallActionsEntryLimit Integer32,
            hmSetupIpv6FirewallActionsEntryUnit INTEGER,
            hmSetupIpv6FirewallActionsEntryTime INTEGER,
            hmSetupIpv6FirewallActionsEntryContext INTEGER,
            hmSetupIpv6FirewallActionsEntryFlags BITS,
            hmSetupIpv6FirewallActionsEntryAction INTEGER,
            hmSetupIpv6FirewallActionsEntryDiffserv INTEGER,
            hmSetupIpv6FirewallActionsEntryDscpValue Integer32,
            hmSetupIpv6FirewallActionsEntryConditions DisplayString,
            hmSetupIpv6FirewallActionsEntryTriggerActions DisplayString
    }

-- {COLUMN} 1.3.6.1.4.1.248.32.18.2.70.5.7.1.1
hmSetupIpv6FirewallActionsEntryName OBJECT-TYPE
    SYNTAX     DisplayString (SIZE(0..32))
    MAX-ACCESS read-write
    STATUS     current
    DESCRIPTION
            "-- empty --"
    ::= { hmSetupIpv6FirewallActionsEntry 1 }

-- {COLUMN} 1.3.6.1.4.1.248.32.18.2.70.5.7.1.2
hmSetupIpv6FirewallActionsEntryLimit OBJECT-TYPE
    SYNTAX     Integer32 (0..2147483647)
    MAX-ACCESS read-write
    STATUS     current
    DESCRIPTION
            "-- empty --"
    ::= { hmSetupIpv6FirewallActionsEntry 2 }

-- {COLUMN} 1.3.6.1.4.1.248.32.18.2.70.5.7.1.3
hmSetupIpv6FirewallActionsEntryUnit OBJECT-TYPE
    SYNTAX     INTEGER {
                  eKbit (0),
                  eKbytes (1),
                  ePackets (2),
                  eSessions (3),
                  eBandwidth (4)
            }
    MAX-ACCESS read-write
    STATUS     current
    DESCRIPTION
            "-- empty --"
    ::= { hmSetupIpv6FirewallActionsEntry 3 }

-- {COLUMN} 1.3.6.1.4.1.248.32.18.2.70.5.7.1.4
hmSetupIpv6FirewallActionsEntryTime OBJECT-TYPE
    SYNTAX     INTEGER {
                  eSecond (0),
                  eMinute (1),
                  eHoute (2),
                  eAbsolute (3)
            }
    MAX-ACCESS read-write
    STATUS     current
    DESCRIPTION
            "-- empty --"
    ::= { hmSetupIpv6FirewallActionsEntry 4 }

-- {COLUMN} 1.3.6.1.4.1.248.32.18.2.70.5.7.1.5
hmSetupIpv6FirewallActionsEntryContext OBJECT-TYPE
    SYNTAX     INTEGER {
                  eSession (0),
                  eStation (1),
                  eGlobal (2)
            }
    MAX-ACCESS read-write
    STATUS     current
    DESCRIPTION
            "-- empty --"
    ::= { hmSetupIpv6FirewallActionsEntry 5 }

-- {COLUMN} 1.3.6.1.4.1.248.32.18.2.70.5.7.1.6
hmSetupIpv6FirewallActionsEntryFlags OBJECT-TYPE
    SYNTAX     BITS {
                  eNone (0),
                  eShared (6),
                  eReset (7)
            }
    MAX-ACCESS read-write
    STATUS     current
    DESCRIPTION
            "-- empty --"
    ::= { hmSetupIpv6FirewallActionsEntry 6 }

-- {COLUMN} 1.3.6.1.4.1.248.32.18.2.70.5.7.1.7
hmSetupIpv6FirewallActionsEntryAction OBJECT-TYPE
    SYNTAX     INTEGER {
                  eReject (0),
                  eDrop (1),
                  eAccept (2)
            }
    MAX-ACCESS read-write
    STATUS     current
    DESCRIPTION
            "-- empty --"
    ::= { hmSetupIpv6FirewallActionsEntry 7 }

-- {COLUMN} 1.3.6.1.4.1.248.32.18.2.70.5.7.1.11
hmSetupIpv6FirewallActionsEntryDiffserv OBJECT-TYPE
    SYNTAX     INTEGER {
                  eBe (0),
                  eCs1 (32),
                  eAf11 (40),
                  eAf12 (48),
                  eAf13 (56),
                  eCs2 (64),
                  eAf21 (72),
                  eAf22 (80),
                  eAf23 (88),
                  eCs3 (96),
                  eAf31 (104),
                  eAf32 (112),
                  eAf33 (120),
                  eCs4 (128),
                  eAf41 (136),
                  eAf42 (144),
                  eAf43 (152),
                  eCs5 (160),
                  eEf (184),
                  eCs6 (192),
                  eCs7 (224),
                  eCs0 (249),
                  eNo (254),
                  eValue (255)
            }
    MAX-ACCESS read-write
    STATUS     current
    DESCRIPTION
            "-- empty --"
    ::= { hmSetupIpv6FirewallActionsEntry 11 }

-- {COLUMN} 1.3.6.1.4.1.248.32.18.2.70.5.7.1.12
hmSetupIpv6FirewallActionsEntryDscpValue OBJECT-TYPE
    SYNTAX     Integer32 (0..255)
    MAX-ACCESS read-write
    STATUS     current
    DESCRIPTION
            "-- empty --"
    ::= { hmSetupIpv6FirewallActionsEntry 12 }

-- {COLUMN} 1.3.6.1.4.1.248.32.18.2.70.5.7.1.13
hmSetupIpv6FirewallActionsEntryConditions OBJECT-TYPE
    SYNTAX     DisplayString (SIZE(0..32))
    MAX-ACCESS read-write
    STATUS     current
    DESCRIPTION
            "-- empty --"
    ::= { hmSetupIpv6FirewallActionsEntry 13 }

-- {COLUMN} 1.3.6.1.4.1.248.32.18.2.70.5.7.1.14
hmSetupIpv6FirewallActionsEntryTriggerActions OBJECT-TYPE
    SYNTAX     DisplayString (SIZE(0..32))
    MAX-ACCESS read-write
    STATUS     current
    DESCRIPTION
            "-- empty --"
    ::= { hmSetupIpv6FirewallActionsEntry 14 }

-- {TABLE} 1.3.6.1.4.1.248.32.18.2.70.5.9
hmSetupIpv6FirewallStationsTable OBJECT-TYPE
    SYNTAX     SEQUENCE OF HmSetupIpv6FirewallStationsEntry
    MAX-ACCESS not-accessible
    STATUS     current
    DESCRIPTION
            "-- empty --"
    ::= { hmSetupIpv6Firewall 9 }

-- {ROW} 1.3.6.1.4.1.248.32.18.2.70.5.9.1
hmSetupIpv6FirewallStationsEntry OBJECT-TYPE
    SYNTAX     HmSetupIpv6FirewallStationsEntry
    MAX-ACCESS not-accessible
    STATUS     current
    DESCRIPTION
            ""
    INDEX {
            hmSetupIpv6FirewallStationsEntryName
          }
    ::= { hmSetupIpv6FirewallStationsTable 1 }

HmSetupIpv6FirewallStationsEntry ::= SEQUENCE {
            hmSetupIpv6FirewallStationsEntryName DisplayString,
            hmSetupIpv6FirewallStationsEntryType INTEGER,
            hmSetupIpv6FirewallStationsEntryLocalNetwork DisplayString,
            hmSetupIpv6FirewallStationsEntryRemotePeerLocalHost DisplayString,
            hmSetupIpv6FirewallStationsEntryAddressPrefix DisplayString
    }

-- {COLUMN} 1.3.6.1.4.1.248.32.18.2.70.5.9.1.1
hmSetupIpv6FirewallStationsEntryName OBJECT-TYPE
    SYNTAX     DisplayString (SIZE(0..32))
    MAX-ACCESS read-write
    STATUS     current
    DESCRIPTION
            "-- empty --"
    ::= { hmSetupIpv6FirewallStationsEntry 1 }

-- {COLUMN} 1.3.6.1.4.1.248.32.18.2.70.5.9.1.2
hmSetupIpv6FirewallStationsEntryType OBJECT-TYPE
    SYNTAX     INTEGER {
                  eLocalNetwork (0),
                  eRemotePeer (1),
                  ePrefix (2),
                  eIdentifier (3),
                  eIpAddress (4),
                  eNamedHost (5)
            }
    MAX-ACCESS read-write
    STATUS     current
    DESCRIPTION
            "-- empty --"
    ::= { hmSetupIpv6FirewallStationsEntry 2 }

-- {COLUMN} 1.3.6.1.4.1.248.32.18.2.70.5.9.1.3
hmSetupIpv6FirewallStationsEntryLocalNetwork OBJECT-TYPE
    SYNTAX     DisplayString (SIZE(0..16))
    MAX-ACCESS read-write
    STATUS     current
    DESCRIPTION
            "-- empty --"
    ::= { hmSetupIpv6FirewallStationsEntry 3 }

-- {COLUMN} 1.3.6.1.4.1.248.32.18.2.70.5.9.1.6
hmSetupIpv6FirewallStationsEntryRemotePeerLocalHost OBJECT-TYPE
    SYNTAX     DisplayString (SIZE(0..64))
    MAX-ACCESS read-write
    STATUS     current
    DESCRIPTION
            "-- empty --"
    ::= { hmSetupIpv6FirewallStationsEntry 6 }

-- {COLUMN} 1.3.6.1.4.1.248.32.18.2.70.5.9.1.7
hmSetupIpv6FirewallStationsEntryAddressPrefix OBJECT-TYPE
    SYNTAX     DisplayString (SIZE(0..43))
    MAX-ACCESS read-write
    STATUS     current
    DESCRIPTION
            "-- empty --"
    ::= { hmSetupIpv6FirewallStationsEntry 7 }

-- {TABLE} 1.3.6.1.4.1.248.32.18.2.70.5.10
hmSetupIpv6FirewallServicesTable OBJECT-TYPE
    SYNTAX     SEQUENCE OF HmSetupIpv6FirewallServicesEntry
    MAX-ACCESS not-accessible
    STATUS     current
    DESCRIPTION
            "-- empty --"
    ::= { hmSetupIpv6Firewall 10 }

-- {ROW} 1.3.6.1.4.1.248.32.18.2.70.5.10.1
hmSetupIpv6FirewallServicesEntry OBJECT-TYPE
    SYNTAX     HmSetupIpv6FirewallServicesEntry
    MAX-ACCESS not-accessible
    STATUS     current
    DESCRIPTION
            ""
    INDEX {
            hmSetupIpv6FirewallServicesEntryName
          }
    ::= { hmSetupIpv6FirewallServicesTable 1 }

HmSetupIpv6FirewallServicesEntry ::= SEQUENCE {
            hmSetupIpv6FirewallServicesEntryName DisplayString,
            hmSetupIpv6FirewallServicesEntryProtocol INTEGER,
            hmSetupIpv6FirewallServicesEntryPorts DisplayString,
            hmSetupIpv6FirewallServicesEntrySrcPorts INTEGER
    }

-- {COLUMN} 1.3.6.1.4.1.248.32.18.2.70.5.10.1.1
hmSetupIpv6FirewallServicesEntryName OBJECT-TYPE
    SYNTAX     DisplayString (SIZE(0..32))
    MAX-ACCESS read-write
    STATUS     current
    DESCRIPTION
            "-- empty --"
    ::= { hmSetupIpv6FirewallServicesEntry 1 }

-- {COLUMN} 1.3.6.1.4.1.248.32.18.2.70.5.10.1.2
hmSetupIpv6FirewallServicesEntryProtocol OBJECT-TYPE
    SYNTAX     INTEGER {
                  eTcp (2),
                  eUdp (4),
                  eTcpPlusUdp (6)
            }
    MAX-ACCESS read-write
    STATUS     current
    DESCRIPTION
            "-- empty --"
    ::= { hmSetupIpv6FirewallServicesEntry 2 }

-- {COLUMN} 1.3.6.1.4.1.248.32.18.2.70.5.10.1.3
hmSetupIpv6FirewallServicesEntryPorts OBJECT-TYPE
    SYNTAX     DisplayString (SIZE(0..64))
    MAX-ACCESS read-write
    STATUS     current
    DESCRIPTION
            "-- empty --"
    ::= { hmSetupIpv6FirewallServicesEntry 3 }

-- {COLUMN} 1.3.6.1.4.1.248.32.18.2.70.5.10.1.4
hmSetupIpv6FirewallServicesEntrySrcPorts OBJECT-TYPE
    SYNTAX     INTEGER {
                  eNo (0),
                  eYes (1)
            }
    MAX-ACCESS read-write
    STATUS     current
    DESCRIPTION
            "-- empty --"
    ::= { hmSetupIpv6FirewallServicesEntry 4 }

-- {TABLE} 1.3.6.1.4.1.248.32.18.2.70.5.11
hmSetupIpv6FirewallProtocolsTable OBJECT-TYPE
    SYNTAX     SEQUENCE OF HmSetupIpv6FirewallProtocolsEntry
    MAX-ACCESS not-accessible
    STATUS     current
    DESCRIPTION
            "-- empty --"
    ::= { hmSetupIpv6Firewall 11 }

-- {ROW} 1.3.6.1.4.1.248.32.18.2.70.5.11.1
hmSetupIpv6FirewallProtocolsEntry OBJECT-TYPE
    SYNTAX     HmSetupIpv6FirewallProtocolsEntry
    MAX-ACCESS not-accessible
    STATUS     current
    DESCRIPTION
            ""
    INDEX {
            hmSetupIpv6FirewallProtocolsEntryName
          }
    ::= { hmSetupIpv6FirewallProtocolsTable 1 }

HmSetupIpv6FirewallProtocolsEntry ::= SEQUENCE {
            hmSetupIpv6FirewallProtocolsEntryName DisplayString,
            hmSetupIpv6FirewallProtocolsEntryProtocol Integer32
    }

-- {COLUMN} 1.3.6.1.4.1.248.32.18.2.70.5.11.1.1
hmSetupIpv6FirewallProtocolsEntryName OBJECT-TYPE
    SYNTAX     DisplayString (SIZE(0..32))
    MAX-ACCESS read-write
    STATUS     current
    DESCRIPTION
            "-- empty --"
    ::= { hmSetupIpv6FirewallProtocolsEntry 1 }

-- {COLUMN} 1.3.6.1.4.1.248.32.18.2.70.5.11.1.2
hmSetupIpv6FirewallProtocolsEntryProtocol OBJECT-TYPE
    SYNTAX     Integer32 (0..2147483647)
    MAX-ACCESS read-write
    STATUS     current
    DESCRIPTION
            "-- empty --"
    ::= { hmSetupIpv6FirewallProtocolsEntry 2 }

-- {TABLE} 1.3.6.1.4.1.248.32.18.2.70.5.12
hmSetupIpv6FirewallConditionsTable OBJECT-TYPE
    SYNTAX     SEQUENCE OF HmSetupIpv6FirewallConditionsEntry
    MAX-ACCESS not-accessible
    STATUS     current
    DESCRIPTION
            "-- empty --"
    ::= { hmSetupIpv6Firewall 12 }

-- {ROW} 1.3.6.1.4.1.248.32.18.2.70.5.12.1
hmSetupIpv6FirewallConditionsEntry OBJECT-TYPE
    SYNTAX     HmSetupIpv6FirewallConditionsEntry
    MAX-ACCESS not-accessible
    STATUS     current
    DESCRIPTION
            ""
    INDEX {
            hmSetupIpv6FirewallConditionsEntryName
          }
    ::= { hmSetupIpv6FirewallConditionsTable 1 }

HmSetupIpv6FirewallConditionsEntry ::= SEQUENCE {
            hmSetupIpv6FirewallConditionsEntryName DisplayString,
            hmSetupIpv6FirewallConditionsEntryConditions BITS,
            hmSetupIpv6FirewallConditionsEntryTransportDirection INTEGER,
            hmSetupIpv6FirewallConditionsEntryDiffserv INTEGER,
            hmSetupIpv6FirewallConditionsEntryDscpValue Integer32
    }

-- {COLUMN} 1.3.6.1.4.1.248.32.18.2.70.5.12.1.1
hmSetupIpv6FirewallConditionsEntryName OBJECT-TYPE
    SYNTAX     DisplayString (SIZE(0..32))
    MAX-ACCESS read-write
    STATUS     current
    DESCRIPTION
            "-- empty --"
    ::= { hmSetupIpv6FirewallConditionsEntry 1 }

-- {COLUMN} 1.3.6.1.4.1.248.32.18.2.70.5.12.1.2
hmSetupIpv6FirewallConditionsEntryConditions OBJECT-TYPE
    SYNTAX     BITS {
                  eNone (0),
                  eReceived (2),
                  eSent (3),
                  eVpnRoute (4),
                  eBackupConnection (5),
                  eDefaultRoute (6),
                  eNotConnected (7)
            }
    MAX-ACCESS read-write
    STATUS     current
    DESCRIPTION
            "-- empty --"
    ::= { hmSetupIpv6FirewallConditionsEntry 2 }

-- {COLUMN} 1.3.6.1.4.1.248.32.18.2.70.5.12.1.3
hmSetupIpv6FirewallConditionsEntryTransportDirection OBJECT-TYPE
    SYNTAX     INTEGER {
                  ePhysical (0),
                  eLogical (1)
            }
    MAX-ACCESS read-write
    STATUS     current
    DESCRIPTION
            "-- empty --"
    ::= { hmSetupIpv6FirewallConditionsEntry 3 }

-- {COLUMN} 1.3.6.1.4.1.248.32.18.2.70.5.12.1.4
hmSetupIpv6FirewallConditionsEntryDiffserv OBJECT-TYPE
    SYNTAX     INTEGER {
                  eBe (0),
                  eCs1 (32),
                  eAf11 (40),
                  eAf12 (48),
                  eAf13 (56),
                  eCs2 (64),
                  eAf21 (72),
                  eAf22 (80),
                  eAf23 (88),
                  eCs3 (96),
                  eAf31 (104),
                  eAf32 (112),
                  eAf33 (120),
                  eCs4 (128),
                  eAf41 (136),
                  eAf42 (144),
                  eAf43 (152),
                  eCs5 (160),
                  eEf (184),
                  eCs6 (192),
                  eCs7 (224),
                  eCsx (240),
                  eAf1x (241),
                  eAf2x (242),
                  eAf3x (243),
                  eAf4x (244),
                  eAfx1 (245),
                  eAfx2 (246),
                  eAfx3 (247),
                  eAfxx (248),
                  eCs0 (249),
                  eIgnore (254),
                  eValue (255)
            }
    MAX-ACCESS read-write
    STATUS     current
    DESCRIPTION
            "-- empty --"
    ::= { hmSetupIpv6FirewallConditionsEntry 4 }

-- {COLUMN} 1.3.6.1.4.1.248.32.18.2.70.5.12.1.5
hmSetupIpv6FirewallConditionsEntryDscpValue OBJECT-TYPE
    SYNTAX     Integer32 (0..255)
    MAX-ACCESS read-write
    STATUS     current
    DESCRIPTION
            "-- empty --"
    ::= { hmSetupIpv6FirewallConditionsEntry 5 }

-- {TABLE} 1.3.6.1.4.1.248.32.18.2.70.5.13
hmSetupIpv6FirewallTriggerActionsTable OBJECT-TYPE
    SYNTAX     SEQUENCE OF HmSetupIpv6FirewallTriggerActionsEntry
    MAX-ACCESS not-accessible
    STATUS     current
    DESCRIPTION
            "-- empty --"
    ::= { hmSetupIpv6Firewall 13 }

-- {ROW} 1.3.6.1.4.1.248.32.18.2.70.5.13.1
hmSetupIpv6FirewallTriggerActionsEntry OBJECT-TYPE
    SYNTAX     HmSetupIpv6FirewallTriggerActionsEntry
    MAX-ACCESS not-accessible
    STATUS     current
    DESCRIPTION
            ""
    INDEX {
            hmSetupIpv6FirewallTriggerActionsEntryName
          }
    ::= { hmSetupIpv6FirewallTriggerActionsTable 1 }

HmSetupIpv6FirewallTriggerActionsEntry ::= SEQUENCE {
            hmSetupIpv6FirewallTriggerActionsEntryName DisplayString,
            hmSetupIpv6FirewallTriggerActionsEntryNotifications BITS,
            hmSetupIpv6FirewallTriggerActionsEntryDisconnect INTEGER,
            hmSetupIpv6FirewallTriggerActionsEntryBlockSource INTEGER,
            hmSetupIpv6FirewallTriggerActionsEntryBlockTime Integer32,
            hmSetupIpv6FirewallTriggerActionsEntryCloseDestination INTEGER,
            hmSetupIpv6FirewallTriggerActionsEntryCloseTime Integer32
    }

-- {COLUMN} 1.3.6.1.4.1.248.32.18.2.70.5.13.1.1
hmSetupIpv6FirewallTriggerActionsEntryName OBJECT-TYPE
    SYNTAX     DisplayString (SIZE(0..32))
    MAX-ACCESS read-write
    STATUS     current
    DESCRIPTION
            "-- empty --"
    ::= { hmSetupIpv6FirewallTriggerActionsEntry 1 }

-- {COLUMN} 1.3.6.1.4.1.248.32.18.2.70.5.13.1.2
hmSetupIpv6FirewallTriggerActionsEntryNotifications OBJECT-TYPE
    SYNTAX     BITS {
                  eNone (0),
                  eEmail (5),
                  eSyslog (6),
                  eSnmp (7)
            }
    MAX-ACCESS read-write
    STATUS     current
    DESCRIPTION
            "-- empty --"
    ::= { hmSetupIpv6FirewallTriggerActionsEntry 2 }

-- {COLUMN} 1.3.6.1.4.1.248.32.18.2.70.5.13.1.3
hmSetupIpv6FirewallTriggerActionsEntryDisconnect OBJECT-TYPE
    SYNTAX     INTEGER {
                  eNo (0),
                  eYes (1)
            }
    MAX-ACCESS read-write
    STATUS     current
    DESCRIPTION
            "-- empty --"
    ::= { hmSetupIpv6FirewallTriggerActionsEntry 3 }

-- {COLUMN} 1.3.6.1.4.1.248.32.18.2.70.5.13.1.4
hmSetupIpv6FirewallTriggerActionsEntryBlockSource OBJECT-TYPE
    SYNTAX     INTEGER {
                  eNo (0),
                  eYes (1)
            }
    MAX-ACCESS read-write
    STATUS     current
    DESCRIPTION
            "-- empty --"
    ::= { hmSetupIpv6FirewallTriggerActionsEntry 4 }

-- {COLUMN} 1.3.6.1.4.1.248.32.18.2.70.5.13.1.5
hmSetupIpv6FirewallTriggerActionsEntryBlockTime OBJECT-TYPE
    SYNTAX     Integer32 (0..2147483647)
    MAX-ACCESS read-write
    STATUS     current
    DESCRIPTION
            "-- empty --"
    ::= { hmSetupIpv6FirewallTriggerActionsEntry 5 }

-- {COLUMN} 1.3.6.1.4.1.248.32.18.2.70.5.13.1.6
hmSetupIpv6FirewallTriggerActionsEntryCloseDestination OBJECT-TYPE
    SYNTAX     INTEGER {
                  eNo (0),
                  eYes (1)
            }
    MAX-ACCESS read-write
    STATUS     current
    DESCRIPTION
            "-- empty --"
    ::= { hmSetupIpv6FirewallTriggerActionsEntry 6 }

-- {COLUMN} 1.3.6.1.4.1.248.32.18.2.70.5.13.1.7
hmSetupIpv6FirewallTriggerActionsEntryCloseTime OBJECT-TYPE
    SYNTAX     Integer32 (0..2147483647)
    MAX-ACCESS read-write
    STATUS     current
    DESCRIPTION
            "-- empty --"
    ::= { hmSetupIpv6FirewallTriggerActionsEntry 7 }

-- {TABLE} 1.3.6.1.4.1.248.32.18.2.70.5.14
hmSetupIpv6FirewallIcmpServicesTable OBJECT-TYPE
    SYNTAX     SEQUENCE OF HmSetupIpv6FirewallIcmpServicesEntry
    MAX-ACCESS not-accessible
    STATUS     current
    DESCRIPTION
            "-- empty --"
    ::= { hmSetupIpv6Firewall 14 }

-- {ROW} 1.3.6.1.4.1.248.32.18.2.70.5.14.1
hmSetupIpv6FirewallIcmpServicesEntry OBJECT-TYPE
    SYNTAX     HmSetupIpv6FirewallIcmpServicesEntry
    MAX-ACCESS not-accessible
    STATUS     current
    DESCRIPTION
            ""
    INDEX {
            hmSetupIpv6FirewallIcmpServicesEntryName
          }
    ::= { hmSetupIpv6FirewallIcmpServicesTable 1 }

HmSetupIpv6FirewallIcmpServicesEntry ::= SEQUENCE {
            hmSetupIpv6FirewallIcmpServicesEntryName DisplayString,
            hmSetupIpv6FirewallIcmpServicesEntryType Integer32,
            hmSetupIpv6FirewallIcmpServicesEntryCode Integer32
    }

-- {COLUMN} 1.3.6.1.4.1.248.32.18.2.70.5.14.1.1
hmSetupIpv6FirewallIcmpServicesEntryName OBJECT-TYPE
    SYNTAX     DisplayString (SIZE(0..32))
    MAX-ACCESS read-write
    STATUS     current
    DESCRIPTION
            "-- empty --"
    ::= { hmSetupIpv6FirewallIcmpServicesEntry 1 }

-- {COLUMN} 1.3.6.1.4.1.248.32.18.2.70.5.14.1.2
hmSetupIpv6FirewallIcmpServicesEntryType OBJECT-TYPE
    SYNTAX     Integer32 (0..2147483647)
    MAX-ACCESS read-write
    STATUS     current
    DESCRIPTION
            "-- empty --"
    ::= { hmSetupIpv6FirewallIcmpServicesEntry 2 }

-- {COLUMN} 1.3.6.1.4.1.248.32.18.2.70.5.14.1.3
hmSetupIpv6FirewallIcmpServicesEntryCode OBJECT-TYPE
    SYNTAX     Integer32 (0..2147483647)
    MAX-ACCESS read-write
    STATUS     current
    DESCRIPTION
            "-- empty --"
    ::= { hmSetupIpv6FirewallIcmpServicesEntry 3 }

-- {TABLE} 1.3.6.1.4.1.248.32.18.2.70.5.15
hmSetupIpv6FirewallInboundRulesTable OBJECT-TYPE
    SYNTAX     SEQUENCE OF HmSetupIpv6FirewallInboundRulesEntry
    MAX-ACCESS not-accessible
    STATUS     current
    DESCRIPTION
            "-- empty --"
    ::= { hmSetupIpv6Firewall 15 }

-- {ROW} 1.3.6.1.4.1.248.32.18.2.70.5.15.1
hmSetupIpv6FirewallInboundRulesEntry OBJECT-TYPE
    SYNTAX     HmSetupIpv6FirewallInboundRulesEntry
    MAX-ACCESS not-accessible
    STATUS     current
    DESCRIPTION
            ""
    INDEX {
            hmSetupIpv6FirewallInboundRulesEntryName
          }
    ::= { hmSetupIpv6FirewallInboundRulesTable 1 }

HmSetupIpv6FirewallInboundRulesEntry ::= SEQUENCE {
            hmSetupIpv6FirewallInboundRulesEntryName DisplayString,
            hmSetupIpv6FirewallInboundRulesEntryActive INTEGER,
            hmSetupIpv6FirewallInboundRulesEntryPrio Integer32,
            hmSetupIpv6FirewallInboundRulesEntryAction DisplayString,
            hmSetupIpv6FirewallInboundRulesEntryServices DisplayString,
            hmSetupIpv6FirewallInboundRulesEntrySourceStations DisplayString,
            hmSetupIpv6FirewallInboundRulesEntryComment DisplayString,
            hmSetupIpv6FirewallInboundRulesEntrySrcTag Integer32
    }

-- {COLUMN} 1.3.6.1.4.1.248.32.18.2.70.5.15.1.1
hmSetupIpv6FirewallInboundRulesEntryName OBJECT-TYPE
    SYNTAX     DisplayString (SIZE(0..36))
    MAX-ACCESS read-write
    STATUS     current
    DESCRIPTION
            "-- empty --"
    ::= { hmSetupIpv6FirewallInboundRulesEntry 1 }

-- {COLUMN} 1.3.6.1.4.1.248.32.18.2.70.5.15.1.2
hmSetupIpv6FirewallInboundRulesEntryActive OBJECT-TYPE
    SYNTAX     INTEGER {
                  eYes (0),
                  eNo (1)
            }
    MAX-ACCESS read-write
    STATUS     current
    DESCRIPTION
            "-- empty --"
    ::= { hmSetupIpv6FirewallInboundRulesEntry 2 }

-- {COLUMN} 1.3.6.1.4.1.248.32.18.2.70.5.15.1.3
hmSetupIpv6FirewallInboundRulesEntryPrio OBJECT-TYPE
    SYNTAX     Integer32 (0..65535)
    MAX-ACCESS read-write
    STATUS     current
    DESCRIPTION
            "-- empty --"
    ::= { hmSetupIpv6FirewallInboundRulesEntry 3 }

-- {COLUMN} 1.3.6.1.4.1.248.32.18.2.70.5.15.1.5
hmSetupIpv6FirewallInboundRulesEntryAction OBJECT-TYPE
    SYNTAX     DisplayString (SIZE(0..64))
    MAX-ACCESS read-write
    STATUS     current
    DESCRIPTION
            "-- empty --"
    ::= { hmSetupIpv6FirewallInboundRulesEntry 5 }

-- {COLUMN} 1.3.6.1.4.1.248.32.18.2.70.5.15.1.7
hmSetupIpv6FirewallInboundRulesEntryServices OBJECT-TYPE
    SYNTAX     DisplayString (SIZE(0..64))
    MAX-ACCESS read-write
    STATUS     current
    DESCRIPTION
            "-- empty --"
    ::= { hmSetupIpv6FirewallInboundRulesEntry 7 }

-- {COLUMN} 1.3.6.1.4.1.248.32.18.2.70.5.15.1.8
hmSetupIpv6FirewallInboundRulesEntrySourceStations OBJECT-TYPE
    SYNTAX     DisplayString (SIZE(0..64))
    MAX-ACCESS read-write
    STATUS     current
    DESCRIPTION
            "-- empty --"
    ::= { hmSetupIpv6FirewallInboundRulesEntry 8 }

-- {COLUMN} 1.3.6.1.4.1.248.32.18.2.70.5.15.1.10
hmSetupIpv6FirewallInboundRulesEntryComment OBJECT-TYPE
    SYNTAX     DisplayString (SIZE(0..64))
    MAX-ACCESS read-write
    STATUS     current
    DESCRIPTION
            "-- empty --"
    ::= { hmSetupIpv6FirewallInboundRulesEntry 10 }

-- {COLUMN} 1.3.6.1.4.1.248.32.18.2.70.5.15.1.11
hmSetupIpv6FirewallInboundRulesEntrySrcTag OBJECT-TYPE
    SYNTAX     Integer32 (0..65535)
    MAX-ACCESS read-write
    STATUS     current
    DESCRIPTION
            "-- empty --"
    ::= { hmSetupIpv6FirewallInboundRulesEntry 11 }

-- {SCALAR} 1.3.6.1.4.1.248.32.18.2.70.5.20
hmSetupIpv6FirewallAllowRouteOptions OBJECT-TYPE
    SYNTAX     INTEGER {
                  eNo (0),
                  eYes (1)
            }
    MAX-ACCESS read-write
    STATUS     current
    DESCRIPTION
            "-- empty --"
    ::= { hmSetupIpv6Firewall 20 }

-- {SCALAR} 1.3.6.1.4.1.248.32.18.2.70.5.21
hmSetupIpv6FirewallDestinationCacheLimit OBJECT-TYPE
    SYNTAX     Integer32 (0..2147483647)
    MAX-ACCESS read-write
    STATUS     current
    DESCRIPTION
            "-- empty --"
    ::= { hmSetupIpv6Firewall 21 }

-- {TABLE} 1.3.6.1.4.1.248.32.18.2.70.6
hmSetupIpv6LanInterfacesTable OBJECT-TYPE
    SYNTAX     SEQUENCE OF HmSetupIpv6LanInterfacesEntry
    MAX-ACCESS not-accessible
    STATUS     current
    DESCRIPTION
            "-- empty --"
    ::= { hmSetupIpv6 6 }

-- {ROW} 1.3.6.1.4.1.248.32.18.2.70.6.1
hmSetupIpv6LanInterfacesEntry OBJECT-TYPE
    SYNTAX     HmSetupIpv6LanInterfacesEntry
    MAX-ACCESS not-accessible
    STATUS     current
    DESCRIPTION
            ""
    INDEX {
            hmSetupIpv6LanInterfacesEntryInterfaceName
          }
    ::= { hmSetupIpv6LanInterfacesTable 1 }

HmSetupIpv6LanInterfacesEntry ::= SEQUENCE {
            hmSetupIpv6LanInterfacesEntryInterfaceName DisplayString,
            hmSetupIpv6LanInterfacesEntryInterfaceId INTEGER,
            hmSetupIpv6LanInterfacesEntryVlanId Integer32,
            hmSetupIpv6LanInterfacesEntryRtgTag Integer32,
            hmSetupIpv6LanInterfacesEntryAutoconf INTEGER,
            hmSetupIpv6LanInterfacesEntryAcceptRa INTEGER,
            hmSetupIpv6LanInterfacesEntryInterfaceStatus INTEGER,
            hmSetupIpv6LanInterfacesEntryForwarding INTEGER,
            hmSetupIpv6LanInterfacesEntryMtu Integer32,
            hmSetupIpv6LanInterfacesEntryFirewall INTEGER,
            hmSetupIpv6LanInterfacesEntryComment DisplayString,
            hmSetupIpv6LanInterfacesEntryDadAttempts Integer32,
            hmSetupIpv6LanInterfacesEntryRsCount Integer32
    }

-- {COLUMN} 1.3.6.1.4.1.248.32.18.2.70.6.1.1
hmSetupIpv6LanInterfacesEntryInterfaceName OBJECT-TYPE
    SYNTAX     DisplayString (SIZE(0..16))
    MAX-ACCESS read-write
    STATUS     current
    DESCRIPTION
            "-- empty --"
    ::= { hmSetupIpv6LanInterfacesEntry 1 }

-- {COLUMN} 1.3.6.1.4.1.248.32.18.2.70.6.1.2
hmSetupIpv6LanInterfacesEntryInterfaceId OBJECT-TYPE
    SYNTAX     INTEGER {
                  eLan1 (256),
                  eLan2 (257),
                  eLan3 (258),
                  eLan4 (259),
                  eWlan1 (512),
                  eWlan2 (513),
                  eP2p11 (768),
                  eP2p12 (769),
                  eP2p13 (770),
                  eP2p14 (771),
                  eP2p15 (772),
                  eP2p16 (773),
                  eP2p21 (774),
                  eP2p22 (775),
                  eP2p23 (776),
                  eP2p24 (777),
                  eP2p25 (778),
                  eP2p26 (779),
                  eP2p17 (799),
                  eP2p18 (800),
                  eP2p19 (801),
                  eP2p110 (802),
                  eP2p111 (803),
                  eP2p112 (804),
                  eP2p113 (805),
                  eP2p114 (806),
                  eP2p115 (807),
                  eP2p116 (808),
                  eP2p27 (831),
                  eP2p28 (832),
                  eP2p29 (833),
                  eP2p210 (834),
                  eP2p211 (835),
                  eP2p212 (836),
                  eP2p213 (837),
                  eP2p214 (838),
                  eP2p215 (839),
                  eP2p216 (840),
                  eWlan12 (1024),
                  eWlan13 (1025),
                  eWlan14 (1026),
                  eWlan15 (1027),
                  eWlan16 (1028),
                  eWlan17 (1029),
                  eWlan18 (1030),
                  eWlan22 (1031),
                  eWlan23 (1032),
                  eWlan24 (1033),
                  eWlan25 (1034),
                  eWlan26 (1035),
                  eWlan27 (1036),
                  eWlan28 (1037),
                  eBrg1 (1536),
                  eBrg2 (1537),
                  eBrg3 (1538),
                  eBrg4 (1539),
                  eBrg5 (1540),
                  eBrg6 (1541),
                  eBrg7 (1542),
                  eBrg8 (1543),
                  eWlcTunnel1 (1792),
                  eWlcTunnel2 (1793),
                  eWlcTunnel3 (1794),
                  eWlcTunnel4 (1795),
                  eWlcTunnel5 (1796),
                  eWlcTunnel6 (1797),
                  eWlcTunnel7 (1798),
                  eWlcTunnel8 (1799),
                  eWlcTunnel9 (1800),
                  eWlcTunnel10 (1801),
                  eWlcTunnel11 (1802),
                  eWlcTunnel12 (1803),
                  eWlcTunnel13 (1804),
                  eWlcTunnel14 (1805),
                  eWlcTunnel15 (1806),
                  eWlcTunnel16 (1807),
                  eWlcTunnel17 (1808),
                  eWlcTunnel18 (1809),
                  eWlcTunnel19 (1810),
                  eWlcTunnel20 (1811),
                  eWlcTunnel21 (1812),
                  eWlcTunnel22 (1813),
                  eWlcTunnel23 (1814),
                  eWlcTunnel24 (1815),
                  eWlcTunnel25 (1816),
                  eWlcTunnel26 (1817),
                  eWlcTunnel27 (1818),
                  eWlcTunnel28 (1819),
                  eWlcTunnel29 (1820),
                  eWlcTunnel30 (1821),
                  eWlcTunnel31 (1822),
                  eWlcTunnel32 (1823),
                  eWlcTunnelAutowds (1824),
                  ePrp1 (2048),
                  ePrp2 (2049),
                  eGreTunnel1 (2304),
                  eGreTunnel2 (2305),
                  eGreTunnel3 (2306),
                  eGreTunnel4 (2307),
                  eGreTunnel5 (2308),
                  eGreTunnel6 (2309),
                  eGreTunnel7 (2310),
                  eGreTunnel8 (2311)
            }
    MAX-ACCESS read-write
    STATUS     current
    DESCRIPTION
            "-- empty --"
    ::= { hmSetupIpv6LanInterfacesEntry 2 }

-- {COLUMN} 1.3.6.1.4.1.248.32.18.2.70.6.1.3
hmSetupIpv6LanInterfacesEntryVlanId OBJECT-TYPE
    SYNTAX     Integer32 (0..65535)
    MAX-ACCESS read-write
    STATUS     current
    DESCRIPTION
            "-- empty --"
    ::= { hmSetupIpv6LanInterfacesEntry 3 }

-- {COLUMN} 1.3.6.1.4.1.248.32.18.2.70.6.1.4
hmSetupIpv6LanInterfacesEntryRtgTag OBJECT-TYPE
    SYNTAX     Integer32 (0..65535)
    MAX-ACCESS read-write
    STATUS     current
    DESCRIPTION
            "-- empty --"
    ::= { hmSetupIpv6LanInterfacesEntry 4 }

-- {COLUMN} 1.3.6.1.4.1.248.32.18.2.70.6.1.5
hmSetupIpv6LanInterfacesEntryAutoconf OBJECT-TYPE
    SYNTAX     INTEGER {
                  eYes (0),
                  eNo (1)
            }
    MAX-ACCESS read-write
    STATUS     current
    DESCRIPTION
            "-- empty --"
    ::= { hmSetupIpv6LanInterfacesEntry 5 }

-- {COLUMN} 1.3.6.1.4.1.248.32.18.2.70.6.1.6
hmSetupIpv6LanInterfacesEntryAcceptRa OBJECT-TYPE
    SYNTAX     INTEGER {
                  eYes (0),
                  eNo (1)
            }
    MAX-ACCESS read-write
    STATUS     current
    DESCRIPTION
            "-- empty --"
    ::= { hmSetupIpv6LanInterfacesEntry 6 }

-- {COLUMN} 1.3.6.1.4.1.248.32.18.2.70.6.1.7
hmSetupIpv6LanInterfacesEntryInterfaceStatus OBJECT-TYPE
    SYNTAX     INTEGER {
                  eUp (1),
                  eDown (2)
            }
    MAX-ACCESS read-write
    STATUS     current
    DESCRIPTION
            "-- empty --"
    ::= { hmSetupIpv6LanInterfacesEntry 7 }

-- {COLUMN} 1.3.6.1.4.1.248.32.18.2.70.6.1.8
hmSetupIpv6LanInterfacesEntryForwarding OBJECT-TYPE
    SYNTAX     INTEGER {
                  eYes (0),
                  eNo (1)
            }
    MAX-ACCESS read-write
    STATUS     current
    DESCRIPTION
            "-- empty --"
    ::= { hmSetupIpv6LanInterfacesEntry 8 }

-- {COLUMN} 1.3.6.1.4.1.248.32.18.2.70.6.1.9
hmSetupIpv6LanInterfacesEntryMtu OBJECT-TYPE
    SYNTAX     Integer32 (0..65535)
    MAX-ACCESS read-write
    STATUS     current
    DESCRIPTION
            "-- empty --"
    ::= { hmSetupIpv6LanInterfacesEntry 9 }

-- {COLUMN} 1.3.6.1.4.1.248.32.18.2.70.6.1.10
hmSetupIpv6LanInterfacesEntryFirewall OBJECT-TYPE
    SYNTAX     INTEGER {
                  eYes (0),
                  eNo (1)
            }
    MAX-ACCESS read-write
    STATUS     current
    DESCRIPTION
            "-- empty --"
    ::= { hmSetupIpv6LanInterfacesEntry 10 }

-- {COLUMN} 1.3.6.1.4.1.248.32.18.2.70.6.1.11
hmSetupIpv6LanInterfacesEntryComment OBJECT-TYPE
    SYNTAX     DisplayString (SIZE(0..64))
    MAX-ACCESS read-write
    STATUS     current
    DESCRIPTION
            "-- empty --"
    ::= { hmSetupIpv6LanInterfacesEntry 11 }

-- {COLUMN} 1.3.6.1.4.1.248.32.18.2.70.6.1.12
hmSetupIpv6LanInterfacesEntryDadAttempts OBJECT-TYPE
    SYNTAX     Integer32 (0..255)
    MAX-ACCESS read-write
    STATUS     current
    DESCRIPTION
            "-- empty --"
    ::= { hmSetupIpv6LanInterfacesEntry 12 }

-- {COLUMN} 1.3.6.1.4.1.248.32.18.2.70.6.1.13
hmSetupIpv6LanInterfacesEntryRsCount OBJECT-TYPE
    SYNTAX     Integer32 (0..255)
    MAX-ACCESS read-write
    STATUS     current
    DESCRIPTION
            "-- empty --"
    ::= { hmSetupIpv6LanInterfacesEntry 13 }

-- {TABLE} 1.3.6.1.4.1.248.32.18.2.70.7
hmSetupIpv6WanInterfacesTable OBJECT-TYPE
    SYNTAX     SEQUENCE OF HmSetupIpv6WanInterfacesEntry
    MAX-ACCESS not-accessible
    STATUS     current
    DESCRIPTION
            "-- empty --"
    ::= { hmSetupIpv6 7 }

-- {ROW} 1.3.6.1.4.1.248.32.18.2.70.7.1
hmSetupIpv6WanInterfacesEntry OBJECT-TYPE
    SYNTAX     HmSetupIpv6WanInterfacesEntry
    MAX-ACCESS not-accessible
    STATUS     current
    DESCRIPTION
            ""
    INDEX {
            hmSetupIpv6WanInterfacesEntryInterfaceName
          }
    ::= { hmSetupIpv6WanInterfacesTable 1 }

HmSetupIpv6WanInterfacesEntry ::= SEQUENCE {
            hmSetupIpv6WanInterfacesEntryInterfaceName DisplayString,
            hmSetupIpv6WanInterfacesEntryRtgTag Integer32,
            hmSetupIpv6WanInterfacesEntryAutoconf INTEGER,
            hmSetupIpv6WanInterfacesEntryAcceptRa INTEGER,
            hmSetupIpv6WanInterfacesEntryInterfaceStatus INTEGER,
            hmSetupIpv6WanInterfacesEntryForwarding INTEGER,
            hmSetupIpv6WanInterfacesEntryFirewall INTEGER,
            hmSetupIpv6WanInterfacesEntryComment DisplayString,
            hmSetupIpv6WanInterfacesEntryDadAttempts Integer32,
            hmSetupIpv6WanInterfacesEntryPdMode INTEGER,
            hmSetupIpv6WanInterfacesEntryRsCount Integer32
    }

-- {COLUMN} 1.3.6.1.4.1.248.32.18.2.70.7.1.1
hmSetupIpv6WanInterfacesEntryInterfaceName OBJECT-TYPE
    SYNTAX     DisplayString (SIZE(0..16))
    MAX-ACCESS read-write
    STATUS     current
    DESCRIPTION
            "-- empty --"
    ::= { hmSetupIpv6WanInterfacesEntry 1 }

-- {COLUMN} 1.3.6.1.4.1.248.32.18.2.70.7.1.2
hmSetupIpv6WanInterfacesEntryRtgTag OBJECT-TYPE
    SYNTAX     Integer32 (0..65535)
    MAX-ACCESS read-write
    STATUS     current
    DESCRIPTION
            "-- empty --"
    ::= { hmSetupIpv6WanInterfacesEntry 2 }

-- {COLUMN} 1.3.6.1.4.1.248.32.18.2.70.7.1.3
hmSetupIpv6WanInterfacesEntryAutoconf OBJECT-TYPE
    SYNTAX     INTEGER {
                  eYes (0),
                  eNo (1)
            }
    MAX-ACCESS read-write
    STATUS     current
    DESCRIPTION
            "-- empty --"
    ::= { hmSetupIpv6WanInterfacesEntry 3 }

-- {COLUMN} 1.3.6.1.4.1.248.32.18.2.70.7.1.4
hmSetupIpv6WanInterfacesEntryAcceptRa OBJECT-TYPE
    SYNTAX     INTEGER {
                  eYes (0),
                  eNo (1)
            }
    MAX-ACCESS read-write
    STATUS     current
    DESCRIPTION
            "-- empty --"
    ::= { hmSetupIpv6WanInterfacesEntry 4 }

-- {COLUMN} 1.3.6.1.4.1.248.32.18.2.70.7.1.5
hmSetupIpv6WanInterfacesEntryInterfaceStatus OBJECT-TYPE
    SYNTAX     INTEGER {
                  eUp (1),
                  eDown (2)
            }
    MAX-ACCESS read-write
    STATUS     current
    DESCRIPTION
            "-- empty --"
    ::= { hmSetupIpv6WanInterfacesEntry 5 }

-- {COLUMN} 1.3.6.1.4.1.248.32.18.2.70.7.1.6
hmSetupIpv6WanInterfacesEntryForwarding OBJECT-TYPE
    SYNTAX     INTEGER {
                  eYes (0),
                  eNo (1)
            }
    MAX-ACCESS read-write
    STATUS     current
    DESCRIPTION
            "-- empty --"
    ::= { hmSetupIpv6WanInterfacesEntry 6 }

-- {COLUMN} 1.3.6.1.4.1.248.32.18.2.70.7.1.7
hmSetupIpv6WanInterfacesEntryFirewall OBJECT-TYPE
    SYNTAX     INTEGER {
                  eYes (0),
                  eNo (1)
            }
    MAX-ACCESS read-write
    STATUS     current
    DESCRIPTION
            "-- empty --"
    ::= { hmSetupIpv6WanInterfacesEntry 7 }

-- {COLUMN} 1.3.6.1.4.1.248.32.18.2.70.7.1.8
hmSetupIpv6WanInterfacesEntryComment OBJECT-TYPE
    SYNTAX     DisplayString (SIZE(0..64))
    MAX-ACCESS read-write
    STATUS     current
    DESCRIPTION
            "-- empty --"
    ::= { hmSetupIpv6WanInterfacesEntry 8 }

-- {COLUMN} 1.3.6.1.4.1.248.32.18.2.70.7.1.9
hmSetupIpv6WanInterfacesEntryDadAttempts OBJECT-TYPE
    SYNTAX     Integer32 (0..255)
    MAX-ACCESS read-write
    STATUS     current
    DESCRIPTION
            "-- empty --"
    ::= { hmSetupIpv6WanInterfacesEntry 9 }

-- {COLUMN} 1.3.6.1.4.1.248.32.18.2.70.7.1.10
hmSetupIpv6WanInterfacesEntryPdMode OBJECT-TYPE
    SYNTAX     INTEGER {
                  eDhcpv6 (0),
                  eRouterAdv (1)
            }
    MAX-ACCESS read-write
    STATUS     current
    DESCRIPTION
            "-- empty --"
    ::= { hmSetupIpv6WanInterfacesEntry 10 }

-- {COLUMN} 1.3.6.1.4.1.248.32.18.2.70.7.1.11
hmSetupIpv6WanInterfacesEntryRsCount OBJECT-TYPE
    SYNTAX     Integer32 (0..255)
    MAX-ACCESS read-write
    STATUS     current
    DESCRIPTION
            "-- empty --"
    ::= { hmSetupIpv6WanInterfacesEntry 11 }

-- {SCALAR} 1.3.6.1.4.1.248.32.18.2.70.10
hmSetupIpv6Operating OBJECT-TYPE
    SYNTAX     INTEGER {
                  eNo (0),
                  eYes (1)
            }
    MAX-ACCESS read-write
    STATUS     current
    DESCRIPTION
            "-- empty --"
    ::= { hmSetupIpv6 10 }

-- {SCALAR} 1.3.6.1.4.1.248.32.18.2.70.11
hmSetupIpv6Forwarding OBJECT-TYPE
    SYNTAX     INTEGER {
                  eNo (0),
                  eYes (1)
            }
    MAX-ACCESS read-write
    STATUS     current
    DESCRIPTION
            "-- empty --"
    ::= { hmSetupIpv6 11 }

-- {NODE} 1.3.6.1.4.1.248.32.18.2.70.12
hmSetupIpv6Router OBJECT IDENTIFIER ::= { hmSetupIpv6 12 }

-- {TABLE} 1.3.6.1.4.1.248.32.18.2.70.12.1
hmSetupIpv6RouterRoutingTableTable OBJECT-TYPE
    SYNTAX     SEQUENCE OF HmSetupIpv6RouterRoutingTableEntry
    MAX-ACCESS not-accessible
    STATUS     current
    DESCRIPTION
            "-- empty --"
    ::= { hmSetupIpv6Router 1 }

-- {ROW} 1.3.6.1.4.1.248.32.18.2.70.12.1.1
hmSetupIpv6RouterRoutingTableEntry OBJECT-TYPE
    SYNTAX     HmSetupIpv6RouterRoutingTableEntry
    MAX-ACCESS not-accessible
    STATUS     current
    DESCRIPTION
            ""
    INDEX {
            hmSetupIpv6RouterRoutingTableEntryPrefix,
            hmSetupIpv6RouterRoutingTableEntryRtgTag
          }
    ::= { hmSetupIpv6RouterRoutingTableTable 1 }

HmSetupIpv6RouterRoutingTableEntry ::= SEQUENCE {
            hmSetupIpv6RouterRoutingTableEntryPrefix DisplayString,
            hmSetupIpv6RouterRoutingTableEntryRtgTag Integer32,
            hmSetupIpv6RouterRoutingTableEntryPeerOrIpv6 DisplayString,
            hmSetupIpv6RouterRoutingTableEntryComment DisplayString
    }

-- {COLUMN} 1.3.6.1.4.1.248.32.18.2.70.12.1.1.1
hmSetupIpv6RouterRoutingTableEntryPrefix OBJECT-TYPE
    SYNTAX     DisplayString (SIZE(0..43))
    MAX-ACCESS read-write
    STATUS     current
    DESCRIPTION
            "-- empty --"
    ::= { hmSetupIpv6RouterRoutingTableEntry 1 }

-- {COLUMN} 1.3.6.1.4.1.248.32.18.2.70.12.1.1.2
hmSetupIpv6RouterRoutingTableEntryRtgTag OBJECT-TYPE
    SYNTAX     Integer32 (0..65535)
    MAX-ACCESS read-write
    STATUS     current
    DESCRIPTION
            "-- empty --"
    ::= { hmSetupIpv6RouterRoutingTableEntry 2 }

-- {COLUMN} 1.3.6.1.4.1.248.32.18.2.70.12.1.1.3
hmSetupIpv6RouterRoutingTableEntryPeerOrIpv6 OBJECT-TYPE
    SYNTAX     DisplayString (SIZE(0..56))
    MAX-ACCESS read-write
    STATUS     current
    DESCRIPTION
            "-- empty --"
    ::= { hmSetupIpv6RouterRoutingTableEntry 3 }

-- {COLUMN} 1.3.6.1.4.1.248.32.18.2.70.12.1.1.4
hmSetupIpv6RouterRoutingTableEntryComment OBJECT-TYPE
    SYNTAX     DisplayString (SIZE(0..64))
    MAX-ACCESS read-write
    STATUS     current
    DESCRIPTION
            "-- empty --"
    ::= { hmSetupIpv6RouterRoutingTableEntry 4 }

-- {SCALAR} 1.3.6.1.4.1.248.32.18.2.70.12.2
hmSetupIpv6RouterDestCacheTimeout OBJECT-TYPE
    SYNTAX     Integer32 (0..65535)
    MAX-ACCESS read-write
    STATUS     current
    DESCRIPTION
            "-- empty --"
    ::= { hmSetupIpv6Router 2 }

-- {TABLE} 1.3.6.1.4.1.248.32.18.2.70.13
hmSetupIpv6Icmpv6Table OBJECT-TYPE
    SYNTAX     SEQUENCE OF HmSetupIpv6Icmpv6Entry
    MAX-ACCESS not-accessible
    STATUS     current
    DESCRIPTION
            "-- empty --"
    ::= { hmSetupIpv6 13 }

-- {ROW} 1.3.6.1.4.1.248.32.18.2.70.13.1
hmSetupIpv6Icmpv6Entry OBJECT-TYPE
    SYNTAX     HmSetupIpv6Icmpv6Entry
    MAX-ACCESS not-accessible
    STATUS     current
    DESCRIPTION
            ""
    INDEX {
            hmSetupIpv6Icmpv6EntryInterfaceName
          }
    ::= { hmSetupIpv6Icmpv6Table 1 }

HmSetupIpv6Icmpv6Entry ::= SEQUENCE {
            hmSetupIpv6Icmpv6EntryInterfaceName DisplayString,
            hmSetupIpv6Icmpv6EntryErrorBandwidth Integer32,
            hmSetupIpv6Icmpv6EntryRedirects INTEGER
    }

-- {COLUMN} 1.3.6.1.4.1.248.32.18.2.70.13.1.1
hmSetupIpv6Icmpv6EntryInterfaceName OBJECT-TYPE
    SYNTAX     DisplayString (SIZE(0..16))
    MAX-ACCESS read-write
    STATUS     current
    DESCRIPTION
            "-- empty --"
    ::= { hmSetupIpv6Icmpv6Entry 1 }

-- {COLUMN} 1.3.6.1.4.1.248.32.18.2.70.13.1.2
hmSetupIpv6Icmpv6EntryErrorBandwidth OBJECT-TYPE
    SYNTAX     Integer32 (0..2147483647)
    MAX-ACCESS read-write
    STATUS     current
    DESCRIPTION
            "-- empty --"
    ::= { hmSetupIpv6Icmpv6Entry 2 }

-- {COLUMN} 1.3.6.1.4.1.248.32.18.2.70.13.1.3
hmSetupIpv6Icmpv6EntryRedirects OBJECT-TYPE
    SYNTAX     INTEGER {
                  eDisable (0),
                  eEnable (1)
            }
    MAX-ACCESS read-write
    STATUS     current
    DESCRIPTION
            "-- empty --"
    ::= { hmSetupIpv6Icmpv6Entry 3 }

-- {TABLE} 1.3.6.1.4.1.248.32.18.2.70.14
hmSetupIpv6RasInterfacesTable OBJECT-TYPE
    SYNTAX     SEQUENCE OF HmSetupIpv6RasInterfacesEntry
    MAX-ACCESS not-accessible
    STATUS     current
    DESCRIPTION
            "-- empty --"
    ::= { hmSetupIpv6 14 }

-- {ROW} 1.3.6.1.4.1.248.32.18.2.70.14.1
hmSetupIpv6RasInterfacesEntry OBJECT-TYPE
    SYNTAX     HmSetupIpv6RasInterfacesEntry
    MAX-ACCESS not-accessible
    STATUS     current
    DESCRIPTION
            ""
    INDEX {
            hmSetupIpv6RasInterfacesEntryInterfaceName
          }
    ::= { hmSetupIpv6RasInterfacesTable 1 }

HmSetupIpv6RasInterfacesEntry ::= SEQUENCE {
            hmSetupIpv6RasInterfacesEntryInterfaceName DisplayString,
            hmSetupIpv6RasInterfacesEntryRtgTag Integer32,
            hmSetupIpv6RasInterfacesEntryInterfaceStatus INTEGER,
            hmSetupIpv6RasInterfacesEntryForwarding INTEGER,
            hmSetupIpv6RasInterfacesEntryFirewall INTEGER,
            hmSetupIpv6RasInterfacesEntryDadAttempts Integer32,
            hmSetupIpv6RasInterfacesEntryPeerName DisplayString,
            hmSetupIpv6RasInterfacesEntryComment DisplayString
    }

-- {COLUMN} 1.3.6.1.4.1.248.32.18.2.70.14.1.1
hmSetupIpv6RasInterfacesEntryInterfaceName OBJECT-TYPE
    SYNTAX     DisplayString (SIZE(0..16))
    MAX-ACCESS read-write
    STATUS     current
    DESCRIPTION
            "-- empty --"
    ::= { hmSetupIpv6RasInterfacesEntry 1 }

-- {COLUMN} 1.3.6.1.4.1.248.32.18.2.70.14.1.2
hmSetupIpv6RasInterfacesEntryRtgTag OBJECT-TYPE
    SYNTAX     Integer32 (0..65535)
    MAX-ACCESS read-write
    STATUS     current
    DESCRIPTION
            "-- empty --"
    ::= { hmSetupIpv6RasInterfacesEntry 2 }

-- {COLUMN} 1.3.6.1.4.1.248.32.18.2.70.14.1.3
hmSetupIpv6RasInterfacesEntryInterfaceStatus OBJECT-TYPE
    SYNTAX     INTEGER {
                  eUp (1),
                  eDown (2)
            }
    MAX-ACCESS read-write
    STATUS     current
    DESCRIPTION
            "-- empty --"
    ::= { hmSetupIpv6RasInterfacesEntry 3 }

-- {COLUMN} 1.3.6.1.4.1.248.32.18.2.70.14.1.4
hmSetupIpv6RasInterfacesEntryForwarding OBJECT-TYPE
    SYNTAX     INTEGER {
                  eYes (0),
                  eNo (1)
            }
    MAX-ACCESS read-write
    STATUS     current
    DESCRIPTION
            "-- empty --"
    ::= { hmSetupIpv6RasInterfacesEntry 4 }

-- {COLUMN} 1.3.6.1.4.1.248.32.18.2.70.14.1.5
hmSetupIpv6RasInterfacesEntryFirewall OBJECT-TYPE
    SYNTAX     INTEGER {
                  eYes (0),
                  eNo (1)
            }
    MAX-ACCESS read-write
    STATUS     current
    DESCRIPTION
            "-- empty --"
    ::= { hmSetupIpv6RasInterfacesEntry 5 }

-- {COLUMN} 1.3.6.1.4.1.248.32.18.2.70.14.1.6
hmSetupIpv6RasInterfacesEntryDadAttempts OBJECT-TYPE
    SYNTAX     Integer32 (0..255)
    MAX-ACCESS read-write
    STATUS     current
    DESCRIPTION
            "-- empty --"
    ::= { hmSetupIpv6RasInterfacesEntry 6 }

-- {COLUMN} 1.3.6.1.4.1.248.32.18.2.70.14.1.7
hmSetupIpv6RasInterfacesEntryPeerName OBJECT-TYPE
    SYNTAX     DisplayString (SIZE(0..16))
    MAX-ACCESS read-write
    STATUS     current
    DESCRIPTION
            "-- empty --"
    ::= { hmSetupIpv6RasInterfacesEntry 7 }

-- {COLUMN} 1.3.6.1.4.1.248.32.18.2.70.14.1.8
hmSetupIpv6RasInterfacesEntryComment OBJECT-TYPE
    SYNTAX     DisplayString (SIZE(0..64))
    MAX-ACCESS read-write
    STATUS     current
    DESCRIPTION
            "-- empty --"
    ::= { hmSetupIpv6RasInterfacesEntry 8 }

-- {NODE} 1.3.6.1.4.1.248.32.18.2.80
hmSetupRelays OBJECT IDENTIFIER ::= { hmSetup 80 }

-- {SCALAR} 1.3.6.1.4.1.248.32.18.2.80.1
hmSetupRelaysRelay1 OBJECT-TYPE
    SYNTAX     INTEGER {
                  eNo (0),
                  eYes (1)
            }
    MAX-ACCESS read-write
    STATUS     current
    DESCRIPTION
            "-- empty --"
    ::= { hmSetupRelays 1 }

-- {SCALAR} 1.3.6.1.4.1.248.32.18.2.80.2
hmSetupRelaysRelay2 OBJECT-TYPE
    SYNTAX     INTEGER {
                  eNo (0),
                  eYes (1)
            }
    MAX-ACCESS read-write
    STATUS     current
    DESCRIPTION
            "-- empty --"
    ::= { hmSetupRelays 2 }

-- {NODE} 1.3.6.1.4.1.248.32.18.2.82
hmSetupCrypto OBJECT IDENTIFIER ::= { hmSetup 82 }

-- {NODE} 1.3.6.1.4.1.248.32.18.2.82.1
hmSetupCryptoRng OBJECT IDENTIFIER ::= { hmSetupCrypto 1 }

-- {SCALAR} 1.3.6.1.4.1.248.32.18.2.82.1.1
hmSetupCryptoRngSeed OBJECT-TYPE
    SYNTAX     DisplayString
    MAX-ACCESS read-write
    STATUS     current
    DESCRIPTION
            "-- empty --"
    ::= { hmSetupCryptoRng 1 }

-- {SCALAR} 1.3.6.1.4.1.248.32.18.2.82.1.2
hmSetupCryptoRngReseed OBJECT-TYPE
    SYNTAX     DisplayString
    MAX-ACCESS read-write
    STATUS     current
    DESCRIPTION
            "-- empty --"
    ::= { hmSetupCryptoRng 2 }

-- {SCALAR} 1.3.6.1.4.1.248.32.18.2.82.1.3
hmSetupCryptoRngReset OBJECT-TYPE
    SYNTAX     DisplayString
    MAX-ACCESS read-write
    STATUS     current
    DESCRIPTION
            "-- empty --"
    ::= { hmSetupCryptoRng 3 }

-- {SCALAR} 1.3.6.1.4.1.248.32.18.2.82.1.4
hmSetupCryptoRngWriteInterval OBJECT-TYPE
    SYNTAX     Integer32 (0..2147483647)
    MAX-ACCESS read-only
    STATUS     current
    DESCRIPTION
            "-- empty --"
    ::= { hmSetupCryptoRng 4 }

-- {NODE} 1.3.6.1.4.1.248.32.18.3
hmFirmware OBJECT IDENTIFIER ::= { bat54rail 3 }

-- {TABLE} 1.3.6.1.4.1.248.32.18.3.1
hmFirmwareVersionTableTable OBJECT-TYPE
    SYNTAX     SEQUENCE OF HmFirmwareVersionTableEntry
    MAX-ACCESS not-accessible
    STATUS     current
    DESCRIPTION
            "-- empty --"
    ::= { hmFirmware 1 }

-- {ROW} 1.3.6.1.4.1.248.32.18.3.1.1
hmFirmwareVersionTableEntry OBJECT-TYPE
    SYNTAX     HmFirmwareVersionTableEntry
    MAX-ACCESS not-accessible
    STATUS     current
    DESCRIPTION
            ""
    INDEX {
            hmFirmwareVersionTableEntryIfc
          }
    ::= { hmFirmwareVersionTableTable 1 }

HmFirmwareVersionTableEntry ::= SEQUENCE {
            hmFirmwareVersionTableEntryIfc INTEGER,
            hmFirmwareVersionTableEntryModule DisplayString,
            hmFirmwareVersionTableEntryVersion DisplayString,
            hmFirmwareVersionTableEntrySerialNumber DisplayString
    }

-- {COLUMN} 1.3.6.1.4.1.248.32.18.3.1.1.1
hmFirmwareVersionTableEntryIfc OBJECT-TYPE
    SYNTAX     INTEGER {
                  eIfc (1)
            }
    MAX-ACCESS read-only
    STATUS     current
    DESCRIPTION
            "-- empty --"
    ::= { hmFirmwareVersionTableEntry 1 }

-- {COLUMN} 1.3.6.1.4.1.248.32.18.3.1.1.2
hmFirmwareVersionTableEntryModule OBJECT-TYPE
    SYNTAX     DisplayString (SIZE(0..64))
    MAX-ACCESS read-only
    STATUS     current
    DESCRIPTION
            "-- empty --"
    ::= { hmFirmwareVersionTableEntry 2 }

-- {COLUMN} 1.3.6.1.4.1.248.32.18.3.1.1.3
hmFirmwareVersionTableEntryVersion OBJECT-TYPE
    SYNTAX     DisplayString (SIZE(0..30))
    MAX-ACCESS read-only
    STATUS     current
    DESCRIPTION
            "-- empty --"
    ::= { hmFirmwareVersionTableEntry 3 }

-- {COLUMN} 1.3.6.1.4.1.248.32.18.3.1.1.4
hmFirmwareVersionTableEntrySerialNumber OBJECT-TYPE
    SYNTAX     DisplayString (SIZE(0..19))
    MAX-ACCESS read-only
    STATUS     current
    DESCRIPTION
            "-- empty --"
    ::= { hmFirmwareVersionTableEntry 4 }

-- {TABLE} 1.3.6.1.4.1.248.32.18.3.2
hmFirmwareTableFirmsafeTable OBJECT-TYPE
    SYNTAX     SEQUENCE OF HmFirmwareTableFirmsafeEntry
    MAX-ACCESS not-accessible
    STATUS     current
    DESCRIPTION
            "-- empty --"
    ::= { hmFirmware 2 }

-- {ROW} 1.3.6.1.4.1.248.32.18.3.2.1
hmFirmwareTableFirmsafeEntry OBJECT-TYPE
    SYNTAX     HmFirmwareTableFirmsafeEntry
    MAX-ACCESS not-accessible
    STATUS     current
    DESCRIPTION
            ""
    INDEX {
            hmFirmwareTableFirmsafeEntryPosition
          }
    ::= { hmFirmwareTableFirmsafeTable 1 }

HmFirmwareTableFirmsafeEntry ::= SEQUENCE {
            hmFirmwareTableFirmsafeEntryPosition Integer32,
            hmFirmwareTableFirmsafeEntryStatus INTEGER,
            hmFirmwareTableFirmsafeEntryVersion DisplayString,
            hmFirmwareTableFirmsafeEntryDate DisplayString,
            hmFirmwareTableFirmsafeEntrySize Integer32,
            hmFirmwareTableFirmsafeEntryIndex Integer32
    }

-- {COLUMN} 1.3.6.1.4.1.248.32.18.3.2.1.1
hmFirmwareTableFirmsafeEntryPosition OBJECT-TYPE
    SYNTAX     Integer32 (0..255)
    MAX-ACCESS read-only
    STATUS     current
    DESCRIPTION
            "-- empty --"
    ::= { hmFirmwareTableFirmsafeEntry 1 }

-- {COLUMN} 1.3.6.1.4.1.248.32.18.3.2.1.2
hmFirmwareTableFirmsafeEntryStatus OBJECT-TYPE
    SYNTAX     INTEGER {
                  eInactive (0),
                  eActive (1),
                  eLoader (2),
                  eMinimalPlusInactive (4),
                  eMinimalPlusActive (5)
            }
    MAX-ACCESS read-write
    STATUS     current
    DESCRIPTION
            "-- empty --"
    ::= { hmFirmwareTableFirmsafeEntry 2 }

-- {COLUMN} 1.3.6.1.4.1.248.32.18.3.2.1.3
hmFirmwareTableFirmsafeEntryVersion OBJECT-TYPE
    SYNTAX     DisplayString (SIZE(0..17))
    MAX-ACCESS read-only
    STATUS     current
    DESCRIPTION
            "-- empty --"
    ::= { hmFirmwareTableFirmsafeEntry 3 }

-- {COLUMN} 1.3.6.1.4.1.248.32.18.3.2.1.4
hmFirmwareTableFirmsafeEntryDate OBJECT-TYPE
    SYNTAX     DisplayString (SIZE(0..9))
    MAX-ACCESS read-only
    STATUS     current
    DESCRIPTION
            "-- empty --"
    ::= { hmFirmwareTableFirmsafeEntry 4 }

-- {COLUMN} 1.3.6.1.4.1.248.32.18.3.2.1.5
hmFirmwareTableFirmsafeEntrySize OBJECT-TYPE
    SYNTAX     Integer32 (0..2147483647)
    MAX-ACCESS read-only
    STATUS     current
    DESCRIPTION
            "-- empty --"
    ::= { hmFirmwareTableFirmsafeEntry 5 }

-- {COLUMN} 1.3.6.1.4.1.248.32.18.3.2.1.6
hmFirmwareTableFirmsafeEntryIndex OBJECT-TYPE
    SYNTAX     Integer32 (0..2147483647)
    MAX-ACCESS read-only
    STATUS     current
    DESCRIPTION
            "-- empty --"
    ::= { hmFirmwareTableFirmsafeEntry 6 }

-- {SCALAR} 1.3.6.1.4.1.248.32.18.3.3
hmFirmwareModeFirmsafe OBJECT-TYPE
    SYNTAX     INTEGER {
                  eImmediate (0),
                  eLogin (1),
                  eManual (2)
            }
    MAX-ACCESS read-write
    STATUS     current
    DESCRIPTION
            "-- empty --"
    ::= { hmFirmware 3 }

-- {SCALAR} 1.3.6.1.4.1.248.32.18.3.4
hmFirmwareTimeoutFirmsafe OBJECT-TYPE
    SYNTAX     Integer32 (0..65535)
    MAX-ACCESS read-write
    STATUS     current
    DESCRIPTION
            "-- empty --"
    ::= { hmFirmware 4 }

-- {NODE} 1.3.6.1.4.1.248.32.18.3.5
hmFirmwareSecureUpload OBJECT IDENTIFIER ::= { hmFirmware 5 }

-- {SCALAR} 1.3.6.1.4.1.248.32.18.3.5.4
hmFirmwareSecureUploadLtkHash OBJECT-TYPE
    SYNTAX     OCTET STRING
    MAX-ACCESS read-only
    STATUS     current
    DESCRIPTION
            "-- empty --"
    ::= { hmFirmwareSecureUpload 4 }

-- {SCALAR} 1.3.6.1.4.1.248.32.18.3.7
hmFirmwareFeatureWord OBJECT-TYPE
    SYNTAX     DisplayString (SIZE(0..34))
    MAX-ACCESS read-only
    STATUS     current
    DESCRIPTION
            "-- empty --"
    ::= { hmFirmware 7 }

-- {NODE} 1.3.6.1.4.1.248.32.18.4
hmOther OBJECT IDENTIFIER ::= { bat54rail 4 }

-- {NODE} 1.3.6.1.4.1.248.32.18.4.1
hmOtherManualDialing OBJECT IDENTIFIER ::= { hmOther 1 }

-- {SCALAR} 1.3.6.1.4.1.248.32.18.4.1.1
hmOtherManualDialingConnect OBJECT-TYPE
    SYNTAX     DisplayString
    MAX-ACCESS read-write
    STATUS     current
    DESCRIPTION
            "-- empty --"
    ::= { hmOtherManualDialing 1 }

-- {SCALAR} 1.3.6.1.4.1.248.32.18.4.1.2
hmOtherManualDialingDisconnect OBJECT-TYPE
    SYNTAX     DisplayString
    MAX-ACCESS read-write
    STATUS     current
    DESCRIPTION
            "-- empty --"
    ::= { hmOtherManualDialing 2 }

-- {SCALAR} 1.3.6.1.4.1.248.32.18.4.2
hmOtherBootSystem OBJECT-TYPE
    SYNTAX     DisplayString
    MAX-ACCESS read-write
    STATUS     current
    DESCRIPTION
            "-- empty --"
    ::= { hmOther 2 }

-- {SCALAR} 1.3.6.1.4.1.248.32.18.4.5
hmOtherColdBoot OBJECT-TYPE
    SYNTAX     DisplayString
    MAX-ACCESS read-write
    STATUS     current
    DESCRIPTION
            "-- empty --"
    ::= { hmOther 5 }

-- {SCALAR} 1.3.6.1.4.1.248.32.18.4.7
hmOtherFlashRestore OBJECT-TYPE
    SYNTAX     DisplayString
    MAX-ACCESS read-write
    STATUS     current
    DESCRIPTION
            "-- empty --"
    ::= { hmOther 7 }

-- {NODE} 1.3.6.1.4.1.248.32.18.8
hmWlanProducts OBJECT IDENTIFIER ::= { bat54rail 8 }

-- {NODE} 1.3.6.1.4.1.248.32.18.8.128
batControllerWlc25 OBJECT IDENTIFIER ::= { hmWlanProducts 128 }

-- {NODE} 1.3.6.1.4.1.248.32.18.8.200
batR OBJECT IDENTIFIER ::= { hmWlanProducts 200 }

-- {NODE} 1.3.6.1.4.1.248.32.18.8.300
batF OBJECT IDENTIFIER ::= { hmWlanProducts 300 }

-- {NODE} 1.3.6.1.4.1.248.32.18.8.400
bat450F OBJECT IDENTIFIER ::= { hmWlanProducts 400 }

--
-- NOTIFICATIONS
--
-- {NOTIFICATION} 1.3.6.1.4.1.248.32.18.0.0.1
hmTrapsStatChan NOTIFICATION-TYPE
    OBJECTS {
            sysDescr,
            sysName,
            hmStatusSnmpEventEntryCount,
            hmStatusWanConnections,
            hmStatusChannelEntryState,
            hmStatusChannelEntryApp,
            hmStatusChannelEntryMode,
            hmStatusChannelEntryCause,
            hmStatusChannelEntryNumber,
            hmStatusChannelEntrySubaddress,
            hmStatusChannelEntryCharge,
            hmStatusChannelEntryExtra,
            hmStatusChannelEntryConnTime,
            hmStatusChannelEntryConnStart,
            hmStatusChannelEntryIsdnDisplay,
            hmStatusChannelEntryPhChan,
            hmStatusChannelEntryPptpConns,
            hmStatusChannelEntryVpnConns
          }
    STATUS     current
    DESCRIPTION
            "WAN connection status"
    ::= { hmTraps 1 }

-- {NOTIFICATION} 1.3.6.1.4.1.248.32.18.0.0.4
hmTrapsFwUplStart NOTIFICATION-TYPE
    OBJECTS {
            sysDescr,
            sysName,
            hmStatusSnmpEventEntryCount,
            hmStatusConfigEventLogEntrySystemTime,
            hmStatusConfigEventLogEntryEvent,
            hmStatusConfigEventLogEntryAccess,
            hmStatusConfigEventLogEntryIpAddressNew,
            hmStatusConfigEventLogEntryIpAddress
          }
    STATUS     current
    DESCRIPTION
            "Firmware upload was started"
    ::= { hmTraps 4 }

-- {NOTIFICATION} 1.3.6.1.4.1.248.32.18.0.0.5
hmTrapsUplsucc NOTIFICATION-TYPE
    OBJECTS {
            sysDescr,
            sysName,
            hmStatusSnmpEventEntryCount,
            hmStatusConfigEventLogEntrySystemTime,
            hmStatusConfigEventLogEntryEvent,
            hmStatusConfigEventLogEntryAccess,
            hmStatusConfigEventLogEntryIpAddressNew,
            hmStatusConfigEventLogEntryIpAddress,
            hmStatusConfigEventLogEntryInfo1,
            hmStatusConfigEventLogEntryInfo2
          }
    STATUS     current
    DESCRIPTION
            "Firmware or configuration upload successful"
    ::= { hmTraps 5 }

-- {NOTIFICATION} 1.3.6.1.4.1.248.32.18.0.0.6
hmTrapsUplfailto NOTIFICATION-TYPE
    OBJECTS {
            sysDescr,
            sysName,
            hmStatusSnmpEventEntryCount,
            hmStatusConfigEventLogEntrySystemTime,
            hmStatusConfigEventLogEntryEvent,
            hmStatusConfigEventLogEntryAccess,
            hmStatusConfigEventLogEntryIpAddressNew,
            hmStatusConfigEventLogEntryIpAddress,
            hmStatusConfigEventLogEntryInfo1,
            hmStatusConfigEventLogEntryInfo2
          }
    STATUS     current
    DESCRIPTION
            "The upload the firmware or configuration failed: maximum time was exceeded"
    ::= { hmTraps 6 }

-- {NOTIFICATION} 1.3.6.1.4.1.248.32.18.0.0.7
hmTrapsUplfailincl NOTIFICATION-TYPE
    OBJECTS {
            sysDescr,
            sysName,
            hmStatusSnmpEventEntryCount,
            hmStatusConfigEventLogEntrySystemTime,
            hmStatusConfigEventLogEntryEvent,
            hmStatusConfigEventLogEntryAccess,
            hmStatusConfigEventLogEntryIpAddressNew,
            hmStatusConfigEventLogEntryIpAddress,
            hmStatusConfigEventLogEntryInfo1,
            hmStatusConfigEventLogEntryInfo2
          }
    STATUS     current
    DESCRIPTION
            "The upload the firmware or configuration failed: incomplete configuration"
    ::= { hmTraps 7 }

-- {NOTIFICATION} 1.3.6.1.4.1.248.32.18.0.0.8
hmTrapsUplfailbaddev NOTIFICATION-TYPE
    OBJECTS {
            sysDescr,
            sysName,
            hmStatusSnmpEventEntryCount,
            hmStatusConfigEventLogEntrySystemTime,
            hmStatusConfigEventLogEntryEvent,
            hmStatusConfigEventLogEntryAccess,
            hmStatusConfigEventLogEntryIpAddressNew,
            hmStatusConfigEventLogEntryIpAddress,
            hmStatusConfigEventLogEntryInfo1,
            hmStatusConfigEventLogEntryInfo2
          }
    STATUS     current
    DESCRIPTION
            "The upload the firmware or configuration failed: wrong device"
    ::= { hmTraps 8 }

-- {NOTIFICATION} 1.3.6.1.4.1.248.32.18.0.0.9
hmTrapsLogin NOTIFICATION-TYPE
    OBJECTS {
            sysDescr,
            sysName,
            hmStatusSnmpEventEntryCount,
            hmStatusConfigEventLogEntrySystemTime,
            hmStatusConfigEventLogEntryEvent,
            hmStatusConfigEventLogEntryAccess,
            hmStatusConfigEventLogEntryIpAddressNew,
            hmStatusConfigEventLogEntryIpAddress
          }
    STATUS     current
    DESCRIPTION
            "Login to configuration successful"
    ::= { hmTraps 9 }

-- {NOTIFICATION} 1.3.6.1.4.1.248.32.18.0.0.10
hmTrapsLogout NOTIFICATION-TYPE
    OBJECTS {
            sysDescr,
            sysName,
            hmStatusSnmpEventEntryCount,
            hmStatusConfigEventLogEntrySystemTime,
            hmStatusConfigEventLogEntryEvent,
            hmStatusConfigEventLogEntryAccess,
            hmStatusConfigEventLogEntryIpAddressNew,
            hmStatusConfigEventLogEntryIpAddress
          }
    STATUS     current
    DESCRIPTION
            "Logout from configuration was successful"
    ::= { hmTraps 10 }

-- {NOTIFICATION} 1.3.6.1.4.1.248.32.18.0.0.11
hmTrapsCnfuplstart NOTIFICATION-TYPE
    OBJECTS {
            sysDescr,
            sysName,
            hmStatusSnmpEventEntryCount,
            hmStatusConfigEventLogEntrySystemTime,
            hmStatusConfigEventLogEntryEvent,
            hmStatusConfigEventLogEntryAccess,
            hmStatusConfigEventLogEntryIpAddressNew,
            hmStatusConfigEventLogEntryIpAddress
          }
    STATUS     current
    DESCRIPTION
            "Configuration upload was started"
    ::= { hmTraps 11 }

-- {NOTIFICATION} 1.3.6.1.4.1.248.32.18.0.0.12
hmTrapsCnfdnlstart NOTIFICATION-TYPE
    OBJECTS {
            sysDescr,
            sysName,
            hmStatusSnmpEventEntryCount,
            hmStatusConfigEventLogEntrySystemTime,
            hmStatusConfigEventLogEntryEvent,
            hmStatusConfigEventLogEntryAccess,
            hmStatusConfigEventLogEntryIpAddressNew,
            hmStatusConfigEventLogEntryIpAddress
          }
    STATUS     current
    DESCRIPTION
            "Configuration download was started"
    ::= { hmTraps 12 }

-- {NOTIFICATION} 1.3.6.1.4.1.248.32.18.0.0.13
hmTrapsCnfdnlsucc NOTIFICATION-TYPE
    OBJECTS {
            sysDescr,
            sysName,
            hmStatusSnmpEventEntryCount,
            hmStatusConfigEventLogEntrySystemTime,
            hmStatusConfigEventLogEntryEvent,
            hmStatusConfigEventLogEntryAccess,
            hmStatusConfigEventLogEntryIpAddressNew,
            hmStatusConfigEventLogEntryIpAddress,
            hmStatusConfigEventLogEntryInfo1,
            hmStatusConfigEventLogEntryInfo2
          }
    STATUS     current
    DESCRIPTION
            "Configuration download successful"
    ::= { hmTraps 13 }

-- {NOTIFICATION} 1.3.6.1.4.1.248.32.18.0.0.14
hmTrapsBssscan NOTIFICATION-TYPE
    OBJECTS {
            sysDescr,
            sysName,
            hmStatusSnmpEventEntryCount,
            hmStatusWlanIfcsEntryIfc
          }
    STATUS     current
    DESCRIPTION
            "WLAN in client mode started initial scan for available networks"
    ::= { hmTraps 14 }

-- {NOTIFICATION} 1.3.6.1.4.1.248.32.18.0.0.15
hmTrapsBssstart NOTIFICATION-TYPE
    OBJECTS {
            sysDescr,
            sysName,
            hmStatusSnmpEventEntryCount,
            hmStatusWlanWlanParameterEntryIfc,
            hmStatusWlanNetworksEntryBssid
          }
    STATUS     current
    DESCRIPTION
            "WLAN in AP mode started operation"
    ::= { hmTraps 15 }

-- {NOTIFICATION} 1.3.6.1.4.1.248.32.18.0.0.16
hmTrapsBssjoin NOTIFICATION-TYPE
    OBJECTS {
            sysDescr,
            sysName,
            hmStatusSnmpEventEntryCount,
            hmStatusWlanWlanParameterEntryIfc,
            hmStatusWlanNetworksEntryBssid
          }
    STATUS     current
    DESCRIPTION
            "WLAN in client mode joined network"
    ::= { hmTraps 16 }

-- {NOTIFICATION} 1.3.6.1.4.1.248.32.18.0.0.17
hmTrapsAuthstation NOTIFICATION-TYPE
    OBJECTS {
            sysDescr,
            sysName,
            hmStatusSnmpEventEntryCount,
            hmStatusWlanStationTableEntryMacAddress,
            hmStatusWlanStationTableEntryIdentification
          }
    STATUS     current
    DESCRIPTION
            "WLAN client passed authentication phase"
    ::= { hmTraps 17 }

-- {NOTIFICATION} 1.3.6.1.4.1.248.32.18.0.0.18
hmTrapsDeauthstation NOTIFICATION-TYPE
    OBJECTS {
            sysDescr,
            sysName,
            hmStatusSnmpEventEntryCount,
            hmStatusWlanStationTableEntryMacAddress,
            hmStatusWlanStationTableEntryIdentification
          }
    STATUS     current
    DESCRIPTION
            "WLAN client was deauthenticated"
    ::= { hmTraps 18 }

-- {NOTIFICATION} 1.3.6.1.4.1.248.32.18.0.0.19
hmTrapsAssstation NOTIFICATION-TYPE
    OBJECTS {
            sysDescr,
            sysName,
            hmStatusSnmpEventEntryCount,
            hmStatusWlanStationTableEntryMacAddress,
            hmStatusWlanStationTableEntryIdentification
          }
    STATUS     current
    DESCRIPTION
            "WLAN client passed association phase"
    ::= { hmTraps 19 }

-- {NOTIFICATION} 1.3.6.1.4.1.248.32.18.0.0.20
hmTrapsReassstation NOTIFICATION-TYPE
    OBJECTS {
            sysDescr,
            sysName,
            hmStatusSnmpEventEntryCount,
            hmStatusWlanStationTableEntryMacAddress,
            hmStatusWlanStationTableEntryIdentification
          }
    STATUS     current
    DESCRIPTION
            "WLAN client passed re-association phase"
    ::= { hmTraps 20 }

-- {NOTIFICATION} 1.3.6.1.4.1.248.32.18.0.0.21
hmTrapsDisassstation NOTIFICATION-TYPE
    OBJECTS {
            sysDescr,
            sysName,
            hmStatusSnmpEventEntryCount,
            hmStatusWlanStationTableEntryMacAddress,
            hmStatusWlanStationTableEntryIdentification
          }
    STATUS     current
    DESCRIPTION
            "WLAN client was disassociated"
    ::= { hmTraps 21 }

-- {NOTIFICATION} 1.3.6.1.4.1.248.32.18.0.0.22
hmTrapsAssrej NOTIFICATION-TYPE
    OBJECTS {
            sysDescr,
            sysName,
            hmStatusSnmpEventEntryCount,
            hmStatusWlanLogTableEntryAddress
          }
    STATUS     current
    DESCRIPTION
            "Association request from client was rejected"
    ::= { hmTraps 22 }

-- {NOTIFICATION} 1.3.6.1.4.1.248.32.18.0.0.25
hmTrapsCardhung NOTIFICATION-TYPE
    OBJECTS {
            sysDescr,
            sysName,
            hmStatusSnmpEventEntryCount,
            hmStatusWlanIfcsEntryIfc
          }
    STATUS     current
    DESCRIPTION
            "General WLAN error"
    ::= { hmTraps 25 }

-- {NOTIFICATION} 1.3.6.1.4.1.248.32.18.0.0.26
hmTrapsIpfwflt NOTIFICATION-TYPE
    OBJECTS {
            sysDescr,
            sysName,
            hmStatusSnmpEventEntryCount,
            hmStatusIpRouterLogTableEntrySystemTime,
            hmStatusIpRouterLogTableEntrySrcAddress,
            hmStatusIpRouterLogTableEntryDstAddress,
            hmStatusIpRouterLogTableEntryProt,
            hmStatusIpRouterLogTableEntrySrcPort,
            hmStatusIpRouterLogTableEntryDstPort,
            hmStatusIpRouterLogTableEntryFilterRule,
            hmStatusIpRouterLogTableEntryLimit,
            hmStatusIpRouterLogTableEntryThreshold,
            hmStatusIpRouterLogTableEntryAction
          }
    STATUS     current
    DESCRIPTION
            "Information about a firewall event"
    ::= { hmTraps 26 }

-- {NOTIFICATION} 1.3.6.1.4.1.248.32.18.0.0.27
hmTrapsVpnconn NOTIFICATION-TYPE
    OBJECTS {
            sysDescr,
            sysName,
            hmStatusSnmpEventEntryCount,
            hmStatusVpnTunnel,
            hmStatusVpnConnectionsEntryPeer,
            hmStatusVpnConnectionsEntryState,
            hmStatusVpnConnectionsEntryLastError,
            hmStatusVpnConnectionsEntryMode,
            hmStatusVpnConnectionsEntryShTime,
            hmStatusVpnConnectionsEntryPhysConn,
            hmStatusVpnConnectionsEntryB1Dt,
            hmStatusVpnConnectionsEntryRemoteGwNew,
            hmStatusVpnConnectionsEntryRemoteGw,
            hmStatusVpnConnectionsEntryNatDetection,
            hmStatusVpnConnectionsEntrySslEncaps,
            hmStatusVpnConnectionsEntryCryptAlg,
            hmStatusVpnConnectionsEntryCryptLength,
            hmStatusVpnConnectionsEntryHashAlg,
            hmStatusVpnConnectionsEntryHashLength,
            hmStatusVpnConnectionsEntryHmacAlg,
            hmStatusVpnConnectionsEntryHmacLength,
            hmStatusVpnConnectionsEntryComprAlg,
            hmStatusVpnConnectionsEntryClientSn
          }
    STATUS     current
    DESCRIPTION
            "Status of VPN connection"
    ::= { hmTraps 27 }

-- {NOTIFICATION} 1.3.6.1.4.1.248.32.18.0.0.28
hmTrapsPptpconn NOTIFICATION-TYPE
    OBJECTS {
            sysDescr,
            sysName,
            hmStatusSnmpEventEntryCount,
            hmStatusPptpTunnel,
            hmStatusPptpConnectionsEntryChannel,
            hmStatusPptpConnectionsEntryState,
            hmStatusPptpConnectionsEntryMode,
            hmStatusPptpConnectionsEntryShTime,
            hmStatusPptpConnectionsEntryPhysConnection,
            hmStatusPptpConnectionsEntryPeerAddress,
            hmStatusPptpConnectionsEntryIpAddress,
            hmStatusPptpConnectionsEntryDnsDefault,
            hmStatusPptpConnectionsEntryNbnsDefault,
            hmStatusPptpConnectionsEntryLastError,
            hmStatusPptpConnectionsEntryDnsBackup,
            hmStatusPptpConnectionsEntryNbnsBackup
          }
    STATUS     current
    DESCRIPTION
            "Status of PPTP connection"
    ::= { hmTraps 28 }

-- {NOTIFICATION} 1.3.6.1.4.1.248.32.18.0.0.29
hmTrapsErrlogin NOTIFICATION-TYPE
    OBJECTS {
            sysDescr,
            sysName,
            hmStatusSnmpEventEntryCount,
            hmStatusConfigEventLogEntrySystemTime,
            hmStatusConfigEventLogEntryEvent,
            hmStatusConfigEventLogEntryAccess,
            hmStatusConfigEventLogEntryIpAddressNew,
            hmStatusConfigEventLogEntryIpAddress
          }
    STATUS     current
    DESCRIPTION
            "Error during login to configuration"
    ::= { hmTraps 29 }

-- {NOTIFICATION} 1.3.6.1.4.1.248.32.18.0.0.33
hmTrapsKeyhandshakeTimeout NOTIFICATION-TYPE
    OBJECTS {
            sysDescr,
            sysName,
            hmStatusSnmpEventEntryCount
          }
    STATUS     current
    DESCRIPTION
            "Timeout during WPA/802.11i key handshake"
    ::= { hmTraps 33 }

-- {NOTIFICATION} 1.3.6.1.4.1.248.32.18.0.0.35
hmTrapsSupervision NOTIFICATION-TYPE
    OBJECTS {
            sysDescr,
            sysName,
            hmStatusSnmpEventEntryCount,
            hmStatusWlanStationTableEntryMacAddress,
            hmStatusWlanStationTableEntryIdentification
          }
    STATUS     current
    DESCRIPTION
            "WLAN client was disassociated from network because it is no longer reachable (supervision)"
    ::= { hmTraps 35 }

-- {NOTIFICATION} 1.3.6.1.4.1.248.32.18.0.0.38
hmTrapsLdblconn NOTIFICATION-TYPE
    OBJECTS {
            sysDescr,
            sysName,
            hmStatusSnmpEventEntryCount,
            hmStatusIpRouterLoadBalancerConnectionsEntryPeer,
            hmStatusIpRouterLoadBalancerConnectionsEntryBundlePeer,
            hmStatusIpRouterLoadBalancerConnectionsEntryState
          }
    STATUS     current
    DESCRIPTION
            "Load balancer connection status"
    ::= { hmTraps 38 }

-- {NOTIFICATION} 1.3.6.1.4.1.248.32.18.0.0.39
hmTrapsPppoesconn NOTIFICATION-TYPE
    OBJECTS {
            sysDescr,
            sysName,
            hmStatusSnmpEventEntryCount,
            hmStatusPppoeServerNumConnections,
            hmStatusPppoeServerConnectionsEntryChannel,
            hmStatusPppoeServerConnectionsEntryMacAddress,
            hmStatusPppoeServerConnectionsEntryState,
            hmStatusPppoeServerConnectionsEntryLastError,
            hmStatusPppoeServerConnectionsEntryShTime,
            hmStatusPppoeServerConnectionsEntryPeerAddress
          }
    STATUS     current
    DESCRIPTION
            "PPPoE server connection status"
    ::= { hmTraps 39 }

-- {NOTIFICATION} 1.3.6.1.4.1.248.32.18.0.0.41
hmTrapsVrrp NOTIFICATION-TYPE
    OBJECTS {
            sysDescr,
            sysName,
            hmStatusSnmpEventEntryCount,
            hmStatusIpRouterVrrpEventLogEntrySystemTime,
            hmStatusIpRouterVrrpEventLogEntrySrcAddress,
            hmStatusIpRouterVrrpEventLogEntryVrid,
            hmStatusIpRouterVrrpEventLogEntryEvent,
            hmStatusIpRouterVrrpEventLogEntryInfo
          }
    STATUS     current
    DESCRIPTION
            "Information about a VRRP event"
    ::= { hmTraps 41 }

-- {NOTIFICATION} 1.3.6.1.4.1.248.32.18.0.0.42
hmTrapsExceirp NOTIFICATION-TYPE
    OBJECTS {
            sysDescr,
            sysName,
            hmStatusSnmpEventEntryCount,
            hmStatusWlanWlanParameterEntryIfc,
            hmStatusWlanWlanParameterEntryEirp
          }
    STATUS     current
    DESCRIPTION
            "Transmit power or EIRP on WLAN interface above regulatory limits"
    ::= { hmTraps 42 }

-- {NOTIFICATION} 1.3.6.1.4.1.248.32.18.0.0.46
hmTrapsIdleTimeout NOTIFICATION-TYPE
    OBJECTS {
            sysDescr,
            sysName,
            hmStatusSnmpEventEntryCount
          }
    STATUS     current
    DESCRIPTION
            "WLAN client was disassociated from network due to idle timeout"
    ::= { hmTraps 46 }

-- {NOTIFICATION} 1.3.6.1.4.1.248.32.18.0.0.47
hmTrapsAdminDeassoc NOTIFICATION-TYPE
    OBJECTS {
            sysDescr,
            sysName,
            hmStatusSnmpEventEntryCount,
            hmStatusWlanStationTableEntryMacAddress,
            hmStatusWlanStationTableEntryIdentification
          }
    STATUS     current
    DESCRIPTION
            "WLAN client was disassociated from network due to admin request"
    ::= { hmTraps 47 }

-- {NOTIFICATION} 1.3.6.1.4.1.248.32.18.0.0.48
hmTrapsWlanovertemp NOTIFICATION-TYPE
    OBJECTS {
            sysDescr,
            sysName,
            hmStatusSnmpEventEntryCount,
            hmStatusHardwareInfoTemperatureDegrees
          }
    STATUS     current
    DESCRIPTION
            "WLAN operation stopped because temperature is above upper limit"
    ::= { hmTraps 48 }

-- {NOTIFICATION} 1.3.6.1.4.1.248.32.18.0.0.49
hmTrapsWlanovertempend NOTIFICATION-TYPE
    OBJECTS {
            sysDescr,
            sysName,
            hmStatusSnmpEventEntryCount,
            hmStatusHardwareInfoTemperatureDegrees
          }
    STATUS     current
    DESCRIPTION
            "WLAN operation resumed because temperature is back below upper limit"
    ::= { hmTraps 49 }

-- {NOTIFICATION} 1.3.6.1.4.1.248.32.18.0.0.50
hmTrapsWlanundertemp NOTIFICATION-TYPE
    OBJECTS {
            sysDescr,
            sysName,
            hmStatusSnmpEventEntryCount,
            hmStatusHardwareInfoTemperatureDegrees
          }
    STATUS     current
    DESCRIPTION
            "WLAN operation stopped because temperature is below lower limit"
    ::= { hmTraps 50 }

-- {NOTIFICATION} 1.3.6.1.4.1.248.32.18.0.0.51
hmTrapsWlanundertempend NOTIFICATION-TYPE
    OBJECTS {
            sysDescr,
            sysName,
            hmStatusSnmpEventEntryCount,
            hmStatusHardwareInfoTemperatureDegrees
          }
    STATUS     current
    DESCRIPTION
            "WLAN operation resumed because temperature is back above lower limit"
    ::= { hmTraps 51 }

-- {NOTIFICATION} 1.3.6.1.4.1.248.32.18.0.0.52
hmTrapsMacchkfail NOTIFICATION-TYPE
    OBJECTS {
            sysDescr,
            sysName,
            hmStatusSnmpEventEntryCount,
            hmStatusWlanStationTableEntryMacAddress,
            hmStatusWlanStationTableEntryIdentification
          }
    STATUS     current
    DESCRIPTION
            "MAC address check for WLAN client failed"
    ::= { hmTraps 52 }

-- {NOTIFICATION} 1.3.6.1.4.1.248.32.18.0.0.53
hmTrapsRoamed NOTIFICATION-TYPE
    OBJECTS {
            sysDescr,
            sysName,
            hmStatusSnmpEventEntryCount,
            hmStatusWlanStationTableEntryMacAddress,
            hmStatusWlanStationTableEntryIdentification
          }
    STATUS     current
    DESCRIPTION
            "WLAN client roamed to another access point"
    ::= { hmTraps 53 }

-- {NOTIFICATION} 1.3.6.1.4.1.248.32.18.0.0.54
hmTrapsConnected NOTIFICATION-TYPE
    OBJECTS {
            sysDescr,
            sysName,
            hmStatusSnmpEventEntryCount,
            hmStatusWlanStationTableEntryMacAddress,
            hmStatusWlanStationTableEntryIdentification
          }
    STATUS     current
    DESCRIPTION
            "WLAN client successfully connected to network"
    ::= { hmTraps 54 }

-- {NOTIFICATION} 1.3.6.1.4.1.248.32.18.0.0.55
hmTrapsClLostconn NOTIFICATION-TYPE
    OBJECTS {
            sysDescr,
            sysName,
            hmStatusSnmpEventEntryCount,
            hmStatusWlanClientIfcsEntryIfc,
            hmStatusWlanClientIfcsEntryState
          }
    STATUS     current
    DESCRIPTION
            "WLAN in client mode lost connection to AP/network"
    ::= { hmTraps 55 }

-- {NOTIFICATION} 1.3.6.1.4.1.248.32.18.0.0.56
hmTrapsClAuthfail NOTIFICATION-TYPE
    OBJECTS {
            sysDescr,
            sysName,
            hmStatusSnmpEventEntryCount,
            hmStatusWlanClientIfcsEntryIfc,
            hmStatusWlanClientIfcsEntryState
          }
    STATUS     current
    DESCRIPTION
            "WLAN in client mode was unable to authenticate to AP/network"
    ::= { hmTraps 56 }

-- {NOTIFICATION} 1.3.6.1.4.1.248.32.18.0.0.57
hmTrapsClAssocfail NOTIFICATION-TYPE
    OBJECTS {
            sysDescr,
            sysName,
            hmStatusSnmpEventEntryCount,
            hmStatusWlanClientIfcsEntryIfc,
            hmStatusWlanClientIfcsEntryState
          }
    STATUS     current
    DESCRIPTION
            "WLAN in client mode was unable to associate to AP/network"
    ::= { hmTraps 57 }

-- {NOTIFICATION} 1.3.6.1.4.1.248.32.18.0.0.58
hmTrapsClConnected NOTIFICATION-TYPE
    OBJECTS {
            sysDescr,
            sysName,
            hmStatusSnmpEventEntryCount,
            hmStatusWlanClientIfcsEntryIfc,
            hmStatusWlanClientIfcsEntryState
          }
    STATUS     current
    DESCRIPTION
            "WLAN in client mode successfully connected to AP/network"
    ::= { hmTraps 58 }

-- {NOTIFICATION} 1.3.6.1.4.1.248.32.18.0.0.59
hmTrapsCl8021xFail NOTIFICATION-TYPE
    OBJECTS {
            sysDescr,
            sysName,
            hmStatusSnmpEventEntryCount,
            hmStatusWlanClientIfcsEntryIfc,
            hmStatusWlanClientIfcsEntryState
          }
    STATUS     current
    DESCRIPTION
            "WLAN in client mode was unable to perform 802.1X authentication"
    ::= { hmTraps 59 }

-- {NOTIFICATION} 1.3.6.1.4.1.248.32.18.0.0.61
hmTrapsCastatchg NOTIFICATION-TYPE
    OBJECTS {
            sysDescr,
            sysName,
            hmStatusSnmpEventEntryCount,
            hmStatusCertsScepCaCaStatusCaStatus,
            hmStatusCertsScepCaCaStatusError
          }
    STATUS     current
    DESCRIPTION
            "Operation state of SCEP-CA has changed"
    ::= { hmTraps 61 }

-- {NOTIFICATION} 1.3.6.1.4.1.248.32.18.0.0.62
hmTrapsNewpendreq NOTIFICATION-TYPE
    OBJECTS {
            sysDescr,
            sysName,
            hmStatusSnmpEventEntryCount,
            hmStatusCertsScepCaRequestsPendReqEntryIndex,
            hmStatusCertsScepCaRequestsPendReqEntryMacAddress,
            hmStatusCertsScepCaRequestsPendReqEntryIpAddress,
            hmStatusCertsScepCaRequestsPendReqEntryReason,
            hmStatusCertsScepCaRequestsPendReqEntryDn,
            hmStatusCertsScepCaRequestsPendReqEntryReceiveDate
          }
    STATUS     current
    DESCRIPTION
            "Pending SCEP request at SCEP-CA"
    ::= { hmTraps 62 }

-- {NOTIFICATION} 1.3.6.1.4.1.248.32.18.0.0.63
hmTrapsMissingAp NOTIFICATION-TYPE
    OBJECTS {
            sysDescr,
            sysName,
            hmStatusSnmpEventEntryCount,
            hmStatusWlanMngmtConnectedExpectedAp,
            hmStatusWlanMngmtNextdoorAp,
            hmStatusWlanMngmtExpectedAp,
            hmStatusWlanMngmtApStatusMissingApEntryApLanMac,
            hmStatusWlanMngmtApStatusMissingApEntryIpAddress,
            hmStatusWlanMngmtApStatusMissingApEntryName,
            hmStatusWlanMngmtApStatusMissingApEntryLocation,
            hmStatusWlanMngmtApStatusMissingApEntryValid,
            hmStatusWlanMngmtApStatusMissingApEntryModule
          }
    STATUS     current
    DESCRIPTION
            "Missing Access Points table updated"
    ::= { hmTraps 63 }

-- {NOTIFICATION} 1.3.6.1.4.1.248.32.18.0.0.64
hmTrapsActiveAp NOTIFICATION-TYPE
    OBJECTS {
            sysDescr,
            sysName,
            hmStatusSnmpEventEntryCount,
            hmStatusWlanMngmtConnectedManagedAp,
            hmStatusWlanMngmtNextdoorAp,
            hmStatusWlanMngmtApStatusActiveRadiosEntryApLanMac,
            hmStatusWlanMngmtApStatusActiveRadiosEntryIfc,
            hmStatusWlanMngmtApStatusActiveRadiosEntryIpAddress,
            hmStatusWlanMngmtApStatusActiveRadiosEntryName,
            hmStatusWlanMngmtApStatusActiveRadiosEntryLocation,
            hmStatusWlanMngmtApStatusActiveRadiosEntryValid,
            hmStatusWlanMngmtApStatusActiveRadiosEntryApWlanMac,
            hmStatusWlanMngmtApStatusActiveRadiosEntryRadioBand,
            hmStatusWlanMngmtApStatusActiveRadiosEntryRadioChannel,
            hmStatusWlanMngmtApStatusActiveRadiosEntryClientCount,
            hmStatusWlanMngmtApStatusActiveRadiosEntryBackgroundScan,
            hmStatusWlanMngmtApStatusActiveRadiosEntryCardId,
            hmStatusWlanMngmtApStatusActiveRadiosEntryCardFirmwareVersion,
            hmStatusWlanMngmtApStatusActiveRadiosEntryCardSerialNumber,
            hmStatusWlanMngmtApStatusActiveRadiosEntryOperating,
            hmStatusWlanMngmtApStatusActiveRadiosEntryTransmitPower,
            hmStatusWlanMngmtApStatusActiveRadiosEntryEirp,
            hmStatusWlanMngmtApStatusActiveRadiosEntryExcEirp,
            hmStatusWlanMngmtApStatusActiveRadiosEntryInternal,
            hmStatusWlanMngmtApStatusActiveRadiosEntryRadios,
            hmStatusWlanMngmtApStatusActiveRadiosEntryModule,
            hmStatusWlanMngmtApStatusActiveRadiosEntrySerialNumber,
            hmStatusWlanMngmtApStatusActiveRadiosEntryVersion,
            hmStatusWlanMngmtApStatusActiveRadiosEntryCardState,
            hmStatusWlanMngmtApStatusActiveRadiosEntryRadioFldOpt,
            hmStatusWlanMngmtApStatusActiveRadiosEntryMinimalModemLoad,
            hmStatusWlanMngmtApStatusActiveRadiosEntryMaximalModemLoad,
            hmStatusWlanMngmtApStatusActiveRadiosEntryAverageModemLoad,
            hmStatusWlanMngmtApStatusActiveRadiosEntryApConnection
          }
    STATUS     current
    DESCRIPTION
            "WLC Active Access Points table updated"
    ::= { hmTraps 64 }

-- {NOTIFICATION} 1.3.6.1.4.1.248.32.18.0.0.65
hmTrapsNewAp NOTIFICATION-TYPE
    OBJECTS {
            sysDescr,
            sysName,
            hmStatusSnmpEventEntryCount,
            hmStatusWlanMngmtConnectedNewAp,
            hmStatusWlanMngmtApStatusNewApEntryApLanMac,
            hmStatusWlanMngmtApStatusNewApEntryIpAddress,
            hmStatusWlanMngmtApStatusNewApEntryName,
            hmStatusWlanMngmtApStatusNewApEntryLocation,
            hmStatusWlanMngmtApStatusNewApEntryValid,
            hmStatusWlanMngmtApStatusNewApEntryConfiguration,
            hmStatusWlanMngmtApStatusNewApEntryAutowdsIntegration
          }
    STATUS     current
    DESCRIPTION
            "WLC New Access Points table updated"
    ::= { hmTraps 65 }

-- {NOTIFICATION} 1.3.6.1.4.1.248.32.18.0.0.66
hmTrapsStations NOTIFICATION-TYPE
    OBJECTS {
            sysDescr,
            sysName,
            hmStatusSnmpEventEntryCount,
            hmStatusWlanMngmtStationTableEntryClientMac,
            hmStatusWlanMngmtStationTableEntryApWlanMac,
            hmStatusWlanMngmtStationTableEntryIdentification,
            hmStatusWlanMngmtStationTableEntryTrap,
            hmStatusWlanMngmtStationTableEntryPhySignal,
            hmStatusWlanMngmtStationTableEntryTxRate,
            hmStatusWlanMngmtStationTableEntryRxRate,
            hmStatusWlanMngmtStationTableEntryNetworkName,
            hmStatusWlanMngmtStationTableEntryKeyType,
            hmStatusWlanMngmtStationTableEntryWpaVersion,
            hmStatusWlanMngmtStationTableEntryState,
            hmStatusWlanMngmtStationTableEntryLastError,
            hmStatusWlanMngmtStationTableEntryIpAddress,
            hmStatusWlanMngmtStationTableEntryInterface,
            hmStatusWlanMngmtStationTableEntryThroughput,
            hmStatusWlanMngmtStationTableEntryCompression,
            hmStatusWlanMngmtStationTableEntryApLanMac,
            hmStatusWlanMngmtStationTableEntryApName,
            hmStatusWlanMngmtStationTableEntryValid,
            hmStatusWlanMngmtStationTableEntryEffTxRate,
            hmStatusWlanMngmtStationTableEntryEffRxRate,
            hmStatusWlanMngmtStationTableEntryBssid,
            hmStatusWlanMngmtStationTableEntryClientSteering,
            hmStatusWlanMngmtStationTableEntryOperationMode,
            hmStatusWlanMngmtStationTableEntryFastRoaming,
            hmStatusWlanMngmtStationTableEntryUserName,
            hmStatusWlanMngmtStationTableEntryRadioBand,
            hmStatusWlanMngmtStationTableEntryRadioChannel
          }
    STATUS     current
    DESCRIPTION
            "WLC Stations table updated"
    ::= { hmTraps 66 }

-- {NOTIFICATION} 1.3.6.1.4.1.248.32.18.0.0.67
hmTrapsNetworks NOTIFICATION-TYPE
    OBJECTS {
            sysDescr,
            sysName,
            hmStatusSnmpEventEntryCount,
            hmStatusWlanMngmtNetworksEntryBssid,
            hmStatusWlanMngmtNetworksEntryApWlanMac,
            hmStatusWlanMngmtNetworksEntryNetNumber,
            hmStatusWlanMngmtNetworksEntryName,
            hmStatusWlanMngmtNetworksEntryClientCount,
            hmStatusWlanMngmtNetworksEntryValid
          }
    STATUS     current
    DESCRIPTION
            "WLC Networks table updated"
    ::= { hmTraps 67 }

-- {NOTIFICATION} 1.3.6.1.4.1.248.32.18.0.0.68
hmTrapsNetworkcounts NOTIFICATION-TYPE
    OBJECTS {
            sysDescr,
            sysName,
            hmStatusSnmpEventEntryCount,
            hmStatusWlanMngmtNetCountEntryName,
            hmStatusWlanMngmtNetCountEntryNumRadios,
            hmStatusWlanMngmtNetCountEntryNumStations,
            hmStatusWlanMngmtNetCountEntrySsid,
            hmStatusWlanMngmtNetCountEntryBridgeInterface
          }
    STATUS     current
    DESCRIPTION
            "WLC network counts updated"
    ::= { hmTraps 68 }

-- {NOTIFICATION} 1.3.6.1.4.1.248.32.18.0.0.69
hmTrapsApCounter NOTIFICATION-TYPE
    OBJECTS {
            sysDescr,
            sysName,
            hmStatusSnmpEventEntryCount,
            hmStatusWlanMngmtConnectedExpectedAp,
            hmStatusWlanMngmtConnectedManagedAp,
            hmStatusWlanMngmtConnectedNewAp,
            hmStatusWlanMngmtNextdoorAp
          }
    STATUS     current
    DESCRIPTION
            "WLC Access Point (WTP) counts updated"
    ::= { hmTraps 69 }

-- {NOTIFICATION} 1.3.6.1.4.1.248.32.18.0.0.73
hmTrapsCerttabmod NOTIFICATION-TYPE
    OBJECTS {
            sysDescr,
            sysName,
            hmStatusSnmpEventEntryCount,
            hmStatusCertsScepCaCertsCertsStatusTabEntryIndex,
            hmStatusCertsScepCaCertsCertsStatusTabEntrySerialnumber,
            hmStatusCertsScepCaCertsCertsStatusTabEntryStatus,
            hmStatusCertsScepCaCertsCertsStatusTabEntryCreationDate,
            hmStatusCertsScepCaCertsCertsStatusTabEntryEndTime,
            hmStatusCertsScepCaCertsCertsStatusTabEntryRevTime,
            hmStatusCertsScepCaCertsCertsStatusTabEntryRevReas,
            hmStatusCertsScepCaCertsCertsStatusTabEntryMacAddress,
            hmStatusCertsScepCaCertsCertsStatusTabEntryDn
          }
    STATUS     current
    DESCRIPTION
            "Certificate list of SCEP CA was modified"
    ::= { hmTraps 73 }

-- {NOTIFICATION} 1.3.6.1.4.1.248.32.18.0.0.74
hmTrapsPendlistmod NOTIFICATION-TYPE
    OBJECTS {
            sysDescr,
            sysName,
            hmStatusSnmpEventEntryCount
          }
    STATUS     current
    DESCRIPTION
            "State of pending SCEP request was changed"
    ::= { hmTraps 74 }

-- {NOTIFICATION} 1.3.6.1.4.1.248.32.18.0.0.75
hmTrapsNextdoorAp NOTIFICATION-TYPE
    OBJECTS {
            sysDescr,
            sysName,
            hmStatusSnmpEventEntryCount,
            hmStatusWlanMngmtNextdoorAp,
            hmStatusWlanMngmtApStatusNextdoorApEntryApLanMac,
            hmStatusWlanMngmtApStatusNextdoorApEntryIpAddress,
            hmStatusWlanMngmtApStatusNextdoorApEntryName,
            hmStatusWlanMngmtApStatusNextdoorApEntryLocation,
            hmStatusWlanMngmtApStatusNextdoorApEntryValid,
            hmStatusWlanMngmtApStatusNextdoorApEntryWlcName
          }
    STATUS     current
    DESCRIPTION
            "Next Door Access Points table updated"
    ::= { hmTraps 75 }

-- {NOTIFICATION} 1.3.6.1.4.1.248.32.18.0.0.76
hmTrapsWlcTunnels NOTIFICATION-TYPE
    OBJECTS {
            sysDescr,
            sysName,
            hmStatusSnmpEventEntryCount,
            hmStatusWlanMngmtWlcTunnelsNumberOfWlcConn,
            hmStatusWlanMngmtWlcTunnelsActiveConnections,
            hmStatusWlanMngmtWlcTunnelsWlcConnectionsEntryIpAddress,
            hmStatusWlanMngmtWlcTunnelsWlcConnectionsEntryPort,
            hmStatusWlanMngmtWlcTunnelsWlcConnectionsEntryResult,
            hmStatusWlanMngmtWlcTunnelsWlcConnectionsEntryName,
            hmStatusWlanMngmtWlcTunnelsWlcConnectionsEntryState,
            hmStatusWlanMngmtWlcTunnelsWlcConnectionsEntryValid
          }
    STATUS     current
    DESCRIPTION
            "WLC Connections updated"
    ::= { hmTraps 76 }

-- {NOTIFICATION} 1.3.6.1.4.1.248.32.18.0.0.77
hmTrapsLicensemgtexpire NOTIFICATION-TYPE
    OBJECTS {
            sysDescr,
            sysName,
            hmStatusSnmpEventEntryCount,
            hmStatusConfigFeaturesEntryFeature,
            hmStatusConfigFeaturesEntryExpires,
            hmStatusConfigFeaturesEntryExpire,
            hmStatusConfigFeaturesEntryState,
            hmStatusConfigFeaturesEntryIndex,
            hmStatusConfigFeaturesEntryCount
          }
    STATUS     current
    DESCRIPTION
            "Software option license has expired"
    ::= { hmTraps 77 }

-- {NOTIFICATION} 1.3.6.1.4.1.248.32.18.0.0.79
hmTrapsScrptuplstart NOTIFICATION-TYPE
    OBJECTS {
            sysDescr,
            sysName,
            hmStatusSnmpEventEntryCount,
            hmStatusConfigEventLogEntrySystemTime,
            hmStatusConfigEventLogEntryEvent,
            hmStatusConfigEventLogEntryAccess,
            hmStatusConfigEventLogEntryIpAddressNew,
            hmStatusConfigEventLogEntryIpAddress
          }
    STATUS     current
    DESCRIPTION
            "Script upload was started"
    ::= { hmTraps 79 }

-- {NOTIFICATION} 1.3.6.1.4.1.248.32.18.0.0.80
hmTrapsScrptdnlstart NOTIFICATION-TYPE
    OBJECTS {
            sysDescr,
            sysName,
            hmStatusSnmpEventEntryCount,
            hmStatusConfigEventLogEntrySystemTime,
            hmStatusConfigEventLogEntryEvent,
            hmStatusConfigEventLogEntryAccess,
            hmStatusConfigEventLogEntryIpAddressNew,
            hmStatusConfigEventLogEntryIpAddress
          }
    STATUS     current
    DESCRIPTION
            "Script download was started"
    ::= { hmTraps 80 }

-- {NOTIFICATION} 1.3.6.1.4.1.248.32.18.0.0.81
hmTrapsIpv6fwflt NOTIFICATION-TYPE
    OBJECTS {
            sysDescr,
            sysName,
            hmStatusSnmpEventEntryCount,
            hmStatusIpv6FirewallLogTableEntrySystemTime,
            hmStatusIpv6FirewallLogTableEntrySrcAddress,
            hmStatusIpv6FirewallLogTableEntryDstAddress,
            hmStatusIpv6FirewallLogTableEntryProt,
            hmStatusIpv6FirewallLogTableEntrySrcPort,
            hmStatusIpv6FirewallLogTableEntryDstPort,
            hmStatusIpv6FirewallLogTableEntryFilterRule,
            hmStatusIpv6FirewallLogTableEntryLimit,
            hmStatusIpv6FirewallLogTableEntryThreshold,
            hmStatusIpv6FirewallLogTableEntryAction
          }
    STATUS     current
    DESCRIPTION
            "Information about an IPv6 firewall event"
    ::= { hmTraps 81 }

-- {NOTIFICATION} 1.3.6.1.4.1.248.32.18.0.0.82
hmTrapsWwanStates NOTIFICATION-TYPE
    OBJECTS {
            sysDescr,
            sysName,
            hmStatusSnmpEventEntryCount,
            hmStatusModemMobileState,
            hmStatusModemMobileRegistration
          }
    STATUS     current
    DESCRIPTION
            "WWAN-States updated"
    ::= { hmTraps 82 }

-- {NOTIFICATION} 1.3.6.1.4.1.248.32.18.0.0.83
hmTrapsDsLite NOTIFICATION-TYPE
    OBJECTS {
            sysDescr,
            sysName,
            hmStatusSnmpEventEntryCount,
            hmStatusDsLiteConnectionsEntryPeer,
            hmStatusDsLiteConnectionsEntryState,
            hmStatusDsLiteConnectionsEntryLastError,
            hmStatusDsLiteConnectionsEntryIpv4Address,
            hmStatusDsLiteConnectionsEntryPhysConn,
            hmStatusDsLiteConnectionsEntryAftrName,
            hmStatusDsLiteConnectionsEntryAftrIpv6Address,
            hmStatusDsLiteConnectionsEntryConnTime
          }
    STATUS     current
    DESCRIPTION
            "DS-LITE connection status"
    ::= { hmTraps 83 }

-- {NOTIFICATION} 1.3.6.1.4.1.248.32.18.0.0.85
hmTrapsL2TP-Endpoints NOTIFICATION-TYPE
    OBJECTS {
            sysDescr,
            sysName,
            hmStatusSnmpEventEntryCount,
            hmStatusL2tpNumEndpoints,
            hmStatusL2tpEndpointsEntryL2tpEndpoint,
            hmStatusL2tpEndpointsEntryState,
            hmStatusL2tpEndpointsEntryLastError,
            hmStatusL2tpEndpointsEntryMode,
            hmStatusL2tpEndpointsEntryPhysConnection,
            hmStatusL2tpEndpointsEntryGateway,
            hmStatusL2tpEndpointsEntrySessions,
            hmStatusL2tpEndpointsEntryConnTime,
            hmStatusL2tpEndpointsEntryEmbeddedErrorMessage
          }
    STATUS     current
    DESCRIPTION
            "L2TP tunnel end point status"
    ::= { hmTraps 85 }

-- {NOTIFICATION} 1.3.6.1.4.1.248.32.18.0.0.86
hmTrapsL2TP-Connections NOTIFICATION-TYPE
    OBJECTS {
            sysDescr,
            sysName,
            hmStatusSnmpEventEntryCount,
            hmStatusL2tpNumConnections,
            hmStatusL2tpConnectionsEntryPeer,
            hmStatusL2tpConnectionsEntryState,
            hmStatusL2tpConnectionsEntryLastError,
            hmStatusL2tpConnectionsEntryMode,
            hmStatusL2tpConnectionsEntryShTime,
            hmStatusL2tpConnectionsEntryL2tpEndpoint,
            hmStatusL2tpConnectionsEntryPeerAddress,
            hmStatusL2tpConnectionsEntryIpAddress,
            hmStatusL2tpConnectionsEntryDnsDefault,
            hmStatusL2tpConnectionsEntryDnsBackup,
            hmStatusL2tpConnectionsEntryNbnsDefault,
            hmStatusL2tpConnectionsEntryNbnsBackup,
            hmStatusL2tpConnectionsEntryConnTime
          }
    STATUS     current
    DESCRIPTION
            "L2TP connection status"
    ::= { hmTraps 86 }

-- {NOTIFICATION} 1.3.6.1.4.1.248.32.18.0.0.87
hmTrapsLoginBlocked NOTIFICATION-TYPE
    OBJECTS {
            sysDescr,
            sysName,
            hmStatusSnmpEventEntryCount,
            hmStatusConfigEventLogEntrySystemTime,
            hmStatusConfigEventLogEntryEvent,
            hmStatusConfigEventLogEntryAccess,
            hmStatusConfigEventLogEntryIpAddressNew
          }
    STATUS     current
    DESCRIPTION
            "Login is temporarily blocked"
    ::= { hmTraps 87 }

-- {NOTIFICATION} 1.3.6.1.4.1.248.32.18.0.0.1000
hmTrapsSpgtreePortstatchg NOTIFICATION-TYPE
    OBJECTS {
            sysDescr,
            sysName,
            hmStatusSnmpEventEntryCount,
            hmStatusLanBridgeSpanningTreePortTableEntryDescription,
            hmStatusLanBridgeSpanningTreePortTableEntryState,
            hmStatusLanBridgeSpanningTreePortTableEntryPathCost
          }
    STATUS     current
    DESCRIPTION
            "Spanning tree port status has changed"
    ::= { hmTraps 1000 }

-- {NOTIFICATION} 1.3.6.1.4.1.248.32.18.0.0.1001
hmTrapsSpgtreeRstpstatchg NOTIFICATION-TYPE
    OBJECTS {
            sysDescr,
            sysName,
            hmStatusSnmpEventEntryCount,
            hmStatusLanBridgeSpanningTreeRstpPortTableEntryDescription,
            hmStatusLanBridgeSpanningTreeRstpPortTableEntryRole,
            hmStatusLanBridgeSpanningTreeRstpPortTableEntryLearning,
            hmStatusLanBridgeSpanningTreeRstpPortTableEntryForwarding,
            hmStatusLanBridgeSpanningTreeRstpPortTableEntryEdgePort,
            hmStatusLanBridgeSpanningTreeRstpPortTableEntryProtocolVersion,
            hmStatusLanBridgeSpanningTreeRstpPortTableEntryPathCost
          }
    STATUS     current
    DESCRIPTION
            "RSTP port status has changed"
    ::= { hmTraps 1001 }

-- {NOTIFICATION} 1.3.6.1.4.1.248.32.18.0.0.1002
hmTrapsSpgtreeRootportchg NOTIFICATION-TYPE
    OBJECTS {
            sysDescr,
            sysName,
            hmStatusSnmpEventEntryCount,
            hmStatusLanBridgeSpanningTreeRootBridge,
            hmStatusLanBridgeSpanningTreeRootPort,
            hmStatusLanBridgeSpanningTreeRootPathCost
          }
    STATUS     current
    DESCRIPTION
            "Spanning tree/RSTP root port has changed"
    ::= { hmTraps 1002 }

-- {NOTIFICATION} 1.3.6.1.4.1.248.32.18.0.0.2000
hmTrapsHttpTunnelOpen NOTIFICATION-TYPE
    OBJECTS {
            sysDescr,
            sysName,
            hmStatusSnmpEventEntryCount,
            hmStatusTcpIpHttpActiveTunnelsEntryIndex,
            hmStatusTcpIpHttpActiveTunnelsEntryRemoteAddress,
            hmStatusTcpIpHttpActiveTunnelsEntryRemotePort,
            hmStatusTcpIpHttpActiveTunnelsEntryLocalHost,
            hmStatusTcpIpHttpActiveTunnelsEntryLocalPort,
            hmStatusTcpIpHttpActiveTunnelsEntryIdleTime,
            hmStatusTcpIpHttpActiveTunnelsEntryLocalRtgTag
          }
    STATUS     current
    DESCRIPTION
            "HTTP tunnel opened successful"
    ::= { hmTraps 2000 }

-- {NOTIFICATION} 1.3.6.1.4.1.248.32.18.0.0.2001
hmTrapsHttpTunnelClose NOTIFICATION-TYPE
    OBJECTS {
            sysDescr,
            sysName,
            hmStatusSnmpEventEntryCount,
            hmStatusTcpIpHttpActiveTunnelsEntryIndex
          }
    STATUS     current
    DESCRIPTION
            "HTTP tunnel closed successful"
    ::= { hmTraps 2001 }

-- {NOTIFICATION} 1.3.6.1.4.1.248.32.18.0.0.3000
hmTrapsLanauthuseradd NOTIFICATION-TYPE
    OBJECTS {
            sysDescr,
            sysName,
            hmStatusSnmpEventEntryCount,
            hmSetupPublicSpotModuleUserTableEntryName,
            hmSetupPublicSpotModuleUserTableEntryComment
          }
    STATUS     current
    DESCRIPTION
            "Public spot user account was created"
    ::= { hmTraps 3000 }

-- {NOTIFICATION} 1.3.6.1.4.1.248.32.18.0.0.3001
hmTrapsLanauthuserdel NOTIFICATION-TYPE
    OBJECTS {
            sysDescr,
            sysName,
            hmStatusSnmpEventEntryCount,
            hmSetupPublicSpotModuleUserTableEntryName,
            hmSetupPublicSpotModuleUserTableEntryComment
          }
    STATUS     current
    DESCRIPTION
            "Public spot user account was deleted"
    ::= { hmTraps 3001 }

-- {NOTIFICATION} 1.3.6.1.4.1.248.32.18.0.0.3002
hmTrapsLanauthsessionstart NOTIFICATION-TYPE
    OBJECTS {
            sysDescr,
            sysName,
            hmStatusSnmpEventEntryCount,
            hmStatusPublicSpotStationTableEntryMacAddress,
            hmStatusPublicSpotStationTableEntryName,
            hmStatusPublicSpotStationTableEntrySessionId
          }
    STATUS     current
    DESCRIPTION
            "Public spot session started"
    ::= { hmTraps 3002 }

-- {NOTIFICATION} 1.3.6.1.4.1.248.32.18.0.0.3003
hmTrapsLanauthsessionend NOTIFICATION-TYPE
    OBJECTS {
            sysDescr,
            sysName,
            hmStatusSnmpEventEntryCount,
            hmStatusPublicSpotStationTableEntryMacAddress,
            hmStatusPublicSpotStationTableEntryName,
            hmStatusPublicSpotStationTableEntrySessionId,
            hmStatusPublicSpotStationTableEntryTxBytesNew,
            hmStatusPublicSpotStationTableEntryRxBytesNew,
            hmStatusPublicSpotStationTableEntryTxPackets,
            hmStatusPublicSpotStationTableEntryRxPackets,
            hmStatusPublicSpotStationTableEntryLoginTime
          }
    STATUS     current
    DESCRIPTION
            "Public spot session ended"
    ::= { hmTraps 3003 }

-- {NOTIFICATION} 1.3.6.1.4.1.248.32.18.0.0.4000
hmTrapsTempmonovertemp NOTIFICATION-TYPE
    OBJECTS {
            sysDescr,
            sysName,
            hmStatusSnmpEventEntryCount,
            hmStatusHardwareInfoTemperatureDegrees
          }
    STATUS     current
    DESCRIPTION
            "Device temperature exceeds the upper tempreature limit"
    ::= { hmTraps 4000 }

-- {NOTIFICATION} 1.3.6.1.4.1.248.32.18.0.0.4001
hmTrapsTempmonnoovertemp NOTIFICATION-TYPE
    OBJECTS {
            sysDescr,
            sysName,
            hmStatusSnmpEventEntryCount,
            hmStatusHardwareInfoTemperatureDegrees
          }
    STATUS     current
    DESCRIPTION
            "Device temperature falls below the upper temperature limit and is in the normal operating range again"
    ::= { hmTraps 4001 }

-- {NOTIFICATION} 1.3.6.1.4.1.248.32.18.0.0.4002
hmTrapsTempmonundertemp NOTIFICATION-TYPE
    OBJECTS {
            sysDescr,
            sysName,
            hmStatusSnmpEventEntryCount,
            hmStatusHardwareInfoTemperatureDegrees
          }
    STATUS     current
    DESCRIPTION
            "Device temperature under-runs the lower temperature limit"
    ::= { hmTraps 4002 }

-- {NOTIFICATION} 1.3.6.1.4.1.248.32.18.0.0.4003
hmTrapsTempmonnoundertemp NOTIFICATION-TYPE
    OBJECTS {
            sysDescr,
            sysName,
            hmStatusSnmpEventEntryCount,
            hmStatusHardwareInfoTemperatureDegrees
          }
    STATUS     current
    DESCRIPTION
            "Device temperature rises above the lower temperature limit and is in the normal operating range again"
    ::= { hmTraps 4003 }

-- {NOTIFICATION} 1.3.6.1.4.1.248.32.18.0.0.5002
hmTrapsLanOvertempThrottle NOTIFICATION-TYPE
    OBJECTS {
            sysDescr,
            sysName,
            hmStatusSnmpEventEntryCount
          }
    STATUS     current
    DESCRIPTION
            "Throttling of LAN Speed due to temperature exceedance active"
    ::= { hmTraps 5002 }

-- {NOTIFICATION} 1.3.6.1.4.1.248.32.18.0.0.5003
hmTrapsLanOvertempThrottleEnd NOTIFICATION-TYPE
    OBJECTS {
            sysDescr,
            sysName,
            hmStatusSnmpEventEntryCount
          }
    STATUS     current
    DESCRIPTION
            "Throttling of LAN Speed due to temperature exceedance stopped"
    ::= { hmTraps 5003 }

-- {NOTIFICATION} 1.3.6.1.4.1.248.32.18.0.0.5004
hmTrapsLanOvertempThrottleRecommend NOTIFICATION-TYPE
    OBJECTS {
            sysDescr,
            sysName,
            hmStatusSnmpEventEntryCount
          }
    STATUS     current
    DESCRIPTION
            "Throttling of LAN Speed due to temperature exceedance recommended"
    ::= { hmTraps 5004 }

-- {NOTIFICATION} 1.3.6.1.4.1.248.32.18.0.0.5101
hmTrapsEthPortDownshift NOTIFICATION-TYPE
    OBJECTS {
            sysDescr,
            sysName,
            hmStatusSnmpEventEntryCount,
            hmStatusEthernetPortsPortsEntryPort,
            hmStatusEthernetPortsPortsEntryAssignment,
            hmStatusEthernetPortsPortsEntryDownshift
          }
    STATUS     current
    DESCRIPTION
            "Ethernet interface downshifts its speed to 100 Mbit"
    ::= { hmTraps 5101 }

-- {NOTIFICATION} 1.3.6.1.4.1.248.32.18.0.0.6100
hmTrapsWlanConfadaptRadiochannel NOTIFICATION-TYPE
    OBJECTS {
            sysDescr,
            sysName,
            hmStatusSnmpEventEntryCount
          }
    STATUS     current
    DESCRIPTION
            "Radio channel configured for WLAN interface could not be used - a different channel was used instead"
    ::= { hmTraps 6100 }

-- {NOTIFICATION} 1.3.6.1.4.1.248.32.18.0.0.6101
hmTrapsWlanConfadaptRadiomode NOTIFICATION-TYPE
    OBJECTS {
            sysDescr,
            sysName,
            hmStatusSnmpEventEntryCount,
            hmStatusWlanNetworksEntryRadioMode
          }
    STATUS     current
    DESCRIPTION
            "Radio mode configured for WLAN interface could not be used and has been adapted to match remaining settings"
    ::= { hmTraps 6101 }

-- {NOTIFICATION} 1.3.6.1.4.1.248.32.18.0.0.6102
hmTrapsWlanConfadaptBasicRate NOTIFICATION-TYPE
    OBJECTS {
            sysDescr,
            sysName,
            hmStatusSnmpEventEntryCount
          }
    STATUS     current
    DESCRIPTION
            "Basic rate configured for WLAN interface could not be used - a different rate was used instead"
    ::= { hmTraps 6102 }

-- {NOTIFICATION} 1.3.6.1.4.1.248.32.18.0.0.6103
hmTrapsWlanConfadaptEapolRate NOTIFICATION-TYPE
    OBJECTS {
            sysDescr,
            sysName,
            hmStatusSnmpEventEntryCount
          }
    STATUS     current
    DESCRIPTION
            "EAPOL rate configured for WLAN interface could not be used - a different rate was used instead"
    ::= { hmTraps 6103 }

-- {NOTIFICATION} 1.3.6.1.4.1.248.32.18.0.0.6104
hmTrapsWlanConfadaptEncryption NOTIFICATION-TYPE
    OBJECTS {
            sysDescr,
            sysName,
            hmStatusSnmpEventEntryCount
          }
    STATUS     current
    DESCRIPTION
            "Encryption settings configured for WLAN interface could not be used and have been adapted for selected radio mode"
    ::= { hmTraps 6104 }

-- {NOTIFICATION} 1.3.6.1.4.1.248.32.18.0.0.6200
hmTrapsWlanAlarmP2pSignal NOTIFICATION-TYPE
    OBJECTS {
            sysDescr,
            sysName,
            hmStatusSnmpEventEntryCount,
            hmStatusWlanInterpointsAccesspointListEntryAlarmState,
            hmStatusWlanInterpointsAccesspointListEntryRxPhySignal,
            hmStatusWlanInterpointsAccesspointListEntryLinkPhySignal
          }
    STATUS     current
    DESCRIPTION
            "Signal strength on WLAN P2P link below configured alarm limit"
    ::= { hmTraps 6200 }

-- {NOTIFICATION} 1.3.6.1.4.1.248.32.18.0.0.6201
hmTrapsWlanAlarmP2pTxtotretries NOTIFICATION-TYPE
    OBJECTS {
            sysDescr,
            sysName,
            hmStatusSnmpEventEntryCount,
            hmStatusWlanInterpointsAccesspointListEntryAlarmState,
            hmStatusWlanInterpointsAccesspointListEntryTxPackets,
            hmStatusWlanInterpointsAccesspointListEntryTotalRetries
          }
    STATUS     current
    DESCRIPTION
            "Ratio of total retries to transmitted packets on WLAN P2P link above configured alarm limit"
    ::= { hmTraps 6201 }

-- {NOTIFICATION} 1.3.6.1.4.1.248.32.18.0.0.6202
hmTrapsWlanAlarmP2pTxerrors NOTIFICATION-TYPE
    OBJECTS {
            sysDescr,
            sysName,
            hmStatusSnmpEventEntryCount,
            hmStatusWlanInterpointsAccesspointListEntryAlarmState,
            hmStatusWlanInterpointsAccesspointListEntryTxPackets,
            hmStatusWlanInterpointsAccesspointListEntryTxErrors
          }
    STATUS     current
    DESCRIPTION
            "Ratio of Tx errors to transmitted packets on WLAN P2P link above configured alarm limit"
    ::= { hmTraps 6202 }

-- {NOTIFICATION} 1.3.6.1.4.1.248.32.18.0.0.6203
hmTrapsWlanAlarmNetwSignal NOTIFICATION-TYPE
    OBJECTS {
            sysDescr,
            sysName,
            hmStatusSnmpEventEntryCount,
            hmStatusWlanNetworksEntryAlarmState
          }
    STATUS     current
    DESCRIPTION
            "Signal strength of at least one WLAN client below configured alarm limit"
    ::= { hmTraps 6203 }

-- {NOTIFICATION} 1.3.6.1.4.1.248.32.18.0.0.6204
hmTrapsWlanAlarmNetwTxtotretries NOTIFICATION-TYPE
    OBJECTS {
            sysDescr,
            sysName,
            hmStatusSnmpEventEntryCount,
            hmStatusWlanNetworksEntryAlarmState
          }
    STATUS     current
    DESCRIPTION
            "Ratio of total retries to transmitted packets for at least one client above configured alarm limit"
    ::= { hmTraps 6204 }

-- {NOTIFICATION} 1.3.6.1.4.1.248.32.18.0.0.6205
hmTrapsWlanAlarmNetwTxerrors NOTIFICATION-TYPE
    OBJECTS {
            sysDescr,
            sysName,
            hmStatusSnmpEventEntryCount,
            hmStatusWlanNetworksEntryAlarmState
          }
    STATUS     current
    DESCRIPTION
            "Ratio of Tx errors to transmitted packets for at least one client above configured alarm limit"
    ::= { hmTraps 6205 }

-- {NOTIFICATION} 1.3.6.1.4.1.248.32.18.0.0.6206
hmTrapsWlanAlarmClientSignal NOTIFICATION-TYPE
    OBJECTS {
            sysDescr,
            sysName,
            hmStatusSnmpEventEntryCount,
            hmStatusWlanClientIfcsEntryAlarmState,
            hmStatusWlanClientIfcsEntryPhySignal,
            hmStatusWlanClientIfcsEntryLinkPhySignal
          }
    STATUS     current
    DESCRIPTION
            "Signal strength on connection to WLAN AP below configured threshold"
    ::= { hmTraps 6206 }

-- {NOTIFICATION} 1.3.6.1.4.1.248.32.18.0.0.6207
hmTrapsWlanAlarmClientTxtotretries NOTIFICATION-TYPE
    OBJECTS {
            sysDescr,
            sysName,
            hmStatusSnmpEventEntryCount,
            hmStatusWlanClientIfcsEntryAlarmState,
            hmStatusWlanClientIfcsEntryTxPackets,
            hmStatusWlanClientIfcsEntryTotalRetries
          }
    STATUS     current
    DESCRIPTION
            "Ratio of total retries to transmitted packets on connection to WLAN AP above configured threshold"
    ::= { hmTraps 6207 }

-- {NOTIFICATION} 1.3.6.1.4.1.248.32.18.0.0.6208
hmTrapsWlanAlarmClientTxerrors NOTIFICATION-TYPE
    OBJECTS {
            sysDescr,
            sysName,
            hmStatusSnmpEventEntryCount,
            hmStatusWlanClientIfcsEntryAlarmState,
            hmStatusWlanClientIfcsEntryTxPackets,
            hmStatusWlanClientIfcsEntryTotalRetries
          }
    STATUS     current
    DESCRIPTION
            "Ratio of Tx errors to transmitted packets on connection to WLAN AP above configured threshold"
    ::= { hmTraps 6208 }

-- {NOTIFICATION} 1.3.6.1.4.1.248.32.18.0.0.6300
hmTrapsWlanDfsAllblocked NOTIFICATION-TYPE
    OBJECTS {
            sysDescr,
            sysName,
            hmStatusSnmpEventEntryCount
          }
    STATUS     current
    DESCRIPTION
            "WLAN cannot be taken into operation because all channels are marked as blocked due to radar detection"
    ::= { hmTraps 6300 }

-- {NOTIFICATION} 1.3.6.1.4.1.248.32.18.0.0.7000
hmTrapsUplinvversion NOTIFICATION-TYPE
    OBJECTS {
            sysDescr,
            sysName,
            hmStatusSnmpEventEntryCount,
            hmStatusConfigEventLogEntrySystemTime,
            hmStatusConfigEventLogEntryEvent,
            hmStatusConfigEventLogEntryAccess,
            hmStatusConfigEventLogEntryIpAddressNew,
            hmStatusConfigEventLogEntryIpAddress,
            hmStatusConfigEventLogEntryInfo1,
            hmStatusConfigEventLogEntryInfo2
          }
    STATUS     current
    DESCRIPTION
            "The upload of firmware failed: invalid firmware version"
    ::= { hmTraps 7000 }

-- {NOTIFICATION} 1.3.6.1.4.1.248.32.18.0.0.7001
hmTrapsUplfileexists NOTIFICATION-TYPE
    OBJECTS {
            sysDescr,
            sysName,
            hmStatusSnmpEventEntryCount,
            hmStatusConfigEventLogEntrySystemTime,
            hmStatusConfigEventLogEntryEvent,
            hmStatusConfigEventLogEntryAccess,
            hmStatusConfigEventLogEntryIpAddressNew,
            hmStatusConfigEventLogEntryIpAddress,
            hmStatusConfigEventLogEntryInfo1,
            hmStatusConfigEventLogEntryInfo2
          }
    STATUS     current
    DESCRIPTION
            "The upload of file failed: file with this version already exists"
    ::= { hmTraps 7001 }

-- {NOTIFICATION} 1.3.6.1.4.1.248.32.18.0.0.10000
hmTrapsIdsTrapEvent NOTIFICATION-TYPE
    OBJECTS {
            sysDescr,
            sysName,
            hmStatusSnmpEventEntryCount,
            hmStatusWlanWirelessIdsEventTableEntryEventType,
            hmStatusWlanWirelessIdsEventTableEntryEventRate,
            hmStatusWlanWirelessIdsEventTableEntryInterface,
            hmStatusWlanWirelessIdsEventTableEntryAttackerMac
          }
    STATUS     current
    DESCRIPTION
            "WLAN wireless IDS Event"
    ::= { hmTraps 10000 }

-- {NOTIFICATION} 1.3.6.1.4.1.248.32.18.0.0.10001
hmTrapsL2fwflt NOTIFICATION-TYPE
    OBJECTS {
            sysDescr,
            sysName,
            hmStatusSnmpEventEntryCount,
            hmStatusLanBridgeL2FirewallLogTableEntrySystemTime,
            hmStatusLanBridgeL2FirewallLogTableEntrySrcAddress,
            hmStatusLanBridgeL2FirewallLogTableEntryDstAddress,
            hmStatusLanBridgeL2FirewallLogTableEntryProtocol,
            hmStatusLanBridgeL2FirewallLogTableEntrySrcPort,
            hmStatusLanBridgeL2FirewallLogTableEntryDstPort,
            hmStatusLanBridgeL2FirewallLogTableEntryRuleIndex,
            hmStatusLanBridgeL2FirewallLogTableEntryAction
          }
    STATUS     current
    DESCRIPTION
            "LAN Bridge L2 Firewall Fault"
    ::= { hmTraps 10001 }

-- {NOTIFICATION} 1.3.6.1.4.1.248.32.18.0.0.10100
hmTrapsWlanLinkStatusLogUpdated NOTIFICATION-TYPE
    OBJECTS {
            sysDescr,
            sysName,
            hmStatusSnmpEventEntryCount,
            hmStatusWlanWlanLinkStatusLogLogTableEntryActiveSince,
            hmStatusWlanWlanLinkStatusLogLogTableEntryDownSince,
            hmStatusWlanWlanLinkStatusLogLogTableEntryRemoteMac,
            hmStatusWlanWlanLinkStatusLogLogTableEntryRemoteIp,
            hmStatusWlanWlanLinkStatusLogLogTableEntryLocalMac,
            hmStatusWlanWlanLinkStatusLogLogTableEntryLocalIp,
            hmStatusWlanWlanLinkStatusLogLogTableEntryLinkName,
            hmStatusWlanWlanLinkStatusLogLogTableEntryLinkType,
            hmStatusWlanWlanLinkStatusLogLogTableEntryCrtLinkPhySignal,
            hmStatusWlanWlanLinkStatusLogLogTableEntryAvgLinkPhySignal,
            hmStatusWlanWlanLinkStatusLogLogTableEntryMinLinkPhySignal,
            hmStatusWlanWlanLinkStatusLogLogTableEntryMaxLinkPhySignal,
            hmStatusWlanWlanLinkStatusLogLogTableEntryLinkFlapCount,
            hmStatusWlanWlanLinkStatusLogLogTableEntryFrameLoss
          }
    STATUS     current
    DESCRIPTION
            "WLAN Link Status Log Updated"
    ::= { hmTraps 10100 }

-- {NOTIFICATION} 1.3.6.1.4.1.248.32.18.0.0.10101
hmTrapsPsustate NOTIFICATION-TYPE
    OBJECTS {
            sysDescr,
            sysName,
            hmStatusSnmpEventEntryCount,
            hmStatusHardwareInfoPowerSuppliesEntryPowerSupply,
            hmStatusHardwareInfoPowerSuppliesEntryStatus
          }
    STATUS     current
    DESCRIPTION
            "Power Supply Status Changed"
    ::= { hmTraps 10101 }

-- {NOTIFICATION} 1.3.6.1.4.1.248.32.18.0.0.10102
hmTrapsSNTPClientStatus NOTIFICATION-TYPE
    OBJECTS {
        sysDescr,
        sysName,
        hmStatusSnmpEventEntryCount,
        hmStatusTimeSntpClientStatus
    }
    STATUS     current
    DESCRIPTION
        "Overall operational status of the SNTP client"
    ::= { hmTraps 10102 }

-- {NOTIFICATION} 1.3.6.1.4.1.248.32.18.0.0.10103
hmTrapsDFSRadarFound NOTIFICATION-TYPE
    OBJECTS {
        sysDescr,
        sysName,
        hmStatusSnmpEventEntryCount,
        hmStatusWlanWlanParameterEntryIfc,
        hmStatusWlanNetworksEntryBssid,
        hmStatusWlanRadiosEntryRadioChannel
    }
    STATUS     current
    DESCRIPTION
        "A radar signal has been detected on the current channel"
    ::= { hmTraps 10103 }

-- {NOTIFICATION} 1.3.6.1.4.1.248.32.18.0.0.10104
hmTrapsClRoamed NOTIFICATION-TYPE
    OBJECTS {
        sysDescr,
        sysName,
        hmStatusSnmpEventEntryCount,
        hmStatusWlanClientIfcsEntryIfc
    }
    STATUS     current
    DESCRIPTION
        "WLAN in client mode initiates roaming to another AP"
    ::= { hmTraps 10104 }
END


-- statistics ---------------------------------------------
-- module-ids     1
-- nodes          337
-- scalars        1614
-- tables         615
-- rows           615
-- columns        5194
-- notifications  105
-----------------------------------------------------------

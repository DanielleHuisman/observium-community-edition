HIRSCHMANN-GENERIC-ERROR-MIB   DEFINITIONS ::= BEGIN

-- 
-- ***********************************************************
-- Hirschmann Generic-Error MIB
-- ***********************************************************
--

IMPORTS
    MODULE-IDENTITY, OBJECT-TYPE, OBJECT-IDENTITY, 
	enterprises, Integer32							FROM SNMPv2-SMI
    TEXTUAL-CONVENTION, DisplayString, 
	AutonomousType, TestAndIncr						FROM SNMPv2-TC;

hirschmann					  OBJECT IDENTIFIER ::= { enterprises 248 }
hmMgmtSEEErrorIDGroup 	OBJECT IDENTIFIER ::= { enterprises hirschmann(248) hmManagement(16) 2  }
hmMgmtSEInfoIDGroup 	OBJECT IDENTIFIER ::= { enterprises hirschmann(248) hmManagement(16) 3  }

-- 
-- ***********************************************************
-- hmMgmtSEEErrorIDGroup
-- ***********************************************************
--
hmRedundancyConflict OBJECT-IDENTITY
           STATUS      current
           DESCRIPTION "Conflict Redundancy Protocols: Cannot enable {0} because of enabled {1}."
           ::= { hmMgmtSEEErrorIDGroup 1 }

hmRedundancyConflictPort OBJECT-IDENTITY
           STATUS      current
           DESCRIPTION "Conflict Redundancy Protocols: Cannot enable {0} because of enabled {1} on Ring Port {2}."
           ::= { hmMgmtSEEErrorIDGroup 2 }

hmMaxNumExceeded OBJECT-IDENTITY
           STATUS      current
           DESCRIPTION "Max. number exceeded for {0}."
           ::= { hmMgmtSEEErrorIDGroup 3 }
           
hmAlreadyCreated OBJECT-IDENTITY
           STATUS      current
           DESCRIPTION "Instance already created."
           ::= { hmMgmtSEEErrorIDGroup 4 }
           
hmRedundancyConflictFpgaPort OBJECT-IDENTITY
           STATUS      current
           DESCRIPTION "Conflict Redundancy Protocols: Cannot enable {0} on configured ports."
           ::= { hmMgmtSEEErrorIDGroup 5 }

hmGenericEnableConflict OBJECT-IDENTITY
           STATUS      current
           DESCRIPTION "Cannot enable {0} because {1} is enabled."
           ::= { hmMgmtSEEErrorIDGroup 6 }

hmRedundancyConflictPortShort OBJECT-IDENTITY
           STATUS      current
           DESCRIPTION "Cannot enable {0} on configured ports. Reason: {1}"
           ::= { hmMgmtSEEErrorIDGroup 7 }
           
-- hmTableFullError - Cannot add more rows to a table.
hmTableFullError OBJECT-IDENTITY
           STATUS      current
           DESCRIPTION "{0} table is full. Maximum allowed: {1}."
           ::= { hmMgmtSEEErrorIDGroup 8 }

hmFunctionNotUsableWithInterface OBJECT-IDENTITY
           STATUS      current
           DESCRIPTION "This function cannot be used with this interface."
           ::= { hmMgmtSEEErrorIDGroup 9 }

-- general conflict 
hmGeneralConflict OBJECT-IDENTITY
           STATUS      current
           DESCRIPTION "{0} conflicts with {1}. {2}."
           ::= { hmMgmtSEEErrorIDGroup 10 }
           
hmGeneralExceededRange OBJECT-IDENTITY
    	STATUS      current
    	DESCRIPTION "The {0} is exceeding the range. Maximum permissable range is {1}..{2}."
    	::= { hmMgmtSEEErrorIDGroup 11 }

hmGenericDisableConflict OBJECT-IDENTITY
         STATUS      current
         DESCRIPTION "Cannot disable {0}, because {1} is using it."
         ::= { hmMgmtSEEErrorIDGroup 12 }

-- hmMgmtSEEErrorIDGroup 100 - RMON Group
hmRmonAlarmTableFullErrorReturn OBJECT-IDENTITY
           STATUS      current
           DESCRIPTION "Alarm table full. Only {0} entries are allowed."
           ::= { hmMgmtSEEErrorIDGroup 100 }

-- hmMgmtSEEErrorIDGroup 200 - MGMT Group
hmMgmtUdpPortInUse OBJECT-IDENTITY
           STATUS      current
           DESCRIPTION "Given UDP port is already in use."
           ::= { hmMgmtSEEErrorIDGroup 200 }

hmMgmtTcpPortInUse OBJECT-IDENTITY
           STATUS      current
           DESCRIPTION "Given TCP port is already in use."
           ::= { hmMgmtSEEErrorIDGroup 201 }

hmMgmtIPAddressConflictWithMgmtIP OBJECT-IDENTITY
           STATUS      current
           DESCRIPTION "Given IP address/netmask {0}/{1} conflicts with the management IP address/netmask."
           ::= { hmMgmtSEEErrorIDGroup 202 }
           
hmMgmtIPAddressConflictWithOobIP OBJECT-IDENTITY
           STATUS      current
           DESCRIPTION "Given IP address/netmask {0}/{1} conflicts with the out-of-band management IP address/netmask."
           ::= { hmMgmtSEEErrorIDGroup 203 }
           
hmMgmtIPAddressConflictWithRouterIP OBJECT-IDENTITY
           STATUS      current
           DESCRIPTION "Given IP address/netmask {0}/{1} conflicts with a routing interface IP address/netmask."
           ::= { hmMgmtSEEErrorIDGroup 204 }

hmMgmtIPAddressConflictWithOobUsbIP OBJECT-IDENTITY
           STATUS      current
           DESCRIPTION "Given IP address/netmask {0}/{1} conflicts with the out-of-band management IP address/netmask with USB connection."
           ::= { hmMgmtSEEErrorIDGroup 205 }

-- hmMgmtSEEErrorIDGroup 300 - MGMT Group
hm2NetIPAddrInvalid OBJECT-IDENTITY
           STATUS      current
           DESCRIPTION "The {0} IP address is not valid."
           ::= { hmMgmtSEEErrorIDGroup 300 }

hm2NetIPAddrAndGateway OBJECT-IDENTITY
           STATUS      current
           DESCRIPTION "Management IP address and gateway are not on the same subnet."
           ::= { hmMgmtSEEErrorIDGroup 301 }

hm2NetIPAddrAndSubnet OBJECT-IDENTITY
           STATUS      current
           DESCRIPTION "The {0} IP address and subnet mask combination is not valid."
           ::= { hmMgmtSEEErrorIDGroup 302 }

hm2NetPrefixLengthInvalid OBJECT-IDENTITY
           STATUS      current
           DESCRIPTION "Subnet mask must have contiguous ones and be no longer than 30 bits."
           ::= { hmMgmtSEEErrorIDGroup 303 }

hm2VlanIdNotExists OBJECT-IDENTITY
           STATUS      current
           DESCRIPTION "VLAN {0} does not exist. Please create VLAN {1} before using it."
           ::= { hmMgmtSEEErrorIDGroup 304 }

-- hmMgmtSEEErrorIDGroup 400 - IPv6 Group
hm2NetIPv6AddressAlreadyExists OBJECT-IDENTITY
           STATUS      current
	       DESCRIPTION "Cannot add IPv6 Address because it already exists."
	       ::= { hmMgmtSEEErrorIDGroup 400 }

hm2NetIPv6ChangeEUIWhileEntryActive OBJECT-IDENTITY
           STATUS      current
           DESCRIPTION "Cannot change IPv6 EUI flag while entry is still active."
           ::= { hmMgmtSEEErrorIDGroup 401 }

hm2NetIPv6ChangeAddressWhileEntryActive OBJECT-IDENTITY
           STATUS      current
           DESCRIPTION "Cannot change IPv6 address while entry is still active."
           ::= { hmMgmtSEEErrorIDGroup 402 }

hm2NetIPv6IncorrectFamilyType OBJECT-IDENTITY
           STATUS      current
           DESCRIPTION "Cannot insert an incorrect address type."
           ::= { hmMgmtSEEErrorIDGroup 403 }

hm2NetIPv6EnableEUIWhilePrefixLenNot64 OBJECT-IDENTITY
           STATUS      current
           DESCRIPTION "Cannot Enable EUI while prefix length value not equal to 64."
           ::= { hmMgmtSEEErrorIDGroup 404 }

hm2NetIPv6ChangeAddressOrigin OBJECT-IDENTITY
           STATUS      current
           DESCRIPTION "Cannot change address origin value."
           ::= { hmMgmtSEEErrorIDGroup 405 }

hm2NetIPv6MaximumNumberStaticAddresses OBJECT-IDENTITY
           STATUS      current
           DESCRIPTION "Cannot insert more than the alloted maximum number of static entries."
           ::= { hmMgmtSEEErrorIDGroup 406 }

hm2NetIPv6IncorrectAddressLength OBJECT-IDENTITY
           STATUS      current
           DESCRIPTION "Cannot use an IPv6 address with an incorrect length."
           ::= { hmMgmtSEEErrorIDGroup 407 }

hm2NetIPv6AddressPrefixNotMatching OBJECT-IDENTITY
           STATUS      current
           DESCRIPTION "Cannot add IPv6 entry if the prefix and address do not match."
           ::= { hmMgmtSEEErrorIDGroup 408 }

hm2NetIPv6PrefixNotSupported OBJECT-IDENTITY
           STATUS      current
           DESCRIPTION "Cannot add IPv6 entry if the used prefix is 127."
           ::= { hmMgmtSEEErrorIDGroup 409 }

hm2NetIPv6CannotAddReservedAddress OBJECT-IDENTITY
           STATUS      current
           DESCRIPTION "Cannot add an IPv6 reserved address."
           ::= { hmMgmtSEEErrorIDGroup 410 }

hm2EntryLenCharset OBJECT-IDENTITY
           STATUS      current
           DESCRIPTION "Indicates that the chosen entry name uses not allowed character(s).
                        Allowed are alphanumerical characters and name size from 1 to 32."
           ::= { hmMgmtSEEErrorIDGroup 411 }
   
hm2UserPwdLen OBJECT-IDENTITY
           STATUS      current
           DESCRIPTION "Indicates that the chosen password is incorrect.
                        Check length, policy matching."
           ::= { hmMgmtSEEErrorIDGroup 412 }

hm2EntryNotExist OBJECT-IDENTITY
           STATUS      current
           DESCRIPTION "User does not exist."
           ::= { hmMgmtSEEErrorIDGroup 413 }

hm2MaxNumUserExceeded OBJECT-IDENTITY
           STATUS      current
           DESCRIPTION "Max. number of user exceeded."
           ::= { hmMgmtSEEErrorIDGroup 414 }

hm2NetIPv6UnreachableGatewaySubnet OBJECT-IDENTITY
           STATUS      current
           DESCRIPTION "Cannot set the IPv6 gateway from an unreachable subnet."
           ::= { hmMgmtSEEErrorIDGroup 415 }

hm2GenericDeleteError OBJECT-IDENTITY
           STATUS      current
           DESCRIPTION "Indicates that the entry cannot be deleted."
           ::= { hmMgmtSEEErrorIDGroup 450 }

hm2GenericCreateError OBJECT-IDENTITY
           STATUS      current
           DESCRIPTION "Indicates that the entry cannot be created."
           ::= { hmMgmtSEEErrorIDGroup 451 }

hm2GenericEntryNotExist OBJECT-IDENTITY
           STATUS      current
           DESCRIPTION "Indicates that the entry does not exists."
           ::= { hmMgmtSEEErrorIDGroup 452 }

hm2GenericIPv4IPv6Supported OBJECT-IDENTITY
           STATUS      current
           DESCRIPTION "Indicates that only IPv4 or IPv6 address
                        types are supported."
           ::= { hmMgmtSEEErrorIDGroup 453 }

hm2GenericMulticastAddrNotAllowed OBJECT-IDENTITY
           STATUS      current
           DESCRIPTION "Indicates that the multicast address type is
                        not allowed."
           ::= { hmMgmtSEEErrorIDGroup 454 }

hm2GenericIPAddrInvalid OBJECT-IDENTITY
           STATUS      current
           DESCRIPTION "Indicates that the value for IP address is invalid."
           ::= { hmMgmtSEEErrorIDGroup 455 }

hm2GenericSourcePortInvalid OBJECT-IDENTITY
           STATUS      current
           DESCRIPTION "Indicates that the value for source port is invalid."
           ::= { hmMgmtSEEErrorIDGroup 456 }

hm2GenericRowCommitError OBJECT-IDENTITY
           STATUS      current
           DESCRIPTION "Indicates that the row commit process is unsuccessful."
           ::= { hmMgmtSEEErrorIDGroup 457 }

hm2GenericDestIPAddrInvalid OBJECT-IDENTITY
           STATUS      current
           DESCRIPTION "Indicates that the value for destination IP address is invalid."
           ::= { hmMgmtSEEErrorIDGroup 458 }

hm2GenericDestMACAddrInvalid OBJECT-IDENTITY
           STATUS      current
           DESCRIPTION "Indicates that the value for destination MAC address is invalid."
           ::= { hmMgmtSEEErrorIDGroup 459 }

hm2GenericDestPortInvalid OBJECT-IDENTITY
           STATUS      current
           DESCRIPTION "Indicates that the value for destination port is invalid."
           ::= { hmMgmtSEEErrorIDGroup 460 }

hm2GenericSourceIPAddrInvalid OBJECT-IDENTITY
           STATUS      current
           DESCRIPTION "Indicates that the value for source IP address is invalid."
           ::= { hmMgmtSEEErrorIDGroup 461 }

hm2GenericSourceMACAddrInvalid OBJECT-IDENTITY
           STATUS      current
           DESCRIPTION "Indicates that the value for source MAC address is invalid."
           ::= { hmMgmtSEEErrorIDGroup 462 }

hm2GenericEntryInvalid OBJECT-IDENTITY
           STATUS      current
           DESCRIPTION "Indicates that the index value is out of range or contains invalid characters."
           ::= { hmMgmtSEEErrorIDGroup 463 }

hm2GenericInterfaceInvalid OBJECT-IDENTITY
           STATUS      current
           DESCRIPTION "Indicates that the interface number is not valid."
           ::= { hmMgmtSEEErrorIDGroup 464 }

hm2GenericOnlySupportsIPv4 OBJECT-IDENTITY
           STATUS      current
           DESCRIPTION "Indicates that only IPv4 address is supported."
           ::= { hmMgmtSEEErrorIDGroup 465 }

hm2GenericVlanIdInvalid OBJECT-IDENTITY
         STATUS      current
         DESCRIPTION "Indicates that the vlaue of VLAN ID is invalid and
                      cannot be processed."
         ::= { hmMgmtSEEErrorIDGroup 466 }

hm2GenericCommitInProgress OBJECT-IDENTITY
           STATUS      current
           DESCRIPTION "Indicates that the row cannot be created, modified or deleted
                        as commit is in progress."
           ::= { hmMgmtSEEErrorIDGroup 467 }

hm2GenericNameInvalid OBJECT-IDENTITY
           STATUS      current
           DESCRIPTION "Indicates that the name for the index is not valid."
           ::= { hmMgmtSEEErrorIDGroup 468 }

hm2GenericDirectionInvalid OBJECT-IDENTITY
           STATUS      current
           DESCRIPTION "Indicates that the packet direction is invalid.
                        Use 'ingress', 'egress' or 'both'."
           ::= { hmMgmtSEEErrorIDGroup 472 }

hm2GenericNameAlreadyExist OBJECT-IDENTITY
           STATUS      current
           DESCRIPTION "Indicates that the entry with the same name already
                        exists."
           ::= { hmMgmtSEEErrorIDGroup 473 }

hm2GenericMinEntryInvalid  OBJECT-IDENTITY
          STATUS         current
          DESCRIPTION  "Indicates that the lower value cannot be greater than the upper value."
          ::= { hmMgmtSEEErrorIDGroup 474 }

hm2GenericEntryExistInSharedTable  OBJECT-IDENTITY
          STATUS         current
          DESCRIPTION  "Indicates that the entry with the same name already exists in shared table."
          ::= { hmMgmtSEEErrorIDGroup 475 }

hm2GenericEntryIsReadOnly  OBJECT-IDENTITY
          STATUS         current
          DESCRIPTION  "Indicates that the field is read-only."
          ::= { hmMgmtSEEErrorIDGroup 476 }
--
-- ***********************************************************
-- hmMgmtSEInfoIDGroup
-- ***********************************************************
--
hmMgmtSEInfoValueChanged OBJECT-IDENTITY
           STATUS      current
           DESCRIPTION "Note: Value changed from {0} to {1}"
           ::= { hmMgmtSEInfoIDGroup 1 }

END

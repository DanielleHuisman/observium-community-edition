-- **************************************************************************
-- *                                                                        *
-- *                                                                        *
-- *                   Hirschmann Electronics GmbH & Co. KG                 *
-- *                                                                        *
-- *                             P.O. Box 1649                              *
-- *                           D-72602 Nuertingen                           *
-- *                                Germany                                 *
-- *                                                                        *
-- *                                                                        *
-- *                       MACH3000 SNMP PRIVATE MIB                        *
-- *                                                                        *
-- *                   Router Configuration  Release 0.5                    *
-- *                                                                        *
-- *                          Date:  30-jul-2001                            *
-- *                                                                        *
-- %*************************************************************************
-- %                                                                        *
-- %     File:          hmrouter.mib                                        *
-- %                                                                        *
-- %                                                                        *
-- %  History of changes:                                                   *
-- %                                                                        *
-- %  When      Who  What                                                   *
-- %  ========  ===  ====================================================== *
-- %  07mar01   En   created from tmsL3Mib.mi2                              *
-- %  13mar01   MH   moved to hmConfiguration.6                             *
-- %  16mar01   En   modified hmRouterMisc, hmRouterIpSubnetTable           *
-- %                 added hmRouterNumInterfaces, hmRouterIfTable,          *
-- %                 hmRouterStaticTable                                    *
-- %  16mar01   MH   official MIB-header                                    *
-- %  12apr01   En   made index variables "durable" (nvdb hack)             *
-- %  16may01   En   hmRouterIfTransmitVlanID -> hmRouterIfVlanID,          *
-- %                 hmRouterIfTReceiveVlanSet deleted                      *
-- %  27may01   En   hmRouterIpSubnetTable merged into hmRouterIfTable      *
-- %  30jul01   En   hmRouterOptions added                                  *
-- %  08aug02	MH   hmRouterRedundancy added                               *
-- %  24sep02	MH   hmRouterRedAdminStatus submitAndGo removed             *
-- %  10jan03   MH   router interface based forwarding control MIB added    *
-- %                                                                        *
-- %*************************************************************************
-- *                                                                        *
-- *    Dies ist die SNMP MIB fuer Hirschmann MACH3000                      *
-- *                                                                        *
-- *    Sollten Sie weitere Fragen haben, wenden Sie sich bitte an ihren    *
-- *    Hirschmann-Vertragspartner.                                         *
-- *                                                                        *
-- *    Aktuelle Hirschmann-Infos zu unseren Produkten erhalten Sie ueber   *
-- *    unseren WWW-Server unter http://www.hirschmann.com                  *
-- *                                                                        *
-- *    This is the SNMP MIB for the Hirschmann MACH3000                    *
-- *                                                                        *
-- *    If you have any further questions please contact your               *
-- *    Hirschmann contractual partner.                                     *
-- *                                                                        *
-- *    You can access current information about Hirschmann products        *
-- *    via our WWW server on http://www.hirschmann.com                     *
-- *                                                                        *
-- **************************************************************************

HIRSCHMANN-ROUTER-MIB  DEFINITIONS ::= BEGIN

IMPORTS     private      FROM RFC1155-SMI
            DisplayString, PhysAddress   FROM RFC1213-MIB;

-- object identifiers for this MIB
-- private             OBJECT IDENTIFIER ::= { iso(1) org(3) dod(6) internet(1) 4 }
enterprises         OBJECT IDENTIFIER ::= { private 1}
hirschmann    OBJECT IDENTIFIER ::= { enterprises 248 }
hmConfiguration     OBJECT IDENTIFIER ::= { hirschmann 14 }

hmRouter            OBJECT IDENTIFIER ::= { hmConfiguration 6 }


------------------------------------------------------------------------------
--
--  hmRouterMisc:
--      This group is used to configure and retrieve global router parameters.
--
------------------------------------------------------------------------------

hmRouterMisc  OBJECT IDENTIFIER ::= { hmRouter 1 }

hmRouterNumInterfaces  OBJECT-TYPE
        SYNTAX  INTEGER
        ACCESS  read-only
        STATUS  mandatory
        DESCRIPTION
            "The number of virtual router interfaces,
             i.e. the number of rows in hmRouterIfTable."
    ::= { hmRouterMisc 1 }

hmRouterMaxHostRouteEntries  OBJECT-TYPE
        SYNTAX  INTEGER
        ACCESS  read-only
        STATUS  mandatory
        DESCRIPTION
            "The maximum number of HOST entries in the routing table."
    ::= { hmRouterMisc 2 }

hmRouterMaxSubnetRouteEntries  OBJECT-TYPE
        SYNTAX  INTEGER
        ACCESS  read-only
        STATUS  mandatory
        DESCRIPTION
            "The maximum number of SUBNET entries in the routing table."
    ::= { hmRouterMisc 3 }

hmRouterRipEnable  OBJECT-TYPE
        SYNTAX  INTEGER { true(1), false(2) }
        ACCESS  read-write
        STATUS  mandatory
        DESCRIPTION
            "DURABLE: { false }
             This variable globally enables or disables RIP.
             Currently, RIP and OSPF cannot be enabled at the same time."
    ::= { hmRouterMisc 4 }

hmRouterOspfEnable  OBJECT-TYPE
        SYNTAX  INTEGER { true(1), false(2) }
        ACCESS  read-write
        STATUS  mandatory
        DESCRIPTION
            "DURABLE: { false }
             This variable globally enables or disables OSPF.
             Currently, RIP and OSPF cannot be enabled at the same time."
    ::= { hmRouterMisc 5 }

hmRouterDHCPServerIpAddr  OBJECT-TYPE
        SYNTAX  IpAddress
        ACCESS  read-write
        STATUS  mandatory
        DESCRIPTION
            "DURABLE:
             The IP address of the first DHCP-server to be addressed by the relay agent.
             If 0.0.0.0, DHCP relaying is switched off for this entry."
    ::= { hmRouterMisc 6 }

hmRouterDHCPServer2IpAddr  OBJECT-TYPE
        SYNTAX  IpAddress
        ACCESS  read-write
        STATUS  mandatory
        DESCRIPTION
            "DURABLE:
             The IP address of the second DHCP-server to be addressed by the relay agent.
             If 0.0.0.0, DHCP relaying is switched off for this entry."
    ::= { hmRouterMisc 7 }

hmRouterDHCPServer3IpAddr  OBJECT-TYPE
        SYNTAX  IpAddress
        ACCESS  read-write
        STATUS  mandatory
        DESCRIPTION
            "DURABLE:
             The IP address of the third DHCP-server to be addressed by the relay agent.
             If 0.0.0.0, DHCP relaying is switched off for this entry."
    ::= { hmRouterMisc 8 }

hmRouterDHCPServer4IpAddr  OBJECT-TYPE
        SYNTAX  IpAddress
        ACCESS  read-write
        STATUS  mandatory
        DESCRIPTION
            "DURABLE:
             The IP address of the fourth DHCP-server to be addressed by the relay agent.
             If 0.0.0.0, DHCP relaying is switched off for this entry."
    ::= { hmRouterMisc 9 }

------------------------------------------------------------------------------
--
--  hmRouterIfTable:
--      This table is used to configure and retrieve parameters of the
--      virtual router interfaces, i.e. vlan id and IP parameters.
--
--      Notes:
--      - A static vlan must be created for each vlan id used in this table.
--      - The subnet's IP address is calculated indirectly by logically
--        AND'ing the IP address (hmRouterIfIpAddr) with the netmask
--        (hmRouterIfSubnetMask).
--
------------------------------------------------------------------------------

hmRouterIfTable  OBJECT-TYPE
        SYNTAX  SEQUENCE OF HmRouterIfEntry
        ACCESS  not-accessible
        STATUS  mandatory
        DESCRIPTION
            "A table of interface parameters.
             There is one entry for each virtual router interface."
    ::= { hmRouter 2 }

hmRouterIfEntry  OBJECT-TYPE
        SYNTAX  HmRouterIfEntry
        ACCESS  not-accessible
        STATUS  mandatory
        DESCRIPTION
            "Parameters for a single virtual router interface."
        INDEX { hmRouterIfIndex }
    ::= { hmRouterIfTable 1 }

HmRouterIfEntry ::= SEQUENCE {
        hmRouterIfIndex                 INTEGER,
        hmRouterIfVlanID                INTEGER,
        hmRouterIfIpAddr                IpAddress,
        hmRouterIfSubnetMask            IpAddress,
        hmRouterIfName                  DisplayString,
        hmRouterIfAdminStatus           INTEGER,
        hmRouterIfOperStatus            INTEGER,
        hmRouterIfRedundantIpAddr       IpAddress
    }

hmRouterIfIndex  OBJECT-TYPE
        SYNTAX  INTEGER
        ACCESS  read-only
        STATUS  mandatory
        DESCRIPTION
            "Interface index of the virtual router interface."
    ::= { hmRouterIfEntry 1 }

hmRouterIfVlanID  OBJECT-TYPE
        SYNTAX  INTEGER (1..4094)
        ACCESS  read-write
        STATUS  mandatory
        DESCRIPTION
            "DURABLE:
             Vlan id to be used by the interface."
    ::= { hmRouterIfEntry 2 }

hmRouterIfIpAddr  OBJECT-TYPE
        SYNTAX  IpAddress
        ACCESS  read-write
        STATUS  mandatory
        DESCRIPTION
            "DURABLE:
             The IP address of the virtual router interface.
             The subnet address is calculated by logically
             AND'ing the IP address (hmRouterIfIpAddr) with the
             netmask (hmRouterIfSubnetMask)."
    ::= { hmRouterIfEntry 3 }

hmRouterIfSubnetMask  OBJECT-TYPE
        SYNTAX  IpAddress
        ACCESS  read-write
        STATUS  mandatory
        DESCRIPTION
            "DURABLE:
             Netmask of the subnet. It contains 1's in the bit positions
             for the subnet and 0's in the bit positions for the host.
             The 1's must be contiguous, starting with the left most bit."
    ::= { hmRouterIfEntry 4 }

hmRouterIfName  OBJECT-TYPE
        SYNTAX  DisplayString (SIZE (0..16))
        ACCESS  read-write
        STATUS  mandatory
        DESCRIPTION
            "DURABLE:
             A user reference name for the interface."
    ::= { hmRouterIfEntry 5 }

hmRouterIfAdminStatus  OBJECT-TYPE
        SYNTAX  INTEGER { up(1), down(2) }
        ACCESS  read-write
        STATUS  mandatory
        DESCRIPTION
        "DURABLE:
         The desired state of the interface.
         Setting this object to up (down) enables (disables)
         the virtual router interface."
    ::= { hmRouterIfEntry 6 }

hmRouterIfOperStatus  OBJECT-TYPE
        SYNTAX  INTEGER { up(1), down(2) }
        ACCESS  read-only
        STATUS  mandatory
        DESCRIPTION
        "The current operational state of the interface."
    ::= { hmRouterIfEntry 7 }

hmRouterIfRedundantIpAddr  OBJECT-TYPE
        SYNTAX  IpAddress
        ACCESS  read-write
        STATUS  mandatory
        DESCRIPTION
            "DURABLE:
			 The IP address of the redundant router interface
             which is residing on the partner router. If the partner
             router fails, the IP address is activated on the
             local routing device.
             The subnet address is calculated by logically
             AND'ing the IP address (hmRouterIfIpAddr) with the
             netmask (hmRouterIfSubnetMask). It must be the same
             as the one of hmRouterIfIpAddr."
    ::= { hmRouterIfEntry 8 }

------------------------------------------------------------------------------
--
--  hmRouterStaticTable:
--      This table may be used to configure and retrieve static routes for
--      both host and subnet IP destinations.
--
--      Use of this table is optional.
--      Static routes may also be entered using the MIB-II ipRouteTable.
--      This table is provided for convenience only.
--
--      Note that the default route entry (0.0.0.0) in this table is directly
--      mapped to the IP Gateway (i.e., next hop router) in the Hirschmann
--      Private MIB (HMPRIV-MGMT-SNMP-MIB: hmNetGatewayIPAddr).
--      This allows the agent to set the IP gateway using the serial console,
--      BOOTP, and/or DHCP.
--
------------------------------------------------------------------------------

hmRouterStaticTable  OBJECT-TYPE
        SYNTAX  SEQUENCE OF HmRouterStaticEntry
        ACCESS  not-accessible
        STATUS  mandatory
        DESCRIPTION
            "The table of static routes (subset of the MIB-II ipRouteTable)."
    ::= { hmRouter 4 }

hmRouterStaticEntry  OBJECT-TYPE
        SYNTAX  HmRouterStaticEntry
        ACCESS  not-accessible
        STATUS  mandatory
        DESCRIPTION
            "A list of static route entries."
        INDEX { hmRouterStaticDestIpAddr }
    ::= { hmRouterStaticTable 1 }

HmRouterStaticEntry ::= SEQUENCE {
        hmRouterStaticDestIpAddr        IpAddress,
        hmRouterStaticMask              IpAddress,
        hmRouterStaticNextHop           IpAddress,
        hmRouterStaticRouteName         DisplayString,
        hmRouterStaticRouteType         INTEGER
    }

hmRouterStaticDestIpAddr  OBJECT-TYPE
        SYNTAX  IpAddress
        ACCESS  read-only
        STATUS  mandatory
        DESCRIPTION
            "DURABLE:
             Host or subnet IP destination address."
    ::= { hmRouterStaticEntry 1 }

hmRouterStaticMask  OBJECT-TYPE
        SYNTAX  IpAddress
        ACCESS  read-write
        STATUS  mandatory
        DESCRIPTION
            "DURABLE:
             The mask for this IP destination.  It contains 1's in the
             bit positions for the net and subnet IDs and 0's in the
             bit positions for host ID.  The 1's must be contiguous,
             starting with the left most bit.
             Note that a host route uses a 255.255.255.255 mask."
    ::= { hmRouterStaticEntry 2 }

hmRouterStaticNextHop  OBJECT-TYPE
        SYNTAX  IpAddress
        ACCESS  read-write
        STATUS  mandatory
        DESCRIPTION
            "DURABLE:
             The IP address of the next hop of this route."
    ::= { hmRouterStaticEntry 3 }

hmRouterStaticRouteName  OBJECT-TYPE
        SYNTAX  DisplayString (SIZE (0..16))
        ACCESS  read-write
        STATUS  mandatory
        DESCRIPTION
            "DURABLE:
             A user reference name for this static route."
    ::= { hmRouterStaticEntry 4 }

hmRouterStaticRouteType  OBJECT-TYPE
        SYNTAX  INTEGER { other(1), invalid(2), direct(3), indirect(4) }
        ACCESS  read-write
        STATUS  mandatory
        DESCRIPTION
            "DURABLE:
             The type of route. See MIB-II, ipRouteType.
             Setting this object to the value invalid(2) removes the
             corresponding entry from hmRouterStaticTable and
             ipRouteTable."
    ::= { hmRouterStaticEntry 5 }


------------------------------------------------------------------------------
--
--  hmRouterOptions:
--      This group contains some additional configuration parameters.
--
------------------------------------------------------------------------------

hmRouterOptions  OBJECT IDENTIFIER ::= { hmRouter 5 }

hmRouterIcmpTimeExceededMessage  OBJECT-TYPE
        SYNTAX  INTEGER { enable(1), disable(2) }
        ACCESS  read-write
        STATUS  mandatory
        DESCRIPTION
            "DURABLE: { enable }
             Controls whether an ICMP 'Time Exceeded' message
             will be generated when the TTL (Time To Live) field
             has expired. Due to RFC1812 (Router Requirements),
             this variable is enabled by default."
    ::= { hmRouterOptions 1 }
    
    
------------------------------------------------------------------------------
--
--  hmRouterStaticArpTable:
--      This table may be used to configure and retrieve static ARP entries.
--
--      Use of this table is optional.
--      Static ARP entries may also be entered using the MIB-II ipNetToMediaTable.
--      This table is provided for convenience only.
--
------------------------------------------------------------------------------

hmRouterStaticArpTable  OBJECT-TYPE
        SYNTAX  SEQUENCE OF HmRouterStaticArpEntry
        ACCESS  not-accessible
        STATUS  mandatory
        DESCRIPTION
            "The table of static ARP entries"
    ::= { hmRouter 6 }

hmRouterStaticArpEntry  OBJECT-TYPE
        SYNTAX  HmRouterStaticArpEntry
        ACCESS  not-accessible
        STATUS  mandatory
        DESCRIPTION
            "A list of static ARP entries."
        INDEX {hmRouterStaticArpNetAddress }
    ::= { hmRouterStaticArpTable 1 }

HmRouterStaticArpEntry ::= SEQUENCE {
        hmRouterStaticArpNetAddress     IpAddress,
        hmRouterStaticArpPhysAddress    PhysAddress,
        hmRouterStaticArpName           DisplayString,
        hmRouterStaticArpType           INTEGER
    }

hmRouterStaticArpNetAddress  OBJECT-TYPE
        SYNTAX  IpAddress
        ACCESS  read-only
        STATUS  mandatory
        DESCRIPTION
            "DURABLE:
             The IpAddress corresponding to the media-
             dependent `physical' address."
    ::= { hmRouterStaticArpEntry 1 }

hmRouterStaticArpPhysAddress  OBJECT-TYPE
        SYNTAX  PhysAddress
        ACCESS  read-write
        STATUS  mandatory
        DESCRIPTION
            "DURABLE:
             The media-dependent `physical' address."
    ::= { hmRouterStaticArpEntry 2 }
    
hmRouterStaticArpName  OBJECT-TYPE
        SYNTAX  DisplayString (SIZE (0..16))
        ACCESS  read-write
        STATUS  mandatory
        DESCRIPTION
            "DURABLE:
             A user reference name for this static ARP entry."
    ::= { hmRouterStaticArpEntry 3 }

hmRouterStaticArpType  OBJECT-TYPE
        SYNTAX  INTEGER { other(1), invalid(2), static(3) }
        ACCESS  read-write
        STATUS  mandatory
        DESCRIPTION
            "DURABLE:
             The type of the ARP entry. See MIB-II, ipNetToMediaType.
             Setting this object to the value invalid(2) removes the
             corresponding entry from hmRouterStaticArpTable and
             ipNetToMediaTable."
    ::= { hmRouterStaticArpEntry 4 }    
    
    
------------------------------------------------------------------------------
--
--  hmRouterRedundancy:
--      This group contains the router redundancy MIB
--
------------------------------------------------------------------------------
hmRouterRedundancy  OBJECT IDENTIFIER ::= { hmRouter 10 }
 
hmRouterRedConfiguration OBJECT IDENTIFIER ::= { hmRouterRedundancy 1 }
hmRouterRedStats OBJECT IDENTIFIER ::= { hmRouterRedundancy 2 }
 
hmRouterRedPartnerIpAddress  OBJECT-TYPE
        SYNTAX  IpAddress
        ACCESS  read-write
        STATUS  mandatory
        DESCRIPTION
            "DURABLE:
             The IP address of the redundancy partner agent."
    ::= { hmRouterRedConfiguration 1 }
 
hmRouterRedPartnerInfo  OBJECT-TYPE
        SYNTAX  OCTET STRING (SIZE (128))
        ACCESS  read-only
        STATUS  mandatory
        DESCRIPTION
            "DURABLE:
             various configuration parameters of the partner agent"
    ::= { hmRouterRedConfiguration 2 }
 
hmRouterRedMessageInterval  OBJECT-TYPE
        SYNTAX  INTEGER (50..5000)
        ACCESS  read-write
        STATUS  mandatory
        DESCRIPTION
            "DURABLE:
             time period in msec between test packets."
    ::= { hmRouterRedConfiguration 3 }
 
hmRouterRedMessageTimeout  OBJECT-TYPE
        SYNTAX  INTEGER (500..60000)
        ACCESS  read-write
        STATUS  mandatory
        DESCRIPTION
            "DURABLE:
             time period in msec before a failure is detected.
             the value should be at least 2 times the value of
             hmRouterRedMessageInterval."
    ::= { hmRouterRedConfiguration 4 }
 
hmRouterRedAdminStatus  OBJECT-TYPE
        SYNTAX  INTEGER { enable(1), disable(2) }
        ACCESS  read-write
        STATUS  mandatory
        DESCRIPTION
            "DURABLE:
             The desired state of the redundancy mechanism.
             Setting this object to enable (disable) enables (disables)
             the router redundancy."
    ::= { hmRouterRedConfiguration 5 }
 
hmRouterRedOperStatus  OBJECT-TYPE
        SYNTAX  INTEGER { disable(1), standby(2), active(3), other(4) }
        ACCESS  read-only
        STATUS  mandatory
        DESCRIPTION
            "The operational state of the redundancy mechanism."
    ::= { hmRouterRedConfiguration 6 }
 
hmRouterRedLastErrorMessage  OBJECT-TYPE
        SYNTAX  DisplayString
        ACCESS  read-only
        STATUS  mandatory
        DESCRIPTION
            "descripting text for the redundancy error state."
    ::= { hmRouterRedConfiguration 7 }
    
hmRouterRedErrorStatus  OBJECT-TYPE
        SYNTAX  INTEGER { ok(1), error(2) }
        ACCESS  read-only
        STATUS  mandatory
        DESCRIPTION
            "The error state of the redundancy mechanism. 
			 If the value is error(2), there is an descripting
			 error text given in hmRouterRedLastErrorMessage."
    ::= { hmRouterRedConfiguration 8 }
    
 
hmRouterRedStatsTakeoverCount  OBJECT-TYPE
        SYNTAX  Counter
        ACCESS  read-only
        STATUS  mandatory
        DESCRIPTION
            "counts the times the redundancy switches over
             between the standby and active state"
    ::= { hmRouterRedStats 1 }
 
hmRouterRedStatsLastChange  OBJECT-TYPE
        SYNTAX 	TimeTicks
        ACCESS  read-only
        STATUS  mandatory
        DESCRIPTION
            "Time since system boot when there was a change in 
             the operational state of the router redundancy
             between active and standby"
    ::= { hmRouterRedStats 2 }


------------------------------------------------------------------------------
--
--  hmRouterForwardControl:
--      This group contains the router interface based forwarding control MIB
--
------------------------------------------------------------------------------
hmRouterForwardControl  OBJECT IDENTIFIER ::= { hmRouter 11 }

hmRouterForwardControlEnable  OBJECT-TYPE
        SYNTAX  INTEGER { enable(1), disable(2) }
        ACCESS  read-write
        STATUS  mandatory
        DESCRIPTION
            "DURABLE: { disable }
             enables or disables router interface based forwarding control.
             when disabled, the router forwards between all interfaces."
    ::= { hmRouterForwardControl 1 }

hmRouterForwardControlTable  OBJECT-TYPE
        SYNTAX  SEQUENCE OF HmRouterForwardControlEntry
        ACCESS  not-accessible
        STATUS  mandatory
        DESCRIPTION
            "A table for the router interface based forwarding control.
             There is one entry for each virtual router interface."
    ::= { hmRouterForwardControl 10 }

hmRouterForwardControlEntry  OBJECT-TYPE
        SYNTAX  HmRouterForwardControlEntry
        ACCESS  not-accessible
        STATUS  mandatory
        DESCRIPTION
            "Parameters for a single virtual router interface."
        INDEX { hmRouterForwardControlIndex }
    ::= { hmRouterForwardControlTable 1 }

HmRouterForwardControlEntry ::= SEQUENCE {
		hmRouterForwardControlIndex     INTEGER,
		hmRouterFCAllowedToGo           OCTET STRING,
		hmRouterFCIngressRejects        Counter,
		hmRouterFCEgressRejects         Counter
		}

hmRouterForwardControlIndex  OBJECT-TYPE
        SYNTAX  INTEGER
        ACCESS  not-accessible
        STATUS  mandatory
        DESCRIPTION
            "Interface index of the corresponding router interface."
    ::= { hmRouterForwardControlEntry 1 }

 hmRouterFCAllowedToGo	OBJECT-TYPE				
        SYNTAX  OCTET STRING (SIZE (10))
        ACCESS  read-write 
        STATUS  mandatory
        DESCRIPTION
            "DURABLE: 
             interface set of the allowed destinations from this port.
             Each octet within the value of this object specifies
             a set of eight interfaces, with the first octet specifying
             interface 1 through 8, the second octet specifying 
             interface 9 through 16, etc.
             Within each octet, the most significant bit represents
             the lowest numbered interface, and the least significant
             bit represents the highest numbered interface.
             Thus, each interface of the router is represented by a single
             bit within the value of this object.
             If that bit has a value of 1 then that interface is included
             in the set of interfaces; the interface is not included if its
             bit has a value of 0."
    ::= { hmRouterForwardControlEntry 2 }

hmRouterFCIngressRejects  OBJECT-TYPE
        SYNTAX  Counter
        ACCESS  read-only
        STATUS  mandatory
        DESCRIPTION
            "counts the frames which were received on this interface
			 and were dropped according to the forwarding rules."
    ::= { hmRouterForwardControlEntry 3 }
 
hmRouterFCEgressRejects  OBJECT-TYPE
        SYNTAX  Counter
        ACCESS  read-only
        STATUS  mandatory
        DESCRIPTION
            "counts the frames which were to be transmitted over 
            this interface and werde dropped according to the
            forwarding rules."
    ::= { hmRouterForwardControlEntry 4 }
 
 
 
------------------------------------------------------------------------------
-- RouterRedundancy traps
------------------------------------------------------------------------------

hmRouterRedTransition  TRAP-TYPE
         ENTERPRISE  hmRouterRedundancy
	     VARIABLES   { hmRouterRedOperStatus }
         DESCRIPTION "The Ring Redundancy mechanism has switched over"
       ::= 1

hmRouterRedConfigError  TRAP-TYPE
         ENTERPRISE  hmRouterRedundancy
	     VARIABLES   { hmRouterRedErrorStatus, hmRouterRedLastErrorMessage, hmRouterRedOperStatus }
         DESCRIPTION "The configuration error status changed"
       ::= 2


END

HIRSCHMANN-WAN-GPS-MIB DEFINITIONS ::= BEGIN

IMPORTS
    OBJECT-TYPE, MODULE-IDENTITY, Integer32
        FROM SNMPv2-SMI -- RFC 2578
    hmWanMgmt
    	FROM HIRSCHMANN-WAN-MIB;

hmWanGpsMib MODULE-IDENTITY
	LAST-UPDATED "201502130000Z" -- Februar 13, 2015
    ORGANIZATION "Hirschmann Automation and Control GmbH"
    CONTACT-INFO
        "Postal:     Stuttgarter Str. 45-51
                     72654 Neckartenzlingen
                     Germany
         Phone:      +49 7127 140
         E-mail:     hac.support@belden.com"
    DESCRIPTION
        "Copyright (C) 2015. All Rights Reserved."
    REVISION     "201502130000Z" -- Februar 13, 2015
    DESCRIPTION
         "Initial version."
    ::= { hmWanMgmt 7 }

hmWanGpsTimeUTC              OBJECT-TYPE
        		SYNTAX	OCTET STRING
			MAX-ACCESS	read-only
			STATUS	current
			::= { hmWanGpsMib 1 }

hmWanGpsLatitude             OBJECT-TYPE
        		SYNTAX	OCTET STRING
			MAX-ACCESS	read-only
			STATUS	current
			::= { hmWanGpsMib 2 }

hmWanGpsLongitude            OBJECT-TYPE
        		SYNTAX	OCTET STRING
			MAX-ACCESS	read-only
			STATUS	current
			::= { hmWanGpsMib 3 }

hmWanGpsAltitude             OBJECT-TYPE
        		SYNTAX	OCTET STRING
			MAX-ACCESS	read-only
			STATUS	current
			::= { hmWanGpsMib 4 }

hmWanGpsSatellites           OBJECT-TYPE
        		SYNTAX	Integer32
			MAX-ACCESS	read-only
			STATUS	current
			::= { hmWanGpsMib 5 }

hmWanGpsFixStatus            OBJECT-TYPE
        		SYNTAX	OCTET STRING
			MAX-ACCESS	read-only
			STATUS	current
			::= { hmWanGpsMib 6 }

hmWanGpsSpeedOverGround      OBJECT-TYPE
        		SYNTAX	OCTET STRING
			MAX-ACCESS	read-only
			STATUS	current
			::= { hmWanGpsMib 7 }

hmWanGpsCourseOverGround     OBJECT-TYPE
        		SYNTAX	OCTET STRING
			MAX-ACCESS	read-only
			STATUS	current
			::= { hmWanGpsMib 8 }

hmWanGpsDate                 OBJECT-TYPE
        		SYNTAX	OCTET STRING
			MAX-ACCESS	read-only
			STATUS	current
			::= { hmWanGpsMib 9 }

END

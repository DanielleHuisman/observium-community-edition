HIRSCHMANN-WAN-INFO-MIB DEFINITIONS ::= BEGIN

IMPORTS
    OBJECT-TYPE, MODULE-IDENTITY
        FROM SNMPv2-SMI -- RFC 2578
    DisplayString
        FROM SNMPv2-TC  -- RFC 2579
    hmWanMgmt
    	FROM HIRSCHMANN-WAN-MIB;

hmWanInfoMib MODULE-IDENTITY
	LAST-UPDATED "201608090000Z" -- August 9, 2016
    ORGANIZATION "Hirschmann Automation and Control GmbH"
    CONTACT-INFO
        "Postal:     Stuttgarter Str. 45-51
                     72654 Neckartenzlingen
                     Germany
         Phone:      +49 7127 140
         E-mail:     hac.support@belden.com"
    DESCRIPTION
        "Copyright (C) 2015. All Rights Reserved."
    REVISION     "201608090000Z" -- August 9, 2016
    DESCRIPTION
         "Initial version."
    ::= { hmWanMgmt 6 }

hmWanInfoProduct        	OBJECT-TYPE
			SYNTAX	DisplayString
			MAX-ACCESS	read-only
			STATUS	current
			::= { hmWanInfoMib 1 }

hmWanInfoFirmware        	OBJECT-TYPE
			SYNTAX	DisplayString
			MAX-ACCESS	read-only
			STATUS	current
			::= { hmWanInfoMib 2 }

hmWanInfoSN             	OBJECT-TYPE
			SYNTAX	DisplayString
			MAX-ACCESS	read-only
			STATUS	current
			::= { hmWanInfoMib 3 }

hmWanInfoIMEI           	OBJECT-TYPE
			SYNTAX	OCTET STRING
			MAX-ACCESS	read-only
			STATUS	current
			::= { hmWanInfoMib 4 }

hmWanInfoESN            	OBJECT-TYPE
			SYNTAX	OCTET STRING
			MAX-ACCESS	read-only
			STATUS	current
			::= { hmWanInfoMib 5 }

hmWanInfoMEID            	OBJECT-TYPE
			SYNTAX	OCTET STRING
			MAX-ACCESS	read-only
			STATUS	current
			::= { hmWanInfoMib 6 }

hmWanInfoICCID            	OBJECT-TYPE
			SYNTAX	OCTET STRING
			MAX-ACCESS	read-only
			STATUS	current
			::= { hmWanInfoMib 7 }

END

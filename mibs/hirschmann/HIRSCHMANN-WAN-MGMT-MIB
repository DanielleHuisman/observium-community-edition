HIRSCHMANN-WAN-MGMT-MIB DEFINITIONS ::= BEGIN

IMPORTS
    MODULE-IDENTITY, OBJECT-TYPE
        FROM SNMPv2-SMI -- RFC 2578
    hmWanMgmt
    	FROM HIRSCHMANN-WAN-MIB;

hmWanMgmtMib MODULE-IDENTITY
	LAST-UPDATED "201608090000Z" -- August 9, 2016
    ORGANIZATION "Hirschmann Automation and Control GmbH"
    CONTACT-INFO
        "Postal:     Stuttgarter Str. 45-51
                     72654 Neckartenzlingen
                     Germany
         Phone:      +49 7127 140
         E-mail:     hac.support@belden.com"
    DESCRIPTION
        "Copyright (C) 2015. All Rights Reserved."
    REVISION     "201608090000Z" -- August 9, 2016
    DESCRIPTION
         "Initial version."
    ::= { hmWanMgmt 9 }

hmWanMgmtAutomaticUpdate	OBJECT-TYPE
			SYNTAX  INTEGER {
                                idle (1),
                                triggered (2)
                        }
			MAX-ACCESS	read-write
			STATUS	        current
			::= { hmWanMgmtMib 1 }

END

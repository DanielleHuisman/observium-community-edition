HIRSCHMANN-WAN-STATUS-MIB DEFINITIONS ::= BEGIN

IMPORTS
    OBJECT-TYPE, MODULE-IDENTITY, Integer32
        FROM SNMPv2-SMI -- RFC 2578
    hmWanMgmt
    	FROM HIRSCHMANN-WAN-MIB;

hmWanStatusMib MODULE-IDENTITY
	LAST-UPDATED "201502130000Z" -- Februar 13, 2015
    ORGANIZATION "Hirschmann Automation and Control GmbH"
    CONTACT-INFO
        "Postal:     Stuttgarter Str. 45-51
                     72654 Neckartenzlingen
                     Germany
         Phone:      +49 7127 140
         E-mail:     hac.support@belden.com"
    DESCRIPTION
        "Copyright (C) 2015. All Rights Reserved."
    REVISION     "201502130000Z" -- Februar 13, 2015
    DESCRIPTION
         "Initial version."
    ::= { hmWanMgmt 3 }

hmWanStatusMBusOverload1	OBJECT-TYPE
			SYNTAX INTEGER {
				no (0),
				yes (1)
			}
			MAX-ACCESS	read-only
			STATUS	current
			::= { hmWanStatusMib 1 }

hmWanStatusMBusOverload2	OBJECT-TYPE
			SYNTAX INTEGER {
				no (0),
				yes (1)
			}
			MAX-ACCESS	read-only
			STATUS	current
			::= { hmWanStatusMib 2 }

hmWanStatusTemperature  	OBJECT-TYPE
			SYNTAX Integer32 
			MAX-ACCESS read-only
			STATUS current
			::= { hmWanStatusMib 3 }

hmWanStatusVoltage        	OBJECT-TYPE
			SYNTAX	Integer32 
			MAX-ACCESS read-only
			STATUS current
			::= { hmWanStatusMib 4 }

END

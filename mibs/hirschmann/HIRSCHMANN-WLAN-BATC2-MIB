HIRSCHMANN-WLAN-BATC2-MIB DEFINITIONS ::= BEGIN

-- This MIB defines the management information for Hirschmann BAT-C2.

IMPORTS
    OBJECT-TYPE, NOTIFICATION-TYPE, MODULE-IDENTITY,
    Integer32, Opaque, enterprises, Counter32
        FROM SNMPv2-SMI

    TEXTUAL-CONVENTION, DisplayString
	    FROM SNMPv2-TC

    batC2
        FROM HIRSCHMANN-WLAN-LT-MIB;

batC2MIB MODULE-IDENTITY
LAST-UPDATED "201807050000Z"
    ORGANIZATION "Hirschmann Automation and Control GmbH"
    CONTACT-INFO "Postal: Stuttgarter Str. 45-51
                  72654 Neckartenzlingen
                  Germany
                  Phone: +49 7127 140
                  E-mail: hac.support@belden.com"
    DESCRIPTION  "Hirschmann WLAN BAT-C2 MIB.
                  Copyright (C) 2018. All Rights Reserved."



    ::= { batC2 0 }

--
-- pwave traps
--
batc2Trap OBJECT IDENTIFIER ::= { batC2 4 }

alarm NOTIFICATION-TYPE
    STATUS	current
    DESCRIPTION
	"This is alarm trap triggered by alarmType with alarmValue condition."
    ::= { batc2Trap 1 }

alarmType OBJECT-TYPE
    SYNTAX	DisplayString
    MAX-ACCESS	read-only
    STATUS	current
    DESCRIPTION
	"This is the type of alarm triggered. This is sent with trap and cannot be read by any get command."
    ::= { batc2Trap 2 }

alarmValue OBJECT-TYPE
    SYNTAX	DisplayString
    MAX-ACCESS	read-only
    STATUS	current
    DESCRIPTION
	"This is the value of alarm following DAQ format. This is sent with trap and cannot be read by any get command."
    ::= { batc2Trap 3 }

END

HIRSCHMANN-WLAN-LT-MIB DEFINITIONS ::= BEGIN

IMPORTS
    MODULE-IDENTITY, enterprises
        FROM SNMPv2-SMI
    hirschmann 
    	FROM HMPRIV-MGMT-SNMP-MIB;

hmWlanLtMgmt MODULE-IDENTITY
    LAST-UPDATED "201807050000Z"
    ORGANIZATION "Hirschmann Automation and Control GmbH"
    CONTACT-INFO "Postal: Stuttgarter Str. 45-51
                  72654 Neckartenzlingen
                  Germany
                  Phone: +49 7127 140
                  E-mail: hac.support@belden.com"
    DESCRIPTION  "Hirschmann WLAN LT-Products Management MIB.
                  Copyright (C) 2018. All Rights Reserved."

-- revision history
    REVISION     "201807050000Z"  -- July 05, 2018
    DESCRIPTION  "The initial version of the MIB module."


    ::= { hirschmann(248) hmWlan(32) 100 }

hmWlanLtProducts    OBJECT IDENTIFIER ::= { hmWlanLtMgmt 1 }
batC2		        OBJECT IDENTIFIER ::= { hmWlanLtProducts 15 }

END

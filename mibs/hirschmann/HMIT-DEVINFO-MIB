------------------------------------------------------------------------------
--
--  File         : HMIT-DEVICE-INFO.mib
--  Description  : 
--  Version      :  
--  Copyright    : Copyright ? 2019 Belden Singapore Pte Ltd., All rights reserved. 
--
-- $Id:
-- 
------------------------------------------------------------------------------

HMIT-DEVINFO-MIB DEFINITIONS ::= BEGIN

IMPORTS
	TEXTUAL-CONVENTION, TruthValue, DisplayString
		FROM SNMPv2-TC
	MODULE-IDENTITY, OBJECT-TYPE, IpAddress, Unsigned32
		FROM SNMPv2-SMI
	hmITMgmt
		FROM HMIT-SMI; 
  	                
hmITDeviceInfoMib	MODULE-IDENTITY
	LAST-UPDATED "201001081700Z"
	ORGANIZATION "Belden Singapore Pte Ltd."
	CONTACT-INFO
		"Belden Singapore Pte Ltd."
	DESCRIPTION
		"Device Information."
	REVISION "201001081700Z"
    DESCRIPTION
		"The initial revision of this mib module "
	::= { hmITMgmt 602 }

hmITDeviceInformation  OBJECT IDENTIFIER ::= {hmITDeviceInfoMib 1}

hmITDeviceSerialNumber  OBJECT-TYPE
    SYNTAX  DisplayString
    ACCESS  read-only
    STATUS  current
    DESCRIPTION
            "The serial number of the device."
    ::= {hmITDeviceInformation 1}

hmITDevHwModel  OBJECT-TYPE
	SYNTAX  DisplayString(SIZE(0..128))
	ACCESS  read-only
	STATUS  current
	DESCRIPTION
		"The  Hardware Model of the device."
::= {hmITDeviceInformation 2}

hmITDeviceInfoTable  OBJECT-TYPE
    SYNTAX  SEQUENCE OF   HmITDeviceInfoEntry
    ACCESS  not-accessible
    STATUS  current
    DESCRIPTION
            "Device info table"
    ::= {hmITDeviceInformation 100}   
    

hmITDeviceInfoEntry  OBJECT-TYPE
    SYNTAX  HmITDeviceInfoEntry
    ACCESS  not-accessible
    STATUS  current
    DESCRIPTION
            "Device info entry"
    INDEX   {hmITDevIndex}
    ::= {hmITDeviceInfoTable 1}
	
HmITDeviceInfoEntry ::= SEQUENCE
{
	hmITDevIndex INTEGER,
	hmITDevName DisplayString,
	hmITDevType Unsigned32,
	hmITDevHwSerial DisplayString,
	hmITDevHwVersion DisplayString,
	hmITDevSwVersion DisplayString,
	hmITDevCfgVersion DisplayString
}

hmITDevIndex  OBJECT-TYPE
    SYNTAX  INTEGER (1..2147483647)
    ACCESS  not-accessible
    STATUS  current
    DESCRIPTION
            "The index of this table."
    ::= {hmITDeviceInfoEntry 1}

hmITDevName  OBJECT-TYPE
    SYNTAX  DisplayString
    ACCESS  read-only
    STATUS  current
    DESCRIPTION
            "The name of the device."
    ::= {hmITDeviceInfoEntry 2}

hmITDevType  OBJECT-TYPE
    SYNTAX  Unsigned32
    ACCESS  read-only
    STATUS  current
    DESCRIPTION
            "The type of the device."
    ::= {hmITDeviceInfoEntry 3}

hmITDevHwSerial  OBJECT-TYPE
    SYNTAX  DisplayString
    ACCESS  read-only
    STATUS  current
    DESCRIPTION
            "The hardware serial of the device."
    ::= {hmITDeviceInfoEntry 4}

hmITDevHwVersion  OBJECT-TYPE
    SYNTAX  DisplayString
    ACCESS  read-only
    STATUS  current
    DESCRIPTION
            "The hardware version of the device."
    ::= {hmITDeviceInfoEntry 5}

hmITDevSwVersion  OBJECT-TYPE
    SYNTAX  DisplayString
    ACCESS  read-only
    STATUS  current
    DESCRIPTION
            "Device SW version"
    ::= {hmITDeviceInfoEntry 6}

hmITDevCfgVersion  OBJECT-TYPE
    SYNTAX  DisplayString(SIZE(0..31))
    ACCESS  read-only
    STATUS  current
    DESCRIPTION
            "The version of the configurate file of the system flash."
    ::= {hmITDeviceInfoEntry 7}
END

------------------------------------------------------------------------------
--
--  File         : HMIT-SW-PORT-INFO-MIB.mib
--  Description  : 
--  Version      :  
--  Copyright    : Copyright ⓒ 2019 Belden Singapore Pte Ltd., All rights reserved. 
--
-- $Id:
-- 
------------------------------------------------------------------------------

------------------------------------------------------------------------------

	HMIT-SW-PORT-INFO-MIB DEFINITIONS ::= BEGIN
 
		IMPORTS
			hmITSwitchTech			
				FROM HMIT-SMI			
			OBJECT-TYPE, MODULE-IDENTITY			
				FROM SNMPv2-SMI
			hmITSwPortMIB
				FROM HMIT-SW-PORT-MGR-MIB
			hmITSwPortmgrMIB
				FROM HMIT-SW-PORT-MGR-MIB;
	
	
		-- 1.3.6.1.4.1.248.100.1.6.3.1
		hmITPortInfoMIB MODULE-IDENTITY 
			LAST-UPDATED "201001081700Z"		-- March 02, 2020 at 22:34 GMT
			ORGANIZATION 
				"Belden Singapore Pte Ltd."
			CONTACT-INFO 
				"Belden Singapore Pte Ltd."
			DESCRIPTION 
				"Port Module"
			REVISION "201001081700Z"		-- January 08, 2010 at 17:00 GMT
			DESCRIPTION 
				"The initial revision of this mib module "
			::= { hmITSwPortmgrMIB 1 }

		hmITMaxPortNumOfBoard OBJECT-TYPE
			SYNTAX INTEGER (1..2147483647)
			MAX-ACCESS read-only
			STATUS current
			DESCRIPTION
				"The max number of the ports on the board."
			::= { hmITPortInfoMIB 1 }

		
		hmITStartPortId OBJECT-TYPE
			SYNTAX INTEGER (1..2147483647)
			MAX-ACCESS read-only
			STATUS current
			DESCRIPTION
				"The number of the first port."
			::= { hmITPortInfoMIB 2 }
	
	END

------------------------------------------------------------------------------
--
--  File         : HMIT-SW-PORTMGR-DDMI-MIB.mib
--  Description  : 
--  Version      :  
--  Copyright    : Copyright ⓒ 2019 Belden Singapore Pte Ltd., Ltd , All rights reserved. 
--
-- $Id:
-- 
------------------------------------------------------------------------------

HMIT-SW-PORTMGR-DDMI-MIB DEFINITIONS ::= BEGIN

IMPORTS
        MODULE-IDENTITY, OBJECT-TYPE, Integer32, Unsigned32, IpAddress, Counter64
                FROM SNMPv2-SMI
        RowStatus, DisplayString, PhysAddress, MacAddress
                FROM SNMPv2-TC           
        hmITSwPortmgrMIB
				FROM HMIT-SW-PORT-MGR-MIB; 

portDDMITable   OBJECT-TYPE
    SYNTAX  SEQUENCE OF PortDDMIEntry
    MAX-ACCESS  not-accessible
    STATUS  current
    DESCRIPTION
            "The information of the DDMI on the switch."
    ::= {hmITSwPortmgrMIB 6}
    
portDDMIEntry   OBJECT-TYPE
    SYNTAX  PortDDMIEntry
    MAX-ACCESS  not-accessible
    STATUS  current
    DESCRIPTION
            "The information of the DDMI on the switch."
    INDEX   { portDDMIIFindex }
    ::= {portDDMITable 1}

PortDDMIEntry ::=
SEQUENCE {
    portDDMIIFindex                     INTEGER, 
    portDDMIDeviceId                    DisplayString,
    portDDMIConnector                   DisplayString,
    portDDMIEncoding                    DisplayString,
--    portDDMIBitRate                     DisplayString,
    portDDMITransmitLen                 DisplayString,
    portDDMIVendorOUI                   OCTET STRING,
    portDDMIVendorName                  DisplayString,
    portDDMIPartName                    DisplayString,
    portDDMIRevisionNum                 DisplayString,
    portDDMILaserWaveLen                INTEGER,
    portDDMISerialNum                   DisplayString,
    portDDMIClass                       INTEGER,
    portDDMIProductDate                 DisplayString,
    portDDMIVendorSpecific              OCTET STRING,
    portDDMITmperature                  DisplayString,
    portDDMITempHighAlarmThreshold      DisplayString,
    portDDMITempLowAlarmThreshold       DisplayString,
    portDDMITempHighWarningThreshold    DisplayString,
    portDDMITempLowWarningThreshold     DisplayString,
    portDDMIVoltage                     DisplayString,
    portDDMIVolHighAlarmThreshold       DisplayString,
    portDDMIVolLowAlarmThreshold        DisplayString,
    portDDMIVolHighWarningThreshold     DisplayString,
    portDDMIVolLowWarningThreshold      DisplayString,    
    
    portDDMITxBias                      DisplayString,       
    portDDMITxBias2                      DisplayString,
    portDDMITxBias3                      DisplayString,
    portDDMITxBias4                      DisplayString,

    portDDMITxBiasHighAlarmThreshold    DisplayString,
    portDDMITxBiasLowAlarmThreshold     DisplayString,
    portDDMITxBiasHighWarningThreshold  DisplayString,
    portDDMITxBiasLowWarningThreshold   DisplayString,
    portDDMITxPower                     DisplayString,
    portDDMITxPower2                    DisplayString,
    portDDMITxPower3                    DisplayString,
    portDDMITxPower4                    DisplayString,
    portDDMITxPowerHighAlarmThreshold   DisplayString,
    portDDMITxPowerLowAlarmThreshold    DisplayString,
    portDDMITxPowerHighWarningThreshold DisplayString,
    portDDMITxPowerLowWarningThreshold  DisplayString,   
    
    portDDMIRxPower                     DisplayString,
    portDDMIRxPower2                     DisplayString,
    portDDMIRxPower3                     DisplayString,
    portDDMIRxPower4                     DisplayString,    
    
    portDDMIRxPowerHighAlarmThreshold   DisplayString,
    portDDMIRxPowerLowAlarmThreshold    DisplayString,
    portDDMIRxPowerHighWarningThreshold DisplayString,
    portDDMIRxPowerLowWarningThreshold  DisplayString,   
    
    portDDMIAlarmStatus                 OCTET STRING,
    portDDMIAlarmStatus2                 OCTET STRING,
    portDDMIAlarmStatus3                 OCTET STRING,
    portDDMIAlarmStatus4                 OCTET STRING,

    portDDMIWarningStatus               OCTET STRING,
    portDDMIWarningStatus2               OCTET STRING,
    portDDMIWarningStatus3               OCTET STRING,
    portDDMIWarningStatus4               OCTET STRING,

    portDDMIIsMonotorImpt               INTEGER,
    portDDMIResult                      INTEGER
}
 
portDDMIIFindex OBJECT-TYPE
    SYNTAX  INTEGER (1..2147483647)
    MAX-ACCESS  read-only
    STATUS  current
    DESCRIPTION
            "The index of the port."
    ::= {portDDMIEntry 1}

portDDMIDeviceId    OBJECT-TYPE
    SYNTAX  DisplayString (SIZE(0..16))
    MAX-ACCESS  read-only
    STATUS  current
    DESCRIPTION
            "The physical device described by
            the two-wire interface information."
    ::= {portDDMIEntry 2}
    
portDDMIConnector   OBJECT-TYPE
    SYNTAX  DisplayString (SIZE(0..32))
    MAX-ACCESS  read-only
    STATUS  current
    DESCRIPTION
            "The external optical or electrical cable connector 
            provided as the media interface."
    ::= {portDDMIEntry 3}
    
portDDMIEncoding  OBJECT-TYPE
    SYNTAX  DisplayString (SIZE(0..64))
    MAX-ACCESS  read-only
    STATUS  current
    DESCRIPTION
            "The serial encoding mechanisms that are supported
            by the particular transceiver."
    ::= {portDDMIEntry 4}

----------------------------------hide OID #69356----------------------------------
--portDDMIBitRate OBJECT-TYPE
--    SYNTAX  DisplayString (SIZE(0..32))
--    MAX-ACCESS  read-only
--    STATUS  current
--    DESCRIPTION
--            "The range of bit(signaling) rate, includes those bits necessary to
--            encode and delimit the singal as well as those bits carrying data
--            information. A value of 0 incdicateds that the bit rate is
--            not specified and must be determined from the transceiver technology.
--            The acutal information transfer rate will depend on the encoding of
--            the data, as defined by the encoding value."
--    ::= {portDDMIEntry 5}
------------------------------------------------------------------------------------

portDDMITransmitLen OBJECT-TYPE
    SYNTAX  DisplayString (SIZE(0..32))
    MAX-ACCESS  read-only
    STATUS  current
    DESCRIPTION
            "The link length that is supported by the transceiver while
            operating in compliance with the applicable standards using
            single mode fiber, 62.5 micron multimode OM1[200MHz*km at 850nm,
            500MHz*km at 1310nm] fiber, 50 micron multimode OM2[500MHz*km at 850nm]
            fiber, 50 micron multimode OM3[2000MHz*km] fiber, copper cable, etc."
    ::= {portDDMIEntry 6}    

portDDMIVendorOUI   OBJECT-TYPE
    SYNTAX  OCTET STRING
    MAX-ACCESS  read-only
    STATUS  current
    DESCRIPTION
            "The vendor organizationally unique identifier(OUI)
            of the transceiver."
    ::= {portDDMIEntry 7}
    
portDDMIVendorName  OBJECT-TYPE
    SYNTAX  DisplayString (SIZE(0..16))
    MAX-ACCESS  read-only
    STATUS  current
    DESCRIPTION
            "The vendor name of the transceiver."
    ::= {portDDMIEntry 8} 
    
portDDMIPartName    OBJECT-TYPE
    SYNTAX  DisplayString (SIZE(0..16))
    MAX-ACCESS  read-only
    STATUS  current
    DESCRIPTION
            "The vendor part number(vendor PN) of the transceiver. A value
            of all zero indicates that the vendor PN is unspecified."
    ::= {portDDMIEntry 9} 
    
portDDMIRevisionNum OBJECT-TYPE
    SYNTAX  DisplayString (SIZE(0..4))
    MAX-ACCESS  read-only
    STATUS  current
    DESCRIPTION
            "The vendor revision number(vendor rev) of the transceiver.
            A value of all zero indicates that the vendor rev is unspecified."
    ::= {portDDMIEntry 10}
    
portDDMILaserWaveLen    OBJECT-TYPE
    SYNTAX  INTEGER (0..2147483647)
    MAX-ACCESS  read-only
    STATUS  current
    DESCRIPTION
            "The laser wavelength of the transceiver."
    ::= {portDDMIEntry 11} 
    
portDDMISerialNum   OBJECT-TYPE
    SYNTAX  DisplayString (SIZE(0..16))
    MAX-ACCESS  read-only
    STATUS  current
    DESCRIPTION
            "The vendor serial number(vendor SN) of the transceiver.
            A value of all zero indicates that the vendor SN is unspecified."
    ::= {portDDMIEntry 12}
    
portDDMIClass   OBJECT-TYPE
    SYNTAX  INTEGER (0..2147483647)
    MAX-ACCESS  read-only
    STATUS  current
    DESCRIPTION
            "No longer in use."
    ::= {portDDMIEntry 13} 
    
portDDMIProductDate OBJECT-TYPE
    SYNTAX  DisplayString (SIZE(0..8))
    MAX-ACCESS  read-only
    STATUS  current
    DESCRIPTION
            "The produce date of the transceiver."
    ::= {portDDMIEntry 14} 
    
portDDMIVendorSpecific  OBJECT-TYPE
    SYNTAX  OCTET STRING
    MAX-ACCESS  read-only
    STATUS  current
    DESCRIPTION
            "The specific content from the vendor of the transceiver."
    ::= {portDDMIEntry 15}
    
portDDMITmperature  OBJECT-TYPE
    SYNTAX  DisplayString (SIZE(0..16))
    MAX-ACCESS  read-only
    STATUS  current
    DESCRIPTION
            "The internal temperature measured by the transceiver itself."
    ::= {portDDMIEntry 16}
    
portDDMITempHighAlarmThreshold  OBJECT-TYPE
    SYNTAX  DisplayString (SIZE(0..16))
    MAX-ACCESS  read-only
    STATUS  current
    DESCRIPTION
            "The high alarm threshold of the temprature for the transceiver."
    ::= {portDDMIEntry 17}
    
portDDMITempLowAlarmThreshold   OBJECT-TYPE
    SYNTAX  DisplayString (SIZE(0..16))
    MAX-ACCESS  read-only
    STATUS  current
    DESCRIPTION
            "The low alarm threshold of the temprature for the transceiver."
    ::= {portDDMIEntry 18}  
        
portDDMITempHighWarningThreshold    OBJECT-TYPE
    SYNTAX  DisplayString (SIZE(0..16))
    MAX-ACCESS  read-only
    STATUS  current
    DESCRIPTION
            "The high warning threshold of the temprature for the transceiver."
    ::= {portDDMIEntry 19}
    
portDDMITempLowWarningThreshold OBJECT-TYPE  
    SYNTAX  DisplayString (SIZE(0..16))
    MAX-ACCESS  read-only
    STATUS  current
    DESCRIPTION
            "The low warning threshold of the temprature for the transceiver."
    ::= {portDDMIEntry 20} 
    
portDDMIVoltage OBJECT-TYPE
    SYNTAX DisplayString (SIZE(0..16)) 
    MAX-ACCESS  read-only
    STATUS  current
    DESCRIPTION
            "The supply voltage measured by the transceiver itself."
    ::= {portDDMIEntry 21}
    
portDDMIVolHighAlarmThreshold   OBJECT-TYPE
    SYNTAX  DisplayString (SIZE(0..16))
    MAX-ACCESS  read-only
    STATUS  current
    DESCRIPTION
            "The high alarm threshold of the voltage for the transceiver."
    ::= {portDDMIEntry 22} 
    
portDDMIVolLowAlarmThreshold    OBJECT-TYPE
    SYNTAX  DisplayString (SIZE(0..16))
    MAX-ACCESS  read-only
    STATUS  current
    DESCRIPTION
            "The low alarm threshold of the voltage for the transceiver."
    ::= {portDDMIEntry 23} 
    
portDDMIVolHighWarningThreshold OBJECT-TYPE
    SYNTAX DisplayString (SIZE(0..16))
    MAX-ACCESS  read-only
    STATUS  current
    DESCRIPTION
            "The high warning threshold of the voltage for the transceiver."
    ::= {portDDMIEntry 24}
    
portDDMIVolLowWarningThreshold  OBJECT-TYPE
    SYNTAX  DisplayString (SIZE(0..16))
    MAX-ACCESS  read-only
    STATUS  current
    DESCRIPTION
            "The low warning threshold of the voltage for the transceiver."
    ::= {portDDMIEntry 25} 
    
portDDMITxBias  OBJECT-TYPE
    SYNTAX  DisplayString (SIZE(0..16))
    MAX-ACCESS  read-only
    STATUS  current
    DESCRIPTION
            "The tx bias measured by the transceiver itself."
    ::= {portDDMIEntry 26}     

portDDMITxBiasHighAlarmThreshold    OBJECT-TYPE 
    SYNTAX  DisplayString (SIZE(0..16))
    MAX-ACCESS  read-only
    STATUS  current
    DESCRIPTION
            "The high alarm threshold of the tx bias for the transceiver."
    ::= {portDDMIEntry 27}
    
portDDMITxBiasLowAlarmThreshold OBJECT-TYPE
    SYNTAX  DisplayString (SIZE(0..16))
    MAX-ACCESS  read-only
    STATUS  current
    DESCRIPTION
            "The low alarm threshold of the tx bias for the transceiver."
    ::= {portDDMIEntry 28} 
    
portDDMITxBiasHighWarningThreshold  OBJECT-TYPE
    SYNTAX  DisplayString(SIZE(0..16))
    MAX-ACCESS  read-only
    STATUS  current
    DESCRIPTION
            "The high warning threshold of the tx bias for the transceiver."
    ::= {portDDMIEntry 29}   
    
portDDMITxBiasLowWarningThreshold   OBJECT-TYPE
    SYNTAX  DisplayString (SIZE(0..16))
    MAX-ACCESS  read-only
    STATUS  current
    DESCRIPTION
            "The low warning threshold of the tx bias for the transceiver."
    ::= {portDDMIEntry 30} 
    
portDDMITxPower OBJECT-TYPE
    SYNTAX  DisplayString (SIZE(0..16))
    MAX-ACCESS  read-only
    STATUS  current
    DESCRIPTION
            "The tx power measured by the transceiver itself."
    ::= {portDDMIEntry 31}
    
portDDMITxPowerHighAlarmThreshold   OBJECT-TYPE
    SYNTAX  DisplayString (SIZE(0..16))
    MAX-ACCESS  read-only
    STATUS  current
    DESCRIPTION
            "The high alarm threshold of the tx power for the transceiver."
    ::= {portDDMIEntry 32} 
    
portDDMITxPowerLowAlarmThreshold    OBJECT-TYPE
    SYNTAX  DisplayString (SIZE(0..16))
    MAX-ACCESS  read-only
    STATUS  current
    DESCRIPTION
            "The low alarm threshold of the tx power for the transceiver."
    ::= {portDDMIEntry 33}
    
portDDMITxPowerHighWarningThreshold OBJECT-TYPE
    SYNTAX  DisplayString (SIZE(0..16))
    MAX-ACCESS  read-only
    STATUS  current
    DESCRIPTION
            "The high warning threshold of the tx power for the transceiver."
    ::= {portDDMIEntry 34} 
    
portDDMITxPowerLowWarningThreshold  OBJECT-TYPE
    SYNTAX  DisplayString (SIZE(0..16))
    MAX-ACCESS  read-only
    STATUS  current
    DESCRIPTION
            "The low warning threshold of the tx power for the transceiver."
    ::= {portDDMIEntry 35} 
    
portDDMIRxPower OBJECT-TYPE
    SYNTAX  DisplayString (SIZE(0..16))
    MAX-ACCESS  read-only
    STATUS  current
    DESCRIPTION
            "The rx power measured by the transceiver itself."
    ::= {portDDMIEntry 36}    
      
portDDMIRxPowerHighAlarmThreshold   OBJECT-TYPE
    SYNTAX  DisplayString (SIZE(0..16))
    MAX-ACCESS  read-only
    STATUS  current
    DESCRIPTION
            "The high alarm threshold of the rx power for the transceiver."
    ::= {portDDMIEntry 37}
    
portDDMIRxPowerLowAlarmThreshold    OBJECT-TYPE
    SYNTAX  DisplayString (SIZE(0..16))
    MAX-ACCESS  read-only
    STATUS  current
    DESCRIPTION
            "The low alarm threshold of the rx power for the transceiver."
    ::= {portDDMIEntry 38}
    
portDDMIRxPowerHighWarningThreshold OBJECT-TYPE
    SYNTAX  DisplayString (SIZE(0..16))
    MAX-ACCESS  read-only
    STATUS  current
    DESCRIPTION
            "The high warning threshold of the rx power for the transceiver."
    ::= {portDDMIEntry 39}   
    
portDDMIRxPowerLowWarningThreshold  OBJECT-TYPE
    SYNTAX  DisplayString (SIZE(0..16))
    MAX-ACCESS  read-only
    STATUS  current
    DESCRIPTION
            "The low warning threshold of the rx power for the transceiver."
    ::= {portDDMIEntry 40}  
    
portDDMIAlarmStatus OBJECT-TYPE
    SYNTAX  OCTET STRING
    MAX-ACCESS  read-only
    STATUS  current
    DESCRIPTION
            "The current alarm status of the temprature/supply voltage
            /TX bias/TX power/RX power for the transceiver."
    ::= {portDDMIEntry 41}     
    
portDDMIWarningStatus   OBJECT-TYPE
    SYNTAX  OCTET STRING
    MAX-ACCESS  read-only
    STATUS  current
    DESCRIPTION
            "The current warning status of the temprature/supply voltage
            /TX bias/TX power/RX power for the transceiver."
    ::= {portDDMIEntry 42}           
 
portDDMIIsMonotorImpt   OBJECT-TYPE
    SYNTAX  INTEGER
		{
		no_monitor(1),
		has_monitor(2)
		}
    MAX-ACCESS read-only
    STATUS  current
    DESCRIPTION
            "The diagnostic monitoring type that is implemented in the transceiver."
    ::= {portDDMIEntry 43} 
   
portDDMIResult  OBJECT-TYPE
	SYNTAX INTEGER
		{
		ok(1),
		offline(2),
		timeout(3),
		error(4)
		}
    MAX-ACCESS read-only
    STATUS  current
    DESCRIPTION
            "The operation result for the transceiver."
    ::= {portDDMIEntry 44}       
    
                    
                    
                    
portDDMITxBias2  OBJECT-TYPE
    SYNTAX  DisplayString (SIZE(0..16))
    MAX-ACCESS  read-only
    STATUS  current
    DESCRIPTION
            "The tx bias measured by the transceiver itself."
    ::= {portDDMIEntry 45}  

portDDMITxBias3  OBJECT-TYPE
    SYNTAX  DisplayString (SIZE(0..16))
    MAX-ACCESS  read-only
    STATUS  current
    DESCRIPTION
            "The tx bias measured by the transceiver itself."
    ::= {portDDMIEntry 46}  

portDDMITxBias4  OBJECT-TYPE
    SYNTAX  DisplayString (SIZE(0..16))
    MAX-ACCESS  read-only
    STATUS  current
    DESCRIPTION
            "The tx bias measured by the transceiver itself."
    ::= {portDDMIEntry 47}  
    
portDDMIRxPower2 OBJECT-TYPE
    SYNTAX  DisplayString (SIZE(0..16))
    MAX-ACCESS  read-only
    STATUS  current
    DESCRIPTION
            "The rx power measured by the transceiver itself."
    ::= {portDDMIEntry 48} 

portDDMIRxPower3 OBJECT-TYPE
    SYNTAX  DisplayString (SIZE(0..16))
    MAX-ACCESS  read-only
    STATUS  current
    DESCRIPTION
            "The rx power measured by the transceiver itself."
    ::= {portDDMIEntry 49} 

portDDMIRxPower4 OBJECT-TYPE
    SYNTAX  DisplayString (SIZE(0..16))
    MAX-ACCESS  read-only
    STATUS  current
    DESCRIPTION
            "The rx power measured by the transceiver itself."
    ::= {portDDMIEntry 50}     
    
portDDMIAlarmStatus2 OBJECT-TYPE
    SYNTAX  OCTET STRING
    MAX-ACCESS  read-only
    STATUS  current
    DESCRIPTION
            "The current alarm status of the temprature/supply voltage
            /TX bias/TX power/RX power for the transceiver."
    ::= {portDDMIEntry 51} 

portDDMIAlarmStatus3 OBJECT-TYPE
    SYNTAX  OCTET STRING
    MAX-ACCESS  read-only
    STATUS  current
    DESCRIPTION
            "The current alarm status of the temprature/supply voltage
            /TX bias/TX power/RX power for the transceiver."
    ::= {portDDMIEntry 52} 

portDDMIAlarmStatus4 OBJECT-TYPE
    SYNTAX  OCTET STRING
    MAX-ACCESS  read-only
    STATUS  current
    DESCRIPTION
            "The current alarm status of the temprature/supply voltage
            /TX bias/TX power/RX power for the transceiver."
    ::= {portDDMIEntry 53}        
    
portDDMIWarningStatus2   OBJECT-TYPE
    SYNTAX  OCTET STRING
    MAX-ACCESS  read-only
    STATUS  current
    DESCRIPTION
            "The current warning status of the temprature/supply voltage
            /TX bias/TX power/RX power for the transceiver."
    ::= {portDDMIEntry 54} 

portDDMIWarningStatus3   OBJECT-TYPE
    SYNTAX  OCTET STRING
    MAX-ACCESS  read-only
    STATUS  current
    DESCRIPTION
            "The current warning status of the temprature/supply voltage
            /TX bias/TX power/RX power for the transceiver."
    ::= {portDDMIEntry 55} 

portDDMIWarningStatus4   OBJECT-TYPE
    SYNTAX  OCTET STRING
    MAX-ACCESS  read-only
    STATUS  current
    DESCRIPTION
            "The current warning status of the temprature/supply voltage
            /TX bias/TX power/RX power for the transceiver."
    ::= {portDDMIEntry 56} 

portDDMITxPower2 OBJECT-TYPE
    SYNTAX  DisplayString (SIZE(0..16))
    MAX-ACCESS  read-only
    STATUS  current
    DESCRIPTION
            "The tx power measured by the transceiver itself."
    ::= {portDDMIEntry 57}

portDDMITxPower3 OBJECT-TYPE
    SYNTAX  DisplayString (SIZE(0..16))
    MAX-ACCESS  read-only
    STATUS  current
    DESCRIPTION
            "The tx power measured by the transceiver itself."
    ::= {portDDMIEntry 58}

portDDMITxPower4 OBJECT-TYPE
    SYNTAX  DisplayString (SIZE(0..16))
    MAX-ACCESS  read-only
    STATUS  current
    DESCRIPTION
            "The tx power measured by the transceiver itself."
    ::= {portDDMIEntry 59} 

opticalModuleExceptionTrap  OBJECT IDENTIFIER ::= {portDDMITable 100}


opticalModuleTemperatureHighWarnTrap NOTIFICATION-TYPE
--    OBJECTS {}
    STATUS  current
    DESCRIPTION
        "optical module temperature high warn."
    ::= {opticalModuleExceptionTrap 1}
	
opticalModuleTemperatureLowWarnTrap NOTIFICATION-TYPE
--    OBJECTS {}
    STATUS  current
    DESCRIPTION
        "optical module temperature low warn."
    ::= {opticalModuleExceptionTrap 2}
	
opticalModuleTemperatureRecoverTrap NOTIFICATION-TYPE
--    OBJECTS {}
    STATUS  current
    DESCRIPTION
        "optical module temperature recover."
    ::= {opticalModuleExceptionTrap 3}
	
opticalModuleRxpowerLowWarnTrap NOTIFICATION-TYPE
--    OBJECTS {}
    STATUS  current
    DESCRIPTION
        "optical module rxpower low."
    ::= {opticalModuleExceptionTrap 4}
	
opticalModuleRxpowerRecoverTrap NOTIFICATION-TYPE
--    OBJECTS {}
    STATUS  current
    DESCRIPTION
       "optical module rxpower recover."
    ::= {opticalModuleExceptionTrap 6}

opticalModuleTxFaultWarnTrap NOTIFICATION-TYPE
--    OBJECTS {}
    STATUS  current
    DESCRIPTION
        "optical module txfault warn."
    ::= {opticalModuleExceptionTrap 7}
	
opticalModuleTxFaultRecoverTrap NOTIFICATION-TYPE
--    OBJECTS {}
    STATUS  current
    DESCRIPTION
        "optical module txfault recover."
    ::= {opticalModuleExceptionTrap 8}

END

HMIT-SYS-IF-MIB DEFINITIONS ::= BEGIN       

IMPORTS
	MODULE-IDENTITY, OBJECT-TYPE, Integer32
		FROM SNMPv2-SMI
    DisplayString	FROM RFC1213-MIB
    hmITSystem		FROM HMIT-SMI;


hmITSysIfMIB MODULE-IDENTITY
	LAST-UPDATED "201001081700Z"
    ORGANIZATION "Belden Singapore Pte Ltd."
    CONTACT-INFO
		 "Belden Singapore Pte Ltd."
    DESCRIPTION
		 "The MIB module for managing interface implementations."
	REVISION "201001081700Z"
	DESCRIPTION
		"The initial revision of this mib module "
    ::= {hmITSystem 11}    
	 
hmITSysIfTable  OBJECT-TYPE
    SYNTAX  SEQUENCE OF   HmITSysIfEntry
    MAX-ACCESS  not-accessible
    STATUS  current
    DESCRIPTION        
          "The table containing per-interface information."
    ::= {hmITSysIfMIB 1}

hmITSysIfEntry  OBJECT-TYPE
    SYNTAX  HmITSysIfEntry
    MAX-ACCESS  not-accessible
    STATUS  current
    DESCRIPTION
           "An entry containing information of interface."
    INDEX   {hmITSysIfIndex}
    ::= {hmITSysIfTable 1}

HmITSysIfEntry  ::=  SEQUENCE {
    hmITSysIfIndex  	INTEGER,
    hmITSysIfName   	DisplayString,
    hmITSysIfReliability	Integer32
}

hmITSysIfIndex  OBJECT-TYPE
    SYNTAX  INTEGER (1..2147483647)
    MAX-ACCESS  not-accessible
    STATUS  current
    DESCRIPTION
           "A unique value for each interface."
    ::= {hmITSysIfEntry 1}

hmITSysIfName  OBJECT-TYPE
    SYNTAX  DisplayString(SIZE(1..39))
    MAX-ACCESS  read-only
    STATUS  current
    DESCRIPTION
           "The textual name of the interface, max length is 39 characters."
    ::= {hmITSysIfEntry 2}

hmITSysIfReliability  OBJECT-TYPE
    SYNTAX  Integer32(0 .. 100) 
    MAX-ACCESS  read-only
    STATUS  current
    DESCRIPTION
           "The reliability(percent) of the interface, for example 100 express 100%."
    ::= {hmITSysIfEntry 3}


END

--*****************************************************************
-- HMIT-SYSTEM-MIB.mib
--
-- 
-- *****************************************************************
--




HMIT-SYSTEM-MIB DEFINITIONS ::= BEGIN

IMPORTS
	MODULE-IDENTITY, OBJECT-TYPE, NOTIFICATION-TYPE, Integer32, Unsigned32, IpAddress, Counter64,
	Gauge32
		FROM SNMPv2-SMI
	TEXTUAL-CONVENTION, TruthValue, DisplayString
		FROM SNMPv2-TC
	hmITMgmt
		FROM HMIT-SMI;

--hmITSystemMib 								OBJECT IDENTIFIER ::= {hmITMgmt 600}

hmITSystemMib MODULE-IDENTITY
	LAST-UPDATED "201001081700Z"
	ORGANIZATION "Belden Singapore Pte Ltd."
	CONTACT-INFO
		"Belden Singapore Pte Ltd."
	DESCRIPTION
		"The Structure of Management Information for Hirschmann."
	REVISION "201001081700Z"
	DESCRIPTION
		"The initial revision of this mib module "
	::= {hmITMgmt 600}

hmITSystemTrap 								OBJECT IDENTIFIER ::= { hmITSystemMib 0 }
hmITSysInfoMib								OBJECT IDENTIFIER ::= {hmITSystemMib 1}
hmITSysMpuMib									OBJECT IDENTIFIER ::= {hmITSystemMib 2}
hmITSysSubSlotMib							OBJECT IDENTIFIER ::= {hmITSystemMib 5}
hmITSysPortMib    						OBJECT IDENTIFIER ::= {hmITSystemMib 6}
hmITSysPowerMib 							OBJECT IDENTIFIER ::= {hmITSystemMib 7}
hmITSysFanCardMib 						OBJECT IDENTIFIER ::= {hmITSystemMib 8}
hmITSysCpuMib 								OBJECT IDENTIFIER ::= {hmITSystemMib 9}
hmITSysMemoryMib 							OBJECT IDENTIFIER ::= {hmITSystemMib 10}


--hmITSystemAlarmTrap     trap information				
--hmITSystemTrap        	OBJECT IDENTIFIER ::= { hmITSystemMib 0 }

hmITSysMemUtilizationAlarm 	NOTIFICATION-TYPE
                    		STATUS  current
                    		DESCRIPTION
                    			"memory utilization alarm"
                    		::= { hmITSystemTrap 5 }

hmITSysCpuUtilizationAlarm	NOTIFICATION-TYPE
                    		STATUS  current
                    		DESCRIPTION
                    			"cpu utilization alarm"
                    		::= { hmITSystemTrap 6 }

hmITSysCacheUtilizationAlarm      NOTIFICATION-TYPE
                    		STATUS  current
                    		DESCRIPTION
                    			"cache utilization alarm"
                    		::= { hmITSystemTrap 7 }

hmITSysMpuCoreNormalAlarm   	NOTIFICATION-TYPE
                    		STATUS  current
                    		DESCRIPTION
                    			"mpu core temperature normal alarm"
                    		::= { hmITSystemTrap 18 }
hmITSysMpuBoardWarnAlarm      NOTIFICATION-TYPE
                    		STATUS  current
                    		DESCRIPTION
                    			"mpu board temperature warning alarm"
                    		::= { hmITSystemTrap 19 }
hmITSysMpuBoardNormalAlarm   	NOTIFICATION-TYPE
                    		STATUS  current
                    		DESCRIPTION
                    			"mpu board temperature normal alarm"
                    		::= { hmITSystemTrap 20 }

--hmITSystemAlarmTrap end



--mpuInfoTable 

mpuInfoTable    OBJECT-TYPE
    SYNTAX  SEQUENCE OF MpuInfoEntry
    MAX-ACCESS  not-accessible
    STATUS  current
    DESCRIPTION
            " "
    ::= {hmITSysMpuMib 1}

mpuInfoEntry  OBJECT-TYPE
    SYNTAX  MpuInfoEntry
    MAX-ACCESS  not-accessible
    STATUS  current
    DESCRIPTION
            " "
    INDEX   {mpuIndex}
    ::= {mpuInfoTable 1}

MpuInfoEntry ::= SEQUENCE 
{ 
	mpuIndex           INTEGER,
	mpuType            Gauge32,
	mpuDescription     DisplayString,
	mpuSerialNumber    DisplayString,   
	mpuSoftwareVersion DisplayString, 
	mpuHardwareVersion DisplayString,    
	mpuFPGAVersion     DisplayString,
	mpuMonitorVersion  DisplayString,  
	mpuCMMSoftwareVersion      DisplayString,  
	mpuCMMHardwareVersion      DisplayString,
	mpuCMMMonitorVersion       DisplayString,
	mpuFlashTotalBytes         Counter64, 
	mpuFlashLeftBytes          Counter64,
	mpuWorkingMode             INTEGER,
	mpuOnlineStatus            INTEGER, 
	mpuWorkingStatus           INTEGER, 
	mpuPowerStatus             INTEGER,   
	mpuSynchronizationStatus   INTEGER,  
	mpuCFStatus                INTEGER,   
	mpuTemperature             INTEGER,
	mpuSubSlotNumber           INTEGER,
	hmITSysMpuUserSerialNumber   DisplayString, 
	mpuModel		DisplayString
}	
	
mpuIndex  OBJECT-TYPE
    SYNTAX  INTEGER (1..2147483647)
    MAX-ACCESS  read-only
    STATUS  current
    DESCRIPTION
            " "
    ::= {mpuInfoEntry 1}

mpuType  OBJECT-TYPE
    SYNTAX  Gauge32 (1..2147483647)
    MAX-ACCESS  read-only
    STATUS  current
    DESCRIPTION
            " "
    ::= {mpuInfoEntry 2}
    
mpuDescription  OBJECT-TYPE
    SYNTAX  DisplayString(SIZE (0..128))
    MAX-ACCESS  read-write
    STATUS  current
    DESCRIPTION
            " "
    ::= {mpuInfoEntry 3}

mpuSerialNumber  OBJECT-TYPE
    SYNTAX  DisplayString(SIZE (0..31))
    MAX-ACCESS  read-only
    STATUS  current
    DESCRIPTION
            " "
    ::= {mpuInfoEntry 4}

mpuSoftwareVersion  OBJECT-TYPE
    SYNTAX  DisplayString(SIZE (0..31))
    MAX-ACCESS  read-only
    STATUS  current
    DESCRIPTION
            " "
    ::= {mpuInfoEntry 5}

mpuHardwareVersion  OBJECT-TYPE
    SYNTAX  DisplayString
    MAX-ACCESS  read-only
    STATUS  current
    DESCRIPTION
            " "
    ::= {mpuInfoEntry 6}

mpuFPGAVersion  OBJECT-TYPE
    SYNTAX  DisplayString
    MAX-ACCESS  read-only
    STATUS  current
    DESCRIPTION
            " "
    ::= {mpuInfoEntry 7}

           
mpuMonitorVersion  OBJECT-TYPE
    SYNTAX  DisplayString(SIZE (0..31))
    MAX-ACCESS  read-only
    STATUS  current
    DESCRIPTION
            " "
    ::= {mpuInfoEntry 8}    

mpuCMMSoftwareVersion  OBJECT-TYPE
    SYNTAX  DisplayString(SIZE (0..31))
    MAX-ACCESS  read-only
    STATUS  current
    DESCRIPTION
            " "
    ::= {mpuInfoEntry 9}
    
mpuCMMHardwareVersion  OBJECT-TYPE
    SYNTAX  DisplayString(SIZE (0..31))
    MAX-ACCESS  read-only
    STATUS  current
    DESCRIPTION
            " "
    ::= {mpuInfoEntry 10}
    
mpuCMMMonitorVersion  OBJECT-TYPE
    SYNTAX  DisplayString(SIZE (0..31))
    MAX-ACCESS  read-only
    STATUS  current
    DESCRIPTION
            " "
    ::= {mpuInfoEntry 11}    
    
mpuFlashTotalBytes  OBJECT-TYPE
    SYNTAX  Counter64
    MAX-ACCESS  read-only
    STATUS  current
    DESCRIPTION
            " "
    ::= {mpuInfoEntry 12}    
    
mpuFlashLeftBytes  OBJECT-TYPE
    SYNTAX  Counter64
    MAX-ACCESS  read-only
    STATUS  current
    DESCRIPTION
            " "
    ::= {mpuInfoEntry 13}        
    
mpuWorkingMode OBJECT-TYPE
    SYNTAX  INTEGER{
    				master(1),
    				slave(2),
    				doubleRouter(3)
    				}
    MAX-ACCESS  read-only
    STATUS  current
    DESCRIPTION
            " "
    ::= {mpuInfoEntry 14}    

mpuOnlineStatus OBJECT-TYPE
    SYNTAX  INTEGER{
                    online(1),
                    offline(2)
                    }
    MAX-ACCESS  read-only
    STATUS  current
    DESCRIPTION
            " "
    ::= {mpuInfoEntry 15}    
        
mpuWorkingStatus  OBJECT-TYPE
    SYNTAX  INTEGER{
    				on(1),
    				off(2)
    				}
    MAX-ACCESS  read-only
    STATUS  current
    DESCRIPTION
            " "
    ::= {mpuInfoEntry 16}
        
mpuPowerStatus OBJECT-TYPE
    SYNTAX  INTEGER{
    				on(1),
    				off(2)
    				}
    MAX-ACCESS  read-only
    STATUS  current
    DESCRIPTION
            " "
    ::= {mpuInfoEntry 17}        

mpuSynchronizationStatus OBJECT-TYPE
    SYNTAX  INTEGER{
    				batchSync(1),
    				realtimeSync(2),
    				noSlave(3),
    				abnormal(4)
    				}
    MAX-ACCESS  read-only
    STATUS  current
    DESCRIPTION
            " "
    ::= {mpuInfoEntry 18}
    
mpuCFStatus OBJECT-TYPE
    SYNTAX  INTEGER{
    				online(1),
    				offline(2)
    				}
    MAX-ACCESS  read-only
    STATUS  current
    DESCRIPTION
            " "
    ::= {mpuInfoEntry 19}
    
mpuTemperature  OBJECT-TYPE
    SYNTAX  INTEGER (-100..1000)
    MAX-ACCESS  read-only
    STATUS  current
    DESCRIPTION
            " "
    ::= {mpuInfoEntry 20}    
    
mpuSubSlotNumber OBJECT-TYPE
    SYNTAX  INTEGER (0..2147483647)
    MAX-ACCESS  read-only
    STATUS  current
    DESCRIPTION
            " "
    ::= {mpuInfoEntry 21}    
	
hmITSysMpuUserSerialNumber OBJECT-TYPE
    SYNTAX  DisplayString(SIZE (0..31))
    MAX-ACCESS  read-only
    STATUS  current
    DESCRIPTION
            " "
    ::= {mpuInfoEntry 22}
	
mpuModel  OBJECT-TYPE
    SYNTAX  DisplayString(SIZE (0..32))
    MAX-ACCESS  read-only
    STATUS  current
    DESCRIPTION
            " "
    ::= {mpuInfoEntry 23}
    
-- mpuInfoTable end


-- subSlotTable  

subSlotTable    OBJECT-TYPE
    SYNTAX  SEQUENCE OF SubSlotEntry
    MAX-ACCESS  not-accessible
    STATUS  current
    DESCRIPTION
            "sub slot table"
    ::= {hmITSysSubSlotMib 1}

subSlotEntry  OBJECT-TYPE
    SYNTAX  SubSlotEntry
    MAX-ACCESS  not-accessible
    STATUS  current
    DESCRIPTION
            " "
    INDEX   {subSlotParentIndex,subSlotIndex}
    ::= {subSlotTable 1}
	
SubSlotEntry ::= SEQUENCE 
{ 
	subSlotParentIndex      INTEGER,
	subSlotIndex            INTEGER, 
	subSlotCardType         Gauge32,
	subSlotPortNumber       INTEGER,
	subSlotOnlineStatus     INTEGER 
}
subSlotParentIndex  OBJECT-TYPE
    SYNTAX  INTEGER (1..2147483647)
    MAX-ACCESS  read-only
    STATUS  current
    DESCRIPTION
            " "
    ::= {subSlotEntry 1}
    
subSlotIndex  OBJECT-TYPE
    SYNTAX  INTEGER (1..2147483647)
    MAX-ACCESS  read-only
    STATUS  current
    DESCRIPTION
            " "
    ::= {subSlotEntry 2}
    
subSlotCardType  OBJECT-TYPE
    SYNTAX  Gauge32 (1..2147483647)
    MAX-ACCESS  read-only
    STATUS  current
    DESCRIPTION
            " "
    ::= {subSlotEntry 3}

subSlotPortNumber  OBJECT-TYPE
    SYNTAX  INTEGER (0..2147483647)
    MAX-ACCESS  read-only
    STATUS  current
    DESCRIPTION
            " "
    ::= {subSlotEntry 4}

subSlotOnlineStatus OBJECT-TYPE
    SYNTAX  INTEGER{
    				online(1),
    				offline(2)
    				}
    MAX-ACCESS  read-only
    STATUS  current
    DESCRIPTION
            " "
    ::= {subSlotEntry 5}
    
-- subSlotTable  end


-- portInfoTable  

portInfoTable    OBJECT-TYPE
    SYNTAX  SEQUENCE OF PortInfoEntry
    MAX-ACCESS  not-accessible
    STATUS  current
    DESCRIPTION
            " "
    ::= {hmITSysPortMib 1}

portInfoEntry  OBJECT-TYPE
    SYNTAX  PortInfoEntry
    MAX-ACCESS  not-accessible
    STATUS  current
    DESCRIPTION
            " "
    INDEX   {portSlotIndex,portSubSlotIndex,portIndex}
    ::= {portInfoTable 1}

PortInfoEntry ::= SEQUENCE 
{ 
	portSlotIndex      INTEGER,
	portSubSlotIndex   INTEGER, 
	portIndex          INTEGER,
	portType           INTEGER,
	portLinkStatus     INTEGER,
	portOnlineStatus   INTEGER
}
portSlotIndex  OBJECT-TYPE
    SYNTAX  INTEGER (1..2147483647)
    MAX-ACCESS  read-only
    STATUS  current
    DESCRIPTION
            " "
    ::= {portInfoEntry 1}
    
portSubSlotIndex  OBJECT-TYPE
    SYNTAX  INTEGER (1..2147483647)
    MAX-ACCESS  read-only
    STATUS  current
    DESCRIPTION
            " "
    ::= {portInfoEntry 2}
    
portIndex  OBJECT-TYPE
    SYNTAX  INTEGER (1..2147483647)
    MAX-ACCESS  read-only
    STATUS  current
    DESCRIPTION
            " "
    ::= {portInfoEntry 3}
    
portType  OBJECT-TYPE
    SYNTAX  INTEGER{
    				copper(1),
    				fiber(2)
    				}
    MAX-ACCESS  read-only
    STATUS  current
    DESCRIPTION
            " "
    ::= {portInfoEntry 4}

portLinkStatus  OBJECT-TYPE
    SYNTAX  INTEGER{
    				up(1),
    				down(2),
    				loop(3)
    				}
    MAX-ACCESS  read-only
    STATUS  current
    DESCRIPTION
            " "
    ::= {portInfoEntry 5}
    
portOnlineStatus OBJECT-TYPE
    SYNTAX  INTEGER{
    				online(1),
    				offline(2)
    				}
    MAX-ACCESS  read-only
    STATUS  current
    DESCRIPTION
            " "
    ::= {portInfoEntry 6}

-- portInfoTable  end


-- powerInfoTable   

powerInfoTable    OBJECT-TYPE
    SYNTAX  SEQUENCE OF PowerInfoEntry
    MAX-ACCESS  not-accessible
    STATUS  current
    DESCRIPTION
            "  "
    ::= {hmITSysPowerMib 1}

powerInfoEntry  OBJECT-TYPE
    SYNTAX  PowerInfoEntry
    MAX-ACCESS  not-accessible
    STATUS  current
    DESCRIPTION
            " "
    INDEX   {powerIndex}
    ::= {powerInfoTable 1}

PowerInfoEntry ::= SEQUENCE 
{ 
	powerIndex           INTEGER,
	powerType            INTEGER,
	powerDescription     DisplayString,
	powerSerialNumber    DisplayString,    
	powerCMMSoftwareVersion      DisplayString,  
	powerCMMHardwareVersion      DisplayString,
	powerCMMMonitorVersion       DisplayString,
	powerOnlineStatus           INTEGER, 
	powerWorkingStatus          INTEGER,
	powerAlarmStatus            INTEGER,  
	powerVoltageInput           INTEGER,  
	powerVoltageOutput          INTEGER, 
	powerCurrentInput           INTEGER,  
	powerCurrentOutput          INTEGER,
	powerUserSerialNumber       DisplayString,
	powerName                   DisplayString
}
powerIndex  OBJECT-TYPE
    SYNTAX  INTEGER (1..2147483647)
    MAX-ACCESS  read-only
    STATUS  current
    DESCRIPTION
            "power system information table index"
    ::= {powerInfoEntry 1}

powerType  OBJECT-TYPE
    SYNTAX  INTEGER{
            alternatingNonIntelligent(1),
            directNonIntelligent(2),
            alternatingIntelligent(3),
            directIntelligent(4)
            }
    MAX-ACCESS  read-only
    STATUS  current
    DESCRIPTION
            "power type(1:alternating and non-intelligent 2:direct and non-intelligent 3:alternating and intelligent 4:direct and intelligent)"
    ::= {powerInfoEntry 2}

powerDescription  OBJECT-TYPE
    SYNTAX  DisplayString(SIZE (0..128))
    MAX-ACCESS  read-write
    STATUS  current
    DESCRIPTION
            "power description, the max length is 128bytes"
    ::= {powerInfoEntry 3}

powerSerialNumber  OBJECT-TYPE
    SYNTAX  DisplayString(SIZE (0..31))
    MAX-ACCESS  read-only
    STATUS  current
    DESCRIPTION
            "power serialnumber, the max length is 32bytes"
    ::= {powerInfoEntry 4}

powerCMMSoftwareVersion  OBJECT-TYPE
    SYNTAX  DisplayString(SIZE (0..31))
    MAX-ACCESS  read-only
    STATUS  current
    DESCRIPTION
            "power cmm software version, the max length is 32bytes"
    ::= {powerInfoEntry 5}
    
powerCMMHardwareVersion  OBJECT-TYPE
    SYNTAX  DisplayString(SIZE (0..31))
    MAX-ACCESS  read-only
    STATUS  current
    DESCRIPTION
            "power cmm hardware version, the max length is 32bytes"
    ::= {powerInfoEntry 6}

powerCMMMonitorVersion  OBJECT-TYPE
    SYNTAX  DisplayString(SIZE (0..31))
    MAX-ACCESS  read-only
    STATUS  current
    DESCRIPTION
            "power cmm monitor version, the max length is 32bytes"
    ::= {powerInfoEntry 7}    
    
powerOnlineStatus  OBJECT-TYPE
    SYNTAX  INTEGER{
    				online(1),
            offline(2)
            }
    MAX-ACCESS  read-only
    STATUS  current
    DESCRIPTION
            "power physical status(1:online 2:offline)"
    ::= {powerInfoEntry 8}    

powerWorkingStatus  OBJECT-TYPE
    SYNTAX  INTEGER{
    				on(1),
            off(2)
            }
    MAX-ACCESS  read-only
    STATUS  current
    DESCRIPTION
            "power work status(1:working 2:not working)"
    ::= {powerInfoEntry 9}    
    
powerAlarmStatus  OBJECT-TYPE
    SYNTAX  INTEGER{
						normal(1),
						alarm(2)
            }
    MAX-ACCESS  read-only
    STATUS  current
    DESCRIPTION
            "power alarm status(1:normal 2:abnormal)"
    ::= {powerInfoEntry 10}        
    
powerVoltageInput  OBJECT-TYPE
    SYNTAX  INTEGER (0..2147483647)
    UNITS   "mV"
    MAX-ACCESS  read-only
    STATUS  current
    DESCRIPTION
            "power input voltage(mv)"
    ::= {powerInfoEntry 11}               
    
powerVoltageOutput  OBJECT-TYPE
    SYNTAX  INTEGER (0..2147483647)
    UNITS   "mV"
    MAX-ACCESS  read-only
    STATUS  current
    DESCRIPTION
            "power output voltage(mv)"
    ::= {powerInfoEntry 12}     
                 
powerCurrentInput  OBJECT-TYPE
    SYNTAX  INTEGER (0..2147483647)
    UNITS   "mA"
    MAX-ACCESS  read-only
    STATUS  current
    DESCRIPTION
            "power input current(mA)"
    ::= {powerInfoEntry 13}    
                  
powerCurrentOutput OBJECT-TYPE
    SYNTAX  INTEGER (0..2147483647)
		UNITS   "mA"
    MAX-ACCESS  read-only
    STATUS  current
    DESCRIPTION
            "power output current(mA)"
    ::= {powerInfoEntry 14}               

powerUserSerialNumber  OBJECT-TYPE
    SYNTAX  DisplayString(SIZE (0..31))
    MAX-ACCESS  read-only
    STATUS  current
    DESCRIPTION
            "power User managment serialnumber, the max length is 32bytes"
    ::= {powerInfoEntry 15}

powerName  OBJECT-TYPE
    SYNTAX  DisplayString(SIZE (0..63))
    MAX-ACCESS  read-only
    STATUS  current
    DESCRIPTION
            "power cardName, the max length is 64bytes"
    ::= {powerInfoEntry 16}


-- powerInfoTable end


-- fanCardInfoTable  

fanCardInfoTable    OBJECT-TYPE
    SYNTAX  SEQUENCE OF FanCardInfoEntry
    MAX-ACCESS  not-accessible
    STATUS  current
    DESCRIPTION
            " "
    ::= {hmITSysFanCardMib 1}

fanCardInfoEntry  OBJECT-TYPE
    SYNTAX  FanCardInfoEntry
    MAX-ACCESS  not-accessible
    STATUS  current
    DESCRIPTION
            " "
    INDEX   {fanCardIndex}
    ::= {fanCardInfoTable 1}

FanCardInfoEntry ::= SEQUENCE 
{ 
	fanCardIndex           INTEGER,
	fanCardDescription     DisplayString,
	fanCardSerialNumber    DisplayString,    
	fanCardCMMSoftwareVersion      DisplayString,  
	fanCardCMMHardwareVersion      DisplayString,
	fanCardCMMMonitorVersion       DisplayString,
	fanCardOnlineStatus           INTEGER, 
	fanCardWorkingStatus          INTEGER,
	fanCardAlarmStatus            INTEGER,  
	fanCardGrps                   INTEGER,  
	fanCardNumPerGrp              INTEGER,
	fanCardUserSerialNumber       DisplayString, 
	fanCardName                   DisplayString
 }
fanCardIndex  OBJECT-TYPE
    SYNTAX  INTEGER (1..2147483647)
    MAX-ACCESS  read-only
    STATUS  current
    DESCRIPTION
            "fan card system information table index"
    ::= {fanCardInfoEntry 1}

fanCardDescription  OBJECT-TYPE
    SYNTAX  DisplayString(SIZE (0..128))
    MAX-ACCESS  read-write
    STATUS  current
    DESCRIPTION
            "fan description, the max length is 128bytes"
    ::= {fanCardInfoEntry 2}

fanCardSerialNumber  OBJECT-TYPE
    SYNTAX  DisplayString(SIZE (0..31))
    MAX-ACCESS  read-only
    STATUS  current
    DESCRIPTION
            "fan serialnumber, the max length is 32bytes"
    ::= {fanCardInfoEntry 3}

fanCardCMMSoftwareVersion  OBJECT-TYPE
    SYNTAX  DisplayString(SIZE (0..31))
    MAX-ACCESS  read-only
    STATUS  current
    DESCRIPTION
            "fan cmm software version, the max length is 32bytes"
    ::= {fanCardInfoEntry 4}
    
fanCardCMMHardwareVersion  OBJECT-TYPE
    SYNTAX  DisplayString(SIZE (0..31))
    MAX-ACCESS  read-only
    STATUS  current
    DESCRIPTION
            "fan cmm hardware version, the max length is 32bytes"
    ::= {fanCardInfoEntry 5}

fanCardCMMMonitorVersion  OBJECT-TYPE
    SYNTAX  DisplayString(SIZE (0..31))
    MAX-ACCESS  read-only
    STATUS  current
    DESCRIPTION
            "fan cmm monitor version, the max length is 32bytes"
    ::= {fanCardInfoEntry 6}       
    
fanCardOnlineStatus  OBJECT-TYPE
    SYNTAX  INTEGER{
    				online(1),
            offline(2)
            }
    MAX-ACCESS  read-only
    STATUS  current
    DESCRIPTION
            "fan physical status(1:online 2:offline)"
    ::= {fanCardInfoEntry 7}    

fanCardWorkingStatus  OBJECT-TYPE
    SYNTAX  INTEGER{
    				on(1),
            off(2)
            }
    MAX-ACCESS  read-only
    STATUS  current
    DESCRIPTION
            "fan work status(1:working 2:not working)"
    ::= {fanCardInfoEntry 8}    
    
fanCardAlarmStatus  OBJECT-TYPE
    SYNTAX  INTEGER{
						normal(1),
						alarm(2)
            }
    MAX-ACCESS  read-only
    STATUS  current
    DESCRIPTION
            "fan alarm status(1:normal 2:abnormal)"
    ::= {fanCardInfoEntry 9}   

fanCardGrps  OBJECT-TYPE
    SYNTAX  INTEGER (0..2147483647)
    MAX-ACCESS  read-only
    STATUS  current
    DESCRIPTION
            "fan group number"
    ::= {fanCardInfoEntry 10}

fanCardNumPerGrp  OBJECT-TYPE
    SYNTAX  INTEGER (0..2147483647)
    MAX-ACCESS  read-only
    STATUS  current
    DESCRIPTION
            "fan number per group"
    ::= {fanCardInfoEntry 11}

fanCardUserSerialNumber  OBJECT-TYPE
    SYNTAX  DisplayString(SIZE (0..31))
    MAX-ACCESS  read-only
    STATUS  current
    DESCRIPTION
            "fan user managment serialnumber, the max length is 32bytes"
    ::= {fanCardInfoEntry 12}
    
fanCardName  OBJECT-TYPE
    SYNTAX  DisplayString(SIZE (0..63))
    MAX-ACCESS  read-only
    STATUS  current
    DESCRIPTION
            "fan cardName, the max length is 64bytes"
    ::= {fanCardInfoEntry 13}

-- fanCardInfoTable  end

-- fanInfoTable   

fanInfoTable    OBJECT-TYPE
    SYNTAX  SEQUENCE OF FanInfoEntry
    MAX-ACCESS  not-accessible
    STATUS  current
    DESCRIPTION
            " "
    ::= {hmITSysFanCardMib 2}

fanInfoEntry  OBJECT-TYPE
    SYNTAX  FanInfoEntry
    MAX-ACCESS  not-accessible
    STATUS  current
    DESCRIPTION
            " "
    INDEX   {fanInfoIndex,fanIndex}
    ::= {fanInfoTable 1}
FanInfoEntry ::= SEQUENCE 
{ 
	fanInfoIndex           INTEGER,
	fanIndex               INTEGER,
	fanStatus              INTEGER, 
	fanSpeed               INTEGER
 }
fanInfoIndex  OBJECT-TYPE
    SYNTAX  INTEGER (1..2147483647)
    MAX-ACCESS  read-only
    STATUS  current
    DESCRIPTION
            "fan card system information index"
    ::= {fanInfoEntry 1}

fanIndex  OBJECT-TYPE
    SYNTAX  INTEGER (1..2147483647)
    MAX-ACCESS  read-only
    STATUS  current
    DESCRIPTION
            "fan system information index"
    ::= {fanInfoEntry 2}


fanStatus  OBJECT-TYPE
    SYNTAX  INTEGER (1..2147483647)
    MAX-ACCESS  read-only
    STATUS  current
    DESCRIPTION
            "fan status(1:OK 2:FAIL)"
    ::= {fanInfoEntry 3}

fanSpeed  OBJECT-TYPE
    SYNTAX  INTEGER (1..2147483647)
    MAX-ACCESS  read-only
    STATUS  current
    DESCRIPTION
            "fan speed (0: min level,7:max level)"
    ::= {fanInfoEntry 4}



-- fanInfoTable  end



-- cpuUtilizationTable  

cpuUtilizationTable    OBJECT-TYPE
    SYNTAX  SEQUENCE OF CpuUtilizationEntry
    MAX-ACCESS  not-accessible
    STATUS  current
    DESCRIPTION
            "cpu utilization table"
    ::= {hmITSysCpuMib 1}

cpuUtilizationEntry  OBJECT-TYPE
    SYNTAX  CpuUtilizationEntry
    MAX-ACCESS  not-accessible
    STATUS  current
    DESCRIPTION
            "cpu utilization table entry"
    INDEX   {cpuIndex,cpuCoreId}
    ::= {cpuUtilizationTable 1}  
    
CpuUtilizationEntry ::= SEQUENCE 
{ 
	cpuIndex                      INTEGER,
	cpuCoreId                     INTEGER,
	cpuCoreUtilization            INTEGER,
	cpuPeakUtilizationPerMinute   INTEGER
}
cpuIndex  OBJECT-TYPE
    SYNTAX  INTEGER (1..2147483647)
    MAX-ACCESS  read-only
    STATUS  current
    DESCRIPTION
            "cpu utilization table index"
    ::= {cpuUtilizationEntry 1}
    
cpuCoreId  OBJECT-TYPE
    SYNTAX  INTEGER (1..2147483647)
    MAX-ACCESS  read-only
    STATUS  current
    DESCRIPTION
            "cpu core id"
    ::= {cpuUtilizationEntry 2}

cpuCoreUtilization   OBJECT-TYPE
    SYNTAX  INTEGER (0..100)
    UNITS   "%"
    MAX-ACCESS  read-only
    STATUS  current
    DESCRIPTION
            "cpu utilization(%)"
    ::= {cpuUtilizationEntry 3}

cpuPeakUtilizationPerMinute   OBJECT-TYPE
    SYNTAX  INTEGER (0..100)
    UNITS   "%"
    MAX-ACCESS  read-only
    STATUS  current
    DESCRIPTION
            "cpu peak utilization per minute(%)"
    ::= {cpuUtilizationEntry 4}

-- cpuUtilizationTable  end


-- cpuTemperatureTable  

cpuTemperatureTable    OBJECT-TYPE
    SYNTAX  SEQUENCE OF CpuTemperatureEntry
    MAX-ACCESS  not-accessible
    STATUS  current
    DESCRIPTION
            "cpu temperature table"
    ::= {hmITSysCpuMib 2}

cpuTemperatureEntry  OBJECT-TYPE
    SYNTAX  CpuTemperatureEntry
    MAX-ACCESS  not-accessible
    STATUS  current
    DESCRIPTION
            "cpu temperature table entry"
    INDEX   {cpuTemperatureIndex}
    ::= {cpuTemperatureTable 1}
CpuTemperatureEntry ::= SEQUENCE 
{ 
	cpuTemperatureIndex           INTEGER,
	cpuTemperature     INTEGER
}
cpuTemperatureIndex  OBJECT-TYPE
    SYNTAX  INTEGER (1..2147483647)
    MAX-ACCESS  read-only
    STATUS  current
    DESCRIPTION
            "cpu temperature table index"
    ::= {cpuTemperatureEntry 1}
    
cpuTemperature  OBJECT-TYPE
    SYNTAX  INTEGER (-100..1000)
    UNITS   "'C"
    MAX-ACCESS  read-only
    STATUS  current
    DESCRIPTION
            "cpu temperature(.c)"
    ::= {cpuTemperatureEntry 2}
    
-- cpuTempTable  end


-- memoryTable  

memoryTable    OBJECT-TYPE
    SYNTAX  SEQUENCE OF MemoryEntry
    MAX-ACCESS  not-accessible
    STATUS  current
    DESCRIPTION
            "memory system information table"
    ::= {hmITSysMemoryMib 1}

memoryEntry  OBJECT-TYPE
    SYNTAX  MemoryEntry
    MAX-ACCESS  not-accessible
    STATUS  current
    DESCRIPTION
            "memory system information table entry"
    INDEX   {memIndex}
    ::= {memoryTable 1}
MemoryEntry ::= SEQUENCE 
{ 
	memIndex                INTEGER,
	memBytesFree            Gauge32,
	memBlocksFree           Gauge32, 
	memAvgBlockSizeFree     Gauge32,
	memMaxBlockSizeFree     Gauge32,  
	memBytesAlloc           Gauge32,  
	memBlocksAlloc          Gauge32, 
	memAvgBlockSizeAlloc    Gauge32,  
	memTotalBytes           Gauge32, 
	memUtilization          Gauge32,
	cacheUtilization	Gauge32,
	memKBytesFree            Counter64,
    memKBytesAlloc           Counter64,  
    memTotalKBytes           Counter64
}
memIndex  OBJECT-TYPE
    SYNTAX  INTEGER (1..2147483647)
    MAX-ACCESS  read-only
    STATUS  current
    DESCRIPTION
            "memory system information table index"
    ::= {memoryEntry 1}


memBytesFree  OBJECT-TYPE 
    SYNTAX  Gauge32 (1..2147483647)
    MAX-ACCESS  read-only
    STATUS  current
    DESCRIPTION
            "the free bytes of memory"
    ::= {memoryEntry 2}
    
memBlocksFree  OBJECT-TYPE
    SYNTAX  Gauge32 (1..2147483647)
    MAX-ACCESS  read-only
    STATUS  current
    DESCRIPTION
            "the free blocks of memory"
    ::= {memoryEntry 3}

memAvgBlockSizeFree  OBJECT-TYPE
    SYNTAX  Gauge32 (1..2147483647)
    MAX-ACCESS  read-only
    STATUS  current
    DESCRIPTION
            "the free blocks on average of memory"
    ::= {memoryEntry 4}
        
memMaxBlockSizeFree  OBJECT-TYPE
    SYNTAX  Gauge32 (1..2147483647)
    MAX-ACCESS  read-only
    STATUS  current
    DESCRIPTION
            "the max free blocks of memory"
    ::= {memoryEntry 5}

memBytesAlloc  OBJECT-TYPE
    SYNTAX  Gauge32 (1..2147483647)
    MAX-ACCESS  read-only
    STATUS  current
    DESCRIPTION
            "the allocate bytes of memory"
    ::= {memoryEntry 6}

memBlocksAlloc  OBJECT-TYPE
    SYNTAX  Gauge32 (1..2147483647)
    MAX-ACCESS  read-only
    STATUS  current
    DESCRIPTION
            "the allocate blocks of memory"
    ::= {memoryEntry 7}

memAvgBlockSizeAlloc  OBJECT-TYPE
    SYNTAX  Gauge32 (1..2147483647)
    MAX-ACCESS  read-only
    STATUS  current
    DESCRIPTION
            "the allocate blocks on average of memory"
    ::= {memoryEntry 8}

memTotalBytes  OBJECT-TYPE
    SYNTAX  Gauge32 (1..2147483647)
    MAX-ACCESS  read-only
    STATUS  current
    DESCRIPTION
            "the total bytes of memory"
    ::= {memoryEntry 9}

memUtilization  OBJECT-TYPE
    SYNTAX  Gauge32(0..100)
    UNITS   "%"
    MAX-ACCESS  read-only
    STATUS  current
    DESCRIPTION
            "memory utilization(%)"
    ::= {memoryEntry 10}
    
cacheUtilization  OBJECT-TYPE
    SYNTAX  Gauge32(0..100)
    UNITS   "%"
    MAX-ACCESS  read-only
    STATUS  current
    DESCRIPTION
            "memory cache utilization(%)"
    ::= {memoryEntry 11}

memKBytesFree  OBJECT-TYPE
    SYNTAX  Counter64
    ACCESS  read-only
    STATUS  current
    DESCRIPTION
            "the free Kbytes of memory"
    ::= {memoryEntry 12}

memKBytesAlloc  OBJECT-TYPE
    SYNTAX  Counter64
    ACCESS  read-only
    STATUS  current
    DESCRIPTION
            "the allocate Kbytes of memory"
    ::= {memoryEntry 13}

memTotalKBytes  OBJECT-TYPE
    SYNTAX  Counter64
    ACCESS  read-only
    STATUS  current
    DESCRIPTION
            "the total Kbytes of memory"
    ::= {memoryEntry 14}

-- memoryTable  end


--hmITSysInfo 
		
sysVoltage  OBJECT-TYPE
    SYNTAX  INTEGER (0..2147483647)
    UNITS   "mV"
    MAX-ACCESS  read-only
    STATUS  current
    DESCRIPTION
            " "
    ::= {hmITSysInfoMib 1}

sysCurrent  OBJECT-TYPE
    SYNTAX  INTEGER (0..2147483647)
    UNITS   "mA"
    MAX-ACCESS  read-only
    STATUS  current
    DESCRIPTION
            " "
    ::= {hmITSysInfoMib 2}
	

    
--mpSysInfo end



END

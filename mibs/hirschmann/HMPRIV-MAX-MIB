HMPRIV-MAX-MIB DEFINITIONS ::= BEGIN

	    IMPORTS
                enterprises,
                IpAddress,
                Counter                FROM RFC1155-SMI	    
                DisplayString,
                PhysAddress            FROM RFC1213-MIB

		OBJECT-TYPE            FROM RFC-1212
        TRAP-TYPE              FROM RFC-1215;

	  hirschmann    OBJECT IDENTIFIER ::= { enterprises 248 }
	  max          OBJECT IDENTIFIER ::= { hirschmann 70 }


	  -- groups in this MIB

	  basics       OBJECT IDENTIFIER ::= { max 1 }

	  switch       OBJECT IDENTIFIER ::= { max 12 }

	  max25     OBJECT IDENTIFIER ::= { switch 6 }
	  max16      OBJECT IDENTIFIER ::= { switch 7 }
	  max32      OBJECT IDENTIFIER ::= { switch 8 }
	  max8       OBJECT IDENTIFIER ::= { switch 9 }
	  max32t     OBJECT IDENTIFIER ::= { switch 10 }	  
	  maxq     OBJECT IDENTIFIER ::= { switch 11 }	  
      mx-events    OBJECT IDENTIFIER ::= { switch 12 }
      max25e     OBJECT IDENTIFIER ::= { switch 13 }
      max32f     OBJECT IDENTIFIER ::= { switch 14 }
      max32fc     OBJECT IDENTIFIER ::= { switch 17 }
      maxqe     OBJECT IDENTIFIER ::= { switch 18 }
      maxl     OBJECT IDENTIFIER ::= { switch 19 }
      max1000     OBJECT IDENTIFIER ::= { switch 20 }
      maxm     OBJECT IDENTIFIER ::= { switch 21 }
      magnum10kt     OBJECT IDENTIFIER ::= { switch 20 }
      max25m     OBJECT IDENTIFIER ::= { switch 21 }
      magnum10kg     OBJECT IDENTIFIER ::= { switch 22 }
      
	  -- the basics group

	  systemGroup  OBJECT IDENTIFIER ::= { basics 1 }

	  systemName OBJECT-TYPE
	      SYNTAX  DisplayString (SIZE (0..255))
	      ACCESS  read-only
	      STATUS  mandatory
	      DESCRIPTION
		      "A textual description of the entity. The value of 
		       this MIB object is similar to the variable 
		       <sysDescr> in MIB-II. But, this object contains 
		       the more specific details about the managed device."
	      REFERENCE
		      "GarrettCom, Inc (Belden) Internal Documents"
	      ::= { systemGroup 1 }

	  systemVersion OBJECT-TYPE
	      SYNTAX  DisplayString (SIZE (0..255))
	      ACCESS  read-only
	      STATUS  mandatory
	      DESCRIPTION
		      "A textual description of the version of software 
		       of the managed device.This MIB object specifies 
		       the version of the agent that is currently used 
		       in this agent unit. This will give the details
		       of, even the build date and the copy right 
		       information of the SNMP agent software."
	      REFERENCE
		      "GarrettCom, Inc (Belden) Internal Documents"
	      ::= { systemGroup 2 }

	  systemFirmwareVersion OBJECT-TYPE
	      SYNTAX  DisplayString (SIZE (0..255))
	      ACCESS  read-only
	      STATUS  mandatory
	      DESCRIPTION
		      "A textual description of the version of the
		       firmware of the managed device."
	      REFERENCE
		      "GarrettCom, Inc (Belden) Internal Documents"
	      ::= { systemGroup 3 }

	  systemMacAddress OBJECT-TYPE
	      SYNTAX  PhysAddress
	      ACCESS  read-only
	      STATUS  mandatory
	      DESCRIPTION
		      "The MAC address of the managed device."
	      ::= { systemGroup 4 }

	  deviceReset OBJECT-TYPE
	      SYNTAX  INTEGER {
			       reset(1),
			       resetDone(2)
	      }
	      ACCESS  read-write
	      STATUS  mandatory
	      DESCRIPTION
		      "This MIB object could be used to reset the device.
		       When ever the manager reads, the value will always 
		       be resetDone"
	      REFERENCE
		      "GarrettCom, Inc (Belden) Internal Documents"
	      ::= { systemGroup 5 }



    systemUpTime		 OBJECT-TYPE
    SYNTAX              DisplayString
    ACCESS          read-only   
    STATUS              mandatory
    DESCRIPTION		"This is the system uptime in string format"
              ::= {systemGroup 6 }

    

    systemLocation		 OBJECT-TYPE
    SYNTAX              DisplayString
    ACCESS          read-write   
    STATUS              mandatory
    DESCRIPTION		"System Location. Same as sysLocation in MIB-II"
              ::= {systemGroup 7}

	systemContact		 OBJECT-TYPE
    SYNTAX              DisplayString
    ACCESS          read-write  
    STATUS              mandatory
    DESCRIPTION		"System Contact. Same as sysContact in MIB-II"
              ::= {systemGroup 8 }

	
	sysIpAddress 		OBJECT-TYPE
    SYNTAX              IpAddress
    ACCESS          read-write
    STATUS              mandatory
    DESCRIPTION		 "System IP Address."
              ::= { systemGroup 9 }

    sysSubnet		OBJECT-TYPE
    SYNTAX              IpAddress
    ACCESS          read-write
    STATUS              mandatory
    DESCRIPTION		 "System Subnet."
              ::= { systemGroup 10 }

    sysGateway 		OBJECT-TYPE
    SYNTAX              IpAddress
    ACCESS          read-write
    STATUS              mandatory
    DESCRIPTION		"System Gateway."
              ::= { systemGroup 11 }

    sysSerial 		OBJECT-TYPE
    SYNTAX          DisplayString
    ACCESS          read-only
    STATUS              mandatory
    DESCRIPTION		"System Serial Number."
              ::= { systemGroup 12 }
              
    sysOrderCode 		OBJECT-TYPE
    SYNTAX          DisplayString
    ACCESS          read-only
    STATUS              mandatory
    DESCRIPTION		"System Order Code."
              ::= { systemGroup 13 }    

    sysTemperature	OBJECT-TYPE
    SYNTAX		INTEGER
    ACCESS		read-only
    STATUS		mandatory
    DESCRIPTION		"System Temperature measured in 1/100 of a degree."
              ::= { systemGroup 14 }    

    sysTempUnit		OBJECT-TYPE
    SYNTAX		INTEGER{
			       fahrenheit(1),
			       celcius(2)
	      		}
    ACCESS		read-write
    STATUS		mandatory
    DESCRIPTION		"Unit of the System Temperature"
              ::= { systemGroup 15 }    

    sysPS1Status		OBJECT-TYPE
    SYNTAX		INTEGER{
			       NotSupported(1),
			       NotConnected(2),
			       Failed(3),
			       Good(4)
	      		}
    ACCESS		read-write
    STATUS		mandatory
    DESCRIPTION		"System Power Supply 1 Status"
              ::= { systemGroup 16 }    
              
    sysPS2Status	OBJECT-TYPE
    SYNTAX		INTEGER{
			       NotSupported(1),
			       NotConnected(2),
			       Failed(3),
			       Good(4)
	      		}
    ACCESS		read-only
    STATUS		mandatory
    DESCRIPTION		"System Power Supply 2 Status."
              ::= { systemGroup 17 }    

    sysCPUusage	OBJECT-TYPE
    SYNTAX		INTEGER
    ACCESS		read-only
    STATUS		mandatory
    DESCRIPTION		"System CPU Usage in percentage."
              ::= { systemGroup 18 }    

    sysMemUsage	OBJECT-TYPE
    SYNTAX		INTEGER
    ACCESS		read-only
    STATUS		mandatory
    DESCRIPTION		"System Memory Usage in percentage."
              ::= { systemGroup 19 }    
              
	--  END OF SYSTEM GROUP












	  snmpGroup    OBJECT IDENTIFIER ::= { basics 2 }

	  mibsInfo OBJECT-TYPE
	      SYNTAX  DisplayString (SIZE (0..255))
	      ACCESS  read-only
	      STATUS  mandatory
	      DESCRIPTION
		      "The value of this string contains the details about 
		       MIBs supported in this version of the agent.
		       Eg. 1213(MIB-II) : 1493(Bridge) : 1757(RMON)"
	      ::= { snmpGroup 1 }



	  -- ethernet switch  group

	  generalmx    OBJECT IDENTIFIER ::= { max25 1 }

	  slotNumber OBJECT-TYPE
	      SYNTAX  INTEGER
	      ACCESS  read-only
	      STATUS  mandatory
	      DESCRIPTION
		      "The number of slots/modules (regardless of
		      their current state) present on this device."
	      ::= { generalmx 1 }

	  portNumber OBJECT-TYPE
	      SYNTAX  INTEGER
	      ACCESS  read-only
	      STATUS  mandatory
	      DESCRIPTION
		      "The number of physical ports (regardless of
		      their current state) present on this device."
	      ::= { generalmx 2 }


	  -- Slot table 

	  slotTable OBJECT-TYPE
	      SYNTAX  SEQUENCE OF SlotEntry
	      ACCESS  not-accessible
	      STATUS  mandatory
	      DESCRIPTION
		      "A list of slot entries. The number of
		      entries is given by the value of slotNumber."
	      ::= { max25 2 }

	  slotEntry OBJECT-TYPE
	      SYNTAX  SlotEntry
	      ACCESS  not-accessible
	      STATUS  mandatory
	      DESCRIPTION
		      "A slot entry containing slot details in the device."
	      INDEX   { slotIndex }
	      ::= { slotTable 1 }

	  SlotEntry ::=
	      SEQUENCE {
		  slotIndex
		      INTEGER,
		  slotName
		      INTEGER,
		  moduleId
		      INTEGER,
		  moduleName        
		      DisplayString
	      }

	  slotIndex OBJECT-TYPE
	      SYNTAX  INTEGER (1..10)
	      ACCESS  read-only
	      STATUS  mandatory
	      DESCRIPTION
		      "A unique value for each slot/module.  Its value
		      ranges between 1 and the value of slotNumber.  The
		      value for each slot must remain constant at
		      least from one re-initialization of the entity's
		      network management system to the next re-
		      initialization."
	      ::= { slotEntry 1 }

	  slotName OBJECT-TYPE
	      SYNTAX  INTEGER {
				 slot1(1),
				 slot2(2),
				 slot3(3),
				 slot4(4),
				 slot5(5),
				 slot6(6),
				 slot7(7),
				 slot8(8),
				 slot9(9),
				 slot10(10)
			      } 
	      ACCESS  read-only
	      STATUS  mandatory
	      DESCRIPTION
		      "A unique value for each slot/module. Its value 
		       is same as slotIndex."
	      ::= { slotEntry 2 }

	  moduleId OBJECT-TYPE
	      SYNTAX  INTEGER {
								unknown(0),
								oneGiga(1),
								eightTP(2),
								fourTPandFour100mbFiber(3),
								fourTPandTwo100mbFiber(4),
								eight100mbFiber(5),
								four100mbFiberandTwo100mbFiber(6),
								fourTPandTwo10mbFiber(7),
								four100mbFiberandTwo10mbFiber(8),
								two10mbFiberandTwo100mbFiber(9),
								four10mbFiber(10),
								four100mbFiber(11),
								twoGiga(12),
								sixTPandTwo100mbFiber(13),
								sixTPandOne100mbFiber(14),
								oneGigaFourTp(15),
								oneGigaFour100mbFiber(16),
								oneGigaTwoTpTwo100mbFiber(17),
								oneGigaTwoTpOne100mbFiber(18),
								oneGigaTwo100mbFiber(19),
								oneGigaTwo10mbFiber(20),
								oneGigaFiveTp(21),
								oneGigaOneTpFour100mbFiber(22),
								oneGigaThreeTpTwo100mbFiber(23),
								oneGigaThreeTpOne100mbFiber(24),
								oneGigaOneTpTwo100mbFiber(25),
								oneGigaOnetpTwo10mbFiber(26),
								oneGigaOne100mbFiberFourTp(27),
								oneGigaFive100mbFiber(28),
								oneGigaTwoTpThree100mbFiber(29),
								oneGigaTwoTpTwo100mbFibeExt(30),
								oneGigaThree100mbFiber(31),
								oneGigaOne100mbFiberTwo10mbFiber(32),
								fixedTPModule(33),
								eightTpMdix(34),
								fourTpMdixandFour100mbFiber(35),
								fourTpMdixandTwo100mbFiber(36),
								eight100mbFiberAlt(37),
								fourFiber100TwoFiber100Alt(38),
								fourTpMdixandTwo10mbFiber(39),
								four100mbFiberandTwo10mbFiberAlt(40),
								two10mbFiberandTwo100mbFiberAlt(41),
								four10mbFiberAlt(42),
								four100mbFiberAlt(43),
								twoGigaAlt(44),
								sixTpMdixandTwo100mbFiber(45),
								sixTpMdixandOne100mbFiber(46),
								oneGigaFourTpMdix(47),
								oneGigaFour100mbFiberAlt(48),
								oneGigaTwoTpMdixTwo100mbFiber(49),
								oneGigaTwoTpMdixOne100mbFiber(50),
								oneGigaTwo100mbFiberAlt(51),
								oneGigaTwo10mbFiberAlt(52),
								oneGigaFiveTpMdix(53),
								oneGigaOneTpMdixFour100mbFiber(54),
								oneGigaThreeTpMdixTwo100mbFiber(55),
								oneGigaThreeTpMdixOne100mbFiber(56),
								oneGigaOneTpMdixTwo100mbFiber(57),
								oneGigaOneTpMdixTwo10mbFiber(58),
								oneGigaOne100mbFiberFourTpMdix(59),
								oneGigaFive100mbFiberAlt(60),
								oneGigaTwoTpMdixThree100mbFiber(61),
								oneGigaTwoTpMdixTwo100mbFiberExt(62),
								oneGigaThree100mbFiberAlt(63),
								oneGigaOneFiber100TwoFiber10Alt(64),
								oneGiga3SpdTFourTpMdix(65),
								oneGiga1000TFourTpMdix(66),
								twoGiga3Spd(67),
								oneGiga3SpdOneGiga(68),
								oneGiga3SpdOneGigaSFP(69),
								oneGiga3SpdFour100mbfiber(70),
								oneGiga3SpdTwoTpMdixTwoFiber100(71),
								oneGiga3SpdTwoTpMdixOneFiber100(72),
								oneGiga3SpdTwo100mbfiber(73),
								oneGiga3SpdOne10mbfiber(74),
								oneGigafourTpMdixPOE(75),
								oneGigatwoTpMdixPOEtwoFiber100(76),
								one3SpdfourTpMdixPOE(77),
								one3SpdtwoTpMdixPOEtwoFiber100(78),
								one3SpdtwoTpMdixPOEoneFiber100(79),
								eightTpMdixPOE(80),
								fourTpMdixPOEfourFiber100(81),
								fourTpMdixPOEtwoFiber100(82),
								fourTpMdixPOEtwoFiber10(83),
								sixTpMdixPOEtwoFiber100(84),
								sixTpMdixPOEoneFiber100(85),
								one3SpdoneGigaSfp1000(86),
								twoGigaSfp1000(87),
								one3Spd(88),
								oneGigaSfp1000(89),
								fourTpMdixPOEfourTpMdix(90),
								fourTpMdixPOEtwoTpMdixtwoFiber100(91),
							    twoTpMdix(92), 
							    threeTpMdixOneFiber100(93), 
							    threeTpMdixPOEoneFiber100(94), 
							    threeFiber100oneTpMdix(95),
								fourTpMdix(96),
								fourFiber100fourTpMdix(97),
								twoFiber100fourTpMdix(98),
								fourFiber100(99),
								twoFiber100(100),
								twoFiber100twoFiber10(101),
								fourTPMDIX(102),
								fourFIBER100(103),
								twoFIBER100(104),
								twoFiber10(105),
								twoTpMdixtwoFiber100(106),
								twoTpMdixoneFiber100(107),
								fourTpMdixPOE(108),
								twoTpMdixPOEtwoFiber100(109),
								twoTpMdixPOEoneFiber100(110),
								oneFiber100(111),
								oneFiber100fourTpMdix(112),
								oneFiber100fourFiber100(113),
								oneFiber100twoFiber100(114),
								oneFiber100twoFiber10(115),
								oneFiber100twoTpMdixtwoFiber100(116),
								oneFiber100twoTpMdixoneFiber100(117),
								twoFiber100twoTpMdixtwoFiber100(118),
								twoFiber100twoTpMdixoneFiber100(119),
								fourTPMDIXPOE(120),
								oneFiber100threeTpMdix(121),
								twoFiber100FourFiber100(122),
								fourFiber100twoTPMDIXtwoFiber100(123),
								fourFiber100twoTPMDIXoneFiber100(124),
								twoTPMDIXfourFiber100(125),
								twoFiber10twoTpMDIX(126),
								fourFiber10(127),
								fourTpMdixIEEE1588(177),
								twoGiga3SpdIEEE1588(178),
								twoGigaSfpIEEE1588(179),
								fourFiber100IEEE1588(181),
								fourFiber100SFP(182),
				                twoFiber100IEEE1588(184),
				                oneMultimediaIEEE1588(186),
				                twoMultimediaIEEE1588(187),
				                fourTPMDIXPOESparePair(188),
			                    sixTpMdix(384),
			                    sevenTpMdixoneFiber100(385),
			                    fiveTpMdixthreeFiber1000(386),			
			                    sixTPMdixPOEtwoFiber100(387),
			                    threeTPMdixOneFiber100(388),
			                    threeTPMdixPOEOneFiber100(389),
			                    threeTpMdixOneFiberThreeTpMdixOneFiber(390),
			                    threeTpMDIXOneFiber100(400),
			                    threeTPMdixPoeOneFiber100(401),
			                    fourTpMdixThreeTpMdixPOEOneFiber100(403),
								oneGiga3SpdSixTpMdix(416),
								oneGiga3SpdFourFiber100TwoTpMdix(417),
								oneGiga3SpdTwoFiber100FourTpMdix(418),
								oneGiga3SpdOneFiber100FourTpMdix(419),
								oneGiga3SpdTwoFiber100TwoTpMdix(420),
								oneGiga3SpdTwoFiber10TwoTpMdix(421),
								oneGiga3SpdTwoTpMdixFourTpMdixPoe(422),
			                    oneGigaSfpSixTpMdix(423),
			                    oneGigaSfpTwoTpMdixFourFiber100(424),
                                oneGigaSfpFourTpMdixTwoFiber100(425),
                                oneGigaSfpFourTpMdixOneFiber100(426),
                                oneGigaSfpTwoTpMdixTwoFiber100(427),
                                oneGigaSfpTwoTpMdixTwoFiber10(428),
                                oneGigaSfpTwoTpMdixFourTpMdixPOE(429),
                                oneGigaSfpSixFiber100(430),
                                oneGigaSfpFourFiber100(431),
				                oneGigaSFPFourTpMdixPOE(432),
				                fourTpMdixwithIEEE1588(433),
				                two3SpdwithIEEE1588(434),
				                twoGigaSfpwithIEEE1588(435),
				                fourTpMdixPOESlotWise(436),
				                fourFiber100withIEEE1588(437),
				                fourFiber100Sfp(438),
				                fourTpMdixPOEPortWise(439),
				                twoFiber100withIEEE1588(440),
				                fourTpMdixPOEPlus(441),
				                oneMultimediaWithIEEE1588(442),
				                twoMultimediaWithIEEE1588(443),
				                fourTpMdixPOESparePair(444)
                              }
	      ACCESS  read-only
	      STATUS  mandatory
	      DESCRIPTION
		      "Module index of the module."
	      REFERENCE
		      "GarrettCom, Inc (Belden) Internal Documents"
	      ::= { slotEntry 3 }

	  moduleName OBJECT-TYPE
	      SYNTAX  DisplayString
	      ACCESS  read-only
	      STATUS  mandatory
	      DESCRIPTION
		      "module name will be depending upon module index."
	      REFERENCE
		      "GarrettCom, Inc (Belden) Internal Documents"
	      ::= { slotEntry 4 }


	  -- Port Control Table 

          portControl    OBJECT IDENTIFIER ::= { max25 3 }

	  savePortControl OBJECT-TYPE
	      SYNTAX  INTEGER {
			       save(1),
			       saveDone(2)
                              }
	      ACCESS  read-write
	      STATUS  mandatory
	      DESCRIPTION
		      "Whenever thie MIB object is set to 1, 
                       the Port Control configurations(portTable) are saved."
	      REFERENCE
		      "GarrettCom, Inc (Belden) Internal Documents"
	      ::= { portControl 1 }
 

	  portTable OBJECT-TYPE
	      SYNTAX  SEQUENCE OF PortEntry
	      ACCESS  not-accessible
	      STATUS  mandatory
	      DESCRIPTION
		      "A list of port entries. The number of
		      entries is given by the value of portNumber."
	      ::= { portControl 2 }

	  portEntry OBJECT-TYPE
	      SYNTAX  PortEntry
	      ACCESS  not-accessible
	      STATUS  mandatory
	      DESCRIPTION
		      "A port entry containing port details(of all modules)
		       in the device."
	      INDEX   { ptSlotIndex, ptPortIndex }
	      ::= { portTable 1 }

	  PortEntry ::=
	      SEQUENCE {
		  ptSlotIndex
		      INTEGER,
		  ptPortIndex
		      INTEGER,
		  ptIfIndex
		      INTEGER,
		  ptPortName
		      DisplayString,
		  ptPortControlStatus
		      INTEGER,
		  ptPortStatus
		      INTEGER,
		  ptPortDuplexStatus
		      INTEGER,
		  ptPortMediaType
		      INTEGER, 
		  ptPortLinkStatus
		      INTEGER,
		  ptPortSpeed
		      INTEGER,
		  ptPortPartitionState
		      INTEGER,
		  ptPortTraffic
		      INTEGER,
		  ptPortAutoNegotiation
		      INTEGER,
		  ptPortNotify
		      INTEGER	      }

	  ptSlotIndex OBJECT-TYPE
	      SYNTAX  INTEGER (1..10)
	      ACCESS  read-only
	      STATUS  mandatory
	      DESCRIPTION
		      "A unique value for each slot/module.  Its value
		      ranges between 1 and the value of slotNumber.  The
		      value for each slot must remain constant at
		      least from one re-initialization of the entity's
		      network management system to the next re-
		      initialization."
	      ::= { portEntry 1 }


	  ptPortIndex OBJECT-TYPE
	      SYNTAX  INTEGER (1..8)
	      ACCESS  read-only
	      STATUS  mandatory
	      DESCRIPTION
		      "A unique value for each port.  Its value
		      ranges between 1 and the value of portNumber."
	      ::= { portEntry 2 }

	  ptIfIndex OBJECT-TYPE
	      SYNTAX  INTEGER
	      ACCESS  read-only
	      STATUS  mandatory
	      DESCRIPTION
		      "The ifIndex of this port. This index is same as that
                       of ifIndex variable in the ifTable of MIB-II.
                       The value of this variable will range from 1 to <ifNumber>."
	      ::= { portEntry 3 }


	  ptPortName OBJECT-TYPE
	      SYNTAX  DisplayString
	      ACCESS  read-write
	      STATUS  mandatory
	      DESCRIPTION
		      "Name of the port."
	      ::= { portEntry 4 }

	  ptPortControlStatus OBJECT-TYPE
	      SYNTAX  INTEGER {
				 enable(1),
				 disable(2),
                                 notApplicable(4)
			      }
	      ACCESS  read-write
	      STATUS  mandatory
	      DESCRIPTION
		      "Enable / disable this port."
	      ::= { portEntry 5 }

	  ptPortStatus OBJECT-TYPE
	      SYNTAX  INTEGER {
				 enabled(1),
				 disabled(2),
				 locked(3),
				 doNotExist(4)   
			      } 
	      ACCESS  read-only
	      STATUS  mandatory
	      DESCRIPTION
		      "Status of the port."
	      ::= { portEntry 6 }

	  ptPortDuplexStatus OBJECT-TYPE
	      SYNTAX  INTEGER {
				halfDuplex(1),
				fullDuplex(2),
                                notApplicable(4)
			      }
	      ACCESS  read-write
	      STATUS  mandatory
	      DESCRIPTION
		      "Duplexity of the port."
	      ::= { portEntry 7 }

	  ptPortMediaType OBJECT-TYPE
	      SYNTAX  INTEGER {
				 doNotExist(1),
				 mediaType10F(2), 
				 mediaType10T(3),
				 mediaType100Tx(4),
				 mediaType100Fx(5),
				 gigabit(6),
				 gigabitCu(7)
			      } 
	      ACCESS  read-only
	      STATUS  mandatory
	      DESCRIPTION
		      "Port media type."
	      ::= { portEntry 8 }

	  ptPortLinkStatus OBJECT-TYPE
	      SYNTAX  INTEGER {
				 up(1),
				 down(2)
			      }
	      ACCESS  read-only
	      STATUS  mandatory
	      DESCRIPTION
		      "Port link status."
	      ::= { portEntry 9 }

	  ptPortSpeed OBJECT-TYPE
	      SYNTAX  INTEGER { 
				 speed10Mbps(1),
				 speed100Mbps(2),
				 speed1000Mbps(3),
                                 notApplicable(4)
			      } 
	      ACCESS  read-write
	      STATUS  mandatory
	      DESCRIPTION
		      "Port speed."
	      ::= { portEntry 10 }

	  ptPortPartitionState OBJECT-TYPE
	      SYNTAX  INTEGER {
				partitioned(1),
				notPartitioned(2),
                                notApplicable(4)
			      }
	      ACCESS  read-only
	      STATUS  mandatory
	      DESCRIPTION
		      "State of port partition."
	      ::= { portEntry 11 }

	  ptPortTraffic OBJECT-TYPE
	      SYNTAX  INTEGER
	      ACCESS  read-only
	      STATUS  mandatory
	      DESCRIPTION
		      "This object gives the count of only received packets
                       on this particular port. This object can be used to
                       check the activity on this port."
	      ::= { portEntry 12 }

	  ptPortAutoNegotiation OBJECT-TYPE
	      SYNTAX  INTEGER {
				 enable(1),
				 disable(2),
                                 notApplicable(4)
			      }
	      ACCESS  read-write
	      STATUS  mandatory
	      DESCRIPTION
		      "Enable/disable of port's Auto negotiation."
	      ::= { portEntry 13 }

	  ptPortNotify OBJECT-TYPE
	      SYNTAX  INTEGER {
				 			none(0),
							log(1),
							trap(2),
							logANDtrap(3),
							alarm(4),
							logANDalarm(5),
							trapANDalarm(6),
							all(7)
			      }
	      ACCESS  read-write
	      STATUS  mandatory
	      DESCRIPTION
		      "Notify Status."
	      ::= { portEntry 14 }

	  -- Port Mirroring 

	  portMirroring       OBJECT IDENTIFIER ::= { max25 4 }

	  monitorPort OBJECT-TYPE
	      SYNTAX  INTEGER
	      ACCESS  read-write
	      STATUS  mandatory
	      DESCRIPTION
		      "Monitored port number."
	      ::= { portMirroring 1 }

	  snifferPort OBJECT-TYPE
	      SYNTAX  INTEGER
	      ACCESS  read-write
	      STATUS  mandatory
	      DESCRIPTION
		      "Sniffer port number."
	      ::= { portMirroring 2 }

	  portMirroringControl OBJECT-TYPE
	      SYNTAX  INTEGER {
				 enable(1),
				 disable(2)
			      }
	      ACCESS  read-write
	      STATUS  mandatory
	      DESCRIPTION
		      "User can control port mirroring through this MIB object."
	      ::= { portMirroring 3 }

	  savePortMirroring OBJECT-TYPE
	      SYNTAX  INTEGER {
			       save(1),
			       saveDone(2)
                              }
	      ACCESS  read-write
	      STATUS  mandatory
	      DESCRIPTION
		      "Whenever thie MIB object is set to 1, 
                       the Port Mirroring configurations are saved."
	      REFERENCE
		      "GarrettCom, Inc (Belden) Internal Documents"
	      ::= { portMirroring 4 }

	  monitorPortList OBJECT-TYPE
	      SYNTAX  DisplayString
	      ACCESS  read-write
	      STATUS  mandatory
	      DESCRIPTION
		      "Monitored port List."
	      ::= { portMirroring 5 }


	  -- Priority Queuing 

	  priorityQueuing     OBJECT IDENTIFIER ::= { max25 5 }



	  priorityQueueControl OBJECT-TYPE
	      SYNTAX  INTEGER {
				 enable(1),
				 disable(2)
			      }
	      ACCESS  read-write
	      STATUS  mandatory
	      DESCRIPTION
		      "User can control priority queueing
		       through this MIB object."
	      ::= { priorityQueuing 1 }

	  savePriorityQueue OBJECT-TYPE
	      SYNTAX  INTEGER {
			       save(1),
			       saveDone(2)
                              }
	      ACCESS  read-write
	      STATUS  mandatory
	      DESCRIPTION
		      "Whenever thie MIB object is set to 1, 
                       the Priority Queue configurations (priorityQueueControl 
                       + priorityQueueTable) are saved."
	      REFERENCE
		      "GarrettCom, Inc (Belden) Internal Documents"
	      ::= { priorityQueuing 2 }


	  priorityQueueTable OBJECT-TYPE
	      SYNTAX  SEQUENCE OF PriorityQueueEntry
	      ACCESS  not-accessible
	      STATUS  mandatory
	      DESCRIPTION
		      "A list of priority queue entries. The number of
		      entries is given by the value of portNumber."
	      ::= { priorityQueuing 3 }

	  priorityQueueEntry OBJECT-TYPE
	      SYNTAX  PriorityQueueEntry
	      ACCESS  not-accessible
	      STATUS  mandatory
	      DESCRIPTION
		      "A priority queue values
		       for each ports in the device."
	      INDEX   { pqPortIndex }
	      ::= { priorityQueueTable 1 }


	   PriorityQueueEntry ::=
	      SEQUENCE {
		  pqPortIndex
		      INTEGER,
		  pqControlStatus
		      INTEGER,
		  pqDefaultQueue
		      INTEGER,
		  priorityForUntaggedPktsOnHighQ
		      INTEGER,
		  priorityForUntaggedPktsOnLowQ
		      INTEGER,
		  qForPktsWithPriority0
		      INTEGER,
		  qForPktsWithPriority1
		      INTEGER,
		  qForPktsWithPriority2
		      INTEGER,
		  qForPktsWithPriority3
		      INTEGER,
		  qForPktsWithPriority4
		      INTEGER,
		  qForPktsWithPriority5
		      INTEGER,
		  qForPktsWithPriority6
		      INTEGER,
		  qForPktsWithPriority7
		      INTEGER
	      }

	  pqPortIndex OBJECT-TYPE
	      SYNTAX  INTEGER (1..48)                                
	      ACCESS  read-only
	      STATUS  mandatory
	      DESCRIPTION
		      "Port index of this port."
	      ::= { priorityQueueEntry 1 }

	  pqControlStatus OBJECT-TYPE
	      SYNTAX  INTEGER {
				 enable(1),
				 disable(2)
			      }
	      ACCESS  read-write
	      STATUS  mandatory
	      DESCRIPTION
		      "Enable/disable the priority queuing on this port."
	      ::= { priorityQueueEntry 2 }

	  pqDefaultQueue OBJECT-TYPE
	      SYNTAX  INTEGER {
				low(1),
				medium(2),
				normal(3),
				high(4),
				none(5)
			      }                                 
	      ACCESS  read-write
	      STATUS  mandatory
	      DESCRIPTION
		      "Default queue for this port. If the value of this object is 
		       none(3), then the packets coming with priorities(0-7) will go 
		       to queue(low/high) as specified by the following MIB variables."
	      ::= { priorityQueueEntry 3 }

	  priorityForUntaggedPktsOnHighQ OBJECT-TYPE
	      SYNTAX  INTEGER {
				priority0(0),
				priority1(1),
				priority2(2),
				priority3(3),
				priority4(4),
				priority5(5),
				priority6(6),
				priority7(7)
			      }                                 
	      ACCESS  read-write
	      STATUS  mandatory
	      DESCRIPTION
		      "Queue for untagged packets received on 
		       HIGH queue on this port."
	      ::= { priorityQueueEntry 4 }

	  priorityForUntaggedPktsOnLowQ OBJECT-TYPE
	      SYNTAX  INTEGER {
				priority0(0),
				priority1(1),
				priority2(2),
				priority3(3),
				priority4(4),
				priority5(5),
				priority6(6),
				priority7(7)
			      }                                 
	      ACCESS  read-write
	      STATUS  mandatory
	      DESCRIPTION
		      "Queue for untagged packets received on 
		       LOW queue on this port."
	      ::= { priorityQueueEntry 5 }

	  qForPktsWithPriority0 OBJECT-TYPE
	      SYNTAX  INTEGER {
				low(1),
				high(2) 
			      }                                 
	      ACCESS  read-write
	      STATUS  mandatory
	      DESCRIPTION
		      "Queue for packets with priority
		       value zero, received on this port."
	      ::= { priorityQueueEntry 6 }

	  qForPktsWithPriority1 OBJECT-TYPE
	      SYNTAX  INTEGER {
				low(1),
				high(2) 
			      }                                 
	      ACCESS  read-write
	      STATUS  mandatory
	      DESCRIPTION
		      "Queue for packets with priority 
		       value one, received on this port."
	      ::= { priorityQueueEntry 7 }

	  qForPktsWithPriority2 OBJECT-TYPE
	      SYNTAX  INTEGER {
				low(1),
				high(2) 
			      }                                 
	      ACCESS  read-write
	      STATUS  mandatory
	      DESCRIPTION
		      "Queue for packets with priority 
		       value two, received on this port."
	      ::= { priorityQueueEntry 8 }

	  qForPktsWithPriority3 OBJECT-TYPE
	      SYNTAX  INTEGER {
				low(1),
				high(2) 
			      }                                 
	      ACCESS  read-write
	      STATUS  mandatory
	      DESCRIPTION
		      "Queue for packets with priority 
		       value three, received on this port."
	      ::= { priorityQueueEntry 9 }

	  qForPktsWithPriority4 OBJECT-TYPE
	      SYNTAX  INTEGER {
				low(1),
				high(2) 
			      }                                 
	      ACCESS  read-write
	      STATUS  mandatory
	      DESCRIPTION
		      "Queue for packets with priority 
		       value four, received on this port."
	      ::= { priorityQueueEntry 10 }

	  qForPktsWithPriority5 OBJECT-TYPE
	      SYNTAX  INTEGER {
				low(1),
				high(2) 
			      }                                 
	      ACCESS  read-write
	      STATUS  mandatory
	      DESCRIPTION
		      "Queue for packets with priority 
		       value five, received on this port."
	      ::= { priorityQueueEntry 11 }

	  qForPktsWithPriority6 OBJECT-TYPE
	      SYNTAX  INTEGER {
				low(1),
				high(2) 
			      }                                 
	      ACCESS  read-write
	      STATUS  mandatory
	      DESCRIPTION
		      "Queue for packets with priority 
		       value six, received on this port."
	      ::= { priorityQueueEntry 12 }

	  qForPktsWithPriority7 OBJECT-TYPE
	      SYNTAX  INTEGER {
				low(1),
				high(2) 
			      }                                 
	      ACCESS  read-write
	      STATUS  mandatory
	      DESCRIPTION
		      "Queue for packets with priority 
		       value seven, received on this port."
	      ::= { priorityQueueEntry 13 }



	  -- Layer 3 Quality Of Service

	  layer3Qos           OBJECT IDENTIFIER ::= { max25 6 }

	  layer3QosControl OBJECT-TYPE
	      SYNTAX  INTEGER {
				 enable(1),
				 disable(2)
			      }
	      ACCESS  read-write
	      STATUS  mandatory
	      DESCRIPTION
		      "User can control layer 3 QOS through this MIB 
		       object."
	      ::= { layer3Qos 1 }

	  savelayer3Qos OBJECT-TYPE
	      SYNTAX  INTEGER {
			       save(1),
			       saveDone(2)
                              }
	      ACCESS  read-write
	      STATUS  mandatory
	      DESCRIPTION
		      "Whenever thie MIB object is set to 1, 
                       the layer 3 QOS configurations (layer3QosControl 
                       + layer3QosPortTable + layer3QosQueueTable) are saved."
	      REFERENCE
		      "GarrettCom, Inc (Belden) Internal Documents"
	      ::= { layer3Qos 2 }


	  layer3QosPortTable  OBJECT-TYPE
	      SYNTAX  SEQUENCE OF Layer3QosPortEntry
	      ACCESS  not-accessible
	      STATUS  mandatory
	      DESCRIPTION
		      "A list of ports, where user can
		       enable/disable Layer 3 QOS per port basis."
	      ::= { layer3Qos 3 }

	  layer3QosPortEntry  OBJECT-TYPE
	      SYNTAX  Layer3QosPortEntry
	      ACCESS  not-accessible
	      STATUS  mandatory
	      DESCRIPTION
		      "Entry contains the layer3 QOS Control 
		       status for each ports in the device."
	      INDEX   { l3qptPortIndex }
	      ::= { layer3QosPortTable  1 }

	   Layer3QosPortEntry ::=
	      SEQUENCE {
		  l3qptPortIndex
		      INTEGER,
		  l3QosControlStatus
		      INTEGER
	      }   

	  l3qptPortIndex OBJECT-TYPE
	      SYNTAX  INTEGER (1..48)                                 
	      ACCESS  read-only
	      STATUS  mandatory
	      DESCRIPTION
		      "Port index of this port."
	      ::= { layer3QosPortEntry  1 }

	  l3QosControlStatus OBJECT-TYPE
	      SYNTAX  INTEGER {
				 enable(1),
				 disable(2)
			      }
	      ACCESS  read-write
	      STATUS  mandatory
	      DESCRIPTION
		      "Enable/disable the Layer 3 QOS on this port."
	      ::= { layer3QosPortEntry  2 }

	  layer3QosQueueTable  OBJECT-TYPE
	      SYNTAX  SEQUENCE OF Layer3QosQueueEntry
	      ACCESS  not-accessible
	      STATUS  mandatory
	      DESCRIPTION
		      "A list of ports, where each port has
		       64 QOS values."
	      ::= { layer3Qos 4 }

	  layer3QosQueueEntry  OBJECT-TYPE
	      SYNTAX  Layer3QosQueueEntry
	      ACCESS  not-accessible
	      STATUS  mandatory
	      DESCRIPTION
		      "Entry contains the Queue(High/Low) value
		       for each DSCP id, where DSCP ids range from 
		       1-64 for all the ports in the device."
	      INDEX   { l3qqtPortIndex,
			l3qqtDscpIndex }
	      ::= { layer3QosQueueTable  1 }

	   Layer3QosQueueEntry ::=
	      SEQUENCE {
		  l3qqtPortIndex
		      INTEGER,
		  l3qqtDscpIndex
		      INTEGER,
		  l3qqtQueueValue
		      INTEGER                      
	      }   

	  l3qqtPortIndex OBJECT-TYPE
	      SYNTAX  INTEGER (1..48)                           
	      ACCESS  read-only
	      STATUS  mandatory
	      DESCRIPTION
		      "Port index of this port."
	      ::= { layer3QosQueueEntry  1 }

	  l3qqtDscpIndex OBJECT-TYPE
	      SYNTAX  INTEGER (1..64)
	      ACCESS  read-only
	      STATUS  mandatory
	      DESCRIPTION
		      "The value of DSCP Id. This object can take
		       any value from 1 to 64."
	      ::= { layer3QosQueueEntry  2 }

	  l3qqtQueueValue OBJECT-TYPE
	      SYNTAX  INTEGER {
				low(1),
				high(2) 
			      }                                 
	      ACCESS  read-write
	      STATUS  mandatory
	      DESCRIPTION
		      "The queue for this port and dscpId."
	      ::= { layer3QosQueueEntry  3 }



	  -- Port Security 

	  portSecurity        OBJECT IDENTIFIER ::= { max25 7 }

	  portSecurityControl OBJECT-TYPE
	      SYNTAX  INTEGER {
				 enable(1),
				 disable(2)
			      }
	      ACCESS  read-write
	      STATUS  mandatory
	      DESCRIPTION
		      "User can control port security through this MIB 
		       object."
	      ::= { portSecurity 1 }

	  saveportSecurity OBJECT-TYPE
	      SYNTAX  INTEGER {
			       save(1),
			       saveDone(2)
                              }
	      ACCESS  read-write
	      STATUS  mandatory
	      DESCRIPTION
		      "Whenever thie MIB object is set to 1, 
                       the portSecurity configurations (portSecurityControl 
                       + portSecurityTable + actionSignalTable) are saved."
	      REFERENCE
		      "GarrettCom, Inc (Belden) Internal Documents"
	      ::= { portSecurity 2 }

	  portSecurityTable  OBJECT-TYPE
	      SYNTAX  SEQUENCE OF PortSecurityEntry
	      ACCESS  not-accessible
	      STATUS  mandatory
	      DESCRIPTION
		      "A list of MAC addresses which are to 
		       be allowed on these ports."
	      ::= { portSecurity 3 }

	  portSecurityEntry OBJECT-TYPE
	      SYNTAX  PortSecurityEntry
	      ACCESS  not-accessible
	      STATUS  mandatory
	      DESCRIPTION
		      "Each entry contains the MAC addresses allowed
		       on this port."
	      INDEX   { psPortIndex,
			psEntryIndex }
	      ::= { portSecurityTable 1 }

	   PortSecurityEntry ::=
	      SEQUENCE {
		  psPortIndex
		      INTEGER,
		  psEntryIndex
		      INTEGER,
		  psMacAddress
		      PhysAddress,
		  psEntryStatus
		      INTEGER
	      }   

	  psPortIndex OBJECT-TYPE
	      SYNTAX  INTEGER (1..48)                                 
	      ACCESS  read-only
	      STATUS  mandatory
	      DESCRIPTION
		      "Port index of this port."
	      ::= { portSecurityEntry 1 }

	  psEntryIndex OBJECT-TYPE
	      SYNTAX  INTEGER (0..500)
	      ACCESS  read-only
	      STATUS  mandatory
	      DESCRIPTION
		      "The entry index of this row in the table."
	      ::= { portSecurityEntry 2 }

	  psMacAddress OBJECT-TYPE
	      SYNTAX  PhysAddress
	      ACCESS  read-write
	      STATUS  mandatory
	      DESCRIPTION
		      "The MAC address of the device, whose packets 
		       are to be allowed on this port."
	      ::= { portSecurityEntry 3 }

	  psEntryStatus OBJECT-TYPE
	      SYNTAX  INTEGER {
				 include(1),
				 exclude(2)
			      }
	      ACCESS  read-write
	      STATUS  mandatory
	      DESCRIPTION
		      "Include is to add a new entry in the table.
		       Exclude will delete the entire row in the table."
	      ::= { portSecurityEntry 4 }


	  actionSignalTable  OBJECT-TYPE
	      SYNTAX  SEQUENCE OF ActionSignalEntry
	      ACCESS  not-accessible
	      STATUS  mandatory
	      DESCRIPTION
		      "A Table for taking the action/signal,
		       after getting an unauthorized packet arrives
		       on the ports of the device."
	      ::= { portSecurity 4 }

	  actionSignalEntry OBJECT-TYPE
	      SYNTAX  ActionSignalEntry
	      ACCESS  not-accessible
	      STATUS  mandatory
	      DESCRIPTION
		      "Each entry contains the action and signal
		       methods on this port."
	      INDEX   { atPortIndex }
	      ::= { actionSignalTable 1 }

	   ActionSignalEntry ::=
	      SEQUENCE {
		  atPortIndex
		      INTEGER,
		  atAction
		      INTEGER,
		  atSignal
		      INTEGER,
		  atLearnMode
		      INTEGER
	      }   

	  atPortIndex   OBJECT-TYPE
	      SYNTAX  INTEGER (1..48)
	      ACCESS  read-only
	      STATUS  mandatory
	      DESCRIPTION
		      "Port index of this port."
	      ::= { actionSignalEntry 1 }

	  atAction   OBJECT-TYPE
	      SYNTAX  INTEGER {
				 disable(1),
				 drop(2),
				 none(3) 
			      }
	      ACCESS  read-write
	      STATUS  mandatory
	      DESCRIPTION
		      "The action to be taken for an unauthorized
		       MAC address."
	      ::= { actionSignalEntry 2 }

	  atSignal   OBJECT-TYPE
	      SYNTAX  INTEGER {
				 log(1),
				 trap(2),
				 log-and-trap(3),
				 none(4) 
			      }
	      ACCESS  read-write
	      STATUS  mandatory
	      DESCRIPTION
		      "The signal to be done for an unauthorized
		       MAC address."
	      ::= { actionSignalEntry 3 }

	  atLearnMode     OBJECT-TYPE
	      SYNTAX  INTEGER {
				 enable(1),
				 disable(2)
			      }
	      ACCESS  read-write
	      STATUS  mandatory
	      DESCRIPTION
		      "To enable / disable the learn mode on this port."
	      ::= { actionSignalEntry 4 }



	  -- Virtual LAN 

	  vlan                OBJECT IDENTIFIER ::= { max25 8 }

	  vlanType   OBJECT-TYPE
	      SYNTAX  INTEGER {
				 portBasedVLAN(1),
				 tagBasedVLAN(3),
				 none(4) 
			      }
	      ACCESS  read-write
	      STATUS  mandatory
	      DESCRIPTION
		      "The type of VLAN. At any point of time, only 
                       one type of VLAN can be running."
	      ::= { vlan 1 }

	  portBasedVLAN       OBJECT IDENTIFIER ::= { vlan 2 }

	  tagBasedVLAN        OBJECT IDENTIFIER ::= { vlan 4 }


	  -- Port based VLAN

	  maxPVLAN   OBJECT-TYPE
	      SYNTAX  INTEGER 
	      ACCESS  read-only
	      STATUS  mandatory
	      DESCRIPTION
		      "The maximum number of port based VLANs possible."
	      ::= { portBasedVLAN 1 }

	  pvlansCreated   OBJECT-TYPE
	      SYNTAX  INTEGER 
	      ACCESS  read-only
	      STATUS  mandatory
	      DESCRIPTION
		      "The number of port based VLANs created.
                       This counter is incremented by one, whenever 
                       user creates a port based VLAN."
	      ::= { portBasedVLAN 2 }

	  savepvlan OBJECT-TYPE
	      SYNTAX  INTEGER {
			       save(1),
			       saveDone(2)
                              }
	      ACCESS  read-write
	      STATUS  mandatory
	      DESCRIPTION
		      "Whenever thie MIB object is set to 1, 
                       the port based VLAN configurations are saved."
	      REFERENCE
		      "GarrettCom, Inc (Belden) Internal Documents"
	      ::= { portBasedVLAN 3 }

	  pvlanControlStatus OBJECT-TYPE
	      SYNTAX  INTEGER {
			       start(1),
                               stop(2) 
                              }
	      ACCESS  read-write
	      STATUS  mandatory
	      DESCRIPTION
		      "To start/stop port based VLAN."
	      REFERENCE
		      "GarrettCom, Inc (Belden) Internal Documents"
	      ::= { portBasedVLAN 4 }

	  pvlanTable  OBJECT-TYPE
	      SYNTAX  SEQUENCE OF PvlanEntry
	      ACCESS  not-accessible
	      STATUS  mandatory
	      DESCRIPTION
		      "Port based VLAN table."
	      ::= { portBasedVLAN 5 }

	  pvlanEntry OBJECT-TYPE
	      SYNTAX  PvlanEntry
	      ACCESS  not-accessible
	      STATUS  mandatory
	      DESCRIPTION
		      "Port based VLAN entries."
	      INDEX   { pvlanIndex }
	      ::= { pvlanTable 1 }

	   PvlanEntry ::=
	      SEQUENCE {
		  pvlanIndex
		      INTEGER,
		  pvlanName
		      DisplayString,
		  pvlanPortList
		      DisplayString,
		  pvlanEntryStatus
		      INTEGER
	      }   

	  pvlanIndex	OBJECT-TYPE
	      SYNTAX  INTEGER (1..48)
	      ACCESS  read-only
	      STATUS  mandatory
	      DESCRIPTION
		      "Port based VLAN Index."
	      ::= { pvlanEntry 1 }

	  pvlanName	OBJECT-TYPE
	      SYNTAX  DisplayString
	      ACCESS  read-write
	      STATUS  mandatory
	      DESCRIPTION
		      "Port based VLAN name."
	      ::= { pvlanEntry 2 }

	  pvlanPortList	OBJECT-TYPE
	      SYNTAX  DisplayString
	      ACCESS  read-write
	      STATUS  mandatory
	      DESCRIPTION
		      "Port numbers separated by comma.
                       Eg. 1,4,6,2."
	      ::= { pvlanEntry 3 }

	  pvlanEntryStatus  OBJECT-TYPE
	      SYNTAX  INTEGER {
				 enable(1),
				 disable(2),
                 delete(3),
                 create(4) 
                         }  
	      ACCESS  read-write
	      STATUS  mandatory
	      DESCRIPTION
		      "Entry status of this Port based VLAN."
	      ::= { pvlanEntry 4 }



	  -- Tag based VLAN

	  maxTVLAN   OBJECT-TYPE
	      SYNTAX  INTEGER 
	      ACCESS  read-only
	      STATUS  mandatory
	      DESCRIPTION
		      "The maximum number of Tag based VLANs possible."
	      ::= { tagBasedVLAN 1 }

	  tvlansCreated   OBJECT-TYPE
	      SYNTAX  INTEGER 
	      ACCESS  read-only
	      STATUS  mandatory
	      DESCRIPTION
		      "The number of Tag based VLANs created.
                       This counter is incremented by one, whenever 
                       user creates a Tag based VLAN."
	      ::= { tagBasedVLAN 2 }

	  savetvlan OBJECT-TYPE
	      SYNTAX  INTEGER {
			       save(1),
			       saveDone(2)
                              }
	      ACCESS  read-write
	      STATUS  mandatory
	      DESCRIPTION
		      "Whenever thie MIB object is set to 1, 
                       the Tag based VLAN configurations are saved."
	      REFERENCE
		      "GarrettCom, Inc (Belden) Internal Documents"
	      ::= { tagBasedVLAN 3 }

	  tvlanControlStatus OBJECT-TYPE
	      SYNTAX  INTEGER {
			       start(1),
                               stop(2) 
                              }
	      ACCESS  read-write
	      STATUS  mandatory
	      DESCRIPTION
		      "To start/stop Tag based VLAN."
	      REFERENCE
		      "GarrettCom, Inc (Belden) Internal Documents"
	      ::= { tagBasedVLAN 4 }

	  tvlanTable  OBJECT-TYPE
	      SYNTAX  SEQUENCE OF TvlanEntry
	      ACCESS  not-accessible
	      STATUS  mandatory
	      DESCRIPTION
		      "Tag based VLAN table."
	      ::= { tagBasedVLAN 5 }

	  tvlanEntry OBJECT-TYPE
	      SYNTAX  TvlanEntry
	      ACCESS  not-accessible
	      STATUS  mandatory
	      DESCRIPTION
		      "Tag based VLAN entries."
	      INDEX   { tvlanIndex }
	      ::= { tvlanTable 1 }

  	  TvlanEntry ::=
	      SEQUENCE {
		  tvlanIndex
		      INTEGER,
		  tvlanName
		      DisplayString,
		  tvlanPortList
		      DisplayString,
		  tvlanEgressRules
		      DisplayString,
		  tvlanEntryStatus
		      INTEGER
	      }   

	  tvlanIndex	OBJECT-TYPE
	      SYNTAX  INTEGER (0..4095)
	      ACCESS  read-only
	      STATUS  mandatory
	      DESCRIPTION
		      "Tag based VLAN Index."
	      ::= { tvlanEntry 1 }

	  tvlanName	OBJECT-TYPE
	      SYNTAX  DisplayString
	      ACCESS  read-write
	      STATUS  mandatory
	      DESCRIPTION
		      "Name for this Tag based VLAN."
	      ::= { tvlanEntry 2 }

	  tvlanPortList	OBJECT-TYPE
	      SYNTAX  DisplayString
	      ACCESS  read-write
	      STATUS  mandatory
	      DESCRIPTION
		      "Port numbers separated by comma.
                       Eg. 1,4,6,2."
	      ::= { tvlanEntry 3 }

	  tvlanEgressRules	OBJECT-TYPE
	      SYNTAX  DisplayString
	      ACCESS  read-write
	      STATUS  mandatory
	      DESCRIPTION
		      "Egress rules. 
                       Eg. 1-t,2-u,3-t"
	      ::= { tvlanEntry 4 }

	  tvlanEntryStatus  OBJECT-TYPE
	      SYNTAX  INTEGER {
				 enable(1),
				 disable(2),
                                 delete(3),
                                 create(4) 
                              }  
	      ACCESS  read-write
	      STATUS  mandatory
	      DESCRIPTION
		      "Entry status of this tag based VLAN entry."
	      ::= { tvlanEntry 5 }


	  ingressTable  OBJECT-TYPE
	      SYNTAX  SEQUENCE OF IngressEntry
	      ACCESS  not-accessible
	      STATUS  mandatory
	      DESCRIPTION
		      "Ingress Table."
	      ::= { tagBasedVLAN 6 }

	  ingressEntry OBJECT-TYPE
	      SYNTAX  IngressEntry
	      ACCESS  not-accessible
	      STATUS  mandatory
	      DESCRIPTION
		      "Ingress table entries."
	      INDEX   { portIndex }
	      ::= { ingressTable 1 }

  	  IngressEntry ::=
	      SEQUENCE {
		  portIndex
		      INTEGER,
		  portDefaultId
		      INTEGER,
		  inCheck
		      INTEGER
	      }   

	  portIndex	OBJECT-TYPE
	      SYNTAX  INTEGER (1..48)
	      ACCESS  read-only
	      STATUS  mandatory
	      DESCRIPTION
		      "Port number."
	      ::= { ingressEntry 1 }

	  portDefaultId	OBJECT-TYPE
	      SYNTAX  INTEGER
	      ACCESS  read-write
	      STATUS  mandatory
	      DESCRIPTION
		      "Port default Id."
	      ::= { ingressEntry 2 }

	  inCheck  OBJECT-TYPE
	      SYNTAX  INTEGER {
				 disable(0),
				 enable(1)
                              }  
	      ACCESS  read-write
	      STATUS  mandatory
	      DESCRIPTION
		      "Incheck status."
	      ::= { ingressEntry 3 }

  -- STP

	  magnumStpGroup 		OBJECT IDENTIFIER ::= { max25 9 }


    magnumBrStpTable          OBJECT-TYPE
    SYNTAX              SEQUENCE OF MagnumBrStpEntry
    ACCESS          not-accessible
    STATUS              mandatory
    DESCRIPTION
                        "Table of bridge spanning tree information."

              ::= { magnumStpGroup 1 }

	magnumBrStpEntry          OBJECT-TYPE
    SYNTAX              MagnumBrStpEntry
    ACCESS          not-accessible
    STATUS              mandatory
    DESCRIPTION
                       "An entry in the magnumBrStpTable."
    INDEX              { magnumBrStpIndex }

              ::= { magnumBrStpTable 1 }


	MagnumBrStpEntry  ::=
    SEQUENCE {
        magnumBrStpIndex                 INTEGER,
        magnumBrStpDesignatedRoot            DisplayString,
        magnumBrStpRootPathCost              INTEGER,
        magnumBrStpRootPort                  INTEGER,
        magnumBrStpRootBridgeMaxAge          INTEGER,
        magnumBrStpRootBridgeHelloTime       INTEGER,
        magnumBrStpRootBridgeFwdDelay        INTEGER,
        magnumBrStpBridgeId                  DisplayString,
        magnumBrStpBridgeMaxAge              INTEGER,
        magnumBrStpBridgeHelloTime           INTEGER,
        magnumBrStpBridgeFwdDelay            INTEGER,
        magnumBrStpTopChangeDetected         INTEGER,
        magnumBrStpTopChange                 INTEGER,
        magnumBrStpHoldTime                  INTEGER,
        magnumBrStpAdminStatus               INTEGER
        
            }	

	magnumBrStpIndex             OBJECT-TYPE
    SYNTAX                     INTEGER (0..31)
    ACCESS                 read-only
    STATUS                     mandatory
    DESCRIPTION		
                               "This object uniquely identifies the lan or virtual lan."

              ::= { magnumBrStpEntry 1 }


	magnumBrStpDesignatedRoot        OBJECT-TYPE
    SYNTAX                     DisplayString
    ACCESS                 read-only
    STATUS                     mandatory
    DESCRIPTION		  "STP Designated Root"

             ::= { magnumBrStpEntry 2 }

	magnumBrStpRootPathCost         OBJECT-TYPE
    SYNTAX                    INTEGER
    ACCESS                read-only
    STATUS                    mandatory
    DESCRIPTION
                              "This field holds the cost of the path to the Root Bridge from 
                              this Bridge ."
             ::= { magnumBrStpEntry 3 }

	magnumBrStpRootPort            OBJECT-TYPE
    SYNTAX                   INTEGER
    ACCESS               read-only
    STATUS                   mandatory
    DESCRIPTION
                             "The port number of the port which offers the lowest cost path 
                             from this bridge to the root bridge."
	
            ::= { magnumBrStpEntry 4 }

	magnumBrStpRootBridgeMaxAge    OBJECT-TYPE
    SYNTAX                   INTEGER (4..30)
    ACCESS               read-only
    STATUS                   mandatory
    DESCRIPTION
                            "STP Bridge MAx Age"

            ::= { magnumBrStpEntry 5 }

	magnumBrStpRootBridgeHelloTime OBJECT-TYPE
    SYNTAX                   INTEGER (1..10)
    ACCESS               read-only
    STATUS                   mandatory
    DESCRIPTION		
                            "Root Bridge Hello Time"

            ::= { magnumBrStpEntry 6 }

	magnumBrStpRootBridgeFwdDelay OBJECT-TYPE
    SYNTAX                      INTEGER (4..30)
    ACCESS                  read-only
    STATUS                      mandatory
    DESCRIPTION		
                               "Root Bridge Fwd Delay"

            ::= { magnumBrStpEntry 7 }


	magnumBrStpBridgeId               OBJECT-TYPE
    SYNTAX                      DisplayString
    ACCESS                  read-only
    STATUS                      mandatory
    DESCRIPTION
                               "This holds the unique bridge identifier for the Bridge."

            ::= { magnumBrStpEntry 8 }

	magnumBrStpBridgeMaxAge           OBJECT-TYPE
    SYNTAX                      INTEGER
    ACCESS                  read-write
    STATUS                      mandatory
    DESCRIPTION
                                "Bridge Max Age"

            ::= {magnumBrStpEntry 9 }

	magnumBrStpBridgeHelloTime		OBJECT-TYPE
    SYNTAX                      INTEGER
    ACCESS                  read-write
    STATUS                      mandatory
    DESCRIPTION
                                "Bridge Hello time"
		
             ::= { magnumBrStpEntry 10 }

	magnumBrStpBridgeFwdDelay        OBJECT-TYPE
    SYNTAX                     INTEGER
    ACCESS                 read-write
    STATUS                     mandatory
    DESCRIPTION
                               "Bridge Fwd Delay"

              ::= { magnumBrStpEntry 11}

	magnumBrStpTopChangeDetected     OBJECT-TYPE
    SYNTAX                     INTEGER{
                                   false(0),
                                   true(1)
                                      }
    ACCESS                 read-only
    STATUS                     mandatory
    DESCRIPTION
                               "This object indicates that whether a topology change has been 
                                detected/notified to the bridge. "
	
              ::= { magnumBrStpEntry 12 }
	
	magnumBrStpTopChange            OBJECT-TYPE
    SYNTAX                    INTEGER{
                                 false(0),
                                 true(1)
                                     }
    ACCESS                read-only
    STATUS                    mandatory
    DESCRIPTION
                             "This field holds the value of the topology change flag in the 
                             configuration BPDU's sent by the bridge . "
	
              ::= { magnumBrStpEntry 13 }


	magnumBrStpHoldTime             OBJECT-TYPE
    SYNTAX                    INTEGER
    ACCESS                read-only
    STATUS                    mandatory
    DESCRIPTION
                              "This time value determines the interval length during which no
                               more than two Configuration bridge PDUs shall be transmitted by
                               this node, in units of hundredths of a second. "

             ::= { magnumBrStpEntry 14 }

	magnumBrStpAdminStatus         OBJECT-TYPE
    SYNTAX                   INTEGER {
                                 enabled (1),
                                 disabled (2)
                                     }
    ACCESS               read-write
    STATUS                   mandatory
    DESCRIPTION
                            "This field holds the user-defined administartive status of the 
                             spanning tree protocol operation . "
	
            ::= { magnumBrStpEntry 15 }


	magnumStpPortTable            OBJECT-TYPE
    SYNTAX                  SEQUENCE OF MagnumStpPortEntry
    ACCESS              not-accessible
    STATUS                  mandatory
    DESCRIPTION
                           "A table that contains port-specific information for the 
                           Spanning Tree Protocol."

           ::= { magnumStpGroup 2 }

	magnumStpPortEntry            OBJECT-TYPE
    SYNTAX                  MagnumStpPortEntry
    ACCESS              not-accessible
    STATUS                  mandatory
    DESCRIPTION
                           "A list of information maintained by every port about the 
                            Spanning Tree Protocol state for that port."

    INDEX                 {  magnumStpPort }

           ::= { magnumStpPortTable 1 }

	MagnumStpPortEntry ::=
    SEQUENCE {
        magnumStpPort                  INTEGER,
        magnumStpPortState             INTEGER,
        magnumStpPortPathCost          INTEGER,
        magnumStpPortDesignatedRoot    DisplayString,
        magnumStpPortDesignatedCost    INTEGER,
        magnumStpPortDesignatedBridge  DisplayString,
        magnumStpPortDesignatedPort    DisplayString,
        magnumStpTopChangeAck          INTEGER,
        magnumStpConfigPending         INTEGER,
        magnumStpPortPriority          INTEGER
        
             }

	magnumStpPort                 OBJECT-TYPE
    SYNTAX                  INTEGER (1..48)
    ACCESS              read-only
    STATUS                  mandatory
    DESCRIPTION	
                           "The port number of the port for which this entry contains Spanning
                            Tree Protocol management information."
    
              ::= { magnumStpPortEntry 1 }


	magnumStpPortState             OBJECT-TYPE
    SYNTAX                   INTEGER {
                                 disabled  (0),
					   listening  (1),
                                 learning  (2),
                                 forwarding(3),
					   blocking (4)
                                     }
    ACCESS               read-only
    STATUS                   mandatory
    DESCRIPTION		
                            "STP Port State"

   
              ::= { magnumStpPortEntry 2 }

	magnumStpPortPathCost           OBJECT-TYPE
    SYNTAX                    INTEGER
    ACCESS                read-write
    STATUS                    mandatory
    DESCRIPTION		
                             "Port Path Cost"

   
              ::= { magnumStpPortEntry 3 }

	magnumStpPortDesignatedRoot     OBJECT-TYPE
    SYNTAX                    DisplayString
    ACCESS                read-only
    STATUS                    mandatory
    DESCRIPTION			
                             "The unique Bridge Identifier of the Bridge recorded as the Root 
                             in the Configuration BPDUs transmitted by the Designated Bridge 
                             for the segment to which the port is attached."


             ::= { magnumStpPortEntry 4 }

	magnumStpPortDesignatedCost    OBJECT-TYPE
    SYNTAX                   INTEGER
    ACCESS               read-only
    STATUS                   mandatory
    DESCRIPTION	       
                            "The path cost of the Designated Port of the segment connected to
                             this port.  This value is compared to the Root Path Cost field in 
                             received bridge PDUs."

   

             ::= { magnumStpPortEntry 5 }

	magnumStpPortDesignatedBridge  OBJECT-TYPE
    SYNTAX                   DisplayString
    ACCESS               read-only
    STATUS                   mandatory
    DESCRIPTION		
                            "The Bridge Identifier of the bridge which this port considers to
                             be the Designated Bridge for this port's segment."

   
             ::= { magnumStpPortEntry 6 }

	magnumStpPortDesignatedPort   OBJECT-TYPE
    SYNTAX                  DisplayString
    ACCESS              read-only
    STATUS                  mandatory
    DESCRIPTION	
                           "The Port Identifier of the port on the Designated Bridge for this
                            port's segment."

   
             ::= { magnumStpPortEntry 7 }

	magnumStpTopChangeAck         OBJECT-TYPE
    SYNTAX                  INTEGER{
                                false (0),
                                true (1),
                                unknown (255)
                                   }
    ACCESS              read-only
    STATUS                  mandatory
    DESCRIPTION	
                           "This field is a flag indicating the value of the topology change.
                           acknowledgement flag in the next configuration BPDU to be transmitted
                           on the port."

            ::={ magnumStpPortEntry 8 }

	magnumStpConfigPending       OBJECT-TYPE
    SYNTAX                 INTEGER{
                               false (0),
                               true (1),
                               unknown (255)
                                  }
    ACCESS             read-only
    STATUS                 mandatory
    DESCRIPTION	
                           "This filed is a flag indicating that a configuration BPDU be transmitted
                            on expiration of the hold timer for the port. "

             ::={ magnumStpPortEntry 9 }

	magnumStpPortPriority       OBJECT-TYPE
    SYNTAX                INTEGER (0..255)
    ACCESS            read-write
    STATUS                mandatory
    DESCRIPTION     
                          "The priority of the port in the bridge."
        
             ::={magnumStpPortEntry 10 }

  --  END OF STPGROUP

  --  BridgeGroup
 magnumBridgeGroup 		OBJECT IDENTIFIER ::= { max25 11 }

magnumStpBridgeAgingTime		OBJECT-TYPE
	SYNTAX				INTEGER
	
	ACCESS			read-write
	STATUS				mandatory
	DESCRIPTION			"Bridge Aging Time"

		::= { magnumBridgeGroup 1 }

magnumMgtBridgeTime		OBJECT-TYPE
	SYNTAX				INTEGER
	
	ACCESS			read-write
	STATUS				mandatory
	DESCRIPTION			"Maanagement Aging Time"

		::= { magnumBridgeGroup 2 }

magnumbridgeMacCount		OBJECT-TYPE
	SYNTAX				INTEGER
	
	ACCESS			read-only
	STATUS				mandatory
	DESCRIPTION			"Mac Count"

		::= { magnumBridgeGroup 3 }



  --  -End Of BridgeGroup
  --  -EVENTLOG GROUP
 magnumEventMgrGroup 		OBJECT IDENTIFIER ::= { max25 12 }


    magnumEventsRaised        OBJECT-TYPE
    SYNTAX              INTEGER (0..2500)
    ACCESS          read-only   
    STATUS              mandatory
    DESCRIPTION		"Events Raised"
    DEFVAL              { 0 }

              ::= {magnumEventMgrGroup 1 }

    magnumSizeOfEventQueue        OBJECT-TYPE
    SYNTAX              INTEGER (0..2500)
    ACCESS          read-write
    STATUS              mandatory
    DESCRIPTION		"Event Queue"
    DEFVAL              { 100 }

              ::= {magnumEventMgrGroup 2 }

    magnumEventLogInvalidEvents  OBJECT-TYPE
    SYNTAX                  INTEGER (0..2500)
    ACCESS              read-only
    STATUS                  mandatory
    DESCRIPTION             "Invalid Events"

              ::= { magnumEventMgrGroup 3 }

    magnumEventLogCriticalEvents  OBJECT-TYPE
    SYNTAX                  INTEGER (0..2500)
    ACCESS              read-only
    STATUS                  mandatory
    DESCRIPTION             "Critical events"

              ::= { magnumEventMgrGroup 4 }


    magnumEventLogDebugEvents    OBJECT-TYPE
    SYNTAX                  INTEGER (0..2500)
    ACCESS              read-only
    STATUS                  mandatory
    DESCRIPTION
                            "Debug Events"

              ::= { magnumEventMgrGroup 5 }

    magnumEventLogFatalEvents     OBJECT-TYPE
    SYNTAX                  INTEGER (0..2500)
    ACCESS              read-only
    STATUS                  mandatory
    DESCRIPTION
                            "Fatal Events"

              ::= { magnumEventMgrGroup 6 }

    magnumEventLogActivityEvents   OBJECT-TYPE
    SYNTAX                  INTEGER (0..2500)
    ACCESS              read-only
    STATUS                  mandatory
    DESCRIPTION
                            "Activity Events"

               ::= { magnumEventMgrGroup 7 }

    magnumEventLogInfoEvents	 OBJECT-TYPE
    SYNTAX                   INTEGER
    ACCESS               read-only
    STATUS                   mandatory
    DESCRIPTION				
                            "Informational Events"
								
                ::= { magnumEventMgrGroup 8 }

    magnumEventTable              OBJECT-TYPE
    SYNTAX                  SEQUENCE OF MagnumEventEntry
    ACCESS              not-accessible
    STATUS                  mandatory
    DESCRIPTION
                           "Event Table"

              ::= { magnumEventMgrGroup 9 }


	magnumEventEntry              OBJECT-TYPE
    SYNTAX                  MagnumEventEntry
    ACCESS              not-accessible
    STATUS                  mandatory
    DESCRIPTION             "Event entry"
    INDEX                 { magnumEventIndex }

              ::= { magnumEventTable 1 }

	MagnumEventEntry ::=
    SEQUENCE{
          magnumEventIndex      INTEGER,
          magnumEventCode       INTEGER,
          magnumEventModuleId     INTEGER,
          magnumEventSeverity   INTEGER,
          magnumEventTimeStamp  DisplayString
           }

	magnumEventIndex          OBJECT-TYPE
    SYNTAX              INTEGER (1..2500)
    ACCESS          read-only
    STATUS              mandatory
    DESCRIPTION		
                       "This object indicates the running serial number of the
                        Event recorded in the Event Log Table. "

              ::= { magnumEventEntry 1 }

	magnumEventCode           OBJECT-TYPE
    SYNTAX              INTEGER
    ACCESS          read-only
    STATUS              mandatory
    DESCRIPTION
                        "An internal code which details the cause of the event.It is
                        intended for use by customer service personnel only . "

              ::= { magnumEventEntry 2 }
        
	magnumEventModuleId         OBJECT-TYPE
    SYNTAX              INTEGER
    ACCESS          read-only
    STATUS              mandatory
    DESCRIPTION     
                        "The module Id of the module which sent this event ."
                        
             ::={magnumEventEntry 3 }
        

	magnumEventSeverity       OBJECT-TYPE
    SYNTAX              INTEGER {
    						fatal (0),
                           alert  (1),
                           critical (2),
                           error  (3),
                            warning(4),
                           notification (5),
                           information (6),
                           debug (7)
                                }
    ACCESS          read-only
    STATUS              mandatory
    DESCRIPTION	
                       "Event Severity"

             ::= { magnumEventEntry 4 }


	magnumEventTimeStamp      OBJECT-TYPE
    SYNTAX              DisplayString
    ACCESS          read-only
    STATUS              mandatory
    DESCRIPTION
                       "The Timestamp of the event. "

              ::= { magnumEventEntry 5 }

  --  END OF EVENTGROUP

  --  ImageLoader
 magnumTftpGroup 		OBJECT IDENTIFIER ::= { max25 13 }

	magnumTFTPSeverIpAddress  OBJECT-TYPE
    SYNTAX              IpAddress	
    ACCESS          read-write
    STATUS              mandatory
    DESCRIPTION
                        "The ipaddress of the Tftp server."

           ::=	{magnumTftpGroup 1 }

	magnumTFTPRemoteFileName  OBJECT-TYPE
    SYNTAX              DisplayString(SIZE(0..50))
    ACCESS          read-write
    STATUS              mandatory
    DESCRIPTION			
                       "The field gives the file name to be downloaded. "

           ::= { magnumTftpGroup 2 }

	magnumTFTPTransferType   OBJECT-TYPE
    SYNTAX             INTEGER{
    					unknown (0),
                          octet (1),
                          nonascii (2)
                              }
    ACCESS         read-only
    STATUS             mandatory
    DESCRIPTION			
                       "This field gives the file transfer type of the TFTP.  "
	
           ::= {magnumTftpGroup 3}

	magnumTFTPAction        OBJECT-TYPE
    SYNTAX            INTEGER{
    					 none (1),
                         downloadImage (2),
                         configUploadText(3),
                         configDownload (4),
                         configUploadEncrypted(5)
                             }
    ACCESS        read-write
    STATUS            mandatory
    DESCRIPTION	   "TFTP Action"

          ::= {magnumTftpGroup 4}

	magnumTFTPTrfrStatus     OBJECT-TYPE
    SYNTAX            INTEGER{
    					 other (0),
                         pending (1),
                         ok(2),
                         failed(3)
                             }
    ACCESS        read-only
    STATUS            mandatory
    DESCRIPTION	  "This object returns the result of the last file transfer
                    other - No File Transfer in progress
                    pending - File Transfer in progress
                    success - File Transfer is successfull
                    failed - File Transfer failed"
          ::= {magnumTftpGroup 5}

  -- End Of ImageLoader

  --  -SNTP group
 magnumSNTPGroup 		OBJECT IDENTIFIER ::= { max25 14 }

    sntpStatus		OBJECT-TYPE
    SYNTAX          INTEGER {
					            disable   (0),
					            enable    (1)
                            }
    ACCESS      read-write
    STATUS          mandatory
    DESCRIPTION     "Enables or disables SNTP feature."

           ::= { magnumSNTPGroup 1 }
           
    sntpTimeFormat  OBJECT-TYPE
    SYNTAX          INTEGER {
					            hrs12  (0),
					            hrs24  (1)
					        }
    ACCESS      read-write
    STATUS          mandatory
    DESCRIPTION     "Time Format"

           ::= { magnumSNTPGroup 2 }
           
    sntpDateFormat  OBJECT-TYPE
    SYNTAX          INTEGER {
					            mm-dd-yyyy   (0),
					            dd-mm-yyyy   (1),
					            yyyy-mm-dd   (2)
					        }
    ACCESS      read-write
    STATUS          mandatory
    DESCRIPTION     "Date Format"

           ::= { magnumSNTPGroup 3 }

	sntpDisplayDate		OBJECT-TYPE
    SYNTAX              DisplayString
    ACCESS          read-only
    STATUS              mandatory
    DESCRIPTION         "Display Date"

           ::= { magnumSNTPGroup 4 }

	sntpDisplayTime		OBJECT-TYPE
    SYNTAX              DisplayString
    ACCESS          read-only
    STATUS              mandatory
    DESCRIPTION         "Display Time"

           ::= { magnumSNTPGroup 5 }


	sntpDisplayTimeZone	   OBJECT-TYPE
    SYNTAX                 DisplayString
    ACCESS             read-only
    STATUS                 mandatory
    DESCRIPTION            "Time Zone"

           ::= { magnumSNTPGroup 6 }

	sntpDayLightSavings		OBJECT-TYPE
    SYNTAX                 DisplayString
    ACCESS             read-write
    STATUS                 mandatory
    DESCRIPTION            "Daylight Savings"

           ::= { magnumSNTPGroup 7 }

	magnumSNTPTable     OBJECT-TYPE
    SYNTAX                SEQUENCE OF MagnumSNTPEntry
    ACCESS            not-accessible
    STATUS                mandatory
    DESCRIPTION
                          "SNTP Table"
             ::= { magnumSNTPGroup 8 }

	magnumSNTPEntry     OBJECT-TYPE
    SYNTAX                MagnumSNTPEntry
    ACCESS            not-accessible
    STATUS                mandatory
    DESCRIPTION	
                          "SNTP Entry"
    INDEX                 { sntpIndex }

        ::= { magnumSNTPTable 1 }

	MagnumSNTPEntry ::= 
    SEQUENCE {	
	sntpIndex				INTEGER,      
	sntpServerIp				IpAddress,
	socketTimeout				INTEGER,
	noOfRetries				INTEGER,
	sntpOperation				INTEGER 
       
            }

	sntpIndex      OBJECT-TYPE
    SYNTAX                 INTEGER      (1..5)

    ACCESS             read-only
    STATUS                 mandatory
    DESCRIPTION            "Sntp Index"

           ::= {magnumSNTPEntry 1}


	sntpServerIp		OBJECT-TYPE
    SYNTAX                 IpAddress
    ACCESS             read-write
    STATUS                 mandatory
    DESCRIPTION            "Server IP"

           ::= {magnumSNTPEntry 2}

	socketTimeout		OBJECT-TYPE
    SYNTAX                 INTEGER
    ACCESS             read-write
    STATUS                 mandatory
    DESCRIPTION            "Timeout"

           ::= {magnumSNTPEntry 3}

	noOfRetries			OBJECT-TYPE
    SYNTAX                 INTEGER
    ACCESS             read-write
    STATUS                 mandatory
    DESCRIPTION            "Retries"

           ::= {magnumSNTPEntry 4}

	sntpOperation			OBJECT-TYPE
    SYNTAX                 INTEGER{
					add(1),
					delete(2),
					modify(3),
					update(4)
					}
    ACCESS             read-write
    STATUS                 mandatory
    DESCRIPTION            "Operation"

           ::= {magnumSNTPEntry 5}

  --  END of SNTPGroup
  --  GVRPGroup


 magnumGVRPGroup 		OBJECT IDENTIFIER ::= { max25 15 }


	deviceGVRPState   	   OBJECT-TYPE
    SYNTAX                 INTEGER{
					                enable   (1),
					                disable  (2)
					              }
    ACCESS             read-write
    STATUS                 mandatory
    DESCRIPTION            "This object indicates whether GVRP feature 
                            is enabled or disable for Tag-based VLANs."

           ::= { magnumGVRPGroup 1 }

	magnumGVRPPortTable    OBJECT-TYPE
    SYNTAX                 SEQUENCE OF MagnumGVRPPortEntry
    ACCESS             not-accessible
    STATUS                 mandatory
    DESCRIPTION            "This table shows/sets the GVRP port states."
           ::= { magnumGVRPGroup 2 }

	magnumGVRPPortEntry    OBJECT-TYPE
    SYNTAX                 MagnumGVRPPortEntry
    ACCESS             not-accessible
    STATUS                 mandatory
    DESCRIPTION	           "GVRP Port Entry"
    INDEX                  { gvrpPortIndex }

           ::= { magnumGVRPPortTable 1 }

	MagnumGVRPPortEntry ::= SEQUENCE 
                            {	
	                            gvrpPortIndex     INTEGER,
                                gvrpPortState     INTEGER
                            }

    gvrpPortIndex          OBJECT-TYPE
    SYNTAX                 INTEGER    (1..48)
    ACCESS             read-only
    STATUS                 mandatory
    DESCRIPTION            "GVRP Port Index"

           ::= { magnumGVRPPortEntry 1 }

    gvrpPortState          OBJECT-TYPE
    SYNTAX                 INTEGER{
					                learn   (1),
					                block   (2),
                                    disable (3)
					              }
    ACCESS             read-write
    STATUS                 mandatory
    DESCRIPTION            "GVRP Port State"

           ::= { magnumGVRPPortEntry 2 }



  -- END of GVRPGroup

  -- PortManagerGroup
 magnumPortManagerGroup 		OBJECT IDENTIFIER ::= { max25 16 }

    magnumPortManagerTable      OBJECT-TYPE
    SYNTAX                   SEQUENCE OF MagnumPortManagerEntry
    ACCESS               not-accessible
    STATUS                   mandatory
    DESCRIPTION
                            "Port Manager"

            ::= { magnumPortManagerGroup 1 }

    magnumPortManagerEntry      OBJECT-TYPE
    SYNTAX                   MagnumPortManagerEntry
    ACCESS               not-accessible
    STATUS                   mandatory
    DESCRIPTION
                             "An entry in the magnumPortManagerTable."	
    INDEX                    {magnumPortNumber }

              ::= { magnumPortManagerTable 1 }

	MagnumPortManagerEntry ::= 
    SEQUENCE {
			magnumPortNumber		    INTEGER,
			magnumPortName  		    DisplayString,
			magnumPortSpeed         	    INTEGER,
			magnumPortDuplexMode		    INTEGER,
			magnumPortAutoNegotiationMode       INTEGER,			
			magnumPortFlowControl               INTEGER,
			magnumPortBackPressure              INTEGER,
			magnumPortVLANId                    INTEGER,			
			magnumPortGVRPstate                 INTEGER,
			magnumPortSTPstate                  INTEGER,
			magnumPortLinkState                 INTEGER,
			magnumPortInterfaceType             DisplayString,
			magnumPortSecurityState             INTEGER,
			magnumPortTaggingState              INTEGER,
			magnumPortNotifyState               INTEGER

		}

	magnumPortNumber         	OBJECT-TYPE	
    SYNTAX               INTEGER     (1..48)
    ACCESS           read-only
    STATUS               mandatory
    DESCRIPTION	
                        "Port Number"

               ::= { magnumPortManagerEntry 1 }


	magnumPortName          OBJECT-TYPE
    SYNTAX               DisplayString
    ACCESS           read-write
    STATUS               mandatory
    DESCRIPTION	
                        "Port Name"

               ::= { magnumPortManagerEntry 2 }

	magnumPortSpeed         	OBJECT-TYPE		
    SYNTAX               INTEGER
    ACCESS           read-write
    STATUS               mandatory
    DESCRIPTION	
                        "Port Speed"

               ::= { magnumPortManagerEntry 3 }

	magnumPortDuplexMode	OBJECT-TYPE		
    SYNTAX               INTEGER{
                          half (0),
                          full (1)
                              }		
    ACCESS           read-write
    STATUS               mandatory
    DESCRIPTION	
                        "Duplex Mode"

               ::= { magnumPortManagerEntry 4 }


	magnumPortAutoNegotiationMode       OBJECT-TYPE		
    SYNTAX               INTEGER{
                              disable (0),
                              enable (1)
                                }	

    ACCESS           read-write
    STATUS               mandatory
    DESCRIPTION	
                        "AutoNeg Mode"

               ::= { magnumPortManagerEntry 5 }

	
          
	magnumPortFlowControl    OBJECT-TYPE		
    SYNTAX               INTEGER{
                              disable (0),
                              enable (1)
                            }		
    ACCESS           read-write
    STATUS               mandatory
    DESCRIPTION	
                        "Flow Ctrl"

               ::= { magnumPortManagerEntry 6 }

	magnumPortBackPressure    OBJECT-TYPE		
    SYNTAX               INTEGER{
                              disable (0),
                              enable (1)
                            }	

    ACCESS           read-write
    STATUS               mandatory
    DESCRIPTION	
                        "Back Pressure"

               ::= { magnumPortManagerEntry 7 }

	magnumPortVLANId           OBJECT-TYPE		
    SYNTAX               INTEGER
    ACCESS           read-only
    STATUS               mandatory
    DESCRIPTION	
                        "Vlan Id"

               ::= { magnumPortManagerEntry 8}

	

	
                               
	magnumPortGVRPstate                    OBJECT-TYPE		
    SYNTAX               INTEGER{
						disable  (0),
					enable  (1)
					}

    ACCESS           read-only
    STATUS               mandatory
    DESCRIPTION	
                        "GVRP State"

               ::= { magnumPortManagerEntry 9}
	
	magnumPortSTPstate                       OBJECT-TYPE		
    SYNTAX               INTEGER{
					blocking  (0),
					disable  (1),
					listening  (2),
					learning    (3),
					forwarding  (4)
					}

    ACCESS           read-only
    STATUS               mandatory
    DESCRIPTION	
                        "STP State"
               ::= { magnumPortManagerEntry 10}

	magnumPortLinkState	OBJECT-TYPE		
    SYNTAX               INTEGER{
					down  (0),
					up  (1)
					}

    ACCESS           read-only
    STATUS               mandatory
    DESCRIPTION	
                        "Link State"

               ::= { magnumPortManagerEntry 11}

    
	magnumPortInterfaceType        	OBJECT-TYPE		
    SYNTAX               DisplayString
    ACCESS           read-only
    STATUS               mandatory
    DESCRIPTION	
                        "Interface type"

               ::= { magnumPortManagerEntry 12}

magnumPortSecurityState                    OBJECT-TYPE
		
    SYNTAX               INTEGER{
					disable  (0),
					enable  (1)
					}

    ACCESS           read-only
    STATUS               mandatory
    DESCRIPTION	
                        "PortSec State"

               ::= { magnumPortManagerEntry 13}

	magnumPortTaggingState                     OBJECT-TYPE		
    SYNTAX               INTEGER{
					disable  (0),
					enable  (1)
					}

    ACCESS           read-only
    STATUS               mandatory
    DESCRIPTION	
                        "Tagging State"

               ::= { magnumPortManagerEntry 14}

	magnumPortNotifyState                     OBJECT-TYPE		
    SYNTAX               INTEGER{
							none(0),
							log(1),
							trap(2),
							logANDtrap(3),
							alarm(4),
							logANDalarm(5),
							trapANDalarm(6),
							all(7)
					}

    ACCESS           read-write
    STATUS               mandatory
    DESCRIPTION	
                        "Notify State"

               ::= { magnumPortManagerEntry 15}

    magnumPortStatsTable      OBJECT-TYPE
    SYNTAX                   SEQUENCE OF MagnumPortStatsEntry
    ACCESS               not-accessible
    STATUS                   mandatory
    DESCRIPTION
                            "Port Stats"

            ::= { magnumPortManagerGroup 2 }

    magnumPortStatsEntry      OBJECT-TYPE
    SYNTAX                   MagnumPortStatsEntry
    ACCESS               not-accessible
    STATUS                   mandatory
    DESCRIPTION
                             "An entry in the MagnumPortstatsTable."	
    INDEX                    {portStatsIndex }

              ::= { magnumPortStatsTable 1 }

	MagnumPortStatsEntry ::= 
    SEQUENCE {
			portStatsIndex				INTEGER,
			portBytesReceived	        	INTEGER,
			portBytesSent             		INTEGER,
			portFramesReceived			INTEGER,
			portFramesSent				INTEGER,
			portTotalBytesReceived      		INTEGER,
			portTotalFramesReceived			INTEGER,
			portBroadcastFramesReceived		INTEGER,
			portMulticastFramesReceived		INTEGER,
			portCrcErrors				INTEGER,
			portOversizeFrames			INTEGER,
			portFragments				INTEGER,
			portJabbers				INTEGER,
			portCollissions				INTEGER,
			portLateCollissions			INTEGER,
			portFrames67-127			INTEGER,
			portFrames128-255			INTEGER,
			portFrames256-511			INTEGER,
			portFrames512-1023			INTEGER,
			portFrames1024-MaxSize			INTEGER,
			portMacRxErrors				INTEGER,
			portDroppedFrames			INTEGER,
			portOutMulticastFrames			INTEGER,
			portOutBroadcastFrames			INTEGER,
			portUndersizeFrames 			INTEGER,
			portClearStatistics                     INTEGER
		}
			
    portStatsIndex          OBJECT-TYPE
    SYNTAX               INTEGER   (1..48)
    ACCESS           read-only
    STATUS               mandatory
    DESCRIPTION	
                        "Index"
               ::= { magnumPortStatsEntry 1 }
    portBytesReceived	 OBJECT-TYPE
    SYNTAX               INTEGER
    ACCESS           read-only
    STATUS               mandatory
    DESCRIPTION	       "Bytes Received"
               ::= { magnumPortStatsEntry 2 }
    portBytesSent          OBJECT-TYPE
    SYNTAX               INTEGER
    ACCESS           read-only
    STATUS               mandatory
    DESCRIPTION	       "Bytes Sent"
               ::= { magnumPortStatsEntry 3 }
    
   portFramesReceived		OBJECT-TYPE
    SYNTAX              	 INTEGER
    ACCESS          	 read-only
    STATUS               	mandatory
    DESCRIPTION	      	 "Frames Received"
               ::= { magnumPortStatsEntry 4 }
    portFramesSent		OBJECT-TYPE
    SYNTAX              	 INTEGER
    ACCESS          	 read-only
    STATUS               	mandatory
    DESCRIPTION	      	 "Frames Sent"
               ::= { magnumPortStatsEntry 5 }
    portTotalBytesReceived      OBJECT-TYPE
    SYNTAX              	 INTEGER
    ACCESS          	 read-only
    STATUS               	mandatory
    DESCRIPTION	      	 "Bytes Received"
               ::= { magnumPortStatsEntry 6 }
    portTotalFramesReceived	OBJECT-TYPE
    SYNTAX              	 INTEGER
    ACCESS          	 read-only
    STATUS               	mandatory
    DESCRIPTION	      	 "Frames Received"
               ::= { magnumPortStatsEntry 7 }
    portBroadcastFramesReceived	OBJECT-TYPE
    SYNTAX              		 INTEGER
    ACCESS          		 read-only
    STATUS               		mandatory
    DESCRIPTION	      		 "Bcast Frames Received"
               ::= { magnumPortStatsEntry 8 }
    portMulticastFramesReceived	OBJECT-TYPE
    SYNTAX              		 INTEGER
    ACCESS          		 read-only
    STATUS               		mandatory
    DESCRIPTION	      		 "Mcast Frames Received"
               ::= { magnumPortStatsEntry 9 }
    portCrcErrors			OBJECT-TYPE
    SYNTAX              		 INTEGER
    ACCESS          		 read-only
    STATUS               		mandatory
    DESCRIPTION	      		 "CRC Errors"
               ::= { magnumPortStatsEntry 10 }
    portOversizeFrames			OBJECT-TYPE
    SYNTAX              		 INTEGER
    ACCESS          		 read-only
    STATUS               		mandatory
    DESCRIPTION	      		 "Oversize Frames"
               ::= { magnumPortStatsEntry 11 }
    portFragments			OBJECT-TYPE
    SYNTAX              		 INTEGER
    ACCESS          		 read-only
    STATUS               		mandatory
    DESCRIPTION	      		 "Fragments"
               ::= { magnumPortStatsEntry 12 }
    portJabbers			OBJECT-TYPE
    SYNTAX              		 INTEGER
    ACCESS          		 read-only
    STATUS               		mandatory
    DESCRIPTION	      		 "Jabbers"
               ::= { magnumPortStatsEntry 13 }
    portCollissions			OBJECT-TYPE
    SYNTAX              		 INTEGER
    ACCESS          		 read-only
    STATUS               		mandatory
    DESCRIPTION	      		 "Collisions"
               ::= { magnumPortStatsEntry 14 }
    portLateCollissions			OBJECT-TYPE
    SYNTAX              		 INTEGER
    ACCESS          		 read-only
    STATUS               		mandatory
    DESCRIPTION	      		 "Late Collisions"
               ::= { magnumPortStatsEntry 15 }
    
    portFrames67-127		OBJECT-TYPE
    SYNTAX              		 INTEGER
    ACCESS          		 read-only
    STATUS               		mandatory
    DESCRIPTION	      		 "Frames67-127"
               ::= { magnumPortStatsEntry 16 }
    portFrames128-255		OBJECT-TYPE
    SYNTAX              		 INTEGER
    ACCESS          		 read-only
    STATUS               		mandatory
    DESCRIPTION	      		 "Frames127-255"
               ::= { magnumPortStatsEntry 17 }
    portFrames256-511		OBJECT-TYPE
    SYNTAX              		 INTEGER
    ACCESS          		 read-only
    STATUS               		mandatory
    DESCRIPTION	      		 "Frames256-511"
               ::= { magnumPortStatsEntry 18 }
    portFrames512-1023		OBJECT-TYPE
    SYNTAX              		 INTEGER
    ACCESS          		 read-only
    STATUS               		mandatory
    DESCRIPTION	      		 "Frames512-1023"
               ::= { magnumPortStatsEntry 19 }
    portFrames1024-MaxSize		OBJECT-TYPE
    SYNTAX              		 INTEGER
    ACCESS          		 read-only
    STATUS               		mandatory
    DESCRIPTION	      		 "Frames1024-Max"
               ::= { magnumPortStatsEntry 20 }
    portMacRxErrors			OBJECT-TYPE
    SYNTAX              		 INTEGER
    ACCESS          		 read-only
    STATUS               		mandatory
    DESCRIPTION	      		 "Mac Rx Err"
               ::= { magnumPortStatsEntry 21 }
    portDroppedFrames			OBJECT-TYPE
    SYNTAX              		 INTEGER
    ACCESS          		 read-only
    STATUS               		mandatory
    DESCRIPTION	      		 "Dropped"
               ::= { magnumPortStatsEntry 22 }
    portOutMulticastFrames		OBJECT-TYPE
    SYNTAX              		 INTEGER
    ACCESS          		 read-only
    STATUS               		mandatory
    DESCRIPTION	      		 "Multicast Frames"
               ::= { magnumPortStatsEntry 23 }
    portOutBroadcastFrames		OBJECT-TYPE
    SYNTAX              		 INTEGER
    ACCESS          		 read-only
    STATUS               		mandatory
    DESCRIPTION	      		 "Broadcast Frames"
               ::= { magnumPortStatsEntry 24 }
 
    portUndersizeFrames 		OBJECT-TYPE
    SYNTAX              		 INTEGER
    ACCESS          		 read-only
    STATUS               		mandatory
    DESCRIPTION	      		 "Undersize"
               ::= { magnumPortStatsEntry 25 }
 
    portClearStatistics       OBJECT-TYPE
    SYNTAX              		 INTEGER{
							clear   (1)
								}
    ACCESS          		 read-write
    STATUS               		mandatory
    DESCRIPTION	      		 "Clear Stats"
               ::= { magnumPortStatsEntry 26 }
          

    magnumPortQosTable      OBJECT-TYPE
    SYNTAX                   SEQUENCE OF MagnumPortQosEntry
    ACCESS               not-accessible
    STATUS                   mandatory
    DESCRIPTION
                            "QOS"

            ::= { magnumPortManagerGroup 3 }

    magnumPortQosEntry      OBJECT-TYPE
    SYNTAX                   MagnumPortQosEntry
    ACCESS               not-accessible
    STATUS                   mandatory
    DESCRIPTION
                             "An entry in the magnumPortManagerTable."	
    INDEX                    {magnumPortNumber }

              ::= { magnumPortQosTable 1 }

    MagnumPortQosEntry ::= 
    SEQUENCE {
			magnumPortQosIndex				INTEGER,
			magnumPortQosPriority  		        	INTEGER,
			magnumTypeOfService				DisplayString
		}
    magnumPortQosIndex		OBJECT-TYPE
    SYNTAX              		 INTEGER
    ACCESS          		 read-write
    STATUS               		mandatory
    DESCRIPTION	      		 "Index"
               ::= { magnumPortQosEntry  1 }

   
    magnumPortQosPriority  	OBJECT-TYPE
    SYNTAX              		 INTEGER{
							low (0),
							high (1)
							}
    ACCESS          		 read-write
    STATUS               		mandatory
    DESCRIPTION	      		 "Priority"
               ::= { magnumPortQosEntry  2 }

    magnumTypeOfService	OBJECT-TYPE
    SYNTAX              		 DisplayString
    ACCESS          		 read-write
    STATUS               		mandatory
    DESCRIPTION	      		 "Type"
               ::= { magnumPortQosEntry  3 }

    magnumDeviceQosTable      OBJECT-TYPE
    SYNTAX                   SEQUENCE OF MagnumDeviceQosEntry
    ACCESS               not-accessible
    STATUS                   mandatory
    DESCRIPTION              "QOS"
            ::= { magnumPortManagerGroup 4 }

    magnumDeviceQosEntry      OBJECT-TYPE
    SYNTAX                   MagnumDeviceQosEntry
    ACCESS               not-accessible
    STATUS                   mandatory
    DESCRIPTION              "An entry in the magnumPortManagerTable."	
    INDEX                    {magnumDeviceQosIndex }
              ::= { magnumDeviceQosTable 1 }

    MagnumDeviceQosEntry ::= 
    SEQUENCE {
			magnumDeviceQosIndex 			INTEGER,
			magnumDefaultQos				INTEGER,
			magnumTagQos  		        	INTEGER,
			magnumIpQos					INTEGER
		}

    magnumDeviceQosIndex 		OBJECT-TYPE
    SYNTAX              		 INTEGER     (1..48)
    ACCESS          		 read-only
    STATUS               		mandatory
    DESCRIPTION	      		 "Index"
               ::= { magnumDeviceQosEntry  1 }

    magnumDefaultQos		OBJECT-TYPE
    SYNTAX              		 INTEGER{
							disable   (0),
							enable     (1)
							}
    ACCESS          		 read-write
    STATUS               		mandatory
    DESCRIPTION	      		 "Default"
               ::= { magnumDeviceQosEntry  2 }

    magnumTagQos 		OBJECT-TYPE
    SYNTAX              		 INTEGER{
							disable   (0),
							enable     (1)
							}

    ACCESS          		 read-write
    STATUS               		mandatory
    DESCRIPTION	      		 "TagQOS"
               ::= { magnumDeviceQosEntry  3 }

    magnumIpQos 		OBJECT-TYPE
    SYNTAX              		 INTEGER{
							disable   (0),
							enable     (1)
							}

    ACCESS          		 read-write
    STATUS               		mandatory
    DESCRIPTION	      		 "IpQOS"
               ::= { magnumDeviceQosEntry  4 }



	
  --  END Of PortManagerGroup  --  

  --  ConfigManagerGroup

    magnumConfigManagerGroup        OBJECT IDENTIFIER ::= { max25 20 }

    saveConfig    OBJECT-TYPE
    SYNTAX        INTEGER {
                              save(1),
			      saveDone(2)
                          }
    ACCESS        read-write
    STATUS        mandatory
    DESCRIPTION
		  "Whenever thie MIB object is set to 1, 
                   the MAC based VLAN configurations are saved."
    REFERENCE
		  "GarrettCom, Inc (Belden) Internal Documents"
	          ::= { magnumConfigManagerGroup 1 }

  --  ConfigManagerGroup
  --  IGMP Group


 magnumIGMPGroup 		OBJECT IDENTIFIER ::= { max25 21 }


	deviceIGMPState   	   OBJECT-TYPE
    SYNTAX                 INTEGER{
					                enable   (1),
					                disable  (2)
					              }
    ACCESS             read-write
    STATUS                 mandatory
    DESCRIPTION            "This object indicates whether IGMP feature 
                            is enabled or disabled."
           ::= { magnumIGMPGroup 1 }
           
    immediateLeave         OBJECT-TYPE
    SYNTAX                 INTEGER{
					                enable   (1),
					                disable  (2)
					              }
    ACCESS             read-write
    STATUS                 mandatory
    DESCRIPTION            "Enables/Disables IGMP immediate leave status."
           ::= { magnumIGMPGroup 2 }

    switchQuerier          OBJECT-TYPE
    SYNTAX                 INTEGER{
					                enable   (1),
					                disable  (2)
					              }
    ACCESS             read-write
    STATUS                 mandatory
    DESCRIPTION            "Enables/Disables the switch as an IGMP querier."
           ::= { magnumIGMPGroup 3 }

    queryInterval          OBJECT-TYPE
    SYNTAX                 INTEGER
    ACCESS             read-write
    STATUS                 mandatory
    DESCRIPTION            "Sets the query interval [60-270] for router ports."
           ::= { magnumIGMPGroup 4 }

    queryResponseInterval          OBJECT-TYPE
    SYNTAX                 INTEGER
    ACCESS             read-write
    STATUS                 mandatory
    DESCRIPTION            "Sets the query response interval for group membership ports"
           ::= { magnumIGMPGroup 5 }
    
	magnumIGMPGroupTable   OBJECT-TYPE
    SYNTAX                 SEQUENCE OF MagnumIGMPGroupEntry
    ACCESS             not-accessible
    STATUS                 mandatory
    DESCRIPTION            "This table shows the IGMP Multicast Groups."
           ::= { magnumIGMPGroup 6 }

	magnumIGMPGroupEntry   OBJECT-TYPE
    SYNTAX                 MagnumIGMPGroupEntry
    ACCESS             not-accessible
    STATUS                 mandatory
    DESCRIPTION	           "IGMP Group Entry"
    INDEX                  { igmpGroupIndex }

           ::= { magnumIGMPGroupTable 1 }

	MagnumIGMPGroupEntry ::= SEQUENCE 
                            {	
	                            igmpGroupIndex     INTEGER,
                                igmpGroupAddress   IpAddress,
                                igmpGroupPort      INTEGER,
                                igmpGroupTimer     INTEGER,
                                igmpGroupLeaveP    INTEGER
                            }

    igmpGroupIndex         OBJECT-TYPE
    SYNTAX                 INTEGER   (1..2000)
    ACCESS             read-only
    STATUS                 mandatory
    DESCRIPTION            "IGMP Group Index"
           ::= { magnumIGMPGroupEntry 1 }

    igmpGroupAddress       OBJECT-TYPE
    SYNTAX                 IpAddress
    ACCESS             read-only
    STATUS                 mandatory
    DESCRIPTION            "Group Multicast address"
           ::= { magnumIGMPGroupEntry 2 }

    igmpGroupPort          OBJECT-TYPE
    SYNTAX                 INTEGER
    ACCESS             read-only
    STATUS                 mandatory
    DESCRIPTION            "Group Port Member"
           ::= { magnumIGMPGroupEntry 3 }

    igmpGroupTimer         OBJECT-TYPE
    SYNTAX                 INTEGER
    ACCESS             read-only
    STATUS                 mandatory
    DESCRIPTION            "Group Timer"
           ::= { magnumIGMPGroupEntry 4 }

    igmpGroupLeaveP        OBJECT-TYPE
    SYNTAX                 INTEGER
    ACCESS             read-only
    STATUS                 mandatory
    DESCRIPTION            "Group Leave Pending"
           ::= { magnumIGMPGroupEntry 5 }

	magnumIGMPRouterTable  OBJECT-TYPE
    SYNTAX                 SEQUENCE OF MagnumIGMPRouterEntry
    ACCESS             not-accessible
    STATUS                 mandatory
    DESCRIPTION            "This table shows the IGMP Router entries."
           ::= { magnumIGMPGroup 7 }

	magnumIGMPRouterEntry   OBJECT-TYPE
    SYNTAX                 MagnumIGMPRouterEntry
    ACCESS             not-accessible
    STATUS                 mandatory
    DESCRIPTION	           "IGMP Router Entry"
    INDEX                  { igmpRouterIndex }

           ::= { magnumIGMPRouterTable 1 }

	MagnumIGMPRouterEntry ::= SEQUENCE 
                            {	
	                            igmpRouterIndex     INTEGER,
                                igmpRouterAddress   IpAddress,
                                igmpRouterPort      INTEGER,
                                igmpRouterTimer     INTEGER
                            }

    igmpRouterIndex        OBJECT-TYPE
    SYNTAX                 INTEGER         (1..2000)
    ACCESS             read-only
    STATUS                 mandatory
    DESCRIPTION            "IGMP Router Index"
           ::= { magnumIGMPRouterEntry 1 }

    igmpRouterAddress      OBJECT-TYPE
    SYNTAX                 IpAddress
    ACCESS             read-only
    STATUS                 mandatory
    DESCRIPTION            "Router IP address"
           ::= { magnumIGMPRouterEntry 2 }

    igmpRouterPort         OBJECT-TYPE
    SYNTAX                 INTEGER
    ACCESS             read-only
    STATUS                 mandatory
    DESCRIPTION            "Router Port Number"
           ::= { magnumIGMPRouterEntry 3 }

    igmpRouterTimer        OBJECT-TYPE
    SYNTAX                 INTEGER
    ACCESS             read-only
    STATUS                 mandatory
    DESCRIPTION            "Router Timer"
           ::= { magnumIGMPRouterEntry 4 }

	magnumIGMPPortTable  OBJECT-TYPE
    SYNTAX                 SEQUENCE OF MagnumIGMPPortEntry
    ACCESS             not-accessible
    STATUS                 mandatory
    DESCRIPTION            "This table shows the IGMP Port entries."
           ::= { magnumIGMPGroup 8 }

	magnumIGMPPortEntry   OBJECT-TYPE
    SYNTAX                 MagnumIGMPPortEntry
    ACCESS             not-accessible
    STATUS                 mandatory
    DESCRIPTION	           "IGMP Port Entry"
    INDEX                  { igmpPortIndex }

           ::= { magnumIGMPPortTable 1 }

	MagnumIGMPPortEntry ::= SEQUENCE 
                            {	
	                            igmpPortIndex     INTEGER,
                                igmpPortMode      INTEGER
                            }

    igmpPortIndex        OBJECT-TYPE
    SYNTAX                 INTEGER     (1..48)
    ACCESS             read-only
    STATUS                 mandatory
    DESCRIPTION            "IGMP Router Index"
           ::= { magnumIGMPPortEntry 1 }

    igmpPortMode         OBJECT-TYPE
    SYNTAX                 INTEGER{
    								unknown  (0),
					                auto     (1),
					                forward  (2),
					                block    (3)
					              }
    ACCESS             read-write
    STATUS                 mandatory
    DESCRIPTION            "Sets the IGMP port mode."
           ::= { magnumIGMPPortEntry 2 } 
    
                       
    unknownMcast	OBJECT-TYPE
    SYNTAX		INTEGER{
			       enable	(1),
			       disable	(2)
	      		}
    ACCESS		read-write
    STATUS		mandatory
    DESCRIPTION		"Enable/ Disables the multicasting of unknown streams."
              ::= { magnumIGMPGroup 9 }    
   
  --  END of IGMP Group
        sring    OBJECT IDENTIFIER ::= { max25 22 }

	  sringControl OBJECT-TYPE
	      SYNTAX  INTEGER {
			  disabled(0),
                    enabled(1),
                    learning(2)
                              }
	      ACCESS  read-write
	      STATUS  mandatory
	      DESCRIPTION
		      "sring Status and Control"
	      REFERENCE
		      "GarrettCom, Inc (Belden) Internal Documents"
	      ::= { sring 1 }
 

	  sringTable OBJECT-TYPE
	      SYNTAX  SEQUENCE OF SringEntry
	      ACCESS  not-accessible
	      STATUS  mandatory
	      DESCRIPTION
		      "A list of sring entries. The number of
		      entries is 12"
	      ::= { sring 2 }

	  sringEntry OBJECT-TYPE
	      SYNTAX  SringEntry
	      ACCESS  not-accessible
	      STATUS  mandatory
	      DESCRIPTION
		      "A port entry containing sring details
		       in the device."
	      INDEX   { sringIndex }
	      ::= { sringTable 1 }

	  SringEntry ::=
	      SEQUENCE {
		  sringIndex
		      INTEGER,
		  sringPort1
		      INTEGER,
		  sringPort2
		      INTEGER,
		  sringStatus
		      INTEGER 
	      }

	  sringIndex OBJECT-TYPE
	      SYNTAX  INTEGER (1..24)
	      ACCESS  read-only
	      STATUS  mandatory
	      DESCRIPTION
		      "A unique value for each entry.  "
	      ::= { sringEntry 1 }


	  sringPort1 OBJECT-TYPE
	      SYNTAX  INTEGER
	      ACCESS  read-write
	      STATUS  mandatory
	      DESCRIPTION
		      "First Port"
	      ::= { sringEntry 2 }

	  sringPort2 OBJECT-TYPE
	      SYNTAX  INTEGER
	      ACCESS  read-write
	      STATUS  mandatory
	      DESCRIPTION
		      "Second Port"
	      ::= { sringEntry 3 }

	  sringStatus OBJECT-TYPE
	      SYNTAX  INTEGER {
				 initial(0),
				 unknown(1),
				 closed(2),
				 open(3)
			      }
	      ACCESS  read-only
	      STATUS  mandatory
	      DESCRIPTION
		      "status of this port pair"
	      ::= { sringEntry 4 }
  --  END of SRING Group

        lll    OBJECT IDENTIFIER ::= { max25 23 }

	  lllControl OBJECT-TYPE
	      SYNTAX  INTEGER {
			  disabled(0),
              enabled(1)
                           }
	      ACCESS  read-write
	      STATUS  mandatory
	      DESCRIPTION
		      "lll Status and Control"
	      REFERENCE
		      "GarrettCom, Inc (Belden) Internal Documents"
	      ::= { lll 1 }
 
	  lllPortMap OBJECT-TYPE
	      SYNTAX  DisplayString
	      ACCESS  read-write
	      STATUS  mandatory
	      DESCRIPTION
		      "lll PortMap"
	      REFERENCE
		      "GarrettCom, Inc (Belden) Internal Documents"
	      ::= { lll 2 }
  --  END of LLL Group

        alarm    OBJECT IDENTIFIER ::= { max25 24 }

	  alarmControl OBJECT-TYPE
	      SYNTAX  INTEGER {
                    enabled(1),
                    disabled(2)
                              }
	      ACCESS  read-write
	      STATUS  mandatory
	      DESCRIPTION
		      "Alarm Status and Control"
	      REFERENCE
		      "GarrettCom, Inc (Belden) Internal Documents"
	      ::= { alarm 1 }

	  alarmWidth OBJECT-TYPE
	      SYNTAX  INTEGER (1..10)
	      ACCESS  read-write
	      STATUS  mandatory
	      DESCRIPTION
		      "Alarm Pulse Width"
	      REFERENCE
		      "GarrettCom, Inc (Belden) Internal Documents"
	      ::= { alarm 2 }
 

	  alarmTable OBJECT-TYPE
	      SYNTAX  SEQUENCE OF AlarmEntry
	      ACCESS  not-accessible
	      STATUS  mandatory
	      DESCRIPTION
		      "A list of alarm entries. The number of
		      entries is 9"
	      ::= { alarm 3 }

	  alarmEntry OBJECT-TYPE
	      SYNTAX  AlarmEntry
	      ACCESS  not-accessible
	      STATUS  mandatory
	      DESCRIPTION
		      "Anentry containing alarm details
		       in the device."
	      INDEX   { alarmIndex }
	      ::= { alarmTable 1 }

	  AlarmEntry ::=
	      SEQUENCE {
		  alarmIndex
		      INTEGER,
		  alarmEvent
		      INTEGER,
		  alarmType
		      INTEGER,
		  alarmDesc
		      DisplayString,		      
		  alarmStatus
		      INTEGER,
		  alarmFlag
		      INTEGER 
	      }

	  alarmIndex OBJECT-TYPE
	      SYNTAX  INTEGER (0..50)
	      ACCESS  read-only
	      STATUS  mandatory
	      DESCRIPTION
		      "A unique value for each entry.  "
	      ::= { alarmEntry 1 }


	  alarmEvent OBJECT-TYPE
	      SYNTAX  INTEGER
	      ACCESS  read-only
	      STATUS  mandatory
	      DESCRIPTION
		      "Event ID"
	      ::= { alarmEntry 2 }

	  alarmType OBJECT-TYPE
	      SYNTAX  INTEGER {
                    sustained(1),
                    momentary(2)
                          }
	      ACCESS  read-only
	      STATUS  mandatory
	      DESCRIPTION
		      "Type of Alarm"
	      ::= { alarmEntry 3 }
	      
	  alarmDesc OBJECT-TYPE
	      SYNTAX  DisplayString
	      ACCESS  read-only
	      STATUS  mandatory
	      DESCRIPTION
		      "Alarm Description"
	      ::= { alarmEntry 4 }	      

	  alarmStatus OBJECT-TYPE
	      SYNTAX  INTEGER {
				 enabled(1),
				 disabled(2)
			      }
	      ACCESS  read-write
	      STATUS  mandatory
	      DESCRIPTION
		      "status of this event"
	      ::= { alarmEntry 5 }
	  alarmFlag OBJECT-TYPE
	      SYNTAX  INTEGER {
				 set(1),
				 reset(2)
			      }
	      ACCESS  read-write
	      STATUS  mandatory
	      DESCRIPTION
		      "historical status of the event"
	      ::= { alarmEntry 6 }

       dualhome    OBJECT IDENTIFIER ::= { max25 25 }

	  dhControl OBJECT-TYPE
	      SYNTAX  INTEGER {
			  disabled(0),
              enabled(1),
              delete(2)
                           }
	      ACCESS  read-write
	      STATUS  mandatory
	      DESCRIPTION
		      "dh Status and Control"
	      REFERENCE
		      "GarrettCom, Inc (Belden) Internal Documents"
	      ::= { dualhome 1 }
 
	  dhMode OBJECT-TYPE
	      SYNTAX  INTEGER {
			  normal(0),
              primarySecondary(1)
                           }
	      ACCESS  read-write
	      STATUS  mandatory
	      DESCRIPTION
		      "dh mode"
	      REFERENCE
		      "GarrettCom, Inc (Belden) Internal Documents"
	      ::= { dualhome 2 }
 
	  dhActive OBJECT-TYPE
	      SYNTAX  INTEGER
	      ACCESS  read-only
	      STATUS  mandatory
	      DESCRIPTION
		      "dh Active Port"
	      REFERENCE
		      "GarrettCom, Inc (Belden) Internal Documents"
	      ::= { dualhome 3 }
 
	  dhPort1 OBJECT-TYPE
	      SYNTAX  INTEGER 
	      ACCESS  read-write
	      STATUS  mandatory
	      DESCRIPTION
		      "dh Port1"
	      REFERENCE
		      "GarrettCom, Inc (Belden) Internal Documents"
	      ::= { dualhome 4 }
 
	  dhPort2 OBJECT-TYPE
	      SYNTAX  INTEGER
	      ACCESS  read-write
	      STATUS  mandatory
	      DESCRIPTION
		      "dh Port2"
	      REFERENCE
		      "GarrettCom, Inc (Belden) Internal Documents"
	      ::= { dualhome 5 }
 

  --  END of DH Group	      
	      
      userAuthFail    OBJECT IDENTIFIER ::= { mx-events 1 }

	  mode OBJECT-TYPE
		SYNTAX  INTEGER {
		        console(1),
		        telnet(2),
		        web(3)
		                  }
		ACCESS  read-only
		STATUS  mandatory
		DESCRIPTION
		  "Access Mode that failed"
		REFERENCE
		  "GarrettCom, Inc (Belden) Internal Documents"
		::= { userAuthFail 1 }

		userIpAddress 		OBJECT-TYPE
	    SYNTAX              IpAddress
	    ACCESS          read-only
	    STATUS              mandatory
		DESCRIPTION
		  "Access Mode that failed"
		REFERENCE
		  "GarrettCom, Inc (Belden) Internal Documents"
	    ::= { userAuthFail 2 }
	    
	    powerAlarm    OBJECT IDENTIFIER ::= { mx-events 2 }

	  powerSupplyFailed OBJECT-TYPE
		SYNTAX  INTEGER {
		        powerSupplyA(1),
		        powerSupplyB(2)
		                  }
		ACCESS  read-only
		STATUS  mandatory
		DESCRIPTION
		  "The Power Supply that is failed"
		REFERENCE
		  "GarrettCom, Inc (Belden) Internal Documents"
		::= { powerAlarm 1 }

	   fanAlarm     OBJECT IDENTIFIER ::= { mx-events 3 }

	  fanNumber OBJECT-TYPE
		SYNTAX  INTEGER
		ACCESS  read-only
		STATUS  mandatory
		DESCRIPTION
		  "Fan Number being reported"
		REFERENCE
		  "GarrettCom, Inc (Belden) Internal Documents"
		::= { fanAlarm 1 }

		fanStatus		OBJECT-TYPE
	    SYNTAX  INTEGER {
		        on(1),
		        off(2),
		        faulted(3)
		                  }
	    ACCESS          read-only
	    STATUS              mandatory
		DESCRIPTION
		  "Fan Status Reported"
		REFERENCE
		  "GarrettCom, Inc (Belden) Internal Documents"
	    ::= { fanAlarm 2 }
	    
	      	      
  --  -EVENTS
    m6kIntruderTrap TRAP-TYPE
    ENTERPRISE mx-events
    DESCRIPTION "Sent out if there is an intruder 
                 mac address being blocked by port 
                 security module"
	::= 1
    m6kSringOpenTrap TRAP-TYPE
    ENTERPRISE mx-events
    DESCRIPTION "Sent out when the SRING changes 
                 from CLOSED to OPEN state" 
	::= 2
	
    m6kSringClosedTrap TRAP-TYPE
    ENTERPRISE mx-events
    DESCRIPTION "Sent out when the SRING changes 
                 from OPEN to CLOSED state" 
	::= 3
    m6kLLLTrap TRAP-TYPE
    ENTERPRISE mx-events
    DESCRIPTION "Sent out when the Link Loss Learn 
                 system is triggered" 
	::= 4
    m6kPMPTrap TRAP-TYPE
    ENTERPRISE mx-events
    DESCRIPTION "Sent out when the Point to Multipoint
                 system is triggered" 
	::= 5	
    m6kUserAuthFailTrap TRAP-TYPE
    ENTERPRISE mx-events
    DESCRIPTION "Sent out when a login fails" 
	::= 6
	
    m6kPowerAlarmTrap TRAP-TYPE
    ENTERPRISE mx-events
    DESCRIPTION "Sent out when one of the dual power supplies fail" 
	::= 7
	
	m6kSTPEnabledTrap TRAP-TYPE
    ENTERPRISE mx-events
    DESCRIPTION "Sent out when STP is Enabled." 
	::= 8
	
	m6kRSTPEnabledTrap TRAP-TYPE
    ENTERPRISE mx-events
    DESCRIPTION "Sent out when RSTP is Enabled." 
	::= 9
	
	m6kSTPDisabledTrap TRAP-TYPE
    ENTERPRISE mx-events
    DESCRIPTION "Sent out when STP is Disabled." 
	::= 10
	
	m6kRSTPDisabledTrap TRAP-TYPE
    ENTERPRISE mx-events
    DESCRIPTION "Sent out when RSTP is Disabled." 
	::= 11
	
	m6kFanAlarmTrap TRAP-TYPE
    ENTERPRISE mx-events
    DESCRIPTION "Sent out when Fan Status Changes." 
	::= 12
	
       END

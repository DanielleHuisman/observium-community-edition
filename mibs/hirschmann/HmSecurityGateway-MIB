--
-- Copyright 2003-2006 Innominate Security Technologies AG
-- All Rights Reserved
--
-- hirschmann Eagle 3.1.1-pre07
--
-- DO NOT MODIFY THIS FILE. Generated from master. Fri Feb  3 15:12:21 CET 2006
--

HmSecurityGateway-MIB DEFINITIONS ::= BEGIN

IMPORTS
  enterprises
    FROM RFC1155-SMI
  OBJECT-TYPE
    FROM RFC-1212
  RowStatus, TruthValue, MacAddress
    FROM SNMPv2-TC
  DisplayString
    FROM RFC1213-MIB
  TRAP-TYPE
    FROM RFC-1215;

  hirschmann       	OBJECT IDENTIFIER ::= { enterprises 248 }
  hmSecurityGateway	OBJECT IDENTIFIER ::= { hirschmann  51 }




  hmSecVPN        OBJECT IDENTIFIER ::= { hmSecurityGateway 1 }
  hmSecFirewall   OBJECT IDENTIFIER ::= { hmSecurityGateway 2 }
  hmSecNetwork    OBJECT IDENTIFIER ::= { hmSecurityGateway 3 }
  hmSecSystem     OBJECT IDENTIFIER ::= { hmSecurityGateway 4 }
  hmSecSNMP       OBJECT IDENTIFIER ::= { hmSecurityGateway 5 }
  hmSecNTP        OBJECT IDENTIFIER ::= { hmSecurityGateway 6 }
  hmSecUpdate     OBJECT IDENTIFIER ::= { hmSecurityGateway 7 }
  hmSecRedundancy OBJECT IDENTIFIER ::= { hmSecurityGateway 9 }
  hmSecInfo       OBJECT IDENTIFIER ::= { hmSecurityGateway 10 }
  hmSecLogging    OBJECT IDENTIFIER ::= { hmSecurityGateway 11 }
  hmSecContFilt   OBJECT IDENTIFIER ::= { hmSecurityGateway 12 }
  hmSecBlade      OBJECT IDENTIFIER ::= { hmSecurityGateway 13 }
  hmSecProfile    OBJECT IDENTIFIER ::= { hmSecurityGateway 14 }

--
-- IPsec: Local Certificate
--

 hmSecVPNMachine OBJECT IDENTIFIER ::= { hmSecVPN 1 }

 hmSecVPNMachineCert OBJECT-TYPE
   SYNTAX DisplayString
   ACCESS read-write
   STATUS mandatory
   DESCRIPTION
     "Machine certificate and private key of this device."
 ::= { hmSecVPNMachine 1 }

 hmSecVPNMachinePrivate OBJECT-TYPE
   SYNTAX DisplayString
   ACCESS read-write
   STATUS mandatory
   DESCRIPTION
     "Private key"
 ::= { hmSecVPNMachine 2 }


--
-- IPsec: Connection
--

 hmSecVPNConnectionTable OBJECT-TYPE
    SYNTAX SEQUENCE OF HmSecVPNConnectionEntry
    ACCESS not-accessible
    STATUS mandatory
    DESCRIPTION
    "A table containing the configuration of
    the local device's VPN connections."
 ::= { hmSecVPN 2 }

 hmSecVPNConnectionEntry OBJECT-TYPE
    SYNTAX HmSecVPNConnectionEntry
    ACCESS not-accessible
    STATUS mandatory
    DESCRIPTION
       "Configuration of a single VPN connection."
    INDEX { hmSecVPNconIndex }
 ::= { hmSecVPNConnectionTable 1 }

 HmSecVPNConnectionEntry ::= SEQUENCE {
    hmSecVPNconIndex    INTEGER,
    hmSecVPNconName	 DisplayString,
    hmSecVPNconEnabled  INTEGER,
    hmSecVPNremGW	 DisplayString,
    hmSecVPNconType	 INTEGER,
    hmSecVPNlocalNet    IpAddress,
    hmSecVPNlocalMask   IpAddress,
    hmSecVPNremoteNet   IpAddress,
    hmSecVPNremoteMask  IpAddress,
    hmSecVPNauthType    INTEGER,
    hmSecVPNpsk         DisplayString,
    hmSecVPNx509        DisplayString,
    hmSecVPNikeDH       INTEGER,
    hmSecVPNikeHash     INTEGER,
    hmSecVPNipsecHash   INTEGER,
    hmSecVPNikeAlg      INTEGER,
    hmSecVPNipsecAlg    INTEGER,
    hmSecVPNpfs         INTEGER,
    hmSecVPNconStartUp  INTEGER,
    hmSecVPNvirtIPMethod INTEGER,
    hmSecVPNvirtIP      IpAddress,
    hmSecVPNFWLogDefIn  INTEGER,
    hmSecVPNFWLogDefOut  INTEGER,
    hmSecVPNProtoAH     INTEGER,
    hmSecVPNProtoESP    INTEGER,
    hmSecVPNComp        INTEGER,
    hmSecVPNLocalIDMode INTEGER,
    hmSecVPNLocalID       DisplayString,
    hmSecVPNRemoteIDMode  INTEGER,
    hmSecVPNRemoteID      DisplayString,
    hmSecVPNIkeLifetime   INTEGER,
    hmSecVPNIpsecLifetime INTEGER,
    hmSecVPNRekeyMargin   INTEGER,
    hmSecVPNRekeyFuzz     INTEGER,
    hmSecVPNKeyingTries   INTEGER,
    hmSecVPNRekey         INTEGER,
    hmSecVPNDPDAction     INTEGER,
    hmSecVPNDPDDelay      INTEGER,
    hmSecVPNDPDTimeout    INTEGER,
    hmSecVPNRowStatus   RowStatus,
    hmSecVPNAggressive    INTEGER,
    hmSecVPNlocal          DisplayString,
    hmSecVPNremote         DisplayString
 }

   hmSecVPNconIndex OBJECT-TYPE
      SYNTAX INTEGER (1..250)
      ACCESS not-accessible
      STATUS mandatory
      DESCRIPTION
         "Index to identify the connection."
   ::= { hmSecVPNConnectionEntry 1 }

   hmSecVPNconName OBJECT-TYPE
      SYNTAX DisplayString
      ACCESS read-write
      STATUS mandatory
      DESCRIPTION
         "Descriptive name of the connection."
   ::= { hmSecVPNConnectionEntry 2 }

   hmSecVPNconEnabled OBJECT-TYPE
      SYNTAX INTEGER {
                        enabled(1),
                        disabled(2)
                     }
      ACCESS read-write
      STATUS mandatory
      DESCRIPTION
         "Is the connection enabled: yes / no ."
   ::= { hmSecVPNConnectionEntry 3 }

   hmSecVPNremGW OBJECT-TYPE
      SYNTAX DisplayString
      ACCESS read-write
      STATUS mandatory
      DESCRIPTION
         "Remote VPN gateway."
   ::= { hmSecVPNConnectionEntry 4 }

   hmSecVPNconType OBJECT-TYPE
      SYNTAX INTEGER {
			transport(1),
			tunnel(2),
			l2tp-w2k(3),
			l2tp-ssh(4)
		     }
      ACCESS read-write
      STATUS mandatory
      DESCRIPTION
         "Type of VPN connection: transport / tunnel / l2tp-w2k / l2tp-ssh"
   ::= { hmSecVPNConnectionEntry 5 }

   hmSecVPNlocalNet OBJECT-TYPE
      SYNTAX IpAddress
      ACCESS read-write
      STATUS deprecated
      DESCRIPTION
         "Local net address for VPN connection in tunnel mode."
   ::= { hmSecVPNConnectionEntry 6 }


   hmSecVPNlocalMask OBJECT-TYPE
      SYNTAX IpAddress
      ACCESS read-write
      STATUS deprecated
      DESCRIPTION
        "Local netmask for VPN connection in tunnel mode."
   ::= { hmSecVPNConnectionEntry 7 }

   hmSecVPNremoteNet OBJECT-TYPE
      SYNTAX IpAddress
      ACCESS read-write
      STATUS deprecated
      DESCRIPTION
        "Remote net address for VPN connection in tunnel mode."
   ::= { hmSecVPNConnectionEntry 8 }

   hmSecVPNremoteMask OBJECT-TYPE
      SYNTAX IpAddress
      ACCESS read-write
      STATUS deprecated
      DESCRIPTION
        "Remote netmask for VPN connection in tunnel mode."
   ::= { hmSecVPNConnectionEntry 9 }

   hmSecVPNauthType OBJECT-TYPE
     SYNTAX INTEGER {
			psk(1),
			x509(2)
		    }
     ACCESS read-write
     STATUS mandatory
     DESCRIPTION
       "Authentification mode of the VPN connection: psk / x509"
   ::= { hmSecVPNConnectionEntry 10 }

    hmSecVPNpsk OBJECT-TYPE
      SYNTAX DisplayString
      ACCESS read-write
      STATUS mandatory
      DESCRIPTION
       "Pre Shared Secret"
    ::= { hmSecVPNConnectionEntry 11 }

     hmSecVPNx509 OBJECT-TYPE
      SYNTAX DisplayString
      ACCESS read-write
      STATUS mandatory
      DESCRIPTION
       "X.509 certificate"
    ::= { hmSecVPNConnectionEntry 12 }

    hmSecVPNikeDH OBJECT-TYPE
     SYNTAX INTEGER{
                      all(1),
                      modp1024(2),
                      modp1536(3),
                      modp2048(4),
                      modp3072(5),
                      modp4096(6)
                   }
     ACCESS read-write
     STATUS mandatory
     DESCRIPTION
        "IKE DH algorithm."
     ::= { hmSecVPNConnectionEntry 13 }

    hmSecVPNikeHash OBJECT-TYPE
      SYNTAX INTEGER {
			all(1),
			md5(2),
			sha1(3)
		     }
      ACCESS read-write
      STATUS mandatory
      DESCRIPTION
         "IKE hash algorithm: all / md5 / sha1"
    ::= { hmSecVPNConnectionEntry 14 }

    hmSecVPNipsecHash OBJECT-TYPE
       SYNTAX INTEGER {
			all(1),
			md5(2),
			sha1(3)
		     }
       ACCESS read-write
       STATUS mandatory
       DESCRIPTION
         "ipsec hash algorithm: all / md5 / sha1"
    ::= { hmSecVPNConnectionEntry 15 }

     hmSecVPNikeAlg OBJECT-TYPE
        SYNTAX INTEGER {
			des(1),
			tripledes168(2),
			aes128(3),
			aes192(4),
			aes256(5)
		     }
        ACCESS read-write
        STATUS mandatory
        DESCRIPTION
          "IKE encryption algorithm: des / 3des168 / aes128 / aes192 / aes256"
    ::= { hmSecVPNConnectionEntry 16 }

     hmSecVPNipsecAlg OBJECT-TYPE
         SYNTAX INTEGER {
			des(1),
			tripledes168(2),
			aes128(3),
			aes192(4),
			aes256(5),
			null(6)
		     }
         ACCESS read-write
         STATUS mandatory
         DESCRIPTION
           "ipsec encryption algorithm: des/ 3des168 / aes128 / aes192 / aes256 / null"
    ::= { hmSecVPNConnectionEntry 17 }

    hmSecVPNpfs OBJECT-TYPE
         SYNTAX INTEGER {
			no(1),
			all(2),
			modp1024(3),
			modp1536(4),
			modp2048(5),
			modp3072(6),
                        modp4096(7)
		     }
         ACCESS read-write
         STATUS mandatory
         DESCRIPTION
           "ipsec perfect forward secrecy: no / all / modp1024 / modp1536 / modp2048 / modp3072 / modp4096"
    ::= { hmSecVPNConnectionEntry 18 }

    hmSecVPNconStartUp OBJECT-TYPE
      SYNTAX INTEGER {
			initiate(1),
			waitForRemote(2)
		     }
      ACCESS read-write
      STATUS mandatory
      DESCRIPTION
        "Recognize the startup of the VPN connection or wait
         for connection startup of the  remote gateway: yes / no ."
    ::= {  hmSecVPNConnectionEntry 19 }

   hmSecVPNvirtIPMethod OBJECT-TYPE
       SYNTAX INTEGER{
              static(1),
              dhcp-over-ipsec(2)
              }
       ACCESS read-write
       STATUS mandatory
       DESCRIPTION
         "This option isn't implemented yet."
     ::= {  hmSecVPNConnectionEntry 20 }

    hmSecVPNvirtIP OBJECT-TYPE
       SYNTAX IpAddress
       ACCESS read-write
       STATUS mandatory
       DESCRIPTION
         "Virtual IP to use"
     ::= {  hmSecVPNConnectionEntry 21 }

     hmSecVPNFWLogDefIn OBJECT-TYPE
       SYNTAX INTEGER{
                      yes(1),
    		      no(2)
 	             }
	ACCESS read-write
	STATUS mandatory
        DESCRIPTION
	   "Log entries for undefined incoming connection attemps ?"
     ::= { hmSecVPNConnectionEntry 22 }

     hmSecVPNFWLogDefOut OBJECT-TYPE
       SYNTAX INTEGER{
                      yes(1),
    		      no(2)
 	             }
	ACCESS read-write
	STATUS mandatory
        DESCRIPTION
	   "Log entries for undefined outgoing connection attemps ?"
     ::= { hmSecVPNConnectionEntry 23 }


     hmSecVPNProtoAH OBJECT-TYPE
       SYNTAX INTEGER{
                      yes(1),
                      no(2)
                     }
       ACCESS read-write
       STATUS mandatory
       DESCRIPTION
        "Use the AH protocoll. Only 'no' is supported."
     ::= { hmSecVPNConnectionEntry 26 }

     hmSecVPNProtoESP OBJECT-TYPE
       SYNTAX INTEGER{
                      yes(1),
                      no(2)
                     }
       ACCESS read-write
       STATUS mandatory
       DESCRIPTION
        "Use the ESP protocoll. Only 'yes' is supported."
     ::= { hmSecVPNConnectionEntry 27 }

     hmSecVPNComp OBJECT-TYPE
       SYNTAX INTEGER{
                      yes(1),
                      no(2)
                     }
       ACCESS read-write
       STATUS mandatory
       DESCRIPTION
        "Use IPsec compression. Only 'no' is supported."
     ::= { hmSecVPNConnectionEntry 28 }

     hmSecVPNLocalIDMode OBJECT-TYPE
      SYNTAX INTEGER{
                      auto(1),
                      freeswan(2)
                     }
      ACCESS read-write
      STATUS mandatory
      DESCRIPTION
       "Mode for local ID. This option isn't implemented yet."
     ::= { hmSecVPNConnectionEntry 29 }

     hmSecVPNLocalID OBJECT-TYPE
      SYNTAX DisplayString
      ACCESS read-write
      STATUS mandatory
      DESCRIPTION
         "Local ID."
     ::= { hmSecVPNConnectionEntry 30 }

     hmSecVPNRemoteIDMode OBJECT-TYPE
      SYNTAX INTEGER{
                      auto(1),
                      freeswan(2)
                     }
      ACCESS read-write
      STATUS mandatory
      DESCRIPTION
       "Mode for remote ID. This option isn't implemented yet."
     ::= { hmSecVPNConnectionEntry 31 }

     hmSecVPNRemoteID OBJECT-TYPE
      SYNTAX DisplayString
      ACCESS read-write
      STATUS mandatory
      DESCRIPTION
         "Local ID."
     ::= { hmSecVPNConnectionEntry 32 }

    hmSecVPNIkeLifetime OBJECT-TYPE
     SYNTAX INTEGER
     ACCESS read-write
     STATUS mandatory
     DESCRIPTION
       "ISAKMP SA  lifetime (seconds)."
    ::= { hmSecVPNConnectionEntry 33 }

    hmSecVPNIpsecLifetime OBJECT-TYPE
     SYNTAX INTEGER
     ACCESS read-write
     STATUS mandatory
     DESCRIPTION
       "IPSec SA lifetime (seconds)."
    ::= { hmSecVPNConnectionEntry 34 }

    hmSecVPNRekeyMargin OBJECT-TYPE
     SYNTAX INTEGER
     ACCESS read-write
     STATUS mandatory
     DESCRIPTION
       "Rekey Margin (seconds)."
    ::= { hmSecVPNConnectionEntry 35 }

    hmSecVPNRekeyFuzz OBJECT-TYPE
     SYNTAX INTEGER
     ACCESS read-write
     STATUS mandatory
     DESCRIPTION
       "Rekey fuzz (in percent)."
    ::= { hmSecVPNConnectionEntry 36 }

    hmSecVPNKeyingTries OBJECT-TYPE
     SYNTAX INTEGER
     ACCESS read-write
     STATUS mandatory
     DESCRIPTION
       "Rekey fuzz (in percent)."
    ::= { hmSecVPNConnectionEntry 37 }

    hmSecVPNRekey OBJECT-TYPE
     SYNTAX INTEGER{
                     yes(1),
                     no(2)
                    }
     ACCESS read-write
     STATUS mandatory
     DESCRIPTION
      "Renegotiate connection after the keys have expired? Must be set to
      'no' on both end to be effective."
    ::= { hmSecVPNConnectionEntry 38 }

    hmSecVPNDPDAction OBJECT-TYPE
      SYNTAX INTEGER{
                      hold(1),
                      clear(2)
                    }
      ACCESS read-write
      STATUS mandatory
      DESCRIPTION
        "What to do in case DPD found out that the connection is dead:
        'hold': renegotiate connection.
        'clear': clear connection and don't renegotiate."
    ::= { hmSecVPNConnectionEntry 39 }

    hmSecVPNDPDDelay OBJECT-TYPE
      SYNTAX INTEGER
      ACCESS read-write
      STATUS mandatory
      DESCRIPTION
        "Interval in seconds to wait before sending DPD requests when
        the remote end didn't send data. The default value is 30."
    ::= { hmSecVPNConnectionEntry 40 }

    hmSecVPNDPDTimeout OBJECT-TYPE
      SYNTAX INTEGER
      ACCESS read-write
      STATUS mandatory
      DESCRIPTION
        "Interval in seconds before declaring the remote end as dead after
        sending the first DPD request. The default value is 120."
    ::= { hmSecVPNConnectionEntry 41 }

    hmSecVPNRowStatus OBJECT-TYPE
      SYNTAX RowStatus
      ACCESS read-write
      STATUS mandatory
      DESCRIPTION
        "RowStatus"
    ::= { hmSecVPNConnectionEntry 42 }

    hmSecVPNAggressive OBJECT-TYPE
      SYNTAX INTEGER{
                      no(1),
                      yes(2)
                    }
      ACCESS read-write
      STATUS mandatory
      DESCRIPTION
        "Wether to use/accept aggressive mode VPn connections for this one."
    ::= { hmSecVPNConnectionEntry 43 }

   hmSecVPNlocal OBJECT-TYPE
      SYNTAX DisplayString
      ACCESS read-write
      STATUS mandatory
      DESCRIPTION
         "Local network for VPN connection in tunnel mode in CIDR notation."
   ::= { hmSecVPNConnectionEntry 44 }
 
   hmSecVPNremote OBJECT-TYPE
      SYNTAX DisplayString
      ACCESS read-write
      STATUS mandatory
      DESCRIPTION
         "Remote network for VPN connection in tunnel mode in CIDR notation."
   ::= { hmSecVPNConnectionEntry 45 }
 
---
--- IPsec: Incoming Firewall
---

  hmSecVPNFW OBJECT IDENTIFIER ::= { hmSecVPN 3 }

  hmSecVPNFWINTable OBJECT-TYPE
    SYNTAX SEQUENCE OF HmSecVPNFWINEntry
    ACCESS not-accessible
    STATUS mandatory
    DESCRIPTION
      "Table of firewall rules for incoming packets."
    ::= { hmSecVPNFW 1 }

    hmSecVPNFWINEntry OBJECT-TYPE
        SYNTAX HmSecVPNFWINEntry
        ACCESS not-accessible
        STATUS mandatory
        DESCRIPTION
            "An entry containing data of a single rule."
        INDEX { hmSecVPNFWINconIndex, hmSecVPNFWINruleIndex }
    ::= { hmSecVPNFWINTable 1 }

    HmSecVPNFWINEntry ::= SEQUENCE{
      hmSecVPNFWINconIndex        INTEGER,
      hmSecVPNFWINruleIndex       INTEGER,
      hmSecVPNFWINsourceIP        DisplayString,
      hmSecVPNFWINdestinationIP   DisplayString,
      hmSecVPNFWINsport           DisplayString,
      hmSecVPNFWINdport           DisplayString,
      hmSecVPNFWINtarget          INTEGER,
      hmSecVPNFWINproto           INTEGER,
      hmSecVPNFWINlog             INTEGER,
      hmSecVPNFWINRowStatus       RowStatus,
      hmSecVPNFWINcomment         DisplayString
    }

    hmSecVPNFWINconIndex OBJECT-TYPE
      SYNTAX   INTEGER (1..250)
      ACCESS   not-accessible
      STATUS   mandatory
      DESCRIPTION
        "Index to identify the rule."
    ::= { hmSecVPNFWINEntry 1 }

    hmSecVPNFWINruleIndex OBJECT-TYPE
      SYNTAX   INTEGER (1..250)
      ACCESS   not-accessible
      STATUS   mandatory
      DESCRIPTION
        "Index to identify the rule."
    ::= { hmSecVPNFWINEntry 2 }

    hmSecVPNFWINsourceIP OBJECT-TYPE
      SYNTAX DisplayString
      ACCESS read-write
      STATUS mandatory
      DESCRIPTION
         "The rule's source IP address"
     ::= { hmSecVPNFWINEntry 3 }

     hmSecVPNFWINdestinationIP OBJECT-TYPE
      SYNTAX DisplayString
      ACCESS read-write
      STATUS mandatory
      DESCRIPTION
         "The rule's source IP address"
     ::= { hmSecVPNFWINEntry 4 }

     hmSecVPNFWINsport OBJECT-TYPE
      SYNTAX DisplayString
      ACCESS read-write
      STATUS mandatory
      DESCRIPTION
         "The rule's source port"
     ::= { hmSecVPNFWINEntry 5 }

      hmSecVPNFWINdport OBJECT-TYPE
      SYNTAX DisplayString
      ACCESS read-write
      STATUS mandatory
      DESCRIPTION
         "The rule's destination port"
     ::= { hmSecVPNFWINEntry 6 }

     hmSecVPNFWINtarget OBJECT-TYPE
       SYNTAX INTEGER {
                        accept(1),
                        reject(2),
                        drop(3)
                      }
       ACCESS read-write
       STATUS mandatory
       DESCRIPTION
          "The rule's target"
     ::= { hmSecVPNFWINEntry 7 }


     hmSecVPNFWINproto OBJECT-TYPE
      SYNTAX INTEGER {
                        tcp(1),
                        udp(2),
                        icmp(3),
                        all(4)
                      }
      ACCESS read-write
      STATUS mandatory
       DESCRIPTION
        "The rule's transport protocol"
     ::= { hmSecVPNFWINEntry 8 }

      hmSecVPNFWINlog OBJECT-TYPE
        SYNTAX INTEGER {
                         yes(1),
                         no(2)
                       }
        ACCESS read-write
        STATUS mandatory
        DESCRIPTION
          "Log packets matching this rule."
        ::= { hmSecVPNFWINEntry 9 }

      hmSecVPNFWINRowStatus OBJECT-TYPE
        SYNTAX RowStatus
        ACCESS read-write
        STATUS mandatory
        DESCRIPTION
           "RowStatus"
      ::= { hmSecVPNFWINEntry 10 }

      hmSecVPNFWINcomment OBJECT-TYPE
        SYNTAX DisplayString
        ACCESS read-write
        STATUS mandatory
        DESCRIPTION
          "Commentary or name for this rule."
        ::= { hmSecVPNFWINEntry 11 }


--
-- IPsec: Outgoing Firewall
--

  hmSecVPNFWOUTTable OBJECT-TYPE
    SYNTAX SEQUENCE OF HmSecVPNFWOUTEntry
    ACCESS not-accessible
    STATUS mandatory
    DESCRIPTION
      "Table of firewall rules for outgoing packets."
    ::= { hmSecVPNFW 2 }

    hmSecVPNFWOUTEntry OBJECT-TYPE
        SYNTAX HmSecVPNFWOUTEntry
        ACCESS not-accessible
        STATUS mandatory
        DESCRIPTION
            "An entry containing data of a single rule."
        INDEX { hmSecVPNFWOUTconIndex, hmSecVPNFWOUTruleIndex }
    ::= { hmSecVPNFWOUTTable 1 }

    HmSecVPNFWOUTEntry ::= SEQUENCE{
      hmSecVPNFWOUTconIndex        INTEGER,
      hmSecVPNFWOUTruleIndex       INTEGER,
      hmSecVPNFWOUTsourceIP        DisplayString,
      hmSecVPNFWOUTdestinationIP   DisplayString,
      hmSecVPNFWOUTsport           DisplayString,
      hmSecVPNFWOUTdport           DisplayString,
      hmSecVPNFWOUTtarget          INTEGER,
      hmSecVPNFWOUTproto           INTEGER,
      hmSecVPNFWOUTlog             INTEGER,
      hmSecVPNFWOUTRowStatus       RowStatus,
      hmSecVPNFWOUTcomment         DisplayString
    }

    hmSecVPNFWOUTconIndex OBJECT-TYPE
      SYNTAX   INTEGER (1..250)
      ACCESS   not-accessible
      STATUS   mandatory
      DESCRIPTION
        "Index to identify the rule."
    ::= { hmSecVPNFWOUTEntry 1 }

    hmSecVPNFWOUTruleIndex OBJECT-TYPE
      SYNTAX   INTEGER (1..250)
      ACCESS   not-accessible
      STATUS   mandatory
      DESCRIPTION
        "Index to identify the rule."
    ::= { hmSecVPNFWOUTEntry 2 }

    hmSecVPNFWOUTsourceIP OBJECT-TYPE
      SYNTAX DisplayString
      ACCESS read-write
      STATUS mandatory
      DESCRIPTION
         "The rule's source IP address"
     ::= { hmSecVPNFWOUTEntry 3 }

     hmSecVPNFWOUTdestinationIP OBJECT-TYPE
      SYNTAX DisplayString
      ACCESS read-write
      STATUS mandatory
      DESCRIPTION
         "The rule's source IP address"
     ::= { hmSecVPNFWOUTEntry 4 }

     hmSecVPNFWOUTsport OBJECT-TYPE
      SYNTAX DisplayString
      ACCESS read-write
      STATUS mandatory
      DESCRIPTION
         "The rule's source port"
     ::= { hmSecVPNFWOUTEntry 5 }

      hmSecVPNFWOUTdport OBJECT-TYPE
      SYNTAX DisplayString
      ACCESS read-write
      STATUS mandatory
      DESCRIPTION
         "The rule's destination port"
     ::= { hmSecVPNFWOUTEntry 6 }

     hmSecVPNFWOUTtarget OBJECT-TYPE
       SYNTAX INTEGER {
                        accept(1),
                        reject(2),
                        drop(3)
                      }
       ACCESS read-write
       STATUS mandatory
       DESCRIPTION
          "The rule's target"
     ::= { hmSecVPNFWOUTEntry 7 }


     hmSecVPNFWOUTproto OBJECT-TYPE
      SYNTAX INTEGER {
                        tcp(1),
                        udp(2),
                        icmp(3),
                        all(4)
                      }
      ACCESS read-write
      STATUS mandatory
       DESCRIPTION
        "The rule's transport protocol"
     ::= { hmSecVPNFWOUTEntry 8 }

      hmSecVPNFWOUTlog OBJECT-TYPE
        SYNTAX INTEGER {
                         yes(1),
                         no(2)
                       }
        ACCESS read-write
        STATUS mandatory
        DESCRIPTION
          "Log packets matching this rule."
        ::= { hmSecVPNFWOUTEntry 9 }

      hmSecVPNFWOUTRowStatus OBJECT-TYPE
        SYNTAX RowStatus
        ACCESS read-write
        STATUS mandatory
        DESCRIPTION
           "RowStatus"
      ::= { hmSecVPNFWOUTEntry 10 }

      hmSecVPNFWOUTcomment OBJECT-TYPE
        SYNTAX DisplayString
        ACCESS read-write
        STATUS mandatory
        DESCRIPTION
          "Commentary or name for this rule."
        ::= { hmSecVPNFWOUTEntry 11 }

--
-- DynDNS Register
--

    hmSecVPNDynDNS OBJECT IDENTIFIER ::= { hmSecVPN 4 }
    hmSecVPNDynDNSRegister OBJECT IDENTIFIER ::= { hmSecVPNDynDNS 1 }
    hmSecVPNDynDNSReg OBJECT-TYPE
     SYNTAX TruthValue
     ACCESS read-write
     STATUS mandatory
     DESCRIPTION
       " Register at a DynDNS service:
         no, yes"
    ::= { hmSecVPNDynDNSRegister 1 }
    hmSecVPNDynDNSRegInterval OBJECT-TYPE
     SYNTAX INTEGER
     ACCESS read-write
     STATUS mandatory
     DESCRIPTION
       " Refresh interval for registration."
    ::= { hmSecVPNDynDNSRegister 2 }
    hmSecVPNDynDNSRegServer OBJECT-TYPE
     SYNTAX DisplayString
     ACCESS read-write
     STATUS mandatory
     DESCRIPTION
       "DynDNS server."
    ::= { hmSecVPNDynDNSRegister 3 }
    hmSecVPNDynDNSRegLogin OBJECT-TYPE
     SYNTAX DisplayString
     ACCESS read-write
     STATUS mandatory
     DESCRIPTION
       "Login for DynDNS server."
    ::= { hmSecVPNDynDNSRegister 4 }
    hmSecVPNDynDNSRegPasswd OBJECT-TYPE
     SYNTAX DisplayString
     ACCESS read-write
     STATUS mandatory
     DESCRIPTION
       "Password for DynDNS server."
    ::= { hmSecVPNDynDNSRegister 5 }
    hmSecVPNDynDNSRegProvider OBJECT-TYPE
      SYNTAX INTEGER {
                       inominate(1),
		       dyndns(2),
		       dns4biz(3)
                     }
      ACCESS read-write
      STATUS mandatory
      DESCRIPTION
        "DynDNS provider"
    ::= { hmSecVPNDynDNSRegister 6 }	
    hmSecVPNDynDNSRegHostname OBJECT-TYPE
          SYNTAX DisplayString
          ACCESS read-write
          STATUS mandatory
          DESCRIPTION
           "Hostname to register"
    ::= { hmSecVPNDynDNSRegister 7 }

--
-- DynDNS Watch
--

    hmSecVPNDynDNSCheck OBJECT IDENTIFIER ::= { hmSecVPNDynDNS 2 }
    hmSecVPNDynDNSCheckDo OBJECT-TYPE
     SYNTAX TruthValue
     ACCESS read-write
     STATUS mandatory
     DESCRIPTION
       "Should hostnames of remote vpn gateways be checked after certain
       time intervals in case they are at a DynDNS provider? : no,yes"
    ::= {  hmSecVPNDynDNSCheck 1 }
    hmSecVPNDynDNSCheckRefresh OBJECT-TYPE
     SYNTAX INTEGER
     ACCESS read-write
     STATUS mandatory
     DESCRIPTION
       "Refresh interval for checking DNS names of remote VPN peers."
    ::= {  hmSecVPNDynDNSCheck 2 }

--
-- IPSec L2TP
--

    hmSecVPNL2TP  OBJECT IDENTIFIER ::= { hmSecVPN 5 }

    hmSecVPNL2TPStart OBJECT-TYPE
     SYNTAX INTEGER {
			enabled(1),
			disabled(2)
		    }
     ACCESS read-write
     STATUS mandatory
     DESCRIPTION
       "Start the L2TP Server ? yes,no"
    ::= { hmSecVPNL2TP 1 }

    hmSecVPNL2TPLocalIP OBJECT-TYPE
     SYNTAX IpAddress
     ACCESS read-write
     STATUS mandatory
     DESCRIPTION
       "Local IP for L2TP connections"
    ::= { hmSecVPNL2TP 2 }

    hmSecVPNL2TPRemoteIPRangeStart OBJECT-TYPE
     SYNTAX IpAddress
     ACCESS read-write
     STATUS mandatory
     DESCRIPTION
       "Start of range of remote IPs."
    ::= { hmSecVPNL2TP 3 }

    hmSecVPNL2TPRemoteIPRangeEnd OBJECT-TYPE
     SYNTAX IpAddress
     ACCESS read-write
     STATUS mandatory
     DESCRIPTION
       "End of range of remote IPs."
    ::= { hmSecVPNL2TP 4 }

    hmSecVPNL2TPpppdOptTable OBJECT-TYPE
      SYNTAX SEQUENCE OF HmSecVPNL2TPpppdOptEntry
      ACCESS not-accessible
      STATUS mandatory
      DESCRIPTION
        "A table of options set for the pppd process implementing IPsec/L2TP."
     ::= { hmSecVPNL2TP 5 }

    hmSecVPNL2TPpppdOptEntry OBJECT-TYPE
        SYNTAX HmSecVPNL2TPpppdOptEntry
        ACCESS not-accessible
        STATUS mandatory
        DESCRIPTION
         "A single option set for pppd. "
        INDEX { hmSecVPNL2TPpppdOptIndex }
    ::= { hmSecVPNL2TPpppdOptTable 1 }

    HmSecVPNL2TPpppdOptEntry  ::= SEQUENCE {
       hmSecVPNL2TPpppdOptIndex     INTEGER,
       hmSecVPNL2TPpppdOptValue     DisplayString,
       hmSecVPNL2TPpppdOptRowStatus RowStatus
    }

    hmSecVPNL2TPpppdOptIndex OBJECT-TYPE
      SYNTAX INTEGER (1..100)
      ACCESS not-accessible
      STATUS mandatory
      DESCRIPTION
        "Table index."
     ::= { hmSecVPNL2TPpppdOptEntry 1 }

     hmSecVPNL2TPpppdOptValue OBJECT-TYPE
      SYNTAX DisplayString
      ACCESS read-write
      STATUS mandatory
      DESCRIPTION
        "The pppd option."
     ::= { hmSecVPNL2TPpppdOptEntry 2 }

     hmSecVPNL2TPpppdOptRowStatus OBJECT-TYPE
      SYNTAX RowStatus
      ACCESS read-write
      STATUS mandatory
      DESCRIPTION
        "Row Status"
     ::= { hmSecVPNL2TPpppdOptEntry 3 }

--
-- IPsec Options
--

   hmSecVPNSettings  OBJECT IDENTIFIER ::= { hmSecVPN 6 }

   hmSecVPNRequireUniqueIDs OBJECT-TYPE
    SYNTAX INTEGER{
                    yes(1),
		    no(2)
                  }	
    ACCESS read-write
    STATUS mandatory
    DESCRIPTION
     "Allow only one open connection per identity (ie. X.509 certificate)."
   ::= { hmSecVPNSettings 1 }

   hmSecVPNNatTraversal OBJECT-TYPE
    SYNTAX INTEGER{
                    on(1),
                    off(2)
                  }
    ACCESS read-write
    STATUS mandatory
    DESCRIPTION
     "Encapsulate ESP traffic into IKE (UDP) packets to pass IPsec unaware NAT routers."
   ::= { hmSecVPNSettings 2 }

   hmSecVPNNatTPortfloating OBJECT-TYPE
    SYNTAX INTEGER{
                    on(1),
                    off(2)
                  }
    ACCESS read-write
    STATUS mandatory
    DESCRIPTION
     "Some NAT routers fail to perform NAT originating low UDP ports. This option moves IKE from UDP 500 to UDP 4500 if possible"
   ::= { hmSecVPNSettings 3 }

   hmSecVPNNatTKeepAliveInterval OBJECT-TYPE
    SYNTAX INTEGER
    ACCESS read-write
    STATUS mandatory
    DESCRIPTION
     "NAT-T Keepalive Interval (in seconds).
      Keepalives will tell the NAT router not to close the connection. "
   ::= { hmSecVPNSettings 4 }

   hmSecVPNNatTKeepAliveForce OBJECT-TYPE
    SYNTAX INTEGER{
                    yes(1),
                    no(2)
                  }
    ACCESS read-write
    STATUS mandatory
    DESCRIPTION
     "Force NAT-T Keepalive ?"
   ::= { hmSecVPNSettings 5 }

   hmSecVPNIkeLog OBJECT-TYPE
    SYNTAX INTEGER{
                    yes(1),
                    no(2)
                  }
    ACCESS read-write
    STATUS mandatory
    DESCRIPTION
     "Log verbose information on IKE ?"
   ::= { hmSecVPNSettings 6 }

   hmSecVPNHideTos OBJECT-TYPE
    SYNTAX INTEGER{
                    yes(1),
                    no(2)
                  }
    ACCESS read-write
    STATUS mandatory
    DESCRIPTION
     "When set to yes the TOS bit will be cleared on IPsec output. "
  ::= { hmSecVPNSettings 7 }

   hmSecVPNmtu OBJECT-TYPE
    SYNTAX INTEGER
    ACCESS read-write
    STATUS mandatory
    DESCRIPTION
     "ipsec0 mtu"
   ::= { hmSecVPNSettings 8 }

   hmSecVPNStrictCRLPolicy OBJECT-TYPE
    SYNTAX INTEGER{
                    yes(1),
                    no(2)
                  }
    ACCESS read-write
    STATUS mandatory
    DESCRIPTION
     "Use a strict CRL policy?"
   ::= { hmSecVPNSettings 9 }

   hmSecVPNNoCertReqSend OBJECT-TYPE
    SYNTAX INTEGER{
                    yes(1),
                    no(2)
                  }
    ACCESS read-write
    STATUS mandatory
    DESCRIPTION
     "Don't send certificate requests?"
   ::= { hmSecVPNSettings 10 }

--
-- Firewall Incoming
--

   hmSecFirewallIncoming  OBJECT IDENTIFIER ::= { hmSecFirewall 1 }

   hmSecFirewallIncomingTable OBJECT-TYPE
     SYNTAX SEQUENCE OF HmSecFirewallIncomingEntry
     ACCESS not-accessible
     STATUS mandatory
     DESCRIPTION
        "A table containing firewall rules for incoming  packets."
   ::= { hmSecFirewallIncoming 1 }

    hmSecFirewallIncomingEntry OBJECT-TYPE
      SYNTAX HmSecFirewallIncomingEntry
      ACCESS not-accessible
      STATUS mandatory
      DESCRIPTION
       "An entry containing data of a single rule."
      INDEX { hmSecFWINruleIndex }
    ::= { hmSecFirewallIncomingTable 1 }

    HmSecFirewallIncomingEntry ::= SEQUENCE{
      hmSecFWINruleIndex       INTEGER,
      hmSecFWINsourceIP        DisplayString,
      hmSecFWINdestinationIP   DisplayString,
      hmSecFWINsport           DisplayString,
      hmSecFWINdport           DisplayString,
      hmSecFWINtarget          INTEGER,
      hmSecFWINproto           INTEGER,
      hmSecFWINlog             INTEGER,
      hmSecFWINRowStatus       RowStatus,
      hmSecFWINcomment         DisplayString
    }

    hmSecFWINruleIndex OBJECT-TYPE
      SYNTAX   INTEGER (1..250)
      ACCESS   not-accessible
      STATUS   mandatory
      DESCRIPTION
        "Index to identify the rule."
    ::= { hmSecFirewallIncomingEntry 1 }

    hmSecFWINsourceIP OBJECT-TYPE
      SYNTAX DisplayString
      ACCESS read-write
      STATUS mandatory
      DESCRIPTION
         "The rule's source IP address"
     ::= { hmSecFirewallIncomingEntry 2 }

    hmSecFWINdestinationIP OBJECT-TYPE
      SYNTAX DisplayString
      ACCESS read-write
      STATUS mandatory
      DESCRIPTION
         "The rule's source IP address"
     ::= { hmSecFirewallIncomingEntry 3 }

     hmSecFWINsport OBJECT-TYPE
      SYNTAX DisplayString
      ACCESS read-write
      STATUS mandatory
      DESCRIPTION
         "The rule's source port"
     ::= { hmSecFirewallIncomingEntry 4 }

     hmSecFWINdport OBJECT-TYPE
      SYNTAX DisplayString
      ACCESS read-write
      STATUS mandatory
      DESCRIPTION
         "The rule's destination port"
     ::= { hmSecFirewallIncomingEntry 5 }

     hmSecFWINtarget OBJECT-TYPE
       SYNTAX INTEGER {
			accept(1),
			reject(2),
			drop(3)
		      }
       ACCESS read-write
       STATUS mandatory
       DESCRIPTION
          "The rule's target"
     ::= { hmSecFirewallIncomingEntry 6 }

     hmSecFWINproto OBJECT-TYPE
      SYNTAX INTEGER {
			tcp(1),
			udp(2),
			icmp(3),
			all(4)
		      }
      ACCESS read-write
      STATUS mandatory
       DESCRIPTION
        "The rule's transport protocol"
     ::= { hmSecFirewallIncomingEntry 7 }

      hmSecFWINlog OBJECT-TYPE
        SYNTAX INTEGER {
	                 yes(1),
			 no(2)
		       }
        ACCESS read-write
        STATUS mandatory
        DESCRIPTION
	  " Log packets matching this rule ?"
       	::= { hmSecFirewallIncomingEntry 8 }

      hmSecFWINRowStatus OBJECT-TYPE
        SYNTAX RowStatus
        ACCESS read-write
        STATUS mandatory
        DESCRIPTION
           "RowStatus"
      ::= { hmSecFirewallIncomingEntry 9 }

       hmSecFWINcomment OBJECT-TYPE
        SYNTAX DisplayString
        ACCESS read-write
        STATUS mandatory
        DESCRIPTION
          "Commentary or name for this rule."
        ::= { hmSecFirewallIncomingEntry 10 }

     hmSecFirewallINLogDefault OBJECT-TYPE
     SYNTAX INTEGER  {
                       yes(1),
		       no(2)
		     }
     ACCESS read-write
     STATUS mandatory
     DESCRIPTION
        "Log entries for unknown connection attemps ?"
   ::= { hmSecFirewallIncoming 2 }

--
-- Firewall Outgoing
--

   hmSecFirewallOutgoing  OBJECT IDENTIFIER ::= { hmSecFirewall 2 }

   hmSecFirewallOutgoingTable OBJECT-TYPE
     SYNTAX SEQUENCE OF HmSecFirewallOutgoingEntry
     ACCESS not-accessible
     STATUS mandatory
     DESCRIPTION
        "A table containing firewall rules for outgoing  packets."
   ::= { hmSecFirewallOutgoing 1 }

    hmSecFirewallOutgoingEntry OBJECT-TYPE
      SYNTAX HmSecFirewallOutgoingEntry
      ACCESS not-accessible
      STATUS mandatory
      DESCRIPTION
       "An entry containing data of a single rule."
      INDEX { hmSecFWOUTruleIndex }
    ::= { hmSecFirewallOutgoingTable 1 }


    HmSecFirewallOutgoingEntry ::= SEQUENCE {
      hmSecFWOUTruleIndex       INTEGER,
      hmSecFWOUTsourceIP        DisplayString,
      hmSecFWOUTdestinationIP   DisplayString,
      hmSecFWOUTsport           DisplayString,
      hmSecFWOUTdport           DisplayString,
      hmSecFWOUTtarget          INTEGER,
      hmSecFWOUTproto           INTEGER,
      hmSecFWOUTlog             INTEGER,
      hmSecFWOUTRowStatus	 RowStatus,
      hmSecFWOUTcomment         DisplayString
    }

    hmSecFWOUTruleIndex OBJECT-TYPE
      SYNTAX   INTEGER (1..250)
      ACCESS   not-accessible
      STATUS   mandatory
      DESCRIPTION
        "Index to identify the rule."
    ::= { hmSecFirewallOutgoingEntry 1 }

     hmSecFWOUTsourceIP OBJECT-TYPE
      SYNTAX DisplayString
      ACCESS read-write
      STATUS mandatory
      DESCRIPTION
         "The rule's source IP address"
     ::= { hmSecFirewallOutgoingEntry 2 }

     hmSecFWOUTdestinationIP OBJECT-TYPE
      SYNTAX DisplayString
      ACCESS read-write
      STATUS mandatory
      DESCRIPTION
         "The rule's source IP address"
     ::= { hmSecFirewallOutgoingEntry 3 }

     hmSecFWOUTsport OBJECT-TYPE
      SYNTAX DisplayString
      ACCESS read-write
      STATUS mandatory
      DESCRIPTION
         "The rule's source port"
     ::= { hmSecFirewallOutgoingEntry 4 }

     hmSecFWOUTdport OBJECT-TYPE
      SYNTAX DisplayString
      ACCESS read-write
      STATUS mandatory
      DESCRIPTION
         "The rule's destination port"
     ::= { hmSecFirewallOutgoingEntry 5 }

     hmSecFWOUTtarget OBJECT-TYPE
       SYNTAX INTEGER {
			accept(1),
			reject(2),
			drop(3)
		      }
       ACCESS read-write
       STATUS mandatory
       DESCRIPTION
          "The rule's target"
     ::= { hmSecFirewallOutgoingEntry 6 }

    hmSecFWOUTproto OBJECT-TYPE
      SYNTAX INTEGER {
			tcp(1),
			udp(2),
			icmp(3),
			all(4)
		      }
      ACCESS read-write
      STATUS mandatory
       DESCRIPTION
        "The rule's transport protocol"
     ::= { hmSecFirewallOutgoingEntry 7 }

    hmSecFWOUTlog OBJECT-TYPE
      SYNTAX INTEGER {
                       yes(1),
                       no(2)
                     }
      ACCESS read-write
      STATUS mandatory
      DESCRIPTION
        " Log packets matching this rule ?"
      ::= { hmSecFirewallOutgoingEntry 8 }

    hmSecFWOUTRowStatus OBJECT-TYPE
        SYNTAX RowStatus
        ACCESS read-write
        STATUS mandatory
        DESCRIPTION
           "RowStatus"
      ::= { hmSecFirewallOutgoingEntry 9 }

      hmSecFWOUTcomment OBJECT-TYPE
       SYNTAX DisplayString
       ACCESS read-write
       STATUS mandatory
       DESCRIPTION
         "Commentary or name for this rule."
       ::= { hmSecFirewallOutgoingEntry 10 }
	
   hmSecFirewallOUTLogDefault OBJECT-TYPE
     SYNTAX INTEGER  {
                       yes(1),
		       no(2)
		     }
     ACCESS read-write
     STATUS mandatory
     DESCRIPTION
        "Log entries for unknown connection attemps ?"
   ::= { hmSecFirewallOutgoing 2 }

--
-- Firwall Portforwarding
--

  hmSecFirewallPortforwarding OBJECT IDENTIFIER ::= { hmSecFirewall 3 }

  hmSecFirewallPortforwardTable OBJECT-TYPE
     SYNTAX SEQUENCE OF HmSecFirewallPortforwardEntry
     ACCESS not-accessible
     STATUS mandatory
     DESCRIPTION
        "A table containing firewall rules for portforwarding."
   ::= { hmSecFirewallPortforwarding 1 }

    hmSecFirewallPortforwardEntry OBJECT-TYPE
      SYNTAX HmSecFirewallPortforwardEntry
      ACCESS not-accessible
      STATUS mandatory
      DESCRIPTION
       "An entry containing data of a single rule."
      INDEX { hmSecFWPORTFORWruleIndex }
    ::= { hmSecFirewallPortforwardTable 1 }

    HmSecFirewallPortforwardEntry ::= SEQUENCE{
      hmSecFWPORTFORWruleIndex       INTEGER,
      hmSecFWPORTFORWinIP        DisplayString,
      hmSecFWPORTFORWoutIP       DisplayString,
      hmSecFWPORTFORWinport      DisplayString,
      hmSecFWPORTFORWoutport     DisplayString,
      hmSecFWPORTFORWproto       INTEGER,
      hmSecFWPORTFORWlog         INTEGER,
      hmSecFWPORTFORWRowStatus   RowStatus,
      hmSecFWPORTFORWsrcIP       DisplayString,
      hmSecFWPORTFORWsrcport     DisplayString,
      hmSecFWPORTFORWcomment     DisplayString
    }

    hmSecFWPORTFORWruleIndex OBJECT-TYPE
      SYNTAX   INTEGER (1..250)
      ACCESS   not-accessible
      STATUS   mandatory
      DESCRIPTION
        "Index to identify the rule."
    ::= { hmSecFirewallPortforwardEntry 1 }

    hmSecFWPORTFORWinIP OBJECT-TYPE
      SYNTAX DisplayString
      ACCESS read-write
      STATUS mandatory
      DESCRIPTION
         "The rule's incoming IP address"
     ::= { hmSecFirewallPortforwardEntry 2 }

    hmSecFWPORTFORWoutIP OBJECT-TYPE
      SYNTAX DisplayString
      ACCESS read-write
      STATUS mandatory
      DESCRIPTION
         "The rule's redirect IP address"
     ::= { hmSecFirewallPortforwardEntry 3 }

    hmSecFWPORTFORWinport OBJECT-TYPE
      SYNTAX DisplayString
      ACCESS read-write
      STATUS mandatory
      DESCRIPTION
         "The rule's incoming port"
     ::= { hmSecFirewallPortforwardEntry 4 }

    hmSecFWPORTFORWoutport OBJECT-TYPE
      SYNTAX DisplayString
      ACCESS read-write
      STATUS mandatory
      DESCRIPTION
         "The rule's destination port"
     ::= { hmSecFirewallPortforwardEntry 5 }

    hmSecFWPORTFORWproto OBJECT-TYPE
      SYNTAX INTEGER {
			tcp(1),
			udp(2)
		      }
      ACCESS read-write
      STATUS mandatory
       DESCRIPTION
        "The rule's transport protocol"
     ::= { hmSecFirewallPortforwardEntry 6 }

    hmSecFWPORTFORWlog OBJECT-TYPE
      SYNTAX INTEGER {
                       yes(1),
                       no(2)
                     }
      ACCESS read-write
      STATUS mandatory
      DESCRIPTION
        " Log packets matching this rule ?"
      ::= { hmSecFirewallPortforwardEntry 7 }

    hmSecFWPORTFORWRowStatus OBJECT-TYPE
        SYNTAX RowStatus
        ACCESS read-write
        STATUS mandatory
        DESCRIPTION
           "RowStatus"
      ::= { hmSecFirewallPortforwardEntry 8 }

    hmSecFWPORTFORWsrcIP OBJECT-TYPE
      SYNTAX DisplayString
      ACCESS read-write
      STATUS mandatory
      DESCRIPTION
         "The rule's source IP address"
     ::= { hmSecFirewallPortforwardEntry 9 }

    hmSecFWPORTFORWsrcport OBJECT-TYPE
      SYNTAX DisplayString
      ACCESS read-write
      STATUS mandatory
      DESCRIPTION
         "The rule's source port"
     ::= { hmSecFirewallPortforwardEntry 10 }

     hmSecFWPORTFORWcomment OBJECT-TYPE
      SYNTAX DisplayString
      ACCESS read-write
      STATUS mandatory
      DESCRIPTION
        "Commentary or name for this rule."
      ::= { hmSecFirewallPortforwardEntry 11 }

--
-- Firewall NAT
--

   hmSecFirewallNAT OBJECT IDENTIFIER ::= { hmSecFirewall 4 }

   hmSecFirewallNATRuleTable OBJECT-TYPE
     SYNTAX SEQUENCE OF HmSecFirewallNATRuleEntry
     ACCESS not-accessible
     STATUS mandatory
     DESCRIPTION
        "A table containing firewall rules for network address translation."
   ::= { hmSecFirewallNAT 1 }

    hmSecFirewallNATRuleEntry OBJECT-TYPE
      SYNTAX HmSecFirewallNATRuleEntry
      ACCESS not-accessible
      STATUS mandatory
      DESCRIPTION
       "An entry containing data of a single rule."
      INDEX { hmSecFWNATruleIndex }
    ::= { hmSecFirewallNATRuleTable 1 }


    HmSecFirewallNATRuleEntry ::= SEQUENCE{
      hmSecFWNATruleIndex       INTEGER,
      hmSecFWNATIP              DisplayString,
      hmSecFWNATRowStatus       RowStatus,
      hmSecFWNATOutIP           DisplayString
    }

    hmSecFWNATruleIndex OBJECT-TYPE
      SYNTAX   INTEGER (1..250)
      ACCESS   not-accessible
      STATUS   mandatory
      DESCRIPTION
        "Index to identify the rule."
    ::= { hmSecFirewallNATRuleEntry 1 }

    hmSecFWNATIP OBJECT-TYPE
      SYNTAX DisplayString
      ACCESS read-write
      STATUS mandatory
      DESCRIPTION
         "The rule's source IP address"
     ::= { hmSecFirewallNATRuleEntry 2 }

    hmSecFWNATRowStatus OBJECT-TYPE
        SYNTAX RowStatus
        ACCESS read-write
        STATUS mandatory
        DESCRIPTION
           "RowStatus"
      ::= { hmSecFirewallNATRuleEntry 3 }

    hmSecFWNATOutIP OBJECT-TYPE
      SYNTAX DisplayString
      ACCESS read-write
      STATUS mandatory
      DESCRIPTION
         "Reserved for future use"
     ::= { hmSecFirewallNATRuleEntry 4 }

--
-- Firewall Extended Settings
--

    hmSecFirewallExtended  OBJECT IDENTIFIER ::= { hmSecFirewall 5 }

    hmSecFirewallIPConntrackMax OBJECT-TYPE
     SYNTAX INTEGER
     ACCESS read-write
     STATUS mandatory
     DESCRIPTION
      "Maximum size of connection tracking table"
    ::= { hmSecFirewallExtended 1 }

    hmSecFirewallIPSynfloodLimitInt OBJECT-TYPE
     SYNTAX INTEGER
     ACCESS read-write
     STATUS mandatory
     DESCRIPTION
      "Maximum number of new outgoing TCP connections (SYN) per second"
    ::= { hmSecFirewallExtended 2 }

    hmSecFirewallIPSynfloodLimitExt OBJECT-TYPE
     SYNTAX INTEGER
     ACCESS read-write
     STATUS mandatory
     DESCRIPTION
      "Maximum number of new incoming TCP connections (SYN) per second"
    ::= { hmSecFirewallExtended  3 }

    hmSecFirewallICMPLimitInt OBJECT-TYPE
     SYNTAX INTEGER
     ACCESS read-write
     STATUS mandatory
     DESCRIPTION
      "Maximum number of outgoing ping frames (ICMP Echo Request) per second"
    ::= { hmSecFirewallExtended  4 }

    hmSecFirewallICMPLimitExt OBJECT-TYPE
     SYNTAX INTEGER
     ACCESS read-write
     STATUS mandatory
     DESCRIPTION
      "Maximum number of incoming ping frames (ICMP Echo Request) per second"
    ::= { hmSecFirewallExtended  5 }

    hmSecFirewallEnableConntrackFTP OBJECT-TYPE
     SYNTAX INTEGER {
                       yes(1),
                       no(2)
                    }
     ACCESS read-write
     STATUS mandatory
     DESCRIPTION
      "Enable active FTP NAT/Connection Tracking support"
    ::= { hmSecFirewallExtended 6 }

    hmSecFirewallConntrackIRC OBJECT-TYPE
     SYNTAX INTEGER {
                       yes(1),
                       no(2)
                    }
     ACCESS read-write
     STATUS mandatory
     DESCRIPTION
      "Enable IRC NAT/Connection Tracking support"
    ::= { hmSecFirewallExtended 7 }

    hmSecFirewallConntrackPPTP OBJECT-TYPE
     SYNTAX INTEGER {
                       yes(1),
                       no(2)
                    }
     ACCESS read-write
     STATUS mandatory
     DESCRIPTION
      "Enable PPTP NAT/Connection Tracking support"
    ::= { hmSecFirewallExtended 8 }

   hmSecFirewallARPLimitInt OBJECT-TYPE
     SYNTAX INTEGER
     ACCESS read-write
     STATUS mandatory
     DESCRIPTION
      "Maximum number of outgoing arp request frames per second (stealth mode only)"
    ::= { hmSecFirewallExtended  9 }

   hmSecFirewallARPLimitExt OBJECT-TYPE
     SYNTAX INTEGER
     ACCESS read-write
     STATUS mandatory
     DESCRIPTION
      "Maximum number of incoming arp request frames per second (stealth mode only)"
    ::= { hmSecFirewallExtended  10 }

   hmSecFirewallICMPPolicy OBJECT-TYPE
     SYNTAX INTEGER {
                       drop(1),
                       ping(2),
		       all(3)
                    }
     ACCESS read-write
     STATUS mandatory
     DESCRIPTION
      "Allow incoming ICMP frames to the hmSec itself (router modes only):
       drop: default, ping: allow incoming ICMP echo request (required to
       answer ping), all: allow all incoming ICMP request to reach the TCP
       stack.
       Note: ICMP packets related to established connections are handled
       by the connection tracking. This setting is used for unrelated ICMP
       traffic."
    ::= { hmSecFirewallExtended 11 }

    hmSecFirewallConntrackH323 OBJECT-TYPE
     SYNTAX INTEGER {
                       yes(1),
                       no(2)
                    }
     ACCESS read-write
     STATUS mandatory
     DESCRIPTION
      "Enable H323 NAT/Connection Tracking support"
    ::= { hmSecFirewallExtended 12 }

    hmSecFirewallIpUncleanMatch OBJECT-TYPE
     SYNTAX INTEGER {
                       yes(1),
                       no(2)
                    }
     ACCESS read-write
     STATUS mandatory
     DESCRIPTION
      "Enable IP Unclean Match"
    ::= { hmSecFirewallExtended 13 }


--
-- Firewall 1:1 NAT
--

   hmSecFirewall11NAT OBJECT IDENTIFIER ::= { hmSecFirewall 6 }
   hmSecFirewall11NATRuleTable OBJECT-TYPE
     SYNTAX SEQUENCE OF HmSecFirewall11NATRuleEntry
     ACCESS not-accessible
     STATUS mandatory
     DESCRIPTION
        "A table containing firewall rules for network address translation."
   ::= { hmSecFirewall11NAT 1 }
    hmSecFirewall11NATRuleEntry OBJECT-TYPE
      SYNTAX HmSecFirewall11NATRuleEntry
      ACCESS not-accessible
      STATUS mandatory
      DESCRIPTION
       "An entry containing data of a single rule."
      INDEX { hmSecFW11NATruleIndex }
    ::= { hmSecFirewall11NATRuleTable 1 }


    HmSecFirewall11NATRuleEntry ::= SEQUENCE{
      hmSecFW11NATruleIndex     INTEGER,
      hmSecFW11NATLocal         IpAddress,
      hmSecFW11NATRemote        IpAddress,
      hmSecFW11NATMask          INTEGER,
      hmSecFW11NATLog		 INTEGER,
      hmSecFW11NATRowStatus     RowStatus
    }

    hmSecFW11NATruleIndex OBJECT-TYPE
      SYNTAX   INTEGER (1..250)
      ACCESS   not-accessible
      STATUS   mandatory
      DESCRIPTION
        "Index to identify the rule."
    ::= { hmSecFirewall11NATRuleEntry 1 }
    hmSecFW11NATLocal OBJECT-TYPE
      SYNTAX IpAddress
      ACCESS read-write
      STATUS mandatory
      DESCRIPTION
         "Network for 1:1 NAT on local interface."
     ::= { hmSecFirewall11NATRuleEntry 2 }
    hmSecFW11NATRemote OBJECT-TYPE
      SYNTAX IpAddress
      ACCESS read-write
      STATUS mandatory
      DESCRIPTION
         "Network for 1:1 NAT on remote interface."
     ::= { hmSecFirewall11NATRuleEntry 3 }
    hmSecFW11NATMask OBJECT-TYPE
      SYNTAX INTEGER
      ACCESS read-write
      STATUS mandatory
      DESCRIPTION
         "Netmask for 1:1 NAT between 0 and 32."
     ::= { hmSecFirewall11NATRuleEntry 4 }
    hmSecFW11NATLog OBJECT-TYPE
      SYNTAX INTEGER {
        yes(1),
        no(2)
      }
      ACCESS read-write
      STATUS mandatory
      DESCRIPTION
         "Log entries for this rule?"
     ::= { hmSecFirewall11NATRuleEntry 5 }
    hmSecFW11NATRowStatus OBJECT-TYPE
        SYNTAX RowStatus
        ACCESS read-write
        STATUS mandatory
        DESCRIPTION
           "RowStatus"
      ::= { hmSecFirewall11NATRuleEntry 10 }

--
-- Network
--

    hmSecNetworkMode OBJECT-TYPE
     SYNTAX INTEGER {
			stealth(1),
			router(2),
			pppoe(3),
			pptp(4)
		    }
     ACCESS read-only
     STATUS mandatory
     DESCRIPTION
        "Network mode:
          router,stealth"
    ::= { hmSecNetwork 1 }


--
-- Stealth
--

    hmSecStealth OBJECT IDENTIFIER ::= { hmSecNetwork 2 }

    hmSecStealthIPConfMode OBJECT-TYPE
     SYNTAX INTEGER {
			autoDetect(1),
			static(2),
			multi(3)
		    }
     ACCESS read-write
     STATUS mandatory
     DESCRIPTION
      "Type of IP Stack configuration in stealth mode.
       autodetect, static, multiple-clients"
    ::= { hmSecStealth 1 }

    hmSecStealthIPConfStatic OBJECT IDENTIFIER ::= { hmSecStealth 2 }

    hmSecStealthStaticIP OBJECT-TYPE
     SYNTAX IpAddress
     ACCESS read-write
     STATUS mandatory
     DESCRIPTION
        "IP address of the protected client in stealth mode (using static ip
        configuration)."
    ::= { hmSecStealthIPConfStatic 1 }

    hmSecStealthStaticMAC OBJECT-TYPE
     SYNTAX MacAddress
     ACCESS read-write
     STATUS mandatory
     DESCRIPTION
        "MAC address of protected client in stealth mode (using static ip
        configuration)."
    ::= { hmSecStealthIPConfStatic 2 }

    hmSecStealthStaticActivate OBJECT-TYPE
      SYNTAX INTEGER {
			activate(1),
			valuescached(2)
		     }
      ACCESS read-write
      STATUS mandatory
      DESCRIPTION
         "Button to activate Stealth Static IP configuration."
   ::= { hmSecStealthIPConfStatic 3 }

    hmSecStealthManageIP OBJECT-TYPE
     SYNTAX IpAddress
     ACCESS read-write
     STATUS mandatory
     DESCRIPTION
        "The management IP address of this system in stealth mode
	 When set, this value is internally cached inside the agent until it
	 is explicitly activated by writing the hmSecStealthManageActivate
	 object. When read the currently active setting is returned, not
	 regarding any cached values."
    ::= { hmSecStealthIPConfStatic 4 }

    hmSecStealthManageNetmask OBJECT-TYPE
     SYNTAX IpAddress
     ACCESS read-write
     STATUS mandatory
     DESCRIPTION
        "The management IP netmask of this system in stealth mode
	 When set, this value is internally cached inside the agent until it
	 is explicitly activated by writing the hmSecStealthManageActivate
	 object. When read the currently active setting is returned, not
	 regarding any cached values."
    ::= { hmSecStealthIPConfStatic 5 }

    hmSecStealthManageGateway OBJECT-TYPE
     SYNTAX IpAddress
     ACCESS read-write
     STATUS mandatory
     DESCRIPTION
        "The default gateway for the management IP of the hmSec in
	 stealth mode When set, this value is internally cached inside the
	 agent until it is explicitly activated by writing the
	 hmSecStealthManageActivate object. When read the currently active
	 setting is returned, not regarding any cached values."
    ::= { hmSecStealthIPConfStatic 6 }

    hmSecStealthManageActivate OBJECT-TYPE
      SYNTAX INTEGER {
			activate(1),
			valuescached(2)
		     }
      ACCESS read-write
      STATUS mandatory
      DESCRIPTION
         "Button to activate the stealth management IP configuration. When
	  activate(1) is written, any cached values for the
	  hmSecStealthManageIP, hmSecStealthManageNetmask, and
	  hmSecStealthManageGateway objects are activated. When read and one
	  or more of the above mentioned objects have been cached,
	  valuescached(2) is returned, not regarding whether the cached valued
	  and the current value are different."
   ::= { hmSecStealthIPConfStatic 7 }


--
-- HiDiscovery in StealthMode
--
 
    hmSecStealthHiDiscoveryRelay OBJECT-TYPE
      SYNTAX INTEGER {
			enabled(1),
			disabled(2)
		     }
      ACCESS read-write
      STATUS mandatory
      DESCRIPTION
         "Relay/bridge HiDiscovery queries when in Stealth Mode."
   ::= { hmSecStealth 3 }
 
    hmSecStealthHiDiscoveryState OBJECT-TYPE
      SYNTAX INTEGER {
			read-write(1),
			read-only(2),
			disabled(3)
		     }
      ACCESS read-write
      STATUS mandatory
      DESCRIPTION
         "Enable HiDiscovery in StealthMode. This is mutually exclusive with 
	  the two HiDiscovery router mode settings of course."
   ::= { hmSecStealth 4 }
 
 

    hmSecStealthL2Filter OBJECT IDENTIFIER ::= { hmSecStealth 5 }

--
--  hmSecStealthL2FilterIntern
--

    hmSecL2FilterInternTable OBJECT-TYPE
      SYNTAX SEQUENCE OF HmSecL2FilterInternEntry
      ACCESS not-accessible
      STATUS mandatory
      DESCRIPTION
        "Table of firewall rules for Layer 2 filtering on internal interface."
      ::= { hmSecStealthL2Filter 1 }

    hmSecL2FilterInternEntry OBJECT-TYPE
        SYNTAX HmSecL2FilterInternEntry
        ACCESS not-accessible
        STATUS mandatory
        DESCRIPTION
         "A single rule for Layer-2 filter in internal interface. "
        INDEX { hmSecL2FilterInternRuleIndex }
    ::= { hmSecL2FilterInternTable 1 }

    HmSecL2FilterInternEntry ::= SEQUENCE{
      hmSecL2FilterInternRuleIndex	INTEGER,
      hmSecL2FilterInternRowStatus	RowStatus,
      hmSecL2FilterInternSrcMac	MacAddress,
      hmSecL2FilterInternDstMac	MacAddress,
      hmSecL2FilterInternEthType	INTEGER,
      hmSecL2FilterInternTarget	INTEGER,
      hmSecL2FilterInternComment	DisplayString
    }

    hmSecL2FilterInternRuleIndex OBJECT-TYPE
      SYNTAX INTEGER (1..100)
      ACCESS not-accessible
      STATUS mandatory
      DESCRIPTION
        "Table index."
     ::= { hmSecL2FilterInternEntry 1 }

    hmSecL2FilterInternRowStatus OBJECT-TYPE
      SYNTAX RowStatus
      ACCESS read-write
      STATUS mandatory
      DESCRIPTION
        "Row Status."
     ::= { hmSecL2FilterInternEntry 2 }

    hmSecL2FilterInternSrcMac OBJECT-TYPE
      SYNTAX MacAddress
      ACCESS read-write
      STATUS mandatory
      DESCRIPTION
        "Source MAC Address to apply this filter rule for."
     ::= { hmSecL2FilterInternEntry 3 }

    hmSecL2FilterInternDstMac OBJECT-TYPE
      SYNTAX MacAddress
      ACCESS read-write
      STATUS mandatory
      DESCRIPTION
        "Desitination MAC Address to apply this filter rule for."
     ::= { hmSecL2FilterInternEntry 4 }

    hmSecL2FilterInternEthType OBJECT-TYPE
      SYNTAX INTEGER
      ACCESS read-write
      STATUS mandatory
      DESCRIPTION
        "Ethernet type to apply this filter rule for."
     ::= { hmSecL2FilterInternEntry 5 }

    hmSecL2FilterInternTarget OBJECT-TYPE
       SYNTAX INTEGER {
                        accept(1),
                        reject(2),
                        drop(3)
                      }
       ACCESS read-write
       STATUS mandatory
       DESCRIPTION
          "The rule's target"
     ::= { hmSecL2FilterInternEntry 6 }

    hmSecL2FilterInternComment OBJECT-TYPE
      SYNTAX DisplayString
      ACCESS read-write
      STATUS mandatory
      DESCRIPTION
        "Comment or name for this rule."
     ::= { hmSecL2FilterInternEntry 7 }




--
--  hmSecStealthL2FilterExtern
--

    hmSecL2FilterExternTable OBJECT-TYPE
      SYNTAX SEQUENCE OF HmSecL2FilterExternEntry
      ACCESS not-accessible
      STATUS mandatory
      DESCRIPTION
        "Table of firewall rules for Layer 2 filterin on external interface."
      ::= { hmSecStealthL2Filter 2 }

    hmSecL2FilterExternEntry OBJECT-TYPE
        SYNTAX HmSecL2FilterExternEntry
        ACCESS not-accessible
        STATUS mandatory
        DESCRIPTION
         "A single rule for Layer-2 filter in external interface. "
        INDEX { hmSecL2FilterExternRuleIndex }
    ::= { hmSecL2FilterExternTable 1 }

    HmSecL2FilterExternEntry ::= SEQUENCE{
      hmSecL2FilterExternRuleIndex	INTEGER,
      hmSecL2FilterExternRowStatus	RowStatus,
      hmSecL2FilterExternSrcMac	MacAddress,
      hmSecL2FilterExternDstMac	MacAddress,
      hmSecL2FilterExternEthType	INTEGER,
      hmSecL2FilterExternTarget	INTEGER,
      hmSecL2FilterExternComment	DisplayString
    }

    hmSecL2FilterExternRuleIndex OBJECT-TYPE
      SYNTAX INTEGER (1..100)
      ACCESS not-accessible
      STATUS mandatory
      DESCRIPTION
        "Table index."
     ::= { hmSecL2FilterExternEntry 1 }

    hmSecL2FilterExternRowStatus OBJECT-TYPE
      SYNTAX RowStatus
      ACCESS read-write
      STATUS mandatory
      DESCRIPTION
        "Row Status."
     ::= { hmSecL2FilterExternEntry 2 }

    hmSecL2FilterExternSrcMac OBJECT-TYPE
      SYNTAX MacAddress
      ACCESS read-write
      STATUS mandatory
      DESCRIPTION
        "Source MAC Address to apply this filter rule for."
     ::= { hmSecL2FilterExternEntry 3 }

    hmSecL2FilterExternDstMac OBJECT-TYPE
      SYNTAX MacAddress
      ACCESS read-write
      STATUS mandatory
      DESCRIPTION
        "Desitination MAC Address to apply this filter rule for."
     ::= { hmSecL2FilterExternEntry 4 }

    hmSecL2FilterExternEthType OBJECT-TYPE
      SYNTAX INTEGER
      ACCESS read-write
      STATUS mandatory
      DESCRIPTION
        "Ethernet type to apply this filter rule for."
     ::= { hmSecL2FilterExternEntry 5 }

    hmSecL2FilterExternTarget OBJECT-TYPE
       SYNTAX INTEGER {
                        accept(1),
                        reject(2),
                        drop(3)
                      }
       ACCESS read-write
       STATUS mandatory
       DESCRIPTION
          "The rule's target"
     ::= { hmSecL2FilterExternEntry 6 }

    hmSecL2FilterExternComment OBJECT-TYPE
      SYNTAX DisplayString
      ACCESS read-write
      STATUS mandatory
      DESCRIPTION
        "Comment or name for this rule."
     ::= { hmSecL2FilterExternEntry 7 }


--
--  hmSecStealthL2Filter fuer spezielle Protokolle
--

    hmSecStealthL2ForwardGVRP OBJECT-TYPE
       SYNTAX INTEGER {
                        yes(1),
                        no(2)
                      }
      ACCESS read-write
      STATUS mandatory
      DESCRIPTION
        "Enable GVRP forwarding in StealthMode."
      ::= { hmSecStealthL2Filter 3 }

    hmSecStealthL2ForwardSTP OBJECT-TYPE
       SYNTAX INTEGER {
                        yes(1),
                        no(2)
                      }
      ACCESS read-write
      STATUS mandatory
      DESCRIPTION
        "Enable STP forwarding in StealthMode."
      ::= { hmSecStealthL2Filter 4 }

    hmSecStealthL2ForwardDHCP OBJECT-TYPE
       SYNTAX INTEGER {
                        yes(1),
                        no(2)
                      }
      ACCESS read-write
      STATUS mandatory
      DESCRIPTION
        "Enable DHCP forwarding in StealthMode. This will allow computers on
	 the internal/protected side to receive their configuration via
	 DHCP even if no special DHCP rule is configured in the firewall"
      ::= { hmSecStealthL2Filter 5 }
 


--
-- Stealth Interface
--

    hmSecStealthInterface OBJECT IDENTIFIER ::= { hmSecStealth 6 }

    hmSecStealthMTU OBJECT-TYPE
     SYNTAX INTEGER
     ACCESS read-write
     STATUS mandatory
     DESCRIPTION
      "MTU to use in Stealth Mode."
    ::= { hmSecStealthInterface 1 }

    hmSecStealthVlanMTU OBJECT-TYPE
     SYNTAX INTEGER
     ACCESS read-write
     STATUS mandatory
     DESCRIPTION
      "MTU to use in Stealth Mode for VLAN packets."
    ::= { hmSecStealthInterface 2 }

    hmSecStealthManageUseVLAN OBJECT-TYPE
      SYNTAX INTEGER {
                        yes(1),
                        no(2)
                      }
     ACCESS read-write
     STATUS mandatory
     DESCRIPTION
      "Use VLAn tagging for the management IP address in Stealth Mode."
    ::= { hmSecStealthInterface 3 }

    hmSecStealthManageVLanID OBJECT-TYPE
     SYNTAX INTEGER
     ACCESS read-write
     STATUS mandatory
     DESCRIPTION
      "VLAN ID for the management IP address in Stealth Mode."
    ::= { hmSecStealthInterface 4 }


--
-- Network Internal IP
--

   hmSecRouter OBJECT IDENTIFIER ::= { hmSecNetwork 3 }

   hmSecRouterLocal OBJECT IDENTIFIER ::= { hmSecRouter 1 }

   hmSecRouterLocalIP OBJECT-TYPE
     SYNTAX IpAddress
     ACCESS read-write
     STATUS mandatory
     DESCRIPTION
        "The internal IP address of this device in router mode. When set,
	 this value is internally cached inside the agent until it is
	 explicitly activated by writing the hmSecRouterLocalActivate
	 object. When read the currently active setting is returned,
	 not regarding any cached values."
    ::= { hmSecRouterLocal 1 }

   hmSecRouterLocalNetmask OBJECT-TYPE
     SYNTAX IpAddress
     ACCESS read-write
     STATUS mandatory
     DESCRIPTION
        "The internal subnet mask of this device in router mode. When set,
	 this value is internally cached inside the agent until it is
	 explicitly activated by writing the hmSecRouterLocalActivate
	 object. When read the currently active setting is returned,
	 not regarding any cached values."
    ::= { hmSecRouterLocal 2 }

  hmSecRouterLocalActivate OBJECT-TYPE
    SYNTAX INTEGER {
			activate(1),
			valuescached(2)
		   }
      ACCESS read-write
      STATUS mandatory
      DESCRIPTION
         "Button to activate the router local IP configuration. When
	  activate(1) is written, any cached values for the hmSecRouterLocalIP,
	  hmSecRouterLocalNetmask, and hmSecRouterExternStaticGateway
	  objects are activated. When read and one or more of the above
	  mentioned objects have been cached, valuescached(2) is returned,
	  not regarding whether the cached valued and the current value
	  are different."
   ::= { hmSecRouterLocal 3 }

--
-- Network Internal Aliases
--

   hmSecRouterLocalAliasesTable OBJECT-TYPE
    SYNTAX SEQUENCE OF HmSecRouterLocalAliasesEntry
    ACCESS not-accessible
    STATUS mandatory
    DESCRIPTION
     "A table containing aliases for the local interface."
   ::= { hmSecRouterLocal 4 }

   hmSecRouterLocalAliasesEntry OBJECT-TYPE
    SYNTAX HmSecRouterLocalAliasesEntry
    ACCESS not-accessible
    STATUS mandatory
    DESCRIPTION
     "An entry  containing a single alias for the local interface."
    INDEX { hmSecLocalAliasIndex }
   ::= { hmSecRouterLocalAliasesTable 1 }

   HmSecRouterLocalAliasesEntry ::= SEQUENCE {
     hmSecLocalAliasIndex      INTEGER,
     hmSecLocalAliasIpAddress  IpAddress,
     hmSecLocalAliasNetmask    IpAddress,
     hmSecLocalAliasRowStatus  RowStatus,
     hmSecLocalAliasUseVLAN    INTEGER,
     hmSecLocalAliasVLANid     INTEGER
   }

   hmSecLocalAliasIndex OBJECT-TYPE
     SYNTAX INTEGER(1..100)
     ACCESS not-accessible
     STATUS mandatory
     DESCRIPTION
       "Identifier."
     ::= { hmSecRouterLocalAliasesEntry 1 }

   hmSecLocalAliasIpAddress OBJECT-TYPE
     SYNTAX IpAddress
     ACCESS read-write
     STATUS mandatory
     DESCRIPTION
       "IP address."
     ::= { hmSecRouterLocalAliasesEntry 2 }

   hmSecLocalAliasNetmask OBJECT-TYPE
    SYNTAX IpAddress
     ACCESS read-write
     STATUS mandatory
     DESCRIPTION
       "Netmask."
     ::= { hmSecRouterLocalAliasesEntry 3 }

    hmSecLocalAliasRowStatus OBJECT-TYPE
     SYNTAX RowStatus
     ACCESS read-write
     STATUS mandatory
     DESCRIPTION
       "RowStatus"
    ::= { hmSecRouterLocalAliasesEntry 4 }

    hmSecLocalAliasUseVLAN OBJECT-TYPE
     SYNTAX INTEGER{
                      yes(1),
    		      no(2)
 	             }
     ACCESS read-write
     STATUS mandatory
     DESCRIPTION
       "Use VLAn tagging with this Alias interface."
    ::= { hmSecRouterLocalAliasesEntry 5 }

    hmSecLocalAliasVLANid OBJECT-TYPE
     SYNTAX INTEGER
     ACCESS read-write
     STATUS mandatory
     DESCRIPTION
       "VLAN ID to be used with this Alias."
    ::= { hmSecRouterLocalAliasesEntry 6 }


--
-- Network Internal Routes
--

    hmSecLocalRoutesTable OBJECT-TYPE
     SYNTAX SEQUENCE OF HmSecLocalRoutesEntry
     ACCESS not-accessible
     STATUS mandatory
     DESCRIPTION
      "A table containing additional internal routes interface."
    ::= { hmSecRouterLocal 5 }

    hmSecLocalRoutesEntry OBJECT-TYPE
     SYNTAX HmSecLocalRoutesEntry
     ACCESS not-accessible
     STATUS mandatory
     DESCRIPTION
      "An entry  containing a single internal route."
     INDEX { hmSecLocalRouteIndex }
    ::= { hmSecLocalRoutesTable 1 }

    HmSecLocalRoutesEntry ::= SEQUENCE {
      hmSecLocalRouteIndex      INTEGER,
      hmSecLocalRouteNetwork    DisplayString,
      hmSecLocalRouteGateway    IpAddress,
      hmSecLocalRouteRowStatus  RowStatus
   }

   hmSecLocalRouteIndex OBJECT-TYPE
     SYNTAX INTEGER(1..100)
     ACCESS not-accessible
     STATUS mandatory
     DESCRIPTION
       "Identifier."
     ::= { hmSecLocalRoutesEntry 1 }

   hmSecLocalRouteNetwork OBJECT-TYPE
     SYNTAX DisplayString
     ACCESS read-write
     STATUS mandatory
     DESCRIPTION
       "Routed network."
     ::= { hmSecLocalRoutesEntry 2 }

    hmSecLocalRouteGateway OBJECT-TYPE
     SYNTAX IpAddress
     ACCESS read-write
     STATUS mandatory
     DESCRIPTION
       "Routing gateway."
     ::= { hmSecLocalRoutesEntry 3 }

     hmSecLocalRouteRowStatus OBJECT-TYPE
     SYNTAX RowStatus
     ACCESS read-write
     STATUS mandatory
     DESCRIPTION
       "RowStatus"
     ::= { hmSecLocalRoutesEntry 4 }


   hmSecRouterLocalDevMTU OBJECT-TYPE
     SYNTAX INTEGER
     ACCESS read-write
     STATUS mandatory
     DESCRIPTION
        "Set the MTU for the local interface. Router-Mode only."
    ::= { hmSecRouterLocal 6 }

   hmSecRouterLocalUseVLAN OBJECT-TYPE
     SYNTAX INTEGER{
                      yes(1),
    		      no(2)
 	             }
     ACCESS read-write
     STATUS mandatory
     DESCRIPTION
        "Use VLAN for the local interface. Router-Mode only."
    ::= { hmSecRouterLocal 7 }

   hmSecRouterLocalVlanId OBJECT-TYPE
     SYNTAX INTEGER
     ACCESS read-write
     STATUS mandatory
     DESCRIPTION
        "VLAN-ID for the local interface, used only if set to use VLAN. Router-Mode only."
    ::= { hmSecRouterLocal 8 }

   hmSecRouterLocalDevVlanMTU OBJECT-TYPE
     SYNTAX INTEGER
     ACCESS read-write
     STATUS mandatory
     DESCRIPTION
        "Set the MTU for the VLAN if enabled on local interface. Router-Mode only."
    ::= { hmSecRouterLocal 9 }



--
-- Network External IP
--

    hmSecRouterExtern OBJECT IDENTIFIER ::= { hmSecRouter 2 }

    hmSecRouterExternDHCP OBJECT-TYPE
     SYNTAX INTEGER {
			enabled(1),
			disabled(2)
		    }
     ACCESS read-write
     STATUS mandatory
     DESCRIPTION
        "When enabled, retrieve the external IP via DHCP, otherwise use
        the value stored in hmSecRouterExternStaticIP."
    ::= { hmSecRouterExtern 1 }

    hmSecRouterExternStatic  OBJECT IDENTIFIER ::= { hmSecRouterExtern 2 }

    hmSecRouterExternStaticIP OBJECT-TYPE
     SYNTAX IpAddress
     ACCESS read-write
     STATUS mandatory
     DESCRIPTION
        "The external IP address of this device in router mode
	 (when statically configured). When set, this value is internally
	 cached inside the agent until it is explicitly activated by writing
	 the hmSecRouterExternStaticActivate object. When read the currently
	 active setting is returned, not regarding any cached values."
    ::= { hmSecRouterExternStatic 1 }

    hmSecRouterExternStaticNetmask OBJECT-TYPE
     SYNTAX IpAddress
     ACCESS read-write
     STATUS mandatory
     DESCRIPTION
        "The external netmask of this device in router mode (when
	 statically configured). When set, this value is internally cached
	 inside the agent until it is explicitly activated by writing the
	 hmSecRouterExternStaticActivate object. When read the currently
	 active setting is returned, not regarding any cached values."
    ::= { hmSecRouterExternStatic 2 }

    hmSecRouterExternStaticGateway OBJECT-TYPE
     SYNTAX IpAddress
     ACCESS read-write
     STATUS mandatory
     DESCRIPTION
        "The (extern) default gateway of this device in router mode (when
	 statically configured). When set, this value is internally cached
	 inside the agent until it is explicitly activated by writing the
	 hmSecRouterExternStaticActivate  or hmSecRouterLocalActivate object.
	 When read the currently active setting is returned, not regarding
	 any cached values."
    ::= { hmSecRouterExternStatic 3 }

   hmSecRouterExternActivate OBJECT-TYPE
    SYNTAX INTEGER {
			activate(1),
			valuescached(2)
		   }
      ACCESS read-write
      STATUS mandatory
      DESCRIPTION
         "Button to activate the router extern IP configuration. When
	  activate(1) is written, any cached values for the
	  hmSecRouterExternStaticIP, hmSecRouterExternStaticNetmask, and
	  hmSecRouterExternStaticGateway objects are activated. When read
	  and one or more of the above mentioned objects have been cached,
	  valuescached(2) is returned, not regarding whether the cached valued
	  and the current value are different."
   ::= { hmSecRouterExternStatic 4 }


   hmSecRouterExternDevMTU OBJECT-TYPE
     SYNTAX INTEGER
     ACCESS read-write
     STATUS mandatory
     DESCRIPTION
        "Set the MTU for the external interface. Router-Mode only."
    ::= { hmSecRouterExtern 6 }

   hmSecRouterExternUseVLAN OBJECT-TYPE
     SYNTAX INTEGER{
                      yes(1),
    		      no(2)
 	             }
     ACCESS read-write
     STATUS mandatory
     DESCRIPTION
        "Use VLAN for the external interface. Router-Mode only."
    ::= { hmSecRouterExtern 7 }

   hmSecRouterExternVlanId OBJECT-TYPE
     SYNTAX INTEGER
     ACCESS read-write
     STATUS mandatory
     DESCRIPTION
        "VLAN-ID for the external interface, used only if set to use VLAN. Router-Mode only."
    ::= { hmSecRouterExtern 8 }

   hmSecRouterExternDevVlanMTU OBJECT-TYPE
     SYNTAX INTEGER
     ACCESS read-write
     STATUS mandatory
     DESCRIPTION
        "Set the MTU for the VLAN if enabled on external interface. Router-Mode only."
    ::= { hmSecRouterExtern 9 }



--
-- Network External Aliases
--

  hmSecRouterExternAliasesTable OBJECT-TYPE
    SYNTAX SEQUENCE OF HmSecRouterExternAliasesEntry
    ACCESS not-accessible
    STATUS mandatory
    DESCRIPTION
     "A table containing aliases for the external interface."
   ::= { hmSecRouterExternStatic 5 }

   hmSecRouterExternAliasesEntry OBJECT-TYPE
    SYNTAX HmSecRouterExternAliasesEntry
    ACCESS not-accessible
    STATUS mandatory
    DESCRIPTION
     "An entry  containing a single alias for the extern interface."
    INDEX { hmSecExternAliasIndex }
   ::= { hmSecRouterExternAliasesTable 1 }

   HmSecRouterExternAliasesEntry ::= SEQUENCE {
     hmSecExternAliasIndex      INTEGER,
     hmSecExternAliasIpAddress  IpAddress,
     hmSecExternAliasNetmask    IpAddress,
     hmSecExternAliasRowStatus  RowStatus,
     hmSecExternAliasUseVLAN    INTEGER,
     hmSecExternAliasVLANid     INTEGER
   }

   hmSecExternAliasIndex OBJECT-TYPE
     SYNTAX INTEGER(1..100)
     ACCESS not-accessible
     STATUS mandatory
     DESCRIPTION
       "Identifier."
     ::= { hmSecRouterExternAliasesEntry 1 }

   hmSecExternAliasIpAddress OBJECT-TYPE
     SYNTAX IpAddress
     ACCESS read-write
     STATUS mandatory
     DESCRIPTION
       "IP address."
     ::= { hmSecRouterExternAliasesEntry 2 }

   hmSecExternAliasNetmask OBJECT-TYPE
    SYNTAX IpAddress
     ACCESS read-write
     STATUS mandatory
     DESCRIPTION
       "Netmask."
     ::= { hmSecRouterExternAliasesEntry 3 }

    hmSecExternAliasRowStatus OBJECT-TYPE
     SYNTAX RowStatus
     ACCESS read-write
     STATUS mandatory
     DESCRIPTION
       "RowStatus"
    ::= { hmSecRouterExternAliasesEntry 4 }

    hmSecExternAliasUseVLAN OBJECT-TYPE
     SYNTAX INTEGER{
                      yes(1),
    		      no(2)
 	             }
     ACCESS read-write
     STATUS mandatory
     DESCRIPTION
       "Use VLAn tagging with this Alias interface."
    ::= { hmSecRouterExternAliasesEntry 5 }

    hmSecExternAliasVLANid OBJECT-TYPE
     SYNTAX INTEGER
     ACCESS read-write
     STATUS mandatory
     DESCRIPTION
       "VLAN ID to be used with this Alias."
    ::= { hmSecRouterExternAliasesEntry 6 }


--
-- Network External Routes
--

    hmSecExternRoutesTable OBJECT-TYPE
     SYNTAX SEQUENCE OF HmSecExternRoutesEntry
     ACCESS not-accessible
     STATUS mandatory
     DESCRIPTION
      "A table containing additional external routes."
    ::= { hmSecRouterExternStatic 6 }

    hmSecExternRoutesEntry OBJECT-TYPE
     SYNTAX HmSecExternRoutesEntry
     ACCESS not-accessible
     STATUS mandatory
     DESCRIPTION
      "An entry  containing a single external route."
     INDEX { hmSecExternRouteIndex }
    ::= { hmSecExternRoutesTable 1 }

    HmSecExternRoutesEntry ::= SEQUENCE {
      hmSecExternRouteIndex      INTEGER,
      hmSecExternRouteNetwork    DisplayString,
      hmSecExternRouteGateway    IpAddress,
      hmSecExternRouteRowStatus  RowStatus
   }

   hmSecExternRouteIndex OBJECT-TYPE
     SYNTAX INTEGER(1..100)
     ACCESS not-accessible
     STATUS mandatory
     DESCRIPTION
       "Identifier."
     ::= { hmSecExternRoutesEntry 1 }

   hmSecExternRouteNetwork OBJECT-TYPE
     SYNTAX DisplayString
     ACCESS read-write
     STATUS mandatory
     DESCRIPTION
       "Routed network."
     ::= { hmSecExternRoutesEntry 2 }

    hmSecExternRouteGateway OBJECT-TYPE
     SYNTAX IpAddress
     ACCESS read-write
     STATUS mandatory
     DESCRIPTION
       "Routing gateway."
     ::= { hmSecExternRoutesEntry 3 }

     hmSecExternRouteRowStatus OBJECT-TYPE
     SYNTAX RowStatus
     ACCESS read-write
     STATUS mandatory
     DESCRIPTION
       "RowStatus"
     ::= { hmSecExternRoutesEntry 4 }


--
-- HiDiscovery in RouterMode
--
   hmSecRouterHiDiscovery OBJECT IDENTIFIER ::= { hmSecRouter 3 }
 
    hmSecRouterHiDiscoveryIntern OBJECT-TYPE
      SYNTAX INTEGER {
			read-write(1),
			read-only(2),
			disabled(3)
		     }
      ACCESS read-write
      STATUS mandatory
      DESCRIPTION
         "Enable HiDiscovery on internal interface in RouterMode."
   ::= { hmSecRouterHiDiscovery 1 }
 
    hmSecRouterHiDiscoveryExtern OBJECT-TYPE
      SYNTAX INTEGER {
			read-write(1),
			read-only(2),
			disabled(3)
		     }
      ACCESS read-write
      STATUS mandatory
      DESCRIPTION
         "Enable HiDiscovery on external interface in RouterMode."
   ::= { hmSecRouterHiDiscovery 2 }
 
 

--
-- Network PPPoE
--

   hmSecPPPOE OBJECT IDENTIFIER ::= { hmSecNetwork 4 }

   hmSecPPPOELogin OBJECT-TYPE
    SYNTAX DisplayString
    ACCESS read-write
    STATUS mandatory
    DESCRIPTION
      "PPPoE login user name."
   ::= { hmSecPPPOE 1 }

   hmSecPPPOEPasswd OBJECT-TYPE
    SYNTAX DisplayString
    ACCESS read-write
    STATUS mandatory
    DESCRIPTION
       "PPPoE login password."
   ::={ hmSecPPPOE 2 }

   hmSecPPPOEMSS OBJECT-TYPE
    SYNTAX DisplayString
    ACCESS read-write
    STATUS mandatory
    DESCRIPTION
       "The maximum segment size used for PPPoE"
   ::={ hmSecPPPOE 3 }

   hmSecPPPOEServiceName OBJECT-TYPE
    SYNTAX DisplayString
    ACCESS read-write
    STATUS obsolete
    DESCRIPTION
       "The service name used for PPPoE, normally not used!"
   ::={ hmSecPPPOE 4 }

   hmSecPPPOEAccessConcentName OBJECT-TYPE
    SYNTAX DisplayString
    ACCESS read-write
    STATUS obsolete
    DESCRIPTION
       "The access concentrator name used for PPPoE, normally not used!"
   ::={ hmSecPPPOE 5 }

   hmSecPPPOEHostUnique OBJECT-TYPE
    SYNTAX INTEGER {
			enabled(1),
			disabled(2)
		   }
    ACCESS read-write
    STATUS obsolete
    DESCRIPTION
      "Set 'Host-Unique' tag for discovery, required for operation with
       several daemons"
   ::={ hmSecPPPOE 6 }

  hmSecPPPOEpppdOptionsTable OBJECT-TYPE
    SYNTAX SEQUENCE OF HmSecPPPOEpppdOptionsEntry
    ACCESS not-accessible
    STATUS mandatory
    DESCRIPTION
      "A table of options set for the pppd process implementing PPPOE."
   ::= { hmSecPPPOE 7 }

  hmSecPPPOEpppdOptionsEntry OBJECT-TYPE
      SYNTAX HmSecPPPOEpppdOptionsEntry
      ACCESS not-accessible
      STATUS mandatory
      DESCRIPTION
       "A single option set for pppd. "
      INDEX { hmSecPPPOEpppdOptionsIndex }
  ::= { hmSecPPPOEpppdOptionsTable 1 }

  HmSecPPPOEpppdOptionsEntry  ::= SEQUENCE {
     hmSecPPPOEpppdOptionsIndex     INTEGER,
     hmSecPPPOEpppdOptionsValue     DisplayString,
     hmSecPPPOEpppdOptionsRowStatus RowStatus
  }

  hmSecPPPOEpppdOptionsIndex OBJECT-TYPE
    SYNTAX INTEGER (1..100)
    ACCESS not-accessible
    STATUS mandatory
    DESCRIPTION
      "Table index."
   ::= { hmSecPPPOEpppdOptionsEntry 1 }

   hmSecPPPOEpppdOptionsValue OBJECT-TYPE
    SYNTAX DisplayString
    ACCESS read-write
    STATUS mandatory
    DESCRIPTION
      "The pppd option."
   ::= { hmSecPPPOEpppdOptionsEntry 2 }

   hmSecPPPOEpppdOptionsRowStatus OBJECT-TYPE
    SYNTAX RowStatus
    ACCESS read-write
    STATUS mandatory
    DESCRIPTION
      "Row Status"
   ::= { hmSecPPPOEpppdOptionsEntry 3 }


--
-- DHCP Server & DHCP Relay
--

   hmSecDHCP OBJECT IDENTIFIER ::= { hmSecNetwork 5 }

   hmSecDHCPInt OBJECT IDENTIFIER ::= { hmSecDHCP 1 }
   hmSecDHCPExt OBJECT IDENTIFIER ::= { hmSecDHCP 2 }

   --
   -- Internal DHCP Server & Relay
   --

   hmSecDHCPIntStart OBJECT-TYPE
    SYNTAX INTEGER {
			enabled(1),
			disabled(2),
                        enabled-relay(3)
		   }
    ACCESS read-write
    STATUS mandatory
    DESCRIPTION
      "Enable the internal DHCP/DHCP Relay Server ?"
   ::={ hmSecDHCPInt 1 }

   --
   -- Internal DHCP Server
   --

   hmSecDHCPIntPoolEnable OBJECT-TYPE
    SYNTAX INTEGER {
			enabled(1),
			disabled(2)
		   }
    ACCESS read-write
    STATUS mandatory
    DESCRIPTION
      "Enable the dynamic DHCP Pool ?"
   ::={ hmSecDHCPInt 2 }

   hmSecDHCPIntRangeStart OBJECT-TYPE
    SYNTAX IpAddress
    ACCESS read-write
    STATUS mandatory
    DESCRIPTION
      "Start of ip range provided by the builtin DHCP Server for the internal network."
   ::={ hmSecDHCPInt 3 }

   hmSecDHCPIntRangeEnd OBJECT-TYPE
     SYNTAX IpAddress
     ACCESS read-write
     STATUS mandatory
     DESCRIPTION
        "End of ip range provided by the builtin DHCP Server for the internal network."
   ::={ hmSecDHCPInt 4 }

   hmSecDHCPIntNetmask OBJECT-TYPE
     SYNTAX IpAddress
     ACCESS read-write
     STATUS mandatory
     DESCRIPTION
        "Netmask provided by the builtin DHCP Server for the internal network."
    ::={ hmSecDHCPInt 5 }

   hmSecDHCPIntGateway OBJECT-TYPE
     SYNTAX IpAddress
     ACCESS read-write
     STATUS mandatory
     DESCRIPTION
        "Default gateway provided by the builtin DHCP Server for the internal network."
    ::={ hmSecDHCPInt 6 }

   hmSecDHCPIntDnsServer OBJECT-TYPE
     SYNTAX IpAddress
     ACCESS read-write
     STATUS mandatory
     DESCRIPTION
        "DNS Server provided by the builtin DHCP server."
    ::={ hmSecDHCPInt 7 }

   hmSecDHCPIntStaticTable OBJECT-TYPE
    SYNTAX SEQUENCE OF HmSecDHCPIntStaticEntry
    ACCESS not-accessible
    STATUS mandatory
    DESCRIPTION
      "A table containing static MAC-IP address allocations."
   ::= { hmSecDHCPInt 8 }

   hmSecDHCPIntStaticEntry OBJECT-TYPE
     SYNTAX HmSecDHCPIntStaticEntry
     ACCESS not-accessible
     STATUS mandatory
     DESCRIPTION
     "An entry containing a single MAC-IP address allocation."
     INDEX { hmSecDHCPIntStaticIndex }
    ::= { hmSecDHCPIntStaticTable 1 }

    HmSecDHCPIntStaticEntry ::= SEQUENCE {
         hmSecDHCPIntStaticIndex INTEGER,
         hmSecDHCPIntStaticMAC   MacAddress,
         hmSecDHCPIntStaticIP    IpAddress,
         hmSecDHCPIntStaticRowStatus   RowStatus
    }

    hmSecDHCPIntStaticIndex OBJECT-TYPE
     SYNTAX INTEGER (1..250)
     ACCESS not-accessible
     STATUS mandatory
     DESCRIPTION
       "Index to identify allocation entry."
    ::= { hmSecDHCPIntStaticEntry 1 }

    hmSecDHCPIntStaticMAC OBJECT-TYPE
     SYNTAX MacAddress
     ACCESS read-write
     STATUS mandatory
     DESCRIPTION
       "The client's MAC address"
    ::= { hmSecDHCPIntStaticEntry 2 }

    hmSecDHCPIntStaticIP OBJECT-TYPE
     SYNTAX IpAddress
     ACCESS read-write
     STATUS mandatory
     DESCRIPTION
       "The allocated IP address"
    ::= { hmSecDHCPIntStaticEntry 3 }

    hmSecDHCPIntStaticRowStatus OBJECT-TYPE
      SYNTAX RowStatus
      ACCESS read-write
      STATUS mandatory
      DESCRIPTION
        "RowStatus"
    ::= { hmSecDHCPIntStaticEntry 4 }

   hmSecDHCPIntBroadcast OBJECT-TYPE
     SYNTAX IpAddress
     ACCESS read-write
     STATUS mandatory
     DESCRIPTION
        "Broadcast address provided by the builtin DHCP server."
    ::={ hmSecDHCPInt 9 }

   hmSecDHCPIntWINS OBJECT-TYPE
     SYNTAX IpAddress
     ACCESS read-write
     STATUS mandatory
     DESCRIPTION
        "WINS provided by the builtin DHCP Server for the internal network."
    ::={ hmSecDHCPInt 10 }

   hmSecDHCPIntLeaseTime OBJECT-TYPE
    SYNTAX INTEGER
    ACCESS read-write
    STATUS mandatory
    DESCRIPTION
      "Lifetime for DHCP Leases"
   ::={ hmSecDHCPInt 11 }

   --
   -- Internal DHCP Relay Server
   --

   hmSecDHCPIntRelayServerTable OBJECT-TYPE
    SYNTAX SEQUENCE OF HmSecDHCPIntRelayServerEntry
    ACCESS not-accessible
    STATUS mandatory
    DESCRIPTION
      "List of DHCP Servers to relay to."
   ::= { hmSecDHCPInt 50 }

   hmSecDHCPIntRelayServerEntry OBJECT-TYPE
     SYNTAX HmSecDHCPIntRelayServerEntry
     ACCESS not-accessible
     STATUS mandatory
     DESCRIPTION
     "An entry containing a DHCP Relay Server IP."
     INDEX { hmSecDHCPIntRelayServerIndex }
    ::= { hmSecDHCPIntRelayServerTable 1 }

    HmSecDHCPIntRelayServerEntry ::= SEQUENCE {
         hmSecDHCPIntRelayServerIndex INTEGER,
         hmSecDHCPIntRelayServerIP    IpAddress,
         hmSecDHCPIntRelayRowStatus   RowStatus
    }

    hmSecDHCPIntRelayServerIndex OBJECT-TYPE
     SYNTAX INTEGER (1..100)
     ACCESS not-accessible
     STATUS mandatory
     DESCRIPTION
       "Index to identify relay server entry."
    ::= { hmSecDHCPIntRelayServerEntry 1 }

    hmSecDHCPIntRelayServerIP OBJECT-TYPE
     SYNTAX IpAddress
     ACCESS read-write
     STATUS mandatory
     DESCRIPTION
       "The allocated IP address"
    ::= { hmSecDHCPIntRelayServerEntry 2 }

    hmSecDHCPIntRelayRowStatus OBJECT-TYPE
      SYNTAX RowStatus
      ACCESS read-write
      STATUS mandatory
      DESCRIPTION
        "RowStatus"
    ::= { hmSecDHCPIntRelayServerEntry 10 }

   hmSecDHCPIntRelayMaxHop OBJECT-TYPE
    SYNTAX INTEGER
    ACCESS read-write
    STATUS mandatory
    DESCRIPTION
      "Maximal number of Hops when relaying."
   ::={ hmSecDHCPInt 51 }

   hmSecDHCPIntRelayAppend OBJECT-TYPE
    SYNTAX TruthValue
    ACCESS read-write
    STATUS mandatory
    DESCRIPTION
      "Whether to append DHCP Relay Agent Information."
   ::={ hmSecDHCPInt 52 }

   hmSecDHCPIntRelayAppendLimit OBJECT-TYPE
    SYNTAX INTEGER
    ACCESS read-write
    STATUS mandatory
    DESCRIPTION
      "When appending DHCP Relay Agent Information would exceed
      this limit, it is not appended."
   ::={ hmSecDHCPInt 53 }

   hmSecDHCPIntRelayCircuitInfo OBJECT-TYPE
     SYNTAX INTEGER {
			none(1),
			if-idx(2),
			if-name(3),
			if-mac(4),
			if-ip(5),
			sysname(6),
			text(7),
			if-prefixed-ip(8),
                        rs2(9)
		    }
     ACCESS read-write
     STATUS mandatory
     DESCRIPTION
       "What to append as Circuit ID:
        none: no Cicuit ID
        if-idx: the system interface index (1 octet)
        if-name: the systems interface name (ascii)
        if-mac: the MAC address (6 octets)
        if-ip: the IP address (4 octets)
        sysname: the systems hostname
        text: a text defined in hmSecDHCPIntRelayCircuitText.0
        if-prefixed-ip: prefix IP with 0xA1 Sub Remote ID (2+4 octets)
        rs2: Hirschmann RS2 Sub Circuit Information"
    ::={ hmSecDHCPInt 54 }

   hmSecDHCPIntRelayCircuitText OBJECT-TYPE
     SYNTAX DisplayString
     ACCESS read-write
     STATUS mandatory
     DESCRIPTION
        "Text in case hmSecDHCPIntRelayCircuitInfo.0 is set to text(7)."
    ::= { hmSecDHCPInt 55 }

   hmSecDHCPIntRelayRemoteInfo OBJECT-TYPE
     SYNTAX INTEGER {
			none(1),
			if-idx(2),
			if-name(3),
			if-mac(4),
			if-ip(5),
			sysname(6),
			text(7),
			if-prefixed-ip(8),
                        rs2(9)
		    }
     ACCESS read-write
     STATUS mandatory
     DESCRIPTION
       "What to append as Remote ID:
        none: no Cicuit ID
        if-idx: the system interface index (1 octet)
        if-name: the systems interface name (ascii)
        if-mac: the MAC address (6 octets)
        if-ip: the IP address (4 octets)
        sysname: the systems hostname
        text: a text defined in hmSecDHCPIntRelayRemoteText.0
        if-prefixed-ip: prefix IP with 0xA1 Sub Remote ID (2+4 octets)
        rs2: Hirschmann RS2 Sub Circuit Information"
    ::={ hmSecDHCPInt 56 }

   hmSecDHCPIntRelayRemoteText OBJECT-TYPE
     SYNTAX DisplayString
     ACCESS read-write
     STATUS mandatory
     DESCRIPTION
        "Text in case hmSecDHCPIntRelayRemoteInfo.0 is set to text(7)."
    ::= { hmSecDHCPInt 57 }

   --
   -- External DHCP Server & Relay
   --

   hmSecDHCPExtStart OBJECT-TYPE
    SYNTAX INTEGER {
			enabled(1),
			disabled(2),
                        enabled-relay(3)
		   }
    ACCESS read-write
    STATUS mandatory
    DESCRIPTION
      "Enable the external DHCP/DHCP Relay Server ?"
   ::={ hmSecDHCPExt 1 }

   --
   -- External DHCP Server
   --

   hmSecDHCPExtPoolEnable OBJECT-TYPE
    SYNTAX INTEGER {
			enabled(1),
			disabled(2)
		   }
    ACCESS read-write
    STATUS mandatory
    DESCRIPTION
      "Enable the dynamic DHCP Pool ?"
   ::={ hmSecDHCPExt 2 }

   hmSecDHCPExtRangeStart OBJECT-TYPE
    SYNTAX IpAddress
    ACCESS read-write
    STATUS mandatory
    DESCRIPTION
      "Start of ip range provided by the builtin DHCP Server for the external network."
   ::={ hmSecDHCPExt 3 }

   hmSecDHCPExtRangeEnd OBJECT-TYPE
     SYNTAX IpAddress
     ACCESS read-write
     STATUS mandatory
     DESCRIPTION
        "End of ip range provided by the builtin DHCP Server for the external network."
   ::={ hmSecDHCPExt 4 }

   hmSecDHCPExtNetmask OBJECT-TYPE
     SYNTAX IpAddress
     ACCESS read-write
     STATUS mandatory
     DESCRIPTION
        "Netmask provided by the builtin DHCP Server for the external network."
    ::={ hmSecDHCPExt 5 }

   hmSecDHCPExtGateway OBJECT-TYPE
     SYNTAX IpAddress
     ACCESS read-write
     STATUS mandatory
     DESCRIPTION
        "Default gateway provided by the builtin DHCP Server for the external network."
    ::={ hmSecDHCPExt 6 }

   hmSecDHCPExtDnsServer OBJECT-TYPE
     SYNTAX IpAddress
     ACCESS read-write
     STATUS mandatory
     DESCRIPTION
        "DNS Server provided by the builtin DHCP server."
    ::={ hmSecDHCPExt 7 }

   hmSecDHCPExtStaticTable OBJECT-TYPE
    SYNTAX SEQUENCE OF HmSecDHCPExtStaticEntry
    ACCESS not-accessible
    STATUS mandatory
    DESCRIPTION
      "A table containing static MAC-IP address allocations."
   ::= { hmSecDHCPExt 8 }

   hmSecDHCPExtStaticEntry OBJECT-TYPE
     SYNTAX HmSecDHCPExtStaticEntry
     ACCESS not-accessible
     STATUS mandatory
     DESCRIPTION
     "An entry containing a single MAC-IP address allocation."
     INDEX { hmSecDHCPExtStaticIndex }
    ::= { hmSecDHCPExtStaticTable 1 }

    HmSecDHCPExtStaticEntry ::= SEQUENCE {
         hmSecDHCPExtStaticIndex INTEGER,
         hmSecDHCPExtStaticMAC   MacAddress,
         hmSecDHCPExtStaticIP    IpAddress,
         hmSecDHCPExtStaticRowStatus   RowStatus
    }

    hmSecDHCPExtStaticIndex OBJECT-TYPE
     SYNTAX INTEGER (1..250)
     ACCESS not-accessible
     STATUS mandatory
     DESCRIPTION
       "Index to identify allocation entry."
    ::= { hmSecDHCPExtStaticEntry 1 }

    hmSecDHCPExtStaticMAC OBJECT-TYPE
     SYNTAX MacAddress
     ACCESS read-write
     STATUS mandatory
     DESCRIPTION
       "The client's MAC address"
    ::= { hmSecDHCPExtStaticEntry 2 }

    hmSecDHCPExtStaticIP OBJECT-TYPE
     SYNTAX IpAddress
     ACCESS read-write
     STATUS mandatory
     DESCRIPTION
       "The allocated IP address"
    ::= { hmSecDHCPExtStaticEntry 3 }

    hmSecDHCPExtStaticRowStatus OBJECT-TYPE
      SYNTAX RowStatus
      ACCESS read-write
      STATUS mandatory
      DESCRIPTION
        "RowStatus"
    ::= { hmSecDHCPExtStaticEntry 4 }

   hmSecDHCPExtBroadcast OBJECT-TYPE
     SYNTAX IpAddress
     ACCESS read-write
     STATUS mandatory
     DESCRIPTION
        "Broadcast address provided by the builtin DHCP server."
    ::={ hmSecDHCPExt 9 }

   hmSecDHCPExtWINS OBJECT-TYPE
     SYNTAX IpAddress
     ACCESS read-write
     STATUS mandatory
     DESCRIPTION
        "WINS provided by the builtin DHCP Server for the external network."
    ::={ hmSecDHCPExt 10 }

   hmSecDHCPExtLeaseTime OBJECT-TYPE
    SYNTAX INTEGER
    ACCESS read-write
    STATUS mandatory
    DESCRIPTION
      "Lifetime for DHCP Leases"
   ::={ hmSecDHCPExt 11 }

   --
   -- External DHCP Relay Server
   --

   hmSecDHCPExtRelayServerTable OBJECT-TYPE
    SYNTAX SEQUENCE OF HmSecDHCPExtRelayServerEntry
    ACCESS not-accessible
    STATUS mandatory
    DESCRIPTION
      "List of DHCP Servers to relay to."
   ::= { hmSecDHCPExt 50 }

   hmSecDHCPExtRelayServerEntry OBJECT-TYPE
     SYNTAX HmSecDHCPExtRelayServerEntry
     ACCESS not-accessible
     STATUS mandatory
     DESCRIPTION
     "An entry containing a DHCP Relay Server IP."
     INDEX { hmSecDHCPExtRelayServerIndex }
    ::= { hmSecDHCPExtRelayServerTable 1 }

    HmSecDHCPExtRelayServerEntry ::= SEQUENCE {
         hmSecDHCPExtRelayServerIndex INTEGER,
         hmSecDHCPExtRelayServerIP    IpAddress,
         hmSecDHCPExtRelayRowStatus   RowStatus
    }

    hmSecDHCPExtRelayServerIndex OBJECT-TYPE
     SYNTAX INTEGER (1..100)
     ACCESS not-accessible
     STATUS mandatory
     DESCRIPTION
       "Index to identify relay server entry."
    ::= { hmSecDHCPExtRelayServerEntry 1 }

    hmSecDHCPExtRelayServerIP OBJECT-TYPE
     SYNTAX IpAddress
     ACCESS read-write
     STATUS mandatory
     DESCRIPTION
       "The allocated IP address"
    ::= { hmSecDHCPExtRelayServerEntry 2 }

    hmSecDHCPExtRelayRowStatus OBJECT-TYPE
      SYNTAX RowStatus
      ACCESS read-write
      STATUS mandatory
      DESCRIPTION
        "RowStatus"
    ::= { hmSecDHCPExtRelayServerEntry 10 }

   hmSecDHCPExtRelayMaxHop OBJECT-TYPE
    SYNTAX INTEGER
    ACCESS read-write
    STATUS mandatory
    DESCRIPTION
      "Maximal number of Hops when relaying."
   ::={ hmSecDHCPExt 51 }

   hmSecDHCPExtRelayAppend OBJECT-TYPE
    SYNTAX TruthValue
    ACCESS read-write
    STATUS mandatory
    DESCRIPTION
      "Whether to append DHCP Relay Agent Information."
   ::={ hmSecDHCPExt 52 }

   hmSecDHCPExtRelayAppendLimit OBJECT-TYPE
    SYNTAX INTEGER
    ACCESS read-write
    STATUS mandatory
    DESCRIPTION
      "When appending DHCP Relay Agent Information would exceed
      this limit, it is not appended."
   ::={ hmSecDHCPExt 53 }

   hmSecDHCPExtRelayCircuitInfo OBJECT-TYPE
     SYNTAX INTEGER {
			none(1),
			if-idx(2),
			if-name(3),
			if-mac(4),
			if-ip(5),
			sysname(6),
			text(7),
			if-prefixed-ip(8),
                        rs2(9)
		    }
     ACCESS read-write
     STATUS mandatory
     DESCRIPTION
       "What to append as Circuit ID:
        none: no Cicuit ID
        if-idx: the system interface index (1 octet)
        if-name: the systems interface name (ascii)
        if-mac: the MAC address (6 octets)
        if-ip: the IP address (4 octets)
        sysname: the systems hostname
        text: a text defined in hmSecDHCPExtRelayCircuitText.0
        if-prefixed-ip: prefix IP with 0xA1 Sub Remote ID (2+4 octets)
        rs2: Hirschmann RS2 Sub Circuit Information"
    ::={ hmSecDHCPExt 54 }

   hmSecDHCPExtRelayCircuitText OBJECT-TYPE
     SYNTAX DisplayString
     ACCESS read-write
     STATUS mandatory
     DESCRIPTION
        "Text in case hmSecDHCPExtRelayCircuitInfo.0 is set to text(7)."
    ::= { hmSecDHCPExt 55 }

   hmSecDHCPExtRelayRemoteInfo OBJECT-TYPE
     SYNTAX INTEGER {
			none(1),
			if-idx(2),
			if-name(3),
			if-mac(4),
			if-ip(5),
			sysname(6),
			text(7),
			if-prefixed-ip(8),
                        rs2(9)
		    }
     ACCESS read-write
     STATUS mandatory
     DESCRIPTION
       "What to append as Remote ID:
        none: no Cicuit ID
        if-idx: the system interface index (1 octet)
        if-name: the systems interface name (ascii)
        if-mac: the MAC address (6 octets)
        if-ip: the IP address (4 octets)
        sysname: the systems hostname
        text: a text defined in hmSecDHCPExtRelayRemoteText.0
        if-prefixed-ip: prefix IP with 0xA1 Sub Remote ID (2+4 octets)
        rs2: Hirschmann RS2 Sub Circuit Information"
    ::={ hmSecDHCPExt 56 }

   hmSecDHCPExtRelayRemoteText OBJECT-TYPE
     SYNTAX DisplayString
     ACCESS read-write
     STATUS mandatory
     DESCRIPTION
        "Text in case hmSecDHCPExtRelayRemoteInfo.0 is set to text(7)."
    ::= { hmSecDHCPExt 57 }


--
-- Network DNS
--

    hmSecDNS OBJECT IDENTIFIER ::= { hmSecNetwork 6 }

    hmSecDNSSearchPath OBJECT-TYPE
     SYNTAX DisplayString
     ACCESS read-write
     STATUS mandatory
     DESCRIPTION
        "Domain search path."
    ::= { hmSecDNS 1 }

    hmSecDNSServerType OBJECT-TYPE
     SYNTAX INTEGER {
			root(1),
			provider(2),
			user(3)
		    }
     ACCESS read-write
     STATUS mandatory
     DESCRIPTION
        "Type of DNS Servers to query:
         root: DNS root servers
         provider: Provider defined DNS Servers (via DHCP,PPPOE)
         user: User defined DNS Servers"
    ::={ hmSecDNS 2 }

    hmSecDNSUserDefinedServerTable OBJECT-TYPE
     SYNTAX SEQUENCE OF HmSecDNSUserDefinedServerEntry
     ACCESS not-accessible
     STATUS mandatory
     DESCRIPTION
       " A table containing user defined DNS Servers"
    ::={ hmSecDNS 3 }

    hmSecDNSUserDefinedServerEntry OBJECT-TYPE
     SYNTAX HmSecDNSUserDefinedServerEntry
     ACCESS not-accessible
     STATUS mandatory
     DESCRIPTION
       "A hmSecDNSServer entry."
     INDEX { hmSecdnsServerIndex }
    ::={ hmSecDNSUserDefinedServerTable 1 }

    HmSecDNSUserDefinedServerEntry ::= SEQUENCE {
      hmSecdnsServerIndex INTEGER,
      hmSecdnsServerIP    IpAddress,
      hmSecdnsServerRowStatus RowStatus
    }

    hmSecdnsServerIndex OBJECT-TYPE
     SYNTAX INTEGER (1..100)
     ACCESS not-accessible
     STATUS mandatory
     DESCRIPTION
       "Index to identify DNS Server entry."
    ::= { hmSecDNSUserDefinedServerEntry 1 }

    hmSecdnsServerIP OBJECT-TYPE
     SYNTAX IpAddress
     ACCESS read-write
     STATUS mandatory
     DESCRIPTION
      "DNS Server IP address."
    ::= { hmSecDNSUserDefinedServerEntry 2 }

    hmSecdnsServerRowStatus OBJECT-TYPE
      SYNTAX RowStatus
      ACCESS read-write
      STATUS mandatory
      DESCRIPTION
       "RowStatus"
    ::= { hmSecDNSUserDefinedServerEntry 3 }

    hmSecDNSCacheEnabled OBJECT-TYPE
     SYNTAX INTEGER {
			enabled(1),
			disabled(2)
		    }
     ACCESS read-write
     STATUS mandatory
     DESCRIPTION
        "Enable or disable built-in DNS cache feature"
    ::= { hmSecDNS 4 }


--
-- NetworkStatus
--

   hmSecNetworkStatus OBJECT IDENTIFIER ::= { hmSecNetwork 7 }

   hmSecNetworkStatMode OBJECT-TYPE
     SYNTAX DisplayString
     ACCESS read-only
     STATUS mandatory
     DESCRIPTION
      "Current network mode of this device."
    ::= { hmSecNetworkStatus 1 }

    hmSecNetworkStatExtIP OBJECT-TYPE
     SYNTAX DisplayString
     ACCESS read-only
     STATUS mandatory
     DESCRIPTION
      "external IP address of this device."
    ::= { hmSecNetworkStatus 2 }

   hmSecNetworkStatGateway OBJECT-TYPE
     SYNTAX DisplayString
     ACCESS read-only
     STATUS mandatory
     DESCRIPTION
      "Default gateway via the external IP address."
    ::= { hmSecNetworkStatus 3 }

   hmSecNetworkStatVPN OBJECT-TYPE
     SYNTAX DisplayString
     ACCESS read-only
     STATUS mandatory
     DESCRIPTION
      "Statistics about the VPN connections (total/used/up)."
    ::= { hmSecNetworkStatus 4 }

   hmSecNetworkStatDynIPReg OBJECT-TYPE
     SYNTAX DisplayString
     ACCESS read-only
     STATUS mandatory
     DESCRIPTION
      "Statistics about VPN DynIP registration."
    ::= { hmSecNetworkStatus 5 }

   hmSecNetworkStatHTTPSRemAccess OBJECT-TYPE
     SYNTAX DisplayString
     ACCESS read-only
     STATUS mandatory
     DESCRIPTION
      "Status of HTTPS remote access (yes/no)."
    ::= { hmSecNetworkStatus 6 }

   hmSecNetworkStatSSHRemoteAccess OBJECT-TYPE
     SYNTAX DisplayString
     ACCESS read-only
     STATUS mandatory
     DESCRIPTION
      "Status of SSH remote access (yes/no)."
    ::= { hmSecNetworkStatus 7 }

   hmSecNetworkSoftwareVersion OBJECT-TYPE
     SYNTAX DisplayString
     ACCESS read-only
     STATUS mandatory
     DESCRIPTION
      "Current software version."
    ::= { hmSecNetworkStatus 8 }

   hmSecNetworkStatUptime OBJECT-TYPE
     SYNTAX DisplayString
     ACCESS read-only
     STATUS mandatory
     DESCRIPTION
      "Uptime."
    ::= { hmSecNetworkStatus 9 }

   hmSecNetworkStatLanguage OBJECT-TYPE
     SYNTAX DisplayString
     ACCESS read-only
     STATUS mandatory
     DESCRIPTION
      "GAI Language."
    ::= { hmSecNetworkStatus 10 }

--
-- Network Hostname
--

   hmSecHostname OBJECT-TYPE
    SYNTAX DisplayString
    ACCESS read-write
    STATUS mandatory
    DESCRIPTION
       "The hostname of this system"
   ::= { hmSecNetwork 8 }


   hmSecHostnameMode OBJECT-TYPE
    SYNTAX INTEGER {
                       userDefined(1),
                       providerDefined(2)
                   }
    ACCESS read-write
    STATUS mandatory
    DESCRIPTION
       "Hostname mode:
                      1: defined by hmSecHostname,
                      2: provider defined (e.g. DHCP)
       "
   ::= { hmSecNetwork 9 }

--
-- Network PPTP
--

  hmSecPPTP OBJECT IDENTIFIER ::= { hmSecNetwork 10 }

  hmSecPPTPLogin OBJECT-TYPE
    SYNTAX DisplayString
    ACCESS read-write
    STATUS mandatory
    DESCRIPTION
      "PPTP login"
  ::= { hmSecPPTP 1 }

  hmSecPPTPassword OBJECT-TYPE
    SYNTAX DisplayString
    ACCESS read-write
    STATUS mandatory
    DESCRIPTION
      "PPTP password"
  ::= { hmSecPPTP 2 }

  hmSecPPTPLocalIPMode OBJECT-TYPE
   SYNTAX INTEGER {
                     static(1),
		     dhcp(2)
                  }
   ACCESS read-write
   STATUS mandatory
   DESCRIPTION
     "When set to static will use the value from hmSecPPTPLocalIP on it
     external interface connecting to the PPTP server/modem. Otherwise it
     it use DHCP."
  ::= { hmSecPPTP 3 }

  hmSecPPTPLocalIP OBJECT-TYPE
   SYNTAX IpAddress
   ACCESS read-write
   STATUS mandatory
   DESCRIPTION
      "The external IP of this system when connecting to the PPTP server/modem
      when hmSecPPTPLocalIPMode is set to static."
  ::= { hmSecPPTP 4 }

  hmSecPPTPModemIP OBJECT-TYPE
   SYNTAX IpAddress
   ACCESS read-write
   STATUS mandatory
   DESCRIPTION
      "The IP of the PPTP server/modem."
  ::= { hmSecPPTP 5 }

  hmSecPPTPpppdOptionsTable OBJECT-TYPE
    SYNTAX SEQUENCE OF HmSecPPTPpppdOptionsEntry
    ACCESS not-accessible
    STATUS mandatory
    DESCRIPTION
      "A table of options set for the pppd process implementing PPTP."
   ::= { hmSecPPTP 6 }

  hmSecPPTPpppdOptionsEntry OBJECT-TYPE
      SYNTAX HmSecPPTPpppdOptionsEntry
      ACCESS not-accessible
      STATUS mandatory
      DESCRIPTION
       "A single option set for pppd. "
      INDEX { hmSecPPTPpppdOptionsIndex }
  ::= { hmSecPPTPpppdOptionsTable 1 }

  HmSecPPTPpppdOptionsEntry  ::= SEQUENCE {
     hmSecPPTPpppdOptionsIndex     INTEGER,
     hmSecPPTPpppdOptionsValue     DisplayString,
     hmSecPPTPpppdOptionsRowStatus RowStatus
  }

  hmSecPPTPpppdOptionsIndex OBJECT-TYPE
    SYNTAX INTEGER (1..100)
    ACCESS not-accessible
    STATUS mandatory
    DESCRIPTION
      "Table index."
   ::= { hmSecPPTPpppdOptionsEntry 1 }

   hmSecPPTPpppdOptionsValue OBJECT-TYPE
    SYNTAX DisplayString
    ACCESS read-write
    STATUS mandatory
    DESCRIPTION
      "The pppd option."
   ::= { hmSecPPTPpppdOptionsEntry 2 }

   hmSecPPTPpppdOptionsRowStatus OBJECT-TYPE
    SYNTAX RowStatus
    ACCESS read-write
    STATUS mandatory
    DESCRIPTION
      "Row Status"
   ::= { hmSecPPTPpppdOptionsEntry 3 }

--
-- hmSecSerial
--

  hmSecSerial OBJECT IDENTIFIER ::= { hmSecNetwork 11 }

    hmSecSerialBaud OBJECT-TYPE
      SYNTAX INTEGER
      ACCESS read-write
      STATUS mandatory
      DESCRIPTION
         "Baudrate for the serial line. Possible values are 9600, 19200,
         38400, 57600"
      ::= { hmSecSerial 1 }

    hmSecSerialHWHandshakeEnable OBJECT-TYPE
      SYNTAX INTEGER {
      	enabled(1),
      	disabled(2)
      }
      ACCESS read-write
      STATUS mandatory
      DESCRIPTION
         "Enable hardware handshake"
      ::= { hmSecSerial 2 }

    -- Serial PPP Options

    hmSecSerialPPP OBJECT IDENTIFIER ::= { hmSecSerial 3 }

    hmSecSerialPPPEnable OBJECT-TYPE
      SYNTAX INTEGER {
      	enabled(1),
      	disabled(2)
      }
      ACCESS read-write
      STATUS mandatory
      DESCRIPTION
         "Enable PPP"
      ::= { hmSecSerialPPP 1 }

    hmSecSerialPPPLogin OBJECT-TYPE
      SYNTAX DisplayString
      ACCESS read-write
      STATUS mandatory
      DESCRIPTION
        "Login for Serial PPP."
      ::= { hmSecSerialPPP 2 }

    hmSecSerialPPPPasswd OBJECT-TYPE
      SYNTAX DisplayString
      ACCESS read-write
      STATUS mandatory
      DESCRIPTION
        "Password for Serial PPP."
      ::= { hmSecSerialPPP 3 }

    hmSecSerialPPPLocalIP OBJECT-TYPE
      SYNTAX IpAddress
      ACCESS read-write
      STATUS mandatory
      DESCRIPTION
        "Local IP address for PPP."
      ::= { hmSecSerialPPP 4 }

    hmSecSerialPPPRemoteIP OBJECT-TYPE
      SYNTAX IpAddress
      ACCESS read-write
      STATUS mandatory
      DESCRIPTION
        "Remote IP address for PPP."
      ::= { hmSecSerialPPP 5 }


-- Serial PPP Incoming Firewall

    hmSecSerialPPPFWIN  OBJECT IDENTIFIER ::= { hmSecSerialPPP 6 }
	
      hmSecSerialPPPFWINTable OBJECT-TYPE
        SYNTAX SEQUENCE OF HmSecSerialPPPFWINEntry
        ACCESS not-accessible
        STATUS mandatory
        DESCRIPTION
          "A table containing firewall rules for incoming  packets."
        ::= { hmSecSerialPPPFWIN 1 }

      hmSecSerialPPPFWINEntry OBJECT-TYPE
        SYNTAX HmSecSerialPPPFWINEntry
        ACCESS not-accessible
        STATUS mandatory
        DESCRIPTION
          "An entry containing data of a single rule."
        INDEX { hmSecFWINruleIndex }
      ::= { hmSecSerialPPPFWINTable 1 }

      HmSecSerialPPPFWINEntry ::= SEQUENCE{
        hmSecSerialPPPFWINruleIndex       INTEGER,
        hmSecSerialPPPFWINsourceIP        DisplayString,
        hmSecSerialPPPFWINdestinationIP   DisplayString,
        hmSecSerialPPPFWINsport           DisplayString,
        hmSecSerialPPPFWINdport           DisplayString,
        hmSecSerialPPPFWINtarget          INTEGER,
        hmSecSerialPPPFWINproto           INTEGER,
        hmSecSerialPPPFWINlog             INTEGER,
        hmSecSerialPPPFWINRowStatus       RowStatus,
        hmSecSerialPPPFWINcomment         DisplayString
      }

      hmSecSerialPPPFWINruleIndex OBJECT-TYPE
        SYNTAX   INTEGER (1..250)
        ACCESS   not-accessible
        STATUS   mandatory
        DESCRIPTION
          "Index to identify the rule."
      ::= { hmSecSerialPPPFWINEntry 1 }

      hmSecSerialPPPFWINsourceIP OBJECT-TYPE
        SYNTAX DisplayString
        ACCESS read-write
        STATUS mandatory
        DESCRIPTION
          "The rule's source IP address"
        ::= { hmSecSerialPPPFWINEntry 2 }

      hmSecSerialPPPFWINdestinationIP OBJECT-TYPE
        SYNTAX DisplayString
        ACCESS read-write
        STATUS mandatory
        DESCRIPTION
          "The rule's source IP address"
        ::= { hmSecSerialPPPFWINEntry 3 }

      hmSecSerialPPPFWINsport OBJECT-TYPE
        SYNTAX DisplayString
        ACCESS read-write
        STATUS mandatory
        DESCRIPTION
          "The rule's source port"
        ::= { hmSecSerialPPPFWINEntry 4 }

      hmSecSerialPPPFWINdport OBJECT-TYPE
        SYNTAX DisplayString
        ACCESS read-write
        STATUS mandatory
        DESCRIPTION
          "The rule's destination port"
        ::= { hmSecSerialPPPFWINEntry 5 }

      hmSecSerialPPPFWINtarget OBJECT-TYPE
        SYNTAX INTEGER {
          	  accept(1),
    		  reject(2),
    		  drop(3)
    		}
        ACCESS read-write
        STATUS mandatory
        DESCRIPTION
          "The rule's target"
        ::= { hmSecSerialPPPFWINEntry 6 }

      hmSecSerialPPPFWINproto OBJECT-TYPE
        SYNTAX INTEGER {
          tcp(1),
    		  udp(2),
    		  icmp(3),
    		  all(4)
        }
        ACCESS read-write
        STATUS mandatory
        DESCRIPTION
          "The rule's protocol"
        ::= { hmSecSerialPPPFWINEntry 7 }

      hmSecSerialPPPFWINlog OBJECT-TYPE
        SYNTAX INTEGER {
          yes(1),
          no(2)
        }
        ACCESS read-write
        STATUS mandatory
        DESCRIPTION
          "Log packets matching this rule ?"
        ::= { hmSecSerialPPPFWINEntry 8 }

      hmSecSerialPPPFWINRowStatus OBJECT-TYPE
        SYNTAX RowStatus
        ACCESS read-write
        STATUS mandatory
        DESCRIPTION
          "RowStatus"
        ::= { hmSecSerialPPPFWINEntry 9 }

       hmSecSerialPPPFWINcomment OBJECT-TYPE
        SYNTAX DisplayString
        ACCESS read-write
        STATUS mandatory
        DESCRIPTION
          "Commentary or name for this rule."
        ::= { hmSecSerialPPPFWINEntry 10 }
	
    hmSecSerialPPPFWINLogDefault OBJECT-TYPE
      SYNTAX INTEGER {
        yes(1),
        no(2)
      }
      ACCESS read-write
      STATUS mandatory
      DESCRIPTION
        "Log entries for undefined incoming connection attemps."
      ::= { hmSecSerialPPPFWIN 2 }

-- Serial PPP Outgoing Firewall

  hmSecSerialPPPFWOUT  OBJECT IDENTIFIER ::= { hmSecSerialPPP 7 }

  hmSecSerialPPPFWOUTTable OBJECT-TYPE
    SYNTAX SEQUENCE OF HmSecSerialPPPFWOUTEntry
    ACCESS not-accessible
    STATUS mandatory
    DESCRIPTION
      "A table containing firewall rules for incoming  packets."
    ::= { hmSecSerialPPPFWOUT 1 }

  hmSecSerialPPPFWOUTEntry OBJECT-TYPE
    SYNTAX HmSecSerialPPPFWOUTEntry
    ACCESS not-accessible
    STATUS mandatory
    DESCRIPTION
      "An entry containing data of a single rule."
    INDEX { hmSecSerialPPPFWOUTruleIndex }
    ::= { hmSecSerialPPPFWOUTTable 1 }

  HmSecSerialPPPFWOUTEntry ::= SEQUENCE{
    hmSecSerialPPPFWOUTruleIndex       INTEGER,
    hmSecSerialPPPFWOUTsourceIP        DisplayString,
    hmSecSerialPPPFWOUTtargetIP   	DisplayString,
    hmSecSerialPPPFWOUTsport           DisplayString,
    hmSecSerialPPPFWOUTdport           DisplayString,
    hmSecSerialPPPFWOUTtarget          INTEGER,
    hmSecSerialPPPFWOUTproto           INTEGER,
    hmSecSerialPPPFWOUTlog             INTEGER,
    hmSecSerialPPPFWOUTRowStatus       RowStatus,
    hmSecSerialPPPFWOUTcomment         DisplayString
  }

  hmSecSerialPPPFWOUTruleIndex OBJECT-TYPE
    SYNTAX   INTEGER (1..250)
    ACCESS   not-accessible
    STATUS   mandatory
    DESCRIPTION
      "Index to identify the rule."
  ::= { hmSecSerialPPPFWOUTEntry 1 }

  hmSecSerialPPPFWOUTsourceIP OBJECT-TYPE
    SYNTAX DisplayString
    ACCESS read-write
    STATUS mandatory
    DESCRIPTION
      "The rule's source IP address"
  ::= { hmSecSerialPPPFWOUTEntry 2 }

  hmSecSerialPPPFWOUTtargetIP OBJECT-TYPE
    SYNTAX DisplayString
    ACCESS read-write
    STATUS mandatory
    DESCRIPTION
      "The rule's source IP address"
    ::= { hmSecSerialPPPFWOUTEntry 3 }

  hmSecSerialPPPFWOUTsport OBJECT-TYPE
    SYNTAX DisplayString
    ACCESS read-write
    STATUS mandatory
    DESCRIPTION
      "The rule's source port"
    ::= { hmSecSerialPPPFWOUTEntry 4 }

  hmSecSerialPPPFWOUTdport OBJECT-TYPE
    SYNTAX DisplayString
    ACCESS read-write
    STATUS mandatory
    DESCRIPTION
      "The rule's destination port"
    ::= { hmSecSerialPPPFWOUTEntry 5 }

  hmSecSerialPPPFWOUTtarget OBJECT-TYPE
    SYNTAX INTEGER {
      accept(1),
		  reject(2),
		  drop(3)
		}
    ACCESS read-write
    STATUS mandatory
    DESCRIPTION
      "The rule's target"
    ::= { hmSecSerialPPPFWOUTEntry 6 }

  hmSecSerialPPPFWOUTproto OBJECT-TYPE
    SYNTAX INTEGER {
      tcp(1),
		  udp(2),
		  icmp(3),
		  all(4)
    }
    ACCESS read-write
    STATUS mandatory
    DESCRIPTION
      "The rule's protocol"
    ::= { hmSecSerialPPPFWOUTEntry 7 }

  hmSecSerialPPPFWOUTlog OBJECT-TYPE
    SYNTAX INTEGER {
      yes(1),
      no(2)
    }
    ACCESS read-write
    STATUS mandatory
    DESCRIPTION
      "Log packets matching this rule ?"
    ::= { hmSecSerialPPPFWOUTEntry 8 }

  hmSecSerialPPPFWOUTRowStatus OBJECT-TYPE
    SYNTAX RowStatus
    ACCESS read-write
    STATUS mandatory
    DESCRIPTION
      "RowStatus"
    ::= { hmSecSerialPPPFWOUTEntry 9 }

    hmSecSerialPPPFWOUTcomment OBJECT-TYPE
     SYNTAX DisplayString
     ACCESS read-write
     STATUS mandatory
     DESCRIPTION
       "Commentary or name for this rule."
     ::= { hmSecSerialPPPFWOUTEntry 10 }

  hmSecSerialPPPFWOUTLogDefault OBJECT-TYPE
    SYNTAX INTEGER{
      yes(1),
      no(2)
    }
    ACCESS read-write
    STATUS mandatory
    DESCRIPTION
      "Log entries for unknown outgoing connection attemps ?"
    ::= { hmSecSerialPPPFWOUT 2 }



--
-- ARP Timeout
--

   hmSecArpTimeout OBJECT-TYPE
    SYNTAX INTEGER
    ACCESS read-write
    STATUS mandatory
    DESCRIPTION
       "Global ARP timeout in seconds."
   ::= { hmSecNetwork 12 }



--
-- Passwords
--

    hmSecPasswords OBJECT IDENTIFIER ::= { hmSecSystem 1 }


    hmSecRootPassword OBJECT-TYPE
     SYNTAX DisplayString
     ACCESS read-write
     STATUS mandatory
     DESCRIPTION
       "Object to change the root password.
       Change by setting:  <old root password> <new root password>"
    ::= { hmSecPasswords 1 }

    hmSecAdminPassword OBJECT-TYPE
     SYNTAX DisplayString
     ACCESS read-write
     STATUS mandatory
     DESCRIPTION
       "Object to change the admin password."
    ::= { hmSecPasswords 2 }

    hmSecUserPassword OBJECT-TYPE
     SYNTAX DisplayString
     ACCESS read-write
     STATUS mandatory
     DESCRIPTION
       "Object to change the user password."
    ::= { hmSecPasswords 3 }

    hmSecUserPwdEnable OBJECT-TYPE
     SYNTAX TruthValue
     ACCESS read-write
     STATUS mandatory
     DESCRIPTION
       "Enable user password ?
           yes,no"
    ::= { hmSecPasswords 4 }

--
-- HTTPS Remote Access
--

    hmSecHTTPSRemoteAccess OBJECT IDENTIFIER ::= { hmSecSystem 2 }

    hmSecHTTPSRemoteEnable OBJECT-TYPE
     SYNTAX TruthValue
     ACCESS read-write
     STATUS mandatory
     DESCRIPTION
       " Value to control HTTPS remote access:
            yes: enabled
            no: disabled"
    ::= { hmSecHTTPSRemoteAccess 1 }

    hmSecHTTPSRemotePort OBJECT-TYPE
     SYNTAX DisplayString
     ACCESS read-write
     STATUS mandatory
     DESCRIPTION
       "Port for HTTPS remote Access (regularly 443), service names allowed."
    ::= { hmSecHTTPSRemoteAccess 2 }

    hmSecHTTPSRemoteFWRuleTable OBJECT-TYPE
     SYNTAX SEQUENCE OF HmSecHTTPSRemoteFWRuleEntry
     ACCESS not-accessible
     STATUS mandatory
     DESCRIPTION
        "A table containing firewall rules to allow HTTPS remote access."
     ::= { hmSecHTTPSRemoteAccess 3 }

    hmSecHTTPSRemoteFWRuleEntry OBJECT-TYPE
     SYNTAX HmSecHTTPSRemoteFWRuleEntry
     ACCESS not-accessible
     STATUS mandatory
     DESCRIPTION
     "An entry containing a single firewall rule to allow HTTPS remote access."
      INDEX { hmSecHTTPSFWruleIndex }
      ::= { hmSecHTTPSRemoteFWRuleTable 1 }

    HmSecHTTPSRemoteFWRuleEntry ::= SEQUENCE {
         hmSecHTTPSFWruleIndex INTEGER,
         hmSecHTTPSFWsourceIP  DisplayString,
         hmSecHTTPSFWinterface INTEGER,
         hmSecHTTPSFWtarget    INTEGER,
         hmSecHTTPSFWlog       INTEGER,
         hmSecHTTPSFWRowStatus  RowStatus,
         hmSecHTTPSFWcomment    DisplayString
    }

    hmSecHTTPSFWruleIndex OBJECT-TYPE
     SYNTAX INTEGER (1..100)
     ACCESS not-accessible
     STATUS mandatory
     DESCRIPTION
       "Index to identify rule."
    ::= { hmSecHTTPSRemoteFWRuleEntry 1 }

    hmSecHTTPSFWsourceIP OBJECT-TYPE
     SYNTAX DisplayString
     ACCESS read-write
     STATUS mandatory
     DESCRIPTION
       "The rule's source IP address  "
    ::= { hmSecHTTPSRemoteFWRuleEntry 2 }

    hmSecHTTPSFWinterface OBJECT-TYPE
     SYNTAX INTEGER {
			extern(1),
			intern(2)
		    }
     ACCESS read-write
     STATUS mandatory
     DESCRIPTION
       "The network interface the rule belongs to (extern/intern)."
    ::= { hmSecHTTPSRemoteFWRuleEntry 3 }

    hmSecHTTPSFWtarget OBJECT-TYPE
     SYNTAX INTEGER {
			accept(1),
			reject(2),
			drop(3)
		    }
     ACCESS read-write
     STATUS mandatory
     DESCRIPTION
       "The target of the rule (accept,reject,drop)."
    ::= { hmSecHTTPSRemoteFWRuleEntry 4 }

    hmSecHTTPSFWlog OBJECT-TYPE
     SYNTAX INTEGER {
                      yes(1),
                      no(2)
                    }
     ACCESS read-write
     STATUS mandatory
     DESCRIPTION
       " Log packets matching this rule ?"
     ::= { hmSecHTTPSRemoteFWRuleEntry 5 }


    hmSecHTTPSFWRowStatus OBJECT-TYPE
     SYNTAX RowStatus
     ACCESS read-write
     STATUS mandatory
     DESCRIPTION
      "RowStatus"
    ::= { hmSecHTTPSRemoteFWRuleEntry 6 }

    hmSecHTTPSFWcomment OBJECT-TYPE
     SYNTAX DisplayString
     ACCESS read-write
     STATUS mandatory
     DESCRIPTION
       "Commentary or name for this rule."
     ::= { hmSecHTTPSRemoteFWRuleEntry 7 }

--
-- SSH Remote Access
--

    hmSecSSHRemoteAccess OBJECT IDENTIFIER ::= { hmSecSystem 3 }

    hmSecSSHRemoteEnable OBJECT-TYPE
     SYNTAX TruthValue
     ACCESS read-write
     STATUS mandatory
     DESCRIPTION
       " Value to control SSH remote access:
            yes: enabled
            no: disabled"
    ::= { hmSecSSHRemoteAccess 1 }


    hmSecSSHRemotePort OBJECT-TYPE
     SYNTAX DisplayString
     ACCESS read-write
     STATUS mandatory
     DESCRIPTION
       "Port for SSH remote Access (regularly 22), service names allowed."
    ::= { hmSecSSHRemoteAccess 2 }


     hmSecSSHRemoteFWRuleTable OBJECT-TYPE
      SYNTAX SEQUENCE OF HmSecSSHRemoteFWRuleEntry
      ACCESS not-accessible
      STATUS mandatory
      DESCRIPTION
        "A table containing firewall rules to allow SSH remote access."
     ::= { hmSecSSHRemoteAccess 3 }

     hmSecSSHRemoteFWRuleEntry OBJECT-TYPE
      SYNTAX HmSecSSHRemoteFWRuleEntry
      ACCESS not-accessible
      STATUS mandatory
      DESCRIPTION
      "An entry containing a single firewall rule to allow SSH remote access."
      INDEX { hmSecSSHFWruleIndex }
     ::= { hmSecSSHRemoteFWRuleTable 1 }

    HmSecSSHRemoteFWRuleEntry ::= SEQUENCE {
         hmSecSSHFWruleIndex INTEGER,
         hmSecSSHFWsourceIP  DisplayString,
         hmSecSSHFWinterface INTEGER,
         hmSecSSHFWtarget    INTEGER,
         hmSecSSHFWlog       INTEGER,
         hmSecSSHFWRowStatus RowStatus,
         hmSecSSHFWcomment   DisplayString
    }

    hmSecSSHFWruleIndex OBJECT-TYPE
     SYNTAX INTEGER (1..100)
     ACCESS not-accessible
     STATUS mandatory
     DESCRIPTION
       "Index to identify rule."
    ::= { hmSecSSHRemoteFWRuleEntry 1 }

    hmSecSSHFWsourceIP OBJECT-TYPE
     SYNTAX DisplayString
     ACCESS read-write
     STATUS mandatory
     DESCRIPTION
       "The rule's source IP address  "
    ::= { hmSecSSHRemoteFWRuleEntry 2 }

    hmSecSSHFWinterface OBJECT-TYPE
     SYNTAX INTEGER {
			extern(1),
			intern(2)
		    }
     ACCESS read-write
     STATUS mandatory
     DESCRIPTION
       "The network interface the rule belongs to (extern/intern)."
    ::= { hmSecSSHRemoteFWRuleEntry 3 }

    hmSecSSHFWtarget OBJECT-TYPE
     SYNTAX INTEGER {
			accept(1),
			reject(2),
			drop(3)
		    }
     ACCESS read-write
     STATUS mandatory
     DESCRIPTION
       "The target of the rule (accept/reject/drop)."
    ::= { hmSecSSHRemoteFWRuleEntry 4 }


     hmSecSSHFWlog OBJECT-TYPE
      SYNTAX INTEGER {
                       yes(1),
                       no(2)
                    }
      ACCESS read-write
      STATUS mandatory
      DESCRIPTION
        " Log packets matching this rule ?"
      ::= { hmSecSSHRemoteFWRuleEntry 5 }


    hmSecSSHFWRowStatus OBJECT-TYPE
     SYNTAX RowStatus
     ACCESS read-write
     STATUS mandatory
     DESCRIPTION
      "RowStatus"
    ::= { hmSecSSHRemoteFWRuleEntry 6 }

    hmSecSSHFWcomment OBJECT-TYPE
     SYNTAX DisplayString
     ACCESS read-write
     STATUS mandatory
     DESCRIPTION
       "Commentary or name for this rule."
     ::= { hmSecSSHRemoteFWRuleEntry 7 }


--
-- Language
--

    hmSecLanguage OBJECT-TYPE
     SYNTAX INTEGER {
			automatic(1),
			englisch(2),
			german(3),
                        japanese(4)
		    }
     ACCESS read-write
     STATUS mandatory
     DESCRIPTION
      "The language for communication with the user via HTTP."
    ::= { hmSecSystem 4 }

--
-- Innominate Product numbers (not implementet for Eagle products)
--
 
--
-- Hardware Information
--

    hmSecHardwareInformation OBJECT IDENTIFIER ::= { hmSecSystem 5 }

    hmSecHardware OBJECT-TYPE
     SYNTAX DisplayString
     ACCESS read-only
     STATUS mandatory
     DESCRIPTION
       "The hardware of the hmSec."
    ::= { hmSecHardwareInformation 1 }


    hmSecCPU OBJECT-TYPE
     SYNTAX DisplayString
     ACCESS read-only
     STATUS mandatory
     DESCRIPTION
       "The CPU name."
    ::= { hmSecHardwareInformation 2 }


    hmSecCPUFamily OBJECT-TYPE
     SYNTAX DisplayString
     ACCESS read-only
     STATUS mandatory
     DESCRIPTION
       "The CPU family."
    ::= { hmSecHardwareInformation 3 }

    hmSecCPUStepping OBJECT-TYPE
     SYNTAX DisplayString
     ACCESS read-only
     STATUS mandatory
     DESCRIPTION
       "The CPU stepping."
    ::= { hmSecHardwareInformation 4 }

   hmSecCPUSpeed OBJECT-TYPE
     SYNTAX DisplayString
     ACCESS read-only
     STATUS mandatory
     DESCRIPTION
       "The CPU speed in MHz."
    ::= { hmSecHardwareInformation 5 }

   hmSecSystemTemperature OBJECT-TYPE
     SYNTAX DisplayString
     ACCESS read-only
     STATUS mandatory
     DESCRIPTION
       "The current system temperature (in degrees Celsius)."
    ::= { hmSecHardwareInformation 6 }

    hmSecUptime OBJECT-TYPE
     SYNTAX DisplayString
     ACCESS read-only
     STATUS mandatory
     DESCRIPTION
       "The system uptime."
    ::= { hmSecHardwareInformation 7 }

    hmSecUSMem OBJECT-TYPE
     SYNTAX DisplayString
     ACCESS read-only
     STATUS mandatory
     DESCRIPTION
       "The userspace memory."
    ::= { hmSecHardwareInformation 8 }

    hmSecMAC1 OBJECT-TYPE
     SYNTAX DisplayString
     ACCESS read-only
     STATUS mandatory
     DESCRIPTION
       "The MAC address of the first network interface."
    ::= { hmSecHardwareInformation 9 }

    hmSecMAC2 OBJECT-TYPE
     SYNTAX DisplayString
     ACCESS read-only
     STATUS mandatory
     DESCRIPTION
       "The MAC address of the second network interface."
    ::= { hmSecHardwareInformation 10 }

    hmSecMAC3 OBJECT-TYPE
     SYNTAX DisplayString
     ACCESS read-only
     STATUS mandatory
     DESCRIPTION
       "The MAC address of the third network interface."
    ::= { hmSecHardwareInformation 11 }

    hmSecSerialNumber OBJECT-TYPE
     SYNTAX DisplayString
     ACCESS read-only
     STATUS mandatory
     DESCRIPTION
       "The system's serial number ."
    ::= { hmSecHardwareInformation 12 }

   hmSecVerParSet OBJECT-TYPE
     SYNTAX DisplayString
     ACCESS read-only
     STATUS mandatory
     DESCRIPTION
       "The parameterset version."
    ::= { hmSecHardwareInformation 13 }

    hmSecProductName OBJECT-TYPE
     SYNTAX DisplayString
     ACCESS read-only
     STATUS mandatory
     DESCRIPTION
       "The product name."
    ::= { hmSecHardwareInformation 14 }

    hmSecOEMName OBJECT-TYPE
     SYNTAX DisplayString
     ACCESS read-only
     STATUS mandatory
     DESCRIPTION
       "The name of the OEM."
    ::= { hmSecHardwareInformation 15 }

    hmSecOEMSerial OBJECT-TYPE
     SYNTAX DisplayString
     ACCESS read-only
     STATUS mandatory
     DESCRIPTION
       "The OEM serial number ."
    ::= { hmSecHardwareInformation 16 }

    hmSecManufacturer OBJECT-TYPE
     SYNTAX DisplayString
     ACCESS read-only
     STATUS mandatory
     DESCRIPTION
       "The system manufacturer."
    ::= { hmSecHardwareInformation 17 }

    hmSecManuDate OBJECT-TYPE
     SYNTAX DisplayString
     ACCESS read-only
     STATUS mandatory
     DESCRIPTION
       "Date of manufacturing."
    ::= { hmSecHardwareInformation 18 }

    hmSecBootLoader OBJECT-TYPE
     SYNTAX DisplayString
     ACCESS read-only
     STATUS mandatory
     DESCRIPTION
       "The bootloader used at production ."
    ::= { hmSecHardwareInformation 19 }

    hmSecHardwareVersion OBJECT-TYPE
     SYNTAX DisplayString
     ACCESS read-only
     STATUS mandatory
     DESCRIPTION
       "The hardware version."
    ::= { hmSecHardwareInformation 20 }

   hmSecRescueSystem OBJECT-TYPE
     SYNTAX DisplayString
     ACCESS read-only
     STATUS mandatory
     DESCRIPTION
       "The rescue system used at production ."
    ::= { hmSecHardwareInformation 21 }

   hmSecProdSoft OBJECT-TYPE
     SYNTAX DisplayString
     ACCESS read-only
     STATUS mandatory
     DESCRIPTION
       "The software used at production ."
    ::= { hmSecHardwareInformation 22 }

--
-- Package Information
--

    hmSecVersions OBJECT IDENTIFIER ::= { hmSecSystem 7 }

    hmSecVersion OBJECT-TYPE
     SYNTAX DisplayString
     ACCESS read-only
     STATUS mandatory
     DESCRIPTION
       "The current version."
    ::= { hmSecVersions 1 }

    hmSecBaseVersion OBJECT-TYPE
     SYNTAX DisplayString
     ACCESS read-only
     STATUS mandatory
     DESCRIPTION
       "The base version."
    ::=  { hmSecVersions 2 }

    hmSecUpdates OBJECT-TYPE
     SYNTAX DisplayString
     ACCESS read-only
     STATUS mandatory
     DESCRIPTION
       "Performed updates."
     ::= { hmSecVersions 3 }


    hmSecPackageVersionTable OBJECT-TYPE
      SYNTAX SEQUENCE OF HmSecPackageVersionEntry
      ACCESS not-accessible
      STATUS mandatory
      DESCRIPTION
       "Package descriptions."
    ::= { hmSecVersions 4 }

     hmSecPackageVersionEntry OBJECT-TYPE
      SYNTAX HmSecPackageVersionEntry
      ACCESS not-accessible
      STATUS mandatory
      DESCRIPTION
       "Description of a single package."
      INDEX { hmSecPkgIndex }
    ::= { hmSecPackageVersionTable 1 }

    HmSecPackageVersionEntry ::= SEQUENCE
    {
      hmSecPkgIndex  INTEGER,
      hmSecPkgName   DisplayString,
      hmSecPkgVerNum DisplayString,
      hmSecPkgVerVersion DisplayString,
      hmSecPkgVerFlavour DisplayString
    }

    hmSecPkgIndex OBJECT-TYPE
     SYNTAX INTEGER (1..250)
     ACCESS not-accessible
     STATUS mandatory
     DESCRIPTION
       "Index to identify package."
    ::= {hmSecPackageVersionEntry 1 }

    hmSecPkgName OBJECT-TYPE
     SYNTAX DisplayString
     ACCESS read-only
     STATUS mandatory
     DESCRIPTION
       "Package name."
    ::= {hmSecPackageVersionEntry 2 }

    hmSecPkgVerNum OBJECT-TYPE
     SYNTAX DisplayString
     ACCESS read-only
     STATUS mandatory
     DESCRIPTION
       "Package version number."
    ::= {hmSecPackageVersionEntry 3 }

    hmSecPkgVerVersion OBJECT-TYPE
     SYNTAX DisplayString
     ACCESS read-only
     STATUS mandatory
     DESCRIPTION
       "Package version."
    ::= {hmSecPackageVersionEntry 4 }

    hmSecPkgVerFlavour OBJECT-TYPE
     SYNTAX DisplayString
     ACCESS read-only
     STATUS mandatory
     DESCRIPTION
       "Package flavour."
    ::= {hmSecPackageVersionEntry 5 }

--
-- Reboot
--

    hmSecAction OBJECT-TYPE
     SYNTAX INTEGER {
			reboot(1)
		    }
     ACCESS read-write
     STATUS mandatory
     DESCRIPTION
       "If set to 1, the system reboots."
    ::= { hmSecSystem 8 }

--
-- SNMP Remote Access
--

   hmSecSNMPenableV3 OBJECT-TYPE
    SYNTAX INTEGER {
                      yes(1),
		      no(2)
		   }
    ACCESS read-write
    STATUS mandatory
    DESCRIPTION
      "Should SNMPv3 be enabled ?"
   ::= { hmSecSNMP 1 }

    hmSecSNMPenableV1 OBJECT-TYPE
    SYNTAX INTEGER {
                      yes(1),
		      no(2)
		   }
    ACCESS read-write
    STATUS mandatory
    DESCRIPTION
      "Should SNMPv1 be enabled ?"
   ::= { hmSecSNMP 2 }

   hmSecSNMPport OBJECT-TYPE
    SYNTAX DisplayString
    ACCESS read-write
    STATUS mandatory
    DESCRIPTION
      "The port the snmp agent listens to."
    ::= { hmSecSNMP 3 }

   hmSecSNMPv1ROCommunity OBJECT-TYPE
    SYNTAX DisplayString
    ACCESS read-write
    STATUS mandatory
    DESCRIPTION
      "Read-only community string for SNMPv1."
   ::= { hmSecSNMP 4 }

   hmSecSNMPv1RWCommunity OBJECT-TYPE
    SYNTAX DisplayString
    ACCESS read-write
    STATUS mandatory
    DESCRIPTION
      "Read-write community string for SNMPv1."
   ::= { hmSecSNMP 5 }


   hmSecSNMPFWRuleTable OBJECT-TYPE
    SYNTAX SEQUENCE OF HmSecSNMPFWRuleEntry
    ACCESS not-accessible
    STATUS mandatory
    DESCRIPTION
      "A table containing firewall rules to allow SNMP access."
   ::= { hmSecSNMP 6 }


-- SNMP access rule table

   hmSecSNMPFWRuleEntry OBJECT-TYPE
     SYNTAX HmSecSNMPFWRuleEntry
     ACCESS not-accessible
     STATUS mandatory
     DESCRIPTION
     "An entry containing a single firewall rule to allow SNMP access."
     INDEX { hmSecSNMPFWruleIndex }
    ::= { hmSecSNMPFWRuleTable 1 }

    HmSecSNMPFWRuleEntry ::= SEQUENCE {
         hmSecSNMPFWruleIndex INTEGER,
         hmSecSNMPFWsourceIP  DisplayString,
         hmSecSNMPFWinterface INTEGER,
         hmSecSNMPFWtarget    INTEGER,
         hmSecSNMPFWlog       INTEGER,
         hmSecSNMPFWRowStatus RowStatus,
         hmSecSNMPFWcomment   DisplayString
    }

    hmSecSNMPFWruleIndex OBJECT-TYPE
     SYNTAX INTEGER (1..100)
     ACCESS not-accessible
     STATUS mandatory
     DESCRIPTION
       "Index to identify rule."
    ::= { hmSecSNMPFWRuleEntry 1 }

    hmSecSNMPFWsourceIP OBJECT-TYPE
     SYNTAX DisplayString
     ACCESS read-write
     STATUS mandatory
     DESCRIPTION
       "The rule's source IP address  "
    ::= { hmSecSNMPFWRuleEntry 2 }

    hmSecSNMPFWinterface OBJECT-TYPE
     SYNTAX INTEGER {
			extern(1),
			intern(2)
		    }
     ACCESS read-write
     STATUS mandatory
     DESCRIPTION
       "The network interface the rule belongs to (extern/intern)."
    ::= { hmSecSNMPFWRuleEntry 3 }

    hmSecSNMPFWtarget OBJECT-TYPE
     SYNTAX INTEGER {
			accept(1),
			reject(2),
			drop(3)
		    }
     ACCESS read-write
     STATUS mandatory
     DESCRIPTION
       "The target of the rule (accept/reject/drop)."
    ::= { hmSecSNMPFWRuleEntry 4 }


     hmSecSNMPFWlog OBJECT-TYPE
      SYNTAX INTEGER {
                       yes(1),
                       no(2)
                     }
      ACCESS read-write
      STATUS mandatory
      DESCRIPTION
        " Log packets matching this rule ?"
      ::= { hmSecSNMPFWRuleEntry 5 }


    hmSecSNMPFWRowStatus OBJECT-TYPE
     SYNTAX RowStatus
     ACCESS read-write
     STATUS mandatory
     DESCRIPTION
      "RowStatus"
    ::= { hmSecSNMPFWRuleEntry 6 }

    hmSecSNMPFWcomment OBJECT-TYPE
     SYNTAX DisplayString
     ACCESS read-write
     STATUS mandatory
     DESCRIPTION
       "Commentary or name for this rule."
     ::= { hmSecSNMPFWRuleEntry 7 }



-- SNMP trap configuration


    hmSecSNMPTrapReceiverTable OBJECT-TYPE
         SYNTAX      SEQUENCE OF HmSecSNMPTrapReceiverEntry
         ACCESS      not-accessible
         STATUS      mandatory
         DESCRIPTION
                     "Trap messages are sent across a network to an SNMP Network Manager.
                     These messages alert the manager to events occurring within the security
                     gateway or on the network. Up to six simultaneous trap receivers are supported."
         ::= { hmSecSNMP 7 }

    hmSecSNMPTrapReceiverEntry OBJECT-TYPE
         SYNTAX      HmSecSNMPTrapReceiverEntry
         ACCESS      not-accessible
         STATUS      mandatory
         DESCRIPTION
                     "Security gateway's Snmp Trap Receiver Config entry"
         INDEX       { hmSecSNMPTrapReceiverIndex }
         ::= { hmSecSNMPTrapReceiverTable 1 }

    HmSecSNMPTrapReceiverEntry ::= SEQUENCE {
           hmSecSNMPTrapReceiverIndex
               INTEGER,
           hmSecSNMPTrapReceiverCommunity
               DisplayString (SIZE(1..16)),
           hmSecSNMPTrapReceiverIPAddress
               IpAddress,
           hmSecSNMPTrapReceiverName
	         DisplayString,
           hmSecSNMPTrapReceiverRowStatus
               INTEGER
       }

    hmSecSNMPTrapReceiverIndex OBJECT-TYPE
         SYNTAX      INTEGER (1..255)
         ACCESS      not-accessible
         STATUS      mandatory
         DESCRIPTION
                     "The security gateway's Snmp Trap Receiver Index"
         ::= { hmSecSNMPTrapReceiverEntry 1 }

    hmSecSNMPTrapReceiverCommunity OBJECT-TYPE
         SYNTAX      DisplayString
         ACCESS      read-write
         STATUS      mandatory
         DESCRIPTION
                     "The security gateway's Snmp Trap Receiver Community Name.
                     This is the SNMP community name of the remote network manager;
                     the name can be up to 16 characters (????), and is case-sensitive."
         ::= { hmSecSNMPTrapReceiverEntry 2 }

    hmSecSNMPTrapReceiverIPAddress OBJECT-TYPE
         SYNTAX      IpAddress
         ACCESS      read-write
         STATUS      mandatory
         DESCRIPTION
                     "IP Address - Each IP address parameter is four integer numbers.
                     The numbers range from 0 to 255."
         ::= { hmSecSNMPTrapReceiverEntry 3 }

    hmSecSNMPTrapReceiverName OBJECT-TYPE
         SYNTAX      DisplayString
         ACCESS      read-write
         STATUS      mandatory
         DESCRIPTION
                     "The name of this Trap Receiver entry "
         ::= { hmSecSNMPTrapReceiverEntry 4 }

    hmSecSNMPTrapReceiverRowStatus OBJECT-TYPE
         SYNTAX      RowStatus
         ACCESS      read-write
         STATUS      mandatory
         DESCRIPTION
                     "The security gateway's Snmp Trap Reciever Row Status."

         ::= { hmSecSNMPTrapReceiverEntry 5 }


    -- hmSecSNMPTrapConfigGroup

    hmSecSNMPTrapConfigGroup       OBJECT IDENTIFIER ::= { hmSecSNMP 8  }

    hmSecSNMPAuthenticationTrapFlag OBJECT-TYPE
         SYNTAX      INTEGER {
                     enable(1),
                     disable(2)
                  }
         ACCESS      read-write
         STATUS      mandatory
         DESCRIPTION
                     "Authentication Flag - Enable/Disable SNMP authentication trap."
         ::= { hmSecSNMPTrapConfigGroup 1 }

    hmSecSNMPLinkUpDownTrapFlag OBJECT-TYPE
         SYNTAX      INTEGER {
                     enable(1),
                     disable(2)
                  }
         ACCESS      read-write
         STATUS      mandatory
         DESCRIPTION
                     "Link Up/Down Flag - Enable/Disable Link Up/Link Down traps for the
                     entire security gateway."
         ::= { hmSecSNMPTrapConfigGroup 2 }

    hmSecSNMPColdStartTrapFlag OBJECT-TYPE
         SYNTAX      INTEGER {
                     enable(1),
                     disable(2)
                  }
         ACCESS      read-write
         STATUS      mandatory
         DESCRIPTION
                     "ColdStart Flag - Enable/Disable SNMP coldstart trap."
         ::= { hmSecSNMPTrapConfigGroup 3 }

    hmSecSNMPTrapFlag OBJECT-TYPE
         SYNTAX      INTEGER {
                     enable(1),
                     disable(2)
                  }
         ACCESS      read-write
         STATUS      mandatory
         DESCRIPTION
                     "Enables/Disables the traps with enterprise = hmSecurityGateway."
         ::= { hmSecSNMPTrapConfigGroup 4 }

    hmSecSNMPChassisTrapFlag OBJECT-TYPE
         SYNTAX      INTEGER {
                     enable(1),
                     disable(2)
                  }
         ACCESS      read-write
         STATUS      mandatory
         DESCRIPTION
                     "Enables/Disables the traps with enterprise = hmChassis."
         ::= { hmSecSNMPTrapConfigGroup 5 }

    hmSecSNMPAgentTrapFlag OBJECT-TYPE
         SYNTAX      INTEGER {
                     enable(1),
                     disable(2)
                  }
         ACCESS      read-write
         STATUS      mandatory
         DESCRIPTION
                     "Enables/Disables the traps with enterprise = hmAgent."
         ::= { hmSecSNMPTrapConfigGroup 6 }

    hmSecSNMPAvFailTrapFlag OBJECT-TYPE
         SYNTAX      INTEGER {
                     enable(1),
                     disable(2)
                  }
         ACCESS      read-write
         STATUS      mandatory
         DESCRIPTION
                     "Enables/Disables the traps with AntiVirus failures (update or engine failures)."
         ::= { hmSecSNMPTrapConfigGroup 7 }

    hmSecSNMPAvInfoTrapFlag OBJECT-TYPE
         SYNTAX      INTEGER {
                     enable(1),
                     disable(2)
                  }
         ACCESS      read-write
         STATUS      mandatory
         DESCRIPTION
                     "Enables/Disables the traps with informational AntiVirus messages."
         ::= { hmSecSNMPTrapConfigGroup 8 }
 
    hmSecSNMPBladeStateTrapFlag OBJECT-TYPE
         SYNTAX      INTEGER {
                     enable(1),
                     disable(2)
                  }
         ACCESS      read-write
         STATUS      mandatory
         DESCRIPTION
                     "Enables/Disables traps sent at blade status change."
         ::= { hmSecSNMPTrapConfigGroup 9 }

    hmSecSNMPBladeConfigTrapFlag OBJECT-TYPE
         SYNTAX      INTEGER {
                     enable(1),
                     disable(2)
                  }
         ACCESS      read-write
         STATUS      mandatory
         DESCRIPTION
                     "Enables/Disables traps sent at automatic blade configuration or backup."
         ::= { hmSecSNMPTrapConfigGroup 10 }
    hmSecSNMPRouterRedundancyStatusFlag OBJECT-TYPE
         SYNTAX      INTEGER {
                     enable(1),
                     disable(2)
                  }
         ACCESS      read-write
         STATUS      mandatory
         DESCRIPTION
                     "Enables/Disables traps sent at change of HA state."
         ::= { hmSecSNMPTrapConfigGroup 11 }
--
-- NTP Service
--

  hmSecNTPactivate OBJECT-TYPE
  SYNTAX INTEGER { yes(1),
                   no(2)
		 }
  ACCESS read-write
  STATUS mandatory
  DESCRIPTION
    "Activate NTP ?"
  ::={ hmSecNTP 1 }

  hmSecNTPtimestamp OBJECT-TYPE
   SYNTAX INTEGER  {
                      yes(1),
		      no(2)
		   }
  ACCESS read-write
  STATUS mandatory
  DESCRIPTION
    "Time stamp in filesystem ?"
  ::={ hmSecNTP 2 }
		
  hmSecNTPServerTable OBJECT-TYPE
    SYNTAX SEQUENCE OF HmSecNTPServerEntry
    ACCESS not-accessible
    STATUS mandatory
    DESCRIPTION
      "A table of NTP Servers."
 ::= { hmSecNTP 3 }

  hmSecNTPTimezone OBJECT-TYPE
   SYNTAX DisplayString
   ACCESS read-write
   STATUS mandatory
   DESCRIPTION
     "Timezone in POSIX.1 notation"
  ::={ hmSecNTP 4 }

   hmSecNTPStatus OBJECT-TYPE
     SYNTAX DisplayString
     ACCESS read-only
     STATUS mandatory
     DESCRIPTION
        "NTP state"
  ::={ hmSecNTP 5 }


  hmSecNTPServerEntry OBJECT-TYPE
      SYNTAX HmSecNTPServerEntry
      ACCESS not-accessible
      STATUS mandatory
      DESCRIPTION
       "A single NTP Server."
      INDEX { hmSecNTPServerIndex }
  ::= { hmSecNTPServerTable 1 }

  HmSecNTPServerEntry  ::= SEQUENCE {
     hmSecNTPServerIndex INTEGER,
     hmSecNTPServerHost DisplayString,
     hmSecNTPServerRowStatus RowStatus
  }

  hmSecNTPServerIndex OBJECT-TYPE
    SYNTAX INTEGER (1..20)
    ACCESS not-accessible
    STATUS mandatory
    DESCRIPTION
      "Table index"
   ::= { hmSecNTPServerEntry 1 }

   hmSecNTPServerHost OBJECT-TYPE
    SYNTAX DisplayString
    ACCESS read-write
    STATUS mandatory
    DESCRIPTION
      "Hostname or IP address of the NTP Server."
   ::= { hmSecNTPServerEntry 2 }

   hmSecNTPServerRowStatus OBJECT-TYPE
    SYNTAX RowStatus
    ACCESS read-write
    STATUS mandatory
    DESCRIPTION
      "Row status"
   ::= { hmSecNTPServerEntry 3 }

--
-- Update Server Table
--

  hmSecUpdateServerTable OBJECT-TYPE
    SYNTAX SEQUENCE OF HmSecUpdateServerEntry
    ACCESS not-accessible
    STATUS mandatory
    DESCRIPTION
      "A table of update server repositories."
   ::= { hmSecUpdate 1 }

  hmSecUpdateServerEntry OBJECT-TYPE
      SYNTAX HmSecUpdateServerEntry
      ACCESS not-accessible
      STATUS mandatory
      DESCRIPTION
       "A single update server repository. "
      INDEX { hmSecUpdateServerIndex }
  ::= { hmSecUpdateServerTable 1 }

  HmSecUpdateServerEntry  ::= SEQUENCE {
     hmSecUpdateServerIndex INTEGER,
     hmSecUpdateServer  DisplayString,
     hmSecUpdateServerRowStatus RowStatus,
     hmSecUpdateServerProto DisplayString,
     hmSecUpdateServerHost DisplayString,
     hmSecUpdateServerLogin DisplayString,
     hmSecUpdateServerPassword DisplayString
  }

  hmSecUpdateServerIndex OBJECT-TYPE
    SYNTAX INTEGER (1..20)
    ACCESS not-accessible
    STATUS mandatory
    DESCRIPTION
      "Table index."
   ::= { hmSecUpdateServerEntry 1 }

   hmSecUpdateServer OBJECT-TYPE
    SYNTAX DisplayString
    ACCESS read-write
    STATUS deprecated
    DESCRIPTION
      "URL of the update server."
   ::= { hmSecUpdateServerEntry 2 }

   hmSecUpdateServerRowStatus OBJECT-TYPE
    SYNTAX RowStatus
    ACCESS read-write
    STATUS mandatory
    DESCRIPTION
      "Row Status"
   ::= { hmSecUpdateServerEntry 3 }

   hmSecUpdateServerProto OBJECT-TYPE
    SYNTAX DisplayString
    ACCESS read-write
    STATUS mandatory
    DESCRIPTION
      "Protocol, either https or http"
   ::= { hmSecUpdateServerEntry 4 }

   hmSecUpdateServerHost OBJECT-TYPE
    SYNTAX DisplayString
    ACCESS read-write
    STATUS mandatory
    DESCRIPTION
      "Hostname of the update server."
   ::= { hmSecUpdateServerEntry 5 }

   hmSecUpdateServerLogin OBJECT-TYPE
    SYNTAX DisplayString
    ACCESS read-write
    STATUS mandatory
    DESCRIPTION
      "Login on the update server."
   ::= { hmSecUpdateServerEntry 6 }

   hmSecUpdateServerPassword OBJECT-TYPE
    SYNTAX DisplayString
    ACCESS read-write
    STATUS mandatory
    DESCRIPTION
      "Password on the update server."
   ::= { hmSecUpdateServerEntry 7 }

--
-- Error
--

   hmSecSNMPError OBJECT-TYPE
    SYNTAX DisplayString
    ACCESS read-only
    STATUS mandatory
    DESCRIPTION
       "Field, providing textual description of errors caused by SNMP
       operations."
   ::= { hmSecurityGateway 8 }

--
-- hmSec Layer2 Redundancy
--
   hmSecL2Redundancy OBJECT IDENTIFIER ::= { hmSecRedundancy 1 }
 
   hmSecL2RedundancyEnable OBJECT-TYPE
      SYNTAX INTEGER {
                        enabled(1),
                        disabled(2)
                     }
      ACCESS read-write
      STATUS mandatory
      DESCRIPTION
         "Enable Ring/Network Coupling/Dual Homing."
   ::= { hmSecL2Redundancy 1 }
 
   hmSecL2RedundancyPort OBJECT-TYPE
      SYNTAX INTEGER {
                        intern(1),
                        extern(2)
                     }
      ACCESS read-write
      STATUS mandatory
      DESCRIPTION
         "Redundancy Port: 'Trusted/Intern' or 'Untrusted/Extern'."
   ::= { hmSecL2Redundancy 2 }
 
 
--
-- hmSec Router Redundancy
--
   hmSecRouterRedundancy OBJECT IDENTIFIER ::= { hmSecRedundancy 2 }

   hmSecRouterRedundancyEnable OBJECT-TYPE
      SYNTAX INTEGER {
                        enabled(1),
                        disabled(2)
                     }
      ACCESS read-write
      STATUS mandatory
      DESCRIPTION
         "Enable Router Redundancy."
   ::= { hmSecRouterRedundancy 1 }

   hmSecRouterRedundancyTrack OBJECT-TYPE
      SYNTAX INTEGER {
                        enabled(1),
                        disabled(2)
                     }
      ACCESS read-write
      STATUS mandatory
      DESCRIPTION
         "Run ICMP checks against redundancy peer."
   ::= { hmSecRouterRedundancy 2 }

   hmSecRouterRedundancyInternalID OBJECT-TYPE
      SYNTAX INTEGER
      ACCESS read-write
      STATUS mandatory
      DESCRIPTION
         "Internal ID of the virtual router."
   ::= { hmSecRouterRedundancy 3 }

   hmSecRouterRedundancyExternalID OBJECT-TYPE
      SYNTAX INTEGER
      ACCESS read-write
      STATUS mandatory
      DESCRIPTION
         "External ID of the virtual router."
   ::= { hmSecRouterRedundancy 4 }

   hmSecRouterRedundancyPassword OBJECT-TYPE
      SYNTAX DisplayString
      ACCESS read-write
      STATUS mandatory
      DESCRIPTION
         "Passwort for synchronization between the virtual router peers."
   ::= { hmSecRouterRedundancy 5 }

   hmSecRouterRedundancyPeerIntern OBJECT-TYPE
      SYNTAX IpAddress
      ACCESS read-write
      STATUS mandatory
      DESCRIPTION
         "Internal IP of the VR peer."
   ::= { hmSecRouterRedundancy 6 }

   hmSecRouterRedundancyPeerExtern OBJECT-TYPE
      SYNTAX IpAddress
      ACCESS read-write
      STATUS mandatory
      DESCRIPTION
         "External IP of the VR peer."
   ::= { hmSecRouterRedundancy 7 }

   hmSecRouterRedundancyPriority OBJECT-TYPE
      SYNTAX INTEGER
      ACCESS read-write
      STATUS mandatory
      DESCRIPTION
         "Priority for the virtual router."
   ::= { hmSecRouterRedundancy 8 }

   hmSecRouterRedundancyVirtIpInt OBJECT-TYPE
      SYNTAX IpAddress
      ACCESS read-write
      STATUS mandatory
      DESCRIPTION
         "Virtual IP address of the HA cluster for the internal network."
   ::= { hmSecRouterRedundancy 9 }

   hmSecRouterRedundancyVirtIpExt OBJECT-TYPE
      SYNTAX IpAddress
      ACCESS read-write
      STATUS mandatory
      DESCRIPTION
         "Virtual IP address of the HA cluster for the external network."
   ::= { hmSecRouterRedundancy 10 }

   hmSecRouterRedundancyWantState OBJECT-TYPE
      SYNTAX INTEGER {
                        master(1),
                        backup(2)
                     }
      ACCESS read-write
      STATUS mandatory
      DESCRIPTION
         "HA cluster state to start this hmSec with at boot time."
   ::= { hmSecRouterRedundancy 11 }


   hmSecRouterRedExtHostCheckTable OBJECT-TYPE
      SYNTAX SEQUENCE OF HmSecRouterRedExtHostCheckEntry
      ACCESS not-accessible
      STATUS mandatory
      DESCRIPTION
        "A table of hosts to check with ICMP for detecting the VR state."
   ::= { hmSecRouterRedundancy 12 }

    hmSecRouterRedExtHostCheckEntry OBJECT-TYPE
        SYNTAX HmSecRouterRedExtHostCheckEntry
        ACCESS not-accessible
        STATUS mandatory
        DESCRIPTION
         "External hosts to check with ICMP for detecting the VR state."
        INDEX { hmSecRouterRedExtHostCheckIndex }
    ::= { hmSecRouterRedExtHostCheckTable 1 }

    HmSecRouterRedExtHostCheckEntry  ::= SEQUENCE {
       hmSecRouterRedExtHostCheckIndex	INTEGER,
       hmSecRouterRedExtHostCheckIP	IpAddress,
       hmSecRouterRedExtHostCheckRowSt	RowStatus
    }

    hmSecRouterRedExtHostCheckIndex OBJECT-TYPE
      SYNTAX INTEGER (1..100)
      ACCESS not-accessible
      STATUS mandatory
      DESCRIPTION
        "Table index."
    ::= { hmSecRouterRedExtHostCheckEntry 1 }

     hmSecRouterRedExtHostCheckIP OBJECT-TYPE
      SYNTAX IpAddress
      ACCESS read-write
      STATUS mandatory
      DESCRIPTION
        "The IP address."
    ::= { hmSecRouterRedExtHostCheckEntry 2 }

     hmSecRouterRedExtHostCheckRowSt OBJECT-TYPE
      SYNTAX RowStatus
      ACCESS read-write
      STATUS mandatory
      DESCRIPTION
        "Row Status"
    ::= { hmSecRouterRedExtHostCheckEntry 3 }



   hmSecRouterRedIntHostCheckTable OBJECT-TYPE
      SYNTAX SEQUENCE OF HmSecRouterRedIntHostCheckEntry
      ACCESS not-accessible
      STATUS mandatory
      DESCRIPTION
        "A table of hosts to check with ICMP for detecting the VR state."
   ::= { hmSecRouterRedundancy 13 }

    hmSecRouterRedIntHostCheckEntry OBJECT-TYPE
        SYNTAX HmSecRouterRedIntHostCheckEntry
        ACCESS not-accessible
        STATUS mandatory
        DESCRIPTION
         "External hosts to check with ICMP for detecting the VR state."
        INDEX { hmSecRouterRedIntHostCheckIndex }
    ::= { hmSecRouterRedIntHostCheckTable 1 }

    HmSecRouterRedIntHostCheckEntry  ::= SEQUENCE {
       hmSecRouterRedIntHostCheckIndex	INTEGER,
       hmSecRouterRedIntHostCheckIP	IpAddress,
       hmSecRouterRedIntHostCheckRowSt	RowStatus
    }

    hmSecRouterRedIntHostCheckIndex OBJECT-TYPE
      SYNTAX INTEGER (1..100)
      ACCESS not-accessible
      STATUS mandatory
      DESCRIPTION
        "Table index."
    ::= { hmSecRouterRedIntHostCheckEntry 1 }

     hmSecRouterRedIntHostCheckIP OBJECT-TYPE
      SYNTAX IpAddress
      ACCESS read-write
      STATUS mandatory
      DESCRIPTION
        "The IP address."
    ::= { hmSecRouterRedIntHostCheckEntry 2 }

     hmSecRouterRedIntHostCheckRowSt OBJECT-TYPE
      SYNTAX RowStatus
      ACCESS read-write
      STATUS mandatory
      DESCRIPTION
        "Row Status"
    ::= { hmSecRouterRedIntHostCheckEntry 3 }
   hmSecRouterRedundancyState OBJECT-TYPE
      SYNTAX INTEGER {
                        backup(1),
			master(2),
                        fault(3),
			disabled(4)
                     }
      ACCESS read-only
      STATUS mandatory
      DESCRIPTION
         "Current HA cluster state."
   ::= { hmSecRouterRedundancy 14 }
-- hmSecInfo

   hmSecHTTPSLastAccessIP OBJECT-TYPE
    SYNTAX IpAddress
    ACCESS read-only
    STATUS mandatory
    DESCRIPTION
       "Address of the last IP from which a wrong authentication information
        was sent for HTTPS access was sent."
   ::= { hmSecInfo 1 }

   hmSecShellLastAccessIP OBJECT-TYPE
    SYNTAX IpAddress
    ACCESS read-only
    STATUS mandatory
    DESCRIPTION
       "Address of the last IP from which a login event occured."
   ::= { hmSecInfo 2 }

   hmSecDHCPLastAccessMAC OBJECT-TYPE
    SYNTAX MacAddress
    ACCESS read-only
    STATUS mandatory
    DESCRIPTION
       "MAC Address of the last unknown client trying to obtain a lease."
   ::= { hmSecInfo 3 }


--
-- hmSecTrapRessources
--

  hmSecTrapRessources  OBJECT IDENTIFIER ::= { hmSecInfo 4 }

   hmSecTResDiscFull OBJECT-TYPE
    SYNTAX INTEGER
                 {
		   free(1),
                   tight(2),
                   full(3)
		 }
    ACCESS read-only
    STATUS mandatory
    DESCRIPTION
       "Status of file system free space. If multiple file systems, the worst state is used."
   ::= { hmSecTrapRessources 1 }

   hmSecTResCpuLoadHigh OBJECT-TYPE
    SYNTAX INTEGER
    ACCESS read-only
    STATUS mandatory
    DESCRIPTION
       "CPU load (uptime*10)."
   ::= { hmSecTrapRessources 2 }

   hmSecTResMemoryFull OBJECT-TYPE
    SYNTAX INTEGER
    ACCESS read-only
    STATUS mandatory
    DESCRIPTION
       "Free memory (RAM) in KiByte."
   ::= { hmSecTrapRessources 3 }

   hmSecTResColdstart OBJECT-TYPE
   SYNTAX INTEGER
    ACCESS read-only
    STATUS mandatory
    DESCRIPTION
       "Trap sent when system rebooted (snmp daemon started)."
   ::= { hmSecTrapRessources 4 }



--
-- hmSecTrapAV
--

  hmSecTResAV  OBJECT IDENTIFIER ::= { hmSecTrapRessources 6 }

   hmSecTResAvUpdateDone OBJECT-TYPE
    SYNTAX DisplayString
    ACCESS read-only
    STATUS mandatory
    DESCRIPTION
       "AV Update was performed successfully."
   ::= { hmSecTResAV 1 }

   hmSecTResAvUpdateError OBJECT-TYPE
    SYNTAX DisplayString
    ACCESS read-only
    STATUS mandatory
    DESCRIPTION
       "Error when performing AV Update."
   ::= { hmSecTResAV 2 }

   hmSecTResAvVirusDetected OBJECT-TYPE
    SYNTAX DisplayString
    ACCESS read-only
    STATUS mandatory
    DESCRIPTION
       "AV found a virus."
   ::= { hmSecTResAV 3 }

   hmSecTResAvFileNotScanned OBJECT-TYPE
    SYNTAX DisplayString
    ACCESS read-only
    STATUS mandatory
    DESCRIPTION
       "The file was not scanned for viruses."
   ::= { hmSecTResAV 4 }

   hmSecTResAvFailed OBJECT-TYPE
    SYNTAX DisplayString
    ACCESS read-only
    STATUS mandatory
    DESCRIPTION
       "General AV failure."
   ::= { hmSecTResAV 5 }


--
-- hmSecTResPlatformSpecific
--

  hmSecTResPlatformSpecific  OBJECT IDENTIFIER ::= { hmSecTrapRessources 7 }


  hmSecTResIndustrial  OBJECT IDENTIFIER ::= { hmSecTResPlatformSpecific 1 }

  hmSecTResIndustrialPower  OBJECT IDENTIFIER ::= { hmSecTResIndustrial 1 }

  hmSecTResIndustrialTemperature  OBJECT IDENTIFIER
    ::= { hmSecTResIndustrial 2 }


  hmSecPSTable OBJECT-TYPE
     SYNTAX SEQUENCE OF MguardPSEntry
     ACCESS not-accessible
     STATUS mandatory
     DESCRIPTION
	"This table contains all variables related to the power supply
         units of the chassis/switch. For each power supply slot exists
	 one instance."
   ::= { hmSecTResIndustrialPower 2 }

  hmSecPSEntry OBJECT-TYPE
     SYNTAX MguardPSEntry
     ACCESS not-accessible
     STATUS mandatory
     DESCRIPTION "Power supply entry"
     INDEX  { hmSecPSSysID, hmSecPSID }
   ::= { hmSecPSTable 1 }

  MguardPSEntry ::= SEQUENCE {
     hmSecPSSysID INTEGER,
     hmSecPSID INTEGER,
     hmSecPSState INTEGER
  }

  hmSecPSSysID OBJECT-TYPE
     SYNTAX INTEGER (1..100)
     ACCESS read-only
     STATUS mandatory
     DESCRIPTION
        "The value of SysID is assigned so as to uniquely identify a
         chassis/switch among the subordinate managed objects of the
         system."
   ::= { hmSecPSEntry 1 }

  hmSecPSID OBJECT-TYPE
     SYNTAX INTEGER(1..100)
     ACCESS read-only
     STATUS mandatory
     DESCRIPTION
        "This Index is used to identify the associated power supply unit."
   ::= { hmSecPSEntry 2 }

  hmSecPSState OBJECT-TYPE
     SYNTAX INTEGER {
                 ok (1),
		 failed (2),
		 notInstalled (3),
		 unknown (4)
     }
     ACCESS read-only
     STATUS mandatory
     DESCRIPTION
        "Indicates the operational state of the associated power supply. If
	 the value of this variable changes, a hmSecPowerSupply trap is sent."
   ::= { hmSecPSEntry 3 }


  hmSecTResIndustrialTempHiLimit OBJECT-TYPE
    SYNTAX INTEGER
    ACCESS read-write
    STATUS mandatory
    DESCRIPTION
       "Upper limit of allowed system temperature."
   ::= { hmSecTResIndustrialTemperature 2 }

  hmSecTResIndustrialTempLowLimit OBJECT-TYPE
    SYNTAX INTEGER
    ACCESS read-write
    STATUS mandatory
    DESCRIPTION
       "Lower limit of allowed system temperature."
   ::= { hmSecTResIndustrialTemperature 3 }

  hmSecTResAutoConfigAdapterState OBJECT-TYPE
    SYNTAX INTEGER {
		notPresent(1),
		removed(2),
		ok(3),
		notInSync(4),
		outOfMemory(5),
		wrongMachine(6),
		checksumErr(7),
		genericErr(8)
	}
    ACCESS read-only
    STATUS mandatory
    DESCRIPTION
       "Trap sent when ACA was accessed."
   ::= { hmSecTResIndustrial 4 }


  hmSecTResSignalRelais  OBJECT IDENTIFIER ::= { hmSecTResIndustrial 3 }

   hmSecTResSignalRelaisState OBJECT-TYPE
      SYNTAX INTEGER
      ACCESS read-only
      STATUS mandatory
      DESCRIPTION
         "Current state of the signal relais (1=on, 2=off)."
   ::= { hmSecTResSignalRelais 1 }

   hmSecTResSignalRelaisReason OBJECT-TYPE
      SYNTAX OBJECT IDENTIFIER
      ACCESS read-only
      STATUS mandatory
      DESCRIPTION
         "Reason why the signal relais was triggered."
   ::= { hmSecTResSignalRelais 2 }

   hmSecTResSignalRelaisReasonIdx OBJECT-TYPE
      SYNTAX INTEGER
      ACCESS read-only
      STATUS mandatory
      DESCRIPTION
         "Reason number (ue0=1, ue1=2, number of TX bytes for eth)."
   ::= { hmSecTResSignalRelais 3 }

   hmSecTResSignalRelaisPowerAlarm OBJECT-TYPE
      SYNTAX	INTEGER {
		enable(1),
		disable(2)
      }
      ACCESS	read-write
      STATUS	mandatory
      DESCRIPTION
	"Enables/disables an alarm for the signalling relay of the powersupply state."
      ::= { hmSecTResSignalRelais 4 }

   hmSecTResSignalRelaisMode OBJECT-TYPE
      SYNTAX INTEGER {
		standard(1),
		manual(2)
      }
      ACCESS read-write
      STATUS mandatory
      DESCRIPTION
      "When set to standard, this is the default, the signalling relay shows the state of
      hmRS2SigRelayState.
      When set to manual, the relay is controlled by the configured Manual State."
      ::= {  hmSecTResSignalRelais 5 }


   hmSecTResSignalRelaisManualStat OBJECT-TYPE
      SYNTAX  INTEGER {
		on(1),
		off(2)
      }
      ACCESS read-write
      STATUS mandatory
      DESCRIPTION
      "When set to on, this is the default, the signalling relay is opened.
      When set to off the relay is closed."
      ::= {  hmSecTResSignalRelais 6 }


  hmSecTResSignalLinkTable  OBJECT IDENTIFIER ::= { hmSecTResIndustrial 5 }

  hmSecTResSigLinkID   OBJECT-TYPE
    SYNTAX    INTEGER  (1..7)
    ACCESS    read-only
    STATUS    mandatory
    DESCRIPTION
     "This index is used to identify the associated link and
     corresponds with ifMauIfIndex."
    ::= { hmSecTResSignalLinkTable 1 }

  hmSecTResSigLinkAlarm   OBJECT-TYPE
    SYNTAX    INTEGER {
        on (1),
        off (2)
        }
    ACCESS    read-write
    STATUS    mandatory
    DESCRIPTION
                 "DURABLE:  { off:all }
                 Indicates whether an alarm for the signalling relay of the
                 associated link will be produced or not, so you can mask the
                 value of ifMauMediaAvailable."
    ::= { hmSecTResSignalLinkTable 2 }




  hmSecTResBladeCTRL  OBJECT IDENTIFIER ::= { hmSecTResPlatformSpecific 2 }

  hmSecTResBladeInfo  OBJECT IDENTIFIER ::= { hmSecTResBladeCTRL 1 }
  hmSecTResBladeCtrlCfg  OBJECT IDENTIFIER ::= { hmSecTResBladeCTRL 5 }

  hmSecTResBladeRackID OBJECT-TYPE
      SYNTAX DisplayString
      ACCESS read-only
      STATUS mandatory
      DESCRIPTION
         "Rack ID in question when sending a Blade-related SNMP trap."
   ::= { hmSecTResBladeInfo 1 }

  hmSecTResBladeSlotNr OBJECT-TYPE
      SYNTAX INTEGER
      ACCESS read-only
      STATUS mandatory
      DESCRIPTION
         "Slot ID in question when sending a Blade-related SNMP trap."
   ::= { hmSecTResBladeInfo 2 }

  hmSecTResBladeCtrlPowerStatus OBJECT-TYPE
    SYNTAX INTEGER
                 {
		   absent(1),
                   present(2),
                   online(3)
		 }
      ACCESS read-only
      STATUS mandatory
      DESCRIPTION
         "Status of the BladePack's power supplies when sending an SNMP trap."
   ::= { hmSecTResBladeCTRL 2 }

  hmSecTResBladeCtrlRunStatus OBJECT-TYPE
    SYNTAX INTEGER
                 {
		   absent(1),
                   present(2),
                   online(3)
		 }
      ACCESS read-only
      STATUS mandatory
      DESCRIPTION
         "Status of the Blade's run status when sending an SNMP trap."
   ::= { hmSecTResBladeCTRL 3 }

  hmSecTResBladeCtrlFailover OBJECT-TYPE
      SYNTAX DisplayString
      ACCESS read-only
      STATUS mandatory
      DESCRIPTION
         "Blade failover reason/details in HA setup when sending an SNMP trap."
   ::= { hmSecTResBladeCTRL 4 }

  hmSecTResBladeCtrlCfgBackup OBJECT-TYPE
      SYNTAX INTEGER {
			downloaded(3)
                     }
      ACCESS read-only
      STATUS mandatory
      DESCRIPTION
         "Reason/details for configuration backup to Blade CTRL when sending an SNMP trap."
   ::= { hmSecTResBladeCtrlCfg 1 }

  hmSecTResBladeCtrlCfgRestored OBJECT-TYPE
      SYNTAX INTEGER {
			automatic(1),
			manual(2)
                     }
      ACCESS read-only
      STATUS mandatory
      DESCRIPTION
         "Reason for configuration restore from Blade CTRL when sending an SNMP trap."
   ::= { hmSecTResBladeCtrlCfg 2 }

   hmSecTResRedundancy  OBJECT IDENTIFIER ::= { hmSecTrapRessources 8 }
   hmSecTResRedundacyReason OBJECT-TYPE
    SYNTAX DisplayString
    ACCESS read-only
    STATUS mandatory
    DESCRIPTION
       "Reason for redundancy status change."
   ::= { hmSecTResRedundancy 1 }
 
   hmSecTResRedundacyBackupDown OBJECT-TYPE
    SYNTAX DisplayString
    ACCESS read-only
    STATUS mandatory
    DESCRIPTION
       "Information sent by Master device when Backup device is not reachable."
   ::= { hmSecTResRedundancy 2 }
 
--
-- Logging
--

   hmSecLoggingRemoteActivate OBJECT-TYPE
       SYNTAX INTEGER
                 {
		   yes(1),
                   no(2)
		 }
       ACCESS read-write
       STATUS mandatory
       DESCRIPTION
          "Activate remote logging?"
   ::={ hmSecLogging 1 }

   hmSecLoggingRemoteIP OBJECT-TYPE
      SYNTAX IpAddress
      ACCESS read-write
      STATUS mandatory
      DESCRIPTION
         "IP address of the remote log server"
   ::= { hmSecLogging 2 }

    hmSecLoggingRemotePort OBJECT-TYPE
      SYNTAX DisplayString
      ACCESS read-write
      STATUS mandatory
      DESCRIPTION
         "UDP port of the remote logging service"
     ::= { hmSecLogging 3 }

--
-- hmSecContFilt
--

  hmSecContFiltAVP    OBJECT IDENTIFIER ::= { hmSecContFilt 1 }
  hmSecContFiltHTTP   OBJECT IDENTIFIER ::= { hmSecContFilt 2 }
  hmSecContFiltPOP3   OBJECT IDENTIFIER ::= { hmSecContFilt 3 }
  hmSecContFiltSMTP   OBJECT IDENTIFIER ::= { hmSecContFilt 4 }
  hmSecContFiltFTP    OBJECT IDENTIFIER ::= { hmSecContFilt 5 }


--
-- hmSecContFiltAVP
--

   hmSecContFiltAVPSchedule OBJECT-TYPE
    SYNTAX INTEGER
              {
	        never(1),
		onboot(2),
		quarterhourly(15),
		halfhourly(30),
		hourly(60),
		bihourly(120),
		triplehourly(360),
		sixhourly(720),
		twicedayly(1440)
	      }
    ACCESS read-write
    STATUS mandatory
    DESCRIPTION
       "The period used when updating the antivirus database"
  ::= { hmSecContFiltAVP 1 }

  hmSecContFiltAVPServerTable OBJECT-TYPE
    SYNTAX SEQUENCE OF HmSecContFiltAVPServerEntry
    ACCESS not-accessible
    STATUS mandatory
    DESCRIPTION
      "A table of update server repositories."
   ::= { hmSecContFiltAVP 2 }

  hmSecContFiltAVPServerEntry OBJECT-TYPE
      SYNTAX HmSecContFiltAVPServerEntry
      ACCESS not-accessible
      STATUS mandatory
      DESCRIPTION
       "A single update server repository. "
      INDEX { hmSecContFiltAVPServerIndex }
  ::= { hmSecContFiltAVPServerTable 1 }

  HmSecContFiltAVPServerEntry  ::= SEQUENCE {
     hmSecContFiltAVPServerIndex INTEGER,
     hmSecContFiltAVPServerProtocol INTEGER,
     hmSecContFiltAVPServerURL  DisplayString,
     hmSecContFiltAVPServerLogin  DisplayString,
     hmSecContFiltAVPServerPassword  DisplayString,
     hmSecContFiltAVPServerRowStatus RowStatus
  }

  hmSecContFiltAVPServerIndex OBJECT-TYPE
    SYNTAX INTEGER (1..100)
    ACCESS not-accessible
    STATUS mandatory
    DESCRIPTION
      "Table index."
   ::= { hmSecContFiltAVPServerEntry 1 }

  hmSecContFiltAVPServerProtocol OBJECT-TYPE
    SYNTAX INTEGER
              {
	        http(1),
		ftp(2)
              }
    ACCESS not-accessible
    STATUS mandatory
    DESCRIPTION
      "Protocol used to access the update server."
   ::= { hmSecContFiltAVPServerEntry 2 }

   hmSecContFiltAVPServerURL OBJECT-TYPE
    SYNTAX DisplayString
    ACCESS read-write
    STATUS mandatory
    DESCRIPTION
      "URL of the update server."
   ::= { hmSecContFiltAVPServerEntry 3 }

   hmSecContFiltAVPServerLogin OBJECT-TYPE
    SYNTAX DisplayString
    ACCESS read-write
    STATUS mandatory
    DESCRIPTION
      "Login to be supplied to the update server."
   ::= { hmSecContFiltAVPServerEntry 4 }

   hmSecContFiltAVPServerPassword OBJECT-TYPE
    SYNTAX DisplayString
    ACCESS read-write
    STATUS mandatory
    DESCRIPTION
      "Password to be supplied to the update server."
   ::= { hmSecContFiltAVPServerEntry 5 }

   hmSecContFiltAVPServerRowStatus OBJECT-TYPE
    SYNTAX RowStatus
    ACCESS read-write
    STATUS mandatory
    DESCRIPTION
      "Row Status"
   ::= { hmSecContFiltAVPServerEntry 6 }


  hmSecContFiltAVPHTTPProxy OBJECT IDENTIFIER ::= { hmSecContFiltAVP 3 }

  hmSecContFiltAVPHTTPProxyLogin OBJECT-TYPE
    SYNTAX DisplayString
    ACCESS read-write
    STATUS mandatory
    DESCRIPTION
       "Login for a HTTP proxy for retrival of anti-virus patterns."
   ::= { hmSecContFiltAVPHTTPProxy 1 }

  hmSecContFiltAVPHTTPProxyPasswd OBJECT-TYPE
    SYNTAX DisplayString
    ACCESS read-write
    STATUS mandatory
    DESCRIPTION
       "Password for hmSecContFiltAVPHTTPProxyLogin."
   ::= { hmSecContFiltAVPHTTPProxy 2 }

  hmSecContFiltAVPHTTPProxyServer OBJECT-TYPE
    SYNTAX DisplayString
    ACCESS read-write
    STATUS mandatory
    DESCRIPTION
       "Hostname or IP of an HTTP proxy for retrival of anti-virus patterns."
   ::= { hmSecContFiltAVPHTTPProxy 3 }

  hmSecContFiltAVPHTTPProxyPort OBJECT-TYPE
    SYNTAX DisplayString
    ACCESS read-write
    STATUS mandatory
    DESCRIPTION
       "Port of an HTTP proxy for retrival of anti-virus patterns, eg. 3128."
   ::= { hmSecContFiltAVPHTTPProxy 4 }

  hmSecContFiltAVPFTPProxy OBJECT IDENTIFIER ::= { hmSecContFiltAVP 4 }

  hmSecContFiltAVPFTPProxyLogin OBJECT-TYPE
    SYNTAX DisplayString
    ACCESS read-write
    STATUS mandatory
    DESCRIPTION
       "Login for a FTP proxy for retrival of anti-virus patterns."
   ::= { hmSecContFiltAVPFTPProxy 1 }

  hmSecContFiltAVPFTPProxyPasswd OBJECT-TYPE
    SYNTAX DisplayString
    ACCESS read-write
    STATUS mandatory
    DESCRIPTION
       "Password for hmSecContFiltAVPFTPProxyLogin."
   ::= { hmSecContFiltAVPFTPProxy 2 }

  hmSecContFiltAVPFTPProxyServer OBJECT-TYPE
    SYNTAX DisplayString
    ACCESS read-write
    STATUS mandatory
    DESCRIPTION
       "Hostname or IP of an FTP proxy for retrival of anti-virus patterns."
   ::= { hmSecContFiltAVPFTPProxy 3 }

  hmSecContFiltAVPFTPProxyPort OBJECT-TYPE
    SYNTAX DisplayString
    ACCESS read-write
    STATUS mandatory
    DESCRIPTION
       "Port of an FTP proxy for retrival of anti-virus patterns, eg. 3128."
   ::= { hmSecContFiltAVPFTPProxy 4 }


-- global AVP settings

   hmSecContFiltAVPLogLevel OBJECT-TYPE
    SYNTAX INTEGER (1..5)
    ACCESS read-write
    STATUS mandatory
    DESCRIPTION
       "AVP log detail level with 0 lowest 5 highest, defaults to 2."
  ::= { hmSecContFiltAVP 5 }

   hmSecContFiltAVPMaxConnections OBJECT-TYPE
    SYNTAX INTEGER
    ACCESS read-write
    STATUS mandatory
    DESCRIPTION
       "Maximum number of connections the AVP will handle."
  ::= { hmSecContFiltAVP 6 }

   hmSecContFiltAVPScanTimeout OBJECT-TYPE
    SYNTAX INTEGER
    ACCESS read-write
    STATUS mandatory
    DESCRIPTION
       "Maximum time the protocol wrapper will wait for the scan engine in seconds."
  ::= { hmSecContFiltAVP 7 }


  hmSecContFiltAVPpass    OBJECT IDENTIFIER ::= { hmSecContFiltAVP 8 }

   hmSecContFiltAVPpassCorrupt OBJECT-TYPE
    SYNTAX INTEGER
              {
	        yes(1),
		no(2)
	      }
    ACCESS read-write
    STATUS mandatory
    DESCRIPTION
       "Let corrupt (archive) files pass, treat them as not virus infected."
  ::= { hmSecContFiltAVPpass 1 }


   hmSecContFiltAVPpassEncrypted OBJECT-TYPE
    SYNTAX INTEGER
              {
	        yes(1),
		no(2)
	      }
    ACCESS read-write
    STATUS mandatory
    DESCRIPTION
       "Let encrypted files pass, treat them as not virus infected."
  ::= { hmSecContFiltAVPpass 2 }


   hmSecContFiltAVPpassSuspicious OBJECT-TYPE
    SYNTAX INTEGER
              {
	        yes(1),
		no(2)
	      }
    ACCESS read-write
    STATUS mandatory
    DESCRIPTION
       "Let suspicious files (e.g. known spyware) pass, treat them as not virus infected."
  ::= { hmSecContFiltAVPpass 3 }


   hmSecContFiltAVPpassWarnings OBJECT-TYPE
    SYNTAX INTEGER
              {
	        yes(1),
		no(2)
	      }
    ACCESS read-write
    STATUS mandatory
    DESCRIPTION
       "Let files pass that triggered a warning, treat them as not virus infected."
  ::= { hmSecContFiltAVPpass 4 }


-- hmSecContFiltQuarantine

  hmSecContFiltQuarantine    OBJECT IDENTIFIER ::= { hmSecContFiltAVP 9 }

  hmSecContFiltQuarantineClean OBJECT-TYPE
    SYNTAX INTEGER
              {
	        yes(1),
		no(2)
	      }
    ACCESS read-write
    STATUS mandatory
    DESCRIPTION
       "Send clean files to quarantine server for debugging
        (warning: do not violate privacy law with this option!)."
   ::= { hmSecContFiltQuarantine 1 }

  hmSecContFiltQuarantineError OBJECT-TYPE
    SYNTAX INTEGER
              {
	        yes(1),
		no(2)
	      }
    ACCESS read-write
    STATUS mandatory
    DESCRIPTION
       "Send files producing an error to quarantine server for debugging
        (warning: do not violate privacy law with this option!)."
   ::= { hmSecContFiltQuarantine 2 }

  hmSecContFiltQuarantineVirus OBJECT-TYPE
    SYNTAX INTEGER
              {
	        yes(1),
		no(2)
	      }
    ACCESS read-write
    STATUS mandatory
    DESCRIPTION
       "Send files found to be infected to quarantine server for debugging
        (warning: do not violate privacy law with this option!)."
   ::= { hmSecContFiltQuarantine 3 }

  hmSecContFiltQuarantineSrvIP OBJECT-TYPE
    SYNTAX DisplayString
    ACCESS read-write
    STATUS mandatory
    DESCRIPTION
       "IP Address of the quarantine server."
   ::= { hmSecContFiltQuarantine 4 }

  hmSecContFiltQuarantineSrvPort OBJECT-TYPE
    SYNTAX DisplayString
    ACCESS read-write
    STATUS mandatory
    DESCRIPTION
       "Port used for/on the quarantine server (Innominate Quarantine Server Protocol)."
   ::= { hmSecContFiltQuarantine 5 }


-- hmSecContFiltInfo

  hmSecContFiltInfo    OBJECT IDENTIFIER ::= { hmSecContFiltAVP 10 }

  hmSecContFiltInfoFlashID OBJECT-TYPE
    SYNTAX DisplayString
    ACCESS read-only
    STATUS mandatory
    DESCRIPTION
       "Flash ID of the device to be used for license handling."
   ::= { hmSecContFiltInfo 1 }

--
-- hmSecContFiltHTTP
--

   hmSecContFiltHTTPEnable OBJECT-TYPE
    SYNTAX INTEGER
              {
	        enable(1),
		disable(2)
	      }
    ACCESS read-write
    STATUS mandatory
    DESCRIPTION
       "Enable HTTP procotol proxy"
  ::= { hmSecContFiltHTTP 1 }

   hmSecContFiltHTTPVirusAction OBJECT-TYPE
    SYNTAX INTEGER
              {
	        error(1)
	      }
    ACCESS read-write
    STATUS mandatory
    DESCRIPTION
       "Action to take on virus detection"
  ::= { hmSecContFiltHTTP 2 }

   hmSecContFiltHTTPMaxSize OBJECT-TYPE
    SYNTAX INTEGER
              {
	        dottwomeg(200000),
	        dotfivemeg(500000),
	        onemeg(1000000),
	        twomeg(2000000),
	        fourmeg(4000000),
	        fivemeg(5000000),
	        eightmeg(8000000)
	      }
    ACCESS read-write
    STATUS mandatory
    DESCRIPTION
       "Maximum object size to be handled (actually sizes may depend on
	software version and underlying hardware."
  ::= { hmSecContFiltHTTP 3 }

   hmSecContFiltHTTPExceedAction OBJECT-TYPE
    SYNTAX INTEGER
              {
	        block(1),
		pass(2)
	      }
    ACCESS read-write
    STATUS mandatory
    DESCRIPTION
       "Action to take if an object exceeds the maximum handled size"
  ::= { hmSecContFiltHTTP 4 }

  hmSecContFiltHTTPSrvrTable OBJECT-TYPE
    SYNTAX SEQUENCE OF HmSecContFiltHTTPSrvrEntry
    ACCESS not-accessible
    STATUS mandatory
    DESCRIPTION
      "A table of update server repositories."
   ::= { hmSecContFiltHTTP 5 }

  hmSecContFiltHTTPSrvrEntry OBJECT-TYPE
      SYNTAX HmSecContFiltHTTPSrvrEntry
      ACCESS not-accessible
      STATUS mandatory
      DESCRIPTION
       "A single update server repository. "
      INDEX { hmSecContFiltHTTPSrvrIndex }
  ::= { hmSecContFiltHTTPSrvrTable 1 }

  HmSecContFiltHTTPSrvrEntry  ::= SEQUENCE {
     hmSecContFiltHTTPSrvrIndex INTEGER,
     hmSecContFiltHTTPSrvrIP DisplayString,
     hmSecContFiltHTTPSrvrPort  DisplayString,
     hmSecContFiltHTTPSrvrScanAction  INTEGER,
     hmSecContFiltHTTPSrvrRowStatus RowStatus,
     hmSecContFiltHTTPSrvrComment  DisplayString
  }

  hmSecContFiltHTTPSrvrIndex OBJECT-TYPE
    SYNTAX INTEGER (1..100)
    ACCESS not-accessible
    STATUS mandatory
    DESCRIPTION
      "Table index."
   ::= { hmSecContFiltHTTPSrvrEntry 1 }

   hmSecContFiltHTTPSrvrIP OBJECT-TYPE
    SYNTAX DisplayString
    ACCESS read-write
    STATUS mandatory
    DESCRIPTION
      "IP address expression for http server(s)."
   ::= { hmSecContFiltHTTPSrvrEntry 2 }

  hmSecContFiltHTTPSrvrPort OBJECT-TYPE
    SYNTAX DisplayString
    ACCESS read-write
    STATUS mandatory
    DESCRIPTION
      "Port the HTTP server listens to.."
   ::= { hmSecContFiltHTTPSrvrEntry 3 }

  hmSecContFiltHTTPSrvrScanAction OBJECT-TYPE
    SYNTAX INTEGER
              {
	        scan(1),
		noscan(2)
              }
    ACCESS read-write
    STATUS mandatory
    DESCRIPTION
      "Action to be taken when contacting respective servers."
   ::= { hmSecContFiltHTTPSrvrEntry 4 }

   hmSecContFiltHTTPSrvrRowStatus OBJECT-TYPE
    SYNTAX RowStatus
    ACCESS read-write
    STATUS mandatory
    DESCRIPTION
      "Row Status"
   ::= { hmSecContFiltHTTPSrvrEntry 5 }

   hmSecContFiltHTTPSrvrComment OBJECT-TYPE
    SYNTAX DisplayString
    ACCESS read-write
    STATUS mandatory
    DESCRIPTION
      "Comment for this rule."
   ::= { hmSecContFiltHTTPSrvrEntry 6 }

--
-- hmSecContFiltPOP3
--

   hmSecContFiltPOP3Enable OBJECT-TYPE
    SYNTAX INTEGER
              {
	        enable(1),
		disable(2)
	      }
    ACCESS read-write
    STATUS mandatory
    DESCRIPTION
       "Enable POP3 procotol proxy"
  ::= { hmSecContFiltPOP3 1 }

   hmSecContFiltPOP3VirusAction OBJECT-TYPE
    SYNTAX INTEGER
              {
	        error(1),
		mail(2)
	      }
    ACCESS read-write
    STATUS mandatory
    DESCRIPTION
       "Action to take on virus detection"
  ::= { hmSecContFiltPOP3 2 }

   hmSecContFiltPOP3MaxSize OBJECT-TYPE
    SYNTAX INTEGER
              {
	        dottwomeg(200000),
	        dotfivemeg(500000),
	        onemeg(1000000),
	        twomeg(2000000),
	        fourmeg(4000000),
	        fivemeg(5000000),
	        eightmeg(8000000)
	      }
    ACCESS read-write
    STATUS mandatory
    DESCRIPTION
       "Maximum object size to be handled (actually sizes may depend on
	software version and underlying hardware."
  ::= { hmSecContFiltPOP3 3 }

   hmSecContFiltPOP3ExceedAction OBJECT-TYPE
    SYNTAX INTEGER
              {
	        block(1),
		pass(2)
	      }
    ACCESS read-write
    STATUS mandatory
    DESCRIPTION
       "Action to take if an object exceeds the maximum handled size"
  ::= { hmSecContFiltPOP3 4 }

  hmSecContFiltPOP3SrvrTable OBJECT-TYPE
    SYNTAX SEQUENCE OF HmSecContFiltPOP3SrvrEntry
    ACCESS not-accessible
    STATUS mandatory
    DESCRIPTION
      "A table of update server repositories."
   ::= { hmSecContFiltPOP3 5 }

  hmSecContFiltPOP3SrvrEntry OBJECT-TYPE
      SYNTAX HmSecContFiltPOP3SrvrEntry
      ACCESS not-accessible
      STATUS mandatory
      DESCRIPTION
       "A single update server repository. "
      INDEX { hmSecContFiltPOP3SrvrIndex }
  ::= { hmSecContFiltPOP3SrvrTable 1 }

  HmSecContFiltPOP3SrvrEntry  ::= SEQUENCE {
     hmSecContFiltPOP3SrvrIndex INTEGER,
     hmSecContFiltPOP3SrvrIP DisplayString,
     hmSecContFiltPOP3SrvrPort  DisplayString,
     hmSecContFiltPOP3SrvrScanAction  INTEGER,
     hmSecContFiltPOP3SrvrRowStatus RowStatus,
     hmSecContFiltPOP3SrvrComment  DisplayString
  }

  hmSecContFiltPOP3SrvrIndex OBJECT-TYPE
    SYNTAX INTEGER (1..100)
    ACCESS not-accessible
    STATUS mandatory
    DESCRIPTION
      "Table index."
   ::= { hmSecContFiltPOP3SrvrEntry 1 }

   hmSecContFiltPOP3SrvrIP OBJECT-TYPE
    SYNTAX DisplayString
    ACCESS read-write
    STATUS mandatory
    DESCRIPTION
      "IP address expression for pop3 server(s)."
   ::= { hmSecContFiltPOP3SrvrEntry 2 }

   hmSecContFiltPOP3SrvrPort OBJECT-TYPE
    SYNTAX DisplayString
    ACCESS read-write
    STATUS mandatory
    DESCRIPTION
      "Port expression for pop3 server(s)."
   ::= { hmSecContFiltPOP3SrvrEntry 3 }

  hmSecContFiltPOP3SrvrScanAction OBJECT-TYPE
    SYNTAX INTEGER
              {
	        scan(1),
		noscan(2)
              }
    ACCESS not-accessible
    STATUS mandatory
    DESCRIPTION
      "Action to be taken when contacting respective servers."
   ::= { hmSecContFiltPOP3SrvrEntry 4 }

   hmSecContFiltPOP3SrvrRowStatus OBJECT-TYPE
    SYNTAX RowStatus
    ACCESS read-write
    STATUS mandatory
    DESCRIPTION
      "Row Status"
   ::= { hmSecContFiltPOP3SrvrEntry 5 }

   hmSecContFiltPOP3SrvrComment OBJECT-TYPE
    SYNTAX DisplayString
    ACCESS read-write
    STATUS mandatory
    DESCRIPTION
      "Comment for this rule."
   ::= { hmSecContFiltPOP3SrvrEntry 6 }

--
-- hmSecContFiltSMTP
--

   hmSecContFiltSMTPEnable OBJECT-TYPE
    SYNTAX INTEGER
              {
	        enable(1),
		disable(2)
	      }
    ACCESS read-write
    STATUS mandatory
    DESCRIPTION
       "Enable SMTP procotol proxy"
  ::= { hmSecContFiltSMTP 1 }

   hmSecContFiltSMTPVirusAction OBJECT-TYPE
    SYNTAX INTEGER
              {
	        error(1)
	      }
    ACCESS read-write
    STATUS mandatory
    DESCRIPTION
       "Action to take on virus detection"
  ::= { hmSecContFiltSMTP 2 }

   hmSecContFiltSMTPMaxSize OBJECT-TYPE
    SYNTAX INTEGER
              {
	        dottwomeg(200000),
	        dotfivemeg(500000),
	        onemeg(1000000),
	        twomeg(2000000),
	        fourmeg(4000000),
	        fivemeg(5000000),
	        eightmeg(8000000)
	      }
    ACCESS read-write
    STATUS mandatory
    DESCRIPTION
       "Maximum object size to be handled (actually sizes may depend on
	software version and underlying hardware."
  ::= { hmSecContFiltSMTP 3 }

   hmSecContFiltSMTPExceedAction OBJECT-TYPE
    SYNTAX INTEGER
              {
	        block(1),
		pass(2)
	      }
    ACCESS read-write
    STATUS mandatory
    DESCRIPTION
       "Action to take if an object exceeds the maximum handled size"
  ::= { hmSecContFiltSMTP 4 }

  hmSecContFiltSMTPSrvrTable OBJECT-TYPE
    SYNTAX SEQUENCE OF HmSecContFiltSMTPSrvrEntry
    ACCESS not-accessible
    STATUS mandatory
    DESCRIPTION
      "A table of update server repositories."
   ::= { hmSecContFiltSMTP 5 }

  hmSecContFiltSMTPSrvrEntry OBJECT-TYPE
      SYNTAX HmSecContFiltSMTPSrvrEntry
      ACCESS not-accessible
      STATUS mandatory
      DESCRIPTION
       "A single update server repository. "
      INDEX { hmSecContFiltSMTPSrvrIndex }
  ::= { hmSecContFiltSMTPSrvrTable 1 }

  HmSecContFiltSMTPSrvrEntry  ::= SEQUENCE {
     hmSecContFiltSMTPSrvrIndex INTEGER,
     hmSecContFiltSMTPSrvrIP DisplayString,
     hmSecContFiltSMTPSrvrPort  DisplayString,
     hmSecContFiltSMTPSrvrScanAction  INTEGER,
     hmSecContFiltSMTPSrvrRowStatus RowStatus,
     hmSecContFiltSMTPSrvrComment  DisplayString
  }

  hmSecContFiltSMTPSrvrIndex OBJECT-TYPE
    SYNTAX INTEGER (1..100)
    ACCESS not-accessible
    STATUS mandatory
    DESCRIPTION
      "Table index."
   ::= { hmSecContFiltSMTPSrvrEntry 1 }

   hmSecContFiltSMTPSrvrIP OBJECT-TYPE
    SYNTAX DisplayString
    ACCESS read-write
    STATUS mandatory
    DESCRIPTION
      "IP address expression for smtp server(s)."
   ::= { hmSecContFiltSMTPSrvrEntry 2 }

   hmSecContFiltSMTPSrvrPort OBJECT-TYPE
    SYNTAX DisplayString
    ACCESS read-write
    STATUS mandatory
    DESCRIPTION
      "Port expression for smtp server(s)."
   ::= { hmSecContFiltSMTPSrvrEntry 3 }

  hmSecContFiltSMTPSrvrScanAction OBJECT-TYPE
    SYNTAX INTEGER
              {
	        scan(1),
		noscan(2)
              }
    ACCESS not-accessible
    STATUS mandatory
    DESCRIPTION
      "Action to be taken when contacting respective servers."
   ::= { hmSecContFiltSMTPSrvrEntry 4 }

   hmSecContFiltSMTPSrvrRowStatus OBJECT-TYPE
    SYNTAX RowStatus
    ACCESS read-write
    STATUS mandatory
    DESCRIPTION
      "Row Status"
   ::= { hmSecContFiltSMTPSrvrEntry 5 }

   hmSecContFiltSMTPSrvrComment OBJECT-TYPE
    SYNTAX DisplayString
    ACCESS read-write
    STATUS mandatory
    DESCRIPTION
      "Comment for this rule."
   ::= { hmSecContFiltSMTPSrvrEntry 6 }

--
-- hmSecContFiltFTP
--
 
   hmSecContFiltFTPEnable OBJECT-TYPE
    SYNTAX INTEGER
              {
	        enable(1),
		disable(2)
	      }
    ACCESS read-write
    STATUS mandatory
    DESCRIPTION
       "Enable FTP procotol proxy"
  ::= { hmSecContFiltFTP 1 }
 
   hmSecContFiltFTPVirusAction OBJECT-TYPE
    SYNTAX INTEGER
              {
	        error(1)
	      }
    ACCESS read-write
    STATUS mandatory
    DESCRIPTION
       "Action to take on virus detection"
  ::= { hmSecContFiltFTP 2 }
 
   hmSecContFiltFTPMaxSize OBJECT-TYPE
    SYNTAX INTEGER
              {
	        dottwomeg(200000),
	        dotfivemeg(500000),
	        onemeg(1000000),
	        twomeg(2000000),
	        fourmeg(4000000),
	        fivemeg(5000000),
	        eightmeg(8000000)
	      }
    ACCESS read-write
    STATUS mandatory
    DESCRIPTION
       "Maximum object size to be handled (actually sizes may depend on
	software version and underlying hardware."
  ::= { hmSecContFiltFTP 3 }
 
   hmSecContFiltFTPExceedAction OBJECT-TYPE
    SYNTAX INTEGER
              {
	        block(1),
		pass(2)
	      }
    ACCESS read-write
    STATUS mandatory
    DESCRIPTION
       "Action to take if an object exceeds the maximum handled size"
  ::= { hmSecContFiltFTP 4 }
 
  hmSecContFiltFTPSrvrTable OBJECT-TYPE
    SYNTAX SEQUENCE OF HmSecContFiltFTPSrvrEntry
    ACCESS not-accessible
    STATUS mandatory
    DESCRIPTION
      "A table of update server repositories."
   ::= { hmSecContFiltFTP 5 }
 
  hmSecContFiltFTPSrvrEntry OBJECT-TYPE
      SYNTAX HmSecContFiltFTPSrvrEntry
      ACCESS not-accessible
      STATUS mandatory
      DESCRIPTION
       "A single update server repository. "
      INDEX { hmSecContFiltFTPSrvrIndex }
  ::= { hmSecContFiltFTPSrvrTable 1 }
 
  HmSecContFiltFTPSrvrEntry  ::= SEQUENCE {
     hmSecContFiltFTPSrvrIndex INTEGER,
     hmSecContFiltFTPSrvrIP DisplayString,
     hmSecContFiltFTPSrvrPort  DisplayString,
     hmSecContFiltFTPSrvrScanAction  INTEGER,
     hmSecContFiltFTPSrvrRowStatus RowStatus,
     hmSecContFiltFTPSrvrComment  DisplayString
  }
 
  hmSecContFiltFTPSrvrIndex OBJECT-TYPE
    SYNTAX INTEGER (1..100)
    ACCESS not-accessible
    STATUS mandatory
    DESCRIPTION
      "Table index."
   ::= { hmSecContFiltFTPSrvrEntry 1 }
 
   hmSecContFiltFTPSrvrIP OBJECT-TYPE
    SYNTAX DisplayString
    ACCESS read-write
    STATUS mandatory
    DESCRIPTION
      "IP address expression for smtp server(s)."
   ::= { hmSecContFiltFTPSrvrEntry 2 }
 
   hmSecContFiltFTPSrvrPort OBJECT-TYPE
    SYNTAX DisplayString
    ACCESS read-write
    STATUS mandatory
    DESCRIPTION
      "Port expression for smtp server(s)."
   ::= { hmSecContFiltFTPSrvrEntry 3 }
 
  hmSecContFiltFTPSrvrScanAction OBJECT-TYPE
    SYNTAX INTEGER
              {
	        scan(1),
		noscan(2)
              }
    ACCESS not-accessible
    STATUS mandatory
    DESCRIPTION
      "Action to be taken when contacting respective servers."
   ::= { hmSecContFiltFTPSrvrEntry 4 }
 
   hmSecContFiltFTPSrvrRowStatus OBJECT-TYPE
    SYNTAX RowStatus
    ACCESS read-write
    STATUS mandatory
    DESCRIPTION
      "Row Status"
   ::= { hmSecContFiltFTPSrvrEntry 5 }
 
   hmSecContFiltFTPSrvrComment OBJECT-TYPE
    SYNTAX DisplayString
    ACCESS read-write
    STATUS mandatory
    DESCRIPTION
      "Comment for this rule."
   ::= { hmSecContFiltFTPSrvrEntry 6 }
 
--
-- Blade
--

  hmSecBladeRackID OBJECT-TYPE
    SYNTAX INTEGER
    ACCESS read-write
    STATUS mandatory
    DESCRIPTION
      "Blade rack ID, read-only on a blade, read-write on a controller"
  ::= { hmSecBlade 1 }

  hmSecBladeSlotID OBJECT-TYPE
    SYNTAX INTEGER
    ACCESS not-accessible
    STATUS mandatory
    DESCRIPTION
      "Blade slot ID, slot ID in a hmSec Rack"
  ::= { hmSecBlade 2 }


  hmSecBladeCtrlTable OBJECT-TYPE
    SYNTAX SEQUENCE OF  HmSecBladeCtrlEntry
    ACCESS not-accessible
    STATUS mandatory
    DESCRIPTION
      "Overview of controlled blades."
   ::= { hmSecBlade 3 }

  hmSecBladeCtrlEntry OBJECT-TYPE
      SYNTAX HmSecBladeCtrlEntry
      ACCESS not-accessible
      STATUS mandatory
      DESCRIPTION
       "A single update server repository. "
      INDEX { hmSecBladeCtrlIndex }
  ::= { hmSecBladeCtrlTable 1 }

  HmSecBladeCtrlEntry  ::= SEQUENCE {
     hmSecBladeCtrlIndex INTEGER,
     hmSecBladeCtrlDevice DisplayString,
     hmSecBladeCtrlStatus INTEGER,
     hmSecBladeCtrlAVRRevision DisplayString,
     hmSecBladeCtrlSlotID DisplayString,
     hmSecBladeCtrlProductID DisplayString,
     hmSecBladeCtrlAssemblyID DisplayString,
     hmSecBladeCtrlSerial DisplayString,
     hmSecBladeCtrlFlashID DisplayString,
     hmSecBladeCtrlVersion DisplayString,
     hmSecBladeCtrlBackup INTEGER,
     hmSecBladeCtrlRestore INTEGER
  }

  hmSecBladeCtrlIndex OBJECT-TYPE
    SYNTAX INTEGER (1..100)
    ACCESS not-accessible
    STATUS mandatory
    DESCRIPTION
      "Table index."
   ::= { hmSecBladeCtrlEntry 1 }

   hmSecBladeCtrlDevice OBJECT-TYPE
    SYNTAX DisplayString
    ACCESS read-only
    STATUS mandatory
    DESCRIPTION
      "The name of the device inside the slot."
   ::= { hmSecBladeCtrlEntry 2 }

   hmSecBladeCtrlStatus OBJECT-TYPE
    SYNTAX INTEGER {
      absent(1),
      present(2),
      online(3)
    }
    ACCESS read-only
    STATUS mandatory
    DESCRIPTION
      "The status of the blade/slot."
   ::= { hmSecBladeCtrlEntry 3 }

   hmSecBladeCtrlAVRRevision OBJECT-TYPE
    SYNTAX DisplayString
    ACCESS read-only
    STATUS mandatory
    DESCRIPTION
      "The AVR revision of the blades bus controller."
   ::= { hmSecBladeCtrlEntry 4 }

   hmSecBladeCtrlSlotID OBJECT-TYPE
    SYNTAX DisplayString
    ACCESS read-only
    STATUS mandatory
    DESCRIPTION
      "The blades slot ID, as seen by the blade."
   ::= { hmSecBladeCtrlEntry 5 }

   hmSecBladeCtrlProductID OBJECT-TYPE
    SYNTAX DisplayString
    ACCESS read-only
    STATUS mandatory
    DESCRIPTION
      "The blades product ID."
   ::= { hmSecBladeCtrlEntry 6 }

   hmSecBladeCtrlAssemblyID OBJECT-TYPE
    SYNTAX DisplayString
    ACCESS read-only
    STATUS mandatory
    DESCRIPTION
      "The blades assembly ID."
   ::= { hmSecBladeCtrlEntry 7 }

   hmSecBladeCtrlSerial OBJECT-TYPE
    SYNTAX DisplayString
    ACCESS read-only
    STATUS mandatory
    DESCRIPTION
      "The blades serial number."
   ::= { hmSecBladeCtrlEntry 8 }

   hmSecBladeCtrlFlashID OBJECT-TYPE
    SYNTAX DisplayString
    ACCESS read-only
    STATUS mandatory
    DESCRIPTION
      "The blades Flash ID."
   ::= { hmSecBladeCtrlEntry 9 }

   hmSecBladeCtrlVersion OBJECT-TYPE
    SYNTAX DisplayString
    ACCESS read-only
    STATUS mandatory
    DESCRIPTION
      "The blades software version."
   ::= { hmSecBladeCtrlEntry 10 }

   hmSecBladeCtrlBackup OBJECT-TYPE
    SYNTAX INTEGER {
      yes(1),
      no(2)
    }
    ACCESS read-write
    STATUS mandatory
    DESCRIPTION
      "Wether to automatically pull the configuration off the blade/slot."
   ::= { hmSecBladeCtrlEntry 11 }

   hmSecBladeCtrlReconfig OBJECT-TYPE
    SYNTAX INTEGER {
      yes(1),
      no(2)
    }
    ACCESS read-write
    STATUS mandatory
    DESCRIPTION
      "Wether to automatically push the configuration to the blade freshly inserted into the slot."
   ::= { hmSecBladeCtrlEntry 12 }


  hmSecBladePwrTable OBJECT-TYPE
    SYNTAX SEQUENCE OF  HmSecBladePwrEntry
    ACCESS not-accessible
    STATUS mandatory
    DESCRIPTION
      "Overview of controlled power supplies."
   ::= { hmSecBlade 4 }

  hmSecBladePwrEntry OBJECT-TYPE
      SYNTAX HmSecBladePwrEntry
      ACCESS not-accessible
      STATUS mandatory
      DESCRIPTION
       "Table entry."
      INDEX { hmSecBladePwrIndex }
  ::= { hmSecBladePwrTable 1 }

  HmSecBladePwrEntry  ::= SEQUENCE {
     hmSecBladePwrIndex INTEGER,
     hmSecBladePwrStatus INTEGER
  }

  hmSecBladePwrIndex OBJECT-TYPE
    SYNTAX INTEGER (1..100)
    ACCESS not-accessible
    STATUS mandatory
    DESCRIPTION
      "Table index."
   ::= { hmSecBladePwrEntry 1 }

   hmSecBladePwrStatus OBJECT-TYPE
    SYNTAX INTEGER {
      absent(1),
      fatal(2),
      defect(3),
      ok(4)
    }
    ACCESS read-only
    STATUS mandatory
    DESCRIPTION
      "Status of the power supply."
   ::= { hmSecBladePwrEntry 2 }


--
-- Configuration Profiles
--

  hmSecProfilePush OBJECT IDENTIFIER ::= { hmSecProfile 1 }

  hmSecProfilePull OBJECT IDENTIFIER ::= { hmSecProfile 2 }

  hmSecProfilePullSchedule OBJECT-TYPE
    SYNTAX INTEGER
              {
	        never(1),
		onboot(2),
		quarterhourly(15),
		halfhourly(30),
		hourly(60),
		bihourly(120),
		triplehourly(360),
		sixhourly(720),
		twicedayly(1440)
	      }
    ACCESS read-write
    STATUS mandatory
    DESCRIPTION
       "The period used when polling remote configuration profiles."
  ::= { hmSecProfilePull 1 }

  hmSecProfilePullHTTPS OBJECT IDENTIFIER ::= { hmSecProfilePull 2 }

  hmSecProfilePullHTTPSCert OBJECT-TYPE
    SYNTAX DisplayString
    ACCESS read-write
    STATUS mandatory
    DESCRIPTION
      "X.509 Certificate of the HTTPS server to pull configuration profiles
       from. This used to authenticate the HTTPS server."
  ::= { hmSecProfilePullHTTPS 1 }

  hmSecProfilePullHTTPSServer OBJECT-TYPE
    SYNTAX DisplayString
    ACCESS read-write
    STATUS mandatory
    DESCRIPTION
      "Hostname or IP of the HTTPS server to pull configuration profiles
       from."
  ::= { hmSecProfilePullHTTPS 2 }

  hmSecProfilePullHTTPSPort OBJECT-TYPE
    SYNTAX DisplayString
    ACCESS read-write
    STATUS mandatory
    DESCRIPTION
      "Port of the HTTPS server to pull configuration profiles from.
       Usually 443."
  ::= { hmSecProfilePullHTTPS 3 }

  hmSecProfilePullHTTPSFile OBJECT-TYPE
    SYNTAX DisplayString
    ACCESS read-write
    STATUS mandatory
    DESCRIPTION
      "Filename of the configuration to pull. Default is an empty name, in
       which case the serialnumber with the extension '.atv' is used."
  ::= { hmSecProfilePullHTTPS 4 }

  hmSecProfilePullHTTPSLogin OBJECT-TYPE
    SYNTAX DisplayString
    ACCESS read-write
    STATUS mandatory
    DESCRIPTION
      "Login on the HTTPS server to pull configuration profiles from."
  ::= { hmSecProfilePullHTTPS 5 }

  hmSecProfilePullHTTPSPasswd OBJECT-TYPE
    SYNTAX DisplayString
    ACCESS read-write
    STATUS mandatory
    DESCRIPTION
      "Password on the HTTPS server to pull configuration profiles from."
  ::= { hmSecProfilePullHTTPS 6 }

  hmSecProfilePullHTTPSDirectory OBJECT-TYPE
    SYNTAX DisplayString
    ACCESS read-write
    STATUS mandatory
    DESCRIPTION
      "Directory on the HTTPS server to pull configuration profiles from."
  ::= { hmSecProfilePullHTTPS 7 }
 
-- ****************************************************************
-- * Traps according to RfC 1215                                  *
-- ****************************************************************

  hmSecTraps  OBJECT IDENTIFIER ::= { hmSecInfo 5 }

   hmSecTrapDiscFull TRAP-TYPE
    ENTERPRISE  hmSecTraps
    VARIABLES  { hmSecTResDiscFull }
    DESCRIPTION
       "Status of file system free space. If multiple file systems, the worst state is used."
   ::= 1

   hmSecTrapCpuLoadHigh TRAP-TYPE
    ENTERPRISE  hmSecTraps
    VARIABLES  { hmSecTResCpuLoadHigh }
    DESCRIPTION
       "CPU load above 1."
   ::= 2

   hmSecTrapMemoryFull TRAP-TYPE
    ENTERPRISE  hmSecTraps
    VARIABLES  { hmSecTResMemoryFull }
    DESCRIPTION
       "Free memory (RAM) low."
   ::= 3

   hmSecTrapColdstart TRAP-TYPE
    ENTERPRISE  hmSecTraps
    VARIABLES  { hmSecTResColdstart }
    DESCRIPTION
       "Trap sent when system rebooted (snmp daemon started)."
   ::= 4


--
-- Traps with enterprise = hmSecurityGateway
--
hmSecHTTPSLoginTrap TRAP-TYPE
	ENTERPRISE	hmSecurityGateway
	VARIABLES	{ hmSecHTTPSLastAccessIP }
	DESCRIPTION
	  "This trap is sent when someone is trying to open a HTTPS session
           using the wrong password. hmSecHTTPSLastAccessIP contains the IP
	   address of the last unsuccessfull login request."
	::= 1

hmSecShellLoginTrap TRAP-TYPE
	ENTERPRISE	hmSecurityGateway
	VARIABLES	{ hmSecShellLastAccessIP }
	DESCRIPTION
	    "This trap is sent when someone opens the shell through SSH or
	     serial console. hmSecShellAccessLastIP contains the IP address of
	     the login request. The value of hmSecShellAccessLastIP is 0.0.0.0,
	     if the request was sent via serial console. "
	::= 2

hmSecDHCPNewClientTrap TRAP-TYPE
	ENTERPRISE	hmSecurityGateway
	VARIABLES	{ hmSecDHCPLastAccessMAC }
	DESCRIPTION
	    "This trap is sent when a DHCP request was received from an unknown
	     client"
	::= 3


--
-- hmSecTrapAV
--

  hmSecTrapAV  OBJECT IDENTIFIER ::= { hmSecInfo 6 }

   hmSecTrapAvUpdateDone TRAP-TYPE
    ENTERPRISE  hmSecTrapAV
    VARIABLES  { hmSecTResAvUpdateDone }
    DESCRIPTION
       "AV Update was performed successfully."
   ::= 1

   hmSecTrapAvUpdateError TRAP-TYPE
    ENTERPRISE  hmSecTrapAV
    VARIABLES  { hmSecTResAvUpdateError }
    DESCRIPTION
       "Error when performing AV Update."
   ::= 2

   hmSecTrapAvVirusDetected TRAP-TYPE
    ENTERPRISE  hmSecTrapAV
    VARIABLES  { hmSecTResAvVirusDetected }
    DESCRIPTION
       "AV found a virus."
   ::= 3

   hmSecTrapAvFileNotScanned TRAP-TYPE
    ENTERPRISE  hmSecTrapAV
    VARIABLES  { hmSecTResAvFileNotScanned }
    DESCRIPTION
       "The file was not scanned for viruses."
   ::= 4

   hmSecTrapAvFailed TRAP-TYPE
    ENTERPRISE  hmSecTrapAV
    VARIABLES  { hmSecTResAvFailed }
    DESCRIPTION
       "General AV failure."
   ::= 5


--
-- hmSecTrapPlatformSpecific
--

  hmSecTrapPlatformSpecific  OBJECT IDENTIFIER ::= { hmSecInfo 7 }

  hmSecTrapIndustrial  OBJECT IDENTIFIER ::= { hmSecTrapPlatformSpecific 1 }
 
  hmSecTrapIndustrialPowerStatus TRAP-TYPE
   ENTERPRISE  hmSecTrapIndustrial
   VARIABLES  { hmSecPSState }
   DESCRIPTION
       "Trap sent when power supply failure was detected."
   ::= 2
 
  hmSecTrapIndustrialTemperature  TRAP-TYPE
   ENTERPRISE  hmSecTrapIndustrial
   VARIABLES  { hmSecSystemTemperature, hmSecTResIndustrialTempHiLimit, hmSecTResIndustrialTempLowLimit }
   DESCRIPTION
       "Trap reporting temperature exceeding the given limits."
   ::= 1
 
  hmSecTrapSignalRelais TRAP-TYPE
    ENTERPRISE  hmSecTrapIndustrial
    VARIABLES  { hmSecTResSignalRelaisState, hmSecTResSignalRelaisReason, hmSecTResSignalRelaisReasonIdx }
    DESCRIPTION
         "Current state of the signal relais changed (0=off, 1=on)."
   ::= 3
 
  hmSecTrapAutoConfigAdapterState TRAP-TYPE
   ENTERPRISE  hmSecTrapIndustrial
   VARIABLES  { hmSecTResAutoConfigAdapterState }
   DESCRIPTION
       "Trap sent when ACA was accessed."
   ::= 4

  hmSecTrapBladeCTRL  OBJECT IDENTIFIER ::= { hmSecTrapPlatformSpecific 2 }

  hmSecTrapBladeCtrlCfg  OBJECT IDENTIFIER ::= { hmSecTrapBladeCTRL 5 }

  hmSecTrapBladeCtrlPowerStatus TRAP-TYPE
   ENTERPRISE  hmSecTrapBladeCTRL
   VARIABLES  { hmSecTResBladeRackID, hmSecTResBladeSlotNr, hmSecTResBladeCtrlPowerStatus }
   DESCRIPTION
         "BladePack's power supplies status changed."
   ::= 2

  hmSecTrapBladeCtrlRunStatus TRAP-TYPE
   ENTERPRISE  hmSecTrapBladeCTRL
   VARIABLES  { hmSecTResBladeRackID, hmSecTResBladeSlotNr, hmSecTResBladeCtrlRunStatus }
   DESCRIPTION
         "Blade's run status changed."
   ::= 3

  hmSecTrapBladeCtrlFailover TRAP-TYPE
   ENTERPRISE  hmSecTrapBladeCTRL
   VARIABLES  { hmSecTResBladeRackID, hmSecTResBladeSlotNr, hmSecTResBladeCtrlFailover }
   DESCRIPTION
         "Blade failover detected (HA configuration only)."
   ::= 4
 
  hmSecTrapBladeCtrlCfgBackup TRAP-TYPE
   ENTERPRISE  hmSecTrapBladeCtrlCfg
   VARIABLES  { hmSecTResBladeRackID, hmSecTResBladeSlotNr, hmSecTResBladeCtrlCfgBackup }
   DESCRIPTION
         "Configuration backup to Blade CTRL is triggered."
   ::= 1

  hmSecTrapBladeCtrlCfgRestored TRAP-TYPE
   ENTERPRISE  hmSecTrapBladeCtrlCfg
   VARIABLES  { hmSecTResBladeRackID, hmSecTResBladeSlotNr, hmSecTResBladeCtrlCfgRestored }
   DESCRIPTION
         "Configuration restore from Blade CTRL is triggered."
   ::= 2

--
-- hmSecTrapRouterRedundancy
--
 
   hmSecTrapRouterRedundancy  OBJECT IDENTIFIER ::= { hmSecInfo 8 }
 
   hmSecTrapRouterRedundancyStatusChange TRAP-TYPE
    ENTERPRISE hmSecTrapRouterRedundancy
    VARIABLES  { hmSecRouterRedundancyState, hmSecTResRedundacyReason }
    DESCRIPTION
       "Current HA cluster state changed."
   ::= 1
 
   hmSecTrapRouterRedundancyBackupDown TRAP-TYPE
    ENTERPRISE hmSecTrapRouterRedundancy
    VARIABLES  { hmSecTResRedundacyBackupDown }
    DESCRIPTION
       "Backup device  is not reachable by Master device (This trap is only sent, when ICMP checks are activated)."
   ::= 2
END

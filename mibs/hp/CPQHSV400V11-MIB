CPQHSV400V11-MIB DEFINITIONS ::= BEGIN

-- This MIB built using parse file: hsv400v11defaultparsefile.txt 130320

-- ****************************************************************************
--
--         StorageWorks cpqHSV Management Information Base (MIB)
--         Management Information Base for SNMP Network Management
--
--
--      Copyright 1999, Compaq Computer Corporation.
--      Copyright 2002, Hewlett-Packard Company.
--      All Rights Reserved.
--
--      The information in this document is subject to change without notice.
--
--      COMPAQ COMPUTER CORPORATION SHALL NOT BE LIABLE FOR TECHNICAL
--      OR EDITORIAL ERRORS OR OMISSIONS CONTAINED HEREIN; NOR FOR INCIDENTAL
--      OR CONSEQUENTIAL DAMAGES RESULTING FROM THE FURNISHING, PERFORMANCE,
--      OR USE OF THIS MATERIAL.
--
--      The HP StorageWorks maHSV1x0 MIB provides HSV Controller information,
--      and HSV Management Agent information.
--
--      The Compaq Enterprise number is 232.
--      The ASN.1 prefix to, and including the Compaq Enterprise is:
--           1.3.6.1.4.1.232
--      iso(1) org(3) dod(6) internet(1) private(4) enterprises(1) compaq(232)
-- ****************************************************************************



	 IMPORTS
		 enterprises             FROM RFC1155-SMI
		 OBJECT-TYPE		 FROM RFC-1212
		 DisplayString           FROM RFC1213-MIB
                 TRAP-TYPE           FROM RFC-1215;

	compaq             OBJECT IDENTIFIER ::= { enterprises 232 } 
	cpqElementManager  OBJECT IDENTIFIER ::= { compaq 136 }
    cpqHSV             OBJECT IDENTIFIER ::= { cpqElementManager 1 }

--  CPQELEMMNGR MIB
	cpqHSVAgent        OBJECT IDENTIFIER ::= { cpqHSV 1 }
	cpqHSVServer       OBJECT IDENTIFIER ::= { cpqHSV 2 }
	hsvObject          OBJECT IDENTIFIER ::= { cpqHSV 3 }  
    maHSVMibRev        OBJECT IDENTIFIER ::= { cpqHSV 4 }


-- HSV SAN OBJECTS 
	scell		 OBJECT IDENTIFIER ::= { hsvObject 1 }
	agent		 OBJECT IDENTIFIER ::= { hsvObject 2 }
	host		 OBJECT IDENTIFIER ::= { hsvObject 3 }
	nsc		     OBJECT IDENTIFIER ::= { hsvObject 4 }
	shelf        OBJECT IDENTIFIER ::= { hsvObject 8 }

-- ********************************************************************	
--      Agent Information Group          1.3.6.1.4.1.232.136.1.1

--                                       1.3.6.1.4.1.232.136.1.1.1
	agManufacturer OBJECT-TYPE
	     SYNTAX  DisplayString
	     ACCESS  read-only
	     STATUS  mandatory
	     DESCRIPTION
		     "The name of the StorageWorks HSV Agent manufacturer."
	     ::= { cpqHSVAgent 1 }

--                                       1.3.6.1.4.1.232.136.1.1.2	
	agMajVersion OBJECT-TYPE
	     SYNTAX  INTEGER
	     ACCESS  read-only
	     STATUS  mandatory
	     DESCRIPTION
		     "StorageWorks HSV Agent Major Version Number (e.g., 3 
		     for 3.0)."	      
	     ::= { cpqHSVAgent 2 }

--                                       1.3.6.1.4.1.232.136.1.1.3
	agMinVersion OBJECT-TYPE
	     SYNTAX  INTEGER
	     ACCESS  read-only
	     STATUS  mandatory
	     DESCRIPTION
		     "StorageWorks HSV Agent Minor Version Number (e.g., 0 
		     for 3.0)."		      
	     ::= { cpqHSVAgent 3 }

--                                       1.3.6.1.4.1.232.136.1.1.4
	agHostName OBJECT-TYPE
	     SYNTAX  DisplayString
	     ACCESS  read-only
	     STATUS  mandatory
	     DESCRIPTION
		     "The Host System Network Name where the agent resides."		      
	     ::= { cpqHSVAgent 4 }

--                                       1.3.6.1.4.1.232.136.1.1.5
	agEnterprise OBJECT-TYPE
	     SYNTAX  OBJECT IDENTIFIER
	     ACCESS  read-only
	     STATUS  mandatory
	     DESCRIPTION
		     "The Enterprise ID subtree for StorageWorks HSV Agent MIB 
		      is registered."
		      
	     ::= { cpqHSVAgent 5 }

--                                       1.3.6.1.4.1.232.136.1.1.6
	agDescription OBJECT-TYPE
	     SYNTAX  DisplayString
	     ACCESS  read-only
	     STATUS  mandatory
	     DESCRIPTION
		     "The StorageWorks HSV Agent description."
		      
	     ::= { cpqHSVAgent 6 }

--                                       1.3.6.1.4.1.232.136.1.1.7
	agStatusTable OBJECT-TYPE                                  
	     SYNTAX  SEQUENCE OF AgentEntry
	     ACCESS  not-accessible
	     STATUS  mandatory
	     DESCRIPTION
		     "This table holds the status information for
		      each HSV Management Agent."
		      
	     ::= { cpqHSVAgent 7 }

--                                       1.3.6.1.4.1.232.136.1.1.7.1
	agentEntry OBJECT-TYPE
	     SYNTAX  AgentEntry
	     ACCESS  not-accessible
	     STATUS  mandatory
	     DESCRIPTION
	     "The Agent information entry."
	     INDEX   { agentEntryIndex }
		      
	     ::= { agStatusTable 1 }

	AgentEntry ::=                                              
	  SEQUENCE{
		agentEntryIndex
			INTEGER,
		agentStatus         
			INTEGER,
		agentEventCode
			INTEGER,
		agentEventLevel
			INTEGER,
        agentEventTimeDate
            DisplayString,
		agentEventDescription
			DisplayString
	  }

--                                       1.3.6.1.4.1.232.136.1.1.7.1.1
	agentEntryIndex OBJECT-TYPE
	     SYNTAX  INTEGER
	     ACCESS  read-only
	     STATUS  mandatory
	     DESCRIPTION
		     "The index into agentStatusTable ."
	     ::= { agentEntry 1 }

--                                       1.3.6.1.4.1.232.136.1.1.7.1.2
	agentStatus OBJECT-TYPE
             SYNTAX  INTEGER  {
                          other(1),
                          ok(2),
                          degraded(3),
                          failed(4)
                      }
 	     ACCESS  read-only
	     STATUS  mandatory
	     DESCRIPTION
		      "This variable reports the overall status of the
		       Agent. 
		       INFORMATIONAL: Normal Operating Condition
		       MINOR: Warning Condition
		       MAJOR: Failure or Failure Immanent
                   CRITICAL: Agent condition is critical or unknown"
	     ::= { agentEntry 2 }

--                                       1.3.6.1.4.1.232.136.1.1.7.1.3
	agentEventCode OBJECT-TYPE
	     SYNTAX  INTEGER
	     ACCESS  read-only
	     STATUS  mandatory
	     DESCRIPTION
		     "The management agent event code."
	     ::= { agentEntry 3 }

--                                       1.3.6.1.4.1.232.136.1.1.7.1.4
	agentEventLevel OBJECT-TYPE
	     SYNTAX  INTEGER
	     ACCESS  read-only
	     STATUS  mandatory
	     DESCRIPTION
		     "The management event level."
	     ::= { agentEntry 4 }

--                                       1.3.6.1.4.1.232.136.1.1.7.1.5
      agentEventTimeDate OBJECT-TYPE
	     SYNTAX  DisplayString
	     ACCESS  read-only
	     STATUS  mandatory
	     DESCRIPTION
		     "The date and time the event occurred dd-mm-yyyy/hr:min:sec." 
	     ::= { agentEntry 5 }
--                                       1.3.6.1.4.1.232.136.1.1.7.1.6
	agentEventDescription OBJECT-TYPE
	     SYNTAX  DisplayString
	     ACCESS  read-only
	     STATUS  mandatory
	     DESCRIPTION
		     "The Description of the management agent event." 
	     ::= { agentEntry 6 }


-- Workstation Group *****************************************************

	srvCPU OBJECT-TYPE
	     SYNTAX  DisplayString
	     ACCESS  read-only
	     STATUS  mandatory
	     DESCRIPTION
		     "The server CPU type (e.g., 80486)."
		      
	     ::= { cpqHSVServer 1 }

	srvComputerType OBJECT-TYPE
	     SYNTAX  DisplayString
	     ACCESS  read-only
	     STATUS  mandatory
	     DESCRIPTION
		     "The server Computer type (e.g., PC/AT)."
		      
	     ::= { cpqHSVServer 2 }

	srvModel OBJECT-TYPE
	     SYNTAX  INTEGER
	     ACCESS  read-only
	     STATUS  mandatory
	     DESCRIPTION
		     "The server model number."
		      
	     ::= { cpqHSVServer 3 }

	srvSubModel OBJECT-TYPE
	     SYNTAX  INTEGER
	     ACCESS  read-only
	     STATUS  mandatory
	     DESCRIPTION
		     "The server submodel number."
		      
	     ::= { cpqHSVServer 4 }

	srvBiosVersion OBJECT-TYPE
	     SYNTAX  DisplayString
	     ACCESS  read-only
	     STATUS  mandatory
	     DESCRIPTION
		     "The server BIOS Version."
		      
	     ::= { cpqHSVServer 5 }

	srvOS OBJECT-TYPE
	     SYNTAX  DisplayString
	     ACCESS  read-only
	     STATUS  mandatory
	     DESCRIPTION
		     "The server operating system name (e.g., WINNT)."
		      
	     ::= { cpqHSVServer 6 }

	srvOSMajVersion OBJECT-TYPE
	     SYNTAX  INTEGER
	     ACCESS  read-only
	     STATUS  mandatory
	     DESCRIPTION
		     "The server OS major version number 
		     (e.g., 3 for WINNT 3.51)."
		      
	     ::= { cpqHSVServer 7 }

	srvOSMinVersion OBJECT-TYPE
	     SYNTAX  INTEGER
	     ACCESS  read-only
	     STATUS  mandatory
	     DESCRIPTION
		     "The server OS minor version number (e.g., 51 for
		     WINNT 3.51)."
		      
	     ::= { cpqHSVServer 8 }

-- maHSVMibRev Group       1.3.6.1.4.1.232.136.1.4

--                         1.3.6.1.4.1.232.136.1.4.1
      maHSVMibRevMajor OBJECT-TYPE
           SYNTAX  INTEGER
           ACCESS  read-only
           STATUS  mandatory
           DESCRIPTION
            "The Major Revision level.
             A change in the major revision level represents a major change
             in the architecture of the MIB.  A change in the major revision
             level may indicate a significant change in the information
             supported and/or the meaning of the supported information,
             correct interpretation of data may require a MIB document with
             the same major revision level."

           ::= { maHSVMibRev 1 }

--                         1.3.6.1.4.1.232.136.1.4.2
     maHSVMibRevMinor OBJECT-TYPE	
           SYNTAX  INTEGER
           ACCESS  read-only
           STATUS  mandatory
           DESCRIPTION
            "The Minor Revision level.
             A change in the minor revision level may represent some minor
             additional support, no changes to any pre-existing information
             has occurred."

           ::= { maHSVMibRev 2 }

-- Object Groups          1.3.6.1.4.1.232.136.1.3

-- *********************************************************************
-- StorageCell  Group         1.3.6.1.4.1.232.136.1.3.1  = scell

--                                  1.3.6.1.4.1.232.136.1.3.1.1
	scellTotal OBJECT-TYPE
	     SYNTAX  INTEGER 
	     ACCESS  read-only
	     STATUS  mandatory
	     DESCRIPTION
		     "The total number of StorageCells (storage pools) present 
                  in the Fusion System."	      
	     ::= { scell 1 }

--                                  1.3.6.1.4.1.232.136.1.3.1.2
	scellStatusTable OBJECT-TYPE                                  
	     SYNTAX  SEQUENCE OF ScellEntry
	     ACCESS  not-accessible
	     STATUS  mandatory
	     DESCRIPTION
		     "This table holds the status information for
		      each StorageCell."   
	     ::= { scell 2 }

--                                 1.3.6.1.4.1.232.136.1.3.1.2.1
	scellEntry OBJECT-TYPE
	     SYNTAX  ScellEntry
	     ACCESS  not-accessible
	     STATUS  mandatory
	     DESCRIPTION
	     "The StorageCell information entry."
	     INDEX   { scellEntryIndex }
	     ::= { scellStatusTable 1 }


	ScellEntry ::=                                              
	  SEQUENCE{
		scellEntryIndex
			INTEGER,
		scellName           
			DisplayString,
		scellUUID           
			DisplayString,
		scellStatus         
			INTEGER,
            scellEventDescription
                  DisplayString,
            scellEventTimeDate
                  DisplayString,
            scellEventCode
                  DisplayString,
		scellSWComponent
                  INTEGER,
            scellECode
			INTEGER,
            scellCAC
			INTEGER,
		scellEIP
			INTEGER,
            scellNameDateTime
                  DisplayString
	  }

--		1.3.6.1.4.1.232.136.1.3.1.2.1.1
	scellEntryIndex OBJECT-TYPE
	     SYNTAX  INTEGER
	     ACCESS  read-only
	     STATUS  mandatory
	     DESCRIPTION
		     "The index into scellStatusTable ."		      
	     ::= { scellEntry 1 }

--		1.3.6.1.4.1.232.136.1.3.1.2.1.2
	scellName OBJECT-TYPE
	     SYNTAX  DisplayString
	     ACCESS  read-only
	     STATUS  mandatory
	     DESCRIPTION
		     "The StorageCell Name."
	     ::= { scellEntry 2 }

--		1.3.6.1.4.1.232.136.1.3.1.2.1.3
	scellUUID OBJECT-TYPE
	     SYNTAX  DisplayString
	     ACCESS  read-only
	     STATUS  mandatory
	     DESCRIPTION
		     "The StorageCell unique ID."		      
	     ::= { scellEntry 3 }

--		1.3.6.1.4.1.232.136.1.3.1.2.1.4
	scellStatus OBJECT-TYPE
             SYNTAX  INTEGER  {
                          informational(1),
                          minor(2),
                          major(3),
                          failed(4)
                      }
 	     ACCESS  read-only
	     STATUS  mandatory
	     DESCRIPTION
		      "This variable reports the overall status of the
		       StorageCell. 
		       INFORMATIONAL: Normal Operating Condition
		       MINOR: Warning Condition
		       MAJOR: Failure or Failure Immanent
                   CRITICAL: Condition is critical or unknown"
	     ::= { scellEntry 4 }

--		1.3.6.1.4.1.232.136.1.3.1.2.1.5
	scellEventDescription OBJECT-TYPE
	     SYNTAX  DisplayString
	     ACCESS  read-only
	     STATUS  mandatory
	     DESCRIPTION
		     "The StorageCell Event Description."		      
	     ::= { scellEntry 5 }

--		1.3.6.1.4.1.232.136.1.3.1.2.1.6
      scellEventTimeDate OBJECT-TYPE
	     SYNTAX  DisplayString
	     ACCESS  read-only
	     STATUS  mandatory
	     DESCRIPTION
		     "The StorageCell Event Time and Date."		      
	     ::= { scellEntry 6 }

--		1.3.6.1.4.1.232.136.1.3.1.2.1.7
      scellEventCode OBJECT-TYPE
	     SYNTAX  DisplayString
	     ACCESS  read-only
	     STATUS  mandatory
	     DESCRIPTION
		     "The StorageCell Event Code."		      
	     ::= { scellEntry 7 }

--		1.3.6.1.4.1.232.136.1.3.1.2.1.8
	scellSWComponent OBJECT-TYPE
	     SYNTAX  INTEGER
	     ACCESS  read-only
	     STATUS  mandatory
	     DESCRIPTION
		     "The Event Code Software Component ID."
	     ::= { scellEntry 8 }

--		1.3.6.1.4.1.232.136.1.3.1.2.1.9
	scellECode OBJECT-TYPE
	     SYNTAX  INTEGER
	     ACCESS  read-only
	     STATUS  mandatory
	     DESCRIPTION
		     "The StorageCell Event Code event number."	      
	     ::= { scellEntry 9 }

--		1.3.6.1.4.1.232.136.1.3.1.2.1.10
	scellCAC OBJECT-TYPE
	     SYNTAX  INTEGER
	     ACCESS  read-only
	     STATUS  mandatory
	     DESCRIPTION
		     "The event code Corrective Action Code."	      
	     ::= { scellEntry 10 }

--		1.3.6.1.4.1.232.136.1.3.1.2.1.11
	scellEIP OBJECT-TYPE
	     SYNTAX  INTEGER
	     ACCESS  read-only
	     STATUS  mandatory
	     DESCRIPTION
		     "The Event Code EIP Type." 
	     ::= { scellEntry 11 }

--		1.3.6.1.4.1.232.136.1.3.1.2.1.12
	scellNameDateTime OBJECT-TYPE
	     SYNTAX  DisplayString
	     ACCESS  read-only
	     STATUS  mandatory
	     DESCRIPTION
		     "The StorageCell Name: Date & Time of Event."
	     ::= { scellEntry 12 }		

-- /*****************************************************************/


-- Host Group		1.3.6.1.4.1.232.136.1.3.3

	hostTotal OBJECT-TYPE
	     SYNTAX  INTEGER 
	     ACCESS  read-only
	     STATUS  mandatory
	     DESCRIPTION
		     "The total number of hosts attached the Fusion System."
--                              1.3.6.1.4.1.232.136.1.3.3.3.1
	     ::= { host 1 }

	hostStatusTable OBJECT-TYPE                                  
	     SYNTAX  SEQUENCE OF HostEntry
	     ACCESS  not-accessible
	     STATUS  mandatory
	     DESCRIPTION
		     "This table holds the status information for
		      each Host."
--                              1.3.6.1.4.1.232.136.1.3.3.3.2		      
	     ::= { host 2 }

	hostEntry OBJECT-TYPE
	     SYNTAX  HostEntry
	     ACCESS  not-accessible
	     STATUS  mandatory
	     DESCRIPTION
	     "The Host information entry."
	     INDEX   { hostEntryIndex }
--                              1.3.6.1.4.1.232.136.1.3.3.3.2.1
	     ::= { hostStatusTable 1 }

	HostEntry ::=                                              
	  SEQUENCE{
		hostEntryIndex
			INTEGER,
		hostName           
			DisplayString,
		hostUUID           
			DisplayString,
		hostStatus         
			INTEGER
	  }



	hostEntryIndex OBJECT-TYPE
	     SYNTAX  INTEGER
	     ACCESS  read-only
	     STATUS  mandatory
	     DESCRIPTION
		     "The index into hostStatusTable ."
--                              1.3.6.1.4.1.232.136.1.3.3.3.2.1.1
	     ::= { hostEntry 1 }

	hostName OBJECT-TYPE
	     SYNTAX  DisplayString
	     ACCESS  read-only
	     STATUS  mandatory
	     DESCRIPTION
		     "The Host Name."
--                              1.3.6.1.4.1.232.136.1.3.3.3.2.1.2
	     ::= { hostEntry 2 }

	hostUUID OBJECT-TYPE
	     SYNTAX  DisplayString
	     ACCESS  read-only
	     STATUS  mandatory
	     DESCRIPTION
		     "The Host unique ID."
--                              1.3.6.1.4.1.232.136.1.3.3.3.2.1.3		      
	     ::= { hostEntry 3 }

	hostStatus OBJECT-TYPE
             SYNTAX  INTEGER  {
                          informational(0),
                          minor(1),
                          major(2),
                          critical(3)
                      }
 	     ACCESS  read-only
	     STATUS  mandatory
	     DESCRIPTION
		      "This variable reports the overall status of the Host. 
		       INFORMATIONAL: Normal Operating Condition
		       MINOR: Warning Condition
		       MAJOR: Failure or Failure Immanent
                   CRITICAL: Condition is critical or unknown"
--                              1.3.6.1.4.1.232.136.1.3.3.3.2.1.4
	     ::= { hostEntry 4 }


-- Network Storage Controller Group   1.3.6.1.4.1.232.136.1.3.3.4

	nscTotal OBJECT-TYPE
	     SYNTAX  INTEGER 
	     ACCESS  read-only
	     STATUS  mandatory
	     DESCRIPTION
		     "The total number of Network Storage Controllers present in the Fusion System."
--                              1.3.6.1.4.1.232.136.1.3.3.4.1
	     ::= { nsc 1 }

	nscStatusTable OBJECT-TYPE                                  
	     SYNTAX  SEQUENCE OF NscEntry
	     ACCESS  not-accessible
	     STATUS  mandatory
	     DESCRIPTION
		     "This table holds the status information for
		      each Network Storage Controller."
--                              1.3.6.1.4.1.232.136.1.3.3.4.2
	     ::= { nsc 2 }

	nscEntry OBJECT-TYPE
	     SYNTAX  NscEntry
	     ACCESS  not-accessible
	     STATUS  mandatory
	     DESCRIPTION
	     "The NSC information entry."
	     INDEX   { nscEntryIndex }
--                              1.3.6.1.4.1.232.136.1.3.3.4.2.1
	     ::= { nscStatusTable 1 }

	NscEntry ::=                                              
	  SEQUENCE{
		nscEntryIndex
			INTEGER,
		nscName           
			DisplayString,
		nscUUID           
			DisplayString,
		nscStatus         
			INTEGER
	  }



	nscEntryIndex OBJECT-TYPE
	     SYNTAX  INTEGER
	     ACCESS  read-only
	     STATUS  mandatory
	     DESCRIPTION
		     "The index into nscStatusTable ."
--                              1.3.6.1.4.1.232.136.1.3.3.4.2.1.1
	     ::= { nscEntry 1 }

	nscName OBJECT-TYPE
	     SYNTAX  DisplayString
	     ACCESS  read-only
	     STATUS  mandatory
	     DESCRIPTION
		     "The Network Storage Controller Name."
--                              1.3.6.1.4.1.232.136.1.3.3.4.2.1.2
	     ::= { nscEntry 2 }

	nscUUID OBJECT-TYPE
	     SYNTAX  DisplayString
	     ACCESS  read-only
	     STATUS  mandatory
	     DESCRIPTION
		     "The NSC unique ID."
--                              1.3.6.1.4.1.232.136.1.3.3.4.2.1.3
	     ::= { nscEntry 3 }

	nscStatus OBJECT-TYPE
             SYNTAX  INTEGER  {
                          informational(0),
                          minor(1),
                          major(2),
                          critical(3)
                      }
 	     ACCESS  read-only
	     STATUS  mandatory
	     DESCRIPTION
		      "This variable reports the overall status of the
		       Network Storage Controller. 
		       INFORMATIONAL: Normal Operating Condition
		       MINOR: Warning Condition
		       MAJOR: Failure or Failure Immanent
                   CRITICAL: Condition is critical or unknown"
--                              1.3.6.1.4.1.232.136.1.3.3.4.2.1.4      
	     ::= { nscEntry 4 }

-- Shelf Group                      1.3.6.1.4.1.232.136.1.3.8
--                                  1.3.6.1.4.1.232.136.1.3.8.1
	shelfTotal OBJECT-TYPE
	     SYNTAX  INTEGER 
	     ACCESS  read-only
	     STATUS  mandatory
	     DESCRIPTION
		     "The total number of disk shelves present in the HSV system."
	     ::= { shelf 1 }

--                                  1.3.6.1.4.1.232.136.1.3.8.2
	shelfStatusTable OBJECT-TYPE                                  
	     SYNTAX  SEQUENCE OF ShelfEntry
	     ACCESS  not-accessible
	     STATUS  mandatory
	     DESCRIPTION
		     "This table holds the status information for
		      each Shelf."
	     ::= { shelf 2 }

--                                  1.3.6.1.4.1.232.136.1.3.8.2.1
	shelfEntry OBJECT-TYPE
	     SYNTAX  ShelfEntry
	     ACCESS  not-accessible
	     STATUS  mandatory
	     DESCRIPTION
	     "The Shelf information entry."
	     INDEX   { shelfEntryIndex }
	     ::= { shelfStatusTable 1 }

	ShelfEntry ::=
	  SEQUENCE{
		shelfEntryIndex
			INTEGER,
		shelfStatus
			INTEGER,
		shelfId	
			INTEGER,
		shelfElementType
			INTEGER,
		shelfElementNum
			INTEGER,
		shelfErrorCode
			INTEGER
	  }

--                                  1.3.6.1.4.1.232.136.1.3.8.2.1.1
	shelfEntryIndex OBJECT-TYPE
	     SYNTAX  INTEGER
	     ACCESS  read-only
	     STATUS  mandatory
	     DESCRIPTION
		     "The index into shelfStatusTable ."		      
	     ::= { shelfEntry 1 }

--                                  1.3.6.1.4.1.232.136.1.3.8.2.1.2
	shelfStatus OBJECT-TYPE
             SYNTAX  INTEGER  {
                          other(1),
                          ok(2),
                          degraded(3),
                          failed(4)
                      }
 	     ACCESS  read-only
	     STATUS  mandatory
	     DESCRIPTION
		      "This variable reports the overall status of the
		       Shelf. 
                   OTHER: unknown or undeterminable
		       OK: Normal Operating Condition
		       DEGRADED: Warning Condition
		       FAILED: Failure"		      
	     ::= { shelfEntry 2 }

--                                  1.3.6.1.4.1.232.136.1.3.8.2.1.3
	shelfId OBJECT-TYPE
	     SYNTAX  INTEGER
	     ACCESS  read-only
	     STATUS  mandatory
	     DESCRIPTION
		     "The Shelf Id (shelf number)."		      
	     ::= { shelfEntry 3 }

--                                  1.3.6.1.4.1.232.136.1.3.8.2.1.4
	shelfElementType OBJECT-TYPE
	     SYNTAX  INTEGER
	     ACCESS  read-only
	     STATUS  mandatory
	     DESCRIPTION
		     "The Shelf Element type.
			01: Disk
			02: Power Supply
			03: Fan
			04: Temp Sensor
			06: Alarm Horn
			07: EMU
			12: LCD
			15: GBIC
			16: Language
			17: Comm Port
			18: Volt Sensor
			19: Amp Sensor
			128:Enclosure
			130:Back plane
			255:Host"
	     ::= { shelfEntry 4 }

--                                  1.3.6.1.4.1.232.136.1.3.8.2.1.5
	shelfElementNum OBJECT-TYPE
	     SYNTAX  INTEGER
	     ACCESS  read-only
	     STATUS  mandatory
	     DESCRIPTION
		     "Which particular Element of that type."
	     ::= { shelfEntry 5 }

--                                  1.3.6.1.4.1.232.136.1.3.8.2.1.6
	shelfErrorCode OBJECT-TYPE
	     SYNTAX  INTEGER
	     ACCESS  read-only
	     STATUS  mandatory
	     DESCRIPTION
		     "The Element Type's Error Code."
	     ::= { shelfEntry 6 }


-- Traps
   emuEventTrapInformative TRAP-TYPE
        ENTERPRISE compaq
        VARIABLES  { scellNameDateTime,
                     shelfId,
                     shelfElementType,
                     shelfElementNum,
                     shelfErrorCode }
        DESCRIPTION
           "An EMU Informational event has occurred
              scellNameDateTime: StorageCell name, and date/time
		  emuShelfId: disk shelf number in the cabinet
		  emuElementType: the element type
		    01: Disk      
		    02: Pwr Supply      
		    03: Fan      
		    04: Temp Sensor      
		    06: Alarm Horn      
		    07: EMU      
		    12: LCD      
		    15: Xcvr      
		    16: Lang      
		    17: Comm Port      
  		    18: Volt Sensor      
		    19: Amp Sensor      
		    128:Encl      
		    130:Back plane      
		  emuErrorCode: error number "

	       --#TYPE      "EMU Informational Event"
             --#SUMMARY   "scellNameDateTime %s : emuShelfId %d : emuElementType %d : emuElementNum %d : emuErrorCode %d"
             --#ARGUMENTS {0,1,2,3,4}
             --#SEVERITY  INFORMATIONAL
             --#TIMEINDEX 136
             --#STATE     OK

        ::= 136001

   emuEventTrapNoncritical TRAP-TYPE
        ENTERPRISE compaq
        VARIABLES  { scellNameDateTime,
                     shelfId,
                     shelfElementType,
                     shelfElementNum,
                     shelfErrorCode }
        DESCRIPTION
           "An EMU Non-critical event has occurred
              scellNameDateTime: StorageCell name, and date/time
		  emuShelfId: disk shelf number in the cabinet
		  emuElementType: the element type
		    01: Disk      
		    02: Pwr Supply      
		    03: Fan      
		    04: Temp Sensor      
		    06: Alarm Horn      
		    07: EMU      
		    12: LCD      
		    15: Xcvr      
		    16: Lang      
		    17: Comm Port      
  		    18: Volt Sensor      
		    19: Amp Sensor      
		    128:Encl      
		    130:Back plane      
		  emuErrorCode: error number "

	       --#TYPE      "EMU Non Critical Event"
             --#SUMMARY   "scellNameDateTime %s : emuShelfId %d : emuElementType %d : emuElementNum %d : emuErrorCode %d"
             --#ARGUMENTS {0,1,2,3,4}
             --#SEVERITY  MINOR
             --#TIMEINDEX 136
             --#STATE     WARNING

        ::= 136002

   emuEventTrapCritical TRAP-TYPE
        ENTERPRISE compaq
        VARIABLES  { scellNameDateTime,
                     shelfId,
                     shelfElementType,
                     shelfElementNum,
                     shelfErrorCode }
        DESCRIPTION
           "An EMU Critical event has occurred
              scellNameDateTime: StorageCell name, and date/time
		  emuShelfId: disk shelf number in the cabinet
		  emuElementType: the element type
		    01: Disk      
		    02: Pwr Supply      
		    03: Fan      
		    04: Temp Sensor      
		    06: Alarm Horn      
		    07: EMU      
		    12: LCD      
		    15: Xcvr      
		    16: Lang      
		    17: Comm Port      
  		    18: Volt Sensor      
		    19: Amp Sensor      
		    128:Encl      
		    130:Back plane      
		  emuErrorCode: error number "

	       --#TYPE      "EMU Critical Event"
             --#SUMMARY   "scellNameDateTime %s : emuShelfId %d : emuElementType %d : emuElementNum %d : emuErrorCode %d"
             --#ARGUMENTS {0,1,2,3,4}
             --#SEVERITY  CRITICAL
             --#TIMEINDEX 136
             --#STATE     CRITICAL

        ::= 136003

   emuEventTrapUnrecoverable TRAP-TYPE
        ENTERPRISE compaq
        VARIABLES  { scellNameDateTime,
                     shelfId,
                     shelfElementType,
                     shelfElementNum,
                     shelfErrorCode }
        DESCRIPTION
           "An EMU Unrecoverable event has occurred
              scellNameDateTime: StorageCell name, and date/time
		  emuShelfId: disk shelf number in the cabinet
		  emuElementType: the element type
		    01: Disk      
		    02: Pwr Supply      
		    03: Fan      
		    04: Temp Sensor      
		    06: Alarm Horn      
		    07: EMU      
		    12: LCD      
		    15: Xcvr      
		    16: Lang      
		    17: Comm Port      
  		    18: Volt Sensor      
		    19: Amp Sensor      
		    128:Encl      
		    130:Back plane      
		  emuErrorCode: error number "

	       --#TYPE      "EMU Unrecoverable Event"
             --#SUMMARY   "scellNameDateTime %s : emuShelfId %d : emuElementType %d : emuElementNum %d : emuErrorCode %d"
             --#ARGUMENTS {0,1,2,3,4}
             --#SEVERITY  CRITICAL
             --#TIMEINDEX 136
             --#STATE     FAILED

        ::= 136004
-- Following are the traps defined for StorageCell Events
-- The trap name is constructed from 2 of the 4 numbers that uniquely Identify
-- a SC Event: Software Component ID, and the Event Number.
-- These numbers are represented as hex numbers in the controller event parse file.
-- For example: sCellEventTrap-9-66  has:
--   Software Component ID: 9 (hex)
--   Event Number: 66 (hex) { = 102 base 10 }
--
--
-- The Trap number is calculated by using the complete number space
-- of the Software Component & Event numbers.  There are a possible
-- 256 s/w components, each with a possible 256 events giving an
-- address space of 65536 events.  To ensure that trap numbers do not
-- change when additional SC Events are defined the following formula
-- is used:  Base + (SWCID * 256) + Event Number
-- The large base was used to avoid collisions with the management trap
-- numbers who share the same address space of 0-65536
-- In our example above: sCellEventTrap-9-66 the trap number is -
-- Base = 13600000  (which preserves our unique OID sub-identifier of 136) +
--        ( 9 * 256 )  +   102 (66hex)   =  13602406


   sCellEventTrap-01-02 TRAP-TYPE  -- CAC Code: 00
        ENTERPRISE compaq
        VARIABLES  { scellNameDateTime,
                     scellSWComponent,
                     scellECode,
                     scellCAC,
                     scellEIP}
        DESCRIPTION
             "Severity: Normal -- informational in nature. A time change occurred."
           --#TYPE      "StorageCell Event 0102000d"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600258

   sCellEventTrap-02-00 TRAP-TYPE  -- CAC Code: 00
        ENTERPRISE compaq
        VARIABLES  { scellNameDateTime,
                     scellSWComponent,
                     scellECode,
                     scellCAC,
                     scellEIP}
        DESCRIPTION
             "Severity: Normal -- informational in nature. A prefetching XD report."
           --#TYPE      "StorageCell Event 0200002f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600512

   sCellEventTrap-03-01 TRAP-TYPE  -- CAC Code: 40
        ENTERPRISE compaq
        VARIABLES  { scellNameDateTime,
                     scellSWComponent,
                     scellECode,
                     scellCAC,
                     scellEIP}
        DESCRIPTION
             "Severity: Critical -- failure or failure imminent. A physical disk drive has been rendered inoperable."
           --#TYPE      "StorageCell Event 0301400b"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13600769

   sCellEventTrap-03-02 TRAP-TYPE  -- CAC Code: 4f
        ENTERPRISE compaq
        VARIABLES  { scellNameDateTime,
                     scellSWComponent,
                     scellECode,
                     scellCAC,
                     scellEIP}
        DESCRIPTION
             "Severity: Warning -- not failed but attention recommended or required. A physical disk drive will not be used because the maximum number of physical disk drives already exist in the current Storage System."
           --#TYPE      "StorageCell Event 03024f0b"
           --#SUMMARY   "SCellName-TimeDate %s : SWCID %d : ECode: %d : CAC %d : EIP %d."
           --#ARGUMENTS {0,1,2,3,4,}
           --#SEVERITY  MINOR
           --#TIMEINDEX 136
           --#STATE     WARNING
        ::= 13600770

   sCellEventTrap-03-03 TRAP-TYPE  -- CAC Code: 00
        ENTERPRISE compaq
        VARIABLES  { scellNameDateTime,
                     scellSWComponent,
                     scellECode,
                     scellCAC,
                     scellEIP}
        DESCRIPTION
             "Severity: Normal -- informational in nature. A controller has begun booting."
           --#TYPE      "StorageCell Event 0303000a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600771

   sCellEventTrap-03-04 TRAP-TYPE  -- CAC Code: 00
        ENTERPRISE compaq
        VARIABLES  { scellNameDateTime,
                     scellSWComponent,
                     scellECode,
                     scellCAC,
                     scellEIP}
        DESCRIPTION
             "Severity: Normal -- informational in nature. A controller has finished the process of bringing the Storage System online."
           --#TYPE      "StorageCell Event 0304000a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600772

   sCellEventTrap-03-05 TRAP-TYPE  -- CAC Code: 00
        ENTERPRISE compaq
        VARIABLES  { scellNameDateTime,
                     scellSWComponent,
                     scellECode,
                     scellCAC,
                     scellEIP}
        DESCRIPTION
             "Severity: Normal -- informational in nature. A controller has been joined into the Storage System."
           --#TYPE      "StorageCell Event 0305000a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600773

   sCellEventTrap-03-06 TRAP-TYPE  -- CAC Code: 00
        ENTERPRISE compaq
        VARIABLES  { scellNameDateTime,
                     scellSWComponent,
                     scellECode,
                     scellCAC,
                     scellEIP}
        DESCRIPTION
             "Severity: Normal -- informational in nature. A controller has been ousted from the Storage System."
           --#TYPE      "StorageCell Event 0306000a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600774

   sCellEventTrap-03-07 TRAP-TYPE  -- CAC Code: 00
        ENTERPRISE compaq
        VARIABLES  { scellNameDateTime,
                     scellSWComponent,
                     scellECode,
                     scellCAC,
                     scellEIP}
        DESCRIPTION
             "Severity: Normal -- informational in nature. A controller is now the Storage System Master."
           --#TYPE      "StorageCell Event 0307000a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600775

   sCellEventTrap-03-08 TRAP-TYPE  -- CAC Code: 00
        ENTERPRISE compaq
        VARIABLES  { scellNameDateTime,
                     scellSWComponent,
                     scellECode,
                     scellCAC,
                     scellEIP}
        DESCRIPTION
             "Severity: Normal -- informational in nature. A controller has been brought into the Storage System."
           --#TYPE      "StorageCell Event 0308000a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600776

   sCellEventTrap-03-09 TRAP-TYPE  -- CAC Code: 00
        ENTERPRISE compaq
        VARIABLES  { scellNameDateTime,
                     scellSWComponent,
                     scellECode,
                     scellCAC,
                     scellEIP}
        DESCRIPTION
             "Severity: Normal -- informational in nature. The Redundant Storage Set has started migrating members."
           --#TYPE      "StorageCell Event 03090018"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600777

   sCellEventTrap-03-0a TRAP-TYPE  -- CAC Code: 00
        ENTERPRISE compaq
        VARIABLES  { scellNameDateTime,
                     scellSWComponent,
                     scellECode,
                     scellCAC,
                     scellEIP}
        DESCRIPTION
             "Severity: Normal -- informational in nature. The Redundant Storage Set has finished migrating members."
           --#TYPE      "StorageCell Event 030a0018"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600778

   sCellEventTrap-03-0b TRAP-TYPE  -- CAC Code: 4f
        ENTERPRISE compaq
        VARIABLES  { scellNameDateTime,
                     scellSWComponent,
                     scellECode,
                     scellCAC,
                     scellEIP}
        DESCRIPTION
             "Severity: Warning -- not failed but attention recommended or required. A physical disk drive has failed during Storage System realization."
           --#TYPE      "StorageCell Event 030b4f0b"
           --#SUMMARY   "SCellName-TimeDate %s : SWCID %d : ECode: %d : CAC %d : EIP %d."
           --#ARGUMENTS {0,1,2,3,4,}
           --#SEVERITY  MINOR
           --#TIMEINDEX 136
           --#STATE     WARNING
        ::= 13600779

   sCellEventTrap-03-0c TRAP-TYPE  -- CAC Code: 00
        ENTERPRISE compaq
        VARIABLES  { scellNameDateTime,
                     scellSWComponent,
                     scellECode,
                     scellCAC,
                     scellEIP}
        DESCRIPTION
             "Severity: Normal -- informational in nature. The DebugFlags and/or PrintFlags have changed."
           --#TYPE      "StorageCell Event 030c001e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600780

   sCellEventTrap-03-0d TRAP-TYPE  -- CAC Code: 00
        ENTERPRISE compaq
        VARIABLES  { scellNameDateTime,
                     scellSWComponent,
                     scellECode,
                     scellCAC,
                     scellEIP}
        DESCRIPTION
             "Severity: Normal -- informational in nature. Process with work during CSM reset:"
           --#TYPE      "StorageCell Event 030d001e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600781

   sCellEventTrap-03-0e TRAP-TYPE  -- CAC Code: 07
        ENTERPRISE compaq
        VARIABLES  { scellNameDateTime,
                     scellSWComponent,
                     scellECode,
                     scellCAC,
                     scellEIP}
        DESCRIPTION
             "Severity: Warning -- not failed but attention recommended or required. About to write ID block to wrong physical disk drive."
           --#TYPE      "StorageCell Event 030e070b"
           --#SUMMARY   "SCellName-TimeDate %s : SWCID %d : ECode: %d : CAC %d : EIP %d."
           --#ARGUMENTS {0,1,2,3,4,}
           --#SEVERITY  MINOR
           --#TIMEINDEX 136
           --#STATE     WARNING
        ::= 13600782

   sCellEventTrap-03-0f TRAP-TYPE  -- CAC Code: 00
        ENTERPRISE compaq
        VARIABLES  { scellNameDateTime,
                     scellSWComponent,
                     scellECode,
                     scellCAC,
                     scellEIP}
        DESCRIPTION
             "Severity: Normal -- informational in nature. RoHS Status of the controller has been determined."
           --#TYPE      "StorageCell Event 030f001e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600783

   sCellEventTrap-03-10 TRAP-TYPE  -- CAC Code: 00
        ENTERPRISE compaq
        VARIABLES  { scellNameDateTime,
                     scellSWComponent,
                     scellECode,
                     scellCAC,
                     scellEIP}
        DESCRIPTION
             "Severity: Normal -- informational in nature. A Storage System Virtual Disk has changed controller mastership."
           --#TYPE      "StorageCell Event 0310001f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600784

   sCellEventTrap-03-12 TRAP-TYPE  -- CAC Code: 00
        ENTERPRISE compaq
        VARIABLES  { scellNameDateTime,
                     scellSWComponent,
                     scellECode,
                     scellCAC,
                     scellEIP}
        DESCRIPTION
             "Severity: Normal -- informational in nature. A Storage System Virtual Disk Attach operation has completed."
           --#TYPE      "StorageCell Event 03120021"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600786

   sCellEventTrap-03-13 TRAP-TYPE  -- CAC Code: 00
        ENTERPRISE compaq
        VARIABLES  { scellNameDateTime,
                     scellSWComponent,
                     scellECode,
                     scellCAC,
                     scellEIP}
        DESCRIPTION
             "Severity: Normal -- informational in nature. A Snapclone Storage System Virtual Disk has completed the Unsharing operation."
           --#TYPE      "StorageCell Event 03130021"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600787

   sCellEventTrap-03-14 TRAP-TYPE  -- CAC Code: 00
        ENTERPRISE compaq
        VARIABLES  { scellNameDateTime,
                     scellSWComponent,
                     scellECode,
                     scellCAC,
                     scellEIP}
        DESCRIPTION
             "Severity: Normal -- informational in nature. A Mirror Clone Storage System Virtual Disk has completed the detach operation."
           --#TYPE      "StorageCell Event 03140021"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600788

   sCellEventTrap-03-15 TRAP-TYPE  -- CAC Code: 00
        ENTERPRISE compaq
        VARIABLES  { scellNameDateTime,
                     scellSWComponent,
                     scellECode,
                     scellCAC,
                     scellEIP}
        DESCRIPTION
             "Severity: Normal -- informational in nature. A Mirror Clone Storage System Virtual Disk has completed the Fracture operation."
           --#TYPE      "StorageCell Event 03150021"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600789

   sCellEventTrap-03-16 TRAP-TYPE  -- CAC Code: 00
        ENTERPRISE compaq
        VARIABLES  { scellNameDateTime,
                     scellSWComponent,
                     scellECode,
                     scellCAC,
                     scellEIP}
        DESCRIPTION
             "Severity: Normal -- informational in nature. A Mirror Clone Storage System Virtual Disk has completed the Synchronization operation."
           --#TYPE      "StorageCell Event 03160021"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600790

   sCellEventTrap-03-17 TRAP-TYPE  -- CAC Code: 00
        ENTERPRISE compaq
        VARIABLES  { scellNameDateTime,
                     scellSWComponent,
                     scellECode,
                     scellCAC,
                     scellEIP}
        DESCRIPTION
             "Severity: Normal -- informational in nature. A Storage System Virtual Disk has completed the Instant Restore operation."
           --#TYPE      "StorageCell Event 03170021"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600791

   sCellEventTrap-03-1b TRAP-TYPE  -- CAC Code: 0d
        ENTERPRISE compaq
        VARIABLES  { scellNameDateTime,
                     scellSWComponent,
                     scellECode,
                     scellCAC,
                     scellEIP}
        DESCRIPTION
             "Severity: Critical -- failure or failure imminent. The system is inoperative."
           --#TYPE      "StorageCell Event 031b0d23"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13600795

   sCellEventTrap-03-1c TRAP-TYPE  -- CAC Code: 4a
        ENTERPRISE compaq
        VARIABLES  { scellNameDateTime,
                     scellSWComponent,
                     scellECode,
                     scellCAC,
                     scellEIP}
        DESCRIPTION
             "Severity: Warning -- not failed but attention recommended or required. One or more ports has been disabled at startup."
           --#TYPE      "StorageCell Event 031c4a23"
           --#SUMMARY   "SCellName-TimeDate %s : SWCID %d : ECode: %d : CAC %d : EIP %d."
           --#ARGUMENTS {0,1,2,3,4,}
           --#SEVERITY  MINOR
           --#TIMEINDEX 136
           --#STATE     WARNING
        ::= 13600796

   sCellEventTrap-03-1d TRAP-TYPE  -- CAC Code: 99
        ENTERPRISE compaq
        VARIABLES  { scellNameDateTime,
                     scellSWComponent,
                     scellECode,
                     scellCAC,
                     scellEIP}
        DESCRIPTION
             "Severity: Critical -- failure or failure imminent. One or more ports have been misconfigured."
           --#TYPE      "StorageCell Event 031d9923"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13600797

   sCellEventTrap-03-1e TRAP-TYPE  -- CAC Code: 0d
        ENTERPRISE compaq
        VARIABLES  { scellNameDateTime,
                     scellSWComponent,
                     scellECode,
                     scellCAC,
                     scellEIP}
        DESCRIPTION
             "Severity: Critical -- failure or failure imminent. The user is required to provide a confirmation as to how the system should proceed."
           --#TYPE      "StorageCell Event 031e0d23"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13600798

   sCellEventTrap-03-1f TRAP-TYPE  -- CAC Code: 99
        ENTERPRISE compaq
        VARIABLES  { scellNameDateTime,
                     scellSWComponent,
                     scellECode,
                     scellCAC,
                     scellEIP}
        DESCRIPTION
             "Severity: Critical -- failure or failure imminent. A backend device has been misconfigured.  The current port states for both the master and the slave should match."
           --#TYPE      "StorageCell Event 031f9923"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13600799

   sCellEventTrap-03-20 TRAP-TYPE  -- CAC Code: 00
        ENTERPRISE compaq
        VARIABLES  { scellNameDateTime,
                     scellSWComponent,
                     scellECode,
                     scellCAC,
                     scellEIP}
        DESCRIPTION
             "Severity: Normal -- informational in nature. The slave controller is prevented from joining because"
           --#TYPE      "StorageCell Event 0320000a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600800

   sCellEventTrap-03-21 TRAP-TYPE  -- CAC Code: f1
        ENTERPRISE compaq
        VARIABLES  { scellNameDateTime,
                     scellSWComponent,
                     scellECode,
                     scellCAC,
                     scellEIP}
        DESCRIPTION
             "Severity: Warning -- not failed but attention recommended or required. An enclosure will not be used because the maximum number of enclosures already exist in the current Storage System."
           --#TYPE      "StorageCell Event 0321f113"
           --#SUMMARY   "SCellName-TimeDate %s : SWCID %d : ECode: %d : CAC %d : EIP %d."
           --#ARGUMENTS {0,1,2,3,4,}
           --#SEVERITY  MINOR
           --#TIMEINDEX 136
           --#STATE     WARNING
        ::= 13600801

   sCellEventTrap-03-22 TRAP-TYPE  -- CAC Code: 00
        ENTERPRISE compaq
        VARIABLES  { scellNameDateTime,
                     scellSWComponent,
                     scellECode,
                     scellCAC,
                     scellEIP}
        DESCRIPTION
             "Severity: Normal -- informational in nature. The CA Port Routing value has been changed."
           --#TYPE      "StorageCell Event 0322000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600802

   sCellEventTrap-03-23 TRAP-TYPE  -- CAC Code: 00
        ENTERPRISE compaq
        VARIABLES  { scellNameDateTime,
                     scellSWComponent,
                     scellECode,
                     scellCAC,
                     scellEIP}
        DESCRIPTION
             "Severity: Normal -- informational in nature. A controller has successfully completed a preserving resync after a code load operation."
           --#TYPE      "StorageCell Event 0323000a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600803

   sCellEventTrap-03-24 TRAP-TYPE  -- CAC Code: 40
        ENTERPRISE compaq
        VARIABLES  { scellNameDateTime,
                     scellSWComponent,
                     scellECode,
                     scellCAC,
                     scellEIP}
        DESCRIPTION
             "Severity: Critical -- failure or failure imminent. A physical disk drive could not be added to a SCELL. The device storage capacity exceeds the maximum supported size."
           --#TYPE      "StorageCell Event 0324400b"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13600804

   sCellEventTrap-03-25 TRAP-TYPE  -- CAC Code: 00
        ENTERPRISE compaq
        VARIABLES  { scellNameDateTime,
                     scellSWComponent,
                     scellECode,
                     scellCAC,
                     scellEIP}
        DESCRIPTION
             "Severity: Normal -- informational in nature. Drive reappeared with Metadata (ID buffer) Scell tag matching with deleted scell, erasing ID BLOCK."
           --#TYPE      "StorageCell Event 0325000a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600805

   sCellEventTrap-03-26 TRAP-TYPE  -- CAC Code: 00
        ENTERPRISE compaq
        VARIABLES  { scellNameDateTime,
                     scellSWComponent,
                     scellECode,
                     scellCAC,
                     scellEIP}
        DESCRIPTION
             "Severity: Normal -- informational in nature. A controller has changed Battery Cache policy"
           --#TYPE      "StorageCell Event 03260027"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600806

   sCellEventTrap-03-27 TRAP-TYPE  -- CAC Code: 01
        ENTERPRISE compaq
        VARIABLES  { scellNameDateTime,
                     scellSWComponent,
                     scellECode,
                     scellCAC,
                     scellEIP}
        DESCRIPTION
             "Severity: Critical -- failure or failure imminent. A physical disk drive has experienced an ID block inconsistency."
           --#TYPE      "StorageCell Event 03270129"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13600807

   sCellEventTrap-03-28 TRAP-TYPE  -- CAC Code: 00
        ENTERPRISE compaq
        VARIABLES  { scellNameDateTime,
                     scellSWComponent,
                     scellECode,
                     scellCAC,
                     scellEIP}
        DESCRIPTION
             "Severity: Normal -- informational in nature. A physical disk drive has experienced an ID block inconsistency during a periodic drive check."
           --#TYPE      "StorageCell Event 03280029"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600808

   sCellEventTrap-03-29 TRAP-TYPE  -- CAC Code: 00
        ENTERPRISE compaq
        VARIABLES  { scellNameDateTime,
                     scellSWComponent,
                     scellECode,
                     scellCAC,
                     scellEIP}
        DESCRIPTION
             "Severity: Normal -- informational in nature. An update to the CVM data base was successfully recovered."
           --#TYPE      "StorageCell Event 0329002a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600809

   sCellEventTrap-03-2a TRAP-TYPE  -- CAC Code: 00
        ENTERPRISE compaq
        VARIABLES  { scellNameDateTime,
                     scellSWComponent,
                     scellECode,
                     scellCAC,
                     scellEIP}
        DESCRIPTION
             "Severity: Normal -- informational in nature. The Redundant Storage Set failed to start migrating members due to insufficient capacity."
           --#TYPE      "StorageCell Event 032a0018"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600810

   sCellEventTrap-03-2b TRAP-TYPE  -- CAC Code: d4
        ENTERPRISE compaq
        VARIABLES  { scellNameDateTime,
                     scellSWComponent,
                     scellECode,
                     scellCAC,
                     scellEIP}
        DESCRIPTION
             "Severity: Critical -- failure or failure imminent. This controller was added and has either different cache and policy memory sizes, a different backend transport technology (SAS vs FC) or has a different NSC controller model (product id); The master will continue to operate, this controller is inoperative. A product id of zero indicates this controller is down revision. A cache memory size of ffffffff indicates incompatible controller models."
           --#TYPE      "StorageCell Event 032bd42c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13600811

   sCellEventTrap-03-2c TRAP-TYPE  -- CAC Code: d4
        ENTERPRISE compaq
        VARIABLES  { scellNameDateTime,
                     scellSWComponent,
                     scellECode,
                     scellCAC,
                     scellEIP}
        DESCRIPTION
             "Severity: Critical -- failure or failure imminent. The other controller has either different cache and policy memory sizes, a different backend transport technology (SAS vs FC) or has a different NSC controller model (product id); This controller, the master will continue to operate.  The other controller is going inoperative. A product id of zero indicates the controller is down revision. A cache memory size of ffffffff indicates incompatible controller models."
           --#TYPE      "StorageCell Event 032cd42c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13600812

   sCellEventTrap-03-2d TRAP-TYPE  -- CAC Code: 00
        ENTERPRISE compaq
        VARIABLES  { scellNameDateTime,
                     scellSWComponent,
                     scellECode,
                     scellCAC,
                     scellEIP}
        DESCRIPTION
             "Severity: Normal -- informational in nature. System synchronization phase entered after discovery/configuration complete."
           --#TYPE      "StorageCell Event 032d002b"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600813

   sCellEventTrap-03-2e TRAP-TYPE  -- CAC Code: 00
        ENTERPRISE compaq
        VARIABLES  { scellNameDateTime,
                     scellSWComponent,
                     scellECode,
                     scellCAC,
                     scellEIP}
        DESCRIPTION
             "Severity: Normal -- informational in nature. System synchronization phase exited."
           --#TYPE      "StorageCell Event 032e002b"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600814

   sCellEventTrap-03-2f TRAP-TYPE  -- CAC Code: 00
        ENTERPRISE compaq
        VARIABLES  { scellNameDateTime,
                     scellSWComponent,
                     scellECode,
                     scellCAC,
                     scellEIP}
        DESCRIPTION
             "Severity: Normal -- informational in nature. A controller has failed to join the Scell."
           --#TYPE      "StorageCell Event 032f000a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600815

   sCellEventTrap-03-30 TRAP-TYPE  -- CAC Code: 00
        ENTERPRISE compaq
        VARIABLES  { scellNameDateTime,
                     scellSWComponent,
                     scellECode,
                     scellCAC,
                     scellEIP}
        DESCRIPTION
             "Severity: Normal -- informational in nature. A request to scrub the Storage System has been received."
           --#TYPE      "StorageCell Event 0330000a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600816

   sCellEventTrap-03-31 TRAP-TYPE  -- CAC Code: 00
        ENTERPRISE compaq
        VARIABLES  { scellNameDateTime,
                     scellSWComponent,
                     scellECode,
                     scellCAC,
                     scellEIP}
        DESCRIPTION
             "Severity: Normal -- informational in nature. The Storage System has been scrubbed."
           --#TYPE      "StorageCell Event 0331000a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600817

   sCellEventTrap-03-32 TRAP-TYPE  -- CAC Code: 00
        ENTERPRISE compaq
        VARIABLES  { scellNameDateTime,
                     scellSWComponent,
                     scellECode,
                     scellCAC,
                     scellEIP}
        DESCRIPTION
             "Severity: Normal -- informational in nature. An invalid request to scrub the Storage System has been ignored."
           --#TYPE      "StorageCell Event 0332000a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600818

   sCellEventTrap-03-33 TRAP-TYPE  -- CAC Code: 00
        ENTERPRISE compaq
        VARIABLES  { scellNameDateTime,
                     scellSWComponent,
                     scellECode,
                     scellCAC,
                     scellEIP}
        DESCRIPTION
             "Severity: Normal -- informational in nature. The Slave controller's Boot Check Timer has been reinitialized to time out in 1 hour to accomodate units that are failing over."
           --#TYPE      "StorageCell Event 0333000a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600819

   sCellEventTrap-03-34 TRAP-TYPE  -- CAC Code: 00
        ENTERPRISE compaq
        VARIABLES  { scellNameDateTime,
                     scellSWComponent,
                     scellECode,
                     scellCAC,
                     scellEIP}
        DESCRIPTION
             "Severity: Normal -- informational in nature. An Redundant Storage Set has more than two abnormal drives, but will not become RAID 6 Inoperative because all members are either NORMAL or REVERTING or UNGROUPING."
           --#TYPE      "StorageCell Event 03340018"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600820

   sCellEventTrap-03-35 TRAP-TYPE  -- CAC Code: 00
        ENTERPRISE compaq
        VARIABLES  { scellNameDateTime,
                     scellSWComponent,
                     scellECode,
                     scellCAC,
                     scellEIP}
        DESCRIPTION
             "Severity: Normal -- informational in nature. A physical disk drive no longer identifies itself as a supported drive, yet is currently part of the active Storage System"
           --#TYPE      "StorageCell Event 0335000b"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600821

   sCellEventTrap-03-40 TRAP-TYPE  -- CAC Code: 00
        ENTERPRISE compaq
        VARIABLES  { scellNameDateTime,
                     scellSWComponent,
                     scellECode,
                     scellCAC,
                     scellEIP}
        DESCRIPTION
             "Severity: Normal -- informational in nature. A Storage System Virtual Disk has completed the Cache Fast Failover operation."
           --#TYPE      "StorageCell Event 03400021"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600832

   sCellEventTrap-03-41 TRAP-TYPE  -- CAC Code: 00
        ENTERPRISE compaq
        VARIABLES  { scellNameDateTime,
                     scellSWComponent,
                     scellECode,
                     scellCAC,
                     scellEIP}
        DESCRIPTION
             "Severity: Normal -- informational in nature. A Storage System Virtual Disk has completed the Clear Container operation."
           --#TYPE      "StorageCell Event 03410021"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600833

   sCellEventTrap-03-42 TRAP-TYPE  -- CAC Code: 00
        ENTERPRISE compaq
        VARIABLES  { scellNameDateTime,
                     scellSWComponent,
                     scellECode,
                     scellCAC,
                     scellEIP}
        DESCRIPTION
             "Severity: Normal -- informational in nature. A Storage System Virtual Disk has removed any sharing relationships (if any existed ) during the delete process."
           --#TYPE      "StorageCell Event 03420021"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600834

   sCellEventTrap-03-43 TRAP-TYPE  -- CAC Code: 00
        ENTERPRISE compaq
        VARIABLES  { scellNameDateTime,
                     scellSWComponent,
                     scellECode,
                     scellCAC,
                     scellEIP}
        DESCRIPTION
             "Severity: Normal -- informational in nature. A Storage System Virtual Disk has completed the Set Capacity operation."
           --#TYPE      "StorageCell Event 03430021"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600835

   sCellEventTrap-03-44 TRAP-TYPE  -- CAC Code: 00
        ENTERPRISE compaq
        VARIABLES  { scellNameDateTime,
                     scellSWComponent,
                     scellECode,
                     scellCAC,
                     scellEIP}
        DESCRIPTION
             "Severity: Normal -- informational in nature. A Storage System Virtual Disk has completed the Reserve Capacity operation."
           --#TYPE      "StorageCell Event 03440021"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600836

   sCellEventTrap-03-45 TRAP-TYPE  -- CAC Code: 00
        ENTERPRISE compaq
        VARIABLES  { scellNameDateTime,
                     scellSWComponent,
                     scellECode,
                     scellCAC,
                     scellEIP}
        DESCRIPTION
             "Severity: Normal -- informational in nature. A Storage System Virtual Disk has completed the Cache Flush operation."
           --#TYPE      "StorageCell Event 03450021"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600837

   sCellEventTrap-03-46 TRAP-TYPE  -- CAC Code: 00
        ENTERPRISE compaq
        VARIABLES  { scellNameDateTime,
                     scellSWComponent,
                     scellECode,
                     scellCAC,
                     scellEIP}
        DESCRIPTION
             "Severity: Normal -- informational in nature. Storage System Virtual Disk creation has started."
           --#TYPE      "StorageCell Event 03460021"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600838

   sCellEventTrap-03-47 TRAP-TYPE  -- CAC Code: 00
        ENTERPRISE compaq
        VARIABLES  { scellNameDateTime,
                     scellSWComponent,
                     scellECode,
                     scellCAC,
                     scellEIP}
        DESCRIPTION
             "Severity: Normal -- informational in nature. A Mirror Clone Storage System Virtual Disk has completed the invert operation."
           --#TYPE      "StorageCell Event 03470021"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600839

   sCellEventTrap-03-48 TRAP-TYPE  -- CAC Code: 4f
        ENTERPRISE compaq
        VARIABLES  { scellNameDateTime,
                     scellSWComponent,
                     scellECode,
                     scellCAC,
                     scellEIP}
        DESCRIPTION
             "Severity: Warning -- not failed but attention recommended or required. A physical disk drive QUORUM disk has been detected"
           --#TYPE      "StorageCell Event 03484f0b"
           --#SUMMARY   "SCellName-TimeDate %s : SWCID %d : ECode: %d : CAC %d : EIP %d."
           --#ARGUMENTS {0,1,2,3,4,}
           --#SEVERITY  MINOR
           --#TIMEINDEX 136
           --#STATE     WARNING
        ::= 13600840

   sCellEventTrap-03-49 TRAP-TYPE  -- CAC Code: 00
        ENTERPRISE compaq
        VARIABLES  { scellNameDateTime,
                     scellSWComponent,
                     scellECode,
                     scellCAC,
                     scellEIP}
        DESCRIPTION
             "Severity: Normal -- informational in nature. A Storage System Virtual Disk VDSB report."
           --#TYPE      "StorageCell Event 0349002f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600841

   sCellEventTrap-03-4a TRAP-TYPE  -- CAC Code: 00
        ENTERPRISE compaq
        VARIABLES  { scellNameDateTime,
                     scellSWComponent,
                     scellECode,
                     scellCAC,
                     scellEIP}
        DESCRIPTION
             "Severity: Normal -- informational in nature. A Storage System Virtual Disk LDSB report."
           --#TYPE      "StorageCell Event 034a002f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600842

   sCellEventTrap-03-60 TRAP-TYPE  -- CAC Code: 00
        ENTERPRISE compaq
        VARIABLES  { scellNameDateTime,
                     scellSWComponent,
                     scellECode,
                     scellCAC,
                     scellEIP}
        DESCRIPTION
             "Severity: Normal -- informational in nature. A Logical Disk operation has completed."
           --#TYPE      "StorageCell Event 03600021"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13600864

   sCellEventTrap-03-61 TRAP-TYPE  -- CAC Code: 53
        ENTERPRISE compaq
        VARIABLES  { scellNameDateTime,
                     scellSWComponent,
                     scellECode,
                     scellCAC,
                     scellEIP}
        DESCRIPTION
             "Severity: Warning -- not failed but attention recommended or required. A controller has more scvds than it can support."
           --#TYPE      "StorageCell Event 03615323"
           --#SUMMARY   "SCellName-TimeDate %s : SWCID %d : ECode: %d : CAC %d : EIP %d."
           --#ARGUMENTS {0,1,2,3,4,}
           --#SEVERITY  MINOR
           --#TIMEINDEX 136
           --#STATE     WARNING
        ::= 13600865

   sCellEventTrap-03-62 TRAP-TYPE  -- CAC Code: 42
        ENTERPRISE compaq
        VARIABLES  { scellNameDateTime,
                     scellSWComponent,
                     scellECode,
                     scellCAC,
                     scellEIP}
        DESCRIPTION
             "Severity: Critical -- failure or failure imminent. A member of a Redundant Storage Set is in an abnormal state."
           --#TYPE      "StorageCell Event 03624218"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13600866

   sCellEventTrap-03-63 TRAP-TYPE  -- CAC Code: 07
        ENTERPRISE compaq
        VARIABLES  { scellNameDateTime,
                     scellSWComponent,
                     scellECode,
                     scellCAC,
                     scellEIP}
        DESCRIPTION
             "Severity: Warning -- not failed but attention recommended or required. A Storage System Virtual Disk has unexpected snapshot relationships still existing."
           --#TYPE      "StorageCell Event 0363071e"
           --#SUMMARY   "SCellName-TimeDate %s : SWCID %d : ECode: %d : CAC %d : EIP %d."
           --#ARGUMENTS {0,1,2,3,4,}
           --#SEVERITY  MINOR
           --#TIMEINDEX 136
           --#STATE     WARNING
        ::= 13600867

   sCellEventTrap-03-64 TRAP-TYPE  -- CAC Code: 07
        ENTERPRISE compaq
        VARIABLES  { scellNameDateTime,
                     scellSWComponent,
                     scellECode,
                     scellCAC,
                     scellEIP}
        DESCRIPTION
             "Severity: Warning -- not failed but attention recommended or required. A Storage System Virtual Disk attempted to start an operation and got an unexpected failure status."
           --#TYPE      "StorageCell Event 03640721"
           --#SUMMARY   "SCellName-TimeDate %s : SWCID %d : ECode: %d : CAC %d : EIP %d."
           --#ARGUMENTS {0,1,2,3,4,}
           --#SEVERITY  MINOR
           --#TIMEINDEX 136
           --#STATE     WARNING
        ::= 13600868

   sCellEventTrap-04-00 TRAP-TYPE  -- CAC Code: 03
        ENTERPRISE compaq
        VARIABLES  { scellNameDateTime,
                     scellSWComponent,
                     scellECode,
                     scellCAC,
                     scellEIP}
        DESCRIPTION
             "Severity: Undetermined -- more information needed to determine severity. Controller operation was terminated due to an unrecoverable event detected by either software or hardware or due to an action initiated via the Storage System Management Interface."
           --#TYPE      "StorageCell Event 0400031c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601024

   sCellEventTrap-04-01 TRAP-TYPE  -- CAC Code: 03
        ENTERPRISE compaq
        VARIABLES  { scellNameDateTime,
                     scellSWComponent,
                     scellECode,
                     scellCAC,
                     scellEIP}
        DESCRIPTION
             "Severity: Undetermined -- more information needed to determine severity. This controller has received a last gasp message from another controller prior to it terminating operation."
           --#TYPE      "StorageCell Event 0401031c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601025

   sCellEventTrap-04-02 TRAP-TYPE  -- CAC Code: 01
        ENTERPRISE compaq
        VARIABLES  { scellNameDateTime,
                     scellSWComponent,
                     scellECode,
                     scellCAC,
                     scellEIP}
        DESCRIPTION
             "Severity: Critical -- failure or failure imminent. A machine check occurred while a termination event was being processed."
           --#TYPE      "StorageCell Event 04020101"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601026

   sCellEventTrap-04-03 TRAP-TYPE  -- CAC Code: 01
        ENTERPRISE compaq
        VARIABLES  { scellNameDateTime,
                     scellSWComponent,
                     scellECode,
                     scellCAC,
                     scellEIP}
        DESCRIPTION
             "Severity: Critical -- failure or failure imminent. An unexpected event occurred while a termination event was being processed."
           --#TYPE      "StorageCell Event 04030102"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601027

   sCellEventTrap-04-04 TRAP-TYPE  -- CAC Code: 00
        ENTERPRISE compaq
        VARIABLES  { scellNameDateTime,
                     scellSWComponent,
                     scellECode,
                     scellCAC,
                     scellEIP}
        DESCRIPTION
             "Severity: Normal -- informational in nature. The Storage System Event Log validation completed successfully."
           --#TYPE      "StorageCell Event 04040003"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601028

   sCellEventTrap-04-05 TRAP-TYPE  -- CAC Code: 00
        ENTERPRISE compaq
        VARIABLES  { scellNameDateTime,
                     scellSWComponent,
                     scellECode,
                     scellCAC,
                     scellEIP}
        DESCRIPTION
             "Severity: Normal -- informational in nature. The Storage System Event Log validation failed."
           --#TYPE      "StorageCell Event 04050003"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601029

   sCellEventTrap-04-06 TRAP-TYPE  -- CAC Code: 08
        ENTERPRISE compaq
        VARIABLES  { scellNameDateTime,
                     scellSWComponent,
                     scellECode,
                     scellCAC,
                     scellEIP}
        DESCRIPTION
             "Severity: Normal -- informational in nature. Local event reports were lost due to an insufficient supply of Event Log Packets on this controller."
           --#TYPE      "StorageCell Event 04060803"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601030

   sCellEventTrap-04-07 TRAP-TYPE  -- CAC Code: 08
        ENTERPRISE compaq
        VARIABLES  { scellNameDateTime,
                     scellSWComponent,
                     scellECode,
                     scellCAC,
                     scellEIP}
        DESCRIPTION
             "Severity: Normal -- informational in nature. Remote event reports were lost due to an insufficient supply of Event Log Packets on this controller."
           --#TYPE      "StorageCell Event 04070803"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601031

   sCellEventTrap-04-08 TRAP-TYPE  -- CAC Code: 00
        ENTERPRISE compaq
        VARIABLES  { scellNameDateTime,
                     scellSWComponent,
                     scellECode,
                     scellCAC,
                     scellEIP}
        DESCRIPTION
             "Severity: Normal -- informational in nature. The Storage System Termination Event Log has become inaccessible."
           --#TYPE      "StorageCell Event 04080003"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601032

   sCellEventTrap-04-09 TRAP-TYPE  -- CAC Code: 00
        ENTERPRISE compaq
        VARIABLES  { scellNameDateTime,
                     scellSWComponent,
                     scellECode,
                     scellCAC,
                     scellEIP}
        DESCRIPTION
             "Severity: Normal -- informational in nature. The Storage System Termination Event Log validation completed successfully."
           --#TYPE      "StorageCell Event 04090003"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601033

   sCellEventTrap-04-0a TRAP-TYPE  -- CAC Code: 00
        ENTERPRISE compaq
        VARIABLES  { scellNameDateTime,
                     scellSWComponent,
                     scellECode,
                     scellCAC,
                     scellEIP}
        DESCRIPTION
             "Severity: Normal -- informational in nature. The Storage System Termination Event Log validation failed."
           --#TYPE      "StorageCell Event 040a0003"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601034

   sCellEventTrap-04-0b TRAP-TYPE  -- CAC Code: 00
        ENTERPRISE compaq
        VARIABLES  { scellNameDateTime,
                     scellSWComponent,
                     scellECode,
                     scellCAC,
                     scellEIP}
        DESCRIPTION
             "Severity: Normal -- informational in nature. The Storage System Termination Event Log has been updated with the termination event information obtained from the controller that is not the Storage System Master."
           --#TYPE      "StorageCell Event 040b0003"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601035

   sCellEventTrap-04-0c TRAP-TYPE  -- CAC Code: 08
        ENTERPRISE compaq
        VARIABLES  { scellNameDateTime,
                     scellSWComponent,
                     scellECode,
                     scellCAC,
                     scellEIP}
        DESCRIPTION
             "Severity: Normal -- informational in nature. The Fault Manager on the Storage System Master received an invalid Event Information Packet from the remote Fault Manager."
           --#TYPE      "StorageCell Event 040c0803"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601036

   sCellEventTrap-04-0d TRAP-TYPE  -- CAC Code: 00
        ENTERPRISE compaq
        VARIABLES  { scellNameDateTime,
                     scellSWComponent,
                     scellECode,
                     scellCAC,
                     scellEIP}
        DESCRIPTION
             "Severity: Normal -- informational in nature. The Fault Manager operation was made quiescent."
           --#TYPE      "StorageCell Event 040d0003"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601037

   sCellEventTrap-04-0e TRAP-TYPE  -- CAC Code: 03
        ENTERPRISE compaq
        VARIABLES  { scellNameDateTime,
                     scellSWComponent,
                     scellECode,
                     scellCAC,
                     scellEIP}
        DESCRIPTION
             "Severity: Undetermined -- more information needed to determine severity. A controller sent a last gasp message prior to terminating operation with an indication that both controllers should terminate operation."
           --#TYPE      "StorageCell Event 040e031c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601038

   sCellEventTrap-04-0f TRAP-TYPE  -- CAC Code: 00
        ENTERPRISE compaq
        VARIABLES  { scellNameDateTime,
                     scellSWComponent,
                     scellECode,
                     scellCAC,
                     scellEIP}
        DESCRIPTION
             "Severity: Normal -- informational in nature. This controller sent its termination event information to the controller that is the Storage System Master."
           --#TYPE      "StorageCell Event 040f0003"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601039

   sCellEventTrap-04-10 TRAP-TYPE  -- CAC Code: 08
        ENTERPRISE compaq
        VARIABLES  { scellNameDateTime,
                     scellSWComponent,
                     scellECode,
                     scellCAC,
                     scellEIP}
        DESCRIPTION
             "Severity: Normal -- informational in nature. Event reports were lost due to an insufficient supply of ISR Event Log Packets on the controller that is the Storage System Master."
           --#TYPE      "StorageCell Event 04100803"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601040

   sCellEventTrap-04-11 TRAP-TYPE  -- CAC Code: 08
        ENTERPRISE compaq
        VARIABLES  { scellNameDateTime,
                     scellSWComponent,
                     scellECode,
                     scellCAC,
                     scellEIP}
        DESCRIPTION
             "Severity: Normal -- informational in nature. Event reports were lost due to an insufficient supply of ISR Event Log Packets on the controller that is not the Storage System Master."
           --#TYPE      "StorageCell Event 04110803"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601041

   sCellEventTrap-04-12 TRAP-TYPE  -- CAC Code: 00
        ENTERPRISE compaq
        VARIABLES  { scellNameDateTime,
                     scellSWComponent,
                     scellECode,
                     scellCAC,
                     scellEIP}
        DESCRIPTION
             "Severity: Normal -- informational in nature. The last event reporting interval has changed or last event reporting has been enabled or disabled."
           --#TYPE      "StorageCell Event 04120003"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601042

   sCellEventTrap-04-13 TRAP-TYPE  -- CAC Code: 00
        ENTERPRISE compaq
        VARIABLES  { scellNameDateTime,
                     scellSWComponent,
                     scellECode,
                     scellCAC,
                     scellEIP}
        DESCRIPTION
             "Severity: Normal -- informational in nature. Storage System event reporting is still active."
           --#TYPE      "StorageCell Event 04130003"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601043

   sCellEventTrap-04-14 TRAP-TYPE  -- CAC Code: 03
        ENTERPRISE compaq
        VARIABLES  { scellNameDateTime,
                     scellSWComponent,
                     scellECode,
                     scellCAC,
                     scellEIP}
        DESCRIPTION
             "Severity: Undetermined -- more information needed to determine severity. controller operation was terminated due to an unrecoverable event detected by either software or hardware or due to an action initiated via the Storage System Management Interface."
           --#TYPE      "StorageCell Event 0414031d"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601044

   sCellEventTrap-04-15 TRAP-TYPE  -- CAC Code: 03
        ENTERPRISE compaq
        VARIABLES  { scellNameDateTime,
                     scellSWComponent,
                     scellECode,
                     scellCAC,
                     scellEIP}
        DESCRIPTION
             "Severity: Undetermined -- more information needed to determine severity. This controller has received a last gasp message from another controller prior to it terminating operation."
           --#TYPE      "StorageCell Event 0415031d"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601045

   sCellEventTrap-04-16 TRAP-TYPE  -- CAC Code: 03
        ENTERPRISE compaq
        VARIABLES  { scellNameDateTime,
                     scellSWComponent,
                     scellECode,
                     scellCAC,
                     scellEIP}
        DESCRIPTION
             "Severity: Undetermined -- more information needed to determine severity. A controller sent a last gasp message prior to terminating operation with an indication that both controllers should terminate operation."
           --#TYPE      "StorageCell Event 0416031d"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601046

   sCellEventTrap-04-18 TRAP-TYPE  -- CAC Code: 00
        ENTERPRISE compaq
        VARIABLES  { scellNameDateTime,
                     scellSWComponent,
                     scellECode,
                     scellCAC,
                     scellEIP}
        DESCRIPTION
             "Severity: Normal -- informational in nature. The Manufacturing Event Analysis Log validation completed successfully."
           --#TYPE      "StorageCell Event 04180003"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601048

   sCellEventTrap-04-19 TRAP-TYPE  -- CAC Code: 00
        ENTERPRISE compaq
        VARIABLES  { scellNameDateTime,
                     scellSWComponent,
                     scellECode,
                     scellCAC,
                     scellEIP}
        DESCRIPTION
             "Severity: Normal -- informational in nature. The Manufacturing Event Analysis Log validation failed."
           --#TYPE      "StorageCell Event 04190003"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601049

   sCellEventTrap-04-1a TRAP-TYPE  -- CAC Code: 03
        ENTERPRISE compaq
        VARIABLES  { scellNameDateTime,
                     scellSWComponent,
                     scellECode,
                     scellCAC,
                     scellEIP}
        DESCRIPTION
             "Severity: Undetermined -- more information needed to determine severity. An error condition was encountered while this controller's Last Termination Event information was being processed."
           --#TYPE      "StorageCell Event 041a031c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601050

   sCellEventTrap-04-1b TRAP-TYPE  -- CAC Code: 03
        ENTERPRISE compaq
        VARIABLES  { scellNameDateTime,
                     scellSWComponent,
                     scellECode,
                     scellCAC,
                     scellEIP}
        DESCRIPTION
             "Severity: Undetermined -- more information needed to determine severity. An error condition was encountered while this controller's Last Termination Event information was being processed."
           --#TYPE      "StorageCell Event 041b031d"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601051

   sCellEventTrap-04-1f TRAP-TYPE  -- CAC Code: 00
        ENTERPRISE compaq
        VARIABLES  { scellNameDateTime,
                     scellSWComponent,
                     scellECode,
                     scellCAC,
                     scellEIP}
        DESCRIPTION
             "Severity: Normal -- informational in nature. Eva NVRAM Uptime invalid"
           --#TYPE      "StorageCell Event 041f0032"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601055

   sCellEventTrap-06-00 TRAP-TYPE  -- CAC Code: 00
        ENTERPRISE compaq
        VARIABLES  { scellNameDateTime,
                     scellSWComponent,
                     scellECode,
                     scellCAC,
                     scellEIP}
        DESCRIPTION
             "Severity: Normal -- informational in nature. A physical disk drive has reported that it has exceeded its failure prediction threshold."
           --#TYPE      "StorageCell Event 06000009"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601536

   sCellEventTrap-06-01 TRAP-TYPE  -- CAC Code: 4a
        ENTERPRISE compaq
        VARIABLES  { scellNameDateTime,
                     scellSWComponent,
                     scellECode,
                     scellCAC,
                     scellEIP}
        DESCRIPTION
             "Severity: Warning -- not failed but attention recommended or required. A Device port on the controller has failed to respond."
           --#TYPE      "StorageCell Event 06014a08"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601537

   sCellEventTrap-06-02 TRAP-TYPE  -- CAC Code: 00
        ENTERPRISE compaq
        VARIABLES  { scellNameDateTime,
                     scellSWComponent,
                     scellECode,
                     scellCAC,
                     scellEIP}
        DESCRIPTION
             "Severity: Normal -- informational in nature. A physical disk drive or an Enclosure Link Module has reported a check condition error."
           --#TYPE      "StorageCell Event 06020009"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601538

   sCellEventTrap-06-03 TRAP-TYPE  -- CAC Code: 47
        ENTERPRISE compaq
        VARIABLES  { scellNameDateTime,
                     scellSWComponent,
                     scellECode,
                     scellCAC,
                     scellEIP}
        DESCRIPTION
             "Severity: Warning -- not failed but attention recommended or required. An exchange sent to a physical disk drive or another controller via the mirror port or a Device port has timed out"
           --#TYPE      "StorageCell Event 06034713"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601539

   sCellEventTrap-06-05 TRAP-TYPE  -- CAC Code: 49
        ENTERPRISE compaq
        VARIABLES  { scellNameDateTime,
                     scellSWComponent,
                     scellECode,
                     scellCAC,
                     scellEIP}
        DESCRIPTION
             "Severity: Warning -- not failed but attention recommended or required. Work has been sent to a physical disk drive or another controller via the mirror port but it did not respond."
           --#TYPE      "StorageCell Event 06054909"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601541

   sCellEventTrap-06-08 TRAP-TYPE  -- CAC Code: 00
        ENTERPRISE compaq
        VARIABLES  { scellNameDateTime,
                     scellSWComponent,
                     scellECode,
                     scellCAC,
                     scellEIP}
        DESCRIPTION
             "Severity: Normal -- informational in nature. An excessive number of link errors were detected on a controller's Device port. This informational event is triggered by the occurrence of an excessive number of Tachyon chip link status errors detected within a particular link status error type."
           --#TYPE      "StorageCell Event 06080007"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601544

   sCellEventTrap-06-09 TRAP-TYPE  -- CAC Code: 00
        ENTERPRISE compaq
        VARIABLES  { scellNameDateTime,
                     scellSWComponent,
                     scellECode,
                     scellCAC,
                     scellEIP}
        DESCRIPTION
             "Severity: Normal -- informational in nature. A physical disk drive has reported numerous failure prediction threshold exceeded errors."
           --#TYPE      "StorageCell Event 06090013"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601545

   sCellEventTrap-06-0a TRAP-TYPE  -- CAC Code: 00
        ENTERPRISE compaq
        VARIABLES  { scellNameDateTime,
                     scellSWComponent,
                     scellECode,
                     scellCAC,
                     scellEIP}
        DESCRIPTION
             "Severity: Normal -- informational in nature. A physical disk drive has reported numerous check condition errors."
           --#TYPE      "StorageCell Event 060a0013"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601546

   sCellEventTrap-06-0b TRAP-TYPE  -- CAC Code: 47
        ENTERPRISE compaq
        VARIABLES  { scellNameDateTime,
                     scellSWComponent,
                     scellECode,
                     scellCAC,
                     scellEIP}
        DESCRIPTION
             "Severity: Warning -- not failed but attention recommended or required. A non-data exchange sent to a physical disk drive has timed out."
           --#TYPE      "StorageCell Event 060b4709"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601547

   sCellEventTrap-06-1a TRAP-TYPE  -- CAC Code: 00
        ENTERPRISE compaq
        VARIABLES  { scellNameDateTime,
                     scellSWComponent,
                     scellECode,
                     scellCAC,
                     scellEIP}
        DESCRIPTION
             "Severity: Normal -- informational in nature. A physical disk drive has exceeded its soft error threshold."
           --#TYPE      "StorageCell Event 061a0009"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601562

   sCellEventTrap-06-1c TRAP-TYPE  -- CAC Code: 47
        ENTERPRISE compaq
        VARIABLES  { scellNameDateTime,
                     scellSWComponent,
                     scellECode,
                     scellCAC,
                     scellEIP}
        DESCRIPTION
             "Severity: Warning -- not failed but attention recommended or required. An outbound frame targeted to a physical disk drive has timed out."
           --#TYPE      "StorageCell Event 061c4709"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601564

   sCellEventTrap-06-1d TRAP-TYPE  -- CAC Code: 47
        ENTERPRISE compaq
        VARIABLES  { scellNameDateTime,
                     scellSWComponent,
                     scellECode,
                     scellCAC,
                     scellEIP}
        DESCRIPTION
             "Severity: Warning -- not failed but attention recommended or required. An exchange to a physical disk drive has been retried."
           --#TYPE      "StorageCell Event 061d4709"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601565

   sCellEventTrap-06-1e TRAP-TYPE  -- CAC Code: 4c
        ENTERPRISE compaq
        VARIABLES  { scellNameDateTime,
                     scellSWComponent,
                     scellECode,
                     scellCAC,
                     scellEIP}
        DESCRIPTION
             "Severity: Critical -- failure or failure imminent. A controller has detected only one accessible port to a device."
           --#TYPE      "StorageCell Event 061e4c13"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601566

   sCellEventTrap-06-1f TRAP-TYPE  -- CAC Code: 00
        ENTERPRISE compaq
        VARIABLES  { scellNameDateTime,
                     scellSWComponent,
                     scellECode,
                     scellCAC,
                     scellEIP}
        DESCRIPTION
             "Severity: Normal -- informational in nature. A previously reported device with only one port has been corrected and redundancy has been restored."
           --#TYPE      "StorageCell Event 061f0013"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601567

   sCellEventTrap-06-20 TRAP-TYPE  -- CAC Code: 40
        ENTERPRISE compaq
        VARIABLES  { scellNameDateTime,
                     scellSWComponent,
                     scellECode,
                     scellCAC,
                     scellEIP}
        DESCRIPTION
             "Severity: Critical -- failure or failure imminent. An unsupported device has been detected.  The device has been failed to prevent possible data corruption or system instability."
           --#TYPE      "StorageCell Event 06204013"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601568

   sCellEventTrap-06-21 TRAP-TYPE  -- CAC Code: 00
        ENTERPRISE compaq
        VARIABLES  { scellNameDateTime,
                     scellSWComponent,
                     scellECode,
                     scellCAC,
                     scellEIP}
        DESCRIPTION
             "Severity: Normal -- informational in nature. A device with incorrect block size has been detected."
           --#TYPE      "StorageCell Event 06210013"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601569

   sCellEventTrap-06-23 TRAP-TYPE  -- CAC Code: 00
        ENTERPRISE compaq
        VARIABLES  { scellNameDateTime,
                     scellSWComponent,
                     scellECode,
                     scellCAC,
                     scellEIP}
        DESCRIPTION
             "Severity: Normal -- informational in nature. A controller is about to retry a failed port."
           --#TYPE      "StorageCell Event 06230013"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601571

   sCellEventTrap-06-29 TRAP-TYPE  -- CAC Code: 00
        ENTERPRISE compaq
        VARIABLES  { scellNameDateTime,
                     scellSWComponent,
                     scellECode,
                     scellCAC,
                     scellEIP}
        DESCRIPTION
             "Severity: Normal -- informational in nature. The controller has sent a Basic Link Service command Abort Sequence Frame."
           --#TYPE      "StorageCell Event 06290009"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601577

   sCellEventTrap-06-2a TRAP-TYPE  -- CAC Code: 00
        ENTERPRISE compaq
        VARIABLES  { scellNameDateTime,
                     scellSWComponent,
                     scellECode,
                     scellCAC,
                     scellEIP}
        DESCRIPTION
             "Severity: Normal -- informational in nature. The controller has sent an Extended Link Service command Reinstate Recovery Qualifier."
           --#TYPE      "StorageCell Event 062a0009"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601578

   sCellEventTrap-06-2c TRAP-TYPE  -- CAC Code: 00
        ENTERPRISE compaq
        VARIABLES  { scellNameDateTime,
                     scellSWComponent,
                     scellECode,
                     scellCAC,
                     scellEIP}
        DESCRIPTION
             "Severity: Normal -- informational in nature. One or more media defects were detected on a physical disk drive."
           --#TYPE      "StorageCell Event 062c0012"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601580

   sCellEventTrap-06-2d TRAP-TYPE  -- CAC Code: 00
        ENTERPRISE compaq
        VARIABLES  { scellNameDateTime,
                     scellSWComponent,
                     scellECode,
                     scellCAC,
                     scellEIP}
        DESCRIPTION
             "Severity: Normal -- informational in nature. A controller issued a directed LIP to an arbitrated loop physical address."
           --#TYPE      "StorageCell Event 062d0012"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601581

   sCellEventTrap-06-30 TRAP-TYPE  -- CAC Code: 4e
        ENTERPRISE compaq
        VARIABLES  { scellNameDateTime,
                     scellSWComponent,
                     scellECode,
                     scellCAC,
                     scellEIP}
        DESCRIPTION
             "Severity: Critical -- failure or failure imminent. A controller has detected only one port of all devices in an enclosure."
           --#TYPE      "StorageCell Event 06304e13"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601584

   sCellEventTrap-06-31 TRAP-TYPE  -- CAC Code: 00
        ENTERPRISE compaq
        VARIABLES  { scellNameDateTime,
                     scellSWComponent,
                     scellECode,
                     scellCAC,
                     scellEIP}
        DESCRIPTION
             "Severity: Normal -- informational in nature. A previously reported device enclosure with only one port has been corrected and redundancy has been restored."
           --#TYPE      "StorageCell Event 06310013"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601585

   sCellEventTrap-06-32 TRAP-TYPE  -- CAC Code: 4e
        ENTERPRISE compaq
        VARIABLES  { scellNameDateTime,
                     scellSWComponent,
                     scellECode,
                     scellCAC,
                     scellEIP}
        DESCRIPTION
             "Severity: Critical -- failure or failure imminent. A controller has detected only one port of all devices on a port-pair."
           --#TYPE      "StorageCell Event 06324e13"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601586

   sCellEventTrap-06-33 TRAP-TYPE  -- CAC Code: 00
        ENTERPRISE compaq
        VARIABLES  { scellNameDateTime,
                     scellSWComponent,
                     scellECode,
                     scellCAC,
                     scellEIP}
        DESCRIPTION
             "Severity: Normal -- informational in nature. A previously reported port-pair with only one port has been corrected and redundancy has been restored."
           --#TYPE      "StorageCell Event 06330013"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601587

   sCellEventTrap-06-34 TRAP-TYPE  -- CAC Code: 00
        ENTERPRISE compaq
        VARIABLES  { scellNameDateTime,
                     scellSWComponent,
                     scellECode,
                     scellCAC,
                     scellEIP}
        DESCRIPTION
             "Severity: Normal -- informational in nature. A controller has been told to enable a device port, and that device port was not disabled during boot diagnostics."
           --#TYPE      "StorageCell Event 06340013"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601588

   sCellEventTrap-06-40 TRAP-TYPE  -- CAC Code: 4d
        ENTERPRISE compaq
        VARIABLES  { scellNameDateTime,
                     scellSWComponent,
                     scellECode,
                     scellCAC,
                     scellEIP}
        DESCRIPTION
             "Severity: Critical -- failure or failure imminent. A physical disk drive that has new capabilities has been detected. The physical disk drive has properties that may or may not be compatible with this release of Enterprise Virtual Array firmware -- the drive will be prevented from being used until the Approved Drive Firmware table has been updated to allow it."
           --#TYPE      "StorageCell Event 06404d04"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601600

   sCellEventTrap-06-41 TRAP-TYPE  -- CAC Code: 00
        ENTERPRISE compaq
        VARIABLES  { scellNameDateTime,
                     scellSWComponent,
                     scellECode,
                     scellCAC,
                     scellEIP}
        DESCRIPTION
             "Severity: Normal -- informational in nature. The device loop configuration has changed on a controller's Device port. This informational event contains a page of the newly genereated fibre channel loop map. Devices are listed in loop order using their ALPAs."
           --#TYPE      "StorageCell Event 06410017"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601601

   sCellEventTrap-06-4b TRAP-TYPE  -- CAC Code: 00
        ENTERPRISE compaq
        VARIABLES  { scellNameDateTime,
                     scellSWComponent,
                     scellECode,
                     scellCAC,
                     scellEIP}
        DESCRIPTION
             "Severity: Normal -- informational in nature. The controller has been instructed to Enable or Disable Loop Recovery Operations."
           --#TYPE      "StorageCell Event 064b0008"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601611

   sCellEventTrap-06-4e TRAP-TYPE  -- CAC Code: 00
        ENTERPRISE compaq
        VARIABLES  { scellNameDateTime,
                     scellSWComponent,
                     scellECode,
                     scellCAC,
                     scellEIP}
        DESCRIPTION
             "Severity: Normal -- informational in nature. A physical disk drive has reported a non-zero RSP_CODE. in response to an I/O. This is not interesting by itself, as the I/O will be retried if retries remain and are allowed for the particular type of I/O."
           --#TYPE      "StorageCell Event 064e0009"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601614

   sCellEventTrap-06-4f TRAP-TYPE  -- CAC Code: 00
        ENTERPRISE compaq
        VARIABLES  { scellNameDateTime,
                     scellSWComponent,
                     scellECode,
                     scellCAC,
                     scellEIP}
        DESCRIPTION
             "Severity: Normal -- informational in nature. An Enclosure Link Module has begun updating its code. Do not power down the Enclosure until the code update has completed."
           --#TYPE      "StorageCell Event 064f0006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601615

   sCellEventTrap-06-50 TRAP-TYPE  -- CAC Code: 00
        ENTERPRISE compaq
        VARIABLES  { scellNameDateTime,
                     scellSWComponent,
                     scellECode,
                     scellCAC,
                     scellEIP}
        DESCRIPTION
             "Severity: Normal -- informational in nature. An Enclosure Link Module has completed updating its code. It is now safe to power down the Enclosure."
           --#TYPE      "StorageCell Event 06500006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601616

   sCellEventTrap-06-51 TRAP-TYPE  -- CAC Code: 00
        ENTERPRISE compaq
        VARIABLES  { scellNameDateTime,
                     scellSWComponent,
                     scellECode,
                     scellCAC,
                     scellEIP}
        DESCRIPTION
             "Severity: Normal -- informational in nature. A controller has sent a SES control page to the Enclosure Link Module in the Enclosure for drive bay bypass control."
           --#TYPE      "StorageCell Event 06510006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601617

   sCellEventTrap-06-52 TRAP-TYPE  -- CAC Code: 00
        ENTERPRISE compaq
        VARIABLES  { scellNameDateTime,
                     scellSWComponent,
                     scellECode,
                     scellCAC,
                     scellEIP}
        DESCRIPTION
             "Severity: Normal -- informational in nature. A controller has sent a SES control page to the Enclosure Link Module in the Enclosure for drive bay power control."
           --#TYPE      "StorageCell Event 06520006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601618

   sCellEventTrap-06-53 TRAP-TYPE  -- CAC Code: 00
        ENTERPRISE compaq
        VARIABLES  { scellNameDateTime,
                     scellSWComponent,
                     scellECode,
                     scellCAC,
                     scellEIP}
        DESCRIPTION
             "Severity: Normal -- informational in nature. A controller has sent a SES control page to the Enclosure Link Module in the Enclosure to change the enclosure ID number."
           --#TYPE      "StorageCell Event 06530006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601619

   sCellEventTrap-06-54 TRAP-TYPE  -- CAC Code: 00
        ENTERPRISE compaq
        VARIABLES  { scellNameDateTime,
                     scellSWComponent,
                     scellECode,
                     scellCAC,
                     scellEIP}
        DESCRIPTION
             "Severity: Normal -- informational in nature. A controller has discovered an Enclosure and is allocating resources for it."
           --#TYPE      "StorageCell Event 06540006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601620

   sCellEventTrap-06-55 TRAP-TYPE  -- CAC Code: 89
        ENTERPRISE compaq
        VARIABLES  { scellNameDateTime,
                     scellSWComponent,
                     scellECode,
                     scellCAC,
                     scellEIP}
        DESCRIPTION
             "Severity: Critical -- failure or failure imminent. An Enclosure Link Module has been failed, and can no longer be used to detect drive position information, or to issue bypass/unbypass commands."
           --#TYPE      "StorageCell Event 06558906"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601621

   sCellEventTrap-06-56 TRAP-TYPE  -- CAC Code: 00
        ENTERPRISE compaq
        VARIABLES  { scellNameDateTime,
                     scellSWComponent,
                     scellECode,
                     scellCAC,
                     scellEIP}
        DESCRIPTION
             "Severity: Normal -- informational in nature. A controller has sent a SES control page to the Enclosure Link Module in the Enclosure to shutdown the drive enclosure."
           --#TYPE      "StorageCell Event 06560006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601622

   sCellEventTrap-06-57 TRAP-TYPE  -- CAC Code: 00
        ENTERPRISE compaq
        VARIABLES  { scellNameDateTime,
                     scellSWComponent,
                     scellECode,
                     scellCAC,
                     scellEIP}
        DESCRIPTION
             "Severity: Normal -- informational in nature. A controller has detected an inconsistency in the enclosure ID numbers reported by the Enclosure Link Modules in the in the Enclosure."
           --#TYPE      "StorageCell Event 06570006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601623

   sCellEventTrap-06-58 TRAP-TYPE  -- CAC Code: 99
        ENTERPRISE compaq
        VARIABLES  { scellNameDateTime,
                     scellSWComponent,
                     scellECode,
                     scellCAC,
                     scellEIP}
        DESCRIPTION
             "Severity: Critical -- failure or failure imminent. A controller has detected a potential cabling error. The Enclosure Link Module in the Enclosure is reporting it is conencted to the wrong Device port."
           --#TYPE      "StorageCell Event 06589906"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601624

   sCellEventTrap-06-59 TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in a physical disk drive bay condition in a Enclosure"
           --#TYPE      "StorageCell Event 06590006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601625

   sCellEventTrap-06-5a TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in a Enclosure condition."
           --#TYPE      "StorageCell Event 065a0006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601626

   sCellEventTrap-06-5b TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in a Enclosure power supply condition."
           --#TYPE      "StorageCell Event 065b0006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601627

   sCellEventTrap-06-5c TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in a Enclosure fan module 1 condition."
           --#TYPE      "StorageCell Event 065c0006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601628

   sCellEventTrap-06-5d TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in a Enclosure fan module 2 condition."
           --#TYPE      "StorageCell Event 065d0006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601629

   sCellEventTrap-06-5e TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in the Enclosure A-side link module's condition."
           --#TYPE      "StorageCell Event 065e0006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601630

   sCellEventTrap-06-5f TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in the Enclosure B-side link module's condition."
           --#TYPE      "StorageCell Event 065f0006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601631

   sCellEventTrap-06-60 TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in the Enclosure A-side link module's transceiver condition."
           --#TYPE      "StorageCell Event 06600006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601632

   sCellEventTrap-06-61 TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in the Enclosure B-side link module's transceiver condition."
           --#TYPE      "StorageCell Event 06610006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601633

   sCellEventTrap-06-62 TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in the Enclosure A-side link module alphanumeric display."
           --#TYPE      "StorageCell Event 06620006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601634

   sCellEventTrap-06-63 TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in the Enclosure B-side link module alphanumeric display."
           --#TYPE      "StorageCell Event 06630006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601635

   sCellEventTrap-06-64 TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in the Enclosure A-side link module temperature sensor."
           --#TYPE      "StorageCell Event 06640006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601636

   sCellEventTrap-06-65 TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in the Enclosure B-side link module temperature sensor."
           --#TYPE      "StorageCell Event 06650006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601637

   sCellEventTrap-06-66 TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in the Enclosure midplane condition."
           --#TYPE      "StorageCell Event 06660006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601638

   sCellEventTrap-06-67 TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in the Enclosure midplane temperature sensor condition."
           --#TYPE      "StorageCell Event 06670006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601639

   sCellEventTrap-06-68 TRAP-TYPE  -- CAC Code: 4c
        ENTERPRISE compaq
        VARIABLES  { scellNameDateTime,
                     scellSWComponent,
                     scellECode,
                     scellCAC,
                     scellEIP}
        DESCRIPTION
             "Severity: Critical -- failure or failure imminent. A controller has detected only one port of a Enclosure device."
           --#TYPE      "StorageCell Event 06684c13"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601640

   sCellEventTrap-06-69 TRAP-TYPE  -- CAC Code: 00
        ENTERPRISE compaq
        VARIABLES  { scellNameDateTime,
                     scellSWComponent,
                     scellECode,
                     scellCAC,
                     scellEIP}
        DESCRIPTION
             "Severity: Normal -- informational in nature. A previously reported Enclosure device with only one port has been corrected and redundancy has been restored."
           --#TYPE      "StorageCell Event 06690013"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601641

   sCellEventTrap-06-6b TRAP-TYPE  -- CAC Code: 00
        ENTERPRISE compaq
        VARIABLES  { scellNameDateTime,
                     scellSWComponent,
                     scellECode,
                     scellCAC,
                     scellEIP}
        DESCRIPTION
             "Severity: Normal -- informational in nature. A Device Port is in the STO (State TimeOut) state, The corresponding device Device port on the specified controller has its loop port state machine hung up for 2 sec."
           --#TYPE      "StorageCell Event 066b0028"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601643

   sCellEventTrap-06-6c TRAP-TYPE  -- CAC Code: 00
        ENTERPRISE compaq
        VARIABLES  { scellNameDateTime,
                     scellSWComponent,
                     scellECode,
                     scellCAC,
                     scellEIP}
        DESCRIPTION
             "Severity: Normal -- informational in nature. The controller has finished codeloads to all Enclosure hardware requiring updates."
           --#TYPE      "StorageCell Event 066c0008"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601644

   sCellEventTrap-06-6d TRAP-TYPE  -- CAC Code: f3
        ENTERPRISE compaq
        VARIABLES  { scellNameDateTime,
                     scellSWComponent,
                     scellECode,
                     scellCAC,
                     scellEIP}
        DESCRIPTION
             "Severity: Critical -- failure or failure imminent. The controller cannot continue to codeload any Enclosure hardware requiring updates until backend redundancy is restored."
           --#TYPE      "StorageCell Event 066df308"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601645

   sCellEventTrap-06-6e TRAP-TYPE  -- CAC Code: 00
        ENTERPRISE compaq
        VARIABLES  { scellNameDateTime,
                     scellSWComponent,
                     scellECode,
                     scellCAC,
                     scellEIP}
        DESCRIPTION
             "Severity: Normal -- informational in nature. The controller has cleared any previous issues blocking codeload of any Enclosure hardware requiring updates. Enclosure codeload operations will now continue."
           --#TYPE      "StorageCell Event 066e0008"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601646

   sCellEventTrap-06-6f TRAP-TYPE  -- CAC Code: 00
        ENTERPRISE compaq
        VARIABLES  { scellNameDateTime,
                     scellSWComponent,
                     scellECode,
                     scellCAC,
                     scellEIP}
        DESCRIPTION
             "Severity: Normal -- informational in nature. One or more Fibre Channel devices have taken too long to complete the SCSI login phase in the allowed time."
           --#TYPE      "StorageCell Event 066f0009"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601647

   sCellEventTrap-06-70 TRAP-TYPE  -- CAC Code: 00
        ENTERPRISE compaq
        VARIABLES  { scellNameDateTime,
                     scellSWComponent,
                     scellECode,
                     scellCAC,
                     scellEIP}
        DESCRIPTION
             "Severity: Normal -- informational in nature. One or more Fibre Channel devices have taken too long to complete the transport login phase in the allowed time."
           --#TYPE      "StorageCell Event 06700009"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601648

   sCellEventTrap-06-71 TRAP-TYPE  -- CAC Code: f4
        ENTERPRISE compaq
        VARIABLES  { scellNameDateTime,
                     scellSWComponent,
                     scellECode,
                     scellCAC,
                     scellEIP}
        DESCRIPTION
             "Severity: Critical -- failure or failure imminent. A controller has detected a critical condition for a Disk Enclosure Power Supply. This often implies a loss in power to the Disk Enclosure Power Supply, causing a loss of redundancy in power to the Disk Enclosure."
           --#TYPE      "StorageCell Event 0671f406"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601649

   sCellEventTrap-06-72 TRAP-TYPE  -- CAC Code: 00
        ENTERPRISE compaq
        VARIABLES  { scellNameDateTime,
                     scellSWComponent,
                     scellECode,
                     scellCAC,
                     scellEIP}
        DESCRIPTION
             "Severity: Normal -- informational in nature. Link Down occurred on a Back-end Port."
           --#TYPE      "StorageCell Event 0672002d"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601650

   sCellEventTrap-06-73 TRAP-TYPE  -- CAC Code: 00
        ENTERPRISE compaq
        VARIABLES  { scellNameDateTime,
                     scellSWComponent,
                     scellECode,
                     scellCAC,
                     scellEIP}
        DESCRIPTION
             "Severity: Normal -- informational in nature. Link Up occurred on a Back-end Port."
           --#TYPE      "StorageCell Event 0673002d"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601651

   sCellEventTrap-06-75 TRAP-TYPE  -- CAC Code: 00
        ENTERPRISE compaq
        VARIABLES  { scellNameDateTime,
                     scellSWComponent,
                     scellECode,
                     scellCAC,
                     scellEIP}
        DESCRIPTION
             "Severity: Normal -- informational in nature. Controller issued a phy disable command to an enclosure."
           --#TYPE      "StorageCell Event 0675002d"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601653

   sCellEventTrap-06-76 TRAP-TYPE  -- CAC Code: 00
        ENTERPRISE compaq
        VARIABLES  { scellNameDateTime,
                     scellSWComponent,
                     scellECode,
                     scellCAC,
                     scellEIP}
        DESCRIPTION
             "Severity: Normal -- informational in nature. Controller issued a phy enable command to an enclosure."
           --#TYPE      "StorageCell Event 0676002d"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601654

   sCellEventTrap-06-77 TRAP-TYPE  -- CAC Code: 00
        ENTERPRISE compaq
        VARIABLES  { scellNameDateTime,
                     scellSWComponent,
                     scellECode,
                     scellCAC,
                     scellEIP}
        DESCRIPTION
             "Severity: Normal -- informational in nature. The device map has changed."
           --#TYPE      "StorageCell Event 0677002e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601655

   sCellEventTrap-06-78 TRAP-TYPE  -- CAC Code: 00
        ENTERPRISE compaq
        VARIABLES  { scellNameDateTime,
                     scellSWComponent,
                     scellECode,
                     scellCAC,
                     scellEIP}
        DESCRIPTION
             "Severity: Normal -- informational in nature. The enclosure layout has changed."
           --#TYPE      "StorageCell Event 0678002d"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601656

   sCellEventTrap-06-79 TRAP-TYPE  -- CAC Code: 00
        ENTERPRISE compaq
        VARIABLES  { scellNameDateTime,
                     scellSWComponent,
                     scellECode,
                     scellCAC,
                     scellEIP}
        DESCRIPTION
             "Severity: Normal -- informational in nature. A device is operating with a degraded link rate."
           --#TYPE      "StorageCell Event 0679002d"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601657

   sCellEventTrap-06-7a TRAP-TYPE  -- CAC Code: 00
        ENTERPRISE compaq
        VARIABLES  { scellNameDateTime,
                     scellSWComponent,
                     scellECode,
                     scellCAC,
                     scellEIP}
        DESCRIPTION
             "Severity: Normal -- informational in nature. A device previously operating with a degraded link rate has been restored to full link rate."
           --#TYPE      "StorageCell Event 067a002d"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601658

   sCellEventTrap-06-7b TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in a SAS expander element's status."
           --#TYPE      "StorageCell Event 067b002d"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601659

   sCellEventTrap-06-7c TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in a SAS connector element's status."
           --#TYPE      "StorageCell Event 067c002d"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601660

   sCellEventTrap-06-7d TRAP-TYPE  -- CAC Code: 40
        ENTERPRISE compaq
        VARIABLES  { scellNameDateTime,
                     scellSWComponent,
                     scellECode,
                     scellCAC,
                     scellEIP}
        DESCRIPTION
             "Severity: Critical -- failure or failure imminent. An invalid disk drive has been inserted, please replace with an EVA disk drive."
           --#TYPE      "StorageCell Event 067d402d"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601661

   sCellEventTrap-06-7e TRAP-TYPE  -- CAC Code: 00
        ENTERPRISE compaq
        VARIABLES  { scellNameDateTime,
                     scellSWComponent,
                     scellECode,
                     scellCAC,
                     scellEIP}
        DESCRIPTION
             "Severity: Normal -- informational in nature. A device did not complete configuration properly and has been placed in an exception state."
           --#TYPE      "StorageCell Event 067e002d"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601662

   sCellEventTrap-06-7f TRAP-TYPE  -- CAC Code: 00
        ENTERPRISE compaq
        VARIABLES  { scellNameDateTime,
                     scellSWComponent,
                     scellECode,
                     scellCAC,
                     scellEIP}
        DESCRIPTION
             "Severity: Normal -- informational in nature. A device completed configuration after being placed in an exception state and is no longer in an exception state."
           --#TYPE      "StorageCell Event 067f002d"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601663

   sCellEventTrap-06-80 TRAP-TYPE  -- CAC Code: 42
        ENTERPRISE compaq
        VARIABLES  { scellNameDateTime,
                     scellSWComponent,
                     scellECode,
                     scellCAC,
                     scellEIP}
        DESCRIPTION
             "Severity: Critical -- failure or failure imminent. A device has failed configuration and is currently unusable."
           --#TYPE      "StorageCell Event 0680422d"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601664

   sCellEventTrap-06-81 TRAP-TYPE  -- CAC Code: 95
        ENTERPRISE compaq
        VARIABLES  { scellNameDateTime,
                     scellSWComponent,
                     scellECode,
                     scellCAC,
                     scellEIP}
        DESCRIPTION
             "Severity: Warning -- not failed but attention recommended or required. An Enclosure Failed to initialize."
           --#TYPE      "StorageCell Event 06819513"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601665

   sCellEventTrap-06-82 TRAP-TYPE  -- CAC Code: 00
        ENTERPRISE compaq
        VARIABLES  { scellNameDateTime,
                     scellSWComponent,
                     scellECode,
                     scellCAC,
                     scellEIP}
        DESCRIPTION
             "Severity: Normal -- informational in nature. This controller has requested that the other controller halt operations"
           --#TYPE      "StorageCell Event 0682000a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601666

   sCellEventTrap-06-85 TRAP-TYPE  -- CAC Code: 99
        ENTERPRISE compaq
        VARIABLES  { scellNameDateTime,
                     scellSWComponent,
                     scellECode,
                     scellCAC,
                     scellEIP}
        DESCRIPTION
             "Severity: Critical -- failure or failure imminent. Bad cabling configuration detected in the backend devices cabling."
           --#TYPE      "StorageCell Event 0685992d"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601669

   sCellEventTrap-06-86 TRAP-TYPE  -- CAC Code: 00
        ENTERPRISE compaq
        VARIABLES  { scellNameDateTime,
                     scellSWComponent,
                     scellECode,
                     scellCAC,
                     scellEIP}
        DESCRIPTION
             "Severity: Normal -- informational in nature. The controller has detected a Enclosure is missing while codeload is in progress."
           --#TYPE      "StorageCell Event 06860006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601670

   sCellEventTrap-06-87 TRAP-TYPE  -- CAC Code: 00
        ENTERPRISE compaq
        VARIABLES  { scellNameDateTime,
                     scellSWComponent,
                     scellECode,
                     scellCAC,
                     scellEIP}
        DESCRIPTION
             "Severity: Normal -- informational in nature. The controller has detected a Enclosure has comeback while codeload is in progress."
           --#TYPE      "StorageCell Event 06870006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601671

   sCellEventTrap-06-88 TRAP-TYPE  -- CAC Code: 00
        ENTERPRISE compaq
        VARIABLES  { scellNameDateTime,
                     scellSWComponent,
                     scellECode,
                     scellCAC,
                     scellEIP}
        DESCRIPTION
             "Severity: Normal -- informational in nature. A controller has detected a Enclosure is in the standby state."
           --#TYPE      "StorageCell Event 06880006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601672

   sCellEventTrap-06-89 TRAP-TYPE  -- CAC Code: 00
        ENTERPRISE compaq
        VARIABLES  { scellNameDateTime,
                     scellSWComponent,
                     scellECode,
                     scellCAC,
                     scellEIP}
        DESCRIPTION
             "Severity: Normal -- informational in nature. A controller has sent a SES control page to the Enclosure Link Module in the Enclosure to powerup the drive enclosure."
           --#TYPE      "StorageCell Event 06890006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601673

   sCellEventTrap-06-8a TRAP-TYPE  -- CAC Code: 00
        ENTERPRISE compaq
        VARIABLES  { scellNameDateTime,
                     scellSWComponent,
                     scellECode,
                     scellCAC,
                     scellEIP}
        DESCRIPTION
             "Severity: Normal -- informational in nature. A controller has detected a Enclosure has left the standby state and is now powered up."
           --#TYPE      "StorageCell Event 068a0006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601674

   sCellEventTrap-06-8c TRAP-TYPE  -- CAC Code: f4
        ENTERPRISE compaq
        VARIABLES  { scellNameDateTime,
                     scellSWComponent,
                     scellECode,
                     scellCAC,
                     scellEIP}
        DESCRIPTION
             "Severity: Critical -- failure or failure imminent. A controller has detected a critical condition for a Disk Enclosure Internal Power Supply. This often implies a failure of the Disk Enclosure Internal Power Supply, causing a loss of redundancy in power to the Disk Enclosure."
           --#TYPE      "StorageCell Event 068cf406"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601676

   sCellEventTrap-06-8d TRAP-TYPE  -- CAC Code: 00
        ENTERPRISE compaq
        VARIABLES  { scellNameDateTime,
                     scellSWComponent,
                     scellECode,
                     scellCAC,
                     scellEIP}
        DESCRIPTION
             "Severity: Normal -- informational in nature. A controller has detected a change in a Enclosure internal power supply condition."
           --#TYPE      "StorageCell Event 068d0006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601677

   sCellEventTrap-06-8f TRAP-TYPE  -- CAC Code: d4
        ENTERPRISE compaq
        VARIABLES  { scellNameDateTime,
                     scellSWComponent,
                     scellECode,
                     scellCAC,
                     scellEIP}
        DESCRIPTION
             "Severity: Critical -- failure or failure imminent. The controller cannot continue to codeload any Enclosure hardware requiring updates because image is corrupted on flash. Controller has to be replaced."
           --#TYPE      "StorageCell Event 068fd408"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601679

   sCellEventTrap-06-91 TRAP-TYPE  -- CAC Code: 40
        ENTERPRISE compaq
        VARIABLES  { scellNameDateTime,
                     scellSWComponent,
                     scellECode,
                     scellCAC,
                     scellEIP}
        DESCRIPTION
             "Severity: Critical -- failure or failure imminent. A physical disk drive whose capacity exceeds 2.2TB has its D_SENSE bit cleared."
           --#TYPE      "StorageCell Event 06914009"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13601681

   sCellEventTrap-07-00 TRAP-TYPE  -- CAC Code: b5
        ENTERPRISE compaq
        VARIABLES  { scellNameDateTime,
                     scellSWComponent,
                     scellECode,
                     scellCAC,
                     scellEIP}
        DESCRIPTION
             "Severity: Warning -- not failed but attention recommended or required. Allocation of a Virtual Disk has stalled due to insufficient space in the Disk Group caused by the failure or pulling of a physical disk drive."
           --#TYPE      "StorageCell Event 0700b515"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601792

   sCellEventTrap-07-01 TRAP-TYPE  -- CAC Code: b5
        ENTERPRISE compaq
        VARIABLES  { scellNameDateTime,
                     scellSWComponent,
                     scellECode,
                     scellCAC,
                     scellEIP}
        DESCRIPTION
             "Severity: Warning -- not failed but attention recommended or required. Expansion of a Virtual Disk has stalled due to insufficient space in the Disk Group caused by the failure or pulling of a physical disk drive."
           --#TYPE      "StorageCell Event 0701b515"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601793

   sCellEventTrap-07-02 TRAP-TYPE  -- CAC Code: 00
        ENTERPRISE compaq
        VARIABLES  { scellNameDateTime,
                     scellSWComponent,
                     scellECode,
                     scellCAC,
                     scellEIP}
        DESCRIPTION
             "Severity: Normal -- informational in nature. Leveling of capacity in a Disk Group has started."
           --#TYPE      "StorageCell Event 07020015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601794

   sCellEventTrap-07-03 TRAP-TYPE  -- CAC Code: 00
        ENTERPRISE compaq
        VARIABLES  { scellNameDateTime,
                     scellSWComponent,
                     scellECode,
                     scellCAC,
                     scellEIP}
        DESCRIPTION
             "Severity: Normal -- informational in nature. Leveling of capacity in a Disk Group has finished."
           --#TYPE      "StorageCell Event 07030015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601795

   sCellEventTrap-07-04 TRAP-TYPE  -- CAC Code: 00
        ENTERPRISE compaq
        VARIABLES  { scellNameDateTime,
                     scellSWComponent,
                     scellECode,
                     scellCAC,
                     scellEIP}
        DESCRIPTION
             "Severity: Normal -- informational in nature. A member management operation has started due to the appearance or disappearance of a physical disk drive."
           --#TYPE      "StorageCell Event 07040015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601796

   sCellEventTrap-07-05 TRAP-TYPE  -- CAC Code: 00
        ENTERPRISE compaq
        VARIABLES  { scellNameDateTime,
                     scellSWComponent,
                     scellECode,
                     scellCAC,
                     scellEIP}
        DESCRIPTION
             "Severity: Normal -- informational in nature. A member management operation has finished."
           --#TYPE      "StorageCell Event 07050015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601797

   sCellEventTrap-07-06 TRAP-TYPE  -- CAC Code: 00
        ENTERPRISE compaq
        VARIABLES  { scellNameDateTime,
                     scellSWComponent,
                     scellECode,
                     scellCAC,
                     scellEIP}
        DESCRIPTION
             "Severity: Normal -- informational in nature. A Disk Group has started changing its internal structure due to the appearance or disappearance of a Volume."
           --#TYPE      "StorageCell Event 07060015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601798

   sCellEventTrap-07-07 TRAP-TYPE  -- CAC Code: 00
        ENTERPRISE compaq
        VARIABLES  { scellNameDateTime,
                     scellSWComponent,
                     scellECode,
                     scellCAC,
                     scellEIP}
        DESCRIPTION
             "Severity: Normal -- informational in nature. A Disk Group has finished changing its internal structure due to the appearance or disappearance of a Volume."
           --#TYPE      "StorageCell Event 07070015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601799

   sCellEventTrap-07-08 TRAP-TYPE  -- CAC Code: 00
        ENTERPRISE compaq
        VARIABLES  { scellNameDateTime,
                     scellSWComponent,
                     scellECode,
                     scellCAC,
                     scellEIP}
        DESCRIPTION
             "Severity: Normal -- informational in nature. Deallocation of a Virtual Disk has failed after three attempts due to unknown circumstances.  This will more than likely be caused by failing physical drives.  The deletion will be restarted when a resync/reboot occurs."
           --#TYPE      "StorageCell Event 07080015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601800

   sCellEventTrap-07-09 TRAP-TYPE  -- CAC Code: b5
        ENTERPRISE compaq
        VARIABLES  { scellNameDateTime,
                     scellSWComponent,
                     scellECode,
                     scellCAC,
                     scellEIP}
        DESCRIPTION
             "Severity: Warning -- not failed but attention recommended or required. A member management operation has stalled due to insufficient space in the Disk Group."
           --#TYPE      "StorageCell Event 0709b515"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601801

   sCellEventTrap-07-0a TRAP-TYPE  -- CAC Code: 00
        ENTERPRISE compaq
        VARIABLES  { scellNameDateTime,
                     scellSWComponent,
                     scellECode,
                     scellCAC,
                     scellEIP}
        DESCRIPTION
             "Severity: Normal -- informational in nature. A stalled member management operation is being restarted."
           --#TYPE      "StorageCell Event 070a0015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601802

   sCellEventTrap-07-0b TRAP-TYPE  -- CAC Code: 00
        ENTERPRISE compaq
        VARIABLES  { scellNameDateTime,
                     scellSWComponent,
                     scellECode,
                     scellCAC,
                     scellEIP}
        DESCRIPTION
             "Severity: Normal -- informational in nature. Metadata utility event. If available, the tag1 field contains the identity of the Volume, and tag2 field contains the identity of the Logical Disk."
           --#TYPE      "StorageCell Event 070b0015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601803

   sCellEventTrap-07-0d TRAP-TYPE  -- CAC Code: 00
        ENTERPRISE compaq
        VARIABLES  { scellNameDateTime,
                     scellSWComponent,
                     scellECode,
                     scellCAC,
                     scellEIP}
        DESCRIPTION
             "Severity: Normal -- informational in nature. A member management operation encounter an error while processing a Logical Disk.  Processing on this logical disk will be retried again."
           --#TYPE      "StorageCell Event 070d0015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601805

   sCellEventTrap-07-0e TRAP-TYPE  -- CAC Code: 00
        ENTERPRISE compaq
        VARIABLES  { scellNameDateTime,
                     scellSWComponent,
                     scellECode,
                     scellCAC,
                     scellEIP}
        DESCRIPTION
             "Severity: Normal -- informational in nature. An range of ebits were set or cleared for a Logical Disk. A read of an LBA that has an ebit set will return MEDIA ERROR. A write to an LBA that has an ebit set will write the data and clear the ebit."
           --#TYPE      "StorageCell Event 070e0015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601806

   sCellEventTrap-07-0f TRAP-TYPE  -- CAC Code: 00
        ENTERPRISE compaq
        VARIABLES  { scellNameDateTime,
                     scellSWComponent,
                     scellECode,
                     scellCAC,
                     scellEIP}
        DESCRIPTION
             "Severity: Normal -- informational in nature. No Free CMAPs. Catastrophic number of drives missing or failed. The system will be inoperative while there are more missing or failed drives than the number of CMAPs in the system."
           --#TYPE      "StorageCell Event 070f0015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601807

   sCellEventTrap-07-10 TRAP-TYPE  -- CAC Code: 00
        ENTERPRISE compaq
        VARIABLES  { scellNameDateTime,
                     scellSWComponent,
                     scellECode,
                     scellCAC,
                     scellEIP}
        DESCRIPTION
             "Severity: Normal -- informational in nature. A member management operation has retried or waited too long"
           --#TYPE      "StorageCell Event 07100015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601808

   sCellEventTrap-07-11 TRAP-TYPE  -- CAC Code: 00
        ENTERPRISE compaq
        VARIABLES  { scellNameDateTime,
                     scellSWComponent,
                     scellECode,
                     scellCAC,
                     scellEIP}
        DESCRIPTION
             "Severity: Normal -- informational in nature. A Disk Group experienced an unexpected error during leveling or Redundant Storage Set migration and will be retried for the affected Virtual Disk."
           --#TYPE      "StorageCell Event 07110015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601809

   sCellEventTrap-07-12 TRAP-TYPE  -- CAC Code: 00
        ENTERPRISE compaq
        VARIABLES  { scellNameDateTime,
                     scellSWComponent,
                     scellECode,
                     scellCAC,
                     scellEIP}
        DESCRIPTION
             "Severity: Normal -- informational in nature. A Virtual Disk experienced an unexpected error during a migration operation and will be retried for the affected Disk Group."
           --#TYPE      "StorageCell Event 07120015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601810

   sCellEventTrap-07-13 TRAP-TYPE  -- CAC Code: 07
        ENTERPRISE compaq
        VARIABLES  { scellNameDateTime,
                     scellSWComponent,
                     scellECode,
                     scellCAC,
                     scellEIP}
        DESCRIPTION
             "Severity: Warning -- not failed but attention recommended or required. Metadata Check 0."
           --#TYPE      "StorageCell Event 07130715"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601811

   sCellEventTrap-07-14 TRAP-TYPE  -- CAC Code: 07
        ENTERPRISE compaq
        VARIABLES  { scellNameDateTime,
                     scellSWComponent,
                     scellECode,
                     scellCAC,
                     scellEIP}
        DESCRIPTION
             "Severity: Warning -- not failed but attention recommended or required. Metadata Check 1."
           --#TYPE      "StorageCell Event 07140715"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601812

   sCellEventTrap-07-15 TRAP-TYPE  -- CAC Code: 07
        ENTERPRISE compaq
        VARIABLES  { scellNameDateTime,
                     scellSWComponent,
                     scellECode,
                     scellCAC,
                     scellEIP}
        DESCRIPTION
             "Severity: Warning -- not failed but attention recommended or required. A Disk Group experienced an unexpected metadata condition, possibly Too Many Cbits or a UDPRS violation."
           --#TYPE      "StorageCell Event 07150715"
           --#SUMMARY   "SCellName-TimeDate %s : SWCID %d : ECode: %d : CAC %d : EIP %d."
           --#ARGUMENTS {0,1,2,3,4,}
           --#SEVERITY  MINOR
           --#TIMEINDEX 136
           --#STATE     WARNING
        ::= 13601813

   sCellEventTrap-07-16 TRAP-TYPE  -- CAC Code: 00
        ENTERPRISE compaq
        VARIABLES  { scellNameDateTime,
                     scellSWComponent,
                     scellECode,
                     scellCAC,
                     scellEIP}
        DESCRIPTION
             "Severity: Normal -- informational in nature. A maintenance command was used to set or clear a cbit in lab code."
           --#TYPE      "StorageCell Event 07160015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601814

   sCellEventTrap-07-17 TRAP-TYPE  -- CAC Code: 00
        ENTERPRISE compaq
        VARIABLES  { scellNameDateTime,
                     scellSWComponent,
                     scellECode,
                     scellCAC,
                     scellEIP}
        DESCRIPTION
             "Severity: Normal -- informational in nature. A Virtual Disk Expand or Shrink operation failed."
           --#TYPE      "StorageCell Event 07170015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601815

   sCellEventTrap-07-18 TRAP-TYPE  -- CAC Code: 00
        ENTERPRISE compaq
        VARIABLES  { scellNameDateTime,
                     scellSWComponent,
                     scellECode,
                     scellCAC,
                     scellEIP}
        DESCRIPTION
             "Severity: Normal -- informational in nature. PLDMC creation has finished for a Logical Disk."
           --#TYPE      "StorageCell Event 07180015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601816

   sCellEventTrap-07-19 TRAP-TYPE  -- CAC Code: 00
        ENTERPRISE compaq
        VARIABLES  { scellNameDateTime,
                     scellSWComponent,
                     scellECode,
                     scellCAC,
                     scellEIP}
        DESCRIPTION
             "Severity: Normal -- informational in nature. A Disk Group is invalid"
           --#TYPE      "StorageCell Event 07190015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601817

   sCellEventTrap-07-1a TRAP-TYPE  -- CAC Code: 00
        ENTERPRISE compaq
        VARIABLES  { scellNameDateTime,
                     scellSWComponent,
                     scellECode,
                     scellCAC,
                     scellEIP}
        DESCRIPTION
             "Severity: Normal -- informational in nature. A DUB pointer is invalid"
           --#TYPE      "StorageCell Event 071a0015"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13601818

   sCellEventTrap-09-01 TRAP-TYPE  -- CAC Code: 00
        ENTERPRISE compaq
        VARIABLES  { scellNameDateTime,
                     scellSWComponent,
                     scellECode,
                     scellCAC,
                     scellEIP}
        DESCRIPTION
             "Severity: Normal -- informational in nature. A physical disk drive has transitioned to the NORMAL state."
           --#TYPE      "StorageCell Event 09010005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602305

   sCellEventTrap-09-02 TRAP-TYPE  -- CAC Code: 00
        ENTERPRISE compaq
        VARIABLES  { scellNameDateTime,
                     scellSWComponent,
                     scellECode,
                     scellCAC,
                     scellEIP}
        DESCRIPTION
             "Severity: Normal -- informational in nature. The state of a Volume has changed."
           --#TYPE      "StorageCell Event 09020005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602306

   sCellEventTrap-09-04 TRAP-TYPE  -- CAC Code: 00
        ENTERPRISE compaq
        VARIABLES  { scellNameDateTime,
                     scellSWComponent,
                     scellECode,
                     scellCAC,
                     scellEIP}
        DESCRIPTION
             "Severity: Normal -- informational in nature. A controller has transitioned to the NORMAL state because the system is no longer inoperative."
           --#TYPE      "StorageCell Event 09040005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602308

   sCellEventTrap-09-05 TRAP-TYPE  -- CAC Code: 00
        ENTERPRISE compaq
        VARIABLES  { scellNameDateTime,
                     scellSWComponent,
                     scellECode,
                     scellCAC,
                     scellEIP}
        DESCRIPTION
             "Severity: Normal -- informational in nature. The state of a battery assembly has changed."
           --#TYPE      "StorageCell Event 09050005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602309

   sCellEventTrap-09-06 TRAP-TYPE  -- CAC Code: bf
        ENTERPRISE compaq
        VARIABLES  { scellNameDateTime,
                     scellSWComponent,
                     scellECode,
                     scellCAC,
                     scellEIP}
        DESCRIPTION
             "Severity: Undetermined -- more information needed to determine severity. A Volume has transitioned to the MISSING state."
           --#TYPE      "StorageCell Event 0906bf05"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602310

   sCellEventTrap-09-07 TRAP-TYPE  -- CAC Code: 00
        ENTERPRISE compaq
        VARIABLES  { scellNameDateTime,
                     scellSWComponent,
                     scellECode,
                     scellCAC,
                     scellEIP}
        DESCRIPTION
             "Severity: Normal -- informational in nature. A Fibre Channel port has transitioned to the NORMAL state."
           --#TYPE      "StorageCell Event 09070005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602311

   sCellEventTrap-09-08 TRAP-TYPE  -- CAC Code: b4
        ENTERPRISE compaq
        VARIABLES  { scellNameDateTime,
                     scellSWComponent,
                     scellECode,
                     scellCAC,
                     scellEIP}
        DESCRIPTION
             "Severity: Warning -- not failed but attention recommended or required. A Disk Group's occupancy alarm level threshold has been reached."
           --#TYPE      "StorageCell Event 0908b405"
           --#SUMMARY   "SCellName-TimeDate %s : SWCID %d : ECode: %d : CAC %d : EIP %d."
           --#ARGUMENTS {0,1,2,3,4,}
           --#SEVERITY  MINOR
           --#TIMEINDEX 136
           --#STATE     WARNING
        ::= 13602312

   sCellEventTrap-09-09 TRAP-TYPE  -- CAC Code: 00
        ENTERPRISE compaq
        VARIABLES  { scellNameDateTime,
                     scellSWComponent,
                     scellECode,
                     scellCAC,
                     scellEIP}
        DESCRIPTION
             "Severity: Normal -- informational in nature. The resource availability state of a Volume has transitioned to the SUFFICIENT state."
           --#TYPE      "StorageCell Event 09090005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602313

   sCellEventTrap-09-0c TRAP-TYPE  -- CAC Code: 00
        ENTERPRISE compaq
        VARIABLES  { scellNameDateTime,
                     scellSWComponent,
                     scellECode,
                     scellCAC,
                     scellEIP}
        DESCRIPTION
             "Severity: Normal -- informational in nature. A snapclone Logical Disk has completed the unsharing operation."
           --#TYPE      "StorageCell Event 090c0005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602316

   sCellEventTrap-09-0d TRAP-TYPE  -- CAC Code: 00
        ENTERPRISE compaq
        VARIABLES  { scellNameDateTime,
                     scellSWComponent,
                     scellECode,
                     scellCAC,
                     scellEIP}
        DESCRIPTION
             "Severity: Normal -- informational in nature. The state of the quorum disk flag of a Volume has changed."
           --#TYPE      "StorageCell Event 090d0005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602317

   sCellEventTrap-09-0e TRAP-TYPE  -- CAC Code: 36
        ENTERPRISE compaq
        VARIABLES  { scellNameDateTime,
                     scellSWComponent,
                     scellECode,
                     scellCAC,
                     scellEIP}
        DESCRIPTION
             "Severity: Critical -- failure or failure imminent. The temperature trip point for a temperature sensor located within a controller has been reached."
           --#TYPE      "StorageCell Event 090e3605"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602318

   sCellEventTrap-09-0f TRAP-TYPE  -- CAC Code: 2e
        ENTERPRISE compaq
        VARIABLES  { scellNameDateTime,
                     scellSWComponent,
                     scellECode,
                     scellCAC,
                     scellEIP}
        DESCRIPTION
             "Severity: Warning -- not failed but attention recommended or required. The temperature within a controller is approaching its trip point."
           --#TYPE      "StorageCell Event 090f2e05"
           --#SUMMARY   "SCellName-TimeDate %s : SWCID %d : ECode: %d : CAC %d : EIP %d."
           --#ARGUMENTS {0,1,2,3,4,}
           --#SEVERITY  MINOR
           --#TIMEINDEX 136
           --#STATE     WARNING
        ::= 13602319

   sCellEventTrap-09-11 TRAP-TYPE  -- CAC Code: 00
        ENTERPRISE compaq
        VARIABLES  { scellNameDateTime,
                     scellSWComponent,
                     scellECode,
                     scellCAC,
                     scellEIP}
        DESCRIPTION
             "Severity: Normal -- informational in nature. A controller's blower '1' is now present."
           --#TYPE      "StorageCell Event 09110005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602321

   sCellEventTrap-09-12 TRAP-TYPE  -- CAC Code: 24
        ENTERPRISE compaq
        VARIABLES  { scellNameDateTime,
                     scellSWComponent,
                     scellECode,
                     scellCAC,
                     scellEIP}
        DESCRIPTION
             "Severity: Critical -- failure or failure imminent. A controller's blower '1' is running slower than the lowest acceptable speed."
           --#TYPE      "StorageCell Event 09122405"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602322

   sCellEventTrap-09-13 TRAP-TYPE  -- CAC Code: 20
        ENTERPRISE compaq
        VARIABLES  { scellNameDateTime,
                     scellSWComponent,
                     scellECode,
                     scellCAC,
                     scellEIP}
        DESCRIPTION
             "Severity: Critical -- failure or failure imminent. A voltage sensor has reported a voltage that is out of range."
           --#TYPE      "StorageCell Event 09132005"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602323

   sCellEventTrap-09-14 TRAP-TYPE  -- CAC Code: bf
        ENTERPRISE compaq
        VARIABLES  { scellNameDateTime,
                     scellSWComponent,
                     scellECode,
                     scellCAC,
                     scellEIP}
        DESCRIPTION
             "Severity: Undetermined -- more information needed to determine severity. A Volume has transitioned to the FAILED state."
           --#TYPE      "StorageCell Event 0914bf05"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602324

   sCellEventTrap-09-15 TRAP-TYPE  -- CAC Code: b9
        ENTERPRISE compaq
        VARIABLES  { scellNameDateTime,
                     scellSWComponent,
                     scellECode,
                     scellCAC,
                     scellEIP}
        DESCRIPTION
             "Severity: Undetermined -- more information needed to determine severity. A controller has failed, as a result of the system becoming inoperative.  Related events have more information."
           --#TYPE      "StorageCell Event 0915b905"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602325

   sCellEventTrap-09-16 TRAP-TYPE  -- CAC Code: 00
        ENTERPRISE compaq
        VARIABLES  { scellNameDateTime,
                     scellSWComponent,
                     scellECode,
                     scellCAC,
                     scellEIP}
        DESCRIPTION
             "Severity: Normal -- informational in nature. The temperature within an controller has returned to its normal operating range."
           --#TYPE      "StorageCell Event 09160005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602326

   sCellEventTrap-09-17 TRAP-TYPE  -- CAC Code: 28
        ENTERPRISE compaq
        VARIABLES  { scellNameDateTime,
                     scellSWComponent,
                     scellECode,
                     scellCAC,
                     scellEIP}
        DESCRIPTION
             "Severity: Critical -- failure or failure imminent. A controller's battery assembly '1' has been removed."
           --#TYPE      "StorageCell Event 09172805"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602327

   sCellEventTrap-09-18 TRAP-TYPE  -- CAC Code: 00
        ENTERPRISE compaq
        VARIABLES  { scellNameDateTime,
                     scellSWComponent,
                     scellECode,
                     scellCAC,
                     scellEIP}
        DESCRIPTION
             "Severity: Normal -- informational in nature. A controller's battery assembly '1' is now in use."
           --#TYPE      "StorageCell Event 09180005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602328

   sCellEventTrap-09-19 TRAP-TYPE  -- CAC Code: 00
        ENTERPRISE compaq
        VARIABLES  { scellNameDateTime,
                     scellSWComponent,
                     scellECode,
                     scellCAC,
                     scellEIP}
        DESCRIPTION
             "Severity: Normal -- informational in nature. A voltage sensor has returned to a normal range."
           --#TYPE      "StorageCell Event 09190005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602329

   sCellEventTrap-09-1a TRAP-TYPE  -- CAC Code: 20
        ENTERPRISE compaq
        VARIABLES  { scellNameDateTime,
                     scellSWComponent,
                     scellECode,
                     scellCAC,
                     scellEIP}
        DESCRIPTION
             "Severity: Critical -- failure or failure imminent. The battery assembly voltage regulator located within a controller is offline."
           --#TYPE      "StorageCell Event 091a2005"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602330

   sCellEventTrap-09-1b TRAP-TYPE  -- CAC Code: 00
        ENTERPRISE compaq
        VARIABLES  { scellNameDateTime,
                     scellSWComponent,
                     scellECode,
                     scellCAC,
                     scellEIP}
        DESCRIPTION
             "Severity: Normal -- informational in nature. A Disk Group has transitioned to the NORMAL state."
           --#TYPE      "StorageCell Event 091b0005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602331

   sCellEventTrap-09-1c TRAP-TYPE  -- CAC Code: 00
        ENTERPRISE compaq
        VARIABLES  { scellNameDateTime,
                     scellSWComponent,
                     scellECode,
                     scellCAC,
                     scellEIP}
        DESCRIPTION
             "Severity: Normal -- informational in nature. The occupancy alarm level for a Disk Group has returned to the normal range."
           --#TYPE      "StorageCell Event 091c0005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602332

   sCellEventTrap-09-1d TRAP-TYPE  -- CAC Code: 22
        ENTERPRISE compaq
        VARIABLES  { scellNameDateTime,
                     scellSWComponent,
                     scellECode,
                     scellCAC,
                     scellEIP}
        DESCRIPTION
             "Severity: Critical -- failure or failure imminent. A controller's battery assembly '1' has malfunctioned."
           --#TYPE      "StorageCell Event 091d2205"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602333

   sCellEventTrap-09-1e TRAP-TYPE  -- CAC Code: 00
        ENTERPRISE compaq
        VARIABLES  { scellNameDateTime,
                     scellSWComponent,
                     scellECode,
                     scellCAC,
                     scellEIP}
        DESCRIPTION
             "Severity: Normal -- informational in nature. A controller's battery assembly '1' is now present."
           --#TYPE      "StorageCell Event 091e0005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602334

   sCellEventTrap-09-1f TRAP-TYPE  -- CAC Code: 29
        ENTERPRISE compaq
        VARIABLES  { scellNameDateTime,
                     scellSWComponent,
                     scellECode,
                     scellCAC,
                     scellEIP}
        DESCRIPTION
             "Severity: Critical -- failure or failure imminent. A controller's battery assembly '2' has been removed."
           --#TYPE      "StorageCell Event 091f2905"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602335

   sCellEventTrap-09-20 TRAP-TYPE  -- CAC Code: 00
        ENTERPRISE compaq
        VARIABLES  { scellNameDateTime,
                     scellSWComponent,
                     scellECode,
                     scellCAC,
                     scellEIP}
        DESCRIPTION
             "Severity: Normal -- informational in nature. A controller's battery assembly '2' is now present."
           --#TYPE      "StorageCell Event 09200005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602336

   sCellEventTrap-09-21 TRAP-TYPE  -- CAC Code: 00
        ENTERPRISE compaq
        VARIABLES  { scellNameDateTime,
                     scellSWComponent,
                     scellECode,
                     scellCAC,
                     scellEIP}
        DESCRIPTION
             "Severity: Normal -- informational in nature. A controller's battery assembly '2' is now functioning properly."
           --#TYPE      "StorageCell Event 09210005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602337

   sCellEventTrap-09-22 TRAP-TYPE  -- CAC Code: 23
        ENTERPRISE compaq
        VARIABLES  { scellNameDateTime,
                     scellSWComponent,
                     scellECode,
                     scellCAC,
                     scellEIP}
        DESCRIPTION
             "Severity: Critical -- failure or failure imminent. A controller's battery assembly has malfunctioned."
           --#TYPE      "StorageCell Event 09222305"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602338

   sCellEventTrap-09-23 TRAP-TYPE  -- CAC Code: 2b
        ENTERPRISE compaq
        VARIABLES  { scellNameDateTime,
                     scellSWComponent,
                     scellECode,
                     scellCAC,
                     scellEIP}
        DESCRIPTION
             "Severity: Critical -- failure or failure imminent. A controller's blower '2' has been removed."
           --#TYPE      "StorageCell Event 09232b05"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602339

   sCellEventTrap-09-24 TRAP-TYPE  -- CAC Code: 00
        ENTERPRISE compaq
        VARIABLES  { scellNameDateTime,
                     scellSWComponent,
                     scellECode,
                     scellCAC,
                     scellEIP}
        DESCRIPTION
             "Severity: Normal -- informational in nature. A controller's blower assembly '2' is now present."
           --#TYPE      "StorageCell Event 09240005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602340

   sCellEventTrap-09-25 TRAP-TYPE  -- CAC Code: 25
        ENTERPRISE compaq
        VARIABLES  { scellNameDateTime,
                     scellSWComponent,
                     scellECode,
                     scellCAC,
                     scellEIP}
        DESCRIPTION
             "Severity: Critical -- failure or failure imminent. A controller's blower assembly '2' is running slower than the lowest acceptable speed."
           --#TYPE      "StorageCell Event 09252505"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602341

   sCellEventTrap-09-26 TRAP-TYPE  -- CAC Code: 2c
        ENTERPRISE compaq
        VARIABLES  { scellNameDateTime,
                     scellSWComponent,
                     scellECode,
                     scellCAC,
                     scellEIP}
        DESCRIPTION
             "Severity: Critical -- failure or failure imminent. A controller's '1' blower/power supply assembly has been removed or AC power has been removed from the power supply."
           --#TYPE      "StorageCell Event 09262c05"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602342

   sCellEventTrap-09-27 TRAP-TYPE  -- CAC Code: 00
        ENTERPRISE compaq
        VARIABLES  { scellNameDateTime,
                     scellSWComponent,
                     scellECode,
                     scellCAC,
                     scellEIP}
        DESCRIPTION
             "Severity: Normal -- informational in nature. A controller's '1' blower/power supply assembly has been reinstalled or AC power has been restored to the power supply."
           --#TYPE      "StorageCell Event 09270005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602343

   sCellEventTrap-09-28 TRAP-TYPE  -- CAC Code: 2d
        ENTERPRISE compaq
        VARIABLES  { scellNameDateTime,
                     scellSWComponent,
                     scellECode,
                     scellCAC,
                     scellEIP}
        DESCRIPTION
             "Severity: Critical -- failure or failure imminent. A controller's '2' blower/power supply assembly has been removed or AC power has been removed from the power supply."
           --#TYPE      "StorageCell Event 09282d05"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602344

   sCellEventTrap-09-29 TRAP-TYPE  -- CAC Code: 00
        ENTERPRISE compaq
        VARIABLES  { scellNameDateTime,
                     scellSWComponent,
                     scellECode,
                     scellCAC,
                     scellEIP}
        DESCRIPTION
             "Severity: Normal -- informational in nature. A controller's '2' blower/power supply assembly has been reinstalled or AC power has been restored to the power supply."
           --#TYPE      "StorageCell Event 09290005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602345

   sCellEventTrap-09-2a TRAP-TYPE  -- CAC Code: 26
        ENTERPRISE compaq
        VARIABLES  { scellNameDateTime,
                     scellSWComponent,
                     scellECode,
                     scellCAC,
                     scellEIP}
        DESCRIPTION
             "Severity: Critical -- failure or failure imminent. A controller's '1' blower/power supply is running slower than the lowest acceptable speed."
           --#TYPE      "StorageCell Event 092a2605"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602346

   sCellEventTrap-09-2b TRAP-TYPE  -- CAC Code: 27
        ENTERPRISE compaq
        VARIABLES  { scellNameDateTime,
                     scellSWComponent,
                     scellECode,
                     scellCAC,
                     scellEIP}
        DESCRIPTION
             "Severity: Critical -- failure or failure imminent. A controller's '2' blower/power supply is running slower than the lowest acceptable speed."
           --#TYPE      "StorageCell Event 092b2705"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602347

   sCellEventTrap-09-2c TRAP-TYPE  -- CAC Code: 2f
        ENTERPRISE compaq
        VARIABLES  { scellNameDateTime,
                     scellSWComponent,
                     scellECode,
                     scellCAC,
                     scellEIP}
        DESCRIPTION
             "Severity: Warning -- not failed but attention recommended or required. A controller's battery assembly has transitioned to the 'Battery System Hold-up Time is zero hours' state."
           --#TYPE      "StorageCell Event 092c2f05"
           --#SUMMARY   "SCellName-TimeDate %s : SWCID %d : ECode: %d : CAC %d : EIP %d."
           --#ARGUMENTS {0,1,2,3,4,}
           --#SEVERITY  MINOR
           --#TIMEINDEX 136
           --#STATE     WARNING
        ::= 13602348

   sCellEventTrap-09-2d TRAP-TYPE  -- CAC Code: bf
        ENTERPRISE compaq
        VARIABLES  { scellNameDateTime,
                     scellSWComponent,
                     scellECode,
                     scellCAC,
                     scellEIP}
        DESCRIPTION
             "Severity: Undetermined -- more information needed to determine severity. The resource availability state of a Volume has transitioned to the INSUFFICIENT state."
           --#TYPE      "StorageCell Event 092dbf05"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602349

   sCellEventTrap-09-2e TRAP-TYPE  -- CAC Code: 00
        ENTERPRISE compaq
        VARIABLES  { scellNameDateTime,
                     scellSWComponent,
                     scellECode,
                     scellCAC,
                     scellEIP}
        DESCRIPTION
             "Severity: Normal -- informational in nature. A controller has rejected a login attempt."
           --#TYPE      "StorageCell Event 092e0005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602350

   sCellEventTrap-09-2f TRAP-TYPE  -- CAC Code: 00
        ENTERPRISE compaq
        VARIABLES  { scellNameDateTime,
                     scellSWComponent,
                     scellECode,
                     scellCAC,
                     scellEIP}
        DESCRIPTION
             "Severity: Normal -- informational in nature. A controller has processed a Storage System Management Interface command with the result of non-success return code."
           --#TYPE      "StorageCell Event 092f0005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602351

   sCellEventTrap-09-30 TRAP-TYPE  -- CAC Code: 00
        ENTERPRISE compaq
        VARIABLES  { scellNameDateTime,
                     scellSWComponent,
                     scellECode,
                     scellCAC,
                     scellEIP}
        DESCRIPTION
             "Severity: Normal -- informational in nature. A controller has updated the physical disk drive map for a loop pair."
           --#TYPE      "StorageCell Event 09300005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602352

   sCellEventTrap-09-31 TRAP-TYPE  -- CAC Code: 42
        ENTERPRISE compaq
        VARIABLES  { scellNameDateTime,
                     scellSWComponent,
                     scellECode,
                     scellCAC,
                     scellEIP}
        DESCRIPTION
             "Severity: Critical -- failure or failure imminent. A physical disk drive has transitioned to the DEGRADED state."
           --#TYPE      "StorageCell Event 09314205"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602353

   sCellEventTrap-09-32 TRAP-TYPE  -- CAC Code: 40
        ENTERPRISE compaq
        VARIABLES  { scellNameDateTime,
                     scellSWComponent,
                     scellECode,
                     scellCAC,
                     scellEIP}
        DESCRIPTION
             "Severity: Critical -- failure or failure imminent. A physical disk drive has transitioned to the FAILED state."
           --#TYPE      "StorageCell Event 09324005"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602354

   sCellEventTrap-09-35 TRAP-TYPE  -- CAC Code: 00
        ENTERPRISE compaq
        VARIABLES  { scellNameDateTime,
                     scellSWComponent,
                     scellECode,
                     scellCAC,
                     scellEIP}
        DESCRIPTION
             "Severity: Normal -- informational in nature. A Disk Group was created."
           --#TYPE      "StorageCell Event 0935000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602357

   sCellEventTrap-09-36 TRAP-TYPE  -- CAC Code: 00
        ENTERPRISE compaq
        VARIABLES  { scellNameDateTime,
                     scellSWComponent,
                     scellECode,
                     scellCAC,
                     scellEIP}
        DESCRIPTION
             "Severity: Normal -- informational in nature. A physical disk drive has appeared."
           --#TYPE      "StorageCell Event 0936000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602358

   sCellEventTrap-09-37 TRAP-TYPE  -- CAC Code: 00
        ENTERPRISE compaq
        VARIABLES  { scellNameDateTime,
                     scellSWComponent,
                     scellECode,
                     scellCAC,
                     scellEIP}
        DESCRIPTION
             "Severity: Normal -- informational in nature. A Presented Unit was created."
           --#TYPE      "StorageCell Event 0937000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602359

   sCellEventTrap-09-38 TRAP-TYPE  -- CAC Code: 00
        ENTERPRISE compaq
        VARIABLES  { scellNameDateTime,
                     scellSWComponent,
                     scellECode,
                     scellCAC,
                     scellEIP}
        DESCRIPTION
             "Severity: Normal -- informational in nature. A Storage System Host Path was created."
           --#TYPE      "StorageCell Event 0938000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602360

   sCellEventTrap-09-39 TRAP-TYPE  -- CAC Code: 00
        ENTERPRISE compaq
        VARIABLES  { scellNameDateTime,
                     scellSWComponent,
                     scellECode,
                     scellCAC,
                     scellEIP}
        DESCRIPTION
             "Severity: Normal -- informational in nature. A Storage System Virtual Disk was created."
           --#TYPE      "StorageCell Event 0939000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602361

   sCellEventTrap-09-3a TRAP-TYPE  -- CAC Code: 00
        ENTERPRISE compaq
        VARIABLES  { scellNameDateTime,
                     scellSWComponent,
                     scellECode,
                     scellCAC,
                     scellEIP}
        DESCRIPTION
             "Severity: Normal -- informational in nature. A Volume was created."
           --#TYPE      "StorageCell Event 093a000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602362

   sCellEventTrap-09-3d TRAP-TYPE  -- CAC Code: 00
        ENTERPRISE compaq
        VARIABLES  { scellNameDateTime,
                     scellSWComponent,
                     scellECode,
                     scellCAC,
                     scellEIP}
        DESCRIPTION
             "Severity: Normal -- informational in nature. A Disk Group was deleted."
           --#TYPE      "StorageCell Event 093d000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602365

   sCellEventTrap-09-3e TRAP-TYPE  -- CAC Code: 42
        ENTERPRISE compaq
        VARIABLES  { scellNameDateTime,
                     scellSWComponent,
                     scellECode,
                     scellCAC,
                     scellEIP}
        DESCRIPTION
             "Severity: Critical -- failure or failure imminent. A physical disk drive has disappeared."
           --#TYPE      "StorageCell Event 093e420e"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602366

   sCellEventTrap-09-3f TRAP-TYPE  -- CAC Code: 00
        ENTERPRISE compaq
        VARIABLES  { scellNameDateTime,
                     scellSWComponent,
                     scellECode,
                     scellCAC,
                     scellEIP}
        DESCRIPTION
             "Severity: Normal -- informational in nature. A Presented Unit was deleted."
           --#TYPE      "StorageCell Event 093f000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602367

   sCellEventTrap-09-40 TRAP-TYPE  -- CAC Code: 00
        ENTERPRISE compaq
        VARIABLES  { scellNameDateTime,
                     scellSWComponent,
                     scellECode,
                     scellCAC,
                     scellEIP}
        DESCRIPTION
             "Severity: Normal -- informational in nature. A Storage System Host Path was deleted."
           --#TYPE      "StorageCell Event 0940000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602368

   sCellEventTrap-09-41 TRAP-TYPE  -- CAC Code: 00
        ENTERPRISE compaq
        VARIABLES  { scellNameDateTime,
                     scellSWComponent,
                     scellECode,
                     scellCAC,
                     scellEIP}
        DESCRIPTION
             "Severity: Normal -- informational in nature. A Storage System Virtual Disk was deleted."
           --#TYPE      "StorageCell Event 0941000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602369

   sCellEventTrap-09-43 TRAP-TYPE  -- CAC Code: 00
        ENTERPRISE compaq
        VARIABLES  { scellNameDateTime,
                     scellSWComponent,
                     scellECode,
                     scellCAC,
                     scellEIP}
        DESCRIPTION
             "Severity: Normal -- informational in nature. A controller has joined the Storage System."
           --#TYPE      "StorageCell Event 0943000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602371

   sCellEventTrap-09-44 TRAP-TYPE  -- CAC Code: ba
        ENTERPRISE compaq
        VARIABLES  { scellNameDateTime,
                     scellSWComponent,
                     scellECode,
                     scellCAC,
                     scellEIP}
        DESCRIPTION
             "Severity: Undetermined -- more information needed to determine severity. A controller has left the Storage System."
           --#TYPE      "StorageCell Event 0944ba0e"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602372

   sCellEventTrap-09-45 TRAP-TYPE  -- CAC Code: 00
        ENTERPRISE compaq
        VARIABLES  { scellNameDateTime,
                     scellSWComponent,
                     scellECode,
                     scellCAC,
                     scellEIP}
        DESCRIPTION
             "Severity: Normal -- informational in nature. The Storage System has been deleted by a controller."
           --#TYPE      "StorageCell Event 0945000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602373

   sCellEventTrap-09-46 TRAP-TYPE  -- CAC Code: 00
        ENTERPRISE compaq
        VARIABLES  { scellNameDateTime,
                     scellSWComponent,
                     scellECode,
                     scellCAC,
                     scellEIP}
        DESCRIPTION
             "Severity: Normal -- informational in nature. A Data Replication Group was created."
           --#TYPE      "StorageCell Event 0946000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602374

   sCellEventTrap-09-47 TRAP-TYPE  -- CAC Code: 00
        ENTERPRISE compaq
        VARIABLES  { scellNameDateTime,
                     scellSWComponent,
                     scellECode,
                     scellCAC,
                     scellEIP}
        DESCRIPTION
             "Severity: Normal -- informational in nature. A Data Replication Group was deleted."
           --#TYPE      "StorageCell Event 0947000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602375

   sCellEventTrap-09-48 TRAP-TYPE  -- CAC Code: 00
        ENTERPRISE compaq
        VARIABLES  { scellNameDateTime,
                     scellSWComponent,
                     scellECode,
                     scellCAC,
                     scellEIP}
        DESCRIPTION
             "Severity: Normal -- informational in nature. A Snapshot Storage System Virtual Disk was created."
           --#TYPE      "StorageCell Event 0948000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602376

   sCellEventTrap-09-49 TRAP-TYPE  -- CAC Code: 00
        ENTERPRISE compaq
        VARIABLES  { scellNameDateTime,
                     scellSWComponent,
                     scellECode,
                     scellCAC,
                     scellEIP}
        DESCRIPTION
             "Severity: Normal -- informational in nature. A Clone Storage System Virtual Disk was created."
           --#TYPE      "StorageCell Event 0949000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602377

   sCellEventTrap-09-4a TRAP-TYPE  -- CAC Code: 00
        ENTERPRISE compaq
        VARIABLES  { scellNameDateTime,
                     scellSWComponent,
                     scellECode,
                     scellCAC,
                     scellEIP}
        DESCRIPTION
             "Severity: Normal -- informational in nature. Destination Data Replication Group not deleted due to inoperative members."
           --#TYPE      "StorageCell Event 094a000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602378

   sCellEventTrap-09-4b TRAP-TYPE  -- CAC Code: 00
        ENTERPRISE compaq
        VARIABLES  { scellNameDateTime,
                     scellSWComponent,
                     scellECode,
                     scellCAC,
                     scellEIP}
        DESCRIPTION
             "Severity: Normal -- informational in nature. A Volume was removed from a LDAD."
           --#TYPE      "StorageCell Event 094b000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602379

   sCellEventTrap-09-4c TRAP-TYPE  -- CAC Code: 00
        ENTERPRISE compaq
        VARIABLES  { scellNameDateTime,
                     scellSWComponent,
                     scellECode,
                     scellCAC,
                     scellEIP}
        DESCRIPTION
             "Severity: Normal -- informational in nature. A new Remote Node has been discovered."
           --#TYPE      "StorageCell Event 094c000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602380

   sCellEventTrap-09-4d TRAP-TYPE  -- CAC Code: 00
        ENTERPRISE compaq
        VARIABLES  { scellNameDateTime,
                     scellSWComponent,
                     scellECode,
                     scellCAC,
                     scellEIP}
        DESCRIPTION
             "Severity: Normal -- informational in nature. The Remote Node object has been discarded."
           --#TYPE      "StorageCell Event 094d000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602381

   sCellEventTrap-09-4e TRAP-TYPE  -- CAC Code: 00
        ENTERPRISE compaq
        VARIABLES  { scellNameDateTime,
                     scellSWComponent,
                     scellECode,
                     scellCAC,
                     scellEIP}
        DESCRIPTION
             "Severity: Normal -- informational in nature. The Remote Node Storage System UUID has changed."
           --#TYPE      "StorageCell Event 094e000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602382

   sCellEventTrap-09-4f TRAP-TYPE  -- CAC Code: 00
        ENTERPRISE compaq
        VARIABLES  { scellNameDateTime,
                     scellSWComponent,
                     scellECode,
                     scellCAC,
                     scellEIP}
        DESCRIPTION
             "Severity: Normal -- informational in nature. An Enclosure Appeared."
           --#TYPE      "StorageCell Event 094f000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602383

   sCellEventTrap-09-50 TRAP-TYPE  -- CAC Code: 00
        ENTERPRISE compaq
        VARIABLES  { scellNameDateTime,
                     scellSWComponent,
                     scellECode,
                     scellCAC,
                     scellEIP}
        DESCRIPTION
             "Severity: Normal -- informational in nature. An Enclosure Disappeared."
           --#TYPE      "StorageCell Event 0950000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602384

   sCellEventTrap-09-51 TRAP-TYPE  -- CAC Code: 00
        ENTERPRISE compaq
        VARIABLES  { scellNameDateTime,
                     scellSWComponent,
                     scellECode,
                     scellCAC,
                     scellEIP}
        DESCRIPTION
             "Severity: Normal -- informational in nature. An IO Module Appeared."
           --#TYPE      "StorageCell Event 0951000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602385

   sCellEventTrap-09-52 TRAP-TYPE  -- CAC Code: 00
        ENTERPRISE compaq
        VARIABLES  { scellNameDateTime,
                     scellSWComponent,
                     scellECode,
                     scellCAC,
                     scellEIP}
        DESCRIPTION
             "Severity: Normal -- informational in nature. An IO Module Disappeared."
           --#TYPE      "StorageCell Event 0952000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602386

   sCellEventTrap-09-65 TRAP-TYPE  -- CAC Code: 00
        ENTERPRISE compaq
        VARIABLES  { scellNameDateTime,
                     scellSWComponent,
                     scellECode,
                     scellCAC,
                     scellEIP}
        DESCRIPTION
             "Severity: Normal -- informational in nature. A host operating system mode has changed."
           --#TYPE      "StorageCell Event 0965000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602405

   sCellEventTrap-09-66 TRAP-TYPE  -- CAC Code: 00
        ENTERPRISE compaq
        VARIABLES  { scellNameDateTime,
                     scellSWComponent,
                     scellECode,
                     scellCAC,
                     scellEIP}
        DESCRIPTION
             "Severity: Normal -- informational in nature. Time was set on a Storage System."
           --#TYPE      "StorageCell Event 0966000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602406

   sCellEventTrap-09-67 TRAP-TYPE  -- CAC Code: 00
        ENTERPRISE compaq
        VARIABLES  { scellNameDateTime,
                     scellSWComponent,
                     scellECode,
                     scellCAC,
                     scellEIP}
        DESCRIPTION
             "Severity: Normal -- informational in nature. The LUN of a Presented Unit has changed."
           --#TYPE      "StorageCell Event 0967000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602407

   sCellEventTrap-09-68 TRAP-TYPE  -- CAC Code: 00
        ENTERPRISE compaq
        VARIABLES  { scellNameDateTime,
                     scellSWComponent,
                     scellECode,
                     scellCAC,
                     scellEIP}
        DESCRIPTION
             "Severity: Normal -- informational in nature. The device addition policy of a Storage System has changed."
           --#TYPE      "StorageCell Event 0968000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602408

   sCellEventTrap-09-69 TRAP-TYPE  -- CAC Code: 00
        ENTERPRISE compaq
        VARIABLES  { scellNameDateTime,
                     scellSWComponent,
                     scellECode,
                     scellCAC,
                     scellEIP}
        DESCRIPTION
             "Severity: Normal -- informational in nature. The quiescent state of a Storage System Virtual Disk has changed."
           --#TYPE      "StorageCell Event 0969000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602409

   sCellEventTrap-09-6a TRAP-TYPE  -- CAC Code: 00
        ENTERPRISE compaq
        VARIABLES  { scellNameDateTime,
                     scellSWComponent,
                     scellECode,
                     scellCAC,
                     scellEIP}
        DESCRIPTION
             "Severity: Normal -- informational in nature. The enabled/disabled state of a Storage System Virtual Disk has changed."
           --#TYPE      "StorageCell Event 096a000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602410

   sCellEventTrap-09-6b TRAP-TYPE  -- CAC Code: 00
        ENTERPRISE compaq
        VARIABLES  { scellNameDateTime,
                     scellSWComponent,
                     scellECode,
                     scellCAC,
                     scellEIP}
        DESCRIPTION
             "Severity: Normal -- informational in nature. The cache policy of a Storage System Virtual Disk has changed."
           --#TYPE      "StorageCell Event 096b000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602411

   sCellEventTrap-09-6c TRAP-TYPE  -- CAC Code: 00
        ENTERPRISE compaq
        VARIABLES  { scellNameDateTime,
                     scellSWComponent,
                     scellECode,
                     scellCAC,
                     scellEIP}
        DESCRIPTION
             "Severity: Normal -- informational in nature. The usage state of a Volume changed."
           --#TYPE      "StorageCell Event 096c000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602412

   sCellEventTrap-09-6d TRAP-TYPE  -- CAC Code: 00
        ENTERPRISE compaq
        VARIABLES  { scellNameDateTime,
                     scellSWComponent,
                     scellECode,
                     scellCAC,
                     scellEIP}
        DESCRIPTION
             "Severity: Normal -- informational in nature. The disk failure protection level of a Disk Group has changed."
           --#TYPE      "StorageCell Event 096d000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602413

   sCellEventTrap-09-6e TRAP-TYPE  -- CAC Code: 00
        ENTERPRISE compaq
        VARIABLES  { scellNameDateTime,
                     scellSWComponent,
                     scellECode,
                     scellCAC,
                     scellEIP}
        DESCRIPTION
             "Severity: Normal -- informational in nature. The write protected state of a Storage System Virtual Disk has changed."
           --#TYPE      "StorageCell Event 096e000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602414

   sCellEventTrap-09-70 TRAP-TYPE  -- CAC Code: 46
        ENTERPRISE compaq
        VARIABLES  { scellNameDateTime,
                     scellSWComponent,
                     scellECode,
                     scellCAC,
                     scellEIP}
        DESCRIPTION
             "Severity: Warning -- not failed but attention recommended or required. A controller has declared a port on a physical disk drive unusable and will not log in to the device on that port due to numerous transport failures."
           --#TYPE      "StorageCell Event 0970460f"
           --#SUMMARY   "SCellName-TimeDate %s : SWCID %d : ECode: %d : CAC %d : EIP %d."
           --#ARGUMENTS {0,1,2,3,4,}
           --#SEVERITY  MINOR
           --#TIMEINDEX 136
           --#STATE     WARNING
        ::= 13602416

   sCellEventTrap-09-71 TRAP-TYPE  -- CAC Code: 00
        ENTERPRISE compaq
        VARIABLES  { scellNameDateTime,
                     scellSWComponent,
                     scellECode,
                     scellCAC,
                     scellEIP}
        DESCRIPTION
             "Severity: Normal -- informational in nature. A controller has received a request to shutdown."
           --#TYPE      "StorageCell Event 0971000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602417

   sCellEventTrap-09-72 TRAP-TYPE  -- CAC Code: 00
        ENTERPRISE compaq
        VARIABLES  { scellNameDateTime,
                     scellSWComponent,
                     scellECode,
                     scellCAC,
                     scellEIP}
        DESCRIPTION
             "Severity: Normal -- informational in nature. A controller has completed its shutdown preparations."
           --#TYPE      "StorageCell Event 0972000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602418

   sCellEventTrap-09-73 TRAP-TYPE  -- CAC Code: 00
        ENTERPRISE compaq
        VARIABLES  { scellNameDateTime,
                     scellSWComponent,
                     scellECode,
                     scellCAC,
                     scellEIP}
        DESCRIPTION
             "Severity: Normal -- informational in nature. The failsafe state of a Data Replication Group has changed."
           --#TYPE      "StorageCell Event 0973000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602419

   sCellEventTrap-09-74 TRAP-TYPE  -- CAC Code: 00
        ENTERPRISE compaq
        VARIABLES  { scellNameDateTime,
                     scellSWComponent,
                     scellECode,
                     scellCAC,
                     scellEIP}
        DESCRIPTION
             "Severity: Normal -- informational in nature. The mode of a Data Replication Group has changed."
           --#TYPE      "StorageCell Event 0974000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602420

   sCellEventTrap-09-75 TRAP-TYPE  -- CAC Code: 00
        ENTERPRISE compaq
        VARIABLES  { scellNameDateTime,
                     scellSWComponent,
                     scellECode,
                     scellCAC,
                     scellEIP}
        DESCRIPTION
             "Severity: Normal -- informational in nature. The synchronous/asynchronous operational state of a Data Replication Group has changed."
           --#TYPE      "StorageCell Event 0975000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602421

   sCellEventTrap-09-76 TRAP-TYPE  -- CAC Code: 00
        ENTERPRISE compaq
        VARIABLES  { scellNameDateTime,
                     scellSWComponent,
                     scellECode,
                     scellCAC,
                     scellEIP}
        DESCRIPTION
             "Severity: Normal -- informational in nature. The read only attribute of a Data Replication Group has changed."
           --#TYPE      "StorageCell Event 0976000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602422

   sCellEventTrap-09-77 TRAP-TYPE  -- CAC Code: 00
        ENTERPRISE compaq
        VARIABLES  { scellNameDateTime,
                     scellSWComponent,
                     scellECode,
                     scellCAC,
                     scellEIP}
        DESCRIPTION
             "Severity: Normal -- informational in nature. A Data Replication Group failover has occurred."
           --#TYPE      "StorageCell Event 0977000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602423

   sCellEventTrap-09-78 TRAP-TYPE  -- CAC Code: 00
        ENTERPRISE compaq
        VARIABLES  { scellNameDateTime,
                     scellSWComponent,
                     scellECode,
                     scellCAC,
                     scellEIP}
        DESCRIPTION
             "Severity: Normal -- informational in nature. A Data Replication Group has been suspended or resumed."
           --#TYPE      "StorageCell Event 0978000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602424

   sCellEventTrap-09-79 TRAP-TYPE  -- CAC Code: 00
        ENTERPRISE compaq
        VARIABLES  { scellNameDateTime,
                     scellSWComponent,
                     scellECode,
                     scellCAC,
                     scellEIP}
        DESCRIPTION
             "Severity: Normal -- informational in nature. A Storage System Virtual Disk was added to a Data Replication Group."
           --#TYPE      "StorageCell Event 0979000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602425

   sCellEventTrap-09-7a TRAP-TYPE  -- CAC Code: 00
        ENTERPRISE compaq
        VARIABLES  { scellNameDateTime,
                     scellSWComponent,
                     scellECode,
                     scellCAC,
                     scellEIP}
        DESCRIPTION
             "Severity: Normal -- informational in nature. A Storage System Virtual Disk was removed from a Data Replication Group."
           --#TYPE      "StorageCell Event 097a000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602426

   sCellEventTrap-09-7b TRAP-TYPE  -- CAC Code: 00
        ENTERPRISE compaq
        VARIABLES  { scellNameDateTime,
                     scellSWComponent,
                     scellECode,
                     scellCAC,
                     scellEIP}
        DESCRIPTION
             "Severity: Normal -- informational in nature. The auto suspend attribute of a Data Replication Group has changed."
           --#TYPE      "StorageCell Event 097b000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602427

   sCellEventTrap-09-7c TRAP-TYPE  -- CAC Code: 00
        ENTERPRISE compaq
        VARIABLES  { scellNameDateTime,
                     scellSWComponent,
                     scellECode,
                     scellCAC,
                     scellEIP}
        DESCRIPTION
             "Severity: Normal -- informational in nature. The destination presentation attribute of a Data Replication Group has changed."
           --#TYPE      "StorageCell Event 097c000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602428

   sCellEventTrap-09-7d TRAP-TYPE  -- CAC Code: 00
        ENTERPRISE compaq
        VARIABLES  { scellNameDateTime,
                     scellSWComponent,
                     scellECode,
                     scellCAC,
                     scellEIP}
        DESCRIPTION
             "Severity: Normal -- informational in nature. The flags of a physical disk drive have changed because of a maintenance mode change."
           --#TYPE      "StorageCell Event 097d000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602429

   sCellEventTrap-09-7e TRAP-TYPE  -- CAC Code: 00
        ENTERPRISE compaq
        VARIABLES  { scellNameDateTime,
                     scellSWComponent,
                     scellECode,
                     scellCAC,
                     scellEIP}
        DESCRIPTION
             "Severity: Normal -- informational in nature. The suspend on full copy attribute of a Data Replication Group has changed."
           --#TYPE      "StorageCell Event 097e000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602430

   sCellEventTrap-09-7f TRAP-TYPE  -- CAC Code: 00
        ENTERPRISE compaq
        VARIABLES  { scellNameDateTime,
                     scellSWComponent,
                     scellECode,
                     scellCAC,
                     scellEIP}
        DESCRIPTION
             "Severity: Normal -- informational in nature. A Data Replication Group has been suspended due to link down."
           --#TYPE      "StorageCell Event 097f000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602431

   sCellEventTrap-09-80 TRAP-TYPE  -- CAC Code: 00
        ENTERPRISE compaq
        VARIABLES  { scellNameDateTime,
                     scellSWComponent,
                     scellECode,
                     scellCAC,
                     scellEIP}
        DESCRIPTION
             "Severity: Normal -- informational in nature. A Data Replication Group has been suspended due to site failover."
           --#TYPE      "StorageCell Event 0980000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602432

   sCellEventTrap-09-81 TRAP-TYPE  -- CAC Code: 00
        ENTERPRISE compaq
        VARIABLES  { scellNameDateTime,
                     scellSWComponent,
                     scellECode,
                     scellCAC,
                     scellEIP}
        DESCRIPTION
             "Severity: Normal -- informational in nature. A Data Replication Group has been suspended due to suspend on full copy."
           --#TYPE      "StorageCell Event 0981000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602433

   sCellEventTrap-09-82 TRAP-TYPE  -- CAC Code: 00
        ENTERPRISE compaq
        VARIABLES  { scellNameDateTime,
                     scellSWComponent,
                     scellECode,
                     scellCAC,
                     scellEIP}
        DESCRIPTION
             "Severity: Normal -- informational in nature. The failsafe on link-down/power-up attribute of a Data Replication Group has changed."
           --#TYPE      "StorageCell Event 0982000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602434

   sCellEventTrap-09-83 TRAP-TYPE  -- CAC Code: 00
        ENTERPRISE compaq
        VARIABLES  { scellNameDateTime,
                     scellSWComponent,
                     scellECode,
                     scellCAC,
                     scellEIP}
        DESCRIPTION
             "Severity: Normal -- informational in nature. A Data Replication Group has been suspended due to instance restore on destination site."
           --#TYPE      "StorageCell Event 0983000f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602435

   sCellEventTrap-09-c9 TRAP-TYPE  -- CAC Code: 51
        ENTERPRISE compaq
        VARIABLES  { scellNameDateTime,
                     scellSWComponent,
                     scellECode,
                     scellCAC,
                     scellEIP}
        DESCRIPTION
             "Severity: Undetermined -- more information needed to determine severity. A Disk Group has transitioned to an INOPERATIVE state."
           --#TYPE      "StorageCell Event 09c95105"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602505

   sCellEventTrap-09-ca TRAP-TYPE  -- CAC Code: 51
        ENTERPRISE compaq
        VARIABLES  { scellNameDateTime,
                     scellSWComponent,
                     scellECode,
                     scellCAC,
                     scellEIP}
        DESCRIPTION
             "Severity: Undetermined -- more information needed to determine severity. A Storage System Virtual Disk has transitioned to the FAILED state."
           --#TYPE      "StorageCell Event 09ca5105"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602506

   sCellEventTrap-09-cb TRAP-TYPE  -- CAC Code: 50
        ENTERPRISE compaq
        VARIABLES  { scellNameDateTime,
                     scellSWComponent,
                     scellECode,
                     scellCAC,
                     scellEIP}
        DESCRIPTION
             "Severity: Critical -- failure or failure imminent. A Storage System Virtual Disk has transitioned to the SNAPSHOT OVERCOMMIT state."
           --#TYPE      "StorageCell Event 09cb5005"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602507

   sCellEventTrap-09-cc TRAP-TYPE  -- CAC Code: 51
        ENTERPRISE compaq
        VARIABLES  { scellNameDateTime,
                     scellSWComponent,
                     scellECode,
                     scellCAC,
                     scellEIP}
        DESCRIPTION
             "Severity: Undetermined -- more information needed to determine severity. A Storage System Virtual Disk has transitioned to the DEVICE DATA LOST state."
           --#TYPE      "StorageCell Event 09cc5105"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602508

   sCellEventTrap-09-cd TRAP-TYPE  -- CAC Code: c3
        ENTERPRISE compaq
        VARIABLES  { scellNameDateTime,
                     scellSWComponent,
                     scellECode,
                     scellCAC,
                     scellEIP}
        DESCRIPTION
             "Severity: Undetermined -- more information needed to determine severity. A Fibre Channel port has transitioned to the FAILED state."
           --#TYPE      "StorageCell Event 09cdc305"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602509

   sCellEventTrap-09-ce TRAP-TYPE  -- CAC Code: 00
        ENTERPRISE compaq
        VARIABLES  { scellNameDateTime,
                     scellSWComponent,
                     scellECode,
                     scellCAC,
                     scellEIP}
        DESCRIPTION
             "Severity: Normal -- informational in nature. A Disk Group has transitioned to an INOPERATIVE MARKED state."
           --#TYPE      "StorageCell Event 09ce0005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602510

   sCellEventTrap-09-d0 TRAP-TYPE  -- CAC Code: 00
        ENTERPRISE compaq
        VARIABLES  { scellNameDateTime,
                     scellSWComponent,
                     scellECode,
                     scellCAC,
                     scellEIP}
        DESCRIPTION
             "Severity: Normal -- informational in nature. A controller no longer needs attention."
           --#TYPE      "StorageCell Event 09d00005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602512

   sCellEventTrap-09-d1 TRAP-TYPE  -- CAC Code: b9
        ENTERPRISE compaq
        VARIABLES  { scellNameDateTime,
                     scellSWComponent,
                     scellECode,
                     scellCAC,
                     scellEIP}
        DESCRIPTION
             "Severity: Undetermined -- more information needed to determine severity. A controller needs attention."
           --#TYPE      "StorageCell Event 09d1b905"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602513

   sCellEventTrap-09-d2 TRAP-TYPE  -- CAC Code: 2a
        ENTERPRISE compaq
        VARIABLES  { scellNameDateTime,
                     scellSWComponent,
                     scellECode,
                     scellCAC,
                     scellEIP}
        DESCRIPTION
             "Severity: Critical -- failure or failure imminent. A controller's blower '1' has been removed."
           --#TYPE      "StorageCell Event 09d22a05"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602514

   sCellEventTrap-09-d3 TRAP-TYPE  -- CAC Code: 51
        ENTERPRISE compaq
        VARIABLES  { scellNameDateTime,
                     scellSWComponent,
                     scellECode,
                     scellCAC,
                     scellEIP}
        DESCRIPTION
             "Severity: Undetermined -- more information needed to determine severity. At least one Storage System Virtual Disk associated with a Data Replication Group has transitioned to the INOPERATIVE state. The remaining Storage System Virtual Disks associated with this Data Replication Group have been forced INOPERATIVE."
           --#TYPE      "StorageCell Event 09d35105"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602515

   sCellEventTrap-09-d4 TRAP-TYPE  -- CAC Code: 00
        ENTERPRISE compaq
        VARIABLES  { scellNameDateTime,
                     scellSWComponent,
                     scellECode,
                     scellCAC,
                     scellEIP}
        DESCRIPTION
             "Severity: Normal -- informational in nature. All the Virtual Disks associated with a Data Replication Group have transitioned to the OPERATIVE state."
           --#TYPE      "StorageCell Event 09d40005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602516

   sCellEventTrap-09-d5 TRAP-TYPE  -- CAC Code: 00
        ENTERPRISE compaq
        VARIABLES  { scellNameDateTime,
                     scellSWComponent,
                     scellECode,
                     scellCAC,
                     scellEIP}
        DESCRIPTION
             "Severity: Normal -- informational in nature. The state of a physical disk drive has transitioned to the Single Port on Fibre state."
           --#TYPE      "StorageCell Event 09d50005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602517

   sCellEventTrap-09-d6 TRAP-TYPE  -- CAC Code: 37
        ENTERPRISE compaq
        VARIABLES  { scellNameDateTime,
                     scellSWComponent,
                     scellECode,
                     scellCAC,
                     scellEIP}
        DESCRIPTION
             "Severity: Warning -- not failed but attention recommended or required. A controller has been powered off because the temperature sensors do not agree and the system temperature can not be accurately determined."
           --#TYPE      "StorageCell Event 09d63705"
           --#SUMMARY   "SCellName-TimeDate %s : SWCID %d : ECode: %d : CAC %d : EIP %d."
           --#ARGUMENTS {0,1,2,3,4,}
           --#SEVERITY  MINOR
           --#TIMEINDEX 136
           --#STATE     WARNING
        ::= 13602518

   sCellEventTrap-09-d7 TRAP-TYPE  -- CAC Code: 37
        ENTERPRISE compaq
        VARIABLES  { scellNameDateTime,
                     scellSWComponent,
                     scellECode,
                     scellCAC,
                     scellEIP}
        DESCRIPTION
             "Severity: Warning -- not failed but attention recommended or required. A controller has been powered off because the temperature sensors can not be accessed and the system temperature can not be accurately determined."
           --#TYPE      "StorageCell Event 09d73705"
           --#SUMMARY   "SCellName-TimeDate %s : SWCID %d : ECode: %d : CAC %d : EIP %d."
           --#ARGUMENTS {0,1,2,3,4,}
           --#SEVERITY  MINOR
           --#TIMEINDEX 136
           --#STATE     WARNING
        ::= 13602519

   sCellEventTrap-09-d8 TRAP-TYPE  -- CAC Code: b6
        ENTERPRISE compaq
        VARIABLES  { scellNameDateTime,
                     scellSWComponent,
                     scellECode,
                     scellCAC,
                     scellEIP}
        DESCRIPTION
             "Severity: Undetermined -- more information needed to determine severity. A Redundant Storage Set has two members on the same Fibre Channel device enclosure causing a Disk Group to lose its Single Point of Failure Robust Configuration."
           --#TYPE      "StorageCell Event 09d8b605"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602520

   sCellEventTrap-09-d9 TRAP-TYPE  -- CAC Code: 00
        ENTERPRISE compaq
        VARIABLES  { scellNameDateTime,
                     scellSWComponent,
                     scellECode,
                     scellCAC,
                     scellEIP}
        DESCRIPTION
             "Severity: Normal -- informational in nature. A Disk Group has attained a Single Point of Failure Robust Configuration."
           --#TYPE      "StorageCell Event 09d90005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602521

   sCellEventTrap-09-da TRAP-TYPE  -- CAC Code: 00
        ENTERPRISE compaq
        VARIABLES  { scellNameDateTime,
                     scellSWComponent,
                     scellECode,
                     scellCAC,
                     scellEIP}
        DESCRIPTION
             "Severity: Normal -- informational in nature. A controller's blower '1' is running at normal speed."
           --#TYPE      "StorageCell Event 09da0005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602522

   sCellEventTrap-09-db TRAP-TYPE  -- CAC Code: 00
        ENTERPRISE compaq
        VARIABLES  { scellNameDateTime,
                     scellSWComponent,
                     scellECode,
                     scellCAC,
                     scellEIP}
        DESCRIPTION
             "Severity: Normal -- informational in nature. A controller's blower '2' is running at normal speed."
           --#TYPE      "StorageCell Event 09db0005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602523

   sCellEventTrap-09-dd TRAP-TYPE  -- CAC Code: 00
        ENTERPRISE compaq
        VARIABLES  { scellNameDateTime,
                     scellSWComponent,
                     scellECode,
                     scellCAC,
                     scellEIP}
        DESCRIPTION
             "Severity: Normal -- informational in nature. A controller receives a maintenance invoke call from the user"
           --#TYPE      "StorageCell Event 09dd0005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602525

   sCellEventTrap-09-de TRAP-TYPE  -- CAC Code: 52
        ENTERPRISE compaq
        VARIABLES  { scellNameDateTime,
                     scellSWComponent,
                     scellECode,
                     scellCAC,
                     scellEIP}
        DESCRIPTION
             "Severity: Critical -- failure or failure imminent. A Storage System Virtual Disk has transitioned to the INVALIDATED state."
           --#TYPE      "StorageCell Event 09de5205"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602526

   sCellEventTrap-09-e3 TRAP-TYPE  -- CAC Code: 00
        ENTERPRISE compaq
        VARIABLES  { scellNameDateTime,
                     scellSWComponent,
                     scellECode,
                     scellCAC,
                     scellEIP}
        DESCRIPTION
             "Severity: Normal -- informational in nature. The state of a Storage System Virtual Disk has changed."
           --#TYPE      "StorageCell Event 09e30005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602531

   sCellEventTrap-09-e4 TRAP-TYPE  -- CAC Code: 51
        ENTERPRISE compaq
        VARIABLES  { scellNameDateTime,
                     scellSWComponent,
                     scellECode,
                     scellCAC,
                     scellEIP}
        DESCRIPTION
             "Severity: Undetermined -- more information needed to determine severity. The data availability state of a Storage System Virtual Disk has transitioned to the DATA LOST state."
           --#TYPE      "StorageCell Event 09e45105"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602532

   sCellEventTrap-09-e5 TRAP-TYPE  -- CAC Code: 00
        ENTERPRISE compaq
        VARIABLES  { scellNameDateTime,
                     scellSWComponent,
                     scellECode,
                     scellCAC,
                     scellEIP}
        DESCRIPTION
             "Severity: Normal -- informational in nature. The data availability state of a Storage System Virtual Disk has transitioned to the NORMAL state."
           --#TYPE      "StorageCell Event 09e50005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602533

   sCellEventTrap-09-e7 TRAP-TYPE  -- CAC Code: b4
        ENTERPRISE compaq
        VARIABLES  { scellNameDateTime,
                     scellSWComponent,
                     scellECode,
                     scellCAC,
                     scellEIP}
        DESCRIPTION
             "Severity: Warning -- not failed but attention recommended or required. A Disk Group's warning occupancy alarm level threshold has been reached."
           --#TYPE      "StorageCell Event 09e7b405"
           --#SUMMARY   "SCellName-TimeDate %s : SWCID %d : ECode: %d : CAC %d : EIP %d."
           --#ARGUMENTS {0,1,2,3,4,}
           --#SEVERITY  MINOR
           --#TIMEINDEX 136
           --#STATE     WARNING
        ::= 13602535

   sCellEventTrap-09-e8 TRAP-TYPE  -- CAC Code: 00
        ENTERPRISE compaq
        VARIABLES  { scellNameDateTime,
                     scellSWComponent,
                     scellECode,
                     scellCAC,
                     scellEIP}
        DESCRIPTION
             "Severity: Normal -- informational in nature. The warning occupancy alarm level for a Disk Group has returned to the normal range."
           --#TYPE      "StorageCell Event 09e80005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602536

   sCellEventTrap-09-e9 TRAP-TYPE  -- CAC Code: b7
        ENTERPRISE compaq
        VARIABLES  { scellNameDateTime,
                     scellSWComponent,
                     scellECode,
                     scellCAC,
                     scellEIP}
        DESCRIPTION
             "Severity: Warning -- not failed but attention recommended or required. A Storage System Virtual Disk's allocation alarm level threshold has been reached."
           --#TYPE      "StorageCell Event 09e9b70e"
           --#SUMMARY   "SCellName-TimeDate %s : SWCID %d : ECode: %d : CAC %d : EIP %d."
           --#ARGUMENTS {0,1,2,3,4,}
           --#SEVERITY  MINOR
           --#TIMEINDEX 136
           --#STATE     WARNING
        ::= 13602537

   sCellEventTrap-09-ea TRAP-TYPE  -- CAC Code: 00
        ENTERPRISE compaq
        VARIABLES  { scellNameDateTime,
                     scellSWComponent,
                     scellECode,
                     scellCAC,
                     scellEIP}
        DESCRIPTION
             "Severity: Normal -- informational in nature. The allocation alarm level for a Storage System Virtual Disk has returned to the normal range."
           --#TYPE      "StorageCell Event 09ea000e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602538

   sCellEventTrap-09-eb TRAP-TYPE  -- CAC Code: b9
        ENTERPRISE compaq
        VARIABLES  { scellNameDateTime,
                     scellSWComponent,
                     scellECode,
                     scellCAC,
                     scellEIP}
        DESCRIPTION
             "Severity: Undetermined -- more information needed to determine severity. An controller entered participation minimal state."
           --#TYPE      "StorageCell Event 09ebb905"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602539

   sCellEventTrap-09-ec TRAP-TYPE  -- CAC Code: b5
        ENTERPRISE compaq
        VARIABLES  { scellNameDateTime,
                     scellSWComponent,
                     scellECode,
                     scellCAC,
                     scellEIP}
        DESCRIPTION
             "Severity: Warning -- not failed but attention recommended or required. A Storage System Virtual Disk in Disk Group has transitioned to the THIN PROVISIONED OVERCOMMIT state."
           --#TYPE      "StorageCell Event 09ecb505"
           --#SUMMARY   "SCellName-TimeDate %s : SWCID %d : ECode: %d : CAC %d : EIP %d."
           --#ARGUMENTS {0,1,2,3,4,}
           --#SEVERITY  MINOR
           --#TIMEINDEX 136
           --#STATE     WARNING
        ::= 13602540

   sCellEventTrap-09-ed TRAP-TYPE  -- CAC Code: 00
        ENTERPRISE compaq
        VARIABLES  { scellNameDateTime,
                     scellSWComponent,
                     scellECode,
                     scellCAC,
                     scellEIP}
        DESCRIPTION
             "Severity: Normal -- informational in nature. The state of a physical disk drive has transitioned to the Exception Processing state."
           --#TYPE      "StorageCell Event 09ed0005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602541

   sCellEventTrap-09-ee TRAP-TYPE  -- CAC Code: 00
        ENTERPRISE compaq
        VARIABLES  { scellNameDateTime,
                     scellSWComponent,
                     scellECode,
                     scellCAC,
                     scellEIP}
        DESCRIPTION
             "Severity: Normal -- informational in nature. The Disk Group failure condition has been accepted."
           --#TYPE      "StorageCell Event 09ee0005"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602542

   sCellEventTrap-0b-00 TRAP-TYPE  -- CAC Code: 00
        ENTERPRISE compaq
        VARIABLES  { scellNameDateTime,
                     scellSWComponent,
                     scellECode,
                     scellCAC,
                     scellEIP}
        DESCRIPTION
             "Severity: Normal -- informational in nature. A controller has begun a resynchronization operation. This is a restart of the controller in a manner that has little or no impact on host system connectivity."
           --#TYPE      "StorageCell Event 0b000010"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602816

   sCellEventTrap-0b-06 TRAP-TYPE  -- CAC Code: 00
        ENTERPRISE compaq
        VARIABLES  { scellNameDateTime,
                     scellSWComponent,
                     scellECode,
                     scellCAC,
                     scellEIP}
        DESCRIPTION
             "Severity: Normal -- informational in nature. A controller has begun/finished a code load, code use, or code burn operation as indicated, in a manner that has little or no impact on host system connectivity."
           --#TYPE      "StorageCell Event 0b06001a"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602822

   sCellEventTrap-0b-09 TRAP-TYPE  -- CAC Code: 00
        ENTERPRISE compaq
        VARIABLES  { scellNameDateTime,
                     scellSWComponent,
                     scellECode,
                     scellCAC,
                     scellEIP}
        DESCRIPTION
             "Severity: Normal -- informational in nature. Process with work, eg. during CSM Hang and Unit Stalled Too Long."
           --#TYPE      "StorageCell Event 0b09001e"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602825

   sCellEventTrap-0b-0b TRAP-TYPE  -- CAC Code: 00
        ENTERPRISE compaq
        VARIABLES  { scellNameDateTime,
                     scellSWComponent,
                     scellECode,
                     scellCAC,
                     scellEIP}
        DESCRIPTION
             "Severity: Normal -- informational in nature. The preserving resync process has been initiated and is progressing."
           --#TYPE      "StorageCell Event 0b0b0024"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602827

   sCellEventTrap-0b-0c TRAP-TYPE  -- CAC Code: 00
        ENTERPRISE compaq
        VARIABLES  { scellNameDateTime,
                     scellSWComponent,
                     scellECode,
                     scellCAC,
                     scellEIP}
        DESCRIPTION
             "Severity: Normal -- informational in nature. A periodic system monitoring event has been generated to report current status."
           --#TYPE      "StorageCell Event 0b0c002f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13602828

   sCellEventTrap-0b-0d TRAP-TYPE  -- CAC Code: 0e
        ENTERPRISE compaq
        VARIABLES  { scellNameDateTime,
                     scellSWComponent,
                     scellECode,
                     scellCAC,
                     scellEIP}
        DESCRIPTION
             "Severity: Critical -- failure or failure imminent. The other controller has been shut down because of a previous failed codeload. A new codeload must be completed before restarting the other controller. Then the other controller can be manually restarted."
           --#TYPE      "StorageCell Event 0b0d0e31"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13602829

   sCellEventTrap-0c-03 TRAP-TYPE  -- CAC Code: 00
        ENTERPRISE compaq
        VARIABLES  { scellNameDateTime,
                     scellSWComponent,
                     scellECode,
                     scellCAC,
                     scellEIP}
        DESCRIPTION
             "Severity: Normal -- informational in nature. The specified Data Replication Group has transitioned to the Merging state, because the Data Replication Destination Storage System is now accessible or resumed."
           --#TYPE      "StorageCell Event 0c03000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603075

   sCellEventTrap-0c-04 TRAP-TYPE  -- CAC Code: 5f
        ENTERPRISE compaq
        VARIABLES  { scellNameDateTime,
                     scellSWComponent,
                     scellECode,
                     scellCAC,
                     scellEIP}
        DESCRIPTION
             "Severity: Critical -- failure or failure imminent. A Data Replication Group has entered the Failsafe Locked state because the Data Replication Destination Storage System is inaccessible."
           --#TYPE      "StorageCell Event 0c045f0c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603076

   sCellEventTrap-0c-05 TRAP-TYPE  -- CAC Code: 61
        ENTERPRISE compaq
        VARIABLES  { scellNameDateTime,
                     scellSWComponent,
                     scellECode,
                     scellCAC,
                     scellEIP}
        DESCRIPTION
             "Severity: Critical -- failure or failure imminent. A Data Replication Group has entered the Failsafe Locked state due to an inaccessible Destination Virtual Disk."
           --#TYPE      "StorageCell Event 0c05610c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603077

   sCellEventTrap-0c-06 TRAP-TYPE  -- CAC Code: 60
        ENTERPRISE compaq
        VARIABLES  { scellNameDateTime,
                     scellSWComponent,
                     scellECode,
                     scellCAC,
                     scellEIP}
        DESCRIPTION
             "Severity: Critical -- failure or failure imminent. A Full Copy was terminated prior to completion: An unrecoverable read error occurred on the specified Source Virtual Disk during the Full Copy."
           --#TYPE      "StorageCell Event 0c06600c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603078

   sCellEventTrap-0c-07 TRAP-TYPE  -- CAC Code: 5f
        ENTERPRISE compaq
        VARIABLES  { scellNameDateTime,
                     scellSWComponent,
                     scellECode,
                     scellCAC,
                     scellEIP}
        DESCRIPTION
             "Severity: Critical -- failure or failure imminent. A Full Copy terminated prior to completion: A remote copy error occurred due to an inaccessible alternate Storage System; The Full Copy will continue when the Data Replication Destination is restored."
           --#TYPE      "StorageCell Event 0c075f0c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603079

   sCellEventTrap-0c-08 TRAP-TYPE  -- CAC Code: 61
        ENTERPRISE compaq
        VARIABLES  { scellNameDateTime,
                     scellSWComponent,
                     scellECode,
                     scellCAC,
                     scellEIP}
        DESCRIPTION
             "Severity: Critical -- failure or failure imminent. A Full Copy terminated prior to completion: A remote copy error occurred due to an inaccessible Destination Virtual Disk; The Full Copy will continue when the Destination Virtual Disk is restored."
           --#TYPE      "StorageCell Event 0c08610c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603080

   sCellEventTrap-0c-09 TRAP-TYPE  -- CAC Code: 62
        ENTERPRISE compaq
        VARIABLES  { scellNameDateTime,
                     scellSWComponent,
                     scellECode,
                     scellCAC,
                     scellEIP}
        DESCRIPTION
             "Severity: Warning -- not failed but attention recommended or required. Data Replication Log for the specified Data Replication Group has reached its maximum capacity; The Data Replication Group has been marked for a Full Copy; Evaluate the need to manually resize the Data Replication Log for affected Data Replication Group."
           --#TYPE      "StorageCell Event 0c09620c"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603081

   sCellEventTrap-0c-0a TRAP-TYPE  -- CAC Code: 00
        ENTERPRISE compaq
        VARIABLES  { scellNameDateTime,
                     scellSWComponent,
                     scellECode,
                     scellCAC,
                     scellEIP}
        DESCRIPTION
             "Severity: Normal -- informational in nature. A Data Replication Log has been reset due to a Data Replication Group failover."
           --#TYPE      "StorageCell Event 0c0a000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603082

   sCellEventTrap-0c-0b TRAP-TYPE  -- CAC Code: 62
        ENTERPRISE compaq
        VARIABLES  { scellNameDateTime,
                     scellSWComponent,
                     scellECode,
                     scellCAC,
                     scellEIP}
        DESCRIPTION
             "Severity: Warning -- not failed but attention recommended or required. An unrecoverable read error occurred on the specified Data Replication Group Data Replication Log logical disk during a background read."
           --#TYPE      "StorageCell Event 0c0b620c"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603083

   sCellEventTrap-0c-0c TRAP-TYPE  -- CAC Code: 00
        ENTERPRISE compaq
        VARIABLES  { scellNameDateTime,
                     scellSWComponent,
                     scellECode,
                     scellCAC,
                     scellEIP}
        DESCRIPTION
             "Severity: Normal -- informational in nature. A Destination Data Replication Group has successfully completed a Merge."
           --#TYPE      "StorageCell Event 0c0c000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603084

   sCellEventTrap-0c-0f TRAP-TYPE  -- CAC Code: 00
        ENTERPRISE compaq
        VARIABLES  { scellNameDateTime,
                     scellSWComponent,
                     scellECode,
                     scellCAC,
                     scellEIP}
        DESCRIPTION
             "Severity: Normal -- informational in nature. A Data Replication Group is no longer in a Failsafe Locked state."
           --#TYPE      "StorageCell Event 0c0f000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603087

   sCellEventTrap-0c-10 TRAP-TYPE  -- CAC Code: 00
        ENTERPRISE compaq
        VARIABLES  { scellNameDateTime,
                     scellSWComponent,
                     scellECode,
                     scellCAC,
                     scellEIP}
        DESCRIPTION
             "Severity: Normal -- informational in nature. A Destination Data Replication Group has been marked for a Full Copy."
           --#TYPE      "StorageCell Event 0c10000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603088

   sCellEventTrap-0c-11 TRAP-TYPE  -- CAC Code: 00
        ENTERPRISE compaq
        VARIABLES  { scellNameDateTime,
                     scellSWComponent,
                     scellECode,
                     scellCAC,
                     scellEIP}
        DESCRIPTION
             "Severity: Normal -- informational in nature. This Data Replication Group is transitioning from a Data Replication Source role to a Data Replication Destination role."
           --#TYPE      "StorageCell Event 0c11000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603089

   sCellEventTrap-0c-12 TRAP-TYPE  -- CAC Code: 00
        ENTERPRISE compaq
        VARIABLES  { scellNameDateTime,
                     scellSWComponent,
                     scellECode,
                     scellCAC,
                     scellEIP}
        DESCRIPTION
             "Severity: Normal -- informational in nature. This Data Replication Group is transitioning from a Data Replication Destination role to a Data Replication Source role."
           --#TYPE      "StorageCell Event 0c12000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603090

   sCellEventTrap-0c-15 TRAP-TYPE  -- CAC Code: 5f
        ENTERPRISE compaq
        VARIABLES  { scellNameDateTime,
                     scellSWComponent,
                     scellECode,
                     scellCAC,
                     scellEIP}
        DESCRIPTION
             "Severity: Critical -- failure or failure imminent. The Data Replication Path between this Storage System and the Peer Storage System has closed, possibly due to a connection failure between the specified host port and the Peer Storage System."
           --#TYPE      "StorageCell Event 0c155f0c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603093

   sCellEventTrap-0c-16 TRAP-TYPE  -- CAC Code: 00
        ENTERPRISE compaq
        VARIABLES  { scellNameDateTime,
                     scellSWComponent,
                     scellECode,
                     scellCAC,
                     scellEIP}
        DESCRIPTION
             "Severity: Normal -- informational in nature. A controller has sent a time report message to this controller."
           --#TYPE      "StorageCell Event 0c160016"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603094

   sCellEventTrap-0c-17 TRAP-TYPE  -- CAC Code: 63
        ENTERPRISE compaq
        VARIABLES  { scellNameDateTime,
                     scellSWComponent,
                     scellECode,
                     scellCAC,
                     scellEIP}
        DESCRIPTION
             "Severity: Critical -- failure or failure imminent. The Data Replication Manager communications protocol version between the Data Replication Source Storage System and a Data Replication Destination Storage System is mismatched."
           --#TYPE      "StorageCell Event 0c17630c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603095

   sCellEventTrap-0c-18 TRAP-TYPE  -- CAC Code: 64
        ENTERPRISE compaq
        VARIABLES  { scellNameDateTime,
                     scellSWComponent,
                     scellECode,
                     scellCAC,
                     scellEIP}
        DESCRIPTION
             "Severity: Critical -- failure or failure imminent. Conditions on the Data Replication Destination Storage System are preventing acceptable replication throughput: Initiating temporary logging on the affected Data Replication Group that is failsafe mode disabled."
           --#TYPE      "StorageCell Event 0c18640c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603096

   sCellEventTrap-0c-19 TRAP-TYPE  -- CAC Code: 02
        ENTERPRISE compaq
        VARIABLES  { scellNameDateTime,
                     scellSWComponent,
                     scellECode,
                     scellCAC,
                     scellEIP}
        DESCRIPTION
             "Severity: Critical -- failure or failure imminent. Overlapping concurrent host writes to an Active/Active Peer Storage System violate a Data Replication Manager architectural requirement, resulting in a reparative resynchronization operation for the master Storage System and a Full Copy operation."
           --#TYPE      "StorageCell Event 0c19020c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603097

   sCellEventTrap-0c-1a TRAP-TYPE  -- CAC Code: 00
        ENTERPRISE compaq
        VARIABLES  { scellNameDateTime,
                     scellSWComponent,
                     scellECode,
                     scellCAC,
                     scellEIP}
        DESCRIPTION
             "Severity: Normal -- informational in nature. The specified Destination Virtual Disk has successfully completed a Full Copy."
           --#TYPE      "StorageCell Event 0c1a000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603098

   sCellEventTrap-0c-1b TRAP-TYPE  -- CAC Code: 5f
        ENTERPRISE compaq
        VARIABLES  { scellNameDateTime,
                     scellSWComponent,
                     scellECode,
                     scellCAC,
                     scellEIP}
        DESCRIPTION
             "Severity: Critical -- failure or failure imminent. A Data Replication Group has transitioned to the Logging state because the alternate Storage System is not accessible."
           --#TYPE      "StorageCell Event 0c1b5f0c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603099

   sCellEventTrap-0c-1c TRAP-TYPE  -- CAC Code: 61
        ENTERPRISE compaq
        VARIABLES  { scellNameDateTime,
                     scellSWComponent,
                     scellECode,
                     scellCAC,
                     scellEIP}
        DESCRIPTION
             "Severity: Critical -- failure or failure imminent. The specified Source Data Replication Group has transitioned to the (not merging) Logging state because a Destination Virtual Disk is not accessible."
           --#TYPE      "StorageCell Event 0c1c610c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603100

   sCellEventTrap-0c-1d TRAP-TYPE  -- CAC Code: 00
        ENTERPRISE compaq
        VARIABLES  { scellNameDateTime,
                     scellSWComponent,
                     scellECode,
                     scellCAC,
                     scellEIP}
        DESCRIPTION
             "Severity: Normal -- informational in nature. Inconsistency was found in the group log: A Full Copy of the affected Data Replication Group will be initiated."
           --#TYPE      "StorageCell Event 0c1d000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603101

   sCellEventTrap-0c-1e TRAP-TYPE  -- CAC Code: 5f
        ENTERPRISE compaq
        VARIABLES  { scellNameDateTime,
                     scellSWComponent,
                     scellECode,
                     scellCAC,
                     scellEIP}
        DESCRIPTION
             "Severity: Critical -- failure or failure imminent. The members of the specified Source Data Replication Group have not been presented to the host because the remote Storage System is not accessible and the failsafe on link-down/power-up state is enabled: Suspend Source Data Replication Group to override this behavior, which will present the members."
           --#TYPE      "StorageCell Event 0c1e5f0c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603102

   sCellEventTrap-0c-1f TRAP-TYPE  -- CAC Code: 00
        ENTERPRISE compaq
        VARIABLES  { scellNameDateTime,
                     scellSWComponent,
                     scellECode,
                     scellCAC,
                     scellEIP}
        DESCRIPTION
             "Severity: Normal -- informational in nature. The members of the specified Source Data Replication Group have been presented to the host because the remote Storage System is now accessible or source group is now suspended."
           --#TYPE      "StorageCell Event 0c1f000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603103

   sCellEventTrap-0c-20 TRAP-TYPE  -- CAC Code: 65
        ENTERPRISE compaq
        VARIABLES  { scellNameDateTime,
                     scellSWComponent,
                     scellECode,
                     scellCAC,
                     scellEIP}
        DESCRIPTION
             "Severity: Critical -- failure or failure imminent. Conditions on the Data Replication Destination Storage System are preventing replication processing: The specified Source Data Replication Group will remain in the Logging or the Failsafe Locked state until corrective action is performed."
           --#TYPE      "StorageCell Event 0c20650c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603104

   sCellEventTrap-0c-21 TRAP-TYPE  -- CAC Code: 66
        ENTERPRISE compaq
        VARIABLES  { scellNameDateTime,
                     scellSWComponent,
                     scellECode,
                     scellCAC,
                     scellEIP}
        DESCRIPTION
             "Severity: Critical -- failure or failure imminent. A replication operation on the Data Replication Source Storage System or Data Replication Destination Storage System has stalled which will prevent replication processing for the specified Data Replication Group until corrective action is performed."
           --#TYPE      "StorageCell Event 0c21660c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603105

   sCellEventTrap-0c-22 TRAP-TYPE  -- CAC Code: 00
        ENTERPRISE compaq
        VARIABLES  { scellNameDateTime,
                     scellSWComponent,
                     scellECode,
                     scellCAC,
                     scellEIP}
        DESCRIPTION
             "Severity: Normal -- informational in nature. A Data Replication Path between this Storage System and the Peer Storage System has been opened."
           --#TYPE      "StorageCell Event 0c22000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603106

   sCellEventTrap-0c-23 TRAP-TYPE  -- CAC Code: 67
        ENTERPRISE compaq
        VARIABLES  { scellNameDateTime,
                     scellSWComponent,
                     scellECode,
                     scellCAC,
                     scellEIP}
        DESCRIPTION
             "Severity: Warning -- not failed but attention recommended or required. Conditions on the inter site link are preventing acceptable replication throughput: Initiating temporary logging on the affected Data Replication Group that is failsafe mode disabled."
           --#TYPE      "StorageCell Event 0c23670c"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603107

   sCellEventTrap-0c-24 TRAP-TYPE  -- CAC Code: 00
        ENTERPRISE compaq
        VARIABLES  { scellNameDateTime,
                     scellSWComponent,
                     scellECode,
                     scellCAC,
                     scellEIP}
        DESCRIPTION
             "Severity: Normal -- informational in nature. The specified Source Data Replication Group has transitioned to the (not merging) Logging state because a Destination Virtual Disk is momentarily inaccessible."
           --#TYPE      "StorageCell Event 0c24000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603108

   sCellEventTrap-0c-25 TRAP-TYPE  -- CAC Code: 00
        ENTERPRISE compaq
        VARIABLES  { scellNameDateTime,
                     scellSWComponent,
                     scellECode,
                     scellCAC,
                     scellEIP}
        DESCRIPTION
             "Severity: Normal -- informational in nature. A Full Copy terminated prior to completion: A remote copy error occurred due to a momentarily inaccessible Destination Virtual Disk; The Full Copy will continue when the Destination Virtual Disk is restored."
           --#TYPE      "StorageCell Event 0c25000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603109

   sCellEventTrap-0c-26 TRAP-TYPE  -- CAC Code: 00
        ENTERPRISE compaq
        VARIABLES  { scellNameDateTime,
                     scellSWComponent,
                     scellECode,
                     scellCAC,
                     scellEIP}
        DESCRIPTION
             "Severity: Normal -- informational in nature. The Data Replication Path between this Storage System and the Peer Storage System has been opened due to simultaneous requests from each Storage System"
           --#TYPE      "StorageCell Event 0c26000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603110

   sCellEventTrap-0c-27 TRAP-TYPE  -- CAC Code: 00
        ENTERPRISE compaq
        VARIABLES  { scellNameDateTime,
                     scellSWComponent,
                     scellECode,
                     scellCAC,
                     scellEIP}
        DESCRIPTION
             "Severity: Normal -- informational in nature. The Data Replication Path between this Storage System and the Peer Storage System has been opened by the Peer Storage System."
           --#TYPE      "StorageCell Event 0c27000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603111

   sCellEventTrap-0c-28 TRAP-TYPE  -- CAC Code: 5f
        ENTERPRISE compaq
        VARIABLES  { scellNameDateTime,
                     scellSWComponent,
                     scellECode,
                     scellCAC,
                     scellEIP}
        DESCRIPTION
             "Severity: Critical -- failure or failure imminent. A Data Replication Path to the Peer Storage System is not currently available."
           --#TYPE      "StorageCell Event 0c285f0c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603112

   sCellEventTrap-0c-29 TRAP-TYPE  -- CAC Code: 00
        ENTERPRISE compaq
        VARIABLES  { scellNameDateTime,
                     scellSWComponent,
                     scellECode,
                     scellCAC,
                     scellEIP}
        DESCRIPTION
             "Severity: Normal -- informational in nature. The Data Replication Path between this Storage System and the Peer Storage System has closed in order to force Data Replication Manager traffic to the controller's Preferred Port."
           --#TYPE      "StorageCell Event 0c29000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603113

   sCellEventTrap-0c-2a TRAP-TYPE  -- CAC Code: 00
        ENTERPRISE compaq
        VARIABLES  { scellNameDateTime,
                     scellSWComponent,
                     scellECode,
                     scellCAC,
                     scellEIP}
        DESCRIPTION
             "Severity: Normal -- informational in nature. A Data Replication Path to a Peer Storage System has been found."
           --#TYPE      "StorageCell Event 0c2a000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603114

   sCellEventTrap-0c-2b TRAP-TYPE  -- CAC Code: 60
        ENTERPRISE compaq
        VARIABLES  { scellNameDateTime,
                     scellSWComponent,
                     scellECode,
                     scellCAC,
                     scellEIP}
        DESCRIPTION
             "Severity: Critical -- failure or failure imminent. A Merge was terminated prior to completion: An unrecoverable read error occurred on the log unit of the specified Data Replication Group during the Merge."
           --#TYPE      "StorageCell Event 0c2b600c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603115

   sCellEventTrap-0c-2c TRAP-TYPE  -- CAC Code: 66
        ENTERPRISE compaq
        VARIABLES  { scellNameDateTime,
                     scellSWComponent,
                     scellECode,
                     scellCAC,
                     scellEIP}
        DESCRIPTION
             "Severity: Critical -- failure or failure imminent. A replication operation on the Data Replication Source Storage System or Data Replication Destination Storage System has stalled which will prevent replication processing for the specified Data Replication Group until corrective action is performed."
           --#TYPE      "StorageCell Event 0c2c660c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603116

   sCellEventTrap-0c-2d TRAP-TYPE  -- CAC Code: 00
        ENTERPRISE compaq
        VARIABLES  { scellNameDateTime,
                     scellSWComponent,
                     scellECode,
                     scellCAC,
                     scellEIP}
        DESCRIPTION
             "Severity: Normal -- informational in nature. The Peer Storage System port name that was incorrectly associated with a host has been deleted from the specified client object."
           --#TYPE      "StorageCell Event 0c2d000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603117

   sCellEventTrap-0c-2e TRAP-TYPE  -- CAC Code: 68
        ENTERPRISE compaq
        VARIABLES  { scellNameDateTime,
                     scellSWComponent,
                     scellECode,
                     scellCAC,
                     scellEIP}
        DESCRIPTION
             "Severity: Warning -- not failed but attention recommended or required. Insufficient resources exist to discover additional remote nodes."
           --#TYPE      "StorageCell Event 0c2e680c"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603118

   sCellEventTrap-0c-2f TRAP-TYPE  -- CAC Code: 00
        ENTERPRISE compaq
        VARIABLES  { scellNameDateTime,
                     scellSWComponent,
                     scellECode,
                     scellCAC,
                     scellEIP}
        DESCRIPTION
             "Severity: Normal -- informational in nature. Sufficient resources now exist to allow discovery of additional remote nodes."
           --#TYPE      "StorageCell Event 0c2f000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603119

   sCellEventTrap-0c-30 TRAP-TYPE  -- CAC Code: 00
        ENTERPRISE compaq
        VARIABLES  { scellNameDateTime,
                     scellSWComponent,
                     scellECode,
                     scellCAC,
                     scellEIP}
        DESCRIPTION
             "Severity: Normal -- informational in nature. A Data Replication Log has been invalidated."
           --#TYPE      "StorageCell Event 0c30000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603120

   sCellEventTrap-0c-31 TRAP-TYPE  -- CAC Code: 00
        ENTERPRISE compaq
        VARIABLES  { scellNameDateTime,
                     scellSWComponent,
                     scellECode,
                     scellCAC,
                     scellEIP}
        DESCRIPTION
             "Severity: Normal -- informational in nature. A stalled Full Copy has been restarted."
           --#TYPE      "StorageCell Event 0c31000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603121

   sCellEventTrap-0c-32 TRAP-TYPE  -- CAC Code: 5f
        ENTERPRISE compaq
        VARIABLES  { scellNameDateTime,
                     scellSWComponent,
                     scellECode,
                     scellCAC,
                     scellEIP}
        DESCRIPTION
             "Severity: Critical -- failure or failure imminent. The Data Replication Path between this Storage System and the Peer Storage System has closed, because the host port connection has failed."
           --#TYPE      "StorageCell Event 0c325f0c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603122

   sCellEventTrap-0c-33 TRAP-TYPE  -- CAC Code: 5f
        ENTERPRISE compaq
        VARIABLES  { scellNameDateTime,
                     scellSWComponent,
                     scellECode,
                     scellCAC,
                     scellEIP}
        DESCRIPTION
             "Severity: Critical -- failure or failure imminent. The Data Replication Path between this Storage System and the Peer Storage System has closed, because the link or the Storage System has become unresponsive."
           --#TYPE      "StorageCell Event 0c335f0c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603123

   sCellEventTrap-0c-34 TRAP-TYPE  -- CAC Code: 5f
        ENTERPRISE compaq
        VARIABLES  { scellNameDateTime,
                     scellSWComponent,
                     scellECode,
                     scellCAC,
                     scellEIP}
        DESCRIPTION
             "Severity: Critical -- failure or failure imminent. The Data Replication Path between this Storage System and the Peer Storage System has closed, due to slow response on the connection between the specified host port and the Peer Storage System."
           --#TYPE      "StorageCell Event 0c345f0c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603124

   sCellEventTrap-0c-35 TRAP-TYPE  -- CAC Code: 07
        ENTERPRISE compaq
        VARIABLES  { scellNameDateTime,
                     scellSWComponent,
                     scellECode,
                     scellCAC,
                     scellEIP}
        DESCRIPTION
             "Severity: Warning -- not failed but attention recommended or required. The Data Replication Path between this Storage System and the Peer Storage System has closed, because a Data Replication Group configuration change lock was not released in a timely manner."
           --#TYPE      "StorageCell Event 0c35070c"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603125

   sCellEventTrap-0c-36 TRAP-TYPE  -- CAC Code: 5f
        ENTERPRISE compaq
        VARIABLES  { scellNameDateTime,
                     scellSWComponent,
                     scellECode,
                     scellCAC,
                     scellEIP}
        DESCRIPTION
             "Severity: Critical -- failure or failure imminent. The Data Replication Path between this Storage System and the Peer Storage System has closed, due to thrashing of the connection between the specified host port and the Peer Storage System."
           --#TYPE      "StorageCell Event 0c365f0c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603126

   sCellEventTrap-0c-37 TRAP-TYPE  -- CAC Code: 5f
        ENTERPRISE compaq
        VARIABLES  { scellNameDateTime,
                     scellSWComponent,
                     scellECode,
                     scellCAC,
                     scellEIP}
        DESCRIPTION
             "Severity: Critical -- failure or failure imminent. The Data Replication Path between this Storage System and the Peer Storage System has closed, because the maximum ping retry count has been exceeded."
           --#TYPE      "StorageCell Event 0c375f0c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603127

   sCellEventTrap-0c-38 TRAP-TYPE  -- CAC Code: 63
        ENTERPRISE compaq
        VARIABLES  { scellNameDateTime,
                     scellSWComponent,
                     scellECode,
                     scellCAC,
                     scellEIP}
        DESCRIPTION
             "Severity: Critical -- failure or failure imminent. The Data Replication Path between this Storage System and the Peer Storage System has closed, because the Data Replication Path protocol version is not supported by the controller firmware."
           --#TYPE      "StorageCell Event 0c38630c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603128

   sCellEventTrap-0c-39 TRAP-TYPE  -- CAC Code: 00
        ENTERPRISE compaq
        VARIABLES  { scellNameDateTime,
                     scellSWComponent,
                     scellECode,
                     scellCAC,
                     scellEIP}
        DESCRIPTION
             "Severity: Normal -- informational in nature. The Data Replication Path between this Storage System and the Peer Storage System has closed, because the Data Replication Path is not being used."
           --#TYPE      "StorageCell Event 0c39000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603129

   sCellEventTrap-0c-3a TRAP-TYPE  -- CAC Code: 5f
        ENTERPRISE compaq
        VARIABLES  { scellNameDateTime,
                     scellSWComponent,
                     scellECode,
                     scellCAC,
                     scellEIP}
        DESCRIPTION
             "Severity: Critical -- failure or failure imminent. A Data Replication Path between this Storage System and the Peer Storage System could not be created, possibly due to a connection failure between the specified host port and the Peer Storage System."
           --#TYPE      "StorageCell Event 0c3a5f0c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603130

   sCellEventTrap-0c-3b TRAP-TYPE  -- CAC Code: 00
        ENTERPRISE compaq
        VARIABLES  { scellNameDateTime,
                     scellSWComponent,
                     scellECode,
                     scellCAC,
                     scellEIP}
        DESCRIPTION
             "Severity: Normal -- informational in nature. The Data Replication Path between this Storage System and the Peer Storage System has closed, because the Peer Storage System requested the creation of a new Data Replication Path."
           --#TYPE      "StorageCell Event 0c3b000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603131

   sCellEventTrap-0c-3c TRAP-TYPE  -- CAC Code: 00
        ENTERPRISE compaq
        VARIABLES  { scellNameDateTime,
                     scellSWComponent,
                     scellECode,
                     scellCAC,
                     scellEIP}
        DESCRIPTION
             "Severity: Normal -- informational in nature. The Data Replication Path between this Storage System and the Peer Storage System has closed because the Peer Storage System tried to open a Data Replication Path to a different host port."
           --#TYPE      "StorageCell Event 0c3c000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603132

   sCellEventTrap-0c-3d TRAP-TYPE  -- CAC Code: 5f
        ENTERPRISE compaq
        VARIABLES  { scellNameDateTime,
                     scellSWComponent,
                     scellECode,
                     scellCAC,
                     scellEIP}
        DESCRIPTION
             "Severity: Critical -- failure or failure imminent. The Data Replication Path between this Storage System and the Peer Storage System has closed because of a frame retransmit limit was reached."
           --#TYPE      "StorageCell Event 0c3d5f0c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603133

   sCellEventTrap-0c-3e TRAP-TYPE  -- CAC Code: 00
        ENTERPRISE compaq
        VARIABLES  { scellNameDateTime,
                     scellSWComponent,
                     scellECode,
                     scellCAC,
                     scellEIP}
        DESCRIPTION
             "Severity: Normal -- informational in nature. The Data Replication Path between this Storage System and the Peer Storage System was closed by the Peer Storage System."
           --#TYPE      "StorageCell Event 0c3e000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603134

   sCellEventTrap-0c-3f TRAP-TYPE  -- CAC Code: 00
        ENTERPRISE compaq
        VARIABLES  { scellNameDateTime,
                     scellSWComponent,
                     scellECode,
                     scellCAC,
                     scellEIP}
        DESCRIPTION
             "Severity: Normal -- informational in nature. The Data Replication Path between this Storage System and the Peer Storage System has closed because the NPortID of the remote port changed."
           --#TYPE      "StorageCell Event 0c3f000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603135

   sCellEventTrap-0c-40 TRAP-TYPE  -- CAC Code: 69
        ENTERPRISE compaq
        VARIABLES  { scellNameDateTime,
                     scellSWComponent,
                     scellECode,
                     scellCAC,
                     scellEIP}
        DESCRIPTION
             "Severity: Warning -- not failed but attention recommended or required. The Data Replication Path between this Storage System and the Peer Storage System has closed because an out of order frame sequence number was detected."
           --#TYPE      "StorageCell Event 0c40690c"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603136

   sCellEventTrap-0c-41 TRAP-TYPE  -- CAC Code: 00
        ENTERPRISE compaq
        VARIABLES  { scellNameDateTime,
                     scellSWComponent,
                     scellECode,
                     scellCAC,
                     scellEIP}
        DESCRIPTION
             "Severity: Normal -- informational in nature. The Data Replication Path between this Storage System and the Peer Storage System has closed to allow creation of a Data Replication Path that requires a lower protocol version."
           --#TYPE      "StorageCell Event 0c41000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603137

   sCellEventTrap-0c-42 TRAP-TYPE  -- CAC Code: 00
        ENTERPRISE compaq
        VARIABLES  { scellNameDateTime,
                     scellSWComponent,
                     scellECode,
                     scellCAC,
                     scellEIP}
        DESCRIPTION
             "Severity: Normal -- informational in nature. The Data Replication Path between this Storage System and the Peer Storage System has closed because Peer Storage System no longer exists."
           --#TYPE      "StorageCell Event 0c42000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603138

   sCellEventTrap-0c-43 TRAP-TYPE  -- CAC Code: 00
        ENTERPRISE compaq
        VARIABLES  { scellNameDateTime,
                     scellSWComponent,
                     scellECode,
                     scellCAC,
                     scellEIP}
        DESCRIPTION
             "Severity: Normal -- informational in nature. The Data Replication Path between this Storage System and the Peer Storage System has been closed by user request."
           --#TYPE      "StorageCell Event 0c43000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603139

   sCellEventTrap-0c-49 TRAP-TYPE  -- CAC Code: 00
        ENTERPRISE compaq
        VARIABLES  { scellNameDateTime,
                     scellSWComponent,
                     scellECode,
                     scellCAC,
                     scellEIP}
        DESCRIPTION
             "Severity: Normal -- informational in nature. The Data Replication Path between this Storage System and the Peer Storage System has closed because the corresponding connection data was deleted. This is typically due to a change in the fabric."
           --#TYPE      "StorageCell Event 0c49000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603145

   sCellEventTrap-0c-4a TRAP-TYPE  -- CAC Code: 00
        ENTERPRISE compaq
        VARIABLES  { scellNameDateTime,
                     scellSWComponent,
                     scellECode,
                     scellCAC,
                     scellEIP}
        DESCRIPTION
             "Severity: Normal -- informational in nature. A request to create a Data Replication Path was rejected because the Storage System is re-starting."
           --#TYPE      "StorageCell Event 0c4a000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603146

   sCellEventTrap-0c-4b TRAP-TYPE  -- CAC Code: 00
        ENTERPRISE compaq
        VARIABLES  { scellNameDateTime,
                     scellSWComponent,
                     scellECode,
                     scellCAC,
                     scellEIP}
        DESCRIPTION
             "Severity: Normal -- informational in nature. A request to create a Data Replication Path was rejected because the Storage System is not active."
           --#TYPE      "StorageCell Event 0c4b000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603147

   sCellEventTrap-0c-4c TRAP-TYPE  -- CAC Code: 00
        ENTERPRISE compaq
        VARIABLES  { scellNameDateTime,
                     scellSWComponent,
                     scellECode,
                     scellCAC,
                     scellEIP}
        DESCRIPTION
             "Severity: Normal -- informational in nature. A request to create a Data Replication Path was rejected because the firmware has not completed Data Replication Path discovery."
           --#TYPE      "StorageCell Event 0c4c000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603148

   sCellEventTrap-0c-4e TRAP-TYPE  -- CAC Code: 00
        ENTERPRISE compaq
        VARIABLES  { scellNameDateTime,
                     scellSWComponent,
                     scellECode,
                     scellCAC,
                     scellEIP}
        DESCRIPTION
             "Severity: Normal -- informational in nature. A request to create a Data Replication Path was rejected because the remote port is not associated with a Enterprise Virtual Array."
           --#TYPE      "StorageCell Event 0c4e000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603150

   sCellEventTrap-0c-4f TRAP-TYPE  -- CAC Code: 00
        ENTERPRISE compaq
        VARIABLES  { scellNameDateTime,
                     scellSWComponent,
                     scellECode,
                     scellCAC,
                     scellEIP}
        DESCRIPTION
             "Severity: Normal -- informational in nature. A request to create a Data Replication Path was rejected because the remote port world wide identifier is associated with a host system."
           --#TYPE      "StorageCell Event 0c4f000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603151

   sCellEventTrap-0c-50 TRAP-TYPE  -- CAC Code: 00
        ENTERPRISE compaq
        VARIABLES  { scellNameDateTime,
                     scellSWComponent,
                     scellECode,
                     scellCAC,
                     scellEIP}
        DESCRIPTION
             "Severity: Normal -- informational in nature. A request to create a Data Replication Path was rejected because the supplied UUID does not match the UUID for this Storage System."
           --#TYPE      "StorageCell Event 0c50000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603152

   sCellEventTrap-0c-51 TRAP-TYPE  -- CAC Code: 00
        ENTERPRISE compaq
        VARIABLES  { scellNameDateTime,
                     scellSWComponent,
                     scellECode,
                     scellCAC,
                     scellEIP}
        DESCRIPTION
             "Severity: Normal -- informational in nature. A request to create a Data Replication Path was rejected because the requested protocol version is not compatible with the existing Data Replication Path."
           --#TYPE      "StorageCell Event 0c51000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603153

   sCellEventTrap-0c-52 TRAP-TYPE  -- CAC Code: 00
        ENTERPRISE compaq
        VARIABLES  { scellNameDateTime,
                     scellSWComponent,
                     scellECode,
                     scellCAC,
                     scellEIP}
        DESCRIPTION
             "Severity: Normal -- informational in nature. A request to create a Data Replication Path was rejected because the requested port was disabled by the user."
           --#TYPE      "StorageCell Event 0c52000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603154

   sCellEventTrap-0c-53 TRAP-TYPE  -- CAC Code: 00
        ENTERPRISE compaq
        VARIABLES  { scellNameDateTime,
                     scellSWComponent,
                     scellECode,
                     scellCAC,
                     scellEIP}
        DESCRIPTION
             "Severity: Normal -- informational in nature. A request to create a Data Replication Path was rejected because the insufficient resources exist to create the Data Replication Path."
           --#TYPE      "StorageCell Event 0c53000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603155

   sCellEventTrap-0c-54 TRAP-TYPE  -- CAC Code: 00
        ENTERPRISE compaq
        VARIABLES  { scellNameDateTime,
                     scellSWComponent,
                     scellECode,
                     scellCAC,
                     scellEIP}
        DESCRIPTION
             "Severity: Normal -- informational in nature. A request to create a Data Replication Path was rejected to force the use of a lower protocol version on the Data Replication Path."
           --#TYPE      "StorageCell Event 0c54000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603156

   sCellEventTrap-0c-55 TRAP-TYPE  -- CAC Code: 00
        ENTERPRISE compaq
        VARIABLES  { scellNameDateTime,
                     scellSWComponent,
                     scellECode,
                     scellCAC,
                     scellEIP}
        DESCRIPTION
             "Severity: Normal -- informational in nature. A time synchronization message has been sent to a Alternate Site."
           --#TYPE      "StorageCell Event 0c550016"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603157

   sCellEventTrap-0c-56 TRAP-TYPE  -- CAC Code: 00
        ENTERPRISE compaq
        VARIABLES  { scellNameDateTime,
                     scellSWComponent,
                     scellECode,
                     scellCAC,
                     scellEIP}
        DESCRIPTION
             "Severity: Normal -- informational in nature. The DRM Forced Logging Timeout value has been changed."
           --#TYPE      "StorageCell Event 0c56000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603158

   sCellEventTrap-0c-57 TRAP-TYPE  -- CAC Code: 00
        ENTERPRISE compaq
        VARIABLES  { scellNameDateTime,
                     scellSWComponent,
                     scellECode,
                     scellCAC,
                     scellEIP}
        DESCRIPTION
             "Severity: Normal -- informational in nature. The DRM Forced Logging Timeout value has been reset to the default value."
           --#TYPE      "StorageCell Event 0c57000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603159

   sCellEventTrap-0c-58 TRAP-TYPE  -- CAC Code: 69
        ENTERPRISE compaq
        VARIABLES  { scellNameDateTime,
                     scellSWComponent,
                     scellECode,
                     scellCAC,
                     scellEIP}
        DESCRIPTION
             "Severity: Warning -- not failed but attention recommended or required. Excessive data exchange retry rate on the inter site link is preventing acceptable replication throughput: Reducing data exchange resources."
           --#TYPE      "StorageCell Event 0c58690c"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603160

   sCellEventTrap-0c-59 TRAP-TYPE  -- CAC Code: 69
        ENTERPRISE compaq
        VARIABLES  { scellNameDateTime,
                     scellSWComponent,
                     scellECode,
                     scellCAC,
                     scellEIP}
        DESCRIPTION
             "Severity: Warning -- not failed but attention recommended or required. Excessive out of order message rate on the inter site link is impacting replication throughput."
           --#TYPE      "StorageCell Event 0c59690c"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603161

   sCellEventTrap-0c-5a TRAP-TYPE  -- CAC Code: 67
        ENTERPRISE compaq
        VARIABLES  { scellNameDateTime,
                     scellSWComponent,
                     scellECode,
                     scellCAC,
                     scellEIP}
        DESCRIPTION
             "Severity: Warning -- not failed but attention recommended or required. Excessive PING response time on the inter site link is preventing acceptable replication throughput: Reducing data exchange resources."
           --#TYPE      "StorageCell Event 0c5a670c"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603162

   sCellEventTrap-0c-5b TRAP-TYPE  -- CAC Code: 67
        ENTERPRISE compaq
        VARIABLES  { scellNameDateTime,
                     scellSWComponent,
                     scellECode,
                     scellCAC,
                     scellEIP}
        DESCRIPTION
             "Severity: Warning -- not failed but attention recommended or required. Replication data exchange write resources on the inter site link have been reduced to the minimum allowed value."
           --#TYPE      "StorageCell Event 0c5b670c"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603163

   sCellEventTrap-0c-5c TRAP-TYPE  -- CAC Code: 67
        ENTERPRISE compaq
        VARIABLES  { scellNameDateTime,
                     scellSWComponent,
                     scellECode,
                     scellCAC,
                     scellEIP}
        DESCRIPTION
             "Severity: Warning -- not failed but attention recommended or required. Replication data exchange copy resources on the inter site link have been reduced to the minimum allowed value."
           --#TYPE      "StorageCell Event 0c5c670c"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603164

   sCellEventTrap-0c-5d TRAP-TYPE  -- CAC Code: 00
        ENTERPRISE compaq
        VARIABLES  { scellNameDateTime,
                     scellSWComponent,
                     scellECode,
                     scellCAC,
                     scellEIP}
        DESCRIPTION
             "Severity: Normal -- informational in nature. Quality of service on the inter site link has improved: Increasing data exchange resources to improve replication throughput."
           --#TYPE      "StorageCell Event 0c5d000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603165

   sCellEventTrap-0c-5e TRAP-TYPE  -- CAC Code: 00
        ENTERPRISE compaq
        VARIABLES  { scellNameDateTime,
                     scellSWComponent,
                     scellECode,
                     scellCAC,
                     scellEIP}
        DESCRIPTION
             "Severity: Normal -- informational in nature. A Data Replication Log Shrink is in progress."
           --#TYPE      "StorageCell Event 0c5e000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603166

   sCellEventTrap-0c-5f TRAP-TYPE  -- CAC Code: 00
        ENTERPRISE compaq
        VARIABLES  { scellNameDateTime,
                     scellSWComponent,
                     scellECode,
                     scellCAC,
                     scellEIP}
        DESCRIPTION
             "Severity: Normal -- informational in nature. A Data Replication Log Shrink has completed."
           --#TYPE      "StorageCell Event 0c5f000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603167

   sCellEventTrap-0c-60 TRAP-TYPE  -- CAC Code: 00
        ENTERPRISE compaq
        VARIABLES  { scellNameDateTime,
                     scellSWComponent,
                     scellECode,
                     scellCAC,
                     scellEIP}
        DESCRIPTION
             "Severity: Normal -- informational in nature. Excessive Vdisk response time at the Data Replication Destination has been detected: Reducing data exchange copy resources on the inter site link to limit replication throughput."
           --#TYPE      "StorageCell Event 0c60000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603168

   sCellEventTrap-0c-61 TRAP-TYPE  -- CAC Code: 00
        ENTERPRISE compaq
        VARIABLES  { scellNameDateTime,
                     scellSWComponent,
                     scellECode,
                     scellCAC,
                     scellEIP}
        DESCRIPTION
             "Severity: Normal -- informational in nature. The Data Replication Path between this Storage System and the Peer Storage System has closed to allow resynchronization with the Peer Storage System."
           --#TYPE      "StorageCell Event 0c61000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603169

   sCellEventTrap-0c-62 TRAP-TYPE  -- CAC Code: 00
        ENTERPRISE compaq
        VARIABLES  { scellNameDateTime,
                     scellSWComponent,
                     scellECode,
                     scellCAC,
                     scellEIP}
        DESCRIPTION
             "Severity: Normal -- informational in nature. The members of the specified Source Data Replication Group have been presented to the host because the failsafe on link-down/power-up protection condition has been encountered, and the failsafe link-down/power-up setting is disabled."
           --#TYPE      "StorageCell Event 0c62000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603170

   sCellEventTrap-0c-64 TRAP-TYPE  -- CAC Code: 00
        ENTERPRISE compaq
        VARIABLES  { scellNameDateTime,
                     scellSWComponent,
                     scellECode,
                     scellCAC,
                     scellEIP}
        DESCRIPTION
             "Severity: Normal -- informational in nature. The failsafe on link-down/power-up attribute for the Data Replication Group was not set on the Data Replication Destination, since the firmware version does not support the feature."
           --#TYPE      "StorageCell Event 0c64000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603172

   sCellEventTrap-0c-65 TRAP-TYPE  -- CAC Code: 00
        ENTERPRISE compaq
        VARIABLES  { scellNameDateTime,
                     scellSWComponent,
                     scellECode,
                     scellCAC,
                     scellEIP}
        DESCRIPTION
             "Severity: Normal -- informational in nature. The specified Data Replication Group Data Replication Log has hit the 50 percent full mark."
           --#TYPE      "StorageCell Event 0c65000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603173

   sCellEventTrap-0c-66 TRAP-TYPE  -- CAC Code: 00
        ENTERPRISE compaq
        VARIABLES  { scellNameDateTime,
                     scellSWComponent,
                     scellECode,
                     scellCAC,
                     scellEIP}
        DESCRIPTION
             "Severity: Normal -- informational in nature. The specified Data Replication Group Data Replication Log has hit the 75 percent full mark."
           --#TYPE      "StorageCell Event 0c66000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603174

   sCellEventTrap-0c-67 TRAP-TYPE  -- CAC Code: 00
        ENTERPRISE compaq
        VARIABLES  { scellNameDateTime,
                     scellSWComponent,
                     scellECode,
                     scellCAC,
                     scellEIP}
        DESCRIPTION
             "Severity: Normal -- informational in nature. The specified Data Replication Group Data Replication Log has hit the 90 percent full mark."
           --#TYPE      "StorageCell Event 0c67000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603175

   sCellEventTrap-0c-68 TRAP-TYPE  -- CAC Code: 00
        ENTERPRISE compaq
        VARIABLES  { scellNameDateTime,
                     scellSWComponent,
                     scellECode,
                     scellCAC,
                     scellEIP}
        DESCRIPTION
             "Severity: Normal -- informational in nature. The specified Data Replication Group Data Replication Log has hit the 95 percent full mark."
           --#TYPE      "StorageCell Event 0c68000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603176

   sCellEventTrap-0c-69 TRAP-TYPE  -- CAC Code: 00
        ENTERPRISE compaq
        VARIABLES  { scellNameDateTime,
                     scellSWComponent,
                     scellECode,
                     scellCAC,
                     scellEIP}
        DESCRIPTION
             "Severity: Normal -- informational in nature. The specified Data Replication Group Data Replication Log has hit the 99 percent full mark."
           --#TYPE      "StorageCell Event 0c69000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603177

   sCellEventTrap-0c-6f TRAP-TYPE  -- CAC Code: 00
        ENTERPRISE compaq
        VARIABLES  { scellNameDateTime,
                     scellSWComponent,
                     scellECode,
                     scellCAC,
                     scellEIP}
        DESCRIPTION
             "Severity: Normal -- informational in nature. Excessive Vdisk response time at the Data Replication Source has been detected: Reducing data exchange copy resources on the inter site link to limit replication throughput."
           --#TYPE      "StorageCell Event 0c6f000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603183

   sCellEventTrap-0c-70 TRAP-TYPE  -- CAC Code: 00
        ENTERPRISE compaq
        VARIABLES  { scellNameDateTime,
                     scellSWComponent,
                     scellECode,
                     scellCAC,
                     scellEIP}
        DESCRIPTION
             "Severity: Normal -- informational in nature. The specified Destination Virtual Disk has successfully completed a Fast Resync."
           --#TYPE      "StorageCell Event 0c70000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603184

   sCellEventTrap-0c-71 TRAP-TYPE  -- CAC Code: 00
        ENTERPRISE compaq
        VARIABLES  { scellNameDateTime,
                     scellSWComponent,
                     scellECode,
                     scellCAC,
                     scellEIP}
        DESCRIPTION
             "Severity: Normal -- informational in nature. Async group removal: the Source Virtual Disk member has been successfully removed from the Async group Data Replication Group."
           --#TYPE      "StorageCell Event 0c71000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603185

   sCellEventTrap-0c-72 TRAP-TYPE  -- CAC Code: 00
        ENTERPRISE compaq
        VARIABLES  { scellNameDateTime,
                     scellSWComponent,
                     scellECode,
                     scellCAC,
                     scellEIP}
        DESCRIPTION
             "Severity: Normal -- informational in nature. The removal of the Source Virtual Disk failed for the Data Replication Group."
           --#TYPE      "StorageCell Event 0c72000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603186

   sCellEventTrap-0c-73 TRAP-TYPE  -- CAC Code: 00
        ENTERPRISE compaq
        VARIABLES  { scellNameDateTime,
                     scellSWComponent,
                     scellECode,
                     scellCAC,
                     scellEIP}
        DESCRIPTION
             "Severity: Normal -- informational in nature. The removal of the Source Virtual Disk completed after a log full condition for a Data Replication Group. The destination member, if retained, may not have all the data."
           --#TYPE      "StorageCell Event 0c73000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603187

   sCellEventTrap-0c-74 TRAP-TYPE  -- CAC Code: 00
        ENTERPRISE compaq
        VARIABLES  { scellNameDateTime,
                     scellSWComponent,
                     scellECode,
                     scellCAC,
                     scellEIP}
        DESCRIPTION
             "Severity: Normal -- informational in nature. The Source Virtual Disk in group Data Replication Group has started Merge Sync."
           --#TYPE      "StorageCell Event 0c74000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603188

   sCellEventTrap-0c-75 TRAP-TYPE  -- CAC Code: 00
        ENTERPRISE compaq
        VARIABLES  { scellNameDateTime,
                     scellSWComponent,
                     scellECode,
                     scellCAC,
                     scellEIP}
        DESCRIPTION
             "Severity: Normal -- informational in nature. The Source Virtual Disk in group Data Replication Group has finished Merge Sync."
           --#TYPE      "StorageCell Event 0c75000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603189

   sCellEventTrap-0c-76 TRAP-TYPE  -- CAC Code: 00
        ENTERPRISE compaq
        VARIABLES  { scellNameDateTime,
                     scellSWComponent,
                     scellECode,
                     scellCAC,
                     scellEIP}
        DESCRIPTION
             "Severity: Normal -- informational in nature. The Data Replication Log of a newly created Data Replication Group has been assigned to a FATA Disk Group."
           --#TYPE      "StorageCell Event 0c76000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603190

   sCellEventTrap-0c-77 TRAP-TYPE  -- CAC Code: 00
        ENTERPRISE compaq
        VARIABLES  { scellNameDateTime,
                     scellSWComponent,
                     scellECode,
                     scellCAC,
                     scellEIP}
        DESCRIPTION
             "Severity: Normal -- informational in nature. This Data Replication Group is failing over during a copy operation."
           --#TYPE      "StorageCell Event 0c77000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603191

   sCellEventTrap-0c-78 TRAP-TYPE  -- CAC Code: 00
        ENTERPRISE compaq
        VARIABLES  { scellNameDateTime,
                     scellSWComponent,
                     scellECode,
                     scellCAC,
                     scellEIP}
        DESCRIPTION
             "Severity: Normal -- informational in nature. The Source Virtual Disk of a Data Replication Group completed shrinking."
           --#TYPE      "StorageCell Event 0c78000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603192

   sCellEventTrap-0c-79 TRAP-TYPE  -- CAC Code: 00
        ENTERPRISE compaq
        VARIABLES  { scellNameDateTime,
                     scellSWComponent,
                     scellECode,
                     scellCAC,
                     scellEIP}
        DESCRIPTION
             "Severity: Normal -- informational in nature. The Source Virtual Disk of a Data Replication Group has failed shrink."
           --#TYPE      "StorageCell Event 0c79000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603193

   sCellEventTrap-0c-7a TRAP-TYPE  -- CAC Code: 00
        ENTERPRISE compaq
        VARIABLES  { scellNameDateTime,
                     scellSWComponent,
                     scellECode,
                     scellCAC,
                     scellEIP}
        DESCRIPTION
             "Severity: Normal -- informational in nature. The Source Virtual Disk of a Data Replication Group will shrink immediately due to a log full condition."
           --#TYPE      "StorageCell Event 0c7a000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603194

   sCellEventTrap-0c-7b TRAP-TYPE  -- CAC Code: 00
        ENTERPRISE compaq
        VARIABLES  { scellNameDateTime,
                     scellSWComponent,
                     scellECode,
                     scellCAC,
                     scellEIP}
        DESCRIPTION
             "Severity: Normal -- informational in nature. The Data Replication Log of a newly created Data Replication Group has been assigned to a SSD Disk Group."
           --#TYPE      "StorageCell Event 0c7b000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603195

   sCellEventTrap-0c-7c TRAP-TYPE  -- CAC Code: 00
        ENTERPRISE compaq
        VARIABLES  { scellNameDateTime,
                     scellSWComponent,
                     scellECode,
                     scellCAC,
                     scellEIP}
        DESCRIPTION
             "Severity: Normal -- informational in nature. The Destination Virtual Disk of a Data Replication Group has been assigned to a SSD Disk Group."
           --#TYPE      "StorageCell Event 0c7c000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603196

   sCellEventTrap-0c-7d TRAP-TYPE  -- CAC Code: 00
        ENTERPRISE compaq
        VARIABLES  { scellNameDateTime,
                     scellSWComponent,
                     scellECode,
                     scellCAC,
                     scellEIP}
        DESCRIPTION
             "Severity: Normal -- informational in nature. The Source Virtual Disk of a Data Replication Group has been assigned to a SSD Disk Group."
           --#TYPE      "StorageCell Event 0c7d000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603197

   sCellEventTrap-0c-7e TRAP-TYPE  -- CAC Code: 5f
        ENTERPRISE compaq
        VARIABLES  { scellNameDateTime,
                     scellSWComponent,
                     scellECode,
                     scellCAC,
                     scellEIP}
        DESCRIPTION
             "Severity: Critical -- failure or failure imminent. The Data Replication Path between this Storage System and the Peer Storage System has closed because the connection has been logged out."
           --#TYPE      "StorageCell Event 0c7e5f0c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603198

   sCellEventTrap-0c-7f TRAP-TYPE  -- CAC Code: 5f
        ENTERPRISE compaq
        VARIABLES  { scellNameDateTime,
                     scellSWComponent,
                     scellECode,
                     scellCAC,
                     scellEIP}
        DESCRIPTION
             "Severity: Critical -- failure or failure imminent. The number of nPortIds supporting the Data Replication Manager protocol exceeds the maximum supported by the firmware."
           --#TYPE      "StorageCell Event 0c7f5f0c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603199

   sCellEventTrap-0c-80 TRAP-TYPE  -- CAC Code: 6a
        ENTERPRISE compaq
        VARIABLES  { scellNameDateTime,
                     scellSWComponent,
                     scellECode,
                     scellCAC,
                     scellEIP}
        DESCRIPTION
             "Severity: Warning -- not failed but attention recommended or required. A request to create a Data Replication Path was rejected because the communication protocol settings are not compatible."
           --#TYPE      "StorageCell Event 0c806a0c"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603200

   sCellEventTrap-0c-81 TRAP-TYPE  -- CAC Code: 5f
        ENTERPRISE compaq
        VARIABLES  { scellNameDateTime,
                     scellSWComponent,
                     scellECode,
                     scellCAC,
                     scellEIP}
        DESCRIPTION
             "Severity: Critical -- failure or failure imminent. The Data Replication Path between this Storage System and the Peer Storage System has closed because the Data Replication Path is disabled or no longer available."
           --#TYPE      "StorageCell Event 0c815f0c"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603201

   sCellEventTrap-0c-83 TRAP-TYPE  -- CAC Code: 00
        ENTERPRISE compaq
        VARIABLES  { scellNameDateTime,
                     scellSWComponent,
                     scellECode,
                     scellCAC,
                     scellEIP}
        DESCRIPTION
             "Severity: Normal -- informational in nature. The Data Replication Group and its members have completed a failover between the master and slave controllers."
           --#TYPE      "StorageCell Event 0c83000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603203

   sCellEventTrap-0c-84 TRAP-TYPE  -- CAC Code: 00
        ENTERPRISE compaq
        VARIABLES  { scellNameDateTime,
                     scellSWComponent,
                     scellECode,
                     scellCAC,
                     scellEIP}
        DESCRIPTION
             "Severity: Normal -- informational in nature. A Data Replication Log expansion has completed."
           --#TYPE      "StorageCell Event 0c84000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603204

   sCellEventTrap-0c-86 TRAP-TYPE  -- CAC Code: 00
        ENTERPRISE compaq
        VARIABLES  { scellNameDateTime,
                     scellSWComponent,
                     scellECode,
                     scellCAC,
                     scellEIP}
        DESCRIPTION
             "Severity: Normal -- informational in nature. The removal of the Source Virtual Disk failed on the DESTINATION for the Data Replication Group."
           --#TYPE      "StorageCell Event 0c86000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603206

   sCellEventTrap-0c-87 TRAP-TYPE  -- CAC Code: 00
        ENTERPRISE compaq
        VARIABLES  { scellNameDateTime,
                     scellSWComponent,
                     scellECode,
                     scellCAC,
                     scellEIP}
        DESCRIPTION
             "Severity: Normal -- informational in nature. A synchronize configuration request is sent by this Source Data Replication Group to its Destination Data Replication Group."
           --#TYPE      "StorageCell Event 0c87000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603207

   sCellEventTrap-0c-88 TRAP-TYPE  -- CAC Code: 00
        ENTERPRISE compaq
        VARIABLES  { scellNameDateTime,
                     scellSWComponent,
                     scellECode,
                     scellCAC,
                     scellEIP}
        DESCRIPTION
             "Severity: Normal -- informational in nature. A synchronize configuration request is received by this Destination Data Replication Group from its Data Replication Source."
           --#TYPE      "StorageCell Event 0c88000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603208

   sCellEventTrap-0c-8a TRAP-TYPE  -- CAC Code: 00
        ENTERPRISE compaq
        VARIABLES  { scellNameDateTime,
                     scellSWComponent,
                     scellECode,
                     scellCAC,
                     scellEIP}
        DESCRIPTION
             "Severity: Normal -- informational in nature. The Data Replication Path between this Storage System and the Peer Storage System has closed, because a management command failed to complete within the timeout period."
           --#TYPE      "StorageCell Event 0c8a000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603210

   sCellEventTrap-0c-8b TRAP-TYPE  -- CAC Code: 00
        ENTERPRISE compaq
        VARIABLES  { scellNameDateTime,
                     scellSWComponent,
                     scellECode,
                     scellCAC,
                     scellEIP}
        DESCRIPTION
             "Severity: Normal -- informational in nature. The Data Replication Path between this Storage System and the Peer Storage System has closed, because of a SCSI exchange retry failure."
           --#TYPE      "StorageCell Event 0c8b000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603211

   sCellEventTrap-0c-8c TRAP-TYPE  -- CAC Code: 00
        ENTERPRISE compaq
        VARIABLES  { scellNameDateTime,
                     scellSWComponent,
                     scellECode,
                     scellCAC,
                     scellEIP}
        DESCRIPTION
             "Severity: Normal -- informational in nature. The Data Replication Path between this Storage System and the Peer Storage System has closed, to avoid a unit stall because a unquiesce management command was not received from the peer controller."
           --#TYPE      "StorageCell Event 0c8c000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603212

   sCellEventTrap-0c-8d TRAP-TYPE  -- CAC Code: 00
        ENTERPRISE compaq
        VARIABLES  { scellNameDateTime,
                     scellSWComponent,
                     scellECode,
                     scellCAC,
                     scellEIP}
        DESCRIPTION
             "Severity: Normal -- informational in nature. A Data Replication Log has been invalidated via the 'Force Full Copy' command; The Data Replication Group has been marked for Full Copy."
           --#TYPE      "StorageCell Event 0c8d000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603213

   sCellEventTrap-0c-8e TRAP-TYPE  -- CAC Code: 00
        ENTERPRISE compaq
        VARIABLES  { scellNameDateTime,
                     scellSWComponent,
                     scellECode,
                     scellCAC,
                     scellEIP}
        DESCRIPTION
             "Severity: Normal -- informational in nature. A Data Replication Group is unable to communicate with remote site because the remote site has been suspended."
           --#TYPE      "StorageCell Event 0c8e000c"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603214

   sCellEventTrap-0d-02 TRAP-TYPE  -- CAC Code: 41
        ENTERPRISE compaq
        VARIABLES  { scellNameDateTime,
                     scellSWComponent,
                     scellECode,
                     scellCAC,
                     scellEIP}
        DESCRIPTION
             "Severity: Warning -- not failed but attention recommended or required. A physical disk drive is improperly installed or missing. This could affect the drive enclosure air flow and cause an over temperature condition."
           --#TYPE      "StorageCell Event 0d024106"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603330

   sCellEventTrap-0d-34 TRAP-TYPE  -- CAC Code: 80
        ENTERPRISE compaq
        VARIABLES  { scellNameDateTime,
                     scellSWComponent,
                     scellECode,
                     scellCAC,
                     scellEIP}
        DESCRIPTION
             "Severity: Critical -- failure or failure imminent. A drive enclosure power supply is improperly installed or missing. This could affect the drive enclosure air flow and cause an over temperature condition. The operational power supply will automatically shut down after a short period of time, thereby disabling the drive enclosure. This condition remains active until either the problem is corrected, or the operational power supply shuts down, whichever occurs first."
           --#TYPE      "StorageCell Event 0d348006"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603380

   sCellEventTrap-0d-47 TRAP-TYPE  -- CAC Code: 83
        ENTERPRISE compaq
        VARIABLES  { scellNameDateTime,
                     scellSWComponent,
                     scellECode,
                     scellCAC,
                     scellEIP}
        DESCRIPTION
             "Severity: Critical -- failure or failure imminent. A drive enclosure fan module is not operating properly. This could affect the drive enclosure air flow and cause an over temperature condition. A single fan operating at high speed can provide sufficient air flow to cool an enclosure. However, operating an enclosure at temperatures approaching an overheating threshold can damage elements and may reduce the mean time before failure of a specific element."
           --#TYPE      "StorageCell Event 0d478306"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603399

   sCellEventTrap-0d-4b TRAP-TYPE  -- CAC Code: 82
        ENTERPRISE compaq
        VARIABLES  { scellNameDateTime,
                     scellSWComponent,
                     scellECode,
                     scellCAC,
                     scellEIP}
        DESCRIPTION
             "Severity: Critical -- failure or failure imminent. A drive enclosure fan module is improperly installed or missing. This affects the drive enclosure air flow and can cause an over temperature condition."
           --#TYPE      "StorageCell Event 0d4b8206"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603403

   sCellEventTrap-0d-5b TRAP-TYPE  -- CAC Code: 86
        ENTERPRISE compaq
        VARIABLES  { scellNameDateTime,
                     scellSWComponent,
                     scellECode,
                     scellCAC,
                     scellEIP}
        DESCRIPTION
             "Severity: Warning -- not failed but attention recommended or required. The temperature of a Enclosure Link Module temperature sensor or Midplane temperature sensor of the disk enclosure is at warning level. The Enterprise Virtual Array system will automatically shut down if the average temperature of all the temperature sensors (IOA, IOB, and 2 Midplane temperature sensors) of the disk enclosure is at or above 50C."
           --#TYPE      "StorageCell Event 0d5b8606"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603419

   sCellEventTrap-0d-5f TRAP-TYPE  -- CAC Code: 87
        ENTERPRISE compaq
        VARIABLES  { scellNameDateTime,
                     scellSWComponent,
                     scellECode,
                     scellCAC,
                     scellEIP}
        DESCRIPTION
             "Severity: Critical -- failure or failure imminent. The temperature of a Enclosure Link Module temperature sensor or Midplane temperature sensor of the disk enclosure is at critical level. The Enterprise Virtual Array system will automatically shut down if the average temperature of all the temperature sensors (IOA, IOB, and 2 Midplane temperature sensors) of the disk enclosure is at or above 50C."
           --#TYPE      "StorageCell Event 0d5f8706"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603423

   sCellEventTrap-0d-8d TRAP-TYPE  -- CAC Code: 90
        ENTERPRISE compaq
        VARIABLES  { scellNameDateTime,
                     scellSWComponent,
                     scellECode,
                     scellCAC,
                     scellEIP}
        DESCRIPTION
             "Severity: Critical -- failure or failure imminent. A drive enclosure transceiver error has been detected."
           --#TYPE      "StorageCell Event 0d8d9006"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603469

   sCellEventTrap-0d-dd TRAP-TYPE  -- CAC Code: 93
        ENTERPRISE compaq
        VARIABLES  { scellNameDateTime,
                     scellSWComponent,
                     scellECode,
                     scellCAC,
                     scellEIP}
        DESCRIPTION
             "Severity: Critical -- failure or failure imminent. A drive enclosure I/O module error has occurred."
           --#TYPE      "StorageCell Event 0ddd9306"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603549

   sCellEventTrap-0d-de TRAP-TYPE  -- CAC Code: 00
        ENTERPRISE compaq
        VARIABLES  { scellNameDateTime,
                     scellSWComponent,
                     scellECode,
                     scellCAC,
                     scellEIP}
        DESCRIPTION
             "Severity: Normal -- informational in nature. A drive enclosure I/O module is not communicating with the other I/O module."
           --#TYPE      "StorageCell Event 0dde0006"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603550

   sCellEventTrap-0d-f0 TRAP-TYPE  -- CAC Code: 00
        ENTERPRISE compaq
        VARIABLES  { scellNameDateTime,
                     scellSWComponent,
                     scellECode,
                     scellCAC,
                     scellEIP}
        DESCRIPTION
             "Severity: Normal -- informational in nature. The status has changed on one or more of the drive enclosures. This informational event is generated for the HSV element manager GUI and contains no user information."
           --#TYPE      "StorageCell Event 0df00011"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603568

   sCellEventTrap-0e-80 TRAP-TYPE  -- CAC Code: 00
        ENTERPRISE compaq
        VARIABLES  { scellNameDateTime,
                     scellSWComponent,
                     scellECode,
                     scellCAC,
                     scellEIP}
        DESCRIPTION
             "Severity: Normal -- informational in nature. Battery subsystem boot time status."
           --#TYPE      "StorageCell Event 0e800019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603712

   sCellEventTrap-0e-81 TRAP-TYPE  -- CAC Code: 00
        ENTERPRISE compaq
        VARIABLES  { scellNameDateTime,
                     scellSWComponent,
                     scellECode,
                     scellCAC,
                     scellEIP}
        DESCRIPTION
             "Severity: Normal -- informational in nature. Battery assembly '0' is now present."
           --#TYPE      "StorageCell Event 0e810019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603713

   sCellEventTrap-0e-82 TRAP-TYPE  -- CAC Code: e1
        ENTERPRISE compaq
        VARIABLES  { scellNameDateTime,
                     scellSWComponent,
                     scellECode,
                     scellCAC,
                     scellEIP}
        DESCRIPTION
             "Severity: Critical -- failure or failure imminent. Battery assembly '0' has been removed."
           --#TYPE      "StorageCell Event 0e82e119"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603714

   sCellEventTrap-0e-83 TRAP-TYPE  -- CAC Code: 00
        ENTERPRISE compaq
        VARIABLES  { scellNameDateTime,
                     scellSWComponent,
                     scellECode,
                     scellCAC,
                     scellEIP}
        DESCRIPTION
             "Severity: Normal -- informational in nature. The status of battery assembly '0' has changed."
           --#TYPE      "StorageCell Event 0e830019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603715

   sCellEventTrap-0e-84 TRAP-TYPE  -- CAC Code: dd
        ENTERPRISE compaq
        VARIABLES  { scellNameDateTime,
                     scellSWComponent,
                     scellECode,
                     scellCAC,
                     scellEIP}
        DESCRIPTION
             "Severity: Critical -- failure or failure imminent. Battery assembly '0' has malfunctioned."
           --#TYPE      "StorageCell Event 0e84dd19"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603716

   sCellEventTrap-0e-85 TRAP-TYPE  -- CAC Code: 00
        ENTERPRISE compaq
        VARIABLES  { scellNameDateTime,
                     scellSWComponent,
                     scellECode,
                     scellCAC,
                     scellEIP}
        DESCRIPTION
             "Severity: Normal -- informational in nature. Battery assembly '1' is now present."
           --#TYPE      "StorageCell Event 0e850019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603717

   sCellEventTrap-0e-86 TRAP-TYPE  -- CAC Code: e2
        ENTERPRISE compaq
        VARIABLES  { scellNameDateTime,
                     scellSWComponent,
                     scellECode,
                     scellCAC,
                     scellEIP}
        DESCRIPTION
             "Severity: Critical -- failure or failure imminent. Battery assembly '1' has been removed."
           --#TYPE      "StorageCell Event 0e86e219"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603718

   sCellEventTrap-0e-87 TRAP-TYPE  -- CAC Code: 00
        ENTERPRISE compaq
        VARIABLES  { scellNameDateTime,
                     scellSWComponent,
                     scellECode,
                     scellCAC,
                     scellEIP}
        DESCRIPTION
             "Severity: Normal -- informational in nature. The status of battery assembly '1' has changed."
           --#TYPE      "StorageCell Event 0e870019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603719

   sCellEventTrap-0e-88 TRAP-TYPE  -- CAC Code: de
        ENTERPRISE compaq
        VARIABLES  { scellNameDateTime,
                     scellSWComponent,
                     scellECode,
                     scellCAC,
                     scellEIP}
        DESCRIPTION
             "Severity: Critical -- failure or failure imminent. Battery assembly '1' has malfunctioned."
           --#TYPE      "StorageCell Event 0e88de19"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603720

   sCellEventTrap-0e-89 TRAP-TYPE  -- CAC Code: 00
        ENTERPRISE compaq
        VARIABLES  { scellNameDateTime,
                     scellSWComponent,
                     scellECode,
                     scellCAC,
                     scellEIP}
        DESCRIPTION
             "Severity: Normal -- informational in nature. Battery assembly '2' is now present."
           --#TYPE      "StorageCell Event 0e890019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603721

   sCellEventTrap-0e-8a TRAP-TYPE  -- CAC Code: e3
        ENTERPRISE compaq
        VARIABLES  { scellNameDateTime,
                     scellSWComponent,
                     scellECode,
                     scellCAC,
                     scellEIP}
        DESCRIPTION
             "Severity: Critical -- failure or failure imminent. Battery assembly '2' has been removed."
           --#TYPE      "StorageCell Event 0e8ae319"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603722

   sCellEventTrap-0e-8b TRAP-TYPE  -- CAC Code: 00
        ENTERPRISE compaq
        VARIABLES  { scellNameDateTime,
                     scellSWComponent,
                     scellECode,
                     scellCAC,
                     scellEIP}
        DESCRIPTION
             "Severity: Normal -- informational in nature. The status of battery assembly '2' has changed."
           --#TYPE      "StorageCell Event 0e8b0019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603723

   sCellEventTrap-0e-8c TRAP-TYPE  -- CAC Code: df
        ENTERPRISE compaq
        VARIABLES  { scellNameDateTime,
                     scellSWComponent,
                     scellECode,
                     scellCAC,
                     scellEIP}
        DESCRIPTION
             "Severity: Critical -- failure or failure imminent. Battery assembly '2' has malfunctioned."
           --#TYPE      "StorageCell Event 0e8cdf19"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603724

   sCellEventTrap-0e-8d TRAP-TYPE  -- CAC Code: 00
        ENTERPRISE compaq
        VARIABLES  { scellNameDateTime,
                     scellSWComponent,
                     scellECode,
                     scellCAC,
                     scellEIP}
        DESCRIPTION
             "Severity: Normal -- informational in nature. Battery assembly '3' is now present."
           --#TYPE      "StorageCell Event 0e8d0019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603725

   sCellEventTrap-0e-8e TRAP-TYPE  -- CAC Code: e4
        ENTERPRISE compaq
        VARIABLES  { scellNameDateTime,
                     scellSWComponent,
                     scellECode,
                     scellCAC,
                     scellEIP}
        DESCRIPTION
             "Severity: Critical -- failure or failure imminent. Battery assembly '3' has been removed."
           --#TYPE      "StorageCell Event 0e8ee419"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603726

   sCellEventTrap-0e-8f TRAP-TYPE  -- CAC Code: 00
        ENTERPRISE compaq
        VARIABLES  { scellNameDateTime,
                     scellSWComponent,
                     scellECode,
                     scellCAC,
                     scellEIP}
        DESCRIPTION
             "Severity: Normal -- informational in nature. The status of battery assembly '3' has changed."
           --#TYPE      "StorageCell Event 0e8f0019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603727

   sCellEventTrap-0e-90 TRAP-TYPE  -- CAC Code: e0
        ENTERPRISE compaq
        VARIABLES  { scellNameDateTime,
                     scellSWComponent,
                     scellECode,
                     scellCAC,
                     scellEIP}
        DESCRIPTION
             "Severity: Critical -- failure or failure imminent. Battery assembly '3' has malfunctioned."
           --#TYPE      "StorageCell Event 0e90e019"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603728

   sCellEventTrap-0e-91 TRAP-TYPE  -- CAC Code: 00
        ENTERPRISE compaq
        VARIABLES  { scellNameDateTime,
                     scellSWComponent,
                     scellECode,
                     scellCAC,
                     scellEIP}
        DESCRIPTION
             "Severity: Normal -- informational in nature. The battery subsystem has transitioned to the good state."
           --#TYPE      "StorageCell Event 0e910019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603729

   sCellEventTrap-0e-92 TRAP-TYPE  -- CAC Code: 00
        ENTERPRISE compaq
        VARIABLES  { scellNameDateTime,
                     scellSWComponent,
                     scellECode,
                     scellCAC,
                     scellEIP}
        DESCRIPTION
             "Severity: Normal -- informational in nature. The battery subsystem has transitioned to the low state."
           --#TYPE      "StorageCell Event 0e920019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603730

   sCellEventTrap-0e-93 TRAP-TYPE  -- CAC Code: e5
        ENTERPRISE compaq
        VARIABLES  { scellNameDateTime,
                     scellSWComponent,
                     scellECode,
                     scellCAC,
                     scellEIP}
        DESCRIPTION
             "Severity: Warning -- not failed but attention recommended or required. The battery subsystem has transitioned to the bad state."
           --#TYPE      "StorageCell Event 0e93e519"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603731

   sCellEventTrap-0e-94 TRAP-TYPE  -- CAC Code: 00
        ENTERPRISE compaq
        VARIABLES  { scellNameDateTime,
                     scellSWComponent,
                     scellECode,
                     scellCAC,
                     scellEIP}
        DESCRIPTION
             "Severity: Normal -- informational in nature. Blower subsystem boot time status."
           --#TYPE      "StorageCell Event 0e940019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603732

   sCellEventTrap-0e-95 TRAP-TYPE  -- CAC Code: 00
        ENTERPRISE compaq
        VARIABLES  { scellNameDateTime,
                     scellSWComponent,
                     scellECode,
                     scellCAC,
                     scellEIP}
        DESCRIPTION
             "Severity: Normal -- informational in nature. Blower assembly '0' is now present."
           --#TYPE      "StorageCell Event 0e950019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603733

   sCellEventTrap-0e-96 TRAP-TYPE  -- CAC Code: e9
        ENTERPRISE compaq
        VARIABLES  { scellNameDateTime,
                     scellSWComponent,
                     scellECode,
                     scellCAC,
                     scellEIP}
        DESCRIPTION
             "Severity: Critical -- failure or failure imminent. Blower assembly '0' has been removed."
           --#TYPE      "StorageCell Event 0e96e919"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603734

   sCellEventTrap-0e-97 TRAP-TYPE  -- CAC Code: 00
        ENTERPRISE compaq
        VARIABLES  { scellNameDateTime,
                     scellSWComponent,
                     scellECode,
                     scellCAC,
                     scellEIP}
        DESCRIPTION
             "Severity: Normal -- informational in nature. The status of blower assembly '0' has changed."
           --#TYPE      "StorageCell Event 0e970019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603735

   sCellEventTrap-0e-98 TRAP-TYPE  -- CAC Code: e7
        ENTERPRISE compaq
        VARIABLES  { scellNameDateTime,
                     scellSWComponent,
                     scellECode,
                     scellCAC,
                     scellEIP}
        DESCRIPTION
             "Severity: Critical -- failure or failure imminent. Blower assembly '0' has malfunctioned."
           --#TYPE      "StorageCell Event 0e98e719"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603736

   sCellEventTrap-0e-99 TRAP-TYPE  -- CAC Code: 00
        ENTERPRISE compaq
        VARIABLES  { scellNameDateTime,
                     scellSWComponent,
                     scellECode,
                     scellCAC,
                     scellEIP}
        DESCRIPTION
             "Severity: Normal -- informational in nature. Blower assembly '1' is now present."
           --#TYPE      "StorageCell Event 0e990019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603737

   sCellEventTrap-0e-9a TRAP-TYPE  -- CAC Code: ea
        ENTERPRISE compaq
        VARIABLES  { scellNameDateTime,
                     scellSWComponent,
                     scellECode,
                     scellCAC,
                     scellEIP}
        DESCRIPTION
             "Severity: Critical -- failure or failure imminent. Blower assembly '1' has been removed."
           --#TYPE      "StorageCell Event 0e9aea19"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603738

   sCellEventTrap-0e-9b TRAP-TYPE  -- CAC Code: 00
        ENTERPRISE compaq
        VARIABLES  { scellNameDateTime,
                     scellSWComponent,
                     scellECode,
                     scellCAC,
                     scellEIP}
        DESCRIPTION
             "Severity: Normal -- informational in nature. The status of blower assembly '1' has changed."
           --#TYPE      "StorageCell Event 0e9b0019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603739

   sCellEventTrap-0e-9c TRAP-TYPE  -- CAC Code: e8
        ENTERPRISE compaq
        VARIABLES  { scellNameDateTime,
                     scellSWComponent,
                     scellECode,
                     scellCAC,
                     scellEIP}
        DESCRIPTION
             "Severity: Critical -- failure or failure imminent. Blower assembly '1' has malfunctioned."
           --#TYPE      "StorageCell Event 0e9ce819"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603740

   sCellEventTrap-0e-9d TRAP-TYPE  -- CAC Code: ef
        ENTERPRISE compaq
        VARIABLES  { scellNameDateTime,
                     scellSWComponent,
                     scellECode,
                     scellCAC,
                     scellEIP}
        DESCRIPTION
             "Severity: Warning -- not failed but attention recommended or required. Battery read memory failure has occurred."
           --#TYPE      "StorageCell Event 0e9def19"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603741

   sCellEventTrap-0e-9e TRAP-TYPE  -- CAC Code: 00
        ENTERPRISE compaq
        VARIABLES  { scellNameDateTime,
                     scellSWComponent,
                     scellECode,
                     scellCAC,
                     scellEIP}
        DESCRIPTION
             "Severity: Normal -- informational in nature. Temperature subsystem boot time status."
           --#TYPE      "StorageCell Event 0e9e0019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603742

   sCellEventTrap-0e-9f TRAP-TYPE  -- CAC Code: 00
        ENTERPRISE compaq
        VARIABLES  { scellNameDateTime,
                     scellSWComponent,
                     scellECode,
                     scellCAC,
                     scellEIP}
        DESCRIPTION
             "Severity: Normal -- informational in nature. The temperature within an controller has returned to its normal operating range."
           --#TYPE      "StorageCell Event 0e9f0019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603743

   sCellEventTrap-0e-a0 TRAP-TYPE  -- CAC Code: 2e
        ENTERPRISE compaq
        VARIABLES  { scellNameDateTime,
                     scellSWComponent,
                     scellECode,
                     scellCAC,
                     scellEIP}
        DESCRIPTION
             "Severity: Warning -- not failed but attention recommended or required. The temperature within an controller is approaching its trip point."
           --#TYPE      "StorageCell Event 0ea02e19"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603744

   sCellEventTrap-0e-a1 TRAP-TYPE  -- CAC Code: 36
        ENTERPRISE compaq
        VARIABLES  { scellNameDateTime,
                     scellSWComponent,
                     scellECode,
                     scellCAC,
                     scellEIP}
        DESCRIPTION
             "Severity: Critical -- failure or failure imminent. The temperature trip point for a temperature sensor located within a controller has been reached."
           --#TYPE      "StorageCell Event 0ea13619"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603745

   sCellEventTrap-0e-a2 TRAP-TYPE  -- CAC Code: 00
        ENTERPRISE compaq
        VARIABLES  { scellNameDateTime,
                     scellSWComponent,
                     scellECode,
                     scellCAC,
                     scellEIP}
        DESCRIPTION
             "Severity: Normal -- informational in nature. Power Supply subsystem boot time status."
           --#TYPE      "StorageCell Event 0ea20019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603746

   sCellEventTrap-0e-a3 TRAP-TYPE  -- CAC Code: 00
        ENTERPRISE compaq
        VARIABLES  { scellNameDateTime,
                     scellSWComponent,
                     scellECode,
                     scellCAC,
                     scellEIP}
        DESCRIPTION
             "Severity: Normal -- informational in nature. Power Supply assembly '0' is now present."
           --#TYPE      "StorageCell Event 0ea30019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603747

   sCellEventTrap-0e-a4 TRAP-TYPE  -- CAC Code: ed
        ENTERPRISE compaq
        VARIABLES  { scellNameDateTime,
                     scellSWComponent,
                     scellECode,
                     scellCAC,
                     scellEIP}
        DESCRIPTION
             "Severity: Critical -- failure or failure imminent. Power Supply assembly '0' has been removed."
           --#TYPE      "StorageCell Event 0ea4ed19"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603748

   sCellEventTrap-0e-a5 TRAP-TYPE  -- CAC Code: 00
        ENTERPRISE compaq
        VARIABLES  { scellNameDateTime,
                     scellSWComponent,
                     scellECode,
                     scellCAC,
                     scellEIP}
        DESCRIPTION
             "Severity: Normal -- informational in nature. The status of power supply assembly '0' has changed."
           --#TYPE      "StorageCell Event 0ea50019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603749

   sCellEventTrap-0e-a6 TRAP-TYPE  -- CAC Code: eb
        ENTERPRISE compaq
        VARIABLES  { scellNameDateTime,
                     scellSWComponent,
                     scellECode,
                     scellCAC,
                     scellEIP}
        DESCRIPTION
             "Severity: Critical -- failure or failure imminent. Power supply assembly '0' lost AC connection or has malfunctioned."
           --#TYPE      "StorageCell Event 0ea6eb19"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603750

   sCellEventTrap-0e-a7 TRAP-TYPE  -- CAC Code: 00
        ENTERPRISE compaq
        VARIABLES  { scellNameDateTime,
                     scellSWComponent,
                     scellECode,
                     scellCAC,
                     scellEIP}
        DESCRIPTION
             "Severity: Normal -- informational in nature. Power Supply assembly '1' is now present."
           --#TYPE      "StorageCell Event 0ea70019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603751

   sCellEventTrap-0e-a8 TRAP-TYPE  -- CAC Code: ee
        ENTERPRISE compaq
        VARIABLES  { scellNameDateTime,
                     scellSWComponent,
                     scellECode,
                     scellCAC,
                     scellEIP}
        DESCRIPTION
             "Severity: Critical -- failure or failure imminent. Power Supply assembly '1' has been removed."
           --#TYPE      "StorageCell Event 0ea8ee19"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603752

   sCellEventTrap-0e-a9 TRAP-TYPE  -- CAC Code: 00
        ENTERPRISE compaq
        VARIABLES  { scellNameDateTime,
                     scellSWComponent,
                     scellECode,
                     scellCAC,
                     scellEIP}
        DESCRIPTION
             "Severity: Normal -- informational in nature. The status of power supply assembly '1' has changed."
           --#TYPE      "StorageCell Event 0ea90019"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603753

   sCellEventTrap-0e-aa TRAP-TYPE  -- CAC Code: ec
        ENTERPRISE compaq
        VARIABLES  { scellNameDateTime,
                     scellSWComponent,
                     scellECode,
                     scellCAC,
                     scellEIP}
        DESCRIPTION
             "Severity: Critical -- failure or failure imminent. Power supply assembly '1' lost AC connection or has malfunctioned."
           --#TYPE      "StorageCell Event 0eaaec19"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13603754

   sCellEventTrap-0f-00 TRAP-TYPE  -- CAC Code: 4a
        ENTERPRISE compaq
        VARIABLES  { scellNameDateTime,
                     scellSWComponent,
                     scellECode,
                     scellCAC,
                     scellEIP}
        DESCRIPTION
             "Severity: Warning -- not failed but attention recommended or required. A Fibre Channel port on the controller has failed to respond."
           --#TYPE      "StorageCell Event 0f004a08"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603840

   sCellEventTrap-0f-01 TRAP-TYPE  -- CAC Code: 00
        ENTERPRISE compaq
        VARIABLES  { scellNameDateTime,
                     scellSWComponent,
                     scellECode,
                     scellCAC,
                     scellEIP}
        DESCRIPTION
             "Severity: Normal -- informational in nature. An excessive number of link errors were detected on a controller's mirror Fibre Channel port. This informational event is triggered by the occurrence of an excessive number of Tachyon chip link status errors detected within a particular link status error type."
           --#TYPE      "StorageCell Event 0f010007"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603841

   sCellEventTrap-0f-02 TRAP-TYPE  -- CAC Code: 00
        ENTERPRISE compaq
        VARIABLES  { scellNameDateTime,
                     scellSWComponent,
                     scellECode,
                     scellCAC,
                     scellEIP}
        DESCRIPTION
             "Severity: Normal -- informational in nature. A controller has been told to enable a mirror port, and that mirror port was not disabled during boot diagnostics."
           --#TYPE      "StorageCell Event 0f020013"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603842

   sCellEventTrap-0f-03 TRAP-TYPE  -- CAC Code: 47
        ENTERPRISE compaq
        VARIABLES  { scellNameDateTime,
                     scellSWComponent,
                     scellECode,
                     scellCAC,
                     scellEIP}
        DESCRIPTION
             "Severity: Warning -- not failed but attention recommended or required. A non-data exchange sent to a mirror port has timed out."
           --#TYPE      "StorageCell Event 0f034709"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603843

   sCellEventTrap-0f-04 TRAP-TYPE  -- CAC Code: 00
        ENTERPRISE compaq
        VARIABLES  { scellNameDateTime,
                     scellSWComponent,
                     scellECode,
                     scellCAC,
                     scellEIP}
        DESCRIPTION
             "Severity: Normal -- informational in nature. The controller has sent an Extended Link Service command Reinstate Recovery Qualifier."
           --#TYPE      "StorageCell Event 0f040009"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603844

   sCellEventTrap-0f-05 TRAP-TYPE  -- CAC Code: 00
        ENTERPRISE compaq
        VARIABLES  { scellNameDateTime,
                     scellSWComponent,
                     scellECode,
                     scellCAC,
                     scellEIP}
        DESCRIPTION
             "Severity: Normal -- informational in nature. The controller has sent a Basic Link Service command Abort Sequence Frame."
           --#TYPE      "StorageCell Event 0f050009"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603845

   sCellEventTrap-0f-06 TRAP-TYPE  -- CAC Code: 00
        ENTERPRISE compaq
        VARIABLES  { scellNameDateTime,
                     scellSWComponent,
                     scellECode,
                     scellCAC,
                     scellEIP}
        DESCRIPTION
             "Severity: Normal -- informational in nature. The controller has updated its Mirror Transport Status."
           --#TYPE      "StorageCell Event 0f060024"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603846

   sCellEventTrap-0f-07 TRAP-TYPE  -- CAC Code: 07
        ENTERPRISE compaq
        VARIABLES  { scellNameDateTime,
                     scellSWComponent,
                     scellECode,
                     scellCAC,
                     scellEIP}
        DESCRIPTION
             "Severity: Warning -- not failed but attention recommended or required. The controller mirror transport performed an invalid status change."
           --#TYPE      "StorageCell Event 0f070724"
           --#SUMMARY   "SCellName-TimeDate %s : SWCID %d : ECode: %d : CAC %d : EIP %d."
           --#ARGUMENTS {0,1,2,3,4,}
           --#SEVERITY  MINOR
           --#TIMEINDEX 136
           --#STATE     WARNING
        ::= 13603847

   sCellEventTrap-0f-08 TRAP-TYPE  -- CAC Code: 00
        ENTERPRISE compaq
        VARIABLES  { scellNameDateTime,
                     scellSWComponent,
                     scellECode,
                     scellCAC,
                     scellEIP}
        DESCRIPTION
             "Severity: Normal -- informational in nature. The controller has updated its Mirror Transport Version."
           --#TYPE      "StorageCell Event 0f080024"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603848

   sCellEventTrap-0f-09 TRAP-TYPE  -- CAC Code: 00
        ENTERPRISE compaq
        VARIABLES  { scellNameDateTime,
                     scellSWComponent,
                     scellECode,
                     scellCAC,
                     scellEIP}
        DESCRIPTION
             "Severity: Normal -- informational in nature. A mirror operation has recovered from an invalid address  or length parameter."
           --#TYPE      "StorageCell Event 0f090021"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13603849

   sCellEventTrap-42-00 TRAP-TYPE  -- CAC Code: 00
        ENTERPRISE compaq
        VARIABLES  { scellNameDateTime,
                     scellSWComponent,
                     scellECode,
                     scellCAC,
                     scellEIP}
        DESCRIPTION
             "Severity: Normal -- informational in nature. A host Fibre Channel port transitioned to the link down state."
           --#TYPE      "StorageCell Event 42000008"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616896

   sCellEventTrap-42-01 TRAP-TYPE  -- CAC Code: 00
        ENTERPRISE compaq
        VARIABLES  { scellNameDateTime,
                     scellSWComponent,
                     scellECode,
                     scellCAC,
                     scellEIP}
        DESCRIPTION
             "Severity: Normal -- informational in nature. A host Fibre Channel port transitioned to the link failed state."
           --#TYPE      "StorageCell Event 42010008"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616897

   sCellEventTrap-42-02 TRAP-TYPE  -- CAC Code: 00
        ENTERPRISE compaq
        VARIABLES  { scellNameDateTime,
                     scellSWComponent,
                     scellECode,
                     scellCAC,
                     scellEIP}
        DESCRIPTION
             "Severity: Normal -- informational in nature. A host Fibre Channel port transitioned to the link up state AND the in-band port is ready for SCSI."
           --#TYPE      "StorageCell Event 42020008"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616898

   sCellEventTrap-42-03 TRAP-TYPE  -- CAC Code: 00
        ENTERPRISE compaq
        VARIABLES  { scellNameDateTime,
                     scellSWComponent,
                     scellECode,
                     scellCAC,
                     scellEIP}
        DESCRIPTION
             "Severity: Normal -- informational in nature. An excessive number of link errors were detected on a host Fibre Channel port."
           --#TYPE      "StorageCell Event 42030007"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616899

   sCellEventTrap-42-04 TRAP-TYPE  -- CAC Code: 4a
        ENTERPRISE compaq
        VARIABLES  { scellNameDateTime,
                     scellSWComponent,
                     scellECode,
                     scellCAC,
                     scellEIP}
        DESCRIPTION
             "Severity: Warning -- not failed but attention recommended or required. A host Fibre Channel port has failed to respond."
           --#TYPE      "StorageCell Event 42044a08"
           --#SUMMARY   "SCellName-TimeDate %s : SWCID %d : ECode: %d : CAC %d : EIP %d."
           --#ARGUMENTS {0,1,2,3,4,}
           --#SEVERITY  MINOR
           --#TIMEINDEX 136
           --#STATE     WARNING
        ::= 13616900

   sCellEventTrap-42-06 TRAP-TYPE  -- CAC Code: 00
        ENTERPRISE compaq
        VARIABLES  { scellNameDateTime,
                     scellSWComponent,
                     scellECode,
                     scellCAC,
                     scellEIP}
        DESCRIPTION
             "Severity: Normal -- informational in nature. Indicated Virtual Disk has transitioned to Stalled Too Long."
           --#TYPE      "StorageCell Event 4206001b"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616902

   sCellEventTrap-42-07 TRAP-TYPE  -- CAC Code: 00
        ENTERPRISE compaq
        VARIABLES  { scellNameDateTime,
                     scellSWComponent,
                     scellECode,
                     scellCAC,
                     scellEIP}
        DESCRIPTION
             "Severity: Normal -- informational in nature. Indicated Virtual Disk is transitioning the ownership to the other controller."
           --#TYPE      "StorageCell Event 4207001b"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616903

   sCellEventTrap-42-0a TRAP-TYPE  -- CAC Code: 00
        ENTERPRISE compaq
        VARIABLES  { scellNameDateTime,
                     scellSWComponent,
                     scellECode,
                     scellCAC,
                     scellEIP}
        DESCRIPTION
             "Severity: Normal -- informational in nature. Indicated Virtual Disk that previously entered into Stalled Too Long has now been unstalled and resumed."
           --#TYPE      "StorageCell Event 420a001b"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616906

   sCellEventTrap-42-0b TRAP-TYPE  -- CAC Code: 00
        ENTERPRISE compaq
        VARIABLES  { scellNameDateTime,
                     scellSWComponent,
                     scellECode,
                     scellCAC,
                     scellEIP}
        DESCRIPTION
             "Severity: Normal -- informational in nature. Indicated Virtual Disk has transitioned to ownership by the other controller."
           --#TYPE      "StorageCell Event 420b001b"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616907

   sCellEventTrap-42-0c TRAP-TYPE  -- CAC Code: 00
        ENTERPRISE compaq
        VARIABLES  { scellNameDateTime,
                     scellSWComponent,
                     scellECode,
                     scellCAC,
                     scellEIP}
        DESCRIPTION
             "Severity: Normal -- informational in nature. Indicated Virtual Disk has failed to transition ownership to the other controller."
           --#TYPE      "StorageCell Event 420c001b"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616908

   sCellEventTrap-42-0d TRAP-TYPE  -- CAC Code: 00
        ENTERPRISE compaq
        VARIABLES  { scellNameDateTime,
                     scellSWComponent,
                     scellECode,
                     scellCAC,
                     scellEIP}
        DESCRIPTION
             "Severity: Normal -- informational in nature. Indicated Virtual Disk has timed out the ownership transition to the other controller."
           --#TYPE      "StorageCell Event 420d001b"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616909

   sCellEventTrap-42-0e TRAP-TYPE  -- CAC Code: 00
        ENTERPRISE compaq
        VARIABLES  { scellNameDateTime,
                     scellSWComponent,
                     scellECode,
                     scellCAC,
                     scellEIP}
        DESCRIPTION
             "Severity: Normal -- informational in nature. Generic frontend service information events."
           --#TYPE      "StorageCell Event 420e0024"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616910

   sCellEventTrap-42-0f TRAP-TYPE  -- CAC Code: 00
        ENTERPRISE compaq
        VARIABLES  { scellNameDateTime,
                     scellSWComponent,
                     scellECode,
                     scellCAC,
                     scellEIP}
        DESCRIPTION
             "Severity: Normal -- informational in nature. A host Fibre Channel port is being reset to clear a credit error which may result in a subsequent LINK DOWN and LINK UP event."
           --#TYPE      "StorageCell Event 420f0008"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616911

   sCellEventTrap-42-10 TRAP-TYPE  -- CAC Code: 00
        ENTERPRISE compaq
        VARIABLES  { scellNameDateTime,
                     scellSWComponent,
                     scellECode,
                     scellCAC,
                     scellEIP}
        DESCRIPTION
             "Severity: Normal -- informational in nature. A host Fibre Channel port has completed name server registration ."
           --#TYPE      "StorageCell Event 42100008"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616912

   sCellEventTrap-42-11 TRAP-TYPE  -- CAC Code: 00
        ENTERPRISE compaq
        VARIABLES  { scellNameDateTime,
                     scellSWComponent,
                     scellECode,
                     scellCAC,
                     scellEIP}
        DESCRIPTION
             "Severity: Normal -- informational in nature. A remote HTB report."
           --#TYPE      "StorageCell Event 4211002f"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13616913

   sCellEventTrap-83-00 TRAP-TYPE  -- CAC Code: 20
        ENTERPRISE compaq
        VARIABLES  { scellNameDateTime,
                     scellSWComponent,
                     scellECode,
                     scellCAC,
                     scellEIP}
        DESCRIPTION
             "Severity: Critical -- failure or failure imminent. A failure was detected during the execution of this controller's on-board diagnostics."
           --#TYPE      "StorageCell Event 83002014"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13633536

   sCellEventTrap-83-01 TRAP-TYPE  -- CAC Code: 30
        ENTERPRISE compaq
        VARIABLES  { scellNameDateTime,
                     scellSWComponent,
                     scellECode,
                     scellCAC,
                     scellEIP}
        DESCRIPTION
             "Severity: Critical -- failure or failure imminent. A GBIC SFF Serial ID Data check code failure was detected during the execution of this controller's on-board diagnostics."
           --#TYPE      "StorageCell Event 83013014"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13633537

   sCellEventTrap-83-07 TRAP-TYPE  -- CAC Code: 3a
        ENTERPRISE compaq
        VARIABLES  { scellNameDateTime,
                     scellSWComponent,
                     scellECode,
                     scellCAC,
                     scellEIP}
        DESCRIPTION
             "Severity: Critical -- failure or failure imminent. A GBIC SFF was determined to be not present during the execution of this controller's on-board diagnostics."
           --#TYPE      "StorageCell Event 83073a14"
           --#SUMMARY   "SCellName-TimeDate %s : SWCID %d : ECode: %d : CAC %d : EIP %d."
           --#ARGUMENTS {0,1,2,3,4,}
           --#SEVERITY  CRITICAL
           --#TIMEINDEX 136
           --#STATE     WARNING
        ::= 13633543

   sCellEventTrap-83-08 TRAP-TYPE  -- CAC Code: 3b
        ENTERPRISE compaq
        VARIABLES  { scellNameDateTime,
                     scellSWComponent,
                     scellECode,
                     scellCAC,
                     scellEIP}
        DESCRIPTION
             "Severity: Warning -- not failed but attention recommended or required. A failure was detected during testing of this controller's SRAM."
           --#TYPE      "StorageCell Event 83083b14"
           --#SUMMARY   "SCellName-TimeDate %s : SWCID %d : ECode: %d : CAC %d : EIP %d."
           --#ARGUMENTS {0,1,2,3,4,}
           --#SEVERITY  MINOR
           --#TIMEINDEX 136
           --#STATE     WARNING
        ::= 13633544

   sCellEventTrap-83-09 TRAP-TYPE  -- CAC Code: 3b
        ENTERPRISE compaq
        VARIABLES  { scellNameDateTime,
                     scellSWComponent,
                     scellECode,
                     scellCAC,
                     scellEIP}
        DESCRIPTION
             "Severity: Warning -- not failed but attention recommended or required. A parity error was detected during testing of this controller's SRAM."
           --#TYPE      "StorageCell Event 83093b14"
           --#SUMMARY   "SCellName-TimeDate %s : SWCID %d : ECode: %d : CAC %d : EIP %d."
           --#ARGUMENTS {0,1,2,3,4,}
           --#SEVERITY  MINOR
           --#TIMEINDEX 136
           --#STATE     WARNING
        ::= 13633545

   sCellEventTrap-83-0a TRAP-TYPE  -- CAC Code: 00
        ENTERPRISE compaq
        VARIABLES  { scellNameDateTime,
                     scellSWComponent,
                     scellECode,
                     scellCAC,
                     scellEIP}
        DESCRIPTION
             "Severity: Normal -- informational in nature. Hardware revisions have been reported by this controller."
           --#TYPE      "StorageCell Event 830a0022"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13633546

   sCellEventTrap-83-0b TRAP-TYPE  -- CAC Code: 00
        ENTERPRISE compaq
        VARIABLES  { scellNameDateTime,
                     scellSWComponent,
                     scellECode,
                     scellCAC,
                     scellEIP}
        DESCRIPTION
             "Severity: Normal -- informational in nature. Cache memory ECC errors exceeded 250/day in this controller's SDRAM."
           --#TYPE      "StorageCell Event 830b0026"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13633547

   sCellEventTrap-83-0c TRAP-TYPE  -- CAC Code: 00
        ENTERPRISE compaq
        VARIABLES  { scellNameDateTime,
                     scellSWComponent,
                     scellECode,
                     scellCAC,
                     scellEIP}
        DESCRIPTION
             "Severity: Normal -- informational in nature. Policy memory ECC errors exceeded 250/day in this controller's SDRAM."
           --#TYPE      "StorageCell Event 830c0026"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13633548

   sCellEventTrap-83-0d TRAP-TYPE  -- CAC Code: 00
        ENTERPRISE compaq
        VARIABLES  { scellNameDateTime,
                     scellSWComponent,
                     scellECode,
                     scellCAC,
                     scellEIP}
        DESCRIPTION
             "Severity: Normal -- informational in nature. Cache memory ECC errors exceeded 750/week in this controller's SDRAM."
           --#TYPE      "StorageCell Event 830d0026"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13633549

   sCellEventTrap-83-0e TRAP-TYPE  -- CAC Code: 00
        ENTERPRISE compaq
        VARIABLES  { scellNameDateTime,
                     scellSWComponent,
                     scellECode,
                     scellCAC,
                     scellEIP}
        DESCRIPTION
             "Severity: Normal -- informational in nature. Policy memory ECC errors exceeded 750/week in this controller's SDRAM."
           --#TYPE      "StorageCell Event 830e0026"
           --#SUMMARY   "SCellName-TimeDate %s : SWCID %d : ECode: %d : CAC %d : EIP %d."
           --#ARGUMENTS {0,1,2,3,4,}
           --#SEVERITY  INFORMATIONAL
           --#TIMEINDEX 136
           --#STATE     WARNING
        ::= 13633550
-- Following are the traps defined for the HSV Management Agent
-- The trap name is constructed from the unique status code for
-- the Management Event.  This numbers is represented as
-- a decimal number.
-- For example: mngmtAgentTrap-5009 has:
--   Status Code of 5009
--
-- The Trap number is calculated by using the status code + a base
-- In our example above: mngmtAgentTrap-5009 the trap number is -
-- Base = 136000000  (which preserves our unique OID sub-identifier of 136)
--        + status code 5009 =  136005009
-- This allows for a large number of uniquely mapped events and
-- avoids trap number collisions with StorageCell Event traps.


   mngmtAgentTrap-1 TRAP-TYPE
        ENTERPRISE compaq
        VARIABLES  { hostName,
                     scellNameDateTime,
                     agentEventCode,
                     agentEventDescription }
        DESCRIPTION
             "Object Already Exists"
           --#TYPE      "Management Agent Event 1"
           --#SUMMARY   "Host %s : SCellName-TimeDate %s : EventCode %d : Description %s"
           --#ARGUMENTS {0,1,2,3,}
            --#SEVERITY  INFORMATIONAL
            --#TIMEINDEX 136
        ::= 136000001

   mngmtAgentTrap-2 TRAP-TYPE
        ENTERPRISE compaq
        VARIABLES  { hostName,
                     scellNameDateTime,
                     agentEventCode,
                     agentEventDescription }
        DESCRIPTION
             "Supplied Buffer Too Small"
           --#TYPE      "Management Agent Event 2"
           --#SUMMARY   "Host %s : SCellName-TimeDate %s : EventCode %d : Description %s"
           --#ARGUMENTS {0,1,2,3,}
            --#SEVERITY  INFORMATIONAL
            --#TIMEINDEX 136
        ::= 136000002

   mngmtAgentTrap-3 TRAP-TYPE
        ENTERPRISE compaq
        VARIABLES  { hostName,
                     scellNameDateTime,
                     agentEventCode,
                     agentEventDescription }
        DESCRIPTION
             "Object Already Assigned"
           --#TYPE      "Management Agent Event 3"
           --#SUMMARY   "Host %s : SCellName-TimeDate %s : EventCode %d : Description %s"
           --#ARGUMENTS {0,1,2,3,}
            --#SEVERITY  INFORMATIONAL
            --#TIMEINDEX 136
        ::= 136000003

   mngmtAgentTrap-4 TRAP-TYPE
        ENTERPRISE compaq
        VARIABLES  { hostName,
                     scellNameDateTime,
                     agentEventCode,
                     agentEventDescription }
        DESCRIPTION
             "Not enough data storage available in the disk groups, or no compatible disk groups available for the requested raid type. If this error occurred during a data replication operation please check if the requested capacity/raid level can be supported in the disk groups on both source and destination."
           --#TYPE      "Management Agent Event 4"
           --#SUMMARY   "Host %s : SCellName-TimeDate %s : EventCode %d : Description %s"
           --#ARGUMENTS {0,1,2,3,}
            --#SEVERITY  CRITICAL
            --#TIMEINDEX 136
        ::= 136000004

   mngmtAgentTrap-5 TRAP-TYPE
        ENTERPRISE compaq
        VARIABLES  { hostName,
                     scellNameDateTime,
                     agentEventCode,
                     agentEventDescription }
        DESCRIPTION
             "Internal Error: An unexpected condition was encountered while processing the request"
           --#TYPE      "Management Agent Event 5"
           --#SUMMARY   "Host %s : SCellName-TimeDate %s : EventCode %d : Description %s"
           --#ARGUMENTS {0,1,2,3,}
            --#SEVERITY  MINOR
            --#TIMEINDEX 136
        ::= 136000005

   mngmtAgentTrap-6 TRAP-TYPE
        ENTERPRISE compaq
        VARIABLES  { hostName,
                     scellNameDateTime,
                     agentEventCode,
                     agentEventDescription }
        DESCRIPTION
             "Invalid status for logical disk"
           --#TYPE      "Management Agent Event 6"
           --#SUMMARY   "Host %s : SCellName-TimeDate %s : EventCode %d : Description %s"
           --#ARGUMENTS {0,1,2,3,}
            --#SEVERITY  INFORMATIONAL
            --#TIMEINDEX 136
        ::= 136000006

   mngmtAgentTrap-7 TRAP-TYPE
        ENTERPRISE compaq
        VARIABLES  { hostName,
                     scellNameDateTime,
                     agentEventCode,
                     agentEventDescription }
        DESCRIPTION
             "Invalid Class"
           --#TYPE      "Management Agent Event 7"
           --#SUMMARY   "Host %s : SCellName-TimeDate %s : EventCode %d : Description %s"
           --#ARGUMENTS {0,1,2,3,}
            --#SEVERITY  INFORMATIONAL
            --#TIMEINDEX 136
        ::= 136000007

   mngmtAgentTrap-8 TRAP-TYPE
        ENTERPRISE compaq
        VARIABLES  { hostName,
                     scellNameDateTime,
                     agentEventCode,
                     agentEventDescription }
        DESCRIPTION
             "Invalid Function"
           --#TYPE      "Management Agent Event 8"
           --#SUMMARY   "Host %s : SCellName-TimeDate %s : EventCode %d : Description %s"
           --#ARGUMENTS {0,1,2,3,}
            --#SEVERITY  INFORMATIONAL
            --#TIMEINDEX 136
        ::= 136000008

   mngmtAgentTrap-9 TRAP-TYPE
        ENTERPRISE compaq
        VARIABLES  { hostName,
                     scellNameDateTime,
                     agentEventCode,
                     agentEventDescription }
        DESCRIPTION
             "Invalid Logical Disk Block State"
           --#TYPE      "Management Agent Event 9"
           --#SUMMARY   "Host %s : SCellName-TimeDate %s : EventCode %d : Description %s"
           --#ARGUMENTS {0,1,2,3,}
            --#SEVERITY  INFORMATIONAL
            --#TIMEINDEX 136
        ::= 136000009

   mngmtAgentTrap-10 TRAP-TYPE
        ENTERPRISE compaq
        VARIABLES  { hostName,
                     scellNameDateTime,
                     agentEventCode,
                     agentEventDescription }
        DESCRIPTION
             "Invalid Loop Configuration"
           --#TYPE      "Management Agent Event 10"
           --#SUMMARY   "Host %s : SCellName-TimeDate %s : EventCode %d : Description %s"
           --#ARGUMENTS {0,1,2,3,}
            --#SEVERITY  INFORMATIONAL
            --#TIMEINDEX 136
        ::= 136000010

   mngmtAgentTrap-11 TRAP-TYPE
        ENTERPRISE compaq
        VARIABLES  { hostName,
                     scellNameDateTime,
                     agentEventCode,
                     agentEventDescription }
        DESCRIPTION
             "Invalid Parameter"
           --#TYPE      "Management Agent Event 11"
           --#SUMMARY   "Host %s : SCellName-TimeDate %s : EventCode %d : Description %s"
           --#ARGUMENTS {0,1,2,3,}
            --#SEVERITY  INFORMATIONAL
            --#TIMEINDEX 136
        ::= 136000011

   mngmtAgentTrap-12 TRAP-TYPE
        ENTERPRISE compaq
        VARIABLES  { hostName,
                     scellNameDateTime,
                     agentEventCode,
                     agentEventDescription }
        DESCRIPTION
             "Invalid Parameter handle"
           --#TYPE      "Management Agent Event 12"
           --#SUMMARY   "Host %s : SCellName-TimeDate %s : EventCode %d : Description %s"
           --#ARGUMENTS {0,1,2,3,}
            --#SEVERITY  INFORMATIONAL
            --#TIMEINDEX 136
        ::= 136000012

   mngmtAgentTrap-13 TRAP-TYPE
        ENTERPRISE compaq
        VARIABLES  { hostName,
                     scellNameDateTime,
                     agentEventCode,
                     agentEventDescription }
        DESCRIPTION
             "Invalid Parameter Id"
           --#TYPE      "Management Agent Event 13"
           --#SUMMARY   "Host %s : SCellName-TimeDate %s : EventCode %d : Description %s"
           --#ARGUMENTS {0,1,2,3,}
            --#SEVERITY  INFORMATIONAL
            --#TIMEINDEX 136
        ::= 136000013

   mngmtAgentTrap-14 TRAP-TYPE
        ENTERPRISE compaq
        VARIABLES  { hostName,
                     scellNameDateTime,
                     agentEventCode,
                     agentEventDescription }
        DESCRIPTION
             "Invalid Quorum Configuration"
           --#TYPE      "Management Agent Event 14"
           --#SUMMARY   "Host %s : SCellName-TimeDate %s : EventCode %d : Description %s"
           --#ARGUMENTS {0,1,2,3,}
            --#SEVERITY  INFORMATIONAL
            --#TIMEINDEX 136
        ::= 136000014

   mngmtAgentTrap-15 TRAP-TYPE
        ENTERPRISE compaq
        VARIABLES  { hostName,
                     scellNameDateTime,
                     agentEventCode,
                     agentEventDescription }
        DESCRIPTION
             "Invalid Target Handle"
           --#TYPE      "Management Agent Event 15"
           --#SUMMARY   "Host %s : SCellName-TimeDate %s : EventCode %d : Description %s"
           --#ARGUMENTS {0,1,2,3,}
            --#SEVERITY  INFORMATIONAL
            --#TIMEINDEX 136
        ::= 136000015

   mngmtAgentTrap-16 TRAP-TYPE
        ENTERPRISE compaq
        VARIABLES  { hostName,
                     scellNameDateTime,
                     agentEventCode,
                     agentEventDescription }
        DESCRIPTION
             "Invalid Target Id"
           --#TYPE      "Management Agent Event 16"
           --#SUMMARY   "Host %s : SCellName-TimeDate %s : EventCode %d : Description %s"
           --#ARGUMENTS {0,1,2,3,}
            --#SEVERITY  INFORMATIONAL
            --#TIMEINDEX 136
        ::= 136000016

   mngmtAgentTrap-17 TRAP-TYPE
        ENTERPRISE compaq
        VARIABLES  { hostName,
                     scellNameDateTime,
                     agentEventCode,
                     agentEventDescription }
        DESCRIPTION
             "Invalid Time"
           --#TYPE      "Management Agent Event 17"
           --#SUMMARY   "Host %s : SCellName-TimeDate %s : EventCode %d : Description %s"
           --#ARGUMENTS {0,1,2,3,}
            --#SEVERITY  INFORMATIONAL
            --#TIMEINDEX 136
        ::= 136000017

   mngmtAgentTrap-18 TRAP-TYPE
        ENTERPRISE compaq
        VARIABLES  { hostName,
                     scellNameDateTime,
                     agentEventCode,
                     agentEventDescription }
        DESCRIPTION
             "Media is Inaccessible"
           --#TYPE      "Management Agent Event 18"
           --#SUMMARY   "Host %s : SCellName-TimeDate %s : EventCode %d : Description %s"
           --#ARGUMENTS {0,1,2,3,}
            --#SEVERITY  MINOR
            --#TIMEINDEX 136
        ::= 136000018

   mngmtAgentTrap-19 TRAP-TYPE
        ENTERPRISE compaq
        VARIABLES  { hostName,
                     scellNameDateTime,
                     agentEventCode,
                     agentEventDescription }
        DESCRIPTION
             "No Fibre Channel Port"
           --#TYPE      "Management Agent Event 19"
           --#SUMMARY   "Host %s : SCellName-TimeDate %s : EventCode %d : Description %s"
           --#ARGUMENTS {0,1,2,3,}
            --#SEVERITY  MINOR
            --#TIMEINDEX 136
        ::= 136000019

   mngmtAgentTrap-20 TRAP-TYPE
        ENTERPRISE compaq
        VARIABLES  { hostName,
                     scellNameDateTime,
                     agentEventCode,
                     agentEventDescription }
        DESCRIPTION
             "No Image"
           --#TYPE      "Management Agent Event 20"
           --#SUMMARY   "Host %s : SCellName-TimeDate %s : EventCode %d : Description %s"
           --#ARGUMENTS {0,1,2,3,}
            --#SEVERITY  INFORMATIONAL
            --#TIMEINDEX 136
        ::= 136000020

   mngmtAgentTrap-21 TRAP-TYPE
        ENTERPRISE compaq
        VARIABLES  { hostName,
                     scellNameDateTime,
                     agentEventCode,
                     agentEventDescription }
        DESCRIPTION
             "No Permission"
           --#TYPE      "Management Agent Event 21"
           --#SUMMARY   "Host %s : SCellName-TimeDate %s : EventCode %d : Description %s"
           --#ARGUMENTS {0,1,2,3,}
            --#SEVERITY  INFORMATIONAL
            --#TIMEINDEX 136
        ::= 136000021

   mngmtAgentTrap-22 TRAP-TYPE
        ENTERPRISE compaq
        VARIABLES  { hostName,
                     scellNameDateTime,
                     agentEventCode,
                     agentEventDescription }
        DESCRIPTION
             "Storage system not initialized"
           --#TYPE      "Management Agent Event 22"
           --#SUMMARY   "Host %s : SCellName-TimeDate %s : EventCode %d : Description %s"
           --#ARGUMENTS {0,1,2,3,}
            --#SEVERITY  INFORMATIONAL
            --#TIMEINDEX 136
        ::= 136000022

   mngmtAgentTrap-23 TRAP-TYPE
        ENTERPRISE compaq
        VARIABLES  { hostName,
                     scellNameDateTime,
                     agentEventCode,
                     agentEventDescription }
        DESCRIPTION
             "Not a Loop Port"
           --#TYPE      "Management Agent Event 23"
           --#SUMMARY   "Host %s : SCellName-TimeDate %s : EventCode %d : Description %s"
           --#ARGUMENTS {0,1,2,3,}
            --#SEVERITY  INFORMATIONAL
            --#TIMEINDEX 136
        ::= 136000023

   mngmtAgentTrap-24 TRAP-TYPE
        ENTERPRISE compaq
        VARIABLES  { hostName,
                     scellNameDateTime,
                     agentEventCode,
                     agentEventDescription }
        DESCRIPTION
             "Not a Participating Controller"
           --#TYPE      "Management Agent Event 24"
           --#SUMMARY   "Host %s : SCellName-TimeDate %s : EventCode %d : Description %s"
           --#ARGUMENTS {0,1,2,3,}
            --#SEVERITY  INFORMATIONAL
            --#TIMEINDEX 136
        ::= 136000024

   mngmtAgentTrap-25 TRAP-TYPE
        ENTERPRISE compaq
        VARIABLES  { hostName,
                     scellNameDateTime,
                     agentEventCode,
                     agentEventDescription }
        DESCRIPTION
             "Objects in your system are in use, and their state prevents the operation you wish to perform."
           --#TYPE      "Management Agent Event 25"
           --#SUMMARY   "Host %s : SCellName-TimeDate %s : EventCode %d : Description %s"
           --#ARGUMENTS {0,1,2,3,}
            --#SEVERITY  INFORMATIONAL
            --#TIMEINDEX 136
        ::= 136000025

   mngmtAgentTrap-26 TRAP-TYPE
        ENTERPRISE compaq
        VARIABLES  { hostName,
                     scellNameDateTime,
                     agentEventCode,
                     agentEventDescription }
        DESCRIPTION
             "Parameter Object Does Not Exist"
           --#TYPE      "Management Agent Event 26"
           --#SUMMARY   "Host %s : SCellName-TimeDate %s : EventCode %d : Description %s"
           --#ARGUMENTS {0,1,2,3,}
            --#SEVERITY  INFORMATIONAL
            --#TIMEINDEX 136
        ::= 136000026

   mngmtAgentTrap-27 TRAP-TYPE
        ENTERPRISE compaq
        VARIABLES  { hostName,
                     scellNameDateTime,
                     agentEventCode,
                     agentEventDescription }
        DESCRIPTION
             "Target Object Does Not Exist"
           --#TYPE      "Management Agent Event 27"
           --#SUMMARY   "Host %s : SCellName-TimeDate %s : EventCode %d : Description %s"
           --#ARGUMENTS {0,1,2,3,}
            --#SEVERITY  INFORMATIONAL
            --#TIMEINDEX 136
        ::= 136000027

   mngmtAgentTrap-28 TRAP-TYPE
        ENTERPRISE compaq
        VARIABLES  { hostName,
                     scellNameDateTime,
                     agentEventCode,
                     agentEventDescription }
        DESCRIPTION
             "Timeout"
           --#TYPE      "Management Agent Event 28"
           --#SUMMARY   "Host %s : SCellName-TimeDate %s : EventCode %d : Description %s"
           --#ARGUMENTS {0,1,2,3,}
            --#SEVERITY  INFORMATIONAL
            --#TIMEINDEX 136
        ::= 136000028

   mngmtAgentTrap-29 TRAP-TYPE
        ENTERPRISE compaq
        VARIABLES  { hostName,
                     scellNameDateTime,
                     agentEventCode,
                     agentEventDescription }
        DESCRIPTION
             "Unknown Id"
           --#TYPE      "Management Agent Event 29"
           --#SUMMARY   "Host %s : SCellName-TimeDate %s : EventCode %d : Description %s"
           --#ARGUMENTS {0,1,2,3,}
            --#SEVERITY  INFORMATIONAL
            --#TIMEINDEX 136
        ::= 136000029

   mngmtAgentTrap-30 TRAP-TYPE
        ENTERPRISE compaq
        VARIABLES  { hostName,
                     scellNameDateTime,
                     agentEventCode,
                     agentEventDescription }
        DESCRIPTION
             "Unknown Parameter Handle"
           --#TYPE      "Management Agent Event 30"
           --#SUMMARY   "Host %s : SCellName-TimeDate %s : EventCode %d : Description %s"
           --#ARGUMENTS {0,1,2,3,}
            --#SEVERITY  INFORMATIONAL
            --#TIMEINDEX 136
        ::= 136000030

   mngmtAgentTrap-31 TRAP-TYPE
        ENTERPRISE compaq
        VARIABLES  { hostName,
                     scellNameDateTime,
                     agentEventCode,
                     agentEventDescription }
        DESCRIPTION
             "Unrecoverable Media Error"
           --#TYPE      "Management Agent Event 31"
           --#SUMMARY   "Host %s : SCellName-TimeDate %s : EventCode %d : Description %s"
           --#ARGUMENTS {0,1,2,3,}
            --#SEVERITY  MAJOR
            --#TIMEINDEX 136
        ::= 136000031

   mngmtAgentTrap-32 TRAP-TYPE
        ENTERPRISE compaq
        VARIABLES  { hostName,
                     scellNameDateTime,
                     agentEventCode,
                     agentEventDescription }
        DESCRIPTION
             "Invalid State"
           --#TYPE      "Management Agent Event 32"
           --#SUMMARY   "Host %s : SCellName-TimeDate %s : EventCode %d : Description %s"
           --#ARGUMENTS {0,1,2,3,}
            --#SEVERITY  INFORMATIONAL
            --#TIMEINDEX 136
        ::= 136000032

   mngmtAgentTrap-33 TRAP-TYPE
        ENTERPRISE compaq
        VARIABLES  { hostName,
                     scellNameDateTime,
                     agentEventCode,
                     agentEventDescription }
        DESCRIPTION
             "Transport Error"
           --#TYPE      "Management Agent Event 33"
           --#SUMMARY   "Host %s : SCellName-TimeDate %s : EventCode %d : Description %s"
           --#ARGUMENTS {0,1,2,3,}
            --#SEVERITY  MINOR
            --#TIMEINDEX 136
        ::= 136000033

   mngmtAgentTrap-34 TRAP-TYPE
        ENTERPRISE compaq
        VARIABLES  { hostName,
                     scellNameDateTime,
                     agentEventCode,
                     agentEventDescription }
        DESCRIPTION
             "Volume is Missing"
           --#TYPE      "Management Agent Event 34"
           --#SUMMARY   "Host %s : SCellName-TimeDate %s : EventCode %d : Description %s"
           --#ARGUMENTS {0,1,2,3,}
            --#SEVERITY  MINOR
            --#TIMEINDEX 136
        ::= 136000034

   mngmtAgentTrap-35 TRAP-TYPE
        ENTERPRISE compaq
        VARIABLES  { hostName,
                     scellNameDateTime,
                     agentEventCode,
                     agentEventDescription }
        DESCRIPTION
             "Invalid Cursor"
           --#TYPE      "Management Agent Event 35"
           --#SUMMARY   "Host %s : SCellName-TimeDate %s : EventCode %d : Description %s"
           --#ARGUMENTS {0,1,2,3,}
            --#SEVERITY  INFORMATIONAL
            --#TIMEINDEX 136
        ::= 136000035

   mngmtAgentTrap-36 TRAP-TYPE
        ENTERPRISE compaq
        VARIABLES  { hostName,
                     scellNameDateTime,
                     agentEventCode,
                     agentEventDescription }
        DESCRIPTION
             "Invalid Target for the Operation"
           --#TYPE      "Management Agent Event 36"
           --#SUMMARY   "Host %s : SCellName-TimeDate %s : EventCode %d : Description %s"
           --#ARGUMENTS {0,1,2,3,}
            --#SEVERITY  INFORMATIONAL
            --#TIMEINDEX 136
        ::= 136000036

   mngmtAgentTrap-37 TRAP-TYPE
        ENTERPRISE compaq
        VARIABLES  { hostName,
                     scellNameDateTime,
                     agentEventCode,
                     agentEventDescription }
        DESCRIPTION
             "No More Events"
           --#TYPE      "Management Agent Event 37"
           --#SUMMARY   "Host %s : SCellName-TimeDate %s : EventCode %d : Description %s"
           --#ARGUMENTS {0,1,2,3,}
            --#SEVERITY  INFORMATIONAL
            --#TIMEINDEX 136
        ::= 136000037

   mngmtAgentTrap-38 TRAP-TYPE
        ENTERPRISE compaq
        VARIABLES  { hostName,
                     scellNameDateTime,
                     agentEventCode,
                     agentEventDescription }
        DESCRIPTION
             "Lock Busy"
           --#TYPE      "Management Agent Event 38"
           --#SUMMARY   "Host %s : SCellName-TimeDate %s : EventCode %d : Description %s"
           --#ARGUMENTS {0,1,2,3,}
            --#SEVERITY  INFORMATIONAL
            --#TIMEINDEX 136
        ::= 136000038

   mngmtAgentTrap-39 TRAP-TYPE
        ENTERPRISE compaq
        VARIABLES  { hostName,
                     scellNameDateTime,
                     agentEventCode,
                     agentEventDescription }
        DESCRIPTION
             "Time Not Set"
           --#TYPE      "Management Agent Event 39"
           --#SUMMARY   "Host %s : SCellName-TimeDate %s : EventCode %d : Description %s"
           --#ARGUMENTS {0,1,2,3,}
            --#SEVERITY  INFORMATIONAL
            --#TIMEINDEX 136
        ::= 136000039

   mngmtAgentTrap-40 TRAP-TYPE
        ENTERPRISE compaq
        VARIABLES  { hostName,
                     scellNameDateTime,
                     agentEventCode,
                     agentEventDescription }
        DESCRIPTION
             "Not a Supported Version"
           --#TYPE      "Management Agent Event 40"
           --#SUMMARY   "Host %s : SCellName-TimeDate %s : EventCode %d : Description %s"
           --#ARGUMENTS {0,1,2,3,}
            --#SEVERITY  INFORMATIONAL
            --#TIMEINDEX 136
        ::= 136000040

   mngmtAgentTrap-41 TRAP-TYPE
        ENTERPRISE compaq
        VARIABLES  { hostName,
                     scellNameDateTime,
                     agentEventCode,
                     agentEventDescription }
        DESCRIPTION
             "No Logical Disk for Vdisk"
           --#TYPE      "Management Agent Event 41"
           --#SUMMARY   "Host %s : SCellName-TimeDate %s : EventCode %d : Description %s"
           --#ARGUMENTS {0,1,2,3,}
            --#SEVERITY  INFORMATIONAL
            --#TIMEINDEX 136
        ::= 136000041

   mngmtAgentTrap-42 TRAP-TYPE
        ENTERPRISE compaq
        VARIABLES  { hostName,
                     scellNameDateTime,
                     agentEventCode,
                     agentEventDescription }
        DESCRIPTION
             "Logical disk Presented"
           --#TYPE      "Management Agent Event 42"
           --#SUMMARY   "Host %s : SCellName-TimeDate %s : EventCode %d : Description %s"
           --#ARGUMENTS {0,1,2,3,}
            --#SEVERITY  INFORMATIONAL
            --#TIMEINDEX 136
        ::= 136000042

   mngmtAgentTrap-43 TRAP-TYPE
        ENTERPRISE compaq
        VARIABLES  { hostName,
                     scellNameDateTime,
                     agentEventCode,
                     agentEventDescription }
        DESCRIPTION
             "Operation Denied On Slave"
           --#TYPE      "Management Agent Event 43"
           --#SUMMARY   "Host %s : SCellName-TimeDate %s : EventCode %d : Description %s"
           --#ARGUMENTS {0,1,2,3,}
            --#SEVERITY  MINOR
            --#TIMEINDEX 136
        ::= 136000043

   mngmtAgentTrap-44 TRAP-TYPE
        ENTERPRISE compaq
        VARIABLES  { hostName,
                     scellNameDateTime,
                     agentEventCode,
                     agentEventDescription }
        DESCRIPTION
             "Not licensed for data replication"
           --#TYPE      "Management Agent Event 44"
           --#SUMMARY   "Host %s : SCellName-TimeDate %s : EventCode %d : Description %s"
           --#ARGUMENTS {0,1,2,3,}
            --#SEVERITY  INFORMATIONAL
            --#TIMEINDEX 136
        ::= 136000044

   mngmtAgentTrap-45 TRAP-TYPE
        ENTERPRISE compaq
        VARIABLES  { hostName,
                     scellNameDateTime,
                     agentEventCode,
                     agentEventDescription }
        DESCRIPTION
             "Not DR group member"
           --#TYPE      "Management Agent Event 45"
           --#SUMMARY   "Host %s : SCellName-TimeDate %s : EventCode %d : Description %s"
           --#ARGUMENTS {0,1,2,3,}
            --#SEVERITY  INFORMATIONAL
            --#TIMEINDEX 136
        ::= 136000045

   mngmtAgentTrap-46 TRAP-TYPE
        ENTERPRISE compaq
        VARIABLES  { hostName,
                     scellNameDateTime,
                     agentEventCode,
                     agentEventDescription }
        DESCRIPTION
             "Invalid DR mode"
           --#TYPE      "Management Agent Event 46"
           --#SUMMARY   "Host %s : SCellName-TimeDate %s : EventCode %d : Description %s"
           --#ARGUMENTS {0,1,2,3,}
            --#SEVERITY  INFORMATIONAL
            --#TIMEINDEX 136
        ::= 136000046

   mngmtAgentTrap-47 TRAP-TYPE
        ENTERPRISE compaq
        VARIABLES  { hostName,
                     scellNameDateTime,
                     agentEventCode,
                     agentEventDescription }
        DESCRIPTION
             "The target DR member is in full copy, operation rejected"
           --#TYPE      "Management Agent Event 47"
           --#SUMMARY   "Host %s : SCellName-TimeDate %s : EventCode %d : Description %s"
           --#ARGUMENTS {0,1,2,3,}
            --#SEVERITY  INFORMATIONAL
            --#TIMEINDEX 136
        ::= 136000047

   mngmtAgentTrap-48 TRAP-TYPE
        ENTERPRISE compaq
        VARIABLES  { hostName,
                     scellNameDateTime,
                     agentEventCode,
                     agentEventDescription }
        DESCRIPTION
             "Security credentials needed. Please update your system's ID and password in the Storage System Access menu."
           --#TYPE      "Management Agent Event 48"
           --#SUMMARY   "Host %s : SCellName-TimeDate %s : EventCode %d : Description %s"
           --#ARGUMENTS {0,1,2,3,}
            --#SEVERITY  INFORMATIONAL
            --#TIMEINDEX 136
        ::= 136000048

   mngmtAgentTrap-49 TRAP-TYPE
        ENTERPRISE compaq
        VARIABLES  { hostName,
                     scellNameDateTime,
                     agentEventCode,
                     agentEventDescription }
        DESCRIPTION
             "Security credentials supplied were invalid. Please update your system's ID and password in the Storage System Access menu."
           --#TYPE      "Management Agent Event 49"
           --#SUMMARY   "Host %s : SCellName-TimeDate %s : EventCode %d : Description %s"
           --#ARGUMENTS {0,1,2,3,}
            --#SEVERITY  INFORMATIONAL
            --#TIMEINDEX 136
        ::= 136000049

   mngmtAgentTrap-50 TRAP-TYPE
        ENTERPRISE compaq
        VARIABLES  { hostName,
                     scellNameDateTime,
                     agentEventCode,
                     agentEventDescription }
        DESCRIPTION
             "Security credentials supplied were invalid. Please update your system's ID and password in the Storage System Access menu."
           --#TYPE      "Management Agent Event 50"
           --#SUMMARY   "Host %s : SCellName-TimeDate %s : EventCode %d : Description %s"
           --#ARGUMENTS {0,1,2,3,}
            --#SEVERITY  INFORMATIONAL
            --#TIMEINDEX 136
        ::= 136000050

   mngmtAgentTrap-51 TRAP-TYPE
        ENTERPRISE compaq
        VARIABLES  { hostName,
                     scellNameDateTime,
                     agentEventCode,
                     agentEventDescription }
        DESCRIPTION
             "Storage system connection down"
           --#TYPE      "Management Agent Event 51"
           --#SUMMARY   "Host %s : SCellName-TimeDate %s : EventCode %d : Description %s"
           --#ARGUMENTS {0,1,2,3,}
            --#SEVERITY  MINOR
            --#TIMEINDEX 136
        ::= 136000051

   mngmtAgentTrap-52 TRAP-TYPE
        ENTERPRISE compaq
        VARIABLES  { hostName,
                     scellNameDateTime,
                     agentEventCode,
                     agentEventDescription }
        DESCRIPTION
             "DR group empty"
           --#TYPE      "Management Agent Event 52"
           --#SUMMARY   "Host %s : SCellName-TimeDate %s : EventCode %d : Description %s"
           --#ARGUMENTS {0,1,2,3,}
            --#SEVERITY  INFORMATIONAL
            --#TIMEINDEX 136
        ::= 136000052

   mngmtAgentTrap-53 TRAP-TYPE
        ENTERPRISE compaq
        VARIABLES  { hostName,
                     scellNameDateTime,
                     agentEventCode,
                     agentEventDescription }
        DESCRIPTION
             "Incompatible attribute"
           --#TYPE      "Management Agent Event 53"
           --#SUMMARY   "Host %s : SCellName-TimeDate %s : EventCode %d : Description %s"
           --#ARGUMENTS {0,1,2,3,}
            --#SEVERITY  INFORMATIONAL
            --#TIMEINDEX 136
        ::= 136000053

   mngmtAgentTrap-54 TRAP-TYPE
        ENTERPRISE compaq
        VARIABLES  { hostName,
                     scellNameDateTime,
                     agentEventCode,
                     agentEventDescription }
        DESCRIPTION
             "Vdisk is a DR group member"
           --#TYPE      "Management Agent Event 54"
           --#SUMMARY   "Host %s : SCellName-TimeDate %s : EventCode %d : Description %s"
           --#ARGUMENTS {0,1,2,3,}
            --#SEVERITY  INFORMATIONAL
            --#TIMEINDEX 136
        ::= 136000054

   mngmtAgentTrap-55 TRAP-TYPE
        ENTERPRISE compaq
        VARIABLES  { hostName,
                     scellNameDateTime,
                     agentEventCode,
                     agentEventDescription }
        DESCRIPTION
             "Vdisk is a DR log unit"
           --#TYPE      "Management Agent Event 55"
           --#SUMMARY   "Host %s : SCellName-TimeDate %s : EventCode %d : Description %s"
           --#ARGUMENTS {0,1,2,3,}
            --#SEVERITY  INFORMATIONAL
            --#TIMEINDEX 136
        ::= 136000055

   mngmtAgentTrap-56 TRAP-TYPE
        ENTERPRISE compaq
        VARIABLES  { hostName,
                     scellNameDateTime,
                     agentEventCode,
                     agentEventDescription }
        DESCRIPTION
             "Cache batteries failed or missing."
           --#TYPE      "Management Agent Event 56"
           --#SUMMARY   "Host %s : SCellName-TimeDate %s : EventCode %d : Description %s"
           --#ARGUMENTS {0,1,2,3,}
            --#SEVERITY  INFORMATIONAL
            --#TIMEINDEX 136
        ::= 136000056

   mngmtAgentTrap-57 TRAP-TYPE
        ENTERPRISE compaq
        VARIABLES  { hostName,
                     scellNameDateTime,
                     agentEventCode,
                     agentEventDescription }
        DESCRIPTION
             "Vdisk is not presented"
           --#TYPE      "Management Agent Event 57"
           --#SUMMARY   "Host %s : SCellName-TimeDate %s : EventCode %d : Description %s"
           --#ARGUMENTS {0,1,2,3,}
            --#SEVERITY  INFORMATIONAL
            --#TIMEINDEX 136
        ::= 136000057

   mngmtAgentTrap-58 TRAP-TYPE
        ENTERPRISE compaq
        VARIABLES  { hostName,
                     scellNameDateTime,
                     agentEventCode,
                     agentEventDescription }
        DESCRIPTION
             "Other controller failed"
           --#TYPE      "Management Agent Event 58"
           --#SUMMARY   "Host %s : SCellName-TimeDate %s : EventCode %d : Description %s"
           --#ARGUMENTS {0,1,2,3,}
            --#SEVERITY  MINOR
            --#TIMEINDEX 136
        ::= 136000058

   mngmtAgentTrap-59 TRAP-TYPE
        ENTERPRISE compaq
        VARIABLES  { hostName,
                     scellNameDateTime,
                     agentEventCode,
                     agentEventDescription }
        DESCRIPTION
             "Maximum Number of Objects Exceeded."
           --#TYPE      "Management Agent Event 59"
           --#SUMMARY   "Host %s : SCellName-TimeDate %s : EventCode %d : Description %s"
           --#ARGUMENTS {0,1,2,3,}
            --#SEVERITY  INFORMATIONAL
            --#TIMEINDEX 136
        ::= 136000059

   mngmtAgentTrap-60 TRAP-TYPE
        ENTERPRISE compaq
        VARIABLES  { hostName,
                     scellNameDateTime,
                     agentEventCode,
                     agentEventDescription }
        DESCRIPTION
             "Max size exceeded"
           --#TYPE      "Management Agent Event 60"
           --#SUMMARY   "Host %s : SCellName-TimeDate %s : EventCode %d : Description %s"
           --#ARGUMENTS {0,1,2,3,}
            --#SEVERITY  INFORMATIONAL
            --#TIMEINDEX 136
        ::= 136000060

   mngmtAgentTrap-61 TRAP-TYPE
        ENTERPRISE compaq
        VARIABLES  { hostName,
                     scellNameDateTime,
                     agentEventCode,
                     agentEventDescription }
        DESCRIPTION
             "Password mismatch. Please update your system's password in the Storage System Access menu. Continued attempts to access this storage system with an incorrect password will disable management of this storage system."
           --#TYPE      "Management Agent Event 61"
           --#SUMMARY   "Host %s : SCellName-TimeDate %s : EventCode %d : Description %s"
           --#ARGUMENTS {0,1,2,3,}
            --#SEVERITY  INFORMATIONAL
            --#TIMEINDEX 136
        ::= 136000061

   mngmtAgentTrap-62 TRAP-TYPE
        ENTERPRISE compaq
        VARIABLES  { hostName,
                     scellNameDateTime,
                     agentEventCode,
                     agentEventDescription }
        DESCRIPTION
             "DR group is merging"
           --#TYPE      "Management Agent Event 62"
           --#SUMMARY   "Host %s : SCellName-TimeDate %s : EventCode %d : Description %s"
           --#ARGUMENTS {0,1,2,3,}
            --#SEVERITY  INFORMATIONAL
            --#TIMEINDEX 136
        ::= 136000062

   mngmtAgentTrap-63 TRAP-TYPE
        ENTERPRISE compaq
        VARIABLES  { hostName,
                     scellNameDateTime,
                     agentEventCode,
                     agentEventDescription }
        DESCRIPTION
             "DR group is logging"
           --#TYPE      "Management Agent Event 63"
           --#SUMMARY   "Host %s : SCellName-TimeDate %s : EventCode %d : Description %s"
           --#ARGUMENTS {0,1,2,3,}
            --#SEVERITY  INFORMATIONAL
            --#TIMEINDEX 136
        ::= 136000063

   mngmtAgentTrap-64 TRAP-TYPE
        ENTERPRISE compaq
        VARIABLES  { hostName,
                     scellNameDateTime,
                     agentEventCode,
                     agentEventDescription }
        DESCRIPTION
             "Connection is suspended"
           --#TYPE      "Management Agent Event 64"
           --#SUMMARY   "Host %s : SCellName-TimeDate %s : EventCode %d : Description %s"
           --#ARGUMENTS {0,1,2,3,}
            --#SEVERITY  INFORMATIONAL
            --#TIMEINDEX 136
        ::= 136000064

   mngmtAgentTrap-65 TRAP-TYPE
        ENTERPRISE compaq
        VARIABLES  { hostName,
                     scellNameDateTime,
                     agentEventCode,
                     agentEventDescription }
        DESCRIPTION
             "Bad image header"
           --#TYPE      "Management Agent Event 65"
           --#SUMMARY   "Host %s : SCellName-TimeDate %s : EventCode %d : Description %s"
           --#ARGUMENTS {0,1,2,3,}
            --#SEVERITY  INFORMATIONAL
            --#TIMEINDEX 136
        ::= 136000065

   mngmtAgentTrap-66 TRAP-TYPE
        ENTERPRISE compaq
        VARIABLES  { hostName,
                     scellNameDateTime,
                     agentEventCode,
                     agentEventDescription }
        DESCRIPTION
             "Bad image"
           --#TYPE      "Management Agent Event 66"
           --#SUMMARY   "Host %s : SCellName-TimeDate %s : EventCode %d : Description %s"
           --#ARGUMENTS {0,1,2,3,}
            --#SEVERITY  INFORMATIONAL
            --#TIMEINDEX 136
        ::= 136000066

   mngmtAgentTrap-67 TRAP-TYPE
        ENTERPRISE compaq
        VARIABLES  { hostName,
                     scellNameDateTime,
                     agentEventCode,
                     agentEventDescription }
        DESCRIPTION
             "Image too large"
           --#TYPE      "Management Agent Event 67"
           --#SUMMARY   "Host %s : SCellName-TimeDate %s : EventCode %d : Description %s"
           --#ARGUMENTS {0,1,2,3,}
            --#SEVERITY  INFORMATIONAL
            --#TIMEINDEX 136
        ::= 136000067

   mngmtAgentTrap-68 TRAP-TYPE
        ENTERPRISE compaq
        VARIABLES  { hostName,
                     scellNameDateTime,
                     agentEventCode,
                     agentEventDescription }
        DESCRIPTION
             "EMU not available"
           --#TYPE      "Management Agent Event 68"
           --#SUMMARY   "Host %s : SCellName-TimeDate %s : EventCode %d : Description %s"
           --#ARGUMENTS {0,1,2,3,}
            --#SEVERITY  INFORMATIONAL
            --#TIMEINDEX 136
        ::= 136000068

   mngmtAgentTrap-69 TRAP-TYPE
        ENTERPRISE compaq
        VARIABLES  { hostName,
                     scellNameDateTime,
                     agentEventCode,
                     agentEventDescription }
        DESCRIPTION
             "EMU indefinite delay"
           --#TYPE      "Management Agent Event 69"
           --#SUMMARY   "Host %s : SCellName-TimeDate %s : EventCode %d : Description %s"
           --#ARGUMENTS {0,1,2,3,}
            --#SEVERITY  INFORMATIONAL
            --#TIMEINDEX 136
        ::= 136000069

   mngmtAgentTrap-70 TRAP-TYPE
        ENTERPRISE compaq
        VARIABLES  { hostName,
                     scellNameDateTime,
                     agentEventCode,
                     agentEventDescription }
        DESCRIPTION
             "Image incompatible with system configuration. Version conflict in upgrade or downgrade not allowed."
           --#TYPE      "Management Agent Event 70"
           --#SUMMARY   "Host %s : SCellName-TimeDate %s : EventCode %d : Description %s"
           --#ARGUMENTS {0,1,2,3,}
            --#SEVERITY  INFORMATIONAL
            --#TIMEINDEX 136
        ::= 136000070

   mngmtAgentTrap-71 TRAP-TYPE
        ENTERPRISE compaq
        VARIABLES  { hostName,
                     scellNameDateTime,
                     agentEventCode,
                     agentEventDescription }
        DESCRIPTION
             "Bad image segment"
           --#TYPE      "Management Agent Event 71"
           --#SUMMARY   "Host %s : SCellName-TimeDate %s : EventCode %d : Description %s"
           --#ARGUMENTS {0,1,2,3,}
            --#SEVERITY  INFORMATIONAL
            --#TIMEINDEX 136
        ::= 136000071

   mngmtAgentTrap-72 TRAP-TYPE
        ENTERPRISE compaq
        VARIABLES  { hostName,
                     scellNameDateTime,
                     agentEventCode,
                     agentEventDescription }
        DESCRIPTION
             "Image already loaded"
           --#TYPE      "Management Agent Event 72"
           --#SUMMARY   "Host %s : SCellName-TimeDate %s : EventCode %d : Description %s"
           --#ARGUMENTS {0,1,2,3,}
            --#SEVERITY  INFORMATIONAL
            --#TIMEINDEX 136
        ::= 136000072

   mngmtAgentTrap-73 TRAP-TYPE
        ENTERPRISE compaq
        VARIABLES  { hostName,
                     scellNameDateTime,
                     agentEventCode,
                     agentEventDescription }
        DESCRIPTION
             "Image Write Error"
           --#TYPE      "Management Agent Event 73"
           --#SUMMARY   "Host %s : SCellName-TimeDate %s : EventCode %d : Description %s"
           --#ARGUMENTS {0,1,2,3,}
            --#SEVERITY  INFORMATIONAL
            --#TIMEINDEX 136
        ::= 136000073

   mngmtAgentTrap-74 TRAP-TYPE
        ENTERPRISE compaq
        VARIABLES  { hostName,
                     scellNameDateTime,
                     agentEventCode,
                     agentEventDescription }
        DESCRIPTION
             "Destination virtual disk has a sharing relationship with a snapshot, mirrorclone or a snapclone."
           --#TYPE      "Management Agent Event 74"
           --#SUMMARY   "Host %s : SCellName-TimeDate %s : EventCode %d : Description %s"
           --#ARGUMENTS {0,1,2,3,}
            --#SEVERITY  INFORMATIONAL
            --#TIMEINDEX 136
        ::= 136000074

   mngmtAgentTrap-75 TRAP-TYPE
        ENTERPRISE compaq
        VARIABLES  { hostName,
                     scellNameDateTime,
                     agentEventCode,
                     agentEventDescription }
        DESCRIPTION
             "Bad Image Size"
           --#TYPE      "Management Agent Event 75"
           --#SUMMARY   "Host %s : SCellName-TimeDate %s : EventCode %d : Description %s"
           --#ARGUMENTS {0,1,2,3,}
            --#SEVERITY  INFORMATIONAL
            --#TIMEINDEX 136
        ::= 136000075

   mngmtAgentTrap-76 TRAP-TYPE
        ENTERPRISE compaq
        VARIABLES  { hostName,
                     scellNameDateTime,
                     agentEventCode,
                     agentEventDescription }
        DESCRIPTION
             "The controller is temporarily busy and it cannot process the request.  Retry the request later."
           --#TYPE      "Management Agent Event 76"
           --#SUMMARY   "Host %s : SCellName-TimeDate %s : EventCode %d : Description %s"
           --#ARGUMENTS {0,1,2,3,}
            --#SEVERITY  INFORMATIONAL
            --#TIMEINDEX 136
        ::= 136000076

   mngmtAgentTrap-77 TRAP-TYPE
        ENTERPRISE compaq
        VARIABLES  { hostName,
                     scellNameDateTime,
                     agentEventCode,
                     agentEventDescription }
        DESCRIPTION
             "Volume Failure Predicted"
           --#TYPE      "Management Agent Event 77"
           --#SUMMARY   "Host %s : SCellName-TimeDate %s : EventCode %d : Description %s"
           --#ARGUMENTS {0,1,2,3,}
            --#SEVERITY  CRITICAL
            --#TIMEINDEX 136
        ::= 136000077

   mngmtAgentTrap-78 TRAP-TYPE
        ENTERPRISE compaq
        VARIABLES  { hostName,
                     scellNameDateTime,
                     agentEventCode,
                     agentEventDescription }
        DESCRIPTION
             "Invalid object condition for this command."
           --#TYPE      "Management Agent Event 78"
           --#SUMMARY   "Host %s : SCellName-TimeDate %s : EventCode %d : Description %s"
           --#ARGUMENTS {0,1,2,3,}
            --#SEVERITY  INFORMATIONAL
            --#TIMEINDEX 136
        ::= 136000078

   mngmtAgentTrap-79 TRAP-TYPE
        ENTERPRISE compaq
        VARIABLES  { hostName,
                     scellNameDateTime,
                     agentEventCode,
                     agentEventDescription }
        DESCRIPTION
             "The requested operation is currently not allowed. A snapshot or clone of the original virtual disk is in the process of being deleted. Please try again later."
           --#TYPE      "Management Agent Event 79"
           --#SUMMARY   "Host %s : SCellName-TimeDate %s : EventCode %d : Description %s"
           --#ARGUMENTS {0,1,2,3,}
            --#SEVERITY  INFORMATIONAL
            --#TIMEINDEX 136
        ::= 136000079

   mngmtAgentTrap-80 TRAP-TYPE
        ENTERPRISE compaq
        VARIABLES  { hostName,
                     scellNameDateTime,
                     agentEventCode,
                     agentEventDescription }
        DESCRIPTION
             "Invalid Volume Usage"
           --#TYPE      "Management Agent Event 80"
           --#SUMMARY   "Host %s : SCellName-TimeDate %s : EventCode %d : Description %s"
           --#ARGUMENTS {0,1,2,3,}
            --#SEVERITY  INFORMATIONAL
            --#TIMEINDEX 136
        ::= 136000080

   mngmtAgentTrap-81 TRAP-TYPE
        ENTERPRISE compaq
        VARIABLES  { hostName,
                     scellNameDateTime,
                     agentEventCode,
                     agentEventDescription }
        DESCRIPTION
             "Minimum Volumes In Disk Group"
           --#TYPE      "Management Agent Event 81"
           --#SUMMARY   "Host %s : SCellName-TimeDate %s : EventCode %d : Description %s"
           --#ARGUMENTS {0,1,2,3,}
            --#SEVERITY  INFORMATIONAL
            --#TIMEINDEX 136
        ::= 136000081

   mngmtAgentTrap-82 TRAP-TYPE
        ENTERPRISE compaq
        VARIABLES  { hostName,
                     scellNameDateTime,
                     agentEventCode,
                     agentEventDescription }
        DESCRIPTION
             "Shutdown In Progress"
           --#TYPE      "Management Agent Event 82"
           --#SUMMARY   "Host %s : SCellName-TimeDate %s : EventCode %d : Description %s"
           --#ARGUMENTS {0,1,2,3,}
            --#SEVERITY  INFORMATIONAL
            --#TIMEINDEX 136
        ::= 136000082

   mngmtAgentTrap-83 TRAP-TYPE
        ENTERPRISE compaq
        VARIABLES  { hostName,
                     scellNameDateTime,
                     agentEventCode,
                     agentEventDescription }
        DESCRIPTION
             "Controller API Not Ready, Try Again Later"
           --#TYPE      "Management Agent Event 83"
           --#SUMMARY   "Host %s : SCellName-TimeDate %s : EventCode %d : Description %s"
           --#ARGUMENTS {0,1,2,3,}
            --#SEVERITY  INFORMATIONAL
            --#TIMEINDEX 136
        ::= 136000083

   mngmtAgentTrap-84 TRAP-TYPE
        ENTERPRISE compaq
        VARIABLES  { hostName,
                     scellNameDateTime,
                     agentEventCode,
                     agentEventDescription }
        DESCRIPTION
             "Is Snapshot"
           --#TYPE      "Management Agent Event 84"
           --#SUMMARY   "Host %s : SCellName-TimeDate %s : EventCode %d : Description %s"
           --#ARGUMENTS {0,1,2,3,}
            --#SEVERITY  INFORMATIONAL
            --#TIMEINDEX 136
        ::= 136000084

   mngmtAgentTrap-85 TRAP-TYPE
        ENTERPRISE compaq
        VARIABLES  { hostName,
                     scellNameDateTime,
                     agentEventCode,
                     agentEventDescription }
        DESCRIPTION
             "Cannot add or remove DR group member. Mirror cache must be active for this Vdisk. Check controller cache condition."
           --#TYPE      "Management Agent Event 85"
           --#SUMMARY   "Host %s : SCellName-TimeDate %s : EventCode %d : Description %s"
           --#ARGUMENTS {0,1,2,3,}
            --#SEVERITY  INFORMATIONAL
            --#TIMEINDEX 136
        ::= 136000085

   mngmtAgentTrap-86 TRAP-TYPE
        ENTERPRISE compaq
        VARIABLES  { hostName,
                     scellNameDateTime,
                     agentEventCode,
                     agentEventDescription }
        DESCRIPTION
             "Inoperative"
           --#TYPE      "Management Agent Event 86"
           --#SUMMARY   "Host %s : SCellName-TimeDate %s : EventCode %d : Description %s"
           --#ARGUMENTS {0,1,2,3,}
            --#SEVERITY  INFORMATIONAL
            --#TIMEINDEX 136
        ::= 136000086

   mngmtAgentTrap-87 TRAP-TYPE
        ENTERPRISE compaq
        VARIABLES  { hostName,
                     scellNameDateTime,
                     agentEventCode,
                     agentEventDescription }
        DESCRIPTION
             "Disk group inoperative or disks in group less than minimum."
           --#TYPE      "Management Agent Event 87"
           --#SUMMARY   "Host %s : SCellName-TimeDate %s : EventCode %d : Description %s"
           --#ARGUMENTS {0,1,2,3,}
            --#SEVERITY  MINOR
            --#TIMEINDEX 136
        ::= 136000087

   mngmtAgentTrap-88 TRAP-TYPE
        ENTERPRISE compaq
        VARIABLES  { hostName,
                     scellNameDateTime,
                     agentEventCode,
                     agentEventDescription }
        DESCRIPTION
             "HP P6000 Command View has detected this array as inoperative. Contact HP Service for assistance."
           --#TYPE      "Management Agent Event 88"
           --#SUMMARY   "Host %s : SCellName-TimeDate %s : EventCode %d : Description %s"
           --#ARGUMENTS {0,1,2,3,}
            --#SEVERITY  CRITICAL
            --#TIMEINDEX 136
        ::= 136000088

   mngmtAgentTrap-89 TRAP-TYPE
        ENTERPRISE compaq
        VARIABLES  { hostName,
                     scellNameDateTime,
                     agentEventCode,
                     agentEventDescription }
        DESCRIPTION
             "Failsafe Locked"
           --#TYPE      "Management Agent Event 89"
           --#SUMMARY   "Host %s : SCellName-TimeDate %s : EventCode %d : Description %s"
           --#ARGUMENTS {0,1,2,3,}
            --#SEVERITY  INFORMATIONAL
            --#TIMEINDEX 136
        ::= 136000089

   mngmtAgentTrap-90 TRAP-TYPE
        ENTERPRISE compaq
        VARIABLES  { hostName,
                     scellNameDateTime,
                     agentEventCode,
                     agentEventDescription }
        DESCRIPTION
             "Data Flush Incomplete"
           --#TYPE      "Management Agent Event 90"
           --#SUMMARY   "Host %s : SCellName-TimeDate %s : EventCode %d : Description %s"
           --#ARGUMENTS {0,1,2,3,}
            --#SEVERITY  MINOR
            --#TIMEINDEX 136
        ::= 136000090

   mngmtAgentTrap-91 TRAP-TYPE
        ENTERPRISE compaq
        VARIABLES  { hostName,
                     scellNameDateTime,
                     agentEventCode,
                     agentEventDescription }
        DESCRIPTION
             "Redundancy Mirrored Inoperative"
           --#TYPE      "Management Agent Event 91"
           --#SUMMARY   "Host %s : SCellName-TimeDate %s : EventCode %d : Description %s"
           --#ARGUMENTS {0,1,2,3,}
            --#SEVERITY  INFORMATIONAL
            --#TIMEINDEX 136
        ::= 136000091

   mngmtAgentTrap-92 TRAP-TYPE
        ENTERPRISE compaq
        VARIABLES  { hostName,
                     scellNameDateTime,
                     agentEventCode,
                     agentEventDescription }
        DESCRIPTION
             "Duplicate LUN"
           --#TYPE      "Management Agent Event 92"
           --#SUMMARY   "Host %s : SCellName-TimeDate %s : EventCode %d : Description %s"
           --#ARGUMENTS {0,1,2,3,}
            --#SEVERITY  INFORMATIONAL
            --#TIMEINDEX 136
        ::= 136000092

   mngmtAgentTrap-93 TRAP-TYPE
        ENTERPRISE compaq
        VARIABLES  { hostName,
                     scellNameDateTime,
                     agentEventCode,
                     agentEventDescription }
        DESCRIPTION
             "Other remote controller failed"
           --#TYPE      "Management Agent Event 93"
           --#SUMMARY   "Host %s : SCellName-TimeDate %s : EventCode %d : Description %s"
           --#ARGUMENTS {0,1,2,3,}
            --#SEVERITY  MINOR
            --#TIMEINDEX 136
        ::= 136000093

   mngmtAgentTrap-94 TRAP-TYPE
        ENTERPRISE compaq
        VARIABLES  { hostName,
                     scellNameDateTime,
                     agentEventCode,
                     agentEventDescription }
        DESCRIPTION
             "Unknown remote Vdisk"
           --#TYPE      "Management Agent Event 94"
           --#SUMMARY   "Host %s : SCellName-TimeDate %s : EventCode %d : Description %s"
           --#ARGUMENTS {0,1,2,3,}
            --#SEVERITY  INFORMATIONAL
            --#TIMEINDEX 136
        ::= 136000094

   mngmtAgentTrap-95 TRAP-TYPE
        ENTERPRISE compaq
        VARIABLES  { hostName,
                     scellNameDateTime,
                     agentEventCode,
                     agentEventDescription }
        DESCRIPTION
             "Unknown remote DR group"
           --#TYPE      "Management Agent Event 95"
           --#SUMMARY   "Host %s : SCellName-TimeDate %s : EventCode %d : Description %s"
           --#ARGUMENTS {0,1,2,3,}
            --#SEVERITY  INFORMATIONAL
            --#TIMEINDEX 136
        ::= 136000095

   mngmtAgentTrap-96 TRAP-TYPE
        ENTERPRISE compaq
        VARIABLES  { hostName,
                     scellNameDateTime,
                     agentEventCode,
                     agentEventDescription }
        DESCRIPTION
             "PLDMC failed"
           --#TYPE      "Management Agent Event 96"
           --#SUMMARY   "Host %s : SCellName-TimeDate %s : EventCode %d : Description %s"
           --#ARGUMENTS {0,1,2,3,}
            --#SEVERITY  CRITICAL
            --#TIMEINDEX 136
        ::= 136000096

   mngmtAgentTrap-97 TRAP-TYPE
        ENTERPRISE compaq
        VARIABLES  { hostName,
                     scellNameDateTime,
                     agentEventCode,
                     agentEventDescription }
        DESCRIPTION
             "Storage system could not be locked. System busy. Try command again."
           --#TYPE      "Management Agent Event 97"
           --#SUMMARY   "Host %s : SCellName-TimeDate %s : EventCode %d : Description %s"
           --#ARGUMENTS {0,1,2,3,}
            --#SEVERITY  CRITICAL
            --#TIMEINDEX 136
        ::= 136000097

   mngmtAgentTrap-98 TRAP-TYPE
        ENTERPRISE compaq
        VARIABLES  { hostName,
                     scellNameDateTime,
                     agentEventCode,
                     agentEventDescription }
        DESCRIPTION
             "Error on remote storage system."
           --#TYPE      "Management Agent Event 98"
           --#SUMMARY   "Host %s : SCellName-TimeDate %s : EventCode %d : Description %s"
           --#ARGUMENTS {0,1,2,3,}
            --#SEVERITY  INFORMATIONAL
            --#TIMEINDEX 136
        ::= 136000098

   mngmtAgentTrap-99 TRAP-TYPE
        ENTERPRISE compaq
        VARIABLES  { hostName,
                     scellNameDateTime,
                     agentEventCode,
                     agentEventDescription }
        DESCRIPTION
             "The DR operation can only be completed when the source-destination connection is down. If you are doing a destination DR deletion, make sure the connection link to the source DR system is down or do a failover operation to make this system the source"
           --#TYPE      "Management Agent Event 99"
           --#SUMMARY   "Host %s : SCellName-TimeDate %s : EventCode %d : Description %s"
           --#ARGUMENTS {0,1,2,3,}
            --#SEVERITY  INFORMATIONAL
            --#TIMEINDEX 136
        ::= 136000099

   mngmtAgentTrap-100 TRAP-TYPE
        ENTERPRISE compaq
        VARIABLES  { hostName,
                     scellNameDateTime,
                     agentEventCode,
                     agentEventDescription }
        DESCRIPTION
             "Login required - password changed."
           --#TYPE      "Management Agent Event 100"
           --#SUMMARY   "Host %s : SCellName-TimeDate %s : EventCode %d : Description %s"
           --#ARGUMENTS {0,1,2,3,}
            --#SEVERITY  INFORMATIONAL
            --#TIMEINDEX 136
        ::= 136000100

   mngmtAgentTrap-101 TRAP-TYPE
        ENTERPRISE compaq
        VARIABLES  { hostName,
                     scellNameDateTime,
                     agentEventCode,
                     agentEventDescription }
        DESCRIPTION
             "Numerous login attempts have been detected that uses an incorrect password. Please update your system's password in the Storage System Access menu."
           --#TYPE      "Management Agent Event 101"
           --#SUMMARY   "Host %s : SCellName-TimeDate %s : EventCode %d : Description %s"
           --#ARGUMENTS {0,1,2,3,}
            --#SEVERITY  INFORMATIONAL
            --#TIMEINDEX 136
        ::= 136000101

   mngmtAgentTrap-102 TRAP-TYPE
        ENTERPRISE compaq
        VARIABLES  { hostName,
                     scellNameDateTime,
                     agentEventCode,
                     agentEventDescription }
        DESCRIPTION
             "Invalid cookie"
           --#TYPE      "Management Agent Event 102"
           --#SUMMARY   "Host %s : SCellName-TimeDate %s : EventCode %d : Description %s"
           --#ARGUMENTS {0,1,2,3,}
            --#SEVERITY  INFORMATIONAL
            --#TIMEINDEX 136
        ::= 136000102

   mngmtAgentTrap-103 TRAP-TYPE
        ENTERPRISE compaq
        VARIABLES  { hostName,
                     scellNameDateTime,
                     agentEventCode,
                     agentEventDescription }
        DESCRIPTION
             "Login timed out"
           --#TYPE      "Management Agent Event 103"
           --#SUMMARY   "Host %s : SCellName-TimeDate %s : EventCode %d : Description %s"
           --#ARGUMENTS {0,1,2,3,}
            --#SEVERITY  INFORMATIONAL
            --#TIMEINDEX 136
        ::= 136000103

   mngmtAgentTrap-104 TRAP-TYPE
        ENTERPRISE compaq
        VARIABLES  { hostName,
                     scellNameDateTime,
                     agentEventCode,
                     agentEventDescription }
        DESCRIPTION
             "Max snapshot depth reached"
           --#TYPE      "Management Agent Event 104"
           --#SUMMARY   "Host %s : SCellName-TimeDate %s : EventCode %d : Description %s"
           --#ARGUMENTS {0,1,2,3,}
            --#SEVERITY  INFORMATIONAL
            --#TIMEINDEX 136
        ::= 136000104

   mngmtAgentTrap-105 TRAP-TYPE
        ENTERPRISE compaq
        VARIABLES  { hostName,
                     scellNameDateTime,
                     agentEventCode,
                     agentEventDescription }
        DESCRIPTION
             "Attribute mismatch"
           --#TYPE      "Management Agent Event 105"
           --#SUMMARY   "Host %s : SCellName-TimeDate %s : EventCode %d : Description %s"
           --#ARGUMENTS {0,1,2,3,}
            --#SEVERITY  INFORMATIONAL
            --#TIMEINDEX 136
        ::= 136000105

   mngmtAgentTrap-106 TRAP-TYPE
        ENTERPRISE compaq
        VARIABLES  { hostName,
                     scellNameDateTime,
                     agentEventCode,
                     agentEventDescription }
        DESCRIPTION
             "The password has been set in HP P6000 Command View. The same password still needs to be set in the controllers."
           --#TYPE      "Management Agent Event 106"
           --#SUMMARY   "Host %s : SCellName-TimeDate %s : EventCode %d : Description %s"
           --#ARGUMENTS {0,1,2,3,}
            --#SEVERITY  INFORMATIONAL
            --#TIMEINDEX 136
        ::= 136000106

   mngmtAgentTrap-107 TRAP-TYPE
        ENTERPRISE compaq
        VARIABLES  { hostName,
                     scellNameDateTime,
                     agentEventCode,
                     agentEventDescription }
        DESCRIPTION
             "Not host port"
           --#TYPE      "Management Agent Event 107"
           --#SUMMARY   "Host %s : SCellName-TimeDate %s : EventCode %d : Description %s"
           --#ARGUMENTS {0,1,2,3,}
            --#SEVERITY  INFORMATIONAL
            --#TIMEINDEX 136
        ::= 136000107

   mngmtAgentTrap-108 TRAP-TYPE
        ENTERPRISE compaq
        VARIABLES  { hostName,
                     scellNameDateTime,
                     agentEventCode,
                     agentEventDescription }
        DESCRIPTION
             "Duplicate Lun WWID"
           --#TYPE      "Management Agent Event 108"
           --#SUMMARY   "Host %s : SCellName-TimeDate %s : EventCode %d : Description %s"
           --#ARGUMENTS {0,1,2,3,}
            --#SEVERITY  INFORMATIONAL
            --#TIMEINDEX 136
        ::= 136000108

   mngmtAgentTrap-109 TRAP-TYPE
        ENTERPRISE compaq
        VARIABLES  { hostName,
                     scellNameDateTime,
                     agentEventCode,
                     agentEventDescription }
        DESCRIPTION
             "System Inoperative"
           --#TYPE      "Management Agent Event 109"
           --#SUMMARY   "Host %s : SCellName-TimeDate %s : EventCode %d : Description %s"
           --#ARGUMENTS {0,1,2,3,}
            --#SEVERITY  INFORMATIONAL
            --#TIMEINDEX 136
        ::= 136000109

   mngmtAgentTrap-110 TRAP-TYPE
        ENTERPRISE compaq
        VARIABLES  { hostName,
                     scellNameDateTime,
                     agentEventCode,
                     agentEventDescription }
        DESCRIPTION
             "SnapClone Active"
           --#TYPE      "Management Agent Event 110"
           --#SUMMARY   "Host %s : SCellName-TimeDate %s : EventCode %d : Description %s"
           --#ARGUMENTS {0,1,2,3,}
            --#SEVERITY  INFORMATIONAL
            --#TIMEINDEX 136
        ::= 136000110

   mngmtAgentTrap-111 TRAP-TYPE
        ENTERPRISE compaq
        VARIABLES  { hostName,
                     scellNameDateTime,
                     agentEventCode,
                     agentEventDescription }
        DESCRIPTION
             "Emu Load Busy"
           --#TYPE      "Management Agent Event 111"
           --#SUMMARY   "Host %s : SCellName-TimeDate %s : EventCode %d : Description %s"
           --#ARGUMENTS {0,1,2,3,}
            --#SEVERITY  INFORMATIONAL
            --#TIMEINDEX 136
        ::= 136000111

   mngmtAgentTrap-112 TRAP-TYPE
        ENTERPRISE compaq
        VARIABLES  { hostName,
                     scellNameDateTime,
                     agentEventCode,
                     agentEventDescription }
        DESCRIPTION
             "Duplicate User Name"
           --#TYPE      "Management Agent Event 112"
           --#SUMMARY   "Host %s : SCellName-TimeDate %s : EventCode %d : Description %s"
           --#ARGUMENTS {0,1,2,3,}
            --#SEVERITY  INFORMATIONAL
            --#TIMEINDEX 136
        ::= 136000112

   mngmtAgentTrap-113 TRAP-TYPE
        ENTERPRISE compaq
        VARIABLES  { hostName,
                     scellNameDateTime,
                     agentEventCode,
                     agentEventDescription }
        DESCRIPTION
             "Drive Reserved For Code Load"
           --#TYPE      "Management Agent Event 113"
           --#SUMMARY   "Host %s : SCellName-TimeDate %s : EventCode %d : Description %s"
           --#ARGUMENTS {0,1,2,3,}
            --#SEVERITY  INFORMATIONAL
            --#TIMEINDEX 136
        ::= 136000113

   mngmtAgentTrap-114 TRAP-TYPE
        ENTERPRISE compaq
        VARIABLES  { hostName,
                     scellNameDateTime,
                     agentEventCode,
                     agentEventDescription }
        DESCRIPTION
             "Already Presented"
           --#TYPE      "Management Agent Event 114"
           --#SUMMARY   "Host %s : SCellName-TimeDate %s : EventCode %d : Description %s"
           --#ARGUMENTS {0,1,2,3,}
            --#SEVERITY  INFORMATIONAL
            --#TIMEINDEX 136
        ::= 136000114

   mngmtAgentTrap-115 TRAP-TYPE
        ENTERPRISE compaq
        VARIABLES  { hostName,
                     scellNameDateTime,
                     agentEventCode,
                     agentEventDescription }
        DESCRIPTION
             "Invalid remote storage system"
           --#TYPE      "Management Agent Event 115"
           --#SUMMARY   "Host %s : SCellName-TimeDate %s : EventCode %d : Description %s"
           --#ARGUMENTS {0,1,2,3,}
            --#SEVERITY  INFORMATIONAL
            --#TIMEINDEX 136
        ::= 136000115

   mngmtAgentTrap-116 TRAP-TYPE
        ENTERPRISE compaq
        VARIABLES  { hostName,
                     scellNameDateTime,
                     agentEventCode,
                     agentEventDescription }
        DESCRIPTION
             "The internal lock needed to execute this command could not be obtained. If this error occurred during a DR group failover please make sure both source and destination are actively managed by this instance of HP P6000 Command View and retry the operation."
           --#TYPE      "Management Agent Event 116"
           --#SUMMARY   "Host %s : SCellName-TimeDate %s : EventCode %d : Description %s"
           --#ARGUMENTS {0,1,2,3,}
            --#SEVERITY  INFORMATIONAL
            --#TIMEINDEX 136
        ::= 136000116

   mngmtAgentTrap-117 TRAP-TYPE
        ENTERPRISE compaq
        VARIABLES  { hostName,
                     scellNameDateTime,
                     agentEventCode,
                     agentEventDescription }
        DESCRIPTION
             "Maximum Number of Members Exceeded"
           --#TYPE      "Management Agent Event 117"
           --#SUMMARY   "Host %s : SCellName-TimeDate %s : EventCode %d : Description %s"
           --#ARGUMENTS {0,1,2,3,}
            --#SEVERITY  INFORMATIONAL
            --#TIMEINDEX 136
        ::= 136000117

   mngmtAgentTrap-118 TRAP-TYPE
        ENTERPRISE compaq
        VARIABLES  { hostName,
                     scellNameDateTime,
                     agentEventCode,
                     agentEventDescription }
        DESCRIPTION
             "Max Destinations"
           --#TYPE      "Management Agent Event 118"
           --#SUMMARY   "Host %s : SCellName-TimeDate %s : EventCode %d : Description %s"
           --#ARGUMENTS {0,1,2,3,}
            --#SEVERITY  INFORMATIONAL
            --#TIMEINDEX 136
        ::= 136000118

   mngmtAgentTrap-119 TRAP-TYPE
        ENTERPRISE compaq
        VARIABLES  { hostName,
                     scellNameDateTime,
                     agentEventCode,
                     agentEventDescription }
        DESCRIPTION
             "Empty User Name"
           --#TYPE      "Management Agent Event 119"
           --#SUMMARY   "Host %s : SCellName-TimeDate %s : EventCode %d : Description %s"
           --#ARGUMENTS {0,1,2,3,}
            --#SEVERITY  INFORMATIONAL
            --#TIMEINDEX 136
        ::= 136000119

   mngmtAgentTrap-120 TRAP-TYPE
        ENTERPRISE compaq
        VARIABLES  { hostName,
                     scellNameDateTime,
                     agentEventCode,
                     agentEventDescription }
        DESCRIPTION
             "Storage system already initialized"
           --#TYPE      "Management Agent Event 120"
           --#SUMMARY   "Host %s : SCellName-TimeDate %s : EventCode %d : Description %s"
           --#ARGUMENTS {0,1,2,3,}
            --#SEVERITY  INFORMATIONAL
            --#TIMEINDEX 136
        ::= 136000120

   mngmtAgentTrap-121 TRAP-TYPE
        ENTERPRISE compaq
        VARIABLES  { hostName,
                     scellNameDateTime,
                     agentEventCode,
                     agentEventDescription }
        DESCRIPTION
             "Already Open"
           --#TYPE      "Management Agent Event 121"
           --#SUMMARY   "Host %s : SCellName-TimeDate %s : EventCode %d : Description %s"
           --#ARGUMENTS {0,1,2,3,}
            --#SEVERITY  INFORMATIONAL
            --#TIMEINDEX 136
        ::= 136000121

   mngmtAgentTrap-122 TRAP-TYPE
        ENTERPRISE compaq
        VARIABLES  { hostName,
                     scellNameDateTime,
                     agentEventCode,
                     agentEventDescription }
        DESCRIPTION
             "Session Not Open"
           --#TYPE      "Management Agent Event 122"
           --#SUMMARY   "Host %s : SCellName-TimeDate %s : EventCode %d : Description %s"
           --#ARGUMENTS {0,1,2,3,}
            --#SEVERITY  INFORMATIONAL
            --#TIMEINDEX 136
        ::= 136000122

   mngmtAgentTrap-123 TRAP-TYPE
        ENTERPRISE compaq
        VARIABLES  { hostName,
                     scellNameDateTime,
                     agentEventCode,
                     agentEventDescription }
        DESCRIPTION
             "Not Marked Inoperative"
           --#TYPE      "Management Agent Event 123"
           --#SUMMARY   "Host %s : SCellName-TimeDate %s : EventCode %d : Description %s"
           --#ARGUMENTS {0,1,2,3,}
            --#SEVERITY  INFORMATIONAL
            --#TIMEINDEX 136
        ::= 136000123

   mngmtAgentTrap-124 TRAP-TYPE
        ENTERPRISE compaq
        VARIABLES  { hostName,
                     scellNameDateTime,
                     agentEventCode,
                     agentEventDescription }
        DESCRIPTION
             "Media Not Available"
           --#TYPE      "Management Agent Event 124"
           --#SUMMARY   "Host %s : SCellName-TimeDate %s : EventCode %d : Description %s"
           --#ARGUMENTS {0,1,2,3,}
            --#SEVERITY  INFORMATIONAL
            --#TIMEINDEX 136
        ::= 136000124

   mngmtAgentTrap-125 TRAP-TYPE
        ENTERPRISE compaq
        VARIABLES  { hostName,
                     scellNameDateTime,
                     agentEventCode,
                     agentEventDescription }
        DESCRIPTION
             "Battery System Failed"
           --#TYPE      "Management Agent Event 125"
           --#SUMMARY   "Host %s : SCellName-TimeDate %s : EventCode %d : Description %s"
           --#ARGUMENTS {0,1,2,3,}
            --#SEVERITY  INFORMATIONAL
            --#TIMEINDEX 136
        ::= 136000125

   mngmtAgentTrap-126 TRAP-TYPE
        ENTERPRISE compaq
        VARIABLES  { hostName,
                     scellNameDateTime,
                     agentEventCode,
                     agentEventDescription }
        DESCRIPTION
             "DR Group Member Is Cache Data Lost"
           --#TYPE      "Management Agent Event 126"
           --#SUMMARY   "Host %s : SCellName-TimeDate %s : EventCode %d : Description %s"
           --#ARGUMENTS {0,1,2,3,}
            --#SEVERITY  INFORMATIONAL
            --#TIMEINDEX 136
        ::= 136000126

   mngmtAgentTrap-127 TRAP-TYPE
        ENTERPRISE compaq
        VARIABLES  { hostName,
                     scellNameDateTime,
                     agentEventCode,
                     agentEventDescription }
        DESCRIPTION
             "The resource needed to execute the request is in use. The operation can be retried later."
           --#TYPE      "Management Agent Event 127"
           --#SUMMARY   "Host %s : SCellName-TimeDate %s : EventCode %d : Description %s"
           --#ARGUMENTS {0,1,2,3,}
            --#SEVERITY  INFORMATIONAL
            --#TIMEINDEX 136
        ::= 136000127

   mngmtAgentTrap-128 TRAP-TYPE
        ENTERPRISE compaq
        VARIABLES  { hostName,
                     scellNameDateTime,
                     agentEventCode,
                     agentEventDescription }
        DESCRIPTION
             "OCP Error"
           --#TYPE      "Management Agent Event 128"
           --#SUMMARY   "Host %s : SCellName-TimeDate %s : EventCode %d : Description %s"
           --#ARGUMENTS {0,1,2,3,}
            --#SEVERITY  INFORMATIONAL
            --#TIMEINDEX 136
        ::= 136000128

   mngmtAgentTrap-129 TRAP-TYPE
        ENTERPRISE compaq
        VARIABLES  { hostName,
                     scellNameDateTime,
                     agentEventCode,
                     agentEventDescription }
        DESCRIPTION
             "Mirror Offline"
           --#TYPE      "Management Agent Event 129"
           --#SUMMARY   "Host %s : SCellName-TimeDate %s : EventCode %d : Description %s"
           --#ARGUMENTS {0,1,2,3,}
            --#SEVERITY  INFORMATIONAL
            --#TIMEINDEX 136
        ::= 136000129

   mngmtAgentTrap-130 TRAP-TYPE
        ENTERPRISE compaq
        VARIABLES  { hostName,
                     scellNameDateTime,
                     agentEventCode,
                     agentEventDescription }
        DESCRIPTION
             "This operation cannot be completed if failsafe mode is enabled."
           --#TYPE      "Management Agent Event 130"
           --#SUMMARY   "Host %s : SCellName-TimeDate %s : EventCode %d : Description %s"
           --#ARGUMENTS {0,1,2,3,}
            --#SEVERITY  INFORMATIONAL
            --#TIMEINDEX 136
        ::= 136000130

   mngmtAgentTrap-131 TRAP-TYPE
        ENTERPRISE compaq
        VARIABLES  { hostName,
                     scellNameDateTime,
                     agentEventCode,
                     agentEventDescription }
        DESCRIPTION
             "Drive firmware load abort due to Raid0 virtual disk(s)."
           --#TYPE      "Management Agent Event 131"
           --#SUMMARY   "Host %s : SCellName-TimeDate %s : EventCode %d : Description %s"
           --#ARGUMENTS {0,1,2,3,}
            --#SEVERITY  INFORMATIONAL
            --#TIMEINDEX 136
        ::= 136000131

   mngmtAgentTrap-132 TRAP-TYPE
        ENTERPRISE compaq
        VARIABLES  { hostName,
                     scellNameDateTime,
                     agentEventCode,
                     agentEventDescription }
        DESCRIPTION
             "Fibre channel ports are unavailable."
           --#TYPE      "Management Agent Event 132"
           --#SUMMARY   "Host %s : SCellName-TimeDate %s : EventCode %d : Description %s"
           --#ARGUMENTS {0,1,2,3,}
            --#SEVERITY  INFORMATIONAL
            --#TIMEINDEX 136
        ::= 136000132

   mngmtAgentTrap-133 TRAP-TYPE
        ENTERPRISE compaq
        VARIABLES  { hostName,
                     scellNameDateTime,
                     agentEventCode,
                     agentEventDescription }
        DESCRIPTION
             "The storage system has reached its maximum number of DR relationship."
           --#TYPE      "Management Agent Event 133"
           --#SUMMARY   "Host %s : SCellName-TimeDate %s : EventCode %d : Description %s"
           --#ARGUMENTS {0,1,2,3,}
            --#SEVERITY  INFORMATIONAL
            --#TIMEINDEX 136
        ::= 136000133

   mngmtAgentTrap-134 TRAP-TYPE
        ENTERPRISE compaq
        VARIABLES  { hostName,
                     scellNameDateTime,
                     agentEventCode,
                     agentEventDescription }
        DESCRIPTION
             "The requested DEFP level cannot be supported."
           --#TYPE      "Management Agent Event 134"
           --#SUMMARY   "Host %s : SCellName-TimeDate %s : EventCode %d : Description %s"
           --#ARGUMENTS {0,1,2,3,}
            --#SEVERITY  INFORMATIONAL
            --#TIMEINDEX 136
        ::= 136000134

   mngmtAgentTrap-141 TRAP-TYPE
        ENTERPRISE compaq
        VARIABLES  { hostName,
                     scellNameDateTime,
                     agentEventCode,
                     agentEventDescription }
        DESCRIPTION
             "DILX is running."
           --#TYPE      "Management Agent Event 141"
           --#SUMMARY   "Host %s : SCellName-TimeDate %s : EventCode %d : Description %s"
           --#ARGUMENTS {0,1,2,3,}
            --#SEVERITY  INFORMATIONAL
            --#TIMEINDEX 136
        ::= 136000141

   mngmtAgentTrap-142 TRAP-TYPE
        ENTERPRISE compaq
        VARIABLES  { hostName,
                     scellNameDateTime,
                     agentEventCode,
                     agentEventDescription }
        DESCRIPTION
             "DILX is not running."
           --#TYPE      "Management Agent Event 142"
           --#SUMMARY   "Host %s : SCellName-TimeDate %s : EventCode %d : Description %s"
           --#ARGUMENTS {0,1,2,3,}
            --#SEVERITY  INFORMATIONAL
            --#TIMEINDEX 136
        ::= 136000142

   mngmtAgentTrap-148 TRAP-TYPE
        ENTERPRISE compaq
        VARIABLES  { hostName,
                     scellNameDateTime,
                     agentEventCode,
                     agentEventDescription }
        DESCRIPTION
             "The Id specified is invalid."
           --#TYPE      "Management Agent Event 148"
           --#SUMMARY   "Host %s : SCellName-TimeDate %s : EventCode %d : Description %s"
           --#ARGUMENTS {0,1,2,3,}
            --#SEVERITY  INFORMATIONAL
            --#TIMEINDEX 136
        ::= 136000148

   mngmtAgentTrap-180 TRAP-TYPE
        ENTERPRISE compaq
        VARIABLES  { hostName,
                     scellNameDateTime,
                     agentEventCode,
                     agentEventDescription }
        DESCRIPTION
             "One or both controllers does not have the required 512 MB of memory."
           --#TYPE      "Management Agent Event 180"
           --#SUMMARY   "Host %s : SCellName-TimeDate %s : EventCode %d : Description %s"
           --#ARGUMENTS {0,1,2,3,}
            --#SEVERITY  INFORMATIONAL
            --#TIMEINDEX 136
        ::= 136000180

   mngmtAgentTrap-181 TRAP-TYPE
        ENTERPRISE compaq
        VARIABLES  { hostName,
                     scellNameDateTime,
                     agentEventCode,
                     agentEventDescription }
        DESCRIPTION
             "Not enough disk drives of requested type to create the disk group."
           --#TYPE      "Management Agent Event 181"
           --#SUMMARY   "Host %s : SCellName-TimeDate %s : EventCode %d : Description %s"
           --#ARGUMENTS {0,1,2,3,}
            --#SEVERITY  INFORMATIONAL
            --#TIMEINDEX 136
        ::= 136000181

   mngmtAgentTrap-182 TRAP-TYPE
        ENTERPRISE compaq
        VARIABLES  { hostName,
                     scellNameDateTime,
                     agentEventCode,
                     agentEventDescription }
        DESCRIPTION
             "Drive Types of Disk and Disk group are different."
           --#TYPE      "Management Agent Event 182"
           --#SUMMARY   "Host %s : SCellName-TimeDate %s : EventCode %d : Description %s"
           --#ARGUMENTS {0,1,2,3,}
            --#SEVERITY  INFORMATIONAL
            --#TIMEINDEX 136
        ::= 136000182

   mngmtAgentTrap-183 TRAP-TYPE
        ENTERPRISE compaq
        VARIABLES  { hostName,
                     scellNameDateTime,
                     agentEventCode,
                     agentEventDescription }
        DESCRIPTION
             "Operation already in ON state."
           --#TYPE      "Management Agent Event 183"
           --#SUMMARY   "Host %s : SCellName-TimeDate %s : EventCode %d : Description %s"
           --#ARGUMENTS {0,1,2,3,}
            --#SEVERITY  INFORMATIONAL
            --#TIMEINDEX 136
        ::= 136000183

   mngmtAgentTrap-184 TRAP-TYPE
        ENTERPRISE compaq
        VARIABLES  { hostName,
                     scellNameDateTime,
                     agentEventCode,
                     agentEventDescription }
        DESCRIPTION
             "Operation already in OFF state."
           --#TYPE      "Management Agent Event 184"
           --#SUMMARY   "Host %s : SCellName-TimeDate %s : EventCode %d : Description %s"
           --#ARGUMENTS {0,1,2,3,}
            --#SEVERITY  INFORMATIONAL
            --#TIMEINDEX 136
        ::= 136000184

   mngmtAgentTrap-195 TRAP-TYPE
        ENTERPRISE compaq
        VARIABLES  { hostName,
                     scellNameDateTime,
                     agentEventCode,
                     agentEventDescription }
        DESCRIPTION
             "The logical disk type is not correct for the requested operation."
           --#TYPE      "Management Agent Event 195"
           --#SUMMARY   "Host %s : SCellName-TimeDate %s : EventCode %d : Description %s"
           --#ARGUMENTS {0,1,2,3,}
            --#SEVERITY  INFORMATIONAL
            --#TIMEINDEX 136
        ::= 136000195

   mngmtAgentTrap-196 TRAP-TYPE
        ENTERPRISE compaq
        VARIABLES  { hostName,
                     scellNameDateTime,
                     agentEventCode,
                     agentEventDescription }
        DESCRIPTION
             "The source logical disk and empty container are in different disk groups"
           --#TYPE      "Management Agent Event 196"
           --#SUMMARY   "Host %s : SCellName-TimeDate %s : EventCode %d : Description %s"
           --#ARGUMENTS {0,1,2,3,}
            --#SEVERITY  INFORMATIONAL
            --#TIMEINDEX 136
        ::= 136000196

   mngmtAgentTrap-197 TRAP-TYPE
        ENTERPRISE compaq
        VARIABLES  { hostName,
                     scellNameDateTime,
                     agentEventCode,
                     agentEventDescription }
        DESCRIPTION
             "This operation is not allowed on an empty container"
           --#TYPE      "Management Agent Event 197"
           --#SUMMARY   "Host %s : SCellName-TimeDate %s : EventCode %d : Description %s"
           --#ARGUMENTS {0,1,2,3,}
            --#SEVERITY  INFORMATIONAL
            --#TIMEINDEX 136
        ::= 136000197

   mngmtAgentTrap-198 TRAP-TYPE
        ENTERPRISE compaq
        VARIABLES  { hostName,
                     scellNameDateTime,
                     agentEventCode,
                     agentEventDescription }
        DESCRIPTION
             "Unsupported operation for AA mode"
           --#TYPE      "Management Agent Event 198"
           --#SUMMARY   "Host %s : SCellName-TimeDate %s : EventCode %d : Description %s"
           --#ARGUMENTS {0,1,2,3,}
            --#SEVERITY  INFORMATIONAL
            --#TIMEINDEX 136
        ::= 136000198

   mngmtAgentTrap-199 TRAP-TYPE
        ENTERPRISE compaq
        VARIABLES  { hostName,
                     scellNameDateTime,
                     agentEventCode,
                     agentEventDescription }
        DESCRIPTION
             "The redundancy specified for this snap is not allowed.  A redundancy level less than or equal to the parent must be selected."
           --#TYPE      "Management Agent Event 199"
           --#SUMMARY   "Host %s : SCellName-TimeDate %s : EventCode %d : Description %s"
           --#ARGUMENTS {0,1,2,3,}
            --#SEVERITY  INFORMATIONAL
            --#TIMEINDEX 136
        ::= 136000199

   mngmtAgentTrap-200 TRAP-TYPE
        ENTERPRISE compaq
        VARIABLES  { hostName,
                     scellNameDateTime,
                     agentEventCode,
                     agentEventDescription }
        DESCRIPTION
             "All snapshots in the same virtual disk family must be the same redundancy level"
           --#TYPE      "Management Agent Event 200"
           --#SUMMARY   "Host %s : SCellName-TimeDate %s : EventCode %d : Description %s"
           --#ARGUMENTS {0,1,2,3,}
            --#SEVERITY  INFORMATIONAL
            --#TIMEINDEX 136
        ::= 136000200

   mngmtAgentTrap-201 TRAP-TYPE
        ENTERPRISE compaq
        VARIABLES  { hostName,
                     scellNameDateTime,
                     agentEventCode,
                     agentEventDescription }
        DESCRIPTION
             "The local storage system has no available path to the remote storage system."
           --#TYPE      "Management Agent Event 201"
           --#SUMMARY   "Host %s : SCellName-TimeDate %s : EventCode %d : Description %s"
           --#ARGUMENTS {0,1,2,3,}
            --#SEVERITY  INFORMATIONAL
            --#TIMEINDEX 136
        ::= 136000201

   mngmtAgentTrap-202 TRAP-TYPE
        ENTERPRISE compaq
        VARIABLES  { hostName,
                     scellNameDateTime,
                     agentEventCode,
                     agentEventDescription }
        DESCRIPTION
             "The DR Group does not exist"
           --#TYPE      "Management Agent Event 202"
           --#SUMMARY   "Host %s : SCellName-TimeDate %s : EventCode %d : Description %s"
           --#ARGUMENTS {0,1,2,3,}
            --#SEVERITY  INFORMATIONAL
            --#TIMEINDEX 136
        ::= 136000202

   mngmtAgentTrap-203 TRAP-TYPE
        ENTERPRISE compaq
        VARIABLES  { hostName,
                     scellNameDateTime,
                     agentEventCode,
                     agentEventDescription }
        DESCRIPTION
             "Invalid Asynch Log Size"
           --#TYPE      "Management Agent Event 203"
           --#SUMMARY   "Host %s : SCellName-TimeDate %s : EventCode %d : Description %s"
           --#ARGUMENTS {0,1,2,3,}
            --#SEVERITY  INFORMATIONAL
            --#TIMEINDEX 136
        ::= 136000203

   mngmtAgentTrap-204 TRAP-TYPE
        ENTERPRISE compaq
        VARIABLES  { hostName,
                     scellNameDateTime,
                     agentEventCode,
                     agentEventDescription }
        DESCRIPTION
             "Asynch Log failure"
           --#TYPE      "Management Agent Event 204"
           --#SUMMARY   "Host %s : SCellName-TimeDate %s : EventCode %d : Description %s"
           --#ARGUMENTS {0,1,2,3,}
            --#SEVERITY  INFORMATIONAL
            --#TIMEINDEX 136
        ::= 136000204

   mngmtAgentTrap-205 TRAP-TYPE
        ENTERPRISE compaq
        VARIABLES  { hostName,
                     scellNameDateTime,
                     agentEventCode,
                     agentEventDescription }
        DESCRIPTION
             "Operation denied.  Not in synchronous mode."
           --#TYPE      "Management Agent Event 205"
           --#SUMMARY   "Host %s : SCellName-TimeDate %s : EventCode %d : Description %s"
           --#ARGUMENTS {0,1,2,3,}
            --#SEVERITY  INFORMATIONAL
            --#TIMEINDEX 136
        ::= 136000205

   mngmtAgentTrap-206 TRAP-TYPE
        ENTERPRISE compaq
        VARIABLES  { hostName,
                     scellNameDateTime,
                     agentEventCode,
                     agentEventDescription }
        DESCRIPTION
             "An instant restore is in progress."
           --#TYPE      "Management Agent Event 206"
           --#SUMMARY   "Host %s : SCellName-TimeDate %s : EventCode %d : Description %s"
           --#ARGUMENTS {0,1,2,3,}
            --#SEVERITY  INFORMATIONAL
            --#TIMEINDEX 136
        ::= 136000206

   mngmtAgentTrap-207 TRAP-TYPE
        ENTERPRISE compaq
        VARIABLES  { hostName,
                     scellNameDateTime,
                     agentEventCode,
                     agentEventDescription }
        DESCRIPTION
             "Operation not allowed on a mirror clone."
           --#TYPE      "Management Agent Event 207"
           --#SUMMARY   "Host %s : SCellName-TimeDate %s : EventCode %d : Description %s"
           --#ARGUMENTS {0,1,2,3,}
            --#SEVERITY  INFORMATIONAL
            --#TIMEINDEX 136
        ::= 136000207

   mngmtAgentTrap-208 TRAP-TYPE
        ENTERPRISE compaq
        VARIABLES  { hostName,
                     scellNameDateTime,
                     agentEventCode,
                     agentEventDescription }
        DESCRIPTION
             "The mirror clone is synchronizing."
           --#TYPE      "Management Agent Event 208"
           --#SUMMARY   "Host %s : SCellName-TimeDate %s : EventCode %d : Description %s"
           --#ARGUMENTS {0,1,2,3,}
            --#SEVERITY  INFORMATIONAL
            --#TIMEINDEX 136
        ::= 136000208

   mngmtAgentTrap-209 TRAP-TYPE
        ENTERPRISE compaq
        VARIABLES  { hostName,
                     scellNameDateTime,
                     agentEventCode,
                     agentEventDescription }
        DESCRIPTION
             "Operation denied.  The virtual disk has a mirror clone."
           --#TYPE      "Management Agent Event 209"
           --#SUMMARY   "Host %s : SCellName-TimeDate %s : EventCode %d : Description %s"
           --#ARGUMENTS {0,1,2,3,}
            --#SEVERITY  INFORMATIONAL
            --#TIMEINDEX 136
        ::= 136000209

   mngmtAgentTrap-210 TRAP-TYPE
        ENTERPRISE compaq
        VARIABLES  { hostName,
                     scellNameDateTime,
                     agentEventCode,
                     agentEventDescription }
        DESCRIPTION
             "Unknown Remote Node."
           --#TYPE      "Management Agent Event 210"
           --#SUMMARY   "Host %s : SCellName-TimeDate %s : EventCode %d : Description %s"
           --#ARGUMENTS {0,1,2,3,}
            --#SEVERITY  INFORMATIONAL
            --#TIMEINDEX 136
        ::= 136000210

   mngmtAgentTrap-211 TRAP-TYPE
        ENTERPRISE compaq
        VARIABLES  { hostName,
                     scellNameDateTime,
                     agentEventCode,
                     agentEventDescription }
        DESCRIPTION
             "Instant Restore Mode incompatible."
           --#TYPE      "Management Agent Event 211"
           --#SUMMARY   "Host %s : SCellName-TimeDate %s : EventCode %d : Description %s"
           --#ARGUMENTS {0,1,2,3,}
            --#SEVERITY  INFORMATIONAL
            --#TIMEINDEX 136
        ::= 136000211

   mngmtAgentTrap-212 TRAP-TYPE
        ENTERPRISE compaq
        VARIABLES  { hostName,
                     scellNameDateTime,
                     agentEventCode,
                     agentEventDescription }
        DESCRIPTION
             "The DRM group is not suspended."
           --#TYPE      "Management Agent Event 212"
           --#SUMMARY   "Host %s : SCellName-TimeDate %s : EventCode %d : Description %s"
           --#ARGUMENTS {0,1,2,3,}
            --#SEVERITY  INFORMATIONAL
            --#TIMEINDEX 136
        ::= 136000212

   mngmtAgentTrap-213 TRAP-TYPE
        ENTERPRISE compaq
        VARIABLES  { hostName,
                     scellNameDateTime,
                     agentEventCode,
                     agentEventDescription }
        DESCRIPTION
             "The virtual disks are not in the same snapshot tree."
           --#TYPE      "Management Agent Event 213"
           --#SUMMARY   "Host %s : SCellName-TimeDate %s : EventCode %d : Description %s"
           --#ARGUMENTS {0,1,2,3,}
            --#SEVERITY  INFORMATIONAL
            --#TIMEINDEX 136
        ::= 136000213

   mngmtAgentTrap-214 TRAP-TYPE
        ENTERPRISE compaq
        VARIABLES  { hostName,
                     scellNameDateTime,
                     agentEventCode,
                     agentEventDescription }
        DESCRIPTION
             "The operation is not allowed on an original virtual disk."
           --#TYPE      "Management Agent Event 214"
           --#SUMMARY   "Host %s : SCellName-TimeDate %s : EventCode %d : Description %s"
           --#ARGUMENTS {0,1,2,3,}
            --#SEVERITY  INFORMATIONAL
            --#TIMEINDEX 136
        ::= 136000214

   mngmtAgentTrap-215 TRAP-TYPE
        ENTERPRISE compaq
        VARIABLES  { hostName,
                     scellNameDateTime,
                     agentEventCode,
                     agentEventDescription }
        DESCRIPTION
             "Recontructing or reverting is in progress."
           --#TYPE      "Management Agent Event 215"
           --#SUMMARY   "Host %s : SCellName-TimeDate %s : EventCode %d : Description %s"
           --#ARGUMENTS {0,1,2,3,}
            --#SEVERITY  INFORMATIONAL
            --#TIMEINDEX 136
        ::= 136000215

   mngmtAgentTrap-216 TRAP-TYPE
        ENTERPRISE compaq
        VARIABLES  { hostName,
                     scellNameDateTime,
                     agentEventCode,
                     agentEventDescription }
        DESCRIPTION
             "Not enough quorum disks for redundancy to do drive codeload."
           --#TYPE      "Management Agent Event 216"
           --#SUMMARY   "Host %s : SCellName-TimeDate %s : EventCode %d : Description %s"
           --#ARGUMENTS {0,1,2,3,}
            --#SEVERITY  INFORMATIONAL
            --#TIMEINDEX 136
        ::= 136000216

   mngmtAgentTrap-217 TRAP-TYPE
        ENTERPRISE compaq
        VARIABLES  { hostName,
                     scellNameDateTime,
                     agentEventCode,
                     agentEventDescription }
        DESCRIPTION
             "The requested operation has already been completed."
           --#TYPE      "Management Agent Event 217"
           --#SUMMARY   "Host %s : SCellName-TimeDate %s : EventCode %d : Description %s"
           --#ARGUMENTS {0,1,2,3,}
            --#SEVERITY  INFORMATIONAL
            --#TIMEINDEX 136
        ::= 136000217

   mngmtAgentTrap-218 TRAP-TYPE
        ENTERPRISE compaq
        VARIABLES  { hostName,
                     scellNameDateTime,
                     agentEventCode,
                     agentEventDescription }
        DESCRIPTION
             "A drive is in maintenance mode."
           --#TYPE      "Management Agent Event 218"
           --#SUMMARY   "Host %s : SCellName-TimeDate %s : EventCode %d : Description %s"
           --#ARGUMENTS {0,1,2,3,}
            --#SEVERITY  INFORMATIONAL
            --#TIMEINDEX 136
        ::= 136000218

   mngmtAgentTrap-219 TRAP-TYPE
        ENTERPRISE compaq
        VARIABLES  { hostName,
                     scellNameDateTime,
                     agentEventCode,
                     agentEventDescription }
        DESCRIPTION
             "Invalid snapshots are being deleted."
           --#TYPE      "Management Agent Event 219"
           --#SUMMARY   "Host %s : SCellName-TimeDate %s : EventCode %d : Description %s"
           --#ARGUMENTS {0,1,2,3,}
            --#SEVERITY  INFORMATIONAL
            --#TIMEINDEX 136
        ::= 136000219

   mngmtAgentTrap-220 TRAP-TYPE
        ENTERPRISE compaq
        VARIABLES  { hostName,
                     scellNameDateTime,
                     agentEventCode,
                     agentEventDescription }
        DESCRIPTION
             "Temporary Sync set."
           --#TYPE      "Management Agent Event 220"
           --#SUMMARY   "Host %s : SCellName-TimeDate %s : EventCode %d : Description %s"
           --#ARGUMENTS {0,1,2,3,}
            --#SEVERITY  INFORMATIONAL
            --#TIMEINDEX 136
        ::= 136000220

   mngmtAgentTrap-221 TRAP-TYPE
        ENTERPRISE compaq
        VARIABLES  { hostName,
                     scellNameDateTime,
                     agentEventCode,
                     agentEventDescription }
        DESCRIPTION
             "Maximum number of simultaneous restores has been exceeded."
           --#TYPE      "Management Agent Event 221"
           --#SUMMARY   "Host %s : SCellName-TimeDate %s : EventCode %d : Description %s"
           --#ARGUMENTS {0,1,2,3,}
            --#SEVERITY  INFORMATIONAL
            --#TIMEINDEX 136
        ::= 136000221

   mngmtAgentTrap-222 TRAP-TYPE
        ENTERPRISE compaq
        VARIABLES  { hostName,
                     scellNameDateTime,
                     agentEventCode,
                     agentEventDescription }
        DESCRIPTION
             "There is no current lock or the lock that was in place had expired and was freed."
           --#TYPE      "Management Agent Event 222"
           --#SUMMARY   "Host %s : SCellName-TimeDate %s : EventCode %d : Description %s"
           --#ARGUMENTS {0,1,2,3,}
            --#SEVERITY  INFORMATIONAL
            --#TIMEINDEX 136
        ::= 136000222

   mngmtAgentTrap-223 TRAP-TYPE
        ENTERPRISE compaq
        VARIABLES  { hostName,
                     scellNameDateTime,
                     agentEventCode,
                     agentEventDescription }
        DESCRIPTION
             "Another user has a valid lock and it does not match the lock id set with this command."
           --#TYPE      "Management Agent Event 223"
           --#SUMMARY   "Host %s : SCellName-TimeDate %s : EventCode %d : Description %s"
           --#ARGUMENTS {0,1,2,3,}
            --#SEVERITY  INFORMATIONAL
            --#TIMEINDEX 136
        ::= 136000223

   mngmtAgentTrap-224 TRAP-TYPE
        ENTERPRISE compaq
        VARIABLES  { hostName,
                     scellNameDateTime,
                     agentEventCode,
                     agentEventDescription }
        DESCRIPTION
             "Can't enter failsafe mode for the DR group because the 'Auto Suspend on Fullcopy' attribute is enabled."
           --#TYPE      "Management Agent Event 224"
           --#SUMMARY   "Host %s : SCellName-TimeDate %s : EventCode %d : Description %s"
           --#ARGUMENTS {0,1,2,3,}
            --#SEVERITY  INFORMATIONAL
            --#TIMEINDEX 136
        ::= 136000224

   mngmtAgentTrap-225 TRAP-TYPE
        ENTERPRISE compaq
        VARIABLES  { hostName,
                     scellNameDateTime,
                     agentEventCode,
                     agentEventDescription }
        DESCRIPTION
             "One or more of the attach operations in a group of attaches has failed."
           --#TYPE      "Management Agent Event 225"
           --#SUMMARY   "Host %s : SCellName-TimeDate %s : EventCode %d : Description %s"
           --#ARGUMENTS {0,1,2,3,}
            --#SEVERITY  INFORMATIONAL
            --#TIMEINDEX 136
        ::= 136000225

   mngmtAgentTrap-226 TRAP-TYPE
        ENTERPRISE compaq
        VARIABLES  { hostName,
                     scellNameDateTime,
                     agentEventCode,
                     agentEventDescription }
        DESCRIPTION
             "Data replication log shrink in progress."
           --#TYPE      "Management Agent Event 226"
           --#SUMMARY   "Host %s : SCellName-TimeDate %s : EventCode %d : Description %s"
           --#ARGUMENTS {0,1,2,3,}
            --#SEVERITY  INFORMATIONAL
            --#TIMEINDEX 136
        ::= 136000226

   mngmtAgentTrap-227 TRAP-TYPE
        ENTERPRISE compaq
        VARIABLES  { hostName,
                     scellNameDateTime,
                     agentEventCode,
                     agentEventDescription }
        DESCRIPTION
             "Data replication log deallocation in progress."
           --#TYPE      "Management Agent Event 227"
           --#SUMMARY   "Host %s : SCellName-TimeDate %s : EventCode %d : Description %s"
           --#ARGUMENTS {0,1,2,3,}
            --#SEVERITY  INFORMATIONAL
            --#TIMEINDEX 136
        ::= 136000227

   mngmtAgentTrap-228 TRAP-TYPE
        ENTERPRISE compaq
        VARIABLES  { hostName,
                     scellNameDateTime,
                     agentEventCode,
                     agentEventDescription }
        DESCRIPTION
             "The WWN is reserved internally by the system."
           --#TYPE      "Management Agent Event 228"
           --#SUMMARY   "Host %s : SCellName-TimeDate %s : EventCode %d : Description %s"
           --#ARGUMENTS {0,1,2,3,}
            --#SEVERITY  INFORMATIONAL
            --#TIMEINDEX 136
        ::= 136000228

   mngmtAgentTrap-229 TRAP-TYPE
        ENTERPRISE compaq
        VARIABLES  { hostName,
                     scellNameDateTime,
                     agentEventCode,
                     agentEventDescription }
        DESCRIPTION
             "Incompatible Disk Group type."
           --#TYPE      "Management Agent Event 229"
           --#SUMMARY   "Host %s : SCellName-TimeDate %s : EventCode %d : Description %s"
           --#ARGUMENTS {0,1,2,3,}
            --#SEVERITY  INFORMATIONAL
            --#TIMEINDEX 136
        ::= 136000229

   mngmtAgentTrap-230 TRAP-TYPE
        ENTERPRISE compaq
        VARIABLES  { hostName,
                     scellNameDateTime,
                     agentEventCode,
                     agentEventDescription }
        DESCRIPTION
             "Cannot clear the inoperative state of the drives. The controllers may need to resynced."
           --#TYPE      "Management Agent Event 230"
           --#SUMMARY   "Host %s : SCellName-TimeDate %s : EventCode %d : Description %s"
           --#ARGUMENTS {0,1,2,3,}
            --#SEVERITY  INFORMATIONAL
            --#TIMEINDEX 136
        ::= 136000230

   mngmtAgentTrap-231 TRAP-TYPE
        ENTERPRISE compaq
        VARIABLES  { hostName,
                     scellNameDateTime,
                     agentEventCode,
                     agentEventDescription }
        DESCRIPTION
             "The DRM group is performing an Async Merge operation."
           --#TYPE      "Management Agent Event 231"
           --#SUMMARY   "Host %s : SCellName-TimeDate %s : EventCode %d : Description %s"
           --#ARGUMENTS {0,1,2,3,}
            --#SEVERITY  INFORMATIONAL
            --#TIMEINDEX 136
        ::= 136000231

   mngmtAgentTrap-232 TRAP-TYPE
        ENTERPRISE compaq
        VARIABLES  { hostName,
                     scellNameDateTime,
                     agentEventCode,
                     agentEventDescription }
        DESCRIPTION
             "The DRM group attained a log full condition while removing a member in async. The destination vdisk may not be an exact copy of the source."
           --#TYPE      "Management Agent Event 232"
           --#SUMMARY   "Host %s : SCellName-TimeDate %s : EventCode %d : Description %s"
           --#ARGUMENTS {0,1,2,3,}
            --#SEVERITY  INFORMATIONAL
            --#TIMEINDEX 136
        ::= 136000232

   mngmtAgentTrap-233 TRAP-TYPE
        ENTERPRISE compaq
        VARIABLES  { hostName,
                     scellNameDateTime,
                     agentEventCode,
                     agentEventDescription }
        DESCRIPTION
             "DRM groups exist."
           --#TYPE      "Management Agent Event 233"
           --#SUMMARY   "Host %s : SCellName-TimeDate %s : EventCode %d : Description %s"
           --#ARGUMENTS {0,1,2,3,}
            --#SEVERITY  INFORMATIONAL
            --#TIMEINDEX 136
        ::= 136000233

   mngmtAgentTrap-234 TRAP-TYPE
        ENTERPRISE compaq
        VARIABLES  { hostName,
                     scellNameDateTime,
                     agentEventCode,
                     agentEventDescription }
        DESCRIPTION
             "Can't resolve a RAID6 INOP condition."
           --#TYPE      "Management Agent Event 234"
           --#SUMMARY   "Host %s : SCellName-TimeDate %s : EventCode %d : Description %s"
           --#ARGUMENTS {0,1,2,3,}
            --#SEVERITY  INFORMATIONAL
            --#TIMEINDEX 136
        ::= 136000234

   mngmtAgentTrap-235 TRAP-TYPE
        ENTERPRISE compaq
        VARIABLES  { hostName,
                     scellNameDateTime,
                     agentEventCode,
                     agentEventDescription }
        DESCRIPTION
             "DRM Destination can't support the source requested Raid Type."
           --#TYPE      "Management Agent Event 235"
           --#SUMMARY   "Host %s : SCellName-TimeDate %s : EventCode %d : Description %s"
           --#ARGUMENTS {0,1,2,3,}
            --#SEVERITY  INFORMATIONAL
            --#TIMEINDEX 136
        ::= 136000235

   mngmtAgentTrap-238 TRAP-TYPE
        ENTERPRISE compaq
        VARIABLES  { hostName,
                     scellNameDateTime,
                     agentEventCode,
                     agentEventDescription }
        DESCRIPTION
             "Check Condition Error.  Autosense data returned"
           --#TYPE      "Management Agent Event 238"
           --#SUMMARY   "Host %s : SCellName-TimeDate %s : EventCode %d : Description %s"
           --#ARGUMENTS {0,1,2,3,}
            --#SEVERITY  INFORMATIONAL
            --#TIMEINDEX 136
        ::= 136000238

   mngmtAgentTrap-240 TRAP-TYPE
        ENTERPRISE compaq
        VARIABLES  { hostName,
                     scellNameDateTime,
                     agentEventCode,
                     agentEventDescription }
        DESCRIPTION
             "Migration of data is not supported with same disk group and raid level as source."
           --#TYPE      "Management Agent Event 240"
           --#SUMMARY   "Host %s : SCellName-TimeDate %s : EventCode %d : Description %s"
           --#ARGUMENTS {0,1,2,3,}
            --#SEVERITY  INFORMATIONAL
            --#TIMEINDEX 136
        ::= 136000240

   mngmtAgentTrap-241 TRAP-TYPE
        ENTERPRISE compaq
        VARIABLES  { hostName,
                     scellNameDateTime,
                     agentEventCode,
                     agentEventDescription }
        DESCRIPTION
             "Drive firmware load abort due to exception processing or unstable back end."
           --#TYPE      "Management Agent Event 241"
           --#SUMMARY   "Host %s : SCellName-TimeDate %s : EventCode %d : Description %s"
           --#ARGUMENTS {0,1,2,3,}
            --#SEVERITY  MINOR
            --#TIMEINDEX 136
        ::= 136000241

   mngmtAgentTrap-242 TRAP-TYPE
        ENTERPRISE compaq
        VARIABLES  { hostName,
                     scellNameDateTime,
                     agentEventCode,
                     agentEventDescription }
        DESCRIPTION
             "Event not found."
           --#TYPE      "Management Agent Event 242"
           --#SUMMARY   "Host %s : SCellName-TimeDate %s : EventCode %d : Description %s"
           --#ARGUMENTS {0,1,2,3,}
            --#SEVERITY  INFORMATIONAL
            --#TIMEINDEX 136
        ::= 136000242

   mngmtAgentTrap-243 TRAP-TYPE
        ENTERPRISE compaq
        VARIABLES  { hostName,
                     scellNameDateTime,
                     agentEventCode,
                     agentEventDescription }
        DESCRIPTION
             "Drive is unsupported"
           --#TYPE      "Management Agent Event 243"
           --#SUMMARY   "Host %s : SCellName-TimeDate %s : EventCode %d : Description %s"
           --#ARGUMENTS {0,1,2,3,}
            --#SEVERITY  INFORMATIONAL
            --#TIMEINDEX 136
        ::= 136000243

   mngmtAgentTrap-244 TRAP-TYPE
        ENTERPRISE compaq
        VARIABLES  { hostName,
                     scellNameDateTime,
                     agentEventCode,
                     agentEventDescription }
        DESCRIPTION
             "Pullover refused while invert in progress"
           --#TYPE      "Management Agent Event 244"
           --#SUMMARY   "Host %s : SCellName-TimeDate %s : EventCode %d : Description %s"
           --#ARGUMENTS {0,1,2,3,}
            --#SEVERITY  MINOR
            --#TIMEINDEX 136
        ::= 136000244

   mngmtAgentTrap-245 TRAP-TYPE
        ENTERPRISE compaq
        VARIABLES  { hostName,
                     scellNameDateTime,
                     agentEventCode,
                     agentEventDescription }
        DESCRIPTION
             "ILF disk already present."
           --#TYPE      "Management Agent Event 245"
           --#SUMMARY   "Host %s : SCellName-TimeDate %s : EventCode %d : Description %s"
           --#ARGUMENTS {0,1,2,3,}
            --#SEVERITY  INFORMATIONAL
            --#TIMEINDEX 136
        ::= 136000245

   mngmtAgentTrap-1000 TRAP-TYPE
        ENTERPRISE compaq
        VARIABLES  { hostName,
                     scellNameDateTime,
                     agentEventCode,
                     agentEventDescription }
        DESCRIPTION
             "Logical Disk Condition Change"
           --#TYPE      "Management Agent Event 1000"
           --#SUMMARY   "Host %s : SCellName-TimeDate %s : EventCode %d : Description %s"
           --#ARGUMENTS {0,1,2,3,}
            --#SEVERITY  INFORMATIONAL
            --#TIMEINDEX 136
        ::= 136001000

   mngmtAgentTrap-1001 TRAP-TYPE
        ENTERPRISE compaq
        VARIABLES  { hostName,
                     scellNameDateTime,
                     agentEventCode,
                     agentEventDescription }
        DESCRIPTION
             "Storage system is FULL  **critical**"
           --#TYPE      "Management Agent Event 1001"
           --#SUMMARY   "Host %s : SCellName-TimeDate %s : EventCode %d : Description %s"
           --#ARGUMENTS {0,1,2,3,}
            --#SEVERITY  CRITICAL
            --#TIMEINDEX 136
        ::= 136001001

   mngmtAgentTrap-1002 TRAP-TYPE
        ENTERPRISE compaq
        VARIABLES  { hostName,
                     scellNameDateTime,
                     agentEventCode,
                     agentEventDescription }
        DESCRIPTION
             "Disk group capacity reached Critical level."
           --#TYPE      "Management Agent Event 1002"
           --#SUMMARY   "Host %s : SCellName-TimeDate %s : EventCode %d : Description %s"
           --#ARGUMENTS {0,1,2,3,}
            --#SEVERITY  MINOR
            --#TIMEINDEX 136
        ::= 136001002

   mngmtAgentTrap-1003 TRAP-TYPE
        ENTERPRISE compaq
        VARIABLES  { hostName,
                     scellNameDateTime,
                     agentEventCode,
                     agentEventDescription }
        DESCRIPTION
             "Controller Cache Battery Condition Change"
           --#TYPE      "Management Agent Event 1003"
           --#SUMMARY   "Host %s : SCellName-TimeDate %s : EventCode %d : Description %s"
           --#ARGUMENTS {0,1,2,3,}
            --#SEVERITY  INFORMATIONAL
            --#TIMEINDEX 136
        ::= 136001003

   mngmtAgentTrap-1004 TRAP-TYPE
        ENTERPRISE compaq
        VARIABLES  { hostName,
                     scellNameDateTime,
                     agentEventCode,
                     agentEventDescription }
        DESCRIPTION
             "Controller Cache Condition Change"
           --#TYPE      "Management Agent Event 1004"
           --#SUMMARY   "Host %s : SCellName-TimeDate %s : EventCode %d : Description %s"
           --#ARGUMENTS {0,1,2,3,}
            --#SEVERITY  INFORMATIONAL
            --#TIMEINDEX 136
        ::= 136001004

   mngmtAgentTrap-1005 TRAP-TYPE
        ENTERPRISE compaq
        VARIABLES  { hostName,
                     scellNameDateTime,
                     agentEventCode,
                     agentEventDescription }
        DESCRIPTION
             "Controller Condition Change"
           --#TYPE      "Management Agent Event 1005"
           --#SUMMARY   "Host %s : SCellName-TimeDate %s : EventCode %d : Description %s"
           --#ARGUMENTS {0,1,2,3,}
            --#SEVERITY  INFORMATIONAL
            --#TIMEINDEX 136
        ::= 136001005

   mngmtAgentTrap-1006 TRAP-TYPE
        ENTERPRISE compaq
        VARIABLES  { hostName,
                     scellNameDateTime,
                     agentEventCode,
                     agentEventDescription }
        DESCRIPTION
             "Controller FC Port Condition Change"
           --#TYPE      "Management Agent Event 1006"
           --#SUMMARY   "Host %s : SCellName-TimeDate %s : EventCode %d : Description %s"
           --#ARGUMENTS {0,1,2,3,}
            --#SEVERITY  INFORMATIONAL
            --#TIMEINDEX 136
        ::= 136001006

   mngmtAgentTrap-1007 TRAP-TYPE
        ENTERPRISE compaq
        VARIABLES  { hostName,
                     scellNameDateTime,
                     agentEventCode,
                     agentEventDescription }
        DESCRIPTION
             "Physical Device Condition Change"
           --#TYPE      "Management Agent Event 1007"
           --#SUMMARY   "Host %s : SCellName-TimeDate %s : EventCode %d : Description %s"
           --#ARGUMENTS {0,1,2,3,}
            --#SEVERITY  INFORMATIONAL
            --#TIMEINDEX 136
        ::= 136001007

   mngmtAgentTrap-1008 TRAP-TYPE
        ENTERPRISE compaq
        VARIABLES  { hostName,
                     scellNameDateTime,
                     agentEventCode,
                     agentEventDescription }
        DESCRIPTION
             "Physical Store Condition Change"
           --#TYPE      "Management Agent Event 1008"
           --#SUMMARY   "Host %s : SCellName-TimeDate %s : EventCode %d : Description %s"
           --#ARGUMENTS {0,1,2,3,}
            --#SEVERITY  INFORMATIONAL
            --#TIMEINDEX 136
        ::= 136001008

   mngmtAgentTrap-1009 TRAP-TYPE
        ENTERPRISE compaq
        VARIABLES  { hostName,
                     scellNameDateTime,
                     agentEventCode,
                     agentEventDescription }
        DESCRIPTION
             "Host condition change"
           --#TYPE      "Management Agent Event 1009"
           --#SUMMARY   "Host %s : SCellName-TimeDate %s : EventCode %d : Description %s"
           --#ARGUMENTS {0,1,2,3,}
            --#SEVERITY  INFORMATIONAL
            --#TIMEINDEX 136
        ::= 136001009

   mngmtAgentTrap-1010 TRAP-TYPE
        ENTERPRISE compaq
        VARIABLES  { hostName,
                     scellNameDateTime,
                     agentEventCode,
                     agentEventDescription }
        DESCRIPTION
             "Storage system time has been set"
           --#TYPE      "Management Agent Event 1010"
           --#SUMMARY   "Host %s : SCellName-TimeDate %s : EventCode %d : Description %s"
           --#ARGUMENTS {0,1,2,3,}
            --#SEVERITY  INFORMATIONAL
            --#TIMEINDEX 136
        ::= 136001010

   mngmtAgentTrap-1011 TRAP-TYPE
        ENTERPRISE compaq
        VARIABLES  { hostName,
                     scellNameDateTime,
                     agentEventCode,
                     agentEventDescription }
        DESCRIPTION
             "Volume Condition change"
           --#TYPE      "Management Agent Event 1011"
           --#SUMMARY   "Host %s : SCellName-TimeDate %s : EventCode %d : Description %s"
           --#ARGUMENTS {0,1,2,3,}
            --#SEVERITY  INFORMATIONAL
            --#TIMEINDEX 136
        ::= 136001011

   mngmtAgentTrap-1012 TRAP-TYPE
        ENTERPRISE compaq
        VARIABLES  { hostName,
                     scellNameDateTime,
                     agentEventCode,
                     agentEventDescription }
        DESCRIPTION
             "Volume insufficient_resources condition change"
           --#TYPE      "Management Agent Event 1012"
           --#SUMMARY   "Host %s : SCellName-TimeDate %s : EventCode %d : Description %s"
           --#ARGUMENTS {0,1,2,3,}
            --#SEVERITY  INFORMATIONAL
            --#TIMEINDEX 136
        ::= 136001012

   mngmtAgentTrap-1013 TRAP-TYPE
        ENTERPRISE compaq
        VARIABLES  { hostName,
                     scellNameDateTime,
                     agentEventCode,
                     agentEventDescription }
        DESCRIPTION
             "Volume Quorum Disk change"
           --#TYPE      "Management Agent Event 1013"
           --#SUMMARY   "Host %s : SCellName-TimeDate %s : EventCode %d : Description %s"
           --#ARGUMENTS {0,1,2,3,}
            --#SEVERITY  INFORMATIONAL
            --#TIMEINDEX 136
        ::= 136001013

   mngmtAgentTrap-1014 TRAP-TYPE
        ENTERPRISE compaq
        VARIABLES  { hostName,
                     scellNameDateTime,
                     agentEventCode,
                     agentEventDescription }
        DESCRIPTION
             "The state of an object in the system has changed. View adjacent events for more detail."
           --#TYPE      "Management Agent Event 1014"
           --#SUMMARY   "Host %s : SCellName-TimeDate %s : EventCode %d : Description %s"
           --#ARGUMENTS {0,1,2,3,}
            --#SEVERITY  INFORMATIONAL
            --#TIMEINDEX 136
        ::= 136001014

   mngmtAgentTrap-1015 TRAP-TYPE
        ENTERPRISE compaq
        VARIABLES  { hostName,
                     scellNameDateTime,
                     agentEventCode,
                     agentEventDescription }
        DESCRIPTION
             "Disk group capacity returned to below Critical level."
           --#TYPE      "Management Agent Event 1015"
           --#SUMMARY   "Host %s : SCellName-TimeDate %s : EventCode %d : Description %s"
           --#ARGUMENTS {0,1,2,3,}
            --#SEVERITY  INFORMATIONAL
            --#TIMEINDEX 136
        ::= 136001015

   mngmtAgentTrap-1016 TRAP-TYPE
        ENTERPRISE compaq
        VARIABLES  { hostName,
                     scellNameDateTime,
                     agentEventCode,
                     agentEventDescription }
        DESCRIPTION
             "Disk group capacity reached Warning level."
           --#TYPE      "Management Agent Event 1016"
           --#SUMMARY   "Host %s : SCellName-TimeDate %s : EventCode %d : Description %s"
           --#ARGUMENTS {0,1,2,3,}
            --#SEVERITY  MINOR
            --#TIMEINDEX 136
        ::= 136001016

   mngmtAgentTrap-1017 TRAP-TYPE
        ENTERPRISE compaq
        VARIABLES  { hostName,
                     scellNameDateTime,
                     agentEventCode,
                     agentEventDescription }
        DESCRIPTION
             "Disk group capacity returned to below Warning level."
           --#TYPE      "Management Agent Event 1017"
           --#SUMMARY   "Host %s : SCellName-TimeDate %s : EventCode %d : Description %s"
           --#ARGUMENTS {0,1,2,3,}
            --#SEVERITY  INFORMATIONAL
            --#TIMEINDEX 136
        ::= 136001017

   mngmtAgentTrap-1018 TRAP-TYPE
        ENTERPRISE compaq
        VARIABLES  { hostName,
                     scellNameDateTime,
                     agentEventCode,
                     agentEventDescription }
        DESCRIPTION
             "Vdisk reached Allocation alarm level."
           --#TYPE      "Management Agent Event 1018"
           --#SUMMARY   "Host %s : SCellName-TimeDate %s : EventCode %d : Description %s"
           --#ARGUMENTS {0,1,2,3,}
            --#SEVERITY  MINOR
            --#TIMEINDEX 136
        ::= 136001018

   mngmtAgentTrap-1019 TRAP-TYPE
        ENTERPRISE compaq
        VARIABLES  { hostName,
                     scellNameDateTime,
                     agentEventCode,
                     agentEventDescription }
        DESCRIPTION
             "Vdisk returned to below Allocation alarm level."
           --#TYPE      "Management Agent Event 1019"
           --#SUMMARY   "Host %s : SCellName-TimeDate %s : EventCode %d : Description %s"
           --#ARGUMENTS {0,1,2,3,}
            --#SEVERITY  INFORMATIONAL
            --#TIMEINDEX 136
        ::= 136001019

   mngmtAgentTrap-2001 TRAP-TYPE
        ENTERPRISE compaq
        VARIABLES  { hostName,
                     scellNameDateTime,
                     agentEventCode,
                     agentEventDescription }
        DESCRIPTION
             "Startup Failed"
           --#TYPE      "Management Agent Event 2001"
           --#SUMMARY   "Host %s : SCellName-TimeDate %s : EventCode %d : Description %s"
           --#ARGUMENTS {0,1,2,3,}
            --#SEVERITY  CRITICAL
            --#TIMEINDEX 136
        ::= 136002001

   mngmtAgentTrap-2002 TRAP-TYPE
        ENTERPRISE compaq
        VARIABLES  { hostName,
                     scellNameDateTime,
                     agentEventCode,
                     agentEventDescription }
        DESCRIPTION
             "Management agent event log cleared successfully"
           --#TYPE      "Management Agent Event 2002"
           --#SUMMARY   "Host %s : SCellName-TimeDate %s : EventCode %d : Description %s"
           --#ARGUMENTS {0,1,2,3,}
            --#SEVERITY  INFORMATIONAL
            --#TIMEINDEX 136
        ::= 136002002

   mngmtAgentTrap-2003 TRAP-TYPE
        ENTERPRISE compaq
        VARIABLES  { hostName,
                     scellNameDateTime,
                     agentEventCode,
                     agentEventDescription }
        DESCRIPTION
             "Invalid name specified for storage system"
           --#TYPE      "Management Agent Event 2003"
           --#SUMMARY   "Host %s : SCellName-TimeDate %s : EventCode %d : Description %s"
           --#ARGUMENTS {0,1,2,3,}
            --#SEVERITY  MINOR
            --#TIMEINDEX 136
        ::= 136002003

   mngmtAgentTrap-2004 TRAP-TYPE
        ENTERPRISE compaq
        VARIABLES  { hostName,
                     scellNameDateTime,
                     agentEventCode,
                     agentEventDescription }
        DESCRIPTION
             "Storage system is not initialized"
           --#TYPE      "Management Agent Event 2004"
           --#SUMMARY   "Host %s : SCellName-TimeDate %s : EventCode %d : Description %s"
           --#ARGUMENTS {0,1,2,3,}
            --#SEVERITY  INFORMATIONAL
            --#TIMEINDEX 136
        ::= 136002004

   mngmtAgentTrap-2006 TRAP-TYPE
        ENTERPRISE compaq
        VARIABLES  { hostName,
                     scellNameDateTime,
                     agentEventCode,
                     agentEventDescription }
        DESCRIPTION
             "Invalid name specified"
           --#TYPE      "Management Agent Event 2006"
           --#SUMMARY   "Host %s : SCellName-TimeDate %s : EventCode %d : Description %s"
           --#ARGUMENTS {0,1,2,3,}
            --#SEVERITY  MINOR
            --#TIMEINDEX 136
        ::= 136002006

   mngmtAgentTrap-2007 TRAP-TYPE
        ENTERPRISE compaq
        VARIABLES  { hostName,
                     scellNameDateTime,
                     agentEventCode,
                     agentEventDescription }
        DESCRIPTION
             "Name exceeds maximum length"
           --#TYPE      "Management Agent Event 2007"
           --#SUMMARY   "Host %s : SCellName-TimeDate %s : EventCode %d : Description %s"
           --#ARGUMENTS {0,1,2,3,}
            --#SEVERITY  MINOR
            --#TIMEINDEX 136
        ::= 136002007

   mngmtAgentTrap-2008 TRAP-TYPE
        ENTERPRISE compaq
        VARIABLES  { hostName,
                     scellNameDateTime,
                     agentEventCode,
                     agentEventDescription }
        DESCRIPTION
             "Invalid parameter specified"
           --#TYPE      "Management Agent Event 2008"
           --#SUMMARY   "Host %s : SCellName-TimeDate %s : EventCode %d : Description %s"
           --#ARGUMENTS {0,1,2,3,}
            --#SEVERITY  MINOR
            --#TIMEINDEX 136
        ::= 136002008

   mngmtAgentTrap-2010 TRAP-TYPE
        ENTERPRISE compaq
        VARIABLES  { hostName,
                     scellNameDateTime,
                     agentEventCode,
                     agentEventDescription }
        DESCRIPTION
             "Specified size exceeds available size"
           --#TYPE      "Management Agent Event 2010"
           --#SUMMARY   "Host %s : SCellName-TimeDate %s : EventCode %d : Description %s"
           --#ARGUMENTS {0,1,2,3,}
            --#SEVERITY  MINOR
            --#TIMEINDEX 136
        ::= 136002010

   mngmtAgentTrap-2011 TRAP-TYPE
        ENTERPRISE compaq
        VARIABLES  { hostName,
                     scellNameDateTime,
                     agentEventCode,
                     agentEventDescription }
        DESCRIPTION
             "There are not enough disk drives to create a disk group"
           --#TYPE      "Management Agent Event 2011"
           --#SUMMARY   "Host %s : SCellName-TimeDate %s : EventCode %d : Description %s"
           --#ARGUMENTS {0,1,2,3,}
            --#SEVERITY  INFORMATIONAL
            --#TIMEINDEX 136
        ::= 136002011

   mngmtAgentTrap-2012 TRAP-TYPE
        ENTERPRISE compaq
        VARIABLES  { hostName,
                     scellNameDateTime,
                     agentEventCode,
                     agentEventDescription }
        DESCRIPTION
             "Number of devices exceeds the available number of disks"
           --#TYPE      "Management Agent Event 2012"
           --#SUMMARY   "Host %s : SCellName-TimeDate %s : EventCode %d : Description %s"
           --#ARGUMENTS {0,1,2,3,}
            --#SEVERITY  MINOR
            --#TIMEINDEX 136
        ::= 136002012

   mngmtAgentTrap-2013 TRAP-TYPE
        ENTERPRISE compaq
        VARIABLES  { hostName,
                     scellNameDateTime,
                     agentEventCode,
                     agentEventDescription }
        DESCRIPTION
             "Number of devices is less than the minimum number required to create a disk group"
           --#TYPE      "Management Agent Event 2013"
           --#SUMMARY   "Host %s : SCellName-TimeDate %s : EventCode %d : Description %s"
           --#ARGUMENTS {0,1,2,3,}
            --#SEVERITY  MINOR
            --#TIMEINDEX 136
        ::= 136002013

   mngmtAgentTrap-2016 TRAP-TYPE
        ENTERPRISE compaq
        VARIABLES  { hostName,
                     scellNameDateTime,
                     agentEventCode,
                     agentEventDescription }
        DESCRIPTION
             "Completed unpresenting virtual disk to host"
           --#TYPE      "Management Agent Event 2016"
           --#SUMMARY   "Host %s : SCellName-TimeDate %s : EventCode %d : Description %s"
           --#ARGUMENTS {0,1,2,3,}
            --#SEVERITY  MINOR
            --#TIMEINDEX 136
        ::= 136002016

   mngmtAgentTrap-2021 TRAP-TYPE
        ENTERPRISE compaq
        VARIABLES  { hostName,
                     scellNameDateTime,
                     agentEventCode,
                     agentEventDescription }
        DESCRIPTION
             "Invalid refresh interval value. Should be numeric and non-negative."
           --#TYPE      "Management Agent Event 2021"
           --#SUMMARY   "Host %s : SCellName-TimeDate %s : EventCode %d : Description %s"
           --#ARGUMENTS {0,1,2,3,}
            --#SEVERITY  MINOR
            --#TIMEINDEX 136
        ::= 136002021

   mngmtAgentTrap-2022 TRAP-TYPE
        ENTERPRISE compaq
        VARIABLES  { hostName,
                     scellNameDateTime,
                     agentEventCode,
                     agentEventDescription }
        DESCRIPTION
             "Invalid security message. Should not be blank."
           --#TYPE      "Management Agent Event 2022"
           --#SUMMARY   "Host %s : SCellName-TimeDate %s : EventCode %d : Description %s"
           --#ARGUMENTS {0,1,2,3,}
            --#SEVERITY  MINOR
            --#TIMEINDEX 136
        ::= 136002022

   mngmtAgentTrap-2023 TRAP-TYPE
        ENTERPRISE compaq
        VARIABLES  { hostName,
                     scellNameDateTime,
                     agentEventCode,
                     agentEventDescription }
        DESCRIPTION
             "Create Complete"
           --#TYPE      "Management Agent Event 2023"
           --#SUMMARY   "Host %s : SCellName-TimeDate %s : EventCode %d : Description %s"
           --#ARGUMENTS {0,1,2,3,}
            --#SEVERITY  INFORMATIONAL
            --#TIMEINDEX 136
        ::= 136002023

   mngmtAgentTrap-2025 TRAP-TYPE
        ENTERPRISE compaq
        VARIABLES  { hostName,
                     scellNameDateTime,
                     agentEventCode,
                     agentEventDescription }
        DESCRIPTION
             "Storage system successfully initialized"
           --#TYPE      "Management Agent Event 2025"
           --#SUMMARY   "Host %s : SCellName-TimeDate %s : EventCode %d : Description %s"
           --#ARGUMENTS {0,1,2,3,}
            --#SEVERITY  INFORMATIONAL
            --#TIMEINDEX 136
        ::= 136002025

   mngmtAgentTrap-2026 TRAP-TYPE
        ENTERPRISE compaq
        VARIABLES  { hostName,
                     scellNameDateTime,
                     agentEventCode,
                     agentEventDescription }
        DESCRIPTION
             "Device Added Successfully"
           --#TYPE      "Management Agent Event 2026"
           --#SUMMARY   "Host %s : SCellName-TimeDate %s : EventCode %d : Description %s"
           --#ARGUMENTS {0,1,2,3,}
            --#SEVERITY  INFORMATIONAL
            --#TIMEINDEX 136
        ::= 136002026

   mngmtAgentTrap-2030 TRAP-TYPE
        ENTERPRISE compaq
        VARIABLES  { hostName,
                     scellNameDateTime,
                     agentEventCode,
                     agentEventDescription }
        DESCRIPTION
             "Refresh Interval Changed"
           --#TYPE      "Management Agent Event 2030"
           --#SUMMARY   "Host %s : SCellName-TimeDate %s : EventCode %d : Description %s"
           --#ARGUMENTS {0,1,2,3,}
            --#SEVERITY  INFORMATIONAL
            --#TIMEINDEX 136
        ::= 136002030

   mngmtAgentTrap-2031 TRAP-TYPE
        ENTERPRISE compaq
        VARIABLES  { hostName,
                     scellNameDateTime,
                     agentEventCode,
                     agentEventDescription }
        DESCRIPTION
             "Security Message Changed"
           --#TYPE      "Management Agent Event 2031"
           --#SUMMARY   "Host %s : SCellName-TimeDate %s : EventCode %d : Description %s"
           --#ARGUMENTS {0,1,2,3,}
            --#SEVERITY  INFORMATIONAL
            --#TIMEINDEX 136
        ::= 136002031

   mngmtAgentTrap-2032 TRAP-TYPE
        ENTERPRISE compaq
        VARIABLES  { hostName,
                     scellNameDateTime,
                     agentEventCode,
                     agentEventDescription }
        DESCRIPTION
             "Present Vdisk to a Host - Complete"
           --#TYPE      "Management Agent Event 2032"
           --#SUMMARY   "Host %s : SCellName-TimeDate %s : EventCode %d : Description %s"
           --#ARGUMENTS {0,1,2,3,}
            --#SEVERITY  INFORMATIONAL
            --#TIMEINDEX 136
        ::= 136002032

   mngmtAgentTrap-2033 TRAP-TYPE
        ENTERPRISE compaq
        VARIABLES  { hostName,
                     scellNameDateTime,
                     agentEventCode,
                     agentEventDescription }
        DESCRIPTION
             "Control Startup Complete"
           --#TYPE      "Management Agent Event 2033"
           --#SUMMARY   "Host %s : SCellName-TimeDate %s : EventCode %d : Description %s"
           --#ARGUMENTS {0,1,2,3,}
            --#SEVERITY  INFORMATIONAL
            --#TIMEINDEX 136
        ::= 136002033

   mngmtAgentTrap-2034 TRAP-TYPE
        ENTERPRISE compaq
        VARIABLES  { hostName,
                     scellNameDateTime,
                     agentEventCode,
                     agentEventDescription }
        DESCRIPTION
             "Change Device Usage Complete"
           --#TYPE      "Management Agent Event 2034"
           --#SUMMARY   "Host %s : SCellName-TimeDate %s : EventCode %d : Description %s"
           --#ARGUMENTS {0,1,2,3,}
            --#SEVERITY  INFORMATIONAL
            --#TIMEINDEX 136
        ::= 136002034

   mngmtAgentTrap-2035 TRAP-TYPE
        ENTERPRISE compaq
        VARIABLES  { hostName,
                     scellNameDateTime,
                     agentEventCode,
                     agentEventDescription }
        DESCRIPTION
             "Control Shutdown - Complete"
           --#TYPE      "Management Agent Event 2035"
           --#SUMMARY   "Host %s : SCellName-TimeDate %s : EventCode %d : Description %s"
           --#ARGUMENTS {0,1,2,3,}
            --#SEVERITY  INFORMATIONAL
            --#TIMEINDEX 136
        ::= 136002035

   mngmtAgentTrap-2036 TRAP-TYPE
        ENTERPRISE compaq
        VARIABLES  { hostName,
                     scellNameDateTime,
                     agentEventCode,
                     agentEventDescription }
        DESCRIPTION
             "Controller Shutdown - Complete"
           --#TYPE      "Management Agent Event 2036"
           --#SUMMARY   "Host %s : SCellName-TimeDate %s : EventCode %d : Description %s"
           --#ARGUMENTS {0,1,2,3,}
            --#SEVERITY  INFORMATIONAL
            --#TIMEINDEX 136
        ::= 136002036

   mngmtAgentTrap-2038 TRAP-TYPE
        ENTERPRISE compaq
        VARIABLES  { hostName,
                     scellNameDateTime,
                     agentEventCode,
                     agentEventDescription }
        DESCRIPTION
             "Control Memory Allocation Failure"
           --#TYPE      "Management Agent Event 2038"
           --#SUMMARY   "Host %s : SCellName-TimeDate %s : EventCode %d : Description %s"
           --#ARGUMENTS {0,1,2,3,}
            --#SEVERITY  CRITICAL
            --#TIMEINDEX 136
        ::= 136002038

   mngmtAgentTrap-2040 TRAP-TYPE
        ENTERPRISE compaq
        VARIABLES  { hostName,
                     scellNameDateTime,
                     agentEventCode,
                     agentEventDescription }
        DESCRIPTION
             "Access level denied or session activity timeout. Please log in again."
           --#TYPE      "Management Agent Event 2040"
           --#SUMMARY   "Host %s : SCellName-TimeDate %s : EventCode %d : Description %s"
           --#ARGUMENTS {0,1,2,3,}
            --#SEVERITY  INFORMATIONAL
            --#TIMEINDEX 136
        ::= 136002040

   mngmtAgentTrap-2041 TRAP-TYPE
        ENTERPRISE compaq
        VARIABLES  { hostName,
                     scellNameDateTime,
                     agentEventCode,
                     agentEventDescription }
        DESCRIPTION
             "Vdisk Snapshot - Completed"
           --#TYPE      "Management Agent Event 2041"
           --#SUMMARY   "Host %s : SCellName-TimeDate %s : EventCode %d : Description %s"
           --#ARGUMENTS {0,1,2,3,}
            --#SEVERITY  INFORMATIONAL
            --#TIMEINDEX 136
        ::= 136002041

   mngmtAgentTrap-2042 TRAP-TYPE
        ENTERPRISE compaq
        VARIABLES  { hostName,
                     scellNameDateTime,
                     agentEventCode,
                     agentEventDescription }
        DESCRIPTION
             "Vdisk Snapclone - Completed"
           --#TYPE      "Management Agent Event 2042"
           --#SUMMARY   "Host %s : SCellName-TimeDate %s : EventCode %d : Description %s"
           --#ARGUMENTS {0,1,2,3,}
            --#SEVERITY  INFORMATIONAL
            --#TIMEINDEX 136
        ::= 136002042

   mngmtAgentTrap-2047 TRAP-TYPE
        ENTERPRISE compaq
        VARIABLES  { hostName,
                     scellNameDateTime,
                     agentEventCode,
                     agentEventDescription }
        DESCRIPTION
             "Host record added successfully"
           --#TYPE      "Management Agent Event 2047"
           --#SUMMARY   "Host %s : SCellName-TimeDate %s : EventCode %d : Description %s"
           --#ARGUMENTS {0,1,2,3,}
            --#SEVERITY  INFORMATIONAL
            --#TIMEINDEX 136
        ::= 136002047

   mngmtAgentTrap-2048 TRAP-TYPE
        ENTERPRISE compaq
        VARIABLES  { hostName,
                     scellNameDateTime,
                     agentEventCode,
                     agentEventDescription }
        DESCRIPTION
             "Logical component deleted successfully"
           --#TYPE      "Management Agent Event 2048"
           --#SUMMARY   "Host %s : SCellName-TimeDate %s : EventCode %d : Description %s"
           --#ARGUMENTS {0,1,2,3,}
            --#SEVERITY  INFORMATIONAL
            --#TIMEINDEX 136
        ::= 136002048

   mngmtAgentTrap-2049 TRAP-TYPE
        ENTERPRISE compaq
        VARIABLES  { hostName,
                     scellNameDateTime,
                     agentEventCode,
                     agentEventDescription }
        DESCRIPTION
             "Invalid host adapter WWN"
           --#TYPE      "Management Agent Event 2049"
           --#SUMMARY   "Host %s : SCellName-TimeDate %s : EventCode %d : Description %s"
           --#ARGUMENTS {0,1,2,3,}
            --#SEVERITY  INFORMATIONAL
            --#TIMEINDEX 136
        ::= 136002049

   mngmtAgentTrap-2050 TRAP-TYPE
        ENTERPRISE compaq
        VARIABLES  { hostName,
                     scellNameDateTime,
                     agentEventCode,
                     agentEventDescription }
        DESCRIPTION
             "Specified device is already a member of the system"
           --#TYPE      "Management Agent Event 2050"
           --#SUMMARY   "Host %s : SCellName-TimeDate %s : EventCode %d : Description %s"
           --#ARGUMENTS {0,1,2,3,}
            --#SEVERITY  INFORMATIONAL
            --#TIMEINDEX 136
        ::= 136002050

   mngmtAgentTrap-2051 TRAP-TYPE
        ENTERPRISE compaq
        VARIABLES  { hostName,
                     scellNameDateTime,
                     agentEventCode,
                     agentEventDescription }
        DESCRIPTION
             "Create Folder - Completed"
           --#TYPE      "Management Agent Event 2051"
           --#SUMMARY   "Host %s : SCellName-TimeDate %s : EventCode %d : Description %s"
           --#ARGUMENTS {0,1,2,3,}
            --#SEVERITY  INFORMATIONAL
            --#TIMEINDEX 136
        ::= 136002051

   mngmtAgentTrap-2052 TRAP-TYPE
        ENTERPRISE compaq
        VARIABLES  { hostName,
                     scellNameDateTime,
                     agentEventCode,
                     agentEventDescription }
        DESCRIPTION
             "Change Object Properties - Completed"
           --#TYPE      "Management Agent Event 2052"
           --#SUMMARY   "Host %s : SCellName-TimeDate %s : EventCode %d : Description %s"
           --#ARGUMENTS {0,1,2,3,}
            --#SEVERITY  INFORMATIONAL
            --#TIMEINDEX 136
        ::= 136002052

   mngmtAgentTrap-2057 TRAP-TYPE
        ENTERPRISE compaq
        VARIABLES  { hostName,
                     scellNameDateTime,
                     agentEventCode,
                     agentEventDescription }
        DESCRIPTION
             "Completed disk group creation"
           --#TYPE      "Management Agent Event 2057"
           --#SUMMARY   "Host %s : SCellName-TimeDate %s : EventCode %d : Description %s"
           --#ARGUMENTS {0,1,2,3,}
            --#SEVERITY  INFORMATIONAL
            --#TIMEINDEX 136
        ::= 136002057

   mngmtAgentTrap-2058 TRAP-TYPE
        ENTERPRISE compaq
        VARIABLES  { hostName,
                     scellNameDateTime,
                     agentEventCode,
                     agentEventDescription }
        DESCRIPTION
             "Added host port"
           --#TYPE      "Management Agent Event 2058"
           --#SUMMARY   "Host %s : SCellName-TimeDate %s : EventCode %d : Description %s"
           --#ARGUMENTS {0,1,2,3,}
            --#SEVERITY  INFORMATIONAL
            --#TIMEINDEX 136
        ::= 136002058

   mngmtAgentTrap-2059 TRAP-TYPE
        ENTERPRISE compaq
        VARIABLES  { hostName,
                     scellNameDateTime,
                     agentEventCode,
                     agentEventDescription }
        DESCRIPTION
             "Discarded host port"
           --#TYPE      "Management Agent Event 2059"
           --#SUMMARY   "Host %s : SCellName-TimeDate %s : EventCode %d : Description %s"
           --#ARGUMENTS {0,1,2,3,}
            --#SEVERITY  INFORMATIONAL
            --#TIMEINDEX 136
        ::= 136002059

   mngmtAgentTrap-2060 TRAP-TYPE
        ENTERPRISE compaq
        VARIABLES  { hostName,
                     scellNameDateTime,
                     agentEventCode,
                     agentEventDescription }
        DESCRIPTION
             "EMU/Shelf code load complete"
           --#TYPE      "Management Agent Event 2060"
           --#SUMMARY   "Host %s : SCellName-TimeDate %s : EventCode %d : Description %s"
           --#ARGUMENTS {0,1,2,3,}
            --#SEVERITY  INFORMATIONAL
            --#TIMEINDEX 136
        ::= 136002060

   mngmtAgentTrap-2061 TRAP-TYPE
        ENTERPRISE compaq
        VARIABLES  { hostName,
                     scellNameDateTime,
                     agentEventCode,
                     agentEventDescription }
        DESCRIPTION
             "Operation will exceed the available capacity of the disk group"
           --#TYPE      "Management Agent Event 2061"
           --#SUMMARY   "Host %s : SCellName-TimeDate %s : EventCode %d : Description %s"
           --#ARGUMENTS {0,1,2,3,}
            --#SEVERITY  INFORMATIONAL
            --#TIMEINDEX 136
        ::= 136002061

   mngmtAgentTrap-2062 TRAP-TYPE
        ENTERPRISE compaq
        VARIABLES  { hostName,
                     scellNameDateTime,
                     agentEventCode,
                     agentEventDescription }
        DESCRIPTION
             "Controller(s) code load complete"
           --#TYPE      "Management Agent Event 2062"
           --#SUMMARY   "Host %s : SCellName-TimeDate %s : EventCode %d : Description %s"
           --#ARGUMENTS {0,1,2,3,}
            --#SEVERITY  INFORMATIONAL
            --#TIMEINDEX 136
        ::= 136002062

   mngmtAgentTrap-2063 TRAP-TYPE
        ENTERPRISE compaq
        VARIABLES  { hostName,
                     scellNameDateTime,
                     agentEventCode,
                     agentEventDescription }
        DESCRIPTION
             "The target device is not in the right condition to perform the operation"
           --#TYPE      "Management Agent Event 2063"
           --#SUMMARY   "Host %s : SCellName-TimeDate %s : EventCode %d : Description %s"
           --#ARGUMENTS {0,1,2,3,}
            --#SEVERITY  INFORMATIONAL
            --#TIMEINDEX 136
        ::= 136002063

   mngmtAgentTrap-2064 TRAP-TYPE
        ENTERPRISE compaq
        VARIABLES  { hostName,
                     scellNameDateTime,
                     agentEventCode,
                     agentEventDescription }
        DESCRIPTION
             "Storage system Device Addition Policy changed successfully"
           --#TYPE      "Management Agent Event 2064"
           --#SUMMARY   "Host %s : SCellName-TimeDate %s : EventCode %d : Description %s"
           --#ARGUMENTS {0,1,2,3,}
            --#SEVERITY  INFORMATIONAL
            --#TIMEINDEX 136
        ::= 136002064

   mngmtAgentTrap-2065 TRAP-TYPE
        ENTERPRISE compaq
        VARIABLES  { hostName,
                     scellNameDateTime,
                     agentEventCode,
                     agentEventDescription }
        DESCRIPTION
             "Maximum number of disk groups exceeded"
           --#TYPE      "Management Agent Event 2065"
           --#SUMMARY   "Host %s : SCellName-TimeDate %s : EventCode %d : Description %s"
           --#ARGUMENTS {0,1,2,3,}
            --#SEVERITY  INFORMATIONAL
            --#TIMEINDEX 136
        ::= 136002065

   mngmtAgentTrap-2066 TRAP-TYPE
        ENTERPRISE compaq
        VARIABLES  { hostName,
                     scellNameDateTime,
                     agentEventCode,
                     agentEventDescription }
        DESCRIPTION
             "Nsa object discard failed."
           --#TYPE      "Management Agent Event 2066"
           --#SUMMARY   "Host %s : SCellName-TimeDate %s : EventCode %d : Description %s"
           --#ARGUMENTS {0,1,2,3,}
            --#SEVERITY  MINOR
            --#TIMEINDEX 136
        ::= 136002066

   mngmtAgentTrap-2067 TRAP-TYPE
        ENTERPRISE compaq
        VARIABLES  { hostName,
                     scellNameDateTime,
                     agentEventCode,
                     agentEventDescription }
        DESCRIPTION
             "There are not enough disks to meet the minimum number requirement"
           --#TYPE      "Management Agent Event 2067"
           --#SUMMARY   "Host %s : SCellName-TimeDate %s : EventCode %d : Description %s"
           --#ARGUMENTS {0,1,2,3,}
            --#SEVERITY  MINOR
            --#TIMEINDEX 136
        ::= 136002067

   mngmtAgentTrap-2068 TRAP-TYPE
        ENTERPRISE compaq
        VARIABLES  { hostName,
                     scellNameDateTime,
                     agentEventCode,
                     agentEventDescription }
        DESCRIPTION
             "Entry added successfully in the password file"
           --#TYPE      "Management Agent Event 2068"
           --#SUMMARY   "Host %s : SCellName-TimeDate %s : EventCode %d : Description %s"
           --#ARGUMENTS {0,1,2,3,}
            --#SEVERITY  INFORMATIONAL
            --#TIMEINDEX 136
        ::= 136002068

   mngmtAgentTrap-2069 TRAP-TYPE
        ENTERPRISE compaq
        VARIABLES  { hostName,
                     scellNameDateTime,
                     agentEventCode,
                     agentEventDescription }
        DESCRIPTION
             "Entry updated successfully in the password file"
           --#TYPE      "Management Agent Event 2069"
           --#SUMMARY   "Host %s : SCellName-TimeDate %s : EventCode %d : Description %s"
           --#ARGUMENTS {0,1,2,3,}
            --#SEVERITY  INFORMATIONAL
            --#TIMEINDEX 136
        ::= 136002069

   mngmtAgentTrap-2070 TRAP-TYPE
        ENTERPRISE compaq
        VARIABLES  { hostName,
                     scellNameDateTime,
                     agentEventCode,
                     agentEventDescription }
        DESCRIPTION
             "Entry discarded successfully in the password file"
           --#TYPE      "Management Agent Event 2070"
           --#SUMMARY   "Host %s : SCellName-TimeDate %s : EventCode %d : Description %s"
           --#ARGUMENTS {0,1,2,3,}
            --#SEVERITY  INFORMATIONAL
            --#TIMEINDEX 136
        ::= 136002070

   mngmtAgentTrap-2071 TRAP-TYPE
        ENTERPRISE compaq
        VARIABLES  { hostName,
                     scellNameDateTime,
                     agentEventCode,
                     agentEventDescription }
        DESCRIPTION
             "The storage system is not responding to management command requests in a timely manner. This may be due to a prior management command request with excessively long response time, or a communication problem. HP P6000 Command View will recover automatically when the storage system is able to respond to management commands. Management command access to the storage system does not affect host I/O."
           --#TYPE      "Management Agent Event 2071"
           --#SUMMARY   "Host %s : SCellName-TimeDate %s : EventCode %d : Description %s"
           --#ARGUMENTS {0,1,2,3,}
            --#SEVERITY  INFORMATIONAL
            --#TIMEINDEX 136
        ::= 136002071

   mngmtAgentTrap-2072 TRAP-TYPE
        ENTERPRISE compaq
        VARIABLES  { hostName,
                     scellNameDateTime,
                     agentEventCode,
                     agentEventDescription }
        DESCRIPTION
             "Object not found. Operation on this object is completed"
           --#TYPE      "Management Agent Event 2072"
           --#SUMMARY   "Host %s : SCellName-TimeDate %s : EventCode %d : Description %s"
           --#ARGUMENTS {0,1,2,3,}
            --#SEVERITY  INFORMATIONAL
            --#TIMEINDEX 136
        ::= 136002072

   mngmtAgentTrap-2073 TRAP-TYPE
        ENTERPRISE compaq
        VARIABLES  { hostName,
                     scellNameDateTime,
                     agentEventCode,
                     agentEventDescription }
        DESCRIPTION
             "There is no more available space"
           --#TYPE      "Management Agent Event 2073"
           --#SUMMARY   "Host %s : SCellName-TimeDate %s : EventCode %d : Description %s"
           --#ARGUMENTS {0,1,2,3,}
            --#SEVERITY  INFORMATIONAL
            --#TIMEINDEX 136
        ::= 136002073

   mngmtAgentTrap-2074 TRAP-TYPE
        ENTERPRISE compaq
        VARIABLES  { hostName,
                     scellNameDateTime,
                     agentEventCode,
                     agentEventDescription }
        DESCRIPTION
             "Name, comment or object lock comment contains invalid character(s)"
           --#TYPE      "Management Agent Event 2074"
           --#SUMMARY   "Host %s : SCellName-TimeDate %s : EventCode %d : Description %s"
           --#ARGUMENTS {0,1,2,3,}
            --#SEVERITY  INFORMATIONAL
            --#TIMEINDEX 136
        ::= 136002074

   mngmtAgentTrap-2075 TRAP-TYPE
        ENTERPRISE compaq
        VARIABLES  { hostName,
                     scellNameDateTime,
                     agentEventCode,
                     agentEventDescription }
        DESCRIPTION
             "Duplicate - Another object with the same name exists."
           --#TYPE      "Management Agent Event 2075"
           --#SUMMARY   "Host %s : SCellName-TimeDate %s : EventCode %d : Description %s"
           --#ARGUMENTS {0,1,2,3,}
            --#SEVERITY  INFORMATIONAL
            --#TIMEINDEX 136
        ::= 136002075

   mngmtAgentTrap-2076 TRAP-TYPE
        ENTERPRISE compaq
        VARIABLES  { hostName,
                     scellNameDateTime,
                     agentEventCode,
                     agentEventDescription }
        DESCRIPTION
             "No healthy disk group(s) to create a Vdisk. Resolve any abnormal conditions in the disk group first."
           --#TYPE      "Management Agent Event 2076"
           --#SUMMARY   "Host %s : SCellName-TimeDate %s : EventCode %d : Description %s"
           --#ARGUMENTS {0,1,2,3,}
            --#SEVERITY  INFORMATIONAL
            --#TIMEINDEX 136
        ::= 136002076

   mngmtAgentTrap-2077 TRAP-TYPE
        ENTERPRISE compaq
        VARIABLES  { hostName,
                     scellNameDateTime,
                     agentEventCode,
                     agentEventDescription }
        DESCRIPTION
             "Operating System ID must be a valid number."
           --#TYPE      "Management Agent Event 2077"
           --#SUMMARY   "Host %s : SCellName-TimeDate %s : EventCode %d : Description %s"
           --#ARGUMENTS {0,1,2,3,}
            --#SEVERITY  INFORMATIONAL
            --#TIMEINDEX 136
        ::= 136002077

   mngmtAgentTrap-2078 TRAP-TYPE
        ENTERPRISE compaq
        VARIABLES  { hostName,
                     scellNameDateTime,
                     agentEventCode,
                     agentEventDescription }
        DESCRIPTION
             "Watchdog successfully started"
           --#TYPE      "Management Agent Event 2078"
           --#SUMMARY   "Host %s : SCellName-TimeDate %s : EventCode %d : Description %s"
           --#ARGUMENTS {0,1,2,3,}
            --#SEVERITY  INFORMATIONAL
            --#TIMEINDEX 136
        ::= 136002078

   mngmtAgentTrap-2079 TRAP-TYPE
        ENTERPRISE compaq
        VARIABLES  { hostName,
                     scellNameDateTime,
                     agentEventCode,
                     agentEventDescription }
        DESCRIPTION
             "Watchdog successfully stopped"
           --#TYPE      "Management Agent Event 2079"
           --#SUMMARY   "Host %s : SCellName-TimeDate %s : EventCode %d : Description %s"
           --#ARGUMENTS {0,1,2,3,}
            --#SEVERITY  INFORMATIONAL
            --#TIMEINDEX 136
        ::= 136002079

   mngmtAgentTrap-2080 TRAP-TYPE
        ENTERPRISE compaq
        VARIABLES  { hostName,
                     scellNameDateTime,
                     agentEventCode,
                     agentEventDescription }
        DESCRIPTION
             "Delete Event Config List failed"
           --#TYPE      "Management Agent Event 2080"
           --#SUMMARY   "Host %s : SCellName-TimeDate %s : EventCode %d : Description %s"
           --#ARGUMENTS {0,1,2,3,}
            --#SEVERITY  MINOR
            --#TIMEINDEX 136
        ::= 136002080

   mngmtAgentTrap-2081 TRAP-TYPE
        ENTERPRISE compaq
        VARIABLES  { hostName,
                     scellNameDateTime,
                     agentEventCode,
                     agentEventDescription }
        DESCRIPTION
             "Inoperative Disk group repaired successfully."
           --#TYPE      "Management Agent Event 2081"
           --#SUMMARY   "Host %s : SCellName-TimeDate %s : EventCode %d : Description %s"
           --#ARGUMENTS {0,1,2,3,}
            --#SEVERITY  INFORMATIONAL
            --#TIMEINDEX 136
        ::= 136002081

   mngmtAgentTrap-2082 TRAP-TYPE
        ENTERPRISE compaq
        VARIABLES  { hostName,
                     scellNameDateTime,
                     agentEventCode,
                     agentEventDescription }
        DESCRIPTION
             "There are no available LUNs to present this Vdisk."
           --#TYPE      "Management Agent Event 2082"
           --#SUMMARY   "Host %s : SCellName-TimeDate %s : EventCode %d : Description %s"
           --#ARGUMENTS {0,1,2,3,}
            --#SEVERITY  INFORMATIONAL
            --#TIMEINDEX 136
        ::= 136002082

   mngmtAgentTrap-2083 TRAP-TYPE
        ENTERPRISE compaq
        VARIABLES  { hostName,
                     scellNameDateTime,
                     agentEventCode,
                     agentEventDescription }
        DESCRIPTION
             "Controller time synchronization turned on."
           --#TYPE      "Management Agent Event 2083"
           --#SUMMARY   "Host %s : SCellName-TimeDate %s : EventCode %d : Description %s"
           --#ARGUMENTS {0,1,2,3,}
            --#SEVERITY  INFORMATIONAL
            --#TIMEINDEX 136
        ::= 136002083

   mngmtAgentTrap-2084 TRAP-TYPE
        ENTERPRISE compaq
        VARIABLES  { hostName,
                     scellNameDateTime,
                     agentEventCode,
                     agentEventDescription }
        DESCRIPTION
             "Controller time synchronization turned off."
           --#TYPE      "Management Agent Event 2084"
           --#SUMMARY   "Host %s : SCellName-TimeDate %s : EventCode %d : Description %s"
           --#ARGUMENTS {0,1,2,3,}
            --#SEVERITY  INFORMATIONAL
            --#TIMEINDEX 136
        ::= 136002084

   mngmtAgentTrap-2085 TRAP-TYPE
        ENTERPRISE compaq
        VARIABLES  { hostName,
                     scellNameDateTime,
                     agentEventCode,
                     agentEventDescription }
        DESCRIPTION
             "System login failed. Invalid password."
           --#TYPE      "Management Agent Event 2085"
           --#SUMMARY   "Host %s : SCellName-TimeDate %s : EventCode %d : Description %s"
           --#ARGUMENTS {0,1,2,3,}
            --#SEVERITY  INFORMATIONAL
            --#TIMEINDEX 136
        ::= 136002085

   mngmtAgentTrap-2086 TRAP-TYPE
        ENTERPRISE compaq
        VARIABLES  { hostName,
                     scellNameDateTime,
                     agentEventCode,
                     agentEventDescription }
        DESCRIPTION
             "System is not set for password validation."
           --#TYPE      "Management Agent Event 2086"
           --#SUMMARY   "Host %s : SCellName-TimeDate %s : EventCode %d : Description %s"
           --#ARGUMENTS {0,1,2,3,}
            --#SEVERITY  INFORMATIONAL
            --#TIMEINDEX 136
        ::= 136002086

   mngmtAgentTrap-2087 TRAP-TYPE
        ENTERPRISE compaq
        VARIABLES  { hostName,
                     scellNameDateTime,
                     agentEventCode,
                     agentEventDescription }
        DESCRIPTION
             "Agent is already logged in to this system."
           --#TYPE      "Management Agent Event 2087"
           --#SUMMARY   "Host %s : SCellName-TimeDate %s : EventCode %d : Description %s"
           --#ARGUMENTS {0,1,2,3,}
            --#SEVERITY  INFORMATIONAL
            --#TIMEINDEX 136
        ::= 136002087

   mngmtAgentTrap-2088 TRAP-TYPE
        ENTERPRISE compaq
        VARIABLES  { hostName,
                     scellNameDateTime,
                     agentEventCode,
                     agentEventDescription }
        DESCRIPTION
             "Storage system time set to custom time. Controller time synchronization automatically turned off."
           --#TYPE      "Management Agent Event 2088"
           --#SUMMARY   "Host %s : SCellName-TimeDate %s : EventCode %d : Description %s"
           --#ARGUMENTS {0,1,2,3,}
            --#SEVERITY  INFORMATIONAL
            --#TIMEINDEX 136
        ::= 136002088

   mngmtAgentTrap-2089 TRAP-TYPE
        ENTERPRISE compaq
        VARIABLES  { hostName,
                     scellNameDateTime,
                     agentEventCode,
                     agentEventDescription }
        DESCRIPTION
             "Storage system time set to SAN management workstation time."
           --#TYPE      "Management Agent Event 2089"
           --#SUMMARY   "Host %s : SCellName-TimeDate %s : EventCode %d : Description %s"
           --#ARGUMENTS {0,1,2,3,}
            --#SEVERITY  INFORMATIONAL
            --#TIMEINDEX 136
        ::= 136002089

   mngmtAgentTrap-2090 TRAP-TYPE
        ENTERPRISE compaq
        VARIABLES  { hostName,
                     scellNameDateTime,
                     agentEventCode,
                     agentEventDescription }
        DESCRIPTION
             "Storage system time set to browser time. Controller time synchronization automatically turned off."
           --#TYPE      "Management Agent Event 2090"
           --#SUMMARY   "Host %s : SCellName-TimeDate %s : EventCode %d : Description %s"
           --#ARGUMENTS {0,1,2,3,}
            --#SEVERITY  INFORMATIONAL
            --#TIMEINDEX 136
        ::= 136002090

   mngmtAgentTrap-2091 TRAP-TYPE
        ENTERPRISE compaq
        VARIABLES  { hostName,
                     scellNameDateTime,
                     agentEventCode,
                     agentEventDescription }
        DESCRIPTION
             "Storage system time set to controller time. Controller time synchronization automatically turned off."
           --#TYPE      "Management Agent Event 2091"
           --#SUMMARY   "Host %s : SCellName-TimeDate %s : EventCode %d : Description %s"
           --#ARGUMENTS {0,1,2,3,}
            --#SEVERITY  INFORMATIONAL
            --#TIMEINDEX 136
        ::= 136002091

   mngmtAgentTrap-2092 TRAP-TYPE
        ENTERPRISE compaq
        VARIABLES  { hostName,
                     scellNameDateTime,
                     agentEventCode,
                     agentEventDescription }
        DESCRIPTION
             "Unable to find DR Group on remote storage system."
           --#TYPE      "Management Agent Event 2092"
           --#SUMMARY   "Host %s : SCellName-TimeDate %s : EventCode %d : Description %s"
           --#ARGUMENTS {0,1,2,3,}
            --#SEVERITY  INFORMATIONAL
            --#TIMEINDEX 136
        ::= 136002092

   mngmtAgentTrap-2093 TRAP-TYPE
        ENTERPRISE compaq
        VARIABLES  { hostName,
                     scellNameDateTime,
                     agentEventCode,
                     agentEventDescription }
        DESCRIPTION
             "A host must have at least one port. Cannot delete the only host port available."
           --#TYPE      "Management Agent Event 2093"
           --#SUMMARY   "Host %s : SCellName-TimeDate %s : EventCode %d : Description %s"
           --#ARGUMENTS {0,1,2,3,}
            --#SEVERITY  INFORMATIONAL
            --#TIMEINDEX 136
        ::= 136002093

   mngmtAgentTrap-2094 TRAP-TYPE
        ENTERPRISE compaq
        VARIABLES  { hostName,
                     scellNameDateTime,
                     agentEventCode,
                     agentEventDescription }
        DESCRIPTION
             "Present Vdisk to multiple host - Complete."
           --#TYPE      "Management Agent Event 2094"
           --#SUMMARY   "Host %s : SCellName-TimeDate %s : EventCode %d : Description %s"
           --#ARGUMENTS {0,1,2,3,}
            --#SEVERITY  INFORMATIONAL
            --#TIMEINDEX 136
        ::= 136002094

   mngmtAgentTrap-2095 TRAP-TYPE
        ENTERPRISE compaq
        VARIABLES  { hostName,
                     scellNameDateTime,
                     agentEventCode,
                     agentEventDescription }
        DESCRIPTION
             "Host creation failed. Maximum number of hosts reached."
           --#TYPE      "Management Agent Event 2095"
           --#SUMMARY   "Host %s : SCellName-TimeDate %s : EventCode %d : Description %s"
           --#ARGUMENTS {0,1,2,3,}
            --#SEVERITY  INFORMATIONAL
            --#TIMEINDEX 136
        ::= 136002095

   mngmtAgentTrap-2096 TRAP-TYPE
        ENTERPRISE compaq
        VARIABLES  { hostName,
                     scellNameDateTime,
                     agentEventCode,
                     agentEventDescription }
        DESCRIPTION
             "Port already exists."
           --#TYPE      "Management Agent Event 2096"
           --#SUMMARY   "Host %s : SCellName-TimeDate %s : EventCode %d : Description %s"
           --#ARGUMENTS {0,1,2,3,}
            --#SEVERITY  INFORMATIONAL
            --#TIMEINDEX 136
        ::= 136002096

   mngmtAgentTrap-2097 TRAP-TYPE
        ENTERPRISE compaq
        VARIABLES  { hostName,
                     scellNameDateTime,
                     agentEventCode,
                     agentEventDescription }
        DESCRIPTION
             "Error reading parameter string. String is empty."
           --#TYPE      "Management Agent Event 2097"
           --#SUMMARY   "Host %s : SCellName-TimeDate %s : EventCode %d : Description %s"
           --#ARGUMENTS {0,1,2,3,}
            --#SEVERITY  INFORMATIONAL
            --#TIMEINDEX 136
        ::= 136002097

   mngmtAgentTrap-2098 TRAP-TYPE
        ENTERPRISE compaq
        VARIABLES  { hostName,
                     scellNameDateTime,
                     agentEventCode,
                     agentEventDescription }
        DESCRIPTION
             "Command could not be completed on Master. Controller not found."
           --#TYPE      "Management Agent Event 2098"
           --#SUMMARY   "Host %s : SCellName-TimeDate %s : EventCode %d : Description %s"
           --#ARGUMENTS {0,1,2,3,}
            --#SEVERITY  INFORMATIONAL
            --#TIMEINDEX 136
        ::= 136002098

   mngmtAgentTrap-2099 TRAP-TYPE
        ENTERPRISE compaq
        VARIABLES  { hostName,
                     scellNameDateTime,
                     agentEventCode,
                     agentEventDescription }
        DESCRIPTION
             "Command could not be completed on Slave. Controller not found."
           --#TYPE      "Management Agent Event 2099"
           --#SUMMARY   "Host %s : SCellName-TimeDate %s : EventCode %d : Description %s"
           --#ARGUMENTS {0,1,2,3,}
            --#SEVERITY  INFORMATIONAL
            --#TIMEINDEX 136
        ::= 136002099

   mngmtAgentTrap-2100 TRAP-TYPE
        ENTERPRISE compaq
        VARIABLES  { hostName,
                     scellNameDateTime,
                     agentEventCode,
                     agentEventDescription }
        DESCRIPTION
             "Password access for all known storage systems is already enabled or set."
           --#TYPE      "Management Agent Event 2100"
           --#SUMMARY   "Host %s : SCellName-TimeDate %s : EventCode %d : Description %s"
           --#ARGUMENTS {0,1,2,3,}
            --#SEVERITY  INFORMATIONAL
            --#TIMEINDEX 136
        ::= 136002100

   mngmtAgentTrap-2102 TRAP-TYPE
        ENTERPRISE compaq
        VARIABLES  { hostName,
                     scellNameDateTime,
                     agentEventCode,
                     agentEventDescription }
        DESCRIPTION
             "The local storage system has reached the maximum allowable DR relationship."
           --#TYPE      "Management Agent Event 2102"
           --#SUMMARY   "Host %s : SCellName-TimeDate %s : EventCode %d : Description %s"
           --#ARGUMENTS {0,1,2,3,}
            --#SEVERITY  INFORMATIONAL
            --#TIMEINDEX 136
        ::= 136002102

   mngmtAgentTrap-2103 TRAP-TYPE
        ENTERPRISE compaq
        VARIABLES  { hostName,
                     scellNameDateTime,
                     agentEventCode,
                     agentEventDescription }
        DESCRIPTION
             "The remote storage system has reached the maximum allowable DR relationship."
           --#TYPE      "Management Agent Event 2103"
           --#SUMMARY   "Host %s : SCellName-TimeDate %s : EventCode %d : Description %s"
           --#ARGUMENTS {0,1,2,3,}
            --#SEVERITY  INFORMATIONAL
            --#TIMEINDEX 136
        ::= 136002103

   mngmtAgentTrap-2104 TRAP-TYPE
        ENTERPRISE compaq
        VARIABLES  { hostName,
                     scellNameDateTime,
                     agentEventCode,
                     agentEventDescription }
        DESCRIPTION
             "Disk Group creation failed.Please make sure that you have the specified number of online drives."
           --#TYPE      "Management Agent Event 2104"
           --#SUMMARY   "Host %s : SCellName-TimeDate %s : EventCode %d : Description %s"
           --#ARGUMENTS {0,1,2,3,}
            --#SEVERITY  INFORMATIONAL
            --#TIMEINDEX 136
        ::= 136002104

   mngmtAgentTrap-2105 TRAP-TYPE
        ENTERPRISE compaq
        VARIABLES  { hostName,
                     scellNameDateTime,
                     agentEventCode,
                     agentEventDescription }
        DESCRIPTION
             "Disk Group creation failed.Please make sure that you have the specified number of near-online drives."
           --#TYPE      "Management Agent Event 2105"
           --#SUMMARY   "Host %s : SCellName-TimeDate %s : EventCode %d : Description %s"
           --#ARGUMENTS {0,1,2,3,}
            --#SEVERITY  INFORMATIONAL
            --#TIMEINDEX 136
        ::= 136002105

   mngmtAgentTrap-2106 TRAP-TYPE
        ENTERPRISE compaq
        VARIABLES  { hostName,
                     scellNameDateTime,
                     agentEventCode,
                     agentEventDescription }
        DESCRIPTION
             "Virtual Disk Restore Successful"
           --#TYPE      "Management Agent Event 2106"
           --#SUMMARY   "Host %s : SCellName-TimeDate %s : EventCode %d : Description %s"
           --#ARGUMENTS {0,1,2,3,}
            --#SEVERITY  INFORMATIONAL
            --#TIMEINDEX 136
        ::= 136002106

   mngmtAgentTrap-2107 TRAP-TYPE
        ENTERPRISE compaq
        VARIABLES  { hostName,
                     scellNameDateTime,
                     agentEventCode,
                     agentEventDescription }
        DESCRIPTION
             "Disk drive is unmappable. The location indicator on the drive may not be activated."
           --#TYPE      "Management Agent Event 2107"
           --#SUMMARY   "Host %s : SCellName-TimeDate %s : EventCode %d : Description %s"
           --#ARGUMENTS {0,1,2,3,}
            --#SEVERITY  INFORMATIONAL
            --#TIMEINDEX 136
        ::= 136002107

   mngmtAgentTrap-2108 TRAP-TYPE
        ENTERPRISE compaq
        VARIABLES  { hostName,
                     scellNameDateTime,
                     agentEventCode,
                     agentEventDescription }
        DESCRIPTION
             "Vdisk Mirrorclone - Completed"
           --#TYPE      "Management Agent Event 2108"
           --#SUMMARY   "Host %s : SCellName-TimeDate %s : EventCode %d : Description %s"
           --#ARGUMENTS {0,1,2,3,}
            --#SEVERITY  INFORMATIONAL
            --#TIMEINDEX 136
        ::= 136002108

   mngmtAgentTrap-2109 TRAP-TYPE
        ENTERPRISE compaq
        VARIABLES  { hostName,
                     scellNameDateTime,
                     agentEventCode,
                     agentEventDescription }
        DESCRIPTION
             "Vdisk Mirrorclone - Failed"
           --#TYPE      "Management Agent Event 2109"
           --#SUMMARY   "Host %s : SCellName-TimeDate %s : EventCode %d : Description %s"
           --#ARGUMENTS {0,1,2,3,}
            --#SEVERITY  INFORMATIONAL
            --#TIMEINDEX 136
        ::= 136002109

   mngmtAgentTrap-2110 TRAP-TYPE
        ENTERPRISE compaq
        VARIABLES  { hostName,
                     scellNameDateTime,
                     agentEventCode,
                     agentEventDescription }
        DESCRIPTION
             "Disk Group creation failed.Please make sure that you have the specified number of solid-state-disk drives."
           --#TYPE      "Management Agent Event 2110"
           --#SUMMARY   "Host %s : SCellName-TimeDate %s : EventCode %d : Description %s"
           --#ARGUMENTS {0,1,2,3,}
            --#SEVERITY  INFORMATIONAL
            --#TIMEINDEX 136
        ::= 136002110

   mngmtAgentTrap-2111 TRAP-TYPE
        ENTERPRISE compaq
        VARIABLES  { hostName,
                     scellNameDateTime,
                     agentEventCode,
                     agentEventDescription }
        DESCRIPTION
             "iSCSI controller discovered successfully"
           --#TYPE      "Management Agent Event 2111"
           --#SUMMARY   "Host %s : SCellName-TimeDate %s : EventCode %d : Description %s"
           --#ARGUMENTS {0,1,2,3,}
            --#SEVERITY  INFORMATIONAL
            --#TIMEINDEX 136
        ::= 136002111

   mngmtAgentTrap-2112 TRAP-TYPE
        ENTERPRISE compaq
        VARIABLES  { hostName,
                     scellNameDateTime,
                     agentEventCode,
                     agentEventDescription }
        DESCRIPTION
             "iSCSI controller deleted successfully"
           --#TYPE      "Management Agent Event 2112"
           --#SUMMARY   "Host %s : SCellName-TimeDate %s : EventCode %d : Description %s"
           --#ARGUMENTS {0,1,2,3,}
            --#SEVERITY  INFORMATIONAL
            --#TIMEINDEX 136
        ::= 136002112

   mngmtAgentTrap-2113 TRAP-TYPE
        ENTERPRISE compaq
        VARIABLES  { hostName,
                     scellNameDateTime,
                     agentEventCode,
                     agentEventDescription }
        DESCRIPTION
             "iSCSI host created successfully"
           --#TYPE      "Management Agent Event 2113"
           --#SUMMARY   "Host %s : SCellName-TimeDate %s : EventCode %d : Description %s"
           --#ARGUMENTS {0,1,2,3,}
            --#SEVERITY  INFORMATIONAL
            --#TIMEINDEX 136
        ::= 136002113

   mngmtAgentTrap-2114 TRAP-TYPE
        ENTERPRISE compaq
        VARIABLES  { hostName,
                     scellNameDateTime,
                     agentEventCode,
                     agentEventDescription }
        DESCRIPTION
             "iSCSI host delete successfully"
           --#TYPE      "Management Agent Event 2114"
           --#SUMMARY   "Host %s : SCellName-TimeDate %s : EventCode %d : Description %s"
           --#ARGUMENTS {0,1,2,3,}
            --#SEVERITY  INFORMATIONAL
            --#TIMEINDEX 136
        ::= 136002114

   mngmtAgentTrap-2115 TRAP-TYPE
        ENTERPRISE compaq
        VARIABLES  { hostName,
                     scellNameDateTime,
                     agentEventCode,
                     agentEventDescription }
        DESCRIPTION
             "Vdisk presented to iSCSI host"
           --#TYPE      "Management Agent Event 2115"
           --#SUMMARY   "Host %s : SCellName-TimeDate %s : EventCode %d : Description %s"
           --#ARGUMENTS {0,1,2,3,}
            --#SEVERITY  INFORMATIONAL
            --#TIMEINDEX 136
        ::= 136002115

   mngmtAgentTrap-2116 TRAP-TYPE
        ENTERPRISE compaq
        VARIABLES  { hostName,
                     scellNameDateTime,
                     agentEventCode,
                     agentEventDescription }
        DESCRIPTION
             "Vdisk unpresented to iSCSI host"
           --#TYPE      "Management Agent Event 2116"
           --#SUMMARY   "Host %s : SCellName-TimeDate %s : EventCode %d : Description %s"
           --#ARGUMENTS {0,1,2,3,}
            --#SEVERITY  INFORMATIONAL
            --#TIMEINDEX 136
        ::= 136002116

   mngmtAgentTrap-2117 TRAP-TYPE
        ENTERPRISE compaq
        VARIABLES  { hostName,
                     scellNameDateTime,
                     agentEventCode,
                     agentEventDescription }
        DESCRIPTION
             "FCoE host created successfully"
           --#TYPE      "Management Agent Event 2117"
           --#SUMMARY   "Host %s : SCellName-TimeDate %s : EventCode %d : Description %s"
           --#ARGUMENTS {0,1,2,3,}
            --#SEVERITY  INFORMATIONAL
            --#TIMEINDEX 136
        ::= 136002117

   mngmtAgentTrap-2118 TRAP-TYPE
        ENTERPRISE compaq
        VARIABLES  { hostName,
                     scellNameDateTime,
                     agentEventCode,
                     agentEventDescription }
        DESCRIPTION
             "FCoE host delete successfully"
           --#TYPE      "Management Agent Event 2118"
           --#SUMMARY   "Host %s : SCellName-TimeDate %s : EventCode %d : Description %s"
           --#ARGUMENTS {0,1,2,3,}
            --#SEVERITY  INFORMATIONAL
            --#TIMEINDEX 136
        ::= 136002118

   mngmtAgentTrap-2119 TRAP-TYPE
        ENTERPRISE compaq
        VARIABLES  { hostName,
                     scellNameDateTime,
                     agentEventCode,
                     agentEventDescription }
        DESCRIPTION
             "Vdisk presented to FCoE host"
           --#TYPE      "Management Agent Event 2119"
           --#SUMMARY   "Host %s : SCellName-TimeDate %s : EventCode %d : Description %s"
           --#ARGUMENTS {0,1,2,3,}
            --#SEVERITY  INFORMATIONAL
            --#TIMEINDEX 136
        ::= 136002119

   mngmtAgentTrap-2120 TRAP-TYPE
        ENTERPRISE compaq
        VARIABLES  { hostName,
                     scellNameDateTime,
                     agentEventCode,
                     agentEventDescription }
        DESCRIPTION
             "Vdisk unpresented to FCoE host"
           --#TYPE      "Management Agent Event 2120"
           --#SUMMARY   "Host %s : SCellName-TimeDate %s : EventCode %d : Description %s"
           --#ARGUMENTS {0,1,2,3,}
            --#SEVERITY  INFORMATIONAL
            --#TIMEINDEX 136
        ::= 136002120

   mngmtAgentTrap-3001 TRAP-TYPE
        ENTERPRISE compaq
        VARIABLES  { hostName,
                     scellNameDateTime,
                     agentEventCode,
                     agentEventDescription }
        DESCRIPTION
             "Event Manager Offline"
           --#TYPE      "Management Agent Event 3001"
           --#SUMMARY   "Host %s : SCellName-TimeDate %s : EventCode %d : Description %s"
           --#ARGUMENTS {0,1,2,3,}
            --#SEVERITY  INFORMATIONAL
            --#TIMEINDEX 136
        ::= 136003001

   mngmtAgentTrap-3002 TRAP-TYPE
        ENTERPRISE compaq
        VARIABLES  { hostName,
                     scellNameDateTime,
                     agentEventCode,
                     agentEventDescription }
        DESCRIPTION
             "Event Manager Online"
           --#TYPE      "Management Agent Event 3002"
           --#SUMMARY   "Host %s : SCellName-TimeDate %s : EventCode %d : Description %s"
           --#ARGUMENTS {0,1,2,3,}
            --#SEVERITY  INFORMATIONAL
            --#TIMEINDEX 136
        ::= 136003002

   mngmtAgentTrap-3003 TRAP-TYPE
        ENTERPRISE compaq
        VARIABLES  { hostName,
                     scellNameDateTime,
                     agentEventCode,
                     agentEventDescription }
        DESCRIPTION
             "Event Manager - Startup Failed"
           --#TYPE      "Management Agent Event 3003"
           --#SUMMARY   "Host %s : SCellName-TimeDate %s : EventCode %d : Description %s"
           --#ARGUMENTS {0,1,2,3,}
            --#SEVERITY  CRITICAL
            --#TIMEINDEX 136
        ::= 136003003

   mngmtAgentTrap-3004 TRAP-TYPE
        ENTERPRISE compaq
        VARIABLES  { hostName,
                     scellNameDateTime,
                     agentEventCode,
                     agentEventDescription }
        DESCRIPTION
             "Event Manager - Startup Complete"
           --#TYPE      "Management Agent Event 3004"
           --#SUMMARY   "Host %s : SCellName-TimeDate %s : EventCode %d : Description %s"
           --#ARGUMENTS {0,1,2,3,}
            --#SEVERITY  INFORMATIONAL
            --#TIMEINDEX 136
        ::= 136003004

   mngmtAgentTrap-3007 TRAP-TYPE
        ENTERPRISE compaq
        VARIABLES  { hostName,
                     scellNameDateTime,
                     agentEventCode,
                     agentEventDescription }
        DESCRIPTION
             "Event Manager - Shutdown Complete"
           --#TYPE      "Management Agent Event 3007"
           --#SUMMARY   "Host %s : SCellName-TimeDate %s : EventCode %d : Description %s"
           --#ARGUMENTS {0,1,2,3,}
            --#SEVERITY  INFORMATIONAL
            --#TIMEINDEX 136
        ::= 136003007

   mngmtAgentTrap-3009 TRAP-TYPE
        ENTERPRISE compaq
        VARIABLES  { hostName,
                     scellNameDateTime,
                     agentEventCode,
                     agentEventDescription }
        DESCRIPTION
             "Unable to open NSA Local Event Log File"
           --#TYPE      "Management Agent Event 3009"
           --#SUMMARY   "Host %s : SCellName-TimeDate %s : EventCode %d : Description %s"
           --#ARGUMENTS {0,1,2,3,}
            --#SEVERITY  MINOR
            --#TIMEINDEX 136
        ::= 136003009

   mngmtAgentTrap-3012 TRAP-TYPE
        ENTERPRISE compaq
        VARIABLES  { hostName,
                     scellNameDateTime,
                     agentEventCode,
                     agentEventDescription }
        DESCRIPTION
             "Unable to open Local Temp Event File - possibly no initialized SC"
           --#TYPE      "Management Agent Event 3012"
           --#SUMMARY   "Host %s : SCellName-TimeDate %s : EventCode %d : Description %s"
           --#ARGUMENTS {0,1,2,3,}
            --#SEVERITY  MINOR
            --#TIMEINDEX 136
        ::= 136003012

   mngmtAgentTrap-3013 TRAP-TYPE
        ENTERPRISE compaq
        VARIABLES  { hostName,
                     scellNameDateTime,
                     agentEventCode,
                     agentEventDescription }
        DESCRIPTION
             "Unable to clear NSA Local Event Log File"
           --#TYPE      "Management Agent Event 3013"
           --#SUMMARY   "Host %s : SCellName-TimeDate %s : EventCode %d : Description %s"
           --#ARGUMENTS {0,1,2,3,}
            --#SEVERITY  MINOR
            --#TIMEINDEX 136
        ::= 136003013

   mngmtAgentTrap-3015 TRAP-TYPE
        ENTERPRISE compaq
        VARIABLES  { hostName,
                     scellNameDateTime,
                     agentEventCode,
                     agentEventDescription }
        DESCRIPTION
             "Unable to clear NSA Event Log File"
           --#TYPE      "Management Agent Event 3015"
           --#SUMMARY   "Host %s : SCellName-TimeDate %s : EventCode %d : Description %s"
           --#ARGUMENTS {0,1,2,3,}
            --#SEVERITY  MINOR
            --#TIMEINDEX 136
        ::= 136003015

   mngmtAgentTrap-3016 TRAP-TYPE
        ENTERPRISE compaq
        VARIABLES  { hostName,
                     scellNameDateTime,
                     agentEventCode,
                     agentEventDescription }
        DESCRIPTION
             "Local log file found on startup"
           --#TYPE      "Management Agent Event 3016"
           --#SUMMARY   "Host %s : SCellName-TimeDate %s : EventCode %d : Description %s"
           --#ARGUMENTS {0,1,2,3,}
            --#SEVERITY  MINOR
            --#TIMEINDEX 136
        ::= 136003016

   mngmtAgentTrap-3017 TRAP-TYPE
        ENTERPRISE compaq
        VARIABLES  { hostName,
                     scellNameDateTime,
                     agentEventCode,
                     agentEventDescription }
        DESCRIPTION
             "Event Queue Flush Error"
           --#TYPE      "Management Agent Event 3017"
           --#SUMMARY   "Host %s : SCellName-TimeDate %s : EventCode %d : Description %s"
           --#ARGUMENTS {0,1,2,3,}
            --#SEVERITY  MINOR
            --#TIMEINDEX 136
        ::= 136003017

   mngmtAgentTrap-3019 TRAP-TYPE
        ENTERPRISE compaq
        VARIABLES  { hostName,
                     scellNameDateTime,
                     agentEventCode,
                     agentEventDescription }
        DESCRIPTION
             "EM File Manager Online"
           --#TYPE      "Management Agent Event 3019"
           --#SUMMARY   "Host %s : SCellName-TimeDate %s : EventCode %d : Description %s"
           --#ARGUMENTS {0,1,2,3,}
            --#SEVERITY  INFORMATIONAL
            --#TIMEINDEX 136
        ::= 136003019

   mngmtAgentTrap-3020 TRAP-TYPE
        ENTERPRISE compaq
        VARIABLES  { hostName,
                     scellNameDateTime,
                     agentEventCode,
                     agentEventDescription }
        DESCRIPTION
             "EM File Manager Offline"
           --#TYPE      "Management Agent Event 3020"
           --#SUMMARY   "Host %s : SCellName-TimeDate %s : EventCode %d : Description %s"
           --#ARGUMENTS {0,1,2,3,}
            --#SEVERITY  INFORMATIONAL
            --#TIMEINDEX 136
        ::= 136003020

   mngmtAgentTrap-3021 TRAP-TYPE
        ENTERPRISE compaq
        VARIABLES  { hostName,
                     scellNameDateTime,
                     agentEventCode,
                     agentEventDescription }
        DESCRIPTION
             "EM Log Manager Online"
           --#TYPE      "Management Agent Event 3021"
           --#SUMMARY   "Host %s : SCellName-TimeDate %s : EventCode %d : Description %s"
           --#ARGUMENTS {0,1,2,3,}
            --#SEVERITY  INFORMATIONAL
            --#TIMEINDEX 136
        ::= 136003021

   mngmtAgentTrap-3022 TRAP-TYPE
        ENTERPRISE compaq
        VARIABLES  { hostName,
                     scellNameDateTime,
                     agentEventCode,
                     agentEventDescription }
        DESCRIPTION
             "EM Log Manager Offline"
           --#TYPE      "Management Agent Event 3022"
           --#SUMMARY   "Host %s : SCellName-TimeDate %s : EventCode %d : Description %s"
           --#ARGUMENTS {0,1,2,3,}
            --#SEVERITY  INFORMATIONAL
            --#TIMEINDEX 136
        ::= 136003022

   mngmtAgentTrap-3024 TRAP-TYPE
        ENTERPRISE compaq
        VARIABLES  { hostName,
                     scellNameDateTime,
                     agentEventCode,
                     agentEventDescription }
        DESCRIPTION
             "Local NSA logfile is empty"
           --#TYPE      "Management Agent Event 3024"
           --#SUMMARY   "Host %s : SCellName-TimeDate %s : EventCode %d : Description %s"
           --#ARGUMENTS {0,1,2,3,}
            --#SEVERITY  INFORMATIONAL
            --#TIMEINDEX 136
        ::= 136003024

   mngmtAgentTrap-3025 TRAP-TYPE
        ENTERPRISE compaq
        VARIABLES  { hostName,
                     scellNameDateTime,
                     agentEventCode,
                     agentEventDescription }
        DESCRIPTION
             "Event Queue Online"
           --#TYPE      "Management Agent Event 3025"
           --#SUMMARY   "Host %s : SCellName-TimeDate %s : EventCode %d : Description %s"
           --#ARGUMENTS {0,1,2,3,}
            --#SEVERITY  INFORMATIONAL
            --#TIMEINDEX 136
        ::= 136003025

   mngmtAgentTrap-3028 TRAP-TYPE
        ENTERPRISE compaq
        VARIABLES  { hostName,
                     scellNameDateTime,
                     agentEventCode,
                     agentEventDescription }
        DESCRIPTION
             "Status Descriptions Unavailable"
           --#TYPE      "Management Agent Event 3028"
           --#SUMMARY   "Host %s : SCellName-TimeDate %s : EventCode %d : Description %s"
           --#ARGUMENTS {0,1,2,3,}
            --#SEVERITY  MINOR
            --#TIMEINDEX 136
        ::= 136003028

   mngmtAgentTrap-3029 TRAP-TYPE
        ENTERPRISE compaq
        VARIABLES  { hostName,
                     scellNameDateTime,
                     agentEventCode,
                     agentEventDescription }
        DESCRIPTION
             "EM Description Mngr Online"
           --#TYPE      "Management Agent Event 3029"
           --#SUMMARY   "Host %s : SCellName-TimeDate %s : EventCode %d : Description %s"
           --#ARGUMENTS {0,1,2,3,}
            --#SEVERITY  INFORMATIONAL
            --#TIMEINDEX 136
        ::= 136003029

   mngmtAgentTrap-3035 TRAP-TYPE
        ENTERPRISE compaq
        VARIABLES  { hostName,
                     scellNameDateTime,
                     agentEventCode,
                     agentEventDescription }
        DESCRIPTION
             "EM: NSA log file unavailable"
           --#TYPE      "Management Agent Event 3035"
           --#SUMMARY   "Host %s : SCellName-TimeDate %s : EventCode %d : Description %s"
           --#ARGUMENTS {0,1,2,3,}
            --#SEVERITY  MINOR
            --#TIMEINDEX 136
        ::= 136003035

   mngmtAgentTrap-3036 TRAP-TYPE
        ENTERPRISE compaq
        VARIABLES  { hostName,
                     scellNameDateTime,
                     agentEventCode,
                     agentEventDescription }
        DESCRIPTION
             "EM Memory Allocation Error"
           --#TYPE      "Management Agent Event 3036"
           --#SUMMARY   "Host %s : SCellName-TimeDate %s : EventCode %d : Description %s"
           --#ARGUMENTS {0,1,2,3,}
            --#SEVERITY  CRITICAL
            --#TIMEINDEX 136
        ::= 136003036

   mngmtAgentTrap-3037 TRAP-TYPE
        ENTERPRISE compaq
        VARIABLES  { hostName,
                     scellNameDateTime,
                     agentEventCode,
                     agentEventDescription }
        DESCRIPTION
             "EM: Local Event Configuration File Unavailable"
           --#TYPE      "Management Agent Event 3037"
           --#SUMMARY   "Host %s : SCellName-TimeDate %s : EventCode %d : Description %s"
           --#ARGUMENTS {0,1,2,3,}
            --#SEVERITY  MINOR
            --#TIMEINDEX 136
        ::= 136003037

   mngmtAgentTrap-3038 TRAP-TYPE
        ENTERPRISE compaq
        VARIABLES  { hostName,
                     scellNameDateTime,
                     agentEventCode,
                     agentEventDescription }
        DESCRIPTION
             "EM: MLD Notification File Unavailable - retrieving local backup copy"
           --#TYPE      "Management Agent Event 3038"
           --#SUMMARY   "Host %s : SCellName-TimeDate %s : EventCode %d : Description %s"
           --#ARGUMENTS {0,1,2,3,}
            --#SEVERITY  MINOR
            --#TIMEINDEX 136
        ::= 136003038

   mngmtAgentTrap-3039 TRAP-TYPE
        ENTERPRISE compaq
        VARIABLES  { hostName,
                     scellNameDateTime,
                     agentEventCode,
                     agentEventDescription }
        DESCRIPTION
             "EM: Local Notification Host List File Unavailable"
           --#TYPE      "Management Agent Event 3039"
           --#SUMMARY   "Host %s : SCellName-TimeDate %s : EventCode %d : Description %s"
           --#ARGUMENTS {0,1,2,3,}
            --#SEVERITY  MINOR
            --#TIMEINDEX 136
        ::= 136003039

   mngmtAgentTrap-3044 TRAP-TYPE
        ENTERPRISE compaq
        VARIABLES  { hostName,
                     scellNameDateTime,
                     agentEventCode,
                     agentEventDescription }
        DESCRIPTION
             "Override this description with missing filename"
           --#TYPE      "Management Agent Event 3044"
           --#SUMMARY   "Host %s : SCellName-TimeDate %s : EventCode %d : Description %s"
           --#ARGUMENTS {0,1,2,3,}
            --#SEVERITY  INFORMATIONAL
            --#TIMEINDEX 136
        ::= 136003044

   mngmtAgentTrap-3045 TRAP-TYPE
        ENTERPRISE compaq
        VARIABLES  { hostName,
                     scellNameDateTime,
                     agentEventCode,
                     agentEventDescription }
        DESCRIPTION
             "Invalid storage system event sequence number - can't retrieve event"
           --#TYPE      "Management Agent Event 3045"
           --#SUMMARY   "Host %s : SCellName-TimeDate %s : EventCode %d : Description %s"
           --#ARGUMENTS {0,1,2,3,}
            --#SEVERITY  INFORMATIONAL
            --#TIMEINDEX 136
        ::= 136003045

   mngmtAgentTrap-3046 TRAP-TYPE
        ENTERPRISE compaq
        VARIABLES  { hostName,
                     scellNameDateTime,
                     agentEventCode,
                     agentEventDescription }
        DESCRIPTION
             "Invalid SC termination event sequence number - can't retrieve event"
           --#TYPE      "Management Agent Event 3046"
           --#SUMMARY   "Host %s : SCellName-TimeDate %s : EventCode %d : Description %s"
           --#ARGUMENTS {0,1,2,3,}
            --#SEVERITY  INFORMATIONAL
            --#TIMEINDEX 136
        ::= 136003046

   mngmtAgentTrap-3047 TRAP-TYPE
        ENTERPRISE compaq
        VARIABLES  { hostName,
                     scellNameDateTime,
                     agentEventCode,
                     agentEventDescription }
        DESCRIPTION
             "EM: Event config file unavailable from MLD - retrieving local backup copy"
           --#TYPE      "Management Agent Event 3047"
           --#SUMMARY   "Host %s : SCellName-TimeDate %s : EventCode %d : Description %s"
           --#ARGUMENTS {0,1,2,3,}
            --#SEVERITY  MINOR
            --#TIMEINDEX 136
        ::= 136003047

   mngmtAgentTrap-3048 TRAP-TYPE
        ENTERPRISE compaq
        VARIABLES  { hostName,
                     scellNameDateTime,
                     agentEventCode,
                     agentEventDescription }
        DESCRIPTION
             "EM: Local user defined event state file unavailable"
           --#TYPE      "Management Agent Event 3048"
           --#SUMMARY   "Host %s : SCellName-TimeDate %s : EventCode %d : Description %s"
           --#ARGUMENTS {0,1,2,3,}
            --#SEVERITY  INFORMATIONAL
            --#TIMEINDEX 136
        ::= 136003048

   mngmtAgentTrap-3049 TRAP-TYPE
        ENTERPRISE compaq
        VARIABLES  { hostName,
                     scellNameDateTime,
                     agentEventCode,
                     agentEventDescription }
        DESCRIPTION
             "EM: EMU event monitoring thread unable to start"
           --#TYPE      "Management Agent Event 3049"
           --#SUMMARY   "Host %s : SCellName-TimeDate %s : EventCode %d : Description %s"
           --#ARGUMENTS {0,1,2,3,}
            --#SEVERITY  INFORMATIONAL
            --#TIMEINDEX 136
        ::= 136003049

   mngmtAgentTrap-3050 TRAP-TYPE
        ENTERPRISE compaq
        VARIABLES  { hostName,
                     scellNameDateTime,
                     agentEventCode,
                     agentEventDescription }
        DESCRIPTION
             "EM: EMU event - this description will be overwritten"
           --#TYPE      "Management Agent Event 3050"
           --#SUMMARY   "Host %s : SCellName-TimeDate %s : EventCode %d : Description %s"
           --#ARGUMENTS {0,1,2,3,}
            --#SEVERITY  CRITICAL
            --#TIMEINDEX 136
        ::= 136003050

   mngmtAgentTrap-3051 TRAP-TYPE
        ENTERPRISE compaq
        VARIABLES  { hostName,
                     scellNameDateTime,
                     agentEventCode,
                     agentEventDescription }
        DESCRIPTION
             "EM: Failed to write Event Config file to MLD"
           --#TYPE      "Management Agent Event 3051"
           --#SUMMARY   "Host %s : SCellName-TimeDate %s : EventCode %d : Description %s"
           --#ARGUMENTS {0,1,2,3,}
            --#SEVERITY  MINOR
            --#TIMEINDEX 136
        ::= 136003051

   mngmtAgentTrap-3053 TRAP-TYPE
        ENTERPRISE compaq
        VARIABLES  { hostName,
                     scellNameDateTime,
                     agentEventCode,
                     agentEventDescription }
        DESCRIPTION
             "EM: Event Configuration Filename Error or File empty"
           --#TYPE      "Management Agent Event 3053"
           --#SUMMARY   "Host %s : SCellName-TimeDate %s : EventCode %d : Description %s"
           --#ARGUMENTS {0,1,2,3,}
            --#SEVERITY  INFORMATIONAL
            --#TIMEINDEX 136
        ::= 136003053

   mngmtAgentTrap-3054 TRAP-TYPE
        ENTERPRISE compaq
        VARIABLES  { hostName,
                     scellNameDateTime,
                     agentEventCode,
                     agentEventDescription }
        DESCRIPTION
             "EM: Notification Hostlist Filename Error or File empty"
           --#TYPE      "Management Agent Event 3054"
           --#SUMMARY   "Host %s : SCellName-TimeDate %s : EventCode %d : Description %s"
           --#ARGUMENTS {0,1,2,3,}
            --#SEVERITY  INFORMATIONAL
            --#TIMEINDEX 136
        ::= 136003054

   mngmtAgentTrap-3055 TRAP-TYPE
        ENTERPRISE compaq
        VARIABLES  { hostName,
                     scellNameDateTime,
                     agentEventCode,
                     agentEventDescription }
        DESCRIPTION
             "EM: Event Config List Object Reference Error"
           --#TYPE      "Management Agent Event 3055"
           --#SUMMARY   "Host %s : SCellName-TimeDate %s : EventCode %d : Description %s"
           --#ARGUMENTS {0,1,2,3,}
            --#SEVERITY  MINOR
            --#TIMEINDEX 136
        ::= 136003055

   mngmtAgentTrap-3056 TRAP-TYPE
        ENTERPRISE compaq
        VARIABLES  { hostName,
                     scellNameDateTime,
                     agentEventCode,
                     agentEventDescription }
        DESCRIPTION
             "EM: SC Parse File successfully uploaded"
           --#TYPE      "Management Agent Event 3056"
           --#SUMMARY   "Host %s : SCellName-TimeDate %s : EventCode %d : Description %s"
           --#ARGUMENTS {0,1,2,3,}
            --#SEVERITY  INFORMATIONAL
            --#TIMEINDEX 136
        ::= 136003056

   mngmtAgentTrap-3057 TRAP-TYPE
        ENTERPRISE compaq
        VARIABLES  { hostName,
                     scellNameDateTime,
                     agentEventCode,
                     agentEventDescription }
        DESCRIPTION
             "EM: SC Parse File upload failed"
           --#TYPE      "Management Agent Event 3057"
           --#SUMMARY   "Host %s : SCellName-TimeDate %s : EventCode %d : Description %s"
           --#ARGUMENTS {0,1,2,3,}
            --#SEVERITY  INFORMATIONAL
            --#TIMEINDEX 136
        ::= 136003057

   mngmtAgentTrap-3058 TRAP-TYPE
        ENTERPRISE compaq
        VARIABLES  { hostName,
                     scellNameDateTime,
                     agentEventCode,
                     agentEventDescription }
        DESCRIPTION
             "EM: Contents of the uploaded parse file invalid - unexpected contents"
           --#TYPE      "Management Agent Event 3058"
           --#SUMMARY   "Host %s : SCellName-TimeDate %s : EventCode %d : Description %s"
           --#ARGUMENTS {0,1,2,3,}
            --#SEVERITY  MINOR
            --#TIMEINDEX 136
        ::= 136003058

   mngmtAgentTrap-3059 TRAP-TYPE
        ENTERPRISE compaq
        VARIABLES  { hostName,
                     scellNameDateTime,
                     agentEventCode,
                     agentEventDescription }
        DESCRIPTION
             "EM: Parse file is empty"
           --#TYPE      "Management Agent Event 3059"
           --#SUMMARY   "Host %s : SCellName-TimeDate %s : EventCode %d : Description %s"
           --#ARGUMENTS {0,1,2,3,}
            --#SEVERITY  MINOR
            --#TIMEINDEX 136
        ::= 136003059

   mngmtAgentTrap-3060 TRAP-TYPE
        ENTERPRISE compaq
        VARIABLES  { hostName,
                     scellNameDateTime,
                     agentEventCode,
                     agentEventDescription }
        DESCRIPTION
             "Storage system being shutdown due to a command failure."
           --#TYPE      "Management Agent Event 3060"
           --#SUMMARY   "Host %s : SCellName-TimeDate %s : EventCode %d : Description %s"
           --#ARGUMENTS {0,1,2,3,}
            --#SEVERITY  CRITICAL
            --#TIMEINDEX 136
        ::= 136003060

   mngmtAgentTrap-3061 TRAP-TYPE
        ENTERPRISE compaq
        VARIABLES  { hostName,
                     scellNameDateTime,
                     agentEventCode,
                     agentEventDescription }
        DESCRIPTION
             "EM: Could not retrieve a storage system event"
           --#TYPE      "Management Agent Event 3061"
           --#SUMMARY   "Host %s : SCellName-TimeDate %s : EventCode %d : Description %s"
           --#ARGUMENTS {0,1,2,3,}
            --#SEVERITY  INFORMATIONAL
            --#TIMEINDEX 136
        ::= 136003061

   mngmtAgentTrap-3062 TRAP-TYPE
        ENTERPRISE compaq
        VARIABLES  { hostName,
                     scellNameDateTime,
                     agentEventCode,
                     agentEventDescription }
        DESCRIPTION
             "EM: Init SC Event config list failed"
           --#TYPE      "Management Agent Event 3062"
           --#SUMMARY   "Host %s : SCellName-TimeDate %s : EventCode %d : Description %s"
           --#ARGUMENTS {0,1,2,3,}
            --#SEVERITY  INFORMATIONAL
            --#TIMEINDEX 136
        ::= 136003062

   mngmtAgentTrap-3063 TRAP-TYPE
        ENTERPRISE compaq
        VARIABLES  { hostName,
                     scellNameDateTime,
                     agentEventCode,
                     agentEventDescription }
        DESCRIPTION
             "Could not initialize Comm infrastructure for event logging to system log"
           --#TYPE      "Management Agent Event 3063"
           --#SUMMARY   "Host %s : SCellName-TimeDate %s : EventCode %d : Description %s"
           --#ARGUMENTS {0,1,2,3,}
            --#SEVERITY  MINOR
            --#TIMEINDEX 136
        ::= 136003063

   mngmtAgentTrap-3064 TRAP-TYPE
        ENTERPRISE compaq
        VARIABLES  { hostName,
                     scellNameDateTime,
                     agentEventCode,
                     agentEventDescription }
        DESCRIPTION
             "EM: Storage system pointer is NULL!"
           --#TYPE      "Management Agent Event 3064"
           --#SUMMARY   "Host %s : SCellName-TimeDate %s : EventCode %d : Description %s"
           --#ARGUMENTS {0,1,2,3,}
            --#SEVERITY  CRITICAL
            --#TIMEINDEX 136
        ::= 136003064

   mngmtAgentTrap-3065 TRAP-TYPE
        ENTERPRISE compaq
        VARIABLES  { hostName,
                     scellNameDateTime,
                     agentEventCode,
                     agentEventDescription }
        DESCRIPTION
             "EM: Failed to log event to the Windows Application Event Log - Windows Application Event Log may be full."
           --#TYPE      "Management Agent Event 3065"
           --#SUMMARY   "Host %s : SCellName-TimeDate %s : EventCode %d : Description %s"
           --#ARGUMENTS {0,1,2,3,}
            --#SEVERITY  CRITICAL
            --#TIMEINDEX 136
        ::= 136003065

   mngmtAgentTrap-3066 TRAP-TYPE
        ENTERPRISE compaq
        VARIABLES  { hostName,
                     scellNameDateTime,
                     agentEventCode,
                     agentEventDescription }
        DESCRIPTION
             "EM: Description Mngr initialize storage system failed"
           --#TYPE      "Management Agent Event 3066"
           --#SUMMARY   "Host %s : SCellName-TimeDate %s : EventCode %d : Description %s"
           --#ARGUMENTS {0,1,2,3,}
            --#SEVERITY  MINOR
            --#TIMEINDEX 136
        ::= 136003066

   mngmtAgentTrap-3067 TRAP-TYPE
        ENTERPRISE compaq
        VARIABLES  { hostName,
                     scellNameDateTime,
                     agentEventCode,
                     agentEventDescription }
        DESCRIPTION
             "EM: Description file too small. File read problem Or Incomplete file."
           --#TYPE      "Management Agent Event 3067"
           --#SUMMARY   "Host %s : SCellName-TimeDate %s : EventCode %d : Description %s"
           --#ARGUMENTS {0,1,2,3,}
            --#SEVERITY  MINOR
            --#TIMEINDEX 136
        ::= 136003067

   mngmtAgentTrap-3068 TRAP-TYPE
        ENTERPRISE compaq
        VARIABLES  { hostName,
                     scellNameDateTime,
                     agentEventCode,
                     agentEventDescription }
        DESCRIPTION
             "EM: Can't init NT Event object pointer"
           --#TYPE      "Management Agent Event 3068"
           --#SUMMARY   "Host %s : SCellName-TimeDate %s : EventCode %d : Description %s"
           --#ARGUMENTS {0,1,2,3,}
            --#SEVERITY  CRITICAL
            --#TIMEINDEX 136
        ::= 136003068

   mngmtAgentTrap-3069 TRAP-TYPE
        ENTERPRISE compaq
        VARIABLES  { hostName,
                     scellNameDateTime,
                     agentEventCode,
                     agentEventDescription }
        DESCRIPTION
             "EM: Can't init NT Notification object pointer"
           --#TYPE      "Management Agent Event 3069"
           --#SUMMARY   "Host %s : SCellName-TimeDate %s : EventCode %d : Description %s"
           --#ARGUMENTS {0,1,2,3,}
            --#SEVERITY  CRITICAL
            --#TIMEINDEX 136
        ::= 136003069

   mngmtAgentTrap-3070 TRAP-TYPE
        ENTERPRISE compaq
        VARIABLES  { hostName,
                     scellNameDateTime,
                     agentEventCode,
                     agentEventDescription }
        DESCRIPTION
             "EM: Management Workstation Event Logging Failure - Windows Application Event Log may be full."
           --#TYPE      "Management Agent Event 3070"
           --#SUMMARY   "Host %s : SCellName-TimeDate %s : EventCode %d : Description %s"
           --#ARGUMENTS {0,1,2,3,}
            --#SEVERITY  CRITICAL
            --#TIMEINDEX 136
        ::= 136003070

   mngmtAgentTrap-3071 TRAP-TYPE
        ENTERPRISE compaq
        VARIABLES  { hostName,
                     scellNameDateTime,
                     agentEventCode,
                     agentEventDescription }
        DESCRIPTION
             "EM: SCMI returned bad additional events number"
           --#TYPE      "Management Agent Event 3071"
           --#SUMMARY   "Host %s : SCellName-TimeDate %s : EventCode %d : Description %s"
           --#ARGUMENTS {0,1,2,3,}
            --#SEVERITY  MINOR
            --#TIMEINDEX 136
        ::= 136003071

   mngmtAgentTrap-3072 TRAP-TYPE
        ENTERPRISE compaq
        VARIABLES  { hostName,
                     scellNameDateTime,
                     agentEventCode,
                     agentEventDescription }
        DESCRIPTION
             "EM: SCMI returned zero sized SC Event"
           --#TYPE      "Management Agent Event 3072"
           --#SUMMARY   "Host %s : SCellName-TimeDate %s : EventCode %d : Description %s"
           --#ARGUMENTS {0,1,2,3,}
            --#SEVERITY  MINOR
            --#TIMEINDEX 136
        ::= 136003072

   mngmtAgentTrap-3075 TRAP-TYPE
        ENTERPRISE compaq
        VARIABLES  { hostName,
                     scellNameDateTime,
                     agentEventCode,
                     agentEventDescription }
        DESCRIPTION
             "EventQueue index passed is out of bounds"
           --#TYPE      "Management Agent Event 3075"
           --#SUMMARY   "Host %s : SCellName-TimeDate %s : EventCode %d : Description %s"
           --#ARGUMENTS {0,1,2,3,}
            --#SEVERITY  INFORMATIONAL
            --#TIMEINDEX 136
        ::= 136003075

   mngmtAgentTrap-3076 TRAP-TYPE
        ENTERPRISE compaq
        VARIABLES  { hostName,
                     scellNameDateTime,
                     agentEventCode,
                     agentEventDescription }
        DESCRIPTION
             "EM: An abnormal number of duplicate events logged - dropping duplicates"
           --#TYPE      "Management Agent Event 3076"
           --#SUMMARY   "Host %s : SCellName-TimeDate %s : EventCode %d : Description %s"
           --#ARGUMENTS {0,1,2,3,}
            --#SEVERITY  MINOR
            --#TIMEINDEX 136
        ::= 136003076

   mngmtAgentTrap-3077 TRAP-TYPE
        ENTERPRISE compaq
        VARIABLES  { hostName,
                     scellNameDateTime,
                     agentEventCode,
                     agentEventDescription }
        DESCRIPTION
             "EM: Update of the MLD Status Description file failed"
           --#TYPE      "Management Agent Event 3077"
           --#SUMMARY   "Host %s : SCellName-TimeDate %s : EventCode %d : Description %s"
           --#ARGUMENTS {0,1,2,3,}
            --#SEVERITY  INFORMATIONAL
            --#TIMEINDEX 136
        ::= 136003077

   mngmtAgentTrap-3078 TRAP-TYPE
        ENTERPRISE compaq
        VARIABLES  { hostName,
                     scellNameDateTime,
                     agentEventCode,
                     agentEventDescription }
        DESCRIPTION
             "EM: NsaStatusDescriptions.txt open file error"
           --#TYPE      "Management Agent Event 3078"
           --#SUMMARY   "Host %s : SCellName-TimeDate %s : EventCode %d : Description %s"
           --#ARGUMENTS {0,1,2,3,}
            --#SEVERITY  INFORMATIONAL
            --#TIMEINDEX 136
        ::= 136003078

   mngmtAgentTrap-3079 TRAP-TYPE
        ENTERPRISE compaq
        VARIABLES  { hostName,
                     scellNameDateTime,
                     agentEventCode,
                     agentEventDescription }
        DESCRIPTION
             "EM: NsaStatusDescriptions.txt file error - file size discrepancy from mld list"
           --#TYPE      "Management Agent Event 3079"
           --#SUMMARY   "Host %s : SCellName-TimeDate %s : EventCode %d : Description %s"
           --#ARGUMENTS {0,1,2,3,}
            --#SEVERITY  INFORMATIONAL
            --#TIMEINDEX 136
        ::= 136003079

   mngmtAgentTrap-3080 TRAP-TYPE
        ENTERPRISE compaq
        VARIABLES  { hostName,
                     scellNameDateTime,
                     agentEventCode,
                     agentEventDescription }
        DESCRIPTION
             "SC Event Log has been cleared and restarted.  Possibly disk group has gone into an inoperative state."
           --#TYPE      "Management Agent Event 3080"
           --#SUMMARY   "Host %s : SCellName-TimeDate %s : EventCode %d : Description %s"
           --#ARGUMENTS {0,1,2,3,}
            --#SEVERITY  CRITICAL
            --#TIMEINDEX 136
        ::= 136003080

   mngmtAgentTrap-3081 TRAP-TYPE
        ENTERPRISE compaq
        VARIABLES  { hostName,
                     scellNameDateTime,
                     agentEventCode,
                     agentEventDescription }
        DESCRIPTION
             "Invalid logType parameter"
           --#TYPE      "Management Agent Event 3081"
           --#SUMMARY   "Host %s : SCellName-TimeDate %s : EventCode %d : Description %s"
           --#ARGUMENTS {0,1,2,3,}
            --#SEVERITY  INFORMATIONAL
            --#TIMEINDEX 136
        ::= 136003081

   mngmtAgentTrap-3083 TRAP-TYPE
        ENTERPRISE compaq
        VARIABLES  { hostName,
                     scellNameDateTime,
                     agentEventCode,
                     agentEventDescription }
        DESCRIPTION
             "Log file is empty"
           --#TYPE      "Management Agent Event 3083"
           --#SUMMARY   "Host %s : SCellName-TimeDate %s : EventCode %d : Description %s"
           --#ARGUMENTS {0,1,2,3,}
            --#SEVERITY  INFORMATIONAL
            --#TIMEINDEX 136
        ::= 136003083

   mngmtAgentTrap-3084 TRAP-TYPE
        ENTERPRISE compaq
        VARIABLES  { hostName,
                     scellNameDateTime,
                     agentEventCode,
                     agentEventDescription }
        DESCRIPTION
             "Storage System with this WWN is not visible to this agent or the WWN is invalid"
           --#TYPE      "Management Agent Event 3084"
           --#SUMMARY   "Host %s : SCellName-TimeDate %s : EventCode %d : Description %s"
           --#ARGUMENTS {0,1,2,3,}
            --#SEVERITY  INFORMATIONAL
            --#TIMEINDEX 136
        ::= 136003084

   mngmtAgentTrap-3086 TRAP-TYPE
        ENTERPRISE compaq
        VARIABLES  { hostName,
                     scellNameDateTime,
                     agentEventCode,
                     agentEventDescription }
        DESCRIPTION
             "Parsefile for current firmware version not found.  Upload correct parse file."
           --#TYPE      "Management Agent Event 3086"
           --#SUMMARY   "Host %s : SCellName-TimeDate %s : EventCode %d : Description %s"
           --#ARGUMENTS {0,1,2,3,}
            --#SEVERITY  INFORMATIONAL
            --#TIMEINDEX 136
        ::= 136003086

   mngmtAgentTrap-3090 TRAP-TYPE
        ENTERPRISE compaq
        VARIABLES  { hostName,
                     scellNameDateTime,
                     agentEventCode,
                     agentEventDescription }
        DESCRIPTION
             "The contents of this file appear to be invalid"
           --#TYPE      "Management Agent Event 3090"
           --#SUMMARY   "Host %s : SCellName-TimeDate %s : EventCode %d : Description %s"
           --#ARGUMENTS {0,1,2,3,}
            --#SEVERITY  INFORMATIONAL
            --#TIMEINDEX 136
        ::= 136003090

   mngmtAgentTrap-3091 TRAP-TYPE
        ENTERPRISE compaq
        VARIABLES  { hostName,
                     scellNameDateTime,
                     agentEventCode,
                     agentEventDescription }
        DESCRIPTION
             "The MIB failed to build due to a missing parse file."
           --#TYPE      "Management Agent Event 3091"
           --#SUMMARY   "Host %s : SCellName-TimeDate %s : EventCode %d : Description %s"
           --#ARGUMENTS {0,1,2,3,}
            --#SEVERITY  INFORMATIONAL
            --#TIMEINDEX 136
        ::= 136003091

   mngmtAgentTrap-3092 TRAP-TYPE
        ENTERPRISE compaq
        VARIABLES  { hostName,
                     scellNameDateTime,
                     agentEventCode,
                     agentEventDescription }
        DESCRIPTION
             "MLD description file is older than local file but system is downrev"
           --#TYPE      "Management Agent Event 3092"
           --#SUMMARY   "Host %s : SCellName-TimeDate %s : EventCode %d : Description %s"
           --#ARGUMENTS {0,1,2,3,}
            --#SEVERITY  INFORMATIONAL
            --#TIMEINDEX 136
        ::= 136003092

   mngmtAgentTrap-3094 TRAP-TYPE
        ENTERPRISE compaq
        VARIABLES  { hostName,
                     scellNameDateTime,
                     agentEventCode,
                     agentEventDescription }
        DESCRIPTION
             "System is initialized: can't get activeQ events"
           --#TYPE      "Management Agent Event 3094"
           --#SUMMARY   "Host %s : SCellName-TimeDate %s : EventCode %d : Description %s"
           --#ARGUMENTS {0,1,2,3,}
            --#SEVERITY  INFORMATIONAL
            --#TIMEINDEX 136
        ::= 136003094

   mngmtAgentTrap-3095 TRAP-TYPE
        ENTERPRISE compaq
        VARIABLES  { hostName,
                     scellNameDateTime,
                     agentEventCode,
                     agentEventDescription }
        DESCRIPTION
             "Failed to write file - file could not be opened."
           --#TYPE      "Management Agent Event 3095"
           --#SUMMARY   "Host %s : SCellName-TimeDate %s : EventCode %d : Description %s"
           --#ARGUMENTS {0,1,2,3,}
            --#SEVERITY  INFORMATIONAL
            --#TIMEINDEX 136
        ::= 136003095

   mngmtAgentTrap-3096 TRAP-TYPE
        ENTERPRISE compaq
        VARIABLES  { hostName,
                     scellNameDateTime,
                     agentEventCode,
                     agentEventDescription }
        DESCRIPTION
             "On startup the event state file and the mldLastRead are out of sequence."
           --#TYPE      "Management Agent Event 3096"
           --#SUMMARY   "Host %s : SCellName-TimeDate %s : EventCode %d : Description %s"
           --#ARGUMENTS {0,1,2,3,}
            --#SEVERITY  INFORMATIONAL
            --#TIMEINDEX 136
        ::= 136003096

   mngmtAgentTrap-4000 TRAP-TYPE
        ENTERPRISE compaq
        VARIABLES  { hostName,
                     scellNameDateTime,
                     agentEventCode,
                     agentEventDescription }
        DESCRIPTION
             "MLD Manager Subsystem Error"
           --#TYPE      "Management Agent Event 4000"
           --#SUMMARY   "Host %s : SCellName-TimeDate %s : EventCode %d : Description %s"
           --#ARGUMENTS {0,1,2,3,}
            --#SEVERITY  INFORMATIONAL
            --#TIMEINDEX 136
        ::= 136004000

   mngmtAgentTrap-4001 TRAP-TYPE
        ENTERPRISE compaq
        VARIABLES  { hostName,
                     scellNameDateTime,
                     agentEventCode,
                     agentEventDescription }
        DESCRIPTION
             "MLD Manager Offline"
           --#TYPE      "Management Agent Event 4001"
           --#SUMMARY   "Host %s : SCellName-TimeDate %s : EventCode %d : Description %s"
           --#ARGUMENTS {0,1,2,3,}
            --#SEVERITY  INFORMATIONAL
            --#TIMEINDEX 136
        ::= 136004001

   mngmtAgentTrap-4004 TRAP-TYPE
        ENTERPRISE compaq
        VARIABLES  { hostName,
                     scellNameDateTime,
                     agentEventCode,
                     agentEventDescription }
        DESCRIPTION
             "MLD Manager Startup Complete"
           --#TYPE      "Management Agent Event 4004"
           --#SUMMARY   "Host %s : SCellName-TimeDate %s : EventCode %d : Description %s"
           --#ARGUMENTS {0,1,2,3,}
            --#SEVERITY  INFORMATIONAL
            --#TIMEINDEX 136
        ::= 136004004

   mngmtAgentTrap-4005 TRAP-TYPE
        ENTERPRISE compaq
        VARIABLES  { hostName,
                     scellNameDateTime,
                     agentEventCode,
                     agentEventDescription }
        DESCRIPTION
             "MLD Manager Abnormal Startup"
           --#TYPE      "Management Agent Event 4005"
           --#SUMMARY   "Host %s : SCellName-TimeDate %s : EventCode %d : Description %s"
           --#ARGUMENTS {0,1,2,3,}
            --#SEVERITY  INFORMATIONAL
            --#TIMEINDEX 136
        ::= 136004005

   mngmtAgentTrap-4007 TRAP-TYPE
        ENTERPRISE compaq
        VARIABLES  { hostName,
                     scellNameDateTime,
                     agentEventCode,
                     agentEventDescription }
        DESCRIPTION
             "MLD Manager Shutdown Complete"
           --#TYPE      "Management Agent Event 4007"
           --#SUMMARY   "Host %s : SCellName-TimeDate %s : EventCode %d : Description %s"
           --#ARGUMENTS {0,1,2,3,}
            --#SEVERITY  INFORMATIONAL
            --#TIMEINDEX 136
        ::= 136004007

   mngmtAgentTrap-4011 TRAP-TYPE
        ENTERPRISE compaq
        VARIABLES  { hostName,
                     scellNameDateTime,
                     agentEventCode,
                     agentEventDescription }
        DESCRIPTION
             "Invalid Host IP Address specified"
           --#TYPE      "Management Agent Event 4011"
           --#SUMMARY   "Host %s : SCellName-TimeDate %s : EventCode %d : Description %s"
           --#ARGUMENTS {0,1,2,3,}
            --#SEVERITY  INFORMATIONAL
            --#TIMEINDEX 136
        ::= 136004011

   mngmtAgentTrap-4012 TRAP-TYPE
        ENTERPRISE compaq
        VARIABLES  { hostName,
                     scellNameDateTime,
                     agentEventCode,
                     agentEventDescription }
        DESCRIPTION
             "Unable to open the NsaMldMgr.dat file for Write"
           --#TYPE      "Management Agent Event 4012"
           --#SUMMARY   "Host %s : SCellName-TimeDate %s : EventCode %d : Description %s"
           --#ARGUMENTS {0,1,2,3,}
            --#SEVERITY  INFORMATIONAL
            --#TIMEINDEX 136
        ::= 136004012

   mngmtAgentTrap-4013 TRAP-TYPE
        ENTERPRISE compaq
        VARIABLES  { hostName,
                     scellNameDateTime,
                     agentEventCode,
                     agentEventDescription }
        DESCRIPTION
             "Unable to open the NsaMldMgr.dat file for Read"
           --#TYPE      "Management Agent Event 4013"
           --#SUMMARY   "Host %s : SCellName-TimeDate %s : EventCode %d : Description %s"
           --#ARGUMENTS {0,1,2,3,}
            --#SEVERITY  INFORMATIONAL
            --#TIMEINDEX 136
        ::= 136004013

   mngmtAgentTrap-4014 TRAP-TYPE
        ENTERPRISE compaq
        VARIABLES  { hostName,
                     scellNameDateTime,
                     agentEventCode,
                     agentEventDescription }
        DESCRIPTION
             "Agent Uid does not exist"
           --#TYPE      "Management Agent Event 4014"
           --#SUMMARY   "Host %s : SCellName-TimeDate %s : EventCode %d : Description %s"
           --#ARGUMENTS {0,1,2,3,}
            --#SEVERITY  INFORMATIONAL
            --#TIMEINDEX 136
        ::= 136004014

   mngmtAgentTrap-4015 TRAP-TYPE
        ENTERPRISE compaq
        VARIABLES  { hostName,
                     scellNameDateTime,
                     agentEventCode,
                     agentEventDescription }
        DESCRIPTION
             "Unable to find object"
           --#TYPE      "Management Agent Event 4015"
           --#SUMMARY   "Host %s : SCellName-TimeDate %s : EventCode %d : Description %s"
           --#ARGUMENTS {0,1,2,3,}
            --#SEVERITY  INFORMATIONAL
            --#TIMEINDEX 136
        ::= 136004015

   mngmtAgentTrap-4016 TRAP-TYPE
        ENTERPRISE compaq
        VARIABLES  { hostName,
                     scellNameDateTime,
                     agentEventCode,
                     agentEventDescription }
        DESCRIPTION
             "Unable to store object"
           --#TYPE      "Management Agent Event 4016"
           --#SUMMARY   "Host %s : SCellName-TimeDate %s : EventCode %d : Description %s"
           --#ARGUMENTS {0,1,2,3,}
            --#SEVERITY  INFORMATIONAL
            --#TIMEINDEX 136
        ::= 136004016

   mngmtAgentTrap-4017 TRAP-TYPE
        ENTERPRISE compaq
        VARIABLES  { hostName,
                     scellNameDateTime,
                     agentEventCode,
                     agentEventDescription }
        DESCRIPTION
             "Unable to find storage system object"
           --#TYPE      "Management Agent Event 4017"
           --#SUMMARY   "Host %s : SCellName-TimeDate %s : EventCode %d : Description %s"
           --#ARGUMENTS {0,1,2,3,}
            --#SEVERITY  INFORMATIONAL
            --#TIMEINDEX 136
        ::= 136004017

   mngmtAgentTrap-4018 TRAP-TYPE
        ENTERPRISE compaq
        VARIABLES  { hostName,
                     scellNameDateTime,
                     agentEventCode,
                     agentEventDescription }
        DESCRIPTION
             "Unable to create MLD"
           --#TYPE      "Management Agent Event 4018"
           --#SUMMARY   "Host %s : SCellName-TimeDate %s : EventCode %d : Description %s"
           --#ARGUMENTS {0,1,2,3,}
            --#SEVERITY  INFORMATIONAL
            --#TIMEINDEX 136
        ::= 136004018

   mngmtAgentTrap-4020 TRAP-TYPE
        ENTERPRISE compaq
        VARIABLES  { hostName,
                     scellNameDateTime,
                     agentEventCode,
                     agentEventDescription }
        DESCRIPTION
             "lastSafeChoiceDelay Expired"
           --#TYPE      "Management Agent Event 4020"
           --#SUMMARY   "Host %s : SCellName-TimeDate %s : EventCode %d : Description %s"
           --#ARGUMENTS {0,1,2,3,}
            --#SEVERITY  INFORMATIONAL
            --#TIMEINDEX 136
        ::= 136004020

   mngmtAgentTrap-4021 TRAP-TYPE
        ENTERPRISE compaq
        VARIABLES  { hostName,
                     scellNameDateTime,
                     agentEventCode,
                     agentEventDescription }
        DESCRIPTION
             "crashDetectDelay Expired"
           --#TYPE      "Management Agent Event 4021"
           --#SUMMARY   "Host %s : SCellName-TimeDate %s : EventCode %d : Description %s"
           --#ARGUMENTS {0,1,2,3,}
            --#SEVERITY  INFORMATIONAL
            --#TIMEINDEX 136
        ::= 136004021

   mngmtAgentTrap-4023 TRAP-TYPE
        ENTERPRISE compaq
        VARIABLES  { hostName,
                     scellNameDateTime,
                     agentEventCode,
                     agentEventDescription }
        DESCRIPTION
             "Unable to read Copy1 of MLD"
           --#TYPE      "Management Agent Event 4023"
           --#SUMMARY   "Host %s : SCellName-TimeDate %s : EventCode %d : Description %s"
           --#ARGUMENTS {0,1,2,3,}
            --#SEVERITY  INFORMATIONAL
            --#TIMEINDEX 136
        ::= 136004023

   mngmtAgentTrap-4024 TRAP-TYPE
        ENTERPRISE compaq
        VARIABLES  { hostName,
                     scellNameDateTime,
                     agentEventCode,
                     agentEventDescription }
        DESCRIPTION
             "Copy 1 of MLD Invalid"
           --#TYPE      "Management Agent Event 4024"
           --#SUMMARY   "Host %s : SCellName-TimeDate %s : EventCode %d : Description %s"
           --#ARGUMENTS {0,1,2,3,}
            --#SEVERITY  INFORMATIONAL
            --#TIMEINDEX 136
        ::= 136004024

   mngmtAgentTrap-4025 TRAP-TYPE
        ENTERPRISE compaq
        VARIABLES  { hostName,
                     scellNameDateTime,
                     agentEventCode,
                     agentEventDescription }
        DESCRIPTION
             "Invalid Copy block of MLD"
           --#TYPE      "Management Agent Event 4025"
           --#SUMMARY   "Host %s : SCellName-TimeDate %s : EventCode %d : Description %s"
           --#ARGUMENTS {0,1,2,3,}
            --#SEVERITY  INFORMATIONAL
            --#TIMEINDEX 136
        ::= 136004025

   mngmtAgentTrap-4027 TRAP-TYPE
        ENTERPRISE compaq
        VARIABLES  { hostName,
                     scellNameDateTime,
                     agentEventCode,
                     agentEventDescription }
        DESCRIPTION
             "MLD database capacity not equal to true MLD capacity"
           --#TYPE      "Management Agent Event 4027"
           --#SUMMARY   "Host %s : SCellName-TimeDate %s : EventCode %d : Description %s"
           --#ARGUMENTS {0,1,2,3,}
            --#SEVERITY  INFORMATIONAL
            --#TIMEINDEX 136
        ::= 136004027

   mngmtAgentTrap-4028 TRAP-TYPE
        ENTERPRISE compaq
        VARIABLES  { hostName,
                     scellNameDateTime,
                     agentEventCode,
                     agentEventDescription }
        DESCRIPTION
             "Backup range out of bounds of copy 1 range"
           --#TYPE      "Management Agent Event 4028"
           --#SUMMARY   "Host %s : SCellName-TimeDate %s : EventCode %d : Description %s"
           --#ARGUMENTS {0,1,2,3,}
            --#SEVERITY  INFORMATIONAL
            --#TIMEINDEX 136
        ::= 136004028

   mngmtAgentTrap-4029 TRAP-TYPE
        ENTERPRISE compaq
        VARIABLES  { hostName,
                     scellNameDateTime,
                     agentEventCode,
                     agentEventDescription }
        DESCRIPTION
             "MLD Manager Lock Crash DetectDelay has expired, just taking lock!"
           --#TYPE      "Management Agent Event 4029"
           --#SUMMARY   "Host %s : SCellName-TimeDate %s : EventCode %d : Description %s"
           --#ARGUMENTS {0,1,2,3,}
            --#SEVERITY  INFORMATIONAL
            --#TIMEINDEX 136
        ::= 136004029

   mngmtAgentTrap-4030 TRAP-TYPE
        ENTERPRISE compaq
        VARIABLES  { hostName,
                     scellNameDateTime,
                     agentEventCode,
                     agentEventDescription }
        DESCRIPTION
             "MLD Copy 1 Restored"
           --#TYPE      "Management Agent Event 4030"
           --#SUMMARY   "Host %s : SCellName-TimeDate %s : EventCode %d : Description %s"
           --#ARGUMENTS {0,1,2,3,}
            --#SEVERITY  INFORMATIONAL
            --#TIMEINDEX 136
        ::= 136004030

   mngmtAgentTrap-4031 TRAP-TYPE
        ENTERPRISE compaq
        VARIABLES  { hostName,
                     scellNameDateTime,
                     agentEventCode,
                     agentEventDescription }
        DESCRIPTION
             "MLD Copy 2 Restored"
           --#TYPE      "Management Agent Event 4031"
           --#SUMMARY   "Host %s : SCellName-TimeDate %s : EventCode %d : Description %s"
           --#ARGUMENTS {0,1,2,3,}
            --#SEVERITY  INFORMATIONAL
            --#TIMEINDEX 136
        ::= 136004031

   mngmtAgentTrap-4032 TRAP-TYPE
        ENTERPRISE compaq
        VARIABLES  { hostName,
                     scellNameDateTime,
                     agentEventCode,
                     agentEventDescription }
        DESCRIPTION
             "Unable to find UidAssoc Object"
           --#TYPE      "Management Agent Event 4032"
           --#SUMMARY   "Host %s : SCellName-TimeDate %s : EventCode %d : Description %s"
           --#ARGUMENTS {0,1,2,3,}
            --#SEVERITY  INFORMATIONAL
            --#TIMEINDEX 136
        ::= 136004032

   mngmtAgentTrap-4033 TRAP-TYPE
        ENTERPRISE compaq
        VARIABLES  { hostName,
                     scellNameDateTime,
                     agentEventCode,
                     agentEventDescription }
        DESCRIPTION
             "Unable to store UID Association Object"
           --#TYPE      "Management Agent Event 4033"
           --#SUMMARY   "Host %s : SCellName-TimeDate %s : EventCode %d : Description %s"
           --#ARGUMENTS {0,1,2,3,}
            --#SEVERITY  INFORMATIONAL
            --#TIMEINDEX 136
        ::= 136004033

   mngmtAgentTrap-4034 TRAP-TYPE
        ENTERPRISE compaq
        VARIABLES  { hostName,
                     scellNameDateTime,
                     agentEventCode,
                     agentEventDescription }
        DESCRIPTION
             "Unable to find UidAssoc Object"
           --#TYPE      "Management Agent Event 4034"
           --#SUMMARY   "Host %s : SCellName-TimeDate %s : EventCode %d : Description %s"
           --#ARGUMENTS {0,1,2,3,}
            --#SEVERITY  INFORMATIONAL
            --#TIMEINDEX 136
        ::= 136004034

   mngmtAgentTrap-4035 TRAP-TYPE
        ENTERPRISE compaq
        VARIABLES  { hostName,
                     scellNameDateTime,
                     agentEventCode,
                     agentEventDescription }
        DESCRIPTION
             "Unable to read last Fusion event read"
           --#TYPE      "Management Agent Event 4035"
           --#SUMMARY   "Host %s : SCellName-TimeDate %s : EventCode %d : Description %s"
           --#ARGUMENTS {0,1,2,3,}
            --#SEVERITY  INFORMATIONAL
            --#TIMEINDEX 136
        ::= 136004035

   mngmtAgentTrap-4036 TRAP-TYPE
        ENTERPRISE compaq
        VARIABLES  { hostName,
                     scellNameDateTime,
                     agentEventCode,
                     agentEventDescription }
        DESCRIPTION
             "MLD Notification Queue Empty"
           --#TYPE      "Management Agent Event 4036"
           --#SUMMARY   "Host %s : SCellName-TimeDate %s : EventCode %d : Description %s"
           --#ARGUMENTS {0,1,2,3,}
            --#SEVERITY  INFORMATIONAL
            --#TIMEINDEX 136
        ::= 136004036

   mngmtAgentTrap-4037 TRAP-TYPE
        ENTERPRISE compaq
        VARIABLES  { hostName,
                     scellNameDateTime,
                     agentEventCode,
                     agentEventDescription }
        DESCRIPTION
             "Unable to find Notification Object"
           --#TYPE      "Management Agent Event 4037"
           --#SUMMARY   "Host %s : SCellName-TimeDate %s : EventCode %d : Description %s"
           --#ARGUMENTS {0,1,2,3,}
            --#SEVERITY  INFORMATIONAL
            --#TIMEINDEX 136
        ::= 136004037

   mngmtAgentTrap-4040 TRAP-TYPE
        ENTERPRISE compaq
        VARIABLES  { hostName,
                     scellNameDateTime,
                     agentEventCode,
                     agentEventDescription }
        DESCRIPTION
             "Unable to read Event Log Pointer"
           --#TYPE      "Management Agent Event 4040"
           --#SUMMARY   "Host %s : SCellName-TimeDate %s : EventCode %d : Description %s"
           --#ARGUMENTS {0,1,2,3,}
            --#SEVERITY  INFORMATIONAL
            --#TIMEINDEX 136
        ::= 136004040

   mngmtAgentTrap-4041 TRAP-TYPE
        ENTERPRISE compaq
        VARIABLES  { hostName,
                     scellNameDateTime,
                     agentEventCode,
                     agentEventDescription }
        DESCRIPTION
             "Unable to read Event Log"
           --#TYPE      "Management Agent Event 4041"
           --#SUMMARY   "Host %s : SCellName-TimeDate %s : EventCode %d : Description %s"
           --#ARGUMENTS {0,1,2,3,}
            --#SEVERITY  INFORMATIONAL
            --#TIMEINDEX 136
        ::= 136004041

   mngmtAgentTrap-4042 TRAP-TYPE
        ENTERPRISE compaq
        VARIABLES  { hostName,
                     scellNameDateTime,
                     agentEventCode,
                     agentEventDescription }
        DESCRIPTION
             "Unable to store Event Log"
           --#TYPE      "Management Agent Event 4042"
           --#SUMMARY   "Host %s : SCellName-TimeDate %s : EventCode %d : Description %s"
           --#ARGUMENTS {0,1,2,3,}
            --#SEVERITY  INFORMATIONAL
            --#TIMEINDEX 136
        ::= 136004042

   mngmtAgentTrap-4043 TRAP-TYPE
        ENTERPRISE compaq
        VARIABLES  { hostName,
                     scellNameDateTime,
                     agentEventCode,
                     agentEventDescription }
        DESCRIPTION
             "Unable to read Event Log"
           --#TYPE      "Management Agent Event 4043"
           --#SUMMARY   "Host %s : SCellName-TimeDate %s : EventCode %d : Description %s"
           --#ARGUMENTS {0,1,2,3,}
            --#SEVERITY  INFORMATIONAL
            --#TIMEINDEX 136
        ::= 136004043

   mngmtAgentTrap-4047 TRAP-TYPE
        ENTERPRISE compaq
        VARIABLES  { hostName,
                     scellNameDateTime,
                     agentEventCode,
                     agentEventDescription }
        DESCRIPTION
             "Previously Read Object Properties do not Match"
           --#TYPE      "Management Agent Event 4047"
           --#SUMMARY   "Host %s : SCellName-TimeDate %s : EventCode %d : Description %s"
           --#ARGUMENTS {0,1,2,3,}
            --#SEVERITY  INFORMATIONAL
            --#TIMEINDEX 136
        ::= 136004047

   mngmtAgentTrap-4048 TRAP-TYPE
        ENTERPRISE compaq
        VARIABLES  { hostName,
                     scellNameDateTime,
                     agentEventCode,
                     agentEventDescription }
        DESCRIPTION
             "Previously Read Object Properties do not Match"
           --#TYPE      "Management Agent Event 4048"
           --#SUMMARY   "Host %s : SCellName-TimeDate %s : EventCode %d : Description %s"
           --#ARGUMENTS {0,1,2,3,}
            --#SEVERITY  INFORMATIONAL
            --#TIMEINDEX 136
        ::= 136004048

   mngmtAgentTrap-4049 TRAP-TYPE
        ENTERPRISE compaq
        VARIABLES  { hostName,
                     scellNameDateTime,
                     agentEventCode,
                     agentEventDescription }
        DESCRIPTION
             "Unable to read  Notification Host List"
           --#TYPE      "Management Agent Event 4049"
           --#SUMMARY   "Host %s : SCellName-TimeDate %s : EventCode %d : Description %s"
           --#ARGUMENTS {0,1,2,3,}
            --#SEVERITY  INFORMATIONAL
            --#TIMEINDEX 136
        ::= 136004049

   mngmtAgentTrap-4050 TRAP-TYPE
        ENTERPRISE compaq
        VARIABLES  { hostName,
                     scellNameDateTime,
                     agentEventCode,
                     agentEventDescription }
        DESCRIPTION
             "Unable to store Notification Host List"
           --#TYPE      "Management Agent Event 4050"
           --#SUMMARY   "Host %s : SCellName-TimeDate %s : EventCode %d : Description %s"
           --#ARGUMENTS {0,1,2,3,}
            --#SEVERITY  INFORMATIONAL
            --#TIMEINDEX 136
        ::= 136004050

   mngmtAgentTrap-4051 TRAP-TYPE
        ENTERPRISE compaq
        VARIABLES  { hostName,
                     scellNameDateTime,
                     agentEventCode,
                     agentEventDescription }
        DESCRIPTION
             "Unable to store Notification Host List and free Lock"
           --#TYPE      "Management Agent Event 4051"
           --#SUMMARY   "Host %s : SCellName-TimeDate %s : EventCode %d : Description %s"
           --#ARGUMENTS {0,1,2,3,}
            --#SEVERITY  INFORMATIONAL
            --#TIMEINDEX 136
        ::= 136004051

   mngmtAgentTrap-4052 TRAP-TYPE
        ENTERPRISE compaq
        VARIABLES  { hostName,
                     scellNameDateTime,
                     agentEventCode,
                     agentEventDescription }
        DESCRIPTION
             "Unable to read  Event Configuration List"
           --#TYPE      "Management Agent Event 4052"
           --#SUMMARY   "Host %s : SCellName-TimeDate %s : EventCode %d : Description %s"
           --#ARGUMENTS {0,1,2,3,}
            --#SEVERITY  INFORMATIONAL
            --#TIMEINDEX 136
        ::= 136004052

   mngmtAgentTrap-4053 TRAP-TYPE
        ENTERPRISE compaq
        VARIABLES  { hostName,
                     scellNameDateTime,
                     agentEventCode,
                     agentEventDescription }
        DESCRIPTION
             "Unable to store Event Configuration List"
           --#TYPE      "Management Agent Event 4053"
           --#SUMMARY   "Host %s : SCellName-TimeDate %s : EventCode %d : Description %s"
           --#ARGUMENTS {0,1,2,3,}
            --#SEVERITY  INFORMATIONAL
            --#TIMEINDEX 136
        ::= 136004053

   mngmtAgentTrap-4054 TRAP-TYPE
        ENTERPRISE compaq
        VARIABLES  { hostName,
                     scellNameDateTime,
                     agentEventCode,
                     agentEventDescription }
        DESCRIPTION
             "Unable to store Event Configuration List and free Lock"
           --#TYPE      "Management Agent Event 4054"
           --#SUMMARY   "Host %s : SCellName-TimeDate %s : EventCode %d : Description %s"
           --#ARGUMENTS {0,1,2,3,}
            --#SEVERITY  INFORMATIONAL
            --#TIMEINDEX 136
        ::= 136004054

   mngmtAgentTrap-4058 TRAP-TYPE
        ENTERPRISE compaq
        VARIABLES  { hostName,
                     scellNameDateTime,
                     agentEventCode,
                     agentEventDescription }
        DESCRIPTION
             "MLD Manager Mutex Timeout error"
           --#TYPE      "Management Agent Event 4058"
           --#SUMMARY   "Host %s : SCellName-TimeDate %s : EventCode %d : Description %s"
           --#ARGUMENTS {0,1,2,3,}
            --#SEVERITY  INFORMATIONAL
            --#TIMEINDEX 136
        ::= 136004058

   mngmtAgentTrap-4059 TRAP-TYPE
        ENTERPRISE compaq
        VARIABLES  { hostName,
                     scellNameDateTime,
                     agentEventCode,
                     agentEventDescription }
        DESCRIPTION
             "MLD Manager list is empty"
           --#TYPE      "Management Agent Event 4059"
           --#SUMMARY   "Host %s : SCellName-TimeDate %s : EventCode %d : Description %s"
           --#ARGUMENTS {0,1,2,3,}
            --#SEVERITY  INFORMATIONAL
            --#TIMEINDEX 136
        ::= 136004059

   mngmtAgentTrap-4075 TRAP-TYPE
        ENTERPRISE compaq
        VARIABLES  { hostName,
                     scellNameDateTime,
                     agentEventCode,
                     agentEventDescription }
        DESCRIPTION
             "Error writing MLD dump to disk"
           --#TYPE      "Management Agent Event 4075"
           --#SUMMARY   "Host %s : SCellName-TimeDate %s : EventCode %d : Description %s"
           --#ARGUMENTS {0,1,2,3,}
            --#SEVERITY  INFORMATIONAL
            --#TIMEINDEX 136
        ::= 136004075

   mngmtAgentTrap-4077 TRAP-TYPE
        ENTERPRISE compaq
        VARIABLES  { hostName,
                     scellNameDateTime,
                     agentEventCode,
                     agentEventDescription }
        DESCRIPTION
             "MLD Mgr detected a type mismatch on read, MLD may be corrupt"
           --#TYPE      "Management Agent Event 4077"
           --#SUMMARY   "Host %s : SCellName-TimeDate %s : EventCode %d : Description %s"
           --#ARGUMENTS {0,1,2,3,}
            --#SEVERITY  CRITICAL
            --#TIMEINDEX 136
        ::= 136004077

   mngmtAgentTrap-4078 TRAP-TYPE
        ENTERPRISE compaq
        VARIABLES  { hostName,
                     scellNameDateTime,
                     agentEventCode,
                     agentEventDescription }
        DESCRIPTION
             "HP P6000 Command View has detected an inconsistency in its management database for this system. Host I/O is not affected. Contact HP Service for assistance."
           --#TYPE      "Management Agent Event 4078"
           --#SUMMARY   "Host %s : SCellName-TimeDate %s : EventCode %d : Description %s"
           --#ARGUMENTS {0,1,2,3,}
            --#SEVERITY  CRITICAL
            --#TIMEINDEX 136
        ::= 136004078

   mngmtAgentTrap-4081 TRAP-TYPE
        ENTERPRISE compaq
        VARIABLES  { hostName,
                     scellNameDateTime,
                     agentEventCode,
                     agentEventDescription }
        DESCRIPTION
             "MLD Mgr failed to get MLD start LDA for object"
           --#TYPE      "Management Agent Event 4081"
           --#SUMMARY   "Host %s : SCellName-TimeDate %s : EventCode %d : Description %s"
           --#ARGUMENTS {0,1,2,3,}
            --#SEVERITY  MINOR
            --#TIMEINDEX 136
        ::= 136004081

   mngmtAgentTrap-5001 TRAP-TYPE
        ENTERPRISE compaq
        VARIABLES  { hostName,
                     scellNameDateTime,
                     agentEventCode,
                     agentEventDescription }
        DESCRIPTION
             "Monitor Startup Complete"
           --#TYPE      "Management Agent Event 5001"
           --#SUMMARY   "Host %s : SCellName-TimeDate %s : EventCode %d : Description %s"
           --#ARGUMENTS {0,1,2,3,}
            --#SEVERITY  INFORMATIONAL
            --#TIMEINDEX 136
        ::= 136005001

   mngmtAgentTrap-5002 TRAP-TYPE
        ENTERPRISE compaq
        VARIABLES  { hostName,
                     scellNameDateTime,
                     agentEventCode,
                     agentEventDescription }
        DESCRIPTION
             "Monitor Startup Failed"
           --#TYPE      "Management Agent Event 5002"
           --#SUMMARY   "Host %s : SCellName-TimeDate %s : EventCode %d : Description %s"
           --#ARGUMENTS {0,1,2,3,}
            --#SEVERITY  INFORMATIONAL
            --#TIMEINDEX 136
        ::= 136005002

   mngmtAgentTrap-5003 TRAP-TYPE
        ENTERPRISE compaq
        VARIABLES  { hostName,
                     scellNameDateTime,
                     agentEventCode,
                     agentEventDescription }
        DESCRIPTION
             "Monitor ShutDown Complete"
           --#TYPE      "Management Agent Event 5003"
           --#SUMMARY   "Host %s : SCellName-TimeDate %s : EventCode %d : Description %s"
           --#ARGUMENTS {0,1,2,3,}
            --#SEVERITY  INFORMATIONAL
            --#TIMEINDEX 136
        ::= 136005003

   mngmtAgentTrap-5004 TRAP-TYPE
        ENTERPRISE compaq
        VARIABLES  { hostName,
                     scellNameDateTime,
                     agentEventCode,
                     agentEventDescription }
        DESCRIPTION
             "Monitor Memory Allocation Failure"
           --#TYPE      "Management Agent Event 5004"
           --#SUMMARY   "Host %s : SCellName-TimeDate %s : EventCode %d : Description %s"
           --#ARGUMENTS {0,1,2,3,}
            --#SEVERITY  CRITICAL
            --#TIMEINDEX 136
        ::= 136005004

   mngmtAgentTrap-5005 TRAP-TYPE
        ENTERPRISE compaq
        VARIABLES  { hostName,
                     scellNameDateTime,
                     agentEventCode,
                     agentEventDescription }
        DESCRIPTION
             "Monitor Mark Agent as Inactive"
           --#TYPE      "Management Agent Event 5005"
           --#SUMMARY   "Host %s : SCellName-TimeDate %s : EventCode %d : Description %s"
           --#ARGUMENTS {0,1,2,3,}
            --#SEVERITY  INFORMATIONAL
            --#TIMEINDEX 136
        ::= 136005005

   mngmtAgentTrap-5006 TRAP-TYPE
        ENTERPRISE compaq
        VARIABLES  { hostName,
                     scellNameDateTime,
                     agentEventCode,
                     agentEventDescription }
        DESCRIPTION
             "Monitor create thread error"
           --#TYPE      "Management Agent Event 5006"
           --#SUMMARY   "Host %s : SCellName-TimeDate %s : EventCode %d : Description %s"
           --#ARGUMENTS {0,1,2,3,}
            --#SEVERITY  INFORMATIONAL
            --#TIMEINDEX 136
        ::= 136005006

   mngmtAgentTrap-5007 TRAP-TYPE
        ENTERPRISE compaq
        VARIABLES  { hostName,
                     scellNameDateTime,
                     agentEventCode,
                     agentEventDescription }
        DESCRIPTION
             "Monitor create timer error"
           --#TYPE      "Management Agent Event 5007"
           --#SUMMARY   "Host %s : SCellName-TimeDate %s : EventCode %d : Description %s"
           --#ARGUMENTS {0,1,2,3,}
            --#SEVERITY  INFORMATIONAL
            --#TIMEINDEX 136
        ::= 136005007

   mngmtAgentTrap-5008 TRAP-TYPE
        ENTERPRISE compaq
        VARIABLES  { hostName,
                     scellNameDateTime,
                     agentEventCode,
                     agentEventDescription }
        DESCRIPTION
             "Monitor agent registration - Complete"
           --#TYPE      "Management Agent Event 5008"
           --#SUMMARY   "Host %s : SCellName-TimeDate %s : EventCode %d : Description %s"
           --#ARGUMENTS {0,1,2,3,}
            --#SEVERITY  INFORMATIONAL
            --#TIMEINDEX 136
        ::= 136005008

   mngmtAgentTrap-5010 TRAP-TYPE
        ENTERPRISE compaq
        VARIABLES  { hostName,
                     scellNameDateTime,
                     agentEventCode,
                     agentEventDescription }
        DESCRIPTION
             "Management of a storage system has been suspended due to an inability to communicate with the array controllers. Management of the storage system will recover automatically when the system is able to respond."
           --#TYPE      "Management Agent Event 5010"
           --#SUMMARY   "Host %s : SCellName-TimeDate %s : EventCode %d : Description %s"
           --#ARGUMENTS {0,1,2,3,}
            --#SEVERITY  MINOR
            --#TIMEINDEX 136
        ::= 136005010

   mngmtAgentTrap-5011 TRAP-TYPE
        ENTERPRISE compaq
        VARIABLES  { hostName,
                     scellNameDateTime,
                     agentEventCode,
                     agentEventDescription }
        DESCRIPTION
             "Unknown storage system rediscovery complete"
           --#TYPE      "Management Agent Event 5011"
           --#SUMMARY   "Host %s : SCellName-TimeDate %s : EventCode %d : Description %s"
           --#ARGUMENTS {0,1,2,3,}
            --#SEVERITY  INFORMATIONAL
            --#TIMEINDEX 136
        ::= 136005011

   mngmtAgentTrap-5012 TRAP-TYPE
        ENTERPRISE compaq
        VARIABLES  { hostName,
                     scellNameDateTime,
                     agentEventCode,
                     agentEventDescription }
        DESCRIPTION
             "Start monitoring thread for storage system - Complete"
           --#TYPE      "Management Agent Event 5012"
           --#SUMMARY   "Host %s : SCellName-TimeDate %s : EventCode %d : Description %s"
           --#ARGUMENTS {0,1,2,3,}
            --#SEVERITY  MINOR
            --#TIMEINDEX 136
        ::= 136005012

   mngmtAgentTrap-5013 TRAP-TYPE
        ENTERPRISE compaq
        VARIABLES  { hostName,
                     scellNameDateTime,
                     agentEventCode,
                     agentEventDescription }
        DESCRIPTION
             "Start monitoring thread for storage system - Fail"
           --#TYPE      "Management Agent Event 5013"
           --#SUMMARY   "Host %s : SCellName-TimeDate %s : EventCode %d : Description %s"
           --#ARGUMENTS {0,1,2,3,}
            --#SEVERITY  INFORMATIONAL
            --#TIMEINDEX 136
        ::= 136005013

   mngmtAgentTrap-5014 TRAP-TYPE
        ENTERPRISE compaq
        VARIABLES  { hostName,
                     scellNameDateTime,
                     agentEventCode,
                     agentEventDescription }
        DESCRIPTION
             "Monitoring thread for storage system terminated"
           --#TYPE      "Management Agent Event 5014"
           --#SUMMARY   "Host %s : SCellName-TimeDate %s : EventCode %d : Description %s"
           --#ARGUMENTS {0,1,2,3,}
            --#SEVERITY  MINOR
            --#TIMEINDEX 136
        ::= 136005014

   mngmtAgentTrap-5015 TRAP-TYPE
        ENTERPRISE compaq
        VARIABLES  { hostName,
                     scellNameDateTime,
                     agentEventCode,
                     agentEventDescription }
        DESCRIPTION
             "Rediscover unknown storage system - Error"
           --#TYPE      "Management Agent Event 5015"
           --#SUMMARY   "Host %s : SCellName-TimeDate %s : EventCode %d : Description %s"
           --#ARGUMENTS {0,1,2,3,}
            --#SEVERITY  INFORMATIONAL
            --#TIMEINDEX 136
        ::= 136005015

   mngmtAgentTrap-5016 TRAP-TYPE
        ENTERPRISE compaq
        VARIABLES  { hostName,
                     scellNameDateTime,
                     agentEventCode,
                     agentEventDescription }
        DESCRIPTION
             "Controller time synchronized to management workstation time."
           --#TYPE      "Management Agent Event 5016"
           --#SUMMARY   "Host %s : SCellName-TimeDate %s : EventCode %d : Description %s"
           --#ARGUMENTS {0,1,2,3,}
            --#SEVERITY  INFORMATIONAL
            --#TIMEINDEX 136
        ::= 136005016

   mngmtAgentTrap-5017 TRAP-TYPE
        ENTERPRISE compaq
        VARIABLES  { hostName,
                     scellNameDateTime,
                     agentEventCode,
                     agentEventDescription }
        DESCRIPTION
             "Management workstation and controller time checked for synchronization."
           --#TYPE      "Management Agent Event 5017"
           --#SUMMARY   "Host %s : SCellName-TimeDate %s : EventCode %d : Description %s"
           --#ARGUMENTS {0,1,2,3,}
            --#SEVERITY  INFORMATIONAL
            --#TIMEINDEX 136
        ::= 136005017

   mngmtAgentTrap-5018 TRAP-TYPE
        ENTERPRISE compaq
        VARIABLES  { hostName,
                     scellNameDateTime,
                     agentEventCode,
                     agentEventDescription }
        DESCRIPTION
             "Controller and management workstation time are the same. No need to synchronize."
           --#TYPE      "Management Agent Event 5018"
           --#SUMMARY   "Host %s : SCellName-TimeDate %s : EventCode %d : Description %s"
           --#ARGUMENTS {0,1,2,3,}
            --#SEVERITY  INFORMATIONAL
            --#TIMEINDEX 136
        ::= 136005018

   mngmtAgentTrap-5019 TRAP-TYPE
        ENTERPRISE compaq
        VARIABLES  { hostName,
                     scellNameDateTime,
                     agentEventCode,
                     agentEventDescription }
        DESCRIPTION
             "Exception caught in monitoring process."
           --#TYPE      "Management Agent Event 5019"
           --#SUMMARY   "Host %s : SCellName-TimeDate %s : EventCode %d : Description %s"
           --#ARGUMENTS {0,1,2,3,}
            --#SEVERITY  INFORMATIONAL
            --#TIMEINDEX 136
        ::= 136005019

   mngmtAgentTrap-6001 TRAP-TYPE
        ENTERPRISE compaq
        VARIABLES  { hostName,
                     scellNameDateTime,
                     agentEventCode,
                     agentEventDescription }
        DESCRIPTION
             "Ready"
           --#TYPE      "Management Agent Event 6001"
           --#SUMMARY   "Host %s : SCellName-TimeDate %s : EventCode %d : Description %s"
           --#ARGUMENTS {0,1,2,3,}
            --#SEVERITY  INFORMATIONAL
            --#TIMEINDEX 136
        ::= 136006001

   mngmtAgentTrap-6002 TRAP-TYPE
        ENTERPRISE compaq
        VARIABLES  { hostName,
                     scellNameDateTime,
                     agentEventCode,
                     agentEventDescription }
        DESCRIPTION
             "Index Out of Range"
           --#TYPE      "Management Agent Event 6002"
           --#SUMMARY   "Host %s : SCellName-TimeDate %s : EventCode %d : Description %s"
           --#ARGUMENTS {0,1,2,3,}
            --#SEVERITY  INFORMATIONAL
            --#TIMEINDEX 136
        ::= 136006002

   mngmtAgentTrap-6003 TRAP-TYPE
        ENTERPRISE compaq
        VARIABLES  { hostName,
                     scellNameDateTime,
                     agentEventCode,
                     agentEventDescription }
        DESCRIPTION
             "Cannot access storage system. Communications error."
           --#TYPE      "Management Agent Event 6003"
           --#SUMMARY   "Host %s : SCellName-TimeDate %s : EventCode %d : Description %s"
           --#ARGUMENTS {0,1,2,3,}
            --#SEVERITY  CRITICAL
            --#TIMEINDEX 136
        ::= 136006003

   mngmtAgentTrap-6004 TRAP-TYPE
        ENTERPRISE compaq
        VARIABLES  { hostName,
                     scellNameDateTime,
                     agentEventCode,
                     agentEventDescription }
        DESCRIPTION
             "No controllers found"
           --#TYPE      "Management Agent Event 6004"
           --#SUMMARY   "Host %s : SCellName-TimeDate %s : EventCode %d : Description %s"
           --#ARGUMENTS {0,1,2,3,}
            --#SEVERITY  INFORMATIONAL
            --#TIMEINDEX 136
        ::= 136006004

   mngmtAgentTrap-6005 TRAP-TYPE
        ENTERPRISE compaq
        VARIABLES  { hostName,
                     scellNameDateTime,
                     agentEventCode,
                     agentEventDescription }
        DESCRIPTION
             "Invalid Index"
           --#TYPE      "Management Agent Event 6005"
           --#SUMMARY   "Host %s : SCellName-TimeDate %s : EventCode %d : Description %s"
           --#ARGUMENTS {0,1,2,3,}
            --#SEVERITY  INFORMATIONAL
            --#TIMEINDEX 136
        ::= 136006005

   mngmtAgentTrap-6006 TRAP-TYPE
        ENTERPRISE compaq
        VARIABLES  { hostName,
                     scellNameDateTime,
                     agentEventCode,
                     agentEventDescription }
        DESCRIPTION
             "Memory allocation failure"
           --#TYPE      "Management Agent Event 6006"
           --#SUMMARY   "Host %s : SCellName-TimeDate %s : EventCode %d : Description %s"
           --#ARGUMENTS {0,1,2,3,}
            --#SEVERITY  CRITICAL
            --#TIMEINDEX 136
        ::= 136006006

   mngmtAgentTrap-6007 TRAP-TYPE
        ENTERPRISE compaq
        VARIABLES  { hostName,
                     scellNameDateTime,
                     agentEventCode,
                     agentEventDescription }
        DESCRIPTION
             "No physical stores found"
           --#TYPE      "Management Agent Event 6007"
           --#SUMMARY   "Host %s : SCellName-TimeDate %s : EventCode %d : Description %s"
           --#ARGUMENTS {0,1,2,3,}
            --#SEVERITY  INFORMATIONAL
            --#TIMEINDEX 136
        ::= 136006007

   mngmtAgentTrap-6008 TRAP-TYPE
        ENTERPRISE compaq
        VARIABLES  { hostName,
                     scellNameDateTime,
                     agentEventCode,
                     agentEventDescription }
        DESCRIPTION
             "No storage system found"
           --#TYPE      "Management Agent Event 6008"
           --#SUMMARY   "Host %s : SCellName-TimeDate %s : EventCode %d : Description %s"
           --#ARGUMENTS {0,1,2,3,}
            --#SEVERITY  INFORMATIONAL
            --#TIMEINDEX 136
        ::= 136006008

   mngmtAgentTrap-6009 TRAP-TYPE
        ENTERPRISE compaq
        VARIABLES  { hostName,
                     scellNameDateTime,
                     agentEventCode,
                     agentEventDescription }
        DESCRIPTION
             "No disk group found"
           --#TYPE      "Management Agent Event 6009"
           --#SUMMARY   "Host %s : SCellName-TimeDate %s : EventCode %d : Description %s"
           --#ARGUMENTS {0,1,2,3,}
            --#SEVERITY  INFORMATIONAL
            --#TIMEINDEX 136
        ::= 136006009

   mngmtAgentTrap-6010 TRAP-TYPE
        ENTERPRISE compaq
        VARIABLES  { hostName,
                     scellNameDateTime,
                     agentEventCode,
                     agentEventDescription }
        DESCRIPTION
             "Too many disk groups"
           --#TYPE      "Management Agent Event 6010"
           --#SUMMARY   "Host %s : SCellName-TimeDate %s : EventCode %d : Description %s"
           --#ARGUMENTS {0,1,2,3,}
            --#SEVERITY  INFORMATIONAL
            --#TIMEINDEX 136
        ::= 136006010

   mngmtAgentTrap-6011 TRAP-TYPE
        ENTERPRISE compaq
        VARIABLES  { hostName,
                     scellNameDateTime,
                     agentEventCode,
                     agentEventDescription }
        DESCRIPTION
             "No volumes found"
           --#TYPE      "Management Agent Event 6011"
           --#SUMMARY   "Host %s : SCellName-TimeDate %s : EventCode %d : Description %s"
           --#ARGUMENTS {0,1,2,3,}
            --#SEVERITY  INFORMATIONAL
            --#TIMEINDEX 136
        ::= 136006011

   mngmtAgentTrap-6012 TRAP-TYPE
        ENTERPRISE compaq
        VARIABLES  { hostName,
                     scellNameDateTime,
                     agentEventCode,
                     agentEventDescription }
        DESCRIPTION
             "No Logical Disks Found"
           --#TYPE      "Management Agent Event 6012"
           --#SUMMARY   "Host %s : SCellName-TimeDate %s : EventCode %d : Description %s"
           --#ARGUMENTS {0,1,2,3,}
            --#SEVERITY  INFORMATIONAL
            --#TIMEINDEX 136
        ::= 136006012

   mngmtAgentTrap-6013 TRAP-TYPE
        ENTERPRISE compaq
        VARIABLES  { hostName,
                     scellNameDateTime,
                     agentEventCode,
                     agentEventDescription }
        DESCRIPTION
             "Context ID changed during operation"
           --#TYPE      "Management Agent Event 6013"
           --#SUMMARY   "Host %s : SCellName-TimeDate %s : EventCode %d : Description %s"
           --#ARGUMENTS {0,1,2,3,}
            --#SEVERITY  INFORMATIONAL
            --#TIMEINDEX 136
        ::= 136006013

   mngmtAgentTrap-6014 TRAP-TYPE
        ENTERPRISE compaq
        VARIABLES  { hostName,
                     scellNameDateTime,
                     agentEventCode,
                     agentEventDescription }
        DESCRIPTION
             "No Name"
           --#TYPE      "Management Agent Event 6014"
           --#SUMMARY   "Host %s : SCellName-TimeDate %s : EventCode %d : Description %s"
           --#ARGUMENTS {0,1,2,3,}
            --#SEVERITY  INFORMATIONAL
            --#TIMEINDEX 136
        ::= 136006014

   mngmtAgentTrap-6015 TRAP-TYPE
        ENTERPRISE compaq
        VARIABLES  { hostName,
                     scellNameDateTime,
                     agentEventCode,
                     agentEventDescription }
        DESCRIPTION
             "Name Size Exceeded"
           --#TYPE      "Management Agent Event 6015"
           --#SUMMARY   "Host %s : SCellName-TimeDate %s : EventCode %d : Description %s"
           --#ARGUMENTS {0,1,2,3,}
            --#SEVERITY  INFORMATIONAL
            --#TIMEINDEX 136
        ::= 136006015

   mngmtAgentTrap-6016 TRAP-TYPE
        ENTERPRISE compaq
        VARIABLES  { hostName,
                     scellNameDateTime,
                     agentEventCode,
                     agentEventDescription }
        DESCRIPTION
             "Shutdown Complete"
           --#TYPE      "Management Agent Event 6016"
           --#SUMMARY   "Host %s : SCellName-TimeDate %s : EventCode %d : Description %s"
           --#ARGUMENTS {0,1,2,3,}
            --#SEVERITY  INFORMATIONAL
            --#TIMEINDEX 136
        ::= 136006016

   mngmtAgentTrap-6017 TRAP-TYPE
        ENTERPRISE compaq
        VARIABLES  { hostName,
                     scellNameDateTime,
                     agentEventCode,
                     agentEventDescription }
        DESCRIPTION
             "Mutex Creation Failure"
           --#TYPE      "Management Agent Event 6017"
           --#SUMMARY   "Host %s : SCellName-TimeDate %s : EventCode %d : Description %s"
           --#ARGUMENTS {0,1,2,3,}
            --#SEVERITY  INFORMATIONAL
            --#TIMEINDEX 136
        ::= 136006017

   mngmtAgentTrap-6018 TRAP-TYPE
        ENTERPRISE compaq
        VARIABLES  { hostName,
                     scellNameDateTime,
                     agentEventCode,
                     agentEventDescription }
        DESCRIPTION
             "The request has timed out. The system is busy processing another command."
           --#TYPE      "Management Agent Event 6018"
           --#SUMMARY   "Host %s : SCellName-TimeDate %s : EventCode %d : Description %s"
           --#ARGUMENTS {0,1,2,3,}
            --#SEVERITY  INFORMATIONAL
            --#TIMEINDEX 136
        ::= 136006018

   mngmtAgentTrap-6019 TRAP-TYPE
        ENTERPRISE compaq
        VARIABLES  { hostName,
                     scellNameDateTime,
                     agentEventCode,
                     agentEventDescription }
        DESCRIPTION
             "No MLD Handle Set"
           --#TYPE      "Management Agent Event 6019"
           --#SUMMARY   "Host %s : SCellName-TimeDate %s : EventCode %d : Description %s"
           --#ARGUMENTS {0,1,2,3,}
            --#SEVERITY  INFORMATIONAL
            --#TIMEINDEX 136
        ::= 136006019

   mngmtAgentTrap-6020 TRAP-TYPE
        ENTERPRISE compaq
        VARIABLES  { hostName,
                     scellNameDateTime,
                     agentEventCode,
                     agentEventDescription }
        DESCRIPTION
             "Failed Transport Layer Communication - No Such Id"
           --#TYPE      "Management Agent Event 6020"
           --#SUMMARY   "Host %s : SCellName-TimeDate %s : EventCode %d : Description %s"
           --#ARGUMENTS {0,1,2,3,}
            --#SEVERITY  INFORMATIONAL
            --#TIMEINDEX 136
        ::= 136006020

   mngmtAgentTrap-6021 TRAP-TYPE
        ENTERPRISE compaq
        VARIABLES  { hostName,
                     scellNameDateTime,
                     agentEventCode,
                     agentEventDescription }
        DESCRIPTION
             "Failed Transport Layer Communication - TimeOut"
           --#TYPE      "Management Agent Event 6021"
           --#SUMMARY   "Host %s : SCellName-TimeDate %s : EventCode %d : Description %s"
           --#ARGUMENTS {0,1,2,3,}
            --#SEVERITY  INFORMATIONAL
            --#TIMEINDEX 136
        ::= 136006021

   mngmtAgentTrap-6022 TRAP-TYPE
        ENTERPRISE compaq
        VARIABLES  { hostName,
                     scellNameDateTime,
                     agentEventCode,
                     agentEventDescription }
        DESCRIPTION
             "No initialized storage system objects found"
           --#TYPE      "Management Agent Event 6022"
           --#SUMMARY   "Host %s : SCellName-TimeDate %s : EventCode %d : Description %s"
           --#ARGUMENTS {0,1,2,3,}
            --#SEVERITY  INFORMATIONAL
            --#TIMEINDEX 136
        ::= 136006022

   mngmtAgentTrap-6023 TRAP-TYPE
        ENTERPRISE compaq
        VARIABLES  { hostName,
                     scellNameDateTime,
                     agentEventCode,
                     agentEventDescription }
        DESCRIPTION
             "No Attached Port Found"
           --#TYPE      "Management Agent Event 6023"
           --#SUMMARY   "Host %s : SCellName-TimeDate %s : EventCode %d : Description %s"
           --#ARGUMENTS {0,1,2,3,}
            --#SEVERITY  INFORMATIONAL
            --#TIMEINDEX 136
        ::= 136006023

   mngmtAgentTrap-6024 TRAP-TYPE
        ENTERPRISE compaq
        VARIABLES  { hostName,
                     scellNameDateTime,
                     agentEventCode,
                     agentEventDescription }
        DESCRIPTION
             "Failed to get SCMI Object Handle"
           --#TYPE      "Management Agent Event 6024"
           --#SUMMARY   "Host %s : SCellName-TimeDate %s : EventCode %d : Description %s"
           --#ARGUMENTS {0,1,2,3,}
            --#SEVERITY  INFORMATIONAL
            --#TIMEINDEX 136
        ::= 136006024

   mngmtAgentTrap-6025 TRAP-TYPE
        ENTERPRISE compaq
        VARIABLES  { hostName,
                     scellNameDateTime,
                     agentEventCode,
                     agentEventDescription }
        DESCRIPTION
             "Shutdown Both Restart And Power Off Requested"
           --#TYPE      "Management Agent Event 6025"
           --#SUMMARY   "Host %s : SCellName-TimeDate %s : EventCode %d : Description %s"
           --#ARGUMENTS {0,1,2,3,}
            --#SEVERITY  INFORMATIONAL
            --#TIMEINDEX 136
        ::= 136006025

   mngmtAgentTrap-6026 TRAP-TYPE
        ENTERPRISE compaq
        VARIABLES  { hostName,
                     scellNameDateTime,
                     agentEventCode,
                     agentEventDescription }
        DESCRIPTION
             "Shutdown Drive Shelf Power Off But No Enclosure Power Off Requested"
           --#TYPE      "Management Agent Event 6026"
           --#SUMMARY   "Host %s : SCellName-TimeDate %s : EventCode %d : Description %s"
           --#ARGUMENTS {0,1,2,3,}
            --#SEVERITY  INFORMATIONAL
            --#TIMEINDEX 136
        ::= 136006026

   mngmtAgentTrap-6027 TRAP-TYPE
        ENTERPRISE compaq
        VARIABLES  { hostName,
                     scellNameDateTime,
                     agentEventCode,
                     agentEventDescription }
        DESCRIPTION
             "Shutdown Disable Battery But No Enclosure Power Off Requested"
           --#TYPE      "Management Agent Event 6027"
           --#SUMMARY   "Host %s : SCellName-TimeDate %s : EventCode %d : Description %s"
           --#ARGUMENTS {0,1,2,3,}
            --#SEVERITY  INFORMATIONAL
            --#TIMEINDEX 136
        ::= 136006027

   mngmtAgentTrap-6028 TRAP-TYPE
        ENTERPRISE compaq
        VARIABLES  { hostName,
                     scellNameDateTime,
                     agentEventCode,
                     agentEventDescription }
        DESCRIPTION
             "Shutdown Disable Battery But Shutdown Unconditional Requested"
           --#TYPE      "Management Agent Event 6028"
           --#SUMMARY   "Host %s : SCellName-TimeDate %s : EventCode %d : Description %s"
           --#ARGUMENTS {0,1,2,3,}
            --#SEVERITY  INFORMATIONAL
            --#TIMEINDEX 136
        ::= 136006028

   mngmtAgentTrap-6029 TRAP-TYPE
        ENTERPRISE compaq
        VARIABLES  { hostName,
                     scellNameDateTime,
                     agentEventCode,
                     agentEventDescription }
        DESCRIPTION
             "Shutdown Delay Out Of Range"
           --#TYPE      "Management Agent Event 6029"
           --#SUMMARY   "Host %s : SCellName-TimeDate %s : EventCode %d : Description %s"
           --#ARGUMENTS {0,1,2,3,}
            --#SEVERITY  INFORMATIONAL
            --#TIMEINDEX 136
        ::= 136006029

   mngmtAgentTrap-6030 TRAP-TYPE
        ENTERPRISE compaq
        VARIABLES  { hostName,
                     scellNameDateTime,
                     agentEventCode,
                     agentEventDescription }
        DESCRIPTION
             "Cache Write Failure"
           --#TYPE      "Management Agent Event 6030"
           --#SUMMARY   "Host %s : SCellName-TimeDate %s : EventCode %d : Description %s"
           --#ARGUMENTS {0,1,2,3,}
            --#SEVERITY  INFORMATIONAL
            --#TIMEINDEX 136
        ::= 136006030

   mngmtAgentTrap-6031 TRAP-TYPE
        ENTERPRISE compaq
        VARIABLES  { hostName,
                     scellNameDateTime,
                     agentEventCode,
                     agentEventDescription }
        DESCRIPTION
             "Battery Disable Failure"
           --#TYPE      "Management Agent Event 6031"
           --#SUMMARY   "Host %s : SCellName-TimeDate %s : EventCode %d : Description %s"
           --#ARGUMENTS {0,1,2,3,}
            --#SEVERITY  INFORMATIONAL
            --#TIMEINDEX 136
        ::= 136006031

   mngmtAgentTrap-6032 TRAP-TYPE
        ENTERPRISE compaq
        VARIABLES  { hostName,
                     scellNameDateTime,
                     agentEventCode,
                     agentEventDescription }
        DESCRIPTION
             "Drive Shelf Disable Failure"
           --#TYPE      "Management Agent Event 6032"
           --#SUMMARY   "Host %s : SCellName-TimeDate %s : EventCode %d : Description %s"
           --#ARGUMENTS {0,1,2,3,}
            --#SEVERITY  INFORMATIONAL
            --#TIMEINDEX 136
        ::= 136006032

   mngmtAgentTrap-6033 TRAP-TYPE
        ENTERPRISE compaq
        VARIABLES  { hostName,
                     scellNameDateTime,
                     agentEventCode,
                     agentEventDescription }
        DESCRIPTION
             "Battery Disable Failed on Both Controllers Batteries"
           --#TYPE      "Management Agent Event 6033"
           --#SUMMARY   "Host %s : SCellName-TimeDate %s : EventCode %d : Description %s"
           --#ARGUMENTS {0,1,2,3,}
            --#SEVERITY  INFORMATIONAL
            --#TIMEINDEX 136
        ::= 136006033

   mngmtAgentTrap-6034 TRAP-TYPE
        ENTERPRISE compaq
        VARIABLES  { hostName,
                     scellNameDateTime,
                     agentEventCode,
                     agentEventDescription }
        DESCRIPTION
             "Battery Disable Failed on This Controllers Battery"
           --#TYPE      "Management Agent Event 6034"
           --#SUMMARY   "Host %s : SCellName-TimeDate %s : EventCode %d : Description %s"
           --#ARGUMENTS {0,1,2,3,}
            --#SEVERITY  INFORMATIONAL
            --#TIMEINDEX 136
        ::= 136006034

   mngmtAgentTrap-6035 TRAP-TYPE
        ENTERPRISE compaq
        VARIABLES  { hostName,
                     scellNameDateTime,
                     agentEventCode,
                     agentEventDescription }
        DESCRIPTION
             "Battery Disable Failed on the Other Controllers Battery"
           --#TYPE      "Management Agent Event 6035"
           --#SUMMARY   "Host %s : SCellName-TimeDate %s : EventCode %d : Description %s"
           --#ARGUMENTS {0,1,2,3,}
            --#SEVERITY  INFORMATIONAL
            --#TIMEINDEX 136
        ::= 136006035

   mngmtAgentTrap-6036 TRAP-TYPE
        ENTERPRISE compaq
        VARIABLES  { hostName,
                     scellNameDateTime,
                     agentEventCode,
                     agentEventDescription }
        DESCRIPTION
             "Requested disk failure protection level is set. Actual level will change when sufficient disk space is available."
           --#TYPE      "Management Agent Event 6036"
           --#SUMMARY   "Host %s : SCellName-TimeDate %s : EventCode %d : Description %s"
           --#ARGUMENTS {0,1,2,3,}
            --#SEVERITY  INFORMATIONAL
            --#TIMEINDEX 136
        ::= 136006036

   mngmtAgentTrap-6037 TRAP-TYPE
        ENTERPRISE compaq
        VARIABLES  { hostName,
                     scellNameDateTime,
                     agentEventCode,
                     agentEventDescription }
        DESCRIPTION
             "Physical Store Contains Stale or Foreign Volume Information."
           --#TYPE      "Management Agent Event 6037"
           --#SUMMARY   "Host %s : SCellName-TimeDate %s : EventCode %d : Description %s"
           --#ARGUMENTS {0,1,2,3,}
            --#SEVERITY  INFORMATIONAL
            --#TIMEINDEX 136
        ::= 136006037

   mngmtAgentTrap-6038 TRAP-TYPE
        ENTERPRISE compaq
        VARIABLES  { hostName,
                     scellNameDateTime,
                     agentEventCode,
                     agentEventDescription }
        DESCRIPTION
             "Controller Resynchronization or Reboot Occurred. Context Error"
           --#TYPE      "Management Agent Event 6038"
           --#SUMMARY   "Host %s : SCellName-TimeDate %s : EventCode %d : Description %s"
           --#ARGUMENTS {0,1,2,3,}
            --#SEVERITY  MINOR
            --#TIMEINDEX 136
        ::= 136006038

   mngmtAgentTrap-6040 TRAP-TYPE
        ENTERPRISE compaq
        VARIABLES  { hostName,
                     scellNameDateTime,
                     agentEventCode,
                     agentEventDescription }
        DESCRIPTION
             "No Drm Members Found"
           --#TYPE      "Management Agent Event 6040"
           --#SUMMARY   "Host %s : SCellName-TimeDate %s : EventCode %d : Description %s"
           --#ARGUMENTS {0,1,2,3,}
            --#SEVERITY  INFORMATIONAL
            --#TIMEINDEX 136
        ::= 136006040

   mngmtAgentTrap-6041 TRAP-TYPE
        ENTERPRISE compaq
        VARIABLES  { hostName,
                     scellNameDateTime,
                     agentEventCode,
                     agentEventDescription }
        DESCRIPTION
             "Service Started"
           --#TYPE      "Management Agent Event 6041"
           --#SUMMARY   "Host %s : SCellName-TimeDate %s : EventCode %d : Description %s"
           --#ARGUMENTS {0,1,2,3,}
            --#SEVERITY  INFORMATIONAL
            --#TIMEINDEX 136
        ::= 136006041

   mngmtAgentTrap-8001 TRAP-TYPE
        ENTERPRISE compaq
        VARIABLES  { hostName,
                     scellNameDateTime,
                     agentEventCode,
                     agentEventDescription }
        DESCRIPTION
             "Invalid Operation"
           --#TYPE      "Management Agent Event 8001"
           --#SUMMARY   "Host %s : SCellName-TimeDate %s : EventCode %d : Description %s"
           --#ARGUMENTS {0,1,2,3,}
            --#SEVERITY  INFORMATIONAL
            --#TIMEINDEX 136
        ::= 136008001

   mngmtAgentTrap-8002 TRAP-TYPE
        ENTERPRISE compaq
        VARIABLES  { hostName,
                     scellNameDateTime,
                     agentEventCode,
                     agentEventDescription }
        DESCRIPTION
             "Storage system already created"
           --#TYPE      "Management Agent Event 8002"
           --#SUMMARY   "Host %s : SCellName-TimeDate %s : EventCode %d : Description %s"
           --#ARGUMENTS {0,1,2,3,}
            --#SEVERITY  INFORMATIONAL
            --#TIMEINDEX 136
        ::= 136008002

   mngmtAgentTrap-8003 TRAP-TYPE
        ENTERPRISE compaq
        VARIABLES  { hostName,
                     scellNameDateTime,
                     agentEventCode,
                     agentEventDescription }
        DESCRIPTION
             "Controller already part of storage system configuration"
           --#TYPE      "Management Agent Event 8003"
           --#SUMMARY   "Host %s : SCellName-TimeDate %s : EventCode %d : Description %s"
           --#ARGUMENTS {0,1,2,3,}
            --#SEVERITY  INFORMATIONAL
            --#TIMEINDEX 136
        ::= 136008003

   mngmtAgentTrap-8004 TRAP-TYPE
        ENTERPRISE compaq
        VARIABLES  { hostName,
                     scellNameDateTime,
                     agentEventCode,
                     agentEventDescription }
        DESCRIPTION
             "Physical Store Count Below Minimum"
           --#TYPE      "Management Agent Event 8004"
           --#SUMMARY   "Host %s : SCellName-TimeDate %s : EventCode %d : Description %s"
           --#ARGUMENTS {0,1,2,3,}
            --#SEVERITY  INFORMATIONAL
            --#TIMEINDEX 136
        ::= 136008004

   mngmtAgentTrap-8005 TRAP-TYPE
        ENTERPRISE compaq
        VARIABLES  { hostName,
                     scellNameDateTime,
                     agentEventCode,
                     agentEventDescription }
        DESCRIPTION
             "Controller not part of storage system configuration"
           --#TYPE      "Management Agent Event 8005"
           --#SUMMARY   "Host %s : SCellName-TimeDate %s : EventCode %d : Description %s"
           --#ARGUMENTS {0,1,2,3,}
            --#SEVERITY  INFORMATIONAL
            --#TIMEINDEX 136
        ::= 136008005

   mngmtAgentTrap-8006 TRAP-TYPE
        ENTERPRISE compaq
        VARIABLES  { hostName,
                     scellNameDateTime,
                     agentEventCode,
                     agentEventDescription }
        DESCRIPTION
             "Failed to uninitialize storage system"
           --#TYPE      "Management Agent Event 8006"
           --#SUMMARY   "Host %s : SCellName-TimeDate %s : EventCode %d : Description %s"
           --#ARGUMENTS {0,1,2,3,}
            --#SEVERITY  INFORMATIONAL
            --#TIMEINDEX 136
        ::= 136008006

   mngmtAgentTrap-8007 TRAP-TYPE
        ENTERPRISE compaq
        VARIABLES  { hostName,
                     scellNameDateTime,
                     agentEventCode,
                     agentEventDescription }
        DESCRIPTION
             "Storage system File Open Error"
           --#TYPE      "Management Agent Event 8007"
           --#SUMMARY   "Host %s : SCellName-TimeDate %s : EventCode %d : Description %s"
           --#ARGUMENTS {0,1,2,3,}
            --#SEVERITY  MINOR
            --#TIMEINDEX 136
        ::= 136008007

   mngmtAgentTrap-8008 TRAP-TYPE
        ENTERPRISE compaq
        VARIABLES  { hostName,
                     scellNameDateTime,
                     agentEventCode,
                     agentEventDescription }
        DESCRIPTION
             "Storage system File Write Error"
           --#TYPE      "Management Agent Event 8008"
           --#SUMMARY   "Host %s : SCellName-TimeDate %s : EventCode %d : Description %s"
           --#ARGUMENTS {0,1,2,3,}
            --#SEVERITY  MINOR
            --#TIMEINDEX 136
        ::= 136008008

   mngmtAgentTrap-8009 TRAP-TYPE
        ENTERPRISE compaq
        VARIABLES  { hostName,
                     scellNameDateTime,
                     agentEventCode,
                     agentEventDescription }
        DESCRIPTION
             "Storage system File Read Error"
           --#TYPE      "Management Agent Event 8009"
           --#SUMMARY   "Host %s : SCellName-TimeDate %s : EventCode %d : Description %s"
           --#ARGUMENTS {0,1,2,3,}
            --#SEVERITY  MINOR
            --#TIMEINDEX 136
        ::= 136008009

   mngmtAgentTrap-8010 TRAP-TYPE
        ENTERPRISE compaq
        VARIABLES  { hostName,
                     scellNameDateTime,
                     agentEventCode,
                     agentEventDescription }
        DESCRIPTION
             "Name too long"
           --#TYPE      "Management Agent Event 8010"
           --#SUMMARY   "Host %s : SCellName-TimeDate %s : EventCode %d : Description %s"
           --#ARGUMENTS {0,1,2,3,}
            --#SEVERITY  INFORMATIONAL
            --#TIMEINDEX 136
        ::= 136008010

   mngmtAgentTrap-8011 TRAP-TYPE
        ENTERPRISE compaq
        VARIABLES  { hostName,
                     scellNameDateTime,
                     agentEventCode,
                     agentEventDescription }
        DESCRIPTION
             "No String Error"
           --#TYPE      "Management Agent Event 8011"
           --#SUMMARY   "Host %s : SCellName-TimeDate %s : EventCode %d : Description %s"
           --#ARGUMENTS {0,1,2,3,}
            --#SEVERITY  INFORMATIONAL
            --#TIMEINDEX 136
        ::= 136008011

   mngmtAgentTrap-8012 TRAP-TYPE
        ENTERPRISE compaq
        VARIABLES  { hostName,
                     scellNameDateTime,
                     agentEventCode,
                     agentEventDescription }
        DESCRIPTION
             "No MLD Handle Found"
           --#TYPE      "Management Agent Event 8012"
           --#SUMMARY   "Host %s : SCellName-TimeDate %s : EventCode %d : Description %s"
           --#ARGUMENTS {0,1,2,3,}
            --#SEVERITY  INFORMATIONAL
            --#TIMEINDEX 136
        ::= 136008012

   mngmtAgentTrap-8013 TRAP-TYPE
        ENTERPRISE compaq
        VARIABLES  { hostName,
                     scellNameDateTime,
                     agentEventCode,
                     agentEventDescription }
        DESCRIPTION
             "No Controllers Found"
           --#TYPE      "Management Agent Event 8013"
           --#SUMMARY   "Host %s : SCellName-TimeDate %s : EventCode %d : Description %s"
           --#ARGUMENTS {0,1,2,3,}
            --#SEVERITY  INFORMATIONAL
            --#TIMEINDEX 136
        ::= 136008013

   mngmtAgentTrap-8014 TRAP-TYPE
        ENTERPRISE compaq
        VARIABLES  { hostName,
                     scellNameDateTime,
                     agentEventCode,
                     agentEventDescription }
        DESCRIPTION
             "Controller Not Found On Loop"
           --#TYPE      "Management Agent Event 8014"
           --#SUMMARY   "Host %s : SCellName-TimeDate %s : EventCode %d : Description %s"
           --#ARGUMENTS {0,1,2,3,}
            --#SEVERITY  INFORMATIONAL
            --#TIMEINDEX 136
        ::= 136008014

   mngmtAgentTrap-8015 TRAP-TYPE
        ENTERPRISE compaq
        VARIABLES  { hostName,
                     scellNameDateTime,
                     agentEventCode,
                     agentEventDescription }
        DESCRIPTION
             "No Disk Groups Found"
           --#TYPE      "Management Agent Event 8015"
           --#SUMMARY   "Host %s : SCellName-TimeDate %s : EventCode %d : Description %s"
           --#ARGUMENTS {0,1,2,3,}
            --#SEVERITY  INFORMATIONAL
            --#TIMEINDEX 136
        ::= 136008015

   mngmtAgentTrap-8016 TRAP-TYPE
        ENTERPRISE compaq
        VARIABLES  { hostName,
                     scellNameDateTime,
                     agentEventCode,
                     agentEventDescription }
        DESCRIPTION
             "No Volumes Found"
           --#TYPE      "Management Agent Event 8016"
           --#SUMMARY   "Host %s : SCellName-TimeDate %s : EventCode %d : Description %s"
           --#ARGUMENTS {0,1,2,3,}
            --#SEVERITY  INFORMATIONAL
            --#TIMEINDEX 136
        ::= 136008016

   mngmtAgentTrap-8017 TRAP-TYPE
        ENTERPRISE compaq
        VARIABLES  { hostName,
                     scellNameDateTime,
                     agentEventCode,
                     agentEventDescription }
        DESCRIPTION
             "No Physical Stores Found"
           --#TYPE      "Management Agent Event 8017"
           --#SUMMARY   "Host %s : SCellName-TimeDate %s : EventCode %d : Description %s"
           --#ARGUMENTS {0,1,2,3,}
            --#SEVERITY  INFORMATIONAL
            --#TIMEINDEX 136
        ::= 136008017

   mngmtAgentTrap-8018 TRAP-TYPE
        ENTERPRISE compaq
        VARIABLES  { hostName,
                     scellNameDateTime,
                     agentEventCode,
                     agentEventDescription }
        DESCRIPTION
             "No Vdisks Found"
           --#TYPE      "Management Agent Event 8018"
           --#SUMMARY   "Host %s : SCellName-TimeDate %s : EventCode %d : Description %s"
           --#ARGUMENTS {0,1,2,3,}
            --#SEVERITY  INFORMATIONAL
            --#TIMEINDEX 136
        ::= 136008018

   mngmtAgentTrap-8019 TRAP-TYPE
        ENTERPRISE compaq
        VARIABLES  { hostName,
                     scellNameDateTime,
                     agentEventCode,
                     agentEventDescription }
        DESCRIPTION
             "No Hosts Found"
           --#TYPE      "Management Agent Event 8019"
           --#SUMMARY   "Host %s : SCellName-TimeDate %s : EventCode %d : Description %s"
           --#ARGUMENTS {0,1,2,3,}
            --#SEVERITY  INFORMATIONAL
            --#TIMEINDEX 136
        ::= 136008019

   mngmtAgentTrap-8020 TRAP-TYPE
        ENTERPRISE compaq
        VARIABLES  { hostName,
                     scellNameDateTime,
                     agentEventCode,
                     agentEventDescription }
        DESCRIPTION
             "Name already exists"
           --#TYPE      "Management Agent Event 8020"
           --#SUMMARY   "Host %s : SCellName-TimeDate %s : EventCode %d : Description %s"
           --#ARGUMENTS {0,1,2,3,}
            --#SEVERITY  INFORMATIONAL
            --#TIMEINDEX 136
        ::= 136008020

   mngmtAgentTrap-8021 TRAP-TYPE
        ENTERPRISE compaq
        VARIABLES  { hostName,
                     scellNameDateTime,
                     agentEventCode,
                     agentEventDescription }
        DESCRIPTION
             "Folder is not empty"
           --#TYPE      "Management Agent Event 8021"
           --#SUMMARY   "Host %s : SCellName-TimeDate %s : EventCode %d : Description %s"
           --#ARGUMENTS {0,1,2,3,}
            --#SEVERITY  INFORMATIONAL
            --#TIMEINDEX 136
        ::= 136008021

   mngmtAgentTrap-8022 TRAP-TYPE
        ENTERPRISE compaq
        VARIABLES  { hostName,
                     scellNameDateTime,
                     agentEventCode,
                     agentEventDescription }
        DESCRIPTION
             "Spares goal could not be met"
           --#TYPE      "Management Agent Event 8022"
           --#SUMMARY   "Host %s : SCellName-TimeDate %s : EventCode %d : Description %s"
           --#ARGUMENTS {0,1,2,3,}
            --#SEVERITY  INFORMATIONAL
            --#TIMEINDEX 136
        ::= 136008022

   mngmtAgentTrap-8023 TRAP-TYPE
        ENTERPRISE compaq
        VARIABLES  { hostName,
                     scellNameDateTime,
                     agentEventCode,
                     agentEventDescription }
        DESCRIPTION
             "Storage system object found"
           --#TYPE      "Management Agent Event 8023"
           --#SUMMARY   "Host %s : SCellName-TimeDate %s : EventCode %d : Description %s"
           --#ARGUMENTS {0,1,2,3,}
            --#SEVERITY  INFORMATIONAL
            --#TIMEINDEX 136
        ::= 136008023

   mngmtAgentTrap-8024 TRAP-TYPE
        ENTERPRISE compaq
        VARIABLES  { hostName,
                     scellNameDateTime,
                     agentEventCode,
                     agentEventDescription }
        DESCRIPTION
             "Storage system object not found"
           --#TYPE      "Management Agent Event 8024"
           --#SUMMARY   "Host %s : SCellName-TimeDate %s : EventCode %d : Description %s"
           --#ARGUMENTS {0,1,2,3,}
            --#SEVERITY  INFORMATIONAL
            --#TIMEINDEX 136
        ::= 136008024

   mngmtAgentTrap-8025 TRAP-TYPE
        ENTERPRISE compaq
        VARIABLES  { hostName,
                     scellNameDateTime,
                     agentEventCode,
                     agentEventDescription }
        DESCRIPTION
             "New Physical Store Detected But Not Found In Physical Store List"
           --#TYPE      "Management Agent Event 8025"
           --#SUMMARY   "Host %s : SCellName-TimeDate %s : EventCode %d : Description %s"
           --#ARGUMENTS {0,1,2,3,}
            --#SEVERITY  INFORMATIONAL
            --#TIMEINDEX 136
        ::= 136008025

   mngmtAgentTrap-8026 TRAP-TYPE
        ENTERPRISE compaq
        VARIABLES  { hostName,
                     scellNameDateTime,
                     agentEventCode,
                     agentEventDescription }
        DESCRIPTION
             "MldManager Handle is NULL"
           --#TYPE      "Management Agent Event 8026"
           --#SUMMARY   "Host %s : SCellName-TimeDate %s : EventCode %d : Description %s"
           --#ARGUMENTS {0,1,2,3,}
            --#SEVERITY  MINOR
            --#TIMEINDEX 136
        ::= 136008026

   mngmtAgentTrap-8027 TRAP-TYPE
        ENTERPRISE compaq
        VARIABLES  { hostName,
                     scellNameDateTime,
                     agentEventCode,
                     agentEventDescription }
        DESCRIPTION
             "NscMngrInterface Handle is NULL"
           --#TYPE      "Management Agent Event 8027"
           --#SUMMARY   "Host %s : SCellName-TimeDate %s : EventCode %d : Description %s"
           --#ARGUMENTS {0,1,2,3,}
            --#SEVERITY  MINOR
            --#TIMEINDEX 136
        ::= 136008027

   mngmtAgentTrap-8028 TRAP-TYPE
        ENTERPRISE compaq
        VARIABLES  { hostName,
                     scellNameDateTime,
                     agentEventCode,
                     agentEventDescription }
        DESCRIPTION
             "ScLockMngr Handle is NULL"
           --#TYPE      "Management Agent Event 8028"
           --#SUMMARY   "Host %s : SCellName-TimeDate %s : EventCode %d : Description %s"
           --#ARGUMENTS {0,1,2,3,}
            --#SEVERITY  MINOR
            --#TIMEINDEX 136
        ::= 136008028

   mngmtAgentTrap-8029 TRAP-TYPE
        ENTERPRISE compaq
        VARIABLES  { hostName,
                     scellNameDateTime,
                     agentEventCode,
                     agentEventDescription }
        DESCRIPTION
             "Storage system initialization failed"
           --#TYPE      "Management Agent Event 8029"
           --#SUMMARY   "Host %s : SCellName-TimeDate %s : EventCode %d : Description %s"
           --#ARGUMENTS {0,1,2,3,}
            --#SEVERITY  CRITICAL
            --#TIMEINDEX 136
        ::= 136008029

   mngmtAgentTrap-8030 TRAP-TYPE
        ENTERPRISE compaq
        VARIABLES  { hostName,
                     scellNameDateTime,
                     agentEventCode,
                     agentEventDescription }
        DESCRIPTION
             "MldMngr, NscMngrInterfaceMngr, or ScLockMngr Handle is NULL"
           --#TYPE      "Management Agent Event 8030"
           --#SUMMARY   "Host %s : SCellName-TimeDate %s : EventCode %d : Description %s"
           --#ARGUMENTS {0,1,2,3,}
            --#SEVERITY  MINOR
            --#TIMEINDEX 136
        ::= 136008030

   mngmtAgentTrap-8031 TRAP-TYPE
        ENTERPRISE compaq
        VARIABLES  { hostName,
                     scellNameDateTime,
                     agentEventCode,
                     agentEventDescription }
        DESCRIPTION
             "Storage system initialization failed"
           --#TYPE      "Management Agent Event 8031"
           --#SUMMARY   "Host %s : SCellName-TimeDate %s : EventCode %d : Description %s"
           --#ARGUMENTS {0,1,2,3,}
            --#SEVERITY  CRITICAL
            --#TIMEINDEX 136
        ::= 136008031

   mngmtAgentTrap-8032 TRAP-TYPE
        ENTERPRISE compaq
        VARIABLES  { hostName,
                     scellNameDateTime,
                     agentEventCode,
                     agentEventDescription }
        DESCRIPTION
             "Storage system discovery failed"
           --#TYPE      "Management Agent Event 8032"
           --#SUMMARY   "Host %s : SCellName-TimeDate %s : EventCode %d : Description %s"
           --#ARGUMENTS {0,1,2,3,}
            --#SEVERITY  MINOR
            --#TIMEINDEX 136
        ::= 136008032

   mngmtAgentTrap-8033 TRAP-TYPE
        ENTERPRISE compaq
        VARIABLES  { hostName,
                     scellNameDateTime,
                     agentEventCode,
                     agentEventDescription }
        DESCRIPTION
             "Storage system already uninitialized or does not exist"
           --#TYPE      "Management Agent Event 8033"
           --#SUMMARY   "Host %s : SCellName-TimeDate %s : EventCode %d : Description %s"
           --#ARGUMENTS {0,1,2,3,}
            --#SEVERITY  INFORMATIONAL
            --#TIMEINDEX 136
        ::= 136008033

   mngmtAgentTrap-8034 TRAP-TYPE
        ENTERPRISE compaq
        VARIABLES  { hostName,
                     scellNameDateTime,
                     agentEventCode,
                     agentEventDescription }
        DESCRIPTION
             "Get Total Storage Failed"
           --#TYPE      "Management Agent Event 8034"
           --#SUMMARY   "Host %s : SCellName-TimeDate %s : EventCode %d : Description %s"
           --#ARGUMENTS {0,1,2,3,}
            --#SEVERITY  MINOR
            --#TIMEINDEX 136
        ::= 136008034

   mngmtAgentTrap-8035 TRAP-TYPE
        ENTERPRISE compaq
        VARIABLES  { hostName,
                     scellNameDateTime,
                     agentEventCode,
                     agentEventDescription }
        DESCRIPTION
             "Storage system is uninitialized"
           --#TYPE      "Management Agent Event 8035"
           --#SUMMARY   "Host %s : SCellName-TimeDate %s : EventCode %d : Description %s"
           --#ARGUMENTS {0,1,2,3,}
            --#SEVERITY  INFORMATIONAL
            --#TIMEINDEX 136
        ::= 136008035

   mngmtAgentTrap-8036 TRAP-TYPE
        ENTERPRISE compaq
        VARIABLES  { hostName,
                     scellNameDateTime,
                     agentEventCode,
                     agentEventDescription }
        DESCRIPTION
             "Get Total Storage Available Failed"
           --#TYPE      "Management Agent Event 8036"
           --#SUMMARY   "Host %s : SCellName-TimeDate %s : EventCode %d : Description %s"
           --#ARGUMENTS {0,1,2,3,}
            --#SEVERITY  MINOR
            --#TIMEINDEX 136
        ::= 136008036

   mngmtAgentTrap-8037 TRAP-TYPE
        ENTERPRISE compaq
        VARIABLES  { hostName,
                     scellNameDateTime,
                     agentEventCode,
                     agentEventDescription }
        DESCRIPTION
             "Get Total Storage Occupied Failed"
           --#TYPE      "Management Agent Event 8037"
           --#SUMMARY   "Host %s : SCellName-TimeDate %s : EventCode %d : Description %s"
           --#ARGUMENTS {0,1,2,3,}
            --#SEVERITY  MINOR
            --#TIMEINDEX 136
        ::= 136008037

   mngmtAgentTrap-8038 TRAP-TYPE
        ENTERPRISE compaq
        VARIABLES  { hostName,
                     scellNameDateTime,
                     agentEventCode,
                     agentEventDescription }
        DESCRIPTION
             "Get Total Storage Free Failed"
           --#TYPE      "Management Agent Event 8038"
           --#SUMMARY   "Host %s : SCellName-TimeDate %s : EventCode %d : Description %s"
           --#ARGUMENTS {0,1,2,3,}
            --#SEVERITY  MINOR
            --#TIMEINDEX 136
        ::= 136008038

   mngmtAgentTrap-8039 TRAP-TYPE
        ENTERPRISE compaq
        VARIABLES  { hostName,
                     scellNameDateTime,
                     agentEventCode,
                     agentEventDescription }
        DESCRIPTION
             "Get Disk Group Failed"
           --#TYPE      "Management Agent Event 8039"
           --#SUMMARY   "Host %s : SCellName-TimeDate %s : EventCode %d : Description %s"
           --#ARGUMENTS {0,1,2,3,}
            --#SEVERITY  MINOR
            --#TIMEINDEX 136
        ::= 136008039

   mngmtAgentTrap-8040 TRAP-TYPE
        ENTERPRISE compaq
        VARIABLES  { hostName,
                     scellNameDateTime,
                     agentEventCode,
                     agentEventDescription }
        DESCRIPTION
             "Get Disk Group List Failed"
           --#TYPE      "Management Agent Event 8040"
           --#SUMMARY   "Host %s : SCellName-TimeDate %s : EventCode %d : Description %s"
           --#ARGUMENTS {0,1,2,3,}
            --#SEVERITY  MINOR
            --#TIMEINDEX 136
        ::= 136008040

   mngmtAgentTrap-8041 TRAP-TYPE
        ENTERPRISE compaq
        VARIABLES  { hostName,
                     scellNameDateTime,
                     agentEventCode,
                     agentEventDescription }
        DESCRIPTION
             "Get Disk Group Count Failed"
           --#TYPE      "Management Agent Event 8041"
           --#SUMMARY   "Host %s : SCellName-TimeDate %s : EventCode %d : Description %s"
           --#ARGUMENTS {0,1,2,3,}
            --#SEVERITY  MINOR
            --#TIMEINDEX 136
        ::= 136008041

   mngmtAgentTrap-8042 TRAP-TYPE
        ENTERPRISE compaq
        VARIABLES  { hostName,
                     scellNameDateTime,
                     agentEventCode,
                     agentEventDescription }
        DESCRIPTION
             "Create Volume Failed"
           --#TYPE      "Management Agent Event 8042"
           --#SUMMARY   "Host %s : SCellName-TimeDate %s : EventCode %d : Description %s"
           --#ARGUMENTS {0,1,2,3,}
            --#SEVERITY  MINOR
            --#TIMEINDEX 136
        ::= 136008042

   mngmtAgentTrap-8043 TRAP-TYPE
        ENTERPRISE compaq
        VARIABLES  { hostName,
                     scellNameDateTime,
                     agentEventCode,
                     agentEventDescription }
        DESCRIPTION
             "Get Volume Failed"
           --#TYPE      "Management Agent Event 8043"
           --#SUMMARY   "Host %s : SCellName-TimeDate %s : EventCode %d : Description %s"
           --#ARGUMENTS {0,1,2,3,}
            --#SEVERITY  MINOR
            --#TIMEINDEX 136
        ::= 136008043

   mngmtAgentTrap-8044 TRAP-TYPE
        ENTERPRISE compaq
        VARIABLES  { hostName,
                     scellNameDateTime,
                     agentEventCode,
                     agentEventDescription }
        DESCRIPTION
             "Get Volumes Failed"
           --#TYPE      "Management Agent Event 8044"
           --#SUMMARY   "Host %s : SCellName-TimeDate %s : EventCode %d : Description %s"
           --#ARGUMENTS {0,1,2,3,}
            --#SEVERITY  MINOR
            --#TIMEINDEX 136
        ::= 136008044

   mngmtAgentTrap-8045 TRAP-TYPE
        ENTERPRISE compaq
        VARIABLES  { hostName,
                     scellNameDateTime,
                     agentEventCode,
                     agentEventDescription }
        DESCRIPTION
             "Get Volumes Count Failed"
           --#TYPE      "Management Agent Event 8045"
           --#SUMMARY   "Host %s : SCellName-TimeDate %s : EventCode %d : Description %s"
           --#ARGUMENTS {0,1,2,3,}
            --#SEVERITY  MINOR
            --#TIMEINDEX 136
        ::= 136008045

   mngmtAgentTrap-8046 TRAP-TYPE
        ENTERPRISE compaq
        VARIABLES  { hostName,
                     scellNameDateTime,
                     agentEventCode,
                     agentEventDescription }
        DESCRIPTION
             "Get Vdisk Failed"
           --#TYPE      "Management Agent Event 8046"
           --#SUMMARY   "Host %s : SCellName-TimeDate %s : EventCode %d : Description %s"
           --#ARGUMENTS {0,1,2,3,}
            --#SEVERITY  MINOR
            --#TIMEINDEX 136
        ::= 136008046

   mngmtAgentTrap-8047 TRAP-TYPE
        ENTERPRISE compaq
        VARIABLES  { hostName,
                     scellNameDateTime,
                     agentEventCode,
                     agentEventDescription }
        DESCRIPTION
             "Get Vdisk List Failed"
           --#TYPE      "Management Agent Event 8047"
           --#SUMMARY   "Host %s : SCellName-TimeDate %s : EventCode %d : Description %s"
           --#ARGUMENTS {0,1,2,3,}
            --#SEVERITY  MINOR
            --#TIMEINDEX 136
        ::= 136008047

   mngmtAgentTrap-8048 TRAP-TYPE
        ENTERPRISE compaq
        VARIABLES  { hostName,
                     scellNameDateTime,
                     agentEventCode,
                     agentEventDescription }
        DESCRIPTION
             "Get Physical Store Failed"
           --#TYPE      "Management Agent Event 8048"
           --#SUMMARY   "Host %s : SCellName-TimeDate %s : EventCode %d : Description %s"
           --#ARGUMENTS {0,1,2,3,}
            --#SEVERITY  MINOR
            --#TIMEINDEX 136
        ::= 136008048

   mngmtAgentTrap-8049 TRAP-TYPE
        ENTERPRISE compaq
        VARIABLES  { hostName,
                     scellNameDateTime,
                     agentEventCode,
                     agentEventDescription }
        DESCRIPTION
             "Get Physical Stores Failed"
           --#TYPE      "Management Agent Event 8049"
           --#SUMMARY   "Host %s : SCellName-TimeDate %s : EventCode %d : Description %s"
           --#ARGUMENTS {0,1,2,3,}
            --#SEVERITY  MINOR
            --#TIMEINDEX 136
        ::= 136008049

   mngmtAgentTrap-8050 TRAP-TYPE
        ENTERPRISE compaq
        VARIABLES  { hostName,
                     scellNameDateTime,
                     agentEventCode,
                     agentEventDescription }
        DESCRIPTION
             "Get Physical Stores Count Failed"
           --#TYPE      "Management Agent Event 8050"
           --#SUMMARY   "Host %s : SCellName-TimeDate %s : EventCode %d : Description %s"
           --#ARGUMENTS {0,1,2,3,}
            --#SEVERITY  MINOR
            --#TIMEINDEX 136
        ::= 136008050

   mngmtAgentTrap-8051 TRAP-TYPE
        ENTERPRISE compaq
        VARIABLES  { hostName,
                     scellNameDateTime,
                     agentEventCode,
                     agentEventDescription }
        DESCRIPTION
             "Create Vdisk Failed"
           --#TYPE      "Management Agent Event 8051"
           --#SUMMARY   "Host %s : SCellName-TimeDate %s : EventCode %d : Description %s"
           --#ARGUMENTS {0,1,2,3,}
            --#SEVERITY  MINOR
            --#TIMEINDEX 136
        ::= 136008051

   mngmtAgentTrap-8052 TRAP-TYPE
        ENTERPRISE compaq
        VARIABLES  { hostName,
                     scellNameDateTime,
                     agentEventCode,
                     agentEventDescription }
        DESCRIPTION
             "Delete Vdisk Failed"
           --#TYPE      "Management Agent Event 8052"
           --#SUMMARY   "Host %s : SCellName-TimeDate %s : EventCode %d : Description %s"
           --#ARGUMENTS {0,1,2,3,}
            --#SEVERITY  MINOR
            --#TIMEINDEX 136
        ::= 136008052

   mngmtAgentTrap-8053 TRAP-TYPE
        ENTERPRISE compaq
        VARIABLES  { hostName,
                     scellNameDateTime,
                     agentEventCode,
                     agentEventDescription }
        DESCRIPTION
             "Get Device Addition Policy Failed"
           --#TYPE      "Management Agent Event 8053"
           --#SUMMARY   "Host %s : SCellName-TimeDate %s : EventCode %d : Description %s"
           --#ARGUMENTS {0,1,2,3,}
            --#SEVERITY  MINOR
            --#TIMEINDEX 136
        ::= 136008053

   mngmtAgentTrap-8054 TRAP-TYPE
        ENTERPRISE compaq
        VARIABLES  { hostName,
                     scellNameDateTime,
                     agentEventCode,
                     agentEventDescription }
        DESCRIPTION
             "Get Spares Current Failed"
           --#TYPE      "Management Agent Event 8054"
           --#SUMMARY   "Host %s : SCellName-TimeDate %s : EventCode %d : Description %s"
           --#ARGUMENTS {0,1,2,3,}
            --#SEVERITY  MINOR
            --#TIMEINDEX 136
        ::= 136008054

   mngmtAgentTrap-8055 TRAP-TYPE
        ENTERPRISE compaq
        VARIABLES  { hostName,
                     scellNameDateTime,
                     agentEventCode,
                     agentEventDescription }
        DESCRIPTION
             "Get Spares Goal Failed"
           --#TYPE      "Management Agent Event 8055"
           --#SUMMARY   "Host %s : SCellName-TimeDate %s : EventCode %d : Description %s"
           --#ARGUMENTS {0,1,2,3,}
            --#SEVERITY  MINOR
            --#TIMEINDEX 136
        ::= 136008055

   mngmtAgentTrap-8056 TRAP-TYPE
        ENTERPRISE compaq
        VARIABLES  { hostName,
                     scellNameDateTime,
                     agentEventCode,
                     agentEventDescription }
        DESCRIPTION
             "Get storage system events failed"
           --#TYPE      "Management Agent Event 8056"
           --#SUMMARY   "Host %s : SCellName-TimeDate %s : EventCode %d : Description %s"
           --#ARGUMENTS {0,1,2,3,}
            --#SEVERITY  MINOR
            --#TIMEINDEX 136
        ::= 136008056

   mngmtAgentTrap-8057 TRAP-TYPE
        ENTERPRISE compaq
        VARIABLES  { hostName,
                     scellNameDateTime,
                     agentEventCode,
                     agentEventDescription }
        DESCRIPTION
             "Get Volume Replacement Delay Failed"
           --#TYPE      "Management Agent Event 8057"
           --#SUMMARY   "Host %s : SCellName-TimeDate %s : EventCode %d : Description %s"
           --#ARGUMENTS {0,1,2,3,}
            --#SEVERITY  MINOR
            --#TIMEINDEX 136
        ::= 136008057

   mngmtAgentTrap-8058 TRAP-TYPE
        ENTERPRISE compaq
        VARIABLES  { hostName,
                     scellNameDateTime,
                     agentEventCode,
                     agentEventDescription }
        DESCRIPTION
             "Set Device Addition Policy Failed"
           --#TYPE      "Management Agent Event 8058"
           --#SUMMARY   "Host %s : SCellName-TimeDate %s : EventCode %d : Description %s"
           --#ARGUMENTS {0,1,2,3,}
            --#SEVERITY  MINOR
            --#TIMEINDEX 136
        ::= 136008058

   mngmtAgentTrap-8059 TRAP-TYPE
        ENTERPRISE compaq
        VARIABLES  { hostName,
                     scellNameDateTime,
                     agentEventCode,
                     agentEventDescription }
        DESCRIPTION
             "Set Spares Goal Failed"
           --#TYPE      "Management Agent Event 8059"
           --#SUMMARY   "Host %s : SCellName-TimeDate %s : EventCode %d : Description %s"
           --#ARGUMENTS {0,1,2,3,}
            --#SEVERITY  MINOR
            --#TIMEINDEX 136
        ::= 136008059

   mngmtAgentTrap-8060 TRAP-TYPE
        ENTERPRISE compaq
        VARIABLES  { hostName,
                     scellNameDateTime,
                     agentEventCode,
                     agentEventDescription }
        DESCRIPTION
             "Set Volume Replacement Delay Failed"
           --#TYPE      "Management Agent Event 8060"
           --#SUMMARY   "Host %s : SCellName-TimeDate %s : EventCode %d : Description %s"
           --#ARGUMENTS {0,1,2,3,}
            --#SEVERITY  MINOR
            --#TIMEINDEX 136
        ::= 136008060

   mngmtAgentTrap-8061 TRAP-TYPE
        ENTERPRISE compaq
        VARIABLES  { hostName,
                     scellNameDateTime,
                     agentEventCode,
                     agentEventDescription }
        DESCRIPTION
             "Create controller Failed"
           --#TYPE      "Management Agent Event 8061"
           --#SUMMARY   "Host %s : SCellName-TimeDate %s : EventCode %d : Description %s"
           --#ARGUMENTS {0,1,2,3,}
            --#SEVERITY  MINOR
            --#TIMEINDEX 136
        ::= 136008061

   mngmtAgentTrap-8062 TRAP-TYPE
        ENTERPRISE compaq
        VARIABLES  { hostName,
                     scellNameDateTime,
                     agentEventCode,
                     agentEventDescription }
        DESCRIPTION
             "Update controller Failed"
           --#TYPE      "Management Agent Event 8062"
           --#SUMMARY   "Host %s : SCellName-TimeDate %s : EventCode %d : Description %s"
           --#ARGUMENTS {0,1,2,3,}
            --#SEVERITY  MINOR
            --#TIMEINDEX 136
        ::= 136008062

   mngmtAgentTrap-8063 TRAP-TYPE
        ENTERPRISE compaq
        VARIABLES  { hostName,
                     scellNameDateTime,
                     agentEventCode,
                     agentEventDescription }
        DESCRIPTION
             "Create Host Failed"
           --#TYPE      "Management Agent Event 8063"
           --#SUMMARY   "Host %s : SCellName-TimeDate %s : EventCode %d : Description %s"
           --#ARGUMENTS {0,1,2,3,}
            --#SEVERITY  MINOR
            --#TIMEINDEX 136
        ::= 136008063

   mngmtAgentTrap-8064 TRAP-TYPE
        ENTERPRISE compaq
        VARIABLES  { hostName,
                     scellNameDateTime,
                     agentEventCode,
                     agentEventDescription }
        DESCRIPTION
             "Discard Host Failed"
           --#TYPE      "Management Agent Event 8064"
           --#SUMMARY   "Host %s : SCellName-TimeDate %s : EventCode %d : Description %s"
           --#ARGUMENTS {0,1,2,3,}
            --#SEVERITY  MINOR
            --#TIMEINDEX 136
        ::= 136008064

   mngmtAgentTrap-8065 TRAP-TYPE
        ENTERPRISE compaq
        VARIABLES  { hostName,
                     scellNameDateTime,
                     agentEventCode,
                     agentEventDescription }
        DESCRIPTION
             "Get Host Failed"
           --#TYPE      "Management Agent Event 8065"
           --#SUMMARY   "Host %s : SCellName-TimeDate %s : EventCode %d : Description %s"
           --#ARGUMENTS {0,1,2,3,}
            --#SEVERITY  MINOR
            --#TIMEINDEX 136
        ::= 136008065

   mngmtAgentTrap-8066 TRAP-TYPE
        ENTERPRISE compaq
        VARIABLES  { hostName,
                     scellNameDateTime,
                     agentEventCode,
                     agentEventDescription }
        DESCRIPTION
             "Get Host List Failed"
           --#TYPE      "Management Agent Event 8066"
           --#SUMMARY   "Host %s : SCellName-TimeDate %s : EventCode %d : Description %s"
           --#ARGUMENTS {0,1,2,3,}
            --#SEVERITY  MINOR
            --#TIMEINDEX 136
        ::= 136008066

   mngmtAgentTrap-8067 TRAP-TYPE
        ENTERPRISE compaq
        VARIABLES  { hostName,
                     scellNameDateTime,
                     agentEventCode,
                     agentEventDescription }
        DESCRIPTION
             "Get Host Count Failed"
           --#TYPE      "Management Agent Event 8067"
           --#SUMMARY   "Host %s : SCellName-TimeDate %s : EventCode %d : Description %s"
           --#ARGUMENTS {0,1,2,3,}
            --#SEVERITY  MINOR
            --#TIMEINDEX 136
        ::= 136008067

   mngmtAgentTrap-8068 TRAP-TYPE
        ENTERPRISE compaq
        VARIABLES  { hostName,
                     scellNameDateTime,
                     agentEventCode,
                     agentEventDescription }
        DESCRIPTION
             "Get Presented Unit List Failed"
           --#TYPE      "Management Agent Event 8068"
           --#SUMMARY   "Host %s : SCellName-TimeDate %s : EventCode %d : Description %s"
           --#ARGUMENTS {0,1,2,3,}
            --#SEVERITY  MINOR
            --#TIMEINDEX 136
        ::= 136008068

   mngmtAgentTrap-8069 TRAP-TYPE
        ENTERPRISE compaq
        VARIABLES  { hostName,
                     scellNameDateTime,
                     agentEventCode,
                     agentEventDescription }
        DESCRIPTION
             "Get Presented Unit Count Failed"
           --#TYPE      "Management Agent Event 8069"
           --#SUMMARY   "Host %s : SCellName-TimeDate %s : EventCode %d : Description %s"
           --#ARGUMENTS {0,1,2,3,}
            --#SEVERITY  MINOR
            --#TIMEINDEX 136
        ::= 136008069

   mngmtAgentTrap-8070 TRAP-TYPE
        ENTERPRISE compaq
        VARIABLES  { hostName,
                     scellNameDateTime,
                     agentEventCode,
                     agentEventDescription }
        DESCRIPTION
             "Free View Failed"
           --#TYPE      "Management Agent Event 8070"
           --#SUMMARY   "Host %s : SCellName-TimeDate %s : EventCode %d : Description %s"
           --#ARGUMENTS {0,1,2,3,}
            --#SEVERITY  MINOR
            --#TIMEINDEX 136
        ::= 136008070

   mngmtAgentTrap-8071 TRAP-TYPE
        ENTERPRISE compaq
        VARIABLES  { hostName,
                     scellNameDateTime,
                     agentEventCode,
                     agentEventDescription }
        DESCRIPTION
             "Storage system shutdown Failed"
           --#TYPE      "Management Agent Event 8071"
           --#SUMMARY   "Host %s : SCellName-TimeDate %s : EventCode %d : Description %s"
           --#ARGUMENTS {0,1,2,3,}
            --#SEVERITY  MINOR
            --#TIMEINDEX 136
        ::= 136008071

   mngmtAgentTrap-8073 TRAP-TYPE
        ENTERPRISE compaq
        VARIABLES  { hostName,
                     scellNameDateTime,
                     agentEventCode,
                     agentEventDescription }
        DESCRIPTION
             "Get Derived Unit List Failed"
           --#TYPE      "Management Agent Event 8073"
           --#SUMMARY   "Host %s : SCellName-TimeDate %s : EventCode %d : Description %s"
           --#ARGUMENTS {0,1,2,3,}
            --#SEVERITY  MINOR
            --#TIMEINDEX 136
        ::= 136008073

   mngmtAgentTrap-8074 TRAP-TYPE
        ENTERPRISE compaq
        VARIABLES  { hostName,
                     scellNameDateTime,
                     agentEventCode,
                     agentEventDescription }
        DESCRIPTION
             "Get Derived Unit Count Failed"
           --#TYPE      "Management Agent Event 8074"
           --#SUMMARY   "Host %s : SCellName-TimeDate %s : EventCode %d : Description %s"
           --#ARGUMENTS {0,1,2,3,}
            --#SEVERITY  MINOR
            --#TIMEINDEX 136
        ::= 136008074

   mngmtAgentTrap-8075 TRAP-TYPE
        ENTERPRISE compaq
        VARIABLES  { hostName,
                     scellNameDateTime,
                     agentEventCode,
                     agentEventDescription }
        DESCRIPTION
             "Get Vdisk list failed"
           --#TYPE      "Management Agent Event 8075"
           --#SUMMARY   "Host %s : SCellName-TimeDate %s : EventCode %d : Description %s"
           --#ARGUMENTS {0,1,2,3,}
            --#SEVERITY  MINOR
            --#TIMEINDEX 136
        ::= 136008075

   mngmtAgentTrap-8076 TRAP-TYPE
        ENTERPRISE compaq
        VARIABLES  { hostName,
                     scellNameDateTime,
                     agentEventCode,
                     agentEventDescription }
        DESCRIPTION
             "Get Vdisk count failed"
           --#TYPE      "Management Agent Event 8076"
           --#SUMMARY   "Host %s : SCellName-TimeDate %s : EventCode %d : Description %s"
           --#ARGUMENTS {0,1,2,3,}
            --#SEVERITY  MINOR
            --#TIMEINDEX 136
        ::= 136008076

   mngmtAgentTrap-8077 TRAP-TYPE
        ENTERPRISE compaq
        VARIABLES  { hostName,
                     scellNameDateTime,
                     agentEventCode,
                     agentEventDescription }
        DESCRIPTION
             "Error while building Virtual Disk view. Please check management event logs for details. Refreshing the properties of the array might help clear the condition."
           --#TYPE      "Management Agent Event 8077"
           --#SUMMARY   "Host %s : SCellName-TimeDate %s : EventCode %d : Description %s"
           --#ARGUMENTS {0,1,2,3,}
            --#SEVERITY  MINOR
            --#TIMEINDEX 136
        ::= 136008077

   mngmtAgentTrap-8078 TRAP-TYPE
        ENTERPRISE compaq
        VARIABLES  { hostName,
                     scellNameDateTime,
                     agentEventCode,
                     agentEventDescription }
        DESCRIPTION
             "Error while building Host view. Please check management event logs for details. Refreshing the properties of the array might help clear the condition."
           --#TYPE      "Management Agent Event 8078"
           --#SUMMARY   "Host %s : SCellName-TimeDate %s : EventCode %d : Description %s"
           --#ARGUMENTS {0,1,2,3,}
            --#SEVERITY  MINOR
            --#TIMEINDEX 136
        ::= 136008078

   mngmtAgentTrap-8079 TRAP-TYPE
        ENTERPRISE compaq
        VARIABLES  { hostName,
                     scellNameDateTime,
                     agentEventCode,
                     agentEventDescription }
        DESCRIPTION
             "Error while building Disk Group view. Please check management event logs for details. Refreshing the properties of the array might help clear the condition."
           --#TYPE      "Management Agent Event 8079"
           --#SUMMARY   "Host %s : SCellName-TimeDate %s : EventCode %d : Description %s"
           --#ARGUMENTS {0,1,2,3,}
            --#SEVERITY  MINOR
            --#TIMEINDEX 136
        ::= 136008079

   mngmtAgentTrap-8080 TRAP-TYPE
        ENTERPRISE compaq
        VARIABLES  { hostName,
                     scellNameDateTime,
                     agentEventCode,
                     agentEventDescription }
        DESCRIPTION
             "Error while building Hardware view. Please check management event logs for details. Refreshing the properties of the array might help clear the condition."
           --#TYPE      "Management Agent Event 8080"
           --#SUMMARY   "Host %s : SCellName-TimeDate %s : EventCode %d : Description %s"
           --#ARGUMENTS {0,1,2,3,}
            --#SEVERITY  MINOR
            --#TIMEINDEX 136
        ::= 136008080

   mngmtAgentTrap-8081 TRAP-TYPE
        ENTERPRISE compaq
        VARIABLES  { hostName,
                     scellNameDateTime,
                     agentEventCode,
                     agentEventDescription }
        DESCRIPTION
             "Specified time format is incorrect"
           --#TYPE      "Management Agent Event 8081"
           --#SUMMARY   "Host %s : SCellName-TimeDate %s : EventCode %d : Description %s"
           --#ARGUMENTS {0,1,2,3,}
            --#SEVERITY  MINOR
            --#TIMEINDEX 136
        ::= 136008081

   mngmtAgentTrap-8082 TRAP-TYPE
        ENTERPRISE compaq
        VARIABLES  { hostName,
                     scellNameDateTime,
                     agentEventCode,
                     agentEventDescription }
        DESCRIPTION
             "Error creating/opening time synchronization file."
           --#TYPE      "Management Agent Event 8082"
           --#SUMMARY   "Host %s : SCellName-TimeDate %s : EventCode %d : Description %s"
           --#ARGUMENTS {0,1,2,3,}
            --#SEVERITY  MINOR
            --#TIMEINDEX 136
        ::= 136008082

   mngmtAgentTrap-8083 TRAP-TYPE
        ENTERPRISE compaq
        VARIABLES  { hostName,
                     scellNameDateTime,
                     agentEventCode,
                     agentEventDescription }
        DESCRIPTION
             "NSCList reordered."
           --#TYPE      "Management Agent Event 8083"
           --#SUMMARY   "Host %s : SCellName-TimeDate %s : EventCode %d : Description %s"
           --#ARGUMENTS {0,1,2,3,}
            --#SEVERITY  MINOR
            --#TIMEINDEX 136
        ::= 136008083

   mngmtAgentTrap-8084 TRAP-TYPE
        ENTERPRISE compaq
        VARIABLES  { hostName,
                     scellNameDateTime,
                     agentEventCode,
                     agentEventDescription }
        DESCRIPTION
             "NscList mutex Get error"
           --#TYPE      "Management Agent Event 8084"
           --#SUMMARY   "Host %s : SCellName-TimeDate %s : EventCode %d : Description %s"
           --#ARGUMENTS {0,1,2,3,}
            --#SEVERITY  MINOR
            --#TIMEINDEX 136
        ::= 136008084

   mngmtAgentTrap-8085 TRAP-TYPE
        ENTERPRISE compaq
        VARIABLES  { hostName,
                     scellNameDateTime,
                     agentEventCode,
                     agentEventDescription }
        DESCRIPTION
             "Storage System is managed by another agent"
           --#TYPE      "Management Agent Event 8085"
           --#SUMMARY   "Host %s : SCellName-TimeDate %s : EventCode %d : Description %s"
           --#ARGUMENTS {0,1,2,3,}
            --#SEVERITY  INFORMATIONAL
            --#TIMEINDEX 136
        ::= 136008085

   mngmtAgentTrap-8086 TRAP-TYPE
        ENTERPRISE compaq
        VARIABLES  { hostName,
                     scellNameDateTime,
                     agentEventCode,
                     agentEventDescription }
        DESCRIPTION
             "Memory allocation failure"
           --#TYPE      "Management Agent Event 8086"
           --#SUMMARY   "Host %s : SCellName-TimeDate %s : EventCode %d : Description %s"
           --#ARGUMENTS {0,1,2,3,}
            --#SEVERITY  INFORMATIONAL
            --#TIMEINDEX 136
        ::= 136008086

   mngmtAgentTrap-8087 TRAP-TYPE
        ENTERPRISE compaq
        VARIABLES  { hostName,
                     scellNameDateTime,
                     agentEventCode,
                     agentEventDescription }
        DESCRIPTION
             "Failed to obtain list of DR Groups"
           --#TYPE      "Management Agent Event 8087"
           --#SUMMARY   "Host %s : SCellName-TimeDate %s : EventCode %d : Description %s"
           --#ARGUMENTS {0,1,2,3,}
            --#SEVERITY  INFORMATIONAL
            --#TIMEINDEX 136
        ::= 136008087

   mngmtAgentTrap-8088 TRAP-TYPE
        ENTERPRISE compaq
        VARIABLES  { hostName,
                     scellNameDateTime,
                     agentEventCode,
                     agentEventDescription }
        DESCRIPTION
             "Failed to obtain count of DR Groups"
           --#TYPE      "Management Agent Event 8088"
           --#SUMMARY   "Host %s : SCellName-TimeDate %s : EventCode %d : Description %s"
           --#ARGUMENTS {0,1,2,3,}
            --#SEVERITY  INFORMATIONAL
            --#TIMEINDEX 136
        ::= 136008088

   mngmtAgentTrap-8089 TRAP-TYPE
        ENTERPRISE compaq
        VARIABLES  { hostName,
                     scellNameDateTime,
                     agentEventCode,
                     agentEventDescription }
        DESCRIPTION
             "Failed to build Data Replication view. Please check management event logs for details. Refreshing the properties of the array might help clear the condition."
           --#TYPE      "Management Agent Event 8089"
           --#SUMMARY   "Host %s : SCellName-TimeDate %s : EventCode %d : Description %s"
           --#ARGUMENTS {0,1,2,3,}
            --#SEVERITY  INFORMATIONAL
            --#TIMEINDEX 136
        ::= 136008089

   mngmtAgentTrap-8090 TRAP-TYPE
        ENTERPRISE compaq
        VARIABLES  { hostName,
                     scellNameDateTime,
                     agentEventCode,
                     agentEventDescription }
        DESCRIPTION
             "No Devices found on Controller Back End Loops"
           --#TYPE      "Management Agent Event 8090"
           --#SUMMARY   "Host %s : SCellName-TimeDate %s : EventCode %d : Description %s"
           --#ARGUMENTS {0,1,2,3,}
            --#SEVERITY  MINOR
            --#TIMEINDEX 136
        ::= 136008090

   mngmtAgentTrap-8091 TRAP-TYPE
        ENTERPRISE compaq
        VARIABLES  { hostName,
                     scellNameDateTime,
                     agentEventCode,
                     agentEventDescription }
        DESCRIPTION
             "The DR Group cannot have Virtual Disks drawn from Disk Groups of different drive types."
           --#TYPE      "Management Agent Event 8091"
           --#SUMMARY   "Host %s : SCellName-TimeDate %s : EventCode %d : Description %s"
           --#ARGUMENTS {0,1,2,3,}
            --#SEVERITY  MINOR
            --#TIMEINDEX 136
        ::= 136008091

   mngmtAgentTrap-8092 TRAP-TYPE
        ENTERPRISE compaq
        VARIABLES  { hostName,
                     scellNameDateTime,
                     agentEventCode,
                     agentEventDescription }
        DESCRIPTION
             "The storage array name has changed from '{1}' to '{2}'"
           --#TYPE      "Management Agent Event 8092"
           --#SUMMARY   "Host %s : SCellName-TimeDate %s : EventCode %d : Description %s"
           --#ARGUMENTS {0,1,2,3,}
            --#SEVERITY  INFORMATIONAL
            --#TIMEINDEX 136
        ::= 136008092

   mngmtAgentTrap-8093 TRAP-TYPE
        ENTERPRISE compaq
        VARIABLES  { hostName,
                     scellNameDateTime,
                     agentEventCode,
                     agentEventDescription }
        DESCRIPTION
             "A new storage array has been discovered."
           --#TYPE      "Management Agent Event 8093"
           --#SUMMARY   "Host %s : SCellName-TimeDate %s : EventCode %d : Description %s"
           --#ARGUMENTS {0,1,2,3,}
            --#SEVERITY  INFORMATIONAL
            --#TIMEINDEX 136
        ::= 136008093

   mngmtAgentTrap-8094 TRAP-TYPE
        ENTERPRISE compaq
        VARIABLES  { hostName,
                     scellNameDateTime,
                     agentEventCode,
                     agentEventDescription }
        DESCRIPTION
             "The storage cell was uninitialized."
           --#TYPE      "Management Agent Event 8094"
           --#SUMMARY   "Host %s : SCellName-TimeDate %s : EventCode %d : Description %s"
           --#ARGUMENTS {0,1,2,3,}
            --#SEVERITY  INFORMATIONAL
            --#TIMEINDEX 136
        ::= 136008094

   mngmtAgentTrap-8095 TRAP-TYPE
        ENTERPRISE compaq
        VARIABLES  { hostName,
                     scellNameDateTime,
                     agentEventCode,
                     agentEventDescription }
        DESCRIPTION
             "The storage cell was initialized."
           --#TYPE      "Management Agent Event 8095"
           --#SUMMARY   "Host %s : SCellName-TimeDate %s : EventCode %d : Description %s"
           --#ARGUMENTS {0,1,2,3,}
            --#SEVERITY  INFORMATIONAL
            --#TIMEINDEX 136
        ::= 136008095

   mngmtAgentTrap-8096 TRAP-TYPE
        ENTERPRISE compaq
        VARIABLES  { hostName,
                     scellNameDateTime,
                     agentEventCode,
                     agentEventDescription }
        DESCRIPTION
             "Storage system directory create error"
           --#TYPE      "Management Agent Event 8096"
           --#SUMMARY   "Host %s : SCellName-TimeDate %s : EventCode %d : Description %s"
           --#ARGUMENTS {0,1,2,3,}
            --#SEVERITY  MINOR
            --#TIMEINDEX 136
        ::= 136008096

   mngmtAgentTrap-8097 TRAP-TYPE
        ENTERPRISE compaq
        VARIABLES  { hostName,
                     scellNameDateTime,
                     agentEventCode,
                     agentEventDescription }
        DESCRIPTION
             "The storage cell is now being managed by this instance of HP P6000 Command View"
           --#TYPE      "Management Agent Event 8097"
           --#SUMMARY   "Host %s : SCellName-TimeDate %s : EventCode %d : Description %s"
           --#ARGUMENTS {0,1,2,3,}
            --#SEVERITY  INFORMATIONAL
            --#TIMEINDEX 136
        ::= 136008097

   mngmtAgentTrap-8098 TRAP-TYPE
        ENTERPRISE compaq
        VARIABLES  { hostName,
                     scellNameDateTime,
                     agentEventCode,
                     agentEventDescription }
        DESCRIPTION
             "This instance of HP P6000 Command View is no longer managing the storage cell"
           --#TYPE      "Management Agent Event 8098"
           --#SUMMARY   "Host %s : SCellName-TimeDate %s : EventCode %d : Description %s"
           --#ARGUMENTS {0,1,2,3,}
            --#SEVERITY  INFORMATIONAL
            --#TIMEINDEX 136
        ::= 136008098

   mngmtAgentTrap-8099 TRAP-TYPE
        ENTERPRISE compaq
        VARIABLES  { hostName,
                     scellNameDateTime,
                     agentEventCode,
                     agentEventDescription }
        DESCRIPTION
             "This instance of HP P6000 Command View has lost communication with the storage cell"
           --#TYPE      "Management Agent Event 8099"
           --#SUMMARY   "Host %s : SCellName-TimeDate %s : EventCode %d : Description %s"
           --#ARGUMENTS {0,1,2,3,}
            --#SEVERITY  MINOR
            --#TIMEINDEX 136
        ::= 136008099

   mngmtAgentTrap-8100 TRAP-TYPE
        ENTERPRISE compaq
        VARIABLES  { hostName,
                     scellNameDateTime,
                     agentEventCode,
                     agentEventDescription }
        DESCRIPTION
             "This instance of HP P6000 Command View has no path to the master controller"
           --#TYPE      "Management Agent Event 8100"
           --#SUMMARY   "Host %s : SCellName-TimeDate %s : EventCode %d : Description %s"
           --#ARGUMENTS {0,1,2,3,}
            --#SEVERITY  MINOR
            --#TIMEINDEX 136
        ::= 136008100

   mngmtAgentTrap-8104 TRAP-TYPE
        ENTERPRISE compaq
        VARIABLES  { hostName,
                     scellNameDateTime,
                     agentEventCode,
                     agentEventDescription }
        DESCRIPTION
             "Your disk drive is in the process of powering off and on again. While it is performing these actions, it will not be visible to your management server. This process may take a number of minutes to complete, at which time your disk drive will again become visible and manageable. You may continue to manage other resources within your storage system while the process completes in the background."
           --#TYPE      "Management Agent Event 8104"
           --#SUMMARY   "Host %s : SCellName-TimeDate %s : EventCode %d : Description %s"
           --#ARGUMENTS {0,1,2,3,}
            --#SEVERITY  INFORMATIONAL
            --#TIMEINDEX 136
        ::= 136008104

   mngmtAgentTrap-8106 TRAP-TYPE
        ENTERPRISE compaq
        VARIABLES  { hostName,
                     scellNameDateTime,
                     agentEventCode,
                     agentEventDescription }
        DESCRIPTION
             "The array may be equipped with more hard drive capacity than could be utilized in an all RAID-0 configuration."
           --#TYPE      "Management Agent Event 8106"
           --#SUMMARY   "Host %s : SCellName-TimeDate %s : EventCode %d : Description %s"
           --#ARGUMENTS {0,1,2,3,}
            --#SEVERITY  INFORMATIONAL
            --#TIMEINDEX 136
        ::= 136008106

   mngmtAgentTrap-8107 TRAP-TYPE
        ENTERPRISE compaq
        VARIABLES  { hostName,
                     scellNameDateTime,
                     agentEventCode,
                     agentEventDescription }
        DESCRIPTION
             "The array may be equipped with more hard drive capacity than could be utilized in an all RAID-1 configuration."
           --#TYPE      "Management Agent Event 8107"
           --#SUMMARY   "Host %s : SCellName-TimeDate %s : EventCode %d : Description %s"
           --#ARGUMENTS {0,1,2,3,}
            --#SEVERITY  INFORMATIONAL
            --#TIMEINDEX 136
        ::= 136008107

   mngmtAgentTrap-8108 TRAP-TYPE
        ENTERPRISE compaq
        VARIABLES  { hostName,
                     scellNameDateTime,
                     agentEventCode,
                     agentEventDescription }
        DESCRIPTION
             "The array may be equipped with more hard drive capacity than could be utilized in an all RAID-5 configuration."
           --#TYPE      "Management Agent Event 8108"
           --#SUMMARY   "Host %s : SCellName-TimeDate %s : EventCode %d : Description %s"
           --#ARGUMENTS {0,1,2,3,}
            --#SEVERITY  INFORMATIONAL
            --#TIMEINDEX 136
        ::= 136008108

   mngmtAgentTrap-8109 TRAP-TYPE
        ENTERPRISE compaq
        VARIABLES  { hostName,
                     scellNameDateTime,
                     agentEventCode,
                     agentEventDescription }
        DESCRIPTION
             "The array may be equipped with more hard drive capacity than could be utilized in an all RAID-6 configuration."
           --#TYPE      "Management Agent Event 8109"
           --#SUMMARY   "Host %s : SCellName-TimeDate %s : EventCode %d : Description %s"
           --#ARGUMENTS {0,1,2,3,}
            --#SEVERITY  INFORMATIONAL
            --#TIMEINDEX 136
        ::= 136008109

   mngmtAgentTrap-9001 TRAP-TYPE
        ENTERPRISE compaq
        VARIABLES  { hostName,
                     scellNameDateTime,
                     agentEventCode,
                     agentEventDescription }
        DESCRIPTION
             "Vdisk File Open Error"
           --#TYPE      "Management Agent Event 9001"
           --#SUMMARY   "Host %s : SCellName-TimeDate %s : EventCode %d : Description %s"
           --#ARGUMENTS {0,1,2,3,}
            --#SEVERITY  MINOR
            --#TIMEINDEX 136
        ::= 136009001

   mngmtAgentTrap-9002 TRAP-TYPE
        ENTERPRISE compaq
        VARIABLES  { hostName,
                     scellNameDateTime,
                     agentEventCode,
                     agentEventDescription }
        DESCRIPTION
             "Vdisk File Write Error"
           --#TYPE      "Management Agent Event 9002"
           --#SUMMARY   "Host %s : SCellName-TimeDate %s : EventCode %d : Description %s"
           --#ARGUMENTS {0,1,2,3,}
            --#SEVERITY  MINOR
            --#TIMEINDEX 136
        ::= 136009002

   mngmtAgentTrap-9003 TRAP-TYPE
        ENTERPRISE compaq
        VARIABLES  { hostName,
                     scellNameDateTime,
                     agentEventCode,
                     agentEventDescription }
        DESCRIPTION
             "Vdisk File Read Error"
           --#TYPE      "Management Agent Event 9003"
           --#SUMMARY   "Host %s : SCellName-TimeDate %s : EventCode %d : Description %s"
           --#ARGUMENTS {0,1,2,3,}
            --#SEVERITY  MINOR
            --#TIMEINDEX 136
        ::= 136009003

   mngmtAgentTrap-9004 TRAP-TYPE
        ENTERPRISE compaq
        VARIABLES  { hostName,
                     scellNameDateTime,
                     agentEventCode,
                     agentEventDescription }
        DESCRIPTION
             "Vdisk name too long"
           --#TYPE      "Management Agent Event 9004"
           --#SUMMARY   "Host %s : SCellName-TimeDate %s : EventCode %d : Description %s"
           --#ARGUMENTS {0,1,2,3,}
            --#SEVERITY  INFORMATIONAL
            --#TIMEINDEX 136
        ::= 136009004

   mngmtAgentTrap-9005 TRAP-TYPE
        ENTERPRISE compaq
        VARIABLES  { hostName,
                     scellNameDateTime,
                     agentEventCode,
                     agentEventDescription }
        DESCRIPTION
             "Vdisk No String Error"
           --#TYPE      "Management Agent Event 9005"
           --#SUMMARY   "Host %s : SCellName-TimeDate %s : EventCode %d : Description %s"
           --#ARGUMENTS {0,1,2,3,}
            --#SEVERITY  INFORMATIONAL
            --#TIMEINDEX 136
        ::= 136009005

   mngmtAgentTrap-9006 TRAP-TYPE
        ENTERPRISE compaq
        VARIABLES  { hostName,
                     scellNameDateTime,
                     agentEventCode,
                     agentEventDescription }
        DESCRIPTION
             "Vdisk No Object Error"
           --#TYPE      "Management Agent Event 9006"
           --#SUMMARY   "Host %s : SCellName-TimeDate %s : EventCode %d : Description %s"
           --#ARGUMENTS {0,1,2,3,}
            --#SEVERITY  INFORMATIONAL
            --#TIMEINDEX 136
        ::= 136009006

   mngmtAgentTrap-9007 TRAP-TYPE
        ENTERPRISE compaq
        VARIABLES  { hostName,
                     scellNameDateTime,
                     agentEventCode,
                     agentEventDescription }
        DESCRIPTION
             "Vdisk still exists"
           --#TYPE      "Management Agent Event 9007"
           --#SUMMARY   "Host %s : SCellName-TimeDate %s : EventCode %d : Description %s"
           --#ARGUMENTS {0,1,2,3,}
            --#SEVERITY  INFORMATIONAL
            --#TIMEINDEX 136
        ::= 136009007

   mngmtAgentTrap-9008 TRAP-TYPE
        ENTERPRISE compaq
        VARIABLES  { hostName,
                     scellNameDateTime,
                     agentEventCode,
                     agentEventDescription }
        DESCRIPTION
             "Vdisk Invalid Value"
           --#TYPE      "Management Agent Event 9008"
           --#SUMMARY   "Host %s : SCellName-TimeDate %s : EventCode %d : Description %s"
           --#ARGUMENTS {0,1,2,3,}
            --#SEVERITY  INFORMATIONAL
            --#TIMEINDEX 136
        ::= 136009008

   mngmtAgentTrap-9009 TRAP-TYPE
        ENTERPRISE compaq
        VARIABLES  { hostName,
                     scellNameDateTime,
                     agentEventCode,
                     agentEventDescription }
        DESCRIPTION
             "An outstanding command is still in progress"
           --#TYPE      "Management Agent Event 9009"
           --#SUMMARY   "Host %s : SCellName-TimeDate %s : EventCode %d : Description %s"
           --#ARGUMENTS {0,1,2,3,}
            --#SEVERITY  INFORMATIONAL
            --#TIMEINDEX 136
        ::= 136009009

   mngmtAgentTrap-9010 TRAP-TYPE
        ENTERPRISE compaq
        VARIABLES  { hostName,
                     scellNameDateTime,
                     agentEventCode,
                     agentEventDescription }
        DESCRIPTION
             "Requested Vdisk size exceeds the available size"
           --#TYPE      "Management Agent Event 9010"
           --#SUMMARY   "Host %s : SCellName-TimeDate %s : EventCode %d : Description %s"
           --#ARGUMENTS {0,1,2,3,}
            --#SEVERITY  INFORMATIONAL
            --#TIMEINDEX 136
        ::= 136009010

   mngmtAgentTrap-9011 TRAP-TYPE
        ENTERPRISE compaq
        VARIABLES  { hostName,
                     scellNameDateTime,
                     agentEventCode,
                     agentEventDescription }
        DESCRIPTION
             "Vdisk size may be expanded but not reduced on this array"
           --#TYPE      "Management Agent Event 9011"
           --#SUMMARY   "Host %s : SCellName-TimeDate %s : EventCode %d : Description %s"
           --#ARGUMENTS {0,1,2,3,}
            --#SEVERITY  INFORMATIONAL
            --#TIMEINDEX 136
        ::= 136009011

   mngmtAgentTrap-9012 TRAP-TYPE
        ENTERPRISE compaq
        VARIABLES  { hostName,
                     scellNameDateTime,
                     agentEventCode,
                     agentEventDescription }
        DESCRIPTION
             "Deletion completed"
           --#TYPE      "Management Agent Event 9012"
           --#SUMMARY   "Host %s : SCellName-TimeDate %s : EventCode %d : Description %s"
           --#ARGUMENTS {0,1,2,3,}
            --#SEVERITY  INFORMATIONAL
            --#TIMEINDEX 136
        ::= 136009012

   mngmtAgentTrap-9013 TRAP-TYPE
        ENTERPRISE compaq
        VARIABLES  { hostName,
                     scellNameDateTime,
                     agentEventCode,
                     agentEventDescription }
        DESCRIPTION
             "Creation completed"
           --#TYPE      "Management Agent Event 9013"
           --#SUMMARY   "Host %s : SCellName-TimeDate %s : EventCode %d : Description %s"
           --#ARGUMENTS {0,1,2,3,}
            --#SEVERITY  INFORMATIONAL
            --#TIMEINDEX 136
        ::= 136009013

   mngmtAgentTrap-9014 TRAP-TYPE
        ENTERPRISE compaq
        VARIABLES  { hostName,
                     scellNameDateTime,
                     agentEventCode,
                     agentEventDescription }
        DESCRIPTION
             "Size expansion completed"
           --#TYPE      "Management Agent Event 9014"
           --#SUMMARY   "Host %s : SCellName-TimeDate %s : EventCode %d : Description %s"
           --#ARGUMENTS {0,1,2,3,}
            --#SEVERITY  INFORMATIONAL
            --#TIMEINDEX 136
        ::= 136009014

   mngmtAgentTrap-9015 TRAP-TYPE
        ENTERPRISE compaq
        VARIABLES  { hostName,
                     scellNameDateTime,
                     agentEventCode,
                     agentEventDescription }
        DESCRIPTION
             "Vdisk cache data lost error"
           --#TYPE      "Management Agent Event 9015"
           --#SUMMARY   "Host %s : SCellName-TimeDate %s : EventCode %d : Description %s"
           --#ARGUMENTS {0,1,2,3,}
            --#SEVERITY  INFORMATIONAL
            --#TIMEINDEX 136
        ::= 136009015

   mngmtAgentTrap-9016 TRAP-TYPE
        ENTERPRISE compaq
        VARIABLES  { hostName,
                     scellNameDateTime,
                     agentEventCode,
                     agentEventDescription }
        DESCRIPTION
             "Vdisk data lost error resolved"
           --#TYPE      "Management Agent Event 9016"
           --#SUMMARY   "Host %s : SCellName-TimeDate %s : EventCode %d : Description %s"
           --#ARGUMENTS {0,1,2,3,}
            --#SEVERITY  INFORMATIONAL
            --#TIMEINDEX 136
        ::= 136009016

   mngmtAgentTrap-9017 TRAP-TYPE
        ENTERPRISE compaq
        VARIABLES  { hostName,
                     scellNameDateTime,
                     agentEventCode,
                     agentEventDescription }
        DESCRIPTION
             "Operation rejected - The Vdisk has a sharing relationship with another object"
           --#TYPE      "Management Agent Event 9017"
           --#SUMMARY   "Host %s : SCellName-TimeDate %s : EventCode %d : Description %s"
           --#ARGUMENTS {0,1,2,3,}
            --#SEVERITY  INFORMATIONAL
            --#TIMEINDEX 136
        ::= 136009017

   mngmtAgentTrap-9018 TRAP-TYPE
        ENTERPRISE compaq
        VARIABLES  { hostName,
                     scellNameDateTime,
                     agentEventCode,
                     agentEventDescription }
        DESCRIPTION
             "Operation on this Vdisk was rejected due to its degraded condition"
           --#TYPE      "Management Agent Event 9018"
           --#SUMMARY   "Host %s : SCellName-TimeDate %s : EventCode %d : Description %s"
           --#ARGUMENTS {0,1,2,3,}
            --#SEVERITY  INFORMATIONAL
            --#TIMEINDEX 136
        ::= 136009018

   mngmtAgentTrap-9019 TRAP-TYPE
        ENTERPRISE compaq
        VARIABLES  { hostName,
                     scellNameDateTime,
                     agentEventCode,
                     agentEventDescription }
        DESCRIPTION
             "Operation on this Vdisk can only be performed if it is presented to a host"
           --#TYPE      "Management Agent Event 9019"
           --#SUMMARY   "Host %s : SCellName-TimeDate %s : EventCode %d : Description %s"
           --#ARGUMENTS {0,1,2,3,}
            --#SEVERITY  INFORMATIONAL
            --#TIMEINDEX 136
        ::= 136009019

   mngmtAgentTrap-9020 TRAP-TYPE
        ENTERPRISE compaq
        VARIABLES  { hostName,
                     scellNameDateTime,
                     agentEventCode,
                     agentEventDescription }
        DESCRIPTION
             "Cache policies cannot be modified if Vdisk is presented to a host"
           --#TYPE      "Management Agent Event 9020"
           --#SUMMARY   "Host %s : SCellName-TimeDate %s : EventCode %d : Description %s"
           --#ARGUMENTS {0,1,2,3,}
            --#SEVERITY  INFORMATIONAL
            --#TIMEINDEX 136
        ::= 136009020

   mngmtAgentTrap-9021 TRAP-TYPE
        ENTERPRISE compaq
        VARIABLES  { hostName,
                     scellNameDateTime,
                     agentEventCode,
                     agentEventDescription }
        DESCRIPTION
             "Allowed property changes successful. (Cache policy changes not allowed while Vdisk is presented to a host.)"
           --#TYPE      "Management Agent Event 9021"
           --#SUMMARY   "Host %s : SCellName-TimeDate %s : EventCode %d : Description %s"
           --#ARGUMENTS {0,1,2,3,}
            --#SEVERITY  INFORMATIONAL
            --#TIMEINDEX 136
        ::= 136009021

   mngmtAgentTrap-9022 TRAP-TYPE
        ENTERPRISE compaq
        VARIABLES  { hostName,
                     scellNameDateTime,
                     agentEventCode,
                     agentEventDescription }
        DESCRIPTION
             "Requested redundancy type cannot be implemented with the current disk group condition."
           --#TYPE      "Management Agent Event 9022"
           --#SUMMARY   "Host %s : SCellName-TimeDate %s : EventCode %d : Description %s"
           --#ARGUMENTS {0,1,2,3,}
            --#SEVERITY  INFORMATIONAL
            --#TIMEINDEX 136
        ::= 136009022

   mngmtAgentTrap-9023 TRAP-TYPE
        ENTERPRISE compaq
        VARIABLES  { hostName,
                     scellNameDateTime,
                     agentEventCode,
                     agentEventDescription }
        DESCRIPTION
             "Your Vdisk was created but cannot be presented at this time. It can be presented when it is fully allocated."
           --#TYPE      "Management Agent Event 9023"
           --#SUMMARY   "Host %s : SCellName-TimeDate %s : EventCode %d : Description %s"
           --#ARGUMENTS {0,1,2,3,}
            --#SEVERITY  INFORMATIONAL
            --#TIMEINDEX 136
        ::= 136009023

   mngmtAgentTrap-9025 TRAP-TYPE
        ENTERPRISE compaq
        VARIABLES  { hostName,
                     scellNameDateTime,
                     agentEventCode,
                     agentEventDescription }
        DESCRIPTION
             "Vdisk device data lost error. The Vdisk has failed because there is not enough space in its diskgroup to accommodate new or copied data."
           --#TYPE      "Management Agent Event 9025"
           --#SUMMARY   "Host %s : SCellName-TimeDate %s : EventCode %d : Description %s"
           --#ARGUMENTS {0,1,2,3,}
            --#SEVERITY  INFORMATIONAL
            --#TIMEINDEX 136
        ::= 136009025

   mngmtAgentTrap-9026 TRAP-TYPE
        ENTERPRISE compaq
        VARIABLES  { hostName,
                     scellNameDateTime,
                     agentEventCode,
                     agentEventDescription }
        DESCRIPTION
             "The first character of the World Wide LUN Name must be a 6."
           --#TYPE      "Management Agent Event 9026"
           --#SUMMARY   "Host %s : SCellName-TimeDate %s : EventCode %d : Description %s"
           --#ARGUMENTS {0,1,2,3,}
            --#SEVERITY  INFORMATIONAL
            --#TIMEINDEX 136
        ::= 136009026

   mngmtAgentTrap-9027 TRAP-TYPE
        ENTERPRISE compaq
        VARIABLES  { hostName,
                     scellNameDateTime,
                     agentEventCode,
                     agentEventDescription }
        DESCRIPTION
             "Virtual disk cache and inoperative data lost error"
           --#TYPE      "Management Agent Event 9027"
           --#SUMMARY   "Host %s : SCellName-TimeDate %s : EventCode %d : Description %s"
           --#ARGUMENTS {0,1,2,3,}
            --#SEVERITY  INFORMATIONAL
            --#TIMEINDEX 136
        ::= 136009027

   mngmtAgentTrap-9028 TRAP-TYPE
        ENTERPRISE compaq
        VARIABLES  { hostName,
                     scellNameDateTime,
                     agentEventCode,
                     agentEventDescription }
        DESCRIPTION
             "Virtual disk inoperative data lost error"
           --#TYPE      "Management Agent Event 9028"
           --#SUMMARY   "Host %s : SCellName-TimeDate %s : EventCode %d : Description %s"
           --#ARGUMENTS {0,1,2,3,}
            --#SEVERITY  INFORMATIONAL
            --#TIMEINDEX 136
        ::= 136009028

   mngmtAgentTrap-9029 TRAP-TYPE
        ENTERPRISE compaq
        VARIABLES  { hostName,
                     scellNameDateTime,
                     agentEventCode,
                     agentEventDescription }
        DESCRIPTION
             "Virtual disk condition failed because of an inoperative data lost error."
           --#TYPE      "Management Agent Event 9029"
           --#SUMMARY   "Host %s : SCellName-TimeDate %s : EventCode %d : Description %s"
           --#ARGUMENTS {0,1,2,3,}
            --#SEVERITY  INFORMATIONAL
            --#TIMEINDEX 136
        ::= 136009029

   mngmtAgentTrap-9030 TRAP-TYPE
        ENTERPRISE compaq
        VARIABLES  { hostName,
                     scellNameDateTime,
                     agentEventCode,
                     agentEventDescription }
        DESCRIPTION
             "The property requested cannot be changed on a snapshot."
           --#TYPE      "Management Agent Event 9030"
           --#SUMMARY   "Host %s : SCellName-TimeDate %s : EventCode %d : Description %s"
           --#ARGUMENTS {0,1,2,3,}
            --#SEVERITY  INFORMATIONAL
            --#TIMEINDEX 136
        ::= 136009030

   mngmtAgentTrap-9031 TRAP-TYPE
        ENTERPRISE compaq
        VARIABLES  { hostName,
                     scellNameDateTime,
                     agentEventCode,
                     agentEventDescription }
        DESCRIPTION
             "The World Wide LUN Name cannot be changed for a presented Vdisk Active member or snapshot."
           --#TYPE      "Management Agent Event 9031"
           --#SUMMARY   "Host %s : SCellName-TimeDate %s : EventCode %d : Description %s"
           --#ARGUMENTS {0,1,2,3,}
            --#SEVERITY  INFORMATIONAL
            --#TIMEINDEX 136
        ::= 136009031

   mngmtAgentTrap-9032 TRAP-TYPE
        ENTERPRISE compaq
        VARIABLES  { hostName,
                     scellNameDateTime,
                     agentEventCode,
                     agentEventDescription }
        DESCRIPTION
             "Unknown property, request rejected"
           --#TYPE      "Management Agent Event 9032"
           --#SUMMARY   "Host %s : SCellName-TimeDate %s : EventCode %d : Description %s"
           --#ARGUMENTS {0,1,2,3,}
            --#SEVERITY  INFORMATIONAL
            --#TIMEINDEX 136
        ::= 136009032

   mngmtAgentTrap-9033 TRAP-TYPE
        ENTERPRISE compaq
        VARIABLES  { hostName,
                     scellNameDateTime,
                     agentEventCode,
                     agentEventDescription }
        DESCRIPTION
             "This Vdisk was deleted as the indirect result of another user command."
           --#TYPE      "Management Agent Event 9033"
           --#SUMMARY   "Host %s : SCellName-TimeDate %s : EventCode %d : Description %s"
           --#ARGUMENTS {0,1,2,3,}
            --#SEVERITY  INFORMATIONAL
            --#TIMEINDEX 136
        ::= 136009033

   mngmtAgentTrap-9034 TRAP-TYPE
        ENTERPRISE compaq
        VARIABLES  { hostName,
                     scellNameDateTime,
                     agentEventCode,
                     agentEventDescription }
        DESCRIPTION
             "The requested allocation policy cannot be satisfied. A different allocation policy is already in use by another snapshot in the same family."
           --#TYPE      "Management Agent Event 9034"
           --#SUMMARY   "Host %s : SCellName-TimeDate %s : EventCode %d : Description %s"
           --#ARGUMENTS {0,1,2,3,}
            --#SEVERITY  INFORMATIONAL
            --#TIMEINDEX 136
        ::= 136009034

   mngmtAgentTrap-9035 TRAP-TYPE
        ENTERPRISE compaq
        VARIABLES  { hostName,
                     scellNameDateTime,
                     agentEventCode,
                     agentEventDescription }
        DESCRIPTION
             "The deletion of this Vdisk cannot take place.  The original Vdisk that this is being snapcloned from is in an Inoperative state which must first be resolved."
           --#TYPE      "Management Agent Event 9035"
           --#SUMMARY   "Host %s : SCellName-TimeDate %s : EventCode %d : Description %s"
           --#ARGUMENTS {0,1,2,3,}
            --#SEVERITY  INFORMATIONAL
            --#TIMEINDEX 136
        ::= 136009035

   mngmtAgentTrap-9036 TRAP-TYPE
        ENTERPRISE compaq
        VARIABLES  { hostName,
                     scellNameDateTime,
                     agentEventCode,
                     agentEventDescription }
        DESCRIPTION
             "Synchronous creation of virtual disk has been aborted due to an internal error. Switching to asynchronous mode to complete the virtual disk creation."
           --#TYPE      "Management Agent Event 9036"
           --#SUMMARY   "Host %s : SCellName-TimeDate %s : EventCode %d : Description %s"
           --#ARGUMENTS {0,1,2,3,}
            --#SEVERITY  INFORMATIONAL
            --#TIMEINDEX 136
        ::= 136009036

   mngmtAgentTrap-9037 TRAP-TYPE
        ENTERPRISE compaq
        VARIABLES  { hostName,
                     scellNameDateTime,
                     agentEventCode,
                     agentEventDescription }
        DESCRIPTION
             "Convert to Container Completed"
           --#TYPE      "Management Agent Event 9037"
           --#SUMMARY   "Host %s : SCellName-TimeDate %s : EventCode %d : Description %s"
           --#ARGUMENTS {0,1,2,3,}
            --#SEVERITY  INFORMATIONAL
            --#TIMEINDEX 136
        ::= 136009037

   mngmtAgentTrap-9038 TRAP-TYPE
        ENTERPRISE compaq
        VARIABLES  { hostName,
                     scellNameDateTime,
                     agentEventCode,
                     agentEventDescription }
        DESCRIPTION
             "Source virtual disk write-cache policy must be Write-Through."
           --#TYPE      "Management Agent Event 9038"
           --#SUMMARY   "Host %s : SCellName-TimeDate %s : EventCode %d : Description %s"
           --#ARGUMENTS {0,1,2,3,}
            --#SEVERITY  INFORMATIONAL
            --#TIMEINDEX 136
        ::= 136009038

   mngmtAgentTrap-9039 TRAP-TYPE
        ENTERPRISE compaq
        VARIABLES  { hostName,
                     scellNameDateTime,
                     agentEventCode,
                     agentEventDescription }
        DESCRIPTION
             "WWID specified is invalid."
           --#TYPE      "Management Agent Event 9039"
           --#SUMMARY   "Host %s : SCellName-TimeDate %s : EventCode %d : Description %s"
           --#ARGUMENTS {0,1,2,3,}
            --#SEVERITY  INFORMATIONAL
            --#TIMEINDEX 136
        ::= 136009039

   mngmtAgentTrap-9040 TRAP-TYPE
        ENTERPRISE compaq
        VARIABLES  { hostName,
                     scellNameDateTime,
                     agentEventCode,
                     agentEventDescription }
        DESCRIPTION
             "This property cannot be changed on this virtual disk (vdisk is either an empty container or a snapshot)."
           --#TYPE      "Management Agent Event 9040"
           --#SUMMARY   "Host %s : SCellName-TimeDate %s : EventCode %d : Description %s"
           --#ARGUMENTS {0,1,2,3,}
            --#SEVERITY  INFORMATIONAL
            --#TIMEINDEX 136
        ::= 136009040

   mngmtAgentTrap-9041 TRAP-TYPE
        ENTERPRISE compaq
        VARIABLES  { hostName,
                     scellNameDateTime,
                     agentEventCode,
                     agentEventDescription }
        DESCRIPTION
             "Cannot perform this operation on a Data Replication (DR) member virtual disk."
           --#TYPE      "Management Agent Event 9041"
           --#SUMMARY   "Host %s : SCellName-TimeDate %s : EventCode %d : Description %s"
           --#ARGUMENTS {0,1,2,3,}
            --#SEVERITY  INFORMATIONAL
            --#TIMEINDEX 136
        ::= 136009041

   mngmtAgentTrap-9042 TRAP-TYPE
        ENTERPRISE compaq
        VARIABLES  { hostName,
                     scellNameDateTime,
                     agentEventCode,
                     agentEventDescription }
        DESCRIPTION
             "Convert to Container Not Complete"
           --#TYPE      "Management Agent Event 9042"
           --#SUMMARY   "Host %s : SCellName-TimeDate %s : EventCode %d : Description %s"
           --#ARGUMENTS {0,1,2,3,}
            --#SEVERITY  INFORMATIONAL
            --#TIMEINDEX 136
        ::= 136009042

   mngmtAgentTrap-9059 TRAP-TYPE
        ENTERPRISE compaq
        VARIABLES  { hostName,
                     scellNameDateTime,
                     agentEventCode,
                     agentEventDescription }
        DESCRIPTION
             "Virtual Disk migration in progress."
           --#TYPE      "Management Agent Event 9059"
           --#SUMMARY   "Host %s : SCellName-TimeDate %s : EventCode %d : Description %s"
           --#ARGUMENTS {0,1,2,3,}
            --#SEVERITY  INFORMATIONAL
            --#TIMEINDEX 136
        ::= 136009059

   mngmtAgentTrap-9060 TRAP-TYPE
        ENTERPRISE compaq
        VARIABLES  { hostName,
                     scellNameDateTime,
                     agentEventCode,
                     agentEventDescription }
        DESCRIPTION
             "Virtual Disk migration failed."
           --#TYPE      "Management Agent Event 9060"
           --#SUMMARY   "Host %s : SCellName-TimeDate %s : EventCode %d : Description %s"
           --#ARGUMENTS {0,1,2,3,}
            --#SEVERITY  MAJOR
            --#TIMEINDEX 136
        ::= 136009060

   mngmtAgentTrap-9061 TRAP-TYPE
        ENTERPRISE compaq
        VARIABLES  { hostName,
                     scellNameDateTime,
                     agentEventCode,
                     agentEventDescription }
        DESCRIPTION
             "Virtual Disk migration completed successfully but clean up failed."
           --#TYPE      "Management Agent Event 9061"
           --#SUMMARY   "Host %s : SCellName-TimeDate %s : EventCode %d : Description %s"
           --#ARGUMENTS {0,1,2,3,}
            --#SEVERITY  MAJOR
            --#TIMEINDEX 136
        ::= 136009061

   mngmtAgentTrap-9063 TRAP-TYPE
        ENTERPRISE compaq
        VARIABLES  { hostName,
                     scellNameDateTime,
                     agentEventCode,
                     agentEventDescription }
        DESCRIPTION
             "The virtual disk structure is inconsistent.  Performing a storage system Refresh may correct the problem."
           --#TYPE      "Management Agent Event 9063"
           --#SUMMARY   "Host %s : SCellName-TimeDate %s : EventCode %d : Description %s"
           --#ARGUMENTS {0,1,2,3,}
            --#SEVERITY  MINOR
            --#TIMEINDEX 136
        ::= 136009063

   mngmtAgentTrap-10001 TRAP-TYPE
        ENTERPRISE compaq
        VARIABLES  { hostName,
                     scellNameDateTime,
                     agentEventCode,
                     agentEventDescription }
        DESCRIPTION
             "Storage Object Broker Ready"
           --#TYPE      "Management Agent Event 10001"
           --#SUMMARY   "Host %s : SCellName-TimeDate %s : EventCode %d : Description %s"
           --#ARGUMENTS {0,1,2,3,}
            --#SEVERITY  INFORMATIONAL
            --#TIMEINDEX 136
        ::= 136010001

   mngmtAgentTrap-10004 TRAP-TYPE
        ENTERPRISE compaq
        VARIABLES  { hostName,
                     scellNameDateTime,
                     agentEventCode,
                     agentEventDescription }
        DESCRIPTION
             "The storage system object could not be found.  Refresh of the view is required."
           --#TYPE      "Management Agent Event 10004"
           --#SUMMARY   "Host %s : SCellName-TimeDate %s : EventCode %d : Description %s"
           --#ARGUMENTS {0,1,2,3,}
            --#SEVERITY  INFORMATIONAL
            --#TIMEINDEX 136
        ::= 136010004

   mngmtAgentTrap-10006 TRAP-TYPE
        ENTERPRISE compaq
        VARIABLES  { hostName,
                     scellNameDateTime,
                     agentEventCode,
                     agentEventDescription }
        DESCRIPTION
             "SOB Memory Allocation Failure"
           --#TYPE      "Management Agent Event 10006"
           --#SUMMARY   "Host %s : SCellName-TimeDate %s : EventCode %d : Description %s"
           --#ARGUMENTS {0,1,2,3,}
            --#SEVERITY  CRITICAL
            --#TIMEINDEX 136
        ::= 136010006

   mngmtAgentTrap-10010 TRAP-TYPE
        ENTERPRISE compaq
        VARIABLES  { hostName,
                     scellNameDateTime,
                     agentEventCode,
                     agentEventDescription }
        DESCRIPTION
             "Your initialized system must have at least one disk group"
           --#TYPE      "Management Agent Event 10010"
           --#SUMMARY   "Host %s : SCellName-TimeDate %s : EventCode %d : Description %s"
           --#ARGUMENTS {0,1,2,3,}
            --#SEVERITY  INFORMATIONAL
            --#TIMEINDEX 136
        ::= 136010010

   mngmtAgentTrap-10011 TRAP-TYPE
        ENTERPRISE compaq
        VARIABLES  { hostName,
                     scellNameDateTime,
                     agentEventCode,
                     agentEventDescription }
        DESCRIPTION
             "Cannot talk to all available controllers"
           --#TYPE      "Management Agent Event 10011"
           --#SUMMARY   "Host %s : SCellName-TimeDate %s : EventCode %d : Description %s"
           --#ARGUMENTS {0,1,2,3,}
            --#SEVERITY  INFORMATIONAL
            --#TIMEINDEX 136
        ::= 136010011

   mngmtAgentTrap-10012 TRAP-TYPE
        ENTERPRISE compaq
        VARIABLES  { hostName,
                     scellNameDateTime,
                     agentEventCode,
                     agentEventDescription }
        DESCRIPTION
             "Command rejected - Folder is not empty"
           --#TYPE      "Management Agent Event 10012"
           --#SUMMARY   "Host %s : SCellName-TimeDate %s : EventCode %d : Description %s"
           --#ARGUMENTS {0,1,2,3,}
            --#SEVERITY  INFORMATIONAL
            --#TIMEINDEX 136
        ::= 136010012

   mngmtAgentTrap-10013 TRAP-TYPE
        ENTERPRISE compaq
        VARIABLES  { hostName,
                     scellNameDateTime,
                     agentEventCode,
                     agentEventDescription }
        DESCRIPTION
             "Command rejected - Vdisk(s), Container(s) or a data replication log are contained in this disk group"
           --#TYPE      "Management Agent Event 10013"
           --#SUMMARY   "Host %s : SCellName-TimeDate %s : EventCode %d : Description %s"
           --#ARGUMENTS {0,1,2,3,}
            --#SEVERITY  INFORMATIONAL
            --#TIMEINDEX 136
        ::= 136010013

   mngmtAgentTrap-10014 TRAP-TYPE
        ENTERPRISE compaq
        VARIABLES  { hostName,
                     scellNameDateTime,
                     agentEventCode,
                     agentEventDescription }
        DESCRIPTION
             "Command rejected - Vdisk(s) are presented to this host"
           --#TYPE      "Management Agent Event 10014"
           --#SUMMARY   "Host %s : SCellName-TimeDate %s : EventCode %d : Description %s"
           --#ARGUMENTS {0,1,2,3,}
            --#SEVERITY  INFORMATIONAL
            --#TIMEINDEX 136
        ::= 136010014

   mngmtAgentTrap-10015 TRAP-TYPE
        ENTERPRISE compaq
        VARIABLES  { hostName,
                     scellNameDateTime,
                     agentEventCode,
                     agentEventDescription }
        DESCRIPTION
             "Command rejected - This Vdisk has a sharing relationship with another object"
           --#TYPE      "Management Agent Event 10015"
           --#SUMMARY   "Host %s : SCellName-TimeDate %s : EventCode %d : Description %s"
           --#ARGUMENTS {0,1,2,3,}
            --#SEVERITY  INFORMATIONAL
            --#TIMEINDEX 136
        ::= 136010015

   mngmtAgentTrap-10017 TRAP-TYPE
        ENTERPRISE compaq
        VARIABLES  { hostName,
                     scellNameDateTime,
                     agentEventCode,
                     agentEventDescription }
        DESCRIPTION
             "Command rejected - Number of disk groups will exceed the maximum allowable number"
           --#TYPE      "Management Agent Event 10017"
           --#SUMMARY   "Host %s : SCellName-TimeDate %s : EventCode %d : Description %s"
           --#ARGUMENTS {0,1,2,3,}
            --#SEVERITY  INFORMATIONAL
            --#TIMEINDEX 136
        ::= 136010017

   mngmtAgentTrap-10018 TRAP-TYPE
        ENTERPRISE compaq
        VARIABLES  { hostName,
                     scellNameDateTime,
                     agentEventCode,
                     agentEventDescription }
        DESCRIPTION
             "Cannot access the password file"
           --#TYPE      "Management Agent Event 10018"
           --#SUMMARY   "Host %s : SCellName-TimeDate %s : EventCode %d : Description %s"
           --#ARGUMENTS {0,1,2,3,}
            --#SEVERITY  INFORMATIONAL
            --#TIMEINDEX 136
        ::= 136010018

   mngmtAgentTrap-10019 TRAP-TYPE
        ENTERPRISE compaq
        VARIABLES  { hostName,
                     scellNameDateTime,
                     agentEventCode,
                     agentEventDescription }
        DESCRIPTION
             "Enterprise Login - Complete"
           --#TYPE      "Management Agent Event 10019"
           --#SUMMARY   "Host %s : SCellName-TimeDate %s : EventCode %d : Description %s"
           --#ARGUMENTS {0,1,2,3,}
            --#SEVERITY  INFORMATIONAL
            --#TIMEINDEX 136
        ::= 136010019

   mngmtAgentTrap-10020 TRAP-TYPE
        ENTERPRISE compaq
        VARIABLES  { hostName,
                     scellNameDateTime,
                     agentEventCode,
                     agentEventDescription }
        DESCRIPTION
             "Command rejected - Disks in the group would go below the minimum required number."
           --#TYPE      "Management Agent Event 10020"
           --#SUMMARY   "Host %s : SCellName-TimeDate %s : EventCode %d : Description %s"
           --#ARGUMENTS {0,1,2,3,}
            --#SEVERITY  INFORMATIONAL
            --#TIMEINDEX 136
        ::= 136010020

   mngmtAgentTrap-10021 TRAP-TYPE
        ENTERPRISE compaq
        VARIABLES  { hostName,
                     scellNameDateTime,
                     agentEventCode,
                     agentEventDescription }
        DESCRIPTION
             "Rediscovery of controllers - Complete"
           --#TYPE      "Management Agent Event 10021"
           --#SUMMARY   "Host %s : SCellName-TimeDate %s : EventCode %d : Description %s"
           --#ARGUMENTS {0,1,2,3,}
            --#SEVERITY  INFORMATIONAL
            --#TIMEINDEX 136
        ::= 136010021

   mngmtAgentTrap-10022 TRAP-TYPE
        ENTERPRISE compaq
        VARIABLES  { hostName,
                     scellNameDateTime,
                     agentEventCode,
                     agentEventDescription }
        DESCRIPTION
             "Unable to establish communication with controller, check all connections."
           --#TYPE      "Management Agent Event 10022"
           --#SUMMARY   "Host %s : SCellName-TimeDate %s : EventCode %d : Description %s"
           --#ARGUMENTS {0,1,2,3,}
            --#SEVERITY  INFORMATIONAL
            --#TIMEINDEX 136
        ::= 136010022

   mngmtAgentTrap-10023 TRAP-TYPE
        ENTERPRISE compaq
        VARIABLES  { hostName,
                     scellNameDateTime,
                     agentEventCode,
                     agentEventDescription }
        DESCRIPTION
             "Disk Group Data Lost Error Resolution Sequence 3 - Disk group resolved to normal"
           --#TYPE      "Management Agent Event 10023"
           --#SUMMARY   "Host %s : SCellName-TimeDate %s : EventCode %d : Description %s"
           --#ARGUMENTS {0,1,2,3,}
            --#SEVERITY  INFORMATIONAL
            --#TIMEINDEX 136
        ::= 136010023

   mngmtAgentTrap-10024 TRAP-TYPE
        ENTERPRISE compaq
        VARIABLES  { hostName,
                     scellNameDateTime,
                     agentEventCode,
                     agentEventDescription }
        DESCRIPTION
             "Disk Group Data Lost Error Resolution Sequence 1 - Failed Vdisks marked for deletion"
           --#TYPE      "Management Agent Event 10024"
           --#SUMMARY   "Host %s : SCellName-TimeDate %s : EventCode %d : Description %s"
           --#ARGUMENTS {0,1,2,3,}
            --#SEVERITY  INFORMATIONAL
            --#TIMEINDEX 136
        ::= 136010024

   mngmtAgentTrap-10025 TRAP-TYPE
        ENTERPRISE compaq
        VARIABLES  { hostName,
                     scellNameDateTime,
                     agentEventCode,
                     agentEventDescription }
        DESCRIPTION
             "Disk Group Data Lost Error Resolution Sequence 2 - Failed Vdisks deletion in progress"
           --#TYPE      "Management Agent Event 10025"
           --#SUMMARY   "Host %s : SCellName-TimeDate %s : EventCode %d : Description %s"
           --#ARGUMENTS {0,1,2,3,}
            --#SEVERITY  INFORMATIONAL
            --#TIMEINDEX 136
        ::= 136010025

   mngmtAgentTrap-10026 TRAP-TYPE
        ENTERPRISE compaq
        VARIABLES  { hostName,
                     scellNameDateTime,
                     agentEventCode,
                     agentEventDescription }
        DESCRIPTION
             "Disk Group Data Lost Error Resolution Sequence 3 - Disk group deleted"
           --#TYPE      "Management Agent Event 10026"
           --#SUMMARY   "Host %s : SCellName-TimeDate %s : EventCode %d : Description %s"
           --#ARGUMENTS {0,1,2,3,}
            --#SEVERITY  INFORMATIONAL
            --#TIMEINDEX 136
        ::= 136010026

   mngmtAgentTrap-10027 TRAP-TYPE
        ENTERPRISE compaq
        VARIABLES  { hostName,
                     scellNameDateTime,
                     agentEventCode,
                     agentEventDescription }
        DESCRIPTION
             "Creating the Vdisk would exceed the maximum allowable Vdisk count"
           --#TYPE      "Management Agent Event 10027"
           --#SUMMARY   "Host %s : SCellName-TimeDate %s : EventCode %d : Description %s"
           --#ARGUMENTS {0,1,2,3,}
            --#SEVERITY  INFORMATIONAL
            --#TIMEINDEX 136
        ::= 136010027

   mngmtAgentTrap-10028 TRAP-TYPE
        ENTERPRISE compaq
        VARIABLES  { hostName,
                     scellNameDateTime,
                     agentEventCode,
                     agentEventDescription }
        DESCRIPTION
             "Volume insufficient resources"
           --#TYPE      "Management Agent Event 10028"
           --#SUMMARY   "Host %s : SCellName-TimeDate %s : EventCode %d : Description %s"
           --#ARGUMENTS {0,1,2,3,}
            --#SEVERITY  INFORMATIONAL
            --#TIMEINDEX 136
        ::= 136010028

   mngmtAgentTrap-10029 TRAP-TYPE
        ENTERPRISE compaq
        VARIABLES  { hostName,
                     scellNameDateTime,
                     agentEventCode,
                     agentEventDescription }
        DESCRIPTION
             "Process mutex is locked"
           --#TYPE      "Management Agent Event 10029"
           --#SUMMARY   "Host %s : SCellName-TimeDate %s : EventCode %d : Description %s"
           --#ARGUMENTS {0,1,2,3,}
            --#SEVERITY  INFORMATIONAL
            --#TIMEINDEX 136
        ::= 136010029

   mngmtAgentTrap-10030 TRAP-TYPE
        ENTERPRISE compaq
        VARIABLES  { hostName,
                     scellNameDateTime,
                     agentEventCode,
                     agentEventDescription }
        DESCRIPTION
             "Invalid URL request type"
           --#TYPE      "Management Agent Event 10030"
           --#SUMMARY   "Host %s : SCellName-TimeDate %s : EventCode %d : Description %s"
           --#ARGUMENTS {0,1,2,3,}
            --#SEVERITY  INFORMATIONAL
            --#TIMEINDEX 136
        ::= 136010030

   mngmtAgentTrap-10031 TRAP-TYPE
        ENTERPRISE compaq
        VARIABLES  { hostName,
                     scellNameDateTime,
                     agentEventCode,
                     agentEventDescription }
        DESCRIPTION
             "Invalid URL object type"
           --#TYPE      "Management Agent Event 10031"
           --#SUMMARY   "Host %s : SCellName-TimeDate %s : EventCode %d : Description %s"
           --#ARGUMENTS {0,1,2,3,}
            --#SEVERITY  INFORMATIONAL
            --#TIMEINDEX 136
        ::= 136010031

   mngmtAgentTrap-10035 TRAP-TYPE
        ENTERPRISE compaq
        VARIABLES  { hostName,
                     scellNameDateTime,
                     agentEventCode,
                     agentEventDescription }
        DESCRIPTION
             "The snapshot/Snapclone license cannot be validated. Either the license key has not been entered, or there is a system communication failure."
           --#TYPE      "Management Agent Event 10035"
           --#SUMMARY   "Host %s : SCellName-TimeDate %s : EventCode %d : Description %s"
           --#ARGUMENTS {0,1,2,3,}
            --#SEVERITY  INFORMATIONAL
            --#TIMEINDEX 136
        ::= 136010035

   mngmtAgentTrap-10036 TRAP-TYPE
        ENTERPRISE compaq
        VARIABLES  { hostName,
                     scellNameDateTime,
                     agentEventCode,
                     agentEventDescription }
        DESCRIPTION
             "A data replication license cannot be validated. Either the license key has not been entered, or there is a system communication failure."
           --#TYPE      "Management Agent Event 10036"
           --#SUMMARY   "Host %s : SCellName-TimeDate %s : EventCode %d : Description %s"
           --#ARGUMENTS {0,1,2,3,}
            --#SEVERITY  INFORMATIONAL
            --#TIMEINDEX 136
        ::= 136010036

   mngmtAgentTrap-10037 TRAP-TYPE
        ENTERPRISE compaq
        VARIABLES  { hostName,
                     scellNameDateTime,
                     agentEventCode,
                     agentEventDescription }
        DESCRIPTION
             "Object name should not be empty or exceed its maximum length"
           --#TYPE      "Management Agent Event 10037"
           --#SUMMARY   "Host %s : SCellName-TimeDate %s : EventCode %d : Description %s"
           --#ARGUMENTS {0,1,2,3,}
            --#SEVERITY  INFORMATIONAL
            --#TIMEINDEX 136
        ::= 136010037

   mngmtAgentTrap-10038 TRAP-TYPE
        ENTERPRISE compaq
        VARIABLES  { hostName,
                     scellNameDateTime,
                     agentEventCode,
                     agentEventDescription }
        DESCRIPTION
             "Object comments exceeds maximum length"
           --#TYPE      "Management Agent Event 10038"
           --#SUMMARY   "Host %s : SCellName-TimeDate %s : EventCode %d : Description %s"
           --#ARGUMENTS {0,1,2,3,}
            --#SEVERITY  INFORMATIONAL
            --#TIMEINDEX 136
        ::= 136010038

   mngmtAgentTrap-10039 TRAP-TYPE
        ENTERPRISE compaq
        VARIABLES  { hostName,
                     scellNameDateTime,
                     agentEventCode,
                     agentEventDescription }
        DESCRIPTION
             "Vdisk does not meet the requirements to be part of a DR group."
           --#TYPE      "Management Agent Event 10039"
           --#SUMMARY   "Host %s : SCellName-TimeDate %s : EventCode %d : Description %s"
           --#ARGUMENTS {0,1,2,3,}
            --#SEVERITY  INFORMATIONAL
            --#TIMEINDEX 136
        ::= 136010039

   mngmtAgentTrap-10040 TRAP-TYPE
        ENTERPRISE compaq
        VARIABLES  { hostName,
                     scellNameDateTime,
                     agentEventCode,
                     agentEventDescription }
        DESCRIPTION
             "The array selected as the Destination for the DR group is invalid. Either it has a DR relationship with another array or it is not the same array that the source array presently has a DR relationship with."
           --#TYPE      "Management Agent Event 10040"
           --#SUMMARY   "Host %s : SCellName-TimeDate %s : EventCode %d : Description %s"
           --#ARGUMENTS {0,1,2,3,}
            --#SEVERITY  INFORMATIONAL
            --#TIMEINDEX 136
        ::= 136010040

   mngmtAgentTrap-10041 TRAP-TYPE
        ENTERPRISE compaq
        VARIABLES  { hostName,
                     scellNameDateTime,
                     agentEventCode,
                     agentEventDescription }
        DESCRIPTION
             "Cannot group the specified disk device because the disk is already in a disk group."
           --#TYPE      "Management Agent Event 10041"
           --#SUMMARY   "Host %s : SCellName-TimeDate %s : EventCode %d : Description %s"
           --#ARGUMENTS {0,1,2,3,}
            --#SEVERITY  INFORMATIONAL
            --#TIMEINDEX 136
        ::= 136010041

   mngmtAgentTrap-10042 TRAP-TYPE
        ENTERPRISE compaq
        VARIABLES  { hostName,
                     scellNameDateTime,
                     agentEventCode,
                     agentEventDescription }
        DESCRIPTION
             "Cannot ungroup the specified disk device because the disk is not grouped."
           --#TYPE      "Management Agent Event 10042"
           --#SUMMARY   "Host %s : SCellName-TimeDate %s : EventCode %d : Description %s"
           --#ARGUMENTS {0,1,2,3,}
            --#SEVERITY  INFORMATIONAL
            --#TIMEINDEX 136
        ::= 136010042

   mngmtAgentTrap-10043 TRAP-TYPE
        ENTERPRISE compaq
        VARIABLES  { hostName,
                     scellNameDateTime,
                     agentEventCode,
                     agentEventDescription }
        DESCRIPTION
             "Object ID provided, or object type, is invalid for the requested operation."
           --#TYPE      "Management Agent Event 10043"
           --#SUMMARY   "Host %s : SCellName-TimeDate %s : EventCode %d : Description %s"
           --#ARGUMENTS {0,1,2,3,}
            --#SEVERITY  INFORMATIONAL
            --#TIMEINDEX 136
        ::= 136010043

   mngmtAgentTrap-10044 TRAP-TYPE
        ENTERPRISE compaq
        VARIABLES  { hostName,
                     scellNameDateTime,
                     agentEventCode,
                     agentEventDescription }
        DESCRIPTION
             "Specified remote disk group does not exist."
           --#TYPE      "Management Agent Event 10044"
           --#SUMMARY   "Host %s : SCellName-TimeDate %s : EventCode %d : Description %s"
           --#ARGUMENTS {0,1,2,3,}
            --#SEVERITY  INFORMATIONAL
            --#TIMEINDEX 136
        ::= 136010044

   mngmtAgentTrap-10047 TRAP-TYPE
        ENTERPRISE compaq
        VARIABLES  { hostName,
                     scellNameDateTime,
                     agentEventCode,
                     agentEventDescription }
        DESCRIPTION
             "The maximum number of iSCSI Controllers per array has been reached."
           --#TYPE      "Management Agent Event 10047"
           --#SUMMARY   "Host %s : SCellName-TimeDate %s : EventCode %d : Description %s"
           --#ARGUMENTS {0,1,2,3,}
            --#SEVERITY  INFORMATIONAL
            --#TIMEINDEX 136
        ::= 136010047

   mngmtAgentTrap-10048 TRAP-TYPE
        ENTERPRISE compaq
        VARIABLES  { hostName,
                     scellNameDateTime,
                     agentEventCode,
                     agentEventDescription }
        DESCRIPTION
             "The iSCSI Host object can not be deleted."
           --#TYPE      "Management Agent Event 10048"
           --#SUMMARY   "Host %s : SCellName-TimeDate %s : EventCode %d : Description %s"
           --#ARGUMENTS {0,1,2,3,}
            --#SEVERITY  INFORMATIONAL
            --#TIMEINDEX 136
        ::= 136010048

   mngmtAgentTrap-10049 TRAP-TYPE
        ENTERPRISE compaq
        VARIABLES  { hostName,
                     scellNameDateTime,
                     agentEventCode,
                     agentEventDescription }
        DESCRIPTION
             "Error received from the iSCSI Controller.  See log file for details."
           --#TYPE      "Management Agent Event 10049"
           --#SUMMARY   "Host %s : SCellName-TimeDate %s : EventCode %d : Description %s"
           --#ARGUMENTS {0,1,2,3,}
            --#SEVERITY  INFORMATIONAL
            --#TIMEINDEX 136
        ::= 136010049

   mngmtAgentTrap-10050 TRAP-TYPE
        ENTERPRISE compaq
        VARIABLES  { hostName,
                     scellNameDateTime,
                     agentEventCode,
                     agentEventDescription }
        DESCRIPTION
             "All presentations to the iSCSI host must be removed first."
           --#TYPE      "Management Agent Event 10050"
           --#SUMMARY   "Host %s : SCellName-TimeDate %s : EventCode %d : Description %s"
           --#ARGUMENTS {0,1,2,3,}
            --#SEVERITY  INFORMATIONAL
            --#TIMEINDEX 136
        ::= 136010050

   mngmtAgentTrap-10051 TRAP-TYPE
        ENTERPRISE compaq
        VARIABLES  { hostName,
                     scellNameDateTime,
                     agentEventCode,
                     agentEventDescription }
        DESCRIPTION
             "All iSCSI presentations must be removed first."
           --#TYPE      "Management Agent Event 10051"
           --#SUMMARY   "Host %s : SCellName-TimeDate %s : EventCode %d : Description %s"
           --#ARGUMENTS {0,1,2,3,}
            --#SEVERITY  INFORMATIONAL
            --#TIMEINDEX 136
        ::= 136010051

   mngmtAgentTrap-10052 TRAP-TYPE
        ENTERPRISE compaq
        VARIABLES  { hostName,
                     scellNameDateTime,
                     agentEventCode,
                     agentEventDescription }
        DESCRIPTION
             "Configuration Error - This iSCSI controller can not communicate with the selected storage cell."
           --#TYPE      "Management Agent Event 10052"
           --#SUMMARY   "Host %s : SCellName-TimeDate %s : EventCode %d : Description %s"
           --#ARGUMENTS {0,1,2,3,}
            --#SEVERITY  INFORMATIONAL
            --#TIMEINDEX 136
        ::= 136010052

   mngmtAgentTrap-10053 TRAP-TYPE
        ENTERPRISE compaq
        VARIABLES  { hostName,
                     scellNameDateTime,
                     agentEventCode,
                     agentEventDescription }
        DESCRIPTION
             "No iSCSI Controller found."
           --#TYPE      "Management Agent Event 10053"
           --#SUMMARY   "Host %s : SCellName-TimeDate %s : EventCode %d : Description %s"
           --#ARGUMENTS {0,1,2,3,}
            --#SEVERITY  INFORMATIONAL
            --#TIMEINDEX 136
        ::= 136010053

   mngmtAgentTrap-10054 TRAP-TYPE
        ENTERPRISE compaq
        VARIABLES  { hostName,
                     scellNameDateTime,
                     agentEventCode,
                     agentEventDescription }
        DESCRIPTION
             "A reboot of your iSCSI Controllers is required in order for the parameter changes to take effect."
           --#TYPE      "Management Agent Event 10054"
           --#SUMMARY   "Host %s : SCellName-TimeDate %s : EventCode %d : Description %s"
           --#ARGUMENTS {0,1,2,3,}
            --#SEVERITY  INFORMATIONAL
            --#TIMEINDEX 136
        ::= 136010054

   mngmtAgentTrap-10055 TRAP-TYPE
        ENTERPRISE compaq
        VARIABLES  { hostName,
                     scellNameDateTime,
                     agentEventCode,
                     agentEventDescription }
        DESCRIPTION
             "The specified iSCSI host os type is not supported."
           --#TYPE      "Management Agent Event 10055"
           --#SUMMARY   "Host %s : SCellName-TimeDate %s : EventCode %d : Description %s"
           --#ARGUMENTS {0,1,2,3,}
            --#SEVERITY  INFORMATIONAL
            --#TIMEINDEX 136
        ::= 136010055

   mngmtAgentTrap-10056 TRAP-TYPE
        ENTERPRISE compaq
        VARIABLES  { hostName,
                     scellNameDateTime,
                     agentEventCode,
                     agentEventDescription }
        DESCRIPTION
             "Adding an iSCSI controller requires the automatic creation of an iSCSI host object but the maximum number of host objects has been exceeded."
           --#TYPE      "Management Agent Event 10056"
           --#SUMMARY   "Host %s : SCellName-TimeDate %s : EventCode %d : Description %s"
           --#ARGUMENTS {0,1,2,3,}
            --#SEVERITY  INFORMATIONAL
            --#TIMEINDEX 136
        ::= 136010056

   mngmtAgentTrap-10057 TRAP-TYPE
        ENTERPRISE compaq
        VARIABLES  { hostName,
                     scellNameDateTime,
                     agentEventCode,
                     agentEventDescription }
        DESCRIPTION
             "Multiple iSCSI controllers are configured however one or more are currently not available.  All configured iSCSI controllers must be functional in order to continue with this operation."
           --#TYPE      "Management Agent Event 10057"
           --#SUMMARY   "Host %s : SCellName-TimeDate %s : EventCode %d : Description %s"
           --#ARGUMENTS {0,1,2,3,}
            --#SEVERITY  INFORMATIONAL
            --#TIMEINDEX 136
        ::= 136010057

   mngmtAgentTrap-10058 TRAP-TYPE
        ENTERPRISE compaq
        VARIABLES  { hostName,
                     scellNameDateTime,
                     agentEventCode,
                     agentEventDescription }
        DESCRIPTION
             "This multi-attach (snap) item will not be processed because it exceeds the maximum allowable attach/snap count."
           --#TYPE      "Management Agent Event 10058"
           --#SUMMARY   "Host %s : SCellName-TimeDate %s : EventCode %d : Description %s"
           --#ARGUMENTS {0,1,2,3,}
            --#SEVERITY  INFORMATIONAL
            --#TIMEINDEX 136
        ::= 136010058

   mngmtAgentTrap-10059 TRAP-TYPE
        ENTERPRISE compaq
        VARIABLES  { hostName,
                     scellNameDateTime,
                     agentEventCode,
                     agentEventDescription }
        DESCRIPTION
             "Command Rejected - At least one snap item should be specified in the multi-attach (snap) operation."
           --#TYPE      "Management Agent Event 10059"
           --#SUMMARY   "Host %s : SCellName-TimeDate %s : EventCode %d : Description %s"
           --#ARGUMENTS {0,1,2,3,}
            --#SEVERITY  INFORMATIONAL
            --#TIMEINDEX 136
        ::= 136010059

   mngmtAgentTrap-10060 TRAP-TYPE
        ENTERPRISE compaq
        VARIABLES  { hostName,
                     scellNameDateTime,
                     agentEventCode,
                     agentEventDescription }
        DESCRIPTION
             "All snap items in the multi-attach operation failed. Please check individual snap item's result code for details."
           --#TYPE      "Management Agent Event 10060"
           --#SUMMARY   "Host %s : SCellName-TimeDate %s : EventCode %d : Description %s"
           --#ARGUMENTS {0,1,2,3,}
            --#SEVERITY  INFORMATIONAL
            --#TIMEINDEX 136
        ::= 136010060

   mngmtAgentTrap-10061 TRAP-TYPE
        ENTERPRISE compaq
        VARIABLES  { hostName,
                     scellNameDateTime,
                     agentEventCode,
                     agentEventDescription }
        DESCRIPTION
             "Mirror Clone must be detached before deleting."
           --#TYPE      "Management Agent Event 10061"
           --#SUMMARY   "Host %s : SCellName-TimeDate %s : EventCode %d : Description %s"
           --#ARGUMENTS {0,1,2,3,}
            --#SEVERITY  INFORMATIONAL
            --#TIMEINDEX 136
        ::= 136010061

   mngmtAgentTrap-10062 TRAP-TYPE
        ENTERPRISE compaq
        VARIABLES  { hostName,
                     scellNameDateTime,
                     agentEventCode,
                     agentEventDescription }
        DESCRIPTION
             "Asynchronous DR Group mode cannot be created between specified systems."
           --#TYPE      "Management Agent Event 10062"
           --#SUMMARY   "Host %s : SCellName-TimeDate %s : EventCode %d : Description %s"
           --#ARGUMENTS {0,1,2,3,}
            --#SEVERITY  INFORMATIONAL
            --#TIMEINDEX 136
        ::= 136010062

   mngmtAgentTrap-10063 TRAP-TYPE
        ENTERPRISE compaq
        VARIABLES  { hostName,
                     scellNameDateTime,
                     agentEventCode,
                     agentEventDescription }
        DESCRIPTION
             "iSCSI host initiator not found with discovered iSCSI controllers."
           --#TYPE      "Management Agent Event 10063"
           --#SUMMARY   "Host %s : SCellName-TimeDate %s : EventCode %d : Description %s"
           --#ARGUMENTS {0,1,2,3,}
            --#SEVERITY  INFORMATIONAL
            --#TIMEINDEX 136
        ::= 136010063

   mngmtAgentTrap-10064 TRAP-TYPE
        ENTERPRISE compaq
        VARIABLES  { hostName,
                     scellNameDateTime,
                     agentEventCode,
                     agentEventDescription }
        DESCRIPTION
             "Adding an iSCSI host requires valid iSCSI node name."
           --#TYPE      "Management Agent Event 10064"
           --#SUMMARY   "Host %s : SCellName-TimeDate %s : EventCode %d : Description %s"
           --#ARGUMENTS {0,1,2,3,}
            --#SEVERITY  INFORMATIONAL
            --#TIMEINDEX 136
        ::= 136010064

   mngmtAgentTrap-10065 TRAP-TYPE
        ENTERPRISE compaq
        VARIABLES  { hostName,
                     scellNameDateTime,
                     agentEventCode,
                     agentEventDescription }
        DESCRIPTION
             "Selected iSCSI initiator node already associated with Host."
           --#TYPE      "Management Agent Event 10065"
           --#SUMMARY   "Host %s : SCellName-TimeDate %s : EventCode %d : Description %s"
           --#ARGUMENTS {0,1,2,3,}
            --#SEVERITY  INFORMATIONAL
            --#TIMEINDEX 136
        ::= 136010065

   mngmtAgentTrap-10066 TRAP-TYPE
        ENTERPRISE compaq
        VARIABLES  { hostName,
                     scellNameDateTime,
                     agentEventCode,
                     agentEventDescription }
        DESCRIPTION
             "iSCSI Host creation failed. Maximum number of iSCSI hosts reached."
           --#TYPE      "Management Agent Event 10066"
           --#SUMMARY   "Host %s : SCellName-TimeDate %s : EventCode %d : Description %s"
           --#ARGUMENTS {0,1,2,3,}
            --#SEVERITY  INFORMATIONAL
            --#TIMEINDEX 136
        ::= 136010066

   mngmtAgentTrap-10067 TRAP-TYPE
        ENTERPRISE compaq
        VARIABLES  { hostName,
                     scellNameDateTime,
                     agentEventCode,
                     agentEventDescription }
        DESCRIPTION
             "Operation not allowed on selected host."
           --#TYPE      "Management Agent Event 10067"
           --#SUMMARY   "Host %s : SCellName-TimeDate %s : EventCode %d : Description %s"
           --#ARGUMENTS {0,1,2,3,}
            --#SEVERITY  INFORMATIONAL
            --#TIMEINDEX 136
        ::= 136010067

   mngmtAgentTrap-10068 TRAP-TYPE
        ENTERPRISE compaq
        VARIABLES  { hostName,
                     scellNameDateTime,
                     agentEventCode,
                     agentEventDescription }
        DESCRIPTION
             "This multi-mirror operation will not be processed because it exceeds the maximum mirroritem-count."
           --#TYPE      "Management Agent Event 10068"
           --#SUMMARY   "Host %s : SCellName-TimeDate %s : EventCode %d : Description %s"
           --#ARGUMENTS {0,1,2,3,}
            --#SEVERITY  MINOR
            --#TIMEINDEX 136
        ::= 136010068

   mngmtAgentTrap-10069 TRAP-TYPE
        ENTERPRISE compaq
        VARIABLES  { hostName,
                     scellNameDateTime,
                     agentEventCode,
                     agentEventDescription }
        DESCRIPTION
             "Command Rejected - At least one mirroritem should be specified in the multi-mirror command."
           --#TYPE      "Management Agent Event 10069"
           --#SUMMARY   "Host %s : SCellName-TimeDate %s : EventCode %d : Description %s"
           --#ARGUMENTS {0,1,2,3,}
            --#SEVERITY  MINOR
            --#TIMEINDEX 136
        ::= 136010069

   mngmtAgentTrap-10070 TRAP-TYPE
        ENTERPRISE compaq
        VARIABLES  { hostName,
                     scellNameDateTime,
                     agentEventCode,
                     agentEventDescription }
        DESCRIPTION
             "All mirroritems in the multi-mirror command failed. Please check individual mirroritem's result code for details."
           --#TYPE      "Management Agent Event 10070"
           --#SUMMARY   "Host %s : SCellName-TimeDate %s : EventCode %d : Description %s"
           --#ARGUMENTS {0,1,2,3,}
            --#SEVERITY  MINOR
            --#TIMEINDEX 136
        ::= 136010070

   mngmtAgentTrap-10071 TRAP-TYPE
        ENTERPRISE compaq
        VARIABLES  { hostName,
                     scellNameDateTime,
                     agentEventCode,
                     agentEventDescription }
        DESCRIPTION
             "There is no operation type specified for this command."
           --#TYPE      "Management Agent Event 10071"
           --#SUMMARY   "Host %s : SCellName-TimeDate %s : EventCode %d : Description %s"
           --#ARGUMENTS {0,1,2,3,}
            --#SEVERITY  MINOR
            --#TIMEINDEX 136
        ::= 136010071

   mngmtAgentTrap-10072 TRAP-TYPE
        ENTERPRISE compaq
        VARIABLES  { hostName,
                     scellNameDateTime,
                     agentEventCode,
                     agentEventDescription }
        DESCRIPTION
             "Could not verify the completion of this operation due to could not locate the mirrorclone."
           --#TYPE      "Management Agent Event 10072"
           --#SUMMARY   "Host %s : SCellName-TimeDate %s : EventCode %d : Description %s"
           --#ARGUMENTS {0,1,2,3,}
            --#SEVERITY  MINOR
            --#TIMEINDEX 136
        ::= 136010072

   mngmtAgentTrap-10073 TRAP-TYPE
        ENTERPRISE compaq
        VARIABLES  { hostName,
                     scellNameDateTime,
                     agentEventCode,
                     agentEventDescription }
        DESCRIPTION
             "Mirrorclone is fractured"
           --#TYPE      "Management Agent Event 10073"
           --#SUMMARY   "Host %s : SCellName-TimeDate %s : EventCode %d : Description %s"
           --#ARGUMENTS {0,1,2,3,}
            --#SEVERITY  INFORMATIONAL
            --#TIMEINDEX 136
        ::= 136010073

   mngmtAgentTrap-10074 TRAP-TYPE
        ENTERPRISE compaq
        VARIABLES  { hostName,
                     scellNameDateTime,
                     agentEventCode,
                     agentEventDescription }
        DESCRIPTION
             "Mirrorclone is detached"
           --#TYPE      "Management Agent Event 10074"
           --#SUMMARY   "Host %s : SCellName-TimeDate %s : EventCode %d : Description %s"
           --#ARGUMENTS {0,1,2,3,}
            --#SEVERITY  INFORMATIONAL
            --#TIMEINDEX 136
        ::= 136010074

   mngmtAgentTrap-10075 TRAP-TYPE
        ENTERPRISE compaq
        VARIABLES  { hostName,
                     scellNameDateTime,
                     agentEventCode,
                     agentEventDescription }
        DESCRIPTION
             "Failed Vdisk has a Mirror Clone relationship. Retry after detaching the Mirror Clones attached to failed vdisks."
           --#TYPE      "Management Agent Event 10075"
           --#SUMMARY   "Host %s : SCellName-TimeDate %s : EventCode %d : Description %s"
           --#ARGUMENTS {0,1,2,3,}
            --#SEVERITY  INFORMATIONAL
            --#TIMEINDEX 136
        ::= 136010075

   mngmtAgentTrap-10076 TRAP-TYPE
        ENTERPRISE compaq
        VARIABLES  { hostName,
                     scellNameDateTime,
                     agentEventCode,
                     agentEventDescription }
        DESCRIPTION
             "Maximum Number of allowed iSCSI Host Presentations reached."
           --#TYPE      "Management Agent Event 10076"
           --#SUMMARY   "Host %s : SCellName-TimeDate %s : EventCode %d : Description %s"
           --#ARGUMENTS {0,1,2,3,}
            --#SEVERITY  INFORMATIONAL
            --#TIMEINDEX 136
        ::= 136010076

   mngmtAgentTrap-10077 TRAP-TYPE
        ENTERPRISE compaq
        VARIABLES  { hostName,
                     scellNameDateTime,
                     agentEventCode,
                     agentEventDescription }
        DESCRIPTION
             "Discovered iSCSI Controller already exist."
           --#TYPE      "Management Agent Event 10077"
           --#SUMMARY   "Host %s : SCellName-TimeDate %s : EventCode %d : Description %s"
           --#ARGUMENTS {0,1,2,3,}
            --#SEVERITY  INFORMATIONAL
            --#TIMEINDEX 136
        ::= 136010077

   mngmtAgentTrap-10078 TRAP-TYPE
        ENTERPRISE compaq
        VARIABLES  { hostName,
                     scellNameDateTime,
                     agentEventCode,
                     agentEventDescription }
        DESCRIPTION
             "Not a supported configuration. Both HP Storage Works MPX200 controllers should belong to same Chassis/Enclosure."
           --#TYPE      "Management Agent Event 10078"
           --#SUMMARY   "Host %s : SCellName-TimeDate %s : EventCode %d : Description %s"
           --#ARGUMENTS {0,1,2,3,}
            --#SEVERITY  INFORMATIONAL
            --#TIMEINDEX 136
        ::= 136010078

   mngmtAgentTrap-10079 TRAP-TYPE
        ENTERPRISE compaq
        VARIABLES  { hostName,
                     scellNameDateTime,
                     agentEventCode,
                     agentEventDescription }
        DESCRIPTION
             "Not a supported configuration. HP Storage Works MPX200 can not be discovered with this array."
           --#TYPE      "Management Agent Event 10079"
           --#SUMMARY   "Host %s : SCellName-TimeDate %s : EventCode %d : Description %s"
           --#ARGUMENTS {0,1,2,3,}
            --#SEVERITY  INFORMATIONAL
            --#TIMEINDEX 136
        ::= 136010079

   mngmtAgentTrap-10080 TRAP-TYPE
        ENTERPRISE compaq
        VARIABLES  { hostName,
                     scellNameDateTime,
                     agentEventCode,
                     agentEventDescription }
        DESCRIPTION
             "Not a supported configuration. HP Storage Works MPX200 controller host port specified does not exist."
           --#TYPE      "Management Agent Event 10080"
           --#SUMMARY   "Host %s : SCellName-TimeDate %s : EventCode %d : Description %s"
           --#ARGUMENTS {0,1,2,3,}
            --#SEVERITY  INFORMATIONAL
            --#TIMEINDEX 136
        ::= 136010080

   mngmtAgentTrap-10081 TRAP-TYPE
        ENTERPRISE compaq
        VARIABLES  { hostName,
                     scellNameDateTime,
                     agentEventCode,
                     agentEventDescription }
        DESCRIPTION
             "Unable to process command at this time. Check all connections as iSCSI controller fibre channel ports are unavailable."
           --#TYPE      "Management Agent Event 10081"
           --#SUMMARY   "Host %s : SCellName-TimeDate %s : EventCode %d : Description %s"
           --#ARGUMENTS {0,1,2,3,}
            --#SEVERITY  INFORMATIONAL
            --#TIMEINDEX 136
        ::= 136010081

   mngmtAgentTrap-10082 TRAP-TYPE
        ENTERPRISE compaq
        VARIABLES  { hostName,
                     scellNameDateTime,
                     agentEventCode,
                     agentEventDescription }
        DESCRIPTION
             "Invalid iSCSI controller configuration file extension."
           --#TYPE      "Management Agent Event 10082"
           --#SUMMARY   "Host %s : SCellName-TimeDate %s : EventCode %d : Description %s"
           --#ARGUMENTS {0,1,2,3,}
            --#SEVERITY  INFORMATIONAL
            --#TIMEINDEX 136
        ::= 136010082

   mngmtAgentTrap-10083 TRAP-TYPE
        ENTERPRISE compaq
        VARIABLES  { hostName,
                     scellNameDateTime,
                     agentEventCode,
                     agentEventDescription }
        DESCRIPTION
             "Saving iSCSI Controller configuration process have been failed."
           --#TYPE      "Management Agent Event 10083"
           --#SUMMARY   "Host %s : SCellName-TimeDate %s : EventCode %d : Description %s"
           --#ARGUMENTS {0,1,2,3,}
            --#SEVERITY  INFORMATIONAL
            --#TIMEINDEX 136
        ::= 136010083

   mngmtAgentTrap-10084 TRAP-TYPE
        ENTERPRISE compaq
        VARIABLES  { hostName,
                     scellNameDateTime,
                     agentEventCode,
                     agentEventDescription }
        DESCRIPTION
             "Selected iSCSI host can not be added to iscsi controller to proceed with this presentation."
           --#TYPE      "Management Agent Event 10084"
           --#SUMMARY   "Host %s : SCellName-TimeDate %s : EventCode %d : Description %s"
           --#ARGUMENTS {0,1,2,3,}
            --#SEVERITY  INFORMATIONAL
            --#TIMEINDEX 136
        ::= 136010084

   mngmtAgentTrap-10085 TRAP-TYPE
        ENTERPRISE compaq
        VARIABLES  { hostName,
                     scellNameDateTime,
                     agentEventCode,
                     agentEventDescription }
        DESCRIPTION
             "Operation failed. iSCSI controller code load file can not open/read."
           --#TYPE      "Management Agent Event 10085"
           --#SUMMARY   "Host %s : SCellName-TimeDate %s : EventCode %d : Description %s"
           --#ARGUMENTS {0,1,2,3,}
            --#SEVERITY  INFORMATIONAL
            --#TIMEINDEX 136
        ::= 136010085

   mngmtAgentTrap-10086 TRAP-TYPE
        ENTERPRISE compaq
        VARIABLES  { hostName,
                     scellNameDateTime,
                     agentEventCode,
                     agentEventDescription }
        DESCRIPTION
             "iSCSI Controller code load process have been failed."
           --#TYPE      "Management Agent Event 10086"
           --#SUMMARY   "Host %s : SCellName-TimeDate %s : EventCode %d : Description %s"
           --#ARGUMENTS {0,1,2,3,}
            --#SEVERITY  INFORMATIONAL
            --#TIMEINDEX 136
        ::= 136010086

   mngmtAgentTrap-10087 TRAP-TYPE
        ENTERPRISE compaq
        VARIABLES  { hostName,
                     scellNameDateTime,
                     agentEventCode,
                     agentEventDescription }
        DESCRIPTION
             "Invalid iSCSI controller code load file extension."
           --#TYPE      "Management Agent Event 10087"
           --#SUMMARY   "Host %s : SCellName-TimeDate %s : EventCode %d : Description %s"
           --#ARGUMENTS {0,1,2,3,}
            --#SEVERITY  INFORMATIONAL
            --#TIMEINDEX 136
        ::= 136010087

   mngmtAgentTrap-10088 TRAP-TYPE
        ENTERPRISE compaq
        VARIABLES  { hostName,
                     scellNameDateTime,
                     agentEventCode,
                     agentEventDescription }
        DESCRIPTION
             "Not a supported configuration. Discovery of HP Storage Works MPX200 controller with Direct connects Fibre Channel attachment mode not allowed."
           --#TYPE      "Management Agent Event 10088"
           --#SUMMARY   "Host %s : SCellName-TimeDate %s : EventCode %d : Description %s"
           --#ARGUMENTS {0,1,2,3,}
            --#SEVERITY  INFORMATIONAL
            --#TIMEINDEX 136
        ::= 136010088

   mngmtAgentTrap-10089 TRAP-TYPE
        ENTERPRISE compaq
        VARIABLES  { hostName,
                     scellNameDateTime,
                     agentEventCode,
                     agentEventDescription }
        DESCRIPTION
             "Discovered iSCSI Controller not found with selected array."
           --#TYPE      "Management Agent Event 10089"
           --#SUMMARY   "Host %s : SCellName-TimeDate %s : EventCode %d : Description %s"
           --#ARGUMENTS {0,1,2,3,}
            --#SEVERITY  INFORMATIONAL
            --#TIMEINDEX 136
        ::= 136010089

   mngmtAgentTrap-10093 TRAP-TYPE
        ENTERPRISE compaq
        VARIABLES  { hostName,
                     scellNameDateTime,
                     agentEventCode,
                     agentEventDescription }
        DESCRIPTION
             "Mirrorclone inversion is successful"
           --#TYPE      "Management Agent Event 10093"
           --#SUMMARY   "Host %s : SCellName-TimeDate %s : EventCode %d : Description %s"
           --#ARGUMENTS {0,1,2,3,}
            --#SEVERITY  INFORMATIONAL
            --#TIMEINDEX 136
        ::= 136010093

   mngmtAgentTrap-10094 TRAP-TYPE
        ENTERPRISE compaq
        VARIABLES  { hostName,
                     scellNameDateTime,
                     agentEventCode,
                     agentEventDescription }
        DESCRIPTION
             "Virtual Disk Migration Failed"
           --#TYPE      "Management Agent Event 10094"
           --#SUMMARY   "Host %s : SCellName-TimeDate %s : EventCode %d : Description %s"
           --#ARGUMENTS {0,1,2,3,}
            --#SEVERITY  INFORMATIONAL
            --#TIMEINDEX 136
        ::= 136010094

   mngmtAgentTrap-10095 TRAP-TYPE
        ENTERPRISE compaq
        VARIABLES  { hostName,
                     scellNameDateTime,
                     agentEventCode,
                     agentEventDescription }
        DESCRIPTION
             "Operation failed. iSCSI Controller event logs can not retrieve."
           --#TYPE      "Management Agent Event 10095"
           --#SUMMARY   "Host %s : SCellName-TimeDate %s : EventCode %d : Description %s"
           --#ARGUMENTS {0,1,2,3,}
            --#SEVERITY  INFORMATIONAL
            --#TIMEINDEX 136
        ::= 136010095

   mngmtAgentTrap-10096 TRAP-TYPE
        ENTERPRISE compaq
        VARIABLES  { hostName,
                     scellNameDateTime,
                     agentEventCode,
                     agentEventDescription }
        DESCRIPTION
             "Save iSCSI Controller event logs process have been failed."
           --#TYPE      "Management Agent Event 10096"
           --#SUMMARY   "Host %s : SCellName-TimeDate %s : EventCode %d : Description %s"
           --#ARGUMENTS {0,1,2,3,}
            --#SEVERITY  INFORMATIONAL
            --#TIMEINDEX 136
        ::= 136010096

   mngmtAgentTrap-10097 TRAP-TYPE
        ENTERPRISE compaq
        VARIABLES  { hostName,
                     scellNameDateTime,
                     agentEventCode,
                     agentEventDescription }
        DESCRIPTION
             "Clear iSCSI Controller event logs process have been failed."
           --#TYPE      "Management Agent Event 10097"
           --#SUMMARY   "Host %s : SCellName-TimeDate %s : EventCode %d : Description %s"
           --#ARGUMENTS {0,1,2,3,}
            --#SEVERITY  INFORMATIONAL
            --#TIMEINDEX 136
        ::= 136010097

   mngmtAgentTrap-10098 TRAP-TYPE
        ENTERPRISE compaq
        VARIABLES  { hostName,
                     scellNameDateTime,
                     agentEventCode,
                     agentEventDescription }
        DESCRIPTION
             "Failed to retrieve licensing information of iSCSI controller."
           --#TYPE      "Management Agent Event 10098"
           --#SUMMARY   "Host %s : SCellName-TimeDate %s : EventCode %d : Description %s"
           --#ARGUMENTS {0,1,2,3,}
            --#SEVERITY  INFORMATIONAL
            --#TIMEINDEX 136
        ::= 136010098

   mngmtAgentTrap-10099 TRAP-TYPE
        ENTERPRISE compaq
        VARIABLES  { hostName,
                     scellNameDateTime,
                     agentEventCode,
                     agentEventDescription }
        DESCRIPTION
             "Error. Add iSCSI Controller license operation failed."
           --#TYPE      "Management Agent Event 10099"
           --#SUMMARY   "Host %s : SCellName-TimeDate %s : EventCode %d : Description %s"
           --#ARGUMENTS {0,1,2,3,}
            --#SEVERITY  INFORMATIONAL
            --#TIMEINDEX 136
        ::= 136010099

   mngmtAgentTrap-10100 TRAP-TYPE
        ENTERPRISE compaq
        VARIABLES  { hostName,
                     scellNameDateTime,
                     agentEventCode,
                     agentEventDescription }
        DESCRIPTION
             "Error. iSCSI Controller license feature keys already presented."
           --#TYPE      "Management Agent Event 10100"
           --#SUMMARY   "Host %s : SCellName-TimeDate %s : EventCode %d : Description %s"
           --#ARGUMENTS {0,1,2,3,}
            --#SEVERITY  INFORMATIONAL
            --#TIMEINDEX 136
        ::= 136010100

   mngmtAgentTrap-10101 TRAP-TYPE
        ENTERPRISE compaq
        VARIABLES  { hostName,
                     scellNameDateTime,
                     agentEventCode,
                     agentEventDescription }
        DESCRIPTION
             "Not a supported operation. FCoE Host creation not allowed with currently discovered iSCSI controller."
           --#TYPE      "Management Agent Event 10101"
           --#SUMMARY   "Host %s : SCellName-TimeDate %s : EventCode %d : Description %s"
           --#ARGUMENTS {0,1,2,3,}
            --#SEVERITY  INFORMATIONAL
            --#TIMEINDEX 136
        ::= 136010101

   mngmtAgentTrap-10102 TRAP-TYPE
        ENTERPRISE compaq
        VARIABLES  { hostName,
                     scellNameDateTime,
                     agentEventCode,
                     agentEventDescription }
        DESCRIPTION
             "Selected FCoE initiator node already associated with Host."
           --#TYPE      "Management Agent Event 10102"
           --#SUMMARY   "Host %s : SCellName-TimeDate %s : EventCode %d : Description %s"
           --#ARGUMENTS {0,1,2,3,}
            --#SEVERITY  INFORMATIONAL
            --#TIMEINDEX 136
        ::= 136010102

   mngmtAgentTrap-10103 TRAP-TYPE
        ENTERPRISE compaq
        VARIABLES  { hostName,
                     scellNameDateTime,
                     agentEventCode,
                     agentEventDescription }
        DESCRIPTION
             "Invalid FCoE initiator node name format."
           --#TYPE      "Management Agent Event 10103"
           --#SUMMARY   "Host %s : SCellName-TimeDate %s : EventCode %d : Description %s"
           --#ARGUMENTS {0,1,2,3,}
            --#SEVERITY  INFORMATIONAL
            --#TIMEINDEX 136
        ::= 136010103

   mngmtAgentTrap-10104 TRAP-TYPE
        ENTERPRISE compaq
        VARIABLES  { hostName,
                     scellNameDateTime,
                     agentEventCode,
                     agentEventDescription }
        DESCRIPTION
             "Adding an FCoE host requires valid FCoE port world wide name."
           --#TYPE      "Management Agent Event 10104"
           --#SUMMARY   "Host %s : SCellName-TimeDate %s : EventCode %d : Description %s"
           --#ARGUMENTS {0,1,2,3,}
            --#SEVERITY  INFORMATIONAL
            --#TIMEINDEX 136
        ::= 136010104

   mngmtAgentTrap-10105 TRAP-TYPE
        ENTERPRISE compaq
        VARIABLES  { hostName,
                     scellNameDateTime,
                     agentEventCode,
                     agentEventDescription }
        DESCRIPTION
             "FCoE Host creation failed. Maximum number of FCoE hosts reached."
           --#TYPE      "Management Agent Event 10105"
           --#SUMMARY   "Host %s : SCellName-TimeDate %s : EventCode %d : Description %s"
           --#ARGUMENTS {0,1,2,3,}
            --#SEVERITY  INFORMATIONAL
            --#TIMEINDEX 136
        ::= 136010105

   mngmtAgentTrap-10106 TRAP-TYPE
        ENTERPRISE compaq
        VARIABLES  { hostName,
                     scellNameDateTime,
                     agentEventCode,
                     agentEventDescription }
        DESCRIPTION
             "An iSCSI host presentation has been found. Unpresent this Vdisk and represent to the FCoE host first, then add the iSCSI host presentation."
           --#TYPE      "Management Agent Event 10106"
           --#SUMMARY   "Host %s : SCellName-TimeDate %s : EventCode %d : Description %s"
           --#ARGUMENTS {0,1,2,3,}
            --#SEVERITY  INFORMATIONAL
            --#TIMEINDEX 136
        ::= 136010106

   mngmtAgentTrap-10107 TRAP-TYPE
        ENTERPRISE compaq
        VARIABLES  { hostName,
                     scellNameDateTime,
                     agentEventCode,
                     agentEventDescription }
        DESCRIPTION
             "Selected FCoE host can not be added to iscsi controller to proceed with this presentation."
           --#TYPE      "Management Agent Event 10107"
           --#SUMMARY   "Host %s : SCellName-TimeDate %s : EventCode %d : Description %s"
           --#ARGUMENTS {0,1,2,3,}
            --#SEVERITY  INFORMATIONAL
            --#TIMEINDEX 136
        ::= 136010107

   mngmtAgentTrap-10108 TRAP-TYPE
        ENTERPRISE compaq
        VARIABLES  { hostName,
                     scellNameDateTime,
                     agentEventCode,
                     agentEventDescription }
        DESCRIPTION
             "The virtual disk operation has failed. Please make sure that FC targets and FCoE portal connections are online."
           --#TYPE      "Management Agent Event 10108"
           --#SUMMARY   "Host %s : SCellName-TimeDate %s : EventCode %d : Description %s"
           --#ARGUMENTS {0,1,2,3,}
            --#SEVERITY  INFORMATIONAL
            --#TIMEINDEX 136
        ::= 136010108

   mngmtAgentTrap-10109 TRAP-TYPE
        ENTERPRISE compaq
        VARIABLES  { hostName,
                     scellNameDateTime,
                     agentEventCode,
                     agentEventDescription }
        DESCRIPTION
             "Maximum Number of allowed FCoE Host Presentations reached."
           --#TYPE      "Management Agent Event 10109"
           --#SUMMARY   "Host %s : SCellName-TimeDate %s : EventCode %d : Description %s"
           --#ARGUMENTS {0,1,2,3,}
            --#SEVERITY  INFORMATIONAL
            --#TIMEINDEX 136
        ::= 136010109

   mngmtAgentTrap-10110 TRAP-TYPE
        ENTERPRISE compaq
        VARIABLES  { hostName,
                     scellNameDateTime,
                     agentEventCode,
                     agentEventDescription }
        DESCRIPTION
             "All presentations to the FCoE host must be removed first."
           --#TYPE      "Management Agent Event 10110"
           --#SUMMARY   "Host %s : SCellName-TimeDate %s : EventCode %d : Description %s"
           --#ARGUMENTS {0,1,2,3,}
            --#SEVERITY  INFORMATIONAL
            --#TIMEINDEX 136
        ::= 136010110

   mngmtAgentTrap-10111 TRAP-TYPE
        ENTERPRISE compaq
        VARIABLES  { hostName,
                     scellNameDateTime,
                     agentEventCode,
                     agentEventDescription }
        DESCRIPTION
             "The FCoE Host object can not be deleted."
           --#TYPE      "Management Agent Event 10111"
           --#SUMMARY   "Host %s : SCellName-TimeDate %s : EventCode %d : Description %s"
           --#ARGUMENTS {0,1,2,3,}
            --#SEVERITY  INFORMATIONAL
            --#TIMEINDEX 136
        ::= 136010111

   mngmtAgentTrap-10112 TRAP-TYPE
        ENTERPRISE compaq
        VARIABLES  { hostName,
                     scellNameDateTime,
                     agentEventCode,
                     agentEventDescription }
        DESCRIPTION
             "All FCoE presentations must be removed first."
           --#TYPE      "Management Agent Event 10112"
           --#SUMMARY   "Host %s : SCellName-TimeDate %s : EventCode %d : Description %s"
           --#ARGUMENTS {0,1,2,3,}
            --#SEVERITY  INFORMATIONAL
            --#TIMEINDEX 136
        ::= 136010112

   mngmtAgentTrap-10113 TRAP-TYPE
        ENTERPRISE compaq
        VARIABLES  { hostName,
                     scellNameDateTime,
                     agentEventCode,
                     agentEventDescription }
        DESCRIPTION
             "Operation failed. Failed to retrieve iSCSI Controller slot information."
           --#TYPE      "Management Agent Event 10113"
           --#SUMMARY   "Host %s : SCellName-TimeDate %s : EventCode %d : Description %s"
           --#ARGUMENTS {0,1,2,3,}
            --#SEVERITY  INFORMATIONAL
            --#TIMEINDEX 136
        ::= 136010113

   mngmtAgentTrap-10114 TRAP-TYPE
        ENTERPRISE compaq
        VARIABLES  { hostName,
                     scellNameDateTime,
                     agentEventCode,
                     agentEventDescription }
        DESCRIPTION
             "FCoE host initiator not found with discovered FCoE controllers."
           --#TYPE      "Management Agent Event 10114"
           --#SUMMARY   "Host %s : SCellName-TimeDate %s : EventCode %d : Description %s"
           --#ARGUMENTS {0,1,2,3,}
            --#SEVERITY  INFORMATIONAL
            --#TIMEINDEX 136
        ::= 136010114

   mngmtAgentTrap-10115 TRAP-TYPE
        ENTERPRISE compaq
        VARIABLES  { hostName,
                     scellNameDateTime,
                     agentEventCode,
                     agentEventDescription }
        DESCRIPTION
             "Unexpeced mirror clone condition after mirror operation."
           --#TYPE      "Management Agent Event 10115"
           --#SUMMARY   "Host %s : SCellName-TimeDate %s : EventCode %d : Description %s"
           --#ARGUMENTS {0,1,2,3,}
            --#SEVERITY  MINOR
            --#TIMEINDEX 136
        ::= 136010115

   mngmtAgentTrap-10116 TRAP-TYPE
        ENTERPRISE compaq
        VARIABLES  { hostName,
                     scellNameDateTime,
                     agentEventCode,
                     agentEventDescription }
        DESCRIPTION
             "iSCSI controller pairing operation has been failed."
           --#TYPE      "Management Agent Event 10116"
           --#SUMMARY   "Host %s : SCellName-TimeDate %s : EventCode %d : Description %s"
           --#ARGUMENTS {0,1,2,3,}
            --#SEVERITY  INFORMATIONAL
            --#TIMEINDEX 136
        ::= 136010116

   mngmtAgentTrap-10117 TRAP-TYPE
        ENTERPRISE compaq
        VARIABLES  { hostName,
                     scellNameDateTime,
                     agentEventCode,
                     agentEventDescription }
        DESCRIPTION
             "iSCSI controller pairing not available."
           --#TYPE      "Management Agent Event 10117"
           --#SUMMARY   "Host %s : SCellName-TimeDate %s : EventCode %d : Description %s"
           --#ARGUMENTS {0,1,2,3,}
            --#SEVERITY  INFORMATIONAL
            --#TIMEINDEX 136
        ::= 136010117

   mngmtAgentTrap-10118 TRAP-TYPE
        ENTERPRISE compaq
        VARIABLES  { hostName,
                     scellNameDateTime,
                     agentEventCode,
                     agentEventDescription }
        DESCRIPTION
             "iSCSI controller remove pairing operation has been failed."
           --#TYPE      "Management Agent Event 10118"
           --#SUMMARY   "Host %s : SCellName-TimeDate %s : EventCode %d : Description %s"
           --#ARGUMENTS {0,1,2,3,}
            --#SEVERITY  INFORMATIONAL
            --#TIMEINDEX 136
        ::= 136010118

   mngmtAgentTrap-10121 TRAP-TYPE
        ENTERPRISE compaq
        VARIABLES  { hostName,
                     scellNameDateTime,
                     agentEventCode,
                     agentEventDescription }
        DESCRIPTION
             "Successfully enabled Enhanced Connectivity option for the discovered iSCSI Controllers."
           --#TYPE      "Management Agent Event 10121"
           --#SUMMARY   "Host %s : SCellName-TimeDate %s : EventCode %d : Description %s"
           --#ARGUMENTS {0,1,2,3,}
            --#SEVERITY  INFORMATIONAL
            --#TIMEINDEX 136
        ::= 136010121

   mngmtAgentTrap-10122 TRAP-TYPE
        ENTERPRISE compaq
        VARIABLES  { hostName,
                     scellNameDateTime,
                     agentEventCode,
                     agentEventDescription }
        DESCRIPTION
             "Enabling Enhanced Connectivity option for the discovered iSCSI Controllers has been unsuccessful."
           --#TYPE      "Management Agent Event 10122"
           --#SUMMARY   "Host %s : SCellName-TimeDate %s : EventCode %d : Description %s"
           --#ARGUMENTS {0,1,2,3,}
            --#SEVERITY  MINOR
            --#TIMEINDEX 136
        ::= 136010122

   mngmtAgentTrap-11001 TRAP-TYPE
        ENTERPRISE compaq
        VARIABLES  { hostName,
                     scellNameDateTime,
                     agentEventCode,
                     agentEventDescription }
        DESCRIPTION
             "Agent startup complete"
           --#TYPE      "Management Agent Event 11001"
           --#SUMMARY   "Host %s : SCellName-TimeDate %s : EventCode %d : Description %s"
           --#ARGUMENTS {0,1,2,3,}
            --#SEVERITY  INFORMATIONAL
            --#TIMEINDEX 136
        ::= 136011001

   mngmtAgentTrap-11002 TRAP-TYPE
        ENTERPRISE compaq
        VARIABLES  { hostName,
                     scellNameDateTime,
                     agentEventCode,
                     agentEventDescription }
        DESCRIPTION
             "Agent shutdown complete"
           --#TYPE      "Management Agent Event 11002"
           --#SUMMARY   "Host %s : SCellName-TimeDate %s : EventCode %d : Description %s"
           --#ARGUMENTS {0,1,2,3,}
            --#SEVERITY  INFORMATIONAL
            --#TIMEINDEX 136
        ::= 136011002

   mngmtAgentTrap-11003 TRAP-TYPE
        ENTERPRISE compaq
        VARIABLES  { hostName,
                     scellNameDateTime,
                     agentEventCode,
                     agentEventDescription }
        DESCRIPTION
             "Insufficient memory to create a new object, Heap may be full!"
           --#TYPE      "Management Agent Event 11003"
           --#SUMMARY   "Host %s : SCellName-TimeDate %s : EventCode %d : Description %s"
           --#ARGUMENTS {0,1,2,3,}
            --#SEVERITY  CRITICAL
            --#TIMEINDEX 136
        ::= 136011003

   mngmtAgentTrap-11004 TRAP-TYPE
        ENTERPRISE compaq
        VARIABLES  { hostName,
                     scellNameDateTime,
                     agentEventCode,
                     agentEventDescription }
        DESCRIPTION
             "Agent Startup Failed"
           --#TYPE      "Management Agent Event 11004"
           --#SUMMARY   "Host %s : SCellName-TimeDate %s : EventCode %d : Description %s"
           --#ARGUMENTS {0,1,2,3,}
            --#SEVERITY  CRITICAL
            --#TIMEINDEX 136
        ::= 136011004

   mngmtAgentTrap-12001 TRAP-TYPE
        ENTERPRISE compaq
        VARIABLES  { hostName,
                     scellNameDateTime,
                     agentEventCode,
                     agentEventDescription }
        DESCRIPTION
             "Nsc Manager Interface No controllers Found"
           --#TYPE      "Management Agent Event 12001"
           --#SUMMARY   "Host %s : SCellName-TimeDate %s : EventCode %d : Description %s"
           --#ARGUMENTS {0,1,2,3,}
            --#SEVERITY  INFORMATIONAL
            --#TIMEINDEX 136
        ::= 136012001

   mngmtAgentTrap-12002 TRAP-TYPE
        ENTERPRISE compaq
        VARIABLES  { hostName,
                     scellNameDateTime,
                     agentEventCode,
                     agentEventDescription }
        DESCRIPTION
             "Nsc Manager Interface Index Out Of Range"
           --#TYPE      "Management Agent Event 12002"
           --#SUMMARY   "Host %s : SCellName-TimeDate %s : EventCode %d : Description %s"
           --#ARGUMENTS {0,1,2,3,}
            --#SEVERITY  INFORMATIONAL
            --#TIMEINDEX 136
        ::= 136012002

   mngmtAgentTrap-12003 TRAP-TYPE
        ENTERPRISE compaq
        VARIABLES  { hostName,
                     scellNameDateTime,
                     agentEventCode,
                     agentEventDescription }
        DESCRIPTION
             "Unable to process command at this time. Retry the command or check all connections."
           --#TYPE      "Management Agent Event 12003"
           --#SUMMARY   "Host %s : SCellName-TimeDate %s : EventCode %d : Description %s"
           --#ARGUMENTS {0,1,2,3,}
            --#SEVERITY  INFORMATIONAL
            --#TIMEINDEX 136
        ::= 136012003

   mngmtAgentTrap-12004 TRAP-TYPE
        ENTERPRISE compaq
        VARIABLES  { hostName,
                     scellNameDateTime,
                     agentEventCode,
                     agentEventDescription }
        DESCRIPTION
             "Nsc Manager Interface Initialization Complete"
           --#TYPE      "Management Agent Event 12004"
           --#SUMMARY   "Host %s : SCellName-TimeDate %s : EventCode %d : Description %s"
           --#ARGUMENTS {0,1,2,3,}
            --#SEVERITY  INFORMATIONAL
            --#TIMEINDEX 136
        ::= 136012004

   mngmtAgentTrap-12005 TRAP-TYPE
        ENTERPRISE compaq
        VARIABLES  { hostName,
                     scellNameDateTime,
                     agentEventCode,
                     agentEventDescription }
        DESCRIPTION
             "Nsc Manager Interface Initialization Failed"
           --#TYPE      "Management Agent Event 12005"
           --#SUMMARY   "Host %s : SCellName-TimeDate %s : EventCode %d : Description %s"
           --#ARGUMENTS {0,1,2,3,}
            --#SEVERITY  INFORMATIONAL
            --#TIMEINDEX 136
        ::= 136012005

   mngmtAgentTrap-12008 TRAP-TYPE
        ENTERPRISE compaq
        VARIABLES  { hostName,
                     scellNameDateTime,
                     agentEventCode,
                     agentEventDescription }
        DESCRIPTION
             "No Disk Groups Available For Access"
           --#TYPE      "Management Agent Event 12008"
           --#SUMMARY   "Host %s : SCellName-TimeDate %s : EventCode %d : Description %s"
           --#ARGUMENTS {0,1,2,3,}
            --#SEVERITY  INFORMATIONAL
            --#TIMEINDEX 136
        ::= 136012008

   mngmtAgentTrap-13002 TRAP-TYPE
        ENTERPRISE compaq
        VARIABLES  { hostName,
                     scellNameDateTime,
                     agentEventCode,
                     agentEventDescription }
        DESCRIPTION
             "Notification Mngr Online"
           --#TYPE      "Management Agent Event 13002"
           --#SUMMARY   "Host %s : SCellName-TimeDate %s : EventCode %d : Description %s"
           --#ARGUMENTS {0,1,2,3,}
            --#SEVERITY  INFORMATIONAL
            --#TIMEINDEX 136
        ::= 136013002

   mngmtAgentTrap-13003 TRAP-TYPE
        ENTERPRISE compaq
        VARIABLES  { hostName,
                     scellNameDateTime,
                     agentEventCode,
                     agentEventDescription }
        DESCRIPTION
             "Notification Mngr Offline"
           --#TYPE      "Management Agent Event 13003"
           --#SUMMARY   "Host %s : SCellName-TimeDate %s : EventCode %d : Description %s"
           --#ARGUMENTS {0,1,2,3,}
            --#SEVERITY  INFORMATIONAL
            --#TIMEINDEX 136
        ::= 136013003

   mngmtAgentTrap-13004 TRAP-TYPE
        ENTERPRISE compaq
        VARIABLES  { hostName,
                     scellNameDateTime,
                     agentEventCode,
                     agentEventDescription }
        DESCRIPTION
             "NM Startup Complete"
           --#TYPE      "Management Agent Event 13004"
           --#SUMMARY   "Host %s : SCellName-TimeDate %s : EventCode %d : Description %s"
           --#ARGUMENTS {0,1,2,3,}
            --#SEVERITY  INFORMATIONAL
            --#TIMEINDEX 136
        ::= 136013004

   mngmtAgentTrap-13007 TRAP-TYPE
        ENTERPRISE compaq
        VARIABLES  { hostName,
                     scellNameDateTime,
                     agentEventCode,
                     agentEventDescription }
        DESCRIPTION
             "Notification Failed"
           --#TYPE      "Management Agent Event 13007"
           --#SUMMARY   "Host %s : SCellName-TimeDate %s : EventCode %d : Description %s"
           --#ARGUMENTS {0,1,2,3,}
            --#SEVERITY  CRITICAL
            --#TIMEINDEX 136
        ::= 136013007

   mngmtAgentTrap-13009 TRAP-TYPE
        ENTERPRISE compaq
        VARIABLES  { hostName,
                     scellNameDateTime,
                     agentEventCode,
                     agentEventDescription }
        DESCRIPTION
             "Notification Failed - Network Error"
           --#TYPE      "Management Agent Event 13009"
           --#SUMMARY   "Host %s : SCellName-TimeDate %s : EventCode %d : Description %s"
           --#ARGUMENTS {0,1,2,3,}
            --#SEVERITY  CRITICAL
            --#TIMEINDEX 136
        ::= 136013009

   mngmtAgentTrap-13012 TRAP-TYPE
        ENTERPRISE compaq
        VARIABLES  { hostName,
                     scellNameDateTime,
                     agentEventCode,
                     agentEventDescription }
        DESCRIPTION
             "NM Prev Failed Notification Successfully Notified"
           --#TYPE      "Management Agent Event 13012"
           --#SUMMARY   "Host %s : SCellName-TimeDate %s : EventCode %d : Description %s"
           --#ARGUMENTS {0,1,2,3,}
            --#SEVERITY  INFORMATIONAL
            --#TIMEINDEX 136
        ::= 136013012

   mngmtAgentTrap-13015 TRAP-TYPE
        ENTERPRISE compaq
        VARIABLES  { hostName,
                     scellNameDateTime,
                     agentEventCode,
                     agentEventDescription }
        DESCRIPTION
             "NM SNMP Packet Failed"
           --#TYPE      "Management Agent Event 13015"
           --#SUMMARY   "Host %s : SCellName-TimeDate %s : EventCode %d : Description %s"
           --#ARGUMENTS {0,1,2,3,}
            --#SEVERITY  CRITICAL
            --#TIMEINDEX 136
        ::= 136013015

   mngmtAgentTrap-13017 TRAP-TYPE
        ENTERPRISE compaq
        VARIABLES  { hostName,
                     scellNameDateTime,
                     agentEventCode,
                     agentEventDescription }
        DESCRIPTION
             "NM Memory Allocation Error"
           --#TYPE      "Management Agent Event 13017"
           --#SUMMARY   "Host %s : SCellName-TimeDate %s : EventCode %d : Description %s"
           --#ARGUMENTS {0,1,2,3,}
            --#SEVERITY  CRITICAL
            --#TIMEINDEX 136
        ::= 136013017

   mngmtAgentTrap-13018 TRAP-TYPE
        ENTERPRISE compaq
        VARIABLES  { hostName,
                     scellNameDateTime,
                     agentEventCode,
                     agentEventDescription }
        DESCRIPTION
             "NM StorageCell handle is NULL"
           --#TYPE      "Management Agent Event 13018"
           --#SUMMARY   "Host %s : SCellName-TimeDate %s : EventCode %d : Description %s"
           --#ARGUMENTS {0,1,2,3,}
            --#SEVERITY  CRITICAL
            --#TIMEINDEX 136
        ::= 136013018

   mngmtAgentTrap-13019 TRAP-TYPE
        ENTERPRISE compaq
        VARIABLES  { hostName,
                     scellNameDateTime,
                     agentEventCode,
                     agentEventDescription }
        DESCRIPTION
             "NM User defined event state file is empty"
           --#TYPE      "Management Agent Event 13019"
           --#SUMMARY   "Host %s : SCellName-TimeDate %s : EventCode %d : Description %s"
           --#ARGUMENTS {0,1,2,3,}
            --#SEVERITY  INFORMATIONAL
            --#TIMEINDEX 136
        ::= 136013019

   mngmtAgentTrap-13020 TRAP-TYPE
        ENTERPRISE compaq
        VARIABLES  { hostName,
                     scellNameDateTime,
                     agentEventCode,
                     agentEventDescription }
        DESCRIPTION
             "NM Notification Failed - Notification Matrix is NULL"
           --#TYPE      "Management Agent Event 13020"
           --#SUMMARY   "Host %s : SCellName-TimeDate %s : EventCode %d : Description %s"
           --#ARGUMENTS {0,1,2,3,}
            --#SEVERITY  MINOR
            --#TIMEINDEX 136
        ::= 136013020

   mngmtAgentTrap-13021 TRAP-TYPE
        ENTERPRISE compaq
        VARIABLES  { hostName,
                     scellNameDateTime,
                     agentEventCode,
                     agentEventDescription }
        DESCRIPTION
             "Remote Service Test Event"
           --#TYPE      "Management Agent Event 13021"
           --#SUMMARY   "Host %s : SCellName-TimeDate %s : EventCode %d : Description %s"
           --#ARGUMENTS {0,1,2,3,}
            --#SEVERITY  INFORMATIONAL
            --#TIMEINDEX 136
        ::= 136013021

   mngmtAgentTrap-13022 TRAP-TYPE
        ENTERPRISE compaq
        VARIABLES  { hostName,
                     scellNameDateTime,
                     agentEventCode,
                     agentEventDescription }
        DESCRIPTION
             "User initiated service mode begin"
           --#TYPE      "Management Agent Event 13022"
           --#SUMMARY   "Host %s : SCellName-TimeDate %s : EventCode %d : Description %s"
           --#ARGUMENTS {0,1,2,3,}
            --#SEVERITY  INFORMATIONAL
            --#TIMEINDEX 136
        ::= 136013022

   mngmtAgentTrap-13023 TRAP-TYPE
        ENTERPRISE compaq
        VARIABLES  { hostName,
                     scellNameDateTime,
                     agentEventCode,
                     agentEventDescription }
        DESCRIPTION
             "User initiated service mode end"
           --#TYPE      "Management Agent Event 13023"
           --#SUMMARY   "Host %s : SCellName-TimeDate %s : EventCode %d : Description %s"
           --#ARGUMENTS {0,1,2,3,}
            --#SEVERITY  INFORMATIONAL
            --#TIMEINDEX 136
        ::= 136013023

   mngmtAgentTrap-13024 TRAP-TYPE
        ENTERPRISE compaq
        VARIABLES  { hostName,
                     scellNameDateTime,
                     agentEventCode,
                     agentEventDescription }
        DESCRIPTION
             "Email not sent - SMTP server not configured for AUTH LOGIN and CV configured for authentication - {1}"
           --#TYPE      "Management Agent Event 13024"
           --#SUMMARY   "Host %s : SCellName-TimeDate %s : EventCode %d : Description %s"
           --#ARGUMENTS {0,1,2,3,}
            --#SEVERITY  CRITICAL
            --#TIMEINDEX 136
        ::= 136013024

   mngmtAgentTrap-13025 TRAP-TYPE
        ENTERPRISE compaq
        VARIABLES  { hostName,
                     scellNameDateTime,
                     agentEventCode,
                     agentEventDescription }
        DESCRIPTION
             "Email not sent - Error sending email to SMTP server - {1} - {2}"
           --#TYPE      "Management Agent Event 13025"
           --#SUMMARY   "Host %s : SCellName-TimeDate %s : EventCode %d : Description %s"
           --#ARGUMENTS {0,1,2,3,}
            --#SEVERITY  CRITICAL
            --#TIMEINDEX 136
        ::= 136013025

   mngmtAgentTrap-13026 TRAP-TYPE
        ENTERPRISE compaq
        VARIABLES  { hostName,
                     scellNameDateTime,
                     agentEventCode,
                     agentEventDescription }
        DESCRIPTION
             "Unable to set the heart beat configuration"
           --#TYPE      "Management Agent Event 13026"
           --#SUMMARY   "Host %s : SCellName-TimeDate %s : EventCode %d : Description %s"
           --#ARGUMENTS {0,1,2,3,}
            --#SEVERITY  INFORMATIONAL
            --#TIMEINDEX 136
        ::= 136013026

   mngmtAgentTrap-13027 TRAP-TYPE
        ENTERPRISE compaq
        VARIABLES  { hostName,
                     scellNameDateTime,
                     agentEventCode,
                     agentEventDescription }
        DESCRIPTION
             "Heart beat interval should be an integer between values 2 and 720"
           --#TYPE      "Management Agent Event 13027"
           --#SUMMARY   "Host %s : SCellName-TimeDate %s : EventCode %d : Description %s"
           --#ARGUMENTS {0,1,2,3,}
            --#SEVERITY  INFORMATIONAL
            --#TIMEINDEX 136
        ::= 136013027

   mngmtAgentTrap-14001 TRAP-TYPE
        ENTERPRISE compaq
        VARIABLES  { hostName,
                     scellNameDateTime,
                     agentEventCode,
                     agentEventDescription }
        DESCRIPTION
             "View Already Exists"
           --#TYPE      "Management Agent Event 14001"
           --#SUMMARY   "Host %s : SCellName-TimeDate %s : EventCode %d : Description %s"
           --#ARGUMENTS {0,1,2,3,}
            --#SEVERITY  INFORMATIONAL
            --#TIMEINDEX 136
        ::= 136014001

   mngmtAgentTrap-14002 TRAP-TYPE
        ENTERPRISE compaq
        VARIABLES  { hostName,
                     scellNameDateTime,
                     agentEventCode,
                     agentEventDescription }
        DESCRIPTION
             "View Is Not Set"
           --#TYPE      "Management Agent Event 14002"
           --#SUMMARY   "Host %s : SCellName-TimeDate %s : EventCode %d : Description %s"
           --#ARGUMENTS {0,1,2,3,}
            --#SEVERITY  INFORMATIONAL
            --#TIMEINDEX 136
        ::= 136014002

   mngmtAgentTrap-14003 TRAP-TYPE
        ENTERPRISE compaq
        VARIABLES  { hostName,
                     scellNameDateTime,
                     agentEventCode,
                     agentEventDescription }
        DESCRIPTION
             "Object not found in View"
           --#TYPE      "Management Agent Event 14003"
           --#SUMMARY   "Host %s : SCellName-TimeDate %s : EventCode %d : Description %s"
           --#ARGUMENTS {0,1,2,3,}
            --#SEVERITY  INFORMATIONAL
            --#TIMEINDEX 136
        ::= 136014003

   mngmtAgentTrap-14004 TRAP-TYPE
        ENTERPRISE compaq
        VARIABLES  { hostName,
                     scellNameDateTime,
                     agentEventCode,
                     agentEventDescription }
        DESCRIPTION
             "View Index Is Out Of Range"
           --#TYPE      "Management Agent Event 14004"
           --#SUMMARY   "Host %s : SCellName-TimeDate %s : EventCode %d : Description %s"
           --#ARGUMENTS {0,1,2,3,}
            --#SEVERITY  INFORMATIONAL
            --#TIMEINDEX 136
        ::= 136014004

   mngmtAgentTrap-14005 TRAP-TYPE
        ENTERPRISE compaq
        VARIABLES  { hostName,
                     scellNameDateTime,
                     agentEventCode,
                     agentEventDescription }
        DESCRIPTION
             "View Object - Invalid Object Condition"
           --#TYPE      "Management Agent Event 14005"
           --#SUMMARY   "Host %s : SCellName-TimeDate %s : EventCode %d : Description %s"
           --#ARGUMENTS {0,1,2,3,}
            --#SEVERITY  INFORMATIONAL
            --#TIMEINDEX 136
        ::= 136014005

   mngmtAgentTrap-14006 TRAP-TYPE
        ENTERPRISE compaq
        VARIABLES  { hostName,
                     scellNameDateTime,
                     agentEventCode,
                     agentEventDescription }
        DESCRIPTION
             "View Object - Invalid Object Type"
           --#TYPE      "Management Agent Event 14006"
           --#SUMMARY   "Host %s : SCellName-TimeDate %s : EventCode %d : Description %s"
           --#ARGUMENTS {0,1,2,3,}
            --#SEVERITY  INFORMATIONAL
            --#TIMEINDEX 136
        ::= 136014006

   mngmtAgentTrap-14007 TRAP-TYPE
        ENTERPRISE compaq
        VARIABLES  { hostName,
                     scellNameDateTime,
                     agentEventCode,
                     agentEventDescription }
        DESCRIPTION
             "View is not built."
           --#TYPE      "Management Agent Event 14007"
           --#SUMMARY   "Host %s : SCellName-TimeDate %s : EventCode %d : Description %s"
           --#ARGUMENTS {0,1,2,3,}
            --#SEVERITY  MINOR
            --#TIMEINDEX 136
        ::= 136014007

   mngmtAgentTrap-14008 TRAP-TYPE
        ENTERPRISE compaq
        VARIABLES  { hostName,
                     scellNameDateTime,
                     agentEventCode,
                     agentEventDescription }
        DESCRIPTION
             "View Object does not exist."
           --#TYPE      "Management Agent Event 14008"
           --#SUMMARY   "Host %s : SCellName-TimeDate %s : EventCode %d : Description %s"
           --#ARGUMENTS {0,1,2,3,}
            --#SEVERITY  MINOR
            --#TIMEINDEX 136
        ::= 136014008

   mngmtAgentTrap-14009 TRAP-TYPE
        ENTERPRISE compaq
        VARIABLES  { hostName,
                     scellNameDateTime,
                     agentEventCode,
                     agentEventDescription }
        DESCRIPTION
             "Building View List Object - Complete"
           --#TYPE      "Management Agent Event 14009"
           --#SUMMARY   "Host %s : SCellName-TimeDate %s : EventCode %d : Description %s"
           --#ARGUMENTS {0,1,2,3,}
            --#SEVERITY  INFORMATIONAL
            --#TIMEINDEX 136
        ::= 136014009

   mngmtAgentTrap-14010 TRAP-TYPE
        ENTERPRISE compaq
        VARIABLES  { hostName,
                     scellNameDateTime,
                     agentEventCode,
                     agentEventDescription }
        DESCRIPTION
             "Building View List Object - Failed. Please refer to management event log for details."
           --#TYPE      "Management Agent Event 14010"
           --#SUMMARY   "Host %s : SCellName-TimeDate %s : EventCode %d : Description %s"
           --#ARGUMENTS {0,1,2,3,}
            --#SEVERITY  MINOR
            --#TIMEINDEX 136
        ::= 136014010

   mngmtAgentTrap-14012 TRAP-TYPE
        ENTERPRISE compaq
        VARIABLES  { hostName,
                     scellNameDateTime,
                     agentEventCode,
                     agentEventDescription }
        DESCRIPTION
             "View Find by UID Failed"
           --#TYPE      "Management Agent Event 14012"
           --#SUMMARY   "Host %s : SCellName-TimeDate %s : EventCode %d : Description %s"
           --#ARGUMENTS {0,1,2,3,}
            --#SEVERITY  INFORMATIONAL
            --#TIMEINDEX 136
        ::= 136014012

   mngmtAgentTrap-14013 TRAP-TYPE
        ENTERPRISE compaq
        VARIABLES  { hostName,
                     scellNameDateTime,
                     agentEventCode,
                     agentEventDescription }
        DESCRIPTION
             "View Find by Type Failed"
           --#TYPE      "Management Agent Event 14013"
           --#SUMMARY   "Host %s : SCellName-TimeDate %s : EventCode %d : Description %s"
           --#ARGUMENTS {0,1,2,3,}
            --#SEVERITY  INFORMATIONAL
            --#TIMEINDEX 136
        ::= 136014013

   mngmtAgentTrap-14017 TRAP-TYPE
        ENTERPRISE compaq
        VARIABLES  { hostName,
                     scellNameDateTime,
                     agentEventCode,
                     agentEventDescription }
        DESCRIPTION
             "View Find by Type by Name Failed"
           --#TYPE      "Management Agent Event 14017"
           --#SUMMARY   "Host %s : SCellName-TimeDate %s : EventCode %d : Description %s"
           --#ARGUMENTS {0,1,2,3,}
            --#SEVERITY  INFORMATIONAL
            --#TIMEINDEX 136
        ::= 136014017

   mngmtAgentTrap-14019 TRAP-TYPE
        ENTERPRISE compaq
        VARIABLES  { hostName,
                     scellNameDateTime,
                     agentEventCode,
                     agentEventDescription }
        DESCRIPTION
             "There are no good candidates from which to restore.  Possible candidiates may be presented or in an invalid condition."
           --#TYPE      "Management Agent Event 14019"
           --#SUMMARY   "Host %s : SCellName-TimeDate %s : EventCode %d : Description %s"
           --#ARGUMENTS {0,1,2,3,}
            --#SEVERITY  INFORMATIONAL
            --#TIMEINDEX 136
        ::= 136014019

   mngmtAgentTrap-15001 TRAP-TYPE
        ENTERPRISE compaq
        VARIABLES  { hostName,
                     scellNameDateTime,
                     agentEventCode,
                     agentEventDescription }
        DESCRIPTION
             "Tree View Symbol Not Found"
           --#TYPE      "Management Agent Event 15001"
           --#SUMMARY   "Host %s : SCellName-TimeDate %s : EventCode %d : Description %s"
           --#ARGUMENTS {0,1,2,3,}
            --#SEVERITY  INFORMATIONAL
            --#TIMEINDEX 136
        ::= 136015001

   mngmtAgentTrap-15002 TRAP-TYPE
        ENTERPRISE compaq
        VARIABLES  { hostName,
                     scellNameDateTime,
                     agentEventCode,
                     agentEventDescription }
        DESCRIPTION
             "Tree View Id Symbol Not Found"
           --#TYPE      "Management Agent Event 15002"
           --#SUMMARY   "Host %s : SCellName-TimeDate %s : EventCode %d : Description %s"
           --#ARGUMENTS {0,1,2,3,}
            --#SEVERITY  INFORMATIONAL
            --#TIMEINDEX 136
        ::= 136015002

   mngmtAgentTrap-15003 TRAP-TYPE
        ENTERPRISE compaq
        VARIABLES  { hostName,
                     scellNameDateTime,
                     agentEventCode,
                     agentEventDescription }
        DESCRIPTION
             "Tree Cursor Symbol Not Found"
           --#TYPE      "Management Agent Event 15003"
           --#SUMMARY   "Host %s : SCellName-TimeDate %s : EventCode %d : Description %s"
           --#ARGUMENTS {0,1,2,3,}
            --#SEVERITY  INFORMATIONAL
            --#TIMEINDEX 136
        ::= 136015003

   mngmtAgentTrap-15004 TRAP-TYPE
        ENTERPRISE compaq
        VARIABLES  { hostName,
                     scellNameDateTime,
                     agentEventCode,
                     agentEventDescription }
        DESCRIPTION
             "Tree Cursor Id Symbol Not Found"
           --#TYPE      "Management Agent Event 15004"
           --#SUMMARY   "Host %s : SCellName-TimeDate %s : EventCode %d : Description %s"
           --#ARGUMENTS {0,1,2,3,}
            --#SEVERITY  INFORMATIONAL
            --#TIMEINDEX 136
        ::= 136015004

   mngmtAgentTrap-15005 TRAP-TYPE
        ENTERPRISE compaq
        VARIABLES  { hostName,
                     scellNameDateTime,
                     agentEventCode,
                     agentEventDescription }
        DESCRIPTION
             "Tree Sibling Symbol Not Found"
           --#TYPE      "Management Agent Event 15005"
           --#SUMMARY   "Host %s : SCellName-TimeDate %s : EventCode %d : Description %s"
           --#ARGUMENTS {0,1,2,3,}
            --#SEVERITY  INFORMATIONAL
            --#TIMEINDEX 136
        ::= 136015005

   mngmtAgentTrap-15006 TRAP-TYPE
        ENTERPRISE compaq
        VARIABLES  { hostName,
                     scellNameDateTime,
                     agentEventCode,
                     agentEventDescription }
        DESCRIPTION
             "Tree Total Children Symbol Not Found"
           --#TYPE      "Management Agent Event 15006"
           --#SUMMARY   "Host %s : SCellName-TimeDate %s : EventCode %d : Description %s"
           --#ARGUMENTS {0,1,2,3,}
            --#SEVERITY  INFORMATIONAL
            --#TIMEINDEX 136
        ::= 136015006

   mngmtAgentTrap-15007 TRAP-TYPE
        ENTERPRISE compaq
        VARIABLES  { hostName,
                     scellNameDateTime,
                     agentEventCode,
                     agentEventDescription }
        DESCRIPTION
             "Tree Expansion Symbol Not Found"
           --#TYPE      "Management Agent Event 15007"
           --#SUMMARY   "Host %s : SCellName-TimeDate %s : EventCode %d : Description %s"
           --#ARGUMENTS {0,1,2,3,}
            --#SEVERITY  INFORMATIONAL
            --#TIMEINDEX 136
        ::= 136015007

   mngmtAgentTrap-15008 TRAP-TYPE
        ENTERPRISE compaq
        VARIABLES  { hostName,
                     scellNameDateTime,
                     agentEventCode,
                     agentEventDescription }
        DESCRIPTION
             "Tree Contraction Symbol Not Found"
           --#TYPE      "Management Agent Event 15008"
           --#SUMMARY   "Host %s : SCellName-TimeDate %s : EventCode %d : Description %s"
           --#ARGUMENTS {0,1,2,3,}
            --#SEVERITY  INFORMATIONAL
            --#TIMEINDEX 136
        ::= 136015008

   mngmtAgentTrap-15009 TRAP-TYPE
        ENTERPRISE compaq
        VARIABLES  { hostName,
                     scellNameDateTime,
                     agentEventCode,
                     agentEventDescription }
        DESCRIPTION
             "Tree Invalid Descriptor String"
           --#TYPE      "Management Agent Event 15009"
           --#SUMMARY   "Host %s : SCellName-TimeDate %s : EventCode %d : Description %s"
           --#ARGUMENTS {0,1,2,3,}
            --#SEVERITY  INFORMATIONAL
            --#TIMEINDEX 136
        ::= 136015009

   mngmtAgentTrap-16001 TRAP-TYPE
        ENTERPRISE compaq
        VARIABLES  { hostName,
                     scellNameDateTime,
                     agentEventCode,
                     agentEventDescription }
        DESCRIPTION
             "Ema Short Status - Reissue Command"
           --#TYPE      "Management Agent Event 16001"
           --#SUMMARY   "Host %s : SCellName-TimeDate %s : EventCode %d : Description %s"
           --#ARGUMENTS {0,1,2,3,}
            --#SEVERITY  INFORMATIONAL
            --#TIMEINDEX 136
        ::= 136016001

   mngmtAgentTrap-16004 TRAP-TYPE
        ENTERPRISE compaq
        VARIABLES  { hostName,
                     scellNameDateTime,
                     agentEventCode,
                     agentEventDescription }
        DESCRIPTION
             "Ema Invalid Handle Set In Request Packet"
           --#TYPE      "Management Agent Event 16004"
           --#SUMMARY   "Host %s : SCellName-TimeDate %s : EventCode %d : Description %s"
           --#ARGUMENTS {0,1,2,3,}
            --#SEVERITY  INFORMATIONAL
            --#TIMEINDEX 136
        ::= 136016004

   mngmtAgentTrap-16005 TRAP-TYPE
        ENTERPRISE compaq
        VARIABLES  { hostName,
                     scellNameDateTime,
                     agentEventCode,
                     agentEventDescription }
        DESCRIPTION
             "Ema No Pstore At Referenced Location"
           --#TYPE      "Management Agent Event 16005"
           --#SUMMARY   "Host %s : SCellName-TimeDate %s : EventCode %d : Description %s"
           --#ARGUMENTS {0,1,2,3,}
            --#SEVERITY  INFORMATIONAL
            --#TIMEINDEX 136
        ::= 136016005

   mngmtAgentTrap-16008 TRAP-TYPE
        ENTERPRISE compaq
        VARIABLES  { hostName,
                     scellNameDateTime,
                     agentEventCode,
                     agentEventDescription }
        DESCRIPTION
             "Ema No Device Found"
           --#TYPE      "Management Agent Event 16008"
           --#SUMMARY   "Host %s : SCellName-TimeDate %s : EventCode %d : Description %s"
           --#ARGUMENTS {0,1,2,3,}
            --#SEVERITY  INFORMATIONAL
            --#TIMEINDEX 136
        ::= 136016008

   mngmtAgentTrap-16010 TRAP-TYPE
        ENTERPRISE compaq
        VARIABLES  { hostName,
                     scellNameDateTime,
                     agentEventCode,
                     agentEventDescription }
        DESCRIPTION
             "Ema Could Not Find SubEnclosure in Configuration List"
           --#TYPE      "Management Agent Event 16010"
           --#SUMMARY   "Host %s : SCellName-TimeDate %s : EventCode %d : Description %s"
           --#ARGUMENTS {0,1,2,3,}
            --#SEVERITY  INFORMATIONAL
            --#TIMEINDEX 136
        ::= 136016010

   mngmtAgentTrap-16012 TRAP-TYPE
        ENTERPRISE compaq
        VARIABLES  { hostName,
                     scellNameDateTime,
                     agentEventCode,
                     agentEventDescription }
        DESCRIPTION
             "Ema Non-specific error occurred"
           --#TYPE      "Management Agent Event 16012"
           --#SUMMARY   "Host %s : SCellName-TimeDate %s : EventCode %d : Description %s"
           --#ARGUMENTS {0,1,2,3,}
            --#SEVERITY  INFORMATIONAL
            --#TIMEINDEX 136
        ::= 136016012

   mngmtAgentTrap-16013 TRAP-TYPE
        ENTERPRISE compaq
        VARIABLES  { hostName,
                     scellNameDateTime,
                     agentEventCode,
                     agentEventDescription }
        DESCRIPTION
             "Ema Shelf WWN Could Not Be Accessed Through A Drive"
           --#TYPE      "Management Agent Event 16013"
           --#SUMMARY   "Host %s : SCellName-TimeDate %s : EventCode %d : Description %s"
           --#ARGUMENTS {0,1,2,3,}
            --#SEVERITY  INFORMATIONAL
            --#TIMEINDEX 136
        ::= 136016013

   mngmtAgentTrap-16014 TRAP-TYPE
        ENTERPRISE compaq
        VARIABLES  { hostName,
                     scellNameDateTime,
                     agentEventCode,
                     agentEventDescription }
        DESCRIPTION
             "Ema EMU Failed To Enter Primary Mode"
           --#TYPE      "Management Agent Event 16014"
           --#SUMMARY   "Host %s : SCellName-TimeDate %s : EventCode %d : Description %s"
           --#ARGUMENTS {0,1,2,3,}
            --#SEVERITY  INFORMATIONAL
            --#TIMEINDEX 136
        ::= 136016014

   mngmtAgentTrap-16015 TRAP-TYPE
        ENTERPRISE compaq
        VARIABLES  { hostName,
                     scellNameDateTime,
                     agentEventCode,
                     agentEventDescription }
        DESCRIPTION
             "Ema EMU Failed To Exit Primary Mode"
           --#TYPE      "Management Agent Event 16015"
           --#SUMMARY   "Host %s : SCellName-TimeDate %s : EventCode %d : Description %s"
           --#ARGUMENTS {0,1,2,3,}
            --#SEVERITY  INFORMATIONAL
            --#TIMEINDEX 136
        ::= 136016015

   mngmtAgentTrap-16016 TRAP-TYPE
        ENTERPRISE compaq
        VARIABLES  { hostName,
                     scellNameDateTime,
                     agentEventCode,
                     agentEventDescription }
        DESCRIPTION
             "Ema Downloaded File Does Not Contain Valid Fibre Channel Loader [status:1]"
           --#TYPE      "Management Agent Event 16016"
           --#SUMMARY   "Host %s : SCellName-TimeDate %s : EventCode %d : Description %s"
           --#ARGUMENTS {0,1,2,3,}
            --#SEVERITY  INFORMATIONAL
            --#TIMEINDEX 136
        ::= 136016016

   mngmtAgentTrap-16017 TRAP-TYPE
        ENTERPRISE compaq
        VARIABLES  { hostName,
                     scellNameDateTime,
                     agentEventCode,
                     agentEventDescription }
        DESCRIPTION
             "Ema Downloaded File Format Is Not Recognized [status:2]"
           --#TYPE      "Management Agent Event 16017"
           --#SUMMARY   "Host %s : SCellName-TimeDate %s : EventCode %d : Description %s"
           --#ARGUMENTS {0,1,2,3,}
            --#SEVERITY  INFORMATIONAL
            --#TIMEINDEX 136
        ::= 136016017

   mngmtAgentTrap-16018 TRAP-TYPE
        ENTERPRISE compaq
        VARIABLES  { hostName,
                     scellNameDateTime,
                     agentEventCode,
                     agentEventDescription }
        DESCRIPTION
             "Ema Incorrect Firmware In Downloaded File [status:3]"
           --#TYPE      "Management Agent Event 16018"
           --#SUMMARY   "Host %s : SCellName-TimeDate %s : EventCode %d : Description %s"
           --#ARGUMENTS {0,1,2,3,}
            --#SEVERITY  INFORMATIONAL
            --#TIMEINDEX 136
        ::= 136016018

   mngmtAgentTrap-16019 TRAP-TYPE
        ENTERPRISE compaq
        VARIABLES  { hostName,
                     scellNameDateTime,
                     agentEventCode,
                     agentEventDescription }
        DESCRIPTION
             "Ema Downloaded Loader is Too Large [status:4]"
           --#TYPE      "Management Agent Event 16019"
           --#SUMMARY   "Host %s : SCellName-TimeDate %s : EventCode %d : Description %s"
           --#ARGUMENTS {0,1,2,3,}
            --#SEVERITY  INFORMATIONAL
            --#TIMEINDEX 136
        ::= 136016019

   mngmtAgentTrap-16020 TRAP-TYPE
        ENTERPRISE compaq
        VARIABLES  { hostName,
                     scellNameDateTime,
                     agentEventCode,
                     agentEventDescription }
        DESCRIPTION
             "Ema Invalid Checksum [status:5]"
           --#TYPE      "Management Agent Event 16020"
           --#SUMMARY   "Host %s : SCellName-TimeDate %s : EventCode %d : Description %s"
           --#ARGUMENTS {0,1,2,3,}
            --#SEVERITY  INFORMATIONAL
            --#TIMEINDEX 136
        ::= 136016020

   mngmtAgentTrap-16021 TRAP-TYPE
        ENTERPRISE compaq
        VARIABLES  { hostName,
                     scellNameDateTime,
                     agentEventCode,
                     agentEventDescription }
        DESCRIPTION
             "Ema Previous Offset Plus Previous Length Not Equal To Current Offset [status:6]"
           --#TYPE      "Management Agent Event 16021"
           --#SUMMARY   "Host %s : SCellName-TimeDate %s : EventCode %d : Description %s"
           --#ARGUMENTS {0,1,2,3,}
            --#SEVERITY  INFORMATIONAL
            --#TIMEINDEX 136
        ::= 136016021

   mngmtAgentTrap-16022 TRAP-TYPE
        ENTERPRISE compaq
        VARIABLES  { hostName,
                     scellNameDateTime,
                     agentEventCode,
                     agentEventDescription }
        DESCRIPTION
             "Ema Downloaded Loader Terminated Incorrectly [status:7]"
           --#TYPE      "Management Agent Event 16022"
           --#SUMMARY   "Host %s : SCellName-TimeDate %s : EventCode %d : Description %s"
           --#ARGUMENTS {0,1,2,3,}
            --#SEVERITY  INFORMATIONAL
            --#TIMEINDEX 136
        ::= 136016022

   mngmtAgentTrap-16023 TRAP-TYPE
        ENTERPRISE compaq
        VARIABLES  { hostName,
                     scellNameDateTime,
                     agentEventCode,
                     agentEventDescription }
        DESCRIPTION
             "Ema EMU Out Of Memory [status:8]"
           --#TYPE      "Management Agent Event 16023"
           --#SUMMARY   "Host %s : SCellName-TimeDate %s : EventCode %d : Description %s"
           --#ARGUMENTS {0,1,2,3,}
            --#SEVERITY  INFORMATIONAL
            --#TIMEINDEX 136
        ::= 136016023

   mngmtAgentTrap-16024 TRAP-TYPE
        ENTERPRISE compaq
        VARIABLES  { hostName,
                     scellNameDateTime,
                     agentEventCode,
                     agentEventDescription }
        DESCRIPTION
             "Ema EMU CDB Timeout -- Download Aborted [status:9]"
           --#TYPE      "Management Agent Event 16024"
           --#SUMMARY   "Host %s : SCellName-TimeDate %s : EventCode %d : Description %s"
           --#ARGUMENTS {0,1,2,3,}
            --#SEVERITY  INFORMATIONAL
            --#TIMEINDEX 136
        ::= 136016024

   mngmtAgentTrap-16025 TRAP-TYPE
        ENTERPRISE compaq
        VARIABLES  { hostName,
                     scellNameDateTime,
                     agentEventCode,
                     agentEventDescription }
        DESCRIPTION
             "Ema EMU Internal State Machine Error [status:10]"
           --#TYPE      "Management Agent Event 16025"
           --#SUMMARY   "Host %s : SCellName-TimeDate %s : EventCode %d : Description %s"
           --#ARGUMENTS {0,1,2,3,}
            --#SEVERITY  INFORMATIONAL
            --#TIMEINDEX 136
        ::= 136016025

   mngmtAgentTrap-16026 TRAP-TYPE
        ENTERPRISE compaq
        VARIABLES  { hostName,
                     scellNameDateTime,
                     agentEventCode,
                     agentEventDescription }
        DESCRIPTION
             "Ema EMU Flash Erasure Failure [status:11]"
           --#TYPE      "Management Agent Event 16026"
           --#SUMMARY   "Host %s : SCellName-TimeDate %s : EventCode %d : Description %s"
           --#ARGUMENTS {0,1,2,3,}
            --#SEVERITY  INFORMATIONAL
            --#TIMEINDEX 136
        ::= 136016026

   mngmtAgentTrap-16027 TRAP-TYPE
        ENTERPRISE compaq
        VARIABLES  { hostName,
                     scellNameDateTime,
                     agentEventCode,
                     agentEventDescription }
        DESCRIPTION
             "Ema EMU In Primary Mode - Cannot Download To Primary EMU [status:12]"
           --#TYPE      "Management Agent Event 16027"
           --#SUMMARY   "Host %s : SCellName-TimeDate %s : EventCode %d : Description %s"
           --#ARGUMENTS {0,1,2,3,}
            --#SEVERITY  INFORMATIONAL
            --#TIMEINDEX 136
        ::= 136016027

   mngmtAgentTrap-16028 TRAP-TYPE
        ENTERPRISE compaq
        VARIABLES  { hostName,
                     scellNameDateTime,
                     agentEventCode,
                     agentEventDescription }
        DESCRIPTION
             "Ema Previous Offset Plus Previous Length Greater Than Total Size [status:13]"
           --#TYPE      "Management Agent Event 16028"
           --#SUMMARY   "Host %s : SCellName-TimeDate %s : EventCode %d : Description %s"
           --#ARGUMENTS {0,1,2,3,}
            --#SEVERITY  INFORMATIONAL
            --#TIMEINDEX 136
        ::= 136016028

   mngmtAgentTrap-16029 TRAP-TYPE
        ENTERPRISE compaq
        VARIABLES  { hostName,
                     scellNameDateTime,
                     agentEventCode,
                     agentEventDescription }
        DESCRIPTION
             "Ema Current Total Size Different From Previous Total Size [status:14]"
           --#TYPE      "Management Agent Event 16029"
           --#SUMMARY   "Host %s : SCellName-TimeDate %s : EventCode %d : Description %s"
           --#ARGUMENTS {0,1,2,3,}
            --#SEVERITY  INFORMATIONAL
            --#TIMEINDEX 136
        ::= 136016029

   mngmtAgentTrap-16030 TRAP-TYPE
        ENTERPRISE compaq
        VARIABLES  { hostName,
                     scellNameDateTime,
                     agentEventCode,
                     agentEventDescription }
        DESCRIPTION
             "Ema Could Not Restore Reporting Group Number. Final Download Record Error"
           --#TYPE      "Management Agent Event 16030"
           --#SUMMARY   "Host %s : SCellName-TimeDate %s : EventCode %d : Description %s"
           --#ARGUMENTS {0,1,2,3,}
            --#SEVERITY  INFORMATIONAL
            --#TIMEINDEX 136
        ::= 136016030

   mngmtAgentTrap-16031 TRAP-TYPE
        ENTERPRISE compaq
        VARIABLES  { hostName,
                     scellNameDateTime,
                     agentEventCode,
                     agentEventDescription }
        DESCRIPTION
             "Ema Could Not Recovery From Invop. Invop Retries Exhausted"
           --#TYPE      "Management Agent Event 16031"
           --#SUMMARY   "Host %s : SCellName-TimeDate %s : EventCode %d : Description %s"
           --#ARGUMENTS {0,1,2,3,}
            --#SEVERITY  INFORMATIONAL
            --#TIMEINDEX 136
        ::= 136016031

   mngmtAgentTrap-16032 TRAP-TYPE
        ENTERPRISE compaq
        VARIABLES  { hostName,
                     scellNameDateTime,
                     agentEventCode,
                     agentEventDescription }
        DESCRIPTION
             "Ema Requested WWN Does Not Match Enclosure WWN"
           --#TYPE      "Management Agent Event 16032"
           --#SUMMARY   "Host %s : SCellName-TimeDate %s : EventCode %d : Description %s"
           --#ARGUMENTS {0,1,2,3,}
            --#SEVERITY  INFORMATIONAL
            --#TIMEINDEX 136
        ::= 136016032

   mngmtAgentTrap-16033 TRAP-TYPE
        ENTERPRISE compaq
        VARIABLES  { hostName,
                     scellNameDateTime,
                     agentEventCode,
                     agentEventDescription }
        DESCRIPTION
             "Ema EMU Enclosure Services Error Occurred. EMU May Be Unavailable or Not Installed"
           --#TYPE      "Management Agent Event 16033"
           --#SUMMARY   "Host %s : SCellName-TimeDate %s : EventCode %d : Description %s"
           --#ARGUMENTS {0,1,2,3,}
            --#SEVERITY  CRITICAL
            --#TIMEINDEX 136
        ::= 136016033

   mngmtAgentTrap-16034 TRAP-TYPE
        ENTERPRISE compaq
        VARIABLES  { hostName,
                     scellNameDateTime,
                     agentEventCode,
                     agentEventDescription }
        DESCRIPTION
             "Ema SCSI Error Occurred While Trying To Communicate With EMU"
           --#TYPE      "Management Agent Event 16034"
           --#SUMMARY   "Host %s : SCellName-TimeDate %s : EventCode %d : Description %s"
           --#ARGUMENTS {0,1,2,3,}
            --#SEVERITY  INFORMATIONAL
            --#TIMEINDEX 136
        ::= 136016034

   mngmtAgentTrap-16035 TRAP-TYPE
        ENTERPRISE compaq
        VARIABLES  { hostName,
                     scellNameDateTime,
                     agentEventCode,
                     agentEventDescription }
        DESCRIPTION
             "Ema Could Not Open EMU Firmware File"
           --#TYPE      "Management Agent Event 16035"
           --#SUMMARY   "Host %s : SCellName-TimeDate %s : EventCode %d : Description %s"
           --#ARGUMENTS {0,1,2,3,}
            --#SEVERITY  INFORMATIONAL
            --#TIMEINDEX 136
        ::= 136016035

   mngmtAgentTrap-16036 TRAP-TYPE
        ENTERPRISE compaq
        VARIABLES  { hostName,
                     scellNameDateTime,
                     agentEventCode,
                     agentEventDescription }
        DESCRIPTION
             "Ema EMU Firmware File Name Is Null"
           --#TYPE      "Management Agent Event 16036"
           --#SUMMARY   "Host %s : SCellName-TimeDate %s : EventCode %d : Description %s"
           --#ARGUMENTS {0,1,2,3,}
            --#SEVERITY  INFORMATIONAL
            --#TIMEINDEX 136
        ::= 136016036

   mngmtAgentTrap-16037 TRAP-TYPE
        ENTERPRISE compaq
        VARIABLES  { hostName,
                     scellNameDateTime,
                     agentEventCode,
                     agentEventDescription }
        DESCRIPTION
             "Ema EMU Firmware Download Retries Exhausted. Manual Download May Be Required"
           --#TYPE      "Management Agent Event 16037"
           --#SUMMARY   "Host %s : SCellName-TimeDate %s : EventCode %d : Description %s"
           --#ARGUMENTS {0,1,2,3,}
            --#SEVERITY  INFORMATIONAL
            --#TIMEINDEX 136
        ::= 136016037

   mngmtAgentTrap-16038 TRAP-TYPE
        ENTERPRISE compaq
        VARIABLES  { hostName,
                     scellNameDateTime,
                     agentEventCode,
                     agentEventDescription }
        DESCRIPTION
             "Ema EMU Current Firmware Version Matches Upgrade Firmware Version. No Upgrade Will Be Performed."
           --#TYPE      "Management Agent Event 16038"
           --#SUMMARY   "Host %s : SCellName-TimeDate %s : EventCode %d : Description %s"
           --#ARGUMENTS {0,1,2,3,}
            --#SEVERITY  INFORMATIONAL
            --#TIMEINDEX 136
        ::= 136016038

   mngmtAgentTrap-16039 TRAP-TYPE
        ENTERPRISE compaq
        VARIABLES  { hostName,
                     scellNameDateTime,
                     agentEventCode,
                     agentEventDescription }
        DESCRIPTION
             "Ema EMU Firmware Upgrade Success"
           --#TYPE      "Management Agent Event 16039"
           --#SUMMARY   "Host %s : SCellName-TimeDate %s : EventCode %d : Description %s"
           --#ARGUMENTS {0,1,2,3,}
            --#SEVERITY  INFORMATIONAL
            --#TIMEINDEX 136
        ::= 136016039

   mngmtAgentTrap-16040 TRAP-TYPE
        ENTERPRISE compaq
        VARIABLES  { hostName,
                     scellNameDateTime,
                     agentEventCode,
                     agentEventDescription }
        DESCRIPTION
             "Ema EMU In Load State. Do Not Power Off. Reload EMU Firmware"
           --#TYPE      "Management Agent Event 16040"
           --#SUMMARY   "Host %s : SCellName-TimeDate %s : EventCode %d : Description %s"
           --#ARGUMENTS {0,1,2,3,}
            --#SEVERITY  INFORMATIONAL
            --#TIMEINDEX 136
        ::= 136016040

   mngmtAgentTrap-17001 TRAP-TYPE
        ENTERPRISE compaq
        VARIABLES  { hostName,
                     scellNameDateTime,
                     agentEventCode,
                     agentEventDescription }
        DESCRIPTION
             "Drive code load - The descriptor file could not be opened."
           --#TYPE      "Management Agent Event 17001"
           --#SUMMARY   "Host %s : SCellName-TimeDate %s : EventCode %d : Description %s"
           --#ARGUMENTS {0,1,2,3,}
            --#SEVERITY  INFORMATIONAL
            --#TIMEINDEX 136
        ::= 136017001

   mngmtAgentTrap-17002 TRAP-TYPE
        ENTERPRISE compaq
        VARIABLES  { hostName,
                     scellNameDateTime,
                     agentEventCode,
                     agentEventDescription }
        DESCRIPTION
             "Drive code load - The descriptor file could not be parsed because of an invalid line in the file."
           --#TYPE      "Management Agent Event 17002"
           --#SUMMARY   "Host %s : SCellName-TimeDate %s : EventCode %d : Description %s"
           --#ARGUMENTS {0,1,2,3,}
            --#SEVERITY  INFORMATIONAL
            --#TIMEINDEX 136
        ::= 136017002

   mngmtAgentTrap-17003 TRAP-TYPE
        ENTERPRISE compaq
        VARIABLES  { hostName,
                     scellNameDateTime,
                     agentEventCode,
                     agentEventDescription }
        DESCRIPTION
             "Drive code load - The image file could not be opened."
           --#TYPE      "Management Agent Event 17003"
           --#SUMMARY   "Host %s : SCellName-TimeDate %s : EventCode %d : Description %s"
           --#ARGUMENTS {0,1,2,3,}
            --#SEVERITY  INFORMATIONAL
            --#TIMEINDEX 136
        ::= 136017003

   mngmtAgentTrap-17004 TRAP-TYPE
        ENTERPRISE compaq
        VARIABLES  { hostName,
                     scellNameDateTime,
                     agentEventCode,
                     agentEventDescription }
        DESCRIPTION
             "Drive code load - The size of the image file could not be determined."
           --#TYPE      "Management Agent Event 17004"
           --#SUMMARY   "Host %s : SCellName-TimeDate %s : EventCode %d : Description %s"
           --#ARGUMENTS {0,1,2,3,}
            --#SEVERITY  INFORMATIONAL
            --#TIMEINDEX 136
        ::= 136017004

   mngmtAgentTrap-17005 TRAP-TYPE
        ENTERPRISE compaq
        VARIABLES  { hostName,
                     scellNameDateTime,
                     agentEventCode,
                     agentEventDescription }
        DESCRIPTION
             "Drive code load - A buffer could not be allocated for the image data."
           --#TYPE      "Management Agent Event 17005"
           --#SUMMARY   "Host %s : SCellName-TimeDate %s : EventCode %d : Description %s"
           --#ARGUMENTS {0,1,2,3,}
            --#SEVERITY  INFORMATIONAL
            --#TIMEINDEX 136
        ::= 136017005

   mngmtAgentTrap-17006 TRAP-TYPE
        ENTERPRISE compaq
        VARIABLES  { hostName,
                     scellNameDateTime,
                     agentEventCode,
                     agentEventDescription }
        DESCRIPTION
             "Drive code load - Image file read error."
           --#TYPE      "Management Agent Event 17006"
           --#SUMMARY   "Host %s : SCellName-TimeDate %s : EventCode %d : Description %s"
           --#ARGUMENTS {0,1,2,3,}
            --#SEVERITY  INFORMATIONAL
            --#TIMEINDEX 136
        ::= 136017006

   mngmtAgentTrap-17007 TRAP-TYPE
        ENTERPRISE compaq
        VARIABLES  { hostName,
                     scellNameDateTime,
                     agentEventCode,
                     agentEventDescription }
        DESCRIPTION
             "Drive code load - A failure occured while trying to update the drive firmware."
           --#TYPE      "Management Agent Event 17007"
           --#SUMMARY   "Host %s : SCellName-TimeDate %s : EventCode %d : Description %s"
           --#ARGUMENTS {0,1,2,3,}
            --#SEVERITY  CRITICAL
            --#TIMEINDEX 136
        ::= 136017007

   mngmtAgentTrap-17008 TRAP-TYPE
        ENTERPRISE compaq
        VARIABLES  { hostName,
                     scellNameDateTime,
                     agentEventCode,
                     agentEventDescription }
        DESCRIPTION
             "Drive code load - An inquiry sent to the drive failed."
           --#TYPE      "Management Agent Event 17008"
           --#SUMMARY   "Host %s : SCellName-TimeDate %s : EventCode %d : Description %s"
           --#ARGUMENTS {0,1,2,3,}
            --#SEVERITY  MINOR
            --#TIMEINDEX 136
        ::= 136017008

   mngmtAgentTrap-17009 TRAP-TYPE
        ENTERPRISE compaq
        VARIABLES  { hostName,
                     scellNameDateTime,
                     agentEventCode,
                     agentEventDescription }
        DESCRIPTION
             "Drive code load - The format command failed."
           --#TYPE      "Management Agent Event 17009"
           --#SUMMARY   "Host %s : SCellName-TimeDate %s : EventCode %d : Description %s"
           --#ARGUMENTS {0,1,2,3,}
            --#SEVERITY  MINOR
            --#TIMEINDEX 136
        ::= 136017009

   mngmtAgentTrap-17012 TRAP-TYPE
        ENTERPRISE compaq
        VARIABLES  { hostName,
                     scellNameDateTime,
                     agentEventCode,
                     agentEventDescription }
        DESCRIPTION
             "Drive code load - Unable to determine the condition of the physical store."
           --#TYPE      "Management Agent Event 17012"
           --#SUMMARY   "Host %s : SCellName-TimeDate %s : EventCode %d : Description %s"
           --#ARGUMENTS {0,1,2,3,}
            --#SEVERITY  INFORMATIONAL
            --#TIMEINDEX 136
        ::= 136017012

   mngmtAgentTrap-17013 TRAP-TYPE
        ENTERPRISE compaq
        VARIABLES  { hostName,
                     scellNameDateTime,
                     agentEventCode,
                     agentEventDescription }
        DESCRIPTION
             "Drive code load - Unable to determine the condition of the volume."
           --#TYPE      "Management Agent Event 17013"
           --#SUMMARY   "Host %s : SCellName-TimeDate %s : EventCode %d : Description %s"
           --#ARGUMENTS {0,1,2,3,}
            --#SEVERITY  INFORMATIONAL
            --#TIMEINDEX 136
        ::= 136017013

   mngmtAgentTrap-17014 TRAP-TYPE
        ENTERPRISE compaq
        VARIABLES  { hostName,
                     scellNameDateTime,
                     agentEventCode,
                     agentEventDescription }
        DESCRIPTION
             "Drive code load - The drive failed to spin up."
           --#TYPE      "Management Agent Event 17014"
           --#SUMMARY   "Host %s : SCellName-TimeDate %s : EventCode %d : Description %s"
           --#ARGUMENTS {0,1,2,3,}
            --#SEVERITY  MINOR
            --#TIMEINDEX 136
        ::= 136017014

   mngmtAgentTrap-17015 TRAP-TYPE
        ENTERPRISE compaq
        VARIABLES  { hostName,
                     scellNameDateTime,
                     agentEventCode,
                     agentEventDescription }
        DESCRIPTION
             "Drive code load - Complete"
           --#TYPE      "Management Agent Event 17015"
           --#SUMMARY   "Host %s : SCellName-TimeDate %s : EventCode %d : Description %s"
           --#ARGUMENTS {0,1,2,3,}
            --#SEVERITY  INFORMATIONAL
            --#TIMEINDEX 136
        ::= 136017015

   mngmtAgentTrap-17016 TRAP-TYPE
        ENTERPRISE compaq
        VARIABLES  { hostName,
                     scellNameDateTime,
                     agentEventCode,
                     agentEventDescription }
        DESCRIPTION
             "Drive code load - A disk group migration is in progress."
           --#TYPE      "Management Agent Event 17016"
           --#SUMMARY   "Host %s : SCellName-TimeDate %s : EventCode %d : Description %s"
           --#ARGUMENTS {0,1,2,3,}
            --#SEVERITY  INFORMATIONAL
            --#TIMEINDEX 136
        ::= 136017016

   mngmtAgentTrap-17017 TRAP-TYPE
        ENTERPRISE compaq
        VARIABLES  { hostName,
                     scellNameDateTime,
                     agentEventCode,
                     agentEventDescription }
        DESCRIPTION
             "Drive code load - The disk cannot be code loaded because it is part of a group."
           --#TYPE      "Management Agent Event 17017"
           --#SUMMARY   "Host %s : SCellName-TimeDate %s : EventCode %d : Description %s"
           --#ARGUMENTS {0,1,2,3,}
            --#SEVERITY  INFORMATIONAL
            --#TIMEINDEX 136
        ::= 136017017

   mngmtAgentTrap-17018 TRAP-TYPE
        ENTERPRISE compaq
        VARIABLES  { hostName,
                     scellNameDateTime,
                     agentEventCode,
                     agentEventDescription }
        DESCRIPTION
             "Drive code load - The disk cannot be code loaded because disk is part of a Vraid0 group. Failure during load may cause data loss."
           --#TYPE      "Management Agent Event 17018"
           --#SUMMARY   "Host %s : SCellName-TimeDate %s : EventCode %d : Description %s"
           --#ARGUMENTS {0,1,2,3,}
            --#SEVERITY  INFORMATIONAL
            --#TIMEINDEX 136
        ::= 136017018

   mngmtAgentTrap-17019 TRAP-TYPE
        ENTERPRISE compaq
        VARIABLES  { hostName,
                     scellNameDateTime,
                     agentEventCode,
                     agentEventDescription }
        DESCRIPTION
             "Drive code load - The diskgroup containing the physical store has background reconstructing or reverting in progress."
           --#TYPE      "Management Agent Event 17019"
           --#SUMMARY   "Host %s : SCellName-TimeDate %s : EventCode %d : Description %s"
           --#ARGUMENTS {0,1,2,3,}
            --#SEVERITY  INFORMATIONAL
            --#TIMEINDEX 136
        ::= 136017019

   mngmtAgentTrap-17020 TRAP-TYPE
        ENTERPRISE compaq
        VARIABLES  { hostName,
                     scellNameDateTime,
                     agentEventCode,
                     agentEventDescription }
        DESCRIPTION
             "Drive code load - The target download physical store is a quorum disk. There are not enough quorum disks in the system to provide sufficient redundancy for metadata protection in case of failure during the drive code download."
           --#TYPE      "Management Agent Event 17020"
           --#SUMMARY   "Host %s : SCellName-TimeDate %s : EventCode %d : Description %s"
           --#ARGUMENTS {0,1,2,3,}
            --#SEVERITY  INFORMATIONAL
            --#TIMEINDEX 136
        ::= 136017020

   mngmtAgentTrap-17021 TRAP-TYPE
        ENTERPRISE compaq
        VARIABLES  { hostName,
                     scellNameDateTime,
                     agentEventCode,
                     agentEventDescription }
        DESCRIPTION
             "Drive code load - The drive is no longer accessible."
           --#TYPE      "Management Agent Event 17021"
           --#SUMMARY   "Host %s : SCellName-TimeDate %s : EventCode %d : Description %s"
           --#ARGUMENTS {0,1,2,3,}
            --#SEVERITY  INFORMATIONAL
            --#TIMEINDEX 136
        ::= 136017021

   mngmtAgentTrap-17022 TRAP-TYPE
        ENTERPRISE compaq
        VARIABLES  { hostName,
                     scellNameDateTime,
                     agentEventCode,
                     agentEventDescription }
        DESCRIPTION
             "Drive code load - The StorageCell is in device discovery, and the requested operation cannot be served."
           --#TYPE      "Management Agent Event 17022"
           --#SUMMARY   "Host %s : SCellName-TimeDate %s : EventCode %d : Description %s"
           --#ARGUMENTS {0,1,2,3,}
            --#SEVERITY  INFORMATIONAL
            --#TIMEINDEX 136
        ::= 136017022

   mngmtAgentTrap-17023 TRAP-TYPE
        ENTERPRISE compaq
        VARIABLES  { hostName,
                     scellNameDateTime,
                     agentEventCode,
                     agentEventDescription }
        DESCRIPTION
             "Drive code load - Failed to set the drive in maintenance mode."
           --#TYPE      "Management Agent Event 17023"
           --#SUMMARY   "Host %s : SCellName-TimeDate %s : EventCode %d : Description %s"
           --#ARGUMENTS {0,1,2,3,}
            --#SEVERITY  INFORMATIONAL
            --#TIMEINDEX 136
        ::= 136017023

   mngmtAgentTrap-17024 TRAP-TYPE
        ENTERPRISE compaq
        VARIABLES  { hostName,
                     scellNameDateTime,
                     agentEventCode,
                     agentEventDescription }
        DESCRIPTION
             "Drive code load - Failed to restore the drive from maintenance mode."
           --#TYPE      "Management Agent Event 17024"
           --#SUMMARY   "Host %s : SCellName-TimeDate %s : EventCode %d : Description %s"
           --#ARGUMENTS {0,1,2,3,}
            --#SEVERITY  INFORMATIONAL
            --#TIMEINDEX 136
        ::= 136017024

   mngmtAgentTrap-18001 TRAP-TYPE
        ENTERPRISE compaq
        VARIABLES  { hostName,
                     scellNameDateTime,
                     agentEventCode,
                     agentEventDescription }
        DESCRIPTION
             "Api Created Element Success"
           --#TYPE      "Management Agent Event 18001"
           --#SUMMARY   "Host %s : SCellName-TimeDate %s : EventCode %d : Description %s"
           --#ARGUMENTS {0,1,2,3,}
            --#SEVERITY  INFORMATIONAL
            --#TIMEINDEX 136
        ::= 136018001

   mngmtAgentTrap-18002 TRAP-TYPE
        ENTERPRISE compaq
        VARIABLES  { hostName,
                     scellNameDateTime,
                     agentEventCode,
                     agentEventDescription }
        DESCRIPTION
             "Api Created Storage Success"
           --#TYPE      "Management Agent Event 18002"
           --#SUMMARY   "Host %s : SCellName-TimeDate %s : EventCode %d : Description %s"
           --#ARGUMENTS {0,1,2,3,}
            --#SEVERITY  INFORMATIONAL
            --#TIMEINDEX 136
        ::= 136018002

   mngmtAgentTrap-18003 TRAP-TYPE
        ENTERPRISE compaq
        VARIABLES  { hostName,
                     scellNameDateTime,
                     agentEventCode,
                     agentEventDescription }
        DESCRIPTION
             "Api Created Storage Client Success"
           --#TYPE      "Management Agent Event 18003"
           --#SUMMARY   "Host %s : SCellName-TimeDate %s : EventCode %d : Description %s"
           --#ARGUMENTS {0,1,2,3,}
            --#SEVERITY  INFORMATIONAL
            --#TIMEINDEX 136
        ::= 136018003

   mngmtAgentTrap-18004 TRAP-TYPE
        ENTERPRISE compaq
        VARIABLES  { hostName,
                     scellNameDateTime,
                     agentEventCode,
                     agentEventDescription }
        DESCRIPTION
             "Api Set Storage Success"
           --#TYPE      "Management Agent Event 18004"
           --#SUMMARY   "Host %s : SCellName-TimeDate %s : EventCode %d : Description %s"
           --#ARGUMENTS {0,1,2,3,}
            --#SEVERITY  INFORMATIONAL
            --#TIMEINDEX 136
        ::= 136018004

   mngmtAgentTrap-18005 TRAP-TYPE
        ENTERPRISE compaq
        VARIABLES  { hostName,
                     scellNameDateTime,
                     agentEventCode,
                     agentEventDescription }
        DESCRIPTION
             "Api Set Element Success"
           --#TYPE      "Management Agent Event 18005"
           --#SUMMARY   "Host %s : SCellName-TimeDate %s : EventCode %d : Description %s"
           --#ARGUMENTS {0,1,2,3,}
            --#SEVERITY  INFORMATIONAL
            --#TIMEINDEX 136
        ::= 136018005

   mngmtAgentTrap-18006 TRAP-TYPE
        ENTERPRISE compaq
        VARIABLES  { hostName,
                     scellNameDateTime,
                     agentEventCode,
                     agentEventDescription }
        DESCRIPTION
             "Api Deleted Element Success"
           --#TYPE      "Management Agent Event 18006"
           --#SUMMARY   "Host %s : SCellName-TimeDate %s : EventCode %d : Description %s"
           --#ARGUMENTS {0,1,2,3,}
            --#SEVERITY  INFORMATIONAL
            --#TIMEINDEX 136
        ::= 136018006

   mngmtAgentTrap-18007 TRAP-TYPE
        ENTERPRISE compaq
        VARIABLES  { hostName,
                     scellNameDateTime,
                     agentEventCode,
                     agentEventDescription }
        DESCRIPTION
             "Api Deleted Storage Success"
           --#TYPE      "Management Agent Event 18007"
           --#SUMMARY   "Host %s : SCellName-TimeDate %s : EventCode %d : Description %s"
           --#ARGUMENTS {0,1,2,3,}
            --#SEVERITY  INFORMATIONAL
            --#TIMEINDEX 136
        ::= 136018007

   mngmtAgentTrap-18008 TRAP-TYPE
        ENTERPRISE compaq
        VARIABLES  { hostName,
                     scellNameDateTime,
                     agentEventCode,
                     agentEventDescription }
        DESCRIPTION
             "Api Deleted Storage Client Success"
           --#TYPE      "Management Agent Event 18008"
           --#SUMMARY   "Host %s : SCellName-TimeDate %s : EventCode %d : Description %s"
           --#ARGUMENTS {0,1,2,3,}
            --#SEVERITY  INFORMATIONAL
            --#TIMEINDEX 136
        ::= 136018008

   mngmtAgentTrap-18009 TRAP-TYPE
        ENTERPRISE compaq
        VARIABLES  { hostName,
                     scellNameDateTime,
                     agentEventCode,
                     agentEventDescription }
        DESCRIPTION
             "Api Created Snapshot Success"
           --#TYPE      "Management Agent Event 18009"
           --#SUMMARY   "Host %s : SCellName-TimeDate %s : EventCode %d : Description %s"
           --#ARGUMENTS {0,1,2,3,}
            --#SEVERITY  INFORMATIONAL
            --#TIMEINDEX 136
        ::= 136018009

   mngmtAgentTrap-18010 TRAP-TYPE
        ENTERPRISE compaq
        VARIABLES  { hostName,
                     scellNameDateTime,
                     agentEventCode,
                     agentEventDescription }
        DESCRIPTION
             "Api Created Clone Success"
           --#TYPE      "Management Agent Event 18010"
           --#SUMMARY   "Host %s : SCellName-TimeDate %s : EventCode %d : Description %s"
           --#ARGUMENTS {0,1,2,3,}
            --#SEVERITY  INFORMATIONAL
            --#TIMEINDEX 136
        ::= 136018010

   mngmtAgentTrap-18018 TRAP-TYPE
        ENTERPRISE compaq
        VARIABLES  { hostName,
                     scellNameDateTime,
                     agentEventCode,
                     agentEventDescription }
        DESCRIPTION
             "Api Unable To Get The Lock"
           --#TYPE      "Management Agent Event 18018"
           --#SUMMARY   "Host %s : SCellName-TimeDate %s : EventCode %d : Description %s"
           --#ARGUMENTS {0,1,2,3,}
            --#SEVERITY  INFORMATIONAL
            --#TIMEINDEX 136
        ::= 136018018

   mngmtAgentTrap-18019 TRAP-TYPE
        ENTERPRISE compaq
        VARIABLES  { hostName,
                     scellNameDateTime,
                     agentEventCode,
                     agentEventDescription }
        DESCRIPTION
             "Api Created PresentedUnit Success"
           --#TYPE      "Management Agent Event 18019"
           --#SUMMARY   "Host %s : SCellName-TimeDate %s : EventCode %d : Description %s"
           --#ARGUMENTS {0,1,2,3,}
            --#SEVERITY  INFORMATIONAL
            --#TIMEINDEX 136
        ::= 136018019

   mngmtAgentTrap-18022 TRAP-TYPE
        ENTERPRISE compaq
        VARIABLES  { hostName,
                     scellNameDateTime,
                     agentEventCode,
                     agentEventDescription }
        DESCRIPTION
             "Api Create DiskGroup Success"
           --#TYPE      "Management Agent Event 18022"
           --#SUMMARY   "Host %s : SCellName-TimeDate %s : EventCode %d : Description %s"
           --#ARGUMENTS {0,1,2,3,}
            --#SEVERITY  INFORMATIONAL
            --#TIMEINDEX 136
        ::= 136018022

   mngmtAgentTrap-18024 TRAP-TYPE
        ENTERPRISE compaq
        VARIABLES  { hostName,
                     scellNameDateTime,
                     agentEventCode,
                     agentEventDescription }
        DESCRIPTION
             "Api Create Folder Success"
           --#TYPE      "Management Agent Event 18024"
           --#SUMMARY   "Host %s : SCellName-TimeDate %s : EventCode %d : Description %s"
           --#ARGUMENTS {0,1,2,3,}
            --#SEVERITY  INFORMATIONAL
            --#TIMEINDEX 136
        ::= 136018024

   mngmtAgentTrap-18025 TRAP-TYPE
        ENTERPRISE compaq
        VARIABLES  { hostName,
                     scellNameDateTime,
                     agentEventCode,
                     agentEventDescription }
        DESCRIPTION
             "Api Delete Folder Success"
           --#TYPE      "Management Agent Event 18025"
           --#SUMMARY   "Host %s : SCellName-TimeDate %s : EventCode %d : Description %s"
           --#ARGUMENTS {0,1,2,3,}
            --#SEVERITY  INFORMATIONAL
            --#TIMEINDEX 136
        ::= 136018025

   mngmtAgentTrap-18028 TRAP-TYPE
        ENTERPRISE compaq
        VARIABLES  { hostName,
                     scellNameDateTime,
                     agentEventCode,
                     agentEventDescription }
        DESCRIPTION
             "Api Set Folder Success"
           --#TYPE      "Management Agent Event 18028"
           --#SUMMARY   "Host %s : SCellName-TimeDate %s : EventCode %d : Description %s"
           --#ARGUMENTS {0,1,2,3,}
            --#SEVERITY  INFORMATIONAL
            --#TIMEINDEX 136
        ::= 136018028

   mngmtAgentTrap-18034 TRAP-TYPE
        ENTERPRISE compaq
        VARIABLES  { hostName,
                     scellNameDateTime,
                     agentEventCode,
                     agentEventDescription }
        DESCRIPTION
             "Api Invalid User Name Or Password Error"
           --#TYPE      "Management Agent Event 18034"
           --#SUMMARY   "Host %s : SCellName-TimeDate %s : EventCode %d : Description %s"
           --#ARGUMENTS {0,1,2,3,}
            --#SEVERITY  INFORMATIONAL
            --#TIMEINDEX 136
        ::= 136018034

   mngmtAgentTrap-18036 TRAP-TYPE
        ENTERPRISE compaq
        VARIABLES  { hostName,
                     scellNameDateTime,
                     agentEventCode,
                     agentEventDescription }
        DESCRIPTION
             "Api Delete Presented Unit Success"
           --#TYPE      "Management Agent Event 18036"
           --#SUMMARY   "Host %s : SCellName-TimeDate %s : EventCode %d : Description %s"
           --#ARGUMENTS {0,1,2,3,}
            --#SEVERITY  INFORMATIONAL
            --#TIMEINDEX 136
        ::= 136018036

   mngmtAgentTrap-18038 TRAP-TYPE
        ENTERPRISE compaq
        VARIABLES  { hostName,
                     scellNameDateTime,
                     agentEventCode,
                     agentEventDescription }
        DESCRIPTION
             "Api Set Diskgroup Success"
           --#TYPE      "Management Agent Event 18038"
           --#SUMMARY   "Host %s : SCellName-TimeDate %s : EventCode %d : Description %s"
           --#ARGUMENTS {0,1,2,3,}
            --#SEVERITY  INFORMATIONAL
            --#TIMEINDEX 136
        ::= 136018038

   mngmtAgentTrap-18039 TRAP-TYPE
        ENTERPRISE compaq
        VARIABLES  { hostName,
                     scellNameDateTime,
                     agentEventCode,
                     agentEventDescription }
        DESCRIPTION
             "Api Set Disk Success"
           --#TYPE      "Management Agent Event 18039"
           --#SUMMARY   "Host %s : SCellName-TimeDate %s : EventCode %d : Description %s"
           --#ARGUMENTS {0,1,2,3,}
            --#SEVERITY  INFORMATIONAL
            --#TIMEINDEX 136
        ::= 136018039

   mngmtAgentTrap-18040 TRAP-TYPE
        ENTERPRISE compaq
        VARIABLES  { hostName,
                     scellNameDateTime,
                     agentEventCode,
                     agentEventDescription }
        DESCRIPTION
             "Api Delete Storage Family Success"
           --#TYPE      "Management Agent Event 18040"
           --#SUMMARY   "Host %s : SCellName-TimeDate %s : EventCode %d : Description %s"
           --#ARGUMENTS {0,1,2,3,}
            --#SEVERITY  INFORMATIONAL
            --#TIMEINDEX 136
        ::= 136018040

   mngmtAgentTrap-18041 TRAP-TYPE
        ENTERPRISE compaq
        VARIABLES  { hostName,
                     scellNameDateTime,
                     agentEventCode,
                     agentEventDescription }
        DESCRIPTION
             "Api Set Storage Family Success"
           --#TYPE      "Management Agent Event 18041"
           --#SUMMARY   "Host %s : SCellName-TimeDate %s : EventCode %d : Description %s"
           --#ARGUMENTS {0,1,2,3,}
            --#SEVERITY  INFORMATIONAL
            --#TIMEINDEX 136
        ::= 136018041

   mngmtAgentTrap-18042 TRAP-TYPE
        ENTERPRISE compaq
        VARIABLES  { hostName,
                     scellNameDateTime,
                     agentEventCode,
                     agentEventDescription }
        DESCRIPTION
             "Api Control Memory Allocation Failure"
           --#TYPE      "Management Agent Event 18042"
           --#SUMMARY   "Host %s : SCellName-TimeDate %s : EventCode %d : Description %s"
           --#ARGUMENTS {0,1,2,3,}
            --#SEVERITY  INFORMATIONAL
            --#TIMEINDEX 136
        ::= 136018042

   mngmtAgentTrap-18045 TRAP-TYPE
        ENTERPRISE compaq
        VARIABLES  { hostName,
                     scellNameDateTime,
                     agentEventCode,
                     agentEventDescription }
        DESCRIPTION
             "Api Element Codeload Success"
           --#TYPE      "Management Agent Event 18045"
           --#SUMMARY   "Host %s : SCellName-TimeDate %s : EventCode %d : Description %s"
           --#ARGUMENTS {0,1,2,3,}
            --#SEVERITY  INFORMATIONAL
            --#TIMEINDEX 136
        ::= 136018045

   mngmtAgentTrap-18047 TRAP-TYPE
        ENTERPRISE compaq
        VARIABLES  { hostName,
                     scellNameDateTime,
                     agentEventCode,
                     agentEventDescription }
        DESCRIPTION
             "Api Disk Codeload Success"
           --#TYPE      "Management Agent Event 18047"
           --#SUMMARY   "Host %s : SCellName-TimeDate %s : EventCode %d : Description %s"
           --#ARGUMENTS {0,1,2,3,}
            --#SEVERITY  INFORMATIONAL
            --#TIMEINDEX 136
        ::= 136018047

   mngmtAgentTrap-18048 TRAP-TYPE
        ENTERPRISE compaq
        VARIABLES  { hostName,
                     scellNameDateTime,
                     agentEventCode,
                     agentEventDescription }
        DESCRIPTION
             "Api Monitor Codeload Success"
           --#TYPE      "Management Agent Event 18048"
           --#SUMMARY   "Host %s : SCellName-TimeDate %s : EventCode %d : Description %s"
           --#ARGUMENTS {0,1,2,3,}
            --#SEVERITY  INFORMATIONAL
            --#TIMEINDEX 136
        ::= 136018048

   mngmtAgentTrap-18049 TRAP-TYPE
        ENTERPRISE compaq
        VARIABLES  { hostName,
                     scellNameDateTime,
                     agentEventCode,
                     agentEventDescription }
        DESCRIPTION
             "Api Added Port WWID Success"
           --#TYPE      "Management Agent Event 18049"
           --#SUMMARY   "Host %s : SCellName-TimeDate %s : EventCode %d : Description %s"
           --#ARGUMENTS {0,1,2,3,}
            --#SEVERITY  INFORMATIONAL
            --#TIMEINDEX 136
        ::= 136018049

   mngmtAgentTrap-18050 TRAP-TYPE
        ENTERPRISE compaq
        VARIABLES  { hostName,
                     scellNameDateTime,
                     agentEventCode,
                     agentEventDescription }
        DESCRIPTION
             "Api Set Storage Client Success"
           --#TYPE      "Management Agent Event 18050"
           --#SUMMARY   "Host %s : SCellName-TimeDate %s : EventCode %d : Description %s"
           --#ARGUMENTS {0,1,2,3,}
            --#SEVERITY  INFORMATIONAL
            --#TIMEINDEX 136
        ::= 136018050

   mngmtAgentTrap-18051 TRAP-TYPE
        ENTERPRISE compaq
        VARIABLES  { hostName,
                     scellNameDateTime,
                     agentEventCode,
                     agentEventDescription }
        DESCRIPTION
             "Api Invalid Operation"
           --#TYPE      "Management Agent Event 18051"
           --#SUMMARY   "Host %s : SCellName-TimeDate %s : EventCode %d : Description %s"
           --#ARGUMENTS {0,1,2,3,}
            --#SEVERITY  INFORMATIONAL
            --#TIMEINDEX 136
        ::= 136018051

   mngmtAgentTrap-18052 TRAP-TYPE
        ENTERPRISE compaq
        VARIABLES  { hostName,
                     scellNameDateTime,
                     agentEventCode,
                     agentEventDescription }
        DESCRIPTION
             "Api Deleted Port WWID Success"
           --#TYPE      "Management Agent Event 18052"
           --#SUMMARY   "Host %s : SCellName-TimeDate %s : EventCode %d : Description %s"
           --#ARGUMENTS {0,1,2,3,}
            --#SEVERITY  INFORMATIONAL
            --#TIMEINDEX 136
        ::= 136018052

   mngmtAgentTrap-18059 TRAP-TYPE
        ENTERPRISE compaq
        VARIABLES  { hostName,
                     scellNameDateTime,
                     agentEventCode,
                     agentEventDescription }
        DESCRIPTION
             "Api Set Power Success"
           --#TYPE      "Management Agent Event 18059"
           --#SUMMARY   "Host %s : SCellName-TimeDate %s : EventCode %d : Description %s"
           --#ARGUMENTS {0,1,2,3,}
            --#SEVERITY  INFORMATIONAL
            --#TIMEINDEX 136
        ::= 136018059

   mngmtAgentTrap-18060 TRAP-TYPE
        ENTERPRISE compaq
        VARIABLES  { hostName,
                     scellNameDateTime,
                     agentEventCode,
                     agentEventDescription }
        DESCRIPTION
             "Api Element Is Not Initialized"
           --#TYPE      "Management Agent Event 18060"
           --#SUMMARY   "Host %s : SCellName-TimeDate %s : EventCode %d : Description %s"
           --#ARGUMENTS {0,1,2,3,}
            --#SEVERITY  INFORMATIONAL
            --#TIMEINDEX 136
        ::= 136018060

   mngmtAgentTrap-18063 TRAP-TYPE
        ENTERPRISE compaq
        VARIABLES  { hostName,
                     scellNameDateTime,
                     agentEventCode,
                     agentEventDescription }
        DESCRIPTION
             "Api Error trying to delete a disk group"
           --#TYPE      "Management Agent Event 18063"
           --#SUMMARY   "Host %s : SCellName-TimeDate %s : EventCode %d : Description %s"
           --#ARGUMENTS {0,1,2,3,}
            --#SEVERITY  INFORMATIONAL
            --#TIMEINDEX 136
        ::= 136018063

   mngmtAgentTrap-18065 TRAP-TYPE
        ENTERPRISE compaq
        VARIABLES  { hostName,
                     scellNameDateTime,
                     agentEventCode,
                     agentEventDescription }
        DESCRIPTION
             "Api A storage (Vdisk) operation is in progress. Try again later."
           --#TYPE      "Management Agent Event 18065"
           --#SUMMARY   "Host %s : SCellName-TimeDate %s : EventCode %d : Description %s"
           --#ARGUMENTS {0,1,2,3,}
            --#SEVERITY  INFORMATIONAL
            --#TIMEINDEX 136
        ::= 136018065

   mngmtAgentTrap-18066 TRAP-TYPE
        ENTERPRISE compaq
        VARIABLES  { hostName,
                     scellNameDateTime,
                     agentEventCode,
                     agentEventDescription }
        DESCRIPTION
             "Api The storage (Vdisk) condition is invalid. The storage may be in error. Try again later."
           --#TYPE      "Management Agent Event 18066"
           --#SUMMARY   "Host %s : SCellName-TimeDate %s : EventCode %d : Description %s"
           --#ARGUMENTS {0,1,2,3,}
            --#SEVERITY  INFORMATIONAL
            --#TIMEINDEX 136
        ::= 136018066

   mngmtAgentTrap-18067 TRAP-TYPE
        ENTERPRISE compaq
        VARIABLES  { hostName,
                     scellNameDateTime,
                     agentEventCode,
                     agentEventDescription }
        DESCRIPTION
             "Api Error calling get Vdisk condition. Vdisk may be deleted. Try again later."
           --#TYPE      "Management Agent Event 18067"
           --#SUMMARY   "Host %s : SCellName-TimeDate %s : EventCode %d : Description %s"
           --#ARGUMENTS {0,1,2,3,}
            --#SEVERITY  INFORMATIONAL
            --#TIMEINDEX 136
        ::= 136018067

   mngmtAgentTrap-18068 TRAP-TYPE
        ENTERPRISE compaq
        VARIABLES  { hostName,
                     scellNameDateTime,
                     agentEventCode,
                     agentEventDescription }
        DESCRIPTION
             "Api Invalid initialization of the API. Cannot start monitoring process. Storage system management limited."
           --#TYPE      "Management Agent Event 18068"
           --#SUMMARY   "Host %s : SCellName-TimeDate %s : EventCode %d : Description %s"
           --#ARGUMENTS {0,1,2,3,}
            --#SEVERITY  INFORMATIONAL
            --#TIMEINDEX 136
        ::= 136018068

   mngmtAgentTrap-18070 TRAP-TYPE
        ENTERPRISE compaq
        VARIABLES  { hostName,
                     scellNameDateTime,
                     agentEventCode,
                     agentEventDescription }
        DESCRIPTION
             "Api A command is currently under execution from another API call. Try again later."
           --#TYPE      "Management Agent Event 18070"
           --#SUMMARY   "Host %s : SCellName-TimeDate %s : EventCode %d : Description %s"
           --#ARGUMENTS {0,1,2,3,}
            --#SEVERITY  INFORMATIONAL
            --#TIMEINDEX 136
        ::= 136018070

   mngmtAgentTrap-18071 TRAP-TYPE
        ENTERPRISE compaq
        VARIABLES  { hostName,
                     scellNameDateTime,
                     agentEventCode,
                     agentEventDescription }
        DESCRIPTION
             "Api The server has not completed initialization, cannot process the request."
           --#TYPE      "Management Agent Event 18071"
           --#SUMMARY   "Host %s : SCellName-TimeDate %s : EventCode %d : Description %s"
           --#ARGUMENTS {0,1,2,3,}
            --#SEVERITY  INFORMATIONAL
            --#TIMEINDEX 136
        ::= 136018071

   mngmtAgentTrap-18073 TRAP-TYPE
        ENTERPRISE compaq
        VARIABLES  { hostName,
                     scellNameDateTime,
                     agentEventCode,
                     agentEventDescription }
        DESCRIPTION
             "Api Removal of disk from disk group successful"
           --#TYPE      "Management Agent Event 18073"
           --#SUMMARY   "Host %s : SCellName-TimeDate %s : EventCode %d : Description %s"
           --#ARGUMENTS {0,1,2,3,}
            --#SEVERITY  INFORMATIONAL
            --#TIMEINDEX 136
        ::= 136018073

   mngmtAgentTrap-18074 TRAP-TYPE
        ENTERPRISE compaq
        VARIABLES  { hostName,
                     scellNameDateTime,
                     agentEventCode,
                     agentEventDescription }
        DESCRIPTION
             "Api Disk(s) added to disk group successfully"
           --#TYPE      "Management Agent Event 18074"
           --#SUMMARY   "Host %s : SCellName-TimeDate %s : EventCode %d : Description %s"
           --#ARGUMENTS {0,1,2,3,}
            --#SEVERITY  INFORMATIONAL
            --#TIMEINDEX 136
        ::= 136018074

   mngmtAgentTrap-18075 TRAP-TYPE
        ENTERPRISE compaq
        VARIABLES  { hostName,
                     scellNameDateTime,
                     agentEventCode,
                     agentEventDescription }
        DESCRIPTION
             "Api Modify monitor properties successful"
           --#TYPE      "Management Agent Event 18075"
           --#SUMMARY   "Host %s : SCellName-TimeDate %s : EventCode %d : Description %s"
           --#ARGUMENTS {0,1,2,3,}
            --#SEVERITY  INFORMATIONAL
            --#TIMEINDEX 136
        ::= 136018075

   mngmtAgentTrap-18076 TRAP-TYPE
        ENTERPRISE compaq
        VARIABLES  { hostName,
                     scellNameDateTime,
                     agentEventCode,
                     agentEventDescription }
        DESCRIPTION
             "Api Element name too long. Maximum is 20 characters."
           --#TYPE      "Management Agent Event 18076"
           --#SUMMARY   "Host %s : SCellName-TimeDate %s : EventCode %d : Description %s"
           --#ARGUMENTS {0,1,2,3,}
            --#SEVERITY  INFORMATIONAL
            --#TIMEINDEX 136
        ::= 136018076

   mngmtAgentTrap-18080 TRAP-TYPE
        ENTERPRISE compaq
        VARIABLES  { hostName,
                     scellNameDateTime,
                     agentEventCode,
                     agentEventDescription }
        DESCRIPTION
             "Api The snapshot/Snapclone license cannot be validated. Either the license key has not been entered, or there is a system communication failure."
           --#TYPE      "Management Agent Event 18080"
           --#SUMMARY   "Host %s : SCellName-TimeDate %s : EventCode %d : Description %s"
           --#ARGUMENTS {0,1,2,3,}
            --#SEVERITY  INFORMATIONAL
            --#TIMEINDEX 136
        ::= 136018080

   mngmtAgentTrap-18081 TRAP-TYPE
        ENTERPRISE compaq
        VARIABLES  { hostName,
                     scellNameDateTime,
                     agentEventCode,
                     agentEventDescription }
        DESCRIPTION
             "Api The folder operation is not valid for the specified folder. Either the folder is a root folder and cannot be modified, or it is a disk group folder for which you should use 'Set Group' command."
           --#TYPE      "Management Agent Event 18081"
           --#SUMMARY   "Host %s : SCellName-TimeDate %s : EventCode %d : Description %s"
           --#ARGUMENTS {0,1,2,3,}
            --#SEVERITY  INFORMATIONAL
            --#TIMEINDEX 136
        ::= 136018081

   mngmtAgentTrap-20001 TRAP-TYPE
        ENTERPRISE compaq
        VARIABLES  { hostName,
                     scellNameDateTime,
                     agentEventCode,
                     agentEventDescription }
        DESCRIPTION
             "LicMngr Memory Allocation Failure"
           --#TYPE      "Management Agent Event 20001"
           --#SUMMARY   "Host %s : SCellName-TimeDate %s : EventCode %d : Description %s"
           --#ARGUMENTS {0,1,2,3,}
            --#SEVERITY  CRITICAL
            --#TIMEINDEX 136
        ::= 136020001

   mngmtAgentTrap-20002 TRAP-TYPE
        ENTERPRISE compaq
        VARIABLES  { hostName,
                     scellNameDateTime,
                     agentEventCode,
                     agentEventDescription }
        DESCRIPTION
             "LicMngr Startup Complete"
           --#TYPE      "Management Agent Event 20002"
           --#SUMMARY   "Host %s : SCellName-TimeDate %s : EventCode %d : Description %s"
           --#ARGUMENTS {0,1,2,3,}
            --#SEVERITY  INFORMATIONAL
            --#TIMEINDEX 136
        ::= 136020002

   mngmtAgentTrap-20003 TRAP-TYPE
        ENTERPRISE compaq
        VARIABLES  { hostName,
                     scellNameDateTime,
                     agentEventCode,
                     agentEventDescription }
        DESCRIPTION
             "LicMngr Startup Failed"
           --#TYPE      "Management Agent Event 20003"
           --#SUMMARY   "Host %s : SCellName-TimeDate %s : EventCode %d : Description %s"
           --#ARGUMENTS {0,1,2,3,}
            --#SEVERITY  CRITICAL
            --#TIMEINDEX 136
        ::= 136020003

   mngmtAgentTrap-20004 TRAP-TYPE
        ENTERPRISE compaq
        VARIABLES  { hostName,
                     scellNameDateTime,
                     agentEventCode,
                     agentEventDescription }
        DESCRIPTION
             "License successfully checked out"
           --#TYPE      "Management Agent Event 20004"
           --#SUMMARY   "Host %s : SCellName-TimeDate %s : EventCode %d : Description %s"
           --#ARGUMENTS {0,1,2,3,}
            --#SEVERITY  INFORMATIONAL
            --#TIMEINDEX 136
        ::= 136020004

   mngmtAgentTrap-20005 TRAP-TYPE
        ENTERPRISE compaq
        VARIABLES  { hostName,
                     scellNameDateTime,
                     agentEventCode,
                     agentEventDescription }
        DESCRIPTION
             "License checkout failed"
           --#TYPE      "Management Agent Event 20005"
           --#SUMMARY   "Host %s : SCellName-TimeDate %s : EventCode %d : Description %s"
           --#ARGUMENTS {0,1,2,3,}
            --#SEVERITY  MINOR
            --#TIMEINDEX 136
        ::= 136020005

   mngmtAgentTrap-20011 TRAP-TYPE
        ENTERPRISE compaq
        VARIABLES  { hostName,
                     scellNameDateTime,
                     agentEventCode,
                     agentEventDescription }
        DESCRIPTION
             "License Line has an incorrect format"
           --#TYPE      "Management Agent Event 20011"
           --#SUMMARY   "Host %s : SCellName-TimeDate %s : EventCode %d : Description %s"
           --#ARGUMENTS {0,1,2,3,}
            --#SEVERITY  MINOR
            --#TIMEINDEX 136
        ::= 136020011

   mngmtAgentTrap-20013 TRAP-TYPE
        ENTERPRISE compaq
        VARIABLES  { hostName,
                     scellNameDateTime,
                     agentEventCode,
                     agentEventDescription }
        DESCRIPTION
             "License Library runtime error"
           --#TYPE      "Management Agent Event 20013"
           --#SUMMARY   "Host %s : SCellName-TimeDate %s : EventCode %d : Description %s"
           --#ARGUMENTS {0,1,2,3,}
            --#SEVERITY  CRITICAL
            --#TIMEINDEX 136
        ::= 136020013

   mngmtAgentTrap-20015 TRAP-TYPE
        ENTERPRISE compaq
        VARIABLES  { hostName,
                     scellNameDateTime,
                     agentEventCode,
                     agentEventDescription }
        DESCRIPTION
             "Failed to retrieve Node WWN from storage system"
           --#TYPE      "Management Agent Event 20015"
           --#SUMMARY   "Host %s : SCellName-TimeDate %s : EventCode %d : Description %s"
           --#ARGUMENTS {0,1,2,3,}
            --#SEVERITY  MINOR
            --#TIMEINDEX 136
        ::= 136020015

   mngmtAgentTrap-20016 TRAP-TYPE
        ENTERPRISE compaq
        VARIABLES  { hostName,
                     scellNameDateTime,
                     agentEventCode,
                     agentEventDescription }
        DESCRIPTION
             "Failed to retrieve license list from MLD"
           --#TYPE      "Management Agent Event 20016"
           --#SUMMARY   "Host %s : SCellName-TimeDate %s : EventCode %d : Description %s"
           --#ARGUMENTS {0,1,2,3,}
            --#SEVERITY  MINOR
            --#TIMEINDEX 136
        ::= 136020016

   mngmtAgentTrap-20017 TRAP-TYPE
        ENTERPRISE compaq
        VARIABLES  { hostName,
                     scellNameDateTime,
                     agentEventCode,
                     agentEventDescription }
        DESCRIPTION
             "Failed to write license list to MLD"
           --#TYPE      "Management Agent Event 20017"
           --#SUMMARY   "Host %s : SCellName-TimeDate %s : EventCode %d : Description %s"
           --#ARGUMENTS {0,1,2,3,}
            --#SEVERITY  MINOR
            --#TIMEINDEX 136
        ::= 136020017

   mngmtAgentTrap-20018 TRAP-TYPE
        ENTERPRISE compaq
        VARIABLES  { hostName,
                     scellNameDateTime,
                     agentEventCode,
                     agentEventDescription }
        DESCRIPTION
             "This license line appears to be invalid"
           --#TYPE      "Management Agent Event 20018"
           --#SUMMARY   "Host %s : SCellName-TimeDate %s : EventCode %d : Description %s"
           --#ARGUMENTS {0,1,2,3,}
            --#SEVERITY  MINOR
            --#TIMEINDEX 136
        ::= 136020018

   mngmtAgentTrap-20019 TRAP-TYPE
        ENTERPRISE compaq
        VARIABLES  { hostName,
                     scellNameDateTime,
                     agentEventCode,
                     agentEventDescription }
        DESCRIPTION
             "MLD Manager Handle is NULL - unable to update MLD License List"
           --#TYPE      "Management Agent Event 20019"
           --#SUMMARY   "Host %s : SCellName-TimeDate %s : EventCode %d : Description %s"
           --#ARGUMENTS {0,1,2,3,}
            --#SEVERITY  MINOR
            --#TIMEINDEX 136
        ::= 136020019

   mngmtAgentTrap-20020 TRAP-TYPE
        ENTERPRISE compaq
        VARIABLES  { hostName,
                     scellNameDateTime,
                     agentEventCode,
                     agentEventDescription }
        DESCRIPTION
             "LicMngr: Storage system handle is NULL"
           --#TYPE      "Management Agent Event 20020"
           --#SUMMARY   "Host %s : SCellName-TimeDate %s : EventCode %d : Description %s"
           --#ARGUMENTS {0,1,2,3,}
            --#SEVERITY  CRITICAL
            --#TIMEINDEX 136
        ::= 136020020

   mngmtAgentTrap-20021 TRAP-TYPE
        ENTERPRISE compaq
        VARIABLES  { hostName,
                     scellNameDateTime,
                     agentEventCode,
                     agentEventDescription }
        DESCRIPTION
             "The license you entered is a valid license but not for the Node WWN and/or firmware version on this controller pair"
           --#TYPE      "Management Agent Event 20021"
           --#SUMMARY   "Host %s : SCellName-TimeDate %s : EventCode %d : Description %s"
           --#ARGUMENTS {0,1,2,3,}
            --#SEVERITY  INFORMATIONAL
            --#TIMEINDEX 136
        ::= 136020021

   mngmtAgentTrap-20022 TRAP-TYPE
        ENTERPRISE compaq
        VARIABLES  { hostName,
                     scellNameDateTime,
                     agentEventCode,
                     agentEventDescription }
        DESCRIPTION
             "Function name string is null or in an incorrect format"
           --#TYPE      "Management Agent Event 20022"
           --#SUMMARY   "Host %s : SCellName-TimeDate %s : EventCode %d : Description %s"
           --#ARGUMENTS {0,1,2,3,}
            --#SEVERITY  INFORMATIONAL
            --#TIMEINDEX 136
        ::= 136020022

   mngmtAgentTrap-20023 TRAP-TYPE
        ENTERPRISE compaq
        VARIABLES  { hostName,
                     scellNameDateTime,
                     agentEventCode,
                     agentEventDescription }
        DESCRIPTION
             "Version string is null or in an incorrect format"
           --#TYPE      "Management Agent Event 20023"
           --#SUMMARY   "Host %s : SCellName-TimeDate %s : EventCode %d : Description %s"
           --#ARGUMENTS {0,1,2,3,}
            --#SEVERITY  INFORMATIONAL
            --#TIMEINDEX 136
        ::= 136020023

   mngmtAgentTrap-20024 TRAP-TYPE
        ENTERPRISE compaq
        VARIABLES  { hostName,
                     scellNameDateTime,
                     agentEventCode,
                     agentEventDescription }
        DESCRIPTION
             "Internal error. Could not open temporary file for licenses."
           --#TYPE      "Management Agent Event 20024"
           --#SUMMARY   "Host %s : SCellName-TimeDate %s : EventCode %d : Description %s"
           --#ARGUMENTS {0,1,2,3,}
            --#SEVERITY  INFORMATIONAL
            --#TIMEINDEX 136
        ::= 136020024

   mngmtAgentTrap-20025 TRAP-TYPE
        ENTERPRISE compaq
        VARIABLES  { hostName,
                     scellNameDateTime,
                     agentEventCode,
                     agentEventDescription }
        DESCRIPTION
             "Internal error. Could not install license(s)."
           --#TYPE      "Management Agent Event 20025"
           --#SUMMARY   "Host %s : SCellName-TimeDate %s : EventCode %d : Description %s"
           --#ARGUMENTS {0,1,2,3,}
            --#SEVERITY  INFORMATIONAL
            --#TIMEINDEX 136
        ::= 136020025

   mngmtAgentTrap-20027 TRAP-TYPE
        ENTERPRISE compaq
        VARIABLES  { hostName,
                     scellNameDateTime,
                     agentEventCode,
                     agentEventDescription }
        DESCRIPTION
             "This operation requires a valid HP P6000 Command View license."
           --#TYPE      "Management Agent Event 20027"
           --#SUMMARY   "Host %s : SCellName-TimeDate %s : EventCode %d : Description %s"
           --#ARGUMENTS {0,1,2,3,}
            --#SEVERITY  INFORMATIONAL
            --#TIMEINDEX 136
        ::= 136020027

   mngmtAgentTrap-20028 TRAP-TYPE
        ENTERPRISE compaq
        VARIABLES  { hostName,
                     scellNameDateTime,
                     agentEventCode,
                     agentEventDescription }
        DESCRIPTION
             "This operation requires a valid HP P6000 Business Copy license."
           --#TYPE      "Management Agent Event 20028"
           --#SUMMARY   "Host %s : SCellName-TimeDate %s : EventCode %d : Description %s"
           --#ARGUMENTS {0,1,2,3,}
            --#SEVERITY  INFORMATIONAL
            --#TIMEINDEX 136
        ::= 136020028

   mngmtAgentTrap-20029 TRAP-TYPE
        ENTERPRISE compaq
        VARIABLES  { hostName,
                     scellNameDateTime,
                     agentEventCode,
                     agentEventDescription }
        DESCRIPTION
             "This operation requires a valid HP P6000 Continuous Access license."
           --#TYPE      "Management Agent Event 20029"
           --#SUMMARY   "Host %s : SCellName-TimeDate %s : EventCode %d : Description %s"
           --#ARGUMENTS {0,1,2,3,}
            --#SEVERITY  INFORMATIONAL
            --#TIMEINDEX 136
        ::= 136020029

   mngmtAgentTrap-20030 TRAP-TYPE
        ENTERPRISE compaq
        VARIABLES  { hostName,
                     scellNameDateTime,
                     agentEventCode,
                     agentEventDescription }
        DESCRIPTION
             "Internal Licensing interface error."
           --#TYPE      "Management Agent Event 20030"
           --#SUMMARY   "Host %s : SCellName-TimeDate %s : EventCode %d : Description %s"
           --#ARGUMENTS {0,1,2,3,}
            --#SEVERITY  INFORMATIONAL
            --#TIMEINDEX 136
        ::= 136020030

   mngmtAgentTrap-20032 TRAP-TYPE
        ENTERPRISE compaq
        VARIABLES  { hostName,
                     scellNameDateTime,
                     agentEventCode,
                     agentEventDescription }
        DESCRIPTION
             "Internal Error. Could not report license information."
           --#TYPE      "Management Agent Event 20032"
           --#SUMMARY   "Host %s : SCellName-TimeDate %s : EventCode %d : Description %s"
           --#ARGUMENTS {0,1,2,3,}
            --#SEVERITY  INFORMATIONAL
            --#TIMEINDEX 136
        ::= 136020032

   mngmtAgentTrap-20033 TRAP-TYPE
        ENTERPRISE compaq
        VARIABLES  { hostName,
                     scellNameDateTime,
                     agentEventCode,
                     agentEventDescription }
        DESCRIPTION
             "Internal Licensing error for this feature."
           --#TYPE      "Management Agent Event 20033"
           --#SUMMARY   "Host %s : SCellName-TimeDate %s : EventCode %d : Description %s"
           --#ARGUMENTS {0,1,2,3,}
            --#SEVERITY  INFORMATIONAL
            --#TIMEINDEX 136
        ::= 136020033

   mngmtAgentTrap-20034 TRAP-TYPE
        ENTERPRISE compaq
        VARIABLES  { hostName,
                     scellNameDateTime,
                     agentEventCode,
                     agentEventDescription }
        DESCRIPTION
             "Internal Error. Could not remove license(s)."
           --#TYPE      "Management Agent Event 20034"
           --#SUMMARY   "Host %s : SCellName-TimeDate %s : EventCode %d : Description %s"
           --#ARGUMENTS {0,1,2,3,}
            --#SEVERITY  INFORMATIONAL
            --#TIMEINDEX 136
        ::= 136020034

   mngmtAgentTrap-20035 TRAP-TYPE
        ENTERPRISE compaq
        VARIABLES  { hostName,
                     scellNameDateTime,
                     agentEventCode,
                     agentEventDescription }
        DESCRIPTION
             "This operation requires a valid HP P6000 Command View license on the destination storage system."
           --#TYPE      "Management Agent Event 20035"
           --#SUMMARY   "Host %s : SCellName-TimeDate %s : EventCode %d : Description %s"
           --#ARGUMENTS {0,1,2,3,}
            --#SEVERITY  INFORMATIONAL
            --#TIMEINDEX 136
        ::= 136020035

   mngmtAgentTrap-20036 TRAP-TYPE
        ENTERPRISE compaq
        VARIABLES  { hostName,
                     scellNameDateTime,
                     agentEventCode,
                     agentEventDescription }
        DESCRIPTION
             "This operation requires a valid HP P6000 Continuous Access license on the destination storage system."
           --#TYPE      "Management Agent Event 20036"
           --#SUMMARY   "Host %s : SCellName-TimeDate %s : EventCode %d : Description %s"
           --#ARGUMENTS {0,1,2,3,}
            --#SEVERITY  INFORMATIONAL
            --#TIMEINDEX 136
        ::= 136020036

   mngmtAgentTrap-20038 TRAP-TYPE
        ENTERPRISE compaq
        VARIABLES  { hostName,
                     scellNameDateTime,
                     agentEventCode,
                     agentEventDescription }
        DESCRIPTION
             "Internal HP P6000 Command View Licensing Error."
           --#TYPE      "Management Agent Event 20038"
           --#SUMMARY   "Host %s : SCellName-TimeDate %s : EventCode %d : Description %s"
           --#ARGUMENTS {0,1,2,3,}
            --#SEVERITY  INFORMATIONAL
            --#TIMEINDEX 136
        ::= 136020038

   mngmtAgentTrap-20039 TRAP-TYPE
        ENTERPRISE compaq
        VARIABLES  { hostName,
                     scellNameDateTime,
                     agentEventCode,
                     agentEventDescription }
        DESCRIPTION
             "Internal HP P6000 Business Copy Licensing Error."
           --#TYPE      "Management Agent Event 20039"
           --#SUMMARY   "Host %s : SCellName-TimeDate %s : EventCode %d : Description %s"
           --#ARGUMENTS {0,1,2,3,}
            --#SEVERITY  INFORMATIONAL
            --#TIMEINDEX 136
        ::= 136020039

   mngmtAgentTrap-20040 TRAP-TYPE
        ENTERPRISE compaq
        VARIABLES  { hostName,
                     scellNameDateTime,
                     agentEventCode,
                     agentEventDescription }
        DESCRIPTION
             "Internal HP P6000 Continuous Access Licensing Error."
           --#TYPE      "Management Agent Event 20040"
           --#SUMMARY   "Host %s : SCellName-TimeDate %s : EventCode %d : Description %s"
           --#ARGUMENTS {0,1,2,3,}
            --#SEVERITY  INFORMATIONAL
            --#TIMEINDEX 136
        ::= 136020040

   mngmtAgentTrap-20041 TRAP-TYPE
        ENTERPRISE compaq
        VARIABLES  { hostName,
                     scellNameDateTime,
                     agentEventCode,
                     agentEventDescription }
        DESCRIPTION
             "The capacity of the HP P6000 Command View license required for this operation has been consumed."
           --#TYPE      "Management Agent Event 20041"
           --#SUMMARY   "Host %s : SCellName-TimeDate %s : EventCode %d : Description %s"
           --#ARGUMENTS {0,1,2,3,}
            --#SEVERITY  INFORMATIONAL
            --#TIMEINDEX 136
        ::= 136020041

   mngmtAgentTrap-20042 TRAP-TYPE
        ENTERPRISE compaq
        VARIABLES  { hostName,
                     scellNameDateTime,
                     agentEventCode,
                     agentEventDescription }
        DESCRIPTION
             "The capacity of the HP P6000 Business Copy license required for this operation has been consumed."
           --#TYPE      "Management Agent Event 20042"
           --#SUMMARY   "Host %s : SCellName-TimeDate %s : EventCode %d : Description %s"
           --#ARGUMENTS {0,1,2,3,}
            --#SEVERITY  INFORMATIONAL
            --#TIMEINDEX 136
        ::= 136020042

   mngmtAgentTrap-20043 TRAP-TYPE
        ENTERPRISE compaq
        VARIABLES  { hostName,
                     scellNameDateTime,
                     agentEventCode,
                     agentEventDescription }
        DESCRIPTION
             "The capacity of the HP P6000 Continuous Access license required for this operation has been consumed."
           --#TYPE      "Management Agent Event 20043"
           --#SUMMARY   "Host %s : SCellName-TimeDate %s : EventCode %d : Description %s"
           --#ARGUMENTS {0,1,2,3,}
            --#SEVERITY  INFORMATIONAL
            --#TIMEINDEX 136
        ::= 136020043

   mngmtAgentTrap-20044 TRAP-TYPE
        ENTERPRISE compaq
        VARIABLES  { hostName,
                     scellNameDateTime,
                     agentEventCode,
                     agentEventDescription }
        DESCRIPTION
             "The HP P6000 Command View license required for this operation has expired."
           --#TYPE      "Management Agent Event 20044"
           --#SUMMARY   "Host %s : SCellName-TimeDate %s : EventCode %d : Description %s"
           --#ARGUMENTS {0,1,2,3,}
            --#SEVERITY  INFORMATIONAL
            --#TIMEINDEX 136
        ::= 136020044

   mngmtAgentTrap-20045 TRAP-TYPE
        ENTERPRISE compaq
        VARIABLES  { hostName,
                     scellNameDateTime,
                     agentEventCode,
                     agentEventDescription }
        DESCRIPTION
             "The HP P6000 Business Copy license required for this operation has expired."
           --#TYPE      "Management Agent Event 20045"
           --#SUMMARY   "Host %s : SCellName-TimeDate %s : EventCode %d : Description %s"
           --#ARGUMENTS {0,1,2,3,}
            --#SEVERITY  INFORMATIONAL
            --#TIMEINDEX 136
        ::= 136020045

   mngmtAgentTrap-20046 TRAP-TYPE
        ENTERPRISE compaq
        VARIABLES  { hostName,
                     scellNameDateTime,
                     agentEventCode,
                     agentEventDescription }
        DESCRIPTION
             "The HP P6000 Continuous Access license required for this operation has expired."
           --#TYPE      "Management Agent Event 20046"
           --#SUMMARY   "Host %s : SCellName-TimeDate %s : EventCode %d : Description %s"
           --#ARGUMENTS {0,1,2,3,}
            --#SEVERITY  INFORMATIONAL
            --#TIMEINDEX 136
        ::= 136020046

   mngmtAgentTrap-20049 TRAP-TYPE
        ENTERPRISE compaq
        VARIABLES  { hostName,
                     scellNameDateTime,
                     agentEventCode,
                     agentEventDescription }
        DESCRIPTION
             "No Licenses Found."
           --#TYPE      "Management Agent Event 20049"
           --#SUMMARY   "Host %s : SCellName-TimeDate %s : EventCode %d : Description %s"
           --#ARGUMENTS {0,1,2,3,}
            --#SEVERITY  INFORMATIONAL
            --#TIMEINDEX 136
        ::= 136020049

   mngmtAgentTrap-20050 TRAP-TYPE
        ENTERPRISE compaq
        VARIABLES  { hostName,
                     scellNameDateTime,
                     agentEventCode,
                     agentEventDescription }
        DESCRIPTION
             "Internal Error. Instant-on Activation failed."
           --#TYPE      "Management Agent Event 20050"
           --#SUMMARY   "Host %s : SCellName-TimeDate %s : EventCode %d : Description %s"
           --#ARGUMENTS {0,1,2,3,}
            --#SEVERITY  INFORMATIONAL
            --#TIMEINDEX 136
        ::= 136020050

   mngmtAgentTrap-20051 TRAP-TYPE
        ENTERPRISE compaq
        VARIABLES  { hostName,
                     scellNameDateTime,
                     agentEventCode,
                     agentEventDescription }
        DESCRIPTION
             "Internal Thin Provisioning Licensing Error."
           --#TYPE      "Management Agent Event 20051"
           --#SUMMARY   "Host %s : SCellName-TimeDate %s : EventCode %d : Description %s"
           --#ARGUMENTS {0,1,2,3,}
            --#SEVERITY  INFORMATIONAL
            --#TIMEINDEX 136
        ::= 136020051

   mngmtAgentTrap-20052 TRAP-TYPE
        ENTERPRISE compaq
        VARIABLES  { hostName,
                     scellNameDateTime,
                     agentEventCode,
                     agentEventDescription }
        DESCRIPTION
             "Thin Provisioning License Not Found."
           --#TYPE      "Management Agent Event 20052"
           --#SUMMARY   "Host %s : SCellName-TimeDate %s : EventCode %d : Description %s"
           --#ARGUMENTS {0,1,2,3,}
            --#SEVERITY  INFORMATIONAL
            --#TIMEINDEX 136
        ::= 136020052

   mngmtAgentTrap-21001 TRAP-TYPE
        ENTERPRISE compaq
        VARIABLES  { hostName,
                     scellNameDateTime,
                     agentEventCode,
                     agentEventDescription }
        DESCRIPTION
             "Firmware image file open error"
           --#TYPE      "Management Agent Event 21001"
           --#SUMMARY   "Host %s : SCellName-TimeDate %s : EventCode %d : Description %s"
           --#ARGUMENTS {0,1,2,3,}
            --#SEVERITY  INFORMATIONAL
            --#TIMEINDEX 136
        ::= 136021001

   mngmtAgentTrap-21002 TRAP-TYPE
        ENTERPRISE compaq
        VARIABLES  { hostName,
                     scellNameDateTime,
                     agentEventCode,
                     agentEventDescription }
        DESCRIPTION
             "Firmware image file buffer allocation error"
           --#TYPE      "Management Agent Event 21002"
           --#SUMMARY   "Host %s : SCellName-TimeDate %s : EventCode %d : Description %s"
           --#ARGUMENTS {0,1,2,3,}
            --#SEVERITY  INFORMATIONAL
            --#TIMEINDEX 136
        ::= 136021002

   mngmtAgentTrap-21003 TRAP-TYPE
        ENTERPRISE compaq
        VARIABLES  { hostName,
                     scellNameDateTime,
                     agentEventCode,
                     agentEventDescription }
        DESCRIPTION
             "Firmware image file read error"
           --#TYPE      "Management Agent Event 21003"
           --#SUMMARY   "Host %s : SCellName-TimeDate %s : EventCode %d : Description %s"
           --#ARGUMENTS {0,1,2,3,}
            --#SEVERITY  INFORMATIONAL
            --#TIMEINDEX 136
        ::= 136021003

   mngmtAgentTrap-21004 TRAP-TYPE
        ENTERPRISE compaq
        VARIABLES  { hostName,
                     scellNameDateTime,
                     agentEventCode,
                     agentEventDescription }
        DESCRIPTION
             "Firmware image event file segment write error"
           --#TYPE      "Management Agent Event 21004"
           --#SUMMARY   "Host %s : SCellName-TimeDate %s : EventCode %d : Description %s"
           --#ARGUMENTS {0,1,2,3,}
            --#SEVERITY  INFORMATIONAL
            --#TIMEINDEX 136
        ::= 136021004

   mngmtAgentTrap-21006 TRAP-TYPE
        ENTERPRISE compaq
        VARIABLES  { hostName,
                     scellNameDateTime,
                     agentEventCode,
                     agentEventDescription }
        DESCRIPTION
             "Invalid firmware image file (global header EDC error)"
           --#TYPE      "Management Agent Event 21006"
           --#SUMMARY   "Host %s : SCellName-TimeDate %s : EventCode %d : Description %s"
           --#ARGUMENTS {0,1,2,3,}
            --#SEVERITY  INFORMATIONAL
            --#TIMEINDEX 136
        ::= 136021006

   mngmtAgentTrap-21007 TRAP-TYPE
        ENTERPRISE compaq
        VARIABLES  { hostName,
                     scellNameDateTime,
                     agentEventCode,
                     agentEventDescription }
        DESCRIPTION
             "Invalid firmware image file (image header EDC error)"
           --#TYPE      "Management Agent Event 21007"
           --#SUMMARY   "Host %s : SCellName-TimeDate %s : EventCode %d : Description %s"
           --#ARGUMENTS {0,1,2,3,}
            --#SEVERITY  INFORMATIONAL
            --#TIMEINDEX 136
        ::= 136021007

   mngmtAgentTrap-21008 TRAP-TYPE
        ENTERPRISE compaq
        VARIABLES  { hostName,
                     scellNameDateTime,
                     agentEventCode,
                     agentEventDescription }
        DESCRIPTION
             "Invalid firmware image file (image type exceeds max image count)"
           --#TYPE      "Management Agent Event 21008"
           --#SUMMARY   "Host %s : SCellName-TimeDate %s : EventCode %d : Description %s"
           --#ARGUMENTS {0,1,2,3,}
            --#SEVERITY  INFORMATIONAL
            --#TIMEINDEX 136
        ::= 136021008

   mngmtAgentTrap-21009 TRAP-TYPE
        ENTERPRISE compaq
        VARIABLES  { hostName,
                     scellNameDateTime,
                     agentEventCode,
                     agentEventDescription }
        DESCRIPTION
             "Invalid firmware image file (not Controller image type)"
           --#TYPE      "Management Agent Event 21009"
           --#SUMMARY   "Host %s : SCellName-TimeDate %s : EventCode %d : Description %s"
           --#ARGUMENTS {0,1,2,3,}
            --#SEVERITY  INFORMATIONAL
            --#TIMEINDEX 136
        ::= 136021009

   mngmtAgentTrap-21010 TRAP-TYPE
        ENTERPRISE compaq
        VARIABLES  { hostName,
                     scellNameDateTime,
                     agentEventCode,
                     agentEventDescription }
        DESCRIPTION
             "Invalid firmware image file (image size exceeded)"
           --#TYPE      "Management Agent Event 21010"
           --#SUMMARY   "Host %s : SCellName-TimeDate %s : EventCode %d : Description %s"
           --#ARGUMENTS {0,1,2,3,}
            --#SEVERITY  INFORMATIONAL
            --#TIMEINDEX 136
        ::= 136021010

   mngmtAgentTrap-21011 TRAP-TYPE
        ENTERPRISE compaq
        VARIABLES  { hostName,
                     scellNameDateTime,
                     agentEventCode,
                     agentEventDescription }
        DESCRIPTION
             "Firmware image event segment file open error"
           --#TYPE      "Management Agent Event 21011"
           --#SUMMARY   "Host %s : SCellName-TimeDate %s : EventCode %d : Description %s"
           --#ARGUMENTS {0,1,2,3,}
            --#SEVERITY  INFORMATIONAL
            --#TIMEINDEX 136
        ::= 136021011

   mngmtAgentTrap-21012 TRAP-TYPE
        ENTERPRISE compaq
        VARIABLES  { hostName,
                     scellNameDateTime,
                     agentEventCode,
                     agentEventDescription }
        DESCRIPTION
             "Invalid firmware image file (image EDC error)"
           --#TYPE      "Management Agent Event 21012"
           --#SUMMARY   "Host %s : SCellName-TimeDate %s : EventCode %d : Description %s"
           --#ARGUMENTS {0,1,2,3,}
            --#SEVERITY  INFORMATIONAL
            --#TIMEINDEX 136
        ::= 136021012

   mngmtAgentTrap-21013 TRAP-TYPE
        ENTERPRISE compaq
        VARIABLES  { hostName,
                     scellNameDateTime,
                     agentEventCode,
                     agentEventDescription }
        DESCRIPTION
             "Invalid firmware image file (Before text not found)"
           --#TYPE      "Management Agent Event 21013"
           --#SUMMARY   "Host %s : SCellName-TimeDate %s : EventCode %d : Description %s"
           --#ARGUMENTS {0,1,2,3,}
            --#SEVERITY  INFORMATIONAL
            --#TIMEINDEX 136
        ::= 136021013

   mngmtAgentTrap-21014 TRAP-TYPE
        ENTERPRISE compaq
        VARIABLES  { hostName,
                     scellNameDateTime,
                     agentEventCode,
                     agentEventDescription }
        DESCRIPTION
             "Invalid firmware image file (After text not found)"
           --#TYPE      "Management Agent Event 21014"
           --#SUMMARY   "Host %s : SCellName-TimeDate %s : EventCode %d : Description %s"
           --#ARGUMENTS {0,1,2,3,}
            --#SEVERITY  INFORMATIONAL
            --#TIMEINDEX 136
        ::= 136021014

   mngmtAgentTrap-21015 TRAP-TYPE
        ENTERPRISE compaq
        VARIABLES  { hostName,
                     scellNameDateTime,
                     agentEventCode,
                     agentEventDescription }
        DESCRIPTION
             "Invalid firmware image file (file format version mismatch)"
           --#TYPE      "Management Agent Event 21015"
           --#SUMMARY   "Host %s : SCellName-TimeDate %s : EventCode %d : Description %s"
           --#ARGUMENTS {0,1,2,3,}
            --#SEVERITY  INFORMATIONAL
            --#TIMEINDEX 136
        ::= 136021015

   mngmtAgentTrap-21016 TRAP-TYPE
        ENTERPRISE compaq
        VARIABLES  { hostName,
                     scellNameDateTime,
                     agentEventCode,
                     agentEventDescription }
        DESCRIPTION
             "Invalid firmware image file (global header format version mismatch)"
           --#TYPE      "Management Agent Event 21016"
           --#SUMMARY   "Host %s : SCellName-TimeDate %s : EventCode %d : Description %s"
           --#ARGUMENTS {0,1,2,3,}
            --#SEVERITY  INFORMATIONAL
            --#TIMEINDEX 136
        ::= 136021016

   mngmtAgentTrap-21017 TRAP-TYPE
        ENTERPRISE compaq
        VARIABLES  { hostName,
                     scellNameDateTime,
                     agentEventCode,
                     agentEventDescription }
        DESCRIPTION
             "Invalid firmware image file (product information not found)"
           --#TYPE      "Management Agent Event 21017"
           --#SUMMARY   "Host %s : SCellName-TimeDate %s : EventCode %d : Description %s"
           --#ARGUMENTS {0,1,2,3,}
            --#SEVERITY  INFORMATIONAL
            --#TIMEINDEX 136
        ::= 136021017

   mngmtAgentTrap-21018 TRAP-TYPE
        ENTERPRISE compaq
        VARIABLES  { hostName,
                     scellNameDateTime,
                     agentEventCode,
                     agentEventDescription }
        DESCRIPTION
             "Invalid firmware image file (event segment not found)"
           --#TYPE      "Management Agent Event 21018"
           --#SUMMARY   "Host %s : SCellName-TimeDate %s : EventCode %d : Description %s"
           --#ARGUMENTS {0,1,2,3,}
            --#SEVERITY  INFORMATIONAL
            --#TIMEINDEX 136
        ::= 136021018

   mngmtAgentTrap-21019 TRAP-TYPE
        ENTERPRISE compaq
        VARIABLES  { hostName,
                     scellNameDateTime,
                     agentEventCode,
                     agentEventDescription }
        DESCRIPTION
             "Invalid firmware image file (all image segments match versions already loaded)"
           --#TYPE      "Management Agent Event 21019"
           --#SUMMARY   "Host %s : SCellName-TimeDate %s : EventCode %d : Description %s"
           --#ARGUMENTS {0,1,2,3,}
            --#SEVERITY  INFORMATIONAL
            --#TIMEINDEX 136
        ::= 136021019

   mngmtAgentTrap-21020 TRAP-TYPE
        ENTERPRISE compaq
        VARIABLES  { hostName,
                     scellNameDateTime,
                     agentEventCode,
                     agentEventDescription }
        DESCRIPTION
             "Invalid firmware image file (unsupported array model)"
           --#TYPE      "Management Agent Event 21020"
           --#SUMMARY   "Host %s : SCellName-TimeDate %s : EventCode %d : Description %s"
           --#ARGUMENTS {0,1,2,3,}
            --#SEVERITY  INFORMATIONAL
            --#TIMEINDEX 136
        ::= 136021020

   mngmtAgentTrap-21021 TRAP-TYPE
        ENTERPRISE compaq
        VARIABLES  { hostName,
                     scellNameDateTime,
                     agentEventCode,
                     agentEventDescription }
        DESCRIPTION
             "Invalid firmware image file (mismatch between global header format version and supported array model)"
           --#TYPE      "Management Agent Event 21021"
           --#SUMMARY   "Host %s : SCellName-TimeDate %s : EventCode %d : Description %s"
           --#ARGUMENTS {0,1,2,3,}
            --#SEVERITY  INFORMATIONAL
            --#TIMEINDEX 136
        ::= 136021021

   mngmtAgentTrap-21022 TRAP-TYPE
        ENTERPRISE compaq
        VARIABLES  { hostName,
                     scellNameDateTime,
                     agentEventCode,
                     agentEventDescription }
        DESCRIPTION
             "Invalid firmware image file (controller image header does not support data item)"
           --#TYPE      "Management Agent Event 21022"
           --#SUMMARY   "Host %s : SCellName-TimeDate %s : EventCode %d : Description %s"
           --#ARGUMENTS {0,1,2,3,}
            --#SEVERITY  INFORMATIONAL
            --#TIMEINDEX 136
        ::= 136021022

   mngmtAgentTrap-21023 TRAP-TYPE
        ENTERPRISE compaq
        VARIABLES  { hostName,
                     scellNameDateTime,
                     agentEventCode,
                     agentEventDescription }
        DESCRIPTION
             "Firmware version is not supported"
           --#TYPE      "Management Agent Event 21023"
           --#SUMMARY   "Host %s : SCellName-TimeDate %s : EventCode %d : Description %s"
           --#ARGUMENTS {0,1,2,3,}
            --#SEVERITY  INFORMATIONAL
            --#TIMEINDEX 136
        ::= 136021023

   mngmtAgentTrap-21024 TRAP-TYPE
        ENTERPRISE compaq
        VARIABLES  { hostName,
                     scellNameDateTime,
                     agentEventCode,
                     agentEventDescription }
        DESCRIPTION
             "You have requested a firmware downgrade that is not supported for your hardware configuration and could cause harm. Please see the HP Enterprise Virtual Array Updating Product Software Guide for more information or contact your HP service representative."
           --#TYPE      "Management Agent Event 21024"
           --#SUMMARY   "Host %s : SCellName-TimeDate %s : EventCode %d : Description %s"
           --#ARGUMENTS {0,1,2,3,}
            --#SEVERITY  MINOR
            --#TIMEINDEX 136
        ::= 136021024

   mngmtAgentTrap-22001 TRAP-TYPE
        ENTERPRISE compaq
        VARIABLES  { hostName,
                     scellNameDateTime,
                     agentEventCode,
                     agentEventDescription }
        DESCRIPTION
             "Trace: Unable to write management agent trace file"
           --#TYPE      "Management Agent Event 22001"
           --#SUMMARY   "Host %s : SCellName-TimeDate %s : EventCode %d : Description %s"
           --#ARGUMENTS {0,1,2,3,}
            --#SEVERITY  MINOR
            --#TIMEINDEX 136
        ::= 136022001

   mngmtAgentTrap-22002 TRAP-TYPE
        ENTERPRISE compaq
        VARIABLES  { hostName,
                     scellNameDateTime,
                     agentEventCode,
                     agentEventDescription }
        DESCRIPTION
             "Trace: file write succeeded"
           --#TYPE      "Management Agent Event 22002"
           --#SUMMARY   "Host %s : SCellName-TimeDate %s : EventCode %d : Description %s"
           --#ARGUMENTS {0,1,2,3,}
            --#SEVERITY  INFORMATIONAL
            --#TIMEINDEX 136
        ::= 136022002

   mngmtAgentTrap-23002 TRAP-TYPE
        ENTERPRISE compaq
        VARIABLES  { hostName,
                     scellNameDateTime,
                     agentEventCode,
                     agentEventDescription }
        DESCRIPTION
             "Diagnostic The view list has errors"
           --#TYPE      "Management Agent Event 23002"
           --#SUMMARY   "Host %s : SCellName-TimeDate %s : EventCode %d : Description %s"
           --#ARGUMENTS {0,1,2,3,}
            --#SEVERITY  MINOR
            --#TIMEINDEX 136
        ::= 136023002

   mngmtAgentTrap-23003 TRAP-TYPE
        ENTERPRISE compaq
        VARIABLES  { hostName,
                     scellNameDateTime,
                     agentEventCode,
                     agentEventDescription }
        DESCRIPTION
             "Diagnostic Memory allocation failure"
           --#TYPE      "Management Agent Event 23003"
           --#SUMMARY   "Host %s : SCellName-TimeDate %s : EventCode %d : Description %s"
           --#ARGUMENTS {0,1,2,3,}
            --#SEVERITY  CRITICAL
            --#TIMEINDEX 136
        ::= 136023003

   mngmtAgentTrap-24001 TRAP-TYPE
        ENTERPRISE compaq
        VARIABLES  { hostName,
                     scellNameDateTime,
                     agentEventCode,
                     agentEventDescription }
        DESCRIPTION
             "Windows system error"
           --#TYPE      "Management Agent Event 24001"
           --#SUMMARY   "Host %s : SCellName-TimeDate %s : EventCode %d : Description %s"
           --#ARGUMENTS {0,1,2,3,}
            --#SEVERITY  INFORMATIONAL
            --#TIMEINDEX 136
        ::= 136024001

   mngmtAgentTrap-24002 TRAP-TYPE
        ENTERPRISE compaq
        VARIABLES  { hostName,
                     scellNameDateTime,
                     agentEventCode,
                     agentEventDescription }
        DESCRIPTION
             "Lock is already taken"
           --#TYPE      "Management Agent Event 24002"
           --#SUMMARY   "Host %s : SCellName-TimeDate %s : EventCode %d : Description %s"
           --#ARGUMENTS {0,1,2,3,}
            --#SEVERITY  INFORMATIONAL
            --#TIMEINDEX 136
        ::= 136024002

   mngmtAgentTrap-24003 TRAP-TYPE
        ENTERPRISE compaq
        VARIABLES  { hostName,
                     scellNameDateTime,
                     agentEventCode,
                     agentEventDescription }
        DESCRIPTION
             "Lock is not taken"
           --#TYPE      "Management Agent Event 24003"
           --#SUMMARY   "Host %s : SCellName-TimeDate %s : EventCode %d : Description %s"
           --#ARGUMENTS {0,1,2,3,}
            --#SEVERITY  INFORMATIONAL
            --#TIMEINDEX 136
        ::= 136024003

   mngmtAgentTrap-24004 TRAP-TYPE
        ENTERPRISE compaq
        VARIABLES  { hostName,
                     scellNameDateTime,
                     agentEventCode,
                     agentEventDescription }
        DESCRIPTION
             "Request timed out"
           --#TYPE      "Management Agent Event 24004"
           --#SUMMARY   "Host %s : SCellName-TimeDate %s : EventCode %d : Description %s"
           --#ARGUMENTS {0,1,2,3,}
            --#SEVERITY  INFORMATIONAL
            --#TIMEINDEX 136
        ::= 136024004

   mngmtAgentTrap-25001 TRAP-TYPE
        ENTERPRISE compaq
        VARIABLES  { hostName,
                     scellNameDateTime,
                     agentEventCode,
                     agentEventDescription }
        DESCRIPTION
             "No path to controller"
           --#TYPE      "Management Agent Event 25001"
           --#SUMMARY   "Host %s : SCellName-TimeDate %s : EventCode %d : Description %s"
           --#ARGUMENTS {0,1,2,3,}
            --#SEVERITY  INFORMATIONAL
            --#TIMEINDEX 136
        ::= 136025001

   mngmtAgentTrap-25002 TRAP-TYPE
        ENTERPRISE compaq
        VARIABLES  { hostName,
                     scellNameDateTime,
                     agentEventCode,
                     agentEventDescription }
        DESCRIPTION
             "Thread is not running"
           --#TYPE      "Management Agent Event 25002"
           --#SUMMARY   "Host %s : SCellName-TimeDate %s : EventCode %d : Description %s"
           --#ARGUMENTS {0,1,2,3,}
            --#SEVERITY  INFORMATIONAL
            --#TIMEINDEX 136
        ::= 136025002

   mngmtAgentTrap-25003 TRAP-TYPE
        ENTERPRISE compaq
        VARIABLES  { hostName,
                     scellNameDateTime,
                     agentEventCode,
                     agentEventDescription }
        DESCRIPTION
             "No physical stores"
           --#TYPE      "Management Agent Event 25003"
           --#SUMMARY   "Host %s : SCellName-TimeDate %s : EventCode %d : Description %s"
           --#ARGUMENTS {0,1,2,3,}
            --#SEVERITY  INFORMATIONAL
            --#TIMEINDEX 136
        ::= 136025003

   mngmtAgentTrap-25004 TRAP-TYPE
        ENTERPRISE compaq
        VARIABLES  { hostName,
                     scellNameDateTime,
                     agentEventCode,
                     agentEventDescription }
        DESCRIPTION
             "Loop context ID changed"
           --#TYPE      "Management Agent Event 25004"
           --#SUMMARY   "Host %s : SCellName-TimeDate %s : EventCode %d : Description %s"
           --#ARGUMENTS {0,1,2,3,}
            --#SEVERITY  INFORMATIONAL
            --#TIMEINDEX 136
        ::= 136025004

   mngmtAgentTrap-25005 TRAP-TYPE
        ENTERPRISE compaq
        VARIABLES  { hostName,
                     scellNameDateTime,
                     agentEventCode,
                     agentEventDescription }
        DESCRIPTION
             "Storage Cell context ID changed"
           --#TYPE      "Management Agent Event 25005"
           --#SUMMARY   "Host %s : SCellName-TimeDate %s : EventCode %d : Description %s"
           --#ARGUMENTS {0,1,2,3,}
            --#SEVERITY  INFORMATIONAL
            --#TIMEINDEX 136
        ::= 136025005

   mngmtAgentTrap-25006 TRAP-TYPE
        ENTERPRISE compaq
        VARIABLES  { hostName,
                     scellNameDateTime,
                     agentEventCode,
                     agentEventDescription }
        DESCRIPTION
             "Cache Write Failure"
           --#TYPE      "Management Agent Event 25006"
           --#SUMMARY   "Host %s : SCellName-TimeDate %s : EventCode %d : Description %s"
           --#ARGUMENTS {0,1,2,3,}
            --#SEVERITY  INFORMATIONAL
            --#TIMEINDEX 136
        ::= 136025006

   mngmtAgentTrap-25007 TRAP-TYPE
        ENTERPRISE compaq
        VARIABLES  { hostName,
                     scellNameDateTime,
                     agentEventCode,
                     agentEventDescription }
        DESCRIPTION
             "Battery Disable Failure"
           --#TYPE      "Management Agent Event 25007"
           --#SUMMARY   "Host %s : SCellName-TimeDate %s : EventCode %d : Description %s"
           --#ARGUMENTS {0,1,2,3,}
            --#SEVERITY  INFORMATIONAL
            --#TIMEINDEX 136
        ::= 136025007

   mngmtAgentTrap-25008 TRAP-TYPE
        ENTERPRISE compaq
        VARIABLES  { hostName,
                     scellNameDateTime,
                     agentEventCode,
                     agentEventDescription }
        DESCRIPTION
             "Drive Shelf Disable Failure"
           --#TYPE      "Management Agent Event 25008"
           --#SUMMARY   "Host %s : SCellName-TimeDate %s : EventCode %d : Description %s"
           --#ARGUMENTS {0,1,2,3,}
            --#SEVERITY  INFORMATIONAL
            --#TIMEINDEX 136
        ::= 136025008

   mngmtAgentTrap-25009 TRAP-TYPE
        ENTERPRISE compaq
        VARIABLES  { hostName,
                     scellNameDateTime,
                     agentEventCode,
                     agentEventDescription }
        DESCRIPTION
             "Shutdown Both Restart And Power Off Requested"
           --#TYPE      "Management Agent Event 25009"
           --#SUMMARY   "Host %s : SCellName-TimeDate %s : EventCode %d : Description %s"
           --#ARGUMENTS {0,1,2,3,}
            --#SEVERITY  INFORMATIONAL
            --#TIMEINDEX 136
        ::= 136025009

   mngmtAgentTrap-25010 TRAP-TYPE
        ENTERPRISE compaq
        VARIABLES  { hostName,
                     scellNameDateTime,
                     agentEventCode,
                     agentEventDescription }
        DESCRIPTION
             "Shutdown Drive Shelf Power Off But No Enclosure Power Off Requested"
           --#TYPE      "Management Agent Event 25010"
           --#SUMMARY   "Host %s : SCellName-TimeDate %s : EventCode %d : Description %s"
           --#ARGUMENTS {0,1,2,3,}
            --#SEVERITY  INFORMATIONAL
            --#TIMEINDEX 136
        ::= 136025010

   mngmtAgentTrap-25011 TRAP-TYPE
        ENTERPRISE compaq
        VARIABLES  { hostName,
                     scellNameDateTime,
                     agentEventCode,
                     agentEventDescription }
        DESCRIPTION
             "Shutdown Disable Battery But No Enclosure Power Off Requested"
           --#TYPE      "Management Agent Event 25011"
           --#SUMMARY   "Host %s : SCellName-TimeDate %s : EventCode %d : Description %s"
           --#ARGUMENTS {0,1,2,3,}
            --#SEVERITY  INFORMATIONAL
            --#TIMEINDEX 136
        ::= 136025011

   mngmtAgentTrap-25012 TRAP-TYPE
        ENTERPRISE compaq
        VARIABLES  { hostName,
                     scellNameDateTime,
                     agentEventCode,
                     agentEventDescription }
        DESCRIPTION
             "Shutdown Disable Battery But Shutdown Unconditional Requested"
           --#TYPE      "Management Agent Event 25012"
           --#SUMMARY   "Host %s : SCellName-TimeDate %s : EventCode %d : Description %s"
           --#ARGUMENTS {0,1,2,3,}
            --#SEVERITY  INFORMATIONAL
            --#TIMEINDEX 136
        ::= 136025012

   mngmtAgentTrap-25013 TRAP-TYPE
        ENTERPRISE compaq
        VARIABLES  { hostName,
                     scellNameDateTime,
                     agentEventCode,
                     agentEventDescription }
        DESCRIPTION
             "Shutdown Delay Out Of Range"
           --#TYPE      "Management Agent Event 25013"
           --#SUMMARY   "Host %s : SCellName-TimeDate %s : EventCode %d : Description %s"
           --#ARGUMENTS {0,1,2,3,}
            --#SEVERITY  INFORMATIONAL
            --#TIMEINDEX 136
        ::= 136025013

   mngmtAgentTrap-25014 TRAP-TYPE
        ENTERPRISE compaq
        VARIABLES  { hostName,
                     scellNameDateTime,
                     agentEventCode,
                     agentEventDescription }
        DESCRIPTION
             "Invalid Storage Cell name"
           --#TYPE      "Management Agent Event 25014"
           --#SUMMARY   "Host %s : SCellName-TimeDate %s : EventCode %d : Description %s"
           --#ARGUMENTS {0,1,2,3,}
            --#SEVERITY  INFORMATIONAL
            --#TIMEINDEX 136
        ::= 136025014

   mngmtAgentTrap-25015 TRAP-TYPE
        ENTERPRISE compaq
        VARIABLES  { hostName,
                     scellNameDateTime,
                     agentEventCode,
                     agentEventDescription }
        DESCRIPTION
             "Requested spares goal cannot be satisfied"
           --#TYPE      "Management Agent Event 25015"
           --#SUMMARY   "Host %s : SCellName-TimeDate %s : EventCode %d : Description %s"
           --#ARGUMENTS {0,1,2,3,}
            --#SEVERITY  INFORMATIONAL
            --#TIMEINDEX 136
        ::= 136025015

   mngmtAgentTrap-25016 TRAP-TYPE
        ENTERPRISE compaq
        VARIABLES  { hostName,
                     scellNameDateTime,
                     agentEventCode,
                     agentEventDescription }
        DESCRIPTION
             "No valid LDAD found"
           --#TYPE      "Management Agent Event 25016"
           --#SUMMARY   "Host %s : SCellName-TimeDate %s : EventCode %d : Description %s"
           --#ARGUMENTS {0,1,2,3,}
            --#SEVERITY  INFORMATIONAL
            --#TIMEINDEX 136
        ::= 136025016

   mngmtAgentTrap-25017 TRAP-TYPE
        ENTERPRISE compaq
        VARIABLES  { hostName,
                     scellNameDateTime,
                     agentEventCode,
                     agentEventDescription }
        DESCRIPTION
             "Mismatched MLD size"
           --#TYPE      "Management Agent Event 25017"
           --#SUMMARY   "Host %s : SCellName-TimeDate %s : EventCode %d : Description %s"
           --#ARGUMENTS {0,1,2,3,}
            --#SEVERITY  INFORMATIONAL
            --#TIMEINDEX 136
        ::= 136025017

   mngmtAgentTrap-25018 TRAP-TYPE
        ENTERPRISE compaq
        VARIABLES  { hostName,
                     scellNameDateTime,
                     agentEventCode,
                     agentEventDescription }
        DESCRIPTION
             "Codeload image file error"
           --#TYPE      "Management Agent Event 25018"
           --#SUMMARY   "Host %s : SCellName-TimeDate %s : EventCode %d : Description %s"
           --#ARGUMENTS {0,1,2,3,}
            --#SEVERITY  INFORMATIONAL
            --#TIMEINDEX 136
        ::= 136025018

   mngmtAgentTrap-25019 TRAP-TYPE
        ENTERPRISE compaq
        VARIABLES  { hostName,
                     scellNameDateTime,
                     agentEventCode,
                     agentEventDescription }
        DESCRIPTION
             "Storage System is not initialized"
           --#TYPE      "Management Agent Event 25019"
           --#SUMMARY   "Host %s : SCellName-TimeDate %s : EventCode %d : Description %s"
           --#ARGUMENTS {0,1,2,3,}
            --#SEVERITY  INFORMATIONAL
            --#TIMEINDEX 136
        ::= 136025019

   mngmtAgentTrap-26002 TRAP-TYPE
        ENTERPRISE compaq
        VARIABLES  { hostName,
                     scellNameDateTime,
                     agentEventCode,
                     agentEventDescription }
        DESCRIPTION
             "Invalid data replication operation"
           --#TYPE      "Management Agent Event 26002"
           --#SUMMARY   "Host %s : SCellName-TimeDate %s : EventCode %d : Description %s"
           --#ARGUMENTS {0,1,2,3,}
            --#SEVERITY  INFORMATIONAL
            --#TIMEINDEX 136
        ::= 136026002

   mngmtAgentTrap-26005 TRAP-TYPE
        ENTERPRISE compaq
        VARIABLES  { hostName,
                     scellNameDateTime,
                     agentEventCode,
                     agentEventDescription }
        DESCRIPTION
             "DR group name exceeds maximum length"
           --#TYPE      "Management Agent Event 26005"
           --#SUMMARY   "Host %s : SCellName-TimeDate %s : EventCode %d : Description %s"
           --#ARGUMENTS {0,1,2,3,}
            --#SEVERITY  INFORMATIONAL
            --#TIMEINDEX 136
        ::= 136026005

   mngmtAgentTrap-26006 TRAP-TYPE
        ENTERPRISE compaq
        VARIABLES  { hostName,
                     scellNameDateTime,
                     agentEventCode,
                     agentEventDescription }
        DESCRIPTION
             "DR group created successfully"
           --#TYPE      "Management Agent Event 26006"
           --#SUMMARY   "Host %s : SCellName-TimeDate %s : EventCode %d : Description %s"
           --#ARGUMENTS {0,1,2,3,}
            --#SEVERITY  INFORMATIONAL
            --#TIMEINDEX 136
        ::= 136026006

   mngmtAgentTrap-26007 TRAP-TYPE
        ENTERPRISE compaq
        VARIABLES  { hostName,
                     scellNameDateTime,
                     agentEventCode,
                     agentEventDescription }
        DESCRIPTION
             "Data replication invalid mode for DR Group create"
           --#TYPE      "Management Agent Event 26007"
           --#SUMMARY   "Host %s : SCellName-TimeDate %s : EventCode %d : Description %s"
           --#ARGUMENTS {0,1,2,3,}
            --#SEVERITY  INFORMATIONAL
            --#TIMEINDEX 136
        ::= 136026007

   mngmtAgentTrap-26008 TRAP-TYPE
        ENTERPRISE compaq
        VARIABLES  { hostName,
                     scellNameDateTime,
                     agentEventCode,
                     agentEventDescription }
        DESCRIPTION
             "A duplicate DR group name exists in the specified source or destination DR group."
           --#TYPE      "Management Agent Event 26008"
           --#SUMMARY   "Host %s : SCellName-TimeDate %s : EventCode %d : Description %s"
           --#ARGUMENTS {0,1,2,3,}
            --#SEVERITY  INFORMATIONAL
            --#TIMEINDEX 136
        ::= 136026008

   mngmtAgentTrap-26009 TRAP-TYPE
        ENTERPRISE compaq
        VARIABLES  { hostName,
                     scellNameDateTime,
                     agentEventCode,
                     agentEventDescription }
        DESCRIPTION
             "Data replication invalid operation while DR Groups exist"
           --#TYPE      "Management Agent Event 26009"
           --#SUMMARY   "Host %s : SCellName-TimeDate %s : EventCode %d : Description %s"
           --#ARGUMENTS {0,1,2,3,}
            --#SEVERITY  INFORMATIONAL
            --#TIMEINDEX 136
        ::= 136026009

   mngmtAgentTrap-26010 TRAP-TYPE
        ENTERPRISE compaq
        VARIABLES  { hostName,
                     scellNameDateTime,
                     agentEventCode,
                     agentEventDescription }
        DESCRIPTION
             "Data replication root folder does not exist"
           --#TYPE      "Management Agent Event 26010"
           --#SUMMARY   "Host %s : SCellName-TimeDate %s : EventCode %d : Description %s"
           --#ARGUMENTS {0,1,2,3,}
            --#SEVERITY  INFORMATIONAL
            --#TIMEINDEX 136
        ::= 136026010

   mngmtAgentTrap-26011 TRAP-TYPE
        ENTERPRISE compaq
        VARIABLES  { hostName,
                     scellNameDateTime,
                     agentEventCode,
                     agentEventDescription }
        DESCRIPTION
             "DR group discarded"
           --#TYPE      "Management Agent Event 26011"
           --#SUMMARY   "Host %s : SCellName-TimeDate %s : EventCode %d : Description %s"
           --#ARGUMENTS {0,1,2,3,}
            --#SEVERITY  INFORMATIONAL
            --#TIMEINDEX 136
        ::= 136026011

   mngmtAgentTrap-26012 TRAP-TYPE
        ENTERPRISE compaq
        VARIABLES  { hostName,
                     scellNameDateTime,
                     agentEventCode,
                     agentEventDescription }
        DESCRIPTION
             "Data replication unknown remote storage system"
           --#TYPE      "Management Agent Event 26012"
           --#SUMMARY   "Host %s : SCellName-TimeDate %s : EventCode %d : Description %s"
           --#ARGUMENTS {0,1,2,3,}
            --#SEVERITY  INFORMATIONAL
            --#TIMEINDEX 136
        ::= 136026012

   mngmtAgentTrap-26013 TRAP-TYPE
        ENTERPRISE compaq
        VARIABLES  { hostName,
                     scellNameDateTime,
                     agentEventCode,
                     agentEventDescription }
        DESCRIPTION
             "Data replication Error. A conflicting Vdisk name exists on the remote storage system."
           --#TYPE      "Management Agent Event 26013"
           --#SUMMARY   "Host %s : SCellName-TimeDate %s : EventCode %d : Description %s"
           --#ARGUMENTS {0,1,2,3,}
            --#SEVERITY  INFORMATIONAL
            --#TIMEINDEX 136
        ::= 136026013

   mngmtAgentTrap-26014 TRAP-TYPE
        ENTERPRISE compaq
        VARIABLES  { hostName,
                     scellNameDateTime,
                     agentEventCode,
                     agentEventDescription }
        DESCRIPTION
             "Data Replication Error. Invalid Remote Vdisk Name specified."
           --#TYPE      "Management Agent Event 26014"
           --#SUMMARY   "Host %s : SCellName-TimeDate %s : EventCode %d : Description %s"
           --#ARGUMENTS {0,1,2,3,}
            --#SEVERITY  INFORMATIONAL
            --#TIMEINDEX 136
        ::= 136026014

   mngmtAgentTrap-26015 TRAP-TYPE
        ENTERPRISE compaq
        VARIABLES  { hostName,
                     scellNameDateTime,
                     agentEventCode,
                     agentEventDescription }
        DESCRIPTION
             "Data Replication Error. Remote Vdisk size cannot be modified."
           --#TYPE      "Management Agent Event 26015"
           --#SUMMARY   "Host %s : SCellName-TimeDate %s : EventCode %d : Description %s"
           --#ARGUMENTS {0,1,2,3,}
            --#SEVERITY  INFORMATIONAL
            --#TIMEINDEX 136
        ::= 136026015

   mngmtAgentTrap-26016 TRAP-TYPE
        ENTERPRISE compaq
        VARIABLES  { hostName,
                     scellNameDateTime,
                     agentEventCode,
                     agentEventDescription }
        DESCRIPTION
             "Data Replication Error. Remote Vdisk should be unpresented to proceed with the discard/detach operation."
           --#TYPE      "Management Agent Event 26016"
           --#SUMMARY   "Host %s : SCellName-TimeDate %s : EventCode %d : Description %s"
           --#ARGUMENTS {0,1,2,3,}
            --#SEVERITY  INFORMATIONAL
            --#TIMEINDEX 136
        ::= 136026016

   mngmtAgentTrap-26017 TRAP-TYPE
        ENTERPRISE compaq
        VARIABLES  { hostName,
                     scellNameDateTime,
                     agentEventCode,
                     agentEventDescription }
        DESCRIPTION
             "The element manager has successfully deallocated the log associated with the specified DR Group. If data exists in the log, DR Group members will be marked for a full copy."
           --#TYPE      "Management Agent Event 26017"
           --#SUMMARY   "Host %s : SCellName-TimeDate %s : EventCode %d : Description %s"
           --#ARGUMENTS {0,1,2,3,}
            --#SEVERITY  INFORMATIONAL
            --#TIMEINDEX 136
        ::= 136026017

   mngmtAgentTrap-26018 TRAP-TYPE
        ENTERPRISE compaq
        VARIABLES  { hostName,
                     scellNameDateTime,
                     agentEventCode,
                     agentEventDescription }
        DESCRIPTION
             "The Data Replication value(s) specified in creating or modifying the DR group is invalid on this type of DR configuration."
           --#TYPE      "Management Agent Event 26018"
           --#SUMMARY   "Host %s : SCellName-TimeDate %s : EventCode %d : Description %s"
           --#ARGUMENTS {0,1,2,3,}
            --#SEVERITY  INFORMATIONAL
            --#TIMEINDEX 136
        ::= 136026018

   mngmtAgentTrap-26019 TRAP-TYPE
        ENTERPRISE compaq
        VARIABLES  { hostName,
                     scellNameDateTime,
                     agentEventCode,
                     agentEventDescription }
        DESCRIPTION
             "No DR Group exist as reported by the controllers."
           --#TYPE      "Management Agent Event 26019"
           --#SUMMARY   "Host %s : SCellName-TimeDate %s : EventCode %d : Description %s"
           --#ARGUMENTS {0,1,2,3,}
            --#SEVERITY  INFORMATIONAL
            --#TIMEINDEX 136
        ::= 136026019

   mngmtAgentTrap-26020 TRAP-TYPE
        ENTERPRISE compaq
        VARIABLES  { hostName,
                     scellNameDateTime,
                     agentEventCode,
                     agentEventDescription }
        DESCRIPTION
             "Mirror clone's source Vdisk cannot be a member of a DR Group."
           --#TYPE      "Management Agent Event 26020"
           --#SUMMARY   "Host %s : SCellName-TimeDate %s : EventCode %d : Description %s"
           --#ARGUMENTS {0,1,2,3,}
            --#SEVERITY  INFORMATIONAL
            --#TIMEINDEX 136
        ::= 136026020

   mngmtAgentTrap-26021 TRAP-TYPE
        ENTERPRISE compaq
        VARIABLES  { hostName,
                     scellNameDateTime,
                     agentEventCode,
                     agentEventDescription }
        DESCRIPTION
             "The requested operation cannot be performed when the link is suspended."
           --#TYPE      "Management Agent Event 26021"
           --#SUMMARY   "Host %s : SCellName-TimeDate %s : EventCode %d : Description %s"
           --#ARGUMENTS {0,1,2,3,}
            --#SEVERITY  INFORMATIONAL
            --#TIMEINDEX 136
        ::= 136026021

   mngmtAgentTrap-26022 TRAP-TYPE
        ENTERPRISE compaq
        VARIABLES  { hostName,
                     scellNameDateTime,
                     agentEventCode,
                     agentEventDescription }
        DESCRIPTION
             "The requested operation cannot be performed when the link is suspended."
           --#TYPE      "Management Agent Event 26022"
           --#SUMMARY   "Host %s : SCellName-TimeDate %s : EventCode %d : Description %s"
           --#ARGUMENTS {0,1,2,3,}
            --#SEVERITY  INFORMATIONAL
            --#TIMEINDEX 136
        ::= 136026022

   mngmtAgentTrap-26023 TRAP-TYPE
        ENTERPRISE compaq
        VARIABLES  { hostName,
                     scellNameDateTime,
                     agentEventCode,
                     agentEventDescription }
        DESCRIPTION
             "The requested operation cannot be performed when the DR Group is in Async Merging state"
           --#TYPE      "Management Agent Event 26023"
           --#SUMMARY   "Host %s : SCellName-TimeDate %s : EventCode %d : Description %s"
           --#ARGUMENTS {0,1,2,3,}
            --#SEVERITY  INFORMATIONAL
            --#TIMEINDEX 136
        ::= 136026023

   mngmtAgentTrap-26024 TRAP-TYPE
        ENTERPRISE compaq
        VARIABLES  { hostName,
                     scellNameDateTime,
                     agentEventCode,
                     agentEventDescription }
        DESCRIPTION
             "The requested operation cannot be performed when the DR Group is in Async Merging (Removal) state"
           --#TYPE      "Management Agent Event 26024"
           --#SUMMARY   "Host %s : SCellName-TimeDate %s : EventCode %d : Description %s"
           --#ARGUMENTS {0,1,2,3,}
            --#SEVERITY  INFORMATIONAL
            --#TIMEINDEX 136
        ::= 136026024

   mngmtAgentTrap-26025 TRAP-TYPE
        ENTERPRISE compaq
        VARIABLES  { hostName,
                     scellNameDateTime,
                     agentEventCode,
                     agentEventDescription }
        DESCRIPTION
             "Failover not allowed when writemode is asynchronous and inter-site links are operational"
           --#TYPE      "Management Agent Event 26025"
           --#SUMMARY   "Host %s : SCellName-TimeDate %s : EventCode %d : Description %s"
           --#ARGUMENTS {0,1,2,3,}
            --#SEVERITY  INFORMATIONAL
            --#TIMEINDEX 136
        ::= 136026025

   mngmtAgentTrap-26026 TRAP-TYPE
        ENTERPRISE compaq
        VARIABLES  { hostName,
                     scellNameDateTime,
                     agentEventCode,
                     agentEventDescription }
        DESCRIPTION
             "DR Port Preferences operation not allowed with this firmware version"
           --#TYPE      "Management Agent Event 26026"
           --#SUMMARY   "Host %s : SCellName-TimeDate %s : EventCode %d : Description %s"
           --#ARGUMENTS {0,1,2,3,}
            --#SEVERITY  INFORMATIONAL
            --#TIMEINDEX 136
        ::= 136026026

   mngmtAgentTrap-26027 TRAP-TYPE
        ENTERPRISE compaq
        VARIABLES  { hostName,
                     scellNameDateTime,
                     agentEventCode,
                     agentEventDescription }
        DESCRIPTION
             "No remote storage systems found"
           --#TYPE      "Management Agent Event 26027"
           --#SUMMARY   "Host %s : SCellName-TimeDate %s : EventCode %d : Description %s"
           --#ARGUMENTS {0,1,2,3,}
            --#SEVERITY  INFORMATIONAL
            --#TIMEINDEX 136
        ::= 136026027

   mngmtAgentTrap-26028 TRAP-TYPE
        ENTERPRISE compaq
        VARIABLES  { hostName,
                     scellNameDateTime,
                     agentEventCode,
                     agentEventDescription }
        DESCRIPTION
             "DR Routing Protocol Settings not allowed with this firmware version"
           --#TYPE      "Management Agent Event 26028"
           --#SUMMARY   "Host %s : SCellName-TimeDate %s : EventCode %d : Description %s"
           --#ARGUMENTS {0,1,2,3,}
            --#SEVERITY  INFORMATIONAL
            --#TIMEINDEX 136
        ::= 136026028

   mngmtAgentTrap-27001 TRAP-TYPE
        ENTERPRISE compaq
        VARIABLES  { hostName,
                     scellNameDateTime,
                     agentEventCode,
                     agentEventDescription }
        DESCRIPTION
             "The element manager has successfully initialized storage system. Command issued through XML Interface."
           --#TYPE      "Management Agent Event 27001"
           --#SUMMARY   "Host %s : SCellName-TimeDate %s : EventCode %d : Description %s"
           --#ARGUMENTS {0,1,2,3,}
            --#SEVERITY  INFORMATIONAL
            --#TIMEINDEX 136
        ::= 136027001

   mngmtAgentTrap-27002 TRAP-TYPE
        ENTERPRISE compaq
        VARIABLES  { hostName,
                     scellNameDateTime,
                     agentEventCode,
                     agentEventDescription }
        DESCRIPTION
             "The element manager has successfully created a virtual disk. Command issued through the XML Interface."
           --#TYPE      "Management Agent Event 27002"
           --#SUMMARY   "Host %s : SCellName-TimeDate %s : EventCode %d : Description %s"
           --#ARGUMENTS {0,1,2,3,}
            --#SEVERITY  INFORMATIONAL
            --#TIMEINDEX 136
        ::= 136027002

   mngmtAgentTrap-27003 TRAP-TYPE
        ENTERPRISE compaq
        VARIABLES  { hostName,
                     scellNameDateTime,
                     agentEventCode,
                     agentEventDescription }
        DESCRIPTION
             "The element manager has successfully created a disk group. Command issued through the XML Interface."
           --#TYPE      "Management Agent Event 27003"
           --#SUMMARY   "Host %s : SCellName-TimeDate %s : EventCode %d : Description %s"
           --#ARGUMENTS {0,1,2,3,}
            --#SEVERITY  INFORMATIONAL
            --#TIMEINDEX 136
        ::= 136027003

   mngmtAgentTrap-27004 TRAP-TYPE
        ENTERPRISE compaq
        VARIABLES  { hostName,
                     scellNameDateTime,
                     agentEventCode,
                     agentEventDescription }
        DESCRIPTION
             "The element manager has successfully created a DRM group. Command issued through the XML Interface."
           --#TYPE      "Management Agent Event 27004"
           --#SUMMARY   "Host %s : SCellName-TimeDate %s : EventCode %d : Description %s"
           --#ARGUMENTS {0,1,2,3,}
            --#SEVERITY  INFORMATIONAL
            --#TIMEINDEX 136
        ::= 136027004

   mngmtAgentTrap-27005 TRAP-TYPE
        ENTERPRISE compaq
        VARIABLES  { hostName,
                     scellNameDateTime,
                     agentEventCode,
                     agentEventDescription }
        DESCRIPTION
             "The element manager has successfully created a host. Command issued through the XML Interface."
           --#TYPE      "Management Agent Event 27005"
           --#SUMMARY   "Host %s : SCellName-TimeDate %s : EventCode %d : Description %s"
           --#ARGUMENTS {0,1,2,3,}
            --#SEVERITY  INFORMATIONAL
            --#TIMEINDEX 136
        ::= 136027005

   mngmtAgentTrap-27006 TRAP-TYPE
        ENTERPRISE compaq
        VARIABLES  { hostName,
                     scellNameDateTime,
                     agentEventCode,
                     agentEventDescription }
        DESCRIPTION
             "The element manager has successfully created a presented unit. Command issued through the XML Interface."
           --#TYPE      "Management Agent Event 27006"
           --#SUMMARY   "Host %s : SCellName-TimeDate %s : EventCode %d : Description %s"
           --#ARGUMENTS {0,1,2,3,}
            --#SEVERITY  INFORMATIONAL
            --#TIMEINDEX 136
        ::= 136027006

   mngmtAgentTrap-27007 TRAP-TYPE
        ENTERPRISE compaq
        VARIABLES  { hostName,
                     scellNameDateTime,
                     agentEventCode,
                     agentEventDescription }
        DESCRIPTION
             "The element manager has successfully created a virtual disk folder. Command issued through the XML Interface."
           --#TYPE      "Management Agent Event 27007"
           --#SUMMARY   "Host %s : SCellName-TimeDate %s : EventCode %d : Description %s"
           --#ARGUMENTS {0,1,2,3,}
            --#SEVERITY  INFORMATIONAL
            --#TIMEINDEX 136
        ::= 136027007

   mngmtAgentTrap-27008 TRAP-TYPE
        ENTERPRISE compaq
        VARIABLES  { hostName,
                     scellNameDateTime,
                     agentEventCode,
                     agentEventDescription }
        DESCRIPTION
             "The element manager has successfully created a host folder. Command issued through the XML Interface."
           --#TYPE      "Management Agent Event 27008"
           --#SUMMARY   "Host %s : SCellName-TimeDate %s : EventCode %d : Description %s"
           --#ARGUMENTS {0,1,2,3,}
            --#SEVERITY  INFORMATIONAL
            --#TIMEINDEX 136
        ::= 136027008

   mngmtAgentTrap-27009 TRAP-TYPE
        ENTERPRISE compaq
        VARIABLES  { hostName,
                     scellNameDateTime,
                     agentEventCode,
                     agentEventDescription }
        DESCRIPTION
             "The element manager has successfully created a disk group folder. Command issued through the XML Interface."
           --#TYPE      "Management Agent Event 27009"
           --#SUMMARY   "Host %s : SCellName-TimeDate %s : EventCode %d : Description %s"
           --#ARGUMENTS {0,1,2,3,}
            --#SEVERITY  INFORMATIONAL
            --#TIMEINDEX 136
        ::= 136027009

   mngmtAgentTrap-27010 TRAP-TYPE
        ENTERPRISE compaq
        VARIABLES  { hostName,
                     scellNameDateTime,
                     agentEventCode,
                     agentEventDescription }
        DESCRIPTION
             "The element manager has successfully created a DRM group folder. Command issued through the XML Interface."
           --#TYPE      "Management Agent Event 27010"
           --#SUMMARY   "Host %s : SCellName-TimeDate %s : EventCode %d : Description %s"
           --#ARGUMENTS {0,1,2,3,}
            --#SEVERITY  INFORMATIONAL
            --#TIMEINDEX 136
        ::= 136027010

   mngmtAgentTrap-27011 TRAP-TYPE
        ENTERPRISE compaq
        VARIABLES  { hostName,
                     scellNameDateTime,
                     agentEventCode,
                     agentEventDescription }
        DESCRIPTION
             "The element manager has successfully created a folder. Command issued through the XML Interface."
           --#TYPE      "Management Agent Event 27011"
           --#SUMMARY   "Host %s : SCellName-TimeDate %s : EventCode %d : Description %s"
           --#ARGUMENTS {0,1,2,3,}
            --#SEVERITY  INFORMATIONAL
            --#TIMEINDEX 136
        ::= 136027011

   mngmtAgentTrap-27012 TRAP-TYPE
        ENTERPRISE compaq
        VARIABLES  { hostName,
                     scellNameDateTime,
                     agentEventCode,
                     agentEventDescription }
        DESCRIPTION
             "The element manager has successfully created a snapshot. Command issued through the XML Interface."
           --#TYPE      "Management Agent Event 27012"
           --#SUMMARY   "Host %s : SCellName-TimeDate %s : EventCode %d : Description %s"
           --#ARGUMENTS {0,1,2,3,}
            --#SEVERITY  INFORMATIONAL
            --#TIMEINDEX 136
        ::= 136027012

   mngmtAgentTrap-27013 TRAP-TYPE
        ENTERPRISE compaq
        VARIABLES  { hostName,
                     scellNameDateTime,
                     agentEventCode,
                     agentEventDescription }
        DESCRIPTION
             "The element manager has successfully created a snapclone. Command issued through the XML Interface."
           --#TYPE      "Management Agent Event 27013"
           --#SUMMARY   "Host %s : SCellName-TimeDate %s : EventCode %d : Description %s"
           --#ARGUMENTS {0,1,2,3,}
            --#SEVERITY  INFORMATIONAL
            --#TIMEINDEX 136
        ::= 136027013

   mngmtAgentTrap-27014 TRAP-TYPE
        ENTERPRISE compaq
        VARIABLES  { hostName,
                     scellNameDateTime,
                     agentEventCode,
                     agentEventDescription }
        DESCRIPTION
             "The element manager has successfully uninitialized the storage system. Command issued through the XML Interface."
           --#TYPE      "Management Agent Event 27014"
           --#SUMMARY   "Host %s : SCellName-TimeDate %s : EventCode %d : Description %s"
           --#ARGUMENTS {0,1,2,3,}
            --#SEVERITY  INFORMATIONAL
            --#TIMEINDEX 136
        ::= 136027014

   mngmtAgentTrap-27015 TRAP-TYPE
        ENTERPRISE compaq
        VARIABLES  { hostName,
                     scellNameDateTime,
                     agentEventCode,
                     agentEventDescription }
        DESCRIPTION
             "The element manager has successfully deleted a virtual disk. Command issued through the XML Interface."
           --#TYPE      "Management Agent Event 27015"
           --#SUMMARY   "Host %s : SCellName-TimeDate %s : EventCode %d : Description %s"
           --#ARGUMENTS {0,1,2,3,}
            --#SEVERITY  INFORMATIONAL
            --#TIMEINDEX 136
        ::= 136027015

   mngmtAgentTrap-27016 TRAP-TYPE
        ENTERPRISE compaq
        VARIABLES  { hostName,
                     scellNameDateTime,
                     agentEventCode,
                     agentEventDescription }
        DESCRIPTION
             "The element manager has successfully deleted a disk group. Command issued through the XML Interface."
           --#TYPE      "Management Agent Event 27016"
           --#SUMMARY   "Host %s : SCellName-TimeDate %s : EventCode %d : Description %s"
           --#ARGUMENTS {0,1,2,3,}
            --#SEVERITY  INFORMATIONAL
            --#TIMEINDEX 136
        ::= 136027016

   mngmtAgentTrap-27017 TRAP-TYPE
        ENTERPRISE compaq
        VARIABLES  { hostName,
                     scellNameDateTime,
                     agentEventCode,
                     agentEventDescription }
        DESCRIPTION
             "The element manager has successfully deleted a DRM group. Command issued through the XML Interface."
           --#TYPE      "Management Agent Event 27017"
           --#SUMMARY   "Host %s : SCellName-TimeDate %s : EventCode %d : Description %s"
           --#ARGUMENTS {0,1,2,3,}
            --#SEVERITY  INFORMATIONAL
            --#TIMEINDEX 136
        ::= 136027017

   mngmtAgentTrap-27018 TRAP-TYPE
        ENTERPRISE compaq
        VARIABLES  { hostName,
                     scellNameDateTime,
                     agentEventCode,
                     agentEventDescription }
        DESCRIPTION
             "The element manager has successfully deleted a host. Command issued through the XML Interface."
           --#TYPE      "Management Agent Event 27018"
           --#SUMMARY   "Host %s : SCellName-TimeDate %s : EventCode %d : Description %s"
           --#ARGUMENTS {0,1,2,3,}
            --#SEVERITY  INFORMATIONAL
            --#TIMEINDEX 136
        ::= 136027018

   mngmtAgentTrap-27019 TRAP-TYPE
        ENTERPRISE compaq
        VARIABLES  { hostName,
                     scellNameDateTime,
                     agentEventCode,
                     agentEventDescription }
        DESCRIPTION
             "The element manager has successfully deleted a presented unit. Command issued through the XML Interface."
           --#TYPE      "Management Agent Event 27019"
           --#SUMMARY   "Host %s : SCellName-TimeDate %s : EventCode %d : Description %s"
           --#ARGUMENTS {0,1,2,3,}
            --#SEVERITY  INFORMATIONAL
            --#TIMEINDEX 136
        ::= 136027019

   mngmtAgentTrap-27020 TRAP-TYPE
        ENTERPRISE compaq
        VARIABLES  { hostName,
                     scellNameDateTime,
                     agentEventCode,
                     agentEventDescription }
        DESCRIPTION
             "The element manager has successfully deleted a virtual disk folder. Command issued through the XML Interface."
           --#TYPE      "Management Agent Event 27020"
           --#SUMMARY   "Host %s : SCellName-TimeDate %s : EventCode %d : Description %s"
           --#ARGUMENTS {0,1,2,3,}
            --#SEVERITY  INFORMATIONAL
            --#TIMEINDEX 136
        ::= 136027020

   mngmtAgentTrap-27021 TRAP-TYPE
        ENTERPRISE compaq
        VARIABLES  { hostName,
                     scellNameDateTime,
                     agentEventCode,
                     agentEventDescription }
        DESCRIPTION
             "The element manager has successfully deleted a host folder. Command issued through the XML Interface."
           --#TYPE      "Management Agent Event 27021"
           --#SUMMARY   "Host %s : SCellName-TimeDate %s : EventCode %d : Description %s"
           --#ARGUMENTS {0,1,2,3,}
            --#SEVERITY  INFORMATIONAL
            --#TIMEINDEX 136
        ::= 136027021

   mngmtAgentTrap-27022 TRAP-TYPE
        ENTERPRISE compaq
        VARIABLES  { hostName,
                     scellNameDateTime,
                     agentEventCode,
                     agentEventDescription }
        DESCRIPTION
             "The element manager has successfully deleted a disk group folder. Command issued through the XML Interface."
           --#TYPE      "Management Agent Event 27022"
           --#SUMMARY   "Host %s : SCellName-TimeDate %s : EventCode %d : Description %s"
           --#ARGUMENTS {0,1,2,3,}
            --#SEVERITY  INFORMATIONAL
            --#TIMEINDEX 136
        ::= 136027022

   mngmtAgentTrap-27023 TRAP-TYPE
        ENTERPRISE compaq
        VARIABLES  { hostName,
                     scellNameDateTime,
                     agentEventCode,
                     agentEventDescription }
        DESCRIPTION
             "The element manager has successfully deleted a DRM group folder. Command issued through the XML Interface."
           --#TYPE      "Management Agent Event 27023"
           --#SUMMARY   "Host %s : SCellName-TimeDate %s : EventCode %d : Description %s"
           --#ARGUMENTS {0,1,2,3,}
            --#SEVERITY  INFORMATIONAL
            --#TIMEINDEX 136
        ::= 136027023

   mngmtAgentTrap-27024 TRAP-TYPE
        ENTERPRISE compaq
        VARIABLES  { hostName,
                     scellNameDateTime,
                     agentEventCode,
                     agentEventDescription }
        DESCRIPTION
             "The element manager has successfully deleted a folder. Command issued through the XML Interface."
           --#TYPE      "Management Agent Event 27024"
           --#SUMMARY   "Host %s : SCellName-TimeDate %s : EventCode %d : Description %s"
           --#ARGUMENTS {0,1,2,3,}
            --#SEVERITY  INFORMATIONAL
            --#TIMEINDEX 136
        ::= 136027024

   mngmtAgentTrap-27025 TRAP-TYPE
        ENTERPRISE compaq
        VARIABLES  { hostName,
                     scellNameDateTime,
                     agentEventCode,
                     agentEventDescription }
        DESCRIPTION
             "The element manager has successfully deleted a snapshot. Command issued through the XML Interface."
           --#TYPE      "Management Agent Event 27025"
           --#SUMMARY   "Host %s : SCellName-TimeDate %s : EventCode %d : Description %s"
           --#ARGUMENTS {0,1,2,3,}
            --#SEVERITY  INFORMATIONAL
            --#TIMEINDEX 136
        ::= 136027025

   mngmtAgentTrap-27026 TRAP-TYPE
        ENTERPRISE compaq
        VARIABLES  { hostName,
                     scellNameDateTime,
                     agentEventCode,
                     agentEventDescription }
        DESCRIPTION
             "The element manager has successfully modified the properties of a storage system. Command issued through the XML Interface."
           --#TYPE      "Management Agent Event 27026"
           --#SUMMARY   "Host %s : SCellName-TimeDate %s : EventCode %d : Description %s"
           --#ARGUMENTS {0,1,2,3,}
            --#SEVERITY  INFORMATIONAL
            --#TIMEINDEX 136
        ::= 136027026

   mngmtAgentTrap-27027 TRAP-TYPE
        ENTERPRISE compaq
        VARIABLES  { hostName,
                     scellNameDateTime,
                     agentEventCode,
                     agentEventDescription }
        DESCRIPTION
             "The element manager has successfully modified the properties of a virtual disk. Command issued through the XML Interface."
           --#TYPE      "Management Agent Event 27027"
           --#SUMMARY   "Host %s : SCellName-TimeDate %s : EventCode %d : Description %s"
           --#ARGUMENTS {0,1,2,3,}
            --#SEVERITY  INFORMATIONAL
            --#TIMEINDEX 136
        ::= 136027027

   mngmtAgentTrap-27028 TRAP-TYPE
        ENTERPRISE compaq
        VARIABLES  { hostName,
                     scellNameDateTime,
                     agentEventCode,
                     agentEventDescription }
        DESCRIPTION
             "The element manager has successfully modified the properties of a disk group. Command issued through the XML Interface."
           --#TYPE      "Management Agent Event 27028"
           --#SUMMARY   "Host %s : SCellName-TimeDate %s : EventCode %d : Description %s"
           --#ARGUMENTS {0,1,2,3,}
            --#SEVERITY  INFORMATIONAL
            --#TIMEINDEX 136
        ::= 136027028

   mngmtAgentTrap-27029 TRAP-TYPE
        ENTERPRISE compaq
        VARIABLES  { hostName,
                     scellNameDateTime,
                     agentEventCode,
                     agentEventDescription }
        DESCRIPTION
             "The element manager has successfully modified the properties of a DRM group. Command issued through the XML Interface."
           --#TYPE      "Management Agent Event 27029"
           --#SUMMARY   "Host %s : SCellName-TimeDate %s : EventCode %d : Description %s"
           --#ARGUMENTS {0,1,2,3,}
            --#SEVERITY  INFORMATIONAL
            --#TIMEINDEX 136
        ::= 136027029

   mngmtAgentTrap-27030 TRAP-TYPE
        ENTERPRISE compaq
        VARIABLES  { hostName,
                     scellNameDateTime,
                     agentEventCode,
                     agentEventDescription }
        DESCRIPTION
             "The element manager has successfully modified the properties of a host. Command issued through the XML Interface."
           --#TYPE      "Management Agent Event 27030"
           --#SUMMARY   "Host %s : SCellName-TimeDate %s : EventCode %d : Description %s"
           --#ARGUMENTS {0,1,2,3,}
            --#SEVERITY  INFORMATIONAL
            --#TIMEINDEX 136
        ::= 136027030

   mngmtAgentTrap-27031 TRAP-TYPE
        ENTERPRISE compaq
        VARIABLES  { hostName,
                     scellNameDateTime,
                     agentEventCode,
                     agentEventDescription }
        DESCRIPTION
             "The element manager has successfully modified the properties of a presented unit. Command issued through the XML Interface."
           --#TYPE      "Management Agent Event 27031"
           --#SUMMARY   "Host %s : SCellName-TimeDate %s : EventCode %d : Description %s"
           --#ARGUMENTS {0,1,2,3,}
            --#SEVERITY  INFORMATIONAL
            --#TIMEINDEX 136
        ::= 136027031

   mngmtAgentTrap-27032 TRAP-TYPE
        ENTERPRISE compaq
        VARIABLES  { hostName,
                     scellNameDateTime,
                     agentEventCode,
                     agentEventDescription }
        DESCRIPTION
             "The element manager has successfully modified the properties of a virtual disk folder. Command issued through the XML Interface."
           --#TYPE      "Management Agent Event 27032"
           --#SUMMARY   "Host %s : SCellName-TimeDate %s : EventCode %d : Description %s"
           --#ARGUMENTS {0,1,2,3,}
            --#SEVERITY  INFORMATIONAL
            --#TIMEINDEX 136
        ::= 136027032

   mngmtAgentTrap-27033 TRAP-TYPE
        ENTERPRISE compaq
        VARIABLES  { hostName,
                     scellNameDateTime,
                     agentEventCode,
                     agentEventDescription }
        DESCRIPTION
             "The element manager has successfully modified the properties of a host folder. Command issued through the XML Interface."
           --#TYPE      "Management Agent Event 27033"
           --#SUMMARY   "Host %s : SCellName-TimeDate %s : EventCode %d : Description %s"
           --#ARGUMENTS {0,1,2,3,}
            --#SEVERITY  INFORMATIONAL
            --#TIMEINDEX 136
        ::= 136027033

   mngmtAgentTrap-27034 TRAP-TYPE
        ENTERPRISE compaq
        VARIABLES  { hostName,
                     scellNameDateTime,
                     agentEventCode,
                     agentEventDescription }
        DESCRIPTION
             "The element manager has successfully modified the properties of a hardware root folder. Command issued through the XML Interface."
           --#TYPE      "Management Agent Event 27034"
           --#SUMMARY   "Host %s : SCellName-TimeDate %s : EventCode %d : Description %s"
           --#ARGUMENTS {0,1,2,3,}
            --#SEVERITY  INFORMATIONAL
            --#TIMEINDEX 136
        ::= 136027034

   mngmtAgentTrap-27035 TRAP-TYPE
        ENTERPRISE compaq
        VARIABLES  { hostName,
                     scellNameDateTime,
                     agentEventCode,
                     agentEventDescription }
        DESCRIPTION
             "The element manager has successfully modified the properties of a disk group folder. Command issued through the XML Interface."
           --#TYPE      "Management Agent Event 27035"
           --#SUMMARY   "Host %s : SCellName-TimeDate %s : EventCode %d : Description %s"
           --#ARGUMENTS {0,1,2,3,}
            --#SEVERITY  INFORMATIONAL
            --#TIMEINDEX 136
        ::= 136027035

   mngmtAgentTrap-27036 TRAP-TYPE
        ENTERPRISE compaq
        VARIABLES  { hostName,
                     scellNameDateTime,
                     agentEventCode,
                     agentEventDescription }
        DESCRIPTION
             "The element manager has successfully modified the properties of a DRM group folder. Command issued through the XML Interface."
           --#TYPE      "Management Agent Event 27036"
           --#SUMMARY   "Host %s : SCellName-TimeDate %s : EventCode %d : Description %s"
           --#ARGUMENTS {0,1,2,3,}
            --#SEVERITY  INFORMATIONAL
            --#TIMEINDEX 136
        ::= 136027036

   mngmtAgentTrap-27037 TRAP-TYPE
        ENTERPRISE compaq
        VARIABLES  { hostName,
                     scellNameDateTime,
                     agentEventCode,
                     agentEventDescription }
        DESCRIPTION
             "The element manager has successfully modified the properties of a DRM group root folder. Command issued through the XML Interface."
           --#TYPE      "Management Agent Event 27037"
           --#SUMMARY   "Host %s : SCellName-TimeDate %s : EventCode %d : Description %s"
           --#ARGUMENTS {0,1,2,3,}
            --#SEVERITY  INFORMATIONAL
            --#TIMEINDEX 136
        ::= 136027037

   mngmtAgentTrap-27038 TRAP-TYPE
        ENTERPRISE compaq
        VARIABLES  { hostName,
                     scellNameDateTime,
                     agentEventCode,
                     agentEventDescription }
        DESCRIPTION
             "The element manager has successfully modified the properties of a folder. Command issued through the XML Interface."
           --#TYPE      "Management Agent Event 27038"
           --#SUMMARY   "Host %s : SCellName-TimeDate %s : EventCode %d : Description %s"
           --#ARGUMENTS {0,1,2,3,}
            --#SEVERITY  INFORMATIONAL
            --#TIMEINDEX 136
        ::= 136027038

   mngmtAgentTrap-27039 TRAP-TYPE
        ENTERPRISE compaq
        VARIABLES  { hostName,
                     scellNameDateTime,
                     agentEventCode,
                     agentEventDescription }
        DESCRIPTION
             "The element manager has successfully modified the properties of a snapshot. Command issued through the XML Interface."
           --#TYPE      "Management Agent Event 27039"
           --#SUMMARY   "Host %s : SCellName-TimeDate %s : EventCode %d : Description %s"
           --#ARGUMENTS {0,1,2,3,}
            --#SEVERITY  INFORMATIONAL
            --#TIMEINDEX 136
        ::= 136027039

   mngmtAgentTrap-27040 TRAP-TYPE
        ENTERPRISE compaq
        VARIABLES  { hostName,
                     scellNameDateTime,
                     agentEventCode,
                     agentEventDescription }
        DESCRIPTION
             "The element manager has successfully modified the properties of a disk. Command issued through the XML Interface."
           --#TYPE      "Management Agent Event 27040"
           --#SUMMARY   "Host %s : SCellName-TimeDate %s : EventCode %d : Description %s"
           --#ARGUMENTS {0,1,2,3,}
            --#SEVERITY  INFORMATIONAL
            --#TIMEINDEX 136
        ::= 136027040

   mngmtAgentTrap-27041 TRAP-TYPE
        ENTERPRISE compaq
        VARIABLES  { hostName,
                     scellNameDateTime,
                     agentEventCode,
                     agentEventDescription }
        DESCRIPTION
             "The element manager has successfully modified the properties of a disk shelf. Command issued through the XML Interface."
           --#TYPE      "Management Agent Event 27041"
           --#SUMMARY   "Host %s : SCellName-TimeDate %s : EventCode %d : Description %s"
           --#ARGUMENTS {0,1,2,3,}
            --#SEVERITY  INFORMATIONAL
            --#TIMEINDEX 136
        ::= 136027041

   mngmtAgentTrap-27042 TRAP-TYPE
        ENTERPRISE compaq
        VARIABLES  { hostName,
                     scellNameDateTime,
                     agentEventCode,
                     agentEventDescription }
        DESCRIPTION
             "The element manager has successfully modified the properties of a controller. Command issued through the XML Interface."
           --#TYPE      "Management Agent Event 27042"
           --#SUMMARY   "Host %s : SCellName-TimeDate %s : EventCode %d : Description %s"
           --#ARGUMENTS {0,1,2,3,}
            --#SEVERITY  INFORMATIONAL
            --#TIMEINDEX 136
        ::= 136027042

   mngmtAgentTrap-27043 TRAP-TYPE
        ENTERPRISE compaq
        VARIABLES  { hostName,
                     scellNameDateTime,
                     agentEventCode,
                     agentEventDescription }
        DESCRIPTION
             "The element manager has successfully modified the properties of a controller shelf. Command issued through the XML Interface."
           --#TYPE      "Management Agent Event 27043"
           --#SUMMARY   "Host %s : SCellName-TimeDate %s : EventCode %d : Description %s"
           --#ARGUMENTS {0,1,2,3,}
            --#SEVERITY  INFORMATIONAL
            --#TIMEINDEX 136
        ::= 136027043

   mngmtAgentTrap-27044 TRAP-TYPE
        ENTERPRISE compaq
        VARIABLES  { hostName,
                     scellNameDateTime,
                     agentEventCode,
                     agentEventDescription }
        DESCRIPTION
             "The element manager has successfully modified the properties of a cabinet. Command issued through the XML Interface."
           --#TYPE      "Management Agent Event 27044"
           --#SUMMARY   "Host %s : SCellName-TimeDate %s : EventCode %d : Description %s"
           --#ARGUMENTS {0,1,2,3,}
            --#SEVERITY  INFORMATIONAL
            --#TIMEINDEX 136
        ::= 136027044

   mngmtAgentTrap-27045 TRAP-TYPE
        ENTERPRISE compaq
        VARIABLES  { hostName,
                     scellNameDateTime,
                     agentEventCode,
                     agentEventDescription }
        DESCRIPTION
             "The element manager has successfully reserved an object. Command issued through the XML Interface."
           --#TYPE      "Management Agent Event 27045"
           --#SUMMARY   "Host %s : SCellName-TimeDate %s : EventCode %d : Description %s"
           --#ARGUMENTS {0,1,2,3,}
            --#SEVERITY  INFORMATIONAL
            --#TIMEINDEX 136
        ::= 136027045

   mngmtAgentTrap-27046 TRAP-TYPE
        ENTERPRISE compaq
        VARIABLES  { hostName,
                     scellNameDateTime,
                     agentEventCode,
                     agentEventDescription }
        DESCRIPTION
             "The element manager has successfully released an object. Command issued through the XML Interface."
           --#TYPE      "Management Agent Event 27046"
           --#SUMMARY   "Host %s : SCellName-TimeDate %s : EventCode %d : Description %s"
           --#ARGUMENTS {0,1,2,3,}
            --#SEVERITY  INFORMATIONAL
            --#TIMEINDEX 136
        ::= 136027046

   mngmtAgentTrap-27047 TRAP-TYPE
        ENTERPRISE compaq
        VARIABLES  { hostName,
                     scellNameDateTime,
                     agentEventCode,
                     agentEventDescription }
        DESCRIPTION
             "XML cache mutex timeout."
           --#TYPE      "Management Agent Event 27047"
           --#SUMMARY   "Host %s : SCellName-TimeDate %s : EventCode %d : Description %s"
           --#ARGUMENTS {0,1,2,3,}
            --#SEVERITY  INFORMATIONAL
            --#TIMEINDEX 136
        ::= 136027047

   mngmtAgentTrap-27048 TRAP-TYPE
        ENTERPRISE compaq
        VARIABLES  { hostName,
                     scellNameDateTime,
                     agentEventCode,
                     agentEventDescription }
        DESCRIPTION
             "XML cache memory allocation error."
           --#TYPE      "Management Agent Event 27048"
           --#SUMMARY   "Host %s : SCellName-TimeDate %s : EventCode %d : Description %s"
           --#ARGUMENTS {0,1,2,3,}
            --#SEVERITY  INFORMATIONAL
            --#TIMEINDEX 136
        ::= 136027048

   mngmtAgentTrap-27049 TRAP-TYPE
        ENTERPRISE compaq
        VARIABLES  { hostName,
                     scellNameDateTime,
                     agentEventCode,
                     agentEventDescription }
        DESCRIPTION
             "XML subsystem unknown error."
           --#TYPE      "Management Agent Event 27049"
           --#SUMMARY   "Host %s : SCellName-TimeDate %s : EventCode %d : Description %s"
           --#ARGUMENTS {0,1,2,3,}
            --#SEVERITY  INFORMATIONAL
            --#TIMEINDEX 136
        ::= 136027049

   mngmtAgentTrap-27050 TRAP-TYPE
        ENTERPRISE compaq
        VARIABLES  { hostName,
                     scellNameDateTime,
                     agentEventCode,
                     agentEventDescription }
        DESCRIPTION
             "The element manager has successfully created a virtual disk container. Command issued through the XML Interface."
           --#TYPE      "Management Agent Event 27050"
           --#SUMMARY   "Host %s : SCellName-TimeDate %s : EventCode %d : Description %s"
           --#ARGUMENTS {0,1,2,3,}
            --#SEVERITY  INFORMATIONAL
            --#TIMEINDEX 136
        ::= 136027050

   mngmtAgentTrap-27051 TRAP-TYPE
        ENTERPRISE compaq
        VARIABLES  { hostName,
                     scellNameDateTime,
                     agentEventCode,
                     agentEventDescription }
        DESCRIPTION
             "The element manager has successfully modified a virtual disk container. Command issued through the XML Interface."
           --#TYPE      "Management Agent Event 27051"
           --#SUMMARY   "Host %s : SCellName-TimeDate %s : EventCode %d : Description %s"
           --#ARGUMENTS {0,1,2,3,}
            --#SEVERITY  INFORMATIONAL
            --#TIMEINDEX 136
        ::= 136027051

   mngmtAgentTrap-27052 TRAP-TYPE
        ENTERPRISE compaq
        VARIABLES  { hostName,
                     scellNameDateTime,
                     agentEventCode,
                     agentEventDescription }
        DESCRIPTION
             "The element manager has successfully deleted a virtual disk container. Command issued through the XML Interface."
           --#TYPE      "Management Agent Event 27052"
           --#SUMMARY   "Host %s : SCellName-TimeDate %s : EventCode %d : Description %s"
           --#ARGUMENTS {0,1,2,3,}
            --#SEVERITY  INFORMATIONAL
            --#TIMEINDEX 136
        ::= 136027052

   mngmtAgentTrap-27053 TRAP-TYPE
        ENTERPRISE compaq
        VARIABLES  { hostName,
                     scellNameDateTime,
                     agentEventCode,
                     agentEventDescription }
        DESCRIPTION
             "The element manager has successfully modified the properties of an iscsi controller. Command issued through the XML Interface."
           --#TYPE      "Management Agent Event 27053"
           --#SUMMARY   "Host %s : SCellName-TimeDate %s : EventCode %d : Description %s"
           --#ARGUMENTS {0,1,2,3,}
            --#SEVERITY  INFORMATIONAL
            --#TIMEINDEX 136
        ::= 136027053

   mngmtAgentTrap-27054 TRAP-TYPE
        ENTERPRISE compaq
        VARIABLES  { hostName,
                     scellNameDateTime,
                     agentEventCode,
                     agentEventDescription }
        DESCRIPTION
             "The element manager has successfully discovered iscsi controller(s). Command issued through the XML Interface."
           --#TYPE      "Management Agent Event 27054"
           --#SUMMARY   "Host %s : SCellName-TimeDate %s : EventCode %d : Description %s"
           --#ARGUMENTS {0,1,2,3,}
            --#SEVERITY  INFORMATIONAL
            --#TIMEINDEX 136
        ::= 136027054

   mngmtAgentTrap-27055 TRAP-TYPE
        ENTERPRISE compaq
        VARIABLES  { hostName,
                     scellNameDateTime,
                     agentEventCode,
                     agentEventDescription }
        DESCRIPTION
             "The element manager has successfully deleted an iscsi controllers. Command issued through the XML Interface."
           --#TYPE      "Management Agent Event 27055"
           --#SUMMARY   "Host %s : SCellName-TimeDate %s : EventCode %d : Description %s"
           --#ARGUMENTS {0,1,2,3,}
            --#SEVERITY  INFORMATIONAL
            --#TIMEINDEX 136
        ::= 136027055

   mngmtAgentTrap-27056 TRAP-TYPE
        ENTERPRISE compaq
        VARIABLES  { hostName,
                     scellNameDateTime,
                     agentEventCode,
                     agentEventDescription }
        DESCRIPTION
             "The element manager has successfully created an iscsi host. Command issued through the XML Interface."
           --#TYPE      "Management Agent Event 27056"
           --#SUMMARY   "Host %s : SCellName-TimeDate %s : EventCode %d : Description %s"
           --#ARGUMENTS {0,1,2,3,}
            --#SEVERITY  INFORMATIONAL
            --#TIMEINDEX 136
        ::= 136027056

   mngmtAgentTrap-27057 TRAP-TYPE
        ENTERPRISE compaq
        VARIABLES  { hostName,
                     scellNameDateTime,
                     agentEventCode,
                     agentEventDescription }
        DESCRIPTION
             "The element manager has successfully modified the properties of an iscsi host. Command issued through the XML Interface."
           --#TYPE      "Management Agent Event 27057"
           --#SUMMARY   "Host %s : SCellName-TimeDate %s : EventCode %d : Description %s"
           --#ARGUMENTS {0,1,2,3,}
            --#SEVERITY  INFORMATIONAL
            --#TIMEINDEX 136
        ::= 136027057

   mngmtAgentTrap-27058 TRAP-TYPE
        ENTERPRISE compaq
        VARIABLES  { hostName,
                     scellNameDateTime,
                     agentEventCode,
                     agentEventDescription }
        DESCRIPTION
             "The element manager has successfully deleted an iscsi host. Command issued through the XML Interface."
           --#TYPE      "Management Agent Event 27058"
           --#SUMMARY   "Host %s : SCellName-TimeDate %s : EventCode %d : Description %s"
           --#ARGUMENTS {0,1,2,3,}
            --#SEVERITY  INFORMATIONAL
            --#TIMEINDEX 136
        ::= 136027058

   mngmtAgentTrap-27059 TRAP-TYPE
        ENTERPRISE compaq
        VARIABLES  { hostName,
                     scellNameDateTime,
                     agentEventCode,
                     agentEventDescription }
        DESCRIPTION
             "The element manager has successfully created an iscsi presented unit. Command issued through the XML Interface."
           --#TYPE      "Management Agent Event 27059"
           --#SUMMARY   "Host %s : SCellName-TimeDate %s : EventCode %d : Description %s"
           --#ARGUMENTS {0,1,2,3,}
            --#SEVERITY  INFORMATIONAL
            --#TIMEINDEX 136
        ::= 136027059

   mngmtAgentTrap-27060 TRAP-TYPE
        ENTERPRISE compaq
        VARIABLES  { hostName,
                     scellNameDateTime,
                     agentEventCode,
                     agentEventDescription }
        DESCRIPTION
             "The element manager has successfully modified the properties of an iscsi presented unit. Command issued through the XML Interface."
           --#TYPE      "Management Agent Event 27060"
           --#SUMMARY   "Host %s : SCellName-TimeDate %s : EventCode %d : Description %s"
           --#ARGUMENTS {0,1,2,3,}
            --#SEVERITY  INFORMATIONAL
            --#TIMEINDEX 136
        ::= 136027060

   mngmtAgentTrap-27061 TRAP-TYPE
        ENTERPRISE compaq
        VARIABLES  { hostName,
                     scellNameDateTime,
                     agentEventCode,
                     agentEventDescription }
        DESCRIPTION
             "The element manager has successfully deleted an iscsi presented unit. Command issued through the XML Interface."
           --#TYPE      "Management Agent Event 27061"
           --#SUMMARY   "Host %s : SCellName-TimeDate %s : EventCode %d : Description %s"
           --#ARGUMENTS {0,1,2,3,}
            --#SEVERITY  INFORMATIONAL
            --#TIMEINDEX 136
        ::= 136027061

   mngmtAgentTrap-27062 TRAP-TYPE
        ENTERPRISE compaq
        VARIABLES  { hostName,
                     scellNameDateTime,
                     agentEventCode,
                     agentEventDescription }
        DESCRIPTION
             "The element manager has successfully created an fcoe host. Command issued through the XML Interface."
           --#TYPE      "Management Agent Event 27062"
           --#SUMMARY   "Host %s : SCellName-TimeDate %s : EventCode %d : Description %s"
           --#ARGUMENTS {0,1,2,3,}
            --#SEVERITY  INFORMATIONAL
            --#TIMEINDEX 136
        ::= 136027062

   mngmtAgentTrap-27063 TRAP-TYPE
        ENTERPRISE compaq
        VARIABLES  { hostName,
                     scellNameDateTime,
                     agentEventCode,
                     agentEventDescription }
        DESCRIPTION
             "The element manager has successfully modified the properties of an fcoe host. Command issued through the XML Interface."
           --#TYPE      "Management Agent Event 27063"
           --#SUMMARY   "Host %s : SCellName-TimeDate %s : EventCode %d : Description %s"
           --#ARGUMENTS {0,1,2,3,}
            --#SEVERITY  INFORMATIONAL
            --#TIMEINDEX 136
        ::= 136027063

   mngmtAgentTrap-27064 TRAP-TYPE
        ENTERPRISE compaq
        VARIABLES  { hostName,
                     scellNameDateTime,
                     agentEventCode,
                     agentEventDescription }
        DESCRIPTION
             "The element manager has successfully deleted an fcoe host. Command issued through the XML Interface."
           --#TYPE      "Management Agent Event 27064"
           --#SUMMARY   "Host %s : SCellName-TimeDate %s : EventCode %d : Description %s"
           --#ARGUMENTS {0,1,2,3,}
            --#SEVERITY  INFORMATIONAL
            --#TIMEINDEX 136
        ::= 136027064

   mngmtAgentTrap-27065 TRAP-TYPE
        ENTERPRISE compaq
        VARIABLES  { hostName,
                     scellNameDateTime,
                     agentEventCode,
                     agentEventDescription }
        DESCRIPTION
             "The element manager has successfully created an fcoe presented unit. Command issued through the XML Interface."
           --#TYPE      "Management Agent Event 27065"
           --#SUMMARY   "Host %s : SCellName-TimeDate %s : EventCode %d : Description %s"
           --#ARGUMENTS {0,1,2,3,}
            --#SEVERITY  INFORMATIONAL
            --#TIMEINDEX 136
        ::= 136027065

   mngmtAgentTrap-27066 TRAP-TYPE
        ENTERPRISE compaq
        VARIABLES  { hostName,
                     scellNameDateTime,
                     agentEventCode,
                     agentEventDescription }
        DESCRIPTION
             "The element manager has successfully modified the properties of an fcoe presented unit. Command issued through the XML Interface."
           --#TYPE      "Management Agent Event 27066"
           --#SUMMARY   "Host %s : SCellName-TimeDate %s : EventCode %d : Description %s"
           --#ARGUMENTS {0,1,2,3,}
            --#SEVERITY  INFORMATIONAL
            --#TIMEINDEX 136
        ::= 136027066

   mngmtAgentTrap-27067 TRAP-TYPE
        ENTERPRISE compaq
        VARIABLES  { hostName,
                     scellNameDateTime,
                     agentEventCode,
                     agentEventDescription }
        DESCRIPTION
             "The element manager has successfully deleted an fcoe presented unit. Command issued through the XML Interface."
           --#TYPE      "Management Agent Event 27067"
           --#SUMMARY   "Host %s : SCellName-TimeDate %s : EventCode %d : Description %s"
           --#ARGUMENTS {0,1,2,3,}
            --#SEVERITY  INFORMATIONAL
            --#TIMEINDEX 136
        ::= 136027067

   mngmtAgentTrap-28001 TRAP-TYPE
        ENTERPRISE compaq
        VARIABLES  { hostName,
                     scellNameDateTime,
                     agentEventCode,
                     agentEventDescription }
        DESCRIPTION
             "A background task failed during execution."
           --#TYPE      "Management Agent Event 28001"
           --#SUMMARY   "Host %s : SCellName-TimeDate %s : EventCode %d : Description %s"
           --#ARGUMENTS {0,1,2,3,}
            --#SEVERITY  INFORMATIONAL
            --#TIMEINDEX 136
        ::= 136028001

   mngmtAgentTrap-29001 TRAP-TYPE
        ENTERPRISE compaq
        VARIABLES  { hostName,
                     scellNameDateTime,
                     agentEventCode,
                     agentEventDescription }
        DESCRIPTION
             "The no-migrate code load process has started."
           --#TYPE      "Management Agent Event 29001"
           --#SUMMARY   "Host %s : SCellName-TimeDate %s : EventCode %d : Description %s"
           --#ARGUMENTS {0,1,2,3,}
            --#SEVERITY  INFORMATIONAL
            --#TIMEINDEX 136
        ::= 136029001

   mngmtAgentTrap-29002 TRAP-TYPE
        ENTERPRISE compaq
        VARIABLES  { hostName,
                     scellNameDateTime,
                     agentEventCode,
                     agentEventDescription }
        DESCRIPTION
             "The no-migrate code load process complete."
           --#TYPE      "Management Agent Event 29002"
           --#SUMMARY   "Host %s : SCellName-TimeDate %s : EventCode %d : Description %s"
           --#ARGUMENTS {0,1,2,3,}
            --#SEVERITY  INFORMATIONAL
            --#TIMEINDEX 136
        ::= 136029002

   mngmtAgentTrap-29003 TRAP-TYPE
        ENTERPRISE compaq
        VARIABLES  { hostName,
                     scellNameDateTime,
                     agentEventCode,
                     agentEventDescription }
        DESCRIPTION
             "The bundled image directory path cannot be found."
           --#TYPE      "Management Agent Event 29003"
           --#SUMMARY   "Host %s : SCellName-TimeDate %s : EventCode %d : Description %s"
           --#ARGUMENTS {0,1,2,3,}
            --#SEVERITY  INFORMATIONAL
            --#TIMEINDEX 136
        ::= 136029003

   mngmtAgentTrap-29004 TRAP-TYPE
        ENTERPRISE compaq
        VARIABLES  { hostName,
                     scellNameDateTime,
                     agentEventCode,
                     agentEventDescription }
        DESCRIPTION
             "The required index file cannot be found."
           --#TYPE      "Management Agent Event 29004"
           --#SUMMARY   "Host %s : SCellName-TimeDate %s : EventCode %d : Description %s"
           --#ARGUMENTS {0,1,2,3,}
            --#SEVERITY  INFORMATIONAL
            --#TIMEINDEX 136
        ::= 136029004

   mngmtAgentTrap-29005 TRAP-TYPE
        ENTERPRISE compaq
        VARIABLES  { hostName,
                     scellNameDateTime,
                     agentEventCode,
                     agentEventDescription }
        DESCRIPTION
             "No-migrate codeload error"
           --#TYPE      "Management Agent Event 29005"
           --#SUMMARY   "Host %s : SCellName-TimeDate %s : EventCode %d : Description %s"
           --#ARGUMENTS {0,1,2,3,}
            --#SEVERITY  INFORMATIONAL
            --#TIMEINDEX 136
        ::= 136029005

   mngmtAgentTrap-29006 TRAP-TYPE
        ENTERPRISE compaq
        VARIABLES  { hostName,
                     scellNameDateTime,
                     agentEventCode,
                     agentEventDescription }
        DESCRIPTION
             "The online drive code load process has been manually canceled. Some drives may not have been updated."
           --#TYPE      "Management Agent Event 29006"
           --#SUMMARY   "Host %s : SCellName-TimeDate %s : EventCode %d : Description %s"
           --#ARGUMENTS {0,1,2,3,}
            --#SEVERITY  INFORMATIONAL
            --#TIMEINDEX 136
        ::= 136029006

   mngmtAgentTrap-30000 TRAP-TYPE
        ENTERPRISE compaq
        VARIABLES  { hostName,
                     scellNameDateTime,
                     agentEventCode,
                     agentEventDescription }
        DESCRIPTION
             "Management Module: No URL info found for WOCP."
           --#TYPE      "Management Agent Event 30000"
           --#SUMMARY   "Host %s : SCellName-TimeDate %s : EventCode %d : Description %s"
           --#ARGUMENTS {0,1,2,3,}
            --#SEVERITY  INFORMATIONAL
            --#TIMEINDEX 136
        ::= 136030000

   mngmtAgentTrap-30001 TRAP-TYPE
        ENTERPRISE compaq
        VARIABLES  { hostName,
                     scellNameDateTime,
                     agentEventCode,
                     agentEventDescription }
        DESCRIPTION
             "Management Module: Currently IPV6 is not supported."
           --#TYPE      "Management Agent Event 30001"
           --#SUMMARY   "Host %s : SCellName-TimeDate %s : EventCode %d : Description %s"
           --#ARGUMENTS {0,1,2,3,}
            --#SEVERITY  INFORMATIONAL
            --#TIMEINDEX 136
        ::= 136030001

   mngmtAgentTrap-30002 TRAP-TYPE
        ENTERPRISE compaq
        VARIABLES  { hostName,
                     scellNameDateTime,
                     agentEventCode,
                     agentEventDescription }
        DESCRIPTION
             "Management Module: Unknown IP version."
           --#TYPE      "Management Agent Event 30002"
           --#SUMMARY   "Host %s : SCellName-TimeDate %s : EventCode %d : Description %s"
           --#ARGUMENTS {0,1,2,3,}
            --#SEVERITY  INFORMATIONAL
            --#TIMEINDEX 136
        ::= 136030002

   mngmtAgentTrap-30003 TRAP-TYPE
        ENTERPRISE compaq
        VARIABLES  { hostName,
                     scellNameDateTime,
                     agentEventCode,
                     agentEventDescription }
        DESCRIPTION
             "Management Module: IP version not set."
           --#TYPE      "Management Agent Event 30003"
           --#SUMMARY   "Host %s : SCellName-TimeDate %s : EventCode %d : Description %s"
           --#ARGUMENTS {0,1,2,3,}
            --#SEVERITY  INFORMATIONAL
            --#TIMEINDEX 136
        ::= 136030003

   mngmtAgentTrap-30004 TRAP-TYPE
        ENTERPRISE compaq
        VARIABLES  { hostName,
                     scellNameDateTime,
                     agentEventCode,
                     agentEventDescription }
        DESCRIPTION
             "Management Module: NTP Client configured. No NTP server reachable.  This could be due to the time needed to sync with an NTP server."
           --#TYPE      "Management Agent Event 30004"
           --#SUMMARY   "Host %s : SCellName-TimeDate %s : EventCode %d : Description %s"
           --#ARGUMENTS {0,1,2,3,}
            --#SEVERITY  MINOR
            --#TIMEINDEX 136
        ::= 136030004

   mngmtAgentTrap-30005 TRAP-TYPE
        ENTERPRISE compaq
        VARIABLES  { hostName,
                     scellNameDateTime,
                     agentEventCode,
                     agentEventDescription }
        DESCRIPTION
             "Management Module: NTP Client configured. No association IDs."
           --#TYPE      "Management Agent Event 30005"
           --#SUMMARY   "Host %s : SCellName-TimeDate %s : EventCode %d : Description %s"
           --#ARGUMENTS {0,1,2,3,}
            --#SEVERITY  MINOR
            --#TIMEINDEX 136
        ::= 136030005

   mngmtAgentTrap-30006 TRAP-TYPE
        ENTERPRISE compaq
        VARIABLES  { hostName,
                     scellNameDateTime,
                     agentEventCode,
                     agentEventDescription }
        DESCRIPTION
             "Management Module: NTP Client configured. NTP client daemon not running."
           --#TYPE      "Management Agent Event 30006"
           --#SUMMARY   "Host %s : SCellName-TimeDate %s : EventCode %d : Description %s"
           --#ARGUMENTS {0,1,2,3,}
            --#SEVERITY  CRITICAL
            --#TIMEINDEX 136
        ::= 136030006

   mngmtAgentTrap-30007 TRAP-TYPE
        ENTERPRISE compaq
        VARIABLES  { hostName,
                     scellNameDateTime,
                     agentEventCode,
                     agentEventDescription }
        DESCRIPTION
             "Management Module: NTP Client configured. Cannot communicate with NTP Client."
           --#TYPE      "Management Agent Event 30007"
           --#SUMMARY   "Host %s : SCellName-TimeDate %s : EventCode %d : Description %s"
           --#ARGUMENTS {0,1,2,3,}
            --#SEVERITY  CRITICAL
            --#TIMEINDEX 136
        ::= 136030007

   mngmtAgentTrap-30008 TRAP-TYPE
        ENTERPRISE compaq
        VARIABLES  { hostName,
                     scellNameDateTime,
                     agentEventCode,
                     agentEventDescription }
        DESCRIPTION
             "Management Module: NTP Client configured. NTP client unknown return."
           --#TYPE      "Management Agent Event 30008"
           --#SUMMARY   "Host %s : SCellName-TimeDate %s : EventCode %d : Description %s"
           --#ARGUMENTS {0,1,2,3,}
            --#SEVERITY  CRITICAL
            --#TIMEINDEX 136
        ::= 136030008

   mngmtAgentTrap-30009 TRAP-TYPE
        ENTERPRISE compaq
        VARIABLES  { hostName,
                     scellNameDateTime,
                     agentEventCode,
                     agentEventDescription }
        DESCRIPTION
             "Management Module: NTP Client is now connected to NTP server."
           --#TYPE      "Management Agent Event 30009"
           --#SUMMARY   "Host %s : SCellName-TimeDate %s : EventCode %d : Description %s"
           --#ARGUMENTS {0,1,2,3,}
            --#SEVERITY  INFORMATIONAL
            --#TIMEINDEX 136
        ::= 136030009

   mngmtAgentTrap-30010 TRAP-TYPE
        ENTERPRISE compaq
        VARIABLES  { hostName,
                     scellNameDateTime,
                     agentEventCode,
                     agentEventDescription }
        DESCRIPTION
             "Management Module: Unable to ping NTP server."
           --#TYPE      "Management Agent Event 30010"
           --#SUMMARY   "Host %s : SCellName-TimeDate %s : EventCode %d : Description %s"
           --#ARGUMENTS {0,1,2,3,}
            --#SEVERITY  MINOR
            --#TIMEINDEX 136
        ::= 136030010

   mngmtAgentTrap-30011 TRAP-TYPE
        ENTERPRISE compaq
        VARIABLES  { hostName,
                     scellNameDateTime,
                     agentEventCode,
                     agentEventDescription }
        DESCRIPTION
             "Management Module: Server not NTP server."
           --#TYPE      "Management Agent Event 30011"
           --#SUMMARY   "Host %s : SCellName-TimeDate %s : EventCode %d : Description %s"
           --#ARGUMENTS {0,1,2,3,}
            --#SEVERITY  MINOR
            --#TIMEINDEX 136
        ::= 136030011

   mngmtAgentTrap-30012 TRAP-TYPE
        ENTERPRISE compaq
        VARIABLES  { hostName,
                     scellNameDateTime,
                     agentEventCode,
                     agentEventDescription }
        DESCRIPTION
             "Management Module: Time keeping method set to NTP."
           --#TYPE      "Management Agent Event 30012"
           --#SUMMARY   "Host %s : SCellName-TimeDate %s : EventCode %d : Description %s"
           --#ARGUMENTS {0,1,2,3,}
            --#SEVERITY  MINOR
            --#TIMEINDEX 136
        ::= 136030012

   mngmtAgentTrap-31000 TRAP-TYPE
        ENTERPRISE compaq
        VARIABLES  { hostName,
                     scellNameDateTime,
                     agentEventCode,
                     agentEventDescription }
        DESCRIPTION
             "Object Lock First Status"
           --#TYPE      "Management Agent Event 31000"
           --#SUMMARY   "Host %s : SCellName-TimeDate %s : EventCode %d : Description %s"
           --#ARGUMENTS {0,1,2,3,}
            --#SEVERITY  INFORMATIONAL
            --#TIMEINDEX 136
        ::= 136031000

   mngmtAgentTrap-31001 TRAP-TYPE
        ENTERPRISE compaq
        VARIABLES  { hostName,
                     scellNameDateTime,
                     agentEventCode,
                     agentEventDescription }
        DESCRIPTION
             "Cannot change VD capacity on a locked VD."
           --#TYPE      "Management Agent Event 31001"
           --#SUMMARY   "Host %s : SCellName-TimeDate %s : EventCode %d : Description %s"
           --#ARGUMENTS {0,1,2,3,}
            --#SEVERITY  INFORMATIONAL
            --#TIMEINDEX 136
        ::= 136031001

   mngmtAgentTrap-31002 TRAP-TYPE
        ENTERPRISE compaq
        VARIABLES  { hostName,
                     scellNameDateTime,
                     agentEventCode,
                     agentEventDescription }
        DESCRIPTION
             "Cannot unpresent a locked VD."
           --#TYPE      "Management Agent Event 31002"
           --#SUMMARY   "Host %s : SCellName-TimeDate %s : EventCode %d : Description %s"
           --#ARGUMENTS {0,1,2,3,}
            --#SEVERITY  INFORMATIONAL
            --#TIMEINDEX 136
        ::= 136031002

   mngmtAgentTrap-31003 TRAP-TYPE
        ENTERPRISE compaq
        VARIABLES  { hostName,
                     scellNameDateTime,
                     agentEventCode,
                     agentEventDescription }
        DESCRIPTION
             "Cannot present a locked VD."
           --#TYPE      "Management Agent Event 31003"
           --#SUMMARY   "Host %s : SCellName-TimeDate %s : EventCode %d : Description %s"
           --#ARGUMENTS {0,1,2,3,}
            --#SEVERITY  INFORMATIONAL
            --#TIMEINDEX 136
        ::= 136031003

   mngmtAgentTrap-31004 TRAP-TYPE
        ENTERPRISE compaq
        VARIABLES  { hostName,
                     scellNameDateTime,
                     agentEventCode,
                     agentEventDescription }
        DESCRIPTION
             "Cannot restore a locked VD from a mirrorclone or snapshot."
           --#TYPE      "Management Agent Event 31004"
           --#SUMMARY   "Host %s : SCellName-TimeDate %s : EventCode %d : Description %s"
           --#ARGUMENTS {0,1,2,3,}
            --#SEVERITY  INFORMATIONAL
            --#TIMEINDEX 136
        ::= 136031004

   mngmtAgentTrap-31005 TRAP-TYPE
        ENTERPRISE compaq
        VARIABLES  { hostName,
                     scellNameDateTime,
                     agentEventCode,
                     agentEventDescription }
        DESCRIPTION
             "Cannot change a locked VDs name."
           --#TYPE      "Management Agent Event 31005"
           --#SUMMARY   "Host %s : SCellName-TimeDate %s : EventCode %d : Description %s"
           --#ARGUMENTS {0,1,2,3,}
            --#SEVERITY  INFORMATIONAL
            --#TIMEINDEX 136
        ::= 136031005

   mngmtAgentTrap-31006 TRAP-TYPE
        ENTERPRISE compaq
        VARIABLES  { hostName,
                     scellNameDateTime,
                     agentEventCode,
                     agentEventDescription }
        DESCRIPTION
             "Cannot change a locked VDs WWN."
           --#TYPE      "Management Agent Event 31006"
           --#SUMMARY   "Host %s : SCellName-TimeDate %s : EventCode %d : Description %s"
           --#ARGUMENTS {0,1,2,3,}
            --#SEVERITY  INFORMATIONAL
            --#TIMEINDEX 136
        ::= 136031006

   mngmtAgentTrap-31007 TRAP-TYPE
        ENTERPRISE compaq
        VARIABLES  { hostName,
                     scellNameDateTime,
                     agentEventCode,
                     agentEventDescription }
        DESCRIPTION
             "Cannot change lock notes/details field on a locked VD."
           --#TYPE      "Management Agent Event 31007"
           --#SUMMARY   "Host %s : SCellName-TimeDate %s : EventCode %d : Description %s"
           --#ARGUMENTS {0,1,2,3,}
            --#SEVERITY  INFORMATIONAL
            --#TIMEINDEX 136
        ::= 136031007

   mngmtAgentTrap-31008 TRAP-TYPE
        ENTERPRISE compaq
        VARIABLES  { hostName,
                     scellNameDateTime,
                     agentEventCode,
                     agentEventDescription }
        DESCRIPTION
             "Cannot delete a locked VD."
           --#TYPE      "Management Agent Event 31008"
           --#SUMMARY   "Host %s : SCellName-TimeDate %s : EventCode %d : Description %s"
           --#ARGUMENTS {0,1,2,3,}
            --#SEVERITY  INFORMATIONAL
            --#TIMEINDEX 136
        ::= 136031008

   mngmtAgentTrap-31009 TRAP-TYPE
        ENTERPRISE compaq
        VARIABLES  { hostName,
                     scellNameDateTime,
                     agentEventCode,
                     agentEventDescription }
        DESCRIPTION
             "Lock notes/details field is required."
           --#TYPE      "Management Agent Event 31009"
           --#SUMMARY   "Host %s : SCellName-TimeDate %s : EventCode %d : Description %s"
           --#ARGUMENTS {0,1,2,3,}
            --#SEVERITY  INFORMATIONAL
            --#TIMEINDEX 136
        ::= 136031009

   mngmtAgentTrap-31010 TRAP-TYPE
        ENTERPRISE compaq
        VARIABLES  { hostName,
                     scellNameDateTime,
                     agentEventCode,
                     agentEventDescription }
        DESCRIPTION
             "Cannot convert a locked VD to a container."
           --#TYPE      "Management Agent Event 31010"
           --#SUMMARY   "Host %s : SCellName-TimeDate %s : EventCode %d : Description %s"
           --#ARGUMENTS {0,1,2,3,}
            --#SEVERITY  INFORMATIONAL
            --#TIMEINDEX 136
        ::= 136031010

   mngmtAgentTrap-31011 TRAP-TYPE
        ENTERPRISE compaq
        VARIABLES  { hostName,
                     scellNameDateTime,
                     agentEventCode,
                     agentEventDescription }
        DESCRIPTION
             "Cannot detach a locked mirror clone."
           --#TYPE      "Management Agent Event 31011"
           --#SUMMARY   "Host %s : SCellName-TimeDate %s : EventCode %d : Description %s"
           --#ARGUMENTS {0,1,2,3,}
            --#SEVERITY  INFORMATIONAL
            --#TIMEINDEX 136
        ::= 136031011

   mngmtAgentTrap-31012 TRAP-TYPE
        ENTERPRISE compaq
        VARIABLES  { hostName,
                     scellNameDateTime,
                     agentEventCode,
                     agentEventDescription }
        DESCRIPTION
             "The requested operation is not valid on a locked mirror clone."
           --#TYPE      "Management Agent Event 31012"
           --#SUMMARY   "Host %s : SCellName-TimeDate %s : EventCode %d : Description %s"
           --#ARGUMENTS {0,1,2,3,}
            --#SEVERITY  INFORMATIONAL
            --#TIMEINDEX 136
        ::= 136031012

   mngmtAgentTrap-31013 TRAP-TYPE
        ENTERPRISE compaq
        VARIABLES  { hostName,
                     scellNameDateTime,
                     agentEventCode,
                     agentEventDescription }
        DESCRIPTION
             "Cannot change write protection on a locked VD."
           --#TYPE      "Management Agent Event 31013"
           --#SUMMARY   "Host %s : SCellName-TimeDate %s : EventCode %d : Description %s"
           --#ARGUMENTS {0,1,2,3,}
            --#SEVERITY  INFORMATIONAL
            --#TIMEINDEX 136
        ::= 136031013

   mngmtAgentTrap-31014 TRAP-TYPE
        ENTERPRISE compaq
        VARIABLES  { hostName,
                     scellNameDateTime,
                     agentEventCode,
                     agentEventDescription }
        DESCRIPTION
             "Cannot change OS unit ID on a locked VD."
           --#TYPE      "Management Agent Event 31014"
           --#SUMMARY   "Host %s : SCellName-TimeDate %s : EventCode %d : Description %s"
           --#ARGUMENTS {0,1,2,3,}
            --#SEVERITY  INFORMATIONAL
            --#TIMEINDEX 136
        ::= 136031014

   mngmtAgentTrap-31015 TRAP-TYPE
        ENTERPRISE compaq
        VARIABLES  { hostName,
                     scellNameDateTime,
                     agentEventCode,
                     agentEventDescription }
        DESCRIPTION
             "Cannot change preferred path on a locked VD."
           --#TYPE      "Management Agent Event 31015"
           --#SUMMARY   "Host %s : SCellName-TimeDate %s : EventCode %d : Description %s"
           --#ARGUMENTS {0,1,2,3,}
            --#SEVERITY  INFORMATIONAL
            --#TIMEINDEX 136
        ::= 136031015

   mngmtAgentTrap-31016 TRAP-TYPE
        ENTERPRISE compaq
        VARIABLES  { hostName,
                     scellNameDateTime,
                     agentEventCode,
                     agentEventDescription }
        DESCRIPTION
             "Member removal disallowed.  Cannot delete a locked destination DR group member."
           --#TYPE      "Management Agent Event 31016"
           --#SUMMARY   "Host %s : SCellName-TimeDate %s : EventCode %d : Description %s"
           --#ARGUMENTS {0,1,2,3,}
            --#SEVERITY  INFORMATIONAL
            --#TIMEINDEX 136
        ::= 136031016

   mngmtAgentTrap-31017 TRAP-TYPE
        ENTERPRISE compaq
        VARIABLES  { hostName,
                     scellNameDateTime,
                     agentEventCode,
                     agentEventDescription }
        DESCRIPTION
             "Cannot migrate a locked VD."
           --#TYPE      "Management Agent Event 31017"
           --#SUMMARY   "Host %s : SCellName-TimeDate %s : EventCode %d : Description %s"
           --#ARGUMENTS {0,1,2,3,}
            --#SEVERITY  INFORMATIONAL
            --#TIMEINDEX 136
        ::= 136031017

   mngmtAgentTrap-31018 TRAP-TYPE
        ENTERPRISE compaq
        VARIABLES  { hostName,
                     scellNameDateTime,
                     agentEventCode,
                     agentEventDescription }
        DESCRIPTION
             "The requested operation is not valid on mirror clone with a locked source VD."
           --#TYPE      "Management Agent Event 31018"
           --#SUMMARY   "Host %s : SCellName-TimeDate %s : EventCode %d : Description %s"
           --#ARGUMENTS {0,1,2,3,}
            --#SEVERITY  INFORMATIONAL
            --#TIMEINDEX 136
        ::= 136031018

   mngmtAgentTrap-32001 TRAP-TYPE
        ENTERPRISE compaq
        VARIABLES  { hostName,
                     scellNameDateTime,
                     agentEventCode,
                     agentEventDescription }
        DESCRIPTION
             "Override needed for presentation of overcommitted thin provisioned virtual disk."
           --#TYPE      "Management Agent Event 32001"
           --#SUMMARY   "Host %s : SCellName-TimeDate %s : EventCode %d : Description %s"
           --#ARGUMENTS {0,1,2,3,}
            --#SEVERITY  MINOR
            --#TIMEINDEX 136
        ::= 136032001

   mngmtAgentTrap-32002 TRAP-TYPE
        ENTERPRISE compaq
        VARIABLES  { hostName,
                     scellNameDateTime,
                     agentEventCode,
                     agentEventDescription }
        DESCRIPTION
             "Override needed for unpresent of overcommitted thin provisioned virtual disk."
           --#TYPE      "Management Agent Event 32002"
           --#SUMMARY   "Host %s : SCellName-TimeDate %s : EventCode %d : Description %s"
           --#ARGUMENTS {0,1,2,3,}
            --#SEVERITY  MINOR
            --#TIMEINDEX 136
        ::= 136032002

   mngmtAgentTrap-33001 TRAP-TYPE
        ENTERPRISE compaq
        VARIABLES  { hostName,
                     scellNameDateTime,
                     agentEventCode,
                     agentEventDescription }
        DESCRIPTION
             "Virtual Disk Migration Succeded."
           --#TYPE      "Management Agent Event 33001"
           --#SUMMARY   "Host %s : SCellName-TimeDate %s : EventCode %d : Description %s"
           --#ARGUMENTS {0,1,2,3,}
            --#SEVERITY  INFORMATIONAL
            --#TIMEINDEX 136
        ::= 136033001

   mngmtAgentTrap-33002 TRAP-TYPE
        ENTERPRISE compaq
        VARIABLES  { hostName,
                     scellNameDateTime,
                     agentEventCode,
                     agentEventDescription }
        DESCRIPTION
             "Virtual Disk Migration Failed."
           --#TYPE      "Management Agent Event 33002"
           --#SUMMARY   "Host %s : SCellName-TimeDate %s : EventCode %d : Description %s"
           --#ARGUMENTS {0,1,2,3,}
            --#SEVERITY  MAJOR
            --#TIMEINDEX 136
        ::= 136033002

   mngmtAgentTrap-33003 TRAP-TYPE
        ENTERPRISE compaq
        VARIABLES  { hostName,
                     scellNameDateTime,
                     agentEventCode,
                     agentEventDescription }
        DESCRIPTION
             "Virtual Disk Migration Clean Up Succeded."
           --#TYPE      "Management Agent Event 33003"
           --#SUMMARY   "Host %s : SCellName-TimeDate %s : EventCode %d : Description %s"
           --#ARGUMENTS {0,1,2,3,}
            --#SEVERITY  INFORMATIONAL
            --#TIMEINDEX 136
        ::= 136033003

   mngmtAgentTrap-33004 TRAP-TYPE
        ENTERPRISE compaq
        VARIABLES  { hostName,
                     scellNameDateTime,
                     agentEventCode,
                     agentEventDescription }
        DESCRIPTION
             "Virtual Disk Migration Clean Up Failed."
           --#TYPE      "Management Agent Event 33004"
           --#SUMMARY   "Host %s : SCellName-TimeDate %s : EventCode %d : Description %s"
           --#ARGUMENTS {0,1,2,3,}
            --#SEVERITY  MAJOR
            --#TIMEINDEX 136
        ::= 136033004

   mngmtAgentTrap-35000 TRAP-TYPE
        ENTERPRISE compaq
        VARIABLES  { hostName,
                     scellNameDateTime,
                     agentEventCode,
                     agentEventDescription,
                     nscStatus,
                     nscName }
        DESCRIPTION
             "A Heart Beat Event is generated for one of the controller"
           --#TYPE      "Management Agent Event 35000"
           --#SUMMARY   "Host %s : SCellName-TimeDate %s : EventCode %d : Description %s : nscStatus %d : nscName %s"
           --#ARGUMENTS {0,1,2,3,4,5,}
           --#SEVERITY  INFORMATIONAL
           --#TIMEINDEX  136
        ::= 136035000

 END

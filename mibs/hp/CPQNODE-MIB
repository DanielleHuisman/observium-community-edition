-- ****************************************************************************
--
--                  Moonshot Node Information
--         Management Information Base for SNMP Network Management
--
--
--      Copyright 1993,2008 Hewlett-Packard Development Company, L.P.
--
--      Hewlett-Packard Company shall not be liable for technical or
--      editorial errors or omissions contained herein. The information in
--      this document is provided "as is" without warranty of any kind and
--      is subject to change without notice. The warranties for HP products
--      are set forth in the express limited warranty statements
--      accompanying such products. Nothing herein should be construed as
--      constituting an additional warranty.
--
--      Confidential computer software. Valid license from HP required for
--      possession, use or copying. Consistent with FAR 12.211 and 12.212,
--      Commercial Computer Software, Computer Software Documentation, and
--      Technical Data for Commercial Items are licensed to the U.S.
--      Government under vendor's standard commercial license.
--
--      Refer to the READMIB.RDM file for more information about the
--      organization of the information in the Compaq Enterprise.
--
--      The Compaq Enterprise number is 232.
--      The ASN.1 prefix to, and including the Compaq Enterprise is:
--           1.3.6.1.4.1.232
--
-- ****************************************************************************


CPQNODE-MIB DEFINITIONS ::= BEGIN

    IMPORTS
        DisplayString               FROM RFC1213-MIB
        OBJECT-TYPE                 FROM RFC-1212
        TRAP-TYPE                   FROM RFC-1215
        sysName                     FROM RFC1213-MIB
        cpqHoTrapFlags              FROM CPQHOST-MIB
        cpqHeThermalDegradedAction  FROM CPQHLTH-MIB
        cpqHeTemperatureChassis     FROM CPQHLTH-MIB
        cpqHeTemperatureLocale      FROM CPQHLTH-MIB
        compaq                      FROM CPQHOST-MIB;

    cpqNode             OBJECT IDENTIFIER ::= { compaq 20 }
    cpqNodeFix          OBJECT IDENTIFIER ::= { cpqNode 2 }
    cpqNodeComponent    OBJECT IDENTIFIER ::= { cpqNodeFix 1 }


    cpqNodeCart OBJECT-TYPE
        SYNTAX  INTEGER
        ACCESS  read-only
        STATUS  mandatory
        DESCRIPTION
            "The cart number to index within this chassis when cpqNodeType is CART."
        ::= { cpqNodeComponent 1 }

    cpqNodeNode OBJECT-TYPE
        SYNTAX  INTEGER
        ACCESS  read-only
        STATUS  mandatory
        DESCRIPTION
            "The node number to index within this chassis when cpqNodeType is NODE."
        ::= { cpqNodeComponent 2 }

    cpqNodeType OBJECT-TYPE
        SYNTAX  INTEGER {
            cartridge(0),
            node(1),
            switch(2),
            unknown(3)
            }
        ACCESS  read-only
        STATUS  mandatory
        DESCRIPTION
            "Indicates whether the event applies to a cartridge, node or switch."
        ::= { cpqNodeComponent 3 }

    cpqNodeUUID OBJECT-TYPE
        SYNTAX  DisplayString (SIZE (0..36))
        ACCESS  read-only
        STATUS  mandatory
        DESCRIPTION
            "Cartridge specific Unique Identitifer to indetify where the trap 
            came from withing the chassis."
        ::= { cpqNodeComponent 4 }

    cpqNodeSerial OBJECT-TYPE
        SYNTAX  DisplayString (SIZE (0..20))
        ACCESS  read-only
        STATUS  mandatory
        DESCRIPTION
            "Cartridge specific Serial Number to indetify where the trap 
            came from withing the chassis."
        ::= { cpqNodeComponent 5 }

    cpqNodeMac1 OBJECT-TYPE
        SYNTAX  DisplayString
        ACCESS  read-only
        STATUS  deprecated
        DESCRIPTION
            "The module date.

             field  octets  contents   
             =====  ======  =======                  
               1      1-2   first byte of mac address
               2       3    : separator
               3      4-5   2nd byte of mac address
               4       6    : separator
               5      7-8   3rd byte of mac address
               6       9    : separator
               7     10-11  4th byte of mac address
               8      12    : separator
               9     13-14  5th byte of mac address
              10      15    : separator
              11     16-17  6th byte of mac address
              12      18    : separator

            First MAC address to identify the node"
        ::= { cpqNodeComponent 6 }

    cpqNodeMac2 OBJECT-TYPE
        SYNTAX  DisplayString
        ACCESS  read-only
        STATUS  deprecated
        DESCRIPTION
            "The module date.

             field  octets  contents   
             =====  ======  =======                  
               1      1-2   first byte of mac address
               2       3    : separator
               3      4-5   2nd byte of mac address
               4       6    : separator
               5      7-8   3rd byte of mac address
               6       9    : separator
               7     10-11  4th byte of mac address
               8      12    : separator
               9     13-14  5th byte of mac address
              10      15    : separator
              11     16-17  6th byte of mac address
              12      18    : separator

            First MAC address to identify the node"
        ::= { cpqNodeComponent 7 }

    cpqNodeMac3 OBJECT-TYPE
        SYNTAX  DisplayString
        ACCESS  read-only
        STATUS  deprecated
        DESCRIPTION
            "The module date.

             field  octets  contents   
             =====  ======  =======                  
               1      1-2   first byte of mac address
               2       3    : separator
               3      4-5   2nd byte of mac address
               4       6    : separator
               5      7-8   3rd byte of mac address
               6       9    : separator
               7     10-11  4th byte of mac address
               8      12    : separator
               9     13-14  5th byte of mac address
              10      15    : separator
              11     16-17  6th byte of mac address
              12      18    : separator

            First MAC address to identify the node"
        ::= { cpqNodeComponent 8 }

    cpqNodeMac4 OBJECT-TYPE
        SYNTAX  DisplayString
        ACCESS  read-only
        STATUS  deprecated
        DESCRIPTION
            "The module date.

             field  octets  contents   
             =====  ======  =======                  
               1      1-2   first byte of mac address
               2       3    : separator
               3      4-5   2nd byte of mac address
               4       6    : separator
               5      7-8   3rd byte of mac address
               6       9    : separator
               7     10-11  4th byte of mac address
               8      12    : separator
               9     13-14  5th byte of mac address
              10      15    : separator
              11     16-17  6th byte of mac address
              12      18    : separator

            First MAC address to identify the node"
        ::= { cpqNodeComponent 9 }

    cpqNodeErrorMessage OBJECT-TYPE
        SYNTAX  DisplayString (SIZE (0..128))
        ACCESS  read-only
        STATUS  mandatory
        DESCRIPTION
            "Cartridge specific message defining what the error is."
        ::= { cpqNodeComponent 10 }


  cpqNodePowerOn TRAP-TYPE 
        ENTERPRISE compaq
        VARIABLES { sysName, cpqHoTrapFlags, cpqNodeCart, cpqNodeNode, cpqNodeType, cpqNodeUUID, cpqNodeSerial, cpqNodeMac1, cpqNodeMac2, cpqNodeMac3, cpqNodeMac4 }
        DESCRIPTION
        "A Moonshot node has powered on."
              --#TYPE "Moonshot node has powered on (23010)"
              --#SUMMARY "Moonshot chassis %s node C%dN%d has powered on"
              --#ARGUMENTS {0, 2, 3}
              --#SEVERITY INFORMATIONAL
              --#TIMEINDEX 99
              --#SIMPLE_SEVERITY OK
              --#HWSTATUS_CATEGORY NONE
              
        ::= 23010

  cpqNodePowerOff TRAP-TYPE 
        ENTERPRISE compaq
        VARIABLES { sysName, cpqHoTrapFlags, cpqNodeCart, cpqNodeNode, cpqNodeType, cpqNodeUUID, cpqNodeSerial, cpqNodeMac1, cpqNodeMac2, cpqNodeMac3, cpqNodeMac4 }
        DESCRIPTION
        "A Moonshot node has powered off."
              --#TYPE "Moonshot node has powered off (23011)"
              --#SUMMARY "Moonshot chassis %s node C%dN%d has powered off"
              --#ARGUMENTS {0, 2, 3}
              --#SEVERITY INFORMATIONAL
              --#TIMEINDEX 99
              --#SIMPLE_SEVERITY OK
              --#HWSTATUS_CATEGORY NONE
              
        ::= 23011

    cpqNodeTemperatureDegraded TRAP-TYPE
        ENTERPRISE compaq
        VARIABLES { sysName, cpqHoTrapFlags, cpqHeThermalDegradedAction, cpqHeTemperatureChassis, cpqHeTemperatureLocale, cpqNodeCart, cpqNodeNode, cpqNodeType, cpqNodeUUID, cpqNodeSerial, cpqNodeMac1, cpqNodeMac2, cpqNodeMac3, cpqNodeMac4 }
        DESCRIPTION
            "The temperature status has been set to degraded in the
            specified chassis and location.

            The server's temperature is outside of the normal operating
            range."

        --#TYPE "Thermal Status Degraded (23001)"
        --#SUMMARY "Temperature out of range on chassis %s, node C%dN%d. Shutdown may occur."
        --#ARGUMENTS {0, 2, 3}
        --#SEVERITY CRITICAL
        --#TIMEINDEX 99
        --#STATE   DEGRADED
        --#SIMPLE_SEVERITY CRITICAL
        --#HWSTATUS_CATEGORY THERMAL
        --#ACTION "Check the system for hardware failures and verify the environment is properly cooled."
        
        ::= 23001
  
   cpqNodeTemperatureOk TRAP-TYPE
        ENTERPRISE compaq
        VARIABLES { sysName, cpqHoTrapFlags, cpqHeTemperatureChassis, cpqHeTemperatureLocale, cpqNodeCart, cpqNodeNode, cpqNodeType, cpqNodeUUID, cpqNodeSerial, cpqNodeMac1, cpqNodeMac2, cpqNodeMac3, cpqNodeMac4 }
        DESCRIPTION
            "The temperature status has been set to ok in the
            specified chassis and location.

            The server's temperature has returned to the normal operating
            range."

        --#TYPE "Thermal Status OK (23002)"
        --#SUMMARY "Temperature normal on chassis %s, node C%dN%d."
        --#ARGUMENTS {0, 2, 3}
        --#SEVERITY INFORMATIONAL
        --#TIMEINDEX 99
        --#STATE OPERATIONAL
        --#SIMPLE_SEVERITY OK
        --#HWSTATUS_CATEGORY THERMAL
        
        ::= 23002
  
    cpqNodeTemperatureFailed TRAP-TYPE
        ENTERPRISE compaq
        VARIABLES { sysName, cpqHoTrapFlags, cpqHeThermalDegradedAction, cpqHeTemperatureChassis, cpqHeTemperatureLocale, cpqNodeCart, cpqNodeNode, cpqNodeType, cpqNodeUUID, cpqNodeSerial, cpqNodeMac1, cpqNodeMac2, cpqNodeMac3, cpqNodeMac4 }
        DESCRIPTION
            "The temperature status has been set to degraded in the
            specified chassis and location.

            The server's temperature is outside of the normal operating
            range."

        --#TYPE "Thermal Status Failed (23003)"
        --#SUMMARY "Temperature out of range on chassis %s, node C%dN%d."
        --#ARGUMENTS {0, 2, 3}
        --#SEVERITY CRITICAL
        --#TIMEINDEX 99
        --#STATE   DEGRADED
        --#SIMPLE_SEVERITY CRITICAL
        --#HWSTATUS_CATEGORY THERMAL
        --#ACTION "Check the system for hardware failures and verify the environment is properly cooled."
        
        ::= 23003
  
    cpqNodeErrorEvent TRAP-TYPE
        ENTERPRISE compaq
        VARIABLES { sysName, cpqHoTrapFlags, cpqNodeErrorMessage, cpqNodeCart, cpqNodeNode, cpqNodeType, cpqNodeUUID, cpqNodeSerial, cpqNodeMac1, cpqNodeMac2, cpqNodeMac3, cpqNodeMac4 }
        DESCRIPTION
            "An error event has been received from a cartridge.  The
            details can be found in the error message string."


        --#TYPE "Error Event (23004)"
        --#SUMMARY "Error event on chassis %s, node C%dN%d."
        --#ARGUMENTS {0, 3, 4}
        --#SEVERITY CRITICAL
        --#TIMEINDEX 99
        --#STATE   DEGRADED
        --#SIMPLE_SEVERITY CRITICAL
        --#HWSTATUS_CATEGORY NONE
        --#ACTION "Check the system for hardware failures."
        
        ::= 23004


  END

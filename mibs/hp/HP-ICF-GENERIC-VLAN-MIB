HP-ICF-GENERIC-VLAN-MIB DEFINITIONS ::= BEGIN

   IMPORTS
      OBJECT-TYPE, MODULE-IDENTITY, TimeTicks
            FROM SNMPv2-SMI
      OBJECT-GROUP, MODULE-COMPLIANCE
            FROM SNMPv2-CONF
      dot1qTpFdbEntry, VlanId
            FROM Q-BRIDGE-MIB
      hpSwitch
            FROM HP-ICF-OID;
   
   hpicfGenericVlanMIB MODULE-IDENTITY
      LAST-UPDATED  "201706280000Z"  -- June 28, 2017
      ORGANIZATION  "HP Networking"
      CONTACT-INFO  "Hewlett Packard Company
                     8000 Foothills Blvd.
                     Roseville, CA 95747"
    
      DESCRIPTION   "The MIB module for generic VLAN features"
            
      REVISION      "201706280000Z"  -- June 28, 2017
      DESCRIPTION   "Added hpicfDot1qTpFdbInstalledTime object.
                     Added hpicfGenericVlanFeaturesConfGrp1.
                     Added hpicfGenericVlanFeaturesComp1.
                     Deprecated hpicfGenericVlanFeaturesCompliance.
                     Deprecated hpicfGenericVlanFeaturesConfigGroup."

      REVISION      "201002080000Z"  -- February 08, 2010
      DESCRIPTION   "The initial revision."

    ::= {hpSwitch 67 }           

   hpicfGenericVlanFeaturesObjects       OBJECT IDENTIFIER
           ::= { hpicfGenericVlanMIB 1 }

   hpicfGenericVlanFeaturesConformance   OBJECT IDENTIFIER 
           ::= { hpicfGenericVlanMIB 2 }


   hpicfGenericVlanFeaturesTable OBJECT-TYPE
      SYNTAX      SEQUENCE OF HpicfGenericVlanFeaturesEntry
      MAX-ACCESS  not-accessible
      STATUS      current
      DESCRIPTION "This table contains objects that are generic to
                   multiple VLAN features, using the same indices as
                   dot1qTpFdbEntry"
      ::= { hpicfGenericVlanFeaturesObjects 1 } 

   hpicfGenericVlanFeaturesEntry  OBJECT-TYPE
      SYNTAX      HpicfGenericVlanFeaturesEntry
      MAX-ACCESS  not-accessible
      STATUS      current
      DESCRIPTION "A row in a table, containing the VLAN ID."
      AUGMENTS { dot1qTpFdbEntry }
      ::= { hpicfGenericVlanFeaturesTable 1 }

   HpicfGenericVlanFeaturesEntry ::=
      SEQUENCE
      {
            hpicfMacNotifyClearVlanControl    INTEGER,
            hpicfDot1qTpFdbVlanId             VlanId,
            hpicfDot1qTpFdbInstalledTime      TimeTicks
      } 
    
   hpicfMacNotifyClearVlanControl OBJECT-TYPE
      SYNTAX      INTEGER {
         noOperation(1),
         macNotifyClearVlan(2)
      }
      MAX-ACCESS  read-write
      STATUS      current
      DESCRIPTION "This variable uniquely identifies the operation that will be
                   executed on the object this entry applies to.
                   When read, noOperation(1) should be returned."
      ::= { hpicfGenericVlanFeaturesEntry 1 }

   hpicfDot1qTpFdbVlanId OBJECT-TYPE
      SYNTAX      VlanId
      MAX-ACCESS      read-only
      STATUS      current
      DESCRIPTION "The VLAN ID to which this entry belongs."
      ::= { hpicfGenericVlanFeaturesEntry 2 }

   hpicfDot1qTpFdbInstalledTime OBJECT-TYPE
       SYNTAX      TimeTicks
       MAX-ACCESS  read-only
       STATUS      current
       DESCRIPTION "The time (in hundredths of a second) when the mac-address
                    got installed in Mgmt module,with respect to System
                    Up time."
      ::= { hpicfGenericVlanFeaturesEntry 3 }
--   MAC Notify MIB Conformance

   hpicfGenericVlanFeaturesCompliances 
         OBJECT IDENTIFIER ::= { hpicfGenericVlanFeaturesConformance 1 }
   hpicfGenericVlanFeaturesGroups     
         OBJECT IDENTIFIER ::= { hpicfGenericVlanFeaturesConformance 2 }

-- compliance statements

   hpicfGenericVlanFeaturesCompliance MODULE-COMPLIANCE
        STATUS      deprecated
        DESCRIPTION "The compliance statement for SNMP entities which
                     implement the MAC Notify MIB."
        MODULE  -- this module
           MANDATORY-GROUPS  {
                   hpicfGenericVlanFeaturesConfigGroup
                             }
        ::= { hpicfGenericVlanFeaturesCompliances 1 }

   hpicfGenericVlanFeaturesComp1 MODULE-COMPLIANCE
        STATUS      current
        DESCRIPTION "The compliance statement for SNMP entities which
                     implement the MAC Notify MIB."
        MODULE  -- this module
           MANDATORY-GROUPS  {
                   hpicfGenericVlanFeaturesConfGrp1
                             }
        ::= { hpicfGenericVlanFeaturesCompliances 2 }

-- ******************
-- Conformance Groups
-- ******************

   hpicfGenericVlanFeaturesConfigGroup  OBJECT-GROUP
        OBJECTS 
           {
              hpicfMacNotifyClearVlanControl,
              hpicfDot1qTpFdbVlanId                          
           }
        STATUS      deprecated
        DESCRIPTION "A collection of objects used for generic
                     VLAN operations."
        ::= { hpicfGenericVlanFeaturesGroups 2 }

   hpicfGenericVlanFeaturesConfGrp1  OBJECT-GROUP
        OBJECTS
           {
              hpicfMacNotifyClearVlanControl,
              hpicfDot1qTpFdbVlanId,
              hpicfDot1qTpFdbInstalledTime
           }
        STATUS      current
        DESCRIPTION "A collection of objects used for generic
                     VLAN operations."
        ::= { hpicfGenericVlanFeaturesGroups 3 }

END

-- ***********************************************************************
-- Module:    hpSwitchTrap.mib
-- 
-- Copyright (C) 2016-2019 Hewlett Packard Enterprise Development LP
-- All Rights Reserved.
--  
-- The contents of this software are proprietary and confidential to
-- the Hewlett Packard Enterprise Development LP. No part of this
-- program may be photocopied, reproduced, or translated into another
-- programming language without prior written consent of the
-- Hewlett Packard Enterprise Development LP.
--
-- Purpose: This file contains MIB definition of HP-SWITCH-TRAP-MIB 
--
-- ***********************************************************************

HP-SWITCH-TRAP-MIB DEFINITIONS ::= BEGIN 

    IMPORTS

	TRAP-TYPE                      FROM RFC-1215

	hpSwitch1600,   hpSwitchJ9079A, hpSwitchJ9080A, hpSwitchJ9028A,
	hpSwitchJ9028B, hpSwitchJ9029A, hpSwitchJ9449A, hpSwitchJ9450A,
	hpSwitchJ9802A, hpSwitchJ9803A, hpSwitchJ9833A, hpSwitchJ9834A, 
	hpSwitch2400,   hpSwitch2424,   hpSwitchJ4812A, hpSwitchJ4813A, 
	hpSwitchJ9019A, hpSwitchJ9019B, hpSwitchJ9020A, hpSwitchJ9279A, 
	hpSwitchJ9280A, hpSwitchJ9137A, hpSwitchJ9138A, hpSwitchJ9298A, 
	hpSwitchJ9299A, hpSwitchJ9772A, hpSwitchJ9773A, hpSwitchJ9774A, 
	hpSwitchJ9775A, hpSwitchJ9776A, hpSwitchJ9777A, hpSwitchJ9778A, 
	hpSwitchJ9779A, hpSwitchJ9780A, hpSwitchJL070A, hpSwitchJ9781A, 
        hpSwitchJ9782A, hpSwitchJ9660A, hpSwitchJ9853A, hpSwitchJ9854A, 
        hpSwitchJ9855A, hpSwitchJ9856A, hpSwitchJ4899A, hpSwitchJ4899B, 
        hpSwitchJ4899C, hpSwitchJ4900A, hpSwitchJ4900B, hpSwitchJ4900C,	
        hpSwitchJ8164A, hpSwitchJ8165A, hpSwitchJ8762A, hpSwitchJ9085A, 
        hpSwitchJ9086A, hpSwitchJ9087A, hpSwitchJ9088A, hpSwitchJ9089A, 
        hpSwitchJ9565A, hpSwitchJ9623A, hpSwitchJ9624A, hpSwitchJ9625A, 
        hpSwitchJ9626A, hpSwitchJ9627A, hpSwitchJ4903A, hpSwitchJ4904A, 
        hpSwitchJ9021A, hpSwitchJ9022A, hpSwitchJ9049A, hpSwitchJ9050A, 
        hpSwitchJ9145A, hpSwitchJ9146A, hpSwitchJ9147A, hpSwitchJ9148A, 
        hpSwitchJ9562A, hpSwitchJ9726A, hpSwitchJ9727A, hpSwitchJ9728A, 
        hpSwitchJ9729A, hpStack2920,    hpSwitchJ4905A, hpSwitchJ4906A, 
        hpSwitchJ8692A, hpSwitchJ8693A, hpSwitchJ9310A, hpSwitchJ9311A, 
        hpSwitchJ9470A, hpSwitchJ9471A, hpSwitchJ9472A, hpSwitchJ9473A, 
        hpSwitchJ9573,  hpSwitchJ9574,  hpSwitchJ9575,  hpSwitchJ9576, 
        hpSwitchJ9584,  hpSwitchJ9585,  hpSwitchJ9586,  hpSwitchJ9587, 
        hpSwitchJ9588,                  hpStack,       hpStackVSF5400R,
                           arubaSwitchJL354A, arubaSwitchJL355A,
        arubaSwitchJL356A, arubaSwitchJL357A,
        arubaStack2930,    arubaStack2930M,   arubaSwitchJL319A,
        arubaSwitchJL321A, arubaSwitchJL320A, arubaSwitchJL322A,
        arubaSwitchJL323A, arubaSwitchJL258A,
        arubaSwitchJL253A, arubaSwitchJL254A, arubaSwitchJL255A,
        arubaSwitchJL256A, arubaSwitchJL259A, arubaSwitchJL260A,
        arubaSwitchJL261A, arubaSwitchJL262A, arubaSwitchJL558A, 
        arubaSwitchJL557A, arubaSwitchJL692A,
        arubaSwitchJL263A, arubaSwitchJL264A, arubaSwitchJL693A,
        arubaSwitchJL559A, arubaSwitchJL324A,
        arubaSwitchR0M67A, arubaSwitchR0M68A,
        arubaStack3810, arubaJL071A,    arubaJL072A,       arubaJL073A,
        arubaJL074A,    arubaJL075A,    arubaJL076A,       arubaJL077A,
        hpSwitch4000,   hpSwitchJ4865A, hpSwitchJ4887A, hpSwitchJ4819A,
        hpSwitchJ4850A,                                 hpSwitchJ8697A,
        hpSwitchJ8698A, hpSwitchJ9850A, hpSwitchJ9851A, hpSwitchJ4902A, 
        hpSwitch516733-B21, hpSwitch498358-B21,         hpSwitchJ8992A, 
        hpSwitch6308, hpSwitchJ8433A,   hpSwitchJ8474A, hpSwitchJ9263A, 
        hpSwitchJ9264A, hpSwitchJ9265A, hpSwitchJ9451A, hpSwitchJ9452A, 
        hpSwitch8000,   hpSwitchJ9477A, hpSwitchJ9091A, hpSwitch9304,   
        hpSwitch9308,   hpSwitchJ4874A, hpSwitchJ8680A, hpAdvSwitch2000, 
        hpAdvSwitch2000B, hpSwitch212M, hpSwitch224M,   hpAdvSwitch800T, 
        hpAdvSwitch200, bridge1010, bridgeRemote, eswitch, eswitch2, 
        netSwitch100, netSwitch200, icfRouterER, icfRouterTR, icfRouterSR, 
        icfRouterFR, icfRouterLR, icfRouterBR, icfRouterPR, icfRouter650, 
        icfRouter230, icfRouter250, icfRouter255, icfRouter210, fiberOptic, 
        advStack12, advStack24, advStack48, advStackU8, advStackU16, 
        hpAdvStkEnetSH12R, hpAdvStkEnetSH24R, hpAdvStkEnetSH24T, 
        hpAdvStk100Tx12TM, hp10BaseTHub12M, hp10BaseTHub24M, 
        hpProCurve10T100THub12M, hpProCurve10T100THub24M, 
        hpAdvStkEnetSHStack, hpSwitchJ9783A, hpSwitchJ9800A, 
	hpSwitchJ9801A
	
	FROM HP-ICF-OID;    


-- -------------
-- 1600 SWITCHES
-- -------------


  hpSwitch1600trap    TRAP-TYPE
        ENTERPRISE    hpSwitch1600
        DESCRIPTION   "An SNMP trap that is generated for an RMON event on a J4120A 1600M Switch."
        ::= 2

-- -------------
-- 1700 SWITCHES
-- -------------
   hpSwitchJ9079Atrap  TRAP-TYPE
        ENTERPRISE     hpSwitchJ9079A
        DESCRIPTION    "An SNMP trap that is generated for an RMON event on a J9079A 1700-8 Switch."
        ::= 2

   hpSwitchJ9080Atrap  TRAP-TYPE
        ENTERPRISE     hpSwitchJ9080A 
        DESCRIPTION    "An SNMP trap that is generated for an RMON event on a J9080A 1700-24 Switch."
        ::= 2

-- -------------
-- 1800 SWITCHES
-- -------------
   hpSwitchJ9028Atrap  TRAP-TYPE
        ENTERPRISE     hpSwitchJ9028A 
        DESCRIPTION    "An SNMP trap that is generated for an RMON event on a J9028A 1800-24G Switch."
        ::= 2

   hpSwitchJ9028Btrap  TRAP-TYPE
        ENTERPRISE     hpSwitchJ9028B 
        DESCRIPTION    "An SNMP trap that is generated for an RMON event on a J9028B 1800-24G Switch."
        ::= 2

   hpSwitchJ9029Atrap  TRAP-TYPE
        ENTERPRISE     hpSwitchJ9029A 
        DESCRIPTION    "An SNMP trap that is generated for an RMON event on a J9029A 1800-24G Switch."
        ::= 2

-- -------------
-- 1810 SWITCHES
-- -------------
   hpSwitchJ9449Atrap  TRAP-TYPE
        ENTERPRISE     hpSwitchJ9449A 
        DESCRIPTION    "An SNMP trap that is generated for an RMON event on a J9449A 1810-8G Switch."
        ::= 2

   hpSwitchJ9450Atrap  TRAP-TYPE
        ENTERPRISE     hpSwitchJ9450A 
        DESCRIPTION    "An SNMP trap that is generated for an RMON event on a J9450A 1810-24G Switch."
        ::= 2

   hpSwitchJ9660Atrap  TRAP-TYPE
        ENTERPRISE     hpSwitchJ9660A 
        DESCRIPTION    "An SNMP trap that is generated for an RMON event on a J9660A 1810-48G Switch."
        ::= 2


   hpSwitchJ9800Atrap  TRAP-TYPE
   	ENTERPRISE     hpSwitchJ9800A 
   	DESCRIPTION    "An SNMP trap that is generated for an RMON event on a J9800A 1810-8 v2 Switch."
   	::= 2


   hpSwitchJ9801Atrap  TRAP-TYPE
  	ENTERPRISE     hpSwitchJ9801A 
  	DESCRIPTION    "An SNMP trap that is generated for an RMON event on a J9801A 1810-24 v2 Switch."
   	::= 2


   hpSwitchJ9802Atrap  TRAP-TYPE
        ENTERPRISE     hpSwitchJ9802A 
        DESCRIPTION    "An SNMP trap that is generated for an RMON event on a J9802A 1810-8G v2 Switch."
        ::= 2

   hpSwitchJ9803Atrap  TRAP-TYPE
        ENTERPRISE     hpSwitchJ9803A 
        DESCRIPTION    "An SNMP trap that is generated for an RMON event on a J9803A 1810-24G v2 Switch."
        ::= 2

   hpSwitchJ9833Atrap  TRAP-TYPE
        ENTERPRISE     hpSwitchJ9833A 
        DESCRIPTION    "An SNMP trap that is generated for an RMON event on a J9833A PS1810-8G Switch."
        ::= 2

   hpSwitchJ9834Atrap  TRAP-TYPE
        ENTERPRISE     hpSwitchJ9834A 
        DESCRIPTION    "An SNMP trap that is generated for an RMON event on a J9834A PS1810-24G Switch."
        ::= 2

-- -------------
-- 2400 SWITCHES
-- -------------
   hpSwitch2400trap    TRAP-TYPE
         ENTERPRISE    hpSwitch2400 
        DESCRIPTION    "An SNMP trap that is generated for an RMON event on a J4122A 2400M Switch."
        ::= 2

   hpSwitch2424trap    TRAP-TYPE
        ENTERPRISE     hpSwitch2424 
        DESCRIPTION    "An SNMP trap that is generated for an RMON event on a J4122B 2424M Switch."
        ::= 2



-- -------------
-- 2500 SWITCHES
-- -------------


   hpSwitchJ4812Atrap    TRAP-TYPE
          ENTERPRISE     hpSwitchJ4812A 
          DESCRIPTION    "An SNMP trap that is generated for an RMON event on a J4812A 2512 Switch."
          ::= 2


   hpSwitchJ4813Atrap    TRAP-TYPE
          ENTERPRISE     hpSwitchJ4813A 
          DESCRIPTION    "An SNMP trap that is generated for an RMON event on a J4813A 2524 Switch."
          ::= 2



-- -------------
-- 2510 SWITCHES
-- -------------


   hpSwitchJ9019Atrap    TRAP-TYPE
          ENTERPRISE     hpSwitchJ9019A 
          DESCRIPTION    "An SNMP trap that is generated for an RMON event on a J9019A 2510-24 Switch."
          ::= 2


   hpSwitchJ9019Btrap    TRAP-TYPE
          ENTERPRISE     hpSwitchJ9019B 
          DESCRIPTION    "An SNMP trap that is generated for an RMON event on a J9019B 2510-24 Switch."
          ::= 2


   hpSwitchJ9020Atrap    TRAP-TYPE
          ENTERPRISE     hpSwitchJ9020A 
          DESCRIPTION    "An SNMP trap that is generated for an RMON event on a J9020A 2510-48 Switch."
          ::= 2


   hpSwitchJ9279Atrap    TRAP-TYPE
          ENTERPRISE     hpSwitchJ9279A 
          DESCRIPTION    "An SNMP trap that is generated for an RMON event on a J9279A 2510-24G Switch."
          ::= 2


   hpSwitchJ9280Atrap    TRAP-TYPE
          ENTERPRISE     hpSwitchJ9280A 
          DESCRIPTION    "An SNMP trap that is generated for an RMON event on a J9280A 2510-48G Switch."
          ::= 2



-- -------------
-- 2520 SWITCHES
-- -------------


   hpSwitchJ9137Atrap    TRAP-TYPE
          ENTERPRISE     hpSwitchJ9137A 
          DESCRIPTION    "An SNMP trap that is generated for an RMON event on a J9137A 2520-8-PoE Switch."
          ::= 2


   hpSwitchJ9138Atrap    TRAP-TYPE
          ENTERPRISE     hpSwitchJ9138A
          DESCRIPTION    "An SNMP trap that is generated for an RMON event on a J9138A 2520-24-PoE Switch."
          ::= 2


   hpSwitchJ9298Atrap    TRAP-TYPE
          ENTERPRISE     hpSwitchJ9298A 
          DESCRIPTION    "An SNMP trap that is generated for an RMON event on a J9298A 2520-8G-PoE Switch."
          ::= 2


   hpSwitchJ9299Atrap    TRAP-TYPE
          ENTERPRISE     hpSwitchJ9299A 
          DESCRIPTION    "An SNMP trap that is generated for an RMON event on a J9298A 2520-24G-PoE Switch."
          ::= 2


-- -------------
-- 2530 SWITCHES
-- -------------


   hpSwitchJ9772Atrap    TRAP-TYPE
          ENTERPRISE     hpSwitchJ9772A 
          DESCRIPTION    "An SNMP trap that is generated for an RMON event on a J9772A 2530-48G-PoE+ Switch."
          ::= 2


   hpSwitchJ9773Atrap    TRAP-TYPE
          ENTERPRISE     hpSwitchJ9773A 
          DESCRIPTION    "An SNMP trap that is generated for an RMON event on a J9773A 2530-24G-PoE+ Switch."
          ::= 2
 

   hpSwitchJ9774Atrap    TRAP-TYPE
          ENTERPRISE     hpSwitchJ9774A 
          DESCRIPTION    "An SNMP trap that is generated for an RMON event on a J9774A 2530-8G-PoE+ Switch."
          ::= 2
 

   hpSwitchJ9775Atrap    TRAP-TYPE
          ENTERPRISE     hpSwitchJ9775A 
          DESCRIPTION    "An SNMP trap that is generated for an RMON event on a J9775A 2530-48G Switch."
          ::= 2


   hpSwitchJ9776Atrap    TRAP-TYPE
          ENTERPRISE     hpSwitchJ9776A 
          DESCRIPTION    "An SNMP trap that is generated for an RMON event on a J9776A 2530-24G Switch."
          ::= 2


   hpSwitchJ9777Atrap    TRAP-TYPE
          ENTERPRISE     hpSwitchJ9777A 
          DESCRIPTION    "An SNMP trap that is generated for an RMON event on a J9777A 2530-8G Switch."
          ::= 2


   hpSwitchJ9778Atrap    TRAP-TYPE
          ENTERPRISE     hpSwitchJ9778A 
          DESCRIPTION    "An SNMP trap that is generated for an RMON event on a J9778A 2530-48-PoE+ Switch."
          ::= 2


   hpSwitchJ9779Atrap    TRAP-TYPE
          ENTERPRISE     hpSwitchJ9779A 
          DESCRIPTION    "An SNMP trap that is generated for an RMON event on a J9779A 2530-24-PoE+ Switch."
          ::= 2


   hpSwitchJ9780Atrap    TRAP-TYPE
          ENTERPRISE     hpSwitchJ9780A 
          DESCRIPTION    "An SNMP trap that is generated for an RMON event on a J9780A 2530-8-PoE+ Switch."
          ::= 2


   hpSwitchJL070Atrap    TRAP-TYPE
          ENTERPRISE     hpSwitchJL070A 
          DESCRIPTION    "An SNMP trap that is generated for an RMON event on a JL070A 2530-8-PoE+ Switch."
          ::= 2


   hpSwitchJ9781Atrap    TRAP-TYPE
          ENTERPRISE     hpSwitchJ9781A 
          DESCRIPTION    "An SNMP trap that is generated for an RMON event on a J9781A 2530-48 Switch."
          ::= 2


   hpSwitchJ9782Atrap    TRAP-TYPE
          ENTERPRISE     hpSwitchJ9782A 
          DESCRIPTION    "An SNMP trap that is generated for an RMON event on a J9782A 2530-24 Switch."
          ::= 2
 

   hpSwitchJ9783Atrap    TRAP-TYPE
          ENTERPRISE     hpSwitchJ9783A 
          DESCRIPTION    "An SNMP trap that is generated for an RMON event on a J9783A 2530-8 Switch."
          ::= 2


   hpSwitchJ9853Atrap    TRAP-TYPE
          ENTERPRISE     hpSwitchJ9853A 
          DESCRIPTION    "An SNMP trap that is generated for an RMON event on a J9853A 2530-48G-PoE+-2SFP+ Switch."
          ::= 2


   hpSwitchJ9854Atrap    TRAP-TYPE
          ENTERPRISE     hpSwitchJ9854A 
          DESCRIPTION    "An SNMP trap that is generated for an RMON event on a J9854A 2530-24G-PoE+-2SFP+ Switch."
          ::= 2


   hpSwitchJ9855Atrap    TRAP-TYPE
          ENTERPRISE     hpSwitchJ9855A 
          DESCRIPTION    "An SNMP trap that is generated for an RMON event on a J9855A 2530-48G-2SFP+ Switch."
          ::= 2


   hpSwitchJ9856Atrap    TRAP-TYPE
          ENTERPRISE     hpSwitchJ9856A 
          DESCRIPTION    "An SNMP trap that is generated for an RMON event on a J9856A 2530-24G-2SFP+ Switch."
          ::= 2



-- -------------
-- 2540 SWITCHES
-- -------------


   arubaSwitchJL354Atrap TRAP-TYPE
          ENTERPRISE     arubaSwitchJL354A
          DESCRIPTION    "An SNMP trap that is generated for an RMON event on a JL354A Aruba 2930F-24G-4SFP+ Switch."
          ::= 2

   arubaSwitchJL355Atrap TRAP-TYPE
          ENTERPRISE     arubaSwitchJL355A
          DESCRIPTION    "An SNMP trap that is generated for an RMON event on a JL355A Aruba 2930F-48G-4SFP+ Switch."
          ::= 2

   arubaSwitchJL356Atrap TRAP-TYPE
          ENTERPRISE     arubaSwitchJL356A
          DESCRIPTION    "An SNMP trap that is generated for an RMON event on a JL356A Aruba 2930F-24G-PoE+-4SFP+ Switch."
          ::= 2

   arubaSwitchJL357Atrap TRAP-TYPE
          ENTERPRISE     arubaSwitchJL357A
          DESCRIPTION    "An SNMP trap that is generated for an RMON event on a JL357A Aruba 2930F-48G-PoE+-4SFP+ Switch."
          ::= 2


-- -------------
-- 2600 SWITCHES
-- -------------


   hpSwitchJ4899Atrap    TRAP-TYPE
          ENTERPRISE     hpSwitchJ4899A 
          DESCRIPTION    "An SNMP trap that is generated for an RMON event on a J4899A 2650 Switch."
          ::= 2


   hpSwitchJ4899Btrap    TRAP-TYPE
          ENTERPRISE     hpSwitchJ4899B 
          DESCRIPTION    "An SNMP trap that is generated for an RMON event on a J4899B 2650 Switch."
          ::= 2


   hpSwitchJ4899Ctrap    TRAP-TYPE
          ENTERPRISE     hpSwitchJ4899C 
          DESCRIPTION    "An SNMP trap that is generated for an RMON event on a J4899C 2650 Switch."
          ::= 2


   hpSwitchJ4900Atrap    TRAP-TYPE
          ENTERPRISE     hpSwitchJ4900A 
          DESCRIPTION    "An SNMP trap that is generated for an RMON event on a J4900A 2626 Switch."
          ::= 2


   hpSwitchJ4900Btrap    TRAP-TYPE
          ENTERPRISE     hpSwitchJ4900B 
          DESCRIPTION    "An SNMP trap that is generated for an RMON event on a J4900B 2626 Switch."
          ::= 2


   hpSwitchJ4900Ctrap    TRAP-TYPE
          ENTERPRISE     hpSwitchJ4900C 
          DESCRIPTION    "An SNMP trap that is generated for an RMON event on a J4900C 2626 Switch."
          ::= 2


   hpSwitchJ8164Atrap    TRAP-TYPE
          ENTERPRISE     hpSwitchJ8164A 
          DESCRIPTION    "An SNMP trap that is generated for an RMON event on a J8164A 2626-PWR Switch."
          ::= 2


   hpSwitchJ8165Atrap    TRAP-TYPE
          ENTERPRISE     hpSwitchJ8165A 
          DESCRIPTION    "An SNMP trap that is generated for an RMON event on a J8165A 2650-PWR Switch."
          ::= 2


   hpSwitchJ8762Atrap    TRAP-TYPE
          ENTERPRISE     hpSwitchJ8762A 
          DESCRIPTION    "An SNMP trap that is generated for an RMON event on a J8762A 2600-8-PWR Switch."
          ::= 2


-- -------------
-- 2610 SWITCHES
-- -------------


  hpSwitchJ9085Atrap    TRAP-TYPE
          ENTERPRISE     hpSwitchJ9085A 
          DESCRIPTION    "An SNMP trap that is generated for an RMON event on a J9085A 2610-24 Switch."
          ::= 2


   hpSwitchJ9086Atrap    TRAP-TYPE
          ENTERPRISE     hpSwitchJ9086A 
          DESCRIPTION    "An SNMP trap that is generated for an RMON event on a J9086A 2610-24-PoE+ Switch."
          ::= 2


   hpSwitchJ9087Atrap    TRAP-TYPE
          ENTERPRISE     hpSwitchJ9087A 
          DESCRIPTION    "An SNMP trap that is generated for an RMON event on a J9087A 2610-24-PoE Switch."
          ::= 2


   hpSwitchJ9088Atrap    TRAP-TYPE
          ENTERPRISE     hpSwitchJ9088A 
          DESCRIPTION    "An SNMP trap that is generated for an RMON event on a J9088A 2610-48 Switch."
          ::= 2


   hpSwitchJ9089Atrap    TRAP-TYPE
          ENTERPRISE     hpSwitchJ9089A 
          DESCRIPTION    "An SNMP trap that is generated for an RMON event on a J9089A 2610-48-PoE Switch."
          ::= 2



-- -------------
-- 2615 SWITCHES
-- -------------


   hpSwitchJ9565Atrap    TRAP-TYPE
          ENTERPRISE     hpSwitchJ9565A 
          DESCRIPTION    "An SNMP trap that is generated for an RMON event on a J9565A 2615-8-PoE Switch."
          ::= 2



-- -------------
-- 2620 SWITCHES
-- -------------


   hpSwitchJ9623Atrap    TRAP-TYPE
          ENTERPRISE     hpSwitchJ9623A 
          DESCRIPTION    "An SNMP trap that is generated for an RMON event on a J9623A 2620-24 Switch."
          ::= 2


   hpSwitchJ9624Atrap    TRAP-TYPE
          ENTERPRISE     hpSwitchJ9624A 
          DESCRIPTION    "An SNMP trap that is generated for an RMON event on a J9624A 2620-24-PPoE+ Switch."
          ::= 2


   hpSwitchJ9625Atrap    TRAP-TYPE
          ENTERPRISE     hpSwitchJ9625A 
          DESCRIPTION    "An SNMP trap that is generated for an RMON event on a J9625A 2620-24-PoE+ Switch."
          ::= 2


   hpSwitchJ9626Atrap    TRAP-TYPE
          ENTERPRISE     hpSwitchJ9626A 
          DESCRIPTION    "An SNMP trap that is generated for an RMON event on a J9626A 2620-48 Switch."
          ::= 2


   hpSwitchJ9627Atrap    TRAP-TYPE
          ENTERPRISE     hpSwitchJ9627A
          DESCRIPTION    "An SNMP trap that is generated for an RMON event on a J9627A 2620-48-PoE+ Switch."
          ::= 2



-- -------------
-- 2800 SWITCHES
-- -------------


   hpSwitchJ4903Atrap    TRAP-TYPE
          ENTERPRISE     hpSwitchJ4903A
          DESCRIPTION    "An SNMP trap that is generated for an RMON event on a J4903A 2824 Switch."
          ::= 2


   hpSwitchJ4904Atrap    TRAP-TYPE
          ENTERPRISE     hpSwitchJ4904A
          DESCRIPTION    "An SNMP trap that is generated for an RMON event on a J4904A 2828 Switch."
          ::= 2



-- -------------
-- 2810 SWITCHES
-- -------------


   hpSwitchJ9021Atrap    TRAP-TYPE
          ENTERPRISE     hpSwitchJ9021A
          DESCRIPTION    "An SNMP trap that is generated for an RMON event on a J9021A 2810-24G Switch."
          ::= 2


   hpSwitchJ9022Atrap    TRAP-TYPE
          ENTERPRISE     hpSwitchJ9022A
          DESCRIPTION    "An SNMP trap that is generated for an RMON event on a J9022A 2810-48G Switch."
          ::= 2



-- -------------
-- 2900 SWITCHES
-- -------------


   hpSwitchJ9049Atrap    TRAP-TYPE
          ENTERPRISE     hpSwitchJ9049A
          DESCRIPTION    "An SNMP trap that is generated for an RMON event on a J9049A 2900-24G Switch."
          ::= 2


   hpSwitchJ9050Atrap    TRAP-TYPE
          ENTERPRISE     hpSwitchJ9050A
          DESCRIPTION    "An SNMP trap that is generated for an RMON event on a J9050A 2900-48G Switch."
          ::= 2


-- -------------
-- 2910 SWITCHES
-- -------------


   hpSwitchJ9145Atrap    TRAP-TYPE
          ENTERPRISE     hpSwitchJ9145A
          DESCRIPTION    "An SNMP trap that is generated for an RMON event on a J9145A 2910-24G Switch."
          ::= 2


   hpSwitchJ9146Atrap    TRAP-TYPE
          ENTERPRISE     hpSwitchJ9146A
          DESCRIPTION    "An SNMP trap that is generated for an RMON event on a J9146A 2910-24G-PoE+ Switch."
          ::= 2


   hpSwitchJ9147Atrap    TRAP-TYPE
          ENTERPRISE     hpSwitchJ9147A
          DESCRIPTION    "An SNMP trap that is generated for an RMON event on a J9147A 2910-48G Switch."
          ::= 2


   hpSwitchJ9148Atrap    TRAP-TYPE
          ENTERPRISE     hpSwitchJ9148A
          DESCRIPTION    "An SNMP trap that is generated for an RMON event on a J9148A 2910-48G-PoE+ Switch."
          ::= 2


-- -------------
-- 2915 SWITCHES
-- -------------


   hpSwitchJ9562Atrap    TRAP-TYPE
          ENTERPRISE     hpSwitchJ9562A
          DESCRIPTION    "An SNMP trap that is generated for an RMON event on a J9562A 2915-8G-PoE Switch."
          ::= 2



-- -------------
-- 2920 SWITCHES
-- -------------


   hpSwitchJ9726Atrap    TRAP-TYPE
          ENTERPRISE     hpSwitchJ9726A
          DESCRIPTION    "An SNMP trap that is generated for an RMON event on a J9726A 2920-24G Switch."
          ::= 2


   hpSwitchJ9727Atrap    TRAP-TYPE
          ENTERPRISE     hpSwitchJ9727A
          DESCRIPTION    "An SNMP trap that is generated for an RMON event on a J9727A 2920-24G-POE+ Switch."
          ::= 2


   hpSwitchJ9728Atrap    TRAP-TYPE
          ENTERPRISE     hpSwitchJ9728A
          DESCRIPTION    "An SNMP trap that is generated for an RMON event on a J9728A 2920-48G Switch."
          ::= 2


   hpSwitchJ9729Atrap    TRAP-TYPE
          ENTERPRISE     hpSwitchJ9729A
          DESCRIPTION    "An SNMP trap that is generated for an RMON event on a J9729A 2920-48G-POE+ Switch."
          ::= 2


   hpStack2920trap       TRAP-TYPE
          ENTERPRISE     hpStack2920
          DESCRIPTION    "An SNMP trap that is generated for an RMON event on a stack of 2920 Switches."
          ::= 2	


-- -------------
-- 2930 SWITCHES
-- -------------

   arubaStack2930Mtrap   TRAP-TYPE
          ENTERPRISE     arubaStack2930M
          DESCRIPTION    "An SNMP trap that is generated for an RMON event on a BPS stack of 2930M switches."
          ::= 2

   arubaStack2930trap    TRAP-TYPE
          ENTERPRISE     arubaStack2930
          DESCRIPTION    "An SNMP trap that is generated for an RMON event on a stack of 2930 Switches."
          ::= 2

   arubaSwitchJL319Atrap TRAP-TYPE
          ENTERPRISE     arubaSwitchJL319A
          DESCRIPTION    "An SNMP trap that is generated for an RMON event on a JL319A Aruba 2930M-24G Switch."
          ::= 2

   arubaSwitchJL321Atrap TRAP-TYPE
          ENTERPRISE     arubaSwitchJL321A
          DESCRIPTION    "An SNMP trap that is generated for an RMON event on a JL321A Aruba 2930M-48G Switch."
          ::= 2

   arubaSwitchJL320Atrap TRAP-TYPE
          ENTERPRISE     arubaSwitchJL320A
          DESCRIPTION    "An SNMP trap that is generated for an RMON event on a JL320A Aruba 2930M-24G-PoE+ Switch."
          ::= 2

   arubaSwitchJL322Atrap TRAP-TYPE
          ENTERPRISE     arubaSwitchJL322A
          DESCRIPTION    "An SNMP trap that is generated for an RMON event on a JL322A Aruba 2930M-48G-PoE+ Switch."
          ::= 2

   arubaSwitchJL324Atrap TRAP-TYPE
          ENTERPRISE     arubaSwitchJL324A
          DESCRIPTION    "An SNMP trap that is generated for an RMON event on a JL324A Aruba 2930M-24SR-PoE+ Switch."
          ::= 2

   arubaSwitchJL323Atrap TRAP-TYPE
          ENTERPRISE     arubaSwitchJL323A
          DESCRIPTION    "An SNMP trap that is generated for an RMON event on a JL323A Aruba 2930M-40G-8SR-PoE+ Switch."
          ::= 2

   arubaSwitchR0M67Atrap TRAP-TYPE
          ENTERPRISE     arubaSwitchR0M67A
          DESCRIPTION    "An SNMP trap that is generated for an RMON event on a R0M67A Aruba 2930M-40G-8SR-PoE-Class6 Switch."
          ::= 2

   arubaSwitchR0M68Atrap TRAP-TYPE
          ENTERPRISE     arubaSwitchR0M68A
          DESCRIPTION    "An SNMP trap that is generated for an RMON event on a R0M68A Aruba 2930M-24SR-PoE-Class6 Switch."
          ::= 2

   arubaSwitchJL693Atrap TRAP-TYPE
          ENTERPRISE     arubaSwitchJL693A
          DESCRIPTION    "An SNMP trap that is generated for an RMON event on a JL693A Aruba 2930F-12G-PoE+-2G-2SFP+ Switch."
          ::= 2

   arubaSwitchJL258Atrap TRAP-TYPE
          ENTERPRISE     arubaSwitchJL258A
          DESCRIPTION    "An SNMP trap that is generated for an RMON event on a JL258A Aruba 2930F-8G-PoE+-2SFP+ Switch."
          ::= 2

   arubaSwitchJL253Atrap TRAP-TYPE
          ENTERPRISE     arubaSwitchJL253A
          DESCRIPTION    "An SNMP trap that is generated for an RMON event on a JL253A Aruba 2930F-24G-4SFP+ Switch."
          ::= 2

   arubaSwitchJL254Atrap TRAP-TYPE
          ENTERPRISE     arubaSwitchJL254A
          DESCRIPTION    "An SNMP trap that is generated for an RMON event on a JL254A Aruba 2930F-48G-4SFP+ Switch."
          ::= 2

   arubaSwitchJL255Atrap TRAP-TYPE
          ENTERPRISE     arubaSwitchJL255A
          DESCRIPTION    "An SNMP trap that is generated for an RMON event on a JL255A Aruba 2930F-24G-PoE+-4SFP+ Switch."
          ::= 2

   arubaSwitchJL256Atrap TRAP-TYPE
          ENTERPRISE     arubaSwitchJL256A
          DESCRIPTION    "An SNMP trap that is generated for an RMON event on a JL256A Aruba 2930F-48G-PoE+-4SFP+ Switch."
          ::= 2

   arubaSwitchJL259Atrap TRAP-TYPE
          ENTERPRISE     arubaSwitchJL259A
          DESCRIPTION    "An SNMP trap that is generated for an RMON event on a JL259A Aruba 2930F-24G-4SFP Switch."
          ::= 2

   arubaSwitchJL260Atrap TRAP-TYPE
          ENTERPRISE     arubaSwitchJL260A
          DESCRIPTION    "An SNMP trap that is generated for an RMON event on a JL260A Aruba 2930F-48G-4SFP Switch."
          ::= 2

   arubaSwitchJL261Atrap TRAP-TYPE
          ENTERPRISE     arubaSwitchJL261A
          DESCRIPTION    "An SNMP trap that is generated for an RMON event on a JL261A Aruba 2930F-24G-PoE+-4SFP Switch."
          ::= 2

   arubaSwitchJL262Atrap TRAP-TYPE
          ENTERPRISE     arubaSwitchJL262A
          DESCRIPTION    "An SNMP trap that is generated for an RMON event on a JL262A Aruba 2930F-48G-PoE+-4SFP Switch."
          ::= 2

   arubaSwitchJL558Atrap TRAP-TYPE
          ENTERPRISE     arubaSwitchJL558A
          DESCRIPTION    "An SNMP trap that is generated for an RMON event on a JL558A Aruba 2930F 48G 740W PoE+ 4SPF+ Switch."
          ::= 2

   arubaSwitchJL557Atrap TRAP-TYPE
          ENTERPRISE     arubaSwitchJL557A
          DESCRIPTION    "An SNMP trap that is generated for an RMON event on a JL557A Aruba 2930F 48G 740W PoE+ 4SPF Switch."
          ::= 2

     arubaSwitchJL692Atrap TRAP-TYPE
          ENTERPRISE     arubaSwitchJL692A
          DESCRIPTION    "An SNMP trap that is generated for an RMON event on a JL692A Aruba 2930F-8G-PoE+-2SFP+-TAA Switch."
          ::= 2

   arubaSwitchJL263Atrap TRAP-TYPE
          ENTERPRISE     arubaSwitchJL263A
          DESCRIPTION    "An SNMP trap that is generated for an RMON event on a JL263A Aruba 2930F-24G-PoE+-4SFP+-TAA Switch."
          ::= 2

   arubaSwitchJL264Atrap TRAP-TYPE
          ENTERPRISE     arubaSwitchJL264A
          DESCRIPTION    "An SNMP trap that is generated for an RMON event on a JL264A Aruba 2930F-48G-PoE+-4SFP+-TAA Switch."
          ::= 2

   arubaSwitchJL559Atrap TRAP-TYPE
          ENTERPRISE     arubaSwitchJL559A
          DESCRIPTION    "An SNMP trap that is generated for an RMON event on a JL559A Aruba 2930F 48G 740W PoE+ 4SPF+ TAA Switch."
          ::= 2

-- -------------
-- 3400 SWITCHES
-- -------------


   hpSwitchJ4905Atrap    TRAP-TYPE
          ENTERPRISE     hpSwitchJ4905A
          DESCRIPTION    "An SNMP trap that is generated for an RMON event on a J4905A 3400-24G Switch."
          ::= 2


   hpSwitchJ4906Atrap    TRAP-TYPE
          ENTERPRISE     hpSwitchJ4906A
          DESCRIPTION    "An SNMP trap that is generated for an RMON event on a J4906A 3400-48G Switch."
          ::= 2



-- -------------
-- 3500 SWITCHES
-- -------------


   hpSwitchJ8692Atrap    TRAP-TYPE
          ENTERPRISE     hpSwitchJ8692A
          DESCRIPTION    "An SNMP trap that is generated for an RMON event on a J8692A 3500-24G-PoE Switch."
          ::= 2


   hpSwitchJ8693Atrap    TRAP-TYPE
          ENTERPRISE     hpSwitchJ8693A
          DESCRIPTION    "An SNMP trap that is generated for an RMON event on a J8693A 3500-48G-PoE Switch."
          ::= 2


   hpSwitchJ9310Atrap    TRAP-TYPE
          ENTERPRISE     hpSwitchJ9310A
          DESCRIPTION    "An SNMP trap that is generated for an RMON event on a J9310A 3500-24G-PoE+ Switch."
          ::= 2


   hpSwitchJ9311Atrap    TRAP-TYPE
          ENTERPRISE     hpSwitchJ9311A
          DESCRIPTION    "An SNMP trap that is generated for an RMON event on a J9311A 3500-48G-PoE+ Switch."
          ::= 2


   hpSwitchJ9470Atrap    TRAP-TYPE
          ENTERPRISE     hpSwitchJ9470A
          DESCRIPTION    "An SNMP trap that is generated for an RMON event on a J9470A 3500-24 Switch."
          ::= 2


   hpSwitchJ9471Atrap    TRAP-TYPE
          ENTERPRISE     hpSwitchJ9471A
          DESCRIPTION    "An SNMP trap that is generated for an RMON event on a J9471A 3500-24-PoE Switch."
          ::= 2


   hpSwitchJ9472Atrap    TRAP-TYPE
          ENTERPRISE     hpSwitchJ9472A
          DESCRIPTION    "An SNMP trap that is generated for an RMON event on a J9472A 3500-48 Switch."
          ::= 2


   hpSwitchJ9473Atrap    TRAP-TYPE
          ENTERPRISE     hpSwitchJ9473A
          DESCRIPTION    "An SNMP trap that is generated for an RMON event on a J9473A 3500-48-PoE Switch."
          ::= 2


-- -------------
-- 3800 SWITCHES
-- -------------


   hpSwitchJ9573Atrap    TRAP-TYPE
          ENTERPRISE     hpSwitchJ9573
          DESCRIPTION    "An SNMP trap that is generated for an RMON event on a J9573A 3800-24G-PoE+-2SFP+ Switch."
          ::= 2


   hpSwitchJ9574Atrap    TRAP-TYPE
          ENTERPRISE     hpSwitchJ9574
          DESCRIPTION    "An SNMP trap that is generated for an RMON event on a J9574A 3800-48G-PoE+-4SFP+ Switch."
          ::= 2


   hpSwitchJ9575Atrap    TRAP-TYPE
          ENTERPRISE     hpSwitchJ9575
          DESCRIPTION    "An SNMP trap that is generated for an RMON event on a J9575A 3800-24G-2SFP+ Switch."
          ::= 2


   hpSwitchJ9576Atrap    TRAP-TYPE
          ENTERPRISE     hpSwitchJ9576
          DESCRIPTION    "An SNMP trap that is generated for an RMON event on a J9576A 3800-48G-4SFP+ Switch."
          ::= 2


   hpSwitchJ9584Atrap    TRAP-TYPE
          ENTERPRISE     hpSwitchJ9584
          DESCRIPTION    "An SNMP trap that is generated for an RMON event on a J9584A 3800-24SFP-2SFP+ Switch."
          ::= 2


   hpSwitchJ9585Atrap    TRAP-TYPE
          ENTERPRISE     hpSwitchJ9585
          DESCRIPTION    "An SNMP trap that is generated for an RMON event on a J9585A 3800-24G-2XG Switch."
          ::= 2


   hpSwitchJ9586Atrap    TRAP-TYPE
          ENTERPRISE     hpSwitchJ9586
          DESCRIPTION    "An SNMP trap that is generated for an RMON event on a J9586A 3800-48G-4XG Switch."
          ::= 2


   hpSwitchJ9587Atrap    TRAP-TYPE
          ENTERPRISE     hpSwitchJ9587
          DESCRIPTION    "An SNMP trap that is generated for an RMON event on a J9587A 3800-24G-PoE+-2XG Switch."
          ::= 2


   hpSwitchJ9588Atrap    TRAP-TYPE
          ENTERPRISE     hpSwitchJ9588
          DESCRIPTION    "An SNMP trap that is generated for an RMON event on a J9588A 3800-48G-PoE+-4XG Switch."
          ::= 2


   hpStacktrap           TRAP-TYPE
          ENTERPRISE     hpStack
          DESCRIPTION    "An SNMP trap that is generated for an RMON event on a stack of 3800 Switches."
          ::= 2	


   hpStackVSF5400Rtrap   TRAP-TYPE
          ENTERPRISE     hpStackVSF5400R
          DESCRIPTION    "An SNMP trap that is generated for an RMON event on a VSF stack of 5400R Switches."
          ::= 2	

-- -------------
-- 3810 SWITCHES
-- -------------


   arubaStack3810trap    TRAP-TYPE
          ENTERPRISE     arubaStack3810
          DESCRIPTION    "An SNMP trap that is generated for an RMON event on a stack of Aruba 3810 Switches."
          ::= 2	

   arubaJL071Atrap       TRAP-TYPE
          ENTERPRISE     arubaJL071A
          DESCRIPTION    "An SNMP trap that is generated for an RMON event on a JL071A Aruba 3810M 24G 1-slot Switch."
          ::= 2

   arubaJL072Atrap       TRAP-TYPE
          ENTERPRISE     arubaJL072A
          DESCRIPTION    "An SNMP trap that is generated for an RMON event on a JL072A Aruba 3810M 48G 1-slot Switch."
          ::= 2

   arubaJL073Atrap       TRAP-TYPE
          ENTERPRISE     arubaJL073A
          DESCRIPTION    "An SNMP trap that is generated for an RMON event on a JL073A Aruba 3810M 24G PoE+ 1-slot Switch."
          ::= 2

   arubaJL074Atrap       TRAP-TYPE
          ENTERPRISE     arubaJL074A
          DESCRIPTION    "An SNMP trap that is generated for an RMON event on a JL074A Aruba 3810M 48G PoE+ 1-slot Switch."
          ::= 2

   arubaJL075Atrap       TRAP-TYPE
          ENTERPRISE     arubaJL075A
          DESCRIPTION    "An SNMP trap that is generated for an RMON event on a JL075A Aruba 3810M 16SFP+ 2-slot Switch."
          ::= 2

   arubaJL076Atrap       TRAP-TYPE
          ENTERPRISE     arubaJL076A
          DESCRIPTION    "An SNMP trap that is generated for an RMON event on a JL076A Aruba 3810M 40G 8 HPE Smart Rate PoE+ 1-slot Switch."
          ::= 2

   arubaJL077Atrap       TRAP-TYPE
          ENTERPRISE     arubaJL077A
          DESCRIPTION    "An SNMP trap that is generated for an RMON event on a JL077A Aruba 3810M 16 HPE Smart Rate PoE+ 2-slot Switch."
          ::= 2


-- -------------
-- 4000 SWITCHES
-- -------------


   hpSwitchJ4121Atrap    TRAP-TYPE
          ENTERPRISE     hpSwitch4000
          DESCRIPTION    "An SNMP trap that is generated for an RMON event on a J4121A 4000M Switch."
          ::= 2


-- -------------
-- 4100 SWITCHES
-- -------------


   hpSwitchJ4865Atrap    TRAP-TYPE
          ENTERPRISE     hpSwitchJ4865A
          DESCRIPTION    "An SNMP trap that is generated for an RMON event on a J4865A 4108GL Switch."
          ::= 2


   hpSwitchJ4887Atrap    TRAP-TYPE
          ENTERPRISE     hpSwitchJ4887A
          DESCRIPTION    "An SNMP trap that is generated for an RMON event on a J4887A 4104GL Switch."
          ::= 2



-- -------------
-- 4200 SWITCHES
-- -------------


--   hpSwitchJ8770Atrap    TRAP-TYPE
--          ENTERPRISE     hpSwitchJ8770A
--          DESCRIPTION    "An SNMP trap that is generated for an RMON event on a J8770A 4204VL Switch."
--          ::= 2


--   hpSwitchJ8771Atrap    TRAP-TYPE
--          ENTERPRISE     hpSwitchJ8771A
--          DESCRIPTION    "An SNMP trap that is generated for an RMON event on a J8771A 4202VL-48G Switch."
--          ::= 2


--   hpSwitchJ8772Atrap    TRAP-TYPE
--          ENTERPRISE     hpSwitchJ8772A
--          DESCRIPTION    "An SNMP trap that is generated for an RMON event on a J8772A 4202VL-72 Switch."
--          ::= 2


--   hpSwitchJ8772Btrap    TRAP-TYPE
--          ENTERPRISE     hpSwitchJ8772B
--          DESCRIPTION    "An SNMP trap that is generated for an RMON event on a J8772B 4202VL-72 Switch."
--          ::= 2


--   hpSwitchJ8773Atrap    TRAP-TYPE
--          ENTERPRISE     hpSwitchJ8773A
--          DESCRIPTION    "An SNMP trap that is generated for an RMON event on a J8773A 4208VL Switch."
--
--          ::= 2



-- -------------
-- 5300 SWITCHES
-- -------------


   hpSwitchJ4819Atrap    TRAP-TYPE
          ENTERPRISE     hpSwitchJ4819A
          DESCRIPTION    "An SNMP trap that is generated for an RMON event on a J4819A 5308XL Switch."
          ::= 2


   hpSwitchJ4850Atrap    TRAP-TYPE
          ENTERPRISE     hpSwitchJ4850A
          DESCRIPTION    "An SNMP trap that is generated for an RMON event on a J4850A 5304XL Switch."
          ::= 2



-- -------------
-- 5400 SWITCHES
-- -------------


   hpSwitchJ8697Atrap    TRAP-TYPE
          ENTERPRISE     hpSwitchJ8697A
          DESCRIPTION    "An SNMP trap that is generated for an RMON event on a J8797A 5406 ZL Switch."
          ::= 2


   hpSwitchJ8698Atrap    TRAP-TYPE
          ENTERPRISE     hpSwitchJ8698A
          DESCRIPTION    "An SNMP trap that is generated for an RMON event on a J8798A 5412 ZL Switch."
          ::= 2


   hpSwitchJ9850Atrap    TRAP-TYPE
          ENTERPRISE     hpSwitchJ9850A
          DESCRIPTION    "An SNMP trap that is generated for an RMON event on a J9850A 5406R ZL Switch."
          ::= 2


   hpSwitchJ9851Atrap    TRAP-TYPE
          ENTERPRISE     hpSwitchJ9851A
          DESCRIPTION    "An SNMP trap that is generated for an RMON event on a J9851A 5412R ZL Switch."
          ::= 2


-- -------------
-- 6100 SWITCHES
-- -------------


   hpSwitchJ4902Atrap    TRAP-TYPE
          ENTERPRISE     hpSwitchJ4902A
          DESCRIPTION    "An SNMP trap that is generated for an RMON event on a J4902A 6108 Switch."
          ::= 2


   hpSwitch516733-B21trap   TRAP-TYPE
          ENTERPRISE        hpSwitch516733-B21
          DESCRIPTION       "An SNMP trap that is generated for an RMON event on a 516733-B21 HP 6120-XG Switch."
          ::= 2


   hpSwitch498358-B21trap   TRAP-TYPE
          ENTERPRISE        hpSwitch498358-B21
          DESCRIPTION       "An SNMP trap that is generated for an RMON event on a 498358-B21 HP 6120-GXG Switch."
          ::= 2



-- -------------
-- 6200 SWITCHES
-- -------------


   hpSwitchJ8992Atrap    TRAP-TYPE
          ENTERPRISE     hpSwitchJ8992A
          DESCRIPTION    "An SNMP trap that is generated for an RMON event on a J8992A 6200-24G Switch."
          ::= 2



-- -------------
-- 6300 SWITCHES
-- -------------


   hpSwitch6308trap      TRAP-TYPE
          ENTERPRISE     hpSwitch6308
          DESCRIPTION    "An SNMP trap that is generated for an RMON event on a J4841A 6308M-SX Switch."
          ::= 2


-- -------------
-- 6400 SWITCHES
-- -------------


   hpSwitchJ8433Atrap    TRAP-TYPE
          ENTERPRISE     hpSwitchJ8433A
          DESCRIPTION    "An SNMP trap that is generated for an RMON event on a J8433A 6400-6XG Switch."
          ::= 2


   hpSwitchJ8474Atrap    TRAP-TYPE
          ENTERPRISE     hpSwitchJ8474A
          DESCRIPTION    "An SNMP trap that is generated for an RMON event on a J8474A 6410-6XG Switch."
          ::= 2



-- -------------
-- 6600 SWITCHES
-- -------------


   hpSwitchJ9263Atrap    TRAP-TYPE
          ENTERPRISE     hpSwitchJ9263A
          DESCRIPTION    "An SNMP trap that is generated for an RMON event on a J9263A 6600-24G Switch."
          ::= 2


   hpSwitchJ9264Atrap    TRAP-TYPE
          ENTERPRISE     hpSwitchJ9264A
          DESCRIPTION    "An SNMP trap that is generated for an RMON event on a J9264A 6600-24G-4XG Switch."
          ::= 2


   hpSwitchJ9265Atrap    TRAP-TYPE
          ENTERPRISE     hpSwitchJ9265A
          DESCRIPTION    "An SNMP trap that is generated for an RMON event on a J9265A 6600-24XG Switch."
          ::= 2


   hpSwitchJ9451Atrap    TRAP-TYPE
          ENTERPRISE     hpSwitchJ9451A
          DESCRIPTION    "An SNMP trap that is generated for an RMON event on a J9451A 6600-48G Switch."
          ::= 2


   hpSwitchJ9452Atrap    TRAP-TYPE
          ENTERPRISE     hpSwitchJ9452A
          DESCRIPTION    "An SNMP trap that is generated for an RMON event on a J9452A 6600-48G-4XG Switch."
          ::= 2


-- -------------
-- 8000 SWITCHES
-- -------------


   hpSwitch8000trap      TRAP-TYPE
          ENTERPRISE     hpSwitch8000
          DESCRIPTION    "An SNMP trap that is generated for an RMON event on a J4110A 8000M Switch."
          ::= 2


-- -------------
-- 8100 SWITCHES
-- -------------


--   hpSwitchJ8727Atrap    TRAP-TYPE
--          ENTERPRISE     hpSwitchJ8727A
--          DESCRIPTION    "An SNMP trap that is generated for an RMON event on a J8727A 8108FL Switch."
--          ::= 2


--   hpSwitchJ8728Atrap    TRAP-TYPE
--          ENTERPRISE     hpSwitchJ8728A
--          DESCRIPTION    "An SNMP trap that is generated for an RMON event on a J8728A 8116FL Switch."
--          ::= 2



-- -------------
-- 8200 SWITCHES
-- -------------


   hpSwitchJ9477Atrap    TRAP-TYPE
          ENTERPRISE     hpSwitchJ9477A
          DESCRIPTION    "An SNMP trap that is generated for an RMON event on a J9477A 8206ZL Switch."
          ::= 2


   hpSwitchJ9091Atrap    TRAP-TYPE
          ENTERPRISE     hpSwitchJ9091A
          DESCRIPTION    "An SNMP trap that is generated for an RMON event on a J9091A 8212ZL Switch."
          ::= 2



-- --------------
-- 9300M SWITCHES
-- --------------


   hpSwitchJ9304trap     TRAP-TYPE
          ENTERPRISE     hpSwitch9304
          DESCRIPTION    "An SNMP trap that is generated for an RMON event on a J4139A 9304M Switch."
          ::= 2


   hpSwitchJ9308trap     TRAP-TYPE
          ENTERPRISE     hpSwitch9308
          DESCRIPTION    "An SNMP trap that is generated for an RMON event on a J4138A 9308M Switch."
          ::= 2


   hpSwitchJ4874Atrap    TRAP-TYPE
          ENTERPRISE     hpSwitchJ4874A
          DESCRIPTION    "An SNMP trap that is generated for an RMON event on a J4874A 9315M Switch."
          ::= 2


-- -------------
-- 9400 SWITCHES
-- -------------



   hpSwitchJ8680Atrap    TRAP-TYPE
          ENTERPRISE     hpSwitchJ8680A
          DESCRIPTION    "An SNMP trap that is generated for an RMON event on a J8680A 9408SL Switch."
          ::= 2


-- ---------------------
-- ADVANCESTACK PRODUCTS
-- ---------------------


-- 208T & 224T

   hpAdvSwitch200trap    TRAP-TYPE
        ENTERPRISE       hpAdvSwitch200
        DESCRIPTION      "An SNMP trap that is generated for an RMON event on a J3175A Advancestack 208T or
                         J3177A Advancestack 224T Switch."
        ::= 2


-- Switch 212M and 224M


   hpSwitch212Mtrap      TRAP-TYPE
        ENTERPRISE       hpSwitch212M
        DESCRIPTION      "An SNMP trap that is generated for an RMON event on a J3298A 212M Switch."
        ::= 2


   hpSwitch224Mtrap      TRAP-TYPE
        ENTERPRISE       hpSwitch224M
        DESCRIPTION      "An SNMP trap that is generated for an RMON event on a J3299A 224M Switch."
        ::= 2



-- Switch 2000

   hpAdvSwitch2000trap   TRAP-TYPE
        ENTERPRISE       hpAdvSwitch2000
        DESCRIPTION      "An SNMP trap that is generated for an RMON event on a J3100A AdvanceStack 2000 Switch."
        ::= 2


   hpAdvSwitch2000Btrap  TRAP-TYPE
        ENTERPRISE       hpAdvSwitch2000B
        DESCRIPTION      "An SNMP trap that is generated for an RMON event on a J3100B AdvanceStack 2000 Switch."
        ::= 2


-- 800T

   hpAdvSwitch800Ttrap   TRAP-TYPE
        ENTERPRISE       hpAdvSwitch800T
        DESCRIPTION      "An SNMP trap that is generated for an RMON event on a J3245A AdvanceStack Switch 800T."
        ::= 2


-- 10:10 LAN Bridge


   bridge1010trap        TRAP-TYPE
        ENTERPRISE       bridge1010
        DESCRIPTION      "An SNMP trap that is generated for an RMON event on a 28673A Bridge 10:10."
        ::= 2


-- Remote Bridge


   bridgeRemotetrap      TRAP-TYPE
        ENTERPRISE       bridgeRemote
        DESCRIPTION      "An SNMP trap that is generated for an RMON event on a 28674A or 28674B Remote Bridge."
        ::= 2


-- eswitch


   eswitchtrap           TRAP-TYPE
        ENTERPRISE       eswitch
        DESCRIPTION      "An SNMP trap that is generated for an RMON event on a J2418A EtherTwist LAN Switch."
        ::= 2


   eswitch2trap          TRAP-TYPE
        ENTERPRISE       eswitch2

        DESCRIPTION      "An SNMP trap that is generated for an RMON event on a J2980A AdvanceStack LAN Switch-16."
        ::= 2


-- netswitch


   netSwitch100trap      TRAP-TYPE
        ENTERPRISE       netSwitch100
        DESCRIPTION      "An SNMP trap that is generated for an RMON event on a J3126A AdvanceStack Switch 100."
        ::= 2


   netSwitch200trap      TRAP-TYPE
        ENTERPRISE       netSwitch200
        DESCRIPTION      "An SNMP trap that is generated for an RMON event on a J3125A AdvanceStack Switch 200."
        ::= 2


-- AdvanceStack Routers 200, 400, 600	


   icfRouterERtrap       TRAP-TYPE
        ENTERPRISE       icfRouterER
        DESCRIPTION      "An SNMP trap that is generated for an RMON event on a 27285A AdvanceStack Router 440."
        ::= 2


   icfRouterTRtrap       TRAP-TYPE
        ENTERPRISE       icfRouterTR
        DESCRIPTION      "An SNMP trap that is generated for an RMON event on a 27286A AdvanceStack Router 445."
        ::= 2


   icfRouterSRtrap       TRAP-TYPE
        ENTERPRISE       icfRouterSR
        DESCRIPTION      "An SNMP trap that is generated for an RMON event on a 27288A AdvanceStack Router 430."
        ::= 2


   icfRouterFRtrap       TRAP-TYPE
        ENTERPRISE       icfRouterFR
        DESCRIPTION      "An SNMP trap that is generated for an RMON event on a 27289A AdvanceStack Router 240."
        ::= 2


   icfRouterLRtrap       TRAP-TYPE
        ENTERPRISE       icfRouterLR
        DESCRIPTION      "An SNMP trap that is generated for an RMON event on a 27287A AdvanceStack Router 470."
        ::= 2 


   icfRouterBRtrap       TRAP-TYPE
        ENTERPRISE       icfRouterBR
        DESCRIPTION      "An SNMP trap that is generated for an RMON event on a 27290A AdvanceStack Router 480."
        ::= 2 


   icfRouterPRtrap       TRAP-TYPE
        ENTERPRISE       icfRouterPR
        DESCRIPTION      "An SNMP trap that is generated for an RMON event on a J2540A AdvanceStack Router PR."
        ::=  2




   icfRouter650trap      TRAP-TYPE
        ENTERPRISE       icfRouter650
        DESCRIPTION      "An SNMP trap that is generated for an RMON event on a J2430A AdvanceStack Router 650."
        ::=  2  


   icfRouter230trap      TRAP-TYPE
        ENTERPRISE       icfRouter230
        DESCRIPTION      "An SNMP trap that is generated for an RMON event on a J2540B AdvanceStack Router 230."
        ::=  2


   icfRouter250trap      TRAP-TYPE
        ENTERPRISE       icfRouter250
        DESCRIPTION      "An SNMP trap that is generated for an RMON event on a 27289B AdvanceStack Router 250."
        ::=  2

   icfRouter255trap      TRAP-TYPE
        ENTERPRISE       icfRouter255
        DESCRIPTION      "An SNMP trap that is generated for an RMON event on a J2543A AdvanceStack Router 255."
        ::=  2


   icfRouter210trap      TRAP-TYPE
        ENTERPRISE       icfRouter210
        DESCRIPTION      "An SNMP trap that is generated for an RMON event on a J2628A AdvanceStack Router 150."
        ::=  2 


-- Managable hubs


   fiberOptictrap        TRAP-TYPE
        ENTERPRISE       fiberOptic
        DESCRIPTION      "An SNMP trap that is generated for an RMON event on a 28682A Fiber-Optic Hub Plus."
        ::=  2 


   advStack12trap        TRAP-TYPE
        ENTERPRISE       advStack12
        DESCRIPTION      "An SNMP trap that is generated for an RMON event on a J2600A AdvanceStack 10Base-T Hub-12."
        ::=  2 


   advStack24trap        TRAP-TYPE
        ENTERPRISE       advStack24
        DESCRIPTION      "An SNMP trap that is generated for an RMON event on a J2601A or J2601B AdvanceStack 10Base-T Hub-24."
        ::=  2  


   advStack48trap        TRAP-TYPE
        ENTERPRISE       advStack48
        DESCRIPTION      "An SNMP trap that is generated for an RMON event on a J2602A or J2602B AdvanceStack 10Base-T Hub-48."
        ::=  2 




   advStackU8trap        TRAP-TYPE
        ENTERPRISE       advStackU8
        DESCRIPTION      "An SNMP trap that is generated for an RMON event on a J2610A AdvanceStack 10Base-T Hub-8U."
        ::=  2  


   advStackU16trap       TRAP-TYPE
        ENTERPRISE       advStackU16
        DESCRIPTION      "An SNMP trap that is generated for an RMON event on a J2611A AdvanceStack 10Base-T Hub-16U."
        ::=  2 


   hpAdvStkEnetSH12Rtrap TRAP-TYPE
        ENTERPRISE       hpAdvStkEnetSH12R
        DESCRIPTION      "An SNMP trap that is generated for an RMON event on a J3200A AdvanceStack 10BT Switching Hub-12R."
        ::=  2  


   hpAdvStkEnetSH24Rtrap TRAP-TYPE
        ENTERPRISE       hpAdvStkEnetSH24R
        DESCRIPTION      "An SNMP trap that is generated for an RMON event on a J3202A AdvanceStack 10BT Switching Hub-24R."
        ::=  2  


   hpAdvStkEnetSH24Ttrap TRAP-TYPE
        ENTERPRISE       hpAdvStkEnetSH24T
        DESCRIPTION      "An SNMP trap that is generated for an RMON event on a J3204A AdvanceStack 10BT Switching Hub-24T."
        ::=  2 


   hpAdvStk100Tx12TMtrap TRAP-TYPE
        ENTERPRISE       hpAdvStk100Tx12TM
        DESCRIPTION      "An SNMP trap that is generated for an RMON event on a J3233A AdvanceStack 100B-TX Hub-12TM."
        ::=  2  




   hp10BaseTHub12Mtrap   TRAP-TYPE
        ENTERPRISE       hp10BaseTHub12M
        DESCRIPTION      "An SNMP trap that is generated for an RMON event on a J3301A 10Base-T Hub-12M."
        ::=  2


   hp10BaseTHub24Mtrap   TRAP-TYPE
        ENTERPRISE       hp10BaseTHub24M

        DESCRIPTION      "An SNMP trap that is generated for an RMON event on a J3303A 10Base-T Hub-24M."
        ::=  2 


   hpProCurve10T100THub12Mtrap   TRAP-TYPE
        ENTERPRISE               hpProCurve10T100THub12M

        DESCRIPTION              "An SNMP trap that is generated for an RMON event on a J3288A 100Base-T Hub 12M."
        ::=  2


   hpProCurve10T100THub24Mtrap   TRAP-TYPE
        ENTERPRISE               hpProCurve10T100THub24M
        DESCRIPTION              "An SNMP trap that is generated for an RMON event on a J3289A 100Base-T Hub 24M."
        ::=  2


   hpAdvStkEnetSHStacktrap   TRAP-TYPE
        ENTERPRISE           hpAdvStkEnetSHStack
        DESCRIPTION          "An SNMP trap that is generated for an RMON event on stack of AdvanceStack 10Base-T Switching Hubs."
        ::=  2  

END

HPE-SWPACKAGEVERSION-MIB DEFINITIONS ::= BEGIN

-- Title:                HPE ROS
--                       Private MIR MIB
-- Version:              7.46
-- Date:                 15-Jan-2007

IMPORTS
    nm                                           FROM HPE-MIB
    OBJECT-TYPE, MODULE-IDENTITY                  FROM SNMPv2-SMI
    DisplayString                                 FROM SNMPv2-TC;

rlSwPackageVersion MODULE-IDENTITY
                LAST-UPDATED "200701020000Z"
                ORGANIZATION "HPE"
                CONTACT-INFO
					"HPE"
                DESCRIPTION
                      "This private MIB module defines SW package version private MIBs."
                REVISION "200701020000Z"
                DESCRIPTION
                      "Initial revision."
        ::= { nm 67 }

rlSwPackageVersionTable OBJECT-TYPE
    SYNTAX  SEQUENCE OF RlSwPackageVersionEntry
    MAX-ACCESS  not-accessible
    STATUS  current
    DESCRIPTION
        "The table listing the current versions of packages
         that are included in the running software."
    ::= { rlSwPackageVersion 1 }

rlSwPackageVersionEntry OBJECT-TYPE
    SYNTAX  RlSwPackageVersionEntry
    MAX-ACCESS  not-accessible
    STATUS  current
    DESCRIPTION
        "The row definition for this table."
    INDEX {IMPLIED rlSwPackageVersionName }
    ::= { rlSwPackageVersionTable 1 }

RlSwPackageVersionEntry ::= SEQUENCE {
    rlSwPackageVersionName        DisplayString,
    rlSwPackageVersionVesrion     DisplayString
}

rlSwPackageVersionName OBJECT-TYPE
    SYNTAX  DisplayString (SIZE (1..20))
    MAX-ACCESS  read-only
    STATUS  current
    DESCRIPTION
        "The Package name."
    ::=  { rlSwPackageVersionEntry 1 }

rlSwPackageVersionVesrion OBJECT-TYPE
    SYNTAX  DisplayString (SIZE (1..20))
    MAX-ACCESS  read-only
    STATUS  current
    DESCRIPTION
        "The Package version."
    ::=  { rlSwPackageVersionEntry 2 }

END

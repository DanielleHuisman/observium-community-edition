HPNSATRAP-MIB DEFINITIONS ::= BEGIN

	IMPORTS
	 enterprises    FROM RFC1155-SMI
	 TRAP-TYPE      FROM RFC-1215;

--
    hp                          OBJECT IDENTIFIER ::= { enterprises 11 }
    adaptec                     OBJECT IDENTIFIER ::= { enterprises 795 }
    nm                          OBJECT IDENTIFIER ::= { hp 2 }
    hpnsa                       OBJECT IDENTIFIER ::= { nm 23 }  
    hpnsaECC        OBJECT IDENTIFIER ::= { hpnsa 6 }  
    hpnsaRemoteAssist                     OBJECT IDENTIFIER ::= { hpnsa 8 }
    adaptecNm           OBJECT IDENTIFIER ::= { adaptec 4 }
    adaptecNmScsiStatus         OBJECT IDENTIFIER ::= { adaptecNm 1 }   
    hpnr OBJECT IDENTIFIER ::= { enterprises 16 }
    hpNetRAID OBJECT IDENTIFIER ::= { hpnr 1 } 
    hpNetRaidMib OBJECT IDENTIFIER ::= { hpNetRAID 1 }
    raidTraps OBJECT IDENTIFIER ::= { hpNetRaidMib 200 }

-- 
-- Alarm Object (NSA Subobject) : System HW
--
--
hpnsaPostError TRAP-TYPE
  ENTERPRISE  hpnsa
       DESCRIPTION
	     "Post Error has occurred."
      --#TYPE         "POST error"
    --#SUMMARY      "%s"
    --#ARGUMENTS    {1}
     --#SEVERITY     MINOR
   --#TIMEINDEX    100
     --#HELP         "nsa.hlp"
       --#HELPTAG      2038
    --#STATE        OPERATIONAL

     -- FIXED STRING  : NOT PRESENT
  -- CUSTOM STRING : PRESENT 
     -- SEVERITY      : WARNING

      ::= 4356


hpnsaParityError TRAP-TYPE
      ENTERPRISE hpnsa
	DESCRIPTION 
	    "Parity error has been detected in parity memory"
       --#TYPE         "Parity error"
  --#SUMMARY      "%s"
    --#ARGUMENTS    {1}
     --#SEVERITY     MAJOR
   --#TIMEINDEX    100
     --#HELP         "nsa.hlp"
       --#HELPTAG      2042
    --#STATE        OPERATIONAL
	     
	-- FIXED STRING  : NOT PRESENT
  -- CUSTOM STRING : PRESENT 
     -- SEVERITY      : MAJOR

	::= 20528

hpnsaBusTimeoutError  TRAP-TYPE
	ENTERPRISE hpnsa
	DESCRIPTION 
	    "One of the bus masters caused a bus timeout"
   
	--#TYPE         "Bus timeout"
   --#SUMMARY      "%s"
    --#ARGUMENTS    {1}
     --#SEVERITY     MAJOR                  
 --#TIMEINDEX    100
     --#HELP         "nsa.hlp"
       --#HELPTAG      2044
    --#STATE        OPERATIONAL

     -- FIXED STRING  : NOT PRESENT
  -- CUSTOM STRING : PRESENT 
     -- SEVERITY      : MAJOR

	::= 20544


hpnsaIOChannelCheck TRAP-TYPE
  ENTERPRISE hpnsa
	DESCRIPTION 
	    "I/0 channel check activated by device in EISA slot caused an error"
    
	--#TYPE         "I/O channel check"
     --#SUMMARY      "%s"
    --#ARGUMENTS    {1}
     --#SEVERITY     MAJOR
   --#TIMEINDEX    100
     --#HELP         "nsa.hlp"
       --#HELPTAG      2045
    --#STATE        OPERATIONAL
	     

	-- FIXED STRING  : NOT PRESENT
  -- CUSTOM STRING : PRESENT 
     -- SEVERITY      : MAJOR

	::= 20560
       

hpnsaSoftwareNMI TRAP-TYPE
      ENTERPRISE hpnsa
	DESCRIPTION 
	    "Software NMI has been generated"
	       
	--#TYPE         "Software NMI"
  --#SUMMARY      "%s"
    --#ARGUMENTS    {1}
     --#SEVERITY     MAJOR
   --#TIMEINDEX    100
     --#HELP         "nsa.hlp"
       --#HELPTAG      2046
    --#STATE        OPERATIONAL


     -- FIXED STRING  : NOT PRESENT
  -- CUSTOM STRING : PRESENT 
     -- SEVERITY      : MAJOR

	::= 20576


hpnsaPostMemoryResize TRAP-TYPE
	ENTERPRISE hpnsa
	DESCRIPTION 
	    "Memory size has been adjusted during the Power-On-Self-Test
	    during the last boot"
	   
	--#TYPE         "Memory resize"
 --#SUMMARY      "%s"
    --#ARGUMENTS    {1}
     --#SEVERITY     MINOR
   --#TIMEINDEX    100
     --#HELP         "nsa.hlp"
       --#HELPTAG      2058
    --#STATE        DEGRADED


	-- FIXED STRING  : NOT PRESENT
  -- CUSTOM STRING : PRESENT 
     -- SEVERITY      : WARNING

      ::= 20592


hpnsaPciParityError TRAP-TYPE
  ENTERPRISE hpnsa
	DESCRIPTION 
	    "Parity error has occurred on a transfer to/from a device on one
		of the PCI buses"
       
	--#TYPE         "PCI bus error"
 --#SUMMARY      "%s"
    --#ARGUMENTS    {1}
     --#SEVERITY     MAJOR
   --#TIMEINDEX    100
     --#HELP         "nsa.hlp"
       --#HELPTAG      2047
    --#STATE        OPERATIONAL
	     

	-- FIXED STRING  : NOT PRESENT
  -- CUSTOM STRING : PRESENT 
     -- SEVERITY      : MAJOR

	::= 20624


hpnsaPciSystemError TRAP-TYPE
  ENTERPRISE hpnsa
	DESCRIPTION 
	    "System error has occurred in the PCI subsystem"
	
	--#TYPE         "PCI system error"
      --#SUMMARY      "%s"
    --#ARGUMENTS    {1}
     --#SEVERITY     MAJOR
   --#TIMEINDEX    100
     --#HELP         "nsa.hlp"
       --#HELPTAG      2048
    --#STATE        OPERATIONAL
	     
	-- FIXED STRING  : NOT PRESENT
  -- CUSTOM STRING : PRESENT 
     -- SEVERITY      : MAJOR

	::= 20640


hpnsaCPUFailure TRAP-TYPE
      ENTERPRISE hpnsa
	DESCRIPTION 
	    "One or more CPUs have failed. Detected by BIOS during POST"
	    
	--#TYPE         "CPU failure"
   --#SUMMARY      "%s"
    --#ARGUMENTS    {1}
     --#SEVERITY     CRITICAL
	--#TIMEINDEX    100
     --#HELP         "nsa.hlp"
       --#HELPTAG      2049
    --#STATE        OPERATIONAL


     -- FIXED STRING  : NOT PRESENT
  -- CUSTOM STRING : PRESENT 
     -- SEVERITY      : CRITICAL

     ::= 20656


hpnsaFailsafeTimeout TRAP-TYPE
 ENTERPRISE hpnsa
	DESCRIPTION 
	    "Timeout of failsafe timer has occurred"
	
	--#TYPE         "Failsafe timer timeout"
	--#SUMMARY      "%s"
    --#ARGUMENTS    {1}
     --#SEVERITY     MAJOR
   --#TIMEINDEX    100
     --#HELP         "nsa.hlp"
       --#HELPTAG      2050
    --#STATE        OPERATIONAL
	     
	-- FIXED STRING  : NOT PRESENT
  -- CUSTOM STRING : PRESENT 
     -- SEVERITY      : MAJOR

	::= 20672


hpnsaErrorLoggingDisabled  TRAP-TYPE
   ENTERPRISE hpnsa
	DESCRIPTION 
	    "Error logging for a specific error has been disabled due to too many
	   errors of that kind in a short time period"
	     
	--#TYPE         "Too many errors of this type"
  --#SUMMARY      "%s"
    --#ARGUMENTS    {1}
     --#SEVERITY     INFORMATIONAL
   --#TIMEINDEX    100
     --#HELP         "nsa.hlp"
       --#HELPTAG      2052
    --#STATE        OPERATIONAL


     -- FIXED STRING  : NOT PRESENT
  -- CUSTOM STRING : PRESENT 
     -- SEVERITY      : INFORMATION

  ::= 20704

       
hpnsaSystemReconfig   TRAP-TYPE
 ENTERPRISE hpnsa
	DESCRIPTION 
	    "EISA Configuration Utility has altered system configuration"
	   
	--#TYPE         "System configuration altered"
  --#SUMMARY      "%s"
    --#ARGUMENTS    {1}
     --#SEVERITY     INFORMATIONAL
   --#TIMEINDEX    100
     --#HELP         "nsa.hlp"
       --#HELPTAG      2051
    --#STATE        OPERATIONAL

     -- FIXED STRING  : NOT PRESENT
  -- CUSTOM STRING : PRESENT 
     -- SEVERITY      : INFORMATION

  ::= 20800
       

hpnsaHotSwapPowerFailure TRAP-TYPE
      ENTERPRISE hpnsa
	DESCRIPTION 
	    "Power connection failure in one of the devices in the hot swap cage"
   
	--#TYPE         "Hot swap: Power failure"
       --#SUMMARY      "%s"
    --#ARGUMENTS    {1}
     --#SEVERITY     MAJOR
   --#TIMEINDEX    100
     --#HELP         "nsa.hlp"
       --#HELPTAG      2053
    --#STATE        DEGRADED
		
	-- FIXED STRING  : NOT PRESENT
  -- CUSTOM STRING : PRESENT 
     -- SEVERITY      : MAJOR

	::= 24453


hpnsaHotSwapDeviceRemoved TRAP-TYPE
    ENTERPRISE hpnsa
	DESCRIPTION 
	    "A device has been removed from the hot swap cage"
	      
	--#TYPE         "Hot swap: Device removed"
      --#SUMMARY      "%s"
    --#ARGUMENTS    {1}
     --#SEVERITY     MAJOR
   --#TIMEINDEX    100
     --#HELP         "nsa.hlp"
       --#HELPTAG      2054
    --#STATE        DEGRADED


	-- FIXED STRING  : NOT PRESENT
  -- CUSTOM STRING : PRESENT 
     -- SEVERITY      : MAJOR

	::= 24454


hpnsaHotSwapDeviceInserted TRAP-TYPE
   ENTERPRISE hpnsa
	DESCRIPTION 
	    "A device has been inserted into the hot swap cage"
	     
	--#TYPE         "Hot swap: Device inserted"
     --#SUMMARY      "%s"
    --#ARGUMENTS    {1}
     --#SEVERITY     INFORMATIONAL
   --#TIMEINDEX    100
     --#HELP         "nsa.hlp"
       --#HELPTAG      2055
    --#STATE        OPERATIONAL


     -- FIXED STRING  : NOT PRESENT
  -- CUSTOM STRING : PRESENT 
     -- SEVERITY      : INFORMATION

  ::= 24455


hpnsaSystemWarning TRAP-TYPE
   ENTERPRISE hpnsa
	DESCRIPTION 
	    "An event of warning severity has occurred in the system. For
	   example, chassis door has been opened"
	  
	--#TYPE         "System Warning limit exceeded"
 --#SUMMARY      "%s"
    --#ARGUMENTS    {1}
     --#SEVERITY     MINOR
   --#TIMEINDEX    100
     --#HELP         "nsa.hlp"
       --#HELPTAG      2065
    --#STATE        OPERATIONAL

     -- FIXED STRING  : NOT PRESENT
  -- CUSTOM STRING : PRESENT 
     -- SEVERITY      : WARNING

      ::= 20736
       

hpnsaSystemCritical TRAP-TYPE
   ENTERPRISE hpnsa
	DESCRIPTION 
	    "An event of critical severity has occurred in the system. For
	  example, both system fans have failed"
  
	--#TYPE         "System critical limit exceeded"
	--#SUMMARY      "%s"
    --#ARGUMENTS    {1}
     --#SEVERITY     CRITICAL
	--#TIMEINDEX    100
     --#HELP         "nsa.hlp"
       --#HELPTAG      2065
    --#STATE        OPERATIONAL
	     
	-- FIXED STRING  : NOT PRESENT
  -- CUSTOM STRING : PRESENT 
     -- SEVERITY      : CRITICAL

     ::= 20737

--
-- 
-- Alarm Object (NSA Subobject) : Storage Cap.
--
--
hpnsaStorageCapWarning TRAP-TYPE
	ENTERPRISE hpnsa
	DESCRIPTION 
	    "Volume Storage Capacity has exceeded the warning 
	       threshold level."
      --#TYPE         "Capacity warning level"
	--#SUMMARY      "%s"
    --#ARGUMENTS    {1}
     --#SEVERITY     MINOR
   --#TIMEINDEX    100
     --#HELP         "nsa.hlp"
       --#HELPTAG      2037
    --#STATE        OPERATIONAL
	     
	-- FIXED STRING  : NOT PRESENT
  -- CUSTOM STRING : PRESENT 
     -- SEVERITY      : WARNING

      ::= 4096


hpnsaStorageCapMinor TRAP-TYPE
  ENTERPRISE hpnsa
	DESCRIPTION 
	    "Volume Storage Capacity has exceeded the minor 
		 threshold level."
      
	--#TYPE         "Capacity minor level"
  --#SUMMARY      "%s"
    --#ARGUMENTS    {1}
     --#SEVERITY     MINOR
   --#TIMEINDEX    100
     --#HELP         "nsa.hlp"
       --#HELPTAG      2037
    --#STATE        OPERATIONAL
       
      -- FIXED STRING  : NOT PRESENT
  -- CUSTOM STRING : PRESENT 
     -- SEVERITY      : MINOR

	::= 4097


hpnsaStorageCapMajor TRAP-TYPE
  ENTERPRISE hpnsa
	DESCRIPTION 
	    "Volume Storage Capacity has exceeded the major 
		 threshold level."
      
	--#TYPE         "Capacity major level"
  --#SUMMARY      "%s"
    --#ARGUMENTS    {1}
     --#SEVERITY     MAJOR
   --#TIMEINDEX    100
     --#HELP         "nsa.hlp"
       --#HELPTAG      2037
    --#STATE        DEGRADED


	-- FIXED STRING  : NOT PRESENT
  -- CUSTOM STRING : PRESENT 
     -- SEVERITY      : MAJOR

	::= 4098


--
--
-- HP DA traps, Do they need to be a separate alarm object?
--
--

hpnsaDaCacheError TRAP-TYPE
  ENTERPRISE hpnsa
	DESCRIPTION
	     "HPDA Controller: Cache Error"
  
	--#TYPE "HPDA Controller: Cache Error"
  --#SUMMARY      "%s"
    --#ARGUMENTS    {1}
     --#SEVERITY     CRITICAL
	--#TIMEINDEX    100
     --#HELP "ovwhpda.hlp"
   --#HELPTAG      1
       --#STATE        DEGRADED

	::= 8609

hpnsaDaLogicalDriveTrap TRAP-TYPE
       ENTERPRISE hpnsa
	DESCRIPTION
	     "HPDA Logical Drive: Critical"

  --#TYPE                 "HPDA Logical Drive: Critical"
  --#SUMMARY      "%s"
    --#ARGUMENTS    {1}
     --#SEVERITY     MINOR
   --#TIMEINDEX    100
     --#HELP         "ovwhpda.hlp"
   --#HELPTAG      2
       --#STATE        OPERATIONAL

     ::= 8625

hpnsaDaLogicalDriveNotAvailable TRAP-TYPE
       ENTERPRISE hpnsa
	DESCRIPTION 
	    "HPDA Logical Drive Not Available"
      --#TYPE         "HPDA Logical Drive Not Available"
      --#SUMMARY      "%s"
    --#ARGUMENTS    {1}
     --#SEVERITY     CRITICAL
	--#TIMEINDEX    100
     --#HELP         "ovwhpda.hlp"
   --#HELPTAG      3
       --#STATE        DEGRADED
	
	::= 8626

hpnsaDaHotSpareFailure TRAP-TYPE
	ENTERPRISE hpnsa
	DESCRIPTION
	     "HPDA Hot Spare:Failed"
 --#TYPE         "HPDA Hot Spare Failed"
 --#SUMMARY      "%s"
    --#ARGUMENTS    {1}
     --#SEVERITY     MINOR
   --#TIMEINDEX    100
     --#HELP         "ovwhpda.hlp"
   --#HELPTAG      4
       --#STATE        OPERATIONAL
     
	::= 8641

hpnsaDaHotSpareSuccess TRAP-TYPE
	ENTERPRISE hpnsa
	DESCRIPTION
	     "HPDA Hot Spare Succeeded"
      --#TYPE                 "HPDA Hot Spare Succeeded"
      --#SUMMARY      "%s"
    --#ARGUMENTS    {1}
     --#SEVERITY     INFORMATIONAL
   --#TIMEINDEX    100
     --#HELP         "ovwhpda.hlp"
   --#HELPTAG      5
       --#STATE        OPERATIONAL

     ::= 8642

hpnsaDaHardDiskFailure TRAP-TYPE
	ENTERPRISE hpnsa
	DESCRIPTION
	     "HPDA Hard Disk Failed"

 --#TYPE         "HPDA Hard Disk Failed"
 --#SUMMARY      "%s"
    --#ARGUMENTS    {1}
     --#SEVERITY     MINOR
   --#TIMEINDEX    100
     --#HELP         "ovwhpda.hlp"
   --#HELPTAG      6
       --#STATE        OPERATIONAL

     ::= 8657

hpnsaDaParityThresholdTrap TRAP-TYPE
    ENTERPRISE hpnsa
	DESCRIPTION 
	    "HPDA Threshold Exceeded: Parity"
       --#TYPE         "HPDA Threshold Exceeded: Parity"
       --#SUMMARY      "%s"
    --#ARGUMENTS    {1}
     --#SEVERITY     MINOR
   --#TIMEINDEX    100
     --#HELP         "ovwhpda.hlp"
   --#HELPTAG      7
       --#STATE        OPERATIONAL

     ::= 8673

hpnsaDaSoftErrorThresholdTrap TRAP-TYPE
 ENTERPRISE hpnsa
	DESCRIPTION
	     "HPDA Threshold Exceeded: Soft Errors"
  --#TYPE                 "HPDA Threshold Exceeded: Soft Errors"
  --#SUMMARY      "%s"
    --#ARGUMENTS    {1}
     --#SEVERITY     MINOR
   --#TIMEINDEX    100
     --#HELP         "ovwhpda.hlp"
   --#HELPTAG      8
       --#STATE        OPERATIONAL

     ::= 8674

hpnsaDaHardwareThresholdTrap TRAP-TYPE 
 ENTERPRISE hpnsa
	DESCRIPTION
	     "HPDA Threshold Exceeded: Hardware Errors"
      --#TYPE         "HPDA Threshold Exceeded: Hardware Errors"
      --#SUMMARY      "%s"
    --#ARGUMENTS    {1}
     --#SEVERITY     MINOR
   --#TIMEINDEX    100
     --#HELP         "ovwhpda.hlp"
   --#HELPTAG      9
       --#STATE        OPERATIONAL

     ::= 8675


hpnsaDaMiscThresholdTrap TRAP-TYPE
      ENTERPRISE hpnsa
	DESCRIPTION
	     "HPDA Threshold Exceeded: Miscellaneous Errors"
 --#TYPE         "HPDA Threshold Exceeded: Miscellaneous Errors"
 --#SUMMARY      "%s"
    --#ARGUMENTS    {1}
     --#SEVERITY     MINOR
   --#TIMEINDEX    100
     --#HELP         "ovwhpda.hlp"
   --#HELPTAG      10
      --#STATE        OPERATIONAL

     ::= 8676

hpnsaDaControllerTrap TRAP-TYPE
 ENTERPRISE hpnsa
	DESCRIPTION
	     "HPDA Controller: NVRAM Age"
    --#TYPE         "HPDA Controller: NVRAM Age"
    --#SUMMARY      "%s"
    --#ARGUMENTS    {1}
     --#SEVERITY     INFORMATIONAL
   --#TIMEINDEX    100
     --#HELP         "ovwhpda.hlp"
   --#HELPTAG      11
      --#STATE        OPERATIONAL
     ::= 8677

--
-- 
-- Alarm Object (NSA Subobject) : SCSI Status
--
--
hpnsaScsiStatusCorruptedDB TRAP-TYPE
      ENTERPRISE adaptecNmScsiStatus
  DESCRIPTION 
	    "Device Database has been corrupted."
   
	--#TYPE         "Corrupt Devices File"
  --#SUMMARY      "%s"
    --#ARGUMENTS    {1}
     --#SEVERITY     MAJOR
   --#TIMEINDEX    100
     --#HELP         "scsiflt.hlp"
   --#HELPTAG      6
       --#STATE        OPERATIONAL
     
	-- FIXED STRING  : NOT PRESENT
  -- CUSTOM STRING : PRESENT
      -- SEVERITY      : MAJOR

	::= 8193


hpnsaScsiStatusUnloadedNLM TRAP-TYPE
    ENTERPRISE adaptecNmScsiStatus
  DESCRIPTION 
	    "SCSI Status agent was unloaded from a NetWare Server."
 
	--#TYPE         "SCSI fault agent unloaded"
     --#SUMMARY      "%s"
    --#ARGUMENTS    {1}
     --#SEVERITY     INFORMATIONAL
   --#TIMEINDEX    100
     --#HELP         "scsiflt.hlp"
   --#HELPTAG      7
       --#STATE        OPERATIONAL
     
	-- FIXED STRING  : NOT PRESENT
  -- CUSTOM STRING : PRESENT
      -- SEVERITY      : INFORMATION

  ::= 8194


hpnsaScsiStatusFailedHBA TRAP-TYPE
      ENTERPRISE adaptecNmScsiStatus
  DESCRIPTION 
	    "One of the SCSI HBAs can no longer be detected by the
	   SCSI Status agent."
    
	--#TYPE         "Host Adapter failed"
   --#SUMMARY      "%s"
    --#ARGUMENTS    {1}
     --#SEVERITY     CRITICAL
	--#TIMEINDEX    100
     --#HELP         "scsiflt.hlp"
   --#HELPTAG      9
       --#STATE        DEGRADED
	
	-- FIXED STRING  : NOT PRESENT
  -- CUSTOM STRING : PRESENT
      -- SEVERITY      : CRITICAL

     ::= 8196


hpnsaScsiStatusRecoveredHBA TRAP-TYPE
   ENTERPRISE adaptecNmScsiStatus
  DESCRIPTION 
	    "A Host Adapter which has failed, has become accessible 
		 again."
	
	--#TYPE         "Host Adapter recovered"
	--#SUMMARY      "%s"
    --#ARGUMENTS    {1}
     --#SEVERITY     INFORMATIONAL
   --#TIMEINDEX    100
     --#HELP         "scsiflt.hlp"
   --#HELPTAG      10
      --#STATE        OPERATIONAL

     -- FIXED STRING  : NOT PRESENT
  -- CUSTOM STRING : PRESENT
      -- SEVERITY      : NORMAL

       ::= 8197


hpnsaScsiStatusDiscoveredHBA TRAP-TYPE
  ENTERPRISE adaptecNmScsiStatus
  DESCRIPTION 
	    "A new SCSI Host Bus Adapter has been discovered or 
	     device database has been cleared."
     
	--#TYPE         "Host Adapter Discovered"
       --#SUMMARY      "%s"
    --#ARGUMENTS    {1}
     --#SEVERITY     INFORMATIONAL
   --#TIMEINDEX    100
     --#HELP         "scsiflt.hlp"
   --#HELPTAG      8
       --#STATE        OPERATIONAL
     
	-- FIXED STRING  : NOT PRESENT
  -- CUSTOM STRING : PRESENT
      -- SEVERITY      : INFORMATION

  ::= 8198


hpnsaScsiStatusDeviceFailed TRAP-TYPE
   ENTERPRISE adaptecNmScsiStatus
  DESCRIPTION 
	    "One of the SCSI devices installed on the server can
	     no longer be detected by the SCSI Status agent."
       
	--#TYPE         "Device Failed"
 --#SUMMARY      "%s"
    --#ARGUMENTS    {1}
     --#SEVERITY     CRITICAL
	--#TIMEINDEX    100
     --#HELP         "scsiflt.hlp"
   --#HELPTAG      14
      --#STATE        DEGRADED
	
	-- FIXED STRING  : NOT PRESENT
  -- CUSTOM STRING : PRESENT
      -- SEVERITY      : CRITICAL

     ::= 8199


hpnsaScsiStatusDeviceRecovered TRAP-TYPE
	ENTERPRISE adaptecNmScsiStatus
  DESCRIPTION 
	    "A SCSI device which has failed, has become accessible
	   again."
	
	--#TYPE         "Device recovered"
      --#SUMMARY      "%s"
    --#ARGUMENTS    {1}
     --#SEVERITY     INFORMATIONAL
   --#TIMEINDEX    100
     --#HELP         "scsiflt.hlp"
   --#HELPTAG      15
      --#STATE        OPERATIONAL
     
	-- FIXED STRING  : NOT PRESENT
  -- CUSTOM STRING : PRESENT
      -- SEVERITY      : NORMAL

       ::= 8200


hpnsaScsiStatusDeviceDiscovered TRAP-TYPE
       ENTERPRISE adaptecNmScsiStatus
  DESCRIPTION 
	    "A new SCSI device has been discovered."
	
	--#TYPE         "Device discovered"
     --#SUMMARY      "%s"
    --#ARGUMENTS    {1}
     --#SEVERITY     INFORMATIONAL
   --#TIMEINDEX    100
     --#HELP         "scsiflt.hlp"
   --#HELPTAG      13
      --#STATE        OPERATIONAL
     
	-- FIXED STRING  : NOT PRESENT
  -- CUSTOM STRING : PRESENT
      -- SEVERITY      : INFORMATION

  ::= 8201


hpnsaScsiStatusChangedHBA TRAP-TYPE
     ENTERPRISE adaptecNmScsiStatus
  DESCRIPTION 
	    "The SCSI Status agent detected that the Host Bus Adapter 
	       has been changed."
     
	--#TYPE         "Host Adapter changed"
  --#SUMMARY      "%s"
    --#ARGUMENTS    {1}
     --#SEVERITY     INFORMATIONAL                           
	--#TIMEINDEX    100
     --#HELP         "scsiflt.hlp"
   --#HELPTAG      11
      --#STATE        OPERATIONAL
     
	-- FIXED STRING  : NOT PRESENT
  -- CUSTOM STRING : PRESENT
      -- SEVERITY      : INFORMATION

  ::= 8205


hpnsaScsiStatusDeviceChanged TRAP-TYPE
  ENTERPRISE adaptecNmScsiStatus
  DESCRIPTION 
	    "The SCSI Status agent detected that a SCSI device installed on
	  the server has been changed."
  
	--#TYPE         "Device Changed"
	--#SUMMARY      "%s"
    --#ARGUMENTS    {1}
     --#SEVERITY     CRITICAL
	--#TIMEINDEX    100
     --#HELP         "scsiflt.hlp"
   --#HELPTAG      16
      --#STATE        OPERATIONAL
     
	-- FIXED STRING  : NOT PRESENT
  -- CUSTOM STRING : PRESENT
      -- SEVERITY      : INFORMATION

  ::= 8206


hpnsaScsiStatusTimeoutHBA TRAP-TYPE
     ENTERPRISE adaptecNmScsiStatus
  DESCRIPTION 
	    "The SCSI Status agent sent a request to an HBA and the request 
		 never completed."
      
	--#TYPE         "Host Adapter Timeout"
  --#SUMMARY      "%s"
    --#ARGUMENTS    {1}
     --#SEVERITY     CRITICAL
	--#TIMEINDEX    100
     --#HELP         "scsiflt.hlp"
   --#HELPTAG      12
      --#STATE        DEGRADED
	
	-- FIXED STRING  : NOT PRESENT
  -- CUSTOM STRING : PRESENT
      -- SEVERITY      : CRITICAL

     ::= 8208


hpnsaScsiStatusDeviceTimeout TRAP-TYPE
  ENTERPRISE adaptecNmScsiStatus
  DESCRIPTION 
	    "The SCSI Status agent sent a request to a SCSI device and the 
	  request never completed."
      
	--#TYPE         "Device timeout"
	--#SUMMARY      "%s"
    --#ARGUMENTS    {1}
     --#SEVERITY     CRITICAL
	--#TIMEINDEX    100
     --#HELP         "scsiflt.hlp"
   --#HELPTAG      17
      --#STATE        DEGRADED
	
	-- FIXED STRING  : NOT PRESENT
  -- CUSTOM STRING : PRESENT
      -- SEVERITY      : CRITICAL

     ::= 8209


--
-- 
-- Alarm Object (NSA Subobject) : HP Disk System
--
--
hpnsaDiskSysDefects TRAP-TYPE
  ENTERPRISE hpnsa
	DESCRIPTION 
	    "The Defect List Threshold has been exceeded."
  
	--#TYPE         "Exceeded Defect List Threshold"
	--#SUMMARY      "%s"
    --#ARGUMENTS    {1}
     --#SEVERITY     MINOR
   --#TIMEINDEX    100
     --#HELP         "ovwdiag.hlp"
   --#HELPTAG      1
       --#STATE        OPERATIONAL

     -- FIXED STRING  : Exceeded Defect List Threshold
       -- CUSTOM STRING : PRESENT
      -- SEVERITY      : WARNING

      ::= 8210



--
-- 
-- Alarm Object (NSA Subobject) : Network Card
--
--
hpnsaNicReceiveErrors TRAP-TYPE
  ENTERPRISE hpnsa
	DESCRIPTION
	     "The total number of packets with receive errors has 
	    exceeded the threshold."
       
	--#TYPE         "Received Errors exceeded threshold"
    --#SUMMARY      "%s"
    --#ARGUMENTS    {1}
     --#SEVERITY     MINOR
   --#TIMEINDEX    100
     --#HELP         "hpnsnic.hlp"
   --#HELPTAG      17
      --#STATE        OPERATIONAL
     
	-- FIXED STRING  : Received Errors exceeded threshold
   -- CUSTOM STRING : PRESENT
      -- SEVERITY      : MINOR

	::= 16385


hpnsaNicTransmitErrors TRAP-TYPE
       ENTERPRISE hpnsa
	DESCRIPTION
	     "The total number of packets with transmit errors has
	    exceeded the threshold."
       
	--#TYPE         "Transmit Error exceeded threshold"
     --#SUMMARY      "%s"
    --#ARGUMENTS    {1}
     --#SEVERITY     MINOR   
	--#TIMEINDEX    100
     --#HELP "hpnsnic.hlp"
   --#HELPTAG      23
      --#STATE        OPERATIONAL
     
	-- FIXED STRING  : Transmit Errors exceeded threshold
   -- CUSTOM STRING : PRESENT
      -- SEVERITY      : MINOR

	::= 16386


hpnsaNicAdapterReset TRAP-TYPE
 ENTERPRISE hpnsa
	DESCRIPTION
	     "The total number of LAN Adapter reset errors has
		exceeded the threshold."
       
	--#TYPE         "Adapter Reset Errors exceeded threshold"
       --#SUMMARY      "%s"
    --#ARGUMENTS    {1}
     --#SEVERITY     MAJOR
   --#TIMEINDEX    100
     --#HELP         "hpnsnic.hlp"
   --#HELPTAG      39
      --#STATE        OPERATIONAL
     
	-- FIXED STRING  : Adapter Reset Errors exceeded threshold
      -- CUSTOM STRING : PRESENT
      -- SEVERITY      : MAJOR

	::= 16387


hpnsaNicAlignmentErrors TRAP-TYPE
      ENTERPRISE hpnsa
	DESCRIPTION
	     "The total number of alignment and CRC errors has 
	       exceeded the threshold."
       
	--#TYPE         "Alignment Errors exceeded threshold"
   --#SUMMARY      "%s"
    --#ARGUMENTS    {1}
     --#SEVERITY     MINOR
   --#TIMEINDEX    100
     --#HELP         "hpnsnic.hlp"
   --#HELPTAG      18
      --#STATE        OPERATIONAL
     
	-- FIXED STRING  : Alignment Errors exceeded threshold
  -- CUSTOM STRING : PRESENT
      -- SEVERITY      : MARGINAL

     ::= 16388


hpnsaNicGiantFrameErrors TRAP-TYPE
     ENTERPRISE hpnsa
	DESCRIPTION
	     "The total number of giant frame packets has exceeded 
	  the threshold."
 
	--#TYPE         "Giant Frame Errors exceeded threshold"
 --#SUMMARY      "%s"
    --#ARGUMENTS    {1}
     --#SEVERITY     MINOR
   --#TIMEINDEX    100
     --#HELP         "hpnsnic.hlp"
   --#HELPTAG      19
      --#STATE        OPERATIONAL
     
	-- FIXED STRING  : GiantFrame Errors exceeded threshold
 -- CUSTOM STRING : PRESENT
      -- SEVERITY      : MARGINAL

     ::= 16389


hpnsaNicHardwareMismatch TRAP-TYPE
     ENTERPRISE hpnsa
	DESCRIPTION
	     "The total number of packets with length less than the 
	 required minimum length has exceeded the threshold."
    
	--#TYPE         "Hardware Mismatch Errors exceeded threshold"
   --#SUMMARY      "%s"
    --#ARGUMENTS    {1}
     --#SEVERITY     MINOR
   --#TIMEINDEX    100
     --#HELP         "hpnsnic.hlp"
   --#HELPTAG      20
      --#STATE        OPERATIONAL

     
	-- FIXED STRING  : Hardware Mismatch Errors exceeded threshold
  -- CUSTOM STRING : PRESENT
      -- SEVERITY      : MARGINAL

     ::= 16390


hpnsaNicLateCollision TRAP-TYPE
	ENTERPRISE hpnsa
	DESCRIPTION
	     "The total number of late collision errors has exceeded
	  the threshold (the network is too large)."
     
	--#TYPE         "Late Collision Errors exceeded threshold"
      --#SUMMARY      "%s"
    --#ARGUMENTS    {1}
     --#SEVERITY     MINOR
   --#TIMEINDEX    100
     --#HELP         "hpnsnic.hlp"
   --#HELPTAG      24
      --#STATE        OPERATIONAL
     
	-- FIXED STRING  : Late Collision Errors exceeded threshold
     -- CUSTOM STRING : PRESENT
      -- SEVERITY      : MARGINAL

     ::= 16391


hpnsaNicExcessiveCollision TRAP-TYPE
   ENTERPRISE hpnsa
	DESCRIPTION
	     "The total number of colliding packets has exceeded 
	     the threshold (the network is too busy)."
      
	--#TYPE         "Excessive Collision Errors exceeded threshold"
 --#SUMMARY      "%s"
    --#ARGUMENTS    {1}
     --#SEVERITY     MINOR
   --#TIMEINDEX    100
     --#HELP         "hpnsnic.hlp"
   --#HELPTAG      25
      --#STATE        OPERATIONAL
     
	-- FIXED STRING  : Excessive Collision Errors exceeded threshold
	-- CUSTOM STRING : PRESENT
      -- SEVERITY      : MARGINAL

     ::= 16392


hpnsaNicCarrierSenseError TRAP-TYPE
    ENTERPRISE hpnsa
	DESCRIPTION
	     "The total number of carrier sense errors has exceeded 
	 the threshold."
 
	--#TYPE         "Carrier Sense Errors exceeded threshold"
       --#SUMMARY      "%s"
    --#ARGUMENTS    {1}
     --#SEVERITY     MINOR
   --#TIMEINDEX    100
     --#HELP         "hpnsnic.hlp"
   --#HELPTAG      26
      --#STATE        OPERATIONAL
     
	-- FIXED STRING  : Carrier Sense Errors exceeded threshold
      -- CUSTOM STRING : PRESENT
      -- SEVERITY      : MARGINAL

     ::= 16393


hpnsaNicDeferralError TRAP-TYPE
	ENTERPRISE hpnsa
	DESCRIPTION
	     "The total number of adapter deferrals has exceeded the
	 threshold (the network is forever busy)."
       
	--#TYPE         "Deferral Errors exceeded threshold"
    --#SUMMARY      "%s"
    --#ARGUMENTS    {1}
     --#SEVERITY     MINOR
   --#TIMEINDEX    100
     --#HELP         "hpnsnic.hlp"
   --#HELPTAG      27
      --#STATE        OPERATIONAL
     
	-- FIXED STRING  : Deferral Errors exceeded threshold
   -- CUSTOM STRING : PRESENT
      -- SEVERITY      : MARGINAL

     ::= 16394


hpnsaNicNoECBError TRAP-TYPE
   ENTERPRISE hpnsa
	DESCRIPTION
	     "The total number of No ECB errors (LAN adapter is out of 
	      receive buffers) errors has exceeded the threshold."
    
	--#TYPE         "No ECB Errors exceeded threshold"
      --#SUMMARY      "%s"
    --#ARGUMENTS    {1}
     --#SEVERITY     MINOR
   --#TIMEINDEX    100
     --#HELP         "hpnsnic.hlp"
   --#HELPTAG      21
      --#STATE        OPERATIONAL
     
	-- FIXED STRING  : No ECB Errors exceeded threshold
     -- CUSTOM STRING : PRESENT
      -- SEVERITY      : MINOR

	::= 16395


hpnsaNicReceiveOverflow TRAP-TYPE
      ENTERPRISE hpnsa
	DESCRIPTION
	     "The total number of Receive Overflow errors has exceeded the 
	   threshold."
    
	--#TYPE         "Rx Overflow errors exceeded threshold"
 --#SUMMARY      "%s"
    --#ARGUMENTS    {1}
     --#SEVERITY     MAJOR                                       
    --#TIMEINDEX    100
     --#HELP         "hpnsnic.hlp"
   --#HELPTAG      22
      --#STATE        OPERATIONAL
     
	-- FIXED STRING  : Rx Overflow errors exceeded threshold
	-- CUSTOM STRING : PRESENT
      -- SEVERITY      : MAJOR

	::= 16396


hpnsaNicUtilCount TRAP-TYPE
    ENTERPRISE hpnsa
	DESCRIPTION
	     "LAN adapter utilization count has exceeded the threshold."
     
	--#TYPE         "Utilization count exceeded threshold"
  --#SUMMARY      "%s"
    --#ARGUMENTS    {1}
     --#SEVERITY     INFORMATIONAL
   --#TIMEINDEX    100
     --#HELP         "hpnsnic.hlp"
   --#HELPTAG      16
      --#STATE        OPERATIONAL

     
	-- FIXED STRING  : Utilization count exceeded threshold
 -- CUSTOM STRING : PRESENT
      -- SEVERITY      : INFORMATION

  ::= 16397


hpnsaNicAdapterMismatch TRAP-TYPE
      ENTERPRISE hpnsa
	DESCRIPTION
	     "The LAN adapter which the alarms were configured for, 
	  has been replaced by another type of LAN adapter."
     
	--#TYPE         "Adapter Mismatch"
      --#SUMMARY      "%s"
    --#ARGUMENTS    {1}
     --#SEVERITY     MINOR
   --#TIMEINDEX    100
     --#HELP         "hpnsnic.hlp"
   --#HELPTAG      40
      --#STATE        OPERATIONAL
     
	-- FIXED STRING  : Adapter Mismatch
     -- CUSTOM STRING : PRESENT
      -- SEVERITY      : MINOR

	::= 16398


hpnsaNicTxFIFOUnderrun TRAP-TYPE
       ENTERPRISE hpnsa
	DESCRIPTION
	     "There possibly is a dataflow problem with your HP LAN adapter."
	
	--#TYPE         "Adapter Tx FIFO Underrun errors"
       --#SUMMARY      "%s"
    --#ARGUMENTS    {1}
     --#SEVERITY     MINOR
   --#TIMEINDEX    100
     --#HELP         "hpnsnic.hlp"
   --#HELPTAG      28
      --#STATE        OPERATIONAL
     
	-- FIXED STRING  : Adapter Tx FIFO Underrun errors 
     -- CUSTOM STRING : PRESENT
      -- SEVERITY      : MINOR

	::= 16399


hpnsaNicTxTimeOut TRAP-TYPE
    ENTERPRISE hpnsa
	DESCRIPTION
	     "The HP LAN adapter driver did not receive a transmit complete 
	  interrupt."
    
	--#TYPE         "Adapter Tx Timed Out error"
    --#SUMMARY      "%s"
    --#ARGUMENTS    {1}
     --#SEVERITY     MINOR
   --#TIMEINDEX    100
     --#HELP         "hpnsnic.hlp"
   --#HELPTAG      29 
     --#STATE        OPERATIONAL
     
	-- FIXED STRING  : Adapter Tx Timed Out errors 
 -- CUSTOM STRING : PRESENT
      -- SEVERITY      : MINOR

	::= 16400


hpnsaNicRxFIFOOverrun TRAP-TYPE
	ENTERPRISE hpnsa
	DESCRIPTION
	     "There possibly is a dataflow problem with your HP LAN adapter."
	
	--#TYPE         "Adapter Rx FIFO Overrun errors"
	--#SUMMARY      "%s"
    --#ARGUMENTS    {1}
     --#SEVERITY     MINOR
   --#TIMEINDEX    100
     --#HELP         "hpnsnic.hlp"
   --#HELPTAG      30
      --#STATE        OPERATIONAL
     
	-- FIXED STRING  : Adapter Rx FIFO Overrun errors 
      -- CUSTOM STRING : PRESENT
      -- SEVERITY      : MINOR

	::= 16401


hpnsaNicRxFalseInterrupts TRAP-TYPE
    ENTERPRISE hpnsa
	DESCRIPTION
	     "There is a dataflow problem with your HP LAN adapter - receive 
		 interrupts are being generated, but no receive packets are being
		present."
      
	--#TYPE         "Adapter Rx False Interrupt errors"
     --#SUMMARY      "%s"
    --#ARGUMENTS    {1}
     --#SEVERITY     INFORMATIONAL
   --#TIMEINDEX    100
     --#HELP         "hpnsnic.hlp"
   --#HELPTAG      31
      --#STATE        OPERATIONAL
     
	-- FIXED STRING  : Adapter Rx False Interrupt errors 
   -- CUSTOM STRING : PRESENT
      -- SEVERITY      : INFORMATION

  ::= 16402


hpnsaNicPagingError TRAP-TYPE
  ENTERPRISE hpnsa
	DESCRIPTION
	     "There possibly is a problem with your HP LAN adapter - 
		 it generates too many buffer pointer errors."
  
	--#TYPE         "Adapter Rx Paging errors"
      --#SUMMARY      "%s"
    --#ARGUMENTS    {1}
     --#SEVERITY     MINOR
   --#TIMEINDEX    100
     --#HELP         "hpnsnic.hlp"
   --#HELPTAG      33
      --#STATE        OPERATIONAL
     
	-- FIXED STRING  : Adapter Rx Paging errors 
    -- CUSTOM STRING : PRESENT
      -- SEVERITY      : MINOR

	::= 16403


hpnsaNicTimedOutDMA TRAP-TYPE
  ENTERPRISE hpnsa
	DESCRIPTION
	     "There possibly is a problem with your HP LAN adapter - 
		 DMA timed out while transmitting or receiving a packet."
       
	--#TYPE         "Adapter DMA Timed Out errors"
  --#SUMMARY      "%s"
    --#ARGUMENTS    {1}                           
  --#SEVERITY     MINOR 
  --#TIMEINDEX    100
     --#HELP         "hpnsnic.hlp"
   --#HELPTAG      34
      --#STATE        OPERATIONAL
     
	-- FIXED STRING  : Adapter DMA Timed Out errors
 -- CUSTOM STRING : PRESENT
      -- SEVERITY      : MINOR

	::= 16404


hpnsaNicTxNoResources TRAP-TYPE
	ENTERPRISE hpnsa
	DESCRIPTION
	     "The HP LAN adapter is transmitting faster than the media 
	       can handle."
   
	--#TYPE         "Adapter Tx No Resources errors"
	--#SUMMARY      "%s"
    --#ARGUMENTS    {1}
     --#SEVERITY     INFORMATIONAL
   --#TIMEINDEX    100
     --#HELP         "hpnsnic.hlp"
   --#HELPTAG      35
      --#STATE        OPERATIONAL
     
	-- FIXED STRING  : Adapter Tx No Resources errors 
      -- CUSTOM STRING : PRESENT
      -- SEVERITY      : INFORMATION

  ::= 16405


hpnsaNicTxExcessiveFrags TRAP-TYPE
     ENTERPRISE hpnsa
	DESCRIPTION
	     "The number of buffer fragments has exceeded the maximum 
		number allowed by the network protocol in your HP LAN
	   adapter."
      
	--#TYPE         "Adapter Tx Excessive Frags errors"
     --#SUMMARY      "%s"
    --#ARGUMENTS    {1}
     --#SEVERITY     MINOR
   --#TIMEINDEX    100
     --#HELP         "hpnsnic.hlp"
   --#HELPTAG      36
      --#STATE        OPERATIONAL

     
	-- FIXED STRING  : Adapter Tx Excessive Frags errors 
   -- CUSTOM STRING : PRESENT
      -- SEVERITY      : MINOR

	::= 16406


hpnsaNicRxLow TRAP-TYPE
	ENTERPRISE hpnsa
	DESCRIPTION
	     "The total number of errors due to requests of an ECB being 
	     denied has exceeded the threshold."
    
	--#TYPE         "Adapter Rx Low Errors"
 --#SUMMARY      "%s"
    --#ARGUMENTS    {1}
     --#SEVERITY     INFORMATIONAL
   --#TIMEINDEX    100
     --#HELP         "hpnsnic.hlp"
   --#HELPTAG      37
      --#STATE        OPERATIONAL
     
	-- FIXED STRING  : Adapter Rx Low errors 
       -- CUSTOM STRING : PRESENT
      -- SEVERITY      : INFORMATION

  ::= 16407


hpnsaNicRxEmpty TRAP-TYPE
      ENTERPRISE hpnsa
	DESCRIPTION
	     "There possibly is a problem with your HP LAN adapter running
	    in bus master mode."
   
	--#TYPE         "Adapter Rx Empty errors"
       --#SUMMARY      "%s"
    --#ARGUMENTS    {1}
     --#SEVERITY     MINOR
   --#TIMEINDEX    100
     --#HELP         "hpnsnic.hlp"
   --#HELPTAG      38
      --#STATE        OPERATIONAL
     
	-- FIXED STRING  : Adapter Rx Empty errors 
     -- CUSTOM STRING : PRESENT
      -- SEVERITY      : MINOR

	::= 16408



--
-- 
-- Alarm Object (NSA Subobject) : Voltage or Remote Assistant Voltage
--
--

hpnsaVoltWarning TRAP-TYPE 
      ENTERPRISE hpnsa
	DESCRIPTION
	     "Warning voltage threshold on one of the system voltage channels has 
	   been exceeded. Voltage channels are +12V, +5V, -12V, +3.3V to PCI, 
	     +3.3V to CPU"
   
	--#TYPE         "Voltage Warning"
       --#SUMMARY      "%s"
    --#ARGUMENTS    {1}
     --#SEVERITY     MINOR    
       --#TIMEINDEX    100
     --#HELP "nsa.hlp"
       --#HELPTAG      2063
    --#STATE        DEGRADED
	
	-- FIXED STRING  : NOT PRESENT
  -- CUSTOM STRING : PRESENT
      -- SEVERITY      : WARNING

      ::= 20739


hpnsaVoltEmergency TRAP-TYPE 
  ENTERPRISE hpnsa
	DESCRIPTION
	     "Fatal voltage threshold on one of the system voltage channels has 
	     been exceeded. Voltage channels are +12V, +5V, -12V, +3.3V to PCI, 
	     +3.3V to CPU"
   
	--#TYPE         "Voltage Emergency"
     --#SUMMARY      "%s"
    --#ARGUMENTS    {1}
     --#SEVERITY     CRITICAL
	--#TIMEINDEX    100
     --#HELP "nsa.hlp"
       --#HELPTAG      2064
    --#STATE        DEGRADED
	
	-- FIXED STRING  : NOT PRESENT
  -- CUSTOM STRING : PRESENT
      -- SEVERITY      : CRITICAL

     ::= 20738


hpnsaRAVoltServerPowerFailure TRAP-TYPE
	ENTERPRISE hpnsaRemoteAssist
      DESCRIPTION 
	    "The server has lost the power completely."
     
	--#TYPE         "Server power failure"
  --#SUMMARY      "%s"
    --#ARGUMENTS    {1}
     --#SEVERITY     MAJOR
   --#TIMEINDEX    100
     --#HELP         "rahelp.hlp"
    --#HELPTAG      8
       --#STATE        DEGRADED
	
	-- FIXED STRING  : NOT PRESENT
  -- CUSTOM STRING : PRESENT
      -- SEVERITY      : MAJOR

	::= 109


hpnsaRAVoltMinus12VUpper TRAP-TYPE
       ENTERPRISE hpnsaRemoteAssist
      DESCRIPTION 
	    "Voltage measured in the server has gone outside of -12V Upper 
	  Threshold."
    
	--#TYPE         "-12V Upper Threshold Warning"
  --#SUMMARY      "%s"
    --#ARGUMENTS    {1}
     --#SEVERITY     MAJOR
   --#TIMEINDEX    100
     --#HELP         "rahelp.hlp"
    --#HELPTAG      8
       --#STATE        DEGRADED
	
	-- FIXED STRING  : NOT PRESENT
  -- CUSTOM STRING : PRESENT
      -- SEVERITY      : MAJOR

	::= 111



hpnsaRAVoltPlus3VUpper TRAP-TYPE
 ENTERPRISE hpnsaRemoteAssist
      DESCRIPTION 
	    "Voltage measured in the server has gone outside of +3.3V Upper 
		 Threshold."
    
	--#TYPE         "+3.3 Upper Threshold Warning"
  --#SUMMARY      "%s"
    --#ARGUMENTS    {1}
     --#SEVERITY     MAJOR
   --#TIMEINDEX    100
     --#HELP         "rahelp.hlp"
    --#HELPTAG      7
       --#STATE        DEGRADED
	
	-- FIXED STRING  : NOT PRESENT
  -- CUSTOM STRING : PRESENT
      -- SEVERITY      : MAJOR

	::= 113


hpnsaRAVoltPlus5VUpper TRAP-TYPE
 ENTERPRISE hpnsaRemoteAssist
      DESCRIPTION 
	    "Voltage measured in the server has gone outside of +5V Upper 
	   Threshold."
    
	--#TYPE         "+5V Upper Threshold Warning"
   --#SUMMARY      "%s"
    --#ARGUMENTS    {1}
     --#SEVERITY     MAJOR
   --#TIMEINDEX    100
     --#HELP         "rahelp.hlp"
    --#HELPTAG      7
       --#STATE        DEGRADED
	
	-- FIXED STRING  : NOT PRESENT
  -- CUSTOM STRING : PRESENT
      -- SEVERITY      : MAJOR

	::= 114


hpnsaRAVoltPlus12VUpper TRAP-TYPE
	ENTERPRISE hpnsaRemoteAssist
      DESCRIPTION 
	    "Voltage measured in the server has gone outside of +12V Upper 
	  Threshold."
    
	--#TYPE         "+12V Upper Threshold Warning"
  --#SUMMARY      "%s"
    --#ARGUMENTS    {1}
     --#SEVERITY     MAJOR
   --#TIMEINDEX    100
     --#HELP         "rahelp.hlp"
    --#HELPTAG      7
       --#STATE        DEGRADED
	
	-- FIXED STRING  : NOT PRESENT
  -- CUSTOM STRING : PRESENT
      -- SEVERITY      : MAJOR

	::= 115


hpnsaRAVoltMinus12VLower TRAP-TYPE
       ENTERPRISE hpnsaRemoteAssist
      DESCRIPTION 
	    "Voltage measured in the server has gone outside of -12V Lower
	   Threshold."
    
	--#TYPE         "-12V Lower Threshold Warning"
  --#SUMMARY      "%s"
    --#ARGUMENTS    {1}
     --#SEVERITY     MAJOR
   --#TIMEINDEX    100
     --#HELP         "rahelp.hlp"
    --#HELPTAG      7
       --#STATE        DEGRADED
	
	-- FIXED STRING  : NOT PRESENT
  -- CUSTOM STRING : PRESENT
      -- SEVERITY      : MAJOR

	::= 121



hpnsaRAVoltBatteryLower TRAP-TYPE
	ENTERPRISE hpnsaRemoteAssist
      DESCRIPTION 
	    "The HP Remote Assistant Card's battery charging circuit is 
	     bad."
  
	--#TYPE         "Battery Lower Threshold Warning"
       --#SUMMARY      "%s"
    --#ARGUMENTS    {1}
     --#SEVERITY     MINOR
   --#TIMEINDEX    100
     --#HELP         "rahelp.hlp"
    --#HELPTAG      7
       --#STATE        OPERATIONAL
			    
 -- FIXED STRING  : NOT PRESENT
  -- CUSTOM STRING : PRESENT
      -- SEVERITY      : WARNING

      ::= 122



hpnsaRAVoltPlus3VLower TRAP-TYPE
 ENTERPRISE hpnsaRemoteAssist
      DESCRIPTION 
	    "Voltage measured in the server has gone outside of +3.3V Lower
	  Threshold."
    
	--#TYPE         "+3.3V Lower Threshold Warning"
 --#SUMMARY      "%s"
    --#ARGUMENTS    {1}
     --#SEVERITY     MAJOR
   --#TIMEINDEX    100
     --#HELP         "rahelp.hlp"
    --#HELPTAG      7
       --#STATE        DEGRADED
	
	
	-- FIXED STRING  : NOT PRESENT
  -- CUSTOM STRING : PRESENT
      -- SEVERITY      : MAJOR

	::= 123



hpnsaRAVoltPlus5VLower TRAP-TYPE
 ENTERPRISE hpnsaRemoteAssist
      DESCRIPTION 
	    "Voltage measured in the server has gone outside of +5V Lower
	    Threshold."
    
	--#TYPE         "+5V Lower Threshold Warning"
   --#SUMMARY      "%s"
    --#ARGUMENTS    {1}
     --#SEVERITY     MAJOR
   --#TIMEINDEX    100
     --#HELP         "rahelp.hlp"
    --#HELPTAG      7
       --#STATE        DEGRADED
	
	
	-- FIXED STRING  : NOT PRESENT
  -- CUSTOM STRING : PRESENT
      -- SEVERITY      : MAJOR

	::= 124



hpnsaRAVoltPlus12VLower TRAP-TYPE
	ENTERPRISE hpnsaRemoteAssist
      DESCRIPTION 
	    "Voltage measured in the server has gone outside of +12V Lower
	   Threshold."
    
	--#TYPE         "+12V Lower Threshold Warning"
  --#SUMMARY      "%s"
    --#ARGUMENTS    {1}
     --#SEVERITY     MAJOR
   --#TIMEINDEX    100
     --#HELP         "rahelp.hlp"
    --#HELPTAG      7
       --#STATE        DEGRADED
	
	
	-- FIXED STRING  : NOT PRESENT
  -- CUSTOM STRING : PRESENT
      -- SEVERITY      : MAJOR

	::= 125


--
-- 
-- Alarm Object (NSA Subobject) : Temperature or Remote Assistant Temperature
--
--

hpnsaTempMonitorError TRAP-TYPE
    ENTERPRISE  hpnsa
       DESCRIPTION
	     "Server temperature monitor cannot read temperature data."
      
	--#TYPE         "Temperature Monitor error"
     --#SUMMARY      "%s"
    --#ARGUMENTS    {1}
     --#SEVERITY     INFORMATIONAL
   --#TIMEINDEX    100
     --#HELP         "nsa.hlp"
       --#HELPTAG      2039
    --#STATE        OPERATIONAL
     
	-- FIXED STRING  : NOT PRESENT
  -- CUSTOM STRING : PRESENT
      -- SEVERITY      : UNKNOWN

      ::= 12288

hpnsaTempTrapWarning TRAP-TYPE
 ENTERPRISE  hpnsa
       DESCRIPTION
	     "Server temperature has exceeded the warning temperature  
	       threshold."
    
	--#TYPE         "Temperature warning" 
  --#SUMMARY      "%s"
    --#ARGUMENTS    {1}
     --#SEVERITY     MINOR
   --#TIMEINDEX    100
     --#HELP         "nsa.hlp"
       --#HELPTAG      2040                             
       --#STATE        OPERATIONAL
     
	-- FIXED STRING  : NOT PRESENT
  -- CUSTOM STRING : PRESENT
      -- SEVERITY      : WARNING

      ::= 12289


hpnsaTempTrapEmergency TRAP-TYPE
       ENTERPRISE  hpnsa
       DESCRIPTION
	     "Server temperature has exceeded the emergency temperature  
	     threshold."
    
	--#TYPE         "Temperature Emergency"
 --#SUMMARY      "%s"
    --#ARGUMENTS    {1}
     --#SEVERITY     CRITICAL
	--#TIMEINDEX    100
     --#HELP         "nsa.hlp"
       --#HELPTAG      2041
    --#STATE        DEGRADED
	
	-- FIXED STRING  : NOT PRESENT
  -- CUSTOM STRING : PRESENT
      -- SEVERITY      : CRITICAL

     ::= 12290


hpnsaHotSwapTempMonitorError TRAP-TYPE
 ENTERPRISE hpnsa
	DESCRIPTION 
	    "Hot Swap Cage: Temperature monitor error occurred"
     
	--#TYPE         "Hot Swap: Temperature monitor error"
   --#SUMMARY      "%s"
    --#ARGUMENTS    {1}
     --#SEVERITY     INFORMATIONAL
   --#TIMEINDEX    100
     --#HELP         "nsa.hlp"
       --#HELPTAG      2066
    --#STATE        OPERATIONAL
	     
	-- FIXED STRING  : NOT PRESENT
  -- CUSTOM STRING : PRESENT 
     -- SEVERITY      : UNKNOWN

      ::= 24449


hpnsaHotSwapTempWarning TRAP-TYPE
      ENTERPRISE hpnsa
	DESCRIPTION 
	    "Hot Swap Cage: Warning temperature exceeded"
   
	--#TYPE         "Hot Swap: Temperature warning"
 --#SUMMARY      "%s"
    --#ARGUMENTS    {1}
     --#SEVERITY     MINOR
   --#TIMEINDEX    100
     --#HELP         "nsa.hlp"
       --#HELPTAG      2067
    --#STATE        OPERATIONAL
	     
	-- FIXED STRING  : NOT PRESENT
  -- CUSTOM STRING : PRESENT 
     -- SEVERITY      : WARNING

      ::= 24451


hpnsaHotSwapTempEmergency TRAP-TYPE
    ENTERPRISE hpnsa
	DESCRIPTION 
	    "Hot Swap Cage: Emergency temperature exceeded!"
	
	--#TYPE         "Hot Swap: Temperature emergency" 
      --#SUMMARY      "%s"
    --#ARGUMENTS    {1}
     --#SEVERITY     CRITICAL
	--#TIMEINDEX    100
     --#HELP         "nsa.hlp"
       --#HELPTAG      2068
    --#STATE        DEGRADED

	-- FIXED STRING  : NOT PRESENT
  -- CUSTOM STRING : PRESENT 
     -- SEVERITY      : CRITICAL

     ::= 24452


hpnsaRATempWarning TRAP-TYPE
   ENTERPRISE hpnsaRemoteAssist
      DESCRIPTION
	     "The server temperature measured on the HP Remote Assistant Card has 
	    exceeded the configured warning threshold."
    
	--#TYPE         "Temperature Warning"
   --#SUMMARY      "%s"
    --#ARGUMENTS    {1}
     --#SEVERITY     WARNING
 --#TIMEINDEX    100
     --#HELP         "rahelp.hlp"
    --#HELPTAG      9
       --#STATE        OPERATIONAL

     -- FIXED STRING  : NOT PRESENT
  -- CUSTOM STRING : PRESENT
      -- SEVERITY      : WARNING

      ::= 211


hpnsaRATempShutdown TRAP-TYPE
    ENTERPRISE hpnsaRemoteAssist
      DESCRIPTION
	     "The server temperature measured on the HP Remote Assistant Card has 
	    exceeded the configured threshold and the server has been 
	      automatically shut down."
      
	--#TYPE         "Temperature Graceful Shutdown"
 --#SUMMARY      "%s"
    --#ARGUMENTS    {1}
     --#SEVERITY     INFORMATIONAL
   --#TIMEINDEX    100
     --#HELP         "rahelp.hlp"
    --#HELPTAG      10
      --#STATE        OPERATIONAL
     
	-- FIXED STRING  : NOT PRESENT
  -- CUSTOM STRING : PRESENT
      -- SEVERITY      : INFORMATION

  ::= 221


hpnsaRATempCritical TRAP-TYPE
    ENTERPRISE hpnsaRemoteAssist
      DESCRIPTION
	     "The server temperature measured on the HP Remote Assistant Card has 
	    exceeded the configured Graceful Shutdown threshold value by 5 
		 degrees C and the server has been automatically shut down."
    
	--#TYPE         "Temperature Critical"
  --#SUMMARY      "%s"
    --#ARGUMENTS    {1}
     --#SEVERITY     INFORMATIONAL
   --#TIMEINDEX    100
     --#HELP         "rahelp.hlp"
    --#HELPTAG       10
     --#STATE        OPERATIONAL
     
	-- FIXED STRING  : NOT PRESENT
  -- CUSTOM STRING : PRESENT
      -- SEVERITY      : INFORMATION

  ::= 231


--
-- 
-- Alarm Object (NSA Subobject) : ASR or Remote Assistant ASR
--
--

hpnsaASRServerRestart TRAP-TYPE
    ENTERPRISE hpnsa
	DESCRIPTION 
	    "Server has been restarted after the system watchdog timer has timed
	    out due to NOS being hung"
      
	--#TYPE         "ASR timeout"
   --#SUMMARY      "%s"
    --#ARGUMENTS    {1}
     --#SEVERITY     INFORMATIONAL
   --#TIMEINDEX    100
     --#HELP         "nsa.hlp"
       --#HELPTAG      2057
    --#STATE        OPERATIONAL
     
	-- FIXED STRING  : NOT PRESENT
  -- CUSTOM STRING : PRESENT
      -- SEVERITY          : INFORMATION

      ::= 20752


hpnsaRAASRHangNOS TRAP-TYPE
    ENTERPRISE hpnsaRemoteAssist
      DESCRIPTION 
	    "ASR has stopped notifying the HP Remote Assistant Card that the 
		system is running correctly (the server probably hung or crashed)."
    
	--#TYPE         "Warning NOS hang (ASR)"
	--#SUMMARY      "%s"
    --#ARGUMENTS    {1}
     --#SEVERITY     INFORMATIONAL
   --#TIMEINDEX    100
     --#HELP         "rahelp.hlp"
    --#HELPTAG      12
      --#STATE        OPERATIONAL
     
	-- FIXED STRING  : NOT PRESENT
  -- CUSTOM STRING : PRESENT
      -- SEVERITY      : INFORMATION

  ::= 501


hpnsaRAASRServerRestart TRAP-TYPE
	ENTERPRISE hpnsaRemoteAssist
      DESCRIPTION 
	    "The HP Remote Assistant card has restarted the server due to the
		NOS being hung."
       
	--#TYPE         "Server Restart after NOS hang (ASR)"
   --#SUMMARY      "%s"
    --#ARGUMENTS    {1}
     --#SEVERITY     INFORMATIONAL
   --#TIMEINDEX    100
     --#HELP         "rahelp.hlp"
    --#HELPTAG      13
      --#STATE        OPERATIONAL
     
	-- FIXED STRING  : NOT PRESENT
  -- CUSTOM STRING : PRESENT
      -- SEVERITY      : INFORMATION

  ::= 502

hpnsaRAASRTimerEnabled TRAP-TYPE
 ENTERPRISE hpnsaRemoteAssist
      DESCRIPTION 
	    "The Automatic Server Restart software has been enabled by the Remote Assistant 
		ASR timer."
     
	--#TYPE         "ASR Timer Enabled"
     --#SUMMARY      "%s"
    --#ARGUMENTS    {1}
     --#SEVERITY     INFORMATIONAL
   --#TIMEINDEX    100
     --#HELP         "rahelp.hlp"
    --#HELPTAG      24
      --#STATE        OPERATIONAL
     
	-- FIXED STRING  : NOT PRESENT
  -- CUSTOM STRING : PRESENT
      -- SEVERITY      : INFORMATION

  ::= 503

hpnsaRAASRTimerDisabled TRAP-TYPE
	ENTERPRISE hpnsaRemoteAssist
      DESCRIPTION 
	    "The HP Remote Assistant Automatic Server Restart timer has been disabled."
     
	--#TYPE         "ASR Timer Disabled"
    --#SUMMARY      "%s"
    --#ARGUMENTS    {1}
     --#SEVERITY     INFORMATIONAL
   --#TIMEINDEX    100
     --#HELP         "rahelp.hlp"
    --#HELPTAG      25
      --#STATE        OPERATIONAL
     
	-- FIXED STRING  : NOT PRESENT
  -- CUSTOM STRING : PRESENT
      -- SEVERITY      : INFORMATION

  ::= 504



--
-- 
-- Alarm Object (NSA Subobject) : Remote Assistant Bus Usage
--
--

hpnsaRABusUtilization TRAP-TYPE
     ENTERPRISE hpnsaRemoteAssist
      DESCRIPTION 
	    "The 5-minute average EISA bus utilization has exceeded the 
	     configured threshold."
 
	--#TYPE         "Bus Utilization"
       --#SUMMARY      "%s"
    --#ARGUMENTS    {1}
     --#SEVERITY     MINOR
   --#TIMEINDEX    100
     --#HELP         "rahelp.hlp"
    --#HELPTAG      14
      --#STATE        OPERATIONAL
     
	-- FIXED STRING  : NOT PRESENT
  -- CUSTOM STRING : PRESENT
      -- SEVERITY      : WARNING

      ::= 800


--
-- 
-- Alarm Object (NSA Subobject) : Remote Assistant Other
--
--
hpnsaRASuccessfulLogin TRAP-TYPE
	ENTERPRISE hpnsaRemoteAssist
      DESCRIPTION 
	    "An administrator has logged in to the HP Remote Assistant Card."
       
	--#TYPE         "Successful Login"
      --#SUMMARY      "%s"
    --#ARGUMENTS    {1}
     --#SEVERITY     INFORMATIONAL
   --#TIMEINDEX    100
     --#HELP         "rahelp.hlp"
    --#HELPTAG      15
      --#STATE        OPERATIONAL
     
	-- FIXED STRING  : NOT PRESENT
  -- CUSTOM STRING : PRESENT
      -- SEVERITY      : INFORMATION

  ::= 401


hpnsaRAIllegalLogin TRAP-TYPE
    ENTERPRISE hpnsaRemoteAssist
      DESCRIPTION 
	    "An unauthorized user has made 3 or more unsuccessful attempts 
	  to log in to the HP Remote Assistant Card within a 5-minute 
	    period of time." 
      
	--#TYPE         "Illegal Login"
 --#SUMMARY      "%s"
    --#ARGUMENTS    {1}
     --#SEVERITY     MINOR
   --#TIMEINDEX    100
     --#HELP         "rahelp.hlp"
    --#HELPTAG      16
      --#STATE        OPERATIONAL
     
	-- FIXED STRING  : NOT PRESENT
  -- CUSTOM STRING : PRESENT
      -- SEVERITY      : WARNING

      ::= 402


hpnsaRALowBatteryCharge TRAP-TYPE
	ENTERPRISE hpnsaRemoteAssist
      DESCRIPTION 
	    "The HP Remote Assistant Card's battery charging circuit is 
	     bad."
  
	--#TYPE         "Low Battery Charge"
    --#SUMMARY      "%s"
    --#ARGUMENTS    {1}
     --#SEVERITY     INFORMATIONAL
   --#TIMEINDEX    100
     --#HELP         "rahelp.hlp"
    --#HELPTAG      17
      --#STATE        OPERATIONAL
     
	-- FIXED STRING  : NOT PRESENT
  -- CUSTOM STRING : PRESENT
      -- SEVERITY      : INFORMATION

  ::= 403


hpnsaRABoardShutDown TRAP-TYPE
   ENTERPRISE hpnsaRemoteAssist
      DESCRIPTION 
	    "The HP Remote Assistant Card has been shut down."
      
	--#TYPE         "Board shut down"
       --#SUMMARY      "%s"
    --#ARGUMENTS    {1}
     --#SEVERITY     INFORMATIONAL
   --#TIMEINDEX    100
     --#HELP         "rahelp.hlp"
    --#HELPTAG      18
      --#STATE        OPERATIONAL
     
	-- FIXED STRING  : NOT PRESENT
  -- CUSTOM STRING : PRESENT
      -- SEVERITY      : INFORMATION

  ::= 404


hpnsaRARemoteInitiatedCtrlAltDel TRAP-TYPE
       ENTERPRISE hpnsaRemoteAssist
      DESCRIPTION 
	    "An administrator has executed a remote <Ctrl-Alt-Del> on the 
	   server via the HP Remote Assistant Card."
      
	--#TYPE         "Remote Initiates <Ctrl-Alt-Del>"
       --#SUMMARY      "%s"
    --#ARGUMENTS    {1}
     --#SEVERITY     INFORMATIONAL
   --#TIMEINDEX    100
     --#HELP         "rahelp.hlp"
    --#HELPTAG      19            
  --#STATE        OPERATIONAL
     
	-- FIXED STRING  : NOT PRESENT
  -- CUSTOM STRING : PRESENT
      -- SEVERITY      : INFORMATION

  ::= 601


hpnsaRARemoteInitiatedReset TRAP-TYPE
    ENTERPRISE hpnsaRemoteAssist
      DESCRIPTION 
	    "An administrator has executed a remote power cycle on the 
	      server via the HP Remote Assistant Card."
      
	--#TYPE         "Remote Initiated Reset or Power Cycle"
 --#SUMMARY      "%s"
    --#ARGUMENTS    {1}
     --#SEVERITY     INFORMATIONAL
   --#TIMEINDEX    100
     --#HELP         "rahelp.hlp"
    --#HELPTAG      20             
 --#STATE        OPERATIONAL
     
	-- FIXED STRING  : NOT PRESENT
  -- CUSTOM STRING : PRESENT
      -- SEVERITY      : INFORMATION

  ::= 602


hpnsaRARemoteInitiatedPowerDown TRAP-TYPE
	ENTERPRISE hpnsaRemoteAssist
      DESCRIPTION 
	    "An administrator has executed a remote power down of the 
	       server via the HP Remote Assistant Card."
      
	--#TYPE         "Remote Initiated Power Down"
   --#SUMMARY      "%s"
    --#ARGUMENTS    {1}
     --#SEVERITY     INFORMATIONAL
   --#TIMEINDEX    100
     --#HELP         "rahelp.hlp"
    --#HELPTAG      21
      --#STATE        OPERATIONAL
     
	-- FIXED STRING  : NOT PRESENT
  -- CUSTOM STRING : PRESENT
      -- SEVERITY      : INFORMATION

  ::= 603


hpnsaRAInitServerBIOS TRAP-TYPE
  ENTERPRISE hpnsaRemoteAssist
      DESCRIPTION 
	    "The server's BIOS has successfully initialized the HP Remote
	    Assistant Card during the boot process."
       
	--#TYPE         "Server BIOS Initialization"
    --#SUMMARY      "%s"
    --#ARGUMENTS    {1}
     --#SEVERITY     INFORMATIONAL
   --#TIMEINDEX    100
     --#HELP         "rahelp.hlp"
    --#HELPTAG      22
      --#STATE        OPERATIONAL
     
	-- FIXED STRING  : NOT PRESENT
  -- CUSTOM STRING : PRESENT
      -- SEVERITY      : INFORMATION

  ::= 701


hpnsaRATestNotification TRAP-TYPE
	ENTERPRISE hpnsaRemoteAssist
      DESCRIPTION 
	    "An administrator has executed Test Page from the HP Remote 
	     Assistant Configuration Utility."
      
	--#TYPE         "Test notification"
     --#SUMMARY      "%s"
    --#ARGUMENTS    {1}
     --#SEVERITY     INFORMATIONAL
   --#TIMEINDEX    100
     --#HELP         "rahelp.hlp"
    --#HELPTAG      23
      --#STATE        OPERATIONAL
     
	-- FIXED STRING  : NOT PRESENT
  -- CUSTOM STRING : PRESENT
      -- SEVERITY      : INFORMATION

  ::= 900

hpnsaRAAdminstratorLogout TRAP-TYPE
      ENTERPRISE hpnsaRemoteAssist
      DESCRIPTION
	     "An administrator disconnected from the HP Remote Assistant board."
     --#TYPE "Administator Logout"
   --#SUMMARY    "%s"
      --#ARGUMENTS  {1}
       --#SEVERITY     INFORMATIONAL
   --#TIMEINDEX    100
     --#HELP "rahelp.hlp"
    --#HELPTAG      26
      --#STATE        OPERATIONAL

     --FIXED STRING: NOT PRESENT
     --CUSTOM STRING: PRESENT
	--SEVERITY: INFORMATIONAL

       ::= 405

hpnsaRAAdministratorAutologout TRAP-TYPE
 ENTERPRISE hpnsaRemoteAssist
      DESCRIPTION
	     "An administrator has been automatically disconnected from the HP Remote 
	       Assistant board. The administrator was inactive for more than five minutes."
    --#TYPE "Administrator Autologout"
      --#SUMMARY      "%s"
    --#ARGUMENTS  {1}
       --#SEVERITY     INFORMATIONAL
   --#TIMEINDEX    100
     --#HELP "rahelp.hlp"
    --#HELPTAG      27
      --#STATE        OPERATIONAL

     --FIXED STRING: NOT PRESENT
     --CUSTOM STRING: PRESENT
	--SEVERITY: INFORMATIONAL

       ::= 406

hpnsaRAAdministratorConnectionLost TRAP-TYPE
     ENTERPRISE hpnsaRemoteAssist
      DESCRIPTION
	     "An administrator has been prematurely disconnected from the Remote Assistant 
	  board."
 --#TYPE "Administrator Connection Lost"
 --#SUMMARY    "%s"
      --#ARGUMENTS  {1}
       --#SEVERITY     WARNING
 --#TIMEINDEX    100
     --#HELP "rahelp.hlp"
    --#HELPTAG      28
      --#STATE        OPERATIONAL

     --FIXED STRING: NOT PRESENT
     --CUSTOM STRING: PRESENT
	--SEVERITY: INFORMATIONAL

       ::= 407

hpnsaRAAdministratorDialbackFailed TRAP-TYPE
     ENTERPRISE hpnsaRemoteAssist
      DESCRIPTION
	     "An administrator failed to connect to the HP Remote Assistant board on a 
	      dialback"
       --#TYPE "Administrator Dialback Failed"
 --#SUMMARY      "%s"
    --#ARGUMENTS  {1}
       --#SEVERITY     WARNING
 --#TIMEINDEX    100
     --#HELP "rahelp.hlp"
    --#HELPTAG      29
      --#STATE        OPERATIONAL

     --FIXED STRING: NOT PRESENT
     --CUSTOM STRING: PRESENT
	--SEVERITY: INFORMATIONAL
       
	::= 408

 hpnsaRATAPNoConnect TRAP-TYPE
   ENTERPRISE hpnsaRemoteAssist
      DESCRIPTION
	     "The HP Remote Assistant modem was unable to connect to the
	      TAP paging service modem."
     --#TYPE "TAP No Connect"
	--#SUMMARY    "%s"
      --#ARGUMENTS  {1}
       --#SEVERITY     INFORMATIONAL
   --#TIMEINDEX    100
     --#HELP "rahelp.hlp"
    --#HELPTAG      30
      --#STATE        OPERATIONAL
     
	--FIXED STRING: NOT PRESENT
     --CUSTOM STRING: PRESENT
	--SEVERITY: INFORMATIONAL
     
  ::= 901
     
     hpnsaRATAPParam1Error TRAP-TYPE
	ENTERPRISE hpnsaRemoteAssist
      DESCRIPTION
	     "HP Remote Assistant was unable to connect with the TAP
	  paging service."
       --#TYPE "TAP Parameter 1 Error"
 --#SUMMARY    "%s"
      --#ARGUMENTS  {1}
       --#SEVERITY     INFORMATIONAL
   --#TIMEINDEX    100
     --#HELP "rahelp.hlp"
    --#HELPTAG      31
      --#STATE        OPERATIONAL
     
	--FIXED STRING: NOT PRESENT
     --CUSTOM STRING: PRESENT
	--SEVERITY: INFORMATIONAL
     
  ::= 902
     
     hpnsaRATAPParam2Error TRAP-TYPE
	ENTERPRISE hpnsaRemoteAssist
      DESCRIPTION
	     "HP Remote Assistant was unable to log on to the TAP
	     paging service."
       --#TYPE "TAP Parameter 2 Error"
 --#SUMMARY    "%s"
      --#ARGUMENTS  {1}
       --#SEVERITY     INFORMATIONAL
   --#TIMEINDEX    100
     --#HELP "rahelp.hlp"
    --#HELPTAG      32
      --#STATE        OPERATIONAL
     
	--FIXED STRING: NOT PRESENT
     --CUSTOM STRING: PRESENT
	--SEVERITY: INFORMATIONAL
     
  ::= 903
     
     hpnsaRATAPParam3Error TRAP-TYPE
	ENTERPRISE hpnsaRemoteAssist
      DESCRIPTION
	     "The HP Remote Assistant pager message was rejected by the
	       TAP paging service."
   --#TYPE "TAP Parameter 3 Error"
 --#SUMMARY    "%s"
      --#ARGUMENTS  {1}
       --#SEVERITY     INFORMATIONAL
   --#TIMEINDEX    100
     --#HELP "rahelp.hlp"
    --#HELPTAG      33
      --#STATE        OPERATIONAL
     
	--FIXED STRING: NOT PRESENT
     --CUSTOM STRING: PRESENT
	--SEVERITY: INFORMATIONAL
     
  ::= 904


--
-- 
-- Alarm Object (NSA Subobject) : HP ECC Memory
--
--

hpnsaEccErrorCorrected TRAP-TYPE
 ENTERPRISE hpnsaECC
     DESCRIPTION 
	    "An ECC single-bit error has been corrected in one of the memory 
	       modules"
	
	--#TYPE         "ECC memory error corrected"
    --#SUMMARY      "%s"
    --#ARGUMENTS    {1}
     --#SEVERITY     MINOR
   --#TIMEINDEX    100
     --#HELP         "nsa.hlp"
       --#HELPTAG      2059
    --#STATE        OPERATIONAL
     
	-- FIXED STRING  : NOT PRESENT
  -- CUSTOM STRING : PRESENT
      -- SEVERITY      : WARNING

      ::= 4353

hpnsaEccSBEOverflow TRAP-TYPE
   ENTERPRISE hpnsaECC
     DESCRIPTION 
	    "Error logging for ECC single-bit errors has been disabled due to too
	   many SBE's detected in a short time period"
     
	--#TYPE         "ECC single-bit overflow; logging disabled"
     --#SUMMARY      "%s"
    --#ARGUMENTS    {1}
     --#SEVERITY     MAJOR
   --#TIMEINDEX    100
     --#HELP         "nsa.hlp"
       --#HELPTAG      2061
    --#STATE        DEGRADED
	
	-- FIXED STRING  : NOT PRESENT
  -- CUSTOM STRING : PRESENT
      -- SEVERITY          : MAJOR

    ::= 4354

hpnsaEccMemoryResize TRAP-TYPE
  ENTERPRISE hpnsaECC
     DESCRIPTION 
	    "ECC Memory size has been adjusted during the Power-On-Self-Test
		during the last boot due to a failed memory module"
     
	--#TYPE         "ECC memory resize error"
       --#SUMMARY      "%s"
    --#ARGUMENTS    {1}
     --#SEVERITY     MINOR
   --#TIMEINDEX    100
     --#HELP         "nsa.hlp"
       --#HELPTAG      2058
    --#STATE        DEGRADED
	
	-- FIXED STRING  : NOT PRESENT
  -- CUSTOM STRING : PRESENT
      -- SEVERITY          : WARNING

  ::= 4355


hpnsaEccMultiBitError TRAP-TYPE
 ENTERPRISE hpnsaECC
     DESCRIPTION 
	    "An ECC double-bit error has occurred in one of the memory modules"
     
	--#TYPE         "ECC multiple bit error" 
       --#SUMMARY      "%s"
    --#ARGUMENTS    {1}
     --#SEVERITY     MAJOR
   --#TIMEINDEX    100
     --#HELP         "nsa.hlp"
       --#HELPTAG      2060
    --#STATE        DEGRADED
	
	-- FIXED STRING  : NOT PRESENT
  -- CUSTOM STRING : PRESENT
      -- SEVERITY          : MAJOR

    ::= 4357


hpnsaEccMultiBitErrorOverflow TRAP-TYPE
 ENTERPRISE hpnsaECC
     DESCRIPTION 
	    "Error logging for ECC multiple-bit errors has been disabled due to too
	 many MBE's detected in a short time period"
     
	--#TYPE         "ECC multi-bit overflow; logging disabled"
      --#SUMMARY      "%s"
    --#ARGUMENTS    {1}
     --#SEVERITY     MAJOR
   --#TIMEINDEX    100
     --#HELP         "nsa.hlp"
       --#HELPTAG      2062
    --#STATE        OPERATIONAL
     
	-- FIXED STRING  : NOT PRESENT
  -- CUSTOM STRING : PRESENT
      -- SEVERITY          : MAJOR

    ::= 4358

--
-- 
-- Alarm Object (NSA Subobject) : HP Redundant Power Supply 
--
--

hpnsaRPSAbnormalCondition TRAP-TYPE
	ENTERPRISE hpnsa
	DESCRIPTION 
	    "The Redundant Power Supply module is not operating properly,
	   but there is no power supply module hardware failure."
  
	--#TYPE         "PSU: Abnormal environmental condition occurred"
	--#SUMMARY      "%s"
    --#ARGUMENTS    {1}
     --#SEVERITY     MAJOR
   --#TIMEINDEX    100
     --#HELP         "nsa.hlp"
       --#HELPTAG      2069
    --#STATE        OPERATIONAL
     
	-- FIXED STRING  : NOT PRESENT
  -- CUSTOM STRING : PRESENT
      -- SEVERITY      : MAJOR

	::= 9101

hpnsaRPSACPowerSourceFailure TRAP-TYPE
  ENTERPRISE hpnsa
	DESCRIPTION 
	    "Indicates a failure with the AC power source that is 
	  connected to one of the redundant power supply units."
  
	--#TYPE         "PSU: AC power source failure"
  --#SUMMARY      "%s"
    --#ARGUMENTS    {1}
     --#SEVERITY     CRITICAL
	--#TIMEINDEX    100
     --#HELP         "nsa.hlp"
       --#HELPTAG      2070
    --#STATE        OPERATIONAL
     
	-- FIXED STRING  : NOT PRESENT
  -- CUSTOM STRING : PRESENT
      -- SEVERITY      : CRITICAL

     ::= 9103

hpnsaRPSPsuFailureDetected TRAP-TYPE
    ENTERPRISE hpnsa
	DESCRIPTION 
	    "Indicates that one of the redundant power supply modules
	       is not in normal operating condition."
  
	--#TYPE         "PSU: Failure detected"
 --#SUMMARY      "%s"
    --#ARGUMENTS    {1}
     --#SEVERITY     CRITICAL
	--#TIMEINDEX    100
     --#HELP         "nsa.hlp"
       --#HELPTAG      2073
    --#STATE        OPERATIONAL
     
	-- FIXED STRING  : NOT PRESENT
  -- CUSTOM STRING : PRESENT
      -- SEVERITY      : CRITICAL

     ::= 9105

hpnsaRPSDCShutdown TRAP-TYPE
    ENTERPRISE hpnsa
	DESCRIPTION 
	    "Indicates that one of the redundant power supply modules
	       is in over temperature protection mode."
	
	--#TYPE         "PSU: Protection temperature exceeded, DC shutdown"
     --#SUMMARY      "%s"
    --#ARGUMENTS    {1}
     --#SEVERITY     CRITICAL
	--#TIMEINDEX    100
     --#HELP         "nsa.hlp"
       --#HELPTAG      2071
    --#STATE        OPERATIONAL
     
	-- FIXED STRING  : NOT PRESENT
  -- CUSTOM STRING : PRESENT
      -- SEVERITY      : CRITICAL

     ::= 9106

hpnsaRPSPsuRemoved TRAP-TYPE
    ENTERPRISE hpnsa
	DESCRIPTION 
	    "Indicates that one of the redundant power supply modules
	       has been physically removed from the HP NetServer Power 
		Supply Subsystem."
      
	--#TYPE         "PSU: Removed"
  --#SUMMARY      "%s"
    --#ARGUMENTS    {1}
     --#SEVERITY     INFORMATIONAL
   --#TIMEINDEX    100
     --#HELP         "nsa.hlp"
       --#HELPTAG      2074
    --#STATE        OPERATIONAL
     
	-- FIXED STRING  : NOT PRESENT
  -- CUSTOM STRING : PRESENT
      -- SEVERITY      : INFORMATIONAL

	::= 9107

hpnsaRPSPsuInserted TRAP-TYPE
   ENTERPRISE hpnsa
	DESCRIPTION 
	    "Indicates that one of the redundant power supply modules
	       has been physically inserted into the HP NetServer Power 
	       Supply Subsystem."
      
	--#TYPE         "PSU: Inserted"
 --#SUMMARY      "%s"
    --#ARGUMENTS    {1}
     --#SEVERITY     INFORMATIONAL
   --#TIMEINDEX    100
     --#HELP         "nsa.hlp"
       --#HELPTAG      2075
    --#STATE        OPERATIONAL
     
	-- FIXED STRING  : NOT PRESENT
  -- CUSTOM STRING : PRESENT
      -- SEVERITY      : INFORMATIONAL

	::= 9108

hpnsaRPSPowerRestored TRAP-TYPE
 ENTERPRISE hpnsa
	DESCRIPTION 
	    "Indicates that one of the redundant power supply modules
	       in the HP NetServer has recovered from an over temperature
	      protection mode."
       
	--#TYPE         "PSU: Protection temperature normal, power restored"
    --#SUMMARY      "%s"
    --#ARGUMENTS    {1}
     --#SEVERITY     INFORMATIONAL
   --#TIMEINDEX    100
     --#HELP         "nsa.hlp"
       --#HELPTAG      2072
    --#STATE        OPERATIONAL
     
	-- FIXED STRING  : NOT PRESENT
  -- CUSTOM STRING : PRESENT
      -- SEVERITY      : INFORMATIONAL

	::= 9109

hpnsaRPSWarningExceeded TRAP-TYPE
       ENTERPRISE hpnsa
	DESCRIPTION 
	    "Indicates that one of the redundant power supply modules
	       in the HP NetServer has exceeded the warning temperature
		level."
 
	--#TYPE         "PSS: Warning temperature exceeded"
     --#SUMMARY      "%s"
    --#ARGUMENTS    {1}
     --#SEVERITY     WARNING
 --#TIMEINDEX    100
     --#HELP         "nsa.hlp"
       --#HELPTAG      2076
    --#STATE        OPERATIONAL
     
	-- FIXED STRING  : NOT PRESENT
  -- CUSTOM STRING : PRESENT
      -- SEVERITY      : WARNING

      ::= 9110

hpnsaRPSEmergencyExceeded TRAP-TYPE
     ENTERPRISE hpnsa
	DESCRIPTION 
	    "Indicates that one of the redundant power supply modules
	       in the HP NetServer has exceeded the emergency temperature
	      level."
 
	--#TYPE         "PSS: Emergency temperature exceeded"
   --#SUMMARY      "%s"
    --#ARGUMENTS    {1}
     --#SEVERITY     CRITICAL
	--#TIMEINDEX    100
     --#HELP         "nsa.hlp"
       --#HELPTAG      2077
    --#STATE        OPERATIONAL
     
	-- FIXED STRING  : NOT PRESENT
  -- CUSTOM STRING : PRESENT
      -- SEVERITY      : CRITICAL

     ::= 9111

	
-- The following is the SNMP trap MIB definition files from various vendors
-- that are part of NSA trap agents.  These agents are integrated into NSA
-- version 2.5 or later but they are usig generic SNMP trap PDU encodings
-- without containing NSA-specific varbind, e.g. like version varbind in its
-- SNMP trap PDU.

--
-- The following object tree is assumed for CYCLONE MIB and can be redefined.
--
--  adaptec                         OBJECT IDENTIFIER ::=  {enterprises 795}
	storagemanagement               OBJECT IDENTIFIER ::=  {adaptec 2}
      cyclone                         OBJECT IDENTIFIER ::=  {storagemanagement 5}
	cycTraps                        OBJECT IDENTIFIER ::=  {cyclone 9000}
--The following are the object defined for cyclone Traps
       
	cycManagerID            OBJECT-TYPE
				     SYNTAX DisplayString    (SIZE(1..16))
				   ACCESS read-only
					STATUS mandatory
					DESCRIPTION
				     "ASCII String description of SCSI Manager"
				      ::=  {cycTraps 9001}

    cycHostAdapterID        OBJECT-TYPE
				     SYNTAX DisplayString    (SIZE(1..16))
				   ACCESS read-only
					STATUS mandatory
					DESCRIPTION
				     "ASCII String description of Hostadapter"
				       ::=  {cycTraps 9002}

    cycHostAdapterNumber    OBJECT-TYPE
				     SYNTAX INTEGER
				  ACCESS read-only
					STATUS mandatory
					DESCRIPTION
				     "The unique Hostadapter Number"
				 ::=  {cycTraps 9003}
    
	cycVendor               OBJECT-TYPE
				     SYNTAX DisplayString    (SIZE(1..8))
				    ACCESS read-only
					STATUS mandatory
					DESCRIPTION
				     "This indicates the Name of the Vendor"
				 ::=  {cycTraps 9004}
		    
	cycProduct              OBJECT-TYPE
				     SYNTAX DisplayString    (SIZE(1..16))
				   ACCESS read-only
					STATUS mandatory
					DESCRIPTION
				     "This indicates the product information"
					::=  {cycTraps 9005}
		    
	cycControllerModel      OBJECT-TYPE
				     SYNTAX DisplayString    (SIZE (1..32))
				  ACCESS read-only
					STATUS mandatory
					DESCRIPTION
				     "The model of the associated controller 
						e.g ATHENA, VIKING etc"
					 ::=  { cycTraps 9006 }

  cycBusNumber            OBJECT-TYPE
				     SYNTAX INTEGER 
				 ACCESS read-only
					STATUS mandatory
					DESCRIPTION
					     "The PCI Bus number"
				    ::=  { cycTraps 9007 }

  cycChannelNumber        OBJECT-TYPE
				     SYNTAX INTEGER 
				       ACCESS read-only
					STATUS mandatory
					DESCRIPTION
				     "Channel Number"
					::=  { cycTraps 9008 }

  cycScsiTargetID        OBJECT-TYPE
				      SYNTAX INTEGER
					  ACCESS read-only
					STATUS mandatory
					DESCRIPTION
				     "SCSI Target ID"
					::=  { cycTraps 9009 }

  cycLun                  OBJECT-TYPE
				     SYNTAX INTEGER
					  ACCESS read-only
					STATUS mandatory
					DESCRIPTION
				     "The LUN of the device ID"
				      ::=  { cycTraps 9010 }

  cycArrayName           OBJECT-TYPE
				      SYNTAX DisplayString    (SIZE (1..32))
				  ACCESS read-only
					STATUS mandatory
					DESCRIPTION
				     "Array name"
				    ::=  { cycTraps 9011 }

  cycMisCompares          OBJECT-TYPE
				     SYNTAX INTEGER
					  ACCESS read-only
					STATUS mandatory
					DESCRIPTION
				     "The number of miscompares in verify "
					  ::=  { cycTraps 9012 }
				  
	cycDriver               OBJECT-TYPE
				     SYNTAX INTEGER
					  ACCESS read-only
					STATUS mandatory
					DESCRIPTION
				     "The Driver version"
					    ::=  { cycTraps 9013 }
				  
	cycManager              OBJECT-TYPE
				     SYNTAX INTEGER
					  ACCESS read-only
					STATUS mandatory
					DESCRIPTION
				     "The CI/O Manager version"
				      ::=  { cycTraps 9014 }
				  
	cycOldArrayName           OBJECT-TYPE
				   SYNTAX DisplayString    (SIZE (1..32))
				  ACCESS read-only
					STATUS mandatory
					DESCRIPTION
				     "Old Array name"
					::=  { cycTraps 9015 }

  cycNewArrayName           OBJECT-TYPE
				   SYNTAX DisplayString    (SIZE (1..32))
				  ACCESS read-only
					STATUS mandatory
					DESCRIPTION
				     "Changed Array name"
				    ::=  { cycTraps 9016 }

  cycPriority             OBJECT-TYPE
				     SYNTAX INTEGER
					  ACCESS read-only
					STATUS mandatory
					DESCRIPTION
				     "The Priority of the operation"
					 ::=  { cycTraps 9017 }
				  
	cycSenseInfo            OBJECT-TYPE
				     SYNTAX INTEGER
					  ACCESS read-only
					STATUS mandatory
					DESCRIPTION
				     "The sense info of the PFA"
				     ::=  { cycTraps 9018 }
				  


-- This trap is generated as soon as the SNMP agent is UP.

      cycSNMPAgentIsUp                TRAP-TYPE
				       ENTERPRISE      cyclone
				 DESCRIPTION
				     "SNMP Agent is up."
				     --#TYPE      "SNMP Agent is up."
				     --#SUMMARY  "SNMP Agent is up"
				     --#ARGUMENTS {}
				     --#SEVERITY INFORMATIONAL
				     --#TIMEINDEX  100 
				     --#STATE OPERATIONAL
				     --#HELP "scsismrt.hlp"
				     --#HELPTAG 101
				  ::=  101

-- This trap is generated as soon as the SNMP agent is Down.

    cycSNMPAgentIsDown              TRAP-TYPE
				       ENTERPRISE      cyclone
				 DESCRIPTION
				     "SNMP Agent is down."
				   --#TYPE      "SNMP Agent is down."
				   --#SUMMARY  "SNMP agent is down"
				   --#ARGUMENTS {}
				   --#SEVERITY INFORMATIONAL
				   --#TIMEINDEX  100 
				   --#STATE OPERATIONAL
				   --#HELP "scsismrt.hlp"
				   --#HELPTAG 102
				  ::=  102
	
-- The following are the  Traps generated by SCSI.
		      


--This Trap is issued when ASPI database illegally contains two identical Hostadapter indices.          

	cycDuplicateHostAdapter         TRAP-TYPE
				       ENTERPRISE      cyclone
				 DESCRIPTION
				     "Cyclone: duplicate hostadapter ID"
				     --#TYPE      "duplicate hostadapter ID"
				     --#SUMMARY  "duplicate hostadapter ID"
				     --#ARGUMENTS {}
				     --#SEVERITY WARNING
				     --#TIMEINDEX  100 
				     --#STATE OPERATIONAL
				     --#HELP "scsismrt.hlp"
				     --#HELPTAG 107
				  ::= 107 

--This Trap is issued when previously unknown Host adapter if found.
		    
	cycHostAdapterDiscovered        TRAP-TYPE
				       ENTERPRISE      cyclone
				 VARIABLES {
					     cycHostAdapterNumber,
					     cycHostAdapterID,
					     cycManagerID
					    }
				       DESCRIPTION
				     "The HostAdapter# %d with HostAdapter Id %s 
				    and Manager Id %s is discovered"
				   --#TYPE "Host Adapter Discovered"
			    --#SUMMARY       "The HostAdapter# %d with HostAdapter Id %s and Manager Id %s is discovered"
				   --#ARGUMENTS {0,1,2}
				   --#SEVERITY INFORMATIONAL
				   --#TIMEINDEX  100 
				   --#STATE OPERATIONAL
				   --#HELP "scsismrt.hlp"
				   --#HELPTAG 108
				  ::= 108 

--This Trap is issued when a Host adapter is swapped for different type one.    
		
	cycHostAdapterChanged           TRAP-TYPE
				       ENTERPRISE      cyclone
				 VARIABLES {
					     cycHostAdapterNumber,
					   cycHostAdapterID,
					       cycManagerID
					    }
				       DESCRIPTION
				     "The HostAdapter# %d has new HostAdapter Id %s 
				 and Manager Id %s "
			     --#TYPE  "Host Adapter changed"
				   --#SUMMARY       "The HostAdapter# %d has new                                                   HostAdapter Id %s and Manager Id %s "
				   --#ARGUMENTS {0,1,2}
				   --#SEVERITY CRITICAL
				   --#TIMEINDEX  100 
				   --#STATE OPERATIONAL
				   --#HELP "scsismrt.hlp"
				   --#HELPTAG 109
				  ::= 109 

--This Trap is issued when a Host adapter  fails.
       
	cycHostAdapterFailed            TRAP-TYPE
				       ENTERPRISE      cyclone
				 VARIABLES {
					     cycHostAdapterNumber
				    }
				       DESCRIPTION
				     "The HostAdapter# %d has Failed"
				    --#TYPE   "Host adapter failed" 
				    --#SUMMARY       "The HostAdapter# %d has Failed"
				    --#ARGUMENTS {0}
				    --#SEVERITY CRITICAL
				    --#TIMEINDEX  100 
				    --#STATE OPERATIONAL
				    --#HELP "scsismrt.hlp"
				    --#HELPTAG 110
				  ::= 110

--This Trap is issued when a previously failed Host adapter starts working again
		 
	cycHostAdapterRecovered         TRAP-TYPE
				       ENTERPRISE      cyclone
				 VARIABLES {
					     cycHostAdapterNumber
				    }
				       DESCRIPTION
				     "Host Adapter# %d recovered"
			      --#TYPE   "Host adapter recovered"  
				   --#SUMMARY       "Host Adapter# %d recovered"
				   --#ARGUMENTS {0}
				   --#SEVERITY CRITICAL
				   --#TIMEINDEX  100 
				   --#STATE OPERATIONAL
				   --#HELP "scsismrt.hlp"
				   --#HELPTAG 111
				  ::= 111 

--This Trap is issued when a previously good device fails
		       
	cycDeviceFailed                 TRAP-TYPE
				       ENTERPRISE      cyclone
				 VARIABLES {
					     cycHostAdapterNumber,
					   cycScsiTargetID,
					    cycLun
				  }
				       DESCRIPTION
				     "The HostAdapter# %d , TargetID %d, 
				    Lun# %d has failed "
			     --#TYPE    "Device failed"  
				  --#SUMMARY "The HostAdapter# %d , TargetID %d, Lun# %d has failed "
				  --#ARGUMENTS {0,1,2}
				  --#SEVERITY CRITICAL
				  --#TIMEINDEX  100 
				  --#STATE OPERATIONAL
				  --#HELP "scsismrt.hlp"
				  --#HELPTAG 112
				  ::= 112 

--This Trap is issued when a previously unknown device is found.
			
	cycDeviceDiscovered             TRAP-TYPE
				       ENTERPRISE      cyclone
				 VARIABLES {
					     cycHostAdapterNumber,
					   cycScsiTargetID,
						cycLun,
					 cycVendor,
					      cycProduct
				      }
				       DESCRIPTION
				     "The HostAdapter# %d , TargetID %d, 
				    Lun# %d of vendor %s  product %s
					has discovered "
			       --#TYPE     "Device discovered"                       
				  --#SUMMARY       "The HostAdapter# %d , TargetID %d, Lun# %d of vendor %s  product %s has discovered "
				  --#ARGUMENTS {0,1,2,3,4}
				  --#SEVERITY INFORMATIONAL
				  --#TIMEINDEX  100 
				  --#STATE OPERATIONAL
				  --#HELP "scsismrt.hlp"
				  --#HELPTAG 113
				  ::= 113 

--This Trap is issued when a previously failed device starts working again.
	     
	cycDeviceRecovered              TRAP-TYPE
				       ENTERPRISE      cyclone
				 VARIABLES {
					     cycHostAdapterNumber,
					   cycScsiTargetID,
						cycLun
				  }
				       DESCRIPTION
				     "The HostAdapter# %d , TargetID %d, 
				    Lun# %d has recovered "
			      --#TYPE "Device recovered"  
				  --#SUMMARY "The HostAdapter# %d , TargetID %d, Lun# %d has recovered "
				  --#ARGUMENTS {0,1,2}
				  --#SEVERITY CRITICAL
				  --#TIMEINDEX  100 
				  --#STATE OPERATIONAL
				  --#HELP "scsismrt.hlp"
				  --#HELPTAG 114
				  ::= 114 

--This Trap is issued when a device is swapped for a different type.
		    
	cycDeviceChanged                TRAP-TYPE
				       ENTERPRISE      cyclone
				 VARIABLES {
					     cycHostAdapterNumber,
					   cycScsiTargetID,
					    cycLun,
					 cycVendor,
					cycProduct
				 }
				       DESCRIPTION
				     "The HostAdapter# %d , TargetID %d, 
				    Lun# %d has new Vendor %s and 
				  Product %s information "
			     --#TYPE "Device Changed"
				   --#SUMMARY "The HostAdapter# %d , TargetID %d, Lun# %d has new Vendor %s and Product %s information "
				   --#ARGUMENTS {0,1,2,3,4}
				   --#SEVERITY INFORMATIONAL
				   --#TIMEINDEX  100 
				   --#STATE OPERATIONAL
				   --#HELP "scsismrt.hlp"
				   --#HELPTAG 115
				  ::= 115 

--This Trap is issued when a PFA event occurs for a device.
     
	cycPredictiveFailure            TRAP-TYPE
				       ENTERPRISE      cyclone
				 VARIABLES {
					     cycHostAdapterNumber,
					   cycScsiTargetID,
						cycLun,
					 cycVendor,
					      cycProduct,
					     cycSenseInfo
				    }
				       DESCRIPTION
				     "The HostAdapter# %d , TargetID %d, 
				    Lun# %d has Predictive Failure Condition 
				       on vendor %s product %s with sense info
				 MSB(sense code), next  8 bits(sense code Qual)
				  next 8 bits (Add sense code Qual) LSB (0000) %d"
				   --#TYPE   "Device has SMART/Predicictive failure event"
				     --#SUMMARY       "The HostAdapter# %d , TargetID %d, Lun# %d has Predictive Failure Condition on vendor %s product %s with senseinfo %d"
				     --#ARGUMENTS {0,1,2,3,4,5}
				     --#SEVERITY INFORMATIONAL
				     --#TIMEINDEX  100 
				     --#STATE OPERATIONAL
				     --#HELP "scsismrt.hlp"
				     --#HELPTAG 116
				  ::= 116 
			
--This Trap is issued when the Aspi database is cleared
 
	cycAspiDatabaseCleared          TRAP-TYPE
				       ENTERPRISE      cyclone
				 DESCRIPTION
				     "The Aspi database is cleared and therefore 
				    all the previous information are not available"
				    --#TYPE       "The Aspi database is cleared"
				    --#SUMMARY  "The ASPI database is cleared and all the previous information are not available"              
				    --#ARGUMENTS {}
				    --#SEVERITY INFORMATIONAL
				    --#TIMEINDEX  100 
				    --#STATE OPERATIONAL
				    --#HELP "scsismrt.hlp"
				    --#HELPTAG 117
				  ::= 117 
			
--This Trap is issued when the Aspi crashes out, the user must restart Iomanager at the server
  
	cycAspiCrash            TRAP-TYPE
				       ENTERPRISE      cyclone
				 DESCRIPTION
				     "The Aspi has crashed"
				    --#TYPE       "The Aspi has crashed"
				    --#SUMMARY  "The ASPI interface module has crashed"
				    --#ARGUMENTS {}
				    --#SEVERITY CRITICAL
				    --#TIMEINDEX  100 
				    --#STATE OPERATIONAL
				    --#HELP "scsismrt.hlp"
				    --#HELPTAG 118
				  ::= 118 
			
--This Trap is issued when there is no memory for Aspi operation
	
	cycAspiNoMemory         TRAP-TYPE
				       ENTERPRISE      cyclone
				 DESCRIPTION
				     "No memory left for Aspi Operations"
				     --#TYPE       "No memory left for Aspi Operations"
				     --#SUMMARY  "No memory left for ASPI operation, internal software error"
				     --#ARGUMENTS {}
				     --#SEVERITY WARNING
				     --#TIMEINDEX  100 
				     --#STATE OPERATIONAL
				     --#HELP "scsismrt.hlp"
				     --#HELPTAG 119
				  ::= 119 
			
--This Trap is issued when it is unable to open the aspi file for writing
       
	cycAspiFileWriteOpenError       TRAP-TYPE
				       ENTERPRISE      cyclone
				 DESCRIPTION
				     "Unable to open Aspi file for writing,
				  problem exists in server hard disk"
				     --#TYPE       "Unable to open Aspi file for writing, problem exists in server hard disk"
				     --#SUMMARY  "Unable to open ASPI database file for writing"
				     --#ARGUMENTS {}
				     --#SEVERITY WARNING
				     --#TIMEINDEX  100 
				     --#STATE OPERATIONAL
				     --#HELP "scsismrt.hlp"
				     --#HELPTAG 120
				  ::= 120 
			
--This Trap is issued when it is unable to open the aspi file
   
	cycAspiFileWriteError   TRAP-TYPE
				       ENTERPRISE      cyclone
				 DESCRIPTION
				     "Unable to open Aspi file ,
				     problem exists in server hard disk"
				     --#TYPE       "Unable to open Aspi file"
				     --#SUMMARY  "Unable to open ASPI database file, problem exists in server hard disk"
				     --#ARGUMENTS {}
				     --#SEVERITY WARNING
				     --#TIMEINDEX  100 
				     --#STATE OPERATIONAL
				     --#HELP "scsismrt.hlp"
				     --#HELPTAG 121
				  ::= 121 
			
--This Trap is issued when no aspi device file exists
   
	cycAspiNoDeviceFile     TRAP-TYPE
				       ENTERPRISE      cyclone
				 DESCRIPTION
				     "Aspi device file doesnot exist"
				     --#TYPE       "Aspi device file doesnot exist"
				     --#SUMMARY  "ASPI device file does not exist"
				     --#ARGUMENTS {}
				     --#SEVERITY WARNING
				     --#TIMEINDEX  100 
				     --#STATE OPERATIONAL
				     --#HELP "scsismrt.hlp"
				     --#HELPTAG 122
				  ::= 122 
			
--This Trap is issued when aspi memory allocation is failing
    
	cycAspiNoMemoryReading  TRAP-TYPE
				       ENTERPRISE      cyclone
				 DESCRIPTION
				     "Aspi: Memory allocation is failing"
				     --#TYPE       "Aspi: Memory allocation is failing"
				     --#SUMMARY  "ASPI: memeory allocation is failing"
				     --#ARGUMENTS {}
				     --#SEVERITY WARNING
				     --#TIMEINDEX  100 
				     --#STATE OPERATIONAL
				     --#HELP "scsismrt.hlp"
				     --#HELPTAG 123
				  ::= 123 
			
--This Trap is issued when it is unable to read the aspi file
   
	cycAspiFileReadError    TRAP-TYPE
				       ENTERPRISE      cyclone
				 DESCRIPTION
				     "Aspi: unable to read the file
				  server hard disk might have problems"
				     --#TYPE       "Aspi: unable to read the database file"
				     --#SUMMARY  "ASPI: unable to read the file, server hard disk may have problems"
				     --#ARGUMENTS {}
				     --#SEVERITY WARNING
				     --#TIMEINDEX  100 
				     --#STATE OPERATIONAL
				     --#HELP "scsismrt.hlp"
				     --#HELPTAG 124
				  ::= 124 
			
--This Trap is issued when aspi database is corrupted
   
	cycAspiBadFileMagic     TRAP-TYPE
				       ENTERPRISE      cyclone
				 DESCRIPTION
				     "Aspi: database is corrupted"
				     --#TYPE       "Aspi: database is corrupted"
				     --#SUMMARY  "ASPI: database file is corrupted"
				     --#ARGUMENTS {}
				     --#SEVERITY WARNING
				     --#TIMEINDEX  100 
				     --#STATE OPERATIONAL
				     --#HELP "scsismrt.hlp"
				     --#HELPTAG 125
				  ::= 125 
			
-- The Following object and trap definitions are from the AMI NetRaid application

rtAdapterNumber  OBJECT-TYPE
	SYNTAX  INTEGER
	ACCESS  read-only
	STATUS  mandatory
	DESCRIPTION
		"Adapter Number for which Trap is generated."
::= { raidTraps 1001 }

rtLogicalDriveNumber  OBJECT-TYPE
	SYNTAX  INTEGER
	ACCESS  read-only
	STATUS  mandatory
	DESCRIPTION
		"Logical Drive Number for which Trap is generated."
::= { raidTraps 1002 }

rtChannelNumber  OBJECT-TYPE
	SYNTAX  INTEGER
	ACCESS  read-only
	STATUS  mandatory
	DESCRIPTION
		"Channel Number on the Adapter for which Trap is Generated."
::= { raidTraps 1003 }

rtTargetID  OBJECT-TYPE
	SYNTAX  INTEGER
	ACCESS  read-only
	STATUS  mandatory
	DESCRIPTION
		"Device ID of the Physical Drive for which Trap is Generated."
::= { raidTraps 1004 }

rtOldDriveState  OBJECT-TYPE
	SYNTAX  DisplayString
	ACCESS  read-only
	STATUS  mandatory
	DESCRIPTION
		"Old State of Logical/Physical Drive, when a State Change Trap
		is Generated."
::= { raidTraps 1005 }

rtNewDriveState  OBJECT-TYPE
	SYNTAX  DisplayString
	ACCESS  read-only
	STATUS  mandatory
	DESCRIPTION
		"New State of Logical/Physical Drive, when a State Change Trap
		is Generated."
::= { raidTraps 1006 }

rtSenseKey  OBJECT-TYPE
	SYNTAX  INTEGER
	ACCESS  read-only
	STATUS  mandatory
	DESCRIPTION
		"Check Condition Sense-Key reported by Physical Drive for which
		Trap is Generated."
::= { raidTraps 1007 }

rtASC  OBJECT-TYPE
	SYNTAX  INTEGER
	ACCESS  read-only
	STATUS  mandatory
	DESCRIPTION
		"Check Condition Additional Sense Code (ASC) reported by Physical
		Drive for which Trap is Generated."
::= { raidTraps 1008 }
rtASCQ  OBJECT-TYPE
	SYNTAX  INTEGER
	ACCESS  read-only
	STATUS  mandatory
	DESCRIPTION
		"Check Condition Additional Sense Code Qualifier (ASCQ) reported by
		Physical Drive for which Trap is Generated."
::= { raidTraps 1009 }

rtDriveVendor  OBJECT-TYPE
	SYNTAX  DisplayString
	ACCESS  read-only
	STATUS  mandatory
	DESCRIPTION
		"Vendor Identification String from the SCSI Inquiry Data for the
		Drive."
::= { raidTraps 1010 }
rtConfigUpdated TRAP-TYPE
	ENTERPRISE raidTraps
	VARIABLES { rtAdapterNumber }
	DESCRIPTION
		"Adapter-%d: A New Configuration has been written."
	--#TYPE "RAID Trap: Configuration Updated"
	--#SUMMARY "Host Adapter-%d: A New Configuration has been written."
	--#ARGUMENTS { 0 }
	--#SEVERITY INFORMATIONAL
	--#TIMEINDEX    100
	--#STATE OPERATIONAL
	::= 9001

rtPhysicalDriveStateChange TRAP-TYPE
	ENTERPRISE raidTraps
	VARIABLES 
		{ 
		rtAdapterNumber,
		rtChannelNumber,
		rtTargetID,
		rtOldDriveState,
		rtNewDriveState
		}
	DESCRIPTION
		"Adapter-%d, Channel-%d, Target-%d: Drive State Changed from %s to %s."
	--#TYPE "RAID Trap: Physical Drive State Change"
	--#SUMMARY "Adapter-%d, Channel-%d, Target-%d: Drive State Changed from %s to %s."
	--#ARGUMENTS { 0, 1, 2, 3, 4 }
	--#SEVERITY INFORMATIONAL
	--#STATE OPERATIONAL
	::= 9002

rtLogicalDriveStateChange TRAP-TYPE
	ENTERPRISE raidTraps
	VARIABLES 
		{ 
		rtAdapterNumber,
		rtLogicalDriveNumber,
		rtOldDriveState,
		rtNewDriveState
		}
	DESCRIPTION
		"Adapter-%d, Logical Drive-%d: State Changed from %s to %s."
	--#TYPE "RAID Trap: Logical Drive State Change"
	--#SUMMARY "Adapter-%d, Logical Drive-%d: State Changed from %s to %s."
	--#ARGUMENTS { 0, 1, 2, 3 }
	--#SEVERITY INFORMATIONAL
	--#STATE OPERATIONAL
	::= 9003

rtInitializeStarted TRAP-TYPE
	ENTERPRISE raidTraps
	VARIABLES 
		{ 
		rtAdapterNumber,
		rtLogicalDriveNumber
		}
	DESCRIPTION
		"Adapter-%d, Logical Drive-%d: Initialization Started."
	--#TYPE "RAID Trap: Initialize Started"
	--#SUMMARY "Adapter-%d, Logical Drive-%d: Initialization Started."
	--#ARGUMENTS { 0, 1 }
	--#SEVERITY INFORMATIONAL
	--#STATE OPERATIONAL
	::= 9004

rtInitializeCompleted TRAP-TYPE
	ENTERPRISE raidTraps
	VARIABLES 
		{ 
		rtAdapterNumber,
		rtLogicalDriveNumber
		}
	DESCRIPTION
		"Adapter-%d, Logical Drive-%d: Initialization Completed Successfully."
	--#TYPE "RAID Trap: Initialize Completed"
	--#SUMMARY "Adapter-%d, Logical Drive-%d: Initialization Completed Successfully."
	--#ARGUMENTS { 0, 1 }
	--#SEVERITY INFORMATIONAL
	--#STATE OPERATIONAL
	::= 9005

rtInitializeAborted TRAP-TYPE
	ENTERPRISE raidTraps
	VARIABLES 
		{ 
		rtAdapterNumber,
		rtLogicalDriveNumber
		}
	DESCRIPTION
		"Adapter-%d, Logical Drive-%d: Initialization Aborted by User."
	--#TYPE "RAID Trap: Initialize Aborted"
	--#SUMMARY "Adapter-%d, Logical Drive-%d: Initialization Aborted by User."
	--#ARGUMENTS { 0, 1 }
	--#SEVERITY INFORMATIONAL
	--#STATE OPERATIONAL
	::= 9006

rtInitializeFailed TRAP-TYPE
	ENTERPRISE raidTraps
	VARIABLES 
		{ 
		rtAdapterNumber,
		rtLogicalDriveNumber
		}
	DESCRIPTION
		"Adapter-%d, Logical Drive-%d: Initialization Failed."
	--#TYPE "RAID Trap: Initialize Failed"
	--#SUMMARY "Adapter-%d, Logical Drive-%d: Initialization Failed."
	--#ARGUMENTS { 0, 1 }
	--#SEVERITY INFORMATIONAL
	--#STATE OPERATIONAL
	::= 9007

rtCheckConsistencyStarted TRAP-TYPE
	ENTERPRISE raidTraps
	VARIABLES 
		{ 
		rtAdapterNumber,
		rtLogicalDriveNumber
		}
	DESCRIPTION
		"Adapter-%d, Logical Drive-%d: Check Consistency Started."
	--#TYPE "RAID Trap: Check Consistency Started"
	--#SUMMARY "Adapter-%d, Logical Drive-%d: Check Consistency Started."
	--#ARGUMENTS { 0, 1 }
	--#SEVERITY INFORMATIONAL
	--#STATE OPERATIONAL
	::= 9008

rtCheckConsistencyCompleted TRAP-TYPE
	ENTERPRISE raidTraps
	VARIABLES 
		{ 
		rtAdapterNumber,
		rtLogicalDriveNumber
		}
	DESCRIPTION
		"Adapter-%d, Logical Drive-%d: Check Consistency Completed. No 
		Inconsistencies Found."
	--#TYPE "RAID Trap: Check Consistency Completed"
	--#SUMMARY "Adapter-%d, Logical Drive-%d: Check Consistency Completed. No"
	--#SUMMARY "Inconsistencies Found."
	--#ARGUMENTS { 0, 1 }
	--#SEVERITY INFORMATIONAL
	--#STATE OPERATIONAL
	::= 9009

rtCheckConsistencyAborted TRAP-TYPE
	ENTERPRISE raidTraps
	VARIABLES 
		{ 
		rtAdapterNumber,
		rtLogicalDriveNumber
		}
	DESCRIPTION
		"Adapter-%d, Logical Drive-%d: Check Consistency Aborted by User."
	--#TYPE "RAID Trap: Check Consistency Aborted"
	--#SUMMARY "Adapter-%d, Logical Drive-%d: Check Consistency Aborted by User."
	--#ARGUMENTS { 0, 1 }
	--#SEVERITY INFORMATIONAL
	--#STATE OPERATIONAL
	::= 9010

rtConsistencyCorrected TRAP-TYPE
	ENTERPRISE raidTraps
	VARIABLES 
		{ 
		rtAdapterNumber,
		rtLogicalDriveNumber
		}
	DESCRIPTION
		"Adapter-%d, Logical Drive-%d: Check Consistency Operation Completed. 
		Inconsistencies have been Cured." 
	--#TYPE "RAID Trap: Check Consistency Corrected"
	--#SUMMARY "Adapter-%d, Logical Drive-%d: Check Consistency Operation"
	--#SUMMARY "Completed. Inconsistencies have been Cured." 
	--#ARGUMENTS { 0, 1 }
	--#SEVERITY INFORMATIONAL
	--#STATE OPERATIONAL
	::= 9011

rtCheckConsistencyFailed TRAP-TYPE
	ENTERPRISE raidTraps
	VARIABLES 
		{ 
		rtAdapterNumber,
		rtLogicalDriveNumber
		}
	DESCRIPTION
		"Adapter-%d, Logical Drive-%d: Check Consistency Failed."
	--#TYPE "RAID Trap: Check Consistency Failed"
	--#SUMMARY "Adapter-%d, Logical Drive-%d: Check Consistency Failed."
	--#ARGUMENTS { 0, 1 }
	--#SEVERITY INFORMATIONAL
	--#STATE OPERATIONAL
	::= 9012

rtReconstructionStarted TRAP-TYPE
	ENTERPRISE raidTraps
	VARIABLES 
		{ 
		rtAdapterNumber,
		rtLogicalDriveNumber
		}
	DESCRIPTION
		"Adapter-%d, Logical Drive-%d: Reconstruction Started."
	--#TYPE "RAID Trap: Reconstruction Started"
	--#SUMMARY "Adapter-%d, Logical Drive-%d: Reconstruction Started."
	--#ARGUMENTS { 0, 1 }
	--#SEVERITY INFORMATIONAL
	--#STATE OPERATIONAL
	::= 9013

rtReconstructionCompleted TRAP-TYPE
	ENTERPRISE raidTraps
	VARIABLES 
		{ 
		rtAdapterNumber,
		rtLogicalDriveNumber
		}
	DESCRIPTION
		"Adapter-%d, Logical Drive-%d: Reconstruction Completed Successfully."
	--#TYPE "RAID Trap: Reconstruction Completed"
	--#SUMMARY "Adapter-%d, Logical Drive-%d: Reconstruction Completed Successfully."
	--#ARGUMENTS { 0, 1 }
	--#SEVERITY INFORMATIONAL
	--#STATE OPERATIONAL
	::= 9014

rtReconstructionFailed TRAP-TYPE
	ENTERPRISE raidTraps
	VARIABLES 
		{ 
		rtAdapterNumber,
		rtLogicalDriveNumber
		}
	DESCRIPTION
		"Adapter-%d, Logical Drive-%d: Reconstruction Failed."
	--#TYPE "RAID Trap: Reconstruction Failed"
	--#SUMMARY "Adapter-%d, Logical Drive-%d: Reconstruction Failed."
	--#ARGUMENTS { 0, 1 }
	--#SEVERITY INFORMATIONAL
	--#STATE OPERATIONAL
	::= 9015

rtPredictiveFailuresFalse TRAP-TYPE
	ENTERPRISE raidTraps
	VARIABLES 
		{ 
		rtAdapterNumber,
		rtChannelNumber,
		rtTargetID,
		rtDriveVendor,
		rtSenseKey,
		rtASC,
		rtASCQ
		}
	DESCRIPTION
		"Adapter-%d, Channel-%d, Target-%d: Reported Failure Prediction
		Threshold Exceeded [FALSE].
		Drive Identification String = %s
		Sense Key = 0x%x, ASC = 0x%x, ASCQ = 0x%x."
	--#TYPE "RAID Trap: Physical Drive Predictive Failures [FALSE]"
	--#SUMMARY "Adapter-%d, Channel-%d, Target-%d: Reported Predictive 
	--#SUMMARY "Failure. (Failure Prediction Threshold Exceeded [FALSE])"
	--#SUMMARY "Drive Identification String = %s"
	--#SUMMARY "Sense Key = 0x%x, ASC = 0x%x, ASCQ = 0x%x."
	--#ARGUMENTS { 0, 1, 2, 3, 4, 5, 6 }
	--#SEVERITY INFORMATIONAL
	--#STATE OPERATIONAL
	::= 9016

rtPredictiveFailuresExceeded TRAP-TYPE
	ENTERPRISE raidTraps
	VARIABLES 
		{ 
		rtAdapterNumber,
		rtChannelNumber,
		rtTargetID,
		rtDriveVendor,
		rtSenseKey,
		rtASC,
		rtASCQ
		}
	DESCRIPTION
		"Adapter-%d, Channel-%d, Target-%d: Reported Predictive Failure.
		Drive Identification String = %s
		Sense Key = 0x%x, ASC = 0x%x, ASCQ = 0x%x."
	--#TYPE "RAID Trap: Physical Drive Failure Prediction Threshold Exceeded"
	--#SUMMARY "Adapter-%d, Channel-%d, Target-%d: Reported Predictive 
	--#SUMMARY "Failure. (Failure Threshold Exceeded)"
	--#SUMMARY "Drive Identification String = %s"
	--#SUMMARY "Sense Key = 0x%x, ASC = 0x%x, ASCQ = 0x%x."
	--#ARGUMENTS { 0, 1, 2, 3, 4, 5, 6 }
	--#SEVERITY INFORMATIONAL
	--#STATE OPERATIONAL
	::= 9017


rtCheckConditionStatus TRAP-TYPE
	ENTERPRISE raidTraps
	VARIABLES 
		{ 
		rtAdapterNumber,
		rtChannelNumber,
		rtTargetID,
		rtSenseKey,
		rtASC,
		rtASCQ
		}
	DESCRIPTION
		"Adapter-%d, Channel-%d, Target-%d: Command Completed with 
		Sense_Key-0x%x ASC-0x%x ASCQ-0x%x."
	--#TYPE "RAID Trap: Physical Drive Check Conditions"
	--#SUMMARY "Adapter-%d, Channel-%d, Target-%d: Command Completed with"
	--#SUMMARY "Sense_Key-0x%x ASC-0x%x ASCQ-0x%x."
	--#ARGUMENTS { 0, 1, 2, 3, 4, 5 }
	--#SEVERITY INFORMATIONAL
	--#STATE OPERATIONAL
	::= 9018

rtNewDriveInserted TRAP-TYPE
	ENTERPRISE raidTraps
	VARIABLES 
		{ 
		rtAdapterNumber,
		rtChannelNumber,
		rtTargetID
		}
	DESCRIPTION
		"Adapter-%d, Channel-%d, Target-%d: New Device Inserted."
	--#TYPE "RAID Trap: New Drive Inserted"
	--#SUMMARY "Adapter-%d, Channel-%d, Target-%d: New Device Inserted."
	--#ARGUMENTS { 0, 1, 2 }
	--#SEVERITY INFORMATIONAL
	--#STATE OPERATIONAL
	::= 9019

rtBatteryMissing TRAP-TYPE
	ENTERPRISE raidTraps
	VARIABLES 
		{ rtAdapterNumber }
	DESCRIPTION
		"Adapter-%d: Battery Module is missing."
	--#TYPE "RAID Trap: Battery Missing"
	--#SUMMARY "Adapter-%d: Battery Module is missing."
	--#ARGUMENTS { 0 }
	--#SEVERITY INFORMATIONAL
	--#STATE OPERATIONAL
	::= 9020

rtBatteryVolatageLow TRAP-TYPE
	ENTERPRISE raidTraps
	VARIABLES 
		{ rtAdapterNumber }
	DESCRIPTION
		"Adapter-%d: Battery Module Voltage is Low."
	--#TYPE "RAID Trap: Battery Voltage Low"
	--#SUMMARY "Adapter-%d: Battery Module Voltage is Low."
	--#ARGUMENTS { 0 }
	--#SEVERITY INFORMATIONAL
	--#STATE OPERATIONAL
	::= 9021

rtBatteryTemperatureHigh TRAP-TYPE
	ENTERPRISE raidTraps
	VARIABLES 
		{ rtAdapterNumber }
	DESCRIPTION
		"Adapter-%d: Battery Module Temperature Exceeded Danger Threshold."
	--#TYPE "RAID Trap: Battery Temperature High"
	--#SUMMARY "Adapter-%d: Battery Module Temperature Exceeded Danger Threshold."
	--#ARGUMENTS { 0 }
	--#SEVERITY INFORMATIONAL
	--#STATE OPERATIONAL
	::= 9022
--
-- End of HP NetServer Assistant trap definition file
--

END

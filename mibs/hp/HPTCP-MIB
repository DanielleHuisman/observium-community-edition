HPTCP-MIB DEFINITIONS ::= BEGIN

    IMPORTS
        hpSwitch            
            FROM HP-ICF-OID            
        OBJECT-GROUP, MODULE-COMPLIANCE            
            FROM SNMPv2-CONF            
    Counter32, OBJECT-TYPE, MODULE-IDENTITY            
            FROM SNMPv2-SMI;
            
-- 1.3.6.1.4.1.11.2.14.11.5.1.79
    hpicfTcpMib MODULE-IDENTITY
    LAST-UPDATED "201009301525Z"
        ORGANIZATION "HP Networking"
        CONTACT-INFO 
            "Hewlett-Packard Company
            8000 Foothills Blvd.
            Roseville, CA 95747"
        DESCRIPTION 
            "This MIB module contains HP proprietary
            objects for monitoring TCP traffic"
    REVISION "201009301525Z"
    DESCRIPTION
           "Added hpicfTcpMib and associated objects."
    ::= {hpSwitch 79}


    -- 1.3.6.1.4.1.11.2.14.11.5.1.79.1
    hpTcpObjects OBJECT IDENTIFIER ::= { hpicfTcpMib 1 }

    hpTcpOutRstsWithAck OBJECT-TYPE
             SYNTAX  Counter32
             MAX-ACCESS  read-only
             STATUS current
             DESCRIPTION
                     "The number of TCP packets
                     sent containing the RST and the ACK flags.
                     This is useful to detect SYN packets sent
                     to closed ports."
             ::= { hpTcpObjects 1 }

    -- 1.3.6.1.4.1.11.2.14.11.5.1.79.2
    hpTcpConformance OBJECT IDENTIFIER ::= { hpicfTcpMib 2 }

    -- 1.3.6.1.4.1.11.2.14.11.5.1.79.2.1
    hpTcpGroups OBJECT IDENTIFIER ::= { hpTcpConformance 1 }

    -- 1.3.6.1.4.1.11.2.14.11.5.1.79.2.1.1
    hpTcpBaseGroup OBJECT-GROUP
    OBJECTS {hpTcpOutRstsWithAck }
        STATUS current
        DESCRIPTION 
            "A collection of proprietary objects for monitoring the
            TCP connections."
        ::= { hpTcpGroups 1 }

    
    -- 1.3.6.1.4.1.11.2.14.11.5.1.79.2.2
    hpTcpCompliances OBJECT IDENTIFIER ::= { hpTcpConformance 2 }

    
    -- 1.3.6.1.4.1.11.2.14.11.5.1.37.2.2.1
    hpTcpCompliance MODULE-COMPLIANCE
        STATUS current
        DESCRIPTION 
            "The compliance statement for HP switches
            that support Dynamic ARP Protection."
        MODULE -- this module
            MANDATORY-GROUPS { hpTcpBaseGroup }
        ::= { hpTcpCompliances 1 }
END

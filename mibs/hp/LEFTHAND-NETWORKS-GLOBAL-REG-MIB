-- ****************************************************************************
-- LEFTHAND-NETWORKS-GLOBAL-REG-MIB
-- Management Information Base for SNMP Network Management
--
-- This MIB provides registrations for all LeftHand Networks products.
--
-- This MIB must be loaded before any other LEFTHAND-NETWORKS MIBs.
--
-- The LeftHand Networks Enterprise number is 9804.
-- The ASN.1 prefix to, and including the LeftHand Networks Enterprise is:
--     1.3.6.1.4.1.9804
-- ****************************************************************************
-- Copyright 2009,2010 Hewlett-Packard Development Company, L.P.
-- Copyright 2008,2009 LeftHand Networks, Inc.
-- All Rights Reserved.
--
-- Hewlett-Packard Company shall not be liable for technical or
-- editorial errors or omissions contained herein. The information in
-- this document is provided "as is" without warranty of any kind and
-- is subject to change without notice. The warranties for HP products
-- are set forth in the express limited warranty statements
-- accompanying such products. Nothing herein should be construed as
-- constituting an additional warranty.
--
-- Confidential computer software. Valid license from HP required for
-- possession, use or copying. Consistent with FAR 12.211 and 12.212,
-- Commercial Computer Software, Computer Software Documentation, and
-- Technical Data for Commercial Items are licensed to the U.S.
-- Government under vendor's standard commercial license.
-- ****************************************************************************

LEFTHAND-NETWORKS-GLOBAL-REG-MIB DEFINITIONS ::= BEGIN

IMPORTS
	MODULE-IDENTITY, OBJECT-IDENTITY, enterprises
		FROM SNMPv2-SMI;

lhnMIB MODULE-IDENTITY
    LAST-UPDATED        "201311210000Z"
    ORGANIZATION        "Hewlett Packard Company, StorageWorks Division"
    CONTACT-INFO        "Product Support
                         Product URL: www.hp.com/go/p4000
                         Support URL: www.itrc.hp.com
                         Product Phone: www.hp.com/go/contact
                                        1-800-786-7967 (US only)
                         Support Phone: www.hp.com/go/contact
                                        1-800-334-5144 (US only)"
    DESCRIPTION         "This MIB defines the registrations for the
                         HP StorageWorks P4000 products."

    REVISION            "201311210000Z"
    DESCRIPTION         "SAN/iQ 7.0, SAN/iQ 8.0, SAN/iQ 8.1, SAN/iQ 8.5, SAN/iQ 9.0, SAN/iQ 9.5, SAN/iQ 10.0, SAN/iQ 10.5, SAN/iQ 11.0, SAN/iQ 11.5"

    REVISION            "201306250000Z"
    DESCRIPTION         "SAN/iQ 7.0, SAN/iQ 8.0, SAN/iQ 8.1, SAN/iQ 8.5, SAN/iQ 9.0, SAN/iQ 9.5, SAN/iQ 10.0, SAN/iQ 10.5, SAN/iQ 11.0"

    REVISION            "201209040000Z"
    DESCRIPTION         "SAN/iQ 7.0, SAN/iQ 8.0, SAN/iQ 8.1, SAN/iQ 8.5, SAN/iQ 9.0, SAN/iQ 9.5, SAN/iQ 10.0"

    REVISION            "201106210000Z"
    DESCRIPTION         "SAN/iQ 7.0, SAN/iQ 8.0, SAN/iQ 8.1, SAN/iQ 8.5, SAN/iQ 9.0, SAN/iQ 9.5"

    REVISION            "201009070000Z"
    DESCRIPTION         "SAN/iQ 7.0, SAN/iQ 8.0, SAN/iQ 8.1, SAN/iQ 8.5, SAN/iQ 9.0"

    REVISION            "201007190000Z"
    DESCRIPTION         "SAN/iQ 7.0, SAN/iQ 8.0, SAN/iQ 8.1, SAN/iQ 8.5 with patch 10076"

    REVISION            "200911200000Z"
    DESCRIPTION         "SAN/iQ 7.0, SAN/iQ 8.0, SAN/iQ 8.1, SAN/iQ 8.5"

    REVISION            "200903100000Z"
    DESCRIPTION         "SAN/iQ 7.0, SAN/iQ 8.0, SAN/iQ 8.1"

    REVISION            "200801240000Z"
    DESCRIPTION         "SAN/iQ 7.0, SAN/iQ 8.0
						Updated object names to use current product branding.
						Added conformance and compliance objects.
						Updated the MIB for increased client compatability."

	::= { lefthandnetworks 1 }

lefthandnetworks OBJECT IDENTIFIER ::= { enterprises 9804 }

lhnMIBNotifications OBJECT IDENTIFIER ::= { lhnMIB 0 }

lhnMIBObjects OBJECT IDENTIFIER ::= { lhnMIB 1 }

lhnMIBConformance OBJECT IDENTIFIER ::= { lhnMIB 2 }

	lhnMIBCompliances OBJECT IDENTIFIER ::= { lhnMIBConformance 1 }

	lhnMIBGroups OBJECT IDENTIFIER ::= { lhnMIBConformance 2 }

lefthandnetworksRegistrations OBJECT IDENTIFIER ::= { lefthandnetworks 2 }

	lhnModules OBJECT-IDENTITY
		STATUS              current
		DESCRIPTION         "The sub-tree for MIB module registrations."
		::= { lefthandnetworksRegistrations 1 }

lefthandnetworksProducts OBJECT IDENTIFIER ::= { lefthandnetworks 3 }

	lhnNsm OBJECT-IDENTITY
		STATUS              current
		DESCRIPTION         "The sub-tree for NSM devices."
		::= { lefthandnetworksProducts 1 }

END

-- END: some MIB compilers require a CR/LF after the END statement --

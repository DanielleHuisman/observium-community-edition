-- ****************************************************************************
-- LEFTHAND-NETWORKS-NSM-MIB
-- Management Information Base for SNMP Network Management
--
-- This MIB provides registrations for all LeftHand Networks NSMs.
--
-- This MIB must be loaded after:
--                                LEFTHAND-NETWORKS-GLOBAL-REG-MIB.mib
--
-- The LeftHand Networks Enterprise number is 9804.
-- The ASN.1 prefix to, and including the LeftHand Networks Enterprise is:
--     1.3.6.1.4.1.9804
-- ****************************************************************************
-- Copyright 2009,2010 Hewlett-Packard Development Company, L.P.
-- Copyright 2008,2009 LeftHand Networks, Inc.
-- All Rights Reserved.
--
-- Hewlett-Packard Company shall not be liable for technical or
-- editorial errors or omissions contained herein. The information in
-- this document is provided "as is" without warranty of any kind and
-- is subject to change without notice. The warranties for HP products
-- are set forth in the express limited warranty statements
-- accompanying such products. Nothing herein should be construed as
-- constituting an additional warranty.
--
-- Confidential computer software. Valid license from HP required for
-- possession, use or copying. Consistent with FAR 12.211 and 12.212,
-- Commercial Computer Software, Computer Software Documentation, and
-- Technical Data for Commercial Items are licensed to the U.S.
-- Government under vendor's standard commercial license.
-- ****************************************************************************

LEFTHAND-NETWORKS-NSM-MIB DEFINITIONS ::= BEGIN

IMPORTS
	MODULE-IDENTITY, OBJECT-IDENTITY
		FROM SNMPv2-SMI
	lhnModules, lhnNsm
		FROM LEFTHAND-NETWORKS-GLOBAL-REG-MIB;

--
-- The lhnNsmMib module defines the MIB modules that are used.
--
lhnNsmMib MODULE-IDENTITY
    LAST-UPDATED        "201311220000Z"
    ORGANIZATION        "Hewlett Packard Company, StorageWorks Division"
    CONTACT-INFO        "Product Support
                         Product URL: www.hp.com/go/p4000
                         Support URL: www.itrc.hp.com
                         Product Phone: www.hp.com/go/contact
                                        1-800-786-7967 (US only)
                         Support Phone: www.hp.com/go/contact
                                        1-800-334-5144 (US only)"
    DESCRIPTION         "This MIB defines the product registrations for the
                         HP StorageWorks P4000 products."

    REVISION            "201311220000Z"
    DESCRIPTION         "SAN/iQ 7.0, SAN/iQ 8.0, SAN/iQ 8.1, SAN/iQ 8.5, SAN/iQ 9.0, SAN/iQ 9.5, SAN/iQ 10.0, SAN/iQ 10.5, SAN/iQ 11.0, SAN/iQ 11.5"

    REVISION            "201306250000Z"
    DESCRIPTION         "SAN/iQ 7.0, SAN/iQ 8.0, SAN/iQ 8.1, SAN/iQ 8.5, SAN/iQ 9.0, SAN/iQ 9.5, SAN/iQ 10.0, SAN/iQ 10.5, SAN/iQ 11.0"

    REVISION            "201209040000Z"
    DESCRIPTION         "SAN/iQ 7.0, SAN/iQ 8.0, SAN/iQ 8.1, SAN/iQ 8.5, SAN/iQ 9.0, SAN/iQ 9.5, SAN/iQ 10.0"

    REVISION            "201106210000Z"
    DESCRIPTION         "SAN/iQ 7.0, SAN/iQ 8.0, SAN/iQ 8.1, SAN/iQ 8.5, SAN/iQ 9.0, SAN/iQ 9.5"

    REVISION            "201009070000Z"
    DESCRIPTION         "SAN/iQ 7.0, SAN/iQ 8.0, SAN/iQ 8.1, SAN/iQ 8.5, SAN/iQ 9.0"

    REVISION            "201007190000Z"
    DESCRIPTION         "SAN/iQ 7.0, SAN/iQ 8.0, SAN/iQ 8.1, SAN/iQ 8.5 with patch 10076"

    REVISION            "200911200000Z"
    DESCRIPTION         "SAN/iQ 7.0, SAN/iQ 8.0, SAN/iQ 8.1, SAN/iQ 8.5
						Fixed an issue with lhnNsmEvents that prevented the used of SNMP v1 Traps."

    REVISION            "200903100000Z"
    DESCRIPTION         "SAN/iQ 7.0, SAN/iQ 8.0, SAN/iQ 8.1"

    REVISION            "200801240000Z"
    DESCRIPTION         "SAN/iQ 7.0, SAN/iQ 8.0
						Added:
							lhnNsmEvents
						Updated object names to use current product branding.
						Added conformance and compliance objects.
						Updated the MIB for increased client compatability."

	::= { lhnModules 1 }

--
-- lefthandnetworksProducts.lhnNsm.lhnNsmDevices
--
lhnNsmDevices OBJECT-IDENTITY
	STATUS              current
	DESCRIPTION         "sub-tree for NSM devices"
	::= { lhnNsm 1 }

--
-- lefthandnetworksProducts.lhnNsm.lhnNsmDevices.lhnNsmEvents
--
lhnNsmEvents OBJECT-IDENTITY
	STATUS              current
	DESCRIPTION         "sub-tree for NSM events"
	::= { lhnNsmDevices 0 }

--
-- lefthandnetworksProducts.lhnNsm.lhnNsmDevices.lhnNsmCommon
--
lhnNsmCommon OBJECT-IDENTITY
	STATUS              obsolete
	DESCRIPTION         "sub-tree for common NSM information"
	::= { lhnNsmDevices 1 }

--
-- lefthandnetworksProducts.lhnNsm.lhnNsmDevices.lhnNsmCommon.lhnNsmObjects
--
lhnNsmObjects OBJECT-IDENTITY
	STATUS              current
	DESCRIPTION         "sub-tree for NSM objects"
	::= { lhnNsmDevices 2 }

	-- lefthandnetworksProducts.lhnNsm.lhnNsmDevices.lhnNsmCommon.lhnNsmObjects.lhnNsmInfo
	lhnNsmInfo OBJECT-IDENTITY
		STATUS              current
		DESCRIPTION         "sub-tree for NSM hardware information"
		::= { lhnNsmObjects 1 }

	-- lefthandnetworksProducts.lhnNsm.lhnNsmDevices.lhnNsmCommon.lhnNsmObjects.lhnNsmNetwork
	lhnNsmNetwork OBJECT-IDENTITY
		STATUS              current
		DESCRIPTION         "sub-tree for NSM network information"
		::= { lhnNsmObjects 2 }

	-- lefthandnetworksProducts.lhnNsm.lhnNsmDevices.lhnNsmCommon.lhnNsmObjects.lhnNsmDNS
	lhnNsmDNS OBJECT-IDENTITY
		STATUS              current
		DESCRIPTION         "sub-tree for NSM DNS information"
		::= { lhnNsmObjects 3 }

	-- lefthandnetworksProducts.lhnNsm.lhnNsmDevices.lhnNsmCommon.lhnNsmObjects.lhnNsmStorage
	lhnNsmStorage OBJECT-IDENTITY
		STATUS              current
		DESCRIPTION         "sub-tree for NSM storage information"
		::= { lhnNsmObjects 4 }

	-- lefthandnetworksProducts.lhnNsm.lhnNsmDevices.lhnNsmCommon.lhnNsmObjects.lhnNsmNTP
	lhnNsmNTP OBJECT-IDENTITY
		STATUS              current
		DESCRIPTION         "sub-tree for NSM NTP information"
		::= { lhnNsmObjects 5 }

	-- lefthandnetworksProducts.lhnNsm.lhnNsmDevices.lhnNsmCommon.lhnNsmObjects.lhnNsmSecurity
	lhnNsmSecurity OBJECT-IDENTITY
		STATUS              current
		DESCRIPTION         "sub-tree for NSM security information"
		::= { lhnNsmObjects 11 }

	-- lefthandnetworksProducts.lhnNsm.lhnNsmDevices.lhnNsmCommon.lhnNsmObjects.lhnNsmClustering
	lhnNsmClustering OBJECT-IDENTITY
		STATUS              current
		DESCRIPTION         "sub-tree for NSM clustering information"
		::= { lhnNsmObjects 12 }

    -- lefthandnetworksProducts.lhnNsm.lhnNsmDevices.lhnNsmCommon.lhnNsmObjects.lhnNsmOldNotification
    lhnNsmOldNotification OBJECT-IDENTITY
        STATUS              current
        DESCRIPTION         "sub-tree for NSM notifications from SAN/iQ 8.1 and earlier"
        ::= { lhnNsmObjects 13 }

	-- lefthandnetworksProducts.lhnNsm.lhnNsmDevices.lhnNsmCommon.lhnNsmObjects.lhnNsmNotification
	lhnNsmNotification OBJECT-IDENTITY
		STATUS              current
		DESCRIPTION         "sub-tree for NSM notifications"
		::= { lhnNsmObjects 15 }

	-- lefthandnetworksProducts.lhnNsm.lhnNsmDevices.lhnNsmCommon.lhnNsmObjects.lhnNsmStatus
	lhnNsmStatus OBJECT-IDENTITY
		STATUS              current
		DESCRIPTION         "sub-tree for NSM SNMP agent status"
		::= { lhnNsmObjects 99 }

--
-- lefthandnetworksProducts.lhnNsm.lhnNsmDevices.lhnNsmOldEvents
--
lhnNsmOldEvents OBJECT-IDENTITY
	STATUS              current
	DESCRIPTION         "sub-tree for NSM events from SAN/iQ 8.1 and earlier"
	::= { lhnNsmDevices 3 }

END

-- END: some MIB compilers require a CR/LF after the END statement --

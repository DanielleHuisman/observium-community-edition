LEFTHAND-NETWORKS-NUS-COMMON-NOTIFICATION-MIB DEFINITIONS ::= BEGIN

-- IMPORTS: Include definitions from other mibs here, which is always
-- the first item in a MIB file.
IMPORTS
    MODULE-IDENTITY, NOTIFICATION-TYPE				FROM SNMPv2-SMI
	 OBJECT-TYPE											FROM RFC-1212
    NOTIFICATION-GROUP        FROM SNMPv2-CONF
    DateAndTime                                  FROM SNMPv2-TC
    lhnModules                                   FROM LEFTHAND-NETWORKS-GLOBAL-REG
    lhnNusCommonNotification,
    lhnNusCommonEvents, lhnNusCommonGroups       FROM LEFTHAND-NETWORKS-NUS-COMMON-MIB;

--
-- A brief description and update information about this mib.
--
lhnNusCommonNotificationModule MODULE-IDENTITY
    LAST-UPDATED "0206250000Z"
    ORGANIZATION "LeftHand Networks, Inc."
    CONTACT-INFO "
                  Author:     Jose Faria
                              LeftHand Networks
                  postal:     1688 Conestoga St.
                              Boulder, CO 80301
                              USA
                  email:      jfaria@lefthandnetworks.com
                  phone:      +1 303 449-4100
                 "
    DESCRIPTION  "Notification (Trap) items for NUS Devices"
    ::= { lhnModules 15 }

-- *********************************************************************************
--
-- Notification Objects
--
-- *********************************************************************************
notificationMessageCount OBJECT-TYPE
    SYNTAX      INTEGER
    MAX-ACCESS  read-only
    STATUS      current
    DESCRIPTION "number of notification messages"
    ::= { lhnNusCommonNotification 1 }

notificationMessageTable OBJECT-TYPE
    SYNTAX      SEQUENCE OF NotificationMessageEntry
    MAX-ACCESS  not-accessible
    STATUS      current
    DESCRIPTION
	"A table of notification messages for the NUS.
	 The number of entries is given by notificationMessageCount."
    ::= { lhnNusCommonNotification 2 }

NotificationMessageEntry ::= SEQUENCE
{
   notificationIndex          INTEGER,
   notificationMessage        OCTET STRING,
   notificationTime           DateAndTime
}

notificationMessageEntry OBJECT-TYPE
    SYNTAX      NotificationMessageEntry
    MAX-ACCESS  not-accessible
    STATUS      current
    DESCRIPTION
	"A row of notification messages for the NUS."
    INDEX { notificationIndex }
    ::= { notificationMessageTable 1 }

notificationIndex OBJECT-TYPE
    SYNTAX      INTEGER
    MAX-ACCESS  read-only
    STATUS      current
    DESCRIPTION
	"notification message index"
    ::= { notificationMessageEntry 1 }

notificationMessage OBJECT-TYPE
    SYNTAX      OCTET STRING
    MAX-ACCESS  read-only
    STATUS      current
    DESCRIPTION "notification message contents"
    ::= { notificationMessageEntry 2 }

notificationTime OBJECT-TYPE
    SYNTAX      DateAndTime
    MAX-ACCESS  read-only
    STATUS      current
    DESCRIPTION "time notification occurred"
    ::= { notificationMessageEntry 3 }

userNotification NOTIFICATION-TYPE
    OBJECTS          { notificationMessage }
    STATUS           current
    DESCRIPTION      "A system variable being monitored reached a threshold.
                     The user chose to be notified of this condition via SNMP.
                     A table of messages exists which stores all the notifications
                     issued.  This trap will carry the OID referring to the
                     corresponding message stored in this table."
    ::= { lhnNusCommonEvents 1 }

lhnNusCommonEventGroup NOTIFICATION-GROUP
   NOTIFICATIONS { userNotification }
   STATUS        current
   DESCRIPTION   "Events defined for NUS devices"
   ::= { lhnNusCommonGroups 2 }

END

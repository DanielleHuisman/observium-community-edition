-- (C)  COPYRIGHT HEWLETT-PACKARD COMPANY 1997.
--
-- LaserJet Series 4000 Printer Model Specific MIB.
--
-- Generated on August 4, 1997.
--
-- Company names and product names mentioned herein may be
-- trademarks, and/or registered trademarks of their respective
-- companies.
--
-- For interal and external use.
--
-- This MIB describes all the printer model specific
-- objects suppported by the LaserJet Series 4000 printer
-- when networked connected using a JetDirect print
-- server.
--
-- The following MIB also contain objects supported
-- by a JetDirect connected LaserJet Series 4000 printer:
--
-- rfc 1213 MIB II
--
-- This MIB complies with the following RFCs:
--
-- rfc 1157 Simple Network Management Protocol
-- rfc 1155 Structure of Management Information
--
-- Notes:
--
-- 1) Proprietary Objects containing a string which are defined in this MIB use the
--    first two bytes to hold the symbol set used to encode the string.
--    The Roman-8 symbol set has a hex encoding of 0x0115.  Other
--    symbol sets are listed in the PCL 5 Comparison Guide in table
--    C-1 Symbol Set Values.  Standard Printer MIB (prt...objects) and Host Resources
--    MIB (hr...objects) strings do not contain symbol set information. 
--
-- 2) Some of the objects included are only supported if an accessory
--    is installed.  These accessories include:
--      MIO/EIO based accessories
--      SIMM/DIMM based accessories
--      Mass storage devices
--      Paper handling accessories
--      Adobe PostScript accessory
--
--
LaserJet-Series4000-MIB DEFINITIONS ::= BEGIN

IMPORTS
   enterprises               FROM SNMPv2-SMI,
   DisplayString             FROM SNMPv2-TC;

hp OBJECT IDENTIFIER ::= { enterprises 11 }
nm OBJECT IDENTIFIER ::= { hp 2 }
hpsystem OBJECT IDENTIFIER ::= { nm 3 }
net-peripheral OBJECT IDENTIFIER ::= { hpsystem 9 }
netdm OBJECT IDENTIFIER ::= { net-peripheral 4 }
dm OBJECT IDENTIFIER ::= {  netdm 2}

device                                 OBJECT IDENTIFIER ::=  { dm 1 } 
system                                 OBJECT IDENTIFIER ::=  { device 1 } 
id                                     OBJECT IDENTIFIER ::=  { system 3 } 
processing-subsystem                   OBJECT IDENTIFIER ::=  { device 3 } 
pdl                                    OBJECT IDENTIFIER ::=  { processing-subsystem 3 } 
settings-pdl                           OBJECT IDENTIFIER ::=  { pdl 1 } 
destination-subsystem                  OBJECT IDENTIFIER ::=  { device 4 } 
print-engine                           OBJECT IDENTIFIER ::=  { destination-subsystem 1 } 
print-media                            OBJECT IDENTIFIER ::=  { print-engine 8 } 
media-modes                            OBJECT IDENTIFIER ::=  { print-media 4 } 
hrm                                    OBJECT IDENTIFIER ::=  { dm 3 } 
hrDevice                               OBJECT IDENTIFIER ::=  { hrm 3 } 
hrDeviceTable                          OBJECT IDENTIFIER ::=  { hrDevice 2 } 
hrDeviceEntry                          OBJECT IDENTIFIER ::=  { hrDeviceTable 1 } 
interface                              OBJECT IDENTIFIER ::=  { system 4 } 
phd                                    OBJECT IDENTIFIER ::=  { interface 5 } 
phd1                                   OBJECT IDENTIFIER ::=  { phd 1 } 
settings-prt-eng                       OBJECT IDENTIFIER ::=  { print-engine 1 } 
intray                                 OBJECT IDENTIFIER ::=  { print-engine 3 } 
settings-intray                        OBJECT IDENTIFIER ::=  { intray 1 } 
intrays                                OBJECT IDENTIFIER ::=  { intray 3 } 
intray1                                OBJECT IDENTIFIER ::=  { intrays 1 } 
intray2                                OBJECT IDENTIFIER ::=  { intrays 2 } 
intray3                                OBJECT IDENTIFIER ::=  { intrays 3 } 
intray4                                OBJECT IDENTIFIER ::=  { intrays 4 } 
intray5                                OBJECT IDENTIFIER ::=  { intrays 5 } 
settings-print-media                   OBJECT IDENTIFIER ::=  { print-media 1 } 
media-info                             OBJECT IDENTIFIER ::=  { print-media 3 } 
media4                                 OBJECT IDENTIFIER ::=  { media-info 4 } 
printmib                               OBJECT IDENTIFIER ::=  { dm 2 } 
prtGeneral                             OBJECT IDENTIFIER ::=  { printmib 5 } 
prtGeneralTable                        OBJECT IDENTIFIER ::=  { prtGeneral 1 } 
prtGeneralEntry                        OBJECT IDENTIFIER ::=  { prtGeneralTable 1 } 
prtInput                               OBJECT IDENTIFIER ::=  { printmib 8 } 
prtInputTable                          OBJECT IDENTIFIER ::=  { prtInput 2 } 
prtInputEntry                          OBJECT IDENTIFIER ::=  { prtInputTable 1 } 
prtOutput                              OBJECT IDENTIFIER ::=  { printmib 9 } 
prtOutputTable                         OBJECT IDENTIFIER ::=  { prtOutput 2 } 
prtOutputEntry                         OBJECT IDENTIFIER ::=  { prtOutputTable 1 } 
prtMarkerSupplies                      OBJECT IDENTIFIER ::=  { printmib 11 } 
prtMarkerSuppliesTable                 OBJECT IDENTIFIER ::=  { prtMarkerSupplies 1 } 
prtMarkerSuppliesEntry                 OBJECT IDENTIFIER ::=  { prtMarkerSuppliesTable 1 } 
prtMediaPath                           OBJECT IDENTIFIER ::=  { printmib 13 } 
prtMediaPathTable                      OBJECT IDENTIFIER ::=  { prtMediaPath 4 } 
prtMediaPathEntry                      OBJECT IDENTIFIER ::=  { prtMediaPathTable 1 } 
tables                                 OBJECT IDENTIFIER ::=  { device 7 } 
channel-table                          OBJECT IDENTIFIER ::=  { tables 2 } 
channel-entry                          OBJECT IDENTIFIER ::=  { channel-table 1 } 
prtChannel                             OBJECT IDENTIFIER ::=  { printmib 14 } 
prtChannelTable                        OBJECT IDENTIFIER ::=  { prtChannel 1 } 
prtChannelEntry                        OBJECT IDENTIFIER ::=  { prtChannelTable 1 } 
settings-system                        OBJECT IDENTIFIER ::=  { system 1 } 
status-system                          OBJECT IDENTIFIER ::=  { system 2 } 
background-message                     OBJECT IDENTIFIER ::=  { status-system 37 } 
background-message1                    OBJECT IDENTIFIER ::=  { background-message 1 } 
background-message2                    OBJECT IDENTIFIER ::=  { background-message 2 } 
simm                                   OBJECT IDENTIFIER ::=  { interface 1 } 
simm1                                  OBJECT IDENTIFIER ::=  { simm 1 } 
simm2                                  OBJECT IDENTIFIER ::=  { simm 2 } 
simm3                                  OBJECT IDENTIFIER ::=  { simm 3 } 
simm4                                  OBJECT IDENTIFIER ::=  { simm 4 } 
test                                   OBJECT IDENTIFIER ::=  { system 5 } 
job                                    OBJECT IDENTIFIER ::=  { system 6 } 
settings-job                           OBJECT IDENTIFIER ::=  { job 1 } 
errorlog                               OBJECT IDENTIFIER ::=  { system 11 } 
error1                                 OBJECT IDENTIFIER ::=  { errorlog 1 } 
error2                                 OBJECT IDENTIFIER ::=  { errorlog 2 } 
error3                                 OBJECT IDENTIFIER ::=  { errorlog 3 } 
error4                                 OBJECT IDENTIFIER ::=  { errorlog 4 } 
error5                                 OBJECT IDENTIFIER ::=  { errorlog 5 } 
error6                                 OBJECT IDENTIFIER ::=  { errorlog 6 } 
error7                                 OBJECT IDENTIFIER ::=  { errorlog 7 } 
error8                                 OBJECT IDENTIFIER ::=  { errorlog 8 } 
error9                                 OBJECT IDENTIFIER ::=  { errorlog 9 } 
error10                                OBJECT IDENTIFIER ::=  { errorlog 10 } 
error11                                OBJECT IDENTIFIER ::=  { errorlog 11 } 
error12                                OBJECT IDENTIFIER ::=  { errorlog 12 } 
error13                                OBJECT IDENTIFIER ::=  { errorlog 13 } 
error14                                OBJECT IDENTIFIER ::=  { errorlog 14 } 
error15                                OBJECT IDENTIFIER ::=  { errorlog 15 } 
error16                                OBJECT IDENTIFIER ::=  { errorlog 16 } 
error17                                OBJECT IDENTIFIER ::=  { errorlog 17 } 
error18                                OBJECT IDENTIFIER ::=  { errorlog 18 } 
error19                                OBJECT IDENTIFIER ::=  { errorlog 19 } 
error20                                OBJECT IDENTIFIER ::=  { errorlog 20 } 
error21                                OBJECT IDENTIFIER ::=  { errorlog 21 } 
error22                                OBJECT IDENTIFIER ::=  { errorlog 22 } 
error23                                OBJECT IDENTIFIER ::=  { errorlog 23 } 
error24                                OBJECT IDENTIFIER ::=  { errorlog 24 } 
error25                                OBJECT IDENTIFIER ::=  { errorlog 25 } 
error26                                OBJECT IDENTIFIER ::=  { errorlog 26 } 
error27                                OBJECT IDENTIFIER ::=  { errorlog 27 } 
error28                                OBJECT IDENTIFIER ::=  { errorlog 28 } 
error29                                OBJECT IDENTIFIER ::=  { errorlog 29 } 
error30                                OBJECT IDENTIFIER ::=  { errorlog 30 } 
mass-storage-block-driver              OBJECT IDENTIFIER ::=  { system 15 } 
settings-mass-storage-bd               OBJECT IDENTIFIER ::=  { mass-storage-block-driver 1 } 
status-mass-storage-bd                 OBJECT IDENTIFIER ::=  { mass-storage-block-driver 2 } 
source-subsystem                       OBJECT IDENTIFIER ::=  { device 2 } 
io                                     OBJECT IDENTIFIER ::=  { source-subsystem 1 } 
settings-io                            OBJECT IDENTIFIER ::=  { io 1 } 
ports                                  OBJECT IDENTIFIER ::=  { io 3 } 
port1                                  OBJECT IDENTIFIER ::=  { ports 1 } 
spooler                                OBJECT IDENTIFIER ::=  { source-subsystem 4 } 
settings-spooler                       OBJECT IDENTIFIER ::=  { spooler 1 } 
pdl-pcl                                OBJECT IDENTIFIER ::=  { pdl 3 } 
pdl-postscript                         OBJECT IDENTIFIER ::=  { pdl 4 } 
pjl                                    OBJECT IDENTIFIER ::=  { processing-subsystem 5 } 
status-prt-eng                         OBJECT IDENTIFIER ::=  { print-engine 2 } 
marking-agent                          OBJECT IDENTIFIER ::=  { print-engine 5 } 
settings-marking-agent                 OBJECT IDENTIFIER ::=  { marking-agent 1 } 
imaging                                OBJECT IDENTIFIER ::=  { print-engine 6 } 
hrStorage                              OBJECT IDENTIFIER ::=  { hrm 2 } 
hrStorageTable                         OBJECT IDENTIFIER ::=  { hrStorage 3 } 
hrStorageEntry                         OBJECT IDENTIFIER ::=  { hrStorageTable 1 } 
hrPrinterTable                         OBJECT IDENTIFIER ::=  { hrDevice 5 } 
hrPrinterEntry                         OBJECT IDENTIFIER ::=  { hrPrinterTable 1 } 
prtLocalization                        OBJECT IDENTIFIER ::=  { printmib 7 } 
prtLocalizationTable                   OBJECT IDENTIFIER ::=  { prtLocalization 1 } 
prtLocalizationEntry                   OBJECT IDENTIFIER ::=  { prtLocalizationTable 1 } 
prtStorageRefTable                     OBJECT IDENTIFIER ::=  { prtGeneral 2 } 
prtStorageRefEntry                     OBJECT IDENTIFIER ::=  { prtStorageRefTable 1 } 
prtDeviceRefTable                      OBJECT IDENTIFIER ::=  { prtGeneral 3 } 
prtDeviceRefEntry                      OBJECT IDENTIFIER ::=  { prtDeviceRefTable 1 } 
prtMarker                              OBJECT IDENTIFIER ::=  { printmib 10 } 
prtMarkerTable                         OBJECT IDENTIFIER ::=  { prtMarker 2 } 
prtMarkerEntry                         OBJECT IDENTIFIER ::=  { prtMarkerTable 1 } 
prtConsoleDisplayBuffer                OBJECT IDENTIFIER ::=  { printmib 16 } 
prtConsoleDisplayBufferTable           OBJECT IDENTIFIER ::=  { prtConsoleDisplayBuffer 5 } 
prtConsoleDisplayBufferEntry           OBJECT IDENTIFIER ::=  { prtConsoleDisplayBufferTable 1 } 
prtConsoleLights                       OBJECT IDENTIFIER ::=  { printmib 17 } 
prtConsoleLightTable                   OBJECT IDENTIFIER ::=  { prtConsoleLights 6 } 
prtConsoleLightEntry                   OBJECT IDENTIFIER ::=  { prtConsoleLightTable 1 } 
prtAlert                               OBJECT IDENTIFIER ::=  { printmib 18 } 
prtAlertTable                          OBJECT IDENTIFIER ::=  { prtAlert 1 } 
prtAlertEntry                          OBJECT IDENTIFIER ::=  { prtAlertTable 1 } 
phd2                                   OBJECT IDENTIFIER ::=  { phd 2 } 
phd3                                   OBJECT IDENTIFIER ::=  { phd 3 } 
phd4                                   OBJECT IDENTIFIER ::=  { phd 4 } 
phd5                                   OBJECT IDENTIFIER ::=  { phd 5 } 
phd6                                   OBJECT IDENTIFIER ::=  { phd 6 } 
outbin                                 OBJECT IDENTIFIER ::=  { print-engine 4 } 
settings-outbin                        OBJECT IDENTIFIER ::=  { outbin 1 } 
outbins                                OBJECT IDENTIFIER ::=  { outbin 3 } 
outbin1                                OBJECT IDENTIFIER ::=  { outbins 1 } 
outbin3                                OBJECT IDENTIFIER ::=  { outbins 3 } 
outbin4                                OBJECT IDENTIFIER ::=  { outbins 4 } 
outbin5                                OBJECT IDENTIFIER ::=  { outbins 5 } 
outbin6                                OBJECT IDENTIFIER ::=  { outbins 6 } 
outbin7                                OBJECT IDENTIFIER ::=  { outbins 7 } 
outbin8                                OBJECT IDENTIFIER ::=  { outbins 8 } 
outbin9                                OBJECT IDENTIFIER ::=  { outbins 9 } 
ph                                     OBJECT IDENTIFIER ::=  { print-engine 7 } 
ph-devices                             OBJECT IDENTIFIER ::=  { ph 3 } 
ph2                                    OBJECT IDENTIFIER ::=  { ph-devices 2 } 
ph3                                    OBJECT IDENTIFIER ::=  { ph-devices 3 } 
ph4                                    OBJECT IDENTIFIER ::=  { ph-devices 4 } 
ph5                                    OBJECT IDENTIFIER ::=  { ph-devices 5 } 
ph6                                    OBJECT IDENTIFIER ::=  { ph-devices 6 } 
media1                                 OBJECT IDENTIFIER ::=  { media-info 1 } 
media2                                 OBJECT IDENTIFIER ::=  { media-info 2 } 
media3                                 OBJECT IDENTIFIER ::=  { media-info 3 } 
media5                                 OBJECT IDENTIFIER ::=  { media-info 5 } 
media6                                 OBJECT IDENTIFIER ::=  { media-info 6 } 
media7                                 OBJECT IDENTIFIER ::=  { media-info 7 } 
media8                                 OBJECT IDENTIFIER ::=  { media-info 8 } 
media9                                 OBJECT IDENTIFIER ::=  { media-info 9 } 
media10                                OBJECT IDENTIFIER ::=  { media-info 10 } 
media11                                OBJECT IDENTIFIER ::=  { media-info 11 } 
media13                                OBJECT IDENTIFIER ::=  { media-info 13 } 
media14                                OBJECT IDENTIFIER ::=  { media-info 14 } 
media15                                OBJECT IDENTIFIER ::=  { media-info 15 } 
media16                                OBJECT IDENTIFIER ::=  { media-info 16 } 
media17                                OBJECT IDENTIFIER ::=  { media-info 17 } 
prtCover                               OBJECT IDENTIFIER ::=  { printmib 6 } 
prtCoverTable                          OBJECT IDENTIFIER ::=  { prtCover 1 } 
prtCoverEntry                          OBJECT IDENTIFIER ::=  { prtCoverTable 1 } 
file-system                            OBJECT IDENTIFIER ::=  { system 10 } 
settings-file-system                   OBJECT IDENTIFIER ::=  { file-system 1 } 
status-file-system                     OBJECT IDENTIFIER ::=  { file-system 2 } 
file-systems                           OBJECT IDENTIFIER ::=  { file-system 3 } 
file-system2                           OBJECT IDENTIFIER ::=  { file-systems 2 } 
file-system3                           OBJECT IDENTIFIER ::=  { file-systems 3 } 
file-system4                           OBJECT IDENTIFIER ::=  { file-systems 4 } 
resource-manager                       OBJECT IDENTIFIER ::=  { system 12 } 
mass-storage-resources                 OBJECT IDENTIFIER ::=  { resource-manager 3 } 
hrDiskStorageTable                     OBJECT IDENTIFIER ::=  { hrDevice 6 } 
hrDiskStorageEntry                     OBJECT IDENTIFIER ::=  { hrDiskStorageTable 1 } 
hrPartitionTable                       OBJECT IDENTIFIER ::=  { hrDevice 7 } 
hrPartitionEntry                       OBJECT IDENTIFIER ::=  { hrPartitionTable 1 } 
hrFSTable                              OBJECT IDENTIFIER ::=  { hrDevice 8 } 
hrFSEntry                              OBJECT IDENTIFIER ::=  { hrFSTable 1 } 
mio                                    OBJECT IDENTIFIER ::=  { interface 3 } 
mio1                                   OBJECT IDENTIFIER ::=  { mio 1 } 
mio2                                   OBJECT IDENTIFIER ::=  { mio 2 } 
active-print-jobs                      OBJECT IDENTIFIER ::=  { job 2 } 
job-being-parsed                       OBJECT IDENTIFIER ::=  { active-print-jobs 1 } 
job-info                               OBJECT IDENTIFIER ::=  { job 5 } 
job-info-attribute                     OBJECT IDENTIFIER ::=  { job-info 23 } 
status-pdl                             OBJECT IDENTIFIER ::=  { pdl 2 } 
jetsend-proc-sub                       OBJECT IDENTIFIER ::=  { processing-subsystem 8 } 
settings-jetsend                       OBJECT IDENTIFIER ::=  { jetsend-proc-sub 1 } 
jetsend-contact                        OBJECT IDENTIFIER ::=  { jetsend-proc-sub 3 } 
settings-jetsend-contact               OBJECT IDENTIFIER ::=  { jetsend-contact 1 } 
remote-procedure-call                  OBJECT IDENTIFIER ::=  { system 13 } 
settings-rpc                           OBJECT IDENTIFIER ::=  { remote-procedure-call 1 } 
status-rpc                             OBJECT IDENTIFIER ::=  { remote-procedure-call 2 } 
rpc-services                           OBJECT IDENTIFIER ::=  { remote-procedure-call 3 } 
nfs-server                             OBJECT IDENTIFIER ::=  { rpc-services 2 } 
settings-nfs-server                    OBJECT IDENTIFIER ::=  { nfs-server 1 } 
status-nfs-server                      OBJECT IDENTIFIER ::=  { nfs-server 2 } 
rpc-bind                               OBJECT IDENTIFIER ::=  { rpc-services 3 } 
settings-rpc-bind                      OBJECT IDENTIFIER ::=  { rpc-bind 1 } 
status-rpc-bind                        OBJECT IDENTIFIER ::=  { rpc-bind 2 } 
xport-interface                        OBJECT IDENTIFIER ::=  { system 14 } 
status-xip                             OBJECT IDENTIFIER ::=  { xport-interface 2 } 
prtInterpreter                         OBJECT IDENTIFIER ::=  { printmib 15 } 
prtInterpreterTable                    OBJECT IDENTIFIER ::=  { prtInterpreter 1 } 
prtInterpreterEntry                    OBJECT IDENTIFIER ::=  { prtInterpreterTable 1 } 


model-name OBJECT-TYPE
    SYNTAX  DisplayString (SIZE(1..32))
    ACCESS  read-only
    STATUS  optional
    DESCRIPTION
                "Identifies the device model name (e.g.  ''DeskJet
                1200C'').  The string is as specific as possible.
                Capitalization and spacing should match family naming
                conventions.  Products should note in POS if the model
                name on the HP corporate price list changes but the
                device reports the previous device name.  If the model
                name changes based on the installed options, the POS
                should indicate if only the base model name is returned,
                or if the device senses the installed options and
                returns the correct model name.  If possible, encode the
                model name in a symbol set (like Roman-8) that matches
                the ASCII character set and limit the characters used to
                ASCII characters.
                Additional information:
                Since the value of this object is frequently used in 
                displaying a list of printers, it is kept relatively short in 
                case systems have limited width for their display area.  The
                model name does not change based on sensing of installed options."
::= { id 2 }
               
               
device-name OBJECT-TYPE
    SYNTAX  DisplayString (SIZE(0..32))
    ACCESS  read-write
    STATUS  optional
    DESCRIPTION
                "User defined device name.  The POS should indicate the
                maximum supported string length.  If the user entered
                string is too long, the device will store as much as
                possible and will return the <noError>.

                Additional information:
                The maximum supported string length is 32  
                characters.  If the user entered string is too long, 
                the device will store the first 32 characters and will 
                return the <noError> status."
::= { id 10 }
               
               
default-media-size OBJECT-TYPE
    SYNTAX  INTEGER {
		   eUSExecutive(1),
		   eUSLetter(2),
		   eUSLegal(3),
		   eISOandJISA5(25),
		   eISOandJISA4(26),
		   eMonarch(80),
		   eCommercial10(81),
		   eInternationalDL(90),
		   eInternationalC5(91),
		   eInternationalB5(100),
		   eCustom(101)
		   }
    ACCESS  read-write
    STATUS  optional
    DESCRIPTION
                "This indicates the default media size.  A write of an
                unsupported value cases an <badValue>.
  Complete list of supported media sizes along
                with their dimensions are listed in the ''Media Size
                Table'' near the end of this document."
::= { settings-pdl 13 }
               
               
engine-media-modes-supported1 OBJECT-TYPE
    SYNTAX  DisplayString
    ACCESS  read-only
    STATUS  optional
    DESCRIPTION
                "The list of engine media modes supported by the device.
                The modes are each separated by a comma character.  An
                example string would be: 'Normal,Rough,Low,Vellum'."
::= { media-modes 1 }
               
               
hrdevicedescr OBJECT-TYPE
    SYNTAX  OCTET STRING (SIZE(0..64))
    ACCESS  read-only
    STATUS  mandatory
    DESCRIPTION
                "A textual description of this device, including
              the device's manufacturer and revision, and
              optionally, its serial number.
              Refer to RFC 1514, Host Resources MIB, for more details.
                Additional information (printer):
                The serial number is not returned with this object.
                This object is not localized. 
                Additional information (mass storage):
                Returns <noSuchName>
                status if attempting to perform a Get on this OID
                with no mass storage device installed."
::= { hrDeviceEntry 3 }
               
               
hrdeviceid OBJECT-TYPE
    SYNTAX  OBJECT IDENTIFIER
    ACCESS  read-only
    STATUS  mandatory
    DESCRIPTION
                "The product ID for this device.
              Refer to RFC 1514, Host Resources MIB, for more details.
                Additional information (printer):
                The complete OID reported by this object is:  
                .1.3.6.1.4.1.11.2.3.9.1.2.5. 
                Additional information (mass storage):
                Constant.  Since we don't know all the
                possible registered OIDs for each mass storage device model that
                could be installed in this printer, this object
                always returns the unknown product ID.  Returns
                <noSuchName> status if attempting
                to perform a Get on this OID with no mass storage device
                installed."
::= { hrDeviceEntry 4 }
               
               
phd1-model OBJECT-TYPE
    SYNTAX  DisplayString
    ACCESS  read-only
    STATUS  optional
    DESCRIPTION
                "Returns product information identifying the PHD device.
                Example: XXXX"
::= { phd1 1 }
               
               
phd1-manufacturing-info OBJECT-TYPE
    SYNTAX  DisplayString
    ACCESS  read-only
    STATUS  optional
    DESCRIPTION
                "Returns information describing the manufacture of this
                particular PHD.  May include serial number and firmware
                revision."
::= { phd1 2 }
               
               
phd1-type OBJECT-TYPE
    SYNTAX  INTEGER {
		   eEmpty(1),
		   eInputPHD(10)
		   }
    ACCESS  read-only
    STATUS  optional
    DESCRIPTION
                "Returns an indication of the type of option installed in
                this particular SIMM interface  See SIMM1-TYPE for an
                explanation of the enumerations.
                Additional information:
                 Returns an indication of whether or not the
                envelope feeder is installed on the printer.  A value of eEmpty means that
                the envelope feeder is not installed."
::= { phd1 3 }
               
               
phd1-capacity OBJECT-TYPE
    SYNTAX  INTEGER
    ACCESS  read-only
    STATUS  optional
    DESCRIPTION
                "Returns an indication of the capacity of the installed
                option.  See SIMM1-CAPACITY for an explanation of the
                meaning of the value of this object.
                Additional information:
                The LaserJet Series 4000 envelope feeder has a single tray."
::= { phd1 4 }
               
               
override-media-size OBJECT-TYPE
    SYNTAX  INTEGER {
		   eUSExecutive(1),
		   eUSLetter(2),
		   eUSLegal(3),
		   eISOandJISA5(25),
		   eISOandJISA4(26),
		   eJISB5(45),
		   eMonarch(80),
		   eCommercial10(81),
		   eInternationalDL(90),
		   eInternationalC5(91),
		   eInternationalB5(100),
		   eCustom(101)
		   }
    ACCESS  read-write
    STATUS  optional
    DESCRIPTION
                "Sets the media size that is to be used in place of the
                currently requested media size.
                Additional information:
                When a request is received to print on a size and
                type of media that is not currently available, this object contains the
                desired size as set by the print job. This object should be set to a media
                size that is currently available to the printer.  
                If a paper mount request is not pending, attempting to get or set this object
                will cause <noSuchName> to be returned."
::= { settings-prt-eng 3 }
               
               
custom-paper-feed-dim OBJECT-TYPE
    SYNTAX  INTEGER
    ACCESS  read-write
    STATUS  optional
    DESCRIPTION
                "Sets the printer's custom paper dimension in the feed
                direction (direction parallel to the direction of paper
                feeding).  The value for this object is specified in
                micrometers or tenthousandths of an inch, depending upon
                the value of CUSTOM-PAPER-DIM-UNIT.  The valid range is
                engine-dependent and should be documented in the POS for
                each product.
                Additional information:
                The valid range for LaserJet Series 4000 is 50000 to 140000 if 
                CUSTOM-PAPER-DIM-UNIT is eTenThousandthsOfInches or
                127000 to 355600 if CUSTOM-PAPER-DIM-UNIT is ePmicrometers.
                Attempts to set this object outside the valid range will result
                in a return value of badValue."
::= { settings-intray 8 }
               
               
custom-paper-xfeed-dim OBJECT-TYPE
    SYNTAX  INTEGER
    ACCESS  read-write
    STATUS  optional
    DESCRIPTION
                "Sets the printer's custom paper dimension in the cross-
                feed direction (direction ninety degrees relative to the
                direction of paper feeding).  The value for this object
                is specified in micrometers or tenthousandths of an
                inch, depending upon the value of CUSTOM-PAPER-DIM-UNIT.
                The valid range is engine-dependent and should be
                documented in the POS for each product.
                Additional information:
                The valid range for LaserJet Series 4000 is 30000 to 85000 if 
                CUSTOM-PAPER-DIM-UNIT is eTenThousandthsOfInches or
                76200 to 215900 if CUSTOM-PAPER-DIM-UNIT is ePmicrometers.
                Attempts to set this object outside the valid range will result
                in a return value of badValue."
::= { settings-intray 9 }
               
               
tray1-media-size-loaded OBJECT-TYPE
    SYNTAX  INTEGER {
		   eUSExecutive(1),
		   eUSLetter(2),
		   eUSLegal(3),
		   eISOandJISA5(25),
		   eISOandJISA4(26),
		   eJISB5(45),
		   eMonarch(80),
		   eCommercial10(81),
		   eInternationalDL(90),
		   eInternationalC5(91),
		   eInternationalB5(100),
		   eCustom(101),
		   eUnknownMediaSize(32767)
		   }
    ACCESS  read-write
    STATUS  optional
    DESCRIPTION
                "Returns the media size that is currently
                configuredconfigured in tray #1.  This object can be set
                to indicate the media size currently loaded, if the
                printer supports input trays that can not sense the
                media size.  Complete list of supported media sizes
                along with their dimensions are listed in the ''Media
                Size Table'' near the end of this document."
::= { intray1 1 }
               
               
tray2-media-size-loaded OBJECT-TYPE
    SYNTAX  INTEGER {
		   eUSExecutive(1),
		   eUSLetter(2),
		   eUSLegal(3),
		   eJISB5(45),
		   eISOandJISA4(26),
		   eCustom(101),
		   eUnknownMediaSize(32767)
		   }
    ACCESS  read-only
    STATUS  optional
    DESCRIPTION
                "Returns the media size that is currently configured in
                tray #2.  Complete list of supported media sizes along
                with their dimensions are listed in the ''Media Size
                Table'' near the end of this document.
                Additional information:
                If the tray drawer is open, a get on this object
                will cause a status of
                <genErr> to be
                returned.  If the tray is empty, the size that the
                tray is configured for will be returned. If Tray 2
                is a 500-sheet standard tray, eJISB5 and eUSExecutive
                are not valid values."
::= { intray2 1 }
               
               
tray2-phd OBJECT-TYPE
    SYNTAX  INTEGER
    ACCESS  read-only
    STATUS  optional
    DESCRIPTION
                "Provides the number of the Paper Handling Device that
                contains this input tray."
::= { intray2 12 }
               
               
tray3-media-size-loaded OBJECT-TYPE
    SYNTAX  INTEGER {
		   eUSExecutive(1),
		   eUSLetter(2),
		   eUSLegal(3),
		   eJISB5(45),
		   eISOandJISA4(26),
		   eCustom(101),
		   eUnknownMediaSize(32767)
		   }
    ACCESS  read-only
    STATUS  optional
    DESCRIPTION
                "Returns the media size that is currently configured in
                tray #3.  Complete list of supported media sizes along
                with their dimensions are listed in the ''Media Size
                Table'' near the end of this document.
                Additional information:
                If the tray drawer is open, a get on this object
                will cause a status of
                <genErr> to be
                returned.  If the tray is empty, the size that the
                tray is configured for will be returned."
::= { intray3 1 }
               
               
tray3-phd OBJECT-TYPE
    SYNTAX  INTEGER
    ACCESS  read-only
    STATUS  optional
    DESCRIPTION
                "Provides the number of the Paper Handling Device that
                contains this input tray."
::= { intray3 12 }
               
               
tray4-phd OBJECT-TYPE
    SYNTAX  INTEGER
    ACCESS  read-only
    STATUS  optional
    DESCRIPTION
                "Provides the number of the Paper Handling Device that
                contains this input tray."
::= { intray4 12 }
               
               
tray5-media-size-loaded OBJECT-TYPE
    SYNTAX  INTEGER {
		   eUSExecutive(1),
		   eUSLetter(2),
		   eUSLegal(3),
		   eJISB5(45),
		   eISOandJISA4(26),
		   eCustom(101),
		   eUnknownMediaSize(32767)
		   }
    ACCESS  read-only
    STATUS  optional
    DESCRIPTION
                "Returns the media size that is currently configured in
                tray #5.  Complete list of supported media sizes along
                with their dimensions are listed in the ''Media Size
                Table'' near the end of this document.
                Additional information:
                If the tray drawer is open, a get on this object
                will cause a status of
                <genErr> to be
                returned.  If the tray is empty, the size that the
                tray is configured for will be returned."
::= { intray5 1 }
               
               
tray5-phd OBJECT-TYPE
    SYNTAX  INTEGER
    ACCESS  read-only
    STATUS  optional
    DESCRIPTION
                "Provides the number of the Paper Handling Device that
                contains this input tray."
::= { intray5 12 }
               
               
media-names-available OBJECT-TYPE
    SYNTAX  OCTET STRING
    ACCESS  read-write
    STATUS  optional
    DESCRIPTION
                "The value of this object controls which of the MEDIAx-
                NAME objects are supported.  If a bit is set to zero,
                then attempting to get or set the corresponding MEDIAx-
                NAME objects will return
                <noSuchName>.
                Additional information:
                Setting a bit to one will cause the corresponding
                MEDIAn- objects to be available (attempting to access
                an unavailable object will return <noSuchName>).
                MEDIA1- objects are always present in LaserJet Series 4000, as this is the default
                media. If this object is set to a value that does not include
                cMediaName1Available, that bit will be set and a status of
                <noError> will be returned.
                cMediaName12Available cannot be changed on LaserJet Series 4000, as MediaName12
                is not a supported Media Name for that product. Attempts to set
                cMediaName12Available will cause <badValue>
                to be returned."
::= { settings-print-media 1 }
               
               
media4-engine-media-mode OBJECT-TYPE
    SYNTAX  INTEGER
    ACCESS  read-write
    STATUS  optional
    DESCRIPTION
                "The engine processing characteristics that are to be
                applied to this media. The processing characteristics
                are device specific.
                Additional information:
                See the description for MEDIA1-ENGINE-MEDIA-MODE."
::= { media4 4 }
               
               
prtoutputdefaultindex OBJECT-TYPE
    SYNTAX  INTEGER
    ACCESS  read-only
    STATUS  optional
    DESCRIPTION
                "The  value of prtOutputIndex  corresponding to the default
        output sub-unit; that is, this object selects the default
        output destination. 
   This value shall be -1 if there is no default output subunit specified
   for the printer as a whole.  In this case, the actual default
   output subunit may be specified by means outside the scope of this
   MIB, such as by each interpreter in a printer with multiple
   interpreters.
   
   Refer to Internet Draft Printer MIB, expiring Sept. 1997 for more details.
                Additional information:
                LaserJet Series 4000 has two output bins in the base product:
                a face-up bin on the back of the engine and a face-down bin on
                the top of the engine. These bins are not firmware-selectable;
                instead, paper is diverted to the face-down bin only if the face-up
                bin is physically closed.  Therefore, these bins are considered
                together as the 'standard' bin. However, if an HCO is attached to the
                engine, users will be able to select between an HCO bin and the
                'standard' bin, which may be either the face-up or face-down bin,
                depending upon whether the face-up bin is open. With external output
                bins attached, the value of this object will be settable from the
                control panel and by the PJL OUTBIN variable."
::= { prtGeneralEntry 7 }
               
               
prtinputtype OBJECT-TYPE
    SYNTAX  INTEGER {
		   ePother(1),
		   ePunknown(2),
		   ePsheetFeedAutoRemovableTray(3),
		   ePsheetFeedAutoNonRemovableTray(4),
		   ePsheetFeedManual(5),
		   ePcontinuousRoll(6),
		   ePcontinuousFanFold(7)
		   }
    ACCESS  read-only
    STATUS  optional
    DESCRIPTION
                "The type of technology (discriminated primarily according to
        	feeder mechanism type) employed by the input sub-unit.  Note,
        	the Optional Input Class provides for a descriptor field to
        	further qualify the other choice.
		Refer to Internet Draft Printer MIB, expiring Sept. 1997 for more details.
                Additional information:
                Tray 1 is the multi-purpose tray and is always present.
                It supports both sheets and envelopes. Its type is
                ePsheetFeedAutoNonRemovableTray.  
                Tray 2 is a removable tray that comes standard
                with the printer, although it is usually not removed
                from the printer.  It is of type
                ePsheetFeedAutoRemovableTray.  
                Tray 3 is either a 250-sheet standard tray in the
                2x250 base engine configuration or a 500-sheet optional tray
                in the 1x500 base engine configuration. (The optional
                tray is only recognized if it's installed before the
                printer is powered on.) It is of type
                ePsheetFeedAutoRemovableTray.  
                The 4th tray in this array is the envelope feeder.  It
                can be detected even when it is installed while the
                printer is powered on.  
                Tray 5 is a 500-sheet optional tray that cannot be
                installed while the printer is powered on. It is of type
                ePsheetFeedAutoRemovableTray."
::= { prtInputEntry 2 }
               
               
prtinputdimunit OBJECT-TYPE
    SYNTAX  INTEGER {
		   ePtenThousandthsOfInches(3),
		   ePmicrometers(4)
		   }
    ACCESS  read-only
    STATUS  optional
    DESCRIPTION
                "The unit of measurement for use calculating and relaying
         	dimensional values for this input sub-unit.
	 	Refer to Internet Draft Printer MIB, expiring Sept. 1997 for more details.
                Additional information:
                Following is a table of paper sizes and dimensions
                for each paper size supported by LaserJet Series 4000:  
                
                Size               Inches (ten-thousandths)    Millimeters  
                ---------------    ------------------------    -----------  
                eUSExecutive       72500 x 105000              184150 x 266700  
                eUSLetter          85000 x 110000              215900 x 279400  
                eUSLegal           85000 x 140000              215900 x 355600  
                eISOandJISA5       58286 x 82677               148000 x 210000  
                eISOandJISA4       82677 x 116929              210000 x 297000  
                eJISB5             71654 x 101181              182000 x 257000  
                eMonarch           38750 x 75000               98425  x 190500  
                eCommercial10      41250 x 95000               104775 x 241300  
                eInternationalDL   43307 x 86614               110000 x 220000  
                eInternationalC5   63780 x 90157               162000 x 229000  
                eInternationalB5   69291 x 98425               176000 x 250000  
                eCustom            85000 x 140000 (max)        215900 x 355600 (max)  "
::= { prtInputEntry 3 }
               
               
prtinputmediadimfeeddirdeclared OBJECT-TYPE
    SYNTAX  INTEGER
    ACCESS  read-write
    STATUS  optional
    DESCRIPTION
                "This object provides the value of the declared dimension, in
        the feed direction, of the media that is (or, if empty, was or
        will be) in this input sub-unit.  The feed direction is the
        direction in which the media is fed on this sub-unit.  This
        dimension is measured in input sub-unit dimensional units
        (prtInputDimUnit).  If this input sub-unit can reliably sense
        this value, the value is sensed by the printer and may not be
        changed by management requests.  Otherwise, the value may be
        changed. The value (-1) means other and specifically means
        that this sub-unit places no restriction on this parameter.
        The value (-2) indicates unknown.
	Refer to Internet Draft Printer MIB, expiring Sept. 1997 for more details.
                Additional information:
                For trays 2, 3, and 5 (which can reliably sense this
                value) these objects behave exactly the same as prtInputMediaDimFeedDirChosen.
                Attempting to set the objects for tray 2, 3, or 5 will cause
                <noSuchName> to be returned.  
                The default values assume the trays are configured for letter size paper (or COM10,
                in the case of the envelope feeder). For tray 1, the value is the dimension for
                the media size currently declared. For the envelope feeder (tray 4), the value is
                the dimension for the media size currently declared.  
                Valid values are 0 to 268435455. If a value within 0.2 inches of a standard
                size (e.g. 85001) is chosen when setting these objects, the standard size will
                be set for the specified tray if the value of prtInputMediaDimXFeedDirDeclared
                is also set to within 0.2 inches of the same standard size. If the value is not
                within 0.2 inches, Custom will be chosen as the size if it is supported by the
                specified tray, otherwise the first available standard size for the tray will
                be selected."
::= { prtInputEntry 4 }
               
               
prtinputmediadimxfeeddirdeclared OBJECT-TYPE
    SYNTAX  INTEGER
    ACCESS  read-write
    STATUS  optional
    DESCRIPTION
                "This object provides the value of the declared dimension, in
        the cross feed direction, of the media that is (or, if empty,
        was or will be) in this input sub-unit.  The cross  feed
        direction is ninety degrees relative to the feed direction
        associated with this sub-unit. This dimension is measured in
        input sub-unit dimensional units (prtInputDimUnit).  If this
        input sub-unit can reliably sense this value, the value is
        sensed by the printer and may not be changed by management
        requests. Otherwise, the value may be changed. The value (-1)
        means other and specifically means that this sub-unit places
        no restriction on this parameter. The value (-2) indicates
        unknown.
	Refer to Internet Draft Printer MIB, expiring Sept. 1997 for more details.
                Additional information:
                For trays 2, 3, and 5 (which can reliably sense this
                value) these objects behave exactly the same as prtInputMediaDimXFeedDirChosen.
                Attempting to set these objects for tray 2, 3, and 5 will cause
                <noSuchName> to be returned.  
                The default values assume the trays are configured for letter size paper (or COM10,
                in the case of the envelope feeder). For tray 1 the value is the dimension for the
                media size currently declared.  
                Valid values are 0 to 268435455. If a value within 0.2 inches of a standard
                size (e.g. 85001) is chosen when setting these objects, the standard size will
                be set for the specified tray if the value of prtInputMediaDimFeedDirDeclared
                is also set to within 0.2 inches of the same standard size. If the value is not
                within 0.2 inches, Custom will be chosen as the size if it is supported by the
                specified tray, otherwise the first available standard size for the tray will
                be selected."
::= { prtInputEntry 5 }
               
               
prtinputmediadimfeeddirchosen OBJECT-TYPE
    SYNTAX  INTEGER
    ACCESS  read-only
    STATUS  optional
    DESCRIPTION
                "The printer will act as if media of the chosen dimension (in
        the feed direction) is present in this input source.  Note
        that this value will be used even if the input tray is empty.
        Feed dimension measurements are taken relative to the feed
        direction associated with that sub-unit and are in input sub-unit
        dimensional units (MediaUnit). If the printer supports the
        declared dimension, the granted dimension is the same as
        the declared dimension. If not, the granted dimension is
        set to the closest dimension that the printer supports
        when the declared dimension is set. The value (-1) means
        other and specifically indicates that this sub-unit
        places no restriction on this parameter. The value (-2)
        indicates unknown.
	Refer to Internet Draft Printer MIB, expiring Sept. 1997 for more details.
                Additional information:
                The objects for trays 2, 3, and 5 reflect the
                configuration of the corresponding trays. When the tray is removed, a value
                of -2 is returned. The default values assume the trays are configured for
                letter size paper (or COM10, in the case of the envelope feeder).  For tray 1
                and the envelope feeder, the object returns the value of the media size for
                which the tray is currently configured because those trays cannot sense what
                size media they contain."
::= { prtInputEntry 6 }
               
               
prtinputmediadimxfeeddirchosen OBJECT-TYPE
    SYNTAX  INTEGER
    ACCESS  read-only
    STATUS  optional
    DESCRIPTION
                "The printer will act as if media of the chosen dimension (in
        the cross feed direction) is present in this input source.
        Note that this value will be used even if the input tray is
        empty.  The cross feed direction is ninety degrees relative
        to the feed direction associated with this sub-unit. This
        dimension is measured in input sub-unit dimensional units
        (MediaUnit).  If the printer supports the declared
        dimension, the granted dimension is the same as the
        declared dimension. If not, the granted dimension is set
        to the closest dimension that the printer supports when
        the declared dimension is set. The value (-1) means other
        and specifically indicates that this sub-unit places no
        restriction on this parameter.  The value (-2) indicates
        unknown.
	Refer to Internet Draft Printer MIB, expiring Sept. 1997 for more details.
                Additional information:
                The objects for trays 2, 3, and 5 reflect the
                configuration of the corresponding trays. When the tray is removed, a value
                of -2 is returned. The default values assume the trays are configured for
                letter size paper (or COM10, in the case of the envelope feeder).  The objects
                for tray 1 and the envelope feeder return the value of the media size for which
                the tray is currently configured because those trays cannot sense what size media
                they contain."
::= { prtInputEntry 7 }
               
               
prtinputcapacityunit OBJECT-TYPE
    SYNTAX  INTEGER {
		   ePtenThousandthsOfInches(3),
		   ePmicrometers(4),
		   ePsheets(8),
		   ePfeet(16),
		   ePmeters(17)
		   }
    ACCESS  read-only
    STATUS  optional
    DESCRIPTION
                "The unit of measurement for use in calculating and relaying
        capacity values for this input sub-unit.
	Refer to Internet Draft Printer MIB, expiring Sept. 1997 for more details.
                Additional information:
                A sheet is a single piece of 20 pound paper. For tray
                4, the envelope feeder, a sheet is one envelope"
::= { prtInputEntry 8 }
               
               
prtinputmaxcapacity OBJECT-TYPE
    SYNTAX  INTEGER
    ACCESS  read-only
    STATUS  optional
    DESCRIPTION
                "The maximum capacity of the input sub-unit in input
        sub-unit capacity units (PrtCapacityUnitTC).  There is no
        convention associated with the media itself so this value
        reflects claimed capacity. If this input sub-unit can
        reliably sense this value, the value is sensed by the
        printer and may not be changed by management requests;
        otherwise, the value may be written.
        The value (-1) means other and specifically
        indicates that the sub-unit places no restrictions
        on this parameter.  The value (-2) means unknown.
	Refer to Internet Draft Printer MIB, expiring Sept. 1997 for more details.
                Additional information:
                This is
                specified assuming 20 pound paper for the paper trays."
::= { prtInputEntry 9 }
               
               
prtinputcurrentlevel OBJECT-TYPE
    SYNTAX  INTEGER
    ACCESS  read-only
    STATUS  optional
    DESCRIPTION
                "The current capacity of the input sub-unit in input
        sub-unit capacity units (PrtCapacityUnitTC). If this input
        sub-unit can reliably sense this value, the value is
        sensed by the printer and may not be changed by
        management requests; otherwise, the value may
        be written (by a Remote Contol Panel or a
        Management Application).  The value (-1) means other and
        specifically indicates that the sub-unit places no
        restrictions on this parameter. The value (-2) means unknown.
        The value (-3) means that the printer knows that at least one
        unit remains.
	Refer to Internet Draft Printer MIB, expiring Sept. 1997 for more details.
                Additional information:
                LaserJet Series 4000 can only detect empty/not empty for its
                trays. It returns -3 for not empty and 0 for empty.
                If a tray is removed, a value of -2 (unknown) will
                be returned."
::= { prtInputEntry 10 }
               
               
prtinputstatus OBJECT-TYPE
    SYNTAX  INTEGER
    ACCESS  read-only
    STATUS  optional
    DESCRIPTION
                "The current status of this input sub-unit.
	Refer to Internet Draft Printer MIB, expiring Sept. 1997 for more details.
                Additional information:
                Values returned by the firmware are detailed in the
                following table. 'Value Or'd Due To Condition' indicates
                that the specified value will be logically or'd into the
                value for this object when the specified Condition occurs.  
                Condition                       Value Or'd Due To Condition  
                -----------------------         ------------------------  
                Tray Lifter Error               3  
                Tray not installed or  
                not inserted or not  
                occupied                        1  
                Tray is current source tray
                and paper is moving             6  
                Tray involved in paper mount    16 + 32  
                Value 3 or 1 is Or'd in         8  
                Tray is lifting                 64  "
::= { prtInputEntry 11 }
               
               
prtinputmedianame OBJECT-TYPE
    SYNTAX  OCTET STRING (SIZE(0..63))
    ACCESS  read-write
    STATUS  optional
    DESCRIPTION
                "A description of the media contained in this input sub-unit;
        This description is intended for display to a human operator.
        This description is not processed by the printer.  It is used
        to provide information not expressible in terms of the other
        media attributes (e.g. prtInputMediaDimFeedDirChosen,
        prtInputMediaDimXFeedDirChosen, prtInputMediaWeight,
        prtInputMediaType). An example would be `legal tender bond
        paper'.
	Refer to Internet Draft Printer MIB, expiring Sept. 1997 for more details.
                Additional information:
                If set to a string other than one contained by a MEDIAn-NAME object, a
                status of <badValue> is returned.  If set to a string
                that is unsupported for the specified tray object, a status of
                <badValue> is returned. The value of this object is
                saved across a power cycle."
::= { prtInputEntry 12 }
               
               
prtinputname OBJECT-TYPE
    SYNTAX  OCTET STRING (SIZE(0..63))
    ACCESS  read-only
    STATUS  optional
    DESCRIPTION
                "The name assigned to this input sub-unit.
	Refer to Internet Draft Printer MIB, expiring Sept. 1997 for more details."
::= { prtInputEntry 13 }
               
               
prtinputvendorname OBJECT-TYPE
    SYNTAX  OCTET STRING (SIZE(0..63))
    ACCESS  read-only
    STATUS  optional
    DESCRIPTION
                "The vendor name of this input sub-unit.
	Refer to Internet Draft Printer MIB, expiring Sept. 1997 for more details."
::= { prtInputEntry 14 }
               
               
prtinputmodel OBJECT-TYPE
    SYNTAX  OCTET STRING (SIZE(0..63))
    ACCESS  read-only
    STATUS  optional
    DESCRIPTION
                "The model name of this input sub-unit.
	Refer to Internet Draft Printer MIB, expiring Sept. 1997 for more details.
                Additional information:
                LaserJet Series 4000 does not specify a model name for Tray1 or Tray2,
                nor for Tray 3 in the 2x250 tray configuration. However, if Tray 3
                is installed in the 1x500 configuration, 'Optional Cassette C4124A' will
                be returned. Tray 3, 4, and 5 objects do not exist unless those trays
                are installed."
::= { prtInputEntry 15 }
               
               
prtinputversion OBJECT-TYPE
    SYNTAX  OCTET STRING (SIZE(0..63))
    ACCESS  read-only
    STATUS  optional
    DESCRIPTION
                "The version of this input sub-unit.
	Refer to Internet Draft Printer MIB, expiring Sept. 1997 for more details.
                Additional information:
                LaserJet Series 4000 does not specify a version number
                for the input trays."
::= { prtInputEntry 16 }
               
               
prtinputserialnumber OBJECT-TYPE
    SYNTAX  OCTET STRING (SIZE(0..32))
    ACCESS  read-only
    STATUS  optional
    DESCRIPTION
                "The serial number assigned to this input sub-unit.
		Refer to Internet Draft Printer MIB, expiring Sept. 1997 for more details.
                Additional information:
                LaserJet Series 4000 does not specify a serial number for the
                input trays."
::= { prtInputEntry 17 }
               
               
prtinputdescription OBJECT-TYPE
    SYNTAX  OCTET STRING (SIZE(0..255))
    ACCESS  read-only
    STATUS  optional
    DESCRIPTION
                "A free-form text description of this input
        sub-unit in the localization specified by
        prtGeneralCurrentLocalization.
	Refer to Internet Draft Printer MIB, expiring Sept. 1997 for more details."
::= { prtInputEntry 18 }
               
               
prtinputsecurity OBJECT-TYPE
    SYNTAX  INTEGER {
		   ePother(1),
		   ePon(3),
		   ePoff(4),
		   ePnotPresent(5)
		   }
    ACCESS  read-only
    STATUS  optional
    DESCRIPTION
                "Indicates if this input sub-unit has some security
        associated with it.
	Refer to Internet Draft Printer MIB, expiring Sept. 1997 for more details.
                Additional information:
                No security mechanism provided."
::= { prtInputEntry 19 }
               
               
prtinputmedialoadtimeout OBJECT-TYPE
    SYNTAX  INTEGER
    ACCESS  read-only
    STATUS  optional
    DESCRIPTION
                "When the printer is not able to print due to a subunit
          being empty or the requested media must be manually loaded, the
          printer will wait for the duration (in seconds) specified by this
          object. Upon expiration of the timeout, the printer will take the
          action specified by prtInputNextIndex.
          The event which causes the printer to enter the waiting state is
          product specific. If the printer is not waiting for manually fed
          media, it may switch from an empty subunit to a different subunit
          without waiting for the timeout to expire.
          A value of (-1) implies 'other' or 'infinite' which translates to
          'wait forever'. The action which causes printing to continue is
          product specific. A value of (-2) implies 'unknown'.
		
		Refer to Internet Draft Printer MIB, expiring Sept. 1997 for more details.
                Additional information:
                This object simply reflects the value of the
                JOB-INPUT-AUTO-CONTINUE-TIMEOUT object. See the description of that object
                for additional information."
::= { prtInputEntry 24 }
               
               
prtinputnextindex OBJECT-TYPE
    SYNTAX  INTEGER
    ACCESS  read-only
    STATUS  optional
    DESCRIPTION
                "The value of prtInputIndex corresponding to the input
          subunit which will be used when this input subunit is emptied and
          the timeout specified by prtInputMediaLoadTimeout expires. A
          value of zero(0) indicates that auto input switching will not
          occur when this input subunit is emptied. If the timeout
          specified by prtInputLoadMediaTimeout expires and this value is
          zero(0), the job will be aborted. A value of (-1) means other.
          The value (-2) means 'unknown' and specifically indicates that an
          implementation specific method will determine the next input
          subunit to use at the time this subunit is emptied and the
          timeout expires. The value(-3) means input switching is not
          supported for this subunit.
		 Refer to Internet Draft Printer MIB, expiring Sept. 1997 for more details.
                Additional information:
                This object reflects the state of JOB-INPUT-AUTO-CONTINUE-MODE
                and JOB-INPUT-AUTO-CONTINUE-TIMEOUT. If
                JOB-INPUT-AUTO-CONTINUE-TIMEOUT is set to -1 or
                JOB-INPUT-AUTO-CONTINUE-MODE is set up to cancel the job,
                this object will return 0. If JOB-INPUT-AUTO-CONTINUE-TIMEOUT
                is >= 0 and JOB-INPUT-AUTO-CONTINUE-MODE is not set up to
                cancel the job, this object will return -2, meaning that
                a product-specific tray switching action will occur."
::= { prtInputEntry 26 }
               
               
prtoutputtype OBJECT-TYPE
    SYNTAX  INTEGER {
		   ePother(1),
		   ePunknown(2),
		   ePremovableBin(3),
		   ePunRemovableBin(4),
		   ePcontinuousRollDevice(5),
		   ePmailBox(6),
		   ePcontinousFanFold(7)
		   }
    ACCESS  read-only
    STATUS  optional
    DESCRIPTION
                "The type of technology supported by this output sub-unit.
		Refer to Internet Draft Printer MIB, expiring Sept. 1997 for more details.
                Additional information:
                LaserJet Series 4000 has two built-in output bins: a face-down
                bin located at the top of the printer and a face-up bin located
                at the rear of the printer. However, neither of these bins is
                firmware-selectable, so both bins are considered together as the
                'standard' bin. LaserJet Series 4000 supports HCO devices as well as a
                stacker/stapler, but these devices are currently T.B.D."
::= { prtOutputEntry 2 }
               
               
prtoutputcapacityunit OBJECT-TYPE
    SYNTAX  INTEGER {
		   ePtenThousandthsOfInches(3),
		   ePmicrometers(4),
		   ePsheets(8),
		   ePfeet(16),
		   ePmeters(17)
		   }
    ACCESS  read-only
    STATUS  optional
    DESCRIPTION
                "The unit of measurement for use in calculating and relaying
        	capacity values for this output sub-unit.
		Refer to Internet Draft Printer MIB, expiring Sept. 1997 for more details.
                Additional information:
                A sheet is a single piece of 20 pound paper."
::= { prtOutputEntry 3 }
               
               
prtoutputmaxcapacity OBJECT-TYPE
    SYNTAX  INTEGER
    ACCESS  read-only
    STATUS  optional
    DESCRIPTION
                "The maximum capacity of this output sub-unit in output
        sub-unit capacity units (PrtCapacityUnitTC). There is no
        convention associated with the media itself so this value
        essentially reflects claimed capacity. If this output
        sub-unit can reliably sense this value, the value is
        sensed by the printer and may not be changed by management
        requests; otherwise, the value may be written.
        The value (-1) means other and specifically indicates
        that the sub-unit places no restrictions on this parameter.
        The value (-2) means unknown.
	Refer to Internet Draft Printer MIB, expiring Sept. 1997 for more details.
                Additional information:
                LaserJet Series 4000 cannot sense the amount of paper in its standard output
                bin; however, the face-up bin can hold 50 sheets of 20lb. paper,
                and the face-down bin can hold 250 sheets. External output devices
                are currently T.B.D."
::= { prtOutputEntry 4 }
               
               
prtoutputremainingcapacity OBJECT-TYPE
    SYNTAX  INTEGER
    ACCESS  read-only
    STATUS  optional
    DESCRIPTION
                "The remaining capacity of the possible output sub-unit
        capacity in output sub-unit capacity units (PrtCapacityUnitTC)
        of this output sub-unit. If this output sub-unit can
        reliably sense this value, the value is sensed by the
        printer and may not be modified by management requests;
        otherwise, the value may be written. 
        The value (-1) means other and
        specifically indicates that the sub-unit places no
        restrictions on this parameter.  The value (-2) means
        unknown.  The value (-3) means that the printer knows that
        there remains capacity for at least one unit.
	Refer to Internet Draft Printer MIB, expiring Sept. 1997 for more details.
                Additional information:
                LaserJet Series 4000 is capable of determining when the face-down
                bin goes full, but not the level of that bin. LaserJet Series 4000
                is not capable of determining whether the face-up bin
                is full. RemainingCapacity capabilities of the
                stapler/stacker, as well as unplanned HCO devices,
                are currently T.B.D.  
                LaserJet Series 4000 will report a value of 0 when the face-down
                bin is full and -3 when the face down bin is not full."
::= { prtOutputEntry 5 }
               
               
prtoutputstatus OBJECT-TYPE
    SYNTAX  INTEGER
    ACCESS  read-only
    STATUS  optional
    DESCRIPTION
                "The current status of this output sub-unit.
	Refer to Internet Draft Printer MIB, expiring Sept. 1997 for more details.
                Additional information:
                The default values assume all bins are empty.   
                See SubUnitStatus in RFC1759 Printer MIB for details on values reported by
                this object. LaserJet Series 4000 will not include values Available and Standby (2),
                Available and Active (4), Unknown (5) or Transitioning to Intended State
                (64).  
                Values returned by the firmware are detailed in the
                following table. 'Value Or'd Due To Condition' indicates
                that the specified value will be logically or'd into the
                value for this object when the specified Condition occurs.  
                Condition                       Value Or'd Due To Condition  
                -----------------------         ------------------------  
                Binder Error                    3  
                Bin full, binder empty,  
                bind limit reached, binder  
                align error, bin attention  
                error, or bin attention  
                warning                         1  
                Bin is current bin and
                paper is moving                 6  
                Bin is the bin responsible
                for Bin Full error message
                being displayed                 16 + 32  
                Value 1 or 3 is Or'd in         8  "
::= { prtOutputEntry 6 }
               
               
prtoutputname OBJECT-TYPE
    SYNTAX  OCTET STRING (SIZE(0..15))
    ACCESS  read-only
    STATUS  optional
    DESCRIPTION
                "The name assigned to this output sub-unit.
	Refer to Internet Draft Printer MIB, expiring Sept. 1997 for more details.
                Additional information:
                The characters must be in the range 20H to 7FH except 5C cannot be used. When
                this string is displayed on the control panel the Roman-8 symbol set is
                used."
::= { prtOutputEntry 7 }
               
               
prtoutputvendorname OBJECT-TYPE
    SYNTAX  OCTET STRING (SIZE(0..63))
    ACCESS  read-only
    STATUS  optional
    DESCRIPTION
                "The vendor name of this output sub-unit.
	Refer to Internet Draft Printer MIB, expiring Sept. 1997 for more details."
::= { prtOutputEntry 8 }
               
               
prtoutputmodel OBJECT-TYPE
    SYNTAX  OCTET STRING (SIZE(0..63))
    ACCESS  read-only
    STATUS  optional
    DESCRIPTION
                "The name assigned to this output sub-unit.
	Refer to Internet Draft Printer MIB, expiring Sept. 1997 for more details.
                Additional information:
                LaserJet Series 4000 does not support a model number for its
                built-in output bins. This object may change in the
                future when external output devices are added."
::= { prtOutputEntry 9 }
               
               
prtoutputversion OBJECT-TYPE
    SYNTAX  OCTET STRING (SIZE(0..63))
    ACCESS  read-only
    STATUS  optional
    DESCRIPTION
                "The version of this output sub-unit.
	Refer to Internet Draft Printer MIB, expiring Sept. 1997 for more details.
                Additional information:
                Returns device-specific information about the configuration
                of the output bin. May include information about the type of
                processing that can be done to media sent to this bin;
                processing includes but is not limited to binding, punching,
                folding and sealing. Format of this object is specified by
                the output device documentation."
::= { prtOutputEntry 10 }
               
               
prtoutputserialnumber OBJECT-TYPE
    SYNTAX  OCTET STRING (SIZE(0..63))
    ACCESS  read-only
    STATUS  optional
    DESCRIPTION
                "The serial number assigned to this output sub-unit.
	Refer to Internet Draft Printer MIB, expiring Sept. 1997 for more details.
                Additional information:
                LaserJet Series 4000 does not support a serial number for output
                devices."
::= { prtOutputEntry 11 }
               
               
prtoutputdescription OBJECT-TYPE
    SYNTAX  OCTET STRING (SIZE(0..255))
    ACCESS  read-only
    STATUS  optional
    DESCRIPTION
                "  A free-form text description of this output sub-unit in the
        localization specified by prtGeneralCurrentLocalization.
	Refer to Internet Draft Printer MIB, expiring Sept. 1997 for more details."
::= { prtOutputEntry 12 }
               
               
prtoutputsecurity OBJECT-TYPE
    SYNTAX  INTEGER {
		   ePother(1),
		   ePon(3),
		   ePoff(4),
		   ePnotPresent(5)
		   }
    ACCESS  read-only
    STATUS  optional
    DESCRIPTION
                "Indicates if this output sub-unit has some security associated
        with it and if that security is enabled or not.
	Refer to Internet Draft Printer MIB, expiring Sept. 1997 for more details.
                Additional information:
                No security mechanism provided."
::= { prtOutputEntry 13 }
               
               
prtoutputdimunit OBJECT-TYPE
    SYNTAX  INTEGER {
		   ePtenThousandthsOfInches(3),
		   ePmicrometers(4)
		   }
    ACCESS  read-only
    STATUS  optional
    DESCRIPTION
                "The unit of measurement for use in calculating and relaying
        dimensional values for this output sub-unit.
	Refer to Internet Draft Printer MIB, expiring Sept. 1997 for more details.
                Additional information:
                See the description for prtInputDimUnit for a table
                of supported paper sizes and their dimensions for LaserJet Series 4000."
::= { prtOutputEntry 14 }
               
               
prtoutputmaxdimfeeddir OBJECT-TYPE
    SYNTAX  INTEGER
    ACCESS  read-only
    STATUS  optional
    DESCRIPTION
                "The maximum dimensions supported by this output sub-unit
        for measurements taken parallel relative to the feed
        direction associated with that sub-unit in output
        sub-unit dimensional units (MediaUnit). If this output
        sub-unit can reliably sense this value, the value is
        sensed by the printer and may not be changed with
        management protocol operations.
	Refer to Internet Draft Printer MIB, expiring Sept. 1997 for more details.
                Additional information:
                LaserJet Series 4000 has two output bins in the base product:
                a face-up bin on the back of the engine and a face-down bin on
                the top of the engine. These bins are not firmware-selectable;
                instead, paper is diverted to the face-down bin only if the face-up
                bin is physically closed.  Therefore, these bins are considered
                together as the 'standard' bin.  
                The value returned by this object depends on the value
                of prtOutputDimUnit. It is 140000 if prtOutputDimUnit is
                ePtenThousandthsOfInches or 355600 if prtOutputDimUnit is ePmicrometers."
::= { prtOutputEntry 15 }
               
               
prtoutputmaxdimxfeeddir OBJECT-TYPE
    SYNTAX  INTEGER
    ACCESS  read-only
    STATUS  optional
    DESCRIPTION
                "The maximum dimensions supported by this output sub-unit
        for measurements taken ninety degrees relative to the
        feed direction associated with that sub-unit in output
        sub-unit dimensional units (MediaUnit). If this output
        sub-unit can reliably sense this value, the value is
        sensed by the printer and may not be changed with
        management protocol operations.
	Refer to Internet Draft Printer MIB, expiring Sept. 1997 for more details.
                Additional information:
                LaserJet Series 4000 has two output bins in the base product:
                a face-up bin on the back of the engine and a face-down bin on
                the top of the engine. These bins are not firmware-selectable;
                instead, paper is diverted to the face-down bin only if the face-up
                bin is physically closed.  Therefore, these bins are considered
                together as the 'standard' bin.  
                The value returned by this object depends on the value
                of prtOutputDimUnit. It is 85000 if prtOutputDimUnit is
                ePtenThousandthsOfInches and 215900 if prtOutputDimUnit
                is ePmicrometers."
::= { prtOutputEntry 16 }
               
               
prtoutputmindimfeeddir OBJECT-TYPE
    SYNTAX  INTEGER
    ACCESS  read-only
    STATUS  optional
    DESCRIPTION
                "The minimum dimensions supported by this output sub-unit
        for measurements taken parallel relative to the feed
        direction associated with that sub-unit in output
        sub-unit dimensional units (DimUnit).  If this output
        sub-unit can reliably sense this value, the value is
        sensed by the printer and may not be changed with
        management protocol operations.
	Refer to Internet Draft Printer MIB, expiring Sept. 1997 for more details.
                Additional information:
                LaserJet Series 4000 has two output bins in the base product:
                a face-up bin on the back of the engine and a face-down bin on
                the top of the engine. These bins are not firmware-selectable;
                instead, paper is diverted to the face-down bin only if the face-up
                bin is physically closed.  Therefore, these bins are considered
                together as the 'standard' bin.  
                The value returned by this object depends on the value
                of prtOutputDimUnit. It is 50000 if prtOutputDimUnit is
                ePtenThousandthsOfInches or 127000 if prtOutputDimUnit is
                ePmicrometers."
::= { prtOutputEntry 17 }
               
               
prtoutputmindimxfeeddir OBJECT-TYPE
    SYNTAX  INTEGER
    ACCESS  read-only
    STATUS  optional
    DESCRIPTION
                "The minimum dimensions supported by this output sub-unit
        for measurements taken ninety degrees relative to the
        feed direction associated with that sub-unit in output
        sub-unit dimensional units (DimUnit). If this output
        sub-unit can reliably sense this value, the value is
        sensed by the printer and may not be changed with
        management protocol operations.
	Refer to Internet Draft Printer MIB, expiring Sept. 1997 for more details.
                Additional information:
                LaserJet Series 4000 has two output bins in the base product:
                a face-up bin on the back of the engine and a face-down bin on
                the top of the engine. These bins are not firmware-selectable;
                instead, paper is diverted to the face-down bin only if the face-up
                bin is physically closed.  Therefore, these bins are considered
                together as the 'standard' bin.  
                The value returned by this object depends on the value
                of prtOutputDimUnit. It is 30000 if prtOutputDimUnit is
                ePtenThousandthsOfInches or 76200 if prtOutputDimUnit is ePmicrometers."
::= { prtOutputEntry 18 }
               
               
prtoutputstackingorder OBJECT-TYPE
    SYNTAX  INTEGER {
		   ePunknown(2),
		   ePfirstToLast(3),
		   ePlastToFirst(4)
		   }
    ACCESS  read-only
    STATUS  optional
    DESCRIPTION
                "The current state of the stacking order for the
        associated output sub-unit. `FirstToLast' means
        that as pages are output the front of the next page is
        placed against the back of the previous page.
        `LasttoFirst' means that as pages are output the back
        of the next page is placed against the front of the
        previous page.
	Refer to Internet Draft Printer MIB, expiring Sept. 1997 for more details."
::= { prtOutputEntry 19 }
               
               
prtoutputpagedeliveryorientation OBJECT-TYPE
    SYNTAX  INTEGER {
		   ePfaceUp(3),
		   ePfaceDown(4)
		   }
    ACCESS  read-only
    STATUS  optional
    DESCRIPTION
                "The reading surface that will be `up' when pages are
        delivered to the associated output sub-unit. Values are
        faceUp and faceDown. (Note: interpretation of these
        values is in general context-dependent based on locale;
        presentation of these values to an end-user should be
        normalized to the expectations of the user).
	Refer to Internet Draft Printer MIB, expiring Sept. 1997 for more details."
::= { prtOutputEntry 20 }
               
               
prtoutputbursting OBJECT-TYPE
    SYNTAX  INTEGER {
		   ePother(1),
		   ePon(3),
		   ePoff(4),
		   ePnotPresent(5)
		   }
    ACCESS  read-only
    STATUS  optional
    DESCRIPTION
                "This object indicates that the outputting sub-unit
        supports bursting, and if so, whether the feature is enabled.
        Bursting is the process by which continuous media is separated
        into individual sheets, typically by bursting along pre-formed
        perforations.
	Refer to Internet Draft Printer MIB, expiring Sept. 1997 for more details."
::= { prtOutputEntry 21 }
               
               
prtoutputdecollating OBJECT-TYPE
    SYNTAX  INTEGER {
		   ePother(1),
		   ePon(3),
		   ePoff(4),
		   ePnotPresent(5)
		   }
    ACCESS  read-only
    STATUS  optional
    DESCRIPTION
                "This object indicates that the output supports
        supports decollating, and if so, whether the feature
        is enabled. Decollating is the process by which the
        individual parts within a multi-part form are separated
        and sorted into separate stacks for each part.
	Refer to Internet Draft Printer MIB, expiring Sept. 1997 for more details."
::= { prtOutputEntry 22 }
               
               
prtoutputpagecollated OBJECT-TYPE
    SYNTAX  INTEGER {
		   ePother(1),
		   ePon(3),
		   ePoff(4),
		   ePnotPresent(5)
		   }
    ACCESS  read-only
    STATUS  optional
    DESCRIPTION
                "This object indicates that the output sub-unit
        supports page collation, and if so, whether the feature is
        enabled. See glossary for definition of how this document defines
        collation.
	Refer to Internet Draft Printer MIB, expiring Sept. 1997 for more details."
::= { prtOutputEntry 23 }
               
               
prtoutputoffsetstacking OBJECT-TYPE
    SYNTAX  INTEGER {
		   ePother(1),
		   ePon(3),
		   ePoff(4),
		   ePnotPresent(5)
		   }
    ACCESS  read-only
    STATUS  optional
    DESCRIPTION
                "This object indicates that the output supports
        supports offset stacking, and if so, whether the feature is
        enabled. See glossary for how Offset Stacking is defined by this
        document.
	Refer to Internet Draft Printer MIB, expiring Sept. 1997 for more details."
::= { prtOutputEntry 24 }
               
               
prtmarkersuppliesdescription OBJECT-TYPE
    SYNTAX  OCTET STRING (SIZE(0..255))
    ACCESS  read-only
    STATUS  optional
    DESCRIPTION
                "The description of this supply container/receptacle in the
        localization specified by prtGeneralCurrentLocalization.
	Refer to Internet Draft Printer MIB, expiring Sept. 1997 for more details."
::= { prtMarkerSuppliesEntry 6 }
               
               
prtmediapathmaxspeed OBJECT-TYPE
    SYNTAX  INTEGER
    ACCESS  read-only
    STATUS  optional
    DESCRIPTION
                "The maximum printing speed of this media path expressed in
        prtMediaPathMaxSpeedUnit's.  A value of (-1) implies
        'other'.
	Refer to Internet Draft Printer MIB, expiring Sept. 1997 for more details.
                Additional information:
                The page size for this performance is 8.5x11. The
                duplex speed is based on 6 ppm."
::= { prtMediaPathEntry 4 }
               
               
prtmediapathmaxmediafeeddir OBJECT-TYPE
    SYNTAX  INTEGER
    ACCESS  read-only
    STATUS  optional
    DESCRIPTION
                "The maximum physical media size in the feed direction of this
        media path expressed in units of measure specified by
        PrtMediaPathMediaSizeUnit.  A value of (-1) implies 'unlimited',
        a value of (-2) implies 'unknown'.
	Refer to Internet Draft Printer MIB, expiring Sept. 1997 for more details.
                Additional information:
                The value returned by this object depends on the value
                of prtMediaPathMediaSizeUnit. It is 140000 if prtMediaPathMediaSizeUnit is
                ePtenThousandthsOfInches or 355600 if prtMediaPathMediaSizeUnit is ePmicrometers."
::= { prtMediaPathEntry 5 }
               
               
prtmediapathmaxmediaxfeeddir OBJECT-TYPE
    SYNTAX  INTEGER
    ACCESS  read-only
    STATUS  optional
    DESCRIPTION
                "The maximum physical media size across the feed direction of
        this media path expressed in units of measure specified by
        prtMediaPathMediaSizeUnit.  A value of (-2) implies 'unknown'.
	Refer to Internet Draft Printer MIB, expiring Sept. 1997 for more details.
                Additional information:
                The value returned by this object depends on the value
                of prtMediaPathMediaSizeUnit. It is 85000 if prtMediaPathMediaSizeUnit is
                ePtenThousandthsOfInches and 215900 if prtMediaPathMediaSizeUnit is ePmicrometers."
::= { prtMediaPathEntry 6 }
               
               
prtmediapathminmediafeeddir OBJECT-TYPE
    SYNTAX  INTEGER
    ACCESS  read-only
    STATUS  optional
    DESCRIPTION
                "The minimum physical media size in the feed direction of this
        media path expressed in units of measure specified by
        prtMediaPathMediaSizeUnit. A value of (-2) implies 'unknown'.
	Refer to Internet Draft Printer MIB, expiring Sept. 1997 for more details.
                Additional information:
                The value returned by this object depends on the value
                of prtMediaPathMediaSizeUnit. It is 50000 if prtMediaPathMediaSizeUnit is
                ePtenThousandthsOfInches or 127000 if prtMediaPathMediaSizeUnit is ePmicrometers."
::= { prtMediaPathEntry 7 }
               
               
prtmediapathminmediaxfeeddir OBJECT-TYPE
    SYNTAX  INTEGER
    ACCESS  read-only
    STATUS  optional
    DESCRIPTION
                "The minimum physical media size across the feed direction of
        this media path expressed in units of measure specified by
        prtMediaPathMediaSizeUnit.  A value of (-2) implies 'unknown'.
	Refer to Internet Draft Printer MIB, expiring Sept. 1997 for more details.
                Additional information:
                The value returned by this object depends on the value
                of prtMediaPathMediaSizeUnit. It is 30000 if prtMediaPathMediaSizeUnit is
                ePtenThousandthsOfInches or 76200 if prtMediaPathMediaSizeUnit is ePmicrometers."
::= { prtMediaPathEntry 8 }
               
               
channel-bytes-sent OBJECT-TYPE
    SYNTAX  INTEGER
    ACCESS  read-only
    STATUS  optional
    DESCRIPTION
                "The low order 31 bits of the number of bytes sent from
                the printer to the host on this logical channel."
::= { channel-entry 2 }
               
               
channel-bytes-received OBJECT-TYPE
    SYNTAX  INTEGER
    ACCESS  read-only
    STATUS  optional
    DESCRIPTION
                "The low order 31 bits of the number of bytes received by
                the printer from the host on this logical channel."
::= { channel-entry 3 }
               
               
channel-io-errors OBJECT-TYPE
    SYNTAX  INTEGER
    ACCESS  read-only
    STATUS  optional
    DESCRIPTION
                "The low order 31 bits of the number of I/O errors which
                have occured on this logical channel."
::= { channel-entry 4 }
               
               
channel-jobs-received OBJECT-TYPE
    SYNTAX  INTEGER
    ACCESS  read-only
    STATUS  optional
    DESCRIPTION
                "The low order 31 bits of the number of print jobs which
                have been received on this logical channel."
::= { channel-entry 5 }
               
               
channel-mio OBJECT-TYPE
    SYNTAX  INTEGER
    ACCESS  read-only
    STATUS  optional
    DESCRIPTION
                "The number of the MIO card associated with this logical
                channel.  If this logical channel is not associated with
                an MIO card a zero is returned.  The value 1 is returned
                if this logical channel is associated with an MIO card
                in slot 1.  The value 2 is returned if this logical
                channel is associated with an MIO card in slot 2.
                Additional information:
                The value returned will be zero for channels 1..3.  
                If an MIOA card is installed, channels 4..10 will 
                return a value of one or two. 
                If an MIOB card is installed, channels 11..17 will 
                return a value of one or two but not the 
                same as channels 4..10.
                When two IIO cards are installed, the value 
                returned by any channel 4..17 may change after the 
                printer is power cycled."
::= { channel-entry 6 }
               
               
prtchanneltype OBJECT-TYPE
    SYNTAX  INTEGER {
		   ePother(1),
		   ePchSerialPort(3),
		   ePchIEEE1284Port(5),
		   ePchAppleTalkPAP(7),
		   ePchNetwareRPrinter(9),
		   ePchNetwarePServer(10),
		   ePchBidirPortTCP(38),
		   ePchDLCLLCPort(15)
		   }
    ACCESS  read-only
    STATUS  optional
    DESCRIPTION
                "The type of this print data channel.  This
        object provides the linkage to ChannelType-specific
        groups that may (conceptually) extend the prtChannelTable
        with additional details about that channel.
	Refer to Internet Draft Printer MIB, expiring Sept. 1997 for more details.
                Additional information:
                IIO based channels provide their own values."
::= { prtChannelEntry 2 }
               
               
prtchannelprotocolversion OBJECT-TYPE
    SYNTAX  OCTET STRING (SIZE(0..63))
    ACCESS  read-only
    STATUS  optional
    DESCRIPTION
                "The version of the protocol used on this
        channel.  The format used for version numbering depends
        on prtChannelType.
	Refer to Internet Draft Printer MIB, expiring Sept. 1997 for more details.
                Additional information:
                IIO-based channels provide their own values.
                The channel 1 value includes (separated by semi colons) 
                different aspectsof the spec:  electrical: logical; and 
                physical connector."
::= { prtChannelEntry 3 }
               
               
prtchannelcurrentjobcntllangindex OBJECT-TYPE
    SYNTAX  INTEGER
    ACCESS  read-only
    STATUS  optional
    DESCRIPTION
                "The value of prtInterpreterIndex  corresponding to the
        Control Language Interpreter for this channel. This
        interpreter defines the syntax used for control
        functions, such as querying or changing environment
        variables and identifying job boundaries (e.g. PJL,
        PostScript, NPAP). Must be 1 or greater.
	Refer to Internet Draft Printer MIB, expiring Sept. 1997 for more details.
                Additional information:
                This object points to the PJL language. It is 
                read-only because PJL is the printer's only job 
                control language."
::= { prtChannelEntry 4 }
               
               
prtchanneldefaultpagedesclangindex OBJECT-TYPE
    SYNTAX  INTEGER
    ACCESS  read-write
    STATUS  optional
    DESCRIPTION
                "The value of prtInterpreterIndex  corresponding to the
        Page Description Language Interpreter for this channel.
        This interpreter defines the default Page Description
        Language interpreter to be used for the print data unless
        the Control Language is used to select a specific
        interpreter (e.g.,  PCL, PostScript Language,
        auto-sense). Must be 1 or greater.
	Refer to Internet Draft Printer MIB, expiring Sept. 1997 for more details.
                Additional information:
                The default points to the 
                automatic language switcher. If this object is changed 
                for one channel, all channels will be changed."
::= { prtChannelEntry 5 }
               
               
prtchannelstate OBJECT-TYPE
    SYNTAX  INTEGER {
		   ePother(1),
		   ePprintDataAccepted(3),
		   ePnoDataAccepted(4)
		   }
    ACCESS  read-only
    STATUS  optional
    DESCRIPTION
                "The state of this print data channel.  The value determines
        whether control information and print data is allowed through
        this channel or not.
	Refer to Internet Draft Printer MIB, expiring Sept. 1997 for more details.
                Additional information:
                IIO-based channels provide their own values for this
                object.  The base-printer's ports always report a value of 
                ePprintDataAccepted.
                If the printer is offline, that is detected by reading the 
                Host Resources General Printer Status objects, not by reading 
                this object."
::= { prtChannelEntry 6 }
               
               
prtchannelifindex OBJECT-TYPE
    SYNTAX  INTEGER
    ACCESS  read-only
    STATUS  optional
    DESCRIPTION
                "The value of ifIndex (in the ifTable; see the interface
        section of MIB-2/RFC 1213) which corresponds to this channel.
        When more than one row of the ifTable is relevant, this is
        the index of the row representing the topmost layer in the
        interface hierarchy.  A value of zero indicates that no
        interface is associated with this channel.
	Refer to Internet Draft Printer MIB, expiring Sept. 1997 for more details.
                Additional information:
                IIO-based channels provide their own values for this
                object."
::= { prtChannelEntry 7 }
               
               
prtchannelstatus OBJECT-TYPE
    SYNTAX  INTEGER
    ACCESS  read-only
    STATUS  optional
    DESCRIPTION
                "The current status of the channel.
	Refer to Internet Draft Printer MIB, expiring Sept. 1997 for more details.
                Additional information:
                IIO-based channels provide their own values for this
                object."
::= { prtChannelEntry 8 }
               
               
prtchannelinformation OBJECT-TYPE
    SYNTAX  OCTET STRING (SIZE(0..255))
    ACCESS  read-only
    STATUS  optional
    DESCRIPTION
                "Auxiliary information to allow a printing application to use
        the channel for data submission to the printer.  An application
        capable of using a specific PrtChannelType should be able to use
        the combined information from the prtChannelInformation and
        other channel and interface group objects to 'bootstrap' its use
        of the channel.  prtChannelInformation is not intended to
        provide a general channel description, nor to provide
        information that is available once the channel is in use. 
        The encoding and interpretation of the prtChannelInformation
        object is specific to channel type.  The description of each
        PrtChannelType enum value for which prtChannelInformation is
        defined specifies the appropriate encoding and interpretation,
        including interaction with other objects.  For channel types
        that do not specify a prtChannelInformation value, its value
        shall be null (0 length).  
        When a new PrtChannelType enumeration value is registered, its
        accompanying description must specify the encoding and
        interpretation of the prtChannelInformation value for the
        channel type.  prtChannelInformation semantics for an existing
        PrtChannelType may be added or amended in the same manner as
        described in section 2.4.1 for type 2 enumeration values.
        The prtChannelInformation specifies values for a collection of
        channel attributes, represented as text according to the
        following rules: 
         1. The prtChannelInformation is coded in the NVT ASCII
            character set.  It is not affected by localization. 
         2. The prtChannelInformation is a list of entries representing
            the attribute values.  Each entry consists of the following
            items, in order: 
             a. a keyword, composed of alphabetic characters (A-Z,
                a-z), that identifies a channel attribute,
             b. an Equals Sign (=) to delimit the keyword,
             c. a data value, consisting of NVT ASCII graphics
                characters (codes 32-126),
             d. a Line Feed character (code 10) to delimit the data
                value. 
            No other characters shall be present. 
            Keywords are case-sensitive.  Conventionally, keywords are
            capitalized (including each word of a multi-word keyword),
            and, since they occupy space in the prtChannelInformation,
            they are kept short. 
         3. If a channel attribute has multiple values, it is
            represented by multiple entries with the same keyword, each
            specifying one value.  Otherwise, there shall be at most
            one entry for each attribute. 
         4. By default, entries may appear in any order.  If there are
            ordering constraints for particular entries, these must be
            specified in their definitions. 
         5. The prtChannelInformation value may represent information
            that is not normally coded in textual form, or that is coded
            in a character set other than NVT ASCII.  In these cases,
            whatever symbolic representation is conventionally used for
            the information should be used for encoding the
            prtChannelInformation.  (For instance, a binary port value
            might be represented as a decimal number, Unicode would
            be represented in UTF-8 format.) 
         6. For each PrtChannelType for which prtChannelInformation
            entries are defined, the descriptive text associated with the
            PrtChannelType enumeration value shall specify the following
            information for each entry: 
            Title:          Brief description phrase, e.g.: 'Port name',
                            'Service Name',
            Keyword:        The keyword value, eg: 'Port', 'Service'
            Syntax:         The encoding of the entry value, if it
                            cannot be directly represented by NVT ASCII,
            Status:         'Mandatory', 'Optional', or 'Conditionally
                            Mandatory',
            Multiplicity:   'Single' or 'Multiple', to indicate whether
                            the entry may be present multiple times,
            Description:    Description of the use of the entry, other
                            information required to complete the
                            definition (e.g.: ordering contstraints,
                            interactions between entries). 
        Applications that interpret prtChannelInformation should ignore
        unrecognized entries, so they are not affected if new entry
        types are added.
		
	Refer to Internet Draft Printer MIB, expiring Sept. 1997 for more details.
                Additional information:
                IIO-based channels provide their own values for this
                object."
::= { prtChannelEntry 9 }
               
               
energy-star OBJECT-TYPE
    SYNTAX  INTEGER
    ACCESS  read-write
    STATUS  optional
    DESCRIPTION
                "Returns or changes the Energy Star sleep value.  If the
                value is greater than zero, then the device will go into
                energy saving sleep mode after the print engine has been
                idle for the number of seconds specified by this object.
                A value of zero means Energy Star is disabled and the
                device will not go to sleep based on print engine idle
                time.  The value must be non-negative.
                Additional information:
                Returns or changes the Energy Star sleep value. 
                The device will go into energy saving sleep 
                mode after the print engine has been idle for 
                the number of seconds specified by this 
                object.   
                
                Supported values are 0, 900, 1800, 
                3600, 7200, and 10800.  A value of 0 means 
                never go to sleep based on print engine idle 
                time.  Setting to an unsupported value causes  
                the printer to substitute a value (listed 
                below) and to return <noError> 
                status.   
                The values are as follow:   
                <=0 snap to 0   
                >=1 and <=1349 snap to 900 (15 minutes)    
                >=1350 and <=2699 snap to 1800 (30 minutes)   
                >=2700 and <=5399 snap to 3600 (1 hour)   
                >=5400 and <=8999 snap to 7200 (2 hours)   
                >=9000 snap to 10800  (3 hours)"
::= { settings-system 1 }
               
               
sleep-mode OBJECT-TYPE
    SYNTAX  INTEGER {
		   eFalse(1),
		   eTrue(2)
		   }
    ACCESS  read-write
    STATUS  optional
    DESCRIPTION
                "Returns eTrue if the device is in energy saving sleep
                mode, otherwise returns eFalse.  Setting SLEEP-MODE to
                eFalse causes the device to wake up, if it is in sleep
                mode.  Setting SLEEP-MODE to eTrue causes the device to
                go into sleep mode.
                Additional information:
                This object returns eTrue if the device is in
                energy saving sleep mode, otherwise it returns eFalse.  
                Setting this object to eTrue while the printer
                is awake will not change the printer's current state
                and will return <genErr>
                status.   
                Setting this object to eTrue while printer is already 
                in Sleep Mode will not change the printer's 
                current state and will return <noError> status.   
                Setting this object to eFalse while printer is already 
                awake  will not change the printer's current state and 
                will return <noError> status.  
                Setting this object to eFalse while the printer is 
                asleep causes the device to wake up.   "
::= { settings-system 2 }
               
               
on-off-line OBJECT-TYPE
    SYNTAX  INTEGER {
		   eOnline(1),
		   eOffline(2),
		   eOfflineAtEndOfJob(3)
		   }
    ACCESS  read-write
    STATUS  optional
    DESCRIPTION
                "To bring the PDL processing sub-system on or off line.
                If the device is a printer, then the printer does not
                process print job data when the printer is off line.
                PML communication persists.
                Additional information:
                When the printer is in the Offline state, 
                printing will stop as soon as possible (no more sheets
                of media are pulled from input trays).  The I/O
                is taken offline also.  
                
                Setting to eOnline has the following affect:
                Printer will immediately go to or remain in the Online
                state; <noError> status is returned.  
                If the printer's current state
                is Offline with a pending error condition that
                prevents the printer from going to the Online
                state, the printer will remain in the Offline state;
                <genErr> status is returned
                
                Setting to eOffline has the following affect:
                Printer will immediately go to or remain in the
                Offline state; <noError> status is returned.
                If pages are being printed, those pages will complete
                with the printer in the Offline state.   
                
                Setting to eOfflineAtEndOfJob has the following
                affect:  
                If not in a job or already in the Offline state, the
                printer will immediately go to or remain in the
                Offline state; <noError> status is returned.  
                If in a job and the current state is Online, the
                printer will remain in the Online state, with the
                value of this object as eOfflineAtEndOfJob, until the
                end of the job; <noError> status is returned. At the end of
                the job, the printer goes to the Offline state and the
                value of this object becomes eOffline.  
                Setting this object to eOffline or eOnline before the
                end of the job causes the action for that value to be
                taken immediately."
::= { status-system 5 }
               
               
continue OBJECT-TYPE
    SYNTAX  INTEGER {
		   eInitiateAction(1)
		   }
    ACCESS  write-only
    STATUS  optional
    DESCRIPTION
                "A device can support a class of errors called
                continuable errors.  When a continuable error is
                encountered, the device requires a continue event to
                occur before the device will continue operation.  One
                continue event is setting the CONTINUE object to
                eInitiateAction.  Devices can support other continue
                events, like auto-continue.  A continue event causes the
                continuable error to be acknowledged, thus allowing the
                device to continue.  Each device needs to list the
                continuable errors.  If the device doesn't currently
                have an unacknowledged continuable error, the response
                will contain <genErr>.
                Additional information:
                See the CLEARABLE-WARNING and AUTO-CONTINUE objects for the 
                errors that this object will clear."
::= { status-system 6 }
               
               
auto-continue OBJECT-TYPE
    SYNTAX  INTEGER {
		   eOff(1),
		   eOn(2)
		   }
    ACCESS  read-write
    STATUS  optional
    DESCRIPTION
                "Indicates if the device will automatically continue
                after encountering a continuable error.  If AUTO-
                CONTINUE is set to eOn, the device will automatically
                generate continue event to acknowledge continuable
                errors.  If AUTO-CONTINUE is set to eOff, then some
                other continue event will have to acknowledge the
                continuable error.
                Additional information:
                If this is set to eOn the device displays an
                error message and goes offline for ten seconds.  After ten seconds the
                printer automatically returns to the online state.  
                
                If this is set to eOff then the device displays an error message and
                goes offline.  It remains offline until the operator presses the GO key or
                until the CONTINUE object is set.  
                
                If the printer is not idle, the new value may not take effect
                until a job boundary is reached. If a get is done on this object before
                the job boundary is reached, the value last set will be returned."
::= { status-system 7 }
               
               
background-status-msg-line1-part1 OBJECT-TYPE
    SYNTAX  DisplayString (SIZE(0..16))
    ACCESS  read-write
    STATUS  optional
    DESCRIPTION
                "The string displayed on the device's front panel in
                place of the printer's built-in background status
                string.  An example built-in background status string is
                '00 READY'.
                Additional information:
                The display size for  The LJ Series 4000 is 2 X 16.
                The value of this object and the current value of
                BACKGROUND-STATUS-MSG-LINE2-PART1 are displayed
                together on the 2-line display, but they must 
                be set independently.  If line 2 has been set, and the
                next message to be displayed only requires line 1,
                BACKGROUND-STATUS-MSG-LINE2-PART1 must be set to the 
                null string to clear it.  
                This object allows a message to be displayed when
                it is the highest priority message. Setting this
                object does not guarantee the message will be
                displayed; and reading it returns the value last
                written, not the currently displayed message (use
                prtConsoleDisplayBufferText to read the
                display).  
                The priority assigned for displaying this message
                is one lower than the READY message.  In other words,
                the only message that can be replaced by these
                objects is the READY message.  
                To clear the message, write a null string to both
                this object and BACKGROUND-STATUS-MSG-LINE2-PART1."
::= { background-message1 1 }
               
               
background-status-msg-line2-part1 OBJECT-TYPE
    SYNTAX  DisplayString (SIZE(0..16))
    ACCESS  read-write
    STATUS  optional
    DESCRIPTION
                "The string displayed on the device's front panel in
                place of the printer's built-in background status
                string.  An example built-in background status string is
                '00 READY'.
                Additional information:
                See BACKGROUND-STATUS-MSG-LINE1-PART1"
::= { background-message2 1 }
               
               
error-log-clear OBJECT-TYPE
    SYNTAX  INTEGER {
		   eClearErrorLog(1)
		   }
    ACCESS  write-only
    STATUS  optional
    DESCRIPTION
                "Setting this object clears all the entries in the error
                log sub-tree.
                Additional information:
                Setting this object removes all errors that have been
                stored in the printer's non-volatile memory."
::= { status-system 38 }
               
               
localization-languages-supported OBJECT-TYPE
    SYNTAX  DisplayString
    ACCESS  read-only
    STATUS  optional
    DESCRIPTION
                "The list of languages supported by the device. The
                languages are primarily, but not limited to, two
                character codes from ISO 639, each separated by a comma
                character.
                Additional information:
                This string will always be in the Roman-8 character
                set.  See prtLocalizationLanguage for details about each language value."
::= { status-system 52 }
               
               
localization-countries-supported OBJECT-TYPE
    SYNTAX  DisplayString
    ACCESS  read-only
    STATUS  optional
    DESCRIPTION
                "The list of countries supported by the device. The
                countries are primarily, but not limited to, two
                character codes from ISO 3166, each separated by a comma
                character.
                Additional information:
                This string will always be in the Roman-8 character
                set.  See prtLocalizationCountry for details about each country value."
::= { status-system 53 }
               
               
model-number OBJECT-TYPE
    SYNTAX  DisplayString
    ACCESS  read-only
    STATUS  optional
    DESCRIPTION
                "Identifies the device model number as listed in the HP
                corporate price list (e.g.  C2121A for DeskJet 500C).
                The string is as specific as possible.  Products should
                note in POS if the model number on the CPL changes but
                the device reports the previous model number.  If the
                model number changes based on the installed options, the
                POS should indicate if only the base model number is
                returned, or if the device senses the installed options
                and returns the correct model number.  If possible,
                encode the model number in a symbol set (like Roman-8)
                that matches the ASCII character set and limit the
                characters used to ASCII characters.
                Additional information:
                The value of this object does not change based on
                the installed options."
::= { id 1 }
               
               
serial-number OBJECT-TYPE
    SYNTAX  DisplayString (SIZE(0..11))
    ACCESS  read-only
    STATUS  optional
    DESCRIPTION
                "Identifies the serial number for the device.  If the
                SERIAL-NUMBER object is set by the user, then setting
                the object does not need to be protected.  If the
                SERIAL-NUMBER object is set at the factory, then the
                SERVICE-PASSWORD object must be set correctly before the
                SERIAL-NUMBER object is writable.  If this is a writable
                object, the POS should indicate the maximum supported
                string length.  If possible, encode the serial number in
                a symbol set (like Roman-8) that matches the ASCII
                character set and limit the characters used to ASCII
                characters.
                Additional information:
                This value IS AFFECTED BY NVRAM resets, it is set to the 
                default value of S46XXXXXXXX, when a NVRAM init is done."
::= { id 3 }
               
               
device-location OBJECT-TYPE
    SYNTAX  DisplayString
    ACCESS  read-write
    STATUS  optional
    DESCRIPTION
                "User defined device location.  The POS should indicate
                the maximum supported string length.  If the user
                entered string is too long, the device will store as
                much as possible and will return the <noError>.

                Additional information:
                The maximum supported string length is 16 
                characters.  If the user entered string is too long, 
                the device will store the first 16 characters and will 
                return the <noError> status."
::= { id 11 }
               
               
asset-number OBJECT-TYPE
    SYNTAX  DisplayString
    ACCESS  read-write
    STATUS  optional
    DESCRIPTION
                "User defined asset number.  The POS should indicate the
                maximum supported string length.  If the user entered
                string is too long, the device will store as much as
                possible and will return the <noError>.

                Additional information:
                The maximum supported string length is 8 
                characters.  If the user entered string is too long, 
                the device will store the first 8 characters and will  
                return the <noError> status."
::= { id 12 }
               
               
simm1-type OBJECT-TYPE
    SYNTAX  INTEGER {
		   eEmpty(1),
		   eUnknown(2),
		   eUnSupported(3),
		   eReadOnlyMemory(4),
		   eVolatileRandomAccessMemory(5),
		   eFlashMemory(7),
		   eRamRom(9)
		   }
    ACCESS  read-only
    STATUS  optional
    DESCRIPTION
                "Returns an indication of the type of option installed in
                SIMM slot 1.
                  eEmpty means the device did not detect any option
                installed in the interface slot.
                  eUnknown means the device doesn't recognize the
                installed option.
                  eUnSupported means the device recognizes the installed
                option, but does not support the option.
                  eReadOnlyMemory means the installed option contains
                ROM Ics.
                  eVolatileRandomAccessMemory means the installed option
                contains RAM ICs that loose data when the power is
                turned off.
                  eNonVolatileRandomAccessMemory means that the
                installed option contains RAM ICs that do not loose data
                when the power is turned off.
                  eFlashMemory means that the installed option contains
                a type of non-volatile RAM that needs to be erased
                before it can be written.
                  eDiskDrive means the installed option contains a disk
                drive.  eRamRom means the installed option contains both
                volatile random access memory and read only memory.
                  eInputPHD means the installed option is an input paper
                handling device.
                  eOutputPHD means the installed option is an output
                paper handling device.
                  eIOCard means the installed option is an I/O card.
                Additional information:
                This object is used for describing DIMMs instead
                of SIMMs on The LJ Series 4000. eRamRom is used to denote the combo simm."
::= { simm1 4 }
               
               
simm1-capacity OBJECT-TYPE
    SYNTAX  INTEGER
    ACCESS  read-only
    STATUS  optional
    DESCRIPTION
                "Returns an indication of the capacity of the SIMM
                installed in SIMM slot 1.  The capacity is dependent on
                the type of option, as indicated by the SIMM1-TYPE
                object.  This object has no meaning if the installed
                option type is eUnknown or eReadOnlyMemory.  This object
                contains the size, in bytes, if the installed option
                type is eVolatileRandomAccessMemory,
                eNonVolatileRandomAccessMemory, eFlashMemory, or
                eDiskDrive.  If the type of the installed option is
                eRamRom, this object contains the size, in bytes, of the
                random access memory.  If the type of the installed
                option is eInputPHD, the capacity indicates the number
                of input trays supported by the installed option.  If
                the type of the installed option is eOutputPHD, the
                capacity indicates the number of output bins supported
                by the installed option.  If the type of the installed
                option is eIOCard, the capacity indicates the number of
                logical I/O ports supported by the I/O card.
                Additional information:
                Returns an indication of the capacity of the 
                installed option in bytes.  This object is not 
                supported unless the SIMM1-TYPE type is 
                eVolatileRandomAccessMemory, eRamRom, or eFlashMemory.
                For eRamRom only the size of the Ram portion of the SIMM
                is returned."
::= { simm1 5 }
               
               
simm2-type OBJECT-TYPE
    SYNTAX  INTEGER {
		   eEmpty(1),
		   eUnknown(2),
		   eUnSupported(3),
		   eReadOnlyMemory(4),
		   eVolatileRandomAccessMemory(5),
		   eFlashMemory(7),
		   eRamRom(9)
		   }
    ACCESS  read-only
    STATUS  optional
    DESCRIPTION
                "Returns an indication of the type of option installed in
                SIMM slot 2.  See SIMM1-TYPE for a description.
                Additional information:
                This object is used for describing DIMMs instead
                of SIMMs on The LJ Series 4000. eRamRom is used to denote the combo simm."
::= { simm2 4 }
               
               
simm2-capacity OBJECT-TYPE
    SYNTAX  INTEGER
    ACCESS  read-only
    STATUS  optional
    DESCRIPTION
                "Returns an indication of the capacity of the SIMM
                installed in SIMM slot 2.  See SIMM1-CAPACITY for a
                description.
                Additional information:
                This object is used for describing DIMMs instead
                of SIMMs on The LJ Series 4000. Returns an indication of the capacity of the 
                installed option in bytes.  This object is not 
                supported unless the SIMM2-TYPE type is 
                eVolatileRandomAccessMemory, eRamRom, or eFlashMemory.
                For eRamRom only the size of the Ram portion of the 
                SIMM is returned."
::= { simm2 5 }
               
               
simm3-type OBJECT-TYPE
    SYNTAX  INTEGER {
		   eEmpty(1),
		   eUnknown(2),
		   eUnSupported(3),
		   eReadOnlyMemory(4),
		   eVolatileRandomAccessMemory(5),
		   eFlashMemory(7),
		   eRamRom(9)
		   }
    ACCESS  read-only
    STATUS  optional
    DESCRIPTION
                "Returns an indication of the type of option installed in
                SIMM slot 3.  See SIMM1-TYPE for a description."
::= { simm3 4 }
               
               
simm3-capacity OBJECT-TYPE
    SYNTAX  INTEGER
    ACCESS  read-only
    STATUS  optional
    DESCRIPTION
                "Returns an indication of the capacity of the SIMM
                installed in SIMM slot 3.  See SIMM1-CAPACITY for a
                description.
                Additional information:
                This object is used for describing DIMMs instead
                of SIMMs on The LJ Series 4000. Returns an indication of the capacity of the 
                installed option in bytes.  This object is not 
                supported unless the SIMM3-TYPE type is 
                eVolatileRandomAccessMemory, eRamRom, or eFlashMemory.
                For eRamRom only the size of the Ram portion of the 
                simm is returned."
::= { simm3 5 }
               
               
simm4-type OBJECT-TYPE
    SYNTAX  INTEGER {
		   eEmpty(1),
		   eUnknown(2),
		   eUnSupported(3),
		   eReadOnlyMemory(4),
		   eVolatileRandomAccessMemory(5),
		   eFlashMemory(7),
		   eRamRom(9)
		   }
    ACCESS  read-only
    STATUS  optional
    DESCRIPTION
                "Returns an indication of the type of option installed in
                SIMM slot 4.  See SIMM1-TYPE for a description.
                Additional information:
                This object is used for describing DIMMs instead
                of SIMMs on The LJ Series 4000. eRamRom is used to denote the combo simm."
::= { simm4 4 }
               
               
simm4-capacity OBJECT-TYPE
    SYNTAX  INTEGER
    ACCESS  read-only
    STATUS  optional
    DESCRIPTION
                "Returns an indication of the capacity of the SIMM
                installed in SIMM slot 4.  See SIMM1-CAPACITY for a
                description.
                Additional information:
                This object is used for describing DIMMs instead
                of SIMMs on The LJ Series 4000. Returns an indication of the capacity of the 
                installed option in bytes.  This object is not 
                supported unless the SIMM4-TYPE type is 
                eVolatileRandomAccessMemory, eRamRom, or eFlashMemory.
                For eRamRom only the size of the Ram portion of the 
                SIMM is returned."
::= { simm4 5 }
               
               
self-test OBJECT-TYPE
    SYNTAX  INTEGER {
		   eNotInASelfTest(1),
		   eNonDestructiveSelfTest(4)
		   }
    ACCESS  read-write
    STATUS  optional
    DESCRIPTION
                "Writing this object allows a device self test to be
                started.  Reading this object provides an indication
                what self-test is currently executing, if any.  Actual
                self-test operation is device specific.  A self test may
                not be allowed at any arbitrary time.  If the device
                supports the requested self test, but can not start the
                execution of the self test when requested, the device
                will respond with <genErr>.  If
                a non-destructive self test is being started, the device
                will generate a response before the self test is
                completed.
                RECOMMENDATION:  If the device is ready (i.e. the NOT-
                READY-PRINTER object does not contain any items, except
                maybe being off-line) and is idle (i.e. the NOT-IDLE
                object does not contain any items), this request should
                always succeed.  This provides a mechanism for driver
                writers to always determine if the action will succeed
                or not.
                Additional information:
                The eNonDestructiveSelfTest performs limited
                testing on the printer and its attached paper handling
                devices. After the self-test is complete a
                configuration page is printed. The recommended
                way to cause a configuration page to be printed is to
                use the PRINT-INTERNAL-PAGE object.  
                
                Setting this object to eNonDestructiveSelfTest results in a status of <noError>
                and a value of eNonDestructiveSelfTest being returned.
                If the printer is not idle (whether printing an external job or printing
                an internal page), this action will be delayed until the next job boundary.
                
                See the PRINT-INTERNAL-PAGE object for more details."
::= { test 1 }
               
               
print-internal-page OBJECT-TYPE
    SYNTAX  INTEGER {
		   eNotPrintingAnInternalPage(1),
		   ePrintingAnUnknownInternalPage(2),
		   eDeviceDemoPage1ConfigurationPage(3),
		   eDeviceDemoPage5ErrorLog(7),
		   eDeviceDemoPage6FileSystemDirectoryListing(8),
		   eDeviceDemoPage7MenuMap(9),
		   ePCLFontList1(350),
		   ePSFontList(450)
		   }
    ACCESS  read-write
    STATUS  optional
    DESCRIPTION
                "Writing this object to a value other than
                eNotPrintingAnInternalPage causes the device to attempt
                to print an internally generated page.  Reading this
                object provides an indication what internally generated
                page is currently being printed, if any.  The actual
                page is device specific.  Some devices may support
                continuously printing an internally generated page.
                Setting this object to eNotPrintingAnInternalPage
                terminates continuously printing internally generated
                pages.  An internally generated page may not be allowed
                to be printed at any arbitrary time; under what
                conditions it will succeed or fail is device specific.
                If the device supports the requested page, but can not
                start printing the page when requested, the device will
                respond with <genErr>.
                RECOMMENDATION:  If the device is ready (i.e. the NOT-
                READY-PRINTER object does not contain any items, except
                maybe being off-line) and is idle (i.e. the NOT-IDLE
                object does not contain any items), this request should
                always succeed.  This provides a mechanism for driver
                writers to always determine if the action will succeed
                or not.
                Additional information:
                Previous products used 
                ePCLDemoPage1ConfigurationPage(300) for the
                Configuration or Self Test page.  This product uses
                eDeviceDemoPage1ConfigurationPage(3).  
                
                The LJ Series 4000 does not support continuously printing a demo page.  
                
                When this object is set to a valid value, the status returned is <noError>
                and the value returned is ePrintingAnUnknownInternalPage.  If the printer
                is idle, the page will be printed immediately.  If the printer is
                currently printing another job, the internal page requested will not print
                until that job is finished.  
                
                Setting this object to a valid value causes the
                desired page to be formatted and put in the printer's
                print queue.  While the page is being formatted a get on this object will
                return the value ePrintingAnUnknownInternalPage.  Once the page (or pages)
                is finished being formatted, this object returns a value of
                eNotPrintingAnInternalPage, even though the page may not have finished
                being printed.  
                
                Setting this object multiple times will queue up the requests, but only
                a limited number will be queued.  Once the queue is full, additional
                requests will be ignored."
::= { test 2 }
               
               
clearable-warning OBJECT-TYPE
    SYNTAX  INTEGER {
		   eOn(2),
		   eJob(3)
		   }
    ACCESS  read-write
    STATUS  optional
    DESCRIPTION
                "Returns or controls how the device will track clearable
                warnings.  A clearable warning indicates a transient
                event in the device.  The device will continue after the
                transient event occurs.  If CLEARABLE-WARNING is eOff,
                the device does not track clearable warnings.  If
                CLEARABLE-WARNING is eOn, all clearable warnings will be
                tracked until cleared (acknowledged).  If CLEARABLE-
                WARNING is eJob, a clearable warning generated due to an
                event that occurs because of the print job being
                processed will be automatically cleared when the device
                has finished processing the job.  Example clearable
                warning events include the device altering resolution or
                page protection due to memory constraints.  The POS will
                document what transient events are treated as clearable
                warnings.
                Additional information:
                If set to eOn, the warning is displayed until the GO key
                is pressed or the CONTINUE object is set.  
                
                If set to eJob, the warning is displayed until the end of the job in which
                it was generated."
::= { settings-job 1 }
               
               
cancel-job OBJECT-TYPE
    SYNTAX  INTEGER(0..32767)
    ACCESS  write-only
    STATUS  optional
    DESCRIPTION
                "Cancels the print job whose ID matches the value written
                to the CANCEL-JOB object.  The host first learns the job
                ID using the CURRENT-JOB-PARSING-ID command.  If the
                printer has completely processed the job, the printer
                responds with <badValue>.  If the
                value of the CURRENT-JOB-PARSING-ID is smaller than the
                value written to the CANCEL-JOB object, then the printer
                responds with <badValue>.  When
                read, returns the value of the last job ID what was
                canceled, or -1 to indicate no job has been canceled.
                Additional information:
                If the value written matches the ID of a job that is
                currently being canceled (for any reason),
                the printer responds with <noError>.  
                The LJ Series 4000 uses job ID's in the range of 0..32767.
                Because the ID number can wrap to zero,
                CURRENT-JOB-PARSING-ID may be smaller than the value
                written to this object; when this occurs, no error
                will result as long as the ID is for a currently
                processing job.  This object is write only, so the
                comment in the general description stating the
                job ID or -1 will be returned on a read does not
                apply."
::= { settings-job 2 }
               
               
error1-time-stamp OBJECT-TYPE
    SYNTAX  INTEGER
    ACCESS  read-only
    STATUS  optional
    DESCRIPTION
                "Contains a time stamp indicating when error 1
                occurred.  Example time stamps include the actual time
                the error occurred (in seconds since Jan. 1, 1970), and
                the total engine page count.  The device POS documents
                the meaning of the time stamp.
                Additional information:
                This item contains the engine
                page count when the error occurred.  
                
                If there is currently no error entry for this object, a '0' will be returned.
                Note that '0' may also be returned when there is a valid error, but a current
                page count was unavailable.  If ERROR1-CODE object also returns '0', then
                an error has not yet been logged for this object.
                
                See ERROR1-CODE for an explanation of the order used for storing errors."
::= { error1 1 }
               
               
error1-code OBJECT-TYPE
    SYNTAX  INTEGER
    ACCESS  read-only
    STATUS  optional
    DESCRIPTION
                "Contains a device specific error code.  Each device POS
                should list what errors are logged to the error log and
                the meaning of each supported error code value.
                Additional information:
                Returns a device specific error code.
                If the error code returned is '0', then the printer has not yet logged an
                error for this object.
                When the maximum number of errors is reached (30 on THE LJ SERIES 4000), and
                a new error occurs, the error in ERROR1-CODE will be replaced by the
                one in ERROR2-CODE, and so on until the last error object will be given
                the value of the new error.  
                
                The error number is returned in the upper 16 bits. 
                If it is 68, 69, 79, or 80, then the sub code is returned in the lower
                16 bits (eg. 68 001C, where the subcode is already a hexadecimal value). 
                If the error number is any other number, then the 1st sub code (XX) 
                will be in bits 15-8 and the 2nd sub code (YY) will be in bits 7-0 (eg.
                55.04.02) where XX=04 and YY=02).  
                
                Example: If the error is 68 001A, then the value returned will be 4456474.  
                To break it down: 4456474 = 0x0044001A  
                The upper 16 bits: 0x0044 = 68  
                The lower 16 bits: 0x001A = 001A
                Which is the error: 68 001A  
                
                Example: If the error is 55.04.241, then the error code will be 3605745.  
                To break it down: 3605745 = 0x003704F1  
                The upper 16 bits: 0x0037 = 55  
                The upper byte of the lower 16 bits: 0x04 = 04  
                The lower byte of the lower 16 bits: 0xF1 = 241  
                Which is the error: 55.04.241"
::= { error1 2 }
               
               
error2-time-stamp OBJECT-TYPE
    SYNTAX  INTEGER
    ACCESS  read-only
    STATUS  optional
    DESCRIPTION
                "Contains a time stamp indicating when error 2
                occurred.  Example time stamps include the actual time
                the error occurred (in seconds since Jan. 1, 1970), and
                the total engine page count.  The device POS documents
                the meaning of the time stamp.
                Additional information:
                See ERROR1-TIME-STAMP."
::= { error2 1 }
               
               
error2-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error2 2 }
               
               
error3-time-stamp OBJECT-TYPE
    SYNTAX  INTEGER
    ACCESS  read-only
    STATUS  optional
    DESCRIPTION
                "Contains a time stamp indicating when error 3
                occurred.  Example time stamps include the actual time
                the error occurred (in seconds since Jan. 1, 1970), and
                the total engine page count.  The device POS documents
                the meaning of the time stamp.
                Additional information:
                See ERROR1-TIME-STAMP."
::= { error3 1 }
               
               
error3-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error3 2 }
               
               
error4-time-stamp OBJECT-TYPE
    SYNTAX  INTEGER
    ACCESS  read-only
    STATUS  optional
    DESCRIPTION
                "Contains a time stamp indicating when error 4
                occurred.  Example time stamps include the actual time
                the error occurred (in seconds since Jan. 1, 1970), and
                the total engine page count.  The device POS documents
                the meaning of the time stamp.
                Additional information:
                See ERROR1-TIME-STAMP."
::= { error4 1 }
               
               
error4-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error4 2 }
               
               
error5-time-stamp OBJECT-TYPE
    SYNTAX  INTEGER
    ACCESS  read-only
    STATUS  optional
    DESCRIPTION
                "Contains a time stamp indicating when error 5
                occurred.  Example time stamps include the actual time
                the error occurred (in seconds since Jan. 1, 1970), and
                the total engine page count.  The device POS documents
                the meaning of the time stamp.
                Additional information:
                See ERROR1-TIME-STAMP."
::= { error5 1 }
               
               
error5-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error5 2 }
               
               
error6-time-stamp OBJECT-TYPE
    SYNTAX  INTEGER
    ACCESS  read-only
    STATUS  optional
    DESCRIPTION
                "Contains a time stamp indicating when error 6
                occurred.  Example time stamps include the actual time
                the error occurred (in seconds since Jan. 1, 1970), and
                the total engine page count.  The device POS documents
                the meaning of the time stamp.
                Additional information:
                See ERROR1-TIME-STAMP."
::= { error6 1 }
               
               
error6-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error6 2 }
               
               
error7-time-stamp OBJECT-TYPE
    SYNTAX  INTEGER
    ACCESS  read-only
    STATUS  optional
    DESCRIPTION
                "Contains a time stamp indicating when error 7
                occurred.  Example time stamps include the actual time
                the error occurred (in seconds since Jan. 1, 1970), and
                the total engine page count.  The device POS documents
                the meaning of the time stamp.
                Additional information:
                See ERROR1-TIME-STAMP."
::= { error7 1 }
               
               
error7-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error7 2 }
               
               
error8-time-stamp OBJECT-TYPE
    SYNTAX  INTEGER
    ACCESS  read-only
    STATUS  optional
    DESCRIPTION
                "Contains a time stamp indicating when error 8
                occurred.  Example time stamps include the actual time
                the error occurred (in seconds since Jan. 1, 1970), and
                the total engine page count.  The device POS documents
                the meaning of the time stamp.
                Additional information:
                See ERROR1-TIME-STAMP."
::= { error8 1 }
               
               
error8-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error8 2 }
               
               
error9-time-stamp OBJECT-TYPE
    SYNTAX  INTEGER
    ACCESS  read-only
    STATUS  optional
    DESCRIPTION
                "Contains a time stamp indicating when error 9
                occurred.  Example time stamps include the actual time
                the error occurred (in seconds since Jan. 1, 1970), and
                the total engine page count.  The device POS documents
                the meaning of the time stamp.
                Additional information:
                See ERROR1-TIME-STAMP."
::= { error9 1 }
               
               
error9-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error9 2 }
               
               
error10-time-stamp OBJECT-TYPE
    SYNTAX  INTEGER
    ACCESS  read-only
    STATUS  optional
    DESCRIPTION
                "Contains a time stamp indicating when error
                10 occurred.  Example time stamps include the actual
                time the error occurred (in seconds since Jan. 1, 1970),
                and the total engine page count.  The device POS
                documents the meaning of the time stamp.
                Additional information:
                See ERROR1-TIME-STAMP."
::= { error10 1 }
               
               
error10-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error10 2 }
               
               
error11-time-stamp OBJECT-TYPE
    SYNTAX  INTEGER
    ACCESS  read-only
    STATUS  optional
    DESCRIPTION
                "Contains a time stamp indicating when error
                11 occurred.  Example time stamps include the actual
                time the error occurred (in seconds since Jan. 1, 1970),
                and the total engine page count.  The device POS
                documents the meaning of the time stamp.
                Additional information:
                See ERROR1-TIME-STAMP."
::= { error11 1 }
               
               
error11-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error11 2 }
               
               
error12-time-stamp OBJECT-TYPE
    SYNTAX  INTEGER
    ACCESS  read-only
    STATUS  optional
    DESCRIPTION
                "Contains a time stamp indicating when error
                12 occurred.  Example time stamps include the actual
                time the error occurred (in seconds since Jan. 1, 1970),
                and the total engine page count.  The device POS
                documents the meaning of the time stamp.
                Additional information:
                See ERROR1-TIME-STAMP."
::= { error12 1 }
               
               
error12-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error12 2 }
               
               
error13-time-stamp OBJECT-TYPE
    SYNTAX  INTEGER
    ACCESS  read-only
    STATUS  optional
    DESCRIPTION
                "Contains a time stamp indicating when error
                13 occurred.  Example time stamps include the actual
                time the error occurred (in seconds since Jan. 1, 1970),
                and the total engine page count.  The device POS
                documents the meaning of the time stamp.
                Additional information:
                See ERROR1-TIME-STAMP."
::= { error13 1 }
               
               
error13-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error13 2 }
               
               
error14-time-stamp OBJECT-TYPE
    SYNTAX  INTEGER
    ACCESS  read-only
    STATUS  optional
    DESCRIPTION
                "Contains a time stamp indicating when error
                14 occurred.  Example time stamps include the actual
                time the error occurred (in seconds since Jan. 1, 1970),
                and the total engine page count.  The device POS
                documents the meaning of the time stamp.
                Additional information:
                See ERROR1-TIME-STAMP."
::= { error14 1 }
               
               
error14-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error14 2 }
               
               
error15-time-stamp OBJECT-TYPE
    SYNTAX  INTEGER
    ACCESS  read-only
    STATUS  optional
    DESCRIPTION
                "Contains a time stamp indicating when error
                15 occurred.  Example time stamps include the actual
                time the error occurred (in seconds since Jan. 1, 1970),
                and the total engine page count.  The device POS
                documents the meaning of the time stamp.
                Additional information:
                See ERROR1-TIME-STAMP."
::= { error15 1 }
               
               
error15-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error15 2 }
               
               
error16-time-stamp OBJECT-TYPE
    SYNTAX  INTEGER
    ACCESS  read-only
    STATUS  optional
    DESCRIPTION
                "Contains a time stamp indicating when error
                16 occurred.  Example time stamps include the actual
                time the error occurred (in seconds since Jan. 1, 1970),
                and the total engine page count.  The device POS
                documents the meaning of the time stamp.
                Additional information:
                See ERROR1-TIME-STAMP."
::= { error16 1 }
               
               
error16-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error16 2 }
               
               
error17-time-stamp OBJECT-TYPE
    SYNTAX  INTEGER
    ACCESS  read-only
    STATUS  optional
    DESCRIPTION
                "Contains a time stamp indicating when error
                17 occurred.  Example time stamps include the actual
                time the error occurred (in seconds since Jan. 1, 1970),
                and the total engine page count.  The device POS
                documents the meaning of the time stamp.
                Additional information:
                See ERROR1-TIME-STAMP."
::= { error17 1 }
               
               
error17-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error17 2 }
               
               
error18-time-stamp OBJECT-TYPE
    SYNTAX  INTEGER
    ACCESS  read-only
    STATUS  optional
    DESCRIPTION
                "Contains a time stamp indicating when error
                18 occurred.  Example time stamps include the actual
                time the error occurred (in seconds since Jan. 1, 1970),
                and the total engine page count.  The device POS
                documents the meaning of the time stamp.
                Additional information:
                See ERROR1-TIME-STAMP."
::= { error18 1 }
               
               
error18-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error18 2 }
               
               
error19-time-stamp OBJECT-TYPE
    SYNTAX  INTEGER
    ACCESS  read-only
    STATUS  optional
    DESCRIPTION
                "Contains a time stamp indicating when error
                19 occurred.  Example time stamps include the actual
                time the error occurred (in seconds since Jan. 1, 1970),
                and the total engine page count.  The device POS
                documents the meaning of the time stamp.
                Additional information:
                See ERROR1-TIME-STAMP."
::= { error19 1 }
               
               
error19-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error19 2 }
               
               
error20-time-stamp OBJECT-TYPE
    SYNTAX  INTEGER
    ACCESS  read-only
    STATUS  optional
    DESCRIPTION
                "Contains a time stamp indicating when error
                20 occurred.  Example time stamps include the actual
                time the error occurred (in seconds since Jan. 1, 1970),
                and the total engine page count.  The device POS
                documents the meaning of the time stamp.
                Additional information:
                See ERROR1-TIME-STAMP."
::= { error20 1 }
               
               
error20-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error20 2 }
               
               
error21-time-stamp OBJECT-TYPE
    SYNTAX  INTEGER
    ACCESS  read-only
    STATUS  optional
    DESCRIPTION
                "Contains a time stamp indicating when error
                21 occurred.  Example time stamps include the actual
                time the error occurred (in seconds since Jan. 1, 1970),
                and the total engine page count.  The device POS
                documents the meaning of the time stamp.
                Additional information:
                See ERROR1-TIME-STAMP."
::= { error21 1 }
               
               
error21-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error21 2 }
               
               
error22-time-stamp OBJECT-TYPE
    SYNTAX  INTEGER
    ACCESS  read-only
    STATUS  optional
    DESCRIPTION
                "Contains a time stamp indicating when error
                22 occurred.  Example time stamps include the actual
                time the error occurred (in seconds since Jan. 1, 1970),
                and the total engine page count.  The device POS
                documents the meaning of the time stamp.
                Additional information:
                See ERROR1-TIME-STAMP."
::= { error22 1 }
               
               
error22-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error22 2 }
               
               
error23-time-stamp OBJECT-TYPE
    SYNTAX  INTEGER
    ACCESS  read-only
    STATUS  optional
    DESCRIPTION
                "Contains a time stamp indicating when error
                23 occurred.  Example time stamps include the actual
                time the error occurred (in seconds since Jan. 1, 1970),
                and the total engine page count.  The device POS
                documents the meaning of the time stamp.
                Additional information:
                See ERROR1-TIME-STAMP."
::= { error23 1 }
               
               
error23-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error23 2 }
               
               
error24-time-stamp OBJECT-TYPE
    SYNTAX  INTEGER
    ACCESS  read-only
    STATUS  optional
    DESCRIPTION
                "Contains a time stamp indicating when error
                24 occurred.  Example time stamps include the actual
                time the error occurred (in seconds since Jan. 1, 1970),
                and the total engine page count.  The device POS
                documents the meaning of the time stamp.
                Additional information:
                See ERROR1-TIME-STAMP."
::= { error24 1 }
               
               
error24-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error24 2 }
               
               
error25-time-stamp OBJECT-TYPE
    SYNTAX  INTEGER
    ACCESS  read-only
    STATUS  optional
    DESCRIPTION
                "Contains a time stamp indicating when error
                25 occurred.  Example time stamps include the actual
                time the error occurred (in seconds since Jan. 1, 1970),
                and the total engine page count.  The device POS
                documents the meaning of the time stamp.
                Additional information:
                See ERROR1-TIME-STAMP."
::= { error25 1 }
               
               
error25-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error25 2 }
               
               
error26-time-stamp OBJECT-TYPE
    SYNTAX  INTEGER
    ACCESS  read-only
    STATUS  optional
    DESCRIPTION
                "Contains a time stamp indicating when error
                26 occurred.  Example time stamps include the actual
                time the error occurred (in seconds since Jan. 1, 1970),
                and the total engine page count.  The device POS
                documents the meaning of the time stamp.
                Additional information:
                See ERROR1-TIME-STAMP."
::= { error26 1 }
               
               
error26-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error26 2 }
               
               
error27-time-stamp OBJECT-TYPE
    SYNTAX  INTEGER
    ACCESS  read-only
    STATUS  optional
    DESCRIPTION
                "Contains a time stamp indicating when error
                27 occurred.  Example time stamps include the actual
                time the error occurred (in seconds since Jan. 1, 1970),
                and the total engine page count.  The device POS
                documents the meaning of the time stamp.
                Additional information:
                See ERROR1-TIME-STAMP."
::= { error27 1 }
               
               
error27-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error27 2 }
               
               
error28-time-stamp OBJECT-TYPE
    SYNTAX  INTEGER
    ACCESS  read-only
    STATUS  optional
    DESCRIPTION
                "Contains a time stamp indicating when error
                28 occurred.  Example time stamps include the actual
                time the error occurred (in seconds since Jan. 1, 1970),
                and the total engine page count.  The device POS
                documents the meaning of the time stamp.
                Additional information:
                See ERROR1-TIME-STAMP."
::= { error28 1 }
               
               
error28-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error28 2 }
               
               
error29-time-stamp OBJECT-TYPE
    SYNTAX  INTEGER
    ACCESS  read-only
    STATUS  optional
    DESCRIPTION
                "Contains a time stamp indicating when error
                29 occurred.  Example time stamps include the actual
                time the error occurred (in seconds since Jan. 1, 1970),
                and the total engine page count.  The device POS
                documents the meaning of the time stamp.
                Additional information:
                See ERROR1-TIME-STAMP."
::= { error29 1 }
               
               
error29-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error29 2 }
               
               
error30-time-stamp OBJECT-TYPE
    SYNTAX  INTEGER
    ACCESS  read-only
    STATUS  optional
    DESCRIPTION
                "Contains a time stamp indicating when error
                30 occurred.  Example time stamps include the actual
                time the error occurred (in seconds since Jan. 1, 1970),
                and the total engine page count.  The device POS
                documents the meaning of the time stamp.
                Additional information:
                See ERROR1-TIME-STAMP."
::= { error30 1 }
               
               
error30-code OBJECT-TYPE
    SYNTAX  INTEGER
    ACCESS  read-only
    STATUS  optional
    DESCRIPTION
                "Contains a device specific error code.  Each device POS
                should list what errors are logged to the error log and
                the meaning of each supported error code value.
                Additional information:
                See ERROR1-CODE."
::= { error30 2 }
               
               
ram-disk-mode OBJECT-TYPE
    SYNTAX  INTEGER {
		   eOff(1),
		   eOn(2),
		   eAuto(3)
		   }
    ACCESS  read-write
    STATUS  optional
    DESCRIPTION
                "Returns or controls RAM disk support.  eOFF turns off
                the RAM disk functionality. eOn turns on the RAM disk
                functionality and creates a RAM disk whose size is
                controlled by the RAM-DISK-SIZE object.  eAuto turns on
                the RAM disk functionality and creates a RAM disk size
                determined by the printer based on installed options and
                other memory related settings.
                Additional information:
                Returns or controls RAM disk support.  eOFF turns off
                the RAM disk functionality. eOn turns on the RAM disk
                functionality and creates a RAM disk whose size is
                controlled by the RAM-DISK-SIZE object.  eAuto turns on
                the RAM disk functionality and creates a RAM disk size
                determined by the printer based on the amount of installed
                memory.  The automatic size will be 25 percent of all memory
                above 4MB."
::= { settings-mass-storage-bd 1 }
               
               
ram-disk-size OBJECT-TYPE
    SYNTAX  INTEGER
    ACCESS  read-write
    STATUS  optional
    DESCRIPTION
                "
                Additional information:
                Returns or controls the size of the RAM disk.  The values
                that can be set depend on the current setting of the RAM-DISK-MODE
                object, and the amount of memory available above 4MB.  Use the 
                MAXIMUM-RAM-DISK-MEMORY object to determine the amount of 
                additional memory available for the RAM disk."
::= { settings-mass-storage-bd 2 }
               
               
maximum-ram-disk-memory OBJECT-TYPE
    SYNTAX  INTEGER
    ACCESS  read-only
    STATUS  optional
    DESCRIPTION
                "This object's name is misleading.  This object does not
                return the maximum configurable RAM disk size.  Instead,
                it returns the maximum amount of memory, in bytes, that
                can used to increase the size of the RAM disk.
                Additional information:
                This object returns the maximum amount of additional 
                memory that is available for increasing the size of the RAM 
                disk."
::= { status-mass-storage-bd 1 }
               
               
io-timeout OBJECT-TYPE
    SYNTAX  INTEGER(5..300)
    ACCESS  read-write
    STATUS  optional
    DESCRIPTION
                "The amount of time, in seconds, to wait for more print
                job data to be received before an I/O timeout occurs.
                The I/O channel being timed is the I/O channel that
                received the data associated with the current print job.
                If an I/O timeout occurs, the PDL processing sub-system
                assumes all the data associated with the current print
                job has been received, and processes the end of job in
                an PDL specific manner.  The POS specifies the supported
                values.
                Additional information:
                If an I/O timeout occurs,the PDL processing
                sub-system will consider it an end of job condition only
                if there is data from another I/O subsystem waiting to be
                processed.    
                The supported values are 5 to 300 seconds. 
                Setting to a value outside the supported range returns 
                <noError> status and the
                value will be snapped to the nearest supported
                value."
::= { settings-io 1 }
               
               
io-switch OBJECT-TYPE
    SYNTAX  INTEGER {
		   eYes(1)
		   }
    ACCESS  read-only
    STATUS  optional
    DESCRIPTION
                "Indicates if the device will switch between I/O channels
                when a job boundary is encountered and print job data is
                available on another I/O channel."
::= { settings-io 2 }
               
               
io-buffering OBJECT-TYPE
    SYNTAX  INTEGER {
		   eOff(1),
		   eOn(2),
		   eAuto(3)
		   }
    ACCESS  read-write
    STATUS  optional
    DESCRIPTION
                "Returns or controls the manner in which the device
                performs I/O data buffering.  I/O data buffering allows
                additional print job data to be buffered by the I/O sub-
                system in an effort to allow the computer sending the
                data to perform other tasks and to keep the PDL
                processing sub-system busy.  eOff, I/O buffering is
                disabled.  When eOn, I/O buffering is enabled and the
                IO-BUFFER-SIZE object controls the amount of memory set
                aside for I/O buffer.  When eAuto, I/O buffering is
                enabled and the I/O buffer size is determined
                automatically by the device and the IO-BUFFER-SIZE
                object is not used.
                Additional information:
                In a PCL-only printer, all values may be set at any time.  
                
                When there is less than 4M of memory installed, setting this object to eOn
                or eAuto will cause <badValue> to be returned.  
                At exactly 4M of memory, eOn is not a valid setting.  At more than 4M
                of memory any setting is valid, subject to the conditions listed in the
                interactions below."
::= { settings-io 5 }
               
               
io-buffer-size OBJECT-TYPE
    SYNTAX  INTEGER
    ACCESS  read-write
    STATUS  optional
    DESCRIPTION
                "Returns or configures the amount of memory, in bytes,
                dedicated to I/O print job data buffering.  Attempting
                to set to an unsupported value causes the device to use
                the closest supported value.  Each device POS should
                document the list of supported values.
                Additional information:
                The minimum supported value is 10K bytes
                (10240).
                The maximum supported value is dependent on total memory installed 
                and the amount of memory currently being used by other memory 
                consumers.  Use the MAXIMUM-IO-BUFFERING-MEMORY object to determine
                this value.  
                
                The following rules determine legal values for this object:  
                1) Sizes less than 10K bytes will snap to 10K bytes.  
                2) Sizes between 10K and 100K bytes will be rounded to the nearest 10K.  
                3) Sizes between 100K bytes and the maximum value allowed will round to
                the nearest 100K bytes.  
                
                If the value had to be snapped or rounded, <noError>
                will be returned along with the actual value that was written.  
                
                Attempting to set this object when IO-BUFFERING is eOff will cause a status
                of <genErr> to be returned.  When IO-BUFFERING is 
                eOff, reading this object will return a value of zero."
::= { settings-io 6 }
               
               
maximum-io-buffering-memory OBJECT-TYPE
    SYNTAX  INTEGER
    ACCESS  read-only
    STATUS  optional
    DESCRIPTION
                "This object's name is misleading.  Returns the maximum
                amount of additional memory, in bytes, that can be
                dedicated to buffering print job data."
::= { settings-io 7 }
               
               
port1-parallel-speed OBJECT-TYPE
    SYNTAX  INTEGER {
		   eSlow(1),
		   eFast(2)
		   }
    ACCESS  read-write
    STATUS  optional
    DESCRIPTION
                "Returns or changes the maximum parallel I/O port speed,
                for port 1.  This object is only supported if this port
                is a parallel port.  An eSlow setting causes a 10 us
                busy pulse per received byte of data.  An eFast setting
                causes a 1.5 us busy pulse per received byte of data.
                In rare cases, setting this value to eFast can cause the
                parallel port to no longer transfer data reliably."
::= { port1 4 }
               
               
port1-parallel-bidirectionality OBJECT-TYPE
    SYNTAX  INTEGER {
		   eUnidirectional(1),
		   eBidirectional(2)
		   }
    ACCESS  read-write
    STATUS  optional
    DESCRIPTION
                "Returns or changes whether the parallel I/O port
                supports bidirectional communication for port 1.  This
                object is only supported if this port is a parallel
                port.
                Additional information:
                A get on this object returns the current mode 
                for the parallel port. Setting this object specifies whether or not 
                bidirectional communications will be allowed."
::= { port1 5 }
               
               
mopy-mode OBJECT-TYPE
    SYNTAX  INTEGER {
		   eOff(1),
		   eStandard(4),
		   eEnhanced(5)
		   }
    ACCESS  read-write
    STATUS  optional
    DESCRIPTION
                "Controls or reports how mopies are generated.  eOff
                turns off the mopy feature.  eStandard spools the I/O
                data and replays the I/O data multiple times to generate
                the mopies.  eEnhanced spools the rasterized page images
                and replays the rasterized data to generate the mopies.
                Typically, the rasterized data will be larger and will
                allow all but the first mopy to print at speed.  If the
                job being mopied is not extremely complex, then the
                first mopy will print at speed also."
::= { settings-spooler 1 }
               
               
default-copies OBJECT-TYPE
    SYNTAX  INTEGER(1..999)
    ACCESS  read-write
    STATUS  optional
    DESCRIPTION
                "Returns or changes default copies.  Default copies is
                the default values used by the PDL to control the number
                of copies of each page in the print job that are
                printed.  The print job can override this value.  The
                list of supported values should be documented in the
                device POS.
                Additional information:
                 The supported values are 1 through 999.   
                Setting to an unsupported value causes the printer to substitute in a snap 
                value and to return <noError> status.    
                The snaps are as follows:   
                <1 snaps to 1   
                >999 snaps to 999"
::= { settings-pdl 4 }
               
               
form-feed OBJECT-TYPE
    SYNTAX  INTEGER {
		   eInitiateAction(1)
		   }
    ACCESS  write-only
    STATUS  optional
    DESCRIPTION
                "Instructs the PDL processing sub-system to finishing
                processing the current page of the current job.  Form
                feed is also known as close page or eject page.  If the
                PDL processing sub-system is in a FORM-FEED-NEEDED
                state, this causes the device to flush or finish
                processing the current page of the current job.  If the
                device is not in the FORM-FEED-NEEDED state, an
                <genErr> will occur."
::= { settings-pdl 5 }
               
               
resource-saving OBJECT-TYPE
    SYNTAX  INTEGER {
		   eOff(1),
		   eOn(2),
		   eAuto(3)
		   }
    ACCESS  read-write
    STATUS  optional
    DESCRIPTION
                "Returns or changes PDL resource saving.  Resource saving
                stores a PDL's permanent soft resources, like fonts,
                even when another PDL is active.  Resource saving is
                also called environment saving.  When eOff, resource
                saving is disabled.  When ON, resource saving is enabled
                and memory is set aside for each PDL based on that PDL's
                resource saving memory size object, to store that PDL's
                permanent soft resources.  When eAuto, resource saving
                is enabled and memory space for each installed PDL is
                determined automatically.  The device POS should
                document what values are legal when only one PDL is
                installed.
                Additional information:
                When PCL (including PCL/XL) is the only PDL
                installed in The LJ Series 4000, eOn is not a legal value.  Attempting to set this object to 
                eOn with a PCL-only printer will result in a status of 
                <badValue> being returned.  
                
                When Postscript is installed and less than 8 Megabytes of RAM are present,
                resource saving is not available.  The only valid value for this object
                is eOff.  Attempting to set this object to eOn or eAuto will cause 
                <badValue> to be returned.  
                
                When Postscript and 8 Megabytes or more of RAM are installed, all values
                are valid, provided I/O Buffering, Mopying, or Ram Disk have not consumed
                the needed memory.  
                
                This object is only supported if Postscript is resident in the printer."
::= { settings-pdl 6 }
               
               
maximum-resource-saving-memory OBJECT-TYPE
    SYNTAX  INTEGER
    ACCESS  read-only
    STATUS  optional
    DESCRIPTION
                "This object's name is misleading.  This object returns
                the maximum amount of additional memory, in bytes, that
                can be dedcated to holding PDL permanent soft
                resources.
                Additional information:
                NOTE:  The following numbers assume that IO-BUFFERING=eOff;
                if IO-BUFFERING<>eOff, the following numbers will be reduced by the value of
                IO-BUFFER-SIZE.  
                
                Memory for resource saving is allocated in increments of 102400 bytes.
                Therefore, for each 1M (1048576 bytes) of memory added to the printer, 102400
                bytes are made available to resource saving (and I/O buffering) and 24576
                bytes are retained until an additional 102400 byte block can be made
                available. The value reported by this object is always rounded down to the
                nearest multiple of 102400.
                
                For a PCL-only printer, the value of this object is zero (all resource saving
                memory is dedicated to PCL).  
                
                If PostScript is installed without a duplex unit, the value of this object is
                as follows:  
                Zero if <7M memory is installed.  
                1048576 if 7M memory is installed and RESOURCE-SAVING=eOff.  
                1048576 if 7M memory is installed and RESOURCE-SAVING=eOn (note that this
                value will be reduced by the amount of memory allocated to
                PCL-RESOURCE-SAVING-MEMORY-SIZE and POSTSCRIPT-RESOURCE-SAVING-MEMORY-SIZE).  
                819200 if 7M memory is installed and RESOURCE-SAVING=eAuto.  
                When RESOURCE-SAVING=eAuto, 819200 bytes of each 1M over 7M memory installed
                are allocated to PCL and PostScript (409600 each) with the remaining bytes
                added to this object.  
                When RESOURCE-SAVING=eOn or eOff, all bytes over 13M memory installed are
                added to this object.  
                
                If PostScript is installed with a duplex unit, the value of this object is as
                follows:  
                Zero if <13M memory is installed.  
                1048576 if 13M memory is installed and RESOURCE-SAVING=eOff.  
                1048576 if 13M memory is installed and RESOURCE-SAVING=eOn (note that this
                value will be reduced by the amount of memory allocated to
                PCL-RESOURCE-SAVING-MEMORY-SIZE and POSTSCRIPT-RESOURCE-SAVING-MEMORY-SIZE).  
                1048576 if 13M memory is installed and RESOURCE-SAVING=eAuto.  
                When RESOURCE-SAVING=eAuto, 810200 bytes of each 1M over 13M memory installed
                are allocated to PCL and PostScript (409600 each) with the remaining bytes
                added to this object.  
                When RESOURCE-SAVING=eOn or eOff, all bytes over 13M memory installed are
                added to this object.  
                
                The above listed values returned by this object will be reduced by the amount
                of memory added to PCL-RESOURCE-SAVING-MEMORY-SIZE and
                POSTSCRIPT-RESOURCE-SAVING-MEMORY-SIZE when RESOURCE-SAVING=eOn."
::= { settings-pdl 7 }
               
               
default-vertical-black-resolution OBJECT-TYPE
    SYNTAX  INTEGER
    ACCESS  read-write
    STATUS  optional
    DESCRIPTION
                "Returns or changes the value of the default vertical
                black resolution.  The units are dots per inch.
                Additional information:
                In The LJ Series 4000 changing this OID also causes  
                DEFAULT- HORIZONTAL-BLACK RESOLUTION to change.   
                DEFAULT- HORIZONTAL-BLACK-RESOLUTION and 
                DEFAULT-VERTICAL-BLACK-RESOLUTION must always be the  
                same.  The supported values are 
                300, 600, and 1200 for the LaserJet Series 4000.     
                Setting to an unsupported value causes the printer 
                to substitute in a snap value and  
                to return <noError> status.   
                The snap values are as follow:  
                LaserJet Series 4000:  
                n < 450 snaps to 300   
                450 >= n < 900 snaps to 600  
                n >= 900 snaps to 1200   "
::= { settings-pdl 8 }
               
               
default-horizontal-black-resolution OBJECT-TYPE
    SYNTAX  INTEGER
    ACCESS  read-write
    STATUS  optional
    DESCRIPTION
                "Returns or changes the value of the default horizontal
                black resolution.  The units are dots per inch.
                Additional information:
                In The LJ Series 4000 changing this object also causes  
                DEFAULT-VERTICAL-BLACK RESOLUTION to change.   
                DEFAULT-HORIZONTAL-BLACK-RESOLUTION and 
                DEFAULT-VERTICAL-BLACK-RESOLUTION must always be the  
                same.  The supported values are 
                300, 600, and 1200 for the LaserJet Series 4000.     
                Setting to an unsupported value causes the printer 
                to substitute in a snap value and to 
                return <noError> status.   
                The snap values are as follow:   
                LaserJet Series 4000:  
                n < 450 snaps to 300   
                450 >= n < 900 snaps to 600  
                n >= 900 snaps to 1200   "
::= { settings-pdl 9 }
               
               
default-page-protect OBJECT-TYPE
    SYNTAX  INTEGER {
		   eOn(2),
		   eAuto(3)
		   }
    ACCESS  read-write
    STATUS  optional
    DESCRIPTION
                "Returns or changes the default page protection behavior.
                If eOff, the device does not reserve memory for holding
                the entire raster form of a processed page.  If eOn,
                then memory is reserved.  If eAuto, the device
                determines the amount of memory to reserve.
                Additional information:
                Setting to eOn causes MET to be more conservative, but
                it will not allocate memory to hold an entire
                rasterized page."
::= { settings-pdl 10 }
               
               
default-lines-per-page OBJECT-TYPE
    SYNTAX  INTEGER
    ACCESS  read-write
    STATUS  optional
    DESCRIPTION
                "Returns or changes the default number of lines per page.
                The POS indicates the supported values.  An unsupported
                value causes the printer to use the closest supported
                value, causing the printer to return the
                <noError>.
                Additional information:
                The supported values are 5 to 128. 
                Setting to an unsupported value causes the  
                the printer to substitute in a snap value and to return 
                <noError> 
                status.   
                The snap values are as follow:   
                <5 snaps to 5   
                >128 snaps to 128"
::= { settings-pdl 11 }
               
               
default-vmi OBJECT-TYPE
    SYNTAX  INTEGER
    ACCESS  read-write
    STATUS  optional
    DESCRIPTION
                "Returns or changes the default vertical motion index.
                The unit of measure for VMI is centipoints per line.
                The POS indicates the supported values.  An unsupported
                value causes the printer to use the closest supported
                value, causing the printer to return
                <noError>."
::= { settings-pdl 12 }
               
               
cold-reset-media-size OBJECT-TYPE
    SYNTAX  INTEGER {
		   eUSLetter(2),
		   eISOandJISA4(26)
		   }
    ACCESS  read-write
    STATUS  optional
    DESCRIPTION
                "Returns or sets the media size that is used as the
                DEFAULT-MEDIA-SIZE when a cold reset occurs."
::= { settings-pdl 19 }
               
               
default-bits-per-pixel OBJECT-TYPE
    SYNTAX  INTEGER
    ACCESS  read-write
    STATUS  optional
    DESCRIPTION
                "Controls the number of levels used (per pixel) when
                printing grayscale or color images."
::= { settings-pdl 39 }
               
               
pcl-resource-saving-memory-size OBJECT-TYPE
    SYNTAX  INTEGER
    ACCESS  read-write
    STATUS  optional
    DESCRIPTION
                "Returns or changes the amount of resource saving memory
                set aside to hold permanent soft PCL resources.
                Additional information:
                The value returned by this object is the amount of
                Resource Saving memory currently dedicated to PCL.  
                
                For a PCL-only printer, the value of this object is zero. All memory is
                dedicated to PCL, but it is not shown as such.  
                
                If Postscript is installed, the default value of this object is as follows:  
                0 if RESOURCE-SAVING = eOff.  
                0 if less than 8 Megabytes of RAM is in the printer.  
                400K bytes if RAM >= 8 Megabytes and RESOURCE-SAVING = eOn.  
                400K bytes if RAM = 8 Megabytes and RESOURCE-SAVING = eAuto, plus 100K bytes
                for each Megabyte of RAM over 8 Megabytes.  
                
                If RESOURCE-SAVING=eOn, this object can be used to set the amount of Resource
                Saving memory currently dedicated to PCL. The range of values supported by
                this object are:  
                0 bytes (which disables resource saving for PCL)  
                400K bytes through (400K bytes + MAXIMUM-RESOURCE-SAVING-MEMORY) in
                increments of 100K bytes.  
                If a value is received that is greater than 0 and less than 400K bytes,
                it will be snapped to 400K bytes and a status of
                <noError> returned.  
                If an unsupported value greater than 400K bytes is received,
                it will be snapped down to the nearest 100K value
                and a status of <noError> returned.  
                
                Attempting to set this object when RESOURCE-SAVING is eAuto or eOff will
                cause a status of <genErr> to be returned."
::= { pdl-pcl 2 }
               
               
pcl-total-page-count OBJECT-TYPE
    SYNTAX  INTEGER
    ACCESS  read-only
    STATUS  optional
    DESCRIPTION
                "Total number of PCL pages printed by the device.
                Additional information:
                The PCL page count is kept in
                NVRAM, and the NVRAM value is updated at least every
                10 pages.  NOTE: The value returned by this object will
                be incremented every page but if power is lost between
                NVRAM updates, up to 9 pages of the page count may be
                lost.  The page count counter will be reset to zero
                after 16,777,215 (2^24-1) pages.  
                The page count is incremented when a sheet of media is pulled from an input
                tray. A duplex printed sheet will cause this counter to be incremented by
                two."
::= { pdl-pcl 5 }
               
               
pcl-default-font-height OBJECT-TYPE
    SYNTAX  INTEGER
    ACCESS  read-write
    STATUS  optional
    DESCRIPTION
                "Returns or changes the default PCL height.  Height is an
                approximate measure of the body of the type in
                centipoints.  A centipoint is 1/7200 inch.  Height
                applies only to proportional fonts.  Point size, in
                points, can be converted to font height, in centipoints,
                by multiplying the point size by 100.  The POS indicates
                the supported values.  An unsupported value causes the
                printer to use the closest supported value, causing the
                printer to return <noError>.''Closest'' means the smallest absolute difference.
                Additional information:
                Supported values range from 400 to 99975, in
                increments of 25 units.
                Setting to an unsupported value causes the 
                printer to substitute in a snap value and to 
                return <noError> status.   
                The snap values are as follow:   
                <=400 snaps to 400   
                >=99975 snaps to 99975   
                Unsupported values in the range 400 to 99975 snap
                DOWN to the previous supported value 
                (i.e 25293 snaps to 25275 or 75038 snaps to 75025)."
::= { pdl-pcl 13 }
               
               
pcl-default-font-source OBJECT-TYPE
    SYNTAX  INTEGER {
		   eInternal(1),
		   ePermanentSoft(2),
		   eRomSimm1(10),
		   eRomSimm2(11),
		   eRomSimm3(12),
		   eRomSimm4(13)
		   }
    ACCESS  read-write
    STATUS  optional
    DESCRIPTION
                "Returns or changes the value of the default font source
                variable in NVRAM."
::= { pdl-pcl 14 }
               
               
pcl-default-font-number OBJECT-TYPE
    SYNTAX  INTEGER(0..255)
    ACCESS  read-write
    STATUS  optional
    DESCRIPTION
                "Returns or changes the value of the default font number
                variable in NVRAM.  Writing an unsupported value causes
                the printer to generate an
                <badValue>.
                Additional information:
                Valid numbers or 0 - 255, but only font numbers that are 
                included in the PCL FONT LIST are selectable."
::= { pdl-pcl 15 }
               
               
pcl-default-font-width OBJECT-TYPE
    SYNTAX  INTEGER
    ACCESS  read-write
    STATUS  optional
    DESCRIPTION
                "Returns or changes the default PCL font width.  Width is
                expressed as the width of a character in centipoints.  A
                centipoint is 1/7200 inch.  Width applies only to fixed
                space fonts.  Pitch, in character per inch, can be
                converted to font width, in centipoints, by dividing
                7200 by the pitch.  The POS indicates the supported
                values.  An unsupported value causes the printer to use
                the closest supported value, causing the printer to
                return <noError>.  ''Closest''
                means the smallest absolute difference.
                Additional information:
                Setting to an unsupported value causes the 
                printer to substitue in a snap value (listed below)
                and return <noError> status.   
                The snap values for pitch are as follow:   
                <=44 snaps to 44   
                >=9999 snaps to 9999"
::= { pdl-pcl 16 }
               
               
postscript-resource-saving-memory-size OBJECT-TYPE
    SYNTAX  INTEGER
    ACCESS  read-write
    STATUS  optional
    DESCRIPTION
                "Returns or changes the amount of resource saving memory
                set aside to hold permanent soft PostScript resources.
                Additional information:
                The value returned by this object is the amount of
                Resource Saving memory currently dedicated to Postscript.  
                
                If Postscript is installed, the default value of this object is as follows:  
                0 if RESOURCE-SAVING = eOff.  
                0 if less than 8 Megabytes of RAM is in the printer.  
                400K bytes if RAM >= 8 Megabytes and RESOURCE-SAVING = eOn.  
                400K bytes if RAM = 8 Megabytes and RESOURCE-SAVING = eAuto, plus 100K bytes
                for each Megabyte of RAM over 8 Megabytes.  
                
                If RESOURCE-SAVING=eOn, this object can be used to set the amount of Resource
                Saving memory currently dedicated to PCL. The range of values supported by
                this object are:  
                0 bytes (which disables resource saving for Postscript)  
                400K bytes through (400K bytes + MAXIMUM-RESOURCE-SAVING-MEMORY) in
                increments of 100K bytes.  
                If a value is received that is greater than 0 and less than 400K bytes,
                it will be snapped to 400K bytes and a status of
                <noError> returned.  
                If an unsupported value greater than 400K bytes is received,
                it will be snapped down to the nearest 100K value
                and a status of <noError> returned.  
                
                Attempting to set this object when RESOURCE-SAVING is eAuto or eOff will
                cause a status of <genErr> to be returned."
::= { pdl-postscript 2 }
               
               
postscript-total-page-count OBJECT-TYPE
    SYNTAX  INTEGER
    ACCESS  read-only
    STATUS  optional
    DESCRIPTION
                "Total number of PostScript pages printed by the device.
                Additional information:
                This object is only supported if the PostScript 
                option is installed.  
                In The LJ Series 4000 the count is kept in NVRAM, and the 
                NVRAM value is updated at least every 10 
                sheets.  NOTE: The value returned by this object will 
                be incremented every sheet but if power is lost between 
                NVRAM updates up to 9 sheets of the count may be 
                lost.  The counter will be reset to zero 
                after 16,777,215 (2^24-1) pages. "
::= { pdl-postscript 5 }
               
               
postscript-print-errors OBJECT-TYPE
    SYNTAX  INTEGER {
		   eOff(1),
		   eOn(2)
		   }
    ACCESS  read-write
    STATUS  optional
    DESCRIPTION
                "Returns or changes the value of the print PostScript
                errors setting.  If eOn, PostScript prints an error page
                showing the error encountered and the stack at the time
                of the error.
                Additional information:
                This object is only supported if the PostScript
                option is installed."
::= { pdl-postscript 11 }
               
               
pjl-password OBJECT-TYPE
    SYNTAX  INTEGER
    ACCESS  read-only
    STATUS  optional
    DESCRIPTION
                "Returns PJL password, if the password is not set (zero).
                If the password is set, then attempting to retrieve the
                password causes an <genErr> to occur
                and will return the <NullValue>."
::= { pjl 1 }
               
               
print-density OBJECT-TYPE
    SYNTAX  INTEGER(1..5)
    ACCESS  read-write
    STATUS  optional
    DESCRIPTION
                "Returns or sets the print density setting.  Print
                density is the instantaneous amount of marking agent
                applied to the paper while printing.  A value of zero
                has the lowest print density, yielding a lighter page.
                A value of 10 has the highest print density, yielding a
                darker page.  Each POS should document what values in
                the 0 to 10 range are supported.
                Additional information:
                When this value is written, the page pipeline
                will be flushed (all pages being printed are completed, no
                new ones are started), the new density setting is set and
                printing resumes.  The acutal change in print density may be
                gradual over several pages.  
                The supported values are 1 through 5.  Setting to an 
                unsupported value causes the printer to substitue in a
                a snap value and to return <noError>
                status.  The snap values are as follows:  
                <1 snaps to 1  
                >5 snaps to 5."
::= { settings-prt-eng 5 }
               
               
duplex-page-count OBJECT-TYPE
    SYNTAX  INTEGER
    ACCESS  read-only
    STATUS  optional
    DESCRIPTION
                "Total number of sheets of media that have been duplex
                printed.  A sheet is counted if it travels through the
                duplex page path, regardless of whether or not marks are
                made on the page.  The POS will indicate if the value is
                kept in NVRAM.
                Additional information:
                In The LJ Series 4000 the count is kept in
                NVRAM however the NVRAM value is only updated every 10
                sheets.  NOTE: The value returned by this object will be
                incremented every sheet but if power is lost between
                NVRAM updates up to 9 sheets of the count may be
                lost.  The counter will be reset to zero
                after 16,777,215 (2^24-1) pages. "
::= { status-prt-eng 22 }
               
               
mp-tray OBJECT-TYPE
    SYNTAX  INTEGER {
		   eCassette(2),
		   eFirst(3)
		   }
    ACCESS  read-write
    STATUS  optional
    DESCRIPTION
                "Returns or changes the value of the multi-purpose (MP)
                tray configuration variable.  The MP tray can be
                configured to operate as an additional input tray
                (eCassette), a manual feed slot (eManual), or in a
                manner compatible with the LaserJet III manual feed slot
                (eFirst).  If configured for eFirst, if media is present
                in the MP tray, that media is used (assuming the size
                matches and the print job didn't specify another tray)
                until the MP tray is empty.
                Additional information:
                The MP tray can be configured for use either as a paper
                cassette or as a priority manual feed tray.  
		When the tray is configured as a manual feed tray, 
		unsolicited status messages are not generated when there is no 
                paper in the tray.  The LJ Series 4000 will pull media from TRAY 1 only if there is
                a sheet present and it matches the needed size and type."
::= { settings-intray 5 }
               
               
low-marking-agent-processing OBJECT-TYPE
    SYNTAX  INTEGER {
		   eStop(1),
		   eCont(2)
		   }
    ACCESS  read-write
    STATUS  optional
    DESCRIPTION
                "Returns or changes how the device processes a low
                marking agent event.  If eCont, then the device
                continues to print.  If eStop, then the device stops
                until a continue event occurs."
::= { settings-marking-agent 3 }
               
               
default-ret OBJECT-TYPE
    SYNTAX  INTEGER {
		   eOff(1),
		   eLight(2),
		   eMedium(3),
		   eDark(4)
		   }
    ACCESS  read-write
    STATUS  optional
    DESCRIPTION
                "Returns or changes the Resolution Enhancement Technology
                setting.  Devices that only support eOff and on should
                map all other values to on and always return the same
                non-eOff value to indicate on.  The list of supported
                values should be documented in the device POS.
                Additional information:
                Setting this object may cause a status of <noError> to be 
                returned, but the new value will not take effect until a job 
                boundary is reached. If a get is done on object before the job 
                boundary is reached, the value last set will be returned.  
                The value of this object is saved over a powercycle."
::= { imaging 5 }
               
               
default-print-quality OBJECT-TYPE
    SYNTAX  INTEGER(0..100)
    ACCESS  read-write
    STATUS  optional
    DESCRIPTION
                "Returns or sets the default print quality.  A value of
                zero has the lowest print quality.  A value of 100 has
                the highest print quality.  Each POS should document
                what values in the 0 to 100 range are supported.
                Additional information:
                The supported values are 0 and
                100.  A value of zero has the lowest print  
                quality (ECONOMODE=ON), thus minimizes the amount of 
                toner used to print a page.  A value of 100 has the 
                highest print quality (ECONOMODE=OFF), thus uses more 
                toner to print a page.  Setting to an unsupported value 
                outside of the 0 to 100 range causes the printer to 
                return <badValue> status.  
                Setting to an unsupported value inside of the 0 to
                100 range causes the printer to substitute in a snap 
                value (listed below) and to return  
                <noError> status.   
                The snap values are as follow:   
                0 to 50 snap to 0   
                51 to 100 snap to 100"
::= { imaging 7 }
               
               
hrmemorysize OBJECT-TYPE
    SYNTAX  INTEGER
    ACCESS  read-only
    STATUS  mandatory
    DESCRIPTION
                "The amount of physical main memory contained by
              the host.
              Refer to RFC 1514, Host Resources MIB, for more details.
                Additional information:
                The unit of measure for this object is 1024 bytes.  
                The default value assumes the base printer with no 
                additional memory."
::= { hrStorage 2 }
               
               
hrstorageused OBJECT-TYPE
    SYNTAX  INTEGER(0..2147483647)
    ACCESS  read-only
    STATUS  mandatory
    DESCRIPTION
                "The amount of the storage represented by this
              entry that is allocated, in units of
              hrStorageAllocationUnits.
              Refer to RFC 1514, Host Resources MIB, for more details.
                Additional information (printer):
                This object returns the amount of memory in use
                by the printer at the current time.  This object should not be 
                used when creating a print
                job for the device because the amount of memory in use will
                likely be different when the printer processes the print job.
                Additional information (mass storage):
                Applications can determine the amount of used
                space on the installed mass storage device by getting the 
                hrStorageAllocationUnits object and this object.  The amount
                of used space is these two returned values multiplied
                together.  Returns the value 0 if the file system
                is not initialized.  Returns <noSuchName>
                status if attempting to perform a Get on this OID
                with no mass storage device installed."
::= { hrStorageEntry 6 }
               
               
hrstorageallocationfailures OBJECT-TYPE
    SYNTAX  INTEGER
    ACCESS  read-only
    STATUS  mandatory
    DESCRIPTION
                "The number of requests for storage represented by
              this entry that could not be honored due to not
              enough storage.  It should be noted that as this
              object has a SYNTAX of Counter, that it does not
              have a defined initial value.  However, it is
              recommended that this object be initialized to
              zero.
              Refer to RFC 1514, Host Resources MIB, for more details.
                Additional information (printer):
                This object is set to zero at power on and when any 
                reset is done via prtGeneralReset.  
                This object is incremented whenever the printer is 
                short on memory.  
                Additional information (mass storage):
                Total number of writes that failed
                (since power on) due to the mass storage device
                being full.  Returns the value 0 when the file
                system has not been initialized.  Returns
                <noSuchName> status if attempting
                to perform a Get on this OID with no mass storage device
                installed."
::= { hrStorageEntry 7 }
               
               
hrdeviceindex OBJECT-TYPE
    SYNTAX  INTEGER(1..2147483647)
    ACCESS  read-only
    STATUS  mandatory
    DESCRIPTION
                "A unique value for each device contained by the
              host.  The value for each device must remain
              constant at least from one re-initialization of the
              agent to the next re-initialization.
              Refer to RFC 1514, Host Resources MIB, for more details.
                Additional information (printer):
                The entry in the Device Table which
                describes the printer.
                Additional information (mass storage):
                Constant.  The index is assigned by the
                person controlling the printer object definition.
                All device/mass storage/file system/partition
                tables in Host Resources MIB and the Printer MIB that
                relate to the mass storage device use the same index value.
                The value of the index of the following objects is
                this object's value:  
                prtDeviceRefIndex  
                hrDiskStorageIndex  
                hrPartitionIndex  
                hrFSIndex  
                The value of the object matches the value of the 
                object's index. Returns
                <noSuchName> status if attempting
                to perform a Get on this OID with no mass storage device
                installed."
::= { hrDeviceEntry 1 }
               
               
hrdevicestatus OBJECT-TYPE
    SYNTAX  INTEGER {
		   eHrunning(2),
		   eHwarning(3),
		   eHtesting(4),
		   eHdown(5)
		   }
    ACCESS  read-only
    STATUS  mandatory
    DESCRIPTION
                "The current operational state of the device
              described by this row of the table.  A value
              unknown(1) indicates that the current state of the
              device is unknown.  running(2) indicates that the
              device is up and running and that no unusual error
              conditions are known.  The warning(3) state
              indicates that agent has been informed of an
              unusual error condition by the operational software
              (e.g., a disk device driver) but that the device is
              still 'operational'.  An example would be high
              number of soft errors on a disk.  A value of
              testing(4), indicates that the device is not
              available for use because it is in the testing
              state.  The state of down(5) is used only when the
              agent has been informed that the device is not
              available for any use.
              Refer to RFC 1514, Host Resources MIB, for more details.
                Additional information (printer):
                The printer's condition is mapped as follows:  
                
                eHrunning -- Printer ready to print or is printing.  May be in power save
                mode.  
                
                eHwarning -- A condition exists that needs attention but it is
                not currently preventing printing. A non-critical alert is active.  
                
                eHdown -- Printer is not printing because it is offline or a critical
                alert is active.  Human interaction is needed to bring the printer to
                a ready state. 
                Additional information (mass storage):
                Returns mass storage device status information.  
                running -- mass storage device functional.  May be in power save
                mode.  
                warning -- The mass storage device failed a self-test but completed
                the power-on initialization sequence.  The mass storage device
                is readable even when the mass storage device fails the power-up 
                self-test in order to give the customer a chance to 
                retrieve any data that can be made available.  
                testing -- Mass storage device is executing a test.  
                down -- Mass storage device is non-functional. Returns
                <noSuchName> status if attempting
                to perform a Get on this OID with no mass storage device
                installed."
::= { hrDeviceEntry 5 }
               
               
hrdeviceerrors OBJECT-TYPE
    SYNTAX  INTEGER
    ACCESS  read-only
    STATUS  mandatory
    DESCRIPTION
                "The number of errors detected on this device.  It
               should be noted that as this object has a SYNTAX
               of Counter, that it does not have a defined
               initial value.  However, it is recommended that
               this object be initialized to zero.
               Refer to RFC 1514, Host Resources MIB, for more details.
                Additional information (printer):
                This is the number of critical alerts that have been 
                entered into the alert table since the device was powered on.
                The maximum value for this object is 2^32-1.  At power-on, this object will
                be set to zero. 
                Additional information (mass storage):
                Total number of read and write errors
                that have occurred since the printer was turned on.
                Returns <noSuchName> status if
                attempting to perform a Get on this OID with no mass storage device
                installed.  Returns 0 if the mass storage device is
                	   uninitialized."
::= { hrDeviceEntry 6 }
               
               
hrprinterstatus OBJECT-TYPE
    SYNTAX  INTEGER {
		   eHother(1),
		   eHidle(3),
		   eHprinting(4),
		   eHwarmup(5)
		   }
    ACCESS  read-only
    STATUS  mandatory
    DESCRIPTION
                "The current status of this printer device.  When
               in the idle(1), printing(2), or warmup(3) state,
               the corresponding hrDeviceStatus should be
               running(2) or warning(3).  When in the unknown
               state, the corresponding hrDeviceStatus should be
               unknown(1).
               Refer to RFC 1514, Host Resources MIB, for more details.
                Additional information: (printer)
                The printer's condition is mapped as follows:  
                
                eHother -- The printer is offline or a critical alert is active. 
                
                eHidle -- The printer is not doing any of the items listed below
                for eHprinting status.  
                
                eHprinting -- A job is currently being processed or printed or a PJL job
                is being processed.
                
                eHwarmup -- If hrDeviceStatus is eHdown, then the printer is currently
                offline but is resolving the condition that caused it be offline.
                If hrDeviceStatus is eHrunning, then the printer was in power save mode
                and is now ready ready to print."
::= { hrPrinterEntry 1 }
               
               
hrprinterdetectederrorstate OBJECT-TYPE
    SYNTAX  OCTET STRING
    ACCESS  read-only
    STATUS  mandatory
    DESCRIPTION
                "This object represents any error conditions
               detected by the printer.  The error conditions are
               encoded as bits in an octet string, with the
               following definitions:
                    Condition         Bit #    hrDeviceStatus
                    lowPaper          0        warning(3)
                    noPaper           1        down(5)
                    lowToner          2        warning(3)
                    noToner           3        down(5)
                    doorOpen          4        down(5)
                    jammed            5        down(5)
                    offline           6        down(5)
                    serviceRequested  7        warning(3)
               If multiple conditions are currently detected and
               the hrDeviceStatus would not otherwise be
               unknown(1) or testing(4), the hrDeviceStatus shall
               correspond to the worst state of those indicated,
               where down(5) is worse than warning(3) which is
               worse than running(2).
               Bits are numbered starting with the most
               significant bit of the first byte being bit 0, the
               least significant bit of the first byte being bit
               7, the most significant bit of the second byte
               being bit 8, and so on.  A one bit encodes that
               the condition was detected, while a zero bit
               encodes that the condition was not detected.
               This object is useful for alerting an operator to
               specific warning or error conditions that may
               occur, especially those requiring human
               intervention.
               Refer to RFC 1514, Host Resources MIB, for more details.
                Additional information:
                The LJ Series 4000 reports error conditions as follows:  
                
                lowPaper -- A tray is empty, but the media to be loaded is not
                currently needed.  
                hrDeviceStatus = eHwarning;  
                hrPrinterStatus = eHidle or eHprinting;  
                A non-critical alert is active.  
                
                noPaper -- A tray is empty and must be filled for printing to continue.  
                hrDeviceStatus = eHdown;  
                hrPrinterStatus = eHother;  
                A critical alert is active.  
                
                lowToner -- Toner is almost gone.  The quality of printed pages will begin
                to deteriorate until the toner is completely gone.  
                hrDeviceStatus = eHwarning;  
                hrPrinterStatus = eHidle or eHprinting;  
                A non-critical alert is active.  
                
                noToner -- The LJ Series 4000 does not report this condition.  
                
                coverOpen -- A printer cover or door is open.  
                hrDeviceStatus = eHdown;  
                hrPrinterStatus = eHother;  
                A critical alert is active.  
                
                jammed -- Paper is jammed and the printer will be unable to continue
                printing until the jam is cleared.  
                hrDeviceStatus = eHdown;  
                hrPrinterStatus = eHother;  
                A critical alert is active.  
                
                offline -- Printer is offline and will not accept new print jobs until
                it is online again.  
                hrDeviceStatus = eHdown;  
                hrPrinterStatus = eHother;  
                A critical alert is active.  
                
                serviceRequested -- Any status or error condition not listed
                above. If the condition prevents printing, the 'offline'
                bit is also set and the hrDeviceStatus and hrPrinterStatus listed for
                offline above are returned.  
                hrDeviceStatus = eHwarning;  
                hrPrinterStatus = eHidle or eHprinting;  
                A non-critical alert is active."
::= { hrPrinterEntry 2 }
               
               
prtgeneralconfigchanges OBJECT-TYPE
    SYNTAX  INTEGER(0..2147483648)
    ACCESS  read-only
    STATUS  optional
    DESCRIPTION
                "Counts configuration changes that change the capabilities of
        a printer, such as the addition/deletion of input/output bins,
        the addition/deletion of interpreters, or changes in media
        size.  Such changes will often affect the capability of the
        printer to service certain types of print jobs.
        Management applications may cache infrequently changed
        configuration  information about sub-units on the printer.
        This object should be incremented whenever the agent wishes
        such applications to invalidate that cache and re-download
        all of this configuration information, thereby signaling a
        change in the printer's configuration.
	
        For example, if an input tray that contained paper of
        different dimensions was added, this counter would be
        incremented.
        As an additional example, this counter would not be
        incremented when an input tray is removed or the level of an
		input device changes.
	Refer to Internet Draft Printer MIB, expiring Sept. 1997 for more details.
                Additional information:
                This is a 32 bit counter (unsigned). When it reaches
                its maximum value, it will roll to zero."
::= { prtGeneralEntry 1 }
               
               
prtgeneralcurrentlocalization OBJECT-TYPE
    SYNTAX  INTEGER(1..17)
    ACCESS  read-write
    STATUS  optional
    DESCRIPTION
                "The value of the prtLocalizationIndex corresponding to the
        current language, country, and character set to be used for
        localized string values that are identified as being dependent
        on the value of this object.  Note that this object does not
        apply to localized strings in the prtConsole group or to any
        object that is not explicitly identified as being localized
        according to prtGeneralCurrentLocalization.
	Refer to Internet Draft Printer MIB, expiring Sept. 1997 for more details.
                Additional information:
                The value of this object is saved in NVRAM."
::= { prtGeneralEntry 2 }
               
               
prtgeneralreset OBJECT-TYPE
    SYNTAX  INTEGER {
		   ePnotResetting(3),
		   ePpowerCycleReset(4),
		   ePresetToNVRAM(5),
		   ePresetToFactoryDefaults(6)
		   }
    ACCESS  read-write
    STATUS  optional
    DESCRIPTION
                "Setting this value to `powerCycleReset', `resetToNVRAM', or
        `resetToFactoryDefaults' will result in the resetting of the
        printer.  When read, this object will always have the value
        `notResetting(3)', and a SET of the value `notResetting' shall
        have no effect on the printer.  Some of the defined values are
        optional.  However, every implementation must support at least
        the values `notResetting' and 'resetToNVRAM'.
	Refer to Internet Draft Printer MIB, expiring Sept. 1997 for more details.
                Additional information:
                The, the following sequence of events occur when this object is set to
                ePpowerCycleReset, ePresetToNVRAM, or ePresetToFactoryDefaults:  
                1. Wait until a job boundary.   
                2. The paper path is flushed.  
                3. The printer is reset per the request. The printer will respond to PML
                requests up to this point in time.  
                
                All settings will make the printer go thru its power-on initialization
                routines and I/O cards are reset.
                
                When this object is set to ePpowerCycleReset or ePresetToNVRAM, the printer
                performs its power on initialization routines.  I/O cards are reset, although
                NVRAM on the cards is not changed, and all I/O buffers are flushed.  This is
                equivalent to turning the printer off and then on again.  
                
                Setting this object to ePresetToFactoryDefaults causes the same action as
                ePpowerCycleReset exept that it also changes all configurable settings back
                to their factory defaults.  It is equivalent to doing a Cold Reset from the
                control panel while turning on the printer."
::= { prtGeneralEntry 3 }
               
               
prtgeneralcurrentoperator OBJECT-TYPE
    SYNTAX  OCTET STRING (SIZE(0..32))
    ACCESS  read-write
    STATUS  optional
    DESCRIPTION
                "The name of the person who is responsible for operating
          this printer. It is suggested that this string include
          information that would enable other humans to reach the operator,
          such as a phone number. As a convention to facilitate automatic
          notification of the operator by the agent or the network
          management station, the phone number, fax number or email address
          should be placed on a separate line starting with ASCII LF (hex
          0x0A) and the ASCII text string (without the quotes): 'phone: ',
          'fax: ', and 'email: ', respectively. Phone numbers may contain
          digits, whitespace and parentheses, which shall be ignored. Phone
          numbers may also include ASCII comma characters(hex 2C) that are
          used to indicate a two-second pause during the dialing sequence.
          If either the phone, fax, or email information is not available,
          then a line should not be included for this information.
          NOTE: For interoperability purposes, it is advisable to use email
          addresses formatted according to RFC 822 requirements.
	 Refer to Internet Draft Printer MIB, expiring Sept. 1997 for more details.
                Additional information:
                The maximum supported string length is 32 characters.  
                Length of 32 was chosen so a phone number could be
                included with the name.  
                If the user entered string is too long, the device 
                will store as much as possible and will return the
                <noError> status."
::= { prtGeneralEntry 4 }
               
               
prtgeneralserviceperson OBJECT-TYPE
    SYNTAX  OCTET STRING (SIZE(0..32))
    ACCESS  read-write
    STATUS  optional
    DESCRIPTION
                "The name of the person responsible for servicing this
          printer. It is suggested that this string include information
          that would enable other humans to reach the service person, such
          as a phone number. As a convention to facilitate automatic
          notification of the service person by the agent or a network
          management station, the phone number, fax number or email address
          should be placed on a separate line starting with ASCII LF (hex
          0x0A) and the ASCII text string (without the quotes): 'phone: ',
          'fax: ', and 'email: ', respectively. Phone numbers may contain
          digits, whitespace and parentheses, which shall be ignored. Phone
          numbers can also include one or more ASCII comma characters(hex
          2C) to indicate a two-second pause during the dialing sequence.
          If either the phone,fax, or email information is not available,
          then a line should not included for this information.
          NOTE: For interoperability purposes, it is advisable to use email
          addresses formatted according to RFC 822 requirements.
		
	 Refer to Internet Draft Printer MIB, expiring Sept. 1997 for more details.
                Additional information:
                The maximum supported string length is 32 characters.  
                Length of 32 was chosen so a phone number could be 
                included with the name.  
                If the user entered string is too long, the device 
                will store as much as possible and will return the
                <noError> status."
::= { prtGeneralEntry 5 }
               
               
prtconsolelocalization OBJECT-TYPE
    SYNTAX  INTEGER(1..17)
    ACCESS  read-write
    STATUS  optional
    DESCRIPTION
                "The value of the prtLocalizationIndex corresponding to
        the language, country, and character set to be used for the
        console.  This localization applies both to the actual display
        on the console as well as the encoding of these console
        objects in management operations.
	Refer to Internet Draft Printer MIB, expiring Sept. 1997 for more details.
                Additional information:
                The value of this object is saved in NVRAM.  
                If a localized string is currently being displayed on the control panel by the
                device, changing this object will cause the displayed string to be changed
                to its new value.  If this object is changed while the printer is processing
                a page that contains localized strings, the results are undefined."
::= { prtGeneralEntry 10 }
               
               
prtconsolenumberofdisplaylines OBJECT-TYPE
    SYNTAX  INTEGER(0..65535)
    ACCESS  read-only
    STATUS  optional
    DESCRIPTION
                "The number of lines on the printer's physical
        display.  This value is 0 if there are no lines on the
        physical display or if there is no physical display
	Refer to Internet Draft Printer MIB, expiring Sept. 1997 for more details.
                Additional information:
                The printer has two physical lines on the display,
                however, in many cases up to four seperate lines
                of text may be displayed by alternating pairs of
                lines every three seconds.  Thus the display really
                has four logical lines for displaying messages.
                This object will return the number of logical
                display lines supported by the printer."
::= { prtGeneralEntry 11 }
               
               
prtconsolenumberofdisplaychars OBJECT-TYPE
    SYNTAX  INTEGER(0..65535)
    ACCESS  read-only
    STATUS  optional
    DESCRIPTION
                "The number of characters per line displayed on the physical
        display.  This value is 0 if there are no lines on the
        physical display or if there is no physical display
	Refer to Internet Draft Printer MIB, expiring Sept. 1997 for more details."
::= { prtGeneralEntry 12 }
               
               
prtconsoledisable OBJECT-TYPE
    SYNTAX  INTEGER {
		   ePoperatorConsoleEnabled(3),
		   ePoperatorConsoleDisabled(4),
		   ePoperatorConsoleEnabledLevel1(5),
		   ePoperatorConsoleEnabledLevel2(6)
		   }
    ACCESS  read-write
    STATUS  optional
    DESCRIPTION
                "If the object prtConsoleDisable has value
          'operatorConsoleDisabled' then input is not accepted from the
          operator console. If the object prtConsoleDisable has the value
          'operatorConsoleEnabled' then input is accepted from the
          operator console. If the object prtConsoleDisable has the value
          'operatorConsoleEnabledLevel1','operatorConsoleEnabledLevel2' or
          'operatorConsoleEnabledLevel3' then limited input is accepted
          from the operator console; the limitations are product specific,
          however, the limitations are generally less restrictive for
          operatorConsoleEnabledLevel1 than for
          operatorConsoleEnabledLeve2, which is less restrictive than
          operatorConsoleEnabledLevel3.
          The value of the prtConsoleDisable object is a type-2
          enumeration.
        Refer to Internet Draft Printer MIB, expiring Sept. 1997 for more details.
                Additional information:
                If the object prtConsoleDisable has value 
                'ePoperatorConsoleDisabled' then manual input is not
                accepted from the operator console.  If the object prtConsoleDisable has the
                value 'ePoperatorConsoleEnabled' then manual input is accepted from the 
                operator console.  
                The following menus are locked with these corresponding
                values:   
                ePoperatorConsoleEnabled (no locking)    
                ePoperatorConsoleEnabledLevel1 (minimal locking)    
                RESETS MENU    
                CONFIGURATION MENU    
                I/O MENU    
                ePoperatorConsoleEnabledLevel2 (moderate locking)    
                PRINT QUALITY MENU    
                PAPER HANDLING MENU    
                menus in level 1   
                ePoperatorConsoleDisabled (maximum locking)    
                PRINTING MENU    
                INFORMATION MENU    
                Job Cancel
                menus in levels 1 and 2"
::= { prtGeneralEntry 13 }
               
               
prtgeneralstartuppage OBJECT-TYPE
    SYNTAX  INTEGER {
		   ePnotPresent(5)
		   }
    ACCESS  read-only
    STATUS  optional
    DESCRIPTION
                "Used to enable or disable printing a startup page. If
		 enabled, a startup page will be printed shortly after
		 power-up, when the device is ready. Typical startup
		 pages include test patterns and/or printer configuration
		 information.
		 Refer to Internet Draft Printer MIB, expiring Sept. 1997 for more details."
::= { prtGeneralEntry 14 }
               
               
prtgeneralbannerpage OBJECT-TYPE
    SYNTAX  INTEGER {
		   ePnotPresent(5)
		   }
    ACCESS  read-only
    STATUS  optional
    DESCRIPTION
                "Used to enable or disable printing banner pages at the
		 beginning of jobs. This is a master switch which applies
		 to all jobs, regardless of interpreter.
		 Refer to Internet Draft Printer MIB, expiring Sept. 1997 for more details."
::= { prtGeneralEntry 15 }
               
               
prtgeneralprintername OBJECT-TYPE
    SYNTAX  OCTET STRING (SIZE(0..32))
    ACCESS  read-write
    STATUS  optional
    DESCRIPTION
                "An administrator-specified name for this printer.
          Depending upon implementation of this printer, the value of this
          object may or may not be same as the value for the MIB-II
          'SysName' object.
		 Refer to Internet Draft Printer MIB, expiring Sept. 1997 for more details.
                Additional information:
                The maximum supported string length is 32 characters.  
                Length of 32 was chosen so a phone number could be 
                included with the name.  
                If the user-entered string is too long, the device 
                will store as much as possible and will return the
                <noError> status.
                The value of this object is saved over a power cycle."
::= { prtGeneralEntry 16 }
               
               
prtgeneralserialnumber OBJECT-TYPE
    SYNTAX  OCTET STRING (SIZE(0..11))
    ACCESS  read-only
    STATUS  optional
    DESCRIPTION
                "A recorded serial number for this device that indexes some type 
		 device catalog or inventory. This value is usually set by the
		 device manufacturer but the MIB supports the option of 
		 writeability for this object for site-specific administration of
		 device inventory or tracking.
		 Refer to Internet Draft Printer MIB, expiring Sept. 1997 for more details."
::= { prtGeneralEntry 17 }
               
               
prtalertcriticalevents OBJECT-TYPE
    SYNTAX  INTEGER
    ACCESS  read-only
    STATUS  optional
    DESCRIPTION
                "A running counter of the number of critical alert events
          that have been recorded in the alert table. The value of this
          object is RESET in the event of a power cycle operation (i.e.,
          the value is not persistent.
     Refer to Internet Draft Printer MIB, expiring Sept. 1997 for more details."
::= { prtGeneralEntry 18 }
               
               
prtalertallevents OBJECT-TYPE
    SYNTAX  INTEGER
    ACCESS  read-only
    STATUS  optional
    DESCRIPTION
                "A running counter of the total number of alert event entries
     (critical and non-critical) that have been recorded in the
     alert table
     Refer to Internet Draft Printer MIB, expiring Sept. 1997 for more details."
::= { prtGeneralEntry 19 }
               
               
prtlocalizationlanguage OBJECT-TYPE
    SYNTAX  OCTET STRING (SIZE(0..2))
    ACCESS  read-only
    STATUS  optional
    DESCRIPTION
                "A two character language code from ISO 639.  Examples
          en, gb, ca, fr, de.
	Refer to Internet Draft Printer MIB, expiring Sept. 1997 for more details.
                Additional information:
                The languages supported by The LJ Series 4000 are English, French,
                German, Italian, Spanish, Swedish, Danish, Norwegian, Dutch, Finnish,
                Portuguese, Turkish, Polish, Japanese, Russian, Czech, and Hungarian."
::= { prtLocalizationEntry 2 }
               
               
prtlocalizationcountry OBJECT-TYPE
    SYNTAX  OCTET STRING (SIZE(0..2))
    ACCESS  read-only
    STATUS  optional
    DESCRIPTION
                "A two character country code from ISO 3166, a blank string
        (two space characters) shall indicate that the country is
        not defined.  Examples: US, FR, DE, ...
	Refer to Internet Draft Printer MIB, expiring Sept. 1997 for more details.
                Additional information:
                The languages supported by The LJ Series 4000 (and corresponding
                country) are English (US, United States), French (FR, France),
                German (DE, Germany), Italian (IT, Italy), Spanish (ES, Spain),
                Swedish (SE, Sweden), Danish (DK, Denmark), Norwegian (NO, Norway),
                Dutch (NL, Netherlands), Finnish (FI, Finland), Portuguese (PT, Portugal),
                Turkish (TR, Turkey), Polish (PL, Poland), Japanese (JP, Japan),
                Russian, (RU, Russia), Czech (CS, Czechoslovakia),
                Hungarian (HU, Hungary)"
::= { prtLocalizationEntry 3 }
               
               
prtlocalizationcharacterset OBJECT-TYPE
    SYNTAX  INTEGER {
		   ePcsHPRoman8(2004),
		   ePcsISOLatin2(5),
		   ePcsISOLatin5(12),
		   ePcsWindows31J(2024),
		   ePcsISOLatinCyrillic(8)
		   }
    ACCESS  read-only
    STATUS  optional
    DESCRIPTION
                "The coded character set used for this localization.
      Refer to Internet Draft Printer MIB, expiring Sept. 1997 for more details."
::= { prtLocalizationEntry 4 }
               
               
prtmarkeraddressabilityfeeddir OBJECT-TYPE
    SYNTAX  INTEGER
    ACCESS  read-only
    STATUS  optional
    DESCRIPTION
                "The maximum number of addressable marking positions in the feed
        direction per 10000 units of measure specified by
        prtMarkerAddressabilityUnit.  A value of (-1) implies 'other' or
        'infinite' while a value of (-2) implies 'unknown'.
	Refer to Internet Draft Printer MIB, expiring Sept. 1997 for more details.
                Additional information:
                This object indicates the value of the resolution
                (dots per inch) setting for the printer.  LaserJet Series 4000 supports 300, 600 and 1200 dots per inch.  
                600 dots per inch is the default."
::= { prtMarkerEntry 9 }
               
               
prtmarkeraddressabilityxfeeddir OBJECT-TYPE
    SYNTAX  INTEGER
    ACCESS  read-only
    STATUS  optional
    DESCRIPTION
                "The maximum number of addressable marking positions in the cross
        feed direction in 10000 units of measure specified by
        prtMarkerAddressabilityUnit.  A value of (-1) implies 'other' or
        'infinite' while a value of (-2) implies 'unknown'.
	Refer to Internet Draft Printer MIB, expiring Sept. 1997 for more details.
                Additional information:
                This object indicates the value of the resolution
                (dots per inch) setting for the printer.  LaserJet Series 4000 supports 300, 600 and 1200 dots per inch.  
                600 dots per inch is the default."
::= { prtMarkerEntry 10 }
               
               
prtconsoledisplaybuffertext OBJECT-TYPE
    SYNTAX  OCTET STRING (SIZE(0..255))
    ACCESS  read-only
    STATUS  optional
    DESCRIPTION
                "The content of a line in the logical display buffer of
        the operator's console of the printer.  When a write
        operation occurs, normally a critical message, to one of
        the LineText strings, the agent should make that line
        displayable if a physical display is present.  Writing
        a zero length string clears the line.  It is an
        implementation-specific matter as to whether the agent allows
        a line to be overwritten before it has been cleared.
        Printer generated strings shall be in the localization
        specified by prtConsoleLocalization.  Management Application
        generated strings should be localized by the Management
        Application.
	Refer to Internet Draft Printer MIB, expiring Sept. 1997 for more details.
                Additional information:
                The objects BACKGROUND-STATUS-MSG-LINE1-PART1 
                and BACKGROUND-STATUS-MSG-LINE2-PART1 should be used to
                write messages to the control panel display.  
                prtConsoleDisplayBufferText.[1..4] maps to logical line
                [1..4] of the display.  There are three types of messages
                that may be shown on the display.  How each type is
                represented through these objects is described below:  
                
                2-Line Display - A display message that has at most two
                physical lines of text.  prtConsoleDisplayBufferText.1 will
                map to the first line.  prtConsoleDisplayBufferText.2 will
                map to the second line.  prtConsoleDisplayBufferText.3 and
                prtConsoleDisplayBufferText.4 will return NULL.  
                
                Two 2-Line Displays Alternating - Two different 2-Line
                messages that are alternating on the display at three
                second intervals.  One message is usually a status message,
                such as READY, and the other is usually a warning message,
                such as TRAY 2 EMPTY.  The order in which the messages
                appear through these objects will not always be the
                same.  In general, if the previous message, such as READY,
                is repeated in the alternating message it will be
                placed in prtConsoleDisplayBufferText.3 and
                prtConsoleDisplayBufferText.4.  The new message that is
                being alternated with the original one will be placed in
                prtConsoleDisplayBufferText.1 and
                prtConsoleDisplayBufferText.2.  This mainly allows the
                new message to be shown right away on the physical
                display, rather then 3 seconds after the event that
                caused it.  
                
                4-Line Display - A display message that has at least
                three and at most four lines of text to be displayed.
                These messages will only be error messages.
                The first two lines of the message will
                alternate every three seconds with the last two lines
                of the message.  prtConsoleDisplayBufferText.1 will
                map to the first line of the 4-line message.
                prtConsoleDisplayBufferText.2 will map to the second line
                of the 4-line message.  prtConsoleDisplayBufferText.3 will
                map to the third line of the 4-line message.
                prtConsoleDisplayBufferText.4 will map to the fourth line
                of the 4-line message.  "
::= { prtConsoleDisplayBufferEntry 2 }
               
               
prtconsoleontime OBJECT-TYPE
    SYNTAX  INTEGER
    ACCESS  read-only
    STATUS  optional
    DESCRIPTION
                "This object, in conjunction with prtConsoleOffTime, defines
        the current status of the light.  If both prtConsoleOnTime and
        prtConsoleOffTime are non-zero, the lamp is blinking and the
        values presented define the on time and off time, respectively,
        in milliseconds.  If prtConsoleOnTime is zero and 
        prtConsoleOffTime is non-zero, the lamp is off.  If 
        prtConsoleOffTime is zero and prtConsoleOnTime is non-zero, 
        the lamp is on.  If both values are zero the status of the
        lamp is undefined.
	Refer to Internet Draft Printer MIB, expiring Sept. 1997 for more details.
                Additional information:
                There are three control panel LED's:  Ready (1),
                Data (2), and Attention (3).  When an LED blinks, it is typically on for
                one half second and off for one half second.  The value used for this object
                is 500 when the LED is on or blinking, otherwise it is zero."
::= { prtConsoleLightEntry 2 }
               
               
prtconsoleofftime OBJECT-TYPE
    SYNTAX  INTEGER
    ACCESS  read-only
    STATUS  optional
    DESCRIPTION
                "This object, in conjunction with prtConsoleOnTime, defines
        the current status of the light.  If both prtConsoleOnTime and
        prtConsoleOffTime are non-zero, the lamp is blinking and the
        values presented define the on time and off time, respectively,
        in milliseconds.  If prtConsoleOnTime is zero and 
        prtConsoleOffTime is non-zero, the lamp is off.  If 
        prtConsoleOffTime is zero and prtConsoleOnTime is non-zero, 
        the lamp is on.  If both values are zero the status of the
        lamp is undefined.
	Refer to Internet Draft Printer MIB, expiring Sept. 1997 for more details.
                Additional information:
                There are three control panel LED's:  Ready (1),
                Data (2), and Attention (3).  When an LED blinks, it is typically on for
                one half second and off for one half second.  The value used for this object
                is 500 when the LED is off or blinking, otherwise it is zero."
::= { prtConsoleLightEntry 3 }
               
               
prtconsolecolor OBJECT-TYPE
    SYNTAX  INTEGER {
		   ePother(1),
		   ePunknown(2),
		   ePwhite(3),
		   ePred(4),
		   ePgreen(5),
		   ePblue(6),
		   ePcyan(7),
		   ePmagenta(8),
		   ePyellow(9)
		   }
    ACCESS  read-only
    STATUS  optional
    DESCRIPTION
                "The color of this light.
	Refer to Internet Draft Printer MIB, expiring Sept. 1997 for more details."
::= { prtConsoleLightEntry 4 }
               
               
prtconsoledescription OBJECT-TYPE
    SYNTAX  OCTET STRING (SIZE(0..255))
    ACCESS  read-only
    STATUS  optional
    DESCRIPTION
                "The vendor description or label of this light in the
        localization specified by prtConsoleLocalization.
	Refer to Internet Draft Printer MIB, expiring Sept. 1997 for more details."
::= { prtConsoleLightEntry 5 }
               
               
prtalertseveritylevel OBJECT-TYPE
    SYNTAX  INTEGER {
		   ePother(1),
		   ePcriticalBinaryChangeEvent(3),
		   ePwarningUnaryChangeEvent(4),
		   ePwarningBinaryChangeEvent(5)
		   }
    ACCESS  read-only
    STATUS  optional
    DESCRIPTION
                "The level of severity of this alert table entry.  The printer
        determines the severity level assigned to each entry into the
        table.
	Refer to Internet Draft Printer MIB, expiring Sept. 1997 for more details."
::= { prtAlertEntry 2 }
               
               
prtalerttraininglevel OBJECT-TYPE
    SYNTAX  INTEGER {
		   ePother(1),
		   ePuntrained(3),
		   ePtrained(4),
		   ePfieldService(5),
		   ePmanagement(6),
		   ePnoInterventionRequired(7)
		   }
    ACCESS  read-only
    STATUS  optional
    DESCRIPTION
                "See textual convention PrtAlertTrainingLevelTC
	Refer to Internet Draft Printer MIB, expiring Sept. 1997 for more details.
                Additional information:
                The value of this object depends on the alert.
                Some examples:  
                ePfieldService: Marker failure.  
                ePtrained: Toner low.  
                ePuntrained: Paper low/out.  
                ePmanagement: Configuration change."
::= { prtAlertEntry 3 }
               
               
prtalertgroup OBJECT-TYPE
    SYNTAX  INTEGER {
		   ePgeneralPrinter(5),
		   ePcover(6),
		   ePinput(8),
		   ePoutput(9),
		   ePmarker(10),
		   ePmarkerSupplies(11),
		   ePchannel(14)
		   }
    ACCESS  read-only
    STATUS  optional
    DESCRIPTION
                "The type of sub-unit within the printer model that this alert
        is related.  Input, output, and markers are examples of
        printer model groups, i.e., examples of types of sub-units.
        Wherever possible, these enumerations match the
        sub-identifier that identifies the relevant table in the
        printmib.
	Refer to Internet Draft Printer MIB, expiring Sept. 1997 for more details."
::= { prtAlertEntry 4 }
               
               
prtalertgroupindex OBJECT-TYPE
    SYNTAX  INTEGER
    ACCESS  read-only
    STATUS  optional
    DESCRIPTION
                "An index of the row within the principle table in the
        group identified by prtAlertGroup that represents the
        sub-unit of the printer that caused this alert.  The
        combination of the prtAlertGroup and the prtAlertGroupIndex defines
        exactly which printer sub-unit caused the alert.; for
        example, Input #3, Output #2, and Marker #1.
        Every object in this MIB is indexed with hrDeviceIndex and
        optionally, another index variable.  If this other index
        variable is present in the table that generated the alert, it
        will be used as the value for this object.  Otherwise, this
        value shall be -1.
	Refer to Internet Draft Printer MIB, expiring Sept. 1997 for more details."
::= { prtAlertEntry 5 }
               
               
prtalertlocation OBJECT-TYPE
    SYNTAX  INTEGER
    ACCESS  read-only
    STATUS  optional
    DESCRIPTION
                "The sub-unit location that is defined by the printer
        manufacturer to further refine the location of this alert
        within the designated sub-unit.  The location is used in
        conjunction with the Group and GroupIndex values; for
        example, there is an alert in Input #2 at location number 7.
	 The value (-2) indicates unknown
	 Refer to Internet Draft Printer MIB, expiring Sept. 1997 for more details."
::= { prtAlertEntry 6 }
               
               
prtalertcode OBJECT-TYPE
    SYNTAX  INTEGER {
		   ePother(1),
		   ePcoverOpened(3),
		   ePjam(8),
		   ePsubunitMissing(9),
		   ePsubunitAlmostEmpty(12),
		   ePsubunitEmpty(13),
		   ePsubunitAlmostFull(14),
		   ePsubunitFull(15),
		   ePsubunitOffline(22),
		   ePsubunitPowerSaver(23),
		   ePsubunitMotorFailure(33),
		   ePsubunitMemoryExhausted(34),
		   ePmarkerFuserUnderTemperature(1001),
		   ePmarkerFuserOverTemperature(1002),
		   ePmarkerTonerEmpty(1101),
		   ePmarkerTonerAlmostEmpty(1104)
		   }
    ACCESS  read-only
    STATUS  optional
    DESCRIPTION
                "See associated textual convention PrtAlertCodeTC
	Refer to Internet Draft Printer MIB, expiring Sept. 1997 for more details."
::= { prtAlertEntry 7 }
               
               
prtalertdescription OBJECT-TYPE
    SYNTAX  OCTET STRING (SIZE(0..255))
    ACCESS  read-only
    STATUS  optional
    DESCRIPTION
                "A description of this alert entry in the localization
        specified by prtGeneralCurrentLocalization.  The description is
        provided by the printer to further elaborate on the enumerated
        alert or provide information in the case where the code is
        classified as `other' or `unknown'.  The printer is required
        to return a description string but the string may be a null
        string.
	Refer to Internet Draft Printer MIB, expiring Sept. 1997 for more details."
::= { prtAlertEntry 8 }
              
 
prtalerttime OBJECT-TYPE
    SYNTAX  INTEGER
    ACCESS  read-only
    STATUS  optional
    DESCRIPTION
                "The value of sysUpTime at the time that this alert was
        generated.
	Refer to Internet Draft Printer MIB, expiring Sept. 1997 for more details."
::= { prtAlertEntry 9 }
               
               
job-input-auto-continue-timeout OBJECT-TYPE
    SYNTAX  INTEGER(-1..3600)
    ACCESS  read-write
    STATUS  optional
    DESCRIPTION
                "The number of seconds the device waits after a job
                related continuable error occurs before automatically
                continuing.  An example job related continuable error is
                the job requesting a media size that is not available.
                After the timeout expires, the device will continue
                processing the job as if a continue event occurred, such
                as the front panel continue key being pressed.  If the
                value is -1, the device does not automatically continue
                after a job related continuable error occurs.  If the
                value is 0, the device immediately continues.  If the
                value is greater than 0, the value represents the
                timeout value in seconds.
                Additional information:
                This object is used only for media requests
                (size and/or name).  
                The LJ Series 4000 supports any value in the range of -1 to 3600. Setting to a value
                outside of that range causes the printer to substitute a value (listed
                below) and to return <noError> status.  
                The values are as follow:  
                <-1 snaps to -1  
                >3600 snaps to 3600  (60 minutes)  
                The action that occurs when this timeout expires is explained by
                JOB-INPUT-AUTO-CONTINUE-MODE. It is not the same as the CONTINUE
                object being set to eInitiateAction or the Select key being pressed on
                the control panel. See 
                the CONTINUE object description for information on the actions that
                occur for those conditions. The value of this object is stored in NVRAM,
                so it is maintained across a power cycle."
::= { status-system 35 }
               
               
job-input-auto-continue-mode OBJECT-TYPE
    SYNTAX  OCTET STRING
    ACCESS  read-write
    STATUS  optional
    DESCRIPTION
                "Returns or sets the device behavior when the desired
                media is not currently available.
                  cCancelJob - The device cancels the job.  The device
                POS should explain what happens if this item is not the
                only item in the collection.
                  cAutoMediaSizeOverride - The device is allowed to
                substitute a different size media.
                  cAutoMediaNameOverride - The device is allowed to
                substitute a different media name.
                Additional information:
                If cCancelJob is set, the current print job will
                be canceled regardless of other item settings. At least one bit of the
                collection must be set; setting this object to zero will cause a status of
                <badValue> to be returned.  
                This object applies to all media requests, including Manual Feed Requests.  
                This object describes the action that is performed when the
                JOB-INPUT-AUTO-CONTINUE-TIMEOUT expires. The action performed by the CONTINUE
                object being set to eInitiateAction or the GO key being pressed on
                the control panel may cause different actions.
                See the CONTINUE object
                description for information on the actions that occur for those conditions."
::= { status-system 36 }
               
               
job-output-auto-continue-timeout OBJECT-TYPE
    SYNTAX  INTEGER(-1..3600)
    ACCESS  read-write
    STATUS  optional
    DESCRIPTION
                "Returns or sets the time that the printer will wait
                after an output bin becomes full and the printer is
                trying to deliver a sheet of media to that output bin.
                When the timeout expires, the job is processed according
                to the OUTBINn-OVERRIDE-MODE.  A value of -1 indicates
                that the printer will wait for a continue event.  A non-
                negative value is the number of seconds to wait.
                Additional information:
                A value of zero means to continue immediately.
                The value of this object is stored in NVRAM, so
                it is maintained across a power cycle."
::= { status-system 40 }
               
               
phd2-model OBJECT-TYPE
    SYNTAX  DisplayString
    ACCESS  read-only
    STATUS  optional
    DESCRIPTION
                "Returns product information identifying PHD device 2.
                Additional information:
                If at least one (1) external paper handling device
                is attached to the printer, then this object will
                exist, otherwise <noSuchName> should be returned. 
                This object returns product information about the
                first paper handling device in the device chain."
::= { phd2 1 }
               
               
phd2-manufacturing-info OBJECT-TYPE
    SYNTAX  DisplayString
    ACCESS  read-only
    STATUS  optional
    DESCRIPTION
                "Returns information describing the manufacture of PHD 2.
                May include serial number and firmware revision.
                Additional information:
                If at least one (1) external paper handling device
                is attached to the printer, then this object will
                exist, otherwise <noSuchName> should be returned.  
                This object returns the name of the manufacturer of
                the first paper handling device."
::= { phd2 2 }
               
               
phd2-type OBJECT-TYPE
    SYNTAX  INTEGER {
		   eEmpty(1),
		   eUnknown(2),
		   eUnSupported(3),
		   eReadOnlyMemory(4),
		   eVolatileRandomAccessMemory(5),
		   eNonVolatileRandomAccessMemory(6),
		   eFlashMemory(7),
		   eDiskDrive(8),
		   eRamRom(9),
		   eInputPHD(10),
		   eOutputPHD(11),
		   eIOCard(12)
		   }
    ACCESS  read-only
    STATUS  optional
    DESCRIPTION
                "Returns an indication of the type of option installed in
                PHD interface 2.  See SIMM1-TYPE for an explanation of
                the enumerations.
                Additional information:
                If at least one (1) external paper handling device
                is attached to the printer, then this object will
                exist, otherwise <noSuchName> should be returned. 
                This object returns whether the device is an input
                device or an output device."
::= { phd2 3 }
               
               
phd2-capacity OBJECT-TYPE
    SYNTAX  INTEGER
    ACCESS  read-only
    STATUS  optional
    DESCRIPTION
                "Returns an indication of the capacity of the installed
                option.  See SIMM1-CAPACITY for an explanation of the
                meaning of the value of this object.
                Additional information:
                If at least one (1) external paper handling device
                (EPHD) is attached to the printer, then this object 
                will exist, otherwise <noSuchName> should be returned. 
                This object returns the number of input trays or
                output bins, depending the the device type (see
                PHD2-TYPE) for the first EPHD in the device chain."
::= { phd2 4 }
               
               
phd3-model OBJECT-TYPE
    SYNTAX  DisplayString
    ACCESS  read-only
    STATUS  optional
    DESCRIPTION
                "Returns product information identifying PHD device 3.
                Additional information:
                If at least two (2) external paper handling devices
                are attached to the printer, then this object will
                exist, otherwise <noSuchName> should be returned.
                This object returns product information about the
                second paper handling device in the device chain."
::= { phd3 1 }
               
               
phd3-manufacturing-info OBJECT-TYPE
    SYNTAX  DisplayString
    ACCESS  read-only
    STATUS  optional
    DESCRIPTION
                "Returns information describing the manufacture of PHD 3.
                May include serial number and firmware revision.
                Additional information:
                If at least two (2) external paper handling devices
                are attached to the printer, then this object will
                exist, otherwise <noSuchName> should be returned. 
                This object returns the name of the manufacturer of
                the second paper handling device."
::= { phd3 2 }
               
               
phd3-type OBJECT-TYPE
    SYNTAX  INTEGER {
		   eEmpty(1),
		   eUnknown(2),
		   eUnSupported(3),
		   eReadOnlyMemory(4),
		   eVolatileRandomAccessMemory(5),
		   eNonVolatileRandomAccessMemory(6),
		   eFlashMemory(7),
		   eDiskDrive(8),
		   eRamRom(9),
		   eInputPHD(10),
		   eOutputPHD(11),
		   eIOCard(12)
		   }
    ACCESS  read-only
    STATUS  optional
    DESCRIPTION
                "Returns an indication of the type of option installed in
                PHD interface 3.  See SIMM1-TYPE for an explanation of
                the enumerations.
                Additional information:
                If at least two (2) external paper handling devices
                are attached to the printer, then this object will
                exist, otherwise <noSuchName> should be returned.
                This object returns whether the second device is an 
                input device or an output device."
::= { phd3 3 }
               
               
phd3-capacity OBJECT-TYPE
    SYNTAX  INTEGER
    ACCESS  read-only
    STATUS  optional
    DESCRIPTION
                "Returns an indication of the capacity of the installed
                option.  See SIMM1-CAPACITY for an explanation of the
                meaning of the value of this object.
                Additional information:
                If at least two (2) external paper handling devices
                (EPHD) are attached to the printer, then this object 
                will exist, otherwise <noSuchName> should be returned. 
                This object returns the number of input trays or
                output bins, depending the the device type (see
                PHD3-TYPE) for the second EPHD in the device chain."
::= { phd3 4 }
               
               
phd4-model OBJECT-TYPE
    SYNTAX  DisplayString
    ACCESS  read-only
    STATUS  optional
    DESCRIPTION
                "Returns product information identifying PHD device 4.
                Additional information:
                If at least three (3) external paper handling devices
                are attached to the printer, then this object will
                exist, otherwise <noSuchName> should be returned. 
                This object returns product information about the
                third paper handling device in the device chain."
::= { phd4 1 }
               
               
phd4-manufacturing-info OBJECT-TYPE
    SYNTAX  DisplayString
    ACCESS  read-only
    STATUS  optional
    DESCRIPTION
                "Returns information describing the manufacture of PHD 4.
                May include serial number and firmware revision.
                Additional information:
                If at least three (3) external paper handling devices
                are attached to the printer, then this object will
                exist, otherwise <noSuchName> should be returned.
                This object returns the name of the manufacturer of
                the third paper handling device."
::= { phd4 2 }
               
               
phd4-type OBJECT-TYPE
    SYNTAX  INTEGER {
		   eEmpty(1),
		   eUnknown(2),
		   eUnSupported(3),
		   eReadOnlyMemory(4),
		   eVolatileRandomAccessMemory(5),
		   eNonVolatileRandomAccessMemory(6),
		   eFlashMemory(7),
		   eDiskDrive(8),
		   eRamRom(9),
		   eInputPHD(10),
		   eOutputPHD(11),
		   eIOCard(12)
		   }
    ACCESS  read-only
    STATUS  optional
    DESCRIPTION
                "Returns an indication of the type of option installed in
                PHD interface 4.  See SIMM1-TYPE for an explanation of
                the enumerations.
                Additional information:
                If at least three (3) external paper handling devices
                are attached to the printer, then this object will
                exist, otherwise <noSuchName> should be returned. 
                This object returns whether the third device is an 
                input device or an output device."
::= { phd4 3 }
               
               
phd4-capacity OBJECT-TYPE
    SYNTAX  INTEGER
    ACCESS  read-only
    STATUS  optional
    DESCRIPTION
                "Returns an indication of the capacity of the installed
                option.  See SIMM1-CAPACITY for an explanation of the
                meaning of the value of this object.
                Additional information:
                If at least three (3) external paper handling devices
                (EPHD) are attached to the printer, then this object 
                will exist, otherwise <noSuchName>
                should be returned.
                This object returns the number of input trays or
                output bins, depending the the device type (see
                PHD4-TYPE) for the third EPHD in the device chain."
::= { phd4 4 }
               
               
phd5-model OBJECT-TYPE
    SYNTAX  DisplayString
    ACCESS  read-only
    STATUS  optional
    DESCRIPTION
                "Returns product information identifying PHD device 3.
                Additional information:
                If at least four (4) external paper handling devices
                are attached to the printer, then this object will
                exist, otherwise <noSuchName>
                should be returned.  
                This object returns product information about the
                fourth paper handling device in the device chain."
::= { phd5 1 }
               
               
phd5-manufacturing-info OBJECT-TYPE
    SYNTAX  DisplayString
    ACCESS  read-only
    STATUS  optional
    DESCRIPTION
                "Returns information describing the manufacture of PHD 5.
                May include serial number and firmware revision.
                Additional information:
                If at least four (4) external paper handling devices
                are attached to the printer, then this object will
                exist, otherwise <noSuchName>
                should be returned.
                This object returns the name of the manufacturer of
                the fourth paper handling device."
::= { phd5 2 }
               
               
phd5-type OBJECT-TYPE
    SYNTAX  INTEGER {
		   eEmpty(1),
		   eUnknown(2),
		   eUnSupported(3),
		   eReadOnlyMemory(4),
		   eVolatileRandomAccessMemory(5),
		   eNonVolatileRandomAccessMemory(6),
		   eFlashMemory(7),
		   eDiskDrive(8),
		   eRamRom(9),
		   eInputPHD(10),
		   eOutputPHD(11),
		   eIOCard(12)
		   }
    ACCESS  read-only
    STATUS  optional
    DESCRIPTION
                "Returns an indication of the type of option installed in
                PHD interface 5.  See SIMM1-TYPE for an explanation of
                the enumerations.
                Additional information:
                If at least four (4) external paper handling devices
                are attached to the printer, then this object will
                exist, otherwise <noSuchName>
                should be returned.  
                This object returns whether the fourth device is an 
                input device or an output device."
::= { phd5 3 }
               
               
phd5-capacity OBJECT-TYPE
    SYNTAX  INTEGER
    ACCESS  read-only
    STATUS  optional
    DESCRIPTION
                "Returns an indication of the capacity of the installed
                option.  See SIMM1-CAPACITY for an explanation of the
                meaning of the value of this object.
                Additional information:
                If at least four (4) external paper handling devices
                (EPHD) are attached to the printer, then this object 
                will exist, otherwise <noSuchName>
                should be returned.
                This object returns the number of input trays or
                output bins, depending the the device type (see
                PHD5-TYPE) for the fourth EPHD in the device chain."
::= { phd5 4 }
               
               
phd6-model OBJECT-TYPE
    SYNTAX  DisplayString
    ACCESS  read-only
    STATUS  optional
    DESCRIPTION
                "Returns product information identifying PHD device 6.
                Additional information:
                If at least five (5) external paper handling devices
                are attached to the printer, then this object will
                exist, otherwise <noSuchName>
                should be returned.  
                This object returns product information about the
                fifth paper handling device in the device chain."
::= { phd6 1 }
               
               
phd6-manufacturing-info OBJECT-TYPE
    SYNTAX  DisplayString
    ACCESS  read-only
    STATUS  optional
    DESCRIPTION
                "Returns information describing the manufacture of PHD 6.
                May include serial number and firmware revision.
                Additional information:
                If at least five (5) external paper handling devices
                are attached to the printer, then this object will
                exist, otherwise <noSuchName>
                should be returned.
                This object returns the name of the manufacturer of
                the fifth paper handling device."
::= { phd6 2 }
               
               
phd6-type OBJECT-TYPE
    SYNTAX  INTEGER {
		   eEmpty(1),
		   eUnknown(2),
		   eUnSupported(3),
		   eReadOnlyMemory(4),
		   eVolatileRandomAccessMemory(5),
		   eNonVolatileRandomAccessMemory(6),
		   eFlashMemory(7),
		   eDiskDrive(8),
		   eRamRom(9),
		   eInputPHD(10),
		   eOutputPHD(11),
		   eIOCard(12)
		   }
    ACCESS  read-only
    STATUS  optional
    DESCRIPTION
                "Returns an indication of the type of option installed in
                PHD interface 6.  See SIMM1-TYPE for an explanation of
                the enumerations.
                Additional information:
                If at least five (5) external paper handling devices
                are attached to the printer, then this object will
                exist, otherwise <noSuchName>
                should be returned.  
                This object returns whether the fifth device is an 
                input device or an output device."
::= { phd6 3 }
               
               
phd6-capacity OBJECT-TYPE
    SYNTAX  INTEGER
    ACCESS  read-only
    STATUS  optional
    DESCRIPTION
                "Returns an indication of the capacity of the installed
                option.  See SIMM1-CAPACITY for an explanation of the
                meaning of the value of this object.
                Additional information:
                If at least five (5) external paper handling devices
                (EPHD) are attached to the printer, then this object 
                will exist, otherwise <noSuchName>
                should be returned.
                This object returns the number of input trays or
                output bins, depending the the device type (see
                PHD6-TYPE) for the fifth EPHD in the device chain."
::= { phd6 4 }
               
               
default-media-name OBJECT-TYPE
    SYNTAX  DisplayString
    ACCESS  read-write
    STATUS  optional
    DESCRIPTION
                "Returns or sets the media name that is used until the
                media name is changed by a print job command.
                Additional information:
                This string must be one of the MEDIAn-NAME 
                objects. The value of this object is saved across a power cycle."
::= { settings-pdl 22 }
               
               
override-media-name OBJECT-TYPE
    SYNTAX  DisplayString
    ACCESS  read-write
    STATUS  optional
    DESCRIPTION
                "Sets a string identifying the media name that is to be
                used in place of the currently requested media.  The
                substitution will continue until another media is
                selected.  If set to a named media that is not currently
                available the requested media is not overridden.
                Additional information:
                When a request is received to print on a size and
                type of media that is not currently available, this object contains the
                desired media name as set by the print job. This object should be set to a
                media name that is currently available in the printer.  
                If a paper mount request is not pending, attempting to get or set this object
                will cause <noSuchName> to be returned.  
                Setting this object to a string other than one of the MEDIAn-NAME objects
                (MEDIA-NAMES-AVAILABLE is applied) will cause a status of
                <badValue> to be returned."
::= { settings-prt-eng 2 }
               
               
custom-paper-dim-unit OBJECT-TYPE
    SYNTAX  INTEGER {
		   eTenThousandthsOfInches(3),
		   eMicrometers(4)
		   }
    ACCESS  read-write
    STATUS  optional
    DESCRIPTION
                "The units of measure used to specify the width and
                height of the printer's custom paper.  The unit of
                measure of eTenThousandthsOfInches is 0.0001 inches."
::= { settings-intray 7 }
               
               
tray1-phd OBJECT-TYPE
    SYNTAX  INTEGER
    ACCESS  read-only
    STATUS  optional
    DESCRIPTION
                "Provides the number of the Paper Handling Device that
                contains this input tray."
::= { intray1 12 }
               
               
overflow-bin OBJECT-TYPE
    SYNTAX  INTEGER
    ACCESS  read-write
    STATUS  optional
    DESCRIPTION
                "Returns or sets the bin that will be used for additional
                sheets of media when the current bin is full and
                printing is allowed to continue.
                Additional information:
                If this object is set to zero, overflowing to another 
                bin is not allowed."
::= { settings-outbin 4 }
               
               
outbin1-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                If cCancelJob is set, the current print job will 
                be cancelled regardless of other item settings.  
                If cOutbinFullOverride is set and this bin is the designated overflow bin 
                (OVERFLOW-BIN = 1), then the bit is ignored.  This object describes the
                action that is performed when the JOB-OUTPUT-AUTO-CONTINUE-TIMEOUT expires.
                If no bits are set, no override action is taken (the printer will continue
                to wait).  
                The action performed by the CONTINUE object being set to eInitiateAction
                or the GO key being pressed on the control panel may cause different actions. 
                See the CONTINUE object description for
                information on the actions that occur for those conditions."
::= { outbin1 9 }
               
               
outbin3-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                If cCancelJob is set, the current print job will 
                be cancelled regardless of other item settings.   
                This object describes the action that is performed when the 
                JOB-OUTPUT-AUTO-CONTINUE-TIMEOUT expires. The action performed by the CONTINUE 
                object being set to eInitiateAction or the GO key being pressed on the
                control panel may cause different actions. 
                See the CONTINUE object description for
                information on the actions that occur for those conditions"
::= { outbin3 9 }
               
               
outbin4-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin4 9 }
               
               
outbin5-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin5 9 }
               
               
outbin6-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin6 9 }
               
               
outbin7-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin7 9 }
               
               
outbin8-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin8 9 }
               
               
outbin9-override-mode OBJECT-TYPE
    SYNTAX  OCTET STRING
    ACCESS  read-write
    STATUS  optional
    DESCRIPTION
                "Returns or sets the device behavior when this output bin
                condition causes printing to stop.  
                  cCancelJob - The device cancels the job.  
                  cOutbinFullOverride - The device sends subsequent
                media to the overflow bin.  
                  cOutbinAttentionOverride - The device ignores the
                attention condition and continues printing.  
                  cBinderAttentionOverride - The device ignores the
                binder attention condition and continues printing.
                Additional information:
                See OUTBIN3-OVERRIDE-MODE."
::= { outbin9 9 }
               
               
phd2-device-specific-command OBJECT-TYPE
    SYNTAX  OCTET STRING
    ACCESS  write-only
    STATUS  optional
    DESCRIPTION
                "This object is used to send device-specific data to the
                paper handling device.  The meaning of the device-
                specific command is dependent on the paper handling
                device and must be specified in the POS.  
                If the paper handling device does not accept the
                command, then an <badValue> will
                be returned.  If the device accepts the command, it may
                still be processing the command after the response has
                been returned.  Depending on the device, the application
                may need to query PHDx-DEVICE-MEMORY to see when the
                command has completed.
                Additional information:
                If at least one (1) external paper handling device
                is attached to the printer, then this object will
                exist, otherwise <noSuchName> 
                will be returned.  
                Since the data formats can vary from device to
                device, this information must be documented for
                each device by the manufacturer of the device.
                If the device does not support this command, then
                an <badValue> error message
                will be returned.  
                Since it will usually take longer to send this
                command to the device than PML allows for <Set>
                operations, this object will have a return value
                that does not necessarily match the value currently
                received by the first device."
::= { ph2 2 }
               
               
phd2-device-memory OBJECT-TYPE
    SYNTAX  OCTET STRING
    ACCESS  read-only
    STATUS  optional
    DESCRIPTION
                "This object is used to read the current values stored in
                shared memory available from the paper handling device.
                Additional information:
                If at least one (1) external paper handling device
                is attached to the printer, then this object will
                exist, otherwise <noSuchName>
                should be returned.  
                This object returns the current memory stored in
                the printer's NVRAM (non-volatile RAM) for the
                first paper handling device.  Currently, the
                printer allocates 16 bytes for each device."
::= { ph2 4 }
               
               
phd3-device-specific-command OBJECT-TYPE
    SYNTAX  OCTET STRING
    ACCESS  write-only
    STATUS  optional
    DESCRIPTION
                "This object is used to send device-specific data to the
                paper handling device.  The meaning of the device-
                specific command is dependent on the paper handling
                device and must be specified in the POS.  
                If the paper handling device does not accept the
                command, then an <badValue> error message will
                be returned.  If the device accepts the command, it may
                still be processing the command after the response has
                been returned.  Depending on the device, the application
                may need to query PHDx-DEVICE-MEMORY to see when the
                command has completed.
                Additional information:
                If at least two (2) external paper handling devices
                are attached to the printer, then this object will
                exist, otherwise <noSuchName> 
                will be returned.  
                Since the data formats can vary from device to
                device, this information must be documented for
                each device by the manufacturer of the device.
                If the device does not support this command, then
                an <badValue> error message will be returned.
                Since it will usually take longer to send this
                command to the device than PML allows for <Set>
                operations, this object will have a return value
                that does not necessarily match the value currently
                received by the second device."
::= { ph3 2 }
               
               
phd3-device-memory OBJECT-TYPE
    SYNTAX  OCTET STRING
    ACCESS  read-only
    STATUS  optional
    DESCRIPTION
                "This object is used to read the current values stored in
                shared memory available from the paper handling device.
                Additional information:
                If at least two (2) external paper handling devices
                are attached to the printer, then this object will
                exist, otherwise <noSuchName>
                should be returned.  
                This object returns the current memory stored in
                the printer's NVRAM (non-volatile RAM) for the
                second paper handling device.  Currently, the
                printer allocates 16 bytes for each device."
::= { ph3 4 }
               
               
phd4-device-specific-command OBJECT-TYPE
    SYNTAX  OCTET STRING
    ACCESS  write-only
    STATUS  optional
    DESCRIPTION
                "This object is used to send device-specific data to the
                paper handling device.  The meaning of the device-
                specific command is dependent on the paper handling
                device and must be specified in the POS.  
                If the paper handling device does not accept the
                command, then an <badValue> will
                be returned.  If the device accepts the command, it may
                still be processing the command after the response has
                been returned.  Depending on the device, the application
                may need to query PHDx-DEVICE-MEMORY to see when the
                command has completed.
                Additional information:
                If at least three (3) external paper handling devices
                are attached to the printer, then this object will
                exist, otherwise <noSuchName> 
                will be returned.  
                Since the data formats can vary from device to
                device, this information must be documented for
                each device by the manufacturer of the device.
                If the device does not support this command, then
                an <badValue> error message
                will be returned.  
                Since it will usually take longer to send this
                command to the device than PML allows for <Set>
                operations, this object will have a return value
                that does not necessarily match the value currently
                received by the third device."
::= { ph4 2 }
               
               
phd4-device-memory OBJECT-TYPE
    SYNTAX  OCTET STRING
    ACCESS  read-only
    STATUS  optional
    DESCRIPTION
                "This object is used to read the current values stored in
                shared memory available from the paper handling device.
                Additional information:
                If at least three (3) external paper handling devices
                are attached to the printer, then this object will
                exist, otherwise <noSuchName>
                should be returned.  
                This object returns the current memory stored in
                the printer's NVRAM (non-volatile RAM) for the
                second paper handling device.  Currently, the
                printer allocates 16 bytes for each device."
::= { ph4 4 }
               
               
phd5-device-specific-command OBJECT-TYPE
    SYNTAX  OCTET STRING
    ACCESS  write-only
    STATUS  optional
    DESCRIPTION
                "This object is used to send device-specific data to the
                paper handling device.  The meaning of the device-
                specific command is dependent on the paper handling
                device and must be specified in the POS.  
                If the paper handling device does not accept the
                command, then an <badValue> will
                be returned.  If the device accepts the command, it may
                still be processing the command after the response has
                been returned.  Depending on the device, the application
                may need to query PHDx-DEVICE-MEMORY to see when the
                command has completed.
                Additional information:
                If at least four (4) external paper handling devices
                are attached to the printer, then this object will
                exist, otherwise <noSuchName> 
                will be returned.  
                Since the data formats can vary from device to
                device, this information must be documented for
                each device by the manufacturer of the device.
                If the device does not support this command, then
                an <badValue> error message
                will be returned.  
                Since it will usually take longer to send this
                command to the device than PML allows for <Set>
                operations, this object will have a return value
                that does not necessarily match the value currently
                received by the fourth device."
::= { ph5 2 }
               
               
phd5-device-memory OBJECT-TYPE
    SYNTAX  OCTET STRING
    ACCESS  read-only
    STATUS  optional
    DESCRIPTION
                "This object is used to read the current values stored in
                shared memory available from the paper handling device.
                Additional information:
                If at least four (4) external paper handling devices
                are attached to the printer, then this object will
                exist, otherwise <noSuchName>
                should be returned.  
                This object returns the current memory stored in
                the printer's NVRAM (non-volatile RAM) for the
                second paper handling device.  Currently, the
                printer allocates 16 bytes for each device."
::= { ph5 4 }
               
               
phd6-device-specific-command OBJECT-TYPE
    SYNTAX  OCTET STRING
    ACCESS  write-only
    STATUS  optional
    DESCRIPTION
                "This object is used to send device-specific data to the
                paper handling device.  The meaning of the device-
                specific command is dependent on the paper handling
                device and must be specified in the POS.  
                If the paper handling device does not accept the
                command, then an <badValue> will
                be returned.  If the device accepts the command, it may
                still be processing the command after the response has
                been returned.  Depending on the device, the application
                may need to query PHDx-DEVICE-MEMORY to see when the
                command has completed.
                Additional information:
                If at least five (5) external paper handling devices
                are attached to the printer, then this object will
                exist, otherwise <noSuchName> 
                will be returned.  
                Since the data formats can vary from device to
                device, this information must be documented for
                each device by the manufacturer of the device.
                If the device does not support this command, then
                an <badValue> error message
                will be returned.  
                Since it will usually take longer to send this
                command to the device than PML allows for <Set>
                operations, this object will have a return value
                that does not necessarily match the value currently
                received by the fifth device."
::= { ph6 2 }
               
               
phd6-device-memory OBJECT-TYPE
    SYNTAX  OCTET STRING
    ACCESS  read-only
    STATUS  optional
    DESCRIPTION
                "This object is used to read the current values stored in
                shared memory available from the paper handling device.
                Additional information:
                If at least five (5) external paper handling devices
                are attached to the printer, then this object will
                exist, otherwise <noSuchName>
                should be returned.  
                This object returns the current memory stored in
                the printer's NVRAM (non-volatile RAM) for the
                second paper handling device.  Currently, the
                printer allocates 16 bytes for each device."
::= { ph6 4 }
               
               
media1-name OBJECT-TYPE
    SYNTAX  DisplayString (SIZE(1..24))
    ACCESS  read-only
    STATUS  optional
    DESCRIPTION
                "Media 1 name.
                Additional information:
                The symbol set for this string is Roman-8."
::= { media1 1 }
               
               
media1-short-name OBJECT-TYPE
    SYNTAX  DisplayString (SIZE(1..9))
    ACCESS  read-only
    STATUS  optional
    DESCRIPTION
                "Length restricted version of the media name 1.  The
                length restriction is required to allow the media name
                to be displayed on the device's control panel.  The
                device POS must state the maximum number of characters
                allowed.  If the device also has a limitation on what
                characters in a character set can be used (e.g. only
                uppercase characters allowed), the POS should also state
                character restrictions.
                Additional information:
                 The maximum supported string length is 9 characters.  If
                the user entered string is too long, the device will store
                the first 9 characters and will return the
                <noError> status.  
                The characters must be in the range 20H to 7FH except 5C
                cannot be used. The default symbol set is Roman-8 for
                English; additional legal symbol sets are ISOLatin5,
                ISOLatin2 and Windows31J. Setting this object with characters
                outside of the range or of an illegal symbol set will cause an
                error status of <badValue> to be returned."
::= { media1 2 }
               
               
media1-page-count OBJECT-TYPE
    SYNTAX  INTEGER
    ACCESS  read-only
    STATUS  optional
    DESCRIPTION
                "Number of sheets of media 1 that have been printed.  The
                device POS should state whether this value is lost
                across a power cycle or kept in NVRAM.
                Additional information:
                For The LJ Series 4000 this page count is saved in NVRAM after every 10 
                pages. The maximum value is 4,294,967,295 which will never be reached in 
                normal operation.  
                The page count is incremented when a sheet of media is pulled from an input 
                tray. A duplex printed sheet will cause this counter to be incremented by 
                one."
::= { media1 3 }
               
               
media1-engine-media-mode OBJECT-TYPE
    SYNTAX  INTEGER
    ACCESS  read-write
    STATUS  optional
    DESCRIPTION
                "The engine processing characteristics that are to be
                applied to this media. The processing characteristics
                are device specific.
                Additional information:
                The engine processing characteristics that are to
                be applied to this media type. Currently, 'engine
                processing characteristics' denotes changes to
                fusing temperature and/or transfer roller voltage."
::= { media1 4 }
               
               
media2-name OBJECT-TYPE
    SYNTAX  DisplayString (SIZE(1..24))
    ACCESS  read-only
    STATUS  optional
    DESCRIPTION
                "Media 2 name.
                Additional information:
                See MEDIA1-NAME."
::= { media2 1 }
               
               
media2-short-name OBJECT-TYPE
    SYNTAX  DisplayString (SIZE(1..9))
    ACCESS  read-only
    STATUS  optional
    DESCRIPTION
                "Length restricted version of the media name 2.  See
                MEDIA1-SHORT-NAME for details.
                Additional information:
                See MEDIA1-SHORT-NAME."
::= { media2 2 }
               
               
media2-page-count OBJECT-TYPE
    SYNTAX  INTEGER
    ACCESS  read-only
    STATUS  optional
    DESCRIPTION
                "Number of sheets of media 2 that have been printed.  See
                MEDIA1-PAGE-COUNT for details.
                Additional information:
                See MEDIA1-PAGE-COUNT."
::= { media2 3 }
               
               
media2-engine-media-mode OBJECT-TYPE
    SYNTAX  INTEGER
    ACCESS  read-write
    STATUS  optional
    DESCRIPTION
                "The engine processing characteristics that are to be
                applied to this media. The processing characteristics
                are device specific.
                Additional information:
                See the description for MEDIA1-ENGINE-MEDIA-MODE."
::= { media2 4 }
               
               
media3-name OBJECT-TYPE
    SYNTAX  DisplayString (SIZE(1..24))
    ACCESS  read-only
    STATUS  optional
    DESCRIPTION
                "Media 3 name.
                Additional information:
                See MEDIA1-NAME."
::= { media3 1 }
               
               
media3-short-name OBJECT-TYPE
    SYNTAX  DisplayString (SIZE(1..9))
    ACCESS  read-only
    STATUS  optional
    DESCRIPTION
                "Length restricted version of the media name 3.  See
                MEDIA1-SHORT-NAME for details.
                Additional information:
                See MEDIA1-SHORT-NAME."
::= { media3 2 }
               
               
media3-page-count OBJECT-TYPE
    SYNTAX  INTEGER
    ACCESS  read-only
    STATUS  optional
    DESCRIPTION
                "Number of sheets of media 3 that have been printed.  See
                MEDIA1-PAGE-COUNT for details.
                Additional information:
                See MEDIA1-PAGE-COUNT."
::= { media3 3 }
               
               
media3-engine-media-mode OBJECT-TYPE
    SYNTAX  INTEGER
    ACCESS  read-write
    STATUS  optional
    DESCRIPTION
                "The engine processing characteristics that are to be
                applied to this media. The processing characteristics
                are device specific.
                Additional information:
                See the description for MEDIA1-ENGINE-MEDIA-MODE."
::= { media3 4 }
               
               
media4-name OBJECT-TYPE
    SYNTAX  DisplayString (SIZE(1..24))
    ACCESS  read-only
    STATUS  optional
    DESCRIPTION
                "Media 4 name.
                Additional information:
                See MEDIA1-NAME."
::= { media4 1 }
               
               
media4-short-name OBJECT-TYPE
    SYNTAX  DisplayString (SIZE(1..9))
    ACCESS  read-only
    STATUS  optional
    DESCRIPTION
                "Length restricted version of the media name 4.  See
                MEDIA1-SHORT-NAME for details.
                Additional information:
                See MEDIA1-SHORT-NAME."
::= { media4 2 }
               
               
media4-page-count OBJECT-TYPE
    SYNTAX  INTEGER
    ACCESS  read-only
    STATUS  optional
    DESCRIPTION
                "Number of sheets of media 4 that have been printed.  See
                MEDIA1-PAGE-COUNT for details.
                Additional information:
                See MEDIA1-PAGE-COUNT."
::= { media4 3 }
               
               
media5-name OBJECT-TYPE
    SYNTAX  DisplayString (SIZE(1..24))
    ACCESS  read-only
    STATUS  optional
    DESCRIPTION
                "Media 5 name.
                Additional information:
                See MEDIA1-NAME."
::= { media5 1 }
               
               
media5-short-name OBJECT-TYPE
    SYNTAX  DisplayString (SIZE(1..9))
    ACCESS  read-only
    STATUS  optional
    DESCRIPTION
                "Length restricted version of the media name 5.  See
                MEDIA1-SHORT-NAME for details.
                Additional information:
                See MEDIA1-SHORT-NAME."
::= { media5 2 }
               
               
media5-page-count OBJECT-TYPE
    SYNTAX  INTEGER
    ACCESS  read-only
    STATUS  optional
    DESCRIPTION
                "Number of sheets of media 5 that have been printed.  See
                MEDIA1-PAGE-COUNT for details.
                Additional information:
                See MEDIA1-PAGE-COUNT."
::= { media5 3 }
               
               
media5-engine-media-mode OBJECT-TYPE
    SYNTAX  INTEGER
    ACCESS  read-write
    STATUS  optional
    DESCRIPTION
                "The engine processing characteristics that are to be
                applied to this media. The processing characteristics
                are device specific.
                Additional information:
                See the description for MEDIA1-ENGINE-MEDIA-MODE."
::= { media5 4 }
               
               
media6-name OBJECT-TYPE
    SYNTAX  DisplayString (SIZE(1..24))
    ACCESS  read-only
    STATUS  optional
    DESCRIPTION
                "Media 6 name.
                Additional information:
                See MEDIA1-NAME."
::= { media6 1 }
               
               
media6-short-name OBJECT-TYPE
    SYNTAX  DisplayString (SIZE(1..9))
    ACCESS  read-only
    STATUS  optional
    DESCRIPTION
                "Length restricted version of the media name 6.  See
                MEDIA1-SHORT-NAME for details.
                Additional information:
                See MEDIA1-SHORT-NAME."
::= { media6 2 }
               
               
media6-page-count OBJECT-TYPE
    SYNTAX  INTEGER
    ACCESS  read-only
    STATUS  optional
    DESCRIPTION
                "Number of sheets of media 6 that have been printed.  See
                MEDIA1-PAGE-COUNT for details.
                Additional information:
                See MEDIA1-PAGE-COUNT."
::= { media6 3 }
               
               
media6-engine-media-mode OBJECT-TYPE
    SYNTAX  INTEGER
    ACCESS  read-write
    STATUS  optional
    DESCRIPTION
                "The engine processing characteristics that are to be
                applied to this media. The processing characteristics
                are device specific.
                Additional information:
                See the description for MEDIA1-ENGINE-MEDIA-MODE."
::= { media6 4 }
               
               
media7-name OBJECT-TYPE
    SYNTAX  DisplayString (SIZE(1..24))
    ACCESS  read-only
    STATUS  optional
    DESCRIPTION
                "Media 7 name.
                Additional information:
                See MEDIA1-NAME."
::= { media7 1 }
               
               
media7-short-name OBJECT-TYPE
    SYNTAX  DisplayString (SIZE(1..9))
    ACCESS  read-only
    STATUS  optional
    DESCRIPTION
                "Length restricted version of the media name 7.  See
                MEDIA1-SHORT-NAME for details.
                Additional information:
                See MEDIA1-SHORT-NAME."
::= { media7 2 }
               
               
media7-page-count OBJECT-TYPE
    SYNTAX  INTEGER
    ACCESS  read-only
    STATUS  optional
    DESCRIPTION
                "Number of sheets of media 7 that have been printed.  See
                MEDIA1-PAGE-COUNT for details.
                Additional information:
                See MEDIA1-PAGE-COUNT."
::= { media7 3 }
               
               
media7-engine-media-mode OBJECT-TYPE
    SYNTAX  INTEGER
    ACCESS  read-write
    STATUS  optional
    DESCRIPTION
                "The engine processing characteristics that are to be
                applied to this media. The processing characteristics
                are device specific.
                Additional information:
                See the description for MEDIA1-ENGINE-MEDIA-MODE."
::= { media7 4 }
               
               
media8-name OBJECT-TYPE
    SYNTAX  DisplayString (SIZE(1..24))
    ACCESS  read-only
    STATUS  optional
    DESCRIPTION
                "Media 8 name.
                Additional information:
                See MEDIA1-NAME."
::= { media8 1 }
               
               
media8-short-name OBJECT-TYPE
    SYNTAX  DisplayString (SIZE(1..9))
    ACCESS  read-only
    STATUS  optional
    DESCRIPTION
                "Length restricted version of the media name 8.  See
                MEDIA1-SHORT-NAME for details.
                Additional information:
                See MEDIA1-SHORT-NAME."
::= { media8 2 }
               
               
media8-page-count OBJECT-TYPE
    SYNTAX  INTEGER
    ACCESS  read-only
    STATUS  optional
    DESCRIPTION
                "Number of sheets of media 8 that have been printed.  See
                MEDIA1-PAGE-COUNT for details.
                Additional information:
                See MEDIA1-PAGE-COUNT."
::= { media8 3 }
               
               
media8-engine-media-mode OBJECT-TYPE
    SYNTAX  INTEGER
    ACCESS  read-write
    STATUS  optional
    DESCRIPTION
                "The engine processing characteristics that are to be
                applied to this media. The processing characteristics
                are device specific.
                Additional information:
                See the description for MEDIA1-ENGINE-MEDIA-MODE."
::= { media8 4 }
               
               
media9-name OBJECT-TYPE
    SYNTAX  DisplayString (SIZE(1..24))
    ACCESS  read-only
    STATUS  optional
    DESCRIPTION
                "Media 9 name.
                Additional information:
                See MEDIA1-NAME."
::= { media9 1 }
               
               
media9-short-name OBJECT-TYPE
    SYNTAX  DisplayString (SIZE(1..9))
    ACCESS  read-only
    STATUS  optional
    DESCRIPTION
                "Length restricted version of the media name 9.  See
                MEDIA1-SHORT-NAME for details.
                Additional information:
                See MEDIA1-SHORT-NAME."
::= { media9 2 }
               
               
media9-page-count OBJECT-TYPE
    SYNTAX  INTEGER
    ACCESS  read-only
    STATUS  optional
    DESCRIPTION
                "Number of sheets of media 9 that have been printed.  See
                MEDIA1-PAGE-COUNT for details.
                Additional information:
                See MEDIA1-PAGE-COUNT."
::= { media9 3 }
               
               
media9-engine-media-mode OBJECT-TYPE
    SYNTAX  INTEGER
    ACCESS  read-write
    STATUS  optional
    DESCRIPTION
                "The engine processing characteristics that are to be
                applied to this media. The processing characteristics
                are device specific.
                Additional information:
                See the description for MEDIA1-ENGINE-MEDIA-MODE."
::= { media9 4 }
               
               
media10-name OBJECT-TYPE
    SYNTAX  DisplayString (SIZE(1..24))
    ACCESS  read-only
    STATUS  optional
    DESCRIPTION
                "Media 10 name.
                Additional information:
                See MEDIA1-NAME."
::= { media10 1 }
               
               
media10-short-name OBJECT-TYPE
    SYNTAX  DisplayString (SIZE(1..9))
    ACCESS  read-only
    STATUS  optional
    DESCRIPTION
                "Length restricted version of the media name 10.  See
                MEDIA1-SHORT-NAME for details.
                Additional information:
                See MEDIA1-SHORT-NAME."
::= { media10 2 }
               
               
media10-page-count OBJECT-TYPE
    SYNTAX  INTEGER
    ACCESS  read-only
    STATUS  optional
    DESCRIPTION
                "Number of sheets of media 10 that have been printed.
                See MEDIA1-PAGE-COUNT for details.
                Additional information:
                See MEDIA1-PAGE-COUNT."
::= { media10 3 }
               
               
media10-engine-media-mode OBJECT-TYPE
    SYNTAX  INTEGER
    ACCESS  read-write
    STATUS  optional
    DESCRIPTION
                "The engine processing characteristics that are to be
                applied to this media. The processing characteristics
                are device specific.
                Additional information:
                See the description for MEDIA1-ENGINE-MEDIA-MODE."
::= { media10 4 }
               
               
media11-name OBJECT-TYPE
    SYNTAX  DisplayString (SIZE(1..24))
    ACCESS  read-only
    STATUS  optional
    DESCRIPTION
                "Media 11 name.
                Additional information:
                See MEDIA1-NAME."
::= { media11 1 }
               
               
media11-short-name OBJECT-TYPE
    SYNTAX  DisplayString (SIZE(1..9))
    ACCESS  read-only
    STATUS  optional
    DESCRIPTION
                "Length restricted version of the media name 11.  See
                MEDIA1-SHORT-NAME for details.
                Additional information:
                See MEDIA1-SHORT-NAME."
::= { media11 2 }
               
               
media11-page-count OBJECT-TYPE
    SYNTAX  INTEGER
    ACCESS  read-only
    STATUS  optional
    DESCRIPTION
                "Number of sheets of media 11 that have been printed.
                See MEDIA1-PAGE-COUNT for details.
                Additional information:
                See MEDIA1-PAGE-COUNT."
::= { media11 3 }
               
               
media11-engine-media-mode OBJECT-TYPE
    SYNTAX  INTEGER
    ACCESS  read-write
    STATUS  optional
    DESCRIPTION
                "The engine processing characteristics that are to be
                applied to this media. The processing characteristics
                are device specific.
                Additional information:
                See the description for MEDIA1-ENGINE-MEDIA-MODE."
::= { media11 4 }
               
               
media13-name OBJECT-TYPE
    SYNTAX  DisplayString (SIZE(1..24))
    ACCESS  read-write
    STATUS  optional
    DESCRIPTION
                "Media 13 name.
                Additional information:
                The maximum supported string length is 24
                bytes.  If the user entered string is too long,
                the device will store the first 24 bytes and
                return the <noError> status.
                See CAUTION statement under Product Specific Use."
::= { media13 1 }
               
               
media13-short-name OBJECT-TYPE
    SYNTAX  DisplayString (SIZE(1..9))
    ACCESS  read-write
    STATUS  optional
    DESCRIPTION
                "Length restricted version of the media name 13.  See
                MEDIA1-SHORT-NAME for details.
                Additional information:
                 The maximum supported string length is 9 characters.  If
                the user entered string is too long, the device will store
                the first 9 characters and will return the
                <noError> status.  
                The characters must be in the range 20H to 7FH except 5C
                cannot be used. The default symbol set is Roman-8 for
                English; additional legal symbol sets are ISOLatin5,
                ISOLatin2 and Windows31J. Setting this object with characters
                outside of the range or of an illegal symbol set will cause an
                error status of <badValue> to be returned."
::= { media13 2 }
               
               
media13-page-count OBJECT-TYPE
    SYNTAX  INTEGER
    ACCESS  read-only
    STATUS  optional
    DESCRIPTION
                "Number of sheets of media 13 that have been printed.
                See MEDIA1-PAGE-COUNT for details.
                Additional information:
                See MEDIA1-PAGE-COUNT."
::= { media13 3 }
               
               
media13-engine-media-mode OBJECT-TYPE
    SYNTAX  INTEGER
    ACCESS  read-write
    STATUS  optional
    DESCRIPTION
                "The engine processing characteristics that are to be
                applied to this media. The processing characteristics
                are device specific.
                Additional information:
                See the description for MEDIA1-ENGINE-MEDIA-MODE."
::= { media13 4 }
               
               
media14-name OBJECT-TYPE
    SYNTAX  DisplayString (SIZE(1..24))
    ACCESS  read-write
    STATUS  optional
    DESCRIPTION
                "Media 14 name.
                Additional information:
                See MEDIA13-NAME."
::= { media14 1 }
               
               
media14-short-name OBJECT-TYPE
    SYNTAX  DisplayString (SIZE(1..9))
    ACCESS  read-write
    STATUS  optional
    DESCRIPTION
                "Length restricted version of the media name 14.  See
                MEDIA1-SHORT-NAME for details.
                Additional information:
                See MEDIA13-SHORT-NAME."
::= { media14 2 }
               
               
media14-page-count OBJECT-TYPE
    SYNTAX  INTEGER
    ACCESS  read-only
    STATUS  optional
    DESCRIPTION
                "Number of sheets of media 14 that have been printed.
                See MEDIA1-PAGE-COUNT for details.
                Additional information:
                See MEDIA13-PAGE-COUNT."
::= { media14 3 }
               
               
media14-engine-media-mode OBJECT-TYPE
    SYNTAX  INTEGER
    ACCESS  read-write
    STATUS  optional
    DESCRIPTION
                "The engine processing characteristics that are to be
                applied to this media. The processing characteristics
                are device specific.
                Additional information:
                See the description for MEDIA1-ENGINE-MEDIA-MODE."
::= { media14 4 }
               
               
media15-name OBJECT-TYPE
    SYNTAX  DisplayString (SIZE(1..24))
    ACCESS  read-write
    STATUS  optional
    DESCRIPTION
                "Media 15 name.
                Additional information:
                See MEDIA13-NAME."
::= { media15 1 }
               
               
media15-short-name OBJECT-TYPE
    SYNTAX  DisplayString (SIZE(1..9))
    ACCESS  read-write
    STATUS  optional
    DESCRIPTION
                "Length restricted version of the media name 15.  See
                MEDIA1-SHORT-NAME for details.
                Additional information:
                See MEDIA13-SHORT-NAME."
::= { media15 2 }
               
               
media15-page-count OBJECT-TYPE
    SYNTAX  INTEGER
    ACCESS  read-only
    STATUS  optional
    DESCRIPTION
                "Number of sheets of media 15 that have been printed.
                See MEDIA1-PAGE-COUNT for details.
                Additional information:
                See MEDIA13-PAGE-COUNT."
::= { media15 3 }
               
               
media15-engine-media-mode OBJECT-TYPE
    SYNTAX  INTEGER
    ACCESS  read-write
    STATUS  optional
    DESCRIPTION
                "The engine processing characteristics that are to be
                applied to this media. The processing characteristics
                are device specific.
                Additional information:
                See the description for MEDIA1-ENGINE-MEDIA-MODE."
::= { media15 4 }
               
               
media16-name OBJECT-TYPE
    SYNTAX  DisplayString (SIZE(1..24))
    ACCESS  read-write
    STATUS  optional
    DESCRIPTION
                "Media 16 name.
                Additional information:
                See MEDIA13-NAME."
::= { media16 1 }
               
               
media16-short-name OBJECT-TYPE
    SYNTAX  DisplayString (SIZE(1..9))
    ACCESS  read-write
    STATUS  optional
    DESCRIPTION
                "Length restricted version of the media name 16.  See
                MEDIA1-SHORT-NAME for details.
                Additional information:
                See MEDIA13-SHORT-NAME."
::= { media16 2 }
               
               
media16-page-count OBJECT-TYPE
    SYNTAX  INTEGER
    ACCESS  read-only
    STATUS  optional
    DESCRIPTION
                "Number of sheets of media 16 that have been printed.
                See MEDIA1-PAGE-COUNT for details.
                Additional information:
                See MEDIA13-PAGE-COUNT."
::= { media16 3 }
               
               
media16-engine-media-mode OBJECT-TYPE
    SYNTAX  INTEGER
    ACCESS  read-write
    STATUS  optional
    DESCRIPTION
                "The engine processing characteristics that are to be
                applied to this media. The processing characteristics
                are device specific.
                Additional information:
                See the description for MEDIA1-ENGINE-MEDIA-MODE."
::= { media16 4 }
               
               
media17-name OBJECT-TYPE
    SYNTAX  DisplayString (SIZE(1..24))
    ACCESS  read-write
    STATUS  optional
    DESCRIPTION
                "Media 17 name.
                Additional information:
                See MEDIA13-NAME."
::= { media17 1 }
               
               
media17-short-name OBJECT-TYPE
    SYNTAX  DisplayString (SIZE(1..9))
    ACCESS  read-write
    STATUS  optional
    DESCRIPTION
                "Length restricted version of the media name 17.  See
                MEDIA1-SHORT-NAME for details.
                Additional information:
                See MEDIA13-SHORT-NAME."
::= { media17 2 }
               
               
media17-page-count OBJECT-TYPE
    SYNTAX  INTEGER
    ACCESS  read-only
    STATUS  optional
    DESCRIPTION
                "Number of sheets of media 17 that have been printed.
                See MEDIA1-PAGE-COUNT for details.
                Additional information:
                See MEDIA13-PAGE-COUNT."
::= { media17 3 }
               
               
media17-engine-media-mode OBJECT-TYPE
    SYNTAX  INTEGER
    ACCESS  read-write
    STATUS  optional
    DESCRIPTION
                "The engine processing characteristics that are to be
                applied to this media. The processing characteristics
                are device specific.
                Additional information:
                See the description for MEDIA1-ENGINE-MEDIA-MODE."
::= { media17 4 }
               
               
prtinputdefaultindex OBJECT-TYPE
    SYNTAX  INTEGER
    ACCESS  read-only
    STATUS  optional
    DESCRIPTION
                "The value of prtInputIndex corresponding to the default input
        sub-unit: that is, this object selects the default source of
        input media. 
   This value shall be -1 if there is no default input subunit specified
   for the printer as a whole.  In this case, the actual default
   input subunit may be specified by means outside the scope of this
   MIB, such as by each interpreter in a printer with multiple
   interpreters.
   Refer to Internet Draft Printer MIB, expiring Sept. 1997 for more details.
                Additional information:
                The default input tray is determined by the printer
                based on DEFAULT-MEDIA-SIZE and DEFAULT-MEDIA-NAME, and whether or
                not optional trays are installed.
                If Tray 1 is set in FIRST mode then the size of paper loaded in
                Tray 1 is assumed to be the requested size. In this case, the printer will
                pick from Tray 1 without regard to the requested size unless the
                print job's paper size, paper type and tray designations exactly
                match the configuration of another tray; in that case, the requested
                tray will be picked."
::= { prtGeneralEntry 6 }
               
               
prtmarkerdefaultindex OBJECT-TYPE
    SYNTAX  INTEGER(1..65535)
    ACCESS  read-only
    STATUS  optional
    DESCRIPTION
                "The value of prtMarkerIndex corresponding to the
        default marker sub-unit; that is, this object selects the
        default marker.
	Refer to Internet Draft Printer MIB, expiring Sept. 1997 for more details.
                Additional information:
                The LJ Series 4000 only has one marker subunit."
::= { prtGeneralEntry 8 }
               
               
prtmediapathdefaultindex OBJECT-TYPE
    SYNTAX  INTEGER(1..3)
    ACCESS  read-write
    STATUS  optional
    DESCRIPTION
                "The value of prtMediaPathIndex corresponding to
        the default media path; that is, the selection of the
        default media path.
	Refer to Internet Draft Printer MIB, expiring Sept. 1997 for more details.
                Additional information:
                If the duplex unit is not installed, the only valid
                value for this object is 1; with duplex unit installed, 1-3 values are 
                valid.  1 is simplex, 2 is LongEdgeBindingDuplex, and 3 is ShortEdgeBindingDuplex.  
                If the printer is not idle, the new value of this object may not take effect
                until a job boundary is reached.  If a get is done on this object before the
                job boundary is reached, the value last set will be returned."
::= { prtGeneralEntry 9 }
               
               
prtcoverdescription OBJECT-TYPE
    SYNTAX  OCTET STRING (SIZE(0..255))
    ACCESS  read-only
    STATUS  optional
    DESCRIPTION
                "The manufacturer provided cover sub-mechanism  name in the
        localization specified by prtGeneralCurrentLocalization.
	Refer to Internet Draft Printer MIB, expiring Sept. 1997 for more details."
::= { prtCoverEntry 2 }
               
               
prtcoverstatus OBJECT-TYPE
    SYNTAX  INTEGER {
		   ePdoorOpen(3),
		   ePdoorClosed(4)
		   }
    ACCESS  read-only
    STATUS  optional
    DESCRIPTION
                "The status of this cover sub-unit.
	Refer to Internet Draft Printer MIB, expiring Sept. 1997 for more details."
::= { prtCoverEntry 3 }
               
               
prtmarkermarktech OBJECT-TYPE
    SYNTAX  INTEGER {
		   ePother(1),
		   ePunknown(2),
		   ePelectrophotographicLED(3),
		   ePelectrophotographicLaser(4),
		   ePelectrophotographicOther(5),
		   ePimpactMovingHeadDotMatrix9pin(6),
		   ePimpactMovingHeadDotMatrix24pin(7),
		   ePimpactMovingHeadDotMatrixOther(8),
		   ePimpactMovingHeadFullyFormed(9),
		   ePimpactBand(10),
		   ePimpactOther(11),
		   ePinkjetAqueous(12),
		   ePinkjetSolid(13),
		   ePinkjetOther(14),
		   ePpen(15),
		   ePthermalTransfer(16),
		   ePthermalSensitive(17),
		   ePthermalDiffusion(18),
		   ePthermalOther(19),
		   ePelectroerosion(20),
		   ePelectrostatic(21),
		   ePphotographicMicrofiche(22),
		   ePphotographicImagesetter(23),
		   ePphotographicOther(24),
		   ePionDeposition(25),
		   ePeBeam(26),
		   ePtypesetter(27)
		   }
    ACCESS  read-only
    STATUS  optional
    DESCRIPTION
                "The type of marking technology used for this marking sub-unit.
	Refer to Internet Draft Printer MIB, expiring Sept. 1997 for more details.
                Additional information:
                ePelectrophotographicLaser is the only value that applies
                for The LJ Series 4000, and this is the value that will
                always be returned for this object."
::= { prtMarkerEntry 2 }
               
               
prtmarkercounterunit OBJECT-TYPE
    SYNTAX  INTEGER {
		   ePtenThousandthsOfInches(3),
		   ePmicrometers(4),
		   ePcharacters(5),
		   ePlines(6),
		   ePimpressions(7),
		   ePsheets(8),
		   ePdotRow(9),
		   ePhours(11),
		   ePfeet(16),
		   ePmeters(17)
		   }
    ACCESS  read-only
    STATUS  optional
    DESCRIPTION
                "The unit that will be used by the printer when reporting
        counter values for this marking sub-unit.  The
        time units of measure are provided for a device like a
        strip recorder that does not or cannot track the physical
        dimensions of the media and does not use characters,
        lines or sheets.
	Refer to Internet Draft Printer MIB, expiring Sept. 1997 for more details.
                Additional information:
                Since The LJ Series 4000 keeps track of pages printed, the
                counter unit will be defined as ePimpressions which would be 
                like saying pages printed."
::= { prtMarkerEntry 3 }
               
               
prtmarkerlifecount OBJECT-TYPE
    SYNTAX  INTEGER
    ACCESS  read-only
    STATUS  optional
    DESCRIPTION
                "The count of the number of units of measure counted during
        the life of printer using units of measure as specified by
        prtMarkerCounterUnit.
	Refer to Internet Draft Printer MIB, expiring Sept. 1997 for more details.
                Additional information:
                The total engine page count is kept in NVRAM however the NVRAM 
                value is only updated every 10 impressions.  
                NOTE: The value returned by this OID will be incremented every page but
                if power is lost between NVRAM updates, up to 9 impressions of the page
                count may be lost.  The counter will be reset to zero after 999999 pages.  
                The page count is incremented when a sheet of media is pulled from an input
                tray. A duplex printed sheet will cause this counter to be incremented by
                two."
::= { prtMarkerEntry 4 }
               
               
prtmarkerpoweroncount OBJECT-TYPE
    SYNTAX  INTEGER
    ACCESS  read-only
    STATUS  optional
    DESCRIPTION
                "The count of the number of units of measure counted since the
        equipment was most recently powered on using units of measure as
        specified by prtMarkerCounterUnit.
	Refer to Internet Draft Printer MIB, expiring Sept. 1997 for more details."
::= { prtMarkerEntry 5 }
               
               
prtmarkerprocesscolorants OBJECT-TYPE
    SYNTAX  INTEGER(0..65535)
    ACCESS  read-only
    STATUS  optional
    DESCRIPTION
                "The number of process colors supported by this marker.  A
        process color of 1 implies monochrome.  The value of this
        object and prtMarkerSpotColorants cannot both be 0.  The value of
        prtMarkerProcessColorants must be 0 or greater.
	Refer to Internet Draft Printer MIB, expiring Sept. 1997 for more details."
::= { prtMarkerEntry 6 }
               
               
prtmarkerspotcolorants OBJECT-TYPE
    SYNTAX  INTEGER(0..65535)
    ACCESS  read-only
    STATUS  optional
    DESCRIPTION
                "The number of spot colors supported by this marker.  The
        value of this object and prtMarkerProcessColorants cannot
        both be 0.  Must be 0 or greater.
	Refer to Internet Draft Printer MIB, expiring Sept. 1997 for more details."
::= { prtMarkerEntry 7 }
               
               
prtmarkeraddressabilityunit OBJECT-TYPE
    SYNTAX  INTEGER {
		   ePtenThousandthsOfInches(3),
		   ePmicrometers(4)
		   }
    ACCESS  read-only
    STATUS  optional
    DESCRIPTION
                "The unit of measure of distances, as applied to the marker's
         resolution.
	 Refer to Internet Draft Printer MIB, expiring Sept. 1997 for more details.
                Additional information:
                This will always be ePtenThousandthsOfInches, no matter
                what COLD-RESET-MEDIA-SIZE is because we are talking about
                resolution and toner addressability, which is always dpi."
::= { prtMarkerEntry 8 }
               
               
prtmarkernorthmargin OBJECT-TYPE
    SYNTAX  INTEGER
    ACCESS  read-only
    STATUS  optional
    DESCRIPTION
                "The margin, in units identified by prtMarkerAddressabilityUnit,
        from the leading edge of the medium as the medium flows
        through the marking engine with the side to be imaged
        facing the observer. The leading edge is the North edge
        and the other edges are defined by the normal compass
        layout of  directions with the compass facing the
        observer.  Printing within the area bounded by all four
        margins is guaranteed for all interpreters.   The value
        (-2) means unknown.
	Refer to Internet Draft Printer MIB, expiring Sept. 1997 for more details."
::= { prtMarkerEntry 11 }
               
               
prtmarkersouthmargin OBJECT-TYPE
    SYNTAX  INTEGER
    ACCESS  read-only
    STATUS  optional
    DESCRIPTION
                "The margin from the South edge  (see prtMarkerNorthMargin)
        of the medium in units identified by
        prtMarkerAddressabilityUnit.  Printing within the area bounded by
        all four margins  is guaranteed for all interpreters.
        The value (-2) means unknown.
	Refer to Internet Draft Printer MIB, expiring Sept. 1997 for more details."
::= { prtMarkerEntry 12 }
               
               
prtmarkerwestmargin OBJECT-TYPE
    SYNTAX  INTEGER
    ACCESS  read-only
    STATUS  optional
    DESCRIPTION
                "The margin from the West edge (see prtMarkerNorthMargin) of the
        medium in units identified by prtMarkerAddressabilityUnit.
        Printing within the area bounded by all four margins is
        guaranteed for all interpreters.   The value (-2) means
        unknown.
	Refer to Internet Draft Printer MIB, expiring Sept. 1997 for more details."
::= { prtMarkerEntry 13 }
               
               
prtmarkereastmargin OBJECT-TYPE
    SYNTAX  INTEGER
    ACCESS  read-only
    STATUS  optional
    DESCRIPTION
                "The margin from the East edge (see prtMarkerNorthMargin) of the
        medium in units identified by prtMarkerAddressabilityUnit.
        Printing within the area bounded by all four margins is
        guaranteed for all interpreters. The value (-2) means
        unknown.
	Refer to Internet Draft Printer MIB, expiring Sept. 1997 for more details."
::= { prtMarkerEntry 14 }
               
               
prtmarkerstatus OBJECT-TYPE
    SYNTAX  INTEGER
    ACCESS  read-only
    STATUS  optional
    DESCRIPTION
                "The current status of this marker sub-unit.
	Refer to Internet Draft Printer MIB, expiring Sept. 1997 for more details.
                Additional information:
                51 = No toner cart.  
                49 = Low toner and toner low = stop in config menu   
                14 = Low toner and toner low = continue in config menu  
                			     and paper is moving.  
                08 = Low toner and toner low = continue in config menu  
                			     and no paper is moving.  
                00 = OK. "
::= { prtMarkerEntry 15 }
               
               
prtmarkersuppliesmarkerindex OBJECT-TYPE
    SYNTAX  INTEGER(0..65535)
    ACCESS  read-only
    STATUS  optional
    DESCRIPTION
                "The value of prtMarkerIndex corresponding to the
        marking sub-unit with which this marker supply
        sub-unit is associated.
	Refer to Internet Draft Printer MIB, expiring Sept. 1997 for more details.
                Additional information:
                The LJ Series 4000 has just one marker supply, the toner 
                cartridge, so this value is always 1."
::= { prtMarkerSuppliesEntry 2 }
               
               
prtmarkersuppliescolorantindex OBJECT-TYPE
    SYNTAX  INTEGER(0..65535)
    ACCESS  read-only
    STATUS  optional
    DESCRIPTION
                "The value of prtMarkerColorantIndex
        corresponding to the colorant with which this
        marker supply sub-unit is associated.  This value
        shall be 0 if there is no colorant table.
	Refer to Internet Draft Printer MIB, expiring Sept. 1997 for more details."
::= { prtMarkerSuppliesEntry 3 }
               
               
prtmarkersuppliesclass OBJECT-TYPE
    SYNTAX  INTEGER {
		   ePother(1),
		   ePsupplyThatIsConsumed(3),
		   ePreceptacleThatIsFilled(4)
		   }
    ACCESS  read-only
    STATUS  optional
    DESCRIPTION
                "Indicates whether this supply entity represents a supply
        that is consumed or a receptacle that is filled.
	Refer to Internet Draft Printer MIB, expiring Sept. 1997 for more details.
                Additional information:
                ePsupplyThatIsConsumed is the only value that applies
                for The LJ Series 4000, and this is the value that will
                always be returned for this object."
::= { prtMarkerSuppliesEntry 4 }
               
               
prtmarkersuppliestype OBJECT-TYPE
    SYNTAX  INTEGER {
		   ePother(1),
		   ePunknown(2),
		   ePtoner(3),
		   ePwasteToner(4),
		   ePink(5),
		   ePinkCartridge(6),
		   ePinkRibbon(7),
		   ePwasteInk(8),
		   ePopc(9),
		   ePdeveloper(10),
		   ePfuserOil(11),
		   ePsolidWax(12),
		   ePribbonWax(13),
		   ePwasteWax(14),
		   ePfuser(15),
		   ePcoronaWire(16),
		   ePfuserOilWick(17),
		   ePcleanerUnit(18),
		   ePfuserCleaningPad(19),
		   ePtransferUnit(20),
		   ePtonerCartridge(21),
		   ePfuserOiler(22)
		   }
    ACCESS  read-only
    STATUS  optional
    DESCRIPTION
                "The type of this supply.
	Refer to Internet Draft Printer MIB, expiring Sept. 1997 for more details.
                Additional information:
                ePtoner is the only value that applies for The LJ Series 4000
                and this is the value that will always be
                returned for this object."
::= { prtMarkerSuppliesEntry 5 }
               
               
prtmarkersuppliessupplyunit OBJECT-TYPE
    SYNTAX  INTEGER {
		   ePtenThousandthsOfInches(3),
		   ePmicrometers(4),
		   ePimpressions(7),
		   ePsheets(8),
		   ePthousandthsOfOunces(12),
		   ePhours(11),
		   ePtenthsOfGrams(13),
		   ePhundrethsOfFluidOunces(14),
		   ePtenthsOfMilliliters(15),
		   ePfeet(16),
		   ePmeters(17)
		   }
    ACCESS  read-only
    STATUS  optional
    DESCRIPTION
                "Unit of measure of this marker supply container/receptacle.
	Refer to Internet Draft Printer MIB, expiring Sept. 1997 for more details.
                Additional information:
                ePtenthsOfGrams will always be returned for this object."
::= { prtMarkerSuppliesEntry 7 }
               
               
prtmarkersuppliesmaxcapacity OBJECT-TYPE
    SYNTAX  INTEGER
    ACCESS  read-only
    STATUS  optional
    DESCRIPTION
                "The maximum capacity of this supply container/receptacle
        expressed in prtMarkerSuppliesSupplyUnit. If this supply
        container/receptacle can reliably sense this value, the
        value is reported by the printer and is read-only;
        otherwise, the value may be written (by a Remote Control
        Panel or a Management Application). The value (-1) means
        other and specifically indicates that the sub-unit places
        no restrictions on this parameter. The value (-2) means
        unknown.
	Refer to Internet Draft Printer MIB, expiring Sept. 1997 for more details.
                Additional information:
                The LJ Series 4000 cannot sense how much toner is left, it just
                senses when the toner reaches a certain low level."
::= { prtMarkerSuppliesEntry 8 }
               
               
prtmarkersupplieslevel OBJECT-TYPE
    SYNTAX  INTEGER
    ACCESS  read-only
    STATUS  optional
    DESCRIPTION
                "The current level if this supply is a container; the
        remaining space if this supply is a receptacle. If this
        supply container/receptacle can reliably sense this
        value, the value is reported by the printer and is
        read-only; otherwise, the value may be written. The
        value (-1) means other and specifically indicates that
        the sub-unit places no restrictions on this parameter.
        The value (-2) means unknown.  A value of (-3) means that the
        printer knows that there is some supply/remaining space,
        respectively.
	Refer to Internet Draft Printer MIB, expiring Sept. 1997 for more details.
                Additional information:
                The LJ Series 4000 detects the toner level as being either
                above or below the 'LOW' sensor. Therefore, a value
                of -3 is returned when the level is above the 'LOW'
                sensor and a value of -2 is returned when the toner
                cartridge detects the 'LOW' condition."
::= { prtMarkerSuppliesEntry 9 }
               
               
prtmediapathmaxspeedprintunit OBJECT-TYPE
    SYNTAX  INTEGER {
		   ePtenThousandthsOfInchesPerHour(3),
		   ePmicrometersPerHour(4),
		   ePcharactersPerHour(5),
		   ePlinesPerHour(6),
		   ePimpressionsPerHour(7),
		   ePsheetsPerHour(8),
		   ePdotRowPerHour(9),
		   ePfeetPerHour(16),
		   ePmetersPerHour(17)
		   }
    ACCESS  read-only
    STATUS  optional
    DESCRIPTION
                "The unit of measure used in specifying the speed of all media
        paths in the printer.
	Refer to Internet Draft Printer MIB, expiring Sept. 1997 for more details.
                Additional information:
                ePimpressionsPerHour is the value that will
                always be returned for this object. (Print Speed is
                measured in pages-per-minute (impressions per minute),
                so ePimpressionsPerHour is a natural extension)."
::= { prtMediaPathEntry 2 }
               
               
prtmediapathmediasizeunit OBJECT-TYPE
    SYNTAX  INTEGER {
		   ePtenThousandthsOfInches(3),
		   ePmicrometers(4)
		   }
    ACCESS  read-only
    STATUS  optional
    DESCRIPTION
                "The units of measure of media size for use in calculating and
        relaying dimensional values for all media paths in the printer.
	Refer to Internet Draft Printer MIB, expiring Sept. 1997 for more details."
::= { prtMediaPathEntry 3 }
               
               
prtmediapathtype OBJECT-TYPE
    SYNTAX  INTEGER {
		   ePlongEdgeBindingDuplex(3),
		   ePshortEdgeBindingDuplex(4),
		   ePsimplex(5)
		   }
    ACCESS  read-only
    STATUS  optional
    DESCRIPTION
                "The type of the media path for this media path.
	Refer to Internet Draft Printer MIB, expiring Sept. 1997 for more details."
::= { prtMediaPathEntry 9 }
               
               
prtmediapathdescription OBJECT-TYPE
    SYNTAX  OCTET STRING (SIZE(0..255))
    ACCESS  read-only
    STATUS  optional
    DESCRIPTION
                "The manufacturer-provided description of this media path in
        the localization specified by prtGeneralCurrentLocalization.
	Refer to Internet Draft Printer MIB, expiring Sept. 1997 for more details."
::= { prtMediaPathEntry 10 }
               
               
prtmediapathstatus OBJECT-TYPE
    SYNTAX  INTEGER
    ACCESS  read-only
    STATUS  optional
    DESCRIPTION
                "The current status of this media path.
	Refer to Internet Draft Printer MIB, expiring Sept. 1997 for more details.
                Additional information:
                The default values assume the printer is idle."
::= { prtMediaPathEntry 11 }
               
               
collated-originals-support OBJECT-TYPE
    SYNTAX  OCTET STRING
    ACCESS  read-only
    STATUS  optional
    DESCRIPTION
                "Indicates that the printer can create multiple, collated
                'originals' of a job and shows the level of support for
                this capability.  
                  cCollatedOriginals - The printer can create multiple
                collated originals, or 'mopies'.  This is the base
                functionality required by the other collection items.  
                  cProofAndHold - The printer saves a copy of the job
                while printing the first mopy.  Later, this held job can
                be released and the rest of the mopies will print.  
                  cSecurityPrint - The printer spools the job and holds
                the job until the user releases the job by entering a
                password at the printer's control panel.  
                  cAutoHighlight - The printer prints  the job a number
                of times with a mail distribution list prepended to each
                job.  A different mailing address is highlighted on each
                mopy.  
                  cCollatedAtSpeed - The printer can create multiple
                collated copies where all copies after the original are
                printed at engine speed.
                Additional information:
                Indicates that the printer can create multiple, collated   
                originals of a job and shows the level of support for this  
                capability.    
                cCollatedOriginals - The printer can create multiple collated  
                originals, or mopies.  
                
                This is the base functionality required by the other   
                collection items.  None of them are supported by LaserJet 5Si Mopier.  
                Without disk, this object will not exist. This will be set at   
                boot-up initialization. If the disk fails, in any way, then   
                the disk error functionality will handle the situation.
                
                The value of this object will be:
                !cCollatedOriginals - Only FLASH installed
                cCollatedOriginals  - IDE is installed combined 
                with/without FLASH
                	       cCollatedOriginals  - RAMDISK is On combined with/without FLASH"
::= { status-system 42 }
               
               
file-system-memory OBJECT-TYPE
    SYNTAX  INTEGER
    ACCESS  read-only
    STATUS  optional
    DESCRIPTION
                "The amount of memory, in bytes, used by the file system
                to buffer file data.
                Additional information:
                Reports the amount of memory, in bytes,
                reserved for use by the file system.  Returns
                <noSuchName> status if attempting
                to access this object and there is no storage device
                is installed.  The values remain constant across reboots.
                	   Possible Values:
                	     FILE-SYSTEM-MAX-OPEN-FILES    32       512
                	       EIO DISK                   69916    198556    
                	       EIO DISK + 1 2MB Flash     88940    217580
                	       1 2MB Flash                33052    161692"
::= { settings-file-system 1 }
               
               
file-system-max-open-files OBJECT-TYPE
    SYNTAX  INTEGER(32..512)
    ACCESS  read-write
    STATUS  optional
    DESCRIPTION
                "The number of open files allowed at one time. Opening a
                file when the maximum number of files are currently open
                will fail.
                Additional information:
                Indicates the number of open files a
                personality (e.g. PCL or PostScript) is guaranteed to be
                able to open before the file system runs out of file handles.
                After writing this object, the printer
                must be rebooted (powercycled) before the change takes effect.
                This object supports any value between 32 - 512 inclusive.
                If a value Less then 32 then it snaps to 32 if greater then
                	   512 it snaps to 512.
                The factory default value is dependent on the amount of
                installed RAM.  The default value of 32 is when
                	   Memory <= 4MB, 128 is if the memory is > 4MB.
                Performing a cold reset sets this object 
                back to the factory default value.  Returns 
                <noSuchName>
                status if attempting to access this object and there
                is no storage device is installed."
::= { settings-file-system 2 }
               
               
file-system-statistic-read-open OBJECT-TYPE
    SYNTAX  INTEGER
    ACCESS  read-only
    STATUS  optional
    DESCRIPTION
                "The number of times the file system has received
                requests to open a file for reading.  Opening a file for
                both reading and writing will cause this value to
                change.  The POS should state if a power cycle causes
                the counter is be reset to zero.
                Additional information:
                Reset to the factory default value after
                a power cycle.  
                Returns <noSuchName>
                status if attempting to access this object and there
                is no storage device is installed.  This value is 
                	   increamented when a file is opened."
::= { status-file-system 1 }
               
               
file-system-statistic-write-open OBJECT-TYPE
    SYNTAX  INTEGER
    ACCESS  read-only
    STATUS  optional
    DESCRIPTION
                "The number of times the file system has received
                requests to open a file for writing.  Opening a file for
                both reading and writing will cause this value to
                change.  The POS should state if a power cycle causes
                the counter is be reset to zero.
                Additional information:
                Reset to the factory default value after
                a power cycle.  
                Returns <noSuchName>
                status if attempting to access this object and there
                is no storage device is installed.  This value is 
                	   increamented when a file is opened."
::= { status-file-system 2 }
               
               
file-system-statistic-successful OBJECT-TYPE
    SYNTAX  INTEGER
    ACCESS  read-only
    STATUS  optional
    DESCRIPTION
                "A counter indicating the number of file system requests
                that completed successfully.  The POS should state if a
                power cycle causes the counter is be reset to zero.
                Additional information:
                Reset to the factory default value after
                a power cycle.  
                Returns <noSuchName>
                status if attempting to access this object and there
                is no storage device is installed."
::= { status-file-system 3 }
               
               
file-system-statistic-unsuccessful OBJECT-TYPE
    SYNTAX  INTEGER
    ACCESS  read-only
    STATUS  optional
    DESCRIPTION
                "A counter indicating the number of file system requests
                that completed unsuccessfully.  The POS should state if
                a power cycle causes the counter is be reset to zero.
                Additional information:
                Reset to the factory default value after
                a power cycle.  
                Returns <noSuchName>
                status if attempting to access this object and there
                is no storage device is installed."
::= { status-file-system 4 }
               
               
file-system-statistic-current-memory-usage OBJECT-TYPE
    SYNTAX  INTEGER
    ACCESS  read-only
    STATUS  optional
    DESCRIPTION
                "A value indicating the number of bytes of RAM currently
                used by the file system firmware.
                Additional information:
                Reset to the factory default value after
                a power cycle.  
                Returns <noSuchName>
                status if attempting to access this object and there
                is no storage device is installed.  This will veri 
                	   depending on the number and size of Mass Storage
                	   devices installed."
::= { status-file-system 5 }
               
               
file-system-statistic-max-memory-usage OBJECT-TYPE
    SYNTAX  INTEGER
    ACCESS  read-only
    STATUS  optional
    DESCRIPTION
                "A value indicating the maximum number of bytes of RAM
                used by the file system firmware.  The POS should state
                if the value is reset to zero after a power cycle.
                Additional information:
                Reset to the factory default value after
                a power cycle.  
                Returns <noSuchName>
                status if attempting to access this object and there
                is no storage device is installed."
::= { status-file-system 6 }
               
               
file-system2-initialize-volume OBJECT-TYPE
    SYNTAX  INTEGER {
		   eInitializing(2)
		   }
    ACCESS  write-only
    STATUS  optional
    DESCRIPTION
                "Setting this object to eInitializing causes file system
                2 to be initialized.  Reading this object indicates if
                the file system is currently being initialized.
                Additional information:
                The hrDeviceIndex value for the mass storage
                device is the same value that is used to index into the
                FILE-SYSTEM sub-tree.  Since this product supports
                up to 3  mass storage device, and since the hrDeviceIndex
                for the mass storage devices will start at 2 if the mass
                	   storage device is installed, the FILE-SYSTEM2-INITIALIZE-VOLUME
                	   object will be the object that allows the mass storage device to be 
                initialized that is the 1st device."
::= { file-system2 6 }
               
               
file-system3-initialize-volume OBJECT-TYPE
    SYNTAX  INTEGER {
		   eInitializing(2)
		   }
    ACCESS  write-only
    STATUS  optional
    DESCRIPTION
                "Setting this object to eInitializing causes file system
                3 to be initialized.  Reading this object indicates if
                the file system is currently being initialized.
                Additional information:
                The hrDeviceIndex value for the mass storage
                device is the same value that is used to index into the
                FILE-SYSTEM sub-tree.  Since this product supports
                up to 3  mass storage device, and since the hrDeviceIndex
                for the mass storage devices will start at 2 if the mass
                	   storage device is installed, the FILE-SYSTEM3-INITIALIZE-VOLUME
                	   object will be the object that allows the mass storage device to be 
                initialized that is the 2nd device."
::= { file-system3 6 }
               
               
file-system4-initialize-volume OBJECT-TYPE
    SYNTAX  INTEGER {
		   eInitializing(2)
		   }
    ACCESS  write-only
    STATUS  optional
    DESCRIPTION
                "Setting this object to eInitializing causes file system
                4 to be initialized.  Reading this object indicates if
                the file system is currently being initialized.
                Additional information:
                The hrDeviceIndex value for the mass storage
                device is the same value that is used to index into the
                FILE-SYSTEM sub-tree.  Since this product supports
                up to 3  mass storage devices, and since the hrDeviceIndex
                for the mass storage devices will start at 2 if the mass
                	   storage device is installed, the FILE-SYSTEM4-INITIALIZE-VOLUME
                	   object will be the object that allows the mass storage device to be 
                initialized that is the 3rd device."
::= { file-system4 6 }
               
               
mass-storage-resource-change-counter OBJECT-TYPE
    SYNTAX  INTEGER
    ACCESS  read-only
    STATUS  optional
    DESCRIPTION
                "A counter which changes when a mass storage based
                resource has been added or deleted.
                Additional information:
                The value of this counter changes 
                each time the MASS-STORAGE-RESOURCE-CHANGED object
                is set to eTrue.  The value also changes when the 
                mass storage device is initialized.  However, the value does not
                change when a mass storage device is removed and a different
                mass storage device is installed.  Initializing all volumes sets 
                this object back to the factory default value.  A reboot sets
                	   this object back to the factory devalut value.
                Returns <noSuchName>
                status if attempting to access this object and there
                is no storage device is installed."
::= { mass-storage-resources 1 }
               
               
mass-storage-resource-changed OBJECT-TYPE
    SYNTAX  INTEGER {
		   eTrue(2)
		   }
    ACCESS  write-only
    STATUS  optional
    DESCRIPTION
                "Setting to eTrue causes MASS-STORAGE-RESOURCE-CHANGE-
                COUNTER to be incremented.
                Additional information:
                Returns <noSuchName>
                status if attempting to access this object and there
                is no storage device is installed."
::= { mass-storage-resources 2 }
               
               
hrstorageindex OBJECT-TYPE
    SYNTAX  INTEGER(1..2147483647)
    ACCESS  read-only
    STATUS  mandatory
    DESCRIPTION
                "A unique value for each logical storage area
              contained by the host.
              Refer to RFC 1514, Host Resources MIB, for more details.
                Additional information:
                Constant.  The index is assigned by the
                person controlling the printer object definition.
                The value of the hrFileSystemStorageIndex and the
                index of the prtStorageRefIndex use the value of
                this object's index.  The value of the object
                matches the value of the object's index.  Returns
                <noSuchName> status if attempting
                to perform a get on this OID with no mass storage device
                installed.  This first volume installed will be number 2, 
                	   followed by the second.  IDE will always be 2.  If ram disk
                	   and flash disk are installed then Flash disk will be 2 followed 
                	   by ram disk.  The Storage types are:
                		 IDE (EIO DISK), Flash Disk, Ram Disk"
::= { hrStorageEntry 1 }
               
               
hrstoragetype OBJECT-TYPE
    SYNTAX  OBJECT IDENTIFIER
    ACCESS  read-only
    STATUS  mandatory
    DESCRIPTION
                "The type of storage represented by this entry.
              Refer to RFC 1514, Host Resources MIB, for more details.
                Additional information:
                Constant.  Returns
                <noSuchName> status if attempting
                to perform a Get on this OID with no mass storage device
                installed.
               	      HRMhrStorageFixedDisk is 1.3.6.1.2.1.25.2.1.4"
::= { hrStorageEntry 2 }
               
               
hrstoragedescr OBJECT-TYPE
    SYNTAX  OCTET STRING
    ACCESS  read-only
    STATUS  mandatory
    DESCRIPTION
                "A description of the type and instance of the
              storage described by this entry.
              Refer to RFC 1514, Host Resources MIB, for more details.
                Additional information:
                This string indicates the location of the installed
                mass storage device.  The supported values are:  
                'Flash disk in DIMM slot 1'  
                'Flash disk in DIMM slot 2'  
                'Flash disk in DIMM slot 3'  
                	   'Disk in EIO 1'  
                	   'Disk in EIO 2'  
                	   'Disk in EIO 3'  
                	   'Static RAM disk using system memory'  
                Applications determine the location of the installed mass storage
                device by getting this object.  This string is not
                localized.  Returns <noSuchName>
                status if attempting to perform a Get on this OID
                with no mass storage device installed."
::= { hrStorageEntry 3 }
               
               
hrstorageallocationunits OBJECT-TYPE
    SYNTAX  INTEGER(1..2147483647)
    ACCESS  read-only
    STATUS  mandatory
    DESCRIPTION
                "The size, in bytes, of the data objects allocated
               from this pool.  If this entry is monitoring
               sectors, blocks, buffers, or packets, for example,
               this number will commonly be greater than one.
               Otherwise this number will typically be one.
               Refer to RFC 1514, Host Resources MIB, for more details.
                Additional information:
                Unit is one byte.
                Returns the value 1024 if the file system is 
                not initialized.  Returns <noSuchName>
                status if attempting to perform a Get on this OID
                with no mass storage device installed."
::= { hrStorageEntry 4 }
               
               
hrstoragesize OBJECT-TYPE
    SYNTAX  INTEGER(0..2147483647)
    ACCESS  read-only
    STATUS  mandatory
    DESCRIPTION
                "The size of the storage represented by this entry,
              in units of hrStorageAllocationUnits.
              Refer to RFC 1514, Host Resources MIB, for more details.
                Additional information:
                Total formatter RAM.
                Applications can determine the size of the 
                installed mass storage device by getting the 
                hrStorageAllocationUnits object and this object. The size
                of the mass storage device is these two returned values multiplied
                together.  Returns <noSuchName>
                status if attempting to perform a Get on this OID
                with no mass storage device installed."
::= { hrStorageEntry 5 }
               
               
hrdevicetype OBJECT-TYPE
    SYNTAX  OBJECT IDENTIFIER
    ACCESS  read-only
    STATUS  mandatory
    DESCRIPTION
                "An indication of the type of device.
              If this value is `hrDeviceProcessor { hrDeviceTypes
              3 }' then an entry exists in the hrProcessorTable
              which corresponds to this device.
              If this value is `hrDeviceNetwork { hrDeviceTypes 4
              }', then an entry exists in the hrNetworkTable
              which corresponds to this device.
              If this value is `hrDevicePrinter { hrDeviceTypes 5
              }', then an entry exists in the hrPrinterTable
              which corresponds to this device.
              If this value is `hrDeviceDiskStorage {
              hrDeviceTypes 6 }', then an entry exists in the
              hrDiskStorageTable which corresponds to this
              device.
              Refer to RFC 1514, Host Resources MIB, for more details.
                Additional information:
                Constant.  Applications should determine if
                a mass storage device is installed by getting this object.
                If the response is something other than HRMhrDeviceDiskStorage,
                the application knows this row in the hrDeviceTable does not
                refer to a mass storage object.  Due to restrictions placed on
                this object by the Host Resources Disk Table, the value of this
                object must be HRMhrDeviceDiskStorge.  Returns
                <noSuchName> status if attempting
                to perform a Get on this OID with no mass storage device
                installed. HRMhrDeviceDiskStorage is 1.3.6.1.2.1.25.3.1.6"
::= { hrDeviceEntry 2 }
               
               
hrdiskstorageaccess OBJECT-TYPE
    SYNTAX  INTEGER {
		   eHreadWrite(1),
		   eHreadOnly(2)
		   }
    ACCESS  read-write
    STATUS  mandatory
    DESCRIPTION
                "An indication if this long-term storage device is
              readable and writable or only readable.  This
              should reflect the media type, any write-protect
              mechanism, and any device configuration that
              affects the entire device.
              Refer to RFC 1514, Host Resources MIB, for more details.
                Additional information:
                This object can be set to write protect
                the mass storage device, even though the host resources MIB
                documents the object as read-only.  Applications wanting to
                know if the mass storage device is writable should get this 
                object.  Applications wanting to change the read/write access
                of the mass storage device should set this object.
                If this object is set to write-protect while a file is being
                written to the mass storage device, the write-protect takes effect
                immediately and the new file doesn't appear in the file system.
                Returns <noSuchName> status if attempting to
                perform a Get on this OID with no mass storage device installed."
::= { hrDiskStorageEntry 1 }
               
               
hrdiskstoragemedia OBJECT-TYPE
    SYNTAX  INTEGER {
		   eHother(1),
		   eHhardDisk(3),
		   eHramDisk(8)
		   }
    ACCESS  read-only
    STATUS  mandatory
    DESCRIPTION
                "An indication of the type of media used in this
              long-term storage device.
              Refer to RFC 1514, Host Resources MIB, for more details.
                Additional information:
                Constant.  Applications can determine if the
                installed mass storage device is a disk or is flash by
                getting this value.  
                		  Possible Values:
                		    EIO DISK returns   eHhardDisk
                		    Ram Disk returns   eHramDisk
                		    Flash Disk returns eHother
                	   Returns <noSuchName> status if attempting
                to perform a Get on this OID with no mass storage device
                installed."
::= { hrDiskStorageEntry 2 }
               
               
hrdiskstorageremoveble OBJECT-TYPE
    SYNTAX  INTEGER {
		   eHfalse(2)
		   }
    ACCESS  read-only
    STATUS  mandatory
    DESCRIPTION
                "Denotes whether or not the disk media may be
               removed from the drive.
               Refer to RFC 1514, Host Resources MIB, for more details.
                Additional information:
                Constant.  Returns
                <noSuchName> status if attempting
                to perform a Get on this OID with no mass storage device
                installed."
::= { hrDiskStorageEntry 3 }
               
               
hrdiskstoragecapacity OBJECT-TYPE
    SYNTAX  INTEGER
    ACCESS  read-only
    STATUS  mandatory
    DESCRIPTION
                "The total size for this long-term storage device.
              Refer to RFC 1514, Host Resources MIB, for more details.
                Additional information:
                The capacity is in Kbytes.  Returns
                <noSuchName> status if attempting
                to perform a Get on this OID with no mass storage device
                installed."
::= { hrDiskStorageEntry 4 }
               
               
hrpartitionindex OBJECT-TYPE
    SYNTAX  INTEGER(1..2147483647)
    ACCESS  read-only
    STATUS  mandatory
    DESCRIPTION
                "A unique value for each partition on this long-
              term storage device.  The value for each long-term
              storage device must remain constant at least from
              one re-initialization of the agent to the next re-
              initialization.
              Refer to RFC 1514, Host Resources MIB, for more details.
                Additional information:
                Constant.  The first and second index 
                indicates the hrDeviceIndex for this mass storage device.
                The value of this object is the same as
                the second index.  The printer only supports one
                partition per mass storage device.  Returns
                <noSuchName> status if attempting
                to perform a Get on this OID with no mass storage device
                installed."
::= { hrPartitionEntry 1 }
               
               
hrpartitionlabel OBJECT-TYPE
    SYNTAX  OCTET STRING (SIZE(0..11))
    ACCESS  read-write
    STATUS  mandatory
    DESCRIPTION
                "A textual description of this partition.
              Refer to RFC 1514, Host Resources MIB, for more details.
                Additional information:
                The MS-DOS volume label.  The volume
                label is writable.  Returns
                <noSuchName> status if attempting
                to perform a Get on this OID with no mass storage device installed.
                This object is settable and returns the empty 
                string if the mass storage device has not been initialized.  NOTE
                	   the RamDisk will lose this value after a PowerCycle."
::= { hrPartitionEntry 2 }
               
               
hrpartitionid OBJECT-TYPE
    SYNTAX  OCTET STRING
    ACCESS  read-only
    STATUS  mandatory
    DESCRIPTION
                "A descriptor which uniquely represents this
              partition to the responsible operating system.  On
              some systems, this might take on a binary
              representation.
              Refer to RFC 1514, Host Resources MIB, for more details.
                Additional information:
                Constant.  The value returned is the
                ASCII string version of the hrDeviceIndex for 
                this mass storage device.  Returns
                <noSuchName> status if attempting
                to perform a Get on this OID with no mass storage device
                installed."
::= { hrPartitionEntry 3 }
               
               
hrpartitionsize OBJECT-TYPE
    SYNTAX  INTEGER
    ACCESS  read-only
    STATUS  mandatory
    DESCRIPTION
                "The size of this partition.
               Refer to RFC 1514, Host Resources MIB, for more details.
                Additional information:
                The capacity is in Kbytes.  Returns the
                same value as hrDiskStorageCapacity.  Returns
                <noSuchName> status if attempting
                to perform a Get on this OID with no mass storage device
                installed."
::= { hrPartitionEntry 4 }
               
               
hrpartitionfsindex OBJECT-TYPE
    SYNTAX  INTEGER(0..2147483647)
    ACCESS  read-only
    STATUS  mandatory
    DESCRIPTION
                "The index of the file system mounted on this
               partition.  If no file system is mounted on this
               partition, then this value shall be zero.  Note
               that multiple partitions may point to one file
               system, denoting that that file system resides on
               those partitions.  Multiple file systems may not
               reside on one partition.
               Refer to RFC 1514, Host Resources MIB, for more details.
                Additional information:
                Indicates if the mass storage device has been
                initialized.  Applications determine if the storage device
                has been initialized by getting this object.  Returns zero 
                if the mass storage device is not
                initialized, otherwise the value matches the
                hrDeviceIndex value for this mass storage device.
                The value indicates the
                hrFileSystemTable index for the file system stored
                on this partition.  Returns
                <noSuchName> status if attempting
                to perform a Get on this OID with no mass storage device
                installed."
::= { hrPartitionEntry 5 }
               
               
hrfsindex OBJECT-TYPE
    SYNTAX  INTEGER(1..2147483647)
    ACCESS  read-only
    STATUS  mandatory
    DESCRIPTION
                "A unique value for each file system local to this
               host.  The value for each file system must remain
               constant at least from one re-initialization of
               the agent to the next re-initialization.
               Refer to RFC 1514, Host Resources MIB, for more details.
                Additional information:
                Constant.  The index is assigned by the
                person controlling the printer object definition.
                Returns <noSuchName> status if
                attempting to perform a Get on this OID with no mass storage device
                installed or if the file system has not been
                initialized."
::= { hrFSEntry 1 }
               
               
hrfsmountpoint OBJECT-TYPE
    SYNTAX  OCTET STRING
    ACCESS  read-only
    STATUS  mandatory
    DESCRIPTION
                "The path name of the root of this file system.
               Refer to RFC 1514, Host Resources MIB, for more details.
                Additional information:
                Constant.  Returns
                <noSuchName> status if attempting
                to perform a Get on this OID with no mass storage device installed
                or if the file system has not been initialized."
::= { hrFSEntry 2 }
               
               
hrfsremotemountpoint OBJECT-TYPE
    SYNTAX  OCTET STRING
    ACCESS  read-only
    STATUS  mandatory
    DESCRIPTION
                "A description of the name and/or address of the
               server that this file system is mounted from.
               This may also include parameters such as the mount
               point on the remote file system.  If this is not a
               remote file system, this string should have a
               length of zero.
               Refer to RFC 1514, Host Resources MIB, for more details.
                Additional information:
                Constant.  This printer does not support
                remote file system mounting.  Returns
                <noSuchName> status if attempting
                to perform a Get on this OID with no mass storage device installed
                or if the file system has not been initialized."
::= { hrFSEntry 3 }
               
               
hrfstype OBJECT-TYPE
    SYNTAX  OBJECT IDENTIFIER
    ACCESS  read-only
    STATUS  mandatory
    DESCRIPTION
                "The value of this object identifies the type of
              this file system.
              Refer to RFC 1514, Host Resources MIB, for more details.
                Additional information:
                Constant.  Returns
                <noSuchName> status if attempting
                to perform a Get on this OID with no mass storage device installed
                or if the file system has not been initialized."
::= { hrFSEntry 4 }
               
               
hrfsaccess OBJECT-TYPE
    SYNTAX  INTEGER {
		   eHreadWrite(1),
		   eHreadOnly(2)
		   }
    ACCESS  read-write
    STATUS  mandatory
    DESCRIPTION
                "An indication if this file system is logically
              configured by the operating system to be readable
              and writable or only readable.  This does not
              represent any local access-control policy, except
              one that is applied to the file system as a whole.
              Refer to RFC 1514, Host Resources MIB, for more details.
                Additional information:
                Returns the same value as
                hrDiskStorageAccess.  Returns
                <noSuchName> status if attempting
                to perform a Get on this OID with no mass storage device installed
                or if the file system has not been initialized."
::= { hrFSEntry 5 }
               
               
hrfsbootable OBJECT-TYPE
    SYNTAX  INTEGER {
		   eHfalse(2)
		   }
    ACCESS  read-only
    STATUS  mandatory
    DESCRIPTION
                "A flag indicating whether this file system is
              bootable.
              Refer to RFC 1514, Host Resources MIB, for more details.
                Additional information:
                Constant.  Returns
                <noSuchName> status if attempting
                to perform a Get on this OID with no mass storage device installed
                or if the file system has not been initialized."
::= { hrFSEntry 6 }
               
               
hrfsstorageindex OBJECT-TYPE
    SYNTAX  INTEGER(0..2147483647)
    ACCESS  read-only
    STATUS  mandatory
    DESCRIPTION
                "The index of the hrStorageEntry that represents
               information about this file system.  If there is
               no such information available, then this value
               shall be zero.  The relevant storage entry will be
               useful in tracking the percent usage of this file
               system and diagnosing errors that may occur when
               it runs out of space.
               Refer to RFC 1514, Host Resources MIB, for more details.
                Additional information:
                Constant.  The value indicates the
                hrStorageTable index for this mass storage device.  Returns
                <noSuchName> status if attempting
                to perform a Get on this OID with no mass storage device installed
                or if the file system has not been initialized."
::= { hrFSEntry 7 }
               
               
hrfslastfullbackupdate OBJECT-TYPE
    SYNTAX  OCTET STRING
    ACCESS  read-only
    STATUS  mandatory
    DESCRIPTION
                "The last date at which this complete file system
              was copied to another storage device for backup.
              This information is useful for ensuring that
              backups are being performed regularly.
              If this information is not known, then this
              variable shall have the value corresponding to
              January 1, year 0000, 00:00:00.0, which is encoded
              as (hex)'00 00 01 01 00 00 00 00'.
              Refer to RFC 1514, Host Resources MIB, for more details.
                Additional information:
                Constant.
                The default value is the value defined
                to represent an unknown time of January 1, year 0000,
                00:00:00.0.  Returns <noSuchName>
                status if attempting to perform a Get on this OID
                with no mass storage device installed or if the file system has not
                been initialized."
::= { hrFSEntry 8 }
               
               
hrfslastpartialbackupdate OBJECT-TYPE
    SYNTAX  OCTET STRING
    ACCESS  read-only
    STATUS  mandatory
    DESCRIPTION
                "The last date at which a portion of this file
              system was copied to another storage device for
              backup.  This information is useful for ensuring
              that backups are being performed regularly.
              If this information is not known, then this
              variable shall have the value corresponding to
              January 1, year 0000, 00:00:00.0, which is encoded
              as (hex)'00 00 01 01 00 00 00 00'.
              Refer to RFC 1514, Host Resources MIB, for more details.
                Additional information:
                Constant.
                The default value is the value defined
                to represent an unknown time of January 1, year 0000,
                00:00:00.0.  Returns <noSuchName>
                status if attempting to perform a Get on this OID
                with no mass storage device installed or if the file system has not
                been initialized."
::= { hrFSEntry 9 }
               
               
prtstoragerefindex OBJECT-TYPE
    SYNTAX  INTEGER(1..65535)
    ACCESS  read-only
    STATUS  optional
    DESCRIPTION
                "The value of the hrDeviceIndex of the printer device that this
        storageEntry is associated with.
	Refer to Internet Draft Printer MIB, expiring Sept. 1997 for more details.
                Additional information:
                Constant.  The index value indicates
                the hrStorageTable index for this storage device.
                The value indicates the hrDeviceTable index for the
                printer which uses this storage device.  Returns
                <noSuchName> status if attempting
                to perform a Get on this OID with no storage device
                is installed."
::= { prtStorageRefEntry 2 }
               
               
prtdevicerefindex OBJECT-TYPE
    SYNTAX  INTEGER(1..65535)
    ACCESS  read-only
    STATUS  optional
    DESCRIPTION
                "The value of the hrDeviceIndex of the printer device that this
        deviceEntry is associated with.
	Refer to Internet Draft Printer MIB, expiring Sept. 1997 for more details.
                Additional information:
                Constant.  The index indicates the
                hrDeviceIndex for this mass storage device.  The value indicates
                the hrDeviceIndex for the printer which uses this
                mass storage device.  Returns <noSuchName> status
                if attempting to perform a Get on this OID with no
                mass storage device installed."
::= { prtDeviceRefEntry 2 }
               
               
mio1-model-name OBJECT-TYPE
    SYNTAX  DisplayString
    ACCESS  read-only
    STATUS  optional
    DESCRIPTION
                "Returns product information identifying the I/O card.
                Example: XXXX"
::= { mio1 2 }
               
               
mio1-manufacturing-info OBJECT-TYPE
    SYNTAX  DisplayString
    ACCESS  read-only
    STATUS  optional
    DESCRIPTION
                "Returns information describing the manufacture of the
                I/O card installed in MIO/EIO slot 1.  May include
                serial number and firmware revision.
                Additional information:
                The format of the string returned is determined by
                the manufacturer of the EIO device. There is no standard for content of the
                string."
::= { mio1 3 }
               
               
mio1-type OBJECT-TYPE
    SYNTAX  INTEGER {
		   eEmpty(1),
		   eUnknown(2),
		   eDiskDrive(8),
		   eIOCard(12)
		   }
    ACCESS  read-only
    STATUS  optional
    DESCRIPTION
                "Returns an indication of the type of option installed in
                MIO/EIO slot 1.  See SIMM1-TYPE for an explanation of
                the enumerations."
::= { mio1 4 }
               
               
mio2-model-name OBJECT-TYPE
    SYNTAX  DisplayString
    ACCESS  read-only
    STATUS  optional
    DESCRIPTION
                "Returns product information identifying the I/O card.
                Example: XXXX"
::= { mio2 2 }
               
               
mio2-manufacturing-info OBJECT-TYPE
    SYNTAX  DisplayString
    ACCESS  read-only
    STATUS  optional
    DESCRIPTION
                "Returns information describing the manufacture of the
                I/O card installed in MIO/EIO slot 2.  May include
                serial number and firmware revision.
                Additional information:
                The format of the string returned is determined by
                the manufacturer of the EIO device. There is no standard for content of the
                string."
::= { mio2 3 }
               
               
mio2-type OBJECT-TYPE
    SYNTAX  INTEGER {
		   eEmpty(1),
		   eUnknown(2),
		   eDiskDrive(8),
		   eIOCard(12)
		   }
    ACCESS  read-only
    STATUS  optional
    DESCRIPTION
                "Returns an indication of the type of option installed in
                MIO/EIO slot 2.  See SIMM1-TYPE for an explanation of
                the enumerations."
::= { mio2 4 }
               
               
job-info-change-id OBJECT-TYPE
    SYNTAX  OCTET STRING (SIZE(16))
    ACCESS  read-only
    STATUS  optional
    DESCRIPTION
                "Returns the current value of an object in the job-info
                sub-tree whose value has changed.  Define the object
                identifier for the object whose value has changed as
                job-info.required-field.optional-field.job-id.  job-info
                represents the OID prefix of all objects in the job-info
                sub-tree.  Required-field represents the OID field value
                that follows the job-info prefix.  Since some objects in
                the job-info sub-tree have two OID fields between the
                job-info prefix and the job-id, the optional-field
                represents the OID field between the required-field and
                the job-id field, if present.  Using this definition,
                the format for the JOB-INFO-CHANGE-ID binary value can
                be described as follows:   
                  Bytes  0-3 :  required-field  
                  Bytes  4-7 :  optional-field, or all zeros if there   
                                is no optional field  
                  Bytes  8-11: Job ID.  
                  Bytes 12-n : The value of the object job-info.   
                               required-field.optional-field.job-id.
                All multi-byte values stored in Motorola (big-endian)
                format, where the most significant byte occurs first.
                Additional information:
                The LJ Series 4000 will use this object to report
                changes to the job-info-pages-printed and job-info-state
                objects.  The required-field (bytes 0 through 3) will 
                designate whether the change to be reported involves the 
                pages printed (13) or job state (15).  The optional-field 
                (bytes 4 through 7) will always be zeroes.  The value-field
                (bytes 12 through 15) will contain the new value for pages
                printed or job state cast to a 32-bit integer."
::= { settings-job 3 }
               
               
current-job-parsing-id OBJECT-TYPE
    SYNTAX  INTEGER(-1..32767)
    ACCESS  read-only
    STATUS  optional
    DESCRIPTION
                "Contains the printer assigned job identification for the
                job currently being processed by the processing PDL sub-
                system.  The job ID is a monotonically increasing
                number.  The job ID may be reset to zero at power-up and
                may roll over to zero after reaching some maximum
                value.
                Additional information:
                A value of -1 is returned when the printer
                is not parsing a job.  
                
                When data for a new job is detected, this object is
                updated (the job may or may not turn out to be a Null
                Job); however, the trap does not occur until the printer
                determines that it is not a Null Job.  (A job is considered
                to be a 'null job' if it has no name or job attribute, 
                causes no pages to be printed, and consumes MIN_JOB_SIZE
                (9) or fewer bytes.)  A trapped value will differ from 
                the previous value by one or more.  
                
                Some job-info- objects are created when the first data
                bytes are received.  If the printer determines that the
                job is a Null Job, the job-info- objects related to the
                Null Job are deleted.  The LJ Series 4000 retains the job-info-
                objects for the MAX_JOBS_IN_LIST (12) most recent jobs 
                that are not Null Jobs.  
                
                The first job received after power-up will have job ID 1,
                and the job ID will increment to 32767 before rolling 
                to zero.  To distinguish whether a power cycle or a 
                rollover causes a reduction in the job ID value, the 
                object prtGeneralConfigChanges can be watched and if it 
                increments at the same time as the drop is observed in
                the value of CURRENT-JOB-PARSING-ID, then a power cycle
                is the most likely cause."
::= { job-being-parsed 1 }
               
               
job-info-name1 OBJECT-TYPE
    SYNTAX  DisplayString
    ACCESS  read-only
    STATUS  optional
    DESCRIPTION
                "Contains the first part of this print job's name.  The
                last OID field for this dynamic object contains the job
                ID.
                Additional information:
                The job name is the string specified by the
                NAME= parameter of the @PJL JOB command which allows a
                maximum of 80 characters.  The first 40 characters are
                in this object and the second 40 are in job-info-name2.
                The symbol set is Roman-8.  
                
                When jobs are nested, the value assigned to this object
                is the name provided by the most recent @PJL JOB NAME=
                command.  If no name is provided, a null string is
                returned."
::= { job-info 1 }
               
               
job-info-name2 OBJECT-TYPE
    SYNTAX  DisplayString
    ACCESS  read-only
    STATUS  optional
    DESCRIPTION
                "Contains the second part of this print job's name.  The
                last OID field for this dynamic object contains the job
                ID.
                Additional information:
                See job-info-name1."
::= { job-info 2 }
               
               
job-info-stage OBJECT-TYPE
    SYNTAX  OCTET STRING
    ACCESS  read-only
    STATUS  optional
    DESCRIPTION
                "Indicates what printer sub-systems are currently
                processing this print job.  The last OID field for this
                dynamic object contains the job ID.
                  cSourceSubsystem -  some of the job is in the printer
                I/O subsystem.
                  cProcessingSubsystem - some of the job is in the
                printer imaging processing subsystem.
                  cDestinationSubsystem -  some of the job is being
                printed.
                Additional information:
                For The LJ Series 4000, cSourceSubsystem and
                cProcessingSubsystem will always be set and cleared
                together.  They are set when the beginning of the
                job is detected, and they are cleared when the end
                of the job is parsed.  
                
                A non-printing job will never set
                cDestinationSubsystem.  
                
                When a page is ready to be printed, 
                cDestinationSubsystem will be set even if a page of a 
                previous job is currently being printed.
                cDestinationSubsystem remains set until the last page of
                the job has finished printing.  
                
                If a page requires extensive processing and allows all
                the previous pages of a job to complete printing,
                cDestinationSubsystem will remain set until the last
                page of the job has finished printing."
::= { job-info 10 }
               
               
job-info-io-source OBJECT-TYPE
    SYNTAX  INTEGER
    ACCESS  read-only
    STATUS  optional
    DESCRIPTION
                "Indicates which I/O source, the print job was received
                over.  The value maps to port numbering scheme supported
                in the DEVICE/SOURCE-SUBSYSTEM/IO/PORTS sub-tree."
::= { job-info 11 }
               
               
job-info-pages-processed OBJECT-TYPE
    SYNTAX  INTEGER
    ACCESS  read-only
    STATUS  optional
    DESCRIPTION
                "Indicates the number of pages processed by the
                processing subsystem.  If neither the cSourceSubsystem
                or the cProcessingSubsystem items are in the associated
                JOB-INFO-STAGE object, then this object contains the
                total number of pages processed for this job.  The last
                OID field for this dynamic object contains the job ID.
                Additional information:
                This object is incremented by one when a
                page is processed (`closed' by the personality), regardless 
                of the number of pages that are printed as a result of the 
                single page processed.  In other words, it does not matter 
                how many identical copies of a page are printed or no pages
                may be printed if operating in silent run mode, this count
                is incremented exactly once.  
                
                A page is considered processed when all of the input
                data has been processed for a page (that is, when the 
                intermediate has been produced, and the personality has 
                `closed' the page.  At this time, the image of the page is 
                not necessarily completely formed.)"
::= { job-info 12 }
               
               
job-info-pages-printed OBJECT-TYPE
    SYNTAX  INTEGER
    ACCESS  read-only
    STATUS  optional
    DESCRIPTION
                "Indicates the number of pages printed by the destination
                subsystem.  If non of the cSourceSubsystem,
                cProcessingSubsystem or cDestinationSubsystem items are
                in the associated JOB-INFO-STAGE object, then this
                object contains the total number of pages printed for
                this job.  This value may increase by two each time for
                duplex jobs.  The last OID field for this dynamic object
                contains the job ID.
                Additional information:
                If multiple copies of a page are printed,
                each copy is counted individually."
::= { job-info 13 }
               
               
job-info-size OBJECT-TYPE
    SYNTAX  INTEGER
    ACCESS  read-only
    STATUS  optional
    DESCRIPTION
                "Indicates the number of bytes of data processed by the
                processing subsystem.  If neither of the
                cSourceSubsystem or cProcessingSubsystem items are in
                the associated JOB-INFO-STAGE object, then this object
                contains the size of this job, in bytes.  The last OID
                field for this dynamic object contains the job ID.
                Additional information:
                This count may be incremented by values
                other than one as blocks of data are processed; blocks
                of data (which may be as large as 2K bytes) will be
                processed in a varying amount of time.  
                
                During the processing of a job and even when a job completes, 
                an exact count of the number of I/O bytes processed by the
                job is not necessarily to be expected."
::= { job-info 14 }
               
               
job-info-state OBJECT-TYPE
    SYNTAX  INTEGER {
		   eAborted(3),
		   eWaitingForResources(4),
		   ePrinted(5),
		   eTerminating(7),
		   eCancelled(10),
		   eProcessing(11)
		   }
    ACCESS  read-only
    STATUS  optional
    DESCRIPTION
                "Indicates the state of the job.  The last OID field for
                this dynamic object contains the job ID.  
                  eAborted - the print job was aborted.  
                  eWaitingForResources - the print job requires
                resources that are not currently available.  Example
                resources that can cause the job to wait include the
                print engine or PDL processor being unavailable.  The
                print engine could be unavailable due to paper out,
                paper jam, staple out, stapler jam, marking agent low,
                output bin full, etc.  The PDL processor could be
                unavailable due to an off-line condition.  Each printer
                specific object specification should state which
                conditions cause a job to be waiting for resources and
                also state which objects can be retrieved by an
                application to determine the exact cause of a resource
                being unavailable.  
                  ePrinted - the job has printed.  The related JOB-INFO-
                OUTCOME object indicates if any problems were
                encountered while the job was processed.  
                  eRetained - the job can be reprinted.  
                  eTerminating - the job was aborted or cancelled and is
                currently is terminating.  
                  eInterrupted - the job has been interrupted.  The job
                can be continued.  
                  ePaused - the job has been paused.  The job can be
                continuted.  
                  eCancelled - the job has been cancelled.  
                  eProcessing - the job is currently being printed
                normally."
::= { job-info 15 }
               
               
job-info-outcome OBJECT-TYPE
    SYNTAX  INTEGER {
		   eOk(3)
		   }
    ACCESS  read-only
    STATUS  optional
    DESCRIPTION
                "Indicates if any warning or error conditions were
                encountered while processing the assoicated job.  The
                last OID field for this dynamic object contains the job
                ID.
                Additional information:
                In The LJ Series 4000, warnings and errors are not recorded
                in this object.  Although no meaningful information can be
                obtained from this object, it is kept around for the
                compatibility needs of existing software."
::= { job-info 19 }
               
               
job-info-outbins-used OBJECT-TYPE
    SYNTAX  OCTET STRING
    ACCESS  read-only
    STATUS  optional
    DESCRIPTION
                "Indicates which output bins this job has delivered
                printed pages to.  The last OID field for this dynamic
                object contains the job ID.
                Additional information:
                The bins designated by this collection include
                the printer's own output bins as well as the `logical output
                bins' associated with any attached external paper handling
                devices.  (The mapping of the physical output bins of an
                external paper handling device to its `logical output bins'
                depends on the usage mode of the device.  For instance, in
                `mailbox mode', there is one-to-one correspondence of 
                `logical output bins' to physical bins, whereas in `stacker 
                mode', one `logical output bin' may map to several physical
                bins.)  
                
                Although the LaserJet Series 4000 comes with two output
                bins -- a face-down bin on the top of the device and a
                face-up bin at the back of the device -- firmware will not
                provide a means of selecting between the two, nor will it
                report which of the two gets used.  For this reason, bit 0
                (cOutbin1) of this collection is being used to designate
                both of these bins together."
::= { job-info 20 }
               
               
job-info-physical-outbins-used OBJECT-TYPE
    SYNTAX  OCTET STRING
    ACCESS  read-only
    STATUS  optional
    DESCRIPTION
                "Indicates which physical output bins this job has
                delivered printed pages to.  The last OID field for this
                dynamic object contains the job ID.
                Additional information:
                The output bins designated by the bits of 
                this collection include only the physical bins of attached
                external paper handling devices.  The configuration (if 
                any) of external paper handling devices will determine 
                the mapping of individual bits in this collection to the
                physical bins of the devices.  For jobs that do not use 
                an external paper handling device, none of the bits in
                this collection should be set."
::= { job-info 22 }
               
               
job-info-attr-1 OBJECT-TYPE
    SYNTAX  OCTET STRING (SIZE(1..80))
    ACCESS  read-only
    STATUS  optional
    DESCRIPTION
                "Returns the value that was set in PJL via the SET
                JOBATTR= command.  Attribute objects are saved
                sequentially, starting with 1, after the start of a job.
                If more attributes are set than there are objects to
                store them, the excess JOBATTR values are ignored.  If
                the corresponding SET JOBATTR= command has not been
                received when a get is done for this object, a status of
                <noSuchName> will be returned."
::= { job-info-attribute 1 }
               
               
job-info-attr-2 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 2 }
               
               
job-info-attr-3 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 3 }
               
               
job-info-attr-4 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 4 }
               
               
job-info-attr-5 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 5 }
               
               
job-info-attr-6 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 6 }
               
               
job-info-attr-7 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 7 }
               
               
job-info-attr-8 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 8 }
               
               
job-info-attr-9 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 9 }
               
               
job-info-attr-10 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 10 }
               
               
job-info-attr-11 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 11 }
               
               
job-info-attr-12 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 12 }
               
               
job-info-attr-13 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 13 }
               
               
job-info-attr-14 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 14 }
               
               
job-info-attr-15 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 15 }
               
               
job-info-attr-16 OBJECT-TYPE
    SYNTAX  OCTET STRING (SIZE(1..80))
    ACCESS  read-only
    STATUS  optional
    DESCRIPTION
                "Returns the value that was set in PJL via the SET
                JOBATTR= command.  See JOB-INFO-ATTR-1 for details."
::= { job-info-attribute 16 }
               
               
job-info-requested-originals OBJECT-TYPE
    SYNTAX  INTEGER
    ACCESS  read-only
    STATUS  optional
    DESCRIPTION
                "The number of requested collated copies.  The value was
                supplied with the job via PJL QTY variable, the
                PostScript Collate and NumCopies entries in the page
                device dictionary, or via some other mechansim."
::= { job-info 24 }
               
               
job-info-page-count-current-original OBJECT-TYPE
    SYNTAX  INTEGER
    ACCESS  read-only
    STATUS  optional
    DESCRIPTION
                "The page number being printed within the current copy of
                a collated multi-copy job.  This value changes when the
                job-info-pages-printed changes.  The job-info-pages-
                printed indicates the total number of pages printed in
                the job, while this object indicates the number of pages
                printed for this copy of a collated multi-copy job.
                Additional information:
                The number of pages in the current copy of a collated
                multi-copy job which have been completely printed and
                safely delivered to the output bin."
::= { job-info 25 }
               
               
job-info-pages-in-original OBJECT-TYPE
    SYNTAX  INTEGER
    ACCESS  read-only
    STATUS  optional
    DESCRIPTION
                "Number of pages in a single copy of a collated multi-
                copy job."
::= { job-info 26 }
               
               
job-info-printed-originals OBJECT-TYPE
    SYNTAX  INTEGER
    ACCESS  read-only
    STATUS  optional
    DESCRIPTION
                "Number of collated copies completely printed and
                delivered to the output bin at time of query."
::= { job-info 27 }
               
               
form-feed-needed OBJECT-TYPE
    SYNTAX  INTEGER {
		   eFalse(1),
		   eTrue(2)
		   }
    ACCESS  read-only
    STATUS  optional
    DESCRIPTION
                "Indicates if the PDL processing sub-system has made
                marks on the current page and the source subsystem has
                been idle for a device specific amount of time.
                Additional information:
                The LJ Series 4000 will set this object to eTrue when it
                has made marks on the current page, the IO-TIMEOUT has
                expired while PCL was running in `backward-compatibility
                mode' (which is caused by jobs consisting purely of PCL
                data with no prepended PJL commands), and no data is pending 
                on another I/O.  Once it is set to eTrue, more data on the 
                same I/O will cause this object to be set to eFalse, until 
                the above conditions are met again."
::= { status-pdl 2 }
               
               
jetsend-mode OBJECT-TYPE
    SYNTAX  INTEGER {
		   eOff(1),
		   eOn(2)
		   }
    ACCESS  read-write
    STATUS  mandatory
    DESCRIPTION
                "Enables or disables the JetSend processing sub-system.
                Additional information:
                Enables or disables the JetSend processing subsystem.
                The valid values are eOff and eOn. (Specifying an invalid mode
                causes an <badValue> error to be returned.)"
::= { settings-jetsend 1 }
               
               
jetsend-contact-password OBJECT-TYPE
    SYNTAX  OCTET STRING (SIZE(16))
    ACCESS  write-only
    STATUS  mandatory
    DESCRIPTION
                "A C structure containing the following fields:
                 typedef struct {
                     ubyte old_password[8];
                     ubyte new_password[8];/
                 } jetsend_change_contact_password_t;
                where ubyte is an unsigned byte (0-255).
                Additional information:
                Controls access to the JetSend processing subsystem.
                Password absence/presence determines whether the device will allow
                a session to be established. The following C data structure
                contains the relevant fields (described in subsequent paragraphs):
                
                typedef struct {
                unsigned char old_password[8];
                unsigned char new_password[8];
                }
                
                Whenever the password is disabled (i.e., is zero-filled for its
                entire length), the device is indicating its willingness to allow
                session establishment. Whenever the password is enabled (i.e., has
                one or more non-zero-filled values), the device is controlling
                session establishment -- all in-progress JetSend sessions must
                supply a matching password or the device will reject the in-progress
                session.
                
                To disable the password, specify the matching password via the
                'old_password' field and zero-fill the 'new_password' field.
                To enable the password for the first time, zero-fill the
                'old_password' field and specify the new password via the
                'new_password' field (the new password should not be
                zero-filled; otherwise, the password will remain disabled).
                To enable or change the password thereafter, specify the
                matching password via the 'old_password' field and specify
                the new password via the 'new_password' field (the new
                desired password should not be zero-filled; otherwise,
                the password will be disabled). To determine if the password
                is enabled, zero-fill both the 'old_password' and 'new_password'
                fields. If an error occurs, the password is enabled; otherwise,
                the password is disabled.
                
                (Specifying either an 'old_password' or 'new_password'
                fields greater than eight (8) bytes causes the error
                <badValue> to be returned.)"
::= { settings-jetsend-contact 1 }
               
               
jetsend-contact-ip-address-security OBJECT-TYPE
    SYNTAX  OCTET STRING (SIZE(16))
    ACCESS  write-only
    STATUS  mandatory
    DESCRIPTION
                "A C structure containing the following fields:
                 typedef struct {
                     ubyte reserved[3];
                     ubyte command; /* command: 0 to 1 */
                     ubyte password[8];
                     ubyte IPAddress[4];
                 } jetsend_contact_ip_address_security_t;
                where ubyte is an unsigned byte (0-255).  The defined
                values defined for command are:  
                  0: Limit JetSend sessions to sessions from a device
                whose IP address matchs the supplied IPAddress.  
                  1: Limit JetSend sessions to session from devices
                whose IP addresses match the mask supplied in IPAddress
                field.  If the result of logically anding the mask value
                supplied in the IPAddress field with the sending
                device's IP address matches the result of logically
                anding the mask value supplied in the IPAddress field
                with this device's IP address, then JetSend will allow
                the session to be established.  
                To disable IP address security, zero out the IPAddress
                field.
                Additional information:
                Controls the device or class of device(s) which may
                communicate with the JetSend processing subsystem. The following C
                data structure contains the relevant fields (described in subsequent
                paragraphs):
                
                typedef struct {
                unsigned char reserved[3];
                unsigned char command;
                unsigned char password[8];
                unsigned char IPAddress[4];
                }
                
                The 'reserved' field is not used and should remain zero-filled.
                The 'command' field interpretation differs based on its value:
                
                0 = Accept session(s) only from the specific device whose
                IP address matches the specified IP address; all other
                session request(s) from non-matching device(s) are rejected.
                1 = Accept session(s) only from the specific device(s) whose
                IP address(es) conform to the mask specified in the 'IPAddress'
                field; all other session request(s) from device(s) with
                non-matching submask(s) are rejected. (If the result of
                logically AND'ing the mask value supplied in the 'IPAddress'
                field with the sending device's IP address matches the result
                of logically AND'ing the mask value supplied in the 'IPAddress'
                field with this device's IP address, then JetSend will allow
                session establishment.
                
                Password absence/presence determines whether the device will allow
                the caller to alter the IP address security. If the password is
                disabled, the caller may set the 'command' and 'IPAddress' fields
                directly. If the password is enabled, the caller may (re-)set the
                'command' and 'IPAddress' fields only after specifying the matching
                'password' field. (Refer to the aforementioned 'JETSEND-CONTACT-PASSWORD'
                object ID.)
                
                (Specifying either an invalid 'command' field value or a 'password'
                field greater than eight (8) bytes or an 'IPAddress' field greater
                than four (4) bytes causes the error <badValue>
                to be returned.)"
::= { settings-jetsend-contact 2 }
               
              
rpc-bind-protocol-address OBJECT-TYPE 
    SYNTAX  OCTET STRING
    ACCESS  read-write
    STATUS  optional
    DESCRIPTION
                "Array of Berkeley sockets style protocol addresses used
                to bind RPC to a communications protocol family.
                Setting an instance of this array object to a zero
                length binary value disables the transport protocol
                indicated by that instance.  All multi-bytes fields are
                in network (or big-endian) order.  Bytes 1 and 2
                indicate the transport protocol.  Some of the transport
                protocol mapping information can be found in RFC 1010
                Assigned Numbers.  A list of interesting transport
                protocol number mappings include:  
                Protocol | Number   
                ---------+-------   
                 UDP/IP  |  17   
                  IPX    |  1000   
                  MLC    |  4660   
                Bytes 3 and 4 indicate the address family.  The address
                family uses the same mapping as the BSD sockets address
                family.  A list of interesting address family mappings
                include:  
                Address Family | Number   
                ---------------+-------   
                    Internet   |   2   
                    NetWare    |   6   
                    MLC        | 22136   
                The format the fifth and following bytes is dependent on
                the address family.  For the Internet address family,
                bytes 5 and 6 contain the port number, bytes 7 through
                10 contain the IP address, and the following eight bytes
                are unused.  For NetWare, bytes 5 through 8 are the
                network number, bytes 9 through 14 are the node number,
                and bytes 15 and 16 are the socket number.
                Additional information:
                The length of the binary value is zero
                if the instance of an object in the rpc-bind-protocol-address
                array is not in use.   A side effect of the 
                implementation is initializing the mass storage device sets this object 
                back to the factory default value.  
                Returns <noSuchName>
                status if attempting to access this object and there
                is no storage device is installed."
::= { settings-rpc 2 }
               
               
rpc-statistic-successful OBJECT-TYPE
    SYNTAX  INTEGER
    ACCESS  read-only
    STATUS  optional
    DESCRIPTION
                "A counter indicating the number of RPC requests that
                completed successfully (reply_data stat is SUCCESS).
                The POS should state if a power cycle causes the counter
                is be reset to zero.
                Additional information:
                Reset to the factory default value after
                a power cycle.  
                Returns <noSuchName>
                status if attempting to access this object and there
                is no storage device is installed."
::= { status-rpc 1 }
               
               
rpc-statistic-unsuccessful OBJECT-TYPE
    SYNTAX  INTEGER
    ACCESS  read-only
    STATUS  optional
    DESCRIPTION
                "A counter indicating the number of RPC requests that
                completed unsuccessfully (reply_data stat is not
                SUCCESS).  The POS should state if a power cycle causes
                the counter is be reset to zero.
                Additional information:
                Reset to the factory default value after
                a power cycle.  
                Returns <noSuchName>
                status if attempting to access this object and there
                is no storage device is installed."
::= { status-rpc 2 }
               
               
rpc-bound-protocol-address OBJECT-TYPE
    SYNTAX  OCTET STRING
    ACCESS  read-only
    STATUS  optional
    DESCRIPTION
                "An array of Berkeley sockets style protocol addresses
                that the NFS service has been bound to successful.  The
                format is that same as the array of RPC-BIND-PROTOCOL-
                ADDRESS of objects.
                Additional information:
                Returns <noSuchName>
                status if attempting to access this object and there
                is no storage device is installed."
::= { status-rpc 3 }
               
               
nfs-server-memory OBJECT-TYPE
    SYNTAX  INTEGER
    ACCESS  read-only
    STATUS  optional
    DESCRIPTION
                "The amount of memory, in bytes, used by the Network File
                System server to buffer file data.
                Additional information:
                Reports the amount of memory, in bytes,
                reserved for use by the NFS server.  A
                side effect of the implementation is initializing
                the mass storage device sets this object back to the factory
                default value.  Also includes the memory used by
                other firmware components in addition to the NFS
                server.  Returns <noSuchName>
                status if attempting to access this object and there
                is no storage device is installed."
::= { settings-nfs-server 1 }
               
               
nfs-server-read-size OBJECT-TYPE
    SYNTAX  INTEGER(256..1500)
    ACCESS  read-write
    STATUS  optional
    DESCRIPTION
                "The maximum amount of data transferred in one NFS server
                read data call.
                Additional information:
                A side effect of the 
                implementation is initializing the mass storage device
                	   sets this object back to the factory default value.  
                Returns <noSuchName>
                status if attempting to access this object and there
                is no storage device is installed.  Rebooting causes
                	   this value to reset to factory default.  
                	      value < 256 snaps to 256
                	      value > 1500 snaps to 1500"
::= { settings-nfs-server 2 }
               
               
nfs-server-write-size OBJECT-TYPE
    SYNTAX  INTEGER(256..1500)
    ACCESS  read-write
    STATUS  optional
    DESCRIPTION
                "The maximum amount of data transferred in one NFS server
                write data call.
                Additional information:
                A side effect of the 
                implementation is initializing the mass storage device sets this object 
                back to the factory default value.  
                Returns <noSuchName>
                status if attempting to access this object and there
                is no storage device is installed."
::= { settings-nfs-server 3 }
               
               
nfs-server-statistic-successful OBJECT-TYPE
    SYNTAX  INTEGER
    ACCESS  read-only
    STATUS  optional
    DESCRIPTION
                "A counter indicating the number of NFS requests that
                completed without error.  The POS should state if a
                power cycle causes the counter is be reset to zero.
                Additional information:
                Reset to the factory default value after
                a power cycle.  
                Returns <noSuchName>
                status if attempting to access this object and there
                is no storage device is installed."
::= { status-nfs-server 1 }
               
               
nfs-server-statistic-unsuccessful OBJECT-TYPE
    SYNTAX  INTEGER
    ACCESS  read-only
    STATUS  optional
    DESCRIPTION
                "A counter indicating the number of NFS requests that
                completed with an NFS status other than NFS_OK (0).  The
                POS should state if a power cycle causes the counter is
                be reset to zero.
                Additional information:
                Reset to the factory default value after
                a power cycle.  
                Returns <noSuchName>
                status if attempting to access this object and there
                is no storage device is installed."
::= { status-nfs-server 2 }
               
               
nfs-server-statistic-current-memory-usage OBJECT-TYPE
    SYNTAX  INTEGER
    ACCESS  read-only
    STATUS  optional
    DESCRIPTION
                "A value indicating the number of bytes of RAM currently
                used by the NFS firmware.
                Additional information:
                Reset to the factory default value after
                a power cycle.  
                Returns <noSuchName>
                status if attempting to access this object and there
                is no storage device is installed."
::= { status-nfs-server 4 }
               
               
nfs-server-statistic-max-memory-usage OBJECT-TYPE
    SYNTAX  INTEGER
    ACCESS  read-only
    STATUS  optional
    DESCRIPTION
                "A value indicating the maximum number of bytes of RAM
                used by the NFS firmware.  The POS should state if the
                value is reset to zero after a power cycle.
                Additional information:
                Reset to the factory default value after
                a power cycle.  
                Returns <noSuchName>
                status if attempting to access this object and there
                is no storage device is installed."
::= { status-nfs-server 5 }
               
               
rpc-bind-statistic-successful OBJECT-TYPE
    SYNTAX  INTEGER
    ACCESS  read-only
    STATUS  optional
    DESCRIPTION
                "A counter indicating the number of RPC bind (RPC program
                number 100000, version 2) requests that completed
                successfully.  The POS should state if a power cycle
                causes the counter is be reset to zero.
                Additional information:
                Reset to the factory default value after
                a power cycle.  
                Returns <noSuchName>
                status if attempting to access this object and there
                is no storage device is installed."
::= { status-rpc-bind 1 }
               
               
rpc-bind-statistic-unsuccessful OBJECT-TYPE
    SYNTAX  INTEGER
    ACCESS  read-only
    STATUS  optional
    DESCRIPTION
                "A counter indicating the number of RPC bind (RPC program
                number 100000, version 2) requests that completed
                unsuccessfully.  The POS should state if a power cycle
                causes the counter is be reset to zero.
                Additional information:
                Reset to the factory default value after
                a power cycle.  
                Returns <noSuchName>
                status if attempting to access this object and there
                is no storage device is installed."
::= { status-rpc-bind 2 }
               
               
xip-statistic-processed OBJECT-TYPE
    SYNTAX  INTEGER
    ACCESS  read-only
    STATUS  optional
    DESCRIPTION
                "A counter indicating the number of XIP requests that
                were processed.  The POS should state if a power cycle
                causes the counter is be reset to zero.
                Additional information:
                The number of XIP datagrams that have
                been received by the XIP service.  Reset to the
                factory default value after a power cycle.  Returns
                <noSuchName> status if attempting
                to access this object and there is no storage device
                is installed."
::= { status-xip 1 }
               
               
xip-statistic-data-in-dropped OBJECT-TYPE
    SYNTAX  INTEGER
    ACCESS  read-only
    STATUS  optional
    DESCRIPTION
                "A counter indicating the number of XIP data in datagrams
                that were dropped (typically due to the printer being
                flooded with XIP requests ).  The POS should state if a
                power cycle causes the counter is be reset to zero.
                Additional information:
                Reset to the factory default value after
                a power cycle.  
                Returns <noSuchName>
                status if attempting to access this object and there
                is no storage device is installed."
::= { status-xip 2 }
               
               
prtinterpreterlangfamily OBJECT-TYPE
    SYNTAX  INTEGER {
		   ePother(1),
		   ePlangPCL(3),
		   ePlangPJL(5),
		   ePlangPS(6),
		   ePlangAutomatic(37),
		   ePlangPCLXL(47)
		   }
    ACCESS  read-only
    STATUS  optional
    DESCRIPTION
                "The family name of a Page Description Language (PDL) or
        control language which this interpreter in the printer can
		interpret or emulate. 
	Refer to Internet Draft Printer MIB, expiring Sept. 1997 for more details.
                Additional information:
                ePlangAutomatic refers to the `super-language'
                made available by implicit language switching."
::= { prtInterpreterEntry 2 }
               
               
prtinterpreterlanglevel OBJECT-TYPE
    SYNTAX  OCTET STRING (SIZE(0..31))
    ACCESS  read-only
    STATUS  optional
    DESCRIPTION
                "The level of the language which this interpreter is
        interpreting or emulating.  This might contain a value like
        '5e' for an interpreter which is emulating level 5e of the PCL
        language.  It might contain '2' for an interpreter which is
        emulating level 2 of the PostScript language.  Similarly it
        might contain '2' for an interpreter which is emulating level
        2 of the HPGL language.
	Refer to Internet Draft Printer MIB, expiring Sept. 1997 for more details."
::= { prtInterpreterEntry 3 }
               
               
prtinterpreterlangversion OBJECT-TYPE
    SYNTAX  OCTET STRING (SIZE(0..31))
    ACCESS  read-only
    STATUS  optional
    DESCRIPTION
                "The date code or version of the language which this interpreter
        is interpreting or emulating.
	Refer to Internet Draft Printer MIB, expiring Sept. 1997 for more details.
                Additional information:
                These values are derived from the dateCode field of the personality
                entities.  (ePlangAutomatic uses the PJL dateCode.)"
::= { prtInterpreterEntry 4 }
               
               
prtinterpreterdescription OBJECT-TYPE
    SYNTAX  OCTET STRING (SIZE(0..255))
    ACCESS  read-only
    STATUS  optional
    DESCRIPTION
                "A string to identify this interpreter in the localization
        specified by prtGeneralCurrentLocalization as opposed to the
        language which is being interpreted.  It is anticipated that
        this string will allow manufacturers to unambiguously identify
        their interpreters.
	Refer to Internet Draft Printer MIB, expiring Sept. 1997 for more details.
                Additional information:
                These values are obtained from the persName fields 
                of the personality entities (except for the hard-coded value
                of 'Automatic Language Switching'.)  
                
                These strings are not localized."
::= { prtInterpreterEntry 5 }
               
               
prtinterpreterversion OBJECT-TYPE
    SYNTAX  OCTET STRING (SIZE(0..31))
    ACCESS  read-only
    STATUS  optional
    DESCRIPTION
                "The date code, version number, or other product specific
        information tied to this interpreter.  This value is
        associated with the interpreter, rather than with the version
        of the language which is being interpreted or emulated.
	Refer to Internet Draft Printer MIB, expiring Sept. 1997 for more details.
                Additional information:
                Same as prtInterpreterLangVersion."
::= { prtInterpreterEntry 6 }
               
               
prtinterpreterdefaultorientation OBJECT-TYPE
    SYNTAX  INTEGER {
		   ePportrait(3),
		   ePlandscape(4)
		   }
    ACCESS  read-write
    STATUS  optional
    DESCRIPTION
                "The current orientation default for this interpreter.  This
        value may be overridden for a particular job (e.g., by a
        command in the input data stream).
	Refer to Internet Draft Printer MIB, expiring Sept. 1997 for more details.
                Additional information:
                The value of the system's DEFAULT-ORIENTATION is
                set or retrieved without regard to interpreters.  Setting this 
                object for one interpreter will change it for all installed 
                interpreters.  
                
                The valid values are ePportrait and ePlandscape.  Attempting 
                to set the orientation to a different value will cause 
                <badValue> to be returned."
::= { prtInterpreterEntry 7 }
               
               
prtinterpreterfeedaddressability OBJECT-TYPE
    SYNTAX  INTEGER
    ACCESS  read-only
    STATUS  optional
    DESCRIPTION
                "The maximum interpreter addressability in the feed
        direction in 10000 prtMarkerAddressabilityUnits (see
        prtMarkerAddressabilityFeedDir ) for this interpreter.
        The value (-1) means other and specifically indicates
        that the sub-unit places no restrictions on this parameter.
	Refer to Internet Draft Printer MIB, expiring Sept. 1997 for more details."
::= { prtInterpreterEntry 8 }
               
               
prtinterpreterxfeedaddressability OBJECT-TYPE
    SYNTAX  INTEGER
    ACCESS  read-only
    STATUS  optional
    DESCRIPTION
                "The maximum interpreter addressability in the cross feed
        direction in 10000 prtMarkerAddressabilityUnits (see
        prtMarkerAddressabilityXFeedDir) for this interpreter.
        The value (-1) means other and specifically indicates
        that the sub-unit places no restrictions on this
        parameter.
	Refer to Internet Draft Printer MIB, expiring Sept. 1997 for more details."
::= { prtInterpreterEntry 9 }
               
               
prtinterpreterdefaultcharsetin OBJECT-TYPE
    SYNTAX  INTEGER {
		   ePcsASCII(3),
		   ePcsISOLatin1(4),
		   ePcsISOLatin2(5),
		   ePcsISOLatin5(12),
		   ePcsISOLatin6(13),
		   ePcsISO4UnitedKingdom(20),
		   ePcsISO11SwedishforNames(21),
		   ePcsISO15Italian(22),
		   ePcsISO17Spanish(23),
		   ePcsISO21German(24),
		   ePcsISO60DanishNorwegian(25),
		   ePcsISO69French(26),
		   ePcsUnicodeIBM2039(1004),
		   ePcsWindows30Latin1(2000),
		   ePcsWindows31Latin1(2001),
		   ePcsWindows31Latin2(2002),
		   ePcsWindows31Latin5(2003),
		   ePcsHPRoman8(2004),
		   ePcsAdobeStandardEncoding(2005),
		   ePcsPC850Multilingual(2009),
		   ePcsPCp852(2010),
		   ePcsPC8CodePage437(2011),
		   ePcsPC8DNDanishNorwegian(2012),
		   ePcsHPPC8Turkish(2014),
		   ePcsHPLegal(2017),
		   ePcsHPDeskTop(2021),
		   ePcsMacintosh(2027),
		   ePcsPC775Baltic(2087),
		   ePcsWindows1257Baltic(2257)
		   }
    ACCESS  read-write
    STATUS  optional
    DESCRIPTION
                "The default coded character set for input octets
        encountered outside a context in which the Page
        Description Language established the interpretation
        of the octets. (Input octets are presented to the
        interpreter through a path defined in the channel group.)
        This value shall be (2) if there is no default.
	Refer to Internet Draft Printer MIB, expiring Sept. 1997 for more details.
                Additional information:
                The object corresponding to PCL has read-write access;
                For all other interpreters, the object is read-only.  
                
                The above list corresponds to the following symbol sets as they 
                appear on the Control Panel:  
                
                ePcsASCII( 3) - ISO-6   
                ePcsISOLatin1( 4) - ISO L1   
                ePcsISOLatin2( 5) - IS L2   
                ePcsISOLatin5( 12) - ISO L5   
                ePcsISOLatin6( 13) - ISO L6   
                ePcsISO4UnitedKingdom( 20) - ISO-4   
                ePcsISO11SwedishforNames( 21) - ISO-11   
                ePcsISO15Italian( 22) - ISO-15   
                ePcsISO17Spanish( 23) - ISO-17   
                ePcsISO21German( 24) - ISO-21   
                ePcsISO60DanishNorwegian( 25) - ISO-60   
                ePcsISO69French( 26) - ISO-69   
                ePcsUnicodeIBM2039(1004) - PC-1004   
                ePcsWindows30Latin1( 2000) - WIN 3.0   
                ePcsWindows31Latin1( 2001) - WIN L1   
                ePcsWindows31Latin2( 2002) - WIN L2   
                ePcsWindows31Latin5( 2003) - WIN L5   
                ePcsHPRoman8( 2004) - ROMAN-8   
                ePcsAdobeStandardEncoding( 2005) - PS TEXT   
                ePcsPC850Multilingual( 2009) - PC-850   
                ePcsPCp852( 2010) - PC-852   
                ePcsPC8CodePage437( 2011) - PC-8   
                ePcsPC8DNDanishNorwegian( 2012) - PC-8DN   
                ePcsHPPC8Turkish( 2014) - PC-8 TK   
                ePcsHPLegal( 2017) - LEGAL   
                ePcsHPDeskTop( 2021) - DESKTOP   
                ePcsMacintosh(2027) - MC TEXT   
                ePcsPC775Baltic( 2087) - PC-775   
                ePcsWindows1257Baltic( 2257) - WINBALT"
::= { prtInterpreterEntry 10 }
               
               
prtinterpreterdefaultcharsetout OBJECT-TYPE
    SYNTAX  INTEGER {
		   ePcsNoDefault(2),
		   ePcsASCII(3),
		   ePcsHPRoman8(2004),
		   ePcsAdobeStandardEncoding(2005)
		   }
    ACCESS  read-only
    STATUS  optional
    DESCRIPTION
                "The default character set for data coming from this interpreter
        through the printer's output channel (i.e. the 'backchannel'). 
        This value shall be (2) if there is no default.
	Refer to Internet Draft Printer MIB, expiring Sept. 1997 for more details."
::= { prtInterpreterEntry 11 }
               
               
prtinterpretertwoway OBJECT-TYPE
    SYNTAX  INTEGER {
		   ePyes(3),
		   ePno(4)
		   }
    ACCESS  read-only
    STATUS  optional
    DESCRIPTION
                "Indicates whether or not this interpreter returns information
        back to the host.
	Refer to Internet Draft Printer MIB, expiring Sept. 1997 for more details."
::= { prtInterpreterEntry 12 }
               
               
END

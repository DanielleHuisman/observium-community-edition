SYNERGY100G-HPE-CPU-UTIL-MIB DEFINITIONS ::= BEGIN

IMPORTS
   	enterprises,
	MODULE-IDENTITY,
	OBJECT-TYPE,
	Integer32,
	NOTIFICATION-TYPE
		FROM SNMPv2-SMI
	hpVCSE-100Gb-F32-Module
		FROM HPSVRMGMT-OID;

syn100GhpeCpuUtilMIB  MODULE-IDENTITY
      LAST-UPDATED "201912190000Z"
      ORGANIZATION "Hewlett Packard Enterprise"
      CONTACT-INFO "Hewlett Packard Enterprise Support Center
                   www.hpe.com/support<http://www.hpe.com/support>
                   US, Canada & Caribbean: 1-800-633-3600
                   UK & Ireland: 0845 161 0050
                   Asia Pacific Region: 61-3-8877-5000"
      DESCRIPTION
          "Initial version of CPU utilization MIB"
      REVISION "201912190000Z"	
	      DESCRIPTION
		  "Initial version."
		  
		  ::= { syn100GhpeSynergyCpuUtilMIBObjects 4130 }

syn100GhpeSynergyCpuUtilMIBObjects OBJECT IDENTIFIER ::= { hpVCSE-100Gb-F32-Module 1 }

-- ------------------------------------------------------------
--         groups in the MIB
-- ------------------------------------------------------------
    syn100GhpeCpuUtilConfig  OBJECT IDENTIFIER ::=  { syn100GhpeCpuUtilMIB 1 }
    syn100GhpeCpuUtiStatus   OBJECT IDENTIFIER ::=  { syn100GhpeCpuUtilMIB 2 }
    syn100GhpeCpuUtilTraps   OBJECT IDENTIFIER ::=  { syn100GhpeCpuUtilMIB 3 }

-- ------------------------------------------------------------------
--         hpeCpuUtilConfig Group
-- ------------------------------------------------------------------
syn100GhpeSwitchMaxCPUThreshold    OBJECT-TYPE
    SYNTAX          Integer32 (1..100)
    MAX-ACCESS      read-write
    STATUS          current
    DESCRIPTION
    "Indicates the maximum CPU usage of the switch in percentage.
     When CPU load exceeds the threshold value,
     an SNMP trap with maximum severity will be sent to the manager."

     DEFVAL { 95 }
     ::= {  syn100GhpeCpuUtilConfig 1 }

syn100GhpeSwitchMinCPUThreshold    OBJECT-TYPE
    SYNTAX          Integer32 (1..100)
    MAX-ACCESS      read-write
    STATUS          current
    DESCRIPTION
    "Indicates the minimum CPU usage of the switch in percentage.
     When CPU load goes below the threshold value,
     an SNMP trap with maximum severity will be sent to the manager."

     DEFVAL { 75 }
     ::= {  syn100GhpeCpuUtilConfig 2 }

-- ------------------------------------------------------------------
--         hpeCpuUtilStatus Group
-- ------------------------------------------------------------------
syn100GhpeSwitchAverageCPUUtilization OBJECT-TYPE
     SYNTAX      Integer32
     UNITS       "percentage"
     MAX-ACCESS  read-only
     STATUS      current
     DESCRIPTION "This object retrieves the average CPU utilization of the switch.
     The average is calculated over 30 samples taken at the interval
     of 10 seconds"
     ::= {  syn100GhpeCpuUtiStatus 1 }

-- ------------------------------------------------------------------
--       hpeCpuUtil Traps
-- ------------------------------------------------------------------

syn100GhpeTrapMaxCPUThreshold NOTIFICATION-TYPE
     OBJECTS      {
                    syn100GhpeSwitchMaxCPUThreshold,
                    syn100GhpeSwitchAverageCPUUtilization
                  }
     STATUS       current
     DESCRIPTION
         "This notification is sent when CPU load exceeds 
          the threshold value"
     ::= { syn100GhpeCpuUtilTraps 1 }

syn100GhpeTrapMinCPUThreshold NOTIFICATION-TYPE
     OBJECTS      {
                    syn100GhpeSwitchMinCPUThreshold,
                    syn100GhpeSwitchAverageCPUUtilization
                  }
     STATUS       current
     DESCRIPTION
         "This notification is sent when CPU load goes below 
          the threshold value"
     ::= { syn100GhpeCpuUtilTraps 2 }

END

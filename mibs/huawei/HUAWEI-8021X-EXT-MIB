-- =====================================================================================
-- Copyright (C) 2018 by  HUAWEI TECHNOLOGIES. All rights reserved.
-- Description:  The MIB module defines the IEEE802.1x protocol MIB objects.
--               IEEE802.1x protocol is mainly used to control the link layer access
--               and identity verification for wireless users.
-- Reference:  
-- Version: V3.34
-- =====================================================================================

    HUAWEI-8021X-EXT-MIB DEFINITIONS ::= BEGIN

        IMPORTS 
            huaweiMgmt            
                FROM HUAWEI-MIB            
            dot1xPaePortNumber            
                FROM IEEE8021-PAE-MIB            
            Unsigned32, Integer32, Counter64, IpAddress, OBJECT-TYPE, MODULE-IDENTITY
                FROM SNMPv2-SMI
            ifIndex
                FROM IF-MIB                
            DisplayString, RowStatus,MacAddress            
                FROM SNMPv2-TC
            InetAddressType, InetAddress
                FROM INET-ADDRESS-MIB;
  

        hwPae8021xExt MODULE-IDENTITY
            LAST-UPDATED "201808210000Z"
            ORGANIZATION "Huawei Technologies Co.,Ltd."
            CONTACT-INFO 
                "Huawei Industrial Base
                 Bantian, Longgang
                 Shenzhen 518129
                 People's Republic of China
                 Website: http://www.huawei.com
                 Email: support@huawei.com
                "
            DESCRIPTION 
                "The MIB module defines the IEEE802.1x protocol MIB objects.
                 IEEE802.1x protocol is mainly used to control the link layer access
                 and identity verification for wireless users."
                 
            --  Revision history
            REVISION     "201808210000Z"
            DESCRIPTION  "V3.34, modified the range and descriptions of hwDot1xQuietPeriodTime, hwDot1xAuthenTimeout, hwDot1xKeepaliveInterval, hwDot1xAuthRequestInterval, 
                          hwDot1xSuppTimeout and hwDot1xReAuthInterval."
                          
            REVISION     "201804040000Z"                          
            DESCRIPTION  "V3.33, added hwOntDot1xMaxRetryTimes,hwOntDot1xQuietPeriodSwitch,hwOntDot1xQuietPeriodTime,hwOntDot1xTxPeriodTime,hwOntDot1xPortUnicastTriggerSwitch 
                          and hwOntDot1xPortMulticastTriggerSwitch."

            REVISION     "201803230000Z"
            DESCRIPTION  "V3.32, modified the descriptions of hwOntDot1xRadiusAuthorServerTable."

            REVISION     "201803200000Z"
            DESCRIPTION  "V3.31, modified the descriptions of hwOntDot1xRadiusAuthorServerTable."
            
            REVISION     "201802260000Z"
            DESCRIPTION  "V3.30, added hwOntDot1xRadiusAcctServerShareKey and hwOntDot1xRadiusSecondaryAcctServerShareKey."
            
            REVISION     "201802110000Z"
            DESCRIPTION  "V3.29, modified the descriptions of hwDot1xReAuthSwitch."			
			
            REVISION     "201801150000Z"
            DESCRIPTION  "V3.28, modified the range of hwDot1xReAuthInterval."
			
            REVISION     "201712150000Z"
            DESCRIPTION  "V3.27, modified the descriptions of hwOntDot1xAcctInterimInterval,hwOntDot1xRadiusServerTimeOut,hwOntDot1xPortRetransmitInterval,hwOntDot1xReAuthPeriod."

            REVISION     "201711150000Z"
            DESCRIPTION  "V3.26, added hwOntDot1xRadiusAcctServerAddrType, hwOntDot1xRadiusAcctServerAddr, hwOntDot1xRadiusAcctServerPort, hwOntDot1xRadiusSecondaryAcctServerAddrType,hwOntDot1xRadiusSecondaryAcctServerAddr,
                          hwOntDot1xRadiusSecondaryAcctServerPort,hwOntDot1xAcctInterimInterval,hwOntDot1xVoiceDeviceControl.
                          added hwOntRadiusStatisticsReceivedAccountingResponseFrames, hwOntRadiusStatisticsReceivedDisconnectRequestFrames, hwOntRadiusStatisticsSentAccountingRequestFrames, 
                          hwOntRadiusStatisticsRetransAccountingRequestFrames, hwOntRadiusStatisticsSentDisconnectAckFrames, hwOntRadiusStatisticsSentDisconnectNakFrames.
                          added new table hwOntDot1xRadiusAuthorServerTable."

            REVISION     "201703290000Z"
            DESCRIPTION  "V3.25, modified the default value of hwOntDot1xPortRetransmitInterval."

            REVISION     "201612210000Z"
            DESCRIPTION  "V3.24, added hwOntDot1xPortMacBypassSwitch, hwOntDot1xPortCriticalVlan and hwOntDot1xRadiusAssignVlan."
			
            REVISION     "201609090000Z"
            DESCRIPTION  "V3.23, modified the descriptions of hwDot1xAuthenTimeout, hwDot1xKeepaliveInterval, hwDot1xQuietPeriodTime, hwDot1xReAuthInterval, hwDot1xAuthRequestInterval and hwDot1xSuppTimeout."
            
            REVISION     "201608230000Z"
            DESCRIPTION  "V3.22, added hwDot1xAuthTimerEffectiveMode, hwDot1xAuthenTimeout, hwDot1xKeepaliveSwitch, hwDot1xKeepaliveRestranTimes, hwDot1xKeepaliveInterval, hwDot1xQuietPeriodTime, hwDot1xReAuthSwitch, hwDot1xReAuthInterval, hwDot1xAuthRequestInterval, hwDot1xRestransmitTimes and hwDot1xSuppTimeout."
                          
            REVISION     "201605130000Z"
            DESCRIPTION  "V3.21, added hwDot1xGuestVlan and hwDot1xRestrictVlan."

            REVISION     "201602240000Z"
            DESCRIPTION  "V3.20, modified the default value of hwDot1xAuthHandshakeCount and hwDot1xAuthHandshakeInterval."

            REVISION     "201507270000Z"
            DESCRIPTION  "V3.19, added new table hwOntDot1xProfileTable, hwOntDot1xPortProfileTable, hwOntPortDot1xStatusTable, hwOntPortDot1xStatisticsTable and hwOntRadiusStatisticsTable."
            
            REVISION     "201105090000Z"
            DESCRIPTION  "V3.18, modified the range of hwDot1xTemplateIndex and hwDot1xPortFramePool."
            
            REVISION     "201011200000Z"
            DESCRIPTION  "V3.17, modified the descriptions of this MIB file and leaves."
                              
            REVISION     "201007290000Z"
            DESCRIPTION  "V3.16, added hwDot1xMacConflictDetectStatus and format to the MIB 
                          file."
            
            REVISION     "201007220000Z"
            DESCRIPTION  "V3.15, modified the descriptions of this MIB file and leaves."
            
            REVISION     "201003160000Z"
            DESCRIPTION  "V3.14, modified the version of this MIB file."   
               
            REVISION     "200912281030Z"
            DESCRIPTION  "V3.11, modified datatype such as INTEGER to Integer32.
                         Moved DEFVAL into DESCRIPTION. 
                         Modified the default values of dot1xAuthSuppTimeout and hwDot1xHandshakeCount 
                         and added the descriptions of hwDot1xTemplateConfigEntry,hwDot1xPortConfigExtEntry 
                         and hwDot1xPortAuthStatsExtEntry "
            
            REVISION     "200905210000Z"
            DESCRIPTION  "V3.09, changed 'anthenrization' to 'authentication' and 'infomation' to 'information'."
                             
            REVISION     "200211290900Z"
            DESCRIPTION  "V2.00, reunification version based on the Fix-Net MIBs baseline by the MIB Standard community."                
            
            ::= { huaweiMgmt 22 }
            
        hwpaeExtMibObjects OBJECT IDENTIFIER ::= { hwPae8021xExt 1 }
        
        hwdot1xPaeSystem OBJECT IDENTIFIER ::= { hwpaeExtMibObjects 1 }
        
        hwdot1xAuthQuietPeriod OBJECT-TYPE
            SYNTAX Unsigned32
            MAX-ACCESS read-write
            STATUS current
            DESCRIPTION
                "Silence period of the system, preventing malicious attack. By 
                 default, it is 60 seconds. DEFVAL { 60 }
                "
            REFERENCE
                " 9.4.1, quietPeriod"
            ::= { hwdot1xPaeSystem 1 }
        
        hwdot1xAuthTxPeriod OBJECT-TYPE
            SYNTAX Unsigned32
            MAX-ACCESS read-write
            STATUS current
            DESCRIPTION
                "Interval period of sending EAP_Request/Id packet. By default,30 seconds.DEFVAL { 30 }
                "
            REFERENCE
                " 
                9.4.1, txPeriod
                "            
            ::= { hwdot1xPaeSystem 2 }
        
        hwdot1xAuthSuppTimeout OBJECT-TYPE
            SYNTAX Unsigned32
            MAX-ACCESS read-write
            STATUS current
            DESCRIPTION
                "Interval period of waiting for the supplicant to response to EAPoL
                 packet.DEFVAL { 30 }
                "
            REFERENCE
                " 
                9.4.1, suppTimeout
                "
            ::= { hwdot1xPaeSystem 3 }
        
        hwdot1xAuthServerTimeout OBJECT-TYPE
            SYNTAX Unsigned32
            MAX-ACCESS read-write
            STATUS current
            DESCRIPTION
                "Configure the period of waiting for the response of Server. By
                 default, it is 30 seconds.DEFVAL { 30 } 
                "
            REFERENCE
                " 
                9.4.1, serverTimeout
                "            
            ::= { hwdot1xPaeSystem 4 }
        
        hwdot1xAuthMaxReq OBJECT-TYPE
            SYNTAX Unsigned32
            MAX-ACCESS read-write
            STATUS current
            DESCRIPTION
                "Maximum times of authentication.DEFVAL { 2 }"
            REFERENCE
                " 
                9.4.1, maxReq
                "            
            ::= { hwdot1xPaeSystem 5 }
        
        hwdot1xAuthReAuthPeriod OBJECT-TYPE
            SYNTAX Unsigned32
            MAX-ACCESS read-write
            STATUS current
            DESCRIPTION
                "Configure the reauthentication period. By default, it is 3600
                 seconds.DEFVAL { 3600 }.
                "
            REFERENCE
                " 
                9.4.1, reAuthPeriod
                "            
            ::= { hwdot1xPaeSystem 6 }
        
        hwdot1xPaeAuthenticator OBJECT IDENTIFIER ::= { hwpaeExtMibObjects 2 }
        
        hwdot1xAuthConfigExtTable OBJECT-TYPE
            SYNTAX SEQUENCE OF Hwdot1xAuthConfigExtEntry
            MAX-ACCESS not-accessible
            STATUS current
            DESCRIPTION
                "It is an extension of the public MIB table dot1xAuthConfigTable, with certain 
                 leaves added for describing the configuration of the object of the port 
                 authenticator. The index of this table is dot1xPaePortNumber.
                "
            REFERENCE
                " 
                9.4.1 Authenticator Configuration
                "
            ::= { hwdot1xPaeAuthenticator 1 }
        
        hwdot1xAuthConfigExtEntry OBJECT-TYPE
            SYNTAX Hwdot1xAuthConfigExtEntry
            MAX-ACCESS not-accessible
            STATUS current
            DESCRIPTION
                "It is an extension of the public MIB table dot1xAuthConfigTable, with certain 
                 leaves added for describing the configuration of the object of the port 
                 authenticator. The index of this entry is dot1xPaePortNumber.
                "
            INDEX { dot1xPaePortNumber }
            ::= { hwdot1xAuthConfigExtTable 1 }
        
        Hwdot1xAuthConfigExtEntry ::=
            SEQUENCE { 
                hwdot1xpaeportAuthAdminStatus
                    INTEGER,
                hwdot1xpaeportControlledType
                    INTEGER,
                hwdot1xpaeportMaxUserNum
                    Integer32,
                hwdot1xpaeportUserNumNow
                    Integer32,
                hwdot1xpaeportClearStatistics
                    INTEGER,
                hwDot1xAuthHandshakeSwitch
                    INTEGER,
                hwDot1xAuthHandshakeCount
                    Integer32,
                hwDot1xAuthHandshakeInterval
                    Integer32, 
                hwDot1xAuthIfEAPEnd
                    INTEGER,
                hwDot1xAuthTimerEffectiveMode
                    BITS                                                      
                }

        hwdot1xpaeportAuthAdminStatus OBJECT-TYPE
            SYNTAX INTEGER
                {
                enabled(1),
                disabled(2)
                }
            MAX-ACCESS read-write
            STATUS current
            DESCRIPTION
                "Indicates he switch of port protocol, enabling or disenabling port 8021X.
                 Options:
                 1. enabled(1)  -indicates port 8021X is enabled
                 2. disabled(2) -indicates port 8021X is disabled
                "
            DEFVAL { 2 }
            ::= { hwdot1xAuthConfigExtEntry 1 }
        
        hwdot1xpaeportControlledType OBJECT-TYPE
            SYNTAX INTEGER
                {
                port(1),
                mac(2)
                }
            MAX-ACCESS read-write
            STATUS current
            DESCRIPTION
                "Port Access Control type, base port access control or base MAC 
                 access control.
                 Options:
                 1. port(1) -base port access control
                 2. mac(2)  -base MAC access control                 
                "
            DEFVAL { 2 }
            ::= { hwdot1xAuthConfigExtEntry 2 }
        
        hwdot1xpaeportMaxUserNum OBJECT-TYPE
            SYNTAX Integer32
            MAX-ACCESS read-write
            STATUS current
            DESCRIPTION
                "Indicates the maximum number of online users in a port.
                "
            DEFVAL { 256 }
            ::= { hwdot1xAuthConfigExtEntry 3 }    
        
        hwdot1xpaeportUserNumNow OBJECT-TYPE
            SYNTAX Integer32
            MAX-ACCESS read-write
            STATUS current
            DESCRIPTION
                "Indicates the number of online users in a port now.
                "
            ::= { hwdot1xAuthConfigExtEntry 4 }
        
        hwdot1xpaeportClearStatistics OBJECT-TYPE
            SYNTAX INTEGER { clear(1) }
            MAX-ACCESS read-write
            STATUS current
            DESCRIPTION
                "Indicates clear various Statistics viz. 
                 Options:
                 1. clear(1)  -indicates clearing various statistics viz
                "
            ::= { hwdot1xAuthConfigExtEntry 5 }     

        hwDot1xAuthHandshakeSwitch OBJECT-TYPE
            SYNTAX INTEGER {open(1),close(0)}
            MAX-ACCESS read-write
            STATUS current
            DESCRIPTION
                "Indicates the status of the handshake function.
                 Options:
                 1. open(1)  -indicates the handshake function is enabled
                 2. close(0) -indicates the handshake function is disabled
                 Default: close(0)
                "
            DEFVAL { 0 }
            ::= { hwdot1xAuthConfigExtEntry 6 }       
            
        hwDot1xAuthHandshakeCount OBJECT-TYPE
            SYNTAX Integer32 (0..10)
            MAX-ACCESS read-write
            STATUS current
            DESCRIPTION
                "Indicates the permitted handshake failures.
                 Range: 0-10
                 The value 0 is meaningless in current version.
                 Default: 3
                "
            DEFVAL { 3 }
            ::= { hwdot1xAuthConfigExtEntry 7 }
        
        hwDot1xAuthHandshakeInterval OBJECT-TYPE
            SYNTAX Integer32 (1..1800)
            MAX-ACCESS read-write
            STATUS current
            DESCRIPTION
                "Indicates the handshake interval.
                 Unit: second
                 Range: 1-1800
                 Default: 15s
                "
            DEFVAL { 15 }
            ::= { hwdot1xAuthConfigExtEntry 8 }  
            
        hwDot1xAuthIfEAPEnd OBJECT-TYPE
            SYNTAX  INTEGER{eapEnd(1),eapRelay(2)}
            MAX-ACCESS read-write
            STATUS current
            DESCRIPTION
                "Indicates which EAP authentication mode is adopted for port or virtual port. 
                 In the 802.1x function, the authentication packet can be processed in two modes: EAP end and EAP relay.
                 Options:
                 1. eapEnd(1)   -indicates the EAP authentication mode is eapEnd
                 2. eapRelay(2) -indicates the EAP authentication mode is eapRelay
                 Default: eapReplay(2)
                "
            DEFVAL {2}
            ::= { hwdot1xAuthConfigExtEntry 9 }  
            
        hwDot1xAuthTimerEffectiveMode OBJECT-TYPE
            SYNTAX BITS
                {
                bAuthenTimeout(0),
                bKeepaliveSwitch(1),
                bKeepaliveRestranTimes(2),
                bKeepaliveInterval(3),
                bQuietPeriodTime(4),
                bReAuthSwitch(5),
                bReAuthInterval(6),
                bRequestInterval(7),
                bRestransmitTimes(8),
                bSuppTimeout(9),
                bDefreserved10(10),
                bDefreserved11(11),
                bDefreserved12(12),
                bDefreserved13(13),
                bDefreserved14(14),
                bDefreserved15(15),
                bDefreserved16(16),
                bDefreserved17(17),
                bDefreserved18(18),
                bDefreserved19(19),
                bDefreserved20(20),
                bDefreserved21(21),
                bDefreserved22(22),
                bDefreserved23(23),
                bDefreserved24(24),
                bDefreserved25(25),
                bDefreserved26(26),
                bDefreserved27(27),
                bDefreserved28(28),
                bDefreserved29(29),
                bDefreserved30(30),
                bDefreserved31(31)
                }           
            MAX-ACCESS read-only
            STATUS current
            DESCRIPTION
                "Indicates the effective mode of the current timer parameters, that is, whether the current timer parameters that take effect are configured globally or based on the flow or port. 
                 Options:
                 1. bAuthenTimeout(0) -Indicates the effective mode of the timeout time for the system to wait for the response packet from the authentication server.
                 2. bKeepaliveSwitch(1) -Indicates the effective mode of the handshake function.
                 3. bKeepaliveRestranTimes(2) -Indicates the effective mode of the number of handshake failures.
                 4. bKeepaliveInterval(3) -Indicates the effective mode of the handshake interval.
                 5. bQuietPeriodTime(4) -Indicates the effective mode of the quiet period.
                 6. bReAuthSwitch(5) -Indicates the effective mode of the re-authentication function.
                 7. bReAuthInterval(6) -Indicates the effective mode of the re-authentication interval.
                 8. bRequestInterval(7) -Indicates the effective mode of the timeout time for the system to wait for the response from the client during authentication.
                 9. bRestransmitTimes(8) -Indicates the effective mode of the times of re-transmitting packets to the client.
                 10. bSuppTimeout(9) -Indicates the effective mode of the timeout time for the system to wait for the response from the client.
                 Other bits are reserved. For each bit, when the corresponding bit of hwDot1xAuthTimerEffectiveMode is 1,
                 1 indicates that the current timer parameters are configured based on the flow and port. 0 indicates that the current timer parameters are configured globally. 
                 Default: 0                              
                "
            ::= { hwdot1xAuthConfigExtEntry 10 }
                                                                       
        hwDot1xMibObjects OBJECT IDENTIFIER ::= {  hwpaeExtMibObjects 3  } 
       
        hwDHCPTripperStatus OBJECT-TYPE 
        SYNTAX   INTEGER { enabled(1), disabled(2) }            
        MAX-ACCESS  read-write
        STATUS      current
        DESCRIPTION
            "The device processes the DHCP DISCOVER and DHCP REQUEST packets only after 
             the DHCP-trigger authentication function is enabled. Otherwise, the device 
             does not process the DHCP DISCOVER or DHCP REQUEST packet. After the 
             DHCP-trigger authentication function is enabled, the device triggers the 
             authentication when receiving the DHCP DISCOVER and DHCP REQUEST packets.
             Indicates the status of the DHCP-trigger authentication function of the device.
             Options:
             1. enabled(1)  -indicates the DHCP-trigger authentication function is enabled
             2. disabled(2) -indicates the DHCP-trigger authentication function is disabled
             Default: disable(2)
            "
        
        ::= { hwDot1xMibObjects 1 }
                                          
                                        
        hwDot1xTemplateConfigTable OBJECT-TYPE
            SYNTAX SEQUENCE OF HwDot1xTemplateConfigEntry
            MAX-ACCESS not-accessible
            STATUS current
            DESCRIPTION
                "It is used to configure the profile used to control the user authentication 
                 through 802.1x. Profile 1 exists permanently, and it cannot be created or deleted. 
                 Other profiles can be created or deleted. The index of this table is hwDot1xTemplateIndex. 
                 This table supports only the profile mode. To create a profile, set hwDot1xTempRowStatus 
                 to createAndGo(4). The index is the ID of the profile to be created. To delete a profile, 
                 set hwDot1xTempRowStatus to destroy(6). The index is the ID of the profile to be deleted.
                "
            ::= { hwDot1xMibObjects 2 }
        
        hwDot1xTemplateConfigEntry OBJECT-TYPE
            SYNTAX HwDot1xTemplateConfigEntry
            MAX-ACCESS not-accessible
            STATUS current
            DESCRIPTION
                "It is used to configure the profile used to control the user authentication 
                 through 802.1x. Profile 1 exists permanently, and it cannot be created or deleted. 
                 Other profiles can be created or deleted. The index of this entry is hwDot1xTemplateIndex. 
                 This table supports only the profile mode. To create a profile, set hwDot1xTempRowStatus 
                 to createAndGo(4). The index is the ID of the profile to be created. To delete a profile, 
                 set hwDot1xTempRowStatus to destroy(6). The index is the ID of the profile to be deleted.
                "
            INDEX { hwDot1xTemplateIndex }
            ::= { hwDot1xTemplateConfigTable 1 }
        
        HwDot1xTemplateConfigEntry ::=
            SEQUENCE { 
                hwDot1xTemplateIndex
                    Integer32,                    
                hwDot1xHandshakeSwitch
                    INTEGER,
                hwDot1xHandshakeCount
                    Integer32,
                hwDot1xHandshakeInterval
                    Integer32, 
                 hwDot1xIfEAPEnd
                    INTEGER,                 
                hwDot1xTempIfUsed
                    INTEGER,        
                   hwDot1xTempRowStatus
                    RowStatus
                }

        hwDot1xTemplateIndex OBJECT-TYPE
            SYNTAX Integer32(0..256)
            MAX-ACCESS not-accessible
            STATUS current
            DESCRIPTION
                "Indicates the profile ID.
                 Range: 1-256
                "
            ::= { hwDot1xTemplateConfigEntry 1 }  
            
        hwDot1xHandshakeSwitch OBJECT-TYPE
            SYNTAX INTEGER {open(1),close(0)}
            MAX-ACCESS read-only
            STATUS current
            DESCRIPTION
                "Indicates the status of the handshake function.
                 Options:
                 1. open(1)  -indicates the handshake function is enabled
                 2. close(0) -indicates the handshake function is disabled
                 Default: close(0)
                "
            ::= { hwDot1xTemplateConfigEntry 2 }
        
        hwDot1xHandshakeCount OBJECT-TYPE
            SYNTAX Integer32 (0..10)
            MAX-ACCESS read-write
            STATUS current
            DESCRIPTION
                "Indicates the permitted handshake failures.
                 Range: 0-10
                 Default: 0
                "
            DEFVAL { 0 }
            ::= { hwDot1xTemplateConfigEntry 3 }
        
        hwDot1xHandshakeInterval OBJECT-TYPE
            SYNTAX Integer32 (1..1800)
            MAX-ACCESS read-write
            STATUS current
            DESCRIPTION
                "Indicates the handshake interval.
                 Unit: second
                 Range: 1-1800
                 Default: 15s
                "
            DEFVAL { 20 }
            ::= { hwDot1xTemplateConfigEntry 4 }  
            
        hwDot1xIfEAPEnd OBJECT-TYPE
            SYNTAX  INTEGER{eapEnd(1),eapRelay(2)}
            MAX-ACCESS read-write
            STATUS current
            DESCRIPTION
                "Indicates which EAP authentication mode is adopted for the specified 802.1x profile. 
                 In the 802.1x function, the authentication packet can be processed in two modes: 
                 EAP end and EAP relay.
                 Options:
                 1. eapEnd(1)   -indicates the EAP end authentication mode. If local user authenticates on 
                                 DSLAM directly, it does not need to communicate with the remote RADIUS server.
                                 If the user is not local user, it must be authenticated on the remote RADIUS 
                                 server. 
                 2. eapRelay(2) -the user must be authenticated on the remote RADIUS server
                 Default: eapReplay(2)
                "                    
            DEFVAL {2}               
            ::= { hwDot1xTemplateConfigEntry 5 }
                                     
        hwDot1xTempIfUsed OBJECT-TYPE
            SYNTAX  INTEGER {used(1),unused(0)}
            MAX-ACCESS read-only
            STATUS current
            DESCRIPTION
                "Indicates whether the profile is used. When a profile is not used, 
                 the profile can be deleted.
                 Options:
                 1. used(1)   -indicates the profile is used
                 2. unused(0) -indicates the profile is not used
                 Default: unused(0)
                "            
            ::= {hwDot1xTemplateConfigEntry 6 }
                 
        hwDot1xTempRowStatus OBJECT-TYPE
            SYNTAX RowStatus
            MAX-ACCESS read-create
            STATUS current
            DESCRIPTION
                "Indicates the operation type of the table.
                 Options:
                 1. active(1)      -indicates query operation
                 2. createAndGo(4) -indicates creating a profile
                 3. destroy(6)     -indicates deleting a profile
                "
            ::= {hwDot1xTemplateConfigEntry 7 } 
                 
        hwDot1xPortConfigExtTable OBJECT-TYPE
            SYNTAX SEQUENCE OF HwDot1xPortConfigExtEntry
            MAX-ACCESS not-accessible
            STATUS current
            DESCRIPTION
                "It is an extension table of dot1xPaePortTable and is used for describing 
                 the authorization mode and authentication status of the port. The index 
                 of this table is dot1xPaePortNumber (defined in dot1xPaePortTable). This 
                 version supports authentication based on the port or service port; therefore, 
                 dot1xPaePortNumber indicates the ID of a port or service port. When the 
                 input value exceeds the maximum ID of the service port, dot1xPaePortNumber 
                 is treated as ifIndex. The range of the service port IDs depends on the version.
                 This table supports the creation of the port table. After the port table 
                 is created, the 802.1x authentication is bound to the port.
                 The create operation is as follows:
                 Specify the ID of the port to which the 802.1x authentication needs to be bound.
                 Set hwDot1xPortRowStatus to createAndGo(4), and issue the set operation.
                 Optionally specify hwDot1xPortMacControl. However, if the ID of the port is 
                 the ID of the service port, hwDot1xPortMacControl cannot be specified. 
                 hwDot1xPortMacControl cannot be issued independently, and it must be issued 
                 together with hwDot1xPortRowStatus during the create operation.
                "
            ::= { hwDot1xMibObjects 3 }
        
        hwDot1xPortConfigExtEntry OBJECT-TYPE
            SYNTAX HwDot1xPortConfigExtEntry
            MAX-ACCESS not-accessible
            STATUS current
            DESCRIPTION
                "It is an extension table of dot1xPaePortTable and is used for describing 
                 the authorization mode and authentication status of the port. The index 
                 of this entry is dot1xPaePortNumber (defined in dot1xPaePortTable). This 
                 version supports authentication based on the port or service port; therefore, 
                 dot1xPaePortNumber indicates the ID of a port or service port. When the 
                 input value exceeds the maximum ID of the service port, dot1xPaePortNumber 
                 is treated as ifIndex. The range of the service port IDs depends on the version.
                 This table supports the creation of the port table. After the port table 
                 is created, the 802.1x authentication is bound to the port.
                 The create operation is as follows:
                 Specify the ID of the port to which the 802.1x authentication needs to be bound.
                 Set hwDot1xPortRowStatus to createAndGo(4), and issue the set operation.
                 Optionally specify hwDot1xPortMacControl. However, if the ID of the port is 
                 the ID of the service port, hwDot1xPortMacControl cannot be specified. 
                 hwDot1xPortMacControl cannot be issued independently, and it must be issued 
                 together with hwDot1xPortRowStatus during the create operation.
                "
            INDEX { dot1xPaePortNumber }
            ::= { hwDot1xPortConfigExtTable 1 }  
            
        HwDot1xPortConfigExtEntry ::=
            SEQUENCE { 
                hwDot1xPortControlType
                    INTEGER,
                hwDot1xPortBindFlag
                    INTEGER, 
                hwDot1xPortAuthMode
                    INTEGER,
                hwDot1xPortAuthState
                    INTEGER,
                hwDot1xPortUserName
                    OCTET STRING,
                hwDot1xPortFramePool
                    DisplayString,
                hwDot1xPortRowStatus 
                    RowStatus,
                hwDot1xPortMacControl
                    INTEGER,
                hwDot1xGuestVlan
                    Integer32,
                hwDot1xRestrictVlan
                    Integer32
                }
                  
        hwDot1xPortControlType OBJECT-TYPE
            SYNTAX INTEGER{physicalPort(1),servicePort(2)}
            MAX-ACCESS read-only
            STATUS current
            DESCRIPTION
                "Indicates the control type of the port. The port can be controlled in the 
                 following two ways: physical port control and service port control.
                 Options:
                 1. physicalPort(1) -physical port control
                 2. servicePort(2)  -service port control
                "
            ::= { hwDot1xPortConfigExtEntry 1 } 
            
        hwDot1xPortBindFlag OBJECT-TYPE
            SYNTAX   INTEGER{binding(1)}
            MAX-ACCESS read-only 
            STATUS current
            DESCRIPTION
                "Indicates that the 802.1x authentication is bound to the port.
                 Options: 
                 1. binding(1) -indicates the 802.1x authentication is bound to the port
                "                                
            ::= { hwDot1xPortConfigExtEntry 2 } 
            
        hwDot1xPortAuthMode OBJECT-TYPE
            SYNTAX INTEGER{forceUnauthorized(1),auto(2),forceAuthorized(3)}
            MAX-ACCESS read-write 
            STATUS current
            DESCRIPTION
                "Indicates the control parameters of the controlled port. A port has three 
                 authorization control modes: force-authorized mode, force-unauthorized mode, 
                 and auto mode. According to different networks, different port control modes 
                 can be selected. By default, a port is in the unauthorized state, and users 
                 connected to the port cannot access network resources. If the authentication 
                 passes, the port state switches to the authorized state and users can access 
                 the network resources.
                 Options:
                 1. forceUnauthorized(1) -indicates force-authorized mode
                 2. auto(2)              -auto mode
                 3. forceAuthorized(3)   -indicates force-unauthorized mode
                 Default: auto(2)
                "              
            DEFVAL { 2 }
            ::= { hwDot1xPortConfigExtEntry 3 } 
            
        hwDot1xPortAuthState OBJECT-TYPE
            SYNTAX INTEGER {auth(1),unAuth(2)}
            MAX-ACCESS read-only 
            STATUS current
            DESCRIPTION
                "Indicates the port authentication status.
                 Options:
                 1. auth(1)   -indicates the port is authenticated
                 2. unAuth(2) -indicates the port is not authenticated
                 Default: unauth(2)
                "                          
            ::= { hwDot1xPortConfigExtEntry 4 }
            
        hwDot1xPortUserName OBJECT-TYPE
            SYNTAX      OCTET STRING(SIZE(0..64))
            MAX-ACCESS read-only 
            STATUS current
            DESCRIPTION
                "Indicates the user name bound to the port.
                "     
            ::= { hwDot1xPortConfigExtEntry 5 }
    
       hwDot1xPortFramePool OBJECT-TYPE
            SYNTAX DisplayString (SIZE(0..255))
            MAX-ACCESS read-only 
            STATUS current
            DESCRIPTION
                "Indicates the address pool of the port binding.
                "     
            ::= { hwDot1xPortConfigExtEntry 6 }
            
       hwDot1xPortRowStatus OBJECT-TYPE
            SYNTAX   RowStatus
            MAX-ACCESS read-create
            STATUS current
            DESCRIPTION
                "Indicates the operation type of the port table: binding the port to the 802.1x 
                 authentication, and unbinding the port from the 802.1x authentication.
                 Options:
                 1. active(1)      -indicates query operation
                 2. createAndGo(4) -indicates binding a port to the 802.1x authentication
                 3. destroy(6)     -indicates unbinding a port from the 802.1x authentication
                "                                
            ::= { hwDot1xPortConfigExtEntry 7}          
            
       hwDot1xPortMacControl OBJECT-TYPE
            SYNTAX INTEGER{enable(1),disable(2)}
            MAX-ACCESS read-write
            STATUS current
            DESCRIPTION
                "Indicates whether to enable the MAC-based control function. This leaf can be 
                 issued with parameters during the create operation. This function supports 
                 port-based rather than service-port-based configuration. When hwDot1xPortMacControl 
                 is set to enable(1), only the packets whose source MAC address is the MAC address 
                 of the authorized user can reach the network side. This leaf does not support the 
                 modify operation.
                 Options:
                 1. enable(1)  -indicates the MAC-based control function is enabled
                 2. disable(2) -indicates the MAC-based control function is disabled
                 Default: disable(2)
                "
            ::= { hwDot1xPortConfigExtEntry 8} 
                    
            hwDot1xGuestVlan OBJECT-TYPE
            SYNTAX Integer32 (-1 | 1..4093)
            MAX-ACCESS read-write 
            STATUS current
            DESCRIPTION
                "Indicates the 802.1x guest VLAN.
                Range: -1, 1-4093, -1 indicates an invalid value, a value between 1 and 4093 indicates the VLAN ID.
                "
            ::= { hwDot1xPortConfigExtEntry 9} 

            hwDot1xRestrictVlan OBJECT-TYPE
            SYNTAX Integer32 (-1 | 1..4093)
            MAX-ACCESS read-write 
            STATUS current
            DESCRIPTION
                "Indicates the 802.1x restrict VLAN.
                Range: -1, 1-4093, -1 indicates an invalid value, a value between 1 and 4093 indicates the VLAN ID.
                "
            ::= { hwDot1xPortConfigExtEntry 10 }
              
        hwDot1xPortAuthStatsExtTable OBJECT-TYPE
            SYNTAX SEQUENCE OF HwDot1xPortAuthStatsExtEntry
            MAX-ACCESS not-accessible
            STATUS current
            DESCRIPTION
                "It is an extension of the public MIB table dot1xAuthStatsEntry, with certain leaves 
                 added for describing the packet statistics of the port. The index of this table is 
                 dot1xPaePortNumber (defined in dot1xPaePortTable). The following tables list the 
                 leaves of this table.
                 Only hwDot1xPortClearStatistics in this table supports the modify operation.
                 The modification process is as follows:
                 Specify the ID of the port to be modified. 
                 Set hwDot1xPortClearStatistics to the required value. The option is clear(1). 
                 Therefore, directly perform the set operation.
                "
            ::= { hwDot1xMibObjects 4 } 
            
        hwDot1xPortAuthStatsExtEntry OBJECT-TYPE
            SYNTAX HwDot1xPortAuthStatsExtEntry
            MAX-ACCESS not-accessible
            STATUS current
            DESCRIPTION
                "It is an extension of the public MIB table dot1xAuthStatsEntry, with certain leaves 
                 added for describing the packet statistics of the port. The index of this entry is 
                 dot1xPaePortNumber (defined in dot1xPaePortTable). The following tables list the 
                 leaves of this table.
                 Only hwDot1xPortClearStatistics in this table supports the modify operation.
                 The modification process is as follows:
                 Specify the ID of the port to be modified. 
                 Set hwDot1xPortClearStatistics to the required value. The option is clear(1). 
                 Therefore, directly perform the set operation.
                "
            INDEX { dot1xPaePortNumber }
            ::= { hwDot1xPortAuthStatsExtTable 1 } 
           
        HwDot1xPortAuthStatsExtEntry ::=
            SEQUENCE { 
                hwDot1xAuthSuccessTimes  
                    Integer32, 
                hwDot1xAuthFailureTimes
                    Integer32,        
                hwDot1xEapolFailurePacketsTx
                    Integer32,
                hwDot1xEapolSuccessPacketsTx
                    Integer32,
                hwDot1xNoSupportPacketsRx
                    Integer32,
                hwDot1xPortClearStatistics
                    INTEGER   
                }   
                              
      hwDot1xAuthSuccessTimes OBJECT-TYPE
          SYNTAX   Integer32
          MAX-ACCESS read-only
          STATUS current
          DESCRIPTION
              "Indicates the number of authentication successes.
              "                            
          ::= { hwDot1xPortAuthStatsExtEntry 1} 

        hwDot1xAuthFailureTimes OBJECT-TYPE
            SYNTAX   Integer32
            MAX-ACCESS read-only
            STATUS current
            DESCRIPTION
              "Indicates the number of authentication failures.
              "                                
            ::= { hwDot1xPortAuthStatsExtEntry 2} 
     
        hwDot1xEapolFailurePacketsTx OBJECT-TYPE
            SYNTAX   Integer32
            MAX-ACCESS read-only
            STATUS current
            DESCRIPTION
              "Indicates the number of the transmitted Eapol-Failure packets.
              "                                
            ::= { hwDot1xPortAuthStatsExtEntry 3} 
            
        hwDot1xEapolSuccessPacketsTx OBJECT-TYPE
            SYNTAX   Integer32
            MAX-ACCESS read-only
            STATUS current
            DESCRIPTION
              "Indicates the number of the transmitted Eapol-Success packets.
              "                                
            ::= { hwDot1xPortAuthStatsExtEntry 4}  
            
        hwDot1xNoSupportPacketsRx OBJECT-TYPE
            SYNTAX   Integer32
            MAX-ACCESS read-only
            STATUS current
            DESCRIPTION
                "Indicates the number of the unsupported EAPoL packets that are received.
                "                                
            ::= { hwDot1xPortAuthStatsExtEntry 5}             
               
        hwDot1xPortClearStatistics OBJECT-TYPE
            SYNTAX   INTEGER {clear(1)}
            MAX-ACCESS read-write
            STATUS current
            DESCRIPTION
                "Clears the port statistics.
                 Options:
                 1. clear(1) -indicates clearing the port statistics
                "                                
            ::= { hwDot1xPortAuthStatsExtEntry 6}
        
        hwDot1xAutoDetect OBJECT-TYPE 
            SYNTAX   INTEGER { enabled(1), disabled(2) }            
            MAX-ACCESS  read-write
            STATUS      current
            DESCRIPTION
                "Indicates the status of the auto-detect function of the device. After the 802.1x 
                 auto-detect function is enabled, the system automatically detects the port status 
                 and requests the user authentication.
                 Options:
                 1. enabled(1)  -indicates the auto-detect function of the device is enabled
                 2. disabled(2) -indicates the auto-detect function of the device is disabled
                 Default: disable(2)
                "        
            ::= { hwDot1xMibObjects 5 }
        
        hwDot1xIntermittentBlinkingProtection OBJECT-TYPE 
            SYNTAX   INTEGER { enabled(1), disabled(2) }            
            MAX-ACCESS  read-write
            STATUS      current
            DESCRIPTION
                "Indicates the intermittent blinking protection function, which is used to reduce 
                 the duration of service interruption caused by port intermittent blinking. After 
                 the intermittent blinking protection function is enabled, the system does not force 
                 the 802.1x user to go offline when the port is down. In this case, if the handshake 
                 function is already enabled, the system detects the user by using the handshake 
                 mechanism; if the handshake function is disabled, the system waits for the duration 
                 of keepalive interval x number of handshake failures, and then forces the user to 
                 go offline if the port is still down. After the intermittent blinking protection 
                 function is enabled, the count of user online duration may be incorrect. Therefore, 
                 this function is applicable to the provisioning of services with the monthly flat 
                 rate rather than in the duration-based charging mode.
                 Indicates the status of the intermittent blinking protection function of the device.
                 Options:
                 1. enabled(1)  -indicates the intermittent blinking protection function is enabled
                 2. disabled(2) -indicates the intermittent blinking protection function is disabled
                 Default: disable(2)
                "        
            ::= { hwDot1xMibObjects 6 }

        hwDot1xGlobalMacControlStatus OBJECT-TYPE 
              SYNTAX   INTEGER { enabled(1), disabled(2) }                        
              MAX-ACCESS  read-write
              STATUS      current
              DESCRIPTION
                   "Whether the global mac control is enabled in the device.
                    Enable indicate that global mac control enable in the device;
                    Disabled indicate that global mac control disable in the device.           
                    DEFVAL      { 2 }
                    Options:
                    1. enabled(1)  -indicates the global mac control is enabled
                    2. disabled(2) -indicates the global mac control is disabled
                   "
                  ::= { hwDot1xMibObjects 7 }

        hwDot1xMacPortInfoTable OBJECT-TYPE
              SYNTAX SEQUENCE OF HwDot1xMacPortInfoEntry
              MAX-ACCESS not-accessible
              STATUS current
              DESCRIPTION
                   "This table describes the port information of 802.1x,
                    The index of this table is mac address.
                   "
              ::= { hwDot1xMibObjects 8 } 

        hwDot1xMacPortInfoEntry OBJECT-TYPE
              SYNTAX HwDot1xMacPortInfoEntry
              MAX-ACCESS not-accessible
              STATUS current
              DESCRIPTION
                   "This table describes the port information of 802.1x,
                    The index of this entry is mac address.
                   "
              INDEX { hwDot1xMacPortInfoMacAddress }
              ::= { hwDot1xMacPortInfoTable 1 }                         
                        
        HwDot1xMacPortInfoEntry ::=
        SEQUENCE {
                   hwDot1xMacPortInfoMacAddress
                   MacAddress,
                   hwDot1xMacPortInfoAuthState
                   Unsigned32, 
                   hwDot1xMacPortInfoAuthType 
                   Unsigned32 
                 }
                        
        hwDot1xMacPortInfoMacAddress OBJECT-TYPE
              SYNTAX MacAddress
              MAX-ACCESS not-accessible
              STATUS current
              DESCRIPTION
                   "Mac address.                                
                   "
              ::= { hwDot1xMacPortInfoEntry 1 }          
                        
        hwDot1xMacPortInfoAuthState OBJECT-TYPE
              SYNTAX Unsigned32
              MAX-ACCESS read-only
              STATUS current
                  DESCRIPTION
                   "Authentication state.                                
                   "
              ::= { hwDot1xMacPortInfoEntry 2 }
                         
        hwDot1xMacPortInfoAuthType OBJECT-TYPE
                 SYNTAX Unsigned32
              MAX-ACCESS read-only
              STATUS current
              DESCRIPTION
                   "Authentication Type.
                   "
              ::= { hwDot1xMacPortInfoEntry 3 }                        

        hwDot1xMacPortStatTable OBJECT-TYPE
              SYNTAX SEQUENCE OF HwDot1xMacPortStatEntry
              MAX-ACCESS not-accessible
              STATUS current
              DESCRIPTION
                   "This table describes the port statistics of 802.1x,
                    The index of this table is mac address.
                   "
              ::= { hwDot1xMibObjects 9 } 
                        
        hwDot1xMacPortStatEntry OBJECT-TYPE
              SYNTAX HwDot1xMacPortStatEntry
              MAX-ACCESS not-accessible
              STATUS current
              DESCRIPTION
                   "This table describes the port statistics of 802.1x,
                    The index of this entry is mac address.
                   "
              INDEX { hwDot1xMacPortInfoMacAddress }
              ::= { hwDot1xMacPortStatTable 1 }                         
                        
        HwDot1xMacPortStatEntry ::=
              SEQUENCE { 
                                hwDot1xMacPortStatAuthSuccessTimes  
                                                Unsigned32, 
                                hwDot1xMacPortStatAuthFailureTimes
                                                Unsigned32,        
                                hwDot1xMacPortStatEapolFailurePacketsTx
                                                Unsigned32,
                                hwDot1xMacPortStatEapolSuccessPacketsTx
                                                Unsigned32,
                                hwDot1xMacPortStatNoSupportPacketsRx
                                                Unsigned32,
                                hwDot1xMacPortStatClearStatistics
                                                INTEGER, 
                                hwDot1xMacPortStatAuthEapolFramesRx
                                                Unsigned32, 
                                hwDot1xMacPortStatAuthEapolFramesTx
                                                Unsigned32, 
                                hwDot1xMacPortStatAuthEapolStartFramesRx
                                                Unsigned32, 
                                hwDot1xMacPortStatAuthEapolLogoffFramesRx
                                                Unsigned32, 
                                hwDot1xMacPortStatAuthEapolRespIdFramesRx
                                                Unsigned32, 
                                hwDot1xMacPortStatAuthEapolRespFramesRx
                                                Unsigned32, 
                                hwDot1xMacPortStatAuthEapolReqIdFramesTx
                                                Unsigned32, 
                                hwDot1xMacPortStatAuthEapolReqFramesTx
                                                Unsigned32, 
                                hwDot1xMacPortStatAuthInvalidEapolFramesRx
                                                Unsigned32, 
                                hwDot1xMacPortStatAuthEapLengthErrorFramesRx
                                                Unsigned32, 
                                hwDot1xMacPortStatAuthLastEapolFrameVersion
                                                Unsigned32, 
                                hwDot1xMacPortStatAuthEapolKeyFramesRx
                                                Unsigned32,     
                                hwDot1xMacPortStatAuthEapolKeyFramesTx
                                                Unsigned32,  
                                hwDot1xMacPortStatAuthEapolPeapFramesRx
                                                Unsigned32,    
                                hwDot1xMacPortStatAuthEapolPeapFramesTx
                                                Unsigned32 
                                  }
                                  
        hwDot1xMacPortStatAuthSuccessTimes OBJECT-TYPE
                SYNTAX   Unsigned32
                MAX-ACCESS read-only
                STATUS current
                DESCRIPTION
                        "Authentication success times
                        "                                
                ::= { hwDot1xMacPortStatEntry 1} 

        hwDot1xMacPortStatAuthFailureTimes OBJECT-TYPE
                SYNTAX   Unsigned32
                MAX-ACCESS read-only
                STATUS current
                DESCRIPTION
                        "Authentication Failure times
                         "                                
                ::= { hwDot1xMacPortStatEntry 2} 
             
        hwDot1xMacPortStatEapolFailurePacketsTx OBJECT-TYPE
                SYNTAX   Unsigned32
                MAX-ACCESS read-only
                STATUS current
                DESCRIPTION
                       "The numbers of the Eapol-Failure Packets which has been send by the port
                       "                                
                ::= { hwDot1xMacPortStatEntry 3} 
                        
        hwDot1xMacPortStatEapolSuccessPacketsTx OBJECT-TYPE
                SYNTAX   Unsigned32
                MAX-ACCESS read-only
                STATUS current
                DESCRIPTION
                        "The numbers of the Eapol-Success Packets which has been send by the port
                         "                                
                ::= { hwDot1xMacPortStatEntry 4}
                        
        hwDot1xMacPortStatNoSupportPacketsRx OBJECT-TYPE
                SYNTAX   Unsigned32
                MAX-ACCESS read-only
                STATUS current
                DESCRIPTION
                        "The numbers of the Eapol packets  which  are not supported have been
                         received in this port
                        "                                
                ::= { hwDot1xMacPortStatEntry 5}                         
                       
        hwDot1xMacPortStatClearStatistics OBJECT-TYPE
                SYNTAX   INTEGER {clear(1)}
                MAX-ACCESS read-write
                STATUS current
                DESCRIPTION
                        "Clear the information of the packets statistics in this port
                         Options:
                         1. clear(1)  -indicates clearing the information of the packets statistics in this port
                        "                                
                ::= { hwDot1xMacPortStatEntry 6}        
                  
        hwDot1xMacPortStatAuthEapolFramesRx OBJECT-TYPE
                SYNTAX Unsigned32
                MAX-ACCESS read-only
                STATUS current
                DESCRIPTION
                        "The number of valid EAPOL frames of any type
                         that has been received by this Authenticator.
                        "                
                ::= { hwDot1xMacPortStatEntry 7 }
                
        hwDot1xMacPortStatAuthEapolFramesTx OBJECT-TYPE
                SYNTAX Unsigned32
                MAX-ACCESS read-only
                STATUS current
                DESCRIPTION
                        "The number of EAPOL frames of any type
                         that has been transmitted by this Authenticator.
                        "                
                ::= { hwDot1xMacPortStatEntry 8 }
                
        hwDot1xMacPortStatAuthEapolStartFramesRx OBJECT-TYPE
                SYNTAX Unsigned32
                MAX-ACCESS read-only
                STATUS current
                DESCRIPTION
                        "The number of EAPOL Start frames that have
                         been received by this Authenticator.
                        "
                ::= { hwDot1xMacPortStatEntry 9 }
                
        hwDot1xMacPortStatAuthEapolLogoffFramesRx OBJECT-TYPE
                SYNTAX Unsigned32
                MAX-ACCESS read-only
                STATUS current
                DESCRIPTION
                       "The number of EAPOL Logoff frames that have
                        been received by this Authenticator.
                       "
                ::= { hwDot1xMacPortStatEntry 10 }
                
        hwDot1xMacPortStatAuthEapolRespIdFramesRx OBJECT-TYPE
                SYNTAX Unsigned32
                MAX-ACCESS read-only
                STATUS current
                DESCRIPTION
                        "The number of EAP Resp/Id frames that have
                         been received by this Authenticator.
                        "
                ::= { hwDot1xMacPortStatEntry 11 }
                
        hwDot1xMacPortStatAuthEapolRespFramesRx OBJECT-TYPE
                SYNTAX Unsigned32
                MAX-ACCESS read-only
                STATUS current
                DESCRIPTION
                        "The number of valid EAP Response frames
                         (other than Resp/Id frames) that have been
                         received by this Authenticator.
                        "
                ::= { hwDot1xMacPortStatEntry 12 }
                
        hwDot1xMacPortStatAuthEapolReqIdFramesTx OBJECT-TYPE
                SYNTAX Unsigned32
                MAX-ACCESS read-only
                STATUS current
                DESCRIPTION
                        "The number of EAP Req/Id frames that have been
                         transmitted by this Authenticator.
                        "
                ::= { hwDot1xMacPortStatEntry 13 }
                
        hwDot1xMacPortStatAuthEapolReqFramesTx OBJECT-TYPE
                SYNTAX Unsigned32
                MAX-ACCESS read-only
                STATUS current
                DESCRIPTION
                        "The number of EAP Request frames
                         (other than Rq/Id frames) that have been
                         transmitted by this Authenticator.
                        "
                ::= { hwDot1xMacPortStatEntry 14 }
                
        hwDot1xMacPortStatAuthInvalidEapolFramesRx OBJECT-TYPE
                SYNTAX Unsigned32
                MAX-ACCESS read-only
                STATUS current
                DESCRIPTION
                        "The number of EAPOL frames that have been
                         received by this Authenticator in which the
                         frame type is not recognized.
                        "
                ::= { hwDot1xMacPortStatEntry 15 }
                
        hwDot1xMacPortStatAuthEapLengthErrorFramesRx OBJECT-TYPE
                SYNTAX Unsigned32
                MAX-ACCESS read-only
                STATUS current
                DESCRIPTION
                        "The number of EAPOL frames that have been received
                         by this Authenticator in which the Packet Body
                         Length field is invalid.
                        "
                
                ::= { hwDot1xMacPortStatEntry 16 }
                
        hwDot1xMacPortStatAuthLastEapolFrameVersion OBJECT-TYPE
                SYNTAX Unsigned32
                MAX-ACCESS read-only
                STATUS current
                DESCRIPTION
                        "The protocol version number carried in the
                         most recently received EAPOL frame.
                        "
                
                ::= { hwDot1xMacPortStatEntry 17 }
                
        hwDot1xMacPortStatAuthEapolKeyFramesRx OBJECT-TYPE
                SYNTAX Unsigned32
                MAX-ACCESS read-only
                STATUS current
                DESCRIPTION
                        "The number of EAPOL key frames that have been received
                         by this Authenticator.
                        "
                ::= { hwDot1xMacPortStatEntry 18 }        
                
        hwDot1xMacPortStatAuthEapolKeyFramesTx OBJECT-TYPE
                SYNTAX Unsigned32
                MAX-ACCESS read-only
                STATUS current
                DESCRIPTION
                        "The number of EAPOL key frames that have been sent
                         by this Authenticator.
                        "
                ::= { hwDot1xMacPortStatEntry 19 }                        
                
        hwDot1xMacPortStatAuthEapolPeapFramesRx OBJECT-TYPE
                SYNTAX Unsigned32
                MAX-ACCESS read-only
                STATUS current
                        DESCRIPTION
                        "The number of EAPOL peap frames that have been received
                         by this Authenticator.
                        "
                ::= { hwDot1xMacPortStatEntry 20 }                
                
        hwDot1xMacPortStatAuthEapolPeapFramesTx OBJECT-TYPE
                SYNTAX Unsigned32
                MAX-ACCESS read-only
                STATUS current
                DESCRIPTION
                        "The number of EAPOL peap frames that have been sent
                         by this Authenticator.
                        "
                ::= { hwDot1xMacPortStatEntry 21 }
                  
        hwDot1xMacConflictDetectStatus OBJECT-TYPE 
              SYNTAX   INTEGER { enabled(1), disabled(2) }                        
              MAX-ACCESS  read-write
              STATUS      current
              DESCRIPTION
                   "Indicates the status of the mac-conflict-detect function of the device. After the 
                    802.1x mac-conflict-detect function is enabled, the system detects the mac conflicts.
                    Options:
                    1. enabled(1)  -indicates the mac-conflict-detect of the device is enabled
                    2. disabled(2) -indicates the mac-conflict-detect of the device is disabled
                    Default: disable(2)
                   "
                  ::= { hwDot1xMibObjects 10 }  

        hwDot1xAuthenTimeout OBJECT-TYPE
              SYNTAX Integer32(100..600)
              MAX-ACCESS read-write
              STATUS current
              DESCRIPTION
                   "The value, in seconds, of the serverTimeout constant currently in use by the Backend Authentication state machine.
                    Unit: second
                   "
                  ::= { hwDot1xMibObjects 11 }  
            
        hwDot1xKeepaliveSwitch OBJECT-TYPE
              SYNTAX INTEGER {open(1),close(0)}
              MAX-ACCESS read-write
              STATUS current
              DESCRIPTION
                   "Indicates the status of the handshake function.
                    Options:
                    1. open(1)  -indicates the handshake function is enabled
                    2. close(0) -indicates the handshake function is disabled
                    Default: close(0)
                   "
                  ::= { hwDot1xMibObjects 12 }
        
        hwDot1xKeepaliveRestranTimes OBJECT-TYPE
              SYNTAX Integer32 (1..10)
              MAX-ACCESS read-write
              STATUS current
              DESCRIPTION
                   "Indicates the permitted handshake failures.
                    Range: 1-10
                    Default: 3
                   "
                  ::= { hwDot1xMibObjects 13 }
        
        hwDot1xKeepaliveInterval OBJECT-TYPE
              SYNTAX Integer32 (1..1800)
              MAX-ACCESS read-write
              STATUS current
              DESCRIPTION
                   "Indicates the handshake interval.
                    Unit: second
                   "
                  ::= { hwDot1xMibObjects 14 }  
            
        hwDot1xQuietPeriodTime OBJECT-TYPE
              SYNTAX  Integer32(10..240)
              MAX-ACCESS read-write
              STATUS current
              DESCRIPTION
                   "The value, in seconds, of the quietPeriod constant currently in use by the Authenticator PAE state machine.
                    Unit: second
                   "              
                  ::= { hwDot1xMibObjects 15 }
                                     
        hwDot1xReAuthSwitch OBJECT-TYPE
              SYNTAX  INTEGER {true(1),false(2)}
              MAX-ACCESS read-write
              STATUS current
              DESCRIPTION
                   "The enable/disable control used by the Reauthentication Timer state machine.
                    Options:
                    1. true(1)  - indicates the reauthentication function is enabled
                    2. false(2) - indicates the reauthentication function is disabled
                    Default: true(1)
                   "            
                  ::= {hwDot1xMibObjects 16 }
                 
        hwDot1xReAuthInterval OBJECT-TYPE
              SYNTAX Integer32(60..86400)
              MAX-ACCESS read-write
              STATUS current
              DESCRIPTION
                   "The value, in seconds, of the reAuthPeriod constant currently in use by the Reauthentication Timer state machine.
                    Unit: second
                   "
                  ::= {hwDot1xMibObjects 17 }
        
        hwDot1xAuthRequestInterval OBJECT-TYPE
              SYNTAX Integer32(10..240)
              MAX-ACCESS read-write
              STATUS current
              DESCRIPTION
                   "The value, in seconds, of the txPeriod constant currently in use by the Authenticator PAE state machine.
                    Unit: second
                   "
                  ::= {hwDot1xMibObjects 18 }
        
        hwDot1xRestransmitTimes OBJECT-TYPE
              SYNTAX Integer32(1..10)
              MAX-ACCESS read-write
              STATUS current
              DESCRIPTION
                   "The value of the maxReq constant currently in use by the Backend Authentication state machine.
                    Range: 1-10
                    Default: 3
                   "
                  ::= {hwDot1xMibObjects 19 }
        
        hwDot1xSuppTimeout OBJECT-TYPE
              SYNTAX Integer32(10..2400)
              MAX-ACCESS read-write
              STATUS current
              DESCRIPTION
                   "The value, in seconds, of the suppTimeout constant currently in use by the Backend Authentication state machine.
                    Unit: second
                   "
                  ::= {hwDot1xMibObjects 20 }
                
        hwOntDot1xMibObjects OBJECT IDENTIFIER ::= {  hwpaeExtMibObjects 4  } 
                          
        hwOntDot1xProfileTable OBJECT-TYPE
            SYNTAX SEQUENCE OF HwOntDot1xProfileEntry
            MAX-ACCESS not-accessible
            STATUS current
            DESCRIPTION
                "This table is used to manage the 802.1x profile and global configuration data of the profile.
                The index of this table is hwOntDot1xProfileName.
                "
            ::= { hwOntDot1xMibObjects 1 }
        
        hwOntDot1xProfileEntry OBJECT-TYPE
            SYNTAX HwOntDot1xProfileEntry
            MAX-ACCESS not-accessible
            STATUS current
            DESCRIPTION
                "This table is used to manage the 802.1x profile and global configuration data of the profile.
                The index of this entry is hwOntDot1xProfileName.
                "
            INDEX { hwOntDot1xProfileName }
            ::= { hwOntDot1xProfileTable 1 }  
            
        HwOntDot1xProfileEntry ::=
            SEQUENCE { 
                hwOntDot1xProfileName
                    OCTET STRING,
                hwOntDot1xRadiusAuthServerIP
                    IpAddress,
                hwOntDot1xRadiusAuthServerPort
                    Integer32,
                hwOntDot1xRadiusSecondaryAuthServerIP
                    IpAddress,
                hwOntDot1xRadiusSecondaryAuthServerPort
                    Integer32,
                hwOntDot1xRadiusAuthSharedKey
                    OCTET STRING,
                hwOntDot1xRadiusSecondaryAuthSharedKey
                    OCTET STRING,
                hwOntDot1xRadiusUserNameFormat
                    INTEGER,
                hwOntDot1xRadiusServerTimeOut
                    Integer32,
                hwOntDot1xRadiusServerRetransmitTimes
                    Integer32,
                hwOntDot1xProfileBindNum
                    Integer32,
                hwOntDot1xProfileCommit
                    INTEGER, 
                hwOntDot1xRadiusAcctServerAddrType
                    InetAddressType,
                hwOntDot1xRadiusAcctServerAddr
                    InetAddress,
                hwOntDot1xRadiusAcctServerPort
                	Integer32,
               	hwOntDot1xRadiusSecondaryAcctServerAddrType
               		InetAddressType, 
                hwOntDot1xRadiusSecondaryAcctServerAddr
                    InetAddress,
                hwOntDot1xRadiusSecondaryAcctServerPort
                	Integer32, 
                hwOntDot1xAcctInterimInterval
                	Integer32,
                hwOntDot1xVoiceDeviceControl
                    INTEGER,
                hwOntDot1xRadiusAcctServerShareKey
                    OCTET STRING,
                hwOntDot1xRadiusSecondaryAcctServerShareKey
                    OCTET STRING,
                hwOntDot1xMaxRetryTimes
                    Integer32, 
                hwOntDot1xQuietPeriodSwitch
                    INTEGER,
                hwOntDot1xQuietPeriodTime
                    Integer32,
                hwOntDot1xTxPeriodTime
                    Integer32,
                hwOntDot1xProfileRowStatus
                    RowStatus              	
                }

       hwOntDot1xProfileName OBJECT-TYPE
            SYNTAX OCTET STRING (SIZE(1..32))
            MAX-ACCESS not-accessible
            STATUS current
            DESCRIPTION
                "802.1x profile name.
                 Range: a string of 1-32 characters.
                "
            ::= { hwOntDot1xProfileEntry 1 }

       hwOntDot1xRadiusAuthServerIP OBJECT-TYPE
            SYNTAX IpAddress
            MAX-ACCESS read-write
            STATUS current
            DESCRIPTION
                "The ip address of primary radius authentication server.
                "
            ::= { hwOntDot1xProfileEntry 2 }

       hwOntDot1xRadiusAuthServerPort OBJECT-TYPE
            SYNTAX Integer32 (0..65535)
            MAX-ACCESS read-write
            STATUS current
            DESCRIPTION
                "The port of primary radius authentication server.
                "
            ::= { hwOntDot1xProfileEntry 3 }

       hwOntDot1xRadiusSecondaryAuthServerIP OBJECT-TYPE
            SYNTAX IpAddress
            MAX-ACCESS read-write
            STATUS current
            DESCRIPTION
                "The ip address of secondary radius authentication server.
                " 
            ::= { hwOntDot1xProfileEntry 4 }

       hwOntDot1xRadiusSecondaryAuthServerPort OBJECT-TYPE
            SYNTAX Integer32 (0..65535)
            MAX-ACCESS read-write
            STATUS current
            DESCRIPTION
                "The port of secondary radius authentication server.
                "
            ::= { hwOntDot1xProfileEntry 5 }

       hwOntDot1xRadiusAuthSharedKey OBJECT-TYPE
            SYNTAX OCTET STRING (SIZE (0..25))
            MAX-ACCESS read-create
            STATUS current
            DESCRIPTION
                "The shared-key of primary redius server.
                "
            ::= { hwOntDot1xProfileEntry 6 }

       hwOntDot1xRadiusSecondaryAuthSharedKey OBJECT-TYPE
            SYNTAX OCTET STRING (SIZE (0..25))
            MAX-ACCESS read-create
            STATUS current
            DESCRIPTION
                "The shared-key of secondary redius server.
                "
            ::= { hwOntDot1xProfileEntry 7 }

       hwOntDot1xRadiusUserNameFormat OBJECT-TYPE
            SYNTAX INTEGER
                {         
                domainincluded(1),
                nodomainincluded(2)
                } 
            MAX-ACCESS read-write
            STATUS current
            DESCRIPTION
                "User name format in the radius packet.
                 Options:
                 1. domainincluded(1)     -Indicates that a user name contains a domain name. 
                 2. nodomainincluded(2)  -Indicates that a user name uses the original name.
                 Defaule: domain-included(1)
                "
            DEFVAL { includingdomain }
            ::= { hwOntDot1xProfileEntry 8 }
                   
       hwOntDot1xRadiusServerTimeOut OBJECT-TYPE
            SYNTAX Integer32 (1..20)
            MAX-ACCESS read-write
            STATUS current
            DESCRIPTION
                "The retransmit timeout period of radius server.
                 Unit: second
                 Default: 5   
                "
            ::= { hwOntDot1xProfileEntry 9 }
                   
       hwOntDot1xRadiusServerRetransmitTimes OBJECT-TYPE
            SYNTAX Integer32 (1..5)
            MAX-ACCESS read-write
            STATUS current
            DESCRIPTION
                "The times of radius packet retransmit.
                Default: 3
                "
            ::= { hwOntDot1xProfileEntry 10 }
       
       hwOntDot1xProfileBindNum OBJECT-TYPE
            SYNTAX Integer32
            MAX-ACCESS read-only
            STATUS current
            DESCRIPTION
                "The binding times of the profile.
                "
            ::= { hwOntDot1xProfileEntry 11 }
       
       hwOntDot1xProfileCommit OBJECT-TYPE
            SYNTAX INTEGER
                {         
                commitExecute(1),
                invalid(-1) 
                } 
            MAX-ACCESS read-write
            STATUS current
            DESCRIPTION
                "Indicates whether the profile-mode configuration of 802.1x is available.
                 Options:
                 1. commitExecute(1)    - indicates to perform the commit operation.
                 2. invalid(-1)         - indicates the invalid state.
                "
            DEFVAL { invalid }
            ::= { hwOntDot1xProfileEntry 12 } 
               
      hwOntDot1xRadiusAcctServerAddrType OBJECT-TYPE
            SYNTAX InetAddressType
            MAX-ACCESS read-write
            STATUS current
            DESCRIPTION 
            	"Indicates the address type of primary radius accounting server."
            ::= { hwOntDot1xProfileEntry 13 } 
      
      hwOntDot1xRadiusAcctServerAddr OBJECT-TYPE
            SYNTAX InetAddress
            MAX-ACCESS read-write
            STATUS current
            DESCRIPTION 
            	"Indicates the ip address of primary radius accounting server"
            ::= { hwOntDot1xProfileEntry 14 }
       
      hwOntDot1xRadiusAcctServerPort OBJECT-TYPE
            SYNTAX Integer32 (0..65535)
            MAX-ACCESS read-write
            STATUS current
            DESCRIPTION 
            	"Indicates the port of primary radius accounting server."
            ::= { hwOntDot1xProfileEntry 15 } 
       
      hwOntDot1xRadiusSecondaryAcctServerAddrType OBJECT-TYPE
            SYNTAX InetAddressType
            MAX-ACCESS read-write
            STATUS current
            DESCRIPTION 
            	"Indicates the address type of secondary radius accounting server."
            ::= { hwOntDot1xProfileEntry 16 } 
      
      hwOntDot1xRadiusSecondaryAcctServerAddr OBJECT-TYPE
            SYNTAX InetAddress
            MAX-ACCESS read-write
            STATUS current
            DESCRIPTION 
            	"Indicates the ip address of secondary radius accounting server."
            ::= { hwOntDot1xProfileEntry 17 }
       
       hwOntDot1xRadiusSecondaryAcctServerPort OBJECT-TYPE
            SYNTAX Integer32 (0..65535)
            MAX-ACCESS read-write
            STATUS current
            DESCRIPTION 
            	"Indicates the port of secondary radius accounting server."
            ::= { hwOntDot1xProfileEntry 18 }  
        
        hwOntDot1xAcctInterimInterval OBJECT-TYPE
            SYNTAX Integer32 (0..60)
            MAX-ACCESS read-write
            STATUS current
            DESCRIPTION 
            	"Indicates interim interval of accounting.  
            	Unit: minute
            	Default: 0 -Indicates that real-time accounting is not performed."
            ::= { hwOntDot1xProfileEntry 19 } 
                
        hwOntDot1xVoiceDeviceControl OBJECT-TYPE
            SYNTAX INTEGER
            	{         
                auto(1),
                forceauthorized(2)
                } 
            MAX-ACCESS read-write
            STATUS current
            DESCRIPTION 
            	"Indicates the authentication control mode of the 802.1X voice device. 
            	Options:
 				1. auto (1)           -Indicates that the control mode of the voice device is in automatic identification.
 				2. forceauthorized(2) -Indicates that the control mode of the voice device is in forced authorization.
 				Default: auto(1)"
            ::= { hwOntDot1xProfileEntry 20 }
       
        hwOntDot1xRadiusAcctServerShareKey OBJECT-TYPE
            SYNTAX OCTET STRING (SIZE (0..25))
            MAX-ACCESS read-create
            STATUS current
            DESCRIPTION
                "The shared-key of primary accounting radius server.
                "
            ::= { hwOntDot1xProfileEntry 21 }

        hwOntDot1xRadiusSecondaryAcctServerShareKey OBJECT-TYPE
            SYNTAX OCTET STRING (SIZE (0..25))
            MAX-ACCESS read-create
            STATUS current
            DESCRIPTION
                "The shared-key of secondary accounting radius server.
                "
            ::= { hwOntDot1xProfileEntry 22 }

        hwOntDot1xMaxRetryTimes OBJECT-TYPE
            SYNTAX Integer32 (1..10)
            MAX-ACCESS read-write
            STATUS current
            DESCRIPTION 
            	"Indicates Maximum number of times that the ONT sends authentication requests to 802.1x users.  
            	Default: 3 "
            ::= { hwOntDot1xProfileEntry 23 } 
         
        hwOntDot1xQuietPeriodSwitch OBJECT-TYPE
            SYNTAX INTEGER
            	{         
                enable(1),
                disable(2)
                } 
            MAX-ACCESS read-write
            STATUS current
            DESCRIPTION 
            	"Indicates 802.1x quiet function of the ONT. 
            	Options:
 				1. enable  (1) -Indicates 802.1x quiet function of the ONT is enabled.
 				2. disable (2) -Indicates 802.1x quiet function of the ONT is disabled.
 				Default: enable(1)"
            ::= { hwOntDot1xProfileEntry 24} 
        
        hwOntDot1xQuietPeriodTime OBJECT-TYPE
            SYNTAX Integer32 (1..3600)
            MAX-ACCESS read-write
            STATUS current
            DESCRIPTION 
            	"Indicates 802.1x quiet period of the ONT.
            	Unit: second  
            	Default: 60"
            ::= { hwOntDot1xProfileEntry 25 }
         
        hwOntDot1xTxPeriodTime OBJECT-TYPE
            SYNTAX Integer32 (1..120)
            MAX-ACCESS read-write
            STATUS current
            DESCRIPTION 
            	"Indicates period for the ONT to transmit authentication requests.
            	Unit: second  
            	Default: 3"
            ::= { hwOntDot1xProfileEntry 26 } 
       
       hwOntDot1xProfileRowStatus OBJECT-TYPE
            SYNTAX RowStatus
            MAX-ACCESS read-create
            STATUS current
            DESCRIPTION
                "Row admin status, only support CreateAndGo(4),Destory(6),Active(1).
                 Options:
                 1. active(1)      -indicates query operation
                 2. createAndGo(4) -indicates creating operation
                 3. destroy(6)     -indicates deleting operation
                "
            ::= { hwOntDot1xProfileEntry 255 }

        hwOntDot1xPortProfileTable OBJECT-TYPE
            SYNTAX SEQUENCE OF HwOntDot1xPortProfileEntry
            MAX-ACCESS not-accessible
            STATUS current
            DESCRIPTION
                "This table is used to manage the port configuration data of the 802.1x profile. 
                The indexes of this table are hwOntDot1xPortProfName, hwOntDot1xOntPhyType, hwOntDot1xOntPhyIndex.
                "
            ::= { hwOntDot1xMibObjects 2 }
        
        hwOntDot1xPortProfileEntry OBJECT-TYPE
            SYNTAX HwOntDot1xPortProfileEntry
            MAX-ACCESS not-accessible
            STATUS current
            DESCRIPTION
                "This table is used to manage the port configuration data of the 802.1x profile. 
                The indexes of this entry are hwOntDot1xPortProfName, hwOntDot1xOntPhyType, hwOntDot1xOntPhyIndex.
                "
            INDEX { hwOntDot1xPortProfName, hwOntDot1xOntPhyType, hwOntDot1xOntPhyIndex }
            ::= { hwOntDot1xPortProfileTable 1 }  
            
        HwOntDot1xPortProfileEntry ::=
            SEQUENCE { 
                hwOntDot1xPortProfName
                    OCTET STRING,
                hwOntDot1xOntPhyType
                    INTEGER, 
                hwOntDot1xOntPhyIndex
                    Integer32,
                hwOntDot1xPortSwitch
                    INTEGER,
                hwOntDot1xPortControl
                    INTEGER,
                hwOntDot1xPortAuthenticationMethod
                    INTEGER,
                hwOntDot1xPortGuestVlan
                    Integer32,
                hwOntDot1xPortRestrictVlan
                    Integer32,
                hwOntDot1xPortKeepaliveSwitch
                    INTEGER,
                hwOntDot1xPortRetransmitTimes
                    Integer32,
                hwOntDot1xPortRetransmitInterval
                    Integer32,
		hwOntDot1xPortMacBypassSwitch
                    INTEGER,	
		hwOntDot1xPortCriticalVlan
                    Integer32,	
                hwOntDot1xPortUnicastTriggerSwitch
                    INTEGER,   
                hwOntDot1xPortMulticastTriggerSwitch
                    INTEGER,
                hwOntDot1xPortRowStatus 
                    RowStatus 
                }
                  
        hwOntDot1xPortProfName OBJECT-TYPE
            SYNTAX OCTET STRING (SIZE(1..32))
            MAX-ACCESS not-accessible
            STATUS current
            DESCRIPTION
                "Indicates the ont dot1x profile name.
                Range: a string of 1-32 characters.
                "
            ::= { hwOntDot1xPortProfileEntry 1 } 
            
        hwOntDot1xOntPhyType OBJECT-TYPE
            SYNTAX   INTEGER{eth(47)}
            MAX-ACCESS not-accessible 
            STATUS current
            DESCRIPTION
                "Indicates the port type of the ONT.
                Options:
                1. eth(47)            - ETH
                "                              
            ::= { hwOntDot1xPortProfileEntry 2 } 
            
        hwOntDot1xOntPhyIndex OBJECT-TYPE
            SYNTAX Integer32
            MAX-ACCESS not-accessible 
            STATUS current
            DESCRIPTION
                "Indicates the ONT port index.
                "
            ::= { hwOntDot1xPortProfileEntry 3 } 
            
        hwOntDot1xPortSwitch OBJECT-TYPE
            SYNTAX INTEGER {enable(1),disable(2)}
            MAX-ACCESS read-write
            STATUS current
            DESCRIPTION
                "Indicates the 802.1x switch.
                Options:
                1. enable(1)               - indicates that the 802.1x switch is enabled.
                2. disable(2)              - indicates that the 802.1x switch is disabled.
                Default: disable(2)
                "                          
            ::= { hwOntDot1xPortProfileEntry 4 }
            
        hwOntDot1xPortControl OBJECT-TYPE
            SYNTAX INTEGER {auto(1),forceauthorized(2),forceunauthorized(3)}
            MAX-ACCESS read-write
            STATUS current
            DESCRIPTION
                "Indicates the 802.1x port control.
                Options:
                1. auto(1)              - indicates that the 802.1x control is auto.
                2. forceauthorized(2)   - indicates that the 802.1x control is force-authorized.
                3. forceunauthorized(3) - indicates that the 802.1x control is force-unauthorized.
                Default: auto(1)
                "     
            ::= { hwOntDot1xPortProfileEntry 5 }
    
       hwOntDot1xPortAuthenticationMethod OBJECT-TYPE
            SYNTAX INTEGER {eap(1),chap(2),pap(3)}
            MAX-ACCESS read-write 
            STATUS current
            DESCRIPTION
                "Indicates the 802.1x authentication method.     
                Options:
                1. eap(1)               - indicates that the 802.1x authentication method is eap.
                2. chap(2)              - indicates that the 802.1x authentication method is chap.
                3. pap(3)               - indicates that the 802.1x authentication method is pap.
                Default: chap(2)
                "     
            ::= { hwOntDot1xPortProfileEntry 6 }
          
       hwOntDot1xPortGuestVlan OBJECT-TYPE
            SYNTAX Integer32 (-1 | 0..4095)
            MAX-ACCESS read-write 
            STATUS current
            DESCRIPTION
                "Indicates the 802.1x guest VLAN.
                Range: -1, 0-4095, -1 indicates an invalid value, a value between 0 and 4095 indicates the VLAN ID.
                "     
            ::= { hwOntDot1xPortProfileEntry 7 }

       hwOntDot1xPortRestrictVlan OBJECT-TYPE
            SYNTAX Integer32 (-1 | 0..4095)
            MAX-ACCESS read-write 
            STATUS current
            DESCRIPTION
                "Indicates the 802.1x restrict VLAN.
                Range: -1, 0-4095, -1 indicates an invalid value, a value between 0 and 4095 indicates the VLAN ID.
                "     
            ::= { hwOntDot1xPortProfileEntry 8 }
              
       hwOntDot1xPortKeepaliveSwitch OBJECT-TYPE
            SYNTAX INTEGER {enable(1),disable(2)}
            MAX-ACCESS read-write 
            STATUS current
            DESCRIPTION
                "Indicates the 802.1x keepalive switch.
                Options:
                1. enable(1)               - indicates that the 802.1x keepalive switch is enabled.
                2. disable(2)              - indicates that the 802.1x keepalive switch is disabled.
                Default: disable(2)
                "     
            ::= { hwOntDot1xPortProfileEntry 9 }

       hwOntDot1xPortRetransmitTimes OBJECT-TYPE
            SYNTAX Integer32 (1..10)
            MAX-ACCESS read-write 
            STATUS current
            DESCRIPTION
                "Indicates the 802.1x keepalive retransmit times.
                Range: 1-10
                Default: 3
                "     
            ::= { hwOntDot1xPortProfileEntry 10 }

       hwOntDot1xPortRetransmitInterval OBJECT-TYPE
            SYNTAX Integer32 (1..1800)
            MAX-ACCESS read-write 
            STATUS current
            DESCRIPTION
                "Indicates the 802.1x keepalive interval.
                Unit: second
                Range: 1-1800
                Default: 15
                "     
            ::= { hwOntDot1xPortProfileEntry 11 }
			
       hwOntDot1xPortMacBypassSwitch OBJECT-TYPE
            SYNTAX INTEGER {enable(1),disable(2)}
            MAX-ACCESS read-write
            STATUS current
            DESCRIPTION
                "Indicates the MacBypass switch.
                Options:
                1. enable(1)               - indicates that the MacBypass switch is enabled.
                2. disable(2)              - indicates that the MacBypass switch is disabled.
                Default: disable(2)
                "                          
            ::= { hwOntDot1xPortProfileEntry 12 }	
			
       hwOntDot1xPortCriticalVlan OBJECT-TYPE
            SYNTAX Integer32 (-1 | 0..4095)
            MAX-ACCESS read-write 
            STATUS current
            DESCRIPTION
                "Indicates the 802.1x critical VLAN.
                Range: -1, 0-4095, -1 indicates an invalid value, a value between 0 and 4095 indicates the VLAN ID.
                "     
            ::= { hwOntDot1xPortProfileEntry 13 }
       
       hwOntDot1xPortUnicastTriggerSwitch OBJECT-TYPE
            SYNTAX INTEGER {enable(1),disable(2)}
            MAX-ACCESS read-write
            STATUS current
            DESCRIPTION
                "Indicates the 802.1x unicast trigger switch.
                Options:
                1. enable(1)               - indicates that the unicast trigger switch switch is enabled.
                2. disable(2)              - indicates that the unicast trigger switch switch is disabled.
                Default: enable(1)
                "                          
            ::= { hwOntDot1xPortProfileEntry 14 }
        
       hwOntDot1xPortMulticastTriggerSwitch OBJECT-TYPE
            SYNTAX INTEGER {enable(1),disable(2)}
            MAX-ACCESS read-write
            STATUS current
            DESCRIPTION
                "Indicates the 802.1x multicast trigger switch.
                Options:
                1. enable(1)               - indicates that the multicast trigger switch is enabled.
                2. disable(2)              - indicates that the multicast trigger switch is disabled.
                Default: disable(2)
                "                          
            ::= { hwOntDot1xPortProfileEntry 15 }	
	       
       hwOntDot1xPortRowStatus OBJECT-TYPE
            SYNTAX   RowStatus
            MAX-ACCESS read-create
            STATUS current
            DESCRIPTION
                "Indicates the operation type of the port table: binding the port to the 802.1x 
                 authentication, and unbinding the port from the 802.1x authentication.
                 Options:
                 1. active(1)      -indicates query operation
                 2. createAndGo(4) -indicates binding a port to the 802.1x authentication
                 3. destroy(6)     -indicates unbinding a port from the 802.1x authentication
                "                                
            ::= { hwOntDot1xPortProfileEntry 255}                                 

        hwOntPortDot1xStatusTable OBJECT-TYPE
            SYNTAX SEQUENCE OF HwOntPortDot1xStatusEntry
            MAX-ACCESS not-accessible
            STATUS current
            DESCRIPTION
                "This table is used to query 802.1x status of ONT ports. 
                The indexes of this table are ifIndex, hwOntDot1xOntId, hwOntDot1xOntPhyType, hwOntDot1xOntPhyIndex.
                "
            ::= { hwOntDot1xMibObjects 3 }
        
        hwOntPortDot1xStatusEntry OBJECT-TYPE
            SYNTAX HwOntPortDot1xStatusEntry
            MAX-ACCESS not-accessible
            STATUS current
            DESCRIPTION
                "This table is used to query 802.1x status of ONT ports. 
                The indexes of this entry are ifIndex, hwOntDot1xOntId, hwOntDot1xOntPhyType, hwOntDot1xOntPhyIndex.
                "
            INDEX { ifIndex, hwOntDot1xOntId, hwOntDot1xOntPhyType, hwOntDot1xOntPhyIndex }
            ::= { hwOntPortDot1xStatusTable 1 }  
            
        HwOntPortDot1xStatusEntry ::=
            SEQUENCE { 
                hwOntDot1xOntId
                    Integer32,
                hwOntDot1xAuthResult
                    INTEGER,
                hwOntDot1xAuthenticatorPAEState
                    INTEGER,
                hwOntDot1xPortBackendAuthState
                    INTEGER,
                hwOntDot1xReAuthPeriod
                    Integer32,
                hwOntDot1xReAuthSwitch
                    INTEGER,
		hwOntDot1xRadiusAssignVlan
		    Integer32
                }
   
       hwOntDot1xOntId OBJECT-TYPE 
            SYNTAX Integer32
            MAX-ACCESS not-accessible
            STATUS current
            DESCRIPTION
                "This object indicates the ONT ID of the port
                "
            ::= { hwOntPortDot1xStatusEntry 1 }
                  
       hwOntDot1xAuthResult OBJECT-TYPE 
           SYNTAX INTEGER
                {         
                authorized(1),
                unauthorized(2),
                invalid(-1)
                } 
            MAX-ACCESS read-only
            STATUS current
            DESCRIPTION
                "Indicates the 802.1x authentication state. 
                 Options:
                 1. authorized(1)    - Indicates the 802.1x authentication state is authorized.
                 2. unauthorized(2)  - Indicates the 802.1x authentication state is unauthorized.
                 3. invalid(-1)      - Indicates the invalid state.
                "
            ::= { hwOntPortDot1xStatusEntry 2 }

       hwOntDot1xAuthenticatorPAEState OBJECT-TYPE
            SYNTAX INTEGER
                {         
                initialize(1),
                disconnected(2),
                connecting(3),
                authenticating(4),
                authenticated(5),
                aborting(6),
                held(7),
                forceauth(8),
                forceunauth(9),
                restart(10),
                invalid(-1) 
                } 
            MAX-ACCESS read-only
            STATUS current
            DESCRIPTION 
                "Indicates the 802.1x authenticator PAE state.
                 Options:
                 1.initialize(1)     -Indicates that 802.1x authenticator PAE state is initialize.
                 2.disconnected(2)   -Indicates that 802.1x authenticator PAE state is disconnected.
                 3.connecting(3)     -Indicates that 802.1x authenticator PAE state is connecting.
                 4.authenticating(4) -Indicates that 802.1x authenticator PAE state is authenticating.
                 5.authenticated(5)  -Indicates that 802.1x authenticator PAE state is authenticated.
                 6.aborting(6)       -Indicates that 802.1x authenticator PAE state is aborting.
                 7.held(7)           -Indicates that 802.1x authenticator PAE state is held.
                 8.forceauth(8)      -Indicates that 802.1x authenticator PAE state is forceauth. 
                 9.forceunauth(9)    -Indicates that 802.1x authenticator PAE state is forceunauth.
                 10.restart(10)      -Indicates that 802.1x authenticator PAE state is restart.
                 11.invalid(-1)      -Indicates the invalid state.
                "
            ::= { hwOntPortDot1xStatusEntry 3 }

       hwOntDot1xPortBackendAuthState OBJECT-TYPE
            SYNTAX INTEGER
                {         
                request(1),
                response(2),
                success(3),
                fail(4),
                timeout(5),
                idle(6),
                initialize(7),
                ignore(8),
                invalid(-1)
                } 
            MAX-ACCESS read-only
            STATUS current
            DESCRIPTION
                "Indicates the 802.1x backend authentication state.
                 Options:
                 1.request(1)     -Indicates that 802.1x backend authentication state is request.
                 2.response(2)    -Indicates that 802.1x backend authentication state is response.
                 3.success(3)     -Indicates that 802.1x backend authentication state is success.
                 4.fail(4)        -Indicates that 802.1x backend authentication state is fail.
                 5.timeout(5)     -Indicates that 802.1x backend authentication state is timeout.
                 6.idle(6)        -Indicates that 802.1x backend authentication state is idle.
                 7.initialize(7)  -Indicates that 802.1x backend authentication state is initialize.
                 8.ignore(8)      -Indicates that 802.1x backend authentication state is ignore.
                 9.invalid(-1)    -Indicates the invalid state.
                "
            ::= { hwOntPortDot1xStatusEntry 4 }

       hwOntDot1xReAuthPeriod OBJECT-TYPE
            SYNTAX Integer32
            MAX-ACCESS read-only
            STATUS current
            DESCRIPTION
                "Indicates the 802.1x re-authentication period(s). 
                 Unit: second
                "
            ::= { hwOntPortDot1xStatusEntry 5 } 

       hwOntDot1xReAuthSwitch OBJECT-TYPE 
            SYNTAX INTEGER
                {         
                enable(1),
                disable(2),
                invalid(-1)
                } 
            MAX-ACCESS read-only
            STATUS current 
            DESCRIPTION
                "Indicates the 802.1x re-authentication switch. 
                 Options:
                 1. enable(1)     -Indicates that 802.1x re-authentication switch is enable.
                 2. disable(2)    -Indicates that 802.1x re-authentication switch is disable.
                 3. invalid(-1)   -Indicates the invalid state.
                "
            ::= { hwOntPortDot1xStatusEntry 6 }
	    
       hwOntDot1xRadiusAssignVlan OBJECT-TYPE 
            SYNTAX Integer32 (-1 | 0..4095)
            MAX-ACCESS read-only
            STATUS current 
            DESCRIPTION
                "Indicates the VLAN by radius server assigned.
                Range: -1, 0-4095, -1 indicates an invalid value, a value between 0 and 4095 indicates the VLAN ID.
                "  
            ::= { hwOntPortDot1xStatusEntry 7 }

        hwOntPortDot1xStatisticsTable OBJECT-TYPE
            SYNTAX SEQUENCE OF HwOntPortDot1xStatisticsEntry
            MAX-ACCESS not-accessible
            STATUS current
            DESCRIPTION
                "This table is used to query and clear 802.1x packet statistics of ONT ports.
                The indexes of this table are ifIndex , hwOntDot1xOntId , hwOntDot1xOntPhyType, hwOntDot1xOntPhyIndex.
                "
            ::= { hwOntDot1xMibObjects 4 }
        
        hwOntPortDot1xStatisticsEntry OBJECT-TYPE
            SYNTAX HwOntPortDot1xStatisticsEntry
            MAX-ACCESS not-accessible
            STATUS current
            DESCRIPTION
                "This table is used to query and clear 802.1x packet statistics of ONT ports. 
                The indexes of this entry are ifIndex , hwOntDot1xOntId , hwOntDot1xOntPhyType, hwOntDot1xOntPhyIndex.
                "
            INDEX { ifIndex, hwOntDot1xOntId, hwOntDot1xOntPhyType, hwOntDot1xOntPhyIndex }
            ::= { hwOntPortDot1xStatisticsTable 1 }  
            
        HwOntPortDot1xStatisticsEntry ::=
            SEQUENCE { 
                hwOntPortDot1xStatisticsReceivedFrames
                    Counter64,
                hwOntPortDot1xStatisticsReceivedStartFrames
                    Counter64,
                hwOntPortDot1xStatisticsReceivedLogOffFrames
                    Counter64,
                hwOntPortDot1xStatisticsReceivedInvalidFrames
                    Counter64,
                hwOntPortDot1xStatisticsReceivedResponseIdentityFrames
                    Counter64,
                hwOntPortDot1xStatisticsReceivedResponseChallengeFrames
                    Counter64,
                hwOntPortDot1xStatisticsReceivedLengthErrorFrames
                    Counter64,
                hwOntPolPortDot1xStatisticsSentInitialRequestFrames
                    Counter64,
                hwOntPolPortDot1xStatisticsSentRequestFrames
                    Counter64,
                hwOntPortDot1xStatisticsSentSuccessFrames
                    Counter64,
                hwOntPortDot1xStatisticsSentFailureFrames
                    Counter64,                                                                                                                                                                                                                             
                hwOntPortDot1xStatisticsClear 
                    INTEGER 
                }
                  
        hwOntPortDot1xStatisticsReceivedFrames OBJECT-TYPE
            SYNTAX Counter64
            MAX-ACCESS read-only
            STATUS current
            DESCRIPTION
                "Indicates the total received EAPoL frames.
                0xffffffffffffffff indicates an invalid value. 
                "
            ::= { hwOntPortDot1xStatisticsEntry 1 }
                    
        hwOntPortDot1xStatisticsReceivedStartFrames OBJECT-TYPE
            SYNTAX Counter64
            MAX-ACCESS read-only
            STATUS current
            DESCRIPTION
                "Indicates the total received EAPoL start frames.
                0xffffffffffffffff indicates an invalid value.
                "
            ::= { hwOntPortDot1xStatisticsEntry 2 }
   
        hwOntPortDot1xStatisticsReceivedLogOffFrames OBJECT-TYPE
            SYNTAX Counter64
            MAX-ACCESS read-only
            STATUS current
            DESCRIPTION
                "Indicates the total received EAPoL logoff frames.
                0xffffffffffffffff indicates an invalid value.
                "
            ::= { hwOntPortDot1xStatisticsEntry 3 }
            
        hwOntPortDot1xStatisticsReceivedInvalidFrames OBJECT-TYPE
            SYNTAX Counter64
            MAX-ACCESS read-only
            STATUS current
            DESCRIPTION
                "Indicates the total received EAPoL Invalid frames.
                0xffffffffffffffff indicates an invalid value.
                "
            ::= { hwOntPortDot1xStatisticsEntry 4 }   
                          
        hwOntPortDot1xStatisticsReceivedResponseIdentityFrames OBJECT-TYPE
            SYNTAX Counter64
            MAX-ACCESS read-only
            STATUS current
            DESCRIPTION
                "Indicates the total received EAPoL response/identity frames.
                0xffffffffffffffff indicates an invalid value.
                "
            ::= { hwOntPortDot1xStatisticsEntry 5 }
                    
        hwOntPortDot1xStatisticsReceivedResponseChallengeFrames OBJECT-TYPE
            SYNTAX Counter64
            MAX-ACCESS read-only
            STATUS current
            DESCRIPTION
                "Indicates the total received EAPoL response/challenge frames.
                0xffffffffffffffff indicates an invalid value.
                "
            ::= { hwOntPortDot1xStatisticsEntry 6 }
   
        hwOntPortDot1xStatisticsReceivedLengthErrorFrames OBJECT-TYPE
            SYNTAX Counter64
            MAX-ACCESS read-only
            STATUS current
            DESCRIPTION
                "Indicates the total received EAPoL length error frames.
                0xffffffffffffffff indicates an invalid value.
                "
            ::= { hwOntPortDot1xStatisticsEntry 7 }
            
        hwOntPolPortDot1xStatisticsSentInitialRequestFrames OBJECT-TYPE
            SYNTAX Counter64
            MAX-ACCESS read-only
            STATUS current
            DESCRIPTION
                "Indicates the total sent EAPoL initial request frames.
                0xffffffffffffffff indicates an invalid value.
                "
            ::= { hwOntPortDot1xStatisticsEntry 8 }    
            
        hwOntPolPortDot1xStatisticsSentRequestFrames OBJECT-TYPE
            SYNTAX Counter64
            MAX-ACCESS read-only
            STATUS current
            DESCRIPTION
                "Indicates the total sent EAPoL request frames.
                0xffffffffffffffff indicates an invalid value.
                "
            ::= { hwOntPortDot1xStatisticsEntry 9 }
   
        hwOntPortDot1xStatisticsSentSuccessFrames OBJECT-TYPE
            SYNTAX Counter64
            MAX-ACCESS read-only
            STATUS current
            DESCRIPTION
                "Indicates the total sent EAPoL success frames.
                0xffffffffffffffff indicates an invalid value.
                "
            ::= { hwOntPortDot1xStatisticsEntry 10 }
            
        hwOntPortDot1xStatisticsSentFailureFrames OBJECT-TYPE
            SYNTAX Counter64
            MAX-ACCESS read-only
            STATUS current
            DESCRIPTION
                "Indicates the total sent EAPoL failure frames.
                0xffffffffffffffff indicates an invalid value.
                "
            ::= { hwOntPortDot1xStatisticsEntry 11 }  
                                                        
        hwOntPortDot1xStatisticsClear OBJECT-TYPE
                SYNTAX INTEGER 
                    {
                    clear(1),
                    invalid(-1)
                    }
                MAX-ACCESS read-write
                STATUS current
                DESCRIPTION
                        "Indicates the statistics clear.
                        Options:
                        1. clear(1)    -indicates to perform the clear operation.
                        2. invalid(-1) -indicates the invalid state.
                        "                                
                ::= { hwOntPortDot1xStatisticsEntry 12}   

        hwOntRadiusStatisticsTable OBJECT-TYPE
            SYNTAX SEQUENCE OF HwOntRadiusStatisticsEntry
            MAX-ACCESS not-accessible
            STATUS current
            DESCRIPTION
                "This table is used to query and clear radius packet statistics of ONT.
                The indexes of this table are ifIndex , hwOntDot1xOntId.
                "
            ::= { hwOntDot1xMibObjects 5 }
        
        hwOntRadiusStatisticsEntry OBJECT-TYPE
            SYNTAX HwOntRadiusStatisticsEntry
            MAX-ACCESS not-accessible
            STATUS current
            DESCRIPTION
                "This table is used to query and clear radius packet statistics of ONT. 
                The indexes of this entry are ifIndex , hwOntDot1xOntId.
                "
            INDEX { ifIndex, hwOntDot1xOntId }
            ::= { hwOntRadiusStatisticsTable 1 }  
            
        HwOntRadiusStatisticsEntry ::=
            SEQUENCE { 
                hwOntRadiusStatisticsReceivedAccessChallengeFrames
                    Counter64,
                hwOntRadiusStatisticsReceivedAccessAcceptFrames
                    Counter64,
                hwOntRadiusStatisticsReceivedAccessRejectFrames
                    Counter64,
                hwOntRadiusStatisticsReceivedInvalidFrames
                    Counter64,
                hwOntRadiusStatisticsSentAccessRequestFrames
                    Counter64,
                hwOntRadiusStatisticsRetransAccessRequestFrames
                    Counter64,
                hwOntRadiusStatisticsClear
                    INTEGER,
                hwOntRadiusStatisticsReceivedAccountingResponseFrames
                	Counter64,
                hwOntRadiusStatisticsReceivedDisconnectRequestFrames
                    Counter64,
                hwOntRadiusStatisticsSentAccountingRequestFrames
                    Counter64,
                hwOntRadiusStatisticsRetransAccountingRequestFrames
                    Counter64,
                hwOntRadiusStatisticsSentDisconnectAckFrames
                    Counter64,
                hwOntRadiusStatisticsSentDisconnectNakFrames
                    Counter64
          
                }
                  
       hwOntRadiusStatisticsReceivedAccessChallengeFrames OBJECT-TYPE
                SYNTAX Counter64
                MAX-ACCESS read-only
                STATUS current
                DESCRIPTION
                    "Indicates the total received access-challenge frames.
                    0xffffffffffffffff indicates an invalid value.
                    "
            ::= { hwOntRadiusStatisticsEntry 1 }

       hwOntRadiusStatisticsReceivedAccessAcceptFrames OBJECT-TYPE
                SYNTAX Counter64
                MAX-ACCESS read-only
                STATUS current
                DESCRIPTION
                    "Indicates the total received access-accept frames.
                    0xffffffffffffffff indicates an invalid value.
                    "
            ::= { hwOntRadiusStatisticsEntry 2 }

       hwOntRadiusStatisticsReceivedAccessRejectFrames OBJECT-TYPE
                SYNTAX Counter64
                MAX-ACCESS read-only
                STATUS current
                DESCRIPTION
                    "Indicates the total received access-accept frames.
                    0xffffffffffffffff indicates an invalid value.
                    "
            ::= { hwOntRadiusStatisticsEntry 3 }

       hwOntRadiusStatisticsReceivedInvalidFrames OBJECT-TYPE
                SYNTAX Counter64
                MAX-ACCESS read-only
                STATUS current
                DESCRIPTION
                    "Indicates the total received invalid frames.
                    0xffffffffffffffff indicates an invalid value.
                    "
            ::= { hwOntRadiusStatisticsEntry 4 } 

       hwOntRadiusStatisticsSentAccessRequestFrames OBJECT-TYPE 
                SYNTAX Counter64
                MAX-ACCESS read-only
                STATUS current
                DESCRIPTION
                    "Indicates the total received access-reject frames.
                    0xffffffffffffffff indicates an invalid value.
                    "
            ::= { hwOntRadiusStatisticsEntry 5 }

       hwOntRadiusStatisticsRetransAccessRequestFrames OBJECT-TYPE 
                SYNTAX Counter64
                MAX-ACCESS read-only
                STATUS current
                DESCRIPTION
                    "Indicates the total sent access-request frames.
                    0xffffffffffffffff indicates an invalid value.
                    "
            ::= { hwOntRadiusStatisticsEntry 6 }

       hwOntRadiusStatisticsClear OBJECT-TYPE 
            SYNTAX INTEGER 
                { 
                clear(1),
                invalid(-1) 
                }
            MAX-ACCESS read-write
            STATUS current
            DESCRIPTION
                "Indicates the statistics clear.
                Options:
                1. clear(1)    -indicates to perform the clear operation.
                2. invalid(-1) -indicates the invalid state.
                "
            ::= { hwOntRadiusStatisticsEntry 7 }  
               
       hwOntRadiusStatisticsReceivedAccountingResponseFrames OBJECT-TYPE 
                SYNTAX Counter64
                MAX-ACCESS read-only
                STATUS current
                DESCRIPTION
                    "Indicates the total received accounting-response frames.
                    0xffffffffffffffff indicates an invalid value.
                    "
            ::= { hwOntRadiusStatisticsEntry 8 } 
            
        hwOntRadiusStatisticsReceivedDisconnectRequestFrames OBJECT-TYPE 
                SYNTAX Counter64
                MAX-ACCESS read-only
                STATUS current
                DESCRIPTION
                    "Indicates the total received disconnect-request frames.
                    0xffffffffffffffff indicates an invalid value.
                    "
            ::= { hwOntRadiusStatisticsEntry 9 }
        
        hwOntRadiusStatisticsSentAccountingRequestFrames OBJECT-TYPE 
                SYNTAX Counter64
                MAX-ACCESS read-only
                STATUS current
                DESCRIPTION
                    "Indicates the total sent accounting-request frames.
                    0xffffffffffffffff indicates an invalid value.
                    "
            ::= { hwOntRadiusStatisticsEntry 10 }
        
        hwOntRadiusStatisticsRetransAccountingRequestFrames OBJECT-TYPE 
                SYNTAX Counter64
                MAX-ACCESS read-only
                STATUS current
                DESCRIPTION
                    "Indicates the total retransmission accounting-request frames.
                    0xffffffffffffffff indicates an invalid value.
                    "
            ::= { hwOntRadiusStatisticsEntry 11 }
        
        hwOntRadiusStatisticsSentDisconnectAckFrames OBJECT-TYPE 
                SYNTAX Counter64
                MAX-ACCESS read-only
                STATUS current
                DESCRIPTION
                    "Indicates the total sent disconnect-ack frames.
                    0xffffffffffffffff indicates an invalid value.
                    "
            ::= { hwOntRadiusStatisticsEntry 12 }  
         
        hwOntRadiusStatisticsSentDisconnectNakFrames OBJECT-TYPE 
                SYNTAX Counter64
                MAX-ACCESS read-only
                STATUS current
                DESCRIPTION
                    "Indicates the total sent disconnect-nak frames.
                    0xffffffffffffffff indicates an invalid value.
                    "
            ::= { hwOntRadiusStatisticsEntry 13 }
 
       hwOntDot1xRadiusAuthorServerTable OBJECT-TYPE
            SYNTAX SEQUENCE OF HwOntDot1xRadiusAuthorServerEntry
            MAX-ACCESS not-accessible
            STATUS current
            DESCRIPTION
                "This table is used to manage the Radius authorization server of 802.1x profile.
                The indexes of this table are hwOntDot1xRadiusAuthorServerProfName, hwOntDot1xRadiusAuthorServerID.
                "
            ::= { hwOntDot1xMibObjects 6 }
        
        hwOntDot1xRadiusAuthorServerEntry OBJECT-TYPE
            SYNTAX HwOntDot1xRadiusAuthorServerEntry
            MAX-ACCESS not-accessible
            STATUS current
            DESCRIPTION
                "This table is used to manage the Radius authorization server of 802.1x profile.
                The indexes of this entry are hwOntDot1xRadiusAuthorServerProfName, hwOntDot1xRadiusAuthorServerID.
                "
            INDEX { hwOntDot1xRadiusAuthorServerProfName, hwOntDot1xRadiusAuthorServerID}
            ::= { hwOntDot1xRadiusAuthorServerTable 1 }  
           
         HwOntDot1xRadiusAuthorServerEntry ::=
            SEQUENCE { 
                hwOntDot1xRadiusAuthorServerProfName
                    OCTET STRING,
                hwOntDot1xRadiusAuthorServerID
                    Integer32,
                hwOntDot1xRadiusAuthorServerAddrType
                    InetAddressType,
                hwOntDot1xRadiusAuthorServerAddr
                    InetAddress,
                hwOntDot1xRadiusAuthorServerSharedKey
                    OCTET STRING,
                hwOntDot1xRadiusAuthorServerRowStatus
                    RowStatus
                } 
                
        hwOntDot1xRadiusAuthorServerProfName OBJECT-TYPE
            SYNTAX OCTET STRING (SIZE(1..32))
            MAX-ACCESS not-accessible
            STATUS current
            DESCRIPTION
                "802.1x profile name.
                 Range: a string of 1-32 characters.
                "
            ::= { hwOntDot1xRadiusAuthorServerEntry 1 }  
        
        hwOntDot1xRadiusAuthorServerID OBJECT-TYPE
            SYNTAX Integer32 (0..15)
            MAX-ACCESS not-accessible
            STATUS current
            DESCRIPTION
                "Indicates the ID of radius authorization server.
                "
            ::= { hwOntDot1xRadiusAuthorServerEntry 2 }  
                    
         hwOntDot1xRadiusAuthorServerAddrType OBJECT-TYPE
            SYNTAX InetAddressType
            MAX-ACCESS read-create
            STATUS current
            DESCRIPTION
                "Indicates the address type of radius authorization server.
                 Options:
                 1. IPv4(1) -indicates the address type is IPv4 
                "
            ::= { hwOntDot1xRadiusAuthorServerEntry 3 } 
          
         hwOntDot1xRadiusAuthorServerAddr OBJECT-TYPE
            SYNTAX InetAddress
            MAX-ACCESS read-create
            STATUS current
            DESCRIPTION
                "Indicates the ip address of radius authorization server.
                "
            ::= { hwOntDot1xRadiusAuthorServerEntry 4 } 
            
         hwOntDot1xRadiusAuthorServerSharedKey OBJECT-TYPE
            SYNTAX OCTET STRING (SIZE (0..25))
            MAX-ACCESS read-create
            STATUS current
            DESCRIPTION
                "Indicates the shared-kye of radius authorization server.
                Range: a string of 1-25 characters.
                "
            ::= { hwOntDot1xRadiusAuthorServerEntry 5 } 
         
         hwOntDot1xRadiusAuthorServerRowStatus OBJECT-TYPE
            SYNTAX RowStatus
            MAX-ACCESS read-create
            STATUS current
            DESCRIPTION
                "Row admin status, only support CreateAndGo(4),Destory(6),Active(1).
                 Options:
                 1. active(1)      -indicates query operation
                 2. createAndGo(4) -indicates creating operation
                 3. destroy(6)     -indicates deleting operation
                "
            ::= { hwOntDot1xRadiusAuthorServerEntry 255 }
   
        END

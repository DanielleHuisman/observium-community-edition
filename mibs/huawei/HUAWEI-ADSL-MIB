-- ============================================================================
-- Copyright (C) 2017 by HUAWEI TECHNOLOGIES. All rights reserved.
-- Description:  This MIB is used for defining Huawei's ADSL management MIB objects.
-- Reference:  
-- Version: V3.47
-- ============================================================================

    HUAWEI-ADSL-MIB DEFINITIONS ::= BEGIN
        IMPORTS 
             adslLineMib,adslMibObjects,adslLineConfProfileEntry, adslLineConfProfileName, adslLineEntry, 
             adslAturChanEntry, adslAtucChanEntry, adslAtucChanPerfDataEntry,
             adslAturChanPerfDataEntry, adslAtucChanIntervalEntry, adslAturChanIntervalEntry, 
             adslTraps, adslAturPhysEntry, adslAtucPhysEntry, adslAtucPerfDataEntry,
             adslAtucIntervalEntry, adslLineAlarmConfProfileEntry
             	FROM ADSL-LINE-MIB	 		
             ifIndex,ifType			
             	FROM IF-MIB			
            hwFrameIndex, hwSlotIndex, hwSubslotIndex, hwPortIndex
                FROM HUAWEI-DEVICE-MIB      
             hwIasConfigChangeTrapID
                FROM HWMUSA-DEV-MIB					
             Integer32, Unsigned32, Gauge32, Counter32, OBJECT-TYPE, NOTIFICATION-TYPE, MODULE-IDENTITY		
             	FROM SNMPv2-SMI						
	
             adslLineExtEntry
             	FROM ADSL-LINE-EXT-MIB
             PerfIntervalCount
             	FROM PerfHist-TC-MIB				

             sysName
             	FROM SNMPv2-MIB
             RowStatus, PhysAddress, DateAndTime, TEXTUAL-CONVENTION	
             	FROM SNMPv2-TC
             hwAlarmId, hwAlarmTime, hwAlarmSn, hwCauseId, hwTrapType
                FROM HUAWEI-TC-MIB 
             huaweiUtility
             	FROM HUAWEI-MIB
             Adsl2TransmissionModeType,
             Adsl2SymbolProtection,
             Adsl2PsdMaskDs,
             Adsl2PsdMaskUs
                FROM ADSL2-LINE-TC-MIB;
             		
             hwAdsl MODULE-IDENTITY    
                LAST-UPDATED "201703210000Z"
                ORGANIZATION
              	   "Huawei Technologies Co.,Ltd."
                CONTACT-INFO 
                   "Huawei Industrial Base
                    Bantian, Longgang
                    Shenzhen 518129
                    People's Republic of China
                    Website: http://www.huawei.com
                    Email: support@huawei.com
                   "
                DESCRIPTION
              	   "This MIB is used for defining Huawei's ADSL management MIB objects."     
              	   
	  --  Revision history
	  REVISION     "201703210000Z"
          DESCRIPTION  "V3.47, Modified the description of the leaf hwxdslDynamicProfTargetSnrmDs,
                        hwxdslDynamicProfTargetSnrmUs, hwxdslDynamicProfMaxSnrmDs, hwxdslDynamicProfMaxSnrmUs,
                        hwxdslDynamicProfMinSnrmDs, hwxdslDynamicProfMinSnrmUs, hwxdslDynamicProfCh1MaxDelayDs,
                        hwxdslDynamicProfCh1MaxDelayUs, hwxdslDynamicProfCh2MaxDelayDs, hwxdslDynamicProfCh2MaxDelayUs,
                        hwxdslDynamicProfL0Time, hwxdslDynamicProfL2Time, hwxdslDynamicProfL2Atpr, hwxdslDynamicProfL2Atprt,
                        hwxdslDynamicProfDpboEsEL, hwxdslDynamicProfDpboMus, hwxdslDynamicProfDpboFMin,
                        hwxdslDynamicProfDpboFMax, hwxdslDynamicProfUpboKL, hwxdslDynamicProfMaxNomAtpDs,
                        hwxdslDynamicProfMaxNomAtpUs."
	  
	  REVISION     "201407070000Z"
          DESCRIPTION  "V3.46, Modified the version of the mib."	  
	  
	 REVISION     "201402250000Z"
         DESCRIPTION  "V3.45, Change ifType import from IF-MIB."

	  REVISION     "201212270000Z"
          DESCRIPTION  "V3.44, modify the status of the nodes to deprecated:hwXdslDynamicInfoCollectTable."
          	  
	  REVISION     "201205020000Z"
          DESCRIPTION  "V3.43, modify the description of the leaf hwxdslDynamicProfMaxNomPsdDs, hwxdslDynamicProfMaxNomPsdUs,
                        modify the node name from hwdslAtucChanPerfPrev1DayCrcBlks to hwadslAtucChanPerfPrev1DayCrcBlks.
                        Delete unnecessary en dashes."
	  
	  REVISION     "201201090000Z"
          DESCRIPTION  "V3.42, modify the description of the leaf hwXdslDynamicInfoCollect."
	  
	  REVISION     "201107070000Z"
          DESCRIPTION  "V3.41, modify the description of the leaf:hwadsl2TranMissionStardardMask, hwadsl2TransMissionAnnexMask, hwAdslTransmissionMode.
                        modify the unit of the leaf nodes from bps to Kbps:hwadsl2L2ModeMinDataRate, hwadsl2L2ModeMaxDataRate, hwadsl2L2ModePayloadRateThreshold."
	  
	  REVISION     "201104070000Z"
          DESCRIPTION  "V3.40, add annexA998-D-48, annexA998-D-128, annexB998ADE17-M2x-M in hwxdslDynamicProfClassMask.
                        modify syntax from annexB997E17-M2x-NUS0 to annexB997E17-M2x-A in hwxdslDynamicProfClassMask.
                        modify the description of hwxdslDynamicProfClassMask."
          
	  REVISION     "201103080000Z"          
          DESCRIPTION  "V3.39, modify the value range of the leaf hwAdslExtDsMaxPsd."
                              
	  REVISION     "201009280000Z"
          DESCRIPTION  "V3.38, modify the description of the whole MIB file."
         	  
                              
	  REVISION     "201009260000Z"
          DESCRIPTION  "V3.37, Add invalid value: hwXdslPortIopCaptureOperType, hwXdslPortIopCaptureOperStatus, hwXdslDynamicInfoCollect."
         	  
	  REVISION     "201009070000Z"
          DESCRIPTION  "V3.36, The name of the node hwAdslAtucPerfFailInits is changed to hwAdslAtucPerfFailFullInits.
                               The name of the node hwAdslAtucPerfCurr15MinFailInits is changed to hwAdslAtucPerfCurr15MinFailFullInits.
                               The name of the node hwAdslAtucPerfCurr1DayFailInits is changed to hwAdslAtucPerfCurr1DayFailFullInits.
                               The name of the node hwAdslAtucPerfPrev1DayFailInits is changed to hwAdslAtucPerfPrev1DayFailFullInits.
                               The name of the node hwAdslAtucIntervalFailInits is changed to hwAdslAtucIntervalFailFullInits."
          
	  REVISION     "201007190000Z"           
          DESCRIPTION  "V3.35, The description of hwXdslPortPowerState is changed and enumerated value l1(4) is added."
	  
	  REVISION     "201006220000Z"          
          DESCRIPTION  "V3.34, modify the errors of the MIB file." 
	  
	  REVISION     "201005050000Z"          
          DESCRIPTION  "V3.33, modify the errors of the MIB file." 
	  
	  REVISION     "201003290000Z"          
          DESCRIPTION  "V3.32, modify the value range of the leaf hwadslLineExtConfProfile, hwadslLineDynamicProfile
                        hwAdslLineConfProfile.                        
                        add invalid value."
                        
	  REVISION     "201003220000Z"          
          DESCRIPTION  "V3.31, Modify the description of the leaf node.
	                Modify the SYNTAX string.
	                Add invalid value."	
                                  
	  REVISION     "201003100000Z"          
          DESCRIPTION  "V3.30, Modify the description of the leaf node."	 
                                
	  REVISION     "201002080000Z"          
          DESCRIPTION  "V3.29, modify the description of the leaf node.
	                Modify the hwAdsl2SCStateTable name from hwAdsl2SCStatusTable to hwAdsl2SCStateTable."
	  
	  REVISION     "201001120000Z"          
          DESCRIPTION  "V3.28, change the data type of nodes hwXdslPortLastUpTime, hwXdslPortLastDownTime, 
	               and hwXdslPortClearUpCntTime from PortDateAndTime to DateAndTime."   
	  
	  REVISION     "200906090000Z"          
          DESCRIPTION  "V3.27, modify hwadsl2TransMissionAnnexMask(The transMission annex Mask) for Annex.J ."                  
                                                
          REVISION     "200906090000Z"          
          DESCRIPTION  "V3.26, Add leaf node hwadslLConfProfAdslMode in table hwadslLineExtConfProfileTable."
	                                        
          REVISION     "200304280000Z"          
          DESCRIPTION  "V3.00, add MIB file description ." 
                                                
          REVISION     "200211290000Z"                                                 
          DESCRIPTION  "V2.00, add hwAdslLinePvcTable"                                 
                                                                                       
          REVISION     "200208220000Z"                                                 
          DESCRIPTION  "V1.00, Initial version"                       	
              	
	    ::= { huaweiUtility 31 }	
	     		                       
    HWADSLSYMBOLPROTECTION ::= TEXTUAL-CONVENTION
		     STATUS current    
		     DESCRIPTION  
		         "Define HWADSLSYMBOLPROTECTION.
		          Options:
		          1. noProtection(0)
		          2. halfSymbol(1)
		          3. singleSymbol(2)
		          4. twoSymbols(4)
		          5. threeSymbols(6)
		          6. fourSymbols(8)
		          7. fiveSymbols(10)
		          8. sixSymbols(12)
		          9. sevenSymbols(14)
		          10. eightSymbols(16)
		          11. nineSymbols(18)
		          12. tenSymbols(20)
		          13. elevenSymbols(22)
		          14. twelveSymbols(24)
		          15. thirteenSymbols(26)
		          16. fourteenSymbols(28)
		          17. fifteenSymbols(30)
		          18. sixteenSymbols(32)
		          19. null(65535)
		         "
		       SYNTAX INTEGER {  
		       noProtection(0),
		       halfSymbol(1),  
		       singleSymbol(2),
		       twoSymbols(4),
		       threeSymbols(6),
		       fourSymbols(8),
		       fiveSymbols(10),
		       sixSymbols(12),
		       sevenSymbols(14),
		       eightSymbols(16),
		       nineSymbols(18),
		       tenSymbols(20),
		       elevenSymbols(22),
		       twelveSymbols(24),
		       thirteenSymbols(26),
		       fourteenSymbols(28),
		       fifteenSymbols(30),
		       sixteenSymbols(32),
		       null(65535)
   		 }
   		 
   	HWADSLTRANSMISSIONMODETYPE ::= TEXTUAL-CONVENTION
		     STATUS current
		     DESCRIPTION  
		         "Define HWADSLTRANSMISSIONMODETYPE.
		          Options:
		          1. none(0)           - Unknown
		          2. q9921gdmt(1)      - G992.1-Annex A
		          3. q9922glite(2)     - G992.2-Annex A
		          4. ansit1413(3)      - T1.413
		          5. q9923adsl2a(4)    - G992.3-Annex A
		          6. q9925adsl2plus(5) - G992.5-Annex A 
		          7. q9923adsl2l(6)    - G992.3-Annex L
		         "
		     SYNTAX INTEGER {
		       none(0),
		       q9921gdmt(1),
		       q9922glite(2),
		       ansit1413(3),
		       q9923adsl2a(4),
		       q9925adsl2plus(5),
		       q9923adsl2l(6)   		 
	       }
       HWADSL2ANNEXMSCOPE ::= TEXTUAL-CONVENTION
		     STATUS current
		     DESCRIPTION  
		         "Define HWADSL2ANNEXMSCOPE.
		          Options:
		          1. toneIndex7to32(1)
		          2. toneIndex7to36(2)
		          3. toneIndex7to40(3)
		          4. toneIndex7to44(4)
		          5. toneIndex7to48(5)
		          6. toneIndex7to52(6)
		          7. toneIndex7to56(7)
		          8. toneIndex7to60(8)
		          9. toneIndex7to64(9)
		          10. invalidValue(-1)
		         "
		     SYNTAX INTEGER { 
		     toneIndex7to32(1),                                                           
                     toneIndex7to36(2),                                                           
                     toneIndex7to40(3),                                                           
                     toneIndex7to44(4),                                                             
                     toneIndex7to48(5),
                     toneIndex7to52(6),  
                     toneIndex7to56(7),                                                           
                     toneIndex7to60(8),                                                           
                     toneIndex7to64(9),
                     invalidValue(-1)
                     }

--    PortDateAndTime ::= TEXTUAL-CONVENTION
--    DISPLAY-HINT "2d-1d-1d,1d:1d:1d.2d"
--    STATUS       current
--    DESCRIPTION
--            "A date-time specification of Xdsl Port.
--
--             field  octets  contents                  range
--               1      1-2   year                      0..65536
--               2       3    month                     1..12
--               3       4    day                       1..31
--               4       5    hour                      0..23
--               5       6    minutes                   0..59
--               6       7    seconds                   0..59
--               7       8-9  mili-seconds              0..999
--
--            For example, Tuesday May 26, 1992 at 1:30:15:999 would be
--           displayed as:
--
--                             1992-5-26,13:30:15.999
--
--           "
--   	SYNTAX       OCTET STRING (SIZE (9)) 
--
-- Node definitions
--
	   	
   	hwadslAturChanCurrINP OBJECT-TYPE
             SYNTAX      Gauge32
             UNITS       "DMT Symbol"
             MAX-ACCESS  read-only
             STATUS      current
             DESCRIPTION
                 "Indicates Impulse Noise Protection on upstream direction.
                  The value multiply 1/10000 is the real value.
                  Unit: DMT Symbol
                 "
         ::= { adslAturChanEntry 65536 }
         
	hwadslAturChanRsSymbols OBJECT-TYPE
            SYNTAX      Gauge32
            UNITS        "byte"
            MAX-ACCESS  read-only
            STATUS      current
            DESCRIPTION
                "Indicates Reed-Solomon symbols on upstream direction.
                 The value multiply 1/10000 is the real value.
                 Unit: byte
                "
	    ::= { adslAturChanEntry 65537 }
	hwadslAturChanRsRedundancy OBJECT-TYPE
            SYNTAX      Gauge32
            UNITS        "byte"
            MAX-ACCESS  read-only
            STATUS      current
            DESCRIPTION
                "Indicates Reed-Solomon redundancy on upstream direction.
                 Unit: byte
                "
	    ::= { adslAturChanEntry 65538 }
	hwadslAturChanRsDepth OBJECT-TYPE
            SYNTAX      Gauge32
            UNITS        "byte"
            MAX-ACCESS  read-only
            STATUS      current
            DESCRIPTION
                "Indicates Reed-Solomon depth on upstream direction.
                 Unit: byte
                "
	    ::= { adslAturChanEntry 65539 }  
	
	hwadslAturChanSymbolLength OBJECT-TYPE
            SYNTAX      Gauge32
            UNITS        "bit"
            MAX-ACCESS  read-only
            STATUS      current
            DESCRIPTION
                "Indicates the Bit Number of the DMT Symbol on upstream direction.
                 Unit: bit
                "
	    ::= { adslAturChanEntry 65540 }
	
	hwadslAturChanPhyRrrcBits OBJECT-TYPE
            SYNTAX      Gauge32
            MAX-ACCESS  read-only
            STATUS      current
            DESCRIPTION
                "The bits in the channel that used to retransmission on upstream direction."
            ::= { adslAturChanEntry 65541 }
    
        hwadslAturChanPhyRtxQueue OBJECT-TYPE
            SYNTAX      Gauge32
            MAX-ACCESS  read-only
            STATUS      current
            DESCRIPTION
                "Queues in send buffer on upstream direction."
            ::= { adslAturChanEntry 65542 }
	        	         	         
	hwadslAturChanRsSize OBJECT-TYPE
            SYNTAX      Gauge32
            UNITS        "byte"
            MAX-ACCESS  read-only
            STATUS      current
            DESCRIPTION
                "Indicates Reed-Solomon Codeword Size on upstream direction.
                 Range: 0-255
                 Unit: byte
                "
	    ::= { adslAturChanEntry 65543 }  
	         
	hwadslAturChanCodeGain OBJECT-TYPE
            SYNTAX      Gauge32
            MAX-ACCESS  read-only
            STATUS      current
            DESCRIPTION
                "Indicates Code Gain on upstream direction.
                 It ranges from 0 to 16 units of 0.5 dB (physical values
                 are 0 to 8 dB).
                "
	    ::= { adslAturChanEntry 65544 } 
	
	hwadslAturTransmissionCapabilities OBJECT-TYPE       
	    SYNTAX      Adsl2TransmissionModeType
	    MAX-ACCESS  read-only
	    STATUS      current
	    DESCRIPTION
	        "The ATU transmission system capability list of the different
	         coding types. It is coded in a bit-map representation with 1
	         or more bits set. A bit set to '1' means that the ATU
	         supports the respective coding. The value may be derived
	         from the handshaking procedures defined in G.994.1.
	        "
            ::= { adslAturPhysEntry 65535 }         

-- adslAturPhysTable
        -- 1.3.6.1.2.1.10.94.1.1.3.1.65536
        hwAdslAturCurrSignalAtn OBJECT-TYPE
            SYNTAX Gauge32 (0..630)
            UNITS "tenth dB"
            MAX-ACCESS read-only
            STATUS current
            DESCRIPTION
                "The signal attenuation value on ATUR: It indicates the difference between the transmit signal of the ATU-C and the receive signal of the ATU-R.
                 Range: 0-630
                 Unit: tenth dB
                "
            ::= { adslAturPhysEntry 65536 }
	hwadslAtucChanCurrINP OBJECT-TYPE
            SYNTAX      Gauge32
            UNITS       "DMT Symbol"
            MAX-ACCESS  read-only
            STATUS      current
            DESCRIPTION
                "Indicates Impulse Noise Protection on downstream direction.
                 The value multiply 1/10000 is the real value.
                 Unit: DMT Symbol
                "
	    ::= { adslAtucChanEntry 65536 }
	         
	hwadslAtucChanRsSymbols OBJECT-TYPE
            SYNTAX      Gauge32
            UNITS        "byte"
            MAX-ACCESS  read-only
            STATUS      current
            DESCRIPTION
                "Indicates Reed-Solomon symbols on downstream direction.
                 The value multiply 1/10000 is the real value.
                 Unit: byte
                "
	    ::= { adslAtucChanEntry 65537 }
	         
	hwadslAtucChanRsRedundancy OBJECT-TYPE
            SYNTAX      Gauge32
            UNITS        "byte"
            MAX-ACCESS  read-only
            STATUS      current
            DESCRIPTION
                "Indicates Reed-Solomon redundancy on downstream direction.
                 Unit: byte
                "
	    ::= { adslAtucChanEntry 65538 }
	hwadslAtucChanRsDepth OBJECT-TYPE
            SYNTAX      Gauge32
            UNITS        "byte"
            MAX-ACCESS  read-only
            STATUS      current
            DESCRIPTION
                "Indicates Reed-Solomon depth on downstream direction.
                 Unit: byte
                "
	    ::= { adslAtucChanEntry 65539 } 
	         
	hwadslAtucChanSymbolLength OBJECT-TYPE
            SYNTAX      Gauge32
            UNITS        "bit"
            MAX-ACCESS  read-only
            STATUS      current
            DESCRIPTION
                "Indicates the Bit Number of the DMT Symbol on downstream direction.
                 Unit: bit
                "
	    ::= { adslAtucChanEntry 65540 }   
	         
	hwadslAtucChanPhyRrrcBits OBJECT-TYPE
            SYNTAX      Gauge32
            MAX-ACCESS  read-only
            STATUS      current
            DESCRIPTION
                "The bits in the channel that used to retransmission on downstream direction."
            ::= { adslAtucChanEntry 65541 }
    
        hwadslAtucChanPhyRtxQueue OBJECT-TYPE
            SYNTAX      Gauge32
            MAX-ACCESS  read-only
            STATUS      current
            DESCRIPTION
                "Queues in send buffer on downstream direction."
            ::= { adslAtucChanEntry 65542 }

        hwadslAtucChanRsSize OBJECT-TYPE
	              SYNTAX      Gauge32
	              UNITS        "byte"
	              MAX-ACCESS  read-only
	              STATUS      current
	              DESCRIPTION
	                  "Indicates Reed-Solomon Codeword Size on downstream direction .
	                   Range: 0-255
	                   Unit: byte
	                  "
	          ::= { adslAtucChanEntry 65543 }    
	          
	    hwadslAtucChanCodeGain OBJECT-TYPE
	              SYNTAX      Gauge32
	              MAX-ACCESS  read-only
	              STATUS      current
	              DESCRIPTION
	                  "Indicates Code Gain on downstream direction.
	                   It ranges from 0 to 16 units of 0.5 dB (physical values
 	                   are 0 to 8 dB).
 	                  "
	          ::= { adslAtucChanEntry 65544 }
        
            hwadslAtucChanPcb OBJECT-TYPE
	              SYNTAX      Gauge32
	              UNITS        "tenth dB"
	              MAX-ACCESS  read-only
	              STATUS      current
	              DESCRIPTION
	                  "Indicates Power Cut-back on downstream direction.
	                   It ranges from 0 to 400 units of 0.1 dB(physical values
 	                   are 0 to 40 dB).
 	                   Unit: tenth dB
 	                  "
	          ::= { adslAtucChanEntry 65545 }

		hwAdslAtucConfDownBitSwap OBJECT-TYPE
			SYNTAX INTEGER
				{
				enabled(1),
				disabled(2)
				}
			MAX-ACCESS read-create
			STATUS current
			DESCRIPTION
			    "Enables and disables the down bitswap of a template.
			     Options:
			     1. enabled(1)  - Indicates that the downstream bit swap is enabled
			     2. disabled(2) - Indicates that the downstream bit swap is disabled
			     Default: enabled(1)
			    "		
                           
			::= { adslLineConfProfileEntry 65536 }
		
		hwAdslAtucConfUpBitSwap OBJECT-TYPE
			SYNTAX INTEGER
				{
				enabled(1),
				disabled(2)
				}
			MAX-ACCESS read-create
			STATUS current
			DESCRIPTION
			    "Enables and disables the up bitswap of a template.
			     Options:
			     1. enabled(1)  - Indicates that the upstream bit swap is enabled
			     2. disabled(2) - Indicates that the upstream bit swap is disabled
			     Default: enabled(1)
			    "
                           
			::= { adslLineConfProfileEntry 65537 }
		
		hwAdslTrellionsModeEnable OBJECT-TYPE
			SYNTAX INTEGER
				{
				enabled(1),
				disabled(2)
				}
			MAX-ACCESS read-create
			STATUS current
			DESCRIPTION
			    "Enables and disables the Trellions mode.
			     Options:
			     1. enabled(1)   - Indicates that the trellis coding is enabled
			     2. disabled(2)  - Indicates that the trellis coding is disabled
			     Default: enabled(1)
			    "
                            
			::= { adslLineConfProfileEntry 65538 }
		
		hwAdslTransmissionMode OBJECT-TYPE
			SYNTAX INTEGER
				{
				all(1),
				fullRate(2),
				gliteOnly(3),
				t1413Only(4),
				gdmtOnly(5),
				ghs(6),
				g992Dot1(7),
				g992Dot2(8),
				g992Dot3(9),
				g992Dot4(10),
				g992Dot5(11),
				adslAllOnly(12),
				adslAndAdsl2(13)
				}
			MAX-ACCESS read-create
			STATUS current
			DESCRIPTION
			    "Indicates the transmission mode of this channel.
			     Options:
			     1. all(1)            - All (G992.1, G992.2, T1.413)(Default)
			     2. fullRate(2)       - Full rate(G992.1 or T1.413)
			     3. gliteOnly(3)      - G992.2(g.lite) only	
			     4. t1413Only(4)      - T1.413 only
			     5. gdmtOnly(5)       - G992.1,G992.3,G992.5,(g.dmt) only
			     6. ghs(6)            - g.hs (G992.1,G992.2,G992.3,G992.4,G992.5,G992.5 is prior)
			     7. g992Dot1(7)       - G992.1
			     8. g992Dot2(8)       - G992.2
			     9. g992Dot3(9)       - G992.3
			     10. g992Dot4(10)	  - G992.4
			     11. g992Dot5(11)	  - G992.5
			     12. adslAllOnly(12)  - ADSL ALL ONLY
			     13. adslAndAdsl2(13) - G.992.1,G.992.3,T1.413(Not support)
			     Default: all(1)
			    "
			
			::= { adslLineConfProfileEntry 65539 }
		
		hwAdslLinePvcTable OBJECT-TYPE
			SYNTAX SEQUENCE OF HwAdslLinePvcEntry
			MAX-ACCESS not-accessible
			STATUS current
			DESCRIPTION
			    "PVC configuration table of the ADSL port and used to configure the VPI and VCI of the ADSL port.
                             The indexes of this table are ifIndex,hwAdsllinePvcVpi,and hwAdsllinePvcVci.
                             This table is used to configure only the CO PVC.
                            "

			::= { adslMibObjects 65536 }
		
		hwAdslLinePvcEntry OBJECT-TYPE
			SYNTAX HwAdslLinePvcEntry
			MAX-ACCESS not-accessible
			STATUS current
			DESCRIPTION
		            "PVC configuration table of the ADSL port and used to configure the VPI and VCI of the ADSL port.
                             The indexes of this entry are ifIndex,hwAdsllinePvcVpi,and hwAdsllinePvcVci.
                             This table is used to configure only the CO PVC.
                            "

			INDEX { ifIndex, hwAdsllinePvcVpi, hwAdslLinePvcVci }
			::= { hwAdslLinePvcTable 1 }
		
		HwAdslLinePvcEntry ::=
			SEQUENCE { 
				hwAdsllinePvcVpi
					Integer32,
				hwAdslLinePvcVci
					Integer32,
				hwAdslLinePvcVlanId
					Integer32,
				hwAdslLinePvcPriority
					Integer32,
				hwAdslLinePvcDsBand
					Integer32,
				hwAdslLinePvcUsBand
					Integer32,
				hwAdslLinePvcMCastEnable
					INTEGER,
				hwAdslLinePvcIGMPEnable
					INTEGER,
				hwAdslLinePvcIndex
					Integer32,
				hwAdslLinePvcConnectType
					INTEGER,	
				hwAdslLinePvcRowStatus
					RowStatus
			 }

		hwAdsllinePvcVpi OBJECT-TYPE
			SYNTAX Integer32 (0..255)
			MAX-ACCESS read-only
			STATUS current
			DESCRIPTION
			    "The VPI of the adsl line."
			::= { hwAdslLinePvcEntry 1 }
		
		hwAdslLinePvcVci OBJECT-TYPE
			SYNTAX Integer32 (0..511)
			MAX-ACCESS read-only
			STATUS current
			DESCRIPTION
			    "The VCI of the adsl line."
			::= { hwAdslLinePvcEntry 2 }
			
		hwAdslLinePvcVlanId OBJECT-TYPE
			SYNTAX Integer32 (1..4000)
			MAX-ACCESS read-write
			STATUS current
			DESCRIPTION
			    "The VLAN ID of the adsl line PVC.
			     Range: 1-4000
			    "
			::= { hwAdslLinePvcEntry 3 }
		
		hwAdslLinePvcPriority OBJECT-TYPE
			SYNTAX Integer32 (0..7)
			MAX-ACCESS read-write
			STATUS current
			DESCRIPTION
			    "The Priority value of the adsl line PVC.
			     Range: 0-7
			    "
			DEFVAL { 0 }
			::= { hwAdslLinePvcEntry 4 }
		
		hwAdslLinePvcDsBand OBJECT-TYPE
			SYNTAX Integer32 (0..450)
			MAX-ACCESS read-write
			STATUS current
			DESCRIPTION
			    "The down stream band of the adsl line PVC.
			     Range: 0-450
			    "
			DEFVAL { 0 }
			::= { hwAdslLinePvcEntry 5 }
		
		hwAdslLinePvcUsBand OBJECT-TYPE
			SYNTAX Integer32 (0..450)
			MAX-ACCESS read-write
			STATUS current
			DESCRIPTION
			    "The up stream band of the adsl line PVC.
			     Range: 0-450
			    "
			::= { hwAdslLinePvcEntry 6 }
		
		hwAdslLinePvcMCastEnable OBJECT-TYPE
			SYNTAX INTEGER
				{
				enable(1),
				disable(2)
				}
			MAX-ACCESS read-write
			STATUS current
			DESCRIPTION
			    "This object allows the adsl line PVC to support multicast.
			     Options:
			     1. enable(1)  - Indicates that the PVC of the ADSL port is enabled to support the multicast
			     2. disable(2) - Indicates that the PVC of the ADSL port is disabled to support the multicast
			     Default: disable(2)
			    "
			DEFVAL { disable }
			::= { hwAdslLinePvcEntry 7 }
		
		hwAdslLinePvcIGMPEnable OBJECT-TYPE
			SYNTAX INTEGER
				{
				enable(1),
				disable(2)
				}
			MAX-ACCESS read-write
			STATUS current
			DESCRIPTION
                "This object allows the adsl line PVC to support IGMP.
                 Options:
                 1. enable(1)  - Indicates that the PVC of the ADSL port is enabled to support IGMP
                 2. disable(2) - Indicates that the PVC of the ADSL port is disabled to support IGMP
                 Default: disable(2)
                "
			DEFVAL { disable }
			::= { hwAdslLinePvcEntry 8 }
		
		hwAdslLinePvcIndex OBJECT-TYPE
			SYNTAX Integer32 (1..8)
			MAX-ACCESS read-write
			STATUS current
			DESCRIPTION
			    "The index of the adsl line PVC.
			     Range: 1-8
			    "
			::= { hwAdslLinePvcEntry 9 }
		
		hwAdslLinePvcConnectType OBJECT-TYPE
			SYNTAX INTEGER 
				{
				auto(0),
				llc1483B(1),
				pppoaLLC(2),
				pppoaVcmux(3),
				ipoaLLc(4),
				ipoaVcmux(5)
				}
			MAX-ACCESS read-only
			STATUS current
			DESCRIPTION
			    "The Connected type of the adsl line PVC.
			     Options:
                             1. auto(0)       - The Connected type of the adsl line PVC is auto
                             2. llc1483B(1)   - The Connected type of the adsl line PVC is llc1483B
                             3. pppoaLLC(2)   - The Connected type of the adsl line PVC is pppoaLLC
                             4. pppoaVcmux(3) - The Connected type of the adsl line PVC is pppoaVcmux
                             5. ipoaLLc(4)    - The Connected type of the adsl line PVC is ipoaLLc
                             6. ipoaVcmux(5)  - The Connected type of the adsl line PVC is ipoaVcmux
			    "
			::= { hwAdslLinePvcEntry 10 }
		
		hwAdslLinePvcRowStatus OBJECT-TYPE
			SYNTAX RowStatus
			MAX-ACCESS read-create
			STATUS current
			DESCRIPTION
				"Row status. Add or delete a table item."
			::= { hwAdslLinePvcEntry 11 }
     --    adsl extend profile (insert to adslLineTable)     
	        hwadslLineExtConfProfile OBJECT-TYPE
	             SYNTAX      OCTET STRING (SIZE (0..32))
	             MAX-ACCESS  read-write
	             STATUS      current
	             DESCRIPTION
	                 "The value of this object identifies the row
	                  in the ADSL Extend Line Configuration Profile Table,
	                  (adslLineExtConfProfileTable), which applies to this
	                  ADSL line, and channels if applicable.
	                  NULL - indicates that there is no extend line profile 
	                  bound to this port.
	                  Range: 0-32
	                "
	         ::= { adslLineEntry 65536 }	
	         
	        hwadslLineDynamicProfile OBJECT-TYPE
	             SYNTAX      OCTET STRING (SIZE (0..32))
	             MAX-ACCESS  read-write
	             STATUS      current
	             DESCRIPTION
	                 "The value of this object identifies the row
	                 in the ADSL Dynamic Profile Table,which applies to this
	                 ADSL line, and channels if applicable.
	                 NULL - indicates that there is no Dynamic profile 
	                 bound to this port.
	                 Range: 0-32
	                "
	         ::= { adslLineEntry 65537 }
		
		hwAdslLineBitAllocationTable OBJECT-TYPE
			SYNTAX SEQUENCE OF HwAdslLineBitAllocationEntry
			MAX-ACCESS not-accessible
			STATUS current
			DESCRIPTION
			    "The hwAdslLineBitAllocationTable contains the detailed bit-allocation
			     information for the current link. This information can be used to determine 
			     whether a given sub-carrier loop has sufficient margin to support ADSL data 
			     rates, and possibly to determine whether certain specific types of interfe-
			     rence or line attenuation exist.The bit allocation information are only va-
			     lid when the ATU-C is in the C-ACTIVE state.
			     The index of this table is ifIndex.
			    "
			::= { adslMibObjects 65537 }
		
		hwAdslLineBitAllocationEntry OBJECT-TYPE
			SYNTAX HwAdslLineBitAllocationEntry
			MAX-ACCESS not-accessible
			STATUS current
			DESCRIPTION
			    "The hwAdslLineBitAllocationTable contains the detailed bit-allocation
			     information for the current link. This information can be used to determine 
			     whether a given sub-carrier loop has sufficient margin to support ADSL data 
			     rates, and possibly to determine whether certain specific types of interfe-
			     rence or line attenuation exist.The bit allocation information are only va-
			     lid when the ATU-C is in the C-ACTIVE state.
			     The index of this entry is ifIndex.
			    "
			INDEX { ifIndex }
			::= { hwAdslLineBitAllocationTable 1 }
		
		HwAdslLineBitAllocationEntry ::=
			SEQUENCE { 
				hwAdslLineDownStreamBitsPerFrame
					Integer32,
				hwAdslLineUpStreamBitsPerFrame
					Integer32,
				hwAdslLineDownStreamBitAllocLow
					OCTET STRING,
				hwAdslLineDownStreamBitAllocHigh
					OCTET STRING,
				hwAdslLineUpStreamBitAlloc
					OCTET STRING
			 }

		hwAdslLineDownStreamBitsPerFrame OBJECT-TYPE
			SYNTAX Integer32
			MAX-ACCESS read-only
			STATUS current
			DESCRIPTION
			    "Number of bits required per frame in the downstream data path for the 
			     current configuration.
			    "
			::= { hwAdslLineBitAllocationEntry 1 }
		
		hwAdslLineUpStreamBitsPerFrame OBJECT-TYPE
			SYNTAX Integer32
			MAX-ACCESS read-only
			STATUS current
			DESCRIPTION
			    "Number of bits required per frame in the upstream data path for the 
			     current configuration. 
			    "
			::= { hwAdslLineBitAllocationEntry 2 }
		
		hwAdslLineDownStreamBitAllocLow OBJECT-TYPE
			SYNTAX OCTET STRING (SIZE (256))
			MAX-ACCESS read-only
			STATUS current
			DESCRIPTION
			    "when used to Adsl board
			    	 This object contains the first 128 downstream sub-carrier bit allocations 
			    	 (sub-carrier # 1-128). This object is 64 bytes in length, where each byte
			    	 contains 2 sub-carrier values. 
			    	
			    	  Byte 1 - 64           Downstream bit allocation (first 128 sub-carriers),  
			    	                        one byte for two sub-carriers. 
			    	                       			      
			    	    1        Bits 4 - 7 # bits in 1st downstream sub-carrier 
			    	    1        Bits 0 - 3 # bits in 2nd downstream sub-carrier 
			    	             ...
			    	    64       Bits 4 - 7 # bits in 127th downstream sub-carrier 
			    	    64       Bits 0 - 3 # bits in 128th downstream sub-carrier
			    	
			     when used to Adsl2+ board
			         This object contains the first 256 downstream sub-carrier bit allocations 
			    	 (sub-carrier # 1-256). This object is 256 bytes in length, where each byte
			    	 contains 1 sub-carrier values. 
			    	
			    	  Byte 1 - 256          Downstream bit allocation (first 256 sub-carriers),  
			    	                        one byte for one sub-carriers. 
			    	                       			      
			    	    1        Bits 0 - 7 # bits in 1st downstream sub-carrier				    
			    	             ...
			    	    255      Bits 0 - 7 # bits in 255th downstream sub-carrier 
			    	    256      Bits 0 - 7 # bits in 256th downstream sub-carrier
			    "
			::= { hwAdslLineBitAllocationEntry 3 }
		
		hwAdslLineDownStreamBitAllocHigh OBJECT-TYPE
			SYNTAX OCTET STRING (SIZE (256))
			MAX-ACCESS read-only
			STATUS current
			DESCRIPTION
			    "when used to Adsl board
			    	 This object contains the second 128 downstream sub-carrier bit allocations 
			    	 (sub-carrier # 129-256). This object is 64 bytes in length, where each byte
			    	 contains 2 sub-carrier values. 
			    	
			    	  Byte 1 - 64           Downstream bit allocation (second 128 sub-carriers),  
			    	                        one byte for two sub-carriers. 
			    	                      			      
			    	    1        Bits 4 - 7 # bits in 129th downstream sub-carrier 
			    	    1        Bits 0 - 3 # bits in 130th downstream sub-carrier 
			    	             ...
			    	    64       Bits 4 - 7 # bits in 255th downstream sub-carrier 
			    	    64       Bits 0 - 3 # bits in 256th downstream sub-carrier
                            
		             when used to Adsl2+ board
			         This object contains the second 256 downstream sub-carrier bit allocations 
			    	 (sub-carrier # 257-512). This object is 256 bytes in length, where each byte
			    	 contains 1 sub-carrier values. 
			    	
			    	  Byte 1 - 256          Downstream bit allocation (second 256 sub-carriers),  
			    	                        one byte for one sub-carriers. 
			    	                       			      
			    	    1        Bits 0 - 7 # bits in 1st downstream sub-carrier				    
			    	             ...
			    	    255      Bits 0 - 7 # bits in 255th downstream sub-carrier 
			    	    256      Bits 0 - 7 # bits in 256th downstream sub-carrier
			    "				
			::= { hwAdslLineBitAllocationEntry 4 }
		
		hwAdslLineUpStreamBitAlloc OBJECT-TYPE
			SYNTAX OCTET STRING (SIZE (64))
			MAX-ACCESS read-only
			STATUS current
			DESCRIPTION
			    "when used to Adsl board
			    	 This Object contains 64 upstream sub-carrier bit allocations (sub-carrier # 1-64).
			    	 This Object is 32 bytes in length, where each byte contains 2 sub-carrier values.
			    	 
			    	   Byte 1-32         	Upstream bit allocation information, total: 32 bytes,
			    	                        one byte for two sub-carriers.
			    	 
			    	    1      Bits 7 - 4  # bits in 1st upstream sub-carrier
			    	    1      Bits 3 - 0  # bits in 2nd upstream sub-carrier
			    	            ...
			    	    32     Bits 7 - 4  # bits in 63rd upstream sub-carrier
			    	    32     Bits 3 - 0  # bits in 64th upstream sub-carrier
			    		
			     when used to Adsl2+ board
			         This Object contains 64 upstream sub-carrier bit allocations (sub-carrier # 1-64).
			    	 This Object is 64 bytes in length, where each byte contains 1 sub-carrier values.
			    	 
			    	   Byte 1-64         	Upstream bit allocation information, total: 64 bytes,
			    	                        one byte for one sub-carriers.
			    	 
			    	    1      Bits 7 - 0  # bits in 1st upstream sub-carrier				  
			    	            ...				   
			    	    64     Bits 7 - 0  # bits in 64th upstream sub-carrier
			    "
			::= { hwAdslLineBitAllocationEntry 5 }
		
		hwXdslPortTable OBJECT-TYPE
			SYNTAX SEQUENCE OF HwXdslPortEntry
			MAX-ACCESS not-accessible
			STATUS current
			DESCRIPTION
			    "This table includes xDSL(e.g. adsl,g.shdsl,vdsl...)port information,
			     Used to support common attributes of the ADSL, G.SHDSL, and VDSL ports.
                             The index of this table is ifIndex.
                            "
			::= { adslMibObjects 65538 }
		
		hwXdslPortEntry OBJECT-TYPE
			SYNTAX HwXdslPortEntry
			MAX-ACCESS not-accessible
			STATUS current
			DESCRIPTION
			    "This table includes xDSL(e.g. adsl,g.shdsl,vdsl...)port information,
			     Used to support common attributes of the ADSL, G.SHDSL, and VDSL ports.
                             The index of this entry is ifIndex.
                            "
			INDEX { ifIndex }
			::= { hwXdslPortTable 1 }
		
		HwXdslPortEntry ::=
			SEQUENCE { 
				hwXdslPortMaxMacLearn
		                    Integer32,
				hwXdslPortRateMonitorThreshold
				    Integer32,
				hwXdslPortUpThresholdTxRate
				    Gauge32,
				hwXdslPortDownThresholdTxRate
				    Gauge32,
				hwXdslPortRateMonitorAlarmEnable
				    INTEGER,
				hwXdslPortUpTime
				    Counter32,
				hwXdslPortNTEPowerStatus
				    INTEGER,
				hwXdslPortCurrentUpRate
				    Integer32 ,
				hwXdslPortCurrentDownRate
				    Integer32 ,
				hwXdslPortFarEndRunState 
				    INTEGER,
				hwXdslPortPowerState 
				    INTEGER,
				hwXdslPortUpCnt
				    Unsigned32 ,
			        hwXdslPortUpCntAdminStatus
				    INTEGER ,
				hwXdslPortLastUpTime 
				    DateAndTime ,
				hwXdslPortLastDownTime
				    DateAndTime ,    
				hwXdslPortClearUpCntTime
                                    DateAndTime ,
     			        hwXdslPortRetrainCnt 
     			            Unsigned32 ,
     			        hwXdslPortLastRetrainReason
     			            Unsigned32,
     			        hwXdslPortLoopFlag 	
     			            INTEGER,
     			        hwXdslPortUpThreshold
     			            Integer32,
     			        hwXdslPortDownThreshold
     			            Integer32			    
			 }

		hwXdslPortMaxMacLearn OBJECT-TYPE
			SYNTAX Integer32 (0..255)
			MAX-ACCESS read-write
			STATUS current
			DESCRIPTION
			    "Set Max MAC count on the XDSL port.
			     Range: 0-255
                             Default: 255
                            "
			DEFVAL { 255 }
			::= { hwXdslPortEntry 1 }
		
		hwXdslPortRateMonitorThreshold OBJECT-TYPE
			SYNTAX Integer32 (0..100)
			MAX-ACCESS read-write
			STATUS current
			DESCRIPTION
			    "Set Port monitoring rate threshold percent. Including upstream and downstream.
			     Range: 0-100
                             Default: 0
                            "
			DEFVAL { 0 }
			::= { hwXdslPortEntry 2 }

		hwXdslPortUpThresholdTxRate  OBJECT-TYPE
		      SYNTAX Gauge32
		      UNITS "bps"
		      MAX-ACCESS read-write
		      STATUS current
		      DESCRIPTION
		          "Set Port monitoring upstream rate threshold value.
		           Default: 0
		           Unit: bps
		          "	
		        DEFVAL { 0 }
		       ::= { hwXdslPortEntry 4 } 
		       
		hwXdslPortDownThresholdTxRate  OBJECT-TYPE
		      SYNTAX Gauge32
	              UNITS "bps"
		      MAX-ACCESS read-write
		      STATUS current
		      DESCRIPTION
		          "Set Port monitoring downstream rate threshold value.
		           Default: 0
		           Unit: bps
		          "	
		        DEFVAL { 0 }
		       ::= { hwXdslPortEntry 5 }
		             		
		hwXdslPortRateMonitorAlarmEnable  OBJECT-TYPE
		      SYNTAX INTEGER
				{
				enabled(1),
				disabled(2)
				}
		      MAX-ACCESS read-write
		      STATUS current
		      DESCRIPTION
		          "Enables/Disables port rate monitor alarm.
		           Options:
		           1. enabled(1)  - The port rate monitor alarm is enabled
		           2. disabled(2) - The port rate monitor alarm is disabled
		          "	
		       ::= { hwXdslPortEntry 6 }


                hwXdslPortUpTime OBJECT-TYPE
			SYNTAX Counter32
			MAX-ACCESS read-only
			STATUS current
			DESCRIPTION 
			    "Duration of the xDSL port activation.
                             Unit: seconds
                            "
 			::= { hwXdslPortEntry 7 }
 		
 		hwXdslPortNTEPowerStatus OBJECT-TYPE      
		SYNTAX INTEGER
				{
					on(1),
					off(2),
					unknown(3)
				}
			MAX-ACCESS read-only
			STATUS current
		    DESCRIPTION
		        "NTE power status, this object is defaulted off(2).
		         Options:
		         1. on(1)      - NTE power on
		         2. off(2)     - NTE power off
		         3. unknown(3) - Unknown status
		        "
		      ::= { hwXdslPortEntry 8 }
		      
		hwXdslPortCurrentUpRate  OBJECT-TYPE
		      SYNTAX Integer32 (0..30000)
		      MAX-ACCESS accessible-for-notify
		      STATUS current
		      DESCRIPTION
		          "Xdsl Port Current Upstream Value.
		           Range: 0-30000
		           Default: 0
		          "		        
		       ::= { hwXdslPortEntry 500 }
		hwXdslPortCurrentDownRate  OBJECT-TYPE
		      SYNTAX Integer32 (0..30000)
		      MAX-ACCESS accessible-for-notify
		      STATUS current
		      DESCRIPTION
		          "Xdsl Port Current Downstream Value.
		           Range: 0-30000
		           Default: 0
		          "
		       ::= { hwXdslPortEntry 501 }      		
		hwXdslPortFarEndRunState OBJECT-TYPE      
		SYNTAX INTEGER
				{
					unknown(1),
					noModem(2),
					handshake(3),
					showtime(4)
					
				}
			MAX-ACCESS read-only
			STATUS current
		DESCRIPTION
		           "Xdsl port far end Run state, This object is defaulted unknown(1).
		            Options:
		            1. unknown(1)   - Unknown status
		            2. noModem(2)   - Port is not connected to modem
		            3. handshake(3) - Handshake status
		            4. showtime(4)  - Port is activated
		           "	      
        
		      ::= { hwXdslPortEntry 600 }
	        hwXdslPortPowerState OBJECT-TYPE      
		SYNTAX INTEGER
				{
				    l0(1),
				    l2(2),
				    l3(3),
				    l1(4),
				    invalidValue(-1)
				}
		      MAX-ACCESS read-only
		      STATUS current
	              DESCRIPTION 
	                  "Xdsl port power state.
	                   Options:
	                   1. l0(1)            - Full-on state
	                   2. l2(2)            - Low power state
	                   3. l3(3)            - Idle state
	                   4. l1(4)            - Low power state
	                   5. invalidValue(-1) - Invalid value
	                   Default: l0(1)"	                                                    
		      ::= { hwXdslPortEntry 601 }  
     			          
        hwXdslPortUpCnt OBJECT-TYPE
	        SYNTAX Unsigned32
	        MAX-ACCESS read-only
	        STATUS current
	        DESCRIPTION
	            "The up counts of Xdsl port."   
	        ::= { hwXdslPortEntry 700 }  	    
		
	hwXdslPortUpCntAdminStatus   OBJECT-TYPE
	 	    SYNTAX INTEGER
	           {
                      reset(0)      
                   }
	        MAX-ACCESS read-write
	        STATUS current
	        DESCRIPTION
	            "Admin the up counts of xDSL port.
	             Options: 
	             1. reset(0) - Reset the up counts of xDSL port
	            "   
	        ::= { hwXdslPortEntry 701 } 
	                
	hwXdslPortLastUpTime OBJECT-TYPE
			SYNTAX DateAndTime
			MAX-ACCESS read-only
			STATUS current
			DESCRIPTION "Last up time of a Xdsl port."
			::= { hwXdslPortEntry 702 }   
			     
	hwXdslPortLastDownTime OBJECT-TYPE
			SYNTAX DateAndTime
			MAX-ACCESS read-only
			STATUS current
			DESCRIPTION "Last down time of a Xdsl port."
			::= { hwXdslPortEntry 703 }  
	           
        hwXdslPortClearUpCntTime OBJECT-TYPE
			SYNTAX DateAndTime
			MAX-ACCESS read-only
			STATUS current
			DESCRIPTION
			    "The time when up counts of a Xdsl port is cleared."
			::= { hwXdslPortEntry 704 }
       
       hwXdslPortRetrainCnt  OBJECT-TYPE
			SYNTAX Unsigned32
			MAX-ACCESS read-only
			STATUS current
			DESCRIPTION
			    "The retrain counts of Xdsl Line."
			::= { hwXdslPortEntry 705 }
	
       hwXdslPortLastRetrainReason OBJECT-TYPE
			SYNTAX Unsigned32
			MAX-ACCESS read-only
			STATUS current
			DESCRIPTION
			    "The last retrain reson of Xdsl Line, coded as bit mask. 
			     Only one bit can be set valid, all bits set valid means invalid retrain reason.
			    "
			::= { hwXdslPortEntry 706 }
			
	hwXdslPortLoopFlag OBJECT-TYPE
		 SYNTAX INTEGER
			{
				false(0),
				true(1)
			}	
			MAX-ACCESS read-only
			STATUS current
			DESCRIPTION
			    "Loop flag.
			     Options:
			     1. false(0) - No loop
			     2. true (1) - Loop
			    "
			::= { hwXdslPortEntry 800 }		      

		hwXdslPortUpThreshold OBJECT-TYPE
			SYNTAX Integer32 (0..100)
			MAX-ACCESS read-write
			STATUS current
			DESCRIPTION
			    "Set Port monitoring upstream rate threshold percent value.
			     Range: 0-100
			    "
			DEFVAL { 0 }
			::= { hwXdslPortEntry 810 }

		hwXdslPortDownThreshold OBJECT-TYPE
			SYNTAX Integer32 (0..100)
			MAX-ACCESS read-write
			STATUS current
			DESCRIPTION
			    "Set Port monitoring downstream rate threshold percent value.
			     Range: 0-100
			    "
			DEFVAL { 0 }
                        ::= { hwXdslPortEntry 811 }


--
-- hwAdslLinePreActParaTable
--		
		hwAdslLinePreActParaTable OBJECT-TYPE
			SYNTAX SEQUENCE OF HwAdslLinePreActParaEntry
			MAX-ACCESS not-accessible
			STATUS current
			DESCRIPTION
			    "This table provides one row for each ADSL PORT.
			     Each row contains the preactived Parameters.
			     The index of this table is ifIndex.
			    "
			::= { adslMibObjects 65539 }
		
		hwAdslLinePreActParaEntry OBJECT-TYPE
			SYNTAX HwAdslLinePreActParaEntry
			MAX-ACCESS not-accessible
			STATUS current
			DESCRIPTION
			    "This table provides one row for each ADSL PORT.
                             Each row contains the preactived Parameters.
                             The index of this entry is ifIndex.
                            "
			INDEX { ifIndex }
			::= { hwAdslLinePreActParaTable 1 }
		
		HwAdslLinePreActParaEntry ::=
			SEQUENCE { 
				hwAdslAtucPrevSnrMgn
					Integer32,
				hwAdslAturPrevSnrMgn
					Integer32,
				hwAdslAtucPrevAttainableRate
					Unsigned32,
				hwAdslAturPrevAttainableRate
					Unsigned32,
				hwAdslAtucPreAtn
					Gauge32,
				hwAdslAturPreAtn
					Gauge32,
			        hwAdslPreActiveTime
			                DateAndTime
			 }

		hwAdslAtucPrevSnrMgn OBJECT-TYPE
			SYNTAX Integer32
			UNITS "tenth dB"
			MAX-ACCESS read-only
			STATUS current
			DESCRIPTION
			    "Noise Margin as seen by this ATU-C at the 
			     time of the last adslAtucRateChangeTrap event.
			     Unit: tenth dB
			    "
			::= { hwAdslLinePreActParaEntry 1 }
		
		hwAdslAturPrevSnrMgn OBJECT-TYPE
			SYNTAX Integer32
			UNITS "tenth dB"
			MAX-ACCESS read-only
			STATUS current
			DESCRIPTION
			    "Noise Margin as seen by this ATU-R at 
			     the time of the last adslAtucRateChangeTrap event.
			     Unit: tenth dB
			    "
			::= { hwAdslLinePreActParaEntry 2 }
		
		hwAdslAtucPrevAttainableRate OBJECT-TYPE
			SYNTAX Unsigned32
			UNITS "bps"
			MAX-ACCESS read-only
			STATUS current
			DESCRIPTION
			    "Indicates the maximum attainable data rate 
			     by the ATU-C at the time of the last 
			     adslAtucRateChangeTrap event.
			     Unit: bps
			    "
			::= { hwAdslLinePreActParaEntry 3 }
		
		hwAdslAturPrevAttainableRate OBJECT-TYPE
			SYNTAX Unsigned32
			UNITS "bps"
			MAX-ACCESS read-only
			STATUS current
			DESCRIPTION
			    "Indicates the maximum attainable data rate 
			     by the ATU-R at the time of the last 
			     adslAtucRateChangeTrap event.
			     Unit: bps
			    "
			::= { hwAdslLinePreActParaEntry 4 }
		
		hwAdslAtucPreAtn OBJECT-TYPE
			SYNTAX Gauge32
			UNITS "tenth dB"
			MAX-ACCESS read-only
			STATUS current
			DESCRIPTION
			    "Measured difference in the total power 
			     transmitted as seen by this ATU-C at the time 
			     of the last adslAtucRateChangeTrap event. in tenth dB.
			     Unit: tenth dB
			    "
			::= { hwAdslLinePreActParaEntry 5 }
		
		hwAdslAturPreAtn OBJECT-TYPE
			SYNTAX Gauge32
			UNITS "tenth dB"
			MAX-ACCESS read-only
			STATUS current
			DESCRIPTION
			    "Measured difference in the total power 
			     transmitted as seen by this ATU-R at the time of the 
			     last adslAtucRateChangeTrap event. in tenth dB.
			     Unit: tenth dB
			    "
			::= { hwAdslLinePreActParaEntry 6 }

       hwAdslPreActiveTime OBJECT-TYPE
                        SYNTAX      DateAndTime
                        MAX-ACCESS  read-only
                        STATUS      current
			DESCRIPTION
			    "The last time at that the port was activated."
			::= { hwAdslLinePreActParaEntry 7 }	

--    hwPortThreePriorityTable

        hwPortThreePriorityTable OBJECT-TYPE
		    SYNTAX SEQUENCE OF HwPortThreePriorityEntry
		    MAX-ACCESS not-accessible
		    STATUS obsolete
		    DESCRIPTION
		    	"Adsl port three priority table.
		    	 The index of this table is ifIndex.
		    	"
		    ::= { adslMibObjects 65540 }
	
	    hwPortThreePriorityEntry OBJECT-TYPE
		    SYNTAX HwPortThreePriorityEntry
		    MAX-ACCESS not-accessible
		    STATUS obsolete
		    DESCRIPTION
		        "Adsl port three priority table.
		         The index of this entry is ifIndex.
		        "
		    INDEX { ifIndex }
		    ::= { hwPortThreePriorityTable 1 }
	
	    HwPortThreePriorityEntry ::=
		    SEQUENCE
    		    {
	    		    hwPortThreePriorityEnable    INTEGER
		    }
		 
	    hwPortThreePriorityEnable OBJECT-TYPE
		    SYNTAX INTEGER
		        {
		            enable(1),
		            disable(2)
		        }
		    MAX-ACCESS read-write
		    STATUS obsolete
		    DESCRIPTION
			    "Three Priority status of the interface.
			     Options:
			     1. enable(1)  - Adsl port three priority is enabled
			     2. disable(2) - Adsl port three priority is disabled
			    "
		    ::= { hwPortThreePriorityEntry 1 }    
		    
--     hwSlotMacMaxNoLimitTable
     hwSlotMacMaxNoLimitTable OBJECT-TYPE
		    SYNTAX SEQUENCE OF HwSlotMacMaxNoLimitEntry
		    MAX-ACCESS not-accessible
		    STATUS obsolete
		    DESCRIPTION
		    	"Max mac learning no limit table.
		    	 The index of this table is hwFrameIndex and hwSlotIndex.
		    	"
		    ::= { adslMibObjects 65541 }
	
	    hwSlotMacMaxNoLimitEntry OBJECT-TYPE
		    SYNTAX HwSlotMacMaxNoLimitEntry
		    MAX-ACCESS not-accessible
		    STATUS obsolete
		    DESCRIPTION
			    "Max mac learning no limit table.
			     The index of this entry is hwFrameIndex and hwSlotIndex.
			    "
		    INDEX { hwFrameIndex, hwSlotIndex }
		    ::= { hwSlotMacMaxNoLimitTable 1 }
	
	    HwSlotMacMaxNoLimitEntry ::=
		    SEQUENCE
    		    {
	    		    hwSlotMacMaxNoLimitEnable    INTEGER
		        }
		 
	    hwSlotMacMaxNoLimitEnable OBJECT-TYPE
		    SYNTAX INTEGER
		        {
		            enable(1),
		            disable(2)
		        }
		    MAX-ACCESS read-write
		    STATUS obsolete
		    DESCRIPTION
			    "This object is used to set whether all the ports in the slot limits the maximum number of learning MAC addresses.
			     Options:
			     1. enable(1)  - Don't limit the max NO. of learning mac addresses in the slot
			     2. disable(2) - Limit the max NO. of learning mac addresses in the slot
			    "
		    ::= { hwSlotMacMaxNoLimitEntry 1 } 

--
--  hwXdslPortStateStatisticTable
--
                hwXdslPortStateStatisticTable OBJECT-TYPE
			SYNTAX SEQUENCE OF HwXdslPortStateStatisticEntry
			MAX-ACCESS not-accessible
			STATUS current
			DESCRIPTION
		            "XDSL port state statistic table, used to support the statistics information about the status mapping and status 
		             of ports on the service boards, such as the ADSL, G.SHDSL and VDSL boards.
		             The indexes of this table are ifType, hwFrameIndex, and hwSlotIndex.
		            "
			::= { adslMibObjects 65542 }
		
		hwXdslPortStateStatisticEntry OBJECT-TYPE
			SYNTAX HwXdslPortStateStatisticEntry
			MAX-ACCESS not-accessible
			STATUS current
			DESCRIPTION
			    "XDSL port state statistic table, used to support the statistics information about the status mapping and status
			     of ports on the service boards, such as the ADSL, G.SHDSL and VDSL boards.
			     The indexes of this entry are ifType, hwFrameIndex, and hwSlotIndex.
			    "
			INDEX {        
			      ifType,
			      hwFrameIndex,
			      hwSlotIndex 
			      }
			::= { hwXdslPortStateStatisticTable 1 }
		
		HwXdslPortStateStatisticEntry ::=
			SEQUENCE{
				hwXdslPortStatePortNumber
					Unsigned32,
				hwXdslPortStateBitmapList
					OCTET STRING,
				hwXdslTotalOfActivatedPorts
					Unsigned32,
				hwXdslTotalOfDeactivatedPorts
					Unsigned32,	
				hwXdslTotalOfActivatingPorts
					Unsigned32,
				hwXdslTotalOfTestingPorts
					Unsigned32,										
				hwXdslTotalOfBlockedPorts
					Unsigned32,
				hwXdslTotalOfLocalLoopbackPorts
					Unsigned32,					
				hwXdslTotalOfRemoteLoopbackPorts
					Unsigned32, 
				hwXdslTotalOfFailedPorts
					Unsigned32,									
				hwXdslTotalOfUnknownPorts
					Unsigned32
				    }

		hwXdslPortStatePortNumber OBJECT-TYPE
			SYNTAX Unsigned32
			MAX-ACCESS read-only
			STATUS current
			DESCRIPTION   
			    "This Object is Port Number of One Slot."
			::= { hwXdslPortStateStatisticEntry 1 }
			
		hwXdslPortStateBitmapList OBJECT-TYPE
			SYNTAX OCTET STRING 
			MAX-ACCESS read-only
			STATUS current
			DESCRIPTION
			    "The type of port status:
			     2   failed;
			     8   testing;
			     9   activated;
			     10  activating; 
			     11  deactivated;
			     18  localloopback;
			     19  remoteloopback;
			     20  blocked;  
			     37  utopialoopback;
			     38  afeloopback; 
			     39  hybridloopback; 
			     255 unknown;
			     HwXdslPortStateBitmapList describes the states of all ports. 
			     Every byte describe the current state of every port.
			     The length is equal to the value of the hwXdslPortStatePortNumber.
			    "
			::= { hwXdslPortStateStatisticEntry 2 }
			
		hwXdslTotalOfActivatedPorts OBJECT-TYPE
			SYNTAX Unsigned32
			MAX-ACCESS read-only
			STATUS current
			DESCRIPTION
			    "The total of the activated ports."
			::= { hwXdslPortStateStatisticEntry 3 }
		
		hwXdslTotalOfDeactivatedPorts OBJECT-TYPE
			SYNTAX Unsigned32			
			MAX-ACCESS read-only
			STATUS current
			DESCRIPTION
			    "The total of the deactivated ports."
			::= { hwXdslPortStateStatisticEntry 4 }
		
		hwXdslTotalOfActivatingPorts OBJECT-TYPE
			SYNTAX Unsigned32			
			MAX-ACCESS read-only
			STATUS current
			DESCRIPTION
			    "The total of the activating ports."
			::= { hwXdslPortStateStatisticEntry 5 }
			
		hwXdslTotalOfTestingPorts OBJECT-TYPE
			SYNTAX Unsigned32			
			MAX-ACCESS read-only
			STATUS current
			DESCRIPTION
			    "The total of the Testing ports."
			::= { hwXdslPortStateStatisticEntry 6 }				
		
		hwXdslTotalOfBlockedPorts OBJECT-TYPE
			SYNTAX Unsigned32			
			MAX-ACCESS read-only
			STATUS current
			DESCRIPTION
			    "The total of the blocked ports."
			::= { hwXdslPortStateStatisticEntry 7 }
		
		hwXdslTotalOfLocalLoopbackPorts OBJECT-TYPE
			SYNTAX Unsigned32			
			MAX-ACCESS read-only
			STATUS current
			DESCRIPTION
			    "The total of the local testing ports."
			::= { hwXdslPortStateStatisticEntry 8 }
		
		hwXdslTotalOfRemoteLoopbackPorts OBJECT-TYPE
			SYNTAX Unsigned32			
			MAX-ACCESS read-only
			STATUS current
			DESCRIPTION
			    "The total of the remote testing ports."
			::= { hwXdslPortStateStatisticEntry 9 }
			
		hwXdslTotalOfFailedPorts OBJECT-TYPE
			SYNTAX Unsigned32			
			MAX-ACCESS read-only
			STATUS current
			DESCRIPTION
			    "The total of the failed ports."
			::= { hwXdslPortStateStatisticEntry 10 }
		
		hwXdslTotalOfUnknownPorts OBJECT-TYPE
			SYNTAX Unsigned32			
			MAX-ACCESS read-only
			STATUS current
			DESCRIPTION
			    "The total of the unknown testing ports."
			::= { hwXdslPortStateStatisticEntry 11 }									               
			

--    adsl line extending table: hwadslLineExtConfProfileTable      
		hwadslLineExtConfProfileTable OBJECT-TYPE
			SYNTAX SEQUENCE OF HwadslLineExtConfProfileEntry
			MAX-ACCESS not-accessible
			STATUS current
			DESCRIPTION
			    "This table contains information on the ADSL extend line
                             configuration.  One entry in this table reflects a
                             extend line profile defined by a manager which can be used to
                             configure the ADSL line.
                             The index of this table is hwadslLineExtConfProfileName.
                            "
			::= { adslMibObjects 65543 }
		
		hwadslLineExtConfProfileEntry OBJECT-TYPE
			SYNTAX HwadslLineExtConfProfileEntry
			MAX-ACCESS not-accessible
			STATUS current
			DESCRIPTION
			    "This table contains information on the ADSL extend line
                             configuration.  One entry in this table reflects a
                             extend line profile defined by a manager which can be used to
                             configure the ADSL line.
                             The index of this entry is hwadslLineExtConfProfileName.
                            "
			INDEX {IMPLIED hwadslLineExtConfProfileName}
			::= { hwadslLineExtConfProfileTable 1 }
		
		HwadslLineExtConfProfileEntry ::=
			SEQUENCE { 
				hwadslLineExtConfProfileName
					OCTET STRING,
				hwadslLineDisableToneSection1Begin	
					Integer32,
				hwadslLineDisableToneSection1End	
					Integer32,
				hwadslLineDisableToneSection1Flag	
					INTEGER,	
				hwadslLineDisableToneSection2Begin	
					Integer32,
				hwadslLineDisableToneSection2End	
					Integer32,
				hwadslLineDisableToneSection2Flag	
					INTEGER,	
				hwadslLineDisableToneSection3Begin	
					Integer32,
				hwadslLineDisableToneSection3End	
					Integer32,
				hwadslLineDisableToneSection3Flag	
					INTEGER,	
				hwadslLineDisableToneSection4Begin	
					Integer32,
				hwadslLineDisableToneSection4End	
					Integer32,
				hwadslLineDisableToneSection4Flag	
					INTEGER,	
				hwadsl2ChConfProfMinProtectionDs
					HWADSLSYMBOLPROTECTION,
				hwadsl2ChConfProfMinProtectionUs
					HWADSLSYMBOLPROTECTION,	
				hwAdslExtDsMinTrainSnrMgn
			                Integer32,                 
				hwAdslExtUsMinTrainSnrMgn   
			                Integer32,
				hwAdslExtDsMaxPsd	       	
					Integer32,
				hwadsl2TSSiPsdMaskDs
				        Adsl2PsdMaskDs,	
			        hwadsl2TranMissionStardardMask	
					Unsigned32,	
		                hwadsl2TransMissionAnnexMask 
					Unsigned32,
				hwadsl2TransMissionAnnexMScope	
				        HWADSL2ANNEXMSCOPE,
				hwadsl2L2ModeState
				        INTEGER,
				hwadsl2L2ModeMinDataRate
				        Integer32,
				hwadsl2L2ModeMaxDataRate
				        Integer32,
				hwadsl2L2ModePayloadRateThreshold
				        Integer32,
				hwadsl2L2ModeGuardTime
				        Integer32,
				hwadsl2L2ModeIntervalTime
				        Integer32,				
				hwadsl2L2ModeIntervalPowerValue        
				        Integer32,
                                hwadsl2L2ModeTotalPowerValue				        
				        Integer32,
		                hwadslExtUsPhyRcontrol
		                    INTEGER,
		                hwadslExtUsINPmax
		                    Adsl2SymbolProtection,
		                hwadslExtUsMinRtxRatio
		                    Integer32,
		                hwadslExtUsMinRSoverhead
		                    Integer32,
		                hwadslExtDsPhyRcontrol
		                    INTEGER,
		                hwadslExtDsINPmax
		                    Adsl2SymbolProtection,
		                hwadslExtDsMinRtxRatio
		                    Integer32,
		                hwadslExtDsMinRSoverhead
		                    Integer32,
				hwadsl2TSSiPsdMaskUs
				    Adsl2PsdMaskUs,
				hwadslLConfProfAdslMode
		                    INTEGER,
				hwadslLineExtConfProfileRowStatus
		                    RowStatus,
				hwadsl2L2ModeL2Time
				    Integer32

			 }

		hwadslLineExtConfProfileName OBJECT-TYPE
	                 SYNTAX          OCTET STRING (SIZE (1..32))
	                 MAX-ACCESS      not-accessible
	                 STATUS          current
	                 DESCRIPTION
	                     "This object is used by the hwadslLineExtConfProfileTable
	                      in order to identify a row of this table.
	                      This object indicates the name of the extended line profile.
	                     "
	         	 ::= { hwadslLineExtConfProfileEntry 1 }
		
		hwadslLineDisableToneSection1Begin OBJECT-TYPE
			SYNTAX Integer32(0..511)
			MAX-ACCESS read-create
			STATUS current
			DESCRIPTION
			    "The begin index of section1.
			     Range: 0-511
			    "
			::= { hwadslLineExtConfProfileEntry 2 }
		
		hwadslLineDisableToneSection1End OBJECT-TYPE
			SYNTAX Integer32(0..511)
			MAX-ACCESS read-create
			STATUS current
			DESCRIPTION
			    "The end index of section1.
			     Range: 0-511
			    "
			::= { hwadslLineExtConfProfileEntry 3 }
			
		hwadslLineDisableToneSection1Flag OBJECT-TYPE
			SYNTAX INTEGER {
			  enabled(1),
			  disabled(2)
			}
			MAX-ACCESS read-create
			STATUS current
			DESCRIPTION
			    "The enable flag of section1.
			     Options:
			     1. enabled(1)  - The first tone section is enabled
			     2. disabled(2) - The first tone section is disabled
			    "
			::= { hwadslLineExtConfProfileEntry 4 }
			
		hwadslLineDisableToneSection2Begin OBJECT-TYPE
			SYNTAX Integer32(0..511)
			MAX-ACCESS read-create
			STATUS current
			DESCRIPTION
			    "The begin index of section2.
			     Range: 0-511
			    "
			::= { hwadslLineExtConfProfileEntry 5 }
		
		hwadslLineDisableToneSection2End OBJECT-TYPE
			SYNTAX Integer32(0..511)
			MAX-ACCESS read-create
			STATUS current
			DESCRIPTION
			    "The end index of section2.
			     Range: 0-511
			    "
			::= { hwadslLineExtConfProfileEntry 6 }
			
		hwadslLineDisableToneSection2Flag OBJECT-TYPE
			SYNTAX INTEGER {
			  enabled(1),
			  disabled(2)
			}
			MAX-ACCESS read-create
			STATUS current
			DESCRIPTION
			    "The enable flag of section2.
			     Options:
			     1. enabled(1)  - The second tone section is enabled
			     2. disabled(2) - The second tone section is disabled
			    "
			::= { hwadslLineExtConfProfileEntry 7 }
				
		hwadslLineDisableToneSection3Begin OBJECT-TYPE
			SYNTAX Integer32(0..511)
			MAX-ACCESS read-create
			STATUS current
			DESCRIPTION
			    "The begin index of section3.
			     Range: 0-511
			    "
			::= { hwadslLineExtConfProfileEntry 8 }
		
		hwadslLineDisableToneSection3End OBJECT-TYPE
			SYNTAX Integer32(0..511)
			MAX-ACCESS read-create
			STATUS current
			DESCRIPTION
			    "The end index of section3.
			     Range: 0-511
			    "
			::= { hwadslLineExtConfProfileEntry 9 }

		hwadslLineDisableToneSection3Flag OBJECT-TYPE
			SYNTAX INTEGER {
			  enabled(1),
			  disabled(2)
			}
			MAX-ACCESS read-create
			STATUS current
			DESCRIPTION
			    "The enable flag of the third section.
			     Options:
			     1. enabled(1)  - The third tone section is enabled
			     2. disabled(2) - The third tone section is disabled
			    "
			::= { hwadslLineExtConfProfileEntry 10 }
			
		hwadslLineDisableToneSection4Begin OBJECT-TYPE
			SYNTAX Integer32(0..511)
			MAX-ACCESS read-create
			STATUS current
			DESCRIPTION
			    "The begin index of the fourth section.
			     Range: 0-511
			    "
			::= { hwadslLineExtConfProfileEntry 11 }
		
		hwadslLineDisableToneSection4End OBJECT-TYPE
			SYNTAX Integer32(0..511)
			MAX-ACCESS read-create
			STATUS current
			DESCRIPTION
			    "The end index of the fourth section.
			     Range: 0-511
			    "
			::= { hwadslLineExtConfProfileEntry 12 }
		
		hwadslLineDisableToneSection4Flag OBJECT-TYPE
			SYNTAX INTEGER {
			  enabled(1),
			  disabled(2)
			}
			MAX-ACCESS read-create
			STATUS current
			DESCRIPTION
			    "The enable flag of the fourth section.
			     Range: 0-511
			     Options:
			     1. enabled(1)  - The fourth tone section is enabled
			     2. disabled(2) - The fourth tone section is disabled
			    "
			::= { hwadslLineExtConfProfileEntry 13 }
			
		hwadsl2ChConfProfMinProtectionDs  OBJECT-TYPE
		     SYNTAX      HWADSLSYMBOLPROTECTION
		     MAX-ACCESS  read-write
		     STATUS      current
		     DESCRIPTION
		         "Minimum Impulse Noise Protection on Downstream direction. The 
		          minimum impulse noise protection for the bearer channel, expressed
		          in symbols. The parameter can take the following values:
		            noProtection(0),
		            halfSymbol(1),
		            singleSymbol(2),
		            twoSymbols(4),
		            threeSymbols(6),
		            fourSymbols(8),
		            fiveSymbols(10),
		            sixSymbols(12),
		            sevenSymbols(14),
		            eightSymbols(16),
		            nineSymbols(18),
		            tenSymbols(20),
		            elevenSymbols(22),
		            twelveSymbols(24),
		            thirteenSymbols(26),
		            fourteenSymbols(28),
		            fifteenSymbols(30),
		            sixteenSymbols(32),
		            null(65535)
		          The value multiply 1/2 is the real value of Noise Protection values.
		         "
		     ::= { hwadslLineExtConfProfileEntry 14 }
		
		hwadsl2ChConfProfMinProtectionUs  OBJECT-TYPE
		     SYNTAX      HWADSLSYMBOLPROTECTION
		     MAX-ACCESS  read-write
		     STATUS      current
		     DESCRIPTION
		         "Minimum Impulse Noise Protection on Upstream direction. The 
		          minimum impulse noise protection for the bearer channel, expressed
		          in symbols. The parameter can take the following values:
		            noProtection(0),
		            halfSymbol(1),
		            singleSymbol(2),
		            twoSymbols(4),
		            threeSymbols(6),
		            fourSymbols(8),
		            fiveSymbols(10),
		            sixSymbols(12),
		            sevenSymbols(14),
		            eightSymbols(16),
		            nineSymbols(18),
		            tenSymbols(20),
		            elevenSymbols(22),
		            twelveSymbols(24),
		            thirteenSymbols(26),
		            fourteenSymbols(28),
		            fifteenSymbols(30),
		            sixteenSymbols(32),
		            null(65535)
		          The value multiply 1/2 is the real value of Noise Protection values.
		         "
		     ::= { hwadslLineExtConfProfileEntry 15 }
		     
		hwAdslExtDsMinTrainSnrMgn OBJECT-TYPE
		     SYNTAX      Integer32  (0..310)
		     UNITS       "tenth dB"
		     MAX-ACCESS  read-create
		     STATUS      current
		     DESCRIPTION
		         "Maximum Trainning Margin in downstream.
		          Range: 0-310
		          Default: 30
		          Unit: tenth dB
		         "
		     DEFVAL { 30 }
		     ::= { hwadslLineExtConfProfileEntry 16 }		              
		              
		hwAdslExtUsMinTrainSnrMgn OBJECT-TYPE
		     SYNTAX      Integer32  (0..310)
		     UNITS       "tenth dB"
		     MAX-ACCESS  read-create
		     STATUS      current
		     DESCRIPTION
		         "Maximum Trainning Margin in upstream.
		          Range: 0-310
		          Default: 30
		          Unit: tenth dB
		         "
		     DEFVAL { 30 }
		     ::= { hwadslLineExtConfProfileEntry 17 }		              
		              
		hwAdslExtDsMaxPsd  OBJECT-TYPE
		     SYNTAX      Integer32  (-60..-30)
		     UNITS       "dBm/Hz"
		     MAX-ACCESS  read-create
		     STATUS      current
		     DESCRIPTION
		         "Maximum PSD margin in downstream."
		     DEFVAL { -40 }
		     ::= { hwadslLineExtConfProfileEntry 18 }
			
		hwadsl2TSSiPsdMaskDs   OBJECT-TYPE
  		    SYNTAX      Adsl2PsdMaskDs
  		    MAX-ACCESS  read-write
  		    STATUS      current
 		    DESCRIPTION
 		         "The downstream PSD mask applicable at the U-C2 reference
 		          point.
 		          This parameter is used only for G992.3 or G992.5 and it may 
 		          impose PSD restrictions (breakpoints) in addition to the 
 		          Limit PSD mask defined in G992.5.
 		          This is a string of 32 pairs of values in the following
 		          structure:
 		          Octets 0-1 - Index of 1st sub-carrier used in the context
 		          of a first breakpoint.
 		          Octet  2   - The PSD reduction for the sub-carrier indicated in
 		                       octets 0 and 1.
 		          Octets 3-5 - Same, for a 2nd breakpoint.
 		          Octets 6-8 - Same, for a 3rd breakpoint.
 		          This architecture continues until octets 94-95, which are
 		          associated with a 32nd breakpoint.
 		          Each subcarrier index is an unsigned number in the range 1 and
 		          NSCds.  Each PSD reduction value is in the range 0 (0dBm/Hz) to
 		          255 (-127.5dBm/Hz) with steps of 0.5dBm/Hz.  Valid values are
 		          in the range 0 to 190 (0 to -95dBm/Hz).
 		          When the number of breakpoints is less than 32, all remaining
 		          octets are set to the value 0.  Note that the content of this
 		          object should be correlated with the sub-carriers mask and with
 		          the RFI setup. 
 		         "
      		REFERENCE    "ITU-T G.997.1, paragraph 7.3.1.2"
        		::= { hwadslLineExtConfProfileEntry 19 }   
		 
		hwadsl2TranMissionStardardMask OBJECT-TYPE
			SYNTAX Unsigned32
			MAX-ACCESS read-write
			STATUS current
			DESCRIPTION
			    "The tranmission stardard mask. 
			     The Mask bit and the corresponding Transmission Standard:
			     0x 1       1       1       1       1       1   
			     ETSI  T1.413  G992.5  G992.3  G992.2  G992.1
			     The Default BitMask: 0X0.
			    "
			::= { hwadslLineExtConfProfileEntry 20 }
			 
			
		hwadsl2TransMissionAnnexMask OBJECT-TYPE
			SYNTAX Unsigned32
			MAX-ACCESS read-write
			STATUS current
			DESCRIPTION
                            "The transMission annex Mask.  
                             The Mask bit and the corresponding Transmission Annex:
                             0x     1         1         1         1         1
                             Annex .J  Annex .M  Annex .L  Annex .B  Annex .A				
                             The Default BitMask:  0X0. 
			    "
			::= { hwadslLineExtConfProfileEntry 21 }
			
		hwadsl2TransMissionAnnexMScope  OBJECT-TYPE
		     SYNTAX      HWADSL2ANNEXMSCOPE
		     MAX-ACCESS  read-create
		     STATUS      current
		     DESCRIPTION
		         "Annex M expand scope:
		          1-Tone Index(7~32)                                                           
		          2-Tone Index(7~36)                                                           
		          3-Tone Index(7~40)                                                           
		          4-Tone Index(7~44)                                                             
		          5-Tone Index(7~48)
		          6-Tone Index(7~52)  
		          7-Tone Index(7~56)                                                           
		          8-Tone Index(7~60)                                                           
		          9-Tone Index(7~64) 
		          -1-invalidValue
		         "
		     ::= { hwadslLineExtConfProfileEntry 22 }
		
		hwadsl2L2ModeState OBJECT-TYPE
			SYNTAX INTEGER {
			  disabled(1),
			  enabled(2),
			  forced(3)
			}
			MAX-ACCESS read-create
			STATUS current
			DESCRIPTION
			    "The state of L2 power management mode.
			     Options:
			     1. disabled(1) - L2 power management mode is disabled
			     2. enabled(2)  - L2 power management mode is enabled
			     3. forced(3)   - L2 power management mode is forced
			     Default: disabled(1)
			    "
			  DEFVAL { disabled }
			 ::= { hwadslLineExtConfProfileEntry 23 }
			
		hwadsl2L2ModeMinDataRate  OBJECT-TYPE
		      SYNTAX Integer32 (128..16384)
		      UNITS "Kbps"
		      MAX-ACCESS read-create
		      STATUS current
		      DESCRIPTION
		          "Minimum Data Rate in L2 Mode.
		           Range: 128-16384
		           Unit: Kbps
		          "	
		        DEFVAL { 256 }
		       ::= { hwadslLineExtConfProfileEntry 24 } 
		       
	        hwadsl2L2ModeMaxDataRate  OBJECT-TYPE
		      SYNTAX Integer32 (128..16384)
		      UNITS "Kbps"
		      MAX-ACCESS read-create
		      STATUS current
		      DESCRIPTION
		          "Maximum Data Rate in L2 Mode.
		           Range: 128-16384
		           Default: 1024
		           Unit: Kbps
		          "	
		        DEFVAL { 1024 }
		       ::= { hwadslLineExtConfProfileEntry 25 }
		       
		hwadsl2L2ModePayloadRateThreshold  OBJECT-TYPE
		      SYNTAX Integer32 (128..16384)
		      UNITS "Kbps"
		      MAX-ACCESS read-create
		      STATUS current
		      DESCRIPTION
		          "Threshold for the Payload Rate Ratio.
		           Range: 128-16384
		           Default: 128
		           Unit: Kbps
		          "	
		        DEFVAL { 128 }
		       ::= { hwadslLineExtConfProfileEntry 26 }
		
		hwadsl2L2ModeGuardTime  OBJECT-TYPE
		      SYNTAX Integer32 (0..1024)
		      UNITS "seconds"
		      MAX-ACCESS read-create
		      STATUS current
		      DESCRIPTION
		          "Guard Time before entering L2 Mode.
		           Range: 0-1024
		           Default: 60
		           Unit: seconds
		          "	
		        DEFVAL { 60 }
		       ::= { hwadslLineExtConfProfileEntry 27 }
		       
		hwadsl2L2ModeIntervalTime  OBJECT-TYPE
		      SYNTAX Integer32 (0..255)
		      UNITS "seconds"
		      MAX-ACCESS read-create
		      STATUS current
		      DESCRIPTION
		          "The minimum interval between two records of L2 mode.
		           Range: 0-255
		           Default: 255
		           Unit: seconds
		          "
		        DEFVAL { 255 }
		       ::= { hwadslLineExtConfProfileEntry 28 }

		hwadsl2L2ModeIntervalPowerValue  OBJECT-TYPE
		        SYNTAX Integer32 (0..31)
		        UNITS "db"
		        MAX-ACCESS read-create
		        STATUS current
		        DESCRIPTION
		            "Maximum aggregate transmit power reduction per L2 request or L2 power trim.
		             Range: 0-31
		             Default: 3
		             Unit: db
		            "
		          DEFVAL { 3 }
		         ::= { hwadslLineExtConfProfileEntry 29 }

		hwadsl2L2ModeTotalPowerValue  OBJECT-TYPE
		        SYNTAX Integer32 (0..31)
		        UNITS "db"
		        MAX-ACCESS read-create
		        STATUS current
		        DESCRIPTION
		            "Total maximum aggregate transmit power reduction in L2.
		             Range: 0-31
		             Default: 9
		             Unit: db
		            "
		          DEFVAL { 9 }
		         ::= { hwadslLineExtConfProfileEntry 30 }
		         
    	hwadslExtUsPhyRcontrol OBJECT-TYPE
            SYNTAX      INTEGER
            {
                enable(1),
                disable(2)
            }
            MAX-ACCESS  read-write
            STATUS      current
            DESCRIPTION
                "To enable or disable the PHY-R function on upstream direction.
                 Options: 
                 1. enable(1)  - The PHY-R function on upstream direction is enabled
                 2. disable(2) - The PHY-R function on upstream direction is disabled
                 Default: disable(2)
                "
            DEFVAL { disable }
            ::= { hwadslLineExtConfProfileEntry 31 }
    
        hwadslExtUsINPmax OBJECT-TYPE
            SYNTAX      Adsl2SymbolProtection
            UNITS       "DMT Symbol"
            MAX-ACCESS  read-write
            STATUS      current
            DESCRIPTION
                "Maximum Impulse Noise Protection on upstream direction.
                 The parameter can take the following values:
                 noProtection(1),
                 halfSymbol(2),
                 singleSymbol(3),
                 twoSymbols(4),
                 threeSymbols(5),
                 fourSymbols(6),
                 fiveSymbols(7),
                 sixSymbols(8),
                 sevenSymbols(9),
                 eightSymbols(10),
                 nineSymbols(11),
                 tenSymbols(12),
                 elevenSymbols(13),
                 twelveSymbols(14),
                 thirteeSymbols(15),
                 fourteenSymbols(16),
                 fifteenSymbols(17),
                 sixteenSymbols(18)
                 The value multiply 1/2 is the real value of Noise Protection values.
                 Unit: DMT Symbol
                 Default: 1
    		"
    		DEFVAL { 1 }
            ::= { hwadslLineExtConfProfileEntry 32 }
    
        hwadslExtUsMinRtxRatio OBJECT-TYPE
            SYNTAX      Integer32 (0..255)
            UNITS       "1/256"
            MAX-ACCESS  read-write
            STATUS      current
            DESCRIPTION
                "Minimum rtxratio on upstream direction.
                 Range: 0-255
		 Default: 0
		 Unit: 1/256
		"
            DEFVAL { 0 }
            ::= { hwadslLineExtConfProfileEntry 33 }
    
        hwadslExtUsMinRSoverhead OBJECT-TYPE
            SYNTAX      Integer32 (0..128)
            UNITS       "1/256"
            MAX-ACCESS  read-write
            STATUS      current
            DESCRIPTION
                "The minimum value of R/N on upstream direction.
                 Range: 0-128
		 Default: 0
		 Unit: 1/256
		"
            DEFVAL { 0 }
            ::= { hwadslLineExtConfProfileEntry 34 }
            
        hwadslExtDsPhyRcontrol OBJECT-TYPE
            SYNTAX      INTEGER
            {
                enable(1),
                disable(2)
            }
            MAX-ACCESS  read-write
            STATUS      current
            DESCRIPTION
                "To enable or disable the PHY-R function on downstream direction.
                 Options: 
                 1. enable(1)  - The PHY-R function on downstream direction is enabled
                 2. disable(2) - The PHY-R function on downstream direction is disabled
                 Default: disable(2)
                "
            DEFVAL { disable }
            ::= { hwadslLineExtConfProfileEntry 35 }
    
        hwadslExtDsINPmax OBJECT-TYPE
            SYNTAX      Adsl2SymbolProtection
            UNITS       "DMT Symbol"
            MAX-ACCESS  read-write
            STATUS      current
            DESCRIPTION
                "Maximum Impulse Noise Protection on downstream direction.
                 The parameter can take the following values:
                 noProtection(1),
                 halfSymbol(2),
                 singleSymbol(3),
                 twoSymbols(4),
                 threeSymbols(5),
                 fourSymbols(6),
                 fiveSymbols(7),
                 sixSymbols(8),
                 sevenSymbols(9),
                 eightSymbols(10),
                 nineSymbols(11),
                 tenSymbols(12),
                 elevenSymbols(13),
                 twelveSymbols(14),
                 thirteeSymbols(15),
                 fourteenSymbols(16),
                 fifteenSymbols(17),
                 sixteenSymbols(18)
                 The value multiply 1/2 is the real value of Noise Protection values.
                 
                 Unit: DMT Symbol
    		"
    		DEFVAL { 1 }
            ::= { hwadslLineExtConfProfileEntry 36 }
    
        hwadslExtDsMinRtxRatio OBJECT-TYPE
            SYNTAX      Integer32 (0..255)
            UNITS       "1/256"
            MAX-ACCESS  read-write
            STATUS      current
            DESCRIPTION
                "Minimum rtxratio on downstream direction.
                 Range: 0-255
		 Default: 0
		 Unit: 1/256
		"
            DEFVAL { 0 }
            ::= { hwadslLineExtConfProfileEntry 37 }
    
        hwadslExtDsMinRSoverhead OBJECT-TYPE
            SYNTAX      Integer32 (0..128)
            UNITS       "1/256"
            MAX-ACCESS  read-write
            STATUS      current
            DESCRIPTION
                "The minimum value of R/N on downstream direction.
                 Range: 0-128
		 Default: 0
		 Unit: 1/256
		"
            DEFVAL { 0 }
            ::= { hwadslLineExtConfProfileEntry 38 }
        	  
        hwadsl2TSSiPsdMaskUs OBJECT-TYPE
  		    SYNTAX      Adsl2PsdMaskUs
  		    MAX-ACCESS  read-write
  		    STATUS      current
 		    DESCRIPTION
 		        "The upstream PSD mask applicable at the U-C2 reference
 		         point.
 		         This parameter is used only for G992.3 or G992.5 and it may impose PSD
 		         restrictions (breakpoints) in addition to the Limit PSD mask
 		         defined in G992.5.
 		         This is a string of 32 pairs of values in the following
  		         structure:
 		         Octets 0+1 - Index of 1st sub-carrier used in the context
		                      of a first breakpoint.
  		         Octet 2    - The PSD reduction for the sub-carrier indicated in
  		                      octets 0 and 1.
  		         Octets 3-5 - Same, for a 2nd breakpoint.
  		         Octets 6-8 - Same, for a 3rd breakpoint.
  		         This architecture continues until octets 9-11, which are
  		         associated with a fourth breakpoint.
   		         Each subcarrier index is an unsigned number in the range 1 and
   		         NSCus.  Each PSD reduction value is in the range 0 (0dBm/Hz) to
		         255 (-127.5dBm/Hz) with steps of 0.5dBm/Hz.  Valid values are
       		         in the range 0 to 190 (0 to -95dBm/Hz).
       		         When the number of breakpoints is less than 4, all remaining
       		         octets are set to the value 0.  Note that the content of this
       		         object should be correlated with the sub-carriers mask and with
       		         the RFI setup. 
       		        "
      		REFERENCE    "ITU-T G.997.1, paragraph 7.3.1.2"
        		::= { hwadslLineExtConfProfileEntry 39 }         
	
	 hwadslLConfProfAdslMode OBJECT-TYPE   
        SYNTAX      INTEGER {
                          defMode (1),
                          adsl (2),
                          adsl2Pots (3),
                          adsl2Isdn (4),
                          adsl2PlusPots (5),
                          adsl2PlusIsdn (6),
                          adsl2ReachExtended (7),
                          invalidValue(-1)          
                          }  
          MAX-ACCESS      read-write        
          STATUS      current
          DESCRIPTION
               "The ADSL2 management model specified includes an ADSL Mode
                attribute which identifies an instance of ADSL Mode-Specific
                PSD Configuration object in the ADSL Line Profile. The
                following classes of ADSL operating mode are defined.
                Options: 
                1. defMode(1)            - ADSL transmit mode is defMode
                2. adsl(2)               - ADSL transmit mode is adsl
                3. adsl2Pots(3)          - ADSL transmit mode is adsl2Pots
                4. adsl2Isdn(4)          - ADSL transmit mode is adsl2Isdn
                5. adsl2PlusPots(5)      - ADSL transmit mode is adsl2PlusPots
                6. adsl2PlusIsdn(6)      - ADSL transmit mode is adsl2PlusIsdn
                7. adsl2ReachExtended(7) - ADSL transmit mode is adsl2ReachExtended
                8. invalidValue(-1)      - Invalid value
               "
           ::= { hwadslLineExtConfProfileEntry 40 }
		
		hwadslLineExtConfProfileRowStatus OBJECT-TYPE
	             SYNTAX          RowStatus
	             MAX-ACCESS      read-create
	             STATUS          current
	             DESCRIPTION
	                 "This object is used to create a new row or modify or
	                  delete an existing row in this table.
	                  A profile activated by setting this object to
	                  'active'.  When 'active' is set, the system
	                  will validate the profile.
	                  
	                  Before a profile can be deleted or taken out of
	                  service, (by setting this object to 'destroy' or
	                  'outOfService') it must be first unreferenced
	                  from all associated lines.
	                  
	                  If the creator of this MIB has chosen not
	                  to implement 'dynamic assignment' of profiles, this
	                  object's MIN-ACCESS is read-only and its value
	                  is always to be 'active'.
	                 "
	         ::= { hwadslLineExtConfProfileEntry 65535 }

		hwadsl2L2ModeL2Time OBJECT-TYPE
		      SYNTAX Integer32 (0..255)
		      UNITS "seconds"
		      MAX-ACCESS read-create
		      STATUS current
		      DESCRIPTION
		          "This minimum time (in seconds) between an Entry into the
		           L2 state and the first Power Trim in the L2 state and between
		           two consecutive Power Trims in the L2 State.
		           It ranges from 0 to 255 seconds.
		           Range: 0-255
		           Default: 30
		           Unit: seconds
		           "
		        DEFVAL { 30 }
		       ::= { hwadslLineExtConfProfileEntry 65536 }

--    hwAdslLineLatestActParaTable
		hwAdslLineLatestActParaTable OBJECT-TYPE
			SYNTAX SEQUENCE OF HwAdslLineLatestActParaEntry
			MAX-ACCESS not-accessible
			STATUS current
			DESCRIPTION
			    "This table provides one row for each ADSL PORT.
			     Each row contains the latest actived Parameters.
			     The index of this table is ifIndex.
			    "
			::= { adslMibObjects 65544 }
		
		hwAdslLineLatestActParaEntry OBJECT-TYPE
			SYNTAX HwAdslLineLatestActParaEntry
			MAX-ACCESS not-accessible
			STATUS current
			DESCRIPTION
			    "This table provides one row for each ADSL PORT.
			     Each row contains the latest actived Parameters.
			     The index of this entry is ifIndex.
			    "
			INDEX { ifIndex }
			::= { hwAdslLineLatestActParaTable 1 }
		
		HwAdslLineLatestActParaEntry ::=
			SEQUENCE {
			        hwAdslLineLatestActiveTime
			                DateAndTime,
			        hwAdslLineLatestDeactiveTime
			                DateAndTime, 
                                hwAdslAtucLatestTxRate
				        Gauge32,
                                hwAdslAturLatestTxRate
				        Gauge32,
				hwAdslAtucLatestSnrMgn
					Integer32,
				hwAdslAturLatestSnrMgn
					Integer32,
				hwAdslAtucLatestAtn
					Gauge32,
				hwAdslAturLatestAtn
					Gauge32,
				hwAdslAtucLatestAttainableRate
					Gauge32,
				hwAdslAturLatestAttainableRate
					Gauge32,
                                hwAdslAtucLatestConfTxRate
                                        Gauge32,
                                hwAdslAturLatestConfTxRate
                                        Gauge32,
				hwAdslAtucLatestInterleaveDelay
				        Gauge32,
				hwAdslAturLatestInterleaveDelay
				        Gauge32,
			        hwAdslAtucLatestTargetSnrMgn
			                Integer32,
			        hwAdslAturLatestTargetSnrMgn
			                Integer32,
			        hwAdslAtucLatestTxRateThreshold 
			                Gauge32,
			        hwAdslAturLatestTxRateThreshold	
			                Gauge32
			 }

  		hwAdslLineLatestActiveTime OBJECT-TYPE
    		SYNTAX      DateAndTime
   			MAX-ACCESS  read-only
    		STATUS      current
            DESCRIPTION
                "Actual time when latest actived."
    	::= { hwAdslLineLatestActParaEntry 1 }

  		hwAdslLineLatestDeactiveTime OBJECT-TYPE
    		SYNTAX      DateAndTime
    		MAX-ACCESS  read-only
    		STATUS      current
            DESCRIPTION
                "Actual time when latest deactived. If port is actived, the value is invalid."
    	::= { hwAdslLineLatestActParaEntry 2 }

        hwAdslAtucLatestTxRate  OBJECT-TYPE
            SYNTAX      Gauge32
            UNITS       "bps"
            MAX-ACCESS  read-only
            STATUS      current
            DESCRIPTION
                "Actual transmit rate on this channel when latest actived.
                 Unit: bps
                "
        ::= { hwAdslLineLatestActParaEntry 3 }

        hwAdslAturLatestTxRate  OBJECT-TYPE
            SYNTAX      Gauge32
            UNITS       "bps"
            MAX-ACCESS  read-only
            STATUS      current
            DESCRIPTION
                "Actual transmit rate on this channel when latest actived.
                 Unit: bps
                "
        ::= { hwAdslLineLatestActParaEntry 4 }

		hwAdslAtucLatestSnrMgn OBJECT-TYPE
			SYNTAX Integer32
			UNITS "tenth dB"
			MAX-ACCESS read-only
			STATUS current
			DESCRIPTION
			    "Noise Margin as seen by this ATU-C at the time of the last adslAtucRateChangeTrap event. in tenth dB.
			     Unit: tenth dB
			    "
			::= { hwAdslLineLatestActParaEntry 5 }
		
		hwAdslAturLatestSnrMgn OBJECT-TYPE
			SYNTAX Integer32
			UNITS "tenth dB"
			MAX-ACCESS read-only
			STATUS current
			DESCRIPTION
			    "Noise Margin as seen by this ATU-R at the time of the last adslAtucRateChangeTrap event. in tenth dB.
			     Unit: tenth dB
			    "
			::= { hwAdslLineLatestActParaEntry 6 }
		
		hwAdslAtucLatestAtn OBJECT-TYPE
			SYNTAX Gauge32
			UNITS "tenth dB"
			MAX-ACCESS read-only
			STATUS current
			DESCRIPTION
			    "Measured difference in the total power transmitted as seen by this ATU-C at the time of the last adslAtucRateChangeTrap event. in tenth dB.
			     Unit: tenth dB
			    "
			::= { hwAdslLineLatestActParaEntry 7 }
		
		hwAdslAturLatestAtn OBJECT-TYPE
			SYNTAX Gauge32
			UNITS "tenth dB"
			MAX-ACCESS read-only
			STATUS current
			DESCRIPTION
			    "Measured difference in the total power transmitted as seen by this ATU-R at the time of the last adslAtucRateChangeTrap event. in tenth dB.
			     Unit: tenth dB
			    "
			::= { hwAdslLineLatestActParaEntry 8 }
        
		hwAdslAtucLatestAttainableRate OBJECT-TYPE
			SYNTAX Gauge32
			UNITS "bps"
			MAX-ACCESS read-only
			STATUS current
			DESCRIPTION
			    "Indicates the maximum attainable data rate by the ATU-C at the time of the last adslAtucRateChangeTrap event.
			     Unit: bps
			    "
			::= { hwAdslLineLatestActParaEntry 9 }
		
		hwAdslAturLatestAttainableRate OBJECT-TYPE
			SYNTAX Gauge32
			UNITS "bps"
			MAX-ACCESS read-only
			STATUS current
			DESCRIPTION
			    "Indicates the maximum attainable data rate by the ATU-R at the time of the last adslAtucRateChangeTrap event.
			     Unit: bps
			    "
			::= { hwAdslLineLatestActParaEntry 10 } 
			
         hwAdslAtucLatestConfTxRate  OBJECT-TYPE
             SYNTAX      Gauge32
             UNITS       "bps"
             MAX-ACCESS  read-only
             STATUS      current
             DESCRIPTION
                 "Configured transmit rate for ADSL port,
                  in bps.  See adslAtucConfRateChanRatio for information
                  regarding RADSL mode and ATUR transmit rate for
                  ATUC receive rates.
                  Unit: bps
		 "
         ::= { hwAdslLineLatestActParaEntry 11 }

         hwAdslAturLatestConfTxRate  OBJECT-TYPE
             SYNTAX      Gauge32
             UNITS       "bps"
             MAX-ACCESS  read-only
             STATUS      current
             DESCRIPTION
                 "Configured receive rate for ADSL port,
                  in bps.  See adslAtucConfRateChanRatio for information
                  regarding RADSL mode and ATUR transmit rate for
                  ATUC receive rates.
                  Unit: bps
                 "
         ::= { hwAdslLineLatestActParaEntry 12 }

         hwAdslAtucLatestInterleaveDelay OBJECT-TYPE
             SYNTAX      Gauge32
             UNITS       "milliseconds"
             MAX-ACCESS  read-only
             STATUS      current
             DESCRIPTION
                 "Interleave Delay for this channel when latest actived.
                  Unit: milliseconds
                 "
         ::= { hwAdslLineLatestActParaEntry 13 }

         hwAdslAturLatestInterleaveDelay OBJECT-TYPE
             SYNTAX      Gauge32
             UNITS       "milliseconds"
             MAX-ACCESS  read-only
             STATUS      current
             DESCRIPTION
                 "Interleave Delay for this channel when latest actived.
                  Unit: milliseconds
                 "
         ::= { hwAdslLineLatestActParaEntry 14 }

        hwAdslAtucLatestTargetSnrMgn OBJECT-TYPE
             SYNTAX      Integer32 (0..310)
             UNITS       "tenth dB"
             MAX-ACCESS  read-only
             STATUS      current
             DESCRIPTION
                 "Port Signal/Noise Margin.
                  Range: 0-310
                  Unit: tenth dB
                 "
         ::= { hwAdslLineLatestActParaEntry 15 }

        hwAdslAturLatestTargetSnrMgn OBJECT-TYPE
             SYNTAX      Integer32 (0..310)
             UNITS       "tenth dB"
             MAX-ACCESS  read-only
             STATUS      current
             DESCRIPTION
                 "Port Signal/Noise Margin.
                  Range: 0-310
                  Unit: tenth dB
                 "
         ::= { hwAdslLineLatestActParaEntry 16 }

	hwAdslAtucLatestTxRateThreshold OBJECT-TYPE
	     SYNTAX Gauge32
	     UNITS "bps"
	     MAX-ACCESS read-only
	     STATUS      current
	     DESCRIPTION
	                "Port down stream threshold.
		 	 Unit: bps
		 	"
         ::= { hwAdslLineLatestActParaEntry 17 }      
            
	hwAdslAturLatestTxRateThreshold OBJECT-TYPE
	     SYNTAX Gauge32
	     UNITS "bps"
	     MAX-ACCESS read-only
	     STATUS      current
	    DESCRIPTION
	               "Port up stream threshold.
	                Unit: bps
	               "
	 ::= { hwAdslLineLatestActParaEntry 18 } 
--
--  hwXdslPortPerformanceStatTable
--
        hwXdslPortPerformanceStatTable OBJECT-TYPE
			SYNTAX SEQUENCE OF HwXdslPortPerformanceStatEntry
			MAX-ACCESS not-accessible
			STATUS current
			DESCRIPTION
			    "XDSL port performance statistic table.
			     The indexes of this table are ifIndex and hwXdslPort15minutesPerformanceInterval.
			    "
			::= { adslMibObjects 65545 }
		
		hwXdslPortPerformanceStatEntry OBJECT-TYPE
			SYNTAX HwXdslPortPerformanceStatEntry
			MAX-ACCESS not-accessible
			STATUS current
			DESCRIPTION
			    "XDSL port performance statistic table.
			     The indexes of this entry are ifIndex and hwXdslPort15minutesPerformanceInterval.
			    "
			INDEX {        
			      ifIndex,
			      hwXdslPort15minutesPerformanceInterval 
			      }
			::= { hwXdslPortPerformanceStatTable 1 }
		
		HwXdslPortPerformanceStatEntry ::=
			SEQUENCE{
			    hwXdslPort15minutesPerformanceInterval
					Integer32,
				hwXdslPort15minutesPerformanceInBytes
					Counter32,
				hwXdslPort15minutesPerformanceOutBytes
					Counter32,
			        hwXdslPortSyncSuccNumber
			                Counter32,
			        hwXdslPortSyncFailNumber
			                Counter32,
			        hwXdslPortAtucCodeViolation
			                Counter32,
			        hwXdslPortAturCodeViolation
			                Counter32,
			        hwXdslPortAtucFecSeconds
			                Counter32,
			        hwXdslPortAturFecSeconds
			                Counter32,			                
				hwXdslPortCurrent15minutesStatTime
					Counter32
				    }       
	    
	    hwXdslPort15minutesPerformanceInterval OBJECT-TYPE
			SYNTAX Integer32(0..96)
			MAX-ACCESS not-accessible
			STATUS current
			DESCRIPTION   
			    "The index of the interval which is queried.
			     Range: 0-96
			    "  
			
			::= { hwXdslPortPerformanceStatEntry 1 }


		hwXdslPort15minutesPerformanceInBytes OBJECT-TYPE
			SYNTAX Counter32
			MAX-ACCESS read-only
			STATUS current
			DESCRIPTION   
			    "Read the receive bytes of xDSL port during 15 minutes."  
			
			::= { hwXdslPortPerformanceStatEntry 2 }
			
		hwXdslPort15minutesPerformanceOutBytes OBJECT-TYPE
			SYNTAX Counter32 
			MAX-ACCESS read-only
			STATUS current
			DESCRIPTION
			    "Read the transmit bytes of xDSL port during 15 minutes." 
			
			::= { hwXdslPortPerformanceStatEntry 3 }
	        
	        hwXdslPortSyncSuccNumber OBJECT-TYPE
			SYNTAX Counter32 
			MAX-ACCESS read-only
			STATUS current
			DESCRIPTION
			    "Number of successful activations of the xDSL port within 15 minutes." 
			
			::= { hwXdslPortPerformanceStatEntry 4 }
		
		hwXdslPortSyncFailNumber OBJECT-TYPE
			SYNTAX Counter32 
			MAX-ACCESS read-only
			STATUS current
			DESCRIPTION
			    "Number of failed activations of the xDSL port within 15 minutes." 
			
			::= { hwXdslPortPerformanceStatEntry 5 }
			
	        hwXdslPortAtucCodeViolation OBJECT-TYPE
			SYNTAX Counter32 
			MAX-ACCESS read-only
			STATUS current
			DESCRIPTION
			    "Number of head errors of the ATUC cell within 15 minutes." 
			
			::= { hwXdslPortPerformanceStatEntry 6 }
			
		hwXdslPortAturCodeViolation OBJECT-TYPE
			SYNTAX Counter32 
			MAX-ACCESS read-only
			STATUS current
			DESCRIPTION
			    "Number of head errors of the ATUR cell within 15 minutes." 
			
			::= { hwXdslPortPerformanceStatEntry 7 }
			
		hwXdslPortAtucFecSeconds OBJECT-TYPE
			SYNTAX Counter32 
			MAX-ACCESS read-only
			STATUS current
			DESCRIPTION
			    "Seconds of the ATUC FEC errors within 15 minutes." 
			
			::= { hwXdslPortPerformanceStatEntry 8 }	
		
		hwXdslPortAturFecSeconds OBJECT-TYPE
			SYNTAX Counter32 
			MAX-ACCESS read-only
			STATUS current
			DESCRIPTION
			    "Seconds of the ATUR FEC errors within 15 minutes." 
			
			::= { hwXdslPortPerformanceStatEntry 9 }
			
		hwXdslPortCurrent15minutesStatTime OBJECT-TYPE
			SYNTAX Counter32
			MAX-ACCESS read-only
			STATUS current
			DESCRIPTION
			    "Seconds passed within the current 15 minutes."  
			
			::= { hwXdslPortPerformanceStatEntry 10 }
-- adslAtucPhysTable
         hwAdslAtucCurrTransMode OBJECT-TYPE
             SYNTAX      HWADSLTRANSMISSIONMODETYPE
             MAX-ACCESS  read-only
             STATUS      current
             DESCRIPTION
                 "A set of ADSL line transmission modes."
         ::= { adslAtucPhysEntry 65536 }

		-- 1.3.6.1.2.1.10.94.1.1.2.1.65537
		hwAdslAtucCurrSignalAtn OBJECT-TYPE
			SYNTAX Gauge32 (0..630)
			UNITS "tenth dB"
			MAX-ACCESS read-only
			STATUS current
			DESCRIPTION
			    "Current signal attenuation of the ATU-C, indicating the difference between the transmit signal of the ATU-R and the receive signal of the ATU-C.
			     Range: 0-630
			     Unit: tenth dB
			    "
			::= { adslAtucPhysEntry 65537 }
		
        hwadsl2LineTransAtucActual OBJECT-TYPE
             SYNTAX      Adsl2TransmissionModeType
             MAX-ACCESS  read-only
             STATUS      current
             DESCRIPTION
                 "The actual transmission mode of the ATU-C.
                  During ADSL line initialization, the ADSL
                  Transceiver Unit - Remote terminal end (ATU-R)
                  will determine the mode used for the link.
                  This value will be limited a single transmission
                  mode that is a subset of those modes enabled
                  by the ATU-C and denoted by
                  adslLineTransAtucConfig. After an initialization
                  has occurred, its mode is saved as the 'Current'
                  mode and is persistence should the link go
                  down. This object returns 0 (i.e. BITS with no
                  mode bit set) if the mode is not known.
                 "
             REFERENCE "Section 7.3.2 ITU G.997.1 "
         ::= { adslLineExtEntry 65555 }
         
--
--  ADSL Port Performance Statistics FEC,HEC,CRC
--
--  adslAtucChanPerfDataTable
         hwadslAtucChanFecBlks  OBJECT-TYPE
             SYNTAX      Counter32
             MAX-ACCESS  read-only
             STATUS      current
             DESCRIPTION
                 "Count of all blocks received with FEC anomalies
                  since agent reset.
                 "
         ::= { adslAtucChanPerfDataEntry 65536 }
         
         hwadslAtucChanHecBlks  OBJECT-TYPE
             SYNTAX      Counter32
             MAX-ACCESS  read-only
             STATUS      current
             DESCRIPTION
                 "Count of all blocks received with HEC anomalies
                  since agent reset.
                 "
         ::= { adslAtucChanPerfDataEntry 65537 }
         
         hwadslAtucChanCrcBlks  OBJECT-TYPE
             SYNTAX      Counter32
             MAX-ACCESS  read-only
             STATUS      current
             DESCRIPTION
                 "Count of all blocks received with CRC anomalies
                  since agent reset.
                 "
         ::= { adslAtucChanPerfDataEntry 65538 }
         
         hwadslAtucChanPerfCurr15MinFecBlks  OBJECT-TYPE
             SYNTAX      Counter32
             MAX-ACCESS  read-only
             STATUS      current
             DESCRIPTION
                 "Count of all blocks received with FEC anomalies
                  on this channel within the current 15 minute
                  interval.
                 "
         ::= { adslAtucChanPerfDataEntry 65539 }
         
         hwadslAtucChanPerfCurr15MinHecBlks  OBJECT-TYPE
             SYNTAX      Counter32
             MAX-ACCESS  read-only
             STATUS      current
             DESCRIPTION
                 "Count of all blocks received with HEC anomalies
                  on this channel within the current 15 minute
                  interval.
                 "
         ::= { adslAtucChanPerfDataEntry 65540 }
         
         hwadslAtucChanPerfCurr15MinCrcBlks  OBJECT-TYPE
             SYNTAX      Counter32
             MAX-ACCESS  read-only
             STATUS      current
             DESCRIPTION
                 "Count of all blocks received with CRC anomalies
                  on this channel within the current 15 minute
                  interval.
                 "
         ::= { adslAtucChanPerfDataEntry 65541 }
         
         hwadslAtucChanPerfCurr1DayFecBlks  OBJECT-TYPE
             SYNTAX      Counter32
             MAX-ACCESS  read-only
             STATUS      current
             DESCRIPTION
                 "Count of all blocks received with FEC anomalies
                  on this channel during the current day as
                  measured by adslAtucChanPerfCurr1DayTimeElapsed.
                 "
         ::= { adslAtucChanPerfDataEntry 65542 }
         
         hwadslAtucChanPerfCurr1DayHecBlks  OBJECT-TYPE
             SYNTAX      Counter32
             MAX-ACCESS  read-only
             STATUS      current
             DESCRIPTION
                 "Count of all blocks received with HEC anomalies
                  on this channel during the current day as
                  measured by adslAtucChanPerfCurr1DayTimeElapsed.
                 "
         ::= { adslAtucChanPerfDataEntry 65543 }
         
         hwadslAtucChanPerfCurr1DayCrcBlks  OBJECT-TYPE
             SYNTAX      Counter32
             MAX-ACCESS  read-only
             STATUS      current
             DESCRIPTION
                 "Count of all blocks received with CRC anomalies
                  on this channel during the current day as
                  measured by adslAtucChanPerfCurr1DayTimeElapsed.
                 "
         ::= { adslAtucChanPerfDataEntry 65544 }
         
         hwadslAtucChanPerfPrev1DayFecBlks  OBJECT-TYPE
             SYNTAX      Counter32
             MAX-ACCESS  read-only
             STATUS      current
             DESCRIPTION
                 "Count of all blocks received with FEC anomalies
                  on this channel within the most recent previous
                  1-day period.
                 "
         ::= { adslAtucChanPerfDataEntry 65545 }
         
         hwadslAtucChanPerfPrev1DayHecBlks  OBJECT-TYPE
             SYNTAX      Counter32
             MAX-ACCESS  read-only
             STATUS      current
             DESCRIPTION
                 "Count of all blocks received with HEC anomalies
                  on this channel within the most recent previous
                  1-day period.
                 "
         ::= { adslAtucChanPerfDataEntry 65546 }
         
         hwadslAtucChanPerfPrev1DayCrcBlks  OBJECT-TYPE
             SYNTAX      Counter32
             MAX-ACCESS  read-only
             STATUS      current
             DESCRIPTION
                 "Count of all blocks received with CRC anomalies
                  on this channel within the most recent previous
                  1-day period.
                 "
         ::= { adslAtucChanPerfDataEntry 65547 }
         
--  adslAturChanPerfDataTable
         hwadslAturChanFecBlks  OBJECT-TYPE
             SYNTAX      Counter32
             MAX-ACCESS  read-only
             STATUS      current
             DESCRIPTION
                 "Count of all blocks received with FEC anomalies
                  since agent reset.
                 "
         ::= { adslAturChanPerfDataEntry 65536 }
         
         hwadslAturChanHecBlks  OBJECT-TYPE
             SYNTAX      Counter32
             MAX-ACCESS  read-only
             STATUS      current
             DESCRIPTION
                 "Count of all blocks received with HEC anomalies
                  since agent reset.
                 "
         ::= { adslAturChanPerfDataEntry 65537 }
         
         hwadslAturChanCrcBlks  OBJECT-TYPE
             SYNTAX      Counter32
             MAX-ACCESS  read-only
             STATUS      current
             DESCRIPTION
                 "Count of all blocks received with CRC anomalies
                  since agent reset.
                 "
         ::= { adslAturChanPerfDataEntry 65538 }
         
         hwadslAturChanPerfCurr15MinFecBlks  OBJECT-TYPE
             SYNTAX      Counter32
             MAX-ACCESS  read-only
             STATUS      current
             DESCRIPTION
                 "Count of all blocks received with FEC anomalies
                  on this channel within the current 15 minute
                  interval.
                 "
         ::= { adslAturChanPerfDataEntry 65539 }
         
         hwadslAturChanPerfCurr15MinHecBlks  OBJECT-TYPE
             SYNTAX      Counter32
             MAX-ACCESS  read-only
             STATUS      current
             DESCRIPTION
                 "Count of all blocks received with HEC anomalies
                  on this channel within the current 15 minute
                  interval.
                 "
         ::= { adslAturChanPerfDataEntry 65540 }
         
         hwadslAturChanPerfCurr15MinCrcBlks  OBJECT-TYPE
             SYNTAX      Counter32
             MAX-ACCESS  read-only
             STATUS      current
             DESCRIPTION
                 "Count of all blocks received with CRC anomalies
                  on this channel within the current 15 minute
                  interval.
                 "
         ::= { adslAturChanPerfDataEntry 65541 }
         
         hwadslAturChanPerfCurr1DayFecBlks  OBJECT-TYPE
             SYNTAX      Counter32
             MAX-ACCESS  read-only
             STATUS      current
             DESCRIPTION
                 "Count of all blocks received with FEC anomalies
                  on this channel during the current day as
                  measured by adslAturChanPerfCurr1DayTimeElapsed.
                 "
         ::= { adslAturChanPerfDataEntry 65542 }
         
         hwadslAturChanPerfCurr1DayHecBlks  OBJECT-TYPE
             SYNTAX      Counter32
             MAX-ACCESS  read-only
             STATUS      current
             DESCRIPTION
                 "Count of all blocks received with HEC anomalies
                  on this channel during the current day as
                  measured by adslAturChanPerfCurr1DayTimeElapsed.
                 "
         ::= { adslAturChanPerfDataEntry 65543 }
         
         hwadslAturChanPerfCurr1DayCrcBlks  OBJECT-TYPE
             SYNTAX      Counter32
             MAX-ACCESS  read-only
             STATUS      current
             DESCRIPTION
                 "Count of all blocks received with CRC anomalies
                  on this channel during the current day as
                  measured by adslAturChanPerfCurr1DayTimeElapsed.
                 "
         ::= { adslAturChanPerfDataEntry 65544 }
         
         hwadslAturChanPerfPrev1DayFecBlks  OBJECT-TYPE
             SYNTAX      Counter32
             MAX-ACCESS  read-only
             STATUS      current
             DESCRIPTION
                 "Count of all blocks received with FEC anomalies
                  on this channel within the most recent previous
                  1-day period.
                 "
         ::= { adslAturChanPerfDataEntry 65545 }
         
         hwadslAturChanPerfPrev1DayHecBlks  OBJECT-TYPE
             SYNTAX      Counter32
             MAX-ACCESS  read-only
             STATUS      current
             DESCRIPTION
                 "Count of all blocks received with HEC anomalies
                  on this channel within the most recent previous
                  1-day period.
                 "
         ::= { adslAturChanPerfDataEntry 65546 }
         
         hwadslAturChanPerfPrev1DayCrcBlks  OBJECT-TYPE
             SYNTAX      Counter32
             MAX-ACCESS  read-only
             STATUS      current
             DESCRIPTION
                 "Count of all blocks received with CRC anomalies
                  on this channel within the most recent previous
                  1-day period.
                 "
         ::= { adslAturChanPerfDataEntry 65547 }
         
--  adslAtucChanIntervalTable
         hwadslAtucChanIntervalFecBlks OBJECT-TYPE
             SYNTAX      PerfIntervalCount
             MAX-ACCESS  read-only
             STATUS      current
             DESCRIPTION
                 "Count of all blocks received with FRC anomalies
                  on this channel during this interval.
                 "
         ::= { adslAtucChanIntervalEntry 65536 }
         
         hwadslAtucChanIntervalHecBlks OBJECT-TYPE
             SYNTAX      PerfIntervalCount
             MAX-ACCESS  read-only
             STATUS      current
             DESCRIPTION
                 "Count of all blocks received with HRC anomalies
                  on this channel during this interval.
                 "
         ::= { adslAtucChanIntervalEntry 65537 }
         
         hwadslAtucChanIntervalCrcBlks OBJECT-TYPE
             SYNTAX      PerfIntervalCount
             MAX-ACCESS  read-only
             STATUS      current
             DESCRIPTION
                 "Count of all blocks received with CRC anomalies
                  on this channel during this interval.
                 "
         ::= { adslAtucChanIntervalEntry 65538 }
         
--  adslAturChanIntervalTable
         hwadslAturChanIntervalFecBlks OBJECT-TYPE
             SYNTAX      PerfIntervalCount
             MAX-ACCESS  read-only
             STATUS      current
             DESCRIPTION
                 "Count of all blocks received with FRC anomalies
                  on this channel during this interval.
                 "
         ::= { adslAturChanIntervalEntry 65536 }
         
         hwadslAturChanIntervalHecBlks OBJECT-TYPE
             SYNTAX      PerfIntervalCount
             MAX-ACCESS  read-only
             STATUS      current
             DESCRIPTION
                 "Count of all blocks received with HRC anomalies
                  on this channel during this interval.
                 "
         ::= { adslAturChanIntervalEntry 65537 }
         
         hwadslAturChanIntervalCrcBlks OBJECT-TYPE
             SYNTAX      PerfIntervalCount
             MAX-ACCESS  read-only
             STATUS      current
             DESCRIPTION
                 "Count of all blocks received with CRC anomalies
                  on this channel during this interval.
                 "
         ::= { adslAturChanIntervalEntry 65538 }

--  adslLineAlarmConfProfileTable
         hwadslLineAlarmConfProfileDyingGasp OBJECT-TYPE
             SYNTAX      INTEGER {
                 enable (1),
                 disable (2)
             }
             MAX-ACCESS  read-create
             STATUS      current
             DESCRIPTION
                 "This object enables/disables the report of LOSS-OF-POWER
                  alarm in an ADSL line, This object is defaulted enable(1).
                  Options: 
                  1. enable (1)  - The LOSS-OF-POWER alarm in an ADSL line will be reported
                  2. disable (2) - The LOSS-OF-POWER alarm in an ADSL line will not be reported
                 "
         
         ::= { adslLineAlarmConfProfileEntry 65536 }
         	
--  hwAdslPortPerformanceStatTable
--
        hwAdslPortPerformanceStatTable OBJECT-TYPE
			SYNTAX SEQUENCE OF HwAdslPortPerformanceStatEntry
			MAX-ACCESS not-accessible
			STATUS current
			DESCRIPTION
			    "This table is used to describe the performance statistics of the ADSL port within 15 minutes.
                             The indexes of this table are ifIndex and hwAdslPort15minutesPerformanceInterval.
                            "

			::= { adslMibObjects 65546 }
		
		hwAdslPortPerformanceStatEntry OBJECT-TYPE
			SYNTAX HwAdslPortPerformanceStatEntry
			MAX-ACCESS not-accessible
			STATUS current
			DESCRIPTION
			    "This table is used to describe the performance statistics of the ADSL port within 15 minutes.
                             The indexes of this entry are ifIndex and hwAdslPort15minutesPerformanceInterval.
                            "
			INDEX {        
			      ifIndex,
			      hwAdslPort15minutesPerformanceInterval 
			      }
			::= { hwAdslPortPerformanceStatTable 1 }
		
		HwAdslPortPerformanceStatEntry ::=
			SEQUENCE{
			        hwAdslPort15minutesPerformanceInterval
					Integer32,
				hwAdslPort15minutesPerformanceInBytes
					Counter32,
				hwAdslPort15minutesPerformanceOutBytes
					Counter32,
			        hwAdslPortSyncSuccNumber
			                Counter32,
			        hwAdslPortSyncFailNumber
			                Counter32,
			        hwAdslPortAtucCodeViolation
			                Counter32,
			        hwAdslPortAturCodeViolation
			                Counter32,
			        hwAdslPortAtucFecSeconds
			                Counter32,
			        hwAdslPortAturFecSeconds
			                Counter32,			                
				hwAdslPortCurrent15minutesTimeElapse
					Counter32,
			        hwAdslPortAtucHecDropCellsCnt
			                Counter32,
			        hwAdslPortAturHecDropCellsCnt
			                Counter32,
			        hwAdslLineConfProfile      
			                OCTET STRING,
			        hwAdslPort15minUpTime
				        Counter32,
				hwAdslAtucCurrAtn                 
				        Gauge32,
				hwAdslAtucCurrSnrMgn
				        Integer32,
				hwAdslAtucCurrAttainableRate
				        Gauge32,
				hwAdslAtucChanCurrTxRate 
				        Gauge32,
				hwAdslAturCurrAtn                 
				        Gauge32,
				hwAdslAturCurrSnrMgn
				        Integer32,
				hwAdslAturCurrAttainableRate      
				        Gauge32,				        
				hwAdslAturChanCurrTxRate
				        Gauge32,
                                hwAdslAtucIntervalESs             
                                        PerfIntervalCount,	
                                hwAdslAtucIntervalLofs            
                                        PerfIntervalCount,
                                hwAdslAtucIntervalLols            
                                        PerfIntervalCount,
                                hwAdslAtucIntervalLoss           
                                        PerfIntervalCount,
                                hwAdslAtucIntervalLprs           
                                        PerfIntervalCount,
                                hwAdslAturIntervalESs             
                                        PerfIntervalCount,
                                hwAdslAturIntervalLofs            
                                        PerfIntervalCount,
                                hwAdslAturIntervalLoss            
                                        PerfIntervalCount,
                                hwAdslAturIntervalLprs            
                                        PerfIntervalCount,
                                hwAdslAtucChanIntervalReceivedBlks    
                                        PerfIntervalCount,
                                hwAdslAtucChanIntervalTransmittedBlks 
                                        PerfIntervalCount,
                                hwAdslAtucChanIntervalCorrectedBlks   
                                        PerfIntervalCount,
                                hwAdslAtucChanIntervalUncorrectBlks  
                                        PerfIntervalCount,
                                hwAdslAturChanIntervalReceivedBlks        
                                        PerfIntervalCount,
                                hwAdslAturChanIntervalTransmittedBlks      
                                        PerfIntervalCount,
                                hwAdslAturChanIntervalCorrectedBlks        
                                        PerfIntervalCount,
                                hwAdslAturChanIntervalUncorrectBlks        
                                        PerfIntervalCount,
                                hwAdslAtucIntervalSesL             
                                        PerfIntervalCount,
                                hwAdslAtucIntervalUasL             
                                        PerfIntervalCount,
                                hwAdslAturIntervalSesL             
                                        PerfIntervalCount,
                                hwAdslAturIntervalUasL            
                                        PerfIntervalCount,
                                hwAdslPortCurrentActMode
                                	INTEGER
				    }       
	                        
	    hwAdslPort15minutesPerformanceInterval OBJECT-TYPE
			SYNTAX Integer32(0..96)
			MAX-ACCESS not-accessible
			STATUS current
			DESCRIPTION   
			    "The index of the interval which is queried.
			     Range: 0-96
			    "  
			
			::= { hwAdslPortPerformanceStatEntry 1 }


		hwAdslPort15minutesPerformanceInBytes OBJECT-TYPE
			SYNTAX Counter32
			MAX-ACCESS read-only
			STATUS current
			DESCRIPTION   
			    "Read the receive bytes of xDSL port during 15 minutes."  
			
			::= { hwAdslPortPerformanceStatEntry 2 }
			
		hwAdslPort15minutesPerformanceOutBytes OBJECT-TYPE
			SYNTAX Counter32 
			MAX-ACCESS read-only
			STATUS current
			DESCRIPTION
			    "Read the transmit bytes of xDSL port during 15 minutes." 
			
			::= { hwAdslPortPerformanceStatEntry 3 }
	        
	        hwAdslPortSyncSuccNumber OBJECT-TYPE
			SYNTAX Counter32 
			MAX-ACCESS read-only
			STATUS current
			DESCRIPTION
			    "Number of successful activations within 15 minutes." 
			
			::= { hwAdslPortPerformanceStatEntry 4 }
		
		hwAdslPortSyncFailNumber OBJECT-TYPE
			SYNTAX Counter32 
			MAX-ACCESS read-only
			STATUS current
			DESCRIPTION
			    "Number of failed activations within 15 minutes." 
			
			::= { hwAdslPortPerformanceStatEntry 5 }
			
	        hwAdslPortAtucCodeViolation OBJECT-TYPE
			SYNTAX Counter32 
			MAX-ACCESS read-only
			STATUS current
			DESCRIPTION
			    "Seconds of head errors of the ATUC cell within 15 minutes." 
			
			::= { hwAdslPortPerformanceStatEntry 6 }
			
		hwAdslPortAturCodeViolation OBJECT-TYPE
			SYNTAX Counter32 
			MAX-ACCESS read-only
			STATUS current
			DESCRIPTION
			    "Seconds of head errors of the ATUC cell within 15 minutes." 
			
			::= { hwAdslPortPerformanceStatEntry 7 }
			
		hwAdslPortAtucFecSeconds OBJECT-TYPE
			SYNTAX Counter32 
			MAX-ACCESS read-only
			STATUS current
			DESCRIPTION
			    "Seconds of the ATUC FEC errors within 15 minutes." 
			
			::= { hwAdslPortPerformanceStatEntry 8 }	
		
		hwAdslPortAturFecSeconds OBJECT-TYPE
			SYNTAX Counter32 
			MAX-ACCESS read-only
			STATUS current
			DESCRIPTION
			    "Error seconds of the ATUR FEC within 15 minutes." 
			
			::= { hwAdslPortPerformanceStatEntry 9 }
			
		hwAdslPortCurrent15minutesTimeElapse OBJECT-TYPE
			SYNTAX Counter32
			MAX-ACCESS read-only
			STATUS current
			DESCRIPTION
			    "Seconds that is passed within the current 15 minutes."  
			
			::= { hwAdslPortPerformanceStatEntry 10 }
				
		hwAdslPortAtucHecDropCellsCnt OBJECT-TYPE
			SYNTAX Counter32
			MAX-ACCESS read-only
			STATUS current
			DESCRIPTION
			    "ATUC cells discarded with HEC Errors."  
			
			::= { hwAdslPortPerformanceStatEntry 11 }
			
		hwAdslPortAturHecDropCellsCnt OBJECT-TYPE
			SYNTAX Counter32
			MAX-ACCESS read-only
			STATUS current
			DESCRIPTION
			    "ATUR cells discarded with HEC Errors."  
			
			::= { hwAdslPortPerformanceStatEntry 12 }
			
	        hwAdslLineConfProfile OBJECT-TYPE
                        SYNTAX      OCTET STRING (SIZE (0..32))
                        MAX-ACCESS  read-only
                        STATUS      current
                        DESCRIPTION
                            "The value of this object identifies the row
                             in the ADSL Line Configuration Profile Table,
                             (adslLineConfProfileTable), which applies for this
                             ADSL line, and channels if applicable.
                             
                             For 'dynamic' mode, in the case which the
                             configuration profile has not been set, the
                             value will be set to 'DEFVAL'.
                             
                             If the creator of this MIB has chosen not
                             to implement 'dynamic assignment' of profiles, this
                             object's MIN-ACCESS is read-only.
                            "
                        ::= { hwAdslPortPerformanceStatEntry 13 }

                hwAdslPort15minUpTime OBJECT-TYPE
			SYNTAX Counter32
			MAX-ACCESS read-only
			STATUS current
			DESCRIPTION
			    "Up time in the interval.
			     Unit: seconds
			    "
 			::= { hwAdslPortPerformanceStatEntry 14 }
 			
 	        hwAdslAtucCurrAtn  OBJECT-TYPE
                        SYNTAX      Gauge32(0..630)
                        UNITS       "tenth dB"
                        MAX-ACCESS  read-only
                        STATUS      current
                        DESCRIPTION
                            "Measured difference in the total power transmitted by
                             the peer ATU and the total power received by this ATU.
                             Range: 0-630
                             Unit: tenth dB
                            "
                        ::= { hwAdslPortPerformanceStatEntry 15 }
                        
                hwAdslAtucCurrSnrMgn OBJECT-TYPE
                        SYNTAX      Integer32 (-640..640)
                        UNITS       "tenth dB"
                        MAX-ACCESS  read-only
                        STATUS      current
                        DESCRIPTION
                            "Noise Margin as seen by this ATU with respect to its
                             received signal in tenth dB.
                             Unit: tenth dB
                            "
                        ::= { hwAdslPortPerformanceStatEntry 16 }
                        
                hwAdslAtucCurrAttainableRate OBJECT-TYPE
                        SYNTAX      Gauge32
                        UNITS       "bps"
                        MAX-ACCESS  read-only
                        STATUS      current
                        DESCRIPTION
                            "Indicates the maximum currently attainable data rate
                             by the ATU.  This value will be equal or greater than
                             the current line rate.
                             Unit: bps
                            "
                        ::= { hwAdslPortPerformanceStatEntry 17 }
                        
                hwAdslAtucChanCurrTxRate  OBJECT-TYPE
                        SYNTAX      Gauge32
                        UNITS       "bps"
                        MAX-ACCESS  read-only
                        STATUS      current
                        DESCRIPTION
                            "Actual transmit rate on this channel.
                             Unit: bps
                            "
                        ::= { hwAdslPortPerformanceStatEntry 18 } 
                        
                hwAdslAturCurrAtn OBJECT-TYPE
                        SYNTAX      Gauge32(0..630)
                        UNITS       "tenth dB"
                        MAX-ACCESS  read-only
                        STATUS      current
                        DESCRIPTION
                            "Measured difference in the total power transmitted by
                             the peer ATU and the total power received by this ATU.
                             Range: 0-630
                             Unit: tenth dB
                            "
                        ::= { hwAdslPortPerformanceStatEntry 19 }
                        
                hwAdslAturCurrSnrMgn OBJECT-TYPE
                        SYNTAX      Integer32 (-640..640)
                        UNITS       "tenth dB"
                        MAX-ACCESS  read-only
                        STATUS      current
                        DESCRIPTION
                            "Noise Margin as seen by this ATU with respect to its
                             received signal in tenth dB.
                             Unit: tenth dB
                            "
                        ::= { hwAdslPortPerformanceStatEntry 20 }
                        
                hwAdslAturCurrAttainableRate OBJECT-TYPE
                        SYNTAX      Gauge32
                        UNITS       "bps"
                        MAX-ACCESS  read-only
                        STATUS      current
                        DESCRIPTION
                            "Indicates the maximum currently attainable data rate
                             by the ATU.  This value will be equal or greater than
                             the current line rate.
                             Unit: bps
                            "
                        ::= { hwAdslPortPerformanceStatEntry 21 }
                        
                hwAdslAturChanCurrTxRate  OBJECT-TYPE
                        SYNTAX      Gauge32
                        UNITS       "bps"
                        MAX-ACCESS  read-only
                        STATUS      current
                        DESCRIPTION
                            "Actual transmit rate on this channel.
                             Unit: bps
                            "
                        ::= { hwAdslPortPerformanceStatEntry 22 }
                        
                hwAdslAtucIntervalESs OBJECT-TYPE
                        SYNTAX      PerfIntervalCount
                        UNITS       "seconds"
                        MAX-ACCESS  read-only
                        STATUS      current
                        DESCRIPTION
                            "Count of Errored Seconds in the interval.
                             The errored second parameter is a count of
                             one-second intervals containing one or more crc
                             anomalies, or one or more los or sef defects.
                             Unit: seconds
                            "
                        ::= { hwAdslPortPerformanceStatEntry 23 }
                        
                hwAdslAtucIntervalLofs OBJECT-TYPE
                        SYNTAX      PerfIntervalCount
                        UNITS       "seconds"
                        MAX-ACCESS  read-only
                        STATUS      current
                        DESCRIPTION
                            "Count of seconds in the interval when there was Loss
                             of Framing.
                             Unit: seconds
                            "
                        ::= { hwAdslPortPerformanceStatEntry 24 }
                        
                hwAdslAtucIntervalLols  OBJECT-TYPE
                        SYNTAX      PerfIntervalCount
                        UNITS       "seconds"
                        MAX-ACCESS  read-only
                        STATUS      current
                        DESCRIPTION
                            "Count of seconds in the interval when there was Loss
                             of Link.
                             Unit: seconds
                            "
                        ::= { hwAdslPortPerformanceStatEntry 25 }
                        
                hwAdslAtucIntervalLoss  OBJECT-TYPE
                        SYNTAX      PerfIntervalCount
                        UNITS       "seconds"
                        MAX-ACCESS  read-only
                        STATUS      current
                        DESCRIPTION
                            "Count of seconds in the interval when there was Loss
                             of Signal.
                             Unit: seconds
                            "
                        ::= { hwAdslPortPerformanceStatEntry 26 }
                        
                hwAdslAtucIntervalLprs  OBJECT-TYPE
                        SYNTAX      PerfIntervalCount
                        UNITS       "seconds"
                        MAX-ACCESS  read-only
                        STATUS      current
                        DESCRIPTION
                            "Count of seconds in the interval when there was Loss of Power.
                             Unit: seconds
                            "
                        ::= { hwAdslPortPerformanceStatEntry 27 }
               
                hwAdslAturIntervalESs OBJECT-TYPE
                        SYNTAX      PerfIntervalCount
                        UNITS       "seconds"
                        MAX-ACCESS  read-only
                        STATUS      current
                        DESCRIPTION
                            "Count of Errored Seconds in the interval.
                             The errored second parameter is a count of
                             one-second intervals containing one or more crc
                             anomalies, or one or more los or sef defects.
                             Unit: seconds
                            "
                        ::= { hwAdslPortPerformanceStatEntry 28 } 
                        
                hwAdslAturIntervalLofs OBJECT-TYPE
                        SYNTAX      PerfIntervalCount
                        UNITS       "seconds"
                        MAX-ACCESS  read-only
                        STATUS      current
                        DESCRIPTION
                            "Count of seconds in the interval when there was
                             Loss of Framing.
                             Unit: seconds
                            "
                        ::= { hwAdslPortPerformanceStatEntry 29 }

                hwAdslAturIntervalLoss  OBJECT-TYPE
                        SYNTAX      PerfIntervalCount
                        UNITS       "seconds"
                        MAX-ACCESS  read-only
                        STATUS      current
                        DESCRIPTION
                            "Count of seconds in the interval when there was Loss of Signal.
                             Unit: seconds
                            "
                        ::= { hwAdslPortPerformanceStatEntry 30 }

                hwAdslAturIntervalLprs  OBJECT-TYPE
                        SYNTAX      PerfIntervalCount
                        UNITS       "seconds"
                        MAX-ACCESS  read-only
                        STATUS      current
                        DESCRIPTION
                            "Count of seconds in the interval when there was Loss of Power.
                             Unit: seconds
                            "
                        ::= { hwAdslPortPerformanceStatEntry 31 }  
                        
                hwAdslAtucChanIntervalReceivedBlks OBJECT-TYPE
                        SYNTAX      PerfIntervalCount
                        MAX-ACCESS  read-only
                        STATUS      current
                        DESCRIPTION
                            "Count of all encoded blocks received on this channel
                             during this interval.
                            "
                        ::= { hwAdslPortPerformanceStatEntry 32 }

                hwAdslAtucChanIntervalTransmittedBlks  OBJECT-TYPE
                        SYNTAX      PerfIntervalCount
                        MAX-ACCESS  read-only
                        STATUS      current
                        DESCRIPTION
                            "Count of all encoded blocks transmitted on this
                             channel during this interval.
                            "
                        ::= { hwAdslPortPerformanceStatEntry 33 }

                hwAdslAtucChanIntervalCorrectedBlks  OBJECT-TYPE
                        SYNTAX      PerfIntervalCount
                        MAX-ACCESS  read-only
                        STATUS      current
                        DESCRIPTION
                            "Count of all blocks received with errors that were
                             corrected on this channel during this interval.
                            "
                        ::= { hwAdslPortPerformanceStatEntry 34 }

                hwAdslAtucChanIntervalUncorrectBlks  OBJECT-TYPE
                        SYNTAX      PerfIntervalCount
                        MAX-ACCESS  read-only
                        STATUS      current
                        DESCRIPTION
                            "Count of all blocks received with uncorrectable
                             errors on this channel during this interval.
                            "
                        ::= { hwAdslPortPerformanceStatEntry 35 }  
                        
                hwAdslAturChanIntervalReceivedBlks OBJECT-TYPE
                        SYNTAX      PerfIntervalCount
                        MAX-ACCESS  read-only
                        STATUS      current
                        DESCRIPTION
                            "Count of all encoded blocks received on this channel
                             during this interval.
                            "
                        ::= { hwAdslPortPerformanceStatEntry 36 }
                   
                hwAdslAturChanIntervalTransmittedBlks  OBJECT-TYPE
                        SYNTAX      PerfIntervalCount
                        MAX-ACCESS  read-only
                        STATUS      current
                        DESCRIPTION
                            "Count of all encoded blocks transmitted on this
                             channel during this interval.
                            "
                        ::= { hwAdslPortPerformanceStatEntry 37 }
                   
                hwAdslAturChanIntervalCorrectedBlks  OBJECT-TYPE
                        SYNTAX      PerfIntervalCount
                        MAX-ACCESS  read-only
                        STATUS      current
                        DESCRIPTION
                            "Count of all blocks received with errors that were
                             corrected on this channel during this interval.
                            "
                        ::= { hwAdslPortPerformanceStatEntry 38 }

                hwAdslAturChanIntervalUncorrectBlks  OBJECT-TYPE
                        SYNTAX      PerfIntervalCount
                        MAX-ACCESS  read-only
                        STATUS      current
                        DESCRIPTION
                            "Count of all blocks received with uncorrectable
                             errors on this channel during this interval.
                            "
                        ::= { hwAdslPortPerformanceStatEntry 39 } 
                        
                hwAdslAtucIntervalSesL OBJECT-TYPE
                        SYNTAX      PerfIntervalCount
                        UNITS       "seconds"
                        MAX-ACCESS  read-only
                        STATUS      current
                        DESCRIPTION
                            "For the each interval, adslAtucIntervalSesL
                             reports the number of seconds during which
                             there have been severely errored seconds-line.
                             Unit: seconds
                            "
                        ::= { hwAdslPortPerformanceStatEntry 40 }

                hwAdslAtucIntervalUasL OBJECT-TYPE
                        SYNTAX      PerfIntervalCount
                        UNITS       "seconds"
                        MAX-ACCESS  read-only
                        STATUS      current
                        DESCRIPTION
                            "For the each interval, adslAtucIntervalUasL
                             reports the number of seconds during which
                             there have been unavailable seconds-line.
                             Unit: seconds
                            "
                        ::= { hwAdslPortPerformanceStatEntry 41 }
                
                hwAdslAturIntervalSesL OBJECT-TYPE
                        SYNTAX      PerfIntervalCount
                        UNITS       "seconds"
                        MAX-ACCESS  read-only
                        STATUS      current
                        DESCRIPTION
                            "For the each interval, adslAturIntervalSesL
                             reports the number of seconds during which
                             there have been severely errored seconds-line.
                             Unit: seconds
                            "
                        ::= { hwAdslPortPerformanceStatEntry 42 }

                hwAdslAturIntervalUasL OBJECT-TYPE
                        SYNTAX      PerfIntervalCount
                        UNITS       "seconds"
                        MAX-ACCESS  read-only
                        STATUS      current
                        DESCRIPTION
                            "For the each interval, adslAturIntervalUasL
                             reports the number of seconds during which
                             there have been unavailable seconds-line.
                             Unit: seconds
                            "
                        ::= { hwAdslPortPerformanceStatEntry 43 }

                hwAdslPortCurrentActMode OBJECT-TYPE
			SYNTAX INTEGER
			{
			    adsl(1),
			    adsl2(2),
			    adsl2plus(3)
			}
                        MAX-ACCESS  read-only
                        STATUS      current
                        DESCRIPTION
                            "Instantaneous value of the technology type
                             that line is currently trained up under.
                             Options: 
                             1. adsl(1)      - Indicates that line is currently trained up under adsl type
                             2. adsl2(2)     - Indicates that line is currently trained up under adsl2 type
                             3. adsl2plus(3) - Indicates that line is currently trained up under adsl2+ type
                            "
                        ::= { hwAdslPortPerformanceStatEntry 44 }
		
		
--  hwAdslPortRateChangeTrapParaTable
--
        hwAdslPortRateChangeTrapParaTable OBJECT-TYPE
			SYNTAX SEQUENCE OF HwAdslPortRateChangeTrapParaEntry
			MAX-ACCESS not-accessible
			STATUS current
			DESCRIPTION
			    "ADSL line rate change trap parameter table.
			     The index of this table is ifIndex.
			    "
			::= { adslMibObjects 65547 }
		
		hwAdslPortRateChangeTrapParaEntry OBJECT-TYPE
			SYNTAX HwAdslPortRateChangeTrapParaEntry
			MAX-ACCESS not-accessible
			STATUS current
			DESCRIPTION
		            "ADSL line rate change trap parameter table.
			     The index of this entry is ifIndex.
			    "
			INDEX { ifIndex }
			::= { hwAdslPortRateChangeTrapParaTable 1 }
		
		HwAdslPortRateChangeTrapParaEntry ::=
			SEQUENCE{
				hwAdslPortRateChangeTrapIPIAID
					OCTET STRING,      
				hwAdslPortRateChangeTrapMUXID     
					OCTET STRING,
				hwAdslPortRateChangeTrapTimeStamp
					Counter32,      
				hwAdslPortRateChangeTrapDSLineRate  
					Gauge32,  
			        hwAdslPortRateChangeTrapUSLineRate  
					Gauge32,
				hwAdslPortRateChangeTrapEventType
					OCTET STRING,
				hwAdslPortRateChangeTrapDslType
			        OCTET STRING
				    }       
		
		hwAdslPortRateChangeTrapIPIAID OBJECT-TYPE
			SYNTAX OCTET STRING (SIZE (0..63))
		    MAX-ACCESS accessible-for-notify
		    STATUS current
			DESCRIPTION
			    "The port IPIAID is reported when the port rate changes."
 			::= { hwAdslPortRateChangeTrapParaEntry 1 }    
 					
 		hwAdslPortRateChangeTrapMUXID OBJECT-TYPE
			SYNTAX OCTET STRING (SIZE (0..20))
		    MAX-ACCESS accessible-for-notify
		    STATUS current
			DESCRIPTION
			    "The port MUXID is reported when the port rate changes."
 			::= { hwAdslPortRateChangeTrapParaEntry 2 }

  		hwAdslPortRateChangeTrapTimeStamp OBJECT-TYPE
			SYNTAX Counter32
			MAX-ACCESS accessible-for-notify
			STATUS current
			DESCRIPTION
			    "The time stamp of Line rate change trap.
			     Standard Unix format; as the number of seconds since 1/1/1970 (UNIT:Second).
			    "
 			::= { hwAdslPortRateChangeTrapParaEntry 3 } 
 				
 		hwAdslPortRateChangeTrapDSLineRate OBJECT-TYPE
			SYNTAX Gauge32
			MAX-ACCESS accessible-for-notify
			STATUS current
			DESCRIPTION
			    "Down stream line rate after line rate change."
 			::= { hwAdslPortRateChangeTrapParaEntry 4 }   
 			 		
 		hwAdslPortRateChangeTrapUSLineRate OBJECT-TYPE
			SYNTAX Gauge32
			MAX-ACCESS accessible-for-notify
			STATUS current
			DESCRIPTION
			    "Up stream line rate after line rate change."
 			::= { hwAdslPortRateChangeTrapParaEntry 5 }
   
	    hwAdslPortRateChangeTrapEventType OBJECT-TYPE
			SYNTAX OCTET STRING (SIZE (0..2))
			MAX-ACCESS accessible-for-notify
			STATUS current
			DESCRIPTION
			    "Event type reported during the previous change of the rate.
			     If both the upstream and downstream rates change, this leaf object outputs character string 'DU'.
			     If only the upstream rates changes, this leaf object outputs character string 'US'.
			     If only the downstream rates changes, this leaf object outputs character string 'DS'.
                            "
 			::= { hwAdslPortRateChangeTrapParaEntry 6 }	
 			
 	    hwAdslPortRateChangeTrapDslType OBJECT-TYPE
			SYNTAX OCTET STRING (SIZE (0..5))
			MAX-ACCESS accessible-for-notify
			STATUS current
			DESCRIPTION
			    "DSL line type of the port whose rate changes."
 			::= { hwAdslPortRateChangeTrapParaEntry 7 } 
 			    	    
--  hwXdslSysManagementParaTable 
--    
        hwXdslSysManagementParaTable OBJECT IDENTIFIER ::= { adslMibObjects 65548 }			 
		hwAdslPortRateChangeTrapConfig OBJECT-TYPE
			SYNTAX INTEGER
				{
				enabled(1),
				disabled(2)
				}			
			MAX-ACCESS read-write
			STATUS current
			DESCRIPTION
				"Enable or disable ADSL port line-rate change trap feature.
				 Options:
				 1. enabled(1)  - ADSL port line-rate change trap feature is enabled
				 2. disabled(2) - ADSL port line-rate change trap feature is disabled
				"
			::= { hwXdslSysManagementParaTable 1 }

--


-- adslAtucPerfDataTable
		-- 1.3.6.1.2.1.10.94.1.1.6.1.65535
		hwAdslAtucPerfFailFullInits OBJECT-TYPE
			SYNTAX Counter32
			MAX-ACCESS read-only
			STATUS current
			DESCRIPTION
			    "Count of the line initialization failed attempts since agent reset."
			::= { adslAtucPerfDataEntry 65535 }
		
		-- 1.3.6.1.2.1.10.94.1.1.6.1.65536
		hwAdslAtucPerfCurr15MinFailFullInits OBJECT-TYPE
			SYNTAX Counter32
			MAX-ACCESS read-only
			STATUS current
			DESCRIPTION
			    "Count of the line initialization failed attempts in the current 15 minute interval."
			::= { adslAtucPerfDataEntry 65536 }
		
		-- 1.3.6.1.2.1.10.94.1.1.6.1.65537
		hwAdslAtucPerfCurr1DayFailFullInits OBJECT-TYPE
			SYNTAX Counter32
			MAX-ACCESS read-only
			STATUS current
			DESCRIPTION
			    "Count of the line initialization failed attempts in the day as measured by adslAtucPerfCurr1DayTimeElapsed."
			::= { adslAtucPerfDataEntry 65537 }
		
		-- 1.3.6.1.2.1.10.94.1.1.6.1.65538
		hwAdslAtucPerfPrev1DayFailFullInits OBJECT-TYPE
			SYNTAX Counter32
			MAX-ACCESS read-only
			STATUS current
			DESCRIPTION
			    "Count of the line initialization failed attempts in the most recent previous 1-day period."
			::= { adslAtucPerfDataEntry 65538 }
		
-- adslAtucIntervalTable
		-- 1.3.6.1.2.1.10.94.1.1.8.1.65535
		hwAdslAtucIntervalFailFullInits OBJECT-TYPE
			SYNTAX Counter32
			MAX-ACCESS read-only
			STATUS current
			DESCRIPTION
			    "Count of the line initialization failed attempts during the interval."
			::= { adslAtucIntervalEntry 65535 }
		
-- adslAtucChanPerfDataTable

        hwadslAtucChanRtxCW OBJECT-TYPE
            SYNTAX      Gauge32
            MAX-ACCESS  read-only
            STATUS      current
            DESCRIPTION
                "Count of units request retransmission since agent reset."
            ::= { adslAtucChanPerfDataEntry 65548 }
    
        hwadslAtucChanRtxCorrectedCW OBJECT-TYPE
            SYNTAX      Gauge32
            MAX-ACCESS  read-only
            STATUS      current
            DESCRIPTION
                "Count of units corrected by retransmission since agent reset."
            ::= { adslAtucChanPerfDataEntry 65549 }
    
        hwadslAtucChanRtxUncorrectedCW OBJECT-TYPE
            SYNTAX      Gauge32
            MAX-ACCESS  read-only
            STATUS      current
            DESCRIPTION
                "Count of units uncorrected by retransmission since agent reset."
            ::= { adslAtucChanPerfDataEntry 65550 }
    
        hwadslAtucChanPerfCurr15MinRtxCW OBJECT-TYPE
            SYNTAX      Gauge32
            MAX-ACCESS  read-only
            STATUS      current
            DESCRIPTION
                "Count of units request retransmission on this
                 channel within the current 15 minute interval.
                "
            ::= { adslAtucChanPerfDataEntry 65551 }
    
        hwadslAtucChanPerfCurr15MinRtxCorrectedCW OBJECT-TYPE
            SYNTAX      Gauge32
            MAX-ACCESS  read-only
            STATUS      current
            DESCRIPTION
                "Count of units corrected by retransmission on this
                 channel within the current 15 minute interval.
                "
            ::= { adslAtucChanPerfDataEntry 65552 }
    
        hwadslAtucChanPerfCurr15MinRtxUncorrectedCW OBJECT-TYPE
            SYNTAX      Gauge32
            MAX-ACCESS  read-only
            STATUS      current
            DESCRIPTION
                "Count of units uncorrected by retransmission on
                 this channel within the current 15 minute interval.
                "
            ::= { adslAtucChanPerfDataEntry 65553 }
    
        hwadslAtucChanPerfCurr1DayRtxCW OBJECT-TYPE
            SYNTAX      Gauge32
            MAX-ACCESS  read-only
            STATUS      current
            DESCRIPTION
                "Count of units request retransmission on
                 this channel during the current day.
                "
            ::= { adslAtucChanPerfDataEntry 65554 }
    
        hwadslAtucChanPerfCurr1DayRtxCorrectedCW OBJECT-TYPE
            SYNTAX      Gauge32
            MAX-ACCESS  read-only
            STATUS      current
            DESCRIPTION
                "Count of units corrected by retransmission
                 on this channel during the current day.
                "
            ::= { adslAtucChanPerfDataEntry 65555 }
    
        hwadslAtucChanPerfCurr1DayRtxUncorrectedCW OBJECT-TYPE
            SYNTAX      Gauge32
            MAX-ACCESS  read-only
            STATUS      current
            DESCRIPTION
                "Count of units uncorrected by retransmission
                 on this channel during the current day.
                "
            ::= { adslAtucChanPerfDataEntry 65556 }
    
        hwadslAtucChanPerfPrev1DayRtxCW OBJECT-TYPE
            SYNTAX      Gauge32
            MAX-ACCESS  read-only
            STATUS      current
            DESCRIPTION
                "Count of units request retransmission on this channel
                 within the most recent previous 1-day period.
                "
            ::= { adslAtucChanPerfDataEntry 65557 }
    
        hwadslAtucChanPerfPrev1DayRtxCorrectedCW OBJECT-TYPE
            SYNTAX      Gauge32
            MAX-ACCESS  read-only
            STATUS      current
            DESCRIPTION
                "Count of units corrected by retransmission on this
                 channel within the most recent previous 1-day period.
                "
            ::= { adslAtucChanPerfDataEntry 65558 }
    
        hwadslAtucChanPerfPrev1DayRtxUncorrectedCW OBJECT-TYPE
            SYNTAX      Gauge32
            MAX-ACCESS  read-only
            STATUS      current
            DESCRIPTION
                "Count of units uncorrected by retransmission on this
                 channel within the most recent previous 1-day period.
                "
            ::= { adslAtucChanPerfDataEntry 65559 }

-- adslAturChanPerfDataTable

        hwadslAturChanRtxCW OBJECT-TYPE
            SYNTAX      Gauge32
            MAX-ACCESS  read-only
            STATUS      current
            DESCRIPTION
                "Count of units request retransmission since agent reset."
            ::= { adslAturChanPerfDataEntry 65548 }
    
        hwadslAturChanRtxCorrectedCW OBJECT-TYPE
            SYNTAX      Gauge32
            MAX-ACCESS  read-only
            STATUS      current
            DESCRIPTION
                "Count of units corrected by retransmission since agent reset."
            ::= { adslAturChanPerfDataEntry 65549 }
    
        hwadslAturChanRtxUncorrectedCW OBJECT-TYPE
            SYNTAX      Gauge32
            MAX-ACCESS  read-only
            STATUS      current
            DESCRIPTION
                "Count of units uncorrected by retransmission since agent reset."
            ::= { adslAturChanPerfDataEntry 65550 }
    
        hwadslAturChanPerfCurr15MinRtxCW OBJECT-TYPE
            SYNTAX      Gauge32
            MAX-ACCESS  read-only
            STATUS      current
            DESCRIPTION
                "Count of units request retransmission on this
                 channel within the current 15 minute interval.
                "
            ::= { adslAturChanPerfDataEntry 65551 }
    
        hwadslAturChanPerfCurr15MinRtxCorrectedCW OBJECT-TYPE
            SYNTAX      Gauge32
            MAX-ACCESS  read-only
            STATUS      current
            DESCRIPTION
                "Count of units corrected by retransmission on
                 this channel within the current 15 minute interval.
                "
            ::= { adslAturChanPerfDataEntry 65552 }
    
        hwadslAturChanPerfCurr15MinRtxUncorrectedCW OBJECT-TYPE
            SYNTAX      Gauge32
            MAX-ACCESS  read-only
            STATUS      current
            DESCRIPTION
                "Count of units uncorrected by retransmission on
                 this channel within the current 15 minute interval.
                "
            ::= { adslAturChanPerfDataEntry 65553 }
    
        hwadslAturChanPerfCurr1DayRtxCW OBJECT-TYPE
            SYNTAX      Gauge32
            MAX-ACCESS  read-only
            STATUS      current
            DESCRIPTION
                "Count of units request retransmission on
                 this channel during the current day.
                "
            ::= { adslAturChanPerfDataEntry 65554 }
    
        hwadslAturChanPerfCurr1DayRtxCorrectedCW OBJECT-TYPE
            SYNTAX      Gauge32
            MAX-ACCESS  read-only
            STATUS      current
            DESCRIPTION
                "Count of units corrected by retransmission
                 on this channel during the current day.
                "
            ::= { adslAturChanPerfDataEntry 65555 }
    
        hwadslAturChanPerfCurr1DayRtxUncorrectedCW OBJECT-TYPE
            SYNTAX      Gauge32
            MAX-ACCESS  read-only
            STATUS      current
            DESCRIPTION
                "Count of units uncorrected by retransmission
                 on this channel during the current day.
                "
            ::= { adslAturChanPerfDataEntry 65556 }
    
        hwadslAturChanPerfPrev1DayRtxCW OBJECT-TYPE
            SYNTAX      Gauge32
            MAX-ACCESS  read-only
            STATUS      current
            DESCRIPTION
                "Count of units request retransmission on this
                 channel within the most recent previous 1-day period.
                "
            ::= { adslAturChanPerfDataEntry 65557 }
    
        hwadslAturChanPerfPrev1DayRtxCorrectedCW OBJECT-TYPE
            SYNTAX      Gauge32
            MAX-ACCESS  read-only
            STATUS      current
            DESCRIPTION
                "Count of units corrected by retransmission on this
                 channel within the most recent previous 1-day period.
                "
            ::= { adslAturChanPerfDataEntry 65558 }
    
        hwadslAturChanPerfPrev1DayRtxUncorrectedCW OBJECT-TYPE
            SYNTAX      Gauge32
            MAX-ACCESS  read-only
            STATUS      current
            DESCRIPTION
                "Count of units uncorrected by retransmission on this
                 channel within the most recent previous 1-day period.
                "
            ::= { adslAturChanPerfDataEntry 65559 }

-- adslAtucChanIntervalTable

        hwadslAtucChanIntervalRtxCW OBJECT-TYPE
            SYNTAX      Gauge32
            MAX-ACCESS  read-only
            STATUS      current
            DESCRIPTION
                "Count of units request retransmission on this channel during this interval."
            ::= { adslAtucChanIntervalEntry 65539 }
    
        hwadslAtucChanIntervalRtxCorrectedCW OBJECT-TYPE
            SYNTAX      Gauge32
            MAX-ACCESS  read-only
            STATUS      current
            DESCRIPTION
                "Count of units corrected by retransmission on this channel during this interval."
            ::= { adslAtucChanIntervalEntry 65540 }
    
        hwadslAtucChanIntervalRtxUncorrectedCW OBJECT-TYPE
            SYNTAX      Gauge32
            MAX-ACCESS  read-only
            STATUS      current
            DESCRIPTION
                "Count of units uncorrected by retransmission on this channel during this interval."
            ::= { adslAtucChanIntervalEntry 65541 }
        
-- adslAturChanIntervalTable

        hwadslAturChanIntervalRtxCW OBJECT-TYPE
            SYNTAX      Gauge32
            MAX-ACCESS  read-only
            STATUS      current
            DESCRIPTION
                "Count of units request retransmission on this channel during this interval."
            ::= { adslAturChanIntervalEntry 65539 }
    
        hwadslAturChanIntervalRtxCorrectedCW OBJECT-TYPE
            SYNTAX      Gauge32
            MAX-ACCESS  read-only
            STATUS      current
            DESCRIPTION
                "Count of units corrected by retransmission on this channel during this interval."
            ::= { adslAturChanIntervalEntry 65540 }
    
        hwadslAturChanIntervalRtxUncorrectedCW OBJECT-TYPE
            SYNTAX      Gauge32
            MAX-ACCESS  read-only
            STATUS      current
            DESCRIPTION
                "Count of units uncorrected by retransmission on this channel during this interval."
            ::= { adslAturChanIntervalEntry 65541 }    

--
-- end PHY-R
--
-- hwAdsl2SCStateTable
--
--
		hwAdsl2SCStateTable OBJECT-TYPE 	
			SYNTAX SEQUENCE OF HwAdsl2SCStateEntry
			MAX-ACCESS not-accessible
			STATUS current
			DESCRIPTION
			    "The table adsl2SCStatusTable contains status parameters
                             of the ADSL2 sub-carriers.
                             The indexes of this table are ifIndex and hwAdsl2SCStatusDirection.
			    "
		 ::= { adslMibObjects 65549 }

		hwAdsl2SCStateEntry OBJECT-TYPE
			SYNTAX HwAdsl2SCStateEntry
			MAX-ACCESS not-accessible
			STATUS current
			DESCRIPTION
			    "The table adsl2SCStatusTable contains status parameters
                             of the ADSL2 sub-carriers.
                             The indexes of this entry are ifIndex and hwAdsl2SCStatusDirection.
 	                    "
			INDEX {        
			      ifIndex,
			      hwAdsl2SCStatusDirection 
			      }
			::= { hwAdsl2SCStateTable 1 }

                HwAdsl2SCStateEntry ::=
			SEQUENCE {      
			      hwAdsl2SCStatusDirection       
			            INTEGER,
			      hwAdsl2SCStatusSnr             
			            OCTET STRING,
			      hwAdsl2SCStatusBitsAlloc       
			            OCTET STRING,
			      hwAdsl2SCStatusGainAlloc      
			            OCTET STRING,
			      hwAdsl2SCStatusLog             
			            OCTET STRING, 
			      hwAdsl2SCStatusQln             
			            OCTET STRING,	
			      hwAdsl2SCStatusSnrMargin       
			            OCTET STRING,
			      hwAdsl2SCStatusTxPSD          
			            OCTET STRING
			      }   
			
		hwAdsl2SCStatusDirection  OBJECT-TYPE
                        SYNTAX INTEGER
		        {   
		        	upstream(1),
		        	downstream(2)	
		        }
               MAX-ACCESS  not-accessible
               STATUS      current
               DESCRIPTION
	               "The direction of the sub-carrier is either upstream or downstream.
	                Options: 
                        1. upstream(1)   - Upstream sub-carrier
                        2. downstream(2) - Downstream sub-carrier
                       "
               ::= { hwAdsl2SCStateEntry 1 } 
               
               hwAdsl2SCStatusSnr  OBJECT-TYPE
	               SYNTAX OCTET STRING  (SIZE(0..512))
	               MAX-ACCESS  read-only
	               STATUS      current
	               DESCRIPTION
	                   "The SNR Margin per sub-carrier, expressing the ratio between
	                    the received signal power and received noise power per
	                    subscriber.  It is an array of 512 octets, designed for
	                    supporting up to 512 (downstream) sub-carriers.
	                    The number of utilized octets on downstream direction depends
	                    on NSCds, and on upstream direction it depends on NSCus.  This
	                    value is referred to here as NSC.
	                    Octet i (0 <= i < NSC) is set to a value in the range 0 to
	                    254 to indicate that the respective downstream or upstream sub-
	                    carrier i has SNR of: (-32 + Adsl2SubcarrierSnr(i)/2) in dB
	                    (i.e., -32 to 95dB).
	                    The special value 255 means that no measurement could be done
	                    for the subcarrier because it is out of the PSD mask passband
	                    or that the noise PSD is out of range to be represented.
	                    Each value in this array is 8 bits wide.
	                   "
               ::= { hwAdsl2SCStateEntry 2 }  
               
               hwAdsl2SCStatusBitsAlloc  OBJECT-TYPE
	               SYNTAX OCTET STRING  (SIZE(0..256))
	               MAX-ACCESS  read-only
	               STATUS      current
	               DESCRIPTION
	                   "The bits allocation per sub-carrier.  An array of 256 octets
	                    (512 nibbles), designed for supporting up to 512 (downstream)
	                    sub-carriers.
	                    The number of utilized nibbles on downstream direction depends
	                    on NSCds, and on upstream direction it depends on NSCus.  This
	                    value is referred to here as NSC.
	                    Nibble i (0 <= i < NSC) is set to a value in the range 0
	                    to 15 to indicate that the respective downstream or upstream
	                    sub-carrier i has the same amount of bits allocation.
	                   "
               ::= { hwAdsl2SCStateEntry 3 }  
               
               hwAdsl2SCStatusGainAlloc  OBJECT-TYPE
	               SYNTAX OCTET STRING  (SIZE(0..1024))
	               MAX-ACCESS  read-only
	               STATUS      current
	               DESCRIPTION
	                   "The gain allocation per sub-carrier.  An array of 512 16-bits
	                    values, designed for supporting up to 512 (downstream) sub-
	                    carriers.
	                    The number of utilized octets on downstream direction depends
	                    on NSCds, and on upstream direction it depends on NSCus.  This
	                    value is referred to here as NSC.
	                    Value i (0 <= i < NSC) is in the range 0 to 4093 to indicate
	                    that the respective downstream or upstream sub-carrier i has the
	                    same amount of gain value.
	                    The gain value is represented as a multiple of 1/512 on a
	                    linear scale.  Each value in this array is 16 bits wide and is
	                    stored in big endian format.
	                   "
               ::= { hwAdsl2SCStateEntry 4 }     
               
               hwAdsl2SCStatusLog  OBJECT-TYPE
	               SYNTAX OCTET STRING  (SIZE(0..1024))
	               MAX-ACCESS  read-only
	               STATUS      current
	               DESCRIPTION
	                   "An array of up to 512 real H(f) logarithmic representation
	                    values in dB for the respective transmission direction. It is
	                    designed to support up to 512 (downstream) sub-carriers.
	                    The number of utilized values on downstream direction depends
	                    on NSCds, and on upstream direction it depends on NSCus. This
	                    value is referred to here as NSC.
	                    Each array entry represents the real Hlog(f = i*Df) value for a
	                    particular sub-carrier index i, (0 <= i < NSC).
	                    The real Hlog(f) value is represented as (6-m(i)/10), with m(i)
	                    in the range 0 to 1022.  A special value m=1023 indicates that
	                    no measurement could be done for the subcarrier because it is
	                    out of the passband or that the attenuation is out of range to
	                    be represented.  This parameter is applicable in loop
	                    diagnostic procedure and initialization.
	                    Each value in this array is 16 bits wide and is stored
	                    in big endian format.
	                   "
               ::= { hwAdsl2SCStateEntry 5 }     
               
               hwAdsl2SCStatusQln  OBJECT-TYPE
	               SYNTAX OCTET STRING  (SIZE(0..512))
	               MAX-ACCESS  read-only
	               STATUS      current
	               DESCRIPTION
	                   "An array of up to 512 real Quiet Line Noise values in dBm/Hz
	                    for the respective transmission direction. It is designed for
	                    up to 512 (downstream) sub-carriers.
	                    The number of utilized values on downstream direction depends
	                    on NSCds, and on upstream direction it depends on NSCus. This
	                    value is referred to here as NSC.
	                    Each array entry represents the QLN(f = i*Df) value for a
	                    particular sub-carrier index i, (0 <= i < NSC).
	                    The QLN(f) is represented as ( -23-n(i)/2), with n(i) in the
	                    range 0 to 254.  A special value n(i)=255 indicates that no
	                    measurement could be done for the subcarrier because it is out
	                    of the passband or that the noise PSD is out of range to be
	                    represented.
	                    This parameter is applicable in loop diagnostic procedure and
	                    initialization. Each value in this array is 8 bits wide.
	                   "
               ::= { hwAdsl2SCStateEntry 6 }  
               
               hwAdsl2SCStatusSnrMargin  OBJECT-TYPE
	               SYNTAX OCTET STRING  (SIZE(0..1024))
	               MAX-ACCESS  read-only
	               STATUS      current
	               DESCRIPTION
	                   "SNR Margin is the maximum increase in dB of the noise power
	                    received at the ATU (ATU-R on downstream direction and ATU-C
	                    on upstream direction), such that the BER requirements are met
	                    for all bearer channels received at the ATU.  It ranges from
	                    -640 to 630 units of 0.1 dB (physical values are -64 to
	                    63 dB).
	                   "
               ::= { hwAdsl2SCStateEntry 7 }   
               
               hwAdsl2SCStatusTxPSD  OBJECT-TYPE
	               SYNTAX OCTET STRING  (SIZE(0..1024))
	               MAX-ACCESS  read-only
	               STATUS      current
	               DESCRIPTION
	                   "The PSD MASK per sub-carrier.An array of 512 16-bits
 	                    values, designed for supporting up to 512 (downstream) sub-carriers. 
 	                    It ranges from -1400 to -300 units of 0.1 dBm/Hz (physical values
 	                    are -140 to -30 dBm/Hz).
 	                   "
               ::= { hwAdsl2SCStateEntry 8 }

--hwxdslDynamicProfTable
--
--
    hwxdslDynamicProfTable   OBJECT-TYPE
         SYNTAX          SEQUENCE OF HwxdslDynamicProfEntry
         MAX-ACCESS      not-accessible
         STATUS          current
         DESCRIPTION
             "This table includes common parameters of the xdsl Dynamic profile.
              The index of this table is hwxdslDynamicProfProfileName.
             "
         ::= { adslMibObjects 65550  }
            
    hwxdslDynamicProfEntry   OBJECT-TYPE
             SYNTAX          HwxdslDynamicProfEntry
             MAX-ACCESS      not-accessible
             STATUS          current
             DESCRIPTION     
                 "This table includes common parameters of the xdsl Dynamic profile.
                  The index of this entry is hwxdslDynamicProfProfileName.
                 "
             INDEX           {  hwxdslDynamicProfProfileName }
         ::= { hwxdslDynamicProfTable 1 }
         
    HwxdslDynamicProfEntry ::=
             SEQUENCE {
             hwxdslDynamicProfProfileName           OCTET STRING,
             hwxdslDynamicProfXtuTransSysEna        BITS,
             hwxdslDynamicProfBitSwapDS             INTEGER,
             hwxdslDynamicProfBitSwapUS             INTEGER,
             hwxdslDynamicProfTargetSnrmDs          Unsigned32,
             hwxdslDynamicProfTargetSnrmUs          Unsigned32,  
             hwxdslDynamicProfMaxSnrmDs             Unsigned32,
             hwxdslDynamicProfMaxSnrmUs             Unsigned32,
             hwxdslDynamicProfMinSnrmDs             Unsigned32,
             hwxdslDynamicProfMinSnrmUs             Unsigned32,             
             hwxdslDynamicProfCh1MinProtectionDs    INTEGER,
             hwxdslDynamicProfCh1MinProtectionUs    INTEGER,
             hwxdslDynamicProfCh1MaxDelayDs         Unsigned32,
             hwxdslDynamicProfCh1MaxDelayUs         Unsigned32,
             hwxdslDynamicProfCh2MinProtectionDs    INTEGER,
             hwxdslDynamicProfCh2MinProtectionUs    INTEGER,
             hwxdslDynamicProfCh2MaxDelayDs         Unsigned32,
             hwxdslDynamicProfCh2MaxDelayUs         Unsigned32,
             hwxdslDynamicProfPmMode                BITS,
             hwxdslDynamicProfL0Time                Unsigned32,
             hwxdslDynamicProfL2Time                Unsigned32,
             hwxdslDynamicProfL2Atpr                Unsigned32,
             hwxdslDynamicProfL2Atprt               Unsigned32,
             hwxdslDynamicProfDpboEPsd              OCTET STRING,
             hwxdslDynamicProfDpboEsEL              Unsigned32,
             hwxdslDynamicProfDpboEscm              OCTET STRING,
             hwxdslDynamicProfDpboMus               Unsigned32,
             hwxdslDynamicProfDpboFMin              Unsigned32,
             hwxdslDynamicProfDpboFMax              Unsigned32,
             hwxdslDynamicProfUpboPsdBand           OCTET STRING,
             hwxdslDynamicProfUpboKLF               INTEGER,
             hwxdslDynamicProfUpboKL                Unsigned32,
             hwxdslDynamicProfRfiBands              OCTET STRING,
             hwxdslDynamicProfToneBlackOut          OCTET STRING,
             hwxdslDynamicProfCarMaskDS             OCTET STRING,
             hwxdslDynamicProfCarMaskUS             OCTET STRING,
             hwxdslDynamicProfXdslMode              INTEGER,
             hwxdslDynamicProfMaxNomPsdDs           Integer32,
             hwxdslDynamicProfMaxNomPsdUs           Integer32,
             hwxdslDynamicProfMaxNomAtpDs           Unsigned32,
             hwxdslDynamicProfMaxNomAtpUs           Unsigned32,
             hwxdslDynamicProfPsdMaskDs             OCTET STRING,
             hwxdslDynamicProfPsdMaskUs             OCTET STRING,
             hwxdslDynamicProfLimitMask             INTEGER,
             hwxdslDynamicProfClassMask             INTEGER,             
             hwxdslDynamicProfBandOptUsage            INTEGER,
             hwxdslDynamicProfVirtualNoiseModeDs    INTEGER,
             hwxdslDynamicProfVirtualNoiseModeUs    INTEGER,
             hwxdslDynamicProfVirtualNoiseDs        OCTET STRING,
             hwxdslDynamicProfVirtualNoiseUs        OCTET STRING,
             hwxdslDynamicProfRowStatus             RowStatus             
             }
             
    hwxdslDynamicProfProfileName OBJECT-TYPE
             SYNTAX      OCTET STRING(SIZE(1..32))
             MAX-ACCESS  not-accessible
             STATUS      current
             DESCRIPTION
                 "The name of xdsl Dynamic Profile."
         ::= { hwxdslDynamicProfEntry 1 }
         
    hwxdslDynamicProfXtuTransSysEna OBJECT-TYPE
             SYNTAX   BITS {
				                     ansit1413(0),
				                     etsi(1),
				                     g9921PotsNonOverlapped(2),
				                     g9921PotsOverlapped(3),
				                     g9921IsdnNonOverlapped(4),
				                     g9921isdnOverlapped(5),
				                     g9921tcmIsdnNonOverlapped(6),
				                     g9921tcmIsdnOverlapped(7),
				                     g9922potsNonOverlapped(8),
				                     g9922potsOverlapped(9),
				                     g9922tcmIsdnNonOverlapped(10),
				                     g9922tcmIsdnOverlapped(11),
				                     g9921tcmIsdnSymmetric(12),
				                     reserved1(13),
				                     reserved2(14),
				                     reserved3(15),
				                     reserved4(16),
				                     reserved5(17),
				                     g9923PotsNonOverlapped(18),
				                     g9923PotsOverlapped(19),
				                     g9923IsdnNonOverlapped(20),
				                     g9923isdnOverlapped(21),
				                     reserved6(22),
				                     reserved7(23),
				                     g9924potsNonOverlapped(24),
				                     g9924potsOverlapped(25),
				                     reserved8(26),
				                     reserved9(27),
				                     g9923AnnexIAllDigNonOverlapped(28),
				                     g9923AnnexIAllDigOverlapped(29),
				                     g9923AnnexJAllDigNonOverlapped(30),
				                     g9923AnnexJAllDigOverlapped(31),
				                     g9924AnnexIAllDigNonOverlapped(32),
				                     g9924AnnexIAllDigOverlapped(33),
				                     g9923AnnexLMode1NonOverlapped(34),
				                     g9923AnnexLMode2NonOverlapped(35),
				                     g9923AnnexLMode3Overlapped(36),
				                     g9923AnnexLMode4Overlapped(37),
				                     g9923AnnexMPotsNonOverlapped(38),
				                     g9923AnnexMPotsOverlapped(39),
				                     g9925PotsNonOverlapped(40),
				                     g9925PotsOverlapped(41),
				                     g9925IsdnNonOverlapped(42),
				                     g9925isdnOverlapped(43),
				                     reserved10(44),
				                     reserved11(45),
				                     g9925AnnexIAllDigNonOverlapped(46),
				                     g9925AnnexIAllDigOverlapped(47),
				                     g9925AnnexJAllDigNonOverlapped(48),
				                     g9925AnnexJAllDigOverlapped(49),
				                     g9925AnnexMPotsNonOverlapped(50),
				                     g9925AnnexMPotsOverlapped(51),
				                     reserved12(52),
				                     reserved13(53),
				                     reserved14(54),
				                     reserved15(55),
				                     reserved16(56),
				                     reserved17(57),
				                     reserved18(58),
				                     reserved19(59),
				                     reserved20(60),
				                     reserved21(61),
				                     reserved22(62),
				                     reserved23(63),
						     reserved24(64),
						     reserved25(65),
						     reserved26(66),
						     reserved27(67),
						     reserved28(68),
						     reserved29(69),
						     reserved30(70),
						     reserved31(71),
						     g9932AnnexAPots(72),
						     g9932AnnexAIsdn(73),
						     g9932AnnexBPots(74),
						     g9932AnnexBIsdn(75),
						     g9932AnnexCPots(76),
						     g9932AnnexCIsdn(77),
						     reserved32(78),
						     reserved33(79)
				                  }     				                  
		     MAX-ACCESS  read-create
             STATUS      current
             DESCRIPTION
                 "Xtu Transmission System Enabling (ATSE). A list of the
 	          different coding types enabled in this profile. It is coded
 	          in a bit-map representation with 1 or more bits set. A bit
 	          set to '1' means that the XTUs may apply the respective
 	          coding for the XDSL line. A bit set to '0' means that
 	          the XTUs cannot apply the respective coding for the XDSL
 	          line. All 'reserved' bits should be set to '0'.
                 "
         ::= { hwxdslDynamicProfEntry 2 }
         
    hwxdslDynamicProfBitSwapDS OBJECT-TYPE
             SYNTAX      INTEGER {
             disable(1),
             enable(2),
             invalidValue(-1)
             }
             MAX-ACCESS  read-create
             STATUS      current
             DESCRIPTION
                 "Enables or disables the bit swap downstream of a line.
                  Options: 
                  1. disable(1)       - The bit swap downstream of a line is disabled
                  2. enable(2)        - The bit swap downstream of a line is enabled
                  3. invalidValue(-1) - Invalid value 
                 "
         ::= { hwxdslDynamicProfEntry 3 }
         
    hwxdslDynamicProfBitSwapUS OBJECT-TYPE
             SYNTAX      INTEGER {
             disable(1),
             enable(2),
             invalidValue(-1)             
             }
             MAX-ACCESS  read-create
             STATUS      current
             DESCRIPTION
                 "Enables or disables the bit swap upstream of a line.
                  Options: 
                  1. disable(1)       - The bit swap upstream of a line is disabled
                  2. enable(2)        - The bit swap upstream of a line is enabled
                  3. invalidValue(-1) - Invalid value
                 "
         ::= { hwxdslDynamicProfEntry 4 }
         
    hwxdslDynamicProfTargetSnrmDs OBJECT-TYPE
             SYNTAX      Unsigned32(0..310)
             UNITS       "0.1 dB"
             MAX-ACCESS  read-create
             STATUS      current
             DESCRIPTION
                 "The target Noise Margin the xTU-R receiver shall achieve,
                  relative to the BER requirement for each of the downstream
                  bearer channels, to successfully complete initialization.
                  The target noise margin ranges from 0 to 310 units of 0.1 dB
                  (Physical values are 0 to 31 dB). The invalid value is 65535. 
                  If data is invalid, the invalid value will be returned.
                  Range: 0-310
                  Unit: 0.1 dB
                 "
         ::= { hwxdslDynamicProfEntry 5 }
         
    hwxdslDynamicProfTargetSnrmUs OBJECT-TYPE
             SYNTAX      Unsigned32(0..310)
             UNITS       "0.1 dB"
             MAX-ACCESS  read-create
             STATUS      current
             DESCRIPTION
                 "The target Noise Margin the xTU-C receiver shall achieve,
                  relative to the BER requirement for each of the downstream
                  bearer channels, to successfully complete initialization.
                  The target noise margin ranges from 0 to 310 units of 0.1 dB
                  (Physical values are 0 to 31 dB). The invalid value is 65535. 
                  If data is invalid, the invalid value will be returned.
                  Range: 0-310
                  Unit: 0.1 dB
                 "
         ::= { hwxdslDynamicProfEntry 6 }
         
    hwxdslDynamicProfMaxSnrmDs OBJECT-TYPE
             SYNTAX      Unsigned32(0..310)
             UNITS       "0.1 dB"
             MAX-ACCESS  read-create
             STATUS      current
             DESCRIPTION
                 "The maximum Noise Margin the xTU-R receiver shall achieve,
                  relative to the BER requirement for each of the downstream
                  bearer channels, to successfully complete initialization.
                  The target noise margin ranges from 0 to 310 units of 0.1 dB
                  (Physical values are 0 to 31 dB). The invalid value is 65535. 
                  If data is invalid, the invalid value will be returned.
                  Range: 0-310
                  Unit: 0.1 dB
                 "
         ::= { hwxdslDynamicProfEntry 7 }
         
    hwxdslDynamicProfMaxSnrmUs OBJECT-TYPE
             SYNTAX      Unsigned32(0..310)
             UNITS       "0.1 dB"
             MAX-ACCESS  read-create
             STATUS      current
             DESCRIPTION
                 "The maximum Noise Margin the xTU-C receiver shall achieve,
                  relative to the BER requirement for each of the downstream
                  bearer channels, to successfully complete initialization.
                  The target noise margin ranges from 0 to 310 units of 0.1 dB
                  (Physical values are 0 to 31 dB). The invalid value is 65535. 
                  If data is invalid, the invalid value will be returned.
                  Range: 0-310
                  Unit: 0.1 dB
                 "
         ::= { hwxdslDynamicProfEntry 8 }       
           
    hwxdslDynamicProfMinSnrmDs OBJECT-TYPE
             SYNTAX      Unsigned32(0..310)
             UNITS       "0.1 dB"
             MAX-ACCESS  read-create
             STATUS      current
             DESCRIPTION
                 "The minimum Noise Margin the xTU-R receiver shall achieve,
                  relative to the BER requirement for each of the downstream
                  bearer channels, to successfully complete initialization.
                  The target noise margin ranges from 0 to 310 units of 0.1 dB
                  (Physical values are 0 to 31 dB). The invalid value is 65535. 
                  If data is invalid, the invalid value will be returned.
                  Range: 0-310
                  Unit: 0.1 dB
                 "
         ::= { hwxdslDynamicProfEntry 9 }                      
         
    hwxdslDynamicProfMinSnrmUs OBJECT-TYPE
             SYNTAX      Unsigned32(0..310)
             UNITS       "0.1 dB"
             MAX-ACCESS  read-create
             STATUS      current
             DESCRIPTION
                 "The minimum Noise Margin the xTU-C receiver shall achieve,
                  relative to the BER requirement for each of the downstream
                  bearer channels, to successfully complete initialization.
                  The target noise margin ranges from 0 to 310 units of 0.1 dB
                  (Physical values are 0 to 31 dB). The invalid value is 65535. 
                  If data is invalid, the invalid value will be returned.
                  Range: 0-310
                  Unit: 0.1 dB
                 "
         ::= { hwxdslDynamicProfEntry 10 }         
        
    hwxdslDynamicProfCh1MinProtectionDs OBJECT-TYPE
             SYNTAX      INTEGER {
                          noProtection (1),
                          halfSymbol (2),
                          singleSymbol (3),
                          twoSymbols (4),
                          threeSymbols (5),
                          fourSymbols (6),
                          fiveSymbols (7),
                          sixSymbols (8),
                          sevenSymbols (9),
                          eightSymbols (10),
                          nineSymbols (11),
                          tenSymbols (12),
                          elevenSymbols (13),
                          twelveSymbols (14),
                          thirteenSymbols (15),
                          fourteenSymbols (16),
                          fifteenSymbols (17),
                          sixteenSymbols (18),
                          invalidValue(-1)         
                        }             
             MAX-ACCESS  read-create
             STATUS      current
             DESCRIPTION
                 "Minimum Impulse Noise Protection on Downstream direction. The
                  minimum impulse noise protection for the bearer channel,
                  expressed in symbols. The parameter can take the following
                  values: noProtection (i.e., INP not required), halfSymbol
                  (i.e., INP length is 1/2 symbol) and 1-16 symbols in steps
                  of 1 symbol.
                  Options: 
                  1. noProtection (1)      - Indicates that the INP value is 0
                  2. halfSymbol (2)        - Indicates that the INP value is 0.5
                  3. singleSymbol (3)      - Indicates that the INP value is 1
                  4. twoSymbols (4)        - Indicates that the INP value is 2
                  5. threeSymbols (5)      - Indicates that the INP value is 3
                  6. fourSymbols (6)       - Indicates that the INP value is 4
                  7. fiveSymbols (7)       - Indicates that the INP value is 5
                  8. sixSymbols (8)        - Indicates that the INP value is 6
                  9. sevenSymbols (9)      - Indicates that the INP value is 7
                  10. eightSymbols (10)    - Indicates that the INP value is 8
                  11. nineSymbols (11)     - Indicates that the INP value is 9
                  12. tenSymbols (12)      - Indicates that the INP value is 10
                  13. elevenSymbols (13)   - Indicates that the INP value is 11
                  14. twelveSymbols (14)   - Indicates that the INP value is 12
                  15. thirteenSymbols (15) - Indicates that the INP value is 13
                  16. fourteenSymbols (16) - Indicates that the INP value is 14
                  17. fifteenSymbols (17)  - Indicates that the INP value is 15
                  18. sixteenSymbols (18)  - Indicates that the INP value is 16
                  19. invalidValue(-1)     - Invalid value
                 "
             REFERENCE    "ITU-T G.997.1, paragraph 7.3.2.3"
         ::= { hwxdslDynamicProfEntry 11 }
         
     hwxdslDynamicProfCh1MinProtectionUs OBJECT-TYPE
             SYNTAX      INTEGER {
                          noProtection (1),
                          halfSymbol (2),
                          singleSymbol (3),
                          twoSymbols (4),
                          threeSymbols (5),
                          fourSymbols (6),
                          fiveSymbols (7),
                          sixSymbols (8),
                          sevenSymbols (9),
                          eightSymbols (10),
                          nineSymbols (11),
                          tenSymbols (12),
                          elevenSymbols (13),
                          twelveSymbols (14),
                          thirteenSymbols (15),
                          fourteenSymbols (16),
                          fifteenSymbols (17),
                          sixteenSymbols (18),
                          invalidValue(-1)
                        }             
             MAX-ACCESS  read-create
             STATUS      current
             DESCRIPTION
                 "Minimum Impulse Noise Protection on Upstream direction. The
                  minimum impulse noise protection for the bearer channel,
                  expressed in symbols. The parameter can take the following
                  values: noProtection (i.e., INP not required), halfSymbol
                  (i.e., INP length is 1/2 symbol) and 1-16 symbols in steps
                  of 1 symbol.
                  Options: 
                  1. noProtection (1)      - Indicates that the INP value is 0
                  2. halfSymbol (2)        - Indicates that the INP value is 0.5
                  3. singleSymbol (3)      - Indicates that the INP value is 1
                  4. twoSymbols (4)        - Indicates that the INP value is 2
                  5. threeSymbols (5)      - Indicates that the INP value is 3
                  6. fourSymbols (6)       - Indicates that the INP value is 4
                  7. fiveSymbols (7)       - Indicates that the INP value is 5
                  8. sixSymbols (8)        - Indicates that the INP value is 6
                  9. sevenSymbols (9)      - Indicates that the INP value is 7
                  10. eightSymbols (10)    - Indicates that the INP value is 8
                  11. nineSymbols (11)     - Indicates that the INP value is 9
                  12. tenSymbols (12)      - Indicates that the INP value is 10
                  13. elevenSymbols (13)   - Indicates that the INP value is 11
                  14. twelveSymbols (14)   - Indicates that the INP value is 12
                  15. thirteenSymbols (15) - Indicates that the INP value is 13
                  16. fourteenSymbols (16) - Indicates that the INP value is 14
                  17. fifteenSymbols (17)  - Indicates that the INP value is 15
                  18. sixteenSymbols (18)  - Indicates that the INP value is 16
                  19. invalidValue(-1)     - Invalid value
                 "
             REFERENCE    "ITU-T G.997.1, paragraph 7.3.2.3"
         ::= { hwxdslDynamicProfEntry 12 }
         
     hwxdslDynamicProfCh1MaxDelayDs OBJECT-TYPE
             SYNTAX      Unsigned32(0..200)
             UNITS       "milliseconds"
             MAX-ACCESS  read-create
             STATUS      current
             DESCRIPTION
                 "Maximum Interleave Delay on Downstream direction. The maximum
                  one-way interleaving delay introduced by the PMS-TC on
                  Downstream direction. The XTUs shall choose the S (factor) and
                  D (depth) values such that the actual one-way interleaving
                  delay is as close as possible to, but less than or equal to, 
                  hwxdslDynamicProfCh1MaxDelayDs. The delay is coded in ms, 
                  with the value 0 indicating no delay bound is being imposed.
                  The invalid value is 65535. If data is invalid, the invalid value 
                  will be returned.
                  Range: 0-200
                  Unit: milliseconds
                 "
             REFERENCE    "ITU-T G.997.1, paragraph 7.3.2.2"
         ::= { hwxdslDynamicProfEntry 13 }
         
     hwxdslDynamicProfCh1MaxDelayUs OBJECT-TYPE
             SYNTAX      Unsigned32(0..200)
             UNITS       "milliseconds"
             MAX-ACCESS  read-create
             STATUS      current
             DESCRIPTION
                 "Maximum Interleave Delay on Upstream direction. The maximum
                  one-way interleaving delay introduced by the PMS-TC on
                  Upstream direction. The XTUs shall choose the S (factor) and
                  D (depth) values such that the actual one-way interleaving
                  delay is as close as possible to, but less than or equal to, 
                  hwxdslDynamicProfCh1MaxDelayUs. The delay is coded in ms, 
                  with the value 0 indicating no delay bound is being imposed.
                  The invalid value is 65535. If data is invalid, the invalid value 
                  will be returned.
                  Range: 0-200
                  Unit: milliseconds
                 "
             REFERENCE    "ITU-T G.997.1, paragraph 7.3.2.2"
         ::= { hwxdslDynamicProfEntry 14 }
                  
     hwxdslDynamicProfCh2MinProtectionDs OBJECT-TYPE
             SYNTAX      INTEGER {
                          noProtection (1),
                          halfSymbol (2),
                          singleSymbol (3),
                          twoSymbols (4),
                          threeSymbols (5),
                          fourSymbols (6),
                          fiveSymbols (7),
                          sixSymbols (8),
                          sevenSymbols (9),
                          eightSymbols (10),
                          nineSymbols (11),
                          tenSymbols (12),
                          elevenSymbols (13),
                          twelveSymbols (14),
                          thirteenSymbols (15),
                          fourteenSymbols (16),
                          fifteenSymbols (17),
                          sixteenSymbols (18),
                          invalidValue(-1)        
                        }             
             MAX-ACCESS  read-create
             STATUS      current
             DESCRIPTION
                 "Minimum Impulse Noise Protection on Downstream direction. The
                  minimum impulse noise protection for the bearer channel,
                  expressed in symbols. The parameter can take the following
                  values: noProtection (i.e., INP not required), halfSymbol
                  (i.e., INP length is 1/2 symbol) and 1-16 symbols in steps
                  of 1 symbol.
                  Options: 
                  1. noProtection (1)      - Indicates that the INP value is 0
                  2. halfSymbol (2)        - Indicates that the INP value is 0.5
                  3. singleSymbol (3)      - Indicates that the INP value is 1
                  4. twoSymbols (4)        - Indicates that the INP value is 2
                  5. threeSymbols (5)      - Indicates that the INP value is 3
                  6. fourSymbols (6)       - Indicates that the INP value is 4
                  7. fiveSymbols (7)       - Indicates that the INP value is 5
                  8. sixSymbols (8)        - Indicates that the INP value is 6
                  9. sevenSymbols (9)      - Indicates that the INP value is 7
                  10. eightSymbols (10)    - Indicates that the INP value is 8
                  11. nineSymbols (11)     - Indicates that the INP value is 9
                  12. tenSymbols (12)      - Indicates that the INP value is 10
                  13. elevenSymbols (13)   - Indicates that the INP value is 11
                  14. twelveSymbols (14)   - Indicates that the INP value is 12
                  15. thirteenSymbols (15) - Indicates that the INP value is 13
                  16. fourteenSymbols (16) - Indicates that the INP value is 14
                  17. fifteenSymbols (17)  - Indicates that the INP value is 15
                  18. sixteenSymbols (18)  - Indicates that the INP value is 16
                  19. invalidValue(-1)     - Invalid value
                 "
             REFERENCE    "ITU-T G.997.1, paragraph 7.3.2.3"
         ::= { hwxdslDynamicProfEntry 15 }
         
     hwxdslDynamicProfCh2MinProtectionUs OBJECT-TYPE
             SYNTAX      INTEGER {
                          noProtection (1),
                          halfSymbol (2),
                          singleSymbol (3),
                          twoSymbols (4),
                          threeSymbols (5),
                          fourSymbols (6),
                          fiveSymbols (7),
                          sixSymbols (8),
                          sevenSymbols (9),
                          eightSymbols (10),
                          nineSymbols (11),
                          tenSymbols (12),
                          elevenSymbols (13),
                          twelveSymbols (14),
                          thirteenSymbols (15),
                          fourteenSymbols (16),
                          fifteenSymbols (17),
                          sixteenSymbols (18),
                          invalidValue(-1)
                        }             
             MAX-ACCESS  read-create
             STATUS      current
             DESCRIPTION
                 "Minimum Impulse Noise Protection on Upstream direction. The
                  minimum impulse noise protection for the bearer channel,
                  expressed in symbols. The parameter can take the following
                  values: noProtection (i.e., INP not required), halfSymbol
                  (i.e., INP length is 1/2 symbol) and 1-16 symbols in steps
                  of 1 symbol.
                  Options: 
                  1. noProtection (1)      - Indicates that the INP value is 0
                  2. halfSymbol (2)        - Indicates that the INP value is 0.5
                  3. singleSymbol (3)      - Indicates that the INP value is 1
                  4. twoSymbols (4)        - Indicates that the INP value is 2
                  5. threeSymbols (5)      - Indicates that the INP value is 3
                  6. fourSymbols (6)       - Indicates that the INP value is 4
                  7. fiveSymbols (7)       - Indicates that the INP value is 5
                  8. sixSymbols (8)        - Indicates that the INP value is 6
                  9. sevenSymbols (9)      - Indicates that the INP value is 7
                  10. eightSymbols (10)    - Indicates that the INP value is 8
                  11. nineSymbols (11)     - Indicates that the INP value is 9
                  12. tenSymbols (12)      - Indicates that the INP value is 10
                  13. elevenSymbols (13)   - Indicates that the INP value is 11
                  14. twelveSymbols (14)   - Indicates that the INP value is 12
                  15. thirteenSymbols (15) - Indicates that the INP value is 13
                  16. fourteenSymbols (16) - Indicates that the INP value is 14
                  17. fifteenSymbols (17)  - Indicates that the INP value is 15
                  18. sixteenSymbols (18)  - Indicates that the INP value is 16
                  19. invalidValue(-1)     - Invalid value
                 "
             REFERENCE    "ITU-T G.997.1, paragraph 7.3.2.3"
         ::= { hwxdslDynamicProfEntry 16 }

     hwxdslDynamicProfCh2MaxDelayDs OBJECT-TYPE
             SYNTAX      Unsigned32(0..200)
             UNITS       "milliseconds"
             MAX-ACCESS  read-create
             STATUS      current
             DESCRIPTION
                 "Maximum Interleave Delay on Downstream direction. The maximum
                  one-way interleaving delay introduced by the PMS-TC on
                  Downstream direction. The XTUs shall choose the S (factor) and
                  D (depth) values such that the actual one-way interleaving
                  delay is as close as possible to, but less than or equal to, 
                  hwxdslDynamicProfCh2MaxDelayDs. The delay is coded in ms, 
                  with the value 0 indicating no delay bound is being imposed.
                  The invalid value is 65535. If data is invalid, the invalid value
                  will be returned.
                  Range: 0-200
                  Unit: milliseconds
                 "
             REFERENCE    "ITU-T G.997.1, paragraph 7.3.2.2"
         ::= { hwxdslDynamicProfEntry 17 }
         
     hwxdslDynamicProfCh2MaxDelayUs OBJECT-TYPE
             SYNTAX      Unsigned32(0..200)
             UNITS       "milliseconds"
             MAX-ACCESS  read-create
             STATUS      current
             DESCRIPTION
                 "Maximum Interleave Delay on Upstream direction. The maximum
                  one-way interleaving delay introduced by the PMS-TC on
                  Upstream direction. The XTUs shall choose the S (factor) and
                  D (depth) values such that the actual one-way interleaving
                  delay is as close as possible to, but less than or equal to, 
                  hwxdslDynamicProfCh2MaxDelayUs. The delay is coded in ms, 
                  with the value 0 indicating no delay bound is being imposed.
                  The invalid value is 65535. If data is invalid, the invalid 
                  value will be returned.
                  Range: 0-200
                  Unit: milliseconds
                 "
             REFERENCE    "ITU-T G.997.1, paragraph 7.3.2.2"
         ::= { hwxdslDynamicProfEntry 18 }
         
     hwxdslDynamicProfPmMode OBJECT-TYPE
             SYNTAX BITS {
                              allowTransitionsToIdle(0),
                              allowTransitionsToLowPower(1)
                         }
             MAX-ACCESS  read-create
             STATUS      current
             DESCRIPTION
                 "Power management state Enabling. Defines the power states the
                  xTU-C or xTU-R may autonomously transition to on this line.
                  The various bit positions are: allowTransitionsToIdle (0) and
                  allowTransitionsToLowPower (1). A bit with a '1' value means
                  that the xTU is allowed to transit into the respective state
                  and a '0' value means that the xTU is not allowed
                  to transit into the respective state.
                 "
             REFERENCE    "ITU-T G.997.1, paragraph 7.3.1.1.4"
         ::= { hwxdslDynamicProfEntry 19 }
         
    hwxdslDynamicProfL0Time OBJECT-TYPE
             SYNTAX Unsigned32 (0..255)
             MAX-ACCESS  read-create
             STATUS      current
             DESCRIPTION
                 "This minimum time (in seconds) between an Exit from the L2
                  state and the next Entry into the L2 state. It ranges from 0
                  to 255 seconds. The invalid value is 65535. If data is invalid,
                  the invalid value will be returned.
                  Range: 0-255
                 "
             REFERENCE    "ITU-T G.997.1, paragraph 7.3.1.1.5"
         ::= { hwxdslDynamicProfEntry 20 }
         
    hwxdslDynamicProfL2Time OBJECT-TYPE
             SYNTAX Unsigned32 (0..255)
             MAX-ACCESS  read-create
             STATUS      current
             DESCRIPTION
                 "This minimum time (in seconds) between an Entry into the
                  L2 state and the first Power Trim in the L2 state and between
                  two consecutive Power Trims in the L2 State.
                  It ranges from 0 to 255 seconds. The invalid value is 65535.
                  If data is invalid, the invalid value will be returned.
                  Range: 0-255
                 "
             REFERENCE    "ITU-T G.997.1, paragraph 7.3.1.1.6"
         ::= { hwxdslDynamicProfEntry 21 }
         
     hwxdslDynamicProfL2Atpr  OBJECT-TYPE
            SYNTAX      Unsigned32 (0..31)
            UNITS       "dB"
            MAX-ACCESS  read-create
            STATUS      current
            DESCRIPTION
                "The maximum aggregate transmit power reduction (in dB) that
                 can be performed at transition of L0 to L2 state or through a
                 single Power Trim in the L2 state.
                 It ranges from 0 dB to 31 dB. The invalid value is 255.
                 If data is invalid, the invalid value will be returned.
                 Range: 0-31
                 Unit: dB
                "
            REFERENCE    "ITU-T G.997.1 (amendment 1), 7.3.1.1.7"
         ::= { hwxdslDynamicProfEntry 22 }

     hwxdslDynamicProfL2Atprt  OBJECT-TYPE
            SYNTAX      Unsigned32 (0..31)
            UNITS       "dB"
            MAX-ACCESS  read-create
            STATUS      current
            DESCRIPTION
                "The total maximum aggregate transmit power reduction
                 (in dB) that can be performed in an L2 state. This is the
                 sum of all reductions of L2 Request (i.e., at transition of
                 L0 to L2 state) and Power Trims. The invalid value is 255. 
                 If data is invalid, the invalid value will be returned.
                 Range: 0-31
                 Unit: dB
                "
            REFERENCE    "ITU-T G.997.1 (amendment 1), 7.3.1.1.9"
         ::= { hwxdslDynamicProfEntry 23 }    
         
     hwxdslDynamicProfDpboEPsd  OBJECT-TYPE
            SYNTAX      OCTET STRING (SIZE(0..48))
            MAX-ACCESS  read-create
            STATUS      current
            DESCRIPTION
                "This parameter defines the PSD mask that is assumed to be permitted at the exchange. 
                 This parameter shall use the same format as PSDMASKds. The maximum number of breakpoints 
                 for DPBOEPSD is 16.
                 This is a string of 16 pairs of values in the following
                 structure:
                 Octets 0+1 - Index of 1st sub-carrier used in the context
                              of a first breakpoint.
                 Octet 2    - The PSD reduction for the sub-carrier indicated in
                              octets 0 and 1.
                 Octets 3-5 - Same, for a 2nd breakpoint.
                 Octets 6-8 - Same, for a 3rd breakpoint.
                 This architecture continues until octets 45-47, which are
                 associated with a 16th breakpoint.
                 Each subcarrier index is an unsigned number in the range 1 and
                 NSCds.  Each PSD reduction value is in the range 0 (0dBm/Hz) to
                 255 (-127.5dBm/Hz) with steps of 0.5dBm/Hz. Valid values are
                 in the range 0 to 190 (0 to -95dBm/Hz).
                 When the number of breakpoints is less than 16, all remaining
                 octets are set to the value 0xff. 
                "
            REFERENCE    "ITU-T G.997.1(200604), paragraph 7.3.1.2.13"         
         ::= { hwxdslDynamicProfEntry 24 }     
         
     hwxdslDynamicProfDpboEsEL  OBJECT-TYPE
            SYNTAX      Unsigned32 (0..511)
            UNITS       "0.5dB"
            MAX-ACCESS  read-create
            STATUS      current
            DESCRIPTION
                "This configuration parameter defines the assumed electrical length of 
                 cables (E-side cables) connecting exchange based DSL services to a remote
                 flexibility point (cabinet), that hosts the xTU-C that is subject to 
                 spectrally shaped downstream power back-off depending on this length. 
                 For this parameter the electrical length is defined as the loss (in dB) 
                 of an equivalent length of hypothetical cable at a reference frequency 
                 defined by the network operator or in spectrum management regulations. 
                 DPBOESEL shall be coded as an unsigned integer representing an electrical 
                 length from 0 dB (coded as 0) to 255.5 dB (coded as 511) in steps of 0.5 dB. 
                 All values in the range are valid. The invalid value is 65535. If data is 
                 invalid, the invalid value will be returned. If DPBOESEL is set to zero, 
                 the DPBO in this section shall be disabled.
                 Range: 0-511
                 Unit: 0.5dB
                "
            REFERENCE    "ITU-T G.997.1(200604), paragraph 7.3.1.2.13"
         ::= { hwxdslDynamicProfEntry 25 }        
      
    hwxdslDynamicProfDpboEscm  OBJECT-TYPE
            SYNTAX      OCTET STRING (SIZE(0..6)) 
            MAX-ACCESS  read-create
            STATUS      current
            DESCRIPTION
                "This configuration parameter defines a cable model in terms of three scalars 
                 DPBOESCMA, DPBOESCMB and DPBOESCMC that shall be used to describe the frequency
                 dependent loss of E-side cables.Parameters DPBOESCMA, DPBOESCMB, DPBOESCMC shall be
                 coded as unsigned integers representing a scalar value from -1 (coded as 0) to 1.5 
                 (coded as 640) in step of 1/256. All values in the range are valid.
                 Octets 0+1 DPBOESCMA
        	 Octets 2+3 DPBOESCMB
                 Octets 4+5 DPBOESCMC
                "
             REFERENCE    "ITU-T G.997.1(200604), paragraph 7.3.1.2.13"          
         ::= { hwxdslDynamicProfEntry 26 }      
         
     hwxdslDynamicProfDpboMus  OBJECT-TYPE
            SYNTAX      Unsigned32 (0..255)
            UNITS       "0.5dBm/Hz"
            MAX-ACCESS  read-create
            STATUS      current
            DESCRIPTION
                "DPBOMUS defines the assumed Minimum Usable receive Signal PSD (in dBm/Hz) for 
                 exchange based services, used to modify parameter DPBOFMAX defined below. It 
                 shall be coded as an unsigned integer representing a PSD level from 0 dBm/Hz 
                 (coded as 0) to -127.5 dBm/Hz (coded as 255) in steps of 0.5 dBm/Hz. 
                 All values in the range are valid. The invalid value is 65535. If data is invalid,
                 the invalid value will be returned.
                 Range: 0-255
                 Unit: 0.5dBm/Hz
                 
                " 
            REFERENCE    "ITU-T G.997.1(200604), paragraph 7.3.1.2.13"                      
         ::= { hwxdslDynamicProfEntry 27 }   

     hwxdslDynamicProfDpboFMin  OBJECT-TYPE
            SYNTAX      Unsigned32 (0..2048)
            UNITS       "4.3125 KHz"
            MAX-ACCESS  read-create
            STATUS      current
            DESCRIPTION
                "DPBOFMIN defines the minimum frequency from which the DPBO shall be applied. 
                 It shall be coded as a 16 bits unsigned integer representing a frequency in 
                 multiple of 4.3125 KHz. The range of valid values is from 0 kHz (coded as 0)
                 to 8832 kHz (coded as 2048). The invalid value is 65535. If data is invalid, 
                 the invalid value will be returned.
                 Range: 0-2048
                 Unit: 4.3125 KHz
                "  
            REFERENCE    "ITU-T G.997.1(200604), paragraph 7.3.1.2.13"            
      ::= { hwxdslDynamicProfEntry 28 }      
      
     hwxdslDynamicProfDpboFMax  OBJECT-TYPE
            SYNTAX      Unsigned32 (32..6956)
            UNITS       "4.3125 KHz"
            MAX-ACCESS  read-create
            STATUS      current
            DESCRIPTION
                "DPBOFMAX defines the maximum frequency at which DPBO may be applied. It shall be
                 coded as a 16 bits unsigned integer representing a frequency in multiple of 4.3125 KHz. 
                 The range of valid values is from 138 kHz (coded as 32) to 29997.75 kHz (coded as 6956).
                 The invalid value is 65535. If data is invalid, the invalid value will be returned.
                 Range: 32-6956
                 Unit: 4.3125 KHz
                "  
            REFERENCE    "ITU-T G.997.1(200604), paragraph 7.3.1.2.13"                      
      ::= { hwxdslDynamicProfEntry 29 }      

     hwxdslDynamicProfUpboPsdBand  OBJECT-TYPE
            SYNTAX      OCTET STRING (SIZE(0..16))  
            MAX-ACCESS  read-create
            STATUS      current
            DESCRIPTION
                "This parameter defines the UPBO reference PSD used to compute the upstream power back-off
                 for each upstream band except US0. A UPBOPSD defined for each band ahsll consist of two 
                 parameters [a, b]. Parameter a shall be coded as an unsigned 12-bit number from 40 dBm/Hz
                 (coded as 0) to 80.95 dBm/Hz (coded as 4095) in steps of 0.01 dBm/Hz; and b shall be coded
                 as an unsigned 12 bit number from 0 (coded as 0) to 40.95 dBm/Hz (coded as 4095) in steps 
                 of 0.01 dBm/Hz. The UPBO reference PSD at the frequency f expressed in MHz shall be equal 
                 to '-a-b(SQRT(f))'. The set of parameter values a = 40 dBm/Hz, b = 0 dBm/Hz is a special configuration
                 to disable UPBO in the respective upstream band.
                 Octets 0+1 -   a[0]
            	 Octets 2+3 -   b[0]
            	 Octets 4+5 -   a[1]
            	 Octets 6+7 -   b[1]
            	 Octets 8+9 -   a[2]
            	 Octets 10+11 - b[2]
            	 Octets 12+13 - a[3]
            	 Octets 14+15 - b[3]
            	"
            REFERENCE    "ITU-T G.997.1(200604), paragraph 7.3.1.2.14"                                
         ::= { hwxdslDynamicProfEntry 30 }      

	 hwxdslDynamicProfUpboKLF  OBJECT-TYPE
            SYNTAX INTEGER {
                     forced(1),
                     auto(2),
                     invalidValue(-1)   
                     }             
            MAX-ACCESS  read-create
            STATUS      current
            DESCRIPTION
                "This parameter is a flag that forces the VTU-R to use the electrical loop length of the CO-MIB
                 (UPBOKL) to compute the UPBO. The value shall be forced if the flag is set to 1. Otherwise, the
                 electrical loop length shall be autonomously selected by the VTU-O.
                 Options: 
                 1. forced(1)         - Force the CPE to use the electrical length of the CO(UPBOKL) to compute the UPBO
                 2. auto(2)           - Electrical length shall be autonomously selected by the CO
                 3. invalidValue(-1)  - Invalid value
                "  
            REFERENCE    "ITU-T G.997.1(200604), paragraph 7.3.1.2.14"    
         ::= { hwxdslDynamicProfEntry 31 }          

	 hwxdslDynamicProfUpboKL  OBJECT-TYPE
            SYNTAX      Unsigned32 (0..1280)
            UNITS       "0.1 dB"
            MAX-ACCESS  read-create
            STATUS      current
            DESCRIPTION
                "This parameter defines the electrical loop length expressed in dB at 1MHz, kl0, configured by
                 the CO-MIB. The value shall be coded as an unsigned 16 bit number in the range 0 (coded as 0) 
                 to 128 dB (coded as 1280) in steps of 0.1 dB. The invalid value is 65535. If data is invalid, 
                 the invalid value will be returned.
                 Range: 0-1280
                 Unit: 0.1 dB
                "
            REFERENCE    "ITU-T G.997.1(200604), paragraph 7.3.1.2.14"                                          
         ::= { hwxdslDynamicProfEntry 32 }        
      
     hwxdslDynamicProfRfiBands  OBJECT-TYPE
            SYNTAX      OCTET STRING(SIZE(0..159))
            MAX-ACCESS  read-create
            STATUS      current
            DESCRIPTION
                "The subset of PSD mask breakpoints that shall be
                 used to notch an RFI band.
                 It is a string of bands consist of begin tone index
                 and end tone index.
                 for example :0-10,20-50,100-4095
                 It can contain as most as 16 bands.
                "
            REFERENCE    "ITU-T G.997.1(200604), paragraph 7.3.1.2.10"
         ::= { hwxdslDynamicProfEntry 33 }
      
     hwxdslDynamicProfToneBlackOut  OBJECT-TYPE
            SYNTAX      OCTET STRING(SIZE(0..79))
            MAX-ACCESS  read-create
            STATUS      current
            DESCRIPTION
                "The subset of subcarriermask that shall be
                 used to mask the subcarriers.
                 It is a string of bands consist of begin tone index
                 and end tone index.
                 for example :0-10,20-50,100-4095
                 It can contain as most as 8 bands.
                "
            REFERENCE    "ITU-T G.997.1(200604), paragraph 7.3.1.2.8"
         ::= { hwxdslDynamicProfEntry 34 }                   
         
     hwxdslDynamicProfCarMaskDS  OBJECT-TYPE
            SYNTAX      OCTET STRING (SIZE(0..64))
            MAX-ACCESS  read-create
            STATUS      current
            DESCRIPTION
                "Sub-carriers mask.  A bitmap of 512 bits that allows masking
                 up to 512 downstream sub-carriers, depending on NSCds.  If bit
                 i (0 &lt;= i &lt; NSCds) is set to '1', the respective
                 downstream sub-carrier i is masked, and if set to '0', the
                 respective sub-carrier is unmasked.  Note that there should
                 always be unmasked sub-carriers (i.e., the object cannot be
                 all 1's).  Also note that if NSCds &lt; 512, all bits
                 i (NSCds i &lt;= 512) should be set to '1'.
                "
            REFERENCE    "ITU-T G.997.1, paragraph 7.3.1.2.6"
         ::= { hwxdslDynamicProfEntry 35 }

     hwxdslDynamicProfCarMaskUS  OBJECT-TYPE
            SYNTAX      OCTET STRING (SIZE(0..8))
            MAX-ACCESS  read-create
            STATUS      current
            DESCRIPTION
                "Sub-carriers mask.  A bitmap of 64 bits that allows masking
                 up to 64 downstream sub-carriers, depending on NSCds.  If
                 bit i (0 &lt;= i &lt; NSCus) is set to '1', the respective
                 upstream sub-carrier i is masked, and if set to '0', the
                 respective sub-carrier is unmasked.  Note that there
                 should always be unmasked sub-carriers (i.e., the object
                 cannot be all 1's).  Also note that if NSCus &lt;
                 64, all bits i (NSCus &lt; i &lt;= 64) should be set to '1'.
                "
            REFERENCE    "ITU-T G.997.1, paragraph 7.3.1.2.7"
         ::= { hwxdslDynamicProfEntry 36 }
                  
     hwxdslDynamicProfXdslMode    OBJECT-TYPE
            SYNTAX    INTEGER {
                     defMode (1),
                     adsl (2),
                     adsl2Pots (3),
                     adsl2Isdn (4),
                     adsl2PlusPots (5),
                     adsl2PlusIsdn (6),
                     adsl2ReachExtended (7),                     
                     g9923PotsNonOverlapped(8),
                     g9923PotsOverlapped(9),
                     g9923IsdnNonOverlapped(10),
                     g9923isdnOverlapped(11),
                     g9924potsNonOverlapped(14),
                     g9924potsOverlapped(15),
                     g9923AnnexIAllDigNonOverlapped(18),
                     g9923AnnexIAllDigOverlapped(19),
                     g9923AnnexJAllDigNonOverlapped(20),
                     g9923AnnexJAllDigOverlapped(21),
                     g9924AnnexIAllDigNonOverlapped(22),
                     g9924AnnexIAllDigOverlapped(23),
                     g9923AnnexLMode1NonOverlapped(24),
                     g9923AnnexLMode2NonOverlapped(25),
                     g9923AnnexLMode3Overlapped(26),
                     g9923AnnexLMode4Overlapped(27),
                     g9923AnnexMPotsNonOverlapped(28),
                     g9923AnnexMPotsOverlapped(29),
                     g9925PotsNonOverlapped(30),
                     g9925PotsOverlapped(31),
                     g9925IsdnNonOverlapped(32),
                     g9925isdnOverlapped(33),
                     g9925AnnexIAllDigNonOverlapped(36),
                     g9925AnnexIAllDigOverlapped(37),
                     g9925AnnexJAllDigNonOverlapped(38),
                     g9925AnnexJAllDigOverlapped(39),
                     g9925AnnexMPotsNonOverlapped(40),
                     g9925AnnexMPotsOverlapped(41),
                     vdsl2Pots (42),
                     vdsl2Isdn (43),
                     invalidValue(-1)
                     }
            MAX-ACCESS  read-create
            STATUS      current
            DESCRIPTION
                "The XDSL Mode is a way of categorizing the various XDSL
                 transmission modes into groups, each group (XDSL Mode) shares
                 the same PSD configuration.
                 Options: 
                 1. defMode (1)                          - XDSL transmit mode is defMode
                 2. adsl (2)                             - XDSL transmit mode is adsl                                    
                 3. adsl2Pots (3)                        - XDSL transmit mode is adsl2Pots                                       
                 4. adsl2Isdn (4)                        - XDSL transmit mode is adsl2Isdn    
                 5. adsl2PlusPots (5)                    - XDSL transmit mode is adsl2PlusPots    
                 6. adsl2PlusIsdn (6)                    - XDSL transmit mode is adsl2PlusIsdn    
                 7. adsl2ReachExtended (7)               - XDSL transmit mode is adsl2ReachExtended
                 8. g9923PotsNonOverlapped(8)            - XDSL transmit mode is g9923PotsNonOverlapped
                 9. g9923PotsOverlapped(9)               - XDSL transmit mode is g9923PotsOverlapped
                 10. g9923IsdnNonOverlapped(10)          - XDSL transmit mode is g9923IsdnNonOverlapped
                 11. g9923isdnOverlapped(11)             - XDSL transmit mode is g9923isdnOverlapped
                 12. g9924potsNonOverlapped(14)          - XDSL transmit mode is g9924potsNonOverlapped
                 13. g9924potsOverlapped(15)             - XDSL transmit mode is g9924potsOverlapped
                 14. g9923AnnexIAllDigNonOverlapped(18)  - XDSL transmit mode is g9923AnnexIAllDigNonOverlapped
                 15. g9923AnnexIAllDigOverlapped(19)     - XDSL transmit mode is g9923AnnexIAllDigOverlapped
                 16. g9923AnnexJAllDigNonOverlapped(20)  - XDSL transmit mode is g9923AnnexJAllDigNonOverlapped
                 17. g9923AnnexJAllDigOverlapped(21)     - XDSL transmit mode is g9923AnnexJAllDigOverlapped
                 18. g9924AnnexIAllDigNonOverlapped(22)  - XDSL transmit mode is g9924AnnexIAllDigNonOverlapped
                 19. g9924AnnexIAllDigOverlapped(23)     - XDSL transmit mode is g9924AnnexIAllDigOverlapped
                 20. g9923AnnexLMode1NonOverlapped(24)   - XDSL transmit mode is g9923AnnexLMode1NonOverlapped 
                 21. g9923AnnexLMode2NonOverlapped(25)   - XDSL transmit mode is g9923AnnexLMode2NonOverlapped
                 22. g9923AnnexLMode3Overlapped(26)      - XDSL transmit mode is g9923AnnexLMode3Overlapped
                 23. g9923AnnexLMode4Overlapped(27)      - XDSL transmit mode is g9923AnnexLMode4Overlapped
                 24. g9923AnnexMPotsNonOverlapped(28)    - XDSL transmit mode is g9923AnnexMPotsNonOverlapped
                 25. g9923AnnexMPotsOverlapped(29)       - XDSL transmit mode is g9923AnnexMPotsOverlapped
                 26. g9925PotsNonOverlapped(30)          - XDSL transmit mode is g9925PotsNonOverlapped
                 27. g9925PotsOverlapped(31)             - XDSL transmit mode is g9925PotsOverlapped
                 28. g9925IsdnNonOverlapped(32)          - XDSL transmit mode is g9925IsdnNonOverlapped
                 29. g9925isdnOverlapped(33)             - XDSL transmit mode is g9925isdnOverlapped
                 30. g9925AnnexIAllDigNonOverlapped(36)  - XDSL transmit mode is g9925AnnexIAllDigNonOverlapped
                 31. g9925AnnexIAllDigOverlapped(37)     - XDSL transmit mode is g9925AnnexIAllDigOverlapped
                 32. g9925AnnexJAllDigNonOverlapped(38)  - XDSL transmit mode is g9925AnnexJAllDigNonOverlapped
                 33. g9925AnnexJAllDigOverlapped(39)     - XDSL transmit mode is g9925AnnexJAllDigOverlapped
                 34. g9925AnnexMPotsNonOverlapped(40)    - XDSL transmit mode is g9925AnnexMPotsNonOverlapped 
                 35. g9925AnnexMPotsOverlapped(41)       - XDSL transmit mode is g9925AnnexMPotsOverlapped 
                 36. vdsl2Pots (42)                      - XDSL transmit mode is vdsl2Pots 
                 37. vdsl2Isdn (43)                      - XDSL transmit mode is vdsl2Isdn
                 38. invalidValue(-1)                    - Invalid value
                "
            REFERENCE    "DSL Forum TR-90, paragraph 5.1.8"
         ::= { hwxdslDynamicProfEntry 37 }
     
    hwxdslDynamicProfMaxNomPsdDs OBJECT-TYPE
             SYNTAX      Integer32(-600..-300 | -1)
             UNITS       "0.1 dB"
             MAX-ACCESS  read-create
             STATUS      current
             DESCRIPTION
                 "The maximum nominal transmit PSD in the downstream
                  direction during initialization and Showtime. It ranges from
                  -600 to -300 units of 0.1 dBm/Hz(physical values are -60 to
                  -30 dBm/Hz). The invalid value is -1. If data is invalid, the invalid value will be returned.
                  Unit: 0.1 dB
                 "
         ::= { hwxdslDynamicProfEntry 38 }
         
    hwxdslDynamicProfMaxNomPsdUs OBJECT-TYPE
             SYNTAX      Integer32(-600..-300 | -1)
             UNITS       "0.1 dB"
             MAX-ACCESS  read-create
             STATUS      current
             DESCRIPTION
                 "The maximum nominal transmit PSD in the upstream
                  direction during initialization and Showtime. It ranges from
                  -600 to -300 units of 0.1 dBm/Hz(physical values are -60 to
                  -30 dBm/Hz). The invalid value is -1. If data is invalid, the invalid value will be returned.
                  Unit: 0.1 dB
                 "
         ::= { hwxdslDynamicProfEntry 39 }
         
    hwxdslDynamicProfMaxNomAtpDs  OBJECT-TYPE
              SYNTAX      Unsigned32 (0..255)
              UNITS       "0.1 dBm"
              MAX-ACCESS  read-create
              STATUS      current
              DESCRIPTION
                  "The maximum nominal aggregate transmit power in the
                   downstream direction during initialization and Showtime. It
                   ranges from 0 to 255 units of 0.1 dBm (physical values are 0
                   to 25.5 dBm). The invalid value is 65535. If data is invalid, 
                   the invalid value will be returned.
                   Range: 0-255
                   Unit: 0.1 dBm
                  "
              REFERENCE    "ITU-T G.997.1, paragraph 7.3.1.2"
        ::= { hwxdslDynamicProfEntry 40 }

    hwxdslDynamicProfMaxNomAtpUs  OBJECT-TYPE
              SYNTAX      Unsigned32 (0..255)
              UNITS       "0.1 dBm"
              MAX-ACCESS  read-create
              STATUS      current
              DESCRIPTION
                 "The maximum nominal aggregate transmit power in the
                  upstream direction during initialization and Showtime. It
                  ranges from 0 to 255 units of 0.1 dBm (physical values are 0
                  to 25.5 dBm). The invalid value is 65535. If data is invalid, 
                  the invalid value will be returned.
                  Range: 0-255
                  Unit: 0.1 dBm
                 "
              REFERENCE    "ITU-T G.997.1, paragraph 7.3.1.2"
        ::= { hwxdslDynamicProfEntry 41 }
                     
     hwxdslDynamicProfPsdMaskDs   OBJECT-TYPE
            SYNTAX      OCTET STRING (SIZE(0..96))
            MAX-ACCESS  read-create
            STATUS      current
            DESCRIPTION
                "This configuration parameter defines the downstream PSD mask 
                 applicable at the U C2 reference point.
                 This MIB PSD mask may impose PSD restrictions in addition 
                 to the Limit PSD mask defined in the relevant Recommendation 
                 (e.g., G.992.5, G.993.2).
                 This is a string of 32 pairs of values in the following
                 structure:
                 Octets 0+1 - Index of 1st sub-carrier used in the context
                              of a first breakpoint.
                 Octet 2    - The PSD reduction for the sub-carrier indicated in
                              octets 0 and 1.
                 Octets 3-5 - Same, for a 2nd breakpoint.
                 Octets 6-8 - Same, for a 3rd breakpoint.
                 This architecture continues until octets 94-95, which are
                 associated with a 32nd breakpoint.
                 Each subcarrier index is an unsigned number in the range 0 and
                 (NSCds - 1).  Each PSD reduction value is in the range 0 (0dBm/Hz) to
                 255 (-127.5dBm/Hz) with steps of 0.5dBm/Hz.  Valid values are
                 in the range 0 to 190 (0 to -95dBm/Hz).
                 When the number of breakpoints is less than 32, all remaining
                 octets are set to the value 0xff.  Note that the content of this
                 object should be correlated with the sub-carriers mask and with
                 the RFI setup.
                "
            REFERENCE    "ITU-T G.997.1(200604), paragraph 7.3.1.2.9"
         ::= { hwxdslDynamicProfEntry 42 }
        
     hwxdslDynamicProfPsdMaskUs   OBJECT-TYPE
            SYNTAX      OCTET STRING (SIZE(0..48))
            MAX-ACCESS  read-create
            STATUS      current
            DESCRIPTION
                "This configuration parameter defines the upstream PSD 
                 mask applicable at the U R2 reference point. This MIB 
                 PSD mask may impose PSD restrictions in addition to the 
                 Limit PSD mask defined in the relevant Recommendations 
                 (e.g., ITU-T Recommendations G.992.3, G.993.2).
                 This is a string of 16 pairs of values in the following
                 structure:
                 Octets 0+1   - Index of 1st sub-carrier used in the context
                                of a first breakpoint.
                 Octet 2      - The PSD reduction for the sub-carrier indicated in
                                octets 0 and 1.
                 Octets 3-5   - Same, for a 2nd breakpoint.
                 Octets 45-47 - Same, for a 3rd breakpoint.
                 This architecture continues until octets 45-47, which are
                 associated with a 16th breakpoint.
                 Each subcarrier index is an unsigned number in the range 0 and
                 (NSCus - 1).  Each PSD reduction value is in the range 0 (0dBm/Hz) to
                 255 (-127.5dBm/Hz) with steps of 0.5dBm/Hz.  Valid values are
                 in the range 0 to 190 (0 to -95dBm/Hz).
                 When the number of breakpoints is less than 16, all remaining
                 octets are set to the value 0xff.  Note that the content of this
                 object should be correlated with the sub-carriers mask and with
                 the RFI setup.
                "
            REFERENCE    "ITU-T G.997.1(200604), paragraph 7.3.1.2.12"
         ::= { hwxdslDynamicProfEntry 43 }                  
         
     hwxdslDynamicProfLimitMask  OBJECT-TYPE
            SYNTAX      INTEGER {
                                  profile8a (1),
                        	  profile8b (2),
                        	  profile8c (3),
                        	  profile8d (4),
                        	  profile12a (5),
                        	  profile12b (6),
                        	  profile17a (7),
                        	  profile30a (8),
                        	  invalidValue(-1)    			
                               }
            MAX-ACCESS  read-create
            STATUS      current
            DESCRIPTION
                "This configuration parameter contains the G.993.2 
                 profiles to be allowed by the near-end xTU on this line.
                 Options: 
                 1. profile8a (1)     - The G.993.2 profile is profile8a
                 2. profile8b (2)     - The G.993.2 profile is profile8b
                 3. profile8c (3)     - The G.993.2 profile is profile8c
                 4. profile8d (4)     - The G.993.2 profile is profile8d
                 5. profile12a (5)    - The G.993.2 profile is profile12a
                 6. profile12b (6)    - The G.993.2 profile is profile12b
                 7. profile17a (7)    - The G.993.2 profile is profile17a
                 8. profile30a (8)    - The G.993.2 profile is profile30a
                 9. invalidValue(-1)  - Invalid value
                "
            REFERENCE    "ITU-T G.997.1(200604), paragraph 7.3.1.1.11"
       ::= { hwxdslDynamicProfEntry 44 }
         
     hwxdslDynamicProfClassMask  OBJECT-TYPE
            SYNTAX    INTEGER {
                          annexA998D32              (1),
                        	annexA998D64              (2),
                        	annexB997M1cA7            (3),
                        	annexB997M1xM8            (4),
                        	annexB997M1xM             (5),
                        	annexB997M2xM8            (6),
                        	annexB997M2xA             (7),
                        	annexB997M2xM             (8),
                        	annexB998M1xA             (9),
                        	annexB998M1xB             (10),
                        	annexB998M1xNUS0          (11),
                        	annexB998M2xA             (12),
                        	annexB998M2xM             (13),
                        	annexB998M2xB             (14),
                        	annexB998M2xNUS0          (15),
                        	annexBHPE17M1             (16),
                        	annexBHPE30M1             (17),
                          annexB997E17M2xA          (18),
                        	annexB997E30M2xNUS0       (19),
                        	annexB998E17M2xNUS0       (20),
                        	annexB998E17M2xNUS0M      (21),
                        	annexB998ADE17M2xNUS0M    (22),
                        	annexB998ADE17M2xB        (23),
                        	annexB998E30M2xNUS0       (24),
                        	annexB998E30M2xNUS0M      (25),
                        	annexB998ADE30M2xNUS0M    (26),
                        	annexB998ADE17M2xA        (27),
                          annexB998ADE30M2xNUS0A    (28),
            	            annexA998D48              (29),
            	            annexA998D128             (30),
            	            annexB998ADE17M2xM        (31),
                        	invalidValue(-1)
                              }
            MAX-ACCESS  read-create
            STATUS      current
            DESCRIPTION
                "In order to reduce the number of configuration possibilities, 
                 the limit PSD masks are grouped in the following PSD mask classes:           
                 Options: 
                 1. annexA998D32(1)               - Class 998 Annex A: D-32, D-64, D-48, D-128
                 2. annexA998D64(2)               - Class 998 Annex A: D-32, D-64, D-48, D-128
                 3. annexB997M1cA7(3)             - Class 997-M1c Annex B: 997-M1c-A-7
                 4. annexB997M1xM8(4)             - Class 997-M1x Annex B: 997-M1x-M-8, 997-M1x-M
                 5. annexB997M1xM(5)              - Class 997-M1x Annex B: 997-M1x-M-8, 997-M1x-M  
                 6. annexB997M2xM8(6)             - Class 997-M2x Annex B: 997-M2x-M-8, 997-M2x-A, 997-M2x-M
                 7. annexB997M2xA(7)              - Class 997-M2x Annex B: 997-M2x-M-8, 997-M2x-A, 997-M2x-M
                 8. annexB997M2xM(8)              - Class 997-M2x Annex B: 997-M2x-M-8, 997-M2x-A, 997-M2x-M
                 9. annexB998M1xA(9)              - Class 998-M1x Annex B: 998-M1x-A, 998-M1x-B, 998-M1x-NUS0
                 10. annexB998M1xB(10)            - Class 998-M1x Annex B: 998-M1x-A, 998-M1x-B, 998-M1x-NUS0
                 11. annexB998M1xNUS0(11)         - Class 998-M1x Annex B: 998-M1x-A, 998-M1x-B, 998-M1x-NUS0
                 12. annexB998M2xA(12)            - Class 998-M2x Annex B: 998-M2x-A, 998-M2x-M, 998-M2x-B, 998-M2x-NUS0
                 13. annexB998M2xM(13)            - Class 998-M2x Annex B: 998-M2x-A, 998-M2x-M, 998-M2x-B, 998-M2x-NUS0
                 14. annexB998M2xB(14)            - Class 998-M2x Annex B: 998-M2x-A, 998-M2x-M, 998-M2x-B, 998-M2x-NUS0
                 15. annexB998M2xNUS0(15)         - Class 998-M2x Annex B: 998-M2x-A, 998-M2x-M, 998-M2x-B, 998-M2x-NUS0
                 16. annexBHPE17M1(16)            - Class HPE17 Annex B: HPE17-M1
                 17. annexBHPE30M1(17)            - Class HPE30 Annex B: HPE30-M1
                 18. annexB997E17M2xA(18)         - Class 997E17-M2x Annex B: 997E17-M2x-A
                 19. annexB997E30M2xNUS0(19)      - Class 997E30-M2x Annex B: 997E30-M2x-NUS0
                 20. annexB998E17M2xNUS0(20)      - Class 998E17-M2x Annex B: 998E17-M2x-NUS0, 998E17-M2x-NUS0-M
                 21. annexB998E17M2xNUS0M(21)     - Class 998E17-M2x Annex B: 998E17-M2x-NUS0, 998E17-M2x-NUS0-M
                 22. annexB998ADE17M2xNUS0M(22)   - Class 998ADE17-M2x Annex B: 998ADE17-M2x-NUS0-M, 998ADE17-M2x-A, 998ADE17-M2x-B, 998ADE17-M2x-M.
                 23. annexB998ADE17M2xB(23)       - Class 998ADE17-M2x Annex B: 998ADE17-M2x-NUS0-M, 998ADE17-M2x-A, 998ADE17-M2x-B, 998ADE17-M2x-M.
                 24. annexB998E30M2xNUS0(24)      - Class 998E30-M2x Annex B: 998E30-M2x-NUS0, 998E30-M2x-NUS0-M
                 25. annexB998E30M2xNUS0M(25)     - Class 998E30-M2x Annex B: 998E30-M2x-NUS0, 998E30-M2x-NUS0-M
                 26. annexB998ADE30M2xNUS0M(26)   - Class 998ADE30-M2x Annex B: 998ADE30-M2x-NUS0-M, 998ADE30-M2x-NUS0-A
                 27. annexB998ADE17M2xA(27)       - Class 998ADE17-M2x Annex B: 998ADE17-M2x-NUS0-M, 998ADE17-M2x-A, 998ADE17-M2x-B, 998ADE17-M2x-M.
                 28. annexB998ADE30M2xNUS0A(28)   - Class 998ADE30-M2x Annex B: 998ADE30-M2x-NUS0-M, 998ADE30-M2x-NUS0-A
                 29. annexA998D48(29)             - Class 998 Annex A: D-32, D-64, D-48, D-128
                 30. annexA998D128(30)            - Class 998 Annex A: D-32, D-64, D-48, D-128
                 31. annexB998ADE17M2xM(31)       - Class 998ADE17-M2x Annex B: 998ADE17-M2x-NUS0-M, 998ADE17-M2x-A, 998ADE17-M2x-B, 998ADE17-M2x-M.
                 32. invalidValue(-1)             - Invalid value
                "
            REFERENCE    "ITU-T G.997.1(200604), paragraph 7.3.1.1.12"
         ::= { hwxdslDynamicProfEntry 45 }
         
     hwxdslDynamicProfBandOptUsage  OBJECT-TYPE
            SYNTAX      INTEGER {
                                     disable(1),
                                     enable(2),
                                     invalidValue(-1)
                                }
            MAX-ACCESS  read-create
            STATUS      current
            DESCRIPTION
                "Defines the VDSL link use of the optional frequency
                 range [25kHz - 138kHz] (Opt).
                 Options: 
                 1. disable(1)       - Indicates Opt is unused
                 2. enable(2)        - Indicates Opt usage is for upstream
                 3. invalidValue(-1) - Invalid value
                 Huawei defined.
                "
      ::= { hwxdslDynamicProfEntry 46 }
      
     hwxdslDynamicProfVirtualNoiseModeDs  OBJECT-TYPE
            SYNTAX      INTEGER {
                                     disable(1),
                                     enable(2),
                                     invalidValue(-1)
                                }
            MAX-ACCESS  read-create
            STATUS      current
            DESCRIPTION
                "Defines the Virtual Noise of downsteam.
                 Options:
                 1. disable(1)       - Unused
                 2. enable(2)        - Used
                 3. invalidValue(-1) - Invalid value
                "
      ::= { hwxdslDynamicProfEntry 47 }
      
      hwxdslDynamicProfVirtualNoiseModeUs  OBJECT-TYPE
            SYNTAX      INTEGER {
                                     disable(1),
                                     enable(2),
                                     invalidValue(-1)
                                }
            MAX-ACCESS  read-create
            STATUS      current
            DESCRIPTION
                "Defines the Virtual Noise of upstream.
                 Options:
                 1. disable(1)       - Unused
                 2. enable(2)        - Used
                 3. invalidValue(-1) - Invalid value
                "
      ::= { hwxdslDynamicProfEntry 48 }
      
      hwxdslDynamicProfVirtualNoiseDs  OBJECT-TYPE
            SYNTAX      OCTET STRING (SIZE(0..96))
            MAX-ACCESS  read-create
            STATUS      current
            DESCRIPTION
                "The Virtual Noise of downsteam.
                 This is a string of 32 pairs of values in the following
                 structure:
                 Octets 0+1 - Index of 1st sub-carrier used in the context
                              of a first breakpoint.
                 Octet 2    - The PSD reduction for the sub-carrier indicated in
                              octets 0 and 1.
                 Octets 3-5 - Same, for a 2nd breakpoint.
                 Octets 6-8 - Same, for a 3rd breakpoint.
                 This architecture continues until octets 94-95, which are
                 associated with a 32nd breakpoint.
                 Each subcarrier index is an unsigned number in the range 0 and
                 (NSCds - 1).  Each PSD reduction value is in the range 0 (0dBm/Hz) to
                 255 (127.5dBm/Hz) with steps of 0.5dBm/Hz.
                "
      ::= { hwxdslDynamicProfEntry 49 }
      
      hwxdslDynamicProfVirtualNoiseUs  OBJECT-TYPE
            SYNTAX      OCTET STRING(SIZE(0..48))
            MAX-ACCESS  read-create
            STATUS      current
            DESCRIPTION
                "The Virtual Noise of upsteam.
                 This is a string of 16 pairs of values in the following
                 structure:
                 Octets 0+1 - Index of 1st sub-carrier used in the context
                              of a first breakpoint.
                 Octet 2    - The PSD reduction for the sub-carrier indicated in
                              octets 0 and 1.
                 Octets 3-5 - Same, for a 2nd breakpoint.
                 Octets 6-8 - Same, for a 3rd breakpoint.
                 This architecture continues until octets 45-47, which are
                 associated with a 16th breakpoint.
                 Each subcarrier index is an unsigned number in the range 0 and
                 (NSCds - 1).  Each PSD reduction value is in the range 0 (0dBm/Hz) to
                 255 (127.5dBm/Hz) with steps of 0.5dBm/Hz.
                "
      ::= { hwxdslDynamicProfEntry 50 }
      
     hwxdslDynamicProfRowStatus  OBJECT-TYPE
      SYNTAX      RowStatus
      MAX-ACCESS  read-create
      STATUS      current
      DESCRIPTION
          "This object is used to create a new row or to modify or
           delete an existing row in this table.
           A profile is activated by setting this object to 'active'.
           When 'active' is set, the system will validate the profile.
           Before a profile can be deleted or taken out of service
           (by setting this object to 'destroy' or 'outOfService'),
           it must be first unreferenced from all associated
           templates.
          "
      ::= { hwxdslDynamicProfEntry 51 }
      
      
--hwXdslPortIopCaptureTable
--
--    
              hwXdslPortIopCaptureTable OBJECT-TYPE 	
			SYNTAX SEQUENCE OF HwXdslPortIopCaptureEntry
			MAX-ACCESS not-accessible
			STATUS current
			DESCRIPTION 
			    "The table hwXdslPortIopCaptureTable implement xDSL port IOP information capture.
			     The index of this table is ifIndex.
			    "
		 ::= { adslMibObjects 65551 }

		hwXdslPortIopCaptureEntry OBJECT-TYPE
			SYNTAX HwXdslPortIopCaptureEntry
			MAX-ACCESS not-accessible
			STATUS current
			DESCRIPTION 
			    "The table hwXdslPortIopCaptureTable implement xDSL port IOP information capture.
                             The index of this entry is ifIndex.
                            "
			INDEX{        
			         ifIndex
			     }
			::= { hwXdslPortIopCaptureTable 1 }

                HwXdslPortIopCaptureEntry ::=
			SEQUENCE{      
			           hwXdslPortIopCaptureOperType
			              INTEGER,
                                   hwXdslPortIopCaptureOperStatus 
			              INTEGER
			        }  
			    
                hwXdslPortIopCaptureOperType OBJECT-TYPE
	             SYNTAX INTEGER
		        {   
		        	start(1),
		        	stop(2),
		        	invalid(-1)	
		        }
	               MAX-ACCESS  read-write
	               STATUS      current
	               DESCRIPTION 
	                   "Start or stop IOP information capture of xDSL port.
	                    Options:
	                    1. start(1)    - Start IOP information capture of xDSL port
	                    2. stop(2)     - Stop IOP information capture of xDSL port
	                    3. invalid(-1) - Invalid value
	                   "
	        ::= { hwXdslPortIopCaptureEntry 1 }  
	        
	        hwXdslPortIopCaptureOperStatus OBJECT-TYPE  
	                SYNTAX INTEGER
			        {   
			        	noCapture(1),
					capturing(2),
					iopGenerate(3),
					captured(4),
					invalid(-1)
			        }    
			MAX-ACCESS read-only
			STATUS     current
			DESCRIPTION 
			    "Port IOP capture status. 
			     Options:
			     1. noCapture(1)   - Indicates that the capture is not performed
			     2. capturing(2)   - Indicates that the capture is being performed
			     3. iopGenerate(3) - Indicates that the IOP file is generated
			     4. captured(4)    - Indicates that the capture is complete
			     5. invalid(-1)    - Invalid value
			    "
	       ::= { hwXdslPortIopCaptureEntry 2 }
--hwXdslDynamicInfoCollectTable
--
--   
              hwXdslDynamicInfoCollectTable OBJECT-TYPE 	
			SYNTAX SEQUENCE OF HwXdslDynamicInfoCollectEntry
			MAX-ACCESS not-accessible
			STATUS deprecated
			DESCRIPTION 
			    "The table hwXdslDynamicInfoCollectTable implement xDSL port Dynamic information collect.
			     The index of this table is hwFrameIndex and hwSlotIndex.
			    "
		 ::= { adslMibObjects 65552 }

		hwXdslDynamicInfoCollectEntry OBJECT-TYPE
			SYNTAX HwXdslDynamicInfoCollectEntry
			MAX-ACCESS not-accessible
			STATUS deprecated
			DESCRIPTION 
			    "The table hwXdslDynamicInfoCollectTable implement xDSL port Dynamic information collect.
			     The index of this entry is hwFrameIndex and hwSlotIndex.
			    "
                            
			INDEX{        
			         hwFrameIndex, 
			         hwSlotIndex
			     }
			::= { hwXdslDynamicInfoCollectTable 1 }

            HwXdslDynamicInfoCollectEntry ::=
			SEQUENCE{      
					hwXdslDynamicInfoCollect
						INTEGER,
					hwXdslDynamicInfoCollectStatus
						INTEGER,
					hwXdslDynamicInfoCollectTime
			              		DateAndTime
			        }  
			    
            hwXdslDynamicInfoCollect OBJECT-TYPE
	             SYNTAX INTEGER
		        {   
		        	start(1),
		        	invalid(-1)
		        }
	               MAX-ACCESS  read-write
	               STATUS      deprecated
	               DESCRIPTION 
	                   "Start Dynamic information collecting of Xdsl port.
	                    Options:
	                    1. start(1)    - Indicates that collecting data starts
	                    2. invalid(-1) - Invalid value
	                   "
	        ::= { hwXdslDynamicInfoCollectEntry 1 }  
	        
	        hwXdslDynamicInfoCollectStatus OBJECT-TYPE  
	                SYNTAX INTEGER
			        {   
			        	noCollect(1),
					collecting(2),
					collected(3)
			        }    
			MAX-ACCESS read-only
			STATUS     deprecated
			DESCRIPTION 
			    "Board Dynamic information collecting status. 
			     Options:
			     1. noCollect(1)  - Indicates that collecting data is not performed
			     2. collecting(2) - Indicates that collecting data is being performed
			     3. collected(3)  - Indicates that collecting data is complete
			    "	      
	       ::= { hwXdslDynamicInfoCollectEntry 2 }
	       
	       hwXdslDynamicInfoCollectTime OBJECT-TYPE
			SYNTAX DateAndTime
			MAX-ACCESS read-only
			STATUS deprecated
			DESCRIPTION "Time when collecting the optimization information is complete."
			::= { hwXdslDynamicInfoCollectEntry 3 }
--
--ADSL traps description
--
    	hwAdslTraps OBJECT IDENTIFIER ::= { adslTraps 65536 }
    	hwAdslGeneralTraps OBJECT IDENTIFIER ::= { hwAdslTraps 1 }
    	hwAdslGeneralTrapsOIDs OBJECT IDENTIFIER ::= { hwAdslGeneralTraps 0 }

	    hwAdslPortActRateMonitorTrap NOTIFICATION-TYPE
            OBJECTS { hwFrameIndex,hwSlotIndex,hwPortIndex,
                    hwAdslAtucLatestTxRate,hwAdslAturLatestTxRate,
                    hwAdslAtucLatestTxRateThreshold,hwAdslAturLatestTxRateThreshold,
                    hwAdslLineLatestActiveTime,hwAdslAtucLatestSnrMgn,hwAdslAturLatestSnrMgn,
                    hwAdslAtucLatestAtn,hwAdslAturLatestAtn,hwAdslAtucLatestAttainableRate,hwAdslAturLatestAttainableRate,
                    hwAdslAtucLatestConfTxRate,hwAdslAturLatestConfTxRate,hwAdslAtucLatestInterleaveDelay,
                    hwAdslAturLatestInterleaveDelay,hwAdslAtucLatestTargetSnrMgn,hwAdslAturLatestTargetSnrMgn,
                    hwSubslotIndex,hwAlarmId,hwAlarmTime,hwAlarmSn,hwCauseId,hwTrapType } 
            STATUS current
            DESCRIPTION
                "Definition of the trap reported when the ADSL port rate fails to meet the requirement. 
                 If ADSL act rate is lower than threshold, hwTrapType is 1. Otherwise, hwTrapType is 2.
                "
            ::= { hwAdslGeneralTrapsOIDs 1 }

	    hwAdslPortRateChangeTrap NOTIFICATION-TYPE
            OBJECTS { hwFrameIndex,hwSlotIndex,hwPortIndex,hwIasConfigChangeTrapID,
                      hwAdslPortRateChangeTrapIPIAID,hwAdslPortRateChangeTrapMUXID,
                      hwAdslPortRateChangeTrapTimeStamp,hwAdslPortRateChangeTrapDSLineRate,
            	      hwAdslPortRateChangeTrapUSLineRate,hwAdslPortRateChangeTrapEventType,hwAdslPortRateChangeTrapDslType} 
            STATUS current
            DESCRIPTION
                "ADSL act rate is change trap.
                 This trap message is generated when the ADSL port rate change.
                "
            ::= { hwAdslGeneralTrapsOIDs 2 }                
	END

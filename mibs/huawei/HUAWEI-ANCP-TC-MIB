-- ============================================================================
-- Copyright (C) 2018 by  HUAWEI TECHNOLOGIES. All rights reserved.
-- Description:  The MIB provides Textual Conventions to be used by
--               MIB files for AN and NAS that are implementing
--               the Access Node Control Protocol (ANCP).
-- Reference:  
-- Version: V1.03
-- ============================================================================
HUAWEI-ANCP-TC-MIB DEFINITIONS ::= BEGIN

IMPORTS
       MODULE-IDENTITY, Unsigned32, mib-2
            FROM SNMPv2-SMI                            -- [RFC2578]

       huaweiMgmt
            FROM HUAWEI-MIB

       TEXTUAL-CONVENTION
            FROM SNMPv2-TC;                            -- [RFC2579]

hwAncpAnMIB MODULE-IDENTITY
       LAST-UPDATED "201809190000Z" 
       ORGANIZATION "Huawei Technologies Co.,Ltd."
       CONTACT-INFO 
                   "Huawei Industrial Base
                    Bantian, Longgang
                    Shenzhen 518129
                    People's Republic of China
                    Website: http://www.huawei.com
                    Email: support@huawei.com
                   "
       DESCRIPTION
           "The MIB provides Textual Conventions to be used by
            MIB files for AN and NAS that are implementing
            the Access Node Control Protocol (ANCP)."
-- RFC Ed.: replace yyyy with actual RFC number & remove this note
       
       --  Revision history
	   REVISION    "201809190000Z"
       DESCRIPTION "V1.03, modified the description of the file."
	   
       REVISION    "201007190000Z"
       DESCRIPTION "V1.02, modified the description of the file."
       
       REVISION    "201005060000Z"
       DESCRIPTION "V1.01, modified the module identity."
       
       REVISION    "200806180000Z"
       DESCRIPTION "V1.00, initial version."
       
-- RFC Ed.: replace yyyy with actual RFC number & remove this note
       ::= { huaweiMgmt 106 }
-- The value xxx to be assigned by IANA.

--
-- Textual Conventions
--

GsmpSubVersion ::= TEXTUAL-CONVENTION
       STATUS     current
       DESCRIPTION
             "The subversion numbers defined for the GSMP protocol."
       SYNTAX     Unsigned32

AncpSessionCapabilities ::= TEXTUAL-CONVENTION
       STATUS current
       DESCRIPTION
             "ANCP capabilities supported by the AN.
              The following capabilities are available:
                 topologyDiscovery (0)- Access Topology Discovery
                 lineConfig (1)       - Line Configuration
                 multicast (2)        - Multicast
                 l2Oam (3)            - Layer 2 OAM
              A bit set means the associated capability is supported."
       SYNTAX BITS {
                     topologyDiscovery (0),
                     lineConfig (1),
                     multicast (2),
                     l2Oam (3)
                   }
END

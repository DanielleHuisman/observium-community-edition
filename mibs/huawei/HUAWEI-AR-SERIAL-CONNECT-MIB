--
-- HUAWEI-AR-SERIAL-CONNECT-MIB.mib
-- MIB generated by MG-SOFT Visual MIB Builder Version 4.0 Build 341
-- Tuesday, December 09, 2014 at 16:31:27
-- 
--  ==================================================================
-- Copyright (C) 2018 by HUAWEI TECHNOLOGIES. All rights reserved.
-- 
-- Description:  This MIB module defines MIB objects of hwGpioTable, hwTransportSessionTable, hwTransSessionOperateTable,
-- 			 hwSocketTransTable, hwModbusTransTable and hwGpioTraps.
-- Reference:
-- Version: V1.02
-- History:
-- V1.0 2007-10-21 publish
-- ==================================================================

	HUAWEI-AR-SERIAL-CONNECT-MIB DEFINITIONS ::= BEGIN
 
		IMPORTS
			hwDatacomm			
				FROM HUAWEI-MIB			
			OBJECT-GROUP, MODULE-COMPLIANCE, NOTIFICATION-GROUP			
				FROM SNMPv2-CONF			
			IpAddress, Integer32, OBJECT-TYPE, MODULE-IDENTITY, NOTIFICATION-TYPE			
				FROM SNMPv2-SMI			
			DateAndTime, RowStatus		
				FROM SNMPv2-TC;
	
	
--             FROM SNMPv2-SMI;
-- DisplayString,TruthValue,RowStatus   
--     FROM SNMPv2-TC;
-- EnabledStatus
-- 1.3.6.1.4.1.2011.5.25.338
-- November 21, 2014 at 11:39 GMT
		-- 1.3.6.1.4.1.2011.5.25.338
		hwARSerialConnectMIB MODULE-IDENTITY 
			LAST-UPDATED "201804131139Z"		-- April 13, 2018 at 11:39 GMT
			ORGANIZATION 
				"Huawei Technologies Co.,Ltd."
			CONTACT-INFO 
				"Huawei Industrial Base                
				Bantian, Longgang                     
				Shenzhen 518129                       
				People's Republic of China            
				Website: http://www.huawei.com        
				Email: support@huawei.com             
				"
			DESCRIPTION 
				"The private mib file includes the general extent 
				information of the device.hwDatacomm(338).hwARSerialConnectMIB" 
                                            REVISION     "201804131139Z"                
                                            DESCRIPTION  "V1.02, Add trap node hwGpioDIFailure hwGpioDIRecovery" 

		    REVISION  "201411211139Z"   
		    DESCRIPTION
		        "Create hwARSerialConnectMIB at 2014-11-21"
			::= { hwDatacomm 338 }

		
	
	
--
-- Node definitions
--
	
--  Node definitions
-- 
-- 1.3.6.1.4.1.2011.5.25.338.1
		hwARSerialConnectMIBObjects OBJECT IDENTIFIER ::= { hwARSerialConnectMIB 1 }

		
--   hwGpioTable Table 
-- 
-- 1.3.6.1.4.1.2011.5.25.338.1.1
		hwGpioTable OBJECT-TYPE
			SYNTAX SEQUENCE OF HwGpioEntry
			MAX-ACCESS not-accessible
			STATUS current
			DESCRIPTION
				"Indicates the functions of GPIO port.
				This table lists the base setting information of GPIO port to realize the function of DI/DO."
			::= { hwARSerialConnectMIBObjects 1 }

		
--  1.3.6.1.4.1.2011.5.25.338.1.1.1
		hwGpioEntry OBJECT-TYPE
			SYNTAX HwGpioEntry
			MAX-ACCESS not-accessible
			STATUS current
			DESCRIPTION
				"Indicates the functions of GPIO port.
				This table lists the base setting information of GPIO port to realize the function of DI/DO."
			INDEX { hwGpioId }
			::= { hwGpioTable 1 }

		
		HwGpioEntry ::=
			SEQUENCE { 
				hwGpioId
					Integer32,
				hwGpioMode
					INTEGER,
				hwGpioDOLevel
					INTEGER,
				hwGpioDIState
					INTEGER,
				hwGpioDODefaultLevel
					INTEGER,
                                                                                hwGpioDIFailReason
                                                                                                    INTEGER
			 }

--  1.3.6.1.4.1.2011.5.25.338.1.1.1.1
		hwGpioId OBJECT-TYPE
			SYNTAX Integer32 (1..6)
			MAX-ACCESS read-only
			STATUS current
			DESCRIPTION
				"Indicates current used GPIO id on the device ."
			::= { hwGpioEntry 1 }

		
--  1.3.6.1.4.1.2011.5.25.338.1.1.1.2
		hwGpioMode OBJECT-TYPE
			SYNTAX INTEGER
				{
				di(0),
				do(1)
				}
			MAX-ACCESS read-write
			STATUS current
			DESCRIPTION
				"Indicates the GPIO work mode,the default value is di."
			DEFVAL { di }
			::= { hwGpioEntry 2 }

		
--  1.3.6.1.4.1.2011.5.25.338.1.1.1.3
		hwGpioDOLevel OBJECT-TYPE
			SYNTAX INTEGER
				{
				low(0),
				high(1),
				null(2)
				}
			MAX-ACCESS read-write
			STATUS current
			DESCRIPTION
				"Indicates the current level of DO mode.When the current GPIOID is in DI mode,the value is null."  
			DEFVAL { null }
			::= { hwGpioEntry 3 }

		
--  1.3.6.1.4.1.2011.5.25.338.1.1.1.4
		hwGpioDIState OBJECT-TYPE
			SYNTAX INTEGER
				{
				low(0),
				high(1),
				null(2)
				}
			MAX-ACCESS read-only
			STATUS current
			DESCRIPTION
				"Indicates the current state of DI mode.When the current GPIOID is in DO mode,the value is null."  
			DEFVAL { null }
			::= { hwGpioEntry 4 }

		
--  1.3.6.1.4.1.2011.5.25.338.1.1.1.5
		hwGpioDODefaultLevel OBJECT-TYPE
			SYNTAX INTEGER
				{
				low(0),
				high(1),
				null(2)
				}
			MAX-ACCESS read-only
			STATUS current
			DESCRIPTION
				"Indicates the default state of DO mode.When the current GPIOID is in DI mode,the value is null."
			DEFVAL { high }
			::= { hwGpioEntry 5 }

--  1.3.6.1.4.1.2011.5.25.338.1.1.1.6
		hwGpioDIFailReason OBJECT-TYPE
			SYNTAX INTEGER
				{
				null(0),
				acfailure(1),
				batterylow(2)
				}
			MAX-ACCESS read-only
			STATUS current
			DESCRIPTION
				"Indicates the default FailReason of DI."
			DEFVAL { high }
			::= { hwGpioEntry 6 }

		
--   hwTransportSessionTable Table 
-- 
-- 1.3.6.1.4.1.2011.5.25.338.1.2
		hwTransportSessionTable OBJECT-TYPE
			SYNTAX SEQUENCE OF HwTransportSessionEntry
			MAX-ACCESS not-accessible
			STATUS current
			DESCRIPTION
				"Indicates the business of serial transportation.This table lists the session information of the serial."
			::= { hwARSerialConnectMIBObjects 2 }


-- 1.3.6.1.4.1.2011.5.25.338.1.2.1
		hwTransportSessionEntry OBJECT-TYPE
			SYNTAX HwTransportSessionEntry
			MAX-ACCESS not-accessible
			STATUS current
			DESCRIPTION
				"Indicates the business of serial transportation.
				This table lists the session information of the remote serial."
			INDEX { hwTtyId }
			::= { hwTransportSessionTable 1 }

		
		HwTransportSessionEntry ::=
			SEQUENCE {   
			                     hwTtyId
					Integer32,
				hwTransportMode
					INTEGER,
				hwTransportRemoteIP
					IpAddress,
				hwTransportRemotePort
					Integer32,
				hwConnectDuration
					OCTET STRING,
				hwBytesReceived
					Integer32,
				hwBytesSend
					Integer32,
				hwConnectionNum
					Integer32,
				hwRefuseConnectionNum
					Integer32,
				hwMsgStatics
					Integer32
			 } 
			 
-- 1.3.6.1.4.1.2011.5.25.338.1.2.1.1
		hwTtyId OBJECT-TYPE
			SYNTAX Integer32 (1..2)
			MAX-ACCESS read-only
			STATUS current
			DESCRIPTION
				"Inicates the current tty index ."
			::= { hwTransportSessionEntry 1 }   
			
-- 1.3.6.1.4.1.2011.5.25.338.1.2.1.2
		hwTransportMode OBJECT-TYPE
			SYNTAX INTEGER
				{ 
				none(0),
				raw(1),
				t101(2),
				modbus(3)
				}
			MAX-ACCESS read-write
			STATUS current
			DESCRIPTION
				"Indicates the current used mode of transparent.During mode switching, 
				if the current communication parameter configuration is not the default configuration ,the mode switching is not allowed."
			::= { hwTransportSessionEntry 2 }
		
-- 1.3.6.1.4.1.2011.5.25.338.1.2.1.3
		hwTransportRemoteIP OBJECT-TYPE
			SYNTAX IpAddress
			MAX-ACCESS read-only
			STATUS current
			DESCRIPTION
				"Indicates the remote IP."
			::= { hwTransportSessionEntry 3 }
		
-- 1.3.6.1.4.1.2011.5.25.338.1.2.1.4
		hwTransportRemotePort OBJECT-TYPE
			SYNTAX Integer32
			MAX-ACCESS read-only
			STATUS current
			DESCRIPTION
				"Indicates the remote port."
			::= { hwTransportSessionEntry 4 }

-- 1.3.6.1.4.1.2011.5.25.338.1.2.1.5
		hwConnectDuration OBJECT-TYPE
			SYNTAX OCTET STRING(SIZE (0..256))
			MAX-ACCESS read-only
			STATUS current
			DESCRIPTION
				"Indicates the time when the connection begins."
			::= { hwTransportSessionEntry 5 }

-- 1.3.6.1.4.1.2011.5.25.338.1.2.1.6
		hwBytesReceived OBJECT-TYPE
			SYNTAX Integer32
			MAX-ACCESS read-only
			STATUS current
			DESCRIPTION
				"Statistics the number of packets received on current connection."
			::= { hwTransportSessionEntry 6 }

-- 1.3.6.1.4.1.2011.5.25.338.1.2.1.7
		hwBytesSend OBJECT-TYPE
			SYNTAX Integer32
			MAX-ACCESS read-only
			STATUS current
			DESCRIPTION
				"Statistics the number of packets sent on current connection."
			::= { hwTransportSessionEntry 7 }

-- 1.3.6.1.4.1.2011.5.25.338.1.2.1.8
		hwConnectionNum OBJECT-TYPE
			SYNTAX Integer32
			MAX-ACCESS read-only
			STATUS current
			DESCRIPTION
				"Statistics the number of connection on current serial."
			::= { hwTransportSessionEntry 8 }

-- 1.3.6.1.4.1.2011.5.25.338.1.2.1.9
		hwRefuseConnectionNum OBJECT-TYPE
			SYNTAX Integer32
			MAX-ACCESS read-only
			STATUS current
			DESCRIPTION
				"Statistics the number of refuseing connection on current serial."
			::= { hwTransportSessionEntry 9 }

-- 1.3.6.1.4.1.2011.5.25.338.1.2.1.10
		hwMsgStatics OBJECT-TYPE
			SYNTAX Integer32
			MAX-ACCESS read-only
			STATUS current
			DESCRIPTION
				"Statistics the number of transmitted and received packets on current connection."
			::= { hwTransportSessionEntry 10 }

		
--   hwTransSessionOperateTable Table 
-- 
-- 1.3.6.1.4.1.2011.5.25.338.1.3
		hwTransSessionOperateTable OBJECT-TYPE
			SYNTAX SEQUENCE OF HwTransSessionOperateEntry
			MAX-ACCESS not-accessible
			STATUS current
			DESCRIPTION
				"Indicates the business of serial transportation.
				This table lists the session information of the serial."
			::= { hwARSerialConnectMIBObjects 3 }

-- 1.3.6.1.4.1.2011.5.25.338.1.3.1
		hwTransSessionOperateEntry OBJECT-TYPE
			SYNTAX HwTransSessionOperateEntry
			MAX-ACCESS not-accessible
			STATUS current
			DESCRIPTION
				"Indicates the business of serial transportation.
				This table lists the session information of the remote serial."
			INDEX { hwTtyId, hwSessionIndex }
			::= { hwTransSessionOperateTable 1 }

		
		HwTransSessionOperateEntry ::=
			SEQUENCE { 
				hwSessionIndex
					Integer32,
				hwTransSessionSessionID
					Integer32,
				hwTransSessionRowStatus
					RowStatus
			 }

-- 1.3.6.1.4.1.2011.5.25.338.1.3.1.1
		hwSessionIndex OBJECT-TYPE
			SYNTAX Integer32
			MAX-ACCESS read-only
			STATUS current
			DESCRIPTION
				"Inicates the connection session id ."
			::= { hwTransSessionOperateEntry 1 }

-- 1.3.6.1.4.1.2011.5.25.338.1.3.1.2
		hwTransSessionSessionID OBJECT-TYPE
			SYNTAX Integer32
			MAX-ACCESS read-create
			STATUS current
			DESCRIPTION
				"Indicates the current used connection session id."
			::= { hwTransSessionOperateEntry 2 }

		
--  1.3.6.1.4.1.2011.5.25.338.1.3.1.3
		hwTransSessionRowStatus OBJECT-TYPE
			SYNTAX RowStatus
			MAX-ACCESS read-create
			STATUS current
			DESCRIPTION
				"This project used to create and delete a connection."
			::= { hwTransSessionOperateEntry 3 }

		
--   hwSocketTransTable Table 
-- 
-- 1.3.6.1.4.1.2011.5.25.338.1.4
		hwSocketTransTable OBJECT-TYPE
			SYNTAX SEQUENCE OF HwSocketTransEntry
			MAX-ACCESS not-accessible
			STATUS current
			DESCRIPTION
				"Indicates the socket information.
				This table lists the base communication of tcp/udp on serial socket."
			::= { hwARSerialConnectMIBObjects 4 }

		
--  1.3.6.1.4.1.2011.5.25.338.1.4.1
		hwSocketTransEntry OBJECT-TYPE
			SYNTAX HwSocketTransEntry
			MAX-ACCESS not-accessible
			STATUS current
			DESCRIPTION
				"Indicates the socket information.
				This table lists the base communication of tcp/udp on serial socket."
			INDEX { hwTtyId }
			::= { hwSocketTransTable 1 }

		
		HwSocketTransEntry ::=
			SEQUENCE { 
				hwSocketTransEnable
					INTEGER,
				hwSocketTransType
					INTEGER,
				hwSocketTransPacketSize
					Integer32,
				hwSocketTransPacketTime
					Integer32,
				hwSocketTransSpecialChar
					Integer32,
				hwSocketTransClientIP
					IpAddress,
				hwSocketTransClientPort
					Integer32,
				hwSocketTransServerIP
					IpAddress,
				hwSocketTransServerPort
					Integer32,
				hwSocketTransTcpIdleTimeout
					Integer32,
				hwSocketTransBestEffort
					INTEGER,
			                     hwRawModeSocketTransEnable
					INTEGER
			 }

--  1.3.6.1.4.1.2011.5.25.338.1.4.1.1
		hwSocketTransEnable OBJECT-TYPE
			SYNTAX INTEGER
				{
				disable(0),
				enable(1)
				}
			MAX-ACCESS read-write
			STATUS current
			DESCRIPTION
				"When current TTY ID is 1,this object used to switch the serial back and forth from management serial to bussiness serial.
				TTY 2 is a bussiness serial,no need to switch."
			DEFVAL { disable }
			::= { hwSocketTransEntry 1 }

		
--  1.3.6.1.4.1.2011.5.25.338.1.4.1.2
		hwSocketTransType OBJECT-TYPE
			SYNTAX INTEGER
				{
				tcpServer(0),
				tcpClient(1),
				udp(2),
				null(3)
				}
			MAX-ACCESS read-write
			STATUS current
			DESCRIPTION
				"Used to set or get the type used to transport.The default value is null(3),
				meaning current serial is not configured for any operating mode."
			::= { hwSocketTransEntry 2 }

		
--  1.3.6.1.4.1.2011.5.25.338.1.4.1.3
		hwSocketTransPacketSize OBJECT-TYPE
			SYNTAX Integer32 (0..1400)
			MAX-ACCESS read-write
			STATUS current
			DESCRIPTION
				"Used to set or get max size of trans packets.The setting range is 16 - 1400.0 is default value."
			::= { hwSocketTransEntry 3 }

		
--  1.3.6.1.4.1.2011.5.25.338.1.4.1.4
		hwSocketTransPacketTime OBJECT-TYPE
			SYNTAX Integer32
			MAX-ACCESS read-write
			STATUS current
			DESCRIPTION
				"Indicates the packet encapsulation timer,the default value is 100ms,parameter units is ms."
			DEFVAL { 100 }
			::= { hwSocketTransEntry 4 }

		
--  1.3.6.1.4.1.2011.5.25.338.1.4.1.5
		hwSocketTransSpecialChar OBJECT-TYPE
			SYNTAX Integer32 (0..255)
			MAX-ACCESS read-write
			STATUS current
			DESCRIPTION
				"Indicates the byte of special characters used to specifie a packet end."
			::= { hwSocketTransEntry 5 }

		
--  1.3.6.1.4.1.2011.5.25.338.1.4.1.6
		hwSocketTransClientIP OBJECT-TYPE
			SYNTAX IpAddress
			MAX-ACCESS read-write
			STATUS current
			DESCRIPTION
				"Indicate the client IP when the serial is worked in tcp server,
				this project can also be the client local IP when the serial is worked in tcp client or udp client."
			::= { hwSocketTransEntry 6 }

		
--  1.3.6.1.4.1.2011.5.25.338.1.4.1.7
		hwSocketTransClientPort OBJECT-TYPE
			SYNTAX Integer32
			MAX-ACCESS read-write
			STATUS current
			DESCRIPTION
				"Indicate the client port when the serial is worked in tcp server,
				this project can also be the client local port when the serial is worked in tcp client or udp client."
			::= { hwSocketTransEntry 7 }

		
--  1.3.6.1.4.1.2011.5.25.338.1.4.1.8
		hwSocketTransServerIP OBJECT-TYPE
			SYNTAX IpAddress
			MAX-ACCESS read-write
			STATUS current
			DESCRIPTION
				"Indicate the local server ip when the serial is worked in tcp server,
				this project can also be the server ip when the serial is worked in tcp client or udp client."
			::= { hwSocketTransEntry 8 }

		
--  1.3.6.1.4.1.2011.5.25.338.1.4.1.9
		hwSocketTransServerPort OBJECT-TYPE
			SYNTAX Integer32
			MAX-ACCESS read-write
			STATUS current
			DESCRIPTION
				"Indicate the local listening server port when the serial is worked in tcp server,
				this project can also be the server port when the serial is worked in tcp client or udp client"
			::= { hwSocketTransEntry 9 }

		
--  1.3.6.1.4.1.2011.5.25.338.1.4.1.10
		hwSocketTransTcpIdleTimeout OBJECT-TYPE
			SYNTAX Integer32 (0..60)
			MAX-ACCESS read-write
			STATUS current
			DESCRIPTION
				"Indicates the interval time of the tcp link keep alive."
			::= { hwSocketTransEntry 10 }

		
--  1.3.6.1.4.1.2011.5.25.338.1.4.1.11
		hwSocketTransBestEffort OBJECT-TYPE
			SYNTAX INTEGER { disable(0), enable(1)}
			MAX-ACCESS read-write
			STATUS current
			DESCRIPTION
				"When configuring a best effort mode, discarding older data cache first, otherwise discard newer data buffer."
			::= { hwSocketTransEntry 11 }

        hwRawModeSocketTransEnable OBJECT-TYPE
			SYNTAX INTEGER
				{
				disable(0),
				enable(1)
				}
			MAX-ACCESS read-write
			STATUS current
			DESCRIPTION
				"Used to enable or disable the transport business on serial.When the transport business is enable,do not allowed to set socket param."
			DEFVAL { disable }
			::= { hwSocketTransEntry 12 }

--  hwModbusTransTable Table 
-- 
		-- 1.3.6.1.4.1.2011.5.25.338.1.5
		hwModbusTransTable OBJECT-TYPE
			SYNTAX SEQUENCE OF HwModbusTransEntry
			MAX-ACCESS not-accessible
			STATUS current
			DESCRIPTION
				"Indicates the attribute of the conntection info of modbus.
				This table lists the connection info of the modbus interface."
			::= { hwARSerialConnectMIBObjects 5 }

		
		-- 1.3.6.1.4.1.2011.5.25.338.1.5.1
		hwModbusTransEntry OBJECT-TYPE
			SYNTAX HwModbusTransEntry
			MAX-ACCESS not-accessible
			STATUS current
			DESCRIPTION
				"Indicates the attribute of the conntection info of modbus.
				This table lists the connection info of the modbus interface."
			INDEX { hwTtyId }
			::= { hwModbusTransTable 1 }

		
		HwModbusTransEntry ::=
			SEQUENCE { 
				hwModbusTransEnable
					INTEGER,
				hwModbusTransServerIP
					IpAddress,
				hwModbusTransServerPort
					Integer32,
				hwModbusTransServerDestIP
					IpAddress,
				hwModbusTransServerDestPort
					Integer32,
				hwModbusTransServerFrameBufNum
					Integer32,       
			    hwModbusTransServerClientNum
			        Integer32,
				hwModbusTransSerialTimeout
					Integer32
			 }

		-- 1.3.6.1.4.1.2011.5.25.338.1.5.1.1
		hwModbusTransEnable OBJECT-TYPE
			SYNTAX INTEGER
				{
				disable(0),
				enable(1)
				}
			MAX-ACCESS read-write
			STATUS current
			DESCRIPTION
				"The object used to enable/disable the modbus transport."
			::= { hwModbusTransEntry 1 }

		
		-- 1.3.6.1.4.1.2011.5.25.338.1.5.1.2
		hwModbusTransServerIP OBJECT-TYPE
			SYNTAX IpAddress
			MAX-ACCESS read-write
			STATUS current
			DESCRIPTION
				"Indicates the Server IP of Modbus Transportation,the device as a server."
			::= { hwModbusTransEntry 2 }

		
		-- 1.3.6.1.4.1.2011.5.25.338.1.5.1.3
		hwModbusTransServerPort OBJECT-TYPE
			SYNTAX Integer32
			MAX-ACCESS read-write
			STATUS current
			DESCRIPTION
				"Indicates the Server Port of Modbus Transportation,the device as a server.
				Modbus used port is 502 + hwModbusTransServerPort."
			::= { hwModbusTransEntry 3 }

		
		-- 1.3.6.1.4.1.2011.5.25.338.1.5.1.4
		hwModbusTransServerDestIP OBJECT-TYPE
			SYNTAX IpAddress
			MAX-ACCESS read-write
			STATUS current
			DESCRIPTION
				"Indicates the remote ip addr,only this ip can connect to the modbus server."
			::= { hwModbusTransEntry 4 }

		
		-- 1.3.6.1.4.1.2011.5.25.338.1.5.1.5
		hwModbusTransServerDestPort OBJECT-TYPE
			SYNTAX Integer32
			MAX-ACCESS read-write
			STATUS current
			DESCRIPTION
				"Indicates the remote port,only this port can connect to the modbus server."
			::= { hwModbusTransEntry 5 }

		
		-- 1.3.6.1.4.1.2011.5.25.338.1.5.1.6
		hwModbusTransServerFrameBufNum OBJECT-TYPE
			SYNTAX Integer32 (1..6)
			MAX-ACCESS read-write
			STATUS current
			DESCRIPTION
				"Indicates the size of cache packets,the default value is 3."
			DEFVAL { 3 }
			::= { hwModbusTransEntry 6 }

        --  1.3.6.1.4.1.2011.5.25.338.1.5.1.7
		hwModbusTransServerClientNum OBJECT-TYPE
			SYNTAX Integer32 (1..4)
			MAX-ACCESS read-write
			STATUS current
			DESCRIPTION
				"Indicates the number of customers which allow to acess the server at the same time,
				the default value is 1."
			DEFVAL { 1 }
			::= { hwModbusTransEntry 7 }
		
		-- 1.3.6.1.4.1.2011.5.25.338.1.5.1.8
		hwModbusTransSerialTimeout OBJECT-TYPE
			SYNTAX Integer32 (1..10)
			MAX-ACCESS read-write
			STATUS current
			DESCRIPTION
				"Indicates the waitting time ,after the master send a message to the modbus slave."
			DEFVAL { 1 }
			::= { hwModbusTransEntry 8 }

--  1.3.6.1.4.1.2011.5.25.338.2
		hwARSerialConnectMIBNotifications OBJECT IDENTIFIER ::= { hwARSerialConnectMIB 2 }

		
--  1.3.6.1.4.1.2011.5.25.338.2.1
		hwGpioTraps OBJECT IDENTIFIER ::= { hwARSerialConnectMIBNotifications 1 }

		
--  1.3.6.1.4.1.2011.5.25.338.2.1.1
		hwGpioDILevelChange NOTIFICATION-TYPE
			OBJECTS { hwGpioId, hwGpioDIState }
			STATUS current
			DESCRIPTION 
				"The notification indicates that the current DI level has changed."
			::= { hwGpioTraps 1 }
--  1.3.6.1.4.1.2011.5.25.338.2.1.2
		hwGpioDIFailure NOTIFICATION-TYPE
			OBJECTS { hwGpioId, hwGpioDIState, hwGpioDIFailReason }
			STATUS current
			DESCRIPTION 
				"The GPIO DI state change fail reason."
			::= { hwGpioTraps 2 }
--  1.3.6.1.4.1.2011.5.25.338.2.1.3
		hwGpioDIRecovery NOTIFICATION-TYPE
			OBJECTS { hwGpioId, hwGpioDIState, hwGpioDIFailReason }
			STATUS current
			DESCRIPTION 
				"The GPIO DI state recovery."
			::= { hwGpioTraps 3 }



		
--    ============== conformance information ==============
-- 1.3.6.1.4.1.2011.5.25.338.3
		hwARSerialConnectConformance OBJECT IDENTIFIER ::= { hwARSerialConnectMIB 3 }

		
--  1.3.6.1.4.1.2011.5.25.338.3.1
		hwSerialConnectCompliances OBJECT IDENTIFIER ::= { hwARSerialConnectConformance 1 }

		
--   this module
-- 1.3.6.1.4.1.2011.5.25.338.3.1.1
		hwSerialConnectCompliance MODULE-COMPLIANCE
			STATUS current
			DESCRIPTION 
				"The compliance statement for systems supporting 
				the this module."
			MODULE HUAWEI-AR-SERIAL-CONNECT-MIB
				MANDATORY-GROUPS { hwGpioGroup, hwTransportSesionGroup, hwSocketTransGroup, hwGpioTrapsGroup, 
				hwTransSessionOperateGroup, hwModbusTransGroup}
			::= { hwSerialConnectCompliances 1 }

		
--    ============== groups ==============  
-- 1.3.6.1.4.1.2011.5.25.338.3.2
		hwSerialConnectGroups OBJECT IDENTIFIER ::= { hwARSerialConnectConformance 2 }

		
--  1.3.6.1.4.1.2011.5.25.338.3.2.1
		hwGpioGroup OBJECT-GROUP
			OBJECTS { hwGpioId, hwGpioMode, hwGpioDOLevel, hwGpioDIState, hwGpioDODefaultLevel
				 }
			STATUS current
			DESCRIPTION 
				"The GPIO group."
			::= { hwSerialConnectGroups 1 }

		
--  1.3.6.1.4.1.2011.5.25.338.3.2.2
		hwTransportSesionGroup OBJECT-GROUP
			OBJECTS {  hwTtyId, hwTransportMode, hwTransportRemoteIP, hwTransportRemotePort, hwConnectDuration, hwBytesReceived, 
				hwBytesSend, hwConnectionNum, hwRefuseConnectionNum, hwMsgStatics
				 }
			STATUS current
			DESCRIPTION 
				"The TransportSesion group."
			::= { hwSerialConnectGroups 2 }

		
--  1.3.6.1.4.1.2011.5.25.338.3.2.3
		hwTransSessionOperateGroup OBJECT-GROUP
			OBJECTS { hwTransSessionSessionID, hwTransSessionRowStatus, hwSessionIndex }
			STATUS current
			DESCRIPTION 
				"The TransportStatics group."
			::= { hwSerialConnectGroups 3 }

		
--  1.3.6.1.4.1.2011.5.25.338.3.2.4
		hwSocketTransGroup OBJECT-GROUP
			OBJECTS { hwSocketTransEnable, hwSocketTransType, hwSocketTransPacketSize, hwSocketTransPacketTime, hwSocketTransSpecialChar, 
				hwSocketTransBestEffort, hwSocketTransTcpIdleTimeout, hwSocketTransClientIP, 
				hwSocketTransClientPort, hwSocketTransServerIP, hwSocketTransServerPort,hwRawModeSocketTransEnable }
			STATUS current
			DESCRIPTION 
				"The SocketTrans group."
			::= { hwSerialConnectGroups 4 }

-- 1.3.6.1.4.1.2011.5.25.338.3.2.5
		hwModbusTransGroup OBJECT-GROUP
			OBJECTS { hwModbusTransEnable, hwModbusTransServerIP, hwModbusTransServerPort, hwModbusTransServerDestIP, hwModbusTransServerDestPort, 
				hwModbusTransServerFrameBufNum, hwModbusTransServerClientNum, hwModbusTransSerialTimeout }
			STATUS current
			DESCRIPTION 
				"The SPR Service group."
			::= { hwSerialConnectGroups 5 }
			
--  1.3.6.1.4.1.2011.5.25.338.3.2.6
		hwGpioTrapsGroup NOTIFICATION-GROUP
			NOTIFICATIONS { hwGpioDILevelChange }
			STATUS current
			DESCRIPTION 
				"The GpioTraps group."
			::= { hwSerialConnectGroups 6 }

		
	
	END

--
-- HUAWEI-AR-SERIAL-CONNECT-MIB.mib
--
